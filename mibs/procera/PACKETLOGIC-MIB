PACKETLOGIC-MIB DEFINITIONS ::= BEGIN

IMPORTS
	NOTIFICATION-TYPE,
	MODULE-IDENTITY, OBJECT-TYPE, Integer32, Counter64,
	Unsigned32, TimeTicks FROM SNMPv2-SMI
	enterprises FROM SNMPv2-SMI
	DisplayString, DateAndTime FROM SNMPv2-TC
	CounterBasedGauge64 FROM HCNUM-TC;

procera MODULE-IDENTITY
	LAST-UPDATED "201909121500Z"
	ORGANIZATION "Procera Networks, Inc."
	CONTACT-INFO "support@proceranetworks.com"
	DESCRIPTION "MIB for PacketLogic2"
	REVISION "201909121500Z"
	DESCRIPTION " Latest version at the revision date for version GET VERSION HERE"

	::={enterprises 15397}
packetlogic2	OBJECT IDENTIFIER ::={procera 2}

plm	OBJECT IDENTIFIER ::={procera 3}

pbs	OBJECT IDENTIFIER ::={procera 4}

sysdiag	OBJECT IDENTIFIER ::={packetlogic2 1}

channelstats	OBJECT IDENTIFIER ::={packetlogic2 2}

pl2Trap	OBJECT IDENTIFIER ::={packetlogic2 8}

snoopers	OBJECT IDENTIFIER ::={packetlogic2 10}

dynamiczones	OBJECT IDENTIFIER ::={packetlogic2 20}

packetprocessing	OBJECT IDENTIFIER ::={sysdiag 8}

packetprocessingRx	OBJECT IDENTIFIER ::={packetprocessing 1}

packetprocessingRxVal	OBJECT-TYPE
	SYNTAX	 Counter64
	MAX-ACCESS read-only
	STATUS current
	DESCRIPTION "RX packets"

	::={packetprocessingRx 1}

packetprocessingRxMom	OBJECT-TYPE
	SYNTAX	 CounterBasedGauge64
	MAX-ACCESS read-only
	STATUS current
	DESCRIPTION "RX packets"

	::={packetprocessingRx 2}

packetprocessingRxMax	OBJECT-TYPE
	SYNTAX	 CounterBasedGauge64
	MAX-ACCESS read-only
	STATUS current
	DESCRIPTION "RX packets"

	::={packetprocessingRx 3}

packetprocessingRxLevelTable OBJECT-TYPE
	SYNTAX      SEQUENCE OF PacketprocessingRxLevelEntry
	MAX-ACCESS  not-accessible
	STATUS      current
	DESCRIPTION
	"Table for packetprocessingRx"
	::={packetprocessingRx 4}

packetprocessingRxLevelEntry OBJECT-TYPE
	SYNTAX      PacketprocessingRxLevelEntry
	MAX-ACCESS  not-accessible
	STATUS      current
	DESCRIPTION
	"Table entry for packetprocessingRx"
	INDEX { packetprocessingRxLevelName }
	::={packetprocessingRxLevelTable 1}

PacketprocessingRxLevelEntry ::=
	SEQUENCE {
		packetprocessingRxLevelName	DisplayString,
		packetprocessingRxLevelVal	Counter64,
		packetprocessingRxLevelMom	CounterBasedGauge64,
		packetprocessingRxLevelMax	CounterBasedGauge64
	}

packetprocessingRxLevelName OBJECT-TYPE
	SYNTAX      DisplayString
	MAX-ACCESS  not-accessible
	STATUS      current
	DESCRIPTION
	"Table entry display string for packetprocessingRx"
	::={packetprocessingRxLevelEntry 1}

packetprocessingRxLevelVal OBJECT-TYPE
	SYNTAX	 Counter64
	MAX-ACCESS  read-only
	STATUS      current
	DESCRIPTION
	"Table entry attribute for packetprocessingRx"
	::={packetprocessingRxLevelEntry 2}

packetprocessingRxLevelMom OBJECT-TYPE
	SYNTAX	 CounterBasedGauge64
	MAX-ACCESS  read-only
	STATUS      current
	DESCRIPTION
	"Table entry attribute for packetprocessingRx"
	::={packetprocessingRxLevelEntry 3}

packetprocessingRxLevelMax OBJECT-TYPE
	SYNTAX	 CounterBasedGauge64
	MAX-ACCESS  read-only
	STATUS      current
	DESCRIPTION
	"Table entry attribute for packetprocessingRx"
	::={packetprocessingRxLevelEntry 4}


packetprocessingRxDrops	OBJECT IDENTIFIER ::={packetprocessing 2}

packetprocessingRxDropsVal	OBJECT-TYPE
	SYNTAX	 Counter64
	MAX-ACCESS read-only
	STATUS current
	DESCRIPTION "RX drops"

	::={packetprocessingRxDrops 1}

packetprocessingRxDropsMom	OBJECT-TYPE
	SYNTAX	 CounterBasedGauge64
	MAX-ACCESS read-only
	STATUS current
	DESCRIPTION "RX drops"

	::={packetprocessingRxDrops 2}

packetprocessingRxDropsMax	OBJECT-TYPE
	SYNTAX	 CounterBasedGauge64
	MAX-ACCESS read-only
	STATUS current
	DESCRIPTION "RX drops"

	::={packetprocessingRxDrops 3}

packetprocessingRxDropsLevelTable OBJECT-TYPE
	SYNTAX      SEQUENCE OF PacketprocessingRxDropsLevelEntry
	MAX-ACCESS  not-accessible
	STATUS      current
	DESCRIPTION
	"Table for packetprocessingRxDrops"
	::={packetprocessingRxDrops 4}

packetprocessingRxDropsLevelEntry OBJECT-TYPE
	SYNTAX      PacketprocessingRxDropsLevelEntry
	MAX-ACCESS  not-accessible
	STATUS      current
	DESCRIPTION
	"Table entry for packetprocessingRxDrops"
	INDEX { packetprocessingRxDropsLevelName }
	::={packetprocessingRxDropsLevelTable 1}

PacketprocessingRxDropsLevelEntry ::=
	SEQUENCE {
		packetprocessingRxDropsLevelName	DisplayString,
		packetprocessingRxDropsLevelVal	Counter64,
		packetprocessingRxDropsLevelMom	CounterBasedGauge64,
		packetprocessingRxDropsLevelMax	CounterBasedGauge64
	}

packetprocessingRxDropsLevelName OBJECT-TYPE
	SYNTAX      DisplayString
	MAX-ACCESS  not-accessible
	STATUS      current
	DESCRIPTION
	"Table entry display string for packetprocessingRxDrops"
	::={packetprocessingRxDropsLevelEntry 1}

packetprocessingRxDropsLevelVal OBJECT-TYPE
	SYNTAX	 Counter64
	MAX-ACCESS  read-only
	STATUS      current
	DESCRIPTION
	"Table entry attribute for packetprocessingRxDrops"
	::={packetprocessingRxDropsLevelEntry 2}

packetprocessingRxDropsLevelMom OBJECT-TYPE
	SYNTAX	 CounterBasedGauge64
	MAX-ACCESS  read-only
	STATUS      current
	DESCRIPTION
	"Table entry attribute for packetprocessingRxDrops"
	::={packetprocessingRxDropsLevelEntry 3}

packetprocessingRxDropsLevelMax OBJECT-TYPE
	SYNTAX	 CounterBasedGauge64
	MAX-ACCESS  read-only
	STATUS      current
	DESCRIPTION
	"Table entry attribute for packetprocessingRxDrops"
	::={packetprocessingRxDropsLevelEntry 4}


packetprocessingTx	OBJECT IDENTIFIER ::={packetprocessing 6}

packetprocessingTxVal	OBJECT-TYPE
	SYNTAX	 Counter64
	MAX-ACCESS read-only
	STATUS current
	DESCRIPTION "TX packets"

	::={packetprocessingTx 1}

packetprocessingTxMom	OBJECT-TYPE
	SYNTAX	 CounterBasedGauge64
	MAX-ACCESS read-only
	STATUS current
	DESCRIPTION "TX packets"

	::={packetprocessingTx 2}

packetprocessingTxMax	OBJECT-TYPE
	SYNTAX	 CounterBasedGauge64
	MAX-ACCESS read-only
	STATUS current
	DESCRIPTION "TX packets"

	::={packetprocessingTx 3}

packetprocessingTxLevelTable OBJECT-TYPE
	SYNTAX      SEQUENCE OF PacketprocessingTxLevelEntry
	MAX-ACCESS  not-accessible
	STATUS      current
	DESCRIPTION
	"Table for packetprocessingTx"
	::={packetprocessingTx 4}

packetprocessingTxLevelEntry OBJECT-TYPE
	SYNTAX      PacketprocessingTxLevelEntry
	MAX-ACCESS  not-accessible
	STATUS      current
	DESCRIPTION
	"Table entry for packetprocessingTx"
	INDEX { packetprocessingTxLevelName }
	::={packetprocessingTxLevelTable 1}

PacketprocessingTxLevelEntry ::=
	SEQUENCE {
		packetprocessingTxLevelName	DisplayString,
		packetprocessingTxLevelVal	Counter64,
		packetprocessingTxLevelMom	CounterBasedGauge64,
		packetprocessingTxLevelMax	CounterBasedGauge64
	}

packetprocessingTxLevelName OBJECT-TYPE
	SYNTAX      DisplayString
	MAX-ACCESS  not-accessible
	STATUS      current
	DESCRIPTION
	"Table entry display string for packetprocessingTx"
	::={packetprocessingTxLevelEntry 1}

packetprocessingTxLevelVal OBJECT-TYPE
	SYNTAX	 Counter64
	MAX-ACCESS  read-only
	STATUS      current
	DESCRIPTION
	"Table entry attribute for packetprocessingTx"
	::={packetprocessingTxLevelEntry 2}

packetprocessingTxLevelMom OBJECT-TYPE
	SYNTAX	 CounterBasedGauge64
	MAX-ACCESS  read-only
	STATUS      current
	DESCRIPTION
	"Table entry attribute for packetprocessingTx"
	::={packetprocessingTxLevelEntry 3}

packetprocessingTxLevelMax OBJECT-TYPE
	SYNTAX	 CounterBasedGauge64
	MAX-ACCESS  read-only
	STATUS      current
	DESCRIPTION
	"Table entry attribute for packetprocessingTx"
	::={packetprocessingTxLevelEntry 4}


packetprocessingTxDrops	OBJECT IDENTIFIER ::={packetprocessing 7}

packetprocessingTxDropsVal	OBJECT-TYPE
	SYNTAX	 Counter64
	MAX-ACCESS read-only
	STATUS current
	DESCRIPTION "TX drops"

	::={packetprocessingTxDrops 1}

packetprocessingTxDropsMom	OBJECT-TYPE
	SYNTAX	 CounterBasedGauge64
	MAX-ACCESS read-only
	STATUS current
	DESCRIPTION "TX drops"

	::={packetprocessingTxDrops 2}

packetprocessingTxDropsMax	OBJECT-TYPE
	SYNTAX	 CounterBasedGauge64
	MAX-ACCESS read-only
	STATUS current
	DESCRIPTION "TX drops"

	::={packetprocessingTxDrops 3}

packetprocessingTxDropsLevelTable OBJECT-TYPE
	SYNTAX      SEQUENCE OF PacketprocessingTxDropsLevelEntry
	MAX-ACCESS  not-accessible
	STATUS      current
	DESCRIPTION
	"Table for packetprocessingTxDrops"
	::={packetprocessingTxDrops 4}

packetprocessingTxDropsLevelEntry OBJECT-TYPE
	SYNTAX      PacketprocessingTxDropsLevelEntry
	MAX-ACCESS  not-accessible
	STATUS      current
	DESCRIPTION
	"Table entry for packetprocessingTxDrops"
	INDEX { packetprocessingTxDropsLevelName }
	::={packetprocessingTxDropsLevelTable 1}

PacketprocessingTxDropsLevelEntry ::=
	SEQUENCE {
		packetprocessingTxDropsLevelName	DisplayString,
		packetprocessingTxDropsLevelVal	Counter64,
		packetprocessingTxDropsLevelMom	CounterBasedGauge64,
		packetprocessingTxDropsLevelMax	CounterBasedGauge64
	}

packetprocessingTxDropsLevelName OBJECT-TYPE
	SYNTAX      DisplayString
	MAX-ACCESS  not-accessible
	STATUS      current
	DESCRIPTION
	"Table entry display string for packetprocessingTxDrops"
	::={packetprocessingTxDropsLevelEntry 1}

packetprocessingTxDropsLevelVal OBJECT-TYPE
	SYNTAX	 Counter64
	MAX-ACCESS  read-only
	STATUS      current
	DESCRIPTION
	"Table entry attribute for packetprocessingTxDrops"
	::={packetprocessingTxDropsLevelEntry 2}

packetprocessingTxDropsLevelMom OBJECT-TYPE
	SYNTAX	 CounterBasedGauge64
	MAX-ACCESS  read-only
	STATUS      current
	DESCRIPTION
	"Table entry attribute for packetprocessingTxDrops"
	::={packetprocessingTxDropsLevelEntry 3}

packetprocessingTxDropsLevelMax OBJECT-TYPE
	SYNTAX	 CounterBasedGauge64
	MAX-ACCESS  read-only
	STATUS      current
	DESCRIPTION
	"Table entry attribute for packetprocessingTxDrops"
	::={packetprocessingTxDropsLevelEntry 4}


packetprocessingPacketPoolSize	OBJECT IDENTIFIER ::={packetprocessing 10}

packetprocessingPacketPoolSizeVal	OBJECT-TYPE
	SYNTAX	 CounterBasedGauge64
	MAX-ACCESS read-only
	STATUS current
	DESCRIPTION "Packets left in pool"

	::={packetprocessingPacketPoolSize 1}

packetprocessingPacketPoolSizeMax	OBJECT-TYPE
	SYNTAX	 CounterBasedGauge64
	MAX-ACCESS read-only
	STATUS current
	DESCRIPTION "Packets left in pool"

	::={packetprocessingPacketPoolSize 3}

packetprocessingPacketPoolSizeLevelTable OBJECT-TYPE
	SYNTAX      SEQUENCE OF PacketprocessingPacketPoolSizeLevelEntry
	MAX-ACCESS  not-accessible
	STATUS      current
	DESCRIPTION
	"Table for packetprocessingPacketPoolSize"
	::={packetprocessingPacketPoolSize 4}

packetprocessingPacketPoolSizeLevelEntry OBJECT-TYPE
	SYNTAX      PacketprocessingPacketPoolSizeLevelEntry
	MAX-ACCESS  not-accessible
	STATUS      current
	DESCRIPTION
	"Table entry for packetprocessingPacketPoolSize"
	INDEX { packetprocessingPacketPoolSizeLevelName }
	::={packetprocessingPacketPoolSizeLevelTable 1}

PacketprocessingPacketPoolSizeLevelEntry ::=
	SEQUENCE {
		packetprocessingPacketPoolSizeLevelName	DisplayString,
		packetprocessingPacketPoolSizeLevelVal	CounterBasedGauge64,
		packetprocessingPacketPoolSizeLevelMax	CounterBasedGauge64
	}

packetprocessingPacketPoolSizeLevelName OBJECT-TYPE
	SYNTAX      DisplayString
	MAX-ACCESS  not-accessible
	STATUS      current
	DESCRIPTION
	"Table entry display string for packetprocessingPacketPoolSize"
	::={packetprocessingPacketPoolSizeLevelEntry 1}

packetprocessingPacketPoolSizeLevelVal OBJECT-TYPE
	SYNTAX	 CounterBasedGauge64
	MAX-ACCESS  read-only
	STATUS      current
	DESCRIPTION
	"Table entry attribute for packetprocessingPacketPoolSize"
	::={packetprocessingPacketPoolSizeLevelEntry 2}

packetprocessingPacketPoolSizeLevelMax OBJECT-TYPE
	SYNTAX	 CounterBasedGauge64
	MAX-ACCESS  read-only
	STATUS      current
	DESCRIPTION
	"Table entry attribute for packetprocessingPacketPoolSize"
	::={packetprocessingPacketPoolSizeLevelEntry 4}


packetprocessingDmaAllocs	OBJECT IDENTIFIER ::={packetprocessing 13}

packetprocessingDmaAllocsVal	OBJECT-TYPE
	SYNTAX	 CounterBasedGauge64
	MAX-ACCESS read-only
	STATUS current
	DESCRIPTION "DMA-allocated packets"

	::={packetprocessingDmaAllocs 1}

packetprocessingDmaAllocsMax	OBJECT-TYPE
	SYNTAX	 CounterBasedGauge64
	MAX-ACCESS read-only
	STATUS current
	DESCRIPTION "DMA-allocated packets"

	::={packetprocessingDmaAllocs 3}

packetprocessingDmaAllocsLevelTable OBJECT-TYPE
	SYNTAX      SEQUENCE OF PacketprocessingDmaAllocsLevelEntry
	MAX-ACCESS  not-accessible
	STATUS      current
	DESCRIPTION
	"Table for packetprocessingDmaAllocs"
	::={packetprocessingDmaAllocs 4}

packetprocessingDmaAllocsLevelEntry OBJECT-TYPE
	SYNTAX      PacketprocessingDmaAllocsLevelEntry
	MAX-ACCESS  not-accessible
	STATUS      current
	DESCRIPTION
	"Table entry for packetprocessingDmaAllocs"
	INDEX { packetprocessingDmaAllocsLevelName }
	::={packetprocessingDmaAllocsLevelTable 1}

PacketprocessingDmaAllocsLevelEntry ::=
	SEQUENCE {
		packetprocessingDmaAllocsLevelName	DisplayString,
		packetprocessingDmaAllocsLevelVal	CounterBasedGauge64,
		packetprocessingDmaAllocsLevelMax	CounterBasedGauge64
	}

packetprocessingDmaAllocsLevelName OBJECT-TYPE
	SYNTAX      DisplayString
	MAX-ACCESS  not-accessible
	STATUS      current
	DESCRIPTION
	"Table entry display string for packetprocessingDmaAllocs"
	::={packetprocessingDmaAllocsLevelEntry 1}

packetprocessingDmaAllocsLevelVal OBJECT-TYPE
	SYNTAX	 CounterBasedGauge64
	MAX-ACCESS  read-only
	STATUS      current
	DESCRIPTION
	"Table entry attribute for packetprocessingDmaAllocs"
	::={packetprocessingDmaAllocsLevelEntry 2}

packetprocessingDmaAllocsLevelMax OBJECT-TYPE
	SYNTAX	 CounterBasedGauge64
	MAX-ACCESS  read-only
	STATUS      current
	DESCRIPTION
	"Table entry attribute for packetprocessingDmaAllocs"
	::={packetprocessingDmaAllocsLevelEntry 4}


packetprocessingLoad	OBJECT IDENTIFIER ::={packetprocessing 15}

packetprocessingLoadVal	OBJECT-TYPE
	SYNTAX	 Unsigned32
	MAX-ACCESS read-only
	STATUS current
	DESCRIPTION "CPU Load"

	::={packetprocessingLoad 1}

packetprocessingLoadMax	OBJECT-TYPE
	SYNTAX	 Unsigned32
	MAX-ACCESS read-only
	STATUS current
	DESCRIPTION "CPU Load"

	::={packetprocessingLoad 3}

packetprocessingLoadLevelTable OBJECT-TYPE
	SYNTAX      SEQUENCE OF PacketprocessingLoadLevelEntry
	MAX-ACCESS  not-accessible
	STATUS      current
	DESCRIPTION
	"Table for packetprocessingLoad"
	::={packetprocessingLoad 4}

packetprocessingLoadLevelEntry OBJECT-TYPE
	SYNTAX      PacketprocessingLoadLevelEntry
	MAX-ACCESS  not-accessible
	STATUS      current
	DESCRIPTION
	"Table entry for packetprocessingLoad"
	INDEX { packetprocessingLoadLevelName }
	::={packetprocessingLoadLevelTable 1}

PacketprocessingLoadLevelEntry ::=
	SEQUENCE {
		packetprocessingLoadLevelName	DisplayString,
		packetprocessingLoadLevelVal	Unsigned32,
		packetprocessingLoadLevelMax	Unsigned32
	}

packetprocessingLoadLevelName OBJECT-TYPE
	SYNTAX      DisplayString
	MAX-ACCESS  not-accessible
	STATUS      current
	DESCRIPTION
	"Table entry display string for packetprocessingLoad"
	::={packetprocessingLoadLevelEntry 1}

packetprocessingLoadLevelVal OBJECT-TYPE
	SYNTAX	 Unsigned32
	MAX-ACCESS  read-only
	STATUS      current
	DESCRIPTION
	"Table entry attribute for packetprocessingLoad"
	::={packetprocessingLoadLevelEntry 2}

packetprocessingLoadLevelMax OBJECT-TYPE
	SYNTAX	 Unsigned32
	MAX-ACCESS  read-only
	STATUS      current
	DESCRIPTION
	"Table entry attribute for packetprocessingLoad"
	::={packetprocessingLoadLevelEntry 4}


packetprocessingUptime	OBJECT IDENTIFIER ::={packetprocessing 17}

packetprocessingUptimeVal	OBJECT-TYPE
	SYNTAX	 TimeTicks
	MAX-ACCESS read-only
	STATUS current
	DESCRIPTION "CPU uptime"

	::={packetprocessingUptime 1}

packetprocessingUptimeLevelTable OBJECT-TYPE
	SYNTAX      SEQUENCE OF PacketprocessingUptimeLevelEntry
	MAX-ACCESS  not-accessible
	STATUS      current
	DESCRIPTION
	"Table for packetprocessingUptime"
	::={packetprocessingUptime 2}

packetprocessingUptimeLevelEntry OBJECT-TYPE
	SYNTAX      PacketprocessingUptimeLevelEntry
	MAX-ACCESS  not-accessible
	STATUS      current
	DESCRIPTION
	"Table entry for packetprocessingUptime"
	INDEX { packetprocessingUptimeLevelName }
	::={packetprocessingUptimeLevelTable 1}

PacketprocessingUptimeLevelEntry ::=
	SEQUENCE {
		packetprocessingUptimeLevelName	DisplayString,
		packetprocessingUptimeLevelVal	TimeTicks
	}

packetprocessingUptimeLevelName OBJECT-TYPE
	SYNTAX      DisplayString
	MAX-ACCESS  not-accessible
	STATUS      current
	DESCRIPTION
	"Table entry display string for packetprocessingUptime"
	::={packetprocessingUptimeLevelEntry 1}

packetprocessingUptimeLevelVal OBJECT-TYPE
	SYNTAX	 TimeTicks
	MAX-ACCESS  read-only
	STATUS      current
	DESCRIPTION
	"Table entry attribute for packetprocessingUptime"
	::={packetprocessingUptimeLevelEntry 2}


packetprocessingHeapfree	OBJECT IDENTIFIER ::={packetprocessing 16}

packetprocessingHeapfreeVal	OBJECT-TYPE
	SYNTAX	 CounterBasedGauge64
	MAX-ACCESS read-only
	STATUS current
	DESCRIPTION "Free memory"

	::={packetprocessingHeapfree 1}

packetprocessingHeapfreeMax	OBJECT-TYPE
	SYNTAX	 CounterBasedGauge64
	MAX-ACCESS read-only
	STATUS current
	DESCRIPTION "Free memory"

	::={packetprocessingHeapfree 3}

packetprocessingHeapfreeLevelTable OBJECT-TYPE
	SYNTAX      SEQUENCE OF PacketprocessingHeapfreeLevelEntry
	MAX-ACCESS  not-accessible
	STATUS      current
	DESCRIPTION
	"Table for packetprocessingHeapfree"
	::={packetprocessingHeapfree 4}

packetprocessingHeapfreeLevelEntry OBJECT-TYPE
	SYNTAX      PacketprocessingHeapfreeLevelEntry
	MAX-ACCESS  not-accessible
	STATUS      current
	DESCRIPTION
	"Table entry for packetprocessingHeapfree"
	INDEX { packetprocessingHeapfreeLevelName }
	::={packetprocessingHeapfreeLevelTable 1}

PacketprocessingHeapfreeLevelEntry ::=
	SEQUENCE {
		packetprocessingHeapfreeLevelName	DisplayString,
		packetprocessingHeapfreeLevelVal	CounterBasedGauge64,
		packetprocessingHeapfreeLevelMax	CounterBasedGauge64
	}

packetprocessingHeapfreeLevelName OBJECT-TYPE
	SYNTAX      DisplayString
	MAX-ACCESS  not-accessible
	STATUS      current
	DESCRIPTION
	"Table entry display string for packetprocessingHeapfree"
	::={packetprocessingHeapfreeLevelEntry 1}

packetprocessingHeapfreeLevelVal OBJECT-TYPE
	SYNTAX	 CounterBasedGauge64
	MAX-ACCESS  read-only
	STATUS      current
	DESCRIPTION
	"Table entry attribute for packetprocessingHeapfree"
	::={packetprocessingHeapfreeLevelEntry 2}

packetprocessingHeapfreeLevelMax OBJECT-TYPE
	SYNTAX	 CounterBasedGauge64
	MAX-ACCESS  read-only
	STATUS      current
	DESCRIPTION
	"Table entry attribute for packetprocessingHeapfree"
	::={packetprocessingHeapfreeLevelEntry 4}


packetprocessingPushbackQueueFull	OBJECT IDENTIFIER ::={packetprocessing 18}

packetprocessingPushbackQueueFullVal	OBJECT-TYPE
	SYNTAX	 Counter64
	MAX-ACCESS read-only
	STATUS obsolete
	DESCRIPTION "Push back queue full"

	::={packetprocessingPushbackQueueFull 1}

packetprocessingPushbackQueueFullMom	OBJECT-TYPE
	SYNTAX	 CounterBasedGauge64
	MAX-ACCESS read-only
	STATUS obsolete
	DESCRIPTION "Push back queue full"

	::={packetprocessingPushbackQueueFull 2}

packetprocessingPushbackQueueFullMax	OBJECT-TYPE
	SYNTAX	 CounterBasedGauge64
	MAX-ACCESS read-only
	STATUS obsolete
	DESCRIPTION "Push back queue full"

	::={packetprocessingPushbackQueueFull 3}

packetprocessingPushbackQueueFullLevelTable OBJECT-TYPE
	SYNTAX      SEQUENCE OF PacketprocessingPushbackQueueFullLevelEntry
	MAX-ACCESS  not-accessible
	STATUS      current
	DESCRIPTION
	"Table for packetprocessingPushbackQueueFull"
	::={packetprocessingPushbackQueueFull 4}

packetprocessingPushbackQueueFullLevelEntry OBJECT-TYPE
	SYNTAX      PacketprocessingPushbackQueueFullLevelEntry
	MAX-ACCESS  not-accessible
	STATUS      current
	DESCRIPTION
	"Table entry for packetprocessingPushbackQueueFull"
	INDEX { packetprocessingPushbackQueueFullLevelName }
	::={packetprocessingPushbackQueueFullLevelTable 1}

PacketprocessingPushbackQueueFullLevelEntry ::=
	SEQUENCE {
		packetprocessingPushbackQueueFullLevelName	DisplayString,
		packetprocessingPushbackQueueFullLevelVal	Counter64,
		packetprocessingPushbackQueueFullLevelMom	CounterBasedGauge64,
		packetprocessingPushbackQueueFullLevelMax	CounterBasedGauge64
	}

packetprocessingPushbackQueueFullLevelName OBJECT-TYPE
	SYNTAX      DisplayString
	MAX-ACCESS  not-accessible
	STATUS      current
	DESCRIPTION
	"Table entry display string for packetprocessingPushbackQueueFull"
	::={packetprocessingPushbackQueueFullLevelEntry 1}

packetprocessingPushbackQueueFullLevelVal OBJECT-TYPE
	SYNTAX	 Counter64
	MAX-ACCESS  read-only
	STATUS      current
	DESCRIPTION
	"Table entry attribute for packetprocessingPushbackQueueFull"
	::={packetprocessingPushbackQueueFullLevelEntry 2}

packetprocessingPushbackQueueFullLevelMom OBJECT-TYPE
	SYNTAX	 CounterBasedGauge64
	MAX-ACCESS  read-only
	STATUS      current
	DESCRIPTION
	"Table entry attribute for packetprocessingPushbackQueueFull"
	::={packetprocessingPushbackQueueFullLevelEntry 3}

packetprocessingPushbackQueueFullLevelMax OBJECT-TYPE
	SYNTAX	 CounterBasedGauge64
	MAX-ACCESS  read-only
	STATUS      current
	DESCRIPTION
	"Table entry attribute for packetprocessingPushbackQueueFull"
	::={packetprocessingPushbackQueueFullLevelEntry 4}


packetprocessingPushbackPackets	OBJECT IDENTIFIER ::={packetprocessing 19}

packetprocessingPushbackPacketsVal	OBJECT-TYPE
	SYNTAX	 Counter64
	MAX-ACCESS read-only
	STATUS obsolete
	DESCRIPTION "Push back packets"

	::={packetprocessingPushbackPackets 1}

packetprocessingPushbackPacketsMom	OBJECT-TYPE
	SYNTAX	 CounterBasedGauge64
	MAX-ACCESS read-only
	STATUS obsolete
	DESCRIPTION "Push back packets"

	::={packetprocessingPushbackPackets 2}

packetprocessingPushbackPacketsMax	OBJECT-TYPE
	SYNTAX	 CounterBasedGauge64
	MAX-ACCESS read-only
	STATUS obsolete
	DESCRIPTION "Push back packets"

	::={packetprocessingPushbackPackets 3}

packetprocessingPushbackPacketsLevelTable OBJECT-TYPE
	SYNTAX      SEQUENCE OF PacketprocessingPushbackPacketsLevelEntry
	MAX-ACCESS  not-accessible
	STATUS      current
	DESCRIPTION
	"Table for packetprocessingPushbackPackets"
	::={packetprocessingPushbackPackets 4}

packetprocessingPushbackPacketsLevelEntry OBJECT-TYPE
	SYNTAX      PacketprocessingPushbackPacketsLevelEntry
	MAX-ACCESS  not-accessible
	STATUS      current
	DESCRIPTION
	"Table entry for packetprocessingPushbackPackets"
	INDEX { packetprocessingPushbackPacketsLevelName }
	::={packetprocessingPushbackPacketsLevelTable 1}

PacketprocessingPushbackPacketsLevelEntry ::=
	SEQUENCE {
		packetprocessingPushbackPacketsLevelName	DisplayString,
		packetprocessingPushbackPacketsLevelVal	Counter64,
		packetprocessingPushbackPacketsLevelMom	CounterBasedGauge64,
		packetprocessingPushbackPacketsLevelMax	CounterBasedGauge64
	}

packetprocessingPushbackPacketsLevelName OBJECT-TYPE
	SYNTAX      DisplayString
	MAX-ACCESS  not-accessible
	STATUS      current
	DESCRIPTION
	"Table entry display string for packetprocessingPushbackPackets"
	::={packetprocessingPushbackPacketsLevelEntry 1}

packetprocessingPushbackPacketsLevelVal OBJECT-TYPE
	SYNTAX	 Counter64
	MAX-ACCESS  read-only
	STATUS      current
	DESCRIPTION
	"Table entry attribute for packetprocessingPushbackPackets"
	::={packetprocessingPushbackPacketsLevelEntry 2}

packetprocessingPushbackPacketsLevelMom OBJECT-TYPE
	SYNTAX	 CounterBasedGauge64
	MAX-ACCESS  read-only
	STATUS      current
	DESCRIPTION
	"Table entry attribute for packetprocessingPushbackPackets"
	::={packetprocessingPushbackPacketsLevelEntry 3}

packetprocessingPushbackPacketsLevelMax OBJECT-TYPE
	SYNTAX	 CounterBasedGauge64
	MAX-ACCESS  read-only
	STATUS      current
	DESCRIPTION
	"Table entry attribute for packetprocessingPushbackPackets"
	::={packetprocessingPushbackPacketsLevelEntry 4}


packetprocessingPushbackQueueSize	OBJECT IDENTIFIER ::={packetprocessing 20}

packetprocessingPushbackQueueSizeVal	OBJECT-TYPE
	SYNTAX	 CounterBasedGauge64
	MAX-ACCESS read-only
	STATUS obsolete
	DESCRIPTION "Push back queue size"

	::={packetprocessingPushbackQueueSize 1}

packetprocessingPushbackQueueSizeMax	OBJECT-TYPE
	SYNTAX	 CounterBasedGauge64
	MAX-ACCESS read-only
	STATUS obsolete
	DESCRIPTION "Push back queue size"

	::={packetprocessingPushbackQueueSize 3}

packetprocessingPushbackQueueSizeLevelTable OBJECT-TYPE
	SYNTAX      SEQUENCE OF PacketprocessingPushbackQueueSizeLevelEntry
	MAX-ACCESS  not-accessible
	STATUS      current
	DESCRIPTION
	"Table for packetprocessingPushbackQueueSize"
	::={packetprocessingPushbackQueueSize 4}

packetprocessingPushbackQueueSizeLevelEntry OBJECT-TYPE
	SYNTAX      PacketprocessingPushbackQueueSizeLevelEntry
	MAX-ACCESS  not-accessible
	STATUS      current
	DESCRIPTION
	"Table entry for packetprocessingPushbackQueueSize"
	INDEX { packetprocessingPushbackQueueSizeLevelName }
	::={packetprocessingPushbackQueueSizeLevelTable 1}

PacketprocessingPushbackQueueSizeLevelEntry ::=
	SEQUENCE {
		packetprocessingPushbackQueueSizeLevelName	DisplayString,
		packetprocessingPushbackQueueSizeLevelVal	CounterBasedGauge64,
		packetprocessingPushbackQueueSizeLevelMax	CounterBasedGauge64
	}

packetprocessingPushbackQueueSizeLevelName OBJECT-TYPE
	SYNTAX      DisplayString
	MAX-ACCESS  not-accessible
	STATUS      current
	DESCRIPTION
	"Table entry display string for packetprocessingPushbackQueueSize"
	::={packetprocessingPushbackQueueSizeLevelEntry 1}

packetprocessingPushbackQueueSizeLevelVal OBJECT-TYPE
	SYNTAX	 CounterBasedGauge64
	MAX-ACCESS  read-only
	STATUS      current
	DESCRIPTION
	"Table entry attribute for packetprocessingPushbackQueueSize"
	::={packetprocessingPushbackQueueSizeLevelEntry 2}

packetprocessingPushbackQueueSizeLevelMax OBJECT-TYPE
	SYNTAX	 CounterBasedGauge64
	MAX-ACCESS  read-only
	STATUS      current
	DESCRIPTION
	"Table entry attribute for packetprocessingPushbackQueueSize"
	::={packetprocessingPushbackQueueSizeLevelEntry 4}


packetprocessingPushbackRequeues	OBJECT IDENTIFIER ::={packetprocessing 21}

packetprocessingPushbackRequeuesVal	OBJECT-TYPE
	SYNTAX	 Counter64
	MAX-ACCESS read-only
	STATUS obsolete
	DESCRIPTION "Push back requeues"

	::={packetprocessingPushbackRequeues 1}

packetprocessingPushbackRequeuesMom	OBJECT-TYPE
	SYNTAX	 CounterBasedGauge64
	MAX-ACCESS read-only
	STATUS obsolete
	DESCRIPTION "Push back requeues"

	::={packetprocessingPushbackRequeues 2}

packetprocessingPushbackRequeuesMax	OBJECT-TYPE
	SYNTAX	 CounterBasedGauge64
	MAX-ACCESS read-only
	STATUS obsolete
	DESCRIPTION "Push back requeues"

	::={packetprocessingPushbackRequeues 3}

packetprocessingPushbackRequeuesLevelTable OBJECT-TYPE
	SYNTAX      SEQUENCE OF PacketprocessingPushbackRequeuesLevelEntry
	MAX-ACCESS  not-accessible
	STATUS      current
	DESCRIPTION
	"Table for packetprocessingPushbackRequeues"
	::={packetprocessingPushbackRequeues 4}

packetprocessingPushbackRequeuesLevelEntry OBJECT-TYPE
	SYNTAX      PacketprocessingPushbackRequeuesLevelEntry
	MAX-ACCESS  not-accessible
	STATUS      current
	DESCRIPTION
	"Table entry for packetprocessingPushbackRequeues"
	INDEX { packetprocessingPushbackRequeuesLevelName }
	::={packetprocessingPushbackRequeuesLevelTable 1}

PacketprocessingPushbackRequeuesLevelEntry ::=
	SEQUENCE {
		packetprocessingPushbackRequeuesLevelName	DisplayString,
		packetprocessingPushbackRequeuesLevelVal	Counter64,
		packetprocessingPushbackRequeuesLevelMom	CounterBasedGauge64,
		packetprocessingPushbackRequeuesLevelMax	CounterBasedGauge64
	}

packetprocessingPushbackRequeuesLevelName OBJECT-TYPE
	SYNTAX      DisplayString
	MAX-ACCESS  not-accessible
	STATUS      current
	DESCRIPTION
	"Table entry display string for packetprocessingPushbackRequeues"
	::={packetprocessingPushbackRequeuesLevelEntry 1}

packetprocessingPushbackRequeuesLevelVal OBJECT-TYPE
	SYNTAX	 Counter64
	MAX-ACCESS  read-only
	STATUS      current
	DESCRIPTION
	"Table entry attribute for packetprocessingPushbackRequeues"
	::={packetprocessingPushbackRequeuesLevelEntry 2}

packetprocessingPushbackRequeuesLevelMom OBJECT-TYPE
	SYNTAX	 CounterBasedGauge64
	MAX-ACCESS  read-only
	STATUS      current
	DESCRIPTION
	"Table entry attribute for packetprocessingPushbackRequeues"
	::={packetprocessingPushbackRequeuesLevelEntry 3}

packetprocessingPushbackRequeuesLevelMax OBJECT-TYPE
	SYNTAX	 CounterBasedGauge64
	MAX-ACCESS  read-only
	STATUS      current
	DESCRIPTION
	"Table entry attribute for packetprocessingPushbackRequeues"
	::={packetprocessingPushbackRequeuesLevelEntry 4}


packetprocessingBalancerDrops	OBJECT IDENTIFIER ::={packetprocessing 22}

packetprocessingBalancerDropsVal	OBJECT-TYPE
	SYNTAX	 Counter64
	MAX-ACCESS read-only
	STATUS current
	DESCRIPTION "Load balancer drops"

	::={packetprocessingBalancerDrops 1}

packetprocessingBalancerDropsMom	OBJECT-TYPE
	SYNTAX	 CounterBasedGauge64
	MAX-ACCESS read-only
	STATUS current
	DESCRIPTION "Load balancer drops"

	::={packetprocessingBalancerDrops 2}

packetprocessingBalancerDropsMax	OBJECT-TYPE
	SYNTAX	 CounterBasedGauge64
	MAX-ACCESS read-only
	STATUS current
	DESCRIPTION "Load balancer drops"

	::={packetprocessingBalancerDrops 3}

packetprocessingBalancerDropsLevelTable OBJECT-TYPE
	SYNTAX      SEQUENCE OF PacketprocessingBalancerDropsLevelEntry
	MAX-ACCESS  not-accessible
	STATUS      current
	DESCRIPTION
	"Table for packetprocessingBalancerDrops"
	::={packetprocessingBalancerDrops 4}

packetprocessingBalancerDropsLevelEntry OBJECT-TYPE
	SYNTAX      PacketprocessingBalancerDropsLevelEntry
	MAX-ACCESS  not-accessible
	STATUS      current
	DESCRIPTION
	"Table entry for packetprocessingBalancerDrops"
	INDEX { packetprocessingBalancerDropsLevelName }
	::={packetprocessingBalancerDropsLevelTable 1}

PacketprocessingBalancerDropsLevelEntry ::=
	SEQUENCE {
		packetprocessingBalancerDropsLevelName	DisplayString,
		packetprocessingBalancerDropsLevelVal	Counter64,
		packetprocessingBalancerDropsLevelMom	CounterBasedGauge64,
		packetprocessingBalancerDropsLevelMax	CounterBasedGauge64
	}

packetprocessingBalancerDropsLevelName OBJECT-TYPE
	SYNTAX      DisplayString
	MAX-ACCESS  not-accessible
	STATUS      current
	DESCRIPTION
	"Table entry display string for packetprocessingBalancerDrops"
	::={packetprocessingBalancerDropsLevelEntry 1}

packetprocessingBalancerDropsLevelVal OBJECT-TYPE
	SYNTAX	 Counter64
	MAX-ACCESS  read-only
	STATUS      current
	DESCRIPTION
	"Table entry attribute for packetprocessingBalancerDrops"
	::={packetprocessingBalancerDropsLevelEntry 2}

packetprocessingBalancerDropsLevelMom OBJECT-TYPE
	SYNTAX	 CounterBasedGauge64
	MAX-ACCESS  read-only
	STATUS      current
	DESCRIPTION
	"Table entry attribute for packetprocessingBalancerDrops"
	::={packetprocessingBalancerDropsLevelEntry 3}

packetprocessingBalancerDropsLevelMax OBJECT-TYPE
	SYNTAX	 CounterBasedGauge64
	MAX-ACCESS  read-only
	STATUS      current
	DESCRIPTION
	"Table entry attribute for packetprocessingBalancerDrops"
	::={packetprocessingBalancerDropsLevelEntry 4}


packetprocessingNICRXDrops	OBJECT IDENTIFIER ::={packetprocessing 23}

packetprocessingNICRXDropsVal	OBJECT-TYPE
	SYNTAX	 Counter64
	MAX-ACCESS read-only
	STATUS current
	DESCRIPTION "NIC RX drops"

	::={packetprocessingNICRXDrops 1}

packetprocessingNICRXDropsMom	OBJECT-TYPE
	SYNTAX	 CounterBasedGauge64
	MAX-ACCESS read-only
	STATUS current
	DESCRIPTION "NIC RX drops"

	::={packetprocessingNICRXDrops 2}

packetprocessingNICRXDropsMax	OBJECT-TYPE
	SYNTAX	 CounterBasedGauge64
	MAX-ACCESS read-only
	STATUS current
	DESCRIPTION "NIC RX drops"

	::={packetprocessingNICRXDrops 3}

packetprocessingNICRXDropsLevelTable OBJECT-TYPE
	SYNTAX      SEQUENCE OF PacketprocessingNICRXDropsLevelEntry
	MAX-ACCESS  not-accessible
	STATUS      current
	DESCRIPTION
	"Table for packetprocessingNICRXDrops"
	::={packetprocessingNICRXDrops 4}

packetprocessingNICRXDropsLevelEntry OBJECT-TYPE
	SYNTAX      PacketprocessingNICRXDropsLevelEntry
	MAX-ACCESS  not-accessible
	STATUS      current
	DESCRIPTION
	"Table entry for packetprocessingNICRXDrops"
	INDEX { packetprocessingNICRXDropsLevelName }
	::={packetprocessingNICRXDropsLevelTable 1}

PacketprocessingNICRXDropsLevelEntry ::=
	SEQUENCE {
		packetprocessingNICRXDropsLevelName	DisplayString,
		packetprocessingNICRXDropsLevelVal	Counter64,
		packetprocessingNICRXDropsLevelMom	CounterBasedGauge64,
		packetprocessingNICRXDropsLevelMax	CounterBasedGauge64
	}

packetprocessingNICRXDropsLevelName OBJECT-TYPE
	SYNTAX      DisplayString
	MAX-ACCESS  not-accessible
	STATUS      current
	DESCRIPTION
	"Table entry display string for packetprocessingNICRXDrops"
	::={packetprocessingNICRXDropsLevelEntry 1}

packetprocessingNICRXDropsLevelVal OBJECT-TYPE
	SYNTAX	 Counter64
	MAX-ACCESS  read-only
	STATUS      current
	DESCRIPTION
	"Table entry attribute for packetprocessingNICRXDrops"
	::={packetprocessingNICRXDropsLevelEntry 2}

packetprocessingNICRXDropsLevelMom OBJECT-TYPE
	SYNTAX	 CounterBasedGauge64
	MAX-ACCESS  read-only
	STATUS      current
	DESCRIPTION
	"Table entry attribute for packetprocessingNICRXDrops"
	::={packetprocessingNICRXDropsLevelEntry 3}

packetprocessingNICRXDropsLevelMax OBJECT-TYPE
	SYNTAX	 CounterBasedGauge64
	MAX-ACCESS  read-only
	STATUS      current
	DESCRIPTION
	"Table entry attribute for packetprocessingNICRXDrops"
	::={packetprocessingNICRXDropsLevelEntry 4}


packetprocessingBalancerQueueLength	OBJECT IDENTIFIER ::={packetprocessing 24}

packetprocessingBalancerQueueLengthVal	OBJECT-TYPE
	SYNTAX	 CounterBasedGauge64
	MAX-ACCESS read-only
	STATUS current
	DESCRIPTION "Load balancer queue length"

	::={packetprocessingBalancerQueueLength 1}

packetprocessingBalancerQueueLengthMax	OBJECT-TYPE
	SYNTAX	 CounterBasedGauge64
	MAX-ACCESS read-only
	STATUS current
	DESCRIPTION "Load balancer queue length"

	::={packetprocessingBalancerQueueLength 3}

packetprocessingBalancerQueueLengthLevelTable OBJECT-TYPE
	SYNTAX      SEQUENCE OF PacketprocessingBalancerQueueLengthLevelEntry
	MAX-ACCESS  not-accessible
	STATUS      current
	DESCRIPTION
	"Table for packetprocessingBalancerQueueLength"
	::={packetprocessingBalancerQueueLength 4}

packetprocessingBalancerQueueLengthLevelEntry OBJECT-TYPE
	SYNTAX      PacketprocessingBalancerQueueLengthLevelEntry
	MAX-ACCESS  not-accessible
	STATUS      current
	DESCRIPTION
	"Table entry for packetprocessingBalancerQueueLength"
	INDEX { packetprocessingBalancerQueueLengthLevelName }
	::={packetprocessingBalancerQueueLengthLevelTable 1}

PacketprocessingBalancerQueueLengthLevelEntry ::=
	SEQUENCE {
		packetprocessingBalancerQueueLengthLevelName	DisplayString,
		packetprocessingBalancerQueueLengthLevelVal	CounterBasedGauge64,
		packetprocessingBalancerQueueLengthLevelMax	CounterBasedGauge64
	}

packetprocessingBalancerQueueLengthLevelName OBJECT-TYPE
	SYNTAX      DisplayString
	MAX-ACCESS  not-accessible
	STATUS      current
	DESCRIPTION
	"Table entry display string for packetprocessingBalancerQueueLength"
	::={packetprocessingBalancerQueueLengthLevelEntry 1}

packetprocessingBalancerQueueLengthLevelVal OBJECT-TYPE
	SYNTAX	 CounterBasedGauge64
	MAX-ACCESS  read-only
	STATUS      current
	DESCRIPTION
	"Table entry attribute for packetprocessingBalancerQueueLength"
	::={packetprocessingBalancerQueueLengthLevelEntry 2}

packetprocessingBalancerQueueLengthLevelMax OBJECT-TYPE
	SYNTAX	 CounterBasedGauge64
	MAX-ACCESS  read-only
	STATUS      current
	DESCRIPTION
	"Table entry attribute for packetprocessingBalancerQueueLength"
	::={packetprocessingBalancerQueueLengthLevelEntry 4}


packetprocessingCpuPowerSave	OBJECT IDENTIFIER ::={packetprocessing 25}

packetprocessingCpuPowerSaveVal	OBJECT-TYPE
	SYNTAX	 Unsigned32
	MAX-ACCESS read-only
	STATUS current
	DESCRIPTION "CPU power save"

	::={packetprocessingCpuPowerSave 1}

packetprocessingCpuPowerSaveMax	OBJECT-TYPE
	SYNTAX	 Unsigned32
	MAX-ACCESS read-only
	STATUS current
	DESCRIPTION "CPU power save"

	::={packetprocessingCpuPowerSave 3}

packetprocessingCpuPowerSaveLevelTable OBJECT-TYPE
	SYNTAX      SEQUENCE OF PacketprocessingCpuPowerSaveLevelEntry
	MAX-ACCESS  not-accessible
	STATUS      current
	DESCRIPTION
	"Table for packetprocessingCpuPowerSave"
	::={packetprocessingCpuPowerSave 4}

packetprocessingCpuPowerSaveLevelEntry OBJECT-TYPE
	SYNTAX      PacketprocessingCpuPowerSaveLevelEntry
	MAX-ACCESS  not-accessible
	STATUS      current
	DESCRIPTION
	"Table entry for packetprocessingCpuPowerSave"
	INDEX { packetprocessingCpuPowerSaveLevelName }
	::={packetprocessingCpuPowerSaveLevelTable 1}

PacketprocessingCpuPowerSaveLevelEntry ::=
	SEQUENCE {
		packetprocessingCpuPowerSaveLevelName	DisplayString,
		packetprocessingCpuPowerSaveLevelVal	Unsigned32,
		packetprocessingCpuPowerSaveLevelMax	Unsigned32
	}

packetprocessingCpuPowerSaveLevelName OBJECT-TYPE
	SYNTAX      DisplayString
	MAX-ACCESS  not-accessible
	STATUS      current
	DESCRIPTION
	"Table entry display string for packetprocessingCpuPowerSave"
	::={packetprocessingCpuPowerSaveLevelEntry 1}

packetprocessingCpuPowerSaveLevelVal OBJECT-TYPE
	SYNTAX	 Unsigned32
	MAX-ACCESS  read-only
	STATUS      current
	DESCRIPTION
	"Table entry attribute for packetprocessingCpuPowerSave"
	::={packetprocessingCpuPowerSaveLevelEntry 2}

packetprocessingCpuPowerSaveLevelMax OBJECT-TYPE
	SYNTAX	 Unsigned32
	MAX-ACCESS  read-only
	STATUS      current
	DESCRIPTION
	"Table entry attribute for packetprocessingCpuPowerSave"
	::={packetprocessingCpuPowerSaveLevelEntry 4}


packetprocessingNoTx	OBJECT IDENTIFIER ::={packetprocessing 26}

packetprocessingNoTxVal	OBJECT-TYPE
	SYNTAX	 Counter64
	MAX-ACCESS read-only
	STATUS current
	DESCRIPTION "TX packets not allowed"

	::={packetprocessingNoTx 1}

packetprocessingNoTxMom	OBJECT-TYPE
	SYNTAX	 CounterBasedGauge64
	MAX-ACCESS read-only
	STATUS current
	DESCRIPTION "TX packets not allowed"

	::={packetprocessingNoTx 2}

packetprocessingNoTxMax	OBJECT-TYPE
	SYNTAX	 CounterBasedGauge64
	MAX-ACCESS read-only
	STATUS current
	DESCRIPTION "TX packets not allowed"

	::={packetprocessingNoTx 3}

packetprocessingNoTxLevelTable OBJECT-TYPE
	SYNTAX      SEQUENCE OF PacketprocessingNoTxLevelEntry
	MAX-ACCESS  not-accessible
	STATUS      current
	DESCRIPTION
	"Table for packetprocessingNoTx"
	::={packetprocessingNoTx 4}

packetprocessingNoTxLevelEntry OBJECT-TYPE
	SYNTAX      PacketprocessingNoTxLevelEntry
	MAX-ACCESS  not-accessible
	STATUS      current
	DESCRIPTION
	"Table entry for packetprocessingNoTx"
	INDEX { packetprocessingNoTxLevelName }
	::={packetprocessingNoTxLevelTable 1}

PacketprocessingNoTxLevelEntry ::=
	SEQUENCE {
		packetprocessingNoTxLevelName	DisplayString,
		packetprocessingNoTxLevelVal	Counter64,
		packetprocessingNoTxLevelMom	CounterBasedGauge64,
		packetprocessingNoTxLevelMax	CounterBasedGauge64
	}

packetprocessingNoTxLevelName OBJECT-TYPE
	SYNTAX      DisplayString
	MAX-ACCESS  not-accessible
	STATUS      current
	DESCRIPTION
	"Table entry display string for packetprocessingNoTx"
	::={packetprocessingNoTxLevelEntry 1}

packetprocessingNoTxLevelVal OBJECT-TYPE
	SYNTAX	 Counter64
	MAX-ACCESS  read-only
	STATUS      current
	DESCRIPTION
	"Table entry attribute for packetprocessingNoTx"
	::={packetprocessingNoTxLevelEntry 2}

packetprocessingNoTxLevelMom OBJECT-TYPE
	SYNTAX	 CounterBasedGauge64
	MAX-ACCESS  read-only
	STATUS      current
	DESCRIPTION
	"Table entry attribute for packetprocessingNoTx"
	::={packetprocessingNoTxLevelEntry 3}

packetprocessingNoTxLevelMax OBJECT-TYPE
	SYNTAX	 CounterBasedGauge64
	MAX-ACCESS  read-only
	STATUS      current
	DESCRIPTION
	"Table entry attribute for packetprocessingNoTx"
	::={packetprocessingNoTxLevelEntry 4}


packetprocessingOverLoad	OBJECT IDENTIFIER ::={packetprocessing 27}

packetprocessingOverLoadVal	OBJECT-TYPE
	SYNTAX INTEGER { not-overloaded(0), drdl-disabled(1), blind-forwarding(2) }
	MAX-ACCESS read-only
	STATUS current
	DESCRIPTION "Overload mode"

	::={packetprocessingOverLoad 1}

packetprocessingOverLoadLevelTable OBJECT-TYPE
	SYNTAX      SEQUENCE OF PacketprocessingOverLoadLevelEntry
	MAX-ACCESS  not-accessible
	STATUS      current
	DESCRIPTION
	"Table for packetprocessingOverLoad"
	::={packetprocessingOverLoad 4}

packetprocessingOverLoadLevelEntry OBJECT-TYPE
	SYNTAX      PacketprocessingOverLoadLevelEntry
	MAX-ACCESS  not-accessible
	STATUS      current
	DESCRIPTION
	"Table entry for packetprocessingOverLoad"
	INDEX { packetprocessingOverLoadLevelName }
	::={packetprocessingOverLoadLevelTable 1}

PacketprocessingOverLoadLevelEntry ::=
	SEQUENCE {
		packetprocessingOverLoadLevelName	DisplayString,
		packetprocessingOverLoadLevelVal	INTEGER
	}

packetprocessingOverLoadLevelName OBJECT-TYPE
	SYNTAX      DisplayString
	MAX-ACCESS  not-accessible
	STATUS      current
	DESCRIPTION
	"Table entry display string for packetprocessingOverLoad"
	::={packetprocessingOverLoadLevelEntry 1}

packetprocessingOverLoadLevelVal OBJECT-TYPE
	SYNTAX INTEGER { not-overloaded(0), drdl-disabled(1), blind-forwarding(2) }
	MAX-ACCESS  read-only
	STATUS      current
	DESCRIPTION
	"Table entry attribute for packetprocessingOverLoad"
	::={packetprocessingOverLoadLevelEntry 2}


packetprocessingCpuIrqs	OBJECT IDENTIFIER ::={packetprocessing 28}

packetprocessingCpuIrqsVal	OBJECT-TYPE
	SYNTAX	 Counter64
	MAX-ACCESS read-only
	STATUS current
	DESCRIPTION "CPU irqs"

	::={packetprocessingCpuIrqs 1}

packetprocessingCpuIrqsMom	OBJECT-TYPE
	SYNTAX	 CounterBasedGauge64
	MAX-ACCESS read-only
	STATUS current
	DESCRIPTION "CPU irqs"

	::={packetprocessingCpuIrqs 2}

packetprocessingCpuIrqsMax	OBJECT-TYPE
	SYNTAX	 CounterBasedGauge64
	MAX-ACCESS read-only
	STATUS current
	DESCRIPTION "CPU irqs"

	::={packetprocessingCpuIrqs 3}

packetprocessingCpuIrqsLevelTable OBJECT-TYPE
	SYNTAX      SEQUENCE OF PacketprocessingCpuIrqsLevelEntry
	MAX-ACCESS  not-accessible
	STATUS      current
	DESCRIPTION
	"Table for packetprocessingCpuIrqs"
	::={packetprocessingCpuIrqs 4}

packetprocessingCpuIrqsLevelEntry OBJECT-TYPE
	SYNTAX      PacketprocessingCpuIrqsLevelEntry
	MAX-ACCESS  not-accessible
	STATUS      current
	DESCRIPTION
	"Table entry for packetprocessingCpuIrqs"
	INDEX { packetprocessingCpuIrqsLevelName }
	::={packetprocessingCpuIrqsLevelTable 1}

PacketprocessingCpuIrqsLevelEntry ::=
	SEQUENCE {
		packetprocessingCpuIrqsLevelName	DisplayString,
		packetprocessingCpuIrqsLevelVal	Counter64,
		packetprocessingCpuIrqsLevelMom	CounterBasedGauge64,
		packetprocessingCpuIrqsLevelMax	CounterBasedGauge64
	}

packetprocessingCpuIrqsLevelName OBJECT-TYPE
	SYNTAX      DisplayString
	MAX-ACCESS  not-accessible
	STATUS      current
	DESCRIPTION
	"Table entry display string for packetprocessingCpuIrqs"
	::={packetprocessingCpuIrqsLevelEntry 1}

packetprocessingCpuIrqsLevelVal OBJECT-TYPE
	SYNTAX	 Counter64
	MAX-ACCESS  read-only
	STATUS      current
	DESCRIPTION
	"Table entry attribute for packetprocessingCpuIrqs"
	::={packetprocessingCpuIrqsLevelEntry 2}

packetprocessingCpuIrqsLevelMom OBJECT-TYPE
	SYNTAX	 CounterBasedGauge64
	MAX-ACCESS  read-only
	STATUS      current
	DESCRIPTION
	"Table entry attribute for packetprocessingCpuIrqs"
	::={packetprocessingCpuIrqsLevelEntry 3}

packetprocessingCpuIrqsLevelMax OBJECT-TYPE
	SYNTAX	 CounterBasedGauge64
	MAX-ACCESS  read-only
	STATUS      current
	DESCRIPTION
	"Table entry attribute for packetprocessingCpuIrqs"
	::={packetprocessingCpuIrqsLevelEntry 4}


packetprocessingCpuWakeups	OBJECT IDENTIFIER ::={packetprocessing 29}

packetprocessingCpuWakeupsVal	OBJECT-TYPE
	SYNTAX	 Counter64
	MAX-ACCESS read-only
	STATUS current
	DESCRIPTION "CPU Wakeups"

	::={packetprocessingCpuWakeups 1}

packetprocessingCpuWakeupsMom	OBJECT-TYPE
	SYNTAX	 CounterBasedGauge64
	MAX-ACCESS read-only
	STATUS current
	DESCRIPTION "CPU Wakeups"

	::={packetprocessingCpuWakeups 2}

packetprocessingCpuWakeupsMax	OBJECT-TYPE
	SYNTAX	 CounterBasedGauge64
	MAX-ACCESS read-only
	STATUS current
	DESCRIPTION "CPU Wakeups"

	::={packetprocessingCpuWakeups 3}

packetprocessingCpuWakeupsLevelTable OBJECT-TYPE
	SYNTAX      SEQUENCE OF PacketprocessingCpuWakeupsLevelEntry
	MAX-ACCESS  not-accessible
	STATUS      current
	DESCRIPTION
	"Table for packetprocessingCpuWakeups"
	::={packetprocessingCpuWakeups 4}

packetprocessingCpuWakeupsLevelEntry OBJECT-TYPE
	SYNTAX      PacketprocessingCpuWakeupsLevelEntry
	MAX-ACCESS  not-accessible
	STATUS      current
	DESCRIPTION
	"Table entry for packetprocessingCpuWakeups"
	INDEX { packetprocessingCpuWakeupsLevelName }
	::={packetprocessingCpuWakeupsLevelTable 1}

PacketprocessingCpuWakeupsLevelEntry ::=
	SEQUENCE {
		packetprocessingCpuWakeupsLevelName	DisplayString,
		packetprocessingCpuWakeupsLevelVal	Counter64,
		packetprocessingCpuWakeupsLevelMom	CounterBasedGauge64,
		packetprocessingCpuWakeupsLevelMax	CounterBasedGauge64
	}

packetprocessingCpuWakeupsLevelName OBJECT-TYPE
	SYNTAX      DisplayString
	MAX-ACCESS  not-accessible
	STATUS      current
	DESCRIPTION
	"Table entry display string for packetprocessingCpuWakeups"
	::={packetprocessingCpuWakeupsLevelEntry 1}

packetprocessingCpuWakeupsLevelVal OBJECT-TYPE
	SYNTAX	 Counter64
	MAX-ACCESS  read-only
	STATUS      current
	DESCRIPTION
	"Table entry attribute for packetprocessingCpuWakeups"
	::={packetprocessingCpuWakeupsLevelEntry 2}

packetprocessingCpuWakeupsLevelMom OBJECT-TYPE
	SYNTAX	 CounterBasedGauge64
	MAX-ACCESS  read-only
	STATUS      current
	DESCRIPTION
	"Table entry attribute for packetprocessingCpuWakeups"
	::={packetprocessingCpuWakeupsLevelEntry 3}

packetprocessingCpuWakeupsLevelMax OBJECT-TYPE
	SYNTAX	 CounterBasedGauge64
	MAX-ACCESS  read-only
	STATUS      current
	DESCRIPTION
	"Table entry attribute for packetprocessingCpuWakeups"
	::={packetprocessingCpuWakeupsLevelEntry 4}


packetprocessingContextsInUse	OBJECT IDENTIFIER ::={packetprocessing 30}

packetprocessingContextsInUseVal	OBJECT-TYPE
	SYNTAX	 CounterBasedGauge64
	MAX-ACCESS read-only
	STATUS current
	DESCRIPTION "Contexts in use"

	::={packetprocessingContextsInUse 1}

packetprocessingContextsInUseMax	OBJECT-TYPE
	SYNTAX	 CounterBasedGauge64
	MAX-ACCESS read-only
	STATUS current
	DESCRIPTION "Contexts in use"

	::={packetprocessingContextsInUse 3}

packetprocessingContextsInUseLevelTable OBJECT-TYPE
	SYNTAX      SEQUENCE OF PacketprocessingContextsInUseLevelEntry
	MAX-ACCESS  not-accessible
	STATUS      current
	DESCRIPTION
	"Table for packetprocessingContextsInUse"
	::={packetprocessingContextsInUse 4}

packetprocessingContextsInUseLevelEntry OBJECT-TYPE
	SYNTAX      PacketprocessingContextsInUseLevelEntry
	MAX-ACCESS  not-accessible
	STATUS      current
	DESCRIPTION
	"Table entry for packetprocessingContextsInUse"
	INDEX { packetprocessingContextsInUseLevelName }
	::={packetprocessingContextsInUseLevelTable 1}

PacketprocessingContextsInUseLevelEntry ::=
	SEQUENCE {
		packetprocessingContextsInUseLevelName	DisplayString,
		packetprocessingContextsInUseLevelVal	CounterBasedGauge64,
		packetprocessingContextsInUseLevelMax	CounterBasedGauge64
	}

packetprocessingContextsInUseLevelName OBJECT-TYPE
	SYNTAX      DisplayString
	MAX-ACCESS  not-accessible
	STATUS      current
	DESCRIPTION
	"Table entry display string for packetprocessingContextsInUse"
	::={packetprocessingContextsInUseLevelEntry 1}

packetprocessingContextsInUseLevelVal OBJECT-TYPE
	SYNTAX	 CounterBasedGauge64
	MAX-ACCESS  read-only
	STATUS      current
	DESCRIPTION
	"Table entry attribute for packetprocessingContextsInUse"
	::={packetprocessingContextsInUseLevelEntry 2}

packetprocessingContextsInUseLevelMax OBJECT-TYPE
	SYNTAX	 CounterBasedGauge64
	MAX-ACCESS  read-only
	STATUS      current
	DESCRIPTION
	"Table entry attribute for packetprocessingContextsInUse"
	::={packetprocessingContextsInUseLevelEntry 4}


packetprocessingContextAlloc	OBJECT IDENTIFIER ::={packetprocessing 31}

packetprocessingContextAllocVal	OBJECT-TYPE
	SYNTAX	 Counter64
	MAX-ACCESS read-only
	STATUS current
	DESCRIPTION "Context allocations"

	::={packetprocessingContextAlloc 1}

packetprocessingContextAllocMom	OBJECT-TYPE
	SYNTAX	 CounterBasedGauge64
	MAX-ACCESS read-only
	STATUS current
	DESCRIPTION "Context allocations"

	::={packetprocessingContextAlloc 2}

packetprocessingContextAllocMax	OBJECT-TYPE
	SYNTAX	 CounterBasedGauge64
	MAX-ACCESS read-only
	STATUS current
	DESCRIPTION "Context allocations"

	::={packetprocessingContextAlloc 3}

packetprocessingContextAllocLevelTable OBJECT-TYPE
	SYNTAX      SEQUENCE OF PacketprocessingContextAllocLevelEntry
	MAX-ACCESS  not-accessible
	STATUS      current
	DESCRIPTION
	"Table for packetprocessingContextAlloc"
	::={packetprocessingContextAlloc 4}

packetprocessingContextAllocLevelEntry OBJECT-TYPE
	SYNTAX      PacketprocessingContextAllocLevelEntry
	MAX-ACCESS  not-accessible
	STATUS      current
	DESCRIPTION
	"Table entry for packetprocessingContextAlloc"
	INDEX { packetprocessingContextAllocLevelName }
	::={packetprocessingContextAllocLevelTable 1}

PacketprocessingContextAllocLevelEntry ::=
	SEQUENCE {
		packetprocessingContextAllocLevelName	DisplayString,
		packetprocessingContextAllocLevelVal	Counter64,
		packetprocessingContextAllocLevelMom	CounterBasedGauge64,
		packetprocessingContextAllocLevelMax	CounterBasedGauge64
	}

packetprocessingContextAllocLevelName OBJECT-TYPE
	SYNTAX      DisplayString
	MAX-ACCESS  not-accessible
	STATUS      current
	DESCRIPTION
	"Table entry display string for packetprocessingContextAlloc"
	::={packetprocessingContextAllocLevelEntry 1}

packetprocessingContextAllocLevelVal OBJECT-TYPE
	SYNTAX	 Counter64
	MAX-ACCESS  read-only
	STATUS      current
	DESCRIPTION
	"Table entry attribute for packetprocessingContextAlloc"
	::={packetprocessingContextAllocLevelEntry 2}

packetprocessingContextAllocLevelMom OBJECT-TYPE
	SYNTAX	 CounterBasedGauge64
	MAX-ACCESS  read-only
	STATUS      current
	DESCRIPTION
	"Table entry attribute for packetprocessingContextAlloc"
	::={packetprocessingContextAllocLevelEntry 3}

packetprocessingContextAllocLevelMax OBJECT-TYPE
	SYNTAX	 CounterBasedGauge64
	MAX-ACCESS  read-only
	STATUS      current
	DESCRIPTION
	"Table entry attribute for packetprocessingContextAlloc"
	::={packetprocessingContextAllocLevelEntry 4}


packetprocessingContextAllocFail	OBJECT IDENTIFIER ::={packetprocessing 32}

packetprocessingContextAllocFailVal	OBJECT-TYPE
	SYNTAX	 Counter64
	MAX-ACCESS read-only
	STATUS current
	DESCRIPTION "Context allocation failures"

	::={packetprocessingContextAllocFail 1}

packetprocessingContextAllocFailMom	OBJECT-TYPE
	SYNTAX	 CounterBasedGauge64
	MAX-ACCESS read-only
	STATUS current
	DESCRIPTION "Context allocation failures"

	::={packetprocessingContextAllocFail 2}

packetprocessingContextAllocFailMax	OBJECT-TYPE
	SYNTAX	 CounterBasedGauge64
	MAX-ACCESS read-only
	STATUS current
	DESCRIPTION "Context allocation failures"

	::={packetprocessingContextAllocFail 3}

packetprocessingContextAllocFailLevelTable OBJECT-TYPE
	SYNTAX      SEQUENCE OF PacketprocessingContextAllocFailLevelEntry
	MAX-ACCESS  not-accessible
	STATUS      current
	DESCRIPTION
	"Table for packetprocessingContextAllocFail"
	::={packetprocessingContextAllocFail 4}

packetprocessingContextAllocFailLevelEntry OBJECT-TYPE
	SYNTAX      PacketprocessingContextAllocFailLevelEntry
	MAX-ACCESS  not-accessible
	STATUS      current
	DESCRIPTION
	"Table entry for packetprocessingContextAllocFail"
	INDEX { packetprocessingContextAllocFailLevelName }
	::={packetprocessingContextAllocFailLevelTable 1}

PacketprocessingContextAllocFailLevelEntry ::=
	SEQUENCE {
		packetprocessingContextAllocFailLevelName	DisplayString,
		packetprocessingContextAllocFailLevelVal	Counter64,
		packetprocessingContextAllocFailLevelMom	CounterBasedGauge64,
		packetprocessingContextAllocFailLevelMax	CounterBasedGauge64
	}

packetprocessingContextAllocFailLevelName OBJECT-TYPE
	SYNTAX      DisplayString
	MAX-ACCESS  not-accessible
	STATUS      current
	DESCRIPTION
	"Table entry display string for packetprocessingContextAllocFail"
	::={packetprocessingContextAllocFailLevelEntry 1}

packetprocessingContextAllocFailLevelVal OBJECT-TYPE
	SYNTAX	 Counter64
	MAX-ACCESS  read-only
	STATUS      current
	DESCRIPTION
	"Table entry attribute for packetprocessingContextAllocFail"
	::={packetprocessingContextAllocFailLevelEntry 2}

packetprocessingContextAllocFailLevelMom OBJECT-TYPE
	SYNTAX	 CounterBasedGauge64
	MAX-ACCESS  read-only
	STATUS      current
	DESCRIPTION
	"Table entry attribute for packetprocessingContextAllocFail"
	::={packetprocessingContextAllocFailLevelEntry 3}

packetprocessingContextAllocFailLevelMax OBJECT-TYPE
	SYNTAX	 CounterBasedGauge64
	MAX-ACCESS  read-only
	STATUS      current
	DESCRIPTION
	"Table entry attribute for packetprocessingContextAllocFail"
	::={packetprocessingContextAllocFailLevelEntry 4}


packetprocessingContextSwitches	OBJECT IDENTIFIER ::={packetprocessing 33}

packetprocessingContextSwitchesVal	OBJECT-TYPE
	SYNTAX	 Counter64
	MAX-ACCESS read-only
	STATUS current
	DESCRIPTION "Context switches"

	::={packetprocessingContextSwitches 1}

packetprocessingContextSwitchesMom	OBJECT-TYPE
	SYNTAX	 CounterBasedGauge64
	MAX-ACCESS read-only
	STATUS current
	DESCRIPTION "Context switches"

	::={packetprocessingContextSwitches 2}

packetprocessingContextSwitchesMax	OBJECT-TYPE
	SYNTAX	 CounterBasedGauge64
	MAX-ACCESS read-only
	STATUS current
	DESCRIPTION "Context switches"

	::={packetprocessingContextSwitches 3}

packetprocessingContextSwitchesLevelTable OBJECT-TYPE
	SYNTAX      SEQUENCE OF PacketprocessingContextSwitchesLevelEntry
	MAX-ACCESS  not-accessible
	STATUS      current
	DESCRIPTION
	"Table for packetprocessingContextSwitches"
	::={packetprocessingContextSwitches 4}

packetprocessingContextSwitchesLevelEntry OBJECT-TYPE
	SYNTAX      PacketprocessingContextSwitchesLevelEntry
	MAX-ACCESS  not-accessible
	STATUS      current
	DESCRIPTION
	"Table entry for packetprocessingContextSwitches"
	INDEX { packetprocessingContextSwitchesLevelName }
	::={packetprocessingContextSwitchesLevelTable 1}

PacketprocessingContextSwitchesLevelEntry ::=
	SEQUENCE {
		packetprocessingContextSwitchesLevelName	DisplayString,
		packetprocessingContextSwitchesLevelVal	Counter64,
		packetprocessingContextSwitchesLevelMom	CounterBasedGauge64,
		packetprocessingContextSwitchesLevelMax	CounterBasedGauge64
	}

packetprocessingContextSwitchesLevelName OBJECT-TYPE
	SYNTAX      DisplayString
	MAX-ACCESS  not-accessible
	STATUS      current
	DESCRIPTION
	"Table entry display string for packetprocessingContextSwitches"
	::={packetprocessingContextSwitchesLevelEntry 1}

packetprocessingContextSwitchesLevelVal OBJECT-TYPE
	SYNTAX	 Counter64
	MAX-ACCESS  read-only
	STATUS      current
	DESCRIPTION
	"Table entry attribute for packetprocessingContextSwitches"
	::={packetprocessingContextSwitchesLevelEntry 2}

packetprocessingContextSwitchesLevelMom OBJECT-TYPE
	SYNTAX	 CounterBasedGauge64
	MAX-ACCESS  read-only
	STATUS      current
	DESCRIPTION
	"Table entry attribute for packetprocessingContextSwitches"
	::={packetprocessingContextSwitchesLevelEntry 3}

packetprocessingContextSwitchesLevelMax OBJECT-TYPE
	SYNTAX	 CounterBasedGauge64
	MAX-ACCESS  read-only
	STATUS      current
	DESCRIPTION
	"Table entry attribute for packetprocessingContextSwitches"
	::={packetprocessingContextSwitchesLevelEntry 4}


packetprocessingMaxWatchdogDelay	OBJECT IDENTIFIER ::={packetprocessing 34}

packetprocessingMaxWatchdogDelayVal	OBJECT-TYPE
	SYNTAX	 CounterBasedGauge64
	MAX-ACCESS read-only
	STATUS current
	DESCRIPTION "Max watchdog delay"

	::={packetprocessingMaxWatchdogDelay 1}

packetprocessingMaxWatchdogDelayMax	OBJECT-TYPE
	SYNTAX	 CounterBasedGauge64
	MAX-ACCESS read-only
	STATUS current
	DESCRIPTION "Max watchdog delay"

	::={packetprocessingMaxWatchdogDelay 3}

packetprocessingMaxWatchdogDelayLevelTable OBJECT-TYPE
	SYNTAX      SEQUENCE OF PacketprocessingMaxWatchdogDelayLevelEntry
	MAX-ACCESS  not-accessible
	STATUS      current
	DESCRIPTION
	"Table for packetprocessingMaxWatchdogDelay"
	::={packetprocessingMaxWatchdogDelay 4}

packetprocessingMaxWatchdogDelayLevelEntry OBJECT-TYPE
	SYNTAX      PacketprocessingMaxWatchdogDelayLevelEntry
	MAX-ACCESS  not-accessible
	STATUS      current
	DESCRIPTION
	"Table entry for packetprocessingMaxWatchdogDelay"
	INDEX { packetprocessingMaxWatchdogDelayLevelName }
	::={packetprocessingMaxWatchdogDelayLevelTable 1}

PacketprocessingMaxWatchdogDelayLevelEntry ::=
	SEQUENCE {
		packetprocessingMaxWatchdogDelayLevelName	DisplayString,
		packetprocessingMaxWatchdogDelayLevelVal	CounterBasedGauge64,
		packetprocessingMaxWatchdogDelayLevelMax	CounterBasedGauge64
	}

packetprocessingMaxWatchdogDelayLevelName OBJECT-TYPE
	SYNTAX      DisplayString
	MAX-ACCESS  not-accessible
	STATUS      current
	DESCRIPTION
	"Table entry display string for packetprocessingMaxWatchdogDelay"
	::={packetprocessingMaxWatchdogDelayLevelEntry 1}

packetprocessingMaxWatchdogDelayLevelVal OBJECT-TYPE
	SYNTAX	 CounterBasedGauge64
	MAX-ACCESS  read-only
	STATUS      current
	DESCRIPTION
	"Table entry attribute for packetprocessingMaxWatchdogDelay"
	::={packetprocessingMaxWatchdogDelayLevelEntry 2}

packetprocessingMaxWatchdogDelayLevelMax OBJECT-TYPE
	SYNTAX	 CounterBasedGauge64
	MAX-ACCESS  read-only
	STATUS      current
	DESCRIPTION
	"Table entry attribute for packetprocessingMaxWatchdogDelay"
	::={packetprocessingMaxWatchdogDelayLevelEntry 4}


drdl	OBJECT IDENTIFIER ::={sysdiag 24}

drdlWaitingChildren	OBJECT IDENTIFIER ::={drdl 1}

drdlWaitingChildrenVal	OBJECT-TYPE
	SYNTAX	 CounterBasedGauge64
	MAX-ACCESS read-only
	STATUS current
	DESCRIPTION "Waiting childconnections"

	::={drdlWaitingChildren 1}

drdlWaitingChildrenMax	OBJECT-TYPE
	SYNTAX	 CounterBasedGauge64
	MAX-ACCESS read-only
	STATUS current
	DESCRIPTION "Waiting childconnections"

	::={drdlWaitingChildren 3}

drdlWaitingChildrenLevelTable OBJECT-TYPE
	SYNTAX      SEQUENCE OF DrdlWaitingChildrenLevelEntry
	MAX-ACCESS  not-accessible
	STATUS      current
	DESCRIPTION
	"Table for drdlWaitingChildren"
	::={drdlWaitingChildren 4}

drdlWaitingChildrenLevelEntry OBJECT-TYPE
	SYNTAX      DrdlWaitingChildrenLevelEntry
	MAX-ACCESS  not-accessible
	STATUS      current
	DESCRIPTION
	"Table entry for drdlWaitingChildren"
	INDEX { drdlWaitingChildrenLevelName }
	::={drdlWaitingChildrenLevelTable 1}

DrdlWaitingChildrenLevelEntry ::=
	SEQUENCE {
		drdlWaitingChildrenLevelName	DisplayString,
		drdlWaitingChildrenLevelVal	CounterBasedGauge64,
		drdlWaitingChildrenLevelMax	CounterBasedGauge64
	}

drdlWaitingChildrenLevelName OBJECT-TYPE
	SYNTAX      DisplayString
	MAX-ACCESS  not-accessible
	STATUS      current
	DESCRIPTION
	"Table entry display string for drdlWaitingChildren"
	::={drdlWaitingChildrenLevelEntry 1}

drdlWaitingChildrenLevelVal OBJECT-TYPE
	SYNTAX	 CounterBasedGauge64
	MAX-ACCESS  read-only
	STATUS      current
	DESCRIPTION
	"Table entry attribute for drdlWaitingChildren"
	::={drdlWaitingChildrenLevelEntry 2}

drdlWaitingChildrenLevelMax OBJECT-TYPE
	SYNTAX	 CounterBasedGauge64
	MAX-ACCESS  read-only
	STATUS      current
	DESCRIPTION
	"Table entry attribute for drdlWaitingChildren"
	::={drdlWaitingChildrenLevelEntry 4}


drdlAddedChildren	OBJECT IDENTIFIER ::={drdl 2}

drdlAddedChildrenVal	OBJECT-TYPE
	SYNTAX	 Counter64
	MAX-ACCESS read-only
	STATUS current
	DESCRIPTION "New childconnections"

	::={drdlAddedChildren 1}

drdlAddedChildrenMom	OBJECT-TYPE
	SYNTAX	 CounterBasedGauge64
	MAX-ACCESS read-only
	STATUS current
	DESCRIPTION "New childconnections"

	::={drdlAddedChildren 2}

drdlAddedChildrenMax	OBJECT-TYPE
	SYNTAX	 CounterBasedGauge64
	MAX-ACCESS read-only
	STATUS current
	DESCRIPTION "New childconnections"

	::={drdlAddedChildren 3}

drdlAddedChildrenLevelTable OBJECT-TYPE
	SYNTAX      SEQUENCE OF DrdlAddedChildrenLevelEntry
	MAX-ACCESS  not-accessible
	STATUS      current
	DESCRIPTION
	"Table for drdlAddedChildren"
	::={drdlAddedChildren 4}

drdlAddedChildrenLevelEntry OBJECT-TYPE
	SYNTAX      DrdlAddedChildrenLevelEntry
	MAX-ACCESS  not-accessible
	STATUS      current
	DESCRIPTION
	"Table entry for drdlAddedChildren"
	INDEX { drdlAddedChildrenLevelName }
	::={drdlAddedChildrenLevelTable 1}

DrdlAddedChildrenLevelEntry ::=
	SEQUENCE {
		drdlAddedChildrenLevelName	DisplayString,
		drdlAddedChildrenLevelVal	Counter64,
		drdlAddedChildrenLevelMom	CounterBasedGauge64,
		drdlAddedChildrenLevelMax	CounterBasedGauge64
	}

drdlAddedChildrenLevelName OBJECT-TYPE
	SYNTAX      DisplayString
	MAX-ACCESS  not-accessible
	STATUS      current
	DESCRIPTION
	"Table entry display string for drdlAddedChildren"
	::={drdlAddedChildrenLevelEntry 1}

drdlAddedChildrenLevelVal OBJECT-TYPE
	SYNTAX	 Counter64
	MAX-ACCESS  read-only
	STATUS      current
	DESCRIPTION
	"Table entry attribute for drdlAddedChildren"
	::={drdlAddedChildrenLevelEntry 2}

drdlAddedChildrenLevelMom OBJECT-TYPE
	SYNTAX	 CounterBasedGauge64
	MAX-ACCESS  read-only
	STATUS      current
	DESCRIPTION
	"Table entry attribute for drdlAddedChildren"
	::={drdlAddedChildrenLevelEntry 3}

drdlAddedChildrenLevelMax OBJECT-TYPE
	SYNTAX	 CounterBasedGauge64
	MAX-ACCESS  read-only
	STATUS      current
	DESCRIPTION
	"Table entry attribute for drdlAddedChildren"
	::={drdlAddedChildrenLevelEntry 4}


drdlChildAbuses	OBJECT IDENTIFIER ::={drdl 3}

drdlChildAbusesVal	OBJECT-TYPE
	SYNTAX	 Counter64
	MAX-ACCESS read-only
	STATUS current
	DESCRIPTION "LRU child allocations"

	::={drdlChildAbuses 1}

drdlChildAbusesMom	OBJECT-TYPE
	SYNTAX	 CounterBasedGauge64
	MAX-ACCESS read-only
	STATUS current
	DESCRIPTION "LRU child allocations"

	::={drdlChildAbuses 2}

drdlChildAbusesMax	OBJECT-TYPE
	SYNTAX	 CounterBasedGauge64
	MAX-ACCESS read-only
	STATUS current
	DESCRIPTION "LRU child allocations"

	::={drdlChildAbuses 3}

drdlChildAbusesLevelTable OBJECT-TYPE
	SYNTAX      SEQUENCE OF DrdlChildAbusesLevelEntry
	MAX-ACCESS  not-accessible
	STATUS      current
	DESCRIPTION
	"Table for drdlChildAbuses"
	::={drdlChildAbuses 4}

drdlChildAbusesLevelEntry OBJECT-TYPE
	SYNTAX      DrdlChildAbusesLevelEntry
	MAX-ACCESS  not-accessible
	STATUS      current
	DESCRIPTION
	"Table entry for drdlChildAbuses"
	INDEX { drdlChildAbusesLevelName }
	::={drdlChildAbusesLevelTable 1}

DrdlChildAbusesLevelEntry ::=
	SEQUENCE {
		drdlChildAbusesLevelName	DisplayString,
		drdlChildAbusesLevelVal	Counter64,
		drdlChildAbusesLevelMom	CounterBasedGauge64,
		drdlChildAbusesLevelMax	CounterBasedGauge64
	}

drdlChildAbusesLevelName OBJECT-TYPE
	SYNTAX      DisplayString
	MAX-ACCESS  not-accessible
	STATUS      current
	DESCRIPTION
	"Table entry display string for drdlChildAbuses"
	::={drdlChildAbusesLevelEntry 1}

drdlChildAbusesLevelVal OBJECT-TYPE
	SYNTAX	 Counter64
	MAX-ACCESS  read-only
	STATUS      current
	DESCRIPTION
	"Table entry attribute for drdlChildAbuses"
	::={drdlChildAbusesLevelEntry 2}

drdlChildAbusesLevelMom OBJECT-TYPE
	SYNTAX	 CounterBasedGauge64
	MAX-ACCESS  read-only
	STATUS      current
	DESCRIPTION
	"Table entry attribute for drdlChildAbuses"
	::={drdlChildAbusesLevelEntry 3}

drdlChildAbusesLevelMax OBJECT-TYPE
	SYNTAX	 CounterBasedGauge64
	MAX-ACCESS  read-only
	STATUS      current
	DESCRIPTION
	"Table entry attribute for drdlChildAbuses"
	::={drdlChildAbusesLevelEntry 4}


drdlChildEmpty	OBJECT IDENTIFIER ::={drdl 4}

drdlChildEmptyVal	OBJECT-TYPE
	SYNTAX	 Counter64
	MAX-ACCESS read-only
	STATUS current
	DESCRIPTION "Child allocation failures"

	::={drdlChildEmpty 1}

drdlChildEmptyMom	OBJECT-TYPE
	SYNTAX	 CounterBasedGauge64
	MAX-ACCESS read-only
	STATUS current
	DESCRIPTION "Child allocation failures"

	::={drdlChildEmpty 2}

drdlChildEmptyMax	OBJECT-TYPE
	SYNTAX	 CounterBasedGauge64
	MAX-ACCESS read-only
	STATUS current
	DESCRIPTION "Child allocation failures"

	::={drdlChildEmpty 3}

drdlChildEmptyLevelTable OBJECT-TYPE
	SYNTAX      SEQUENCE OF DrdlChildEmptyLevelEntry
	MAX-ACCESS  not-accessible
	STATUS      current
	DESCRIPTION
	"Table for drdlChildEmpty"
	::={drdlChildEmpty 4}

drdlChildEmptyLevelEntry OBJECT-TYPE
	SYNTAX      DrdlChildEmptyLevelEntry
	MAX-ACCESS  not-accessible
	STATUS      current
	DESCRIPTION
	"Table entry for drdlChildEmpty"
	INDEX { drdlChildEmptyLevelName }
	::={drdlChildEmptyLevelTable 1}

DrdlChildEmptyLevelEntry ::=
	SEQUENCE {
		drdlChildEmptyLevelName	DisplayString,
		drdlChildEmptyLevelVal	Counter64,
		drdlChildEmptyLevelMom	CounterBasedGauge64,
		drdlChildEmptyLevelMax	CounterBasedGauge64
	}

drdlChildEmptyLevelName OBJECT-TYPE
	SYNTAX      DisplayString
	MAX-ACCESS  not-accessible
	STATUS      current
	DESCRIPTION
	"Table entry display string for drdlChildEmpty"
	::={drdlChildEmptyLevelEntry 1}

drdlChildEmptyLevelVal OBJECT-TYPE
	SYNTAX	 Counter64
	MAX-ACCESS  read-only
	STATUS      current
	DESCRIPTION
	"Table entry attribute for drdlChildEmpty"
	::={drdlChildEmptyLevelEntry 2}

drdlChildEmptyLevelMom OBJECT-TYPE
	SYNTAX	 CounterBasedGauge64
	MAX-ACCESS  read-only
	STATUS      current
	DESCRIPTION
	"Table entry attribute for drdlChildEmpty"
	::={drdlChildEmptyLevelEntry 3}

drdlChildEmptyLevelMax OBJECT-TYPE
	SYNTAX	 CounterBasedGauge64
	MAX-ACCESS  read-only
	STATUS      current
	DESCRIPTION
	"Table entry attribute for drdlChildEmpty"
	::={drdlChildEmptyLevelEntry 4}


drdlProp32Fail	OBJECT IDENTIFIER ::={drdl 5}

drdlProp32FailVal	OBJECT-TYPE
	SYNTAX	 Counter64
	MAX-ACCESS read-only
	STATUS current
	DESCRIPTION "Property allocation failures (32)"

	::={drdlProp32Fail 1}

drdlProp32FailMom	OBJECT-TYPE
	SYNTAX	 CounterBasedGauge64
	MAX-ACCESS read-only
	STATUS current
	DESCRIPTION "Property allocation failures (32)"

	::={drdlProp32Fail 2}

drdlProp32FailMax	OBJECT-TYPE
	SYNTAX	 CounterBasedGauge64
	MAX-ACCESS read-only
	STATUS current
	DESCRIPTION "Property allocation failures (32)"

	::={drdlProp32Fail 3}

drdlProp32FailLevelTable OBJECT-TYPE
	SYNTAX      SEQUENCE OF DrdlProp32FailLevelEntry
	MAX-ACCESS  not-accessible
	STATUS      current
	DESCRIPTION
	"Table for drdlProp32Fail"
	::={drdlProp32Fail 4}

drdlProp32FailLevelEntry OBJECT-TYPE
	SYNTAX      DrdlProp32FailLevelEntry
	MAX-ACCESS  not-accessible
	STATUS      current
	DESCRIPTION
	"Table entry for drdlProp32Fail"
	INDEX { drdlProp32FailLevelName }
	::={drdlProp32FailLevelTable 1}

DrdlProp32FailLevelEntry ::=
	SEQUENCE {
		drdlProp32FailLevelName	DisplayString,
		drdlProp32FailLevelVal	Counter64,
		drdlProp32FailLevelMom	CounterBasedGauge64,
		drdlProp32FailLevelMax	CounterBasedGauge64
	}

drdlProp32FailLevelName OBJECT-TYPE
	SYNTAX      DisplayString
	MAX-ACCESS  not-accessible
	STATUS      current
	DESCRIPTION
	"Table entry display string for drdlProp32Fail"
	::={drdlProp32FailLevelEntry 1}

drdlProp32FailLevelVal OBJECT-TYPE
	SYNTAX	 Counter64
	MAX-ACCESS  read-only
	STATUS      current
	DESCRIPTION
	"Table entry attribute for drdlProp32Fail"
	::={drdlProp32FailLevelEntry 2}

drdlProp32FailLevelMom OBJECT-TYPE
	SYNTAX	 CounterBasedGauge64
	MAX-ACCESS  read-only
	STATUS      current
	DESCRIPTION
	"Table entry attribute for drdlProp32Fail"
	::={drdlProp32FailLevelEntry 3}

drdlProp32FailLevelMax OBJECT-TYPE
	SYNTAX	 CounterBasedGauge64
	MAX-ACCESS  read-only
	STATUS      current
	DESCRIPTION
	"Table entry attribute for drdlProp32Fail"
	::={drdlProp32FailLevelEntry 4}


drdlProp64Fail	OBJECT IDENTIFIER ::={drdl 6}

drdlProp64FailVal	OBJECT-TYPE
	SYNTAX	 Counter64
	MAX-ACCESS read-only
	STATUS obsolete
	DESCRIPTION "Unused"

	::={drdlProp64Fail 1}

drdlProp64FailMom	OBJECT-TYPE
	SYNTAX	 CounterBasedGauge64
	MAX-ACCESS read-only
	STATUS obsolete
	DESCRIPTION "Unused"

	::={drdlProp64Fail 2}

drdlProp64FailMax	OBJECT-TYPE
	SYNTAX	 CounterBasedGauge64
	MAX-ACCESS read-only
	STATUS obsolete
	DESCRIPTION "Unused"

	::={drdlProp64Fail 3}

drdlProp64FailLevelTable OBJECT-TYPE
	SYNTAX      SEQUENCE OF DrdlProp64FailLevelEntry
	MAX-ACCESS  not-accessible
	STATUS      current
	DESCRIPTION
	"Table for drdlProp64Fail"
	::={drdlProp64Fail 4}

drdlProp64FailLevelEntry OBJECT-TYPE
	SYNTAX      DrdlProp64FailLevelEntry
	MAX-ACCESS  not-accessible
	STATUS      current
	DESCRIPTION
	"Table entry for drdlProp64Fail"
	INDEX { drdlProp64FailLevelName }
	::={drdlProp64FailLevelTable 1}

DrdlProp64FailLevelEntry ::=
	SEQUENCE {
		drdlProp64FailLevelName	DisplayString,
		drdlProp64FailLevelVal	Counter64,
		drdlProp64FailLevelMom	CounterBasedGauge64,
		drdlProp64FailLevelMax	CounterBasedGauge64
	}

drdlProp64FailLevelName OBJECT-TYPE
	SYNTAX      DisplayString
	MAX-ACCESS  not-accessible
	STATUS      current
	DESCRIPTION
	"Table entry display string for drdlProp64Fail"
	::={drdlProp64FailLevelEntry 1}

drdlProp64FailLevelVal OBJECT-TYPE
	SYNTAX	 Counter64
	MAX-ACCESS  read-only
	STATUS      current
	DESCRIPTION
	"Table entry attribute for drdlProp64Fail"
	::={drdlProp64FailLevelEntry 2}

drdlProp64FailLevelMom OBJECT-TYPE
	SYNTAX	 CounterBasedGauge64
	MAX-ACCESS  read-only
	STATUS      current
	DESCRIPTION
	"Table entry attribute for drdlProp64Fail"
	::={drdlProp64FailLevelEntry 3}

drdlProp64FailLevelMax OBJECT-TYPE
	SYNTAX	 CounterBasedGauge64
	MAX-ACCESS  read-only
	STATUS      current
	DESCRIPTION
	"Table entry attribute for drdlProp64Fail"
	::={drdlProp64FailLevelEntry 4}


drdlProp256Fail	OBJECT IDENTIFIER ::={drdl 7}

drdlProp256FailVal	OBJECT-TYPE
	SYNTAX	 Counter64
	MAX-ACCESS read-only
	STATUS current
	DESCRIPTION "Property allocation failures (256)"

	::={drdlProp256Fail 1}

drdlProp256FailMom	OBJECT-TYPE
	SYNTAX	 CounterBasedGauge64
	MAX-ACCESS read-only
	STATUS current
	DESCRIPTION "Property allocation failures (256)"

	::={drdlProp256Fail 2}

drdlProp256FailMax	OBJECT-TYPE
	SYNTAX	 CounterBasedGauge64
	MAX-ACCESS read-only
	STATUS current
	DESCRIPTION "Property allocation failures (256)"

	::={drdlProp256Fail 3}

drdlProp256FailLevelTable OBJECT-TYPE
	SYNTAX      SEQUENCE OF DrdlProp256FailLevelEntry
	MAX-ACCESS  not-accessible
	STATUS      current
	DESCRIPTION
	"Table for drdlProp256Fail"
	::={drdlProp256Fail 4}

drdlProp256FailLevelEntry OBJECT-TYPE
	SYNTAX      DrdlProp256FailLevelEntry
	MAX-ACCESS  not-accessible
	STATUS      current
	DESCRIPTION
	"Table entry for drdlProp256Fail"
	INDEX { drdlProp256FailLevelName }
	::={drdlProp256FailLevelTable 1}

DrdlProp256FailLevelEntry ::=
	SEQUENCE {
		drdlProp256FailLevelName	DisplayString,
		drdlProp256FailLevelVal	Counter64,
		drdlProp256FailLevelMom	CounterBasedGauge64,
		drdlProp256FailLevelMax	CounterBasedGauge64
	}

drdlProp256FailLevelName OBJECT-TYPE
	SYNTAX      DisplayString
	MAX-ACCESS  not-accessible
	STATUS      current
	DESCRIPTION
	"Table entry display string for drdlProp256Fail"
	::={drdlProp256FailLevelEntry 1}

drdlProp256FailLevelVal OBJECT-TYPE
	SYNTAX	 Counter64
	MAX-ACCESS  read-only
	STATUS      current
	DESCRIPTION
	"Table entry attribute for drdlProp256Fail"
	::={drdlProp256FailLevelEntry 2}

drdlProp256FailLevelMom OBJECT-TYPE
	SYNTAX	 CounterBasedGauge64
	MAX-ACCESS  read-only
	STATUS      current
	DESCRIPTION
	"Table entry attribute for drdlProp256Fail"
	::={drdlProp256FailLevelEntry 3}

drdlProp256FailLevelMax OBJECT-TYPE
	SYNTAX	 CounterBasedGauge64
	MAX-ACCESS  read-only
	STATUS      current
	DESCRIPTION
	"Table entry attribute for drdlProp256Fail"
	::={drdlProp256FailLevelEntry 4}


drdlProp32Used	OBJECT IDENTIFIER ::={drdl 8}

drdlProp32UsedVal	OBJECT-TYPE
	SYNTAX	 CounterBasedGauge64
	MAX-ACCESS read-only
	STATUS current
	DESCRIPTION "Properties used (32)"

	::={drdlProp32Used 1}

drdlProp32UsedMax	OBJECT-TYPE
	SYNTAX	 CounterBasedGauge64
	MAX-ACCESS read-only
	STATUS current
	DESCRIPTION "Properties used (32)"

	::={drdlProp32Used 3}

drdlProp32UsedLevelTable OBJECT-TYPE
	SYNTAX      SEQUENCE OF DrdlProp32UsedLevelEntry
	MAX-ACCESS  not-accessible
	STATUS      current
	DESCRIPTION
	"Table for drdlProp32Used"
	::={drdlProp32Used 4}

drdlProp32UsedLevelEntry OBJECT-TYPE
	SYNTAX      DrdlProp32UsedLevelEntry
	MAX-ACCESS  not-accessible
	STATUS      current
	DESCRIPTION
	"Table entry for drdlProp32Used"
	INDEX { drdlProp32UsedLevelName }
	::={drdlProp32UsedLevelTable 1}

DrdlProp32UsedLevelEntry ::=
	SEQUENCE {
		drdlProp32UsedLevelName	DisplayString,
		drdlProp32UsedLevelVal	CounterBasedGauge64,
		drdlProp32UsedLevelMax	CounterBasedGauge64
	}

drdlProp32UsedLevelName OBJECT-TYPE
	SYNTAX      DisplayString
	MAX-ACCESS  not-accessible
	STATUS      current
	DESCRIPTION
	"Table entry display string for drdlProp32Used"
	::={drdlProp32UsedLevelEntry 1}

drdlProp32UsedLevelVal OBJECT-TYPE
	SYNTAX	 CounterBasedGauge64
	MAX-ACCESS  read-only
	STATUS      current
	DESCRIPTION
	"Table entry attribute for drdlProp32Used"
	::={drdlProp32UsedLevelEntry 2}

drdlProp32UsedLevelMax OBJECT-TYPE
	SYNTAX	 CounterBasedGauge64
	MAX-ACCESS  read-only
	STATUS      current
	DESCRIPTION
	"Table entry attribute for drdlProp32Used"
	::={drdlProp32UsedLevelEntry 4}


drdlProp64Used	OBJECT IDENTIFIER ::={drdl 9}

drdlProp64UsedVal	OBJECT-TYPE
	SYNTAX	 Counter64
	MAX-ACCESS read-only
	STATUS obsolete
	DESCRIPTION "Unused"

	::={drdlProp64Used 1}

drdlProp64UsedMom	OBJECT-TYPE
	SYNTAX	 CounterBasedGauge64
	MAX-ACCESS read-only
	STATUS obsolete
	DESCRIPTION "Unused"

	::={drdlProp64Used 2}

drdlProp64UsedMax	OBJECT-TYPE
	SYNTAX	 CounterBasedGauge64
	MAX-ACCESS read-only
	STATUS obsolete
	DESCRIPTION "Unused"

	::={drdlProp64Used 3}

drdlProp64UsedLevelTable OBJECT-TYPE
	SYNTAX      SEQUENCE OF DrdlProp64UsedLevelEntry
	MAX-ACCESS  not-accessible
	STATUS      current
	DESCRIPTION
	"Table for drdlProp64Used"
	::={drdlProp64Used 4}

drdlProp64UsedLevelEntry OBJECT-TYPE
	SYNTAX      DrdlProp64UsedLevelEntry
	MAX-ACCESS  not-accessible
	STATUS      current
	DESCRIPTION
	"Table entry for drdlProp64Used"
	INDEX { drdlProp64UsedLevelName }
	::={drdlProp64UsedLevelTable 1}

DrdlProp64UsedLevelEntry ::=
	SEQUENCE {
		drdlProp64UsedLevelName	DisplayString,
		drdlProp64UsedLevelVal	Counter64,
		drdlProp64UsedLevelMom	CounterBasedGauge64,
		drdlProp64UsedLevelMax	CounterBasedGauge64
	}

drdlProp64UsedLevelName OBJECT-TYPE
	SYNTAX      DisplayString
	MAX-ACCESS  not-accessible
	STATUS      current
	DESCRIPTION
	"Table entry display string for drdlProp64Used"
	::={drdlProp64UsedLevelEntry 1}

drdlProp64UsedLevelVal OBJECT-TYPE
	SYNTAX	 Counter64
	MAX-ACCESS  read-only
	STATUS      current
	DESCRIPTION
	"Table entry attribute for drdlProp64Used"
	::={drdlProp64UsedLevelEntry 2}

drdlProp64UsedLevelMom OBJECT-TYPE
	SYNTAX	 CounterBasedGauge64
	MAX-ACCESS  read-only
	STATUS      current
	DESCRIPTION
	"Table entry attribute for drdlProp64Used"
	::={drdlProp64UsedLevelEntry 3}

drdlProp64UsedLevelMax OBJECT-TYPE
	SYNTAX	 CounterBasedGauge64
	MAX-ACCESS  read-only
	STATUS      current
	DESCRIPTION
	"Table entry attribute for drdlProp64Used"
	::={drdlProp64UsedLevelEntry 4}


drdlProp256Used	OBJECT IDENTIFIER ::={drdl 10}

drdlProp256UsedVal	OBJECT-TYPE
	SYNTAX	 CounterBasedGauge64
	MAX-ACCESS read-only
	STATUS current
	DESCRIPTION "Properties used (256)"

	::={drdlProp256Used 1}

drdlProp256UsedMax	OBJECT-TYPE
	SYNTAX	 CounterBasedGauge64
	MAX-ACCESS read-only
	STATUS current
	DESCRIPTION "Properties used (256)"

	::={drdlProp256Used 3}

drdlProp256UsedLevelTable OBJECT-TYPE
	SYNTAX      SEQUENCE OF DrdlProp256UsedLevelEntry
	MAX-ACCESS  not-accessible
	STATUS      current
	DESCRIPTION
	"Table for drdlProp256Used"
	::={drdlProp256Used 4}

drdlProp256UsedLevelEntry OBJECT-TYPE
	SYNTAX      DrdlProp256UsedLevelEntry
	MAX-ACCESS  not-accessible
	STATUS      current
	DESCRIPTION
	"Table entry for drdlProp256Used"
	INDEX { drdlProp256UsedLevelName }
	::={drdlProp256UsedLevelTable 1}

DrdlProp256UsedLevelEntry ::=
	SEQUENCE {
		drdlProp256UsedLevelName	DisplayString,
		drdlProp256UsedLevelVal	CounterBasedGauge64,
		drdlProp256UsedLevelMax	CounterBasedGauge64
	}

drdlProp256UsedLevelName OBJECT-TYPE
	SYNTAX      DisplayString
	MAX-ACCESS  not-accessible
	STATUS      current
	DESCRIPTION
	"Table entry display string for drdlProp256Used"
	::={drdlProp256UsedLevelEntry 1}

drdlProp256UsedLevelVal OBJECT-TYPE
	SYNTAX	 CounterBasedGauge64
	MAX-ACCESS  read-only
	STATUS      current
	DESCRIPTION
	"Table entry attribute for drdlProp256Used"
	::={drdlProp256UsedLevelEntry 2}

drdlProp256UsedLevelMax OBJECT-TYPE
	SYNTAX	 CounterBasedGauge64
	MAX-ACCESS  read-only
	STATUS      current
	DESCRIPTION
	"Table entry attribute for drdlProp256Used"
	::={drdlProp256UsedLevelEntry 4}


drdlAnalyzerChecks	OBJECT IDENTIFIER ::={drdl 11}

drdlAnalyzerChecksVal	OBJECT-TYPE
	SYNTAX	 Counter64
	MAX-ACCESS read-only
	STATUS current
	DESCRIPTION "Analyzer packet checks"

	::={drdlAnalyzerChecks 1}

drdlAnalyzerChecksMom	OBJECT-TYPE
	SYNTAX	 CounterBasedGauge64
	MAX-ACCESS read-only
	STATUS current
	DESCRIPTION "Analyzer packet checks"

	::={drdlAnalyzerChecks 2}

drdlAnalyzerChecksMax	OBJECT-TYPE
	SYNTAX	 CounterBasedGauge64
	MAX-ACCESS read-only
	STATUS current
	DESCRIPTION "Analyzer packet checks"

	::={drdlAnalyzerChecks 3}

drdlAnalyzerChecksLevelTable OBJECT-TYPE
	SYNTAX      SEQUENCE OF DrdlAnalyzerChecksLevelEntry
	MAX-ACCESS  not-accessible
	STATUS      current
	DESCRIPTION
	"Table for drdlAnalyzerChecks"
	::={drdlAnalyzerChecks 4}

drdlAnalyzerChecksLevelEntry OBJECT-TYPE
	SYNTAX      DrdlAnalyzerChecksLevelEntry
	MAX-ACCESS  not-accessible
	STATUS      current
	DESCRIPTION
	"Table entry for drdlAnalyzerChecks"
	INDEX { drdlAnalyzerChecksLevelName }
	::={drdlAnalyzerChecksLevelTable 1}

DrdlAnalyzerChecksLevelEntry ::=
	SEQUENCE {
		drdlAnalyzerChecksLevelName	DisplayString,
		drdlAnalyzerChecksLevelVal	Counter64,
		drdlAnalyzerChecksLevelMom	CounterBasedGauge64,
		drdlAnalyzerChecksLevelMax	CounterBasedGauge64
	}

drdlAnalyzerChecksLevelName OBJECT-TYPE
	SYNTAX      DisplayString
	MAX-ACCESS  not-accessible
	STATUS      current
	DESCRIPTION
	"Table entry display string for drdlAnalyzerChecks"
	::={drdlAnalyzerChecksLevelEntry 1}

drdlAnalyzerChecksLevelVal OBJECT-TYPE
	SYNTAX	 Counter64
	MAX-ACCESS  read-only
	STATUS      current
	DESCRIPTION
	"Table entry attribute for drdlAnalyzerChecks"
	::={drdlAnalyzerChecksLevelEntry 2}

drdlAnalyzerChecksLevelMom OBJECT-TYPE
	SYNTAX	 CounterBasedGauge64
	MAX-ACCESS  read-only
	STATUS      current
	DESCRIPTION
	"Table entry attribute for drdlAnalyzerChecks"
	::={drdlAnalyzerChecksLevelEntry 3}

drdlAnalyzerChecksLevelMax OBJECT-TYPE
	SYNTAX	 CounterBasedGauge64
	MAX-ACCESS  read-only
	STATUS      current
	DESCRIPTION
	"Table entry attribute for drdlAnalyzerChecks"
	::={drdlAnalyzerChecksLevelEntry 4}


drdlAnalyzerCheckedBytes	OBJECT IDENTIFIER ::={drdl 12}

drdlAnalyzerCheckedBytesVal	OBJECT-TYPE
	SYNTAX	 Counter64
	MAX-ACCESS read-only
	STATUS current
	DESCRIPTION "Analyzed bytes"

	::={drdlAnalyzerCheckedBytes 1}

drdlAnalyzerCheckedBytesMom	OBJECT-TYPE
	SYNTAX	 CounterBasedGauge64
	MAX-ACCESS read-only
	STATUS current
	DESCRIPTION "Analyzed bytes"

	::={drdlAnalyzerCheckedBytes 2}

drdlAnalyzerCheckedBytesMax	OBJECT-TYPE
	SYNTAX	 CounterBasedGauge64
	MAX-ACCESS read-only
	STATUS current
	DESCRIPTION "Analyzed bytes"

	::={drdlAnalyzerCheckedBytes 3}

drdlAnalyzerCheckedBytesLevelTable OBJECT-TYPE
	SYNTAX      SEQUENCE OF DrdlAnalyzerCheckedBytesLevelEntry
	MAX-ACCESS  not-accessible
	STATUS      current
	DESCRIPTION
	"Table for drdlAnalyzerCheckedBytes"
	::={drdlAnalyzerCheckedBytes 4}

drdlAnalyzerCheckedBytesLevelEntry OBJECT-TYPE
	SYNTAX      DrdlAnalyzerCheckedBytesLevelEntry
	MAX-ACCESS  not-accessible
	STATUS      current
	DESCRIPTION
	"Table entry for drdlAnalyzerCheckedBytes"
	INDEX { drdlAnalyzerCheckedBytesLevelName }
	::={drdlAnalyzerCheckedBytesLevelTable 1}

DrdlAnalyzerCheckedBytesLevelEntry ::=
	SEQUENCE {
		drdlAnalyzerCheckedBytesLevelName	DisplayString,
		drdlAnalyzerCheckedBytesLevelVal	Counter64,
		drdlAnalyzerCheckedBytesLevelMom	CounterBasedGauge64,
		drdlAnalyzerCheckedBytesLevelMax	CounterBasedGauge64
	}

drdlAnalyzerCheckedBytesLevelName OBJECT-TYPE
	SYNTAX      DisplayString
	MAX-ACCESS  not-accessible
	STATUS      current
	DESCRIPTION
	"Table entry display string for drdlAnalyzerCheckedBytes"
	::={drdlAnalyzerCheckedBytesLevelEntry 1}

drdlAnalyzerCheckedBytesLevelVal OBJECT-TYPE
	SYNTAX	 Counter64
	MAX-ACCESS  read-only
	STATUS      current
	DESCRIPTION
	"Table entry attribute for drdlAnalyzerCheckedBytes"
	::={drdlAnalyzerCheckedBytesLevelEntry 2}

drdlAnalyzerCheckedBytesLevelMom OBJECT-TYPE
	SYNTAX	 CounterBasedGauge64
	MAX-ACCESS  read-only
	STATUS      current
	DESCRIPTION
	"Table entry attribute for drdlAnalyzerCheckedBytes"
	::={drdlAnalyzerCheckedBytesLevelEntry 3}

drdlAnalyzerCheckedBytesLevelMax OBJECT-TYPE
	SYNTAX	 CounterBasedGauge64
	MAX-ACCESS  read-only
	STATUS      current
	DESCRIPTION
	"Table entry attribute for drdlAnalyzerCheckedBytes"
	::={drdlAnalyzerCheckedBytesLevelEntry 4}


drdlAnalyzerSkippedBytes	OBJECT IDENTIFIER ::={drdl 13}

drdlAnalyzerSkippedBytesVal	OBJECT-TYPE
	SYNTAX	 Counter64
	MAX-ACCESS read-only
	STATUS current
	DESCRIPTION "Skipped bytes"

	::={drdlAnalyzerSkippedBytes 1}

drdlAnalyzerSkippedBytesMom	OBJECT-TYPE
	SYNTAX	 CounterBasedGauge64
	MAX-ACCESS read-only
	STATUS current
	DESCRIPTION "Skipped bytes"

	::={drdlAnalyzerSkippedBytes 2}

drdlAnalyzerSkippedBytesMax	OBJECT-TYPE
	SYNTAX	 CounterBasedGauge64
	MAX-ACCESS read-only
	STATUS current
	DESCRIPTION "Skipped bytes"

	::={drdlAnalyzerSkippedBytes 3}

drdlAnalyzerSkippedBytesLevelTable OBJECT-TYPE
	SYNTAX      SEQUENCE OF DrdlAnalyzerSkippedBytesLevelEntry
	MAX-ACCESS  not-accessible
	STATUS      current
	DESCRIPTION
	"Table for drdlAnalyzerSkippedBytes"
	::={drdlAnalyzerSkippedBytes 4}

drdlAnalyzerSkippedBytesLevelEntry OBJECT-TYPE
	SYNTAX      DrdlAnalyzerSkippedBytesLevelEntry
	MAX-ACCESS  not-accessible
	STATUS      current
	DESCRIPTION
	"Table entry for drdlAnalyzerSkippedBytes"
	INDEX { drdlAnalyzerSkippedBytesLevelName }
	::={drdlAnalyzerSkippedBytesLevelTable 1}

DrdlAnalyzerSkippedBytesLevelEntry ::=
	SEQUENCE {
		drdlAnalyzerSkippedBytesLevelName	DisplayString,
		drdlAnalyzerSkippedBytesLevelVal	Counter64,
		drdlAnalyzerSkippedBytesLevelMom	CounterBasedGauge64,
		drdlAnalyzerSkippedBytesLevelMax	CounterBasedGauge64
	}

drdlAnalyzerSkippedBytesLevelName OBJECT-TYPE
	SYNTAX      DisplayString
	MAX-ACCESS  not-accessible
	STATUS      current
	DESCRIPTION
	"Table entry display string for drdlAnalyzerSkippedBytes"
	::={drdlAnalyzerSkippedBytesLevelEntry 1}

drdlAnalyzerSkippedBytesLevelVal OBJECT-TYPE
	SYNTAX	 Counter64
	MAX-ACCESS  read-only
	STATUS      current
	DESCRIPTION
	"Table entry attribute for drdlAnalyzerSkippedBytes"
	::={drdlAnalyzerSkippedBytesLevelEntry 2}

drdlAnalyzerSkippedBytesLevelMom OBJECT-TYPE
	SYNTAX	 CounterBasedGauge64
	MAX-ACCESS  read-only
	STATUS      current
	DESCRIPTION
	"Table entry attribute for drdlAnalyzerSkippedBytes"
	::={drdlAnalyzerSkippedBytesLevelEntry 3}

drdlAnalyzerSkippedBytesLevelMax OBJECT-TYPE
	SYNTAX	 CounterBasedGauge64
	MAX-ACCESS  read-only
	STATUS      current
	DESCRIPTION
	"Table entry attribute for drdlAnalyzerSkippedBytes"
	::={drdlAnalyzerSkippedBytesLevelEntry 4}


drdlAnalyzerActions	OBJECT IDENTIFIER ::={drdl 14}

drdlAnalyzerActionsVal	OBJECT-TYPE
	SYNTAX	 Counter64
	MAX-ACCESS read-only
	STATUS current
	DESCRIPTION "Analyzer actions called"

	::={drdlAnalyzerActions 1}

drdlAnalyzerActionsMom	OBJECT-TYPE
	SYNTAX	 CounterBasedGauge64
	MAX-ACCESS read-only
	STATUS current
	DESCRIPTION "Analyzer actions called"

	::={drdlAnalyzerActions 2}

drdlAnalyzerActionsMax	OBJECT-TYPE
	SYNTAX	 CounterBasedGauge64
	MAX-ACCESS read-only
	STATUS current
	DESCRIPTION "Analyzer actions called"

	::={drdlAnalyzerActions 3}

drdlAnalyzerActionsLevelTable OBJECT-TYPE
	SYNTAX      SEQUENCE OF DrdlAnalyzerActionsLevelEntry
	MAX-ACCESS  not-accessible
	STATUS      current
	DESCRIPTION
	"Table for drdlAnalyzerActions"
	::={drdlAnalyzerActions 4}

drdlAnalyzerActionsLevelEntry OBJECT-TYPE
	SYNTAX      DrdlAnalyzerActionsLevelEntry
	MAX-ACCESS  not-accessible
	STATUS      current
	DESCRIPTION
	"Table entry for drdlAnalyzerActions"
	INDEX { drdlAnalyzerActionsLevelName }
	::={drdlAnalyzerActionsLevelTable 1}

DrdlAnalyzerActionsLevelEntry ::=
	SEQUENCE {
		drdlAnalyzerActionsLevelName	DisplayString,
		drdlAnalyzerActionsLevelVal	Counter64,
		drdlAnalyzerActionsLevelMom	CounterBasedGauge64,
		drdlAnalyzerActionsLevelMax	CounterBasedGauge64
	}

drdlAnalyzerActionsLevelName OBJECT-TYPE
	SYNTAX      DisplayString
	MAX-ACCESS  not-accessible
	STATUS      current
	DESCRIPTION
	"Table entry display string for drdlAnalyzerActions"
	::={drdlAnalyzerActionsLevelEntry 1}

drdlAnalyzerActionsLevelVal OBJECT-TYPE
	SYNTAX	 Counter64
	MAX-ACCESS  read-only
	STATUS      current
	DESCRIPTION
	"Table entry attribute for drdlAnalyzerActions"
	::={drdlAnalyzerActionsLevelEntry 2}

drdlAnalyzerActionsLevelMom OBJECT-TYPE
	SYNTAX	 CounterBasedGauge64
	MAX-ACCESS  read-only
	STATUS      current
	DESCRIPTION
	"Table entry attribute for drdlAnalyzerActions"
	::={drdlAnalyzerActionsLevelEntry 3}

drdlAnalyzerActionsLevelMax OBJECT-TYPE
	SYNTAX	 CounterBasedGauge64
	MAX-ACCESS  read-only
	STATUS      current
	DESCRIPTION
	"Table entry attribute for drdlAnalyzerActions"
	::={drdlAnalyzerActionsLevelEntry 4}


drdlPropertySet	OBJECT IDENTIFIER ::={drdl 15}

drdlPropertySetVal	OBJECT-TYPE
	SYNTAX	 Counter64
	MAX-ACCESS read-only
	STATUS current
	DESCRIPTION "Analyzer properties set"

	::={drdlPropertySet 1}

drdlPropertySetMom	OBJECT-TYPE
	SYNTAX	 CounterBasedGauge64
	MAX-ACCESS read-only
	STATUS current
	DESCRIPTION "Analyzer properties set"

	::={drdlPropertySet 2}

drdlPropertySetMax	OBJECT-TYPE
	SYNTAX	 CounterBasedGauge64
	MAX-ACCESS read-only
	STATUS current
	DESCRIPTION "Analyzer properties set"

	::={drdlPropertySet 3}

drdlPropertySetLevelTable OBJECT-TYPE
	SYNTAX      SEQUENCE OF DrdlPropertySetLevelEntry
	MAX-ACCESS  not-accessible
	STATUS      current
	DESCRIPTION
	"Table for drdlPropertySet"
	::={drdlPropertySet 4}

drdlPropertySetLevelEntry OBJECT-TYPE
	SYNTAX      DrdlPropertySetLevelEntry
	MAX-ACCESS  not-accessible
	STATUS      current
	DESCRIPTION
	"Table entry for drdlPropertySet"
	INDEX { drdlPropertySetLevelName }
	::={drdlPropertySetLevelTable 1}

DrdlPropertySetLevelEntry ::=
	SEQUENCE {
		drdlPropertySetLevelName	DisplayString,
		drdlPropertySetLevelVal	Counter64,
		drdlPropertySetLevelMom	CounterBasedGauge64,
		drdlPropertySetLevelMax	CounterBasedGauge64
	}

drdlPropertySetLevelName OBJECT-TYPE
	SYNTAX      DisplayString
	MAX-ACCESS  not-accessible
	STATUS      current
	DESCRIPTION
	"Table entry display string for drdlPropertySet"
	::={drdlPropertySetLevelEntry 1}

drdlPropertySetLevelVal OBJECT-TYPE
	SYNTAX	 Counter64
	MAX-ACCESS  read-only
	STATUS      current
	DESCRIPTION
	"Table entry attribute for drdlPropertySet"
	::={drdlPropertySetLevelEntry 2}

drdlPropertySetLevelMom OBJECT-TYPE
	SYNTAX	 CounterBasedGauge64
	MAX-ACCESS  read-only
	STATUS      current
	DESCRIPTION
	"Table entry attribute for drdlPropertySet"
	::={drdlPropertySetLevelEntry 3}

drdlPropertySetLevelMax OBJECT-TYPE
	SYNTAX	 CounterBasedGauge64
	MAX-ACCESS  read-only
	STATUS      current
	DESCRIPTION
	"Table entry attribute for drdlPropertySet"
	::={drdlPropertySetLevelEntry 4}


drdlOrphans	OBJECT IDENTIFIER ::={drdl 18}

drdlOrphansVal	OBJECT-TYPE
	SYNTAX	 Counter64
	MAX-ACCESS read-only
	STATUS current
	DESCRIPTION "Orphaned childconnections"

	::={drdlOrphans 1}

drdlOrphansMom	OBJECT-TYPE
	SYNTAX	 CounterBasedGauge64
	MAX-ACCESS read-only
	STATUS current
	DESCRIPTION "Orphaned childconnections"

	::={drdlOrphans 2}

drdlOrphansMax	OBJECT-TYPE
	SYNTAX	 CounterBasedGauge64
	MAX-ACCESS read-only
	STATUS current
	DESCRIPTION "Orphaned childconnections"

	::={drdlOrphans 3}

drdlOrphansLevelTable OBJECT-TYPE
	SYNTAX      SEQUENCE OF DrdlOrphansLevelEntry
	MAX-ACCESS  not-accessible
	STATUS      current
	DESCRIPTION
	"Table for drdlOrphans"
	::={drdlOrphans 4}

drdlOrphansLevelEntry OBJECT-TYPE
	SYNTAX      DrdlOrphansLevelEntry
	MAX-ACCESS  not-accessible
	STATUS      current
	DESCRIPTION
	"Table entry for drdlOrphans"
	INDEX { drdlOrphansLevelName }
	::={drdlOrphansLevelTable 1}

DrdlOrphansLevelEntry ::=
	SEQUENCE {
		drdlOrphansLevelName	DisplayString,
		drdlOrphansLevelVal	Counter64,
		drdlOrphansLevelMom	CounterBasedGauge64,
		drdlOrphansLevelMax	CounterBasedGauge64
	}

drdlOrphansLevelName OBJECT-TYPE
	SYNTAX      DisplayString
	MAX-ACCESS  not-accessible
	STATUS      current
	DESCRIPTION
	"Table entry display string for drdlOrphans"
	::={drdlOrphansLevelEntry 1}

drdlOrphansLevelVal OBJECT-TYPE
	SYNTAX	 Counter64
	MAX-ACCESS  read-only
	STATUS      current
	DESCRIPTION
	"Table entry attribute for drdlOrphans"
	::={drdlOrphansLevelEntry 2}

drdlOrphansLevelMom OBJECT-TYPE
	SYNTAX	 CounterBasedGauge64
	MAX-ACCESS  read-only
	STATUS      current
	DESCRIPTION
	"Table entry attribute for drdlOrphans"
	::={drdlOrphansLevelEntry 3}

drdlOrphansLevelMax OBJECT-TYPE
	SYNTAX	 CounterBasedGauge64
	MAX-ACCESS  read-only
	STATUS      current
	DESCRIPTION
	"Table entry attribute for drdlOrphans"
	::={drdlOrphansLevelEntry 4}


drdlAutoAccepts	OBJECT IDENTIFIER ::={drdl 21}

drdlAutoAcceptsVal	OBJECT-TYPE
	SYNTAX	 Counter64
	MAX-ACCESS read-only
	STATUS current
	DESCRIPTION "Number of automatic accepts"

	::={drdlAutoAccepts 1}

drdlAutoAcceptsMom	OBJECT-TYPE
	SYNTAX	 CounterBasedGauge64
	MAX-ACCESS read-only
	STATUS current
	DESCRIPTION "Number of automatic accepts"

	::={drdlAutoAccepts 2}

drdlAutoAcceptsMax	OBJECT-TYPE
	SYNTAX	 CounterBasedGauge64
	MAX-ACCESS read-only
	STATUS current
	DESCRIPTION "Number of automatic accepts"

	::={drdlAutoAccepts 3}

drdlAutoAcceptsLevelTable OBJECT-TYPE
	SYNTAX      SEQUENCE OF DrdlAutoAcceptsLevelEntry
	MAX-ACCESS  not-accessible
	STATUS      current
	DESCRIPTION
	"Table for drdlAutoAccepts"
	::={drdlAutoAccepts 4}

drdlAutoAcceptsLevelEntry OBJECT-TYPE
	SYNTAX      DrdlAutoAcceptsLevelEntry
	MAX-ACCESS  not-accessible
	STATUS      current
	DESCRIPTION
	"Table entry for drdlAutoAccepts"
	INDEX { drdlAutoAcceptsLevelName }
	::={drdlAutoAcceptsLevelTable 1}

DrdlAutoAcceptsLevelEntry ::=
	SEQUENCE {
		drdlAutoAcceptsLevelName	DisplayString,
		drdlAutoAcceptsLevelVal	Counter64,
		drdlAutoAcceptsLevelMom	CounterBasedGauge64,
		drdlAutoAcceptsLevelMax	CounterBasedGauge64
	}

drdlAutoAcceptsLevelName OBJECT-TYPE
	SYNTAX      DisplayString
	MAX-ACCESS  not-accessible
	STATUS      current
	DESCRIPTION
	"Table entry display string for drdlAutoAccepts"
	::={drdlAutoAcceptsLevelEntry 1}

drdlAutoAcceptsLevelVal OBJECT-TYPE
	SYNTAX	 Counter64
	MAX-ACCESS  read-only
	STATUS      current
	DESCRIPTION
	"Table entry attribute for drdlAutoAccepts"
	::={drdlAutoAcceptsLevelEntry 2}

drdlAutoAcceptsLevelMom OBJECT-TYPE
	SYNTAX	 CounterBasedGauge64
	MAX-ACCESS  read-only
	STATUS      current
	DESCRIPTION
	"Table entry attribute for drdlAutoAccepts"
	::={drdlAutoAcceptsLevelEntry 3}

drdlAutoAcceptsLevelMax OBJECT-TYPE
	SYNTAX	 CounterBasedGauge64
	MAX-ACCESS  read-only
	STATUS      current
	DESCRIPTION
	"Table entry attribute for drdlAutoAccepts"
	::={drdlAutoAcceptsLevelEntry 4}


drdlBuffersUsed	OBJECT IDENTIFIER ::={drdl 22}

drdlBuffersUsedVal	OBJECT-TYPE
	SYNTAX	 CounterBasedGauge64
	MAX-ACCESS read-only
	STATUS current
	DESCRIPTION "Number of buffers used"

	::={drdlBuffersUsed 1}

drdlBuffersUsedMax	OBJECT-TYPE
	SYNTAX	 CounterBasedGauge64
	MAX-ACCESS read-only
	STATUS current
	DESCRIPTION "Number of buffers used"

	::={drdlBuffersUsed 3}

drdlBuffersUsedLevelTable OBJECT-TYPE
	SYNTAX      SEQUENCE OF DrdlBuffersUsedLevelEntry
	MAX-ACCESS  not-accessible
	STATUS      current
	DESCRIPTION
	"Table for drdlBuffersUsed"
	::={drdlBuffersUsed 4}

drdlBuffersUsedLevelEntry OBJECT-TYPE
	SYNTAX      DrdlBuffersUsedLevelEntry
	MAX-ACCESS  not-accessible
	STATUS      current
	DESCRIPTION
	"Table entry for drdlBuffersUsed"
	INDEX { drdlBuffersUsedLevelName }
	::={drdlBuffersUsedLevelTable 1}

DrdlBuffersUsedLevelEntry ::=
	SEQUENCE {
		drdlBuffersUsedLevelName	DisplayString,
		drdlBuffersUsedLevelVal	CounterBasedGauge64,
		drdlBuffersUsedLevelMax	CounterBasedGauge64
	}

drdlBuffersUsedLevelName OBJECT-TYPE
	SYNTAX      DisplayString
	MAX-ACCESS  not-accessible
	STATUS      current
	DESCRIPTION
	"Table entry display string for drdlBuffersUsed"
	::={drdlBuffersUsedLevelEntry 1}

drdlBuffersUsedLevelVal OBJECT-TYPE
	SYNTAX	 CounterBasedGauge64
	MAX-ACCESS  read-only
	STATUS      current
	DESCRIPTION
	"Table entry attribute for drdlBuffersUsed"
	::={drdlBuffersUsedLevelEntry 2}

drdlBuffersUsedLevelMax OBJECT-TYPE
	SYNTAX	 CounterBasedGauge64
	MAX-ACCESS  read-only
	STATUS      current
	DESCRIPTION
	"Table entry attribute for drdlBuffersUsed"
	::={drdlBuffersUsedLevelEntry 4}


drdlBufferAllocationFailures	OBJECT IDENTIFIER ::={drdl 23}

drdlBufferAllocationFailuresVal	OBJECT-TYPE
	SYNTAX	 Counter64
	MAX-ACCESS read-only
	STATUS current
	DESCRIPTION "Number of buffer allocation failures"

	::={drdlBufferAllocationFailures 1}

drdlBufferAllocationFailuresMom	OBJECT-TYPE
	SYNTAX	 CounterBasedGauge64
	MAX-ACCESS read-only
	STATUS current
	DESCRIPTION "Number of buffer allocation failures"

	::={drdlBufferAllocationFailures 2}

drdlBufferAllocationFailuresMax	OBJECT-TYPE
	SYNTAX	 CounterBasedGauge64
	MAX-ACCESS read-only
	STATUS current
	DESCRIPTION "Number of buffer allocation failures"

	::={drdlBufferAllocationFailures 3}

drdlBufferAllocationFailuresLevelTable OBJECT-TYPE
	SYNTAX      SEQUENCE OF DrdlBufferAllocationFailuresLevelEntry
	MAX-ACCESS  not-accessible
	STATUS      current
	DESCRIPTION
	"Table for drdlBufferAllocationFailures"
	::={drdlBufferAllocationFailures 4}

drdlBufferAllocationFailuresLevelEntry OBJECT-TYPE
	SYNTAX      DrdlBufferAllocationFailuresLevelEntry
	MAX-ACCESS  not-accessible
	STATUS      current
	DESCRIPTION
	"Table entry for drdlBufferAllocationFailures"
	INDEX { drdlBufferAllocationFailuresLevelName }
	::={drdlBufferAllocationFailuresLevelTable 1}

DrdlBufferAllocationFailuresLevelEntry ::=
	SEQUENCE {
		drdlBufferAllocationFailuresLevelName	DisplayString,
		drdlBufferAllocationFailuresLevelVal	Counter64,
		drdlBufferAllocationFailuresLevelMom	CounterBasedGauge64,
		drdlBufferAllocationFailuresLevelMax	CounterBasedGauge64
	}

drdlBufferAllocationFailuresLevelName OBJECT-TYPE
	SYNTAX      DisplayString
	MAX-ACCESS  not-accessible
	STATUS      current
	DESCRIPTION
	"Table entry display string for drdlBufferAllocationFailures"
	::={drdlBufferAllocationFailuresLevelEntry 1}

drdlBufferAllocationFailuresLevelVal OBJECT-TYPE
	SYNTAX	 Counter64
	MAX-ACCESS  read-only
	STATUS      current
	DESCRIPTION
	"Table entry attribute for drdlBufferAllocationFailures"
	::={drdlBufferAllocationFailuresLevelEntry 2}

drdlBufferAllocationFailuresLevelMom OBJECT-TYPE
	SYNTAX	 CounterBasedGauge64
	MAX-ACCESS  read-only
	STATUS      current
	DESCRIPTION
	"Table entry attribute for drdlBufferAllocationFailures"
	::={drdlBufferAllocationFailuresLevelEntry 3}

drdlBufferAllocationFailuresLevelMax OBJECT-TYPE
	SYNTAX	 CounterBasedGauge64
	MAX-ACCESS  read-only
	STATUS      current
	DESCRIPTION
	"Table entry attribute for drdlBufferAllocationFailures"
	::={drdlBufferAllocationFailuresLevelEntry 4}


drdlFullPackets	OBJECT IDENTIFIER ::={drdl 24}

drdlFullPacketsVal	OBJECT-TYPE
	SYNTAX	 Counter64
	MAX-ACCESS read-only
	STATUS current
	DESCRIPTION "Number of full run packets"

	::={drdlFullPackets 1}

drdlFullPacketsMom	OBJECT-TYPE
	SYNTAX	 CounterBasedGauge64
	MAX-ACCESS read-only
	STATUS current
	DESCRIPTION "Number of full run packets"

	::={drdlFullPackets 2}

drdlFullPacketsMax	OBJECT-TYPE
	SYNTAX	 CounterBasedGauge64
	MAX-ACCESS read-only
	STATUS current
	DESCRIPTION "Number of full run packets"

	::={drdlFullPackets 3}

drdlFullPacketsLevelTable OBJECT-TYPE
	SYNTAX      SEQUENCE OF DrdlFullPacketsLevelEntry
	MAX-ACCESS  not-accessible
	STATUS      current
	DESCRIPTION
	"Table for drdlFullPackets"
	::={drdlFullPackets 4}

drdlFullPacketsLevelEntry OBJECT-TYPE
	SYNTAX      DrdlFullPacketsLevelEntry
	MAX-ACCESS  not-accessible
	STATUS      current
	DESCRIPTION
	"Table entry for drdlFullPackets"
	INDEX { drdlFullPacketsLevelName }
	::={drdlFullPacketsLevelTable 1}

DrdlFullPacketsLevelEntry ::=
	SEQUENCE {
		drdlFullPacketsLevelName	DisplayString,
		drdlFullPacketsLevelVal	Counter64,
		drdlFullPacketsLevelMom	CounterBasedGauge64,
		drdlFullPacketsLevelMax	CounterBasedGauge64
	}

drdlFullPacketsLevelName OBJECT-TYPE
	SYNTAX      DisplayString
	MAX-ACCESS  not-accessible
	STATUS      current
	DESCRIPTION
	"Table entry display string for drdlFullPackets"
	::={drdlFullPacketsLevelEntry 1}

drdlFullPacketsLevelVal OBJECT-TYPE
	SYNTAX	 Counter64
	MAX-ACCESS  read-only
	STATUS      current
	DESCRIPTION
	"Table entry attribute for drdlFullPackets"
	::={drdlFullPacketsLevelEntry 2}

drdlFullPacketsLevelMom OBJECT-TYPE
	SYNTAX	 CounterBasedGauge64
	MAX-ACCESS  read-only
	STATUS      current
	DESCRIPTION
	"Table entry attribute for drdlFullPackets"
	::={drdlFullPacketsLevelEntry 3}

drdlFullPacketsLevelMax OBJECT-TYPE
	SYNTAX	 CounterBasedGauge64
	MAX-ACCESS  read-only
	STATUS      current
	DESCRIPTION
	"Table entry attribute for drdlFullPackets"
	::={drdlFullPacketsLevelEntry 4}


drdlProp0Fail	OBJECT IDENTIFIER ::={drdl 25}

drdlProp0FailVal	OBJECT-TYPE
	SYNTAX	 CounterBasedGauge64
	MAX-ACCESS read-only
	STATUS obsolete
	DESCRIPTION "Unused"

	::={drdlProp0Fail 1}

drdlProp0FailMax	OBJECT-TYPE
	SYNTAX	 CounterBasedGauge64
	MAX-ACCESS read-only
	STATUS obsolete
	DESCRIPTION "Unused"

	::={drdlProp0Fail 3}

drdlProp0FailLevelTable OBJECT-TYPE
	SYNTAX      SEQUENCE OF DrdlProp0FailLevelEntry
	MAX-ACCESS  not-accessible
	STATUS      current
	DESCRIPTION
	"Table for drdlProp0Fail"
	::={drdlProp0Fail 4}

drdlProp0FailLevelEntry OBJECT-TYPE
	SYNTAX      DrdlProp0FailLevelEntry
	MAX-ACCESS  not-accessible
	STATUS      current
	DESCRIPTION
	"Table entry for drdlProp0Fail"
	INDEX { drdlProp0FailLevelName }
	::={drdlProp0FailLevelTable 1}

DrdlProp0FailLevelEntry ::=
	SEQUENCE {
		drdlProp0FailLevelName	DisplayString,
		drdlProp0FailLevelVal	CounterBasedGauge64,
		drdlProp0FailLevelMax	CounterBasedGauge64
	}

drdlProp0FailLevelName OBJECT-TYPE
	SYNTAX      DisplayString
	MAX-ACCESS  not-accessible
	STATUS      current
	DESCRIPTION
	"Table entry display string for drdlProp0Fail"
	::={drdlProp0FailLevelEntry 1}

drdlProp0FailLevelVal OBJECT-TYPE
	SYNTAX	 CounterBasedGauge64
	MAX-ACCESS  read-only
	STATUS      current
	DESCRIPTION
	"Table entry attribute for drdlProp0Fail"
	::={drdlProp0FailLevelEntry 2}

drdlProp0FailLevelMax OBJECT-TYPE
	SYNTAX	 CounterBasedGauge64
	MAX-ACCESS  read-only
	STATUS      current
	DESCRIPTION
	"Table entry attribute for drdlProp0Fail"
	::={drdlProp0FailLevelEntry 4}


drdlProp0Used	OBJECT IDENTIFIER ::={drdl 26}

drdlProp0UsedVal	OBJECT-TYPE
	SYNTAX	 CounterBasedGauge64
	MAX-ACCESS read-only
	STATUS obsolete
	DESCRIPTION "Unused"

	::={drdlProp0Used 1}

drdlProp0UsedMax	OBJECT-TYPE
	SYNTAX	 CounterBasedGauge64
	MAX-ACCESS read-only
	STATUS obsolete
	DESCRIPTION "Unused"

	::={drdlProp0Used 3}

drdlProp0UsedLevelTable OBJECT-TYPE
	SYNTAX      SEQUENCE OF DrdlProp0UsedLevelEntry
	MAX-ACCESS  not-accessible
	STATUS      current
	DESCRIPTION
	"Table for drdlProp0Used"
	::={drdlProp0Used 4}

drdlProp0UsedLevelEntry OBJECT-TYPE
	SYNTAX      DrdlProp0UsedLevelEntry
	MAX-ACCESS  not-accessible
	STATUS      current
	DESCRIPTION
	"Table entry for drdlProp0Used"
	INDEX { drdlProp0UsedLevelName }
	::={drdlProp0UsedLevelTable 1}

DrdlProp0UsedLevelEntry ::=
	SEQUENCE {
		drdlProp0UsedLevelName	DisplayString,
		drdlProp0UsedLevelVal	CounterBasedGauge64,
		drdlProp0UsedLevelMax	CounterBasedGauge64
	}

drdlProp0UsedLevelName OBJECT-TYPE
	SYNTAX      DisplayString
	MAX-ACCESS  not-accessible
	STATUS      current
	DESCRIPTION
	"Table entry display string for drdlProp0Used"
	::={drdlProp0UsedLevelEntry 1}

drdlProp0UsedLevelVal OBJECT-TYPE
	SYNTAX	 CounterBasedGauge64
	MAX-ACCESS  read-only
	STATUS      current
	DESCRIPTION
	"Table entry attribute for drdlProp0Used"
	::={drdlProp0UsedLevelEntry 2}

drdlProp0UsedLevelMax OBJECT-TYPE
	SYNTAX	 CounterBasedGauge64
	MAX-ACCESS  read-only
	STATUS      current
	DESCRIPTION
	"Table entry attribute for drdlProp0Used"
	::={drdlProp0UsedLevelEntry 4}


drdlSliceStateUsed	OBJECT IDENTIFIER ::={drdl 27}

drdlSliceStateUsedVal	OBJECT-TYPE
	SYNTAX	 CounterBasedGauge64
	MAX-ACCESS read-only
	STATUS current
	DESCRIPTION "Number of slice state structures used"

	::={drdlSliceStateUsed 1}

drdlSliceStateUsedMax	OBJECT-TYPE
	SYNTAX	 CounterBasedGauge64
	MAX-ACCESS read-only
	STATUS current
	DESCRIPTION "Number of slice state structures used"

	::={drdlSliceStateUsed 3}

drdlSliceStateUsedLevelTable OBJECT-TYPE
	SYNTAX      SEQUENCE OF DrdlSliceStateUsedLevelEntry
	MAX-ACCESS  not-accessible
	STATUS      current
	DESCRIPTION
	"Table for drdlSliceStateUsed"
	::={drdlSliceStateUsed 4}

drdlSliceStateUsedLevelEntry OBJECT-TYPE
	SYNTAX      DrdlSliceStateUsedLevelEntry
	MAX-ACCESS  not-accessible
	STATUS      current
	DESCRIPTION
	"Table entry for drdlSliceStateUsed"
	INDEX { drdlSliceStateUsedLevelName }
	::={drdlSliceStateUsedLevelTable 1}

DrdlSliceStateUsedLevelEntry ::=
	SEQUENCE {
		drdlSliceStateUsedLevelName	DisplayString,
		drdlSliceStateUsedLevelVal	CounterBasedGauge64,
		drdlSliceStateUsedLevelMax	CounterBasedGauge64
	}

drdlSliceStateUsedLevelName OBJECT-TYPE
	SYNTAX      DisplayString
	MAX-ACCESS  not-accessible
	STATUS      current
	DESCRIPTION
	"Table entry display string for drdlSliceStateUsed"
	::={drdlSliceStateUsedLevelEntry 1}

drdlSliceStateUsedLevelVal OBJECT-TYPE
	SYNTAX	 CounterBasedGauge64
	MAX-ACCESS  read-only
	STATUS      current
	DESCRIPTION
	"Table entry attribute for drdlSliceStateUsed"
	::={drdlSliceStateUsedLevelEntry 2}

drdlSliceStateUsedLevelMax OBJECT-TYPE
	SYNTAX	 CounterBasedGauge64
	MAX-ACCESS  read-only
	STATUS      current
	DESCRIPTION
	"Table entry attribute for drdlSliceStateUsed"
	::={drdlSliceStateUsedLevelEntry 4}


drdlSliceStateFail	OBJECT IDENTIFIER ::={drdl 28}

drdlSliceStateFailVal	OBJECT-TYPE
	SYNTAX	 Counter64
	MAX-ACCESS read-only
	STATUS current
	DESCRIPTION "Number of slice state structure allocation failures"

	::={drdlSliceStateFail 1}

drdlSliceStateFailMom	OBJECT-TYPE
	SYNTAX	 CounterBasedGauge64
	MAX-ACCESS read-only
	STATUS current
	DESCRIPTION "Number of slice state structure allocation failures"

	::={drdlSliceStateFail 2}

drdlSliceStateFailMax	OBJECT-TYPE
	SYNTAX	 CounterBasedGauge64
	MAX-ACCESS read-only
	STATUS current
	DESCRIPTION "Number of slice state structure allocation failures"

	::={drdlSliceStateFail 3}

drdlSliceStateFailLevelTable OBJECT-TYPE
	SYNTAX      SEQUENCE OF DrdlSliceStateFailLevelEntry
	MAX-ACCESS  not-accessible
	STATUS      current
	DESCRIPTION
	"Table for drdlSliceStateFail"
	::={drdlSliceStateFail 4}

drdlSliceStateFailLevelEntry OBJECT-TYPE
	SYNTAX      DrdlSliceStateFailLevelEntry
	MAX-ACCESS  not-accessible
	STATUS      current
	DESCRIPTION
	"Table entry for drdlSliceStateFail"
	INDEX { drdlSliceStateFailLevelName }
	::={drdlSliceStateFailLevelTable 1}

DrdlSliceStateFailLevelEntry ::=
	SEQUENCE {
		drdlSliceStateFailLevelName	DisplayString,
		drdlSliceStateFailLevelVal	Counter64,
		drdlSliceStateFailLevelMom	CounterBasedGauge64,
		drdlSliceStateFailLevelMax	CounterBasedGauge64
	}

drdlSliceStateFailLevelName OBJECT-TYPE
	SYNTAX      DisplayString
	MAX-ACCESS  not-accessible
	STATUS      current
	DESCRIPTION
	"Table entry display string for drdlSliceStateFail"
	::={drdlSliceStateFailLevelEntry 1}

drdlSliceStateFailLevelVal OBJECT-TYPE
	SYNTAX	 Counter64
	MAX-ACCESS  read-only
	STATUS      current
	DESCRIPTION
	"Table entry attribute for drdlSliceStateFail"
	::={drdlSliceStateFailLevelEntry 2}

drdlSliceStateFailLevelMom OBJECT-TYPE
	SYNTAX	 CounterBasedGauge64
	MAX-ACCESS  read-only
	STATUS      current
	DESCRIPTION
	"Table entry attribute for drdlSliceStateFail"
	::={drdlSliceStateFailLevelEntry 3}

drdlSliceStateFailLevelMax OBJECT-TYPE
	SYNTAX	 CounterBasedGauge64
	MAX-ACCESS  read-only
	STATUS      current
	DESCRIPTION
	"Table entry attribute for drdlSliceStateFail"
	::={drdlSliceStateFailLevelEntry 4}


drdlLiteralSet	OBJECT IDENTIFIER ::={drdl 29}

drdlLiteralSetVal	OBJECT-TYPE
	SYNTAX	 Counter64
	MAX-ACCESS read-only
	STATUS current
	DESCRIPTION "Analyzer literals set"

	::={drdlLiteralSet 1}

drdlLiteralSetMom	OBJECT-TYPE
	SYNTAX	 CounterBasedGauge64
	MAX-ACCESS read-only
	STATUS current
	DESCRIPTION "Analyzer literals set"

	::={drdlLiteralSet 2}

drdlLiteralSetMax	OBJECT-TYPE
	SYNTAX	 CounterBasedGauge64
	MAX-ACCESS read-only
	STATUS current
	DESCRIPTION "Analyzer literals set"

	::={drdlLiteralSet 3}

drdlLiteralSetLevelTable OBJECT-TYPE
	SYNTAX      SEQUENCE OF DrdlLiteralSetLevelEntry
	MAX-ACCESS  not-accessible
	STATUS      current
	DESCRIPTION
	"Table for drdlLiteralSet"
	::={drdlLiteralSet 4}

drdlLiteralSetLevelEntry OBJECT-TYPE
	SYNTAX      DrdlLiteralSetLevelEntry
	MAX-ACCESS  not-accessible
	STATUS      current
	DESCRIPTION
	"Table entry for drdlLiteralSet"
	INDEX { drdlLiteralSetLevelName }
	::={drdlLiteralSetLevelTable 1}

DrdlLiteralSetLevelEntry ::=
	SEQUENCE {
		drdlLiteralSetLevelName	DisplayString,
		drdlLiteralSetLevelVal	Counter64,
		drdlLiteralSetLevelMom	CounterBasedGauge64,
		drdlLiteralSetLevelMax	CounterBasedGauge64
	}

drdlLiteralSetLevelName OBJECT-TYPE
	SYNTAX      DisplayString
	MAX-ACCESS  not-accessible
	STATUS      current
	DESCRIPTION
	"Table entry display string for drdlLiteralSet"
	::={drdlLiteralSetLevelEntry 1}

drdlLiteralSetLevelVal OBJECT-TYPE
	SYNTAX	 Counter64
	MAX-ACCESS  read-only
	STATUS      current
	DESCRIPTION
	"Table entry attribute for drdlLiteralSet"
	::={drdlLiteralSetLevelEntry 2}

drdlLiteralSetLevelMom OBJECT-TYPE
	SYNTAX	 CounterBasedGauge64
	MAX-ACCESS  read-only
	STATUS      current
	DESCRIPTION
	"Table entry attribute for drdlLiteralSet"
	::={drdlLiteralSetLevelEntry 3}

drdlLiteralSetLevelMax OBJECT-TYPE
	SYNTAX	 CounterBasedGauge64
	MAX-ACCESS  read-only
	STATUS      current
	DESCRIPTION
	"Table entry attribute for drdlLiteralSet"
	::={drdlLiteralSetLevelEntry 4}


drdlPropertyFail	OBJECT IDENTIFIER ::={drdl 30}

drdlPropertyFailVal	OBJECT-TYPE
	SYNTAX	 Counter64
	MAX-ACCESS read-only
	STATUS current
	DESCRIPTION "Analyzer properties that could not be set"

	::={drdlPropertyFail 1}

drdlPropertyFailMom	OBJECT-TYPE
	SYNTAX	 CounterBasedGauge64
	MAX-ACCESS read-only
	STATUS current
	DESCRIPTION "Analyzer properties that could not be set"

	::={drdlPropertyFail 2}

drdlPropertyFailMax	OBJECT-TYPE
	SYNTAX	 CounterBasedGauge64
	MAX-ACCESS read-only
	STATUS current
	DESCRIPTION "Analyzer properties that could not be set"

	::={drdlPropertyFail 3}

drdlPropertyFailLevelTable OBJECT-TYPE
	SYNTAX      SEQUENCE OF DrdlPropertyFailLevelEntry
	MAX-ACCESS  not-accessible
	STATUS      current
	DESCRIPTION
	"Table for drdlPropertyFail"
	::={drdlPropertyFail 4}

drdlPropertyFailLevelEntry OBJECT-TYPE
	SYNTAX      DrdlPropertyFailLevelEntry
	MAX-ACCESS  not-accessible
	STATUS      current
	DESCRIPTION
	"Table entry for drdlPropertyFail"
	INDEX { drdlPropertyFailLevelName }
	::={drdlPropertyFailLevelTable 1}

DrdlPropertyFailLevelEntry ::=
	SEQUENCE {
		drdlPropertyFailLevelName	DisplayString,
		drdlPropertyFailLevelVal	Counter64,
		drdlPropertyFailLevelMom	CounterBasedGauge64,
		drdlPropertyFailLevelMax	CounterBasedGauge64
	}

drdlPropertyFailLevelName OBJECT-TYPE
	SYNTAX      DisplayString
	MAX-ACCESS  not-accessible
	STATUS      current
	DESCRIPTION
	"Table entry display string for drdlPropertyFail"
	::={drdlPropertyFailLevelEntry 1}

drdlPropertyFailLevelVal OBJECT-TYPE
	SYNTAX	 Counter64
	MAX-ACCESS  read-only
	STATUS      current
	DESCRIPTION
	"Table entry attribute for drdlPropertyFail"
	::={drdlPropertyFailLevelEntry 2}

drdlPropertyFailLevelMom OBJECT-TYPE
	SYNTAX	 CounterBasedGauge64
	MAX-ACCESS  read-only
	STATUS      current
	DESCRIPTION
	"Table entry attribute for drdlPropertyFail"
	::={drdlPropertyFailLevelEntry 3}

drdlPropertyFailLevelMax OBJECT-TYPE
	SYNTAX	 CounterBasedGauge64
	MAX-ACCESS  read-only
	STATUS      current
	DESCRIPTION
	"Table entry attribute for drdlPropertyFail"
	::={drdlPropertyFailLevelEntry 4}


drdlVsRangeTests	OBJECT IDENTIFIER ::={drdl 45}

drdlVsRangeTestsVal	OBJECT-TYPE
	SYNTAX	 Counter64
	MAX-ACCESS read-only
	STATUS current
	DESCRIPTION "Virtual services range tests"

	::={drdlVsRangeTests 1}

drdlVsRangeTestsMom	OBJECT-TYPE
	SYNTAX	 CounterBasedGauge64
	MAX-ACCESS read-only
	STATUS current
	DESCRIPTION "Virtual services range tests"

	::={drdlVsRangeTests 2}

drdlVsRangeTestsMax	OBJECT-TYPE
	SYNTAX	 CounterBasedGauge64
	MAX-ACCESS read-only
	STATUS current
	DESCRIPTION "Virtual services range tests"

	::={drdlVsRangeTests 3}

drdlVsRangeTestsLevelTable OBJECT-TYPE
	SYNTAX      SEQUENCE OF DrdlVsRangeTestsLevelEntry
	MAX-ACCESS  not-accessible
	STATUS      current
	DESCRIPTION
	"Table for drdlVsRangeTests"
	::={drdlVsRangeTests 4}

drdlVsRangeTestsLevelEntry OBJECT-TYPE
	SYNTAX      DrdlVsRangeTestsLevelEntry
	MAX-ACCESS  not-accessible
	STATUS      current
	DESCRIPTION
	"Table entry for drdlVsRangeTests"
	INDEX { drdlVsRangeTestsLevelName }
	::={drdlVsRangeTestsLevelTable 1}

DrdlVsRangeTestsLevelEntry ::=
	SEQUENCE {
		drdlVsRangeTestsLevelName	DisplayString,
		drdlVsRangeTestsLevelVal	Counter64,
		drdlVsRangeTestsLevelMom	CounterBasedGauge64,
		drdlVsRangeTestsLevelMax	CounterBasedGauge64
	}

drdlVsRangeTestsLevelName OBJECT-TYPE
	SYNTAX      DisplayString
	MAX-ACCESS  not-accessible
	STATUS      current
	DESCRIPTION
	"Table entry display string for drdlVsRangeTests"
	::={drdlVsRangeTestsLevelEntry 1}

drdlVsRangeTestsLevelVal OBJECT-TYPE
	SYNTAX	 Counter64
	MAX-ACCESS  read-only
	STATUS      current
	DESCRIPTION
	"Table entry attribute for drdlVsRangeTests"
	::={drdlVsRangeTestsLevelEntry 2}

drdlVsRangeTestsLevelMom OBJECT-TYPE
	SYNTAX	 CounterBasedGauge64
	MAX-ACCESS  read-only
	STATUS      current
	DESCRIPTION
	"Table entry attribute for drdlVsRangeTests"
	::={drdlVsRangeTestsLevelEntry 3}

drdlVsRangeTestsLevelMax OBJECT-TYPE
	SYNTAX	 CounterBasedGauge64
	MAX-ACCESS  read-only
	STATUS      current
	DESCRIPTION
	"Table entry attribute for drdlVsRangeTests"
	::={drdlVsRangeTestsLevelEntry 4}


drdlVsRangeSteps	OBJECT IDENTIFIER ::={drdl 46}

drdlVsRangeStepsVal	OBJECT-TYPE
	SYNTAX	 Counter64
	MAX-ACCESS read-only
	STATUS current
	DESCRIPTION "Virtual services range steps"

	::={drdlVsRangeSteps 1}

drdlVsRangeStepsMom	OBJECT-TYPE
	SYNTAX	 CounterBasedGauge64
	MAX-ACCESS read-only
	STATUS current
	DESCRIPTION "Virtual services range steps"

	::={drdlVsRangeSteps 2}

drdlVsRangeStepsMax	OBJECT-TYPE
	SYNTAX	 CounterBasedGauge64
	MAX-ACCESS read-only
	STATUS current
	DESCRIPTION "Virtual services range steps"

	::={drdlVsRangeSteps 3}

drdlVsRangeStepsLevelTable OBJECT-TYPE
	SYNTAX      SEQUENCE OF DrdlVsRangeStepsLevelEntry
	MAX-ACCESS  not-accessible
	STATUS      current
	DESCRIPTION
	"Table for drdlVsRangeSteps"
	::={drdlVsRangeSteps 4}

drdlVsRangeStepsLevelEntry OBJECT-TYPE
	SYNTAX      DrdlVsRangeStepsLevelEntry
	MAX-ACCESS  not-accessible
	STATUS      current
	DESCRIPTION
	"Table entry for drdlVsRangeSteps"
	INDEX { drdlVsRangeStepsLevelName }
	::={drdlVsRangeStepsLevelTable 1}

DrdlVsRangeStepsLevelEntry ::=
	SEQUENCE {
		drdlVsRangeStepsLevelName	DisplayString,
		drdlVsRangeStepsLevelVal	Counter64,
		drdlVsRangeStepsLevelMom	CounterBasedGauge64,
		drdlVsRangeStepsLevelMax	CounterBasedGauge64
	}

drdlVsRangeStepsLevelName OBJECT-TYPE
	SYNTAX      DisplayString
	MAX-ACCESS  not-accessible
	STATUS      current
	DESCRIPTION
	"Table entry display string for drdlVsRangeSteps"
	::={drdlVsRangeStepsLevelEntry 1}

drdlVsRangeStepsLevelVal OBJECT-TYPE
	SYNTAX	 Counter64
	MAX-ACCESS  read-only
	STATUS      current
	DESCRIPTION
	"Table entry attribute for drdlVsRangeSteps"
	::={drdlVsRangeStepsLevelEntry 2}

drdlVsRangeStepsLevelMom OBJECT-TYPE
	SYNTAX	 CounterBasedGauge64
	MAX-ACCESS  read-only
	STATUS      current
	DESCRIPTION
	"Table entry attribute for drdlVsRangeSteps"
	::={drdlVsRangeStepsLevelEntry 3}

drdlVsRangeStepsLevelMax OBJECT-TYPE
	SYNTAX	 CounterBasedGauge64
	MAX-ACCESS  read-only
	STATUS      current
	DESCRIPTION
	"Table entry attribute for drdlVsRangeSteps"
	::={drdlVsRangeStepsLevelEntry 4}


drdlVsRegexTests	OBJECT IDENTIFIER ::={drdl 47}

drdlVsRegexTestsVal	OBJECT-TYPE
	SYNTAX	 Counter64
	MAX-ACCESS read-only
	STATUS current
	DESCRIPTION "Virtual services regex tests"

	::={drdlVsRegexTests 1}

drdlVsRegexTestsMom	OBJECT-TYPE
	SYNTAX	 CounterBasedGauge64
	MAX-ACCESS read-only
	STATUS current
	DESCRIPTION "Virtual services regex tests"

	::={drdlVsRegexTests 2}

drdlVsRegexTestsMax	OBJECT-TYPE
	SYNTAX	 CounterBasedGauge64
	MAX-ACCESS read-only
	STATUS current
	DESCRIPTION "Virtual services regex tests"

	::={drdlVsRegexTests 3}

drdlVsRegexTestsLevelTable OBJECT-TYPE
	SYNTAX      SEQUENCE OF DrdlVsRegexTestsLevelEntry
	MAX-ACCESS  not-accessible
	STATUS      current
	DESCRIPTION
	"Table for drdlVsRegexTests"
	::={drdlVsRegexTests 4}

drdlVsRegexTestsLevelEntry OBJECT-TYPE
	SYNTAX      DrdlVsRegexTestsLevelEntry
	MAX-ACCESS  not-accessible
	STATUS      current
	DESCRIPTION
	"Table entry for drdlVsRegexTests"
	INDEX { drdlVsRegexTestsLevelName }
	::={drdlVsRegexTestsLevelTable 1}

DrdlVsRegexTestsLevelEntry ::=
	SEQUENCE {
		drdlVsRegexTestsLevelName	DisplayString,
		drdlVsRegexTestsLevelVal	Counter64,
		drdlVsRegexTestsLevelMom	CounterBasedGauge64,
		drdlVsRegexTestsLevelMax	CounterBasedGauge64
	}

drdlVsRegexTestsLevelName OBJECT-TYPE
	SYNTAX      DisplayString
	MAX-ACCESS  not-accessible
	STATUS      current
	DESCRIPTION
	"Table entry display string for drdlVsRegexTests"
	::={drdlVsRegexTestsLevelEntry 1}

drdlVsRegexTestsLevelVal OBJECT-TYPE
	SYNTAX	 Counter64
	MAX-ACCESS  read-only
	STATUS      current
	DESCRIPTION
	"Table entry attribute for drdlVsRegexTests"
	::={drdlVsRegexTestsLevelEntry 2}

drdlVsRegexTestsLevelMom OBJECT-TYPE
	SYNTAX	 CounterBasedGauge64
	MAX-ACCESS  read-only
	STATUS      current
	DESCRIPTION
	"Table entry attribute for drdlVsRegexTests"
	::={drdlVsRegexTestsLevelEntry 3}

drdlVsRegexTestsLevelMax OBJECT-TYPE
	SYNTAX	 CounterBasedGauge64
	MAX-ACCESS  read-only
	STATUS      current
	DESCRIPTION
	"Table entry attribute for drdlVsRegexTests"
	::={drdlVsRegexTestsLevelEntry 4}


drdlVsRegexSteps	OBJECT IDENTIFIER ::={drdl 48}

drdlVsRegexStepsVal	OBJECT-TYPE
	SYNTAX	 Counter64
	MAX-ACCESS read-only
	STATUS current
	DESCRIPTION "Virtual services regex steps"

	::={drdlVsRegexSteps 1}

drdlVsRegexStepsMom	OBJECT-TYPE
	SYNTAX	 CounterBasedGauge64
	MAX-ACCESS read-only
	STATUS current
	DESCRIPTION "Virtual services regex steps"

	::={drdlVsRegexSteps 2}

drdlVsRegexStepsMax	OBJECT-TYPE
	SYNTAX	 CounterBasedGauge64
	MAX-ACCESS read-only
	STATUS current
	DESCRIPTION "Virtual services regex steps"

	::={drdlVsRegexSteps 3}

drdlVsRegexStepsLevelTable OBJECT-TYPE
	SYNTAX      SEQUENCE OF DrdlVsRegexStepsLevelEntry
	MAX-ACCESS  not-accessible
	STATUS      current
	DESCRIPTION
	"Table for drdlVsRegexSteps"
	::={drdlVsRegexSteps 4}

drdlVsRegexStepsLevelEntry OBJECT-TYPE
	SYNTAX      DrdlVsRegexStepsLevelEntry
	MAX-ACCESS  not-accessible
	STATUS      current
	DESCRIPTION
	"Table entry for drdlVsRegexSteps"
	INDEX { drdlVsRegexStepsLevelName }
	::={drdlVsRegexStepsLevelTable 1}

DrdlVsRegexStepsLevelEntry ::=
	SEQUENCE {
		drdlVsRegexStepsLevelName	DisplayString,
		drdlVsRegexStepsLevelVal	Counter64,
		drdlVsRegexStepsLevelMom	CounterBasedGauge64,
		drdlVsRegexStepsLevelMax	CounterBasedGauge64
	}

drdlVsRegexStepsLevelName OBJECT-TYPE
	SYNTAX      DisplayString
	MAX-ACCESS  not-accessible
	STATUS      current
	DESCRIPTION
	"Table entry display string for drdlVsRegexSteps"
	::={drdlVsRegexStepsLevelEntry 1}

drdlVsRegexStepsLevelVal OBJECT-TYPE
	SYNTAX	 Counter64
	MAX-ACCESS  read-only
	STATUS      current
	DESCRIPTION
	"Table entry attribute for drdlVsRegexSteps"
	::={drdlVsRegexStepsLevelEntry 2}

drdlVsRegexStepsLevelMom OBJECT-TYPE
	SYNTAX	 CounterBasedGauge64
	MAX-ACCESS  read-only
	STATUS      current
	DESCRIPTION
	"Table entry attribute for drdlVsRegexSteps"
	::={drdlVsRegexStepsLevelEntry 3}

drdlVsRegexStepsLevelMax OBJECT-TYPE
	SYNTAX	 CounterBasedGauge64
	MAX-ACCESS  read-only
	STATUS      current
	DESCRIPTION
	"Table entry attribute for drdlVsRegexSteps"
	::={drdlVsRegexStepsLevelEntry 4}


drdlTaintFill	OBJECT IDENTIFIER ::={drdl 49}

drdlTaintFillVal	OBJECT-TYPE
	SYNTAX	 CounterBasedGauge64
	MAX-ACCESS read-only
	STATUS current
	DESCRIPTION "Buckets used in taint store"

	::={drdlTaintFill 1}

drdlTaintFillMax	OBJECT-TYPE
	SYNTAX	 CounterBasedGauge64
	MAX-ACCESS read-only
	STATUS current
	DESCRIPTION "Buckets used in taint store"

	::={drdlTaintFill 3}

drdlTaintFillLevelTable OBJECT-TYPE
	SYNTAX      SEQUENCE OF DrdlTaintFillLevelEntry
	MAX-ACCESS  not-accessible
	STATUS      current
	DESCRIPTION
	"Table for drdlTaintFill"
	::={drdlTaintFill 4}

drdlTaintFillLevelEntry OBJECT-TYPE
	SYNTAX      DrdlTaintFillLevelEntry
	MAX-ACCESS  not-accessible
	STATUS      current
	DESCRIPTION
	"Table entry for drdlTaintFill"
	INDEX { drdlTaintFillLevelName }
	::={drdlTaintFillLevelTable 1}

DrdlTaintFillLevelEntry ::=
	SEQUENCE {
		drdlTaintFillLevelName	DisplayString,
		drdlTaintFillLevelVal	CounterBasedGauge64,
		drdlTaintFillLevelMax	CounterBasedGauge64
	}

drdlTaintFillLevelName OBJECT-TYPE
	SYNTAX      DisplayString
	MAX-ACCESS  not-accessible
	STATUS      current
	DESCRIPTION
	"Table entry display string for drdlTaintFill"
	::={drdlTaintFillLevelEntry 1}

drdlTaintFillLevelVal OBJECT-TYPE
	SYNTAX	 CounterBasedGauge64
	MAX-ACCESS  read-only
	STATUS      current
	DESCRIPTION
	"Table entry attribute for drdlTaintFill"
	::={drdlTaintFillLevelEntry 2}

drdlTaintFillLevelMax OBJECT-TYPE
	SYNTAX	 CounterBasedGauge64
	MAX-ACCESS  read-only
	STATUS      current
	DESCRIPTION
	"Table entry attribute for drdlTaintFill"
	::={drdlTaintFillLevelEntry 4}


drdlChildIterateMax	OBJECT IDENTIFIER ::={drdl 33}

drdlChildIterateMaxVal	OBJECT-TYPE
	SYNTAX	 CounterBasedGauge64
	MAX-ACCESS read-only
	STATUS obsolete
	DESCRIPTION "Childconnection iterations during search (max)"

	::={drdlChildIterateMax 1}

drdlChildIterateMaxMax	OBJECT-TYPE
	SYNTAX	 CounterBasedGauge64
	MAX-ACCESS read-only
	STATUS obsolete
	DESCRIPTION "Childconnection iterations during search (max)"

	::={drdlChildIterateMax 3}

drdlChildIterateMaxLevelTable OBJECT-TYPE
	SYNTAX      SEQUENCE OF DrdlChildIterateMaxLevelEntry
	MAX-ACCESS  not-accessible
	STATUS      current
	DESCRIPTION
	"Table for drdlChildIterateMax"
	::={drdlChildIterateMax 4}

drdlChildIterateMaxLevelEntry OBJECT-TYPE
	SYNTAX      DrdlChildIterateMaxLevelEntry
	MAX-ACCESS  not-accessible
	STATUS      current
	DESCRIPTION
	"Table entry for drdlChildIterateMax"
	INDEX { drdlChildIterateMaxLevelName }
	::={drdlChildIterateMaxLevelTable 1}

DrdlChildIterateMaxLevelEntry ::=
	SEQUENCE {
		drdlChildIterateMaxLevelName	DisplayString,
		drdlChildIterateMaxLevelVal	CounterBasedGauge64,
		drdlChildIterateMaxLevelMax	CounterBasedGauge64
	}

drdlChildIterateMaxLevelName OBJECT-TYPE
	SYNTAX      DisplayString
	MAX-ACCESS  not-accessible
	STATUS      current
	DESCRIPTION
	"Table entry display string for drdlChildIterateMax"
	::={drdlChildIterateMaxLevelEntry 1}

drdlChildIterateMaxLevelVal OBJECT-TYPE
	SYNTAX	 CounterBasedGauge64
	MAX-ACCESS  read-only
	STATUS      current
	DESCRIPTION
	"Table entry attribute for drdlChildIterateMax"
	::={drdlChildIterateMaxLevelEntry 2}

drdlChildIterateMaxLevelMax OBJECT-TYPE
	SYNTAX	 CounterBasedGauge64
	MAX-ACCESS  read-only
	STATUS      current
	DESCRIPTION
	"Table entry attribute for drdlChildIterateMax"
	::={drdlChildIterateMaxLevelEntry 4}


drdlUCapPktQueues	OBJECT IDENTIFIER ::={drdl 50}

drdlUCapPktQueuesVal	OBJECT-TYPE
	SYNTAX	 Counter64
	MAX-ACCESS read-only
	STATUS current
	DESCRIPTION "UCAP: Allocated packet queues"

	::={drdlUCapPktQueues 1}

drdlUCapPktQueuesMom	OBJECT-TYPE
	SYNTAX	 CounterBasedGauge64
	MAX-ACCESS read-only
	STATUS current
	DESCRIPTION "UCAP: Allocated packet queues"

	::={drdlUCapPktQueues 2}

drdlUCapPktQueuesMax	OBJECT-TYPE
	SYNTAX	 CounterBasedGauge64
	MAX-ACCESS read-only
	STATUS current
	DESCRIPTION "UCAP: Allocated packet queues"

	::={drdlUCapPktQueues 3}

drdlUCapPktQueuesLevelTable OBJECT-TYPE
	SYNTAX      SEQUENCE OF DrdlUCapPktQueuesLevelEntry
	MAX-ACCESS  not-accessible
	STATUS      current
	DESCRIPTION
	"Table for drdlUCapPktQueues"
	::={drdlUCapPktQueues 4}

drdlUCapPktQueuesLevelEntry OBJECT-TYPE
	SYNTAX      DrdlUCapPktQueuesLevelEntry
	MAX-ACCESS  not-accessible
	STATUS      current
	DESCRIPTION
	"Table entry for drdlUCapPktQueues"
	INDEX { drdlUCapPktQueuesLevelName }
	::={drdlUCapPktQueuesLevelTable 1}

DrdlUCapPktQueuesLevelEntry ::=
	SEQUENCE {
		drdlUCapPktQueuesLevelName	DisplayString,
		drdlUCapPktQueuesLevelVal	Counter64,
		drdlUCapPktQueuesLevelMom	CounterBasedGauge64,
		drdlUCapPktQueuesLevelMax	CounterBasedGauge64
	}

drdlUCapPktQueuesLevelName OBJECT-TYPE
	SYNTAX      DisplayString
	MAX-ACCESS  not-accessible
	STATUS      current
	DESCRIPTION
	"Table entry display string for drdlUCapPktQueues"
	::={drdlUCapPktQueuesLevelEntry 1}

drdlUCapPktQueuesLevelVal OBJECT-TYPE
	SYNTAX	 Counter64
	MAX-ACCESS  read-only
	STATUS      current
	DESCRIPTION
	"Table entry attribute for drdlUCapPktQueues"
	::={drdlUCapPktQueuesLevelEntry 2}

drdlUCapPktQueuesLevelMom OBJECT-TYPE
	SYNTAX	 CounterBasedGauge64
	MAX-ACCESS  read-only
	STATUS      current
	DESCRIPTION
	"Table entry attribute for drdlUCapPktQueues"
	::={drdlUCapPktQueuesLevelEntry 3}

drdlUCapPktQueuesLevelMax OBJECT-TYPE
	SYNTAX	 CounterBasedGauge64
	MAX-ACCESS  read-only
	STATUS      current
	DESCRIPTION
	"Table entry attribute for drdlUCapPktQueues"
	::={drdlUCapPktQueuesLevelEntry 4}


drdlUCapPktAdded	OBJECT IDENTIFIER ::={drdl 51}

drdlUCapPktAddedVal	OBJECT-TYPE
	SYNTAX	 Counter64
	MAX-ACCESS read-only
	STATUS current
	DESCRIPTION "UCAP: Packets held in packet queues"

	::={drdlUCapPktAdded 1}

drdlUCapPktAddedMom	OBJECT-TYPE
	SYNTAX	 CounterBasedGauge64
	MAX-ACCESS read-only
	STATUS current
	DESCRIPTION "UCAP: Packets held in packet queues"

	::={drdlUCapPktAdded 2}

drdlUCapPktAddedMax	OBJECT-TYPE
	SYNTAX	 CounterBasedGauge64
	MAX-ACCESS read-only
	STATUS current
	DESCRIPTION "UCAP: Packets held in packet queues"

	::={drdlUCapPktAdded 3}

drdlUCapPktAddedLevelTable OBJECT-TYPE
	SYNTAX      SEQUENCE OF DrdlUCapPktAddedLevelEntry
	MAX-ACCESS  not-accessible
	STATUS      current
	DESCRIPTION
	"Table for drdlUCapPktAdded"
	::={drdlUCapPktAdded 4}

drdlUCapPktAddedLevelEntry OBJECT-TYPE
	SYNTAX      DrdlUCapPktAddedLevelEntry
	MAX-ACCESS  not-accessible
	STATUS      current
	DESCRIPTION
	"Table entry for drdlUCapPktAdded"
	INDEX { drdlUCapPktAddedLevelName }
	::={drdlUCapPktAddedLevelTable 1}

DrdlUCapPktAddedLevelEntry ::=
	SEQUENCE {
		drdlUCapPktAddedLevelName	DisplayString,
		drdlUCapPktAddedLevelVal	Counter64,
		drdlUCapPktAddedLevelMom	CounterBasedGauge64,
		drdlUCapPktAddedLevelMax	CounterBasedGauge64
	}

drdlUCapPktAddedLevelName OBJECT-TYPE
	SYNTAX      DisplayString
	MAX-ACCESS  not-accessible
	STATUS      current
	DESCRIPTION
	"Table entry display string for drdlUCapPktAdded"
	::={drdlUCapPktAddedLevelEntry 1}

drdlUCapPktAddedLevelVal OBJECT-TYPE
	SYNTAX	 Counter64
	MAX-ACCESS  read-only
	STATUS      current
	DESCRIPTION
	"Table entry attribute for drdlUCapPktAdded"
	::={drdlUCapPktAddedLevelEntry 2}

drdlUCapPktAddedLevelMom OBJECT-TYPE
	SYNTAX	 CounterBasedGauge64
	MAX-ACCESS  read-only
	STATUS      current
	DESCRIPTION
	"Table entry attribute for drdlUCapPktAdded"
	::={drdlUCapPktAddedLevelEntry 3}

drdlUCapPktAddedLevelMax OBJECT-TYPE
	SYNTAX	 CounterBasedGauge64
	MAX-ACCESS  read-only
	STATUS      current
	DESCRIPTION
	"Table entry attribute for drdlUCapPktAdded"
	::={drdlUCapPktAddedLevelEntry 4}


drdlUCapConnsSent	OBJECT IDENTIFIER ::={drdl 52}

drdlUCapConnsSentVal	OBJECT-TYPE
	SYNTAX	 Counter64
	MAX-ACCESS read-only
	STATUS current
	DESCRIPTION "UCAP: Connections sent to userspace"

	::={drdlUCapConnsSent 1}

drdlUCapConnsSentMom	OBJECT-TYPE
	SYNTAX	 CounterBasedGauge64
	MAX-ACCESS read-only
	STATUS current
	DESCRIPTION "UCAP: Connections sent to userspace"

	::={drdlUCapConnsSent 2}

drdlUCapConnsSentMax	OBJECT-TYPE
	SYNTAX	 CounterBasedGauge64
	MAX-ACCESS read-only
	STATUS current
	DESCRIPTION "UCAP: Connections sent to userspace"

	::={drdlUCapConnsSent 3}

drdlUCapConnsSentLevelTable OBJECT-TYPE
	SYNTAX      SEQUENCE OF DrdlUCapConnsSentLevelEntry
	MAX-ACCESS  not-accessible
	STATUS      current
	DESCRIPTION
	"Table for drdlUCapConnsSent"
	::={drdlUCapConnsSent 4}

drdlUCapConnsSentLevelEntry OBJECT-TYPE
	SYNTAX      DrdlUCapConnsSentLevelEntry
	MAX-ACCESS  not-accessible
	STATUS      current
	DESCRIPTION
	"Table entry for drdlUCapConnsSent"
	INDEX { drdlUCapConnsSentLevelName }
	::={drdlUCapConnsSentLevelTable 1}

DrdlUCapConnsSentLevelEntry ::=
	SEQUENCE {
		drdlUCapConnsSentLevelName	DisplayString,
		drdlUCapConnsSentLevelVal	Counter64,
		drdlUCapConnsSentLevelMom	CounterBasedGauge64,
		drdlUCapConnsSentLevelMax	CounterBasedGauge64
	}

drdlUCapConnsSentLevelName OBJECT-TYPE
	SYNTAX      DisplayString
	MAX-ACCESS  not-accessible
	STATUS      current
	DESCRIPTION
	"Table entry display string for drdlUCapConnsSent"
	::={drdlUCapConnsSentLevelEntry 1}

drdlUCapConnsSentLevelVal OBJECT-TYPE
	SYNTAX	 Counter64
	MAX-ACCESS  read-only
	STATUS      current
	DESCRIPTION
	"Table entry attribute for drdlUCapConnsSent"
	::={drdlUCapConnsSentLevelEntry 2}

drdlUCapConnsSentLevelMom OBJECT-TYPE
	SYNTAX	 CounterBasedGauge64
	MAX-ACCESS  read-only
	STATUS      current
	DESCRIPTION
	"Table entry attribute for drdlUCapConnsSent"
	::={drdlUCapConnsSentLevelEntry 3}

drdlUCapConnsSentLevelMax OBJECT-TYPE
	SYNTAX	 CounterBasedGauge64
	MAX-ACCESS  read-only
	STATUS      current
	DESCRIPTION
	"Table entry attribute for drdlUCapConnsSent"
	::={drdlUCapConnsSentLevelEntry 4}


drdlUCapQueueOverflow	OBJECT IDENTIFIER ::={drdl 53}

drdlUCapQueueOverflowVal	OBJECT-TYPE
	SYNTAX	 Counter64
	MAX-ACCESS read-only
	STATUS current
	DESCRIPTION "UCAP: Overflows in packet queues"

	::={drdlUCapQueueOverflow 1}

drdlUCapQueueOverflowMom	OBJECT-TYPE
	SYNTAX	 CounterBasedGauge64
	MAX-ACCESS read-only
	STATUS current
	DESCRIPTION "UCAP: Overflows in packet queues"

	::={drdlUCapQueueOverflow 2}

drdlUCapQueueOverflowMax	OBJECT-TYPE
	SYNTAX	 CounterBasedGauge64
	MAX-ACCESS read-only
	STATUS current
	DESCRIPTION "UCAP: Overflows in packet queues"

	::={drdlUCapQueueOverflow 3}

drdlUCapQueueOverflowLevelTable OBJECT-TYPE
	SYNTAX      SEQUENCE OF DrdlUCapQueueOverflowLevelEntry
	MAX-ACCESS  not-accessible
	STATUS      current
	DESCRIPTION
	"Table for drdlUCapQueueOverflow"
	::={drdlUCapQueueOverflow 4}

drdlUCapQueueOverflowLevelEntry OBJECT-TYPE
	SYNTAX      DrdlUCapQueueOverflowLevelEntry
	MAX-ACCESS  not-accessible
	STATUS      current
	DESCRIPTION
	"Table entry for drdlUCapQueueOverflow"
	INDEX { drdlUCapQueueOverflowLevelName }
	::={drdlUCapQueueOverflowLevelTable 1}

DrdlUCapQueueOverflowLevelEntry ::=
	SEQUENCE {
		drdlUCapQueueOverflowLevelName	DisplayString,
		drdlUCapQueueOverflowLevelVal	Counter64,
		drdlUCapQueueOverflowLevelMom	CounterBasedGauge64,
		drdlUCapQueueOverflowLevelMax	CounterBasedGauge64
	}

drdlUCapQueueOverflowLevelName OBJECT-TYPE
	SYNTAX      DisplayString
	MAX-ACCESS  not-accessible
	STATUS      current
	DESCRIPTION
	"Table entry display string for drdlUCapQueueOverflow"
	::={drdlUCapQueueOverflowLevelEntry 1}

drdlUCapQueueOverflowLevelVal OBJECT-TYPE
	SYNTAX	 Counter64
	MAX-ACCESS  read-only
	STATUS      current
	DESCRIPTION
	"Table entry attribute for drdlUCapQueueOverflow"
	::={drdlUCapQueueOverflowLevelEntry 2}

drdlUCapQueueOverflowLevelMom OBJECT-TYPE
	SYNTAX	 CounterBasedGauge64
	MAX-ACCESS  read-only
	STATUS      current
	DESCRIPTION
	"Table entry attribute for drdlUCapQueueOverflow"
	::={drdlUCapQueueOverflowLevelEntry 3}

drdlUCapQueueOverflowLevelMax OBJECT-TYPE
	SYNTAX	 CounterBasedGauge64
	MAX-ACCESS  read-only
	STATUS      current
	DESCRIPTION
	"Table entry attribute for drdlUCapQueueOverflow"
	::={drdlUCapQueueOverflowLevelEntry 4}


drdlTaintFillPercent	OBJECT IDENTIFIER ::={drdl 54}

drdlTaintFillPercentVal	OBJECT-TYPE
	SYNTAX	 Unsigned32
	MAX-ACCESS read-only
	STATUS current
	DESCRIPTION "Connection tainting data structure usage"

	::={drdlTaintFillPercent 1}

drdlTaintFillPercentMax	OBJECT-TYPE
	SYNTAX	 Unsigned32
	MAX-ACCESS read-only
	STATUS current
	DESCRIPTION "Connection tainting data structure usage"

	::={drdlTaintFillPercent 3}

drdlTaintFillPercentLevelTable OBJECT-TYPE
	SYNTAX      SEQUENCE OF DrdlTaintFillPercentLevelEntry
	MAX-ACCESS  not-accessible
	STATUS      current
	DESCRIPTION
	"Table for drdlTaintFillPercent"
	::={drdlTaintFillPercent 4}

drdlTaintFillPercentLevelEntry OBJECT-TYPE
	SYNTAX      DrdlTaintFillPercentLevelEntry
	MAX-ACCESS  not-accessible
	STATUS      current
	DESCRIPTION
	"Table entry for drdlTaintFillPercent"
	INDEX { drdlTaintFillPercentLevelName }
	::={drdlTaintFillPercentLevelTable 1}

DrdlTaintFillPercentLevelEntry ::=
	SEQUENCE {
		drdlTaintFillPercentLevelName	DisplayString,
		drdlTaintFillPercentLevelVal	Unsigned32,
		drdlTaintFillPercentLevelMax	Unsigned32
	}

drdlTaintFillPercentLevelName OBJECT-TYPE
	SYNTAX      DisplayString
	MAX-ACCESS  not-accessible
	STATUS      current
	DESCRIPTION
	"Table entry display string for drdlTaintFillPercent"
	::={drdlTaintFillPercentLevelEntry 1}

drdlTaintFillPercentLevelVal OBJECT-TYPE
	SYNTAX	 Unsigned32
	MAX-ACCESS  read-only
	STATUS      current
	DESCRIPTION
	"Table entry attribute for drdlTaintFillPercent"
	::={drdlTaintFillPercentLevelEntry 2}

drdlTaintFillPercentLevelMax OBJECT-TYPE
	SYNTAX	 Unsigned32
	MAX-ACCESS  read-only
	STATUS      current
	DESCRIPTION
	"Table entry attribute for drdlTaintFillPercent"
	::={drdlTaintFillPercentLevelEntry 4}


drdlProp2048Fail	OBJECT IDENTIFIER ::={drdl 55}

drdlProp2048FailVal	OBJECT-TYPE
	SYNTAX	 Counter64
	MAX-ACCESS read-only
	STATUS current
	DESCRIPTION "Property allocation failures (2048)"

	::={drdlProp2048Fail 1}

drdlProp2048FailMom	OBJECT-TYPE
	SYNTAX	 CounterBasedGauge64
	MAX-ACCESS read-only
	STATUS current
	DESCRIPTION "Property allocation failures (2048)"

	::={drdlProp2048Fail 2}

drdlProp2048FailMax	OBJECT-TYPE
	SYNTAX	 CounterBasedGauge64
	MAX-ACCESS read-only
	STATUS current
	DESCRIPTION "Property allocation failures (2048)"

	::={drdlProp2048Fail 3}

drdlProp2048FailLevelTable OBJECT-TYPE
	SYNTAX      SEQUENCE OF DrdlProp2048FailLevelEntry
	MAX-ACCESS  not-accessible
	STATUS      current
	DESCRIPTION
	"Table for drdlProp2048Fail"
	::={drdlProp2048Fail 4}

drdlProp2048FailLevelEntry OBJECT-TYPE
	SYNTAX      DrdlProp2048FailLevelEntry
	MAX-ACCESS  not-accessible
	STATUS      current
	DESCRIPTION
	"Table entry for drdlProp2048Fail"
	INDEX { drdlProp2048FailLevelName }
	::={drdlProp2048FailLevelTable 1}

DrdlProp2048FailLevelEntry ::=
	SEQUENCE {
		drdlProp2048FailLevelName	DisplayString,
		drdlProp2048FailLevelVal	Counter64,
		drdlProp2048FailLevelMom	CounterBasedGauge64,
		drdlProp2048FailLevelMax	CounterBasedGauge64
	}

drdlProp2048FailLevelName OBJECT-TYPE
	SYNTAX      DisplayString
	MAX-ACCESS  not-accessible
	STATUS      current
	DESCRIPTION
	"Table entry display string for drdlProp2048Fail"
	::={drdlProp2048FailLevelEntry 1}

drdlProp2048FailLevelVal OBJECT-TYPE
	SYNTAX	 Counter64
	MAX-ACCESS  read-only
	STATUS      current
	DESCRIPTION
	"Table entry attribute for drdlProp2048Fail"
	::={drdlProp2048FailLevelEntry 2}

drdlProp2048FailLevelMom OBJECT-TYPE
	SYNTAX	 CounterBasedGauge64
	MAX-ACCESS  read-only
	STATUS      current
	DESCRIPTION
	"Table entry attribute for drdlProp2048Fail"
	::={drdlProp2048FailLevelEntry 3}

drdlProp2048FailLevelMax OBJECT-TYPE
	SYNTAX	 CounterBasedGauge64
	MAX-ACCESS  read-only
	STATUS      current
	DESCRIPTION
	"Table entry attribute for drdlProp2048Fail"
	::={drdlProp2048FailLevelEntry 4}


drdlProp2048Used	OBJECT IDENTIFIER ::={drdl 56}

drdlProp2048UsedVal	OBJECT-TYPE
	SYNTAX	 CounterBasedGauge64
	MAX-ACCESS read-only
	STATUS current
	DESCRIPTION "Properties used (2048)"

	::={drdlProp2048Used 1}

drdlProp2048UsedMax	OBJECT-TYPE
	SYNTAX	 CounterBasedGauge64
	MAX-ACCESS read-only
	STATUS current
	DESCRIPTION "Properties used (2048)"

	::={drdlProp2048Used 3}

drdlProp2048UsedLevelTable OBJECT-TYPE
	SYNTAX      SEQUENCE OF DrdlProp2048UsedLevelEntry
	MAX-ACCESS  not-accessible
	STATUS      current
	DESCRIPTION
	"Table for drdlProp2048Used"
	::={drdlProp2048Used 4}

drdlProp2048UsedLevelEntry OBJECT-TYPE
	SYNTAX      DrdlProp2048UsedLevelEntry
	MAX-ACCESS  not-accessible
	STATUS      current
	DESCRIPTION
	"Table entry for drdlProp2048Used"
	INDEX { drdlProp2048UsedLevelName }
	::={drdlProp2048UsedLevelTable 1}

DrdlProp2048UsedLevelEntry ::=
	SEQUENCE {
		drdlProp2048UsedLevelName	DisplayString,
		drdlProp2048UsedLevelVal	CounterBasedGauge64,
		drdlProp2048UsedLevelMax	CounterBasedGauge64
	}

drdlProp2048UsedLevelName OBJECT-TYPE
	SYNTAX      DisplayString
	MAX-ACCESS  not-accessible
	STATUS      current
	DESCRIPTION
	"Table entry display string for drdlProp2048Used"
	::={drdlProp2048UsedLevelEntry 1}

drdlProp2048UsedLevelVal OBJECT-TYPE
	SYNTAX	 CounterBasedGauge64
	MAX-ACCESS  read-only
	STATUS      current
	DESCRIPTION
	"Table entry attribute for drdlProp2048Used"
	::={drdlProp2048UsedLevelEntry 2}

drdlProp2048UsedLevelMax OBJECT-TYPE
	SYNTAX	 CounterBasedGauge64
	MAX-ACCESS  read-only
	STATUS      current
	DESCRIPTION
	"Table entry attribute for drdlProp2048Used"
	::={drdlProp2048UsedLevelEntry 4}


drdlKvstoreEntries	OBJECT IDENTIFIER ::={drdl 57}

drdlKvstoreEntriesVal	OBJECT-TYPE
	SYNTAX	 Counter64
	MAX-ACCESS read-only
	STATUS current
	DESCRIPTION "Key-Value store entries added."

	::={drdlKvstoreEntries 1}

drdlKvstoreEntriesMom	OBJECT-TYPE
	SYNTAX	 CounterBasedGauge64
	MAX-ACCESS read-only
	STATUS current
	DESCRIPTION "Key-Value store entries added."

	::={drdlKvstoreEntries 2}

drdlKvstoreEntriesMax	OBJECT-TYPE
	SYNTAX	 CounterBasedGauge64
	MAX-ACCESS read-only
	STATUS current
	DESCRIPTION "Key-Value store entries added."

	::={drdlKvstoreEntries 3}

drdlKvstoreEntriesLevelTable OBJECT-TYPE
	SYNTAX      SEQUENCE OF DrdlKvstoreEntriesLevelEntry
	MAX-ACCESS  not-accessible
	STATUS      current
	DESCRIPTION
	"Table for drdlKvstoreEntries"
	::={drdlKvstoreEntries 4}

drdlKvstoreEntriesLevelEntry OBJECT-TYPE
	SYNTAX      DrdlKvstoreEntriesLevelEntry
	MAX-ACCESS  not-accessible
	STATUS      current
	DESCRIPTION
	"Table entry for drdlKvstoreEntries"
	INDEX { drdlKvstoreEntriesLevelName }
	::={drdlKvstoreEntriesLevelTable 1}

DrdlKvstoreEntriesLevelEntry ::=
	SEQUENCE {
		drdlKvstoreEntriesLevelName	DisplayString,
		drdlKvstoreEntriesLevelVal	Counter64,
		drdlKvstoreEntriesLevelMom	CounterBasedGauge64,
		drdlKvstoreEntriesLevelMax	CounterBasedGauge64
	}

drdlKvstoreEntriesLevelName OBJECT-TYPE
	SYNTAX      DisplayString
	MAX-ACCESS  not-accessible
	STATUS      current
	DESCRIPTION
	"Table entry display string for drdlKvstoreEntries"
	::={drdlKvstoreEntriesLevelEntry 1}

drdlKvstoreEntriesLevelVal OBJECT-TYPE
	SYNTAX	 Counter64
	MAX-ACCESS  read-only
	STATUS      current
	DESCRIPTION
	"Table entry attribute for drdlKvstoreEntries"
	::={drdlKvstoreEntriesLevelEntry 2}

drdlKvstoreEntriesLevelMom OBJECT-TYPE
	SYNTAX	 CounterBasedGauge64
	MAX-ACCESS  read-only
	STATUS      current
	DESCRIPTION
	"Table entry attribute for drdlKvstoreEntries"
	::={drdlKvstoreEntriesLevelEntry 3}

drdlKvstoreEntriesLevelMax OBJECT-TYPE
	SYNTAX	 CounterBasedGauge64
	MAX-ACCESS  read-only
	STATUS      current
	DESCRIPTION
	"Table entry attribute for drdlKvstoreEntries"
	::={drdlKvstoreEntriesLevelEntry 4}


drdlKvstoreHits	OBJECT IDENTIFIER ::={drdl 58}

drdlKvstoreHitsVal	OBJECT-TYPE
	SYNTAX	 Counter64
	MAX-ACCESS read-only
	STATUS current
	DESCRIPTION "Key-Value store lookup hits."

	::={drdlKvstoreHits 1}

drdlKvstoreHitsMom	OBJECT-TYPE
	SYNTAX	 CounterBasedGauge64
	MAX-ACCESS read-only
	STATUS current
	DESCRIPTION "Key-Value store lookup hits."

	::={drdlKvstoreHits 2}

drdlKvstoreHitsMax	OBJECT-TYPE
	SYNTAX	 CounterBasedGauge64
	MAX-ACCESS read-only
	STATUS current
	DESCRIPTION "Key-Value store lookup hits."

	::={drdlKvstoreHits 3}

drdlKvstoreHitsLevelTable OBJECT-TYPE
	SYNTAX      SEQUENCE OF DrdlKvstoreHitsLevelEntry
	MAX-ACCESS  not-accessible
	STATUS      current
	DESCRIPTION
	"Table for drdlKvstoreHits"
	::={drdlKvstoreHits 4}

drdlKvstoreHitsLevelEntry OBJECT-TYPE
	SYNTAX      DrdlKvstoreHitsLevelEntry
	MAX-ACCESS  not-accessible
	STATUS      current
	DESCRIPTION
	"Table entry for drdlKvstoreHits"
	INDEX { drdlKvstoreHitsLevelName }
	::={drdlKvstoreHitsLevelTable 1}

DrdlKvstoreHitsLevelEntry ::=
	SEQUENCE {
		drdlKvstoreHitsLevelName	DisplayString,
		drdlKvstoreHitsLevelVal	Counter64,
		drdlKvstoreHitsLevelMom	CounterBasedGauge64,
		drdlKvstoreHitsLevelMax	CounterBasedGauge64
	}

drdlKvstoreHitsLevelName OBJECT-TYPE
	SYNTAX      DisplayString
	MAX-ACCESS  not-accessible
	STATUS      current
	DESCRIPTION
	"Table entry display string for drdlKvstoreHits"
	::={drdlKvstoreHitsLevelEntry 1}

drdlKvstoreHitsLevelVal OBJECT-TYPE
	SYNTAX	 Counter64
	MAX-ACCESS  read-only
	STATUS      current
	DESCRIPTION
	"Table entry attribute for drdlKvstoreHits"
	::={drdlKvstoreHitsLevelEntry 2}

drdlKvstoreHitsLevelMom OBJECT-TYPE
	SYNTAX	 CounterBasedGauge64
	MAX-ACCESS  read-only
	STATUS      current
	DESCRIPTION
	"Table entry attribute for drdlKvstoreHits"
	::={drdlKvstoreHitsLevelEntry 3}

drdlKvstoreHitsLevelMax OBJECT-TYPE
	SYNTAX	 CounterBasedGauge64
	MAX-ACCESS  read-only
	STATUS      current
	DESCRIPTION
	"Table entry attribute for drdlKvstoreHits"
	::={drdlKvstoreHitsLevelEntry 4}


drdlKvstoreMisses	OBJECT IDENTIFIER ::={drdl 59}

drdlKvstoreMissesVal	OBJECT-TYPE
	SYNTAX	 Counter64
	MAX-ACCESS read-only
	STATUS current
	DESCRIPTION "Key-Value store lookup misses."

	::={drdlKvstoreMisses 1}

drdlKvstoreMissesMom	OBJECT-TYPE
	SYNTAX	 CounterBasedGauge64
	MAX-ACCESS read-only
	STATUS current
	DESCRIPTION "Key-Value store lookup misses."

	::={drdlKvstoreMisses 2}

drdlKvstoreMissesMax	OBJECT-TYPE
	SYNTAX	 CounterBasedGauge64
	MAX-ACCESS read-only
	STATUS current
	DESCRIPTION "Key-Value store lookup misses."

	::={drdlKvstoreMisses 3}

drdlKvstoreMissesLevelTable OBJECT-TYPE
	SYNTAX      SEQUENCE OF DrdlKvstoreMissesLevelEntry
	MAX-ACCESS  not-accessible
	STATUS      current
	DESCRIPTION
	"Table for drdlKvstoreMisses"
	::={drdlKvstoreMisses 4}

drdlKvstoreMissesLevelEntry OBJECT-TYPE
	SYNTAX      DrdlKvstoreMissesLevelEntry
	MAX-ACCESS  not-accessible
	STATUS      current
	DESCRIPTION
	"Table entry for drdlKvstoreMisses"
	INDEX { drdlKvstoreMissesLevelName }
	::={drdlKvstoreMissesLevelTable 1}

DrdlKvstoreMissesLevelEntry ::=
	SEQUENCE {
		drdlKvstoreMissesLevelName	DisplayString,
		drdlKvstoreMissesLevelVal	Counter64,
		drdlKvstoreMissesLevelMom	CounterBasedGauge64,
		drdlKvstoreMissesLevelMax	CounterBasedGauge64
	}

drdlKvstoreMissesLevelName OBJECT-TYPE
	SYNTAX      DisplayString
	MAX-ACCESS  not-accessible
	STATUS      current
	DESCRIPTION
	"Table entry display string for drdlKvstoreMisses"
	::={drdlKvstoreMissesLevelEntry 1}

drdlKvstoreMissesLevelVal OBJECT-TYPE
	SYNTAX	 Counter64
	MAX-ACCESS  read-only
	STATUS      current
	DESCRIPTION
	"Table entry attribute for drdlKvstoreMisses"
	::={drdlKvstoreMissesLevelEntry 2}

drdlKvstoreMissesLevelMom OBJECT-TYPE
	SYNTAX	 CounterBasedGauge64
	MAX-ACCESS  read-only
	STATUS      current
	DESCRIPTION
	"Table entry attribute for drdlKvstoreMisses"
	::={drdlKvstoreMissesLevelEntry 3}

drdlKvstoreMissesLevelMax OBJECT-TYPE
	SYNTAX	 CounterBasedGauge64
	MAX-ACCESS  read-only
	STATUS      current
	DESCRIPTION
	"Table entry attribute for drdlKvstoreMisses"
	::={drdlKvstoreMissesLevelEntry 4}


drdlDynReoptimizations	OBJECT IDENTIFIER ::={drdl 60}

drdlDynReoptimizationsVal	OBJECT-TYPE
	SYNTAX	 Counter64
	MAX-ACCESS read-only
	STATUS current
	DESCRIPTION "Dynamic reoptimizations."

	::={drdlDynReoptimizations 1}

drdlDynReoptimizationsMom	OBJECT-TYPE
	SYNTAX	 CounterBasedGauge64
	MAX-ACCESS read-only
	STATUS current
	DESCRIPTION "Dynamic reoptimizations."

	::={drdlDynReoptimizations 2}

drdlDynReoptimizationsMax	OBJECT-TYPE
	SYNTAX	 CounterBasedGauge64
	MAX-ACCESS read-only
	STATUS current
	DESCRIPTION "Dynamic reoptimizations."

	::={drdlDynReoptimizations 3}

drdlDynReoptimizationsLevelTable OBJECT-TYPE
	SYNTAX      SEQUENCE OF DrdlDynReoptimizationsLevelEntry
	MAX-ACCESS  not-accessible
	STATUS      current
	DESCRIPTION
	"Table for drdlDynReoptimizations"
	::={drdlDynReoptimizations 4}

drdlDynReoptimizationsLevelEntry OBJECT-TYPE
	SYNTAX      DrdlDynReoptimizationsLevelEntry
	MAX-ACCESS  not-accessible
	STATUS      current
	DESCRIPTION
	"Table entry for drdlDynReoptimizations"
	INDEX { drdlDynReoptimizationsLevelName }
	::={drdlDynReoptimizationsLevelTable 1}

DrdlDynReoptimizationsLevelEntry ::=
	SEQUENCE {
		drdlDynReoptimizationsLevelName	DisplayString,
		drdlDynReoptimizationsLevelVal	Counter64,
		drdlDynReoptimizationsLevelMom	CounterBasedGauge64,
		drdlDynReoptimizationsLevelMax	CounterBasedGauge64
	}

drdlDynReoptimizationsLevelName OBJECT-TYPE
	SYNTAX      DisplayString
	MAX-ACCESS  not-accessible
	STATUS      current
	DESCRIPTION
	"Table entry display string for drdlDynReoptimizations"
	::={drdlDynReoptimizationsLevelEntry 1}

drdlDynReoptimizationsLevelVal OBJECT-TYPE
	SYNTAX	 Counter64
	MAX-ACCESS  read-only
	STATUS      current
	DESCRIPTION
	"Table entry attribute for drdlDynReoptimizations"
	::={drdlDynReoptimizationsLevelEntry 2}

drdlDynReoptimizationsLevelMom OBJECT-TYPE
	SYNTAX	 CounterBasedGauge64
	MAX-ACCESS  read-only
	STATUS      current
	DESCRIPTION
	"Table entry attribute for drdlDynReoptimizations"
	::={drdlDynReoptimizationsLevelEntry 3}

drdlDynReoptimizationsLevelMax OBJECT-TYPE
	SYNTAX	 CounterBasedGauge64
	MAX-ACCESS  read-only
	STATUS      current
	DESCRIPTION
	"Table entry attribute for drdlDynReoptimizations"
	::={drdlDynReoptimizationsLevelEntry 4}


drdlTruncatedOverlongPackets	OBJECT IDENTIFIER ::={drdl 61}

drdlTruncatedOverlongPacketsVal	OBJECT-TYPE
	SYNTAX	 Counter64
	MAX-ACCESS read-only
	STATUS current
	DESCRIPTION "Truncated overlong packets"

	::={drdlTruncatedOverlongPackets 1}

drdlTruncatedOverlongPacketsMom	OBJECT-TYPE
	SYNTAX	 CounterBasedGauge64
	MAX-ACCESS read-only
	STATUS current
	DESCRIPTION "Truncated overlong packets"

	::={drdlTruncatedOverlongPackets 2}

drdlTruncatedOverlongPacketsMax	OBJECT-TYPE
	SYNTAX	 CounterBasedGauge64
	MAX-ACCESS read-only
	STATUS current
	DESCRIPTION "Truncated overlong packets"

	::={drdlTruncatedOverlongPackets 3}

drdlTruncatedOverlongPacketsLevelTable OBJECT-TYPE
	SYNTAX      SEQUENCE OF DrdlTruncatedOverlongPacketsLevelEntry
	MAX-ACCESS  not-accessible
	STATUS      current
	DESCRIPTION
	"Table for drdlTruncatedOverlongPackets"
	::={drdlTruncatedOverlongPackets 4}

drdlTruncatedOverlongPacketsLevelEntry OBJECT-TYPE
	SYNTAX      DrdlTruncatedOverlongPacketsLevelEntry
	MAX-ACCESS  not-accessible
	STATUS      current
	DESCRIPTION
	"Table entry for drdlTruncatedOverlongPackets"
	INDEX { drdlTruncatedOverlongPacketsLevelName }
	::={drdlTruncatedOverlongPacketsLevelTable 1}

DrdlTruncatedOverlongPacketsLevelEntry ::=
	SEQUENCE {
		drdlTruncatedOverlongPacketsLevelName	DisplayString,
		drdlTruncatedOverlongPacketsLevelVal	Counter64,
		drdlTruncatedOverlongPacketsLevelMom	CounterBasedGauge64,
		drdlTruncatedOverlongPacketsLevelMax	CounterBasedGauge64
	}

drdlTruncatedOverlongPacketsLevelName OBJECT-TYPE
	SYNTAX      DisplayString
	MAX-ACCESS  not-accessible
	STATUS      current
	DESCRIPTION
	"Table entry display string for drdlTruncatedOverlongPackets"
	::={drdlTruncatedOverlongPacketsLevelEntry 1}

drdlTruncatedOverlongPacketsLevelVal OBJECT-TYPE
	SYNTAX	 Counter64
	MAX-ACCESS  read-only
	STATUS      current
	DESCRIPTION
	"Table entry attribute for drdlTruncatedOverlongPackets"
	::={drdlTruncatedOverlongPacketsLevelEntry 2}

drdlTruncatedOverlongPacketsLevelMom OBJECT-TYPE
	SYNTAX	 CounterBasedGauge64
	MAX-ACCESS  read-only
	STATUS      current
	DESCRIPTION
	"Table entry attribute for drdlTruncatedOverlongPackets"
	::={drdlTruncatedOverlongPacketsLevelEntry 3}

drdlTruncatedOverlongPacketsLevelMax OBJECT-TYPE
	SYNTAX	 CounterBasedGauge64
	MAX-ACCESS  read-only
	STATUS      current
	DESCRIPTION
	"Table entry attribute for drdlTruncatedOverlongPackets"
	::={drdlTruncatedOverlongPacketsLevelEntry 4}


drdlCutoffStuckUndet	OBJECT IDENTIFIER ::={drdl 62}

drdlCutoffStuckUndetVal	OBJECT-TYPE
	SYNTAX	 Counter64
	MAX-ACCESS read-only
	STATUS current
	DESCRIPTION "Cutoffs (stuck in Being Analyzed)"

	::={drdlCutoffStuckUndet 1}

drdlCutoffStuckUndetMom	OBJECT-TYPE
	SYNTAX	 CounterBasedGauge64
	MAX-ACCESS read-only
	STATUS current
	DESCRIPTION "Cutoffs (stuck in Being Analyzed)"

	::={drdlCutoffStuckUndet 2}

drdlCutoffStuckUndetMax	OBJECT-TYPE
	SYNTAX	 CounterBasedGauge64
	MAX-ACCESS read-only
	STATUS current
	DESCRIPTION "Cutoffs (stuck in Being Analyzed)"

	::={drdlCutoffStuckUndet 3}

drdlCutoffStuckUndetLevelTable OBJECT-TYPE
	SYNTAX      SEQUENCE OF DrdlCutoffStuckUndetLevelEntry
	MAX-ACCESS  not-accessible
	STATUS      current
	DESCRIPTION
	"Table for drdlCutoffStuckUndet"
	::={drdlCutoffStuckUndet 4}

drdlCutoffStuckUndetLevelEntry OBJECT-TYPE
	SYNTAX      DrdlCutoffStuckUndetLevelEntry
	MAX-ACCESS  not-accessible
	STATUS      current
	DESCRIPTION
	"Table entry for drdlCutoffStuckUndet"
	INDEX { drdlCutoffStuckUndetLevelName }
	::={drdlCutoffStuckUndetLevelTable 1}

DrdlCutoffStuckUndetLevelEntry ::=
	SEQUENCE {
		drdlCutoffStuckUndetLevelName	DisplayString,
		drdlCutoffStuckUndetLevelVal	Counter64,
		drdlCutoffStuckUndetLevelMom	CounterBasedGauge64,
		drdlCutoffStuckUndetLevelMax	CounterBasedGauge64
	}

drdlCutoffStuckUndetLevelName OBJECT-TYPE
	SYNTAX      DisplayString
	MAX-ACCESS  not-accessible
	STATUS      current
	DESCRIPTION
	"Table entry display string for drdlCutoffStuckUndet"
	::={drdlCutoffStuckUndetLevelEntry 1}

drdlCutoffStuckUndetLevelVal OBJECT-TYPE
	SYNTAX	 Counter64
	MAX-ACCESS  read-only
	STATUS      current
	DESCRIPTION
	"Table entry attribute for drdlCutoffStuckUndet"
	::={drdlCutoffStuckUndetLevelEntry 2}

drdlCutoffStuckUndetLevelMom OBJECT-TYPE
	SYNTAX	 CounterBasedGauge64
	MAX-ACCESS  read-only
	STATUS      current
	DESCRIPTION
	"Table entry attribute for drdlCutoffStuckUndet"
	::={drdlCutoffStuckUndetLevelEntry 3}

drdlCutoffStuckUndetLevelMax OBJECT-TYPE
	SYNTAX	 CounterBasedGauge64
	MAX-ACCESS  read-only
	STATUS      current
	DESCRIPTION
	"Table entry attribute for drdlCutoffStuckUndet"
	::={drdlCutoffStuckUndetLevelEntry 4}


drdlCutoffStuckWithoutAction	OBJECT IDENTIFIER ::={drdl 63}

drdlCutoffStuckWithoutActionVal	OBJECT-TYPE
	SYNTAX	 Counter64
	MAX-ACCESS read-only
	STATUS current
	DESCRIPTION "Cutoffs (stuck without action)"

	::={drdlCutoffStuckWithoutAction 1}

drdlCutoffStuckWithoutActionMom	OBJECT-TYPE
	SYNTAX	 CounterBasedGauge64
	MAX-ACCESS read-only
	STATUS current
	DESCRIPTION "Cutoffs (stuck without action)"

	::={drdlCutoffStuckWithoutAction 2}

drdlCutoffStuckWithoutActionMax	OBJECT-TYPE
	SYNTAX	 CounterBasedGauge64
	MAX-ACCESS read-only
	STATUS current
	DESCRIPTION "Cutoffs (stuck without action)"

	::={drdlCutoffStuckWithoutAction 3}

drdlCutoffStuckWithoutActionLevelTable OBJECT-TYPE
	SYNTAX      SEQUENCE OF DrdlCutoffStuckWithoutActionLevelEntry
	MAX-ACCESS  not-accessible
	STATUS      current
	DESCRIPTION
	"Table for drdlCutoffStuckWithoutAction"
	::={drdlCutoffStuckWithoutAction 4}

drdlCutoffStuckWithoutActionLevelEntry OBJECT-TYPE
	SYNTAX      DrdlCutoffStuckWithoutActionLevelEntry
	MAX-ACCESS  not-accessible
	STATUS      current
	DESCRIPTION
	"Table entry for drdlCutoffStuckWithoutAction"
	INDEX { drdlCutoffStuckWithoutActionLevelName }
	::={drdlCutoffStuckWithoutActionLevelTable 1}

DrdlCutoffStuckWithoutActionLevelEntry ::=
	SEQUENCE {
		drdlCutoffStuckWithoutActionLevelName	DisplayString,
		drdlCutoffStuckWithoutActionLevelVal	Counter64,
		drdlCutoffStuckWithoutActionLevelMom	CounterBasedGauge64,
		drdlCutoffStuckWithoutActionLevelMax	CounterBasedGauge64
	}

drdlCutoffStuckWithoutActionLevelName OBJECT-TYPE
	SYNTAX      DisplayString
	MAX-ACCESS  not-accessible
	STATUS      current
	DESCRIPTION
	"Table entry display string for drdlCutoffStuckWithoutAction"
	::={drdlCutoffStuckWithoutActionLevelEntry 1}

drdlCutoffStuckWithoutActionLevelVal OBJECT-TYPE
	SYNTAX	 Counter64
	MAX-ACCESS  read-only
	STATUS      current
	DESCRIPTION
	"Table entry attribute for drdlCutoffStuckWithoutAction"
	::={drdlCutoffStuckWithoutActionLevelEntry 2}

drdlCutoffStuckWithoutActionLevelMom OBJECT-TYPE
	SYNTAX	 CounterBasedGauge64
	MAX-ACCESS  read-only
	STATUS      current
	DESCRIPTION
	"Table entry attribute for drdlCutoffStuckWithoutAction"
	::={drdlCutoffStuckWithoutActionLevelEntry 3}

drdlCutoffStuckWithoutActionLevelMax OBJECT-TYPE
	SYNTAX	 CounterBasedGauge64
	MAX-ACCESS  read-only
	STATUS      current
	DESCRIPTION
	"Table entry attribute for drdlCutoffStuckWithoutAction"
	::={drdlCutoffStuckWithoutActionLevelEntry 4}


drdlConnsWithQueuedPkts	OBJECT IDENTIFIER ::={drdl 64}

drdlConnsWithQueuedPktsVal	OBJECT-TYPE
	SYNTAX	 CounterBasedGauge64
	MAX-ACCESS read-only
	STATUS current
	DESCRIPTION "Connections with queued packets"

	::={drdlConnsWithQueuedPkts 1}

drdlConnsWithQueuedPktsMax	OBJECT-TYPE
	SYNTAX	 CounterBasedGauge64
	MAX-ACCESS read-only
	STATUS current
	DESCRIPTION "Connections with queued packets"

	::={drdlConnsWithQueuedPkts 3}

drdlConnsWithQueuedPktsLevelTable OBJECT-TYPE
	SYNTAX      SEQUENCE OF DrdlConnsWithQueuedPktsLevelEntry
	MAX-ACCESS  not-accessible
	STATUS      current
	DESCRIPTION
	"Table for drdlConnsWithQueuedPkts"
	::={drdlConnsWithQueuedPkts 4}

drdlConnsWithQueuedPktsLevelEntry OBJECT-TYPE
	SYNTAX      DrdlConnsWithQueuedPktsLevelEntry
	MAX-ACCESS  not-accessible
	STATUS      current
	DESCRIPTION
	"Table entry for drdlConnsWithQueuedPkts"
	INDEX { drdlConnsWithQueuedPktsLevelName }
	::={drdlConnsWithQueuedPktsLevelTable 1}

DrdlConnsWithQueuedPktsLevelEntry ::=
	SEQUENCE {
		drdlConnsWithQueuedPktsLevelName	DisplayString,
		drdlConnsWithQueuedPktsLevelVal	CounterBasedGauge64,
		drdlConnsWithQueuedPktsLevelMax	CounterBasedGauge64
	}

drdlConnsWithQueuedPktsLevelName OBJECT-TYPE
	SYNTAX      DisplayString
	MAX-ACCESS  not-accessible
	STATUS      current
	DESCRIPTION
	"Table entry display string for drdlConnsWithQueuedPkts"
	::={drdlConnsWithQueuedPktsLevelEntry 1}

drdlConnsWithQueuedPktsLevelVal OBJECT-TYPE
	SYNTAX	 CounterBasedGauge64
	MAX-ACCESS  read-only
	STATUS      current
	DESCRIPTION
	"Table entry attribute for drdlConnsWithQueuedPkts"
	::={drdlConnsWithQueuedPktsLevelEntry 2}

drdlConnsWithQueuedPktsLevelMax OBJECT-TYPE
	SYNTAX	 CounterBasedGauge64
	MAX-ACCESS  read-only
	STATUS      current
	DESCRIPTION
	"Table entry attribute for drdlConnsWithQueuedPkts"
	::={drdlConnsWithQueuedPktsLevelEntry 4}


drdlQueuedPacketsSegments	OBJECT IDENTIFIER ::={drdl 65}

drdlQueuedPacketsSegmentsVal	OBJECT-TYPE
	SYNTAX	 Counter64
	MAX-ACCESS read-only
	STATUS current
	DESCRIPTION "Queued packets (too long segment chains)"

	::={drdlQueuedPacketsSegments 1}

drdlQueuedPacketsSegmentsMom	OBJECT-TYPE
	SYNTAX	 CounterBasedGauge64
	MAX-ACCESS read-only
	STATUS current
	DESCRIPTION "Queued packets (too long segment chains)"

	::={drdlQueuedPacketsSegments 2}

drdlQueuedPacketsSegmentsMax	OBJECT-TYPE
	SYNTAX	 CounterBasedGauge64
	MAX-ACCESS read-only
	STATUS current
	DESCRIPTION "Queued packets (too long segment chains)"

	::={drdlQueuedPacketsSegments 3}

drdlQueuedPacketsSegmentsLevelTable OBJECT-TYPE
	SYNTAX      SEQUENCE OF DrdlQueuedPacketsSegmentsLevelEntry
	MAX-ACCESS  not-accessible
	STATUS      current
	DESCRIPTION
	"Table for drdlQueuedPacketsSegments"
	::={drdlQueuedPacketsSegments 4}

drdlQueuedPacketsSegmentsLevelEntry OBJECT-TYPE
	SYNTAX      DrdlQueuedPacketsSegmentsLevelEntry
	MAX-ACCESS  not-accessible
	STATUS      current
	DESCRIPTION
	"Table entry for drdlQueuedPacketsSegments"
	INDEX { drdlQueuedPacketsSegmentsLevelName }
	::={drdlQueuedPacketsSegmentsLevelTable 1}

DrdlQueuedPacketsSegmentsLevelEntry ::=
	SEQUENCE {
		drdlQueuedPacketsSegmentsLevelName	DisplayString,
		drdlQueuedPacketsSegmentsLevelVal	Counter64,
		drdlQueuedPacketsSegmentsLevelMom	CounterBasedGauge64,
		drdlQueuedPacketsSegmentsLevelMax	CounterBasedGauge64
	}

drdlQueuedPacketsSegmentsLevelName OBJECT-TYPE
	SYNTAX      DisplayString
	MAX-ACCESS  not-accessible
	STATUS      current
	DESCRIPTION
	"Table entry display string for drdlQueuedPacketsSegments"
	::={drdlQueuedPacketsSegmentsLevelEntry 1}

drdlQueuedPacketsSegmentsLevelVal OBJECT-TYPE
	SYNTAX	 Counter64
	MAX-ACCESS  read-only
	STATUS      current
	DESCRIPTION
	"Table entry attribute for drdlQueuedPacketsSegments"
	::={drdlQueuedPacketsSegmentsLevelEntry 2}

drdlQueuedPacketsSegmentsLevelMom OBJECT-TYPE
	SYNTAX	 CounterBasedGauge64
	MAX-ACCESS  read-only
	STATUS      current
	DESCRIPTION
	"Table entry attribute for drdlQueuedPacketsSegments"
	::={drdlQueuedPacketsSegmentsLevelEntry 3}

drdlQueuedPacketsSegmentsLevelMax OBJECT-TYPE
	SYNTAX	 CounterBasedGauge64
	MAX-ACCESS  read-only
	STATUS      current
	DESCRIPTION
	"Table entry attribute for drdlQueuedPacketsSegments"
	::={drdlQueuedPacketsSegmentsLevelEntry 4}


drdlDequeuedPackets	OBJECT IDENTIFIER ::={drdl 66}

drdlDequeuedPacketsVal	OBJECT-TYPE
	SYNTAX	 Counter64
	MAX-ACCESS read-only
	STATUS current
	DESCRIPTION "Dequeued packets"

	::={drdlDequeuedPackets 1}

drdlDequeuedPacketsMom	OBJECT-TYPE
	SYNTAX	 CounterBasedGauge64
	MAX-ACCESS read-only
	STATUS current
	DESCRIPTION "Dequeued packets"

	::={drdlDequeuedPackets 2}

drdlDequeuedPacketsMax	OBJECT-TYPE
	SYNTAX	 CounterBasedGauge64
	MAX-ACCESS read-only
	STATUS current
	DESCRIPTION "Dequeued packets"

	::={drdlDequeuedPackets 3}

drdlDequeuedPacketsLevelTable OBJECT-TYPE
	SYNTAX      SEQUENCE OF DrdlDequeuedPacketsLevelEntry
	MAX-ACCESS  not-accessible
	STATUS      current
	DESCRIPTION
	"Table for drdlDequeuedPackets"
	::={drdlDequeuedPackets 4}

drdlDequeuedPacketsLevelEntry OBJECT-TYPE
	SYNTAX      DrdlDequeuedPacketsLevelEntry
	MAX-ACCESS  not-accessible
	STATUS      current
	DESCRIPTION
	"Table entry for drdlDequeuedPackets"
	INDEX { drdlDequeuedPacketsLevelName }
	::={drdlDequeuedPacketsLevelTable 1}

DrdlDequeuedPacketsLevelEntry ::=
	SEQUENCE {
		drdlDequeuedPacketsLevelName	DisplayString,
		drdlDequeuedPacketsLevelVal	Counter64,
		drdlDequeuedPacketsLevelMom	CounterBasedGauge64,
		drdlDequeuedPacketsLevelMax	CounterBasedGauge64
	}

drdlDequeuedPacketsLevelName OBJECT-TYPE
	SYNTAX      DisplayString
	MAX-ACCESS  not-accessible
	STATUS      current
	DESCRIPTION
	"Table entry display string for drdlDequeuedPackets"
	::={drdlDequeuedPacketsLevelEntry 1}

drdlDequeuedPacketsLevelVal OBJECT-TYPE
	SYNTAX	 Counter64
	MAX-ACCESS  read-only
	STATUS      current
	DESCRIPTION
	"Table entry attribute for drdlDequeuedPackets"
	::={drdlDequeuedPacketsLevelEntry 2}

drdlDequeuedPacketsLevelMom OBJECT-TYPE
	SYNTAX	 CounterBasedGauge64
	MAX-ACCESS  read-only
	STATUS      current
	DESCRIPTION
	"Table entry attribute for drdlDequeuedPackets"
	::={drdlDequeuedPacketsLevelEntry 3}

drdlDequeuedPacketsLevelMax OBJECT-TYPE
	SYNTAX	 CounterBasedGauge64
	MAX-ACCESS  read-only
	STATUS      current
	DESCRIPTION
	"Table entry attribute for drdlDequeuedPackets"
	::={drdlDequeuedPacketsLevelEntry 4}


drdlPacketQueueLength	OBJECT IDENTIFIER ::={drdl 67}

drdlPacketQueueLengthVal	OBJECT-TYPE
	SYNTAX	 CounterBasedGauge64
	MAX-ACCESS read-only
	STATUS current
	DESCRIPTION "Packet queue length"

	::={drdlPacketQueueLength 1}

drdlPacketQueueLengthMax	OBJECT-TYPE
	SYNTAX	 CounterBasedGauge64
	MAX-ACCESS read-only
	STATUS current
	DESCRIPTION "Packet queue length"

	::={drdlPacketQueueLength 3}

drdlPacketQueueLengthLevelTable OBJECT-TYPE
	SYNTAX      SEQUENCE OF DrdlPacketQueueLengthLevelEntry
	MAX-ACCESS  not-accessible
	STATUS      current
	DESCRIPTION
	"Table for drdlPacketQueueLength"
	::={drdlPacketQueueLength 4}

drdlPacketQueueLengthLevelEntry OBJECT-TYPE
	SYNTAX      DrdlPacketQueueLengthLevelEntry
	MAX-ACCESS  not-accessible
	STATUS      current
	DESCRIPTION
	"Table entry for drdlPacketQueueLength"
	INDEX { drdlPacketQueueLengthLevelName }
	::={drdlPacketQueueLengthLevelTable 1}

DrdlPacketQueueLengthLevelEntry ::=
	SEQUENCE {
		drdlPacketQueueLengthLevelName	DisplayString,
		drdlPacketQueueLengthLevelVal	CounterBasedGauge64,
		drdlPacketQueueLengthLevelMax	CounterBasedGauge64
	}

drdlPacketQueueLengthLevelName OBJECT-TYPE
	SYNTAX      DisplayString
	MAX-ACCESS  not-accessible
	STATUS      current
	DESCRIPTION
	"Table entry display string for drdlPacketQueueLength"
	::={drdlPacketQueueLengthLevelEntry 1}

drdlPacketQueueLengthLevelVal OBJECT-TYPE
	SYNTAX	 CounterBasedGauge64
	MAX-ACCESS  read-only
	STATUS      current
	DESCRIPTION
	"Table entry attribute for drdlPacketQueueLength"
	::={drdlPacketQueueLengthLevelEntry 2}

drdlPacketQueueLengthLevelMax OBJECT-TYPE
	SYNTAX	 CounterBasedGauge64
	MAX-ACCESS  read-only
	STATUS      current
	DESCRIPTION
	"Table entry attribute for drdlPacketQueueLength"
	::={drdlPacketQueueLengthLevelEntry 4}


drdlQueuedPacketsTimeSpent	OBJECT IDENTIFIER ::={drdl 68}

drdlQueuedPacketsTimeSpentVal	OBJECT-TYPE
	SYNTAX	 Counter64
	MAX-ACCESS read-only
	STATUS current
	DESCRIPTION "Queued packets (time spent)"

	::={drdlQueuedPacketsTimeSpent 1}

drdlQueuedPacketsTimeSpentMom	OBJECT-TYPE
	SYNTAX	 CounterBasedGauge64
	MAX-ACCESS read-only
	STATUS current
	DESCRIPTION "Queued packets (time spent)"

	::={drdlQueuedPacketsTimeSpent 2}

drdlQueuedPacketsTimeSpentMax	OBJECT-TYPE
	SYNTAX	 CounterBasedGauge64
	MAX-ACCESS read-only
	STATUS current
	DESCRIPTION "Queued packets (time spent)"

	::={drdlQueuedPacketsTimeSpent 3}

drdlQueuedPacketsTimeSpentLevelTable OBJECT-TYPE
	SYNTAX      SEQUENCE OF DrdlQueuedPacketsTimeSpentLevelEntry
	MAX-ACCESS  not-accessible
	STATUS      current
	DESCRIPTION
	"Table for drdlQueuedPacketsTimeSpent"
	::={drdlQueuedPacketsTimeSpent 4}

drdlQueuedPacketsTimeSpentLevelEntry OBJECT-TYPE
	SYNTAX      DrdlQueuedPacketsTimeSpentLevelEntry
	MAX-ACCESS  not-accessible
	STATUS      current
	DESCRIPTION
	"Table entry for drdlQueuedPacketsTimeSpent"
	INDEX { drdlQueuedPacketsTimeSpentLevelName }
	::={drdlQueuedPacketsTimeSpentLevelTable 1}

DrdlQueuedPacketsTimeSpentLevelEntry ::=
	SEQUENCE {
		drdlQueuedPacketsTimeSpentLevelName	DisplayString,
		drdlQueuedPacketsTimeSpentLevelVal	Counter64,
		drdlQueuedPacketsTimeSpentLevelMom	CounterBasedGauge64,
		drdlQueuedPacketsTimeSpentLevelMax	CounterBasedGauge64
	}

drdlQueuedPacketsTimeSpentLevelName OBJECT-TYPE
	SYNTAX      DisplayString
	MAX-ACCESS  not-accessible
	STATUS      current
	DESCRIPTION
	"Table entry display string for drdlQueuedPacketsTimeSpent"
	::={drdlQueuedPacketsTimeSpentLevelEntry 1}

drdlQueuedPacketsTimeSpentLevelVal OBJECT-TYPE
	SYNTAX	 Counter64
	MAX-ACCESS  read-only
	STATUS      current
	DESCRIPTION
	"Table entry attribute for drdlQueuedPacketsTimeSpent"
	::={drdlQueuedPacketsTimeSpentLevelEntry 2}

drdlQueuedPacketsTimeSpentLevelMom OBJECT-TYPE
	SYNTAX	 CounterBasedGauge64
	MAX-ACCESS  read-only
	STATUS      current
	DESCRIPTION
	"Table entry attribute for drdlQueuedPacketsTimeSpent"
	::={drdlQueuedPacketsTimeSpentLevelEntry 3}

drdlQueuedPacketsTimeSpentLevelMax OBJECT-TYPE
	SYNTAX	 CounterBasedGauge64
	MAX-ACCESS  read-only
	STATUS      current
	DESCRIPTION
	"Table entry attribute for drdlQueuedPacketsTimeSpent"
	::={drdlQueuedPacketsTimeSpentLevelEntry 4}


drdlQueueAllocationFailure	OBJECT IDENTIFIER ::={drdl 69}

drdlQueueAllocationFailureVal	OBJECT-TYPE
	SYNTAX	 Counter64
	MAX-ACCESS read-only
	STATUS current
	DESCRIPTION "Queue allocation failures"

	::={drdlQueueAllocationFailure 1}

drdlQueueAllocationFailureMom	OBJECT-TYPE
	SYNTAX	 CounterBasedGauge64
	MAX-ACCESS read-only
	STATUS current
	DESCRIPTION "Queue allocation failures"

	::={drdlQueueAllocationFailure 2}

drdlQueueAllocationFailureMax	OBJECT-TYPE
	SYNTAX	 CounterBasedGauge64
	MAX-ACCESS read-only
	STATUS current
	DESCRIPTION "Queue allocation failures"

	::={drdlQueueAllocationFailure 3}

drdlQueueAllocationFailureLevelTable OBJECT-TYPE
	SYNTAX      SEQUENCE OF DrdlQueueAllocationFailureLevelEntry
	MAX-ACCESS  not-accessible
	STATUS      current
	DESCRIPTION
	"Table for drdlQueueAllocationFailure"
	::={drdlQueueAllocationFailure 4}

drdlQueueAllocationFailureLevelEntry OBJECT-TYPE
	SYNTAX      DrdlQueueAllocationFailureLevelEntry
	MAX-ACCESS  not-accessible
	STATUS      current
	DESCRIPTION
	"Table entry for drdlQueueAllocationFailure"
	INDEX { drdlQueueAllocationFailureLevelName }
	::={drdlQueueAllocationFailureLevelTable 1}

DrdlQueueAllocationFailureLevelEntry ::=
	SEQUENCE {
		drdlQueueAllocationFailureLevelName	DisplayString,
		drdlQueueAllocationFailureLevelVal	Counter64,
		drdlQueueAllocationFailureLevelMom	CounterBasedGauge64,
		drdlQueueAllocationFailureLevelMax	CounterBasedGauge64
	}

drdlQueueAllocationFailureLevelName OBJECT-TYPE
	SYNTAX      DisplayString
	MAX-ACCESS  not-accessible
	STATUS      current
	DESCRIPTION
	"Table entry display string for drdlQueueAllocationFailure"
	::={drdlQueueAllocationFailureLevelEntry 1}

drdlQueueAllocationFailureLevelVal OBJECT-TYPE
	SYNTAX	 Counter64
	MAX-ACCESS  read-only
	STATUS      current
	DESCRIPTION
	"Table entry attribute for drdlQueueAllocationFailure"
	::={drdlQueueAllocationFailureLevelEntry 2}

drdlQueueAllocationFailureLevelMom OBJECT-TYPE
	SYNTAX	 CounterBasedGauge64
	MAX-ACCESS  read-only
	STATUS      current
	DESCRIPTION
	"Table entry attribute for drdlQueueAllocationFailure"
	::={drdlQueueAllocationFailureLevelEntry 3}

drdlQueueAllocationFailureLevelMax OBJECT-TYPE
	SYNTAX	 CounterBasedGauge64
	MAX-ACCESS  read-only
	STATUS      current
	DESCRIPTION
	"Table entry attribute for drdlQueueAllocationFailure"
	::={drdlQueueAllocationFailureLevelEntry 4}


drdlSyncedBufferClears	OBJECT IDENTIFIER ::={drdl 70}

drdlSyncedBufferClearsVal	OBJECT-TYPE
	SYNTAX	 Counter64
	MAX-ACCESS read-only
	STATUS current
	DESCRIPTION "Buffer clears because of incoming sync states"

	::={drdlSyncedBufferClears 1}

drdlSyncedBufferClearsMom	OBJECT-TYPE
	SYNTAX	 CounterBasedGauge64
	MAX-ACCESS read-only
	STATUS current
	DESCRIPTION "Buffer clears because of incoming sync states"

	::={drdlSyncedBufferClears 2}

drdlSyncedBufferClearsMax	OBJECT-TYPE
	SYNTAX	 CounterBasedGauge64
	MAX-ACCESS read-only
	STATUS current
	DESCRIPTION "Buffer clears because of incoming sync states"

	::={drdlSyncedBufferClears 3}

drdlSyncedBufferClearsLevelTable OBJECT-TYPE
	SYNTAX      SEQUENCE OF DrdlSyncedBufferClearsLevelEntry
	MAX-ACCESS  not-accessible
	STATUS      current
	DESCRIPTION
	"Table for drdlSyncedBufferClears"
	::={drdlSyncedBufferClears 4}

drdlSyncedBufferClearsLevelEntry OBJECT-TYPE
	SYNTAX      DrdlSyncedBufferClearsLevelEntry
	MAX-ACCESS  not-accessible
	STATUS      current
	DESCRIPTION
	"Table entry for drdlSyncedBufferClears"
	INDEX { drdlSyncedBufferClearsLevelName }
	::={drdlSyncedBufferClearsLevelTable 1}

DrdlSyncedBufferClearsLevelEntry ::=
	SEQUENCE {
		drdlSyncedBufferClearsLevelName	DisplayString,
		drdlSyncedBufferClearsLevelVal	Counter64,
		drdlSyncedBufferClearsLevelMom	CounterBasedGauge64,
		drdlSyncedBufferClearsLevelMax	CounterBasedGauge64
	}

drdlSyncedBufferClearsLevelName OBJECT-TYPE
	SYNTAX      DisplayString
	MAX-ACCESS  not-accessible
	STATUS      current
	DESCRIPTION
	"Table entry display string for drdlSyncedBufferClears"
	::={drdlSyncedBufferClearsLevelEntry 1}

drdlSyncedBufferClearsLevelVal OBJECT-TYPE
	SYNTAX	 Counter64
	MAX-ACCESS  read-only
	STATUS      current
	DESCRIPTION
	"Table entry attribute for drdlSyncedBufferClears"
	::={drdlSyncedBufferClearsLevelEntry 2}

drdlSyncedBufferClearsLevelMom OBJECT-TYPE
	SYNTAX	 CounterBasedGauge64
	MAX-ACCESS  read-only
	STATUS      current
	DESCRIPTION
	"Table entry attribute for drdlSyncedBufferClears"
	::={drdlSyncedBufferClearsLevelEntry 3}

drdlSyncedBufferClearsLevelMax OBJECT-TYPE
	SYNTAX	 CounterBasedGauge64
	MAX-ACCESS  read-only
	STATUS      current
	DESCRIPTION
	"Table entry attribute for drdlSyncedBufferClears"
	::={drdlSyncedBufferClearsLevelEntry 4}


drdlGrabCodeEarlifications	OBJECT IDENTIFIER ::={drdl 71}

drdlGrabCodeEarlificationsVal	OBJECT-TYPE
	SYNTAX	 Counter64
	MAX-ACCESS read-only
	STATUS current
	DESCRIPTION "Number of bytes grab code has been executed earlier"

	::={drdlGrabCodeEarlifications 1}

drdlGrabCodeEarlificationsMom	OBJECT-TYPE
	SYNTAX	 CounterBasedGauge64
	MAX-ACCESS read-only
	STATUS current
	DESCRIPTION "Number of bytes grab code has been executed earlier"

	::={drdlGrabCodeEarlifications 2}

drdlGrabCodeEarlificationsMax	OBJECT-TYPE
	SYNTAX	 CounterBasedGauge64
	MAX-ACCESS read-only
	STATUS current
	DESCRIPTION "Number of bytes grab code has been executed earlier"

	::={drdlGrabCodeEarlifications 3}

drdlGrabCodeEarlificationsLevelTable OBJECT-TYPE
	SYNTAX      SEQUENCE OF DrdlGrabCodeEarlificationsLevelEntry
	MAX-ACCESS  not-accessible
	STATUS      current
	DESCRIPTION
	"Table for drdlGrabCodeEarlifications"
	::={drdlGrabCodeEarlifications 4}

drdlGrabCodeEarlificationsLevelEntry OBJECT-TYPE
	SYNTAX      DrdlGrabCodeEarlificationsLevelEntry
	MAX-ACCESS  not-accessible
	STATUS      current
	DESCRIPTION
	"Table entry for drdlGrabCodeEarlifications"
	INDEX { drdlGrabCodeEarlificationsLevelName }
	::={drdlGrabCodeEarlificationsLevelTable 1}

DrdlGrabCodeEarlificationsLevelEntry ::=
	SEQUENCE {
		drdlGrabCodeEarlificationsLevelName	DisplayString,
		drdlGrabCodeEarlificationsLevelVal	Counter64,
		drdlGrabCodeEarlificationsLevelMom	CounterBasedGauge64,
		drdlGrabCodeEarlificationsLevelMax	CounterBasedGauge64
	}

drdlGrabCodeEarlificationsLevelName OBJECT-TYPE
	SYNTAX      DisplayString
	MAX-ACCESS  not-accessible
	STATUS      current
	DESCRIPTION
	"Table entry display string for drdlGrabCodeEarlifications"
	::={drdlGrabCodeEarlificationsLevelEntry 1}

drdlGrabCodeEarlificationsLevelVal OBJECT-TYPE
	SYNTAX	 Counter64
	MAX-ACCESS  read-only
	STATUS      current
	DESCRIPTION
	"Table entry attribute for drdlGrabCodeEarlifications"
	::={drdlGrabCodeEarlificationsLevelEntry 2}

drdlGrabCodeEarlificationsLevelMom OBJECT-TYPE
	SYNTAX	 CounterBasedGauge64
	MAX-ACCESS  read-only
	STATUS      current
	DESCRIPTION
	"Table entry attribute for drdlGrabCodeEarlifications"
	::={drdlGrabCodeEarlificationsLevelEntry 3}

drdlGrabCodeEarlificationsLevelMax OBJECT-TYPE
	SYNTAX	 CounterBasedGauge64
	MAX-ACCESS  read-only
	STATUS      current
	DESCRIPTION
	"Table entry attribute for drdlGrabCodeEarlifications"
	::={drdlGrabCodeEarlificationsLevelEntry 4}


drdlKvstoreMinLifetime	OBJECT IDENTIFIER ::={drdl 72}

drdlKvstoreMinLifetimeVal	OBJECT-TYPE
	SYNTAX	 TimeTicks
	MAX-ACCESS read-only
	STATUS current
	DESCRIPTION "The minimum lifetime of the lately reused key-value objects"

	::={drdlKvstoreMinLifetime 1}

drdlKvstoreMinLifetimeLevelTable OBJECT-TYPE
	SYNTAX      SEQUENCE OF DrdlKvstoreMinLifetimeLevelEntry
	MAX-ACCESS  not-accessible
	STATUS      current
	DESCRIPTION
	"Table for drdlKvstoreMinLifetime"
	::={drdlKvstoreMinLifetime 2}

drdlKvstoreMinLifetimeLevelEntry OBJECT-TYPE
	SYNTAX      DrdlKvstoreMinLifetimeLevelEntry
	MAX-ACCESS  not-accessible
	STATUS      current
	DESCRIPTION
	"Table entry for drdlKvstoreMinLifetime"
	INDEX { drdlKvstoreMinLifetimeLevelName }
	::={drdlKvstoreMinLifetimeLevelTable 1}

DrdlKvstoreMinLifetimeLevelEntry ::=
	SEQUENCE {
		drdlKvstoreMinLifetimeLevelName	DisplayString,
		drdlKvstoreMinLifetimeLevelVal	TimeTicks
	}

drdlKvstoreMinLifetimeLevelName OBJECT-TYPE
	SYNTAX      DisplayString
	MAX-ACCESS  not-accessible
	STATUS      current
	DESCRIPTION
	"Table entry display string for drdlKvstoreMinLifetime"
	::={drdlKvstoreMinLifetimeLevelEntry 1}

drdlKvstoreMinLifetimeLevelVal OBJECT-TYPE
	SYNTAX	 TimeTicks
	MAX-ACCESS  read-only
	STATUS      current
	DESCRIPTION
	"Table entry attribute for drdlKvstoreMinLifetime"
	::={drdlKvstoreMinLifetimeLevelEntry 2}


drdlKvstoreReuses	OBJECT IDENTIFIER ::={drdl 73}

drdlKvstoreReusesVal	OBJECT-TYPE
	SYNTAX	 Counter64
	MAX-ACCESS read-only
	STATUS current
	DESCRIPTION "How many key-value store objects are being reused"

	::={drdlKvstoreReuses 1}

drdlKvstoreReusesMom	OBJECT-TYPE
	SYNTAX	 CounterBasedGauge64
	MAX-ACCESS read-only
	STATUS current
	DESCRIPTION "How many key-value store objects are being reused"

	::={drdlKvstoreReuses 2}

drdlKvstoreReusesMax	OBJECT-TYPE
	SYNTAX	 CounterBasedGauge64
	MAX-ACCESS read-only
	STATUS current
	DESCRIPTION "How many key-value store objects are being reused"

	::={drdlKvstoreReuses 3}

drdlKvstoreReusesLevelTable OBJECT-TYPE
	SYNTAX      SEQUENCE OF DrdlKvstoreReusesLevelEntry
	MAX-ACCESS  not-accessible
	STATUS      current
	DESCRIPTION
	"Table for drdlKvstoreReuses"
	::={drdlKvstoreReuses 4}

drdlKvstoreReusesLevelEntry OBJECT-TYPE
	SYNTAX      DrdlKvstoreReusesLevelEntry
	MAX-ACCESS  not-accessible
	STATUS      current
	DESCRIPTION
	"Table entry for drdlKvstoreReuses"
	INDEX { drdlKvstoreReusesLevelName }
	::={drdlKvstoreReusesLevelTable 1}

DrdlKvstoreReusesLevelEntry ::=
	SEQUENCE {
		drdlKvstoreReusesLevelName	DisplayString,
		drdlKvstoreReusesLevelVal	Counter64,
		drdlKvstoreReusesLevelMom	CounterBasedGauge64,
		drdlKvstoreReusesLevelMax	CounterBasedGauge64
	}

drdlKvstoreReusesLevelName OBJECT-TYPE
	SYNTAX      DisplayString
	MAX-ACCESS  not-accessible
	STATUS      current
	DESCRIPTION
	"Table entry display string for drdlKvstoreReuses"
	::={drdlKvstoreReusesLevelEntry 1}

drdlKvstoreReusesLevelVal OBJECT-TYPE
	SYNTAX	 Counter64
	MAX-ACCESS  read-only
	STATUS      current
	DESCRIPTION
	"Table entry attribute for drdlKvstoreReuses"
	::={drdlKvstoreReusesLevelEntry 2}

drdlKvstoreReusesLevelMom OBJECT-TYPE
	SYNTAX	 CounterBasedGauge64
	MAX-ACCESS  read-only
	STATUS      current
	DESCRIPTION
	"Table entry attribute for drdlKvstoreReuses"
	::={drdlKvstoreReusesLevelEntry 3}

drdlKvstoreReusesLevelMax OBJECT-TYPE
	SYNTAX	 CounterBasedGauge64
	MAX-ACCESS  read-only
	STATUS      current
	DESCRIPTION
	"Table entry attribute for drdlKvstoreReuses"
	::={drdlKvstoreReusesLevelEntry 4}


drdlProp128Fail	OBJECT IDENTIFIER ::={drdl 74}

drdlProp128FailVal	OBJECT-TYPE
	SYNTAX	 Counter64
	MAX-ACCESS read-only
	STATUS current
	DESCRIPTION "Property allocation failures (128)"

	::={drdlProp128Fail 1}

drdlProp128FailMom	OBJECT-TYPE
	SYNTAX	 CounterBasedGauge64
	MAX-ACCESS read-only
	STATUS current
	DESCRIPTION "Property allocation failures (128)"

	::={drdlProp128Fail 2}

drdlProp128FailMax	OBJECT-TYPE
	SYNTAX	 CounterBasedGauge64
	MAX-ACCESS read-only
	STATUS current
	DESCRIPTION "Property allocation failures (128)"

	::={drdlProp128Fail 3}

drdlProp128FailLevelTable OBJECT-TYPE
	SYNTAX      SEQUENCE OF DrdlProp128FailLevelEntry
	MAX-ACCESS  not-accessible
	STATUS      current
	DESCRIPTION
	"Table for drdlProp128Fail"
	::={drdlProp128Fail 4}

drdlProp128FailLevelEntry OBJECT-TYPE
	SYNTAX      DrdlProp128FailLevelEntry
	MAX-ACCESS  not-accessible
	STATUS      current
	DESCRIPTION
	"Table entry for drdlProp128Fail"
	INDEX { drdlProp128FailLevelName }
	::={drdlProp128FailLevelTable 1}

DrdlProp128FailLevelEntry ::=
	SEQUENCE {
		drdlProp128FailLevelName	DisplayString,
		drdlProp128FailLevelVal	Counter64,
		drdlProp128FailLevelMom	CounterBasedGauge64,
		drdlProp128FailLevelMax	CounterBasedGauge64
	}

drdlProp128FailLevelName OBJECT-TYPE
	SYNTAX      DisplayString
	MAX-ACCESS  not-accessible
	STATUS      current
	DESCRIPTION
	"Table entry display string for drdlProp128Fail"
	::={drdlProp128FailLevelEntry 1}

drdlProp128FailLevelVal OBJECT-TYPE
	SYNTAX	 Counter64
	MAX-ACCESS  read-only
	STATUS      current
	DESCRIPTION
	"Table entry attribute for drdlProp128Fail"
	::={drdlProp128FailLevelEntry 2}

drdlProp128FailLevelMom OBJECT-TYPE
	SYNTAX	 CounterBasedGauge64
	MAX-ACCESS  read-only
	STATUS      current
	DESCRIPTION
	"Table entry attribute for drdlProp128Fail"
	::={drdlProp128FailLevelEntry 3}

drdlProp128FailLevelMax OBJECT-TYPE
	SYNTAX	 CounterBasedGauge64
	MAX-ACCESS  read-only
	STATUS      current
	DESCRIPTION
	"Table entry attribute for drdlProp128Fail"
	::={drdlProp128FailLevelEntry 4}


drdlProp128Used	OBJECT IDENTIFIER ::={drdl 75}

drdlProp128UsedVal	OBJECT-TYPE
	SYNTAX	 CounterBasedGauge64
	MAX-ACCESS read-only
	STATUS current
	DESCRIPTION "Properties used (128)"

	::={drdlProp128Used 1}

drdlProp128UsedMax	OBJECT-TYPE
	SYNTAX	 CounterBasedGauge64
	MAX-ACCESS read-only
	STATUS current
	DESCRIPTION "Properties used (128)"

	::={drdlProp128Used 3}

drdlProp128UsedLevelTable OBJECT-TYPE
	SYNTAX      SEQUENCE OF DrdlProp128UsedLevelEntry
	MAX-ACCESS  not-accessible
	STATUS      current
	DESCRIPTION
	"Table for drdlProp128Used"
	::={drdlProp128Used 4}

drdlProp128UsedLevelEntry OBJECT-TYPE
	SYNTAX      DrdlProp128UsedLevelEntry
	MAX-ACCESS  not-accessible
	STATUS      current
	DESCRIPTION
	"Table entry for drdlProp128Used"
	INDEX { drdlProp128UsedLevelName }
	::={drdlProp128UsedLevelTable 1}

DrdlProp128UsedLevelEntry ::=
	SEQUENCE {
		drdlProp128UsedLevelName	DisplayString,
		drdlProp128UsedLevelVal	CounterBasedGauge64,
		drdlProp128UsedLevelMax	CounterBasedGauge64
	}

drdlProp128UsedLevelName OBJECT-TYPE
	SYNTAX      DisplayString
	MAX-ACCESS  not-accessible
	STATUS      current
	DESCRIPTION
	"Table entry display string for drdlProp128Used"
	::={drdlProp128UsedLevelEntry 1}

drdlProp128UsedLevelVal OBJECT-TYPE
	SYNTAX	 CounterBasedGauge64
	MAX-ACCESS  read-only
	STATUS      current
	DESCRIPTION
	"Table entry attribute for drdlProp128Used"
	::={drdlProp128UsedLevelEntry 2}

drdlProp128UsedLevelMax OBJECT-TYPE
	SYNTAX	 CounterBasedGauge64
	MAX-ACCESS  read-only
	STATUS      current
	DESCRIPTION
	"Table entry attribute for drdlProp128Used"
	::={drdlProp128UsedLevelEntry 4}


drdlBincode	OBJECT IDENTIFIER ::={sysdiag 25}

drdlBincodePropertySet	OBJECT IDENTIFIER ::={drdlBincode 1}

drdlBincodePropertySetVal	OBJECT-TYPE
	SYNTAX	 Counter64
	MAX-ACCESS read-only
	STATUS current
	DESCRIPTION "Analyzer properties set from bincode"

	::={drdlBincodePropertySet 1}

drdlBincodePropertySetMom	OBJECT-TYPE
	SYNTAX	 CounterBasedGauge64
	MAX-ACCESS read-only
	STATUS current
	DESCRIPTION "Analyzer properties set from bincode"

	::={drdlBincodePropertySet 2}

drdlBincodePropertySetMax	OBJECT-TYPE
	SYNTAX	 CounterBasedGauge64
	MAX-ACCESS read-only
	STATUS current
	DESCRIPTION "Analyzer properties set from bincode"

	::={drdlBincodePropertySet 3}

drdlBincodePropertySetLevelTable OBJECT-TYPE
	SYNTAX      SEQUENCE OF DrdlBincodePropertySetLevelEntry
	MAX-ACCESS  not-accessible
	STATUS      current
	DESCRIPTION
	"Table for drdlBincodePropertySet"
	::={drdlBincodePropertySet 4}

drdlBincodePropertySetLevelEntry OBJECT-TYPE
	SYNTAX      DrdlBincodePropertySetLevelEntry
	MAX-ACCESS  not-accessible
	STATUS      current
	DESCRIPTION
	"Table entry for drdlBincodePropertySet"
	INDEX { drdlBincodePropertySetLevelName }
	::={drdlBincodePropertySetLevelTable 1}

DrdlBincodePropertySetLevelEntry ::=
	SEQUENCE {
		drdlBincodePropertySetLevelName	DisplayString,
		drdlBincodePropertySetLevelVal	Counter64,
		drdlBincodePropertySetLevelMom	CounterBasedGauge64,
		drdlBincodePropertySetLevelMax	CounterBasedGauge64
	}

drdlBincodePropertySetLevelName OBJECT-TYPE
	SYNTAX      DisplayString
	MAX-ACCESS  not-accessible
	STATUS      current
	DESCRIPTION
	"Table entry display string for drdlBincodePropertySet"
	::={drdlBincodePropertySetLevelEntry 1}

drdlBincodePropertySetLevelVal OBJECT-TYPE
	SYNTAX	 Counter64
	MAX-ACCESS  read-only
	STATUS      current
	DESCRIPTION
	"Table entry attribute for drdlBincodePropertySet"
	::={drdlBincodePropertySetLevelEntry 2}

drdlBincodePropertySetLevelMom OBJECT-TYPE
	SYNTAX	 CounterBasedGauge64
	MAX-ACCESS  read-only
	STATUS      current
	DESCRIPTION
	"Table entry attribute for drdlBincodePropertySet"
	::={drdlBincodePropertySetLevelEntry 3}

drdlBincodePropertySetLevelMax OBJECT-TYPE
	SYNTAX	 CounterBasedGauge64
	MAX-ACCESS  read-only
	STATUS      current
	DESCRIPTION
	"Table entry attribute for drdlBincodePropertySet"
	::={drdlBincodePropertySetLevelEntry 4}


drdlBincodePropertyFail	OBJECT IDENTIFIER ::={drdlBincode 2}

drdlBincodePropertyFailVal	OBJECT-TYPE
	SYNTAX	 Counter64
	MAX-ACCESS read-only
	STATUS current
	DESCRIPTION "Analyzer properties that could not be set from bincode"

	::={drdlBincodePropertyFail 1}

drdlBincodePropertyFailMom	OBJECT-TYPE
	SYNTAX	 CounterBasedGauge64
	MAX-ACCESS read-only
	STATUS current
	DESCRIPTION "Analyzer properties that could not be set from bincode"

	::={drdlBincodePropertyFail 2}

drdlBincodePropertyFailMax	OBJECT-TYPE
	SYNTAX	 CounterBasedGauge64
	MAX-ACCESS read-only
	STATUS current
	DESCRIPTION "Analyzer properties that could not be set from bincode"

	::={drdlBincodePropertyFail 3}

drdlBincodePropertyFailLevelTable OBJECT-TYPE
	SYNTAX      SEQUENCE OF DrdlBincodePropertyFailLevelEntry
	MAX-ACCESS  not-accessible
	STATUS      current
	DESCRIPTION
	"Table for drdlBincodePropertyFail"
	::={drdlBincodePropertyFail 4}

drdlBincodePropertyFailLevelEntry OBJECT-TYPE
	SYNTAX      DrdlBincodePropertyFailLevelEntry
	MAX-ACCESS  not-accessible
	STATUS      current
	DESCRIPTION
	"Table entry for drdlBincodePropertyFail"
	INDEX { drdlBincodePropertyFailLevelName }
	::={drdlBincodePropertyFailLevelTable 1}

DrdlBincodePropertyFailLevelEntry ::=
	SEQUENCE {
		drdlBincodePropertyFailLevelName	DisplayString,
		drdlBincodePropertyFailLevelVal	Counter64,
		drdlBincodePropertyFailLevelMom	CounterBasedGauge64,
		drdlBincodePropertyFailLevelMax	CounterBasedGauge64
	}

drdlBincodePropertyFailLevelName OBJECT-TYPE
	SYNTAX      DisplayString
	MAX-ACCESS  not-accessible
	STATUS      current
	DESCRIPTION
	"Table entry display string for drdlBincodePropertyFail"
	::={drdlBincodePropertyFailLevelEntry 1}

drdlBincodePropertyFailLevelVal OBJECT-TYPE
	SYNTAX	 Counter64
	MAX-ACCESS  read-only
	STATUS      current
	DESCRIPTION
	"Table entry attribute for drdlBincodePropertyFail"
	::={drdlBincodePropertyFailLevelEntry 2}

drdlBincodePropertyFailLevelMom OBJECT-TYPE
	SYNTAX	 CounterBasedGauge64
	MAX-ACCESS  read-only
	STATUS      current
	DESCRIPTION
	"Table entry attribute for drdlBincodePropertyFail"
	::={drdlBincodePropertyFailLevelEntry 3}

drdlBincodePropertyFailLevelMax OBJECT-TYPE
	SYNTAX	 CounterBasedGauge64
	MAX-ACCESS  read-only
	STATUS      current
	DESCRIPTION
	"Table entry attribute for drdlBincodePropertyFail"
	::={drdlBincodePropertyFailLevelEntry 4}


drdlBincodeKvstoreAdded	OBJECT IDENTIFIER ::={drdlBincode 3}

drdlBincodeKvstoreAddedVal	OBJECT-TYPE
	SYNTAX	 Counter64
	MAX-ACCESS read-only
	STATUS current
	DESCRIPTION "Key-Value store entries added from bincode"

	::={drdlBincodeKvstoreAdded 1}

drdlBincodeKvstoreAddedMom	OBJECT-TYPE
	SYNTAX	 CounterBasedGauge64
	MAX-ACCESS read-only
	STATUS current
	DESCRIPTION "Key-Value store entries added from bincode"

	::={drdlBincodeKvstoreAdded 2}

drdlBincodeKvstoreAddedMax	OBJECT-TYPE
	SYNTAX	 CounterBasedGauge64
	MAX-ACCESS read-only
	STATUS current
	DESCRIPTION "Key-Value store entries added from bincode"

	::={drdlBincodeKvstoreAdded 3}

drdlBincodeKvstoreAddedLevelTable OBJECT-TYPE
	SYNTAX      SEQUENCE OF DrdlBincodeKvstoreAddedLevelEntry
	MAX-ACCESS  not-accessible
	STATUS      current
	DESCRIPTION
	"Table for drdlBincodeKvstoreAdded"
	::={drdlBincodeKvstoreAdded 4}

drdlBincodeKvstoreAddedLevelEntry OBJECT-TYPE
	SYNTAX      DrdlBincodeKvstoreAddedLevelEntry
	MAX-ACCESS  not-accessible
	STATUS      current
	DESCRIPTION
	"Table entry for drdlBincodeKvstoreAdded"
	INDEX { drdlBincodeKvstoreAddedLevelName }
	::={drdlBincodeKvstoreAddedLevelTable 1}

DrdlBincodeKvstoreAddedLevelEntry ::=
	SEQUENCE {
		drdlBincodeKvstoreAddedLevelName	DisplayString,
		drdlBincodeKvstoreAddedLevelVal	Counter64,
		drdlBincodeKvstoreAddedLevelMom	CounterBasedGauge64,
		drdlBincodeKvstoreAddedLevelMax	CounterBasedGauge64
	}

drdlBincodeKvstoreAddedLevelName OBJECT-TYPE
	SYNTAX      DisplayString
	MAX-ACCESS  not-accessible
	STATUS      current
	DESCRIPTION
	"Table entry display string for drdlBincodeKvstoreAdded"
	::={drdlBincodeKvstoreAddedLevelEntry 1}

drdlBincodeKvstoreAddedLevelVal OBJECT-TYPE
	SYNTAX	 Counter64
	MAX-ACCESS  read-only
	STATUS      current
	DESCRIPTION
	"Table entry attribute for drdlBincodeKvstoreAdded"
	::={drdlBincodeKvstoreAddedLevelEntry 2}

drdlBincodeKvstoreAddedLevelMom OBJECT-TYPE
	SYNTAX	 CounterBasedGauge64
	MAX-ACCESS  read-only
	STATUS      current
	DESCRIPTION
	"Table entry attribute for drdlBincodeKvstoreAdded"
	::={drdlBincodeKvstoreAddedLevelEntry 3}

drdlBincodeKvstoreAddedLevelMax OBJECT-TYPE
	SYNTAX	 CounterBasedGauge64
	MAX-ACCESS  read-only
	STATUS      current
	DESCRIPTION
	"Table entry attribute for drdlBincodeKvstoreAdded"
	::={drdlBincodeKvstoreAddedLevelEntry 4}


drdlBincodeKvstoreHits	OBJECT IDENTIFIER ::={drdlBincode 4}

drdlBincodeKvstoreHitsVal	OBJECT-TYPE
	SYNTAX	 Counter64
	MAX-ACCESS read-only
	STATUS current
	DESCRIPTION "Key-Value store lookup hits from bincode"

	::={drdlBincodeKvstoreHits 1}

drdlBincodeKvstoreHitsMom	OBJECT-TYPE
	SYNTAX	 CounterBasedGauge64
	MAX-ACCESS read-only
	STATUS current
	DESCRIPTION "Key-Value store lookup hits from bincode"

	::={drdlBincodeKvstoreHits 2}

drdlBincodeKvstoreHitsMax	OBJECT-TYPE
	SYNTAX	 CounterBasedGauge64
	MAX-ACCESS read-only
	STATUS current
	DESCRIPTION "Key-Value store lookup hits from bincode"

	::={drdlBincodeKvstoreHits 3}

drdlBincodeKvstoreHitsLevelTable OBJECT-TYPE
	SYNTAX      SEQUENCE OF DrdlBincodeKvstoreHitsLevelEntry
	MAX-ACCESS  not-accessible
	STATUS      current
	DESCRIPTION
	"Table for drdlBincodeKvstoreHits"
	::={drdlBincodeKvstoreHits 4}

drdlBincodeKvstoreHitsLevelEntry OBJECT-TYPE
	SYNTAX      DrdlBincodeKvstoreHitsLevelEntry
	MAX-ACCESS  not-accessible
	STATUS      current
	DESCRIPTION
	"Table entry for drdlBincodeKvstoreHits"
	INDEX { drdlBincodeKvstoreHitsLevelName }
	::={drdlBincodeKvstoreHitsLevelTable 1}

DrdlBincodeKvstoreHitsLevelEntry ::=
	SEQUENCE {
		drdlBincodeKvstoreHitsLevelName	DisplayString,
		drdlBincodeKvstoreHitsLevelVal	Counter64,
		drdlBincodeKvstoreHitsLevelMom	CounterBasedGauge64,
		drdlBincodeKvstoreHitsLevelMax	CounterBasedGauge64
	}

drdlBincodeKvstoreHitsLevelName OBJECT-TYPE
	SYNTAX      DisplayString
	MAX-ACCESS  not-accessible
	STATUS      current
	DESCRIPTION
	"Table entry display string for drdlBincodeKvstoreHits"
	::={drdlBincodeKvstoreHitsLevelEntry 1}

drdlBincodeKvstoreHitsLevelVal OBJECT-TYPE
	SYNTAX	 Counter64
	MAX-ACCESS  read-only
	STATUS      current
	DESCRIPTION
	"Table entry attribute for drdlBincodeKvstoreHits"
	::={drdlBincodeKvstoreHitsLevelEntry 2}

drdlBincodeKvstoreHitsLevelMom OBJECT-TYPE
	SYNTAX	 CounterBasedGauge64
	MAX-ACCESS  read-only
	STATUS      current
	DESCRIPTION
	"Table entry attribute for drdlBincodeKvstoreHits"
	::={drdlBincodeKvstoreHitsLevelEntry 3}

drdlBincodeKvstoreHitsLevelMax OBJECT-TYPE
	SYNTAX	 CounterBasedGauge64
	MAX-ACCESS  read-only
	STATUS      current
	DESCRIPTION
	"Table entry attribute for drdlBincodeKvstoreHits"
	::={drdlBincodeKvstoreHitsLevelEntry 4}


drdlBincodeKvstoreMisses	OBJECT IDENTIFIER ::={drdlBincode 5}

drdlBincodeKvstoreMissesVal	OBJECT-TYPE
	SYNTAX	 Counter64
	MAX-ACCESS read-only
	STATUS current
	DESCRIPTION "Key-Value store lookup misses from bincode"

	::={drdlBincodeKvstoreMisses 1}

drdlBincodeKvstoreMissesMom	OBJECT-TYPE
	SYNTAX	 CounterBasedGauge64
	MAX-ACCESS read-only
	STATUS current
	DESCRIPTION "Key-Value store lookup misses from bincode"

	::={drdlBincodeKvstoreMisses 2}

drdlBincodeKvstoreMissesMax	OBJECT-TYPE
	SYNTAX	 CounterBasedGauge64
	MAX-ACCESS read-only
	STATUS current
	DESCRIPTION "Key-Value store lookup misses from bincode"

	::={drdlBincodeKvstoreMisses 3}

drdlBincodeKvstoreMissesLevelTable OBJECT-TYPE
	SYNTAX      SEQUENCE OF DrdlBincodeKvstoreMissesLevelEntry
	MAX-ACCESS  not-accessible
	STATUS      current
	DESCRIPTION
	"Table for drdlBincodeKvstoreMisses"
	::={drdlBincodeKvstoreMisses 4}

drdlBincodeKvstoreMissesLevelEntry OBJECT-TYPE
	SYNTAX      DrdlBincodeKvstoreMissesLevelEntry
	MAX-ACCESS  not-accessible
	STATUS      current
	DESCRIPTION
	"Table entry for drdlBincodeKvstoreMisses"
	INDEX { drdlBincodeKvstoreMissesLevelName }
	::={drdlBincodeKvstoreMissesLevelTable 1}

DrdlBincodeKvstoreMissesLevelEntry ::=
	SEQUENCE {
		drdlBincodeKvstoreMissesLevelName	DisplayString,
		drdlBincodeKvstoreMissesLevelVal	Counter64,
		drdlBincodeKvstoreMissesLevelMom	CounterBasedGauge64,
		drdlBincodeKvstoreMissesLevelMax	CounterBasedGauge64
	}

drdlBincodeKvstoreMissesLevelName OBJECT-TYPE
	SYNTAX      DisplayString
	MAX-ACCESS  not-accessible
	STATUS      current
	DESCRIPTION
	"Table entry display string for drdlBincodeKvstoreMisses"
	::={drdlBincodeKvstoreMissesLevelEntry 1}

drdlBincodeKvstoreMissesLevelVal OBJECT-TYPE
	SYNTAX	 Counter64
	MAX-ACCESS  read-only
	STATUS      current
	DESCRIPTION
	"Table entry attribute for drdlBincodeKvstoreMisses"
	::={drdlBincodeKvstoreMissesLevelEntry 2}

drdlBincodeKvstoreMissesLevelMom OBJECT-TYPE
	SYNTAX	 CounterBasedGauge64
	MAX-ACCESS  read-only
	STATUS      current
	DESCRIPTION
	"Table entry attribute for drdlBincodeKvstoreMisses"
	::={drdlBincodeKvstoreMissesLevelEntry 3}

drdlBincodeKvstoreMissesLevelMax OBJECT-TYPE
	SYNTAX	 CounterBasedGauge64
	MAX-ACCESS  read-only
	STATUS      current
	DESCRIPTION
	"Table entry attribute for drdlBincodeKvstoreMisses"
	::={drdlBincodeKvstoreMissesLevelEntry 4}


drdlBincodePropertyStateSet	OBJECT IDENTIFIER ::={drdlBincode 6}

drdlBincodePropertyStateSetVal	OBJECT-TYPE
	SYNTAX	 Counter64
	MAX-ACCESS read-only
	STATUS current
	DESCRIPTION "Analyzer state properties allocated from bincode"

	::={drdlBincodePropertyStateSet 1}

drdlBincodePropertyStateSetMom	OBJECT-TYPE
	SYNTAX	 CounterBasedGauge64
	MAX-ACCESS read-only
	STATUS current
	DESCRIPTION "Analyzer state properties allocated from bincode"

	::={drdlBincodePropertyStateSet 2}

drdlBincodePropertyStateSetMax	OBJECT-TYPE
	SYNTAX	 CounterBasedGauge64
	MAX-ACCESS read-only
	STATUS current
	DESCRIPTION "Analyzer state properties allocated from bincode"

	::={drdlBincodePropertyStateSet 3}

drdlBincodePropertyStateSetLevelTable OBJECT-TYPE
	SYNTAX      SEQUENCE OF DrdlBincodePropertyStateSetLevelEntry
	MAX-ACCESS  not-accessible
	STATUS      current
	DESCRIPTION
	"Table for drdlBincodePropertyStateSet"
	::={drdlBincodePropertyStateSet 4}

drdlBincodePropertyStateSetLevelEntry OBJECT-TYPE
	SYNTAX      DrdlBincodePropertyStateSetLevelEntry
	MAX-ACCESS  not-accessible
	STATUS      current
	DESCRIPTION
	"Table entry for drdlBincodePropertyStateSet"
	INDEX { drdlBincodePropertyStateSetLevelName }
	::={drdlBincodePropertyStateSetLevelTable 1}

DrdlBincodePropertyStateSetLevelEntry ::=
	SEQUENCE {
		drdlBincodePropertyStateSetLevelName	DisplayString,
		drdlBincodePropertyStateSetLevelVal	Counter64,
		drdlBincodePropertyStateSetLevelMom	CounterBasedGauge64,
		drdlBincodePropertyStateSetLevelMax	CounterBasedGauge64
	}

drdlBincodePropertyStateSetLevelName OBJECT-TYPE
	SYNTAX      DisplayString
	MAX-ACCESS  not-accessible
	STATUS      current
	DESCRIPTION
	"Table entry display string for drdlBincodePropertyStateSet"
	::={drdlBincodePropertyStateSetLevelEntry 1}

drdlBincodePropertyStateSetLevelVal OBJECT-TYPE
	SYNTAX	 Counter64
	MAX-ACCESS  read-only
	STATUS      current
	DESCRIPTION
	"Table entry attribute for drdlBincodePropertyStateSet"
	::={drdlBincodePropertyStateSetLevelEntry 2}

drdlBincodePropertyStateSetLevelMom OBJECT-TYPE
	SYNTAX	 CounterBasedGauge64
	MAX-ACCESS  read-only
	STATUS      current
	DESCRIPTION
	"Table entry attribute for drdlBincodePropertyStateSet"
	::={drdlBincodePropertyStateSetLevelEntry 3}

drdlBincodePropertyStateSetLevelMax OBJECT-TYPE
	SYNTAX	 CounterBasedGauge64
	MAX-ACCESS  read-only
	STATUS      current
	DESCRIPTION
	"Table entry attribute for drdlBincodePropertyStateSet"
	::={drdlBincodePropertyStateSetLevelEntry 4}


drdlBincodePropertyStateFail	OBJECT IDENTIFIER ::={drdlBincode 7}

drdlBincodePropertyStateFailVal	OBJECT-TYPE
	SYNTAX	 Counter64
	MAX-ACCESS read-only
	STATUS current
	DESCRIPTION "Analyzer state properties failed to allocate from bincode"

	::={drdlBincodePropertyStateFail 1}

drdlBincodePropertyStateFailMom	OBJECT-TYPE
	SYNTAX	 CounterBasedGauge64
	MAX-ACCESS read-only
	STATUS current
	DESCRIPTION "Analyzer state properties failed to allocate from bincode"

	::={drdlBincodePropertyStateFail 2}

drdlBincodePropertyStateFailMax	OBJECT-TYPE
	SYNTAX	 CounterBasedGauge64
	MAX-ACCESS read-only
	STATUS current
	DESCRIPTION "Analyzer state properties failed to allocate from bincode"

	::={drdlBincodePropertyStateFail 3}

drdlBincodePropertyStateFailLevelTable OBJECT-TYPE
	SYNTAX      SEQUENCE OF DrdlBincodePropertyStateFailLevelEntry
	MAX-ACCESS  not-accessible
	STATUS      current
	DESCRIPTION
	"Table for drdlBincodePropertyStateFail"
	::={drdlBincodePropertyStateFail 4}

drdlBincodePropertyStateFailLevelEntry OBJECT-TYPE
	SYNTAX      DrdlBincodePropertyStateFailLevelEntry
	MAX-ACCESS  not-accessible
	STATUS      current
	DESCRIPTION
	"Table entry for drdlBincodePropertyStateFail"
	INDEX { drdlBincodePropertyStateFailLevelName }
	::={drdlBincodePropertyStateFailLevelTable 1}

DrdlBincodePropertyStateFailLevelEntry ::=
	SEQUENCE {
		drdlBincodePropertyStateFailLevelName	DisplayString,
		drdlBincodePropertyStateFailLevelVal	Counter64,
		drdlBincodePropertyStateFailLevelMom	CounterBasedGauge64,
		drdlBincodePropertyStateFailLevelMax	CounterBasedGauge64
	}

drdlBincodePropertyStateFailLevelName OBJECT-TYPE
	SYNTAX      DisplayString
	MAX-ACCESS  not-accessible
	STATUS      current
	DESCRIPTION
	"Table entry display string for drdlBincodePropertyStateFail"
	::={drdlBincodePropertyStateFailLevelEntry 1}

drdlBincodePropertyStateFailLevelVal OBJECT-TYPE
	SYNTAX	 Counter64
	MAX-ACCESS  read-only
	STATUS      current
	DESCRIPTION
	"Table entry attribute for drdlBincodePropertyStateFail"
	::={drdlBincodePropertyStateFailLevelEntry 2}

drdlBincodePropertyStateFailLevelMom OBJECT-TYPE
	SYNTAX	 CounterBasedGauge64
	MAX-ACCESS  read-only
	STATUS      current
	DESCRIPTION
	"Table entry attribute for drdlBincodePropertyStateFail"
	::={drdlBincodePropertyStateFailLevelEntry 3}

drdlBincodePropertyStateFailLevelMax OBJECT-TYPE
	SYNTAX	 CounterBasedGauge64
	MAX-ACCESS  read-only
	STATUS      current
	DESCRIPTION
	"Table entry attribute for drdlBincodePropertyStateFail"
	::={drdlBincodePropertyStateFailLevelEntry 4}


drdlBincodePropertyStateSnafu	OBJECT IDENTIFIER ::={drdlBincode 8}

drdlBincodePropertyStateSnafuVal	OBJECT-TYPE
	SYNTAX	 Counter64
	MAX-ACCESS read-only
	STATUS current
	DESCRIPTION "Analyzer allocated but could not retrieve state from bincode"

	::={drdlBincodePropertyStateSnafu 1}

drdlBincodePropertyStateSnafuMom	OBJECT-TYPE
	SYNTAX	 CounterBasedGauge64
	MAX-ACCESS read-only
	STATUS current
	DESCRIPTION "Analyzer allocated but could not retrieve state from bincode"

	::={drdlBincodePropertyStateSnafu 2}

drdlBincodePropertyStateSnafuMax	OBJECT-TYPE
	SYNTAX	 CounterBasedGauge64
	MAX-ACCESS read-only
	STATUS current
	DESCRIPTION "Analyzer allocated but could not retrieve state from bincode"

	::={drdlBincodePropertyStateSnafu 3}

drdlBincodePropertyStateSnafuLevelTable OBJECT-TYPE
	SYNTAX      SEQUENCE OF DrdlBincodePropertyStateSnafuLevelEntry
	MAX-ACCESS  not-accessible
	STATUS      current
	DESCRIPTION
	"Table for drdlBincodePropertyStateSnafu"
	::={drdlBincodePropertyStateSnafu 4}

drdlBincodePropertyStateSnafuLevelEntry OBJECT-TYPE
	SYNTAX      DrdlBincodePropertyStateSnafuLevelEntry
	MAX-ACCESS  not-accessible
	STATUS      current
	DESCRIPTION
	"Table entry for drdlBincodePropertyStateSnafu"
	INDEX { drdlBincodePropertyStateSnafuLevelName }
	::={drdlBincodePropertyStateSnafuLevelTable 1}

DrdlBincodePropertyStateSnafuLevelEntry ::=
	SEQUENCE {
		drdlBincodePropertyStateSnafuLevelName	DisplayString,
		drdlBincodePropertyStateSnafuLevelVal	Counter64,
		drdlBincodePropertyStateSnafuLevelMom	CounterBasedGauge64,
		drdlBincodePropertyStateSnafuLevelMax	CounterBasedGauge64
	}

drdlBincodePropertyStateSnafuLevelName OBJECT-TYPE
	SYNTAX      DisplayString
	MAX-ACCESS  not-accessible
	STATUS      current
	DESCRIPTION
	"Table entry display string for drdlBincodePropertyStateSnafu"
	::={drdlBincodePropertyStateSnafuLevelEntry 1}

drdlBincodePropertyStateSnafuLevelVal OBJECT-TYPE
	SYNTAX	 Counter64
	MAX-ACCESS  read-only
	STATUS      current
	DESCRIPTION
	"Table entry attribute for drdlBincodePropertyStateSnafu"
	::={drdlBincodePropertyStateSnafuLevelEntry 2}

drdlBincodePropertyStateSnafuLevelMom OBJECT-TYPE
	SYNTAX	 CounterBasedGauge64
	MAX-ACCESS  read-only
	STATUS      current
	DESCRIPTION
	"Table entry attribute for drdlBincodePropertyStateSnafu"
	::={drdlBincodePropertyStateSnafuLevelEntry 3}

drdlBincodePropertyStateSnafuLevelMax OBJECT-TYPE
	SYNTAX	 CounterBasedGauge64
	MAX-ACCESS  read-only
	STATUS      current
	DESCRIPTION
	"Table entry attribute for drdlBincodePropertyStateSnafu"
	::={drdlBincodePropertyStateSnafuLevelEntry 4}


drdlBincodeHeuristicFlagHit	OBJECT IDENTIFIER ::={drdlBincode 9}

drdlBincodeHeuristicFlagHitVal	OBJECT-TYPE
	SYNTAX	 Counter64
	MAX-ACCESS read-only
	STATUS current
	DESCRIPTION "Analyzer heuristic flag access from bincode"

	::={drdlBincodeHeuristicFlagHit 1}

drdlBincodeHeuristicFlagHitMom	OBJECT-TYPE
	SYNTAX	 CounterBasedGauge64
	MAX-ACCESS read-only
	STATUS current
	DESCRIPTION "Analyzer heuristic flag access from bincode"

	::={drdlBincodeHeuristicFlagHit 2}

drdlBincodeHeuristicFlagHitMax	OBJECT-TYPE
	SYNTAX	 CounterBasedGauge64
	MAX-ACCESS read-only
	STATUS current
	DESCRIPTION "Analyzer heuristic flag access from bincode"

	::={drdlBincodeHeuristicFlagHit 3}

drdlBincodeHeuristicFlagHitLevelTable OBJECT-TYPE
	SYNTAX      SEQUENCE OF DrdlBincodeHeuristicFlagHitLevelEntry
	MAX-ACCESS  not-accessible
	STATUS      current
	DESCRIPTION
	"Table for drdlBincodeHeuristicFlagHit"
	::={drdlBincodeHeuristicFlagHit 4}

drdlBincodeHeuristicFlagHitLevelEntry OBJECT-TYPE
	SYNTAX      DrdlBincodeHeuristicFlagHitLevelEntry
	MAX-ACCESS  not-accessible
	STATUS      current
	DESCRIPTION
	"Table entry for drdlBincodeHeuristicFlagHit"
	INDEX { drdlBincodeHeuristicFlagHitLevelName }
	::={drdlBincodeHeuristicFlagHitLevelTable 1}

DrdlBincodeHeuristicFlagHitLevelEntry ::=
	SEQUENCE {
		drdlBincodeHeuristicFlagHitLevelName	DisplayString,
		drdlBincodeHeuristicFlagHitLevelVal	Counter64,
		drdlBincodeHeuristicFlagHitLevelMom	CounterBasedGauge64,
		drdlBincodeHeuristicFlagHitLevelMax	CounterBasedGauge64
	}

drdlBincodeHeuristicFlagHitLevelName OBJECT-TYPE
	SYNTAX      DisplayString
	MAX-ACCESS  not-accessible
	STATUS      current
	DESCRIPTION
	"Table entry display string for drdlBincodeHeuristicFlagHit"
	::={drdlBincodeHeuristicFlagHitLevelEntry 1}

drdlBincodeHeuristicFlagHitLevelVal OBJECT-TYPE
	SYNTAX	 Counter64
	MAX-ACCESS  read-only
	STATUS      current
	DESCRIPTION
	"Table entry attribute for drdlBincodeHeuristicFlagHit"
	::={drdlBincodeHeuristicFlagHitLevelEntry 2}

drdlBincodeHeuristicFlagHitLevelMom OBJECT-TYPE
	SYNTAX	 CounterBasedGauge64
	MAX-ACCESS  read-only
	STATUS      current
	DESCRIPTION
	"Table entry attribute for drdlBincodeHeuristicFlagHit"
	::={drdlBincodeHeuristicFlagHitLevelEntry 3}

drdlBincodeHeuristicFlagHitLevelMax OBJECT-TYPE
	SYNTAX	 CounterBasedGauge64
	MAX-ACCESS  read-only
	STATUS      current
	DESCRIPTION
	"Table entry attribute for drdlBincodeHeuristicFlagHit"
	::={drdlBincodeHeuristicFlagHitLevelEntry 4}


drdlBincodeHeuristicFlagMiss	OBJECT IDENTIFIER ::={drdlBincode 10}

drdlBincodeHeuristicFlagMissVal	OBJECT-TYPE
	SYNTAX	 Counter64
	MAX-ACCESS read-only
	STATUS current
	DESCRIPTION "Analyzer heuristic flag invalid access from bincode"

	::={drdlBincodeHeuristicFlagMiss 1}

drdlBincodeHeuristicFlagMissMom	OBJECT-TYPE
	SYNTAX	 CounterBasedGauge64
	MAX-ACCESS read-only
	STATUS current
	DESCRIPTION "Analyzer heuristic flag invalid access from bincode"

	::={drdlBincodeHeuristicFlagMiss 2}

drdlBincodeHeuristicFlagMissMax	OBJECT-TYPE
	SYNTAX	 CounterBasedGauge64
	MAX-ACCESS read-only
	STATUS current
	DESCRIPTION "Analyzer heuristic flag invalid access from bincode"

	::={drdlBincodeHeuristicFlagMiss 3}

drdlBincodeHeuristicFlagMissLevelTable OBJECT-TYPE
	SYNTAX      SEQUENCE OF DrdlBincodeHeuristicFlagMissLevelEntry
	MAX-ACCESS  not-accessible
	STATUS      current
	DESCRIPTION
	"Table for drdlBincodeHeuristicFlagMiss"
	::={drdlBincodeHeuristicFlagMiss 4}

drdlBincodeHeuristicFlagMissLevelEntry OBJECT-TYPE
	SYNTAX      DrdlBincodeHeuristicFlagMissLevelEntry
	MAX-ACCESS  not-accessible
	STATUS      current
	DESCRIPTION
	"Table entry for drdlBincodeHeuristicFlagMiss"
	INDEX { drdlBincodeHeuristicFlagMissLevelName }
	::={drdlBincodeHeuristicFlagMissLevelTable 1}

DrdlBincodeHeuristicFlagMissLevelEntry ::=
	SEQUENCE {
		drdlBincodeHeuristicFlagMissLevelName	DisplayString,
		drdlBincodeHeuristicFlagMissLevelVal	Counter64,
		drdlBincodeHeuristicFlagMissLevelMom	CounterBasedGauge64,
		drdlBincodeHeuristicFlagMissLevelMax	CounterBasedGauge64
	}

drdlBincodeHeuristicFlagMissLevelName OBJECT-TYPE
	SYNTAX      DisplayString
	MAX-ACCESS  not-accessible
	STATUS      current
	DESCRIPTION
	"Table entry display string for drdlBincodeHeuristicFlagMiss"
	::={drdlBincodeHeuristicFlagMissLevelEntry 1}

drdlBincodeHeuristicFlagMissLevelVal OBJECT-TYPE
	SYNTAX	 Counter64
	MAX-ACCESS  read-only
	STATUS      current
	DESCRIPTION
	"Table entry attribute for drdlBincodeHeuristicFlagMiss"
	::={drdlBincodeHeuristicFlagMissLevelEntry 2}

drdlBincodeHeuristicFlagMissLevelMom OBJECT-TYPE
	SYNTAX	 CounterBasedGauge64
	MAX-ACCESS  read-only
	STATUS      current
	DESCRIPTION
	"Table entry attribute for drdlBincodeHeuristicFlagMiss"
	::={drdlBincodeHeuristicFlagMissLevelEntry 3}

drdlBincodeHeuristicFlagMissLevelMax OBJECT-TYPE
	SYNTAX	 CounterBasedGauge64
	MAX-ACCESS  read-only
	STATUS      current
	DESCRIPTION
	"Table entry attribute for drdlBincodeHeuristicFlagMiss"
	::={drdlBincodeHeuristicFlagMissLevelEntry 4}


drdlBincodeExecuteSuccess	OBJECT IDENTIFIER ::={drdlBincode 11}

drdlBincodeExecuteSuccessVal	OBJECT-TYPE
	SYNTAX	 Counter64
	MAX-ACCESS read-only
	STATUS current
	DESCRIPTION "Successful executions of bincode"

	::={drdlBincodeExecuteSuccess 1}

drdlBincodeExecuteSuccessMom	OBJECT-TYPE
	SYNTAX	 CounterBasedGauge64
	MAX-ACCESS read-only
	STATUS current
	DESCRIPTION "Successful executions of bincode"

	::={drdlBincodeExecuteSuccess 2}

drdlBincodeExecuteSuccessMax	OBJECT-TYPE
	SYNTAX	 CounterBasedGauge64
	MAX-ACCESS read-only
	STATUS current
	DESCRIPTION "Successful executions of bincode"

	::={drdlBincodeExecuteSuccess 3}

drdlBincodeExecuteSuccessLevelTable OBJECT-TYPE
	SYNTAX      SEQUENCE OF DrdlBincodeExecuteSuccessLevelEntry
	MAX-ACCESS  not-accessible
	STATUS      current
	DESCRIPTION
	"Table for drdlBincodeExecuteSuccess"
	::={drdlBincodeExecuteSuccess 4}

drdlBincodeExecuteSuccessLevelEntry OBJECT-TYPE
	SYNTAX      DrdlBincodeExecuteSuccessLevelEntry
	MAX-ACCESS  not-accessible
	STATUS      current
	DESCRIPTION
	"Table entry for drdlBincodeExecuteSuccess"
	INDEX { drdlBincodeExecuteSuccessLevelName }
	::={drdlBincodeExecuteSuccessLevelTable 1}

DrdlBincodeExecuteSuccessLevelEntry ::=
	SEQUENCE {
		drdlBincodeExecuteSuccessLevelName	DisplayString,
		drdlBincodeExecuteSuccessLevelVal	Counter64,
		drdlBincodeExecuteSuccessLevelMom	CounterBasedGauge64,
		drdlBincodeExecuteSuccessLevelMax	CounterBasedGauge64
	}

drdlBincodeExecuteSuccessLevelName OBJECT-TYPE
	SYNTAX      DisplayString
	MAX-ACCESS  not-accessible
	STATUS      current
	DESCRIPTION
	"Table entry display string for drdlBincodeExecuteSuccess"
	::={drdlBincodeExecuteSuccessLevelEntry 1}

drdlBincodeExecuteSuccessLevelVal OBJECT-TYPE
	SYNTAX	 Counter64
	MAX-ACCESS  read-only
	STATUS      current
	DESCRIPTION
	"Table entry attribute for drdlBincodeExecuteSuccess"
	::={drdlBincodeExecuteSuccessLevelEntry 2}

drdlBincodeExecuteSuccessLevelMom OBJECT-TYPE
	SYNTAX	 CounterBasedGauge64
	MAX-ACCESS  read-only
	STATUS      current
	DESCRIPTION
	"Table entry attribute for drdlBincodeExecuteSuccess"
	::={drdlBincodeExecuteSuccessLevelEntry 3}

drdlBincodeExecuteSuccessLevelMax OBJECT-TYPE
	SYNTAX	 CounterBasedGauge64
	MAX-ACCESS  read-only
	STATUS      current
	DESCRIPTION
	"Table entry attribute for drdlBincodeExecuteSuccess"
	::={drdlBincodeExecuteSuccessLevelEntry 4}


drdlBincodeExecuteFail	OBJECT IDENTIFIER ::={drdlBincode 12}

drdlBincodeExecuteFailVal	OBJECT-TYPE
	SYNTAX	 Counter64
	MAX-ACCESS read-only
	STATUS current
	DESCRIPTION "Failed executions of bincode"

	::={drdlBincodeExecuteFail 1}

drdlBincodeExecuteFailMom	OBJECT-TYPE
	SYNTAX	 CounterBasedGauge64
	MAX-ACCESS read-only
	STATUS current
	DESCRIPTION "Failed executions of bincode"

	::={drdlBincodeExecuteFail 2}

drdlBincodeExecuteFailMax	OBJECT-TYPE
	SYNTAX	 CounterBasedGauge64
	MAX-ACCESS read-only
	STATUS current
	DESCRIPTION "Failed executions of bincode"

	::={drdlBincodeExecuteFail 3}

drdlBincodeExecuteFailLevelTable OBJECT-TYPE
	SYNTAX      SEQUENCE OF DrdlBincodeExecuteFailLevelEntry
	MAX-ACCESS  not-accessible
	STATUS      current
	DESCRIPTION
	"Table for drdlBincodeExecuteFail"
	::={drdlBincodeExecuteFail 4}

drdlBincodeExecuteFailLevelEntry OBJECT-TYPE
	SYNTAX      DrdlBincodeExecuteFailLevelEntry
	MAX-ACCESS  not-accessible
	STATUS      current
	DESCRIPTION
	"Table entry for drdlBincodeExecuteFail"
	INDEX { drdlBincodeExecuteFailLevelName }
	::={drdlBincodeExecuteFailLevelTable 1}

DrdlBincodeExecuteFailLevelEntry ::=
	SEQUENCE {
		drdlBincodeExecuteFailLevelName	DisplayString,
		drdlBincodeExecuteFailLevelVal	Counter64,
		drdlBincodeExecuteFailLevelMom	CounterBasedGauge64,
		drdlBincodeExecuteFailLevelMax	CounterBasedGauge64
	}

drdlBincodeExecuteFailLevelName OBJECT-TYPE
	SYNTAX      DisplayString
	MAX-ACCESS  not-accessible
	STATUS      current
	DESCRIPTION
	"Table entry display string for drdlBincodeExecuteFail"
	::={drdlBincodeExecuteFailLevelEntry 1}

drdlBincodeExecuteFailLevelVal OBJECT-TYPE
	SYNTAX	 Counter64
	MAX-ACCESS  read-only
	STATUS      current
	DESCRIPTION
	"Table entry attribute for drdlBincodeExecuteFail"
	::={drdlBincodeExecuteFailLevelEntry 2}

drdlBincodeExecuteFailLevelMom OBJECT-TYPE
	SYNTAX	 CounterBasedGauge64
	MAX-ACCESS  read-only
	STATUS      current
	DESCRIPTION
	"Table entry attribute for drdlBincodeExecuteFail"
	::={drdlBincodeExecuteFailLevelEntry 3}

drdlBincodeExecuteFailLevelMax OBJECT-TYPE
	SYNTAX	 CounterBasedGauge64
	MAX-ACCESS  read-only
	STATUS      current
	DESCRIPTION
	"Table entry attribute for drdlBincodeExecuteFail"
	::={drdlBincodeExecuteFailLevelEntry 4}


drdlBincodePacketBytesTouched	OBJECT IDENTIFIER ::={drdlBincode 13}

drdlBincodePacketBytesTouchedVal	OBJECT-TYPE
	SYNTAX	 Counter64
	MAX-ACCESS read-only
	STATUS current
	DESCRIPTION "Total packet bytes access from bincode"

	::={drdlBincodePacketBytesTouched 1}

drdlBincodePacketBytesTouchedMom	OBJECT-TYPE
	SYNTAX	 CounterBasedGauge64
	MAX-ACCESS read-only
	STATUS current
	DESCRIPTION "Total packet bytes access from bincode"

	::={drdlBincodePacketBytesTouched 2}

drdlBincodePacketBytesTouchedMax	OBJECT-TYPE
	SYNTAX	 CounterBasedGauge64
	MAX-ACCESS read-only
	STATUS current
	DESCRIPTION "Total packet bytes access from bincode"

	::={drdlBincodePacketBytesTouched 3}

drdlBincodePacketBytesTouchedLevelTable OBJECT-TYPE
	SYNTAX      SEQUENCE OF DrdlBincodePacketBytesTouchedLevelEntry
	MAX-ACCESS  not-accessible
	STATUS      current
	DESCRIPTION
	"Table for drdlBincodePacketBytesTouched"
	::={drdlBincodePacketBytesTouched 4}

drdlBincodePacketBytesTouchedLevelEntry OBJECT-TYPE
	SYNTAX      DrdlBincodePacketBytesTouchedLevelEntry
	MAX-ACCESS  not-accessible
	STATUS      current
	DESCRIPTION
	"Table entry for drdlBincodePacketBytesTouched"
	INDEX { drdlBincodePacketBytesTouchedLevelName }
	::={drdlBincodePacketBytesTouchedLevelTable 1}

DrdlBincodePacketBytesTouchedLevelEntry ::=
	SEQUENCE {
		drdlBincodePacketBytesTouchedLevelName	DisplayString,
		drdlBincodePacketBytesTouchedLevelVal	Counter64,
		drdlBincodePacketBytesTouchedLevelMom	CounterBasedGauge64,
		drdlBincodePacketBytesTouchedLevelMax	CounterBasedGauge64
	}

drdlBincodePacketBytesTouchedLevelName OBJECT-TYPE
	SYNTAX      DisplayString
	MAX-ACCESS  not-accessible
	STATUS      current
	DESCRIPTION
	"Table entry display string for drdlBincodePacketBytesTouched"
	::={drdlBincodePacketBytesTouchedLevelEntry 1}

drdlBincodePacketBytesTouchedLevelVal OBJECT-TYPE
	SYNTAX	 Counter64
	MAX-ACCESS  read-only
	STATUS      current
	DESCRIPTION
	"Table entry attribute for drdlBincodePacketBytesTouched"
	::={drdlBincodePacketBytesTouchedLevelEntry 2}

drdlBincodePacketBytesTouchedLevelMom OBJECT-TYPE
	SYNTAX	 CounterBasedGauge64
	MAX-ACCESS  read-only
	STATUS      current
	DESCRIPTION
	"Table entry attribute for drdlBincodePacketBytesTouched"
	::={drdlBincodePacketBytesTouchedLevelEntry 3}

drdlBincodePacketBytesTouchedLevelMax OBJECT-TYPE
	SYNTAX	 CounterBasedGauge64
	MAX-ACCESS  read-only
	STATUS      current
	DESCRIPTION
	"Table entry attribute for drdlBincodePacketBytesTouched"
	::={drdlBincodePacketBytesTouchedLevelEntry 4}


drdlBincodeStringLookupFail	OBJECT IDENTIFIER ::={drdlBincode 14}

drdlBincodeStringLookupFailVal	OBJECT-TYPE
	SYNTAX	 Counter64
	MAX-ACCESS read-only
	STATUS current
	DESCRIPTION "String table lookup failures from bincode"

	::={drdlBincodeStringLookupFail 1}

drdlBincodeStringLookupFailMom	OBJECT-TYPE
	SYNTAX	 CounterBasedGauge64
	MAX-ACCESS read-only
	STATUS current
	DESCRIPTION "String table lookup failures from bincode"

	::={drdlBincodeStringLookupFail 2}

drdlBincodeStringLookupFailMax	OBJECT-TYPE
	SYNTAX	 CounterBasedGauge64
	MAX-ACCESS read-only
	STATUS current
	DESCRIPTION "String table lookup failures from bincode"

	::={drdlBincodeStringLookupFail 3}

drdlBincodeStringLookupFailLevelTable OBJECT-TYPE
	SYNTAX      SEQUENCE OF DrdlBincodeStringLookupFailLevelEntry
	MAX-ACCESS  not-accessible
	STATUS      current
	DESCRIPTION
	"Table for drdlBincodeStringLookupFail"
	::={drdlBincodeStringLookupFail 4}

drdlBincodeStringLookupFailLevelEntry OBJECT-TYPE
	SYNTAX      DrdlBincodeStringLookupFailLevelEntry
	MAX-ACCESS  not-accessible
	STATUS      current
	DESCRIPTION
	"Table entry for drdlBincodeStringLookupFail"
	INDEX { drdlBincodeStringLookupFailLevelName }
	::={drdlBincodeStringLookupFailLevelTable 1}

DrdlBincodeStringLookupFailLevelEntry ::=
	SEQUENCE {
		drdlBincodeStringLookupFailLevelName	DisplayString,
		drdlBincodeStringLookupFailLevelVal	Counter64,
		drdlBincodeStringLookupFailLevelMom	CounterBasedGauge64,
		drdlBincodeStringLookupFailLevelMax	CounterBasedGauge64
	}

drdlBincodeStringLookupFailLevelName OBJECT-TYPE
	SYNTAX      DisplayString
	MAX-ACCESS  not-accessible
	STATUS      current
	DESCRIPTION
	"Table entry display string for drdlBincodeStringLookupFail"
	::={drdlBincodeStringLookupFailLevelEntry 1}

drdlBincodeStringLookupFailLevelVal OBJECT-TYPE
	SYNTAX	 Counter64
	MAX-ACCESS  read-only
	STATUS      current
	DESCRIPTION
	"Table entry attribute for drdlBincodeStringLookupFail"
	::={drdlBincodeStringLookupFailLevelEntry 2}

drdlBincodeStringLookupFailLevelMom OBJECT-TYPE
	SYNTAX	 CounterBasedGauge64
	MAX-ACCESS  read-only
	STATUS      current
	DESCRIPTION
	"Table entry attribute for drdlBincodeStringLookupFail"
	::={drdlBincodeStringLookupFailLevelEntry 3}

drdlBincodeStringLookupFailLevelMax OBJECT-TYPE
	SYNTAX	 CounterBasedGauge64
	MAX-ACCESS  read-only
	STATUS      current
	DESCRIPTION
	"Table entry attribute for drdlBincodeStringLookupFail"
	::={drdlBincodeStringLookupFailLevelEntry 4}


drdlBincodeConfigLookupSuccess	OBJECT IDENTIFIER ::={drdlBincode 15}

drdlBincodeConfigLookupSuccessVal	OBJECT-TYPE
	SYNTAX	 Counter64
	MAX-ACCESS read-only
	STATUS current
	DESCRIPTION "Bincode local config lookup success"

	::={drdlBincodeConfigLookupSuccess 1}

drdlBincodeConfigLookupSuccessMom	OBJECT-TYPE
	SYNTAX	 CounterBasedGauge64
	MAX-ACCESS read-only
	STATUS current
	DESCRIPTION "Bincode local config lookup success"

	::={drdlBincodeConfigLookupSuccess 2}

drdlBincodeConfigLookupSuccessMax	OBJECT-TYPE
	SYNTAX	 CounterBasedGauge64
	MAX-ACCESS read-only
	STATUS current
	DESCRIPTION "Bincode local config lookup success"

	::={drdlBincodeConfigLookupSuccess 3}

drdlBincodeConfigLookupSuccessLevelTable OBJECT-TYPE
	SYNTAX      SEQUENCE OF DrdlBincodeConfigLookupSuccessLevelEntry
	MAX-ACCESS  not-accessible
	STATUS      current
	DESCRIPTION
	"Table for drdlBincodeConfigLookupSuccess"
	::={drdlBincodeConfigLookupSuccess 4}

drdlBincodeConfigLookupSuccessLevelEntry OBJECT-TYPE
	SYNTAX      DrdlBincodeConfigLookupSuccessLevelEntry
	MAX-ACCESS  not-accessible
	STATUS      current
	DESCRIPTION
	"Table entry for drdlBincodeConfigLookupSuccess"
	INDEX { drdlBincodeConfigLookupSuccessLevelName }
	::={drdlBincodeConfigLookupSuccessLevelTable 1}

DrdlBincodeConfigLookupSuccessLevelEntry ::=
	SEQUENCE {
		drdlBincodeConfigLookupSuccessLevelName	DisplayString,
		drdlBincodeConfigLookupSuccessLevelVal	Counter64,
		drdlBincodeConfigLookupSuccessLevelMom	CounterBasedGauge64,
		drdlBincodeConfigLookupSuccessLevelMax	CounterBasedGauge64
	}

drdlBincodeConfigLookupSuccessLevelName OBJECT-TYPE
	SYNTAX      DisplayString
	MAX-ACCESS  not-accessible
	STATUS      current
	DESCRIPTION
	"Table entry display string for drdlBincodeConfigLookupSuccess"
	::={drdlBincodeConfigLookupSuccessLevelEntry 1}

drdlBincodeConfigLookupSuccessLevelVal OBJECT-TYPE
	SYNTAX	 Counter64
	MAX-ACCESS  read-only
	STATUS      current
	DESCRIPTION
	"Table entry attribute for drdlBincodeConfigLookupSuccess"
	::={drdlBincodeConfigLookupSuccessLevelEntry 2}

drdlBincodeConfigLookupSuccessLevelMom OBJECT-TYPE
	SYNTAX	 CounterBasedGauge64
	MAX-ACCESS  read-only
	STATUS      current
	DESCRIPTION
	"Table entry attribute for drdlBincodeConfigLookupSuccess"
	::={drdlBincodeConfigLookupSuccessLevelEntry 3}

drdlBincodeConfigLookupSuccessLevelMax OBJECT-TYPE
	SYNTAX	 CounterBasedGauge64
	MAX-ACCESS  read-only
	STATUS      current
	DESCRIPTION
	"Table entry attribute for drdlBincodeConfigLookupSuccess"
	::={drdlBincodeConfigLookupSuccessLevelEntry 4}


drdlBincodeConfigLookupFail	OBJECT IDENTIFIER ::={drdlBincode 16}

drdlBincodeConfigLookupFailVal	OBJECT-TYPE
	SYNTAX	 Counter64
	MAX-ACCESS read-only
	STATUS current
	DESCRIPTION "Bincode local config lookup failure"

	::={drdlBincodeConfigLookupFail 1}

drdlBincodeConfigLookupFailMom	OBJECT-TYPE
	SYNTAX	 CounterBasedGauge64
	MAX-ACCESS read-only
	STATUS current
	DESCRIPTION "Bincode local config lookup failure"

	::={drdlBincodeConfigLookupFail 2}

drdlBincodeConfigLookupFailMax	OBJECT-TYPE
	SYNTAX	 CounterBasedGauge64
	MAX-ACCESS read-only
	STATUS current
	DESCRIPTION "Bincode local config lookup failure"

	::={drdlBincodeConfigLookupFail 3}

drdlBincodeConfigLookupFailLevelTable OBJECT-TYPE
	SYNTAX      SEQUENCE OF DrdlBincodeConfigLookupFailLevelEntry
	MAX-ACCESS  not-accessible
	STATUS      current
	DESCRIPTION
	"Table for drdlBincodeConfigLookupFail"
	::={drdlBincodeConfigLookupFail 4}

drdlBincodeConfigLookupFailLevelEntry OBJECT-TYPE
	SYNTAX      DrdlBincodeConfigLookupFailLevelEntry
	MAX-ACCESS  not-accessible
	STATUS      current
	DESCRIPTION
	"Table entry for drdlBincodeConfigLookupFail"
	INDEX { drdlBincodeConfigLookupFailLevelName }
	::={drdlBincodeConfigLookupFailLevelTable 1}

DrdlBincodeConfigLookupFailLevelEntry ::=
	SEQUENCE {
		drdlBincodeConfigLookupFailLevelName	DisplayString,
		drdlBincodeConfigLookupFailLevelVal	Counter64,
		drdlBincodeConfigLookupFailLevelMom	CounterBasedGauge64,
		drdlBincodeConfigLookupFailLevelMax	CounterBasedGauge64
	}

drdlBincodeConfigLookupFailLevelName OBJECT-TYPE
	SYNTAX      DisplayString
	MAX-ACCESS  not-accessible
	STATUS      current
	DESCRIPTION
	"Table entry display string for drdlBincodeConfigLookupFail"
	::={drdlBincodeConfigLookupFailLevelEntry 1}

drdlBincodeConfigLookupFailLevelVal OBJECT-TYPE
	SYNTAX	 Counter64
	MAX-ACCESS  read-only
	STATUS      current
	DESCRIPTION
	"Table entry attribute for drdlBincodeConfigLookupFail"
	::={drdlBincodeConfigLookupFailLevelEntry 2}

drdlBincodeConfigLookupFailLevelMom OBJECT-TYPE
	SYNTAX	 CounterBasedGauge64
	MAX-ACCESS  read-only
	STATUS      current
	DESCRIPTION
	"Table entry attribute for drdlBincodeConfigLookupFail"
	::={drdlBincodeConfigLookupFailLevelEntry 3}

drdlBincodeConfigLookupFailLevelMax OBJECT-TYPE
	SYNTAX	 CounterBasedGauge64
	MAX-ACCESS  read-only
	STATUS      current
	DESCRIPTION
	"Table entry attribute for drdlBincodeConfigLookupFail"
	::={drdlBincodeConfigLookupFailLevelEntry 4}


ethernet	OBJECT IDENTIFIER ::={sysdiag 28}

ethernetUnicast	OBJECT IDENTIFIER ::={ethernet 1}

ethernetUnicastVal	OBJECT-TYPE
	SYNTAX	 Counter64
	MAX-ACCESS read-only
	STATUS current
	DESCRIPTION "Unicast packets"

	::={ethernetUnicast 1}

ethernetUnicastMom	OBJECT-TYPE
	SYNTAX	 CounterBasedGauge64
	MAX-ACCESS read-only
	STATUS current
	DESCRIPTION "Unicast packets"

	::={ethernetUnicast 2}

ethernetUnicastMax	OBJECT-TYPE
	SYNTAX	 CounterBasedGauge64
	MAX-ACCESS read-only
	STATUS current
	DESCRIPTION "Unicast packets"

	::={ethernetUnicast 3}

ethernetUnicastLevelTable OBJECT-TYPE
	SYNTAX      SEQUENCE OF EthernetUnicastLevelEntry
	MAX-ACCESS  not-accessible
	STATUS      current
	DESCRIPTION
	"Table for ethernetUnicast"
	::={ethernetUnicast 4}

ethernetUnicastLevelEntry OBJECT-TYPE
	SYNTAX      EthernetUnicastLevelEntry
	MAX-ACCESS  not-accessible
	STATUS      current
	DESCRIPTION
	"Table entry for ethernetUnicast"
	INDEX { ethernetUnicastLevelName }
	::={ethernetUnicastLevelTable 1}

EthernetUnicastLevelEntry ::=
	SEQUENCE {
		ethernetUnicastLevelName	DisplayString,
		ethernetUnicastLevelVal	Counter64,
		ethernetUnicastLevelMom	CounterBasedGauge64,
		ethernetUnicastLevelMax	CounterBasedGauge64
	}

ethernetUnicastLevelName OBJECT-TYPE
	SYNTAX      DisplayString
	MAX-ACCESS  not-accessible
	STATUS      current
	DESCRIPTION
	"Table entry display string for ethernetUnicast"
	::={ethernetUnicastLevelEntry 1}

ethernetUnicastLevelVal OBJECT-TYPE
	SYNTAX	 Counter64
	MAX-ACCESS  read-only
	STATUS      current
	DESCRIPTION
	"Table entry attribute for ethernetUnicast"
	::={ethernetUnicastLevelEntry 2}

ethernetUnicastLevelMom OBJECT-TYPE
	SYNTAX	 CounterBasedGauge64
	MAX-ACCESS  read-only
	STATUS      current
	DESCRIPTION
	"Table entry attribute for ethernetUnicast"
	::={ethernetUnicastLevelEntry 3}

ethernetUnicastLevelMax OBJECT-TYPE
	SYNTAX	 CounterBasedGauge64
	MAX-ACCESS  read-only
	STATUS      current
	DESCRIPTION
	"Table entry attribute for ethernetUnicast"
	::={ethernetUnicastLevelEntry 4}


ethernetBroadcast	OBJECT IDENTIFIER ::={ethernet 2}

ethernetBroadcastVal	OBJECT-TYPE
	SYNTAX	 Counter64
	MAX-ACCESS read-only
	STATUS current
	DESCRIPTION "Broadcast packets"

	::={ethernetBroadcast 1}

ethernetBroadcastMom	OBJECT-TYPE
	SYNTAX	 CounterBasedGauge64
	MAX-ACCESS read-only
	STATUS current
	DESCRIPTION "Broadcast packets"

	::={ethernetBroadcast 2}

ethernetBroadcastMax	OBJECT-TYPE
	SYNTAX	 CounterBasedGauge64
	MAX-ACCESS read-only
	STATUS current
	DESCRIPTION "Broadcast packets"

	::={ethernetBroadcast 3}

ethernetBroadcastLevelTable OBJECT-TYPE
	SYNTAX      SEQUENCE OF EthernetBroadcastLevelEntry
	MAX-ACCESS  not-accessible
	STATUS      current
	DESCRIPTION
	"Table for ethernetBroadcast"
	::={ethernetBroadcast 4}

ethernetBroadcastLevelEntry OBJECT-TYPE
	SYNTAX      EthernetBroadcastLevelEntry
	MAX-ACCESS  not-accessible
	STATUS      current
	DESCRIPTION
	"Table entry for ethernetBroadcast"
	INDEX { ethernetBroadcastLevelName }
	::={ethernetBroadcastLevelTable 1}

EthernetBroadcastLevelEntry ::=
	SEQUENCE {
		ethernetBroadcastLevelName	DisplayString,
		ethernetBroadcastLevelVal	Counter64,
		ethernetBroadcastLevelMom	CounterBasedGauge64,
		ethernetBroadcastLevelMax	CounterBasedGauge64
	}

ethernetBroadcastLevelName OBJECT-TYPE
	SYNTAX      DisplayString
	MAX-ACCESS  not-accessible
	STATUS      current
	DESCRIPTION
	"Table entry display string for ethernetBroadcast"
	::={ethernetBroadcastLevelEntry 1}

ethernetBroadcastLevelVal OBJECT-TYPE
	SYNTAX	 Counter64
	MAX-ACCESS  read-only
	STATUS      current
	DESCRIPTION
	"Table entry attribute for ethernetBroadcast"
	::={ethernetBroadcastLevelEntry 2}

ethernetBroadcastLevelMom OBJECT-TYPE
	SYNTAX	 CounterBasedGauge64
	MAX-ACCESS  read-only
	STATUS      current
	DESCRIPTION
	"Table entry attribute for ethernetBroadcast"
	::={ethernetBroadcastLevelEntry 3}

ethernetBroadcastLevelMax OBJECT-TYPE
	SYNTAX	 CounterBasedGauge64
	MAX-ACCESS  read-only
	STATUS      current
	DESCRIPTION
	"Table entry attribute for ethernetBroadcast"
	::={ethernetBroadcastLevelEntry 4}


ethernetMulticast	OBJECT IDENTIFIER ::={ethernet 3}

ethernetMulticastVal	OBJECT-TYPE
	SYNTAX	 Counter64
	MAX-ACCESS read-only
	STATUS current
	DESCRIPTION "Multicast packets"

	::={ethernetMulticast 1}

ethernetMulticastMom	OBJECT-TYPE
	SYNTAX	 CounterBasedGauge64
	MAX-ACCESS read-only
	STATUS current
	DESCRIPTION "Multicast packets"

	::={ethernetMulticast 2}

ethernetMulticastMax	OBJECT-TYPE
	SYNTAX	 CounterBasedGauge64
	MAX-ACCESS read-only
	STATUS current
	DESCRIPTION "Multicast packets"

	::={ethernetMulticast 3}

ethernetMulticastLevelTable OBJECT-TYPE
	SYNTAX      SEQUENCE OF EthernetMulticastLevelEntry
	MAX-ACCESS  not-accessible
	STATUS      current
	DESCRIPTION
	"Table for ethernetMulticast"
	::={ethernetMulticast 4}

ethernetMulticastLevelEntry OBJECT-TYPE
	SYNTAX      EthernetMulticastLevelEntry
	MAX-ACCESS  not-accessible
	STATUS      current
	DESCRIPTION
	"Table entry for ethernetMulticast"
	INDEX { ethernetMulticastLevelName }
	::={ethernetMulticastLevelTable 1}

EthernetMulticastLevelEntry ::=
	SEQUENCE {
		ethernetMulticastLevelName	DisplayString,
		ethernetMulticastLevelVal	Counter64,
		ethernetMulticastLevelMom	CounterBasedGauge64,
		ethernetMulticastLevelMax	CounterBasedGauge64
	}

ethernetMulticastLevelName OBJECT-TYPE
	SYNTAX      DisplayString
	MAX-ACCESS  not-accessible
	STATUS      current
	DESCRIPTION
	"Table entry display string for ethernetMulticast"
	::={ethernetMulticastLevelEntry 1}

ethernetMulticastLevelVal OBJECT-TYPE
	SYNTAX	 Counter64
	MAX-ACCESS  read-only
	STATUS      current
	DESCRIPTION
	"Table entry attribute for ethernetMulticast"
	::={ethernetMulticastLevelEntry 2}

ethernetMulticastLevelMom OBJECT-TYPE
	SYNTAX	 CounterBasedGauge64
	MAX-ACCESS  read-only
	STATUS      current
	DESCRIPTION
	"Table entry attribute for ethernetMulticast"
	::={ethernetMulticastLevelEntry 3}

ethernetMulticastLevelMax OBJECT-TYPE
	SYNTAX	 CounterBasedGauge64
	MAX-ACCESS  read-only
	STATUS      current
	DESCRIPTION
	"Table entry attribute for ethernetMulticast"
	::={ethernetMulticastLevelEntry 4}


ethernet8021q	OBJECT IDENTIFIER ::={ethernet 4}

ethernet8021qVal	OBJECT-TYPE
	SYNTAX	 Counter64
	MAX-ACCESS read-only
	STATUS current
	DESCRIPTION "802.1q encapsulated packets"

	::={ethernet8021q 1}

ethernet8021qMom	OBJECT-TYPE
	SYNTAX	 CounterBasedGauge64
	MAX-ACCESS read-only
	STATUS current
	DESCRIPTION "802.1q encapsulated packets"

	::={ethernet8021q 2}

ethernet8021qMax	OBJECT-TYPE
	SYNTAX	 CounterBasedGauge64
	MAX-ACCESS read-only
	STATUS current
	DESCRIPTION "802.1q encapsulated packets"

	::={ethernet8021q 3}

ethernet8021qLevelTable OBJECT-TYPE
	SYNTAX      SEQUENCE OF Ethernet8021qLevelEntry
	MAX-ACCESS  not-accessible
	STATUS      current
	DESCRIPTION
	"Table for ethernet8021q"
	::={ethernet8021q 4}

ethernet8021qLevelEntry OBJECT-TYPE
	SYNTAX      Ethernet8021qLevelEntry
	MAX-ACCESS  not-accessible
	STATUS      current
	DESCRIPTION
	"Table entry for ethernet8021q"
	INDEX { ethernet8021qLevelName }
	::={ethernet8021qLevelTable 1}

Ethernet8021qLevelEntry ::=
	SEQUENCE {
		ethernet8021qLevelName	DisplayString,
		ethernet8021qLevelVal	Counter64,
		ethernet8021qLevelMom	CounterBasedGauge64,
		ethernet8021qLevelMax	CounterBasedGauge64
	}

ethernet8021qLevelName OBJECT-TYPE
	SYNTAX      DisplayString
	MAX-ACCESS  not-accessible
	STATUS      current
	DESCRIPTION
	"Table entry display string for ethernet8021q"
	::={ethernet8021qLevelEntry 1}

ethernet8021qLevelVal OBJECT-TYPE
	SYNTAX	 Counter64
	MAX-ACCESS  read-only
	STATUS      current
	DESCRIPTION
	"Table entry attribute for ethernet8021q"
	::={ethernet8021qLevelEntry 2}

ethernet8021qLevelMom OBJECT-TYPE
	SYNTAX	 CounterBasedGauge64
	MAX-ACCESS  read-only
	STATUS      current
	DESCRIPTION
	"Table entry attribute for ethernet8021q"
	::={ethernet8021qLevelEntry 3}

ethernet8021qLevelMax OBJECT-TYPE
	SYNTAX	 CounterBasedGauge64
	MAX-ACCESS  read-only
	STATUS      current
	DESCRIPTION
	"Table entry attribute for ethernet8021q"
	::={ethernet8021qLevelEntry 4}


ethernetMpls	OBJECT IDENTIFIER ::={ethernet 5}

ethernetMplsVal	OBJECT-TYPE
	SYNTAX	 Counter64
	MAX-ACCESS read-only
	STATUS current
	DESCRIPTION "MPLS over Ethernet frames"

	::={ethernetMpls 1}

ethernetMplsMom	OBJECT-TYPE
	SYNTAX	 CounterBasedGauge64
	MAX-ACCESS read-only
	STATUS current
	DESCRIPTION "MPLS over Ethernet frames"

	::={ethernetMpls 2}

ethernetMplsMax	OBJECT-TYPE
	SYNTAX	 CounterBasedGauge64
	MAX-ACCESS read-only
	STATUS current
	DESCRIPTION "MPLS over Ethernet frames"

	::={ethernetMpls 3}

ethernetMplsLevelTable OBJECT-TYPE
	SYNTAX      SEQUENCE OF EthernetMplsLevelEntry
	MAX-ACCESS  not-accessible
	STATUS      current
	DESCRIPTION
	"Table for ethernetMpls"
	::={ethernetMpls 4}

ethernetMplsLevelEntry OBJECT-TYPE
	SYNTAX      EthernetMplsLevelEntry
	MAX-ACCESS  not-accessible
	STATUS      current
	DESCRIPTION
	"Table entry for ethernetMpls"
	INDEX { ethernetMplsLevelName }
	::={ethernetMplsLevelTable 1}

EthernetMplsLevelEntry ::=
	SEQUENCE {
		ethernetMplsLevelName	DisplayString,
		ethernetMplsLevelVal	Counter64,
		ethernetMplsLevelMom	CounterBasedGauge64,
		ethernetMplsLevelMax	CounterBasedGauge64
	}

ethernetMplsLevelName OBJECT-TYPE
	SYNTAX      DisplayString
	MAX-ACCESS  not-accessible
	STATUS      current
	DESCRIPTION
	"Table entry display string for ethernetMpls"
	::={ethernetMplsLevelEntry 1}

ethernetMplsLevelVal OBJECT-TYPE
	SYNTAX	 Counter64
	MAX-ACCESS  read-only
	STATUS      current
	DESCRIPTION
	"Table entry attribute for ethernetMpls"
	::={ethernetMplsLevelEntry 2}

ethernetMplsLevelMom OBJECT-TYPE
	SYNTAX	 CounterBasedGauge64
	MAX-ACCESS  read-only
	STATUS      current
	DESCRIPTION
	"Table entry attribute for ethernetMpls"
	::={ethernetMplsLevelEntry 3}

ethernetMplsLevelMax OBJECT-TYPE
	SYNTAX	 CounterBasedGauge64
	MAX-ACCESS  read-only
	STATUS      current
	DESCRIPTION
	"Table entry attribute for ethernetMpls"
	::={ethernetMplsLevelEntry 4}


ethernetMplsOoh	OBJECT IDENTIFIER ::={ethernet 6}

ethernetMplsOohVal	OBJECT-TYPE
	SYNTAX	 Counter64
	MAX-ACCESS read-only
	STATUS current
	DESCRIPTION "Invalid MPLS frames"

	::={ethernetMplsOoh 1}

ethernetMplsOohMom	OBJECT-TYPE
	SYNTAX	 CounterBasedGauge64
	MAX-ACCESS read-only
	STATUS current
	DESCRIPTION "Invalid MPLS frames"

	::={ethernetMplsOoh 2}

ethernetMplsOohMax	OBJECT-TYPE
	SYNTAX	 CounterBasedGauge64
	MAX-ACCESS read-only
	STATUS current
	DESCRIPTION "Invalid MPLS frames"

	::={ethernetMplsOoh 3}

ethernetMplsOohLevelTable OBJECT-TYPE
	SYNTAX      SEQUENCE OF EthernetMplsOohLevelEntry
	MAX-ACCESS  not-accessible
	STATUS      current
	DESCRIPTION
	"Table for ethernetMplsOoh"
	::={ethernetMplsOoh 4}

ethernetMplsOohLevelEntry OBJECT-TYPE
	SYNTAX      EthernetMplsOohLevelEntry
	MAX-ACCESS  not-accessible
	STATUS      current
	DESCRIPTION
	"Table entry for ethernetMplsOoh"
	INDEX { ethernetMplsOohLevelName }
	::={ethernetMplsOohLevelTable 1}

EthernetMplsOohLevelEntry ::=
	SEQUENCE {
		ethernetMplsOohLevelName	DisplayString,
		ethernetMplsOohLevelVal	Counter64,
		ethernetMplsOohLevelMom	CounterBasedGauge64,
		ethernetMplsOohLevelMax	CounterBasedGauge64
	}

ethernetMplsOohLevelName OBJECT-TYPE
	SYNTAX      DisplayString
	MAX-ACCESS  not-accessible
	STATUS      current
	DESCRIPTION
	"Table entry display string for ethernetMplsOoh"
	::={ethernetMplsOohLevelEntry 1}

ethernetMplsOohLevelVal OBJECT-TYPE
	SYNTAX	 Counter64
	MAX-ACCESS  read-only
	STATUS      current
	DESCRIPTION
	"Table entry attribute for ethernetMplsOoh"
	::={ethernetMplsOohLevelEntry 2}

ethernetMplsOohLevelMom OBJECT-TYPE
	SYNTAX	 CounterBasedGauge64
	MAX-ACCESS  read-only
	STATUS      current
	DESCRIPTION
	"Table entry attribute for ethernetMplsOoh"
	::={ethernetMplsOohLevelEntry 3}

ethernetMplsOohLevelMax OBJECT-TYPE
	SYNTAX	 CounterBasedGauge64
	MAX-ACCESS  read-only
	STATUS      current
	DESCRIPTION
	"Table entry attribute for ethernetMplsOoh"
	::={ethernetMplsOohLevelEntry 4}


ethernetNonIp	OBJECT IDENTIFIER ::={ethernet 7}

ethernetNonIpVal	OBJECT-TYPE
	SYNTAX	 Counter64
	MAX-ACCESS read-only
	STATUS current
	DESCRIPTION "Non IP packets"

	::={ethernetNonIp 1}

ethernetNonIpMom	OBJECT-TYPE
	SYNTAX	 CounterBasedGauge64
	MAX-ACCESS read-only
	STATUS current
	DESCRIPTION "Non IP packets"

	::={ethernetNonIp 2}

ethernetNonIpMax	OBJECT-TYPE
	SYNTAX	 CounterBasedGauge64
	MAX-ACCESS read-only
	STATUS current
	DESCRIPTION "Non IP packets"

	::={ethernetNonIp 3}

ethernetNonIpLevelTable OBJECT-TYPE
	SYNTAX      SEQUENCE OF EthernetNonIpLevelEntry
	MAX-ACCESS  not-accessible
	STATUS      current
	DESCRIPTION
	"Table for ethernetNonIp"
	::={ethernetNonIp 4}

ethernetNonIpLevelEntry OBJECT-TYPE
	SYNTAX      EthernetNonIpLevelEntry
	MAX-ACCESS  not-accessible
	STATUS      current
	DESCRIPTION
	"Table entry for ethernetNonIp"
	INDEX { ethernetNonIpLevelName }
	::={ethernetNonIpLevelTable 1}

EthernetNonIpLevelEntry ::=
	SEQUENCE {
		ethernetNonIpLevelName	DisplayString,
		ethernetNonIpLevelVal	Counter64,
		ethernetNonIpLevelMom	CounterBasedGauge64,
		ethernetNonIpLevelMax	CounterBasedGauge64
	}

ethernetNonIpLevelName OBJECT-TYPE
	SYNTAX      DisplayString
	MAX-ACCESS  not-accessible
	STATUS      current
	DESCRIPTION
	"Table entry display string for ethernetNonIp"
	::={ethernetNonIpLevelEntry 1}

ethernetNonIpLevelVal OBJECT-TYPE
	SYNTAX	 Counter64
	MAX-ACCESS  read-only
	STATUS      current
	DESCRIPTION
	"Table entry attribute for ethernetNonIp"
	::={ethernetNonIpLevelEntry 2}

ethernetNonIpLevelMom OBJECT-TYPE
	SYNTAX	 CounterBasedGauge64
	MAX-ACCESS  read-only
	STATUS      current
	DESCRIPTION
	"Table entry attribute for ethernetNonIp"
	::={ethernetNonIpLevelEntry 3}

ethernetNonIpLevelMax OBJECT-TYPE
	SYNTAX	 CounterBasedGauge64
	MAX-ACCESS  read-only
	STATUS      current
	DESCRIPTION
	"Table entry attribute for ethernetNonIp"
	::={ethernetNonIpLevelEntry 4}


ethernetDivert	OBJECT IDENTIFIER ::={ethernet 8}

ethernetDivertVal	OBJECT-TYPE
	SYNTAX	 Counter64
	MAX-ACCESS read-only
	STATUS current
	DESCRIPTION "Divert packets"

	::={ethernetDivert 1}

ethernetDivertMom	OBJECT-TYPE
	SYNTAX	 CounterBasedGauge64
	MAX-ACCESS read-only
	STATUS current
	DESCRIPTION "Divert packets"

	::={ethernetDivert 2}

ethernetDivertMax	OBJECT-TYPE
	SYNTAX	 CounterBasedGauge64
	MAX-ACCESS read-only
	STATUS current
	DESCRIPTION "Divert packets"

	::={ethernetDivert 3}

ethernetDivertLevelTable OBJECT-TYPE
	SYNTAX      SEQUENCE OF EthernetDivertLevelEntry
	MAX-ACCESS  not-accessible
	STATUS      current
	DESCRIPTION
	"Table for ethernetDivert"
	::={ethernetDivert 4}

ethernetDivertLevelEntry OBJECT-TYPE
	SYNTAX      EthernetDivertLevelEntry
	MAX-ACCESS  not-accessible
	STATUS      current
	DESCRIPTION
	"Table entry for ethernetDivert"
	INDEX { ethernetDivertLevelName }
	::={ethernetDivertLevelTable 1}

EthernetDivertLevelEntry ::=
	SEQUENCE {
		ethernetDivertLevelName	DisplayString,
		ethernetDivertLevelVal	Counter64,
		ethernetDivertLevelMom	CounterBasedGauge64,
		ethernetDivertLevelMax	CounterBasedGauge64
	}

ethernetDivertLevelName OBJECT-TYPE
	SYNTAX      DisplayString
	MAX-ACCESS  not-accessible
	STATUS      current
	DESCRIPTION
	"Table entry display string for ethernetDivert"
	::={ethernetDivertLevelEntry 1}

ethernetDivertLevelVal OBJECT-TYPE
	SYNTAX	 Counter64
	MAX-ACCESS  read-only
	STATUS      current
	DESCRIPTION
	"Table entry attribute for ethernetDivert"
	::={ethernetDivertLevelEntry 2}

ethernetDivertLevelMom OBJECT-TYPE
	SYNTAX	 CounterBasedGauge64
	MAX-ACCESS  read-only
	STATUS      current
	DESCRIPTION
	"Table entry attribute for ethernetDivert"
	::={ethernetDivertLevelEntry 3}

ethernetDivertLevelMax OBJECT-TYPE
	SYNTAX	 CounterBasedGauge64
	MAX-ACCESS  read-only
	STATUS      current
	DESCRIPTION
	"Table entry attribute for ethernetDivert"
	::={ethernetDivertLevelEntry 4}


ethernetShuntEthertypePackets	OBJECT IDENTIFIER ::={ethernet 22}

ethernetShuntEthertypePacketsVal	OBJECT-TYPE
	SYNTAX	 Counter64
	MAX-ACCESS read-only
	STATUS current
	DESCRIPTION "Shunted packets (ethertype)"

	::={ethernetShuntEthertypePackets 1}

ethernetShuntEthertypePacketsMom	OBJECT-TYPE
	SYNTAX	 CounterBasedGauge64
	MAX-ACCESS read-only
	STATUS current
	DESCRIPTION "Shunted packets (ethertype)"

	::={ethernetShuntEthertypePackets 2}

ethernetShuntEthertypePacketsMax	OBJECT-TYPE
	SYNTAX	 CounterBasedGauge64
	MAX-ACCESS read-only
	STATUS current
	DESCRIPTION "Shunted packets (ethertype)"

	::={ethernetShuntEthertypePackets 3}

ethernetShuntEthertypePacketsLevelTable OBJECT-TYPE
	SYNTAX      SEQUENCE OF EthernetShuntEthertypePacketsLevelEntry
	MAX-ACCESS  not-accessible
	STATUS      current
	DESCRIPTION
	"Table for ethernetShuntEthertypePackets"
	::={ethernetShuntEthertypePackets 4}

ethernetShuntEthertypePacketsLevelEntry OBJECT-TYPE
	SYNTAX      EthernetShuntEthertypePacketsLevelEntry
	MAX-ACCESS  not-accessible
	STATUS      current
	DESCRIPTION
	"Table entry for ethernetShuntEthertypePackets"
	INDEX { ethernetShuntEthertypePacketsLevelName }
	::={ethernetShuntEthertypePacketsLevelTable 1}

EthernetShuntEthertypePacketsLevelEntry ::=
	SEQUENCE {
		ethernetShuntEthertypePacketsLevelName	DisplayString,
		ethernetShuntEthertypePacketsLevelVal	Counter64,
		ethernetShuntEthertypePacketsLevelMom	CounterBasedGauge64,
		ethernetShuntEthertypePacketsLevelMax	CounterBasedGauge64
	}

ethernetShuntEthertypePacketsLevelName OBJECT-TYPE
	SYNTAX      DisplayString
	MAX-ACCESS  not-accessible
	STATUS      current
	DESCRIPTION
	"Table entry display string for ethernetShuntEthertypePackets"
	::={ethernetShuntEthertypePacketsLevelEntry 1}

ethernetShuntEthertypePacketsLevelVal OBJECT-TYPE
	SYNTAX	 Counter64
	MAX-ACCESS  read-only
	STATUS      current
	DESCRIPTION
	"Table entry attribute for ethernetShuntEthertypePackets"
	::={ethernetShuntEthertypePacketsLevelEntry 2}

ethernetShuntEthertypePacketsLevelMom OBJECT-TYPE
	SYNTAX	 CounterBasedGauge64
	MAX-ACCESS  read-only
	STATUS      current
	DESCRIPTION
	"Table entry attribute for ethernetShuntEthertypePackets"
	::={ethernetShuntEthertypePacketsLevelEntry 3}

ethernetShuntEthertypePacketsLevelMax OBJECT-TYPE
	SYNTAX	 CounterBasedGauge64
	MAX-ACCESS  read-only
	STATUS      current
	DESCRIPTION
	"Table entry attribute for ethernetShuntEthertypePackets"
	::={ethernetShuntEthertypePacketsLevelEntry 4}


ethernetShuntEthertypeBytes	OBJECT IDENTIFIER ::={ethernet 23}

ethernetShuntEthertypeBytesVal	OBJECT-TYPE
	SYNTAX	 Counter64
	MAX-ACCESS read-only
	STATUS current
	DESCRIPTION "Shunted bytes (ethertype)"

	::={ethernetShuntEthertypeBytes 1}

ethernetShuntEthertypeBytesMom	OBJECT-TYPE
	SYNTAX	 CounterBasedGauge64
	MAX-ACCESS read-only
	STATUS current
	DESCRIPTION "Shunted bytes (ethertype)"

	::={ethernetShuntEthertypeBytes 2}

ethernetShuntEthertypeBytesMax	OBJECT-TYPE
	SYNTAX	 CounterBasedGauge64
	MAX-ACCESS read-only
	STATUS current
	DESCRIPTION "Shunted bytes (ethertype)"

	::={ethernetShuntEthertypeBytes 3}

ethernetShuntEthertypeBytesLevelTable OBJECT-TYPE
	SYNTAX      SEQUENCE OF EthernetShuntEthertypeBytesLevelEntry
	MAX-ACCESS  not-accessible
	STATUS      current
	DESCRIPTION
	"Table for ethernetShuntEthertypeBytes"
	::={ethernetShuntEthertypeBytes 4}

ethernetShuntEthertypeBytesLevelEntry OBJECT-TYPE
	SYNTAX      EthernetShuntEthertypeBytesLevelEntry
	MAX-ACCESS  not-accessible
	STATUS      current
	DESCRIPTION
	"Table entry for ethernetShuntEthertypeBytes"
	INDEX { ethernetShuntEthertypeBytesLevelName }
	::={ethernetShuntEthertypeBytesLevelTable 1}

EthernetShuntEthertypeBytesLevelEntry ::=
	SEQUENCE {
		ethernetShuntEthertypeBytesLevelName	DisplayString,
		ethernetShuntEthertypeBytesLevelVal	Counter64,
		ethernetShuntEthertypeBytesLevelMom	CounterBasedGauge64,
		ethernetShuntEthertypeBytesLevelMax	CounterBasedGauge64
	}

ethernetShuntEthertypeBytesLevelName OBJECT-TYPE
	SYNTAX      DisplayString
	MAX-ACCESS  not-accessible
	STATUS      current
	DESCRIPTION
	"Table entry display string for ethernetShuntEthertypeBytes"
	::={ethernetShuntEthertypeBytesLevelEntry 1}

ethernetShuntEthertypeBytesLevelVal OBJECT-TYPE
	SYNTAX	 Counter64
	MAX-ACCESS  read-only
	STATUS      current
	DESCRIPTION
	"Table entry attribute for ethernetShuntEthertypeBytes"
	::={ethernetShuntEthertypeBytesLevelEntry 2}

ethernetShuntEthertypeBytesLevelMom OBJECT-TYPE
	SYNTAX	 CounterBasedGauge64
	MAX-ACCESS  read-only
	STATUS      current
	DESCRIPTION
	"Table entry attribute for ethernetShuntEthertypeBytes"
	::={ethernetShuntEthertypeBytesLevelEntry 3}

ethernetShuntEthertypeBytesLevelMax OBJECT-TYPE
	SYNTAX	 CounterBasedGauge64
	MAX-ACCESS  read-only
	STATUS      current
	DESCRIPTION
	"Table entry attribute for ethernetShuntEthertypeBytes"
	::={ethernetShuntEthertypeBytesLevelEntry 4}


ethernetShuntMplsPackets	OBJECT IDENTIFIER ::={ethernet 24}

ethernetShuntMplsPacketsVal	OBJECT-TYPE
	SYNTAX	 Counter64
	MAX-ACCESS read-only
	STATUS current
	DESCRIPTION "Shunted packets (MPLS)"

	::={ethernetShuntMplsPackets 1}

ethernetShuntMplsPacketsMom	OBJECT-TYPE
	SYNTAX	 CounterBasedGauge64
	MAX-ACCESS read-only
	STATUS current
	DESCRIPTION "Shunted packets (MPLS)"

	::={ethernetShuntMplsPackets 2}

ethernetShuntMplsPacketsMax	OBJECT-TYPE
	SYNTAX	 CounterBasedGauge64
	MAX-ACCESS read-only
	STATUS current
	DESCRIPTION "Shunted packets (MPLS)"

	::={ethernetShuntMplsPackets 3}

ethernetShuntMplsPacketsLevelTable OBJECT-TYPE
	SYNTAX      SEQUENCE OF EthernetShuntMplsPacketsLevelEntry
	MAX-ACCESS  not-accessible
	STATUS      current
	DESCRIPTION
	"Table for ethernetShuntMplsPackets"
	::={ethernetShuntMplsPackets 4}

ethernetShuntMplsPacketsLevelEntry OBJECT-TYPE
	SYNTAX      EthernetShuntMplsPacketsLevelEntry
	MAX-ACCESS  not-accessible
	STATUS      current
	DESCRIPTION
	"Table entry for ethernetShuntMplsPackets"
	INDEX { ethernetShuntMplsPacketsLevelName }
	::={ethernetShuntMplsPacketsLevelTable 1}

EthernetShuntMplsPacketsLevelEntry ::=
	SEQUENCE {
		ethernetShuntMplsPacketsLevelName	DisplayString,
		ethernetShuntMplsPacketsLevelVal	Counter64,
		ethernetShuntMplsPacketsLevelMom	CounterBasedGauge64,
		ethernetShuntMplsPacketsLevelMax	CounterBasedGauge64
	}

ethernetShuntMplsPacketsLevelName OBJECT-TYPE
	SYNTAX      DisplayString
	MAX-ACCESS  not-accessible
	STATUS      current
	DESCRIPTION
	"Table entry display string for ethernetShuntMplsPackets"
	::={ethernetShuntMplsPacketsLevelEntry 1}

ethernetShuntMplsPacketsLevelVal OBJECT-TYPE
	SYNTAX	 Counter64
	MAX-ACCESS  read-only
	STATUS      current
	DESCRIPTION
	"Table entry attribute for ethernetShuntMplsPackets"
	::={ethernetShuntMplsPacketsLevelEntry 2}

ethernetShuntMplsPacketsLevelMom OBJECT-TYPE
	SYNTAX	 CounterBasedGauge64
	MAX-ACCESS  read-only
	STATUS      current
	DESCRIPTION
	"Table entry attribute for ethernetShuntMplsPackets"
	::={ethernetShuntMplsPacketsLevelEntry 3}

ethernetShuntMplsPacketsLevelMax OBJECT-TYPE
	SYNTAX	 CounterBasedGauge64
	MAX-ACCESS  read-only
	STATUS      current
	DESCRIPTION
	"Table entry attribute for ethernetShuntMplsPackets"
	::={ethernetShuntMplsPacketsLevelEntry 4}


ethernetShuntMplsBytes	OBJECT IDENTIFIER ::={ethernet 25}

ethernetShuntMplsBytesVal	OBJECT-TYPE
	SYNTAX	 Counter64
	MAX-ACCESS read-only
	STATUS current
	DESCRIPTION "Shunted bytes (MPLS)"

	::={ethernetShuntMplsBytes 1}

ethernetShuntMplsBytesMom	OBJECT-TYPE
	SYNTAX	 CounterBasedGauge64
	MAX-ACCESS read-only
	STATUS current
	DESCRIPTION "Shunted bytes (MPLS)"

	::={ethernetShuntMplsBytes 2}

ethernetShuntMplsBytesMax	OBJECT-TYPE
	SYNTAX	 CounterBasedGauge64
	MAX-ACCESS read-only
	STATUS current
	DESCRIPTION "Shunted bytes (MPLS)"

	::={ethernetShuntMplsBytes 3}

ethernetShuntMplsBytesLevelTable OBJECT-TYPE
	SYNTAX      SEQUENCE OF EthernetShuntMplsBytesLevelEntry
	MAX-ACCESS  not-accessible
	STATUS      current
	DESCRIPTION
	"Table for ethernetShuntMplsBytes"
	::={ethernetShuntMplsBytes 4}

ethernetShuntMplsBytesLevelEntry OBJECT-TYPE
	SYNTAX      EthernetShuntMplsBytesLevelEntry
	MAX-ACCESS  not-accessible
	STATUS      current
	DESCRIPTION
	"Table entry for ethernetShuntMplsBytes"
	INDEX { ethernetShuntMplsBytesLevelName }
	::={ethernetShuntMplsBytesLevelTable 1}

EthernetShuntMplsBytesLevelEntry ::=
	SEQUENCE {
		ethernetShuntMplsBytesLevelName	DisplayString,
		ethernetShuntMplsBytesLevelVal	Counter64,
		ethernetShuntMplsBytesLevelMom	CounterBasedGauge64,
		ethernetShuntMplsBytesLevelMax	CounterBasedGauge64
	}

ethernetShuntMplsBytesLevelName OBJECT-TYPE
	SYNTAX      DisplayString
	MAX-ACCESS  not-accessible
	STATUS      current
	DESCRIPTION
	"Table entry display string for ethernetShuntMplsBytes"
	::={ethernetShuntMplsBytesLevelEntry 1}

ethernetShuntMplsBytesLevelVal OBJECT-TYPE
	SYNTAX	 Counter64
	MAX-ACCESS  read-only
	STATUS      current
	DESCRIPTION
	"Table entry attribute for ethernetShuntMplsBytes"
	::={ethernetShuntMplsBytesLevelEntry 2}

ethernetShuntMplsBytesLevelMom OBJECT-TYPE
	SYNTAX	 CounterBasedGauge64
	MAX-ACCESS  read-only
	STATUS      current
	DESCRIPTION
	"Table entry attribute for ethernetShuntMplsBytes"
	::={ethernetShuntMplsBytesLevelEntry 3}

ethernetShuntMplsBytesLevelMax OBJECT-TYPE
	SYNTAX	 CounterBasedGauge64
	MAX-ACCESS  read-only
	STATUS      current
	DESCRIPTION
	"Table entry attribute for ethernetShuntMplsBytes"
	::={ethernetShuntMplsBytesLevelEntry 4}


ethernetShuntEoMplsPackets	OBJECT IDENTIFIER ::={ethernet 26}

ethernetShuntEoMplsPacketsVal	OBJECT-TYPE
	SYNTAX	 Counter64
	MAX-ACCESS read-only
	STATUS current
	DESCRIPTION "Shunted packets (EoMPLS)"

	::={ethernetShuntEoMplsPackets 1}

ethernetShuntEoMplsPacketsMom	OBJECT-TYPE
	SYNTAX	 CounterBasedGauge64
	MAX-ACCESS read-only
	STATUS current
	DESCRIPTION "Shunted packets (EoMPLS)"

	::={ethernetShuntEoMplsPackets 2}

ethernetShuntEoMplsPacketsMax	OBJECT-TYPE
	SYNTAX	 CounterBasedGauge64
	MAX-ACCESS read-only
	STATUS current
	DESCRIPTION "Shunted packets (EoMPLS)"

	::={ethernetShuntEoMplsPackets 3}

ethernetShuntEoMplsPacketsLevelTable OBJECT-TYPE
	SYNTAX      SEQUENCE OF EthernetShuntEoMplsPacketsLevelEntry
	MAX-ACCESS  not-accessible
	STATUS      current
	DESCRIPTION
	"Table for ethernetShuntEoMplsPackets"
	::={ethernetShuntEoMplsPackets 4}

ethernetShuntEoMplsPacketsLevelEntry OBJECT-TYPE
	SYNTAX      EthernetShuntEoMplsPacketsLevelEntry
	MAX-ACCESS  not-accessible
	STATUS      current
	DESCRIPTION
	"Table entry for ethernetShuntEoMplsPackets"
	INDEX { ethernetShuntEoMplsPacketsLevelName }
	::={ethernetShuntEoMplsPacketsLevelTable 1}

EthernetShuntEoMplsPacketsLevelEntry ::=
	SEQUENCE {
		ethernetShuntEoMplsPacketsLevelName	DisplayString,
		ethernetShuntEoMplsPacketsLevelVal	Counter64,
		ethernetShuntEoMplsPacketsLevelMom	CounterBasedGauge64,
		ethernetShuntEoMplsPacketsLevelMax	CounterBasedGauge64
	}

ethernetShuntEoMplsPacketsLevelName OBJECT-TYPE
	SYNTAX      DisplayString
	MAX-ACCESS  not-accessible
	STATUS      current
	DESCRIPTION
	"Table entry display string for ethernetShuntEoMplsPackets"
	::={ethernetShuntEoMplsPacketsLevelEntry 1}

ethernetShuntEoMplsPacketsLevelVal OBJECT-TYPE
	SYNTAX	 Counter64
	MAX-ACCESS  read-only
	STATUS      current
	DESCRIPTION
	"Table entry attribute for ethernetShuntEoMplsPackets"
	::={ethernetShuntEoMplsPacketsLevelEntry 2}

ethernetShuntEoMplsPacketsLevelMom OBJECT-TYPE
	SYNTAX	 CounterBasedGauge64
	MAX-ACCESS  read-only
	STATUS      current
	DESCRIPTION
	"Table entry attribute for ethernetShuntEoMplsPackets"
	::={ethernetShuntEoMplsPacketsLevelEntry 3}

ethernetShuntEoMplsPacketsLevelMax OBJECT-TYPE
	SYNTAX	 CounterBasedGauge64
	MAX-ACCESS  read-only
	STATUS      current
	DESCRIPTION
	"Table entry attribute for ethernetShuntEoMplsPackets"
	::={ethernetShuntEoMplsPacketsLevelEntry 4}


ethernetShuntEoMplsBytes	OBJECT IDENTIFIER ::={ethernet 27}

ethernetShuntEoMplsBytesVal	OBJECT-TYPE
	SYNTAX	 Counter64
	MAX-ACCESS read-only
	STATUS current
	DESCRIPTION "Shunted bytes (EoMPLS)"

	::={ethernetShuntEoMplsBytes 1}

ethernetShuntEoMplsBytesMom	OBJECT-TYPE
	SYNTAX	 CounterBasedGauge64
	MAX-ACCESS read-only
	STATUS current
	DESCRIPTION "Shunted bytes (EoMPLS)"

	::={ethernetShuntEoMplsBytes 2}

ethernetShuntEoMplsBytesMax	OBJECT-TYPE
	SYNTAX	 CounterBasedGauge64
	MAX-ACCESS read-only
	STATUS current
	DESCRIPTION "Shunted bytes (EoMPLS)"

	::={ethernetShuntEoMplsBytes 3}

ethernetShuntEoMplsBytesLevelTable OBJECT-TYPE
	SYNTAX      SEQUENCE OF EthernetShuntEoMplsBytesLevelEntry
	MAX-ACCESS  not-accessible
	STATUS      current
	DESCRIPTION
	"Table for ethernetShuntEoMplsBytes"
	::={ethernetShuntEoMplsBytes 4}

ethernetShuntEoMplsBytesLevelEntry OBJECT-TYPE
	SYNTAX      EthernetShuntEoMplsBytesLevelEntry
	MAX-ACCESS  not-accessible
	STATUS      current
	DESCRIPTION
	"Table entry for ethernetShuntEoMplsBytes"
	INDEX { ethernetShuntEoMplsBytesLevelName }
	::={ethernetShuntEoMplsBytesLevelTable 1}

EthernetShuntEoMplsBytesLevelEntry ::=
	SEQUENCE {
		ethernetShuntEoMplsBytesLevelName	DisplayString,
		ethernetShuntEoMplsBytesLevelVal	Counter64,
		ethernetShuntEoMplsBytesLevelMom	CounterBasedGauge64,
		ethernetShuntEoMplsBytesLevelMax	CounterBasedGauge64
	}

ethernetShuntEoMplsBytesLevelName OBJECT-TYPE
	SYNTAX      DisplayString
	MAX-ACCESS  not-accessible
	STATUS      current
	DESCRIPTION
	"Table entry display string for ethernetShuntEoMplsBytes"
	::={ethernetShuntEoMplsBytesLevelEntry 1}

ethernetShuntEoMplsBytesLevelVal OBJECT-TYPE
	SYNTAX	 Counter64
	MAX-ACCESS  read-only
	STATUS      current
	DESCRIPTION
	"Table entry attribute for ethernetShuntEoMplsBytes"
	::={ethernetShuntEoMplsBytesLevelEntry 2}

ethernetShuntEoMplsBytesLevelMom OBJECT-TYPE
	SYNTAX	 CounterBasedGauge64
	MAX-ACCESS  read-only
	STATUS      current
	DESCRIPTION
	"Table entry attribute for ethernetShuntEoMplsBytes"
	::={ethernetShuntEoMplsBytesLevelEntry 3}

ethernetShuntEoMplsBytesLevelMax OBJECT-TYPE
	SYNTAX	 CounterBasedGauge64
	MAX-ACCESS  read-only
	STATUS      current
	DESCRIPTION
	"Table entry attribute for ethernetShuntEoMplsBytes"
	::={ethernetShuntEoMplsBytesLevelEntry 4}


ethernetShuntDot1qPackets	OBJECT IDENTIFIER ::={ethernet 28}

ethernetShuntDot1qPacketsVal	OBJECT-TYPE
	SYNTAX	 Counter64
	MAX-ACCESS read-only
	STATUS current
	DESCRIPTION "Shunted packets (Dot1q)"

	::={ethernetShuntDot1qPackets 1}

ethernetShuntDot1qPacketsMom	OBJECT-TYPE
	SYNTAX	 CounterBasedGauge64
	MAX-ACCESS read-only
	STATUS current
	DESCRIPTION "Shunted packets (Dot1q)"

	::={ethernetShuntDot1qPackets 2}

ethernetShuntDot1qPacketsMax	OBJECT-TYPE
	SYNTAX	 CounterBasedGauge64
	MAX-ACCESS read-only
	STATUS current
	DESCRIPTION "Shunted packets (Dot1q)"

	::={ethernetShuntDot1qPackets 3}

ethernetShuntDot1qPacketsLevelTable OBJECT-TYPE
	SYNTAX      SEQUENCE OF EthernetShuntDot1qPacketsLevelEntry
	MAX-ACCESS  not-accessible
	STATUS      current
	DESCRIPTION
	"Table for ethernetShuntDot1qPackets"
	::={ethernetShuntDot1qPackets 4}

ethernetShuntDot1qPacketsLevelEntry OBJECT-TYPE
	SYNTAX      EthernetShuntDot1qPacketsLevelEntry
	MAX-ACCESS  not-accessible
	STATUS      current
	DESCRIPTION
	"Table entry for ethernetShuntDot1qPackets"
	INDEX { ethernetShuntDot1qPacketsLevelName }
	::={ethernetShuntDot1qPacketsLevelTable 1}

EthernetShuntDot1qPacketsLevelEntry ::=
	SEQUENCE {
		ethernetShuntDot1qPacketsLevelName	DisplayString,
		ethernetShuntDot1qPacketsLevelVal	Counter64,
		ethernetShuntDot1qPacketsLevelMom	CounterBasedGauge64,
		ethernetShuntDot1qPacketsLevelMax	CounterBasedGauge64
	}

ethernetShuntDot1qPacketsLevelName OBJECT-TYPE
	SYNTAX      DisplayString
	MAX-ACCESS  not-accessible
	STATUS      current
	DESCRIPTION
	"Table entry display string for ethernetShuntDot1qPackets"
	::={ethernetShuntDot1qPacketsLevelEntry 1}

ethernetShuntDot1qPacketsLevelVal OBJECT-TYPE
	SYNTAX	 Counter64
	MAX-ACCESS  read-only
	STATUS      current
	DESCRIPTION
	"Table entry attribute for ethernetShuntDot1qPackets"
	::={ethernetShuntDot1qPacketsLevelEntry 2}

ethernetShuntDot1qPacketsLevelMom OBJECT-TYPE
	SYNTAX	 CounterBasedGauge64
	MAX-ACCESS  read-only
	STATUS      current
	DESCRIPTION
	"Table entry attribute for ethernetShuntDot1qPackets"
	::={ethernetShuntDot1qPacketsLevelEntry 3}

ethernetShuntDot1qPacketsLevelMax OBJECT-TYPE
	SYNTAX	 CounterBasedGauge64
	MAX-ACCESS  read-only
	STATUS      current
	DESCRIPTION
	"Table entry attribute for ethernetShuntDot1qPackets"
	::={ethernetShuntDot1qPacketsLevelEntry 4}


ethernetShuntDot1qBytes	OBJECT IDENTIFIER ::={ethernet 29}

ethernetShuntDot1qBytesVal	OBJECT-TYPE
	SYNTAX	 Counter64
	MAX-ACCESS read-only
	STATUS current
	DESCRIPTION "Shunted bytes (Dot1q)"

	::={ethernetShuntDot1qBytes 1}

ethernetShuntDot1qBytesMom	OBJECT-TYPE
	SYNTAX	 CounterBasedGauge64
	MAX-ACCESS read-only
	STATUS current
	DESCRIPTION "Shunted bytes (Dot1q)"

	::={ethernetShuntDot1qBytes 2}

ethernetShuntDot1qBytesMax	OBJECT-TYPE
	SYNTAX	 CounterBasedGauge64
	MAX-ACCESS read-only
	STATUS current
	DESCRIPTION "Shunted bytes (Dot1q)"

	::={ethernetShuntDot1qBytes 3}

ethernetShuntDot1qBytesLevelTable OBJECT-TYPE
	SYNTAX      SEQUENCE OF EthernetShuntDot1qBytesLevelEntry
	MAX-ACCESS  not-accessible
	STATUS      current
	DESCRIPTION
	"Table for ethernetShuntDot1qBytes"
	::={ethernetShuntDot1qBytes 4}

ethernetShuntDot1qBytesLevelEntry OBJECT-TYPE
	SYNTAX      EthernetShuntDot1qBytesLevelEntry
	MAX-ACCESS  not-accessible
	STATUS      current
	DESCRIPTION
	"Table entry for ethernetShuntDot1qBytes"
	INDEX { ethernetShuntDot1qBytesLevelName }
	::={ethernetShuntDot1qBytesLevelTable 1}

EthernetShuntDot1qBytesLevelEntry ::=
	SEQUENCE {
		ethernetShuntDot1qBytesLevelName	DisplayString,
		ethernetShuntDot1qBytesLevelVal	Counter64,
		ethernetShuntDot1qBytesLevelMom	CounterBasedGauge64,
		ethernetShuntDot1qBytesLevelMax	CounterBasedGauge64
	}

ethernetShuntDot1qBytesLevelName OBJECT-TYPE
	SYNTAX      DisplayString
	MAX-ACCESS  not-accessible
	STATUS      current
	DESCRIPTION
	"Table entry display string for ethernetShuntDot1qBytes"
	::={ethernetShuntDot1qBytesLevelEntry 1}

ethernetShuntDot1qBytesLevelVal OBJECT-TYPE
	SYNTAX	 Counter64
	MAX-ACCESS  read-only
	STATUS      current
	DESCRIPTION
	"Table entry attribute for ethernetShuntDot1qBytes"
	::={ethernetShuntDot1qBytesLevelEntry 2}

ethernetShuntDot1qBytesLevelMom OBJECT-TYPE
	SYNTAX	 CounterBasedGauge64
	MAX-ACCESS  read-only
	STATUS      current
	DESCRIPTION
	"Table entry attribute for ethernetShuntDot1qBytes"
	::={ethernetShuntDot1qBytesLevelEntry 3}

ethernetShuntDot1qBytesLevelMax OBJECT-TYPE
	SYNTAX	 CounterBasedGauge64
	MAX-ACCESS  read-only
	STATUS      current
	DESCRIPTION
	"Table entry attribute for ethernetShuntDot1qBytes"
	::={ethernetShuntDot1qBytesLevelEntry 4}


ethernetCountBytesIPv4IPv6	OBJECT IDENTIFIER ::={ethernet 30}

ethernetCountBytesIPv4IPv6Val	OBJECT-TYPE
	SYNTAX	 Counter64
	MAX-ACCESS read-only
	STATUS current
	DESCRIPTION "Ethernet bytes (IPv4 and IPv6)"

	::={ethernetCountBytesIPv4IPv6 1}

ethernetCountBytesIPv4IPv6Mom	OBJECT-TYPE
	SYNTAX	 CounterBasedGauge64
	MAX-ACCESS read-only
	STATUS current
	DESCRIPTION "Ethernet bytes (IPv4 and IPv6)"

	::={ethernetCountBytesIPv4IPv6 2}

ethernetCountBytesIPv4IPv6Max	OBJECT-TYPE
	SYNTAX	 CounterBasedGauge64
	MAX-ACCESS read-only
	STATUS current
	DESCRIPTION "Ethernet bytes (IPv4 and IPv6)"

	::={ethernetCountBytesIPv4IPv6 3}

ethernetCountBytesIPv4IPv6LevelTable OBJECT-TYPE
	SYNTAX      SEQUENCE OF EthernetCountBytesIPv4IPv6LevelEntry
	MAX-ACCESS  not-accessible
	STATUS      current
	DESCRIPTION
	"Table for ethernetCountBytesIPv4IPv6"
	::={ethernetCountBytesIPv4IPv6 4}

ethernetCountBytesIPv4IPv6LevelEntry OBJECT-TYPE
	SYNTAX      EthernetCountBytesIPv4IPv6LevelEntry
	MAX-ACCESS  not-accessible
	STATUS      current
	DESCRIPTION
	"Table entry for ethernetCountBytesIPv4IPv6"
	INDEX { ethernetCountBytesIPv4IPv6LevelName }
	::={ethernetCountBytesIPv4IPv6LevelTable 1}

EthernetCountBytesIPv4IPv6LevelEntry ::=
	SEQUENCE {
		ethernetCountBytesIPv4IPv6LevelName	DisplayString,
		ethernetCountBytesIPv4IPv6LevelVal	Counter64,
		ethernetCountBytesIPv4IPv6LevelMom	CounterBasedGauge64,
		ethernetCountBytesIPv4IPv6LevelMax	CounterBasedGauge64
	}

ethernetCountBytesIPv4IPv6LevelName OBJECT-TYPE
	SYNTAX      DisplayString
	MAX-ACCESS  not-accessible
	STATUS      current
	DESCRIPTION
	"Table entry display string for ethernetCountBytesIPv4IPv6"
	::={ethernetCountBytesIPv4IPv6LevelEntry 1}

ethernetCountBytesIPv4IPv6LevelVal OBJECT-TYPE
	SYNTAX	 Counter64
	MAX-ACCESS  read-only
	STATUS      current
	DESCRIPTION
	"Table entry attribute for ethernetCountBytesIPv4IPv6"
	::={ethernetCountBytesIPv4IPv6LevelEntry 2}

ethernetCountBytesIPv4IPv6LevelMom OBJECT-TYPE
	SYNTAX	 CounterBasedGauge64
	MAX-ACCESS  read-only
	STATUS      current
	DESCRIPTION
	"Table entry attribute for ethernetCountBytesIPv4IPv6"
	::={ethernetCountBytesIPv4IPv6LevelEntry 3}

ethernetCountBytesIPv4IPv6LevelMax OBJECT-TYPE
	SYNTAX	 CounterBasedGauge64
	MAX-ACCESS  read-only
	STATUS      current
	DESCRIPTION
	"Table entry attribute for ethernetCountBytesIPv4IPv6"
	::={ethernetCountBytesIPv4IPv6LevelEntry 4}


ethernetUniqueLinkLevelHeadersStored	OBJECT IDENTIFIER ::={ethernet 31}

ethernetUniqueLinkLevelHeadersStoredVal	OBJECT-TYPE
	SYNTAX	 CounterBasedGauge64
	MAX-ACCESS read-only
	STATUS current
	DESCRIPTION "Number of unique link-level headers stored"

	::={ethernetUniqueLinkLevelHeadersStored 1}

ethernetUniqueLinkLevelHeadersStoredMax	OBJECT-TYPE
	SYNTAX	 CounterBasedGauge64
	MAX-ACCESS read-only
	STATUS current
	DESCRIPTION "Number of unique link-level headers stored"

	::={ethernetUniqueLinkLevelHeadersStored 3}

ethernetUniqueLinkLevelHeadersStoredLevelTable OBJECT-TYPE
	SYNTAX      SEQUENCE OF EthernetUniqueLinkLevelHeadersStoredLevelEntry
	MAX-ACCESS  not-accessible
	STATUS      current
	DESCRIPTION
	"Table for ethernetUniqueLinkLevelHeadersStored"
	::={ethernetUniqueLinkLevelHeadersStored 4}

ethernetUniqueLinkLevelHeadersStoredLevelEntry OBJECT-TYPE
	SYNTAX      EthernetUniqueLinkLevelHeadersStoredLevelEntry
	MAX-ACCESS  not-accessible
	STATUS      current
	DESCRIPTION
	"Table entry for ethernetUniqueLinkLevelHeadersStored"
	INDEX { ethernetUniqueLinkLevelHeadersStoredLevelName }
	::={ethernetUniqueLinkLevelHeadersStoredLevelTable 1}

EthernetUniqueLinkLevelHeadersStoredLevelEntry ::=
	SEQUENCE {
		ethernetUniqueLinkLevelHeadersStoredLevelName	DisplayString,
		ethernetUniqueLinkLevelHeadersStoredLevelVal	CounterBasedGauge64,
		ethernetUniqueLinkLevelHeadersStoredLevelMax	CounterBasedGauge64
	}

ethernetUniqueLinkLevelHeadersStoredLevelName OBJECT-TYPE
	SYNTAX      DisplayString
	MAX-ACCESS  not-accessible
	STATUS      current
	DESCRIPTION
	"Table entry display string for ethernetUniqueLinkLevelHeadersStored"
	::={ethernetUniqueLinkLevelHeadersStoredLevelEntry 1}

ethernetUniqueLinkLevelHeadersStoredLevelVal OBJECT-TYPE
	SYNTAX	 CounterBasedGauge64
	MAX-ACCESS  read-only
	STATUS      current
	DESCRIPTION
	"Table entry attribute for ethernetUniqueLinkLevelHeadersStored"
	::={ethernetUniqueLinkLevelHeadersStoredLevelEntry 2}

ethernetUniqueLinkLevelHeadersStoredLevelMax OBJECT-TYPE
	SYNTAX	 CounterBasedGauge64
	MAX-ACCESS  read-only
	STATUS      current
	DESCRIPTION
	"Table entry attribute for ethernetUniqueLinkLevelHeadersStored"
	::={ethernetUniqueLinkLevelHeadersStoredLevelEntry 4}


ethernetUniqueLinkLevelHeaderOversized	OBJECT IDENTIFIER ::={ethernet 32}

ethernetUniqueLinkLevelHeaderOversizedVal	OBJECT-TYPE
	SYNTAX	 Counter64
	MAX-ACCESS read-only
	STATUS current
	DESCRIPTION "Not stored link-level header (oversized)"

	::={ethernetUniqueLinkLevelHeaderOversized 1}

ethernetUniqueLinkLevelHeaderOversizedMom	OBJECT-TYPE
	SYNTAX	 CounterBasedGauge64
	MAX-ACCESS read-only
	STATUS current
	DESCRIPTION "Not stored link-level header (oversized)"

	::={ethernetUniqueLinkLevelHeaderOversized 2}

ethernetUniqueLinkLevelHeaderOversizedMax	OBJECT-TYPE
	SYNTAX	 CounterBasedGauge64
	MAX-ACCESS read-only
	STATUS current
	DESCRIPTION "Not stored link-level header (oversized)"

	::={ethernetUniqueLinkLevelHeaderOversized 3}

ethernetUniqueLinkLevelHeaderOversizedLevelTable OBJECT-TYPE
	SYNTAX      SEQUENCE OF EthernetUniqueLinkLevelHeaderOversizedLevelEntry
	MAX-ACCESS  not-accessible
	STATUS      current
	DESCRIPTION
	"Table for ethernetUniqueLinkLevelHeaderOversized"
	::={ethernetUniqueLinkLevelHeaderOversized 4}

ethernetUniqueLinkLevelHeaderOversizedLevelEntry OBJECT-TYPE
	SYNTAX      EthernetUniqueLinkLevelHeaderOversizedLevelEntry
	MAX-ACCESS  not-accessible
	STATUS      current
	DESCRIPTION
	"Table entry for ethernetUniqueLinkLevelHeaderOversized"
	INDEX { ethernetUniqueLinkLevelHeaderOversizedLevelName }
	::={ethernetUniqueLinkLevelHeaderOversizedLevelTable 1}

EthernetUniqueLinkLevelHeaderOversizedLevelEntry ::=
	SEQUENCE {
		ethernetUniqueLinkLevelHeaderOversizedLevelName	DisplayString,
		ethernetUniqueLinkLevelHeaderOversizedLevelVal	Counter64,
		ethernetUniqueLinkLevelHeaderOversizedLevelMom	CounterBasedGauge64,
		ethernetUniqueLinkLevelHeaderOversizedLevelMax	CounterBasedGauge64
	}

ethernetUniqueLinkLevelHeaderOversizedLevelName OBJECT-TYPE
	SYNTAX      DisplayString
	MAX-ACCESS  not-accessible
	STATUS      current
	DESCRIPTION
	"Table entry display string for ethernetUniqueLinkLevelHeaderOversized"
	::={ethernetUniqueLinkLevelHeaderOversizedLevelEntry 1}

ethernetUniqueLinkLevelHeaderOversizedLevelVal OBJECT-TYPE
	SYNTAX	 Counter64
	MAX-ACCESS  read-only
	STATUS      current
	DESCRIPTION
	"Table entry attribute for ethernetUniqueLinkLevelHeaderOversized"
	::={ethernetUniqueLinkLevelHeaderOversizedLevelEntry 2}

ethernetUniqueLinkLevelHeaderOversizedLevelMom OBJECT-TYPE
	SYNTAX	 CounterBasedGauge64
	MAX-ACCESS  read-only
	STATUS      current
	DESCRIPTION
	"Table entry attribute for ethernetUniqueLinkLevelHeaderOversized"
	::={ethernetUniqueLinkLevelHeaderOversizedLevelEntry 3}

ethernetUniqueLinkLevelHeaderOversizedLevelMax OBJECT-TYPE
	SYNTAX	 CounterBasedGauge64
	MAX-ACCESS  read-only
	STATUS      current
	DESCRIPTION
	"Table entry attribute for ethernetUniqueLinkLevelHeaderOversized"
	::={ethernetUniqueLinkLevelHeaderOversizedLevelEntry 4}


ethernetUniqueLinkLevelHeaderOutOfEntries	OBJECT IDENTIFIER ::={ethernet 33}

ethernetUniqueLinkLevelHeaderOutOfEntriesVal	OBJECT-TYPE
	SYNTAX	 Counter64
	MAX-ACCESS read-only
	STATUS current
	DESCRIPTION "Not stored link-level header (out of entries)"

	::={ethernetUniqueLinkLevelHeaderOutOfEntries 1}

ethernetUniqueLinkLevelHeaderOutOfEntriesMom	OBJECT-TYPE
	SYNTAX	 CounterBasedGauge64
	MAX-ACCESS read-only
	STATUS current
	DESCRIPTION "Not stored link-level header (out of entries)"

	::={ethernetUniqueLinkLevelHeaderOutOfEntries 2}

ethernetUniqueLinkLevelHeaderOutOfEntriesMax	OBJECT-TYPE
	SYNTAX	 CounterBasedGauge64
	MAX-ACCESS read-only
	STATUS current
	DESCRIPTION "Not stored link-level header (out of entries)"

	::={ethernetUniqueLinkLevelHeaderOutOfEntries 3}

ethernetUniqueLinkLevelHeaderOutOfEntriesLevelTable OBJECT-TYPE
	SYNTAX      SEQUENCE OF EthernetUniqueLinkLevelHeaderOutOfEntriesLevelEntry
	MAX-ACCESS  not-accessible
	STATUS      current
	DESCRIPTION
	"Table for ethernetUniqueLinkLevelHeaderOutOfEntries"
	::={ethernetUniqueLinkLevelHeaderOutOfEntries 4}

ethernetUniqueLinkLevelHeaderOutOfEntriesLevelEntry OBJECT-TYPE
	SYNTAX      EthernetUniqueLinkLevelHeaderOutOfEntriesLevelEntry
	MAX-ACCESS  not-accessible
	STATUS      current
	DESCRIPTION
	"Table entry for ethernetUniqueLinkLevelHeaderOutOfEntries"
	INDEX { ethernetUniqueLinkLevelHeaderOutOfEntriesLevelName }
	::={ethernetUniqueLinkLevelHeaderOutOfEntriesLevelTable 1}

EthernetUniqueLinkLevelHeaderOutOfEntriesLevelEntry ::=
	SEQUENCE {
		ethernetUniqueLinkLevelHeaderOutOfEntriesLevelName	DisplayString,
		ethernetUniqueLinkLevelHeaderOutOfEntriesLevelVal	Counter64,
		ethernetUniqueLinkLevelHeaderOutOfEntriesLevelMom	CounterBasedGauge64,
		ethernetUniqueLinkLevelHeaderOutOfEntriesLevelMax	CounterBasedGauge64
	}

ethernetUniqueLinkLevelHeaderOutOfEntriesLevelName OBJECT-TYPE
	SYNTAX      DisplayString
	MAX-ACCESS  not-accessible
	STATUS      current
	DESCRIPTION
	"Table entry display string for ethernetUniqueLinkLevelHeaderOutOfEntries"
	::={ethernetUniqueLinkLevelHeaderOutOfEntriesLevelEntry 1}

ethernetUniqueLinkLevelHeaderOutOfEntriesLevelVal OBJECT-TYPE
	SYNTAX	 Counter64
	MAX-ACCESS  read-only
	STATUS      current
	DESCRIPTION
	"Table entry attribute for ethernetUniqueLinkLevelHeaderOutOfEntries"
	::={ethernetUniqueLinkLevelHeaderOutOfEntriesLevelEntry 2}

ethernetUniqueLinkLevelHeaderOutOfEntriesLevelMom OBJECT-TYPE
	SYNTAX	 CounterBasedGauge64
	MAX-ACCESS  read-only
	STATUS      current
	DESCRIPTION
	"Table entry attribute for ethernetUniqueLinkLevelHeaderOutOfEntries"
	::={ethernetUniqueLinkLevelHeaderOutOfEntriesLevelEntry 3}

ethernetUniqueLinkLevelHeaderOutOfEntriesLevelMax OBJECT-TYPE
	SYNTAX	 CounterBasedGauge64
	MAX-ACCESS  read-only
	STATUS      current
	DESCRIPTION
	"Table entry attribute for ethernetUniqueLinkLevelHeaderOutOfEntries"
	::={ethernetUniqueLinkLevelHeaderOutOfEntriesLevelEntry 4}


ethernetUniqueLinkLevelHeaderLargestSeen	OBJECT IDENTIFIER ::={ethernet 34}

ethernetUniqueLinkLevelHeaderLargestSeenVal	OBJECT-TYPE
	SYNTAX	 CounterBasedGauge64
	MAX-ACCESS read-only
	STATUS current
	DESCRIPTION "Largest seen link-level header"

	::={ethernetUniqueLinkLevelHeaderLargestSeen 1}

ethernetUniqueLinkLevelHeaderLargestSeenMax	OBJECT-TYPE
	SYNTAX	 CounterBasedGauge64
	MAX-ACCESS read-only
	STATUS current
	DESCRIPTION "Largest seen link-level header"

	::={ethernetUniqueLinkLevelHeaderLargestSeen 3}

ethernetUniqueLinkLevelHeaderLargestSeenLevelTable OBJECT-TYPE
	SYNTAX      SEQUENCE OF EthernetUniqueLinkLevelHeaderLargestSeenLevelEntry
	MAX-ACCESS  not-accessible
	STATUS      current
	DESCRIPTION
	"Table for ethernetUniqueLinkLevelHeaderLargestSeen"
	::={ethernetUniqueLinkLevelHeaderLargestSeen 4}

ethernetUniqueLinkLevelHeaderLargestSeenLevelEntry OBJECT-TYPE
	SYNTAX      EthernetUniqueLinkLevelHeaderLargestSeenLevelEntry
	MAX-ACCESS  not-accessible
	STATUS      current
	DESCRIPTION
	"Table entry for ethernetUniqueLinkLevelHeaderLargestSeen"
	INDEX { ethernetUniqueLinkLevelHeaderLargestSeenLevelName }
	::={ethernetUniqueLinkLevelHeaderLargestSeenLevelTable 1}

EthernetUniqueLinkLevelHeaderLargestSeenLevelEntry ::=
	SEQUENCE {
		ethernetUniqueLinkLevelHeaderLargestSeenLevelName	DisplayString,
		ethernetUniqueLinkLevelHeaderLargestSeenLevelVal	CounterBasedGauge64,
		ethernetUniqueLinkLevelHeaderLargestSeenLevelMax	CounterBasedGauge64
	}

ethernetUniqueLinkLevelHeaderLargestSeenLevelName OBJECT-TYPE
	SYNTAX      DisplayString
	MAX-ACCESS  not-accessible
	STATUS      current
	DESCRIPTION
	"Table entry display string for ethernetUniqueLinkLevelHeaderLargestSeen"
	::={ethernetUniqueLinkLevelHeaderLargestSeenLevelEntry 1}

ethernetUniqueLinkLevelHeaderLargestSeenLevelVal OBJECT-TYPE
	SYNTAX	 CounterBasedGauge64
	MAX-ACCESS  read-only
	STATUS      current
	DESCRIPTION
	"Table entry attribute for ethernetUniqueLinkLevelHeaderLargestSeen"
	::={ethernetUniqueLinkLevelHeaderLargestSeenLevelEntry 2}

ethernetUniqueLinkLevelHeaderLargestSeenLevelMax OBJECT-TYPE
	SYNTAX	 CounterBasedGauge64
	MAX-ACCESS  read-only
	STATUS      current
	DESCRIPTION
	"Table entry attribute for ethernetUniqueLinkLevelHeaderLargestSeen"
	::={ethernetUniqueLinkLevelHeaderLargestSeenLevelEntry 4}


ethernetFlowsyncPacketsOnNonFlowsyncChannels	OBJECT IDENTIFIER ::={ethernet 35}

ethernetFlowsyncPacketsOnNonFlowsyncChannelsVal	OBJECT-TYPE
	SYNTAX	 Counter64
	MAX-ACCESS read-only
	STATUS current
	DESCRIPTION "Flowsync packets received on non-flowsync interface"

	::={ethernetFlowsyncPacketsOnNonFlowsyncChannels 1}

ethernetFlowsyncPacketsOnNonFlowsyncChannelsMom	OBJECT-TYPE
	SYNTAX	 CounterBasedGauge64
	MAX-ACCESS read-only
	STATUS current
	DESCRIPTION "Flowsync packets received on non-flowsync interface"

	::={ethernetFlowsyncPacketsOnNonFlowsyncChannels 2}

ethernetFlowsyncPacketsOnNonFlowsyncChannelsMax	OBJECT-TYPE
	SYNTAX	 CounterBasedGauge64
	MAX-ACCESS read-only
	STATUS current
	DESCRIPTION "Flowsync packets received on non-flowsync interface"

	::={ethernetFlowsyncPacketsOnNonFlowsyncChannels 3}

ethernetFlowsyncPacketsOnNonFlowsyncChannelsLevelTable OBJECT-TYPE
	SYNTAX      SEQUENCE OF EthernetFlowsyncPacketsOnNonFlowsyncChannelsLevelEntry
	MAX-ACCESS  not-accessible
	STATUS      current
	DESCRIPTION
	"Table for ethernetFlowsyncPacketsOnNonFlowsyncChannels"
	::={ethernetFlowsyncPacketsOnNonFlowsyncChannels 4}

ethernetFlowsyncPacketsOnNonFlowsyncChannelsLevelEntry OBJECT-TYPE
	SYNTAX      EthernetFlowsyncPacketsOnNonFlowsyncChannelsLevelEntry
	MAX-ACCESS  not-accessible
	STATUS      current
	DESCRIPTION
	"Table entry for ethernetFlowsyncPacketsOnNonFlowsyncChannels"
	INDEX { ethernetFlowsyncPacketsOnNonFlowsyncChannelsLevelName }
	::={ethernetFlowsyncPacketsOnNonFlowsyncChannelsLevelTable 1}

EthernetFlowsyncPacketsOnNonFlowsyncChannelsLevelEntry ::=
	SEQUENCE {
		ethernetFlowsyncPacketsOnNonFlowsyncChannelsLevelName	DisplayString,
		ethernetFlowsyncPacketsOnNonFlowsyncChannelsLevelVal	Counter64,
		ethernetFlowsyncPacketsOnNonFlowsyncChannelsLevelMom	CounterBasedGauge64,
		ethernetFlowsyncPacketsOnNonFlowsyncChannelsLevelMax	CounterBasedGauge64
	}

ethernetFlowsyncPacketsOnNonFlowsyncChannelsLevelName OBJECT-TYPE
	SYNTAX      DisplayString
	MAX-ACCESS  not-accessible
	STATUS      current
	DESCRIPTION
	"Table entry display string for ethernetFlowsyncPacketsOnNonFlowsyncChannels"
	::={ethernetFlowsyncPacketsOnNonFlowsyncChannelsLevelEntry 1}

ethernetFlowsyncPacketsOnNonFlowsyncChannelsLevelVal OBJECT-TYPE
	SYNTAX	 Counter64
	MAX-ACCESS  read-only
	STATUS      current
	DESCRIPTION
	"Table entry attribute for ethernetFlowsyncPacketsOnNonFlowsyncChannels"
	::={ethernetFlowsyncPacketsOnNonFlowsyncChannelsLevelEntry 2}

ethernetFlowsyncPacketsOnNonFlowsyncChannelsLevelMom OBJECT-TYPE
	SYNTAX	 CounterBasedGauge64
	MAX-ACCESS  read-only
	STATUS      current
	DESCRIPTION
	"Table entry attribute for ethernetFlowsyncPacketsOnNonFlowsyncChannels"
	::={ethernetFlowsyncPacketsOnNonFlowsyncChannelsLevelEntry 3}

ethernetFlowsyncPacketsOnNonFlowsyncChannelsLevelMax OBJECT-TYPE
	SYNTAX	 CounterBasedGauge64
	MAX-ACCESS  read-only
	STATUS      current
	DESCRIPTION
	"Table entry attribute for ethernetFlowsyncPacketsOnNonFlowsyncChannels"
	::={ethernetFlowsyncPacketsOnNonFlowsyncChannelsLevelEntry 4}


ethernetNatsyncPacketsOnNonNatsyncChannels	OBJECT IDENTIFIER ::={ethernet 36}

ethernetNatsyncPacketsOnNonNatsyncChannelsVal	OBJECT-TYPE
	SYNTAX	 Counter64
	MAX-ACCESS read-only
	STATUS current
	DESCRIPTION "Natsync packets received on non-natsync interface"

	::={ethernetNatsyncPacketsOnNonNatsyncChannels 1}

ethernetNatsyncPacketsOnNonNatsyncChannelsMom	OBJECT-TYPE
	SYNTAX	 CounterBasedGauge64
	MAX-ACCESS read-only
	STATUS current
	DESCRIPTION "Natsync packets received on non-natsync interface"

	::={ethernetNatsyncPacketsOnNonNatsyncChannels 2}

ethernetNatsyncPacketsOnNonNatsyncChannelsMax	OBJECT-TYPE
	SYNTAX	 CounterBasedGauge64
	MAX-ACCESS read-only
	STATUS current
	DESCRIPTION "Natsync packets received on non-natsync interface"

	::={ethernetNatsyncPacketsOnNonNatsyncChannels 3}

ethernetNatsyncPacketsOnNonNatsyncChannelsLevelTable OBJECT-TYPE
	SYNTAX      SEQUENCE OF EthernetNatsyncPacketsOnNonNatsyncChannelsLevelEntry
	MAX-ACCESS  not-accessible
	STATUS      current
	DESCRIPTION
	"Table for ethernetNatsyncPacketsOnNonNatsyncChannels"
	::={ethernetNatsyncPacketsOnNonNatsyncChannels 4}

ethernetNatsyncPacketsOnNonNatsyncChannelsLevelEntry OBJECT-TYPE
	SYNTAX      EthernetNatsyncPacketsOnNonNatsyncChannelsLevelEntry
	MAX-ACCESS  not-accessible
	STATUS      current
	DESCRIPTION
	"Table entry for ethernetNatsyncPacketsOnNonNatsyncChannels"
	INDEX { ethernetNatsyncPacketsOnNonNatsyncChannelsLevelName }
	::={ethernetNatsyncPacketsOnNonNatsyncChannelsLevelTable 1}

EthernetNatsyncPacketsOnNonNatsyncChannelsLevelEntry ::=
	SEQUENCE {
		ethernetNatsyncPacketsOnNonNatsyncChannelsLevelName	DisplayString,
		ethernetNatsyncPacketsOnNonNatsyncChannelsLevelVal	Counter64,
		ethernetNatsyncPacketsOnNonNatsyncChannelsLevelMom	CounterBasedGauge64,
		ethernetNatsyncPacketsOnNonNatsyncChannelsLevelMax	CounterBasedGauge64
	}

ethernetNatsyncPacketsOnNonNatsyncChannelsLevelName OBJECT-TYPE
	SYNTAX      DisplayString
	MAX-ACCESS  not-accessible
	STATUS      current
	DESCRIPTION
	"Table entry display string for ethernetNatsyncPacketsOnNonNatsyncChannels"
	::={ethernetNatsyncPacketsOnNonNatsyncChannelsLevelEntry 1}

ethernetNatsyncPacketsOnNonNatsyncChannelsLevelVal OBJECT-TYPE
	SYNTAX	 Counter64
	MAX-ACCESS  read-only
	STATUS      current
	DESCRIPTION
	"Table entry attribute for ethernetNatsyncPacketsOnNonNatsyncChannels"
	::={ethernetNatsyncPacketsOnNonNatsyncChannelsLevelEntry 2}

ethernetNatsyncPacketsOnNonNatsyncChannelsLevelMom OBJECT-TYPE
	SYNTAX	 CounterBasedGauge64
	MAX-ACCESS  read-only
	STATUS      current
	DESCRIPTION
	"Table entry attribute for ethernetNatsyncPacketsOnNonNatsyncChannels"
	::={ethernetNatsyncPacketsOnNonNatsyncChannelsLevelEntry 3}

ethernetNatsyncPacketsOnNonNatsyncChannelsLevelMax OBJECT-TYPE
	SYNTAX	 CounterBasedGauge64
	MAX-ACCESS  read-only
	STATUS      current
	DESCRIPTION
	"Table entry attribute for ethernetNatsyncPacketsOnNonNatsyncChannels"
	::={ethernetNatsyncPacketsOnNonNatsyncChannelsLevelEntry 4}


ethernetShuntChannelRole	OBJECT IDENTIFIER ::={ethernet 37}

ethernetShuntChannelRoleVal	OBJECT-TYPE
	SYNTAX	 Counter64
	MAX-ACCESS read-only
	STATUS current
	DESCRIPTION "Shunted packets (Channel role)"

	::={ethernetShuntChannelRole 1}

ethernetShuntChannelRoleMom	OBJECT-TYPE
	SYNTAX	 CounterBasedGauge64
	MAX-ACCESS read-only
	STATUS current
	DESCRIPTION "Shunted packets (Channel role)"

	::={ethernetShuntChannelRole 2}

ethernetShuntChannelRoleMax	OBJECT-TYPE
	SYNTAX	 CounterBasedGauge64
	MAX-ACCESS read-only
	STATUS current
	DESCRIPTION "Shunted packets (Channel role)"

	::={ethernetShuntChannelRole 3}

ethernetShuntChannelRoleLevelTable OBJECT-TYPE
	SYNTAX      SEQUENCE OF EthernetShuntChannelRoleLevelEntry
	MAX-ACCESS  not-accessible
	STATUS      current
	DESCRIPTION
	"Table for ethernetShuntChannelRole"
	::={ethernetShuntChannelRole 4}

ethernetShuntChannelRoleLevelEntry OBJECT-TYPE
	SYNTAX      EthernetShuntChannelRoleLevelEntry
	MAX-ACCESS  not-accessible
	STATUS      current
	DESCRIPTION
	"Table entry for ethernetShuntChannelRole"
	INDEX { ethernetShuntChannelRoleLevelName }
	::={ethernetShuntChannelRoleLevelTable 1}

EthernetShuntChannelRoleLevelEntry ::=
	SEQUENCE {
		ethernetShuntChannelRoleLevelName	DisplayString,
		ethernetShuntChannelRoleLevelVal	Counter64,
		ethernetShuntChannelRoleLevelMom	CounterBasedGauge64,
		ethernetShuntChannelRoleLevelMax	CounterBasedGauge64
	}

ethernetShuntChannelRoleLevelName OBJECT-TYPE
	SYNTAX      DisplayString
	MAX-ACCESS  not-accessible
	STATUS      current
	DESCRIPTION
	"Table entry display string for ethernetShuntChannelRole"
	::={ethernetShuntChannelRoleLevelEntry 1}

ethernetShuntChannelRoleLevelVal OBJECT-TYPE
	SYNTAX	 Counter64
	MAX-ACCESS  read-only
	STATUS      current
	DESCRIPTION
	"Table entry attribute for ethernetShuntChannelRole"
	::={ethernetShuntChannelRoleLevelEntry 2}

ethernetShuntChannelRoleLevelMom OBJECT-TYPE
	SYNTAX	 CounterBasedGauge64
	MAX-ACCESS  read-only
	STATUS      current
	DESCRIPTION
	"Table entry attribute for ethernetShuntChannelRole"
	::={ethernetShuntChannelRoleLevelEntry 3}

ethernetShuntChannelRoleLevelMax OBJECT-TYPE
	SYNTAX	 CounterBasedGauge64
	MAX-ACCESS  read-only
	STATUS      current
	DESCRIPTION
	"Table entry attribute for ethernetShuntChannelRole"
	::={ethernetShuntChannelRoleLevelEntry 4}


ethernetShuntChannleRoleBytes	OBJECT IDENTIFIER ::={ethernet 38}

ethernetShuntChannleRoleBytesVal	OBJECT-TYPE
	SYNTAX	 Counter64
	MAX-ACCESS read-only
	STATUS current
	DESCRIPTION "Shunted bytes (Channel role)"

	::={ethernetShuntChannleRoleBytes 1}

ethernetShuntChannleRoleBytesMom	OBJECT-TYPE
	SYNTAX	 CounterBasedGauge64
	MAX-ACCESS read-only
	STATUS current
	DESCRIPTION "Shunted bytes (Channel role)"

	::={ethernetShuntChannleRoleBytes 2}

ethernetShuntChannleRoleBytesMax	OBJECT-TYPE
	SYNTAX	 CounterBasedGauge64
	MAX-ACCESS read-only
	STATUS current
	DESCRIPTION "Shunted bytes (Channel role)"

	::={ethernetShuntChannleRoleBytes 3}

ethernetShuntChannleRoleBytesLevelTable OBJECT-TYPE
	SYNTAX      SEQUENCE OF EthernetShuntChannleRoleBytesLevelEntry
	MAX-ACCESS  not-accessible
	STATUS      current
	DESCRIPTION
	"Table for ethernetShuntChannleRoleBytes"
	::={ethernetShuntChannleRoleBytes 4}

ethernetShuntChannleRoleBytesLevelEntry OBJECT-TYPE
	SYNTAX      EthernetShuntChannleRoleBytesLevelEntry
	MAX-ACCESS  not-accessible
	STATUS      current
	DESCRIPTION
	"Table entry for ethernetShuntChannleRoleBytes"
	INDEX { ethernetShuntChannleRoleBytesLevelName }
	::={ethernetShuntChannleRoleBytesLevelTable 1}

EthernetShuntChannleRoleBytesLevelEntry ::=
	SEQUENCE {
		ethernetShuntChannleRoleBytesLevelName	DisplayString,
		ethernetShuntChannleRoleBytesLevelVal	Counter64,
		ethernetShuntChannleRoleBytesLevelMom	CounterBasedGauge64,
		ethernetShuntChannleRoleBytesLevelMax	CounterBasedGauge64
	}

ethernetShuntChannleRoleBytesLevelName OBJECT-TYPE
	SYNTAX      DisplayString
	MAX-ACCESS  not-accessible
	STATUS      current
	DESCRIPTION
	"Table entry display string for ethernetShuntChannleRoleBytes"
	::={ethernetShuntChannleRoleBytesLevelEntry 1}

ethernetShuntChannleRoleBytesLevelVal OBJECT-TYPE
	SYNTAX	 Counter64
	MAX-ACCESS  read-only
	STATUS      current
	DESCRIPTION
	"Table entry attribute for ethernetShuntChannleRoleBytes"
	::={ethernetShuntChannleRoleBytesLevelEntry 2}

ethernetShuntChannleRoleBytesLevelMom OBJECT-TYPE
	SYNTAX	 CounterBasedGauge64
	MAX-ACCESS  read-only
	STATUS      current
	DESCRIPTION
	"Table entry attribute for ethernetShuntChannleRoleBytes"
	::={ethernetShuntChannleRoleBytesLevelEntry 3}

ethernetShuntChannleRoleBytesLevelMax OBJECT-TYPE
	SYNTAX	 CounterBasedGauge64
	MAX-ACCESS  read-only
	STATUS      current
	DESCRIPTION
	"Table entry attribute for ethernetShuntChannleRoleBytes"
	::={ethernetShuntChannleRoleBytesLevelEntry 4}


ethernetBlindForwardedPackets	OBJECT IDENTIFIER ::={ethernet 39}

ethernetBlindForwardedPacketsVal	OBJECT-TYPE
	SYNTAX	 Counter64
	MAX-ACCESS read-only
	STATUS current
	DESCRIPTION "Blind forwarded packets"

	::={ethernetBlindForwardedPackets 1}

ethernetBlindForwardedPacketsMom	OBJECT-TYPE
	SYNTAX	 CounterBasedGauge64
	MAX-ACCESS read-only
	STATUS current
	DESCRIPTION "Blind forwarded packets"

	::={ethernetBlindForwardedPackets 2}

ethernetBlindForwardedPacketsMax	OBJECT-TYPE
	SYNTAX	 CounterBasedGauge64
	MAX-ACCESS read-only
	STATUS current
	DESCRIPTION "Blind forwarded packets"

	::={ethernetBlindForwardedPackets 3}

ethernetBlindForwardedPacketsLevelTable OBJECT-TYPE
	SYNTAX      SEQUENCE OF EthernetBlindForwardedPacketsLevelEntry
	MAX-ACCESS  not-accessible
	STATUS      current
	DESCRIPTION
	"Table for ethernetBlindForwardedPackets"
	::={ethernetBlindForwardedPackets 4}

ethernetBlindForwardedPacketsLevelEntry OBJECT-TYPE
	SYNTAX      EthernetBlindForwardedPacketsLevelEntry
	MAX-ACCESS  not-accessible
	STATUS      current
	DESCRIPTION
	"Table entry for ethernetBlindForwardedPackets"
	INDEX { ethernetBlindForwardedPacketsLevelName }
	::={ethernetBlindForwardedPacketsLevelTable 1}

EthernetBlindForwardedPacketsLevelEntry ::=
	SEQUENCE {
		ethernetBlindForwardedPacketsLevelName	DisplayString,
		ethernetBlindForwardedPacketsLevelVal	Counter64,
		ethernetBlindForwardedPacketsLevelMom	CounterBasedGauge64,
		ethernetBlindForwardedPacketsLevelMax	CounterBasedGauge64
	}

ethernetBlindForwardedPacketsLevelName OBJECT-TYPE
	SYNTAX      DisplayString
	MAX-ACCESS  not-accessible
	STATUS      current
	DESCRIPTION
	"Table entry display string for ethernetBlindForwardedPackets"
	::={ethernetBlindForwardedPacketsLevelEntry 1}

ethernetBlindForwardedPacketsLevelVal OBJECT-TYPE
	SYNTAX	 Counter64
	MAX-ACCESS  read-only
	STATUS      current
	DESCRIPTION
	"Table entry attribute for ethernetBlindForwardedPackets"
	::={ethernetBlindForwardedPacketsLevelEntry 2}

ethernetBlindForwardedPacketsLevelMom OBJECT-TYPE
	SYNTAX	 CounterBasedGauge64
	MAX-ACCESS  read-only
	STATUS      current
	DESCRIPTION
	"Table entry attribute for ethernetBlindForwardedPackets"
	::={ethernetBlindForwardedPacketsLevelEntry 3}

ethernetBlindForwardedPacketsLevelMax OBJECT-TYPE
	SYNTAX	 CounterBasedGauge64
	MAX-ACCESS  read-only
	STATUS      current
	DESCRIPTION
	"Table entry attribute for ethernetBlindForwardedPackets"
	::={ethernetBlindForwardedPacketsLevelEntry 4}


ethernetBlindForwardedBytes	OBJECT IDENTIFIER ::={ethernet 40}

ethernetBlindForwardedBytesVal	OBJECT-TYPE
	SYNTAX	 Counter64
	MAX-ACCESS read-only
	STATUS current
	DESCRIPTION "Blind forwarded bytes"

	::={ethernetBlindForwardedBytes 1}

ethernetBlindForwardedBytesMom	OBJECT-TYPE
	SYNTAX	 CounterBasedGauge64
	MAX-ACCESS read-only
	STATUS current
	DESCRIPTION "Blind forwarded bytes"

	::={ethernetBlindForwardedBytes 2}

ethernetBlindForwardedBytesMax	OBJECT-TYPE
	SYNTAX	 CounterBasedGauge64
	MAX-ACCESS read-only
	STATUS current
	DESCRIPTION "Blind forwarded bytes"

	::={ethernetBlindForwardedBytes 3}

ethernetBlindForwardedBytesLevelTable OBJECT-TYPE
	SYNTAX      SEQUENCE OF EthernetBlindForwardedBytesLevelEntry
	MAX-ACCESS  not-accessible
	STATUS      current
	DESCRIPTION
	"Table for ethernetBlindForwardedBytes"
	::={ethernetBlindForwardedBytes 4}

ethernetBlindForwardedBytesLevelEntry OBJECT-TYPE
	SYNTAX      EthernetBlindForwardedBytesLevelEntry
	MAX-ACCESS  not-accessible
	STATUS      current
	DESCRIPTION
	"Table entry for ethernetBlindForwardedBytes"
	INDEX { ethernetBlindForwardedBytesLevelName }
	::={ethernetBlindForwardedBytesLevelTable 1}

EthernetBlindForwardedBytesLevelEntry ::=
	SEQUENCE {
		ethernetBlindForwardedBytesLevelName	DisplayString,
		ethernetBlindForwardedBytesLevelVal	Counter64,
		ethernetBlindForwardedBytesLevelMom	CounterBasedGauge64,
		ethernetBlindForwardedBytesLevelMax	CounterBasedGauge64
	}

ethernetBlindForwardedBytesLevelName OBJECT-TYPE
	SYNTAX      DisplayString
	MAX-ACCESS  not-accessible
	STATUS      current
	DESCRIPTION
	"Table entry display string for ethernetBlindForwardedBytes"
	::={ethernetBlindForwardedBytesLevelEntry 1}

ethernetBlindForwardedBytesLevelVal OBJECT-TYPE
	SYNTAX	 Counter64
	MAX-ACCESS  read-only
	STATUS      current
	DESCRIPTION
	"Table entry attribute for ethernetBlindForwardedBytes"
	::={ethernetBlindForwardedBytesLevelEntry 2}

ethernetBlindForwardedBytesLevelMom OBJECT-TYPE
	SYNTAX	 CounterBasedGauge64
	MAX-ACCESS  read-only
	STATUS      current
	DESCRIPTION
	"Table entry attribute for ethernetBlindForwardedBytes"
	::={ethernetBlindForwardedBytesLevelEntry 3}

ethernetBlindForwardedBytesLevelMax OBJECT-TYPE
	SYNTAX	 CounterBasedGauge64
	MAX-ACCESS  read-only
	STATUS      current
	DESCRIPTION
	"Table entry attribute for ethernetBlindForwardedBytes"
	::={ethernetBlindForwardedBytesLevelEntry 4}


ipv4	OBJECT IDENTIFIER ::={sysdiag 32}

ipv4Packets	OBJECT IDENTIFIER ::={ipv4 1}

ipv4PacketsVal	OBJECT-TYPE
	SYNTAX	 Counter64
	MAX-ACCESS read-only
	STATUS current
	DESCRIPTION "RX packets"

	::={ipv4Packets 1}

ipv4PacketsMom	OBJECT-TYPE
	SYNTAX	 CounterBasedGauge64
	MAX-ACCESS read-only
	STATUS current
	DESCRIPTION "RX packets"

	::={ipv4Packets 2}

ipv4PacketsMax	OBJECT-TYPE
	SYNTAX	 CounterBasedGauge64
	MAX-ACCESS read-only
	STATUS current
	DESCRIPTION "RX packets"

	::={ipv4Packets 3}

ipv4PacketsLevelTable OBJECT-TYPE
	SYNTAX      SEQUENCE OF Ipv4PacketsLevelEntry
	MAX-ACCESS  not-accessible
	STATUS      current
	DESCRIPTION
	"Table for ipv4Packets"
	::={ipv4Packets 4}

ipv4PacketsLevelEntry OBJECT-TYPE
	SYNTAX      Ipv4PacketsLevelEntry
	MAX-ACCESS  not-accessible
	STATUS      current
	DESCRIPTION
	"Table entry for ipv4Packets"
	INDEX { ipv4PacketsLevelName }
	::={ipv4PacketsLevelTable 1}

Ipv4PacketsLevelEntry ::=
	SEQUENCE {
		ipv4PacketsLevelName	DisplayString,
		ipv4PacketsLevelVal	Counter64,
		ipv4PacketsLevelMom	CounterBasedGauge64,
		ipv4PacketsLevelMax	CounterBasedGauge64
	}

ipv4PacketsLevelName OBJECT-TYPE
	SYNTAX      DisplayString
	MAX-ACCESS  not-accessible
	STATUS      current
	DESCRIPTION
	"Table entry display string for ipv4Packets"
	::={ipv4PacketsLevelEntry 1}

ipv4PacketsLevelVal OBJECT-TYPE
	SYNTAX	 Counter64
	MAX-ACCESS  read-only
	STATUS      current
	DESCRIPTION
	"Table entry attribute for ipv4Packets"
	::={ipv4PacketsLevelEntry 2}

ipv4PacketsLevelMom OBJECT-TYPE
	SYNTAX	 CounterBasedGauge64
	MAX-ACCESS  read-only
	STATUS      current
	DESCRIPTION
	"Table entry attribute for ipv4Packets"
	::={ipv4PacketsLevelEntry 3}

ipv4PacketsLevelMax OBJECT-TYPE
	SYNTAX	 CounterBasedGauge64
	MAX-ACCESS  read-only
	STATUS      current
	DESCRIPTION
	"Table entry attribute for ipv4Packets"
	::={ipv4PacketsLevelEntry 4}


ipv4Bytes	OBJECT IDENTIFIER ::={ipv4 2}

ipv4BytesVal	OBJECT-TYPE
	SYNTAX	 Counter64
	MAX-ACCESS read-only
	STATUS current
	DESCRIPTION "RX data"

	::={ipv4Bytes 1}

ipv4BytesMom	OBJECT-TYPE
	SYNTAX	 CounterBasedGauge64
	MAX-ACCESS read-only
	STATUS current
	DESCRIPTION "RX data"

	::={ipv4Bytes 2}

ipv4BytesMax	OBJECT-TYPE
	SYNTAX	 CounterBasedGauge64
	MAX-ACCESS read-only
	STATUS current
	DESCRIPTION "RX data"

	::={ipv4Bytes 3}

ipv4BytesLevelTable OBJECT-TYPE
	SYNTAX      SEQUENCE OF Ipv4BytesLevelEntry
	MAX-ACCESS  not-accessible
	STATUS      current
	DESCRIPTION
	"Table for ipv4Bytes"
	::={ipv4Bytes 4}

ipv4BytesLevelEntry OBJECT-TYPE
	SYNTAX      Ipv4BytesLevelEntry
	MAX-ACCESS  not-accessible
	STATUS      current
	DESCRIPTION
	"Table entry for ipv4Bytes"
	INDEX { ipv4BytesLevelName }
	::={ipv4BytesLevelTable 1}

Ipv4BytesLevelEntry ::=
	SEQUENCE {
		ipv4BytesLevelName	DisplayString,
		ipv4BytesLevelVal	Counter64,
		ipv4BytesLevelMom	CounterBasedGauge64,
		ipv4BytesLevelMax	CounterBasedGauge64
	}

ipv4BytesLevelName OBJECT-TYPE
	SYNTAX      DisplayString
	MAX-ACCESS  not-accessible
	STATUS      current
	DESCRIPTION
	"Table entry display string for ipv4Bytes"
	::={ipv4BytesLevelEntry 1}

ipv4BytesLevelVal OBJECT-TYPE
	SYNTAX	 Counter64
	MAX-ACCESS  read-only
	STATUS      current
	DESCRIPTION
	"Table entry attribute for ipv4Bytes"
	::={ipv4BytesLevelEntry 2}

ipv4BytesLevelMom OBJECT-TYPE
	SYNTAX	 CounterBasedGauge64
	MAX-ACCESS  read-only
	STATUS      current
	DESCRIPTION
	"Table entry attribute for ipv4Bytes"
	::={ipv4BytesLevelEntry 3}

ipv4BytesLevelMax OBJECT-TYPE
	SYNTAX	 CounterBasedGauge64
	MAX-ACCESS  read-only
	STATUS      current
	DESCRIPTION
	"Table entry attribute for ipv4Bytes"
	::={ipv4BytesLevelEntry 4}


ipv4RefusedShort	OBJECT IDENTIFIER ::={ipv4 3}

ipv4RefusedShortVal	OBJECT-TYPE
	SYNTAX	 Counter64
	MAX-ACCESS read-only
	STATUS current
	DESCRIPTION "Refused (packet is too short)"

	::={ipv4RefusedShort 1}

ipv4RefusedShortMom	OBJECT-TYPE
	SYNTAX	 CounterBasedGauge64
	MAX-ACCESS read-only
	STATUS current
	DESCRIPTION "Refused (packet is too short)"

	::={ipv4RefusedShort 2}

ipv4RefusedShortMax	OBJECT-TYPE
	SYNTAX	 CounterBasedGauge64
	MAX-ACCESS read-only
	STATUS current
	DESCRIPTION "Refused (packet is too short)"

	::={ipv4RefusedShort 3}

ipv4RefusedShortLevelTable OBJECT-TYPE
	SYNTAX      SEQUENCE OF Ipv4RefusedShortLevelEntry
	MAX-ACCESS  not-accessible
	STATUS      current
	DESCRIPTION
	"Table for ipv4RefusedShort"
	::={ipv4RefusedShort 4}

ipv4RefusedShortLevelEntry OBJECT-TYPE
	SYNTAX      Ipv4RefusedShortLevelEntry
	MAX-ACCESS  not-accessible
	STATUS      current
	DESCRIPTION
	"Table entry for ipv4RefusedShort"
	INDEX { ipv4RefusedShortLevelName }
	::={ipv4RefusedShortLevelTable 1}

Ipv4RefusedShortLevelEntry ::=
	SEQUENCE {
		ipv4RefusedShortLevelName	DisplayString,
		ipv4RefusedShortLevelVal	Counter64,
		ipv4RefusedShortLevelMom	CounterBasedGauge64,
		ipv4RefusedShortLevelMax	CounterBasedGauge64
	}

ipv4RefusedShortLevelName OBJECT-TYPE
	SYNTAX      DisplayString
	MAX-ACCESS  not-accessible
	STATUS      current
	DESCRIPTION
	"Table entry display string for ipv4RefusedShort"
	::={ipv4RefusedShortLevelEntry 1}

ipv4RefusedShortLevelVal OBJECT-TYPE
	SYNTAX	 Counter64
	MAX-ACCESS  read-only
	STATUS      current
	DESCRIPTION
	"Table entry attribute for ipv4RefusedShort"
	::={ipv4RefusedShortLevelEntry 2}

ipv4RefusedShortLevelMom OBJECT-TYPE
	SYNTAX	 CounterBasedGauge64
	MAX-ACCESS  read-only
	STATUS      current
	DESCRIPTION
	"Table entry attribute for ipv4RefusedShort"
	::={ipv4RefusedShortLevelEntry 3}

ipv4RefusedShortLevelMax OBJECT-TYPE
	SYNTAX	 CounterBasedGauge64
	MAX-ACCESS  read-only
	STATUS      current
	DESCRIPTION
	"Table entry attribute for ipv4RefusedShort"
	::={ipv4RefusedShortLevelEntry 4}


ipv4RefusedVersion	OBJECT IDENTIFIER ::={ipv4 4}

ipv4RefusedVersionVal	OBJECT-TYPE
	SYNTAX	 Counter64
	MAX-ACCESS read-only
	STATUS current
	DESCRIPTION "Refused (invalid version)"

	::={ipv4RefusedVersion 1}

ipv4RefusedVersionMom	OBJECT-TYPE
	SYNTAX	 CounterBasedGauge64
	MAX-ACCESS read-only
	STATUS current
	DESCRIPTION "Refused (invalid version)"

	::={ipv4RefusedVersion 2}

ipv4RefusedVersionMax	OBJECT-TYPE
	SYNTAX	 CounterBasedGauge64
	MAX-ACCESS read-only
	STATUS current
	DESCRIPTION "Refused (invalid version)"

	::={ipv4RefusedVersion 3}

ipv4RefusedVersionLevelTable OBJECT-TYPE
	SYNTAX      SEQUENCE OF Ipv4RefusedVersionLevelEntry
	MAX-ACCESS  not-accessible
	STATUS      current
	DESCRIPTION
	"Table for ipv4RefusedVersion"
	::={ipv4RefusedVersion 4}

ipv4RefusedVersionLevelEntry OBJECT-TYPE
	SYNTAX      Ipv4RefusedVersionLevelEntry
	MAX-ACCESS  not-accessible
	STATUS      current
	DESCRIPTION
	"Table entry for ipv4RefusedVersion"
	INDEX { ipv4RefusedVersionLevelName }
	::={ipv4RefusedVersionLevelTable 1}

Ipv4RefusedVersionLevelEntry ::=
	SEQUENCE {
		ipv4RefusedVersionLevelName	DisplayString,
		ipv4RefusedVersionLevelVal	Counter64,
		ipv4RefusedVersionLevelMom	CounterBasedGauge64,
		ipv4RefusedVersionLevelMax	CounterBasedGauge64
	}

ipv4RefusedVersionLevelName OBJECT-TYPE
	SYNTAX      DisplayString
	MAX-ACCESS  not-accessible
	STATUS      current
	DESCRIPTION
	"Table entry display string for ipv4RefusedVersion"
	::={ipv4RefusedVersionLevelEntry 1}

ipv4RefusedVersionLevelVal OBJECT-TYPE
	SYNTAX	 Counter64
	MAX-ACCESS  read-only
	STATUS      current
	DESCRIPTION
	"Table entry attribute for ipv4RefusedVersion"
	::={ipv4RefusedVersionLevelEntry 2}

ipv4RefusedVersionLevelMom OBJECT-TYPE
	SYNTAX	 CounterBasedGauge64
	MAX-ACCESS  read-only
	STATUS      current
	DESCRIPTION
	"Table entry attribute for ipv4RefusedVersion"
	::={ipv4RefusedVersionLevelEntry 3}

ipv4RefusedVersionLevelMax OBJECT-TYPE
	SYNTAX	 CounterBasedGauge64
	MAX-ACCESS  read-only
	STATUS      current
	DESCRIPTION
	"Table entry attribute for ipv4RefusedVersion"
	::={ipv4RefusedVersionLevelEntry 4}


ipv4RefusedSelf	OBJECT IDENTIFIER ::={ipv4 5}

ipv4RefusedSelfVal	OBJECT-TYPE
	SYNTAX	 Counter64
	MAX-ACCESS read-only
	STATUS obsolete
	DESCRIPTION "Refused (src == dest)"

	::={ipv4RefusedSelf 1}

ipv4RefusedSelfMom	OBJECT-TYPE
	SYNTAX	 CounterBasedGauge64
	MAX-ACCESS read-only
	STATUS obsolete
	DESCRIPTION "Refused (src == dest)"

	::={ipv4RefusedSelf 2}

ipv4RefusedSelfMax	OBJECT-TYPE
	SYNTAX	 CounterBasedGauge64
	MAX-ACCESS read-only
	STATUS obsolete
	DESCRIPTION "Refused (src == dest)"

	::={ipv4RefusedSelf 3}

ipv4RefusedSelfLevelTable OBJECT-TYPE
	SYNTAX      SEQUENCE OF Ipv4RefusedSelfLevelEntry
	MAX-ACCESS  not-accessible
	STATUS      current
	DESCRIPTION
	"Table for ipv4RefusedSelf"
	::={ipv4RefusedSelf 4}

ipv4RefusedSelfLevelEntry OBJECT-TYPE
	SYNTAX      Ipv4RefusedSelfLevelEntry
	MAX-ACCESS  not-accessible
	STATUS      current
	DESCRIPTION
	"Table entry for ipv4RefusedSelf"
	INDEX { ipv4RefusedSelfLevelName }
	::={ipv4RefusedSelfLevelTable 1}

Ipv4RefusedSelfLevelEntry ::=
	SEQUENCE {
		ipv4RefusedSelfLevelName	DisplayString,
		ipv4RefusedSelfLevelVal	Counter64,
		ipv4RefusedSelfLevelMom	CounterBasedGauge64,
		ipv4RefusedSelfLevelMax	CounterBasedGauge64
	}

ipv4RefusedSelfLevelName OBJECT-TYPE
	SYNTAX      DisplayString
	MAX-ACCESS  not-accessible
	STATUS      current
	DESCRIPTION
	"Table entry display string for ipv4RefusedSelf"
	::={ipv4RefusedSelfLevelEntry 1}

ipv4RefusedSelfLevelVal OBJECT-TYPE
	SYNTAX	 Counter64
	MAX-ACCESS  read-only
	STATUS      current
	DESCRIPTION
	"Table entry attribute for ipv4RefusedSelf"
	::={ipv4RefusedSelfLevelEntry 2}

ipv4RefusedSelfLevelMom OBJECT-TYPE
	SYNTAX	 CounterBasedGauge64
	MAX-ACCESS  read-only
	STATUS      current
	DESCRIPTION
	"Table entry attribute for ipv4RefusedSelf"
	::={ipv4RefusedSelfLevelEntry 3}

ipv4RefusedSelfLevelMax OBJECT-TYPE
	SYNTAX	 CounterBasedGauge64
	MAX-ACCESS  read-only
	STATUS      current
	DESCRIPTION
	"Table entry attribute for ipv4RefusedSelf"
	::={ipv4RefusedSelfLevelEntry 4}


ipv4Unfragmented	OBJECT IDENTIFIER ::={ipv4 6}

ipv4UnfragmentedVal	OBJECT-TYPE
	SYNTAX	 Counter64
	MAX-ACCESS read-only
	STATUS current
	DESCRIPTION "Unfragmented packets"

	::={ipv4Unfragmented 1}

ipv4UnfragmentedMom	OBJECT-TYPE
	SYNTAX	 CounterBasedGauge64
	MAX-ACCESS read-only
	STATUS current
	DESCRIPTION "Unfragmented packets"

	::={ipv4Unfragmented 2}

ipv4UnfragmentedMax	OBJECT-TYPE
	SYNTAX	 CounterBasedGauge64
	MAX-ACCESS read-only
	STATUS current
	DESCRIPTION "Unfragmented packets"

	::={ipv4Unfragmented 3}

ipv4UnfragmentedLevelTable OBJECT-TYPE
	SYNTAX      SEQUENCE OF Ipv4UnfragmentedLevelEntry
	MAX-ACCESS  not-accessible
	STATUS      current
	DESCRIPTION
	"Table for ipv4Unfragmented"
	::={ipv4Unfragmented 4}

ipv4UnfragmentedLevelEntry OBJECT-TYPE
	SYNTAX      Ipv4UnfragmentedLevelEntry
	MAX-ACCESS  not-accessible
	STATUS      current
	DESCRIPTION
	"Table entry for ipv4Unfragmented"
	INDEX { ipv4UnfragmentedLevelName }
	::={ipv4UnfragmentedLevelTable 1}

Ipv4UnfragmentedLevelEntry ::=
	SEQUENCE {
		ipv4UnfragmentedLevelName	DisplayString,
		ipv4UnfragmentedLevelVal	Counter64,
		ipv4UnfragmentedLevelMom	CounterBasedGauge64,
		ipv4UnfragmentedLevelMax	CounterBasedGauge64
	}

ipv4UnfragmentedLevelName OBJECT-TYPE
	SYNTAX      DisplayString
	MAX-ACCESS  not-accessible
	STATUS      current
	DESCRIPTION
	"Table entry display string for ipv4Unfragmented"
	::={ipv4UnfragmentedLevelEntry 1}

ipv4UnfragmentedLevelVal OBJECT-TYPE
	SYNTAX	 Counter64
	MAX-ACCESS  read-only
	STATUS      current
	DESCRIPTION
	"Table entry attribute for ipv4Unfragmented"
	::={ipv4UnfragmentedLevelEntry 2}

ipv4UnfragmentedLevelMom OBJECT-TYPE
	SYNTAX	 CounterBasedGauge64
	MAX-ACCESS  read-only
	STATUS      current
	DESCRIPTION
	"Table entry attribute for ipv4Unfragmented"
	::={ipv4UnfragmentedLevelEntry 3}

ipv4UnfragmentedLevelMax OBJECT-TYPE
	SYNTAX	 CounterBasedGauge64
	MAX-ACCESS  read-only
	STATUS      current
	DESCRIPTION
	"Table entry attribute for ipv4Unfragmented"
	::={ipv4UnfragmentedLevelEntry 4}


ipv4Fragmented	OBJECT IDENTIFIER ::={ipv4 7}

ipv4FragmentedVal	OBJECT-TYPE
	SYNTAX	 Counter64
	MAX-ACCESS read-only
	STATUS current
	DESCRIPTION "Packet fragments"

	::={ipv4Fragmented 1}

ipv4FragmentedMom	OBJECT-TYPE
	SYNTAX	 CounterBasedGauge64
	MAX-ACCESS read-only
	STATUS current
	DESCRIPTION "Packet fragments"

	::={ipv4Fragmented 2}

ipv4FragmentedMax	OBJECT-TYPE
	SYNTAX	 CounterBasedGauge64
	MAX-ACCESS read-only
	STATUS current
	DESCRIPTION "Packet fragments"

	::={ipv4Fragmented 3}

ipv4FragmentedLevelTable OBJECT-TYPE
	SYNTAX      SEQUENCE OF Ipv4FragmentedLevelEntry
	MAX-ACCESS  not-accessible
	STATUS      current
	DESCRIPTION
	"Table for ipv4Fragmented"
	::={ipv4Fragmented 4}

ipv4FragmentedLevelEntry OBJECT-TYPE
	SYNTAX      Ipv4FragmentedLevelEntry
	MAX-ACCESS  not-accessible
	STATUS      current
	DESCRIPTION
	"Table entry for ipv4Fragmented"
	INDEX { ipv4FragmentedLevelName }
	::={ipv4FragmentedLevelTable 1}

Ipv4FragmentedLevelEntry ::=
	SEQUENCE {
		ipv4FragmentedLevelName	DisplayString,
		ipv4FragmentedLevelVal	Counter64,
		ipv4FragmentedLevelMom	CounterBasedGauge64,
		ipv4FragmentedLevelMax	CounterBasedGauge64
	}

ipv4FragmentedLevelName OBJECT-TYPE
	SYNTAX      DisplayString
	MAX-ACCESS  not-accessible
	STATUS      current
	DESCRIPTION
	"Table entry display string for ipv4Fragmented"
	::={ipv4FragmentedLevelEntry 1}

ipv4FragmentedLevelVal OBJECT-TYPE
	SYNTAX	 Counter64
	MAX-ACCESS  read-only
	STATUS      current
	DESCRIPTION
	"Table entry attribute for ipv4Fragmented"
	::={ipv4FragmentedLevelEntry 2}

ipv4FragmentedLevelMom OBJECT-TYPE
	SYNTAX	 CounterBasedGauge64
	MAX-ACCESS  read-only
	STATUS      current
	DESCRIPTION
	"Table entry attribute for ipv4Fragmented"
	::={ipv4FragmentedLevelEntry 3}

ipv4FragmentedLevelMax OBJECT-TYPE
	SYNTAX	 CounterBasedGauge64
	MAX-ACCESS  read-only
	STATUS      current
	DESCRIPTION
	"Table entry attribute for ipv4Fragmented"
	::={ipv4FragmentedLevelEntry 4}


ipv4FragmentedIds	OBJECT IDENTIFIER ::={ipv4 10}

ipv4FragmentedIdsVal	OBJECT-TYPE
	SYNTAX	 CounterBasedGauge64
	MAX-ACCESS read-only
	STATUS current
	DESCRIPTION "Fragment ids"

	::={ipv4FragmentedIds 1}

ipv4FragmentedIdsMax	OBJECT-TYPE
	SYNTAX	 CounterBasedGauge64
	MAX-ACCESS read-only
	STATUS current
	DESCRIPTION "Fragment ids"

	::={ipv4FragmentedIds 3}

ipv4FragmentedIdsLevelTable OBJECT-TYPE
	SYNTAX      SEQUENCE OF Ipv4FragmentedIdsLevelEntry
	MAX-ACCESS  not-accessible
	STATUS      current
	DESCRIPTION
	"Table for ipv4FragmentedIds"
	::={ipv4FragmentedIds 4}

ipv4FragmentedIdsLevelEntry OBJECT-TYPE
	SYNTAX      Ipv4FragmentedIdsLevelEntry
	MAX-ACCESS  not-accessible
	STATUS      current
	DESCRIPTION
	"Table entry for ipv4FragmentedIds"
	INDEX { ipv4FragmentedIdsLevelName }
	::={ipv4FragmentedIdsLevelTable 1}

Ipv4FragmentedIdsLevelEntry ::=
	SEQUENCE {
		ipv4FragmentedIdsLevelName	DisplayString,
		ipv4FragmentedIdsLevelVal	CounterBasedGauge64,
		ipv4FragmentedIdsLevelMax	CounterBasedGauge64
	}

ipv4FragmentedIdsLevelName OBJECT-TYPE
	SYNTAX      DisplayString
	MAX-ACCESS  not-accessible
	STATUS      current
	DESCRIPTION
	"Table entry display string for ipv4FragmentedIds"
	::={ipv4FragmentedIdsLevelEntry 1}

ipv4FragmentedIdsLevelVal OBJECT-TYPE
	SYNTAX	 CounterBasedGauge64
	MAX-ACCESS  read-only
	STATUS      current
	DESCRIPTION
	"Table entry attribute for ipv4FragmentedIds"
	::={ipv4FragmentedIdsLevelEntry 2}

ipv4FragmentedIdsLevelMax OBJECT-TYPE
	SYNTAX	 CounterBasedGauge64
	MAX-ACCESS  read-only
	STATUS      current
	DESCRIPTION
	"Table entry attribute for ipv4FragmentedIds"
	::={ipv4FragmentedIdsLevelEntry 4}


ipv4Fragments	OBJECT IDENTIFIER ::={ipv4 11}

ipv4FragmentsVal	OBJECT-TYPE
	SYNTAX	 CounterBasedGauge64
	MAX-ACCESS read-only
	STATUS current
	DESCRIPTION "Fragments in queue"

	::={ipv4Fragments 1}

ipv4FragmentsMax	OBJECT-TYPE
	SYNTAX	 CounterBasedGauge64
	MAX-ACCESS read-only
	STATUS current
	DESCRIPTION "Fragments in queue"

	::={ipv4Fragments 3}

ipv4FragmentsLevelTable OBJECT-TYPE
	SYNTAX      SEQUENCE OF Ipv4FragmentsLevelEntry
	MAX-ACCESS  not-accessible
	STATUS      current
	DESCRIPTION
	"Table for ipv4Fragments"
	::={ipv4Fragments 4}

ipv4FragmentsLevelEntry OBJECT-TYPE
	SYNTAX      Ipv4FragmentsLevelEntry
	MAX-ACCESS  not-accessible
	STATUS      current
	DESCRIPTION
	"Table entry for ipv4Fragments"
	INDEX { ipv4FragmentsLevelName }
	::={ipv4FragmentsLevelTable 1}

Ipv4FragmentsLevelEntry ::=
	SEQUENCE {
		ipv4FragmentsLevelName	DisplayString,
		ipv4FragmentsLevelVal	CounterBasedGauge64,
		ipv4FragmentsLevelMax	CounterBasedGauge64
	}

ipv4FragmentsLevelName OBJECT-TYPE
	SYNTAX      DisplayString
	MAX-ACCESS  not-accessible
	STATUS      current
	DESCRIPTION
	"Table entry display string for ipv4Fragments"
	::={ipv4FragmentsLevelEntry 1}

ipv4FragmentsLevelVal OBJECT-TYPE
	SYNTAX	 CounterBasedGauge64
	MAX-ACCESS  read-only
	STATUS      current
	DESCRIPTION
	"Table entry attribute for ipv4Fragments"
	::={ipv4FragmentsLevelEntry 2}

ipv4FragmentsLevelMax OBJECT-TYPE
	SYNTAX	 CounterBasedGauge64
	MAX-ACCESS  read-only
	STATUS      current
	DESCRIPTION
	"Table entry attribute for ipv4Fragments"
	::={ipv4FragmentsLevelEntry 4}


ipv4RefusedOof	OBJECT IDENTIFIER ::={ipv4 14}

ipv4RefusedOofVal	OBJECT-TYPE
	SYNTAX	 Counter64
	MAX-ACCESS read-only
	STATUS obsolete
	DESCRIPTION "Refused (out of fragments)"

	::={ipv4RefusedOof 1}

ipv4RefusedOofMom	OBJECT-TYPE
	SYNTAX	 CounterBasedGauge64
	MAX-ACCESS read-only
	STATUS obsolete
	DESCRIPTION "Refused (out of fragments)"

	::={ipv4RefusedOof 2}

ipv4RefusedOofMax	OBJECT-TYPE
	SYNTAX	 CounterBasedGauge64
	MAX-ACCESS read-only
	STATUS obsolete
	DESCRIPTION "Refused (out of fragments)"

	::={ipv4RefusedOof 3}

ipv4RefusedOofLevelTable OBJECT-TYPE
	SYNTAX      SEQUENCE OF Ipv4RefusedOofLevelEntry
	MAX-ACCESS  not-accessible
	STATUS      current
	DESCRIPTION
	"Table for ipv4RefusedOof"
	::={ipv4RefusedOof 4}

ipv4RefusedOofLevelEntry OBJECT-TYPE
	SYNTAX      Ipv4RefusedOofLevelEntry
	MAX-ACCESS  not-accessible
	STATUS      current
	DESCRIPTION
	"Table entry for ipv4RefusedOof"
	INDEX { ipv4RefusedOofLevelName }
	::={ipv4RefusedOofLevelTable 1}

Ipv4RefusedOofLevelEntry ::=
	SEQUENCE {
		ipv4RefusedOofLevelName	DisplayString,
		ipv4RefusedOofLevelVal	Counter64,
		ipv4RefusedOofLevelMom	CounterBasedGauge64,
		ipv4RefusedOofLevelMax	CounterBasedGauge64
	}

ipv4RefusedOofLevelName OBJECT-TYPE
	SYNTAX      DisplayString
	MAX-ACCESS  not-accessible
	STATUS      current
	DESCRIPTION
	"Table entry display string for ipv4RefusedOof"
	::={ipv4RefusedOofLevelEntry 1}

ipv4RefusedOofLevelVal OBJECT-TYPE
	SYNTAX	 Counter64
	MAX-ACCESS  read-only
	STATUS      current
	DESCRIPTION
	"Table entry attribute for ipv4RefusedOof"
	::={ipv4RefusedOofLevelEntry 2}

ipv4RefusedOofLevelMom OBJECT-TYPE
	SYNTAX	 CounterBasedGauge64
	MAX-ACCESS  read-only
	STATUS      current
	DESCRIPTION
	"Table entry attribute for ipv4RefusedOof"
	::={ipv4RefusedOofLevelEntry 3}

ipv4RefusedOofLevelMax OBJECT-TYPE
	SYNTAX	 CounterBasedGauge64
	MAX-ACCESS  read-only
	STATUS      current
	DESCRIPTION
	"Table entry attribute for ipv4RefusedOof"
	::={ipv4RefusedOofLevelEntry 4}


ipv4FragmentAllocationFailures	OBJECT IDENTIFIER ::={ipv4 15}

ipv4FragmentAllocationFailuresVal	OBJECT-TYPE
	SYNTAX	 Counter64
	MAX-ACCESS read-only
	STATUS current
	DESCRIPTION "Fragment allocation failures"

	::={ipv4FragmentAllocationFailures 1}

ipv4FragmentAllocationFailuresMom	OBJECT-TYPE
	SYNTAX	 CounterBasedGauge64
	MAX-ACCESS read-only
	STATUS current
	DESCRIPTION "Fragment allocation failures"

	::={ipv4FragmentAllocationFailures 2}

ipv4FragmentAllocationFailuresMax	OBJECT-TYPE
	SYNTAX	 CounterBasedGauge64
	MAX-ACCESS read-only
	STATUS current
	DESCRIPTION "Fragment allocation failures"

	::={ipv4FragmentAllocationFailures 3}

ipv4FragmentAllocationFailuresLevelTable OBJECT-TYPE
	SYNTAX      SEQUENCE OF Ipv4FragmentAllocationFailuresLevelEntry
	MAX-ACCESS  not-accessible
	STATUS      current
	DESCRIPTION
	"Table for ipv4FragmentAllocationFailures"
	::={ipv4FragmentAllocationFailures 4}

ipv4FragmentAllocationFailuresLevelEntry OBJECT-TYPE
	SYNTAX      Ipv4FragmentAllocationFailuresLevelEntry
	MAX-ACCESS  not-accessible
	STATUS      current
	DESCRIPTION
	"Table entry for ipv4FragmentAllocationFailures"
	INDEX { ipv4FragmentAllocationFailuresLevelName }
	::={ipv4FragmentAllocationFailuresLevelTable 1}

Ipv4FragmentAllocationFailuresLevelEntry ::=
	SEQUENCE {
		ipv4FragmentAllocationFailuresLevelName	DisplayString,
		ipv4FragmentAllocationFailuresLevelVal	Counter64,
		ipv4FragmentAllocationFailuresLevelMom	CounterBasedGauge64,
		ipv4FragmentAllocationFailuresLevelMax	CounterBasedGauge64
	}

ipv4FragmentAllocationFailuresLevelName OBJECT-TYPE
	SYNTAX      DisplayString
	MAX-ACCESS  not-accessible
	STATUS      current
	DESCRIPTION
	"Table entry display string for ipv4FragmentAllocationFailures"
	::={ipv4FragmentAllocationFailuresLevelEntry 1}

ipv4FragmentAllocationFailuresLevelVal OBJECT-TYPE
	SYNTAX	 Counter64
	MAX-ACCESS  read-only
	STATUS      current
	DESCRIPTION
	"Table entry attribute for ipv4FragmentAllocationFailures"
	::={ipv4FragmentAllocationFailuresLevelEntry 2}

ipv4FragmentAllocationFailuresLevelMom OBJECT-TYPE
	SYNTAX	 CounterBasedGauge64
	MAX-ACCESS  read-only
	STATUS      current
	DESCRIPTION
	"Table entry attribute for ipv4FragmentAllocationFailures"
	::={ipv4FragmentAllocationFailuresLevelEntry 3}

ipv4FragmentAllocationFailuresLevelMax OBJECT-TYPE
	SYNTAX	 CounterBasedGauge64
	MAX-ACCESS  read-only
	STATUS      current
	DESCRIPTION
	"Table entry attribute for ipv4FragmentAllocationFailures"
	::={ipv4FragmentAllocationFailuresLevelEntry 4}


ipv4FragmentReassFail	OBJECT IDENTIFIER ::={ipv4 16}

ipv4FragmentReassFailVal	OBJECT-TYPE
	SYNTAX	 Counter64
	MAX-ACCESS read-only
	STATUS current
	DESCRIPTION "Fragment reassembly failures"

	::={ipv4FragmentReassFail 1}

ipv4FragmentReassFailMom	OBJECT-TYPE
	SYNTAX	 CounterBasedGauge64
	MAX-ACCESS read-only
	STATUS current
	DESCRIPTION "Fragment reassembly failures"

	::={ipv4FragmentReassFail 2}

ipv4FragmentReassFailMax	OBJECT-TYPE
	SYNTAX	 CounterBasedGauge64
	MAX-ACCESS read-only
	STATUS current
	DESCRIPTION "Fragment reassembly failures"

	::={ipv4FragmentReassFail 3}

ipv4FragmentReassFailLevelTable OBJECT-TYPE
	SYNTAX      SEQUENCE OF Ipv4FragmentReassFailLevelEntry
	MAX-ACCESS  not-accessible
	STATUS      current
	DESCRIPTION
	"Table for ipv4FragmentReassFail"
	::={ipv4FragmentReassFail 4}

ipv4FragmentReassFailLevelEntry OBJECT-TYPE
	SYNTAX      Ipv4FragmentReassFailLevelEntry
	MAX-ACCESS  not-accessible
	STATUS      current
	DESCRIPTION
	"Table entry for ipv4FragmentReassFail"
	INDEX { ipv4FragmentReassFailLevelName }
	::={ipv4FragmentReassFailLevelTable 1}

Ipv4FragmentReassFailLevelEntry ::=
	SEQUENCE {
		ipv4FragmentReassFailLevelName	DisplayString,
		ipv4FragmentReassFailLevelVal	Counter64,
		ipv4FragmentReassFailLevelMom	CounterBasedGauge64,
		ipv4FragmentReassFailLevelMax	CounterBasedGauge64
	}

ipv4FragmentReassFailLevelName OBJECT-TYPE
	SYNTAX      DisplayString
	MAX-ACCESS  not-accessible
	STATUS      current
	DESCRIPTION
	"Table entry display string for ipv4FragmentReassFail"
	::={ipv4FragmentReassFailLevelEntry 1}

ipv4FragmentReassFailLevelVal OBJECT-TYPE
	SYNTAX	 Counter64
	MAX-ACCESS  read-only
	STATUS      current
	DESCRIPTION
	"Table entry attribute for ipv4FragmentReassFail"
	::={ipv4FragmentReassFailLevelEntry 2}

ipv4FragmentReassFailLevelMom OBJECT-TYPE
	SYNTAX	 CounterBasedGauge64
	MAX-ACCESS  read-only
	STATUS      current
	DESCRIPTION
	"Table entry attribute for ipv4FragmentReassFail"
	::={ipv4FragmentReassFailLevelEntry 3}

ipv4FragmentReassFailLevelMax OBJECT-TYPE
	SYNTAX	 CounterBasedGauge64
	MAX-ACCESS  read-only
	STATUS      current
	DESCRIPTION
	"Table entry attribute for ipv4FragmentReassFail"
	::={ipv4FragmentReassFailLevelEntry 4}


ipv4RefusedFilter	OBJECT IDENTIFIER ::={ipv4 17}

ipv4RefusedFilterVal	OBJECT-TYPE
	SYNTAX	 Counter64
	MAX-ACCESS read-only
	STATUS current
	DESCRIPTION "Packets refused by lowlevel filter"

	::={ipv4RefusedFilter 1}

ipv4RefusedFilterMom	OBJECT-TYPE
	SYNTAX	 CounterBasedGauge64
	MAX-ACCESS read-only
	STATUS current
	DESCRIPTION "Packets refused by lowlevel filter"

	::={ipv4RefusedFilter 2}

ipv4RefusedFilterMax	OBJECT-TYPE
	SYNTAX	 CounterBasedGauge64
	MAX-ACCESS read-only
	STATUS current
	DESCRIPTION "Packets refused by lowlevel filter"

	::={ipv4RefusedFilter 3}

ipv4RefusedFilterLevelTable OBJECT-TYPE
	SYNTAX      SEQUENCE OF Ipv4RefusedFilterLevelEntry
	MAX-ACCESS  not-accessible
	STATUS      current
	DESCRIPTION
	"Table for ipv4RefusedFilter"
	::={ipv4RefusedFilter 4}

ipv4RefusedFilterLevelEntry OBJECT-TYPE
	SYNTAX      Ipv4RefusedFilterLevelEntry
	MAX-ACCESS  not-accessible
	STATUS      current
	DESCRIPTION
	"Table entry for ipv4RefusedFilter"
	INDEX { ipv4RefusedFilterLevelName }
	::={ipv4RefusedFilterLevelTable 1}

Ipv4RefusedFilterLevelEntry ::=
	SEQUENCE {
		ipv4RefusedFilterLevelName	DisplayString,
		ipv4RefusedFilterLevelVal	Counter64,
		ipv4RefusedFilterLevelMom	CounterBasedGauge64,
		ipv4RefusedFilterLevelMax	CounterBasedGauge64
	}

ipv4RefusedFilterLevelName OBJECT-TYPE
	SYNTAX      DisplayString
	MAX-ACCESS  not-accessible
	STATUS      current
	DESCRIPTION
	"Table entry display string for ipv4RefusedFilter"
	::={ipv4RefusedFilterLevelEntry 1}

ipv4RefusedFilterLevelVal OBJECT-TYPE
	SYNTAX	 Counter64
	MAX-ACCESS  read-only
	STATUS      current
	DESCRIPTION
	"Table entry attribute for ipv4RefusedFilter"
	::={ipv4RefusedFilterLevelEntry 2}

ipv4RefusedFilterLevelMom OBJECT-TYPE
	SYNTAX	 CounterBasedGauge64
	MAX-ACCESS  read-only
	STATUS      current
	DESCRIPTION
	"Table entry attribute for ipv4RefusedFilter"
	::={ipv4RefusedFilterLevelEntry 3}

ipv4RefusedFilterLevelMax OBJECT-TYPE
	SYNTAX	 CounterBasedGauge64
	MAX-ACCESS  read-only
	STATUS      current
	DESCRIPTION
	"Table entry attribute for ipv4RefusedFilter"
	::={ipv4RefusedFilterLevelEntry 4}


ipv4FragmentTooNoisy	OBJECT IDENTIFIER ::={ipv4 19}

ipv4FragmentTooNoisyVal	OBJECT-TYPE
	SYNTAX	 Counter64
	MAX-ACCESS read-only
	STATUS current
	DESCRIPTION "Packets refused (too many fragments)"

	::={ipv4FragmentTooNoisy 1}

ipv4FragmentTooNoisyMom	OBJECT-TYPE
	SYNTAX	 CounterBasedGauge64
	MAX-ACCESS read-only
	STATUS current
	DESCRIPTION "Packets refused (too many fragments)"

	::={ipv4FragmentTooNoisy 2}

ipv4FragmentTooNoisyMax	OBJECT-TYPE
	SYNTAX	 CounterBasedGauge64
	MAX-ACCESS read-only
	STATUS current
	DESCRIPTION "Packets refused (too many fragments)"

	::={ipv4FragmentTooNoisy 3}

ipv4FragmentTooNoisyLevelTable OBJECT-TYPE
	SYNTAX      SEQUENCE OF Ipv4FragmentTooNoisyLevelEntry
	MAX-ACCESS  not-accessible
	STATUS      current
	DESCRIPTION
	"Table for ipv4FragmentTooNoisy"
	::={ipv4FragmentTooNoisy 4}

ipv4FragmentTooNoisyLevelEntry OBJECT-TYPE
	SYNTAX      Ipv4FragmentTooNoisyLevelEntry
	MAX-ACCESS  not-accessible
	STATUS      current
	DESCRIPTION
	"Table entry for ipv4FragmentTooNoisy"
	INDEX { ipv4FragmentTooNoisyLevelName }
	::={ipv4FragmentTooNoisyLevelTable 1}

Ipv4FragmentTooNoisyLevelEntry ::=
	SEQUENCE {
		ipv4FragmentTooNoisyLevelName	DisplayString,
		ipv4FragmentTooNoisyLevelVal	Counter64,
		ipv4FragmentTooNoisyLevelMom	CounterBasedGauge64,
		ipv4FragmentTooNoisyLevelMax	CounterBasedGauge64
	}

ipv4FragmentTooNoisyLevelName OBJECT-TYPE
	SYNTAX      DisplayString
	MAX-ACCESS  not-accessible
	STATUS      current
	DESCRIPTION
	"Table entry display string for ipv4FragmentTooNoisy"
	::={ipv4FragmentTooNoisyLevelEntry 1}

ipv4FragmentTooNoisyLevelVal OBJECT-TYPE
	SYNTAX	 Counter64
	MAX-ACCESS  read-only
	STATUS      current
	DESCRIPTION
	"Table entry attribute for ipv4FragmentTooNoisy"
	::={ipv4FragmentTooNoisyLevelEntry 2}

ipv4FragmentTooNoisyLevelMom OBJECT-TYPE
	SYNTAX	 CounterBasedGauge64
	MAX-ACCESS  read-only
	STATUS      current
	DESCRIPTION
	"Table entry attribute for ipv4FragmentTooNoisy"
	::={ipv4FragmentTooNoisyLevelEntry 3}

ipv4FragmentTooNoisyLevelMax OBJECT-TYPE
	SYNTAX	 CounterBasedGauge64
	MAX-ACCESS  read-only
	STATUS      current
	DESCRIPTION
	"Table entry attribute for ipv4FragmentTooNoisy"
	::={ipv4FragmentTooNoisyLevelEntry 4}


ipv4Reassembled	OBJECT IDENTIFIER ::={ipv4 20}

ipv4ReassembledVal	OBJECT-TYPE
	SYNTAX	 Counter64
	MAX-ACCESS read-only
	STATUS current
	DESCRIPTION "Reassembled packets"

	::={ipv4Reassembled 1}

ipv4ReassembledMom	OBJECT-TYPE
	SYNTAX	 CounterBasedGauge64
	MAX-ACCESS read-only
	STATUS current
	DESCRIPTION "Reassembled packets"

	::={ipv4Reassembled 2}

ipv4ReassembledMax	OBJECT-TYPE
	SYNTAX	 CounterBasedGauge64
	MAX-ACCESS read-only
	STATUS current
	DESCRIPTION "Reassembled packets"

	::={ipv4Reassembled 3}

ipv4ReassembledLevelTable OBJECT-TYPE
	SYNTAX      SEQUENCE OF Ipv4ReassembledLevelEntry
	MAX-ACCESS  not-accessible
	STATUS      current
	DESCRIPTION
	"Table for ipv4Reassembled"
	::={ipv4Reassembled 4}

ipv4ReassembledLevelEntry OBJECT-TYPE
	SYNTAX      Ipv4ReassembledLevelEntry
	MAX-ACCESS  not-accessible
	STATUS      current
	DESCRIPTION
	"Table entry for ipv4Reassembled"
	INDEX { ipv4ReassembledLevelName }
	::={ipv4ReassembledLevelTable 1}

Ipv4ReassembledLevelEntry ::=
	SEQUENCE {
		ipv4ReassembledLevelName	DisplayString,
		ipv4ReassembledLevelVal	Counter64,
		ipv4ReassembledLevelMom	CounterBasedGauge64,
		ipv4ReassembledLevelMax	CounterBasedGauge64
	}

ipv4ReassembledLevelName OBJECT-TYPE
	SYNTAX      DisplayString
	MAX-ACCESS  not-accessible
	STATUS      current
	DESCRIPTION
	"Table entry display string for ipv4Reassembled"
	::={ipv4ReassembledLevelEntry 1}

ipv4ReassembledLevelVal OBJECT-TYPE
	SYNTAX	 Counter64
	MAX-ACCESS  read-only
	STATUS      current
	DESCRIPTION
	"Table entry attribute for ipv4Reassembled"
	::={ipv4ReassembledLevelEntry 2}

ipv4ReassembledLevelMom OBJECT-TYPE
	SYNTAX	 CounterBasedGauge64
	MAX-ACCESS  read-only
	STATUS      current
	DESCRIPTION
	"Table entry attribute for ipv4Reassembled"
	::={ipv4ReassembledLevelEntry 3}

ipv4ReassembledLevelMax OBJECT-TYPE
	SYNTAX	 CounterBasedGauge64
	MAX-ACCESS  read-only
	STATUS      current
	DESCRIPTION
	"Table entry attribute for ipv4Reassembled"
	::={ipv4ReassembledLevelEntry 4}


ipv4FragmentDrops	OBJECT IDENTIFIER ::={ipv4 21}

ipv4FragmentDropsVal	OBJECT-TYPE
	SYNTAX	 Counter64
	MAX-ACCESS read-only
	STATUS current
	DESCRIPTION "Dropped fragments (timeout/LRU)"

	::={ipv4FragmentDrops 1}

ipv4FragmentDropsMom	OBJECT-TYPE
	SYNTAX	 CounterBasedGauge64
	MAX-ACCESS read-only
	STATUS current
	DESCRIPTION "Dropped fragments (timeout/LRU)"

	::={ipv4FragmentDrops 2}

ipv4FragmentDropsMax	OBJECT-TYPE
	SYNTAX	 CounterBasedGauge64
	MAX-ACCESS read-only
	STATUS current
	DESCRIPTION "Dropped fragments (timeout/LRU)"

	::={ipv4FragmentDrops 3}

ipv4FragmentDropsLevelTable OBJECT-TYPE
	SYNTAX      SEQUENCE OF Ipv4FragmentDropsLevelEntry
	MAX-ACCESS  not-accessible
	STATUS      current
	DESCRIPTION
	"Table for ipv4FragmentDrops"
	::={ipv4FragmentDrops 4}

ipv4FragmentDropsLevelEntry OBJECT-TYPE
	SYNTAX      Ipv4FragmentDropsLevelEntry
	MAX-ACCESS  not-accessible
	STATUS      current
	DESCRIPTION
	"Table entry for ipv4FragmentDrops"
	INDEX { ipv4FragmentDropsLevelName }
	::={ipv4FragmentDropsLevelTable 1}

Ipv4FragmentDropsLevelEntry ::=
	SEQUENCE {
		ipv4FragmentDropsLevelName	DisplayString,
		ipv4FragmentDropsLevelVal	Counter64,
		ipv4FragmentDropsLevelMom	CounterBasedGauge64,
		ipv4FragmentDropsLevelMax	CounterBasedGauge64
	}

ipv4FragmentDropsLevelName OBJECT-TYPE
	SYNTAX      DisplayString
	MAX-ACCESS  not-accessible
	STATUS      current
	DESCRIPTION
	"Table entry display string for ipv4FragmentDrops"
	::={ipv4FragmentDropsLevelEntry 1}

ipv4FragmentDropsLevelVal OBJECT-TYPE
	SYNTAX	 Counter64
	MAX-ACCESS  read-only
	STATUS      current
	DESCRIPTION
	"Table entry attribute for ipv4FragmentDrops"
	::={ipv4FragmentDropsLevelEntry 2}

ipv4FragmentDropsLevelMom OBJECT-TYPE
	SYNTAX	 CounterBasedGauge64
	MAX-ACCESS  read-only
	STATUS      current
	DESCRIPTION
	"Table entry attribute for ipv4FragmentDrops"
	::={ipv4FragmentDropsLevelEntry 3}

ipv4FragmentDropsLevelMax OBJECT-TYPE
	SYNTAX	 CounterBasedGauge64
	MAX-ACCESS  read-only
	STATUS      current
	DESCRIPTION
	"Table entry attribute for ipv4FragmentDrops"
	::={ipv4FragmentDropsLevelEntry 4}


ipv4ShuntAddressPackets	OBJECT IDENTIFIER ::={ipv4 35}

ipv4ShuntAddressPacketsVal	OBJECT-TYPE
	SYNTAX	 Counter64
	MAX-ACCESS read-only
	STATUS current
	DESCRIPTION "Shunted packets (address)"

	::={ipv4ShuntAddressPackets 1}

ipv4ShuntAddressPacketsMom	OBJECT-TYPE
	SYNTAX	 CounterBasedGauge64
	MAX-ACCESS read-only
	STATUS current
	DESCRIPTION "Shunted packets (address)"

	::={ipv4ShuntAddressPackets 2}

ipv4ShuntAddressPacketsMax	OBJECT-TYPE
	SYNTAX	 CounterBasedGauge64
	MAX-ACCESS read-only
	STATUS current
	DESCRIPTION "Shunted packets (address)"

	::={ipv4ShuntAddressPackets 3}

ipv4ShuntAddressPacketsLevelTable OBJECT-TYPE
	SYNTAX      SEQUENCE OF Ipv4ShuntAddressPacketsLevelEntry
	MAX-ACCESS  not-accessible
	STATUS      current
	DESCRIPTION
	"Table for ipv4ShuntAddressPackets"
	::={ipv4ShuntAddressPackets 4}

ipv4ShuntAddressPacketsLevelEntry OBJECT-TYPE
	SYNTAX      Ipv4ShuntAddressPacketsLevelEntry
	MAX-ACCESS  not-accessible
	STATUS      current
	DESCRIPTION
	"Table entry for ipv4ShuntAddressPackets"
	INDEX { ipv4ShuntAddressPacketsLevelName }
	::={ipv4ShuntAddressPacketsLevelTable 1}

Ipv4ShuntAddressPacketsLevelEntry ::=
	SEQUENCE {
		ipv4ShuntAddressPacketsLevelName	DisplayString,
		ipv4ShuntAddressPacketsLevelVal	Counter64,
		ipv4ShuntAddressPacketsLevelMom	CounterBasedGauge64,
		ipv4ShuntAddressPacketsLevelMax	CounterBasedGauge64
	}

ipv4ShuntAddressPacketsLevelName OBJECT-TYPE
	SYNTAX      DisplayString
	MAX-ACCESS  not-accessible
	STATUS      current
	DESCRIPTION
	"Table entry display string for ipv4ShuntAddressPackets"
	::={ipv4ShuntAddressPacketsLevelEntry 1}

ipv4ShuntAddressPacketsLevelVal OBJECT-TYPE
	SYNTAX	 Counter64
	MAX-ACCESS  read-only
	STATUS      current
	DESCRIPTION
	"Table entry attribute for ipv4ShuntAddressPackets"
	::={ipv4ShuntAddressPacketsLevelEntry 2}

ipv4ShuntAddressPacketsLevelMom OBJECT-TYPE
	SYNTAX	 CounterBasedGauge64
	MAX-ACCESS  read-only
	STATUS      current
	DESCRIPTION
	"Table entry attribute for ipv4ShuntAddressPackets"
	::={ipv4ShuntAddressPacketsLevelEntry 3}

ipv4ShuntAddressPacketsLevelMax OBJECT-TYPE
	SYNTAX	 CounterBasedGauge64
	MAX-ACCESS  read-only
	STATUS      current
	DESCRIPTION
	"Table entry attribute for ipv4ShuntAddressPackets"
	::={ipv4ShuntAddressPacketsLevelEntry 4}


ipv4ShuntAddressBytes	OBJECT IDENTIFIER ::={ipv4 36}

ipv4ShuntAddressBytesVal	OBJECT-TYPE
	SYNTAX	 Counter64
	MAX-ACCESS read-only
	STATUS current
	DESCRIPTION "Shunted bytes (address)"

	::={ipv4ShuntAddressBytes 1}

ipv4ShuntAddressBytesMom	OBJECT-TYPE
	SYNTAX	 CounterBasedGauge64
	MAX-ACCESS read-only
	STATUS current
	DESCRIPTION "Shunted bytes (address)"

	::={ipv4ShuntAddressBytes 2}

ipv4ShuntAddressBytesMax	OBJECT-TYPE
	SYNTAX	 CounterBasedGauge64
	MAX-ACCESS read-only
	STATUS current
	DESCRIPTION "Shunted bytes (address)"

	::={ipv4ShuntAddressBytes 3}

ipv4ShuntAddressBytesLevelTable OBJECT-TYPE
	SYNTAX      SEQUENCE OF Ipv4ShuntAddressBytesLevelEntry
	MAX-ACCESS  not-accessible
	STATUS      current
	DESCRIPTION
	"Table for ipv4ShuntAddressBytes"
	::={ipv4ShuntAddressBytes 4}

ipv4ShuntAddressBytesLevelEntry OBJECT-TYPE
	SYNTAX      Ipv4ShuntAddressBytesLevelEntry
	MAX-ACCESS  not-accessible
	STATUS      current
	DESCRIPTION
	"Table entry for ipv4ShuntAddressBytes"
	INDEX { ipv4ShuntAddressBytesLevelName }
	::={ipv4ShuntAddressBytesLevelTable 1}

Ipv4ShuntAddressBytesLevelEntry ::=
	SEQUENCE {
		ipv4ShuntAddressBytesLevelName	DisplayString,
		ipv4ShuntAddressBytesLevelVal	Counter64,
		ipv4ShuntAddressBytesLevelMom	CounterBasedGauge64,
		ipv4ShuntAddressBytesLevelMax	CounterBasedGauge64
	}

ipv4ShuntAddressBytesLevelName OBJECT-TYPE
	SYNTAX      DisplayString
	MAX-ACCESS  not-accessible
	STATUS      current
	DESCRIPTION
	"Table entry display string for ipv4ShuntAddressBytes"
	::={ipv4ShuntAddressBytesLevelEntry 1}

ipv4ShuntAddressBytesLevelVal OBJECT-TYPE
	SYNTAX	 Counter64
	MAX-ACCESS  read-only
	STATUS      current
	DESCRIPTION
	"Table entry attribute for ipv4ShuntAddressBytes"
	::={ipv4ShuntAddressBytesLevelEntry 2}

ipv4ShuntAddressBytesLevelMom OBJECT-TYPE
	SYNTAX	 CounterBasedGauge64
	MAX-ACCESS  read-only
	STATUS      current
	DESCRIPTION
	"Table entry attribute for ipv4ShuntAddressBytes"
	::={ipv4ShuntAddressBytesLevelEntry 3}

ipv4ShuntAddressBytesLevelMax OBJECT-TYPE
	SYNTAX	 CounterBasedGauge64
	MAX-ACCESS  read-only
	STATUS      current
	DESCRIPTION
	"Table entry attribute for ipv4ShuntAddressBytes"
	::={ipv4ShuntAddressBytesLevelEntry 4}


ipv4ShuntProtoPackets	OBJECT IDENTIFIER ::={ipv4 37}

ipv4ShuntProtoPacketsVal	OBJECT-TYPE
	SYNTAX	 Counter64
	MAX-ACCESS read-only
	STATUS current
	DESCRIPTION "Shunted packets (protocol)"

	::={ipv4ShuntProtoPackets 1}

ipv4ShuntProtoPacketsMom	OBJECT-TYPE
	SYNTAX	 CounterBasedGauge64
	MAX-ACCESS read-only
	STATUS current
	DESCRIPTION "Shunted packets (protocol)"

	::={ipv4ShuntProtoPackets 2}

ipv4ShuntProtoPacketsMax	OBJECT-TYPE
	SYNTAX	 CounterBasedGauge64
	MAX-ACCESS read-only
	STATUS current
	DESCRIPTION "Shunted packets (protocol)"

	::={ipv4ShuntProtoPackets 3}

ipv4ShuntProtoPacketsLevelTable OBJECT-TYPE
	SYNTAX      SEQUENCE OF Ipv4ShuntProtoPacketsLevelEntry
	MAX-ACCESS  not-accessible
	STATUS      current
	DESCRIPTION
	"Table for ipv4ShuntProtoPackets"
	::={ipv4ShuntProtoPackets 4}

ipv4ShuntProtoPacketsLevelEntry OBJECT-TYPE
	SYNTAX      Ipv4ShuntProtoPacketsLevelEntry
	MAX-ACCESS  not-accessible
	STATUS      current
	DESCRIPTION
	"Table entry for ipv4ShuntProtoPackets"
	INDEX { ipv4ShuntProtoPacketsLevelName }
	::={ipv4ShuntProtoPacketsLevelTable 1}

Ipv4ShuntProtoPacketsLevelEntry ::=
	SEQUENCE {
		ipv4ShuntProtoPacketsLevelName	DisplayString,
		ipv4ShuntProtoPacketsLevelVal	Counter64,
		ipv4ShuntProtoPacketsLevelMom	CounterBasedGauge64,
		ipv4ShuntProtoPacketsLevelMax	CounterBasedGauge64
	}

ipv4ShuntProtoPacketsLevelName OBJECT-TYPE
	SYNTAX      DisplayString
	MAX-ACCESS  not-accessible
	STATUS      current
	DESCRIPTION
	"Table entry display string for ipv4ShuntProtoPackets"
	::={ipv4ShuntProtoPacketsLevelEntry 1}

ipv4ShuntProtoPacketsLevelVal OBJECT-TYPE
	SYNTAX	 Counter64
	MAX-ACCESS  read-only
	STATUS      current
	DESCRIPTION
	"Table entry attribute for ipv4ShuntProtoPackets"
	::={ipv4ShuntProtoPacketsLevelEntry 2}

ipv4ShuntProtoPacketsLevelMom OBJECT-TYPE
	SYNTAX	 CounterBasedGauge64
	MAX-ACCESS  read-only
	STATUS      current
	DESCRIPTION
	"Table entry attribute for ipv4ShuntProtoPackets"
	::={ipv4ShuntProtoPacketsLevelEntry 3}

ipv4ShuntProtoPacketsLevelMax OBJECT-TYPE
	SYNTAX	 CounterBasedGauge64
	MAX-ACCESS  read-only
	STATUS      current
	DESCRIPTION
	"Table entry attribute for ipv4ShuntProtoPackets"
	::={ipv4ShuntProtoPacketsLevelEntry 4}


ipv4ShuntProtoBytes	OBJECT IDENTIFIER ::={ipv4 38}

ipv4ShuntProtoBytesVal	OBJECT-TYPE
	SYNTAX	 Counter64
	MAX-ACCESS read-only
	STATUS current
	DESCRIPTION "Shunted bytes (protocol)"

	::={ipv4ShuntProtoBytes 1}

ipv4ShuntProtoBytesMom	OBJECT-TYPE
	SYNTAX	 CounterBasedGauge64
	MAX-ACCESS read-only
	STATUS current
	DESCRIPTION "Shunted bytes (protocol)"

	::={ipv4ShuntProtoBytes 2}

ipv4ShuntProtoBytesMax	OBJECT-TYPE
	SYNTAX	 CounterBasedGauge64
	MAX-ACCESS read-only
	STATUS current
	DESCRIPTION "Shunted bytes (protocol)"

	::={ipv4ShuntProtoBytes 3}

ipv4ShuntProtoBytesLevelTable OBJECT-TYPE
	SYNTAX      SEQUENCE OF Ipv4ShuntProtoBytesLevelEntry
	MAX-ACCESS  not-accessible
	STATUS      current
	DESCRIPTION
	"Table for ipv4ShuntProtoBytes"
	::={ipv4ShuntProtoBytes 4}

ipv4ShuntProtoBytesLevelEntry OBJECT-TYPE
	SYNTAX      Ipv4ShuntProtoBytesLevelEntry
	MAX-ACCESS  not-accessible
	STATUS      current
	DESCRIPTION
	"Table entry for ipv4ShuntProtoBytes"
	INDEX { ipv4ShuntProtoBytesLevelName }
	::={ipv4ShuntProtoBytesLevelTable 1}

Ipv4ShuntProtoBytesLevelEntry ::=
	SEQUENCE {
		ipv4ShuntProtoBytesLevelName	DisplayString,
		ipv4ShuntProtoBytesLevelVal	Counter64,
		ipv4ShuntProtoBytesLevelMom	CounterBasedGauge64,
		ipv4ShuntProtoBytesLevelMax	CounterBasedGauge64
	}

ipv4ShuntProtoBytesLevelName OBJECT-TYPE
	SYNTAX      DisplayString
	MAX-ACCESS  not-accessible
	STATUS      current
	DESCRIPTION
	"Table entry display string for ipv4ShuntProtoBytes"
	::={ipv4ShuntProtoBytesLevelEntry 1}

ipv4ShuntProtoBytesLevelVal OBJECT-TYPE
	SYNTAX	 Counter64
	MAX-ACCESS  read-only
	STATUS      current
	DESCRIPTION
	"Table entry attribute for ipv4ShuntProtoBytes"
	::={ipv4ShuntProtoBytesLevelEntry 2}

ipv4ShuntProtoBytesLevelMom OBJECT-TYPE
	SYNTAX	 CounterBasedGauge64
	MAX-ACCESS  read-only
	STATUS      current
	DESCRIPTION
	"Table entry attribute for ipv4ShuntProtoBytes"
	::={ipv4ShuntProtoBytesLevelEntry 3}

ipv4ShuntProtoBytesLevelMax OBJECT-TYPE
	SYNTAX	 CounterBasedGauge64
	MAX-ACCESS  read-only
	STATUS      current
	DESCRIPTION
	"Table entry attribute for ipv4ShuntProtoBytes"
	::={ipv4ShuntProtoBytesLevelEntry 4}


ipv4EcnEct0	OBJECT IDENTIFIER ::={ipv4 39}

ipv4EcnEct0Val	OBJECT-TYPE
	SYNTAX	 Counter64
	MAX-ACCESS read-only
	STATUS current
	DESCRIPTION "ECN Capable Packets ECT(0)"

	::={ipv4EcnEct0 1}

ipv4EcnEct0Mom	OBJECT-TYPE
	SYNTAX	 CounterBasedGauge64
	MAX-ACCESS read-only
	STATUS current
	DESCRIPTION "ECN Capable Packets ECT(0)"

	::={ipv4EcnEct0 2}

ipv4EcnEct0Max	OBJECT-TYPE
	SYNTAX	 CounterBasedGauge64
	MAX-ACCESS read-only
	STATUS current
	DESCRIPTION "ECN Capable Packets ECT(0)"

	::={ipv4EcnEct0 3}

ipv4EcnEct0LevelTable OBJECT-TYPE
	SYNTAX      SEQUENCE OF Ipv4EcnEct0LevelEntry
	MAX-ACCESS  not-accessible
	STATUS      current
	DESCRIPTION
	"Table for ipv4EcnEct0"
	::={ipv4EcnEct0 4}

ipv4EcnEct0LevelEntry OBJECT-TYPE
	SYNTAX      Ipv4EcnEct0LevelEntry
	MAX-ACCESS  not-accessible
	STATUS      current
	DESCRIPTION
	"Table entry for ipv4EcnEct0"
	INDEX { ipv4EcnEct0LevelName }
	::={ipv4EcnEct0LevelTable 1}

Ipv4EcnEct0LevelEntry ::=
	SEQUENCE {
		ipv4EcnEct0LevelName	DisplayString,
		ipv4EcnEct0LevelVal	Counter64,
		ipv4EcnEct0LevelMom	CounterBasedGauge64,
		ipv4EcnEct0LevelMax	CounterBasedGauge64
	}

ipv4EcnEct0LevelName OBJECT-TYPE
	SYNTAX      DisplayString
	MAX-ACCESS  not-accessible
	STATUS      current
	DESCRIPTION
	"Table entry display string for ipv4EcnEct0"
	::={ipv4EcnEct0LevelEntry 1}

ipv4EcnEct0LevelVal OBJECT-TYPE
	SYNTAX	 Counter64
	MAX-ACCESS  read-only
	STATUS      current
	DESCRIPTION
	"Table entry attribute for ipv4EcnEct0"
	::={ipv4EcnEct0LevelEntry 2}

ipv4EcnEct0LevelMom OBJECT-TYPE
	SYNTAX	 CounterBasedGauge64
	MAX-ACCESS  read-only
	STATUS      current
	DESCRIPTION
	"Table entry attribute for ipv4EcnEct0"
	::={ipv4EcnEct0LevelEntry 3}

ipv4EcnEct0LevelMax OBJECT-TYPE
	SYNTAX	 CounterBasedGauge64
	MAX-ACCESS  read-only
	STATUS      current
	DESCRIPTION
	"Table entry attribute for ipv4EcnEct0"
	::={ipv4EcnEct0LevelEntry 4}


ipv4EcnEct1	OBJECT IDENTIFIER ::={ipv4 40}

ipv4EcnEct1Val	OBJECT-TYPE
	SYNTAX	 Counter64
	MAX-ACCESS read-only
	STATUS current
	DESCRIPTION "ECN Capable Packets ECT(1)"

	::={ipv4EcnEct1 1}

ipv4EcnEct1Mom	OBJECT-TYPE
	SYNTAX	 CounterBasedGauge64
	MAX-ACCESS read-only
	STATUS current
	DESCRIPTION "ECN Capable Packets ECT(1)"

	::={ipv4EcnEct1 2}

ipv4EcnEct1Max	OBJECT-TYPE
	SYNTAX	 CounterBasedGauge64
	MAX-ACCESS read-only
	STATUS current
	DESCRIPTION "ECN Capable Packets ECT(1)"

	::={ipv4EcnEct1 3}

ipv4EcnEct1LevelTable OBJECT-TYPE
	SYNTAX      SEQUENCE OF Ipv4EcnEct1LevelEntry
	MAX-ACCESS  not-accessible
	STATUS      current
	DESCRIPTION
	"Table for ipv4EcnEct1"
	::={ipv4EcnEct1 4}

ipv4EcnEct1LevelEntry OBJECT-TYPE
	SYNTAX      Ipv4EcnEct1LevelEntry
	MAX-ACCESS  not-accessible
	STATUS      current
	DESCRIPTION
	"Table entry for ipv4EcnEct1"
	INDEX { ipv4EcnEct1LevelName }
	::={ipv4EcnEct1LevelTable 1}

Ipv4EcnEct1LevelEntry ::=
	SEQUENCE {
		ipv4EcnEct1LevelName	DisplayString,
		ipv4EcnEct1LevelVal	Counter64,
		ipv4EcnEct1LevelMom	CounterBasedGauge64,
		ipv4EcnEct1LevelMax	CounterBasedGauge64
	}

ipv4EcnEct1LevelName OBJECT-TYPE
	SYNTAX      DisplayString
	MAX-ACCESS  not-accessible
	STATUS      current
	DESCRIPTION
	"Table entry display string for ipv4EcnEct1"
	::={ipv4EcnEct1LevelEntry 1}

ipv4EcnEct1LevelVal OBJECT-TYPE
	SYNTAX	 Counter64
	MAX-ACCESS  read-only
	STATUS      current
	DESCRIPTION
	"Table entry attribute for ipv4EcnEct1"
	::={ipv4EcnEct1LevelEntry 2}

ipv4EcnEct1LevelMom OBJECT-TYPE
	SYNTAX	 CounterBasedGauge64
	MAX-ACCESS  read-only
	STATUS      current
	DESCRIPTION
	"Table entry attribute for ipv4EcnEct1"
	::={ipv4EcnEct1LevelEntry 3}

ipv4EcnEct1LevelMax OBJECT-TYPE
	SYNTAX	 CounterBasedGauge64
	MAX-ACCESS  read-only
	STATUS      current
	DESCRIPTION
	"Table entry attribute for ipv4EcnEct1"
	::={ipv4EcnEct1LevelEntry 4}


ipv4EcnCn	OBJECT IDENTIFIER ::={ipv4 41}

ipv4EcnCnVal	OBJECT-TYPE
	SYNTAX	 Counter64
	MAX-ACCESS read-only
	STATUS current
	DESCRIPTION "ECN Packets Congestion Experienced"

	::={ipv4EcnCn 1}

ipv4EcnCnMom	OBJECT-TYPE
	SYNTAX	 CounterBasedGauge64
	MAX-ACCESS read-only
	STATUS current
	DESCRIPTION "ECN Packets Congestion Experienced"

	::={ipv4EcnCn 2}

ipv4EcnCnMax	OBJECT-TYPE
	SYNTAX	 CounterBasedGauge64
	MAX-ACCESS read-only
	STATUS current
	DESCRIPTION "ECN Packets Congestion Experienced"

	::={ipv4EcnCn 3}

ipv4EcnCnLevelTable OBJECT-TYPE
	SYNTAX      SEQUENCE OF Ipv4EcnCnLevelEntry
	MAX-ACCESS  not-accessible
	STATUS      current
	DESCRIPTION
	"Table for ipv4EcnCn"
	::={ipv4EcnCn 4}

ipv4EcnCnLevelEntry OBJECT-TYPE
	SYNTAX      Ipv4EcnCnLevelEntry
	MAX-ACCESS  not-accessible
	STATUS      current
	DESCRIPTION
	"Table entry for ipv4EcnCn"
	INDEX { ipv4EcnCnLevelName }
	::={ipv4EcnCnLevelTable 1}

Ipv4EcnCnLevelEntry ::=
	SEQUENCE {
		ipv4EcnCnLevelName	DisplayString,
		ipv4EcnCnLevelVal	Counter64,
		ipv4EcnCnLevelMom	CounterBasedGauge64,
		ipv4EcnCnLevelMax	CounterBasedGauge64
	}

ipv4EcnCnLevelName OBJECT-TYPE
	SYNTAX      DisplayString
	MAX-ACCESS  not-accessible
	STATUS      current
	DESCRIPTION
	"Table entry display string for ipv4EcnCn"
	::={ipv4EcnCnLevelEntry 1}

ipv4EcnCnLevelVal OBJECT-TYPE
	SYNTAX	 Counter64
	MAX-ACCESS  read-only
	STATUS      current
	DESCRIPTION
	"Table entry attribute for ipv4EcnCn"
	::={ipv4EcnCnLevelEntry 2}

ipv4EcnCnLevelMom OBJECT-TYPE
	SYNTAX	 CounterBasedGauge64
	MAX-ACCESS  read-only
	STATUS      current
	DESCRIPTION
	"Table entry attribute for ipv4EcnCn"
	::={ipv4EcnCnLevelEntry 3}

ipv4EcnCnLevelMax OBJECT-TYPE
	SYNTAX	 CounterBasedGauge64
	MAX-ACCESS  read-only
	STATUS      current
	DESCRIPTION
	"Table entry attribute for ipv4EcnCn"
	::={ipv4EcnCnLevelEntry 4}


ipv4FragmentRateLimitDrops	OBJECT IDENTIFIER ::={ipv4 42}

ipv4FragmentRateLimitDropsVal	OBJECT-TYPE
	SYNTAX	 Counter64
	MAX-ACCESS read-only
	STATUS current
	DESCRIPTION "Reassembly refused (Rate Limit)"

	::={ipv4FragmentRateLimitDrops 1}

ipv4FragmentRateLimitDropsMom	OBJECT-TYPE
	SYNTAX	 CounterBasedGauge64
	MAX-ACCESS read-only
	STATUS current
	DESCRIPTION "Reassembly refused (Rate Limit)"

	::={ipv4FragmentRateLimitDrops 2}

ipv4FragmentRateLimitDropsMax	OBJECT-TYPE
	SYNTAX	 CounterBasedGauge64
	MAX-ACCESS read-only
	STATUS current
	DESCRIPTION "Reassembly refused (Rate Limit)"

	::={ipv4FragmentRateLimitDrops 3}

ipv4FragmentRateLimitDropsLevelTable OBJECT-TYPE
	SYNTAX      SEQUENCE OF Ipv4FragmentRateLimitDropsLevelEntry
	MAX-ACCESS  not-accessible
	STATUS      current
	DESCRIPTION
	"Table for ipv4FragmentRateLimitDrops"
	::={ipv4FragmentRateLimitDrops 4}

ipv4FragmentRateLimitDropsLevelEntry OBJECT-TYPE
	SYNTAX      Ipv4FragmentRateLimitDropsLevelEntry
	MAX-ACCESS  not-accessible
	STATUS      current
	DESCRIPTION
	"Table entry for ipv4FragmentRateLimitDrops"
	INDEX { ipv4FragmentRateLimitDropsLevelName }
	::={ipv4FragmentRateLimitDropsLevelTable 1}

Ipv4FragmentRateLimitDropsLevelEntry ::=
	SEQUENCE {
		ipv4FragmentRateLimitDropsLevelName	DisplayString,
		ipv4FragmentRateLimitDropsLevelVal	Counter64,
		ipv4FragmentRateLimitDropsLevelMom	CounterBasedGauge64,
		ipv4FragmentRateLimitDropsLevelMax	CounterBasedGauge64
	}

ipv4FragmentRateLimitDropsLevelName OBJECT-TYPE
	SYNTAX      DisplayString
	MAX-ACCESS  not-accessible
	STATUS      current
	DESCRIPTION
	"Table entry display string for ipv4FragmentRateLimitDrops"
	::={ipv4FragmentRateLimitDropsLevelEntry 1}

ipv4FragmentRateLimitDropsLevelVal OBJECT-TYPE
	SYNTAX	 Counter64
	MAX-ACCESS  read-only
	STATUS      current
	DESCRIPTION
	"Table entry attribute for ipv4FragmentRateLimitDrops"
	::={ipv4FragmentRateLimitDropsLevelEntry 2}

ipv4FragmentRateLimitDropsLevelMom OBJECT-TYPE
	SYNTAX	 CounterBasedGauge64
	MAX-ACCESS  read-only
	STATUS      current
	DESCRIPTION
	"Table entry attribute for ipv4FragmentRateLimitDrops"
	::={ipv4FragmentRateLimitDropsLevelEntry 3}

ipv4FragmentRateLimitDropsLevelMax OBJECT-TYPE
	SYNTAX	 CounterBasedGauge64
	MAX-ACCESS  read-only
	STATUS      current
	DESCRIPTION
	"Table entry attribute for ipv4FragmentRateLimitDrops"
	::={ipv4FragmentRateLimitDropsLevelEntry 4}


ipv4ShuntDscpPackets	OBJECT IDENTIFIER ::={ipv4 43}

ipv4ShuntDscpPacketsVal	OBJECT-TYPE
	SYNTAX	 Counter64
	MAX-ACCESS read-only
	STATUS current
	DESCRIPTION "Shunted packets (DSCP)"

	::={ipv4ShuntDscpPackets 1}

ipv4ShuntDscpPacketsMom	OBJECT-TYPE
	SYNTAX	 CounterBasedGauge64
	MAX-ACCESS read-only
	STATUS current
	DESCRIPTION "Shunted packets (DSCP)"

	::={ipv4ShuntDscpPackets 2}

ipv4ShuntDscpPacketsMax	OBJECT-TYPE
	SYNTAX	 CounterBasedGauge64
	MAX-ACCESS read-only
	STATUS current
	DESCRIPTION "Shunted packets (DSCP)"

	::={ipv4ShuntDscpPackets 3}

ipv4ShuntDscpPacketsLevelTable OBJECT-TYPE
	SYNTAX      SEQUENCE OF Ipv4ShuntDscpPacketsLevelEntry
	MAX-ACCESS  not-accessible
	STATUS      current
	DESCRIPTION
	"Table for ipv4ShuntDscpPackets"
	::={ipv4ShuntDscpPackets 4}

ipv4ShuntDscpPacketsLevelEntry OBJECT-TYPE
	SYNTAX      Ipv4ShuntDscpPacketsLevelEntry
	MAX-ACCESS  not-accessible
	STATUS      current
	DESCRIPTION
	"Table entry for ipv4ShuntDscpPackets"
	INDEX { ipv4ShuntDscpPacketsLevelName }
	::={ipv4ShuntDscpPacketsLevelTable 1}

Ipv4ShuntDscpPacketsLevelEntry ::=
	SEQUENCE {
		ipv4ShuntDscpPacketsLevelName	DisplayString,
		ipv4ShuntDscpPacketsLevelVal	Counter64,
		ipv4ShuntDscpPacketsLevelMom	CounterBasedGauge64,
		ipv4ShuntDscpPacketsLevelMax	CounterBasedGauge64
	}

ipv4ShuntDscpPacketsLevelName OBJECT-TYPE
	SYNTAX      DisplayString
	MAX-ACCESS  not-accessible
	STATUS      current
	DESCRIPTION
	"Table entry display string for ipv4ShuntDscpPackets"
	::={ipv4ShuntDscpPacketsLevelEntry 1}

ipv4ShuntDscpPacketsLevelVal OBJECT-TYPE
	SYNTAX	 Counter64
	MAX-ACCESS  read-only
	STATUS      current
	DESCRIPTION
	"Table entry attribute for ipv4ShuntDscpPackets"
	::={ipv4ShuntDscpPacketsLevelEntry 2}

ipv4ShuntDscpPacketsLevelMom OBJECT-TYPE
	SYNTAX	 CounterBasedGauge64
	MAX-ACCESS  read-only
	STATUS      current
	DESCRIPTION
	"Table entry attribute for ipv4ShuntDscpPackets"
	::={ipv4ShuntDscpPacketsLevelEntry 3}

ipv4ShuntDscpPacketsLevelMax OBJECT-TYPE
	SYNTAX	 CounterBasedGauge64
	MAX-ACCESS  read-only
	STATUS      current
	DESCRIPTION
	"Table entry attribute for ipv4ShuntDscpPackets"
	::={ipv4ShuntDscpPacketsLevelEntry 4}


ipv4ShuntDscpBytes	OBJECT IDENTIFIER ::={ipv4 44}

ipv4ShuntDscpBytesVal	OBJECT-TYPE
	SYNTAX	 Counter64
	MAX-ACCESS read-only
	STATUS current
	DESCRIPTION "Shunted bytes (DSCP)"

	::={ipv4ShuntDscpBytes 1}

ipv4ShuntDscpBytesMom	OBJECT-TYPE
	SYNTAX	 CounterBasedGauge64
	MAX-ACCESS read-only
	STATUS current
	DESCRIPTION "Shunted bytes (DSCP)"

	::={ipv4ShuntDscpBytes 2}

ipv4ShuntDscpBytesMax	OBJECT-TYPE
	SYNTAX	 CounterBasedGauge64
	MAX-ACCESS read-only
	STATUS current
	DESCRIPTION "Shunted bytes (DSCP)"

	::={ipv4ShuntDscpBytes 3}

ipv4ShuntDscpBytesLevelTable OBJECT-TYPE
	SYNTAX      SEQUENCE OF Ipv4ShuntDscpBytesLevelEntry
	MAX-ACCESS  not-accessible
	STATUS      current
	DESCRIPTION
	"Table for ipv4ShuntDscpBytes"
	::={ipv4ShuntDscpBytes 4}

ipv4ShuntDscpBytesLevelEntry OBJECT-TYPE
	SYNTAX      Ipv4ShuntDscpBytesLevelEntry
	MAX-ACCESS  not-accessible
	STATUS      current
	DESCRIPTION
	"Table entry for ipv4ShuntDscpBytes"
	INDEX { ipv4ShuntDscpBytesLevelName }
	::={ipv4ShuntDscpBytesLevelTable 1}

Ipv4ShuntDscpBytesLevelEntry ::=
	SEQUENCE {
		ipv4ShuntDscpBytesLevelName	DisplayString,
		ipv4ShuntDscpBytesLevelVal	Counter64,
		ipv4ShuntDscpBytesLevelMom	CounterBasedGauge64,
		ipv4ShuntDscpBytesLevelMax	CounterBasedGauge64
	}

ipv4ShuntDscpBytesLevelName OBJECT-TYPE
	SYNTAX      DisplayString
	MAX-ACCESS  not-accessible
	STATUS      current
	DESCRIPTION
	"Table entry display string for ipv4ShuntDscpBytes"
	::={ipv4ShuntDscpBytesLevelEntry 1}

ipv4ShuntDscpBytesLevelVal OBJECT-TYPE
	SYNTAX	 Counter64
	MAX-ACCESS  read-only
	STATUS      current
	DESCRIPTION
	"Table entry attribute for ipv4ShuntDscpBytes"
	::={ipv4ShuntDscpBytesLevelEntry 2}

ipv4ShuntDscpBytesLevelMom OBJECT-TYPE
	SYNTAX	 CounterBasedGauge64
	MAX-ACCESS  read-only
	STATUS      current
	DESCRIPTION
	"Table entry attribute for ipv4ShuntDscpBytes"
	::={ipv4ShuntDscpBytesLevelEntry 3}

ipv4ShuntDscpBytesLevelMax OBJECT-TYPE
	SYNTAX	 CounterBasedGauge64
	MAX-ACCESS  read-only
	STATUS      current
	DESCRIPTION
	"Table entry attribute for ipv4ShuntDscpBytes"
	::={ipv4ShuntDscpBytesLevelEntry 4}


ipv6	OBJECT IDENTIFIER ::={sysdiag 126}

ipv6Packets	OBJECT IDENTIFIER ::={ipv6 1}

ipv6PacketsVal	OBJECT-TYPE
	SYNTAX	 Counter64
	MAX-ACCESS read-only
	STATUS current
	DESCRIPTION "RX packets"

	::={ipv6Packets 1}

ipv6PacketsMom	OBJECT-TYPE
	SYNTAX	 CounterBasedGauge64
	MAX-ACCESS read-only
	STATUS current
	DESCRIPTION "RX packets"

	::={ipv6Packets 2}

ipv6PacketsMax	OBJECT-TYPE
	SYNTAX	 CounterBasedGauge64
	MAX-ACCESS read-only
	STATUS current
	DESCRIPTION "RX packets"

	::={ipv6Packets 3}

ipv6PacketsLevelTable OBJECT-TYPE
	SYNTAX      SEQUENCE OF Ipv6PacketsLevelEntry
	MAX-ACCESS  not-accessible
	STATUS      current
	DESCRIPTION
	"Table for ipv6Packets"
	::={ipv6Packets 4}

ipv6PacketsLevelEntry OBJECT-TYPE
	SYNTAX      Ipv6PacketsLevelEntry
	MAX-ACCESS  not-accessible
	STATUS      current
	DESCRIPTION
	"Table entry for ipv6Packets"
	INDEX { ipv6PacketsLevelName }
	::={ipv6PacketsLevelTable 1}

Ipv6PacketsLevelEntry ::=
	SEQUENCE {
		ipv6PacketsLevelName	DisplayString,
		ipv6PacketsLevelVal	Counter64,
		ipv6PacketsLevelMom	CounterBasedGauge64,
		ipv6PacketsLevelMax	CounterBasedGauge64
	}

ipv6PacketsLevelName OBJECT-TYPE
	SYNTAX      DisplayString
	MAX-ACCESS  not-accessible
	STATUS      current
	DESCRIPTION
	"Table entry display string for ipv6Packets"
	::={ipv6PacketsLevelEntry 1}

ipv6PacketsLevelVal OBJECT-TYPE
	SYNTAX	 Counter64
	MAX-ACCESS  read-only
	STATUS      current
	DESCRIPTION
	"Table entry attribute for ipv6Packets"
	::={ipv6PacketsLevelEntry 2}

ipv6PacketsLevelMom OBJECT-TYPE
	SYNTAX	 CounterBasedGauge64
	MAX-ACCESS  read-only
	STATUS      current
	DESCRIPTION
	"Table entry attribute for ipv6Packets"
	::={ipv6PacketsLevelEntry 3}

ipv6PacketsLevelMax OBJECT-TYPE
	SYNTAX	 CounterBasedGauge64
	MAX-ACCESS  read-only
	STATUS      current
	DESCRIPTION
	"Table entry attribute for ipv6Packets"
	::={ipv6PacketsLevelEntry 4}


ipv6Bytes	OBJECT IDENTIFIER ::={ipv6 2}

ipv6BytesVal	OBJECT-TYPE
	SYNTAX	 Counter64
	MAX-ACCESS read-only
	STATUS current
	DESCRIPTION "RX data"

	::={ipv6Bytes 1}

ipv6BytesMom	OBJECT-TYPE
	SYNTAX	 CounterBasedGauge64
	MAX-ACCESS read-only
	STATUS current
	DESCRIPTION "RX data"

	::={ipv6Bytes 2}

ipv6BytesMax	OBJECT-TYPE
	SYNTAX	 CounterBasedGauge64
	MAX-ACCESS read-only
	STATUS current
	DESCRIPTION "RX data"

	::={ipv6Bytes 3}

ipv6BytesLevelTable OBJECT-TYPE
	SYNTAX      SEQUENCE OF Ipv6BytesLevelEntry
	MAX-ACCESS  not-accessible
	STATUS      current
	DESCRIPTION
	"Table for ipv6Bytes"
	::={ipv6Bytes 4}

ipv6BytesLevelEntry OBJECT-TYPE
	SYNTAX      Ipv6BytesLevelEntry
	MAX-ACCESS  not-accessible
	STATUS      current
	DESCRIPTION
	"Table entry for ipv6Bytes"
	INDEX { ipv6BytesLevelName }
	::={ipv6BytesLevelTable 1}

Ipv6BytesLevelEntry ::=
	SEQUENCE {
		ipv6BytesLevelName	DisplayString,
		ipv6BytesLevelVal	Counter64,
		ipv6BytesLevelMom	CounterBasedGauge64,
		ipv6BytesLevelMax	CounterBasedGauge64
	}

ipv6BytesLevelName OBJECT-TYPE
	SYNTAX      DisplayString
	MAX-ACCESS  not-accessible
	STATUS      current
	DESCRIPTION
	"Table entry display string for ipv6Bytes"
	::={ipv6BytesLevelEntry 1}

ipv6BytesLevelVal OBJECT-TYPE
	SYNTAX	 Counter64
	MAX-ACCESS  read-only
	STATUS      current
	DESCRIPTION
	"Table entry attribute for ipv6Bytes"
	::={ipv6BytesLevelEntry 2}

ipv6BytesLevelMom OBJECT-TYPE
	SYNTAX	 CounterBasedGauge64
	MAX-ACCESS  read-only
	STATUS      current
	DESCRIPTION
	"Table entry attribute for ipv6Bytes"
	::={ipv6BytesLevelEntry 3}

ipv6BytesLevelMax OBJECT-TYPE
	SYNTAX	 CounterBasedGauge64
	MAX-ACCESS  read-only
	STATUS      current
	DESCRIPTION
	"Table entry attribute for ipv6Bytes"
	::={ipv6BytesLevelEntry 4}


ipv6RefusedShort	OBJECT IDENTIFIER ::={ipv6 3}

ipv6RefusedShortVal	OBJECT-TYPE
	SYNTAX	 Counter64
	MAX-ACCESS read-only
	STATUS current
	DESCRIPTION "Refused (packet is too short)"

	::={ipv6RefusedShort 1}

ipv6RefusedShortMom	OBJECT-TYPE
	SYNTAX	 CounterBasedGauge64
	MAX-ACCESS read-only
	STATUS current
	DESCRIPTION "Refused (packet is too short)"

	::={ipv6RefusedShort 2}

ipv6RefusedShortMax	OBJECT-TYPE
	SYNTAX	 CounterBasedGauge64
	MAX-ACCESS read-only
	STATUS current
	DESCRIPTION "Refused (packet is too short)"

	::={ipv6RefusedShort 3}

ipv6RefusedShortLevelTable OBJECT-TYPE
	SYNTAX      SEQUENCE OF Ipv6RefusedShortLevelEntry
	MAX-ACCESS  not-accessible
	STATUS      current
	DESCRIPTION
	"Table for ipv6RefusedShort"
	::={ipv6RefusedShort 4}

ipv6RefusedShortLevelEntry OBJECT-TYPE
	SYNTAX      Ipv6RefusedShortLevelEntry
	MAX-ACCESS  not-accessible
	STATUS      current
	DESCRIPTION
	"Table entry for ipv6RefusedShort"
	INDEX { ipv6RefusedShortLevelName }
	::={ipv6RefusedShortLevelTable 1}

Ipv6RefusedShortLevelEntry ::=
	SEQUENCE {
		ipv6RefusedShortLevelName	DisplayString,
		ipv6RefusedShortLevelVal	Counter64,
		ipv6RefusedShortLevelMom	CounterBasedGauge64,
		ipv6RefusedShortLevelMax	CounterBasedGauge64
	}

ipv6RefusedShortLevelName OBJECT-TYPE
	SYNTAX      DisplayString
	MAX-ACCESS  not-accessible
	STATUS      current
	DESCRIPTION
	"Table entry display string for ipv6RefusedShort"
	::={ipv6RefusedShortLevelEntry 1}

ipv6RefusedShortLevelVal OBJECT-TYPE
	SYNTAX	 Counter64
	MAX-ACCESS  read-only
	STATUS      current
	DESCRIPTION
	"Table entry attribute for ipv6RefusedShort"
	::={ipv6RefusedShortLevelEntry 2}

ipv6RefusedShortLevelMom OBJECT-TYPE
	SYNTAX	 CounterBasedGauge64
	MAX-ACCESS  read-only
	STATUS      current
	DESCRIPTION
	"Table entry attribute for ipv6RefusedShort"
	::={ipv6RefusedShortLevelEntry 3}

ipv6RefusedShortLevelMax OBJECT-TYPE
	SYNTAX	 CounterBasedGauge64
	MAX-ACCESS  read-only
	STATUS      current
	DESCRIPTION
	"Table entry attribute for ipv6RefusedShort"
	::={ipv6RefusedShortLevelEntry 4}


ipv6RefusedVersion	OBJECT IDENTIFIER ::={ipv6 4}

ipv6RefusedVersionVal	OBJECT-TYPE
	SYNTAX	 Counter64
	MAX-ACCESS read-only
	STATUS current
	DESCRIPTION "Refused (invalid version)"

	::={ipv6RefusedVersion 1}

ipv6RefusedVersionMom	OBJECT-TYPE
	SYNTAX	 CounterBasedGauge64
	MAX-ACCESS read-only
	STATUS current
	DESCRIPTION "Refused (invalid version)"

	::={ipv6RefusedVersion 2}

ipv6RefusedVersionMax	OBJECT-TYPE
	SYNTAX	 CounterBasedGauge64
	MAX-ACCESS read-only
	STATUS current
	DESCRIPTION "Refused (invalid version)"

	::={ipv6RefusedVersion 3}

ipv6RefusedVersionLevelTable OBJECT-TYPE
	SYNTAX      SEQUENCE OF Ipv6RefusedVersionLevelEntry
	MAX-ACCESS  not-accessible
	STATUS      current
	DESCRIPTION
	"Table for ipv6RefusedVersion"
	::={ipv6RefusedVersion 4}

ipv6RefusedVersionLevelEntry OBJECT-TYPE
	SYNTAX      Ipv6RefusedVersionLevelEntry
	MAX-ACCESS  not-accessible
	STATUS      current
	DESCRIPTION
	"Table entry for ipv6RefusedVersion"
	INDEX { ipv6RefusedVersionLevelName }
	::={ipv6RefusedVersionLevelTable 1}

Ipv6RefusedVersionLevelEntry ::=
	SEQUENCE {
		ipv6RefusedVersionLevelName	DisplayString,
		ipv6RefusedVersionLevelVal	Counter64,
		ipv6RefusedVersionLevelMom	CounterBasedGauge64,
		ipv6RefusedVersionLevelMax	CounterBasedGauge64
	}

ipv6RefusedVersionLevelName OBJECT-TYPE
	SYNTAX      DisplayString
	MAX-ACCESS  not-accessible
	STATUS      current
	DESCRIPTION
	"Table entry display string for ipv6RefusedVersion"
	::={ipv6RefusedVersionLevelEntry 1}

ipv6RefusedVersionLevelVal OBJECT-TYPE
	SYNTAX	 Counter64
	MAX-ACCESS  read-only
	STATUS      current
	DESCRIPTION
	"Table entry attribute for ipv6RefusedVersion"
	::={ipv6RefusedVersionLevelEntry 2}

ipv6RefusedVersionLevelMom OBJECT-TYPE
	SYNTAX	 CounterBasedGauge64
	MAX-ACCESS  read-only
	STATUS      current
	DESCRIPTION
	"Table entry attribute for ipv6RefusedVersion"
	::={ipv6RefusedVersionLevelEntry 3}

ipv6RefusedVersionLevelMax OBJECT-TYPE
	SYNTAX	 CounterBasedGauge64
	MAX-ACCESS  read-only
	STATUS      current
	DESCRIPTION
	"Table entry attribute for ipv6RefusedVersion"
	::={ipv6RefusedVersionLevelEntry 4}


ipv6RefusedSelf	OBJECT IDENTIFIER ::={ipv6 5}

ipv6RefusedSelfVal	OBJECT-TYPE
	SYNTAX	 Counter64
	MAX-ACCESS read-only
	STATUS current
	DESCRIPTION "Refused (src == dest)"

	::={ipv6RefusedSelf 1}

ipv6RefusedSelfMom	OBJECT-TYPE
	SYNTAX	 CounterBasedGauge64
	MAX-ACCESS read-only
	STATUS current
	DESCRIPTION "Refused (src == dest)"

	::={ipv6RefusedSelf 2}

ipv6RefusedSelfMax	OBJECT-TYPE
	SYNTAX	 CounterBasedGauge64
	MAX-ACCESS read-only
	STATUS current
	DESCRIPTION "Refused (src == dest)"

	::={ipv6RefusedSelf 3}

ipv6RefusedSelfLevelTable OBJECT-TYPE
	SYNTAX      SEQUENCE OF Ipv6RefusedSelfLevelEntry
	MAX-ACCESS  not-accessible
	STATUS      current
	DESCRIPTION
	"Table for ipv6RefusedSelf"
	::={ipv6RefusedSelf 4}

ipv6RefusedSelfLevelEntry OBJECT-TYPE
	SYNTAX      Ipv6RefusedSelfLevelEntry
	MAX-ACCESS  not-accessible
	STATUS      current
	DESCRIPTION
	"Table entry for ipv6RefusedSelf"
	INDEX { ipv6RefusedSelfLevelName }
	::={ipv6RefusedSelfLevelTable 1}

Ipv6RefusedSelfLevelEntry ::=
	SEQUENCE {
		ipv6RefusedSelfLevelName	DisplayString,
		ipv6RefusedSelfLevelVal	Counter64,
		ipv6RefusedSelfLevelMom	CounterBasedGauge64,
		ipv6RefusedSelfLevelMax	CounterBasedGauge64
	}

ipv6RefusedSelfLevelName OBJECT-TYPE
	SYNTAX      DisplayString
	MAX-ACCESS  not-accessible
	STATUS      current
	DESCRIPTION
	"Table entry display string for ipv6RefusedSelf"
	::={ipv6RefusedSelfLevelEntry 1}

ipv6RefusedSelfLevelVal OBJECT-TYPE
	SYNTAX	 Counter64
	MAX-ACCESS  read-only
	STATUS      current
	DESCRIPTION
	"Table entry attribute for ipv6RefusedSelf"
	::={ipv6RefusedSelfLevelEntry 2}

ipv6RefusedSelfLevelMom OBJECT-TYPE
	SYNTAX	 CounterBasedGauge64
	MAX-ACCESS  read-only
	STATUS      current
	DESCRIPTION
	"Table entry attribute for ipv6RefusedSelf"
	::={ipv6RefusedSelfLevelEntry 3}

ipv6RefusedSelfLevelMax OBJECT-TYPE
	SYNTAX	 CounterBasedGauge64
	MAX-ACCESS  read-only
	STATUS      current
	DESCRIPTION
	"Table entry attribute for ipv6RefusedSelf"
	::={ipv6RefusedSelfLevelEntry 4}


ipv6Fragmented	OBJECT IDENTIFIER ::={ipv6 7}

ipv6FragmentedVal	OBJECT-TYPE
	SYNTAX	 Counter64
	MAX-ACCESS read-only
	STATUS current
	DESCRIPTION "Packet fragments"

	::={ipv6Fragmented 1}

ipv6FragmentedMom	OBJECT-TYPE
	SYNTAX	 CounterBasedGauge64
	MAX-ACCESS read-only
	STATUS current
	DESCRIPTION "Packet fragments"

	::={ipv6Fragmented 2}

ipv6FragmentedMax	OBJECT-TYPE
	SYNTAX	 CounterBasedGauge64
	MAX-ACCESS read-only
	STATUS current
	DESCRIPTION "Packet fragments"

	::={ipv6Fragmented 3}

ipv6FragmentedLevelTable OBJECT-TYPE
	SYNTAX      SEQUENCE OF Ipv6FragmentedLevelEntry
	MAX-ACCESS  not-accessible
	STATUS      current
	DESCRIPTION
	"Table for ipv6Fragmented"
	::={ipv6Fragmented 4}

ipv6FragmentedLevelEntry OBJECT-TYPE
	SYNTAX      Ipv6FragmentedLevelEntry
	MAX-ACCESS  not-accessible
	STATUS      current
	DESCRIPTION
	"Table entry for ipv6Fragmented"
	INDEX { ipv6FragmentedLevelName }
	::={ipv6FragmentedLevelTable 1}

Ipv6FragmentedLevelEntry ::=
	SEQUENCE {
		ipv6FragmentedLevelName	DisplayString,
		ipv6FragmentedLevelVal	Counter64,
		ipv6FragmentedLevelMom	CounterBasedGauge64,
		ipv6FragmentedLevelMax	CounterBasedGauge64
	}

ipv6FragmentedLevelName OBJECT-TYPE
	SYNTAX      DisplayString
	MAX-ACCESS  not-accessible
	STATUS      current
	DESCRIPTION
	"Table entry display string for ipv6Fragmented"
	::={ipv6FragmentedLevelEntry 1}

ipv6FragmentedLevelVal OBJECT-TYPE
	SYNTAX	 Counter64
	MAX-ACCESS  read-only
	STATUS      current
	DESCRIPTION
	"Table entry attribute for ipv6Fragmented"
	::={ipv6FragmentedLevelEntry 2}

ipv6FragmentedLevelMom OBJECT-TYPE
	SYNTAX	 CounterBasedGauge64
	MAX-ACCESS  read-only
	STATUS      current
	DESCRIPTION
	"Table entry attribute for ipv6Fragmented"
	::={ipv6FragmentedLevelEntry 3}

ipv6FragmentedLevelMax OBJECT-TYPE
	SYNTAX	 CounterBasedGauge64
	MAX-ACCESS  read-only
	STATUS      current
	DESCRIPTION
	"Table entry attribute for ipv6Fragmented"
	::={ipv6FragmentedLevelEntry 4}


ipv6FragmentedIds	OBJECT IDENTIFIER ::={ipv6 10}

ipv6FragmentedIdsVal	OBJECT-TYPE
	SYNTAX	 CounterBasedGauge64
	MAX-ACCESS read-only
	STATUS current
	DESCRIPTION "Fragment ids"

	::={ipv6FragmentedIds 1}

ipv6FragmentedIdsMax	OBJECT-TYPE
	SYNTAX	 CounterBasedGauge64
	MAX-ACCESS read-only
	STATUS current
	DESCRIPTION "Fragment ids"

	::={ipv6FragmentedIds 3}

ipv6FragmentedIdsLevelTable OBJECT-TYPE
	SYNTAX      SEQUENCE OF Ipv6FragmentedIdsLevelEntry
	MAX-ACCESS  not-accessible
	STATUS      current
	DESCRIPTION
	"Table for ipv6FragmentedIds"
	::={ipv6FragmentedIds 4}

ipv6FragmentedIdsLevelEntry OBJECT-TYPE
	SYNTAX      Ipv6FragmentedIdsLevelEntry
	MAX-ACCESS  not-accessible
	STATUS      current
	DESCRIPTION
	"Table entry for ipv6FragmentedIds"
	INDEX { ipv6FragmentedIdsLevelName }
	::={ipv6FragmentedIdsLevelTable 1}

Ipv6FragmentedIdsLevelEntry ::=
	SEQUENCE {
		ipv6FragmentedIdsLevelName	DisplayString,
		ipv6FragmentedIdsLevelVal	CounterBasedGauge64,
		ipv6FragmentedIdsLevelMax	CounterBasedGauge64
	}

ipv6FragmentedIdsLevelName OBJECT-TYPE
	SYNTAX      DisplayString
	MAX-ACCESS  not-accessible
	STATUS      current
	DESCRIPTION
	"Table entry display string for ipv6FragmentedIds"
	::={ipv6FragmentedIdsLevelEntry 1}

ipv6FragmentedIdsLevelVal OBJECT-TYPE
	SYNTAX	 CounterBasedGauge64
	MAX-ACCESS  read-only
	STATUS      current
	DESCRIPTION
	"Table entry attribute for ipv6FragmentedIds"
	::={ipv6FragmentedIdsLevelEntry 2}

ipv6FragmentedIdsLevelMax OBJECT-TYPE
	SYNTAX	 CounterBasedGauge64
	MAX-ACCESS  read-only
	STATUS      current
	DESCRIPTION
	"Table entry attribute for ipv6FragmentedIds"
	::={ipv6FragmentedIdsLevelEntry 4}


ipv6Fragments	OBJECT IDENTIFIER ::={ipv6 11}

ipv6FragmentsVal	OBJECT-TYPE
	SYNTAX	 CounterBasedGauge64
	MAX-ACCESS read-only
	STATUS current
	DESCRIPTION "Fragments in queue"

	::={ipv6Fragments 1}

ipv6FragmentsMax	OBJECT-TYPE
	SYNTAX	 CounterBasedGauge64
	MAX-ACCESS read-only
	STATUS current
	DESCRIPTION "Fragments in queue"

	::={ipv6Fragments 3}

ipv6FragmentsLevelTable OBJECT-TYPE
	SYNTAX      SEQUENCE OF Ipv6FragmentsLevelEntry
	MAX-ACCESS  not-accessible
	STATUS      current
	DESCRIPTION
	"Table for ipv6Fragments"
	::={ipv6Fragments 4}

ipv6FragmentsLevelEntry OBJECT-TYPE
	SYNTAX      Ipv6FragmentsLevelEntry
	MAX-ACCESS  not-accessible
	STATUS      current
	DESCRIPTION
	"Table entry for ipv6Fragments"
	INDEX { ipv6FragmentsLevelName }
	::={ipv6FragmentsLevelTable 1}

Ipv6FragmentsLevelEntry ::=
	SEQUENCE {
		ipv6FragmentsLevelName	DisplayString,
		ipv6FragmentsLevelVal	CounterBasedGauge64,
		ipv6FragmentsLevelMax	CounterBasedGauge64
	}

ipv6FragmentsLevelName OBJECT-TYPE
	SYNTAX      DisplayString
	MAX-ACCESS  not-accessible
	STATUS      current
	DESCRIPTION
	"Table entry display string for ipv6Fragments"
	::={ipv6FragmentsLevelEntry 1}

ipv6FragmentsLevelVal OBJECT-TYPE
	SYNTAX	 CounterBasedGauge64
	MAX-ACCESS  read-only
	STATUS      current
	DESCRIPTION
	"Table entry attribute for ipv6Fragments"
	::={ipv6FragmentsLevelEntry 2}

ipv6FragmentsLevelMax OBJECT-TYPE
	SYNTAX	 CounterBasedGauge64
	MAX-ACCESS  read-only
	STATUS      current
	DESCRIPTION
	"Table entry attribute for ipv6Fragments"
	::={ipv6FragmentsLevelEntry 4}


ipv6RefusedOof	OBJECT IDENTIFIER ::={ipv6 14}

ipv6RefusedOofVal	OBJECT-TYPE
	SYNTAX	 Counter64
	MAX-ACCESS read-only
	STATUS obsolete
	DESCRIPTION "Refused (out of fragments)"

	::={ipv6RefusedOof 1}

ipv6RefusedOofMom	OBJECT-TYPE
	SYNTAX	 CounterBasedGauge64
	MAX-ACCESS read-only
	STATUS obsolete
	DESCRIPTION "Refused (out of fragments)"

	::={ipv6RefusedOof 2}

ipv6RefusedOofMax	OBJECT-TYPE
	SYNTAX	 CounterBasedGauge64
	MAX-ACCESS read-only
	STATUS obsolete
	DESCRIPTION "Refused (out of fragments)"

	::={ipv6RefusedOof 3}

ipv6RefusedOofLevelTable OBJECT-TYPE
	SYNTAX      SEQUENCE OF Ipv6RefusedOofLevelEntry
	MAX-ACCESS  not-accessible
	STATUS      current
	DESCRIPTION
	"Table for ipv6RefusedOof"
	::={ipv6RefusedOof 4}

ipv6RefusedOofLevelEntry OBJECT-TYPE
	SYNTAX      Ipv6RefusedOofLevelEntry
	MAX-ACCESS  not-accessible
	STATUS      current
	DESCRIPTION
	"Table entry for ipv6RefusedOof"
	INDEX { ipv6RefusedOofLevelName }
	::={ipv6RefusedOofLevelTable 1}

Ipv6RefusedOofLevelEntry ::=
	SEQUENCE {
		ipv6RefusedOofLevelName	DisplayString,
		ipv6RefusedOofLevelVal	Counter64,
		ipv6RefusedOofLevelMom	CounterBasedGauge64,
		ipv6RefusedOofLevelMax	CounterBasedGauge64
	}

ipv6RefusedOofLevelName OBJECT-TYPE
	SYNTAX      DisplayString
	MAX-ACCESS  not-accessible
	STATUS      current
	DESCRIPTION
	"Table entry display string for ipv6RefusedOof"
	::={ipv6RefusedOofLevelEntry 1}

ipv6RefusedOofLevelVal OBJECT-TYPE
	SYNTAX	 Counter64
	MAX-ACCESS  read-only
	STATUS      current
	DESCRIPTION
	"Table entry attribute for ipv6RefusedOof"
	::={ipv6RefusedOofLevelEntry 2}

ipv6RefusedOofLevelMom OBJECT-TYPE
	SYNTAX	 CounterBasedGauge64
	MAX-ACCESS  read-only
	STATUS      current
	DESCRIPTION
	"Table entry attribute for ipv6RefusedOof"
	::={ipv6RefusedOofLevelEntry 3}

ipv6RefusedOofLevelMax OBJECT-TYPE
	SYNTAX	 CounterBasedGauge64
	MAX-ACCESS  read-only
	STATUS      current
	DESCRIPTION
	"Table entry attribute for ipv6RefusedOof"
	::={ipv6RefusedOofLevelEntry 4}


ipv6FragmentAllocationFailures	OBJECT IDENTIFIER ::={ipv6 15}

ipv6FragmentAllocationFailuresVal	OBJECT-TYPE
	SYNTAX	 Counter64
	MAX-ACCESS read-only
	STATUS current
	DESCRIPTION "Fragment allocation failures"

	::={ipv6FragmentAllocationFailures 1}

ipv6FragmentAllocationFailuresMom	OBJECT-TYPE
	SYNTAX	 CounterBasedGauge64
	MAX-ACCESS read-only
	STATUS current
	DESCRIPTION "Fragment allocation failures"

	::={ipv6FragmentAllocationFailures 2}

ipv6FragmentAllocationFailuresMax	OBJECT-TYPE
	SYNTAX	 CounterBasedGauge64
	MAX-ACCESS read-only
	STATUS current
	DESCRIPTION "Fragment allocation failures"

	::={ipv6FragmentAllocationFailures 3}

ipv6FragmentAllocationFailuresLevelTable OBJECT-TYPE
	SYNTAX      SEQUENCE OF Ipv6FragmentAllocationFailuresLevelEntry
	MAX-ACCESS  not-accessible
	STATUS      current
	DESCRIPTION
	"Table for ipv6FragmentAllocationFailures"
	::={ipv6FragmentAllocationFailures 4}

ipv6FragmentAllocationFailuresLevelEntry OBJECT-TYPE
	SYNTAX      Ipv6FragmentAllocationFailuresLevelEntry
	MAX-ACCESS  not-accessible
	STATUS      current
	DESCRIPTION
	"Table entry for ipv6FragmentAllocationFailures"
	INDEX { ipv6FragmentAllocationFailuresLevelName }
	::={ipv6FragmentAllocationFailuresLevelTable 1}

Ipv6FragmentAllocationFailuresLevelEntry ::=
	SEQUENCE {
		ipv6FragmentAllocationFailuresLevelName	DisplayString,
		ipv6FragmentAllocationFailuresLevelVal	Counter64,
		ipv6FragmentAllocationFailuresLevelMom	CounterBasedGauge64,
		ipv6FragmentAllocationFailuresLevelMax	CounterBasedGauge64
	}

ipv6FragmentAllocationFailuresLevelName OBJECT-TYPE
	SYNTAX      DisplayString
	MAX-ACCESS  not-accessible
	STATUS      current
	DESCRIPTION
	"Table entry display string for ipv6FragmentAllocationFailures"
	::={ipv6FragmentAllocationFailuresLevelEntry 1}

ipv6FragmentAllocationFailuresLevelVal OBJECT-TYPE
	SYNTAX	 Counter64
	MAX-ACCESS  read-only
	STATUS      current
	DESCRIPTION
	"Table entry attribute for ipv6FragmentAllocationFailures"
	::={ipv6FragmentAllocationFailuresLevelEntry 2}

ipv6FragmentAllocationFailuresLevelMom OBJECT-TYPE
	SYNTAX	 CounterBasedGauge64
	MAX-ACCESS  read-only
	STATUS      current
	DESCRIPTION
	"Table entry attribute for ipv6FragmentAllocationFailures"
	::={ipv6FragmentAllocationFailuresLevelEntry 3}

ipv6FragmentAllocationFailuresLevelMax OBJECT-TYPE
	SYNTAX	 CounterBasedGauge64
	MAX-ACCESS  read-only
	STATUS      current
	DESCRIPTION
	"Table entry attribute for ipv6FragmentAllocationFailures"
	::={ipv6FragmentAllocationFailuresLevelEntry 4}


ipv6FragmentReassFail	OBJECT IDENTIFIER ::={ipv6 16}

ipv6FragmentReassFailVal	OBJECT-TYPE
	SYNTAX	 Counter64
	MAX-ACCESS read-only
	STATUS current
	DESCRIPTION "Fragment reassembly failures"

	::={ipv6FragmentReassFail 1}

ipv6FragmentReassFailMom	OBJECT-TYPE
	SYNTAX	 CounterBasedGauge64
	MAX-ACCESS read-only
	STATUS current
	DESCRIPTION "Fragment reassembly failures"

	::={ipv6FragmentReassFail 2}

ipv6FragmentReassFailMax	OBJECT-TYPE
	SYNTAX	 CounterBasedGauge64
	MAX-ACCESS read-only
	STATUS current
	DESCRIPTION "Fragment reassembly failures"

	::={ipv6FragmentReassFail 3}

ipv6FragmentReassFailLevelTable OBJECT-TYPE
	SYNTAX      SEQUENCE OF Ipv6FragmentReassFailLevelEntry
	MAX-ACCESS  not-accessible
	STATUS      current
	DESCRIPTION
	"Table for ipv6FragmentReassFail"
	::={ipv6FragmentReassFail 4}

ipv6FragmentReassFailLevelEntry OBJECT-TYPE
	SYNTAX      Ipv6FragmentReassFailLevelEntry
	MAX-ACCESS  not-accessible
	STATUS      current
	DESCRIPTION
	"Table entry for ipv6FragmentReassFail"
	INDEX { ipv6FragmentReassFailLevelName }
	::={ipv6FragmentReassFailLevelTable 1}

Ipv6FragmentReassFailLevelEntry ::=
	SEQUENCE {
		ipv6FragmentReassFailLevelName	DisplayString,
		ipv6FragmentReassFailLevelVal	Counter64,
		ipv6FragmentReassFailLevelMom	CounterBasedGauge64,
		ipv6FragmentReassFailLevelMax	CounterBasedGauge64
	}

ipv6FragmentReassFailLevelName OBJECT-TYPE
	SYNTAX      DisplayString
	MAX-ACCESS  not-accessible
	STATUS      current
	DESCRIPTION
	"Table entry display string for ipv6FragmentReassFail"
	::={ipv6FragmentReassFailLevelEntry 1}

ipv6FragmentReassFailLevelVal OBJECT-TYPE
	SYNTAX	 Counter64
	MAX-ACCESS  read-only
	STATUS      current
	DESCRIPTION
	"Table entry attribute for ipv6FragmentReassFail"
	::={ipv6FragmentReassFailLevelEntry 2}

ipv6FragmentReassFailLevelMom OBJECT-TYPE
	SYNTAX	 CounterBasedGauge64
	MAX-ACCESS  read-only
	STATUS      current
	DESCRIPTION
	"Table entry attribute for ipv6FragmentReassFail"
	::={ipv6FragmentReassFailLevelEntry 3}

ipv6FragmentReassFailLevelMax OBJECT-TYPE
	SYNTAX	 CounterBasedGauge64
	MAX-ACCESS  read-only
	STATUS      current
	DESCRIPTION
	"Table entry attribute for ipv6FragmentReassFail"
	::={ipv6FragmentReassFailLevelEntry 4}


ipv6FragmentTooNoisy	OBJECT IDENTIFIER ::={ipv6 19}

ipv6FragmentTooNoisyVal	OBJECT-TYPE
	SYNTAX	 Counter64
	MAX-ACCESS read-only
	STATUS current
	DESCRIPTION "Packets refused (too many fragments)"

	::={ipv6FragmentTooNoisy 1}

ipv6FragmentTooNoisyMom	OBJECT-TYPE
	SYNTAX	 CounterBasedGauge64
	MAX-ACCESS read-only
	STATUS current
	DESCRIPTION "Packets refused (too many fragments)"

	::={ipv6FragmentTooNoisy 2}

ipv6FragmentTooNoisyMax	OBJECT-TYPE
	SYNTAX	 CounterBasedGauge64
	MAX-ACCESS read-only
	STATUS current
	DESCRIPTION "Packets refused (too many fragments)"

	::={ipv6FragmentTooNoisy 3}

ipv6FragmentTooNoisyLevelTable OBJECT-TYPE
	SYNTAX      SEQUENCE OF Ipv6FragmentTooNoisyLevelEntry
	MAX-ACCESS  not-accessible
	STATUS      current
	DESCRIPTION
	"Table for ipv6FragmentTooNoisy"
	::={ipv6FragmentTooNoisy 4}

ipv6FragmentTooNoisyLevelEntry OBJECT-TYPE
	SYNTAX      Ipv6FragmentTooNoisyLevelEntry
	MAX-ACCESS  not-accessible
	STATUS      current
	DESCRIPTION
	"Table entry for ipv6FragmentTooNoisy"
	INDEX { ipv6FragmentTooNoisyLevelName }
	::={ipv6FragmentTooNoisyLevelTable 1}

Ipv6FragmentTooNoisyLevelEntry ::=
	SEQUENCE {
		ipv6FragmentTooNoisyLevelName	DisplayString,
		ipv6FragmentTooNoisyLevelVal	Counter64,
		ipv6FragmentTooNoisyLevelMom	CounterBasedGauge64,
		ipv6FragmentTooNoisyLevelMax	CounterBasedGauge64
	}

ipv6FragmentTooNoisyLevelName OBJECT-TYPE
	SYNTAX      DisplayString
	MAX-ACCESS  not-accessible
	STATUS      current
	DESCRIPTION
	"Table entry display string for ipv6FragmentTooNoisy"
	::={ipv6FragmentTooNoisyLevelEntry 1}

ipv6FragmentTooNoisyLevelVal OBJECT-TYPE
	SYNTAX	 Counter64
	MAX-ACCESS  read-only
	STATUS      current
	DESCRIPTION
	"Table entry attribute for ipv6FragmentTooNoisy"
	::={ipv6FragmentTooNoisyLevelEntry 2}

ipv6FragmentTooNoisyLevelMom OBJECT-TYPE
	SYNTAX	 CounterBasedGauge64
	MAX-ACCESS  read-only
	STATUS      current
	DESCRIPTION
	"Table entry attribute for ipv6FragmentTooNoisy"
	::={ipv6FragmentTooNoisyLevelEntry 3}

ipv6FragmentTooNoisyLevelMax OBJECT-TYPE
	SYNTAX	 CounterBasedGauge64
	MAX-ACCESS  read-only
	STATUS      current
	DESCRIPTION
	"Table entry attribute for ipv6FragmentTooNoisy"
	::={ipv6FragmentTooNoisyLevelEntry 4}


ipv6Reassembled	OBJECT IDENTIFIER ::={ipv6 20}

ipv6ReassembledVal	OBJECT-TYPE
	SYNTAX	 Counter64
	MAX-ACCESS read-only
	STATUS current
	DESCRIPTION "Reassembled packets"

	::={ipv6Reassembled 1}

ipv6ReassembledMom	OBJECT-TYPE
	SYNTAX	 CounterBasedGauge64
	MAX-ACCESS read-only
	STATUS current
	DESCRIPTION "Reassembled packets"

	::={ipv6Reassembled 2}

ipv6ReassembledMax	OBJECT-TYPE
	SYNTAX	 CounterBasedGauge64
	MAX-ACCESS read-only
	STATUS current
	DESCRIPTION "Reassembled packets"

	::={ipv6Reassembled 3}

ipv6ReassembledLevelTable OBJECT-TYPE
	SYNTAX      SEQUENCE OF Ipv6ReassembledLevelEntry
	MAX-ACCESS  not-accessible
	STATUS      current
	DESCRIPTION
	"Table for ipv6Reassembled"
	::={ipv6Reassembled 4}

ipv6ReassembledLevelEntry OBJECT-TYPE
	SYNTAX      Ipv6ReassembledLevelEntry
	MAX-ACCESS  not-accessible
	STATUS      current
	DESCRIPTION
	"Table entry for ipv6Reassembled"
	INDEX { ipv6ReassembledLevelName }
	::={ipv6ReassembledLevelTable 1}

Ipv6ReassembledLevelEntry ::=
	SEQUENCE {
		ipv6ReassembledLevelName	DisplayString,
		ipv6ReassembledLevelVal	Counter64,
		ipv6ReassembledLevelMom	CounterBasedGauge64,
		ipv6ReassembledLevelMax	CounterBasedGauge64
	}

ipv6ReassembledLevelName OBJECT-TYPE
	SYNTAX      DisplayString
	MAX-ACCESS  not-accessible
	STATUS      current
	DESCRIPTION
	"Table entry display string for ipv6Reassembled"
	::={ipv6ReassembledLevelEntry 1}

ipv6ReassembledLevelVal OBJECT-TYPE
	SYNTAX	 Counter64
	MAX-ACCESS  read-only
	STATUS      current
	DESCRIPTION
	"Table entry attribute for ipv6Reassembled"
	::={ipv6ReassembledLevelEntry 2}

ipv6ReassembledLevelMom OBJECT-TYPE
	SYNTAX	 CounterBasedGauge64
	MAX-ACCESS  read-only
	STATUS      current
	DESCRIPTION
	"Table entry attribute for ipv6Reassembled"
	::={ipv6ReassembledLevelEntry 3}

ipv6ReassembledLevelMax OBJECT-TYPE
	SYNTAX	 CounterBasedGauge64
	MAX-ACCESS  read-only
	STATUS      current
	DESCRIPTION
	"Table entry attribute for ipv6Reassembled"
	::={ipv6ReassembledLevelEntry 4}


ipv6FragmentOverlap	OBJECT IDENTIFIER ::={ipv6 21}

ipv6FragmentOverlapVal	OBJECT-TYPE
	SYNTAX	 Counter64
	MAX-ACCESS read-only
	STATUS current
	DESCRIPTION "Overlapping Fragments"

	::={ipv6FragmentOverlap 1}

ipv6FragmentOverlapMom	OBJECT-TYPE
	SYNTAX	 CounterBasedGauge64
	MAX-ACCESS read-only
	STATUS current
	DESCRIPTION "Overlapping Fragments"

	::={ipv6FragmentOverlap 2}

ipv6FragmentOverlapMax	OBJECT-TYPE
	SYNTAX	 CounterBasedGauge64
	MAX-ACCESS read-only
	STATUS current
	DESCRIPTION "Overlapping Fragments"

	::={ipv6FragmentOverlap 3}

ipv6FragmentOverlapLevelTable OBJECT-TYPE
	SYNTAX      SEQUENCE OF Ipv6FragmentOverlapLevelEntry
	MAX-ACCESS  not-accessible
	STATUS      current
	DESCRIPTION
	"Table for ipv6FragmentOverlap"
	::={ipv6FragmentOverlap 4}

ipv6FragmentOverlapLevelEntry OBJECT-TYPE
	SYNTAX      Ipv6FragmentOverlapLevelEntry
	MAX-ACCESS  not-accessible
	STATUS      current
	DESCRIPTION
	"Table entry for ipv6FragmentOverlap"
	INDEX { ipv6FragmentOverlapLevelName }
	::={ipv6FragmentOverlapLevelTable 1}

Ipv6FragmentOverlapLevelEntry ::=
	SEQUENCE {
		ipv6FragmentOverlapLevelName	DisplayString,
		ipv6FragmentOverlapLevelVal	Counter64,
		ipv6FragmentOverlapLevelMom	CounterBasedGauge64,
		ipv6FragmentOverlapLevelMax	CounterBasedGauge64
	}

ipv6FragmentOverlapLevelName OBJECT-TYPE
	SYNTAX      DisplayString
	MAX-ACCESS  not-accessible
	STATUS      current
	DESCRIPTION
	"Table entry display string for ipv6FragmentOverlap"
	::={ipv6FragmentOverlapLevelEntry 1}

ipv6FragmentOverlapLevelVal OBJECT-TYPE
	SYNTAX	 Counter64
	MAX-ACCESS  read-only
	STATUS      current
	DESCRIPTION
	"Table entry attribute for ipv6FragmentOverlap"
	::={ipv6FragmentOverlapLevelEntry 2}

ipv6FragmentOverlapLevelMom OBJECT-TYPE
	SYNTAX	 CounterBasedGauge64
	MAX-ACCESS  read-only
	STATUS      current
	DESCRIPTION
	"Table entry attribute for ipv6FragmentOverlap"
	::={ipv6FragmentOverlapLevelEntry 3}

ipv6FragmentOverlapLevelMax OBJECT-TYPE
	SYNTAX	 CounterBasedGauge64
	MAX-ACCESS  read-only
	STATUS      current
	DESCRIPTION
	"Table entry attribute for ipv6FragmentOverlap"
	::={ipv6FragmentOverlapLevelEntry 4}


ipv6ExtDest	OBJECT IDENTIFIER ::={ipv6 22}

ipv6ExtDestVal	OBJECT-TYPE
	SYNTAX	 Counter64
	MAX-ACCESS read-only
	STATUS current
	DESCRIPTION "Destination Ext. Headers"

	::={ipv6ExtDest 1}

ipv6ExtDestMom	OBJECT-TYPE
	SYNTAX	 CounterBasedGauge64
	MAX-ACCESS read-only
	STATUS current
	DESCRIPTION "Destination Ext. Headers"

	::={ipv6ExtDest 2}

ipv6ExtDestMax	OBJECT-TYPE
	SYNTAX	 CounterBasedGauge64
	MAX-ACCESS read-only
	STATUS current
	DESCRIPTION "Destination Ext. Headers"

	::={ipv6ExtDest 3}

ipv6ExtDestLevelTable OBJECT-TYPE
	SYNTAX      SEQUENCE OF Ipv6ExtDestLevelEntry
	MAX-ACCESS  not-accessible
	STATUS      current
	DESCRIPTION
	"Table for ipv6ExtDest"
	::={ipv6ExtDest 4}

ipv6ExtDestLevelEntry OBJECT-TYPE
	SYNTAX      Ipv6ExtDestLevelEntry
	MAX-ACCESS  not-accessible
	STATUS      current
	DESCRIPTION
	"Table entry for ipv6ExtDest"
	INDEX { ipv6ExtDestLevelName }
	::={ipv6ExtDestLevelTable 1}

Ipv6ExtDestLevelEntry ::=
	SEQUENCE {
		ipv6ExtDestLevelName	DisplayString,
		ipv6ExtDestLevelVal	Counter64,
		ipv6ExtDestLevelMom	CounterBasedGauge64,
		ipv6ExtDestLevelMax	CounterBasedGauge64
	}

ipv6ExtDestLevelName OBJECT-TYPE
	SYNTAX      DisplayString
	MAX-ACCESS  not-accessible
	STATUS      current
	DESCRIPTION
	"Table entry display string for ipv6ExtDest"
	::={ipv6ExtDestLevelEntry 1}

ipv6ExtDestLevelVal OBJECT-TYPE
	SYNTAX	 Counter64
	MAX-ACCESS  read-only
	STATUS      current
	DESCRIPTION
	"Table entry attribute for ipv6ExtDest"
	::={ipv6ExtDestLevelEntry 2}

ipv6ExtDestLevelMom OBJECT-TYPE
	SYNTAX	 CounterBasedGauge64
	MAX-ACCESS  read-only
	STATUS      current
	DESCRIPTION
	"Table entry attribute for ipv6ExtDest"
	::={ipv6ExtDestLevelEntry 3}

ipv6ExtDestLevelMax OBJECT-TYPE
	SYNTAX	 CounterBasedGauge64
	MAX-ACCESS  read-only
	STATUS      current
	DESCRIPTION
	"Table entry attribute for ipv6ExtDest"
	::={ipv6ExtDestLevelEntry 4}


ipv6ExtHbh	OBJECT IDENTIFIER ::={ipv6 23}

ipv6ExtHbhVal	OBJECT-TYPE
	SYNTAX	 Counter64
	MAX-ACCESS read-only
	STATUS current
	DESCRIPTION "Hob-by-hop Ext. Headers"

	::={ipv6ExtHbh 1}

ipv6ExtHbhMom	OBJECT-TYPE
	SYNTAX	 CounterBasedGauge64
	MAX-ACCESS read-only
	STATUS current
	DESCRIPTION "Hob-by-hop Ext. Headers"

	::={ipv6ExtHbh 2}

ipv6ExtHbhMax	OBJECT-TYPE
	SYNTAX	 CounterBasedGauge64
	MAX-ACCESS read-only
	STATUS current
	DESCRIPTION "Hob-by-hop Ext. Headers"

	::={ipv6ExtHbh 3}

ipv6ExtHbhLevelTable OBJECT-TYPE
	SYNTAX      SEQUENCE OF Ipv6ExtHbhLevelEntry
	MAX-ACCESS  not-accessible
	STATUS      current
	DESCRIPTION
	"Table for ipv6ExtHbh"
	::={ipv6ExtHbh 4}

ipv6ExtHbhLevelEntry OBJECT-TYPE
	SYNTAX      Ipv6ExtHbhLevelEntry
	MAX-ACCESS  not-accessible
	STATUS      current
	DESCRIPTION
	"Table entry for ipv6ExtHbh"
	INDEX { ipv6ExtHbhLevelName }
	::={ipv6ExtHbhLevelTable 1}

Ipv6ExtHbhLevelEntry ::=
	SEQUENCE {
		ipv6ExtHbhLevelName	DisplayString,
		ipv6ExtHbhLevelVal	Counter64,
		ipv6ExtHbhLevelMom	CounterBasedGauge64,
		ipv6ExtHbhLevelMax	CounterBasedGauge64
	}

ipv6ExtHbhLevelName OBJECT-TYPE
	SYNTAX      DisplayString
	MAX-ACCESS  not-accessible
	STATUS      current
	DESCRIPTION
	"Table entry display string for ipv6ExtHbh"
	::={ipv6ExtHbhLevelEntry 1}

ipv6ExtHbhLevelVal OBJECT-TYPE
	SYNTAX	 Counter64
	MAX-ACCESS  read-only
	STATUS      current
	DESCRIPTION
	"Table entry attribute for ipv6ExtHbh"
	::={ipv6ExtHbhLevelEntry 2}

ipv6ExtHbhLevelMom OBJECT-TYPE
	SYNTAX	 CounterBasedGauge64
	MAX-ACCESS  read-only
	STATUS      current
	DESCRIPTION
	"Table entry attribute for ipv6ExtHbh"
	::={ipv6ExtHbhLevelEntry 3}

ipv6ExtHbhLevelMax OBJECT-TYPE
	SYNTAX	 CounterBasedGauge64
	MAX-ACCESS  read-only
	STATUS      current
	DESCRIPTION
	"Table entry attribute for ipv6ExtHbh"
	::={ipv6ExtHbhLevelEntry 4}


ipv6ExtRoute	OBJECT IDENTIFIER ::={ipv6 24}

ipv6ExtRouteVal	OBJECT-TYPE
	SYNTAX	 Counter64
	MAX-ACCESS read-only
	STATUS current
	DESCRIPTION "Route Ext, Headers"

	::={ipv6ExtRoute 1}

ipv6ExtRouteMom	OBJECT-TYPE
	SYNTAX	 CounterBasedGauge64
	MAX-ACCESS read-only
	STATUS current
	DESCRIPTION "Route Ext, Headers"

	::={ipv6ExtRoute 2}

ipv6ExtRouteMax	OBJECT-TYPE
	SYNTAX	 CounterBasedGauge64
	MAX-ACCESS read-only
	STATUS current
	DESCRIPTION "Route Ext, Headers"

	::={ipv6ExtRoute 3}

ipv6ExtRouteLevelTable OBJECT-TYPE
	SYNTAX      SEQUENCE OF Ipv6ExtRouteLevelEntry
	MAX-ACCESS  not-accessible
	STATUS      current
	DESCRIPTION
	"Table for ipv6ExtRoute"
	::={ipv6ExtRoute 4}

ipv6ExtRouteLevelEntry OBJECT-TYPE
	SYNTAX      Ipv6ExtRouteLevelEntry
	MAX-ACCESS  not-accessible
	STATUS      current
	DESCRIPTION
	"Table entry for ipv6ExtRoute"
	INDEX { ipv6ExtRouteLevelName }
	::={ipv6ExtRouteLevelTable 1}

Ipv6ExtRouteLevelEntry ::=
	SEQUENCE {
		ipv6ExtRouteLevelName	DisplayString,
		ipv6ExtRouteLevelVal	Counter64,
		ipv6ExtRouteLevelMom	CounterBasedGauge64,
		ipv6ExtRouteLevelMax	CounterBasedGauge64
	}

ipv6ExtRouteLevelName OBJECT-TYPE
	SYNTAX      DisplayString
	MAX-ACCESS  not-accessible
	STATUS      current
	DESCRIPTION
	"Table entry display string for ipv6ExtRoute"
	::={ipv6ExtRouteLevelEntry 1}

ipv6ExtRouteLevelVal OBJECT-TYPE
	SYNTAX	 Counter64
	MAX-ACCESS  read-only
	STATUS      current
	DESCRIPTION
	"Table entry attribute for ipv6ExtRoute"
	::={ipv6ExtRouteLevelEntry 2}

ipv6ExtRouteLevelMom OBJECT-TYPE
	SYNTAX	 CounterBasedGauge64
	MAX-ACCESS  read-only
	STATUS      current
	DESCRIPTION
	"Table entry attribute for ipv6ExtRoute"
	::={ipv6ExtRouteLevelEntry 3}

ipv6ExtRouteLevelMax OBJECT-TYPE
	SYNTAX	 CounterBasedGauge64
	MAX-ACCESS  read-only
	STATUS      current
	DESCRIPTION
	"Table entry attribute for ipv6ExtRoute"
	::={ipv6ExtRouteLevelEntry 4}


ipv6ExtInvl	OBJECT IDENTIFIER ::={ipv6 25}

ipv6ExtInvlVal	OBJECT-TYPE
	SYNTAX	 Counter64
	MAX-ACCESS read-only
	STATUS current
	DESCRIPTION "Invalid Ext. Headers"

	::={ipv6ExtInvl 1}

ipv6ExtInvlMom	OBJECT-TYPE
	SYNTAX	 CounterBasedGauge64
	MAX-ACCESS read-only
	STATUS current
	DESCRIPTION "Invalid Ext. Headers"

	::={ipv6ExtInvl 2}

ipv6ExtInvlMax	OBJECT-TYPE
	SYNTAX	 CounterBasedGauge64
	MAX-ACCESS read-only
	STATUS current
	DESCRIPTION "Invalid Ext. Headers"

	::={ipv6ExtInvl 3}

ipv6ExtInvlLevelTable OBJECT-TYPE
	SYNTAX      SEQUENCE OF Ipv6ExtInvlLevelEntry
	MAX-ACCESS  not-accessible
	STATUS      current
	DESCRIPTION
	"Table for ipv6ExtInvl"
	::={ipv6ExtInvl 4}

ipv6ExtInvlLevelEntry OBJECT-TYPE
	SYNTAX      Ipv6ExtInvlLevelEntry
	MAX-ACCESS  not-accessible
	STATUS      current
	DESCRIPTION
	"Table entry for ipv6ExtInvl"
	INDEX { ipv6ExtInvlLevelName }
	::={ipv6ExtInvlLevelTable 1}

Ipv6ExtInvlLevelEntry ::=
	SEQUENCE {
		ipv6ExtInvlLevelName	DisplayString,
		ipv6ExtInvlLevelVal	Counter64,
		ipv6ExtInvlLevelMom	CounterBasedGauge64,
		ipv6ExtInvlLevelMax	CounterBasedGauge64
	}

ipv6ExtInvlLevelName OBJECT-TYPE
	SYNTAX      DisplayString
	MAX-ACCESS  not-accessible
	STATUS      current
	DESCRIPTION
	"Table entry display string for ipv6ExtInvl"
	::={ipv6ExtInvlLevelEntry 1}

ipv6ExtInvlLevelVal OBJECT-TYPE
	SYNTAX	 Counter64
	MAX-ACCESS  read-only
	STATUS      current
	DESCRIPTION
	"Table entry attribute for ipv6ExtInvl"
	::={ipv6ExtInvlLevelEntry 2}

ipv6ExtInvlLevelMom OBJECT-TYPE
	SYNTAX	 CounterBasedGauge64
	MAX-ACCESS  read-only
	STATUS      current
	DESCRIPTION
	"Table entry attribute for ipv6ExtInvl"
	::={ipv6ExtInvlLevelEntry 3}

ipv6ExtInvlLevelMax OBJECT-TYPE
	SYNTAX	 CounterBasedGauge64
	MAX-ACCESS  read-only
	STATUS      current
	DESCRIPTION
	"Table entry attribute for ipv6ExtInvl"
	::={ipv6ExtInvlLevelEntry 4}


ipv6FragnentTimeout	OBJECT IDENTIFIER ::={ipv6 26}

ipv6FragnentTimeoutVal	OBJECT-TYPE
	SYNTAX	 Counter64
	MAX-ACCESS read-only
	STATUS current
	DESCRIPTION "Reassembly Timeout"

	::={ipv6FragnentTimeout 1}

ipv6FragnentTimeoutMom	OBJECT-TYPE
	SYNTAX	 CounterBasedGauge64
	MAX-ACCESS read-only
	STATUS current
	DESCRIPTION "Reassembly Timeout"

	::={ipv6FragnentTimeout 2}

ipv6FragnentTimeoutMax	OBJECT-TYPE
	SYNTAX	 CounterBasedGauge64
	MAX-ACCESS read-only
	STATUS current
	DESCRIPTION "Reassembly Timeout"

	::={ipv6FragnentTimeout 3}

ipv6FragnentTimeoutLevelTable OBJECT-TYPE
	SYNTAX      SEQUENCE OF Ipv6FragnentTimeoutLevelEntry
	MAX-ACCESS  not-accessible
	STATUS      current
	DESCRIPTION
	"Table for ipv6FragnentTimeout"
	::={ipv6FragnentTimeout 4}

ipv6FragnentTimeoutLevelEntry OBJECT-TYPE
	SYNTAX      Ipv6FragnentTimeoutLevelEntry
	MAX-ACCESS  not-accessible
	STATUS      current
	DESCRIPTION
	"Table entry for ipv6FragnentTimeout"
	INDEX { ipv6FragnentTimeoutLevelName }
	::={ipv6FragnentTimeoutLevelTable 1}

Ipv6FragnentTimeoutLevelEntry ::=
	SEQUENCE {
		ipv6FragnentTimeoutLevelName	DisplayString,
		ipv6FragnentTimeoutLevelVal	Counter64,
		ipv6FragnentTimeoutLevelMom	CounterBasedGauge64,
		ipv6FragnentTimeoutLevelMax	CounterBasedGauge64
	}

ipv6FragnentTimeoutLevelName OBJECT-TYPE
	SYNTAX      DisplayString
	MAX-ACCESS  not-accessible
	STATUS      current
	DESCRIPTION
	"Table entry display string for ipv6FragnentTimeout"
	::={ipv6FragnentTimeoutLevelEntry 1}

ipv6FragnentTimeoutLevelVal OBJECT-TYPE
	SYNTAX	 Counter64
	MAX-ACCESS  read-only
	STATUS      current
	DESCRIPTION
	"Table entry attribute for ipv6FragnentTimeout"
	::={ipv6FragnentTimeoutLevelEntry 2}

ipv6FragnentTimeoutLevelMom OBJECT-TYPE
	SYNTAX	 CounterBasedGauge64
	MAX-ACCESS  read-only
	STATUS      current
	DESCRIPTION
	"Table entry attribute for ipv6FragnentTimeout"
	::={ipv6FragnentTimeoutLevelEntry 3}

ipv6FragnentTimeoutLevelMax OBJECT-TYPE
	SYNTAX	 CounterBasedGauge64
	MAX-ACCESS  read-only
	STATUS      current
	DESCRIPTION
	"Table entry attribute for ipv6FragnentTimeout"
	::={ipv6FragnentTimeoutLevelEntry 4}


ipv6FragmentDrops	OBJECT IDENTIFIER ::={ipv6 27}

ipv6FragmentDropsVal	OBJECT-TYPE
	SYNTAX	 Counter64
	MAX-ACCESS read-only
	STATUS current
	DESCRIPTION "Dropped fragments (timeout/LRU)"

	::={ipv6FragmentDrops 1}

ipv6FragmentDropsMom	OBJECT-TYPE
	SYNTAX	 CounterBasedGauge64
	MAX-ACCESS read-only
	STATUS current
	DESCRIPTION "Dropped fragments (timeout/LRU)"

	::={ipv6FragmentDrops 2}

ipv6FragmentDropsMax	OBJECT-TYPE
	SYNTAX	 CounterBasedGauge64
	MAX-ACCESS read-only
	STATUS current
	DESCRIPTION "Dropped fragments (timeout/LRU)"

	::={ipv6FragmentDrops 3}

ipv6FragmentDropsLevelTable OBJECT-TYPE
	SYNTAX      SEQUENCE OF Ipv6FragmentDropsLevelEntry
	MAX-ACCESS  not-accessible
	STATUS      current
	DESCRIPTION
	"Table for ipv6FragmentDrops"
	::={ipv6FragmentDrops 4}

ipv6FragmentDropsLevelEntry OBJECT-TYPE
	SYNTAX      Ipv6FragmentDropsLevelEntry
	MAX-ACCESS  not-accessible
	STATUS      current
	DESCRIPTION
	"Table entry for ipv6FragmentDrops"
	INDEX { ipv6FragmentDropsLevelName }
	::={ipv6FragmentDropsLevelTable 1}

Ipv6FragmentDropsLevelEntry ::=
	SEQUENCE {
		ipv6FragmentDropsLevelName	DisplayString,
		ipv6FragmentDropsLevelVal	Counter64,
		ipv6FragmentDropsLevelMom	CounterBasedGauge64,
		ipv6FragmentDropsLevelMax	CounterBasedGauge64
	}

ipv6FragmentDropsLevelName OBJECT-TYPE
	SYNTAX      DisplayString
	MAX-ACCESS  not-accessible
	STATUS      current
	DESCRIPTION
	"Table entry display string for ipv6FragmentDrops"
	::={ipv6FragmentDropsLevelEntry 1}

ipv6FragmentDropsLevelVal OBJECT-TYPE
	SYNTAX	 Counter64
	MAX-ACCESS  read-only
	STATUS      current
	DESCRIPTION
	"Table entry attribute for ipv6FragmentDrops"
	::={ipv6FragmentDropsLevelEntry 2}

ipv6FragmentDropsLevelMom OBJECT-TYPE
	SYNTAX	 CounterBasedGauge64
	MAX-ACCESS  read-only
	STATUS      current
	DESCRIPTION
	"Table entry attribute for ipv6FragmentDrops"
	::={ipv6FragmentDropsLevelEntry 3}

ipv6FragmentDropsLevelMax OBJECT-TYPE
	SYNTAX	 CounterBasedGauge64
	MAX-ACCESS  read-only
	STATUS      current
	DESCRIPTION
	"Table entry attribute for ipv6FragmentDrops"
	::={ipv6FragmentDropsLevelEntry 4}


ipv6ShuntAddressPackets	OBJECT IDENTIFIER ::={ipv6 28}

ipv6ShuntAddressPacketsVal	OBJECT-TYPE
	SYNTAX	 Counter64
	MAX-ACCESS read-only
	STATUS current
	DESCRIPTION "Shunted packets (address)"

	::={ipv6ShuntAddressPackets 1}

ipv6ShuntAddressPacketsMom	OBJECT-TYPE
	SYNTAX	 CounterBasedGauge64
	MAX-ACCESS read-only
	STATUS current
	DESCRIPTION "Shunted packets (address)"

	::={ipv6ShuntAddressPackets 2}

ipv6ShuntAddressPacketsMax	OBJECT-TYPE
	SYNTAX	 CounterBasedGauge64
	MAX-ACCESS read-only
	STATUS current
	DESCRIPTION "Shunted packets (address)"

	::={ipv6ShuntAddressPackets 3}

ipv6ShuntAddressPacketsLevelTable OBJECT-TYPE
	SYNTAX      SEQUENCE OF Ipv6ShuntAddressPacketsLevelEntry
	MAX-ACCESS  not-accessible
	STATUS      current
	DESCRIPTION
	"Table for ipv6ShuntAddressPackets"
	::={ipv6ShuntAddressPackets 4}

ipv6ShuntAddressPacketsLevelEntry OBJECT-TYPE
	SYNTAX      Ipv6ShuntAddressPacketsLevelEntry
	MAX-ACCESS  not-accessible
	STATUS      current
	DESCRIPTION
	"Table entry for ipv6ShuntAddressPackets"
	INDEX { ipv6ShuntAddressPacketsLevelName }
	::={ipv6ShuntAddressPacketsLevelTable 1}

Ipv6ShuntAddressPacketsLevelEntry ::=
	SEQUENCE {
		ipv6ShuntAddressPacketsLevelName	DisplayString,
		ipv6ShuntAddressPacketsLevelVal	Counter64,
		ipv6ShuntAddressPacketsLevelMom	CounterBasedGauge64,
		ipv6ShuntAddressPacketsLevelMax	CounterBasedGauge64
	}

ipv6ShuntAddressPacketsLevelName OBJECT-TYPE
	SYNTAX      DisplayString
	MAX-ACCESS  not-accessible
	STATUS      current
	DESCRIPTION
	"Table entry display string for ipv6ShuntAddressPackets"
	::={ipv6ShuntAddressPacketsLevelEntry 1}

ipv6ShuntAddressPacketsLevelVal OBJECT-TYPE
	SYNTAX	 Counter64
	MAX-ACCESS  read-only
	STATUS      current
	DESCRIPTION
	"Table entry attribute for ipv6ShuntAddressPackets"
	::={ipv6ShuntAddressPacketsLevelEntry 2}

ipv6ShuntAddressPacketsLevelMom OBJECT-TYPE
	SYNTAX	 CounterBasedGauge64
	MAX-ACCESS  read-only
	STATUS      current
	DESCRIPTION
	"Table entry attribute for ipv6ShuntAddressPackets"
	::={ipv6ShuntAddressPacketsLevelEntry 3}

ipv6ShuntAddressPacketsLevelMax OBJECT-TYPE
	SYNTAX	 CounterBasedGauge64
	MAX-ACCESS  read-only
	STATUS      current
	DESCRIPTION
	"Table entry attribute for ipv6ShuntAddressPackets"
	::={ipv6ShuntAddressPacketsLevelEntry 4}


ipv6ShuntAddressBytes	OBJECT IDENTIFIER ::={ipv6 29}

ipv6ShuntAddressBytesVal	OBJECT-TYPE
	SYNTAX	 Counter64
	MAX-ACCESS read-only
	STATUS current
	DESCRIPTION "Shunted bytes (address)"

	::={ipv6ShuntAddressBytes 1}

ipv6ShuntAddressBytesMom	OBJECT-TYPE
	SYNTAX	 CounterBasedGauge64
	MAX-ACCESS read-only
	STATUS current
	DESCRIPTION "Shunted bytes (address)"

	::={ipv6ShuntAddressBytes 2}

ipv6ShuntAddressBytesMax	OBJECT-TYPE
	SYNTAX	 CounterBasedGauge64
	MAX-ACCESS read-only
	STATUS current
	DESCRIPTION "Shunted bytes (address)"

	::={ipv6ShuntAddressBytes 3}

ipv6ShuntAddressBytesLevelTable OBJECT-TYPE
	SYNTAX      SEQUENCE OF Ipv6ShuntAddressBytesLevelEntry
	MAX-ACCESS  not-accessible
	STATUS      current
	DESCRIPTION
	"Table for ipv6ShuntAddressBytes"
	::={ipv6ShuntAddressBytes 4}

ipv6ShuntAddressBytesLevelEntry OBJECT-TYPE
	SYNTAX      Ipv6ShuntAddressBytesLevelEntry
	MAX-ACCESS  not-accessible
	STATUS      current
	DESCRIPTION
	"Table entry for ipv6ShuntAddressBytes"
	INDEX { ipv6ShuntAddressBytesLevelName }
	::={ipv6ShuntAddressBytesLevelTable 1}

Ipv6ShuntAddressBytesLevelEntry ::=
	SEQUENCE {
		ipv6ShuntAddressBytesLevelName	DisplayString,
		ipv6ShuntAddressBytesLevelVal	Counter64,
		ipv6ShuntAddressBytesLevelMom	CounterBasedGauge64,
		ipv6ShuntAddressBytesLevelMax	CounterBasedGauge64
	}

ipv6ShuntAddressBytesLevelName OBJECT-TYPE
	SYNTAX      DisplayString
	MAX-ACCESS  not-accessible
	STATUS      current
	DESCRIPTION
	"Table entry display string for ipv6ShuntAddressBytes"
	::={ipv6ShuntAddressBytesLevelEntry 1}

ipv6ShuntAddressBytesLevelVal OBJECT-TYPE
	SYNTAX	 Counter64
	MAX-ACCESS  read-only
	STATUS      current
	DESCRIPTION
	"Table entry attribute for ipv6ShuntAddressBytes"
	::={ipv6ShuntAddressBytesLevelEntry 2}

ipv6ShuntAddressBytesLevelMom OBJECT-TYPE
	SYNTAX	 CounterBasedGauge64
	MAX-ACCESS  read-only
	STATUS      current
	DESCRIPTION
	"Table entry attribute for ipv6ShuntAddressBytes"
	::={ipv6ShuntAddressBytesLevelEntry 3}

ipv6ShuntAddressBytesLevelMax OBJECT-TYPE
	SYNTAX	 CounterBasedGauge64
	MAX-ACCESS  read-only
	STATUS      current
	DESCRIPTION
	"Table entry attribute for ipv6ShuntAddressBytes"
	::={ipv6ShuntAddressBytesLevelEntry 4}


ipv6ShuntProtoPackets	OBJECT IDENTIFIER ::={ipv6 30}

ipv6ShuntProtoPacketsVal	OBJECT-TYPE
	SYNTAX	 Counter64
	MAX-ACCESS read-only
	STATUS current
	DESCRIPTION "Shunted packets (protocol)"

	::={ipv6ShuntProtoPackets 1}

ipv6ShuntProtoPacketsMom	OBJECT-TYPE
	SYNTAX	 CounterBasedGauge64
	MAX-ACCESS read-only
	STATUS current
	DESCRIPTION "Shunted packets (protocol)"

	::={ipv6ShuntProtoPackets 2}

ipv6ShuntProtoPacketsMax	OBJECT-TYPE
	SYNTAX	 CounterBasedGauge64
	MAX-ACCESS read-only
	STATUS current
	DESCRIPTION "Shunted packets (protocol)"

	::={ipv6ShuntProtoPackets 3}

ipv6ShuntProtoPacketsLevelTable OBJECT-TYPE
	SYNTAX      SEQUENCE OF Ipv6ShuntProtoPacketsLevelEntry
	MAX-ACCESS  not-accessible
	STATUS      current
	DESCRIPTION
	"Table for ipv6ShuntProtoPackets"
	::={ipv6ShuntProtoPackets 4}

ipv6ShuntProtoPacketsLevelEntry OBJECT-TYPE
	SYNTAX      Ipv6ShuntProtoPacketsLevelEntry
	MAX-ACCESS  not-accessible
	STATUS      current
	DESCRIPTION
	"Table entry for ipv6ShuntProtoPackets"
	INDEX { ipv6ShuntProtoPacketsLevelName }
	::={ipv6ShuntProtoPacketsLevelTable 1}

Ipv6ShuntProtoPacketsLevelEntry ::=
	SEQUENCE {
		ipv6ShuntProtoPacketsLevelName	DisplayString,
		ipv6ShuntProtoPacketsLevelVal	Counter64,
		ipv6ShuntProtoPacketsLevelMom	CounterBasedGauge64,
		ipv6ShuntProtoPacketsLevelMax	CounterBasedGauge64
	}

ipv6ShuntProtoPacketsLevelName OBJECT-TYPE
	SYNTAX      DisplayString
	MAX-ACCESS  not-accessible
	STATUS      current
	DESCRIPTION
	"Table entry display string for ipv6ShuntProtoPackets"
	::={ipv6ShuntProtoPacketsLevelEntry 1}

ipv6ShuntProtoPacketsLevelVal OBJECT-TYPE
	SYNTAX	 Counter64
	MAX-ACCESS  read-only
	STATUS      current
	DESCRIPTION
	"Table entry attribute for ipv6ShuntProtoPackets"
	::={ipv6ShuntProtoPacketsLevelEntry 2}

ipv6ShuntProtoPacketsLevelMom OBJECT-TYPE
	SYNTAX	 CounterBasedGauge64
	MAX-ACCESS  read-only
	STATUS      current
	DESCRIPTION
	"Table entry attribute for ipv6ShuntProtoPackets"
	::={ipv6ShuntProtoPacketsLevelEntry 3}

ipv6ShuntProtoPacketsLevelMax OBJECT-TYPE
	SYNTAX	 CounterBasedGauge64
	MAX-ACCESS  read-only
	STATUS      current
	DESCRIPTION
	"Table entry attribute for ipv6ShuntProtoPackets"
	::={ipv6ShuntProtoPacketsLevelEntry 4}


ipv6ShuntProtoBytes	OBJECT IDENTIFIER ::={ipv6 31}

ipv6ShuntProtoBytesVal	OBJECT-TYPE
	SYNTAX	 Counter64
	MAX-ACCESS read-only
	STATUS current
	DESCRIPTION "Shunted bytes (protocol)"

	::={ipv6ShuntProtoBytes 1}

ipv6ShuntProtoBytesMom	OBJECT-TYPE
	SYNTAX	 CounterBasedGauge64
	MAX-ACCESS read-only
	STATUS current
	DESCRIPTION "Shunted bytes (protocol)"

	::={ipv6ShuntProtoBytes 2}

ipv6ShuntProtoBytesMax	OBJECT-TYPE
	SYNTAX	 CounterBasedGauge64
	MAX-ACCESS read-only
	STATUS current
	DESCRIPTION "Shunted bytes (protocol)"

	::={ipv6ShuntProtoBytes 3}

ipv6ShuntProtoBytesLevelTable OBJECT-TYPE
	SYNTAX      SEQUENCE OF Ipv6ShuntProtoBytesLevelEntry
	MAX-ACCESS  not-accessible
	STATUS      current
	DESCRIPTION
	"Table for ipv6ShuntProtoBytes"
	::={ipv6ShuntProtoBytes 4}

ipv6ShuntProtoBytesLevelEntry OBJECT-TYPE
	SYNTAX      Ipv6ShuntProtoBytesLevelEntry
	MAX-ACCESS  not-accessible
	STATUS      current
	DESCRIPTION
	"Table entry for ipv6ShuntProtoBytes"
	INDEX { ipv6ShuntProtoBytesLevelName }
	::={ipv6ShuntProtoBytesLevelTable 1}

Ipv6ShuntProtoBytesLevelEntry ::=
	SEQUENCE {
		ipv6ShuntProtoBytesLevelName	DisplayString,
		ipv6ShuntProtoBytesLevelVal	Counter64,
		ipv6ShuntProtoBytesLevelMom	CounterBasedGauge64,
		ipv6ShuntProtoBytesLevelMax	CounterBasedGauge64
	}

ipv6ShuntProtoBytesLevelName OBJECT-TYPE
	SYNTAX      DisplayString
	MAX-ACCESS  not-accessible
	STATUS      current
	DESCRIPTION
	"Table entry display string for ipv6ShuntProtoBytes"
	::={ipv6ShuntProtoBytesLevelEntry 1}

ipv6ShuntProtoBytesLevelVal OBJECT-TYPE
	SYNTAX	 Counter64
	MAX-ACCESS  read-only
	STATUS      current
	DESCRIPTION
	"Table entry attribute for ipv6ShuntProtoBytes"
	::={ipv6ShuntProtoBytesLevelEntry 2}

ipv6ShuntProtoBytesLevelMom OBJECT-TYPE
	SYNTAX	 CounterBasedGauge64
	MAX-ACCESS  read-only
	STATUS      current
	DESCRIPTION
	"Table entry attribute for ipv6ShuntProtoBytes"
	::={ipv6ShuntProtoBytesLevelEntry 3}

ipv6ShuntProtoBytesLevelMax OBJECT-TYPE
	SYNTAX	 CounterBasedGauge64
	MAX-ACCESS  read-only
	STATUS      current
	DESCRIPTION
	"Table entry attribute for ipv6ShuntProtoBytes"
	::={ipv6ShuntProtoBytesLevelEntry 4}


ipv6FragInFrag	OBJECT IDENTIFIER ::={ipv6 32}

ipv6FragInFragVal	OBJECT-TYPE
	SYNTAX	 Counter64
	MAX-ACCESS read-only
	STATUS current
	DESCRIPTION "Fragments in Fragments"

	::={ipv6FragInFrag 1}

ipv6FragInFragMom	OBJECT-TYPE
	SYNTAX	 CounterBasedGauge64
	MAX-ACCESS read-only
	STATUS current
	DESCRIPTION "Fragments in Fragments"

	::={ipv6FragInFrag 2}

ipv6FragInFragMax	OBJECT-TYPE
	SYNTAX	 CounterBasedGauge64
	MAX-ACCESS read-only
	STATUS current
	DESCRIPTION "Fragments in Fragments"

	::={ipv6FragInFrag 3}

ipv6FragInFragLevelTable OBJECT-TYPE
	SYNTAX      SEQUENCE OF Ipv6FragInFragLevelEntry
	MAX-ACCESS  not-accessible
	STATUS      current
	DESCRIPTION
	"Table for ipv6FragInFrag"
	::={ipv6FragInFrag 4}

ipv6FragInFragLevelEntry OBJECT-TYPE
	SYNTAX      Ipv6FragInFragLevelEntry
	MAX-ACCESS  not-accessible
	STATUS      current
	DESCRIPTION
	"Table entry for ipv6FragInFrag"
	INDEX { ipv6FragInFragLevelName }
	::={ipv6FragInFragLevelTable 1}

Ipv6FragInFragLevelEntry ::=
	SEQUENCE {
		ipv6FragInFragLevelName	DisplayString,
		ipv6FragInFragLevelVal	Counter64,
		ipv6FragInFragLevelMom	CounterBasedGauge64,
		ipv6FragInFragLevelMax	CounterBasedGauge64
	}

ipv6FragInFragLevelName OBJECT-TYPE
	SYNTAX      DisplayString
	MAX-ACCESS  not-accessible
	STATUS      current
	DESCRIPTION
	"Table entry display string for ipv6FragInFrag"
	::={ipv6FragInFragLevelEntry 1}

ipv6FragInFragLevelVal OBJECT-TYPE
	SYNTAX	 Counter64
	MAX-ACCESS  read-only
	STATUS      current
	DESCRIPTION
	"Table entry attribute for ipv6FragInFrag"
	::={ipv6FragInFragLevelEntry 2}

ipv6FragInFragLevelMom OBJECT-TYPE
	SYNTAX	 CounterBasedGauge64
	MAX-ACCESS  read-only
	STATUS      current
	DESCRIPTION
	"Table entry attribute for ipv6FragInFrag"
	::={ipv6FragInFragLevelEntry 3}

ipv6FragInFragLevelMax OBJECT-TYPE
	SYNTAX	 CounterBasedGauge64
	MAX-ACCESS  read-only
	STATUS      current
	DESCRIPTION
	"Table entry attribute for ipv6FragInFrag"
	::={ipv6FragInFragLevelEntry 4}


ipv6EcnEct0	OBJECT IDENTIFIER ::={ipv6 33}

ipv6EcnEct0Val	OBJECT-TYPE
	SYNTAX	 Counter64
	MAX-ACCESS read-only
	STATUS current
	DESCRIPTION "ECN Capable Packets ECT(0)"

	::={ipv6EcnEct0 1}

ipv6EcnEct0Mom	OBJECT-TYPE
	SYNTAX	 CounterBasedGauge64
	MAX-ACCESS read-only
	STATUS current
	DESCRIPTION "ECN Capable Packets ECT(0)"

	::={ipv6EcnEct0 2}

ipv6EcnEct0Max	OBJECT-TYPE
	SYNTAX	 CounterBasedGauge64
	MAX-ACCESS read-only
	STATUS current
	DESCRIPTION "ECN Capable Packets ECT(0)"

	::={ipv6EcnEct0 3}

ipv6EcnEct0LevelTable OBJECT-TYPE
	SYNTAX      SEQUENCE OF Ipv6EcnEct0LevelEntry
	MAX-ACCESS  not-accessible
	STATUS      current
	DESCRIPTION
	"Table for ipv6EcnEct0"
	::={ipv6EcnEct0 4}

ipv6EcnEct0LevelEntry OBJECT-TYPE
	SYNTAX      Ipv6EcnEct0LevelEntry
	MAX-ACCESS  not-accessible
	STATUS      current
	DESCRIPTION
	"Table entry for ipv6EcnEct0"
	INDEX { ipv6EcnEct0LevelName }
	::={ipv6EcnEct0LevelTable 1}

Ipv6EcnEct0LevelEntry ::=
	SEQUENCE {
		ipv6EcnEct0LevelName	DisplayString,
		ipv6EcnEct0LevelVal	Counter64,
		ipv6EcnEct0LevelMom	CounterBasedGauge64,
		ipv6EcnEct0LevelMax	CounterBasedGauge64
	}

ipv6EcnEct0LevelName OBJECT-TYPE
	SYNTAX      DisplayString
	MAX-ACCESS  not-accessible
	STATUS      current
	DESCRIPTION
	"Table entry display string for ipv6EcnEct0"
	::={ipv6EcnEct0LevelEntry 1}

ipv6EcnEct0LevelVal OBJECT-TYPE
	SYNTAX	 Counter64
	MAX-ACCESS  read-only
	STATUS      current
	DESCRIPTION
	"Table entry attribute for ipv6EcnEct0"
	::={ipv6EcnEct0LevelEntry 2}

ipv6EcnEct0LevelMom OBJECT-TYPE
	SYNTAX	 CounterBasedGauge64
	MAX-ACCESS  read-only
	STATUS      current
	DESCRIPTION
	"Table entry attribute for ipv6EcnEct0"
	::={ipv6EcnEct0LevelEntry 3}

ipv6EcnEct0LevelMax OBJECT-TYPE
	SYNTAX	 CounterBasedGauge64
	MAX-ACCESS  read-only
	STATUS      current
	DESCRIPTION
	"Table entry attribute for ipv6EcnEct0"
	::={ipv6EcnEct0LevelEntry 4}


ipv6EcnEct1	OBJECT IDENTIFIER ::={ipv6 34}

ipv6EcnEct1Val	OBJECT-TYPE
	SYNTAX	 Counter64
	MAX-ACCESS read-only
	STATUS current
	DESCRIPTION "ECN Capable Packets ECT(1)"

	::={ipv6EcnEct1 1}

ipv6EcnEct1Mom	OBJECT-TYPE
	SYNTAX	 CounterBasedGauge64
	MAX-ACCESS read-only
	STATUS current
	DESCRIPTION "ECN Capable Packets ECT(1)"

	::={ipv6EcnEct1 2}

ipv6EcnEct1Max	OBJECT-TYPE
	SYNTAX	 CounterBasedGauge64
	MAX-ACCESS read-only
	STATUS current
	DESCRIPTION "ECN Capable Packets ECT(1)"

	::={ipv6EcnEct1 3}

ipv6EcnEct1LevelTable OBJECT-TYPE
	SYNTAX      SEQUENCE OF Ipv6EcnEct1LevelEntry
	MAX-ACCESS  not-accessible
	STATUS      current
	DESCRIPTION
	"Table for ipv6EcnEct1"
	::={ipv6EcnEct1 4}

ipv6EcnEct1LevelEntry OBJECT-TYPE
	SYNTAX      Ipv6EcnEct1LevelEntry
	MAX-ACCESS  not-accessible
	STATUS      current
	DESCRIPTION
	"Table entry for ipv6EcnEct1"
	INDEX { ipv6EcnEct1LevelName }
	::={ipv6EcnEct1LevelTable 1}

Ipv6EcnEct1LevelEntry ::=
	SEQUENCE {
		ipv6EcnEct1LevelName	DisplayString,
		ipv6EcnEct1LevelVal	Counter64,
		ipv6EcnEct1LevelMom	CounterBasedGauge64,
		ipv6EcnEct1LevelMax	CounterBasedGauge64
	}

ipv6EcnEct1LevelName OBJECT-TYPE
	SYNTAX      DisplayString
	MAX-ACCESS  not-accessible
	STATUS      current
	DESCRIPTION
	"Table entry display string for ipv6EcnEct1"
	::={ipv6EcnEct1LevelEntry 1}

ipv6EcnEct1LevelVal OBJECT-TYPE
	SYNTAX	 Counter64
	MAX-ACCESS  read-only
	STATUS      current
	DESCRIPTION
	"Table entry attribute for ipv6EcnEct1"
	::={ipv6EcnEct1LevelEntry 2}

ipv6EcnEct1LevelMom OBJECT-TYPE
	SYNTAX	 CounterBasedGauge64
	MAX-ACCESS  read-only
	STATUS      current
	DESCRIPTION
	"Table entry attribute for ipv6EcnEct1"
	::={ipv6EcnEct1LevelEntry 3}

ipv6EcnEct1LevelMax OBJECT-TYPE
	SYNTAX	 CounterBasedGauge64
	MAX-ACCESS  read-only
	STATUS      current
	DESCRIPTION
	"Table entry attribute for ipv6EcnEct1"
	::={ipv6EcnEct1LevelEntry 4}


ipv6EcnCn	OBJECT IDENTIFIER ::={ipv6 35}

ipv6EcnCnVal	OBJECT-TYPE
	SYNTAX	 Counter64
	MAX-ACCESS read-only
	STATUS current
	DESCRIPTION "ECN Packets Congestion Experienced"

	::={ipv6EcnCn 1}

ipv6EcnCnMom	OBJECT-TYPE
	SYNTAX	 CounterBasedGauge64
	MAX-ACCESS read-only
	STATUS current
	DESCRIPTION "ECN Packets Congestion Experienced"

	::={ipv6EcnCn 2}

ipv6EcnCnMax	OBJECT-TYPE
	SYNTAX	 CounterBasedGauge64
	MAX-ACCESS read-only
	STATUS current
	DESCRIPTION "ECN Packets Congestion Experienced"

	::={ipv6EcnCn 3}

ipv6EcnCnLevelTable OBJECT-TYPE
	SYNTAX      SEQUENCE OF Ipv6EcnCnLevelEntry
	MAX-ACCESS  not-accessible
	STATUS      current
	DESCRIPTION
	"Table for ipv6EcnCn"
	::={ipv6EcnCn 4}

ipv6EcnCnLevelEntry OBJECT-TYPE
	SYNTAX      Ipv6EcnCnLevelEntry
	MAX-ACCESS  not-accessible
	STATUS      current
	DESCRIPTION
	"Table entry for ipv6EcnCn"
	INDEX { ipv6EcnCnLevelName }
	::={ipv6EcnCnLevelTable 1}

Ipv6EcnCnLevelEntry ::=
	SEQUENCE {
		ipv6EcnCnLevelName	DisplayString,
		ipv6EcnCnLevelVal	Counter64,
		ipv6EcnCnLevelMom	CounterBasedGauge64,
		ipv6EcnCnLevelMax	CounterBasedGauge64
	}

ipv6EcnCnLevelName OBJECT-TYPE
	SYNTAX      DisplayString
	MAX-ACCESS  not-accessible
	STATUS      current
	DESCRIPTION
	"Table entry display string for ipv6EcnCn"
	::={ipv6EcnCnLevelEntry 1}

ipv6EcnCnLevelVal OBJECT-TYPE
	SYNTAX	 Counter64
	MAX-ACCESS  read-only
	STATUS      current
	DESCRIPTION
	"Table entry attribute for ipv6EcnCn"
	::={ipv6EcnCnLevelEntry 2}

ipv6EcnCnLevelMom OBJECT-TYPE
	SYNTAX	 CounterBasedGauge64
	MAX-ACCESS  read-only
	STATUS      current
	DESCRIPTION
	"Table entry attribute for ipv6EcnCn"
	::={ipv6EcnCnLevelEntry 3}

ipv6EcnCnLevelMax OBJECT-TYPE
	SYNTAX	 CounterBasedGauge64
	MAX-ACCESS  read-only
	STATUS      current
	DESCRIPTION
	"Table entry attribute for ipv6EcnCn"
	::={ipv6EcnCnLevelEntry 4}


ipv6ShuntDscpPackets	OBJECT IDENTIFIER ::={ipv6 36}

ipv6ShuntDscpPacketsVal	OBJECT-TYPE
	SYNTAX	 Counter64
	MAX-ACCESS read-only
	STATUS current
	DESCRIPTION "Shunted packets (DSCP)"

	::={ipv6ShuntDscpPackets 1}

ipv6ShuntDscpPacketsMom	OBJECT-TYPE
	SYNTAX	 CounterBasedGauge64
	MAX-ACCESS read-only
	STATUS current
	DESCRIPTION "Shunted packets (DSCP)"

	::={ipv6ShuntDscpPackets 2}

ipv6ShuntDscpPacketsMax	OBJECT-TYPE
	SYNTAX	 CounterBasedGauge64
	MAX-ACCESS read-only
	STATUS current
	DESCRIPTION "Shunted packets (DSCP)"

	::={ipv6ShuntDscpPackets 3}

ipv6ShuntDscpPacketsLevelTable OBJECT-TYPE
	SYNTAX      SEQUENCE OF Ipv6ShuntDscpPacketsLevelEntry
	MAX-ACCESS  not-accessible
	STATUS      current
	DESCRIPTION
	"Table for ipv6ShuntDscpPackets"
	::={ipv6ShuntDscpPackets 4}

ipv6ShuntDscpPacketsLevelEntry OBJECT-TYPE
	SYNTAX      Ipv6ShuntDscpPacketsLevelEntry
	MAX-ACCESS  not-accessible
	STATUS      current
	DESCRIPTION
	"Table entry for ipv6ShuntDscpPackets"
	INDEX { ipv6ShuntDscpPacketsLevelName }
	::={ipv6ShuntDscpPacketsLevelTable 1}

Ipv6ShuntDscpPacketsLevelEntry ::=
	SEQUENCE {
		ipv6ShuntDscpPacketsLevelName	DisplayString,
		ipv6ShuntDscpPacketsLevelVal	Counter64,
		ipv6ShuntDscpPacketsLevelMom	CounterBasedGauge64,
		ipv6ShuntDscpPacketsLevelMax	CounterBasedGauge64
	}

ipv6ShuntDscpPacketsLevelName OBJECT-TYPE
	SYNTAX      DisplayString
	MAX-ACCESS  not-accessible
	STATUS      current
	DESCRIPTION
	"Table entry display string for ipv6ShuntDscpPackets"
	::={ipv6ShuntDscpPacketsLevelEntry 1}

ipv6ShuntDscpPacketsLevelVal OBJECT-TYPE
	SYNTAX	 Counter64
	MAX-ACCESS  read-only
	STATUS      current
	DESCRIPTION
	"Table entry attribute for ipv6ShuntDscpPackets"
	::={ipv6ShuntDscpPacketsLevelEntry 2}

ipv6ShuntDscpPacketsLevelMom OBJECT-TYPE
	SYNTAX	 CounterBasedGauge64
	MAX-ACCESS  read-only
	STATUS      current
	DESCRIPTION
	"Table entry attribute for ipv6ShuntDscpPackets"
	::={ipv6ShuntDscpPacketsLevelEntry 3}

ipv6ShuntDscpPacketsLevelMax OBJECT-TYPE
	SYNTAX	 CounterBasedGauge64
	MAX-ACCESS  read-only
	STATUS      current
	DESCRIPTION
	"Table entry attribute for ipv6ShuntDscpPackets"
	::={ipv6ShuntDscpPacketsLevelEntry 4}


ipv6ShuntDscpBytes	OBJECT IDENTIFIER ::={ipv6 37}

ipv6ShuntDscpBytesVal	OBJECT-TYPE
	SYNTAX	 Counter64
	MAX-ACCESS read-only
	STATUS current
	DESCRIPTION "Shunted bytes (DSCP)"

	::={ipv6ShuntDscpBytes 1}

ipv6ShuntDscpBytesMom	OBJECT-TYPE
	SYNTAX	 CounterBasedGauge64
	MAX-ACCESS read-only
	STATUS current
	DESCRIPTION "Shunted bytes (DSCP)"

	::={ipv6ShuntDscpBytes 2}

ipv6ShuntDscpBytesMax	OBJECT-TYPE
	SYNTAX	 CounterBasedGauge64
	MAX-ACCESS read-only
	STATUS current
	DESCRIPTION "Shunted bytes (DSCP)"

	::={ipv6ShuntDscpBytes 3}

ipv6ShuntDscpBytesLevelTable OBJECT-TYPE
	SYNTAX      SEQUENCE OF Ipv6ShuntDscpBytesLevelEntry
	MAX-ACCESS  not-accessible
	STATUS      current
	DESCRIPTION
	"Table for ipv6ShuntDscpBytes"
	::={ipv6ShuntDscpBytes 4}

ipv6ShuntDscpBytesLevelEntry OBJECT-TYPE
	SYNTAX      Ipv6ShuntDscpBytesLevelEntry
	MAX-ACCESS  not-accessible
	STATUS      current
	DESCRIPTION
	"Table entry for ipv6ShuntDscpBytes"
	INDEX { ipv6ShuntDscpBytesLevelName }
	::={ipv6ShuntDscpBytesLevelTable 1}

Ipv6ShuntDscpBytesLevelEntry ::=
	SEQUENCE {
		ipv6ShuntDscpBytesLevelName	DisplayString,
		ipv6ShuntDscpBytesLevelVal	Counter64,
		ipv6ShuntDscpBytesLevelMom	CounterBasedGauge64,
		ipv6ShuntDscpBytesLevelMax	CounterBasedGauge64
	}

ipv6ShuntDscpBytesLevelName OBJECT-TYPE
	SYNTAX      DisplayString
	MAX-ACCESS  not-accessible
	STATUS      current
	DESCRIPTION
	"Table entry display string for ipv6ShuntDscpBytes"
	::={ipv6ShuntDscpBytesLevelEntry 1}

ipv6ShuntDscpBytesLevelVal OBJECT-TYPE
	SYNTAX	 Counter64
	MAX-ACCESS  read-only
	STATUS      current
	DESCRIPTION
	"Table entry attribute for ipv6ShuntDscpBytes"
	::={ipv6ShuntDscpBytesLevelEntry 2}

ipv6ShuntDscpBytesLevelMom OBJECT-TYPE
	SYNTAX	 CounterBasedGauge64
	MAX-ACCESS  read-only
	STATUS      current
	DESCRIPTION
	"Table entry attribute for ipv6ShuntDscpBytes"
	::={ipv6ShuntDscpBytesLevelEntry 3}

ipv6ShuntDscpBytesLevelMax OBJECT-TYPE
	SYNTAX	 CounterBasedGauge64
	MAX-ACCESS  read-only
	STATUS      current
	DESCRIPTION
	"Table entry attribute for ipv6ShuntDscpBytes"
	::={ipv6ShuntDscpBytesLevelEntry 4}


tcpv4	OBJECT IDENTIFIER ::={sysdiag 48}

tcpv4Packets	OBJECT IDENTIFIER ::={tcpv4 1}

tcpv4PacketsVal	OBJECT-TYPE
	SYNTAX	 Counter64
	MAX-ACCESS read-only
	STATUS current
	DESCRIPTION "RX packets"

	::={tcpv4Packets 1}

tcpv4PacketsMom	OBJECT-TYPE
	SYNTAX	 CounterBasedGauge64
	MAX-ACCESS read-only
	STATUS current
	DESCRIPTION "RX packets"

	::={tcpv4Packets 2}

tcpv4PacketsMax	OBJECT-TYPE
	SYNTAX	 CounterBasedGauge64
	MAX-ACCESS read-only
	STATUS current
	DESCRIPTION "RX packets"

	::={tcpv4Packets 3}

tcpv4PacketsLevelTable OBJECT-TYPE
	SYNTAX      SEQUENCE OF Tcpv4PacketsLevelEntry
	MAX-ACCESS  not-accessible
	STATUS      current
	DESCRIPTION
	"Table for tcpv4Packets"
	::={tcpv4Packets 4}

tcpv4PacketsLevelEntry OBJECT-TYPE
	SYNTAX      Tcpv4PacketsLevelEntry
	MAX-ACCESS  not-accessible
	STATUS      current
	DESCRIPTION
	"Table entry for tcpv4Packets"
	INDEX { tcpv4PacketsLevelName }
	::={tcpv4PacketsLevelTable 1}

Tcpv4PacketsLevelEntry ::=
	SEQUENCE {
		tcpv4PacketsLevelName	DisplayString,
		tcpv4PacketsLevelVal	Counter64,
		tcpv4PacketsLevelMom	CounterBasedGauge64,
		tcpv4PacketsLevelMax	CounterBasedGauge64
	}

tcpv4PacketsLevelName OBJECT-TYPE
	SYNTAX      DisplayString
	MAX-ACCESS  not-accessible
	STATUS      current
	DESCRIPTION
	"Table entry display string for tcpv4Packets"
	::={tcpv4PacketsLevelEntry 1}

tcpv4PacketsLevelVal OBJECT-TYPE
	SYNTAX	 Counter64
	MAX-ACCESS  read-only
	STATUS      current
	DESCRIPTION
	"Table entry attribute for tcpv4Packets"
	::={tcpv4PacketsLevelEntry 2}

tcpv4PacketsLevelMom OBJECT-TYPE
	SYNTAX	 CounterBasedGauge64
	MAX-ACCESS  read-only
	STATUS      current
	DESCRIPTION
	"Table entry attribute for tcpv4Packets"
	::={tcpv4PacketsLevelEntry 3}

tcpv4PacketsLevelMax OBJECT-TYPE
	SYNTAX	 CounterBasedGauge64
	MAX-ACCESS  read-only
	STATUS      current
	DESCRIPTION
	"Table entry attribute for tcpv4Packets"
	::={tcpv4PacketsLevelEntry 4}


tcpv4Bytes	OBJECT IDENTIFIER ::={tcpv4 2}

tcpv4BytesVal	OBJECT-TYPE
	SYNTAX	 Counter64
	MAX-ACCESS read-only
	STATUS current
	DESCRIPTION "RX bytes"

	::={tcpv4Bytes 1}

tcpv4BytesMom	OBJECT-TYPE
	SYNTAX	 CounterBasedGauge64
	MAX-ACCESS read-only
	STATUS current
	DESCRIPTION "RX bytes"

	::={tcpv4Bytes 2}

tcpv4BytesMax	OBJECT-TYPE
	SYNTAX	 CounterBasedGauge64
	MAX-ACCESS read-only
	STATUS current
	DESCRIPTION "RX bytes"

	::={tcpv4Bytes 3}

tcpv4BytesLevelTable OBJECT-TYPE
	SYNTAX      SEQUENCE OF Tcpv4BytesLevelEntry
	MAX-ACCESS  not-accessible
	STATUS      current
	DESCRIPTION
	"Table for tcpv4Bytes"
	::={tcpv4Bytes 4}

tcpv4BytesLevelEntry OBJECT-TYPE
	SYNTAX      Tcpv4BytesLevelEntry
	MAX-ACCESS  not-accessible
	STATUS      current
	DESCRIPTION
	"Table entry for tcpv4Bytes"
	INDEX { tcpv4BytesLevelName }
	::={tcpv4BytesLevelTable 1}

Tcpv4BytesLevelEntry ::=
	SEQUENCE {
		tcpv4BytesLevelName	DisplayString,
		tcpv4BytesLevelVal	Counter64,
		tcpv4BytesLevelMom	CounterBasedGauge64,
		tcpv4BytesLevelMax	CounterBasedGauge64
	}

tcpv4BytesLevelName OBJECT-TYPE
	SYNTAX      DisplayString
	MAX-ACCESS  not-accessible
	STATUS      current
	DESCRIPTION
	"Table entry display string for tcpv4Bytes"
	::={tcpv4BytesLevelEntry 1}

tcpv4BytesLevelVal OBJECT-TYPE
	SYNTAX	 Counter64
	MAX-ACCESS  read-only
	STATUS      current
	DESCRIPTION
	"Table entry attribute for tcpv4Bytes"
	::={tcpv4BytesLevelEntry 2}

tcpv4BytesLevelMom OBJECT-TYPE
	SYNTAX	 CounterBasedGauge64
	MAX-ACCESS  read-only
	STATUS      current
	DESCRIPTION
	"Table entry attribute for tcpv4Bytes"
	::={tcpv4BytesLevelEntry 3}

tcpv4BytesLevelMax OBJECT-TYPE
	SYNTAX	 CounterBasedGauge64
	MAX-ACCESS  read-only
	STATUS      current
	DESCRIPTION
	"Table entry attribute for tcpv4Bytes"
	::={tcpv4BytesLevelEntry 4}


tcpv4CreateAttempts	OBJECT IDENTIFIER ::={tcpv4 4}

tcpv4CreateAttemptsVal	OBJECT-TYPE
	SYNTAX	 Counter64
	MAX-ACCESS read-only
	STATUS current
	DESCRIPTION "Connection create attempts"

	::={tcpv4CreateAttempts 1}

tcpv4CreateAttemptsMom	OBJECT-TYPE
	SYNTAX	 CounterBasedGauge64
	MAX-ACCESS read-only
	STATUS current
	DESCRIPTION "Connection create attempts"

	::={tcpv4CreateAttempts 2}

tcpv4CreateAttemptsMax	OBJECT-TYPE
	SYNTAX	 CounterBasedGauge64
	MAX-ACCESS read-only
	STATUS current
	DESCRIPTION "Connection create attempts"

	::={tcpv4CreateAttempts 3}

tcpv4CreateAttemptsLevelTable OBJECT-TYPE
	SYNTAX      SEQUENCE OF Tcpv4CreateAttemptsLevelEntry
	MAX-ACCESS  not-accessible
	STATUS      current
	DESCRIPTION
	"Table for tcpv4CreateAttempts"
	::={tcpv4CreateAttempts 4}

tcpv4CreateAttemptsLevelEntry OBJECT-TYPE
	SYNTAX      Tcpv4CreateAttemptsLevelEntry
	MAX-ACCESS  not-accessible
	STATUS      current
	DESCRIPTION
	"Table entry for tcpv4CreateAttempts"
	INDEX { tcpv4CreateAttemptsLevelName }
	::={tcpv4CreateAttemptsLevelTable 1}

Tcpv4CreateAttemptsLevelEntry ::=
	SEQUENCE {
		tcpv4CreateAttemptsLevelName	DisplayString,
		tcpv4CreateAttemptsLevelVal	Counter64,
		tcpv4CreateAttemptsLevelMom	CounterBasedGauge64,
		tcpv4CreateAttemptsLevelMax	CounterBasedGauge64
	}

tcpv4CreateAttemptsLevelName OBJECT-TYPE
	SYNTAX      DisplayString
	MAX-ACCESS  not-accessible
	STATUS      current
	DESCRIPTION
	"Table entry display string for tcpv4CreateAttempts"
	::={tcpv4CreateAttemptsLevelEntry 1}

tcpv4CreateAttemptsLevelVal OBJECT-TYPE
	SYNTAX	 Counter64
	MAX-ACCESS  read-only
	STATUS      current
	DESCRIPTION
	"Table entry attribute for tcpv4CreateAttempts"
	::={tcpv4CreateAttemptsLevelEntry 2}

tcpv4CreateAttemptsLevelMom OBJECT-TYPE
	SYNTAX	 CounterBasedGauge64
	MAX-ACCESS  read-only
	STATUS      current
	DESCRIPTION
	"Table entry attribute for tcpv4CreateAttempts"
	::={tcpv4CreateAttemptsLevelEntry 3}

tcpv4CreateAttemptsLevelMax OBJECT-TYPE
	SYNTAX	 CounterBasedGauge64
	MAX-ACCESS  read-only
	STATUS      current
	DESCRIPTION
	"Table entry attribute for tcpv4CreateAttempts"
	::={tcpv4CreateAttemptsLevelEntry 4}


tcpv4Created	OBJECT IDENTIFIER ::={tcpv4 5}

tcpv4CreatedVal	OBJECT-TYPE
	SYNTAX	 Counter64
	MAX-ACCESS read-only
	STATUS current
	DESCRIPTION "Connections created"

	::={tcpv4Created 1}

tcpv4CreatedMom	OBJECT-TYPE
	SYNTAX	 CounterBasedGauge64
	MAX-ACCESS read-only
	STATUS current
	DESCRIPTION "Connections created"

	::={tcpv4Created 2}

tcpv4CreatedMax	OBJECT-TYPE
	SYNTAX	 CounterBasedGauge64
	MAX-ACCESS read-only
	STATUS current
	DESCRIPTION "Connections created"

	::={tcpv4Created 3}

tcpv4CreatedLevelTable OBJECT-TYPE
	SYNTAX      SEQUENCE OF Tcpv4CreatedLevelEntry
	MAX-ACCESS  not-accessible
	STATUS      current
	DESCRIPTION
	"Table for tcpv4Created"
	::={tcpv4Created 4}

tcpv4CreatedLevelEntry OBJECT-TYPE
	SYNTAX      Tcpv4CreatedLevelEntry
	MAX-ACCESS  not-accessible
	STATUS      current
	DESCRIPTION
	"Table entry for tcpv4Created"
	INDEX { tcpv4CreatedLevelName }
	::={tcpv4CreatedLevelTable 1}

Tcpv4CreatedLevelEntry ::=
	SEQUENCE {
		tcpv4CreatedLevelName	DisplayString,
		tcpv4CreatedLevelVal	Counter64,
		tcpv4CreatedLevelMom	CounterBasedGauge64,
		tcpv4CreatedLevelMax	CounterBasedGauge64
	}

tcpv4CreatedLevelName OBJECT-TYPE
	SYNTAX      DisplayString
	MAX-ACCESS  not-accessible
	STATUS      current
	DESCRIPTION
	"Table entry display string for tcpv4Created"
	::={tcpv4CreatedLevelEntry 1}

tcpv4CreatedLevelVal OBJECT-TYPE
	SYNTAX	 Counter64
	MAX-ACCESS  read-only
	STATUS      current
	DESCRIPTION
	"Table entry attribute for tcpv4Created"
	::={tcpv4CreatedLevelEntry 2}

tcpv4CreatedLevelMom OBJECT-TYPE
	SYNTAX	 CounterBasedGauge64
	MAX-ACCESS  read-only
	STATUS      current
	DESCRIPTION
	"Table entry attribute for tcpv4Created"
	::={tcpv4CreatedLevelEntry 3}

tcpv4CreatedLevelMax OBJECT-TYPE
	SYNTAX	 CounterBasedGauge64
	MAX-ACCESS  read-only
	STATUS      current
	DESCRIPTION
	"Table entry attribute for tcpv4Created"
	::={tcpv4CreatedLevelEntry 4}


tcpv4RefusedRuleset	OBJECT IDENTIFIER ::={tcpv4 6}

tcpv4RefusedRulesetVal	OBJECT-TYPE
	SYNTAX	 Counter64
	MAX-ACCESS read-only
	STATUS current
	DESCRIPTION "Refused (ruleset)"

	::={tcpv4RefusedRuleset 1}

tcpv4RefusedRulesetMom	OBJECT-TYPE
	SYNTAX	 CounterBasedGauge64
	MAX-ACCESS read-only
	STATUS current
	DESCRIPTION "Refused (ruleset)"

	::={tcpv4RefusedRuleset 2}

tcpv4RefusedRulesetMax	OBJECT-TYPE
	SYNTAX	 CounterBasedGauge64
	MAX-ACCESS read-only
	STATUS current
	DESCRIPTION "Refused (ruleset)"

	::={tcpv4RefusedRuleset 3}

tcpv4RefusedRulesetLevelTable OBJECT-TYPE
	SYNTAX      SEQUENCE OF Tcpv4RefusedRulesetLevelEntry
	MAX-ACCESS  not-accessible
	STATUS      current
	DESCRIPTION
	"Table for tcpv4RefusedRuleset"
	::={tcpv4RefusedRuleset 4}

tcpv4RefusedRulesetLevelEntry OBJECT-TYPE
	SYNTAX      Tcpv4RefusedRulesetLevelEntry
	MAX-ACCESS  not-accessible
	STATUS      current
	DESCRIPTION
	"Table entry for tcpv4RefusedRuleset"
	INDEX { tcpv4RefusedRulesetLevelName }
	::={tcpv4RefusedRulesetLevelTable 1}

Tcpv4RefusedRulesetLevelEntry ::=
	SEQUENCE {
		tcpv4RefusedRulesetLevelName	DisplayString,
		tcpv4RefusedRulesetLevelVal	Counter64,
		tcpv4RefusedRulesetLevelMom	CounterBasedGauge64,
		tcpv4RefusedRulesetLevelMax	CounterBasedGauge64
	}

tcpv4RefusedRulesetLevelName OBJECT-TYPE
	SYNTAX      DisplayString
	MAX-ACCESS  not-accessible
	STATUS      current
	DESCRIPTION
	"Table entry display string for tcpv4RefusedRuleset"
	::={tcpv4RefusedRulesetLevelEntry 1}

tcpv4RefusedRulesetLevelVal OBJECT-TYPE
	SYNTAX	 Counter64
	MAX-ACCESS  read-only
	STATUS      current
	DESCRIPTION
	"Table entry attribute for tcpv4RefusedRuleset"
	::={tcpv4RefusedRulesetLevelEntry 2}

tcpv4RefusedRulesetLevelMom OBJECT-TYPE
	SYNTAX	 CounterBasedGauge64
	MAX-ACCESS  read-only
	STATUS      current
	DESCRIPTION
	"Table entry attribute for tcpv4RefusedRuleset"
	::={tcpv4RefusedRulesetLevelEntry 3}

tcpv4RefusedRulesetLevelMax OBJECT-TYPE
	SYNTAX	 CounterBasedGauge64
	MAX-ACCESS  read-only
	STATUS      current
	DESCRIPTION
	"Table entry attribute for tcpv4RefusedRuleset"
	::={tcpv4RefusedRulesetLevelEntry 4}


tcpv4RefusedShort	OBJECT IDENTIFIER ::={tcpv4 7}

tcpv4RefusedShortVal	OBJECT-TYPE
	SYNTAX	 Counter64
	MAX-ACCESS read-only
	STATUS current
	DESCRIPTION "Refused (short)"

	::={tcpv4RefusedShort 1}

tcpv4RefusedShortMom	OBJECT-TYPE
	SYNTAX	 CounterBasedGauge64
	MAX-ACCESS read-only
	STATUS current
	DESCRIPTION "Refused (short)"

	::={tcpv4RefusedShort 2}

tcpv4RefusedShortMax	OBJECT-TYPE
	SYNTAX	 CounterBasedGauge64
	MAX-ACCESS read-only
	STATUS current
	DESCRIPTION "Refused (short)"

	::={tcpv4RefusedShort 3}

tcpv4RefusedShortLevelTable OBJECT-TYPE
	SYNTAX      SEQUENCE OF Tcpv4RefusedShortLevelEntry
	MAX-ACCESS  not-accessible
	STATUS      current
	DESCRIPTION
	"Table for tcpv4RefusedShort"
	::={tcpv4RefusedShort 4}

tcpv4RefusedShortLevelEntry OBJECT-TYPE
	SYNTAX      Tcpv4RefusedShortLevelEntry
	MAX-ACCESS  not-accessible
	STATUS      current
	DESCRIPTION
	"Table entry for tcpv4RefusedShort"
	INDEX { tcpv4RefusedShortLevelName }
	::={tcpv4RefusedShortLevelTable 1}

Tcpv4RefusedShortLevelEntry ::=
	SEQUENCE {
		tcpv4RefusedShortLevelName	DisplayString,
		tcpv4RefusedShortLevelVal	Counter64,
		tcpv4RefusedShortLevelMom	CounterBasedGauge64,
		tcpv4RefusedShortLevelMax	CounterBasedGauge64
	}

tcpv4RefusedShortLevelName OBJECT-TYPE
	SYNTAX      DisplayString
	MAX-ACCESS  not-accessible
	STATUS      current
	DESCRIPTION
	"Table entry display string for tcpv4RefusedShort"
	::={tcpv4RefusedShortLevelEntry 1}

tcpv4RefusedShortLevelVal OBJECT-TYPE
	SYNTAX	 Counter64
	MAX-ACCESS  read-only
	STATUS      current
	DESCRIPTION
	"Table entry attribute for tcpv4RefusedShort"
	::={tcpv4RefusedShortLevelEntry 2}

tcpv4RefusedShortLevelMom OBJECT-TYPE
	SYNTAX	 CounterBasedGauge64
	MAX-ACCESS  read-only
	STATUS      current
	DESCRIPTION
	"Table entry attribute for tcpv4RefusedShort"
	::={tcpv4RefusedShortLevelEntry 3}

tcpv4RefusedShortLevelMax OBJECT-TYPE
	SYNTAX	 CounterBasedGauge64
	MAX-ACCESS  read-only
	STATUS      current
	DESCRIPTION
	"Table entry attribute for tcpv4RefusedShort"
	::={tcpv4RefusedShortLevelEntry 4}


tcpv4RefusedBroadcast	OBJECT IDENTIFIER ::={tcpv4 8}

tcpv4RefusedBroadcastVal	OBJECT-TYPE
	SYNTAX	 Counter64
	MAX-ACCESS read-only
	STATUS current
	DESCRIPTION "Refused (broadcast)"

	::={tcpv4RefusedBroadcast 1}

tcpv4RefusedBroadcastMom	OBJECT-TYPE
	SYNTAX	 CounterBasedGauge64
	MAX-ACCESS read-only
	STATUS current
	DESCRIPTION "Refused (broadcast)"

	::={tcpv4RefusedBroadcast 2}

tcpv4RefusedBroadcastMax	OBJECT-TYPE
	SYNTAX	 CounterBasedGauge64
	MAX-ACCESS read-only
	STATUS current
	DESCRIPTION "Refused (broadcast)"

	::={tcpv4RefusedBroadcast 3}

tcpv4RefusedBroadcastLevelTable OBJECT-TYPE
	SYNTAX      SEQUENCE OF Tcpv4RefusedBroadcastLevelEntry
	MAX-ACCESS  not-accessible
	STATUS      current
	DESCRIPTION
	"Table for tcpv4RefusedBroadcast"
	::={tcpv4RefusedBroadcast 4}

tcpv4RefusedBroadcastLevelEntry OBJECT-TYPE
	SYNTAX      Tcpv4RefusedBroadcastLevelEntry
	MAX-ACCESS  not-accessible
	STATUS      current
	DESCRIPTION
	"Table entry for tcpv4RefusedBroadcast"
	INDEX { tcpv4RefusedBroadcastLevelName }
	::={tcpv4RefusedBroadcastLevelTable 1}

Tcpv4RefusedBroadcastLevelEntry ::=
	SEQUENCE {
		tcpv4RefusedBroadcastLevelName	DisplayString,
		tcpv4RefusedBroadcastLevelVal	Counter64,
		tcpv4RefusedBroadcastLevelMom	CounterBasedGauge64,
		tcpv4RefusedBroadcastLevelMax	CounterBasedGauge64
	}

tcpv4RefusedBroadcastLevelName OBJECT-TYPE
	SYNTAX      DisplayString
	MAX-ACCESS  not-accessible
	STATUS      current
	DESCRIPTION
	"Table entry display string for tcpv4RefusedBroadcast"
	::={tcpv4RefusedBroadcastLevelEntry 1}

tcpv4RefusedBroadcastLevelVal OBJECT-TYPE
	SYNTAX	 Counter64
	MAX-ACCESS  read-only
	STATUS      current
	DESCRIPTION
	"Table entry attribute for tcpv4RefusedBroadcast"
	::={tcpv4RefusedBroadcastLevelEntry 2}

tcpv4RefusedBroadcastLevelMom OBJECT-TYPE
	SYNTAX	 CounterBasedGauge64
	MAX-ACCESS  read-only
	STATUS      current
	DESCRIPTION
	"Table entry attribute for tcpv4RefusedBroadcast"
	::={tcpv4RefusedBroadcastLevelEntry 3}

tcpv4RefusedBroadcastLevelMax OBJECT-TYPE
	SYNTAX	 CounterBasedGauge64
	MAX-ACCESS  read-only
	STATUS      current
	DESCRIPTION
	"Table entry attribute for tcpv4RefusedBroadcast"
	::={tcpv4RefusedBroadcastLevelEntry 4}


tcpv4RefusedOffset	OBJECT IDENTIFIER ::={tcpv4 9}

tcpv4RefusedOffsetVal	OBJECT-TYPE
	SYNTAX	 Counter64
	MAX-ACCESS read-only
	STATUS current
	DESCRIPTION "Refused (offset)"

	::={tcpv4RefusedOffset 1}

tcpv4RefusedOffsetMom	OBJECT-TYPE
	SYNTAX	 CounterBasedGauge64
	MAX-ACCESS read-only
	STATUS current
	DESCRIPTION "Refused (offset)"

	::={tcpv4RefusedOffset 2}

tcpv4RefusedOffsetMax	OBJECT-TYPE
	SYNTAX	 CounterBasedGauge64
	MAX-ACCESS read-only
	STATUS current
	DESCRIPTION "Refused (offset)"

	::={tcpv4RefusedOffset 3}

tcpv4RefusedOffsetLevelTable OBJECT-TYPE
	SYNTAX      SEQUENCE OF Tcpv4RefusedOffsetLevelEntry
	MAX-ACCESS  not-accessible
	STATUS      current
	DESCRIPTION
	"Table for tcpv4RefusedOffset"
	::={tcpv4RefusedOffset 4}

tcpv4RefusedOffsetLevelEntry OBJECT-TYPE
	SYNTAX      Tcpv4RefusedOffsetLevelEntry
	MAX-ACCESS  not-accessible
	STATUS      current
	DESCRIPTION
	"Table entry for tcpv4RefusedOffset"
	INDEX { tcpv4RefusedOffsetLevelName }
	::={tcpv4RefusedOffsetLevelTable 1}

Tcpv4RefusedOffsetLevelEntry ::=
	SEQUENCE {
		tcpv4RefusedOffsetLevelName	DisplayString,
		tcpv4RefusedOffsetLevelVal	Counter64,
		tcpv4RefusedOffsetLevelMom	CounterBasedGauge64,
		tcpv4RefusedOffsetLevelMax	CounterBasedGauge64
	}

tcpv4RefusedOffsetLevelName OBJECT-TYPE
	SYNTAX      DisplayString
	MAX-ACCESS  not-accessible
	STATUS      current
	DESCRIPTION
	"Table entry display string for tcpv4RefusedOffset"
	::={tcpv4RefusedOffsetLevelEntry 1}

tcpv4RefusedOffsetLevelVal OBJECT-TYPE
	SYNTAX	 Counter64
	MAX-ACCESS  read-only
	STATUS      current
	DESCRIPTION
	"Table entry attribute for tcpv4RefusedOffset"
	::={tcpv4RefusedOffsetLevelEntry 2}

tcpv4RefusedOffsetLevelMom OBJECT-TYPE
	SYNTAX	 CounterBasedGauge64
	MAX-ACCESS  read-only
	STATUS      current
	DESCRIPTION
	"Table entry attribute for tcpv4RefusedOffset"
	::={tcpv4RefusedOffsetLevelEntry 3}

tcpv4RefusedOffsetLevelMax OBJECT-TYPE
	SYNTAX	 CounterBasedGauge64
	MAX-ACCESS  read-only
	STATUS      current
	DESCRIPTION
	"Table entry attribute for tcpv4RefusedOffset"
	::={tcpv4RefusedOffsetLevelEntry 4}


tcpv4Rejected	OBJECT IDENTIFIER ::={tcpv4 10}

tcpv4RejectedVal	OBJECT-TYPE
	SYNTAX	 Counter64
	MAX-ACCESS read-only
	STATUS current
	DESCRIPTION "Rejected packets"

	::={tcpv4Rejected 1}

tcpv4RejectedMom	OBJECT-TYPE
	SYNTAX	 CounterBasedGauge64
	MAX-ACCESS read-only
	STATUS current
	DESCRIPTION "Rejected packets"

	::={tcpv4Rejected 2}

tcpv4RejectedMax	OBJECT-TYPE
	SYNTAX	 CounterBasedGauge64
	MAX-ACCESS read-only
	STATUS current
	DESCRIPTION "Rejected packets"

	::={tcpv4Rejected 3}

tcpv4RejectedLevelTable OBJECT-TYPE
	SYNTAX      SEQUENCE OF Tcpv4RejectedLevelEntry
	MAX-ACCESS  not-accessible
	STATUS      current
	DESCRIPTION
	"Table for tcpv4Rejected"
	::={tcpv4Rejected 4}

tcpv4RejectedLevelEntry OBJECT-TYPE
	SYNTAX      Tcpv4RejectedLevelEntry
	MAX-ACCESS  not-accessible
	STATUS      current
	DESCRIPTION
	"Table entry for tcpv4Rejected"
	INDEX { tcpv4RejectedLevelName }
	::={tcpv4RejectedLevelTable 1}

Tcpv4RejectedLevelEntry ::=
	SEQUENCE {
		tcpv4RejectedLevelName	DisplayString,
		tcpv4RejectedLevelVal	Counter64,
		tcpv4RejectedLevelMom	CounterBasedGauge64,
		tcpv4RejectedLevelMax	CounterBasedGauge64
	}

tcpv4RejectedLevelName OBJECT-TYPE
	SYNTAX      DisplayString
	MAX-ACCESS  not-accessible
	STATUS      current
	DESCRIPTION
	"Table entry display string for tcpv4Rejected"
	::={tcpv4RejectedLevelEntry 1}

tcpv4RejectedLevelVal OBJECT-TYPE
	SYNTAX	 Counter64
	MAX-ACCESS  read-only
	STATUS      current
	DESCRIPTION
	"Table entry attribute for tcpv4Rejected"
	::={tcpv4RejectedLevelEntry 2}

tcpv4RejectedLevelMom OBJECT-TYPE
	SYNTAX	 CounterBasedGauge64
	MAX-ACCESS  read-only
	STATUS      current
	DESCRIPTION
	"Table entry attribute for tcpv4Rejected"
	::={tcpv4RejectedLevelEntry 3}

tcpv4RejectedLevelMax OBJECT-TYPE
	SYNTAX	 CounterBasedGauge64
	MAX-ACCESS  read-only
	STATUS      current
	DESCRIPTION
	"Table entry attribute for tcpv4Rejected"
	::={tcpv4RejectedLevelEntry 4}


tcpv4Lostsync	OBJECT IDENTIFIER ::={tcpv4 12}

tcpv4LostsyncVal	OBJECT-TYPE
	SYNTAX	 CounterBasedGauge64
	MAX-ACCESS read-only
	STATUS current
	DESCRIPTION "Out-of-sync connections"

	::={tcpv4Lostsync 1}

tcpv4LostsyncMax	OBJECT-TYPE
	SYNTAX	 CounterBasedGauge64
	MAX-ACCESS read-only
	STATUS current
	DESCRIPTION "Out-of-sync connections"

	::={tcpv4Lostsync 3}

tcpv4LostsyncLevelTable OBJECT-TYPE
	SYNTAX      SEQUENCE OF Tcpv4LostsyncLevelEntry
	MAX-ACCESS  not-accessible
	STATUS      current
	DESCRIPTION
	"Table for tcpv4Lostsync"
	::={tcpv4Lostsync 4}

tcpv4LostsyncLevelEntry OBJECT-TYPE
	SYNTAX      Tcpv4LostsyncLevelEntry
	MAX-ACCESS  not-accessible
	STATUS      current
	DESCRIPTION
	"Table entry for tcpv4Lostsync"
	INDEX { tcpv4LostsyncLevelName }
	::={tcpv4LostsyncLevelTable 1}

Tcpv4LostsyncLevelEntry ::=
	SEQUENCE {
		tcpv4LostsyncLevelName	DisplayString,
		tcpv4LostsyncLevelVal	CounterBasedGauge64,
		tcpv4LostsyncLevelMax	CounterBasedGauge64
	}

tcpv4LostsyncLevelName OBJECT-TYPE
	SYNTAX      DisplayString
	MAX-ACCESS  not-accessible
	STATUS      current
	DESCRIPTION
	"Table entry display string for tcpv4Lostsync"
	::={tcpv4LostsyncLevelEntry 1}

tcpv4LostsyncLevelVal OBJECT-TYPE
	SYNTAX	 CounterBasedGauge64
	MAX-ACCESS  read-only
	STATUS      current
	DESCRIPTION
	"Table entry attribute for tcpv4Lostsync"
	::={tcpv4LostsyncLevelEntry 2}

tcpv4LostsyncLevelMax OBJECT-TYPE
	SYNTAX	 CounterBasedGauge64
	MAX-ACCESS  read-only
	STATUS      current
	DESCRIPTION
	"Table entry attribute for tcpv4Lostsync"
	::={tcpv4LostsyncLevelEntry 4}


tcpv4UntrackedPackets	OBJECT IDENTIFIER ::={tcpv4 13}

tcpv4UntrackedPacketsVal	OBJECT-TYPE
	SYNTAX	 Counter64
	MAX-ACCESS read-only
	STATUS current
	DESCRIPTION "Untracked packets"

	::={tcpv4UntrackedPackets 1}

tcpv4UntrackedPacketsMom	OBJECT-TYPE
	SYNTAX	 CounterBasedGauge64
	MAX-ACCESS read-only
	STATUS current
	DESCRIPTION "Untracked packets"

	::={tcpv4UntrackedPackets 2}

tcpv4UntrackedPacketsMax	OBJECT-TYPE
	SYNTAX	 CounterBasedGauge64
	MAX-ACCESS read-only
	STATUS current
	DESCRIPTION "Untracked packets"

	::={tcpv4UntrackedPackets 3}

tcpv4UntrackedPacketsLevelTable OBJECT-TYPE
	SYNTAX      SEQUENCE OF Tcpv4UntrackedPacketsLevelEntry
	MAX-ACCESS  not-accessible
	STATUS      current
	DESCRIPTION
	"Table for tcpv4UntrackedPackets"
	::={tcpv4UntrackedPackets 4}

tcpv4UntrackedPacketsLevelEntry OBJECT-TYPE
	SYNTAX      Tcpv4UntrackedPacketsLevelEntry
	MAX-ACCESS  not-accessible
	STATUS      current
	DESCRIPTION
	"Table entry for tcpv4UntrackedPackets"
	INDEX { tcpv4UntrackedPacketsLevelName }
	::={tcpv4UntrackedPacketsLevelTable 1}

Tcpv4UntrackedPacketsLevelEntry ::=
	SEQUENCE {
		tcpv4UntrackedPacketsLevelName	DisplayString,
		tcpv4UntrackedPacketsLevelVal	Counter64,
		tcpv4UntrackedPacketsLevelMom	CounterBasedGauge64,
		tcpv4UntrackedPacketsLevelMax	CounterBasedGauge64
	}

tcpv4UntrackedPacketsLevelName OBJECT-TYPE
	SYNTAX      DisplayString
	MAX-ACCESS  not-accessible
	STATUS      current
	DESCRIPTION
	"Table entry display string for tcpv4UntrackedPackets"
	::={tcpv4UntrackedPacketsLevelEntry 1}

tcpv4UntrackedPacketsLevelVal OBJECT-TYPE
	SYNTAX	 Counter64
	MAX-ACCESS  read-only
	STATUS      current
	DESCRIPTION
	"Table entry attribute for tcpv4UntrackedPackets"
	::={tcpv4UntrackedPacketsLevelEntry 2}

tcpv4UntrackedPacketsLevelMom OBJECT-TYPE
	SYNTAX	 CounterBasedGauge64
	MAX-ACCESS  read-only
	STATUS      current
	DESCRIPTION
	"Table entry attribute for tcpv4UntrackedPackets"
	::={tcpv4UntrackedPacketsLevelEntry 3}

tcpv4UntrackedPacketsLevelMax OBJECT-TYPE
	SYNTAX	 CounterBasedGauge64
	MAX-ACCESS  read-only
	STATUS      current
	DESCRIPTION
	"Table entry attribute for tcpv4UntrackedPackets"
	::={tcpv4UntrackedPacketsLevelEntry 4}


tcpv4GoodputPackets	OBJECT IDENTIFIER ::={tcpv4 14}

tcpv4GoodputPacketsVal	OBJECT-TYPE
	SYNTAX	 Counter64
	MAX-ACCESS read-only
	STATUS current
	DESCRIPTION "Goodput packets"

	::={tcpv4GoodputPackets 1}

tcpv4GoodputPacketsMom	OBJECT-TYPE
	SYNTAX	 CounterBasedGauge64
	MAX-ACCESS read-only
	STATUS current
	DESCRIPTION "Goodput packets"

	::={tcpv4GoodputPackets 2}

tcpv4GoodputPacketsMax	OBJECT-TYPE
	SYNTAX	 CounterBasedGauge64
	MAX-ACCESS read-only
	STATUS current
	DESCRIPTION "Goodput packets"

	::={tcpv4GoodputPackets 3}

tcpv4GoodputPacketsLevelTable OBJECT-TYPE
	SYNTAX      SEQUENCE OF Tcpv4GoodputPacketsLevelEntry
	MAX-ACCESS  not-accessible
	STATUS      current
	DESCRIPTION
	"Table for tcpv4GoodputPackets"
	::={tcpv4GoodputPackets 4}

tcpv4GoodputPacketsLevelEntry OBJECT-TYPE
	SYNTAX      Tcpv4GoodputPacketsLevelEntry
	MAX-ACCESS  not-accessible
	STATUS      current
	DESCRIPTION
	"Table entry for tcpv4GoodputPackets"
	INDEX { tcpv4GoodputPacketsLevelName }
	::={tcpv4GoodputPacketsLevelTable 1}

Tcpv4GoodputPacketsLevelEntry ::=
	SEQUENCE {
		tcpv4GoodputPacketsLevelName	DisplayString,
		tcpv4GoodputPacketsLevelVal	Counter64,
		tcpv4GoodputPacketsLevelMom	CounterBasedGauge64,
		tcpv4GoodputPacketsLevelMax	CounterBasedGauge64
	}

tcpv4GoodputPacketsLevelName OBJECT-TYPE
	SYNTAX      DisplayString
	MAX-ACCESS  not-accessible
	STATUS      current
	DESCRIPTION
	"Table entry display string for tcpv4GoodputPackets"
	::={tcpv4GoodputPacketsLevelEntry 1}

tcpv4GoodputPacketsLevelVal OBJECT-TYPE
	SYNTAX	 Counter64
	MAX-ACCESS  read-only
	STATUS      current
	DESCRIPTION
	"Table entry attribute for tcpv4GoodputPackets"
	::={tcpv4GoodputPacketsLevelEntry 2}

tcpv4GoodputPacketsLevelMom OBJECT-TYPE
	SYNTAX	 CounterBasedGauge64
	MAX-ACCESS  read-only
	STATUS      current
	DESCRIPTION
	"Table entry attribute for tcpv4GoodputPackets"
	::={tcpv4GoodputPacketsLevelEntry 3}

tcpv4GoodputPacketsLevelMax OBJECT-TYPE
	SYNTAX	 CounterBasedGauge64
	MAX-ACCESS  read-only
	STATUS      current
	DESCRIPTION
	"Table entry attribute for tcpv4GoodputPackets"
	::={tcpv4GoodputPacketsLevelEntry 4}


tcpv4GoodputBytes	OBJECT IDENTIFIER ::={tcpv4 15}

tcpv4GoodputBytesVal	OBJECT-TYPE
	SYNTAX	 Counter64
	MAX-ACCESS read-only
	STATUS current
	DESCRIPTION "Goodput bytes"

	::={tcpv4GoodputBytes 1}

tcpv4GoodputBytesMom	OBJECT-TYPE
	SYNTAX	 CounterBasedGauge64
	MAX-ACCESS read-only
	STATUS current
	DESCRIPTION "Goodput bytes"

	::={tcpv4GoodputBytes 2}

tcpv4GoodputBytesMax	OBJECT-TYPE
	SYNTAX	 CounterBasedGauge64
	MAX-ACCESS read-only
	STATUS current
	DESCRIPTION "Goodput bytes"

	::={tcpv4GoodputBytes 3}

tcpv4GoodputBytesLevelTable OBJECT-TYPE
	SYNTAX      SEQUENCE OF Tcpv4GoodputBytesLevelEntry
	MAX-ACCESS  not-accessible
	STATUS      current
	DESCRIPTION
	"Table for tcpv4GoodputBytes"
	::={tcpv4GoodputBytes 4}

tcpv4GoodputBytesLevelEntry OBJECT-TYPE
	SYNTAX      Tcpv4GoodputBytesLevelEntry
	MAX-ACCESS  not-accessible
	STATUS      current
	DESCRIPTION
	"Table entry for tcpv4GoodputBytes"
	INDEX { tcpv4GoodputBytesLevelName }
	::={tcpv4GoodputBytesLevelTable 1}

Tcpv4GoodputBytesLevelEntry ::=
	SEQUENCE {
		tcpv4GoodputBytesLevelName	DisplayString,
		tcpv4GoodputBytesLevelVal	Counter64,
		tcpv4GoodputBytesLevelMom	CounterBasedGauge64,
		tcpv4GoodputBytesLevelMax	CounterBasedGauge64
	}

tcpv4GoodputBytesLevelName OBJECT-TYPE
	SYNTAX      DisplayString
	MAX-ACCESS  not-accessible
	STATUS      current
	DESCRIPTION
	"Table entry display string for tcpv4GoodputBytes"
	::={tcpv4GoodputBytesLevelEntry 1}

tcpv4GoodputBytesLevelVal OBJECT-TYPE
	SYNTAX	 Counter64
	MAX-ACCESS  read-only
	STATUS      current
	DESCRIPTION
	"Table entry attribute for tcpv4GoodputBytes"
	::={tcpv4GoodputBytesLevelEntry 2}

tcpv4GoodputBytesLevelMom OBJECT-TYPE
	SYNTAX	 CounterBasedGauge64
	MAX-ACCESS  read-only
	STATUS      current
	DESCRIPTION
	"Table entry attribute for tcpv4GoodputBytes"
	::={tcpv4GoodputBytesLevelEntry 3}

tcpv4GoodputBytesLevelMax OBJECT-TYPE
	SYNTAX	 CounterBasedGauge64
	MAX-ACCESS  read-only
	STATUS      current
	DESCRIPTION
	"Table entry attribute for tcpv4GoodputBytes"
	::={tcpv4GoodputBytesLevelEntry 4}


tcpv4Segments	OBJECT IDENTIFIER ::={tcpv4 16}

tcpv4SegmentsVal	OBJECT-TYPE
	SYNTAX	 CounterBasedGauge64
	MAX-ACCESS read-only
	STATUS current
	DESCRIPTION "Saved segments"

	::={tcpv4Segments 1}

tcpv4SegmentsMax	OBJECT-TYPE
	SYNTAX	 CounterBasedGauge64
	MAX-ACCESS read-only
	STATUS current
	DESCRIPTION "Saved segments"

	::={tcpv4Segments 3}

tcpv4SegmentsLevelTable OBJECT-TYPE
	SYNTAX      SEQUENCE OF Tcpv4SegmentsLevelEntry
	MAX-ACCESS  not-accessible
	STATUS      current
	DESCRIPTION
	"Table for tcpv4Segments"
	::={tcpv4Segments 4}

tcpv4SegmentsLevelEntry OBJECT-TYPE
	SYNTAX      Tcpv4SegmentsLevelEntry
	MAX-ACCESS  not-accessible
	STATUS      current
	DESCRIPTION
	"Table entry for tcpv4Segments"
	INDEX { tcpv4SegmentsLevelName }
	::={tcpv4SegmentsLevelTable 1}

Tcpv4SegmentsLevelEntry ::=
	SEQUENCE {
		tcpv4SegmentsLevelName	DisplayString,
		tcpv4SegmentsLevelVal	CounterBasedGauge64,
		tcpv4SegmentsLevelMax	CounterBasedGauge64
	}

tcpv4SegmentsLevelName OBJECT-TYPE
	SYNTAX      DisplayString
	MAX-ACCESS  not-accessible
	STATUS      current
	DESCRIPTION
	"Table entry display string for tcpv4Segments"
	::={tcpv4SegmentsLevelEntry 1}

tcpv4SegmentsLevelVal OBJECT-TYPE
	SYNTAX	 CounterBasedGauge64
	MAX-ACCESS  read-only
	STATUS      current
	DESCRIPTION
	"Table entry attribute for tcpv4Segments"
	::={tcpv4SegmentsLevelEntry 2}

tcpv4SegmentsLevelMax OBJECT-TYPE
	SYNTAX	 CounterBasedGauge64
	MAX-ACCESS  read-only
	STATUS      current
	DESCRIPTION
	"Table entry attribute for tcpv4Segments"
	::={tcpv4SegmentsLevelEntry 4}


tcpv4SegmentsPayload	OBJECT IDENTIFIER ::={tcpv4 17}

tcpv4SegmentsPayloadVal	OBJECT-TYPE
	SYNTAX	 CounterBasedGauge64
	MAX-ACCESS read-only
	STATUS current
	DESCRIPTION "Saved segments with payload"

	::={tcpv4SegmentsPayload 1}

tcpv4SegmentsPayloadMax	OBJECT-TYPE
	SYNTAX	 CounterBasedGauge64
	MAX-ACCESS read-only
	STATUS current
	DESCRIPTION "Saved segments with payload"

	::={tcpv4SegmentsPayload 3}

tcpv4SegmentsPayloadLevelTable OBJECT-TYPE
	SYNTAX      SEQUENCE OF Tcpv4SegmentsPayloadLevelEntry
	MAX-ACCESS  not-accessible
	STATUS      current
	DESCRIPTION
	"Table for tcpv4SegmentsPayload"
	::={tcpv4SegmentsPayload 4}

tcpv4SegmentsPayloadLevelEntry OBJECT-TYPE
	SYNTAX      Tcpv4SegmentsPayloadLevelEntry
	MAX-ACCESS  not-accessible
	STATUS      current
	DESCRIPTION
	"Table entry for tcpv4SegmentsPayload"
	INDEX { tcpv4SegmentsPayloadLevelName }
	::={tcpv4SegmentsPayloadLevelTable 1}

Tcpv4SegmentsPayloadLevelEntry ::=
	SEQUENCE {
		tcpv4SegmentsPayloadLevelName	DisplayString,
		tcpv4SegmentsPayloadLevelVal	CounterBasedGauge64,
		tcpv4SegmentsPayloadLevelMax	CounterBasedGauge64
	}

tcpv4SegmentsPayloadLevelName OBJECT-TYPE
	SYNTAX      DisplayString
	MAX-ACCESS  not-accessible
	STATUS      current
	DESCRIPTION
	"Table entry display string for tcpv4SegmentsPayload"
	::={tcpv4SegmentsPayloadLevelEntry 1}

tcpv4SegmentsPayloadLevelVal OBJECT-TYPE
	SYNTAX	 CounterBasedGauge64
	MAX-ACCESS  read-only
	STATUS      current
	DESCRIPTION
	"Table entry attribute for tcpv4SegmentsPayload"
	::={tcpv4SegmentsPayloadLevelEntry 2}

tcpv4SegmentsPayloadLevelMax OBJECT-TYPE
	SYNTAX	 CounterBasedGauge64
	MAX-ACCESS  read-only
	STATUS      current
	DESCRIPTION
	"Table entry attribute for tcpv4SegmentsPayload"
	::={tcpv4SegmentsPayloadLevelEntry 4}


tcpv4SegmentsDropped	OBJECT IDENTIFIER ::={tcpv4 18}

tcpv4SegmentsDroppedVal	OBJECT-TYPE
	SYNTAX	 Counter64
	MAX-ACCESS read-only
	STATUS current
	DESCRIPTION "Ignored segments"

	::={tcpv4SegmentsDropped 1}

tcpv4SegmentsDroppedMom	OBJECT-TYPE
	SYNTAX	 CounterBasedGauge64
	MAX-ACCESS read-only
	STATUS current
	DESCRIPTION "Ignored segments"

	::={tcpv4SegmentsDropped 2}

tcpv4SegmentsDroppedMax	OBJECT-TYPE
	SYNTAX	 CounterBasedGauge64
	MAX-ACCESS read-only
	STATUS current
	DESCRIPTION "Ignored segments"

	::={tcpv4SegmentsDropped 3}

tcpv4SegmentsDroppedLevelTable OBJECT-TYPE
	SYNTAX      SEQUENCE OF Tcpv4SegmentsDroppedLevelEntry
	MAX-ACCESS  not-accessible
	STATUS      current
	DESCRIPTION
	"Table for tcpv4SegmentsDropped"
	::={tcpv4SegmentsDropped 4}

tcpv4SegmentsDroppedLevelEntry OBJECT-TYPE
	SYNTAX      Tcpv4SegmentsDroppedLevelEntry
	MAX-ACCESS  not-accessible
	STATUS      current
	DESCRIPTION
	"Table entry for tcpv4SegmentsDropped"
	INDEX { tcpv4SegmentsDroppedLevelName }
	::={tcpv4SegmentsDroppedLevelTable 1}

Tcpv4SegmentsDroppedLevelEntry ::=
	SEQUENCE {
		tcpv4SegmentsDroppedLevelName	DisplayString,
		tcpv4SegmentsDroppedLevelVal	Counter64,
		tcpv4SegmentsDroppedLevelMom	CounterBasedGauge64,
		tcpv4SegmentsDroppedLevelMax	CounterBasedGauge64
	}

tcpv4SegmentsDroppedLevelName OBJECT-TYPE
	SYNTAX      DisplayString
	MAX-ACCESS  not-accessible
	STATUS      current
	DESCRIPTION
	"Table entry display string for tcpv4SegmentsDropped"
	::={tcpv4SegmentsDroppedLevelEntry 1}

tcpv4SegmentsDroppedLevelVal OBJECT-TYPE
	SYNTAX	 Counter64
	MAX-ACCESS  read-only
	STATUS      current
	DESCRIPTION
	"Table entry attribute for tcpv4SegmentsDropped"
	::={tcpv4SegmentsDroppedLevelEntry 2}

tcpv4SegmentsDroppedLevelMom OBJECT-TYPE
	SYNTAX	 CounterBasedGauge64
	MAX-ACCESS  read-only
	STATUS      current
	DESCRIPTION
	"Table entry attribute for tcpv4SegmentsDropped"
	::={tcpv4SegmentsDroppedLevelEntry 3}

tcpv4SegmentsDroppedLevelMax OBJECT-TYPE
	SYNTAX	 CounterBasedGauge64
	MAX-ACCESS  read-only
	STATUS      current
	DESCRIPTION
	"Table entry attribute for tcpv4SegmentsDropped"
	::={tcpv4SegmentsDroppedLevelEntry 4}


tcpv4PacketAllocFail	OBJECT IDENTIFIER ::={tcpv4 19}

tcpv4PacketAllocFailVal	OBJECT-TYPE
	SYNTAX	 Counter64
	MAX-ACCESS read-only
	STATUS current
	DESCRIPTION "Packet allocation failures"

	::={tcpv4PacketAllocFail 1}

tcpv4PacketAllocFailMom	OBJECT-TYPE
	SYNTAX	 CounterBasedGauge64
	MAX-ACCESS read-only
	STATUS current
	DESCRIPTION "Packet allocation failures"

	::={tcpv4PacketAllocFail 2}

tcpv4PacketAllocFailMax	OBJECT-TYPE
	SYNTAX	 CounterBasedGauge64
	MAX-ACCESS read-only
	STATUS current
	DESCRIPTION "Packet allocation failures"

	::={tcpv4PacketAllocFail 3}

tcpv4PacketAllocFailLevelTable OBJECT-TYPE
	SYNTAX      SEQUENCE OF Tcpv4PacketAllocFailLevelEntry
	MAX-ACCESS  not-accessible
	STATUS      current
	DESCRIPTION
	"Table for tcpv4PacketAllocFail"
	::={tcpv4PacketAllocFail 4}

tcpv4PacketAllocFailLevelEntry OBJECT-TYPE
	SYNTAX      Tcpv4PacketAllocFailLevelEntry
	MAX-ACCESS  not-accessible
	STATUS      current
	DESCRIPTION
	"Table entry for tcpv4PacketAllocFail"
	INDEX { tcpv4PacketAllocFailLevelName }
	::={tcpv4PacketAllocFailLevelTable 1}

Tcpv4PacketAllocFailLevelEntry ::=
	SEQUENCE {
		tcpv4PacketAllocFailLevelName	DisplayString,
		tcpv4PacketAllocFailLevelVal	Counter64,
		tcpv4PacketAllocFailLevelMom	CounterBasedGauge64,
		tcpv4PacketAllocFailLevelMax	CounterBasedGauge64
	}

tcpv4PacketAllocFailLevelName OBJECT-TYPE
	SYNTAX      DisplayString
	MAX-ACCESS  not-accessible
	STATUS      current
	DESCRIPTION
	"Table entry display string for tcpv4PacketAllocFail"
	::={tcpv4PacketAllocFailLevelEntry 1}

tcpv4PacketAllocFailLevelVal OBJECT-TYPE
	SYNTAX	 Counter64
	MAX-ACCESS  read-only
	STATUS      current
	DESCRIPTION
	"Table entry attribute for tcpv4PacketAllocFail"
	::={tcpv4PacketAllocFailLevelEntry 2}

tcpv4PacketAllocFailLevelMom OBJECT-TYPE
	SYNTAX	 CounterBasedGauge64
	MAX-ACCESS  read-only
	STATUS      current
	DESCRIPTION
	"Table entry attribute for tcpv4PacketAllocFail"
	::={tcpv4PacketAllocFailLevelEntry 3}

tcpv4PacketAllocFailLevelMax OBJECT-TYPE
	SYNTAX	 CounterBasedGauge64
	MAX-ACCESS  read-only
	STATUS      current
	DESCRIPTION
	"Table entry attribute for tcpv4PacketAllocFail"
	::={tcpv4PacketAllocFailLevelEntry 4}


tcpv4UntrackedGoodput	OBJECT IDENTIFIER ::={tcpv4 23}

tcpv4UntrackedGoodputVal	OBJECT-TYPE
	SYNTAX	 Counter64
	MAX-ACCESS read-only
	STATUS current
	DESCRIPTION "Untracked bytes (goodput)"

	::={tcpv4UntrackedGoodput 1}

tcpv4UntrackedGoodputMom	OBJECT-TYPE
	SYNTAX	 CounterBasedGauge64
	MAX-ACCESS read-only
	STATUS current
	DESCRIPTION "Untracked bytes (goodput)"

	::={tcpv4UntrackedGoodput 2}

tcpv4UntrackedGoodputMax	OBJECT-TYPE
	SYNTAX	 CounterBasedGauge64
	MAX-ACCESS read-only
	STATUS current
	DESCRIPTION "Untracked bytes (goodput)"

	::={tcpv4UntrackedGoodput 3}

tcpv4UntrackedGoodputLevelTable OBJECT-TYPE
	SYNTAX      SEQUENCE OF Tcpv4UntrackedGoodputLevelEntry
	MAX-ACCESS  not-accessible
	STATUS      current
	DESCRIPTION
	"Table for tcpv4UntrackedGoodput"
	::={tcpv4UntrackedGoodput 4}

tcpv4UntrackedGoodputLevelEntry OBJECT-TYPE
	SYNTAX      Tcpv4UntrackedGoodputLevelEntry
	MAX-ACCESS  not-accessible
	STATUS      current
	DESCRIPTION
	"Table entry for tcpv4UntrackedGoodput"
	INDEX { tcpv4UntrackedGoodputLevelName }
	::={tcpv4UntrackedGoodputLevelTable 1}

Tcpv4UntrackedGoodputLevelEntry ::=
	SEQUENCE {
		tcpv4UntrackedGoodputLevelName	DisplayString,
		tcpv4UntrackedGoodputLevelVal	Counter64,
		tcpv4UntrackedGoodputLevelMom	CounterBasedGauge64,
		tcpv4UntrackedGoodputLevelMax	CounterBasedGauge64
	}

tcpv4UntrackedGoodputLevelName OBJECT-TYPE
	SYNTAX      DisplayString
	MAX-ACCESS  not-accessible
	STATUS      current
	DESCRIPTION
	"Table entry display string for tcpv4UntrackedGoodput"
	::={tcpv4UntrackedGoodputLevelEntry 1}

tcpv4UntrackedGoodputLevelVal OBJECT-TYPE
	SYNTAX	 Counter64
	MAX-ACCESS  read-only
	STATUS      current
	DESCRIPTION
	"Table entry attribute for tcpv4UntrackedGoodput"
	::={tcpv4UntrackedGoodputLevelEntry 2}

tcpv4UntrackedGoodputLevelMom OBJECT-TYPE
	SYNTAX	 CounterBasedGauge64
	MAX-ACCESS  read-only
	STATUS      current
	DESCRIPTION
	"Table entry attribute for tcpv4UntrackedGoodput"
	::={tcpv4UntrackedGoodputLevelEntry 3}

tcpv4UntrackedGoodputLevelMax OBJECT-TYPE
	SYNTAX	 CounterBasedGauge64
	MAX-ACCESS  read-only
	STATUS      current
	DESCRIPTION
	"Table entry attribute for tcpv4UntrackedGoodput"
	::={tcpv4UntrackedGoodputLevelEntry 4}


tcpv4UntrackedBytes	OBJECT IDENTIFIER ::={tcpv4 24}

tcpv4UntrackedBytesVal	OBJECT-TYPE
	SYNTAX	 Counter64
	MAX-ACCESS read-only
	STATUS current
	DESCRIPTION "Untracked bytes"

	::={tcpv4UntrackedBytes 1}

tcpv4UntrackedBytesMom	OBJECT-TYPE
	SYNTAX	 CounterBasedGauge64
	MAX-ACCESS read-only
	STATUS current
	DESCRIPTION "Untracked bytes"

	::={tcpv4UntrackedBytes 2}

tcpv4UntrackedBytesMax	OBJECT-TYPE
	SYNTAX	 CounterBasedGauge64
	MAX-ACCESS read-only
	STATUS current
	DESCRIPTION "Untracked bytes"

	::={tcpv4UntrackedBytes 3}

tcpv4UntrackedBytesLevelTable OBJECT-TYPE
	SYNTAX      SEQUENCE OF Tcpv4UntrackedBytesLevelEntry
	MAX-ACCESS  not-accessible
	STATUS      current
	DESCRIPTION
	"Table for tcpv4UntrackedBytes"
	::={tcpv4UntrackedBytes 4}

tcpv4UntrackedBytesLevelEntry OBJECT-TYPE
	SYNTAX      Tcpv4UntrackedBytesLevelEntry
	MAX-ACCESS  not-accessible
	STATUS      current
	DESCRIPTION
	"Table entry for tcpv4UntrackedBytes"
	INDEX { tcpv4UntrackedBytesLevelName }
	::={tcpv4UntrackedBytesLevelTable 1}

Tcpv4UntrackedBytesLevelEntry ::=
	SEQUENCE {
		tcpv4UntrackedBytesLevelName	DisplayString,
		tcpv4UntrackedBytesLevelVal	Counter64,
		tcpv4UntrackedBytesLevelMom	CounterBasedGauge64,
		tcpv4UntrackedBytesLevelMax	CounterBasedGauge64
	}

tcpv4UntrackedBytesLevelName OBJECT-TYPE
	SYNTAX      DisplayString
	MAX-ACCESS  not-accessible
	STATUS      current
	DESCRIPTION
	"Table entry display string for tcpv4UntrackedBytes"
	::={tcpv4UntrackedBytesLevelEntry 1}

tcpv4UntrackedBytesLevelVal OBJECT-TYPE
	SYNTAX	 Counter64
	MAX-ACCESS  read-only
	STATUS      current
	DESCRIPTION
	"Table entry attribute for tcpv4UntrackedBytes"
	::={tcpv4UntrackedBytesLevelEntry 2}

tcpv4UntrackedBytesLevelMom OBJECT-TYPE
	SYNTAX	 CounterBasedGauge64
	MAX-ACCESS  read-only
	STATUS      current
	DESCRIPTION
	"Table entry attribute for tcpv4UntrackedBytes"
	::={tcpv4UntrackedBytesLevelEntry 3}

tcpv4UntrackedBytesLevelMax OBJECT-TYPE
	SYNTAX	 CounterBasedGauge64
	MAX-ACCESS  read-only
	STATUS      current
	DESCRIPTION
	"Table entry attribute for tcpv4UntrackedBytes"
	::={tcpv4UntrackedBytesLevelEntry 4}


tcpv4CorruptOptions	OBJECT IDENTIFIER ::={tcpv4 25}

tcpv4CorruptOptionsVal	OBJECT-TYPE
	SYNTAX	 Counter64
	MAX-ACCESS read-only
	STATUS current
	DESCRIPTION "Packets with corrupt options"

	::={tcpv4CorruptOptions 1}

tcpv4CorruptOptionsMom	OBJECT-TYPE
	SYNTAX	 CounterBasedGauge64
	MAX-ACCESS read-only
	STATUS current
	DESCRIPTION "Packets with corrupt options"

	::={tcpv4CorruptOptions 2}

tcpv4CorruptOptionsMax	OBJECT-TYPE
	SYNTAX	 CounterBasedGauge64
	MAX-ACCESS read-only
	STATUS current
	DESCRIPTION "Packets with corrupt options"

	::={tcpv4CorruptOptions 3}

tcpv4CorruptOptionsLevelTable OBJECT-TYPE
	SYNTAX      SEQUENCE OF Tcpv4CorruptOptionsLevelEntry
	MAX-ACCESS  not-accessible
	STATUS      current
	DESCRIPTION
	"Table for tcpv4CorruptOptions"
	::={tcpv4CorruptOptions 4}

tcpv4CorruptOptionsLevelEntry OBJECT-TYPE
	SYNTAX      Tcpv4CorruptOptionsLevelEntry
	MAX-ACCESS  not-accessible
	STATUS      current
	DESCRIPTION
	"Table entry for tcpv4CorruptOptions"
	INDEX { tcpv4CorruptOptionsLevelName }
	::={tcpv4CorruptOptionsLevelTable 1}

Tcpv4CorruptOptionsLevelEntry ::=
	SEQUENCE {
		tcpv4CorruptOptionsLevelName	DisplayString,
		tcpv4CorruptOptionsLevelVal	Counter64,
		tcpv4CorruptOptionsLevelMom	CounterBasedGauge64,
		tcpv4CorruptOptionsLevelMax	CounterBasedGauge64
	}

tcpv4CorruptOptionsLevelName OBJECT-TYPE
	SYNTAX      DisplayString
	MAX-ACCESS  not-accessible
	STATUS      current
	DESCRIPTION
	"Table entry display string for tcpv4CorruptOptions"
	::={tcpv4CorruptOptionsLevelEntry 1}

tcpv4CorruptOptionsLevelVal OBJECT-TYPE
	SYNTAX	 Counter64
	MAX-ACCESS  read-only
	STATUS      current
	DESCRIPTION
	"Table entry attribute for tcpv4CorruptOptions"
	::={tcpv4CorruptOptionsLevelEntry 2}

tcpv4CorruptOptionsLevelMom OBJECT-TYPE
	SYNTAX	 CounterBasedGauge64
	MAX-ACCESS  read-only
	STATUS      current
	DESCRIPTION
	"Table entry attribute for tcpv4CorruptOptions"
	::={tcpv4CorruptOptionsLevelEntry 3}

tcpv4CorruptOptionsLevelMax OBJECT-TYPE
	SYNTAX	 CounterBasedGauge64
	MAX-ACCESS  read-only
	STATUS      current
	DESCRIPTION
	"Table entry attribute for tcpv4CorruptOptions"
	::={tcpv4CorruptOptionsLevelEntry 4}


tcpv4CorruptConn	OBJECT IDENTIFIER ::={tcpv4 26}

tcpv4CorruptConnVal	OBJECT-TYPE
	SYNTAX	 Counter64
	MAX-ACCESS read-only
	STATUS current
	DESCRIPTION "Packets with corrupt conn"

	::={tcpv4CorruptConn 1}

tcpv4CorruptConnMom	OBJECT-TYPE
	SYNTAX	 CounterBasedGauge64
	MAX-ACCESS read-only
	STATUS current
	DESCRIPTION "Packets with corrupt conn"

	::={tcpv4CorruptConn 2}

tcpv4CorruptConnMax	OBJECT-TYPE
	SYNTAX	 CounterBasedGauge64
	MAX-ACCESS read-only
	STATUS current
	DESCRIPTION "Packets with corrupt conn"

	::={tcpv4CorruptConn 3}

tcpv4CorruptConnLevelTable OBJECT-TYPE
	SYNTAX      SEQUENCE OF Tcpv4CorruptConnLevelEntry
	MAX-ACCESS  not-accessible
	STATUS      current
	DESCRIPTION
	"Table for tcpv4CorruptConn"
	::={tcpv4CorruptConn 4}

tcpv4CorruptConnLevelEntry OBJECT-TYPE
	SYNTAX      Tcpv4CorruptConnLevelEntry
	MAX-ACCESS  not-accessible
	STATUS      current
	DESCRIPTION
	"Table entry for tcpv4CorruptConn"
	INDEX { tcpv4CorruptConnLevelName }
	::={tcpv4CorruptConnLevelTable 1}

Tcpv4CorruptConnLevelEntry ::=
	SEQUENCE {
		tcpv4CorruptConnLevelName	DisplayString,
		tcpv4CorruptConnLevelVal	Counter64,
		tcpv4CorruptConnLevelMom	CounterBasedGauge64,
		tcpv4CorruptConnLevelMax	CounterBasedGauge64
	}

tcpv4CorruptConnLevelName OBJECT-TYPE
	SYNTAX      DisplayString
	MAX-ACCESS  not-accessible
	STATUS      current
	DESCRIPTION
	"Table entry display string for tcpv4CorruptConn"
	::={tcpv4CorruptConnLevelEntry 1}

tcpv4CorruptConnLevelVal OBJECT-TYPE
	SYNTAX	 Counter64
	MAX-ACCESS  read-only
	STATUS      current
	DESCRIPTION
	"Table entry attribute for tcpv4CorruptConn"
	::={tcpv4CorruptConnLevelEntry 2}

tcpv4CorruptConnLevelMom OBJECT-TYPE
	SYNTAX	 CounterBasedGauge64
	MAX-ACCESS  read-only
	STATUS      current
	DESCRIPTION
	"Table entry attribute for tcpv4CorruptConn"
	::={tcpv4CorruptConnLevelEntry 3}

tcpv4CorruptConnLevelMax OBJECT-TYPE
	SYNTAX	 CounterBasedGauge64
	MAX-ACCESS  read-only
	STATUS      current
	DESCRIPTION
	"Table entry attribute for tcpv4CorruptConn"
	::={tcpv4CorruptConnLevelEntry 4}


tcpv4SegmentedConnections	OBJECT IDENTIFIER ::={tcpv4 27}

tcpv4SegmentedConnectionsVal	OBJECT-TYPE
	SYNTAX	 CounterBasedGauge64
	MAX-ACCESS read-only
	STATUS current
	DESCRIPTION "Connections with segments"

	::={tcpv4SegmentedConnections 1}

tcpv4SegmentedConnectionsMax	OBJECT-TYPE
	SYNTAX	 CounterBasedGauge64
	MAX-ACCESS read-only
	STATUS current
	DESCRIPTION "Connections with segments"

	::={tcpv4SegmentedConnections 3}

tcpv4SegmentedConnectionsLevelTable OBJECT-TYPE
	SYNTAX      SEQUENCE OF Tcpv4SegmentedConnectionsLevelEntry
	MAX-ACCESS  not-accessible
	STATUS      current
	DESCRIPTION
	"Table for tcpv4SegmentedConnections"
	::={tcpv4SegmentedConnections 4}

tcpv4SegmentedConnectionsLevelEntry OBJECT-TYPE
	SYNTAX      Tcpv4SegmentedConnectionsLevelEntry
	MAX-ACCESS  not-accessible
	STATUS      current
	DESCRIPTION
	"Table entry for tcpv4SegmentedConnections"
	INDEX { tcpv4SegmentedConnectionsLevelName }
	::={tcpv4SegmentedConnectionsLevelTable 1}

Tcpv4SegmentedConnectionsLevelEntry ::=
	SEQUENCE {
		tcpv4SegmentedConnectionsLevelName	DisplayString,
		tcpv4SegmentedConnectionsLevelVal	CounterBasedGauge64,
		tcpv4SegmentedConnectionsLevelMax	CounterBasedGauge64
	}

tcpv4SegmentedConnectionsLevelName OBJECT-TYPE
	SYNTAX      DisplayString
	MAX-ACCESS  not-accessible
	STATUS      current
	DESCRIPTION
	"Table entry display string for tcpv4SegmentedConnections"
	::={tcpv4SegmentedConnectionsLevelEntry 1}

tcpv4SegmentedConnectionsLevelVal OBJECT-TYPE
	SYNTAX	 CounterBasedGauge64
	MAX-ACCESS  read-only
	STATUS      current
	DESCRIPTION
	"Table entry attribute for tcpv4SegmentedConnections"
	::={tcpv4SegmentedConnectionsLevelEntry 2}

tcpv4SegmentedConnectionsLevelMax OBJECT-TYPE
	SYNTAX	 CounterBasedGauge64
	MAX-ACCESS  read-only
	STATUS      current
	DESCRIPTION
	"Table entry attribute for tcpv4SegmentedConnections"
	::={tcpv4SegmentedConnectionsLevelEntry 4}


tcpv4OutOfWindowPackets	OBJECT IDENTIFIER ::={tcpv4 28}

tcpv4OutOfWindowPacketsVal	OBJECT-TYPE
	SYNTAX	 Counter64
	MAX-ACCESS read-only
	STATUS current
	DESCRIPTION "Out of window packets (ignored)"

	::={tcpv4OutOfWindowPackets 1}

tcpv4OutOfWindowPacketsMom	OBJECT-TYPE
	SYNTAX	 CounterBasedGauge64
	MAX-ACCESS read-only
	STATUS current
	DESCRIPTION "Out of window packets (ignored)"

	::={tcpv4OutOfWindowPackets 2}

tcpv4OutOfWindowPacketsMax	OBJECT-TYPE
	SYNTAX	 CounterBasedGauge64
	MAX-ACCESS read-only
	STATUS current
	DESCRIPTION "Out of window packets (ignored)"

	::={tcpv4OutOfWindowPackets 3}

tcpv4OutOfWindowPacketsLevelTable OBJECT-TYPE
	SYNTAX      SEQUENCE OF Tcpv4OutOfWindowPacketsLevelEntry
	MAX-ACCESS  not-accessible
	STATUS      current
	DESCRIPTION
	"Table for tcpv4OutOfWindowPackets"
	::={tcpv4OutOfWindowPackets 4}

tcpv4OutOfWindowPacketsLevelEntry OBJECT-TYPE
	SYNTAX      Tcpv4OutOfWindowPacketsLevelEntry
	MAX-ACCESS  not-accessible
	STATUS      current
	DESCRIPTION
	"Table entry for tcpv4OutOfWindowPackets"
	INDEX { tcpv4OutOfWindowPacketsLevelName }
	::={tcpv4OutOfWindowPacketsLevelTable 1}

Tcpv4OutOfWindowPacketsLevelEntry ::=
	SEQUENCE {
		tcpv4OutOfWindowPacketsLevelName	DisplayString,
		tcpv4OutOfWindowPacketsLevelVal	Counter64,
		tcpv4OutOfWindowPacketsLevelMom	CounterBasedGauge64,
		tcpv4OutOfWindowPacketsLevelMax	CounterBasedGauge64
	}

tcpv4OutOfWindowPacketsLevelName OBJECT-TYPE
	SYNTAX      DisplayString
	MAX-ACCESS  not-accessible
	STATUS      current
	DESCRIPTION
	"Table entry display string for tcpv4OutOfWindowPackets"
	::={tcpv4OutOfWindowPacketsLevelEntry 1}

tcpv4OutOfWindowPacketsLevelVal OBJECT-TYPE
	SYNTAX	 Counter64
	MAX-ACCESS  read-only
	STATUS      current
	DESCRIPTION
	"Table entry attribute for tcpv4OutOfWindowPackets"
	::={tcpv4OutOfWindowPacketsLevelEntry 2}

tcpv4OutOfWindowPacketsLevelMom OBJECT-TYPE
	SYNTAX	 CounterBasedGauge64
	MAX-ACCESS  read-only
	STATUS      current
	DESCRIPTION
	"Table entry attribute for tcpv4OutOfWindowPackets"
	::={tcpv4OutOfWindowPacketsLevelEntry 3}

tcpv4OutOfWindowPacketsLevelMax OBJECT-TYPE
	SYNTAX	 CounterBasedGauge64
	MAX-ACCESS  read-only
	STATUS      current
	DESCRIPTION
	"Table entry attribute for tcpv4OutOfWindowPackets"
	::={tcpv4OutOfWindowPacketsLevelEntry 4}


tcpv4RefusedFilter	OBJECT IDENTIFIER ::={tcpv4 29}

tcpv4RefusedFilterVal	OBJECT-TYPE
	SYNTAX	 Counter64
	MAX-ACCESS read-only
	STATUS current
	DESCRIPTION "Packets refused by lowlevel filter"

	::={tcpv4RefusedFilter 1}

tcpv4RefusedFilterMom	OBJECT-TYPE
	SYNTAX	 CounterBasedGauge64
	MAX-ACCESS read-only
	STATUS current
	DESCRIPTION "Packets refused by lowlevel filter"

	::={tcpv4RefusedFilter 2}

tcpv4RefusedFilterMax	OBJECT-TYPE
	SYNTAX	 CounterBasedGauge64
	MAX-ACCESS read-only
	STATUS current
	DESCRIPTION "Packets refused by lowlevel filter"

	::={tcpv4RefusedFilter 3}

tcpv4RefusedFilterLevelTable OBJECT-TYPE
	SYNTAX      SEQUENCE OF Tcpv4RefusedFilterLevelEntry
	MAX-ACCESS  not-accessible
	STATUS      current
	DESCRIPTION
	"Table for tcpv4RefusedFilter"
	::={tcpv4RefusedFilter 4}

tcpv4RefusedFilterLevelEntry OBJECT-TYPE
	SYNTAX      Tcpv4RefusedFilterLevelEntry
	MAX-ACCESS  not-accessible
	STATUS      current
	DESCRIPTION
	"Table entry for tcpv4RefusedFilter"
	INDEX { tcpv4RefusedFilterLevelName }
	::={tcpv4RefusedFilterLevelTable 1}

Tcpv4RefusedFilterLevelEntry ::=
	SEQUENCE {
		tcpv4RefusedFilterLevelName	DisplayString,
		tcpv4RefusedFilterLevelVal	Counter64,
		tcpv4RefusedFilterLevelMom	CounterBasedGauge64,
		tcpv4RefusedFilterLevelMax	CounterBasedGauge64
	}

tcpv4RefusedFilterLevelName OBJECT-TYPE
	SYNTAX      DisplayString
	MAX-ACCESS  not-accessible
	STATUS      current
	DESCRIPTION
	"Table entry display string for tcpv4RefusedFilter"
	::={tcpv4RefusedFilterLevelEntry 1}

tcpv4RefusedFilterLevelVal OBJECT-TYPE
	SYNTAX	 Counter64
	MAX-ACCESS  read-only
	STATUS      current
	DESCRIPTION
	"Table entry attribute for tcpv4RefusedFilter"
	::={tcpv4RefusedFilterLevelEntry 2}

tcpv4RefusedFilterLevelMom OBJECT-TYPE
	SYNTAX	 CounterBasedGauge64
	MAX-ACCESS  read-only
	STATUS      current
	DESCRIPTION
	"Table entry attribute for tcpv4RefusedFilter"
	::={tcpv4RefusedFilterLevelEntry 3}

tcpv4RefusedFilterLevelMax OBJECT-TYPE
	SYNTAX	 CounterBasedGauge64
	MAX-ACCESS  read-only
	STATUS      current
	DESCRIPTION
	"Table entry attribute for tcpv4RefusedFilter"
	::={tcpv4RefusedFilterLevelEntry 4}


tcpv4SynExisting	OBJECT IDENTIFIER ::={tcpv4 32}

tcpv4SynExistingVal	OBJECT-TYPE
	SYNTAX	 Counter64
	MAX-ACCESS read-only
	STATUS current
	DESCRIPTION "SYN packets for existing connections"

	::={tcpv4SynExisting 1}

tcpv4SynExistingMom	OBJECT-TYPE
	SYNTAX	 CounterBasedGauge64
	MAX-ACCESS read-only
	STATUS current
	DESCRIPTION "SYN packets for existing connections"

	::={tcpv4SynExisting 2}

tcpv4SynExistingMax	OBJECT-TYPE
	SYNTAX	 CounterBasedGauge64
	MAX-ACCESS read-only
	STATUS current
	DESCRIPTION "SYN packets for existing connections"

	::={tcpv4SynExisting 3}

tcpv4SynExistingLevelTable OBJECT-TYPE
	SYNTAX      SEQUENCE OF Tcpv4SynExistingLevelEntry
	MAX-ACCESS  not-accessible
	STATUS      current
	DESCRIPTION
	"Table for tcpv4SynExisting"
	::={tcpv4SynExisting 4}

tcpv4SynExistingLevelEntry OBJECT-TYPE
	SYNTAX      Tcpv4SynExistingLevelEntry
	MAX-ACCESS  not-accessible
	STATUS      current
	DESCRIPTION
	"Table entry for tcpv4SynExisting"
	INDEX { tcpv4SynExistingLevelName }
	::={tcpv4SynExistingLevelTable 1}

Tcpv4SynExistingLevelEntry ::=
	SEQUENCE {
		tcpv4SynExistingLevelName	DisplayString,
		tcpv4SynExistingLevelVal	Counter64,
		tcpv4SynExistingLevelMom	CounterBasedGauge64,
		tcpv4SynExistingLevelMax	CounterBasedGauge64
	}

tcpv4SynExistingLevelName OBJECT-TYPE
	SYNTAX      DisplayString
	MAX-ACCESS  not-accessible
	STATUS      current
	DESCRIPTION
	"Table entry display string for tcpv4SynExisting"
	::={tcpv4SynExistingLevelEntry 1}

tcpv4SynExistingLevelVal OBJECT-TYPE
	SYNTAX	 Counter64
	MAX-ACCESS  read-only
	STATUS      current
	DESCRIPTION
	"Table entry attribute for tcpv4SynExisting"
	::={tcpv4SynExistingLevelEntry 2}

tcpv4SynExistingLevelMom OBJECT-TYPE
	SYNTAX	 CounterBasedGauge64
	MAX-ACCESS  read-only
	STATUS      current
	DESCRIPTION
	"Table entry attribute for tcpv4SynExisting"
	::={tcpv4SynExistingLevelEntry 3}

tcpv4SynExistingLevelMax OBJECT-TYPE
	SYNTAX	 CounterBasedGauge64
	MAX-ACCESS  read-only
	STATUS      current
	DESCRIPTION
	"Table entry attribute for tcpv4SynExisting"
	::={tcpv4SynExistingLevelEntry 4}


tcpv4SegmentAllocFail	OBJECT IDENTIFIER ::={tcpv4 33}

tcpv4SegmentAllocFailVal	OBJECT-TYPE
	SYNTAX	 Counter64
	MAX-ACCESS read-only
	STATUS current
	DESCRIPTION "Segment allocation failures"

	::={tcpv4SegmentAllocFail 1}

tcpv4SegmentAllocFailMom	OBJECT-TYPE
	SYNTAX	 CounterBasedGauge64
	MAX-ACCESS read-only
	STATUS current
	DESCRIPTION "Segment allocation failures"

	::={tcpv4SegmentAllocFail 2}

tcpv4SegmentAllocFailMax	OBJECT-TYPE
	SYNTAX	 CounterBasedGauge64
	MAX-ACCESS read-only
	STATUS current
	DESCRIPTION "Segment allocation failures"

	::={tcpv4SegmentAllocFail 3}

tcpv4SegmentAllocFailLevelTable OBJECT-TYPE
	SYNTAX      SEQUENCE OF Tcpv4SegmentAllocFailLevelEntry
	MAX-ACCESS  not-accessible
	STATUS      current
	DESCRIPTION
	"Table for tcpv4SegmentAllocFail"
	::={tcpv4SegmentAllocFail 4}

tcpv4SegmentAllocFailLevelEntry OBJECT-TYPE
	SYNTAX      Tcpv4SegmentAllocFailLevelEntry
	MAX-ACCESS  not-accessible
	STATUS      current
	DESCRIPTION
	"Table entry for tcpv4SegmentAllocFail"
	INDEX { tcpv4SegmentAllocFailLevelName }
	::={tcpv4SegmentAllocFailLevelTable 1}

Tcpv4SegmentAllocFailLevelEntry ::=
	SEQUENCE {
		tcpv4SegmentAllocFailLevelName	DisplayString,
		tcpv4SegmentAllocFailLevelVal	Counter64,
		tcpv4SegmentAllocFailLevelMom	CounterBasedGauge64,
		tcpv4SegmentAllocFailLevelMax	CounterBasedGauge64
	}

tcpv4SegmentAllocFailLevelName OBJECT-TYPE
	SYNTAX      DisplayString
	MAX-ACCESS  not-accessible
	STATUS      current
	DESCRIPTION
	"Table entry display string for tcpv4SegmentAllocFail"
	::={tcpv4SegmentAllocFailLevelEntry 1}

tcpv4SegmentAllocFailLevelVal OBJECT-TYPE
	SYNTAX	 Counter64
	MAX-ACCESS  read-only
	STATUS      current
	DESCRIPTION
	"Table entry attribute for tcpv4SegmentAllocFail"
	::={tcpv4SegmentAllocFailLevelEntry 2}

tcpv4SegmentAllocFailLevelMom OBJECT-TYPE
	SYNTAX	 CounterBasedGauge64
	MAX-ACCESS  read-only
	STATUS      current
	DESCRIPTION
	"Table entry attribute for tcpv4SegmentAllocFail"
	::={tcpv4SegmentAllocFailLevelEntry 3}

tcpv4SegmentAllocFailLevelMax OBJECT-TYPE
	SYNTAX	 CounterBasedGauge64
	MAX-ACCESS  read-only
	STATUS      current
	DESCRIPTION
	"Table entry attribute for tcpv4SegmentAllocFail"
	::={tcpv4SegmentAllocFailLevelEntry 4}


tcpv4EnqueuedSegments	OBJECT IDENTIFIER ::={tcpv4 34}

tcpv4EnqueuedSegmentsVal	OBJECT-TYPE
	SYNTAX	 Counter64
	MAX-ACCESS read-only
	STATUS current
	DESCRIPTION "Enqueued segments"

	::={tcpv4EnqueuedSegments 1}

tcpv4EnqueuedSegmentsMom	OBJECT-TYPE
	SYNTAX	 CounterBasedGauge64
	MAX-ACCESS read-only
	STATUS current
	DESCRIPTION "Enqueued segments"

	::={tcpv4EnqueuedSegments 2}

tcpv4EnqueuedSegmentsMax	OBJECT-TYPE
	SYNTAX	 CounterBasedGauge64
	MAX-ACCESS read-only
	STATUS current
	DESCRIPTION "Enqueued segments"

	::={tcpv4EnqueuedSegments 3}

tcpv4EnqueuedSegmentsLevelTable OBJECT-TYPE
	SYNTAX      SEQUENCE OF Tcpv4EnqueuedSegmentsLevelEntry
	MAX-ACCESS  not-accessible
	STATUS      current
	DESCRIPTION
	"Table for tcpv4EnqueuedSegments"
	::={tcpv4EnqueuedSegments 4}

tcpv4EnqueuedSegmentsLevelEntry OBJECT-TYPE
	SYNTAX      Tcpv4EnqueuedSegmentsLevelEntry
	MAX-ACCESS  not-accessible
	STATUS      current
	DESCRIPTION
	"Table entry for tcpv4EnqueuedSegments"
	INDEX { tcpv4EnqueuedSegmentsLevelName }
	::={tcpv4EnqueuedSegmentsLevelTable 1}

Tcpv4EnqueuedSegmentsLevelEntry ::=
	SEQUENCE {
		tcpv4EnqueuedSegmentsLevelName	DisplayString,
		tcpv4EnqueuedSegmentsLevelVal	Counter64,
		tcpv4EnqueuedSegmentsLevelMom	CounterBasedGauge64,
		tcpv4EnqueuedSegmentsLevelMax	CounterBasedGauge64
	}

tcpv4EnqueuedSegmentsLevelName OBJECT-TYPE
	SYNTAX      DisplayString
	MAX-ACCESS  not-accessible
	STATUS      current
	DESCRIPTION
	"Table entry display string for tcpv4EnqueuedSegments"
	::={tcpv4EnqueuedSegmentsLevelEntry 1}

tcpv4EnqueuedSegmentsLevelVal OBJECT-TYPE
	SYNTAX	 Counter64
	MAX-ACCESS  read-only
	STATUS      current
	DESCRIPTION
	"Table entry attribute for tcpv4EnqueuedSegments"
	::={tcpv4EnqueuedSegmentsLevelEntry 2}

tcpv4EnqueuedSegmentsLevelMom OBJECT-TYPE
	SYNTAX	 CounterBasedGauge64
	MAX-ACCESS  read-only
	STATUS      current
	DESCRIPTION
	"Table entry attribute for tcpv4EnqueuedSegments"
	::={tcpv4EnqueuedSegmentsLevelEntry 3}

tcpv4EnqueuedSegmentsLevelMax OBJECT-TYPE
	SYNTAX	 CounterBasedGauge64
	MAX-ACCESS  read-only
	STATUS      current
	DESCRIPTION
	"Table entry attribute for tcpv4EnqueuedSegments"
	::={tcpv4EnqueuedSegmentsLevelEntry 4}


tcpv4DequeuedSegments	OBJECT IDENTIFIER ::={tcpv4 35}

tcpv4DequeuedSegmentsVal	OBJECT-TYPE
	SYNTAX	 Counter64
	MAX-ACCESS read-only
	STATUS current
	DESCRIPTION "Dequeued segments"

	::={tcpv4DequeuedSegments 1}

tcpv4DequeuedSegmentsMom	OBJECT-TYPE
	SYNTAX	 CounterBasedGauge64
	MAX-ACCESS read-only
	STATUS current
	DESCRIPTION "Dequeued segments"

	::={tcpv4DequeuedSegments 2}

tcpv4DequeuedSegmentsMax	OBJECT-TYPE
	SYNTAX	 CounterBasedGauge64
	MAX-ACCESS read-only
	STATUS current
	DESCRIPTION "Dequeued segments"

	::={tcpv4DequeuedSegments 3}

tcpv4DequeuedSegmentsLevelTable OBJECT-TYPE
	SYNTAX      SEQUENCE OF Tcpv4DequeuedSegmentsLevelEntry
	MAX-ACCESS  not-accessible
	STATUS      current
	DESCRIPTION
	"Table for tcpv4DequeuedSegments"
	::={tcpv4DequeuedSegments 4}

tcpv4DequeuedSegmentsLevelEntry OBJECT-TYPE
	SYNTAX      Tcpv4DequeuedSegmentsLevelEntry
	MAX-ACCESS  not-accessible
	STATUS      current
	DESCRIPTION
	"Table entry for tcpv4DequeuedSegments"
	INDEX { tcpv4DequeuedSegmentsLevelName }
	::={tcpv4DequeuedSegmentsLevelTable 1}

Tcpv4DequeuedSegmentsLevelEntry ::=
	SEQUENCE {
		tcpv4DequeuedSegmentsLevelName	DisplayString,
		tcpv4DequeuedSegmentsLevelVal	Counter64,
		tcpv4DequeuedSegmentsLevelMom	CounterBasedGauge64,
		tcpv4DequeuedSegmentsLevelMax	CounterBasedGauge64
	}

tcpv4DequeuedSegmentsLevelName OBJECT-TYPE
	SYNTAX      DisplayString
	MAX-ACCESS  not-accessible
	STATUS      current
	DESCRIPTION
	"Table entry display string for tcpv4DequeuedSegments"
	::={tcpv4DequeuedSegmentsLevelEntry 1}

tcpv4DequeuedSegmentsLevelVal OBJECT-TYPE
	SYNTAX	 Counter64
	MAX-ACCESS  read-only
	STATUS      current
	DESCRIPTION
	"Table entry attribute for tcpv4DequeuedSegments"
	::={tcpv4DequeuedSegmentsLevelEntry 2}

tcpv4DequeuedSegmentsLevelMom OBJECT-TYPE
	SYNTAX	 CounterBasedGauge64
	MAX-ACCESS  read-only
	STATUS      current
	DESCRIPTION
	"Table entry attribute for tcpv4DequeuedSegments"
	::={tcpv4DequeuedSegmentsLevelEntry 3}

tcpv4DequeuedSegmentsLevelMax OBJECT-TYPE
	SYNTAX	 CounterBasedGauge64
	MAX-ACCESS  read-only
	STATUS      current
	DESCRIPTION
	"Table entry attribute for tcpv4DequeuedSegments"
	::={tcpv4DequeuedSegmentsLevelEntry 4}


tcpv4DiscardedSegments	OBJECT IDENTIFIER ::={tcpv4 36}

tcpv4DiscardedSegmentsVal	OBJECT-TYPE
	SYNTAX	 Counter64
	MAX-ACCESS read-only
	STATUS current
	DESCRIPTION "Discarded segments"

	::={tcpv4DiscardedSegments 1}

tcpv4DiscardedSegmentsMom	OBJECT-TYPE
	SYNTAX	 CounterBasedGauge64
	MAX-ACCESS read-only
	STATUS current
	DESCRIPTION "Discarded segments"

	::={tcpv4DiscardedSegments 2}

tcpv4DiscardedSegmentsMax	OBJECT-TYPE
	SYNTAX	 CounterBasedGauge64
	MAX-ACCESS read-only
	STATUS current
	DESCRIPTION "Discarded segments"

	::={tcpv4DiscardedSegments 3}

tcpv4DiscardedSegmentsLevelTable OBJECT-TYPE
	SYNTAX      SEQUENCE OF Tcpv4DiscardedSegmentsLevelEntry
	MAX-ACCESS  not-accessible
	STATUS      current
	DESCRIPTION
	"Table for tcpv4DiscardedSegments"
	::={tcpv4DiscardedSegments 4}

tcpv4DiscardedSegmentsLevelEntry OBJECT-TYPE
	SYNTAX      Tcpv4DiscardedSegmentsLevelEntry
	MAX-ACCESS  not-accessible
	STATUS      current
	DESCRIPTION
	"Table entry for tcpv4DiscardedSegments"
	INDEX { tcpv4DiscardedSegmentsLevelName }
	::={tcpv4DiscardedSegmentsLevelTable 1}

Tcpv4DiscardedSegmentsLevelEntry ::=
	SEQUENCE {
		tcpv4DiscardedSegmentsLevelName	DisplayString,
		tcpv4DiscardedSegmentsLevelVal	Counter64,
		tcpv4DiscardedSegmentsLevelMom	CounterBasedGauge64,
		tcpv4DiscardedSegmentsLevelMax	CounterBasedGauge64
	}

tcpv4DiscardedSegmentsLevelName OBJECT-TYPE
	SYNTAX      DisplayString
	MAX-ACCESS  not-accessible
	STATUS      current
	DESCRIPTION
	"Table entry display string for tcpv4DiscardedSegments"
	::={tcpv4DiscardedSegmentsLevelEntry 1}

tcpv4DiscardedSegmentsLevelVal OBJECT-TYPE
	SYNTAX	 Counter64
	MAX-ACCESS  read-only
	STATUS      current
	DESCRIPTION
	"Table entry attribute for tcpv4DiscardedSegments"
	::={tcpv4DiscardedSegmentsLevelEntry 2}

tcpv4DiscardedSegmentsLevelMom OBJECT-TYPE
	SYNTAX	 CounterBasedGauge64
	MAX-ACCESS  read-only
	STATUS      current
	DESCRIPTION
	"Table entry attribute for tcpv4DiscardedSegments"
	::={tcpv4DiscardedSegmentsLevelEntry 3}

tcpv4DiscardedSegmentsLevelMax OBJECT-TYPE
	SYNTAX	 CounterBasedGauge64
	MAX-ACCESS  read-only
	STATUS      current
	DESCRIPTION
	"Table entry attribute for tcpv4DiscardedSegments"
	::={tcpv4DiscardedSegmentsLevelEntry 4}


tcpv4EmptyPackets	OBJECT IDENTIFIER ::={tcpv4 37}

tcpv4EmptyPacketsVal	OBJECT-TYPE
	SYNTAX	 Counter64
	MAX-ACCESS read-only
	STATUS current
	DESCRIPTION "Packets without payload"

	::={tcpv4EmptyPackets 1}

tcpv4EmptyPacketsMom	OBJECT-TYPE
	SYNTAX	 CounterBasedGauge64
	MAX-ACCESS read-only
	STATUS current
	DESCRIPTION "Packets without payload"

	::={tcpv4EmptyPackets 2}

tcpv4EmptyPacketsMax	OBJECT-TYPE
	SYNTAX	 CounterBasedGauge64
	MAX-ACCESS read-only
	STATUS current
	DESCRIPTION "Packets without payload"

	::={tcpv4EmptyPackets 3}

tcpv4EmptyPacketsLevelTable OBJECT-TYPE
	SYNTAX      SEQUENCE OF Tcpv4EmptyPacketsLevelEntry
	MAX-ACCESS  not-accessible
	STATUS      current
	DESCRIPTION
	"Table for tcpv4EmptyPackets"
	::={tcpv4EmptyPackets 4}

tcpv4EmptyPacketsLevelEntry OBJECT-TYPE
	SYNTAX      Tcpv4EmptyPacketsLevelEntry
	MAX-ACCESS  not-accessible
	STATUS      current
	DESCRIPTION
	"Table entry for tcpv4EmptyPackets"
	INDEX { tcpv4EmptyPacketsLevelName }
	::={tcpv4EmptyPacketsLevelTable 1}

Tcpv4EmptyPacketsLevelEntry ::=
	SEQUENCE {
		tcpv4EmptyPacketsLevelName	DisplayString,
		tcpv4EmptyPacketsLevelVal	Counter64,
		tcpv4EmptyPacketsLevelMom	CounterBasedGauge64,
		tcpv4EmptyPacketsLevelMax	CounterBasedGauge64
	}

tcpv4EmptyPacketsLevelName OBJECT-TYPE
	SYNTAX      DisplayString
	MAX-ACCESS  not-accessible
	STATUS      current
	DESCRIPTION
	"Table entry display string for tcpv4EmptyPackets"
	::={tcpv4EmptyPacketsLevelEntry 1}

tcpv4EmptyPacketsLevelVal OBJECT-TYPE
	SYNTAX	 Counter64
	MAX-ACCESS  read-only
	STATUS      current
	DESCRIPTION
	"Table entry attribute for tcpv4EmptyPackets"
	::={tcpv4EmptyPacketsLevelEntry 2}

tcpv4EmptyPacketsLevelMom OBJECT-TYPE
	SYNTAX	 CounterBasedGauge64
	MAX-ACCESS  read-only
	STATUS      current
	DESCRIPTION
	"Table entry attribute for tcpv4EmptyPackets"
	::={tcpv4EmptyPacketsLevelEntry 3}

tcpv4EmptyPacketsLevelMax OBJECT-TYPE
	SYNTAX	 CounterBasedGauge64
	MAX-ACCESS  read-only
	STATUS      current
	DESCRIPTION
	"Table entry attribute for tcpv4EmptyPackets"
	::={tcpv4EmptyPacketsLevelEntry 4}


tcpv4OosPackets	OBJECT IDENTIFIER ::={tcpv4 38}

tcpv4OosPacketsVal	OBJECT-TYPE
	SYNTAX	 Counter64
	MAX-ACCESS read-only
	STATUS current
	DESCRIPTION "Out-of-sync packets"

	::={tcpv4OosPackets 1}

tcpv4OosPacketsMom	OBJECT-TYPE
	SYNTAX	 CounterBasedGauge64
	MAX-ACCESS read-only
	STATUS current
	DESCRIPTION "Out-of-sync packets"

	::={tcpv4OosPackets 2}

tcpv4OosPacketsMax	OBJECT-TYPE
	SYNTAX	 CounterBasedGauge64
	MAX-ACCESS read-only
	STATUS current
	DESCRIPTION "Out-of-sync packets"

	::={tcpv4OosPackets 3}

tcpv4OosPacketsLevelTable OBJECT-TYPE
	SYNTAX      SEQUENCE OF Tcpv4OosPacketsLevelEntry
	MAX-ACCESS  not-accessible
	STATUS      current
	DESCRIPTION
	"Table for tcpv4OosPackets"
	::={tcpv4OosPackets 4}

tcpv4OosPacketsLevelEntry OBJECT-TYPE
	SYNTAX      Tcpv4OosPacketsLevelEntry
	MAX-ACCESS  not-accessible
	STATUS      current
	DESCRIPTION
	"Table entry for tcpv4OosPackets"
	INDEX { tcpv4OosPacketsLevelName }
	::={tcpv4OosPacketsLevelTable 1}

Tcpv4OosPacketsLevelEntry ::=
	SEQUENCE {
		tcpv4OosPacketsLevelName	DisplayString,
		tcpv4OosPacketsLevelVal	Counter64,
		tcpv4OosPacketsLevelMom	CounterBasedGauge64,
		tcpv4OosPacketsLevelMax	CounterBasedGauge64
	}

tcpv4OosPacketsLevelName OBJECT-TYPE
	SYNTAX      DisplayString
	MAX-ACCESS  not-accessible
	STATUS      current
	DESCRIPTION
	"Table entry display string for tcpv4OosPackets"
	::={tcpv4OosPacketsLevelEntry 1}

tcpv4OosPacketsLevelVal OBJECT-TYPE
	SYNTAX	 Counter64
	MAX-ACCESS  read-only
	STATUS      current
	DESCRIPTION
	"Table entry attribute for tcpv4OosPackets"
	::={tcpv4OosPacketsLevelEntry 2}

tcpv4OosPacketsLevelMom OBJECT-TYPE
	SYNTAX	 CounterBasedGauge64
	MAX-ACCESS  read-only
	STATUS      current
	DESCRIPTION
	"Table entry attribute for tcpv4OosPackets"
	::={tcpv4OosPacketsLevelEntry 3}

tcpv4OosPacketsLevelMax OBJECT-TYPE
	SYNTAX	 CounterBasedGauge64
	MAX-ACCESS  read-only
	STATUS      current
	DESCRIPTION
	"Table entry attribute for tcpv4OosPackets"
	::={tcpv4OosPacketsLevelEntry 4}


tcpv4OosBytes	OBJECT IDENTIFIER ::={tcpv4 39}

tcpv4OosBytesVal	OBJECT-TYPE
	SYNTAX	 Counter64
	MAX-ACCESS read-only
	STATUS current
	DESCRIPTION "Out-of-sync bytes"

	::={tcpv4OosBytes 1}

tcpv4OosBytesMom	OBJECT-TYPE
	SYNTAX	 CounterBasedGauge64
	MAX-ACCESS read-only
	STATUS current
	DESCRIPTION "Out-of-sync bytes"

	::={tcpv4OosBytes 2}

tcpv4OosBytesMax	OBJECT-TYPE
	SYNTAX	 CounterBasedGauge64
	MAX-ACCESS read-only
	STATUS current
	DESCRIPTION "Out-of-sync bytes"

	::={tcpv4OosBytes 3}

tcpv4OosBytesLevelTable OBJECT-TYPE
	SYNTAX      SEQUENCE OF Tcpv4OosBytesLevelEntry
	MAX-ACCESS  not-accessible
	STATUS      current
	DESCRIPTION
	"Table for tcpv4OosBytes"
	::={tcpv4OosBytes 4}

tcpv4OosBytesLevelEntry OBJECT-TYPE
	SYNTAX      Tcpv4OosBytesLevelEntry
	MAX-ACCESS  not-accessible
	STATUS      current
	DESCRIPTION
	"Table entry for tcpv4OosBytes"
	INDEX { tcpv4OosBytesLevelName }
	::={tcpv4OosBytesLevelTable 1}

Tcpv4OosBytesLevelEntry ::=
	SEQUENCE {
		tcpv4OosBytesLevelName	DisplayString,
		tcpv4OosBytesLevelVal	Counter64,
		tcpv4OosBytesLevelMom	CounterBasedGauge64,
		tcpv4OosBytesLevelMax	CounterBasedGauge64
	}

tcpv4OosBytesLevelName OBJECT-TYPE
	SYNTAX      DisplayString
	MAX-ACCESS  not-accessible
	STATUS      current
	DESCRIPTION
	"Table entry display string for tcpv4OosBytes"
	::={tcpv4OosBytesLevelEntry 1}

tcpv4OosBytesLevelVal OBJECT-TYPE
	SYNTAX	 Counter64
	MAX-ACCESS  read-only
	STATUS      current
	DESCRIPTION
	"Table entry attribute for tcpv4OosBytes"
	::={tcpv4OosBytesLevelEntry 2}

tcpv4OosBytesLevelMom OBJECT-TYPE
	SYNTAX	 CounterBasedGauge64
	MAX-ACCESS  read-only
	STATUS      current
	DESCRIPTION
	"Table entry attribute for tcpv4OosBytes"
	::={tcpv4OosBytesLevelEntry 3}

tcpv4OosBytesLevelMax OBJECT-TYPE
	SYNTAX	 CounterBasedGauge64
	MAX-ACCESS  read-only
	STATUS      current
	DESCRIPTION
	"Table entry attribute for tcpv4OosBytes"
	::={tcpv4OosBytesLevelEntry 4}


tcpv4Retransmits	OBJECT IDENTIFIER ::={tcpv4 40}

tcpv4RetransmitsVal	OBJECT-TYPE
	SYNTAX	 Counter64
	MAX-ACCESS read-only
	STATUS current
	DESCRIPTION "Retransmitted packets"

	::={tcpv4Retransmits 1}

tcpv4RetransmitsMom	OBJECT-TYPE
	SYNTAX	 CounterBasedGauge64
	MAX-ACCESS read-only
	STATUS current
	DESCRIPTION "Retransmitted packets"

	::={tcpv4Retransmits 2}

tcpv4RetransmitsMax	OBJECT-TYPE
	SYNTAX	 CounterBasedGauge64
	MAX-ACCESS read-only
	STATUS current
	DESCRIPTION "Retransmitted packets"

	::={tcpv4Retransmits 3}

tcpv4RetransmitsLevelTable OBJECT-TYPE
	SYNTAX      SEQUENCE OF Tcpv4RetransmitsLevelEntry
	MAX-ACCESS  not-accessible
	STATUS      current
	DESCRIPTION
	"Table for tcpv4Retransmits"
	::={tcpv4Retransmits 4}

tcpv4RetransmitsLevelEntry OBJECT-TYPE
	SYNTAX      Tcpv4RetransmitsLevelEntry
	MAX-ACCESS  not-accessible
	STATUS      current
	DESCRIPTION
	"Table entry for tcpv4Retransmits"
	INDEX { tcpv4RetransmitsLevelName }
	::={tcpv4RetransmitsLevelTable 1}

Tcpv4RetransmitsLevelEntry ::=
	SEQUENCE {
		tcpv4RetransmitsLevelName	DisplayString,
		tcpv4RetransmitsLevelVal	Counter64,
		tcpv4RetransmitsLevelMom	CounterBasedGauge64,
		tcpv4RetransmitsLevelMax	CounterBasedGauge64
	}

tcpv4RetransmitsLevelName OBJECT-TYPE
	SYNTAX      DisplayString
	MAX-ACCESS  not-accessible
	STATUS      current
	DESCRIPTION
	"Table entry display string for tcpv4Retransmits"
	::={tcpv4RetransmitsLevelEntry 1}

tcpv4RetransmitsLevelVal OBJECT-TYPE
	SYNTAX	 Counter64
	MAX-ACCESS  read-only
	STATUS      current
	DESCRIPTION
	"Table entry attribute for tcpv4Retransmits"
	::={tcpv4RetransmitsLevelEntry 2}

tcpv4RetransmitsLevelMom OBJECT-TYPE
	SYNTAX	 CounterBasedGauge64
	MAX-ACCESS  read-only
	STATUS      current
	DESCRIPTION
	"Table entry attribute for tcpv4Retransmits"
	::={tcpv4RetransmitsLevelEntry 3}

tcpv4RetransmitsLevelMax OBJECT-TYPE
	SYNTAX	 CounterBasedGauge64
	MAX-ACCESS  read-only
	STATUS      current
	DESCRIPTION
	"Table entry attribute for tcpv4Retransmits"
	::={tcpv4RetransmitsLevelEntry 4}


tcpv4Cwr	OBJECT IDENTIFIER ::={tcpv4 41}

tcpv4CwrVal	OBJECT-TYPE
	SYNTAX	 Counter64
	MAX-ACCESS read-only
	STATUS current
	DESCRIPTION "Congestion Window Reduced Packets"

	::={tcpv4Cwr 1}

tcpv4CwrMom	OBJECT-TYPE
	SYNTAX	 CounterBasedGauge64
	MAX-ACCESS read-only
	STATUS current
	DESCRIPTION "Congestion Window Reduced Packets"

	::={tcpv4Cwr 2}

tcpv4CwrMax	OBJECT-TYPE
	SYNTAX	 CounterBasedGauge64
	MAX-ACCESS read-only
	STATUS current
	DESCRIPTION "Congestion Window Reduced Packets"

	::={tcpv4Cwr 3}

tcpv4CwrLevelTable OBJECT-TYPE
	SYNTAX      SEQUENCE OF Tcpv4CwrLevelEntry
	MAX-ACCESS  not-accessible
	STATUS      current
	DESCRIPTION
	"Table for tcpv4Cwr"
	::={tcpv4Cwr 4}

tcpv4CwrLevelEntry OBJECT-TYPE
	SYNTAX      Tcpv4CwrLevelEntry
	MAX-ACCESS  not-accessible
	STATUS      current
	DESCRIPTION
	"Table entry for tcpv4Cwr"
	INDEX { tcpv4CwrLevelName }
	::={tcpv4CwrLevelTable 1}

Tcpv4CwrLevelEntry ::=
	SEQUENCE {
		tcpv4CwrLevelName	DisplayString,
		tcpv4CwrLevelVal	Counter64,
		tcpv4CwrLevelMom	CounterBasedGauge64,
		tcpv4CwrLevelMax	CounterBasedGauge64
	}

tcpv4CwrLevelName OBJECT-TYPE
	SYNTAX      DisplayString
	MAX-ACCESS  not-accessible
	STATUS      current
	DESCRIPTION
	"Table entry display string for tcpv4Cwr"
	::={tcpv4CwrLevelEntry 1}

tcpv4CwrLevelVal OBJECT-TYPE
	SYNTAX	 Counter64
	MAX-ACCESS  read-only
	STATUS      current
	DESCRIPTION
	"Table entry attribute for tcpv4Cwr"
	::={tcpv4CwrLevelEntry 2}

tcpv4CwrLevelMom OBJECT-TYPE
	SYNTAX	 CounterBasedGauge64
	MAX-ACCESS  read-only
	STATUS      current
	DESCRIPTION
	"Table entry attribute for tcpv4Cwr"
	::={tcpv4CwrLevelEntry 3}

tcpv4CwrLevelMax OBJECT-TYPE
	SYNTAX	 CounterBasedGauge64
	MAX-ACCESS  read-only
	STATUS      current
	DESCRIPTION
	"Table entry attribute for tcpv4Cwr"
	::={tcpv4CwrLevelEntry 4}


tcpv4Ecne	OBJECT IDENTIFIER ::={tcpv4 42}

tcpv4EcneVal	OBJECT-TYPE
	SYNTAX	 Counter64
	MAX-ACCESS read-only
	STATUS current
	DESCRIPTION "Explicit Congestion Notification Echo Packets"

	::={tcpv4Ecne 1}

tcpv4EcneMom	OBJECT-TYPE
	SYNTAX	 CounterBasedGauge64
	MAX-ACCESS read-only
	STATUS current
	DESCRIPTION "Explicit Congestion Notification Echo Packets"

	::={tcpv4Ecne 2}

tcpv4EcneMax	OBJECT-TYPE
	SYNTAX	 CounterBasedGauge64
	MAX-ACCESS read-only
	STATUS current
	DESCRIPTION "Explicit Congestion Notification Echo Packets"

	::={tcpv4Ecne 3}

tcpv4EcneLevelTable OBJECT-TYPE
	SYNTAX      SEQUENCE OF Tcpv4EcneLevelEntry
	MAX-ACCESS  not-accessible
	STATUS      current
	DESCRIPTION
	"Table for tcpv4Ecne"
	::={tcpv4Ecne 4}

tcpv4EcneLevelEntry OBJECT-TYPE
	SYNTAX      Tcpv4EcneLevelEntry
	MAX-ACCESS  not-accessible
	STATUS      current
	DESCRIPTION
	"Table entry for tcpv4Ecne"
	INDEX { tcpv4EcneLevelName }
	::={tcpv4EcneLevelTable 1}

Tcpv4EcneLevelEntry ::=
	SEQUENCE {
		tcpv4EcneLevelName	DisplayString,
		tcpv4EcneLevelVal	Counter64,
		tcpv4EcneLevelMom	CounterBasedGauge64,
		tcpv4EcneLevelMax	CounterBasedGauge64
	}

tcpv4EcneLevelName OBJECT-TYPE
	SYNTAX      DisplayString
	MAX-ACCESS  not-accessible
	STATUS      current
	DESCRIPTION
	"Table entry display string for tcpv4Ecne"
	::={tcpv4EcneLevelEntry 1}

tcpv4EcneLevelVal OBJECT-TYPE
	SYNTAX	 Counter64
	MAX-ACCESS  read-only
	STATUS      current
	DESCRIPTION
	"Table entry attribute for tcpv4Ecne"
	::={tcpv4EcneLevelEntry 2}

tcpv4EcneLevelMom OBJECT-TYPE
	SYNTAX	 CounterBasedGauge64
	MAX-ACCESS  read-only
	STATUS      current
	DESCRIPTION
	"Table entry attribute for tcpv4Ecne"
	::={tcpv4EcneLevelEntry 3}

tcpv4EcneLevelMax OBJECT-TYPE
	SYNTAX	 CounterBasedGauge64
	MAX-ACCESS  read-only
	STATUS      current
	DESCRIPTION
	"Table entry attribute for tcpv4Ecne"
	::={tcpv4EcneLevelEntry 4}


tcpv4SimOpen	OBJECT IDENTIFIER ::={tcpv4 43}

tcpv4SimOpenVal	OBJECT-TYPE
	SYNTAX	 Counter64
	MAX-ACCESS read-only
	STATUS current
	DESCRIPTION "Simultaneous Open"

	::={tcpv4SimOpen 1}

tcpv4SimOpenMom	OBJECT-TYPE
	SYNTAX	 CounterBasedGauge64
	MAX-ACCESS read-only
	STATUS current
	DESCRIPTION "Simultaneous Open"

	::={tcpv4SimOpen 2}

tcpv4SimOpenMax	OBJECT-TYPE
	SYNTAX	 CounterBasedGauge64
	MAX-ACCESS read-only
	STATUS current
	DESCRIPTION "Simultaneous Open"

	::={tcpv4SimOpen 3}

tcpv4SimOpenLevelTable OBJECT-TYPE
	SYNTAX      SEQUENCE OF Tcpv4SimOpenLevelEntry
	MAX-ACCESS  not-accessible
	STATUS      current
	DESCRIPTION
	"Table for tcpv4SimOpen"
	::={tcpv4SimOpen 4}

tcpv4SimOpenLevelEntry OBJECT-TYPE
	SYNTAX      Tcpv4SimOpenLevelEntry
	MAX-ACCESS  not-accessible
	STATUS      current
	DESCRIPTION
	"Table entry for tcpv4SimOpen"
	INDEX { tcpv4SimOpenLevelName }
	::={tcpv4SimOpenLevelTable 1}

Tcpv4SimOpenLevelEntry ::=
	SEQUENCE {
		tcpv4SimOpenLevelName	DisplayString,
		tcpv4SimOpenLevelVal	Counter64,
		tcpv4SimOpenLevelMom	CounterBasedGauge64,
		tcpv4SimOpenLevelMax	CounterBasedGauge64
	}

tcpv4SimOpenLevelName OBJECT-TYPE
	SYNTAX      DisplayString
	MAX-ACCESS  not-accessible
	STATUS      current
	DESCRIPTION
	"Table entry display string for tcpv4SimOpen"
	::={tcpv4SimOpenLevelEntry 1}

tcpv4SimOpenLevelVal OBJECT-TYPE
	SYNTAX	 Counter64
	MAX-ACCESS  read-only
	STATUS      current
	DESCRIPTION
	"Table entry attribute for tcpv4SimOpen"
	::={tcpv4SimOpenLevelEntry 2}

tcpv4SimOpenLevelMom OBJECT-TYPE
	SYNTAX	 CounterBasedGauge64
	MAX-ACCESS  read-only
	STATUS      current
	DESCRIPTION
	"Table entry attribute for tcpv4SimOpen"
	::={tcpv4SimOpenLevelEntry 3}

tcpv4SimOpenLevelMax OBJECT-TYPE
	SYNTAX	 CounterBasedGauge64
	MAX-ACCESS  read-only
	STATUS      current
	DESCRIPTION
	"Table entry attribute for tcpv4SimOpen"
	::={tcpv4SimOpenLevelEntry 4}


tcpv4Reopened	OBJECT IDENTIFIER ::={tcpv4 44}

tcpv4ReopenedVal	OBJECT-TYPE
	SYNTAX	 Counter64
	MAX-ACCESS read-only
	STATUS current
	DESCRIPTION "Connections reopened"

	::={tcpv4Reopened 1}

tcpv4ReopenedMom	OBJECT-TYPE
	SYNTAX	 CounterBasedGauge64
	MAX-ACCESS read-only
	STATUS current
	DESCRIPTION "Connections reopened"

	::={tcpv4Reopened 2}

tcpv4ReopenedMax	OBJECT-TYPE
	SYNTAX	 CounterBasedGauge64
	MAX-ACCESS read-only
	STATUS current
	DESCRIPTION "Connections reopened"

	::={tcpv4Reopened 3}

tcpv4ReopenedLevelTable OBJECT-TYPE
	SYNTAX      SEQUENCE OF Tcpv4ReopenedLevelEntry
	MAX-ACCESS  not-accessible
	STATUS      current
	DESCRIPTION
	"Table for tcpv4Reopened"
	::={tcpv4Reopened 4}

tcpv4ReopenedLevelEntry OBJECT-TYPE
	SYNTAX      Tcpv4ReopenedLevelEntry
	MAX-ACCESS  not-accessible
	STATUS      current
	DESCRIPTION
	"Table entry for tcpv4Reopened"
	INDEX { tcpv4ReopenedLevelName }
	::={tcpv4ReopenedLevelTable 1}

Tcpv4ReopenedLevelEntry ::=
	SEQUENCE {
		tcpv4ReopenedLevelName	DisplayString,
		tcpv4ReopenedLevelVal	Counter64,
		tcpv4ReopenedLevelMom	CounterBasedGauge64,
		tcpv4ReopenedLevelMax	CounterBasedGauge64
	}

tcpv4ReopenedLevelName OBJECT-TYPE
	SYNTAX      DisplayString
	MAX-ACCESS  not-accessible
	STATUS      current
	DESCRIPTION
	"Table entry display string for tcpv4Reopened"
	::={tcpv4ReopenedLevelEntry 1}

tcpv4ReopenedLevelVal OBJECT-TYPE
	SYNTAX	 Counter64
	MAX-ACCESS  read-only
	STATUS      current
	DESCRIPTION
	"Table entry attribute for tcpv4Reopened"
	::={tcpv4ReopenedLevelEntry 2}

tcpv4ReopenedLevelMom OBJECT-TYPE
	SYNTAX	 CounterBasedGauge64
	MAX-ACCESS  read-only
	STATUS      current
	DESCRIPTION
	"Table entry attribute for tcpv4Reopened"
	::={tcpv4ReopenedLevelEntry 3}

tcpv4ReopenedLevelMax OBJECT-TYPE
	SYNTAX	 CounterBasedGauge64
	MAX-ACCESS  read-only
	STATUS      current
	DESCRIPTION
	"Table entry attribute for tcpv4Reopened"
	::={tcpv4ReopenedLevelEntry 4}


tcpv4TsPacket	OBJECT IDENTIFIER ::={tcpv4 45}

tcpv4TsPacketVal	OBJECT-TYPE
	SYNTAX	 Counter64
	MAX-ACCESS read-only
	STATUS current
	DESCRIPTION "Packets with Time Stamp Option"

	::={tcpv4TsPacket 1}

tcpv4TsPacketMom	OBJECT-TYPE
	SYNTAX	 CounterBasedGauge64
	MAX-ACCESS read-only
	STATUS current
	DESCRIPTION "Packets with Time Stamp Option"

	::={tcpv4TsPacket 2}

tcpv4TsPacketMax	OBJECT-TYPE
	SYNTAX	 CounterBasedGauge64
	MAX-ACCESS read-only
	STATUS current
	DESCRIPTION "Packets with Time Stamp Option"

	::={tcpv4TsPacket 3}

tcpv4TsPacketLevelTable OBJECT-TYPE
	SYNTAX      SEQUENCE OF Tcpv4TsPacketLevelEntry
	MAX-ACCESS  not-accessible
	STATUS      current
	DESCRIPTION
	"Table for tcpv4TsPacket"
	::={tcpv4TsPacket 4}

tcpv4TsPacketLevelEntry OBJECT-TYPE
	SYNTAX      Tcpv4TsPacketLevelEntry
	MAX-ACCESS  not-accessible
	STATUS      current
	DESCRIPTION
	"Table entry for tcpv4TsPacket"
	INDEX { tcpv4TsPacketLevelName }
	::={tcpv4TsPacketLevelTable 1}

Tcpv4TsPacketLevelEntry ::=
	SEQUENCE {
		tcpv4TsPacketLevelName	DisplayString,
		tcpv4TsPacketLevelVal	Counter64,
		tcpv4TsPacketLevelMom	CounterBasedGauge64,
		tcpv4TsPacketLevelMax	CounterBasedGauge64
	}

tcpv4TsPacketLevelName OBJECT-TYPE
	SYNTAX      DisplayString
	MAX-ACCESS  not-accessible
	STATUS      current
	DESCRIPTION
	"Table entry display string for tcpv4TsPacket"
	::={tcpv4TsPacketLevelEntry 1}

tcpv4TsPacketLevelVal OBJECT-TYPE
	SYNTAX	 Counter64
	MAX-ACCESS  read-only
	STATUS      current
	DESCRIPTION
	"Table entry attribute for tcpv4TsPacket"
	::={tcpv4TsPacketLevelEntry 2}

tcpv4TsPacketLevelMom OBJECT-TYPE
	SYNTAX	 CounterBasedGauge64
	MAX-ACCESS  read-only
	STATUS      current
	DESCRIPTION
	"Table entry attribute for tcpv4TsPacket"
	::={tcpv4TsPacketLevelEntry 3}

tcpv4TsPacketLevelMax OBJECT-TYPE
	SYNTAX	 CounterBasedGauge64
	MAX-ACCESS  read-only
	STATUS      current
	DESCRIPTION
	"Table entry attribute for tcpv4TsPacket"
	::={tcpv4TsPacketLevelEntry 4}


tcpv4TsCalibrationSuccess	OBJECT IDENTIFIER ::={tcpv4 46}

tcpv4TsCalibrationSuccessVal	OBJECT-TYPE
	SYNTAX	 Counter64
	MAX-ACCESS read-only
	STATUS current
	DESCRIPTION "Successfull RTT Calibration"

	::={tcpv4TsCalibrationSuccess 1}

tcpv4TsCalibrationSuccessMom	OBJECT-TYPE
	SYNTAX	 CounterBasedGauge64
	MAX-ACCESS read-only
	STATUS current
	DESCRIPTION "Successfull RTT Calibration"

	::={tcpv4TsCalibrationSuccess 2}

tcpv4TsCalibrationSuccessMax	OBJECT-TYPE
	SYNTAX	 CounterBasedGauge64
	MAX-ACCESS read-only
	STATUS current
	DESCRIPTION "Successfull RTT Calibration"

	::={tcpv4TsCalibrationSuccess 3}

tcpv4TsCalibrationSuccessLevelTable OBJECT-TYPE
	SYNTAX      SEQUENCE OF Tcpv4TsCalibrationSuccessLevelEntry
	MAX-ACCESS  not-accessible
	STATUS      current
	DESCRIPTION
	"Table for tcpv4TsCalibrationSuccess"
	::={tcpv4TsCalibrationSuccess 4}

tcpv4TsCalibrationSuccessLevelEntry OBJECT-TYPE
	SYNTAX      Tcpv4TsCalibrationSuccessLevelEntry
	MAX-ACCESS  not-accessible
	STATUS      current
	DESCRIPTION
	"Table entry for tcpv4TsCalibrationSuccess"
	INDEX { tcpv4TsCalibrationSuccessLevelName }
	::={tcpv4TsCalibrationSuccessLevelTable 1}

Tcpv4TsCalibrationSuccessLevelEntry ::=
	SEQUENCE {
		tcpv4TsCalibrationSuccessLevelName	DisplayString,
		tcpv4TsCalibrationSuccessLevelVal	Counter64,
		tcpv4TsCalibrationSuccessLevelMom	CounterBasedGauge64,
		tcpv4TsCalibrationSuccessLevelMax	CounterBasedGauge64
	}

tcpv4TsCalibrationSuccessLevelName OBJECT-TYPE
	SYNTAX      DisplayString
	MAX-ACCESS  not-accessible
	STATUS      current
	DESCRIPTION
	"Table entry display string for tcpv4TsCalibrationSuccess"
	::={tcpv4TsCalibrationSuccessLevelEntry 1}

tcpv4TsCalibrationSuccessLevelVal OBJECT-TYPE
	SYNTAX	 Counter64
	MAX-ACCESS  read-only
	STATUS      current
	DESCRIPTION
	"Table entry attribute for tcpv4TsCalibrationSuccess"
	::={tcpv4TsCalibrationSuccessLevelEntry 2}

tcpv4TsCalibrationSuccessLevelMom OBJECT-TYPE
	SYNTAX	 CounterBasedGauge64
	MAX-ACCESS  read-only
	STATUS      current
	DESCRIPTION
	"Table entry attribute for tcpv4TsCalibrationSuccess"
	::={tcpv4TsCalibrationSuccessLevelEntry 3}

tcpv4TsCalibrationSuccessLevelMax OBJECT-TYPE
	SYNTAX	 CounterBasedGauge64
	MAX-ACCESS  read-only
	STATUS      current
	DESCRIPTION
	"Table entry attribute for tcpv4TsCalibrationSuccess"
	::={tcpv4TsCalibrationSuccessLevelEntry 4}


tcpv4TsCalibrationFail	OBJECT IDENTIFIER ::={tcpv4 47}

tcpv4TsCalibrationFailVal	OBJECT-TYPE
	SYNTAX	 Counter64
	MAX-ACCESS read-only
	STATUS current
	DESCRIPTION "Failed RTT Calibration"

	::={tcpv4TsCalibrationFail 1}

tcpv4TsCalibrationFailMom	OBJECT-TYPE
	SYNTAX	 CounterBasedGauge64
	MAX-ACCESS read-only
	STATUS current
	DESCRIPTION "Failed RTT Calibration"

	::={tcpv4TsCalibrationFail 2}

tcpv4TsCalibrationFailMax	OBJECT-TYPE
	SYNTAX	 CounterBasedGauge64
	MAX-ACCESS read-only
	STATUS current
	DESCRIPTION "Failed RTT Calibration"

	::={tcpv4TsCalibrationFail 3}

tcpv4TsCalibrationFailLevelTable OBJECT-TYPE
	SYNTAX      SEQUENCE OF Tcpv4TsCalibrationFailLevelEntry
	MAX-ACCESS  not-accessible
	STATUS      current
	DESCRIPTION
	"Table for tcpv4TsCalibrationFail"
	::={tcpv4TsCalibrationFail 4}

tcpv4TsCalibrationFailLevelEntry OBJECT-TYPE
	SYNTAX      Tcpv4TsCalibrationFailLevelEntry
	MAX-ACCESS  not-accessible
	STATUS      current
	DESCRIPTION
	"Table entry for tcpv4TsCalibrationFail"
	INDEX { tcpv4TsCalibrationFailLevelName }
	::={tcpv4TsCalibrationFailLevelTable 1}

Tcpv4TsCalibrationFailLevelEntry ::=
	SEQUENCE {
		tcpv4TsCalibrationFailLevelName	DisplayString,
		tcpv4TsCalibrationFailLevelVal	Counter64,
		tcpv4TsCalibrationFailLevelMom	CounterBasedGauge64,
		tcpv4TsCalibrationFailLevelMax	CounterBasedGauge64
	}

tcpv4TsCalibrationFailLevelName OBJECT-TYPE
	SYNTAX      DisplayString
	MAX-ACCESS  not-accessible
	STATUS      current
	DESCRIPTION
	"Table entry display string for tcpv4TsCalibrationFail"
	::={tcpv4TsCalibrationFailLevelEntry 1}

tcpv4TsCalibrationFailLevelVal OBJECT-TYPE
	SYNTAX	 Counter64
	MAX-ACCESS  read-only
	STATUS      current
	DESCRIPTION
	"Table entry attribute for tcpv4TsCalibrationFail"
	::={tcpv4TsCalibrationFailLevelEntry 2}

tcpv4TsCalibrationFailLevelMom OBJECT-TYPE
	SYNTAX	 CounterBasedGauge64
	MAX-ACCESS  read-only
	STATUS      current
	DESCRIPTION
	"Table entry attribute for tcpv4TsCalibrationFail"
	::={tcpv4TsCalibrationFailLevelEntry 3}

tcpv4TsCalibrationFailLevelMax OBJECT-TYPE
	SYNTAX	 CounterBasedGauge64
	MAX-ACCESS  read-only
	STATUS      current
	DESCRIPTION
	"Table entry attribute for tcpv4TsCalibrationFail"
	::={tcpv4TsCalibrationFailLevelEntry 4}


tcpv4SegmentsFailedDequeue	OBJECT IDENTIFIER ::={tcpv4 48}

tcpv4SegmentsFailedDequeueVal	OBJECT-TYPE
	SYNTAX	 Counter64
	MAX-ACCESS read-only
	STATUS current
	DESCRIPTION "Segments that failed to dequeue due to invalid TCP sequences"

	::={tcpv4SegmentsFailedDequeue 1}

tcpv4SegmentsFailedDequeueMom	OBJECT-TYPE
	SYNTAX	 CounterBasedGauge64
	MAX-ACCESS read-only
	STATUS current
	DESCRIPTION "Segments that failed to dequeue due to invalid TCP sequences"

	::={tcpv4SegmentsFailedDequeue 2}

tcpv4SegmentsFailedDequeueMax	OBJECT-TYPE
	SYNTAX	 CounterBasedGauge64
	MAX-ACCESS read-only
	STATUS current
	DESCRIPTION "Segments that failed to dequeue due to invalid TCP sequences"

	::={tcpv4SegmentsFailedDequeue 3}

tcpv4SegmentsFailedDequeueLevelTable OBJECT-TYPE
	SYNTAX      SEQUENCE OF Tcpv4SegmentsFailedDequeueLevelEntry
	MAX-ACCESS  not-accessible
	STATUS      current
	DESCRIPTION
	"Table for tcpv4SegmentsFailedDequeue"
	::={tcpv4SegmentsFailedDequeue 4}

tcpv4SegmentsFailedDequeueLevelEntry OBJECT-TYPE
	SYNTAX      Tcpv4SegmentsFailedDequeueLevelEntry
	MAX-ACCESS  not-accessible
	STATUS      current
	DESCRIPTION
	"Table entry for tcpv4SegmentsFailedDequeue"
	INDEX { tcpv4SegmentsFailedDequeueLevelName }
	::={tcpv4SegmentsFailedDequeueLevelTable 1}

Tcpv4SegmentsFailedDequeueLevelEntry ::=
	SEQUENCE {
		tcpv4SegmentsFailedDequeueLevelName	DisplayString,
		tcpv4SegmentsFailedDequeueLevelVal	Counter64,
		tcpv4SegmentsFailedDequeueLevelMom	CounterBasedGauge64,
		tcpv4SegmentsFailedDequeueLevelMax	CounterBasedGauge64
	}

tcpv4SegmentsFailedDequeueLevelName OBJECT-TYPE
	SYNTAX      DisplayString
	MAX-ACCESS  not-accessible
	STATUS      current
	DESCRIPTION
	"Table entry display string for tcpv4SegmentsFailedDequeue"
	::={tcpv4SegmentsFailedDequeueLevelEntry 1}

tcpv4SegmentsFailedDequeueLevelVal OBJECT-TYPE
	SYNTAX	 Counter64
	MAX-ACCESS  read-only
	STATUS      current
	DESCRIPTION
	"Table entry attribute for tcpv4SegmentsFailedDequeue"
	::={tcpv4SegmentsFailedDequeueLevelEntry 2}

tcpv4SegmentsFailedDequeueLevelMom OBJECT-TYPE
	SYNTAX	 CounterBasedGauge64
	MAX-ACCESS  read-only
	STATUS      current
	DESCRIPTION
	"Table entry attribute for tcpv4SegmentsFailedDequeue"
	::={tcpv4SegmentsFailedDequeueLevelEntry 3}

tcpv4SegmentsFailedDequeueLevelMax OBJECT-TYPE
	SYNTAX	 CounterBasedGauge64
	MAX-ACCESS  read-only
	STATUS      current
	DESCRIPTION
	"Table entry attribute for tcpv4SegmentsFailedDequeue"
	::={tcpv4SegmentsFailedDequeueLevelEntry 4}


tcpv4SegmentsFailedDequeueSkip	OBJECT IDENTIFIER ::={tcpv4 49}

tcpv4SegmentsFailedDequeueSkipVal	OBJECT-TYPE
	SYNTAX	 Counter64
	MAX-ACCESS read-only
	STATUS current
	DESCRIPTION "Segments that failed to dequeue due to DRDL skip state becoming out of sync"

	::={tcpv4SegmentsFailedDequeueSkip 1}

tcpv4SegmentsFailedDequeueSkipMom	OBJECT-TYPE
	SYNTAX	 CounterBasedGauge64
	MAX-ACCESS read-only
	STATUS current
	DESCRIPTION "Segments that failed to dequeue due to DRDL skip state becoming out of sync"

	::={tcpv4SegmentsFailedDequeueSkip 2}

tcpv4SegmentsFailedDequeueSkipMax	OBJECT-TYPE
	SYNTAX	 CounterBasedGauge64
	MAX-ACCESS read-only
	STATUS current
	DESCRIPTION "Segments that failed to dequeue due to DRDL skip state becoming out of sync"

	::={tcpv4SegmentsFailedDequeueSkip 3}

tcpv4SegmentsFailedDequeueSkipLevelTable OBJECT-TYPE
	SYNTAX      SEQUENCE OF Tcpv4SegmentsFailedDequeueSkipLevelEntry
	MAX-ACCESS  not-accessible
	STATUS      current
	DESCRIPTION
	"Table for tcpv4SegmentsFailedDequeueSkip"
	::={tcpv4SegmentsFailedDequeueSkip 4}

tcpv4SegmentsFailedDequeueSkipLevelEntry OBJECT-TYPE
	SYNTAX      Tcpv4SegmentsFailedDequeueSkipLevelEntry
	MAX-ACCESS  not-accessible
	STATUS      current
	DESCRIPTION
	"Table entry for tcpv4SegmentsFailedDequeueSkip"
	INDEX { tcpv4SegmentsFailedDequeueSkipLevelName }
	::={tcpv4SegmentsFailedDequeueSkipLevelTable 1}

Tcpv4SegmentsFailedDequeueSkipLevelEntry ::=
	SEQUENCE {
		tcpv4SegmentsFailedDequeueSkipLevelName	DisplayString,
		tcpv4SegmentsFailedDequeueSkipLevelVal	Counter64,
		tcpv4SegmentsFailedDequeueSkipLevelMom	CounterBasedGauge64,
		tcpv4SegmentsFailedDequeueSkipLevelMax	CounterBasedGauge64
	}

tcpv4SegmentsFailedDequeueSkipLevelName OBJECT-TYPE
	SYNTAX      DisplayString
	MAX-ACCESS  not-accessible
	STATUS      current
	DESCRIPTION
	"Table entry display string for tcpv4SegmentsFailedDequeueSkip"
	::={tcpv4SegmentsFailedDequeueSkipLevelEntry 1}

tcpv4SegmentsFailedDequeueSkipLevelVal OBJECT-TYPE
	SYNTAX	 Counter64
	MAX-ACCESS  read-only
	STATUS      current
	DESCRIPTION
	"Table entry attribute for tcpv4SegmentsFailedDequeueSkip"
	::={tcpv4SegmentsFailedDequeueSkipLevelEntry 2}

tcpv4SegmentsFailedDequeueSkipLevelMom OBJECT-TYPE
	SYNTAX	 CounterBasedGauge64
	MAX-ACCESS  read-only
	STATUS      current
	DESCRIPTION
	"Table entry attribute for tcpv4SegmentsFailedDequeueSkip"
	::={tcpv4SegmentsFailedDequeueSkipLevelEntry 3}

tcpv4SegmentsFailedDequeueSkipLevelMax OBJECT-TYPE
	SYNTAX	 CounterBasedGauge64
	MAX-ACCESS  read-only
	STATUS      current
	DESCRIPTION
	"Table entry attribute for tcpv4SegmentsFailedDequeueSkip"
	::={tcpv4SegmentsFailedDequeueSkipLevelEntry 4}


tcpv4SegmentsFailedDequeueTfo	OBJECT IDENTIFIER ::={tcpv4 50}

tcpv4SegmentsFailedDequeueTfoVal	OBJECT-TYPE
	SYNTAX	 Counter64
	MAX-ACCESS read-only
	STATUS current
	DESCRIPTION "Segments that failed to dequeue due invalid TFO state"

	::={tcpv4SegmentsFailedDequeueTfo 1}

tcpv4SegmentsFailedDequeueTfoMom	OBJECT-TYPE
	SYNTAX	 CounterBasedGauge64
	MAX-ACCESS read-only
	STATUS current
	DESCRIPTION "Segments that failed to dequeue due invalid TFO state"

	::={tcpv4SegmentsFailedDequeueTfo 2}

tcpv4SegmentsFailedDequeueTfoMax	OBJECT-TYPE
	SYNTAX	 CounterBasedGauge64
	MAX-ACCESS read-only
	STATUS current
	DESCRIPTION "Segments that failed to dequeue due invalid TFO state"

	::={tcpv4SegmentsFailedDequeueTfo 3}

tcpv4SegmentsFailedDequeueTfoLevelTable OBJECT-TYPE
	SYNTAX      SEQUENCE OF Tcpv4SegmentsFailedDequeueTfoLevelEntry
	MAX-ACCESS  not-accessible
	STATUS      current
	DESCRIPTION
	"Table for tcpv4SegmentsFailedDequeueTfo"
	::={tcpv4SegmentsFailedDequeueTfo 4}

tcpv4SegmentsFailedDequeueTfoLevelEntry OBJECT-TYPE
	SYNTAX      Tcpv4SegmentsFailedDequeueTfoLevelEntry
	MAX-ACCESS  not-accessible
	STATUS      current
	DESCRIPTION
	"Table entry for tcpv4SegmentsFailedDequeueTfo"
	INDEX { tcpv4SegmentsFailedDequeueTfoLevelName }
	::={tcpv4SegmentsFailedDequeueTfoLevelTable 1}

Tcpv4SegmentsFailedDequeueTfoLevelEntry ::=
	SEQUENCE {
		tcpv4SegmentsFailedDequeueTfoLevelName	DisplayString,
		tcpv4SegmentsFailedDequeueTfoLevelVal	Counter64,
		tcpv4SegmentsFailedDequeueTfoLevelMom	CounterBasedGauge64,
		tcpv4SegmentsFailedDequeueTfoLevelMax	CounterBasedGauge64
	}

tcpv4SegmentsFailedDequeueTfoLevelName OBJECT-TYPE
	SYNTAX      DisplayString
	MAX-ACCESS  not-accessible
	STATUS      current
	DESCRIPTION
	"Table entry display string for tcpv4SegmentsFailedDequeueTfo"
	::={tcpv4SegmentsFailedDequeueTfoLevelEntry 1}

tcpv4SegmentsFailedDequeueTfoLevelVal OBJECT-TYPE
	SYNTAX	 Counter64
	MAX-ACCESS  read-only
	STATUS      current
	DESCRIPTION
	"Table entry attribute for tcpv4SegmentsFailedDequeueTfo"
	::={tcpv4SegmentsFailedDequeueTfoLevelEntry 2}

tcpv4SegmentsFailedDequeueTfoLevelMom OBJECT-TYPE
	SYNTAX	 CounterBasedGauge64
	MAX-ACCESS  read-only
	STATUS      current
	DESCRIPTION
	"Table entry attribute for tcpv4SegmentsFailedDequeueTfo"
	::={tcpv4SegmentsFailedDequeueTfoLevelEntry 3}

tcpv4SegmentsFailedDequeueTfoLevelMax OBJECT-TYPE
	SYNTAX	 CounterBasedGauge64
	MAX-ACCESS  read-only
	STATUS      current
	DESCRIPTION
	"Table entry attribute for tcpv4SegmentsFailedDequeueTfo"
	::={tcpv4SegmentsFailedDequeueTfoLevelEntry 4}


icmpv4	OBJECT IDENTIFIER ::={sysdiag 49}

icmpv4Packets	OBJECT IDENTIFIER ::={icmpv4 1}

icmpv4PacketsVal	OBJECT-TYPE
	SYNTAX	 Counter64
	MAX-ACCESS read-only
	STATUS current
	DESCRIPTION "RX packets"

	::={icmpv4Packets 1}

icmpv4PacketsMom	OBJECT-TYPE
	SYNTAX	 CounterBasedGauge64
	MAX-ACCESS read-only
	STATUS current
	DESCRIPTION "RX packets"

	::={icmpv4Packets 2}

icmpv4PacketsMax	OBJECT-TYPE
	SYNTAX	 CounterBasedGauge64
	MAX-ACCESS read-only
	STATUS current
	DESCRIPTION "RX packets"

	::={icmpv4Packets 3}

icmpv4PacketsLevelTable OBJECT-TYPE
	SYNTAX      SEQUENCE OF Icmpv4PacketsLevelEntry
	MAX-ACCESS  not-accessible
	STATUS      current
	DESCRIPTION
	"Table for icmpv4Packets"
	::={icmpv4Packets 4}

icmpv4PacketsLevelEntry OBJECT-TYPE
	SYNTAX      Icmpv4PacketsLevelEntry
	MAX-ACCESS  not-accessible
	STATUS      current
	DESCRIPTION
	"Table entry for icmpv4Packets"
	INDEX { icmpv4PacketsLevelName }
	::={icmpv4PacketsLevelTable 1}

Icmpv4PacketsLevelEntry ::=
	SEQUENCE {
		icmpv4PacketsLevelName	DisplayString,
		icmpv4PacketsLevelVal	Counter64,
		icmpv4PacketsLevelMom	CounterBasedGauge64,
		icmpv4PacketsLevelMax	CounterBasedGauge64
	}

icmpv4PacketsLevelName OBJECT-TYPE
	SYNTAX      DisplayString
	MAX-ACCESS  not-accessible
	STATUS      current
	DESCRIPTION
	"Table entry display string for icmpv4Packets"
	::={icmpv4PacketsLevelEntry 1}

icmpv4PacketsLevelVal OBJECT-TYPE
	SYNTAX	 Counter64
	MAX-ACCESS  read-only
	STATUS      current
	DESCRIPTION
	"Table entry attribute for icmpv4Packets"
	::={icmpv4PacketsLevelEntry 2}

icmpv4PacketsLevelMom OBJECT-TYPE
	SYNTAX	 CounterBasedGauge64
	MAX-ACCESS  read-only
	STATUS      current
	DESCRIPTION
	"Table entry attribute for icmpv4Packets"
	::={icmpv4PacketsLevelEntry 3}

icmpv4PacketsLevelMax OBJECT-TYPE
	SYNTAX	 CounterBasedGauge64
	MAX-ACCESS  read-only
	STATUS      current
	DESCRIPTION
	"Table entry attribute for icmpv4Packets"
	::={icmpv4PacketsLevelEntry 4}


icmpv4Bytes	OBJECT IDENTIFIER ::={icmpv4 2}

icmpv4BytesVal	OBJECT-TYPE
	SYNTAX	 Counter64
	MAX-ACCESS read-only
	STATUS current
	DESCRIPTION "RX bytes"

	::={icmpv4Bytes 1}

icmpv4BytesMom	OBJECT-TYPE
	SYNTAX	 CounterBasedGauge64
	MAX-ACCESS read-only
	STATUS current
	DESCRIPTION "RX bytes"

	::={icmpv4Bytes 2}

icmpv4BytesMax	OBJECT-TYPE
	SYNTAX	 CounterBasedGauge64
	MAX-ACCESS read-only
	STATUS current
	DESCRIPTION "RX bytes"

	::={icmpv4Bytes 3}

icmpv4BytesLevelTable OBJECT-TYPE
	SYNTAX      SEQUENCE OF Icmpv4BytesLevelEntry
	MAX-ACCESS  not-accessible
	STATUS      current
	DESCRIPTION
	"Table for icmpv4Bytes"
	::={icmpv4Bytes 4}

icmpv4BytesLevelEntry OBJECT-TYPE
	SYNTAX      Icmpv4BytesLevelEntry
	MAX-ACCESS  not-accessible
	STATUS      current
	DESCRIPTION
	"Table entry for icmpv4Bytes"
	INDEX { icmpv4BytesLevelName }
	::={icmpv4BytesLevelTable 1}

Icmpv4BytesLevelEntry ::=
	SEQUENCE {
		icmpv4BytesLevelName	DisplayString,
		icmpv4BytesLevelVal	Counter64,
		icmpv4BytesLevelMom	CounterBasedGauge64,
		icmpv4BytesLevelMax	CounterBasedGauge64
	}

icmpv4BytesLevelName OBJECT-TYPE
	SYNTAX      DisplayString
	MAX-ACCESS  not-accessible
	STATUS      current
	DESCRIPTION
	"Table entry display string for icmpv4Bytes"
	::={icmpv4BytesLevelEntry 1}

icmpv4BytesLevelVal OBJECT-TYPE
	SYNTAX	 Counter64
	MAX-ACCESS  read-only
	STATUS      current
	DESCRIPTION
	"Table entry attribute for icmpv4Bytes"
	::={icmpv4BytesLevelEntry 2}

icmpv4BytesLevelMom OBJECT-TYPE
	SYNTAX	 CounterBasedGauge64
	MAX-ACCESS  read-only
	STATUS      current
	DESCRIPTION
	"Table entry attribute for icmpv4Bytes"
	::={icmpv4BytesLevelEntry 3}

icmpv4BytesLevelMax OBJECT-TYPE
	SYNTAX	 CounterBasedGauge64
	MAX-ACCESS  read-only
	STATUS      current
	DESCRIPTION
	"Table entry attribute for icmpv4Bytes"
	::={icmpv4BytesLevelEntry 4}


icmpv4RefusedRuleset	OBJECT IDENTIFIER ::={icmpv4 3}

icmpv4RefusedRulesetVal	OBJECT-TYPE
	SYNTAX	 Counter64
	MAX-ACCESS read-only
	STATUS current
	DESCRIPTION "Refused (ruleset)"

	::={icmpv4RefusedRuleset 1}

icmpv4RefusedRulesetMom	OBJECT-TYPE
	SYNTAX	 CounterBasedGauge64
	MAX-ACCESS read-only
	STATUS current
	DESCRIPTION "Refused (ruleset)"

	::={icmpv4RefusedRuleset 2}

icmpv4RefusedRulesetMax	OBJECT-TYPE
	SYNTAX	 CounterBasedGauge64
	MAX-ACCESS read-only
	STATUS current
	DESCRIPTION "Refused (ruleset)"

	::={icmpv4RefusedRuleset 3}

icmpv4RefusedRulesetLevelTable OBJECT-TYPE
	SYNTAX      SEQUENCE OF Icmpv4RefusedRulesetLevelEntry
	MAX-ACCESS  not-accessible
	STATUS      current
	DESCRIPTION
	"Table for icmpv4RefusedRuleset"
	::={icmpv4RefusedRuleset 4}

icmpv4RefusedRulesetLevelEntry OBJECT-TYPE
	SYNTAX      Icmpv4RefusedRulesetLevelEntry
	MAX-ACCESS  not-accessible
	STATUS      current
	DESCRIPTION
	"Table entry for icmpv4RefusedRuleset"
	INDEX { icmpv4RefusedRulesetLevelName }
	::={icmpv4RefusedRulesetLevelTable 1}

Icmpv4RefusedRulesetLevelEntry ::=
	SEQUENCE {
		icmpv4RefusedRulesetLevelName	DisplayString,
		icmpv4RefusedRulesetLevelVal	Counter64,
		icmpv4RefusedRulesetLevelMom	CounterBasedGauge64,
		icmpv4RefusedRulesetLevelMax	CounterBasedGauge64
	}

icmpv4RefusedRulesetLevelName OBJECT-TYPE
	SYNTAX      DisplayString
	MAX-ACCESS  not-accessible
	STATUS      current
	DESCRIPTION
	"Table entry display string for icmpv4RefusedRuleset"
	::={icmpv4RefusedRulesetLevelEntry 1}

icmpv4RefusedRulesetLevelVal OBJECT-TYPE
	SYNTAX	 Counter64
	MAX-ACCESS  read-only
	STATUS      current
	DESCRIPTION
	"Table entry attribute for icmpv4RefusedRuleset"
	::={icmpv4RefusedRulesetLevelEntry 2}

icmpv4RefusedRulesetLevelMom OBJECT-TYPE
	SYNTAX	 CounterBasedGauge64
	MAX-ACCESS  read-only
	STATUS      current
	DESCRIPTION
	"Table entry attribute for icmpv4RefusedRuleset"
	::={icmpv4RefusedRulesetLevelEntry 3}

icmpv4RefusedRulesetLevelMax OBJECT-TYPE
	SYNTAX	 CounterBasedGauge64
	MAX-ACCESS  read-only
	STATUS      current
	DESCRIPTION
	"Table entry attribute for icmpv4RefusedRuleset"
	::={icmpv4RefusedRulesetLevelEntry 4}


icmpv4RefusedShort	OBJECT IDENTIFIER ::={icmpv4 4}

icmpv4RefusedShortVal	OBJECT-TYPE
	SYNTAX	 Counter64
	MAX-ACCESS read-only
	STATUS current
	DESCRIPTION "Refused (short)"

	::={icmpv4RefusedShort 1}

icmpv4RefusedShortMom	OBJECT-TYPE
	SYNTAX	 CounterBasedGauge64
	MAX-ACCESS read-only
	STATUS current
	DESCRIPTION "Refused (short)"

	::={icmpv4RefusedShort 2}

icmpv4RefusedShortMax	OBJECT-TYPE
	SYNTAX	 CounterBasedGauge64
	MAX-ACCESS read-only
	STATUS current
	DESCRIPTION "Refused (short)"

	::={icmpv4RefusedShort 3}

icmpv4RefusedShortLevelTable OBJECT-TYPE
	SYNTAX      SEQUENCE OF Icmpv4RefusedShortLevelEntry
	MAX-ACCESS  not-accessible
	STATUS      current
	DESCRIPTION
	"Table for icmpv4RefusedShort"
	::={icmpv4RefusedShort 4}

icmpv4RefusedShortLevelEntry OBJECT-TYPE
	SYNTAX      Icmpv4RefusedShortLevelEntry
	MAX-ACCESS  not-accessible
	STATUS      current
	DESCRIPTION
	"Table entry for icmpv4RefusedShort"
	INDEX { icmpv4RefusedShortLevelName }
	::={icmpv4RefusedShortLevelTable 1}

Icmpv4RefusedShortLevelEntry ::=
	SEQUENCE {
		icmpv4RefusedShortLevelName	DisplayString,
		icmpv4RefusedShortLevelVal	Counter64,
		icmpv4RefusedShortLevelMom	CounterBasedGauge64,
		icmpv4RefusedShortLevelMax	CounterBasedGauge64
	}

icmpv4RefusedShortLevelName OBJECT-TYPE
	SYNTAX      DisplayString
	MAX-ACCESS  not-accessible
	STATUS      current
	DESCRIPTION
	"Table entry display string for icmpv4RefusedShort"
	::={icmpv4RefusedShortLevelEntry 1}

icmpv4RefusedShortLevelVal OBJECT-TYPE
	SYNTAX	 Counter64
	MAX-ACCESS  read-only
	STATUS      current
	DESCRIPTION
	"Table entry attribute for icmpv4RefusedShort"
	::={icmpv4RefusedShortLevelEntry 2}

icmpv4RefusedShortLevelMom OBJECT-TYPE
	SYNTAX	 CounterBasedGauge64
	MAX-ACCESS  read-only
	STATUS      current
	DESCRIPTION
	"Table entry attribute for icmpv4RefusedShort"
	::={icmpv4RefusedShortLevelEntry 3}

icmpv4RefusedShortLevelMax OBJECT-TYPE
	SYNTAX	 CounterBasedGauge64
	MAX-ACCESS  read-only
	STATUS      current
	DESCRIPTION
	"Table entry attribute for icmpv4RefusedShort"
	::={icmpv4RefusedShortLevelEntry 4}


icmpv6	OBJECT IDENTIFIER ::={sysdiag 50}

icmpv6Packets	OBJECT IDENTIFIER ::={icmpv6 1}

icmpv6PacketsVal	OBJECT-TYPE
	SYNTAX	 Counter64
	MAX-ACCESS read-only
	STATUS current
	DESCRIPTION "RX packets"

	::={icmpv6Packets 1}

icmpv6PacketsMom	OBJECT-TYPE
	SYNTAX	 CounterBasedGauge64
	MAX-ACCESS read-only
	STATUS current
	DESCRIPTION "RX packets"

	::={icmpv6Packets 2}

icmpv6PacketsMax	OBJECT-TYPE
	SYNTAX	 CounterBasedGauge64
	MAX-ACCESS read-only
	STATUS current
	DESCRIPTION "RX packets"

	::={icmpv6Packets 3}

icmpv6PacketsLevelTable OBJECT-TYPE
	SYNTAX      SEQUENCE OF Icmpv6PacketsLevelEntry
	MAX-ACCESS  not-accessible
	STATUS      current
	DESCRIPTION
	"Table for icmpv6Packets"
	::={icmpv6Packets 4}

icmpv6PacketsLevelEntry OBJECT-TYPE
	SYNTAX      Icmpv6PacketsLevelEntry
	MAX-ACCESS  not-accessible
	STATUS      current
	DESCRIPTION
	"Table entry for icmpv6Packets"
	INDEX { icmpv6PacketsLevelName }
	::={icmpv6PacketsLevelTable 1}

Icmpv6PacketsLevelEntry ::=
	SEQUENCE {
		icmpv6PacketsLevelName	DisplayString,
		icmpv6PacketsLevelVal	Counter64,
		icmpv6PacketsLevelMom	CounterBasedGauge64,
		icmpv6PacketsLevelMax	CounterBasedGauge64
	}

icmpv6PacketsLevelName OBJECT-TYPE
	SYNTAX      DisplayString
	MAX-ACCESS  not-accessible
	STATUS      current
	DESCRIPTION
	"Table entry display string for icmpv6Packets"
	::={icmpv6PacketsLevelEntry 1}

icmpv6PacketsLevelVal OBJECT-TYPE
	SYNTAX	 Counter64
	MAX-ACCESS  read-only
	STATUS      current
	DESCRIPTION
	"Table entry attribute for icmpv6Packets"
	::={icmpv6PacketsLevelEntry 2}

icmpv6PacketsLevelMom OBJECT-TYPE
	SYNTAX	 CounterBasedGauge64
	MAX-ACCESS  read-only
	STATUS      current
	DESCRIPTION
	"Table entry attribute for icmpv6Packets"
	::={icmpv6PacketsLevelEntry 3}

icmpv6PacketsLevelMax OBJECT-TYPE
	SYNTAX	 CounterBasedGauge64
	MAX-ACCESS  read-only
	STATUS      current
	DESCRIPTION
	"Table entry attribute for icmpv6Packets"
	::={icmpv6PacketsLevelEntry 4}


icmpv6Bytes	OBJECT IDENTIFIER ::={icmpv6 2}

icmpv6BytesVal	OBJECT-TYPE
	SYNTAX	 Counter64
	MAX-ACCESS read-only
	STATUS current
	DESCRIPTION "RX bytes"

	::={icmpv6Bytes 1}

icmpv6BytesMom	OBJECT-TYPE
	SYNTAX	 CounterBasedGauge64
	MAX-ACCESS read-only
	STATUS current
	DESCRIPTION "RX bytes"

	::={icmpv6Bytes 2}

icmpv6BytesMax	OBJECT-TYPE
	SYNTAX	 CounterBasedGauge64
	MAX-ACCESS read-only
	STATUS current
	DESCRIPTION "RX bytes"

	::={icmpv6Bytes 3}

icmpv6BytesLevelTable OBJECT-TYPE
	SYNTAX      SEQUENCE OF Icmpv6BytesLevelEntry
	MAX-ACCESS  not-accessible
	STATUS      current
	DESCRIPTION
	"Table for icmpv6Bytes"
	::={icmpv6Bytes 4}

icmpv6BytesLevelEntry OBJECT-TYPE
	SYNTAX      Icmpv6BytesLevelEntry
	MAX-ACCESS  not-accessible
	STATUS      current
	DESCRIPTION
	"Table entry for icmpv6Bytes"
	INDEX { icmpv6BytesLevelName }
	::={icmpv6BytesLevelTable 1}

Icmpv6BytesLevelEntry ::=
	SEQUENCE {
		icmpv6BytesLevelName	DisplayString,
		icmpv6BytesLevelVal	Counter64,
		icmpv6BytesLevelMom	CounterBasedGauge64,
		icmpv6BytesLevelMax	CounterBasedGauge64
	}

icmpv6BytesLevelName OBJECT-TYPE
	SYNTAX      DisplayString
	MAX-ACCESS  not-accessible
	STATUS      current
	DESCRIPTION
	"Table entry display string for icmpv6Bytes"
	::={icmpv6BytesLevelEntry 1}

icmpv6BytesLevelVal OBJECT-TYPE
	SYNTAX	 Counter64
	MAX-ACCESS  read-only
	STATUS      current
	DESCRIPTION
	"Table entry attribute for icmpv6Bytes"
	::={icmpv6BytesLevelEntry 2}

icmpv6BytesLevelMom OBJECT-TYPE
	SYNTAX	 CounterBasedGauge64
	MAX-ACCESS  read-only
	STATUS      current
	DESCRIPTION
	"Table entry attribute for icmpv6Bytes"
	::={icmpv6BytesLevelEntry 3}

icmpv6BytesLevelMax OBJECT-TYPE
	SYNTAX	 CounterBasedGauge64
	MAX-ACCESS  read-only
	STATUS      current
	DESCRIPTION
	"Table entry attribute for icmpv6Bytes"
	::={icmpv6BytesLevelEntry 4}


icmpv6RefusedRuleset	OBJECT IDENTIFIER ::={icmpv6 3}

icmpv6RefusedRulesetVal	OBJECT-TYPE
	SYNTAX	 Counter64
	MAX-ACCESS read-only
	STATUS current
	DESCRIPTION "Refused (ruleset)"

	::={icmpv6RefusedRuleset 1}

icmpv6RefusedRulesetMom	OBJECT-TYPE
	SYNTAX	 CounterBasedGauge64
	MAX-ACCESS read-only
	STATUS current
	DESCRIPTION "Refused (ruleset)"

	::={icmpv6RefusedRuleset 2}

icmpv6RefusedRulesetMax	OBJECT-TYPE
	SYNTAX	 CounterBasedGauge64
	MAX-ACCESS read-only
	STATUS current
	DESCRIPTION "Refused (ruleset)"

	::={icmpv6RefusedRuleset 3}

icmpv6RefusedRulesetLevelTable OBJECT-TYPE
	SYNTAX      SEQUENCE OF Icmpv6RefusedRulesetLevelEntry
	MAX-ACCESS  not-accessible
	STATUS      current
	DESCRIPTION
	"Table for icmpv6RefusedRuleset"
	::={icmpv6RefusedRuleset 4}

icmpv6RefusedRulesetLevelEntry OBJECT-TYPE
	SYNTAX      Icmpv6RefusedRulesetLevelEntry
	MAX-ACCESS  not-accessible
	STATUS      current
	DESCRIPTION
	"Table entry for icmpv6RefusedRuleset"
	INDEX { icmpv6RefusedRulesetLevelName }
	::={icmpv6RefusedRulesetLevelTable 1}

Icmpv6RefusedRulesetLevelEntry ::=
	SEQUENCE {
		icmpv6RefusedRulesetLevelName	DisplayString,
		icmpv6RefusedRulesetLevelVal	Counter64,
		icmpv6RefusedRulesetLevelMom	CounterBasedGauge64,
		icmpv6RefusedRulesetLevelMax	CounterBasedGauge64
	}

icmpv6RefusedRulesetLevelName OBJECT-TYPE
	SYNTAX      DisplayString
	MAX-ACCESS  not-accessible
	STATUS      current
	DESCRIPTION
	"Table entry display string for icmpv6RefusedRuleset"
	::={icmpv6RefusedRulesetLevelEntry 1}

icmpv6RefusedRulesetLevelVal OBJECT-TYPE
	SYNTAX	 Counter64
	MAX-ACCESS  read-only
	STATUS      current
	DESCRIPTION
	"Table entry attribute for icmpv6RefusedRuleset"
	::={icmpv6RefusedRulesetLevelEntry 2}

icmpv6RefusedRulesetLevelMom OBJECT-TYPE
	SYNTAX	 CounterBasedGauge64
	MAX-ACCESS  read-only
	STATUS      current
	DESCRIPTION
	"Table entry attribute for icmpv6RefusedRuleset"
	::={icmpv6RefusedRulesetLevelEntry 3}

icmpv6RefusedRulesetLevelMax OBJECT-TYPE
	SYNTAX	 CounterBasedGauge64
	MAX-ACCESS  read-only
	STATUS      current
	DESCRIPTION
	"Table entry attribute for icmpv6RefusedRuleset"
	::={icmpv6RefusedRulesetLevelEntry 4}


icmpv6RefusedShort	OBJECT IDENTIFIER ::={icmpv6 4}

icmpv6RefusedShortVal	OBJECT-TYPE
	SYNTAX	 Counter64
	MAX-ACCESS read-only
	STATUS current
	DESCRIPTION "Refused (short)"

	::={icmpv6RefusedShort 1}

icmpv6RefusedShortMom	OBJECT-TYPE
	SYNTAX	 CounterBasedGauge64
	MAX-ACCESS read-only
	STATUS current
	DESCRIPTION "Refused (short)"

	::={icmpv6RefusedShort 2}

icmpv6RefusedShortMax	OBJECT-TYPE
	SYNTAX	 CounterBasedGauge64
	MAX-ACCESS read-only
	STATUS current
	DESCRIPTION "Refused (short)"

	::={icmpv6RefusedShort 3}

icmpv6RefusedShortLevelTable OBJECT-TYPE
	SYNTAX      SEQUENCE OF Icmpv6RefusedShortLevelEntry
	MAX-ACCESS  not-accessible
	STATUS      current
	DESCRIPTION
	"Table for icmpv6RefusedShort"
	::={icmpv6RefusedShort 4}

icmpv6RefusedShortLevelEntry OBJECT-TYPE
	SYNTAX      Icmpv6RefusedShortLevelEntry
	MAX-ACCESS  not-accessible
	STATUS      current
	DESCRIPTION
	"Table entry for icmpv6RefusedShort"
	INDEX { icmpv6RefusedShortLevelName }
	::={icmpv6RefusedShortLevelTable 1}

Icmpv6RefusedShortLevelEntry ::=
	SEQUENCE {
		icmpv6RefusedShortLevelName	DisplayString,
		icmpv6RefusedShortLevelVal	Counter64,
		icmpv6RefusedShortLevelMom	CounterBasedGauge64,
		icmpv6RefusedShortLevelMax	CounterBasedGauge64
	}

icmpv6RefusedShortLevelName OBJECT-TYPE
	SYNTAX      DisplayString
	MAX-ACCESS  not-accessible
	STATUS      current
	DESCRIPTION
	"Table entry display string for icmpv6RefusedShort"
	::={icmpv6RefusedShortLevelEntry 1}

icmpv6RefusedShortLevelVal OBJECT-TYPE
	SYNTAX	 Counter64
	MAX-ACCESS  read-only
	STATUS      current
	DESCRIPTION
	"Table entry attribute for icmpv6RefusedShort"
	::={icmpv6RefusedShortLevelEntry 2}

icmpv6RefusedShortLevelMom OBJECT-TYPE
	SYNTAX	 CounterBasedGauge64
	MAX-ACCESS  read-only
	STATUS      current
	DESCRIPTION
	"Table entry attribute for icmpv6RefusedShort"
	::={icmpv6RefusedShortLevelEntry 3}

icmpv6RefusedShortLevelMax OBJECT-TYPE
	SYNTAX	 CounterBasedGauge64
	MAX-ACCESS  read-only
	STATUS      current
	DESCRIPTION
	"Table entry attribute for icmpv6RefusedShort"
	::={icmpv6RefusedShortLevelEntry 4}


udpv4	OBJECT IDENTIFIER ::={sysdiag 51}

udpv4Packets	OBJECT IDENTIFIER ::={udpv4 1}

udpv4PacketsVal	OBJECT-TYPE
	SYNTAX	 Counter64
	MAX-ACCESS read-only
	STATUS current
	DESCRIPTION "RX packets"

	::={udpv4Packets 1}

udpv4PacketsMom	OBJECT-TYPE
	SYNTAX	 CounterBasedGauge64
	MAX-ACCESS read-only
	STATUS current
	DESCRIPTION "RX packets"

	::={udpv4Packets 2}

udpv4PacketsMax	OBJECT-TYPE
	SYNTAX	 CounterBasedGauge64
	MAX-ACCESS read-only
	STATUS current
	DESCRIPTION "RX packets"

	::={udpv4Packets 3}

udpv4PacketsLevelTable OBJECT-TYPE
	SYNTAX      SEQUENCE OF Udpv4PacketsLevelEntry
	MAX-ACCESS  not-accessible
	STATUS      current
	DESCRIPTION
	"Table for udpv4Packets"
	::={udpv4Packets 4}

udpv4PacketsLevelEntry OBJECT-TYPE
	SYNTAX      Udpv4PacketsLevelEntry
	MAX-ACCESS  not-accessible
	STATUS      current
	DESCRIPTION
	"Table entry for udpv4Packets"
	INDEX { udpv4PacketsLevelName }
	::={udpv4PacketsLevelTable 1}

Udpv4PacketsLevelEntry ::=
	SEQUENCE {
		udpv4PacketsLevelName	DisplayString,
		udpv4PacketsLevelVal	Counter64,
		udpv4PacketsLevelMom	CounterBasedGauge64,
		udpv4PacketsLevelMax	CounterBasedGauge64
	}

udpv4PacketsLevelName OBJECT-TYPE
	SYNTAX      DisplayString
	MAX-ACCESS  not-accessible
	STATUS      current
	DESCRIPTION
	"Table entry display string for udpv4Packets"
	::={udpv4PacketsLevelEntry 1}

udpv4PacketsLevelVal OBJECT-TYPE
	SYNTAX	 Counter64
	MAX-ACCESS  read-only
	STATUS      current
	DESCRIPTION
	"Table entry attribute for udpv4Packets"
	::={udpv4PacketsLevelEntry 2}

udpv4PacketsLevelMom OBJECT-TYPE
	SYNTAX	 CounterBasedGauge64
	MAX-ACCESS  read-only
	STATUS      current
	DESCRIPTION
	"Table entry attribute for udpv4Packets"
	::={udpv4PacketsLevelEntry 3}

udpv4PacketsLevelMax OBJECT-TYPE
	SYNTAX	 CounterBasedGauge64
	MAX-ACCESS  read-only
	STATUS      current
	DESCRIPTION
	"Table entry attribute for udpv4Packets"
	::={udpv4PacketsLevelEntry 4}


udpv4Bytes	OBJECT IDENTIFIER ::={udpv4 2}

udpv4BytesVal	OBJECT-TYPE
	SYNTAX	 Counter64
	MAX-ACCESS read-only
	STATUS current
	DESCRIPTION "RX bytes"

	::={udpv4Bytes 1}

udpv4BytesMom	OBJECT-TYPE
	SYNTAX	 CounterBasedGauge64
	MAX-ACCESS read-only
	STATUS current
	DESCRIPTION "RX bytes"

	::={udpv4Bytes 2}

udpv4BytesMax	OBJECT-TYPE
	SYNTAX	 CounterBasedGauge64
	MAX-ACCESS read-only
	STATUS current
	DESCRIPTION "RX bytes"

	::={udpv4Bytes 3}

udpv4BytesLevelTable OBJECT-TYPE
	SYNTAX      SEQUENCE OF Udpv4BytesLevelEntry
	MAX-ACCESS  not-accessible
	STATUS      current
	DESCRIPTION
	"Table for udpv4Bytes"
	::={udpv4Bytes 4}

udpv4BytesLevelEntry OBJECT-TYPE
	SYNTAX      Udpv4BytesLevelEntry
	MAX-ACCESS  not-accessible
	STATUS      current
	DESCRIPTION
	"Table entry for udpv4Bytes"
	INDEX { udpv4BytesLevelName }
	::={udpv4BytesLevelTable 1}

Udpv4BytesLevelEntry ::=
	SEQUENCE {
		udpv4BytesLevelName	DisplayString,
		udpv4BytesLevelVal	Counter64,
		udpv4BytesLevelMom	CounterBasedGauge64,
		udpv4BytesLevelMax	CounterBasedGauge64
	}

udpv4BytesLevelName OBJECT-TYPE
	SYNTAX      DisplayString
	MAX-ACCESS  not-accessible
	STATUS      current
	DESCRIPTION
	"Table entry display string for udpv4Bytes"
	::={udpv4BytesLevelEntry 1}

udpv4BytesLevelVal OBJECT-TYPE
	SYNTAX	 Counter64
	MAX-ACCESS  read-only
	STATUS      current
	DESCRIPTION
	"Table entry attribute for udpv4Bytes"
	::={udpv4BytesLevelEntry 2}

udpv4BytesLevelMom OBJECT-TYPE
	SYNTAX	 CounterBasedGauge64
	MAX-ACCESS  read-only
	STATUS      current
	DESCRIPTION
	"Table entry attribute for udpv4Bytes"
	::={udpv4BytesLevelEntry 3}

udpv4BytesLevelMax OBJECT-TYPE
	SYNTAX	 CounterBasedGauge64
	MAX-ACCESS  read-only
	STATUS      current
	DESCRIPTION
	"Table entry attribute for udpv4Bytes"
	::={udpv4BytesLevelEntry 4}


udpv4RefusedRuleset	OBJECT IDENTIFIER ::={udpv4 3}

udpv4RefusedRulesetVal	OBJECT-TYPE
	SYNTAX	 Counter64
	MAX-ACCESS read-only
	STATUS current
	DESCRIPTION "Refused (ruleset)"

	::={udpv4RefusedRuleset 1}

udpv4RefusedRulesetMom	OBJECT-TYPE
	SYNTAX	 CounterBasedGauge64
	MAX-ACCESS read-only
	STATUS current
	DESCRIPTION "Refused (ruleset)"

	::={udpv4RefusedRuleset 2}

udpv4RefusedRulesetMax	OBJECT-TYPE
	SYNTAX	 CounterBasedGauge64
	MAX-ACCESS read-only
	STATUS current
	DESCRIPTION "Refused (ruleset)"

	::={udpv4RefusedRuleset 3}

udpv4RefusedRulesetLevelTable OBJECT-TYPE
	SYNTAX      SEQUENCE OF Udpv4RefusedRulesetLevelEntry
	MAX-ACCESS  not-accessible
	STATUS      current
	DESCRIPTION
	"Table for udpv4RefusedRuleset"
	::={udpv4RefusedRuleset 4}

udpv4RefusedRulesetLevelEntry OBJECT-TYPE
	SYNTAX      Udpv4RefusedRulesetLevelEntry
	MAX-ACCESS  not-accessible
	STATUS      current
	DESCRIPTION
	"Table entry for udpv4RefusedRuleset"
	INDEX { udpv4RefusedRulesetLevelName }
	::={udpv4RefusedRulesetLevelTable 1}

Udpv4RefusedRulesetLevelEntry ::=
	SEQUENCE {
		udpv4RefusedRulesetLevelName	DisplayString,
		udpv4RefusedRulesetLevelVal	Counter64,
		udpv4RefusedRulesetLevelMom	CounterBasedGauge64,
		udpv4RefusedRulesetLevelMax	CounterBasedGauge64
	}

udpv4RefusedRulesetLevelName OBJECT-TYPE
	SYNTAX      DisplayString
	MAX-ACCESS  not-accessible
	STATUS      current
	DESCRIPTION
	"Table entry display string for udpv4RefusedRuleset"
	::={udpv4RefusedRulesetLevelEntry 1}

udpv4RefusedRulesetLevelVal OBJECT-TYPE
	SYNTAX	 Counter64
	MAX-ACCESS  read-only
	STATUS      current
	DESCRIPTION
	"Table entry attribute for udpv4RefusedRuleset"
	::={udpv4RefusedRulesetLevelEntry 2}

udpv4RefusedRulesetLevelMom OBJECT-TYPE
	SYNTAX	 CounterBasedGauge64
	MAX-ACCESS  read-only
	STATUS      current
	DESCRIPTION
	"Table entry attribute for udpv4RefusedRuleset"
	::={udpv4RefusedRulesetLevelEntry 3}

udpv4RefusedRulesetLevelMax OBJECT-TYPE
	SYNTAX	 CounterBasedGauge64
	MAX-ACCESS  read-only
	STATUS      current
	DESCRIPTION
	"Table entry attribute for udpv4RefusedRuleset"
	::={udpv4RefusedRulesetLevelEntry 4}


udpv4RefusedShort	OBJECT IDENTIFIER ::={udpv4 4}

udpv4RefusedShortVal	OBJECT-TYPE
	SYNTAX	 Counter64
	MAX-ACCESS read-only
	STATUS current
	DESCRIPTION "Refused (short)"

	::={udpv4RefusedShort 1}

udpv4RefusedShortMom	OBJECT-TYPE
	SYNTAX	 CounterBasedGauge64
	MAX-ACCESS read-only
	STATUS current
	DESCRIPTION "Refused (short)"

	::={udpv4RefusedShort 2}

udpv4RefusedShortMax	OBJECT-TYPE
	SYNTAX	 CounterBasedGauge64
	MAX-ACCESS read-only
	STATUS current
	DESCRIPTION "Refused (short)"

	::={udpv4RefusedShort 3}

udpv4RefusedShortLevelTable OBJECT-TYPE
	SYNTAX      SEQUENCE OF Udpv4RefusedShortLevelEntry
	MAX-ACCESS  not-accessible
	STATUS      current
	DESCRIPTION
	"Table for udpv4RefusedShort"
	::={udpv4RefusedShort 4}

udpv4RefusedShortLevelEntry OBJECT-TYPE
	SYNTAX      Udpv4RefusedShortLevelEntry
	MAX-ACCESS  not-accessible
	STATUS      current
	DESCRIPTION
	"Table entry for udpv4RefusedShort"
	INDEX { udpv4RefusedShortLevelName }
	::={udpv4RefusedShortLevelTable 1}

Udpv4RefusedShortLevelEntry ::=
	SEQUENCE {
		udpv4RefusedShortLevelName	DisplayString,
		udpv4RefusedShortLevelVal	Counter64,
		udpv4RefusedShortLevelMom	CounterBasedGauge64,
		udpv4RefusedShortLevelMax	CounterBasedGauge64
	}

udpv4RefusedShortLevelName OBJECT-TYPE
	SYNTAX      DisplayString
	MAX-ACCESS  not-accessible
	STATUS      current
	DESCRIPTION
	"Table entry display string for udpv4RefusedShort"
	::={udpv4RefusedShortLevelEntry 1}

udpv4RefusedShortLevelVal OBJECT-TYPE
	SYNTAX	 Counter64
	MAX-ACCESS  read-only
	STATUS      current
	DESCRIPTION
	"Table entry attribute for udpv4RefusedShort"
	::={udpv4RefusedShortLevelEntry 2}

udpv4RefusedShortLevelMom OBJECT-TYPE
	SYNTAX	 CounterBasedGauge64
	MAX-ACCESS  read-only
	STATUS      current
	DESCRIPTION
	"Table entry attribute for udpv4RefusedShort"
	::={udpv4RefusedShortLevelEntry 3}

udpv4RefusedShortLevelMax OBJECT-TYPE
	SYNTAX	 CounterBasedGauge64
	MAX-ACCESS  read-only
	STATUS      current
	DESCRIPTION
	"Table entry attribute for udpv4RefusedShort"
	::={udpv4RefusedShortLevelEntry 4}


udpv6	OBJECT IDENTIFIER ::={sysdiag 52}

udpv6Packets	OBJECT IDENTIFIER ::={udpv6 1}

udpv6PacketsVal	OBJECT-TYPE
	SYNTAX	 Counter64
	MAX-ACCESS read-only
	STATUS current
	DESCRIPTION "RX packets"

	::={udpv6Packets 1}

udpv6PacketsMom	OBJECT-TYPE
	SYNTAX	 CounterBasedGauge64
	MAX-ACCESS read-only
	STATUS current
	DESCRIPTION "RX packets"

	::={udpv6Packets 2}

udpv6PacketsMax	OBJECT-TYPE
	SYNTAX	 CounterBasedGauge64
	MAX-ACCESS read-only
	STATUS current
	DESCRIPTION "RX packets"

	::={udpv6Packets 3}

udpv6PacketsLevelTable OBJECT-TYPE
	SYNTAX      SEQUENCE OF Udpv6PacketsLevelEntry
	MAX-ACCESS  not-accessible
	STATUS      current
	DESCRIPTION
	"Table for udpv6Packets"
	::={udpv6Packets 4}

udpv6PacketsLevelEntry OBJECT-TYPE
	SYNTAX      Udpv6PacketsLevelEntry
	MAX-ACCESS  not-accessible
	STATUS      current
	DESCRIPTION
	"Table entry for udpv6Packets"
	INDEX { udpv6PacketsLevelName }
	::={udpv6PacketsLevelTable 1}

Udpv6PacketsLevelEntry ::=
	SEQUENCE {
		udpv6PacketsLevelName	DisplayString,
		udpv6PacketsLevelVal	Counter64,
		udpv6PacketsLevelMom	CounterBasedGauge64,
		udpv6PacketsLevelMax	CounterBasedGauge64
	}

udpv6PacketsLevelName OBJECT-TYPE
	SYNTAX      DisplayString
	MAX-ACCESS  not-accessible
	STATUS      current
	DESCRIPTION
	"Table entry display string for udpv6Packets"
	::={udpv6PacketsLevelEntry 1}

udpv6PacketsLevelVal OBJECT-TYPE
	SYNTAX	 Counter64
	MAX-ACCESS  read-only
	STATUS      current
	DESCRIPTION
	"Table entry attribute for udpv6Packets"
	::={udpv6PacketsLevelEntry 2}

udpv6PacketsLevelMom OBJECT-TYPE
	SYNTAX	 CounterBasedGauge64
	MAX-ACCESS  read-only
	STATUS      current
	DESCRIPTION
	"Table entry attribute for udpv6Packets"
	::={udpv6PacketsLevelEntry 3}

udpv6PacketsLevelMax OBJECT-TYPE
	SYNTAX	 CounterBasedGauge64
	MAX-ACCESS  read-only
	STATUS      current
	DESCRIPTION
	"Table entry attribute for udpv6Packets"
	::={udpv6PacketsLevelEntry 4}


udpv6Bytes	OBJECT IDENTIFIER ::={udpv6 2}

udpv6BytesVal	OBJECT-TYPE
	SYNTAX	 Counter64
	MAX-ACCESS read-only
	STATUS current
	DESCRIPTION "RX bytes"

	::={udpv6Bytes 1}

udpv6BytesMom	OBJECT-TYPE
	SYNTAX	 CounterBasedGauge64
	MAX-ACCESS read-only
	STATUS current
	DESCRIPTION "RX bytes"

	::={udpv6Bytes 2}

udpv6BytesMax	OBJECT-TYPE
	SYNTAX	 CounterBasedGauge64
	MAX-ACCESS read-only
	STATUS current
	DESCRIPTION "RX bytes"

	::={udpv6Bytes 3}

udpv6BytesLevelTable OBJECT-TYPE
	SYNTAX      SEQUENCE OF Udpv6BytesLevelEntry
	MAX-ACCESS  not-accessible
	STATUS      current
	DESCRIPTION
	"Table for udpv6Bytes"
	::={udpv6Bytes 4}

udpv6BytesLevelEntry OBJECT-TYPE
	SYNTAX      Udpv6BytesLevelEntry
	MAX-ACCESS  not-accessible
	STATUS      current
	DESCRIPTION
	"Table entry for udpv6Bytes"
	INDEX { udpv6BytesLevelName }
	::={udpv6BytesLevelTable 1}

Udpv6BytesLevelEntry ::=
	SEQUENCE {
		udpv6BytesLevelName	DisplayString,
		udpv6BytesLevelVal	Counter64,
		udpv6BytesLevelMom	CounterBasedGauge64,
		udpv6BytesLevelMax	CounterBasedGauge64
	}

udpv6BytesLevelName OBJECT-TYPE
	SYNTAX      DisplayString
	MAX-ACCESS  not-accessible
	STATUS      current
	DESCRIPTION
	"Table entry display string for udpv6Bytes"
	::={udpv6BytesLevelEntry 1}

udpv6BytesLevelVal OBJECT-TYPE
	SYNTAX	 Counter64
	MAX-ACCESS  read-only
	STATUS      current
	DESCRIPTION
	"Table entry attribute for udpv6Bytes"
	::={udpv6BytesLevelEntry 2}

udpv6BytesLevelMom OBJECT-TYPE
	SYNTAX	 CounterBasedGauge64
	MAX-ACCESS  read-only
	STATUS      current
	DESCRIPTION
	"Table entry attribute for udpv6Bytes"
	::={udpv6BytesLevelEntry 3}

udpv6BytesLevelMax OBJECT-TYPE
	SYNTAX	 CounterBasedGauge64
	MAX-ACCESS  read-only
	STATUS      current
	DESCRIPTION
	"Table entry attribute for udpv6Bytes"
	::={udpv6BytesLevelEntry 4}


udpv6RefusedRuleset	OBJECT IDENTIFIER ::={udpv6 3}

udpv6RefusedRulesetVal	OBJECT-TYPE
	SYNTAX	 Counter64
	MAX-ACCESS read-only
	STATUS current
	DESCRIPTION "Refused (ruleset)"

	::={udpv6RefusedRuleset 1}

udpv6RefusedRulesetMom	OBJECT-TYPE
	SYNTAX	 CounterBasedGauge64
	MAX-ACCESS read-only
	STATUS current
	DESCRIPTION "Refused (ruleset)"

	::={udpv6RefusedRuleset 2}

udpv6RefusedRulesetMax	OBJECT-TYPE
	SYNTAX	 CounterBasedGauge64
	MAX-ACCESS read-only
	STATUS current
	DESCRIPTION "Refused (ruleset)"

	::={udpv6RefusedRuleset 3}

udpv6RefusedRulesetLevelTable OBJECT-TYPE
	SYNTAX      SEQUENCE OF Udpv6RefusedRulesetLevelEntry
	MAX-ACCESS  not-accessible
	STATUS      current
	DESCRIPTION
	"Table for udpv6RefusedRuleset"
	::={udpv6RefusedRuleset 4}

udpv6RefusedRulesetLevelEntry OBJECT-TYPE
	SYNTAX      Udpv6RefusedRulesetLevelEntry
	MAX-ACCESS  not-accessible
	STATUS      current
	DESCRIPTION
	"Table entry for udpv6RefusedRuleset"
	INDEX { udpv6RefusedRulesetLevelName }
	::={udpv6RefusedRulesetLevelTable 1}

Udpv6RefusedRulesetLevelEntry ::=
	SEQUENCE {
		udpv6RefusedRulesetLevelName	DisplayString,
		udpv6RefusedRulesetLevelVal	Counter64,
		udpv6RefusedRulesetLevelMom	CounterBasedGauge64,
		udpv6RefusedRulesetLevelMax	CounterBasedGauge64
	}

udpv6RefusedRulesetLevelName OBJECT-TYPE
	SYNTAX      DisplayString
	MAX-ACCESS  not-accessible
	STATUS      current
	DESCRIPTION
	"Table entry display string for udpv6RefusedRuleset"
	::={udpv6RefusedRulesetLevelEntry 1}

udpv6RefusedRulesetLevelVal OBJECT-TYPE
	SYNTAX	 Counter64
	MAX-ACCESS  read-only
	STATUS      current
	DESCRIPTION
	"Table entry attribute for udpv6RefusedRuleset"
	::={udpv6RefusedRulesetLevelEntry 2}

udpv6RefusedRulesetLevelMom OBJECT-TYPE
	SYNTAX	 CounterBasedGauge64
	MAX-ACCESS  read-only
	STATUS      current
	DESCRIPTION
	"Table entry attribute for udpv6RefusedRuleset"
	::={udpv6RefusedRulesetLevelEntry 3}

udpv6RefusedRulesetLevelMax OBJECT-TYPE
	SYNTAX	 CounterBasedGauge64
	MAX-ACCESS  read-only
	STATUS      current
	DESCRIPTION
	"Table entry attribute for udpv6RefusedRuleset"
	::={udpv6RefusedRulesetLevelEntry 4}


udpv6RefusedShort	OBJECT IDENTIFIER ::={udpv6 4}

udpv6RefusedShortVal	OBJECT-TYPE
	SYNTAX	 Counter64
	MAX-ACCESS read-only
	STATUS current
	DESCRIPTION "Refused (short)"

	::={udpv6RefusedShort 1}

udpv6RefusedShortMom	OBJECT-TYPE
	SYNTAX	 CounterBasedGauge64
	MAX-ACCESS read-only
	STATUS current
	DESCRIPTION "Refused (short)"

	::={udpv6RefusedShort 2}

udpv6RefusedShortMax	OBJECT-TYPE
	SYNTAX	 CounterBasedGauge64
	MAX-ACCESS read-only
	STATUS current
	DESCRIPTION "Refused (short)"

	::={udpv6RefusedShort 3}

udpv6RefusedShortLevelTable OBJECT-TYPE
	SYNTAX      SEQUENCE OF Udpv6RefusedShortLevelEntry
	MAX-ACCESS  not-accessible
	STATUS      current
	DESCRIPTION
	"Table for udpv6RefusedShort"
	::={udpv6RefusedShort 4}

udpv6RefusedShortLevelEntry OBJECT-TYPE
	SYNTAX      Udpv6RefusedShortLevelEntry
	MAX-ACCESS  not-accessible
	STATUS      current
	DESCRIPTION
	"Table entry for udpv6RefusedShort"
	INDEX { udpv6RefusedShortLevelName }
	::={udpv6RefusedShortLevelTable 1}

Udpv6RefusedShortLevelEntry ::=
	SEQUENCE {
		udpv6RefusedShortLevelName	DisplayString,
		udpv6RefusedShortLevelVal	Counter64,
		udpv6RefusedShortLevelMom	CounterBasedGauge64,
		udpv6RefusedShortLevelMax	CounterBasedGauge64
	}

udpv6RefusedShortLevelName OBJECT-TYPE
	SYNTAX      DisplayString
	MAX-ACCESS  not-accessible
	STATUS      current
	DESCRIPTION
	"Table entry display string for udpv6RefusedShort"
	::={udpv6RefusedShortLevelEntry 1}

udpv6RefusedShortLevelVal OBJECT-TYPE
	SYNTAX	 Counter64
	MAX-ACCESS  read-only
	STATUS      current
	DESCRIPTION
	"Table entry attribute for udpv6RefusedShort"
	::={udpv6RefusedShortLevelEntry 2}

udpv6RefusedShortLevelMom OBJECT-TYPE
	SYNTAX	 CounterBasedGauge64
	MAX-ACCESS  read-only
	STATUS      current
	DESCRIPTION
	"Table entry attribute for udpv6RefusedShort"
	::={udpv6RefusedShortLevelEntry 3}

udpv6RefusedShortLevelMax OBJECT-TYPE
	SYNTAX	 CounterBasedGauge64
	MAX-ACCESS  read-only
	STATUS      current
	DESCRIPTION
	"Table entry attribute for udpv6RefusedShort"
	::={udpv6RefusedShortLevelEntry 4}


tcpv6	OBJECT IDENTIFIER ::={sysdiag 127}

tcpv6Packets	OBJECT IDENTIFIER ::={tcpv6 1}

tcpv6PacketsVal	OBJECT-TYPE
	SYNTAX	 Counter64
	MAX-ACCESS read-only
	STATUS current
	DESCRIPTION "RX packets"

	::={tcpv6Packets 1}

tcpv6PacketsMom	OBJECT-TYPE
	SYNTAX	 CounterBasedGauge64
	MAX-ACCESS read-only
	STATUS current
	DESCRIPTION "RX packets"

	::={tcpv6Packets 2}

tcpv6PacketsMax	OBJECT-TYPE
	SYNTAX	 CounterBasedGauge64
	MAX-ACCESS read-only
	STATUS current
	DESCRIPTION "RX packets"

	::={tcpv6Packets 3}

tcpv6PacketsLevelTable OBJECT-TYPE
	SYNTAX      SEQUENCE OF Tcpv6PacketsLevelEntry
	MAX-ACCESS  not-accessible
	STATUS      current
	DESCRIPTION
	"Table for tcpv6Packets"
	::={tcpv6Packets 4}

tcpv6PacketsLevelEntry OBJECT-TYPE
	SYNTAX      Tcpv6PacketsLevelEntry
	MAX-ACCESS  not-accessible
	STATUS      current
	DESCRIPTION
	"Table entry for tcpv6Packets"
	INDEX { tcpv6PacketsLevelName }
	::={tcpv6PacketsLevelTable 1}

Tcpv6PacketsLevelEntry ::=
	SEQUENCE {
		tcpv6PacketsLevelName	DisplayString,
		tcpv6PacketsLevelVal	Counter64,
		tcpv6PacketsLevelMom	CounterBasedGauge64,
		tcpv6PacketsLevelMax	CounterBasedGauge64
	}

tcpv6PacketsLevelName OBJECT-TYPE
	SYNTAX      DisplayString
	MAX-ACCESS  not-accessible
	STATUS      current
	DESCRIPTION
	"Table entry display string for tcpv6Packets"
	::={tcpv6PacketsLevelEntry 1}

tcpv6PacketsLevelVal OBJECT-TYPE
	SYNTAX	 Counter64
	MAX-ACCESS  read-only
	STATUS      current
	DESCRIPTION
	"Table entry attribute for tcpv6Packets"
	::={tcpv6PacketsLevelEntry 2}

tcpv6PacketsLevelMom OBJECT-TYPE
	SYNTAX	 CounterBasedGauge64
	MAX-ACCESS  read-only
	STATUS      current
	DESCRIPTION
	"Table entry attribute for tcpv6Packets"
	::={tcpv6PacketsLevelEntry 3}

tcpv6PacketsLevelMax OBJECT-TYPE
	SYNTAX	 CounterBasedGauge64
	MAX-ACCESS  read-only
	STATUS      current
	DESCRIPTION
	"Table entry attribute for tcpv6Packets"
	::={tcpv6PacketsLevelEntry 4}


tcpv6Bytes	OBJECT IDENTIFIER ::={tcpv6 2}

tcpv6BytesVal	OBJECT-TYPE
	SYNTAX	 Counter64
	MAX-ACCESS read-only
	STATUS current
	DESCRIPTION "RX bytes"

	::={tcpv6Bytes 1}

tcpv6BytesMom	OBJECT-TYPE
	SYNTAX	 CounterBasedGauge64
	MAX-ACCESS read-only
	STATUS current
	DESCRIPTION "RX bytes"

	::={tcpv6Bytes 2}

tcpv6BytesMax	OBJECT-TYPE
	SYNTAX	 CounterBasedGauge64
	MAX-ACCESS read-only
	STATUS current
	DESCRIPTION "RX bytes"

	::={tcpv6Bytes 3}

tcpv6BytesLevelTable OBJECT-TYPE
	SYNTAX      SEQUENCE OF Tcpv6BytesLevelEntry
	MAX-ACCESS  not-accessible
	STATUS      current
	DESCRIPTION
	"Table for tcpv6Bytes"
	::={tcpv6Bytes 4}

tcpv6BytesLevelEntry OBJECT-TYPE
	SYNTAX      Tcpv6BytesLevelEntry
	MAX-ACCESS  not-accessible
	STATUS      current
	DESCRIPTION
	"Table entry for tcpv6Bytes"
	INDEX { tcpv6BytesLevelName }
	::={tcpv6BytesLevelTable 1}

Tcpv6BytesLevelEntry ::=
	SEQUENCE {
		tcpv6BytesLevelName	DisplayString,
		tcpv6BytesLevelVal	Counter64,
		tcpv6BytesLevelMom	CounterBasedGauge64,
		tcpv6BytesLevelMax	CounterBasedGauge64
	}

tcpv6BytesLevelName OBJECT-TYPE
	SYNTAX      DisplayString
	MAX-ACCESS  not-accessible
	STATUS      current
	DESCRIPTION
	"Table entry display string for tcpv6Bytes"
	::={tcpv6BytesLevelEntry 1}

tcpv6BytesLevelVal OBJECT-TYPE
	SYNTAX	 Counter64
	MAX-ACCESS  read-only
	STATUS      current
	DESCRIPTION
	"Table entry attribute for tcpv6Bytes"
	::={tcpv6BytesLevelEntry 2}

tcpv6BytesLevelMom OBJECT-TYPE
	SYNTAX	 CounterBasedGauge64
	MAX-ACCESS  read-only
	STATUS      current
	DESCRIPTION
	"Table entry attribute for tcpv6Bytes"
	::={tcpv6BytesLevelEntry 3}

tcpv6BytesLevelMax OBJECT-TYPE
	SYNTAX	 CounterBasedGauge64
	MAX-ACCESS  read-only
	STATUS      current
	DESCRIPTION
	"Table entry attribute for tcpv6Bytes"
	::={tcpv6BytesLevelEntry 4}


tcpv6CreateAttempts	OBJECT IDENTIFIER ::={tcpv6 4}

tcpv6CreateAttemptsVal	OBJECT-TYPE
	SYNTAX	 Counter64
	MAX-ACCESS read-only
	STATUS current
	DESCRIPTION "Connection create attempts"

	::={tcpv6CreateAttempts 1}

tcpv6CreateAttemptsMom	OBJECT-TYPE
	SYNTAX	 CounterBasedGauge64
	MAX-ACCESS read-only
	STATUS current
	DESCRIPTION "Connection create attempts"

	::={tcpv6CreateAttempts 2}

tcpv6CreateAttemptsMax	OBJECT-TYPE
	SYNTAX	 CounterBasedGauge64
	MAX-ACCESS read-only
	STATUS current
	DESCRIPTION "Connection create attempts"

	::={tcpv6CreateAttempts 3}

tcpv6CreateAttemptsLevelTable OBJECT-TYPE
	SYNTAX      SEQUENCE OF Tcpv6CreateAttemptsLevelEntry
	MAX-ACCESS  not-accessible
	STATUS      current
	DESCRIPTION
	"Table for tcpv6CreateAttempts"
	::={tcpv6CreateAttempts 4}

tcpv6CreateAttemptsLevelEntry OBJECT-TYPE
	SYNTAX      Tcpv6CreateAttemptsLevelEntry
	MAX-ACCESS  not-accessible
	STATUS      current
	DESCRIPTION
	"Table entry for tcpv6CreateAttempts"
	INDEX { tcpv6CreateAttemptsLevelName }
	::={tcpv6CreateAttemptsLevelTable 1}

Tcpv6CreateAttemptsLevelEntry ::=
	SEQUENCE {
		tcpv6CreateAttemptsLevelName	DisplayString,
		tcpv6CreateAttemptsLevelVal	Counter64,
		tcpv6CreateAttemptsLevelMom	CounterBasedGauge64,
		tcpv6CreateAttemptsLevelMax	CounterBasedGauge64
	}

tcpv6CreateAttemptsLevelName OBJECT-TYPE
	SYNTAX      DisplayString
	MAX-ACCESS  not-accessible
	STATUS      current
	DESCRIPTION
	"Table entry display string for tcpv6CreateAttempts"
	::={tcpv6CreateAttemptsLevelEntry 1}

tcpv6CreateAttemptsLevelVal OBJECT-TYPE
	SYNTAX	 Counter64
	MAX-ACCESS  read-only
	STATUS      current
	DESCRIPTION
	"Table entry attribute for tcpv6CreateAttempts"
	::={tcpv6CreateAttemptsLevelEntry 2}

tcpv6CreateAttemptsLevelMom OBJECT-TYPE
	SYNTAX	 CounterBasedGauge64
	MAX-ACCESS  read-only
	STATUS      current
	DESCRIPTION
	"Table entry attribute for tcpv6CreateAttempts"
	::={tcpv6CreateAttemptsLevelEntry 3}

tcpv6CreateAttemptsLevelMax OBJECT-TYPE
	SYNTAX	 CounterBasedGauge64
	MAX-ACCESS  read-only
	STATUS      current
	DESCRIPTION
	"Table entry attribute for tcpv6CreateAttempts"
	::={tcpv6CreateAttemptsLevelEntry 4}


tcpv6Created	OBJECT IDENTIFIER ::={tcpv6 5}

tcpv6CreatedVal	OBJECT-TYPE
	SYNTAX	 Counter64
	MAX-ACCESS read-only
	STATUS current
	DESCRIPTION "Connections created"

	::={tcpv6Created 1}

tcpv6CreatedMom	OBJECT-TYPE
	SYNTAX	 CounterBasedGauge64
	MAX-ACCESS read-only
	STATUS current
	DESCRIPTION "Connections created"

	::={tcpv6Created 2}

tcpv6CreatedMax	OBJECT-TYPE
	SYNTAX	 CounterBasedGauge64
	MAX-ACCESS read-only
	STATUS current
	DESCRIPTION "Connections created"

	::={tcpv6Created 3}

tcpv6CreatedLevelTable OBJECT-TYPE
	SYNTAX      SEQUENCE OF Tcpv6CreatedLevelEntry
	MAX-ACCESS  not-accessible
	STATUS      current
	DESCRIPTION
	"Table for tcpv6Created"
	::={tcpv6Created 4}

tcpv6CreatedLevelEntry OBJECT-TYPE
	SYNTAX      Tcpv6CreatedLevelEntry
	MAX-ACCESS  not-accessible
	STATUS      current
	DESCRIPTION
	"Table entry for tcpv6Created"
	INDEX { tcpv6CreatedLevelName }
	::={tcpv6CreatedLevelTable 1}

Tcpv6CreatedLevelEntry ::=
	SEQUENCE {
		tcpv6CreatedLevelName	DisplayString,
		tcpv6CreatedLevelVal	Counter64,
		tcpv6CreatedLevelMom	CounterBasedGauge64,
		tcpv6CreatedLevelMax	CounterBasedGauge64
	}

tcpv6CreatedLevelName OBJECT-TYPE
	SYNTAX      DisplayString
	MAX-ACCESS  not-accessible
	STATUS      current
	DESCRIPTION
	"Table entry display string for tcpv6Created"
	::={tcpv6CreatedLevelEntry 1}

tcpv6CreatedLevelVal OBJECT-TYPE
	SYNTAX	 Counter64
	MAX-ACCESS  read-only
	STATUS      current
	DESCRIPTION
	"Table entry attribute for tcpv6Created"
	::={tcpv6CreatedLevelEntry 2}

tcpv6CreatedLevelMom OBJECT-TYPE
	SYNTAX	 CounterBasedGauge64
	MAX-ACCESS  read-only
	STATUS      current
	DESCRIPTION
	"Table entry attribute for tcpv6Created"
	::={tcpv6CreatedLevelEntry 3}

tcpv6CreatedLevelMax OBJECT-TYPE
	SYNTAX	 CounterBasedGauge64
	MAX-ACCESS  read-only
	STATUS      current
	DESCRIPTION
	"Table entry attribute for tcpv6Created"
	::={tcpv6CreatedLevelEntry 4}


tcpv6RefusedRuleset	OBJECT IDENTIFIER ::={tcpv6 6}

tcpv6RefusedRulesetVal	OBJECT-TYPE
	SYNTAX	 Counter64
	MAX-ACCESS read-only
	STATUS current
	DESCRIPTION "Refused (ruleset)"

	::={tcpv6RefusedRuleset 1}

tcpv6RefusedRulesetMom	OBJECT-TYPE
	SYNTAX	 CounterBasedGauge64
	MAX-ACCESS read-only
	STATUS current
	DESCRIPTION "Refused (ruleset)"

	::={tcpv6RefusedRuleset 2}

tcpv6RefusedRulesetMax	OBJECT-TYPE
	SYNTAX	 CounterBasedGauge64
	MAX-ACCESS read-only
	STATUS current
	DESCRIPTION "Refused (ruleset)"

	::={tcpv6RefusedRuleset 3}

tcpv6RefusedRulesetLevelTable OBJECT-TYPE
	SYNTAX      SEQUENCE OF Tcpv6RefusedRulesetLevelEntry
	MAX-ACCESS  not-accessible
	STATUS      current
	DESCRIPTION
	"Table for tcpv6RefusedRuleset"
	::={tcpv6RefusedRuleset 4}

tcpv6RefusedRulesetLevelEntry OBJECT-TYPE
	SYNTAX      Tcpv6RefusedRulesetLevelEntry
	MAX-ACCESS  not-accessible
	STATUS      current
	DESCRIPTION
	"Table entry for tcpv6RefusedRuleset"
	INDEX { tcpv6RefusedRulesetLevelName }
	::={tcpv6RefusedRulesetLevelTable 1}

Tcpv6RefusedRulesetLevelEntry ::=
	SEQUENCE {
		tcpv6RefusedRulesetLevelName	DisplayString,
		tcpv6RefusedRulesetLevelVal	Counter64,
		tcpv6RefusedRulesetLevelMom	CounterBasedGauge64,
		tcpv6RefusedRulesetLevelMax	CounterBasedGauge64
	}

tcpv6RefusedRulesetLevelName OBJECT-TYPE
	SYNTAX      DisplayString
	MAX-ACCESS  not-accessible
	STATUS      current
	DESCRIPTION
	"Table entry display string for tcpv6RefusedRuleset"
	::={tcpv6RefusedRulesetLevelEntry 1}

tcpv6RefusedRulesetLevelVal OBJECT-TYPE
	SYNTAX	 Counter64
	MAX-ACCESS  read-only
	STATUS      current
	DESCRIPTION
	"Table entry attribute for tcpv6RefusedRuleset"
	::={tcpv6RefusedRulesetLevelEntry 2}

tcpv6RefusedRulesetLevelMom OBJECT-TYPE
	SYNTAX	 CounterBasedGauge64
	MAX-ACCESS  read-only
	STATUS      current
	DESCRIPTION
	"Table entry attribute for tcpv6RefusedRuleset"
	::={tcpv6RefusedRulesetLevelEntry 3}

tcpv6RefusedRulesetLevelMax OBJECT-TYPE
	SYNTAX	 CounterBasedGauge64
	MAX-ACCESS  read-only
	STATUS      current
	DESCRIPTION
	"Table entry attribute for tcpv6RefusedRuleset"
	::={tcpv6RefusedRulesetLevelEntry 4}


tcpv6RefusedShort	OBJECT IDENTIFIER ::={tcpv6 7}

tcpv6RefusedShortVal	OBJECT-TYPE
	SYNTAX	 Counter64
	MAX-ACCESS read-only
	STATUS current
	DESCRIPTION "Refused (short)"

	::={tcpv6RefusedShort 1}

tcpv6RefusedShortMom	OBJECT-TYPE
	SYNTAX	 CounterBasedGauge64
	MAX-ACCESS read-only
	STATUS current
	DESCRIPTION "Refused (short)"

	::={tcpv6RefusedShort 2}

tcpv6RefusedShortMax	OBJECT-TYPE
	SYNTAX	 CounterBasedGauge64
	MAX-ACCESS read-only
	STATUS current
	DESCRIPTION "Refused (short)"

	::={tcpv6RefusedShort 3}

tcpv6RefusedShortLevelTable OBJECT-TYPE
	SYNTAX      SEQUENCE OF Tcpv6RefusedShortLevelEntry
	MAX-ACCESS  not-accessible
	STATUS      current
	DESCRIPTION
	"Table for tcpv6RefusedShort"
	::={tcpv6RefusedShort 4}

tcpv6RefusedShortLevelEntry OBJECT-TYPE
	SYNTAX      Tcpv6RefusedShortLevelEntry
	MAX-ACCESS  not-accessible
	STATUS      current
	DESCRIPTION
	"Table entry for tcpv6RefusedShort"
	INDEX { tcpv6RefusedShortLevelName }
	::={tcpv6RefusedShortLevelTable 1}

Tcpv6RefusedShortLevelEntry ::=
	SEQUENCE {
		tcpv6RefusedShortLevelName	DisplayString,
		tcpv6RefusedShortLevelVal	Counter64,
		tcpv6RefusedShortLevelMom	CounterBasedGauge64,
		tcpv6RefusedShortLevelMax	CounterBasedGauge64
	}

tcpv6RefusedShortLevelName OBJECT-TYPE
	SYNTAX      DisplayString
	MAX-ACCESS  not-accessible
	STATUS      current
	DESCRIPTION
	"Table entry display string for tcpv6RefusedShort"
	::={tcpv6RefusedShortLevelEntry 1}

tcpv6RefusedShortLevelVal OBJECT-TYPE
	SYNTAX	 Counter64
	MAX-ACCESS  read-only
	STATUS      current
	DESCRIPTION
	"Table entry attribute for tcpv6RefusedShort"
	::={tcpv6RefusedShortLevelEntry 2}

tcpv6RefusedShortLevelMom OBJECT-TYPE
	SYNTAX	 CounterBasedGauge64
	MAX-ACCESS  read-only
	STATUS      current
	DESCRIPTION
	"Table entry attribute for tcpv6RefusedShort"
	::={tcpv6RefusedShortLevelEntry 3}

tcpv6RefusedShortLevelMax OBJECT-TYPE
	SYNTAX	 CounterBasedGauge64
	MAX-ACCESS  read-only
	STATUS      current
	DESCRIPTION
	"Table entry attribute for tcpv6RefusedShort"
	::={tcpv6RefusedShortLevelEntry 4}


tcpv6RefusedBroadcast	OBJECT IDENTIFIER ::={tcpv6 8}

tcpv6RefusedBroadcastVal	OBJECT-TYPE
	SYNTAX	 Counter64
	MAX-ACCESS read-only
	STATUS current
	DESCRIPTION "Refused (broadcast)"

	::={tcpv6RefusedBroadcast 1}

tcpv6RefusedBroadcastMom	OBJECT-TYPE
	SYNTAX	 CounterBasedGauge64
	MAX-ACCESS read-only
	STATUS current
	DESCRIPTION "Refused (broadcast)"

	::={tcpv6RefusedBroadcast 2}

tcpv6RefusedBroadcastMax	OBJECT-TYPE
	SYNTAX	 CounterBasedGauge64
	MAX-ACCESS read-only
	STATUS current
	DESCRIPTION "Refused (broadcast)"

	::={tcpv6RefusedBroadcast 3}

tcpv6RefusedBroadcastLevelTable OBJECT-TYPE
	SYNTAX      SEQUENCE OF Tcpv6RefusedBroadcastLevelEntry
	MAX-ACCESS  not-accessible
	STATUS      current
	DESCRIPTION
	"Table for tcpv6RefusedBroadcast"
	::={tcpv6RefusedBroadcast 4}

tcpv6RefusedBroadcastLevelEntry OBJECT-TYPE
	SYNTAX      Tcpv6RefusedBroadcastLevelEntry
	MAX-ACCESS  not-accessible
	STATUS      current
	DESCRIPTION
	"Table entry for tcpv6RefusedBroadcast"
	INDEX { tcpv6RefusedBroadcastLevelName }
	::={tcpv6RefusedBroadcastLevelTable 1}

Tcpv6RefusedBroadcastLevelEntry ::=
	SEQUENCE {
		tcpv6RefusedBroadcastLevelName	DisplayString,
		tcpv6RefusedBroadcastLevelVal	Counter64,
		tcpv6RefusedBroadcastLevelMom	CounterBasedGauge64,
		tcpv6RefusedBroadcastLevelMax	CounterBasedGauge64
	}

tcpv6RefusedBroadcastLevelName OBJECT-TYPE
	SYNTAX      DisplayString
	MAX-ACCESS  not-accessible
	STATUS      current
	DESCRIPTION
	"Table entry display string for tcpv6RefusedBroadcast"
	::={tcpv6RefusedBroadcastLevelEntry 1}

tcpv6RefusedBroadcastLevelVal OBJECT-TYPE
	SYNTAX	 Counter64
	MAX-ACCESS  read-only
	STATUS      current
	DESCRIPTION
	"Table entry attribute for tcpv6RefusedBroadcast"
	::={tcpv6RefusedBroadcastLevelEntry 2}

tcpv6RefusedBroadcastLevelMom OBJECT-TYPE
	SYNTAX	 CounterBasedGauge64
	MAX-ACCESS  read-only
	STATUS      current
	DESCRIPTION
	"Table entry attribute for tcpv6RefusedBroadcast"
	::={tcpv6RefusedBroadcastLevelEntry 3}

tcpv6RefusedBroadcastLevelMax OBJECT-TYPE
	SYNTAX	 CounterBasedGauge64
	MAX-ACCESS  read-only
	STATUS      current
	DESCRIPTION
	"Table entry attribute for tcpv6RefusedBroadcast"
	::={tcpv6RefusedBroadcastLevelEntry 4}


tcpv6RefusedOffset	OBJECT IDENTIFIER ::={tcpv6 9}

tcpv6RefusedOffsetVal	OBJECT-TYPE
	SYNTAX	 Counter64
	MAX-ACCESS read-only
	STATUS current
	DESCRIPTION "Refused (offset)"

	::={tcpv6RefusedOffset 1}

tcpv6RefusedOffsetMom	OBJECT-TYPE
	SYNTAX	 CounterBasedGauge64
	MAX-ACCESS read-only
	STATUS current
	DESCRIPTION "Refused (offset)"

	::={tcpv6RefusedOffset 2}

tcpv6RefusedOffsetMax	OBJECT-TYPE
	SYNTAX	 CounterBasedGauge64
	MAX-ACCESS read-only
	STATUS current
	DESCRIPTION "Refused (offset)"

	::={tcpv6RefusedOffset 3}

tcpv6RefusedOffsetLevelTable OBJECT-TYPE
	SYNTAX      SEQUENCE OF Tcpv6RefusedOffsetLevelEntry
	MAX-ACCESS  not-accessible
	STATUS      current
	DESCRIPTION
	"Table for tcpv6RefusedOffset"
	::={tcpv6RefusedOffset 4}

tcpv6RefusedOffsetLevelEntry OBJECT-TYPE
	SYNTAX      Tcpv6RefusedOffsetLevelEntry
	MAX-ACCESS  not-accessible
	STATUS      current
	DESCRIPTION
	"Table entry for tcpv6RefusedOffset"
	INDEX { tcpv6RefusedOffsetLevelName }
	::={tcpv6RefusedOffsetLevelTable 1}

Tcpv6RefusedOffsetLevelEntry ::=
	SEQUENCE {
		tcpv6RefusedOffsetLevelName	DisplayString,
		tcpv6RefusedOffsetLevelVal	Counter64,
		tcpv6RefusedOffsetLevelMom	CounterBasedGauge64,
		tcpv6RefusedOffsetLevelMax	CounterBasedGauge64
	}

tcpv6RefusedOffsetLevelName OBJECT-TYPE
	SYNTAX      DisplayString
	MAX-ACCESS  not-accessible
	STATUS      current
	DESCRIPTION
	"Table entry display string for tcpv6RefusedOffset"
	::={tcpv6RefusedOffsetLevelEntry 1}

tcpv6RefusedOffsetLevelVal OBJECT-TYPE
	SYNTAX	 Counter64
	MAX-ACCESS  read-only
	STATUS      current
	DESCRIPTION
	"Table entry attribute for tcpv6RefusedOffset"
	::={tcpv6RefusedOffsetLevelEntry 2}

tcpv6RefusedOffsetLevelMom OBJECT-TYPE
	SYNTAX	 CounterBasedGauge64
	MAX-ACCESS  read-only
	STATUS      current
	DESCRIPTION
	"Table entry attribute for tcpv6RefusedOffset"
	::={tcpv6RefusedOffsetLevelEntry 3}

tcpv6RefusedOffsetLevelMax OBJECT-TYPE
	SYNTAX	 CounterBasedGauge64
	MAX-ACCESS  read-only
	STATUS      current
	DESCRIPTION
	"Table entry attribute for tcpv6RefusedOffset"
	::={tcpv6RefusedOffsetLevelEntry 4}


tcpv6Rejected	OBJECT IDENTIFIER ::={tcpv6 10}

tcpv6RejectedVal	OBJECT-TYPE
	SYNTAX	 Counter64
	MAX-ACCESS read-only
	STATUS current
	DESCRIPTION "Rejected packets"

	::={tcpv6Rejected 1}

tcpv6RejectedMom	OBJECT-TYPE
	SYNTAX	 CounterBasedGauge64
	MAX-ACCESS read-only
	STATUS current
	DESCRIPTION "Rejected packets"

	::={tcpv6Rejected 2}

tcpv6RejectedMax	OBJECT-TYPE
	SYNTAX	 CounterBasedGauge64
	MAX-ACCESS read-only
	STATUS current
	DESCRIPTION "Rejected packets"

	::={tcpv6Rejected 3}

tcpv6RejectedLevelTable OBJECT-TYPE
	SYNTAX      SEQUENCE OF Tcpv6RejectedLevelEntry
	MAX-ACCESS  not-accessible
	STATUS      current
	DESCRIPTION
	"Table for tcpv6Rejected"
	::={tcpv6Rejected 4}

tcpv6RejectedLevelEntry OBJECT-TYPE
	SYNTAX      Tcpv6RejectedLevelEntry
	MAX-ACCESS  not-accessible
	STATUS      current
	DESCRIPTION
	"Table entry for tcpv6Rejected"
	INDEX { tcpv6RejectedLevelName }
	::={tcpv6RejectedLevelTable 1}

Tcpv6RejectedLevelEntry ::=
	SEQUENCE {
		tcpv6RejectedLevelName	DisplayString,
		tcpv6RejectedLevelVal	Counter64,
		tcpv6RejectedLevelMom	CounterBasedGauge64,
		tcpv6RejectedLevelMax	CounterBasedGauge64
	}

tcpv6RejectedLevelName OBJECT-TYPE
	SYNTAX      DisplayString
	MAX-ACCESS  not-accessible
	STATUS      current
	DESCRIPTION
	"Table entry display string for tcpv6Rejected"
	::={tcpv6RejectedLevelEntry 1}

tcpv6RejectedLevelVal OBJECT-TYPE
	SYNTAX	 Counter64
	MAX-ACCESS  read-only
	STATUS      current
	DESCRIPTION
	"Table entry attribute for tcpv6Rejected"
	::={tcpv6RejectedLevelEntry 2}

tcpv6RejectedLevelMom OBJECT-TYPE
	SYNTAX	 CounterBasedGauge64
	MAX-ACCESS  read-only
	STATUS      current
	DESCRIPTION
	"Table entry attribute for tcpv6Rejected"
	::={tcpv6RejectedLevelEntry 3}

tcpv6RejectedLevelMax OBJECT-TYPE
	SYNTAX	 CounterBasedGauge64
	MAX-ACCESS  read-only
	STATUS      current
	DESCRIPTION
	"Table entry attribute for tcpv6Rejected"
	::={tcpv6RejectedLevelEntry 4}


tcpv6Lostsync	OBJECT IDENTIFIER ::={tcpv6 12}

tcpv6LostsyncVal	OBJECT-TYPE
	SYNTAX	 CounterBasedGauge64
	MAX-ACCESS read-only
	STATUS current
	DESCRIPTION "Out-of-sync connections"

	::={tcpv6Lostsync 1}

tcpv6LostsyncMax	OBJECT-TYPE
	SYNTAX	 CounterBasedGauge64
	MAX-ACCESS read-only
	STATUS current
	DESCRIPTION "Out-of-sync connections"

	::={tcpv6Lostsync 3}

tcpv6LostsyncLevelTable OBJECT-TYPE
	SYNTAX      SEQUENCE OF Tcpv6LostsyncLevelEntry
	MAX-ACCESS  not-accessible
	STATUS      current
	DESCRIPTION
	"Table for tcpv6Lostsync"
	::={tcpv6Lostsync 4}

tcpv6LostsyncLevelEntry OBJECT-TYPE
	SYNTAX      Tcpv6LostsyncLevelEntry
	MAX-ACCESS  not-accessible
	STATUS      current
	DESCRIPTION
	"Table entry for tcpv6Lostsync"
	INDEX { tcpv6LostsyncLevelName }
	::={tcpv6LostsyncLevelTable 1}

Tcpv6LostsyncLevelEntry ::=
	SEQUENCE {
		tcpv6LostsyncLevelName	DisplayString,
		tcpv6LostsyncLevelVal	CounterBasedGauge64,
		tcpv6LostsyncLevelMax	CounterBasedGauge64
	}

tcpv6LostsyncLevelName OBJECT-TYPE
	SYNTAX      DisplayString
	MAX-ACCESS  not-accessible
	STATUS      current
	DESCRIPTION
	"Table entry display string for tcpv6Lostsync"
	::={tcpv6LostsyncLevelEntry 1}

tcpv6LostsyncLevelVal OBJECT-TYPE
	SYNTAX	 CounterBasedGauge64
	MAX-ACCESS  read-only
	STATUS      current
	DESCRIPTION
	"Table entry attribute for tcpv6Lostsync"
	::={tcpv6LostsyncLevelEntry 2}

tcpv6LostsyncLevelMax OBJECT-TYPE
	SYNTAX	 CounterBasedGauge64
	MAX-ACCESS  read-only
	STATUS      current
	DESCRIPTION
	"Table entry attribute for tcpv6Lostsync"
	::={tcpv6LostsyncLevelEntry 4}


tcpv6UntrackedPackets	OBJECT IDENTIFIER ::={tcpv6 13}

tcpv6UntrackedPacketsVal	OBJECT-TYPE
	SYNTAX	 Counter64
	MAX-ACCESS read-only
	STATUS current
	DESCRIPTION "Untracked packets"

	::={tcpv6UntrackedPackets 1}

tcpv6UntrackedPacketsMom	OBJECT-TYPE
	SYNTAX	 CounterBasedGauge64
	MAX-ACCESS read-only
	STATUS current
	DESCRIPTION "Untracked packets"

	::={tcpv6UntrackedPackets 2}

tcpv6UntrackedPacketsMax	OBJECT-TYPE
	SYNTAX	 CounterBasedGauge64
	MAX-ACCESS read-only
	STATUS current
	DESCRIPTION "Untracked packets"

	::={tcpv6UntrackedPackets 3}

tcpv6UntrackedPacketsLevelTable OBJECT-TYPE
	SYNTAX      SEQUENCE OF Tcpv6UntrackedPacketsLevelEntry
	MAX-ACCESS  not-accessible
	STATUS      current
	DESCRIPTION
	"Table for tcpv6UntrackedPackets"
	::={tcpv6UntrackedPackets 4}

tcpv6UntrackedPacketsLevelEntry OBJECT-TYPE
	SYNTAX      Tcpv6UntrackedPacketsLevelEntry
	MAX-ACCESS  not-accessible
	STATUS      current
	DESCRIPTION
	"Table entry for tcpv6UntrackedPackets"
	INDEX { tcpv6UntrackedPacketsLevelName }
	::={tcpv6UntrackedPacketsLevelTable 1}

Tcpv6UntrackedPacketsLevelEntry ::=
	SEQUENCE {
		tcpv6UntrackedPacketsLevelName	DisplayString,
		tcpv6UntrackedPacketsLevelVal	Counter64,
		tcpv6UntrackedPacketsLevelMom	CounterBasedGauge64,
		tcpv6UntrackedPacketsLevelMax	CounterBasedGauge64
	}

tcpv6UntrackedPacketsLevelName OBJECT-TYPE
	SYNTAX      DisplayString
	MAX-ACCESS  not-accessible
	STATUS      current
	DESCRIPTION
	"Table entry display string for tcpv6UntrackedPackets"
	::={tcpv6UntrackedPacketsLevelEntry 1}

tcpv6UntrackedPacketsLevelVal OBJECT-TYPE
	SYNTAX	 Counter64
	MAX-ACCESS  read-only
	STATUS      current
	DESCRIPTION
	"Table entry attribute for tcpv6UntrackedPackets"
	::={tcpv6UntrackedPacketsLevelEntry 2}

tcpv6UntrackedPacketsLevelMom OBJECT-TYPE
	SYNTAX	 CounterBasedGauge64
	MAX-ACCESS  read-only
	STATUS      current
	DESCRIPTION
	"Table entry attribute for tcpv6UntrackedPackets"
	::={tcpv6UntrackedPacketsLevelEntry 3}

tcpv6UntrackedPacketsLevelMax OBJECT-TYPE
	SYNTAX	 CounterBasedGauge64
	MAX-ACCESS  read-only
	STATUS      current
	DESCRIPTION
	"Table entry attribute for tcpv6UntrackedPackets"
	::={tcpv6UntrackedPacketsLevelEntry 4}


tcpv6GoodputPackets	OBJECT IDENTIFIER ::={tcpv6 14}

tcpv6GoodputPacketsVal	OBJECT-TYPE
	SYNTAX	 Counter64
	MAX-ACCESS read-only
	STATUS current
	DESCRIPTION "Goodput packets"

	::={tcpv6GoodputPackets 1}

tcpv6GoodputPacketsMom	OBJECT-TYPE
	SYNTAX	 CounterBasedGauge64
	MAX-ACCESS read-only
	STATUS current
	DESCRIPTION "Goodput packets"

	::={tcpv6GoodputPackets 2}

tcpv6GoodputPacketsMax	OBJECT-TYPE
	SYNTAX	 CounterBasedGauge64
	MAX-ACCESS read-only
	STATUS current
	DESCRIPTION "Goodput packets"

	::={tcpv6GoodputPackets 3}

tcpv6GoodputPacketsLevelTable OBJECT-TYPE
	SYNTAX      SEQUENCE OF Tcpv6GoodputPacketsLevelEntry
	MAX-ACCESS  not-accessible
	STATUS      current
	DESCRIPTION
	"Table for tcpv6GoodputPackets"
	::={tcpv6GoodputPackets 4}

tcpv6GoodputPacketsLevelEntry OBJECT-TYPE
	SYNTAX      Tcpv6GoodputPacketsLevelEntry
	MAX-ACCESS  not-accessible
	STATUS      current
	DESCRIPTION
	"Table entry for tcpv6GoodputPackets"
	INDEX { tcpv6GoodputPacketsLevelName }
	::={tcpv6GoodputPacketsLevelTable 1}

Tcpv6GoodputPacketsLevelEntry ::=
	SEQUENCE {
		tcpv6GoodputPacketsLevelName	DisplayString,
		tcpv6GoodputPacketsLevelVal	Counter64,
		tcpv6GoodputPacketsLevelMom	CounterBasedGauge64,
		tcpv6GoodputPacketsLevelMax	CounterBasedGauge64
	}

tcpv6GoodputPacketsLevelName OBJECT-TYPE
	SYNTAX      DisplayString
	MAX-ACCESS  not-accessible
	STATUS      current
	DESCRIPTION
	"Table entry display string for tcpv6GoodputPackets"
	::={tcpv6GoodputPacketsLevelEntry 1}

tcpv6GoodputPacketsLevelVal OBJECT-TYPE
	SYNTAX	 Counter64
	MAX-ACCESS  read-only
	STATUS      current
	DESCRIPTION
	"Table entry attribute for tcpv6GoodputPackets"
	::={tcpv6GoodputPacketsLevelEntry 2}

tcpv6GoodputPacketsLevelMom OBJECT-TYPE
	SYNTAX	 CounterBasedGauge64
	MAX-ACCESS  read-only
	STATUS      current
	DESCRIPTION
	"Table entry attribute for tcpv6GoodputPackets"
	::={tcpv6GoodputPacketsLevelEntry 3}

tcpv6GoodputPacketsLevelMax OBJECT-TYPE
	SYNTAX	 CounterBasedGauge64
	MAX-ACCESS  read-only
	STATUS      current
	DESCRIPTION
	"Table entry attribute for tcpv6GoodputPackets"
	::={tcpv6GoodputPacketsLevelEntry 4}


tcpv6GoodputBytes	OBJECT IDENTIFIER ::={tcpv6 15}

tcpv6GoodputBytesVal	OBJECT-TYPE
	SYNTAX	 Counter64
	MAX-ACCESS read-only
	STATUS current
	DESCRIPTION "Goodput bytes"

	::={tcpv6GoodputBytes 1}

tcpv6GoodputBytesMom	OBJECT-TYPE
	SYNTAX	 CounterBasedGauge64
	MAX-ACCESS read-only
	STATUS current
	DESCRIPTION "Goodput bytes"

	::={tcpv6GoodputBytes 2}

tcpv6GoodputBytesMax	OBJECT-TYPE
	SYNTAX	 CounterBasedGauge64
	MAX-ACCESS read-only
	STATUS current
	DESCRIPTION "Goodput bytes"

	::={tcpv6GoodputBytes 3}

tcpv6GoodputBytesLevelTable OBJECT-TYPE
	SYNTAX      SEQUENCE OF Tcpv6GoodputBytesLevelEntry
	MAX-ACCESS  not-accessible
	STATUS      current
	DESCRIPTION
	"Table for tcpv6GoodputBytes"
	::={tcpv6GoodputBytes 4}

tcpv6GoodputBytesLevelEntry OBJECT-TYPE
	SYNTAX      Tcpv6GoodputBytesLevelEntry
	MAX-ACCESS  not-accessible
	STATUS      current
	DESCRIPTION
	"Table entry for tcpv6GoodputBytes"
	INDEX { tcpv6GoodputBytesLevelName }
	::={tcpv6GoodputBytesLevelTable 1}

Tcpv6GoodputBytesLevelEntry ::=
	SEQUENCE {
		tcpv6GoodputBytesLevelName	DisplayString,
		tcpv6GoodputBytesLevelVal	Counter64,
		tcpv6GoodputBytesLevelMom	CounterBasedGauge64,
		tcpv6GoodputBytesLevelMax	CounterBasedGauge64
	}

tcpv6GoodputBytesLevelName OBJECT-TYPE
	SYNTAX      DisplayString
	MAX-ACCESS  not-accessible
	STATUS      current
	DESCRIPTION
	"Table entry display string for tcpv6GoodputBytes"
	::={tcpv6GoodputBytesLevelEntry 1}

tcpv6GoodputBytesLevelVal OBJECT-TYPE
	SYNTAX	 Counter64
	MAX-ACCESS  read-only
	STATUS      current
	DESCRIPTION
	"Table entry attribute for tcpv6GoodputBytes"
	::={tcpv6GoodputBytesLevelEntry 2}

tcpv6GoodputBytesLevelMom OBJECT-TYPE
	SYNTAX	 CounterBasedGauge64
	MAX-ACCESS  read-only
	STATUS      current
	DESCRIPTION
	"Table entry attribute for tcpv6GoodputBytes"
	::={tcpv6GoodputBytesLevelEntry 3}

tcpv6GoodputBytesLevelMax OBJECT-TYPE
	SYNTAX	 CounterBasedGauge64
	MAX-ACCESS  read-only
	STATUS      current
	DESCRIPTION
	"Table entry attribute for tcpv6GoodputBytes"
	::={tcpv6GoodputBytesLevelEntry 4}


tcpv6Segments	OBJECT IDENTIFIER ::={tcpv6 16}

tcpv6SegmentsVal	OBJECT-TYPE
	SYNTAX	 CounterBasedGauge64
	MAX-ACCESS read-only
	STATUS current
	DESCRIPTION "Saved segments"

	::={tcpv6Segments 1}

tcpv6SegmentsMax	OBJECT-TYPE
	SYNTAX	 CounterBasedGauge64
	MAX-ACCESS read-only
	STATUS current
	DESCRIPTION "Saved segments"

	::={tcpv6Segments 3}

tcpv6SegmentsLevelTable OBJECT-TYPE
	SYNTAX      SEQUENCE OF Tcpv6SegmentsLevelEntry
	MAX-ACCESS  not-accessible
	STATUS      current
	DESCRIPTION
	"Table for tcpv6Segments"
	::={tcpv6Segments 4}

tcpv6SegmentsLevelEntry OBJECT-TYPE
	SYNTAX      Tcpv6SegmentsLevelEntry
	MAX-ACCESS  not-accessible
	STATUS      current
	DESCRIPTION
	"Table entry for tcpv6Segments"
	INDEX { tcpv6SegmentsLevelName }
	::={tcpv6SegmentsLevelTable 1}

Tcpv6SegmentsLevelEntry ::=
	SEQUENCE {
		tcpv6SegmentsLevelName	DisplayString,
		tcpv6SegmentsLevelVal	CounterBasedGauge64,
		tcpv6SegmentsLevelMax	CounterBasedGauge64
	}

tcpv6SegmentsLevelName OBJECT-TYPE
	SYNTAX      DisplayString
	MAX-ACCESS  not-accessible
	STATUS      current
	DESCRIPTION
	"Table entry display string for tcpv6Segments"
	::={tcpv6SegmentsLevelEntry 1}

tcpv6SegmentsLevelVal OBJECT-TYPE
	SYNTAX	 CounterBasedGauge64
	MAX-ACCESS  read-only
	STATUS      current
	DESCRIPTION
	"Table entry attribute for tcpv6Segments"
	::={tcpv6SegmentsLevelEntry 2}

tcpv6SegmentsLevelMax OBJECT-TYPE
	SYNTAX	 CounterBasedGauge64
	MAX-ACCESS  read-only
	STATUS      current
	DESCRIPTION
	"Table entry attribute for tcpv6Segments"
	::={tcpv6SegmentsLevelEntry 4}


tcpv6SegmentsPayload	OBJECT IDENTIFIER ::={tcpv6 17}

tcpv6SegmentsPayloadVal	OBJECT-TYPE
	SYNTAX	 CounterBasedGauge64
	MAX-ACCESS read-only
	STATUS current
	DESCRIPTION "Saved segments with payload"

	::={tcpv6SegmentsPayload 1}

tcpv6SegmentsPayloadMax	OBJECT-TYPE
	SYNTAX	 CounterBasedGauge64
	MAX-ACCESS read-only
	STATUS current
	DESCRIPTION "Saved segments with payload"

	::={tcpv6SegmentsPayload 3}

tcpv6SegmentsPayloadLevelTable OBJECT-TYPE
	SYNTAX      SEQUENCE OF Tcpv6SegmentsPayloadLevelEntry
	MAX-ACCESS  not-accessible
	STATUS      current
	DESCRIPTION
	"Table for tcpv6SegmentsPayload"
	::={tcpv6SegmentsPayload 4}

tcpv6SegmentsPayloadLevelEntry OBJECT-TYPE
	SYNTAX      Tcpv6SegmentsPayloadLevelEntry
	MAX-ACCESS  not-accessible
	STATUS      current
	DESCRIPTION
	"Table entry for tcpv6SegmentsPayload"
	INDEX { tcpv6SegmentsPayloadLevelName }
	::={tcpv6SegmentsPayloadLevelTable 1}

Tcpv6SegmentsPayloadLevelEntry ::=
	SEQUENCE {
		tcpv6SegmentsPayloadLevelName	DisplayString,
		tcpv6SegmentsPayloadLevelVal	CounterBasedGauge64,
		tcpv6SegmentsPayloadLevelMax	CounterBasedGauge64
	}

tcpv6SegmentsPayloadLevelName OBJECT-TYPE
	SYNTAX      DisplayString
	MAX-ACCESS  not-accessible
	STATUS      current
	DESCRIPTION
	"Table entry display string for tcpv6SegmentsPayload"
	::={tcpv6SegmentsPayloadLevelEntry 1}

tcpv6SegmentsPayloadLevelVal OBJECT-TYPE
	SYNTAX	 CounterBasedGauge64
	MAX-ACCESS  read-only
	STATUS      current
	DESCRIPTION
	"Table entry attribute for tcpv6SegmentsPayload"
	::={tcpv6SegmentsPayloadLevelEntry 2}

tcpv6SegmentsPayloadLevelMax OBJECT-TYPE
	SYNTAX	 CounterBasedGauge64
	MAX-ACCESS  read-only
	STATUS      current
	DESCRIPTION
	"Table entry attribute for tcpv6SegmentsPayload"
	::={tcpv6SegmentsPayloadLevelEntry 4}


tcpv6SegmentsDropped	OBJECT IDENTIFIER ::={tcpv6 18}

tcpv6SegmentsDroppedVal	OBJECT-TYPE
	SYNTAX	 Counter64
	MAX-ACCESS read-only
	STATUS current
	DESCRIPTION "Ignored segments"

	::={tcpv6SegmentsDropped 1}

tcpv6SegmentsDroppedMom	OBJECT-TYPE
	SYNTAX	 CounterBasedGauge64
	MAX-ACCESS read-only
	STATUS current
	DESCRIPTION "Ignored segments"

	::={tcpv6SegmentsDropped 2}

tcpv6SegmentsDroppedMax	OBJECT-TYPE
	SYNTAX	 CounterBasedGauge64
	MAX-ACCESS read-only
	STATUS current
	DESCRIPTION "Ignored segments"

	::={tcpv6SegmentsDropped 3}

tcpv6SegmentsDroppedLevelTable OBJECT-TYPE
	SYNTAX      SEQUENCE OF Tcpv6SegmentsDroppedLevelEntry
	MAX-ACCESS  not-accessible
	STATUS      current
	DESCRIPTION
	"Table for tcpv6SegmentsDropped"
	::={tcpv6SegmentsDropped 4}

tcpv6SegmentsDroppedLevelEntry OBJECT-TYPE
	SYNTAX      Tcpv6SegmentsDroppedLevelEntry
	MAX-ACCESS  not-accessible
	STATUS      current
	DESCRIPTION
	"Table entry for tcpv6SegmentsDropped"
	INDEX { tcpv6SegmentsDroppedLevelName }
	::={tcpv6SegmentsDroppedLevelTable 1}

Tcpv6SegmentsDroppedLevelEntry ::=
	SEQUENCE {
		tcpv6SegmentsDroppedLevelName	DisplayString,
		tcpv6SegmentsDroppedLevelVal	Counter64,
		tcpv6SegmentsDroppedLevelMom	CounterBasedGauge64,
		tcpv6SegmentsDroppedLevelMax	CounterBasedGauge64
	}

tcpv6SegmentsDroppedLevelName OBJECT-TYPE
	SYNTAX      DisplayString
	MAX-ACCESS  not-accessible
	STATUS      current
	DESCRIPTION
	"Table entry display string for tcpv6SegmentsDropped"
	::={tcpv6SegmentsDroppedLevelEntry 1}

tcpv6SegmentsDroppedLevelVal OBJECT-TYPE
	SYNTAX	 Counter64
	MAX-ACCESS  read-only
	STATUS      current
	DESCRIPTION
	"Table entry attribute for tcpv6SegmentsDropped"
	::={tcpv6SegmentsDroppedLevelEntry 2}

tcpv6SegmentsDroppedLevelMom OBJECT-TYPE
	SYNTAX	 CounterBasedGauge64
	MAX-ACCESS  read-only
	STATUS      current
	DESCRIPTION
	"Table entry attribute for tcpv6SegmentsDropped"
	::={tcpv6SegmentsDroppedLevelEntry 3}

tcpv6SegmentsDroppedLevelMax OBJECT-TYPE
	SYNTAX	 CounterBasedGauge64
	MAX-ACCESS  read-only
	STATUS      current
	DESCRIPTION
	"Table entry attribute for tcpv6SegmentsDropped"
	::={tcpv6SegmentsDroppedLevelEntry 4}


tcpv6PacketAllocFail	OBJECT IDENTIFIER ::={tcpv6 19}

tcpv6PacketAllocFailVal	OBJECT-TYPE
	SYNTAX	 Counter64
	MAX-ACCESS read-only
	STATUS current
	DESCRIPTION "Packet allocation failures"

	::={tcpv6PacketAllocFail 1}

tcpv6PacketAllocFailMom	OBJECT-TYPE
	SYNTAX	 CounterBasedGauge64
	MAX-ACCESS read-only
	STATUS current
	DESCRIPTION "Packet allocation failures"

	::={tcpv6PacketAllocFail 2}

tcpv6PacketAllocFailMax	OBJECT-TYPE
	SYNTAX	 CounterBasedGauge64
	MAX-ACCESS read-only
	STATUS current
	DESCRIPTION "Packet allocation failures"

	::={tcpv6PacketAllocFail 3}

tcpv6PacketAllocFailLevelTable OBJECT-TYPE
	SYNTAX      SEQUENCE OF Tcpv6PacketAllocFailLevelEntry
	MAX-ACCESS  not-accessible
	STATUS      current
	DESCRIPTION
	"Table for tcpv6PacketAllocFail"
	::={tcpv6PacketAllocFail 4}

tcpv6PacketAllocFailLevelEntry OBJECT-TYPE
	SYNTAX      Tcpv6PacketAllocFailLevelEntry
	MAX-ACCESS  not-accessible
	STATUS      current
	DESCRIPTION
	"Table entry for tcpv6PacketAllocFail"
	INDEX { tcpv6PacketAllocFailLevelName }
	::={tcpv6PacketAllocFailLevelTable 1}

Tcpv6PacketAllocFailLevelEntry ::=
	SEQUENCE {
		tcpv6PacketAllocFailLevelName	DisplayString,
		tcpv6PacketAllocFailLevelVal	Counter64,
		tcpv6PacketAllocFailLevelMom	CounterBasedGauge64,
		tcpv6PacketAllocFailLevelMax	CounterBasedGauge64
	}

tcpv6PacketAllocFailLevelName OBJECT-TYPE
	SYNTAX      DisplayString
	MAX-ACCESS  not-accessible
	STATUS      current
	DESCRIPTION
	"Table entry display string for tcpv6PacketAllocFail"
	::={tcpv6PacketAllocFailLevelEntry 1}

tcpv6PacketAllocFailLevelVal OBJECT-TYPE
	SYNTAX	 Counter64
	MAX-ACCESS  read-only
	STATUS      current
	DESCRIPTION
	"Table entry attribute for tcpv6PacketAllocFail"
	::={tcpv6PacketAllocFailLevelEntry 2}

tcpv6PacketAllocFailLevelMom OBJECT-TYPE
	SYNTAX	 CounterBasedGauge64
	MAX-ACCESS  read-only
	STATUS      current
	DESCRIPTION
	"Table entry attribute for tcpv6PacketAllocFail"
	::={tcpv6PacketAllocFailLevelEntry 3}

tcpv6PacketAllocFailLevelMax OBJECT-TYPE
	SYNTAX	 CounterBasedGauge64
	MAX-ACCESS  read-only
	STATUS      current
	DESCRIPTION
	"Table entry attribute for tcpv6PacketAllocFail"
	::={tcpv6PacketAllocFailLevelEntry 4}


tcpv6UntrackedGoodput	OBJECT IDENTIFIER ::={tcpv6 23}

tcpv6UntrackedGoodputVal	OBJECT-TYPE
	SYNTAX	 Counter64
	MAX-ACCESS read-only
	STATUS current
	DESCRIPTION "Untracked bytes (goodput)"

	::={tcpv6UntrackedGoodput 1}

tcpv6UntrackedGoodputMom	OBJECT-TYPE
	SYNTAX	 CounterBasedGauge64
	MAX-ACCESS read-only
	STATUS current
	DESCRIPTION "Untracked bytes (goodput)"

	::={tcpv6UntrackedGoodput 2}

tcpv6UntrackedGoodputMax	OBJECT-TYPE
	SYNTAX	 CounterBasedGauge64
	MAX-ACCESS read-only
	STATUS current
	DESCRIPTION "Untracked bytes (goodput)"

	::={tcpv6UntrackedGoodput 3}

tcpv6UntrackedGoodputLevelTable OBJECT-TYPE
	SYNTAX      SEQUENCE OF Tcpv6UntrackedGoodputLevelEntry
	MAX-ACCESS  not-accessible
	STATUS      current
	DESCRIPTION
	"Table for tcpv6UntrackedGoodput"
	::={tcpv6UntrackedGoodput 4}

tcpv6UntrackedGoodputLevelEntry OBJECT-TYPE
	SYNTAX      Tcpv6UntrackedGoodputLevelEntry
	MAX-ACCESS  not-accessible
	STATUS      current
	DESCRIPTION
	"Table entry for tcpv6UntrackedGoodput"
	INDEX { tcpv6UntrackedGoodputLevelName }
	::={tcpv6UntrackedGoodputLevelTable 1}

Tcpv6UntrackedGoodputLevelEntry ::=
	SEQUENCE {
		tcpv6UntrackedGoodputLevelName	DisplayString,
		tcpv6UntrackedGoodputLevelVal	Counter64,
		tcpv6UntrackedGoodputLevelMom	CounterBasedGauge64,
		tcpv6UntrackedGoodputLevelMax	CounterBasedGauge64
	}

tcpv6UntrackedGoodputLevelName OBJECT-TYPE
	SYNTAX      DisplayString
	MAX-ACCESS  not-accessible
	STATUS      current
	DESCRIPTION
	"Table entry display string for tcpv6UntrackedGoodput"
	::={tcpv6UntrackedGoodputLevelEntry 1}

tcpv6UntrackedGoodputLevelVal OBJECT-TYPE
	SYNTAX	 Counter64
	MAX-ACCESS  read-only
	STATUS      current
	DESCRIPTION
	"Table entry attribute for tcpv6UntrackedGoodput"
	::={tcpv6UntrackedGoodputLevelEntry 2}

tcpv6UntrackedGoodputLevelMom OBJECT-TYPE
	SYNTAX	 CounterBasedGauge64
	MAX-ACCESS  read-only
	STATUS      current
	DESCRIPTION
	"Table entry attribute for tcpv6UntrackedGoodput"
	::={tcpv6UntrackedGoodputLevelEntry 3}

tcpv6UntrackedGoodputLevelMax OBJECT-TYPE
	SYNTAX	 CounterBasedGauge64
	MAX-ACCESS  read-only
	STATUS      current
	DESCRIPTION
	"Table entry attribute for tcpv6UntrackedGoodput"
	::={tcpv6UntrackedGoodputLevelEntry 4}


tcpv6UntrackedBytes	OBJECT IDENTIFIER ::={tcpv6 24}

tcpv6UntrackedBytesVal	OBJECT-TYPE
	SYNTAX	 Counter64
	MAX-ACCESS read-only
	STATUS current
	DESCRIPTION "Untracked bytes"

	::={tcpv6UntrackedBytes 1}

tcpv6UntrackedBytesMom	OBJECT-TYPE
	SYNTAX	 CounterBasedGauge64
	MAX-ACCESS read-only
	STATUS current
	DESCRIPTION "Untracked bytes"

	::={tcpv6UntrackedBytes 2}

tcpv6UntrackedBytesMax	OBJECT-TYPE
	SYNTAX	 CounterBasedGauge64
	MAX-ACCESS read-only
	STATUS current
	DESCRIPTION "Untracked bytes"

	::={tcpv6UntrackedBytes 3}

tcpv6UntrackedBytesLevelTable OBJECT-TYPE
	SYNTAX      SEQUENCE OF Tcpv6UntrackedBytesLevelEntry
	MAX-ACCESS  not-accessible
	STATUS      current
	DESCRIPTION
	"Table for tcpv6UntrackedBytes"
	::={tcpv6UntrackedBytes 4}

tcpv6UntrackedBytesLevelEntry OBJECT-TYPE
	SYNTAX      Tcpv6UntrackedBytesLevelEntry
	MAX-ACCESS  not-accessible
	STATUS      current
	DESCRIPTION
	"Table entry for tcpv6UntrackedBytes"
	INDEX { tcpv6UntrackedBytesLevelName }
	::={tcpv6UntrackedBytesLevelTable 1}

Tcpv6UntrackedBytesLevelEntry ::=
	SEQUENCE {
		tcpv6UntrackedBytesLevelName	DisplayString,
		tcpv6UntrackedBytesLevelVal	Counter64,
		tcpv6UntrackedBytesLevelMom	CounterBasedGauge64,
		tcpv6UntrackedBytesLevelMax	CounterBasedGauge64
	}

tcpv6UntrackedBytesLevelName OBJECT-TYPE
	SYNTAX      DisplayString
	MAX-ACCESS  not-accessible
	STATUS      current
	DESCRIPTION
	"Table entry display string for tcpv6UntrackedBytes"
	::={tcpv6UntrackedBytesLevelEntry 1}

tcpv6UntrackedBytesLevelVal OBJECT-TYPE
	SYNTAX	 Counter64
	MAX-ACCESS  read-only
	STATUS      current
	DESCRIPTION
	"Table entry attribute for tcpv6UntrackedBytes"
	::={tcpv6UntrackedBytesLevelEntry 2}

tcpv6UntrackedBytesLevelMom OBJECT-TYPE
	SYNTAX	 CounterBasedGauge64
	MAX-ACCESS  read-only
	STATUS      current
	DESCRIPTION
	"Table entry attribute for tcpv6UntrackedBytes"
	::={tcpv6UntrackedBytesLevelEntry 3}

tcpv6UntrackedBytesLevelMax OBJECT-TYPE
	SYNTAX	 CounterBasedGauge64
	MAX-ACCESS  read-only
	STATUS      current
	DESCRIPTION
	"Table entry attribute for tcpv6UntrackedBytes"
	::={tcpv6UntrackedBytesLevelEntry 4}


tcpv6CorruptOptions	OBJECT IDENTIFIER ::={tcpv6 25}

tcpv6CorruptOptionsVal	OBJECT-TYPE
	SYNTAX	 Counter64
	MAX-ACCESS read-only
	STATUS current
	DESCRIPTION "Packets with corrupt options"

	::={tcpv6CorruptOptions 1}

tcpv6CorruptOptionsMom	OBJECT-TYPE
	SYNTAX	 CounterBasedGauge64
	MAX-ACCESS read-only
	STATUS current
	DESCRIPTION "Packets with corrupt options"

	::={tcpv6CorruptOptions 2}

tcpv6CorruptOptionsMax	OBJECT-TYPE
	SYNTAX	 CounterBasedGauge64
	MAX-ACCESS read-only
	STATUS current
	DESCRIPTION "Packets with corrupt options"

	::={tcpv6CorruptOptions 3}

tcpv6CorruptOptionsLevelTable OBJECT-TYPE
	SYNTAX      SEQUENCE OF Tcpv6CorruptOptionsLevelEntry
	MAX-ACCESS  not-accessible
	STATUS      current
	DESCRIPTION
	"Table for tcpv6CorruptOptions"
	::={tcpv6CorruptOptions 4}

tcpv6CorruptOptionsLevelEntry OBJECT-TYPE
	SYNTAX      Tcpv6CorruptOptionsLevelEntry
	MAX-ACCESS  not-accessible
	STATUS      current
	DESCRIPTION
	"Table entry for tcpv6CorruptOptions"
	INDEX { tcpv6CorruptOptionsLevelName }
	::={tcpv6CorruptOptionsLevelTable 1}

Tcpv6CorruptOptionsLevelEntry ::=
	SEQUENCE {
		tcpv6CorruptOptionsLevelName	DisplayString,
		tcpv6CorruptOptionsLevelVal	Counter64,
		tcpv6CorruptOptionsLevelMom	CounterBasedGauge64,
		tcpv6CorruptOptionsLevelMax	CounterBasedGauge64
	}

tcpv6CorruptOptionsLevelName OBJECT-TYPE
	SYNTAX      DisplayString
	MAX-ACCESS  not-accessible
	STATUS      current
	DESCRIPTION
	"Table entry display string for tcpv6CorruptOptions"
	::={tcpv6CorruptOptionsLevelEntry 1}

tcpv6CorruptOptionsLevelVal OBJECT-TYPE
	SYNTAX	 Counter64
	MAX-ACCESS  read-only
	STATUS      current
	DESCRIPTION
	"Table entry attribute for tcpv6CorruptOptions"
	::={tcpv6CorruptOptionsLevelEntry 2}

tcpv6CorruptOptionsLevelMom OBJECT-TYPE
	SYNTAX	 CounterBasedGauge64
	MAX-ACCESS  read-only
	STATUS      current
	DESCRIPTION
	"Table entry attribute for tcpv6CorruptOptions"
	::={tcpv6CorruptOptionsLevelEntry 3}

tcpv6CorruptOptionsLevelMax OBJECT-TYPE
	SYNTAX	 CounterBasedGauge64
	MAX-ACCESS  read-only
	STATUS      current
	DESCRIPTION
	"Table entry attribute for tcpv6CorruptOptions"
	::={tcpv6CorruptOptionsLevelEntry 4}


tcpv6CorruptConn	OBJECT IDENTIFIER ::={tcpv6 26}

tcpv6CorruptConnVal	OBJECT-TYPE
	SYNTAX	 Counter64
	MAX-ACCESS read-only
	STATUS current
	DESCRIPTION "Packets with corrupt conn"

	::={tcpv6CorruptConn 1}

tcpv6CorruptConnMom	OBJECT-TYPE
	SYNTAX	 CounterBasedGauge64
	MAX-ACCESS read-only
	STATUS current
	DESCRIPTION "Packets with corrupt conn"

	::={tcpv6CorruptConn 2}

tcpv6CorruptConnMax	OBJECT-TYPE
	SYNTAX	 CounterBasedGauge64
	MAX-ACCESS read-only
	STATUS current
	DESCRIPTION "Packets with corrupt conn"

	::={tcpv6CorruptConn 3}

tcpv6CorruptConnLevelTable OBJECT-TYPE
	SYNTAX      SEQUENCE OF Tcpv6CorruptConnLevelEntry
	MAX-ACCESS  not-accessible
	STATUS      current
	DESCRIPTION
	"Table for tcpv6CorruptConn"
	::={tcpv6CorruptConn 4}

tcpv6CorruptConnLevelEntry OBJECT-TYPE
	SYNTAX      Tcpv6CorruptConnLevelEntry
	MAX-ACCESS  not-accessible
	STATUS      current
	DESCRIPTION
	"Table entry for tcpv6CorruptConn"
	INDEX { tcpv6CorruptConnLevelName }
	::={tcpv6CorruptConnLevelTable 1}

Tcpv6CorruptConnLevelEntry ::=
	SEQUENCE {
		tcpv6CorruptConnLevelName	DisplayString,
		tcpv6CorruptConnLevelVal	Counter64,
		tcpv6CorruptConnLevelMom	CounterBasedGauge64,
		tcpv6CorruptConnLevelMax	CounterBasedGauge64
	}

tcpv6CorruptConnLevelName OBJECT-TYPE
	SYNTAX      DisplayString
	MAX-ACCESS  not-accessible
	STATUS      current
	DESCRIPTION
	"Table entry display string for tcpv6CorruptConn"
	::={tcpv6CorruptConnLevelEntry 1}

tcpv6CorruptConnLevelVal OBJECT-TYPE
	SYNTAX	 Counter64
	MAX-ACCESS  read-only
	STATUS      current
	DESCRIPTION
	"Table entry attribute for tcpv6CorruptConn"
	::={tcpv6CorruptConnLevelEntry 2}

tcpv6CorruptConnLevelMom OBJECT-TYPE
	SYNTAX	 CounterBasedGauge64
	MAX-ACCESS  read-only
	STATUS      current
	DESCRIPTION
	"Table entry attribute for tcpv6CorruptConn"
	::={tcpv6CorruptConnLevelEntry 3}

tcpv6CorruptConnLevelMax OBJECT-TYPE
	SYNTAX	 CounterBasedGauge64
	MAX-ACCESS  read-only
	STATUS      current
	DESCRIPTION
	"Table entry attribute for tcpv6CorruptConn"
	::={tcpv6CorruptConnLevelEntry 4}


tcpv6SegmentedConnections	OBJECT IDENTIFIER ::={tcpv6 27}

tcpv6SegmentedConnectionsVal	OBJECT-TYPE
	SYNTAX	 CounterBasedGauge64
	MAX-ACCESS read-only
	STATUS current
	DESCRIPTION "Connections with segments"

	::={tcpv6SegmentedConnections 1}

tcpv6SegmentedConnectionsMax	OBJECT-TYPE
	SYNTAX	 CounterBasedGauge64
	MAX-ACCESS read-only
	STATUS current
	DESCRIPTION "Connections with segments"

	::={tcpv6SegmentedConnections 3}

tcpv6SegmentedConnectionsLevelTable OBJECT-TYPE
	SYNTAX      SEQUENCE OF Tcpv6SegmentedConnectionsLevelEntry
	MAX-ACCESS  not-accessible
	STATUS      current
	DESCRIPTION
	"Table for tcpv6SegmentedConnections"
	::={tcpv6SegmentedConnections 4}

tcpv6SegmentedConnectionsLevelEntry OBJECT-TYPE
	SYNTAX      Tcpv6SegmentedConnectionsLevelEntry
	MAX-ACCESS  not-accessible
	STATUS      current
	DESCRIPTION
	"Table entry for tcpv6SegmentedConnections"
	INDEX { tcpv6SegmentedConnectionsLevelName }
	::={tcpv6SegmentedConnectionsLevelTable 1}

Tcpv6SegmentedConnectionsLevelEntry ::=
	SEQUENCE {
		tcpv6SegmentedConnectionsLevelName	DisplayString,
		tcpv6SegmentedConnectionsLevelVal	CounterBasedGauge64,
		tcpv6SegmentedConnectionsLevelMax	CounterBasedGauge64
	}

tcpv6SegmentedConnectionsLevelName OBJECT-TYPE
	SYNTAX      DisplayString
	MAX-ACCESS  not-accessible
	STATUS      current
	DESCRIPTION
	"Table entry display string for tcpv6SegmentedConnections"
	::={tcpv6SegmentedConnectionsLevelEntry 1}

tcpv6SegmentedConnectionsLevelVal OBJECT-TYPE
	SYNTAX	 CounterBasedGauge64
	MAX-ACCESS  read-only
	STATUS      current
	DESCRIPTION
	"Table entry attribute for tcpv6SegmentedConnections"
	::={tcpv6SegmentedConnectionsLevelEntry 2}

tcpv6SegmentedConnectionsLevelMax OBJECT-TYPE
	SYNTAX	 CounterBasedGauge64
	MAX-ACCESS  read-only
	STATUS      current
	DESCRIPTION
	"Table entry attribute for tcpv6SegmentedConnections"
	::={tcpv6SegmentedConnectionsLevelEntry 4}


tcpv6OutOfWindowPackets	OBJECT IDENTIFIER ::={tcpv6 28}

tcpv6OutOfWindowPacketsVal	OBJECT-TYPE
	SYNTAX	 Counter64
	MAX-ACCESS read-only
	STATUS current
	DESCRIPTION "Out of window packets (ignored)"

	::={tcpv6OutOfWindowPackets 1}

tcpv6OutOfWindowPacketsMom	OBJECT-TYPE
	SYNTAX	 CounterBasedGauge64
	MAX-ACCESS read-only
	STATUS current
	DESCRIPTION "Out of window packets (ignored)"

	::={tcpv6OutOfWindowPackets 2}

tcpv6OutOfWindowPacketsMax	OBJECT-TYPE
	SYNTAX	 CounterBasedGauge64
	MAX-ACCESS read-only
	STATUS current
	DESCRIPTION "Out of window packets (ignored)"

	::={tcpv6OutOfWindowPackets 3}

tcpv6OutOfWindowPacketsLevelTable OBJECT-TYPE
	SYNTAX      SEQUENCE OF Tcpv6OutOfWindowPacketsLevelEntry
	MAX-ACCESS  not-accessible
	STATUS      current
	DESCRIPTION
	"Table for tcpv6OutOfWindowPackets"
	::={tcpv6OutOfWindowPackets 4}

tcpv6OutOfWindowPacketsLevelEntry OBJECT-TYPE
	SYNTAX      Tcpv6OutOfWindowPacketsLevelEntry
	MAX-ACCESS  not-accessible
	STATUS      current
	DESCRIPTION
	"Table entry for tcpv6OutOfWindowPackets"
	INDEX { tcpv6OutOfWindowPacketsLevelName }
	::={tcpv6OutOfWindowPacketsLevelTable 1}

Tcpv6OutOfWindowPacketsLevelEntry ::=
	SEQUENCE {
		tcpv6OutOfWindowPacketsLevelName	DisplayString,
		tcpv6OutOfWindowPacketsLevelVal	Counter64,
		tcpv6OutOfWindowPacketsLevelMom	CounterBasedGauge64,
		tcpv6OutOfWindowPacketsLevelMax	CounterBasedGauge64
	}

tcpv6OutOfWindowPacketsLevelName OBJECT-TYPE
	SYNTAX      DisplayString
	MAX-ACCESS  not-accessible
	STATUS      current
	DESCRIPTION
	"Table entry display string for tcpv6OutOfWindowPackets"
	::={tcpv6OutOfWindowPacketsLevelEntry 1}

tcpv6OutOfWindowPacketsLevelVal OBJECT-TYPE
	SYNTAX	 Counter64
	MAX-ACCESS  read-only
	STATUS      current
	DESCRIPTION
	"Table entry attribute for tcpv6OutOfWindowPackets"
	::={tcpv6OutOfWindowPacketsLevelEntry 2}

tcpv6OutOfWindowPacketsLevelMom OBJECT-TYPE
	SYNTAX	 CounterBasedGauge64
	MAX-ACCESS  read-only
	STATUS      current
	DESCRIPTION
	"Table entry attribute for tcpv6OutOfWindowPackets"
	::={tcpv6OutOfWindowPacketsLevelEntry 3}

tcpv6OutOfWindowPacketsLevelMax OBJECT-TYPE
	SYNTAX	 CounterBasedGauge64
	MAX-ACCESS  read-only
	STATUS      current
	DESCRIPTION
	"Table entry attribute for tcpv6OutOfWindowPackets"
	::={tcpv6OutOfWindowPacketsLevelEntry 4}


tcpv6RefusedFilter	OBJECT IDENTIFIER ::={tcpv6 29}

tcpv6RefusedFilterVal	OBJECT-TYPE
	SYNTAX	 Counter64
	MAX-ACCESS read-only
	STATUS current
	DESCRIPTION "Packets refused by lowlevel filter"

	::={tcpv6RefusedFilter 1}

tcpv6RefusedFilterMom	OBJECT-TYPE
	SYNTAX	 CounterBasedGauge64
	MAX-ACCESS read-only
	STATUS current
	DESCRIPTION "Packets refused by lowlevel filter"

	::={tcpv6RefusedFilter 2}

tcpv6RefusedFilterMax	OBJECT-TYPE
	SYNTAX	 CounterBasedGauge64
	MAX-ACCESS read-only
	STATUS current
	DESCRIPTION "Packets refused by lowlevel filter"

	::={tcpv6RefusedFilter 3}

tcpv6RefusedFilterLevelTable OBJECT-TYPE
	SYNTAX      SEQUENCE OF Tcpv6RefusedFilterLevelEntry
	MAX-ACCESS  not-accessible
	STATUS      current
	DESCRIPTION
	"Table for tcpv6RefusedFilter"
	::={tcpv6RefusedFilter 4}

tcpv6RefusedFilterLevelEntry OBJECT-TYPE
	SYNTAX      Tcpv6RefusedFilterLevelEntry
	MAX-ACCESS  not-accessible
	STATUS      current
	DESCRIPTION
	"Table entry for tcpv6RefusedFilter"
	INDEX { tcpv6RefusedFilterLevelName }
	::={tcpv6RefusedFilterLevelTable 1}

Tcpv6RefusedFilterLevelEntry ::=
	SEQUENCE {
		tcpv6RefusedFilterLevelName	DisplayString,
		tcpv6RefusedFilterLevelVal	Counter64,
		tcpv6RefusedFilterLevelMom	CounterBasedGauge64,
		tcpv6RefusedFilterLevelMax	CounterBasedGauge64
	}

tcpv6RefusedFilterLevelName OBJECT-TYPE
	SYNTAX      DisplayString
	MAX-ACCESS  not-accessible
	STATUS      current
	DESCRIPTION
	"Table entry display string for tcpv6RefusedFilter"
	::={tcpv6RefusedFilterLevelEntry 1}

tcpv6RefusedFilterLevelVal OBJECT-TYPE
	SYNTAX	 Counter64
	MAX-ACCESS  read-only
	STATUS      current
	DESCRIPTION
	"Table entry attribute for tcpv6RefusedFilter"
	::={tcpv6RefusedFilterLevelEntry 2}

tcpv6RefusedFilterLevelMom OBJECT-TYPE
	SYNTAX	 CounterBasedGauge64
	MAX-ACCESS  read-only
	STATUS      current
	DESCRIPTION
	"Table entry attribute for tcpv6RefusedFilter"
	::={tcpv6RefusedFilterLevelEntry 3}

tcpv6RefusedFilterLevelMax OBJECT-TYPE
	SYNTAX	 CounterBasedGauge64
	MAX-ACCESS  read-only
	STATUS      current
	DESCRIPTION
	"Table entry attribute for tcpv6RefusedFilter"
	::={tcpv6RefusedFilterLevelEntry 4}


tcpv6SynExisting	OBJECT IDENTIFIER ::={tcpv6 32}

tcpv6SynExistingVal	OBJECT-TYPE
	SYNTAX	 Counter64
	MAX-ACCESS read-only
	STATUS current
	DESCRIPTION "SYN packets for existing connections"

	::={tcpv6SynExisting 1}

tcpv6SynExistingMom	OBJECT-TYPE
	SYNTAX	 CounterBasedGauge64
	MAX-ACCESS read-only
	STATUS current
	DESCRIPTION "SYN packets for existing connections"

	::={tcpv6SynExisting 2}

tcpv6SynExistingMax	OBJECT-TYPE
	SYNTAX	 CounterBasedGauge64
	MAX-ACCESS read-only
	STATUS current
	DESCRIPTION "SYN packets for existing connections"

	::={tcpv6SynExisting 3}

tcpv6SynExistingLevelTable OBJECT-TYPE
	SYNTAX      SEQUENCE OF Tcpv6SynExistingLevelEntry
	MAX-ACCESS  not-accessible
	STATUS      current
	DESCRIPTION
	"Table for tcpv6SynExisting"
	::={tcpv6SynExisting 4}

tcpv6SynExistingLevelEntry OBJECT-TYPE
	SYNTAX      Tcpv6SynExistingLevelEntry
	MAX-ACCESS  not-accessible
	STATUS      current
	DESCRIPTION
	"Table entry for tcpv6SynExisting"
	INDEX { tcpv6SynExistingLevelName }
	::={tcpv6SynExistingLevelTable 1}

Tcpv6SynExistingLevelEntry ::=
	SEQUENCE {
		tcpv6SynExistingLevelName	DisplayString,
		tcpv6SynExistingLevelVal	Counter64,
		tcpv6SynExistingLevelMom	CounterBasedGauge64,
		tcpv6SynExistingLevelMax	CounterBasedGauge64
	}

tcpv6SynExistingLevelName OBJECT-TYPE
	SYNTAX      DisplayString
	MAX-ACCESS  not-accessible
	STATUS      current
	DESCRIPTION
	"Table entry display string for tcpv6SynExisting"
	::={tcpv6SynExistingLevelEntry 1}

tcpv6SynExistingLevelVal OBJECT-TYPE
	SYNTAX	 Counter64
	MAX-ACCESS  read-only
	STATUS      current
	DESCRIPTION
	"Table entry attribute for tcpv6SynExisting"
	::={tcpv6SynExistingLevelEntry 2}

tcpv6SynExistingLevelMom OBJECT-TYPE
	SYNTAX	 CounterBasedGauge64
	MAX-ACCESS  read-only
	STATUS      current
	DESCRIPTION
	"Table entry attribute for tcpv6SynExisting"
	::={tcpv6SynExistingLevelEntry 3}

tcpv6SynExistingLevelMax OBJECT-TYPE
	SYNTAX	 CounterBasedGauge64
	MAX-ACCESS  read-only
	STATUS      current
	DESCRIPTION
	"Table entry attribute for tcpv6SynExisting"
	::={tcpv6SynExistingLevelEntry 4}


tcpv6SegmentAllocFail	OBJECT IDENTIFIER ::={tcpv6 33}

tcpv6SegmentAllocFailVal	OBJECT-TYPE
	SYNTAX	 Counter64
	MAX-ACCESS read-only
	STATUS current
	DESCRIPTION "Segment allocation failures"

	::={tcpv6SegmentAllocFail 1}

tcpv6SegmentAllocFailMom	OBJECT-TYPE
	SYNTAX	 CounterBasedGauge64
	MAX-ACCESS read-only
	STATUS current
	DESCRIPTION "Segment allocation failures"

	::={tcpv6SegmentAllocFail 2}

tcpv6SegmentAllocFailMax	OBJECT-TYPE
	SYNTAX	 CounterBasedGauge64
	MAX-ACCESS read-only
	STATUS current
	DESCRIPTION "Segment allocation failures"

	::={tcpv6SegmentAllocFail 3}

tcpv6SegmentAllocFailLevelTable OBJECT-TYPE
	SYNTAX      SEQUENCE OF Tcpv6SegmentAllocFailLevelEntry
	MAX-ACCESS  not-accessible
	STATUS      current
	DESCRIPTION
	"Table for tcpv6SegmentAllocFail"
	::={tcpv6SegmentAllocFail 4}

tcpv6SegmentAllocFailLevelEntry OBJECT-TYPE
	SYNTAX      Tcpv6SegmentAllocFailLevelEntry
	MAX-ACCESS  not-accessible
	STATUS      current
	DESCRIPTION
	"Table entry for tcpv6SegmentAllocFail"
	INDEX { tcpv6SegmentAllocFailLevelName }
	::={tcpv6SegmentAllocFailLevelTable 1}

Tcpv6SegmentAllocFailLevelEntry ::=
	SEQUENCE {
		tcpv6SegmentAllocFailLevelName	DisplayString,
		tcpv6SegmentAllocFailLevelVal	Counter64,
		tcpv6SegmentAllocFailLevelMom	CounterBasedGauge64,
		tcpv6SegmentAllocFailLevelMax	CounterBasedGauge64
	}

tcpv6SegmentAllocFailLevelName OBJECT-TYPE
	SYNTAX      DisplayString
	MAX-ACCESS  not-accessible
	STATUS      current
	DESCRIPTION
	"Table entry display string for tcpv6SegmentAllocFail"
	::={tcpv6SegmentAllocFailLevelEntry 1}

tcpv6SegmentAllocFailLevelVal OBJECT-TYPE
	SYNTAX	 Counter64
	MAX-ACCESS  read-only
	STATUS      current
	DESCRIPTION
	"Table entry attribute for tcpv6SegmentAllocFail"
	::={tcpv6SegmentAllocFailLevelEntry 2}

tcpv6SegmentAllocFailLevelMom OBJECT-TYPE
	SYNTAX	 CounterBasedGauge64
	MAX-ACCESS  read-only
	STATUS      current
	DESCRIPTION
	"Table entry attribute for tcpv6SegmentAllocFail"
	::={tcpv6SegmentAllocFailLevelEntry 3}

tcpv6SegmentAllocFailLevelMax OBJECT-TYPE
	SYNTAX	 CounterBasedGauge64
	MAX-ACCESS  read-only
	STATUS      current
	DESCRIPTION
	"Table entry attribute for tcpv6SegmentAllocFail"
	::={tcpv6SegmentAllocFailLevelEntry 4}


tcpv6EnqueuedSegments	OBJECT IDENTIFIER ::={tcpv6 34}

tcpv6EnqueuedSegmentsVal	OBJECT-TYPE
	SYNTAX	 Counter64
	MAX-ACCESS read-only
	STATUS current
	DESCRIPTION "Enqueued segments"

	::={tcpv6EnqueuedSegments 1}

tcpv6EnqueuedSegmentsMom	OBJECT-TYPE
	SYNTAX	 CounterBasedGauge64
	MAX-ACCESS read-only
	STATUS current
	DESCRIPTION "Enqueued segments"

	::={tcpv6EnqueuedSegments 2}

tcpv6EnqueuedSegmentsMax	OBJECT-TYPE
	SYNTAX	 CounterBasedGauge64
	MAX-ACCESS read-only
	STATUS current
	DESCRIPTION "Enqueued segments"

	::={tcpv6EnqueuedSegments 3}

tcpv6EnqueuedSegmentsLevelTable OBJECT-TYPE
	SYNTAX      SEQUENCE OF Tcpv6EnqueuedSegmentsLevelEntry
	MAX-ACCESS  not-accessible
	STATUS      current
	DESCRIPTION
	"Table for tcpv6EnqueuedSegments"
	::={tcpv6EnqueuedSegments 4}

tcpv6EnqueuedSegmentsLevelEntry OBJECT-TYPE
	SYNTAX      Tcpv6EnqueuedSegmentsLevelEntry
	MAX-ACCESS  not-accessible
	STATUS      current
	DESCRIPTION
	"Table entry for tcpv6EnqueuedSegments"
	INDEX { tcpv6EnqueuedSegmentsLevelName }
	::={tcpv6EnqueuedSegmentsLevelTable 1}

Tcpv6EnqueuedSegmentsLevelEntry ::=
	SEQUENCE {
		tcpv6EnqueuedSegmentsLevelName	DisplayString,
		tcpv6EnqueuedSegmentsLevelVal	Counter64,
		tcpv6EnqueuedSegmentsLevelMom	CounterBasedGauge64,
		tcpv6EnqueuedSegmentsLevelMax	CounterBasedGauge64
	}

tcpv6EnqueuedSegmentsLevelName OBJECT-TYPE
	SYNTAX      DisplayString
	MAX-ACCESS  not-accessible
	STATUS      current
	DESCRIPTION
	"Table entry display string for tcpv6EnqueuedSegments"
	::={tcpv6EnqueuedSegmentsLevelEntry 1}

tcpv6EnqueuedSegmentsLevelVal OBJECT-TYPE
	SYNTAX	 Counter64
	MAX-ACCESS  read-only
	STATUS      current
	DESCRIPTION
	"Table entry attribute for tcpv6EnqueuedSegments"
	::={tcpv6EnqueuedSegmentsLevelEntry 2}

tcpv6EnqueuedSegmentsLevelMom OBJECT-TYPE
	SYNTAX	 CounterBasedGauge64
	MAX-ACCESS  read-only
	STATUS      current
	DESCRIPTION
	"Table entry attribute for tcpv6EnqueuedSegments"
	::={tcpv6EnqueuedSegmentsLevelEntry 3}

tcpv6EnqueuedSegmentsLevelMax OBJECT-TYPE
	SYNTAX	 CounterBasedGauge64
	MAX-ACCESS  read-only
	STATUS      current
	DESCRIPTION
	"Table entry attribute for tcpv6EnqueuedSegments"
	::={tcpv6EnqueuedSegmentsLevelEntry 4}


tcpv6DequeuedSegments	OBJECT IDENTIFIER ::={tcpv6 35}

tcpv6DequeuedSegmentsVal	OBJECT-TYPE
	SYNTAX	 Counter64
	MAX-ACCESS read-only
	STATUS current
	DESCRIPTION "Dequeued segments"

	::={tcpv6DequeuedSegments 1}

tcpv6DequeuedSegmentsMom	OBJECT-TYPE
	SYNTAX	 CounterBasedGauge64
	MAX-ACCESS read-only
	STATUS current
	DESCRIPTION "Dequeued segments"

	::={tcpv6DequeuedSegments 2}

tcpv6DequeuedSegmentsMax	OBJECT-TYPE
	SYNTAX	 CounterBasedGauge64
	MAX-ACCESS read-only
	STATUS current
	DESCRIPTION "Dequeued segments"

	::={tcpv6DequeuedSegments 3}

tcpv6DequeuedSegmentsLevelTable OBJECT-TYPE
	SYNTAX      SEQUENCE OF Tcpv6DequeuedSegmentsLevelEntry
	MAX-ACCESS  not-accessible
	STATUS      current
	DESCRIPTION
	"Table for tcpv6DequeuedSegments"
	::={tcpv6DequeuedSegments 4}

tcpv6DequeuedSegmentsLevelEntry OBJECT-TYPE
	SYNTAX      Tcpv6DequeuedSegmentsLevelEntry
	MAX-ACCESS  not-accessible
	STATUS      current
	DESCRIPTION
	"Table entry for tcpv6DequeuedSegments"
	INDEX { tcpv6DequeuedSegmentsLevelName }
	::={tcpv6DequeuedSegmentsLevelTable 1}

Tcpv6DequeuedSegmentsLevelEntry ::=
	SEQUENCE {
		tcpv6DequeuedSegmentsLevelName	DisplayString,
		tcpv6DequeuedSegmentsLevelVal	Counter64,
		tcpv6DequeuedSegmentsLevelMom	CounterBasedGauge64,
		tcpv6DequeuedSegmentsLevelMax	CounterBasedGauge64
	}

tcpv6DequeuedSegmentsLevelName OBJECT-TYPE
	SYNTAX      DisplayString
	MAX-ACCESS  not-accessible
	STATUS      current
	DESCRIPTION
	"Table entry display string for tcpv6DequeuedSegments"
	::={tcpv6DequeuedSegmentsLevelEntry 1}

tcpv6DequeuedSegmentsLevelVal OBJECT-TYPE
	SYNTAX	 Counter64
	MAX-ACCESS  read-only
	STATUS      current
	DESCRIPTION
	"Table entry attribute for tcpv6DequeuedSegments"
	::={tcpv6DequeuedSegmentsLevelEntry 2}

tcpv6DequeuedSegmentsLevelMom OBJECT-TYPE
	SYNTAX	 CounterBasedGauge64
	MAX-ACCESS  read-only
	STATUS      current
	DESCRIPTION
	"Table entry attribute for tcpv6DequeuedSegments"
	::={tcpv6DequeuedSegmentsLevelEntry 3}

tcpv6DequeuedSegmentsLevelMax OBJECT-TYPE
	SYNTAX	 CounterBasedGauge64
	MAX-ACCESS  read-only
	STATUS      current
	DESCRIPTION
	"Table entry attribute for tcpv6DequeuedSegments"
	::={tcpv6DequeuedSegmentsLevelEntry 4}


tcpv6DiscardedSegments	OBJECT IDENTIFIER ::={tcpv6 36}

tcpv6DiscardedSegmentsVal	OBJECT-TYPE
	SYNTAX	 Counter64
	MAX-ACCESS read-only
	STATUS current
	DESCRIPTION "Discarded segments"

	::={tcpv6DiscardedSegments 1}

tcpv6DiscardedSegmentsMom	OBJECT-TYPE
	SYNTAX	 CounterBasedGauge64
	MAX-ACCESS read-only
	STATUS current
	DESCRIPTION "Discarded segments"

	::={tcpv6DiscardedSegments 2}

tcpv6DiscardedSegmentsMax	OBJECT-TYPE
	SYNTAX	 CounterBasedGauge64
	MAX-ACCESS read-only
	STATUS current
	DESCRIPTION "Discarded segments"

	::={tcpv6DiscardedSegments 3}

tcpv6DiscardedSegmentsLevelTable OBJECT-TYPE
	SYNTAX      SEQUENCE OF Tcpv6DiscardedSegmentsLevelEntry
	MAX-ACCESS  not-accessible
	STATUS      current
	DESCRIPTION
	"Table for tcpv6DiscardedSegments"
	::={tcpv6DiscardedSegments 4}

tcpv6DiscardedSegmentsLevelEntry OBJECT-TYPE
	SYNTAX      Tcpv6DiscardedSegmentsLevelEntry
	MAX-ACCESS  not-accessible
	STATUS      current
	DESCRIPTION
	"Table entry for tcpv6DiscardedSegments"
	INDEX { tcpv6DiscardedSegmentsLevelName }
	::={tcpv6DiscardedSegmentsLevelTable 1}

Tcpv6DiscardedSegmentsLevelEntry ::=
	SEQUENCE {
		tcpv6DiscardedSegmentsLevelName	DisplayString,
		tcpv6DiscardedSegmentsLevelVal	Counter64,
		tcpv6DiscardedSegmentsLevelMom	CounterBasedGauge64,
		tcpv6DiscardedSegmentsLevelMax	CounterBasedGauge64
	}

tcpv6DiscardedSegmentsLevelName OBJECT-TYPE
	SYNTAX      DisplayString
	MAX-ACCESS  not-accessible
	STATUS      current
	DESCRIPTION
	"Table entry display string for tcpv6DiscardedSegments"
	::={tcpv6DiscardedSegmentsLevelEntry 1}

tcpv6DiscardedSegmentsLevelVal OBJECT-TYPE
	SYNTAX	 Counter64
	MAX-ACCESS  read-only
	STATUS      current
	DESCRIPTION
	"Table entry attribute for tcpv6DiscardedSegments"
	::={tcpv6DiscardedSegmentsLevelEntry 2}

tcpv6DiscardedSegmentsLevelMom OBJECT-TYPE
	SYNTAX	 CounterBasedGauge64
	MAX-ACCESS  read-only
	STATUS      current
	DESCRIPTION
	"Table entry attribute for tcpv6DiscardedSegments"
	::={tcpv6DiscardedSegmentsLevelEntry 3}

tcpv6DiscardedSegmentsLevelMax OBJECT-TYPE
	SYNTAX	 CounterBasedGauge64
	MAX-ACCESS  read-only
	STATUS      current
	DESCRIPTION
	"Table entry attribute for tcpv6DiscardedSegments"
	::={tcpv6DiscardedSegmentsLevelEntry 4}


tcpv6EmptyPackets	OBJECT IDENTIFIER ::={tcpv6 37}

tcpv6EmptyPacketsVal	OBJECT-TYPE
	SYNTAX	 Counter64
	MAX-ACCESS read-only
	STATUS current
	DESCRIPTION "Packets without payload"

	::={tcpv6EmptyPackets 1}

tcpv6EmptyPacketsMom	OBJECT-TYPE
	SYNTAX	 CounterBasedGauge64
	MAX-ACCESS read-only
	STATUS current
	DESCRIPTION "Packets without payload"

	::={tcpv6EmptyPackets 2}

tcpv6EmptyPacketsMax	OBJECT-TYPE
	SYNTAX	 CounterBasedGauge64
	MAX-ACCESS read-only
	STATUS current
	DESCRIPTION "Packets without payload"

	::={tcpv6EmptyPackets 3}

tcpv6EmptyPacketsLevelTable OBJECT-TYPE
	SYNTAX      SEQUENCE OF Tcpv6EmptyPacketsLevelEntry
	MAX-ACCESS  not-accessible
	STATUS      current
	DESCRIPTION
	"Table for tcpv6EmptyPackets"
	::={tcpv6EmptyPackets 4}

tcpv6EmptyPacketsLevelEntry OBJECT-TYPE
	SYNTAX      Tcpv6EmptyPacketsLevelEntry
	MAX-ACCESS  not-accessible
	STATUS      current
	DESCRIPTION
	"Table entry for tcpv6EmptyPackets"
	INDEX { tcpv6EmptyPacketsLevelName }
	::={tcpv6EmptyPacketsLevelTable 1}

Tcpv6EmptyPacketsLevelEntry ::=
	SEQUENCE {
		tcpv6EmptyPacketsLevelName	DisplayString,
		tcpv6EmptyPacketsLevelVal	Counter64,
		tcpv6EmptyPacketsLevelMom	CounterBasedGauge64,
		tcpv6EmptyPacketsLevelMax	CounterBasedGauge64
	}

tcpv6EmptyPacketsLevelName OBJECT-TYPE
	SYNTAX      DisplayString
	MAX-ACCESS  not-accessible
	STATUS      current
	DESCRIPTION
	"Table entry display string for tcpv6EmptyPackets"
	::={tcpv6EmptyPacketsLevelEntry 1}

tcpv6EmptyPacketsLevelVal OBJECT-TYPE
	SYNTAX	 Counter64
	MAX-ACCESS  read-only
	STATUS      current
	DESCRIPTION
	"Table entry attribute for tcpv6EmptyPackets"
	::={tcpv6EmptyPacketsLevelEntry 2}

tcpv6EmptyPacketsLevelMom OBJECT-TYPE
	SYNTAX	 CounterBasedGauge64
	MAX-ACCESS  read-only
	STATUS      current
	DESCRIPTION
	"Table entry attribute for tcpv6EmptyPackets"
	::={tcpv6EmptyPacketsLevelEntry 3}

tcpv6EmptyPacketsLevelMax OBJECT-TYPE
	SYNTAX	 CounterBasedGauge64
	MAX-ACCESS  read-only
	STATUS      current
	DESCRIPTION
	"Table entry attribute for tcpv6EmptyPackets"
	::={tcpv6EmptyPacketsLevelEntry 4}


tcpv6OosPackets	OBJECT IDENTIFIER ::={tcpv6 38}

tcpv6OosPacketsVal	OBJECT-TYPE
	SYNTAX	 Counter64
	MAX-ACCESS read-only
	STATUS current
	DESCRIPTION "Out-of-sync packets"

	::={tcpv6OosPackets 1}

tcpv6OosPacketsMom	OBJECT-TYPE
	SYNTAX	 CounterBasedGauge64
	MAX-ACCESS read-only
	STATUS current
	DESCRIPTION "Out-of-sync packets"

	::={tcpv6OosPackets 2}

tcpv6OosPacketsMax	OBJECT-TYPE
	SYNTAX	 CounterBasedGauge64
	MAX-ACCESS read-only
	STATUS current
	DESCRIPTION "Out-of-sync packets"

	::={tcpv6OosPackets 3}

tcpv6OosPacketsLevelTable OBJECT-TYPE
	SYNTAX      SEQUENCE OF Tcpv6OosPacketsLevelEntry
	MAX-ACCESS  not-accessible
	STATUS      current
	DESCRIPTION
	"Table for tcpv6OosPackets"
	::={tcpv6OosPackets 4}

tcpv6OosPacketsLevelEntry OBJECT-TYPE
	SYNTAX      Tcpv6OosPacketsLevelEntry
	MAX-ACCESS  not-accessible
	STATUS      current
	DESCRIPTION
	"Table entry for tcpv6OosPackets"
	INDEX { tcpv6OosPacketsLevelName }
	::={tcpv6OosPacketsLevelTable 1}

Tcpv6OosPacketsLevelEntry ::=
	SEQUENCE {
		tcpv6OosPacketsLevelName	DisplayString,
		tcpv6OosPacketsLevelVal	Counter64,
		tcpv6OosPacketsLevelMom	CounterBasedGauge64,
		tcpv6OosPacketsLevelMax	CounterBasedGauge64
	}

tcpv6OosPacketsLevelName OBJECT-TYPE
	SYNTAX      DisplayString
	MAX-ACCESS  not-accessible
	STATUS      current
	DESCRIPTION
	"Table entry display string for tcpv6OosPackets"
	::={tcpv6OosPacketsLevelEntry 1}

tcpv6OosPacketsLevelVal OBJECT-TYPE
	SYNTAX	 Counter64
	MAX-ACCESS  read-only
	STATUS      current
	DESCRIPTION
	"Table entry attribute for tcpv6OosPackets"
	::={tcpv6OosPacketsLevelEntry 2}

tcpv6OosPacketsLevelMom OBJECT-TYPE
	SYNTAX	 CounterBasedGauge64
	MAX-ACCESS  read-only
	STATUS      current
	DESCRIPTION
	"Table entry attribute for tcpv6OosPackets"
	::={tcpv6OosPacketsLevelEntry 3}

tcpv6OosPacketsLevelMax OBJECT-TYPE
	SYNTAX	 CounterBasedGauge64
	MAX-ACCESS  read-only
	STATUS      current
	DESCRIPTION
	"Table entry attribute for tcpv6OosPackets"
	::={tcpv6OosPacketsLevelEntry 4}


tcpv6OosBytes	OBJECT IDENTIFIER ::={tcpv6 39}

tcpv6OosBytesVal	OBJECT-TYPE
	SYNTAX	 Counter64
	MAX-ACCESS read-only
	STATUS current
	DESCRIPTION "Out-of-sync bytes"

	::={tcpv6OosBytes 1}

tcpv6OosBytesMom	OBJECT-TYPE
	SYNTAX	 CounterBasedGauge64
	MAX-ACCESS read-only
	STATUS current
	DESCRIPTION "Out-of-sync bytes"

	::={tcpv6OosBytes 2}

tcpv6OosBytesMax	OBJECT-TYPE
	SYNTAX	 CounterBasedGauge64
	MAX-ACCESS read-only
	STATUS current
	DESCRIPTION "Out-of-sync bytes"

	::={tcpv6OosBytes 3}

tcpv6OosBytesLevelTable OBJECT-TYPE
	SYNTAX      SEQUENCE OF Tcpv6OosBytesLevelEntry
	MAX-ACCESS  not-accessible
	STATUS      current
	DESCRIPTION
	"Table for tcpv6OosBytes"
	::={tcpv6OosBytes 4}

tcpv6OosBytesLevelEntry OBJECT-TYPE
	SYNTAX      Tcpv6OosBytesLevelEntry
	MAX-ACCESS  not-accessible
	STATUS      current
	DESCRIPTION
	"Table entry for tcpv6OosBytes"
	INDEX { tcpv6OosBytesLevelName }
	::={tcpv6OosBytesLevelTable 1}

Tcpv6OosBytesLevelEntry ::=
	SEQUENCE {
		tcpv6OosBytesLevelName	DisplayString,
		tcpv6OosBytesLevelVal	Counter64,
		tcpv6OosBytesLevelMom	CounterBasedGauge64,
		tcpv6OosBytesLevelMax	CounterBasedGauge64
	}

tcpv6OosBytesLevelName OBJECT-TYPE
	SYNTAX      DisplayString
	MAX-ACCESS  not-accessible
	STATUS      current
	DESCRIPTION
	"Table entry display string for tcpv6OosBytes"
	::={tcpv6OosBytesLevelEntry 1}

tcpv6OosBytesLevelVal OBJECT-TYPE
	SYNTAX	 Counter64
	MAX-ACCESS  read-only
	STATUS      current
	DESCRIPTION
	"Table entry attribute for tcpv6OosBytes"
	::={tcpv6OosBytesLevelEntry 2}

tcpv6OosBytesLevelMom OBJECT-TYPE
	SYNTAX	 CounterBasedGauge64
	MAX-ACCESS  read-only
	STATUS      current
	DESCRIPTION
	"Table entry attribute for tcpv6OosBytes"
	::={tcpv6OosBytesLevelEntry 3}

tcpv6OosBytesLevelMax OBJECT-TYPE
	SYNTAX	 CounterBasedGauge64
	MAX-ACCESS  read-only
	STATUS      current
	DESCRIPTION
	"Table entry attribute for tcpv6OosBytes"
	::={tcpv6OosBytesLevelEntry 4}


tcpv6Retransmits	OBJECT IDENTIFIER ::={tcpv6 40}

tcpv6RetransmitsVal	OBJECT-TYPE
	SYNTAX	 Counter64
	MAX-ACCESS read-only
	STATUS current
	DESCRIPTION "Retransmitted packets"

	::={tcpv6Retransmits 1}

tcpv6RetransmitsMom	OBJECT-TYPE
	SYNTAX	 CounterBasedGauge64
	MAX-ACCESS read-only
	STATUS current
	DESCRIPTION "Retransmitted packets"

	::={tcpv6Retransmits 2}

tcpv6RetransmitsMax	OBJECT-TYPE
	SYNTAX	 CounterBasedGauge64
	MAX-ACCESS read-only
	STATUS current
	DESCRIPTION "Retransmitted packets"

	::={tcpv6Retransmits 3}

tcpv6RetransmitsLevelTable OBJECT-TYPE
	SYNTAX      SEQUENCE OF Tcpv6RetransmitsLevelEntry
	MAX-ACCESS  not-accessible
	STATUS      current
	DESCRIPTION
	"Table for tcpv6Retransmits"
	::={tcpv6Retransmits 4}

tcpv6RetransmitsLevelEntry OBJECT-TYPE
	SYNTAX      Tcpv6RetransmitsLevelEntry
	MAX-ACCESS  not-accessible
	STATUS      current
	DESCRIPTION
	"Table entry for tcpv6Retransmits"
	INDEX { tcpv6RetransmitsLevelName }
	::={tcpv6RetransmitsLevelTable 1}

Tcpv6RetransmitsLevelEntry ::=
	SEQUENCE {
		tcpv6RetransmitsLevelName	DisplayString,
		tcpv6RetransmitsLevelVal	Counter64,
		tcpv6RetransmitsLevelMom	CounterBasedGauge64,
		tcpv6RetransmitsLevelMax	CounterBasedGauge64
	}

tcpv6RetransmitsLevelName OBJECT-TYPE
	SYNTAX      DisplayString
	MAX-ACCESS  not-accessible
	STATUS      current
	DESCRIPTION
	"Table entry display string for tcpv6Retransmits"
	::={tcpv6RetransmitsLevelEntry 1}

tcpv6RetransmitsLevelVal OBJECT-TYPE
	SYNTAX	 Counter64
	MAX-ACCESS  read-only
	STATUS      current
	DESCRIPTION
	"Table entry attribute for tcpv6Retransmits"
	::={tcpv6RetransmitsLevelEntry 2}

tcpv6RetransmitsLevelMom OBJECT-TYPE
	SYNTAX	 CounterBasedGauge64
	MAX-ACCESS  read-only
	STATUS      current
	DESCRIPTION
	"Table entry attribute for tcpv6Retransmits"
	::={tcpv6RetransmitsLevelEntry 3}

tcpv6RetransmitsLevelMax OBJECT-TYPE
	SYNTAX	 CounterBasedGauge64
	MAX-ACCESS  read-only
	STATUS      current
	DESCRIPTION
	"Table entry attribute for tcpv6Retransmits"
	::={tcpv6RetransmitsLevelEntry 4}


tcpv6Cwr	OBJECT IDENTIFIER ::={tcpv6 41}

tcpv6CwrVal	OBJECT-TYPE
	SYNTAX	 Counter64
	MAX-ACCESS read-only
	STATUS current
	DESCRIPTION "Congestion Window Reduced Packets"

	::={tcpv6Cwr 1}

tcpv6CwrMom	OBJECT-TYPE
	SYNTAX	 CounterBasedGauge64
	MAX-ACCESS read-only
	STATUS current
	DESCRIPTION "Congestion Window Reduced Packets"

	::={tcpv6Cwr 2}

tcpv6CwrMax	OBJECT-TYPE
	SYNTAX	 CounterBasedGauge64
	MAX-ACCESS read-only
	STATUS current
	DESCRIPTION "Congestion Window Reduced Packets"

	::={tcpv6Cwr 3}

tcpv6CwrLevelTable OBJECT-TYPE
	SYNTAX      SEQUENCE OF Tcpv6CwrLevelEntry
	MAX-ACCESS  not-accessible
	STATUS      current
	DESCRIPTION
	"Table for tcpv6Cwr"
	::={tcpv6Cwr 4}

tcpv6CwrLevelEntry OBJECT-TYPE
	SYNTAX      Tcpv6CwrLevelEntry
	MAX-ACCESS  not-accessible
	STATUS      current
	DESCRIPTION
	"Table entry for tcpv6Cwr"
	INDEX { tcpv6CwrLevelName }
	::={tcpv6CwrLevelTable 1}

Tcpv6CwrLevelEntry ::=
	SEQUENCE {
		tcpv6CwrLevelName	DisplayString,
		tcpv6CwrLevelVal	Counter64,
		tcpv6CwrLevelMom	CounterBasedGauge64,
		tcpv6CwrLevelMax	CounterBasedGauge64
	}

tcpv6CwrLevelName OBJECT-TYPE
	SYNTAX      DisplayString
	MAX-ACCESS  not-accessible
	STATUS      current
	DESCRIPTION
	"Table entry display string for tcpv6Cwr"
	::={tcpv6CwrLevelEntry 1}

tcpv6CwrLevelVal OBJECT-TYPE
	SYNTAX	 Counter64
	MAX-ACCESS  read-only
	STATUS      current
	DESCRIPTION
	"Table entry attribute for tcpv6Cwr"
	::={tcpv6CwrLevelEntry 2}

tcpv6CwrLevelMom OBJECT-TYPE
	SYNTAX	 CounterBasedGauge64
	MAX-ACCESS  read-only
	STATUS      current
	DESCRIPTION
	"Table entry attribute for tcpv6Cwr"
	::={tcpv6CwrLevelEntry 3}

tcpv6CwrLevelMax OBJECT-TYPE
	SYNTAX	 CounterBasedGauge64
	MAX-ACCESS  read-only
	STATUS      current
	DESCRIPTION
	"Table entry attribute for tcpv6Cwr"
	::={tcpv6CwrLevelEntry 4}


tcpv6Ecne	OBJECT IDENTIFIER ::={tcpv6 42}

tcpv6EcneVal	OBJECT-TYPE
	SYNTAX	 Counter64
	MAX-ACCESS read-only
	STATUS current
	DESCRIPTION "Explicit Congestion Notification Echo Packets"

	::={tcpv6Ecne 1}

tcpv6EcneMom	OBJECT-TYPE
	SYNTAX	 CounterBasedGauge64
	MAX-ACCESS read-only
	STATUS current
	DESCRIPTION "Explicit Congestion Notification Echo Packets"

	::={tcpv6Ecne 2}

tcpv6EcneMax	OBJECT-TYPE
	SYNTAX	 CounterBasedGauge64
	MAX-ACCESS read-only
	STATUS current
	DESCRIPTION "Explicit Congestion Notification Echo Packets"

	::={tcpv6Ecne 3}

tcpv6EcneLevelTable OBJECT-TYPE
	SYNTAX      SEQUENCE OF Tcpv6EcneLevelEntry
	MAX-ACCESS  not-accessible
	STATUS      current
	DESCRIPTION
	"Table for tcpv6Ecne"
	::={tcpv6Ecne 4}

tcpv6EcneLevelEntry OBJECT-TYPE
	SYNTAX      Tcpv6EcneLevelEntry
	MAX-ACCESS  not-accessible
	STATUS      current
	DESCRIPTION
	"Table entry for tcpv6Ecne"
	INDEX { tcpv6EcneLevelName }
	::={tcpv6EcneLevelTable 1}

Tcpv6EcneLevelEntry ::=
	SEQUENCE {
		tcpv6EcneLevelName	DisplayString,
		tcpv6EcneLevelVal	Counter64,
		tcpv6EcneLevelMom	CounterBasedGauge64,
		tcpv6EcneLevelMax	CounterBasedGauge64
	}

tcpv6EcneLevelName OBJECT-TYPE
	SYNTAX      DisplayString
	MAX-ACCESS  not-accessible
	STATUS      current
	DESCRIPTION
	"Table entry display string for tcpv6Ecne"
	::={tcpv6EcneLevelEntry 1}

tcpv6EcneLevelVal OBJECT-TYPE
	SYNTAX	 Counter64
	MAX-ACCESS  read-only
	STATUS      current
	DESCRIPTION
	"Table entry attribute for tcpv6Ecne"
	::={tcpv6EcneLevelEntry 2}

tcpv6EcneLevelMom OBJECT-TYPE
	SYNTAX	 CounterBasedGauge64
	MAX-ACCESS  read-only
	STATUS      current
	DESCRIPTION
	"Table entry attribute for tcpv6Ecne"
	::={tcpv6EcneLevelEntry 3}

tcpv6EcneLevelMax OBJECT-TYPE
	SYNTAX	 CounterBasedGauge64
	MAX-ACCESS  read-only
	STATUS      current
	DESCRIPTION
	"Table entry attribute for tcpv6Ecne"
	::={tcpv6EcneLevelEntry 4}


tcpv6SimOpen	OBJECT IDENTIFIER ::={tcpv6 43}

tcpv6SimOpenVal	OBJECT-TYPE
	SYNTAX	 Counter64
	MAX-ACCESS read-only
	STATUS current
	DESCRIPTION "Simultaneous Open"

	::={tcpv6SimOpen 1}

tcpv6SimOpenMom	OBJECT-TYPE
	SYNTAX	 CounterBasedGauge64
	MAX-ACCESS read-only
	STATUS current
	DESCRIPTION "Simultaneous Open"

	::={tcpv6SimOpen 2}

tcpv6SimOpenMax	OBJECT-TYPE
	SYNTAX	 CounterBasedGauge64
	MAX-ACCESS read-only
	STATUS current
	DESCRIPTION "Simultaneous Open"

	::={tcpv6SimOpen 3}

tcpv6SimOpenLevelTable OBJECT-TYPE
	SYNTAX      SEQUENCE OF Tcpv6SimOpenLevelEntry
	MAX-ACCESS  not-accessible
	STATUS      current
	DESCRIPTION
	"Table for tcpv6SimOpen"
	::={tcpv6SimOpen 4}

tcpv6SimOpenLevelEntry OBJECT-TYPE
	SYNTAX      Tcpv6SimOpenLevelEntry
	MAX-ACCESS  not-accessible
	STATUS      current
	DESCRIPTION
	"Table entry for tcpv6SimOpen"
	INDEX { tcpv6SimOpenLevelName }
	::={tcpv6SimOpenLevelTable 1}

Tcpv6SimOpenLevelEntry ::=
	SEQUENCE {
		tcpv6SimOpenLevelName	DisplayString,
		tcpv6SimOpenLevelVal	Counter64,
		tcpv6SimOpenLevelMom	CounterBasedGauge64,
		tcpv6SimOpenLevelMax	CounterBasedGauge64
	}

tcpv6SimOpenLevelName OBJECT-TYPE
	SYNTAX      DisplayString
	MAX-ACCESS  not-accessible
	STATUS      current
	DESCRIPTION
	"Table entry display string for tcpv6SimOpen"
	::={tcpv6SimOpenLevelEntry 1}

tcpv6SimOpenLevelVal OBJECT-TYPE
	SYNTAX	 Counter64
	MAX-ACCESS  read-only
	STATUS      current
	DESCRIPTION
	"Table entry attribute for tcpv6SimOpen"
	::={tcpv6SimOpenLevelEntry 2}

tcpv6SimOpenLevelMom OBJECT-TYPE
	SYNTAX	 CounterBasedGauge64
	MAX-ACCESS  read-only
	STATUS      current
	DESCRIPTION
	"Table entry attribute for tcpv6SimOpen"
	::={tcpv6SimOpenLevelEntry 3}

tcpv6SimOpenLevelMax OBJECT-TYPE
	SYNTAX	 CounterBasedGauge64
	MAX-ACCESS  read-only
	STATUS      current
	DESCRIPTION
	"Table entry attribute for tcpv6SimOpen"
	::={tcpv6SimOpenLevelEntry 4}


tcpv6Reopened	OBJECT IDENTIFIER ::={tcpv6 44}

tcpv6ReopenedVal	OBJECT-TYPE
	SYNTAX	 Counter64
	MAX-ACCESS read-only
	STATUS current
	DESCRIPTION "Connections reopened"

	::={tcpv6Reopened 1}

tcpv6ReopenedMom	OBJECT-TYPE
	SYNTAX	 CounterBasedGauge64
	MAX-ACCESS read-only
	STATUS current
	DESCRIPTION "Connections reopened"

	::={tcpv6Reopened 2}

tcpv6ReopenedMax	OBJECT-TYPE
	SYNTAX	 CounterBasedGauge64
	MAX-ACCESS read-only
	STATUS current
	DESCRIPTION "Connections reopened"

	::={tcpv6Reopened 3}

tcpv6ReopenedLevelTable OBJECT-TYPE
	SYNTAX      SEQUENCE OF Tcpv6ReopenedLevelEntry
	MAX-ACCESS  not-accessible
	STATUS      current
	DESCRIPTION
	"Table for tcpv6Reopened"
	::={tcpv6Reopened 4}

tcpv6ReopenedLevelEntry OBJECT-TYPE
	SYNTAX      Tcpv6ReopenedLevelEntry
	MAX-ACCESS  not-accessible
	STATUS      current
	DESCRIPTION
	"Table entry for tcpv6Reopened"
	INDEX { tcpv6ReopenedLevelName }
	::={tcpv6ReopenedLevelTable 1}

Tcpv6ReopenedLevelEntry ::=
	SEQUENCE {
		tcpv6ReopenedLevelName	DisplayString,
		tcpv6ReopenedLevelVal	Counter64,
		tcpv6ReopenedLevelMom	CounterBasedGauge64,
		tcpv6ReopenedLevelMax	CounterBasedGauge64
	}

tcpv6ReopenedLevelName OBJECT-TYPE
	SYNTAX      DisplayString
	MAX-ACCESS  not-accessible
	STATUS      current
	DESCRIPTION
	"Table entry display string for tcpv6Reopened"
	::={tcpv6ReopenedLevelEntry 1}

tcpv6ReopenedLevelVal OBJECT-TYPE
	SYNTAX	 Counter64
	MAX-ACCESS  read-only
	STATUS      current
	DESCRIPTION
	"Table entry attribute for tcpv6Reopened"
	::={tcpv6ReopenedLevelEntry 2}

tcpv6ReopenedLevelMom OBJECT-TYPE
	SYNTAX	 CounterBasedGauge64
	MAX-ACCESS  read-only
	STATUS      current
	DESCRIPTION
	"Table entry attribute for tcpv6Reopened"
	::={tcpv6ReopenedLevelEntry 3}

tcpv6ReopenedLevelMax OBJECT-TYPE
	SYNTAX	 CounterBasedGauge64
	MAX-ACCESS  read-only
	STATUS      current
	DESCRIPTION
	"Table entry attribute for tcpv6Reopened"
	::={tcpv6ReopenedLevelEntry 4}


tcpv6TsPacket	OBJECT IDENTIFIER ::={tcpv6 45}

tcpv6TsPacketVal	OBJECT-TYPE
	SYNTAX	 Counter64
	MAX-ACCESS read-only
	STATUS current
	DESCRIPTION "Packets with Time Stamp Option"

	::={tcpv6TsPacket 1}

tcpv6TsPacketMom	OBJECT-TYPE
	SYNTAX	 CounterBasedGauge64
	MAX-ACCESS read-only
	STATUS current
	DESCRIPTION "Packets with Time Stamp Option"

	::={tcpv6TsPacket 2}

tcpv6TsPacketMax	OBJECT-TYPE
	SYNTAX	 CounterBasedGauge64
	MAX-ACCESS read-only
	STATUS current
	DESCRIPTION "Packets with Time Stamp Option"

	::={tcpv6TsPacket 3}

tcpv6TsPacketLevelTable OBJECT-TYPE
	SYNTAX      SEQUENCE OF Tcpv6TsPacketLevelEntry
	MAX-ACCESS  not-accessible
	STATUS      current
	DESCRIPTION
	"Table for tcpv6TsPacket"
	::={tcpv6TsPacket 4}

tcpv6TsPacketLevelEntry OBJECT-TYPE
	SYNTAX      Tcpv6TsPacketLevelEntry
	MAX-ACCESS  not-accessible
	STATUS      current
	DESCRIPTION
	"Table entry for tcpv6TsPacket"
	INDEX { tcpv6TsPacketLevelName }
	::={tcpv6TsPacketLevelTable 1}

Tcpv6TsPacketLevelEntry ::=
	SEQUENCE {
		tcpv6TsPacketLevelName	DisplayString,
		tcpv6TsPacketLevelVal	Counter64,
		tcpv6TsPacketLevelMom	CounterBasedGauge64,
		tcpv6TsPacketLevelMax	CounterBasedGauge64
	}

tcpv6TsPacketLevelName OBJECT-TYPE
	SYNTAX      DisplayString
	MAX-ACCESS  not-accessible
	STATUS      current
	DESCRIPTION
	"Table entry display string for tcpv6TsPacket"
	::={tcpv6TsPacketLevelEntry 1}

tcpv6TsPacketLevelVal OBJECT-TYPE
	SYNTAX	 Counter64
	MAX-ACCESS  read-only
	STATUS      current
	DESCRIPTION
	"Table entry attribute for tcpv6TsPacket"
	::={tcpv6TsPacketLevelEntry 2}

tcpv6TsPacketLevelMom OBJECT-TYPE
	SYNTAX	 CounterBasedGauge64
	MAX-ACCESS  read-only
	STATUS      current
	DESCRIPTION
	"Table entry attribute for tcpv6TsPacket"
	::={tcpv6TsPacketLevelEntry 3}

tcpv6TsPacketLevelMax OBJECT-TYPE
	SYNTAX	 CounterBasedGauge64
	MAX-ACCESS  read-only
	STATUS      current
	DESCRIPTION
	"Table entry attribute for tcpv6TsPacket"
	::={tcpv6TsPacketLevelEntry 4}


tcpv6TsCalibrationSuccess	OBJECT IDENTIFIER ::={tcpv6 46}

tcpv6TsCalibrationSuccessVal	OBJECT-TYPE
	SYNTAX	 Counter64
	MAX-ACCESS read-only
	STATUS current
	DESCRIPTION "Successfull RTT Calibration"

	::={tcpv6TsCalibrationSuccess 1}

tcpv6TsCalibrationSuccessMom	OBJECT-TYPE
	SYNTAX	 CounterBasedGauge64
	MAX-ACCESS read-only
	STATUS current
	DESCRIPTION "Successfull RTT Calibration"

	::={tcpv6TsCalibrationSuccess 2}

tcpv6TsCalibrationSuccessMax	OBJECT-TYPE
	SYNTAX	 CounterBasedGauge64
	MAX-ACCESS read-only
	STATUS current
	DESCRIPTION "Successfull RTT Calibration"

	::={tcpv6TsCalibrationSuccess 3}

tcpv6TsCalibrationSuccessLevelTable OBJECT-TYPE
	SYNTAX      SEQUENCE OF Tcpv6TsCalibrationSuccessLevelEntry
	MAX-ACCESS  not-accessible
	STATUS      current
	DESCRIPTION
	"Table for tcpv6TsCalibrationSuccess"
	::={tcpv6TsCalibrationSuccess 4}

tcpv6TsCalibrationSuccessLevelEntry OBJECT-TYPE
	SYNTAX      Tcpv6TsCalibrationSuccessLevelEntry
	MAX-ACCESS  not-accessible
	STATUS      current
	DESCRIPTION
	"Table entry for tcpv6TsCalibrationSuccess"
	INDEX { tcpv6TsCalibrationSuccessLevelName }
	::={tcpv6TsCalibrationSuccessLevelTable 1}

Tcpv6TsCalibrationSuccessLevelEntry ::=
	SEQUENCE {
		tcpv6TsCalibrationSuccessLevelName	DisplayString,
		tcpv6TsCalibrationSuccessLevelVal	Counter64,
		tcpv6TsCalibrationSuccessLevelMom	CounterBasedGauge64,
		tcpv6TsCalibrationSuccessLevelMax	CounterBasedGauge64
	}

tcpv6TsCalibrationSuccessLevelName OBJECT-TYPE
	SYNTAX      DisplayString
	MAX-ACCESS  not-accessible
	STATUS      current
	DESCRIPTION
	"Table entry display string for tcpv6TsCalibrationSuccess"
	::={tcpv6TsCalibrationSuccessLevelEntry 1}

tcpv6TsCalibrationSuccessLevelVal OBJECT-TYPE
	SYNTAX	 Counter64
	MAX-ACCESS  read-only
	STATUS      current
	DESCRIPTION
	"Table entry attribute for tcpv6TsCalibrationSuccess"
	::={tcpv6TsCalibrationSuccessLevelEntry 2}

tcpv6TsCalibrationSuccessLevelMom OBJECT-TYPE
	SYNTAX	 CounterBasedGauge64
	MAX-ACCESS  read-only
	STATUS      current
	DESCRIPTION
	"Table entry attribute for tcpv6TsCalibrationSuccess"
	::={tcpv6TsCalibrationSuccessLevelEntry 3}

tcpv6TsCalibrationSuccessLevelMax OBJECT-TYPE
	SYNTAX	 CounterBasedGauge64
	MAX-ACCESS  read-only
	STATUS      current
	DESCRIPTION
	"Table entry attribute for tcpv6TsCalibrationSuccess"
	::={tcpv6TsCalibrationSuccessLevelEntry 4}


tcpv6TsCalibrationFail	OBJECT IDENTIFIER ::={tcpv6 47}

tcpv6TsCalibrationFailVal	OBJECT-TYPE
	SYNTAX	 Counter64
	MAX-ACCESS read-only
	STATUS current
	DESCRIPTION "Failed RTT Calibration"

	::={tcpv6TsCalibrationFail 1}

tcpv6TsCalibrationFailMom	OBJECT-TYPE
	SYNTAX	 CounterBasedGauge64
	MAX-ACCESS read-only
	STATUS current
	DESCRIPTION "Failed RTT Calibration"

	::={tcpv6TsCalibrationFail 2}

tcpv6TsCalibrationFailMax	OBJECT-TYPE
	SYNTAX	 CounterBasedGauge64
	MAX-ACCESS read-only
	STATUS current
	DESCRIPTION "Failed RTT Calibration"

	::={tcpv6TsCalibrationFail 3}

tcpv6TsCalibrationFailLevelTable OBJECT-TYPE
	SYNTAX      SEQUENCE OF Tcpv6TsCalibrationFailLevelEntry
	MAX-ACCESS  not-accessible
	STATUS      current
	DESCRIPTION
	"Table for tcpv6TsCalibrationFail"
	::={tcpv6TsCalibrationFail 4}

tcpv6TsCalibrationFailLevelEntry OBJECT-TYPE
	SYNTAX      Tcpv6TsCalibrationFailLevelEntry
	MAX-ACCESS  not-accessible
	STATUS      current
	DESCRIPTION
	"Table entry for tcpv6TsCalibrationFail"
	INDEX { tcpv6TsCalibrationFailLevelName }
	::={tcpv6TsCalibrationFailLevelTable 1}

Tcpv6TsCalibrationFailLevelEntry ::=
	SEQUENCE {
		tcpv6TsCalibrationFailLevelName	DisplayString,
		tcpv6TsCalibrationFailLevelVal	Counter64,
		tcpv6TsCalibrationFailLevelMom	CounterBasedGauge64,
		tcpv6TsCalibrationFailLevelMax	CounterBasedGauge64
	}

tcpv6TsCalibrationFailLevelName OBJECT-TYPE
	SYNTAX      DisplayString
	MAX-ACCESS  not-accessible
	STATUS      current
	DESCRIPTION
	"Table entry display string for tcpv6TsCalibrationFail"
	::={tcpv6TsCalibrationFailLevelEntry 1}

tcpv6TsCalibrationFailLevelVal OBJECT-TYPE
	SYNTAX	 Counter64
	MAX-ACCESS  read-only
	STATUS      current
	DESCRIPTION
	"Table entry attribute for tcpv6TsCalibrationFail"
	::={tcpv6TsCalibrationFailLevelEntry 2}

tcpv6TsCalibrationFailLevelMom OBJECT-TYPE
	SYNTAX	 CounterBasedGauge64
	MAX-ACCESS  read-only
	STATUS      current
	DESCRIPTION
	"Table entry attribute for tcpv6TsCalibrationFail"
	::={tcpv6TsCalibrationFailLevelEntry 3}

tcpv6TsCalibrationFailLevelMax OBJECT-TYPE
	SYNTAX	 CounterBasedGauge64
	MAX-ACCESS  read-only
	STATUS      current
	DESCRIPTION
	"Table entry attribute for tcpv6TsCalibrationFail"
	::={tcpv6TsCalibrationFailLevelEntry 4}


tcpv6SegmentsFailedDequeue	OBJECT IDENTIFIER ::={tcpv6 48}

tcpv6SegmentsFailedDequeueVal	OBJECT-TYPE
	SYNTAX	 Counter64
	MAX-ACCESS read-only
	STATUS current
	DESCRIPTION "Segments that failed to dequeue due to invalid TCP sequences"

	::={tcpv6SegmentsFailedDequeue 1}

tcpv6SegmentsFailedDequeueMom	OBJECT-TYPE
	SYNTAX	 CounterBasedGauge64
	MAX-ACCESS read-only
	STATUS current
	DESCRIPTION "Segments that failed to dequeue due to invalid TCP sequences"

	::={tcpv6SegmentsFailedDequeue 2}

tcpv6SegmentsFailedDequeueMax	OBJECT-TYPE
	SYNTAX	 CounterBasedGauge64
	MAX-ACCESS read-only
	STATUS current
	DESCRIPTION "Segments that failed to dequeue due to invalid TCP sequences"

	::={tcpv6SegmentsFailedDequeue 3}

tcpv6SegmentsFailedDequeueLevelTable OBJECT-TYPE
	SYNTAX      SEQUENCE OF Tcpv6SegmentsFailedDequeueLevelEntry
	MAX-ACCESS  not-accessible
	STATUS      current
	DESCRIPTION
	"Table for tcpv6SegmentsFailedDequeue"
	::={tcpv6SegmentsFailedDequeue 4}

tcpv6SegmentsFailedDequeueLevelEntry OBJECT-TYPE
	SYNTAX      Tcpv6SegmentsFailedDequeueLevelEntry
	MAX-ACCESS  not-accessible
	STATUS      current
	DESCRIPTION
	"Table entry for tcpv6SegmentsFailedDequeue"
	INDEX { tcpv6SegmentsFailedDequeueLevelName }
	::={tcpv6SegmentsFailedDequeueLevelTable 1}

Tcpv6SegmentsFailedDequeueLevelEntry ::=
	SEQUENCE {
		tcpv6SegmentsFailedDequeueLevelName	DisplayString,
		tcpv6SegmentsFailedDequeueLevelVal	Counter64,
		tcpv6SegmentsFailedDequeueLevelMom	CounterBasedGauge64,
		tcpv6SegmentsFailedDequeueLevelMax	CounterBasedGauge64
	}

tcpv6SegmentsFailedDequeueLevelName OBJECT-TYPE
	SYNTAX      DisplayString
	MAX-ACCESS  not-accessible
	STATUS      current
	DESCRIPTION
	"Table entry display string for tcpv6SegmentsFailedDequeue"
	::={tcpv6SegmentsFailedDequeueLevelEntry 1}

tcpv6SegmentsFailedDequeueLevelVal OBJECT-TYPE
	SYNTAX	 Counter64
	MAX-ACCESS  read-only
	STATUS      current
	DESCRIPTION
	"Table entry attribute for tcpv6SegmentsFailedDequeue"
	::={tcpv6SegmentsFailedDequeueLevelEntry 2}

tcpv6SegmentsFailedDequeueLevelMom OBJECT-TYPE
	SYNTAX	 CounterBasedGauge64
	MAX-ACCESS  read-only
	STATUS      current
	DESCRIPTION
	"Table entry attribute for tcpv6SegmentsFailedDequeue"
	::={tcpv6SegmentsFailedDequeueLevelEntry 3}

tcpv6SegmentsFailedDequeueLevelMax OBJECT-TYPE
	SYNTAX	 CounterBasedGauge64
	MAX-ACCESS  read-only
	STATUS      current
	DESCRIPTION
	"Table entry attribute for tcpv6SegmentsFailedDequeue"
	::={tcpv6SegmentsFailedDequeueLevelEntry 4}


tcpv6SegmentsFailedDequeueSkip	OBJECT IDENTIFIER ::={tcpv6 49}

tcpv6SegmentsFailedDequeueSkipVal	OBJECT-TYPE
	SYNTAX	 Counter64
	MAX-ACCESS read-only
	STATUS current
	DESCRIPTION "Segments that failed to dequeue due to DRDL skip state becoming out of sync"

	::={tcpv6SegmentsFailedDequeueSkip 1}

tcpv6SegmentsFailedDequeueSkipMom	OBJECT-TYPE
	SYNTAX	 CounterBasedGauge64
	MAX-ACCESS read-only
	STATUS current
	DESCRIPTION "Segments that failed to dequeue due to DRDL skip state becoming out of sync"

	::={tcpv6SegmentsFailedDequeueSkip 2}

tcpv6SegmentsFailedDequeueSkipMax	OBJECT-TYPE
	SYNTAX	 CounterBasedGauge64
	MAX-ACCESS read-only
	STATUS current
	DESCRIPTION "Segments that failed to dequeue due to DRDL skip state becoming out of sync"

	::={tcpv6SegmentsFailedDequeueSkip 3}

tcpv6SegmentsFailedDequeueSkipLevelTable OBJECT-TYPE
	SYNTAX      SEQUENCE OF Tcpv6SegmentsFailedDequeueSkipLevelEntry
	MAX-ACCESS  not-accessible
	STATUS      current
	DESCRIPTION
	"Table for tcpv6SegmentsFailedDequeueSkip"
	::={tcpv6SegmentsFailedDequeueSkip 4}

tcpv6SegmentsFailedDequeueSkipLevelEntry OBJECT-TYPE
	SYNTAX      Tcpv6SegmentsFailedDequeueSkipLevelEntry
	MAX-ACCESS  not-accessible
	STATUS      current
	DESCRIPTION
	"Table entry for tcpv6SegmentsFailedDequeueSkip"
	INDEX { tcpv6SegmentsFailedDequeueSkipLevelName }
	::={tcpv6SegmentsFailedDequeueSkipLevelTable 1}

Tcpv6SegmentsFailedDequeueSkipLevelEntry ::=
	SEQUENCE {
		tcpv6SegmentsFailedDequeueSkipLevelName	DisplayString,
		tcpv6SegmentsFailedDequeueSkipLevelVal	Counter64,
		tcpv6SegmentsFailedDequeueSkipLevelMom	CounterBasedGauge64,
		tcpv6SegmentsFailedDequeueSkipLevelMax	CounterBasedGauge64
	}

tcpv6SegmentsFailedDequeueSkipLevelName OBJECT-TYPE
	SYNTAX      DisplayString
	MAX-ACCESS  not-accessible
	STATUS      current
	DESCRIPTION
	"Table entry display string for tcpv6SegmentsFailedDequeueSkip"
	::={tcpv6SegmentsFailedDequeueSkipLevelEntry 1}

tcpv6SegmentsFailedDequeueSkipLevelVal OBJECT-TYPE
	SYNTAX	 Counter64
	MAX-ACCESS  read-only
	STATUS      current
	DESCRIPTION
	"Table entry attribute for tcpv6SegmentsFailedDequeueSkip"
	::={tcpv6SegmentsFailedDequeueSkipLevelEntry 2}

tcpv6SegmentsFailedDequeueSkipLevelMom OBJECT-TYPE
	SYNTAX	 CounterBasedGauge64
	MAX-ACCESS  read-only
	STATUS      current
	DESCRIPTION
	"Table entry attribute for tcpv6SegmentsFailedDequeueSkip"
	::={tcpv6SegmentsFailedDequeueSkipLevelEntry 3}

tcpv6SegmentsFailedDequeueSkipLevelMax OBJECT-TYPE
	SYNTAX	 CounterBasedGauge64
	MAX-ACCESS  read-only
	STATUS      current
	DESCRIPTION
	"Table entry attribute for tcpv6SegmentsFailedDequeueSkip"
	::={tcpv6SegmentsFailedDequeueSkipLevelEntry 4}


tcpv6SegmentsFailedDequeueTfo	OBJECT IDENTIFIER ::={tcpv6 50}

tcpv6SegmentsFailedDequeueTfoVal	OBJECT-TYPE
	SYNTAX	 Counter64
	MAX-ACCESS read-only
	STATUS current
	DESCRIPTION "Segments that failed to dequeue due invalid TFO state"

	::={tcpv6SegmentsFailedDequeueTfo 1}

tcpv6SegmentsFailedDequeueTfoMom	OBJECT-TYPE
	SYNTAX	 CounterBasedGauge64
	MAX-ACCESS read-only
	STATUS current
	DESCRIPTION "Segments that failed to dequeue due invalid TFO state"

	::={tcpv6SegmentsFailedDequeueTfo 2}

tcpv6SegmentsFailedDequeueTfoMax	OBJECT-TYPE
	SYNTAX	 CounterBasedGauge64
	MAX-ACCESS read-only
	STATUS current
	DESCRIPTION "Segments that failed to dequeue due invalid TFO state"

	::={tcpv6SegmentsFailedDequeueTfo 3}

tcpv6SegmentsFailedDequeueTfoLevelTable OBJECT-TYPE
	SYNTAX      SEQUENCE OF Tcpv6SegmentsFailedDequeueTfoLevelEntry
	MAX-ACCESS  not-accessible
	STATUS      current
	DESCRIPTION
	"Table for tcpv6SegmentsFailedDequeueTfo"
	::={tcpv6SegmentsFailedDequeueTfo 4}

tcpv6SegmentsFailedDequeueTfoLevelEntry OBJECT-TYPE
	SYNTAX      Tcpv6SegmentsFailedDequeueTfoLevelEntry
	MAX-ACCESS  not-accessible
	STATUS      current
	DESCRIPTION
	"Table entry for tcpv6SegmentsFailedDequeueTfo"
	INDEX { tcpv6SegmentsFailedDequeueTfoLevelName }
	::={tcpv6SegmentsFailedDequeueTfoLevelTable 1}

Tcpv6SegmentsFailedDequeueTfoLevelEntry ::=
	SEQUENCE {
		tcpv6SegmentsFailedDequeueTfoLevelName	DisplayString,
		tcpv6SegmentsFailedDequeueTfoLevelVal	Counter64,
		tcpv6SegmentsFailedDequeueTfoLevelMom	CounterBasedGauge64,
		tcpv6SegmentsFailedDequeueTfoLevelMax	CounterBasedGauge64
	}

tcpv6SegmentsFailedDequeueTfoLevelName OBJECT-TYPE
	SYNTAX      DisplayString
	MAX-ACCESS  not-accessible
	STATUS      current
	DESCRIPTION
	"Table entry display string for tcpv6SegmentsFailedDequeueTfo"
	::={tcpv6SegmentsFailedDequeueTfoLevelEntry 1}

tcpv6SegmentsFailedDequeueTfoLevelVal OBJECT-TYPE
	SYNTAX	 Counter64
	MAX-ACCESS  read-only
	STATUS      current
	DESCRIPTION
	"Table entry attribute for tcpv6SegmentsFailedDequeueTfo"
	::={tcpv6SegmentsFailedDequeueTfoLevelEntry 2}

tcpv6SegmentsFailedDequeueTfoLevelMom OBJECT-TYPE
	SYNTAX	 CounterBasedGauge64
	MAX-ACCESS  read-only
	STATUS      current
	DESCRIPTION
	"Table entry attribute for tcpv6SegmentsFailedDequeueTfo"
	::={tcpv6SegmentsFailedDequeueTfoLevelEntry 3}

tcpv6SegmentsFailedDequeueTfoLevelMax OBJECT-TYPE
	SYNTAX	 CounterBasedGauge64
	MAX-ACCESS  read-only
	STATUS      current
	DESCRIPTION
	"Table entry attribute for tcpv6SegmentsFailedDequeueTfo"
	::={tcpv6SegmentsFailedDequeueTfoLevelEntry 4}


connection	OBJECT IDENTIFIER ::={sysdiag 56}

connectionCount	OBJECT IDENTIFIER ::={connection 1}

connectionCountVal	OBJECT-TYPE
	SYNTAX	 CounterBasedGauge64
	MAX-ACCESS read-only
	STATUS current
	DESCRIPTION "Current count"

	::={connectionCount 1}

connectionCountMax	OBJECT-TYPE
	SYNTAX	 CounterBasedGauge64
	MAX-ACCESS read-only
	STATUS current
	DESCRIPTION "Current count"

	::={connectionCount 3}

connectionCountLevelTable OBJECT-TYPE
	SYNTAX      SEQUENCE OF ConnectionCountLevelEntry
	MAX-ACCESS  not-accessible
	STATUS      current
	DESCRIPTION
	"Table for connectionCount"
	::={connectionCount 4}

connectionCountLevelEntry OBJECT-TYPE
	SYNTAX      ConnectionCountLevelEntry
	MAX-ACCESS  not-accessible
	STATUS      current
	DESCRIPTION
	"Table entry for connectionCount"
	INDEX { connectionCountLevelName }
	::={connectionCountLevelTable 1}

ConnectionCountLevelEntry ::=
	SEQUENCE {
		connectionCountLevelName	DisplayString,
		connectionCountLevelVal	CounterBasedGauge64,
		connectionCountLevelMax	CounterBasedGauge64
	}

connectionCountLevelName OBJECT-TYPE
	SYNTAX      DisplayString
	MAX-ACCESS  not-accessible
	STATUS      current
	DESCRIPTION
	"Table entry display string for connectionCount"
	::={connectionCountLevelEntry 1}

connectionCountLevelVal OBJECT-TYPE
	SYNTAX	 CounterBasedGauge64
	MAX-ACCESS  read-only
	STATUS      current
	DESCRIPTION
	"Table entry attribute for connectionCount"
	::={connectionCountLevelEntry 2}

connectionCountLevelMax OBJECT-TYPE
	SYNTAX	 CounterBasedGauge64
	MAX-ACCESS  read-only
	STATUS      current
	DESCRIPTION
	"Table entry attribute for connectionCount"
	::={connectionCountLevelEntry 4}


connectionEstCount	OBJECT IDENTIFIER ::={connection 2}

connectionEstCountVal	OBJECT-TYPE
	SYNTAX	 CounterBasedGauge64
	MAX-ACCESS read-only
	STATUS current
	DESCRIPTION "Current established count"

	::={connectionEstCount 1}

connectionEstCountMax	OBJECT-TYPE
	SYNTAX	 CounterBasedGauge64
	MAX-ACCESS read-only
	STATUS current
	DESCRIPTION "Current established count"

	::={connectionEstCount 3}

connectionEstCountLevelTable OBJECT-TYPE
	SYNTAX      SEQUENCE OF ConnectionEstCountLevelEntry
	MAX-ACCESS  not-accessible
	STATUS      current
	DESCRIPTION
	"Table for connectionEstCount"
	::={connectionEstCount 4}

connectionEstCountLevelEntry OBJECT-TYPE
	SYNTAX      ConnectionEstCountLevelEntry
	MAX-ACCESS  not-accessible
	STATUS      current
	DESCRIPTION
	"Table entry for connectionEstCount"
	INDEX { connectionEstCountLevelName }
	::={connectionEstCountLevelTable 1}

ConnectionEstCountLevelEntry ::=
	SEQUENCE {
		connectionEstCountLevelName	DisplayString,
		connectionEstCountLevelVal	CounterBasedGauge64,
		connectionEstCountLevelMax	CounterBasedGauge64
	}

connectionEstCountLevelName OBJECT-TYPE
	SYNTAX      DisplayString
	MAX-ACCESS  not-accessible
	STATUS      current
	DESCRIPTION
	"Table entry display string for connectionEstCount"
	::={connectionEstCountLevelEntry 1}

connectionEstCountLevelVal OBJECT-TYPE
	SYNTAX	 CounterBasedGauge64
	MAX-ACCESS  read-only
	STATUS      current
	DESCRIPTION
	"Table entry attribute for connectionEstCount"
	::={connectionEstCountLevelEntry 2}

connectionEstCountLevelMax OBJECT-TYPE
	SYNTAX	 CounterBasedGauge64
	MAX-ACCESS  read-only
	STATUS      current
	DESCRIPTION
	"Table entry attribute for connectionEstCount"
	::={connectionEstCountLevelEntry 4}


connectionCreateAttemptsInbound	OBJECT IDENTIFIER ::={connection 3}

connectionCreateAttemptsInboundVal	OBJECT-TYPE
	SYNTAX	 Counter64
	MAX-ACCESS read-only
	STATUS current
	DESCRIPTION "Create attempts inbound"

	::={connectionCreateAttemptsInbound 1}

connectionCreateAttemptsInboundMom	OBJECT-TYPE
	SYNTAX	 CounterBasedGauge64
	MAX-ACCESS read-only
	STATUS current
	DESCRIPTION "Create attempts inbound"

	::={connectionCreateAttemptsInbound 2}

connectionCreateAttemptsInboundMax	OBJECT-TYPE
	SYNTAX	 CounterBasedGauge64
	MAX-ACCESS read-only
	STATUS current
	DESCRIPTION "Create attempts inbound"

	::={connectionCreateAttemptsInbound 3}

connectionCreateAttemptsInboundLevelTable OBJECT-TYPE
	SYNTAX      SEQUENCE OF ConnectionCreateAttemptsInboundLevelEntry
	MAX-ACCESS  not-accessible
	STATUS      current
	DESCRIPTION
	"Table for connectionCreateAttemptsInbound"
	::={connectionCreateAttemptsInbound 4}

connectionCreateAttemptsInboundLevelEntry OBJECT-TYPE
	SYNTAX      ConnectionCreateAttemptsInboundLevelEntry
	MAX-ACCESS  not-accessible
	STATUS      current
	DESCRIPTION
	"Table entry for connectionCreateAttemptsInbound"
	INDEX { connectionCreateAttemptsInboundLevelName }
	::={connectionCreateAttemptsInboundLevelTable 1}

ConnectionCreateAttemptsInboundLevelEntry ::=
	SEQUENCE {
		connectionCreateAttemptsInboundLevelName	DisplayString,
		connectionCreateAttemptsInboundLevelVal	Counter64,
		connectionCreateAttemptsInboundLevelMom	CounterBasedGauge64,
		connectionCreateAttemptsInboundLevelMax	CounterBasedGauge64
	}

connectionCreateAttemptsInboundLevelName OBJECT-TYPE
	SYNTAX      DisplayString
	MAX-ACCESS  not-accessible
	STATUS      current
	DESCRIPTION
	"Table entry display string for connectionCreateAttemptsInbound"
	::={connectionCreateAttemptsInboundLevelEntry 1}

connectionCreateAttemptsInboundLevelVal OBJECT-TYPE
	SYNTAX	 Counter64
	MAX-ACCESS  read-only
	STATUS      current
	DESCRIPTION
	"Table entry attribute for connectionCreateAttemptsInbound"
	::={connectionCreateAttemptsInboundLevelEntry 2}

connectionCreateAttemptsInboundLevelMom OBJECT-TYPE
	SYNTAX	 CounterBasedGauge64
	MAX-ACCESS  read-only
	STATUS      current
	DESCRIPTION
	"Table entry attribute for connectionCreateAttemptsInbound"
	::={connectionCreateAttemptsInboundLevelEntry 3}

connectionCreateAttemptsInboundLevelMax OBJECT-TYPE
	SYNTAX	 CounterBasedGauge64
	MAX-ACCESS  read-only
	STATUS      current
	DESCRIPTION
	"Table entry attribute for connectionCreateAttemptsInbound"
	::={connectionCreateAttemptsInboundLevelEntry 4}


connectionCreateAttemptsOutbound	OBJECT IDENTIFIER ::={connection 4}

connectionCreateAttemptsOutboundVal	OBJECT-TYPE
	SYNTAX	 Counter64
	MAX-ACCESS read-only
	STATUS current
	DESCRIPTION "Create attempts outbound"

	::={connectionCreateAttemptsOutbound 1}

connectionCreateAttemptsOutboundMom	OBJECT-TYPE
	SYNTAX	 CounterBasedGauge64
	MAX-ACCESS read-only
	STATUS current
	DESCRIPTION "Create attempts outbound"

	::={connectionCreateAttemptsOutbound 2}

connectionCreateAttemptsOutboundMax	OBJECT-TYPE
	SYNTAX	 CounterBasedGauge64
	MAX-ACCESS read-only
	STATUS current
	DESCRIPTION "Create attempts outbound"

	::={connectionCreateAttemptsOutbound 3}

connectionCreateAttemptsOutboundLevelTable OBJECT-TYPE
	SYNTAX      SEQUENCE OF ConnectionCreateAttemptsOutboundLevelEntry
	MAX-ACCESS  not-accessible
	STATUS      current
	DESCRIPTION
	"Table for connectionCreateAttemptsOutbound"
	::={connectionCreateAttemptsOutbound 4}

connectionCreateAttemptsOutboundLevelEntry OBJECT-TYPE
	SYNTAX      ConnectionCreateAttemptsOutboundLevelEntry
	MAX-ACCESS  not-accessible
	STATUS      current
	DESCRIPTION
	"Table entry for connectionCreateAttemptsOutbound"
	INDEX { connectionCreateAttemptsOutboundLevelName }
	::={connectionCreateAttemptsOutboundLevelTable 1}

ConnectionCreateAttemptsOutboundLevelEntry ::=
	SEQUENCE {
		connectionCreateAttemptsOutboundLevelName	DisplayString,
		connectionCreateAttemptsOutboundLevelVal	Counter64,
		connectionCreateAttemptsOutboundLevelMom	CounterBasedGauge64,
		connectionCreateAttemptsOutboundLevelMax	CounterBasedGauge64
	}

connectionCreateAttemptsOutboundLevelName OBJECT-TYPE
	SYNTAX      DisplayString
	MAX-ACCESS  not-accessible
	STATUS      current
	DESCRIPTION
	"Table entry display string for connectionCreateAttemptsOutbound"
	::={connectionCreateAttemptsOutboundLevelEntry 1}

connectionCreateAttemptsOutboundLevelVal OBJECT-TYPE
	SYNTAX	 Counter64
	MAX-ACCESS  read-only
	STATUS      current
	DESCRIPTION
	"Table entry attribute for connectionCreateAttemptsOutbound"
	::={connectionCreateAttemptsOutboundLevelEntry 2}

connectionCreateAttemptsOutboundLevelMom OBJECT-TYPE
	SYNTAX	 CounterBasedGauge64
	MAX-ACCESS  read-only
	STATUS      current
	DESCRIPTION
	"Table entry attribute for connectionCreateAttemptsOutbound"
	::={connectionCreateAttemptsOutboundLevelEntry 3}

connectionCreateAttemptsOutboundLevelMax OBJECT-TYPE
	SYNTAX	 CounterBasedGauge64
	MAX-ACCESS  read-only
	STATUS      current
	DESCRIPTION
	"Table entry attribute for connectionCreateAttemptsOutbound"
	::={connectionCreateAttemptsOutboundLevelEntry 4}


connectionRefusedProt	OBJECT IDENTIFIER ::={connection 5}

connectionRefusedProtVal	OBJECT-TYPE
	SYNTAX	 Counter64
	MAX-ACCESS read-only
	STATUS current
	DESCRIPTION "Attempts refused (connprot)"

	::={connectionRefusedProt 1}

connectionRefusedProtMom	OBJECT-TYPE
	SYNTAX	 CounterBasedGauge64
	MAX-ACCESS read-only
	STATUS current
	DESCRIPTION "Attempts refused (connprot)"

	::={connectionRefusedProt 2}

connectionRefusedProtMax	OBJECT-TYPE
	SYNTAX	 CounterBasedGauge64
	MAX-ACCESS read-only
	STATUS current
	DESCRIPTION "Attempts refused (connprot)"

	::={connectionRefusedProt 3}

connectionRefusedProtLevelTable OBJECT-TYPE
	SYNTAX      SEQUENCE OF ConnectionRefusedProtLevelEntry
	MAX-ACCESS  not-accessible
	STATUS      current
	DESCRIPTION
	"Table for connectionRefusedProt"
	::={connectionRefusedProt 4}

connectionRefusedProtLevelEntry OBJECT-TYPE
	SYNTAX      ConnectionRefusedProtLevelEntry
	MAX-ACCESS  not-accessible
	STATUS      current
	DESCRIPTION
	"Table entry for connectionRefusedProt"
	INDEX { connectionRefusedProtLevelName }
	::={connectionRefusedProtLevelTable 1}

ConnectionRefusedProtLevelEntry ::=
	SEQUENCE {
		connectionRefusedProtLevelName	DisplayString,
		connectionRefusedProtLevelVal	Counter64,
		connectionRefusedProtLevelMom	CounterBasedGauge64,
		connectionRefusedProtLevelMax	CounterBasedGauge64
	}

connectionRefusedProtLevelName OBJECT-TYPE
	SYNTAX      DisplayString
	MAX-ACCESS  not-accessible
	STATUS      current
	DESCRIPTION
	"Table entry display string for connectionRefusedProt"
	::={connectionRefusedProtLevelEntry 1}

connectionRefusedProtLevelVal OBJECT-TYPE
	SYNTAX	 Counter64
	MAX-ACCESS  read-only
	STATUS      current
	DESCRIPTION
	"Table entry attribute for connectionRefusedProt"
	::={connectionRefusedProtLevelEntry 2}

connectionRefusedProtLevelMom OBJECT-TYPE
	SYNTAX	 CounterBasedGauge64
	MAX-ACCESS  read-only
	STATUS      current
	DESCRIPTION
	"Table entry attribute for connectionRefusedProt"
	::={connectionRefusedProtLevelEntry 3}

connectionRefusedProtLevelMax OBJECT-TYPE
	SYNTAX	 CounterBasedGauge64
	MAX-ACCESS  read-only
	STATUS      current
	DESCRIPTION
	"Table entry attribute for connectionRefusedProt"
	::={connectionRefusedProtLevelEntry 4}


connectionRefusedFull	OBJECT IDENTIFIER ::={connection 6}

connectionRefusedFullVal	OBJECT-TYPE
	SYNTAX	 Counter64
	MAX-ACCESS read-only
	STATUS current
	DESCRIPTION "Attempts refused (resources)"

	::={connectionRefusedFull 1}

connectionRefusedFullMom	OBJECT-TYPE
	SYNTAX	 CounterBasedGauge64
	MAX-ACCESS read-only
	STATUS current
	DESCRIPTION "Attempts refused (resources)"

	::={connectionRefusedFull 2}

connectionRefusedFullMax	OBJECT-TYPE
	SYNTAX	 CounterBasedGauge64
	MAX-ACCESS read-only
	STATUS current
	DESCRIPTION "Attempts refused (resources)"

	::={connectionRefusedFull 3}

connectionRefusedFullLevelTable OBJECT-TYPE
	SYNTAX      SEQUENCE OF ConnectionRefusedFullLevelEntry
	MAX-ACCESS  not-accessible
	STATUS      current
	DESCRIPTION
	"Table for connectionRefusedFull"
	::={connectionRefusedFull 4}

connectionRefusedFullLevelEntry OBJECT-TYPE
	SYNTAX      ConnectionRefusedFullLevelEntry
	MAX-ACCESS  not-accessible
	STATUS      current
	DESCRIPTION
	"Table entry for connectionRefusedFull"
	INDEX { connectionRefusedFullLevelName }
	::={connectionRefusedFullLevelTable 1}

ConnectionRefusedFullLevelEntry ::=
	SEQUENCE {
		connectionRefusedFullLevelName	DisplayString,
		connectionRefusedFullLevelVal	Counter64,
		connectionRefusedFullLevelMom	CounterBasedGauge64,
		connectionRefusedFullLevelMax	CounterBasedGauge64
	}

connectionRefusedFullLevelName OBJECT-TYPE
	SYNTAX      DisplayString
	MAX-ACCESS  not-accessible
	STATUS      current
	DESCRIPTION
	"Table entry display string for connectionRefusedFull"
	::={connectionRefusedFullLevelEntry 1}

connectionRefusedFullLevelVal OBJECT-TYPE
	SYNTAX	 Counter64
	MAX-ACCESS  read-only
	STATUS      current
	DESCRIPTION
	"Table entry attribute for connectionRefusedFull"
	::={connectionRefusedFullLevelEntry 2}

connectionRefusedFullLevelMom OBJECT-TYPE
	SYNTAX	 CounterBasedGauge64
	MAX-ACCESS  read-only
	STATUS      current
	DESCRIPTION
	"Table entry attribute for connectionRefusedFull"
	::={connectionRefusedFullLevelEntry 3}

connectionRefusedFullLevelMax OBJECT-TYPE
	SYNTAX	 CounterBasedGauge64
	MAX-ACCESS  read-only
	STATUS      current
	DESCRIPTION
	"Table entry attribute for connectionRefusedFull"
	::={connectionRefusedFullLevelEntry 4}


connectionCreatedInbound	OBJECT IDENTIFIER ::={connection 7}

connectionCreatedInboundVal	OBJECT-TYPE
	SYNTAX	 Counter64
	MAX-ACCESS read-only
	STATUS current
	DESCRIPTION "Created inbound"

	::={connectionCreatedInbound 1}

connectionCreatedInboundMom	OBJECT-TYPE
	SYNTAX	 CounterBasedGauge64
	MAX-ACCESS read-only
	STATUS current
	DESCRIPTION "Created inbound"

	::={connectionCreatedInbound 2}

connectionCreatedInboundMax	OBJECT-TYPE
	SYNTAX	 CounterBasedGauge64
	MAX-ACCESS read-only
	STATUS current
	DESCRIPTION "Created inbound"

	::={connectionCreatedInbound 3}

connectionCreatedInboundLevelTable OBJECT-TYPE
	SYNTAX      SEQUENCE OF ConnectionCreatedInboundLevelEntry
	MAX-ACCESS  not-accessible
	STATUS      current
	DESCRIPTION
	"Table for connectionCreatedInbound"
	::={connectionCreatedInbound 4}

connectionCreatedInboundLevelEntry OBJECT-TYPE
	SYNTAX      ConnectionCreatedInboundLevelEntry
	MAX-ACCESS  not-accessible
	STATUS      current
	DESCRIPTION
	"Table entry for connectionCreatedInbound"
	INDEX { connectionCreatedInboundLevelName }
	::={connectionCreatedInboundLevelTable 1}

ConnectionCreatedInboundLevelEntry ::=
	SEQUENCE {
		connectionCreatedInboundLevelName	DisplayString,
		connectionCreatedInboundLevelVal	Counter64,
		connectionCreatedInboundLevelMom	CounterBasedGauge64,
		connectionCreatedInboundLevelMax	CounterBasedGauge64
	}

connectionCreatedInboundLevelName OBJECT-TYPE
	SYNTAX      DisplayString
	MAX-ACCESS  not-accessible
	STATUS      current
	DESCRIPTION
	"Table entry display string for connectionCreatedInbound"
	::={connectionCreatedInboundLevelEntry 1}

connectionCreatedInboundLevelVal OBJECT-TYPE
	SYNTAX	 Counter64
	MAX-ACCESS  read-only
	STATUS      current
	DESCRIPTION
	"Table entry attribute for connectionCreatedInbound"
	::={connectionCreatedInboundLevelEntry 2}

connectionCreatedInboundLevelMom OBJECT-TYPE
	SYNTAX	 CounterBasedGauge64
	MAX-ACCESS  read-only
	STATUS      current
	DESCRIPTION
	"Table entry attribute for connectionCreatedInbound"
	::={connectionCreatedInboundLevelEntry 3}

connectionCreatedInboundLevelMax OBJECT-TYPE
	SYNTAX	 CounterBasedGauge64
	MAX-ACCESS  read-only
	STATUS      current
	DESCRIPTION
	"Table entry attribute for connectionCreatedInbound"
	::={connectionCreatedInboundLevelEntry 4}


connectionCreatedOutbound	OBJECT IDENTIFIER ::={connection 8}

connectionCreatedOutboundVal	OBJECT-TYPE
	SYNTAX	 Counter64
	MAX-ACCESS read-only
	STATUS current
	DESCRIPTION "Created outbound"

	::={connectionCreatedOutbound 1}

connectionCreatedOutboundMom	OBJECT-TYPE
	SYNTAX	 CounterBasedGauge64
	MAX-ACCESS read-only
	STATUS current
	DESCRIPTION "Created outbound"

	::={connectionCreatedOutbound 2}

connectionCreatedOutboundMax	OBJECT-TYPE
	SYNTAX	 CounterBasedGauge64
	MAX-ACCESS read-only
	STATUS current
	DESCRIPTION "Created outbound"

	::={connectionCreatedOutbound 3}

connectionCreatedOutboundLevelTable OBJECT-TYPE
	SYNTAX      SEQUENCE OF ConnectionCreatedOutboundLevelEntry
	MAX-ACCESS  not-accessible
	STATUS      current
	DESCRIPTION
	"Table for connectionCreatedOutbound"
	::={connectionCreatedOutbound 4}

connectionCreatedOutboundLevelEntry OBJECT-TYPE
	SYNTAX      ConnectionCreatedOutboundLevelEntry
	MAX-ACCESS  not-accessible
	STATUS      current
	DESCRIPTION
	"Table entry for connectionCreatedOutbound"
	INDEX { connectionCreatedOutboundLevelName }
	::={connectionCreatedOutboundLevelTable 1}

ConnectionCreatedOutboundLevelEntry ::=
	SEQUENCE {
		connectionCreatedOutboundLevelName	DisplayString,
		connectionCreatedOutboundLevelVal	Counter64,
		connectionCreatedOutboundLevelMom	CounterBasedGauge64,
		connectionCreatedOutboundLevelMax	CounterBasedGauge64
	}

connectionCreatedOutboundLevelName OBJECT-TYPE
	SYNTAX      DisplayString
	MAX-ACCESS  not-accessible
	STATUS      current
	DESCRIPTION
	"Table entry display string for connectionCreatedOutbound"
	::={connectionCreatedOutboundLevelEntry 1}

connectionCreatedOutboundLevelVal OBJECT-TYPE
	SYNTAX	 Counter64
	MAX-ACCESS  read-only
	STATUS      current
	DESCRIPTION
	"Table entry attribute for connectionCreatedOutbound"
	::={connectionCreatedOutboundLevelEntry 2}

connectionCreatedOutboundLevelMom OBJECT-TYPE
	SYNTAX	 CounterBasedGauge64
	MAX-ACCESS  read-only
	STATUS      current
	DESCRIPTION
	"Table entry attribute for connectionCreatedOutbound"
	::={connectionCreatedOutboundLevelEntry 3}

connectionCreatedOutboundLevelMax OBJECT-TYPE
	SYNTAX	 CounterBasedGauge64
	MAX-ACCESS  read-only
	STATUS      current
	DESCRIPTION
	"Table entry attribute for connectionCreatedOutbound"
	::={connectionCreatedOutboundLevelEntry 4}


connectionLruAllocs	OBJECT IDENTIFIER ::={connection 9}

connectionLruAllocsVal	OBJECT-TYPE
	SYNTAX	 Counter64
	MAX-ACCESS read-only
	STATUS current
	DESCRIPTION "Connections allocated from LRU"

	::={connectionLruAllocs 1}

connectionLruAllocsMom	OBJECT-TYPE
	SYNTAX	 CounterBasedGauge64
	MAX-ACCESS read-only
	STATUS current
	DESCRIPTION "Connections allocated from LRU"

	::={connectionLruAllocs 2}

connectionLruAllocsMax	OBJECT-TYPE
	SYNTAX	 CounterBasedGauge64
	MAX-ACCESS read-only
	STATUS current
	DESCRIPTION "Connections allocated from LRU"

	::={connectionLruAllocs 3}

connectionLruAllocsLevelTable OBJECT-TYPE
	SYNTAX      SEQUENCE OF ConnectionLruAllocsLevelEntry
	MAX-ACCESS  not-accessible
	STATUS      current
	DESCRIPTION
	"Table for connectionLruAllocs"
	::={connectionLruAllocs 4}

connectionLruAllocsLevelEntry OBJECT-TYPE
	SYNTAX      ConnectionLruAllocsLevelEntry
	MAX-ACCESS  not-accessible
	STATUS      current
	DESCRIPTION
	"Table entry for connectionLruAllocs"
	INDEX { connectionLruAllocsLevelName }
	::={connectionLruAllocsLevelTable 1}

ConnectionLruAllocsLevelEntry ::=
	SEQUENCE {
		connectionLruAllocsLevelName	DisplayString,
		connectionLruAllocsLevelVal	Counter64,
		connectionLruAllocsLevelMom	CounterBasedGauge64,
		connectionLruAllocsLevelMax	CounterBasedGauge64
	}

connectionLruAllocsLevelName OBJECT-TYPE
	SYNTAX      DisplayString
	MAX-ACCESS  not-accessible
	STATUS      current
	DESCRIPTION
	"Table entry display string for connectionLruAllocs"
	::={connectionLruAllocsLevelEntry 1}

connectionLruAllocsLevelVal OBJECT-TYPE
	SYNTAX	 Counter64
	MAX-ACCESS  read-only
	STATUS      current
	DESCRIPTION
	"Table entry attribute for connectionLruAllocs"
	::={connectionLruAllocsLevelEntry 2}

connectionLruAllocsLevelMom OBJECT-TYPE
	SYNTAX	 CounterBasedGauge64
	MAX-ACCESS  read-only
	STATUS      current
	DESCRIPTION
	"Table entry attribute for connectionLruAllocs"
	::={connectionLruAllocsLevelEntry 3}

connectionLruAllocsLevelMax OBJECT-TYPE
	SYNTAX	 CounterBasedGauge64
	MAX-ACCESS  read-only
	STATUS      current
	DESCRIPTION
	"Table entry attribute for connectionLruAllocs"
	::={connectionLruAllocsLevelEntry 4}


connectionLookups	OBJECT IDENTIFIER ::={connection 10}

connectionLookupsVal	OBJECT-TYPE
	SYNTAX	 Counter64
	MAX-ACCESS read-only
	STATUS current
	DESCRIPTION "Lookups"

	::={connectionLookups 1}

connectionLookupsMom	OBJECT-TYPE
	SYNTAX	 CounterBasedGauge64
	MAX-ACCESS read-only
	STATUS current
	DESCRIPTION "Lookups"

	::={connectionLookups 2}

connectionLookupsMax	OBJECT-TYPE
	SYNTAX	 CounterBasedGauge64
	MAX-ACCESS read-only
	STATUS current
	DESCRIPTION "Lookups"

	::={connectionLookups 3}

connectionLookupsLevelTable OBJECT-TYPE
	SYNTAX      SEQUENCE OF ConnectionLookupsLevelEntry
	MAX-ACCESS  not-accessible
	STATUS      current
	DESCRIPTION
	"Table for connectionLookups"
	::={connectionLookups 4}

connectionLookupsLevelEntry OBJECT-TYPE
	SYNTAX      ConnectionLookupsLevelEntry
	MAX-ACCESS  not-accessible
	STATUS      current
	DESCRIPTION
	"Table entry for connectionLookups"
	INDEX { connectionLookupsLevelName }
	::={connectionLookupsLevelTable 1}

ConnectionLookupsLevelEntry ::=
	SEQUENCE {
		connectionLookupsLevelName	DisplayString,
		connectionLookupsLevelVal	Counter64,
		connectionLookupsLevelMom	CounterBasedGauge64,
		connectionLookupsLevelMax	CounterBasedGauge64
	}

connectionLookupsLevelName OBJECT-TYPE
	SYNTAX      DisplayString
	MAX-ACCESS  not-accessible
	STATUS      current
	DESCRIPTION
	"Table entry display string for connectionLookups"
	::={connectionLookupsLevelEntry 1}

connectionLookupsLevelVal OBJECT-TYPE
	SYNTAX	 Counter64
	MAX-ACCESS  read-only
	STATUS      current
	DESCRIPTION
	"Table entry attribute for connectionLookups"
	::={connectionLookupsLevelEntry 2}

connectionLookupsLevelMom OBJECT-TYPE
	SYNTAX	 CounterBasedGauge64
	MAX-ACCESS  read-only
	STATUS      current
	DESCRIPTION
	"Table entry attribute for connectionLookups"
	::={connectionLookupsLevelEntry 3}

connectionLookupsLevelMax OBJECT-TYPE
	SYNTAX	 CounterBasedGauge64
	MAX-ACCESS  read-only
	STATUS      current
	DESCRIPTION
	"Table entry attribute for connectionLookups"
	::={connectionLookupsLevelEntry 4}


connectionEstablished	OBJECT IDENTIFIER ::={connection 11}

connectionEstablishedVal	OBJECT-TYPE
	SYNTAX	 Counter64
	MAX-ACCESS read-only
	STATUS current
	DESCRIPTION "Made established"

	::={connectionEstablished 1}

connectionEstablishedMom	OBJECT-TYPE
	SYNTAX	 CounterBasedGauge64
	MAX-ACCESS read-only
	STATUS current
	DESCRIPTION "Made established"

	::={connectionEstablished 2}

connectionEstablishedMax	OBJECT-TYPE
	SYNTAX	 CounterBasedGauge64
	MAX-ACCESS read-only
	STATUS current
	DESCRIPTION "Made established"

	::={connectionEstablished 3}

connectionEstablishedLevelTable OBJECT-TYPE
	SYNTAX      SEQUENCE OF ConnectionEstablishedLevelEntry
	MAX-ACCESS  not-accessible
	STATUS      current
	DESCRIPTION
	"Table for connectionEstablished"
	::={connectionEstablished 4}

connectionEstablishedLevelEntry OBJECT-TYPE
	SYNTAX      ConnectionEstablishedLevelEntry
	MAX-ACCESS  not-accessible
	STATUS      current
	DESCRIPTION
	"Table entry for connectionEstablished"
	INDEX { connectionEstablishedLevelName }
	::={connectionEstablishedLevelTable 1}

ConnectionEstablishedLevelEntry ::=
	SEQUENCE {
		connectionEstablishedLevelName	DisplayString,
		connectionEstablishedLevelVal	Counter64,
		connectionEstablishedLevelMom	CounterBasedGauge64,
		connectionEstablishedLevelMax	CounterBasedGauge64
	}

connectionEstablishedLevelName OBJECT-TYPE
	SYNTAX      DisplayString
	MAX-ACCESS  not-accessible
	STATUS      current
	DESCRIPTION
	"Table entry display string for connectionEstablished"
	::={connectionEstablishedLevelEntry 1}

connectionEstablishedLevelVal OBJECT-TYPE
	SYNTAX	 Counter64
	MAX-ACCESS  read-only
	STATUS      current
	DESCRIPTION
	"Table entry attribute for connectionEstablished"
	::={connectionEstablishedLevelEntry 2}

connectionEstablishedLevelMom OBJECT-TYPE
	SYNTAX	 CounterBasedGauge64
	MAX-ACCESS  read-only
	STATUS      current
	DESCRIPTION
	"Table entry attribute for connectionEstablished"
	::={connectionEstablishedLevelEntry 3}

connectionEstablishedLevelMax OBJECT-TYPE
	SYNTAX	 CounterBasedGauge64
	MAX-ACCESS  read-only
	STATUS      current
	DESCRIPTION
	"Table entry attribute for connectionEstablished"
	::={connectionEstablishedLevelEntry 4}


connectionUpdates	OBJECT IDENTIFIER ::={connection 12}

connectionUpdatesVal	OBJECT-TYPE
	SYNTAX	 Counter64
	MAX-ACCESS read-only
	STATUS current
	DESCRIPTION "Updates sent"

	::={connectionUpdates 1}

connectionUpdatesMom	OBJECT-TYPE
	SYNTAX	 CounterBasedGauge64
	MAX-ACCESS read-only
	STATUS current
	DESCRIPTION "Updates sent"

	::={connectionUpdates 2}

connectionUpdatesMax	OBJECT-TYPE
	SYNTAX	 CounterBasedGauge64
	MAX-ACCESS read-only
	STATUS current
	DESCRIPTION "Updates sent"

	::={connectionUpdates 3}

connectionUpdatesLevelTable OBJECT-TYPE
	SYNTAX      SEQUENCE OF ConnectionUpdatesLevelEntry
	MAX-ACCESS  not-accessible
	STATUS      current
	DESCRIPTION
	"Table for connectionUpdates"
	::={connectionUpdates 4}

connectionUpdatesLevelEntry OBJECT-TYPE
	SYNTAX      ConnectionUpdatesLevelEntry
	MAX-ACCESS  not-accessible
	STATUS      current
	DESCRIPTION
	"Table entry for connectionUpdates"
	INDEX { connectionUpdatesLevelName }
	::={connectionUpdatesLevelTable 1}

ConnectionUpdatesLevelEntry ::=
	SEQUENCE {
		connectionUpdatesLevelName	DisplayString,
		connectionUpdatesLevelVal	Counter64,
		connectionUpdatesLevelMom	CounterBasedGauge64,
		connectionUpdatesLevelMax	CounterBasedGauge64
	}

connectionUpdatesLevelName OBJECT-TYPE
	SYNTAX      DisplayString
	MAX-ACCESS  not-accessible
	STATUS      current
	DESCRIPTION
	"Table entry display string for connectionUpdates"
	::={connectionUpdatesLevelEntry 1}

connectionUpdatesLevelVal OBJECT-TYPE
	SYNTAX	 Counter64
	MAX-ACCESS  read-only
	STATUS      current
	DESCRIPTION
	"Table entry attribute for connectionUpdates"
	::={connectionUpdatesLevelEntry 2}

connectionUpdatesLevelMom OBJECT-TYPE
	SYNTAX	 CounterBasedGauge64
	MAX-ACCESS  read-only
	STATUS      current
	DESCRIPTION
	"Table entry attribute for connectionUpdates"
	::={connectionUpdatesLevelEntry 3}

connectionUpdatesLevelMax OBJECT-TYPE
	SYNTAX	 CounterBasedGauge64
	MAX-ACCESS  read-only
	STATUS      current
	DESCRIPTION
	"Table entry attribute for connectionUpdates"
	::={connectionUpdatesLevelEntry 4}


connectionTtlTimeouts	OBJECT IDENTIFIER ::={connection 13}

connectionTtlTimeoutsVal	OBJECT-TYPE
	SYNTAX	 Counter64
	MAX-ACCESS read-only
	STATUS current
	DESCRIPTION "TTL timeouts"

	::={connectionTtlTimeouts 1}

connectionTtlTimeoutsMom	OBJECT-TYPE
	SYNTAX	 CounterBasedGauge64
	MAX-ACCESS read-only
	STATUS current
	DESCRIPTION "TTL timeouts"

	::={connectionTtlTimeouts 2}

connectionTtlTimeoutsMax	OBJECT-TYPE
	SYNTAX	 CounterBasedGauge64
	MAX-ACCESS read-only
	STATUS current
	DESCRIPTION "TTL timeouts"

	::={connectionTtlTimeouts 3}

connectionTtlTimeoutsLevelTable OBJECT-TYPE
	SYNTAX      SEQUENCE OF ConnectionTtlTimeoutsLevelEntry
	MAX-ACCESS  not-accessible
	STATUS      current
	DESCRIPTION
	"Table for connectionTtlTimeouts"
	::={connectionTtlTimeouts 4}

connectionTtlTimeoutsLevelEntry OBJECT-TYPE
	SYNTAX      ConnectionTtlTimeoutsLevelEntry
	MAX-ACCESS  not-accessible
	STATUS      current
	DESCRIPTION
	"Table entry for connectionTtlTimeouts"
	INDEX { connectionTtlTimeoutsLevelName }
	::={connectionTtlTimeoutsLevelTable 1}

ConnectionTtlTimeoutsLevelEntry ::=
	SEQUENCE {
		connectionTtlTimeoutsLevelName	DisplayString,
		connectionTtlTimeoutsLevelVal	Counter64,
		connectionTtlTimeoutsLevelMom	CounterBasedGauge64,
		connectionTtlTimeoutsLevelMax	CounterBasedGauge64
	}

connectionTtlTimeoutsLevelName OBJECT-TYPE
	SYNTAX      DisplayString
	MAX-ACCESS  not-accessible
	STATUS      current
	DESCRIPTION
	"Table entry display string for connectionTtlTimeouts"
	::={connectionTtlTimeoutsLevelEntry 1}

connectionTtlTimeoutsLevelVal OBJECT-TYPE
	SYNTAX	 Counter64
	MAX-ACCESS  read-only
	STATUS      current
	DESCRIPTION
	"Table entry attribute for connectionTtlTimeouts"
	::={connectionTtlTimeoutsLevelEntry 2}

connectionTtlTimeoutsLevelMom OBJECT-TYPE
	SYNTAX	 CounterBasedGauge64
	MAX-ACCESS  read-only
	STATUS      current
	DESCRIPTION
	"Table entry attribute for connectionTtlTimeouts"
	::={connectionTtlTimeoutsLevelEntry 3}

connectionTtlTimeoutsLevelMax OBJECT-TYPE
	SYNTAX	 CounterBasedGauge64
	MAX-ACCESS  read-only
	STATUS      current
	DESCRIPTION
	"Table entry attribute for connectionTtlTimeouts"
	::={connectionTtlTimeoutsLevelEntry 4}


connectionProtEnables	OBJECT IDENTIFIER ::={connection 14}

connectionProtEnablesVal	OBJECT-TYPE
	SYNTAX	 Counter64
	MAX-ACCESS read-only
	STATUS current
	DESCRIPTION "Protection enabled"

	::={connectionProtEnables 1}

connectionProtEnablesMom	OBJECT-TYPE
	SYNTAX	 CounterBasedGauge64
	MAX-ACCESS read-only
	STATUS current
	DESCRIPTION "Protection enabled"

	::={connectionProtEnables 2}

connectionProtEnablesMax	OBJECT-TYPE
	SYNTAX	 CounterBasedGauge64
	MAX-ACCESS read-only
	STATUS current
	DESCRIPTION "Protection enabled"

	::={connectionProtEnables 3}

connectionProtEnablesLevelTable OBJECT-TYPE
	SYNTAX      SEQUENCE OF ConnectionProtEnablesLevelEntry
	MAX-ACCESS  not-accessible
	STATUS      current
	DESCRIPTION
	"Table for connectionProtEnables"
	::={connectionProtEnables 4}

connectionProtEnablesLevelEntry OBJECT-TYPE
	SYNTAX      ConnectionProtEnablesLevelEntry
	MAX-ACCESS  not-accessible
	STATUS      current
	DESCRIPTION
	"Table entry for connectionProtEnables"
	INDEX { connectionProtEnablesLevelName }
	::={connectionProtEnablesLevelTable 1}

ConnectionProtEnablesLevelEntry ::=
	SEQUENCE {
		connectionProtEnablesLevelName	DisplayString,
		connectionProtEnablesLevelVal	Counter64,
		connectionProtEnablesLevelMom	CounterBasedGauge64,
		connectionProtEnablesLevelMax	CounterBasedGauge64
	}

connectionProtEnablesLevelName OBJECT-TYPE
	SYNTAX      DisplayString
	MAX-ACCESS  not-accessible
	STATUS      current
	DESCRIPTION
	"Table entry display string for connectionProtEnables"
	::={connectionProtEnablesLevelEntry 1}

connectionProtEnablesLevelVal OBJECT-TYPE
	SYNTAX	 Counter64
	MAX-ACCESS  read-only
	STATUS      current
	DESCRIPTION
	"Table entry attribute for connectionProtEnables"
	::={connectionProtEnablesLevelEntry 2}

connectionProtEnablesLevelMom OBJECT-TYPE
	SYNTAX	 CounterBasedGauge64
	MAX-ACCESS  read-only
	STATUS      current
	DESCRIPTION
	"Table entry attribute for connectionProtEnables"
	::={connectionProtEnablesLevelEntry 3}

connectionProtEnablesLevelMax OBJECT-TYPE
	SYNTAX	 CounterBasedGauge64
	MAX-ACCESS  read-only
	STATUS      current
	DESCRIPTION
	"Table entry attribute for connectionProtEnables"
	::={connectionProtEnablesLevelEntry 4}


connectionNotFound	OBJECT IDENTIFIER ::={connection 15}

connectionNotFoundVal	OBJECT-TYPE
	SYNTAX	 Counter64
	MAX-ACCESS read-only
	STATUS current
	DESCRIPTION "Failed lookups"

	::={connectionNotFound 1}

connectionNotFoundMom	OBJECT-TYPE
	SYNTAX	 CounterBasedGauge64
	MAX-ACCESS read-only
	STATUS current
	DESCRIPTION "Failed lookups"

	::={connectionNotFound 2}

connectionNotFoundMax	OBJECT-TYPE
	SYNTAX	 CounterBasedGauge64
	MAX-ACCESS read-only
	STATUS current
	DESCRIPTION "Failed lookups"

	::={connectionNotFound 3}

connectionNotFoundLevelTable OBJECT-TYPE
	SYNTAX      SEQUENCE OF ConnectionNotFoundLevelEntry
	MAX-ACCESS  not-accessible
	STATUS      current
	DESCRIPTION
	"Table for connectionNotFound"
	::={connectionNotFound 4}

connectionNotFoundLevelEntry OBJECT-TYPE
	SYNTAX      ConnectionNotFoundLevelEntry
	MAX-ACCESS  not-accessible
	STATUS      current
	DESCRIPTION
	"Table entry for connectionNotFound"
	INDEX { connectionNotFoundLevelName }
	::={connectionNotFoundLevelTable 1}

ConnectionNotFoundLevelEntry ::=
	SEQUENCE {
		connectionNotFoundLevelName	DisplayString,
		connectionNotFoundLevelVal	Counter64,
		connectionNotFoundLevelMom	CounterBasedGauge64,
		connectionNotFoundLevelMax	CounterBasedGauge64
	}

connectionNotFoundLevelName OBJECT-TYPE
	SYNTAX      DisplayString
	MAX-ACCESS  not-accessible
	STATUS      current
	DESCRIPTION
	"Table entry display string for connectionNotFound"
	::={connectionNotFoundLevelEntry 1}

connectionNotFoundLevelVal OBJECT-TYPE
	SYNTAX	 Counter64
	MAX-ACCESS  read-only
	STATUS      current
	DESCRIPTION
	"Table entry attribute for connectionNotFound"
	::={connectionNotFoundLevelEntry 2}

connectionNotFoundLevelMom OBJECT-TYPE
	SYNTAX	 CounterBasedGauge64
	MAX-ACCESS  read-only
	STATUS      current
	DESCRIPTION
	"Table entry attribute for connectionNotFound"
	::={connectionNotFoundLevelEntry 3}

connectionNotFoundLevelMax OBJECT-TYPE
	SYNTAX	 CounterBasedGauge64
	MAX-ACCESS  read-only
	STATUS      current
	DESCRIPTION
	"Table entry attribute for connectionNotFound"
	::={connectionNotFoundLevelEntry 4}


connectionRefusedExisting	OBJECT IDENTIFIER ::={connection 18}

connectionRefusedExistingVal	OBJECT-TYPE
	SYNTAX	 Counter64
	MAX-ACCESS read-only
	STATUS current
	DESCRIPTION "Attempts refused (already existed)"

	::={connectionRefusedExisting 1}

connectionRefusedExistingMom	OBJECT-TYPE
	SYNTAX	 CounterBasedGauge64
	MAX-ACCESS read-only
	STATUS current
	DESCRIPTION "Attempts refused (already existed)"

	::={connectionRefusedExisting 2}

connectionRefusedExistingMax	OBJECT-TYPE
	SYNTAX	 CounterBasedGauge64
	MAX-ACCESS read-only
	STATUS current
	DESCRIPTION "Attempts refused (already existed)"

	::={connectionRefusedExisting 3}

connectionRefusedExistingLevelTable OBJECT-TYPE
	SYNTAX      SEQUENCE OF ConnectionRefusedExistingLevelEntry
	MAX-ACCESS  not-accessible
	STATUS      current
	DESCRIPTION
	"Table for connectionRefusedExisting"
	::={connectionRefusedExisting 4}

connectionRefusedExistingLevelEntry OBJECT-TYPE
	SYNTAX      ConnectionRefusedExistingLevelEntry
	MAX-ACCESS  not-accessible
	STATUS      current
	DESCRIPTION
	"Table entry for connectionRefusedExisting"
	INDEX { connectionRefusedExistingLevelName }
	::={connectionRefusedExistingLevelTable 1}

ConnectionRefusedExistingLevelEntry ::=
	SEQUENCE {
		connectionRefusedExistingLevelName	DisplayString,
		connectionRefusedExistingLevelVal	Counter64,
		connectionRefusedExistingLevelMom	CounterBasedGauge64,
		connectionRefusedExistingLevelMax	CounterBasedGauge64
	}

connectionRefusedExistingLevelName OBJECT-TYPE
	SYNTAX      DisplayString
	MAX-ACCESS  not-accessible
	STATUS      current
	DESCRIPTION
	"Table entry display string for connectionRefusedExisting"
	::={connectionRefusedExistingLevelEntry 1}

connectionRefusedExistingLevelVal OBJECT-TYPE
	SYNTAX	 Counter64
	MAX-ACCESS  read-only
	STATUS      current
	DESCRIPTION
	"Table entry attribute for connectionRefusedExisting"
	::={connectionRefusedExistingLevelEntry 2}

connectionRefusedExistingLevelMom OBJECT-TYPE
	SYNTAX	 CounterBasedGauge64
	MAX-ACCESS  read-only
	STATUS      current
	DESCRIPTION
	"Table entry attribute for connectionRefusedExisting"
	::={connectionRefusedExistingLevelEntry 3}

connectionRefusedExistingLevelMax OBJECT-TYPE
	SYNTAX	 CounterBasedGauge64
	MAX-ACCESS  read-only
	STATUS      current
	DESCRIPTION
	"Table entry attribute for connectionRefusedExisting"
	::={connectionRefusedExistingLevelEntry 4}


connectionRefusedRuleset	OBJECT IDENTIFIER ::={connection 19}

connectionRefusedRulesetVal	OBJECT-TYPE
	SYNTAX	 Counter64
	MAX-ACCESS read-only
	STATUS current
	DESCRIPTION "Attempts refused (ruleset)"

	::={connectionRefusedRuleset 1}

connectionRefusedRulesetMom	OBJECT-TYPE
	SYNTAX	 CounterBasedGauge64
	MAX-ACCESS read-only
	STATUS current
	DESCRIPTION "Attempts refused (ruleset)"

	::={connectionRefusedRuleset 2}

connectionRefusedRulesetMax	OBJECT-TYPE
	SYNTAX	 CounterBasedGauge64
	MAX-ACCESS read-only
	STATUS current
	DESCRIPTION "Attempts refused (ruleset)"

	::={connectionRefusedRuleset 3}

connectionRefusedRulesetLevelTable OBJECT-TYPE
	SYNTAX      SEQUENCE OF ConnectionRefusedRulesetLevelEntry
	MAX-ACCESS  not-accessible
	STATUS      current
	DESCRIPTION
	"Table for connectionRefusedRuleset"
	::={connectionRefusedRuleset 4}

connectionRefusedRulesetLevelEntry OBJECT-TYPE
	SYNTAX      ConnectionRefusedRulesetLevelEntry
	MAX-ACCESS  not-accessible
	STATUS      current
	DESCRIPTION
	"Table entry for connectionRefusedRuleset"
	INDEX { connectionRefusedRulesetLevelName }
	::={connectionRefusedRulesetLevelTable 1}

ConnectionRefusedRulesetLevelEntry ::=
	SEQUENCE {
		connectionRefusedRulesetLevelName	DisplayString,
		connectionRefusedRulesetLevelVal	Counter64,
		connectionRefusedRulesetLevelMom	CounterBasedGauge64,
		connectionRefusedRulesetLevelMax	CounterBasedGauge64
	}

connectionRefusedRulesetLevelName OBJECT-TYPE
	SYNTAX      DisplayString
	MAX-ACCESS  not-accessible
	STATUS      current
	DESCRIPTION
	"Table entry display string for connectionRefusedRuleset"
	::={connectionRefusedRulesetLevelEntry 1}

connectionRefusedRulesetLevelVal OBJECT-TYPE
	SYNTAX	 Counter64
	MAX-ACCESS  read-only
	STATUS      current
	DESCRIPTION
	"Table entry attribute for connectionRefusedRuleset"
	::={connectionRefusedRulesetLevelEntry 2}

connectionRefusedRulesetLevelMom OBJECT-TYPE
	SYNTAX	 CounterBasedGauge64
	MAX-ACCESS  read-only
	STATUS      current
	DESCRIPTION
	"Table entry attribute for connectionRefusedRuleset"
	::={connectionRefusedRulesetLevelEntry 3}

connectionRefusedRulesetLevelMax OBJECT-TYPE
	SYNTAX	 CounterBasedGauge64
	MAX-ACCESS  read-only
	STATUS      current
	DESCRIPTION
	"Table entry attribute for connectionRefusedRuleset"
	::={connectionRefusedRulesetLevelEntry 4}


connectionUnestablished	OBJECT IDENTIFIER ::={connection 24}

connectionUnestablishedVal	OBJECT-TYPE
	SYNTAX	 Counter64
	MAX-ACCESS read-only
	STATUS current
	DESCRIPTION "Made unestablished"

	::={connectionUnestablished 1}

connectionUnestablishedMom	OBJECT-TYPE
	SYNTAX	 CounterBasedGauge64
	MAX-ACCESS read-only
	STATUS current
	DESCRIPTION "Made unestablished"

	::={connectionUnestablished 2}

connectionUnestablishedMax	OBJECT-TYPE
	SYNTAX	 CounterBasedGauge64
	MAX-ACCESS read-only
	STATUS current
	DESCRIPTION "Made unestablished"

	::={connectionUnestablished 3}

connectionUnestablishedLevelTable OBJECT-TYPE
	SYNTAX      SEQUENCE OF ConnectionUnestablishedLevelEntry
	MAX-ACCESS  not-accessible
	STATUS      current
	DESCRIPTION
	"Table for connectionUnestablished"
	::={connectionUnestablished 4}

connectionUnestablishedLevelEntry OBJECT-TYPE
	SYNTAX      ConnectionUnestablishedLevelEntry
	MAX-ACCESS  not-accessible
	STATUS      current
	DESCRIPTION
	"Table entry for connectionUnestablished"
	INDEX { connectionUnestablishedLevelName }
	::={connectionUnestablishedLevelTable 1}

ConnectionUnestablishedLevelEntry ::=
	SEQUENCE {
		connectionUnestablishedLevelName	DisplayString,
		connectionUnestablishedLevelVal	Counter64,
		connectionUnestablishedLevelMom	CounterBasedGauge64,
		connectionUnestablishedLevelMax	CounterBasedGauge64
	}

connectionUnestablishedLevelName OBJECT-TYPE
	SYNTAX      DisplayString
	MAX-ACCESS  not-accessible
	STATUS      current
	DESCRIPTION
	"Table entry display string for connectionUnestablished"
	::={connectionUnestablishedLevelEntry 1}

connectionUnestablishedLevelVal OBJECT-TYPE
	SYNTAX	 Counter64
	MAX-ACCESS  read-only
	STATUS      current
	DESCRIPTION
	"Table entry attribute for connectionUnestablished"
	::={connectionUnestablishedLevelEntry 2}

connectionUnestablishedLevelMom OBJECT-TYPE
	SYNTAX	 CounterBasedGauge64
	MAX-ACCESS  read-only
	STATUS      current
	DESCRIPTION
	"Table entry attribute for connectionUnestablished"
	::={connectionUnestablishedLevelEntry 3}

connectionUnestablishedLevelMax OBJECT-TYPE
	SYNTAX	 CounterBasedGauge64
	MAX-ACCESS  read-only
	STATUS      current
	DESCRIPTION
	"Table entry attribute for connectionUnestablished"
	::={connectionUnestablishedLevelEntry 4}


connectionDestroyedEst	OBJECT IDENTIFIER ::={connection 25}

connectionDestroyedEstVal	OBJECT-TYPE
	SYNTAX	 Counter64
	MAX-ACCESS read-only
	STATUS current
	DESCRIPTION "Destroyed established"

	::={connectionDestroyedEst 1}

connectionDestroyedEstMom	OBJECT-TYPE
	SYNTAX	 CounterBasedGauge64
	MAX-ACCESS read-only
	STATUS current
	DESCRIPTION "Destroyed established"

	::={connectionDestroyedEst 2}

connectionDestroyedEstMax	OBJECT-TYPE
	SYNTAX	 CounterBasedGauge64
	MAX-ACCESS read-only
	STATUS current
	DESCRIPTION "Destroyed established"

	::={connectionDestroyedEst 3}

connectionDestroyedEstLevelTable OBJECT-TYPE
	SYNTAX      SEQUENCE OF ConnectionDestroyedEstLevelEntry
	MAX-ACCESS  not-accessible
	STATUS      current
	DESCRIPTION
	"Table for connectionDestroyedEst"
	::={connectionDestroyedEst 4}

connectionDestroyedEstLevelEntry OBJECT-TYPE
	SYNTAX      ConnectionDestroyedEstLevelEntry
	MAX-ACCESS  not-accessible
	STATUS      current
	DESCRIPTION
	"Table entry for connectionDestroyedEst"
	INDEX { connectionDestroyedEstLevelName }
	::={connectionDestroyedEstLevelTable 1}

ConnectionDestroyedEstLevelEntry ::=
	SEQUENCE {
		connectionDestroyedEstLevelName	DisplayString,
		connectionDestroyedEstLevelVal	Counter64,
		connectionDestroyedEstLevelMom	CounterBasedGauge64,
		connectionDestroyedEstLevelMax	CounterBasedGauge64
	}

connectionDestroyedEstLevelName OBJECT-TYPE
	SYNTAX      DisplayString
	MAX-ACCESS  not-accessible
	STATUS      current
	DESCRIPTION
	"Table entry display string for connectionDestroyedEst"
	::={connectionDestroyedEstLevelEntry 1}

connectionDestroyedEstLevelVal OBJECT-TYPE
	SYNTAX	 Counter64
	MAX-ACCESS  read-only
	STATUS      current
	DESCRIPTION
	"Table entry attribute for connectionDestroyedEst"
	::={connectionDestroyedEstLevelEntry 2}

connectionDestroyedEstLevelMom OBJECT-TYPE
	SYNTAX	 CounterBasedGauge64
	MAX-ACCESS  read-only
	STATUS      current
	DESCRIPTION
	"Table entry attribute for connectionDestroyedEst"
	::={connectionDestroyedEstLevelEntry 3}

connectionDestroyedEstLevelMax OBJECT-TYPE
	SYNTAX	 CounterBasedGauge64
	MAX-ACCESS  read-only
	STATUS      current
	DESCRIPTION
	"Table entry attribute for connectionDestroyedEst"
	::={connectionDestroyedEstLevelEntry 4}


connectionInvalidRulesetUpdate	OBJECT IDENTIFIER ::={connection 26}

connectionInvalidRulesetUpdateVal	OBJECT-TYPE
	SYNTAX	 Counter64
	MAX-ACCESS read-only
	STATUS current
	DESCRIPTION "Updates with invalid ruleset"

	::={connectionInvalidRulesetUpdate 1}

connectionInvalidRulesetUpdateMom	OBJECT-TYPE
	SYNTAX	 CounterBasedGauge64
	MAX-ACCESS read-only
	STATUS current
	DESCRIPTION "Updates with invalid ruleset"

	::={connectionInvalidRulesetUpdate 2}

connectionInvalidRulesetUpdateMax	OBJECT-TYPE
	SYNTAX	 CounterBasedGauge64
	MAX-ACCESS read-only
	STATUS current
	DESCRIPTION "Updates with invalid ruleset"

	::={connectionInvalidRulesetUpdate 3}

connectionInvalidRulesetUpdateLevelTable OBJECT-TYPE
	SYNTAX      SEQUENCE OF ConnectionInvalidRulesetUpdateLevelEntry
	MAX-ACCESS  not-accessible
	STATUS      current
	DESCRIPTION
	"Table for connectionInvalidRulesetUpdate"
	::={connectionInvalidRulesetUpdate 4}

connectionInvalidRulesetUpdateLevelEntry OBJECT-TYPE
	SYNTAX      ConnectionInvalidRulesetUpdateLevelEntry
	MAX-ACCESS  not-accessible
	STATUS      current
	DESCRIPTION
	"Table entry for connectionInvalidRulesetUpdate"
	INDEX { connectionInvalidRulesetUpdateLevelName }
	::={connectionInvalidRulesetUpdateLevelTable 1}

ConnectionInvalidRulesetUpdateLevelEntry ::=
	SEQUENCE {
		connectionInvalidRulesetUpdateLevelName	DisplayString,
		connectionInvalidRulesetUpdateLevelVal	Counter64,
		connectionInvalidRulesetUpdateLevelMom	CounterBasedGauge64,
		connectionInvalidRulesetUpdateLevelMax	CounterBasedGauge64
	}

connectionInvalidRulesetUpdateLevelName OBJECT-TYPE
	SYNTAX      DisplayString
	MAX-ACCESS  not-accessible
	STATUS      current
	DESCRIPTION
	"Table entry display string for connectionInvalidRulesetUpdate"
	::={connectionInvalidRulesetUpdateLevelEntry 1}

connectionInvalidRulesetUpdateLevelVal OBJECT-TYPE
	SYNTAX	 Counter64
	MAX-ACCESS  read-only
	STATUS      current
	DESCRIPTION
	"Table entry attribute for connectionInvalidRulesetUpdate"
	::={connectionInvalidRulesetUpdateLevelEntry 2}

connectionInvalidRulesetUpdateLevelMom OBJECT-TYPE
	SYNTAX	 CounterBasedGauge64
	MAX-ACCESS  read-only
	STATUS      current
	DESCRIPTION
	"Table entry attribute for connectionInvalidRulesetUpdate"
	::={connectionInvalidRulesetUpdateLevelEntry 3}

connectionInvalidRulesetUpdateLevelMax OBJECT-TYPE
	SYNTAX	 CounterBasedGauge64
	MAX-ACCESS  read-only
	STATUS      current
	DESCRIPTION
	"Table entry attribute for connectionInvalidRulesetUpdate"
	::={connectionInvalidRulesetUpdateLevelEntry 4}


connectionOrphaned	OBJECT IDENTIFIER ::={connection 27}

connectionOrphanedVal	OBJECT-TYPE
	SYNTAX	 CounterBasedGauge64
	MAX-ACCESS read-only
	STATUS current
	DESCRIPTION "Connections without timer"

	::={connectionOrphaned 1}

connectionOrphanedMax	OBJECT-TYPE
	SYNTAX	 CounterBasedGauge64
	MAX-ACCESS read-only
	STATUS current
	DESCRIPTION "Connections without timer"

	::={connectionOrphaned 3}

connectionOrphanedLevelTable OBJECT-TYPE
	SYNTAX      SEQUENCE OF ConnectionOrphanedLevelEntry
	MAX-ACCESS  not-accessible
	STATUS      current
	DESCRIPTION
	"Table for connectionOrphaned"
	::={connectionOrphaned 4}

connectionOrphanedLevelEntry OBJECT-TYPE
	SYNTAX      ConnectionOrphanedLevelEntry
	MAX-ACCESS  not-accessible
	STATUS      current
	DESCRIPTION
	"Table entry for connectionOrphaned"
	INDEX { connectionOrphanedLevelName }
	::={connectionOrphanedLevelTable 1}

ConnectionOrphanedLevelEntry ::=
	SEQUENCE {
		connectionOrphanedLevelName	DisplayString,
		connectionOrphanedLevelVal	CounterBasedGauge64,
		connectionOrphanedLevelMax	CounterBasedGauge64
	}

connectionOrphanedLevelName OBJECT-TYPE
	SYNTAX      DisplayString
	MAX-ACCESS  not-accessible
	STATUS      current
	DESCRIPTION
	"Table entry display string for connectionOrphaned"
	::={connectionOrphanedLevelEntry 1}

connectionOrphanedLevelVal OBJECT-TYPE
	SYNTAX	 CounterBasedGauge64
	MAX-ACCESS  read-only
	STATUS      current
	DESCRIPTION
	"Table entry attribute for connectionOrphaned"
	::={connectionOrphanedLevelEntry 2}

connectionOrphanedLevelMax OBJECT-TYPE
	SYNTAX	 CounterBasedGauge64
	MAX-ACCESS  read-only
	STATUS      current
	DESCRIPTION
	"Table entry attribute for connectionOrphaned"
	::={connectionOrphanedLevelEntry 4}


connectionFailureShuntPackets	OBJECT IDENTIFIER ::={connection 40}

connectionFailureShuntPacketsVal	OBJECT-TYPE
	SYNTAX	 Counter64
	MAX-ACCESS read-only
	STATUS current
	DESCRIPTION "Shunted packets (connection create failure)"

	::={connectionFailureShuntPackets 1}

connectionFailureShuntPacketsMom	OBJECT-TYPE
	SYNTAX	 CounterBasedGauge64
	MAX-ACCESS read-only
	STATUS current
	DESCRIPTION "Shunted packets (connection create failure)"

	::={connectionFailureShuntPackets 2}

connectionFailureShuntPacketsMax	OBJECT-TYPE
	SYNTAX	 CounterBasedGauge64
	MAX-ACCESS read-only
	STATUS current
	DESCRIPTION "Shunted packets (connection create failure)"

	::={connectionFailureShuntPackets 3}

connectionFailureShuntPacketsLevelTable OBJECT-TYPE
	SYNTAX      SEQUENCE OF ConnectionFailureShuntPacketsLevelEntry
	MAX-ACCESS  not-accessible
	STATUS      current
	DESCRIPTION
	"Table for connectionFailureShuntPackets"
	::={connectionFailureShuntPackets 4}

connectionFailureShuntPacketsLevelEntry OBJECT-TYPE
	SYNTAX      ConnectionFailureShuntPacketsLevelEntry
	MAX-ACCESS  not-accessible
	STATUS      current
	DESCRIPTION
	"Table entry for connectionFailureShuntPackets"
	INDEX { connectionFailureShuntPacketsLevelName }
	::={connectionFailureShuntPacketsLevelTable 1}

ConnectionFailureShuntPacketsLevelEntry ::=
	SEQUENCE {
		connectionFailureShuntPacketsLevelName	DisplayString,
		connectionFailureShuntPacketsLevelVal	Counter64,
		connectionFailureShuntPacketsLevelMom	CounterBasedGauge64,
		connectionFailureShuntPacketsLevelMax	CounterBasedGauge64
	}

connectionFailureShuntPacketsLevelName OBJECT-TYPE
	SYNTAX      DisplayString
	MAX-ACCESS  not-accessible
	STATUS      current
	DESCRIPTION
	"Table entry display string for connectionFailureShuntPackets"
	::={connectionFailureShuntPacketsLevelEntry 1}

connectionFailureShuntPacketsLevelVal OBJECT-TYPE
	SYNTAX	 Counter64
	MAX-ACCESS  read-only
	STATUS      current
	DESCRIPTION
	"Table entry attribute for connectionFailureShuntPackets"
	::={connectionFailureShuntPacketsLevelEntry 2}

connectionFailureShuntPacketsLevelMom OBJECT-TYPE
	SYNTAX	 CounterBasedGauge64
	MAX-ACCESS  read-only
	STATUS      current
	DESCRIPTION
	"Table entry attribute for connectionFailureShuntPackets"
	::={connectionFailureShuntPacketsLevelEntry 3}

connectionFailureShuntPacketsLevelMax OBJECT-TYPE
	SYNTAX	 CounterBasedGauge64
	MAX-ACCESS  read-only
	STATUS      current
	DESCRIPTION
	"Table entry attribute for connectionFailureShuntPackets"
	::={connectionFailureShuntPacketsLevelEntry 4}


connectionFailureShuntBytes	OBJECT IDENTIFIER ::={connection 41}

connectionFailureShuntBytesVal	OBJECT-TYPE
	SYNTAX	 Counter64
	MAX-ACCESS read-only
	STATUS current
	DESCRIPTION "Shunted bytes (connection create failure)"

	::={connectionFailureShuntBytes 1}

connectionFailureShuntBytesMom	OBJECT-TYPE
	SYNTAX	 CounterBasedGauge64
	MAX-ACCESS read-only
	STATUS current
	DESCRIPTION "Shunted bytes (connection create failure)"

	::={connectionFailureShuntBytes 2}

connectionFailureShuntBytesMax	OBJECT-TYPE
	SYNTAX	 CounterBasedGauge64
	MAX-ACCESS read-only
	STATUS current
	DESCRIPTION "Shunted bytes (connection create failure)"

	::={connectionFailureShuntBytes 3}

connectionFailureShuntBytesLevelTable OBJECT-TYPE
	SYNTAX      SEQUENCE OF ConnectionFailureShuntBytesLevelEntry
	MAX-ACCESS  not-accessible
	STATUS      current
	DESCRIPTION
	"Table for connectionFailureShuntBytes"
	::={connectionFailureShuntBytes 4}

connectionFailureShuntBytesLevelEntry OBJECT-TYPE
	SYNTAX      ConnectionFailureShuntBytesLevelEntry
	MAX-ACCESS  not-accessible
	STATUS      current
	DESCRIPTION
	"Table entry for connectionFailureShuntBytes"
	INDEX { connectionFailureShuntBytesLevelName }
	::={connectionFailureShuntBytesLevelTable 1}

ConnectionFailureShuntBytesLevelEntry ::=
	SEQUENCE {
		connectionFailureShuntBytesLevelName	DisplayString,
		connectionFailureShuntBytesLevelVal	Counter64,
		connectionFailureShuntBytesLevelMom	CounterBasedGauge64,
		connectionFailureShuntBytesLevelMax	CounterBasedGauge64
	}

connectionFailureShuntBytesLevelName OBJECT-TYPE
	SYNTAX      DisplayString
	MAX-ACCESS  not-accessible
	STATUS      current
	DESCRIPTION
	"Table entry display string for connectionFailureShuntBytes"
	::={connectionFailureShuntBytesLevelEntry 1}

connectionFailureShuntBytesLevelVal OBJECT-TYPE
	SYNTAX	 Counter64
	MAX-ACCESS  read-only
	STATUS      current
	DESCRIPTION
	"Table entry attribute for connectionFailureShuntBytes"
	::={connectionFailureShuntBytesLevelEntry 2}

connectionFailureShuntBytesLevelMom OBJECT-TYPE
	SYNTAX	 CounterBasedGauge64
	MAX-ACCESS  read-only
	STATUS      current
	DESCRIPTION
	"Table entry attribute for connectionFailureShuntBytes"
	::={connectionFailureShuntBytesLevelEntry 3}

connectionFailureShuntBytesLevelMax OBJECT-TYPE
	SYNTAX	 CounterBasedGauge64
	MAX-ACCESS  read-only
	STATUS      current
	DESCRIPTION
	"Table entry attribute for connectionFailureShuntBytes"
	::={connectionFailureShuntBytesLevelEntry 4}


connectionTrafficAfterClose	OBJECT IDENTIFIER ::={connection 42}

connectionTrafficAfterCloseVal	OBJECT-TYPE
	SYNTAX	 Counter64
	MAX-ACCESS read-only
	STATUS current
	DESCRIPTION "Bytes received after connection close"

	::={connectionTrafficAfterClose 1}

connectionTrafficAfterCloseMom	OBJECT-TYPE
	SYNTAX	 CounterBasedGauge64
	MAX-ACCESS read-only
	STATUS current
	DESCRIPTION "Bytes received after connection close"

	::={connectionTrafficAfterClose 2}

connectionTrafficAfterCloseMax	OBJECT-TYPE
	SYNTAX	 CounterBasedGauge64
	MAX-ACCESS read-only
	STATUS current
	DESCRIPTION "Bytes received after connection close"

	::={connectionTrafficAfterClose 3}

connectionTrafficAfterCloseLevelTable OBJECT-TYPE
	SYNTAX      SEQUENCE OF ConnectionTrafficAfterCloseLevelEntry
	MAX-ACCESS  not-accessible
	STATUS      current
	DESCRIPTION
	"Table for connectionTrafficAfterClose"
	::={connectionTrafficAfterClose 4}

connectionTrafficAfterCloseLevelEntry OBJECT-TYPE
	SYNTAX      ConnectionTrafficAfterCloseLevelEntry
	MAX-ACCESS  not-accessible
	STATUS      current
	DESCRIPTION
	"Table entry for connectionTrafficAfterClose"
	INDEX { connectionTrafficAfterCloseLevelName }
	::={connectionTrafficAfterCloseLevelTable 1}

ConnectionTrafficAfterCloseLevelEntry ::=
	SEQUENCE {
		connectionTrafficAfterCloseLevelName	DisplayString,
		connectionTrafficAfterCloseLevelVal	Counter64,
		connectionTrafficAfterCloseLevelMom	CounterBasedGauge64,
		connectionTrafficAfterCloseLevelMax	CounterBasedGauge64
	}

connectionTrafficAfterCloseLevelName OBJECT-TYPE
	SYNTAX      DisplayString
	MAX-ACCESS  not-accessible
	STATUS      current
	DESCRIPTION
	"Table entry display string for connectionTrafficAfterClose"
	::={connectionTrafficAfterCloseLevelEntry 1}

connectionTrafficAfterCloseLevelVal OBJECT-TYPE
	SYNTAX	 Counter64
	MAX-ACCESS  read-only
	STATUS      current
	DESCRIPTION
	"Table entry attribute for connectionTrafficAfterClose"
	::={connectionTrafficAfterCloseLevelEntry 2}

connectionTrafficAfterCloseLevelMom OBJECT-TYPE
	SYNTAX	 CounterBasedGauge64
	MAX-ACCESS  read-only
	STATUS      current
	DESCRIPTION
	"Table entry attribute for connectionTrafficAfterClose"
	::={connectionTrafficAfterCloseLevelEntry 3}

connectionTrafficAfterCloseLevelMax OBJECT-TYPE
	SYNTAX	 CounterBasedGauge64
	MAX-ACCESS  read-only
	STATUS      current
	DESCRIPTION
	"Table entry attribute for connectionTrafficAfterClose"
	::={connectionTrafficAfterCloseLevelEntry 4}


connectionRefusedRewriteFailure	OBJECT IDENTIFIER ::={connection 43}

connectionRefusedRewriteFailureVal	OBJECT-TYPE
	SYNTAX	 Counter64
	MAX-ACCESS read-only
	STATUS current
	DESCRIPTION "Attempts refused (rewrite failure)"

	::={connectionRefusedRewriteFailure 1}

connectionRefusedRewriteFailureMom	OBJECT-TYPE
	SYNTAX	 CounterBasedGauge64
	MAX-ACCESS read-only
	STATUS current
	DESCRIPTION "Attempts refused (rewrite failure)"

	::={connectionRefusedRewriteFailure 2}

connectionRefusedRewriteFailureMax	OBJECT-TYPE
	SYNTAX	 CounterBasedGauge64
	MAX-ACCESS read-only
	STATUS current
	DESCRIPTION "Attempts refused (rewrite failure)"

	::={connectionRefusedRewriteFailure 3}

connectionRefusedRewriteFailureLevelTable OBJECT-TYPE
	SYNTAX      SEQUENCE OF ConnectionRefusedRewriteFailureLevelEntry
	MAX-ACCESS  not-accessible
	STATUS      current
	DESCRIPTION
	"Table for connectionRefusedRewriteFailure"
	::={connectionRefusedRewriteFailure 4}

connectionRefusedRewriteFailureLevelEntry OBJECT-TYPE
	SYNTAX      ConnectionRefusedRewriteFailureLevelEntry
	MAX-ACCESS  not-accessible
	STATUS      current
	DESCRIPTION
	"Table entry for connectionRefusedRewriteFailure"
	INDEX { connectionRefusedRewriteFailureLevelName }
	::={connectionRefusedRewriteFailureLevelTable 1}

ConnectionRefusedRewriteFailureLevelEntry ::=
	SEQUENCE {
		connectionRefusedRewriteFailureLevelName	DisplayString,
		connectionRefusedRewriteFailureLevelVal	Counter64,
		connectionRefusedRewriteFailureLevelMom	CounterBasedGauge64,
		connectionRefusedRewriteFailureLevelMax	CounterBasedGauge64
	}

connectionRefusedRewriteFailureLevelName OBJECT-TYPE
	SYNTAX      DisplayString
	MAX-ACCESS  not-accessible
	STATUS      current
	DESCRIPTION
	"Table entry display string for connectionRefusedRewriteFailure"
	::={connectionRefusedRewriteFailureLevelEntry 1}

connectionRefusedRewriteFailureLevelVal OBJECT-TYPE
	SYNTAX	 Counter64
	MAX-ACCESS  read-only
	STATUS      current
	DESCRIPTION
	"Table entry attribute for connectionRefusedRewriteFailure"
	::={connectionRefusedRewriteFailureLevelEntry 2}

connectionRefusedRewriteFailureLevelMom OBJECT-TYPE
	SYNTAX	 CounterBasedGauge64
	MAX-ACCESS  read-only
	STATUS      current
	DESCRIPTION
	"Table entry attribute for connectionRefusedRewriteFailure"
	::={connectionRefusedRewriteFailureLevelEntry 3}

connectionRefusedRewriteFailureLevelMax OBJECT-TYPE
	SYNTAX	 CounterBasedGauge64
	MAX-ACCESS  read-only
	STATUS      current
	DESCRIPTION
	"Table entry attribute for connectionRefusedRewriteFailure"
	::={connectionRefusedRewriteFailureLevelEntry 4}


connectionPushUpdates	OBJECT IDENTIFIER ::={connection 44}

connectionPushUpdatesVal	OBJECT-TYPE
	SYNTAX	 Counter64
	MAX-ACCESS read-only
	STATUS current
	DESCRIPTION "Updates sent (push updates))"

	::={connectionPushUpdates 1}

connectionPushUpdatesMom	OBJECT-TYPE
	SYNTAX	 CounterBasedGauge64
	MAX-ACCESS read-only
	STATUS current
	DESCRIPTION "Updates sent (push updates))"

	::={connectionPushUpdates 2}

connectionPushUpdatesMax	OBJECT-TYPE
	SYNTAX	 CounterBasedGauge64
	MAX-ACCESS read-only
	STATUS current
	DESCRIPTION "Updates sent (push updates))"

	::={connectionPushUpdates 3}

connectionPushUpdatesLevelTable OBJECT-TYPE
	SYNTAX      SEQUENCE OF ConnectionPushUpdatesLevelEntry
	MAX-ACCESS  not-accessible
	STATUS      current
	DESCRIPTION
	"Table for connectionPushUpdates"
	::={connectionPushUpdates 4}

connectionPushUpdatesLevelEntry OBJECT-TYPE
	SYNTAX      ConnectionPushUpdatesLevelEntry
	MAX-ACCESS  not-accessible
	STATUS      current
	DESCRIPTION
	"Table entry for connectionPushUpdates"
	INDEX { connectionPushUpdatesLevelName }
	::={connectionPushUpdatesLevelTable 1}

ConnectionPushUpdatesLevelEntry ::=
	SEQUENCE {
		connectionPushUpdatesLevelName	DisplayString,
		connectionPushUpdatesLevelVal	Counter64,
		connectionPushUpdatesLevelMom	CounterBasedGauge64,
		connectionPushUpdatesLevelMax	CounterBasedGauge64
	}

connectionPushUpdatesLevelName OBJECT-TYPE
	SYNTAX      DisplayString
	MAX-ACCESS  not-accessible
	STATUS      current
	DESCRIPTION
	"Table entry display string for connectionPushUpdates"
	::={connectionPushUpdatesLevelEntry 1}

connectionPushUpdatesLevelVal OBJECT-TYPE
	SYNTAX	 Counter64
	MAX-ACCESS  read-only
	STATUS      current
	DESCRIPTION
	"Table entry attribute for connectionPushUpdates"
	::={connectionPushUpdatesLevelEntry 2}

connectionPushUpdatesLevelMom OBJECT-TYPE
	SYNTAX	 CounterBasedGauge64
	MAX-ACCESS  read-only
	STATUS      current
	DESCRIPTION
	"Table entry attribute for connectionPushUpdates"
	::={connectionPushUpdatesLevelEntry 3}

connectionPushUpdatesLevelMax OBJECT-TYPE
	SYNTAX	 CounterBasedGauge64
	MAX-ACCESS  read-only
	STATUS      current
	DESCRIPTION
	"Table entry attribute for connectionPushUpdates"
	::={connectionPushUpdatesLevelEntry 4}


connectionUpdateBytes	OBJECT IDENTIFIER ::={connection 45}

connectionUpdateBytesVal	OBJECT-TYPE
	SYNTAX	 Counter64
	MAX-ACCESS read-only
	STATUS current
	DESCRIPTION "Bytes sent in connection updates"

	::={connectionUpdateBytes 1}

connectionUpdateBytesMom	OBJECT-TYPE
	SYNTAX	 CounterBasedGauge64
	MAX-ACCESS read-only
	STATUS current
	DESCRIPTION "Bytes sent in connection updates"

	::={connectionUpdateBytes 2}

connectionUpdateBytesMax	OBJECT-TYPE
	SYNTAX	 CounterBasedGauge64
	MAX-ACCESS read-only
	STATUS current
	DESCRIPTION "Bytes sent in connection updates"

	::={connectionUpdateBytes 3}

connectionUpdateBytesLevelTable OBJECT-TYPE
	SYNTAX      SEQUENCE OF ConnectionUpdateBytesLevelEntry
	MAX-ACCESS  not-accessible
	STATUS      current
	DESCRIPTION
	"Table for connectionUpdateBytes"
	::={connectionUpdateBytes 4}

connectionUpdateBytesLevelEntry OBJECT-TYPE
	SYNTAX      ConnectionUpdateBytesLevelEntry
	MAX-ACCESS  not-accessible
	STATUS      current
	DESCRIPTION
	"Table entry for connectionUpdateBytes"
	INDEX { connectionUpdateBytesLevelName }
	::={connectionUpdateBytesLevelTable 1}

ConnectionUpdateBytesLevelEntry ::=
	SEQUENCE {
		connectionUpdateBytesLevelName	DisplayString,
		connectionUpdateBytesLevelVal	Counter64,
		connectionUpdateBytesLevelMom	CounterBasedGauge64,
		connectionUpdateBytesLevelMax	CounterBasedGauge64
	}

connectionUpdateBytesLevelName OBJECT-TYPE
	SYNTAX      DisplayString
	MAX-ACCESS  not-accessible
	STATUS      current
	DESCRIPTION
	"Table entry display string for connectionUpdateBytes"
	::={connectionUpdateBytesLevelEntry 1}

connectionUpdateBytesLevelVal OBJECT-TYPE
	SYNTAX	 Counter64
	MAX-ACCESS  read-only
	STATUS      current
	DESCRIPTION
	"Table entry attribute for connectionUpdateBytes"
	::={connectionUpdateBytesLevelEntry 2}

connectionUpdateBytesLevelMom OBJECT-TYPE
	SYNTAX	 CounterBasedGauge64
	MAX-ACCESS  read-only
	STATUS      current
	DESCRIPTION
	"Table entry attribute for connectionUpdateBytes"
	::={connectionUpdateBytesLevelEntry 3}

connectionUpdateBytesLevelMax OBJECT-TYPE
	SYNTAX	 CounterBasedGauge64
	MAX-ACCESS  read-only
	STATUS      current
	DESCRIPTION
	"Table entry attribute for connectionUpdateBytes"
	::={connectionUpdateBytesLevelEntry 4}


connectionPushUpdateBytes	OBJECT IDENTIFIER ::={connection 46}

connectionPushUpdateBytesVal	OBJECT-TYPE
	SYNTAX	 Counter64
	MAX-ACCESS read-only
	STATUS current
	DESCRIPTION "Bytes sent in connection updates (push updates)"

	::={connectionPushUpdateBytes 1}

connectionPushUpdateBytesMom	OBJECT-TYPE
	SYNTAX	 CounterBasedGauge64
	MAX-ACCESS read-only
	STATUS current
	DESCRIPTION "Bytes sent in connection updates (push updates)"

	::={connectionPushUpdateBytes 2}

connectionPushUpdateBytesMax	OBJECT-TYPE
	SYNTAX	 CounterBasedGauge64
	MAX-ACCESS read-only
	STATUS current
	DESCRIPTION "Bytes sent in connection updates (push updates)"

	::={connectionPushUpdateBytes 3}

connectionPushUpdateBytesLevelTable OBJECT-TYPE
	SYNTAX      SEQUENCE OF ConnectionPushUpdateBytesLevelEntry
	MAX-ACCESS  not-accessible
	STATUS      current
	DESCRIPTION
	"Table for connectionPushUpdateBytes"
	::={connectionPushUpdateBytes 4}

connectionPushUpdateBytesLevelEntry OBJECT-TYPE
	SYNTAX      ConnectionPushUpdateBytesLevelEntry
	MAX-ACCESS  not-accessible
	STATUS      current
	DESCRIPTION
	"Table entry for connectionPushUpdateBytes"
	INDEX { connectionPushUpdateBytesLevelName }
	::={connectionPushUpdateBytesLevelTable 1}

ConnectionPushUpdateBytesLevelEntry ::=
	SEQUENCE {
		connectionPushUpdateBytesLevelName	DisplayString,
		connectionPushUpdateBytesLevelVal	Counter64,
		connectionPushUpdateBytesLevelMom	CounterBasedGauge64,
		connectionPushUpdateBytesLevelMax	CounterBasedGauge64
	}

connectionPushUpdateBytesLevelName OBJECT-TYPE
	SYNTAX      DisplayString
	MAX-ACCESS  not-accessible
	STATUS      current
	DESCRIPTION
	"Table entry display string for connectionPushUpdateBytes"
	::={connectionPushUpdateBytesLevelEntry 1}

connectionPushUpdateBytesLevelVal OBJECT-TYPE
	SYNTAX	 Counter64
	MAX-ACCESS  read-only
	STATUS      current
	DESCRIPTION
	"Table entry attribute for connectionPushUpdateBytes"
	::={connectionPushUpdateBytesLevelEntry 2}

connectionPushUpdateBytesLevelMom OBJECT-TYPE
	SYNTAX	 CounterBasedGauge64
	MAX-ACCESS  read-only
	STATUS      current
	DESCRIPTION
	"Table entry attribute for connectionPushUpdateBytes"
	::={connectionPushUpdateBytesLevelEntry 3}

connectionPushUpdateBytesLevelMax OBJECT-TYPE
	SYNTAX	 CounterBasedGauge64
	MAX-ACCESS  read-only
	STATUS      current
	DESCRIPTION
	"Table entry attribute for connectionPushUpdateBytes"
	::={connectionPushUpdateBytesLevelEntry 4}


connectionFilteredUpdates	OBJECT IDENTIFIER ::={connection 47}

connectionFilteredUpdatesVal	OBJECT-TYPE
	SYNTAX	 Counter64
	MAX-ACCESS read-only
	STATUS current
	DESCRIPTION "Filtered out updates"

	::={connectionFilteredUpdates 1}

connectionFilteredUpdatesMom	OBJECT-TYPE
	SYNTAX	 CounterBasedGauge64
	MAX-ACCESS read-only
	STATUS current
	DESCRIPTION "Filtered out updates"

	::={connectionFilteredUpdates 2}

connectionFilteredUpdatesMax	OBJECT-TYPE
	SYNTAX	 CounterBasedGauge64
	MAX-ACCESS read-only
	STATUS current
	DESCRIPTION "Filtered out updates"

	::={connectionFilteredUpdates 3}

connectionFilteredUpdatesLevelTable OBJECT-TYPE
	SYNTAX      SEQUENCE OF ConnectionFilteredUpdatesLevelEntry
	MAX-ACCESS  not-accessible
	STATUS      current
	DESCRIPTION
	"Table for connectionFilteredUpdates"
	::={connectionFilteredUpdates 4}

connectionFilteredUpdatesLevelEntry OBJECT-TYPE
	SYNTAX      ConnectionFilteredUpdatesLevelEntry
	MAX-ACCESS  not-accessible
	STATUS      current
	DESCRIPTION
	"Table entry for connectionFilteredUpdates"
	INDEX { connectionFilteredUpdatesLevelName }
	::={connectionFilteredUpdatesLevelTable 1}

ConnectionFilteredUpdatesLevelEntry ::=
	SEQUENCE {
		connectionFilteredUpdatesLevelName	DisplayString,
		connectionFilteredUpdatesLevelVal	Counter64,
		connectionFilteredUpdatesLevelMom	CounterBasedGauge64,
		connectionFilteredUpdatesLevelMax	CounterBasedGauge64
	}

connectionFilteredUpdatesLevelName OBJECT-TYPE
	SYNTAX      DisplayString
	MAX-ACCESS  not-accessible
	STATUS      current
	DESCRIPTION
	"Table entry display string for connectionFilteredUpdates"
	::={connectionFilteredUpdatesLevelEntry 1}

connectionFilteredUpdatesLevelVal OBJECT-TYPE
	SYNTAX	 Counter64
	MAX-ACCESS  read-only
	STATUS      current
	DESCRIPTION
	"Table entry attribute for connectionFilteredUpdates"
	::={connectionFilteredUpdatesLevelEntry 2}

connectionFilteredUpdatesLevelMom OBJECT-TYPE
	SYNTAX	 CounterBasedGauge64
	MAX-ACCESS  read-only
	STATUS      current
	DESCRIPTION
	"Table entry attribute for connectionFilteredUpdates"
	::={connectionFilteredUpdatesLevelEntry 3}

connectionFilteredUpdatesLevelMax OBJECT-TYPE
	SYNTAX	 CounterBasedGauge64
	MAX-ACCESS  read-only
	STATUS      current
	DESCRIPTION
	"Table entry attribute for connectionFilteredUpdates"
	::={connectionFilteredUpdatesLevelEntry 4}


connectionDestroyedStalePassback	OBJECT IDENTIFIER ::={connection 48}

connectionDestroyedStalePassbackVal	OBJECT-TYPE
	SYNTAX	 Counter64
	MAX-ACCESS read-only
	STATUS current
	DESCRIPTION "Connections destroyed on stale passback"

	::={connectionDestroyedStalePassback 1}

connectionDestroyedStalePassbackMom	OBJECT-TYPE
	SYNTAX	 CounterBasedGauge64
	MAX-ACCESS read-only
	STATUS current
	DESCRIPTION "Connections destroyed on stale passback"

	::={connectionDestroyedStalePassback 2}

connectionDestroyedStalePassbackMax	OBJECT-TYPE
	SYNTAX	 CounterBasedGauge64
	MAX-ACCESS read-only
	STATUS current
	DESCRIPTION "Connections destroyed on stale passback"

	::={connectionDestroyedStalePassback 3}

connectionDestroyedStalePassbackLevelTable OBJECT-TYPE
	SYNTAX      SEQUENCE OF ConnectionDestroyedStalePassbackLevelEntry
	MAX-ACCESS  not-accessible
	STATUS      current
	DESCRIPTION
	"Table for connectionDestroyedStalePassback"
	::={connectionDestroyedStalePassback 4}

connectionDestroyedStalePassbackLevelEntry OBJECT-TYPE
	SYNTAX      ConnectionDestroyedStalePassbackLevelEntry
	MAX-ACCESS  not-accessible
	STATUS      current
	DESCRIPTION
	"Table entry for connectionDestroyedStalePassback"
	INDEX { connectionDestroyedStalePassbackLevelName }
	::={connectionDestroyedStalePassbackLevelTable 1}

ConnectionDestroyedStalePassbackLevelEntry ::=
	SEQUENCE {
		connectionDestroyedStalePassbackLevelName	DisplayString,
		connectionDestroyedStalePassbackLevelVal	Counter64,
		connectionDestroyedStalePassbackLevelMom	CounterBasedGauge64,
		connectionDestroyedStalePassbackLevelMax	CounterBasedGauge64
	}

connectionDestroyedStalePassbackLevelName OBJECT-TYPE
	SYNTAX      DisplayString
	MAX-ACCESS  not-accessible
	STATUS      current
	DESCRIPTION
	"Table entry display string for connectionDestroyedStalePassback"
	::={connectionDestroyedStalePassbackLevelEntry 1}

connectionDestroyedStalePassbackLevelVal OBJECT-TYPE
	SYNTAX	 Counter64
	MAX-ACCESS  read-only
	STATUS      current
	DESCRIPTION
	"Table entry attribute for connectionDestroyedStalePassback"
	::={connectionDestroyedStalePassbackLevelEntry 2}

connectionDestroyedStalePassbackLevelMom OBJECT-TYPE
	SYNTAX	 CounterBasedGauge64
	MAX-ACCESS  read-only
	STATUS      current
	DESCRIPTION
	"Table entry attribute for connectionDestroyedStalePassback"
	::={connectionDestroyedStalePassbackLevelEntry 3}

connectionDestroyedStalePassbackLevelMax OBJECT-TYPE
	SYNTAX	 CounterBasedGauge64
	MAX-ACCESS  read-only
	STATUS      current
	DESCRIPTION
	"Table entry attribute for connectionDestroyedStalePassback"
	::={connectionDestroyedStalePassbackLevelEntry 4}


connectionDestroyedLBUnset	OBJECT IDENTIFIER ::={connection 49}

connectionDestroyedLBUnsetVal	OBJECT-TYPE
	SYNTAX	 Counter64
	MAX-ACCESS read-only
	STATUS current
	DESCRIPTION "Connections destroyed on LB unset command"

	::={connectionDestroyedLBUnset 1}

connectionDestroyedLBUnsetMom	OBJECT-TYPE
	SYNTAX	 CounterBasedGauge64
	MAX-ACCESS read-only
	STATUS current
	DESCRIPTION "Connections destroyed on LB unset command"

	::={connectionDestroyedLBUnset 2}

connectionDestroyedLBUnsetMax	OBJECT-TYPE
	SYNTAX	 CounterBasedGauge64
	MAX-ACCESS read-only
	STATUS current
	DESCRIPTION "Connections destroyed on LB unset command"

	::={connectionDestroyedLBUnset 3}

connectionDestroyedLBUnsetLevelTable OBJECT-TYPE
	SYNTAX      SEQUENCE OF ConnectionDestroyedLBUnsetLevelEntry
	MAX-ACCESS  not-accessible
	STATUS      current
	DESCRIPTION
	"Table for connectionDestroyedLBUnset"
	::={connectionDestroyedLBUnset 4}

connectionDestroyedLBUnsetLevelEntry OBJECT-TYPE
	SYNTAX      ConnectionDestroyedLBUnsetLevelEntry
	MAX-ACCESS  not-accessible
	STATUS      current
	DESCRIPTION
	"Table entry for connectionDestroyedLBUnset"
	INDEX { connectionDestroyedLBUnsetLevelName }
	::={connectionDestroyedLBUnsetLevelTable 1}

ConnectionDestroyedLBUnsetLevelEntry ::=
	SEQUENCE {
		connectionDestroyedLBUnsetLevelName	DisplayString,
		connectionDestroyedLBUnsetLevelVal	Counter64,
		connectionDestroyedLBUnsetLevelMom	CounterBasedGauge64,
		connectionDestroyedLBUnsetLevelMax	CounterBasedGauge64
	}

connectionDestroyedLBUnsetLevelName OBJECT-TYPE
	SYNTAX      DisplayString
	MAX-ACCESS  not-accessible
	STATUS      current
	DESCRIPTION
	"Table entry display string for connectionDestroyedLBUnset"
	::={connectionDestroyedLBUnsetLevelEntry 1}

connectionDestroyedLBUnsetLevelVal OBJECT-TYPE
	SYNTAX	 Counter64
	MAX-ACCESS  read-only
	STATUS      current
	DESCRIPTION
	"Table entry attribute for connectionDestroyedLBUnset"
	::={connectionDestroyedLBUnsetLevelEntry 2}

connectionDestroyedLBUnsetLevelMom OBJECT-TYPE
	SYNTAX	 CounterBasedGauge64
	MAX-ACCESS  read-only
	STATUS      current
	DESCRIPTION
	"Table entry attribute for connectionDestroyedLBUnset"
	::={connectionDestroyedLBUnsetLevelEntry 3}

connectionDestroyedLBUnsetLevelMax OBJECT-TYPE
	SYNTAX	 CounterBasedGauge64
	MAX-ACCESS  read-only
	STATUS      current
	DESCRIPTION
	"Table entry attribute for connectionDestroyedLBUnset"
	::={connectionDestroyedLBUnsetLevelEntry 4}


connsync	OBJECT IDENTIFIER ::={sysdiag 60}

connsyncSeenSnt	OBJECT IDENTIFIER ::={connsync 1}

connsyncSeenSntVal	OBJECT-TYPE
	SYNTAX	 Counter64
	MAX-ACCESS read-only
	STATUS current
	DESCRIPTION "Seen sent"

	::={connsyncSeenSnt 1}

connsyncSeenSntMom	OBJECT-TYPE
	SYNTAX	 CounterBasedGauge64
	MAX-ACCESS read-only
	STATUS current
	DESCRIPTION "Seen sent"

	::={connsyncSeenSnt 2}

connsyncSeenSntMax	OBJECT-TYPE
	SYNTAX	 CounterBasedGauge64
	MAX-ACCESS read-only
	STATUS current
	DESCRIPTION "Seen sent"

	::={connsyncSeenSnt 3}

connsyncSeenSntLevelTable OBJECT-TYPE
	SYNTAX      SEQUENCE OF ConnsyncSeenSntLevelEntry
	MAX-ACCESS  not-accessible
	STATUS      current
	DESCRIPTION
	"Table for connsyncSeenSnt"
	::={connsyncSeenSnt 4}

connsyncSeenSntLevelEntry OBJECT-TYPE
	SYNTAX      ConnsyncSeenSntLevelEntry
	MAX-ACCESS  not-accessible
	STATUS      current
	DESCRIPTION
	"Table entry for connsyncSeenSnt"
	INDEX { connsyncSeenSntLevelName }
	::={connsyncSeenSntLevelTable 1}

ConnsyncSeenSntLevelEntry ::=
	SEQUENCE {
		connsyncSeenSntLevelName	DisplayString,
		connsyncSeenSntLevelVal	Counter64,
		connsyncSeenSntLevelMom	CounterBasedGauge64,
		connsyncSeenSntLevelMax	CounterBasedGauge64
	}

connsyncSeenSntLevelName OBJECT-TYPE
	SYNTAX      DisplayString
	MAX-ACCESS  not-accessible
	STATUS      current
	DESCRIPTION
	"Table entry display string for connsyncSeenSnt"
	::={connsyncSeenSntLevelEntry 1}

connsyncSeenSntLevelVal OBJECT-TYPE
	SYNTAX	 Counter64
	MAX-ACCESS  read-only
	STATUS      current
	DESCRIPTION
	"Table entry attribute for connsyncSeenSnt"
	::={connsyncSeenSntLevelEntry 2}

connsyncSeenSntLevelMom OBJECT-TYPE
	SYNTAX	 CounterBasedGauge64
	MAX-ACCESS  read-only
	STATUS      current
	DESCRIPTION
	"Table entry attribute for connsyncSeenSnt"
	::={connsyncSeenSntLevelEntry 3}

connsyncSeenSntLevelMax OBJECT-TYPE
	SYNTAX	 CounterBasedGauge64
	MAX-ACCESS  read-only
	STATUS      current
	DESCRIPTION
	"Table entry attribute for connsyncSeenSnt"
	::={connsyncSeenSntLevelEntry 4}


connsyncSeenRcv	OBJECT IDENTIFIER ::={connsync 2}

connsyncSeenRcvVal	OBJECT-TYPE
	SYNTAX	 Counter64
	MAX-ACCESS read-only
	STATUS current
	DESCRIPTION "Seen received"

	::={connsyncSeenRcv 1}

connsyncSeenRcvMom	OBJECT-TYPE
	SYNTAX	 CounterBasedGauge64
	MAX-ACCESS read-only
	STATUS current
	DESCRIPTION "Seen received"

	::={connsyncSeenRcv 2}

connsyncSeenRcvMax	OBJECT-TYPE
	SYNTAX	 CounterBasedGauge64
	MAX-ACCESS read-only
	STATUS current
	DESCRIPTION "Seen received"

	::={connsyncSeenRcv 3}

connsyncSeenRcvLevelTable OBJECT-TYPE
	SYNTAX      SEQUENCE OF ConnsyncSeenRcvLevelEntry
	MAX-ACCESS  not-accessible
	STATUS      current
	DESCRIPTION
	"Table for connsyncSeenRcv"
	::={connsyncSeenRcv 4}

connsyncSeenRcvLevelEntry OBJECT-TYPE
	SYNTAX      ConnsyncSeenRcvLevelEntry
	MAX-ACCESS  not-accessible
	STATUS      current
	DESCRIPTION
	"Table entry for connsyncSeenRcv"
	INDEX { connsyncSeenRcvLevelName }
	::={connsyncSeenRcvLevelTable 1}

ConnsyncSeenRcvLevelEntry ::=
	SEQUENCE {
		connsyncSeenRcvLevelName	DisplayString,
		connsyncSeenRcvLevelVal	Counter64,
		connsyncSeenRcvLevelMom	CounterBasedGauge64,
		connsyncSeenRcvLevelMax	CounterBasedGauge64
	}

connsyncSeenRcvLevelName OBJECT-TYPE
	SYNTAX      DisplayString
	MAX-ACCESS  not-accessible
	STATUS      current
	DESCRIPTION
	"Table entry display string for connsyncSeenRcv"
	::={connsyncSeenRcvLevelEntry 1}

connsyncSeenRcvLevelVal OBJECT-TYPE
	SYNTAX	 Counter64
	MAX-ACCESS  read-only
	STATUS      current
	DESCRIPTION
	"Table entry attribute for connsyncSeenRcv"
	::={connsyncSeenRcvLevelEntry 2}

connsyncSeenRcvLevelMom OBJECT-TYPE
	SYNTAX	 CounterBasedGauge64
	MAX-ACCESS  read-only
	STATUS      current
	DESCRIPTION
	"Table entry attribute for connsyncSeenRcv"
	::={connsyncSeenRcvLevelEntry 3}

connsyncSeenRcvLevelMax OBJECT-TYPE
	SYNTAX	 CounterBasedGauge64
	MAX-ACCESS  read-only
	STATUS      current
	DESCRIPTION
	"Table entry attribute for connsyncSeenRcv"
	::={connsyncSeenRcvLevelEntry 4}


connsyncUpdateSnt	OBJECT IDENTIFIER ::={connsync 3}

connsyncUpdateSntVal	OBJECT-TYPE
	SYNTAX	 Counter64
	MAX-ACCESS read-only
	STATUS current
	DESCRIPTION "Updates Sent"

	::={connsyncUpdateSnt 1}

connsyncUpdateSntMom	OBJECT-TYPE
	SYNTAX	 CounterBasedGauge64
	MAX-ACCESS read-only
	STATUS current
	DESCRIPTION "Updates Sent"

	::={connsyncUpdateSnt 2}

connsyncUpdateSntMax	OBJECT-TYPE
	SYNTAX	 CounterBasedGauge64
	MAX-ACCESS read-only
	STATUS current
	DESCRIPTION "Updates Sent"

	::={connsyncUpdateSnt 3}

connsyncUpdateSntLevelTable OBJECT-TYPE
	SYNTAX      SEQUENCE OF ConnsyncUpdateSntLevelEntry
	MAX-ACCESS  not-accessible
	STATUS      current
	DESCRIPTION
	"Table for connsyncUpdateSnt"
	::={connsyncUpdateSnt 4}

connsyncUpdateSntLevelEntry OBJECT-TYPE
	SYNTAX      ConnsyncUpdateSntLevelEntry
	MAX-ACCESS  not-accessible
	STATUS      current
	DESCRIPTION
	"Table entry for connsyncUpdateSnt"
	INDEX { connsyncUpdateSntLevelName }
	::={connsyncUpdateSntLevelTable 1}

ConnsyncUpdateSntLevelEntry ::=
	SEQUENCE {
		connsyncUpdateSntLevelName	DisplayString,
		connsyncUpdateSntLevelVal	Counter64,
		connsyncUpdateSntLevelMom	CounterBasedGauge64,
		connsyncUpdateSntLevelMax	CounterBasedGauge64
	}

connsyncUpdateSntLevelName OBJECT-TYPE
	SYNTAX      DisplayString
	MAX-ACCESS  not-accessible
	STATUS      current
	DESCRIPTION
	"Table entry display string for connsyncUpdateSnt"
	::={connsyncUpdateSntLevelEntry 1}

connsyncUpdateSntLevelVal OBJECT-TYPE
	SYNTAX	 Counter64
	MAX-ACCESS  read-only
	STATUS      current
	DESCRIPTION
	"Table entry attribute for connsyncUpdateSnt"
	::={connsyncUpdateSntLevelEntry 2}

connsyncUpdateSntLevelMom OBJECT-TYPE
	SYNTAX	 CounterBasedGauge64
	MAX-ACCESS  read-only
	STATUS      current
	DESCRIPTION
	"Table entry attribute for connsyncUpdateSnt"
	::={connsyncUpdateSntLevelEntry 3}

connsyncUpdateSntLevelMax OBJECT-TYPE
	SYNTAX	 CounterBasedGauge64
	MAX-ACCESS  read-only
	STATUS      current
	DESCRIPTION
	"Table entry attribute for connsyncUpdateSnt"
	::={connsyncUpdateSntLevelEntry 4}


connsyncSeenackRcv	OBJECT IDENTIFIER ::={connsync 4}

connsyncSeenackRcvVal	OBJECT-TYPE
	SYNTAX	 Counter64
	MAX-ACCESS read-only
	STATUS current
	DESCRIPTION "First updates received (seen-ack)"

	::={connsyncSeenackRcv 1}

connsyncSeenackRcvMom	OBJECT-TYPE
	SYNTAX	 CounterBasedGauge64
	MAX-ACCESS read-only
	STATUS current
	DESCRIPTION "First updates received (seen-ack)"

	::={connsyncSeenackRcv 2}

connsyncSeenackRcvMax	OBJECT-TYPE
	SYNTAX	 CounterBasedGauge64
	MAX-ACCESS read-only
	STATUS current
	DESCRIPTION "First updates received (seen-ack)"

	::={connsyncSeenackRcv 3}

connsyncSeenackRcvLevelTable OBJECT-TYPE
	SYNTAX      SEQUENCE OF ConnsyncSeenackRcvLevelEntry
	MAX-ACCESS  not-accessible
	STATUS      current
	DESCRIPTION
	"Table for connsyncSeenackRcv"
	::={connsyncSeenackRcv 4}

connsyncSeenackRcvLevelEntry OBJECT-TYPE
	SYNTAX      ConnsyncSeenackRcvLevelEntry
	MAX-ACCESS  not-accessible
	STATUS      current
	DESCRIPTION
	"Table entry for connsyncSeenackRcv"
	INDEX { connsyncSeenackRcvLevelName }
	::={connsyncSeenackRcvLevelTable 1}

ConnsyncSeenackRcvLevelEntry ::=
	SEQUENCE {
		connsyncSeenackRcvLevelName	DisplayString,
		connsyncSeenackRcvLevelVal	Counter64,
		connsyncSeenackRcvLevelMom	CounterBasedGauge64,
		connsyncSeenackRcvLevelMax	CounterBasedGauge64
	}

connsyncSeenackRcvLevelName OBJECT-TYPE
	SYNTAX      DisplayString
	MAX-ACCESS  not-accessible
	STATUS      current
	DESCRIPTION
	"Table entry display string for connsyncSeenackRcv"
	::={connsyncSeenackRcvLevelEntry 1}

connsyncSeenackRcvLevelVal OBJECT-TYPE
	SYNTAX	 Counter64
	MAX-ACCESS  read-only
	STATUS      current
	DESCRIPTION
	"Table entry attribute for connsyncSeenackRcv"
	::={connsyncSeenackRcvLevelEntry 2}

connsyncSeenackRcvLevelMom OBJECT-TYPE
	SYNTAX	 CounterBasedGauge64
	MAX-ACCESS  read-only
	STATUS      current
	DESCRIPTION
	"Table entry attribute for connsyncSeenackRcv"
	::={connsyncSeenackRcvLevelEntry 3}

connsyncSeenackRcvLevelMax OBJECT-TYPE
	SYNTAX	 CounterBasedGauge64
	MAX-ACCESS  read-only
	STATUS      current
	DESCRIPTION
	"Table entry attribute for connsyncSeenackRcv"
	::={connsyncSeenackRcvLevelEntry 4}


connsyncUpdateRcv	OBJECT IDENTIFIER ::={connsync 5}

connsyncUpdateRcvVal	OBJECT-TYPE
	SYNTAX	 Counter64
	MAX-ACCESS read-only
	STATUS current
	DESCRIPTION "Updates received"

	::={connsyncUpdateRcv 1}

connsyncUpdateRcvMom	OBJECT-TYPE
	SYNTAX	 CounterBasedGauge64
	MAX-ACCESS read-only
	STATUS current
	DESCRIPTION "Updates received"

	::={connsyncUpdateRcv 2}

connsyncUpdateRcvMax	OBJECT-TYPE
	SYNTAX	 CounterBasedGauge64
	MAX-ACCESS read-only
	STATUS current
	DESCRIPTION "Updates received"

	::={connsyncUpdateRcv 3}

connsyncUpdateRcvLevelTable OBJECT-TYPE
	SYNTAX      SEQUENCE OF ConnsyncUpdateRcvLevelEntry
	MAX-ACCESS  not-accessible
	STATUS      current
	DESCRIPTION
	"Table for connsyncUpdateRcv"
	::={connsyncUpdateRcv 4}

connsyncUpdateRcvLevelEntry OBJECT-TYPE
	SYNTAX      ConnsyncUpdateRcvLevelEntry
	MAX-ACCESS  not-accessible
	STATUS      current
	DESCRIPTION
	"Table entry for connsyncUpdateRcv"
	INDEX { connsyncUpdateRcvLevelName }
	::={connsyncUpdateRcvLevelTable 1}

ConnsyncUpdateRcvLevelEntry ::=
	SEQUENCE {
		connsyncUpdateRcvLevelName	DisplayString,
		connsyncUpdateRcvLevelVal	Counter64,
		connsyncUpdateRcvLevelMom	CounterBasedGauge64,
		connsyncUpdateRcvLevelMax	CounterBasedGauge64
	}

connsyncUpdateRcvLevelName OBJECT-TYPE
	SYNTAX      DisplayString
	MAX-ACCESS  not-accessible
	STATUS      current
	DESCRIPTION
	"Table entry display string for connsyncUpdateRcv"
	::={connsyncUpdateRcvLevelEntry 1}

connsyncUpdateRcvLevelVal OBJECT-TYPE
	SYNTAX	 Counter64
	MAX-ACCESS  read-only
	STATUS      current
	DESCRIPTION
	"Table entry attribute for connsyncUpdateRcv"
	::={connsyncUpdateRcvLevelEntry 2}

connsyncUpdateRcvLevelMom OBJECT-TYPE
	SYNTAX	 CounterBasedGauge64
	MAX-ACCESS  read-only
	STATUS      current
	DESCRIPTION
	"Table entry attribute for connsyncUpdateRcv"
	::={connsyncUpdateRcvLevelEntry 3}

connsyncUpdateRcvLevelMax OBJECT-TYPE
	SYNTAX	 CounterBasedGauge64
	MAX-ACCESS  read-only
	STATUS      current
	DESCRIPTION
	"Table entry attribute for connsyncUpdateRcv"
	::={connsyncUpdateRcvLevelEntry 4}


connsyncUnknownUpdateRcv	OBJECT IDENTIFIER ::={connsync 6}

connsyncUnknownUpdateRcvVal	OBJECT-TYPE
	SYNTAX	 Counter64
	MAX-ACCESS read-only
	STATUS current
	DESCRIPTION "Updates for unknown connections received"

	::={connsyncUnknownUpdateRcv 1}

connsyncUnknownUpdateRcvMom	OBJECT-TYPE
	SYNTAX	 CounterBasedGauge64
	MAX-ACCESS read-only
	STATUS current
	DESCRIPTION "Updates for unknown connections received"

	::={connsyncUnknownUpdateRcv 2}

connsyncUnknownUpdateRcvMax	OBJECT-TYPE
	SYNTAX	 CounterBasedGauge64
	MAX-ACCESS read-only
	STATUS current
	DESCRIPTION "Updates for unknown connections received"

	::={connsyncUnknownUpdateRcv 3}

connsyncUnknownUpdateRcvLevelTable OBJECT-TYPE
	SYNTAX      SEQUENCE OF ConnsyncUnknownUpdateRcvLevelEntry
	MAX-ACCESS  not-accessible
	STATUS      current
	DESCRIPTION
	"Table for connsyncUnknownUpdateRcv"
	::={connsyncUnknownUpdateRcv 4}

connsyncUnknownUpdateRcvLevelEntry OBJECT-TYPE
	SYNTAX      ConnsyncUnknownUpdateRcvLevelEntry
	MAX-ACCESS  not-accessible
	STATUS      current
	DESCRIPTION
	"Table entry for connsyncUnknownUpdateRcv"
	INDEX { connsyncUnknownUpdateRcvLevelName }
	::={connsyncUnknownUpdateRcvLevelTable 1}

ConnsyncUnknownUpdateRcvLevelEntry ::=
	SEQUENCE {
		connsyncUnknownUpdateRcvLevelName	DisplayString,
		connsyncUnknownUpdateRcvLevelVal	Counter64,
		connsyncUnknownUpdateRcvLevelMom	CounterBasedGauge64,
		connsyncUnknownUpdateRcvLevelMax	CounterBasedGauge64
	}

connsyncUnknownUpdateRcvLevelName OBJECT-TYPE
	SYNTAX      DisplayString
	MAX-ACCESS  not-accessible
	STATUS      current
	DESCRIPTION
	"Table entry display string for connsyncUnknownUpdateRcv"
	::={connsyncUnknownUpdateRcvLevelEntry 1}

connsyncUnknownUpdateRcvLevelVal OBJECT-TYPE
	SYNTAX	 Counter64
	MAX-ACCESS  read-only
	STATUS      current
	DESCRIPTION
	"Table entry attribute for connsyncUnknownUpdateRcv"
	::={connsyncUnknownUpdateRcvLevelEntry 2}

connsyncUnknownUpdateRcvLevelMom OBJECT-TYPE
	SYNTAX	 CounterBasedGauge64
	MAX-ACCESS  read-only
	STATUS      current
	DESCRIPTION
	"Table entry attribute for connsyncUnknownUpdateRcv"
	::={connsyncUnknownUpdateRcvLevelEntry 3}

connsyncUnknownUpdateRcvLevelMax OBJECT-TYPE
	SYNTAX	 CounterBasedGauge64
	MAX-ACCESS  read-only
	STATUS      current
	DESCRIPTION
	"Table entry attribute for connsyncUnknownUpdateRcv"
	::={connsyncUnknownUpdateRcvLevelEntry 4}


connsyncOutofsync	OBJECT IDENTIFIER ::={connsync 7}

connsyncOutofsyncVal	OBJECT-TYPE
	SYNTAX	 Counter64
	MAX-ACCESS read-only
	STATUS current
	DESCRIPTION "Out of syncs"

	::={connsyncOutofsync 1}

connsyncOutofsyncMom	OBJECT-TYPE
	SYNTAX	 CounterBasedGauge64
	MAX-ACCESS read-only
	STATUS current
	DESCRIPTION "Out of syncs"

	::={connsyncOutofsync 2}

connsyncOutofsyncMax	OBJECT-TYPE
	SYNTAX	 CounterBasedGauge64
	MAX-ACCESS read-only
	STATUS current
	DESCRIPTION "Out of syncs"

	::={connsyncOutofsync 3}

connsyncOutofsyncLevelTable OBJECT-TYPE
	SYNTAX      SEQUENCE OF ConnsyncOutofsyncLevelEntry
	MAX-ACCESS  not-accessible
	STATUS      current
	DESCRIPTION
	"Table for connsyncOutofsync"
	::={connsyncOutofsync 4}

connsyncOutofsyncLevelEntry OBJECT-TYPE
	SYNTAX      ConnsyncOutofsyncLevelEntry
	MAX-ACCESS  not-accessible
	STATUS      current
	DESCRIPTION
	"Table entry for connsyncOutofsync"
	INDEX { connsyncOutofsyncLevelName }
	::={connsyncOutofsyncLevelTable 1}

ConnsyncOutofsyncLevelEntry ::=
	SEQUENCE {
		connsyncOutofsyncLevelName	DisplayString,
		connsyncOutofsyncLevelVal	Counter64,
		connsyncOutofsyncLevelMom	CounterBasedGauge64,
		connsyncOutofsyncLevelMax	CounterBasedGauge64
	}

connsyncOutofsyncLevelName OBJECT-TYPE
	SYNTAX      DisplayString
	MAX-ACCESS  not-accessible
	STATUS      current
	DESCRIPTION
	"Table entry display string for connsyncOutofsync"
	::={connsyncOutofsyncLevelEntry 1}

connsyncOutofsyncLevelVal OBJECT-TYPE
	SYNTAX	 Counter64
	MAX-ACCESS  read-only
	STATUS      current
	DESCRIPTION
	"Table entry attribute for connsyncOutofsync"
	::={connsyncOutofsyncLevelEntry 2}

connsyncOutofsyncLevelMom OBJECT-TYPE
	SYNTAX	 CounterBasedGauge64
	MAX-ACCESS  read-only
	STATUS      current
	DESCRIPTION
	"Table entry attribute for connsyncOutofsync"
	::={connsyncOutofsyncLevelEntry 3}

connsyncOutofsyncLevelMax OBJECT-TYPE
	SYNTAX	 CounterBasedGauge64
	MAX-ACCESS  read-only
	STATUS      current
	DESCRIPTION
	"Table entry attribute for connsyncOutofsync"
	::={connsyncOutofsyncLevelEntry 4}


connsyncSynced	OBJECT IDENTIFIER ::={connsync 8}

connsyncSyncedVal	OBJECT-TYPE
	SYNTAX	 CounterBasedGauge64
	MAX-ACCESS read-only
	STATUS current
	DESCRIPTION "Connections actively syncing"

	::={connsyncSynced 1}

connsyncSyncedMax	OBJECT-TYPE
	SYNTAX	 CounterBasedGauge64
	MAX-ACCESS read-only
	STATUS current
	DESCRIPTION "Connections actively syncing"

	::={connsyncSynced 3}

connsyncSyncedLevelTable OBJECT-TYPE
	SYNTAX      SEQUENCE OF ConnsyncSyncedLevelEntry
	MAX-ACCESS  not-accessible
	STATUS      current
	DESCRIPTION
	"Table for connsyncSynced"
	::={connsyncSynced 4}

connsyncSyncedLevelEntry OBJECT-TYPE
	SYNTAX      ConnsyncSyncedLevelEntry
	MAX-ACCESS  not-accessible
	STATUS      current
	DESCRIPTION
	"Table entry for connsyncSynced"
	INDEX { connsyncSyncedLevelName }
	::={connsyncSyncedLevelTable 1}

ConnsyncSyncedLevelEntry ::=
	SEQUENCE {
		connsyncSyncedLevelName	DisplayString,
		connsyncSyncedLevelVal	CounterBasedGauge64,
		connsyncSyncedLevelMax	CounterBasedGauge64
	}

connsyncSyncedLevelName OBJECT-TYPE
	SYNTAX      DisplayString
	MAX-ACCESS  not-accessible
	STATUS      current
	DESCRIPTION
	"Table entry display string for connsyncSynced"
	::={connsyncSyncedLevelEntry 1}

connsyncSyncedLevelVal OBJECT-TYPE
	SYNTAX	 CounterBasedGauge64
	MAX-ACCESS  read-only
	STATUS      current
	DESCRIPTION
	"Table entry attribute for connsyncSynced"
	::={connsyncSyncedLevelEntry 2}

connsyncSyncedLevelMax OBJECT-TYPE
	SYNTAX	 CounterBasedGauge64
	MAX-ACCESS  read-only
	STATUS      current
	DESCRIPTION
	"Table entry attribute for connsyncSynced"
	::={connsyncSyncedLevelEntry 4}


connsyncDoubleSeen	OBJECT IDENTIFIER ::={connsync 9}

connsyncDoubleSeenVal	OBJECT-TYPE
	SYNTAX	 Counter64
	MAX-ACCESS read-only
	STATUS current
	DESCRIPTION "Double seen"

	::={connsyncDoubleSeen 1}

connsyncDoubleSeenMom	OBJECT-TYPE
	SYNTAX	 CounterBasedGauge64
	MAX-ACCESS read-only
	STATUS current
	DESCRIPTION "Double seen"

	::={connsyncDoubleSeen 2}

connsyncDoubleSeenMax	OBJECT-TYPE
	SYNTAX	 CounterBasedGauge64
	MAX-ACCESS read-only
	STATUS current
	DESCRIPTION "Double seen"

	::={connsyncDoubleSeen 3}

connsyncDoubleSeenLevelTable OBJECT-TYPE
	SYNTAX      SEQUENCE OF ConnsyncDoubleSeenLevelEntry
	MAX-ACCESS  not-accessible
	STATUS      current
	DESCRIPTION
	"Table for connsyncDoubleSeen"
	::={connsyncDoubleSeen 4}

connsyncDoubleSeenLevelEntry OBJECT-TYPE
	SYNTAX      ConnsyncDoubleSeenLevelEntry
	MAX-ACCESS  not-accessible
	STATUS      current
	DESCRIPTION
	"Table entry for connsyncDoubleSeen"
	INDEX { connsyncDoubleSeenLevelName }
	::={connsyncDoubleSeenLevelTable 1}

ConnsyncDoubleSeenLevelEntry ::=
	SEQUENCE {
		connsyncDoubleSeenLevelName	DisplayString,
		connsyncDoubleSeenLevelVal	Counter64,
		connsyncDoubleSeenLevelMom	CounterBasedGauge64,
		connsyncDoubleSeenLevelMax	CounterBasedGauge64
	}

connsyncDoubleSeenLevelName OBJECT-TYPE
	SYNTAX      DisplayString
	MAX-ACCESS  not-accessible
	STATUS      current
	DESCRIPTION
	"Table entry display string for connsyncDoubleSeen"
	::={connsyncDoubleSeenLevelEntry 1}

connsyncDoubleSeenLevelVal OBJECT-TYPE
	SYNTAX	 Counter64
	MAX-ACCESS  read-only
	STATUS      current
	DESCRIPTION
	"Table entry attribute for connsyncDoubleSeen"
	::={connsyncDoubleSeenLevelEntry 2}

connsyncDoubleSeenLevelMom OBJECT-TYPE
	SYNTAX	 CounterBasedGauge64
	MAX-ACCESS  read-only
	STATUS      current
	DESCRIPTION
	"Table entry attribute for connsyncDoubleSeen"
	::={connsyncDoubleSeenLevelEntry 3}

connsyncDoubleSeenLevelMax OBJECT-TYPE
	SYNTAX	 CounterBasedGauge64
	MAX-ACCESS  read-only
	STATUS      current
	DESCRIPTION
	"Table entry attribute for connsyncDoubleSeen"
	::={connsyncDoubleSeenLevelEntry 4}


connsyncHelloRcv	OBJECT IDENTIFIER ::={connsync 10}

connsyncHelloRcvVal	OBJECT-TYPE
	SYNTAX	 Counter64
	MAX-ACCESS read-only
	STATUS current
	DESCRIPTION "Hello received"

	::={connsyncHelloRcv 1}

connsyncHelloRcvMom	OBJECT-TYPE
	SYNTAX	 CounterBasedGauge64
	MAX-ACCESS read-only
	STATUS current
	DESCRIPTION "Hello received"

	::={connsyncHelloRcv 2}

connsyncHelloRcvMax	OBJECT-TYPE
	SYNTAX	 CounterBasedGauge64
	MAX-ACCESS read-only
	STATUS current
	DESCRIPTION "Hello received"

	::={connsyncHelloRcv 3}

connsyncHelloRcvLevelTable OBJECT-TYPE
	SYNTAX      SEQUENCE OF ConnsyncHelloRcvLevelEntry
	MAX-ACCESS  not-accessible
	STATUS      current
	DESCRIPTION
	"Table for connsyncHelloRcv"
	::={connsyncHelloRcv 4}

connsyncHelloRcvLevelEntry OBJECT-TYPE
	SYNTAX      ConnsyncHelloRcvLevelEntry
	MAX-ACCESS  not-accessible
	STATUS      current
	DESCRIPTION
	"Table entry for connsyncHelloRcv"
	INDEX { connsyncHelloRcvLevelName }
	::={connsyncHelloRcvLevelTable 1}

ConnsyncHelloRcvLevelEntry ::=
	SEQUENCE {
		connsyncHelloRcvLevelName	DisplayString,
		connsyncHelloRcvLevelVal	Counter64,
		connsyncHelloRcvLevelMom	CounterBasedGauge64,
		connsyncHelloRcvLevelMax	CounterBasedGauge64
	}

connsyncHelloRcvLevelName OBJECT-TYPE
	SYNTAX      DisplayString
	MAX-ACCESS  not-accessible
	STATUS      current
	DESCRIPTION
	"Table entry display string for connsyncHelloRcv"
	::={connsyncHelloRcvLevelEntry 1}

connsyncHelloRcvLevelVal OBJECT-TYPE
	SYNTAX	 Counter64
	MAX-ACCESS  read-only
	STATUS      current
	DESCRIPTION
	"Table entry attribute for connsyncHelloRcv"
	::={connsyncHelloRcvLevelEntry 2}

connsyncHelloRcvLevelMom OBJECT-TYPE
	SYNTAX	 CounterBasedGauge64
	MAX-ACCESS  read-only
	STATUS      current
	DESCRIPTION
	"Table entry attribute for connsyncHelloRcv"
	::={connsyncHelloRcvLevelEntry 3}

connsyncHelloRcvLevelMax OBJECT-TYPE
	SYNTAX	 CounterBasedGauge64
	MAX-ACCESS  read-only
	STATUS      current
	DESCRIPTION
	"Table entry attribute for connsyncHelloRcv"
	::={connsyncHelloRcvLevelEntry 4}


connsyncOutofsyncMissedRcv	OBJECT IDENTIFIER ::={connsync 11}

connsyncOutofsyncMissedRcvVal	OBJECT-TYPE
	SYNTAX	 Counter64
	MAX-ACCESS read-only
	STATUS current
	DESCRIPTION "Out of sync - missed rcv/late collision"

	::={connsyncOutofsyncMissedRcv 1}

connsyncOutofsyncMissedRcvMom	OBJECT-TYPE
	SYNTAX	 CounterBasedGauge64
	MAX-ACCESS read-only
	STATUS current
	DESCRIPTION "Out of sync - missed rcv/late collision"

	::={connsyncOutofsyncMissedRcv 2}

connsyncOutofsyncMissedRcvMax	OBJECT-TYPE
	SYNTAX	 CounterBasedGauge64
	MAX-ACCESS read-only
	STATUS current
	DESCRIPTION "Out of sync - missed rcv/late collision"

	::={connsyncOutofsyncMissedRcv 3}

connsyncOutofsyncMissedRcvLevelTable OBJECT-TYPE
	SYNTAX      SEQUENCE OF ConnsyncOutofsyncMissedRcvLevelEntry
	MAX-ACCESS  not-accessible
	STATUS      current
	DESCRIPTION
	"Table for connsyncOutofsyncMissedRcv"
	::={connsyncOutofsyncMissedRcv 4}

connsyncOutofsyncMissedRcvLevelEntry OBJECT-TYPE
	SYNTAX      ConnsyncOutofsyncMissedRcvLevelEntry
	MAX-ACCESS  not-accessible
	STATUS      current
	DESCRIPTION
	"Table entry for connsyncOutofsyncMissedRcv"
	INDEX { connsyncOutofsyncMissedRcvLevelName }
	::={connsyncOutofsyncMissedRcvLevelTable 1}

ConnsyncOutofsyncMissedRcvLevelEntry ::=
	SEQUENCE {
		connsyncOutofsyncMissedRcvLevelName	DisplayString,
		connsyncOutofsyncMissedRcvLevelVal	Counter64,
		connsyncOutofsyncMissedRcvLevelMom	CounterBasedGauge64,
		connsyncOutofsyncMissedRcvLevelMax	CounterBasedGauge64
	}

connsyncOutofsyncMissedRcvLevelName OBJECT-TYPE
	SYNTAX      DisplayString
	MAX-ACCESS  not-accessible
	STATUS      current
	DESCRIPTION
	"Table entry display string for connsyncOutofsyncMissedRcv"
	::={connsyncOutofsyncMissedRcvLevelEntry 1}

connsyncOutofsyncMissedRcvLevelVal OBJECT-TYPE
	SYNTAX	 Counter64
	MAX-ACCESS  read-only
	STATUS      current
	DESCRIPTION
	"Table entry attribute for connsyncOutofsyncMissedRcv"
	::={connsyncOutofsyncMissedRcvLevelEntry 2}

connsyncOutofsyncMissedRcvLevelMom OBJECT-TYPE
	SYNTAX	 CounterBasedGauge64
	MAX-ACCESS  read-only
	STATUS      current
	DESCRIPTION
	"Table entry attribute for connsyncOutofsyncMissedRcv"
	::={connsyncOutofsyncMissedRcvLevelEntry 3}

connsyncOutofsyncMissedRcvLevelMax OBJECT-TYPE
	SYNTAX	 CounterBasedGauge64
	MAX-ACCESS  read-only
	STATUS      current
	DESCRIPTION
	"Table entry attribute for connsyncOutofsyncMissedRcv"
	::={connsyncOutofsyncMissedRcvLevelEntry 4}


connsyncOutofsyncCollision	OBJECT IDENTIFIER ::={connsync 12}

connsyncOutofsyncCollisionVal	OBJECT-TYPE
	SYNTAX	 Counter64
	MAX-ACCESS read-only
	STATUS current
	DESCRIPTION "Out of sync - collision"

	::={connsyncOutofsyncCollision 1}

connsyncOutofsyncCollisionMom	OBJECT-TYPE
	SYNTAX	 CounterBasedGauge64
	MAX-ACCESS read-only
	STATUS current
	DESCRIPTION "Out of sync - collision"

	::={connsyncOutofsyncCollision 2}

connsyncOutofsyncCollisionMax	OBJECT-TYPE
	SYNTAX	 CounterBasedGauge64
	MAX-ACCESS read-only
	STATUS current
	DESCRIPTION "Out of sync - collision"

	::={connsyncOutofsyncCollision 3}

connsyncOutofsyncCollisionLevelTable OBJECT-TYPE
	SYNTAX      SEQUENCE OF ConnsyncOutofsyncCollisionLevelEntry
	MAX-ACCESS  not-accessible
	STATUS      current
	DESCRIPTION
	"Table for connsyncOutofsyncCollision"
	::={connsyncOutofsyncCollision 4}

connsyncOutofsyncCollisionLevelEntry OBJECT-TYPE
	SYNTAX      ConnsyncOutofsyncCollisionLevelEntry
	MAX-ACCESS  not-accessible
	STATUS      current
	DESCRIPTION
	"Table entry for connsyncOutofsyncCollision"
	INDEX { connsyncOutofsyncCollisionLevelName }
	::={connsyncOutofsyncCollisionLevelTable 1}

ConnsyncOutofsyncCollisionLevelEntry ::=
	SEQUENCE {
		connsyncOutofsyncCollisionLevelName	DisplayString,
		connsyncOutofsyncCollisionLevelVal	Counter64,
		connsyncOutofsyncCollisionLevelMom	CounterBasedGauge64,
		connsyncOutofsyncCollisionLevelMax	CounterBasedGauge64
	}

connsyncOutofsyncCollisionLevelName OBJECT-TYPE
	SYNTAX      DisplayString
	MAX-ACCESS  not-accessible
	STATUS      current
	DESCRIPTION
	"Table entry display string for connsyncOutofsyncCollision"
	::={connsyncOutofsyncCollisionLevelEntry 1}

connsyncOutofsyncCollisionLevelVal OBJECT-TYPE
	SYNTAX	 Counter64
	MAX-ACCESS  read-only
	STATUS      current
	DESCRIPTION
	"Table entry attribute for connsyncOutofsyncCollision"
	::={connsyncOutofsyncCollisionLevelEntry 2}

connsyncOutofsyncCollisionLevelMom OBJECT-TYPE
	SYNTAX	 CounterBasedGauge64
	MAX-ACCESS  read-only
	STATUS      current
	DESCRIPTION
	"Table entry attribute for connsyncOutofsyncCollision"
	::={connsyncOutofsyncCollisionLevelEntry 3}

connsyncOutofsyncCollisionLevelMax OBJECT-TYPE
	SYNTAX	 CounterBasedGauge64
	MAX-ACCESS  read-only
	STATUS      current
	DESCRIPTION
	"Table entry attribute for connsyncOutofsyncCollision"
	::={connsyncOutofsyncCollisionLevelEntry 4}


connsyncBadAdler	OBJECT IDENTIFIER ::={connsync 13}

connsyncBadAdlerVal	OBJECT-TYPE
	SYNTAX	 Counter64
	MAX-ACCESS read-only
	STATUS current
	DESCRIPTION "Updates for mismatching ARM"

	::={connsyncBadAdler 1}

connsyncBadAdlerMom	OBJECT-TYPE
	SYNTAX	 CounterBasedGauge64
	MAX-ACCESS read-only
	STATUS current
	DESCRIPTION "Updates for mismatching ARM"

	::={connsyncBadAdler 2}

connsyncBadAdlerMax	OBJECT-TYPE
	SYNTAX	 CounterBasedGauge64
	MAX-ACCESS read-only
	STATUS current
	DESCRIPTION "Updates for mismatching ARM"

	::={connsyncBadAdler 3}

connsyncBadAdlerLevelTable OBJECT-TYPE
	SYNTAX      SEQUENCE OF ConnsyncBadAdlerLevelEntry
	MAX-ACCESS  not-accessible
	STATUS      current
	DESCRIPTION
	"Table for connsyncBadAdler"
	::={connsyncBadAdler 4}

connsyncBadAdlerLevelEntry OBJECT-TYPE
	SYNTAX      ConnsyncBadAdlerLevelEntry
	MAX-ACCESS  not-accessible
	STATUS      current
	DESCRIPTION
	"Table entry for connsyncBadAdler"
	INDEX { connsyncBadAdlerLevelName }
	::={connsyncBadAdlerLevelTable 1}

ConnsyncBadAdlerLevelEntry ::=
	SEQUENCE {
		connsyncBadAdlerLevelName	DisplayString,
		connsyncBadAdlerLevelVal	Counter64,
		connsyncBadAdlerLevelMom	CounterBasedGauge64,
		connsyncBadAdlerLevelMax	CounterBasedGauge64
	}

connsyncBadAdlerLevelName OBJECT-TYPE
	SYNTAX      DisplayString
	MAX-ACCESS  not-accessible
	STATUS      current
	DESCRIPTION
	"Table entry display string for connsyncBadAdler"
	::={connsyncBadAdlerLevelEntry 1}

connsyncBadAdlerLevelVal OBJECT-TYPE
	SYNTAX	 Counter64
	MAX-ACCESS  read-only
	STATUS      current
	DESCRIPTION
	"Table entry attribute for connsyncBadAdler"
	::={connsyncBadAdlerLevelEntry 2}

connsyncBadAdlerLevelMom OBJECT-TYPE
	SYNTAX	 CounterBasedGauge64
	MAX-ACCESS  read-only
	STATUS      current
	DESCRIPTION
	"Table entry attribute for connsyncBadAdler"
	::={connsyncBadAdlerLevelEntry 3}

connsyncBadAdlerLevelMax OBJECT-TYPE
	SYNTAX	 CounterBasedGauge64
	MAX-ACCESS  read-only
	STATUS      current
	DESCRIPTION
	"Table entry attribute for connsyncBadAdler"
	::={connsyncBadAdlerLevelEntry 4}


connsyncPktOverflow	OBJECT IDENTIFIER ::={connsync 14}

connsyncPktOverflowVal	OBJECT-TYPE
	SYNTAX	 Counter64
	MAX-ACCESS read-only
	STATUS current
	DESCRIPTION "Update packet overflow"

	::={connsyncPktOverflow 1}

connsyncPktOverflowMom	OBJECT-TYPE
	SYNTAX	 CounterBasedGauge64
	MAX-ACCESS read-only
	STATUS current
	DESCRIPTION "Update packet overflow"

	::={connsyncPktOverflow 2}

connsyncPktOverflowMax	OBJECT-TYPE
	SYNTAX	 CounterBasedGauge64
	MAX-ACCESS read-only
	STATUS current
	DESCRIPTION "Update packet overflow"

	::={connsyncPktOverflow 3}

connsyncPktOverflowLevelTable OBJECT-TYPE
	SYNTAX      SEQUENCE OF ConnsyncPktOverflowLevelEntry
	MAX-ACCESS  not-accessible
	STATUS      current
	DESCRIPTION
	"Table for connsyncPktOverflow"
	::={connsyncPktOverflow 4}

connsyncPktOverflowLevelEntry OBJECT-TYPE
	SYNTAX      ConnsyncPktOverflowLevelEntry
	MAX-ACCESS  not-accessible
	STATUS      current
	DESCRIPTION
	"Table entry for connsyncPktOverflow"
	INDEX { connsyncPktOverflowLevelName }
	::={connsyncPktOverflowLevelTable 1}

ConnsyncPktOverflowLevelEntry ::=
	SEQUENCE {
		connsyncPktOverflowLevelName	DisplayString,
		connsyncPktOverflowLevelVal	Counter64,
		connsyncPktOverflowLevelMom	CounterBasedGauge64,
		connsyncPktOverflowLevelMax	CounterBasedGauge64
	}

connsyncPktOverflowLevelName OBJECT-TYPE
	SYNTAX      DisplayString
	MAX-ACCESS  not-accessible
	STATUS      current
	DESCRIPTION
	"Table entry display string for connsyncPktOverflow"
	::={connsyncPktOverflowLevelEntry 1}

connsyncPktOverflowLevelVal OBJECT-TYPE
	SYNTAX	 Counter64
	MAX-ACCESS  read-only
	STATUS      current
	DESCRIPTION
	"Table entry attribute for connsyncPktOverflow"
	::={connsyncPktOverflowLevelEntry 2}

connsyncPktOverflowLevelMom OBJECT-TYPE
	SYNTAX	 CounterBasedGauge64
	MAX-ACCESS  read-only
	STATUS      current
	DESCRIPTION
	"Table entry attribute for connsyncPktOverflow"
	::={connsyncPktOverflowLevelEntry 3}

connsyncPktOverflowLevelMax OBJECT-TYPE
	SYNTAX	 CounterBasedGauge64
	MAX-ACCESS  read-only
	STATUS      current
	DESCRIPTION
	"Table entry attribute for connsyncPktOverflow"
	::={connsyncPktOverflowLevelEntry 4}


connsyncCorruptPkt	OBJECT IDENTIFIER ::={connsync 15}

connsyncCorruptPktVal	OBJECT-TYPE
	SYNTAX	 Counter64
	MAX-ACCESS read-only
	STATUS current
	DESCRIPTION "Corrupt packet received"

	::={connsyncCorruptPkt 1}

connsyncCorruptPktMom	OBJECT-TYPE
	SYNTAX	 CounterBasedGauge64
	MAX-ACCESS read-only
	STATUS current
	DESCRIPTION "Corrupt packet received"

	::={connsyncCorruptPkt 2}

connsyncCorruptPktMax	OBJECT-TYPE
	SYNTAX	 CounterBasedGauge64
	MAX-ACCESS read-only
	STATUS current
	DESCRIPTION "Corrupt packet received"

	::={connsyncCorruptPkt 3}

connsyncCorruptPktLevelTable OBJECT-TYPE
	SYNTAX      SEQUENCE OF ConnsyncCorruptPktLevelEntry
	MAX-ACCESS  not-accessible
	STATUS      current
	DESCRIPTION
	"Table for connsyncCorruptPkt"
	::={connsyncCorruptPkt 4}

connsyncCorruptPktLevelEntry OBJECT-TYPE
	SYNTAX      ConnsyncCorruptPktLevelEntry
	MAX-ACCESS  not-accessible
	STATUS      current
	DESCRIPTION
	"Table entry for connsyncCorruptPkt"
	INDEX { connsyncCorruptPktLevelName }
	::={connsyncCorruptPktLevelTable 1}

ConnsyncCorruptPktLevelEntry ::=
	SEQUENCE {
		connsyncCorruptPktLevelName	DisplayString,
		connsyncCorruptPktLevelVal	Counter64,
		connsyncCorruptPktLevelMom	CounterBasedGauge64,
		connsyncCorruptPktLevelMax	CounterBasedGauge64
	}

connsyncCorruptPktLevelName OBJECT-TYPE
	SYNTAX      DisplayString
	MAX-ACCESS  not-accessible
	STATUS      current
	DESCRIPTION
	"Table entry display string for connsyncCorruptPkt"
	::={connsyncCorruptPktLevelEntry 1}

connsyncCorruptPktLevelVal OBJECT-TYPE
	SYNTAX	 Counter64
	MAX-ACCESS  read-only
	STATUS      current
	DESCRIPTION
	"Table entry attribute for connsyncCorruptPkt"
	::={connsyncCorruptPktLevelEntry 2}

connsyncCorruptPktLevelMom OBJECT-TYPE
	SYNTAX	 CounterBasedGauge64
	MAX-ACCESS  read-only
	STATUS      current
	DESCRIPTION
	"Table entry attribute for connsyncCorruptPkt"
	::={connsyncCorruptPktLevelEntry 3}

connsyncCorruptPktLevelMax OBJECT-TYPE
	SYNTAX	 CounterBasedGauge64
	MAX-ACCESS  read-only
	STATUS      current
	DESCRIPTION
	"Table entry attribute for connsyncCorruptPkt"
	::={connsyncCorruptPktLevelEntry 4}


connsyncConnNotfound	OBJECT IDENTIFIER ::={connsync 16}

connsyncConnNotfoundVal	OBJECT-TYPE
	SYNTAX	 Counter64
	MAX-ACCESS read-only
	STATUS current
	DESCRIPTION "Connection not found"

	::={connsyncConnNotfound 1}

connsyncConnNotfoundMom	OBJECT-TYPE
	SYNTAX	 CounterBasedGauge64
	MAX-ACCESS read-only
	STATUS current
	DESCRIPTION "Connection not found"

	::={connsyncConnNotfound 2}

connsyncConnNotfoundMax	OBJECT-TYPE
	SYNTAX	 CounterBasedGauge64
	MAX-ACCESS read-only
	STATUS current
	DESCRIPTION "Connection not found"

	::={connsyncConnNotfound 3}

connsyncConnNotfoundLevelTable OBJECT-TYPE
	SYNTAX      SEQUENCE OF ConnsyncConnNotfoundLevelEntry
	MAX-ACCESS  not-accessible
	STATUS      current
	DESCRIPTION
	"Table for connsyncConnNotfound"
	::={connsyncConnNotfound 4}

connsyncConnNotfoundLevelEntry OBJECT-TYPE
	SYNTAX      ConnsyncConnNotfoundLevelEntry
	MAX-ACCESS  not-accessible
	STATUS      current
	DESCRIPTION
	"Table entry for connsyncConnNotfound"
	INDEX { connsyncConnNotfoundLevelName }
	::={connsyncConnNotfoundLevelTable 1}

ConnsyncConnNotfoundLevelEntry ::=
	SEQUENCE {
		connsyncConnNotfoundLevelName	DisplayString,
		connsyncConnNotfoundLevelVal	Counter64,
		connsyncConnNotfoundLevelMom	CounterBasedGauge64,
		connsyncConnNotfoundLevelMax	CounterBasedGauge64
	}

connsyncConnNotfoundLevelName OBJECT-TYPE
	SYNTAX      DisplayString
	MAX-ACCESS  not-accessible
	STATUS      current
	DESCRIPTION
	"Table entry display string for connsyncConnNotfound"
	::={connsyncConnNotfoundLevelEntry 1}

connsyncConnNotfoundLevelVal OBJECT-TYPE
	SYNTAX	 Counter64
	MAX-ACCESS  read-only
	STATUS      current
	DESCRIPTION
	"Table entry attribute for connsyncConnNotfound"
	::={connsyncConnNotfoundLevelEntry 2}

connsyncConnNotfoundLevelMom OBJECT-TYPE
	SYNTAX	 CounterBasedGauge64
	MAX-ACCESS  read-only
	STATUS      current
	DESCRIPTION
	"Table entry attribute for connsyncConnNotfound"
	::={connsyncConnNotfoundLevelEntry 3}

connsyncConnNotfoundLevelMax OBJECT-TYPE
	SYNTAX	 CounterBasedGauge64
	MAX-ACCESS  read-only
	STATUS      current
	DESCRIPTION
	"Table entry attribute for connsyncConnNotfound"
	::={connsyncConnNotfoundLevelEntry 4}


connsyncBadVer	OBJECT IDENTIFIER ::={connsync 17}

connsyncBadVerVal	OBJECT-TYPE
	SYNTAX	 Counter64
	MAX-ACCESS read-only
	STATUS current
	DESCRIPTION "Received packets with incompatible version"

	::={connsyncBadVer 1}

connsyncBadVerMom	OBJECT-TYPE
	SYNTAX	 CounterBasedGauge64
	MAX-ACCESS read-only
	STATUS current
	DESCRIPTION "Received packets with incompatible version"

	::={connsyncBadVer 2}

connsyncBadVerMax	OBJECT-TYPE
	SYNTAX	 CounterBasedGauge64
	MAX-ACCESS read-only
	STATUS current
	DESCRIPTION "Received packets with incompatible version"

	::={connsyncBadVer 3}

connsyncBadVerLevelTable OBJECT-TYPE
	SYNTAX      SEQUENCE OF ConnsyncBadVerLevelEntry
	MAX-ACCESS  not-accessible
	STATUS      current
	DESCRIPTION
	"Table for connsyncBadVer"
	::={connsyncBadVer 4}

connsyncBadVerLevelEntry OBJECT-TYPE
	SYNTAX      ConnsyncBadVerLevelEntry
	MAX-ACCESS  not-accessible
	STATUS      current
	DESCRIPTION
	"Table entry for connsyncBadVer"
	INDEX { connsyncBadVerLevelName }
	::={connsyncBadVerLevelTable 1}

ConnsyncBadVerLevelEntry ::=
	SEQUENCE {
		connsyncBadVerLevelName	DisplayString,
		connsyncBadVerLevelVal	Counter64,
		connsyncBadVerLevelMom	CounterBasedGauge64,
		connsyncBadVerLevelMax	CounterBasedGauge64
	}

connsyncBadVerLevelName OBJECT-TYPE
	SYNTAX      DisplayString
	MAX-ACCESS  not-accessible
	STATUS      current
	DESCRIPTION
	"Table entry display string for connsyncBadVer"
	::={connsyncBadVerLevelEntry 1}

connsyncBadVerLevelVal OBJECT-TYPE
	SYNTAX	 Counter64
	MAX-ACCESS  read-only
	STATUS      current
	DESCRIPTION
	"Table entry attribute for connsyncBadVer"
	::={connsyncBadVerLevelEntry 2}

connsyncBadVerLevelMom OBJECT-TYPE
	SYNTAX	 CounterBasedGauge64
	MAX-ACCESS  read-only
	STATUS      current
	DESCRIPTION
	"Table entry attribute for connsyncBadVer"
	::={connsyncBadVerLevelEntry 3}

connsyncBadVerLevelMax OBJECT-TYPE
	SYNTAX	 CounterBasedGauge64
	MAX-ACCESS  read-only
	STATUS      current
	DESCRIPTION
	"Table entry attribute for connsyncBadVer"
	::={connsyncBadVerLevelEntry 4}


connsyncBadType	OBJECT IDENTIFIER ::={connsync 18}

connsyncBadTypeVal	OBJECT-TYPE
	SYNTAX	 Counter64
	MAX-ACCESS read-only
	STATUS current
	DESCRIPTION "Received packets with incorrect ethernet type"

	::={connsyncBadType 1}

connsyncBadTypeMom	OBJECT-TYPE
	SYNTAX	 CounterBasedGauge64
	MAX-ACCESS read-only
	STATUS current
	DESCRIPTION "Received packets with incorrect ethernet type"

	::={connsyncBadType 2}

connsyncBadTypeMax	OBJECT-TYPE
	SYNTAX	 CounterBasedGauge64
	MAX-ACCESS read-only
	STATUS current
	DESCRIPTION "Received packets with incorrect ethernet type"

	::={connsyncBadType 3}

connsyncBadTypeLevelTable OBJECT-TYPE
	SYNTAX      SEQUENCE OF ConnsyncBadTypeLevelEntry
	MAX-ACCESS  not-accessible
	STATUS      current
	DESCRIPTION
	"Table for connsyncBadType"
	::={connsyncBadType 4}

connsyncBadTypeLevelEntry OBJECT-TYPE
	SYNTAX      ConnsyncBadTypeLevelEntry
	MAX-ACCESS  not-accessible
	STATUS      current
	DESCRIPTION
	"Table entry for connsyncBadType"
	INDEX { connsyncBadTypeLevelName }
	::={connsyncBadTypeLevelTable 1}

ConnsyncBadTypeLevelEntry ::=
	SEQUENCE {
		connsyncBadTypeLevelName	DisplayString,
		connsyncBadTypeLevelVal	Counter64,
		connsyncBadTypeLevelMom	CounterBasedGauge64,
		connsyncBadTypeLevelMax	CounterBasedGauge64
	}

connsyncBadTypeLevelName OBJECT-TYPE
	SYNTAX      DisplayString
	MAX-ACCESS  not-accessible
	STATUS      current
	DESCRIPTION
	"Table entry display string for connsyncBadType"
	::={connsyncBadTypeLevelEntry 1}

connsyncBadTypeLevelVal OBJECT-TYPE
	SYNTAX	 Counter64
	MAX-ACCESS  read-only
	STATUS      current
	DESCRIPTION
	"Table entry attribute for connsyncBadType"
	::={connsyncBadTypeLevelEntry 2}

connsyncBadTypeLevelMom OBJECT-TYPE
	SYNTAX	 CounterBasedGauge64
	MAX-ACCESS  read-only
	STATUS      current
	DESCRIPTION
	"Table entry attribute for connsyncBadType"
	::={connsyncBadTypeLevelEntry 3}

connsyncBadTypeLevelMax OBJECT-TYPE
	SYNTAX	 CounterBasedGauge64
	MAX-ACCESS  read-only
	STATUS      current
	DESCRIPTION
	"Table entry attribute for connsyncBadType"
	::={connsyncBadTypeLevelEntry 4}


connsyncBadEngineid	OBJECT IDENTIFIER ::={connsync 19}

connsyncBadEngineidVal	OBJECT-TYPE
	SYNTAX	 Counter64
	MAX-ACCESS read-only
	STATUS current
	DESCRIPTION "Received packets with own engine-id"

	::={connsyncBadEngineid 1}

connsyncBadEngineidMom	OBJECT-TYPE
	SYNTAX	 CounterBasedGauge64
	MAX-ACCESS read-only
	STATUS current
	DESCRIPTION "Received packets with own engine-id"

	::={connsyncBadEngineid 2}

connsyncBadEngineidMax	OBJECT-TYPE
	SYNTAX	 CounterBasedGauge64
	MAX-ACCESS read-only
	STATUS current
	DESCRIPTION "Received packets with own engine-id"

	::={connsyncBadEngineid 3}

connsyncBadEngineidLevelTable OBJECT-TYPE
	SYNTAX      SEQUENCE OF ConnsyncBadEngineidLevelEntry
	MAX-ACCESS  not-accessible
	STATUS      current
	DESCRIPTION
	"Table for connsyncBadEngineid"
	::={connsyncBadEngineid 4}

connsyncBadEngineidLevelEntry OBJECT-TYPE
	SYNTAX      ConnsyncBadEngineidLevelEntry
	MAX-ACCESS  not-accessible
	STATUS      current
	DESCRIPTION
	"Table entry for connsyncBadEngineid"
	INDEX { connsyncBadEngineidLevelName }
	::={connsyncBadEngineidLevelTable 1}

ConnsyncBadEngineidLevelEntry ::=
	SEQUENCE {
		connsyncBadEngineidLevelName	DisplayString,
		connsyncBadEngineidLevelVal	Counter64,
		connsyncBadEngineidLevelMom	CounterBasedGauge64,
		connsyncBadEngineidLevelMax	CounterBasedGauge64
	}

connsyncBadEngineidLevelName OBJECT-TYPE
	SYNTAX      DisplayString
	MAX-ACCESS  not-accessible
	STATUS      current
	DESCRIPTION
	"Table entry display string for connsyncBadEngineid"
	::={connsyncBadEngineidLevelEntry 1}

connsyncBadEngineidLevelVal OBJECT-TYPE
	SYNTAX	 Counter64
	MAX-ACCESS  read-only
	STATUS      current
	DESCRIPTION
	"Table entry attribute for connsyncBadEngineid"
	::={connsyncBadEngineidLevelEntry 2}

connsyncBadEngineidLevelMom OBJECT-TYPE
	SYNTAX	 CounterBasedGauge64
	MAX-ACCESS  read-only
	STATUS      current
	DESCRIPTION
	"Table entry attribute for connsyncBadEngineid"
	::={connsyncBadEngineidLevelEntry 3}

connsyncBadEngineidLevelMax OBJECT-TYPE
	SYNTAX	 CounterBasedGauge64
	MAX-ACCESS  read-only
	STATUS      current
	DESCRIPTION
	"Table entry attribute for connsyncBadEngineid"
	::={connsyncBadEngineidLevelEntry 4}


connsyncUdpSnt	OBJECT IDENTIFIER ::={connsync 20}

connsyncUdpSntVal	OBJECT-TYPE
	SYNTAX	 Counter64
	MAX-ACCESS read-only
	STATUS current
	DESCRIPTION "UDP sent"

	::={connsyncUdpSnt 1}

connsyncUdpSntMom	OBJECT-TYPE
	SYNTAX	 CounterBasedGauge64
	MAX-ACCESS read-only
	STATUS current
	DESCRIPTION "UDP sent"

	::={connsyncUdpSnt 2}

connsyncUdpSntMax	OBJECT-TYPE
	SYNTAX	 CounterBasedGauge64
	MAX-ACCESS read-only
	STATUS current
	DESCRIPTION "UDP sent"

	::={connsyncUdpSnt 3}

connsyncUdpSntLevelTable OBJECT-TYPE
	SYNTAX      SEQUENCE OF ConnsyncUdpSntLevelEntry
	MAX-ACCESS  not-accessible
	STATUS      current
	DESCRIPTION
	"Table for connsyncUdpSnt"
	::={connsyncUdpSnt 4}

connsyncUdpSntLevelEntry OBJECT-TYPE
	SYNTAX      ConnsyncUdpSntLevelEntry
	MAX-ACCESS  not-accessible
	STATUS      current
	DESCRIPTION
	"Table entry for connsyncUdpSnt"
	INDEX { connsyncUdpSntLevelName }
	::={connsyncUdpSntLevelTable 1}

ConnsyncUdpSntLevelEntry ::=
	SEQUENCE {
		connsyncUdpSntLevelName	DisplayString,
		connsyncUdpSntLevelVal	Counter64,
		connsyncUdpSntLevelMom	CounterBasedGauge64,
		connsyncUdpSntLevelMax	CounterBasedGauge64
	}

connsyncUdpSntLevelName OBJECT-TYPE
	SYNTAX      DisplayString
	MAX-ACCESS  not-accessible
	STATUS      current
	DESCRIPTION
	"Table entry display string for connsyncUdpSnt"
	::={connsyncUdpSntLevelEntry 1}

connsyncUdpSntLevelVal OBJECT-TYPE
	SYNTAX	 Counter64
	MAX-ACCESS  read-only
	STATUS      current
	DESCRIPTION
	"Table entry attribute for connsyncUdpSnt"
	::={connsyncUdpSntLevelEntry 2}

connsyncUdpSntLevelMom OBJECT-TYPE
	SYNTAX	 CounterBasedGauge64
	MAX-ACCESS  read-only
	STATUS      current
	DESCRIPTION
	"Table entry attribute for connsyncUdpSnt"
	::={connsyncUdpSntLevelEntry 3}

connsyncUdpSntLevelMax OBJECT-TYPE
	SYNTAX	 CounterBasedGauge64
	MAX-ACCESS  read-only
	STATUS      current
	DESCRIPTION
	"Table entry attribute for connsyncUdpSnt"
	::={connsyncUdpSntLevelEntry 4}


connsyncUdpRcv	OBJECT IDENTIFIER ::={connsync 21}

connsyncUdpRcvVal	OBJECT-TYPE
	SYNTAX	 Counter64
	MAX-ACCESS read-only
	STATUS current
	DESCRIPTION "UDP received"

	::={connsyncUdpRcv 1}

connsyncUdpRcvMom	OBJECT-TYPE
	SYNTAX	 CounterBasedGauge64
	MAX-ACCESS read-only
	STATUS current
	DESCRIPTION "UDP received"

	::={connsyncUdpRcv 2}

connsyncUdpRcvMax	OBJECT-TYPE
	SYNTAX	 CounterBasedGauge64
	MAX-ACCESS read-only
	STATUS current
	DESCRIPTION "UDP received"

	::={connsyncUdpRcv 3}

connsyncUdpRcvLevelTable OBJECT-TYPE
	SYNTAX      SEQUENCE OF ConnsyncUdpRcvLevelEntry
	MAX-ACCESS  not-accessible
	STATUS      current
	DESCRIPTION
	"Table for connsyncUdpRcv"
	::={connsyncUdpRcv 4}

connsyncUdpRcvLevelEntry OBJECT-TYPE
	SYNTAX      ConnsyncUdpRcvLevelEntry
	MAX-ACCESS  not-accessible
	STATUS      current
	DESCRIPTION
	"Table entry for connsyncUdpRcv"
	INDEX { connsyncUdpRcvLevelName }
	::={connsyncUdpRcvLevelTable 1}

ConnsyncUdpRcvLevelEntry ::=
	SEQUENCE {
		connsyncUdpRcvLevelName	DisplayString,
		connsyncUdpRcvLevelVal	Counter64,
		connsyncUdpRcvLevelMom	CounterBasedGauge64,
		connsyncUdpRcvLevelMax	CounterBasedGauge64
	}

connsyncUdpRcvLevelName OBJECT-TYPE
	SYNTAX      DisplayString
	MAX-ACCESS  not-accessible
	STATUS      current
	DESCRIPTION
	"Table entry display string for connsyncUdpRcv"
	::={connsyncUdpRcvLevelEntry 1}

connsyncUdpRcvLevelVal OBJECT-TYPE
	SYNTAX	 Counter64
	MAX-ACCESS  read-only
	STATUS      current
	DESCRIPTION
	"Table entry attribute for connsyncUdpRcv"
	::={connsyncUdpRcvLevelEntry 2}

connsyncUdpRcvLevelMom OBJECT-TYPE
	SYNTAX	 CounterBasedGauge64
	MAX-ACCESS  read-only
	STATUS      current
	DESCRIPTION
	"Table entry attribute for connsyncUdpRcv"
	::={connsyncUdpRcvLevelEntry 3}

connsyncUdpRcvLevelMax OBJECT-TYPE
	SYNTAX	 CounterBasedGauge64
	MAX-ACCESS  read-only
	STATUS      current
	DESCRIPTION
	"Table entry attribute for connsyncUdpRcv"
	::={connsyncUdpRcvLevelEntry 4}


connsyncUdpRwSnt	OBJECT IDENTIFIER ::={connsync 22}

connsyncUdpRwSntVal	OBJECT-TYPE
	SYNTAX	 Counter64
	MAX-ACCESS read-only
	STATUS current
	DESCRIPTION "UDP rewrite headers sent"

	::={connsyncUdpRwSnt 1}

connsyncUdpRwSntMom	OBJECT-TYPE
	SYNTAX	 CounterBasedGauge64
	MAX-ACCESS read-only
	STATUS current
	DESCRIPTION "UDP rewrite headers sent"

	::={connsyncUdpRwSnt 2}

connsyncUdpRwSntMax	OBJECT-TYPE
	SYNTAX	 CounterBasedGauge64
	MAX-ACCESS read-only
	STATUS current
	DESCRIPTION "UDP rewrite headers sent"

	::={connsyncUdpRwSnt 3}

connsyncUdpRwSntLevelTable OBJECT-TYPE
	SYNTAX      SEQUENCE OF ConnsyncUdpRwSntLevelEntry
	MAX-ACCESS  not-accessible
	STATUS      current
	DESCRIPTION
	"Table for connsyncUdpRwSnt"
	::={connsyncUdpRwSnt 4}

connsyncUdpRwSntLevelEntry OBJECT-TYPE
	SYNTAX      ConnsyncUdpRwSntLevelEntry
	MAX-ACCESS  not-accessible
	STATUS      current
	DESCRIPTION
	"Table entry for connsyncUdpRwSnt"
	INDEX { connsyncUdpRwSntLevelName }
	::={connsyncUdpRwSntLevelTable 1}

ConnsyncUdpRwSntLevelEntry ::=
	SEQUENCE {
		connsyncUdpRwSntLevelName	DisplayString,
		connsyncUdpRwSntLevelVal	Counter64,
		connsyncUdpRwSntLevelMom	CounterBasedGauge64,
		connsyncUdpRwSntLevelMax	CounterBasedGauge64
	}

connsyncUdpRwSntLevelName OBJECT-TYPE
	SYNTAX      DisplayString
	MAX-ACCESS  not-accessible
	STATUS      current
	DESCRIPTION
	"Table entry display string for connsyncUdpRwSnt"
	::={connsyncUdpRwSntLevelEntry 1}

connsyncUdpRwSntLevelVal OBJECT-TYPE
	SYNTAX	 Counter64
	MAX-ACCESS  read-only
	STATUS      current
	DESCRIPTION
	"Table entry attribute for connsyncUdpRwSnt"
	::={connsyncUdpRwSntLevelEntry 2}

connsyncUdpRwSntLevelMom OBJECT-TYPE
	SYNTAX	 CounterBasedGauge64
	MAX-ACCESS  read-only
	STATUS      current
	DESCRIPTION
	"Table entry attribute for connsyncUdpRwSnt"
	::={connsyncUdpRwSntLevelEntry 3}

connsyncUdpRwSntLevelMax OBJECT-TYPE
	SYNTAX	 CounterBasedGauge64
	MAX-ACCESS  read-only
	STATUS      current
	DESCRIPTION
	"Table entry attribute for connsyncUdpRwSnt"
	::={connsyncUdpRwSntLevelEntry 4}


connsyncUdpRwRcv	OBJECT IDENTIFIER ::={connsync 23}

connsyncUdpRwRcvVal	OBJECT-TYPE
	SYNTAX	 Counter64
	MAX-ACCESS read-only
	STATUS current
	DESCRIPTION "UDP rewrite headers received"

	::={connsyncUdpRwRcv 1}

connsyncUdpRwRcvMom	OBJECT-TYPE
	SYNTAX	 CounterBasedGauge64
	MAX-ACCESS read-only
	STATUS current
	DESCRIPTION "UDP rewrite headers received"

	::={connsyncUdpRwRcv 2}

connsyncUdpRwRcvMax	OBJECT-TYPE
	SYNTAX	 CounterBasedGauge64
	MAX-ACCESS read-only
	STATUS current
	DESCRIPTION "UDP rewrite headers received"

	::={connsyncUdpRwRcv 3}

connsyncUdpRwRcvLevelTable OBJECT-TYPE
	SYNTAX      SEQUENCE OF ConnsyncUdpRwRcvLevelEntry
	MAX-ACCESS  not-accessible
	STATUS      current
	DESCRIPTION
	"Table for connsyncUdpRwRcv"
	::={connsyncUdpRwRcv 4}

connsyncUdpRwRcvLevelEntry OBJECT-TYPE
	SYNTAX      ConnsyncUdpRwRcvLevelEntry
	MAX-ACCESS  not-accessible
	STATUS      current
	DESCRIPTION
	"Table entry for connsyncUdpRwRcv"
	INDEX { connsyncUdpRwRcvLevelName }
	::={connsyncUdpRwRcvLevelTable 1}

ConnsyncUdpRwRcvLevelEntry ::=
	SEQUENCE {
		connsyncUdpRwRcvLevelName	DisplayString,
		connsyncUdpRwRcvLevelVal	Counter64,
		connsyncUdpRwRcvLevelMom	CounterBasedGauge64,
		connsyncUdpRwRcvLevelMax	CounterBasedGauge64
	}

connsyncUdpRwRcvLevelName OBJECT-TYPE
	SYNTAX      DisplayString
	MAX-ACCESS  not-accessible
	STATUS      current
	DESCRIPTION
	"Table entry display string for connsyncUdpRwRcv"
	::={connsyncUdpRwRcvLevelEntry 1}

connsyncUdpRwRcvLevelVal OBJECT-TYPE
	SYNTAX	 Counter64
	MAX-ACCESS  read-only
	STATUS      current
	DESCRIPTION
	"Table entry attribute for connsyncUdpRwRcv"
	::={connsyncUdpRwRcvLevelEntry 2}

connsyncUdpRwRcvLevelMom OBJECT-TYPE
	SYNTAX	 CounterBasedGauge64
	MAX-ACCESS  read-only
	STATUS      current
	DESCRIPTION
	"Table entry attribute for connsyncUdpRwRcv"
	::={connsyncUdpRwRcvLevelEntry 3}

connsyncUdpRwRcvLevelMax OBJECT-TYPE
	SYNTAX	 CounterBasedGauge64
	MAX-ACCESS  read-only
	STATUS      current
	DESCRIPTION
	"Table entry attribute for connsyncUdpRwRcv"
	::={connsyncUdpRwRcvLevelEntry 4}


connsyncUdpUnknownRwRcv	OBJECT IDENTIFIER ::={connsync 24}

connsyncUdpUnknownRwRcvVal	OBJECT-TYPE
	SYNTAX	 Counter64
	MAX-ACCESS read-only
	STATUS current
	DESCRIPTION "UDP unknown rewrite headers received"

	::={connsyncUdpUnknownRwRcv 1}

connsyncUdpUnknownRwRcvMom	OBJECT-TYPE
	SYNTAX	 CounterBasedGauge64
	MAX-ACCESS read-only
	STATUS current
	DESCRIPTION "UDP unknown rewrite headers received"

	::={connsyncUdpUnknownRwRcv 2}

connsyncUdpUnknownRwRcvMax	OBJECT-TYPE
	SYNTAX	 CounterBasedGauge64
	MAX-ACCESS read-only
	STATUS current
	DESCRIPTION "UDP unknown rewrite headers received"

	::={connsyncUdpUnknownRwRcv 3}

connsyncUdpUnknownRwRcvLevelTable OBJECT-TYPE
	SYNTAX      SEQUENCE OF ConnsyncUdpUnknownRwRcvLevelEntry
	MAX-ACCESS  not-accessible
	STATUS      current
	DESCRIPTION
	"Table for connsyncUdpUnknownRwRcv"
	::={connsyncUdpUnknownRwRcv 4}

connsyncUdpUnknownRwRcvLevelEntry OBJECT-TYPE
	SYNTAX      ConnsyncUdpUnknownRwRcvLevelEntry
	MAX-ACCESS  not-accessible
	STATUS      current
	DESCRIPTION
	"Table entry for connsyncUdpUnknownRwRcv"
	INDEX { connsyncUdpUnknownRwRcvLevelName }
	::={connsyncUdpUnknownRwRcvLevelTable 1}

ConnsyncUdpUnknownRwRcvLevelEntry ::=
	SEQUENCE {
		connsyncUdpUnknownRwRcvLevelName	DisplayString,
		connsyncUdpUnknownRwRcvLevelVal	Counter64,
		connsyncUdpUnknownRwRcvLevelMom	CounterBasedGauge64,
		connsyncUdpUnknownRwRcvLevelMax	CounterBasedGauge64
	}

connsyncUdpUnknownRwRcvLevelName OBJECT-TYPE
	SYNTAX      DisplayString
	MAX-ACCESS  not-accessible
	STATUS      current
	DESCRIPTION
	"Table entry display string for connsyncUdpUnknownRwRcv"
	::={connsyncUdpUnknownRwRcvLevelEntry 1}

connsyncUdpUnknownRwRcvLevelVal OBJECT-TYPE
	SYNTAX	 Counter64
	MAX-ACCESS  read-only
	STATUS      current
	DESCRIPTION
	"Table entry attribute for connsyncUdpUnknownRwRcv"
	::={connsyncUdpUnknownRwRcvLevelEntry 2}

connsyncUdpUnknownRwRcvLevelMom OBJECT-TYPE
	SYNTAX	 CounterBasedGauge64
	MAX-ACCESS  read-only
	STATUS      current
	DESCRIPTION
	"Table entry attribute for connsyncUdpUnknownRwRcv"
	::={connsyncUdpUnknownRwRcvLevelEntry 3}

connsyncUdpUnknownRwRcvLevelMax OBJECT-TYPE
	SYNTAX	 CounterBasedGauge64
	MAX-ACCESS  read-only
	STATUS      current
	DESCRIPTION
	"Table entry attribute for connsyncUdpUnknownRwRcv"
	::={connsyncUdpUnknownRwRcvLevelEntry 4}


connsyncRwSnt	OBJECT IDENTIFIER ::={connsync 25}

connsyncRwSntVal	OBJECT-TYPE
	SYNTAX	 Counter64
	MAX-ACCESS read-only
	STATUS current
	DESCRIPTION "Rewrite headers sent"

	::={connsyncRwSnt 1}

connsyncRwSntMom	OBJECT-TYPE
	SYNTAX	 CounterBasedGauge64
	MAX-ACCESS read-only
	STATUS current
	DESCRIPTION "Rewrite headers sent"

	::={connsyncRwSnt 2}

connsyncRwSntMax	OBJECT-TYPE
	SYNTAX	 CounterBasedGauge64
	MAX-ACCESS read-only
	STATUS current
	DESCRIPTION "Rewrite headers sent"

	::={connsyncRwSnt 3}

connsyncRwSntLevelTable OBJECT-TYPE
	SYNTAX      SEQUENCE OF ConnsyncRwSntLevelEntry
	MAX-ACCESS  not-accessible
	STATUS      current
	DESCRIPTION
	"Table for connsyncRwSnt"
	::={connsyncRwSnt 4}

connsyncRwSntLevelEntry OBJECT-TYPE
	SYNTAX      ConnsyncRwSntLevelEntry
	MAX-ACCESS  not-accessible
	STATUS      current
	DESCRIPTION
	"Table entry for connsyncRwSnt"
	INDEX { connsyncRwSntLevelName }
	::={connsyncRwSntLevelTable 1}

ConnsyncRwSntLevelEntry ::=
	SEQUENCE {
		connsyncRwSntLevelName	DisplayString,
		connsyncRwSntLevelVal	Counter64,
		connsyncRwSntLevelMom	CounterBasedGauge64,
		connsyncRwSntLevelMax	CounterBasedGauge64
	}

connsyncRwSntLevelName OBJECT-TYPE
	SYNTAX      DisplayString
	MAX-ACCESS  not-accessible
	STATUS      current
	DESCRIPTION
	"Table entry display string for connsyncRwSnt"
	::={connsyncRwSntLevelEntry 1}

connsyncRwSntLevelVal OBJECT-TYPE
	SYNTAX	 Counter64
	MAX-ACCESS  read-only
	STATUS      current
	DESCRIPTION
	"Table entry attribute for connsyncRwSnt"
	::={connsyncRwSntLevelEntry 2}

connsyncRwSntLevelMom OBJECT-TYPE
	SYNTAX	 CounterBasedGauge64
	MAX-ACCESS  read-only
	STATUS      current
	DESCRIPTION
	"Table entry attribute for connsyncRwSnt"
	::={connsyncRwSntLevelEntry 3}

connsyncRwSntLevelMax OBJECT-TYPE
	SYNTAX	 CounterBasedGauge64
	MAX-ACCESS  read-only
	STATUS      current
	DESCRIPTION
	"Table entry attribute for connsyncRwSnt"
	::={connsyncRwSntLevelEntry 4}


connsyncRwRcv	OBJECT IDENTIFIER ::={connsync 26}

connsyncRwRcvVal	OBJECT-TYPE
	SYNTAX	 Counter64
	MAX-ACCESS read-only
	STATUS current
	DESCRIPTION "Rewrite headers received"

	::={connsyncRwRcv 1}

connsyncRwRcvMom	OBJECT-TYPE
	SYNTAX	 CounterBasedGauge64
	MAX-ACCESS read-only
	STATUS current
	DESCRIPTION "Rewrite headers received"

	::={connsyncRwRcv 2}

connsyncRwRcvMax	OBJECT-TYPE
	SYNTAX	 CounterBasedGauge64
	MAX-ACCESS read-only
	STATUS current
	DESCRIPTION "Rewrite headers received"

	::={connsyncRwRcv 3}

connsyncRwRcvLevelTable OBJECT-TYPE
	SYNTAX      SEQUENCE OF ConnsyncRwRcvLevelEntry
	MAX-ACCESS  not-accessible
	STATUS      current
	DESCRIPTION
	"Table for connsyncRwRcv"
	::={connsyncRwRcv 4}

connsyncRwRcvLevelEntry OBJECT-TYPE
	SYNTAX      ConnsyncRwRcvLevelEntry
	MAX-ACCESS  not-accessible
	STATUS      current
	DESCRIPTION
	"Table entry for connsyncRwRcv"
	INDEX { connsyncRwRcvLevelName }
	::={connsyncRwRcvLevelTable 1}

ConnsyncRwRcvLevelEntry ::=
	SEQUENCE {
		connsyncRwRcvLevelName	DisplayString,
		connsyncRwRcvLevelVal	Counter64,
		connsyncRwRcvLevelMom	CounterBasedGauge64,
		connsyncRwRcvLevelMax	CounterBasedGauge64
	}

connsyncRwRcvLevelName OBJECT-TYPE
	SYNTAX      DisplayString
	MAX-ACCESS  not-accessible
	STATUS      current
	DESCRIPTION
	"Table entry display string for connsyncRwRcv"
	::={connsyncRwRcvLevelEntry 1}

connsyncRwRcvLevelVal OBJECT-TYPE
	SYNTAX	 Counter64
	MAX-ACCESS  read-only
	STATUS      current
	DESCRIPTION
	"Table entry attribute for connsyncRwRcv"
	::={connsyncRwRcvLevelEntry 2}

connsyncRwRcvLevelMom OBJECT-TYPE
	SYNTAX	 CounterBasedGauge64
	MAX-ACCESS  read-only
	STATUS      current
	DESCRIPTION
	"Table entry attribute for connsyncRwRcv"
	::={connsyncRwRcvLevelEntry 3}

connsyncRwRcvLevelMax OBJECT-TYPE
	SYNTAX	 CounterBasedGauge64
	MAX-ACCESS  read-only
	STATUS      current
	DESCRIPTION
	"Table entry attribute for connsyncRwRcv"
	::={connsyncRwRcvLevelEntry 4}


connsyncUnknownRwRcv	OBJECT IDENTIFIER ::={connsync 27}

connsyncUnknownRwRcvVal	OBJECT-TYPE
	SYNTAX	 Counter64
	MAX-ACCESS read-only
	STATUS current
	DESCRIPTION "Unknown rewrite headers received"

	::={connsyncUnknownRwRcv 1}

connsyncUnknownRwRcvMom	OBJECT-TYPE
	SYNTAX	 CounterBasedGauge64
	MAX-ACCESS read-only
	STATUS current
	DESCRIPTION "Unknown rewrite headers received"

	::={connsyncUnknownRwRcv 2}

connsyncUnknownRwRcvMax	OBJECT-TYPE
	SYNTAX	 CounterBasedGauge64
	MAX-ACCESS read-only
	STATUS current
	DESCRIPTION "Unknown rewrite headers received"

	::={connsyncUnknownRwRcv 3}

connsyncUnknownRwRcvLevelTable OBJECT-TYPE
	SYNTAX      SEQUENCE OF ConnsyncUnknownRwRcvLevelEntry
	MAX-ACCESS  not-accessible
	STATUS      current
	DESCRIPTION
	"Table for connsyncUnknownRwRcv"
	::={connsyncUnknownRwRcv 4}

connsyncUnknownRwRcvLevelEntry OBJECT-TYPE
	SYNTAX      ConnsyncUnknownRwRcvLevelEntry
	MAX-ACCESS  not-accessible
	STATUS      current
	DESCRIPTION
	"Table entry for connsyncUnknownRwRcv"
	INDEX { connsyncUnknownRwRcvLevelName }
	::={connsyncUnknownRwRcvLevelTable 1}

ConnsyncUnknownRwRcvLevelEntry ::=
	SEQUENCE {
		connsyncUnknownRwRcvLevelName	DisplayString,
		connsyncUnknownRwRcvLevelVal	Counter64,
		connsyncUnknownRwRcvLevelMom	CounterBasedGauge64,
		connsyncUnknownRwRcvLevelMax	CounterBasedGauge64
	}

connsyncUnknownRwRcvLevelName OBJECT-TYPE
	SYNTAX      DisplayString
	MAX-ACCESS  not-accessible
	STATUS      current
	DESCRIPTION
	"Table entry display string for connsyncUnknownRwRcv"
	::={connsyncUnknownRwRcvLevelEntry 1}

connsyncUnknownRwRcvLevelVal OBJECT-TYPE
	SYNTAX	 Counter64
	MAX-ACCESS  read-only
	STATUS      current
	DESCRIPTION
	"Table entry attribute for connsyncUnknownRwRcv"
	::={connsyncUnknownRwRcvLevelEntry 2}

connsyncUnknownRwRcvLevelMom OBJECT-TYPE
	SYNTAX	 CounterBasedGauge64
	MAX-ACCESS  read-only
	STATUS      current
	DESCRIPTION
	"Table entry attribute for connsyncUnknownRwRcv"
	::={connsyncUnknownRwRcvLevelEntry 3}

connsyncUnknownRwRcvLevelMax OBJECT-TYPE
	SYNTAX	 CounterBasedGauge64
	MAX-ACCESS  read-only
	STATUS      current
	DESCRIPTION
	"Table entry attribute for connsyncUnknownRwRcv"
	::={connsyncUnknownRwRcvLevelEntry 4}


connsyncAsymmBuf	OBJECT IDENTIFIER ::={connsync 28}

connsyncAsymmBufVal	OBJECT-TYPE
	SYNTAX	 CounterBasedGauge64
	MAX-ACCESS read-only
	STATUS current
	DESCRIPTION "Buffered asymmetric packets"

	::={connsyncAsymmBuf 1}

connsyncAsymmBufMax	OBJECT-TYPE
	SYNTAX	 CounterBasedGauge64
	MAX-ACCESS read-only
	STATUS current
	DESCRIPTION "Buffered asymmetric packets"

	::={connsyncAsymmBuf 3}

connsyncAsymmBufLevelTable OBJECT-TYPE
	SYNTAX      SEQUENCE OF ConnsyncAsymmBufLevelEntry
	MAX-ACCESS  not-accessible
	STATUS      current
	DESCRIPTION
	"Table for connsyncAsymmBuf"
	::={connsyncAsymmBuf 4}

connsyncAsymmBufLevelEntry OBJECT-TYPE
	SYNTAX      ConnsyncAsymmBufLevelEntry
	MAX-ACCESS  not-accessible
	STATUS      current
	DESCRIPTION
	"Table entry for connsyncAsymmBuf"
	INDEX { connsyncAsymmBufLevelName }
	::={connsyncAsymmBufLevelTable 1}

ConnsyncAsymmBufLevelEntry ::=
	SEQUENCE {
		connsyncAsymmBufLevelName	DisplayString,
		connsyncAsymmBufLevelVal	CounterBasedGauge64,
		connsyncAsymmBufLevelMax	CounterBasedGauge64
	}

connsyncAsymmBufLevelName OBJECT-TYPE
	SYNTAX      DisplayString
	MAX-ACCESS  not-accessible
	STATUS      current
	DESCRIPTION
	"Table entry display string for connsyncAsymmBuf"
	::={connsyncAsymmBufLevelEntry 1}

connsyncAsymmBufLevelVal OBJECT-TYPE
	SYNTAX	 CounterBasedGauge64
	MAX-ACCESS  read-only
	STATUS      current
	DESCRIPTION
	"Table entry attribute for connsyncAsymmBuf"
	::={connsyncAsymmBufLevelEntry 2}

connsyncAsymmBufLevelMax OBJECT-TYPE
	SYNTAX	 CounterBasedGauge64
	MAX-ACCESS  read-only
	STATUS      current
	DESCRIPTION
	"Table entry attribute for connsyncAsymmBuf"
	::={connsyncAsymmBufLevelEntry 4}


connsyncIcmpRwSnt	OBJECT IDENTIFIER ::={connsync 29}

connsyncIcmpRwSntVal	OBJECT-TYPE
	SYNTAX	 Counter64
	MAX-ACCESS read-only
	STATUS current
	DESCRIPTION "ICMP rewrite headers sent"

	::={connsyncIcmpRwSnt 1}

connsyncIcmpRwSntMom	OBJECT-TYPE
	SYNTAX	 CounterBasedGauge64
	MAX-ACCESS read-only
	STATUS current
	DESCRIPTION "ICMP rewrite headers sent"

	::={connsyncIcmpRwSnt 2}

connsyncIcmpRwSntMax	OBJECT-TYPE
	SYNTAX	 CounterBasedGauge64
	MAX-ACCESS read-only
	STATUS current
	DESCRIPTION "ICMP rewrite headers sent"

	::={connsyncIcmpRwSnt 3}

connsyncIcmpRwSntLevelTable OBJECT-TYPE
	SYNTAX      SEQUENCE OF ConnsyncIcmpRwSntLevelEntry
	MAX-ACCESS  not-accessible
	STATUS      current
	DESCRIPTION
	"Table for connsyncIcmpRwSnt"
	::={connsyncIcmpRwSnt 4}

connsyncIcmpRwSntLevelEntry OBJECT-TYPE
	SYNTAX      ConnsyncIcmpRwSntLevelEntry
	MAX-ACCESS  not-accessible
	STATUS      current
	DESCRIPTION
	"Table entry for connsyncIcmpRwSnt"
	INDEX { connsyncIcmpRwSntLevelName }
	::={connsyncIcmpRwSntLevelTable 1}

ConnsyncIcmpRwSntLevelEntry ::=
	SEQUENCE {
		connsyncIcmpRwSntLevelName	DisplayString,
		connsyncIcmpRwSntLevelVal	Counter64,
		connsyncIcmpRwSntLevelMom	CounterBasedGauge64,
		connsyncIcmpRwSntLevelMax	CounterBasedGauge64
	}

connsyncIcmpRwSntLevelName OBJECT-TYPE
	SYNTAX      DisplayString
	MAX-ACCESS  not-accessible
	STATUS      current
	DESCRIPTION
	"Table entry display string for connsyncIcmpRwSnt"
	::={connsyncIcmpRwSntLevelEntry 1}

connsyncIcmpRwSntLevelVal OBJECT-TYPE
	SYNTAX	 Counter64
	MAX-ACCESS  read-only
	STATUS      current
	DESCRIPTION
	"Table entry attribute for connsyncIcmpRwSnt"
	::={connsyncIcmpRwSntLevelEntry 2}

connsyncIcmpRwSntLevelMom OBJECT-TYPE
	SYNTAX	 CounterBasedGauge64
	MAX-ACCESS  read-only
	STATUS      current
	DESCRIPTION
	"Table entry attribute for connsyncIcmpRwSnt"
	::={connsyncIcmpRwSntLevelEntry 3}

connsyncIcmpRwSntLevelMax OBJECT-TYPE
	SYNTAX	 CounterBasedGauge64
	MAX-ACCESS  read-only
	STATUS      current
	DESCRIPTION
	"Table entry attribute for connsyncIcmpRwSnt"
	::={connsyncIcmpRwSntLevelEntry 4}


connsyncIcmpRwRcv	OBJECT IDENTIFIER ::={connsync 30}

connsyncIcmpRwRcvVal	OBJECT-TYPE
	SYNTAX	 Counter64
	MAX-ACCESS read-only
	STATUS current
	DESCRIPTION "ICMP rewrite headers received"

	::={connsyncIcmpRwRcv 1}

connsyncIcmpRwRcvMom	OBJECT-TYPE
	SYNTAX	 CounterBasedGauge64
	MAX-ACCESS read-only
	STATUS current
	DESCRIPTION "ICMP rewrite headers received"

	::={connsyncIcmpRwRcv 2}

connsyncIcmpRwRcvMax	OBJECT-TYPE
	SYNTAX	 CounterBasedGauge64
	MAX-ACCESS read-only
	STATUS current
	DESCRIPTION "ICMP rewrite headers received"

	::={connsyncIcmpRwRcv 3}

connsyncIcmpRwRcvLevelTable OBJECT-TYPE
	SYNTAX      SEQUENCE OF ConnsyncIcmpRwRcvLevelEntry
	MAX-ACCESS  not-accessible
	STATUS      current
	DESCRIPTION
	"Table for connsyncIcmpRwRcv"
	::={connsyncIcmpRwRcv 4}

connsyncIcmpRwRcvLevelEntry OBJECT-TYPE
	SYNTAX      ConnsyncIcmpRwRcvLevelEntry
	MAX-ACCESS  not-accessible
	STATUS      current
	DESCRIPTION
	"Table entry for connsyncIcmpRwRcv"
	INDEX { connsyncIcmpRwRcvLevelName }
	::={connsyncIcmpRwRcvLevelTable 1}

ConnsyncIcmpRwRcvLevelEntry ::=
	SEQUENCE {
		connsyncIcmpRwRcvLevelName	DisplayString,
		connsyncIcmpRwRcvLevelVal	Counter64,
		connsyncIcmpRwRcvLevelMom	CounterBasedGauge64,
		connsyncIcmpRwRcvLevelMax	CounterBasedGauge64
	}

connsyncIcmpRwRcvLevelName OBJECT-TYPE
	SYNTAX      DisplayString
	MAX-ACCESS  not-accessible
	STATUS      current
	DESCRIPTION
	"Table entry display string for connsyncIcmpRwRcv"
	::={connsyncIcmpRwRcvLevelEntry 1}

connsyncIcmpRwRcvLevelVal OBJECT-TYPE
	SYNTAX	 Counter64
	MAX-ACCESS  read-only
	STATUS      current
	DESCRIPTION
	"Table entry attribute for connsyncIcmpRwRcv"
	::={connsyncIcmpRwRcvLevelEntry 2}

connsyncIcmpRwRcvLevelMom OBJECT-TYPE
	SYNTAX	 CounterBasedGauge64
	MAX-ACCESS  read-only
	STATUS      current
	DESCRIPTION
	"Table entry attribute for connsyncIcmpRwRcv"
	::={connsyncIcmpRwRcvLevelEntry 3}

connsyncIcmpRwRcvLevelMax OBJECT-TYPE
	SYNTAX	 CounterBasedGauge64
	MAX-ACCESS  read-only
	STATUS      current
	DESCRIPTION
	"Table entry attribute for connsyncIcmpRwRcv"
	::={connsyncIcmpRwRcvLevelEntry 4}


connsyncIcmpUnknownRwRcv	OBJECT IDENTIFIER ::={connsync 31}

connsyncIcmpUnknownRwRcvVal	OBJECT-TYPE
	SYNTAX	 Counter64
	MAX-ACCESS read-only
	STATUS current
	DESCRIPTION "ICMP unknown rewrite headers received"

	::={connsyncIcmpUnknownRwRcv 1}

connsyncIcmpUnknownRwRcvMom	OBJECT-TYPE
	SYNTAX	 CounterBasedGauge64
	MAX-ACCESS read-only
	STATUS current
	DESCRIPTION "ICMP unknown rewrite headers received"

	::={connsyncIcmpUnknownRwRcv 2}

connsyncIcmpUnknownRwRcvMax	OBJECT-TYPE
	SYNTAX	 CounterBasedGauge64
	MAX-ACCESS read-only
	STATUS current
	DESCRIPTION "ICMP unknown rewrite headers received"

	::={connsyncIcmpUnknownRwRcv 3}

connsyncIcmpUnknownRwRcvLevelTable OBJECT-TYPE
	SYNTAX      SEQUENCE OF ConnsyncIcmpUnknownRwRcvLevelEntry
	MAX-ACCESS  not-accessible
	STATUS      current
	DESCRIPTION
	"Table for connsyncIcmpUnknownRwRcv"
	::={connsyncIcmpUnknownRwRcv 4}

connsyncIcmpUnknownRwRcvLevelEntry OBJECT-TYPE
	SYNTAX      ConnsyncIcmpUnknownRwRcvLevelEntry
	MAX-ACCESS  not-accessible
	STATUS      current
	DESCRIPTION
	"Table entry for connsyncIcmpUnknownRwRcv"
	INDEX { connsyncIcmpUnknownRwRcvLevelName }
	::={connsyncIcmpUnknownRwRcvLevelTable 1}

ConnsyncIcmpUnknownRwRcvLevelEntry ::=
	SEQUENCE {
		connsyncIcmpUnknownRwRcvLevelName	DisplayString,
		connsyncIcmpUnknownRwRcvLevelVal	Counter64,
		connsyncIcmpUnknownRwRcvLevelMom	CounterBasedGauge64,
		connsyncIcmpUnknownRwRcvLevelMax	CounterBasedGauge64
	}

connsyncIcmpUnknownRwRcvLevelName OBJECT-TYPE
	SYNTAX      DisplayString
	MAX-ACCESS  not-accessible
	STATUS      current
	DESCRIPTION
	"Table entry display string for connsyncIcmpUnknownRwRcv"
	::={connsyncIcmpUnknownRwRcvLevelEntry 1}

connsyncIcmpUnknownRwRcvLevelVal OBJECT-TYPE
	SYNTAX	 Counter64
	MAX-ACCESS  read-only
	STATUS      current
	DESCRIPTION
	"Table entry attribute for connsyncIcmpUnknownRwRcv"
	::={connsyncIcmpUnknownRwRcvLevelEntry 2}

connsyncIcmpUnknownRwRcvLevelMom OBJECT-TYPE
	SYNTAX	 CounterBasedGauge64
	MAX-ACCESS  read-only
	STATUS      current
	DESCRIPTION
	"Table entry attribute for connsyncIcmpUnknownRwRcv"
	::={connsyncIcmpUnknownRwRcvLevelEntry 3}

connsyncIcmpUnknownRwRcvLevelMax OBJECT-TYPE
	SYNTAX	 CounterBasedGauge64
	MAX-ACCESS  read-only
	STATUS      current
	DESCRIPTION
	"Table entry attribute for connsyncIcmpUnknownRwRcv"
	::={connsyncIcmpUnknownRwRcvLevelEntry 4}


connsyncPeers	OBJECT IDENTIFIER ::={connsync 32}

connsyncPeersVal	OBJECT-TYPE
	SYNTAX	 CounterBasedGauge64
	MAX-ACCESS read-only
	STATUS current
	DESCRIPTION "Number of connsynced peers"

	::={connsyncPeers 1}

connsyncPeersMax	OBJECT-TYPE
	SYNTAX	 CounterBasedGauge64
	MAX-ACCESS read-only
	STATUS current
	DESCRIPTION "Number of connsynced peers"

	::={connsyncPeers 3}

connsyncPeersLevelTable OBJECT-TYPE
	SYNTAX      SEQUENCE OF ConnsyncPeersLevelEntry
	MAX-ACCESS  not-accessible
	STATUS      current
	DESCRIPTION
	"Table for connsyncPeers"
	::={connsyncPeers 4}

connsyncPeersLevelEntry OBJECT-TYPE
	SYNTAX      ConnsyncPeersLevelEntry
	MAX-ACCESS  not-accessible
	STATUS      current
	DESCRIPTION
	"Table entry for connsyncPeers"
	INDEX { connsyncPeersLevelName }
	::={connsyncPeersLevelTable 1}

ConnsyncPeersLevelEntry ::=
	SEQUENCE {
		connsyncPeersLevelName	DisplayString,
		connsyncPeersLevelVal	CounterBasedGauge64,
		connsyncPeersLevelMax	CounterBasedGauge64
	}

connsyncPeersLevelName OBJECT-TYPE
	SYNTAX      DisplayString
	MAX-ACCESS  not-accessible
	STATUS      current
	DESCRIPTION
	"Table entry display string for connsyncPeers"
	::={connsyncPeersLevelEntry 1}

connsyncPeersLevelVal OBJECT-TYPE
	SYNTAX	 CounterBasedGauge64
	MAX-ACCESS  read-only
	STATUS      current
	DESCRIPTION
	"Table entry attribute for connsyncPeers"
	::={connsyncPeersLevelEntry 2}

connsyncPeersLevelMax OBJECT-TYPE
	SYNTAX	 CounterBasedGauge64
	MAX-ACCESS  read-only
	STATUS      current
	DESCRIPTION
	"Table entry attribute for connsyncPeers"
	::={connsyncPeersLevelEntry 4}


connsyncTunnelNotFound	OBJECT IDENTIFIER ::={connsync 46}

connsyncTunnelNotFoundVal	OBJECT-TYPE
	SYNTAX	 Counter64
	MAX-ACCESS read-only
	STATUS current
	DESCRIPTION "Tunnel referenced in seen not found"

	::={connsyncTunnelNotFound 1}

connsyncTunnelNotFoundMom	OBJECT-TYPE
	SYNTAX	 CounterBasedGauge64
	MAX-ACCESS read-only
	STATUS current
	DESCRIPTION "Tunnel referenced in seen not found"

	::={connsyncTunnelNotFound 2}

connsyncTunnelNotFoundMax	OBJECT-TYPE
	SYNTAX	 CounterBasedGauge64
	MAX-ACCESS read-only
	STATUS current
	DESCRIPTION "Tunnel referenced in seen not found"

	::={connsyncTunnelNotFound 3}

connsyncTunnelNotFoundLevelTable OBJECT-TYPE
	SYNTAX      SEQUENCE OF ConnsyncTunnelNotFoundLevelEntry
	MAX-ACCESS  not-accessible
	STATUS      current
	DESCRIPTION
	"Table for connsyncTunnelNotFound"
	::={connsyncTunnelNotFound 4}

connsyncTunnelNotFoundLevelEntry OBJECT-TYPE
	SYNTAX      ConnsyncTunnelNotFoundLevelEntry
	MAX-ACCESS  not-accessible
	STATUS      current
	DESCRIPTION
	"Table entry for connsyncTunnelNotFound"
	INDEX { connsyncTunnelNotFoundLevelName }
	::={connsyncTunnelNotFoundLevelTable 1}

ConnsyncTunnelNotFoundLevelEntry ::=
	SEQUENCE {
		connsyncTunnelNotFoundLevelName	DisplayString,
		connsyncTunnelNotFoundLevelVal	Counter64,
		connsyncTunnelNotFoundLevelMom	CounterBasedGauge64,
		connsyncTunnelNotFoundLevelMax	CounterBasedGauge64
	}

connsyncTunnelNotFoundLevelName OBJECT-TYPE
	SYNTAX      DisplayString
	MAX-ACCESS  not-accessible
	STATUS      current
	DESCRIPTION
	"Table entry display string for connsyncTunnelNotFound"
	::={connsyncTunnelNotFoundLevelEntry 1}

connsyncTunnelNotFoundLevelVal OBJECT-TYPE
	SYNTAX	 Counter64
	MAX-ACCESS  read-only
	STATUS      current
	DESCRIPTION
	"Table entry attribute for connsyncTunnelNotFound"
	::={connsyncTunnelNotFoundLevelEntry 2}

connsyncTunnelNotFoundLevelMom OBJECT-TYPE
	SYNTAX	 CounterBasedGauge64
	MAX-ACCESS  read-only
	STATUS      current
	DESCRIPTION
	"Table entry attribute for connsyncTunnelNotFound"
	::={connsyncTunnelNotFoundLevelEntry 3}

connsyncTunnelNotFoundLevelMax OBJECT-TYPE
	SYNTAX	 CounterBasedGauge64
	MAX-ACCESS  read-only
	STATUS      current
	DESCRIPTION
	"Table entry attribute for connsyncTunnelNotFound"
	::={connsyncTunnelNotFoundLevelEntry 4}


connsyncHeaderEnrichmentUpdateRcv	OBJECT IDENTIFIER ::={connsync 47}

connsyncHeaderEnrichmentUpdateRcvVal	OBJECT-TYPE
	SYNTAX	 Counter64
	MAX-ACCESS read-only
	STATUS current
	DESCRIPTION "Header enrichment updates received"

	::={connsyncHeaderEnrichmentUpdateRcv 1}

connsyncHeaderEnrichmentUpdateRcvMom	OBJECT-TYPE
	SYNTAX	 CounterBasedGauge64
	MAX-ACCESS read-only
	STATUS current
	DESCRIPTION "Header enrichment updates received"

	::={connsyncHeaderEnrichmentUpdateRcv 2}

connsyncHeaderEnrichmentUpdateRcvMax	OBJECT-TYPE
	SYNTAX	 CounterBasedGauge64
	MAX-ACCESS read-only
	STATUS current
	DESCRIPTION "Header enrichment updates received"

	::={connsyncHeaderEnrichmentUpdateRcv 3}

connsyncHeaderEnrichmentUpdateRcvLevelTable OBJECT-TYPE
	SYNTAX      SEQUENCE OF ConnsyncHeaderEnrichmentUpdateRcvLevelEntry
	MAX-ACCESS  not-accessible
	STATUS      current
	DESCRIPTION
	"Table for connsyncHeaderEnrichmentUpdateRcv"
	::={connsyncHeaderEnrichmentUpdateRcv 4}

connsyncHeaderEnrichmentUpdateRcvLevelEntry OBJECT-TYPE
	SYNTAX      ConnsyncHeaderEnrichmentUpdateRcvLevelEntry
	MAX-ACCESS  not-accessible
	STATUS      current
	DESCRIPTION
	"Table entry for connsyncHeaderEnrichmentUpdateRcv"
	INDEX { connsyncHeaderEnrichmentUpdateRcvLevelName }
	::={connsyncHeaderEnrichmentUpdateRcvLevelTable 1}

ConnsyncHeaderEnrichmentUpdateRcvLevelEntry ::=
	SEQUENCE {
		connsyncHeaderEnrichmentUpdateRcvLevelName	DisplayString,
		connsyncHeaderEnrichmentUpdateRcvLevelVal	Counter64,
		connsyncHeaderEnrichmentUpdateRcvLevelMom	CounterBasedGauge64,
		connsyncHeaderEnrichmentUpdateRcvLevelMax	CounterBasedGauge64
	}

connsyncHeaderEnrichmentUpdateRcvLevelName OBJECT-TYPE
	SYNTAX      DisplayString
	MAX-ACCESS  not-accessible
	STATUS      current
	DESCRIPTION
	"Table entry display string for connsyncHeaderEnrichmentUpdateRcv"
	::={connsyncHeaderEnrichmentUpdateRcvLevelEntry 1}

connsyncHeaderEnrichmentUpdateRcvLevelVal OBJECT-TYPE
	SYNTAX	 Counter64
	MAX-ACCESS  read-only
	STATUS      current
	DESCRIPTION
	"Table entry attribute for connsyncHeaderEnrichmentUpdateRcv"
	::={connsyncHeaderEnrichmentUpdateRcvLevelEntry 2}

connsyncHeaderEnrichmentUpdateRcvLevelMom OBJECT-TYPE
	SYNTAX	 CounterBasedGauge64
	MAX-ACCESS  read-only
	STATUS      current
	DESCRIPTION
	"Table entry attribute for connsyncHeaderEnrichmentUpdateRcv"
	::={connsyncHeaderEnrichmentUpdateRcvLevelEntry 3}

connsyncHeaderEnrichmentUpdateRcvLevelMax OBJECT-TYPE
	SYNTAX	 CounterBasedGauge64
	MAX-ACCESS  read-only
	STATUS      current
	DESCRIPTION
	"Table entry attribute for connsyncHeaderEnrichmentUpdateRcv"
	::={connsyncHeaderEnrichmentUpdateRcvLevelEntry 4}


connsyncHeaderEnrichmentUpdateSnt	OBJECT IDENTIFIER ::={connsync 48}

connsyncHeaderEnrichmentUpdateSntVal	OBJECT-TYPE
	SYNTAX	 Counter64
	MAX-ACCESS read-only
	STATUS current
	DESCRIPTION "Header enrichment updates sent"

	::={connsyncHeaderEnrichmentUpdateSnt 1}

connsyncHeaderEnrichmentUpdateSntMom	OBJECT-TYPE
	SYNTAX	 CounterBasedGauge64
	MAX-ACCESS read-only
	STATUS current
	DESCRIPTION "Header enrichment updates sent"

	::={connsyncHeaderEnrichmentUpdateSnt 2}

connsyncHeaderEnrichmentUpdateSntMax	OBJECT-TYPE
	SYNTAX	 CounterBasedGauge64
	MAX-ACCESS read-only
	STATUS current
	DESCRIPTION "Header enrichment updates sent"

	::={connsyncHeaderEnrichmentUpdateSnt 3}

connsyncHeaderEnrichmentUpdateSntLevelTable OBJECT-TYPE
	SYNTAX      SEQUENCE OF ConnsyncHeaderEnrichmentUpdateSntLevelEntry
	MAX-ACCESS  not-accessible
	STATUS      current
	DESCRIPTION
	"Table for connsyncHeaderEnrichmentUpdateSnt"
	::={connsyncHeaderEnrichmentUpdateSnt 4}

connsyncHeaderEnrichmentUpdateSntLevelEntry OBJECT-TYPE
	SYNTAX      ConnsyncHeaderEnrichmentUpdateSntLevelEntry
	MAX-ACCESS  not-accessible
	STATUS      current
	DESCRIPTION
	"Table entry for connsyncHeaderEnrichmentUpdateSnt"
	INDEX { connsyncHeaderEnrichmentUpdateSntLevelName }
	::={connsyncHeaderEnrichmentUpdateSntLevelTable 1}

ConnsyncHeaderEnrichmentUpdateSntLevelEntry ::=
	SEQUENCE {
		connsyncHeaderEnrichmentUpdateSntLevelName	DisplayString,
		connsyncHeaderEnrichmentUpdateSntLevelVal	Counter64,
		connsyncHeaderEnrichmentUpdateSntLevelMom	CounterBasedGauge64,
		connsyncHeaderEnrichmentUpdateSntLevelMax	CounterBasedGauge64
	}

connsyncHeaderEnrichmentUpdateSntLevelName OBJECT-TYPE
	SYNTAX      DisplayString
	MAX-ACCESS  not-accessible
	STATUS      current
	DESCRIPTION
	"Table entry display string for connsyncHeaderEnrichmentUpdateSnt"
	::={connsyncHeaderEnrichmentUpdateSntLevelEntry 1}

connsyncHeaderEnrichmentUpdateSntLevelVal OBJECT-TYPE
	SYNTAX	 Counter64
	MAX-ACCESS  read-only
	STATUS      current
	DESCRIPTION
	"Table entry attribute for connsyncHeaderEnrichmentUpdateSnt"
	::={connsyncHeaderEnrichmentUpdateSntLevelEntry 2}

connsyncHeaderEnrichmentUpdateSntLevelMom OBJECT-TYPE
	SYNTAX	 CounterBasedGauge64
	MAX-ACCESS  read-only
	STATUS      current
	DESCRIPTION
	"Table entry attribute for connsyncHeaderEnrichmentUpdateSnt"
	::={connsyncHeaderEnrichmentUpdateSntLevelEntry 3}

connsyncHeaderEnrichmentUpdateSntLevelMax OBJECT-TYPE
	SYNTAX	 CounterBasedGauge64
	MAX-ACCESS  read-only
	STATUS      current
	DESCRIPTION
	"Table entry attribute for connsyncHeaderEnrichmentUpdateSnt"
	::={connsyncHeaderEnrichmentUpdateSntLevelEntry 4}


connsyncProxySntPackets	OBJECT IDENTIFIER ::={connsync 49}

connsyncProxySntPacketsVal	OBJECT-TYPE
	SYNTAX	 Counter64
	MAX-ACCESS read-only
	STATUS current
	DESCRIPTION "Proxy sent packets"

	::={connsyncProxySntPackets 1}

connsyncProxySntPacketsMom	OBJECT-TYPE
	SYNTAX	 CounterBasedGauge64
	MAX-ACCESS read-only
	STATUS current
	DESCRIPTION "Proxy sent packets"

	::={connsyncProxySntPackets 2}

connsyncProxySntPacketsMax	OBJECT-TYPE
	SYNTAX	 CounterBasedGauge64
	MAX-ACCESS read-only
	STATUS current
	DESCRIPTION "Proxy sent packets"

	::={connsyncProxySntPackets 3}

connsyncProxySntPacketsLevelTable OBJECT-TYPE
	SYNTAX      SEQUENCE OF ConnsyncProxySntPacketsLevelEntry
	MAX-ACCESS  not-accessible
	STATUS      current
	DESCRIPTION
	"Table for connsyncProxySntPackets"
	::={connsyncProxySntPackets 4}

connsyncProxySntPacketsLevelEntry OBJECT-TYPE
	SYNTAX      ConnsyncProxySntPacketsLevelEntry
	MAX-ACCESS  not-accessible
	STATUS      current
	DESCRIPTION
	"Table entry for connsyncProxySntPackets"
	INDEX { connsyncProxySntPacketsLevelName }
	::={connsyncProxySntPacketsLevelTable 1}

ConnsyncProxySntPacketsLevelEntry ::=
	SEQUENCE {
		connsyncProxySntPacketsLevelName	DisplayString,
		connsyncProxySntPacketsLevelVal	Counter64,
		connsyncProxySntPacketsLevelMom	CounterBasedGauge64,
		connsyncProxySntPacketsLevelMax	CounterBasedGauge64
	}

connsyncProxySntPacketsLevelName OBJECT-TYPE
	SYNTAX      DisplayString
	MAX-ACCESS  not-accessible
	STATUS      current
	DESCRIPTION
	"Table entry display string for connsyncProxySntPackets"
	::={connsyncProxySntPacketsLevelEntry 1}

connsyncProxySntPacketsLevelVal OBJECT-TYPE
	SYNTAX	 Counter64
	MAX-ACCESS  read-only
	STATUS      current
	DESCRIPTION
	"Table entry attribute for connsyncProxySntPackets"
	::={connsyncProxySntPacketsLevelEntry 2}

connsyncProxySntPacketsLevelMom OBJECT-TYPE
	SYNTAX	 CounterBasedGauge64
	MAX-ACCESS  read-only
	STATUS      current
	DESCRIPTION
	"Table entry attribute for connsyncProxySntPackets"
	::={connsyncProxySntPacketsLevelEntry 3}

connsyncProxySntPacketsLevelMax OBJECT-TYPE
	SYNTAX	 CounterBasedGauge64
	MAX-ACCESS  read-only
	STATUS      current
	DESCRIPTION
	"Table entry attribute for connsyncProxySntPackets"
	::={connsyncProxySntPacketsLevelEntry 4}


connsyncProxySntError	OBJECT IDENTIFIER ::={connsync 50}

connsyncProxySntErrorVal	OBJECT-TYPE
	SYNTAX	 Counter64
	MAX-ACCESS read-only
	STATUS current
	DESCRIPTION "Proxy send error"

	::={connsyncProxySntError 1}

connsyncProxySntErrorMom	OBJECT-TYPE
	SYNTAX	 CounterBasedGauge64
	MAX-ACCESS read-only
	STATUS current
	DESCRIPTION "Proxy send error"

	::={connsyncProxySntError 2}

connsyncProxySntErrorMax	OBJECT-TYPE
	SYNTAX	 CounterBasedGauge64
	MAX-ACCESS read-only
	STATUS current
	DESCRIPTION "Proxy send error"

	::={connsyncProxySntError 3}

connsyncProxySntErrorLevelTable OBJECT-TYPE
	SYNTAX      SEQUENCE OF ConnsyncProxySntErrorLevelEntry
	MAX-ACCESS  not-accessible
	STATUS      current
	DESCRIPTION
	"Table for connsyncProxySntError"
	::={connsyncProxySntError 4}

connsyncProxySntErrorLevelEntry OBJECT-TYPE
	SYNTAX      ConnsyncProxySntErrorLevelEntry
	MAX-ACCESS  not-accessible
	STATUS      current
	DESCRIPTION
	"Table entry for connsyncProxySntError"
	INDEX { connsyncProxySntErrorLevelName }
	::={connsyncProxySntErrorLevelTable 1}

ConnsyncProxySntErrorLevelEntry ::=
	SEQUENCE {
		connsyncProxySntErrorLevelName	DisplayString,
		connsyncProxySntErrorLevelVal	Counter64,
		connsyncProxySntErrorLevelMom	CounterBasedGauge64,
		connsyncProxySntErrorLevelMax	CounterBasedGauge64
	}

connsyncProxySntErrorLevelName OBJECT-TYPE
	SYNTAX      DisplayString
	MAX-ACCESS  not-accessible
	STATUS      current
	DESCRIPTION
	"Table entry display string for connsyncProxySntError"
	::={connsyncProxySntErrorLevelEntry 1}

connsyncProxySntErrorLevelVal OBJECT-TYPE
	SYNTAX	 Counter64
	MAX-ACCESS  read-only
	STATUS      current
	DESCRIPTION
	"Table entry attribute for connsyncProxySntError"
	::={connsyncProxySntErrorLevelEntry 2}

connsyncProxySntErrorLevelMom OBJECT-TYPE
	SYNTAX	 CounterBasedGauge64
	MAX-ACCESS  read-only
	STATUS      current
	DESCRIPTION
	"Table entry attribute for connsyncProxySntError"
	::={connsyncProxySntErrorLevelEntry 3}

connsyncProxySntErrorLevelMax OBJECT-TYPE
	SYNTAX	 CounterBasedGauge64
	MAX-ACCESS  read-only
	STATUS      current
	DESCRIPTION
	"Table entry attribute for connsyncProxySntError"
	::={connsyncProxySntErrorLevelEntry 4}


connsyncProxySntErrorTransFailed	OBJECT IDENTIFIER ::={connsync 51}

connsyncProxySntErrorTransFailedVal	OBJECT-TYPE
	SYNTAX	 Counter64
	MAX-ACCESS read-only
	STATUS current
	DESCRIPTION "Proxy send error (transformation failed)"

	::={connsyncProxySntErrorTransFailed 1}

connsyncProxySntErrorTransFailedMom	OBJECT-TYPE
	SYNTAX	 CounterBasedGauge64
	MAX-ACCESS read-only
	STATUS current
	DESCRIPTION "Proxy send error (transformation failed)"

	::={connsyncProxySntErrorTransFailed 2}

connsyncProxySntErrorTransFailedMax	OBJECT-TYPE
	SYNTAX	 CounterBasedGauge64
	MAX-ACCESS read-only
	STATUS current
	DESCRIPTION "Proxy send error (transformation failed)"

	::={connsyncProxySntErrorTransFailed 3}

connsyncProxySntErrorTransFailedLevelTable OBJECT-TYPE
	SYNTAX      SEQUENCE OF ConnsyncProxySntErrorTransFailedLevelEntry
	MAX-ACCESS  not-accessible
	STATUS      current
	DESCRIPTION
	"Table for connsyncProxySntErrorTransFailed"
	::={connsyncProxySntErrorTransFailed 4}

connsyncProxySntErrorTransFailedLevelEntry OBJECT-TYPE
	SYNTAX      ConnsyncProxySntErrorTransFailedLevelEntry
	MAX-ACCESS  not-accessible
	STATUS      current
	DESCRIPTION
	"Table entry for connsyncProxySntErrorTransFailed"
	INDEX { connsyncProxySntErrorTransFailedLevelName }
	::={connsyncProxySntErrorTransFailedLevelTable 1}

ConnsyncProxySntErrorTransFailedLevelEntry ::=
	SEQUENCE {
		connsyncProxySntErrorTransFailedLevelName	DisplayString,
		connsyncProxySntErrorTransFailedLevelVal	Counter64,
		connsyncProxySntErrorTransFailedLevelMom	CounterBasedGauge64,
		connsyncProxySntErrorTransFailedLevelMax	CounterBasedGauge64
	}

connsyncProxySntErrorTransFailedLevelName OBJECT-TYPE
	SYNTAX      DisplayString
	MAX-ACCESS  not-accessible
	STATUS      current
	DESCRIPTION
	"Table entry display string for connsyncProxySntErrorTransFailed"
	::={connsyncProxySntErrorTransFailedLevelEntry 1}

connsyncProxySntErrorTransFailedLevelVal OBJECT-TYPE
	SYNTAX	 Counter64
	MAX-ACCESS  read-only
	STATUS      current
	DESCRIPTION
	"Table entry attribute for connsyncProxySntErrorTransFailed"
	::={connsyncProxySntErrorTransFailedLevelEntry 2}

connsyncProxySntErrorTransFailedLevelMom OBJECT-TYPE
	SYNTAX	 CounterBasedGauge64
	MAX-ACCESS  read-only
	STATUS      current
	DESCRIPTION
	"Table entry attribute for connsyncProxySntErrorTransFailed"
	::={connsyncProxySntErrorTransFailedLevelEntry 3}

connsyncProxySntErrorTransFailedLevelMax OBJECT-TYPE
	SYNTAX	 CounterBasedGauge64
	MAX-ACCESS  read-only
	STATUS      current
	DESCRIPTION
	"Table entry attribute for connsyncProxySntErrorTransFailed"
	::={connsyncProxySntErrorTransFailedLevelEntry 4}


connsyncProxyRcvPackets	OBJECT IDENTIFIER ::={connsync 52}

connsyncProxyRcvPacketsVal	OBJECT-TYPE
	SYNTAX	 Counter64
	MAX-ACCESS read-only
	STATUS current
	DESCRIPTION "Proxy received packets"

	::={connsyncProxyRcvPackets 1}

connsyncProxyRcvPacketsMom	OBJECT-TYPE
	SYNTAX	 CounterBasedGauge64
	MAX-ACCESS read-only
	STATUS current
	DESCRIPTION "Proxy received packets"

	::={connsyncProxyRcvPackets 2}

connsyncProxyRcvPacketsMax	OBJECT-TYPE
	SYNTAX	 CounterBasedGauge64
	MAX-ACCESS read-only
	STATUS current
	DESCRIPTION "Proxy received packets"

	::={connsyncProxyRcvPackets 3}

connsyncProxyRcvPacketsLevelTable OBJECT-TYPE
	SYNTAX      SEQUENCE OF ConnsyncProxyRcvPacketsLevelEntry
	MAX-ACCESS  not-accessible
	STATUS      current
	DESCRIPTION
	"Table for connsyncProxyRcvPackets"
	::={connsyncProxyRcvPackets 4}

connsyncProxyRcvPacketsLevelEntry OBJECT-TYPE
	SYNTAX      ConnsyncProxyRcvPacketsLevelEntry
	MAX-ACCESS  not-accessible
	STATUS      current
	DESCRIPTION
	"Table entry for connsyncProxyRcvPackets"
	INDEX { connsyncProxyRcvPacketsLevelName }
	::={connsyncProxyRcvPacketsLevelTable 1}

ConnsyncProxyRcvPacketsLevelEntry ::=
	SEQUENCE {
		connsyncProxyRcvPacketsLevelName	DisplayString,
		connsyncProxyRcvPacketsLevelVal	Counter64,
		connsyncProxyRcvPacketsLevelMom	CounterBasedGauge64,
		connsyncProxyRcvPacketsLevelMax	CounterBasedGauge64
	}

connsyncProxyRcvPacketsLevelName OBJECT-TYPE
	SYNTAX      DisplayString
	MAX-ACCESS  not-accessible
	STATUS      current
	DESCRIPTION
	"Table entry display string for connsyncProxyRcvPackets"
	::={connsyncProxyRcvPacketsLevelEntry 1}

connsyncProxyRcvPacketsLevelVal OBJECT-TYPE
	SYNTAX	 Counter64
	MAX-ACCESS  read-only
	STATUS      current
	DESCRIPTION
	"Table entry attribute for connsyncProxyRcvPackets"
	::={connsyncProxyRcvPacketsLevelEntry 2}

connsyncProxyRcvPacketsLevelMom OBJECT-TYPE
	SYNTAX	 CounterBasedGauge64
	MAX-ACCESS  read-only
	STATUS      current
	DESCRIPTION
	"Table entry attribute for connsyncProxyRcvPackets"
	::={connsyncProxyRcvPacketsLevelEntry 3}

connsyncProxyRcvPacketsLevelMax OBJECT-TYPE
	SYNTAX	 CounterBasedGauge64
	MAX-ACCESS  read-only
	STATUS      current
	DESCRIPTION
	"Table entry attribute for connsyncProxyRcvPackets"
	::={connsyncProxyRcvPacketsLevelEntry 4}


connsyncProxyRcvError	OBJECT IDENTIFIER ::={connsync 53}

connsyncProxyRcvErrorVal	OBJECT-TYPE
	SYNTAX	 Counter64
	MAX-ACCESS read-only
	STATUS current
	DESCRIPTION "Proxy receive error"

	::={connsyncProxyRcvError 1}

connsyncProxyRcvErrorMom	OBJECT-TYPE
	SYNTAX	 CounterBasedGauge64
	MAX-ACCESS read-only
	STATUS current
	DESCRIPTION "Proxy receive error"

	::={connsyncProxyRcvError 2}

connsyncProxyRcvErrorMax	OBJECT-TYPE
	SYNTAX	 CounterBasedGauge64
	MAX-ACCESS read-only
	STATUS current
	DESCRIPTION "Proxy receive error"

	::={connsyncProxyRcvError 3}

connsyncProxyRcvErrorLevelTable OBJECT-TYPE
	SYNTAX      SEQUENCE OF ConnsyncProxyRcvErrorLevelEntry
	MAX-ACCESS  not-accessible
	STATUS      current
	DESCRIPTION
	"Table for connsyncProxyRcvError"
	::={connsyncProxyRcvError 4}

connsyncProxyRcvErrorLevelEntry OBJECT-TYPE
	SYNTAX      ConnsyncProxyRcvErrorLevelEntry
	MAX-ACCESS  not-accessible
	STATUS      current
	DESCRIPTION
	"Table entry for connsyncProxyRcvError"
	INDEX { connsyncProxyRcvErrorLevelName }
	::={connsyncProxyRcvErrorLevelTable 1}

ConnsyncProxyRcvErrorLevelEntry ::=
	SEQUENCE {
		connsyncProxyRcvErrorLevelName	DisplayString,
		connsyncProxyRcvErrorLevelVal	Counter64,
		connsyncProxyRcvErrorLevelMom	CounterBasedGauge64,
		connsyncProxyRcvErrorLevelMax	CounterBasedGauge64
	}

connsyncProxyRcvErrorLevelName OBJECT-TYPE
	SYNTAX      DisplayString
	MAX-ACCESS  not-accessible
	STATUS      current
	DESCRIPTION
	"Table entry display string for connsyncProxyRcvError"
	::={connsyncProxyRcvErrorLevelEntry 1}

connsyncProxyRcvErrorLevelVal OBJECT-TYPE
	SYNTAX	 Counter64
	MAX-ACCESS  read-only
	STATUS      current
	DESCRIPTION
	"Table entry attribute for connsyncProxyRcvError"
	::={connsyncProxyRcvErrorLevelEntry 2}

connsyncProxyRcvErrorLevelMom OBJECT-TYPE
	SYNTAX	 CounterBasedGauge64
	MAX-ACCESS  read-only
	STATUS      current
	DESCRIPTION
	"Table entry attribute for connsyncProxyRcvError"
	::={connsyncProxyRcvErrorLevelEntry 3}

connsyncProxyRcvErrorLevelMax OBJECT-TYPE
	SYNTAX	 CounterBasedGauge64
	MAX-ACCESS  read-only
	STATUS      current
	DESCRIPTION
	"Table entry attribute for connsyncProxyRcvError"
	::={connsyncProxyRcvErrorLevelEntry 4}


connsyncProxyRcvErrorUnknownConnection	OBJECT IDENTIFIER ::={connsync 54}

connsyncProxyRcvErrorUnknownConnectionVal	OBJECT-TYPE
	SYNTAX	 Counter64
	MAX-ACCESS read-only
	STATUS current
	DESCRIPTION "Proxy receive error (unknown connection)"

	::={connsyncProxyRcvErrorUnknownConnection 1}

connsyncProxyRcvErrorUnknownConnectionMom	OBJECT-TYPE
	SYNTAX	 CounterBasedGauge64
	MAX-ACCESS read-only
	STATUS current
	DESCRIPTION "Proxy receive error (unknown connection)"

	::={connsyncProxyRcvErrorUnknownConnection 2}

connsyncProxyRcvErrorUnknownConnectionMax	OBJECT-TYPE
	SYNTAX	 CounterBasedGauge64
	MAX-ACCESS read-only
	STATUS current
	DESCRIPTION "Proxy receive error (unknown connection)"

	::={connsyncProxyRcvErrorUnknownConnection 3}

connsyncProxyRcvErrorUnknownConnectionLevelTable OBJECT-TYPE
	SYNTAX      SEQUENCE OF ConnsyncProxyRcvErrorUnknownConnectionLevelEntry
	MAX-ACCESS  not-accessible
	STATUS      current
	DESCRIPTION
	"Table for connsyncProxyRcvErrorUnknownConnection"
	::={connsyncProxyRcvErrorUnknownConnection 4}

connsyncProxyRcvErrorUnknownConnectionLevelEntry OBJECT-TYPE
	SYNTAX      ConnsyncProxyRcvErrorUnknownConnectionLevelEntry
	MAX-ACCESS  not-accessible
	STATUS      current
	DESCRIPTION
	"Table entry for connsyncProxyRcvErrorUnknownConnection"
	INDEX { connsyncProxyRcvErrorUnknownConnectionLevelName }
	::={connsyncProxyRcvErrorUnknownConnectionLevelTable 1}

ConnsyncProxyRcvErrorUnknownConnectionLevelEntry ::=
	SEQUENCE {
		connsyncProxyRcvErrorUnknownConnectionLevelName	DisplayString,
		connsyncProxyRcvErrorUnknownConnectionLevelVal	Counter64,
		connsyncProxyRcvErrorUnknownConnectionLevelMom	CounterBasedGauge64,
		connsyncProxyRcvErrorUnknownConnectionLevelMax	CounterBasedGauge64
	}

connsyncProxyRcvErrorUnknownConnectionLevelName OBJECT-TYPE
	SYNTAX      DisplayString
	MAX-ACCESS  not-accessible
	STATUS      current
	DESCRIPTION
	"Table entry display string for connsyncProxyRcvErrorUnknownConnection"
	::={connsyncProxyRcvErrorUnknownConnectionLevelEntry 1}

connsyncProxyRcvErrorUnknownConnectionLevelVal OBJECT-TYPE
	SYNTAX	 Counter64
	MAX-ACCESS  read-only
	STATUS      current
	DESCRIPTION
	"Table entry attribute for connsyncProxyRcvErrorUnknownConnection"
	::={connsyncProxyRcvErrorUnknownConnectionLevelEntry 2}

connsyncProxyRcvErrorUnknownConnectionLevelMom OBJECT-TYPE
	SYNTAX	 CounterBasedGauge64
	MAX-ACCESS  read-only
	STATUS      current
	DESCRIPTION
	"Table entry attribute for connsyncProxyRcvErrorUnknownConnection"
	::={connsyncProxyRcvErrorUnknownConnectionLevelEntry 3}

connsyncProxyRcvErrorUnknownConnectionLevelMax OBJECT-TYPE
	SYNTAX	 CounterBasedGauge64
	MAX-ACCESS  read-only
	STATUS      current
	DESCRIPTION
	"Table entry attribute for connsyncProxyRcvErrorUnknownConnection"
	::={connsyncProxyRcvErrorUnknownConnectionLevelEntry 4}


connsyncProxyRcvErrorUnknownConnType	OBJECT IDENTIFIER ::={connsync 55}

connsyncProxyRcvErrorUnknownConnTypeVal	OBJECT-TYPE
	SYNTAX	 Counter64
	MAX-ACCESS read-only
	STATUS current
	DESCRIPTION "Proxy receive error (unknown connection type)"

	::={connsyncProxyRcvErrorUnknownConnType 1}

connsyncProxyRcvErrorUnknownConnTypeMom	OBJECT-TYPE
	SYNTAX	 CounterBasedGauge64
	MAX-ACCESS read-only
	STATUS current
	DESCRIPTION "Proxy receive error (unknown connection type)"

	::={connsyncProxyRcvErrorUnknownConnType 2}

connsyncProxyRcvErrorUnknownConnTypeMax	OBJECT-TYPE
	SYNTAX	 CounterBasedGauge64
	MAX-ACCESS read-only
	STATUS current
	DESCRIPTION "Proxy receive error (unknown connection type)"

	::={connsyncProxyRcvErrorUnknownConnType 3}

connsyncProxyRcvErrorUnknownConnTypeLevelTable OBJECT-TYPE
	SYNTAX      SEQUENCE OF ConnsyncProxyRcvErrorUnknownConnTypeLevelEntry
	MAX-ACCESS  not-accessible
	STATUS      current
	DESCRIPTION
	"Table for connsyncProxyRcvErrorUnknownConnType"
	::={connsyncProxyRcvErrorUnknownConnType 4}

connsyncProxyRcvErrorUnknownConnTypeLevelEntry OBJECT-TYPE
	SYNTAX      ConnsyncProxyRcvErrorUnknownConnTypeLevelEntry
	MAX-ACCESS  not-accessible
	STATUS      current
	DESCRIPTION
	"Table entry for connsyncProxyRcvErrorUnknownConnType"
	INDEX { connsyncProxyRcvErrorUnknownConnTypeLevelName }
	::={connsyncProxyRcvErrorUnknownConnTypeLevelTable 1}

ConnsyncProxyRcvErrorUnknownConnTypeLevelEntry ::=
	SEQUENCE {
		connsyncProxyRcvErrorUnknownConnTypeLevelName	DisplayString,
		connsyncProxyRcvErrorUnknownConnTypeLevelVal	Counter64,
		connsyncProxyRcvErrorUnknownConnTypeLevelMom	CounterBasedGauge64,
		connsyncProxyRcvErrorUnknownConnTypeLevelMax	CounterBasedGauge64
	}

connsyncProxyRcvErrorUnknownConnTypeLevelName OBJECT-TYPE
	SYNTAX      DisplayString
	MAX-ACCESS  not-accessible
	STATUS      current
	DESCRIPTION
	"Table entry display string for connsyncProxyRcvErrorUnknownConnType"
	::={connsyncProxyRcvErrorUnknownConnTypeLevelEntry 1}

connsyncProxyRcvErrorUnknownConnTypeLevelVal OBJECT-TYPE
	SYNTAX	 Counter64
	MAX-ACCESS  read-only
	STATUS      current
	DESCRIPTION
	"Table entry attribute for connsyncProxyRcvErrorUnknownConnType"
	::={connsyncProxyRcvErrorUnknownConnTypeLevelEntry 2}

connsyncProxyRcvErrorUnknownConnTypeLevelMom OBJECT-TYPE
	SYNTAX	 CounterBasedGauge64
	MAX-ACCESS  read-only
	STATUS      current
	DESCRIPTION
	"Table entry attribute for connsyncProxyRcvErrorUnknownConnType"
	::={connsyncProxyRcvErrorUnknownConnTypeLevelEntry 3}

connsyncProxyRcvErrorUnknownConnTypeLevelMax OBJECT-TYPE
	SYNTAX	 CounterBasedGauge64
	MAX-ACCESS  read-only
	STATUS      current
	DESCRIPTION
	"Table entry attribute for connsyncProxyRcvErrorUnknownConnType"
	::={connsyncProxyRcvErrorUnknownConnTypeLevelEntry 4}


connsyncProxyRcvErrorCorruptPacket	OBJECT IDENTIFIER ::={connsync 56}

connsyncProxyRcvErrorCorruptPacketVal	OBJECT-TYPE
	SYNTAX	 Counter64
	MAX-ACCESS read-only
	STATUS current
	DESCRIPTION "Proxy receive error (corrupt packet)"

	::={connsyncProxyRcvErrorCorruptPacket 1}

connsyncProxyRcvErrorCorruptPacketMom	OBJECT-TYPE
	SYNTAX	 CounterBasedGauge64
	MAX-ACCESS read-only
	STATUS current
	DESCRIPTION "Proxy receive error (corrupt packet)"

	::={connsyncProxyRcvErrorCorruptPacket 2}

connsyncProxyRcvErrorCorruptPacketMax	OBJECT-TYPE
	SYNTAX	 CounterBasedGauge64
	MAX-ACCESS read-only
	STATUS current
	DESCRIPTION "Proxy receive error (corrupt packet)"

	::={connsyncProxyRcvErrorCorruptPacket 3}

connsyncProxyRcvErrorCorruptPacketLevelTable OBJECT-TYPE
	SYNTAX      SEQUENCE OF ConnsyncProxyRcvErrorCorruptPacketLevelEntry
	MAX-ACCESS  not-accessible
	STATUS      current
	DESCRIPTION
	"Table for connsyncProxyRcvErrorCorruptPacket"
	::={connsyncProxyRcvErrorCorruptPacket 4}

connsyncProxyRcvErrorCorruptPacketLevelEntry OBJECT-TYPE
	SYNTAX      ConnsyncProxyRcvErrorCorruptPacketLevelEntry
	MAX-ACCESS  not-accessible
	STATUS      current
	DESCRIPTION
	"Table entry for connsyncProxyRcvErrorCorruptPacket"
	INDEX { connsyncProxyRcvErrorCorruptPacketLevelName }
	::={connsyncProxyRcvErrorCorruptPacketLevelTable 1}

ConnsyncProxyRcvErrorCorruptPacketLevelEntry ::=
	SEQUENCE {
		connsyncProxyRcvErrorCorruptPacketLevelName	DisplayString,
		connsyncProxyRcvErrorCorruptPacketLevelVal	Counter64,
		connsyncProxyRcvErrorCorruptPacketLevelMom	CounterBasedGauge64,
		connsyncProxyRcvErrorCorruptPacketLevelMax	CounterBasedGauge64
	}

connsyncProxyRcvErrorCorruptPacketLevelName OBJECT-TYPE
	SYNTAX      DisplayString
	MAX-ACCESS  not-accessible
	STATUS      current
	DESCRIPTION
	"Table entry display string for connsyncProxyRcvErrorCorruptPacket"
	::={connsyncProxyRcvErrorCorruptPacketLevelEntry 1}

connsyncProxyRcvErrorCorruptPacketLevelVal OBJECT-TYPE
	SYNTAX	 Counter64
	MAX-ACCESS  read-only
	STATUS      current
	DESCRIPTION
	"Table entry attribute for connsyncProxyRcvErrorCorruptPacket"
	::={connsyncProxyRcvErrorCorruptPacketLevelEntry 2}

connsyncProxyRcvErrorCorruptPacketLevelMom OBJECT-TYPE
	SYNTAX	 CounterBasedGauge64
	MAX-ACCESS  read-only
	STATUS      current
	DESCRIPTION
	"Table entry attribute for connsyncProxyRcvErrorCorruptPacket"
	::={connsyncProxyRcvErrorCorruptPacketLevelEntry 3}

connsyncProxyRcvErrorCorruptPacketLevelMax OBJECT-TYPE
	SYNTAX	 CounterBasedGauge64
	MAX-ACCESS  read-only
	STATUS      current
	DESCRIPTION
	"Table entry attribute for connsyncProxyRcvErrorCorruptPacket"
	::={connsyncProxyRcvErrorCorruptPacketLevelEntry 4}


connsyncProxyDivertNotifySnt	OBJECT IDENTIFIER ::={connsync 57}

connsyncProxyDivertNotifySntVal	OBJECT-TYPE
	SYNTAX	 Counter64
	MAX-ACCESS read-only
	STATUS current
	DESCRIPTION "Proxy divert notifications sent"

	::={connsyncProxyDivertNotifySnt 1}

connsyncProxyDivertNotifySntMom	OBJECT-TYPE
	SYNTAX	 CounterBasedGauge64
	MAX-ACCESS read-only
	STATUS current
	DESCRIPTION "Proxy divert notifications sent"

	::={connsyncProxyDivertNotifySnt 2}

connsyncProxyDivertNotifySntMax	OBJECT-TYPE
	SYNTAX	 CounterBasedGauge64
	MAX-ACCESS read-only
	STATUS current
	DESCRIPTION "Proxy divert notifications sent"

	::={connsyncProxyDivertNotifySnt 3}

connsyncProxyDivertNotifySntLevelTable OBJECT-TYPE
	SYNTAX      SEQUENCE OF ConnsyncProxyDivertNotifySntLevelEntry
	MAX-ACCESS  not-accessible
	STATUS      current
	DESCRIPTION
	"Table for connsyncProxyDivertNotifySnt"
	::={connsyncProxyDivertNotifySnt 4}

connsyncProxyDivertNotifySntLevelEntry OBJECT-TYPE
	SYNTAX      ConnsyncProxyDivertNotifySntLevelEntry
	MAX-ACCESS  not-accessible
	STATUS      current
	DESCRIPTION
	"Table entry for connsyncProxyDivertNotifySnt"
	INDEX { connsyncProxyDivertNotifySntLevelName }
	::={connsyncProxyDivertNotifySntLevelTable 1}

ConnsyncProxyDivertNotifySntLevelEntry ::=
	SEQUENCE {
		connsyncProxyDivertNotifySntLevelName	DisplayString,
		connsyncProxyDivertNotifySntLevelVal	Counter64,
		connsyncProxyDivertNotifySntLevelMom	CounterBasedGauge64,
		connsyncProxyDivertNotifySntLevelMax	CounterBasedGauge64
	}

connsyncProxyDivertNotifySntLevelName OBJECT-TYPE
	SYNTAX      DisplayString
	MAX-ACCESS  not-accessible
	STATUS      current
	DESCRIPTION
	"Table entry display string for connsyncProxyDivertNotifySnt"
	::={connsyncProxyDivertNotifySntLevelEntry 1}

connsyncProxyDivertNotifySntLevelVal OBJECT-TYPE
	SYNTAX	 Counter64
	MAX-ACCESS  read-only
	STATUS      current
	DESCRIPTION
	"Table entry attribute for connsyncProxyDivertNotifySnt"
	::={connsyncProxyDivertNotifySntLevelEntry 2}

connsyncProxyDivertNotifySntLevelMom OBJECT-TYPE
	SYNTAX	 CounterBasedGauge64
	MAX-ACCESS  read-only
	STATUS      current
	DESCRIPTION
	"Table entry attribute for connsyncProxyDivertNotifySnt"
	::={connsyncProxyDivertNotifySntLevelEntry 3}

connsyncProxyDivertNotifySntLevelMax OBJECT-TYPE
	SYNTAX	 CounterBasedGauge64
	MAX-ACCESS  read-only
	STATUS      current
	DESCRIPTION
	"Table entry attribute for connsyncProxyDivertNotifySnt"
	::={connsyncProxyDivertNotifySntLevelEntry 4}


connsyncProxyDivertNotifyRcv	OBJECT IDENTIFIER ::={connsync 58}

connsyncProxyDivertNotifyRcvVal	OBJECT-TYPE
	SYNTAX	 Counter64
	MAX-ACCESS read-only
	STATUS current
	DESCRIPTION "Proxy divert notifications received"

	::={connsyncProxyDivertNotifyRcv 1}

connsyncProxyDivertNotifyRcvMom	OBJECT-TYPE
	SYNTAX	 CounterBasedGauge64
	MAX-ACCESS read-only
	STATUS current
	DESCRIPTION "Proxy divert notifications received"

	::={connsyncProxyDivertNotifyRcv 2}

connsyncProxyDivertNotifyRcvMax	OBJECT-TYPE
	SYNTAX	 CounterBasedGauge64
	MAX-ACCESS read-only
	STATUS current
	DESCRIPTION "Proxy divert notifications received"

	::={connsyncProxyDivertNotifyRcv 3}

connsyncProxyDivertNotifyRcvLevelTable OBJECT-TYPE
	SYNTAX      SEQUENCE OF ConnsyncProxyDivertNotifyRcvLevelEntry
	MAX-ACCESS  not-accessible
	STATUS      current
	DESCRIPTION
	"Table for connsyncProxyDivertNotifyRcv"
	::={connsyncProxyDivertNotifyRcv 4}

connsyncProxyDivertNotifyRcvLevelEntry OBJECT-TYPE
	SYNTAX      ConnsyncProxyDivertNotifyRcvLevelEntry
	MAX-ACCESS  not-accessible
	STATUS      current
	DESCRIPTION
	"Table entry for connsyncProxyDivertNotifyRcv"
	INDEX { connsyncProxyDivertNotifyRcvLevelName }
	::={connsyncProxyDivertNotifyRcvLevelTable 1}

ConnsyncProxyDivertNotifyRcvLevelEntry ::=
	SEQUENCE {
		connsyncProxyDivertNotifyRcvLevelName	DisplayString,
		connsyncProxyDivertNotifyRcvLevelVal	Counter64,
		connsyncProxyDivertNotifyRcvLevelMom	CounterBasedGauge64,
		connsyncProxyDivertNotifyRcvLevelMax	CounterBasedGauge64
	}

connsyncProxyDivertNotifyRcvLevelName OBJECT-TYPE
	SYNTAX      DisplayString
	MAX-ACCESS  not-accessible
	STATUS      current
	DESCRIPTION
	"Table entry display string for connsyncProxyDivertNotifyRcv"
	::={connsyncProxyDivertNotifyRcvLevelEntry 1}

connsyncProxyDivertNotifyRcvLevelVal OBJECT-TYPE
	SYNTAX	 Counter64
	MAX-ACCESS  read-only
	STATUS      current
	DESCRIPTION
	"Table entry attribute for connsyncProxyDivertNotifyRcv"
	::={connsyncProxyDivertNotifyRcvLevelEntry 2}

connsyncProxyDivertNotifyRcvLevelMom OBJECT-TYPE
	SYNTAX	 CounterBasedGauge64
	MAX-ACCESS  read-only
	STATUS      current
	DESCRIPTION
	"Table entry attribute for connsyncProxyDivertNotifyRcv"
	::={connsyncProxyDivertNotifyRcvLevelEntry 3}

connsyncProxyDivertNotifyRcvLevelMax OBJECT-TYPE
	SYNTAX	 CounterBasedGauge64
	MAX-ACCESS  read-only
	STATUS      current
	DESCRIPTION
	"Table entry attribute for connsyncProxyDivertNotifyRcv"
	::={connsyncProxyDivertNotifyRcvLevelEntry 4}


connsyncProxyDivertNotifyRcvErrorNotFound	OBJECT IDENTIFIER ::={connsync 59}

connsyncProxyDivertNotifyRcvErrorNotFoundVal	OBJECT-TYPE
	SYNTAX	 Counter64
	MAX-ACCESS read-only
	STATUS current
	DESCRIPTION "Proxy divert notifications receive errors (connection not found)"

	::={connsyncProxyDivertNotifyRcvErrorNotFound 1}

connsyncProxyDivertNotifyRcvErrorNotFoundMom	OBJECT-TYPE
	SYNTAX	 CounterBasedGauge64
	MAX-ACCESS read-only
	STATUS current
	DESCRIPTION "Proxy divert notifications receive errors (connection not found)"

	::={connsyncProxyDivertNotifyRcvErrorNotFound 2}

connsyncProxyDivertNotifyRcvErrorNotFoundMax	OBJECT-TYPE
	SYNTAX	 CounterBasedGauge64
	MAX-ACCESS read-only
	STATUS current
	DESCRIPTION "Proxy divert notifications receive errors (connection not found)"

	::={connsyncProxyDivertNotifyRcvErrorNotFound 3}

connsyncProxyDivertNotifyRcvErrorNotFoundLevelTable OBJECT-TYPE
	SYNTAX      SEQUENCE OF ConnsyncProxyDivertNotifyRcvErrorNotFoundLevelEntry
	MAX-ACCESS  not-accessible
	STATUS      current
	DESCRIPTION
	"Table for connsyncProxyDivertNotifyRcvErrorNotFound"
	::={connsyncProxyDivertNotifyRcvErrorNotFound 4}

connsyncProxyDivertNotifyRcvErrorNotFoundLevelEntry OBJECT-TYPE
	SYNTAX      ConnsyncProxyDivertNotifyRcvErrorNotFoundLevelEntry
	MAX-ACCESS  not-accessible
	STATUS      current
	DESCRIPTION
	"Table entry for connsyncProxyDivertNotifyRcvErrorNotFound"
	INDEX { connsyncProxyDivertNotifyRcvErrorNotFoundLevelName }
	::={connsyncProxyDivertNotifyRcvErrorNotFoundLevelTable 1}

ConnsyncProxyDivertNotifyRcvErrorNotFoundLevelEntry ::=
	SEQUENCE {
		connsyncProxyDivertNotifyRcvErrorNotFoundLevelName	DisplayString,
		connsyncProxyDivertNotifyRcvErrorNotFoundLevelVal	Counter64,
		connsyncProxyDivertNotifyRcvErrorNotFoundLevelMom	CounterBasedGauge64,
		connsyncProxyDivertNotifyRcvErrorNotFoundLevelMax	CounterBasedGauge64
	}

connsyncProxyDivertNotifyRcvErrorNotFoundLevelName OBJECT-TYPE
	SYNTAX      DisplayString
	MAX-ACCESS  not-accessible
	STATUS      current
	DESCRIPTION
	"Table entry display string for connsyncProxyDivertNotifyRcvErrorNotFound"
	::={connsyncProxyDivertNotifyRcvErrorNotFoundLevelEntry 1}

connsyncProxyDivertNotifyRcvErrorNotFoundLevelVal OBJECT-TYPE
	SYNTAX	 Counter64
	MAX-ACCESS  read-only
	STATUS      current
	DESCRIPTION
	"Table entry attribute for connsyncProxyDivertNotifyRcvErrorNotFound"
	::={connsyncProxyDivertNotifyRcvErrorNotFoundLevelEntry 2}

connsyncProxyDivertNotifyRcvErrorNotFoundLevelMom OBJECT-TYPE
	SYNTAX	 CounterBasedGauge64
	MAX-ACCESS  read-only
	STATUS      current
	DESCRIPTION
	"Table entry attribute for connsyncProxyDivertNotifyRcvErrorNotFound"
	::={connsyncProxyDivertNotifyRcvErrorNotFoundLevelEntry 3}

connsyncProxyDivertNotifyRcvErrorNotFoundLevelMax OBJECT-TYPE
	SYNTAX	 CounterBasedGauge64
	MAX-ACCESS  read-only
	STATUS      current
	DESCRIPTION
	"Table entry attribute for connsyncProxyDivertNotifyRcvErrorNotFound"
	::={connsyncProxyDivertNotifyRcvErrorNotFoundLevelEntry 4}


connsyncOhaiRcv	OBJECT IDENTIFIER ::={connsync 60}

connsyncOhaiRcvVal	OBJECT-TYPE
	SYNTAX	 Counter64
	MAX-ACCESS read-only
	STATUS current
	DESCRIPTION "Ohai received"

	::={connsyncOhaiRcv 1}

connsyncOhaiRcvMom	OBJECT-TYPE
	SYNTAX	 CounterBasedGauge64
	MAX-ACCESS read-only
	STATUS current
	DESCRIPTION "Ohai received"

	::={connsyncOhaiRcv 2}

connsyncOhaiRcvMax	OBJECT-TYPE
	SYNTAX	 CounterBasedGauge64
	MAX-ACCESS read-only
	STATUS current
	DESCRIPTION "Ohai received"

	::={connsyncOhaiRcv 3}

connsyncOhaiRcvLevelTable OBJECT-TYPE
	SYNTAX      SEQUENCE OF ConnsyncOhaiRcvLevelEntry
	MAX-ACCESS  not-accessible
	STATUS      current
	DESCRIPTION
	"Table for connsyncOhaiRcv"
	::={connsyncOhaiRcv 4}

connsyncOhaiRcvLevelEntry OBJECT-TYPE
	SYNTAX      ConnsyncOhaiRcvLevelEntry
	MAX-ACCESS  not-accessible
	STATUS      current
	DESCRIPTION
	"Table entry for connsyncOhaiRcv"
	INDEX { connsyncOhaiRcvLevelName }
	::={connsyncOhaiRcvLevelTable 1}

ConnsyncOhaiRcvLevelEntry ::=
	SEQUENCE {
		connsyncOhaiRcvLevelName	DisplayString,
		connsyncOhaiRcvLevelVal	Counter64,
		connsyncOhaiRcvLevelMom	CounterBasedGauge64,
		connsyncOhaiRcvLevelMax	CounterBasedGauge64
	}

connsyncOhaiRcvLevelName OBJECT-TYPE
	SYNTAX      DisplayString
	MAX-ACCESS  not-accessible
	STATUS      current
	DESCRIPTION
	"Table entry display string for connsyncOhaiRcv"
	::={connsyncOhaiRcvLevelEntry 1}

connsyncOhaiRcvLevelVal OBJECT-TYPE
	SYNTAX	 Counter64
	MAX-ACCESS  read-only
	STATUS      current
	DESCRIPTION
	"Table entry attribute for connsyncOhaiRcv"
	::={connsyncOhaiRcvLevelEntry 2}

connsyncOhaiRcvLevelMom OBJECT-TYPE
	SYNTAX	 CounterBasedGauge64
	MAX-ACCESS  read-only
	STATUS      current
	DESCRIPTION
	"Table entry attribute for connsyncOhaiRcv"
	::={connsyncOhaiRcvLevelEntry 3}

connsyncOhaiRcvLevelMax OBJECT-TYPE
	SYNTAX	 CounterBasedGauge64
	MAX-ACCESS  read-only
	STATUS      current
	DESCRIPTION
	"Table entry attribute for connsyncOhaiRcv"
	::={connsyncOhaiRcvLevelEntry 4}


connsyncPeerRttAverage	OBJECT IDENTIFIER ::={connsync 61}

connsyncPeerRttAverageVal	OBJECT-TYPE
	SYNTAX	 CounterBasedGauge64
	MAX-ACCESS read-only
	STATUS current
	DESCRIPTION "Peer RTT mean (ms)"

	::={connsyncPeerRttAverage 1}

connsyncPeerRttAverageMax	OBJECT-TYPE
	SYNTAX	 CounterBasedGauge64
	MAX-ACCESS read-only
	STATUS current
	DESCRIPTION "Peer RTT mean (ms)"

	::={connsyncPeerRttAverage 3}

connsyncPeerRttAverageLevelTable OBJECT-TYPE
	SYNTAX      SEQUENCE OF ConnsyncPeerRttAverageLevelEntry
	MAX-ACCESS  not-accessible
	STATUS      current
	DESCRIPTION
	"Table for connsyncPeerRttAverage"
	::={connsyncPeerRttAverage 4}

connsyncPeerRttAverageLevelEntry OBJECT-TYPE
	SYNTAX      ConnsyncPeerRttAverageLevelEntry
	MAX-ACCESS  not-accessible
	STATUS      current
	DESCRIPTION
	"Table entry for connsyncPeerRttAverage"
	INDEX { connsyncPeerRttAverageLevelName }
	::={connsyncPeerRttAverageLevelTable 1}

ConnsyncPeerRttAverageLevelEntry ::=
	SEQUENCE {
		connsyncPeerRttAverageLevelName	DisplayString,
		connsyncPeerRttAverageLevelVal	CounterBasedGauge64,
		connsyncPeerRttAverageLevelMax	CounterBasedGauge64
	}

connsyncPeerRttAverageLevelName OBJECT-TYPE
	SYNTAX      DisplayString
	MAX-ACCESS  not-accessible
	STATUS      current
	DESCRIPTION
	"Table entry display string for connsyncPeerRttAverage"
	::={connsyncPeerRttAverageLevelEntry 1}

connsyncPeerRttAverageLevelVal OBJECT-TYPE
	SYNTAX	 CounterBasedGauge64
	MAX-ACCESS  read-only
	STATUS      current
	DESCRIPTION
	"Table entry attribute for connsyncPeerRttAverage"
	::={connsyncPeerRttAverageLevelEntry 2}

connsyncPeerRttAverageLevelMax OBJECT-TYPE
	SYNTAX	 CounterBasedGauge64
	MAX-ACCESS  read-only
	STATUS      current
	DESCRIPTION
	"Table entry attribute for connsyncPeerRttAverage"
	::={connsyncPeerRttAverageLevelEntry 4}


connsyncPeerRttVariance	OBJECT IDENTIFIER ::={connsync 62}

connsyncPeerRttVarianceVal	OBJECT-TYPE
	SYNTAX	 CounterBasedGauge64
	MAX-ACCESS read-only
	STATUS current
	DESCRIPTION "Peer RTT variance (ms)"

	::={connsyncPeerRttVariance 1}

connsyncPeerRttVarianceMax	OBJECT-TYPE
	SYNTAX	 CounterBasedGauge64
	MAX-ACCESS read-only
	STATUS current
	DESCRIPTION "Peer RTT variance (ms)"

	::={connsyncPeerRttVariance 3}

connsyncPeerRttVarianceLevelTable OBJECT-TYPE
	SYNTAX      SEQUENCE OF ConnsyncPeerRttVarianceLevelEntry
	MAX-ACCESS  not-accessible
	STATUS      current
	DESCRIPTION
	"Table for connsyncPeerRttVariance"
	::={connsyncPeerRttVariance 4}

connsyncPeerRttVarianceLevelEntry OBJECT-TYPE
	SYNTAX      ConnsyncPeerRttVarianceLevelEntry
	MAX-ACCESS  not-accessible
	STATUS      current
	DESCRIPTION
	"Table entry for connsyncPeerRttVariance"
	INDEX { connsyncPeerRttVarianceLevelName }
	::={connsyncPeerRttVarianceLevelTable 1}

ConnsyncPeerRttVarianceLevelEntry ::=
	SEQUENCE {
		connsyncPeerRttVarianceLevelName	DisplayString,
		connsyncPeerRttVarianceLevelVal	CounterBasedGauge64,
		connsyncPeerRttVarianceLevelMax	CounterBasedGauge64
	}

connsyncPeerRttVarianceLevelName OBJECT-TYPE
	SYNTAX      DisplayString
	MAX-ACCESS  not-accessible
	STATUS      current
	DESCRIPTION
	"Table entry display string for connsyncPeerRttVariance"
	::={connsyncPeerRttVarianceLevelEntry 1}

connsyncPeerRttVarianceLevelVal OBJECT-TYPE
	SYNTAX	 CounterBasedGauge64
	MAX-ACCESS  read-only
	STATUS      current
	DESCRIPTION
	"Table entry attribute for connsyncPeerRttVariance"
	::={connsyncPeerRttVarianceLevelEntry 2}

connsyncPeerRttVarianceLevelMax OBJECT-TYPE
	SYNTAX	 CounterBasedGauge64
	MAX-ACCESS  read-only
	STATUS      current
	DESCRIPTION
	"Table entry attribute for connsyncPeerRttVariance"
	::={connsyncPeerRttVarianceLevelEntry 4}


connsyncPeerClockDiff	OBJECT IDENTIFIER ::={connsync 63}

connsyncPeerClockDiffVal	OBJECT-TYPE
	SYNTAX	 CounterBasedGauge64
	MAX-ACCESS read-only
	STATUS current
	DESCRIPTION "Peer PLOS clock difference (ms)"

	::={connsyncPeerClockDiff 1}

connsyncPeerClockDiffMax	OBJECT-TYPE
	SYNTAX	 CounterBasedGauge64
	MAX-ACCESS read-only
	STATUS current
	DESCRIPTION "Peer PLOS clock difference (ms)"

	::={connsyncPeerClockDiff 3}

connsyncPeerClockDiffLevelTable OBJECT-TYPE
	SYNTAX      SEQUENCE OF ConnsyncPeerClockDiffLevelEntry
	MAX-ACCESS  not-accessible
	STATUS      current
	DESCRIPTION
	"Table for connsyncPeerClockDiff"
	::={connsyncPeerClockDiff 4}

connsyncPeerClockDiffLevelEntry OBJECT-TYPE
	SYNTAX      ConnsyncPeerClockDiffLevelEntry
	MAX-ACCESS  not-accessible
	STATUS      current
	DESCRIPTION
	"Table entry for connsyncPeerClockDiff"
	INDEX { connsyncPeerClockDiffLevelName }
	::={connsyncPeerClockDiffLevelTable 1}

ConnsyncPeerClockDiffLevelEntry ::=
	SEQUENCE {
		connsyncPeerClockDiffLevelName	DisplayString,
		connsyncPeerClockDiffLevelVal	CounterBasedGauge64,
		connsyncPeerClockDiffLevelMax	CounterBasedGauge64
	}

connsyncPeerClockDiffLevelName OBJECT-TYPE
	SYNTAX      DisplayString
	MAX-ACCESS  not-accessible
	STATUS      current
	DESCRIPTION
	"Table entry display string for connsyncPeerClockDiff"
	::={connsyncPeerClockDiffLevelEntry 1}

connsyncPeerClockDiffLevelVal OBJECT-TYPE
	SYNTAX	 CounterBasedGauge64
	MAX-ACCESS  read-only
	STATUS      current
	DESCRIPTION
	"Table entry attribute for connsyncPeerClockDiff"
	::={connsyncPeerClockDiffLevelEntry 2}

connsyncPeerClockDiffLevelMax OBJECT-TYPE
	SYNTAX	 CounterBasedGauge64
	MAX-ACCESS  read-only
	STATUS      current
	DESCRIPTION
	"Table entry attribute for connsyncPeerClockDiff"
	::={connsyncPeerClockDiffLevelEntry 4}


connsyncPeerClockOutOfSync	OBJECT IDENTIFIER ::={connsync 64}

connsyncPeerClockOutOfSyncVal	OBJECT-TYPE
	SYNTAX	 Counter64
	MAX-ACCESS read-only
	STATUS current
	DESCRIPTION "Clocks out of sync between peers"

	::={connsyncPeerClockOutOfSync 1}

connsyncPeerClockOutOfSyncMom	OBJECT-TYPE
	SYNTAX	 CounterBasedGauge64
	MAX-ACCESS read-only
	STATUS current
	DESCRIPTION "Clocks out of sync between peers"

	::={connsyncPeerClockOutOfSync 2}

connsyncPeerClockOutOfSyncMax	OBJECT-TYPE
	SYNTAX	 CounterBasedGauge64
	MAX-ACCESS read-only
	STATUS current
	DESCRIPTION "Clocks out of sync between peers"

	::={connsyncPeerClockOutOfSync 3}

connsyncPeerClockOutOfSyncLevelTable OBJECT-TYPE
	SYNTAX      SEQUENCE OF ConnsyncPeerClockOutOfSyncLevelEntry
	MAX-ACCESS  not-accessible
	STATUS      current
	DESCRIPTION
	"Table for connsyncPeerClockOutOfSync"
	::={connsyncPeerClockOutOfSync 4}

connsyncPeerClockOutOfSyncLevelEntry OBJECT-TYPE
	SYNTAX      ConnsyncPeerClockOutOfSyncLevelEntry
	MAX-ACCESS  not-accessible
	STATUS      current
	DESCRIPTION
	"Table entry for connsyncPeerClockOutOfSync"
	INDEX { connsyncPeerClockOutOfSyncLevelName }
	::={connsyncPeerClockOutOfSyncLevelTable 1}

ConnsyncPeerClockOutOfSyncLevelEntry ::=
	SEQUENCE {
		connsyncPeerClockOutOfSyncLevelName	DisplayString,
		connsyncPeerClockOutOfSyncLevelVal	Counter64,
		connsyncPeerClockOutOfSyncLevelMom	CounterBasedGauge64,
		connsyncPeerClockOutOfSyncLevelMax	CounterBasedGauge64
	}

connsyncPeerClockOutOfSyncLevelName OBJECT-TYPE
	SYNTAX      DisplayString
	MAX-ACCESS  not-accessible
	STATUS      current
	DESCRIPTION
	"Table entry display string for connsyncPeerClockOutOfSync"
	::={connsyncPeerClockOutOfSyncLevelEntry 1}

connsyncPeerClockOutOfSyncLevelVal OBJECT-TYPE
	SYNTAX	 Counter64
	MAX-ACCESS  read-only
	STATUS      current
	DESCRIPTION
	"Table entry attribute for connsyncPeerClockOutOfSync"
	::={connsyncPeerClockOutOfSyncLevelEntry 2}

connsyncPeerClockOutOfSyncLevelMom OBJECT-TYPE
	SYNTAX	 CounterBasedGauge64
	MAX-ACCESS  read-only
	STATUS      current
	DESCRIPTION
	"Table entry attribute for connsyncPeerClockOutOfSync"
	::={connsyncPeerClockOutOfSyncLevelEntry 3}

connsyncPeerClockOutOfSyncLevelMax OBJECT-TYPE
	SYNTAX	 CounterBasedGauge64
	MAX-ACCESS  read-only
	STATUS      current
	DESCRIPTION
	"Table entry attribute for connsyncPeerClockOutOfSync"
	::={connsyncPeerClockOutOfSyncLevelEntry 4}


connsyncUdpPropReq	OBJECT IDENTIFIER ::={connsync 65}

connsyncUdpPropReqVal	OBJECT-TYPE
	SYNTAX	 Counter64
	MAX-ACCESS read-only
	STATUS current
	DESCRIPTION "UDP Property Sync requests"

	::={connsyncUdpPropReq 1}

connsyncUdpPropReqMom	OBJECT-TYPE
	SYNTAX	 CounterBasedGauge64
	MAX-ACCESS read-only
	STATUS current
	DESCRIPTION "UDP Property Sync requests"

	::={connsyncUdpPropReq 2}

connsyncUdpPropReqMax	OBJECT-TYPE
	SYNTAX	 CounterBasedGauge64
	MAX-ACCESS read-only
	STATUS current
	DESCRIPTION "UDP Property Sync requests"

	::={connsyncUdpPropReq 3}

connsyncUdpPropReqLevelTable OBJECT-TYPE
	SYNTAX      SEQUENCE OF ConnsyncUdpPropReqLevelEntry
	MAX-ACCESS  not-accessible
	STATUS      current
	DESCRIPTION
	"Table for connsyncUdpPropReq"
	::={connsyncUdpPropReq 4}

connsyncUdpPropReqLevelEntry OBJECT-TYPE
	SYNTAX      ConnsyncUdpPropReqLevelEntry
	MAX-ACCESS  not-accessible
	STATUS      current
	DESCRIPTION
	"Table entry for connsyncUdpPropReq"
	INDEX { connsyncUdpPropReqLevelName }
	::={connsyncUdpPropReqLevelTable 1}

ConnsyncUdpPropReqLevelEntry ::=
	SEQUENCE {
		connsyncUdpPropReqLevelName	DisplayString,
		connsyncUdpPropReqLevelVal	Counter64,
		connsyncUdpPropReqLevelMom	CounterBasedGauge64,
		connsyncUdpPropReqLevelMax	CounterBasedGauge64
	}

connsyncUdpPropReqLevelName OBJECT-TYPE
	SYNTAX      DisplayString
	MAX-ACCESS  not-accessible
	STATUS      current
	DESCRIPTION
	"Table entry display string for connsyncUdpPropReq"
	::={connsyncUdpPropReqLevelEntry 1}

connsyncUdpPropReqLevelVal OBJECT-TYPE
	SYNTAX	 Counter64
	MAX-ACCESS  read-only
	STATUS      current
	DESCRIPTION
	"Table entry attribute for connsyncUdpPropReq"
	::={connsyncUdpPropReqLevelEntry 2}

connsyncUdpPropReqLevelMom OBJECT-TYPE
	SYNTAX	 CounterBasedGauge64
	MAX-ACCESS  read-only
	STATUS      current
	DESCRIPTION
	"Table entry attribute for connsyncUdpPropReq"
	::={connsyncUdpPropReqLevelEntry 3}

connsyncUdpPropReqLevelMax OBJECT-TYPE
	SYNTAX	 CounterBasedGauge64
	MAX-ACCESS  read-only
	STATUS      current
	DESCRIPTION
	"Table entry attribute for connsyncUdpPropReq"
	::={connsyncUdpPropReqLevelEntry 4}


connsyncUdpPropResp	OBJECT IDENTIFIER ::={connsync 66}

connsyncUdpPropRespVal	OBJECT-TYPE
	SYNTAX	 Counter64
	MAX-ACCESS read-only
	STATUS current
	DESCRIPTION "UDP Property Sync responses"

	::={connsyncUdpPropResp 1}

connsyncUdpPropRespMom	OBJECT-TYPE
	SYNTAX	 CounterBasedGauge64
	MAX-ACCESS read-only
	STATUS current
	DESCRIPTION "UDP Property Sync responses"

	::={connsyncUdpPropResp 2}

connsyncUdpPropRespMax	OBJECT-TYPE
	SYNTAX	 CounterBasedGauge64
	MAX-ACCESS read-only
	STATUS current
	DESCRIPTION "UDP Property Sync responses"

	::={connsyncUdpPropResp 3}

connsyncUdpPropRespLevelTable OBJECT-TYPE
	SYNTAX      SEQUENCE OF ConnsyncUdpPropRespLevelEntry
	MAX-ACCESS  not-accessible
	STATUS      current
	DESCRIPTION
	"Table for connsyncUdpPropResp"
	::={connsyncUdpPropResp 4}

connsyncUdpPropRespLevelEntry OBJECT-TYPE
	SYNTAX      ConnsyncUdpPropRespLevelEntry
	MAX-ACCESS  not-accessible
	STATUS      current
	DESCRIPTION
	"Table entry for connsyncUdpPropResp"
	INDEX { connsyncUdpPropRespLevelName }
	::={connsyncUdpPropRespLevelTable 1}

ConnsyncUdpPropRespLevelEntry ::=
	SEQUENCE {
		connsyncUdpPropRespLevelName	DisplayString,
		connsyncUdpPropRespLevelVal	Counter64,
		connsyncUdpPropRespLevelMom	CounterBasedGauge64,
		connsyncUdpPropRespLevelMax	CounterBasedGauge64
	}

connsyncUdpPropRespLevelName OBJECT-TYPE
	SYNTAX      DisplayString
	MAX-ACCESS  not-accessible
	STATUS      current
	DESCRIPTION
	"Table entry display string for connsyncUdpPropResp"
	::={connsyncUdpPropRespLevelEntry 1}

connsyncUdpPropRespLevelVal OBJECT-TYPE
	SYNTAX	 Counter64
	MAX-ACCESS  read-only
	STATUS      current
	DESCRIPTION
	"Table entry attribute for connsyncUdpPropResp"
	::={connsyncUdpPropRespLevelEntry 2}

connsyncUdpPropRespLevelMom OBJECT-TYPE
	SYNTAX	 CounterBasedGauge64
	MAX-ACCESS  read-only
	STATUS      current
	DESCRIPTION
	"Table entry attribute for connsyncUdpPropResp"
	::={connsyncUdpPropRespLevelEntry 3}

connsyncUdpPropRespLevelMax OBJECT-TYPE
	SYNTAX	 CounterBasedGauge64
	MAX-ACCESS  read-only
	STATUS      current
	DESCRIPTION
	"Table entry attribute for connsyncUdpPropResp"
	::={connsyncUdpPropRespLevelEntry 4}


natsync	OBJECT IDENTIFIER ::={sysdiag 61}

natsyncCorruptPkt	OBJECT IDENTIFIER ::={natsync 1}

natsyncCorruptPktVal	OBJECT-TYPE
	SYNTAX	 Counter64
	MAX-ACCESS read-only
	STATUS current
	DESCRIPTION "Corrupt packet received"

	::={natsyncCorruptPkt 1}

natsyncCorruptPktMom	OBJECT-TYPE
	SYNTAX	 CounterBasedGauge64
	MAX-ACCESS read-only
	STATUS current
	DESCRIPTION "Corrupt packet received"

	::={natsyncCorruptPkt 2}

natsyncCorruptPktMax	OBJECT-TYPE
	SYNTAX	 CounterBasedGauge64
	MAX-ACCESS read-only
	STATUS current
	DESCRIPTION "Corrupt packet received"

	::={natsyncCorruptPkt 3}

natsyncCorruptPktLevelTable OBJECT-TYPE
	SYNTAX      SEQUENCE OF NatsyncCorruptPktLevelEntry
	MAX-ACCESS  not-accessible
	STATUS      current
	DESCRIPTION
	"Table for natsyncCorruptPkt"
	::={natsyncCorruptPkt 4}

natsyncCorruptPktLevelEntry OBJECT-TYPE
	SYNTAX      NatsyncCorruptPktLevelEntry
	MAX-ACCESS  not-accessible
	STATUS      current
	DESCRIPTION
	"Table entry for natsyncCorruptPkt"
	INDEX { natsyncCorruptPktLevelName }
	::={natsyncCorruptPktLevelTable 1}

NatsyncCorruptPktLevelEntry ::=
	SEQUENCE {
		natsyncCorruptPktLevelName	DisplayString,
		natsyncCorruptPktLevelVal	Counter64,
		natsyncCorruptPktLevelMom	CounterBasedGauge64,
		natsyncCorruptPktLevelMax	CounterBasedGauge64
	}

natsyncCorruptPktLevelName OBJECT-TYPE
	SYNTAX      DisplayString
	MAX-ACCESS  not-accessible
	STATUS      current
	DESCRIPTION
	"Table entry display string for natsyncCorruptPkt"
	::={natsyncCorruptPktLevelEntry 1}

natsyncCorruptPktLevelVal OBJECT-TYPE
	SYNTAX	 Counter64
	MAX-ACCESS  read-only
	STATUS      current
	DESCRIPTION
	"Table entry attribute for natsyncCorruptPkt"
	::={natsyncCorruptPktLevelEntry 2}

natsyncCorruptPktLevelMom OBJECT-TYPE
	SYNTAX	 CounterBasedGauge64
	MAX-ACCESS  read-only
	STATUS      current
	DESCRIPTION
	"Table entry attribute for natsyncCorruptPkt"
	::={natsyncCorruptPktLevelEntry 3}

natsyncCorruptPktLevelMax OBJECT-TYPE
	SYNTAX	 CounterBasedGauge64
	MAX-ACCESS  read-only
	STATUS      current
	DESCRIPTION
	"Table entry attribute for natsyncCorruptPkt"
	::={natsyncCorruptPktLevelEntry 4}


natsyncBadVer	OBJECT IDENTIFIER ::={natsync 2}

natsyncBadVerVal	OBJECT-TYPE
	SYNTAX	 Counter64
	MAX-ACCESS read-only
	STATUS current
	DESCRIPTION "Received natsync packets with incompatible version"

	::={natsyncBadVer 1}

natsyncBadVerMom	OBJECT-TYPE
	SYNTAX	 CounterBasedGauge64
	MAX-ACCESS read-only
	STATUS current
	DESCRIPTION "Received natsync packets with incompatible version"

	::={natsyncBadVer 2}

natsyncBadVerMax	OBJECT-TYPE
	SYNTAX	 CounterBasedGauge64
	MAX-ACCESS read-only
	STATUS current
	DESCRIPTION "Received natsync packets with incompatible version"

	::={natsyncBadVer 3}

natsyncBadVerLevelTable OBJECT-TYPE
	SYNTAX      SEQUENCE OF NatsyncBadVerLevelEntry
	MAX-ACCESS  not-accessible
	STATUS      current
	DESCRIPTION
	"Table for natsyncBadVer"
	::={natsyncBadVer 4}

natsyncBadVerLevelEntry OBJECT-TYPE
	SYNTAX      NatsyncBadVerLevelEntry
	MAX-ACCESS  not-accessible
	STATUS      current
	DESCRIPTION
	"Table entry for natsyncBadVer"
	INDEX { natsyncBadVerLevelName }
	::={natsyncBadVerLevelTable 1}

NatsyncBadVerLevelEntry ::=
	SEQUENCE {
		natsyncBadVerLevelName	DisplayString,
		natsyncBadVerLevelVal	Counter64,
		natsyncBadVerLevelMom	CounterBasedGauge64,
		natsyncBadVerLevelMax	CounterBasedGauge64
	}

natsyncBadVerLevelName OBJECT-TYPE
	SYNTAX      DisplayString
	MAX-ACCESS  not-accessible
	STATUS      current
	DESCRIPTION
	"Table entry display string for natsyncBadVer"
	::={natsyncBadVerLevelEntry 1}

natsyncBadVerLevelVal OBJECT-TYPE
	SYNTAX	 Counter64
	MAX-ACCESS  read-only
	STATUS      current
	DESCRIPTION
	"Table entry attribute for natsyncBadVer"
	::={natsyncBadVerLevelEntry 2}

natsyncBadVerLevelMom OBJECT-TYPE
	SYNTAX	 CounterBasedGauge64
	MAX-ACCESS  read-only
	STATUS      current
	DESCRIPTION
	"Table entry attribute for natsyncBadVer"
	::={natsyncBadVerLevelEntry 3}

natsyncBadVerLevelMax OBJECT-TYPE
	SYNTAX	 CounterBasedGauge64
	MAX-ACCESS  read-only
	STATUS      current
	DESCRIPTION
	"Table entry attribute for natsyncBadVer"
	::={natsyncBadVerLevelEntry 4}


natsyncBadID	OBJECT IDENTIFIER ::={natsync 3}

natsyncBadIDVal	OBJECT-TYPE
	SYNTAX	 Counter64
	MAX-ACCESS read-only
	STATUS current
	DESCRIPTION "Received natsync packets from myself."

	::={natsyncBadID 1}

natsyncBadIDMom	OBJECT-TYPE
	SYNTAX	 CounterBasedGauge64
	MAX-ACCESS read-only
	STATUS current
	DESCRIPTION "Received natsync packets from myself."

	::={natsyncBadID 2}

natsyncBadIDMax	OBJECT-TYPE
	SYNTAX	 CounterBasedGauge64
	MAX-ACCESS read-only
	STATUS current
	DESCRIPTION "Received natsync packets from myself."

	::={natsyncBadID 3}

natsyncBadIDLevelTable OBJECT-TYPE
	SYNTAX      SEQUENCE OF NatsyncBadIDLevelEntry
	MAX-ACCESS  not-accessible
	STATUS      current
	DESCRIPTION
	"Table for natsyncBadID"
	::={natsyncBadID 4}

natsyncBadIDLevelEntry OBJECT-TYPE
	SYNTAX      NatsyncBadIDLevelEntry
	MAX-ACCESS  not-accessible
	STATUS      current
	DESCRIPTION
	"Table entry for natsyncBadID"
	INDEX { natsyncBadIDLevelName }
	::={natsyncBadIDLevelTable 1}

NatsyncBadIDLevelEntry ::=
	SEQUENCE {
		natsyncBadIDLevelName	DisplayString,
		natsyncBadIDLevelVal	Counter64,
		natsyncBadIDLevelMom	CounterBasedGauge64,
		natsyncBadIDLevelMax	CounterBasedGauge64
	}

natsyncBadIDLevelName OBJECT-TYPE
	SYNTAX      DisplayString
	MAX-ACCESS  not-accessible
	STATUS      current
	DESCRIPTION
	"Table entry display string for natsyncBadID"
	::={natsyncBadIDLevelEntry 1}

natsyncBadIDLevelVal OBJECT-TYPE
	SYNTAX	 Counter64
	MAX-ACCESS  read-only
	STATUS      current
	DESCRIPTION
	"Table entry attribute for natsyncBadID"
	::={natsyncBadIDLevelEntry 2}

natsyncBadIDLevelMom OBJECT-TYPE
	SYNTAX	 CounterBasedGauge64
	MAX-ACCESS  read-only
	STATUS      current
	DESCRIPTION
	"Table entry attribute for natsyncBadID"
	::={natsyncBadIDLevelEntry 3}

natsyncBadIDLevelMax OBJECT-TYPE
	SYNTAX	 CounterBasedGauge64
	MAX-ACCESS  read-only
	STATUS      current
	DESCRIPTION
	"Table entry attribute for natsyncBadID"
	::={natsyncBadIDLevelEntry 4}


natsyncMessageNotSent	OBJECT IDENTIFIER ::={natsync 4}

natsyncMessageNotSentVal	OBJECT-TYPE
	SYNTAX	 Counter64
	MAX-ACCESS read-only
	STATUS current
	DESCRIPTION "Natsync message over connsync not sent"

	::={natsyncMessageNotSent 1}

natsyncMessageNotSentMom	OBJECT-TYPE
	SYNTAX	 CounterBasedGauge64
	MAX-ACCESS read-only
	STATUS current
	DESCRIPTION "Natsync message over connsync not sent"

	::={natsyncMessageNotSent 2}

natsyncMessageNotSentMax	OBJECT-TYPE
	SYNTAX	 CounterBasedGauge64
	MAX-ACCESS read-only
	STATUS current
	DESCRIPTION "Natsync message over connsync not sent"

	::={natsyncMessageNotSent 3}

natsyncMessageNotSentLevelTable OBJECT-TYPE
	SYNTAX      SEQUENCE OF NatsyncMessageNotSentLevelEntry
	MAX-ACCESS  not-accessible
	STATUS      current
	DESCRIPTION
	"Table for natsyncMessageNotSent"
	::={natsyncMessageNotSent 4}

natsyncMessageNotSentLevelEntry OBJECT-TYPE
	SYNTAX      NatsyncMessageNotSentLevelEntry
	MAX-ACCESS  not-accessible
	STATUS      current
	DESCRIPTION
	"Table entry for natsyncMessageNotSent"
	INDEX { natsyncMessageNotSentLevelName }
	::={natsyncMessageNotSentLevelTable 1}

NatsyncMessageNotSentLevelEntry ::=
	SEQUENCE {
		natsyncMessageNotSentLevelName	DisplayString,
		natsyncMessageNotSentLevelVal	Counter64,
		natsyncMessageNotSentLevelMom	CounterBasedGauge64,
		natsyncMessageNotSentLevelMax	CounterBasedGauge64
	}

natsyncMessageNotSentLevelName OBJECT-TYPE
	SYNTAX      DisplayString
	MAX-ACCESS  not-accessible
	STATUS      current
	DESCRIPTION
	"Table entry display string for natsyncMessageNotSent"
	::={natsyncMessageNotSentLevelEntry 1}

natsyncMessageNotSentLevelVal OBJECT-TYPE
	SYNTAX	 Counter64
	MAX-ACCESS  read-only
	STATUS      current
	DESCRIPTION
	"Table entry attribute for natsyncMessageNotSent"
	::={natsyncMessageNotSentLevelEntry 2}

natsyncMessageNotSentLevelMom OBJECT-TYPE
	SYNTAX	 CounterBasedGauge64
	MAX-ACCESS  read-only
	STATUS      current
	DESCRIPTION
	"Table entry attribute for natsyncMessageNotSent"
	::={natsyncMessageNotSentLevelEntry 3}

natsyncMessageNotSentLevelMax OBJECT-TYPE
	SYNTAX	 CounterBasedGauge64
	MAX-ACCESS  read-only
	STATUS      current
	DESCRIPTION
	"Table entry attribute for natsyncMessageNotSent"
	::={natsyncMessageNotSentLevelEntry 4}


natsyncSyncMessageSent	OBJECT IDENTIFIER ::={natsync 5}

natsyncSyncMessageSentVal	OBJECT-TYPE
	SYNTAX	 Counter64
	MAX-ACCESS read-only
	STATUS current
	DESCRIPTION "Natsync sync messages sent to natsync peers"

	::={natsyncSyncMessageSent 1}

natsyncSyncMessageSentMom	OBJECT-TYPE
	SYNTAX	 CounterBasedGauge64
	MAX-ACCESS read-only
	STATUS current
	DESCRIPTION "Natsync sync messages sent to natsync peers"

	::={natsyncSyncMessageSent 2}

natsyncSyncMessageSentMax	OBJECT-TYPE
	SYNTAX	 CounterBasedGauge64
	MAX-ACCESS read-only
	STATUS current
	DESCRIPTION "Natsync sync messages sent to natsync peers"

	::={natsyncSyncMessageSent 3}

natsyncSyncMessageSentLevelTable OBJECT-TYPE
	SYNTAX      SEQUENCE OF NatsyncSyncMessageSentLevelEntry
	MAX-ACCESS  not-accessible
	STATUS      current
	DESCRIPTION
	"Table for natsyncSyncMessageSent"
	::={natsyncSyncMessageSent 4}

natsyncSyncMessageSentLevelEntry OBJECT-TYPE
	SYNTAX      NatsyncSyncMessageSentLevelEntry
	MAX-ACCESS  not-accessible
	STATUS      current
	DESCRIPTION
	"Table entry for natsyncSyncMessageSent"
	INDEX { natsyncSyncMessageSentLevelName }
	::={natsyncSyncMessageSentLevelTable 1}

NatsyncSyncMessageSentLevelEntry ::=
	SEQUENCE {
		natsyncSyncMessageSentLevelName	DisplayString,
		natsyncSyncMessageSentLevelVal	Counter64,
		natsyncSyncMessageSentLevelMom	CounterBasedGauge64,
		natsyncSyncMessageSentLevelMax	CounterBasedGauge64
	}

natsyncSyncMessageSentLevelName OBJECT-TYPE
	SYNTAX      DisplayString
	MAX-ACCESS  not-accessible
	STATUS      current
	DESCRIPTION
	"Table entry display string for natsyncSyncMessageSent"
	::={natsyncSyncMessageSentLevelEntry 1}

natsyncSyncMessageSentLevelVal OBJECT-TYPE
	SYNTAX	 Counter64
	MAX-ACCESS  read-only
	STATUS      current
	DESCRIPTION
	"Table entry attribute for natsyncSyncMessageSent"
	::={natsyncSyncMessageSentLevelEntry 2}

natsyncSyncMessageSentLevelMom OBJECT-TYPE
	SYNTAX	 CounterBasedGauge64
	MAX-ACCESS  read-only
	STATUS      current
	DESCRIPTION
	"Table entry attribute for natsyncSyncMessageSent"
	::={natsyncSyncMessageSentLevelEntry 3}

natsyncSyncMessageSentLevelMax OBJECT-TYPE
	SYNTAX	 CounterBasedGauge64
	MAX-ACCESS  read-only
	STATUS      current
	DESCRIPTION
	"Table entry attribute for natsyncSyncMessageSent"
	::={natsyncSyncMessageSentLevelEntry 4}


natsyncRemoveMessageSent	OBJECT IDENTIFIER ::={natsync 6}

natsyncRemoveMessageSentVal	OBJECT-TYPE
	SYNTAX	 Counter64
	MAX-ACCESS read-only
	STATUS current
	DESCRIPTION "Natsync remove messages sent to natsync peers"

	::={natsyncRemoveMessageSent 1}

natsyncRemoveMessageSentMom	OBJECT-TYPE
	SYNTAX	 CounterBasedGauge64
	MAX-ACCESS read-only
	STATUS current
	DESCRIPTION "Natsync remove messages sent to natsync peers"

	::={natsyncRemoveMessageSent 2}

natsyncRemoveMessageSentMax	OBJECT-TYPE
	SYNTAX	 CounterBasedGauge64
	MAX-ACCESS read-only
	STATUS current
	DESCRIPTION "Natsync remove messages sent to natsync peers"

	::={natsyncRemoveMessageSent 3}

natsyncRemoveMessageSentLevelTable OBJECT-TYPE
	SYNTAX      SEQUENCE OF NatsyncRemoveMessageSentLevelEntry
	MAX-ACCESS  not-accessible
	STATUS      current
	DESCRIPTION
	"Table for natsyncRemoveMessageSent"
	::={natsyncRemoveMessageSent 4}

natsyncRemoveMessageSentLevelEntry OBJECT-TYPE
	SYNTAX      NatsyncRemoveMessageSentLevelEntry
	MAX-ACCESS  not-accessible
	STATUS      current
	DESCRIPTION
	"Table entry for natsyncRemoveMessageSent"
	INDEX { natsyncRemoveMessageSentLevelName }
	::={natsyncRemoveMessageSentLevelTable 1}

NatsyncRemoveMessageSentLevelEntry ::=
	SEQUENCE {
		natsyncRemoveMessageSentLevelName	DisplayString,
		natsyncRemoveMessageSentLevelVal	Counter64,
		natsyncRemoveMessageSentLevelMom	CounterBasedGauge64,
		natsyncRemoveMessageSentLevelMax	CounterBasedGauge64
	}

natsyncRemoveMessageSentLevelName OBJECT-TYPE
	SYNTAX      DisplayString
	MAX-ACCESS  not-accessible
	STATUS      current
	DESCRIPTION
	"Table entry display string for natsyncRemoveMessageSent"
	::={natsyncRemoveMessageSentLevelEntry 1}

natsyncRemoveMessageSentLevelVal OBJECT-TYPE
	SYNTAX	 Counter64
	MAX-ACCESS  read-only
	STATUS      current
	DESCRIPTION
	"Table entry attribute for natsyncRemoveMessageSent"
	::={natsyncRemoveMessageSentLevelEntry 2}

natsyncRemoveMessageSentLevelMom OBJECT-TYPE
	SYNTAX	 CounterBasedGauge64
	MAX-ACCESS  read-only
	STATUS      current
	DESCRIPTION
	"Table entry attribute for natsyncRemoveMessageSent"
	::={natsyncRemoveMessageSentLevelEntry 3}

natsyncRemoveMessageSentLevelMax OBJECT-TYPE
	SYNTAX	 CounterBasedGauge64
	MAX-ACCESS  read-only
	STATUS      current
	DESCRIPTION
	"Table entry attribute for natsyncRemoveMessageSent"
	::={natsyncRemoveMessageSentLevelEntry 4}


natsyncSyncMessageReceived	OBJECT IDENTIFIER ::={natsync 7}

natsyncSyncMessageReceivedVal	OBJECT-TYPE
	SYNTAX	 Counter64
	MAX-ACCESS read-only
	STATUS current
	DESCRIPTION "Natsync sync messages received from other natsync peers"

	::={natsyncSyncMessageReceived 1}

natsyncSyncMessageReceivedMom	OBJECT-TYPE
	SYNTAX	 CounterBasedGauge64
	MAX-ACCESS read-only
	STATUS current
	DESCRIPTION "Natsync sync messages received from other natsync peers"

	::={natsyncSyncMessageReceived 2}

natsyncSyncMessageReceivedMax	OBJECT-TYPE
	SYNTAX	 CounterBasedGauge64
	MAX-ACCESS read-only
	STATUS current
	DESCRIPTION "Natsync sync messages received from other natsync peers"

	::={natsyncSyncMessageReceived 3}

natsyncSyncMessageReceivedLevelTable OBJECT-TYPE
	SYNTAX      SEQUENCE OF NatsyncSyncMessageReceivedLevelEntry
	MAX-ACCESS  not-accessible
	STATUS      current
	DESCRIPTION
	"Table for natsyncSyncMessageReceived"
	::={natsyncSyncMessageReceived 4}

natsyncSyncMessageReceivedLevelEntry OBJECT-TYPE
	SYNTAX      NatsyncSyncMessageReceivedLevelEntry
	MAX-ACCESS  not-accessible
	STATUS      current
	DESCRIPTION
	"Table entry for natsyncSyncMessageReceived"
	INDEX { natsyncSyncMessageReceivedLevelName }
	::={natsyncSyncMessageReceivedLevelTable 1}

NatsyncSyncMessageReceivedLevelEntry ::=
	SEQUENCE {
		natsyncSyncMessageReceivedLevelName	DisplayString,
		natsyncSyncMessageReceivedLevelVal	Counter64,
		natsyncSyncMessageReceivedLevelMom	CounterBasedGauge64,
		natsyncSyncMessageReceivedLevelMax	CounterBasedGauge64
	}

natsyncSyncMessageReceivedLevelName OBJECT-TYPE
	SYNTAX      DisplayString
	MAX-ACCESS  not-accessible
	STATUS      current
	DESCRIPTION
	"Table entry display string for natsyncSyncMessageReceived"
	::={natsyncSyncMessageReceivedLevelEntry 1}

natsyncSyncMessageReceivedLevelVal OBJECT-TYPE
	SYNTAX	 Counter64
	MAX-ACCESS  read-only
	STATUS      current
	DESCRIPTION
	"Table entry attribute for natsyncSyncMessageReceived"
	::={natsyncSyncMessageReceivedLevelEntry 2}

natsyncSyncMessageReceivedLevelMom OBJECT-TYPE
	SYNTAX	 CounterBasedGauge64
	MAX-ACCESS  read-only
	STATUS      current
	DESCRIPTION
	"Table entry attribute for natsyncSyncMessageReceived"
	::={natsyncSyncMessageReceivedLevelEntry 3}

natsyncSyncMessageReceivedLevelMax OBJECT-TYPE
	SYNTAX	 CounterBasedGauge64
	MAX-ACCESS  read-only
	STATUS      current
	DESCRIPTION
	"Table entry attribute for natsyncSyncMessageReceived"
	::={natsyncSyncMessageReceivedLevelEntry 4}


natsyncRemoveMessageReceived	OBJECT IDENTIFIER ::={natsync 8}

natsyncRemoveMessageReceivedVal	OBJECT-TYPE
	SYNTAX	 Counter64
	MAX-ACCESS read-only
	STATUS current
	DESCRIPTION "Natsync remove messages received from other natsync peers"

	::={natsyncRemoveMessageReceived 1}

natsyncRemoveMessageReceivedMom	OBJECT-TYPE
	SYNTAX	 CounterBasedGauge64
	MAX-ACCESS read-only
	STATUS current
	DESCRIPTION "Natsync remove messages received from other natsync peers"

	::={natsyncRemoveMessageReceived 2}

natsyncRemoveMessageReceivedMax	OBJECT-TYPE
	SYNTAX	 CounterBasedGauge64
	MAX-ACCESS read-only
	STATUS current
	DESCRIPTION "Natsync remove messages received from other natsync peers"

	::={natsyncRemoveMessageReceived 3}

natsyncRemoveMessageReceivedLevelTable OBJECT-TYPE
	SYNTAX      SEQUENCE OF NatsyncRemoveMessageReceivedLevelEntry
	MAX-ACCESS  not-accessible
	STATUS      current
	DESCRIPTION
	"Table for natsyncRemoveMessageReceived"
	::={natsyncRemoveMessageReceived 4}

natsyncRemoveMessageReceivedLevelEntry OBJECT-TYPE
	SYNTAX      NatsyncRemoveMessageReceivedLevelEntry
	MAX-ACCESS  not-accessible
	STATUS      current
	DESCRIPTION
	"Table entry for natsyncRemoveMessageReceived"
	INDEX { natsyncRemoveMessageReceivedLevelName }
	::={natsyncRemoveMessageReceivedLevelTable 1}

NatsyncRemoveMessageReceivedLevelEntry ::=
	SEQUENCE {
		natsyncRemoveMessageReceivedLevelName	DisplayString,
		natsyncRemoveMessageReceivedLevelVal	Counter64,
		natsyncRemoveMessageReceivedLevelMom	CounterBasedGauge64,
		natsyncRemoveMessageReceivedLevelMax	CounterBasedGauge64
	}

natsyncRemoveMessageReceivedLevelName OBJECT-TYPE
	SYNTAX      DisplayString
	MAX-ACCESS  not-accessible
	STATUS      current
	DESCRIPTION
	"Table entry display string for natsyncRemoveMessageReceived"
	::={natsyncRemoveMessageReceivedLevelEntry 1}

natsyncRemoveMessageReceivedLevelVal OBJECT-TYPE
	SYNTAX	 Counter64
	MAX-ACCESS  read-only
	STATUS      current
	DESCRIPTION
	"Table entry attribute for natsyncRemoveMessageReceived"
	::={natsyncRemoveMessageReceivedLevelEntry 2}

natsyncRemoveMessageReceivedLevelMom OBJECT-TYPE
	SYNTAX	 CounterBasedGauge64
	MAX-ACCESS  read-only
	STATUS      current
	DESCRIPTION
	"Table entry attribute for natsyncRemoveMessageReceived"
	::={natsyncRemoveMessageReceivedLevelEntry 3}

natsyncRemoveMessageReceivedLevelMax OBJECT-TYPE
	SYNTAX	 CounterBasedGauge64
	MAX-ACCESS  read-only
	STATUS      current
	DESCRIPTION
	"Table entry attribute for natsyncRemoveMessageReceived"
	::={natsyncRemoveMessageReceivedLevelEntry 4}


natsyncChksumMismatch	OBJECT IDENTIFIER ::={natsync 9}

natsyncChksumMismatchVal	OBJECT-TYPE
	SYNTAX	 Counter64
	MAX-ACCESS read-only
	STATUS current
	DESCRIPTION "Checksum mismatch in received sync"

	::={natsyncChksumMismatch 1}

natsyncChksumMismatchMom	OBJECT-TYPE
	SYNTAX	 CounterBasedGauge64
	MAX-ACCESS read-only
	STATUS current
	DESCRIPTION "Checksum mismatch in received sync"

	::={natsyncChksumMismatch 2}

natsyncChksumMismatchMax	OBJECT-TYPE
	SYNTAX	 CounterBasedGauge64
	MAX-ACCESS read-only
	STATUS current
	DESCRIPTION "Checksum mismatch in received sync"

	::={natsyncChksumMismatch 3}

natsyncChksumMismatchLevelTable OBJECT-TYPE
	SYNTAX      SEQUENCE OF NatsyncChksumMismatchLevelEntry
	MAX-ACCESS  not-accessible
	STATUS      current
	DESCRIPTION
	"Table for natsyncChksumMismatch"
	::={natsyncChksumMismatch 4}

natsyncChksumMismatchLevelEntry OBJECT-TYPE
	SYNTAX      NatsyncChksumMismatchLevelEntry
	MAX-ACCESS  not-accessible
	STATUS      current
	DESCRIPTION
	"Table entry for natsyncChksumMismatch"
	INDEX { natsyncChksumMismatchLevelName }
	::={natsyncChksumMismatchLevelTable 1}

NatsyncChksumMismatchLevelEntry ::=
	SEQUENCE {
		natsyncChksumMismatchLevelName	DisplayString,
		natsyncChksumMismatchLevelVal	Counter64,
		natsyncChksumMismatchLevelMom	CounterBasedGauge64,
		natsyncChksumMismatchLevelMax	CounterBasedGauge64
	}

natsyncChksumMismatchLevelName OBJECT-TYPE
	SYNTAX      DisplayString
	MAX-ACCESS  not-accessible
	STATUS      current
	DESCRIPTION
	"Table entry display string for natsyncChksumMismatch"
	::={natsyncChksumMismatchLevelEntry 1}

natsyncChksumMismatchLevelVal OBJECT-TYPE
	SYNTAX	 Counter64
	MAX-ACCESS  read-only
	STATUS      current
	DESCRIPTION
	"Table entry attribute for natsyncChksumMismatch"
	::={natsyncChksumMismatchLevelEntry 2}

natsyncChksumMismatchLevelMom OBJECT-TYPE
	SYNTAX	 CounterBasedGauge64
	MAX-ACCESS  read-only
	STATUS      current
	DESCRIPTION
	"Table entry attribute for natsyncChksumMismatch"
	::={natsyncChksumMismatchLevelEntry 3}

natsyncChksumMismatchLevelMax OBJECT-TYPE
	SYNTAX	 CounterBasedGauge64
	MAX-ACCESS  read-only
	STATUS      current
	DESCRIPTION
	"Table entry attribute for natsyncChksumMismatch"
	::={natsyncChksumMismatchLevelEntry 4}


ruleset	OBJECT IDENTIFIER ::={sysdiag 64}

rulesetReceived	OBJECT IDENTIFIER ::={ruleset 1}

rulesetReceivedVal	OBJECT-TYPE
	SYNTAX	 Counter64
	MAX-ACCESS read-only
	STATUS obsolete
	DESCRIPTION "RX packets"

	::={rulesetReceived 1}

rulesetReceivedMom	OBJECT-TYPE
	SYNTAX	 CounterBasedGauge64
	MAX-ACCESS read-only
	STATUS obsolete
	DESCRIPTION "RX packets"

	::={rulesetReceived 2}

rulesetReceivedMax	OBJECT-TYPE
	SYNTAX	 CounterBasedGauge64
	MAX-ACCESS read-only
	STATUS obsolete
	DESCRIPTION "RX packets"

	::={rulesetReceived 3}

rulesetReceivedLevelTable OBJECT-TYPE
	SYNTAX      SEQUENCE OF RulesetReceivedLevelEntry
	MAX-ACCESS  not-accessible
	STATUS      current
	DESCRIPTION
	"Table for rulesetReceived"
	::={rulesetReceived 4}

rulesetReceivedLevelEntry OBJECT-TYPE
	SYNTAX      RulesetReceivedLevelEntry
	MAX-ACCESS  not-accessible
	STATUS      current
	DESCRIPTION
	"Table entry for rulesetReceived"
	INDEX { rulesetReceivedLevelName }
	::={rulesetReceivedLevelTable 1}

RulesetReceivedLevelEntry ::=
	SEQUENCE {
		rulesetReceivedLevelName	DisplayString,
		rulesetReceivedLevelVal	Counter64,
		rulesetReceivedLevelMom	CounterBasedGauge64,
		rulesetReceivedLevelMax	CounterBasedGauge64
	}

rulesetReceivedLevelName OBJECT-TYPE
	SYNTAX      DisplayString
	MAX-ACCESS  not-accessible
	STATUS      current
	DESCRIPTION
	"Table entry display string for rulesetReceived"
	::={rulesetReceivedLevelEntry 1}

rulesetReceivedLevelVal OBJECT-TYPE
	SYNTAX	 Counter64
	MAX-ACCESS  read-only
	STATUS      current
	DESCRIPTION
	"Table entry attribute for rulesetReceived"
	::={rulesetReceivedLevelEntry 2}

rulesetReceivedLevelMom OBJECT-TYPE
	SYNTAX	 CounterBasedGauge64
	MAX-ACCESS  read-only
	STATUS      current
	DESCRIPTION
	"Table entry attribute for rulesetReceived"
	::={rulesetReceivedLevelEntry 3}

rulesetReceivedLevelMax OBJECT-TYPE
	SYNTAX	 CounterBasedGauge64
	MAX-ACCESS  read-only
	STATUS      current
	DESCRIPTION
	"Table entry attribute for rulesetReceived"
	::={rulesetReceivedLevelEntry 4}


rulesetFwrules	OBJECT IDENTIFIER ::={ruleset 5}

rulesetFwrulesVal	OBJECT-TYPE
	SYNTAX	 CounterBasedGauge64
	MAX-ACCESS read-only
	STATUS current
	DESCRIPTION "Ruleset: 1 FW rules loaded"

	::={rulesetFwrules 1}

rulesetFwrulesMax	OBJECT-TYPE
	SYNTAX	 CounterBasedGauge64
	MAX-ACCESS read-only
	STATUS current
	DESCRIPTION "Ruleset: 1 FW rules loaded"

	::={rulesetFwrules 3}

rulesetFwrulesLevelTable OBJECT-TYPE
	SYNTAX      SEQUENCE OF RulesetFwrulesLevelEntry
	MAX-ACCESS  not-accessible
	STATUS      current
	DESCRIPTION
	"Table for rulesetFwrules"
	::={rulesetFwrules 4}

rulesetFwrulesLevelEntry OBJECT-TYPE
	SYNTAX      RulesetFwrulesLevelEntry
	MAX-ACCESS  not-accessible
	STATUS      current
	DESCRIPTION
	"Table entry for rulesetFwrules"
	INDEX { rulesetFwrulesLevelName }
	::={rulesetFwrulesLevelTable 1}

RulesetFwrulesLevelEntry ::=
	SEQUENCE {
		rulesetFwrulesLevelName	DisplayString,
		rulesetFwrulesLevelVal	CounterBasedGauge64,
		rulesetFwrulesLevelMax	CounterBasedGauge64
	}

rulesetFwrulesLevelName OBJECT-TYPE
	SYNTAX      DisplayString
	MAX-ACCESS  not-accessible
	STATUS      current
	DESCRIPTION
	"Table entry display string for rulesetFwrules"
	::={rulesetFwrulesLevelEntry 1}

rulesetFwrulesLevelVal OBJECT-TYPE
	SYNTAX	 CounterBasedGauge64
	MAX-ACCESS  read-only
	STATUS      current
	DESCRIPTION
	"Table entry attribute for rulesetFwrules"
	::={rulesetFwrulesLevelEntry 2}

rulesetFwrulesLevelMax OBJECT-TYPE
	SYNTAX	 CounterBasedGauge64
	MAX-ACCESS  read-only
	STATUS      current
	DESCRIPTION
	"Table entry attribute for rulesetFwrules"
	::={rulesetFwrulesLevelEntry 4}


rulesetShapingrules	OBJECT IDENTIFIER ::={ruleset 6}

rulesetShapingrulesVal	OBJECT-TYPE
	SYNTAX	 CounterBasedGauge64
	MAX-ACCESS read-only
	STATUS current
	DESCRIPTION "Ruleset: 2 Shaping rules loaded"

	::={rulesetShapingrules 1}

rulesetShapingrulesMax	OBJECT-TYPE
	SYNTAX	 CounterBasedGauge64
	MAX-ACCESS read-only
	STATUS current
	DESCRIPTION "Ruleset: 2 Shaping rules loaded"

	::={rulesetShapingrules 3}

rulesetShapingrulesLevelTable OBJECT-TYPE
	SYNTAX      SEQUENCE OF RulesetShapingrulesLevelEntry
	MAX-ACCESS  not-accessible
	STATUS      current
	DESCRIPTION
	"Table for rulesetShapingrules"
	::={rulesetShapingrules 4}

rulesetShapingrulesLevelEntry OBJECT-TYPE
	SYNTAX      RulesetShapingrulesLevelEntry
	MAX-ACCESS  not-accessible
	STATUS      current
	DESCRIPTION
	"Table entry for rulesetShapingrules"
	INDEX { rulesetShapingrulesLevelName }
	::={rulesetShapingrulesLevelTable 1}

RulesetShapingrulesLevelEntry ::=
	SEQUENCE {
		rulesetShapingrulesLevelName	DisplayString,
		rulesetShapingrulesLevelVal	CounterBasedGauge64,
		rulesetShapingrulesLevelMax	CounterBasedGauge64
	}

rulesetShapingrulesLevelName OBJECT-TYPE
	SYNTAX      DisplayString
	MAX-ACCESS  not-accessible
	STATUS      current
	DESCRIPTION
	"Table entry display string for rulesetShapingrules"
	::={rulesetShapingrulesLevelEntry 1}

rulesetShapingrulesLevelVal OBJECT-TYPE
	SYNTAX	 CounterBasedGauge64
	MAX-ACCESS  read-only
	STATUS      current
	DESCRIPTION
	"Table entry attribute for rulesetShapingrules"
	::={rulesetShapingrulesLevelEntry 2}

rulesetShapingrulesLevelMax OBJECT-TYPE
	SYNTAX	 CounterBasedGauge64
	MAX-ACCESS  read-only
	STATUS      current
	DESCRIPTION
	"Table entry attribute for rulesetShapingrules"
	::={rulesetShapingrulesLevelEntry 4}


rulesetStatisticsrules	OBJECT IDENTIFIER ::={ruleset 24}

rulesetStatisticsrulesVal	OBJECT-TYPE
	SYNTAX	 CounterBasedGauge64
	MAX-ACCESS read-only
	STATUS current
	DESCRIPTION "Ruleset: 3 Statistics rules loaded"

	::={rulesetStatisticsrules 1}

rulesetStatisticsrulesMax	OBJECT-TYPE
	SYNTAX	 CounterBasedGauge64
	MAX-ACCESS read-only
	STATUS current
	DESCRIPTION "Ruleset: 3 Statistics rules loaded"

	::={rulesetStatisticsrules 3}

rulesetStatisticsrulesLevelTable OBJECT-TYPE
	SYNTAX      SEQUENCE OF RulesetStatisticsrulesLevelEntry
	MAX-ACCESS  not-accessible
	STATUS      current
	DESCRIPTION
	"Table for rulesetStatisticsrules"
	::={rulesetStatisticsrules 4}

rulesetStatisticsrulesLevelEntry OBJECT-TYPE
	SYNTAX      RulesetStatisticsrulesLevelEntry
	MAX-ACCESS  not-accessible
	STATUS      current
	DESCRIPTION
	"Table entry for rulesetStatisticsrules"
	INDEX { rulesetStatisticsrulesLevelName }
	::={rulesetStatisticsrulesLevelTable 1}

RulesetStatisticsrulesLevelEntry ::=
	SEQUENCE {
		rulesetStatisticsrulesLevelName	DisplayString,
		rulesetStatisticsrulesLevelVal	CounterBasedGauge64,
		rulesetStatisticsrulesLevelMax	CounterBasedGauge64
	}

rulesetStatisticsrulesLevelName OBJECT-TYPE
	SYNTAX      DisplayString
	MAX-ACCESS  not-accessible
	STATUS      current
	DESCRIPTION
	"Table entry display string for rulesetStatisticsrules"
	::={rulesetStatisticsrulesLevelEntry 1}

rulesetStatisticsrulesLevelVal OBJECT-TYPE
	SYNTAX	 CounterBasedGauge64
	MAX-ACCESS  read-only
	STATUS      current
	DESCRIPTION
	"Table entry attribute for rulesetStatisticsrules"
	::={rulesetStatisticsrulesLevelEntry 2}

rulesetStatisticsrulesLevelMax OBJECT-TYPE
	SYNTAX	 CounterBasedGauge64
	MAX-ACCESS  read-only
	STATUS      current
	DESCRIPTION
	"Table entry attribute for rulesetStatisticsrules"
	::={rulesetStatisticsrulesLevelEntry 4}


rulesetLastUpdate	OBJECT IDENTIFIER ::={ruleset 22}

rulesetLastUpdateVal	OBJECT-TYPE
	SYNTAX	 DateAndTime
	MAX-ACCESS read-only
	STATUS current
	DESCRIPTION "Ruleset: Current ruleset loaded"

	::={rulesetLastUpdate 1}

rulesetLastUpdateLevelTable OBJECT-TYPE
	SYNTAX      SEQUENCE OF RulesetLastUpdateLevelEntry
	MAX-ACCESS  not-accessible
	STATUS      current
	DESCRIPTION
	"Table for rulesetLastUpdate"
	::={rulesetLastUpdate 2}

rulesetLastUpdateLevelEntry OBJECT-TYPE
	SYNTAX      RulesetLastUpdateLevelEntry
	MAX-ACCESS  not-accessible
	STATUS      current
	DESCRIPTION
	"Table entry for rulesetLastUpdate"
	INDEX { rulesetLastUpdateLevelName }
	::={rulesetLastUpdateLevelTable 1}

RulesetLastUpdateLevelEntry ::=
	SEQUENCE {
		rulesetLastUpdateLevelName	DisplayString,
		rulesetLastUpdateLevelVal	DateAndTime
	}

rulesetLastUpdateLevelName OBJECT-TYPE
	SYNTAX      DisplayString
	MAX-ACCESS  not-accessible
	STATUS      current
	DESCRIPTION
	"Table entry display string for rulesetLastUpdate"
	::={rulesetLastUpdateLevelEntry 1}

rulesetLastUpdateLevelVal OBJECT-TYPE
	SYNTAX	 DateAndTime
	MAX-ACCESS  read-only
	STATUS      current
	DESCRIPTION
	"Table entry attribute for rulesetLastUpdate"
	::={rulesetLastUpdateLevelEntry 2}


rulesetStatisticsRuleOverflow	OBJECT IDENTIFIER ::={ruleset 26}

rulesetStatisticsRuleOverflowVal	OBJECT-TYPE
	SYNTAX	 Counter64
	MAX-ACCESS read-only
	STATUS current
	DESCRIPTION "Ruleset problem: Too many matching statistics rules"

	::={rulesetStatisticsRuleOverflow 1}

rulesetStatisticsRuleOverflowMom	OBJECT-TYPE
	SYNTAX	 CounterBasedGauge64
	MAX-ACCESS read-only
	STATUS current
	DESCRIPTION "Ruleset problem: Too many matching statistics rules"

	::={rulesetStatisticsRuleOverflow 2}

rulesetStatisticsRuleOverflowMax	OBJECT-TYPE
	SYNTAX	 CounterBasedGauge64
	MAX-ACCESS read-only
	STATUS current
	DESCRIPTION "Ruleset problem: Too many matching statistics rules"

	::={rulesetStatisticsRuleOverflow 3}

rulesetStatisticsRuleOverflowLevelTable OBJECT-TYPE
	SYNTAX      SEQUENCE OF RulesetStatisticsRuleOverflowLevelEntry
	MAX-ACCESS  not-accessible
	STATUS      current
	DESCRIPTION
	"Table for rulesetStatisticsRuleOverflow"
	::={rulesetStatisticsRuleOverflow 4}

rulesetStatisticsRuleOverflowLevelEntry OBJECT-TYPE
	SYNTAX      RulesetStatisticsRuleOverflowLevelEntry
	MAX-ACCESS  not-accessible
	STATUS      current
	DESCRIPTION
	"Table entry for rulesetStatisticsRuleOverflow"
	INDEX { rulesetStatisticsRuleOverflowLevelName }
	::={rulesetStatisticsRuleOverflowLevelTable 1}

RulesetStatisticsRuleOverflowLevelEntry ::=
	SEQUENCE {
		rulesetStatisticsRuleOverflowLevelName	DisplayString,
		rulesetStatisticsRuleOverflowLevelVal	Counter64,
		rulesetStatisticsRuleOverflowLevelMom	CounterBasedGauge64,
		rulesetStatisticsRuleOverflowLevelMax	CounterBasedGauge64
	}

rulesetStatisticsRuleOverflowLevelName OBJECT-TYPE
	SYNTAX      DisplayString
	MAX-ACCESS  not-accessible
	STATUS      current
	DESCRIPTION
	"Table entry display string for rulesetStatisticsRuleOverflow"
	::={rulesetStatisticsRuleOverflowLevelEntry 1}

rulesetStatisticsRuleOverflowLevelVal OBJECT-TYPE
	SYNTAX	 Counter64
	MAX-ACCESS  read-only
	STATUS      current
	DESCRIPTION
	"Table entry attribute for rulesetStatisticsRuleOverflow"
	::={rulesetStatisticsRuleOverflowLevelEntry 2}

rulesetStatisticsRuleOverflowLevelMom OBJECT-TYPE
	SYNTAX	 CounterBasedGauge64
	MAX-ACCESS  read-only
	STATUS      current
	DESCRIPTION
	"Table entry attribute for rulesetStatisticsRuleOverflow"
	::={rulesetStatisticsRuleOverflowLevelEntry 3}

rulesetStatisticsRuleOverflowLevelMax OBJECT-TYPE
	SYNTAX	 CounterBasedGauge64
	MAX-ACCESS  read-only
	STATUS      current
	DESCRIPTION
	"Table entry attribute for rulesetStatisticsRuleOverflow"
	::={rulesetStatisticsRuleOverflowLevelEntry 4}


rulesetClienttreeSize	OBJECT IDENTIFIER ::={ruleset 7}

rulesetClienttreeSizeVal	OBJECT-TYPE
	SYNTAX	 CounterBasedGauge64
	MAX-ACCESS read-only
	STATUS obsolete
	DESCRIPTION "Nodes in Client IP-tree"

	::={rulesetClienttreeSize 1}

rulesetClienttreeSizeMax	OBJECT-TYPE
	SYNTAX	 CounterBasedGauge64
	MAX-ACCESS read-only
	STATUS obsolete
	DESCRIPTION "Nodes in Client IP-tree"

	::={rulesetClienttreeSize 3}

rulesetClienttreeSizeLevelTable OBJECT-TYPE
	SYNTAX      SEQUENCE OF RulesetClienttreeSizeLevelEntry
	MAX-ACCESS  not-accessible
	STATUS      current
	DESCRIPTION
	"Table for rulesetClienttreeSize"
	::={rulesetClienttreeSize 4}

rulesetClienttreeSizeLevelEntry OBJECT-TYPE
	SYNTAX      RulesetClienttreeSizeLevelEntry
	MAX-ACCESS  not-accessible
	STATUS      current
	DESCRIPTION
	"Table entry for rulesetClienttreeSize"
	INDEX { rulesetClienttreeSizeLevelName }
	::={rulesetClienttreeSizeLevelTable 1}

RulesetClienttreeSizeLevelEntry ::=
	SEQUENCE {
		rulesetClienttreeSizeLevelName	DisplayString,
		rulesetClienttreeSizeLevelVal	CounterBasedGauge64,
		rulesetClienttreeSizeLevelMax	CounterBasedGauge64
	}

rulesetClienttreeSizeLevelName OBJECT-TYPE
	SYNTAX      DisplayString
	MAX-ACCESS  not-accessible
	STATUS      current
	DESCRIPTION
	"Table entry display string for rulesetClienttreeSize"
	::={rulesetClienttreeSizeLevelEntry 1}

rulesetClienttreeSizeLevelVal OBJECT-TYPE
	SYNTAX	 CounterBasedGauge64
	MAX-ACCESS  read-only
	STATUS      current
	DESCRIPTION
	"Table entry attribute for rulesetClienttreeSize"
	::={rulesetClienttreeSizeLevelEntry 2}

rulesetClienttreeSizeLevelMax OBJECT-TYPE
	SYNTAX	 CounterBasedGauge64
	MAX-ACCESS  read-only
	STATUS      current
	DESCRIPTION
	"Table entry attribute for rulesetClienttreeSize"
	::={rulesetClienttreeSizeLevelEntry 4}


rulesetServertreeSize	OBJECT IDENTIFIER ::={ruleset 8}

rulesetServertreeSizeVal	OBJECT-TYPE
	SYNTAX	 CounterBasedGauge64
	MAX-ACCESS read-only
	STATUS obsolete
	DESCRIPTION "Nodes in Server IP-tree"

	::={rulesetServertreeSize 1}

rulesetServertreeSizeMax	OBJECT-TYPE
	SYNTAX	 CounterBasedGauge64
	MAX-ACCESS read-only
	STATUS obsolete
	DESCRIPTION "Nodes in Server IP-tree"

	::={rulesetServertreeSize 3}

rulesetServertreeSizeLevelTable OBJECT-TYPE
	SYNTAX      SEQUENCE OF RulesetServertreeSizeLevelEntry
	MAX-ACCESS  not-accessible
	STATUS      current
	DESCRIPTION
	"Table for rulesetServertreeSize"
	::={rulesetServertreeSize 4}

rulesetServertreeSizeLevelEntry OBJECT-TYPE
	SYNTAX      RulesetServertreeSizeLevelEntry
	MAX-ACCESS  not-accessible
	STATUS      current
	DESCRIPTION
	"Table entry for rulesetServertreeSize"
	INDEX { rulesetServertreeSizeLevelName }
	::={rulesetServertreeSizeLevelTable 1}

RulesetServertreeSizeLevelEntry ::=
	SEQUENCE {
		rulesetServertreeSizeLevelName	DisplayString,
		rulesetServertreeSizeLevelVal	CounterBasedGauge64,
		rulesetServertreeSizeLevelMax	CounterBasedGauge64
	}

rulesetServertreeSizeLevelName OBJECT-TYPE
	SYNTAX      DisplayString
	MAX-ACCESS  not-accessible
	STATUS      current
	DESCRIPTION
	"Table entry display string for rulesetServertreeSize"
	::={rulesetServertreeSizeLevelEntry 1}

rulesetServertreeSizeLevelVal OBJECT-TYPE
	SYNTAX	 CounterBasedGauge64
	MAX-ACCESS  read-only
	STATUS      current
	DESCRIPTION
	"Table entry attribute for rulesetServertreeSize"
	::={rulesetServertreeSizeLevelEntry 2}

rulesetServertreeSizeLevelMax OBJECT-TYPE
	SYNTAX	 CounterBasedGauge64
	MAX-ACCESS  read-only
	STATUS      current
	DESCRIPTION
	"Table entry attribute for rulesetServertreeSize"
	::={rulesetServertreeSizeLevelEntry 4}


rulesetPropChecks	OBJECT IDENTIFIER ::={ruleset 13}

rulesetPropChecksVal	OBJECT-TYPE
	SYNTAX	 Counter64
	MAX-ACCESS read-only
	STATUS obsolete
	DESCRIPTION "Property checks"

	::={rulesetPropChecks 1}

rulesetPropChecksMom	OBJECT-TYPE
	SYNTAX	 CounterBasedGauge64
	MAX-ACCESS read-only
	STATUS obsolete
	DESCRIPTION "Property checks"

	::={rulesetPropChecks 2}

rulesetPropChecksMax	OBJECT-TYPE
	SYNTAX	 CounterBasedGauge64
	MAX-ACCESS read-only
	STATUS obsolete
	DESCRIPTION "Property checks"

	::={rulesetPropChecks 3}

rulesetPropChecksLevelTable OBJECT-TYPE
	SYNTAX      SEQUENCE OF RulesetPropChecksLevelEntry
	MAX-ACCESS  not-accessible
	STATUS      current
	DESCRIPTION
	"Table for rulesetPropChecks"
	::={rulesetPropChecks 4}

rulesetPropChecksLevelEntry OBJECT-TYPE
	SYNTAX      RulesetPropChecksLevelEntry
	MAX-ACCESS  not-accessible
	STATUS      current
	DESCRIPTION
	"Table entry for rulesetPropChecks"
	INDEX { rulesetPropChecksLevelName }
	::={rulesetPropChecksLevelTable 1}

RulesetPropChecksLevelEntry ::=
	SEQUENCE {
		rulesetPropChecksLevelName	DisplayString,
		rulesetPropChecksLevelVal	Counter64,
		rulesetPropChecksLevelMom	CounterBasedGauge64,
		rulesetPropChecksLevelMax	CounterBasedGauge64
	}

rulesetPropChecksLevelName OBJECT-TYPE
	SYNTAX      DisplayString
	MAX-ACCESS  not-accessible
	STATUS      current
	DESCRIPTION
	"Table entry display string for rulesetPropChecks"
	::={rulesetPropChecksLevelEntry 1}

rulesetPropChecksLevelVal OBJECT-TYPE
	SYNTAX	 Counter64
	MAX-ACCESS  read-only
	STATUS      current
	DESCRIPTION
	"Table entry attribute for rulesetPropChecks"
	::={rulesetPropChecksLevelEntry 2}

rulesetPropChecksLevelMom OBJECT-TYPE
	SYNTAX	 CounterBasedGauge64
	MAX-ACCESS  read-only
	STATUS      current
	DESCRIPTION
	"Table entry attribute for rulesetPropChecks"
	::={rulesetPropChecksLevelEntry 3}

rulesetPropChecksLevelMax OBJECT-TYPE
	SYNTAX	 CounterBasedGauge64
	MAX-ACCESS  read-only
	STATUS      current
	DESCRIPTION
	"Table entry attribute for rulesetPropChecks"
	::={rulesetPropChecksLevelEntry 4}


rulesetLocaltreeSize	OBJECT IDENTIFIER ::={ruleset 25}

rulesetLocaltreeSizeVal	OBJECT-TYPE
	SYNTAX	 CounterBasedGauge64
	MAX-ACCESS read-only
	STATUS obsolete
	DESCRIPTION "Nodes in Local IP-tree"

	::={rulesetLocaltreeSize 1}

rulesetLocaltreeSizeMax	OBJECT-TYPE
	SYNTAX	 CounterBasedGauge64
	MAX-ACCESS read-only
	STATUS obsolete
	DESCRIPTION "Nodes in Local IP-tree"

	::={rulesetLocaltreeSize 3}

rulesetLocaltreeSizeLevelTable OBJECT-TYPE
	SYNTAX      SEQUENCE OF RulesetLocaltreeSizeLevelEntry
	MAX-ACCESS  not-accessible
	STATUS      current
	DESCRIPTION
	"Table for rulesetLocaltreeSize"
	::={rulesetLocaltreeSize 4}

rulesetLocaltreeSizeLevelEntry OBJECT-TYPE
	SYNTAX      RulesetLocaltreeSizeLevelEntry
	MAX-ACCESS  not-accessible
	STATUS      current
	DESCRIPTION
	"Table entry for rulesetLocaltreeSize"
	INDEX { rulesetLocaltreeSizeLevelName }
	::={rulesetLocaltreeSizeLevelTable 1}

RulesetLocaltreeSizeLevelEntry ::=
	SEQUENCE {
		rulesetLocaltreeSizeLevelName	DisplayString,
		rulesetLocaltreeSizeLevelVal	CounterBasedGauge64,
		rulesetLocaltreeSizeLevelMax	CounterBasedGauge64
	}

rulesetLocaltreeSizeLevelName OBJECT-TYPE
	SYNTAX      DisplayString
	MAX-ACCESS  not-accessible
	STATUS      current
	DESCRIPTION
	"Table entry display string for rulesetLocaltreeSize"
	::={rulesetLocaltreeSizeLevelEntry 1}

rulesetLocaltreeSizeLevelVal OBJECT-TYPE
	SYNTAX	 CounterBasedGauge64
	MAX-ACCESS  read-only
	STATUS      current
	DESCRIPTION
	"Table entry attribute for rulesetLocaltreeSize"
	::={rulesetLocaltreeSizeLevelEntry 2}

rulesetLocaltreeSizeLevelMax OBJECT-TYPE
	SYNTAX	 CounterBasedGauge64
	MAX-ACCESS  read-only
	STATUS      current
	DESCRIPTION
	"Table entry attribute for rulesetLocaltreeSize"
	::={rulesetLocaltreeSizeLevelEntry 4}


rulesetBgpNumpaths	OBJECT IDENTIFIER ::={ruleset 9}

rulesetBgpNumpathsVal	OBJECT-TYPE
	SYNTAX	 CounterBasedGauge64
	MAX-ACCESS read-only
	STATUS current
	DESCRIPTION "BGP: Number of ASPaths"

	::={rulesetBgpNumpaths 1}

rulesetBgpNumpathsMax	OBJECT-TYPE
	SYNTAX	 CounterBasedGauge64
	MAX-ACCESS read-only
	STATUS current
	DESCRIPTION "BGP: Number of ASPaths"

	::={rulesetBgpNumpaths 3}

rulesetBgpNumpathsLevelTable OBJECT-TYPE
	SYNTAX      SEQUENCE OF RulesetBgpNumpathsLevelEntry
	MAX-ACCESS  not-accessible
	STATUS      current
	DESCRIPTION
	"Table for rulesetBgpNumpaths"
	::={rulesetBgpNumpaths 4}

rulesetBgpNumpathsLevelEntry OBJECT-TYPE
	SYNTAX      RulesetBgpNumpathsLevelEntry
	MAX-ACCESS  not-accessible
	STATUS      current
	DESCRIPTION
	"Table entry for rulesetBgpNumpaths"
	INDEX { rulesetBgpNumpathsLevelName }
	::={rulesetBgpNumpathsLevelTable 1}

RulesetBgpNumpathsLevelEntry ::=
	SEQUENCE {
		rulesetBgpNumpathsLevelName	DisplayString,
		rulesetBgpNumpathsLevelVal	CounterBasedGauge64,
		rulesetBgpNumpathsLevelMax	CounterBasedGauge64
	}

rulesetBgpNumpathsLevelName OBJECT-TYPE
	SYNTAX      DisplayString
	MAX-ACCESS  not-accessible
	STATUS      current
	DESCRIPTION
	"Table entry display string for rulesetBgpNumpaths"
	::={rulesetBgpNumpathsLevelEntry 1}

rulesetBgpNumpathsLevelVal OBJECT-TYPE
	SYNTAX	 CounterBasedGauge64
	MAX-ACCESS  read-only
	STATUS      current
	DESCRIPTION
	"Table entry attribute for rulesetBgpNumpaths"
	::={rulesetBgpNumpathsLevelEntry 2}

rulesetBgpNumpathsLevelMax OBJECT-TYPE
	SYNTAX	 CounterBasedGauge64
	MAX-ACCESS  read-only
	STATUS      current
	DESCRIPTION
	"Table entry attribute for rulesetBgpNumpaths"
	::={rulesetBgpNumpathsLevelEntry 4}


rulesetBgpBitmasks	OBJECT IDENTIFIER ::={ruleset 65}

rulesetBgpBitmasksVal	OBJECT-TYPE
	SYNTAX	 CounterBasedGauge64
	MAX-ACCESS read-only
	STATUS current
	DESCRIPTION "BGP: Number of bitmasks"

	::={rulesetBgpBitmasks 1}

rulesetBgpBitmasksMax	OBJECT-TYPE
	SYNTAX	 CounterBasedGauge64
	MAX-ACCESS read-only
	STATUS current
	DESCRIPTION "BGP: Number of bitmasks"

	::={rulesetBgpBitmasks 3}

rulesetBgpBitmasksLevelTable OBJECT-TYPE
	SYNTAX      SEQUENCE OF RulesetBgpBitmasksLevelEntry
	MAX-ACCESS  not-accessible
	STATUS      current
	DESCRIPTION
	"Table for rulesetBgpBitmasks"
	::={rulesetBgpBitmasks 4}

rulesetBgpBitmasksLevelEntry OBJECT-TYPE
	SYNTAX      RulesetBgpBitmasksLevelEntry
	MAX-ACCESS  not-accessible
	STATUS      current
	DESCRIPTION
	"Table entry for rulesetBgpBitmasks"
	INDEX { rulesetBgpBitmasksLevelName }
	::={rulesetBgpBitmasksLevelTable 1}

RulesetBgpBitmasksLevelEntry ::=
	SEQUENCE {
		rulesetBgpBitmasksLevelName	DisplayString,
		rulesetBgpBitmasksLevelVal	CounterBasedGauge64,
		rulesetBgpBitmasksLevelMax	CounterBasedGauge64
	}

rulesetBgpBitmasksLevelName OBJECT-TYPE
	SYNTAX      DisplayString
	MAX-ACCESS  not-accessible
	STATUS      current
	DESCRIPTION
	"Table entry display string for rulesetBgpBitmasks"
	::={rulesetBgpBitmasksLevelEntry 1}

rulesetBgpBitmasksLevelVal OBJECT-TYPE
	SYNTAX	 CounterBasedGauge64
	MAX-ACCESS  read-only
	STATUS      current
	DESCRIPTION
	"Table entry attribute for rulesetBgpBitmasks"
	::={rulesetBgpBitmasksLevelEntry 2}

rulesetBgpBitmasksLevelMax OBJECT-TYPE
	SYNTAX	 CounterBasedGauge64
	MAX-ACCESS  read-only
	STATUS      current
	DESCRIPTION
	"Table entry attribute for rulesetBgpBitmasks"
	::={rulesetBgpBitmasksLevelEntry 4}


rulesetBgpLoaded	OBJECT IDENTIFIER ::={ruleset 66}

rulesetBgpLoadedVal	OBJECT-TYPE
	SYNTAX	 DateAndTime
	MAX-ACCESS read-only
	STATUS current
	DESCRIPTION "BGP: Current BGP-ruleset loaded"

	::={rulesetBgpLoaded 1}

rulesetBgpLoadedLevelTable OBJECT-TYPE
	SYNTAX      SEQUENCE OF RulesetBgpLoadedLevelEntry
	MAX-ACCESS  not-accessible
	STATUS      current
	DESCRIPTION
	"Table for rulesetBgpLoaded"
	::={rulesetBgpLoaded 2}

rulesetBgpLoadedLevelEntry OBJECT-TYPE
	SYNTAX      RulesetBgpLoadedLevelEntry
	MAX-ACCESS  not-accessible
	STATUS      current
	DESCRIPTION
	"Table entry for rulesetBgpLoaded"
	INDEX { rulesetBgpLoadedLevelName }
	::={rulesetBgpLoadedLevelTable 1}

RulesetBgpLoadedLevelEntry ::=
	SEQUENCE {
		rulesetBgpLoadedLevelName	DisplayString,
		rulesetBgpLoadedLevelVal	DateAndTime
	}

rulesetBgpLoadedLevelName OBJECT-TYPE
	SYNTAX      DisplayString
	MAX-ACCESS  not-accessible
	STATUS      current
	DESCRIPTION
	"Table entry display string for rulesetBgpLoaded"
	::={rulesetBgpLoadedLevelEntry 1}

rulesetBgpLoadedLevelVal OBJECT-TYPE
	SYNTAX	 DateAndTime
	MAX-ACCESS  read-only
	STATUS      current
	DESCRIPTION
	"Table entry attribute for rulesetBgpLoaded"
	::={rulesetBgpLoadedLevelEntry 2}


rulesetBgpIpv4Size	OBJECT IDENTIFIER ::={ruleset 10}

rulesetBgpIpv4SizeVal	OBJECT-TYPE
	SYNTAX	 CounterBasedGauge64
	MAX-ACCESS read-only
	STATUS current
	DESCRIPTION "BGP: Entries in BGP IPv4 lookup table"

	::={rulesetBgpIpv4Size 1}

rulesetBgpIpv4SizeMax	OBJECT-TYPE
	SYNTAX	 CounterBasedGauge64
	MAX-ACCESS read-only
	STATUS current
	DESCRIPTION "BGP: Entries in BGP IPv4 lookup table"

	::={rulesetBgpIpv4Size 3}

rulesetBgpIpv4SizeLevelTable OBJECT-TYPE
	SYNTAX      SEQUENCE OF RulesetBgpIpv4SizeLevelEntry
	MAX-ACCESS  not-accessible
	STATUS      current
	DESCRIPTION
	"Table for rulesetBgpIpv4Size"
	::={rulesetBgpIpv4Size 4}

rulesetBgpIpv4SizeLevelEntry OBJECT-TYPE
	SYNTAX      RulesetBgpIpv4SizeLevelEntry
	MAX-ACCESS  not-accessible
	STATUS      current
	DESCRIPTION
	"Table entry for rulesetBgpIpv4Size"
	INDEX { rulesetBgpIpv4SizeLevelName }
	::={rulesetBgpIpv4SizeLevelTable 1}

RulesetBgpIpv4SizeLevelEntry ::=
	SEQUENCE {
		rulesetBgpIpv4SizeLevelName	DisplayString,
		rulesetBgpIpv4SizeLevelVal	CounterBasedGauge64,
		rulesetBgpIpv4SizeLevelMax	CounterBasedGauge64
	}

rulesetBgpIpv4SizeLevelName OBJECT-TYPE
	SYNTAX      DisplayString
	MAX-ACCESS  not-accessible
	STATUS      current
	DESCRIPTION
	"Table entry display string for rulesetBgpIpv4Size"
	::={rulesetBgpIpv4SizeLevelEntry 1}

rulesetBgpIpv4SizeLevelVal OBJECT-TYPE
	SYNTAX	 CounterBasedGauge64
	MAX-ACCESS  read-only
	STATUS      current
	DESCRIPTION
	"Table entry attribute for rulesetBgpIpv4Size"
	::={rulesetBgpIpv4SizeLevelEntry 2}

rulesetBgpIpv4SizeLevelMax OBJECT-TYPE
	SYNTAX	 CounterBasedGauge64
	MAX-ACCESS  read-only
	STATUS      current
	DESCRIPTION
	"Table entry attribute for rulesetBgpIpv4Size"
	::={rulesetBgpIpv4SizeLevelEntry 4}


rulesetBgpIpv6Size	OBJECT IDENTIFIER ::={ruleset 53}

rulesetBgpIpv6SizeVal	OBJECT-TYPE
	SYNTAX	 CounterBasedGauge64
	MAX-ACCESS read-only
	STATUS current
	DESCRIPTION "BGP: Entries in BGP IPv6 lookup table"

	::={rulesetBgpIpv6Size 1}

rulesetBgpIpv6SizeMax	OBJECT-TYPE
	SYNTAX	 CounterBasedGauge64
	MAX-ACCESS read-only
	STATUS current
	DESCRIPTION "BGP: Entries in BGP IPv6 lookup table"

	::={rulesetBgpIpv6Size 3}

rulesetBgpIpv6SizeLevelTable OBJECT-TYPE
	SYNTAX      SEQUENCE OF RulesetBgpIpv6SizeLevelEntry
	MAX-ACCESS  not-accessible
	STATUS      current
	DESCRIPTION
	"Table for rulesetBgpIpv6Size"
	::={rulesetBgpIpv6Size 4}

rulesetBgpIpv6SizeLevelEntry OBJECT-TYPE
	SYNTAX      RulesetBgpIpv6SizeLevelEntry
	MAX-ACCESS  not-accessible
	STATUS      current
	DESCRIPTION
	"Table entry for rulesetBgpIpv6Size"
	INDEX { rulesetBgpIpv6SizeLevelName }
	::={rulesetBgpIpv6SizeLevelTable 1}

RulesetBgpIpv6SizeLevelEntry ::=
	SEQUENCE {
		rulesetBgpIpv6SizeLevelName	DisplayString,
		rulesetBgpIpv6SizeLevelVal	CounterBasedGauge64,
		rulesetBgpIpv6SizeLevelMax	CounterBasedGauge64
	}

rulesetBgpIpv6SizeLevelName OBJECT-TYPE
	SYNTAX      DisplayString
	MAX-ACCESS  not-accessible
	STATUS      current
	DESCRIPTION
	"Table entry display string for rulesetBgpIpv6Size"
	::={rulesetBgpIpv6SizeLevelEntry 1}

rulesetBgpIpv6SizeLevelVal OBJECT-TYPE
	SYNTAX	 CounterBasedGauge64
	MAX-ACCESS  read-only
	STATUS      current
	DESCRIPTION
	"Table entry attribute for rulesetBgpIpv6Size"
	::={rulesetBgpIpv6SizeLevelEntry 2}

rulesetBgpIpv6SizeLevelMax OBJECT-TYPE
	SYNTAX	 CounterBasedGauge64
	MAX-ACCESS  read-only
	STATUS      current
	DESCRIPTION
	"Table entry attribute for rulesetBgpIpv6Size"
	::={rulesetBgpIpv6SizeLevelEntry 4}


rulesetBgpNumLookup	OBJECT IDENTIFIER ::={ruleset 12}

rulesetBgpNumLookupVal	OBJECT-TYPE
	SYNTAX	 Counter64
	MAX-ACCESS read-only
	STATUS current
	DESCRIPTION "BGP: Path lookups"

	::={rulesetBgpNumLookup 1}

rulesetBgpNumLookupMom	OBJECT-TYPE
	SYNTAX	 CounterBasedGauge64
	MAX-ACCESS read-only
	STATUS current
	DESCRIPTION "BGP: Path lookups"

	::={rulesetBgpNumLookup 2}

rulesetBgpNumLookupMax	OBJECT-TYPE
	SYNTAX	 CounterBasedGauge64
	MAX-ACCESS read-only
	STATUS current
	DESCRIPTION "BGP: Path lookups"

	::={rulesetBgpNumLookup 3}

rulesetBgpNumLookupLevelTable OBJECT-TYPE
	SYNTAX      SEQUENCE OF RulesetBgpNumLookupLevelEntry
	MAX-ACCESS  not-accessible
	STATUS      current
	DESCRIPTION
	"Table for rulesetBgpNumLookup"
	::={rulesetBgpNumLookup 4}

rulesetBgpNumLookupLevelEntry OBJECT-TYPE
	SYNTAX      RulesetBgpNumLookupLevelEntry
	MAX-ACCESS  not-accessible
	STATUS      current
	DESCRIPTION
	"Table entry for rulesetBgpNumLookup"
	INDEX { rulesetBgpNumLookupLevelName }
	::={rulesetBgpNumLookupLevelTable 1}

RulesetBgpNumLookupLevelEntry ::=
	SEQUENCE {
		rulesetBgpNumLookupLevelName	DisplayString,
		rulesetBgpNumLookupLevelVal	Counter64,
		rulesetBgpNumLookupLevelMom	CounterBasedGauge64,
		rulesetBgpNumLookupLevelMax	CounterBasedGauge64
	}

rulesetBgpNumLookupLevelName OBJECT-TYPE
	SYNTAX      DisplayString
	MAX-ACCESS  not-accessible
	STATUS      current
	DESCRIPTION
	"Table entry display string for rulesetBgpNumLookup"
	::={rulesetBgpNumLookupLevelEntry 1}

rulesetBgpNumLookupLevelVal OBJECT-TYPE
	SYNTAX	 Counter64
	MAX-ACCESS  read-only
	STATUS      current
	DESCRIPTION
	"Table entry attribute for rulesetBgpNumLookup"
	::={rulesetBgpNumLookupLevelEntry 2}

rulesetBgpNumLookupLevelMom OBJECT-TYPE
	SYNTAX	 CounterBasedGauge64
	MAX-ACCESS  read-only
	STATUS      current
	DESCRIPTION
	"Table entry attribute for rulesetBgpNumLookup"
	::={rulesetBgpNumLookupLevelEntry 3}

rulesetBgpNumLookupLevelMax OBJECT-TYPE
	SYNTAX	 CounterBasedGauge64
	MAX-ACCESS  read-only
	STATUS      current
	DESCRIPTION
	"Table entry attribute for rulesetBgpNumLookup"
	::={rulesetBgpNumLookupLevelEntry 4}


rulesetBadAspath	OBJECT IDENTIFIER ::={ruleset 38}

rulesetBadAspathVal	OBJECT-TYPE
	SYNTAX	 Counter64
	MAX-ACCESS read-only
	STATUS obsolete
	DESCRIPTION "Old or corrupted AS-path entry"

	::={rulesetBadAspath 1}

rulesetBadAspathMom	OBJECT-TYPE
	SYNTAX	 CounterBasedGauge64
	MAX-ACCESS read-only
	STATUS obsolete
	DESCRIPTION "Old or corrupted AS-path entry"

	::={rulesetBadAspath 2}

rulesetBadAspathMax	OBJECT-TYPE
	SYNTAX	 CounterBasedGauge64
	MAX-ACCESS read-only
	STATUS obsolete
	DESCRIPTION "Old or corrupted AS-path entry"

	::={rulesetBadAspath 3}

rulesetBadAspathLevelTable OBJECT-TYPE
	SYNTAX      SEQUENCE OF RulesetBadAspathLevelEntry
	MAX-ACCESS  not-accessible
	STATUS      current
	DESCRIPTION
	"Table for rulesetBadAspath"
	::={rulesetBadAspath 4}

rulesetBadAspathLevelEntry OBJECT-TYPE
	SYNTAX      RulesetBadAspathLevelEntry
	MAX-ACCESS  not-accessible
	STATUS      current
	DESCRIPTION
	"Table entry for rulesetBadAspath"
	INDEX { rulesetBadAspathLevelName }
	::={rulesetBadAspathLevelTable 1}

RulesetBadAspathLevelEntry ::=
	SEQUENCE {
		rulesetBadAspathLevelName	DisplayString,
		rulesetBadAspathLevelVal	Counter64,
		rulesetBadAspathLevelMom	CounterBasedGauge64,
		rulesetBadAspathLevelMax	CounterBasedGauge64
	}

rulesetBadAspathLevelName OBJECT-TYPE
	SYNTAX      DisplayString
	MAX-ACCESS  not-accessible
	STATUS      current
	DESCRIPTION
	"Table entry display string for rulesetBadAspath"
	::={rulesetBadAspathLevelEntry 1}

rulesetBadAspathLevelVal OBJECT-TYPE
	SYNTAX	 Counter64
	MAX-ACCESS  read-only
	STATUS      current
	DESCRIPTION
	"Table entry attribute for rulesetBadAspath"
	::={rulesetBadAspathLevelEntry 2}

rulesetBadAspathLevelMom OBJECT-TYPE
	SYNTAX	 CounterBasedGauge64
	MAX-ACCESS  read-only
	STATUS      current
	DESCRIPTION
	"Table entry attribute for rulesetBadAspath"
	::={rulesetBadAspathLevelEntry 3}

rulesetBadAspathLevelMax OBJECT-TYPE
	SYNTAX	 CounterBasedGauge64
	MAX-ACCESS  read-only
	STATUS      current
	DESCRIPTION
	"Table entry attribute for rulesetBadAspath"
	::={rulesetBadAspathLevelEntry 4}


rulesetNetobjectPrefixesIPv4	OBJECT IDENTIFIER ::={ruleset 23}

rulesetNetobjectPrefixesIPv4Val	OBJECT-TYPE
	SYNTAX	 CounterBasedGauge64
	MAX-ACCESS read-only
	STATUS current
	DESCRIPTION "Netobject prefixes: Number of IPv4 prefixes"

	::={rulesetNetobjectPrefixesIPv4 1}

rulesetNetobjectPrefixesIPv4Max	OBJECT-TYPE
	SYNTAX	 CounterBasedGauge64
	MAX-ACCESS read-only
	STATUS current
	DESCRIPTION "Netobject prefixes: Number of IPv4 prefixes"

	::={rulesetNetobjectPrefixesIPv4 3}

rulesetNetobjectPrefixesIPv4LevelTable OBJECT-TYPE
	SYNTAX      SEQUENCE OF RulesetNetobjectPrefixesIPv4LevelEntry
	MAX-ACCESS  not-accessible
	STATUS      current
	DESCRIPTION
	"Table for rulesetNetobjectPrefixesIPv4"
	::={rulesetNetobjectPrefixesIPv4 4}

rulesetNetobjectPrefixesIPv4LevelEntry OBJECT-TYPE
	SYNTAX      RulesetNetobjectPrefixesIPv4LevelEntry
	MAX-ACCESS  not-accessible
	STATUS      current
	DESCRIPTION
	"Table entry for rulesetNetobjectPrefixesIPv4"
	INDEX { rulesetNetobjectPrefixesIPv4LevelName }
	::={rulesetNetobjectPrefixesIPv4LevelTable 1}

RulesetNetobjectPrefixesIPv4LevelEntry ::=
	SEQUENCE {
		rulesetNetobjectPrefixesIPv4LevelName	DisplayString,
		rulesetNetobjectPrefixesIPv4LevelVal	CounterBasedGauge64,
		rulesetNetobjectPrefixesIPv4LevelMax	CounterBasedGauge64
	}

rulesetNetobjectPrefixesIPv4LevelName OBJECT-TYPE
	SYNTAX      DisplayString
	MAX-ACCESS  not-accessible
	STATUS      current
	DESCRIPTION
	"Table entry display string for rulesetNetobjectPrefixesIPv4"
	::={rulesetNetobjectPrefixesIPv4LevelEntry 1}

rulesetNetobjectPrefixesIPv4LevelVal OBJECT-TYPE
	SYNTAX	 CounterBasedGauge64
	MAX-ACCESS  read-only
	STATUS      current
	DESCRIPTION
	"Table entry attribute for rulesetNetobjectPrefixesIPv4"
	::={rulesetNetobjectPrefixesIPv4LevelEntry 2}

rulesetNetobjectPrefixesIPv4LevelMax OBJECT-TYPE
	SYNTAX	 CounterBasedGauge64
	MAX-ACCESS  read-only
	STATUS      current
	DESCRIPTION
	"Table entry attribute for rulesetNetobjectPrefixesIPv4"
	::={rulesetNetobjectPrefixesIPv4LevelEntry 4}


rulesetNetobjectPrefixesIPv6	OBJECT IDENTIFIER ::={ruleset 61}

rulesetNetobjectPrefixesIPv6Val	OBJECT-TYPE
	SYNTAX	 CounterBasedGauge64
	MAX-ACCESS read-only
	STATUS current
	DESCRIPTION "Netobject prefixes: Number of IPv6 prefixes"

	::={rulesetNetobjectPrefixesIPv6 1}

rulesetNetobjectPrefixesIPv6Max	OBJECT-TYPE
	SYNTAX	 CounterBasedGauge64
	MAX-ACCESS read-only
	STATUS current
	DESCRIPTION "Netobject prefixes: Number of IPv6 prefixes"

	::={rulesetNetobjectPrefixesIPv6 3}

rulesetNetobjectPrefixesIPv6LevelTable OBJECT-TYPE
	SYNTAX      SEQUENCE OF RulesetNetobjectPrefixesIPv6LevelEntry
	MAX-ACCESS  not-accessible
	STATUS      current
	DESCRIPTION
	"Table for rulesetNetobjectPrefixesIPv6"
	::={rulesetNetobjectPrefixesIPv6 4}

rulesetNetobjectPrefixesIPv6LevelEntry OBJECT-TYPE
	SYNTAX      RulesetNetobjectPrefixesIPv6LevelEntry
	MAX-ACCESS  not-accessible
	STATUS      current
	DESCRIPTION
	"Table entry for rulesetNetobjectPrefixesIPv6"
	INDEX { rulesetNetobjectPrefixesIPv6LevelName }
	::={rulesetNetobjectPrefixesIPv6LevelTable 1}

RulesetNetobjectPrefixesIPv6LevelEntry ::=
	SEQUENCE {
		rulesetNetobjectPrefixesIPv6LevelName	DisplayString,
		rulesetNetobjectPrefixesIPv6LevelVal	CounterBasedGauge64,
		rulesetNetobjectPrefixesIPv6LevelMax	CounterBasedGauge64
	}

rulesetNetobjectPrefixesIPv6LevelName OBJECT-TYPE
	SYNTAX      DisplayString
	MAX-ACCESS  not-accessible
	STATUS      current
	DESCRIPTION
	"Table entry display string for rulesetNetobjectPrefixesIPv6"
	::={rulesetNetobjectPrefixesIPv6LevelEntry 1}

rulesetNetobjectPrefixesIPv6LevelVal OBJECT-TYPE
	SYNTAX	 CounterBasedGauge64
	MAX-ACCESS  read-only
	STATUS      current
	DESCRIPTION
	"Table entry attribute for rulesetNetobjectPrefixesIPv6"
	::={rulesetNetobjectPrefixesIPv6LevelEntry 2}

rulesetNetobjectPrefixesIPv6LevelMax OBJECT-TYPE
	SYNTAX	 CounterBasedGauge64
	MAX-ACCESS  read-only
	STATUS      current
	DESCRIPTION
	"Table entry attribute for rulesetNetobjectPrefixesIPv6"
	::={rulesetNetobjectPrefixesIPv6LevelEntry 4}


rulesetNetobjectPrefixesBitmasks	OBJECT IDENTIFIER ::={ruleset 62}

rulesetNetobjectPrefixesBitmasksVal	OBJECT-TYPE
	SYNTAX	 CounterBasedGauge64
	MAX-ACCESS read-only
	STATUS current
	DESCRIPTION "Netobject prefixes: Number of bitmasks"

	::={rulesetNetobjectPrefixesBitmasks 1}

rulesetNetobjectPrefixesBitmasksMax	OBJECT-TYPE
	SYNTAX	 CounterBasedGauge64
	MAX-ACCESS read-only
	STATUS current
	DESCRIPTION "Netobject prefixes: Number of bitmasks"

	::={rulesetNetobjectPrefixesBitmasks 3}

rulesetNetobjectPrefixesBitmasksLevelTable OBJECT-TYPE
	SYNTAX      SEQUENCE OF RulesetNetobjectPrefixesBitmasksLevelEntry
	MAX-ACCESS  not-accessible
	STATUS      current
	DESCRIPTION
	"Table for rulesetNetobjectPrefixesBitmasks"
	::={rulesetNetobjectPrefixesBitmasks 4}

rulesetNetobjectPrefixesBitmasksLevelEntry OBJECT-TYPE
	SYNTAX      RulesetNetobjectPrefixesBitmasksLevelEntry
	MAX-ACCESS  not-accessible
	STATUS      current
	DESCRIPTION
	"Table entry for rulesetNetobjectPrefixesBitmasks"
	INDEX { rulesetNetobjectPrefixesBitmasksLevelName }
	::={rulesetNetobjectPrefixesBitmasksLevelTable 1}

RulesetNetobjectPrefixesBitmasksLevelEntry ::=
	SEQUENCE {
		rulesetNetobjectPrefixesBitmasksLevelName	DisplayString,
		rulesetNetobjectPrefixesBitmasksLevelVal	CounterBasedGauge64,
		rulesetNetobjectPrefixesBitmasksLevelMax	CounterBasedGauge64
	}

rulesetNetobjectPrefixesBitmasksLevelName OBJECT-TYPE
	SYNTAX      DisplayString
	MAX-ACCESS  not-accessible
	STATUS      current
	DESCRIPTION
	"Table entry display string for rulesetNetobjectPrefixesBitmasks"
	::={rulesetNetobjectPrefixesBitmasksLevelEntry 1}

rulesetNetobjectPrefixesBitmasksLevelVal OBJECT-TYPE
	SYNTAX	 CounterBasedGauge64
	MAX-ACCESS  read-only
	STATUS      current
	DESCRIPTION
	"Table entry attribute for rulesetNetobjectPrefixesBitmasks"
	::={rulesetNetobjectPrefixesBitmasksLevelEntry 2}

rulesetNetobjectPrefixesBitmasksLevelMax OBJECT-TYPE
	SYNTAX	 CounterBasedGauge64
	MAX-ACCESS  read-only
	STATUS      current
	DESCRIPTION
	"Table entry attribute for rulesetNetobjectPrefixesBitmasks"
	::={rulesetNetobjectPrefixesBitmasksLevelEntry 4}


rulesetNetobjectPrefixesOpers	OBJECT IDENTIFIER ::={ruleset 63}

rulesetNetobjectPrefixesOpersVal	OBJECT-TYPE
	SYNTAX	 Counter64
	MAX-ACCESS read-only
	STATUS current
	DESCRIPTION "Netobject prefixes: Number of updating operations"

	::={rulesetNetobjectPrefixesOpers 1}

rulesetNetobjectPrefixesOpersMom	OBJECT-TYPE
	SYNTAX	 CounterBasedGauge64
	MAX-ACCESS read-only
	STATUS current
	DESCRIPTION "Netobject prefixes: Number of updating operations"

	::={rulesetNetobjectPrefixesOpers 2}

rulesetNetobjectPrefixesOpersMax	OBJECT-TYPE
	SYNTAX	 CounterBasedGauge64
	MAX-ACCESS read-only
	STATUS current
	DESCRIPTION "Netobject prefixes: Number of updating operations"

	::={rulesetNetobjectPrefixesOpers 3}

rulesetNetobjectPrefixesOpersLevelTable OBJECT-TYPE
	SYNTAX      SEQUENCE OF RulesetNetobjectPrefixesOpersLevelEntry
	MAX-ACCESS  not-accessible
	STATUS      current
	DESCRIPTION
	"Table for rulesetNetobjectPrefixesOpers"
	::={rulesetNetobjectPrefixesOpers 4}

rulesetNetobjectPrefixesOpersLevelEntry OBJECT-TYPE
	SYNTAX      RulesetNetobjectPrefixesOpersLevelEntry
	MAX-ACCESS  not-accessible
	STATUS      current
	DESCRIPTION
	"Table entry for rulesetNetobjectPrefixesOpers"
	INDEX { rulesetNetobjectPrefixesOpersLevelName }
	::={rulesetNetobjectPrefixesOpersLevelTable 1}

RulesetNetobjectPrefixesOpersLevelEntry ::=
	SEQUENCE {
		rulesetNetobjectPrefixesOpersLevelName	DisplayString,
		rulesetNetobjectPrefixesOpersLevelVal	Counter64,
		rulesetNetobjectPrefixesOpersLevelMom	CounterBasedGauge64,
		rulesetNetobjectPrefixesOpersLevelMax	CounterBasedGauge64
	}

rulesetNetobjectPrefixesOpersLevelName OBJECT-TYPE
	SYNTAX      DisplayString
	MAX-ACCESS  not-accessible
	STATUS      current
	DESCRIPTION
	"Table entry display string for rulesetNetobjectPrefixesOpers"
	::={rulesetNetobjectPrefixesOpersLevelEntry 1}

rulesetNetobjectPrefixesOpersLevelVal OBJECT-TYPE
	SYNTAX	 Counter64
	MAX-ACCESS  read-only
	STATUS      current
	DESCRIPTION
	"Table entry attribute for rulesetNetobjectPrefixesOpers"
	::={rulesetNetobjectPrefixesOpersLevelEntry 2}

rulesetNetobjectPrefixesOpersLevelMom OBJECT-TYPE
	SYNTAX	 CounterBasedGauge64
	MAX-ACCESS  read-only
	STATUS      current
	DESCRIPTION
	"Table entry attribute for rulesetNetobjectPrefixesOpers"
	::={rulesetNetobjectPrefixesOpersLevelEntry 3}

rulesetNetobjectPrefixesOpersLevelMax OBJECT-TYPE
	SYNTAX	 CounterBasedGauge64
	MAX-ACCESS  read-only
	STATUS      current
	DESCRIPTION
	"Table entry attribute for rulesetNetobjectPrefixesOpers"
	::={rulesetNetobjectPrefixesOpersLevelEntry 4}


rulesetNetobjectPrefixesErrors	OBJECT IDENTIFIER ::={ruleset 64}

rulesetNetobjectPrefixesErrorsVal	OBJECT-TYPE
	SYNTAX	 Counter64
	MAX-ACCESS read-only
	STATUS current
	DESCRIPTION "Netobject prefixes: Number of errors"

	::={rulesetNetobjectPrefixesErrors 1}

rulesetNetobjectPrefixesErrorsMom	OBJECT-TYPE
	SYNTAX	 CounterBasedGauge64
	MAX-ACCESS read-only
	STATUS current
	DESCRIPTION "Netobject prefixes: Number of errors"

	::={rulesetNetobjectPrefixesErrors 2}

rulesetNetobjectPrefixesErrorsMax	OBJECT-TYPE
	SYNTAX	 CounterBasedGauge64
	MAX-ACCESS read-only
	STATUS current
	DESCRIPTION "Netobject prefixes: Number of errors"

	::={rulesetNetobjectPrefixesErrors 3}

rulesetNetobjectPrefixesErrorsLevelTable OBJECT-TYPE
	SYNTAX      SEQUENCE OF RulesetNetobjectPrefixesErrorsLevelEntry
	MAX-ACCESS  not-accessible
	STATUS      current
	DESCRIPTION
	"Table for rulesetNetobjectPrefixesErrors"
	::={rulesetNetobjectPrefixesErrors 4}

rulesetNetobjectPrefixesErrorsLevelEntry OBJECT-TYPE
	SYNTAX      RulesetNetobjectPrefixesErrorsLevelEntry
	MAX-ACCESS  not-accessible
	STATUS      current
	DESCRIPTION
	"Table entry for rulesetNetobjectPrefixesErrors"
	INDEX { rulesetNetobjectPrefixesErrorsLevelName }
	::={rulesetNetobjectPrefixesErrorsLevelTable 1}

RulesetNetobjectPrefixesErrorsLevelEntry ::=
	SEQUENCE {
		rulesetNetobjectPrefixesErrorsLevelName	DisplayString,
		rulesetNetobjectPrefixesErrorsLevelVal	Counter64,
		rulesetNetobjectPrefixesErrorsLevelMom	CounterBasedGauge64,
		rulesetNetobjectPrefixesErrorsLevelMax	CounterBasedGauge64
	}

rulesetNetobjectPrefixesErrorsLevelName OBJECT-TYPE
	SYNTAX      DisplayString
	MAX-ACCESS  not-accessible
	STATUS      current
	DESCRIPTION
	"Table entry display string for rulesetNetobjectPrefixesErrors"
	::={rulesetNetobjectPrefixesErrorsLevelEntry 1}

rulesetNetobjectPrefixesErrorsLevelVal OBJECT-TYPE
	SYNTAX	 Counter64
	MAX-ACCESS  read-only
	STATUS      current
	DESCRIPTION
	"Table entry attribute for rulesetNetobjectPrefixesErrors"
	::={rulesetNetobjectPrefixesErrorsLevelEntry 2}

rulesetNetobjectPrefixesErrorsLevelMom OBJECT-TYPE
	SYNTAX	 CounterBasedGauge64
	MAX-ACCESS  read-only
	STATUS      current
	DESCRIPTION
	"Table entry attribute for rulesetNetobjectPrefixesErrors"
	::={rulesetNetobjectPrefixesErrorsLevelEntry 3}

rulesetNetobjectPrefixesErrorsLevelMax OBJECT-TYPE
	SYNTAX	 CounterBasedGauge64
	MAX-ACCESS  read-only
	STATUS      current
	DESCRIPTION
	"Table entry attribute for rulesetNetobjectPrefixesErrors"
	::={rulesetNetobjectPrefixesErrorsLevelEntry 4}


rulesetBitmasksAvg	OBJECT IDENTIFIER ::={ruleset 15}

rulesetBitmasksAvgVal	OBJECT-TYPE
	SYNTAX	 CounterBasedGauge64
	MAX-ACCESS read-only
	STATUS obsolete
	DESCRIPTION "Bitmask average number of words"

	::={rulesetBitmasksAvg 1}

rulesetBitmasksAvgMax	OBJECT-TYPE
	SYNTAX	 CounterBasedGauge64
	MAX-ACCESS read-only
	STATUS obsolete
	DESCRIPTION "Bitmask average number of words"

	::={rulesetBitmasksAvg 3}

rulesetBitmasksAvgLevelTable OBJECT-TYPE
	SYNTAX      SEQUENCE OF RulesetBitmasksAvgLevelEntry
	MAX-ACCESS  not-accessible
	STATUS      current
	DESCRIPTION
	"Table for rulesetBitmasksAvg"
	::={rulesetBitmasksAvg 4}

rulesetBitmasksAvgLevelEntry OBJECT-TYPE
	SYNTAX      RulesetBitmasksAvgLevelEntry
	MAX-ACCESS  not-accessible
	STATUS      current
	DESCRIPTION
	"Table entry for rulesetBitmasksAvg"
	INDEX { rulesetBitmasksAvgLevelName }
	::={rulesetBitmasksAvgLevelTable 1}

RulesetBitmasksAvgLevelEntry ::=
	SEQUENCE {
		rulesetBitmasksAvgLevelName	DisplayString,
		rulesetBitmasksAvgLevelVal	CounterBasedGauge64,
		rulesetBitmasksAvgLevelMax	CounterBasedGauge64
	}

rulesetBitmasksAvgLevelName OBJECT-TYPE
	SYNTAX      DisplayString
	MAX-ACCESS  not-accessible
	STATUS      current
	DESCRIPTION
	"Table entry display string for rulesetBitmasksAvg"
	::={rulesetBitmasksAvgLevelEntry 1}

rulesetBitmasksAvgLevelVal OBJECT-TYPE
	SYNTAX	 CounterBasedGauge64
	MAX-ACCESS  read-only
	STATUS      current
	DESCRIPTION
	"Table entry attribute for rulesetBitmasksAvg"
	::={rulesetBitmasksAvgLevelEntry 2}

rulesetBitmasksAvgLevelMax OBJECT-TYPE
	SYNTAX	 CounterBasedGauge64
	MAX-ACCESS  read-only
	STATUS      current
	DESCRIPTION
	"Table entry attribute for rulesetBitmasksAvg"
	::={rulesetBitmasksAvgLevelEntry 4}


rulesetBitmasksMax	OBJECT IDENTIFIER ::={ruleset 16}

rulesetBitmasksMaxVal	OBJECT-TYPE
	SYNTAX	 CounterBasedGauge64
	MAX-ACCESS read-only
	STATUS obsolete
	DESCRIPTION "Bitmask max number of words"

	::={rulesetBitmasksMax 1}

rulesetBitmasksMaxMax	OBJECT-TYPE
	SYNTAX	 CounterBasedGauge64
	MAX-ACCESS read-only
	STATUS obsolete
	DESCRIPTION "Bitmask max number of words"

	::={rulesetBitmasksMax 3}

rulesetBitmasksMaxLevelTable OBJECT-TYPE
	SYNTAX      SEQUENCE OF RulesetBitmasksMaxLevelEntry
	MAX-ACCESS  not-accessible
	STATUS      current
	DESCRIPTION
	"Table for rulesetBitmasksMax"
	::={rulesetBitmasksMax 4}

rulesetBitmasksMaxLevelEntry OBJECT-TYPE
	SYNTAX      RulesetBitmasksMaxLevelEntry
	MAX-ACCESS  not-accessible
	STATUS      current
	DESCRIPTION
	"Table entry for rulesetBitmasksMax"
	INDEX { rulesetBitmasksMaxLevelName }
	::={rulesetBitmasksMaxLevelTable 1}

RulesetBitmasksMaxLevelEntry ::=
	SEQUENCE {
		rulesetBitmasksMaxLevelName	DisplayString,
		rulesetBitmasksMaxLevelVal	CounterBasedGauge64,
		rulesetBitmasksMaxLevelMax	CounterBasedGauge64
	}

rulesetBitmasksMaxLevelName OBJECT-TYPE
	SYNTAX      DisplayString
	MAX-ACCESS  not-accessible
	STATUS      current
	DESCRIPTION
	"Table entry display string for rulesetBitmasksMax"
	::={rulesetBitmasksMaxLevelEntry 1}

rulesetBitmasksMaxLevelVal OBJECT-TYPE
	SYNTAX	 CounterBasedGauge64
	MAX-ACCESS  read-only
	STATUS      current
	DESCRIPTION
	"Table entry attribute for rulesetBitmasksMax"
	::={rulesetBitmasksMaxLevelEntry 2}

rulesetBitmasksMaxLevelMax OBJECT-TYPE
	SYNTAX	 CounterBasedGauge64
	MAX-ACCESS  read-only
	STATUS      current
	DESCRIPTION
	"Table entry attribute for rulesetBitmasksMax"
	::={rulesetBitmasksMaxLevelEntry 4}


rulesetDynipAdd	OBJECT IDENTIFIER ::={ruleset 17}

rulesetDynipAddVal	OBJECT-TYPE
	SYNTAX	 Counter64
	MAX-ACCESS read-only
	STATUS obsolete
	DESCRIPTION "Dynamic ips added"

	::={rulesetDynipAdd 1}

rulesetDynipAddMom	OBJECT-TYPE
	SYNTAX	 CounterBasedGauge64
	MAX-ACCESS read-only
	STATUS obsolete
	DESCRIPTION "Dynamic ips added"

	::={rulesetDynipAdd 2}

rulesetDynipAddMax	OBJECT-TYPE
	SYNTAX	 CounterBasedGauge64
	MAX-ACCESS read-only
	STATUS obsolete
	DESCRIPTION "Dynamic ips added"

	::={rulesetDynipAdd 3}

rulesetDynipAddLevelTable OBJECT-TYPE
	SYNTAX      SEQUENCE OF RulesetDynipAddLevelEntry
	MAX-ACCESS  not-accessible
	STATUS      current
	DESCRIPTION
	"Table for rulesetDynipAdd"
	::={rulesetDynipAdd 4}

rulesetDynipAddLevelEntry OBJECT-TYPE
	SYNTAX      RulesetDynipAddLevelEntry
	MAX-ACCESS  not-accessible
	STATUS      current
	DESCRIPTION
	"Table entry for rulesetDynipAdd"
	INDEX { rulesetDynipAddLevelName }
	::={rulesetDynipAddLevelTable 1}

RulesetDynipAddLevelEntry ::=
	SEQUENCE {
		rulesetDynipAddLevelName	DisplayString,
		rulesetDynipAddLevelVal	Counter64,
		rulesetDynipAddLevelMom	CounterBasedGauge64,
		rulesetDynipAddLevelMax	CounterBasedGauge64
	}

rulesetDynipAddLevelName OBJECT-TYPE
	SYNTAX      DisplayString
	MAX-ACCESS  not-accessible
	STATUS      current
	DESCRIPTION
	"Table entry display string for rulesetDynipAdd"
	::={rulesetDynipAddLevelEntry 1}

rulesetDynipAddLevelVal OBJECT-TYPE
	SYNTAX	 Counter64
	MAX-ACCESS  read-only
	STATUS      current
	DESCRIPTION
	"Table entry attribute for rulesetDynipAdd"
	::={rulesetDynipAddLevelEntry 2}

rulesetDynipAddLevelMom OBJECT-TYPE
	SYNTAX	 CounterBasedGauge64
	MAX-ACCESS  read-only
	STATUS      current
	DESCRIPTION
	"Table entry attribute for rulesetDynipAdd"
	::={rulesetDynipAddLevelEntry 3}

rulesetDynipAddLevelMax OBJECT-TYPE
	SYNTAX	 CounterBasedGauge64
	MAX-ACCESS  read-only
	STATUS      current
	DESCRIPTION
	"Table entry attribute for rulesetDynipAdd"
	::={rulesetDynipAddLevelEntry 4}


rulesetDynipRemove	OBJECT IDENTIFIER ::={ruleset 18}

rulesetDynipRemoveVal	OBJECT-TYPE
	SYNTAX	 Counter64
	MAX-ACCESS read-only
	STATUS obsolete
	DESCRIPTION "Dynamic ips removed"

	::={rulesetDynipRemove 1}

rulesetDynipRemoveMom	OBJECT-TYPE
	SYNTAX	 CounterBasedGauge64
	MAX-ACCESS read-only
	STATUS obsolete
	DESCRIPTION "Dynamic ips removed"

	::={rulesetDynipRemove 2}

rulesetDynipRemoveMax	OBJECT-TYPE
	SYNTAX	 CounterBasedGauge64
	MAX-ACCESS read-only
	STATUS obsolete
	DESCRIPTION "Dynamic ips removed"

	::={rulesetDynipRemove 3}

rulesetDynipRemoveLevelTable OBJECT-TYPE
	SYNTAX      SEQUENCE OF RulesetDynipRemoveLevelEntry
	MAX-ACCESS  not-accessible
	STATUS      current
	DESCRIPTION
	"Table for rulesetDynipRemove"
	::={rulesetDynipRemove 4}

rulesetDynipRemoveLevelEntry OBJECT-TYPE
	SYNTAX      RulesetDynipRemoveLevelEntry
	MAX-ACCESS  not-accessible
	STATUS      current
	DESCRIPTION
	"Table entry for rulesetDynipRemove"
	INDEX { rulesetDynipRemoveLevelName }
	::={rulesetDynipRemoveLevelTable 1}

RulesetDynipRemoveLevelEntry ::=
	SEQUENCE {
		rulesetDynipRemoveLevelName	DisplayString,
		rulesetDynipRemoveLevelVal	Counter64,
		rulesetDynipRemoveLevelMom	CounterBasedGauge64,
		rulesetDynipRemoveLevelMax	CounterBasedGauge64
	}

rulesetDynipRemoveLevelName OBJECT-TYPE
	SYNTAX      DisplayString
	MAX-ACCESS  not-accessible
	STATUS      current
	DESCRIPTION
	"Table entry display string for rulesetDynipRemove"
	::={rulesetDynipRemoveLevelEntry 1}

rulesetDynipRemoveLevelVal OBJECT-TYPE
	SYNTAX	 Counter64
	MAX-ACCESS  read-only
	STATUS      current
	DESCRIPTION
	"Table entry attribute for rulesetDynipRemove"
	::={rulesetDynipRemoveLevelEntry 2}

rulesetDynipRemoveLevelMom OBJECT-TYPE
	SYNTAX	 CounterBasedGauge64
	MAX-ACCESS  read-only
	STATUS      current
	DESCRIPTION
	"Table entry attribute for rulesetDynipRemove"
	::={rulesetDynipRemoveLevelEntry 3}

rulesetDynipRemoveLevelMax OBJECT-TYPE
	SYNTAX	 CounterBasedGauge64
	MAX-ACCESS  read-only
	STATUS      current
	DESCRIPTION
	"Table entry attribute for rulesetDynipRemove"
	::={rulesetDynipRemoveLevelEntry 4}


rulesetDynipAllocFail	OBJECT IDENTIFIER ::={ruleset 41}

rulesetDynipAllocFailVal	OBJECT-TYPE
	SYNTAX	 Counter64
	MAX-ACCESS read-only
	STATUS obsolete
	DESCRIPTION "Dynamic ip loading failures (allocation failure)"

	::={rulesetDynipAllocFail 1}

rulesetDynipAllocFailMom	OBJECT-TYPE
	SYNTAX	 CounterBasedGauge64
	MAX-ACCESS read-only
	STATUS obsolete
	DESCRIPTION "Dynamic ip loading failures (allocation failure)"

	::={rulesetDynipAllocFail 2}

rulesetDynipAllocFailMax	OBJECT-TYPE
	SYNTAX	 CounterBasedGauge64
	MAX-ACCESS read-only
	STATUS obsolete
	DESCRIPTION "Dynamic ip loading failures (allocation failure)"

	::={rulesetDynipAllocFail 3}

rulesetDynipAllocFailLevelTable OBJECT-TYPE
	SYNTAX      SEQUENCE OF RulesetDynipAllocFailLevelEntry
	MAX-ACCESS  not-accessible
	STATUS      current
	DESCRIPTION
	"Table for rulesetDynipAllocFail"
	::={rulesetDynipAllocFail 4}

rulesetDynipAllocFailLevelEntry OBJECT-TYPE
	SYNTAX      RulesetDynipAllocFailLevelEntry
	MAX-ACCESS  not-accessible
	STATUS      current
	DESCRIPTION
	"Table entry for rulesetDynipAllocFail"
	INDEX { rulesetDynipAllocFailLevelName }
	::={rulesetDynipAllocFailLevelTable 1}

RulesetDynipAllocFailLevelEntry ::=
	SEQUENCE {
		rulesetDynipAllocFailLevelName	DisplayString,
		rulesetDynipAllocFailLevelVal	Counter64,
		rulesetDynipAllocFailLevelMom	CounterBasedGauge64,
		rulesetDynipAllocFailLevelMax	CounterBasedGauge64
	}

rulesetDynipAllocFailLevelName OBJECT-TYPE
	SYNTAX      DisplayString
	MAX-ACCESS  not-accessible
	STATUS      current
	DESCRIPTION
	"Table entry display string for rulesetDynipAllocFail"
	::={rulesetDynipAllocFailLevelEntry 1}

rulesetDynipAllocFailLevelVal OBJECT-TYPE
	SYNTAX	 Counter64
	MAX-ACCESS  read-only
	STATUS      current
	DESCRIPTION
	"Table entry attribute for rulesetDynipAllocFail"
	::={rulesetDynipAllocFailLevelEntry 2}

rulesetDynipAllocFailLevelMom OBJECT-TYPE
	SYNTAX	 CounterBasedGauge64
	MAX-ACCESS  read-only
	STATUS      current
	DESCRIPTION
	"Table entry attribute for rulesetDynipAllocFail"
	::={rulesetDynipAllocFailLevelEntry 3}

rulesetDynipAllocFailLevelMax OBJECT-TYPE
	SYNTAX	 CounterBasedGauge64
	MAX-ACCESS  read-only
	STATUS      current
	DESCRIPTION
	"Table entry attribute for rulesetDynipAllocFail"
	::={rulesetDynipAllocFailLevelEntry 4}


rulesetDynipOversized	OBJECT IDENTIFIER ::={ruleset 42}

rulesetDynipOversizedVal	OBJECT-TYPE
	SYNTAX	 Counter64
	MAX-ACCESS read-only
	STATUS obsolete
	DESCRIPTION "Dynamic ip loading failures (oversized)"

	::={rulesetDynipOversized 1}

rulesetDynipOversizedMom	OBJECT-TYPE
	SYNTAX	 CounterBasedGauge64
	MAX-ACCESS read-only
	STATUS obsolete
	DESCRIPTION "Dynamic ip loading failures (oversized)"

	::={rulesetDynipOversized 2}

rulesetDynipOversizedMax	OBJECT-TYPE
	SYNTAX	 CounterBasedGauge64
	MAX-ACCESS read-only
	STATUS obsolete
	DESCRIPTION "Dynamic ip loading failures (oversized)"

	::={rulesetDynipOversized 3}

rulesetDynipOversizedLevelTable OBJECT-TYPE
	SYNTAX      SEQUENCE OF RulesetDynipOversizedLevelEntry
	MAX-ACCESS  not-accessible
	STATUS      current
	DESCRIPTION
	"Table for rulesetDynipOversized"
	::={rulesetDynipOversized 4}

rulesetDynipOversizedLevelEntry OBJECT-TYPE
	SYNTAX      RulesetDynipOversizedLevelEntry
	MAX-ACCESS  not-accessible
	STATUS      current
	DESCRIPTION
	"Table entry for rulesetDynipOversized"
	INDEX { rulesetDynipOversizedLevelName }
	::={rulesetDynipOversizedLevelTable 1}

RulesetDynipOversizedLevelEntry ::=
	SEQUENCE {
		rulesetDynipOversizedLevelName	DisplayString,
		rulesetDynipOversizedLevelVal	Counter64,
		rulesetDynipOversizedLevelMom	CounterBasedGauge64,
		rulesetDynipOversizedLevelMax	CounterBasedGauge64
	}

rulesetDynipOversizedLevelName OBJECT-TYPE
	SYNTAX      DisplayString
	MAX-ACCESS  not-accessible
	STATUS      current
	DESCRIPTION
	"Table entry display string for rulesetDynipOversized"
	::={rulesetDynipOversizedLevelEntry 1}

rulesetDynipOversizedLevelVal OBJECT-TYPE
	SYNTAX	 Counter64
	MAX-ACCESS  read-only
	STATUS      current
	DESCRIPTION
	"Table entry attribute for rulesetDynipOversized"
	::={rulesetDynipOversizedLevelEntry 2}

rulesetDynipOversizedLevelMom OBJECT-TYPE
	SYNTAX	 CounterBasedGauge64
	MAX-ACCESS  read-only
	STATUS      current
	DESCRIPTION
	"Table entry attribute for rulesetDynipOversized"
	::={rulesetDynipOversizedLevelEntry 3}

rulesetDynipOversizedLevelMax OBJECT-TYPE
	SYNTAX	 CounterBasedGauge64
	MAX-ACCESS  read-only
	STATUS      current
	DESCRIPTION
	"Table entry attribute for rulesetDynipOversized"
	::={rulesetDynipOversizedLevelEntry 4}


rulesetDynRulesUsedPlens	OBJECT IDENTIFIER ::={ruleset 50}

rulesetDynRulesUsedPlensVal	OBJECT-TYPE
	SYNTAX	 CounterBasedGauge64
	MAX-ACCESS read-only
	STATUS obsolete
	DESCRIPTION "Different number of prefix lengths used for dynamic IPv4 rules"

	::={rulesetDynRulesUsedPlens 1}

rulesetDynRulesUsedPlensMax	OBJECT-TYPE
	SYNTAX	 CounterBasedGauge64
	MAX-ACCESS read-only
	STATUS obsolete
	DESCRIPTION "Different number of prefix lengths used for dynamic IPv4 rules"

	::={rulesetDynRulesUsedPlens 3}

rulesetDynRulesUsedPlensLevelTable OBJECT-TYPE
	SYNTAX      SEQUENCE OF RulesetDynRulesUsedPlensLevelEntry
	MAX-ACCESS  not-accessible
	STATUS      current
	DESCRIPTION
	"Table for rulesetDynRulesUsedPlens"
	::={rulesetDynRulesUsedPlens 4}

rulesetDynRulesUsedPlensLevelEntry OBJECT-TYPE
	SYNTAX      RulesetDynRulesUsedPlensLevelEntry
	MAX-ACCESS  not-accessible
	STATUS      current
	DESCRIPTION
	"Table entry for rulesetDynRulesUsedPlens"
	INDEX { rulesetDynRulesUsedPlensLevelName }
	::={rulesetDynRulesUsedPlensLevelTable 1}

RulesetDynRulesUsedPlensLevelEntry ::=
	SEQUENCE {
		rulesetDynRulesUsedPlensLevelName	DisplayString,
		rulesetDynRulesUsedPlensLevelVal	CounterBasedGauge64,
		rulesetDynRulesUsedPlensLevelMax	CounterBasedGauge64
	}

rulesetDynRulesUsedPlensLevelName OBJECT-TYPE
	SYNTAX      DisplayString
	MAX-ACCESS  not-accessible
	STATUS      current
	DESCRIPTION
	"Table entry display string for rulesetDynRulesUsedPlens"
	::={rulesetDynRulesUsedPlensLevelEntry 1}

rulesetDynRulesUsedPlensLevelVal OBJECT-TYPE
	SYNTAX	 CounterBasedGauge64
	MAX-ACCESS  read-only
	STATUS      current
	DESCRIPTION
	"Table entry attribute for rulesetDynRulesUsedPlens"
	::={rulesetDynRulesUsedPlensLevelEntry 2}

rulesetDynRulesUsedPlensLevelMax OBJECT-TYPE
	SYNTAX	 CounterBasedGauge64
	MAX-ACCESS  read-only
	STATUS      current
	DESCRIPTION
	"Table entry attribute for rulesetDynRulesUsedPlens"
	::={rulesetDynRulesUsedPlensLevelEntry 4}


rulesetDynruleLoaded	OBJECT IDENTIFIER ::={ruleset 67}

rulesetDynruleLoadedVal	OBJECT-TYPE
	SYNTAX	 DateAndTime
	MAX-ACCESS read-only
	STATUS current
	DESCRIPTION "Dynamic Rule: Current dynamic rule loaded"

	::={rulesetDynruleLoaded 1}

rulesetDynruleLoadedLevelTable OBJECT-TYPE
	SYNTAX      SEQUENCE OF RulesetDynruleLoadedLevelEntry
	MAX-ACCESS  not-accessible
	STATUS      current
	DESCRIPTION
	"Table for rulesetDynruleLoaded"
	::={rulesetDynruleLoaded 2}

rulesetDynruleLoadedLevelEntry OBJECT-TYPE
	SYNTAX      RulesetDynruleLoadedLevelEntry
	MAX-ACCESS  not-accessible
	STATUS      current
	DESCRIPTION
	"Table entry for rulesetDynruleLoaded"
	INDEX { rulesetDynruleLoadedLevelName }
	::={rulesetDynruleLoadedLevelTable 1}

RulesetDynruleLoadedLevelEntry ::=
	SEQUENCE {
		rulesetDynruleLoadedLevelName	DisplayString,
		rulesetDynruleLoadedLevelVal	DateAndTime
	}

rulesetDynruleLoadedLevelName OBJECT-TYPE
	SYNTAX      DisplayString
	MAX-ACCESS  not-accessible
	STATUS      current
	DESCRIPTION
	"Table entry display string for rulesetDynruleLoaded"
	::={rulesetDynruleLoadedLevelEntry 1}

rulesetDynruleLoadedLevelVal OBJECT-TYPE
	SYNTAX	 DateAndTime
	MAX-ACCESS  read-only
	STATUS      current
	DESCRIPTION
	"Table entry attribute for rulesetDynruleLoaded"
	::={rulesetDynruleLoadedLevelEntry 2}


rulesetConnStatechange	OBJECT IDENTIFIER ::={ruleset 27}

rulesetConnStatechangeVal	OBJECT-TYPE
	SYNTAX	 Counter64
	MAX-ACCESS read-only
	STATUS current
	DESCRIPTION "Flow ruleset statechanges"

	::={rulesetConnStatechange 1}

rulesetConnStatechangeMom	OBJECT-TYPE
	SYNTAX	 CounterBasedGauge64
	MAX-ACCESS read-only
	STATUS current
	DESCRIPTION "Flow ruleset statechanges"

	::={rulesetConnStatechange 2}

rulesetConnStatechangeMax	OBJECT-TYPE
	SYNTAX	 CounterBasedGauge64
	MAX-ACCESS read-only
	STATUS current
	DESCRIPTION "Flow ruleset statechanges"

	::={rulesetConnStatechange 3}

rulesetConnStatechangeLevelTable OBJECT-TYPE
	SYNTAX      SEQUENCE OF RulesetConnStatechangeLevelEntry
	MAX-ACCESS  not-accessible
	STATUS      current
	DESCRIPTION
	"Table for rulesetConnStatechange"
	::={rulesetConnStatechange 4}

rulesetConnStatechangeLevelEntry OBJECT-TYPE
	SYNTAX      RulesetConnStatechangeLevelEntry
	MAX-ACCESS  not-accessible
	STATUS      current
	DESCRIPTION
	"Table entry for rulesetConnStatechange"
	INDEX { rulesetConnStatechangeLevelName }
	::={rulesetConnStatechangeLevelTable 1}

RulesetConnStatechangeLevelEntry ::=
	SEQUENCE {
		rulesetConnStatechangeLevelName	DisplayString,
		rulesetConnStatechangeLevelVal	Counter64,
		rulesetConnStatechangeLevelMom	CounterBasedGauge64,
		rulesetConnStatechangeLevelMax	CounterBasedGauge64
	}

rulesetConnStatechangeLevelName OBJECT-TYPE
	SYNTAX      DisplayString
	MAX-ACCESS  not-accessible
	STATUS      current
	DESCRIPTION
	"Table entry display string for rulesetConnStatechange"
	::={rulesetConnStatechangeLevelEntry 1}

rulesetConnStatechangeLevelVal OBJECT-TYPE
	SYNTAX	 Counter64
	MAX-ACCESS  read-only
	STATUS      current
	DESCRIPTION
	"Table entry attribute for rulesetConnStatechange"
	::={rulesetConnStatechangeLevelEntry 2}

rulesetConnStatechangeLevelMom OBJECT-TYPE
	SYNTAX	 CounterBasedGauge64
	MAX-ACCESS  read-only
	STATUS      current
	DESCRIPTION
	"Table entry attribute for rulesetConnStatechange"
	::={rulesetConnStatechangeLevelEntry 3}

rulesetConnStatechangeLevelMax OBJECT-TYPE
	SYNTAX	 CounterBasedGauge64
	MAX-ACCESS  read-only
	STATUS      current
	DESCRIPTION
	"Table entry attribute for rulesetConnStatechange"
	::={rulesetConnStatechangeLevelEntry 4}


rulesetConnStatechangeProp	OBJECT IDENTIFIER ::={ruleset 28}

rulesetConnStatechangePropVal	OBJECT-TYPE
	SYNTAX	 Counter64
	MAX-ACCESS read-only
	STATUS current
	DESCRIPTION "Flow ruleset statechanges (prop)"

	::={rulesetConnStatechangeProp 1}

rulesetConnStatechangePropMom	OBJECT-TYPE
	SYNTAX	 CounterBasedGauge64
	MAX-ACCESS read-only
	STATUS current
	DESCRIPTION "Flow ruleset statechanges (prop)"

	::={rulesetConnStatechangeProp 2}

rulesetConnStatechangePropMax	OBJECT-TYPE
	SYNTAX	 CounterBasedGauge64
	MAX-ACCESS read-only
	STATUS current
	DESCRIPTION "Flow ruleset statechanges (prop)"

	::={rulesetConnStatechangeProp 3}

rulesetConnStatechangePropLevelTable OBJECT-TYPE
	SYNTAX      SEQUENCE OF RulesetConnStatechangePropLevelEntry
	MAX-ACCESS  not-accessible
	STATUS      current
	DESCRIPTION
	"Table for rulesetConnStatechangeProp"
	::={rulesetConnStatechangeProp 4}

rulesetConnStatechangePropLevelEntry OBJECT-TYPE
	SYNTAX      RulesetConnStatechangePropLevelEntry
	MAX-ACCESS  not-accessible
	STATUS      current
	DESCRIPTION
	"Table entry for rulesetConnStatechangeProp"
	INDEX { rulesetConnStatechangePropLevelName }
	::={rulesetConnStatechangePropLevelTable 1}

RulesetConnStatechangePropLevelEntry ::=
	SEQUENCE {
		rulesetConnStatechangePropLevelName	DisplayString,
		rulesetConnStatechangePropLevelVal	Counter64,
		rulesetConnStatechangePropLevelMom	CounterBasedGauge64,
		rulesetConnStatechangePropLevelMax	CounterBasedGauge64
	}

rulesetConnStatechangePropLevelName OBJECT-TYPE
	SYNTAX      DisplayString
	MAX-ACCESS  not-accessible
	STATUS      current
	DESCRIPTION
	"Table entry display string for rulesetConnStatechangeProp"
	::={rulesetConnStatechangePropLevelEntry 1}

rulesetConnStatechangePropLevelVal OBJECT-TYPE
	SYNTAX	 Counter64
	MAX-ACCESS  read-only
	STATUS      current
	DESCRIPTION
	"Table entry attribute for rulesetConnStatechangeProp"
	::={rulesetConnStatechangePropLevelEntry 2}

rulesetConnStatechangePropLevelMom OBJECT-TYPE
	SYNTAX	 CounterBasedGauge64
	MAX-ACCESS  read-only
	STATUS      current
	DESCRIPTION
	"Table entry attribute for rulesetConnStatechangeProp"
	::={rulesetConnStatechangePropLevelEntry 3}

rulesetConnStatechangePropLevelMax OBJECT-TYPE
	SYNTAX	 CounterBasedGauge64
	MAX-ACCESS  read-only
	STATUS      current
	DESCRIPTION
	"Table entry attribute for rulesetConnStatechangeProp"
	::={rulesetConnStatechangePropLevelEntry 4}


rulesetConnStatechangeService	OBJECT IDENTIFIER ::={ruleset 29}

rulesetConnStatechangeServiceVal	OBJECT-TYPE
	SYNTAX	 Counter64
	MAX-ACCESS read-only
	STATUS current
	DESCRIPTION "Flow ruleset statechanges (service)"

	::={rulesetConnStatechangeService 1}

rulesetConnStatechangeServiceMom	OBJECT-TYPE
	SYNTAX	 CounterBasedGauge64
	MAX-ACCESS read-only
	STATUS current
	DESCRIPTION "Flow ruleset statechanges (service)"

	::={rulesetConnStatechangeService 2}

rulesetConnStatechangeServiceMax	OBJECT-TYPE
	SYNTAX	 CounterBasedGauge64
	MAX-ACCESS read-only
	STATUS current
	DESCRIPTION "Flow ruleset statechanges (service)"

	::={rulesetConnStatechangeService 3}

rulesetConnStatechangeServiceLevelTable OBJECT-TYPE
	SYNTAX      SEQUENCE OF RulesetConnStatechangeServiceLevelEntry
	MAX-ACCESS  not-accessible
	STATUS      current
	DESCRIPTION
	"Table for rulesetConnStatechangeService"
	::={rulesetConnStatechangeService 4}

rulesetConnStatechangeServiceLevelEntry OBJECT-TYPE
	SYNTAX      RulesetConnStatechangeServiceLevelEntry
	MAX-ACCESS  not-accessible
	STATUS      current
	DESCRIPTION
	"Table entry for rulesetConnStatechangeService"
	INDEX { rulesetConnStatechangeServiceLevelName }
	::={rulesetConnStatechangeServiceLevelTable 1}

RulesetConnStatechangeServiceLevelEntry ::=
	SEQUENCE {
		rulesetConnStatechangeServiceLevelName	DisplayString,
		rulesetConnStatechangeServiceLevelVal	Counter64,
		rulesetConnStatechangeServiceLevelMom	CounterBasedGauge64,
		rulesetConnStatechangeServiceLevelMax	CounterBasedGauge64
	}

rulesetConnStatechangeServiceLevelName OBJECT-TYPE
	SYNTAX      DisplayString
	MAX-ACCESS  not-accessible
	STATUS      current
	DESCRIPTION
	"Table entry display string for rulesetConnStatechangeService"
	::={rulesetConnStatechangeServiceLevelEntry 1}

rulesetConnStatechangeServiceLevelVal OBJECT-TYPE
	SYNTAX	 Counter64
	MAX-ACCESS  read-only
	STATUS      current
	DESCRIPTION
	"Table entry attribute for rulesetConnStatechangeService"
	::={rulesetConnStatechangeServiceLevelEntry 2}

rulesetConnStatechangeServiceLevelMom OBJECT-TYPE
	SYNTAX	 CounterBasedGauge64
	MAX-ACCESS  read-only
	STATUS      current
	DESCRIPTION
	"Table entry attribute for rulesetConnStatechangeService"
	::={rulesetConnStatechangeServiceLevelEntry 3}

rulesetConnStatechangeServiceLevelMax OBJECT-TYPE
	SYNTAX	 CounterBasedGauge64
	MAX-ACCESS  read-only
	STATUS      current
	DESCRIPTION
	"Table entry attribute for rulesetConnStatechangeService"
	::={rulesetConnStatechangeServiceLevelEntry 4}


rulesetConnStatechangeFlags	OBJECT IDENTIFIER ::={ruleset 30}

rulesetConnStatechangeFlagsVal	OBJECT-TYPE
	SYNTAX	 Counter64
	MAX-ACCESS read-only
	STATUS current
	DESCRIPTION "Flow ruleset statechanges (flags)"

	::={rulesetConnStatechangeFlags 1}

rulesetConnStatechangeFlagsMom	OBJECT-TYPE
	SYNTAX	 CounterBasedGauge64
	MAX-ACCESS read-only
	STATUS current
	DESCRIPTION "Flow ruleset statechanges (flags)"

	::={rulesetConnStatechangeFlags 2}

rulesetConnStatechangeFlagsMax	OBJECT-TYPE
	SYNTAX	 CounterBasedGauge64
	MAX-ACCESS read-only
	STATUS current
	DESCRIPTION "Flow ruleset statechanges (flags)"

	::={rulesetConnStatechangeFlags 3}

rulesetConnStatechangeFlagsLevelTable OBJECT-TYPE
	SYNTAX      SEQUENCE OF RulesetConnStatechangeFlagsLevelEntry
	MAX-ACCESS  not-accessible
	STATUS      current
	DESCRIPTION
	"Table for rulesetConnStatechangeFlags"
	::={rulesetConnStatechangeFlags 4}

rulesetConnStatechangeFlagsLevelEntry OBJECT-TYPE
	SYNTAX      RulesetConnStatechangeFlagsLevelEntry
	MAX-ACCESS  not-accessible
	STATUS      current
	DESCRIPTION
	"Table entry for rulesetConnStatechangeFlags"
	INDEX { rulesetConnStatechangeFlagsLevelName }
	::={rulesetConnStatechangeFlagsLevelTable 1}

RulesetConnStatechangeFlagsLevelEntry ::=
	SEQUENCE {
		rulesetConnStatechangeFlagsLevelName	DisplayString,
		rulesetConnStatechangeFlagsLevelVal	Counter64,
		rulesetConnStatechangeFlagsLevelMom	CounterBasedGauge64,
		rulesetConnStatechangeFlagsLevelMax	CounterBasedGauge64
	}

rulesetConnStatechangeFlagsLevelName OBJECT-TYPE
	SYNTAX      DisplayString
	MAX-ACCESS  not-accessible
	STATUS      current
	DESCRIPTION
	"Table entry display string for rulesetConnStatechangeFlags"
	::={rulesetConnStatechangeFlagsLevelEntry 1}

rulesetConnStatechangeFlagsLevelVal OBJECT-TYPE
	SYNTAX	 Counter64
	MAX-ACCESS  read-only
	STATUS      current
	DESCRIPTION
	"Table entry attribute for rulesetConnStatechangeFlags"
	::={rulesetConnStatechangeFlagsLevelEntry 2}

rulesetConnStatechangeFlagsLevelMom OBJECT-TYPE
	SYNTAX	 CounterBasedGauge64
	MAX-ACCESS  read-only
	STATUS      current
	DESCRIPTION
	"Table entry attribute for rulesetConnStatechangeFlags"
	::={rulesetConnStatechangeFlagsLevelEntry 3}

rulesetConnStatechangeFlagsLevelMax OBJECT-TYPE
	SYNTAX	 CounterBasedGauge64
	MAX-ACCESS  read-only
	STATUS      current
	DESCRIPTION
	"Table entry attribute for rulesetConnStatechangeFlags"
	::={rulesetConnStatechangeFlagsLevelEntry 4}


rulesetConnStatechangeAspath	OBJECT IDENTIFIER ::={ruleset 31}

rulesetConnStatechangeAspathVal	OBJECT-TYPE
	SYNTAX	 Counter64
	MAX-ACCESS read-only
	STATUS current
	DESCRIPTION "Flow ruleset statechanges (aspath)"

	::={rulesetConnStatechangeAspath 1}

rulesetConnStatechangeAspathMom	OBJECT-TYPE
	SYNTAX	 CounterBasedGauge64
	MAX-ACCESS read-only
	STATUS current
	DESCRIPTION "Flow ruleset statechanges (aspath)"

	::={rulesetConnStatechangeAspath 2}

rulesetConnStatechangeAspathMax	OBJECT-TYPE
	SYNTAX	 CounterBasedGauge64
	MAX-ACCESS read-only
	STATUS current
	DESCRIPTION "Flow ruleset statechanges (aspath)"

	::={rulesetConnStatechangeAspath 3}

rulesetConnStatechangeAspathLevelTable OBJECT-TYPE
	SYNTAX      SEQUENCE OF RulesetConnStatechangeAspathLevelEntry
	MAX-ACCESS  not-accessible
	STATUS      current
	DESCRIPTION
	"Table for rulesetConnStatechangeAspath"
	::={rulesetConnStatechangeAspath 4}

rulesetConnStatechangeAspathLevelEntry OBJECT-TYPE
	SYNTAX      RulesetConnStatechangeAspathLevelEntry
	MAX-ACCESS  not-accessible
	STATUS      current
	DESCRIPTION
	"Table entry for rulesetConnStatechangeAspath"
	INDEX { rulesetConnStatechangeAspathLevelName }
	::={rulesetConnStatechangeAspathLevelTable 1}

RulesetConnStatechangeAspathLevelEntry ::=
	SEQUENCE {
		rulesetConnStatechangeAspathLevelName	DisplayString,
		rulesetConnStatechangeAspathLevelVal	Counter64,
		rulesetConnStatechangeAspathLevelMom	CounterBasedGauge64,
		rulesetConnStatechangeAspathLevelMax	CounterBasedGauge64
	}

rulesetConnStatechangeAspathLevelName OBJECT-TYPE
	SYNTAX      DisplayString
	MAX-ACCESS  not-accessible
	STATUS      current
	DESCRIPTION
	"Table entry display string for rulesetConnStatechangeAspath"
	::={rulesetConnStatechangeAspathLevelEntry 1}

rulesetConnStatechangeAspathLevelVal OBJECT-TYPE
	SYNTAX	 Counter64
	MAX-ACCESS  read-only
	STATUS      current
	DESCRIPTION
	"Table entry attribute for rulesetConnStatechangeAspath"
	::={rulesetConnStatechangeAspathLevelEntry 2}

rulesetConnStatechangeAspathLevelMom OBJECT-TYPE
	SYNTAX	 CounterBasedGauge64
	MAX-ACCESS  read-only
	STATUS      current
	DESCRIPTION
	"Table entry attribute for rulesetConnStatechangeAspath"
	::={rulesetConnStatechangeAspathLevelEntry 3}

rulesetConnStatechangeAspathLevelMax OBJECT-TYPE
	SYNTAX	 CounterBasedGauge64
	MAX-ACCESS  read-only
	STATUS      current
	DESCRIPTION
	"Table entry attribute for rulesetConnStatechangeAspath"
	::={rulesetConnStatechangeAspathLevelEntry 4}


rulesetConnStatechangeLinklevel	OBJECT IDENTIFIER ::={ruleset 39}

rulesetConnStatechangeLinklevelVal	OBJECT-TYPE
	SYNTAX	 Counter64
	MAX-ACCESS read-only
	STATUS current
	DESCRIPTION "Flow ruleset statechanges (linklevel)"

	::={rulesetConnStatechangeLinklevel 1}

rulesetConnStatechangeLinklevelMom	OBJECT-TYPE
	SYNTAX	 CounterBasedGauge64
	MAX-ACCESS read-only
	STATUS current
	DESCRIPTION "Flow ruleset statechanges (linklevel)"

	::={rulesetConnStatechangeLinklevel 2}

rulesetConnStatechangeLinklevelMax	OBJECT-TYPE
	SYNTAX	 CounterBasedGauge64
	MAX-ACCESS read-only
	STATUS current
	DESCRIPTION "Flow ruleset statechanges (linklevel)"

	::={rulesetConnStatechangeLinklevel 3}

rulesetConnStatechangeLinklevelLevelTable OBJECT-TYPE
	SYNTAX      SEQUENCE OF RulesetConnStatechangeLinklevelLevelEntry
	MAX-ACCESS  not-accessible
	STATUS      current
	DESCRIPTION
	"Table for rulesetConnStatechangeLinklevel"
	::={rulesetConnStatechangeLinklevel 4}

rulesetConnStatechangeLinklevelLevelEntry OBJECT-TYPE
	SYNTAX      RulesetConnStatechangeLinklevelLevelEntry
	MAX-ACCESS  not-accessible
	STATUS      current
	DESCRIPTION
	"Table entry for rulesetConnStatechangeLinklevel"
	INDEX { rulesetConnStatechangeLinklevelLevelName }
	::={rulesetConnStatechangeLinklevelLevelTable 1}

RulesetConnStatechangeLinklevelLevelEntry ::=
	SEQUENCE {
		rulesetConnStatechangeLinklevelLevelName	DisplayString,
		rulesetConnStatechangeLinklevelLevelVal	Counter64,
		rulesetConnStatechangeLinklevelLevelMom	CounterBasedGauge64,
		rulesetConnStatechangeLinklevelLevelMax	CounterBasedGauge64
	}

rulesetConnStatechangeLinklevelLevelName OBJECT-TYPE
	SYNTAX      DisplayString
	MAX-ACCESS  not-accessible
	STATUS      current
	DESCRIPTION
	"Table entry display string for rulesetConnStatechangeLinklevel"
	::={rulesetConnStatechangeLinklevelLevelEntry 1}

rulesetConnStatechangeLinklevelLevelVal OBJECT-TYPE
	SYNTAX	 Counter64
	MAX-ACCESS  read-only
	STATUS      current
	DESCRIPTION
	"Table entry attribute for rulesetConnStatechangeLinklevel"
	::={rulesetConnStatechangeLinklevelLevelEntry 2}

rulesetConnStatechangeLinklevelLevelMom OBJECT-TYPE
	SYNTAX	 CounterBasedGauge64
	MAX-ACCESS  read-only
	STATUS      current
	DESCRIPTION
	"Table entry attribute for rulesetConnStatechangeLinklevel"
	::={rulesetConnStatechangeLinklevelLevelEntry 3}

rulesetConnStatechangeLinklevelLevelMax OBJECT-TYPE
	SYNTAX	 CounterBasedGauge64
	MAX-ACCESS  read-only
	STATUS      current
	DESCRIPTION
	"Table entry attribute for rulesetConnStatechangeLinklevel"
	::={rulesetConnStatechangeLinklevelLevelEntry 4}


rulesetContentLogicChange	OBJECT IDENTIFIER ::={ruleset 52}

rulesetContentLogicChangeVal	OBJECT-TYPE
	SYNTAX	 Counter64
	MAX-ACCESS read-only
	STATUS current
	DESCRIPTION "Flow ContentLogic statechanges"

	::={rulesetContentLogicChange 1}

rulesetContentLogicChangeMom	OBJECT-TYPE
	SYNTAX	 CounterBasedGauge64
	MAX-ACCESS read-only
	STATUS current
	DESCRIPTION "Flow ContentLogic statechanges"

	::={rulesetContentLogicChange 2}

rulesetContentLogicChangeMax	OBJECT-TYPE
	SYNTAX	 CounterBasedGauge64
	MAX-ACCESS read-only
	STATUS current
	DESCRIPTION "Flow ContentLogic statechanges"

	::={rulesetContentLogicChange 3}

rulesetContentLogicChangeLevelTable OBJECT-TYPE
	SYNTAX      SEQUENCE OF RulesetContentLogicChangeLevelEntry
	MAX-ACCESS  not-accessible
	STATUS      current
	DESCRIPTION
	"Table for rulesetContentLogicChange"
	::={rulesetContentLogicChange 4}

rulesetContentLogicChangeLevelEntry OBJECT-TYPE
	SYNTAX      RulesetContentLogicChangeLevelEntry
	MAX-ACCESS  not-accessible
	STATUS      current
	DESCRIPTION
	"Table entry for rulesetContentLogicChange"
	INDEX { rulesetContentLogicChangeLevelName }
	::={rulesetContentLogicChangeLevelTable 1}

RulesetContentLogicChangeLevelEntry ::=
	SEQUENCE {
		rulesetContentLogicChangeLevelName	DisplayString,
		rulesetContentLogicChangeLevelVal	Counter64,
		rulesetContentLogicChangeLevelMom	CounterBasedGauge64,
		rulesetContentLogicChangeLevelMax	CounterBasedGauge64
	}

rulesetContentLogicChangeLevelName OBJECT-TYPE
	SYNTAX      DisplayString
	MAX-ACCESS  not-accessible
	STATUS      current
	DESCRIPTION
	"Table entry display string for rulesetContentLogicChange"
	::={rulesetContentLogicChangeLevelEntry 1}

rulesetContentLogicChangeLevelVal OBJECT-TYPE
	SYNTAX	 Counter64
	MAX-ACCESS  read-only
	STATUS      current
	DESCRIPTION
	"Table entry attribute for rulesetContentLogicChange"
	::={rulesetContentLogicChangeLevelEntry 2}

rulesetContentLogicChangeLevelMom OBJECT-TYPE
	SYNTAX	 CounterBasedGauge64
	MAX-ACCESS  read-only
	STATUS      current
	DESCRIPTION
	"Table entry attribute for rulesetContentLogicChange"
	::={rulesetContentLogicChangeLevelEntry 3}

rulesetContentLogicChangeLevelMax OBJECT-TYPE
	SYNTAX	 CounterBasedGauge64
	MAX-ACCESS  read-only
	STATUS      current
	DESCRIPTION
	"Table entry attribute for rulesetContentLogicChange"
	::={rulesetContentLogicChangeLevelEntry 4}


rulesetConnStatechangeSC	OBJECT IDENTIFIER ::={ruleset 68}

rulesetConnStatechangeSCVal	OBJECT-TYPE
	SYNTAX	 Counter64
	MAX-ACCESS read-only
	STATUS current
	DESCRIPTION "Flow ruleset statechanges (Session context)"

	::={rulesetConnStatechangeSC 1}

rulesetConnStatechangeSCMom	OBJECT-TYPE
	SYNTAX	 CounterBasedGauge64
	MAX-ACCESS read-only
	STATUS current
	DESCRIPTION "Flow ruleset statechanges (Session context)"

	::={rulesetConnStatechangeSC 2}

rulesetConnStatechangeSCMax	OBJECT-TYPE
	SYNTAX	 CounterBasedGauge64
	MAX-ACCESS read-only
	STATUS current
	DESCRIPTION "Flow ruleset statechanges (Session context)"

	::={rulesetConnStatechangeSC 3}

rulesetConnStatechangeSCLevelTable OBJECT-TYPE
	SYNTAX      SEQUENCE OF RulesetConnStatechangeSCLevelEntry
	MAX-ACCESS  not-accessible
	STATUS      current
	DESCRIPTION
	"Table for rulesetConnStatechangeSC"
	::={rulesetConnStatechangeSC 4}

rulesetConnStatechangeSCLevelEntry OBJECT-TYPE
	SYNTAX      RulesetConnStatechangeSCLevelEntry
	MAX-ACCESS  not-accessible
	STATUS      current
	DESCRIPTION
	"Table entry for rulesetConnStatechangeSC"
	INDEX { rulesetConnStatechangeSCLevelName }
	::={rulesetConnStatechangeSCLevelTable 1}

RulesetConnStatechangeSCLevelEntry ::=
	SEQUENCE {
		rulesetConnStatechangeSCLevelName	DisplayString,
		rulesetConnStatechangeSCLevelVal	Counter64,
		rulesetConnStatechangeSCLevelMom	CounterBasedGauge64,
		rulesetConnStatechangeSCLevelMax	CounterBasedGauge64
	}

rulesetConnStatechangeSCLevelName OBJECT-TYPE
	SYNTAX      DisplayString
	MAX-ACCESS  not-accessible
	STATUS      current
	DESCRIPTION
	"Table entry display string for rulesetConnStatechangeSC"
	::={rulesetConnStatechangeSCLevelEntry 1}

rulesetConnStatechangeSCLevelVal OBJECT-TYPE
	SYNTAX	 Counter64
	MAX-ACCESS  read-only
	STATUS      current
	DESCRIPTION
	"Table entry attribute for rulesetConnStatechangeSC"
	::={rulesetConnStatechangeSCLevelEntry 2}

rulesetConnStatechangeSCLevelMom OBJECT-TYPE
	SYNTAX	 CounterBasedGauge64
	MAX-ACCESS  read-only
	STATUS      current
	DESCRIPTION
	"Table entry attribute for rulesetConnStatechangeSC"
	::={rulesetConnStatechangeSCLevelEntry 3}

rulesetConnStatechangeSCLevelMax OBJECT-TYPE
	SYNTAX	 CounterBasedGauge64
	MAX-ACCESS  read-only
	STATUS      current
	DESCRIPTION
	"Table entry attribute for rulesetConnStatechangeSC"
	::={rulesetConnStatechangeSCLevelEntry 4}


rulesetRecalcVersion	OBJECT IDENTIFIER ::={ruleset 32}

rulesetRecalcVersionVal	OBJECT-TYPE
	SYNTAX	 Counter64
	MAX-ACCESS read-only
	STATUS current
	DESCRIPTION "Flow ruleset recalcs from version"

	::={rulesetRecalcVersion 1}

rulesetRecalcVersionMom	OBJECT-TYPE
	SYNTAX	 CounterBasedGauge64
	MAX-ACCESS read-only
	STATUS current
	DESCRIPTION "Flow ruleset recalcs from version"

	::={rulesetRecalcVersion 2}

rulesetRecalcVersionMax	OBJECT-TYPE
	SYNTAX	 CounterBasedGauge64
	MAX-ACCESS read-only
	STATUS current
	DESCRIPTION "Flow ruleset recalcs from version"

	::={rulesetRecalcVersion 3}

rulesetRecalcVersionLevelTable OBJECT-TYPE
	SYNTAX      SEQUENCE OF RulesetRecalcVersionLevelEntry
	MAX-ACCESS  not-accessible
	STATUS      current
	DESCRIPTION
	"Table for rulesetRecalcVersion"
	::={rulesetRecalcVersion 4}

rulesetRecalcVersionLevelEntry OBJECT-TYPE
	SYNTAX      RulesetRecalcVersionLevelEntry
	MAX-ACCESS  not-accessible
	STATUS      current
	DESCRIPTION
	"Table entry for rulesetRecalcVersion"
	INDEX { rulesetRecalcVersionLevelName }
	::={rulesetRecalcVersionLevelTable 1}

RulesetRecalcVersionLevelEntry ::=
	SEQUENCE {
		rulesetRecalcVersionLevelName	DisplayString,
		rulesetRecalcVersionLevelVal	Counter64,
		rulesetRecalcVersionLevelMom	CounterBasedGauge64,
		rulesetRecalcVersionLevelMax	CounterBasedGauge64
	}

rulesetRecalcVersionLevelName OBJECT-TYPE
	SYNTAX      DisplayString
	MAX-ACCESS  not-accessible
	STATUS      current
	DESCRIPTION
	"Table entry display string for rulesetRecalcVersion"
	::={rulesetRecalcVersionLevelEntry 1}

rulesetRecalcVersionLevelVal OBJECT-TYPE
	SYNTAX	 Counter64
	MAX-ACCESS  read-only
	STATUS      current
	DESCRIPTION
	"Table entry attribute for rulesetRecalcVersion"
	::={rulesetRecalcVersionLevelEntry 2}

rulesetRecalcVersionLevelMom OBJECT-TYPE
	SYNTAX	 CounterBasedGauge64
	MAX-ACCESS  read-only
	STATUS      current
	DESCRIPTION
	"Table entry attribute for rulesetRecalcVersion"
	::={rulesetRecalcVersionLevelEntry 3}

rulesetRecalcVersionLevelMax OBJECT-TYPE
	SYNTAX	 CounterBasedGauge64
	MAX-ACCESS  read-only
	STATUS      current
	DESCRIPTION
	"Table entry attribute for rulesetRecalcVersion"
	::={rulesetRecalcVersionLevelEntry 4}


rulesetRecalcTime	OBJECT IDENTIFIER ::={ruleset 33}

rulesetRecalcTimeVal	OBJECT-TYPE
	SYNTAX	 Counter64
	MAX-ACCESS read-only
	STATUS current
	DESCRIPTION "Flow ruleset recalcs from time"

	::={rulesetRecalcTime 1}

rulesetRecalcTimeMom	OBJECT-TYPE
	SYNTAX	 CounterBasedGauge64
	MAX-ACCESS read-only
	STATUS current
	DESCRIPTION "Flow ruleset recalcs from time"

	::={rulesetRecalcTime 2}

rulesetRecalcTimeMax	OBJECT-TYPE
	SYNTAX	 CounterBasedGauge64
	MAX-ACCESS read-only
	STATUS current
	DESCRIPTION "Flow ruleset recalcs from time"

	::={rulesetRecalcTime 3}

rulesetRecalcTimeLevelTable OBJECT-TYPE
	SYNTAX      SEQUENCE OF RulesetRecalcTimeLevelEntry
	MAX-ACCESS  not-accessible
	STATUS      current
	DESCRIPTION
	"Table for rulesetRecalcTime"
	::={rulesetRecalcTime 4}

rulesetRecalcTimeLevelEntry OBJECT-TYPE
	SYNTAX      RulesetRecalcTimeLevelEntry
	MAX-ACCESS  not-accessible
	STATUS      current
	DESCRIPTION
	"Table entry for rulesetRecalcTime"
	INDEX { rulesetRecalcTimeLevelName }
	::={rulesetRecalcTimeLevelTable 1}

RulesetRecalcTimeLevelEntry ::=
	SEQUENCE {
		rulesetRecalcTimeLevelName	DisplayString,
		rulesetRecalcTimeLevelVal	Counter64,
		rulesetRecalcTimeLevelMom	CounterBasedGauge64,
		rulesetRecalcTimeLevelMax	CounterBasedGauge64
	}

rulesetRecalcTimeLevelName OBJECT-TYPE
	SYNTAX      DisplayString
	MAX-ACCESS  not-accessible
	STATUS      current
	DESCRIPTION
	"Table entry display string for rulesetRecalcTime"
	::={rulesetRecalcTimeLevelEntry 1}

rulesetRecalcTimeLevelVal OBJECT-TYPE
	SYNTAX	 Counter64
	MAX-ACCESS  read-only
	STATUS      current
	DESCRIPTION
	"Table entry attribute for rulesetRecalcTime"
	::={rulesetRecalcTimeLevelEntry 2}

rulesetRecalcTimeLevelMom OBJECT-TYPE
	SYNTAX	 CounterBasedGauge64
	MAX-ACCESS  read-only
	STATUS      current
	DESCRIPTION
	"Table entry attribute for rulesetRecalcTime"
	::={rulesetRecalcTimeLevelEntry 3}

rulesetRecalcTimeLevelMax OBJECT-TYPE
	SYNTAX	 CounterBasedGauge64
	MAX-ACCESS  read-only
	STATUS      current
	DESCRIPTION
	"Table entry attribute for rulesetRecalcTime"
	::={rulesetRecalcTimeLevelEntry 4}


rulesetRecalcBgp	OBJECT IDENTIFIER ::={ruleset 34}

rulesetRecalcBgpVal	OBJECT-TYPE
	SYNTAX	 Counter64
	MAX-ACCESS read-only
	STATUS current
	DESCRIPTION "Flow ruleset recalcs from bgp"

	::={rulesetRecalcBgp 1}

rulesetRecalcBgpMom	OBJECT-TYPE
	SYNTAX	 CounterBasedGauge64
	MAX-ACCESS read-only
	STATUS current
	DESCRIPTION "Flow ruleset recalcs from bgp"

	::={rulesetRecalcBgp 2}

rulesetRecalcBgpMax	OBJECT-TYPE
	SYNTAX	 CounterBasedGauge64
	MAX-ACCESS read-only
	STATUS current
	DESCRIPTION "Flow ruleset recalcs from bgp"

	::={rulesetRecalcBgp 3}

rulesetRecalcBgpLevelTable OBJECT-TYPE
	SYNTAX      SEQUENCE OF RulesetRecalcBgpLevelEntry
	MAX-ACCESS  not-accessible
	STATUS      current
	DESCRIPTION
	"Table for rulesetRecalcBgp"
	::={rulesetRecalcBgp 4}

rulesetRecalcBgpLevelEntry OBJECT-TYPE
	SYNTAX      RulesetRecalcBgpLevelEntry
	MAX-ACCESS  not-accessible
	STATUS      current
	DESCRIPTION
	"Table entry for rulesetRecalcBgp"
	INDEX { rulesetRecalcBgpLevelName }
	::={rulesetRecalcBgpLevelTable 1}

RulesetRecalcBgpLevelEntry ::=
	SEQUENCE {
		rulesetRecalcBgpLevelName	DisplayString,
		rulesetRecalcBgpLevelVal	Counter64,
		rulesetRecalcBgpLevelMom	CounterBasedGauge64,
		rulesetRecalcBgpLevelMax	CounterBasedGauge64
	}

rulesetRecalcBgpLevelName OBJECT-TYPE
	SYNTAX      DisplayString
	MAX-ACCESS  not-accessible
	STATUS      current
	DESCRIPTION
	"Table entry display string for rulesetRecalcBgp"
	::={rulesetRecalcBgpLevelEntry 1}

rulesetRecalcBgpLevelVal OBJECT-TYPE
	SYNTAX	 Counter64
	MAX-ACCESS  read-only
	STATUS      current
	DESCRIPTION
	"Table entry attribute for rulesetRecalcBgp"
	::={rulesetRecalcBgpLevelEntry 2}

rulesetRecalcBgpLevelMom OBJECT-TYPE
	SYNTAX	 CounterBasedGauge64
	MAX-ACCESS  read-only
	STATUS      current
	DESCRIPTION
	"Table entry attribute for rulesetRecalcBgp"
	::={rulesetRecalcBgpLevelEntry 3}

rulesetRecalcBgpLevelMax OBJECT-TYPE
	SYNTAX	 CounterBasedGauge64
	MAX-ACCESS  read-only
	STATUS      current
	DESCRIPTION
	"Table entry attribute for rulesetRecalcBgp"
	::={rulesetRecalcBgpLevelEntry 4}


rulesetRecalcUnknown	OBJECT IDENTIFIER ::={ruleset 35}

rulesetRecalcUnknownVal	OBJECT-TYPE
	SYNTAX	 Counter64
	MAX-ACCESS read-only
	STATUS current
	DESCRIPTION "Flow ruleset recalcs from state"

	::={rulesetRecalcUnknown 1}

rulesetRecalcUnknownMom	OBJECT-TYPE
	SYNTAX	 CounterBasedGauge64
	MAX-ACCESS read-only
	STATUS current
	DESCRIPTION "Flow ruleset recalcs from state"

	::={rulesetRecalcUnknown 2}

rulesetRecalcUnknownMax	OBJECT-TYPE
	SYNTAX	 CounterBasedGauge64
	MAX-ACCESS read-only
	STATUS current
	DESCRIPTION "Flow ruleset recalcs from state"

	::={rulesetRecalcUnknown 3}

rulesetRecalcUnknownLevelTable OBJECT-TYPE
	SYNTAX      SEQUENCE OF RulesetRecalcUnknownLevelEntry
	MAX-ACCESS  not-accessible
	STATUS      current
	DESCRIPTION
	"Table for rulesetRecalcUnknown"
	::={rulesetRecalcUnknown 4}

rulesetRecalcUnknownLevelEntry OBJECT-TYPE
	SYNTAX      RulesetRecalcUnknownLevelEntry
	MAX-ACCESS  not-accessible
	STATUS      current
	DESCRIPTION
	"Table entry for rulesetRecalcUnknown"
	INDEX { rulesetRecalcUnknownLevelName }
	::={rulesetRecalcUnknownLevelTable 1}

RulesetRecalcUnknownLevelEntry ::=
	SEQUENCE {
		rulesetRecalcUnknownLevelName	DisplayString,
		rulesetRecalcUnknownLevelVal	Counter64,
		rulesetRecalcUnknownLevelMom	CounterBasedGauge64,
		rulesetRecalcUnknownLevelMax	CounterBasedGauge64
	}

rulesetRecalcUnknownLevelName OBJECT-TYPE
	SYNTAX      DisplayString
	MAX-ACCESS  not-accessible
	STATUS      current
	DESCRIPTION
	"Table entry display string for rulesetRecalcUnknown"
	::={rulesetRecalcUnknownLevelEntry 1}

rulesetRecalcUnknownLevelVal OBJECT-TYPE
	SYNTAX	 Counter64
	MAX-ACCESS  read-only
	STATUS      current
	DESCRIPTION
	"Table entry attribute for rulesetRecalcUnknown"
	::={rulesetRecalcUnknownLevelEntry 2}

rulesetRecalcUnknownLevelMom OBJECT-TYPE
	SYNTAX	 CounterBasedGauge64
	MAX-ACCESS  read-only
	STATUS      current
	DESCRIPTION
	"Table entry attribute for rulesetRecalcUnknown"
	::={rulesetRecalcUnknownLevelEntry 3}

rulesetRecalcUnknownLevelMax OBJECT-TYPE
	SYNTAX	 CounterBasedGauge64
	MAX-ACCESS  read-only
	STATUS      current
	DESCRIPTION
	"Table entry attribute for rulesetRecalcUnknown"
	::={rulesetRecalcUnknownLevelEntry 4}


rulesetOutdatedService	OBJECT IDENTIFIER ::={ruleset 36}

rulesetOutdatedServiceVal	OBJECT-TYPE
	SYNTAX	 Counter64
	MAX-ACCESS read-only
	STATUS obsolete
	DESCRIPTION "Ruleset recalcs with outdated service ruleset"

	::={rulesetOutdatedService 1}

rulesetOutdatedServiceMom	OBJECT-TYPE
	SYNTAX	 CounterBasedGauge64
	MAX-ACCESS read-only
	STATUS obsolete
	DESCRIPTION "Ruleset recalcs with outdated service ruleset"

	::={rulesetOutdatedService 2}

rulesetOutdatedServiceMax	OBJECT-TYPE
	SYNTAX	 CounterBasedGauge64
	MAX-ACCESS read-only
	STATUS obsolete
	DESCRIPTION "Ruleset recalcs with outdated service ruleset"

	::={rulesetOutdatedService 3}

rulesetOutdatedServiceLevelTable OBJECT-TYPE
	SYNTAX      SEQUENCE OF RulesetOutdatedServiceLevelEntry
	MAX-ACCESS  not-accessible
	STATUS      current
	DESCRIPTION
	"Table for rulesetOutdatedService"
	::={rulesetOutdatedService 4}

rulesetOutdatedServiceLevelEntry OBJECT-TYPE
	SYNTAX      RulesetOutdatedServiceLevelEntry
	MAX-ACCESS  not-accessible
	STATUS      current
	DESCRIPTION
	"Table entry for rulesetOutdatedService"
	INDEX { rulesetOutdatedServiceLevelName }
	::={rulesetOutdatedServiceLevelTable 1}

RulesetOutdatedServiceLevelEntry ::=
	SEQUENCE {
		rulesetOutdatedServiceLevelName	DisplayString,
		rulesetOutdatedServiceLevelVal	Counter64,
		rulesetOutdatedServiceLevelMom	CounterBasedGauge64,
		rulesetOutdatedServiceLevelMax	CounterBasedGauge64
	}

rulesetOutdatedServiceLevelName OBJECT-TYPE
	SYNTAX      DisplayString
	MAX-ACCESS  not-accessible
	STATUS      current
	DESCRIPTION
	"Table entry display string for rulesetOutdatedService"
	::={rulesetOutdatedServiceLevelEntry 1}

rulesetOutdatedServiceLevelVal OBJECT-TYPE
	SYNTAX	 Counter64
	MAX-ACCESS  read-only
	STATUS      current
	DESCRIPTION
	"Table entry attribute for rulesetOutdatedService"
	::={rulesetOutdatedServiceLevelEntry 2}

rulesetOutdatedServiceLevelMom OBJECT-TYPE
	SYNTAX	 CounterBasedGauge64
	MAX-ACCESS  read-only
	STATUS      current
	DESCRIPTION
	"Table entry attribute for rulesetOutdatedService"
	::={rulesetOutdatedServiceLevelEntry 3}

rulesetOutdatedServiceLevelMax OBJECT-TYPE
	SYNTAX	 CounterBasedGauge64
	MAX-ACCESS  read-only
	STATUS      current
	DESCRIPTION
	"Table entry attribute for rulesetOutdatedService"
	::={rulesetOutdatedServiceLevelEntry 4}


rulesetSubscriberEntries	OBJECT IDENTIFIER ::={ruleset 37}

rulesetSubscriberEntriesVal	OBJECT-TYPE
	SYNTAX	 CounterBasedGauge64
	MAX-ACCESS read-only
	STATUS current
	DESCRIPTION "Subscriber: Entries (netobjid, ipprefix)-pairs in storage in engine"

	::={rulesetSubscriberEntries 1}

rulesetSubscriberEntriesMax	OBJECT-TYPE
	SYNTAX	 CounterBasedGauge64
	MAX-ACCESS read-only
	STATUS current
	DESCRIPTION "Subscriber: Entries (netobjid, ipprefix)-pairs in storage in engine"

	::={rulesetSubscriberEntries 3}

rulesetSubscriberEntriesLevelTable OBJECT-TYPE
	SYNTAX      SEQUENCE OF RulesetSubscriberEntriesLevelEntry
	MAX-ACCESS  not-accessible
	STATUS      current
	DESCRIPTION
	"Table for rulesetSubscriberEntries"
	::={rulesetSubscriberEntries 4}

rulesetSubscriberEntriesLevelEntry OBJECT-TYPE
	SYNTAX      RulesetSubscriberEntriesLevelEntry
	MAX-ACCESS  not-accessible
	STATUS      current
	DESCRIPTION
	"Table entry for rulesetSubscriberEntries"
	INDEX { rulesetSubscriberEntriesLevelName }
	::={rulesetSubscriberEntriesLevelTable 1}

RulesetSubscriberEntriesLevelEntry ::=
	SEQUENCE {
		rulesetSubscriberEntriesLevelName	DisplayString,
		rulesetSubscriberEntriesLevelVal	CounterBasedGauge64,
		rulesetSubscriberEntriesLevelMax	CounterBasedGauge64
	}

rulesetSubscriberEntriesLevelName OBJECT-TYPE
	SYNTAX      DisplayString
	MAX-ACCESS  not-accessible
	STATUS      current
	DESCRIPTION
	"Table entry display string for rulesetSubscriberEntries"
	::={rulesetSubscriberEntriesLevelEntry 1}

rulesetSubscriberEntriesLevelVal OBJECT-TYPE
	SYNTAX	 CounterBasedGauge64
	MAX-ACCESS  read-only
	STATUS      current
	DESCRIPTION
	"Table entry attribute for rulesetSubscriberEntries"
	::={rulesetSubscriberEntriesLevelEntry 2}

rulesetSubscriberEntriesLevelMax OBJECT-TYPE
	SYNTAX	 CounterBasedGauge64
	MAX-ACCESS  read-only
	STATUS      current
	DESCRIPTION
	"Table entry attribute for rulesetSubscriberEntries"
	::={rulesetSubscriberEntriesLevelEntry 4}


rulesetSubscriberOpers	OBJECT IDENTIFIER ::={ruleset 59}

rulesetSubscriberOpersVal	OBJECT-TYPE
	SYNTAX	 Counter64
	MAX-ACCESS read-only
	STATUS current
	DESCRIPTION "Subscriber: Number of operations sent to engine"

	::={rulesetSubscriberOpers 1}

rulesetSubscriberOpersMom	OBJECT-TYPE
	SYNTAX	 CounterBasedGauge64
	MAX-ACCESS read-only
	STATUS current
	DESCRIPTION "Subscriber: Number of operations sent to engine"

	::={rulesetSubscriberOpers 2}

rulesetSubscriberOpersMax	OBJECT-TYPE
	SYNTAX	 CounterBasedGauge64
	MAX-ACCESS read-only
	STATUS current
	DESCRIPTION "Subscriber: Number of operations sent to engine"

	::={rulesetSubscriberOpers 3}

rulesetSubscriberOpersLevelTable OBJECT-TYPE
	SYNTAX      SEQUENCE OF RulesetSubscriberOpersLevelEntry
	MAX-ACCESS  not-accessible
	STATUS      current
	DESCRIPTION
	"Table for rulesetSubscriberOpers"
	::={rulesetSubscriberOpers 4}

rulesetSubscriberOpersLevelEntry OBJECT-TYPE
	SYNTAX      RulesetSubscriberOpersLevelEntry
	MAX-ACCESS  not-accessible
	STATUS      current
	DESCRIPTION
	"Table entry for rulesetSubscriberOpers"
	INDEX { rulesetSubscriberOpersLevelName }
	::={rulesetSubscriberOpersLevelTable 1}

RulesetSubscriberOpersLevelEntry ::=
	SEQUENCE {
		rulesetSubscriberOpersLevelName	DisplayString,
		rulesetSubscriberOpersLevelVal	Counter64,
		rulesetSubscriberOpersLevelMom	CounterBasedGauge64,
		rulesetSubscriberOpersLevelMax	CounterBasedGauge64
	}

rulesetSubscriberOpersLevelName OBJECT-TYPE
	SYNTAX      DisplayString
	MAX-ACCESS  not-accessible
	STATUS      current
	DESCRIPTION
	"Table entry display string for rulesetSubscriberOpers"
	::={rulesetSubscriberOpersLevelEntry 1}

rulesetSubscriberOpersLevelVal OBJECT-TYPE
	SYNTAX	 Counter64
	MAX-ACCESS  read-only
	STATUS      current
	DESCRIPTION
	"Table entry attribute for rulesetSubscriberOpers"
	::={rulesetSubscriberOpersLevelEntry 2}

rulesetSubscriberOpersLevelMom OBJECT-TYPE
	SYNTAX	 CounterBasedGauge64
	MAX-ACCESS  read-only
	STATUS      current
	DESCRIPTION
	"Table entry attribute for rulesetSubscriberOpers"
	::={rulesetSubscriberOpersLevelEntry 3}

rulesetSubscriberOpersLevelMax OBJECT-TYPE
	SYNTAX	 CounterBasedGauge64
	MAX-ACCESS  read-only
	STATUS      current
	DESCRIPTION
	"Table entry attribute for rulesetSubscriberOpers"
	::={rulesetSubscriberOpersLevelEntry 4}


rulesetSubscriberFull	OBJECT IDENTIFIER ::={ruleset 40}

rulesetSubscriberFullVal	OBJECT-TYPE
	SYNTAX	 Counter64
	MAX-ACCESS read-only
	STATUS current
	DESCRIPTION "Subscriber: Storage in engine is full"

	::={rulesetSubscriberFull 1}

rulesetSubscriberFullMom	OBJECT-TYPE
	SYNTAX	 CounterBasedGauge64
	MAX-ACCESS read-only
	STATUS current
	DESCRIPTION "Subscriber: Storage in engine is full"

	::={rulesetSubscriberFull 2}

rulesetSubscriberFullMax	OBJECT-TYPE
	SYNTAX	 CounterBasedGauge64
	MAX-ACCESS read-only
	STATUS current
	DESCRIPTION "Subscriber: Storage in engine is full"

	::={rulesetSubscriberFull 3}

rulesetSubscriberFullLevelTable OBJECT-TYPE
	SYNTAX      SEQUENCE OF RulesetSubscriberFullLevelEntry
	MAX-ACCESS  not-accessible
	STATUS      current
	DESCRIPTION
	"Table for rulesetSubscriberFull"
	::={rulesetSubscriberFull 4}

rulesetSubscriberFullLevelEntry OBJECT-TYPE
	SYNTAX      RulesetSubscriberFullLevelEntry
	MAX-ACCESS  not-accessible
	STATUS      current
	DESCRIPTION
	"Table entry for rulesetSubscriberFull"
	INDEX { rulesetSubscriberFullLevelName }
	::={rulesetSubscriberFullLevelTable 1}

RulesetSubscriberFullLevelEntry ::=
	SEQUENCE {
		rulesetSubscriberFullLevelName	DisplayString,
		rulesetSubscriberFullLevelVal	Counter64,
		rulesetSubscriberFullLevelMom	CounterBasedGauge64,
		rulesetSubscriberFullLevelMax	CounterBasedGauge64
	}

rulesetSubscriberFullLevelName OBJECT-TYPE
	SYNTAX      DisplayString
	MAX-ACCESS  not-accessible
	STATUS      current
	DESCRIPTION
	"Table entry display string for rulesetSubscriberFull"
	::={rulesetSubscriberFullLevelEntry 1}

rulesetSubscriberFullLevelVal OBJECT-TYPE
	SYNTAX	 Counter64
	MAX-ACCESS  read-only
	STATUS      current
	DESCRIPTION
	"Table entry attribute for rulesetSubscriberFull"
	::={rulesetSubscriberFullLevelEntry 2}

rulesetSubscriberFullLevelMom OBJECT-TYPE
	SYNTAX	 CounterBasedGauge64
	MAX-ACCESS  read-only
	STATUS      current
	DESCRIPTION
	"Table entry attribute for rulesetSubscriberFull"
	::={rulesetSubscriberFullLevelEntry 3}

rulesetSubscriberFullLevelMax OBJECT-TYPE
	SYNTAX	 CounterBasedGauge64
	MAX-ACCESS  read-only
	STATUS      current
	DESCRIPTION
	"Table entry attribute for rulesetSubscriberFull"
	::={rulesetSubscriberFullLevelEntry 4}


rulesetSubscriberError	OBJECT IDENTIFIER ::={ruleset 58}

rulesetSubscriberErrorVal	OBJECT-TYPE
	SYNTAX	 Counter64
	MAX-ACCESS read-only
	STATUS current
	DESCRIPTION "Subscriber: Parsing/handling errors in engine"

	::={rulesetSubscriberError 1}

rulesetSubscriberErrorMom	OBJECT-TYPE
	SYNTAX	 CounterBasedGauge64
	MAX-ACCESS read-only
	STATUS current
	DESCRIPTION "Subscriber: Parsing/handling errors in engine"

	::={rulesetSubscriberError 2}

rulesetSubscriberErrorMax	OBJECT-TYPE
	SYNTAX	 CounterBasedGauge64
	MAX-ACCESS read-only
	STATUS current
	DESCRIPTION "Subscriber: Parsing/handling errors in engine"

	::={rulesetSubscriberError 3}

rulesetSubscriberErrorLevelTable OBJECT-TYPE
	SYNTAX      SEQUENCE OF RulesetSubscriberErrorLevelEntry
	MAX-ACCESS  not-accessible
	STATUS      current
	DESCRIPTION
	"Table for rulesetSubscriberError"
	::={rulesetSubscriberError 4}

rulesetSubscriberErrorLevelEntry OBJECT-TYPE
	SYNTAX      RulesetSubscriberErrorLevelEntry
	MAX-ACCESS  not-accessible
	STATUS      current
	DESCRIPTION
	"Table entry for rulesetSubscriberError"
	INDEX { rulesetSubscriberErrorLevelName }
	::={rulesetSubscriberErrorLevelTable 1}

RulesetSubscriberErrorLevelEntry ::=
	SEQUENCE {
		rulesetSubscriberErrorLevelName	DisplayString,
		rulesetSubscriberErrorLevelVal	Counter64,
		rulesetSubscriberErrorLevelMom	CounterBasedGauge64,
		rulesetSubscriberErrorLevelMax	CounterBasedGauge64
	}

rulesetSubscriberErrorLevelName OBJECT-TYPE
	SYNTAX      DisplayString
	MAX-ACCESS  not-accessible
	STATUS      current
	DESCRIPTION
	"Table entry display string for rulesetSubscriberError"
	::={rulesetSubscriberErrorLevelEntry 1}

rulesetSubscriberErrorLevelVal OBJECT-TYPE
	SYNTAX	 Counter64
	MAX-ACCESS  read-only
	STATUS      current
	DESCRIPTION
	"Table entry attribute for rulesetSubscriberError"
	::={rulesetSubscriberErrorLevelEntry 2}

rulesetSubscriberErrorLevelMom OBJECT-TYPE
	SYNTAX	 CounterBasedGauge64
	MAX-ACCESS  read-only
	STATUS      current
	DESCRIPTION
	"Table entry attribute for rulesetSubscriberError"
	::={rulesetSubscriberErrorLevelEntry 3}

rulesetSubscriberErrorLevelMax OBJECT-TYPE
	SYNTAX	 CounterBasedGauge64
	MAX-ACCESS  read-only
	STATUS      current
	DESCRIPTION
	"Table entry attribute for rulesetSubscriberError"
	::={rulesetSubscriberErrorLevelEntry 4}


rulesetSubscriberNonexistent	OBJECT IDENTIFIER ::={ruleset 43}

rulesetSubscriberNonexistentVal	OBJECT-TYPE
	SYNTAX	 Counter64
	MAX-ACCESS read-only
	STATUS current
	DESCRIPTION "Subscriber: Split on unknown subscriber"

	::={rulesetSubscriberNonexistent 1}

rulesetSubscriberNonexistentMom	OBJECT-TYPE
	SYNTAX	 CounterBasedGauge64
	MAX-ACCESS read-only
	STATUS current
	DESCRIPTION "Subscriber: Split on unknown subscriber"

	::={rulesetSubscriberNonexistent 2}

rulesetSubscriberNonexistentMax	OBJECT-TYPE
	SYNTAX	 CounterBasedGauge64
	MAX-ACCESS read-only
	STATUS current
	DESCRIPTION "Subscriber: Split on unknown subscriber"

	::={rulesetSubscriberNonexistent 3}

rulesetSubscriberNonexistentLevelTable OBJECT-TYPE
	SYNTAX      SEQUENCE OF RulesetSubscriberNonexistentLevelEntry
	MAX-ACCESS  not-accessible
	STATUS      current
	DESCRIPTION
	"Table for rulesetSubscriberNonexistent"
	::={rulesetSubscriberNonexistent 4}

rulesetSubscriberNonexistentLevelEntry OBJECT-TYPE
	SYNTAX      RulesetSubscriberNonexistentLevelEntry
	MAX-ACCESS  not-accessible
	STATUS      current
	DESCRIPTION
	"Table entry for rulesetSubscriberNonexistent"
	INDEX { rulesetSubscriberNonexistentLevelName }
	::={rulesetSubscriberNonexistentLevelTable 1}

RulesetSubscriberNonexistentLevelEntry ::=
	SEQUENCE {
		rulesetSubscriberNonexistentLevelName	DisplayString,
		rulesetSubscriberNonexistentLevelVal	Counter64,
		rulesetSubscriberNonexistentLevelMom	CounterBasedGauge64,
		rulesetSubscriberNonexistentLevelMax	CounterBasedGauge64
	}

rulesetSubscriberNonexistentLevelName OBJECT-TYPE
	SYNTAX      DisplayString
	MAX-ACCESS  not-accessible
	STATUS      current
	DESCRIPTION
	"Table entry display string for rulesetSubscriberNonexistent"
	::={rulesetSubscriberNonexistentLevelEntry 1}

rulesetSubscriberNonexistentLevelVal OBJECT-TYPE
	SYNTAX	 Counter64
	MAX-ACCESS  read-only
	STATUS      current
	DESCRIPTION
	"Table entry attribute for rulesetSubscriberNonexistent"
	::={rulesetSubscriberNonexistentLevelEntry 2}

rulesetSubscriberNonexistentLevelMom OBJECT-TYPE
	SYNTAX	 CounterBasedGauge64
	MAX-ACCESS  read-only
	STATUS      current
	DESCRIPTION
	"Table entry attribute for rulesetSubscriberNonexistent"
	::={rulesetSubscriberNonexistentLevelEntry 3}

rulesetSubscriberNonexistentLevelMax OBJECT-TYPE
	SYNTAX	 CounterBasedGauge64
	MAX-ACCESS  read-only
	STATUS      current
	DESCRIPTION
	"Table entry attribute for rulesetSubscriberNonexistent"
	::={rulesetSubscriberNonexistentLevelEntry 4}


rulesetSessionContextNonexistent	OBJECT IDENTIFIER ::={ruleset 44}

rulesetSessionContextNonexistentVal	OBJECT-TYPE
	SYNTAX	 Counter64
	MAX-ACCESS read-only
	STATUS current
	DESCRIPTION "Subscriber: Split on unknown sessioncontext"

	::={rulesetSessionContextNonexistent 1}

rulesetSessionContextNonexistentMom	OBJECT-TYPE
	SYNTAX	 CounterBasedGauge64
	MAX-ACCESS read-only
	STATUS current
	DESCRIPTION "Subscriber: Split on unknown sessioncontext"

	::={rulesetSessionContextNonexistent 2}

rulesetSessionContextNonexistentMax	OBJECT-TYPE
	SYNTAX	 CounterBasedGauge64
	MAX-ACCESS read-only
	STATUS current
	DESCRIPTION "Subscriber: Split on unknown sessioncontext"

	::={rulesetSessionContextNonexistent 3}

rulesetSessionContextNonexistentLevelTable OBJECT-TYPE
	SYNTAX      SEQUENCE OF RulesetSessionContextNonexistentLevelEntry
	MAX-ACCESS  not-accessible
	STATUS      current
	DESCRIPTION
	"Table for rulesetSessionContextNonexistent"
	::={rulesetSessionContextNonexistent 4}

rulesetSessionContextNonexistentLevelEntry OBJECT-TYPE
	SYNTAX      RulesetSessionContextNonexistentLevelEntry
	MAX-ACCESS  not-accessible
	STATUS      current
	DESCRIPTION
	"Table entry for rulesetSessionContextNonexistent"
	INDEX { rulesetSessionContextNonexistentLevelName }
	::={rulesetSessionContextNonexistentLevelTable 1}

RulesetSessionContextNonexistentLevelEntry ::=
	SEQUENCE {
		rulesetSessionContextNonexistentLevelName	DisplayString,
		rulesetSessionContextNonexistentLevelVal	Counter64,
		rulesetSessionContextNonexistentLevelMom	CounterBasedGauge64,
		rulesetSessionContextNonexistentLevelMax	CounterBasedGauge64
	}

rulesetSessionContextNonexistentLevelName OBJECT-TYPE
	SYNTAX      DisplayString
	MAX-ACCESS  not-accessible
	STATUS      current
	DESCRIPTION
	"Table entry display string for rulesetSessionContextNonexistent"
	::={rulesetSessionContextNonexistentLevelEntry 1}

rulesetSessionContextNonexistentLevelVal OBJECT-TYPE
	SYNTAX	 Counter64
	MAX-ACCESS  read-only
	STATUS      current
	DESCRIPTION
	"Table entry attribute for rulesetSessionContextNonexistent"
	::={rulesetSessionContextNonexistentLevelEntry 2}

rulesetSessionContextNonexistentLevelMom OBJECT-TYPE
	SYNTAX	 CounterBasedGauge64
	MAX-ACCESS  read-only
	STATUS      current
	DESCRIPTION
	"Table entry attribute for rulesetSessionContextNonexistent"
	::={rulesetSessionContextNonexistentLevelEntry 3}

rulesetSessionContextNonexistentLevelMax OBJECT-TYPE
	SYNTAX	 CounterBasedGauge64
	MAX-ACCESS  read-only
	STATUS      current
	DESCRIPTION
	"Table entry attribute for rulesetSessionContextNonexistent"
	::={rulesetSessionContextNonexistentLevelEntry 4}


rulesetDynSubscriberUsedPlens	OBJECT IDENTIFIER ::={ruleset 51}

rulesetDynSubscriberUsedPlensVal	OBJECT-TYPE
	SYNTAX	 CounterBasedGauge64
	MAX-ACCESS read-only
	STATUS obsolete
	DESCRIPTION "Different number of prefix lengths used for dynamic IPv4 subscribers"

	::={rulesetDynSubscriberUsedPlens 1}

rulesetDynSubscriberUsedPlensMax	OBJECT-TYPE
	SYNTAX	 CounterBasedGauge64
	MAX-ACCESS read-only
	STATUS obsolete
	DESCRIPTION "Different number of prefix lengths used for dynamic IPv4 subscribers"

	::={rulesetDynSubscriberUsedPlens 3}

rulesetDynSubscriberUsedPlensLevelTable OBJECT-TYPE
	SYNTAX      SEQUENCE OF RulesetDynSubscriberUsedPlensLevelEntry
	MAX-ACCESS  not-accessible
	STATUS      current
	DESCRIPTION
	"Table for rulesetDynSubscriberUsedPlens"
	::={rulesetDynSubscriberUsedPlens 4}

rulesetDynSubscriberUsedPlensLevelEntry OBJECT-TYPE
	SYNTAX      RulesetDynSubscriberUsedPlensLevelEntry
	MAX-ACCESS  not-accessible
	STATUS      current
	DESCRIPTION
	"Table entry for rulesetDynSubscriberUsedPlens"
	INDEX { rulesetDynSubscriberUsedPlensLevelName }
	::={rulesetDynSubscriberUsedPlensLevelTable 1}

RulesetDynSubscriberUsedPlensLevelEntry ::=
	SEQUENCE {
		rulesetDynSubscriberUsedPlensLevelName	DisplayString,
		rulesetDynSubscriberUsedPlensLevelVal	CounterBasedGauge64,
		rulesetDynSubscriberUsedPlensLevelMax	CounterBasedGauge64
	}

rulesetDynSubscriberUsedPlensLevelName OBJECT-TYPE
	SYNTAX      DisplayString
	MAX-ACCESS  not-accessible
	STATUS      current
	DESCRIPTION
	"Table entry display string for rulesetDynSubscriberUsedPlens"
	::={rulesetDynSubscriberUsedPlensLevelEntry 1}

rulesetDynSubscriberUsedPlensLevelVal OBJECT-TYPE
	SYNTAX	 CounterBasedGauge64
	MAX-ACCESS  read-only
	STATUS      current
	DESCRIPTION
	"Table entry attribute for rulesetDynSubscriberUsedPlens"
	::={rulesetDynSubscriberUsedPlensLevelEntry 2}

rulesetDynSubscriberUsedPlensLevelMax OBJECT-TYPE
	SYNTAX	 CounterBasedGauge64
	MAX-ACCESS  read-only
	STATUS      current
	DESCRIPTION
	"Table entry attribute for rulesetDynSubscriberUsedPlens"
	::={rulesetDynSubscriberUsedPlensLevelEntry 4}


rulesetEnrichEntries	OBJECT IDENTIFIER ::={ruleset 54}

rulesetEnrichEntriesVal	OBJECT-TYPE
	SYNTAX	 CounterBasedGauge64
	MAX-ACCESS read-only
	STATUS current
	DESCRIPTION "Enrich: Entries (netobjid, ipprefix)-pairs in storage in engine"

	::={rulesetEnrichEntries 1}

rulesetEnrichEntriesMax	OBJECT-TYPE
	SYNTAX	 CounterBasedGauge64
	MAX-ACCESS read-only
	STATUS current
	DESCRIPTION "Enrich: Entries (netobjid, ipprefix)-pairs in storage in engine"

	::={rulesetEnrichEntries 3}

rulesetEnrichEntriesLevelTable OBJECT-TYPE
	SYNTAX      SEQUENCE OF RulesetEnrichEntriesLevelEntry
	MAX-ACCESS  not-accessible
	STATUS      current
	DESCRIPTION
	"Table for rulesetEnrichEntries"
	::={rulesetEnrichEntries 4}

rulesetEnrichEntriesLevelEntry OBJECT-TYPE
	SYNTAX      RulesetEnrichEntriesLevelEntry
	MAX-ACCESS  not-accessible
	STATUS      current
	DESCRIPTION
	"Table entry for rulesetEnrichEntries"
	INDEX { rulesetEnrichEntriesLevelName }
	::={rulesetEnrichEntriesLevelTable 1}

RulesetEnrichEntriesLevelEntry ::=
	SEQUENCE {
		rulesetEnrichEntriesLevelName	DisplayString,
		rulesetEnrichEntriesLevelVal	CounterBasedGauge64,
		rulesetEnrichEntriesLevelMax	CounterBasedGauge64
	}

rulesetEnrichEntriesLevelName OBJECT-TYPE
	SYNTAX      DisplayString
	MAX-ACCESS  not-accessible
	STATUS      current
	DESCRIPTION
	"Table entry display string for rulesetEnrichEntries"
	::={rulesetEnrichEntriesLevelEntry 1}

rulesetEnrichEntriesLevelVal OBJECT-TYPE
	SYNTAX	 CounterBasedGauge64
	MAX-ACCESS  read-only
	STATUS      current
	DESCRIPTION
	"Table entry attribute for rulesetEnrichEntries"
	::={rulesetEnrichEntriesLevelEntry 2}

rulesetEnrichEntriesLevelMax OBJECT-TYPE
	SYNTAX	 CounterBasedGauge64
	MAX-ACCESS  read-only
	STATUS      current
	DESCRIPTION
	"Table entry attribute for rulesetEnrichEntries"
	::={rulesetEnrichEntriesLevelEntry 4}


rulesetEnrichOpers	OBJECT IDENTIFIER ::={ruleset 60}

rulesetEnrichOpersVal	OBJECT-TYPE
	SYNTAX	 Counter64
	MAX-ACCESS read-only
	STATUS current
	DESCRIPTION "Enrich: Number of operations sent to engine"

	::={rulesetEnrichOpers 1}

rulesetEnrichOpersMom	OBJECT-TYPE
	SYNTAX	 CounterBasedGauge64
	MAX-ACCESS read-only
	STATUS current
	DESCRIPTION "Enrich: Number of operations sent to engine"

	::={rulesetEnrichOpers 2}

rulesetEnrichOpersMax	OBJECT-TYPE
	SYNTAX	 CounterBasedGauge64
	MAX-ACCESS read-only
	STATUS current
	DESCRIPTION "Enrich: Number of operations sent to engine"

	::={rulesetEnrichOpers 3}

rulesetEnrichOpersLevelTable OBJECT-TYPE
	SYNTAX      SEQUENCE OF RulesetEnrichOpersLevelEntry
	MAX-ACCESS  not-accessible
	STATUS      current
	DESCRIPTION
	"Table for rulesetEnrichOpers"
	::={rulesetEnrichOpers 4}

rulesetEnrichOpersLevelEntry OBJECT-TYPE
	SYNTAX      RulesetEnrichOpersLevelEntry
	MAX-ACCESS  not-accessible
	STATUS      current
	DESCRIPTION
	"Table entry for rulesetEnrichOpers"
	INDEX { rulesetEnrichOpersLevelName }
	::={rulesetEnrichOpersLevelTable 1}

RulesetEnrichOpersLevelEntry ::=
	SEQUENCE {
		rulesetEnrichOpersLevelName	DisplayString,
		rulesetEnrichOpersLevelVal	Counter64,
		rulesetEnrichOpersLevelMom	CounterBasedGauge64,
		rulesetEnrichOpersLevelMax	CounterBasedGauge64
	}

rulesetEnrichOpersLevelName OBJECT-TYPE
	SYNTAX      DisplayString
	MAX-ACCESS  not-accessible
	STATUS      current
	DESCRIPTION
	"Table entry display string for rulesetEnrichOpers"
	::={rulesetEnrichOpersLevelEntry 1}

rulesetEnrichOpersLevelVal OBJECT-TYPE
	SYNTAX	 Counter64
	MAX-ACCESS  read-only
	STATUS      current
	DESCRIPTION
	"Table entry attribute for rulesetEnrichOpers"
	::={rulesetEnrichOpersLevelEntry 2}

rulesetEnrichOpersLevelMom OBJECT-TYPE
	SYNTAX	 CounterBasedGauge64
	MAX-ACCESS  read-only
	STATUS      current
	DESCRIPTION
	"Table entry attribute for rulesetEnrichOpers"
	::={rulesetEnrichOpersLevelEntry 3}

rulesetEnrichOpersLevelMax OBJECT-TYPE
	SYNTAX	 CounterBasedGauge64
	MAX-ACCESS  read-only
	STATUS      current
	DESCRIPTION
	"Table entry attribute for rulesetEnrichOpers"
	::={rulesetEnrichOpersLevelEntry 4}


rulesetEnrichFull	OBJECT IDENTIFIER ::={ruleset 55}

rulesetEnrichFullVal	OBJECT-TYPE
	SYNTAX	 Counter64
	MAX-ACCESS read-only
	STATUS current
	DESCRIPTION "Enrich: Storage in engine is full"

	::={rulesetEnrichFull 1}

rulesetEnrichFullMom	OBJECT-TYPE
	SYNTAX	 CounterBasedGauge64
	MAX-ACCESS read-only
	STATUS current
	DESCRIPTION "Enrich: Storage in engine is full"

	::={rulesetEnrichFull 2}

rulesetEnrichFullMax	OBJECT-TYPE
	SYNTAX	 CounterBasedGauge64
	MAX-ACCESS read-only
	STATUS current
	DESCRIPTION "Enrich: Storage in engine is full"

	::={rulesetEnrichFull 3}

rulesetEnrichFullLevelTable OBJECT-TYPE
	SYNTAX      SEQUENCE OF RulesetEnrichFullLevelEntry
	MAX-ACCESS  not-accessible
	STATUS      current
	DESCRIPTION
	"Table for rulesetEnrichFull"
	::={rulesetEnrichFull 4}

rulesetEnrichFullLevelEntry OBJECT-TYPE
	SYNTAX      RulesetEnrichFullLevelEntry
	MAX-ACCESS  not-accessible
	STATUS      current
	DESCRIPTION
	"Table entry for rulesetEnrichFull"
	INDEX { rulesetEnrichFullLevelName }
	::={rulesetEnrichFullLevelTable 1}

RulesetEnrichFullLevelEntry ::=
	SEQUENCE {
		rulesetEnrichFullLevelName	DisplayString,
		rulesetEnrichFullLevelVal	Counter64,
		rulesetEnrichFullLevelMom	CounterBasedGauge64,
		rulesetEnrichFullLevelMax	CounterBasedGauge64
	}

rulesetEnrichFullLevelName OBJECT-TYPE
	SYNTAX      DisplayString
	MAX-ACCESS  not-accessible
	STATUS      current
	DESCRIPTION
	"Table entry display string for rulesetEnrichFull"
	::={rulesetEnrichFullLevelEntry 1}

rulesetEnrichFullLevelVal OBJECT-TYPE
	SYNTAX	 Counter64
	MAX-ACCESS  read-only
	STATUS      current
	DESCRIPTION
	"Table entry attribute for rulesetEnrichFull"
	::={rulesetEnrichFullLevelEntry 2}

rulesetEnrichFullLevelMom OBJECT-TYPE
	SYNTAX	 CounterBasedGauge64
	MAX-ACCESS  read-only
	STATUS      current
	DESCRIPTION
	"Table entry attribute for rulesetEnrichFull"
	::={rulesetEnrichFullLevelEntry 3}

rulesetEnrichFullLevelMax OBJECT-TYPE
	SYNTAX	 CounterBasedGauge64
	MAX-ACCESS  read-only
	STATUS      current
	DESCRIPTION
	"Table entry attribute for rulesetEnrichFull"
	::={rulesetEnrichFullLevelEntry 4}


rulesetEnrichError	OBJECT IDENTIFIER ::={ruleset 56}

rulesetEnrichErrorVal	OBJECT-TYPE
	SYNTAX	 Counter64
	MAX-ACCESS read-only
	STATUS current
	DESCRIPTION "Enrich: Parsing/handling errors in engine"

	::={rulesetEnrichError 1}

rulesetEnrichErrorMom	OBJECT-TYPE
	SYNTAX	 CounterBasedGauge64
	MAX-ACCESS read-only
	STATUS current
	DESCRIPTION "Enrich: Parsing/handling errors in engine"

	::={rulesetEnrichError 2}

rulesetEnrichErrorMax	OBJECT-TYPE
	SYNTAX	 CounterBasedGauge64
	MAX-ACCESS read-only
	STATUS current
	DESCRIPTION "Enrich: Parsing/handling errors in engine"

	::={rulesetEnrichError 3}

rulesetEnrichErrorLevelTable OBJECT-TYPE
	SYNTAX      SEQUENCE OF RulesetEnrichErrorLevelEntry
	MAX-ACCESS  not-accessible
	STATUS      current
	DESCRIPTION
	"Table for rulesetEnrichError"
	::={rulesetEnrichError 4}

rulesetEnrichErrorLevelEntry OBJECT-TYPE
	SYNTAX      RulesetEnrichErrorLevelEntry
	MAX-ACCESS  not-accessible
	STATUS      current
	DESCRIPTION
	"Table entry for rulesetEnrichError"
	INDEX { rulesetEnrichErrorLevelName }
	::={rulesetEnrichErrorLevelTable 1}

RulesetEnrichErrorLevelEntry ::=
	SEQUENCE {
		rulesetEnrichErrorLevelName	DisplayString,
		rulesetEnrichErrorLevelVal	Counter64,
		rulesetEnrichErrorLevelMom	CounterBasedGauge64,
		rulesetEnrichErrorLevelMax	CounterBasedGauge64
	}

rulesetEnrichErrorLevelName OBJECT-TYPE
	SYNTAX      DisplayString
	MAX-ACCESS  not-accessible
	STATUS      current
	DESCRIPTION
	"Table entry display string for rulesetEnrichError"
	::={rulesetEnrichErrorLevelEntry 1}

rulesetEnrichErrorLevelVal OBJECT-TYPE
	SYNTAX	 Counter64
	MAX-ACCESS  read-only
	STATUS      current
	DESCRIPTION
	"Table entry attribute for rulesetEnrichError"
	::={rulesetEnrichErrorLevelEntry 2}

rulesetEnrichErrorLevelMom OBJECT-TYPE
	SYNTAX	 CounterBasedGauge64
	MAX-ACCESS  read-only
	STATUS      current
	DESCRIPTION
	"Table entry attribute for rulesetEnrichError"
	::={rulesetEnrichErrorLevelEntry 3}

rulesetEnrichErrorLevelMax OBJECT-TYPE
	SYNTAX	 CounterBasedGauge64
	MAX-ACCESS  read-only
	STATUS      current
	DESCRIPTION
	"Table entry attribute for rulesetEnrichError"
	::={rulesetEnrichErrorLevelEntry 4}


rulesetEnrichNonexistent	OBJECT IDENTIFIER ::={ruleset 57}

rulesetEnrichNonexistentVal	OBJECT-TYPE
	SYNTAX	 Counter64
	MAX-ACCESS read-only
	STATUS current
	DESCRIPTION "Enrich: Lookup in engine of non-existing enrich property"

	::={rulesetEnrichNonexistent 1}

rulesetEnrichNonexistentMom	OBJECT-TYPE
	SYNTAX	 CounterBasedGauge64
	MAX-ACCESS read-only
	STATUS current
	DESCRIPTION "Enrich: Lookup in engine of non-existing enrich property"

	::={rulesetEnrichNonexistent 2}

rulesetEnrichNonexistentMax	OBJECT-TYPE
	SYNTAX	 CounterBasedGauge64
	MAX-ACCESS read-only
	STATUS current
	DESCRIPTION "Enrich: Lookup in engine of non-existing enrich property"

	::={rulesetEnrichNonexistent 3}

rulesetEnrichNonexistentLevelTable OBJECT-TYPE
	SYNTAX      SEQUENCE OF RulesetEnrichNonexistentLevelEntry
	MAX-ACCESS  not-accessible
	STATUS      current
	DESCRIPTION
	"Table for rulesetEnrichNonexistent"
	::={rulesetEnrichNonexistent 4}

rulesetEnrichNonexistentLevelEntry OBJECT-TYPE
	SYNTAX      RulesetEnrichNonexistentLevelEntry
	MAX-ACCESS  not-accessible
	STATUS      current
	DESCRIPTION
	"Table entry for rulesetEnrichNonexistent"
	INDEX { rulesetEnrichNonexistentLevelName }
	::={rulesetEnrichNonexistentLevelTable 1}

RulesetEnrichNonexistentLevelEntry ::=
	SEQUENCE {
		rulesetEnrichNonexistentLevelName	DisplayString,
		rulesetEnrichNonexistentLevelVal	Counter64,
		rulesetEnrichNonexistentLevelMom	CounterBasedGauge64,
		rulesetEnrichNonexistentLevelMax	CounterBasedGauge64
	}

rulesetEnrichNonexistentLevelName OBJECT-TYPE
	SYNTAX      DisplayString
	MAX-ACCESS  not-accessible
	STATUS      current
	DESCRIPTION
	"Table entry display string for rulesetEnrichNonexistent"
	::={rulesetEnrichNonexistentLevelEntry 1}

rulesetEnrichNonexistentLevelVal OBJECT-TYPE
	SYNTAX	 Counter64
	MAX-ACCESS  read-only
	STATUS      current
	DESCRIPTION
	"Table entry attribute for rulesetEnrichNonexistent"
	::={rulesetEnrichNonexistentLevelEntry 2}

rulesetEnrichNonexistentLevelMom OBJECT-TYPE
	SYNTAX	 CounterBasedGauge64
	MAX-ACCESS  read-only
	STATUS      current
	DESCRIPTION
	"Table entry attribute for rulesetEnrichNonexistent"
	::={rulesetEnrichNonexistentLevelEntry 3}

rulesetEnrichNonexistentLevelMax OBJECT-TYPE
	SYNTAX	 CounterBasedGauge64
	MAX-ACCESS  read-only
	STATUS      current
	DESCRIPTION
	"Table entry attribute for rulesetEnrichNonexistent"
	::={rulesetEnrichNonexistentLevelEntry 4}


rulesetNatcfgStatic	OBJECT IDENTIFIER ::={ruleset 45}

rulesetNatcfgStaticVal	OBJECT-TYPE
	SYNTAX	 CounterBasedGauge64
	MAX-ACCESS read-only
	STATUS current
	DESCRIPTION "NatCfg: Number of static natcfg entries from ruleset"

	::={rulesetNatcfgStatic 1}

rulesetNatcfgStaticMax	OBJECT-TYPE
	SYNTAX	 CounterBasedGauge64
	MAX-ACCESS read-only
	STATUS current
	DESCRIPTION "NatCfg: Number of static natcfg entries from ruleset"

	::={rulesetNatcfgStatic 3}

rulesetNatcfgStaticLevelTable OBJECT-TYPE
	SYNTAX      SEQUENCE OF RulesetNatcfgStaticLevelEntry
	MAX-ACCESS  not-accessible
	STATUS      current
	DESCRIPTION
	"Table for rulesetNatcfgStatic"
	::={rulesetNatcfgStatic 4}

rulesetNatcfgStaticLevelEntry OBJECT-TYPE
	SYNTAX      RulesetNatcfgStaticLevelEntry
	MAX-ACCESS  not-accessible
	STATUS      current
	DESCRIPTION
	"Table entry for rulesetNatcfgStatic"
	INDEX { rulesetNatcfgStaticLevelName }
	::={rulesetNatcfgStaticLevelTable 1}

RulesetNatcfgStaticLevelEntry ::=
	SEQUENCE {
		rulesetNatcfgStaticLevelName	DisplayString,
		rulesetNatcfgStaticLevelVal	CounterBasedGauge64,
		rulesetNatcfgStaticLevelMax	CounterBasedGauge64
	}

rulesetNatcfgStaticLevelName OBJECT-TYPE
	SYNTAX      DisplayString
	MAX-ACCESS  not-accessible
	STATUS      current
	DESCRIPTION
	"Table entry display string for rulesetNatcfgStatic"
	::={rulesetNatcfgStaticLevelEntry 1}

rulesetNatcfgStaticLevelVal OBJECT-TYPE
	SYNTAX	 CounterBasedGauge64
	MAX-ACCESS  read-only
	STATUS      current
	DESCRIPTION
	"Table entry attribute for rulesetNatcfgStatic"
	::={rulesetNatcfgStaticLevelEntry 2}

rulesetNatcfgStaticLevelMax OBJECT-TYPE
	SYNTAX	 CounterBasedGauge64
	MAX-ACCESS  read-only
	STATUS      current
	DESCRIPTION
	"Table entry attribute for rulesetNatcfgStatic"
	::={rulesetNatcfgStaticLevelEntry 4}


rulesetNatcfgDynamic	OBJECT IDENTIFIER ::={ruleset 46}

rulesetNatcfgDynamicVal	OBJECT-TYPE
	SYNTAX	 CounterBasedGauge64
	MAX-ACCESS read-only
	STATUS current
	DESCRIPTION "NatCfg: Number of dynamic natcfg entries"

	::={rulesetNatcfgDynamic 1}

rulesetNatcfgDynamicMax	OBJECT-TYPE
	SYNTAX	 CounterBasedGauge64
	MAX-ACCESS read-only
	STATUS current
	DESCRIPTION "NatCfg: Number of dynamic natcfg entries"

	::={rulesetNatcfgDynamic 3}

rulesetNatcfgDynamicLevelTable OBJECT-TYPE
	SYNTAX      SEQUENCE OF RulesetNatcfgDynamicLevelEntry
	MAX-ACCESS  not-accessible
	STATUS      current
	DESCRIPTION
	"Table for rulesetNatcfgDynamic"
	::={rulesetNatcfgDynamic 4}

rulesetNatcfgDynamicLevelEntry OBJECT-TYPE
	SYNTAX      RulesetNatcfgDynamicLevelEntry
	MAX-ACCESS  not-accessible
	STATUS      current
	DESCRIPTION
	"Table entry for rulesetNatcfgDynamic"
	INDEX { rulesetNatcfgDynamicLevelName }
	::={rulesetNatcfgDynamicLevelTable 1}

RulesetNatcfgDynamicLevelEntry ::=
	SEQUENCE {
		rulesetNatcfgDynamicLevelName	DisplayString,
		rulesetNatcfgDynamicLevelVal	CounterBasedGauge64,
		rulesetNatcfgDynamicLevelMax	CounterBasedGauge64
	}

rulesetNatcfgDynamicLevelName OBJECT-TYPE
	SYNTAX      DisplayString
	MAX-ACCESS  not-accessible
	STATUS      current
	DESCRIPTION
	"Table entry display string for rulesetNatcfgDynamic"
	::={rulesetNatcfgDynamicLevelEntry 1}

rulesetNatcfgDynamicLevelVal OBJECT-TYPE
	SYNTAX	 CounterBasedGauge64
	MAX-ACCESS  read-only
	STATUS      current
	DESCRIPTION
	"Table entry attribute for rulesetNatcfgDynamic"
	::={rulesetNatcfgDynamicLevelEntry 2}

rulesetNatcfgDynamicLevelMax OBJECT-TYPE
	SYNTAX	 CounterBasedGauge64
	MAX-ACCESS  read-only
	STATUS      current
	DESCRIPTION
	"Table entry attribute for rulesetNatcfgDynamic"
	::={rulesetNatcfgDynamicLevelEntry 4}


rulesetNatcfgAllocFail	OBJECT IDENTIFIER ::={ruleset 47}

rulesetNatcfgAllocFailVal	OBJECT-TYPE
	SYNTAX	 Counter64
	MAX-ACCESS read-only
	STATUS current
	DESCRIPTION "NatCfg: Dynamic natcfg allocation failures"

	::={rulesetNatcfgAllocFail 1}

rulesetNatcfgAllocFailMom	OBJECT-TYPE
	SYNTAX	 CounterBasedGauge64
	MAX-ACCESS read-only
	STATUS current
	DESCRIPTION "NatCfg: Dynamic natcfg allocation failures"

	::={rulesetNatcfgAllocFail 2}

rulesetNatcfgAllocFailMax	OBJECT-TYPE
	SYNTAX	 CounterBasedGauge64
	MAX-ACCESS read-only
	STATUS current
	DESCRIPTION "NatCfg: Dynamic natcfg allocation failures"

	::={rulesetNatcfgAllocFail 3}

rulesetNatcfgAllocFailLevelTable OBJECT-TYPE
	SYNTAX      SEQUENCE OF RulesetNatcfgAllocFailLevelEntry
	MAX-ACCESS  not-accessible
	STATUS      current
	DESCRIPTION
	"Table for rulesetNatcfgAllocFail"
	::={rulesetNatcfgAllocFail 4}

rulesetNatcfgAllocFailLevelEntry OBJECT-TYPE
	SYNTAX      RulesetNatcfgAllocFailLevelEntry
	MAX-ACCESS  not-accessible
	STATUS      current
	DESCRIPTION
	"Table entry for rulesetNatcfgAllocFail"
	INDEX { rulesetNatcfgAllocFailLevelName }
	::={rulesetNatcfgAllocFailLevelTable 1}

RulesetNatcfgAllocFailLevelEntry ::=
	SEQUENCE {
		rulesetNatcfgAllocFailLevelName	DisplayString,
		rulesetNatcfgAllocFailLevelVal	Counter64,
		rulesetNatcfgAllocFailLevelMom	CounterBasedGauge64,
		rulesetNatcfgAllocFailLevelMax	CounterBasedGauge64
	}

rulesetNatcfgAllocFailLevelName OBJECT-TYPE
	SYNTAX      DisplayString
	MAX-ACCESS  not-accessible
	STATUS      current
	DESCRIPTION
	"Table entry display string for rulesetNatcfgAllocFail"
	::={rulesetNatcfgAllocFailLevelEntry 1}

rulesetNatcfgAllocFailLevelVal OBJECT-TYPE
	SYNTAX	 Counter64
	MAX-ACCESS  read-only
	STATUS      current
	DESCRIPTION
	"Table entry attribute for rulesetNatcfgAllocFail"
	::={rulesetNatcfgAllocFailLevelEntry 2}

rulesetNatcfgAllocFailLevelMom OBJECT-TYPE
	SYNTAX	 CounterBasedGauge64
	MAX-ACCESS  read-only
	STATUS      current
	DESCRIPTION
	"Table entry attribute for rulesetNatcfgAllocFail"
	::={rulesetNatcfgAllocFailLevelEntry 3}

rulesetNatcfgAllocFailLevelMax OBJECT-TYPE
	SYNTAX	 CounterBasedGauge64
	MAX-ACCESS  read-only
	STATUS      current
	DESCRIPTION
	"Table entry attribute for rulesetNatcfgAllocFail"
	::={rulesetNatcfgAllocFailLevelEntry 4}


rulesetNatcfgParseFail	OBJECT IDENTIFIER ::={ruleset 48}

rulesetNatcfgParseFailVal	OBJECT-TYPE
	SYNTAX	 Counter64
	MAX-ACCESS read-only
	STATUS current
	DESCRIPTION "NatCfg: Dynamic natcfg parsing failures"

	::={rulesetNatcfgParseFail 1}

rulesetNatcfgParseFailMom	OBJECT-TYPE
	SYNTAX	 CounterBasedGauge64
	MAX-ACCESS read-only
	STATUS current
	DESCRIPTION "NatCfg: Dynamic natcfg parsing failures"

	::={rulesetNatcfgParseFail 2}

rulesetNatcfgParseFailMax	OBJECT-TYPE
	SYNTAX	 CounterBasedGauge64
	MAX-ACCESS read-only
	STATUS current
	DESCRIPTION "NatCfg: Dynamic natcfg parsing failures"

	::={rulesetNatcfgParseFail 3}

rulesetNatcfgParseFailLevelTable OBJECT-TYPE
	SYNTAX      SEQUENCE OF RulesetNatcfgParseFailLevelEntry
	MAX-ACCESS  not-accessible
	STATUS      current
	DESCRIPTION
	"Table for rulesetNatcfgParseFail"
	::={rulesetNatcfgParseFail 4}

rulesetNatcfgParseFailLevelEntry OBJECT-TYPE
	SYNTAX      RulesetNatcfgParseFailLevelEntry
	MAX-ACCESS  not-accessible
	STATUS      current
	DESCRIPTION
	"Table entry for rulesetNatcfgParseFail"
	INDEX { rulesetNatcfgParseFailLevelName }
	::={rulesetNatcfgParseFailLevelTable 1}

RulesetNatcfgParseFailLevelEntry ::=
	SEQUENCE {
		rulesetNatcfgParseFailLevelName	DisplayString,
		rulesetNatcfgParseFailLevelVal	Counter64,
		rulesetNatcfgParseFailLevelMom	CounterBasedGauge64,
		rulesetNatcfgParseFailLevelMax	CounterBasedGauge64
	}

rulesetNatcfgParseFailLevelName OBJECT-TYPE
	SYNTAX      DisplayString
	MAX-ACCESS  not-accessible
	STATUS      current
	DESCRIPTION
	"Table entry display string for rulesetNatcfgParseFail"
	::={rulesetNatcfgParseFailLevelEntry 1}

rulesetNatcfgParseFailLevelVal OBJECT-TYPE
	SYNTAX	 Counter64
	MAX-ACCESS  read-only
	STATUS      current
	DESCRIPTION
	"Table entry attribute for rulesetNatcfgParseFail"
	::={rulesetNatcfgParseFailLevelEntry 2}

rulesetNatcfgParseFailLevelMom OBJECT-TYPE
	SYNTAX	 CounterBasedGauge64
	MAX-ACCESS  read-only
	STATUS      current
	DESCRIPTION
	"Table entry attribute for rulesetNatcfgParseFail"
	::={rulesetNatcfgParseFailLevelEntry 3}

rulesetNatcfgParseFailLevelMax OBJECT-TYPE
	SYNTAX	 CounterBasedGauge64
	MAX-ACCESS  read-only
	STATUS      current
	DESCRIPTION
	"Table entry attribute for rulesetNatcfgParseFail"
	::={rulesetNatcfgParseFailLevelEntry 4}


rulesetNatcfgNonexistent	OBJECT IDENTIFIER ::={ruleset 49}

rulesetNatcfgNonexistentVal	OBJECT-TYPE
	SYNTAX	 Counter64
	MAX-ACCESS read-only
	STATUS current
	DESCRIPTION "NatCfg: Lookup of non-existing dynamic natcfg"

	::={rulesetNatcfgNonexistent 1}

rulesetNatcfgNonexistentMom	OBJECT-TYPE
	SYNTAX	 CounterBasedGauge64
	MAX-ACCESS read-only
	STATUS current
	DESCRIPTION "NatCfg: Lookup of non-existing dynamic natcfg"

	::={rulesetNatcfgNonexistent 2}

rulesetNatcfgNonexistentMax	OBJECT-TYPE
	SYNTAX	 CounterBasedGauge64
	MAX-ACCESS read-only
	STATUS current
	DESCRIPTION "NatCfg: Lookup of non-existing dynamic natcfg"

	::={rulesetNatcfgNonexistent 3}

rulesetNatcfgNonexistentLevelTable OBJECT-TYPE
	SYNTAX      SEQUENCE OF RulesetNatcfgNonexistentLevelEntry
	MAX-ACCESS  not-accessible
	STATUS      current
	DESCRIPTION
	"Table for rulesetNatcfgNonexistent"
	::={rulesetNatcfgNonexistent 4}

rulesetNatcfgNonexistentLevelEntry OBJECT-TYPE
	SYNTAX      RulesetNatcfgNonexistentLevelEntry
	MAX-ACCESS  not-accessible
	STATUS      current
	DESCRIPTION
	"Table entry for rulesetNatcfgNonexistent"
	INDEX { rulesetNatcfgNonexistentLevelName }
	::={rulesetNatcfgNonexistentLevelTable 1}

RulesetNatcfgNonexistentLevelEntry ::=
	SEQUENCE {
		rulesetNatcfgNonexistentLevelName	DisplayString,
		rulesetNatcfgNonexistentLevelVal	Counter64,
		rulesetNatcfgNonexistentLevelMom	CounterBasedGauge64,
		rulesetNatcfgNonexistentLevelMax	CounterBasedGauge64
	}

rulesetNatcfgNonexistentLevelName OBJECT-TYPE
	SYNTAX      DisplayString
	MAX-ACCESS  not-accessible
	STATUS      current
	DESCRIPTION
	"Table entry display string for rulesetNatcfgNonexistent"
	::={rulesetNatcfgNonexistentLevelEntry 1}

rulesetNatcfgNonexistentLevelVal OBJECT-TYPE
	SYNTAX	 Counter64
	MAX-ACCESS  read-only
	STATUS      current
	DESCRIPTION
	"Table entry attribute for rulesetNatcfgNonexistent"
	::={rulesetNatcfgNonexistentLevelEntry 2}

rulesetNatcfgNonexistentLevelMom OBJECT-TYPE
	SYNTAX	 CounterBasedGauge64
	MAX-ACCESS  read-only
	STATUS      current
	DESCRIPTION
	"Table entry attribute for rulesetNatcfgNonexistent"
	::={rulesetNatcfgNonexistentLevelEntry 3}

rulesetNatcfgNonexistentLevelMax OBJECT-TYPE
	SYNTAX	 CounterBasedGauge64
	MAX-ACCESS  read-only
	STATUS      current
	DESCRIPTION
	"Table entry attribute for rulesetNatcfgNonexistent"
	::={rulesetNatcfgNonexistentLevelEntry 4}


firewall	OBJECT IDENTIFIER ::={sysdiag 80}

fwAccepts	OBJECT IDENTIFIER ::={firewall 1}

fwAcceptsVal	OBJECT-TYPE
	SYNTAX	 Counter64
	MAX-ACCESS read-only
	STATUS current
	DESCRIPTION "Ruleset evaluations giving ACCEPT"

	::={fwAccepts 1}

fwAcceptsMom	OBJECT-TYPE
	SYNTAX	 CounterBasedGauge64
	MAX-ACCESS read-only
	STATUS current
	DESCRIPTION "Ruleset evaluations giving ACCEPT"

	::={fwAccepts 2}

fwAcceptsMax	OBJECT-TYPE
	SYNTAX	 CounterBasedGauge64
	MAX-ACCESS read-only
	STATUS current
	DESCRIPTION "Ruleset evaluations giving ACCEPT"

	::={fwAccepts 3}

fwAcceptsLevelTable OBJECT-TYPE
	SYNTAX      SEQUENCE OF FwAcceptsLevelEntry
	MAX-ACCESS  not-accessible
	STATUS      current
	DESCRIPTION
	"Table for fwAccepts"
	::={fwAccepts 4}

fwAcceptsLevelEntry OBJECT-TYPE
	SYNTAX      FwAcceptsLevelEntry
	MAX-ACCESS  not-accessible
	STATUS      current
	DESCRIPTION
	"Table entry for fwAccepts"
	INDEX { fwAcceptsLevelName }
	::={fwAcceptsLevelTable 1}

FwAcceptsLevelEntry ::=
	SEQUENCE {
		fwAcceptsLevelName	DisplayString,
		fwAcceptsLevelVal	Counter64,
		fwAcceptsLevelMom	CounterBasedGauge64,
		fwAcceptsLevelMax	CounterBasedGauge64
	}

fwAcceptsLevelName OBJECT-TYPE
	SYNTAX      DisplayString
	MAX-ACCESS  not-accessible
	STATUS      current
	DESCRIPTION
	"Table entry display string for fwAccepts"
	::={fwAcceptsLevelEntry 1}

fwAcceptsLevelVal OBJECT-TYPE
	SYNTAX	 Counter64
	MAX-ACCESS  read-only
	STATUS      current
	DESCRIPTION
	"Table entry attribute for fwAccepts"
	::={fwAcceptsLevelEntry 2}

fwAcceptsLevelMom OBJECT-TYPE
	SYNTAX	 CounterBasedGauge64
	MAX-ACCESS  read-only
	STATUS      current
	DESCRIPTION
	"Table entry attribute for fwAccepts"
	::={fwAcceptsLevelEntry 3}

fwAcceptsLevelMax OBJECT-TYPE
	SYNTAX	 CounterBasedGauge64
	MAX-ACCESS  read-only
	STATUS      current
	DESCRIPTION
	"Table entry attribute for fwAccepts"
	::={fwAcceptsLevelEntry 4}


fwRejects	OBJECT IDENTIFIER ::={firewall 2}

fwRejectsVal	OBJECT-TYPE
	SYNTAX	 Counter64
	MAX-ACCESS read-only
	STATUS current
	DESCRIPTION "Ruleset evaluations giving REJECT"

	::={fwRejects 1}

fwRejectsMom	OBJECT-TYPE
	SYNTAX	 CounterBasedGauge64
	MAX-ACCESS read-only
	STATUS current
	DESCRIPTION "Ruleset evaluations giving REJECT"

	::={fwRejects 2}

fwRejectsMax	OBJECT-TYPE
	SYNTAX	 CounterBasedGauge64
	MAX-ACCESS read-only
	STATUS current
	DESCRIPTION "Ruleset evaluations giving REJECT"

	::={fwRejects 3}

fwRejectsLevelTable OBJECT-TYPE
	SYNTAX      SEQUENCE OF FwRejectsLevelEntry
	MAX-ACCESS  not-accessible
	STATUS      current
	DESCRIPTION
	"Table for fwRejects"
	::={fwRejects 4}

fwRejectsLevelEntry OBJECT-TYPE
	SYNTAX      FwRejectsLevelEntry
	MAX-ACCESS  not-accessible
	STATUS      current
	DESCRIPTION
	"Table entry for fwRejects"
	INDEX { fwRejectsLevelName }
	::={fwRejectsLevelTable 1}

FwRejectsLevelEntry ::=
	SEQUENCE {
		fwRejectsLevelName	DisplayString,
		fwRejectsLevelVal	Counter64,
		fwRejectsLevelMom	CounterBasedGauge64,
		fwRejectsLevelMax	CounterBasedGauge64
	}

fwRejectsLevelName OBJECT-TYPE
	SYNTAX      DisplayString
	MAX-ACCESS  not-accessible
	STATUS      current
	DESCRIPTION
	"Table entry display string for fwRejects"
	::={fwRejectsLevelEntry 1}

fwRejectsLevelVal OBJECT-TYPE
	SYNTAX	 Counter64
	MAX-ACCESS  read-only
	STATUS      current
	DESCRIPTION
	"Table entry attribute for fwRejects"
	::={fwRejectsLevelEntry 2}

fwRejectsLevelMom OBJECT-TYPE
	SYNTAX	 CounterBasedGauge64
	MAX-ACCESS  read-only
	STATUS      current
	DESCRIPTION
	"Table entry attribute for fwRejects"
	::={fwRejectsLevelEntry 3}

fwRejectsLevelMax OBJECT-TYPE
	SYNTAX	 CounterBasedGauge64
	MAX-ACCESS  read-only
	STATUS      current
	DESCRIPTION
	"Table entry attribute for fwRejects"
	::={fwRejectsLevelEntry 4}


fwDrops	OBJECT IDENTIFIER ::={firewall 3}

fwDropsVal	OBJECT-TYPE
	SYNTAX	 Counter64
	MAX-ACCESS read-only
	STATUS current
	DESCRIPTION "Ruleset evaluations giving DROP"

	::={fwDrops 1}

fwDropsMom	OBJECT-TYPE
	SYNTAX	 CounterBasedGauge64
	MAX-ACCESS read-only
	STATUS current
	DESCRIPTION "Ruleset evaluations giving DROP"

	::={fwDrops 2}

fwDropsMax	OBJECT-TYPE
	SYNTAX	 CounterBasedGauge64
	MAX-ACCESS read-only
	STATUS current
	DESCRIPTION "Ruleset evaluations giving DROP"

	::={fwDrops 3}

fwDropsLevelTable OBJECT-TYPE
	SYNTAX      SEQUENCE OF FwDropsLevelEntry
	MAX-ACCESS  not-accessible
	STATUS      current
	DESCRIPTION
	"Table for fwDrops"
	::={fwDrops 4}

fwDropsLevelEntry OBJECT-TYPE
	SYNTAX      FwDropsLevelEntry
	MAX-ACCESS  not-accessible
	STATUS      current
	DESCRIPTION
	"Table entry for fwDrops"
	INDEX { fwDropsLevelName }
	::={fwDropsLevelTable 1}

FwDropsLevelEntry ::=
	SEQUENCE {
		fwDropsLevelName	DisplayString,
		fwDropsLevelVal	Counter64,
		fwDropsLevelMom	CounterBasedGauge64,
		fwDropsLevelMax	CounterBasedGauge64
	}

fwDropsLevelName OBJECT-TYPE
	SYNTAX      DisplayString
	MAX-ACCESS  not-accessible
	STATUS      current
	DESCRIPTION
	"Table entry display string for fwDrops"
	::={fwDropsLevelEntry 1}

fwDropsLevelVal OBJECT-TYPE
	SYNTAX	 Counter64
	MAX-ACCESS  read-only
	STATUS      current
	DESCRIPTION
	"Table entry attribute for fwDrops"
	::={fwDropsLevelEntry 2}

fwDropsLevelMom OBJECT-TYPE
	SYNTAX	 CounterBasedGauge64
	MAX-ACCESS  read-only
	STATUS      current
	DESCRIPTION
	"Table entry attribute for fwDrops"
	::={fwDropsLevelEntry 3}

fwDropsLevelMax OBJECT-TYPE
	SYNTAX	 CounterBasedGauge64
	MAX-ACCESS  read-only
	STATUS      current
	DESCRIPTION
	"Table entry attribute for fwDrops"
	::={fwDropsLevelEntry 4}


fwRewites	OBJECT IDENTIFIER ::={firewall 4}

fwRewitesVal	OBJECT-TYPE
	SYNTAX	 Counter64
	MAX-ACCESS read-only
	STATUS current
	DESCRIPTION "Ruleset evaluations giving REWRITE"

	::={fwRewites 1}

fwRewitesMom	OBJECT-TYPE
	SYNTAX	 CounterBasedGauge64
	MAX-ACCESS read-only
	STATUS current
	DESCRIPTION "Ruleset evaluations giving REWRITE"

	::={fwRewites 2}

fwRewitesMax	OBJECT-TYPE
	SYNTAX	 CounterBasedGauge64
	MAX-ACCESS read-only
	STATUS current
	DESCRIPTION "Ruleset evaluations giving REWRITE"

	::={fwRewites 3}

fwRewitesLevelTable OBJECT-TYPE
	SYNTAX      SEQUENCE OF FwRewitesLevelEntry
	MAX-ACCESS  not-accessible
	STATUS      current
	DESCRIPTION
	"Table for fwRewites"
	::={fwRewites 4}

fwRewitesLevelEntry OBJECT-TYPE
	SYNTAX      FwRewitesLevelEntry
	MAX-ACCESS  not-accessible
	STATUS      current
	DESCRIPTION
	"Table entry for fwRewites"
	INDEX { fwRewitesLevelName }
	::={fwRewitesLevelTable 1}

FwRewitesLevelEntry ::=
	SEQUENCE {
		fwRewitesLevelName	DisplayString,
		fwRewitesLevelVal	Counter64,
		fwRewitesLevelMom	CounterBasedGauge64,
		fwRewitesLevelMax	CounterBasedGauge64
	}

fwRewitesLevelName OBJECT-TYPE
	SYNTAX      DisplayString
	MAX-ACCESS  not-accessible
	STATUS      current
	DESCRIPTION
	"Table entry display string for fwRewites"
	::={fwRewitesLevelEntry 1}

fwRewitesLevelVal OBJECT-TYPE
	SYNTAX	 Counter64
	MAX-ACCESS  read-only
	STATUS      current
	DESCRIPTION
	"Table entry attribute for fwRewites"
	::={fwRewitesLevelEntry 2}

fwRewitesLevelMom OBJECT-TYPE
	SYNTAX	 CounterBasedGauge64
	MAX-ACCESS  read-only
	STATUS      current
	DESCRIPTION
	"Table entry attribute for fwRewites"
	::={fwRewitesLevelEntry 3}

fwRewitesLevelMax OBJECT-TYPE
	SYNTAX	 CounterBasedGauge64
	MAX-ACCESS  read-only
	STATUS      current
	DESCRIPTION
	"Table entry attribute for fwRewites"
	::={fwRewitesLevelEntry 4}


fwDiverts	OBJECT IDENTIFIER ::={firewall 5}

fwDivertsVal	OBJECT-TYPE
	SYNTAX	 Counter64
	MAX-ACCESS read-only
	STATUS current
	DESCRIPTION "Ruleset evaluations giving DIVERT"

	::={fwDiverts 1}

fwDivertsMom	OBJECT-TYPE
	SYNTAX	 CounterBasedGauge64
	MAX-ACCESS read-only
	STATUS current
	DESCRIPTION "Ruleset evaluations giving DIVERT"

	::={fwDiverts 2}

fwDivertsMax	OBJECT-TYPE
	SYNTAX	 CounterBasedGauge64
	MAX-ACCESS read-only
	STATUS current
	DESCRIPTION "Ruleset evaluations giving DIVERT"

	::={fwDiverts 3}

fwDivertsLevelTable OBJECT-TYPE
	SYNTAX      SEQUENCE OF FwDivertsLevelEntry
	MAX-ACCESS  not-accessible
	STATUS      current
	DESCRIPTION
	"Table for fwDiverts"
	::={fwDiverts 4}

fwDivertsLevelEntry OBJECT-TYPE
	SYNTAX      FwDivertsLevelEntry
	MAX-ACCESS  not-accessible
	STATUS      current
	DESCRIPTION
	"Table entry for fwDiverts"
	INDEX { fwDivertsLevelName }
	::={fwDivertsLevelTable 1}

FwDivertsLevelEntry ::=
	SEQUENCE {
		fwDivertsLevelName	DisplayString,
		fwDivertsLevelVal	Counter64,
		fwDivertsLevelMom	CounterBasedGauge64,
		fwDivertsLevelMax	CounterBasedGauge64
	}

fwDivertsLevelName OBJECT-TYPE
	SYNTAX      DisplayString
	MAX-ACCESS  not-accessible
	STATUS      current
	DESCRIPTION
	"Table entry display string for fwDiverts"
	::={fwDivertsLevelEntry 1}

fwDivertsLevelVal OBJECT-TYPE
	SYNTAX	 Counter64
	MAX-ACCESS  read-only
	STATUS      current
	DESCRIPTION
	"Table entry attribute for fwDiverts"
	::={fwDivertsLevelEntry 2}

fwDivertsLevelMom OBJECT-TYPE
	SYNTAX	 CounterBasedGauge64
	MAX-ACCESS  read-only
	STATUS      current
	DESCRIPTION
	"Table entry attribute for fwDiverts"
	::={fwDivertsLevelEntry 3}

fwDivertsLevelMax OBJECT-TYPE
	SYNTAX	 CounterBasedGauge64
	MAX-ACCESS  read-only
	STATUS      current
	DESCRIPTION
	"Table entry attribute for fwDiverts"
	::={fwDivertsLevelEntry 4}


fwRuleSets	OBJECT IDENTIFIER ::={firewall 6}

fwRuleSetsVal	OBJECT-TYPE
	SYNTAX	 Counter64
	MAX-ACCESS read-only
	STATUS current
	DESCRIPTION "Ruleset evaluations"

	::={fwRuleSets 1}

fwRuleSetsMom	OBJECT-TYPE
	SYNTAX	 CounterBasedGauge64
	MAX-ACCESS read-only
	STATUS current
	DESCRIPTION "Ruleset evaluations"

	::={fwRuleSets 2}

fwRuleSetsMax	OBJECT-TYPE
	SYNTAX	 CounterBasedGauge64
	MAX-ACCESS read-only
	STATUS current
	DESCRIPTION "Ruleset evaluations"

	::={fwRuleSets 3}

fwRuleSetsLevelTable OBJECT-TYPE
	SYNTAX      SEQUENCE OF FwRuleSetsLevelEntry
	MAX-ACCESS  not-accessible
	STATUS      current
	DESCRIPTION
	"Table for fwRuleSets"
	::={fwRuleSets 4}

fwRuleSetsLevelEntry OBJECT-TYPE
	SYNTAX      FwRuleSetsLevelEntry
	MAX-ACCESS  not-accessible
	STATUS      current
	DESCRIPTION
	"Table entry for fwRuleSets"
	INDEX { fwRuleSetsLevelName }
	::={fwRuleSetsLevelTable 1}

FwRuleSetsLevelEntry ::=
	SEQUENCE {
		fwRuleSetsLevelName	DisplayString,
		fwRuleSetsLevelVal	Counter64,
		fwRuleSetsLevelMom	CounterBasedGauge64,
		fwRuleSetsLevelMax	CounterBasedGauge64
	}

fwRuleSetsLevelName OBJECT-TYPE
	SYNTAX      DisplayString
	MAX-ACCESS  not-accessible
	STATUS      current
	DESCRIPTION
	"Table entry display string for fwRuleSets"
	::={fwRuleSetsLevelEntry 1}

fwRuleSetsLevelVal OBJECT-TYPE
	SYNTAX	 Counter64
	MAX-ACCESS  read-only
	STATUS      current
	DESCRIPTION
	"Table entry attribute for fwRuleSets"
	::={fwRuleSetsLevelEntry 2}

fwRuleSetsLevelMom OBJECT-TYPE
	SYNTAX	 CounterBasedGauge64
	MAX-ACCESS  read-only
	STATUS      current
	DESCRIPTION
	"Table entry attribute for fwRuleSets"
	::={fwRuleSetsLevelEntry 3}

fwRuleSetsLevelMax OBJECT-TYPE
	SYNTAX	 CounterBasedGauge64
	MAX-ACCESS  read-only
	STATUS      current
	DESCRIPTION
	"Table entry attribute for fwRuleSets"
	::={fwRuleSetsLevelEntry 4}


fwLogs	OBJECT IDENTIFIER ::={firewall 7}

fwLogsVal	OBJECT-TYPE
	SYNTAX	 Counter64
	MAX-ACCESS read-only
	STATUS current
	DESCRIPTION "Log entries"

	::={fwLogs 1}

fwLogsMom	OBJECT-TYPE
	SYNTAX	 CounterBasedGauge64
	MAX-ACCESS read-only
	STATUS current
	DESCRIPTION "Log entries"

	::={fwLogs 2}

fwLogsMax	OBJECT-TYPE
	SYNTAX	 CounterBasedGauge64
	MAX-ACCESS read-only
	STATUS current
	DESCRIPTION "Log entries"

	::={fwLogs 3}

fwLogsLevelTable OBJECT-TYPE
	SYNTAX      SEQUENCE OF FwLogsLevelEntry
	MAX-ACCESS  not-accessible
	STATUS      current
	DESCRIPTION
	"Table for fwLogs"
	::={fwLogs 4}

fwLogsLevelEntry OBJECT-TYPE
	SYNTAX      FwLogsLevelEntry
	MAX-ACCESS  not-accessible
	STATUS      current
	DESCRIPTION
	"Table entry for fwLogs"
	INDEX { fwLogsLevelName }
	::={fwLogsLevelTable 1}

FwLogsLevelEntry ::=
	SEQUENCE {
		fwLogsLevelName	DisplayString,
		fwLogsLevelVal	Counter64,
		fwLogsLevelMom	CounterBasedGauge64,
		fwLogsLevelMax	CounterBasedGauge64
	}

fwLogsLevelName OBJECT-TYPE
	SYNTAX      DisplayString
	MAX-ACCESS  not-accessible
	STATUS      current
	DESCRIPTION
	"Table entry display string for fwLogs"
	::={fwLogsLevelEntry 1}

fwLogsLevelVal OBJECT-TYPE
	SYNTAX	 Counter64
	MAX-ACCESS  read-only
	STATUS      current
	DESCRIPTION
	"Table entry attribute for fwLogs"
	::={fwLogsLevelEntry 2}

fwLogsLevelMom OBJECT-TYPE
	SYNTAX	 CounterBasedGauge64
	MAX-ACCESS  read-only
	STATUS      current
	DESCRIPTION
	"Table entry attribute for fwLogs"
	::={fwLogsLevelEntry 3}

fwLogsLevelMax OBJECT-TYPE
	SYNTAX	 CounterBasedGauge64
	MAX-ACCESS  read-only
	STATUS      current
	DESCRIPTION
	"Table entry attribute for fwLogs"
	::={fwLogsLevelEntry 4}


fwMonitor	OBJECT IDENTIFIER ::={firewall 8}

fwMonitorVal	OBJECT-TYPE
	SYNTAX	 Counter64
	MAX-ACCESS read-only
	STATUS current
	DESCRIPTION "Monitored packets"

	::={fwMonitor 1}

fwMonitorMom	OBJECT-TYPE
	SYNTAX	 CounterBasedGauge64
	MAX-ACCESS read-only
	STATUS current
	DESCRIPTION "Monitored packets"

	::={fwMonitor 2}

fwMonitorMax	OBJECT-TYPE
	SYNTAX	 CounterBasedGauge64
	MAX-ACCESS read-only
	STATUS current
	DESCRIPTION "Monitored packets"

	::={fwMonitor 3}

fwMonitorLevelTable OBJECT-TYPE
	SYNTAX      SEQUENCE OF FwMonitorLevelEntry
	MAX-ACCESS  not-accessible
	STATUS      current
	DESCRIPTION
	"Table for fwMonitor"
	::={fwMonitor 4}

fwMonitorLevelEntry OBJECT-TYPE
	SYNTAX      FwMonitorLevelEntry
	MAX-ACCESS  not-accessible
	STATUS      current
	DESCRIPTION
	"Table entry for fwMonitor"
	INDEX { fwMonitorLevelName }
	::={fwMonitorLevelTable 1}

FwMonitorLevelEntry ::=
	SEQUENCE {
		fwMonitorLevelName	DisplayString,
		fwMonitorLevelVal	Counter64,
		fwMonitorLevelMom	CounterBasedGauge64,
		fwMonitorLevelMax	CounterBasedGauge64
	}

fwMonitorLevelName OBJECT-TYPE
	SYNTAX      DisplayString
	MAX-ACCESS  not-accessible
	STATUS      current
	DESCRIPTION
	"Table entry display string for fwMonitor"
	::={fwMonitorLevelEntry 1}

fwMonitorLevelVal OBJECT-TYPE
	SYNTAX	 Counter64
	MAX-ACCESS  read-only
	STATUS      current
	DESCRIPTION
	"Table entry attribute for fwMonitor"
	::={fwMonitorLevelEntry 2}

fwMonitorLevelMom OBJECT-TYPE
	SYNTAX	 CounterBasedGauge64
	MAX-ACCESS  read-only
	STATUS      current
	DESCRIPTION
	"Table entry attribute for fwMonitor"
	::={fwMonitorLevelEntry 3}

fwMonitorLevelMax OBJECT-TYPE
	SYNTAX	 CounterBasedGauge64
	MAX-ACCESS  read-only
	STATUS      current
	DESCRIPTION
	"Table entry attribute for fwMonitor"
	::={fwMonitorLevelEntry 4}


fwMonitorFailures	OBJECT IDENTIFIER ::={firewall 9}

fwMonitorFailuresVal	OBJECT-TYPE
	SYNTAX	 Counter64
	MAX-ACCESS read-only
	STATUS current
	DESCRIPTION "Failed monitored packets"

	::={fwMonitorFailures 1}

fwMonitorFailuresMom	OBJECT-TYPE
	SYNTAX	 CounterBasedGauge64
	MAX-ACCESS read-only
	STATUS current
	DESCRIPTION "Failed monitored packets"

	::={fwMonitorFailures 2}

fwMonitorFailuresMax	OBJECT-TYPE
	SYNTAX	 CounterBasedGauge64
	MAX-ACCESS read-only
	STATUS current
	DESCRIPTION "Failed monitored packets"

	::={fwMonitorFailures 3}

fwMonitorFailuresLevelTable OBJECT-TYPE
	SYNTAX      SEQUENCE OF FwMonitorFailuresLevelEntry
	MAX-ACCESS  not-accessible
	STATUS      current
	DESCRIPTION
	"Table for fwMonitorFailures"
	::={fwMonitorFailures 4}

fwMonitorFailuresLevelEntry OBJECT-TYPE
	SYNTAX      FwMonitorFailuresLevelEntry
	MAX-ACCESS  not-accessible
	STATUS      current
	DESCRIPTION
	"Table entry for fwMonitorFailures"
	INDEX { fwMonitorFailuresLevelName }
	::={fwMonitorFailuresLevelTable 1}

FwMonitorFailuresLevelEntry ::=
	SEQUENCE {
		fwMonitorFailuresLevelName	DisplayString,
		fwMonitorFailuresLevelVal	Counter64,
		fwMonitorFailuresLevelMom	CounterBasedGauge64,
		fwMonitorFailuresLevelMax	CounterBasedGauge64
	}

fwMonitorFailuresLevelName OBJECT-TYPE
	SYNTAX      DisplayString
	MAX-ACCESS  not-accessible
	STATUS      current
	DESCRIPTION
	"Table entry display string for fwMonitorFailures"
	::={fwMonitorFailuresLevelEntry 1}

fwMonitorFailuresLevelVal OBJECT-TYPE
	SYNTAX	 Counter64
	MAX-ACCESS  read-only
	STATUS      current
	DESCRIPTION
	"Table entry attribute for fwMonitorFailures"
	::={fwMonitorFailuresLevelEntry 2}

fwMonitorFailuresLevelMom OBJECT-TYPE
	SYNTAX	 CounterBasedGauge64
	MAX-ACCESS  read-only
	STATUS      current
	DESCRIPTION
	"Table entry attribute for fwMonitorFailures"
	::={fwMonitorFailuresLevelEntry 3}

fwMonitorFailuresLevelMax OBJECT-TYPE
	SYNTAX	 CounterBasedGauge64
	MAX-ACCESS  read-only
	STATUS      current
	DESCRIPTION
	"Table entry attribute for fwMonitorFailures"
	::={fwMonitorFailuresLevelEntry 4}


fwInjects	OBJECT IDENTIFIER ::={firewall 10}

fwInjectsVal	OBJECT-TYPE
	SYNTAX	 Counter64
	MAX-ACCESS read-only
	STATUS current
	DESCRIPTION "Ruleset evaluations giving INJECT"

	::={fwInjects 1}

fwInjectsMom	OBJECT-TYPE
	SYNTAX	 CounterBasedGauge64
	MAX-ACCESS read-only
	STATUS current
	DESCRIPTION "Ruleset evaluations giving INJECT"

	::={fwInjects 2}

fwInjectsMax	OBJECT-TYPE
	SYNTAX	 CounterBasedGauge64
	MAX-ACCESS read-only
	STATUS current
	DESCRIPTION "Ruleset evaluations giving INJECT"

	::={fwInjects 3}

fwInjectsLevelTable OBJECT-TYPE
	SYNTAX      SEQUENCE OF FwInjectsLevelEntry
	MAX-ACCESS  not-accessible
	STATUS      current
	DESCRIPTION
	"Table for fwInjects"
	::={fwInjects 4}

fwInjectsLevelEntry OBJECT-TYPE
	SYNTAX      FwInjectsLevelEntry
	MAX-ACCESS  not-accessible
	STATUS      current
	DESCRIPTION
	"Table entry for fwInjects"
	INDEX { fwInjectsLevelName }
	::={fwInjectsLevelTable 1}

FwInjectsLevelEntry ::=
	SEQUENCE {
		fwInjectsLevelName	DisplayString,
		fwInjectsLevelVal	Counter64,
		fwInjectsLevelMom	CounterBasedGauge64,
		fwInjectsLevelMax	CounterBasedGauge64
	}

fwInjectsLevelName OBJECT-TYPE
	SYNTAX      DisplayString
	MAX-ACCESS  not-accessible
	STATUS      current
	DESCRIPTION
	"Table entry display string for fwInjects"
	::={fwInjectsLevelEntry 1}

fwInjectsLevelVal OBJECT-TYPE
	SYNTAX	 Counter64
	MAX-ACCESS  read-only
	STATUS      current
	DESCRIPTION
	"Table entry attribute for fwInjects"
	::={fwInjectsLevelEntry 2}

fwInjectsLevelMom OBJECT-TYPE
	SYNTAX	 CounterBasedGauge64
	MAX-ACCESS  read-only
	STATUS      current
	DESCRIPTION
	"Table entry attribute for fwInjects"
	::={fwInjectsLevelEntry 3}

fwInjectsLevelMax OBJECT-TYPE
	SYNTAX	 CounterBasedGauge64
	MAX-ACCESS  read-only
	STATUS      current
	DESCRIPTION
	"Table entry attribute for fwInjects"
	::={fwInjectsLevelEntry 4}


fwInjectsFailures	OBJECT IDENTIFIER ::={firewall 11}

fwInjectsFailuresVal	OBJECT-TYPE
	SYNTAX	 Counter64
	MAX-ACCESS read-only
	STATUS current
	DESCRIPTION "Inject data preparation failures"

	::={fwInjectsFailures 1}

fwInjectsFailuresMom	OBJECT-TYPE
	SYNTAX	 CounterBasedGauge64
	MAX-ACCESS read-only
	STATUS current
	DESCRIPTION "Inject data preparation failures"

	::={fwInjectsFailures 2}

fwInjectsFailuresMax	OBJECT-TYPE
	SYNTAX	 CounterBasedGauge64
	MAX-ACCESS read-only
	STATUS current
	DESCRIPTION "Inject data preparation failures"

	::={fwInjectsFailures 3}

fwInjectsFailuresLevelTable OBJECT-TYPE
	SYNTAX      SEQUENCE OF FwInjectsFailuresLevelEntry
	MAX-ACCESS  not-accessible
	STATUS      current
	DESCRIPTION
	"Table for fwInjectsFailures"
	::={fwInjectsFailures 4}

fwInjectsFailuresLevelEntry OBJECT-TYPE
	SYNTAX      FwInjectsFailuresLevelEntry
	MAX-ACCESS  not-accessible
	STATUS      current
	DESCRIPTION
	"Table entry for fwInjectsFailures"
	INDEX { fwInjectsFailuresLevelName }
	::={fwInjectsFailuresLevelTable 1}

FwInjectsFailuresLevelEntry ::=
	SEQUENCE {
		fwInjectsFailuresLevelName	DisplayString,
		fwInjectsFailuresLevelVal	Counter64,
		fwInjectsFailuresLevelMom	CounterBasedGauge64,
		fwInjectsFailuresLevelMax	CounterBasedGauge64
	}

fwInjectsFailuresLevelName OBJECT-TYPE
	SYNTAX      DisplayString
	MAX-ACCESS  not-accessible
	STATUS      current
	DESCRIPTION
	"Table entry display string for fwInjectsFailures"
	::={fwInjectsFailuresLevelEntry 1}

fwInjectsFailuresLevelVal OBJECT-TYPE
	SYNTAX	 Counter64
	MAX-ACCESS  read-only
	STATUS      current
	DESCRIPTION
	"Table entry attribute for fwInjectsFailures"
	::={fwInjectsFailuresLevelEntry 2}

fwInjectsFailuresLevelMom OBJECT-TYPE
	SYNTAX	 CounterBasedGauge64
	MAX-ACCESS  read-only
	STATUS      current
	DESCRIPTION
	"Table entry attribute for fwInjectsFailures"
	::={fwInjectsFailuresLevelEntry 3}

fwInjectsFailuresLevelMax OBJECT-TYPE
	SYNTAX	 CounterBasedGauge64
	MAX-ACCESS  read-only
	STATUS      current
	DESCRIPTION
	"Table entry attribute for fwInjectsFailures"
	::={fwInjectsFailuresLevelEntry 4}


fwInjectsFailuresProp	OBJECT IDENTIFIER ::={firewall 12}

fwInjectsFailuresPropVal	OBJECT-TYPE
	SYNTAX	 Counter64
	MAX-ACCESS read-only
	STATUS current
	DESCRIPTION "Inject data invalid properties"

	::={fwInjectsFailuresProp 1}

fwInjectsFailuresPropMom	OBJECT-TYPE
	SYNTAX	 CounterBasedGauge64
	MAX-ACCESS read-only
	STATUS current
	DESCRIPTION "Inject data invalid properties"

	::={fwInjectsFailuresProp 2}

fwInjectsFailuresPropMax	OBJECT-TYPE
	SYNTAX	 CounterBasedGauge64
	MAX-ACCESS read-only
	STATUS current
	DESCRIPTION "Inject data invalid properties"

	::={fwInjectsFailuresProp 3}

fwInjectsFailuresPropLevelTable OBJECT-TYPE
	SYNTAX      SEQUENCE OF FwInjectsFailuresPropLevelEntry
	MAX-ACCESS  not-accessible
	STATUS      current
	DESCRIPTION
	"Table for fwInjectsFailuresProp"
	::={fwInjectsFailuresProp 4}

fwInjectsFailuresPropLevelEntry OBJECT-TYPE
	SYNTAX      FwInjectsFailuresPropLevelEntry
	MAX-ACCESS  not-accessible
	STATUS      current
	DESCRIPTION
	"Table entry for fwInjectsFailuresProp"
	INDEX { fwInjectsFailuresPropLevelName }
	::={fwInjectsFailuresPropLevelTable 1}

FwInjectsFailuresPropLevelEntry ::=
	SEQUENCE {
		fwInjectsFailuresPropLevelName	DisplayString,
		fwInjectsFailuresPropLevelVal	Counter64,
		fwInjectsFailuresPropLevelMom	CounterBasedGauge64,
		fwInjectsFailuresPropLevelMax	CounterBasedGauge64
	}

fwInjectsFailuresPropLevelName OBJECT-TYPE
	SYNTAX      DisplayString
	MAX-ACCESS  not-accessible
	STATUS      current
	DESCRIPTION
	"Table entry display string for fwInjectsFailuresProp"
	::={fwInjectsFailuresPropLevelEntry 1}

fwInjectsFailuresPropLevelVal OBJECT-TYPE
	SYNTAX	 Counter64
	MAX-ACCESS  read-only
	STATUS      current
	DESCRIPTION
	"Table entry attribute for fwInjectsFailuresProp"
	::={fwInjectsFailuresPropLevelEntry 2}

fwInjectsFailuresPropLevelMom OBJECT-TYPE
	SYNTAX	 CounterBasedGauge64
	MAX-ACCESS  read-only
	STATUS      current
	DESCRIPTION
	"Table entry attribute for fwInjectsFailuresProp"
	::={fwInjectsFailuresPropLevelEntry 3}

fwInjectsFailuresPropLevelMax OBJECT-TYPE
	SYNTAX	 CounterBasedGauge64
	MAX-ACCESS  read-only
	STATUS      current
	DESCRIPTION
	"Table entry attribute for fwInjectsFailuresProp"
	::={fwInjectsFailuresPropLevelEntry 4}


fwMidconnRewrite	OBJECT IDENTIFIER ::={firewall 13}

fwMidconnRewriteVal	OBJECT-TYPE
	SYNTAX	 Counter64
	MAX-ACCESS read-only
	STATUS current
	DESCRIPTION "Rewrites changed in active connection"

	::={fwMidconnRewrite 1}

fwMidconnRewriteMom	OBJECT-TYPE
	SYNTAX	 CounterBasedGauge64
	MAX-ACCESS read-only
	STATUS current
	DESCRIPTION "Rewrites changed in active connection"

	::={fwMidconnRewrite 2}

fwMidconnRewriteMax	OBJECT-TYPE
	SYNTAX	 CounterBasedGauge64
	MAX-ACCESS read-only
	STATUS current
	DESCRIPTION "Rewrites changed in active connection"

	::={fwMidconnRewrite 3}

fwMidconnRewriteLevelTable OBJECT-TYPE
	SYNTAX      SEQUENCE OF FwMidconnRewriteLevelEntry
	MAX-ACCESS  not-accessible
	STATUS      current
	DESCRIPTION
	"Table for fwMidconnRewrite"
	::={fwMidconnRewrite 4}

fwMidconnRewriteLevelEntry OBJECT-TYPE
	SYNTAX      FwMidconnRewriteLevelEntry
	MAX-ACCESS  not-accessible
	STATUS      current
	DESCRIPTION
	"Table entry for fwMidconnRewrite"
	INDEX { fwMidconnRewriteLevelName }
	::={fwMidconnRewriteLevelTable 1}

FwMidconnRewriteLevelEntry ::=
	SEQUENCE {
		fwMidconnRewriteLevelName	DisplayString,
		fwMidconnRewriteLevelVal	Counter64,
		fwMidconnRewriteLevelMom	CounterBasedGauge64,
		fwMidconnRewriteLevelMax	CounterBasedGauge64
	}

fwMidconnRewriteLevelName OBJECT-TYPE
	SYNTAX      DisplayString
	MAX-ACCESS  not-accessible
	STATUS      current
	DESCRIPTION
	"Table entry display string for fwMidconnRewrite"
	::={fwMidconnRewriteLevelEntry 1}

fwMidconnRewriteLevelVal OBJECT-TYPE
	SYNTAX	 Counter64
	MAX-ACCESS  read-only
	STATUS      current
	DESCRIPTION
	"Table entry attribute for fwMidconnRewrite"
	::={fwMidconnRewriteLevelEntry 2}

fwMidconnRewriteLevelMom OBJECT-TYPE
	SYNTAX	 CounterBasedGauge64
	MAX-ACCESS  read-only
	STATUS      current
	DESCRIPTION
	"Table entry attribute for fwMidconnRewrite"
	::={fwMidconnRewriteLevelEntry 3}

fwMidconnRewriteLevelMax OBJECT-TYPE
	SYNTAX	 CounterBasedGauge64
	MAX-ACCESS  read-only
	STATUS      current
	DESCRIPTION
	"Table entry attribute for fwMidconnRewrite"
	::={fwMidconnRewriteLevelEntry 4}


fwEnrich	OBJECT IDENTIFIER ::={firewall 14}

fwEnrichVal	OBJECT-TYPE
	SYNTAX	 Counter64
	MAX-ACCESS read-only
	STATUS current
	DESCRIPTION "Ruleset evaluations giving ENRICH"

	::={fwEnrich 1}

fwEnrichMom	OBJECT-TYPE
	SYNTAX	 CounterBasedGauge64
	MAX-ACCESS read-only
	STATUS current
	DESCRIPTION "Ruleset evaluations giving ENRICH"

	::={fwEnrich 2}

fwEnrichMax	OBJECT-TYPE
	SYNTAX	 CounterBasedGauge64
	MAX-ACCESS read-only
	STATUS current
	DESCRIPTION "Ruleset evaluations giving ENRICH"

	::={fwEnrich 3}

fwEnrichLevelTable OBJECT-TYPE
	SYNTAX      SEQUENCE OF FwEnrichLevelEntry
	MAX-ACCESS  not-accessible
	STATUS      current
	DESCRIPTION
	"Table for fwEnrich"
	::={fwEnrich 4}

fwEnrichLevelEntry OBJECT-TYPE
	SYNTAX      FwEnrichLevelEntry
	MAX-ACCESS  not-accessible
	STATUS      current
	DESCRIPTION
	"Table entry for fwEnrich"
	INDEX { fwEnrichLevelName }
	::={fwEnrichLevelTable 1}

FwEnrichLevelEntry ::=
	SEQUENCE {
		fwEnrichLevelName	DisplayString,
		fwEnrichLevelVal	Counter64,
		fwEnrichLevelMom	CounterBasedGauge64,
		fwEnrichLevelMax	CounterBasedGauge64
	}

fwEnrichLevelName OBJECT-TYPE
	SYNTAX      DisplayString
	MAX-ACCESS  not-accessible
	STATUS      current
	DESCRIPTION
	"Table entry display string for fwEnrich"
	::={fwEnrichLevelEntry 1}

fwEnrichLevelVal OBJECT-TYPE
	SYNTAX	 Counter64
	MAX-ACCESS  read-only
	STATUS      current
	DESCRIPTION
	"Table entry attribute for fwEnrich"
	::={fwEnrichLevelEntry 2}

fwEnrichLevelMom OBJECT-TYPE
	SYNTAX	 CounterBasedGauge64
	MAX-ACCESS  read-only
	STATUS      current
	DESCRIPTION
	"Table entry attribute for fwEnrich"
	::={fwEnrichLevelEntry 3}

fwEnrichLevelMax OBJECT-TYPE
	SYNTAX	 CounterBasedGauge64
	MAX-ACCESS  read-only
	STATUS      current
	DESCRIPTION
	"Table entry attribute for fwEnrich"
	::={fwEnrichLevelEntry 4}


shaping	OBJECT IDENTIFIER ::={sysdiag 88}

shapingEnqueued	OBJECT IDENTIFIER ::={shaping 1}

shapingEnqueuedVal	OBJECT-TYPE
	SYNTAX	 Counter64
	MAX-ACCESS read-only
	STATUS current
	DESCRIPTION "Enqueued packets"

	::={shapingEnqueued 1}

shapingEnqueuedMom	OBJECT-TYPE
	SYNTAX	 CounterBasedGauge64
	MAX-ACCESS read-only
	STATUS current
	DESCRIPTION "Enqueued packets"

	::={shapingEnqueued 2}

shapingEnqueuedMax	OBJECT-TYPE
	SYNTAX	 CounterBasedGauge64
	MAX-ACCESS read-only
	STATUS current
	DESCRIPTION "Enqueued packets"

	::={shapingEnqueued 3}

shapingEnqueuedLevelTable OBJECT-TYPE
	SYNTAX      SEQUENCE OF ShapingEnqueuedLevelEntry
	MAX-ACCESS  not-accessible
	STATUS      current
	DESCRIPTION
	"Table for shapingEnqueued"
	::={shapingEnqueued 4}

shapingEnqueuedLevelEntry OBJECT-TYPE
	SYNTAX      ShapingEnqueuedLevelEntry
	MAX-ACCESS  not-accessible
	STATUS      current
	DESCRIPTION
	"Table entry for shapingEnqueued"
	INDEX { shapingEnqueuedLevelName }
	::={shapingEnqueuedLevelTable 1}

ShapingEnqueuedLevelEntry ::=
	SEQUENCE {
		shapingEnqueuedLevelName	DisplayString,
		shapingEnqueuedLevelVal	Counter64,
		shapingEnqueuedLevelMom	CounterBasedGauge64,
		shapingEnqueuedLevelMax	CounterBasedGauge64
	}

shapingEnqueuedLevelName OBJECT-TYPE
	SYNTAX      DisplayString
	MAX-ACCESS  not-accessible
	STATUS      current
	DESCRIPTION
	"Table entry display string for shapingEnqueued"
	::={shapingEnqueuedLevelEntry 1}

shapingEnqueuedLevelVal OBJECT-TYPE
	SYNTAX	 Counter64
	MAX-ACCESS  read-only
	STATUS      current
	DESCRIPTION
	"Table entry attribute for shapingEnqueued"
	::={shapingEnqueuedLevelEntry 2}

shapingEnqueuedLevelMom OBJECT-TYPE
	SYNTAX	 CounterBasedGauge64
	MAX-ACCESS  read-only
	STATUS      current
	DESCRIPTION
	"Table entry attribute for shapingEnqueued"
	::={shapingEnqueuedLevelEntry 3}

shapingEnqueuedLevelMax OBJECT-TYPE
	SYNTAX	 CounterBasedGauge64
	MAX-ACCESS  read-only
	STATUS      current
	DESCRIPTION
	"Table entry attribute for shapingEnqueued"
	::={shapingEnqueuedLevelEntry 4}


shapingDequeued	OBJECT IDENTIFIER ::={shaping 2}

shapingDequeuedVal	OBJECT-TYPE
	SYNTAX	 Counter64
	MAX-ACCESS read-only
	STATUS current
	DESCRIPTION "Dequeued packets"

	::={shapingDequeued 1}

shapingDequeuedMom	OBJECT-TYPE
	SYNTAX	 CounterBasedGauge64
	MAX-ACCESS read-only
	STATUS current
	DESCRIPTION "Dequeued packets"

	::={shapingDequeued 2}

shapingDequeuedMax	OBJECT-TYPE
	SYNTAX	 CounterBasedGauge64
	MAX-ACCESS read-only
	STATUS current
	DESCRIPTION "Dequeued packets"

	::={shapingDequeued 3}

shapingDequeuedLevelTable OBJECT-TYPE
	SYNTAX      SEQUENCE OF ShapingDequeuedLevelEntry
	MAX-ACCESS  not-accessible
	STATUS      current
	DESCRIPTION
	"Table for shapingDequeued"
	::={shapingDequeued 4}

shapingDequeuedLevelEntry OBJECT-TYPE
	SYNTAX      ShapingDequeuedLevelEntry
	MAX-ACCESS  not-accessible
	STATUS      current
	DESCRIPTION
	"Table entry for shapingDequeued"
	INDEX { shapingDequeuedLevelName }
	::={shapingDequeuedLevelTable 1}

ShapingDequeuedLevelEntry ::=
	SEQUENCE {
		shapingDequeuedLevelName	DisplayString,
		shapingDequeuedLevelVal	Counter64,
		shapingDequeuedLevelMom	CounterBasedGauge64,
		shapingDequeuedLevelMax	CounterBasedGauge64
	}

shapingDequeuedLevelName OBJECT-TYPE
	SYNTAX      DisplayString
	MAX-ACCESS  not-accessible
	STATUS      current
	DESCRIPTION
	"Table entry display string for shapingDequeued"
	::={shapingDequeuedLevelEntry 1}

shapingDequeuedLevelVal OBJECT-TYPE
	SYNTAX	 Counter64
	MAX-ACCESS  read-only
	STATUS      current
	DESCRIPTION
	"Table entry attribute for shapingDequeued"
	::={shapingDequeuedLevelEntry 2}

shapingDequeuedLevelMom OBJECT-TYPE
	SYNTAX	 CounterBasedGauge64
	MAX-ACCESS  read-only
	STATUS      current
	DESCRIPTION
	"Table entry attribute for shapingDequeued"
	::={shapingDequeuedLevelEntry 3}

shapingDequeuedLevelMax OBJECT-TYPE
	SYNTAX	 CounterBasedGauge64
	MAX-ACCESS  read-only
	STATUS      current
	DESCRIPTION
	"Table entry attribute for shapingDequeued"
	::={shapingDequeuedLevelEntry 4}


shapingBrownConnDrops	OBJECT IDENTIFIER ::={shaping 8}

shapingBrownConnDropsVal	OBJECT-TYPE
	SYNTAX	 Counter64
	MAX-ACCESS read-only
	STATUS current
	DESCRIPTION "BROWN per connection drops"

	::={shapingBrownConnDrops 1}

shapingBrownConnDropsMom	OBJECT-TYPE
	SYNTAX	 CounterBasedGauge64
	MAX-ACCESS read-only
	STATUS current
	DESCRIPTION "BROWN per connection drops"

	::={shapingBrownConnDrops 2}

shapingBrownConnDropsMax	OBJECT-TYPE
	SYNTAX	 CounterBasedGauge64
	MAX-ACCESS read-only
	STATUS current
	DESCRIPTION "BROWN per connection drops"

	::={shapingBrownConnDrops 3}

shapingBrownConnDropsLevelTable OBJECT-TYPE
	SYNTAX      SEQUENCE OF ShapingBrownConnDropsLevelEntry
	MAX-ACCESS  not-accessible
	STATUS      current
	DESCRIPTION
	"Table for shapingBrownConnDrops"
	::={shapingBrownConnDrops 4}

shapingBrownConnDropsLevelEntry OBJECT-TYPE
	SYNTAX      ShapingBrownConnDropsLevelEntry
	MAX-ACCESS  not-accessible
	STATUS      current
	DESCRIPTION
	"Table entry for shapingBrownConnDrops"
	INDEX { shapingBrownConnDropsLevelName }
	::={shapingBrownConnDropsLevelTable 1}

ShapingBrownConnDropsLevelEntry ::=
	SEQUENCE {
		shapingBrownConnDropsLevelName	DisplayString,
		shapingBrownConnDropsLevelVal	Counter64,
		shapingBrownConnDropsLevelMom	CounterBasedGauge64,
		shapingBrownConnDropsLevelMax	CounterBasedGauge64
	}

shapingBrownConnDropsLevelName OBJECT-TYPE
	SYNTAX      DisplayString
	MAX-ACCESS  not-accessible
	STATUS      current
	DESCRIPTION
	"Table entry display string for shapingBrownConnDrops"
	::={shapingBrownConnDropsLevelEntry 1}

shapingBrownConnDropsLevelVal OBJECT-TYPE
	SYNTAX	 Counter64
	MAX-ACCESS  read-only
	STATUS      current
	DESCRIPTION
	"Table entry attribute for shapingBrownConnDrops"
	::={shapingBrownConnDropsLevelEntry 2}

shapingBrownConnDropsLevelMom OBJECT-TYPE
	SYNTAX	 CounterBasedGauge64
	MAX-ACCESS  read-only
	STATUS      current
	DESCRIPTION
	"Table entry attribute for shapingBrownConnDrops"
	::={shapingBrownConnDropsLevelEntry 3}

shapingBrownConnDropsLevelMax OBJECT-TYPE
	SYNTAX	 CounterBasedGauge64
	MAX-ACCESS  read-only
	STATUS      current
	DESCRIPTION
	"Table entry attribute for shapingBrownConnDrops"
	::={shapingBrownConnDropsLevelEntry 4}


shapingQueueSize	OBJECT IDENTIFIER ::={shaping 9}

shapingQueueSizeVal	OBJECT-TYPE
	SYNTAX	 CounterBasedGauge64
	MAX-ACCESS read-only
	STATUS current
	DESCRIPTION "Queue size"

	::={shapingQueueSize 1}

shapingQueueSizeMax	OBJECT-TYPE
	SYNTAX	 CounterBasedGauge64
	MAX-ACCESS read-only
	STATUS current
	DESCRIPTION "Queue size"

	::={shapingQueueSize 3}

shapingQueueSizeLevelTable OBJECT-TYPE
	SYNTAX      SEQUENCE OF ShapingQueueSizeLevelEntry
	MAX-ACCESS  not-accessible
	STATUS      current
	DESCRIPTION
	"Table for shapingQueueSize"
	::={shapingQueueSize 4}

shapingQueueSizeLevelEntry OBJECT-TYPE
	SYNTAX      ShapingQueueSizeLevelEntry
	MAX-ACCESS  not-accessible
	STATUS      current
	DESCRIPTION
	"Table entry for shapingQueueSize"
	INDEX { shapingQueueSizeLevelName }
	::={shapingQueueSizeLevelTable 1}

ShapingQueueSizeLevelEntry ::=
	SEQUENCE {
		shapingQueueSizeLevelName	DisplayString,
		shapingQueueSizeLevelVal	CounterBasedGauge64,
		shapingQueueSizeLevelMax	CounterBasedGauge64
	}

shapingQueueSizeLevelName OBJECT-TYPE
	SYNTAX      DisplayString
	MAX-ACCESS  not-accessible
	STATUS      current
	DESCRIPTION
	"Table entry display string for shapingQueueSize"
	::={shapingQueueSizeLevelEntry 1}

shapingQueueSizeLevelVal OBJECT-TYPE
	SYNTAX	 CounterBasedGauge64
	MAX-ACCESS  read-only
	STATUS      current
	DESCRIPTION
	"Table entry attribute for shapingQueueSize"
	::={shapingQueueSizeLevelEntry 2}

shapingQueueSizeLevelMax OBJECT-TYPE
	SYNTAX	 CounterBasedGauge64
	MAX-ACCESS  read-only
	STATUS      current
	DESCRIPTION
	"Table entry attribute for shapingQueueSize"
	::={shapingQueueSizeLevelEntry 4}


shapingRulesSetCount	OBJECT IDENTIFIER ::={shaping 10}

shapingRulesSetCountVal	OBJECT-TYPE
	SYNTAX	 Counter64
	MAX-ACCESS read-only
	STATUS current
	DESCRIPTION "Rule sets"

	::={shapingRulesSetCount 1}

shapingRulesSetCountMom	OBJECT-TYPE
	SYNTAX	 CounterBasedGauge64
	MAX-ACCESS read-only
	STATUS current
	DESCRIPTION "Rule sets"

	::={shapingRulesSetCount 2}

shapingRulesSetCountMax	OBJECT-TYPE
	SYNTAX	 CounterBasedGauge64
	MAX-ACCESS read-only
	STATUS current
	DESCRIPTION "Rule sets"

	::={shapingRulesSetCount 3}

shapingRulesSetCountLevelTable OBJECT-TYPE
	SYNTAX      SEQUENCE OF ShapingRulesSetCountLevelEntry
	MAX-ACCESS  not-accessible
	STATUS      current
	DESCRIPTION
	"Table for shapingRulesSetCount"
	::={shapingRulesSetCount 4}

shapingRulesSetCountLevelEntry OBJECT-TYPE
	SYNTAX      ShapingRulesSetCountLevelEntry
	MAX-ACCESS  not-accessible
	STATUS      current
	DESCRIPTION
	"Table entry for shapingRulesSetCount"
	INDEX { shapingRulesSetCountLevelName }
	::={shapingRulesSetCountLevelTable 1}

ShapingRulesSetCountLevelEntry ::=
	SEQUENCE {
		shapingRulesSetCountLevelName	DisplayString,
		shapingRulesSetCountLevelVal	Counter64,
		shapingRulesSetCountLevelMom	CounterBasedGauge64,
		shapingRulesSetCountLevelMax	CounterBasedGauge64
	}

shapingRulesSetCountLevelName OBJECT-TYPE
	SYNTAX      DisplayString
	MAX-ACCESS  not-accessible
	STATUS      current
	DESCRIPTION
	"Table entry display string for shapingRulesSetCount"
	::={shapingRulesSetCountLevelEntry 1}

shapingRulesSetCountLevelVal OBJECT-TYPE
	SYNTAX	 Counter64
	MAX-ACCESS  read-only
	STATUS      current
	DESCRIPTION
	"Table entry attribute for shapingRulesSetCount"
	::={shapingRulesSetCountLevelEntry 2}

shapingRulesSetCountLevelMom OBJECT-TYPE
	SYNTAX	 CounterBasedGauge64
	MAX-ACCESS  read-only
	STATUS      current
	DESCRIPTION
	"Table entry attribute for shapingRulesSetCount"
	::={shapingRulesSetCountLevelEntry 3}

shapingRulesSetCountLevelMax OBJECT-TYPE
	SYNTAX	 CounterBasedGauge64
	MAX-ACCESS  read-only
	STATUS      current
	DESCRIPTION
	"Table entry attribute for shapingRulesSetCount"
	::={shapingRulesSetCountLevelEntry 4}


shapingEnqueuedBytes	OBJECT IDENTIFIER ::={shaping 11}

shapingEnqueuedBytesVal	OBJECT-TYPE
	SYNTAX	 Counter64
	MAX-ACCESS read-only
	STATUS current
	DESCRIPTION "Enqueued bytes"

	::={shapingEnqueuedBytes 1}

shapingEnqueuedBytesMom	OBJECT-TYPE
	SYNTAX	 CounterBasedGauge64
	MAX-ACCESS read-only
	STATUS current
	DESCRIPTION "Enqueued bytes"

	::={shapingEnqueuedBytes 2}

shapingEnqueuedBytesMax	OBJECT-TYPE
	SYNTAX	 CounterBasedGauge64
	MAX-ACCESS read-only
	STATUS current
	DESCRIPTION "Enqueued bytes"

	::={shapingEnqueuedBytes 3}

shapingEnqueuedBytesLevelTable OBJECT-TYPE
	SYNTAX      SEQUENCE OF ShapingEnqueuedBytesLevelEntry
	MAX-ACCESS  not-accessible
	STATUS      current
	DESCRIPTION
	"Table for shapingEnqueuedBytes"
	::={shapingEnqueuedBytes 4}

shapingEnqueuedBytesLevelEntry OBJECT-TYPE
	SYNTAX      ShapingEnqueuedBytesLevelEntry
	MAX-ACCESS  not-accessible
	STATUS      current
	DESCRIPTION
	"Table entry for shapingEnqueuedBytes"
	INDEX { shapingEnqueuedBytesLevelName }
	::={shapingEnqueuedBytesLevelTable 1}

ShapingEnqueuedBytesLevelEntry ::=
	SEQUENCE {
		shapingEnqueuedBytesLevelName	DisplayString,
		shapingEnqueuedBytesLevelVal	Counter64,
		shapingEnqueuedBytesLevelMom	CounterBasedGauge64,
		shapingEnqueuedBytesLevelMax	CounterBasedGauge64
	}

shapingEnqueuedBytesLevelName OBJECT-TYPE
	SYNTAX      DisplayString
	MAX-ACCESS  not-accessible
	STATUS      current
	DESCRIPTION
	"Table entry display string for shapingEnqueuedBytes"
	::={shapingEnqueuedBytesLevelEntry 1}

shapingEnqueuedBytesLevelVal OBJECT-TYPE
	SYNTAX	 Counter64
	MAX-ACCESS  read-only
	STATUS      current
	DESCRIPTION
	"Table entry attribute for shapingEnqueuedBytes"
	::={shapingEnqueuedBytesLevelEntry 2}

shapingEnqueuedBytesLevelMom OBJECT-TYPE
	SYNTAX	 CounterBasedGauge64
	MAX-ACCESS  read-only
	STATUS      current
	DESCRIPTION
	"Table entry attribute for shapingEnqueuedBytes"
	::={shapingEnqueuedBytesLevelEntry 3}

shapingEnqueuedBytesLevelMax OBJECT-TYPE
	SYNTAX	 CounterBasedGauge64
	MAX-ACCESS  read-only
	STATUS      current
	DESCRIPTION
	"Table entry attribute for shapingEnqueuedBytes"
	::={shapingEnqueuedBytesLevelEntry 4}


shapingDequeuedBytes	OBJECT IDENTIFIER ::={shaping 12}

shapingDequeuedBytesVal	OBJECT-TYPE
	SYNTAX	 Counter64
	MAX-ACCESS read-only
	STATUS current
	DESCRIPTION "Dequeued bytes"

	::={shapingDequeuedBytes 1}

shapingDequeuedBytesMom	OBJECT-TYPE
	SYNTAX	 CounterBasedGauge64
	MAX-ACCESS read-only
	STATUS current
	DESCRIPTION "Dequeued bytes"

	::={shapingDequeuedBytes 2}

shapingDequeuedBytesMax	OBJECT-TYPE
	SYNTAX	 CounterBasedGauge64
	MAX-ACCESS read-only
	STATUS current
	DESCRIPTION "Dequeued bytes"

	::={shapingDequeuedBytes 3}

shapingDequeuedBytesLevelTable OBJECT-TYPE
	SYNTAX      SEQUENCE OF ShapingDequeuedBytesLevelEntry
	MAX-ACCESS  not-accessible
	STATUS      current
	DESCRIPTION
	"Table for shapingDequeuedBytes"
	::={shapingDequeuedBytes 4}

shapingDequeuedBytesLevelEntry OBJECT-TYPE
	SYNTAX      ShapingDequeuedBytesLevelEntry
	MAX-ACCESS  not-accessible
	STATUS      current
	DESCRIPTION
	"Table entry for shapingDequeuedBytes"
	INDEX { shapingDequeuedBytesLevelName }
	::={shapingDequeuedBytesLevelTable 1}

ShapingDequeuedBytesLevelEntry ::=
	SEQUENCE {
		shapingDequeuedBytesLevelName	DisplayString,
		shapingDequeuedBytesLevelVal	Counter64,
		shapingDequeuedBytesLevelMom	CounterBasedGauge64,
		shapingDequeuedBytesLevelMax	CounterBasedGauge64
	}

shapingDequeuedBytesLevelName OBJECT-TYPE
	SYNTAX      DisplayString
	MAX-ACCESS  not-accessible
	STATUS      current
	DESCRIPTION
	"Table entry display string for shapingDequeuedBytes"
	::={shapingDequeuedBytesLevelEntry 1}

shapingDequeuedBytesLevelVal OBJECT-TYPE
	SYNTAX	 Counter64
	MAX-ACCESS  read-only
	STATUS      current
	DESCRIPTION
	"Table entry attribute for shapingDequeuedBytes"
	::={shapingDequeuedBytesLevelEntry 2}

shapingDequeuedBytesLevelMom OBJECT-TYPE
	SYNTAX	 CounterBasedGauge64
	MAX-ACCESS  read-only
	STATUS      current
	DESCRIPTION
	"Table entry attribute for shapingDequeuedBytes"
	::={shapingDequeuedBytesLevelEntry 3}

shapingDequeuedBytesLevelMax OBJECT-TYPE
	SYNTAX	 CounterBasedGauge64
	MAX-ACCESS  read-only
	STATUS      current
	DESCRIPTION
	"Table entry attribute for shapingDequeuedBytes"
	::={shapingDequeuedBytesLevelEntry 4}


shapingObjectCopies	OBJECT IDENTIFIER ::={shaping 13}

shapingObjectCopiesVal	OBJECT-TYPE
	SYNTAX	 CounterBasedGauge64
	MAX-ACCESS read-only
	STATUS current
	DESCRIPTION "Object copies"

	::={shapingObjectCopies 1}

shapingObjectCopiesMax	OBJECT-TYPE
	SYNTAX	 CounterBasedGauge64
	MAX-ACCESS read-only
	STATUS current
	DESCRIPTION "Object copies"

	::={shapingObjectCopies 3}

shapingObjectCopiesLevelTable OBJECT-TYPE
	SYNTAX      SEQUENCE OF ShapingObjectCopiesLevelEntry
	MAX-ACCESS  not-accessible
	STATUS      current
	DESCRIPTION
	"Table for shapingObjectCopies"
	::={shapingObjectCopies 4}

shapingObjectCopiesLevelEntry OBJECT-TYPE
	SYNTAX      ShapingObjectCopiesLevelEntry
	MAX-ACCESS  not-accessible
	STATUS      current
	DESCRIPTION
	"Table entry for shapingObjectCopies"
	INDEX { shapingObjectCopiesLevelName }
	::={shapingObjectCopiesLevelTable 1}

ShapingObjectCopiesLevelEntry ::=
	SEQUENCE {
		shapingObjectCopiesLevelName	DisplayString,
		shapingObjectCopiesLevelVal	CounterBasedGauge64,
		shapingObjectCopiesLevelMax	CounterBasedGauge64
	}

shapingObjectCopiesLevelName OBJECT-TYPE
	SYNTAX      DisplayString
	MAX-ACCESS  not-accessible
	STATUS      current
	DESCRIPTION
	"Table entry display string for shapingObjectCopies"
	::={shapingObjectCopiesLevelEntry 1}

shapingObjectCopiesLevelVal OBJECT-TYPE
	SYNTAX	 CounterBasedGauge64
	MAX-ACCESS  read-only
	STATUS      current
	DESCRIPTION
	"Table entry attribute for shapingObjectCopies"
	::={shapingObjectCopiesLevelEntry 2}

shapingObjectCopiesLevelMax OBJECT-TYPE
	SYNTAX	 CounterBasedGauge64
	MAX-ACCESS  read-only
	STATUS      current
	DESCRIPTION
	"Table entry attribute for shapingObjectCopies"
	::={shapingObjectCopiesLevelEntry 4}


shapingOutofpacketsDrops	OBJECT IDENTIFIER ::={shaping 15}

shapingOutofpacketsDropsVal	OBJECT-TYPE
	SYNTAX	 Counter64
	MAX-ACCESS read-only
	STATUS current
	DESCRIPTION "Out of packets drops"

	::={shapingOutofpacketsDrops 1}

shapingOutofpacketsDropsMom	OBJECT-TYPE
	SYNTAX	 CounterBasedGauge64
	MAX-ACCESS read-only
	STATUS current
	DESCRIPTION "Out of packets drops"

	::={shapingOutofpacketsDrops 2}

shapingOutofpacketsDropsMax	OBJECT-TYPE
	SYNTAX	 CounterBasedGauge64
	MAX-ACCESS read-only
	STATUS current
	DESCRIPTION "Out of packets drops"

	::={shapingOutofpacketsDrops 3}

shapingOutofpacketsDropsLevelTable OBJECT-TYPE
	SYNTAX      SEQUENCE OF ShapingOutofpacketsDropsLevelEntry
	MAX-ACCESS  not-accessible
	STATUS      current
	DESCRIPTION
	"Table for shapingOutofpacketsDrops"
	::={shapingOutofpacketsDrops 4}

shapingOutofpacketsDropsLevelEntry OBJECT-TYPE
	SYNTAX      ShapingOutofpacketsDropsLevelEntry
	MAX-ACCESS  not-accessible
	STATUS      current
	DESCRIPTION
	"Table entry for shapingOutofpacketsDrops"
	INDEX { shapingOutofpacketsDropsLevelName }
	::={shapingOutofpacketsDropsLevelTable 1}

ShapingOutofpacketsDropsLevelEntry ::=
	SEQUENCE {
		shapingOutofpacketsDropsLevelName	DisplayString,
		shapingOutofpacketsDropsLevelVal	Counter64,
		shapingOutofpacketsDropsLevelMom	CounterBasedGauge64,
		shapingOutofpacketsDropsLevelMax	CounterBasedGauge64
	}

shapingOutofpacketsDropsLevelName OBJECT-TYPE
	SYNTAX      DisplayString
	MAX-ACCESS  not-accessible
	STATUS      current
	DESCRIPTION
	"Table entry display string for shapingOutofpacketsDrops"
	::={shapingOutofpacketsDropsLevelEntry 1}

shapingOutofpacketsDropsLevelVal OBJECT-TYPE
	SYNTAX	 Counter64
	MAX-ACCESS  read-only
	STATUS      current
	DESCRIPTION
	"Table entry attribute for shapingOutofpacketsDrops"
	::={shapingOutofpacketsDropsLevelEntry 2}

shapingOutofpacketsDropsLevelMom OBJECT-TYPE
	SYNTAX	 CounterBasedGauge64
	MAX-ACCESS  read-only
	STATUS      current
	DESCRIPTION
	"Table entry attribute for shapingOutofpacketsDrops"
	::={shapingOutofpacketsDropsLevelEntry 3}

shapingOutofpacketsDropsLevelMax OBJECT-TYPE
	SYNTAX	 CounterBasedGauge64
	MAX-ACCESS  read-only
	STATUS      current
	DESCRIPTION
	"Table entry attribute for shapingOutofpacketsDrops"
	::={shapingOutofpacketsDropsLevelEntry 4}


shapingReceived	OBJECT IDENTIFIER ::={shaping 16}

shapingReceivedVal	OBJECT-TYPE
	SYNTAX	 Counter64
	MAX-ACCESS read-only
	STATUS current
	DESCRIPTION "Packets received"

	::={shapingReceived 1}

shapingReceivedMom	OBJECT-TYPE
	SYNTAX	 CounterBasedGauge64
	MAX-ACCESS read-only
	STATUS current
	DESCRIPTION "Packets received"

	::={shapingReceived 2}

shapingReceivedMax	OBJECT-TYPE
	SYNTAX	 CounterBasedGauge64
	MAX-ACCESS read-only
	STATUS current
	DESCRIPTION "Packets received"

	::={shapingReceived 3}

shapingReceivedLevelTable OBJECT-TYPE
	SYNTAX      SEQUENCE OF ShapingReceivedLevelEntry
	MAX-ACCESS  not-accessible
	STATUS      current
	DESCRIPTION
	"Table for shapingReceived"
	::={shapingReceived 4}

shapingReceivedLevelEntry OBJECT-TYPE
	SYNTAX      ShapingReceivedLevelEntry
	MAX-ACCESS  not-accessible
	STATUS      current
	DESCRIPTION
	"Table entry for shapingReceived"
	INDEX { shapingReceivedLevelName }
	::={shapingReceivedLevelTable 1}

ShapingReceivedLevelEntry ::=
	SEQUENCE {
		shapingReceivedLevelName	DisplayString,
		shapingReceivedLevelVal	Counter64,
		shapingReceivedLevelMom	CounterBasedGauge64,
		shapingReceivedLevelMax	CounterBasedGauge64
	}

shapingReceivedLevelName OBJECT-TYPE
	SYNTAX      DisplayString
	MAX-ACCESS  not-accessible
	STATUS      current
	DESCRIPTION
	"Table entry display string for shapingReceived"
	::={shapingReceivedLevelEntry 1}

shapingReceivedLevelVal OBJECT-TYPE
	SYNTAX	 Counter64
	MAX-ACCESS  read-only
	STATUS      current
	DESCRIPTION
	"Table entry attribute for shapingReceived"
	::={shapingReceivedLevelEntry 2}

shapingReceivedLevelMom OBJECT-TYPE
	SYNTAX	 CounterBasedGauge64
	MAX-ACCESS  read-only
	STATUS      current
	DESCRIPTION
	"Table entry attribute for shapingReceived"
	::={shapingReceivedLevelEntry 3}

shapingReceivedLevelMax OBJECT-TYPE
	SYNTAX	 CounterBasedGauge64
	MAX-ACCESS  read-only
	STATUS      current
	DESCRIPTION
	"Table entry attribute for shapingReceived"
	::={shapingReceivedLevelEntry 4}


shapingObjectChecks	OBJECT IDENTIFIER ::={shaping 17}

shapingObjectChecksVal	OBJECT-TYPE
	SYNTAX	 Counter64
	MAX-ACCESS read-only
	STATUS current
	DESCRIPTION "Object checks"

	::={shapingObjectChecks 1}

shapingObjectChecksMom	OBJECT-TYPE
	SYNTAX	 CounterBasedGauge64
	MAX-ACCESS read-only
	STATUS current
	DESCRIPTION "Object checks"

	::={shapingObjectChecks 2}

shapingObjectChecksMax	OBJECT-TYPE
	SYNTAX	 CounterBasedGauge64
	MAX-ACCESS read-only
	STATUS current
	DESCRIPTION "Object checks"

	::={shapingObjectChecks 3}

shapingObjectChecksLevelTable OBJECT-TYPE
	SYNTAX      SEQUENCE OF ShapingObjectChecksLevelEntry
	MAX-ACCESS  not-accessible
	STATUS      current
	DESCRIPTION
	"Table for shapingObjectChecks"
	::={shapingObjectChecks 4}

shapingObjectChecksLevelEntry OBJECT-TYPE
	SYNTAX      ShapingObjectChecksLevelEntry
	MAX-ACCESS  not-accessible
	STATUS      current
	DESCRIPTION
	"Table entry for shapingObjectChecks"
	INDEX { shapingObjectChecksLevelName }
	::={shapingObjectChecksLevelTable 1}

ShapingObjectChecksLevelEntry ::=
	SEQUENCE {
		shapingObjectChecksLevelName	DisplayString,
		shapingObjectChecksLevelVal	Counter64,
		shapingObjectChecksLevelMom	CounterBasedGauge64,
		shapingObjectChecksLevelMax	CounterBasedGauge64
	}

shapingObjectChecksLevelName OBJECT-TYPE
	SYNTAX      DisplayString
	MAX-ACCESS  not-accessible
	STATUS      current
	DESCRIPTION
	"Table entry display string for shapingObjectChecks"
	::={shapingObjectChecksLevelEntry 1}

shapingObjectChecksLevelVal OBJECT-TYPE
	SYNTAX	 Counter64
	MAX-ACCESS  read-only
	STATUS      current
	DESCRIPTION
	"Table entry attribute for shapingObjectChecks"
	::={shapingObjectChecksLevelEntry 2}

shapingObjectChecksLevelMom OBJECT-TYPE
	SYNTAX	 CounterBasedGauge64
	MAX-ACCESS  read-only
	STATUS      current
	DESCRIPTION
	"Table entry attribute for shapingObjectChecks"
	::={shapingObjectChecksLevelEntry 3}

shapingObjectChecksLevelMax OBJECT-TYPE
	SYNTAX	 CounterBasedGauge64
	MAX-ACCESS  read-only
	STATUS      current
	DESCRIPTION
	"Table entry attribute for shapingObjectChecks"
	::={shapingObjectChecksLevelEntry 4}


shapingObjectPoolExhausted	OBJECT IDENTIFIER ::={shaping 25}

shapingObjectPoolExhaustedVal	OBJECT-TYPE
	SYNTAX	 Counter64
	MAX-ACCESS read-only
	STATUS current
	DESCRIPTION "Too many dynamic objects"

	::={shapingObjectPoolExhausted 1}

shapingObjectPoolExhaustedMom	OBJECT-TYPE
	SYNTAX	 CounterBasedGauge64
	MAX-ACCESS read-only
	STATUS current
	DESCRIPTION "Too many dynamic objects"

	::={shapingObjectPoolExhausted 2}

shapingObjectPoolExhaustedMax	OBJECT-TYPE
	SYNTAX	 CounterBasedGauge64
	MAX-ACCESS read-only
	STATUS current
	DESCRIPTION "Too many dynamic objects"

	::={shapingObjectPoolExhausted 3}

shapingObjectPoolExhaustedLevelTable OBJECT-TYPE
	SYNTAX      SEQUENCE OF ShapingObjectPoolExhaustedLevelEntry
	MAX-ACCESS  not-accessible
	STATUS      current
	DESCRIPTION
	"Table for shapingObjectPoolExhausted"
	::={shapingObjectPoolExhausted 4}

shapingObjectPoolExhaustedLevelEntry OBJECT-TYPE
	SYNTAX      ShapingObjectPoolExhaustedLevelEntry
	MAX-ACCESS  not-accessible
	STATUS      current
	DESCRIPTION
	"Table entry for shapingObjectPoolExhausted"
	INDEX { shapingObjectPoolExhaustedLevelName }
	::={shapingObjectPoolExhaustedLevelTable 1}

ShapingObjectPoolExhaustedLevelEntry ::=
	SEQUENCE {
		shapingObjectPoolExhaustedLevelName	DisplayString,
		shapingObjectPoolExhaustedLevelVal	Counter64,
		shapingObjectPoolExhaustedLevelMom	CounterBasedGauge64,
		shapingObjectPoolExhaustedLevelMax	CounterBasedGauge64
	}

shapingObjectPoolExhaustedLevelName OBJECT-TYPE
	SYNTAX      DisplayString
	MAX-ACCESS  not-accessible
	STATUS      current
	DESCRIPTION
	"Table entry display string for shapingObjectPoolExhausted"
	::={shapingObjectPoolExhaustedLevelEntry 1}

shapingObjectPoolExhaustedLevelVal OBJECT-TYPE
	SYNTAX	 Counter64
	MAX-ACCESS  read-only
	STATUS      current
	DESCRIPTION
	"Table entry attribute for shapingObjectPoolExhausted"
	::={shapingObjectPoolExhaustedLevelEntry 2}

shapingObjectPoolExhaustedLevelMom OBJECT-TYPE
	SYNTAX	 CounterBasedGauge64
	MAX-ACCESS  read-only
	STATUS      current
	DESCRIPTION
	"Table entry attribute for shapingObjectPoolExhausted"
	::={shapingObjectPoolExhaustedLevelEntry 3}

shapingObjectPoolExhaustedLevelMax OBJECT-TYPE
	SYNTAX	 CounterBasedGauge64
	MAX-ACCESS  read-only
	STATUS      current
	DESCRIPTION
	"Table entry attribute for shapingObjectPoolExhausted"
	::={shapingObjectPoolExhaustedLevelEntry 4}


shapingOutOfCreditsDrops	OBJECT IDENTIFIER ::={shaping 26}

shapingOutOfCreditsDropsVal	OBJECT-TYPE
	SYNTAX	 Counter64
	MAX-ACCESS read-only
	STATUS obsolete
	DESCRIPTION "Out of credits (vbs) drops"

	::={shapingOutOfCreditsDrops 1}

shapingOutOfCreditsDropsMom	OBJECT-TYPE
	SYNTAX	 CounterBasedGauge64
	MAX-ACCESS read-only
	STATUS obsolete
	DESCRIPTION "Out of credits (vbs) drops"

	::={shapingOutOfCreditsDrops 2}

shapingOutOfCreditsDropsMax	OBJECT-TYPE
	SYNTAX	 CounterBasedGauge64
	MAX-ACCESS read-only
	STATUS obsolete
	DESCRIPTION "Out of credits (vbs) drops"

	::={shapingOutOfCreditsDrops 3}

shapingOutOfCreditsDropsLevelTable OBJECT-TYPE
	SYNTAX      SEQUENCE OF ShapingOutOfCreditsDropsLevelEntry
	MAX-ACCESS  not-accessible
	STATUS      current
	DESCRIPTION
	"Table for shapingOutOfCreditsDrops"
	::={shapingOutOfCreditsDrops 4}

shapingOutOfCreditsDropsLevelEntry OBJECT-TYPE
	SYNTAX      ShapingOutOfCreditsDropsLevelEntry
	MAX-ACCESS  not-accessible
	STATUS      current
	DESCRIPTION
	"Table entry for shapingOutOfCreditsDrops"
	INDEX { shapingOutOfCreditsDropsLevelName }
	::={shapingOutOfCreditsDropsLevelTable 1}

ShapingOutOfCreditsDropsLevelEntry ::=
	SEQUENCE {
		shapingOutOfCreditsDropsLevelName	DisplayString,
		shapingOutOfCreditsDropsLevelVal	Counter64,
		shapingOutOfCreditsDropsLevelMom	CounterBasedGauge64,
		shapingOutOfCreditsDropsLevelMax	CounterBasedGauge64
	}

shapingOutOfCreditsDropsLevelName OBJECT-TYPE
	SYNTAX      DisplayString
	MAX-ACCESS  not-accessible
	STATUS      current
	DESCRIPTION
	"Table entry display string for shapingOutOfCreditsDrops"
	::={shapingOutOfCreditsDropsLevelEntry 1}

shapingOutOfCreditsDropsLevelVal OBJECT-TYPE
	SYNTAX	 Counter64
	MAX-ACCESS  read-only
	STATUS      current
	DESCRIPTION
	"Table entry attribute for shapingOutOfCreditsDrops"
	::={shapingOutOfCreditsDropsLevelEntry 2}

shapingOutOfCreditsDropsLevelMom OBJECT-TYPE
	SYNTAX	 CounterBasedGauge64
	MAX-ACCESS  read-only
	STATUS      current
	DESCRIPTION
	"Table entry attribute for shapingOutOfCreditsDrops"
	::={shapingOutOfCreditsDropsLevelEntry 3}

shapingOutOfCreditsDropsLevelMax OBJECT-TYPE
	SYNTAX	 CounterBasedGauge64
	MAX-ACCESS  read-only
	STATUS      current
	DESCRIPTION
	"Table entry attribute for shapingOutOfCreditsDrops"
	::={shapingOutOfCreditsDropsLevelEntry 4}


shapingObjectOverflow	OBJECT IDENTIFIER ::={shaping 31}

shapingObjectOverflowVal	OBJECT-TYPE
	SYNTAX	 Counter64
	MAX-ACCESS read-only
	STATUS current
	DESCRIPTION "Too many shaping objects matching a connection"

	::={shapingObjectOverflow 1}

shapingObjectOverflowMom	OBJECT-TYPE
	SYNTAX	 CounterBasedGauge64
	MAX-ACCESS read-only
	STATUS current
	DESCRIPTION "Too many shaping objects matching a connection"

	::={shapingObjectOverflow 2}

shapingObjectOverflowMax	OBJECT-TYPE
	SYNTAX	 CounterBasedGauge64
	MAX-ACCESS read-only
	STATUS current
	DESCRIPTION "Too many shaping objects matching a connection"

	::={shapingObjectOverflow 3}

shapingObjectOverflowLevelTable OBJECT-TYPE
	SYNTAX      SEQUENCE OF ShapingObjectOverflowLevelEntry
	MAX-ACCESS  not-accessible
	STATUS      current
	DESCRIPTION
	"Table for shapingObjectOverflow"
	::={shapingObjectOverflow 4}

shapingObjectOverflowLevelEntry OBJECT-TYPE
	SYNTAX      ShapingObjectOverflowLevelEntry
	MAX-ACCESS  not-accessible
	STATUS      current
	DESCRIPTION
	"Table entry for shapingObjectOverflow"
	INDEX { shapingObjectOverflowLevelName }
	::={shapingObjectOverflowLevelTable 1}

ShapingObjectOverflowLevelEntry ::=
	SEQUENCE {
		shapingObjectOverflowLevelName	DisplayString,
		shapingObjectOverflowLevelVal	Counter64,
		shapingObjectOverflowLevelMom	CounterBasedGauge64,
		shapingObjectOverflowLevelMax	CounterBasedGauge64
	}

shapingObjectOverflowLevelName OBJECT-TYPE
	SYNTAX      DisplayString
	MAX-ACCESS  not-accessible
	STATUS      current
	DESCRIPTION
	"Table entry display string for shapingObjectOverflow"
	::={shapingObjectOverflowLevelEntry 1}

shapingObjectOverflowLevelVal OBJECT-TYPE
	SYNTAX	 Counter64
	MAX-ACCESS  read-only
	STATUS      current
	DESCRIPTION
	"Table entry attribute for shapingObjectOverflow"
	::={shapingObjectOverflowLevelEntry 2}

shapingObjectOverflowLevelMom OBJECT-TYPE
	SYNTAX	 CounterBasedGauge64
	MAX-ACCESS  read-only
	STATUS      current
	DESCRIPTION
	"Table entry attribute for shapingObjectOverflow"
	::={shapingObjectOverflowLevelEntry 3}

shapingObjectOverflowLevelMax OBJECT-TYPE
	SYNTAX	 CounterBasedGauge64
	MAX-ACCESS  read-only
	STATUS      current
	DESCRIPTION
	"Table entry attribute for shapingObjectOverflow"
	::={shapingObjectOverflowLevelEntry 4}


shapingRuleOverflow	OBJECT IDENTIFIER ::={shaping 32}

shapingRuleOverflowVal	OBJECT-TYPE
	SYNTAX	 Counter64
	MAX-ACCESS read-only
	STATUS current
	DESCRIPTION "Too many matching rules"

	::={shapingRuleOverflow 1}

shapingRuleOverflowMom	OBJECT-TYPE
	SYNTAX	 CounterBasedGauge64
	MAX-ACCESS read-only
	STATUS current
	DESCRIPTION "Too many matching rules"

	::={shapingRuleOverflow 2}

shapingRuleOverflowMax	OBJECT-TYPE
	SYNTAX	 CounterBasedGauge64
	MAX-ACCESS read-only
	STATUS current
	DESCRIPTION "Too many matching rules"

	::={shapingRuleOverflow 3}

shapingRuleOverflowLevelTable OBJECT-TYPE
	SYNTAX      SEQUENCE OF ShapingRuleOverflowLevelEntry
	MAX-ACCESS  not-accessible
	STATUS      current
	DESCRIPTION
	"Table for shapingRuleOverflow"
	::={shapingRuleOverflow 4}

shapingRuleOverflowLevelEntry OBJECT-TYPE
	SYNTAX      ShapingRuleOverflowLevelEntry
	MAX-ACCESS  not-accessible
	STATUS      current
	DESCRIPTION
	"Table entry for shapingRuleOverflow"
	INDEX { shapingRuleOverflowLevelName }
	::={shapingRuleOverflowLevelTable 1}

ShapingRuleOverflowLevelEntry ::=
	SEQUENCE {
		shapingRuleOverflowLevelName	DisplayString,
		shapingRuleOverflowLevelVal	Counter64,
		shapingRuleOverflowLevelMom	CounterBasedGauge64,
		shapingRuleOverflowLevelMax	CounterBasedGauge64
	}

shapingRuleOverflowLevelName OBJECT-TYPE
	SYNTAX      DisplayString
	MAX-ACCESS  not-accessible
	STATUS      current
	DESCRIPTION
	"Table entry display string for shapingRuleOverflow"
	::={shapingRuleOverflowLevelEntry 1}

shapingRuleOverflowLevelVal OBJECT-TYPE
	SYNTAX	 Counter64
	MAX-ACCESS  read-only
	STATUS      current
	DESCRIPTION
	"Table entry attribute for shapingRuleOverflow"
	::={shapingRuleOverflowLevelEntry 2}

shapingRuleOverflowLevelMom OBJECT-TYPE
	SYNTAX	 CounterBasedGauge64
	MAX-ACCESS  read-only
	STATUS      current
	DESCRIPTION
	"Table entry attribute for shapingRuleOverflow"
	::={shapingRuleOverflowLevelEntry 3}

shapingRuleOverflowLevelMax OBJECT-TYPE
	SYNTAX	 CounterBasedGauge64
	MAX-ACCESS  read-only
	STATUS      current
	DESCRIPTION
	"Table entry attribute for shapingRuleOverflow"
	::={shapingRuleOverflowLevelEntry 4}


shapingDrops	OBJECT IDENTIFIER ::={shaping 37}

shapingDropsVal	OBJECT-TYPE
	SYNTAX	 Counter64
	MAX-ACCESS read-only
	STATUS current
	DESCRIPTION "Queuing drops (all types)"

	::={shapingDrops 1}

shapingDropsMom	OBJECT-TYPE
	SYNTAX	 CounterBasedGauge64
	MAX-ACCESS read-only
	STATUS current
	DESCRIPTION "Queuing drops (all types)"

	::={shapingDrops 2}

shapingDropsMax	OBJECT-TYPE
	SYNTAX	 CounterBasedGauge64
	MAX-ACCESS read-only
	STATUS current
	DESCRIPTION "Queuing drops (all types)"

	::={shapingDrops 3}

shapingDropsLevelTable OBJECT-TYPE
	SYNTAX      SEQUENCE OF ShapingDropsLevelEntry
	MAX-ACCESS  not-accessible
	STATUS      current
	DESCRIPTION
	"Table for shapingDrops"
	::={shapingDrops 4}

shapingDropsLevelEntry OBJECT-TYPE
	SYNTAX      ShapingDropsLevelEntry
	MAX-ACCESS  not-accessible
	STATUS      current
	DESCRIPTION
	"Table entry for shapingDrops"
	INDEX { shapingDropsLevelName }
	::={shapingDropsLevelTable 1}

ShapingDropsLevelEntry ::=
	SEQUENCE {
		shapingDropsLevelName	DisplayString,
		shapingDropsLevelVal	Counter64,
		shapingDropsLevelMom	CounterBasedGauge64,
		shapingDropsLevelMax	CounterBasedGauge64
	}

shapingDropsLevelName OBJECT-TYPE
	SYNTAX      DisplayString
	MAX-ACCESS  not-accessible
	STATUS      current
	DESCRIPTION
	"Table entry display string for shapingDrops"
	::={shapingDropsLevelEntry 1}

shapingDropsLevelVal OBJECT-TYPE
	SYNTAX	 Counter64
	MAX-ACCESS  read-only
	STATUS      current
	DESCRIPTION
	"Table entry attribute for shapingDrops"
	::={shapingDropsLevelEntry 2}

shapingDropsLevelMom OBJECT-TYPE
	SYNTAX	 CounterBasedGauge64
	MAX-ACCESS  read-only
	STATUS      current
	DESCRIPTION
	"Table entry attribute for shapingDrops"
	::={shapingDropsLevelEntry 3}

shapingDropsLevelMax OBJECT-TYPE
	SYNTAX	 CounterBasedGauge64
	MAX-ACCESS  read-only
	STATUS      current
	DESCRIPTION
	"Table entry attribute for shapingDrops"
	::={shapingDropsLevelEntry 4}


shapingObjectFull	OBJECT IDENTIFIER ::={shaping 38}

shapingObjectFullVal	OBJECT-TYPE
	SYNTAX	 Counter64
	MAX-ACCESS read-only
	STATUS obsolete
	DESCRIPTION "Shaping object queue full"

	::={shapingObjectFull 1}

shapingObjectFullMom	OBJECT-TYPE
	SYNTAX	 CounterBasedGauge64
	MAX-ACCESS read-only
	STATUS obsolete
	DESCRIPTION "Shaping object queue full"

	::={shapingObjectFull 2}

shapingObjectFullMax	OBJECT-TYPE
	SYNTAX	 CounterBasedGauge64
	MAX-ACCESS read-only
	STATUS obsolete
	DESCRIPTION "Shaping object queue full"

	::={shapingObjectFull 3}

shapingObjectFullLevelTable OBJECT-TYPE
	SYNTAX      SEQUENCE OF ShapingObjectFullLevelEntry
	MAX-ACCESS  not-accessible
	STATUS      current
	DESCRIPTION
	"Table for shapingObjectFull"
	::={shapingObjectFull 4}

shapingObjectFullLevelEntry OBJECT-TYPE
	SYNTAX      ShapingObjectFullLevelEntry
	MAX-ACCESS  not-accessible
	STATUS      current
	DESCRIPTION
	"Table entry for shapingObjectFull"
	INDEX { shapingObjectFullLevelName }
	::={shapingObjectFullLevelTable 1}

ShapingObjectFullLevelEntry ::=
	SEQUENCE {
		shapingObjectFullLevelName	DisplayString,
		shapingObjectFullLevelVal	Counter64,
		shapingObjectFullLevelMom	CounterBasedGauge64,
		shapingObjectFullLevelMax	CounterBasedGauge64
	}

shapingObjectFullLevelName OBJECT-TYPE
	SYNTAX      DisplayString
	MAX-ACCESS  not-accessible
	STATUS      current
	DESCRIPTION
	"Table entry display string for shapingObjectFull"
	::={shapingObjectFullLevelEntry 1}

shapingObjectFullLevelVal OBJECT-TYPE
	SYNTAX	 Counter64
	MAX-ACCESS  read-only
	STATUS      current
	DESCRIPTION
	"Table entry attribute for shapingObjectFull"
	::={shapingObjectFullLevelEntry 2}

shapingObjectFullLevelMom OBJECT-TYPE
	SYNTAX	 CounterBasedGauge64
	MAX-ACCESS  read-only
	STATUS      current
	DESCRIPTION
	"Table entry attribute for shapingObjectFull"
	::={shapingObjectFullLevelEntry 3}

shapingObjectFullLevelMax OBJECT-TYPE
	SYNTAX	 CounterBasedGauge64
	MAX-ACCESS  read-only
	STATUS      current
	DESCRIPTION
	"Table entry attribute for shapingObjectFull"
	::={shapingObjectFullLevelEntry 4}


shapingUnshaped	OBJECT IDENTIFIER ::={shaping 39}

shapingUnshapedVal	OBJECT-TYPE
	SYNTAX	 Counter64
	MAX-ACCESS read-only
	STATUS current
	DESCRIPTION "Unshaped packets"

	::={shapingUnshaped 1}

shapingUnshapedMom	OBJECT-TYPE
	SYNTAX	 CounterBasedGauge64
	MAX-ACCESS read-only
	STATUS current
	DESCRIPTION "Unshaped packets"

	::={shapingUnshaped 2}

shapingUnshapedMax	OBJECT-TYPE
	SYNTAX	 CounterBasedGauge64
	MAX-ACCESS read-only
	STATUS current
	DESCRIPTION "Unshaped packets"

	::={shapingUnshaped 3}

shapingUnshapedLevelTable OBJECT-TYPE
	SYNTAX      SEQUENCE OF ShapingUnshapedLevelEntry
	MAX-ACCESS  not-accessible
	STATUS      current
	DESCRIPTION
	"Table for shapingUnshaped"
	::={shapingUnshaped 4}

shapingUnshapedLevelEntry OBJECT-TYPE
	SYNTAX      ShapingUnshapedLevelEntry
	MAX-ACCESS  not-accessible
	STATUS      current
	DESCRIPTION
	"Table entry for shapingUnshaped"
	INDEX { shapingUnshapedLevelName }
	::={shapingUnshapedLevelTable 1}

ShapingUnshapedLevelEntry ::=
	SEQUENCE {
		shapingUnshapedLevelName	DisplayString,
		shapingUnshapedLevelVal	Counter64,
		shapingUnshapedLevelMom	CounterBasedGauge64,
		shapingUnshapedLevelMax	CounterBasedGauge64
	}

shapingUnshapedLevelName OBJECT-TYPE
	SYNTAX      DisplayString
	MAX-ACCESS  not-accessible
	STATUS      current
	DESCRIPTION
	"Table entry display string for shapingUnshaped"
	::={shapingUnshapedLevelEntry 1}

shapingUnshapedLevelVal OBJECT-TYPE
	SYNTAX	 Counter64
	MAX-ACCESS  read-only
	STATUS      current
	DESCRIPTION
	"Table entry attribute for shapingUnshaped"
	::={shapingUnshapedLevelEntry 2}

shapingUnshapedLevelMom OBJECT-TYPE
	SYNTAX	 CounterBasedGauge64
	MAX-ACCESS  read-only
	STATUS      current
	DESCRIPTION
	"Table entry attribute for shapingUnshaped"
	::={shapingUnshapedLevelEntry 3}

shapingUnshapedLevelMax OBJECT-TYPE
	SYNTAX	 CounterBasedGauge64
	MAX-ACCESS  read-only
	STATUS      current
	DESCRIPTION
	"Table entry attribute for shapingUnshaped"
	::={shapingUnshapedLevelEntry 4}


shapingUnshapedBytes	OBJECT IDENTIFIER ::={shaping 40}

shapingUnshapedBytesVal	OBJECT-TYPE
	SYNTAX	 Counter64
	MAX-ACCESS read-only
	STATUS current
	DESCRIPTION "Unshaped bytes"

	::={shapingUnshapedBytes 1}

shapingUnshapedBytesMom	OBJECT-TYPE
	SYNTAX	 CounterBasedGauge64
	MAX-ACCESS read-only
	STATUS current
	DESCRIPTION "Unshaped bytes"

	::={shapingUnshapedBytes 2}

shapingUnshapedBytesMax	OBJECT-TYPE
	SYNTAX	 CounterBasedGauge64
	MAX-ACCESS read-only
	STATUS current
	DESCRIPTION "Unshaped bytes"

	::={shapingUnshapedBytes 3}

shapingUnshapedBytesLevelTable OBJECT-TYPE
	SYNTAX      SEQUENCE OF ShapingUnshapedBytesLevelEntry
	MAX-ACCESS  not-accessible
	STATUS      current
	DESCRIPTION
	"Table for shapingUnshapedBytes"
	::={shapingUnshapedBytes 4}

shapingUnshapedBytesLevelEntry OBJECT-TYPE
	SYNTAX      ShapingUnshapedBytesLevelEntry
	MAX-ACCESS  not-accessible
	STATUS      current
	DESCRIPTION
	"Table entry for shapingUnshapedBytes"
	INDEX { shapingUnshapedBytesLevelName }
	::={shapingUnshapedBytesLevelTable 1}

ShapingUnshapedBytesLevelEntry ::=
	SEQUENCE {
		shapingUnshapedBytesLevelName	DisplayString,
		shapingUnshapedBytesLevelVal	Counter64,
		shapingUnshapedBytesLevelMom	CounterBasedGauge64,
		shapingUnshapedBytesLevelMax	CounterBasedGauge64
	}

shapingUnshapedBytesLevelName OBJECT-TYPE
	SYNTAX      DisplayString
	MAX-ACCESS  not-accessible
	STATUS      current
	DESCRIPTION
	"Table entry display string for shapingUnshapedBytes"
	::={shapingUnshapedBytesLevelEntry 1}

shapingUnshapedBytesLevelVal OBJECT-TYPE
	SYNTAX	 Counter64
	MAX-ACCESS  read-only
	STATUS      current
	DESCRIPTION
	"Table entry attribute for shapingUnshapedBytes"
	::={shapingUnshapedBytesLevelEntry 2}

shapingUnshapedBytesLevelMom OBJECT-TYPE
	SYNTAX	 CounterBasedGauge64
	MAX-ACCESS  read-only
	STATUS      current
	DESCRIPTION
	"Table entry attribute for shapingUnshapedBytes"
	::={shapingUnshapedBytesLevelEntry 3}

shapingUnshapedBytesLevelMax OBJECT-TYPE
	SYNTAX	 CounterBasedGauge64
	MAX-ACCESS  read-only
	STATUS      current
	DESCRIPTION
	"Table entry attribute for shapingUnshapedBytes"
	::={shapingUnshapedBytesLevelEntry 4}


shapingDequeueCalls	OBJECT IDENTIFIER ::={shaping 41}

shapingDequeueCallsVal	OBJECT-TYPE
	SYNTAX	 Counter64
	MAX-ACCESS read-only
	STATUS current
	DESCRIPTION "Dequeue calls"

	::={shapingDequeueCalls 1}

shapingDequeueCallsMom	OBJECT-TYPE
	SYNTAX	 CounterBasedGauge64
	MAX-ACCESS read-only
	STATUS current
	DESCRIPTION "Dequeue calls"

	::={shapingDequeueCalls 2}

shapingDequeueCallsMax	OBJECT-TYPE
	SYNTAX	 CounterBasedGauge64
	MAX-ACCESS read-only
	STATUS current
	DESCRIPTION "Dequeue calls"

	::={shapingDequeueCalls 3}

shapingDequeueCallsLevelTable OBJECT-TYPE
	SYNTAX      SEQUENCE OF ShapingDequeueCallsLevelEntry
	MAX-ACCESS  not-accessible
	STATUS      current
	DESCRIPTION
	"Table for shapingDequeueCalls"
	::={shapingDequeueCalls 4}

shapingDequeueCallsLevelEntry OBJECT-TYPE
	SYNTAX      ShapingDequeueCallsLevelEntry
	MAX-ACCESS  not-accessible
	STATUS      current
	DESCRIPTION
	"Table entry for shapingDequeueCalls"
	INDEX { shapingDequeueCallsLevelName }
	::={shapingDequeueCallsLevelTable 1}

ShapingDequeueCallsLevelEntry ::=
	SEQUENCE {
		shapingDequeueCallsLevelName	DisplayString,
		shapingDequeueCallsLevelVal	Counter64,
		shapingDequeueCallsLevelMom	CounterBasedGauge64,
		shapingDequeueCallsLevelMax	CounterBasedGauge64
	}

shapingDequeueCallsLevelName OBJECT-TYPE
	SYNTAX      DisplayString
	MAX-ACCESS  not-accessible
	STATUS      current
	DESCRIPTION
	"Table entry display string for shapingDequeueCalls"
	::={shapingDequeueCallsLevelEntry 1}

shapingDequeueCallsLevelVal OBJECT-TYPE
	SYNTAX	 Counter64
	MAX-ACCESS  read-only
	STATUS      current
	DESCRIPTION
	"Table entry attribute for shapingDequeueCalls"
	::={shapingDequeueCallsLevelEntry 2}

shapingDequeueCallsLevelMom OBJECT-TYPE
	SYNTAX	 CounterBasedGauge64
	MAX-ACCESS  read-only
	STATUS      current
	DESCRIPTION
	"Table entry attribute for shapingDequeueCalls"
	::={shapingDequeueCallsLevelEntry 3}

shapingDequeueCallsLevelMax OBJECT-TYPE
	SYNTAX	 CounterBasedGauge64
	MAX-ACCESS  read-only
	STATUS      current
	DESCRIPTION
	"Table entry attribute for shapingDequeueCalls"
	::={shapingDequeueCallsLevelEntry 4}


shapingRecycleObjects	OBJECT IDENTIFIER ::={shaping 42}

shapingRecycleObjectsVal	OBJECT-TYPE
	SYNTAX	 CounterBasedGauge64
	MAX-ACCESS read-only
	STATUS obsolete
	DESCRIPTION "Objects in recycle queue"

	::={shapingRecycleObjects 1}

shapingRecycleObjectsMax	OBJECT-TYPE
	SYNTAX	 CounterBasedGauge64
	MAX-ACCESS read-only
	STATUS obsolete
	DESCRIPTION "Objects in recycle queue"

	::={shapingRecycleObjects 3}

shapingRecycleObjectsLevelTable OBJECT-TYPE
	SYNTAX      SEQUENCE OF ShapingRecycleObjectsLevelEntry
	MAX-ACCESS  not-accessible
	STATUS      current
	DESCRIPTION
	"Table for shapingRecycleObjects"
	::={shapingRecycleObjects 4}

shapingRecycleObjectsLevelEntry OBJECT-TYPE
	SYNTAX      ShapingRecycleObjectsLevelEntry
	MAX-ACCESS  not-accessible
	STATUS      current
	DESCRIPTION
	"Table entry for shapingRecycleObjects"
	INDEX { shapingRecycleObjectsLevelName }
	::={shapingRecycleObjectsLevelTable 1}

ShapingRecycleObjectsLevelEntry ::=
	SEQUENCE {
		shapingRecycleObjectsLevelName	DisplayString,
		shapingRecycleObjectsLevelVal	CounterBasedGauge64,
		shapingRecycleObjectsLevelMax	CounterBasedGauge64
	}

shapingRecycleObjectsLevelName OBJECT-TYPE
	SYNTAX      DisplayString
	MAX-ACCESS  not-accessible
	STATUS      current
	DESCRIPTION
	"Table entry display string for shapingRecycleObjects"
	::={shapingRecycleObjectsLevelEntry 1}

shapingRecycleObjectsLevelVal OBJECT-TYPE
	SYNTAX	 CounterBasedGauge64
	MAX-ACCESS  read-only
	STATUS      current
	DESCRIPTION
	"Table entry attribute for shapingRecycleObjects"
	::={shapingRecycleObjectsLevelEntry 2}

shapingRecycleObjectsLevelMax OBJECT-TYPE
	SYNTAX	 CounterBasedGauge64
	MAX-ACCESS  read-only
	STATUS      current
	DESCRIPTION
	"Table entry attribute for shapingRecycleObjects"
	::={shapingRecycleObjectsLevelEntry 4}


shapingDirect	OBJECT IDENTIFIER ::={shaping 44}

shapingDirectVal	OBJECT-TYPE
	SYNTAX	 Counter64
	MAX-ACCESS read-only
	STATUS current
	DESCRIPTION "Directly sent packets"

	::={shapingDirect 1}

shapingDirectMom	OBJECT-TYPE
	SYNTAX	 CounterBasedGauge64
	MAX-ACCESS read-only
	STATUS current
	DESCRIPTION "Directly sent packets"

	::={shapingDirect 2}

shapingDirectMax	OBJECT-TYPE
	SYNTAX	 CounterBasedGauge64
	MAX-ACCESS read-only
	STATUS current
	DESCRIPTION "Directly sent packets"

	::={shapingDirect 3}

shapingDirectLevelTable OBJECT-TYPE
	SYNTAX      SEQUENCE OF ShapingDirectLevelEntry
	MAX-ACCESS  not-accessible
	STATUS      current
	DESCRIPTION
	"Table for shapingDirect"
	::={shapingDirect 4}

shapingDirectLevelEntry OBJECT-TYPE
	SYNTAX      ShapingDirectLevelEntry
	MAX-ACCESS  not-accessible
	STATUS      current
	DESCRIPTION
	"Table entry for shapingDirect"
	INDEX { shapingDirectLevelName }
	::={shapingDirectLevelTable 1}

ShapingDirectLevelEntry ::=
	SEQUENCE {
		shapingDirectLevelName	DisplayString,
		shapingDirectLevelVal	Counter64,
		shapingDirectLevelMom	CounterBasedGauge64,
		shapingDirectLevelMax	CounterBasedGauge64
	}

shapingDirectLevelName OBJECT-TYPE
	SYNTAX      DisplayString
	MAX-ACCESS  not-accessible
	STATUS      current
	DESCRIPTION
	"Table entry display string for shapingDirect"
	::={shapingDirectLevelEntry 1}

shapingDirectLevelVal OBJECT-TYPE
	SYNTAX	 Counter64
	MAX-ACCESS  read-only
	STATUS      current
	DESCRIPTION
	"Table entry attribute for shapingDirect"
	::={shapingDirectLevelEntry 2}

shapingDirectLevelMom OBJECT-TYPE
	SYNTAX	 CounterBasedGauge64
	MAX-ACCESS  read-only
	STATUS      current
	DESCRIPTION
	"Table entry attribute for shapingDirect"
	::={shapingDirectLevelEntry 3}

shapingDirectLevelMax OBJECT-TYPE
	SYNTAX	 CounterBasedGauge64
	MAX-ACCESS  read-only
	STATUS      current
	DESCRIPTION
	"Table entry attribute for shapingDirect"
	::={shapingDirectLevelEntry 4}


shapingDirectBytes	OBJECT IDENTIFIER ::={shaping 45}

shapingDirectBytesVal	OBJECT-TYPE
	SYNTAX	 Counter64
	MAX-ACCESS read-only
	STATUS current
	DESCRIPTION "Directly sent bytes"

	::={shapingDirectBytes 1}

shapingDirectBytesMom	OBJECT-TYPE
	SYNTAX	 CounterBasedGauge64
	MAX-ACCESS read-only
	STATUS current
	DESCRIPTION "Directly sent bytes"

	::={shapingDirectBytes 2}

shapingDirectBytesMax	OBJECT-TYPE
	SYNTAX	 CounterBasedGauge64
	MAX-ACCESS read-only
	STATUS current
	DESCRIPTION "Directly sent bytes"

	::={shapingDirectBytes 3}

shapingDirectBytesLevelTable OBJECT-TYPE
	SYNTAX      SEQUENCE OF ShapingDirectBytesLevelEntry
	MAX-ACCESS  not-accessible
	STATUS      current
	DESCRIPTION
	"Table for shapingDirectBytes"
	::={shapingDirectBytes 4}

shapingDirectBytesLevelEntry OBJECT-TYPE
	SYNTAX      ShapingDirectBytesLevelEntry
	MAX-ACCESS  not-accessible
	STATUS      current
	DESCRIPTION
	"Table entry for shapingDirectBytes"
	INDEX { shapingDirectBytesLevelName }
	::={shapingDirectBytesLevelTable 1}

ShapingDirectBytesLevelEntry ::=
	SEQUENCE {
		shapingDirectBytesLevelName	DisplayString,
		shapingDirectBytesLevelVal	Counter64,
		shapingDirectBytesLevelMom	CounterBasedGauge64,
		shapingDirectBytesLevelMax	CounterBasedGauge64
	}

shapingDirectBytesLevelName OBJECT-TYPE
	SYNTAX      DisplayString
	MAX-ACCESS  not-accessible
	STATUS      current
	DESCRIPTION
	"Table entry display string for shapingDirectBytes"
	::={shapingDirectBytesLevelEntry 1}

shapingDirectBytesLevelVal OBJECT-TYPE
	SYNTAX	 Counter64
	MAX-ACCESS  read-only
	STATUS      current
	DESCRIPTION
	"Table entry attribute for shapingDirectBytes"
	::={shapingDirectBytesLevelEntry 2}

shapingDirectBytesLevelMom OBJECT-TYPE
	SYNTAX	 CounterBasedGauge64
	MAX-ACCESS  read-only
	STATUS      current
	DESCRIPTION
	"Table entry attribute for shapingDirectBytes"
	::={shapingDirectBytesLevelEntry 3}

shapingDirectBytesLevelMax OBJECT-TYPE
	SYNTAX	 CounterBasedGauge64
	MAX-ACCESS  read-only
	STATUS      current
	DESCRIPTION
	"Table entry attribute for shapingDirectBytes"
	::={shapingDirectBytesLevelEntry 4}


shapingBorrowDequeues	OBJECT IDENTIFIER ::={shaping 46}

shapingBorrowDequeuesVal	OBJECT-TYPE
	SYNTAX	 Counter64
	MAX-ACCESS read-only
	STATUS obsolete
	DESCRIPTION "Borrowing dequeues"

	::={shapingBorrowDequeues 1}

shapingBorrowDequeuesMom	OBJECT-TYPE
	SYNTAX	 CounterBasedGauge64
	MAX-ACCESS read-only
	STATUS obsolete
	DESCRIPTION "Borrowing dequeues"

	::={shapingBorrowDequeues 2}

shapingBorrowDequeuesMax	OBJECT-TYPE
	SYNTAX	 CounterBasedGauge64
	MAX-ACCESS read-only
	STATUS obsolete
	DESCRIPTION "Borrowing dequeues"

	::={shapingBorrowDequeues 3}

shapingBorrowDequeuesLevelTable OBJECT-TYPE
	SYNTAX      SEQUENCE OF ShapingBorrowDequeuesLevelEntry
	MAX-ACCESS  not-accessible
	STATUS      current
	DESCRIPTION
	"Table for shapingBorrowDequeues"
	::={shapingBorrowDequeues 4}

shapingBorrowDequeuesLevelEntry OBJECT-TYPE
	SYNTAX      ShapingBorrowDequeuesLevelEntry
	MAX-ACCESS  not-accessible
	STATUS      current
	DESCRIPTION
	"Table entry for shapingBorrowDequeues"
	INDEX { shapingBorrowDequeuesLevelName }
	::={shapingBorrowDequeuesLevelTable 1}

ShapingBorrowDequeuesLevelEntry ::=
	SEQUENCE {
		shapingBorrowDequeuesLevelName	DisplayString,
		shapingBorrowDequeuesLevelVal	Counter64,
		shapingBorrowDequeuesLevelMom	CounterBasedGauge64,
		shapingBorrowDequeuesLevelMax	CounterBasedGauge64
	}

shapingBorrowDequeuesLevelName OBJECT-TYPE
	SYNTAX      DisplayString
	MAX-ACCESS  not-accessible
	STATUS      current
	DESCRIPTION
	"Table entry display string for shapingBorrowDequeues"
	::={shapingBorrowDequeuesLevelEntry 1}

shapingBorrowDequeuesLevelVal OBJECT-TYPE
	SYNTAX	 Counter64
	MAX-ACCESS  read-only
	STATUS      current
	DESCRIPTION
	"Table entry attribute for shapingBorrowDequeues"
	::={shapingBorrowDequeuesLevelEntry 2}

shapingBorrowDequeuesLevelMom OBJECT-TYPE
	SYNTAX	 CounterBasedGauge64
	MAX-ACCESS  read-only
	STATUS      current
	DESCRIPTION
	"Table entry attribute for shapingBorrowDequeues"
	::={shapingBorrowDequeuesLevelEntry 3}

shapingBorrowDequeuesLevelMax OBJECT-TYPE
	SYNTAX	 CounterBasedGauge64
	MAX-ACCESS  read-only
	STATUS      current
	DESCRIPTION
	"Table entry attribute for shapingBorrowDequeues"
	::={shapingBorrowDequeuesLevelEntry 4}


shapingVbsSplitError	OBJECT IDENTIFIER ::={shaping 47}

shapingVbsSplitErrorVal	OBJECT-TYPE
	SYNTAX	 Counter64
	MAX-ACCESS read-only
	STATUS obsolete
	DESCRIPTION "VBS split allocation failures"

	::={shapingVbsSplitError 1}

shapingVbsSplitErrorMom	OBJECT-TYPE
	SYNTAX	 CounterBasedGauge64
	MAX-ACCESS read-only
	STATUS obsolete
	DESCRIPTION "VBS split allocation failures"

	::={shapingVbsSplitError 2}

shapingVbsSplitErrorMax	OBJECT-TYPE
	SYNTAX	 CounterBasedGauge64
	MAX-ACCESS read-only
	STATUS obsolete
	DESCRIPTION "VBS split allocation failures"

	::={shapingVbsSplitError 3}

shapingVbsSplitErrorLevelTable OBJECT-TYPE
	SYNTAX      SEQUENCE OF ShapingVbsSplitErrorLevelEntry
	MAX-ACCESS  not-accessible
	STATUS      current
	DESCRIPTION
	"Table for shapingVbsSplitError"
	::={shapingVbsSplitError 4}

shapingVbsSplitErrorLevelEntry OBJECT-TYPE
	SYNTAX      ShapingVbsSplitErrorLevelEntry
	MAX-ACCESS  not-accessible
	STATUS      current
	DESCRIPTION
	"Table entry for shapingVbsSplitError"
	INDEX { shapingVbsSplitErrorLevelName }
	::={shapingVbsSplitErrorLevelTable 1}

ShapingVbsSplitErrorLevelEntry ::=
	SEQUENCE {
		shapingVbsSplitErrorLevelName	DisplayString,
		shapingVbsSplitErrorLevelVal	Counter64,
		shapingVbsSplitErrorLevelMom	CounterBasedGauge64,
		shapingVbsSplitErrorLevelMax	CounterBasedGauge64
	}

shapingVbsSplitErrorLevelName OBJECT-TYPE
	SYNTAX      DisplayString
	MAX-ACCESS  not-accessible
	STATUS      current
	DESCRIPTION
	"Table entry display string for shapingVbsSplitError"
	::={shapingVbsSplitErrorLevelEntry 1}

shapingVbsSplitErrorLevelVal OBJECT-TYPE
	SYNTAX	 Counter64
	MAX-ACCESS  read-only
	STATUS      current
	DESCRIPTION
	"Table entry attribute for shapingVbsSplitError"
	::={shapingVbsSplitErrorLevelEntry 2}

shapingVbsSplitErrorLevelMom OBJECT-TYPE
	SYNTAX	 CounterBasedGauge64
	MAX-ACCESS  read-only
	STATUS      current
	DESCRIPTION
	"Table entry attribute for shapingVbsSplitError"
	::={shapingVbsSplitErrorLevelEntry 3}

shapingVbsSplitErrorLevelMax OBJECT-TYPE
	SYNTAX	 CounterBasedGauge64
	MAX-ACCESS  read-only
	STATUS      current
	DESCRIPTION
	"Table entry attribute for shapingVbsSplitError"
	::={shapingVbsSplitErrorLevelEntry 4}


shapingBrownHostDrops	OBJECT IDENTIFIER ::={shaping 48}

shapingBrownHostDropsVal	OBJECT-TYPE
	SYNTAX	 Counter64
	MAX-ACCESS read-only
	STATUS current
	DESCRIPTION "BROWN per host drops"

	::={shapingBrownHostDrops 1}

shapingBrownHostDropsMom	OBJECT-TYPE
	SYNTAX	 CounterBasedGauge64
	MAX-ACCESS read-only
	STATUS current
	DESCRIPTION "BROWN per host drops"

	::={shapingBrownHostDrops 2}

shapingBrownHostDropsMax	OBJECT-TYPE
	SYNTAX	 CounterBasedGauge64
	MAX-ACCESS read-only
	STATUS current
	DESCRIPTION "BROWN per host drops"

	::={shapingBrownHostDrops 3}

shapingBrownHostDropsLevelTable OBJECT-TYPE
	SYNTAX      SEQUENCE OF ShapingBrownHostDropsLevelEntry
	MAX-ACCESS  not-accessible
	STATUS      current
	DESCRIPTION
	"Table for shapingBrownHostDrops"
	::={shapingBrownHostDrops 4}

shapingBrownHostDropsLevelEntry OBJECT-TYPE
	SYNTAX      ShapingBrownHostDropsLevelEntry
	MAX-ACCESS  not-accessible
	STATUS      current
	DESCRIPTION
	"Table entry for shapingBrownHostDrops"
	INDEX { shapingBrownHostDropsLevelName }
	::={shapingBrownHostDropsLevelTable 1}

ShapingBrownHostDropsLevelEntry ::=
	SEQUENCE {
		shapingBrownHostDropsLevelName	DisplayString,
		shapingBrownHostDropsLevelVal	Counter64,
		shapingBrownHostDropsLevelMom	CounterBasedGauge64,
		shapingBrownHostDropsLevelMax	CounterBasedGauge64
	}

shapingBrownHostDropsLevelName OBJECT-TYPE
	SYNTAX      DisplayString
	MAX-ACCESS  not-accessible
	STATUS      current
	DESCRIPTION
	"Table entry display string for shapingBrownHostDrops"
	::={shapingBrownHostDropsLevelEntry 1}

shapingBrownHostDropsLevelVal OBJECT-TYPE
	SYNTAX	 Counter64
	MAX-ACCESS  read-only
	STATUS      current
	DESCRIPTION
	"Table entry attribute for shapingBrownHostDrops"
	::={shapingBrownHostDropsLevelEntry 2}

shapingBrownHostDropsLevelMom OBJECT-TYPE
	SYNTAX	 CounterBasedGauge64
	MAX-ACCESS  read-only
	STATUS      current
	DESCRIPTION
	"Table entry attribute for shapingBrownHostDrops"
	::={shapingBrownHostDropsLevelEntry 3}

shapingBrownHostDropsLevelMax OBJECT-TYPE
	SYNTAX	 CounterBasedGauge64
	MAX-ACCESS  read-only
	STATUS      current
	DESCRIPTION
	"Table entry attribute for shapingBrownHostDrops"
	::={shapingBrownHostDropsLevelEntry 4}


shapingMaxConnDrops	OBJECT IDENTIFIER ::={shaping 49}

shapingMaxConnDropsVal	OBJECT-TYPE
	SYNTAX	 Counter64
	MAX-ACCESS read-only
	STATUS current
	DESCRIPTION "Object max connections reached"

	::={shapingMaxConnDrops 1}

shapingMaxConnDropsMom	OBJECT-TYPE
	SYNTAX	 CounterBasedGauge64
	MAX-ACCESS read-only
	STATUS current
	DESCRIPTION "Object max connections reached"

	::={shapingMaxConnDrops 2}

shapingMaxConnDropsMax	OBJECT-TYPE
	SYNTAX	 CounterBasedGauge64
	MAX-ACCESS read-only
	STATUS current
	DESCRIPTION "Object max connections reached"

	::={shapingMaxConnDrops 3}

shapingMaxConnDropsLevelTable OBJECT-TYPE
	SYNTAX      SEQUENCE OF ShapingMaxConnDropsLevelEntry
	MAX-ACCESS  not-accessible
	STATUS      current
	DESCRIPTION
	"Table for shapingMaxConnDrops"
	::={shapingMaxConnDrops 4}

shapingMaxConnDropsLevelEntry OBJECT-TYPE
	SYNTAX      ShapingMaxConnDropsLevelEntry
	MAX-ACCESS  not-accessible
	STATUS      current
	DESCRIPTION
	"Table entry for shapingMaxConnDrops"
	INDEX { shapingMaxConnDropsLevelName }
	::={shapingMaxConnDropsLevelTable 1}

ShapingMaxConnDropsLevelEntry ::=
	SEQUENCE {
		shapingMaxConnDropsLevelName	DisplayString,
		shapingMaxConnDropsLevelVal	Counter64,
		shapingMaxConnDropsLevelMom	CounterBasedGauge64,
		shapingMaxConnDropsLevelMax	CounterBasedGauge64
	}

shapingMaxConnDropsLevelName OBJECT-TYPE
	SYNTAX      DisplayString
	MAX-ACCESS  not-accessible
	STATUS      current
	DESCRIPTION
	"Table entry display string for shapingMaxConnDrops"
	::={shapingMaxConnDropsLevelEntry 1}

shapingMaxConnDropsLevelVal OBJECT-TYPE
	SYNTAX	 Counter64
	MAX-ACCESS  read-only
	STATUS      current
	DESCRIPTION
	"Table entry attribute for shapingMaxConnDrops"
	::={shapingMaxConnDropsLevelEntry 2}

shapingMaxConnDropsLevelMom OBJECT-TYPE
	SYNTAX	 CounterBasedGauge64
	MAX-ACCESS  read-only
	STATUS      current
	DESCRIPTION
	"Table entry attribute for shapingMaxConnDrops"
	::={shapingMaxConnDropsLevelEntry 3}

shapingMaxConnDropsLevelMax OBJECT-TYPE
	SYNTAX	 CounterBasedGauge64
	MAX-ACCESS  read-only
	STATUS      current
	DESCRIPTION
	"Table entry attribute for shapingMaxConnDrops"
	::={shapingMaxConnDropsLevelEntry 4}


shapingScheduledOdirs	OBJECT IDENTIFIER ::={shaping 50}

shapingScheduledOdirsVal	OBJECT-TYPE
	SYNTAX	 CounterBasedGauge64
	MAX-ACCESS read-only
	STATUS obsolete
	DESCRIPTION "Scheduled odirs"

	::={shapingScheduledOdirs 1}

shapingScheduledOdirsMax	OBJECT-TYPE
	SYNTAX	 CounterBasedGauge64
	MAX-ACCESS read-only
	STATUS obsolete
	DESCRIPTION "Scheduled odirs"

	::={shapingScheduledOdirs 3}

shapingScheduledOdirsLevelTable OBJECT-TYPE
	SYNTAX      SEQUENCE OF ShapingScheduledOdirsLevelEntry
	MAX-ACCESS  not-accessible
	STATUS      current
	DESCRIPTION
	"Table for shapingScheduledOdirs"
	::={shapingScheduledOdirs 4}

shapingScheduledOdirsLevelEntry OBJECT-TYPE
	SYNTAX      ShapingScheduledOdirsLevelEntry
	MAX-ACCESS  not-accessible
	STATUS      current
	DESCRIPTION
	"Table entry for shapingScheduledOdirs"
	INDEX { shapingScheduledOdirsLevelName }
	::={shapingScheduledOdirsLevelTable 1}

ShapingScheduledOdirsLevelEntry ::=
	SEQUENCE {
		shapingScheduledOdirsLevelName	DisplayString,
		shapingScheduledOdirsLevelVal	CounterBasedGauge64,
		shapingScheduledOdirsLevelMax	CounterBasedGauge64
	}

shapingScheduledOdirsLevelName OBJECT-TYPE
	SYNTAX      DisplayString
	MAX-ACCESS  not-accessible
	STATUS      current
	DESCRIPTION
	"Table entry display string for shapingScheduledOdirs"
	::={shapingScheduledOdirsLevelEntry 1}

shapingScheduledOdirsLevelVal OBJECT-TYPE
	SYNTAX	 CounterBasedGauge64
	MAX-ACCESS  read-only
	STATUS      current
	DESCRIPTION
	"Table entry attribute for shapingScheduledOdirs"
	::={shapingScheduledOdirsLevelEntry 2}

shapingScheduledOdirsLevelMax OBJECT-TYPE
	SYNTAX	 CounterBasedGauge64
	MAX-ACCESS  read-only
	STATUS      current
	DESCRIPTION
	"Table entry attribute for shapingScheduledOdirs"
	::={shapingScheduledOdirsLevelEntry 4}


shapingQueuePoolExhausted	OBJECT IDENTIFIER ::={shaping 51}

shapingQueuePoolExhaustedVal	OBJECT-TYPE
	SYNTAX	 Counter64
	MAX-ACCESS read-only
	STATUS obsolete
	DESCRIPTION "Queue pool exhausted"

	::={shapingQueuePoolExhausted 1}

shapingQueuePoolExhaustedMom	OBJECT-TYPE
	SYNTAX	 CounterBasedGauge64
	MAX-ACCESS read-only
	STATUS obsolete
	DESCRIPTION "Queue pool exhausted"

	::={shapingQueuePoolExhausted 2}

shapingQueuePoolExhaustedMax	OBJECT-TYPE
	SYNTAX	 CounterBasedGauge64
	MAX-ACCESS read-only
	STATUS obsolete
	DESCRIPTION "Queue pool exhausted"

	::={shapingQueuePoolExhausted 3}

shapingQueuePoolExhaustedLevelTable OBJECT-TYPE
	SYNTAX      SEQUENCE OF ShapingQueuePoolExhaustedLevelEntry
	MAX-ACCESS  not-accessible
	STATUS      current
	DESCRIPTION
	"Table for shapingQueuePoolExhausted"
	::={shapingQueuePoolExhausted 4}

shapingQueuePoolExhaustedLevelEntry OBJECT-TYPE
	SYNTAX      ShapingQueuePoolExhaustedLevelEntry
	MAX-ACCESS  not-accessible
	STATUS      current
	DESCRIPTION
	"Table entry for shapingQueuePoolExhausted"
	INDEX { shapingQueuePoolExhaustedLevelName }
	::={shapingQueuePoolExhaustedLevelTable 1}

ShapingQueuePoolExhaustedLevelEntry ::=
	SEQUENCE {
		shapingQueuePoolExhaustedLevelName	DisplayString,
		shapingQueuePoolExhaustedLevelVal	Counter64,
		shapingQueuePoolExhaustedLevelMom	CounterBasedGauge64,
		shapingQueuePoolExhaustedLevelMax	CounterBasedGauge64
	}

shapingQueuePoolExhaustedLevelName OBJECT-TYPE
	SYNTAX      DisplayString
	MAX-ACCESS  not-accessible
	STATUS      current
	DESCRIPTION
	"Table entry display string for shapingQueuePoolExhausted"
	::={shapingQueuePoolExhaustedLevelEntry 1}

shapingQueuePoolExhaustedLevelVal OBJECT-TYPE
	SYNTAX	 Counter64
	MAX-ACCESS  read-only
	STATUS      current
	DESCRIPTION
	"Table entry attribute for shapingQueuePoolExhausted"
	::={shapingQueuePoolExhaustedLevelEntry 2}

shapingQueuePoolExhaustedLevelMom OBJECT-TYPE
	SYNTAX	 CounterBasedGauge64
	MAX-ACCESS  read-only
	STATUS      current
	DESCRIPTION
	"Table entry attribute for shapingQueuePoolExhausted"
	::={shapingQueuePoolExhaustedLevelEntry 3}

shapingQueuePoolExhaustedLevelMax OBJECT-TYPE
	SYNTAX	 CounterBasedGauge64
	MAX-ACCESS  read-only
	STATUS      current
	DESCRIPTION
	"Table entry attribute for shapingQueuePoolExhausted"
	::={shapingQueuePoolExhaustedLevelEntry 4}


shapingActiveQueues	OBJECT IDENTIFIER ::={shaping 52}

shapingActiveQueuesVal	OBJECT-TYPE
	SYNTAX	 CounterBasedGauge64
	MAX-ACCESS read-only
	STATUS obsolete
	DESCRIPTION "Active queues"

	::={shapingActiveQueues 1}

shapingActiveQueuesMax	OBJECT-TYPE
	SYNTAX	 CounterBasedGauge64
	MAX-ACCESS read-only
	STATUS obsolete
	DESCRIPTION "Active queues"

	::={shapingActiveQueues 3}

shapingActiveQueuesLevelTable OBJECT-TYPE
	SYNTAX      SEQUENCE OF ShapingActiveQueuesLevelEntry
	MAX-ACCESS  not-accessible
	STATUS      current
	DESCRIPTION
	"Table for shapingActiveQueues"
	::={shapingActiveQueues 4}

shapingActiveQueuesLevelEntry OBJECT-TYPE
	SYNTAX      ShapingActiveQueuesLevelEntry
	MAX-ACCESS  not-accessible
	STATUS      current
	DESCRIPTION
	"Table entry for shapingActiveQueues"
	INDEX { shapingActiveQueuesLevelName }
	::={shapingActiveQueuesLevelTable 1}

ShapingActiveQueuesLevelEntry ::=
	SEQUENCE {
		shapingActiveQueuesLevelName	DisplayString,
		shapingActiveQueuesLevelVal	CounterBasedGauge64,
		shapingActiveQueuesLevelMax	CounterBasedGauge64
	}

shapingActiveQueuesLevelName OBJECT-TYPE
	SYNTAX      DisplayString
	MAX-ACCESS  not-accessible
	STATUS      current
	DESCRIPTION
	"Table entry display string for shapingActiveQueues"
	::={shapingActiveQueuesLevelEntry 1}

shapingActiveQueuesLevelVal OBJECT-TYPE
	SYNTAX	 CounterBasedGauge64
	MAX-ACCESS  read-only
	STATUS      current
	DESCRIPTION
	"Table entry attribute for shapingActiveQueues"
	::={shapingActiveQueuesLevelEntry 2}

shapingActiveQueuesLevelMax OBJECT-TYPE
	SYNTAX	 CounterBasedGauge64
	MAX-ACCESS  read-only
	STATUS      current
	DESCRIPTION
	"Table entry attribute for shapingActiveQueues"
	::={shapingActiveQueuesLevelEntry 4}


shapingQueueAllocations	OBJECT IDENTIFIER ::={shaping 53}

shapingQueueAllocationsVal	OBJECT-TYPE
	SYNTAX	 Counter64
	MAX-ACCESS read-only
	STATUS obsolete
	DESCRIPTION "Queue allocations"

	::={shapingQueueAllocations 1}

shapingQueueAllocationsMom	OBJECT-TYPE
	SYNTAX	 CounterBasedGauge64
	MAX-ACCESS read-only
	STATUS obsolete
	DESCRIPTION "Queue allocations"

	::={shapingQueueAllocations 2}

shapingQueueAllocationsMax	OBJECT-TYPE
	SYNTAX	 CounterBasedGauge64
	MAX-ACCESS read-only
	STATUS obsolete
	DESCRIPTION "Queue allocations"

	::={shapingQueueAllocations 3}

shapingQueueAllocationsLevelTable OBJECT-TYPE
	SYNTAX      SEQUENCE OF ShapingQueueAllocationsLevelEntry
	MAX-ACCESS  not-accessible
	STATUS      current
	DESCRIPTION
	"Table for shapingQueueAllocations"
	::={shapingQueueAllocations 4}

shapingQueueAllocationsLevelEntry OBJECT-TYPE
	SYNTAX      ShapingQueueAllocationsLevelEntry
	MAX-ACCESS  not-accessible
	STATUS      current
	DESCRIPTION
	"Table entry for shapingQueueAllocations"
	INDEX { shapingQueueAllocationsLevelName }
	::={shapingQueueAllocationsLevelTable 1}

ShapingQueueAllocationsLevelEntry ::=
	SEQUENCE {
		shapingQueueAllocationsLevelName	DisplayString,
		shapingQueueAllocationsLevelVal	Counter64,
		shapingQueueAllocationsLevelMom	CounterBasedGauge64,
		shapingQueueAllocationsLevelMax	CounterBasedGauge64
	}

shapingQueueAllocationsLevelName OBJECT-TYPE
	SYNTAX      DisplayString
	MAX-ACCESS  not-accessible
	STATUS      current
	DESCRIPTION
	"Table entry display string for shapingQueueAllocations"
	::={shapingQueueAllocationsLevelEntry 1}

shapingQueueAllocationsLevelVal OBJECT-TYPE
	SYNTAX	 Counter64
	MAX-ACCESS  read-only
	STATUS      current
	DESCRIPTION
	"Table entry attribute for shapingQueueAllocations"
	::={shapingQueueAllocationsLevelEntry 2}

shapingQueueAllocationsLevelMom OBJECT-TYPE
	SYNTAX	 CounterBasedGauge64
	MAX-ACCESS  read-only
	STATUS      current
	DESCRIPTION
	"Table entry attribute for shapingQueueAllocations"
	::={shapingQueueAllocationsLevelEntry 3}

shapingQueueAllocationsLevelMax OBJECT-TYPE
	SYNTAX	 CounterBasedGauge64
	MAX-ACCESS  read-only
	STATUS      current
	DESCRIPTION
	"Table entry attribute for shapingQueueAllocations"
	::={shapingQueueAllocationsLevelEntry 4}


shapingDropsPrio1	OBJECT IDENTIFIER ::={shaping 54}

shapingDropsPrio1Val	OBJECT-TYPE
	SYNTAX	 Counter64
	MAX-ACCESS read-only
	STATUS current
	DESCRIPTION "Queuing drops (prio 1)"

	::={shapingDropsPrio1 1}

shapingDropsPrio1Mom	OBJECT-TYPE
	SYNTAX	 CounterBasedGauge64
	MAX-ACCESS read-only
	STATUS current
	DESCRIPTION "Queuing drops (prio 1)"

	::={shapingDropsPrio1 2}

shapingDropsPrio1Max	OBJECT-TYPE
	SYNTAX	 CounterBasedGauge64
	MAX-ACCESS read-only
	STATUS current
	DESCRIPTION "Queuing drops (prio 1)"

	::={shapingDropsPrio1 3}

shapingDropsPrio1LevelTable OBJECT-TYPE
	SYNTAX      SEQUENCE OF ShapingDropsPrio1LevelEntry
	MAX-ACCESS  not-accessible
	STATUS      current
	DESCRIPTION
	"Table for shapingDropsPrio1"
	::={shapingDropsPrio1 4}

shapingDropsPrio1LevelEntry OBJECT-TYPE
	SYNTAX      ShapingDropsPrio1LevelEntry
	MAX-ACCESS  not-accessible
	STATUS      current
	DESCRIPTION
	"Table entry for shapingDropsPrio1"
	INDEX { shapingDropsPrio1LevelName }
	::={shapingDropsPrio1LevelTable 1}

ShapingDropsPrio1LevelEntry ::=
	SEQUENCE {
		shapingDropsPrio1LevelName	DisplayString,
		shapingDropsPrio1LevelVal	Counter64,
		shapingDropsPrio1LevelMom	CounterBasedGauge64,
		shapingDropsPrio1LevelMax	CounterBasedGauge64
	}

shapingDropsPrio1LevelName OBJECT-TYPE
	SYNTAX      DisplayString
	MAX-ACCESS  not-accessible
	STATUS      current
	DESCRIPTION
	"Table entry display string for shapingDropsPrio1"
	::={shapingDropsPrio1LevelEntry 1}

shapingDropsPrio1LevelVal OBJECT-TYPE
	SYNTAX	 Counter64
	MAX-ACCESS  read-only
	STATUS      current
	DESCRIPTION
	"Table entry attribute for shapingDropsPrio1"
	::={shapingDropsPrio1LevelEntry 2}

shapingDropsPrio1LevelMom OBJECT-TYPE
	SYNTAX	 CounterBasedGauge64
	MAX-ACCESS  read-only
	STATUS      current
	DESCRIPTION
	"Table entry attribute for shapingDropsPrio1"
	::={shapingDropsPrio1LevelEntry 3}

shapingDropsPrio1LevelMax OBJECT-TYPE
	SYNTAX	 CounterBasedGauge64
	MAX-ACCESS  read-only
	STATUS      current
	DESCRIPTION
	"Table entry attribute for shapingDropsPrio1"
	::={shapingDropsPrio1LevelEntry 4}


shapingDropsPrio2	OBJECT IDENTIFIER ::={shaping 55}

shapingDropsPrio2Val	OBJECT-TYPE
	SYNTAX	 Counter64
	MAX-ACCESS read-only
	STATUS current
	DESCRIPTION "Queuing drops (prio 2)"

	::={shapingDropsPrio2 1}

shapingDropsPrio2Mom	OBJECT-TYPE
	SYNTAX	 CounterBasedGauge64
	MAX-ACCESS read-only
	STATUS current
	DESCRIPTION "Queuing drops (prio 2)"

	::={shapingDropsPrio2 2}

shapingDropsPrio2Max	OBJECT-TYPE
	SYNTAX	 CounterBasedGauge64
	MAX-ACCESS read-only
	STATUS current
	DESCRIPTION "Queuing drops (prio 2)"

	::={shapingDropsPrio2 3}

shapingDropsPrio2LevelTable OBJECT-TYPE
	SYNTAX      SEQUENCE OF ShapingDropsPrio2LevelEntry
	MAX-ACCESS  not-accessible
	STATUS      current
	DESCRIPTION
	"Table for shapingDropsPrio2"
	::={shapingDropsPrio2 4}

shapingDropsPrio2LevelEntry OBJECT-TYPE
	SYNTAX      ShapingDropsPrio2LevelEntry
	MAX-ACCESS  not-accessible
	STATUS      current
	DESCRIPTION
	"Table entry for shapingDropsPrio2"
	INDEX { shapingDropsPrio2LevelName }
	::={shapingDropsPrio2LevelTable 1}

ShapingDropsPrio2LevelEntry ::=
	SEQUENCE {
		shapingDropsPrio2LevelName	DisplayString,
		shapingDropsPrio2LevelVal	Counter64,
		shapingDropsPrio2LevelMom	CounterBasedGauge64,
		shapingDropsPrio2LevelMax	CounterBasedGauge64
	}

shapingDropsPrio2LevelName OBJECT-TYPE
	SYNTAX      DisplayString
	MAX-ACCESS  not-accessible
	STATUS      current
	DESCRIPTION
	"Table entry display string for shapingDropsPrio2"
	::={shapingDropsPrio2LevelEntry 1}

shapingDropsPrio2LevelVal OBJECT-TYPE
	SYNTAX	 Counter64
	MAX-ACCESS  read-only
	STATUS      current
	DESCRIPTION
	"Table entry attribute for shapingDropsPrio2"
	::={shapingDropsPrio2LevelEntry 2}

shapingDropsPrio2LevelMom OBJECT-TYPE
	SYNTAX	 CounterBasedGauge64
	MAX-ACCESS  read-only
	STATUS      current
	DESCRIPTION
	"Table entry attribute for shapingDropsPrio2"
	::={shapingDropsPrio2LevelEntry 3}

shapingDropsPrio2LevelMax OBJECT-TYPE
	SYNTAX	 CounterBasedGauge64
	MAX-ACCESS  read-only
	STATUS      current
	DESCRIPTION
	"Table entry attribute for shapingDropsPrio2"
	::={shapingDropsPrio2LevelEntry 4}


shapingDropsPrio3	OBJECT IDENTIFIER ::={shaping 56}

shapingDropsPrio3Val	OBJECT-TYPE
	SYNTAX	 Counter64
	MAX-ACCESS read-only
	STATUS current
	DESCRIPTION "Queuing drops (prio 3)"

	::={shapingDropsPrio3 1}

shapingDropsPrio3Mom	OBJECT-TYPE
	SYNTAX	 CounterBasedGauge64
	MAX-ACCESS read-only
	STATUS current
	DESCRIPTION "Queuing drops (prio 3)"

	::={shapingDropsPrio3 2}

shapingDropsPrio3Max	OBJECT-TYPE
	SYNTAX	 CounterBasedGauge64
	MAX-ACCESS read-only
	STATUS current
	DESCRIPTION "Queuing drops (prio 3)"

	::={shapingDropsPrio3 3}

shapingDropsPrio3LevelTable OBJECT-TYPE
	SYNTAX      SEQUENCE OF ShapingDropsPrio3LevelEntry
	MAX-ACCESS  not-accessible
	STATUS      current
	DESCRIPTION
	"Table for shapingDropsPrio3"
	::={shapingDropsPrio3 4}

shapingDropsPrio3LevelEntry OBJECT-TYPE
	SYNTAX      ShapingDropsPrio3LevelEntry
	MAX-ACCESS  not-accessible
	STATUS      current
	DESCRIPTION
	"Table entry for shapingDropsPrio3"
	INDEX { shapingDropsPrio3LevelName }
	::={shapingDropsPrio3LevelTable 1}

ShapingDropsPrio3LevelEntry ::=
	SEQUENCE {
		shapingDropsPrio3LevelName	DisplayString,
		shapingDropsPrio3LevelVal	Counter64,
		shapingDropsPrio3LevelMom	CounterBasedGauge64,
		shapingDropsPrio3LevelMax	CounterBasedGauge64
	}

shapingDropsPrio3LevelName OBJECT-TYPE
	SYNTAX      DisplayString
	MAX-ACCESS  not-accessible
	STATUS      current
	DESCRIPTION
	"Table entry display string for shapingDropsPrio3"
	::={shapingDropsPrio3LevelEntry 1}

shapingDropsPrio3LevelVal OBJECT-TYPE
	SYNTAX	 Counter64
	MAX-ACCESS  read-only
	STATUS      current
	DESCRIPTION
	"Table entry attribute for shapingDropsPrio3"
	::={shapingDropsPrio3LevelEntry 2}

shapingDropsPrio3LevelMom OBJECT-TYPE
	SYNTAX	 CounterBasedGauge64
	MAX-ACCESS  read-only
	STATUS      current
	DESCRIPTION
	"Table entry attribute for shapingDropsPrio3"
	::={shapingDropsPrio3LevelEntry 3}

shapingDropsPrio3LevelMax OBJECT-TYPE
	SYNTAX	 CounterBasedGauge64
	MAX-ACCESS  read-only
	STATUS      current
	DESCRIPTION
	"Table entry attribute for shapingDropsPrio3"
	::={shapingDropsPrio3LevelEntry 4}


shapingDropsPrio4	OBJECT IDENTIFIER ::={shaping 57}

shapingDropsPrio4Val	OBJECT-TYPE
	SYNTAX	 Counter64
	MAX-ACCESS read-only
	STATUS current
	DESCRIPTION "Queuing drops (prio 4)"

	::={shapingDropsPrio4 1}

shapingDropsPrio4Mom	OBJECT-TYPE
	SYNTAX	 CounterBasedGauge64
	MAX-ACCESS read-only
	STATUS current
	DESCRIPTION "Queuing drops (prio 4)"

	::={shapingDropsPrio4 2}

shapingDropsPrio4Max	OBJECT-TYPE
	SYNTAX	 CounterBasedGauge64
	MAX-ACCESS read-only
	STATUS current
	DESCRIPTION "Queuing drops (prio 4)"

	::={shapingDropsPrio4 3}

shapingDropsPrio4LevelTable OBJECT-TYPE
	SYNTAX      SEQUENCE OF ShapingDropsPrio4LevelEntry
	MAX-ACCESS  not-accessible
	STATUS      current
	DESCRIPTION
	"Table for shapingDropsPrio4"
	::={shapingDropsPrio4 4}

shapingDropsPrio4LevelEntry OBJECT-TYPE
	SYNTAX      ShapingDropsPrio4LevelEntry
	MAX-ACCESS  not-accessible
	STATUS      current
	DESCRIPTION
	"Table entry for shapingDropsPrio4"
	INDEX { shapingDropsPrio4LevelName }
	::={shapingDropsPrio4LevelTable 1}

ShapingDropsPrio4LevelEntry ::=
	SEQUENCE {
		shapingDropsPrio4LevelName	DisplayString,
		shapingDropsPrio4LevelVal	Counter64,
		shapingDropsPrio4LevelMom	CounterBasedGauge64,
		shapingDropsPrio4LevelMax	CounterBasedGauge64
	}

shapingDropsPrio4LevelName OBJECT-TYPE
	SYNTAX      DisplayString
	MAX-ACCESS  not-accessible
	STATUS      current
	DESCRIPTION
	"Table entry display string for shapingDropsPrio4"
	::={shapingDropsPrio4LevelEntry 1}

shapingDropsPrio4LevelVal OBJECT-TYPE
	SYNTAX	 Counter64
	MAX-ACCESS  read-only
	STATUS      current
	DESCRIPTION
	"Table entry attribute for shapingDropsPrio4"
	::={shapingDropsPrio4LevelEntry 2}

shapingDropsPrio4LevelMom OBJECT-TYPE
	SYNTAX	 CounterBasedGauge64
	MAX-ACCESS  read-only
	STATUS      current
	DESCRIPTION
	"Table entry attribute for shapingDropsPrio4"
	::={shapingDropsPrio4LevelEntry 3}

shapingDropsPrio4LevelMax OBJECT-TYPE
	SYNTAX	 CounterBasedGauge64
	MAX-ACCESS  read-only
	STATUS      current
	DESCRIPTION
	"Table entry attribute for shapingDropsPrio4"
	::={shapingDropsPrio4LevelEntry 4}


shapingDropsPrio5	OBJECT IDENTIFIER ::={shaping 58}

shapingDropsPrio5Val	OBJECT-TYPE
	SYNTAX	 Counter64
	MAX-ACCESS read-only
	STATUS current
	DESCRIPTION "Queuing drops (prio 5)"

	::={shapingDropsPrio5 1}

shapingDropsPrio5Mom	OBJECT-TYPE
	SYNTAX	 CounterBasedGauge64
	MAX-ACCESS read-only
	STATUS current
	DESCRIPTION "Queuing drops (prio 5)"

	::={shapingDropsPrio5 2}

shapingDropsPrio5Max	OBJECT-TYPE
	SYNTAX	 CounterBasedGauge64
	MAX-ACCESS read-only
	STATUS current
	DESCRIPTION "Queuing drops (prio 5)"

	::={shapingDropsPrio5 3}

shapingDropsPrio5LevelTable OBJECT-TYPE
	SYNTAX      SEQUENCE OF ShapingDropsPrio5LevelEntry
	MAX-ACCESS  not-accessible
	STATUS      current
	DESCRIPTION
	"Table for shapingDropsPrio5"
	::={shapingDropsPrio5 4}

shapingDropsPrio5LevelEntry OBJECT-TYPE
	SYNTAX      ShapingDropsPrio5LevelEntry
	MAX-ACCESS  not-accessible
	STATUS      current
	DESCRIPTION
	"Table entry for shapingDropsPrio5"
	INDEX { shapingDropsPrio5LevelName }
	::={shapingDropsPrio5LevelTable 1}

ShapingDropsPrio5LevelEntry ::=
	SEQUENCE {
		shapingDropsPrio5LevelName	DisplayString,
		shapingDropsPrio5LevelVal	Counter64,
		shapingDropsPrio5LevelMom	CounterBasedGauge64,
		shapingDropsPrio5LevelMax	CounterBasedGauge64
	}

shapingDropsPrio5LevelName OBJECT-TYPE
	SYNTAX      DisplayString
	MAX-ACCESS  not-accessible
	STATUS      current
	DESCRIPTION
	"Table entry display string for shapingDropsPrio5"
	::={shapingDropsPrio5LevelEntry 1}

shapingDropsPrio5LevelVal OBJECT-TYPE
	SYNTAX	 Counter64
	MAX-ACCESS  read-only
	STATUS      current
	DESCRIPTION
	"Table entry attribute for shapingDropsPrio5"
	::={shapingDropsPrio5LevelEntry 2}

shapingDropsPrio5LevelMom OBJECT-TYPE
	SYNTAX	 CounterBasedGauge64
	MAX-ACCESS  read-only
	STATUS      current
	DESCRIPTION
	"Table entry attribute for shapingDropsPrio5"
	::={shapingDropsPrio5LevelEntry 3}

shapingDropsPrio5LevelMax OBJECT-TYPE
	SYNTAX	 CounterBasedGauge64
	MAX-ACCESS  read-only
	STATUS      current
	DESCRIPTION
	"Table entry attribute for shapingDropsPrio5"
	::={shapingDropsPrio5LevelEntry 4}


shapingDropsPrio6	OBJECT IDENTIFIER ::={shaping 59}

shapingDropsPrio6Val	OBJECT-TYPE
	SYNTAX	 Counter64
	MAX-ACCESS read-only
	STATUS current
	DESCRIPTION "Queuing drops (prio 6)"

	::={shapingDropsPrio6 1}

shapingDropsPrio6Mom	OBJECT-TYPE
	SYNTAX	 CounterBasedGauge64
	MAX-ACCESS read-only
	STATUS current
	DESCRIPTION "Queuing drops (prio 6)"

	::={shapingDropsPrio6 2}

shapingDropsPrio6Max	OBJECT-TYPE
	SYNTAX	 CounterBasedGauge64
	MAX-ACCESS read-only
	STATUS current
	DESCRIPTION "Queuing drops (prio 6)"

	::={shapingDropsPrio6 3}

shapingDropsPrio6LevelTable OBJECT-TYPE
	SYNTAX      SEQUENCE OF ShapingDropsPrio6LevelEntry
	MAX-ACCESS  not-accessible
	STATUS      current
	DESCRIPTION
	"Table for shapingDropsPrio6"
	::={shapingDropsPrio6 4}

shapingDropsPrio6LevelEntry OBJECT-TYPE
	SYNTAX      ShapingDropsPrio6LevelEntry
	MAX-ACCESS  not-accessible
	STATUS      current
	DESCRIPTION
	"Table entry for shapingDropsPrio6"
	INDEX { shapingDropsPrio6LevelName }
	::={shapingDropsPrio6LevelTable 1}

ShapingDropsPrio6LevelEntry ::=
	SEQUENCE {
		shapingDropsPrio6LevelName	DisplayString,
		shapingDropsPrio6LevelVal	Counter64,
		shapingDropsPrio6LevelMom	CounterBasedGauge64,
		shapingDropsPrio6LevelMax	CounterBasedGauge64
	}

shapingDropsPrio6LevelName OBJECT-TYPE
	SYNTAX      DisplayString
	MAX-ACCESS  not-accessible
	STATUS      current
	DESCRIPTION
	"Table entry display string for shapingDropsPrio6"
	::={shapingDropsPrio6LevelEntry 1}

shapingDropsPrio6LevelVal OBJECT-TYPE
	SYNTAX	 Counter64
	MAX-ACCESS  read-only
	STATUS      current
	DESCRIPTION
	"Table entry attribute for shapingDropsPrio6"
	::={shapingDropsPrio6LevelEntry 2}

shapingDropsPrio6LevelMom OBJECT-TYPE
	SYNTAX	 CounterBasedGauge64
	MAX-ACCESS  read-only
	STATUS      current
	DESCRIPTION
	"Table entry attribute for shapingDropsPrio6"
	::={shapingDropsPrio6LevelEntry 3}

shapingDropsPrio6LevelMax OBJECT-TYPE
	SYNTAX	 CounterBasedGauge64
	MAX-ACCESS  read-only
	STATUS      current
	DESCRIPTION
	"Table entry attribute for shapingDropsPrio6"
	::={shapingDropsPrio6LevelEntry 4}


shapingDropsPrio7	OBJECT IDENTIFIER ::={shaping 60}

shapingDropsPrio7Val	OBJECT-TYPE
	SYNTAX	 Counter64
	MAX-ACCESS read-only
	STATUS current
	DESCRIPTION "Queuing drops (prio 7)"

	::={shapingDropsPrio7 1}

shapingDropsPrio7Mom	OBJECT-TYPE
	SYNTAX	 CounterBasedGauge64
	MAX-ACCESS read-only
	STATUS current
	DESCRIPTION "Queuing drops (prio 7)"

	::={shapingDropsPrio7 2}

shapingDropsPrio7Max	OBJECT-TYPE
	SYNTAX	 CounterBasedGauge64
	MAX-ACCESS read-only
	STATUS current
	DESCRIPTION "Queuing drops (prio 7)"

	::={shapingDropsPrio7 3}

shapingDropsPrio7LevelTable OBJECT-TYPE
	SYNTAX      SEQUENCE OF ShapingDropsPrio7LevelEntry
	MAX-ACCESS  not-accessible
	STATUS      current
	DESCRIPTION
	"Table for shapingDropsPrio7"
	::={shapingDropsPrio7 4}

shapingDropsPrio7LevelEntry OBJECT-TYPE
	SYNTAX      ShapingDropsPrio7LevelEntry
	MAX-ACCESS  not-accessible
	STATUS      current
	DESCRIPTION
	"Table entry for shapingDropsPrio7"
	INDEX { shapingDropsPrio7LevelName }
	::={shapingDropsPrio7LevelTable 1}

ShapingDropsPrio7LevelEntry ::=
	SEQUENCE {
		shapingDropsPrio7LevelName	DisplayString,
		shapingDropsPrio7LevelVal	Counter64,
		shapingDropsPrio7LevelMom	CounterBasedGauge64,
		shapingDropsPrio7LevelMax	CounterBasedGauge64
	}

shapingDropsPrio7LevelName OBJECT-TYPE
	SYNTAX      DisplayString
	MAX-ACCESS  not-accessible
	STATUS      current
	DESCRIPTION
	"Table entry display string for shapingDropsPrio7"
	::={shapingDropsPrio7LevelEntry 1}

shapingDropsPrio7LevelVal OBJECT-TYPE
	SYNTAX	 Counter64
	MAX-ACCESS  read-only
	STATUS      current
	DESCRIPTION
	"Table entry attribute for shapingDropsPrio7"
	::={shapingDropsPrio7LevelEntry 2}

shapingDropsPrio7LevelMom OBJECT-TYPE
	SYNTAX	 CounterBasedGauge64
	MAX-ACCESS  read-only
	STATUS      current
	DESCRIPTION
	"Table entry attribute for shapingDropsPrio7"
	::={shapingDropsPrio7LevelEntry 3}

shapingDropsPrio7LevelMax OBJECT-TYPE
	SYNTAX	 CounterBasedGauge64
	MAX-ACCESS  read-only
	STATUS      current
	DESCRIPTION
	"Table entry attribute for shapingDropsPrio7"
	::={shapingDropsPrio7LevelEntry 4}


shapingDropsPrio8	OBJECT IDENTIFIER ::={shaping 61}

shapingDropsPrio8Val	OBJECT-TYPE
	SYNTAX	 Counter64
	MAX-ACCESS read-only
	STATUS current
	DESCRIPTION "Queuing drops (prio 8)"

	::={shapingDropsPrio8 1}

shapingDropsPrio8Mom	OBJECT-TYPE
	SYNTAX	 CounterBasedGauge64
	MAX-ACCESS read-only
	STATUS current
	DESCRIPTION "Queuing drops (prio 8)"

	::={shapingDropsPrio8 2}

shapingDropsPrio8Max	OBJECT-TYPE
	SYNTAX	 CounterBasedGauge64
	MAX-ACCESS read-only
	STATUS current
	DESCRIPTION "Queuing drops (prio 8)"

	::={shapingDropsPrio8 3}

shapingDropsPrio8LevelTable OBJECT-TYPE
	SYNTAX      SEQUENCE OF ShapingDropsPrio8LevelEntry
	MAX-ACCESS  not-accessible
	STATUS      current
	DESCRIPTION
	"Table for shapingDropsPrio8"
	::={shapingDropsPrio8 4}

shapingDropsPrio8LevelEntry OBJECT-TYPE
	SYNTAX      ShapingDropsPrio8LevelEntry
	MAX-ACCESS  not-accessible
	STATUS      current
	DESCRIPTION
	"Table entry for shapingDropsPrio8"
	INDEX { shapingDropsPrio8LevelName }
	::={shapingDropsPrio8LevelTable 1}

ShapingDropsPrio8LevelEntry ::=
	SEQUENCE {
		shapingDropsPrio8LevelName	DisplayString,
		shapingDropsPrio8LevelVal	Counter64,
		shapingDropsPrio8LevelMom	CounterBasedGauge64,
		shapingDropsPrio8LevelMax	CounterBasedGauge64
	}

shapingDropsPrio8LevelName OBJECT-TYPE
	SYNTAX      DisplayString
	MAX-ACCESS  not-accessible
	STATUS      current
	DESCRIPTION
	"Table entry display string for shapingDropsPrio8"
	::={shapingDropsPrio8LevelEntry 1}

shapingDropsPrio8LevelVal OBJECT-TYPE
	SYNTAX	 Counter64
	MAX-ACCESS  read-only
	STATUS      current
	DESCRIPTION
	"Table entry attribute for shapingDropsPrio8"
	::={shapingDropsPrio8LevelEntry 2}

shapingDropsPrio8LevelMom OBJECT-TYPE
	SYNTAX	 CounterBasedGauge64
	MAX-ACCESS  read-only
	STATUS      current
	DESCRIPTION
	"Table entry attribute for shapingDropsPrio8"
	::={shapingDropsPrio8LevelEntry 3}

shapingDropsPrio8LevelMax OBJECT-TYPE
	SYNTAX	 CounterBasedGauge64
	MAX-ACCESS  read-only
	STATUS      current
	DESCRIPTION
	"Table entry attribute for shapingDropsPrio8"
	::={shapingDropsPrio8LevelEntry 4}


shapingDropsPrio9	OBJECT IDENTIFIER ::={shaping 62}

shapingDropsPrio9Val	OBJECT-TYPE
	SYNTAX	 Counter64
	MAX-ACCESS read-only
	STATUS current
	DESCRIPTION "Queuing drops (prio 9)"

	::={shapingDropsPrio9 1}

shapingDropsPrio9Mom	OBJECT-TYPE
	SYNTAX	 CounterBasedGauge64
	MAX-ACCESS read-only
	STATUS current
	DESCRIPTION "Queuing drops (prio 9)"

	::={shapingDropsPrio9 2}

shapingDropsPrio9Max	OBJECT-TYPE
	SYNTAX	 CounterBasedGauge64
	MAX-ACCESS read-only
	STATUS current
	DESCRIPTION "Queuing drops (prio 9)"

	::={shapingDropsPrio9 3}

shapingDropsPrio9LevelTable OBJECT-TYPE
	SYNTAX      SEQUENCE OF ShapingDropsPrio9LevelEntry
	MAX-ACCESS  not-accessible
	STATUS      current
	DESCRIPTION
	"Table for shapingDropsPrio9"
	::={shapingDropsPrio9 4}

shapingDropsPrio9LevelEntry OBJECT-TYPE
	SYNTAX      ShapingDropsPrio9LevelEntry
	MAX-ACCESS  not-accessible
	STATUS      current
	DESCRIPTION
	"Table entry for shapingDropsPrio9"
	INDEX { shapingDropsPrio9LevelName }
	::={shapingDropsPrio9LevelTable 1}

ShapingDropsPrio9LevelEntry ::=
	SEQUENCE {
		shapingDropsPrio9LevelName	DisplayString,
		shapingDropsPrio9LevelVal	Counter64,
		shapingDropsPrio9LevelMom	CounterBasedGauge64,
		shapingDropsPrio9LevelMax	CounterBasedGauge64
	}

shapingDropsPrio9LevelName OBJECT-TYPE
	SYNTAX      DisplayString
	MAX-ACCESS  not-accessible
	STATUS      current
	DESCRIPTION
	"Table entry display string for shapingDropsPrio9"
	::={shapingDropsPrio9LevelEntry 1}

shapingDropsPrio9LevelVal OBJECT-TYPE
	SYNTAX	 Counter64
	MAX-ACCESS  read-only
	STATUS      current
	DESCRIPTION
	"Table entry attribute for shapingDropsPrio9"
	::={shapingDropsPrio9LevelEntry 2}

shapingDropsPrio9LevelMom OBJECT-TYPE
	SYNTAX	 CounterBasedGauge64
	MAX-ACCESS  read-only
	STATUS      current
	DESCRIPTION
	"Table entry attribute for shapingDropsPrio9"
	::={shapingDropsPrio9LevelEntry 3}

shapingDropsPrio9LevelMax OBJECT-TYPE
	SYNTAX	 CounterBasedGauge64
	MAX-ACCESS  read-only
	STATUS      current
	DESCRIPTION
	"Table entry attribute for shapingDropsPrio9"
	::={shapingDropsPrio9LevelEntry 4}


shapingDropsPrioOther	OBJECT IDENTIFIER ::={shaping 63}

shapingDropsPrioOtherVal	OBJECT-TYPE
	SYNTAX	 Counter64
	MAX-ACCESS read-only
	STATUS current
	DESCRIPTION "Queuing drops (other prio)"

	::={shapingDropsPrioOther 1}

shapingDropsPrioOtherMom	OBJECT-TYPE
	SYNTAX	 CounterBasedGauge64
	MAX-ACCESS read-only
	STATUS current
	DESCRIPTION "Queuing drops (other prio)"

	::={shapingDropsPrioOther 2}

shapingDropsPrioOtherMax	OBJECT-TYPE
	SYNTAX	 CounterBasedGauge64
	MAX-ACCESS read-only
	STATUS current
	DESCRIPTION "Queuing drops (other prio)"

	::={shapingDropsPrioOther 3}

shapingDropsPrioOtherLevelTable OBJECT-TYPE
	SYNTAX      SEQUENCE OF ShapingDropsPrioOtherLevelEntry
	MAX-ACCESS  not-accessible
	STATUS      current
	DESCRIPTION
	"Table for shapingDropsPrioOther"
	::={shapingDropsPrioOther 4}

shapingDropsPrioOtherLevelEntry OBJECT-TYPE
	SYNTAX      ShapingDropsPrioOtherLevelEntry
	MAX-ACCESS  not-accessible
	STATUS      current
	DESCRIPTION
	"Table entry for shapingDropsPrioOther"
	INDEX { shapingDropsPrioOtherLevelName }
	::={shapingDropsPrioOtherLevelTable 1}

ShapingDropsPrioOtherLevelEntry ::=
	SEQUENCE {
		shapingDropsPrioOtherLevelName	DisplayString,
		shapingDropsPrioOtherLevelVal	Counter64,
		shapingDropsPrioOtherLevelMom	CounterBasedGauge64,
		shapingDropsPrioOtherLevelMax	CounterBasedGauge64
	}

shapingDropsPrioOtherLevelName OBJECT-TYPE
	SYNTAX      DisplayString
	MAX-ACCESS  not-accessible
	STATUS      current
	DESCRIPTION
	"Table entry display string for shapingDropsPrioOther"
	::={shapingDropsPrioOtherLevelEntry 1}

shapingDropsPrioOtherLevelVal OBJECT-TYPE
	SYNTAX	 Counter64
	MAX-ACCESS  read-only
	STATUS      current
	DESCRIPTION
	"Table entry attribute for shapingDropsPrioOther"
	::={shapingDropsPrioOtherLevelEntry 2}

shapingDropsPrioOtherLevelMom OBJECT-TYPE
	SYNTAX	 CounterBasedGauge64
	MAX-ACCESS  read-only
	STATUS      current
	DESCRIPTION
	"Table entry attribute for shapingDropsPrioOther"
	::={shapingDropsPrioOtherLevelEntry 3}

shapingDropsPrioOtherLevelMax OBJECT-TYPE
	SYNTAX	 CounterBasedGauge64
	MAX-ACCESS  read-only
	STATUS      current
	DESCRIPTION
	"Table entry attribute for shapingDropsPrioOther"
	::={shapingDropsPrioOtherLevelEntry 4}


shapingDropsCps	OBJECT IDENTIFIER ::={shaping 64}

shapingDropsCpsVal	OBJECT-TYPE
	SYNTAX	 Counter64
	MAX-ACCESS read-only
	STATUS current
	DESCRIPTION "CPS limit drops"

	::={shapingDropsCps 1}

shapingDropsCpsMom	OBJECT-TYPE
	SYNTAX	 CounterBasedGauge64
	MAX-ACCESS read-only
	STATUS current
	DESCRIPTION "CPS limit drops"

	::={shapingDropsCps 2}

shapingDropsCpsMax	OBJECT-TYPE
	SYNTAX	 CounterBasedGauge64
	MAX-ACCESS read-only
	STATUS current
	DESCRIPTION "CPS limit drops"

	::={shapingDropsCps 3}

shapingDropsCpsLevelTable OBJECT-TYPE
	SYNTAX      SEQUENCE OF ShapingDropsCpsLevelEntry
	MAX-ACCESS  not-accessible
	STATUS      current
	DESCRIPTION
	"Table for shapingDropsCps"
	::={shapingDropsCps 4}

shapingDropsCpsLevelEntry OBJECT-TYPE
	SYNTAX      ShapingDropsCpsLevelEntry
	MAX-ACCESS  not-accessible
	STATUS      current
	DESCRIPTION
	"Table entry for shapingDropsCps"
	INDEX { shapingDropsCpsLevelName }
	::={shapingDropsCpsLevelTable 1}

ShapingDropsCpsLevelEntry ::=
	SEQUENCE {
		shapingDropsCpsLevelName	DisplayString,
		shapingDropsCpsLevelVal	Counter64,
		shapingDropsCpsLevelMom	CounterBasedGauge64,
		shapingDropsCpsLevelMax	CounterBasedGauge64
	}

shapingDropsCpsLevelName OBJECT-TYPE
	SYNTAX      DisplayString
	MAX-ACCESS  not-accessible
	STATUS      current
	DESCRIPTION
	"Table entry display string for shapingDropsCps"
	::={shapingDropsCpsLevelEntry 1}

shapingDropsCpsLevelVal OBJECT-TYPE
	SYNTAX	 Counter64
	MAX-ACCESS  read-only
	STATUS      current
	DESCRIPTION
	"Table entry attribute for shapingDropsCps"
	::={shapingDropsCpsLevelEntry 2}

shapingDropsCpsLevelMom OBJECT-TYPE
	SYNTAX	 CounterBasedGauge64
	MAX-ACCESS  read-only
	STATUS      current
	DESCRIPTION
	"Table entry attribute for shapingDropsCps"
	::={shapingDropsCpsLevelEntry 3}

shapingDropsCpsLevelMax OBJECT-TYPE
	SYNTAX	 CounterBasedGauge64
	MAX-ACCESS  read-only
	STATUS      current
	DESCRIPTION
	"Table entry attribute for shapingDropsCps"
	::={shapingDropsCpsLevelEntry 4}


shapingFailedFairnessObjects	OBJECT IDENTIFIER ::={shaping 65}

shapingFailedFairnessObjectsVal	OBJECT-TYPE
	SYNTAX	 Counter64
	MAX-ACCESS read-only
	STATUS current
	DESCRIPTION "Host fairness data allocation failures"

	::={shapingFailedFairnessObjects 1}

shapingFailedFairnessObjectsMom	OBJECT-TYPE
	SYNTAX	 CounterBasedGauge64
	MAX-ACCESS read-only
	STATUS current
	DESCRIPTION "Host fairness data allocation failures"

	::={shapingFailedFairnessObjects 2}

shapingFailedFairnessObjectsMax	OBJECT-TYPE
	SYNTAX	 CounterBasedGauge64
	MAX-ACCESS read-only
	STATUS current
	DESCRIPTION "Host fairness data allocation failures"

	::={shapingFailedFairnessObjects 3}

shapingFailedFairnessObjectsLevelTable OBJECT-TYPE
	SYNTAX      SEQUENCE OF ShapingFailedFairnessObjectsLevelEntry
	MAX-ACCESS  not-accessible
	STATUS      current
	DESCRIPTION
	"Table for shapingFailedFairnessObjects"
	::={shapingFailedFairnessObjects 4}

shapingFailedFairnessObjectsLevelEntry OBJECT-TYPE
	SYNTAX      ShapingFailedFairnessObjectsLevelEntry
	MAX-ACCESS  not-accessible
	STATUS      current
	DESCRIPTION
	"Table entry for shapingFailedFairnessObjects"
	INDEX { shapingFailedFairnessObjectsLevelName }
	::={shapingFailedFairnessObjectsLevelTable 1}

ShapingFailedFairnessObjectsLevelEntry ::=
	SEQUENCE {
		shapingFailedFairnessObjectsLevelName	DisplayString,
		shapingFailedFairnessObjectsLevelVal	Counter64,
		shapingFailedFairnessObjectsLevelMom	CounterBasedGauge64,
		shapingFailedFairnessObjectsLevelMax	CounterBasedGauge64
	}

shapingFailedFairnessObjectsLevelName OBJECT-TYPE
	SYNTAX      DisplayString
	MAX-ACCESS  not-accessible
	STATUS      current
	DESCRIPTION
	"Table entry display string for shapingFailedFairnessObjects"
	::={shapingFailedFairnessObjectsLevelEntry 1}

shapingFailedFairnessObjectsLevelVal OBJECT-TYPE
	SYNTAX	 Counter64
	MAX-ACCESS  read-only
	STATUS      current
	DESCRIPTION
	"Table entry attribute for shapingFailedFairnessObjects"
	::={shapingFailedFairnessObjectsLevelEntry 2}

shapingFailedFairnessObjectsLevelMom OBJECT-TYPE
	SYNTAX	 CounterBasedGauge64
	MAX-ACCESS  read-only
	STATUS      current
	DESCRIPTION
	"Table entry attribute for shapingFailedFairnessObjects"
	::={shapingFailedFairnessObjectsLevelEntry 3}

shapingFailedFairnessObjectsLevelMax OBJECT-TYPE
	SYNTAX	 CounterBasedGauge64
	MAX-ACCESS  read-only
	STATUS      current
	DESCRIPTION
	"Table entry attribute for shapingFailedFairnessObjects"
	::={shapingFailedFairnessObjectsLevelEntry 4}


shapingUsedFairnessObjects	OBJECT IDENTIFIER ::={shaping 66}

shapingUsedFairnessObjectsVal	OBJECT-TYPE
	SYNTAX	 CounterBasedGauge64
	MAX-ACCESS read-only
	STATUS current
	DESCRIPTION "Host fairness data used"

	::={shapingUsedFairnessObjects 1}

shapingUsedFairnessObjectsMax	OBJECT-TYPE
	SYNTAX	 CounterBasedGauge64
	MAX-ACCESS read-only
	STATUS current
	DESCRIPTION "Host fairness data used"

	::={shapingUsedFairnessObjects 3}

shapingUsedFairnessObjectsLevelTable OBJECT-TYPE
	SYNTAX      SEQUENCE OF ShapingUsedFairnessObjectsLevelEntry
	MAX-ACCESS  not-accessible
	STATUS      current
	DESCRIPTION
	"Table for shapingUsedFairnessObjects"
	::={shapingUsedFairnessObjects 4}

shapingUsedFairnessObjectsLevelEntry OBJECT-TYPE
	SYNTAX      ShapingUsedFairnessObjectsLevelEntry
	MAX-ACCESS  not-accessible
	STATUS      current
	DESCRIPTION
	"Table entry for shapingUsedFairnessObjects"
	INDEX { shapingUsedFairnessObjectsLevelName }
	::={shapingUsedFairnessObjectsLevelTable 1}

ShapingUsedFairnessObjectsLevelEntry ::=
	SEQUENCE {
		shapingUsedFairnessObjectsLevelName	DisplayString,
		shapingUsedFairnessObjectsLevelVal	CounterBasedGauge64,
		shapingUsedFairnessObjectsLevelMax	CounterBasedGauge64
	}

shapingUsedFairnessObjectsLevelName OBJECT-TYPE
	SYNTAX      DisplayString
	MAX-ACCESS  not-accessible
	STATUS      current
	DESCRIPTION
	"Table entry display string for shapingUsedFairnessObjects"
	::={shapingUsedFairnessObjectsLevelEntry 1}

shapingUsedFairnessObjectsLevelVal OBJECT-TYPE
	SYNTAX	 CounterBasedGauge64
	MAX-ACCESS  read-only
	STATUS      current
	DESCRIPTION
	"Table entry attribute for shapingUsedFairnessObjects"
	::={shapingUsedFairnessObjectsLevelEntry 2}

shapingUsedFairnessObjectsLevelMax OBJECT-TYPE
	SYNTAX	 CounterBasedGauge64
	MAX-ACCESS  read-only
	STATUS      current
	DESCRIPTION
	"Table entry attribute for shapingUsedFairnessObjects"
	::={shapingUsedFairnessObjectsLevelEntry 4}


shapingReloadDrops	OBJECT IDENTIFIER ::={shaping 67}

shapingReloadDropsVal	OBJECT-TYPE
	SYNTAX	 Counter64
	MAX-ACCESS read-only
	STATUS obsolete
	DESCRIPTION "Drops caused by ruleset reload"

	::={shapingReloadDrops 1}

shapingReloadDropsMom	OBJECT-TYPE
	SYNTAX	 CounterBasedGauge64
	MAX-ACCESS read-only
	STATUS obsolete
	DESCRIPTION "Drops caused by ruleset reload"

	::={shapingReloadDrops 2}

shapingReloadDropsMax	OBJECT-TYPE
	SYNTAX	 CounterBasedGauge64
	MAX-ACCESS read-only
	STATUS obsolete
	DESCRIPTION "Drops caused by ruleset reload"

	::={shapingReloadDrops 3}

shapingReloadDropsLevelTable OBJECT-TYPE
	SYNTAX      SEQUENCE OF ShapingReloadDropsLevelEntry
	MAX-ACCESS  not-accessible
	STATUS      current
	DESCRIPTION
	"Table for shapingReloadDrops"
	::={shapingReloadDrops 4}

shapingReloadDropsLevelEntry OBJECT-TYPE
	SYNTAX      ShapingReloadDropsLevelEntry
	MAX-ACCESS  not-accessible
	STATUS      current
	DESCRIPTION
	"Table entry for shapingReloadDrops"
	INDEX { shapingReloadDropsLevelName }
	::={shapingReloadDropsLevelTable 1}

ShapingReloadDropsLevelEntry ::=
	SEQUENCE {
		shapingReloadDropsLevelName	DisplayString,
		shapingReloadDropsLevelVal	Counter64,
		shapingReloadDropsLevelMom	CounterBasedGauge64,
		shapingReloadDropsLevelMax	CounterBasedGauge64
	}

shapingReloadDropsLevelName OBJECT-TYPE
	SYNTAX      DisplayString
	MAX-ACCESS  not-accessible
	STATUS      current
	DESCRIPTION
	"Table entry display string for shapingReloadDrops"
	::={shapingReloadDropsLevelEntry 1}

shapingReloadDropsLevelVal OBJECT-TYPE
	SYNTAX	 Counter64
	MAX-ACCESS  read-only
	STATUS      current
	DESCRIPTION
	"Table entry attribute for shapingReloadDrops"
	::={shapingReloadDropsLevelEntry 2}

shapingReloadDropsLevelMom OBJECT-TYPE
	SYNTAX	 CounterBasedGauge64
	MAX-ACCESS  read-only
	STATUS      current
	DESCRIPTION
	"Table entry attribute for shapingReloadDrops"
	::={shapingReloadDropsLevelEntry 3}

shapingReloadDropsLevelMax OBJECT-TYPE
	SYNTAX	 CounterBasedGauge64
	MAX-ACCESS  read-only
	STATUS      current
	DESCRIPTION
	"Table entry attribute for shapingReloadDrops"
	::={shapingReloadDropsLevelEntry 4}


shapingRequeueQueueUsed	OBJECT IDENTIFIER ::={shaping 68}

shapingRequeueQueueUsedVal	OBJECT-TYPE
	SYNTAX	 CounterBasedGauge64
	MAX-ACCESS read-only
	STATUS obsolete
	DESCRIPTION "Packets in requeue queue"

	::={shapingRequeueQueueUsed 1}

shapingRequeueQueueUsedMax	OBJECT-TYPE
	SYNTAX	 CounterBasedGauge64
	MAX-ACCESS read-only
	STATUS obsolete
	DESCRIPTION "Packets in requeue queue"

	::={shapingRequeueQueueUsed 3}

shapingRequeueQueueUsedLevelTable OBJECT-TYPE
	SYNTAX      SEQUENCE OF ShapingRequeueQueueUsedLevelEntry
	MAX-ACCESS  not-accessible
	STATUS      current
	DESCRIPTION
	"Table for shapingRequeueQueueUsed"
	::={shapingRequeueQueueUsed 4}

shapingRequeueQueueUsedLevelEntry OBJECT-TYPE
	SYNTAX      ShapingRequeueQueueUsedLevelEntry
	MAX-ACCESS  not-accessible
	STATUS      current
	DESCRIPTION
	"Table entry for shapingRequeueQueueUsed"
	INDEX { shapingRequeueQueueUsedLevelName }
	::={shapingRequeueQueueUsedLevelTable 1}

ShapingRequeueQueueUsedLevelEntry ::=
	SEQUENCE {
		shapingRequeueQueueUsedLevelName	DisplayString,
		shapingRequeueQueueUsedLevelVal	CounterBasedGauge64,
		shapingRequeueQueueUsedLevelMax	CounterBasedGauge64
	}

shapingRequeueQueueUsedLevelName OBJECT-TYPE
	SYNTAX      DisplayString
	MAX-ACCESS  not-accessible
	STATUS      current
	DESCRIPTION
	"Table entry display string for shapingRequeueQueueUsed"
	::={shapingRequeueQueueUsedLevelEntry 1}

shapingRequeueQueueUsedLevelVal OBJECT-TYPE
	SYNTAX	 CounterBasedGauge64
	MAX-ACCESS  read-only
	STATUS      current
	DESCRIPTION
	"Table entry attribute for shapingRequeueQueueUsed"
	::={shapingRequeueQueueUsedLevelEntry 2}

shapingRequeueQueueUsedLevelMax OBJECT-TYPE
	SYNTAX	 CounterBasedGauge64
	MAX-ACCESS  read-only
	STATUS      current
	DESCRIPTION
	"Table entry attribute for shapingRequeueQueueUsed"
	::={shapingRequeueQueueUsedLevelEntry 4}


shapingDirectBytesPrio0	OBJECT IDENTIFIER ::={shaping 69}

shapingDirectBytesPrio0Val	OBJECT-TYPE
	SYNTAX	 Counter64
	MAX-ACCESS read-only
	STATUS current
	DESCRIPTION "Directly sent bytes (prio 0)"

	::={shapingDirectBytesPrio0 1}

shapingDirectBytesPrio0Mom	OBJECT-TYPE
	SYNTAX	 CounterBasedGauge64
	MAX-ACCESS read-only
	STATUS current
	DESCRIPTION "Directly sent bytes (prio 0)"

	::={shapingDirectBytesPrio0 2}

shapingDirectBytesPrio0Max	OBJECT-TYPE
	SYNTAX	 CounterBasedGauge64
	MAX-ACCESS read-only
	STATUS current
	DESCRIPTION "Directly sent bytes (prio 0)"

	::={shapingDirectBytesPrio0 3}

shapingDirectBytesPrio0LevelTable OBJECT-TYPE
	SYNTAX      SEQUENCE OF ShapingDirectBytesPrio0LevelEntry
	MAX-ACCESS  not-accessible
	STATUS      current
	DESCRIPTION
	"Table for shapingDirectBytesPrio0"
	::={shapingDirectBytesPrio0 4}

shapingDirectBytesPrio0LevelEntry OBJECT-TYPE
	SYNTAX      ShapingDirectBytesPrio0LevelEntry
	MAX-ACCESS  not-accessible
	STATUS      current
	DESCRIPTION
	"Table entry for shapingDirectBytesPrio0"
	INDEX { shapingDirectBytesPrio0LevelName }
	::={shapingDirectBytesPrio0LevelTable 1}

ShapingDirectBytesPrio0LevelEntry ::=
	SEQUENCE {
		shapingDirectBytesPrio0LevelName	DisplayString,
		shapingDirectBytesPrio0LevelVal	Counter64,
		shapingDirectBytesPrio0LevelMom	CounterBasedGauge64,
		shapingDirectBytesPrio0LevelMax	CounterBasedGauge64
	}

shapingDirectBytesPrio0LevelName OBJECT-TYPE
	SYNTAX      DisplayString
	MAX-ACCESS  not-accessible
	STATUS      current
	DESCRIPTION
	"Table entry display string for shapingDirectBytesPrio0"
	::={shapingDirectBytesPrio0LevelEntry 1}

shapingDirectBytesPrio0LevelVal OBJECT-TYPE
	SYNTAX	 Counter64
	MAX-ACCESS  read-only
	STATUS      current
	DESCRIPTION
	"Table entry attribute for shapingDirectBytesPrio0"
	::={shapingDirectBytesPrio0LevelEntry 2}

shapingDirectBytesPrio0LevelMom OBJECT-TYPE
	SYNTAX	 CounterBasedGauge64
	MAX-ACCESS  read-only
	STATUS      current
	DESCRIPTION
	"Table entry attribute for shapingDirectBytesPrio0"
	::={shapingDirectBytesPrio0LevelEntry 3}

shapingDirectBytesPrio0LevelMax OBJECT-TYPE
	SYNTAX	 CounterBasedGauge64
	MAX-ACCESS  read-only
	STATUS      current
	DESCRIPTION
	"Table entry attribute for shapingDirectBytesPrio0"
	::={shapingDirectBytesPrio0LevelEntry 4}


shapingDequeuedOdirs	OBJECT IDENTIFIER ::={shaping 70}

shapingDequeuedOdirsVal	OBJECT-TYPE
	SYNTAX	 Counter64
	MAX-ACCESS read-only
	STATUS obsolete
	DESCRIPTION "Dequeued Odirs"

	::={shapingDequeuedOdirs 1}

shapingDequeuedOdirsMom	OBJECT-TYPE
	SYNTAX	 CounterBasedGauge64
	MAX-ACCESS read-only
	STATUS obsolete
	DESCRIPTION "Dequeued Odirs"

	::={shapingDequeuedOdirs 2}

shapingDequeuedOdirsMax	OBJECT-TYPE
	SYNTAX	 CounterBasedGauge64
	MAX-ACCESS read-only
	STATUS obsolete
	DESCRIPTION "Dequeued Odirs"

	::={shapingDequeuedOdirs 3}

shapingDequeuedOdirsLevelTable OBJECT-TYPE
	SYNTAX      SEQUENCE OF ShapingDequeuedOdirsLevelEntry
	MAX-ACCESS  not-accessible
	STATUS      current
	DESCRIPTION
	"Table for shapingDequeuedOdirs"
	::={shapingDequeuedOdirs 4}

shapingDequeuedOdirsLevelEntry OBJECT-TYPE
	SYNTAX      ShapingDequeuedOdirsLevelEntry
	MAX-ACCESS  not-accessible
	STATUS      current
	DESCRIPTION
	"Table entry for shapingDequeuedOdirs"
	INDEX { shapingDequeuedOdirsLevelName }
	::={shapingDequeuedOdirsLevelTable 1}

ShapingDequeuedOdirsLevelEntry ::=
	SEQUENCE {
		shapingDequeuedOdirsLevelName	DisplayString,
		shapingDequeuedOdirsLevelVal	Counter64,
		shapingDequeuedOdirsLevelMom	CounterBasedGauge64,
		shapingDequeuedOdirsLevelMax	CounterBasedGauge64
	}

shapingDequeuedOdirsLevelName OBJECT-TYPE
	SYNTAX      DisplayString
	MAX-ACCESS  not-accessible
	STATUS      current
	DESCRIPTION
	"Table entry display string for shapingDequeuedOdirs"
	::={shapingDequeuedOdirsLevelEntry 1}

shapingDequeuedOdirsLevelVal OBJECT-TYPE
	SYNTAX	 Counter64
	MAX-ACCESS  read-only
	STATUS      current
	DESCRIPTION
	"Table entry attribute for shapingDequeuedOdirs"
	::={shapingDequeuedOdirsLevelEntry 2}

shapingDequeuedOdirsLevelMom OBJECT-TYPE
	SYNTAX	 CounterBasedGauge64
	MAX-ACCESS  read-only
	STATUS      current
	DESCRIPTION
	"Table entry attribute for shapingDequeuedOdirs"
	::={shapingDequeuedOdirsLevelEntry 3}

shapingDequeuedOdirsLevelMax OBJECT-TYPE
	SYNTAX	 CounterBasedGauge64
	MAX-ACCESS  read-only
	STATUS      current
	DESCRIPTION
	"Table entry attribute for shapingDequeuedOdirs"
	::={shapingDequeuedOdirsLevelEntry 4}


shapingSkippedQsyncUpdates	OBJECT IDENTIFIER ::={shaping 71}

shapingSkippedQsyncUpdatesVal	OBJECT-TYPE
	SYNTAX	 Counter64
	MAX-ACCESS read-only
	STATUS current
	DESCRIPTION "Skipped qsync updates (no xfer)"

	::={shapingSkippedQsyncUpdates 1}

shapingSkippedQsyncUpdatesMom	OBJECT-TYPE
	SYNTAX	 CounterBasedGauge64
	MAX-ACCESS read-only
	STATUS current
	DESCRIPTION "Skipped qsync updates (no xfer)"

	::={shapingSkippedQsyncUpdates 2}

shapingSkippedQsyncUpdatesMax	OBJECT-TYPE
	SYNTAX	 CounterBasedGauge64
	MAX-ACCESS read-only
	STATUS current
	DESCRIPTION "Skipped qsync updates (no xfer)"

	::={shapingSkippedQsyncUpdates 3}

shapingSkippedQsyncUpdatesLevelTable OBJECT-TYPE
	SYNTAX      SEQUENCE OF ShapingSkippedQsyncUpdatesLevelEntry
	MAX-ACCESS  not-accessible
	STATUS      current
	DESCRIPTION
	"Table for shapingSkippedQsyncUpdates"
	::={shapingSkippedQsyncUpdates 4}

shapingSkippedQsyncUpdatesLevelEntry OBJECT-TYPE
	SYNTAX      ShapingSkippedQsyncUpdatesLevelEntry
	MAX-ACCESS  not-accessible
	STATUS      current
	DESCRIPTION
	"Table entry for shapingSkippedQsyncUpdates"
	INDEX { shapingSkippedQsyncUpdatesLevelName }
	::={shapingSkippedQsyncUpdatesLevelTable 1}

ShapingSkippedQsyncUpdatesLevelEntry ::=
	SEQUENCE {
		shapingSkippedQsyncUpdatesLevelName	DisplayString,
		shapingSkippedQsyncUpdatesLevelVal	Counter64,
		shapingSkippedQsyncUpdatesLevelMom	CounterBasedGauge64,
		shapingSkippedQsyncUpdatesLevelMax	CounterBasedGauge64
	}

shapingSkippedQsyncUpdatesLevelName OBJECT-TYPE
	SYNTAX      DisplayString
	MAX-ACCESS  not-accessible
	STATUS      current
	DESCRIPTION
	"Table entry display string for shapingSkippedQsyncUpdates"
	::={shapingSkippedQsyncUpdatesLevelEntry 1}

shapingSkippedQsyncUpdatesLevelVal OBJECT-TYPE
	SYNTAX	 Counter64
	MAX-ACCESS  read-only
	STATUS      current
	DESCRIPTION
	"Table entry attribute for shapingSkippedQsyncUpdates"
	::={shapingSkippedQsyncUpdatesLevelEntry 2}

shapingSkippedQsyncUpdatesLevelMom OBJECT-TYPE
	SYNTAX	 CounterBasedGauge64
	MAX-ACCESS  read-only
	STATUS      current
	DESCRIPTION
	"Table entry attribute for shapingSkippedQsyncUpdates"
	::={shapingSkippedQsyncUpdatesLevelEntry 3}

shapingSkippedQsyncUpdatesLevelMax OBJECT-TYPE
	SYNTAX	 CounterBasedGauge64
	MAX-ACCESS  read-only
	STATUS      current
	DESCRIPTION
	"Table entry attribute for shapingSkippedQsyncUpdates"
	::={shapingSkippedQsyncUpdatesLevelEntry 4}


shapingObjectCopiesCreated	OBJECT IDENTIFIER ::={shaping 72}

shapingObjectCopiesCreatedVal	OBJECT-TYPE
	SYNTAX	 Counter64
	MAX-ACCESS read-only
	STATUS current
	DESCRIPTION "Object copies created"

	::={shapingObjectCopiesCreated 1}

shapingObjectCopiesCreatedMom	OBJECT-TYPE
	SYNTAX	 CounterBasedGauge64
	MAX-ACCESS read-only
	STATUS current
	DESCRIPTION "Object copies created"

	::={shapingObjectCopiesCreated 2}

shapingObjectCopiesCreatedMax	OBJECT-TYPE
	SYNTAX	 CounterBasedGauge64
	MAX-ACCESS read-only
	STATUS current
	DESCRIPTION "Object copies created"

	::={shapingObjectCopiesCreated 3}

shapingObjectCopiesCreatedLevelTable OBJECT-TYPE
	SYNTAX      SEQUENCE OF ShapingObjectCopiesCreatedLevelEntry
	MAX-ACCESS  not-accessible
	STATUS      current
	DESCRIPTION
	"Table for shapingObjectCopiesCreated"
	::={shapingObjectCopiesCreated 4}

shapingObjectCopiesCreatedLevelEntry OBJECT-TYPE
	SYNTAX      ShapingObjectCopiesCreatedLevelEntry
	MAX-ACCESS  not-accessible
	STATUS      current
	DESCRIPTION
	"Table entry for shapingObjectCopiesCreated"
	INDEX { shapingObjectCopiesCreatedLevelName }
	::={shapingObjectCopiesCreatedLevelTable 1}

ShapingObjectCopiesCreatedLevelEntry ::=
	SEQUENCE {
		shapingObjectCopiesCreatedLevelName	DisplayString,
		shapingObjectCopiesCreatedLevelVal	Counter64,
		shapingObjectCopiesCreatedLevelMom	CounterBasedGauge64,
		shapingObjectCopiesCreatedLevelMax	CounterBasedGauge64
	}

shapingObjectCopiesCreatedLevelName OBJECT-TYPE
	SYNTAX      DisplayString
	MAX-ACCESS  not-accessible
	STATUS      current
	DESCRIPTION
	"Table entry display string for shapingObjectCopiesCreated"
	::={shapingObjectCopiesCreatedLevelEntry 1}

shapingObjectCopiesCreatedLevelVal OBJECT-TYPE
	SYNTAX	 Counter64
	MAX-ACCESS  read-only
	STATUS      current
	DESCRIPTION
	"Table entry attribute for shapingObjectCopiesCreated"
	::={shapingObjectCopiesCreatedLevelEntry 2}

shapingObjectCopiesCreatedLevelMom OBJECT-TYPE
	SYNTAX	 CounterBasedGauge64
	MAX-ACCESS  read-only
	STATUS      current
	DESCRIPTION
	"Table entry attribute for shapingObjectCopiesCreated"
	::={shapingObjectCopiesCreatedLevelEntry 3}

shapingObjectCopiesCreatedLevelMax OBJECT-TYPE
	SYNTAX	 CounterBasedGauge64
	MAX-ACCESS  read-only
	STATUS      current
	DESCRIPTION
	"Table entry attribute for shapingObjectCopiesCreated"
	::={shapingObjectCopiesCreatedLevelEntry 4}


shapingEcnMarks	OBJECT IDENTIFIER ::={shaping 73}

shapingEcnMarksVal	OBJECT-TYPE
	SYNTAX	 Counter64
	MAX-ACCESS read-only
	STATUS current
	DESCRIPTION "ECN Marked Packets"

	::={shapingEcnMarks 1}

shapingEcnMarksMom	OBJECT-TYPE
	SYNTAX	 CounterBasedGauge64
	MAX-ACCESS read-only
	STATUS current
	DESCRIPTION "ECN Marked Packets"

	::={shapingEcnMarks 2}

shapingEcnMarksMax	OBJECT-TYPE
	SYNTAX	 CounterBasedGauge64
	MAX-ACCESS read-only
	STATUS current
	DESCRIPTION "ECN Marked Packets"

	::={shapingEcnMarks 3}

shapingEcnMarksLevelTable OBJECT-TYPE
	SYNTAX      SEQUENCE OF ShapingEcnMarksLevelEntry
	MAX-ACCESS  not-accessible
	STATUS      current
	DESCRIPTION
	"Table for shapingEcnMarks"
	::={shapingEcnMarks 4}

shapingEcnMarksLevelEntry OBJECT-TYPE
	SYNTAX      ShapingEcnMarksLevelEntry
	MAX-ACCESS  not-accessible
	STATUS      current
	DESCRIPTION
	"Table entry for shapingEcnMarks"
	INDEX { shapingEcnMarksLevelName }
	::={shapingEcnMarksLevelTable 1}

ShapingEcnMarksLevelEntry ::=
	SEQUENCE {
		shapingEcnMarksLevelName	DisplayString,
		shapingEcnMarksLevelVal	Counter64,
		shapingEcnMarksLevelMom	CounterBasedGauge64,
		shapingEcnMarksLevelMax	CounterBasedGauge64
	}

shapingEcnMarksLevelName OBJECT-TYPE
	SYNTAX      DisplayString
	MAX-ACCESS  not-accessible
	STATUS      current
	DESCRIPTION
	"Table entry display string for shapingEcnMarks"
	::={shapingEcnMarksLevelEntry 1}

shapingEcnMarksLevelVal OBJECT-TYPE
	SYNTAX	 Counter64
	MAX-ACCESS  read-only
	STATUS      current
	DESCRIPTION
	"Table entry attribute for shapingEcnMarks"
	::={shapingEcnMarksLevelEntry 2}

shapingEcnMarksLevelMom OBJECT-TYPE
	SYNTAX	 CounterBasedGauge64
	MAX-ACCESS  read-only
	STATUS      current
	DESCRIPTION
	"Table entry attribute for shapingEcnMarks"
	::={shapingEcnMarksLevelEntry 3}

shapingEcnMarksLevelMax OBJECT-TYPE
	SYNTAX	 CounterBasedGauge64
	MAX-ACCESS  read-only
	STATUS      current
	DESCRIPTION
	"Table entry attribute for shapingEcnMarks"
	::={shapingEcnMarksLevelEntry 4}


shapingAQMDrops	OBJECT IDENTIFIER ::={shaping 74}

shapingAQMDropsVal	OBJECT-TYPE
	SYNTAX	 Counter64
	MAX-ACCESS read-only
	STATUS current
	DESCRIPTION "AQM packet drops"

	::={shapingAQMDrops 1}

shapingAQMDropsMom	OBJECT-TYPE
	SYNTAX	 CounterBasedGauge64
	MAX-ACCESS read-only
	STATUS current
	DESCRIPTION "AQM packet drops"

	::={shapingAQMDrops 2}

shapingAQMDropsMax	OBJECT-TYPE
	SYNTAX	 CounterBasedGauge64
	MAX-ACCESS read-only
	STATUS current
	DESCRIPTION "AQM packet drops"

	::={shapingAQMDrops 3}

shapingAQMDropsLevelTable OBJECT-TYPE
	SYNTAX      SEQUENCE OF ShapingAQMDropsLevelEntry
	MAX-ACCESS  not-accessible
	STATUS      current
	DESCRIPTION
	"Table for shapingAQMDrops"
	::={shapingAQMDrops 4}

shapingAQMDropsLevelEntry OBJECT-TYPE
	SYNTAX      ShapingAQMDropsLevelEntry
	MAX-ACCESS  not-accessible
	STATUS      current
	DESCRIPTION
	"Table entry for shapingAQMDrops"
	INDEX { shapingAQMDropsLevelName }
	::={shapingAQMDropsLevelTable 1}

ShapingAQMDropsLevelEntry ::=
	SEQUENCE {
		shapingAQMDropsLevelName	DisplayString,
		shapingAQMDropsLevelVal	Counter64,
		shapingAQMDropsLevelMom	CounterBasedGauge64,
		shapingAQMDropsLevelMax	CounterBasedGauge64
	}

shapingAQMDropsLevelName OBJECT-TYPE
	SYNTAX      DisplayString
	MAX-ACCESS  not-accessible
	STATUS      current
	DESCRIPTION
	"Table entry display string for shapingAQMDrops"
	::={shapingAQMDropsLevelEntry 1}

shapingAQMDropsLevelVal OBJECT-TYPE
	SYNTAX	 Counter64
	MAX-ACCESS  read-only
	STATUS      current
	DESCRIPTION
	"Table entry attribute for shapingAQMDrops"
	::={shapingAQMDropsLevelEntry 2}

shapingAQMDropsLevelMom OBJECT-TYPE
	SYNTAX	 CounterBasedGauge64
	MAX-ACCESS  read-only
	STATUS      current
	DESCRIPTION
	"Table entry attribute for shapingAQMDrops"
	::={shapingAQMDropsLevelEntry 3}

shapingAQMDropsLevelMax OBJECT-TYPE
	SYNTAX	 CounterBasedGauge64
	MAX-ACCESS  read-only
	STATUS      current
	DESCRIPTION
	"Table entry attribute for shapingAQMDrops"
	::={shapingAQMDropsLevelEntry 4}


shapingMissedPolls	OBJECT IDENTIFIER ::={shaping 75}

shapingMissedPollsVal	OBJECT-TYPE
	SYNTAX	 Counter64
	MAX-ACCESS read-only
	STATUS current
	DESCRIPTION "Delayed Polls"

	::={shapingMissedPolls 1}

shapingMissedPollsMom	OBJECT-TYPE
	SYNTAX	 CounterBasedGauge64
	MAX-ACCESS read-only
	STATUS current
	DESCRIPTION "Delayed Polls"

	::={shapingMissedPolls 2}

shapingMissedPollsMax	OBJECT-TYPE
	SYNTAX	 CounterBasedGauge64
	MAX-ACCESS read-only
	STATUS current
	DESCRIPTION "Delayed Polls"

	::={shapingMissedPolls 3}

shapingMissedPollsLevelTable OBJECT-TYPE
	SYNTAX      SEQUENCE OF ShapingMissedPollsLevelEntry
	MAX-ACCESS  not-accessible
	STATUS      current
	DESCRIPTION
	"Table for shapingMissedPolls"
	::={shapingMissedPolls 4}

shapingMissedPollsLevelEntry OBJECT-TYPE
	SYNTAX      ShapingMissedPollsLevelEntry
	MAX-ACCESS  not-accessible
	STATUS      current
	DESCRIPTION
	"Table entry for shapingMissedPolls"
	INDEX { shapingMissedPollsLevelName }
	::={shapingMissedPollsLevelTable 1}

ShapingMissedPollsLevelEntry ::=
	SEQUENCE {
		shapingMissedPollsLevelName	DisplayString,
		shapingMissedPollsLevelVal	Counter64,
		shapingMissedPollsLevelMom	CounterBasedGauge64,
		shapingMissedPollsLevelMax	CounterBasedGauge64
	}

shapingMissedPollsLevelName OBJECT-TYPE
	SYNTAX      DisplayString
	MAX-ACCESS  not-accessible
	STATUS      current
	DESCRIPTION
	"Table entry display string for shapingMissedPolls"
	::={shapingMissedPollsLevelEntry 1}

shapingMissedPollsLevelVal OBJECT-TYPE
	SYNTAX	 Counter64
	MAX-ACCESS  read-only
	STATUS      current
	DESCRIPTION
	"Table entry attribute for shapingMissedPolls"
	::={shapingMissedPollsLevelEntry 2}

shapingMissedPollsLevelMom OBJECT-TYPE
	SYNTAX	 CounterBasedGauge64
	MAX-ACCESS  read-only
	STATUS      current
	DESCRIPTION
	"Table entry attribute for shapingMissedPolls"
	::={shapingMissedPollsLevelEntry 3}

shapingMissedPollsLevelMax OBJECT-TYPE
	SYNTAX	 CounterBasedGauge64
	MAX-ACCESS  read-only
	STATUS      current
	DESCRIPTION
	"Table entry attribute for shapingMissedPolls"
	::={shapingMissedPollsLevelEntry 4}


shapingUnresponsiveCons	OBJECT IDENTIFIER ::={shaping 76}

shapingUnresponsiveConsVal	OBJECT-TYPE
	SYNTAX	 Counter64
	MAX-ACCESS read-only
	STATUS current
	DESCRIPTION "Unresponsive Connections Detected"

	::={shapingUnresponsiveCons 1}

shapingUnresponsiveConsMom	OBJECT-TYPE
	SYNTAX	 CounterBasedGauge64
	MAX-ACCESS read-only
	STATUS current
	DESCRIPTION "Unresponsive Connections Detected"

	::={shapingUnresponsiveCons 2}

shapingUnresponsiveConsMax	OBJECT-TYPE
	SYNTAX	 CounterBasedGauge64
	MAX-ACCESS read-only
	STATUS current
	DESCRIPTION "Unresponsive Connections Detected"

	::={shapingUnresponsiveCons 3}

shapingUnresponsiveConsLevelTable OBJECT-TYPE
	SYNTAX      SEQUENCE OF ShapingUnresponsiveConsLevelEntry
	MAX-ACCESS  not-accessible
	STATUS      current
	DESCRIPTION
	"Table for shapingUnresponsiveCons"
	::={shapingUnresponsiveCons 4}

shapingUnresponsiveConsLevelEntry OBJECT-TYPE
	SYNTAX      ShapingUnresponsiveConsLevelEntry
	MAX-ACCESS  not-accessible
	STATUS      current
	DESCRIPTION
	"Table entry for shapingUnresponsiveCons"
	INDEX { shapingUnresponsiveConsLevelName }
	::={shapingUnresponsiveConsLevelTable 1}

ShapingUnresponsiveConsLevelEntry ::=
	SEQUENCE {
		shapingUnresponsiveConsLevelName	DisplayString,
		shapingUnresponsiveConsLevelVal	Counter64,
		shapingUnresponsiveConsLevelMom	CounterBasedGauge64,
		shapingUnresponsiveConsLevelMax	CounterBasedGauge64
	}

shapingUnresponsiveConsLevelName OBJECT-TYPE
	SYNTAX      DisplayString
	MAX-ACCESS  not-accessible
	STATUS      current
	DESCRIPTION
	"Table entry display string for shapingUnresponsiveCons"
	::={shapingUnresponsiveConsLevelEntry 1}

shapingUnresponsiveConsLevelVal OBJECT-TYPE
	SYNTAX	 Counter64
	MAX-ACCESS  read-only
	STATUS      current
	DESCRIPTION
	"Table entry attribute for shapingUnresponsiveCons"
	::={shapingUnresponsiveConsLevelEntry 2}

shapingUnresponsiveConsLevelMom OBJECT-TYPE
	SYNTAX	 CounterBasedGauge64
	MAX-ACCESS  read-only
	STATUS      current
	DESCRIPTION
	"Table entry attribute for shapingUnresponsiveCons"
	::={shapingUnresponsiveConsLevelEntry 3}

shapingUnresponsiveConsLevelMax OBJECT-TYPE
	SYNTAX	 CounterBasedGauge64
	MAX-ACCESS  read-only
	STATUS      current
	DESCRIPTION
	"Table entry attribute for shapingUnresponsiveCons"
	::={shapingUnresponsiveConsLevelEntry 4}


shapingEnqueueFails	OBJECT IDENTIFIER ::={shaping 77}

shapingEnqueueFailsVal	OBJECT-TYPE
	SYNTAX	 Counter64
	MAX-ACCESS read-only
	STATUS current
	DESCRIPTION "Enqueue Failures"

	::={shapingEnqueueFails 1}

shapingEnqueueFailsMom	OBJECT-TYPE
	SYNTAX	 CounterBasedGauge64
	MAX-ACCESS read-only
	STATUS current
	DESCRIPTION "Enqueue Failures"

	::={shapingEnqueueFails 2}

shapingEnqueueFailsMax	OBJECT-TYPE
	SYNTAX	 CounterBasedGauge64
	MAX-ACCESS read-only
	STATUS current
	DESCRIPTION "Enqueue Failures"

	::={shapingEnqueueFails 3}

shapingEnqueueFailsLevelTable OBJECT-TYPE
	SYNTAX      SEQUENCE OF ShapingEnqueueFailsLevelEntry
	MAX-ACCESS  not-accessible
	STATUS      current
	DESCRIPTION
	"Table for shapingEnqueueFails"
	::={shapingEnqueueFails 4}

shapingEnqueueFailsLevelEntry OBJECT-TYPE
	SYNTAX      ShapingEnqueueFailsLevelEntry
	MAX-ACCESS  not-accessible
	STATUS      current
	DESCRIPTION
	"Table entry for shapingEnqueueFails"
	INDEX { shapingEnqueueFailsLevelName }
	::={shapingEnqueueFailsLevelTable 1}

ShapingEnqueueFailsLevelEntry ::=
	SEQUENCE {
		shapingEnqueueFailsLevelName	DisplayString,
		shapingEnqueueFailsLevelVal	Counter64,
		shapingEnqueueFailsLevelMom	CounterBasedGauge64,
		shapingEnqueueFailsLevelMax	CounterBasedGauge64
	}

shapingEnqueueFailsLevelName OBJECT-TYPE
	SYNTAX      DisplayString
	MAX-ACCESS  not-accessible
	STATUS      current
	DESCRIPTION
	"Table entry display string for shapingEnqueueFails"
	::={shapingEnqueueFailsLevelEntry 1}

shapingEnqueueFailsLevelVal OBJECT-TYPE
	SYNTAX	 Counter64
	MAX-ACCESS  read-only
	STATUS      current
	DESCRIPTION
	"Table entry attribute for shapingEnqueueFails"
	::={shapingEnqueueFailsLevelEntry 2}

shapingEnqueueFailsLevelMom OBJECT-TYPE
	SYNTAX	 CounterBasedGauge64
	MAX-ACCESS  read-only
	STATUS      current
	DESCRIPTION
	"Table entry attribute for shapingEnqueueFails"
	::={shapingEnqueueFailsLevelEntry 3}

shapingEnqueueFailsLevelMax OBJECT-TYPE
	SYNTAX	 CounterBasedGauge64
	MAX-ACCESS  read-only
	STATUS      current
	DESCRIPTION
	"Table entry attribute for shapingEnqueueFails"
	::={shapingEnqueueFailsLevelEntry 4}


shapingSessionContextSpeedNoValue	OBJECT IDENTIFIER ::={shaping 78}

shapingSessionContextSpeedNoValueVal	OBJECT-TYPE
	SYNTAX	 Counter64
	MAX-ACCESS read-only
	STATUS current
	DESCRIPTION "Failures to set speed from session context value - not provisioned"

	::={shapingSessionContextSpeedNoValue 1}

shapingSessionContextSpeedNoValueMom	OBJECT-TYPE
	SYNTAX	 CounterBasedGauge64
	MAX-ACCESS read-only
	STATUS current
	DESCRIPTION "Failures to set speed from session context value - not provisioned"

	::={shapingSessionContextSpeedNoValue 2}

shapingSessionContextSpeedNoValueMax	OBJECT-TYPE
	SYNTAX	 CounterBasedGauge64
	MAX-ACCESS read-only
	STATUS current
	DESCRIPTION "Failures to set speed from session context value - not provisioned"

	::={shapingSessionContextSpeedNoValue 3}

shapingSessionContextSpeedNoValueLevelTable OBJECT-TYPE
	SYNTAX      SEQUENCE OF ShapingSessionContextSpeedNoValueLevelEntry
	MAX-ACCESS  not-accessible
	STATUS      current
	DESCRIPTION
	"Table for shapingSessionContextSpeedNoValue"
	::={shapingSessionContextSpeedNoValue 4}

shapingSessionContextSpeedNoValueLevelEntry OBJECT-TYPE
	SYNTAX      ShapingSessionContextSpeedNoValueLevelEntry
	MAX-ACCESS  not-accessible
	STATUS      current
	DESCRIPTION
	"Table entry for shapingSessionContextSpeedNoValue"
	INDEX { shapingSessionContextSpeedNoValueLevelName }
	::={shapingSessionContextSpeedNoValueLevelTable 1}

ShapingSessionContextSpeedNoValueLevelEntry ::=
	SEQUENCE {
		shapingSessionContextSpeedNoValueLevelName	DisplayString,
		shapingSessionContextSpeedNoValueLevelVal	Counter64,
		shapingSessionContextSpeedNoValueLevelMom	CounterBasedGauge64,
		shapingSessionContextSpeedNoValueLevelMax	CounterBasedGauge64
	}

shapingSessionContextSpeedNoValueLevelName OBJECT-TYPE
	SYNTAX      DisplayString
	MAX-ACCESS  not-accessible
	STATUS      current
	DESCRIPTION
	"Table entry display string for shapingSessionContextSpeedNoValue"
	::={shapingSessionContextSpeedNoValueLevelEntry 1}

shapingSessionContextSpeedNoValueLevelVal OBJECT-TYPE
	SYNTAX	 Counter64
	MAX-ACCESS  read-only
	STATUS      current
	DESCRIPTION
	"Table entry attribute for shapingSessionContextSpeedNoValue"
	::={shapingSessionContextSpeedNoValueLevelEntry 2}

shapingSessionContextSpeedNoValueLevelMom OBJECT-TYPE
	SYNTAX	 CounterBasedGauge64
	MAX-ACCESS  read-only
	STATUS      current
	DESCRIPTION
	"Table entry attribute for shapingSessionContextSpeedNoValue"
	::={shapingSessionContextSpeedNoValueLevelEntry 3}

shapingSessionContextSpeedNoValueLevelMax OBJECT-TYPE
	SYNTAX	 CounterBasedGauge64
	MAX-ACCESS  read-only
	STATUS      current
	DESCRIPTION
	"Table entry attribute for shapingSessionContextSpeedNoValue"
	::={shapingSessionContextSpeedNoValueLevelEntry 4}


shapingSessionContextSpeedInvalidType	OBJECT IDENTIFIER ::={shaping 79}

shapingSessionContextSpeedInvalidTypeVal	OBJECT-TYPE
	SYNTAX	 Counter64
	MAX-ACCESS read-only
	STATUS current
	DESCRIPTION "Failures to set speed from session context value - non-numeric type"

	::={shapingSessionContextSpeedInvalidType 1}

shapingSessionContextSpeedInvalidTypeMom	OBJECT-TYPE
	SYNTAX	 CounterBasedGauge64
	MAX-ACCESS read-only
	STATUS current
	DESCRIPTION "Failures to set speed from session context value - non-numeric type"

	::={shapingSessionContextSpeedInvalidType 2}

shapingSessionContextSpeedInvalidTypeMax	OBJECT-TYPE
	SYNTAX	 CounterBasedGauge64
	MAX-ACCESS read-only
	STATUS current
	DESCRIPTION "Failures to set speed from session context value - non-numeric type"

	::={shapingSessionContextSpeedInvalidType 3}

shapingSessionContextSpeedInvalidTypeLevelTable OBJECT-TYPE
	SYNTAX      SEQUENCE OF ShapingSessionContextSpeedInvalidTypeLevelEntry
	MAX-ACCESS  not-accessible
	STATUS      current
	DESCRIPTION
	"Table for shapingSessionContextSpeedInvalidType"
	::={shapingSessionContextSpeedInvalidType 4}

shapingSessionContextSpeedInvalidTypeLevelEntry OBJECT-TYPE
	SYNTAX      ShapingSessionContextSpeedInvalidTypeLevelEntry
	MAX-ACCESS  not-accessible
	STATUS      current
	DESCRIPTION
	"Table entry for shapingSessionContextSpeedInvalidType"
	INDEX { shapingSessionContextSpeedInvalidTypeLevelName }
	::={shapingSessionContextSpeedInvalidTypeLevelTable 1}

ShapingSessionContextSpeedInvalidTypeLevelEntry ::=
	SEQUENCE {
		shapingSessionContextSpeedInvalidTypeLevelName	DisplayString,
		shapingSessionContextSpeedInvalidTypeLevelVal	Counter64,
		shapingSessionContextSpeedInvalidTypeLevelMom	CounterBasedGauge64,
		shapingSessionContextSpeedInvalidTypeLevelMax	CounterBasedGauge64
	}

shapingSessionContextSpeedInvalidTypeLevelName OBJECT-TYPE
	SYNTAX      DisplayString
	MAX-ACCESS  not-accessible
	STATUS      current
	DESCRIPTION
	"Table entry display string for shapingSessionContextSpeedInvalidType"
	::={shapingSessionContextSpeedInvalidTypeLevelEntry 1}

shapingSessionContextSpeedInvalidTypeLevelVal OBJECT-TYPE
	SYNTAX	 Counter64
	MAX-ACCESS  read-only
	STATUS      current
	DESCRIPTION
	"Table entry attribute for shapingSessionContextSpeedInvalidType"
	::={shapingSessionContextSpeedInvalidTypeLevelEntry 2}

shapingSessionContextSpeedInvalidTypeLevelMom OBJECT-TYPE
	SYNTAX	 CounterBasedGauge64
	MAX-ACCESS  read-only
	STATUS      current
	DESCRIPTION
	"Table entry attribute for shapingSessionContextSpeedInvalidType"
	::={shapingSessionContextSpeedInvalidTypeLevelEntry 3}

shapingSessionContextSpeedInvalidTypeLevelMax OBJECT-TYPE
	SYNTAX	 CounterBasedGauge64
	MAX-ACCESS  read-only
	STATUS      current
	DESCRIPTION
	"Table entry attribute for shapingSessionContextSpeedInvalidType"
	::={shapingSessionContextSpeedInvalidTypeLevelEntry 4}


shapingSessionContextSpeedTooLow	OBJECT IDENTIFIER ::={shaping 80}

shapingSessionContextSpeedTooLowVal	OBJECT-TYPE
	SYNTAX	 Counter64
	MAX-ACCESS read-only
	STATUS current
	DESCRIPTION "Failures to set speed from session context value - too low speed"

	::={shapingSessionContextSpeedTooLow 1}

shapingSessionContextSpeedTooLowMom	OBJECT-TYPE
	SYNTAX	 CounterBasedGauge64
	MAX-ACCESS read-only
	STATUS current
	DESCRIPTION "Failures to set speed from session context value - too low speed"

	::={shapingSessionContextSpeedTooLow 2}

shapingSessionContextSpeedTooLowMax	OBJECT-TYPE
	SYNTAX	 CounterBasedGauge64
	MAX-ACCESS read-only
	STATUS current
	DESCRIPTION "Failures to set speed from session context value - too low speed"

	::={shapingSessionContextSpeedTooLow 3}

shapingSessionContextSpeedTooLowLevelTable OBJECT-TYPE
	SYNTAX      SEQUENCE OF ShapingSessionContextSpeedTooLowLevelEntry
	MAX-ACCESS  not-accessible
	STATUS      current
	DESCRIPTION
	"Table for shapingSessionContextSpeedTooLow"
	::={shapingSessionContextSpeedTooLow 4}

shapingSessionContextSpeedTooLowLevelEntry OBJECT-TYPE
	SYNTAX      ShapingSessionContextSpeedTooLowLevelEntry
	MAX-ACCESS  not-accessible
	STATUS      current
	DESCRIPTION
	"Table entry for shapingSessionContextSpeedTooLow"
	INDEX { shapingSessionContextSpeedTooLowLevelName }
	::={shapingSessionContextSpeedTooLowLevelTable 1}

ShapingSessionContextSpeedTooLowLevelEntry ::=
	SEQUENCE {
		shapingSessionContextSpeedTooLowLevelName	DisplayString,
		shapingSessionContextSpeedTooLowLevelVal	Counter64,
		shapingSessionContextSpeedTooLowLevelMom	CounterBasedGauge64,
		shapingSessionContextSpeedTooLowLevelMax	CounterBasedGauge64
	}

shapingSessionContextSpeedTooLowLevelName OBJECT-TYPE
	SYNTAX      DisplayString
	MAX-ACCESS  not-accessible
	STATUS      current
	DESCRIPTION
	"Table entry display string for shapingSessionContextSpeedTooLow"
	::={shapingSessionContextSpeedTooLowLevelEntry 1}

shapingSessionContextSpeedTooLowLevelVal OBJECT-TYPE
	SYNTAX	 Counter64
	MAX-ACCESS  read-only
	STATUS      current
	DESCRIPTION
	"Table entry attribute for shapingSessionContextSpeedTooLow"
	::={shapingSessionContextSpeedTooLowLevelEntry 2}

shapingSessionContextSpeedTooLowLevelMom OBJECT-TYPE
	SYNTAX	 CounterBasedGauge64
	MAX-ACCESS  read-only
	STATUS      current
	DESCRIPTION
	"Table entry attribute for shapingSessionContextSpeedTooLow"
	::={shapingSessionContextSpeedTooLowLevelEntry 3}

shapingSessionContextSpeedTooLowLevelMax OBJECT-TYPE
	SYNTAX	 CounterBasedGauge64
	MAX-ACCESS  read-only
	STATUS      current
	DESCRIPTION
	"Table entry attribute for shapingSessionContextSpeedTooLow"
	::={shapingSessionContextSpeedTooLowLevelEntry 4}


shapingObjectsInSplitObjectsFifo	OBJECT IDENTIFIER ::={shaping 81}

shapingObjectsInSplitObjectsFifoVal	OBJECT-TYPE
	SYNTAX	 Counter64
	MAX-ACCESS read-only
	STATUS current
	DESCRIPTION "Objects processed in splitobjects timer func"

	::={shapingObjectsInSplitObjectsFifo 1}

shapingObjectsInSplitObjectsFifoMom	OBJECT-TYPE
	SYNTAX	 CounterBasedGauge64
	MAX-ACCESS read-only
	STATUS current
	DESCRIPTION "Objects processed in splitobjects timer func"

	::={shapingObjectsInSplitObjectsFifo 2}

shapingObjectsInSplitObjectsFifoMax	OBJECT-TYPE
	SYNTAX	 CounterBasedGauge64
	MAX-ACCESS read-only
	STATUS current
	DESCRIPTION "Objects processed in splitobjects timer func"

	::={shapingObjectsInSplitObjectsFifo 3}

shapingObjectsInSplitObjectsFifoLevelTable OBJECT-TYPE
	SYNTAX      SEQUENCE OF ShapingObjectsInSplitObjectsFifoLevelEntry
	MAX-ACCESS  not-accessible
	STATUS      current
	DESCRIPTION
	"Table for shapingObjectsInSplitObjectsFifo"
	::={shapingObjectsInSplitObjectsFifo 4}

shapingObjectsInSplitObjectsFifoLevelEntry OBJECT-TYPE
	SYNTAX      ShapingObjectsInSplitObjectsFifoLevelEntry
	MAX-ACCESS  not-accessible
	STATUS      current
	DESCRIPTION
	"Table entry for shapingObjectsInSplitObjectsFifo"
	INDEX { shapingObjectsInSplitObjectsFifoLevelName }
	::={shapingObjectsInSplitObjectsFifoLevelTable 1}

ShapingObjectsInSplitObjectsFifoLevelEntry ::=
	SEQUENCE {
		shapingObjectsInSplitObjectsFifoLevelName	DisplayString,
		shapingObjectsInSplitObjectsFifoLevelVal	Counter64,
		shapingObjectsInSplitObjectsFifoLevelMom	CounterBasedGauge64,
		shapingObjectsInSplitObjectsFifoLevelMax	CounterBasedGauge64
	}

shapingObjectsInSplitObjectsFifoLevelName OBJECT-TYPE
	SYNTAX      DisplayString
	MAX-ACCESS  not-accessible
	STATUS      current
	DESCRIPTION
	"Table entry display string for shapingObjectsInSplitObjectsFifo"
	::={shapingObjectsInSplitObjectsFifoLevelEntry 1}

shapingObjectsInSplitObjectsFifoLevelVal OBJECT-TYPE
	SYNTAX	 Counter64
	MAX-ACCESS  read-only
	STATUS      current
	DESCRIPTION
	"Table entry attribute for shapingObjectsInSplitObjectsFifo"
	::={shapingObjectsInSplitObjectsFifoLevelEntry 2}

shapingObjectsInSplitObjectsFifoLevelMom OBJECT-TYPE
	SYNTAX	 CounterBasedGauge64
	MAX-ACCESS  read-only
	STATUS      current
	DESCRIPTION
	"Table entry attribute for shapingObjectsInSplitObjectsFifo"
	::={shapingObjectsInSplitObjectsFifoLevelEntry 3}

shapingObjectsInSplitObjectsFifoLevelMax OBJECT-TYPE
	SYNTAX	 CounterBasedGauge64
	MAX-ACCESS  read-only
	STATUS      current
	DESCRIPTION
	"Table entry attribute for shapingObjectsInSplitObjectsFifo"
	::={shapingObjectsInSplitObjectsFifoLevelEntry 4}


shapingEnqueueCpu0	OBJECT IDENTIFIER ::={shaping 82}

shapingEnqueueCpu0Val	OBJECT-TYPE
	SYNTAX	 Counter64
	MAX-ACCESS read-only
	STATUS current
	DESCRIPTION "Enqueue attemps on CPU0"

	::={shapingEnqueueCpu0 1}

shapingEnqueueCpu0Mom	OBJECT-TYPE
	SYNTAX	 CounterBasedGauge64
	MAX-ACCESS read-only
	STATUS current
	DESCRIPTION "Enqueue attemps on CPU0"

	::={shapingEnqueueCpu0 2}

shapingEnqueueCpu0Max	OBJECT-TYPE
	SYNTAX	 CounterBasedGauge64
	MAX-ACCESS read-only
	STATUS current
	DESCRIPTION "Enqueue attemps on CPU0"

	::={shapingEnqueueCpu0 3}

shapingEnqueueCpu0LevelTable OBJECT-TYPE
	SYNTAX      SEQUENCE OF ShapingEnqueueCpu0LevelEntry
	MAX-ACCESS  not-accessible
	STATUS      current
	DESCRIPTION
	"Table for shapingEnqueueCpu0"
	::={shapingEnqueueCpu0 4}

shapingEnqueueCpu0LevelEntry OBJECT-TYPE
	SYNTAX      ShapingEnqueueCpu0LevelEntry
	MAX-ACCESS  not-accessible
	STATUS      current
	DESCRIPTION
	"Table entry for shapingEnqueueCpu0"
	INDEX { shapingEnqueueCpu0LevelName }
	::={shapingEnqueueCpu0LevelTable 1}

ShapingEnqueueCpu0LevelEntry ::=
	SEQUENCE {
		shapingEnqueueCpu0LevelName	DisplayString,
		shapingEnqueueCpu0LevelVal	Counter64,
		shapingEnqueueCpu0LevelMom	CounterBasedGauge64,
		shapingEnqueueCpu0LevelMax	CounterBasedGauge64
	}

shapingEnqueueCpu0LevelName OBJECT-TYPE
	SYNTAX      DisplayString
	MAX-ACCESS  not-accessible
	STATUS      current
	DESCRIPTION
	"Table entry display string for shapingEnqueueCpu0"
	::={shapingEnqueueCpu0LevelEntry 1}

shapingEnqueueCpu0LevelVal OBJECT-TYPE
	SYNTAX	 Counter64
	MAX-ACCESS  read-only
	STATUS      current
	DESCRIPTION
	"Table entry attribute for shapingEnqueueCpu0"
	::={shapingEnqueueCpu0LevelEntry 2}

shapingEnqueueCpu0LevelMom OBJECT-TYPE
	SYNTAX	 CounterBasedGauge64
	MAX-ACCESS  read-only
	STATUS      current
	DESCRIPTION
	"Table entry attribute for shapingEnqueueCpu0"
	::={shapingEnqueueCpu0LevelEntry 3}

shapingEnqueueCpu0LevelMax OBJECT-TYPE
	SYNTAX	 CounterBasedGauge64
	MAX-ACCESS  read-only
	STATUS      current
	DESCRIPTION
	"Table entry attribute for shapingEnqueueCpu0"
	::={shapingEnqueueCpu0LevelEntry 4}


pppoe	OBJECT IDENTIFIER ::={sysdiag 96}

pppoeShortPackets	OBJECT IDENTIFIER ::={pppoe 1}

pppoeShortPacketsVal	OBJECT-TYPE
	SYNTAX	 Counter64
	MAX-ACCESS read-only
	STATUS current
	DESCRIPTION "Short Packets dropped"

	::={pppoeShortPackets 1}

pppoeShortPacketsMom	OBJECT-TYPE
	SYNTAX	 CounterBasedGauge64
	MAX-ACCESS read-only
	STATUS current
	DESCRIPTION "Short Packets dropped"

	::={pppoeShortPackets 2}

pppoeShortPacketsMax	OBJECT-TYPE
	SYNTAX	 CounterBasedGauge64
	MAX-ACCESS read-only
	STATUS current
	DESCRIPTION "Short Packets dropped"

	::={pppoeShortPackets 3}

pppoeShortPacketsLevelTable OBJECT-TYPE
	SYNTAX      SEQUENCE OF PppoeShortPacketsLevelEntry
	MAX-ACCESS  not-accessible
	STATUS      current
	DESCRIPTION
	"Table for pppoeShortPackets"
	::={pppoeShortPackets 4}

pppoeShortPacketsLevelEntry OBJECT-TYPE
	SYNTAX      PppoeShortPacketsLevelEntry
	MAX-ACCESS  not-accessible
	STATUS      current
	DESCRIPTION
	"Table entry for pppoeShortPackets"
	INDEX { pppoeShortPacketsLevelName }
	::={pppoeShortPacketsLevelTable 1}

PppoeShortPacketsLevelEntry ::=
	SEQUENCE {
		pppoeShortPacketsLevelName	DisplayString,
		pppoeShortPacketsLevelVal	Counter64,
		pppoeShortPacketsLevelMom	CounterBasedGauge64,
		pppoeShortPacketsLevelMax	CounterBasedGauge64
	}

pppoeShortPacketsLevelName OBJECT-TYPE
	SYNTAX      DisplayString
	MAX-ACCESS  not-accessible
	STATUS      current
	DESCRIPTION
	"Table entry display string for pppoeShortPackets"
	::={pppoeShortPacketsLevelEntry 1}

pppoeShortPacketsLevelVal OBJECT-TYPE
	SYNTAX	 Counter64
	MAX-ACCESS  read-only
	STATUS      current
	DESCRIPTION
	"Table entry attribute for pppoeShortPackets"
	::={pppoeShortPacketsLevelEntry 2}

pppoeShortPacketsLevelMom OBJECT-TYPE
	SYNTAX	 CounterBasedGauge64
	MAX-ACCESS  read-only
	STATUS      current
	DESCRIPTION
	"Table entry attribute for pppoeShortPackets"
	::={pppoeShortPacketsLevelEntry 3}

pppoeShortPacketsLevelMax OBJECT-TYPE
	SYNTAX	 CounterBasedGauge64
	MAX-ACCESS  read-only
	STATUS      current
	DESCRIPTION
	"Table entry attribute for pppoeShortPackets"
	::={pppoeShortPacketsLevelEntry 4}


pppoeBadversionPackets	OBJECT IDENTIFIER ::={pppoe 2}

pppoeBadversionPacketsVal	OBJECT-TYPE
	SYNTAX	 Counter64
	MAX-ACCESS read-only
	STATUS current
	DESCRIPTION "Packets with unknown version"

	::={pppoeBadversionPackets 1}

pppoeBadversionPacketsMom	OBJECT-TYPE
	SYNTAX	 CounterBasedGauge64
	MAX-ACCESS read-only
	STATUS current
	DESCRIPTION "Packets with unknown version"

	::={pppoeBadversionPackets 2}

pppoeBadversionPacketsMax	OBJECT-TYPE
	SYNTAX	 CounterBasedGauge64
	MAX-ACCESS read-only
	STATUS current
	DESCRIPTION "Packets with unknown version"

	::={pppoeBadversionPackets 3}

pppoeBadversionPacketsLevelTable OBJECT-TYPE
	SYNTAX      SEQUENCE OF PppoeBadversionPacketsLevelEntry
	MAX-ACCESS  not-accessible
	STATUS      current
	DESCRIPTION
	"Table for pppoeBadversionPackets"
	::={pppoeBadversionPackets 4}

pppoeBadversionPacketsLevelEntry OBJECT-TYPE
	SYNTAX      PppoeBadversionPacketsLevelEntry
	MAX-ACCESS  not-accessible
	STATUS      current
	DESCRIPTION
	"Table entry for pppoeBadversionPackets"
	INDEX { pppoeBadversionPacketsLevelName }
	::={pppoeBadversionPacketsLevelTable 1}

PppoeBadversionPacketsLevelEntry ::=
	SEQUENCE {
		pppoeBadversionPacketsLevelName	DisplayString,
		pppoeBadversionPacketsLevelVal	Counter64,
		pppoeBadversionPacketsLevelMom	CounterBasedGauge64,
		pppoeBadversionPacketsLevelMax	CounterBasedGauge64
	}

pppoeBadversionPacketsLevelName OBJECT-TYPE
	SYNTAX      DisplayString
	MAX-ACCESS  not-accessible
	STATUS      current
	DESCRIPTION
	"Table entry display string for pppoeBadversionPackets"
	::={pppoeBadversionPacketsLevelEntry 1}

pppoeBadversionPacketsLevelVal OBJECT-TYPE
	SYNTAX	 Counter64
	MAX-ACCESS  read-only
	STATUS      current
	DESCRIPTION
	"Table entry attribute for pppoeBadversionPackets"
	::={pppoeBadversionPacketsLevelEntry 2}

pppoeBadversionPacketsLevelMom OBJECT-TYPE
	SYNTAX	 CounterBasedGauge64
	MAX-ACCESS  read-only
	STATUS      current
	DESCRIPTION
	"Table entry attribute for pppoeBadversionPackets"
	::={pppoeBadversionPacketsLevelEntry 3}

pppoeBadversionPacketsLevelMax OBJECT-TYPE
	SYNTAX	 CounterBasedGauge64
	MAX-ACCESS  read-only
	STATUS      current
	DESCRIPTION
	"Table entry attribute for pppoeBadversionPackets"
	::={pppoeBadversionPacketsLevelEntry 4}


pppoeControlPackets	OBJECT IDENTIFIER ::={pppoe 3}

pppoeControlPacketsVal	OBJECT-TYPE
	SYNTAX	 Counter64
	MAX-ACCESS read-only
	STATUS current
	DESCRIPTION "Control packets"

	::={pppoeControlPackets 1}

pppoeControlPacketsMom	OBJECT-TYPE
	SYNTAX	 CounterBasedGauge64
	MAX-ACCESS read-only
	STATUS current
	DESCRIPTION "Control packets"

	::={pppoeControlPackets 2}

pppoeControlPacketsMax	OBJECT-TYPE
	SYNTAX	 CounterBasedGauge64
	MAX-ACCESS read-only
	STATUS current
	DESCRIPTION "Control packets"

	::={pppoeControlPackets 3}

pppoeControlPacketsLevelTable OBJECT-TYPE
	SYNTAX      SEQUENCE OF PppoeControlPacketsLevelEntry
	MAX-ACCESS  not-accessible
	STATUS      current
	DESCRIPTION
	"Table for pppoeControlPackets"
	::={pppoeControlPackets 4}

pppoeControlPacketsLevelEntry OBJECT-TYPE
	SYNTAX      PppoeControlPacketsLevelEntry
	MAX-ACCESS  not-accessible
	STATUS      current
	DESCRIPTION
	"Table entry for pppoeControlPackets"
	INDEX { pppoeControlPacketsLevelName }
	::={pppoeControlPacketsLevelTable 1}

PppoeControlPacketsLevelEntry ::=
	SEQUENCE {
		pppoeControlPacketsLevelName	DisplayString,
		pppoeControlPacketsLevelVal	Counter64,
		pppoeControlPacketsLevelMom	CounterBasedGauge64,
		pppoeControlPacketsLevelMax	CounterBasedGauge64
	}

pppoeControlPacketsLevelName OBJECT-TYPE
	SYNTAX      DisplayString
	MAX-ACCESS  not-accessible
	STATUS      current
	DESCRIPTION
	"Table entry display string for pppoeControlPackets"
	::={pppoeControlPacketsLevelEntry 1}

pppoeControlPacketsLevelVal OBJECT-TYPE
	SYNTAX	 Counter64
	MAX-ACCESS  read-only
	STATUS      current
	DESCRIPTION
	"Table entry attribute for pppoeControlPackets"
	::={pppoeControlPacketsLevelEntry 2}

pppoeControlPacketsLevelMom OBJECT-TYPE
	SYNTAX	 CounterBasedGauge64
	MAX-ACCESS  read-only
	STATUS      current
	DESCRIPTION
	"Table entry attribute for pppoeControlPackets"
	::={pppoeControlPacketsLevelEntry 3}

pppoeControlPacketsLevelMax OBJECT-TYPE
	SYNTAX	 CounterBasedGauge64
	MAX-ACCESS  read-only
	STATUS      current
	DESCRIPTION
	"Table entry attribute for pppoeControlPackets"
	::={pppoeControlPacketsLevelEntry 4}


pppoeTruncatedPackets	OBJECT IDENTIFIER ::={pppoe 4}

pppoeTruncatedPacketsVal	OBJECT-TYPE
	SYNTAX	 Counter64
	MAX-ACCESS read-only
	STATUS current
	DESCRIPTION "Truncated packets dropped"

	::={pppoeTruncatedPackets 1}

pppoeTruncatedPacketsMom	OBJECT-TYPE
	SYNTAX	 CounterBasedGauge64
	MAX-ACCESS read-only
	STATUS current
	DESCRIPTION "Truncated packets dropped"

	::={pppoeTruncatedPackets 2}

pppoeTruncatedPacketsMax	OBJECT-TYPE
	SYNTAX	 CounterBasedGauge64
	MAX-ACCESS read-only
	STATUS current
	DESCRIPTION "Truncated packets dropped"

	::={pppoeTruncatedPackets 3}

pppoeTruncatedPacketsLevelTable OBJECT-TYPE
	SYNTAX      SEQUENCE OF PppoeTruncatedPacketsLevelEntry
	MAX-ACCESS  not-accessible
	STATUS      current
	DESCRIPTION
	"Table for pppoeTruncatedPackets"
	::={pppoeTruncatedPackets 4}

pppoeTruncatedPacketsLevelEntry OBJECT-TYPE
	SYNTAX      PppoeTruncatedPacketsLevelEntry
	MAX-ACCESS  not-accessible
	STATUS      current
	DESCRIPTION
	"Table entry for pppoeTruncatedPackets"
	INDEX { pppoeTruncatedPacketsLevelName }
	::={pppoeTruncatedPacketsLevelTable 1}

PppoeTruncatedPacketsLevelEntry ::=
	SEQUENCE {
		pppoeTruncatedPacketsLevelName	DisplayString,
		pppoeTruncatedPacketsLevelVal	Counter64,
		pppoeTruncatedPacketsLevelMom	CounterBasedGauge64,
		pppoeTruncatedPacketsLevelMax	CounterBasedGauge64
	}

pppoeTruncatedPacketsLevelName OBJECT-TYPE
	SYNTAX      DisplayString
	MAX-ACCESS  not-accessible
	STATUS      current
	DESCRIPTION
	"Table entry display string for pppoeTruncatedPackets"
	::={pppoeTruncatedPacketsLevelEntry 1}

pppoeTruncatedPacketsLevelVal OBJECT-TYPE
	SYNTAX	 Counter64
	MAX-ACCESS  read-only
	STATUS      current
	DESCRIPTION
	"Table entry attribute for pppoeTruncatedPackets"
	::={pppoeTruncatedPacketsLevelEntry 2}

pppoeTruncatedPacketsLevelMom OBJECT-TYPE
	SYNTAX	 CounterBasedGauge64
	MAX-ACCESS  read-only
	STATUS      current
	DESCRIPTION
	"Table entry attribute for pppoeTruncatedPackets"
	::={pppoeTruncatedPacketsLevelEntry 3}

pppoeTruncatedPacketsLevelMax OBJECT-TYPE
	SYNTAX	 CounterBasedGauge64
	MAX-ACCESS  read-only
	STATUS      current
	DESCRIPTION
	"Table entry attribute for pppoeTruncatedPackets"
	::={pppoeTruncatedPacketsLevelEntry 4}


pppoePaddedPackets	OBJECT IDENTIFIER ::={pppoe 5}

pppoePaddedPacketsVal	OBJECT-TYPE
	SYNTAX	 Counter64
	MAX-ACCESS read-only
	STATUS current
	DESCRIPTION "Padded packets"

	::={pppoePaddedPackets 1}

pppoePaddedPacketsMom	OBJECT-TYPE
	SYNTAX	 CounterBasedGauge64
	MAX-ACCESS read-only
	STATUS current
	DESCRIPTION "Padded packets"

	::={pppoePaddedPackets 2}

pppoePaddedPacketsMax	OBJECT-TYPE
	SYNTAX	 CounterBasedGauge64
	MAX-ACCESS read-only
	STATUS current
	DESCRIPTION "Padded packets"

	::={pppoePaddedPackets 3}

pppoePaddedPacketsLevelTable OBJECT-TYPE
	SYNTAX      SEQUENCE OF PppoePaddedPacketsLevelEntry
	MAX-ACCESS  not-accessible
	STATUS      current
	DESCRIPTION
	"Table for pppoePaddedPackets"
	::={pppoePaddedPackets 4}

pppoePaddedPacketsLevelEntry OBJECT-TYPE
	SYNTAX      PppoePaddedPacketsLevelEntry
	MAX-ACCESS  not-accessible
	STATUS      current
	DESCRIPTION
	"Table entry for pppoePaddedPackets"
	INDEX { pppoePaddedPacketsLevelName }
	::={pppoePaddedPacketsLevelTable 1}

PppoePaddedPacketsLevelEntry ::=
	SEQUENCE {
		pppoePaddedPacketsLevelName	DisplayString,
		pppoePaddedPacketsLevelVal	Counter64,
		pppoePaddedPacketsLevelMom	CounterBasedGauge64,
		pppoePaddedPacketsLevelMax	CounterBasedGauge64
	}

pppoePaddedPacketsLevelName OBJECT-TYPE
	SYNTAX      DisplayString
	MAX-ACCESS  not-accessible
	STATUS      current
	DESCRIPTION
	"Table entry display string for pppoePaddedPackets"
	::={pppoePaddedPacketsLevelEntry 1}

pppoePaddedPacketsLevelVal OBJECT-TYPE
	SYNTAX	 Counter64
	MAX-ACCESS  read-only
	STATUS      current
	DESCRIPTION
	"Table entry attribute for pppoePaddedPackets"
	::={pppoePaddedPacketsLevelEntry 2}

pppoePaddedPacketsLevelMom OBJECT-TYPE
	SYNTAX	 CounterBasedGauge64
	MAX-ACCESS  read-only
	STATUS      current
	DESCRIPTION
	"Table entry attribute for pppoePaddedPackets"
	::={pppoePaddedPacketsLevelEntry 3}

pppoePaddedPacketsLevelMax OBJECT-TYPE
	SYNTAX	 CounterBasedGauge64
	MAX-ACCESS  read-only
	STATUS      current
	DESCRIPTION
	"Table entry attribute for pppoePaddedPackets"
	::={pppoePaddedPacketsLevelEntry 4}


pppoeIpv4Packets	OBJECT IDENTIFIER ::={pppoe 6}

pppoeIpv4PacketsVal	OBJECT-TYPE
	SYNTAX	 Counter64
	MAX-ACCESS read-only
	STATUS current
	DESCRIPTION "IPv4 packets"

	::={pppoeIpv4Packets 1}

pppoeIpv4PacketsMom	OBJECT-TYPE
	SYNTAX	 CounterBasedGauge64
	MAX-ACCESS read-only
	STATUS current
	DESCRIPTION "IPv4 packets"

	::={pppoeIpv4Packets 2}

pppoeIpv4PacketsMax	OBJECT-TYPE
	SYNTAX	 CounterBasedGauge64
	MAX-ACCESS read-only
	STATUS current
	DESCRIPTION "IPv4 packets"

	::={pppoeIpv4Packets 3}

pppoeIpv4PacketsLevelTable OBJECT-TYPE
	SYNTAX      SEQUENCE OF PppoeIpv4PacketsLevelEntry
	MAX-ACCESS  not-accessible
	STATUS      current
	DESCRIPTION
	"Table for pppoeIpv4Packets"
	::={pppoeIpv4Packets 4}

pppoeIpv4PacketsLevelEntry OBJECT-TYPE
	SYNTAX      PppoeIpv4PacketsLevelEntry
	MAX-ACCESS  not-accessible
	STATUS      current
	DESCRIPTION
	"Table entry for pppoeIpv4Packets"
	INDEX { pppoeIpv4PacketsLevelName }
	::={pppoeIpv4PacketsLevelTable 1}

PppoeIpv4PacketsLevelEntry ::=
	SEQUENCE {
		pppoeIpv4PacketsLevelName	DisplayString,
		pppoeIpv4PacketsLevelVal	Counter64,
		pppoeIpv4PacketsLevelMom	CounterBasedGauge64,
		pppoeIpv4PacketsLevelMax	CounterBasedGauge64
	}

pppoeIpv4PacketsLevelName OBJECT-TYPE
	SYNTAX      DisplayString
	MAX-ACCESS  not-accessible
	STATUS      current
	DESCRIPTION
	"Table entry display string for pppoeIpv4Packets"
	::={pppoeIpv4PacketsLevelEntry 1}

pppoeIpv4PacketsLevelVal OBJECT-TYPE
	SYNTAX	 Counter64
	MAX-ACCESS  read-only
	STATUS      current
	DESCRIPTION
	"Table entry attribute for pppoeIpv4Packets"
	::={pppoeIpv4PacketsLevelEntry 2}

pppoeIpv4PacketsLevelMom OBJECT-TYPE
	SYNTAX	 CounterBasedGauge64
	MAX-ACCESS  read-only
	STATUS      current
	DESCRIPTION
	"Table entry attribute for pppoeIpv4Packets"
	::={pppoeIpv4PacketsLevelEntry 3}

pppoeIpv4PacketsLevelMax OBJECT-TYPE
	SYNTAX	 CounterBasedGauge64
	MAX-ACCESS  read-only
	STATUS      current
	DESCRIPTION
	"Table entry attribute for pppoeIpv4Packets"
	::={pppoeIpv4PacketsLevelEntry 4}


pppoeNonIpPackets	OBJECT IDENTIFIER ::={pppoe 7}

pppoeNonIpPacketsVal	OBJECT-TYPE
	SYNTAX	 Counter64
	MAX-ACCESS read-only
	STATUS current
	DESCRIPTION "Non IP packets"

	::={pppoeNonIpPackets 1}

pppoeNonIpPacketsMom	OBJECT-TYPE
	SYNTAX	 CounterBasedGauge64
	MAX-ACCESS read-only
	STATUS current
	DESCRIPTION "Non IP packets"

	::={pppoeNonIpPackets 2}

pppoeNonIpPacketsMax	OBJECT-TYPE
	SYNTAX	 CounterBasedGauge64
	MAX-ACCESS read-only
	STATUS current
	DESCRIPTION "Non IP packets"

	::={pppoeNonIpPackets 3}

pppoeNonIpPacketsLevelTable OBJECT-TYPE
	SYNTAX      SEQUENCE OF PppoeNonIpPacketsLevelEntry
	MAX-ACCESS  not-accessible
	STATUS      current
	DESCRIPTION
	"Table for pppoeNonIpPackets"
	::={pppoeNonIpPackets 4}

pppoeNonIpPacketsLevelEntry OBJECT-TYPE
	SYNTAX      PppoeNonIpPacketsLevelEntry
	MAX-ACCESS  not-accessible
	STATUS      current
	DESCRIPTION
	"Table entry for pppoeNonIpPackets"
	INDEX { pppoeNonIpPacketsLevelName }
	::={pppoeNonIpPacketsLevelTable 1}

PppoeNonIpPacketsLevelEntry ::=
	SEQUENCE {
		pppoeNonIpPacketsLevelName	DisplayString,
		pppoeNonIpPacketsLevelVal	Counter64,
		pppoeNonIpPacketsLevelMom	CounterBasedGauge64,
		pppoeNonIpPacketsLevelMax	CounterBasedGauge64
	}

pppoeNonIpPacketsLevelName OBJECT-TYPE
	SYNTAX      DisplayString
	MAX-ACCESS  not-accessible
	STATUS      current
	DESCRIPTION
	"Table entry display string for pppoeNonIpPackets"
	::={pppoeNonIpPacketsLevelEntry 1}

pppoeNonIpPacketsLevelVal OBJECT-TYPE
	SYNTAX	 Counter64
	MAX-ACCESS  read-only
	STATUS      current
	DESCRIPTION
	"Table entry attribute for pppoeNonIpPackets"
	::={pppoeNonIpPacketsLevelEntry 2}

pppoeNonIpPacketsLevelMom OBJECT-TYPE
	SYNTAX	 CounterBasedGauge64
	MAX-ACCESS  read-only
	STATUS      current
	DESCRIPTION
	"Table entry attribute for pppoeNonIpPackets"
	::={pppoeNonIpPacketsLevelEntry 3}

pppoeNonIpPacketsLevelMax OBJECT-TYPE
	SYNTAX	 CounterBasedGauge64
	MAX-ACCESS  read-only
	STATUS      current
	DESCRIPTION
	"Table entry attribute for pppoeNonIpPackets"
	::={pppoeNonIpPacketsLevelEntry 4}


pppoeIpv6Packets	OBJECT IDENTIFIER ::={pppoe 8}

pppoeIpv6PacketsVal	OBJECT-TYPE
	SYNTAX	 Counter64
	MAX-ACCESS read-only
	STATUS current
	DESCRIPTION "IPv6 packets"

	::={pppoeIpv6Packets 1}

pppoeIpv6PacketsMom	OBJECT-TYPE
	SYNTAX	 CounterBasedGauge64
	MAX-ACCESS read-only
	STATUS current
	DESCRIPTION "IPv6 packets"

	::={pppoeIpv6Packets 2}

pppoeIpv6PacketsMax	OBJECT-TYPE
	SYNTAX	 CounterBasedGauge64
	MAX-ACCESS read-only
	STATUS current
	DESCRIPTION "IPv6 packets"

	::={pppoeIpv6Packets 3}

pppoeIpv6PacketsLevelTable OBJECT-TYPE
	SYNTAX      SEQUENCE OF PppoeIpv6PacketsLevelEntry
	MAX-ACCESS  not-accessible
	STATUS      current
	DESCRIPTION
	"Table for pppoeIpv6Packets"
	::={pppoeIpv6Packets 4}

pppoeIpv6PacketsLevelEntry OBJECT-TYPE
	SYNTAX      PppoeIpv6PacketsLevelEntry
	MAX-ACCESS  not-accessible
	STATUS      current
	DESCRIPTION
	"Table entry for pppoeIpv6Packets"
	INDEX { pppoeIpv6PacketsLevelName }
	::={pppoeIpv6PacketsLevelTable 1}

PppoeIpv6PacketsLevelEntry ::=
	SEQUENCE {
		pppoeIpv6PacketsLevelName	DisplayString,
		pppoeIpv6PacketsLevelVal	Counter64,
		pppoeIpv6PacketsLevelMom	CounterBasedGauge64,
		pppoeIpv6PacketsLevelMax	CounterBasedGauge64
	}

pppoeIpv6PacketsLevelName OBJECT-TYPE
	SYNTAX      DisplayString
	MAX-ACCESS  not-accessible
	STATUS      current
	DESCRIPTION
	"Table entry display string for pppoeIpv6Packets"
	::={pppoeIpv6PacketsLevelEntry 1}

pppoeIpv6PacketsLevelVal OBJECT-TYPE
	SYNTAX	 Counter64
	MAX-ACCESS  read-only
	STATUS      current
	DESCRIPTION
	"Table entry attribute for pppoeIpv6Packets"
	::={pppoeIpv6PacketsLevelEntry 2}

pppoeIpv6PacketsLevelMom OBJECT-TYPE
	SYNTAX	 CounterBasedGauge64
	MAX-ACCESS  read-only
	STATUS      current
	DESCRIPTION
	"Table entry attribute for pppoeIpv6Packets"
	::={pppoeIpv6PacketsLevelEntry 3}

pppoeIpv6PacketsLevelMax OBJECT-TYPE
	SYNTAX	 CounterBasedGauge64
	MAX-ACCESS  read-only
	STATUS      current
	DESCRIPTION
	"Table entry attribute for pppoeIpv6Packets"
	::={pppoeIpv6PacketsLevelEntry 4}


interface	OBJECT IDENTIFIER ::={sysdiag 120}

interfaceBytesToEngine	OBJECT IDENTIFIER ::={interface 8}

interfaceBytesToEngineVal	OBJECT-TYPE
	SYNTAX	 Counter64
	MAX-ACCESS read-only
	STATUS current
	DESCRIPTION "Sent to engine"

	::={interfaceBytesToEngine 1}

interfaceBytesToEngineMom	OBJECT-TYPE
	SYNTAX	 CounterBasedGauge64
	MAX-ACCESS read-only
	STATUS current
	DESCRIPTION "Sent to engine"

	::={interfaceBytesToEngine 2}

interfaceBytesToEngineMax	OBJECT-TYPE
	SYNTAX	 CounterBasedGauge64
	MAX-ACCESS read-only
	STATUS current
	DESCRIPTION "Sent to engine"

	::={interfaceBytesToEngine 3}

interfaceBytesToEngineLevelTable OBJECT-TYPE
	SYNTAX      SEQUENCE OF InterfaceBytesToEngineLevelEntry
	MAX-ACCESS  not-accessible
	STATUS      current
	DESCRIPTION
	"Table for interfaceBytesToEngine"
	::={interfaceBytesToEngine 4}

interfaceBytesToEngineLevelEntry OBJECT-TYPE
	SYNTAX      InterfaceBytesToEngineLevelEntry
	MAX-ACCESS  not-accessible
	STATUS      current
	DESCRIPTION
	"Table entry for interfaceBytesToEngine"
	INDEX { interfaceBytesToEngineLevelName }
	::={interfaceBytesToEngineLevelTable 1}

InterfaceBytesToEngineLevelEntry ::=
	SEQUENCE {
		interfaceBytesToEngineLevelName	DisplayString,
		interfaceBytesToEngineLevelVal	Counter64,
		interfaceBytesToEngineLevelMom	CounterBasedGauge64,
		interfaceBytesToEngineLevelMax	CounterBasedGauge64
	}

interfaceBytesToEngineLevelName OBJECT-TYPE
	SYNTAX      DisplayString
	MAX-ACCESS  not-accessible
	STATUS      current
	DESCRIPTION
	"Table entry display string for interfaceBytesToEngine"
	::={interfaceBytesToEngineLevelEntry 1}

interfaceBytesToEngineLevelVal OBJECT-TYPE
	SYNTAX	 Counter64
	MAX-ACCESS  read-only
	STATUS      current
	DESCRIPTION
	"Table entry attribute for interfaceBytesToEngine"
	::={interfaceBytesToEngineLevelEntry 2}

interfaceBytesToEngineLevelMom OBJECT-TYPE
	SYNTAX	 CounterBasedGauge64
	MAX-ACCESS  read-only
	STATUS      current
	DESCRIPTION
	"Table entry attribute for interfaceBytesToEngine"
	::={interfaceBytesToEngineLevelEntry 3}

interfaceBytesToEngineLevelMax OBJECT-TYPE
	SYNTAX	 CounterBasedGauge64
	MAX-ACCESS  read-only
	STATUS      current
	DESCRIPTION
	"Table entry attribute for interfaceBytesToEngine"
	::={interfaceBytesToEngineLevelEntry 4}


interfaceBytesFromEngine	OBJECT IDENTIFIER ::={interface 9}

interfaceBytesFromEngineVal	OBJECT-TYPE
	SYNTAX	 Counter64
	MAX-ACCESS read-only
	STATUS current
	DESCRIPTION "Received from engine"

	::={interfaceBytesFromEngine 1}

interfaceBytesFromEngineMom	OBJECT-TYPE
	SYNTAX	 CounterBasedGauge64
	MAX-ACCESS read-only
	STATUS current
	DESCRIPTION "Received from engine"

	::={interfaceBytesFromEngine 2}

interfaceBytesFromEngineMax	OBJECT-TYPE
	SYNTAX	 CounterBasedGauge64
	MAX-ACCESS read-only
	STATUS current
	DESCRIPTION "Received from engine"

	::={interfaceBytesFromEngine 3}

interfaceBytesFromEngineLevelTable OBJECT-TYPE
	SYNTAX      SEQUENCE OF InterfaceBytesFromEngineLevelEntry
	MAX-ACCESS  not-accessible
	STATUS      current
	DESCRIPTION
	"Table for interfaceBytesFromEngine"
	::={interfaceBytesFromEngine 4}

interfaceBytesFromEngineLevelEntry OBJECT-TYPE
	SYNTAX      InterfaceBytesFromEngineLevelEntry
	MAX-ACCESS  not-accessible
	STATUS      current
	DESCRIPTION
	"Table entry for interfaceBytesFromEngine"
	INDEX { interfaceBytesFromEngineLevelName }
	::={interfaceBytesFromEngineLevelTable 1}

InterfaceBytesFromEngineLevelEntry ::=
	SEQUENCE {
		interfaceBytesFromEngineLevelName	DisplayString,
		interfaceBytesFromEngineLevelVal	Counter64,
		interfaceBytesFromEngineLevelMom	CounterBasedGauge64,
		interfaceBytesFromEngineLevelMax	CounterBasedGauge64
	}

interfaceBytesFromEngineLevelName OBJECT-TYPE
	SYNTAX      DisplayString
	MAX-ACCESS  not-accessible
	STATUS      current
	DESCRIPTION
	"Table entry display string for interfaceBytesFromEngine"
	::={interfaceBytesFromEngineLevelEntry 1}

interfaceBytesFromEngineLevelVal OBJECT-TYPE
	SYNTAX	 Counter64
	MAX-ACCESS  read-only
	STATUS      current
	DESCRIPTION
	"Table entry attribute for interfaceBytesFromEngine"
	::={interfaceBytesFromEngineLevelEntry 2}

interfaceBytesFromEngineLevelMom OBJECT-TYPE
	SYNTAX	 CounterBasedGauge64
	MAX-ACCESS  read-only
	STATUS      current
	DESCRIPTION
	"Table entry attribute for interfaceBytesFromEngine"
	::={interfaceBytesFromEngineLevelEntry 3}

interfaceBytesFromEngineLevelMax OBJECT-TYPE
	SYNTAX	 CounterBasedGauge64
	MAX-ACCESS  read-only
	STATUS      current
	DESCRIPTION
	"Table entry attribute for interfaceBytesFromEngine"
	::={interfaceBytesFromEngineLevelEntry 4}


interfaceFlowNewMissed	OBJECT IDENTIFIER ::={interface 10}

interfaceFlowNewMissedVal	OBJECT-TYPE
	SYNTAX	 Counter64
	MAX-ACCESS read-only
	STATUS current
	DESCRIPTION "New flows missed"

	::={interfaceFlowNewMissed 1}

interfaceFlowNewMissedMom	OBJECT-TYPE
	SYNTAX	 CounterBasedGauge64
	MAX-ACCESS read-only
	STATUS current
	DESCRIPTION "New flows missed"

	::={interfaceFlowNewMissed 2}

interfaceFlowNewMissedMax	OBJECT-TYPE
	SYNTAX	 CounterBasedGauge64
	MAX-ACCESS read-only
	STATUS current
	DESCRIPTION "New flows missed"

	::={interfaceFlowNewMissed 3}

interfaceFlowNewMissedLevelTable OBJECT-TYPE
	SYNTAX      SEQUENCE OF InterfaceFlowNewMissedLevelEntry
	MAX-ACCESS  not-accessible
	STATUS      current
	DESCRIPTION
	"Table for interfaceFlowNewMissed"
	::={interfaceFlowNewMissed 4}

interfaceFlowNewMissedLevelEntry OBJECT-TYPE
	SYNTAX      InterfaceFlowNewMissedLevelEntry
	MAX-ACCESS  not-accessible
	STATUS      current
	DESCRIPTION
	"Table entry for interfaceFlowNewMissed"
	INDEX { interfaceFlowNewMissedLevelName }
	::={interfaceFlowNewMissedLevelTable 1}

InterfaceFlowNewMissedLevelEntry ::=
	SEQUENCE {
		interfaceFlowNewMissedLevelName	DisplayString,
		interfaceFlowNewMissedLevelVal	Counter64,
		interfaceFlowNewMissedLevelMom	CounterBasedGauge64,
		interfaceFlowNewMissedLevelMax	CounterBasedGauge64
	}

interfaceFlowNewMissedLevelName OBJECT-TYPE
	SYNTAX      DisplayString
	MAX-ACCESS  not-accessible
	STATUS      current
	DESCRIPTION
	"Table entry display string for interfaceFlowNewMissed"
	::={interfaceFlowNewMissedLevelEntry 1}

interfaceFlowNewMissedLevelVal OBJECT-TYPE
	SYNTAX	 Counter64
	MAX-ACCESS  read-only
	STATUS      current
	DESCRIPTION
	"Table entry attribute for interfaceFlowNewMissed"
	::={interfaceFlowNewMissedLevelEntry 2}

interfaceFlowNewMissedLevelMom OBJECT-TYPE
	SYNTAX	 CounterBasedGauge64
	MAX-ACCESS  read-only
	STATUS      current
	DESCRIPTION
	"Table entry attribute for interfaceFlowNewMissed"
	::={interfaceFlowNewMissedLevelEntry 3}

interfaceFlowNewMissedLevelMax OBJECT-TYPE
	SYNTAX	 CounterBasedGauge64
	MAX-ACCESS  read-only
	STATUS      current
	DESCRIPTION
	"Table entry attribute for interfaceFlowNewMissed"
	::={interfaceFlowNewMissedLevelEntry 4}


interfaceFlowUpdMissed	OBJECT IDENTIFIER ::={interface 11}

interfaceFlowUpdMissedVal	OBJECT-TYPE
	SYNTAX	 Counter64
	MAX-ACCESS read-only
	STATUS current
	DESCRIPTION "Flow updates missed"

	::={interfaceFlowUpdMissed 1}

interfaceFlowUpdMissedMom	OBJECT-TYPE
	SYNTAX	 CounterBasedGauge64
	MAX-ACCESS read-only
	STATUS current
	DESCRIPTION "Flow updates missed"

	::={interfaceFlowUpdMissed 2}

interfaceFlowUpdMissedMax	OBJECT-TYPE
	SYNTAX	 CounterBasedGauge64
	MAX-ACCESS read-only
	STATUS current
	DESCRIPTION "Flow updates missed"

	::={interfaceFlowUpdMissed 3}

interfaceFlowUpdMissedLevelTable OBJECT-TYPE
	SYNTAX      SEQUENCE OF InterfaceFlowUpdMissedLevelEntry
	MAX-ACCESS  not-accessible
	STATUS      current
	DESCRIPTION
	"Table for interfaceFlowUpdMissed"
	::={interfaceFlowUpdMissed 4}

interfaceFlowUpdMissedLevelEntry OBJECT-TYPE
	SYNTAX      InterfaceFlowUpdMissedLevelEntry
	MAX-ACCESS  not-accessible
	STATUS      current
	DESCRIPTION
	"Table entry for interfaceFlowUpdMissed"
	INDEX { interfaceFlowUpdMissedLevelName }
	::={interfaceFlowUpdMissedLevelTable 1}

InterfaceFlowUpdMissedLevelEntry ::=
	SEQUENCE {
		interfaceFlowUpdMissedLevelName	DisplayString,
		interfaceFlowUpdMissedLevelVal	Counter64,
		interfaceFlowUpdMissedLevelMom	CounterBasedGauge64,
		interfaceFlowUpdMissedLevelMax	CounterBasedGauge64
	}

interfaceFlowUpdMissedLevelName OBJECT-TYPE
	SYNTAX      DisplayString
	MAX-ACCESS  not-accessible
	STATUS      current
	DESCRIPTION
	"Table entry display string for interfaceFlowUpdMissed"
	::={interfaceFlowUpdMissedLevelEntry 1}

interfaceFlowUpdMissedLevelVal OBJECT-TYPE
	SYNTAX	 Counter64
	MAX-ACCESS  read-only
	STATUS      current
	DESCRIPTION
	"Table entry attribute for interfaceFlowUpdMissed"
	::={interfaceFlowUpdMissedLevelEntry 2}

interfaceFlowUpdMissedLevelMom OBJECT-TYPE
	SYNTAX	 CounterBasedGauge64
	MAX-ACCESS  read-only
	STATUS      current
	DESCRIPTION
	"Table entry attribute for interfaceFlowUpdMissed"
	::={interfaceFlowUpdMissedLevelEntry 3}

interfaceFlowUpdMissedLevelMax OBJECT-TYPE
	SYNTAX	 CounterBasedGauge64
	MAX-ACCESS  read-only
	STATUS      current
	DESCRIPTION
	"Table entry attribute for interfaceFlowUpdMissed"
	::={interfaceFlowUpdMissedLevelEntry 4}


interfaceFlowNew	OBJECT IDENTIFIER ::={interface 12}

interfaceFlowNewVal	OBJECT-TYPE
	SYNTAX	 Counter64
	MAX-ACCESS read-only
	STATUS current
	DESCRIPTION "New flows"

	::={interfaceFlowNew 1}

interfaceFlowNewMom	OBJECT-TYPE
	SYNTAX	 CounterBasedGauge64
	MAX-ACCESS read-only
	STATUS current
	DESCRIPTION "New flows"

	::={interfaceFlowNew 2}

interfaceFlowNewMax	OBJECT-TYPE
	SYNTAX	 CounterBasedGauge64
	MAX-ACCESS read-only
	STATUS current
	DESCRIPTION "New flows"

	::={interfaceFlowNew 3}

interfaceFlowNewLevelTable OBJECT-TYPE
	SYNTAX      SEQUENCE OF InterfaceFlowNewLevelEntry
	MAX-ACCESS  not-accessible
	STATUS      current
	DESCRIPTION
	"Table for interfaceFlowNew"
	::={interfaceFlowNew 4}

interfaceFlowNewLevelEntry OBJECT-TYPE
	SYNTAX      InterfaceFlowNewLevelEntry
	MAX-ACCESS  not-accessible
	STATUS      current
	DESCRIPTION
	"Table entry for interfaceFlowNew"
	INDEX { interfaceFlowNewLevelName }
	::={interfaceFlowNewLevelTable 1}

InterfaceFlowNewLevelEntry ::=
	SEQUENCE {
		interfaceFlowNewLevelName	DisplayString,
		interfaceFlowNewLevelVal	Counter64,
		interfaceFlowNewLevelMom	CounterBasedGauge64,
		interfaceFlowNewLevelMax	CounterBasedGauge64
	}

interfaceFlowNewLevelName OBJECT-TYPE
	SYNTAX      DisplayString
	MAX-ACCESS  not-accessible
	STATUS      current
	DESCRIPTION
	"Table entry display string for interfaceFlowNew"
	::={interfaceFlowNewLevelEntry 1}

interfaceFlowNewLevelVal OBJECT-TYPE
	SYNTAX	 Counter64
	MAX-ACCESS  read-only
	STATUS      current
	DESCRIPTION
	"Table entry attribute for interfaceFlowNew"
	::={interfaceFlowNewLevelEntry 2}

interfaceFlowNewLevelMom OBJECT-TYPE
	SYNTAX	 CounterBasedGauge64
	MAX-ACCESS  read-only
	STATUS      current
	DESCRIPTION
	"Table entry attribute for interfaceFlowNew"
	::={interfaceFlowNewLevelEntry 3}

interfaceFlowNewLevelMax OBJECT-TYPE
	SYNTAX	 CounterBasedGauge64
	MAX-ACCESS  read-only
	STATUS      current
	DESCRIPTION
	"Table entry attribute for interfaceFlowNew"
	::={interfaceFlowNewLevelEntry 4}


interfaceFlowHostnameAllocFail	OBJECT IDENTIFIER ::={interface 13}

interfaceFlowHostnameAllocFailVal	OBJECT-TYPE
	SYNTAX	 Counter64
	MAX-ACCESS read-only
	STATUS current
	DESCRIPTION "Hostname allocation failures"

	::={interfaceFlowHostnameAllocFail 1}

interfaceFlowHostnameAllocFailMom	OBJECT-TYPE
	SYNTAX	 CounterBasedGauge64
	MAX-ACCESS read-only
	STATUS current
	DESCRIPTION "Hostname allocation failures"

	::={interfaceFlowHostnameAllocFail 2}

interfaceFlowHostnameAllocFailMax	OBJECT-TYPE
	SYNTAX	 CounterBasedGauge64
	MAX-ACCESS read-only
	STATUS current
	DESCRIPTION "Hostname allocation failures"

	::={interfaceFlowHostnameAllocFail 3}

interfaceFlowHostnameAllocFailLevelTable OBJECT-TYPE
	SYNTAX      SEQUENCE OF InterfaceFlowHostnameAllocFailLevelEntry
	MAX-ACCESS  not-accessible
	STATUS      current
	DESCRIPTION
	"Table for interfaceFlowHostnameAllocFail"
	::={interfaceFlowHostnameAllocFail 4}

interfaceFlowHostnameAllocFailLevelEntry OBJECT-TYPE
	SYNTAX      InterfaceFlowHostnameAllocFailLevelEntry
	MAX-ACCESS  not-accessible
	STATUS      current
	DESCRIPTION
	"Table entry for interfaceFlowHostnameAllocFail"
	INDEX { interfaceFlowHostnameAllocFailLevelName }
	::={interfaceFlowHostnameAllocFailLevelTable 1}

InterfaceFlowHostnameAllocFailLevelEntry ::=
	SEQUENCE {
		interfaceFlowHostnameAllocFailLevelName	DisplayString,
		interfaceFlowHostnameAllocFailLevelVal	Counter64,
		interfaceFlowHostnameAllocFailLevelMom	CounterBasedGauge64,
		interfaceFlowHostnameAllocFailLevelMax	CounterBasedGauge64
	}

interfaceFlowHostnameAllocFailLevelName OBJECT-TYPE
	SYNTAX      DisplayString
	MAX-ACCESS  not-accessible
	STATUS      current
	DESCRIPTION
	"Table entry display string for interfaceFlowHostnameAllocFail"
	::={interfaceFlowHostnameAllocFailLevelEntry 1}

interfaceFlowHostnameAllocFailLevelVal OBJECT-TYPE
	SYNTAX	 Counter64
	MAX-ACCESS  read-only
	STATUS      current
	DESCRIPTION
	"Table entry attribute for interfaceFlowHostnameAllocFail"
	::={interfaceFlowHostnameAllocFailLevelEntry 2}

interfaceFlowHostnameAllocFailLevelMom OBJECT-TYPE
	SYNTAX	 CounterBasedGauge64
	MAX-ACCESS  read-only
	STATUS      current
	DESCRIPTION
	"Table entry attribute for interfaceFlowHostnameAllocFail"
	::={interfaceFlowHostnameAllocFailLevelEntry 3}

interfaceFlowHostnameAllocFailLevelMax OBJECT-TYPE
	SYNTAX	 CounterBasedGauge64
	MAX-ACCESS  read-only
	STATUS      current
	DESCRIPTION
	"Table entry attribute for interfaceFlowHostnameAllocFail"
	::={interfaceFlowHostnameAllocFailLevelEntry 4}


interfaceFlowUpdReordered	OBJECT IDENTIFIER ::={interface 14}

interfaceFlowUpdReorderedVal	OBJECT-TYPE
	SYNTAX	 Counter64
	MAX-ACCESS read-only
	STATUS current
	DESCRIPTION "Reordered flow updates"

	::={interfaceFlowUpdReordered 1}

interfaceFlowUpdReorderedMom	OBJECT-TYPE
	SYNTAX	 CounterBasedGauge64
	MAX-ACCESS read-only
	STATUS current
	DESCRIPTION "Reordered flow updates"

	::={interfaceFlowUpdReordered 2}

interfaceFlowUpdReorderedMax	OBJECT-TYPE
	SYNTAX	 CounterBasedGauge64
	MAX-ACCESS read-only
	STATUS current
	DESCRIPTION "Reordered flow updates"

	::={interfaceFlowUpdReordered 3}

interfaceFlowUpdReorderedLevelTable OBJECT-TYPE
	SYNTAX      SEQUENCE OF InterfaceFlowUpdReorderedLevelEntry
	MAX-ACCESS  not-accessible
	STATUS      current
	DESCRIPTION
	"Table for interfaceFlowUpdReordered"
	::={interfaceFlowUpdReordered 4}

interfaceFlowUpdReorderedLevelEntry OBJECT-TYPE
	SYNTAX      InterfaceFlowUpdReorderedLevelEntry
	MAX-ACCESS  not-accessible
	STATUS      current
	DESCRIPTION
	"Table entry for interfaceFlowUpdReordered"
	INDEX { interfaceFlowUpdReorderedLevelName }
	::={interfaceFlowUpdReorderedLevelTable 1}

InterfaceFlowUpdReorderedLevelEntry ::=
	SEQUENCE {
		interfaceFlowUpdReorderedLevelName	DisplayString,
		interfaceFlowUpdReorderedLevelVal	Counter64,
		interfaceFlowUpdReorderedLevelMom	CounterBasedGauge64,
		interfaceFlowUpdReorderedLevelMax	CounterBasedGauge64
	}

interfaceFlowUpdReorderedLevelName OBJECT-TYPE
	SYNTAX      DisplayString
	MAX-ACCESS  not-accessible
	STATUS      current
	DESCRIPTION
	"Table entry display string for interfaceFlowUpdReordered"
	::={interfaceFlowUpdReorderedLevelEntry 1}

interfaceFlowUpdReorderedLevelVal OBJECT-TYPE
	SYNTAX	 Counter64
	MAX-ACCESS  read-only
	STATUS      current
	DESCRIPTION
	"Table entry attribute for interfaceFlowUpdReordered"
	::={interfaceFlowUpdReorderedLevelEntry 2}

interfaceFlowUpdReorderedLevelMom OBJECT-TYPE
	SYNTAX	 CounterBasedGauge64
	MAX-ACCESS  read-only
	STATUS      current
	DESCRIPTION
	"Table entry attribute for interfaceFlowUpdReordered"
	::={interfaceFlowUpdReorderedLevelEntry 3}

interfaceFlowUpdReorderedLevelMax OBJECT-TYPE
	SYNTAX	 CounterBasedGauge64
	MAX-ACCESS  read-only
	STATUS      current
	DESCRIPTION
	"Table entry attribute for interfaceFlowUpdReordered"
	::={interfaceFlowUpdReorderedLevelEntry 4}


interfaceFlowHostnameAllocated	OBJECT IDENTIFIER ::={interface 15}

interfaceFlowHostnameAllocatedVal	OBJECT-TYPE
	SYNTAX	 CounterBasedGauge64
	MAX-ACCESS read-only
	STATUS current
	DESCRIPTION "Hostname allocations"

	::={interfaceFlowHostnameAllocated 1}

interfaceFlowHostnameAllocatedMax	OBJECT-TYPE
	SYNTAX	 CounterBasedGauge64
	MAX-ACCESS read-only
	STATUS current
	DESCRIPTION "Hostname allocations"

	::={interfaceFlowHostnameAllocated 3}

interfaceFlowHostnameAllocatedLevelTable OBJECT-TYPE
	SYNTAX      SEQUENCE OF InterfaceFlowHostnameAllocatedLevelEntry
	MAX-ACCESS  not-accessible
	STATUS      current
	DESCRIPTION
	"Table for interfaceFlowHostnameAllocated"
	::={interfaceFlowHostnameAllocated 4}

interfaceFlowHostnameAllocatedLevelEntry OBJECT-TYPE
	SYNTAX      InterfaceFlowHostnameAllocatedLevelEntry
	MAX-ACCESS  not-accessible
	STATUS      current
	DESCRIPTION
	"Table entry for interfaceFlowHostnameAllocated"
	INDEX { interfaceFlowHostnameAllocatedLevelName }
	::={interfaceFlowHostnameAllocatedLevelTable 1}

InterfaceFlowHostnameAllocatedLevelEntry ::=
	SEQUENCE {
		interfaceFlowHostnameAllocatedLevelName	DisplayString,
		interfaceFlowHostnameAllocatedLevelVal	CounterBasedGauge64,
		interfaceFlowHostnameAllocatedLevelMax	CounterBasedGauge64
	}

interfaceFlowHostnameAllocatedLevelName OBJECT-TYPE
	SYNTAX      DisplayString
	MAX-ACCESS  not-accessible
	STATUS      current
	DESCRIPTION
	"Table entry display string for interfaceFlowHostnameAllocated"
	::={interfaceFlowHostnameAllocatedLevelEntry 1}

interfaceFlowHostnameAllocatedLevelVal OBJECT-TYPE
	SYNTAX	 CounterBasedGauge64
	MAX-ACCESS  read-only
	STATUS      current
	DESCRIPTION
	"Table entry attribute for interfaceFlowHostnameAllocated"
	::={interfaceFlowHostnameAllocatedLevelEntry 2}

interfaceFlowHostnameAllocatedLevelMax OBJECT-TYPE
	SYNTAX	 CounterBasedGauge64
	MAX-ACCESS  read-only
	STATUS      current
	DESCRIPTION
	"Table entry attribute for interfaceFlowHostnameAllocated"
	::={interfaceFlowHostnameAllocatedLevelEntry 4}


dynnetobjs	OBJECT IDENTIFIER ::={sysdiag 121}

dynamicnetobjectCurrentIpCount	OBJECT IDENTIFIER ::={dynnetobjs 5}

dynamicnetobjectCurrentIpCountVal	OBJECT-TYPE
	SYNTAX	 CounterBasedGauge64
	MAX-ACCESS read-only
	STATUS current
	DESCRIPTION "Dynamic prefixes: Total number of dynamic prefixes"

	::={dynamicnetobjectCurrentIpCount 1}

dynamicnetobjectCurrentIpCountMax	OBJECT-TYPE
	SYNTAX	 CounterBasedGauge64
	MAX-ACCESS read-only
	STATUS current
	DESCRIPTION "Dynamic prefixes: Total number of dynamic prefixes"

	::={dynamicnetobjectCurrentIpCount 3}

dynamicnetobjectCurrentIpCountLevelTable OBJECT-TYPE
	SYNTAX      SEQUENCE OF DynamicnetobjectCurrentIpCountLevelEntry
	MAX-ACCESS  not-accessible
	STATUS      current
	DESCRIPTION
	"Table for dynamicnetobjectCurrentIpCount"
	::={dynamicnetobjectCurrentIpCount 4}

dynamicnetobjectCurrentIpCountLevelEntry OBJECT-TYPE
	SYNTAX      DynamicnetobjectCurrentIpCountLevelEntry
	MAX-ACCESS  not-accessible
	STATUS      current
	DESCRIPTION
	"Table entry for dynamicnetobjectCurrentIpCount"
	INDEX { dynamicnetobjectCurrentIpCountLevelName }
	::={dynamicnetobjectCurrentIpCountLevelTable 1}

DynamicnetobjectCurrentIpCountLevelEntry ::=
	SEQUENCE {
		dynamicnetobjectCurrentIpCountLevelName	DisplayString,
		dynamicnetobjectCurrentIpCountLevelVal	CounterBasedGauge64,
		dynamicnetobjectCurrentIpCountLevelMax	CounterBasedGauge64
	}

dynamicnetobjectCurrentIpCountLevelName OBJECT-TYPE
	SYNTAX      DisplayString
	MAX-ACCESS  not-accessible
	STATUS      current
	DESCRIPTION
	"Table entry display string for dynamicnetobjectCurrentIpCount"
	::={dynamicnetobjectCurrentIpCountLevelEntry 1}

dynamicnetobjectCurrentIpCountLevelVal OBJECT-TYPE
	SYNTAX	 CounterBasedGauge64
	MAX-ACCESS  read-only
	STATUS      current
	DESCRIPTION
	"Table entry attribute for dynamicnetobjectCurrentIpCount"
	::={dynamicnetobjectCurrentIpCountLevelEntry 2}

dynamicnetobjectCurrentIpCountLevelMax OBJECT-TYPE
	SYNTAX	 CounterBasedGauge64
	MAX-ACCESS  read-only
	STATUS      current
	DESCRIPTION
	"Table entry attribute for dynamicnetobjectCurrentIpCount"
	::={dynamicnetobjectCurrentIpCountLevelEntry 4}


dynamicnetobjectCurrentCountV4	OBJECT IDENTIFIER ::={dynnetobjs 63}

dynamicnetobjectCurrentCountV4Val	OBJECT-TYPE
	SYNTAX	 CounterBasedGauge64
	MAX-ACCESS read-only
	STATUS current
	DESCRIPTION "Dynamic prefixes: Number of dynamic IPv4 prefixes"

	::={dynamicnetobjectCurrentCountV4 1}

dynamicnetobjectCurrentCountV4Max	OBJECT-TYPE
	SYNTAX	 CounterBasedGauge64
	MAX-ACCESS read-only
	STATUS current
	DESCRIPTION "Dynamic prefixes: Number of dynamic IPv4 prefixes"

	::={dynamicnetobjectCurrentCountV4 3}

dynamicnetobjectCurrentCountV4LevelTable OBJECT-TYPE
	SYNTAX      SEQUENCE OF DynamicnetobjectCurrentCountV4LevelEntry
	MAX-ACCESS  not-accessible
	STATUS      current
	DESCRIPTION
	"Table for dynamicnetobjectCurrentCountV4"
	::={dynamicnetobjectCurrentCountV4 4}

dynamicnetobjectCurrentCountV4LevelEntry OBJECT-TYPE
	SYNTAX      DynamicnetobjectCurrentCountV4LevelEntry
	MAX-ACCESS  not-accessible
	STATUS      current
	DESCRIPTION
	"Table entry for dynamicnetobjectCurrentCountV4"
	INDEX { dynamicnetobjectCurrentCountV4LevelName }
	::={dynamicnetobjectCurrentCountV4LevelTable 1}

DynamicnetobjectCurrentCountV4LevelEntry ::=
	SEQUENCE {
		dynamicnetobjectCurrentCountV4LevelName	DisplayString,
		dynamicnetobjectCurrentCountV4LevelVal	CounterBasedGauge64,
		dynamicnetobjectCurrentCountV4LevelMax	CounterBasedGauge64
	}

dynamicnetobjectCurrentCountV4LevelName OBJECT-TYPE
	SYNTAX      DisplayString
	MAX-ACCESS  not-accessible
	STATUS      current
	DESCRIPTION
	"Table entry display string for dynamicnetobjectCurrentCountV4"
	::={dynamicnetobjectCurrentCountV4LevelEntry 1}

dynamicnetobjectCurrentCountV4LevelVal OBJECT-TYPE
	SYNTAX	 CounterBasedGauge64
	MAX-ACCESS  read-only
	STATUS      current
	DESCRIPTION
	"Table entry attribute for dynamicnetobjectCurrentCountV4"
	::={dynamicnetobjectCurrentCountV4LevelEntry 2}

dynamicnetobjectCurrentCountV4LevelMax OBJECT-TYPE
	SYNTAX	 CounterBasedGauge64
	MAX-ACCESS  read-only
	STATUS      current
	DESCRIPTION
	"Table entry attribute for dynamicnetobjectCurrentCountV4"
	::={dynamicnetobjectCurrentCountV4LevelEntry 4}


dynamicnetobjectCurrentCountV6	OBJECT IDENTIFIER ::={dynnetobjs 52}

dynamicnetobjectCurrentCountV6Val	OBJECT-TYPE
	SYNTAX	 CounterBasedGauge64
	MAX-ACCESS read-only
	STATUS current
	DESCRIPTION "Dynamic prefixes: Number of dynamic IPv6 prefixes"

	::={dynamicnetobjectCurrentCountV6 1}

dynamicnetobjectCurrentCountV6Max	OBJECT-TYPE
	SYNTAX	 CounterBasedGauge64
	MAX-ACCESS read-only
	STATUS current
	DESCRIPTION "Dynamic prefixes: Number of dynamic IPv6 prefixes"

	::={dynamicnetobjectCurrentCountV6 3}

dynamicnetobjectCurrentCountV6LevelTable OBJECT-TYPE
	SYNTAX      SEQUENCE OF DynamicnetobjectCurrentCountV6LevelEntry
	MAX-ACCESS  not-accessible
	STATUS      current
	DESCRIPTION
	"Table for dynamicnetobjectCurrentCountV6"
	::={dynamicnetobjectCurrentCountV6 4}

dynamicnetobjectCurrentCountV6LevelEntry OBJECT-TYPE
	SYNTAX      DynamicnetobjectCurrentCountV6LevelEntry
	MAX-ACCESS  not-accessible
	STATUS      current
	DESCRIPTION
	"Table entry for dynamicnetobjectCurrentCountV6"
	INDEX { dynamicnetobjectCurrentCountV6LevelName }
	::={dynamicnetobjectCurrentCountV6LevelTable 1}

DynamicnetobjectCurrentCountV6LevelEntry ::=
	SEQUENCE {
		dynamicnetobjectCurrentCountV6LevelName	DisplayString,
		dynamicnetobjectCurrentCountV6LevelVal	CounterBasedGauge64,
		dynamicnetobjectCurrentCountV6LevelMax	CounterBasedGauge64
	}

dynamicnetobjectCurrentCountV6LevelName OBJECT-TYPE
	SYNTAX      DisplayString
	MAX-ACCESS  not-accessible
	STATUS      current
	DESCRIPTION
	"Table entry display string for dynamicnetobjectCurrentCountV6"
	::={dynamicnetobjectCurrentCountV6LevelEntry 1}

dynamicnetobjectCurrentCountV6LevelVal OBJECT-TYPE
	SYNTAX	 CounterBasedGauge64
	MAX-ACCESS  read-only
	STATUS      current
	DESCRIPTION
	"Table entry attribute for dynamicnetobjectCurrentCountV6"
	::={dynamicnetobjectCurrentCountV6LevelEntry 2}

dynamicnetobjectCurrentCountV6LevelMax OBJECT-TYPE
	SYNTAX	 CounterBasedGauge64
	MAX-ACCESS  read-only
	STATUS      current
	DESCRIPTION
	"Table entry attribute for dynamicnetobjectCurrentCountV6"
	::={dynamicnetobjectCurrentCountV6LevelEntry 4}


dynamicnetobjectFailedInserts	OBJECT IDENTIFIER ::={dynnetobjs 1}

dynamicnetobjectFailedInsertsVal	OBJECT-TYPE
	SYNTAX	 Counter64
	MAX-ACCESS read-only
	STATUS current
	DESCRIPTION "Dynamic prefixes: Storage for dynamic prefixes is full"

	::={dynamicnetobjectFailedInserts 1}

dynamicnetobjectFailedInsertsMom	OBJECT-TYPE
	SYNTAX	 CounterBasedGauge64
	MAX-ACCESS read-only
	STATUS current
	DESCRIPTION "Dynamic prefixes: Storage for dynamic prefixes is full"

	::={dynamicnetobjectFailedInserts 2}

dynamicnetobjectFailedInsertsMax	OBJECT-TYPE
	SYNTAX	 CounterBasedGauge64
	MAX-ACCESS read-only
	STATUS current
	DESCRIPTION "Dynamic prefixes: Storage for dynamic prefixes is full"

	::={dynamicnetobjectFailedInserts 3}

dynamicnetobjectFailedInsertsLevelTable OBJECT-TYPE
	SYNTAX      SEQUENCE OF DynamicnetobjectFailedInsertsLevelEntry
	MAX-ACCESS  not-accessible
	STATUS      current
	DESCRIPTION
	"Table for dynamicnetobjectFailedInserts"
	::={dynamicnetobjectFailedInserts 4}

dynamicnetobjectFailedInsertsLevelEntry OBJECT-TYPE
	SYNTAX      DynamicnetobjectFailedInsertsLevelEntry
	MAX-ACCESS  not-accessible
	STATUS      current
	DESCRIPTION
	"Table entry for dynamicnetobjectFailedInserts"
	INDEX { dynamicnetobjectFailedInsertsLevelName }
	::={dynamicnetobjectFailedInsertsLevelTable 1}

DynamicnetobjectFailedInsertsLevelEntry ::=
	SEQUENCE {
		dynamicnetobjectFailedInsertsLevelName	DisplayString,
		dynamicnetobjectFailedInsertsLevelVal	Counter64,
		dynamicnetobjectFailedInsertsLevelMom	CounterBasedGauge64,
		dynamicnetobjectFailedInsertsLevelMax	CounterBasedGauge64
	}

dynamicnetobjectFailedInsertsLevelName OBJECT-TYPE
	SYNTAX      DisplayString
	MAX-ACCESS  not-accessible
	STATUS      current
	DESCRIPTION
	"Table entry display string for dynamicnetobjectFailedInserts"
	::={dynamicnetobjectFailedInsertsLevelEntry 1}

dynamicnetobjectFailedInsertsLevelVal OBJECT-TYPE
	SYNTAX	 Counter64
	MAX-ACCESS  read-only
	STATUS      current
	DESCRIPTION
	"Table entry attribute for dynamicnetobjectFailedInserts"
	::={dynamicnetobjectFailedInsertsLevelEntry 2}

dynamicnetobjectFailedInsertsLevelMom OBJECT-TYPE
	SYNTAX	 CounterBasedGauge64
	MAX-ACCESS  read-only
	STATUS      current
	DESCRIPTION
	"Table entry attribute for dynamicnetobjectFailedInserts"
	::={dynamicnetobjectFailedInsertsLevelEntry 3}

dynamicnetobjectFailedInsertsLevelMax OBJECT-TYPE
	SYNTAX	 CounterBasedGauge64
	MAX-ACCESS  read-only
	STATUS      current
	DESCRIPTION
	"Table entry attribute for dynamicnetobjectFailedInserts"
	::={dynamicnetobjectFailedInsertsLevelEntry 4}


dynamicnetobjectCurrentCount	OBJECT IDENTIFIER ::={dynnetobjs 6}

dynamicnetobjectCurrentCountVal	OBJECT-TYPE
	SYNTAX	 CounterBasedGauge64
	MAX-ACCESS read-only
	STATUS current
	DESCRIPTION "Dynamic item: Number of dynamic items (pair Netobject-ID, Prefix)"

	::={dynamicnetobjectCurrentCount 1}

dynamicnetobjectCurrentCountMax	OBJECT-TYPE
	SYNTAX	 CounterBasedGauge64
	MAX-ACCESS read-only
	STATUS current
	DESCRIPTION "Dynamic item: Number of dynamic items (pair Netobject-ID, Prefix)"

	::={dynamicnetobjectCurrentCount 3}

dynamicnetobjectCurrentCountLevelTable OBJECT-TYPE
	SYNTAX      SEQUENCE OF DynamicnetobjectCurrentCountLevelEntry
	MAX-ACCESS  not-accessible
	STATUS      current
	DESCRIPTION
	"Table for dynamicnetobjectCurrentCount"
	::={dynamicnetobjectCurrentCount 4}

dynamicnetobjectCurrentCountLevelEntry OBJECT-TYPE
	SYNTAX      DynamicnetobjectCurrentCountLevelEntry
	MAX-ACCESS  not-accessible
	STATUS      current
	DESCRIPTION
	"Table entry for dynamicnetobjectCurrentCount"
	INDEX { dynamicnetobjectCurrentCountLevelName }
	::={dynamicnetobjectCurrentCountLevelTable 1}

DynamicnetobjectCurrentCountLevelEntry ::=
	SEQUENCE {
		dynamicnetobjectCurrentCountLevelName	DisplayString,
		dynamicnetobjectCurrentCountLevelVal	CounterBasedGauge64,
		dynamicnetobjectCurrentCountLevelMax	CounterBasedGauge64
	}

dynamicnetobjectCurrentCountLevelName OBJECT-TYPE
	SYNTAX      DisplayString
	MAX-ACCESS  not-accessible
	STATUS      current
	DESCRIPTION
	"Table entry display string for dynamicnetobjectCurrentCount"
	::={dynamicnetobjectCurrentCountLevelEntry 1}

dynamicnetobjectCurrentCountLevelVal OBJECT-TYPE
	SYNTAX	 CounterBasedGauge64
	MAX-ACCESS  read-only
	STATUS      current
	DESCRIPTION
	"Table entry attribute for dynamicnetobjectCurrentCount"
	::={dynamicnetobjectCurrentCountLevelEntry 2}

dynamicnetobjectCurrentCountLevelMax OBJECT-TYPE
	SYNTAX	 CounterBasedGauge64
	MAX-ACCESS  read-only
	STATUS      current
	DESCRIPTION
	"Table entry attribute for dynamicnetobjectCurrentCount"
	::={dynamicnetobjectCurrentCountLevelEntry 4}


dynamicnetobjectSubscriberCount	OBJECT IDENTIFIER ::={dynnetobjs 18}

dynamicnetobjectSubscriberCountVal	OBJECT-TYPE
	SYNTAX	 CounterBasedGauge64
	MAX-ACCESS read-only
	STATUS current
	DESCRIPTION "Subscriber: Number of unique subscriber names"

	::={dynamicnetobjectSubscriberCount 1}

dynamicnetobjectSubscriberCountMax	OBJECT-TYPE
	SYNTAX	 CounterBasedGauge64
	MAX-ACCESS read-only
	STATUS current
	DESCRIPTION "Subscriber: Number of unique subscriber names"

	::={dynamicnetobjectSubscriberCount 3}

dynamicnetobjectSubscriberCountLevelTable OBJECT-TYPE
	SYNTAX      SEQUENCE OF DynamicnetobjectSubscriberCountLevelEntry
	MAX-ACCESS  not-accessible
	STATUS      current
	DESCRIPTION
	"Table for dynamicnetobjectSubscriberCount"
	::={dynamicnetobjectSubscriberCount 4}

dynamicnetobjectSubscriberCountLevelEntry OBJECT-TYPE
	SYNTAX      DynamicnetobjectSubscriberCountLevelEntry
	MAX-ACCESS  not-accessible
	STATUS      current
	DESCRIPTION
	"Table entry for dynamicnetobjectSubscriberCount"
	INDEX { dynamicnetobjectSubscriberCountLevelName }
	::={dynamicnetobjectSubscriberCountLevelTable 1}

DynamicnetobjectSubscriberCountLevelEntry ::=
	SEQUENCE {
		dynamicnetobjectSubscriberCountLevelName	DisplayString,
		dynamicnetobjectSubscriberCountLevelVal	CounterBasedGauge64,
		dynamicnetobjectSubscriberCountLevelMax	CounterBasedGauge64
	}

dynamicnetobjectSubscriberCountLevelName OBJECT-TYPE
	SYNTAX      DisplayString
	MAX-ACCESS  not-accessible
	STATUS      current
	DESCRIPTION
	"Table entry display string for dynamicnetobjectSubscriberCount"
	::={dynamicnetobjectSubscriberCountLevelEntry 1}

dynamicnetobjectSubscriberCountLevelVal OBJECT-TYPE
	SYNTAX	 CounterBasedGauge64
	MAX-ACCESS  read-only
	STATUS      current
	DESCRIPTION
	"Table entry attribute for dynamicnetobjectSubscriberCount"
	::={dynamicnetobjectSubscriberCountLevelEntry 2}

dynamicnetobjectSubscriberCountLevelMax OBJECT-TYPE
	SYNTAX	 CounterBasedGauge64
	MAX-ACCESS  read-only
	STATUS      current
	DESCRIPTION
	"Table entry attribute for dynamicnetobjectSubscriberCount"
	::={dynamicnetobjectSubscriberCountLevelEntry 4}


dynamicnetobjectSubscriberTooMany	OBJECT IDENTIFIER ::={dynnetobjs 19}

dynamicnetobjectSubscriberTooManyVal	OBJECT-TYPE
	SYNTAX	 Counter64
	MAX-ACCESS read-only
	STATUS current
	DESCRIPTION "Subscriber: Storage for unique subscriber names is full"

	::={dynamicnetobjectSubscriberTooMany 1}

dynamicnetobjectSubscriberTooManyMom	OBJECT-TYPE
	SYNTAX	 CounterBasedGauge64
	MAX-ACCESS read-only
	STATUS current
	DESCRIPTION "Subscriber: Storage for unique subscriber names is full"

	::={dynamicnetobjectSubscriberTooMany 2}

dynamicnetobjectSubscriberTooManyMax	OBJECT-TYPE
	SYNTAX	 CounterBasedGauge64
	MAX-ACCESS read-only
	STATUS current
	DESCRIPTION "Subscriber: Storage for unique subscriber names is full"

	::={dynamicnetobjectSubscriberTooMany 3}

dynamicnetobjectSubscriberTooManyLevelTable OBJECT-TYPE
	SYNTAX      SEQUENCE OF DynamicnetobjectSubscriberTooManyLevelEntry
	MAX-ACCESS  not-accessible
	STATUS      current
	DESCRIPTION
	"Table for dynamicnetobjectSubscriberTooMany"
	::={dynamicnetobjectSubscriberTooMany 4}

dynamicnetobjectSubscriberTooManyLevelEntry OBJECT-TYPE
	SYNTAX      DynamicnetobjectSubscriberTooManyLevelEntry
	MAX-ACCESS  not-accessible
	STATUS      current
	DESCRIPTION
	"Table entry for dynamicnetobjectSubscriberTooMany"
	INDEX { dynamicnetobjectSubscriberTooManyLevelName }
	::={dynamicnetobjectSubscriberTooManyLevelTable 1}

DynamicnetobjectSubscriberTooManyLevelEntry ::=
	SEQUENCE {
		dynamicnetobjectSubscriberTooManyLevelName	DisplayString,
		dynamicnetobjectSubscriberTooManyLevelVal	Counter64,
		dynamicnetobjectSubscriberTooManyLevelMom	CounterBasedGauge64,
		dynamicnetobjectSubscriberTooManyLevelMax	CounterBasedGauge64
	}

dynamicnetobjectSubscriberTooManyLevelName OBJECT-TYPE
	SYNTAX      DisplayString
	MAX-ACCESS  not-accessible
	STATUS      current
	DESCRIPTION
	"Table entry display string for dynamicnetobjectSubscriberTooMany"
	::={dynamicnetobjectSubscriberTooManyLevelEntry 1}

dynamicnetobjectSubscriberTooManyLevelVal OBJECT-TYPE
	SYNTAX	 Counter64
	MAX-ACCESS  read-only
	STATUS      current
	DESCRIPTION
	"Table entry attribute for dynamicnetobjectSubscriberTooMany"
	::={dynamicnetobjectSubscriberTooManyLevelEntry 2}

dynamicnetobjectSubscriberTooManyLevelMom OBJECT-TYPE
	SYNTAX	 CounterBasedGauge64
	MAX-ACCESS  read-only
	STATUS      current
	DESCRIPTION
	"Table entry attribute for dynamicnetobjectSubscriberTooMany"
	::={dynamicnetobjectSubscriberTooManyLevelEntry 3}

dynamicnetobjectSubscriberTooManyLevelMax OBJECT-TYPE
	SYNTAX	 CounterBasedGauge64
	MAX-ACCESS  read-only
	STATUS      current
	DESCRIPTION
	"Table entry attribute for dynamicnetobjectSubscriberTooMany"
	::={dynamicnetobjectSubscriberTooManyLevelEntry 4}


dynamicnetobjectSaveLast	OBJECT IDENTIFIER ::={dynnetobjs 60}

dynamicnetobjectSaveLastVal	OBJECT-TYPE
	SYNTAX	 DateAndTime
	MAX-ACCESS read-only
	STATUS current
	DESCRIPTION "Save: Last time saved to disk"

	::={dynamicnetobjectSaveLast 1}

dynamicnetobjectSaveLastLevelTable OBJECT-TYPE
	SYNTAX      SEQUENCE OF DynamicnetobjectSaveLastLevelEntry
	MAX-ACCESS  not-accessible
	STATUS      current
	DESCRIPTION
	"Table for dynamicnetobjectSaveLast"
	::={dynamicnetobjectSaveLast 2}

dynamicnetobjectSaveLastLevelEntry OBJECT-TYPE
	SYNTAX      DynamicnetobjectSaveLastLevelEntry
	MAX-ACCESS  not-accessible
	STATUS      current
	DESCRIPTION
	"Table entry for dynamicnetobjectSaveLast"
	INDEX { dynamicnetobjectSaveLastLevelName }
	::={dynamicnetobjectSaveLastLevelTable 1}

DynamicnetobjectSaveLastLevelEntry ::=
	SEQUENCE {
		dynamicnetobjectSaveLastLevelName	DisplayString,
		dynamicnetobjectSaveLastLevelVal	DateAndTime
	}

dynamicnetobjectSaveLastLevelName OBJECT-TYPE
	SYNTAX      DisplayString
	MAX-ACCESS  not-accessible
	STATUS      current
	DESCRIPTION
	"Table entry display string for dynamicnetobjectSaveLast"
	::={dynamicnetobjectSaveLastLevelEntry 1}

dynamicnetobjectSaveLastLevelVal OBJECT-TYPE
	SYNTAX	 DateAndTime
	MAX-ACCESS  read-only
	STATUS      current
	DESCRIPTION
	"Table entry attribute for dynamicnetobjectSaveLast"
	::={dynamicnetobjectSaveLastLevelEntry 2}


dynamicnetobjectSaveTime	OBJECT IDENTIFIER ::={dynnetobjs 61}

dynamicnetobjectSaveTimeVal	OBJECT-TYPE
	SYNTAX	 CounterBasedGauge64
	MAX-ACCESS read-only
	STATUS current
	DESCRIPTION "Save: Milliseconds it took to save to disk"

	::={dynamicnetobjectSaveTime 1}

dynamicnetobjectSaveTimeMax	OBJECT-TYPE
	SYNTAX	 CounterBasedGauge64
	MAX-ACCESS read-only
	STATUS current
	DESCRIPTION "Save: Milliseconds it took to save to disk"

	::={dynamicnetobjectSaveTime 3}

dynamicnetobjectSaveTimeLevelTable OBJECT-TYPE
	SYNTAX      SEQUENCE OF DynamicnetobjectSaveTimeLevelEntry
	MAX-ACCESS  not-accessible
	STATUS      current
	DESCRIPTION
	"Table for dynamicnetobjectSaveTime"
	::={dynamicnetobjectSaveTime 4}

dynamicnetobjectSaveTimeLevelEntry OBJECT-TYPE
	SYNTAX      DynamicnetobjectSaveTimeLevelEntry
	MAX-ACCESS  not-accessible
	STATUS      current
	DESCRIPTION
	"Table entry for dynamicnetobjectSaveTime"
	INDEX { dynamicnetobjectSaveTimeLevelName }
	::={dynamicnetobjectSaveTimeLevelTable 1}

DynamicnetobjectSaveTimeLevelEntry ::=
	SEQUENCE {
		dynamicnetobjectSaveTimeLevelName	DisplayString,
		dynamicnetobjectSaveTimeLevelVal	CounterBasedGauge64,
		dynamicnetobjectSaveTimeLevelMax	CounterBasedGauge64
	}

dynamicnetobjectSaveTimeLevelName OBJECT-TYPE
	SYNTAX      DisplayString
	MAX-ACCESS  not-accessible
	STATUS      current
	DESCRIPTION
	"Table entry display string for dynamicnetobjectSaveTime"
	::={dynamicnetobjectSaveTimeLevelEntry 1}

dynamicnetobjectSaveTimeLevelVal OBJECT-TYPE
	SYNTAX	 CounterBasedGauge64
	MAX-ACCESS  read-only
	STATUS      current
	DESCRIPTION
	"Table entry attribute for dynamicnetobjectSaveTime"
	::={dynamicnetobjectSaveTimeLevelEntry 2}

dynamicnetobjectSaveTimeLevelMax OBJECT-TYPE
	SYNTAX	 CounterBasedGauge64
	MAX-ACCESS  read-only
	STATUS      current
	DESCRIPTION
	"Table entry attribute for dynamicnetobjectSaveTime"
	::={dynamicnetobjectSaveTimeLevelEntry 4}


dynamicnetobjectAddCalls	OBJECT IDENTIFIER ::={dynnetobjs 11}

dynamicnetobjectAddCallsVal	OBJECT-TYPE
	SYNTAX	 Counter64
	MAX-ACCESS read-only
	STATUS current
	DESCRIPTION "Oper ADD: Add calls"

	::={dynamicnetobjectAddCalls 1}

dynamicnetobjectAddCallsMom	OBJECT-TYPE
	SYNTAX	 CounterBasedGauge64
	MAX-ACCESS read-only
	STATUS current
	DESCRIPTION "Oper ADD: Add calls"

	::={dynamicnetobjectAddCalls 2}

dynamicnetobjectAddCallsMax	OBJECT-TYPE
	SYNTAX	 CounterBasedGauge64
	MAX-ACCESS read-only
	STATUS current
	DESCRIPTION "Oper ADD: Add calls"

	::={dynamicnetobjectAddCalls 3}

dynamicnetobjectAddCallsLevelTable OBJECT-TYPE
	SYNTAX      SEQUENCE OF DynamicnetobjectAddCallsLevelEntry
	MAX-ACCESS  not-accessible
	STATUS      current
	DESCRIPTION
	"Table for dynamicnetobjectAddCalls"
	::={dynamicnetobjectAddCalls 4}

dynamicnetobjectAddCallsLevelEntry OBJECT-TYPE
	SYNTAX      DynamicnetobjectAddCallsLevelEntry
	MAX-ACCESS  not-accessible
	STATUS      current
	DESCRIPTION
	"Table entry for dynamicnetobjectAddCalls"
	INDEX { dynamicnetobjectAddCallsLevelName }
	::={dynamicnetobjectAddCallsLevelTable 1}

DynamicnetobjectAddCallsLevelEntry ::=
	SEQUENCE {
		dynamicnetobjectAddCallsLevelName	DisplayString,
		dynamicnetobjectAddCallsLevelVal	Counter64,
		dynamicnetobjectAddCallsLevelMom	CounterBasedGauge64,
		dynamicnetobjectAddCallsLevelMax	CounterBasedGauge64
	}

dynamicnetobjectAddCallsLevelName OBJECT-TYPE
	SYNTAX      DisplayString
	MAX-ACCESS  not-accessible
	STATUS      current
	DESCRIPTION
	"Table entry display string for dynamicnetobjectAddCalls"
	::={dynamicnetobjectAddCallsLevelEntry 1}

dynamicnetobjectAddCallsLevelVal OBJECT-TYPE
	SYNTAX	 Counter64
	MAX-ACCESS  read-only
	STATUS      current
	DESCRIPTION
	"Table entry attribute for dynamicnetobjectAddCalls"
	::={dynamicnetobjectAddCallsLevelEntry 2}

dynamicnetobjectAddCallsLevelMom OBJECT-TYPE
	SYNTAX	 CounterBasedGauge64
	MAX-ACCESS  read-only
	STATUS      current
	DESCRIPTION
	"Table entry attribute for dynamicnetobjectAddCalls"
	::={dynamicnetobjectAddCallsLevelEntry 3}

dynamicnetobjectAddCallsLevelMax OBJECT-TYPE
	SYNTAX	 CounterBasedGauge64
	MAX-ACCESS  read-only
	STATUS      current
	DESCRIPTION
	"Table entry attribute for dynamicnetobjectAddCalls"
	::={dynamicnetobjectAddCallsLevelEntry 4}


dynamicnetobjectAddFailed	OBJECT IDENTIFIER ::={dynnetobjs 9}

dynamicnetobjectAddFailedVal	OBJECT-TYPE
	SYNTAX	 Counter64
	MAX-ACCESS read-only
	STATUS current
	DESCRIPTION "Oper ADD: Add calls failed"

	::={dynamicnetobjectAddFailed 1}

dynamicnetobjectAddFailedMom	OBJECT-TYPE
	SYNTAX	 CounterBasedGauge64
	MAX-ACCESS read-only
	STATUS current
	DESCRIPTION "Oper ADD: Add calls failed"

	::={dynamicnetobjectAddFailed 2}

dynamicnetobjectAddFailedMax	OBJECT-TYPE
	SYNTAX	 CounterBasedGauge64
	MAX-ACCESS read-only
	STATUS current
	DESCRIPTION "Oper ADD: Add calls failed"

	::={dynamicnetobjectAddFailed 3}

dynamicnetobjectAddFailedLevelTable OBJECT-TYPE
	SYNTAX      SEQUENCE OF DynamicnetobjectAddFailedLevelEntry
	MAX-ACCESS  not-accessible
	STATUS      current
	DESCRIPTION
	"Table for dynamicnetobjectAddFailed"
	::={dynamicnetobjectAddFailed 4}

dynamicnetobjectAddFailedLevelEntry OBJECT-TYPE
	SYNTAX      DynamicnetobjectAddFailedLevelEntry
	MAX-ACCESS  not-accessible
	STATUS      current
	DESCRIPTION
	"Table entry for dynamicnetobjectAddFailed"
	INDEX { dynamicnetobjectAddFailedLevelName }
	::={dynamicnetobjectAddFailedLevelTable 1}

DynamicnetobjectAddFailedLevelEntry ::=
	SEQUENCE {
		dynamicnetobjectAddFailedLevelName	DisplayString,
		dynamicnetobjectAddFailedLevelVal	Counter64,
		dynamicnetobjectAddFailedLevelMom	CounterBasedGauge64,
		dynamicnetobjectAddFailedLevelMax	CounterBasedGauge64
	}

dynamicnetobjectAddFailedLevelName OBJECT-TYPE
	SYNTAX      DisplayString
	MAX-ACCESS  not-accessible
	STATUS      current
	DESCRIPTION
	"Table entry display string for dynamicnetobjectAddFailed"
	::={dynamicnetobjectAddFailedLevelEntry 1}

dynamicnetobjectAddFailedLevelVal OBJECT-TYPE
	SYNTAX	 Counter64
	MAX-ACCESS  read-only
	STATUS      current
	DESCRIPTION
	"Table entry attribute for dynamicnetobjectAddFailed"
	::={dynamicnetobjectAddFailedLevelEntry 2}

dynamicnetobjectAddFailedLevelMom OBJECT-TYPE
	SYNTAX	 CounterBasedGauge64
	MAX-ACCESS  read-only
	STATUS      current
	DESCRIPTION
	"Table entry attribute for dynamicnetobjectAddFailed"
	::={dynamicnetobjectAddFailedLevelEntry 3}

dynamicnetobjectAddFailedLevelMax OBJECT-TYPE
	SYNTAX	 CounterBasedGauge64
	MAX-ACCESS  read-only
	STATUS      current
	DESCRIPTION
	"Table entry attribute for dynamicnetobjectAddFailed"
	::={dynamicnetobjectAddFailedLevelEntry 4}


dynamicnetobjectRemoveCalls	OBJECT IDENTIFIER ::={dynnetobjs 12}

dynamicnetobjectRemoveCallsVal	OBJECT-TYPE
	SYNTAX	 Counter64
	MAX-ACCESS read-only
	STATUS current
	DESCRIPTION "Oper REMOVE: Remove calls"

	::={dynamicnetobjectRemoveCalls 1}

dynamicnetobjectRemoveCallsMom	OBJECT-TYPE
	SYNTAX	 CounterBasedGauge64
	MAX-ACCESS read-only
	STATUS current
	DESCRIPTION "Oper REMOVE: Remove calls"

	::={dynamicnetobjectRemoveCalls 2}

dynamicnetobjectRemoveCallsMax	OBJECT-TYPE
	SYNTAX	 CounterBasedGauge64
	MAX-ACCESS read-only
	STATUS current
	DESCRIPTION "Oper REMOVE: Remove calls"

	::={dynamicnetobjectRemoveCalls 3}

dynamicnetobjectRemoveCallsLevelTable OBJECT-TYPE
	SYNTAX      SEQUENCE OF DynamicnetobjectRemoveCallsLevelEntry
	MAX-ACCESS  not-accessible
	STATUS      current
	DESCRIPTION
	"Table for dynamicnetobjectRemoveCalls"
	::={dynamicnetobjectRemoveCalls 4}

dynamicnetobjectRemoveCallsLevelEntry OBJECT-TYPE
	SYNTAX      DynamicnetobjectRemoveCallsLevelEntry
	MAX-ACCESS  not-accessible
	STATUS      current
	DESCRIPTION
	"Table entry for dynamicnetobjectRemoveCalls"
	INDEX { dynamicnetobjectRemoveCallsLevelName }
	::={dynamicnetobjectRemoveCallsLevelTable 1}

DynamicnetobjectRemoveCallsLevelEntry ::=
	SEQUENCE {
		dynamicnetobjectRemoveCallsLevelName	DisplayString,
		dynamicnetobjectRemoveCallsLevelVal	Counter64,
		dynamicnetobjectRemoveCallsLevelMom	CounterBasedGauge64,
		dynamicnetobjectRemoveCallsLevelMax	CounterBasedGauge64
	}

dynamicnetobjectRemoveCallsLevelName OBJECT-TYPE
	SYNTAX      DisplayString
	MAX-ACCESS  not-accessible
	STATUS      current
	DESCRIPTION
	"Table entry display string for dynamicnetobjectRemoveCalls"
	::={dynamicnetobjectRemoveCallsLevelEntry 1}

dynamicnetobjectRemoveCallsLevelVal OBJECT-TYPE
	SYNTAX	 Counter64
	MAX-ACCESS  read-only
	STATUS      current
	DESCRIPTION
	"Table entry attribute for dynamicnetobjectRemoveCalls"
	::={dynamicnetobjectRemoveCallsLevelEntry 2}

dynamicnetobjectRemoveCallsLevelMom OBJECT-TYPE
	SYNTAX	 CounterBasedGauge64
	MAX-ACCESS  read-only
	STATUS      current
	DESCRIPTION
	"Table entry attribute for dynamicnetobjectRemoveCalls"
	::={dynamicnetobjectRemoveCallsLevelEntry 3}

dynamicnetobjectRemoveCallsLevelMax OBJECT-TYPE
	SYNTAX	 CounterBasedGauge64
	MAX-ACCESS  read-only
	STATUS      current
	DESCRIPTION
	"Table entry attribute for dynamicnetobjectRemoveCalls"
	::={dynamicnetobjectRemoveCallsLevelEntry 4}


dynamicnetobjectRemoveFailed	OBJECT IDENTIFIER ::={dynnetobjs 4}

dynamicnetobjectRemoveFailedVal	OBJECT-TYPE
	SYNTAX	 Counter64
	MAX-ACCESS read-only
	STATUS current
	DESCRIPTION "Oper REMOVE: Remove calls failed"

	::={dynamicnetobjectRemoveFailed 1}

dynamicnetobjectRemoveFailedMom	OBJECT-TYPE
	SYNTAX	 CounterBasedGauge64
	MAX-ACCESS read-only
	STATUS current
	DESCRIPTION "Oper REMOVE: Remove calls failed"

	::={dynamicnetobjectRemoveFailed 2}

dynamicnetobjectRemoveFailedMax	OBJECT-TYPE
	SYNTAX	 CounterBasedGauge64
	MAX-ACCESS read-only
	STATUS current
	DESCRIPTION "Oper REMOVE: Remove calls failed"

	::={dynamicnetobjectRemoveFailed 3}

dynamicnetobjectRemoveFailedLevelTable OBJECT-TYPE
	SYNTAX      SEQUENCE OF DynamicnetobjectRemoveFailedLevelEntry
	MAX-ACCESS  not-accessible
	STATUS      current
	DESCRIPTION
	"Table for dynamicnetobjectRemoveFailed"
	::={dynamicnetobjectRemoveFailed 4}

dynamicnetobjectRemoveFailedLevelEntry OBJECT-TYPE
	SYNTAX      DynamicnetobjectRemoveFailedLevelEntry
	MAX-ACCESS  not-accessible
	STATUS      current
	DESCRIPTION
	"Table entry for dynamicnetobjectRemoveFailed"
	INDEX { dynamicnetobjectRemoveFailedLevelName }
	::={dynamicnetobjectRemoveFailedLevelTable 1}

DynamicnetobjectRemoveFailedLevelEntry ::=
	SEQUENCE {
		dynamicnetobjectRemoveFailedLevelName	DisplayString,
		dynamicnetobjectRemoveFailedLevelVal	Counter64,
		dynamicnetobjectRemoveFailedLevelMom	CounterBasedGauge64,
		dynamicnetobjectRemoveFailedLevelMax	CounterBasedGauge64
	}

dynamicnetobjectRemoveFailedLevelName OBJECT-TYPE
	SYNTAX      DisplayString
	MAX-ACCESS  not-accessible
	STATUS      current
	DESCRIPTION
	"Table entry display string for dynamicnetobjectRemoveFailed"
	::={dynamicnetobjectRemoveFailedLevelEntry 1}

dynamicnetobjectRemoveFailedLevelVal OBJECT-TYPE
	SYNTAX	 Counter64
	MAX-ACCESS  read-only
	STATUS      current
	DESCRIPTION
	"Table entry attribute for dynamicnetobjectRemoveFailed"
	::={dynamicnetobjectRemoveFailedLevelEntry 2}

dynamicnetobjectRemoveFailedLevelMom OBJECT-TYPE
	SYNTAX	 CounterBasedGauge64
	MAX-ACCESS  read-only
	STATUS      current
	DESCRIPTION
	"Table entry attribute for dynamicnetobjectRemoveFailed"
	::={dynamicnetobjectRemoveFailedLevelEntry 3}

dynamicnetobjectRemoveFailedLevelMax OBJECT-TYPE
	SYNTAX	 CounterBasedGauge64
	MAX-ACCESS  read-only
	STATUS      current
	DESCRIPTION
	"Table entry attribute for dynamicnetobjectRemoveFailed"
	::={dynamicnetobjectRemoveFailedLevelEntry 4}


dynamicnetobjectListCalls	OBJECT IDENTIFIER ::={dynnetobjs 15}

dynamicnetobjectListCallsVal	OBJECT-TYPE
	SYNTAX	 Counter64
	MAX-ACCESS read-only
	STATUS current
	DESCRIPTION "Oper LIST: List calls"

	::={dynamicnetobjectListCalls 1}

dynamicnetobjectListCallsMom	OBJECT-TYPE
	SYNTAX	 CounterBasedGauge64
	MAX-ACCESS read-only
	STATUS current
	DESCRIPTION "Oper LIST: List calls"

	::={dynamicnetobjectListCalls 2}

dynamicnetobjectListCallsMax	OBJECT-TYPE
	SYNTAX	 CounterBasedGauge64
	MAX-ACCESS read-only
	STATUS current
	DESCRIPTION "Oper LIST: List calls"

	::={dynamicnetobjectListCalls 3}

dynamicnetobjectListCallsLevelTable OBJECT-TYPE
	SYNTAX      SEQUENCE OF DynamicnetobjectListCallsLevelEntry
	MAX-ACCESS  not-accessible
	STATUS      current
	DESCRIPTION
	"Table for dynamicnetobjectListCalls"
	::={dynamicnetobjectListCalls 4}

dynamicnetobjectListCallsLevelEntry OBJECT-TYPE
	SYNTAX      DynamicnetobjectListCallsLevelEntry
	MAX-ACCESS  not-accessible
	STATUS      current
	DESCRIPTION
	"Table entry for dynamicnetobjectListCalls"
	INDEX { dynamicnetobjectListCallsLevelName }
	::={dynamicnetobjectListCallsLevelTable 1}

DynamicnetobjectListCallsLevelEntry ::=
	SEQUENCE {
		dynamicnetobjectListCallsLevelName	DisplayString,
		dynamicnetobjectListCallsLevelVal	Counter64,
		dynamicnetobjectListCallsLevelMom	CounterBasedGauge64,
		dynamicnetobjectListCallsLevelMax	CounterBasedGauge64
	}

dynamicnetobjectListCallsLevelName OBJECT-TYPE
	SYNTAX      DisplayString
	MAX-ACCESS  not-accessible
	STATUS      current
	DESCRIPTION
	"Table entry display string for dynamicnetobjectListCalls"
	::={dynamicnetobjectListCallsLevelEntry 1}

dynamicnetobjectListCallsLevelVal OBJECT-TYPE
	SYNTAX	 Counter64
	MAX-ACCESS  read-only
	STATUS      current
	DESCRIPTION
	"Table entry attribute for dynamicnetobjectListCalls"
	::={dynamicnetobjectListCallsLevelEntry 2}

dynamicnetobjectListCallsLevelMom OBJECT-TYPE
	SYNTAX	 CounterBasedGauge64
	MAX-ACCESS  read-only
	STATUS      current
	DESCRIPTION
	"Table entry attribute for dynamicnetobjectListCalls"
	::={dynamicnetobjectListCallsLevelEntry 3}

dynamicnetobjectListCallsLevelMax OBJECT-TYPE
	SYNTAX	 CounterBasedGauge64
	MAX-ACCESS  read-only
	STATUS      current
	DESCRIPTION
	"Table entry attribute for dynamicnetobjectListCalls"
	::={dynamicnetobjectListCallsLevelEntry 4}


dynamicnetobjectListFailed	OBJECT IDENTIFIER ::={dynnetobjs 44}

dynamicnetobjectListFailedVal	OBJECT-TYPE
	SYNTAX	 Counter64
	MAX-ACCESS read-only
	STATUS current
	DESCRIPTION "Oper LIST: List calls failed"

	::={dynamicnetobjectListFailed 1}

dynamicnetobjectListFailedMom	OBJECT-TYPE
	SYNTAX	 CounterBasedGauge64
	MAX-ACCESS read-only
	STATUS current
	DESCRIPTION "Oper LIST: List calls failed"

	::={dynamicnetobjectListFailed 2}

dynamicnetobjectListFailedMax	OBJECT-TYPE
	SYNTAX	 CounterBasedGauge64
	MAX-ACCESS read-only
	STATUS current
	DESCRIPTION "Oper LIST: List calls failed"

	::={dynamicnetobjectListFailed 3}

dynamicnetobjectListFailedLevelTable OBJECT-TYPE
	SYNTAX      SEQUENCE OF DynamicnetobjectListFailedLevelEntry
	MAX-ACCESS  not-accessible
	STATUS      current
	DESCRIPTION
	"Table for dynamicnetobjectListFailed"
	::={dynamicnetobjectListFailed 4}

dynamicnetobjectListFailedLevelEntry OBJECT-TYPE
	SYNTAX      DynamicnetobjectListFailedLevelEntry
	MAX-ACCESS  not-accessible
	STATUS      current
	DESCRIPTION
	"Table entry for dynamicnetobjectListFailed"
	INDEX { dynamicnetobjectListFailedLevelName }
	::={dynamicnetobjectListFailedLevelTable 1}

DynamicnetobjectListFailedLevelEntry ::=
	SEQUENCE {
		dynamicnetobjectListFailedLevelName	DisplayString,
		dynamicnetobjectListFailedLevelVal	Counter64,
		dynamicnetobjectListFailedLevelMom	CounterBasedGauge64,
		dynamicnetobjectListFailedLevelMax	CounterBasedGauge64
	}

dynamicnetobjectListFailedLevelName OBJECT-TYPE
	SYNTAX      DisplayString
	MAX-ACCESS  not-accessible
	STATUS      current
	DESCRIPTION
	"Table entry display string for dynamicnetobjectListFailed"
	::={dynamicnetobjectListFailedLevelEntry 1}

dynamicnetobjectListFailedLevelVal OBJECT-TYPE
	SYNTAX	 Counter64
	MAX-ACCESS  read-only
	STATUS      current
	DESCRIPTION
	"Table entry attribute for dynamicnetobjectListFailed"
	::={dynamicnetobjectListFailedLevelEntry 2}

dynamicnetobjectListFailedLevelMom OBJECT-TYPE
	SYNTAX	 CounterBasedGauge64
	MAX-ACCESS  read-only
	STATUS      current
	DESCRIPTION
	"Table entry attribute for dynamicnetobjectListFailed"
	::={dynamicnetobjectListFailedLevelEntry 3}

dynamicnetobjectListFailedLevelMax OBJECT-TYPE
	SYNTAX	 CounterBasedGauge64
	MAX-ACCESS  read-only
	STATUS      current
	DESCRIPTION
	"Table entry attribute for dynamicnetobjectListFailed"
	::={dynamicnetobjectListFailedLevelEntry 4}


dynamicnetobjectSetCalls	OBJECT IDENTIFIER ::={dynnetobjs 30}

dynamicnetobjectSetCallsVal	OBJECT-TYPE
	SYNTAX	 Counter64
	MAX-ACCESS read-only
	STATUS current
	DESCRIPTION "Oper SET: Set calls"

	::={dynamicnetobjectSetCalls 1}

dynamicnetobjectSetCallsMom	OBJECT-TYPE
	SYNTAX	 CounterBasedGauge64
	MAX-ACCESS read-only
	STATUS current
	DESCRIPTION "Oper SET: Set calls"

	::={dynamicnetobjectSetCalls 2}

dynamicnetobjectSetCallsMax	OBJECT-TYPE
	SYNTAX	 CounterBasedGauge64
	MAX-ACCESS read-only
	STATUS current
	DESCRIPTION "Oper SET: Set calls"

	::={dynamicnetobjectSetCalls 3}

dynamicnetobjectSetCallsLevelTable OBJECT-TYPE
	SYNTAX      SEQUENCE OF DynamicnetobjectSetCallsLevelEntry
	MAX-ACCESS  not-accessible
	STATUS      current
	DESCRIPTION
	"Table for dynamicnetobjectSetCalls"
	::={dynamicnetobjectSetCalls 4}

dynamicnetobjectSetCallsLevelEntry OBJECT-TYPE
	SYNTAX      DynamicnetobjectSetCallsLevelEntry
	MAX-ACCESS  not-accessible
	STATUS      current
	DESCRIPTION
	"Table entry for dynamicnetobjectSetCalls"
	INDEX { dynamicnetobjectSetCallsLevelName }
	::={dynamicnetobjectSetCallsLevelTable 1}

DynamicnetobjectSetCallsLevelEntry ::=
	SEQUENCE {
		dynamicnetobjectSetCallsLevelName	DisplayString,
		dynamicnetobjectSetCallsLevelVal	Counter64,
		dynamicnetobjectSetCallsLevelMom	CounterBasedGauge64,
		dynamicnetobjectSetCallsLevelMax	CounterBasedGauge64
	}

dynamicnetobjectSetCallsLevelName OBJECT-TYPE
	SYNTAX      DisplayString
	MAX-ACCESS  not-accessible
	STATUS      current
	DESCRIPTION
	"Table entry display string for dynamicnetobjectSetCalls"
	::={dynamicnetobjectSetCallsLevelEntry 1}

dynamicnetobjectSetCallsLevelVal OBJECT-TYPE
	SYNTAX	 Counter64
	MAX-ACCESS  read-only
	STATUS      current
	DESCRIPTION
	"Table entry attribute for dynamicnetobjectSetCalls"
	::={dynamicnetobjectSetCallsLevelEntry 2}

dynamicnetobjectSetCallsLevelMom OBJECT-TYPE
	SYNTAX	 CounterBasedGauge64
	MAX-ACCESS  read-only
	STATUS      current
	DESCRIPTION
	"Table entry attribute for dynamicnetobjectSetCalls"
	::={dynamicnetobjectSetCallsLevelEntry 3}

dynamicnetobjectSetCallsLevelMax OBJECT-TYPE
	SYNTAX	 CounterBasedGauge64
	MAX-ACCESS  read-only
	STATUS      current
	DESCRIPTION
	"Table entry attribute for dynamicnetobjectSetCalls"
	::={dynamicnetobjectSetCallsLevelEntry 4}


dynamicnetobjectSetFailed	OBJECT IDENTIFIER ::={dynnetobjs 32}

dynamicnetobjectSetFailedVal	OBJECT-TYPE
	SYNTAX	 Counter64
	MAX-ACCESS read-only
	STATUS current
	DESCRIPTION "Oper SET: Set calls failed"

	::={dynamicnetobjectSetFailed 1}

dynamicnetobjectSetFailedMom	OBJECT-TYPE
	SYNTAX	 CounterBasedGauge64
	MAX-ACCESS read-only
	STATUS current
	DESCRIPTION "Oper SET: Set calls failed"

	::={dynamicnetobjectSetFailed 2}

dynamicnetobjectSetFailedMax	OBJECT-TYPE
	SYNTAX	 CounterBasedGauge64
	MAX-ACCESS read-only
	STATUS current
	DESCRIPTION "Oper SET: Set calls failed"

	::={dynamicnetobjectSetFailed 3}

dynamicnetobjectSetFailedLevelTable OBJECT-TYPE
	SYNTAX      SEQUENCE OF DynamicnetobjectSetFailedLevelEntry
	MAX-ACCESS  not-accessible
	STATUS      current
	DESCRIPTION
	"Table for dynamicnetobjectSetFailed"
	::={dynamicnetobjectSetFailed 4}

dynamicnetobjectSetFailedLevelEntry OBJECT-TYPE
	SYNTAX      DynamicnetobjectSetFailedLevelEntry
	MAX-ACCESS  not-accessible
	STATUS      current
	DESCRIPTION
	"Table entry for dynamicnetobjectSetFailed"
	INDEX { dynamicnetobjectSetFailedLevelName }
	::={dynamicnetobjectSetFailedLevelTable 1}

DynamicnetobjectSetFailedLevelEntry ::=
	SEQUENCE {
		dynamicnetobjectSetFailedLevelName	DisplayString,
		dynamicnetobjectSetFailedLevelVal	Counter64,
		dynamicnetobjectSetFailedLevelMom	CounterBasedGauge64,
		dynamicnetobjectSetFailedLevelMax	CounterBasedGauge64
	}

dynamicnetobjectSetFailedLevelName OBJECT-TYPE
	SYNTAX      DisplayString
	MAX-ACCESS  not-accessible
	STATUS      current
	DESCRIPTION
	"Table entry display string for dynamicnetobjectSetFailed"
	::={dynamicnetobjectSetFailedLevelEntry 1}

dynamicnetobjectSetFailedLevelVal OBJECT-TYPE
	SYNTAX	 Counter64
	MAX-ACCESS  read-only
	STATUS      current
	DESCRIPTION
	"Table entry attribute for dynamicnetobjectSetFailed"
	::={dynamicnetobjectSetFailedLevelEntry 2}

dynamicnetobjectSetFailedLevelMom OBJECT-TYPE
	SYNTAX	 CounterBasedGauge64
	MAX-ACCESS  read-only
	STATUS      current
	DESCRIPTION
	"Table entry attribute for dynamicnetobjectSetFailed"
	::={dynamicnetobjectSetFailedLevelEntry 3}

dynamicnetobjectSetFailedLevelMax OBJECT-TYPE
	SYNTAX	 CounterBasedGauge64
	MAX-ACCESS  read-only
	STATUS      current
	DESCRIPTION
	"Table entry attribute for dynamicnetobjectSetFailed"
	::={dynamicnetobjectSetFailedLevelEntry 4}


dynamicnetobjectSetAdded	OBJECT IDENTIFIER ::={dynnetobjs 27}

dynamicnetobjectSetAddedVal	OBJECT-TYPE
	SYNTAX	 Counter64
	MAX-ACCESS read-only
	STATUS current
	DESCRIPTION "Oper SET: Dynamic netobject items ADDED during set operations"

	::={dynamicnetobjectSetAdded 1}

dynamicnetobjectSetAddedMom	OBJECT-TYPE
	SYNTAX	 CounterBasedGauge64
	MAX-ACCESS read-only
	STATUS current
	DESCRIPTION "Oper SET: Dynamic netobject items ADDED during set operations"

	::={dynamicnetobjectSetAdded 2}

dynamicnetobjectSetAddedMax	OBJECT-TYPE
	SYNTAX	 CounterBasedGauge64
	MAX-ACCESS read-only
	STATUS current
	DESCRIPTION "Oper SET: Dynamic netobject items ADDED during set operations"

	::={dynamicnetobjectSetAdded 3}

dynamicnetobjectSetAddedLevelTable OBJECT-TYPE
	SYNTAX      SEQUENCE OF DynamicnetobjectSetAddedLevelEntry
	MAX-ACCESS  not-accessible
	STATUS      current
	DESCRIPTION
	"Table for dynamicnetobjectSetAdded"
	::={dynamicnetobjectSetAdded 4}

dynamicnetobjectSetAddedLevelEntry OBJECT-TYPE
	SYNTAX      DynamicnetobjectSetAddedLevelEntry
	MAX-ACCESS  not-accessible
	STATUS      current
	DESCRIPTION
	"Table entry for dynamicnetobjectSetAdded"
	INDEX { dynamicnetobjectSetAddedLevelName }
	::={dynamicnetobjectSetAddedLevelTable 1}

DynamicnetobjectSetAddedLevelEntry ::=
	SEQUENCE {
		dynamicnetobjectSetAddedLevelName	DisplayString,
		dynamicnetobjectSetAddedLevelVal	Counter64,
		dynamicnetobjectSetAddedLevelMom	CounterBasedGauge64,
		dynamicnetobjectSetAddedLevelMax	CounterBasedGauge64
	}

dynamicnetobjectSetAddedLevelName OBJECT-TYPE
	SYNTAX      DisplayString
	MAX-ACCESS  not-accessible
	STATUS      current
	DESCRIPTION
	"Table entry display string for dynamicnetobjectSetAdded"
	::={dynamicnetobjectSetAddedLevelEntry 1}

dynamicnetobjectSetAddedLevelVal OBJECT-TYPE
	SYNTAX	 Counter64
	MAX-ACCESS  read-only
	STATUS      current
	DESCRIPTION
	"Table entry attribute for dynamicnetobjectSetAdded"
	::={dynamicnetobjectSetAddedLevelEntry 2}

dynamicnetobjectSetAddedLevelMom OBJECT-TYPE
	SYNTAX	 CounterBasedGauge64
	MAX-ACCESS  read-only
	STATUS      current
	DESCRIPTION
	"Table entry attribute for dynamicnetobjectSetAdded"
	::={dynamicnetobjectSetAddedLevelEntry 3}

dynamicnetobjectSetAddedLevelMax OBJECT-TYPE
	SYNTAX	 CounterBasedGauge64
	MAX-ACCESS  read-only
	STATUS      current
	DESCRIPTION
	"Table entry attribute for dynamicnetobjectSetAdded"
	::={dynamicnetobjectSetAddedLevelEntry 4}


dynamicnetobjectSetRemoved	OBJECT IDENTIFIER ::={dynnetobjs 28}

dynamicnetobjectSetRemovedVal	OBJECT-TYPE
	SYNTAX	 Counter64
	MAX-ACCESS read-only
	STATUS current
	DESCRIPTION "Oper SET: Dynamic netobject items REMOVED during set operations"

	::={dynamicnetobjectSetRemoved 1}

dynamicnetobjectSetRemovedMom	OBJECT-TYPE
	SYNTAX	 CounterBasedGauge64
	MAX-ACCESS read-only
	STATUS current
	DESCRIPTION "Oper SET: Dynamic netobject items REMOVED during set operations"

	::={dynamicnetobjectSetRemoved 2}

dynamicnetobjectSetRemovedMax	OBJECT-TYPE
	SYNTAX	 CounterBasedGauge64
	MAX-ACCESS read-only
	STATUS current
	DESCRIPTION "Oper SET: Dynamic netobject items REMOVED during set operations"

	::={dynamicnetobjectSetRemoved 3}

dynamicnetobjectSetRemovedLevelTable OBJECT-TYPE
	SYNTAX      SEQUENCE OF DynamicnetobjectSetRemovedLevelEntry
	MAX-ACCESS  not-accessible
	STATUS      current
	DESCRIPTION
	"Table for dynamicnetobjectSetRemoved"
	::={dynamicnetobjectSetRemoved 4}

dynamicnetobjectSetRemovedLevelEntry OBJECT-TYPE
	SYNTAX      DynamicnetobjectSetRemovedLevelEntry
	MAX-ACCESS  not-accessible
	STATUS      current
	DESCRIPTION
	"Table entry for dynamicnetobjectSetRemoved"
	INDEX { dynamicnetobjectSetRemovedLevelName }
	::={dynamicnetobjectSetRemovedLevelTable 1}

DynamicnetobjectSetRemovedLevelEntry ::=
	SEQUENCE {
		dynamicnetobjectSetRemovedLevelName	DisplayString,
		dynamicnetobjectSetRemovedLevelVal	Counter64,
		dynamicnetobjectSetRemovedLevelMom	CounterBasedGauge64,
		dynamicnetobjectSetRemovedLevelMax	CounterBasedGauge64
	}

dynamicnetobjectSetRemovedLevelName OBJECT-TYPE
	SYNTAX      DisplayString
	MAX-ACCESS  not-accessible
	STATUS      current
	DESCRIPTION
	"Table entry display string for dynamicnetobjectSetRemoved"
	::={dynamicnetobjectSetRemovedLevelEntry 1}

dynamicnetobjectSetRemovedLevelVal OBJECT-TYPE
	SYNTAX	 Counter64
	MAX-ACCESS  read-only
	STATUS      current
	DESCRIPTION
	"Table entry attribute for dynamicnetobjectSetRemoved"
	::={dynamicnetobjectSetRemovedLevelEntry 2}

dynamicnetobjectSetRemovedLevelMom OBJECT-TYPE
	SYNTAX	 CounterBasedGauge64
	MAX-ACCESS  read-only
	STATUS      current
	DESCRIPTION
	"Table entry attribute for dynamicnetobjectSetRemoved"
	::={dynamicnetobjectSetRemovedLevelEntry 3}

dynamicnetobjectSetRemovedLevelMax OBJECT-TYPE
	SYNTAX	 CounterBasedGauge64
	MAX-ACCESS  read-only
	STATUS      current
	DESCRIPTION
	"Table entry attribute for dynamicnetobjectSetRemoved"
	::={dynamicnetobjectSetRemovedLevelEntry 4}


dynamicnetobjectSetReplaced	OBJECT IDENTIFIER ::={dynnetobjs 64}

dynamicnetobjectSetReplacedVal	OBJECT-TYPE
	SYNTAX	 Counter64
	MAX-ACCESS read-only
	STATUS current
	DESCRIPTION "Oper SET: Dynamic netobject items REPLACED during set operations"

	::={dynamicnetobjectSetReplaced 1}

dynamicnetobjectSetReplacedMom	OBJECT-TYPE
	SYNTAX	 CounterBasedGauge64
	MAX-ACCESS read-only
	STATUS current
	DESCRIPTION "Oper SET: Dynamic netobject items REPLACED during set operations"

	::={dynamicnetobjectSetReplaced 2}

dynamicnetobjectSetReplacedMax	OBJECT-TYPE
	SYNTAX	 CounterBasedGauge64
	MAX-ACCESS read-only
	STATUS current
	DESCRIPTION "Oper SET: Dynamic netobject items REPLACED during set operations"

	::={dynamicnetobjectSetReplaced 3}

dynamicnetobjectSetReplacedLevelTable OBJECT-TYPE
	SYNTAX      SEQUENCE OF DynamicnetobjectSetReplacedLevelEntry
	MAX-ACCESS  not-accessible
	STATUS      current
	DESCRIPTION
	"Table for dynamicnetobjectSetReplaced"
	::={dynamicnetobjectSetReplaced 4}

dynamicnetobjectSetReplacedLevelEntry OBJECT-TYPE
	SYNTAX      DynamicnetobjectSetReplacedLevelEntry
	MAX-ACCESS  not-accessible
	STATUS      current
	DESCRIPTION
	"Table entry for dynamicnetobjectSetReplaced"
	INDEX { dynamicnetobjectSetReplacedLevelName }
	::={dynamicnetobjectSetReplacedLevelTable 1}

DynamicnetobjectSetReplacedLevelEntry ::=
	SEQUENCE {
		dynamicnetobjectSetReplacedLevelName	DisplayString,
		dynamicnetobjectSetReplacedLevelVal	Counter64,
		dynamicnetobjectSetReplacedLevelMom	CounterBasedGauge64,
		dynamicnetobjectSetReplacedLevelMax	CounterBasedGauge64
	}

dynamicnetobjectSetReplacedLevelName OBJECT-TYPE
	SYNTAX      DisplayString
	MAX-ACCESS  not-accessible
	STATUS      current
	DESCRIPTION
	"Table entry display string for dynamicnetobjectSetReplaced"
	::={dynamicnetobjectSetReplacedLevelEntry 1}

dynamicnetobjectSetReplacedLevelVal OBJECT-TYPE
	SYNTAX	 Counter64
	MAX-ACCESS  read-only
	STATUS      current
	DESCRIPTION
	"Table entry attribute for dynamicnetobjectSetReplaced"
	::={dynamicnetobjectSetReplacedLevelEntry 2}

dynamicnetobjectSetReplacedLevelMom OBJECT-TYPE
	SYNTAX	 CounterBasedGauge64
	MAX-ACCESS  read-only
	STATUS      current
	DESCRIPTION
	"Table entry attribute for dynamicnetobjectSetReplaced"
	::={dynamicnetobjectSetReplacedLevelEntry 3}

dynamicnetobjectSetReplacedLevelMax OBJECT-TYPE
	SYNTAX	 CounterBasedGauge64
	MAX-ACCESS  read-only
	STATUS      current
	DESCRIPTION
	"Table entry attribute for dynamicnetobjectSetReplaced"
	::={dynamicnetobjectSetReplacedLevelEntry 4}


dynamicnetobjectSetUnchanged	OBJECT IDENTIFIER ::={dynnetobjs 29}

dynamicnetobjectSetUnchangedVal	OBJECT-TYPE
	SYNTAX	 Counter64
	MAX-ACCESS read-only
	STATUS current
	DESCRIPTION "Oper SET: Dynamic netobject items UNCHANGED during set operations"

	::={dynamicnetobjectSetUnchanged 1}

dynamicnetobjectSetUnchangedMom	OBJECT-TYPE
	SYNTAX	 CounterBasedGauge64
	MAX-ACCESS read-only
	STATUS current
	DESCRIPTION "Oper SET: Dynamic netobject items UNCHANGED during set operations"

	::={dynamicnetobjectSetUnchanged 2}

dynamicnetobjectSetUnchangedMax	OBJECT-TYPE
	SYNTAX	 CounterBasedGauge64
	MAX-ACCESS read-only
	STATUS current
	DESCRIPTION "Oper SET: Dynamic netobject items UNCHANGED during set operations"

	::={dynamicnetobjectSetUnchanged 3}

dynamicnetobjectSetUnchangedLevelTable OBJECT-TYPE
	SYNTAX      SEQUENCE OF DynamicnetobjectSetUnchangedLevelEntry
	MAX-ACCESS  not-accessible
	STATUS      current
	DESCRIPTION
	"Table for dynamicnetobjectSetUnchanged"
	::={dynamicnetobjectSetUnchanged 4}

dynamicnetobjectSetUnchangedLevelEntry OBJECT-TYPE
	SYNTAX      DynamicnetobjectSetUnchangedLevelEntry
	MAX-ACCESS  not-accessible
	STATUS      current
	DESCRIPTION
	"Table entry for dynamicnetobjectSetUnchanged"
	INDEX { dynamicnetobjectSetUnchangedLevelName }
	::={dynamicnetobjectSetUnchangedLevelTable 1}

DynamicnetobjectSetUnchangedLevelEntry ::=
	SEQUENCE {
		dynamicnetobjectSetUnchangedLevelName	DisplayString,
		dynamicnetobjectSetUnchangedLevelVal	Counter64,
		dynamicnetobjectSetUnchangedLevelMom	CounterBasedGauge64,
		dynamicnetobjectSetUnchangedLevelMax	CounterBasedGauge64
	}

dynamicnetobjectSetUnchangedLevelName OBJECT-TYPE
	SYNTAX      DisplayString
	MAX-ACCESS  not-accessible
	STATUS      current
	DESCRIPTION
	"Table entry display string for dynamicnetobjectSetUnchanged"
	::={dynamicnetobjectSetUnchangedLevelEntry 1}

dynamicnetobjectSetUnchangedLevelVal OBJECT-TYPE
	SYNTAX	 Counter64
	MAX-ACCESS  read-only
	STATUS      current
	DESCRIPTION
	"Table entry attribute for dynamicnetobjectSetUnchanged"
	::={dynamicnetobjectSetUnchangedLevelEntry 2}

dynamicnetobjectSetUnchangedLevelMom OBJECT-TYPE
	SYNTAX	 CounterBasedGauge64
	MAX-ACCESS  read-only
	STATUS      current
	DESCRIPTION
	"Table entry attribute for dynamicnetobjectSetUnchanged"
	::={dynamicnetobjectSetUnchangedLevelEntry 3}

dynamicnetobjectSetUnchangedLevelMax OBJECT-TYPE
	SYNTAX	 CounterBasedGauge64
	MAX-ACCESS  read-only
	STATUS      current
	DESCRIPTION
	"Table entry attribute for dynamicnetobjectSetUnchanged"
	::={dynamicnetobjectSetUnchangedLevelEntry 4}


dynamicnetobjectSetBeginCalls	OBJECT IDENTIFIER ::={dynnetobjs 33}

dynamicnetobjectSetBeginCallsVal	OBJECT-TYPE
	SYNTAX	 Counter64
	MAX-ACCESS read-only
	STATUS current
	DESCRIPTION "Oper SET_BEGIN: SetBegin calls"

	::={dynamicnetobjectSetBeginCalls 1}

dynamicnetobjectSetBeginCallsMom	OBJECT-TYPE
	SYNTAX	 CounterBasedGauge64
	MAX-ACCESS read-only
	STATUS current
	DESCRIPTION "Oper SET_BEGIN: SetBegin calls"

	::={dynamicnetobjectSetBeginCalls 2}

dynamicnetobjectSetBeginCallsMax	OBJECT-TYPE
	SYNTAX	 CounterBasedGauge64
	MAX-ACCESS read-only
	STATUS current
	DESCRIPTION "Oper SET_BEGIN: SetBegin calls"

	::={dynamicnetobjectSetBeginCalls 3}

dynamicnetobjectSetBeginCallsLevelTable OBJECT-TYPE
	SYNTAX      SEQUENCE OF DynamicnetobjectSetBeginCallsLevelEntry
	MAX-ACCESS  not-accessible
	STATUS      current
	DESCRIPTION
	"Table for dynamicnetobjectSetBeginCalls"
	::={dynamicnetobjectSetBeginCalls 4}

dynamicnetobjectSetBeginCallsLevelEntry OBJECT-TYPE
	SYNTAX      DynamicnetobjectSetBeginCallsLevelEntry
	MAX-ACCESS  not-accessible
	STATUS      current
	DESCRIPTION
	"Table entry for dynamicnetobjectSetBeginCalls"
	INDEX { dynamicnetobjectSetBeginCallsLevelName }
	::={dynamicnetobjectSetBeginCallsLevelTable 1}

DynamicnetobjectSetBeginCallsLevelEntry ::=
	SEQUENCE {
		dynamicnetobjectSetBeginCallsLevelName	DisplayString,
		dynamicnetobjectSetBeginCallsLevelVal	Counter64,
		dynamicnetobjectSetBeginCallsLevelMom	CounterBasedGauge64,
		dynamicnetobjectSetBeginCallsLevelMax	CounterBasedGauge64
	}

dynamicnetobjectSetBeginCallsLevelName OBJECT-TYPE
	SYNTAX      DisplayString
	MAX-ACCESS  not-accessible
	STATUS      current
	DESCRIPTION
	"Table entry display string for dynamicnetobjectSetBeginCalls"
	::={dynamicnetobjectSetBeginCallsLevelEntry 1}

dynamicnetobjectSetBeginCallsLevelVal OBJECT-TYPE
	SYNTAX	 Counter64
	MAX-ACCESS  read-only
	STATUS      current
	DESCRIPTION
	"Table entry attribute for dynamicnetobjectSetBeginCalls"
	::={dynamicnetobjectSetBeginCallsLevelEntry 2}

dynamicnetobjectSetBeginCallsLevelMom OBJECT-TYPE
	SYNTAX	 CounterBasedGauge64
	MAX-ACCESS  read-only
	STATUS      current
	DESCRIPTION
	"Table entry attribute for dynamicnetobjectSetBeginCalls"
	::={dynamicnetobjectSetBeginCallsLevelEntry 3}

dynamicnetobjectSetBeginCallsLevelMax OBJECT-TYPE
	SYNTAX	 CounterBasedGauge64
	MAX-ACCESS  read-only
	STATUS      current
	DESCRIPTION
	"Table entry attribute for dynamicnetobjectSetBeginCalls"
	::={dynamicnetobjectSetBeginCallsLevelEntry 4}


dynamicnetobjectSetBeginFailed	OBJECT IDENTIFIER ::={dynnetobjs 35}

dynamicnetobjectSetBeginFailedVal	OBJECT-TYPE
	SYNTAX	 Counter64
	MAX-ACCESS read-only
	STATUS current
	DESCRIPTION "Oper SET_BEGIN: SetBegin calls failed"

	::={dynamicnetobjectSetBeginFailed 1}

dynamicnetobjectSetBeginFailedMom	OBJECT-TYPE
	SYNTAX	 CounterBasedGauge64
	MAX-ACCESS read-only
	STATUS current
	DESCRIPTION "Oper SET_BEGIN: SetBegin calls failed"

	::={dynamicnetobjectSetBeginFailed 2}

dynamicnetobjectSetBeginFailedMax	OBJECT-TYPE
	SYNTAX	 CounterBasedGauge64
	MAX-ACCESS read-only
	STATUS current
	DESCRIPTION "Oper SET_BEGIN: SetBegin calls failed"

	::={dynamicnetobjectSetBeginFailed 3}

dynamicnetobjectSetBeginFailedLevelTable OBJECT-TYPE
	SYNTAX      SEQUENCE OF DynamicnetobjectSetBeginFailedLevelEntry
	MAX-ACCESS  not-accessible
	STATUS      current
	DESCRIPTION
	"Table for dynamicnetobjectSetBeginFailed"
	::={dynamicnetobjectSetBeginFailed 4}

dynamicnetobjectSetBeginFailedLevelEntry OBJECT-TYPE
	SYNTAX      DynamicnetobjectSetBeginFailedLevelEntry
	MAX-ACCESS  not-accessible
	STATUS      current
	DESCRIPTION
	"Table entry for dynamicnetobjectSetBeginFailed"
	INDEX { dynamicnetobjectSetBeginFailedLevelName }
	::={dynamicnetobjectSetBeginFailedLevelTable 1}

DynamicnetobjectSetBeginFailedLevelEntry ::=
	SEQUENCE {
		dynamicnetobjectSetBeginFailedLevelName	DisplayString,
		dynamicnetobjectSetBeginFailedLevelVal	Counter64,
		dynamicnetobjectSetBeginFailedLevelMom	CounterBasedGauge64,
		dynamicnetobjectSetBeginFailedLevelMax	CounterBasedGauge64
	}

dynamicnetobjectSetBeginFailedLevelName OBJECT-TYPE
	SYNTAX      DisplayString
	MAX-ACCESS  not-accessible
	STATUS      current
	DESCRIPTION
	"Table entry display string for dynamicnetobjectSetBeginFailed"
	::={dynamicnetobjectSetBeginFailedLevelEntry 1}

dynamicnetobjectSetBeginFailedLevelVal OBJECT-TYPE
	SYNTAX	 Counter64
	MAX-ACCESS  read-only
	STATUS      current
	DESCRIPTION
	"Table entry attribute for dynamicnetobjectSetBeginFailed"
	::={dynamicnetobjectSetBeginFailedLevelEntry 2}

dynamicnetobjectSetBeginFailedLevelMom OBJECT-TYPE
	SYNTAX	 CounterBasedGauge64
	MAX-ACCESS  read-only
	STATUS      current
	DESCRIPTION
	"Table entry attribute for dynamicnetobjectSetBeginFailed"
	::={dynamicnetobjectSetBeginFailedLevelEntry 3}

dynamicnetobjectSetBeginFailedLevelMax OBJECT-TYPE
	SYNTAX	 CounterBasedGauge64
	MAX-ACCESS  read-only
	STATUS      current
	DESCRIPTION
	"Table entry attribute for dynamicnetobjectSetBeginFailed"
	::={dynamicnetobjectSetBeginFailedLevelEntry 4}


dynamicnetobjectSetEndCalls	OBJECT IDENTIFIER ::={dynnetobjs 36}

dynamicnetobjectSetEndCallsVal	OBJECT-TYPE
	SYNTAX	 Counter64
	MAX-ACCESS read-only
	STATUS current
	DESCRIPTION "Oper SET_END: SetEnd calls"

	::={dynamicnetobjectSetEndCalls 1}

dynamicnetobjectSetEndCallsMom	OBJECT-TYPE
	SYNTAX	 CounterBasedGauge64
	MAX-ACCESS read-only
	STATUS current
	DESCRIPTION "Oper SET_END: SetEnd calls"

	::={dynamicnetobjectSetEndCalls 2}

dynamicnetobjectSetEndCallsMax	OBJECT-TYPE
	SYNTAX	 CounterBasedGauge64
	MAX-ACCESS read-only
	STATUS current
	DESCRIPTION "Oper SET_END: SetEnd calls"

	::={dynamicnetobjectSetEndCalls 3}

dynamicnetobjectSetEndCallsLevelTable OBJECT-TYPE
	SYNTAX      SEQUENCE OF DynamicnetobjectSetEndCallsLevelEntry
	MAX-ACCESS  not-accessible
	STATUS      current
	DESCRIPTION
	"Table for dynamicnetobjectSetEndCalls"
	::={dynamicnetobjectSetEndCalls 4}

dynamicnetobjectSetEndCallsLevelEntry OBJECT-TYPE
	SYNTAX      DynamicnetobjectSetEndCallsLevelEntry
	MAX-ACCESS  not-accessible
	STATUS      current
	DESCRIPTION
	"Table entry for dynamicnetobjectSetEndCalls"
	INDEX { dynamicnetobjectSetEndCallsLevelName }
	::={dynamicnetobjectSetEndCallsLevelTable 1}

DynamicnetobjectSetEndCallsLevelEntry ::=
	SEQUENCE {
		dynamicnetobjectSetEndCallsLevelName	DisplayString,
		dynamicnetobjectSetEndCallsLevelVal	Counter64,
		dynamicnetobjectSetEndCallsLevelMom	CounterBasedGauge64,
		dynamicnetobjectSetEndCallsLevelMax	CounterBasedGauge64
	}

dynamicnetobjectSetEndCallsLevelName OBJECT-TYPE
	SYNTAX      DisplayString
	MAX-ACCESS  not-accessible
	STATUS      current
	DESCRIPTION
	"Table entry display string for dynamicnetobjectSetEndCalls"
	::={dynamicnetobjectSetEndCallsLevelEntry 1}

dynamicnetobjectSetEndCallsLevelVal OBJECT-TYPE
	SYNTAX	 Counter64
	MAX-ACCESS  read-only
	STATUS      current
	DESCRIPTION
	"Table entry attribute for dynamicnetobjectSetEndCalls"
	::={dynamicnetobjectSetEndCallsLevelEntry 2}

dynamicnetobjectSetEndCallsLevelMom OBJECT-TYPE
	SYNTAX	 CounterBasedGauge64
	MAX-ACCESS  read-only
	STATUS      current
	DESCRIPTION
	"Table entry attribute for dynamicnetobjectSetEndCalls"
	::={dynamicnetobjectSetEndCallsLevelEntry 3}

dynamicnetobjectSetEndCallsLevelMax OBJECT-TYPE
	SYNTAX	 CounterBasedGauge64
	MAX-ACCESS  read-only
	STATUS      current
	DESCRIPTION
	"Table entry attribute for dynamicnetobjectSetEndCalls"
	::={dynamicnetobjectSetEndCallsLevelEntry 4}


dynamicnetobjectSetEndFailed	OBJECT IDENTIFIER ::={dynnetobjs 38}

dynamicnetobjectSetEndFailedVal	OBJECT-TYPE
	SYNTAX	 Counter64
	MAX-ACCESS read-only
	STATUS current
	DESCRIPTION "Oper SET_END: SetEnd calls failed"

	::={dynamicnetobjectSetEndFailed 1}

dynamicnetobjectSetEndFailedMom	OBJECT-TYPE
	SYNTAX	 CounterBasedGauge64
	MAX-ACCESS read-only
	STATUS current
	DESCRIPTION "Oper SET_END: SetEnd calls failed"

	::={dynamicnetobjectSetEndFailed 2}

dynamicnetobjectSetEndFailedMax	OBJECT-TYPE
	SYNTAX	 CounterBasedGauge64
	MAX-ACCESS read-only
	STATUS current
	DESCRIPTION "Oper SET_END: SetEnd calls failed"

	::={dynamicnetobjectSetEndFailed 3}

dynamicnetobjectSetEndFailedLevelTable OBJECT-TYPE
	SYNTAX      SEQUENCE OF DynamicnetobjectSetEndFailedLevelEntry
	MAX-ACCESS  not-accessible
	STATUS      current
	DESCRIPTION
	"Table for dynamicnetobjectSetEndFailed"
	::={dynamicnetobjectSetEndFailed 4}

dynamicnetobjectSetEndFailedLevelEntry OBJECT-TYPE
	SYNTAX      DynamicnetobjectSetEndFailedLevelEntry
	MAX-ACCESS  not-accessible
	STATUS      current
	DESCRIPTION
	"Table entry for dynamicnetobjectSetEndFailed"
	INDEX { dynamicnetobjectSetEndFailedLevelName }
	::={dynamicnetobjectSetEndFailedLevelTable 1}

DynamicnetobjectSetEndFailedLevelEntry ::=
	SEQUENCE {
		dynamicnetobjectSetEndFailedLevelName	DisplayString,
		dynamicnetobjectSetEndFailedLevelVal	Counter64,
		dynamicnetobjectSetEndFailedLevelMom	CounterBasedGauge64,
		dynamicnetobjectSetEndFailedLevelMax	CounterBasedGauge64
	}

dynamicnetobjectSetEndFailedLevelName OBJECT-TYPE
	SYNTAX      DisplayString
	MAX-ACCESS  not-accessible
	STATUS      current
	DESCRIPTION
	"Table entry display string for dynamicnetobjectSetEndFailed"
	::={dynamicnetobjectSetEndFailedLevelEntry 1}

dynamicnetobjectSetEndFailedLevelVal OBJECT-TYPE
	SYNTAX	 Counter64
	MAX-ACCESS  read-only
	STATUS      current
	DESCRIPTION
	"Table entry attribute for dynamicnetobjectSetEndFailed"
	::={dynamicnetobjectSetEndFailedLevelEntry 2}

dynamicnetobjectSetEndFailedLevelMom OBJECT-TYPE
	SYNTAX	 CounterBasedGauge64
	MAX-ACCESS  read-only
	STATUS      current
	DESCRIPTION
	"Table entry attribute for dynamicnetobjectSetEndFailed"
	::={dynamicnetobjectSetEndFailedLevelEntry 3}

dynamicnetobjectSetEndFailedLevelMax OBJECT-TYPE
	SYNTAX	 CounterBasedGauge64
	MAX-ACCESS  read-only
	STATUS      current
	DESCRIPTION
	"Table entry attribute for dynamicnetobjectSetEndFailed"
	::={dynamicnetobjectSetEndFailedLevelEntry 4}


dynamicnetobjectSetEndRemoved	OBJECT IDENTIFIER ::={dynnetobjs 65}

dynamicnetobjectSetEndRemovedVal	OBJECT-TYPE
	SYNTAX	 Counter64
	MAX-ACCESS read-only
	STATUS current
	DESCRIPTION "Oper SET_END: Dynamic netobject items REMOVED during set_end operations due to being touched in previous set operations"

	::={dynamicnetobjectSetEndRemoved 1}

dynamicnetobjectSetEndRemovedMom	OBJECT-TYPE
	SYNTAX	 CounterBasedGauge64
	MAX-ACCESS read-only
	STATUS current
	DESCRIPTION "Oper SET_END: Dynamic netobject items REMOVED during set_end operations due to being touched in previous set operations"

	::={dynamicnetobjectSetEndRemoved 2}

dynamicnetobjectSetEndRemovedMax	OBJECT-TYPE
	SYNTAX	 CounterBasedGauge64
	MAX-ACCESS read-only
	STATUS current
	DESCRIPTION "Oper SET_END: Dynamic netobject items REMOVED during set_end operations due to being touched in previous set operations"

	::={dynamicnetobjectSetEndRemoved 3}

dynamicnetobjectSetEndRemovedLevelTable OBJECT-TYPE
	SYNTAX      SEQUENCE OF DynamicnetobjectSetEndRemovedLevelEntry
	MAX-ACCESS  not-accessible
	STATUS      current
	DESCRIPTION
	"Table for dynamicnetobjectSetEndRemoved"
	::={dynamicnetobjectSetEndRemoved 4}

dynamicnetobjectSetEndRemovedLevelEntry OBJECT-TYPE
	SYNTAX      DynamicnetobjectSetEndRemovedLevelEntry
	MAX-ACCESS  not-accessible
	STATUS      current
	DESCRIPTION
	"Table entry for dynamicnetobjectSetEndRemoved"
	INDEX { dynamicnetobjectSetEndRemovedLevelName }
	::={dynamicnetobjectSetEndRemovedLevelTable 1}

DynamicnetobjectSetEndRemovedLevelEntry ::=
	SEQUENCE {
		dynamicnetobjectSetEndRemovedLevelName	DisplayString,
		dynamicnetobjectSetEndRemovedLevelVal	Counter64,
		dynamicnetobjectSetEndRemovedLevelMom	CounterBasedGauge64,
		dynamicnetobjectSetEndRemovedLevelMax	CounterBasedGauge64
	}

dynamicnetobjectSetEndRemovedLevelName OBJECT-TYPE
	SYNTAX      DisplayString
	MAX-ACCESS  not-accessible
	STATUS      current
	DESCRIPTION
	"Table entry display string for dynamicnetobjectSetEndRemoved"
	::={dynamicnetobjectSetEndRemovedLevelEntry 1}

dynamicnetobjectSetEndRemovedLevelVal OBJECT-TYPE
	SYNTAX	 Counter64
	MAX-ACCESS  read-only
	STATUS      current
	DESCRIPTION
	"Table entry attribute for dynamicnetobjectSetEndRemoved"
	::={dynamicnetobjectSetEndRemovedLevelEntry 2}

dynamicnetobjectSetEndRemovedLevelMom OBJECT-TYPE
	SYNTAX	 CounterBasedGauge64
	MAX-ACCESS  read-only
	STATUS      current
	DESCRIPTION
	"Table entry attribute for dynamicnetobjectSetEndRemoved"
	::={dynamicnetobjectSetEndRemovedLevelEntry 3}

dynamicnetobjectSetEndRemovedLevelMax OBJECT-TYPE
	SYNTAX	 CounterBasedGauge64
	MAX-ACCESS  read-only
	STATUS      current
	DESCRIPTION
	"Table entry attribute for dynamicnetobjectSetEndRemoved"
	::={dynamicnetobjectSetEndRemovedLevelEntry 4}


dynamicnetobjectRemoveOrphansCalls	OBJECT IDENTIFIER ::={dynnetobjs 40}

dynamicnetobjectRemoveOrphansCallsVal	OBJECT-TYPE
	SYNTAX	 Counter64
	MAX-ACCESS read-only
	STATUS current
	DESCRIPTION "Oper REMOVEORPHANS: RemoveOrphans calls"

	::={dynamicnetobjectRemoveOrphansCalls 1}

dynamicnetobjectRemoveOrphansCallsMom	OBJECT-TYPE
	SYNTAX	 CounterBasedGauge64
	MAX-ACCESS read-only
	STATUS current
	DESCRIPTION "Oper REMOVEORPHANS: RemoveOrphans calls"

	::={dynamicnetobjectRemoveOrphansCalls 2}

dynamicnetobjectRemoveOrphansCallsMax	OBJECT-TYPE
	SYNTAX	 CounterBasedGauge64
	MAX-ACCESS read-only
	STATUS current
	DESCRIPTION "Oper REMOVEORPHANS: RemoveOrphans calls"

	::={dynamicnetobjectRemoveOrphansCalls 3}

dynamicnetobjectRemoveOrphansCallsLevelTable OBJECT-TYPE
	SYNTAX      SEQUENCE OF DynamicnetobjectRemoveOrphansCallsLevelEntry
	MAX-ACCESS  not-accessible
	STATUS      current
	DESCRIPTION
	"Table for dynamicnetobjectRemoveOrphansCalls"
	::={dynamicnetobjectRemoveOrphansCalls 4}

dynamicnetobjectRemoveOrphansCallsLevelEntry OBJECT-TYPE
	SYNTAX      DynamicnetobjectRemoveOrphansCallsLevelEntry
	MAX-ACCESS  not-accessible
	STATUS      current
	DESCRIPTION
	"Table entry for dynamicnetobjectRemoveOrphansCalls"
	INDEX { dynamicnetobjectRemoveOrphansCallsLevelName }
	::={dynamicnetobjectRemoveOrphansCallsLevelTable 1}

DynamicnetobjectRemoveOrphansCallsLevelEntry ::=
	SEQUENCE {
		dynamicnetobjectRemoveOrphansCallsLevelName	DisplayString,
		dynamicnetobjectRemoveOrphansCallsLevelVal	Counter64,
		dynamicnetobjectRemoveOrphansCallsLevelMom	CounterBasedGauge64,
		dynamicnetobjectRemoveOrphansCallsLevelMax	CounterBasedGauge64
	}

dynamicnetobjectRemoveOrphansCallsLevelName OBJECT-TYPE
	SYNTAX      DisplayString
	MAX-ACCESS  not-accessible
	STATUS      current
	DESCRIPTION
	"Table entry display string for dynamicnetobjectRemoveOrphansCalls"
	::={dynamicnetobjectRemoveOrphansCallsLevelEntry 1}

dynamicnetobjectRemoveOrphansCallsLevelVal OBJECT-TYPE
	SYNTAX	 Counter64
	MAX-ACCESS  read-only
	STATUS      current
	DESCRIPTION
	"Table entry attribute for dynamicnetobjectRemoveOrphansCalls"
	::={dynamicnetobjectRemoveOrphansCallsLevelEntry 2}

dynamicnetobjectRemoveOrphansCallsLevelMom OBJECT-TYPE
	SYNTAX	 CounterBasedGauge64
	MAX-ACCESS  read-only
	STATUS      current
	DESCRIPTION
	"Table entry attribute for dynamicnetobjectRemoveOrphansCalls"
	::={dynamicnetobjectRemoveOrphansCallsLevelEntry 3}

dynamicnetobjectRemoveOrphansCallsLevelMax OBJECT-TYPE
	SYNTAX	 CounterBasedGauge64
	MAX-ACCESS  read-only
	STATUS      current
	DESCRIPTION
	"Table entry attribute for dynamicnetobjectRemoveOrphansCalls"
	::={dynamicnetobjectRemoveOrphansCallsLevelEntry 4}


dynamicnetobjectRemoveOrphansFailed	OBJECT IDENTIFIER ::={dynnetobjs 42}

dynamicnetobjectRemoveOrphansFailedVal	OBJECT-TYPE
	SYNTAX	 Counter64
	MAX-ACCESS read-only
	STATUS current
	DESCRIPTION "Oper REMOVEORPHANS: RemoveOrphans calls failed"

	::={dynamicnetobjectRemoveOrphansFailed 1}

dynamicnetobjectRemoveOrphansFailedMom	OBJECT-TYPE
	SYNTAX	 CounterBasedGauge64
	MAX-ACCESS read-only
	STATUS current
	DESCRIPTION "Oper REMOVEORPHANS: RemoveOrphans calls failed"

	::={dynamicnetobjectRemoveOrphansFailed 2}

dynamicnetobjectRemoveOrphansFailedMax	OBJECT-TYPE
	SYNTAX	 CounterBasedGauge64
	MAX-ACCESS read-only
	STATUS current
	DESCRIPTION "Oper REMOVEORPHANS: RemoveOrphans calls failed"

	::={dynamicnetobjectRemoveOrphansFailed 3}

dynamicnetobjectRemoveOrphansFailedLevelTable OBJECT-TYPE
	SYNTAX      SEQUENCE OF DynamicnetobjectRemoveOrphansFailedLevelEntry
	MAX-ACCESS  not-accessible
	STATUS      current
	DESCRIPTION
	"Table for dynamicnetobjectRemoveOrphansFailed"
	::={dynamicnetobjectRemoveOrphansFailed 4}

dynamicnetobjectRemoveOrphansFailedLevelEntry OBJECT-TYPE
	SYNTAX      DynamicnetobjectRemoveOrphansFailedLevelEntry
	MAX-ACCESS  not-accessible
	STATUS      current
	DESCRIPTION
	"Table entry for dynamicnetobjectRemoveOrphansFailed"
	INDEX { dynamicnetobjectRemoveOrphansFailedLevelName }
	::={dynamicnetobjectRemoveOrphansFailedLevelTable 1}

DynamicnetobjectRemoveOrphansFailedLevelEntry ::=
	SEQUENCE {
		dynamicnetobjectRemoveOrphansFailedLevelName	DisplayString,
		dynamicnetobjectRemoveOrphansFailedLevelVal	Counter64,
		dynamicnetobjectRemoveOrphansFailedLevelMom	CounterBasedGauge64,
		dynamicnetobjectRemoveOrphansFailedLevelMax	CounterBasedGauge64
	}

dynamicnetobjectRemoveOrphansFailedLevelName OBJECT-TYPE
	SYNTAX      DisplayString
	MAX-ACCESS  not-accessible
	STATUS      current
	DESCRIPTION
	"Table entry display string for dynamicnetobjectRemoveOrphansFailed"
	::={dynamicnetobjectRemoveOrphansFailedLevelEntry 1}

dynamicnetobjectRemoveOrphansFailedLevelVal OBJECT-TYPE
	SYNTAX	 Counter64
	MAX-ACCESS  read-only
	STATUS      current
	DESCRIPTION
	"Table entry attribute for dynamicnetobjectRemoveOrphansFailed"
	::={dynamicnetobjectRemoveOrphansFailedLevelEntry 2}

dynamicnetobjectRemoveOrphansFailedLevelMom OBJECT-TYPE
	SYNTAX	 CounterBasedGauge64
	MAX-ACCESS  read-only
	STATUS      current
	DESCRIPTION
	"Table entry attribute for dynamicnetobjectRemoveOrphansFailed"
	::={dynamicnetobjectRemoveOrphansFailedLevelEntry 3}

dynamicnetobjectRemoveOrphansFailedLevelMax OBJECT-TYPE
	SYNTAX	 CounterBasedGauge64
	MAX-ACCESS  read-only
	STATUS      current
	DESCRIPTION
	"Table entry attribute for dynamicnetobjectRemoveOrphansFailed"
	::={dynamicnetobjectRemoveOrphansFailedLevelEntry 4}


dynamicnetobjectOrphansRemoved	OBJECT IDENTIFIER ::={dynnetobjs 43}

dynamicnetobjectOrphansRemovedVal	OBJECT-TYPE
	SYNTAX	 Counter64
	MAX-ACCESS read-only
	STATUS current
	DESCRIPTION "Oper REMOVEORPHANS: Orphan dynamic netobject items removed"

	::={dynamicnetobjectOrphansRemoved 1}

dynamicnetobjectOrphansRemovedMom	OBJECT-TYPE
	SYNTAX	 CounterBasedGauge64
	MAX-ACCESS read-only
	STATUS current
	DESCRIPTION "Oper REMOVEORPHANS: Orphan dynamic netobject items removed"

	::={dynamicnetobjectOrphansRemoved 2}

dynamicnetobjectOrphansRemovedMax	OBJECT-TYPE
	SYNTAX	 CounterBasedGauge64
	MAX-ACCESS read-only
	STATUS current
	DESCRIPTION "Oper REMOVEORPHANS: Orphan dynamic netobject items removed"

	::={dynamicnetobjectOrphansRemoved 3}

dynamicnetobjectOrphansRemovedLevelTable OBJECT-TYPE
	SYNTAX      SEQUENCE OF DynamicnetobjectOrphansRemovedLevelEntry
	MAX-ACCESS  not-accessible
	STATUS      current
	DESCRIPTION
	"Table for dynamicnetobjectOrphansRemoved"
	::={dynamicnetobjectOrphansRemoved 4}

dynamicnetobjectOrphansRemovedLevelEntry OBJECT-TYPE
	SYNTAX      DynamicnetobjectOrphansRemovedLevelEntry
	MAX-ACCESS  not-accessible
	STATUS      current
	DESCRIPTION
	"Table entry for dynamicnetobjectOrphansRemoved"
	INDEX { dynamicnetobjectOrphansRemovedLevelName }
	::={dynamicnetobjectOrphansRemovedLevelTable 1}

DynamicnetobjectOrphansRemovedLevelEntry ::=
	SEQUENCE {
		dynamicnetobjectOrphansRemovedLevelName	DisplayString,
		dynamicnetobjectOrphansRemovedLevelVal	Counter64,
		dynamicnetobjectOrphansRemovedLevelMom	CounterBasedGauge64,
		dynamicnetobjectOrphansRemovedLevelMax	CounterBasedGauge64
	}

dynamicnetobjectOrphansRemovedLevelName OBJECT-TYPE
	SYNTAX      DisplayString
	MAX-ACCESS  not-accessible
	STATUS      current
	DESCRIPTION
	"Table entry display string for dynamicnetobjectOrphansRemoved"
	::={dynamicnetobjectOrphansRemovedLevelEntry 1}

dynamicnetobjectOrphansRemovedLevelVal OBJECT-TYPE
	SYNTAX	 Counter64
	MAX-ACCESS  read-only
	STATUS      current
	DESCRIPTION
	"Table entry attribute for dynamicnetobjectOrphansRemoved"
	::={dynamicnetobjectOrphansRemovedLevelEntry 2}

dynamicnetobjectOrphansRemovedLevelMom OBJECT-TYPE
	SYNTAX	 CounterBasedGauge64
	MAX-ACCESS  read-only
	STATUS      current
	DESCRIPTION
	"Table entry attribute for dynamicnetobjectOrphansRemoved"
	::={dynamicnetobjectOrphansRemovedLevelEntry 3}

dynamicnetobjectOrphansRemovedLevelMax OBJECT-TYPE
	SYNTAX	 CounterBasedGauge64
	MAX-ACCESS  read-only
	STATUS      current
	DESCRIPTION
	"Table entry attribute for dynamicnetobjectOrphansRemoved"
	::={dynamicnetobjectOrphansRemovedLevelEntry 4}


dynamicnetobjectAddSucceeded	OBJECT IDENTIFIER ::={dynnetobjs 8}

dynamicnetobjectAddSucceededVal	OBJECT-TYPE
	SYNTAX	 Counter64
	MAX-ACCESS read-only
	STATUS obsolete
	DESCRIPTION "Add calls succeeded"

	::={dynamicnetobjectAddSucceeded 1}

dynamicnetobjectAddSucceededMom	OBJECT-TYPE
	SYNTAX	 CounterBasedGauge64
	MAX-ACCESS read-only
	STATUS obsolete
	DESCRIPTION "Add calls succeeded"

	::={dynamicnetobjectAddSucceeded 2}

dynamicnetobjectAddSucceededMax	OBJECT-TYPE
	SYNTAX	 CounterBasedGauge64
	MAX-ACCESS read-only
	STATUS obsolete
	DESCRIPTION "Add calls succeeded"

	::={dynamicnetobjectAddSucceeded 3}

dynamicnetobjectAddSucceededLevelTable OBJECT-TYPE
	SYNTAX      SEQUENCE OF DynamicnetobjectAddSucceededLevelEntry
	MAX-ACCESS  not-accessible
	STATUS      current
	DESCRIPTION
	"Table for dynamicnetobjectAddSucceeded"
	::={dynamicnetobjectAddSucceeded 4}

dynamicnetobjectAddSucceededLevelEntry OBJECT-TYPE
	SYNTAX      DynamicnetobjectAddSucceededLevelEntry
	MAX-ACCESS  not-accessible
	STATUS      current
	DESCRIPTION
	"Table entry for dynamicnetobjectAddSucceeded"
	INDEX { dynamicnetobjectAddSucceededLevelName }
	::={dynamicnetobjectAddSucceededLevelTable 1}

DynamicnetobjectAddSucceededLevelEntry ::=
	SEQUENCE {
		dynamicnetobjectAddSucceededLevelName	DisplayString,
		dynamicnetobjectAddSucceededLevelVal	Counter64,
		dynamicnetobjectAddSucceededLevelMom	CounterBasedGauge64,
		dynamicnetobjectAddSucceededLevelMax	CounterBasedGauge64
	}

dynamicnetobjectAddSucceededLevelName OBJECT-TYPE
	SYNTAX      DisplayString
	MAX-ACCESS  not-accessible
	STATUS      current
	DESCRIPTION
	"Table entry display string for dynamicnetobjectAddSucceeded"
	::={dynamicnetobjectAddSucceededLevelEntry 1}

dynamicnetobjectAddSucceededLevelVal OBJECT-TYPE
	SYNTAX	 Counter64
	MAX-ACCESS  read-only
	STATUS      current
	DESCRIPTION
	"Table entry attribute for dynamicnetobjectAddSucceeded"
	::={dynamicnetobjectAddSucceededLevelEntry 2}

dynamicnetobjectAddSucceededLevelMom OBJECT-TYPE
	SYNTAX	 CounterBasedGauge64
	MAX-ACCESS  read-only
	STATUS      current
	DESCRIPTION
	"Table entry attribute for dynamicnetobjectAddSucceeded"
	::={dynamicnetobjectAddSucceededLevelEntry 3}

dynamicnetobjectAddSucceededLevelMax OBJECT-TYPE
	SYNTAX	 CounterBasedGauge64
	MAX-ACCESS  read-only
	STATUS      current
	DESCRIPTION
	"Table entry attribute for dynamicnetobjectAddSucceeded"
	::={dynamicnetobjectAddSucceededLevelEntry 4}


dynamicnetobjectRemoveSucceeded	OBJECT IDENTIFIER ::={dynnetobjs 3}

dynamicnetobjectRemoveSucceededVal	OBJECT-TYPE
	SYNTAX	 Counter64
	MAX-ACCESS read-only
	STATUS obsolete
	DESCRIPTION "Remove calls succeeded"

	::={dynamicnetobjectRemoveSucceeded 1}

dynamicnetobjectRemoveSucceededMom	OBJECT-TYPE
	SYNTAX	 CounterBasedGauge64
	MAX-ACCESS read-only
	STATUS obsolete
	DESCRIPTION "Remove calls succeeded"

	::={dynamicnetobjectRemoveSucceeded 2}

dynamicnetobjectRemoveSucceededMax	OBJECT-TYPE
	SYNTAX	 CounterBasedGauge64
	MAX-ACCESS read-only
	STATUS obsolete
	DESCRIPTION "Remove calls succeeded"

	::={dynamicnetobjectRemoveSucceeded 3}

dynamicnetobjectRemoveSucceededLevelTable OBJECT-TYPE
	SYNTAX      SEQUENCE OF DynamicnetobjectRemoveSucceededLevelEntry
	MAX-ACCESS  not-accessible
	STATUS      current
	DESCRIPTION
	"Table for dynamicnetobjectRemoveSucceeded"
	::={dynamicnetobjectRemoveSucceeded 4}

dynamicnetobjectRemoveSucceededLevelEntry OBJECT-TYPE
	SYNTAX      DynamicnetobjectRemoveSucceededLevelEntry
	MAX-ACCESS  not-accessible
	STATUS      current
	DESCRIPTION
	"Table entry for dynamicnetobjectRemoveSucceeded"
	INDEX { dynamicnetobjectRemoveSucceededLevelName }
	::={dynamicnetobjectRemoveSucceededLevelTable 1}

DynamicnetobjectRemoveSucceededLevelEntry ::=
	SEQUENCE {
		dynamicnetobjectRemoveSucceededLevelName	DisplayString,
		dynamicnetobjectRemoveSucceededLevelVal	Counter64,
		dynamicnetobjectRemoveSucceededLevelMom	CounterBasedGauge64,
		dynamicnetobjectRemoveSucceededLevelMax	CounterBasedGauge64
	}

dynamicnetobjectRemoveSucceededLevelName OBJECT-TYPE
	SYNTAX      DisplayString
	MAX-ACCESS  not-accessible
	STATUS      current
	DESCRIPTION
	"Table entry display string for dynamicnetobjectRemoveSucceeded"
	::={dynamicnetobjectRemoveSucceededLevelEntry 1}

dynamicnetobjectRemoveSucceededLevelVal OBJECT-TYPE
	SYNTAX	 Counter64
	MAX-ACCESS  read-only
	STATUS      current
	DESCRIPTION
	"Table entry attribute for dynamicnetobjectRemoveSucceeded"
	::={dynamicnetobjectRemoveSucceededLevelEntry 2}

dynamicnetobjectRemoveSucceededLevelMom OBJECT-TYPE
	SYNTAX	 CounterBasedGauge64
	MAX-ACCESS  read-only
	STATUS      current
	DESCRIPTION
	"Table entry attribute for dynamicnetobjectRemoveSucceeded"
	::={dynamicnetobjectRemoveSucceededLevelEntry 3}

dynamicnetobjectRemoveSucceededLevelMax OBJECT-TYPE
	SYNTAX	 CounterBasedGauge64
	MAX-ACCESS  read-only
	STATUS      current
	DESCRIPTION
	"Table entry attribute for dynamicnetobjectRemoveSucceeded"
	::={dynamicnetobjectRemoveSucceededLevelEntry 4}


dynamicnetobjectInsertPldbFailed	OBJECT IDENTIFIER ::={dynnetobjs 10}

dynamicnetobjectInsertPldbFailedVal	OBJECT-TYPE
	SYNTAX	 Counter64
	MAX-ACCESS read-only
	STATUS obsolete
	DESCRIPTION "Add calls failed in PLDB"

	::={dynamicnetobjectInsertPldbFailed 1}

dynamicnetobjectInsertPldbFailedMom	OBJECT-TYPE
	SYNTAX	 CounterBasedGauge64
	MAX-ACCESS read-only
	STATUS obsolete
	DESCRIPTION "Add calls failed in PLDB"

	::={dynamicnetobjectInsertPldbFailed 2}

dynamicnetobjectInsertPldbFailedMax	OBJECT-TYPE
	SYNTAX	 CounterBasedGauge64
	MAX-ACCESS read-only
	STATUS obsolete
	DESCRIPTION "Add calls failed in PLDB"

	::={dynamicnetobjectInsertPldbFailed 3}

dynamicnetobjectInsertPldbFailedLevelTable OBJECT-TYPE
	SYNTAX      SEQUENCE OF DynamicnetobjectInsertPldbFailedLevelEntry
	MAX-ACCESS  not-accessible
	STATUS      current
	DESCRIPTION
	"Table for dynamicnetobjectInsertPldbFailed"
	::={dynamicnetobjectInsertPldbFailed 4}

dynamicnetobjectInsertPldbFailedLevelEntry OBJECT-TYPE
	SYNTAX      DynamicnetobjectInsertPldbFailedLevelEntry
	MAX-ACCESS  not-accessible
	STATUS      current
	DESCRIPTION
	"Table entry for dynamicnetobjectInsertPldbFailed"
	INDEX { dynamicnetobjectInsertPldbFailedLevelName }
	::={dynamicnetobjectInsertPldbFailedLevelTable 1}

DynamicnetobjectInsertPldbFailedLevelEntry ::=
	SEQUENCE {
		dynamicnetobjectInsertPldbFailedLevelName	DisplayString,
		dynamicnetobjectInsertPldbFailedLevelVal	Counter64,
		dynamicnetobjectInsertPldbFailedLevelMom	CounterBasedGauge64,
		dynamicnetobjectInsertPldbFailedLevelMax	CounterBasedGauge64
	}

dynamicnetobjectInsertPldbFailedLevelName OBJECT-TYPE
	SYNTAX      DisplayString
	MAX-ACCESS  not-accessible
	STATUS      current
	DESCRIPTION
	"Table entry display string for dynamicnetobjectInsertPldbFailed"
	::={dynamicnetobjectInsertPldbFailedLevelEntry 1}

dynamicnetobjectInsertPldbFailedLevelVal OBJECT-TYPE
	SYNTAX	 Counter64
	MAX-ACCESS  read-only
	STATUS      current
	DESCRIPTION
	"Table entry attribute for dynamicnetobjectInsertPldbFailed"
	::={dynamicnetobjectInsertPldbFailedLevelEntry 2}

dynamicnetobjectInsertPldbFailedLevelMom OBJECT-TYPE
	SYNTAX	 CounterBasedGauge64
	MAX-ACCESS  read-only
	STATUS      current
	DESCRIPTION
	"Table entry attribute for dynamicnetobjectInsertPldbFailed"
	::={dynamicnetobjectInsertPldbFailedLevelEntry 3}

dynamicnetobjectInsertPldbFailedLevelMax OBJECT-TYPE
	SYNTAX	 CounterBasedGauge64
	MAX-ACCESS  read-only
	STATUS      current
	DESCRIPTION
	"Table entry attribute for dynamicnetobjectInsertPldbFailed"
	::={dynamicnetobjectInsertPldbFailedLevelEntry 4}


dynamicnetobjectSqliteMemoryUsed	OBJECT IDENTIFIER ::={dynnetobjs 20}

dynamicnetobjectSqliteMemoryUsedVal	OBJECT-TYPE
	SYNTAX	 CounterBasedGauge64
	MAX-ACCESS read-only
	STATUS obsolete
	DESCRIPTION "Add requests in queue"

	::={dynamicnetobjectSqliteMemoryUsed 1}

dynamicnetobjectSqliteMemoryUsedMax	OBJECT-TYPE
	SYNTAX	 CounterBasedGauge64
	MAX-ACCESS read-only
	STATUS obsolete
	DESCRIPTION "Add requests in queue"

	::={dynamicnetobjectSqliteMemoryUsed 3}

dynamicnetobjectSqliteMemoryUsedLevelTable OBJECT-TYPE
	SYNTAX      SEQUENCE OF DynamicnetobjectSqliteMemoryUsedLevelEntry
	MAX-ACCESS  not-accessible
	STATUS      current
	DESCRIPTION
	"Table for dynamicnetobjectSqliteMemoryUsed"
	::={dynamicnetobjectSqliteMemoryUsed 4}

dynamicnetobjectSqliteMemoryUsedLevelEntry OBJECT-TYPE
	SYNTAX      DynamicnetobjectSqliteMemoryUsedLevelEntry
	MAX-ACCESS  not-accessible
	STATUS      current
	DESCRIPTION
	"Table entry for dynamicnetobjectSqliteMemoryUsed"
	INDEX { dynamicnetobjectSqliteMemoryUsedLevelName }
	::={dynamicnetobjectSqliteMemoryUsedLevelTable 1}

DynamicnetobjectSqliteMemoryUsedLevelEntry ::=
	SEQUENCE {
		dynamicnetobjectSqliteMemoryUsedLevelName	DisplayString,
		dynamicnetobjectSqliteMemoryUsedLevelVal	CounterBasedGauge64,
		dynamicnetobjectSqliteMemoryUsedLevelMax	CounterBasedGauge64
	}

dynamicnetobjectSqliteMemoryUsedLevelName OBJECT-TYPE
	SYNTAX      DisplayString
	MAX-ACCESS  not-accessible
	STATUS      current
	DESCRIPTION
	"Table entry display string for dynamicnetobjectSqliteMemoryUsed"
	::={dynamicnetobjectSqliteMemoryUsedLevelEntry 1}

dynamicnetobjectSqliteMemoryUsedLevelVal OBJECT-TYPE
	SYNTAX	 CounterBasedGauge64
	MAX-ACCESS  read-only
	STATUS      current
	DESCRIPTION
	"Table entry attribute for dynamicnetobjectSqliteMemoryUsed"
	::={dynamicnetobjectSqliteMemoryUsedLevelEntry 2}

dynamicnetobjectSqliteMemoryUsedLevelMax OBJECT-TYPE
	SYNTAX	 CounterBasedGauge64
	MAX-ACCESS  read-only
	STATUS      current
	DESCRIPTION
	"Table entry attribute for dynamicnetobjectSqliteMemoryUsed"
	::={dynamicnetobjectSqliteMemoryUsedLevelEntry 4}


dynamicnetobjectPendingAdds	OBJECT IDENTIFIER ::={dynnetobjs 21}

dynamicnetobjectPendingAddsVal	OBJECT-TYPE
	SYNTAX	 CounterBasedGauge64
	MAX-ACCESS read-only
	STATUS obsolete
	DESCRIPTION "Memory used by the dynitems sqlite thread"

	::={dynamicnetobjectPendingAdds 1}

dynamicnetobjectPendingAddsMax	OBJECT-TYPE
	SYNTAX	 CounterBasedGauge64
	MAX-ACCESS read-only
	STATUS obsolete
	DESCRIPTION "Memory used by the dynitems sqlite thread"

	::={dynamicnetobjectPendingAdds 3}

dynamicnetobjectPendingAddsLevelTable OBJECT-TYPE
	SYNTAX      SEQUENCE OF DynamicnetobjectPendingAddsLevelEntry
	MAX-ACCESS  not-accessible
	STATUS      current
	DESCRIPTION
	"Table for dynamicnetobjectPendingAdds"
	::={dynamicnetobjectPendingAdds 4}

dynamicnetobjectPendingAddsLevelEntry OBJECT-TYPE
	SYNTAX      DynamicnetobjectPendingAddsLevelEntry
	MAX-ACCESS  not-accessible
	STATUS      current
	DESCRIPTION
	"Table entry for dynamicnetobjectPendingAdds"
	INDEX { dynamicnetobjectPendingAddsLevelName }
	::={dynamicnetobjectPendingAddsLevelTable 1}

DynamicnetobjectPendingAddsLevelEntry ::=
	SEQUENCE {
		dynamicnetobjectPendingAddsLevelName	DisplayString,
		dynamicnetobjectPendingAddsLevelVal	CounterBasedGauge64,
		dynamicnetobjectPendingAddsLevelMax	CounterBasedGauge64
	}

dynamicnetobjectPendingAddsLevelName OBJECT-TYPE
	SYNTAX      DisplayString
	MAX-ACCESS  not-accessible
	STATUS      current
	DESCRIPTION
	"Table entry display string for dynamicnetobjectPendingAdds"
	::={dynamicnetobjectPendingAddsLevelEntry 1}

dynamicnetobjectPendingAddsLevelVal OBJECT-TYPE
	SYNTAX	 CounterBasedGauge64
	MAX-ACCESS  read-only
	STATUS      current
	DESCRIPTION
	"Table entry attribute for dynamicnetobjectPendingAdds"
	::={dynamicnetobjectPendingAddsLevelEntry 2}

dynamicnetobjectPendingAddsLevelMax OBJECT-TYPE
	SYNTAX	 CounterBasedGauge64
	MAX-ACCESS  read-only
	STATUS      current
	DESCRIPTION
	"Table entry attribute for dynamicnetobjectPendingAdds"
	::={dynamicnetobjectPendingAddsLevelEntry 4}


dynamicnetobjectSubscriberConflicts	OBJECT IDENTIFIER ::={dynnetobjs 17}

dynamicnetobjectSubscriberConflictsVal	OBJECT-TYPE
	SYNTAX	 Counter64
	MAX-ACCESS read-only
	STATUS obsolete
	DESCRIPTION "Conflicting subscriber names"

	::={dynamicnetobjectSubscriberConflicts 1}

dynamicnetobjectSubscriberConflictsMom	OBJECT-TYPE
	SYNTAX	 CounterBasedGauge64
	MAX-ACCESS read-only
	STATUS obsolete
	DESCRIPTION "Conflicting subscriber names"

	::={dynamicnetobjectSubscriberConflicts 2}

dynamicnetobjectSubscriberConflictsMax	OBJECT-TYPE
	SYNTAX	 CounterBasedGauge64
	MAX-ACCESS read-only
	STATUS obsolete
	DESCRIPTION "Conflicting subscriber names"

	::={dynamicnetobjectSubscriberConflicts 3}

dynamicnetobjectSubscriberConflictsLevelTable OBJECT-TYPE
	SYNTAX      SEQUENCE OF DynamicnetobjectSubscriberConflictsLevelEntry
	MAX-ACCESS  not-accessible
	STATUS      current
	DESCRIPTION
	"Table for dynamicnetobjectSubscriberConflicts"
	::={dynamicnetobjectSubscriberConflicts 4}

dynamicnetobjectSubscriberConflictsLevelEntry OBJECT-TYPE
	SYNTAX      DynamicnetobjectSubscriberConflictsLevelEntry
	MAX-ACCESS  not-accessible
	STATUS      current
	DESCRIPTION
	"Table entry for dynamicnetobjectSubscriberConflicts"
	INDEX { dynamicnetobjectSubscriberConflictsLevelName }
	::={dynamicnetobjectSubscriberConflictsLevelTable 1}

DynamicnetobjectSubscriberConflictsLevelEntry ::=
	SEQUENCE {
		dynamicnetobjectSubscriberConflictsLevelName	DisplayString,
		dynamicnetobjectSubscriberConflictsLevelVal	Counter64,
		dynamicnetobjectSubscriberConflictsLevelMom	CounterBasedGauge64,
		dynamicnetobjectSubscriberConflictsLevelMax	CounterBasedGauge64
	}

dynamicnetobjectSubscriberConflictsLevelName OBJECT-TYPE
	SYNTAX      DisplayString
	MAX-ACCESS  not-accessible
	STATUS      current
	DESCRIPTION
	"Table entry display string for dynamicnetobjectSubscriberConflicts"
	::={dynamicnetobjectSubscriberConflictsLevelEntry 1}

dynamicnetobjectSubscriberConflictsLevelVal OBJECT-TYPE
	SYNTAX	 Counter64
	MAX-ACCESS  read-only
	STATUS      current
	DESCRIPTION
	"Table entry attribute for dynamicnetobjectSubscriberConflicts"
	::={dynamicnetobjectSubscriberConflictsLevelEntry 2}

dynamicnetobjectSubscriberConflictsLevelMom OBJECT-TYPE
	SYNTAX	 CounterBasedGauge64
	MAX-ACCESS  read-only
	STATUS      current
	DESCRIPTION
	"Table entry attribute for dynamicnetobjectSubscriberConflicts"
	::={dynamicnetobjectSubscriberConflictsLevelEntry 3}

dynamicnetobjectSubscriberConflictsLevelMax OBJECT-TYPE
	SYNTAX	 CounterBasedGauge64
	MAX-ACCESS  read-only
	STATUS      current
	DESCRIPTION
	"Table entry attribute for dynamicnetobjectSubscriberConflicts"
	::={dynamicnetobjectSubscriberConflictsLevelEntry 4}


dynamicnetobjectListItems	OBJECT IDENTIFIER ::={dynnetobjs 2}

dynamicnetobjectListItemsVal	OBJECT-TYPE
	SYNTAX	 CounterBasedGauge64
	MAX-ACCESS read-only
	STATUS obsolete
	DESCRIPTION "Items returned from last PLDB query"

	::={dynamicnetobjectListItems 1}

dynamicnetobjectListItemsMax	OBJECT-TYPE
	SYNTAX	 CounterBasedGauge64
	MAX-ACCESS read-only
	STATUS obsolete
	DESCRIPTION "Items returned from last PLDB query"

	::={dynamicnetobjectListItems 3}

dynamicnetobjectListItemsLevelTable OBJECT-TYPE
	SYNTAX      SEQUENCE OF DynamicnetobjectListItemsLevelEntry
	MAX-ACCESS  not-accessible
	STATUS      current
	DESCRIPTION
	"Table for dynamicnetobjectListItems"
	::={dynamicnetobjectListItems 4}

dynamicnetobjectListItemsLevelEntry OBJECT-TYPE
	SYNTAX      DynamicnetobjectListItemsLevelEntry
	MAX-ACCESS  not-accessible
	STATUS      current
	DESCRIPTION
	"Table entry for dynamicnetobjectListItems"
	INDEX { dynamicnetobjectListItemsLevelName }
	::={dynamicnetobjectListItemsLevelTable 1}

DynamicnetobjectListItemsLevelEntry ::=
	SEQUENCE {
		dynamicnetobjectListItemsLevelName	DisplayString,
		dynamicnetobjectListItemsLevelVal	CounterBasedGauge64,
		dynamicnetobjectListItemsLevelMax	CounterBasedGauge64
	}

dynamicnetobjectListItemsLevelName OBJECT-TYPE
	SYNTAX      DisplayString
	MAX-ACCESS  not-accessible
	STATUS      current
	DESCRIPTION
	"Table entry display string for dynamicnetobjectListItems"
	::={dynamicnetobjectListItemsLevelEntry 1}

dynamicnetobjectListItemsLevelVal OBJECT-TYPE
	SYNTAX	 CounterBasedGauge64
	MAX-ACCESS  read-only
	STATUS      current
	DESCRIPTION
	"Table entry attribute for dynamicnetobjectListItems"
	::={dynamicnetobjectListItemsLevelEntry 2}

dynamicnetobjectListItemsLevelMax OBJECT-TYPE
	SYNTAX	 CounterBasedGauge64
	MAX-ACCESS  read-only
	STATUS      current
	DESCRIPTION
	"Table entry attribute for dynamicnetobjectListItems"
	::={dynamicnetobjectListItemsLevelEntry 4}


dynamicnetobjectSetSucceeded	OBJECT IDENTIFIER ::={dynnetobjs 31}

dynamicnetobjectSetSucceededVal	OBJECT-TYPE
	SYNTAX	 Counter64
	MAX-ACCESS read-only
	STATUS obsolete
	DESCRIPTION "Set calls succeeded"

	::={dynamicnetobjectSetSucceeded 1}

dynamicnetobjectSetSucceededMom	OBJECT-TYPE
	SYNTAX	 CounterBasedGauge64
	MAX-ACCESS read-only
	STATUS obsolete
	DESCRIPTION "Set calls succeeded"

	::={dynamicnetobjectSetSucceeded 2}

dynamicnetobjectSetSucceededMax	OBJECT-TYPE
	SYNTAX	 CounterBasedGauge64
	MAX-ACCESS read-only
	STATUS obsolete
	DESCRIPTION "Set calls succeeded"

	::={dynamicnetobjectSetSucceeded 3}

dynamicnetobjectSetSucceededLevelTable OBJECT-TYPE
	SYNTAX      SEQUENCE OF DynamicnetobjectSetSucceededLevelEntry
	MAX-ACCESS  not-accessible
	STATUS      current
	DESCRIPTION
	"Table for dynamicnetobjectSetSucceeded"
	::={dynamicnetobjectSetSucceeded 4}

dynamicnetobjectSetSucceededLevelEntry OBJECT-TYPE
	SYNTAX      DynamicnetobjectSetSucceededLevelEntry
	MAX-ACCESS  not-accessible
	STATUS      current
	DESCRIPTION
	"Table entry for dynamicnetobjectSetSucceeded"
	INDEX { dynamicnetobjectSetSucceededLevelName }
	::={dynamicnetobjectSetSucceededLevelTable 1}

DynamicnetobjectSetSucceededLevelEntry ::=
	SEQUENCE {
		dynamicnetobjectSetSucceededLevelName	DisplayString,
		dynamicnetobjectSetSucceededLevelVal	Counter64,
		dynamicnetobjectSetSucceededLevelMom	CounterBasedGauge64,
		dynamicnetobjectSetSucceededLevelMax	CounterBasedGauge64
	}

dynamicnetobjectSetSucceededLevelName OBJECT-TYPE
	SYNTAX      DisplayString
	MAX-ACCESS  not-accessible
	STATUS      current
	DESCRIPTION
	"Table entry display string for dynamicnetobjectSetSucceeded"
	::={dynamicnetobjectSetSucceededLevelEntry 1}

dynamicnetobjectSetSucceededLevelVal OBJECT-TYPE
	SYNTAX	 Counter64
	MAX-ACCESS  read-only
	STATUS      current
	DESCRIPTION
	"Table entry attribute for dynamicnetobjectSetSucceeded"
	::={dynamicnetobjectSetSucceededLevelEntry 2}

dynamicnetobjectSetSucceededLevelMom OBJECT-TYPE
	SYNTAX	 CounterBasedGauge64
	MAX-ACCESS  read-only
	STATUS      current
	DESCRIPTION
	"Table entry attribute for dynamicnetobjectSetSucceeded"
	::={dynamicnetobjectSetSucceededLevelEntry 3}

dynamicnetobjectSetSucceededLevelMax OBJECT-TYPE
	SYNTAX	 CounterBasedGauge64
	MAX-ACCESS  read-only
	STATUS      current
	DESCRIPTION
	"Table entry attribute for dynamicnetobjectSetSucceeded"
	::={dynamicnetobjectSetSucceededLevelEntry 4}


dynamicnetobjectSetBeginSucceeded	OBJECT IDENTIFIER ::={dynnetobjs 34}

dynamicnetobjectSetBeginSucceededVal	OBJECT-TYPE
	SYNTAX	 Counter64
	MAX-ACCESS read-only
	STATUS obsolete
	DESCRIPTION "SetBegin calls succeeded"

	::={dynamicnetobjectSetBeginSucceeded 1}

dynamicnetobjectSetBeginSucceededMom	OBJECT-TYPE
	SYNTAX	 CounterBasedGauge64
	MAX-ACCESS read-only
	STATUS obsolete
	DESCRIPTION "SetBegin calls succeeded"

	::={dynamicnetobjectSetBeginSucceeded 2}

dynamicnetobjectSetBeginSucceededMax	OBJECT-TYPE
	SYNTAX	 CounterBasedGauge64
	MAX-ACCESS read-only
	STATUS obsolete
	DESCRIPTION "SetBegin calls succeeded"

	::={dynamicnetobjectSetBeginSucceeded 3}

dynamicnetobjectSetBeginSucceededLevelTable OBJECT-TYPE
	SYNTAX      SEQUENCE OF DynamicnetobjectSetBeginSucceededLevelEntry
	MAX-ACCESS  not-accessible
	STATUS      current
	DESCRIPTION
	"Table for dynamicnetobjectSetBeginSucceeded"
	::={dynamicnetobjectSetBeginSucceeded 4}

dynamicnetobjectSetBeginSucceededLevelEntry OBJECT-TYPE
	SYNTAX      DynamicnetobjectSetBeginSucceededLevelEntry
	MAX-ACCESS  not-accessible
	STATUS      current
	DESCRIPTION
	"Table entry for dynamicnetobjectSetBeginSucceeded"
	INDEX { dynamicnetobjectSetBeginSucceededLevelName }
	::={dynamicnetobjectSetBeginSucceededLevelTable 1}

DynamicnetobjectSetBeginSucceededLevelEntry ::=
	SEQUENCE {
		dynamicnetobjectSetBeginSucceededLevelName	DisplayString,
		dynamicnetobjectSetBeginSucceededLevelVal	Counter64,
		dynamicnetobjectSetBeginSucceededLevelMom	CounterBasedGauge64,
		dynamicnetobjectSetBeginSucceededLevelMax	CounterBasedGauge64
	}

dynamicnetobjectSetBeginSucceededLevelName OBJECT-TYPE
	SYNTAX      DisplayString
	MAX-ACCESS  not-accessible
	STATUS      current
	DESCRIPTION
	"Table entry display string for dynamicnetobjectSetBeginSucceeded"
	::={dynamicnetobjectSetBeginSucceededLevelEntry 1}

dynamicnetobjectSetBeginSucceededLevelVal OBJECT-TYPE
	SYNTAX	 Counter64
	MAX-ACCESS  read-only
	STATUS      current
	DESCRIPTION
	"Table entry attribute for dynamicnetobjectSetBeginSucceeded"
	::={dynamicnetobjectSetBeginSucceededLevelEntry 2}

dynamicnetobjectSetBeginSucceededLevelMom OBJECT-TYPE
	SYNTAX	 CounterBasedGauge64
	MAX-ACCESS  read-only
	STATUS      current
	DESCRIPTION
	"Table entry attribute for dynamicnetobjectSetBeginSucceeded"
	::={dynamicnetobjectSetBeginSucceededLevelEntry 3}

dynamicnetobjectSetBeginSucceededLevelMax OBJECT-TYPE
	SYNTAX	 CounterBasedGauge64
	MAX-ACCESS  read-only
	STATUS      current
	DESCRIPTION
	"Table entry attribute for dynamicnetobjectSetBeginSucceeded"
	::={dynamicnetobjectSetBeginSucceededLevelEntry 4}


dynamicnetobjectSetEndSucceeded	OBJECT IDENTIFIER ::={dynnetobjs 37}

dynamicnetobjectSetEndSucceededVal	OBJECT-TYPE
	SYNTAX	 Counter64
	MAX-ACCESS read-only
	STATUS obsolete
	DESCRIPTION "SetEnd calls succeeded"

	::={dynamicnetobjectSetEndSucceeded 1}

dynamicnetobjectSetEndSucceededMom	OBJECT-TYPE
	SYNTAX	 CounterBasedGauge64
	MAX-ACCESS read-only
	STATUS obsolete
	DESCRIPTION "SetEnd calls succeeded"

	::={dynamicnetobjectSetEndSucceeded 2}

dynamicnetobjectSetEndSucceededMax	OBJECT-TYPE
	SYNTAX	 CounterBasedGauge64
	MAX-ACCESS read-only
	STATUS obsolete
	DESCRIPTION "SetEnd calls succeeded"

	::={dynamicnetobjectSetEndSucceeded 3}

dynamicnetobjectSetEndSucceededLevelTable OBJECT-TYPE
	SYNTAX      SEQUENCE OF DynamicnetobjectSetEndSucceededLevelEntry
	MAX-ACCESS  not-accessible
	STATUS      current
	DESCRIPTION
	"Table for dynamicnetobjectSetEndSucceeded"
	::={dynamicnetobjectSetEndSucceeded 4}

dynamicnetobjectSetEndSucceededLevelEntry OBJECT-TYPE
	SYNTAX      DynamicnetobjectSetEndSucceededLevelEntry
	MAX-ACCESS  not-accessible
	STATUS      current
	DESCRIPTION
	"Table entry for dynamicnetobjectSetEndSucceeded"
	INDEX { dynamicnetobjectSetEndSucceededLevelName }
	::={dynamicnetobjectSetEndSucceededLevelTable 1}

DynamicnetobjectSetEndSucceededLevelEntry ::=
	SEQUENCE {
		dynamicnetobjectSetEndSucceededLevelName	DisplayString,
		dynamicnetobjectSetEndSucceededLevelVal	Counter64,
		dynamicnetobjectSetEndSucceededLevelMom	CounterBasedGauge64,
		dynamicnetobjectSetEndSucceededLevelMax	CounterBasedGauge64
	}

dynamicnetobjectSetEndSucceededLevelName OBJECT-TYPE
	SYNTAX      DisplayString
	MAX-ACCESS  not-accessible
	STATUS      current
	DESCRIPTION
	"Table entry display string for dynamicnetobjectSetEndSucceeded"
	::={dynamicnetobjectSetEndSucceededLevelEntry 1}

dynamicnetobjectSetEndSucceededLevelVal OBJECT-TYPE
	SYNTAX	 Counter64
	MAX-ACCESS  read-only
	STATUS      current
	DESCRIPTION
	"Table entry attribute for dynamicnetobjectSetEndSucceeded"
	::={dynamicnetobjectSetEndSucceededLevelEntry 2}

dynamicnetobjectSetEndSucceededLevelMom OBJECT-TYPE
	SYNTAX	 CounterBasedGauge64
	MAX-ACCESS  read-only
	STATUS      current
	DESCRIPTION
	"Table entry attribute for dynamicnetobjectSetEndSucceeded"
	::={dynamicnetobjectSetEndSucceededLevelEntry 3}

dynamicnetobjectSetEndSucceededLevelMax OBJECT-TYPE
	SYNTAX	 CounterBasedGauge64
	MAX-ACCESS  read-only
	STATUS      current
	DESCRIPTION
	"Table entry attribute for dynamicnetobjectSetEndSucceeded"
	::={dynamicnetobjectSetEndSucceededLevelEntry 4}


dynamicnetobjectRemoveOrphansSucceeded	OBJECT IDENTIFIER ::={dynnetobjs 41}

dynamicnetobjectRemoveOrphansSucceededVal	OBJECT-TYPE
	SYNTAX	 Counter64
	MAX-ACCESS read-only
	STATUS obsolete
	DESCRIPTION "SetEnd calls succeeded"

	::={dynamicnetobjectRemoveOrphansSucceeded 1}

dynamicnetobjectRemoveOrphansSucceededMom	OBJECT-TYPE
	SYNTAX	 CounterBasedGauge64
	MAX-ACCESS read-only
	STATUS obsolete
	DESCRIPTION "SetEnd calls succeeded"

	::={dynamicnetobjectRemoveOrphansSucceeded 2}

dynamicnetobjectRemoveOrphansSucceededMax	OBJECT-TYPE
	SYNTAX	 CounterBasedGauge64
	MAX-ACCESS read-only
	STATUS obsolete
	DESCRIPTION "SetEnd calls succeeded"

	::={dynamicnetobjectRemoveOrphansSucceeded 3}

dynamicnetobjectRemoveOrphansSucceededLevelTable OBJECT-TYPE
	SYNTAX      SEQUENCE OF DynamicnetobjectRemoveOrphansSucceededLevelEntry
	MAX-ACCESS  not-accessible
	STATUS      current
	DESCRIPTION
	"Table for dynamicnetobjectRemoveOrphansSucceeded"
	::={dynamicnetobjectRemoveOrphansSucceeded 4}

dynamicnetobjectRemoveOrphansSucceededLevelEntry OBJECT-TYPE
	SYNTAX      DynamicnetobjectRemoveOrphansSucceededLevelEntry
	MAX-ACCESS  not-accessible
	STATUS      current
	DESCRIPTION
	"Table entry for dynamicnetobjectRemoveOrphansSucceeded"
	INDEX { dynamicnetobjectRemoveOrphansSucceededLevelName }
	::={dynamicnetobjectRemoveOrphansSucceededLevelTable 1}

DynamicnetobjectRemoveOrphansSucceededLevelEntry ::=
	SEQUENCE {
		dynamicnetobjectRemoveOrphansSucceededLevelName	DisplayString,
		dynamicnetobjectRemoveOrphansSucceededLevelVal	Counter64,
		dynamicnetobjectRemoveOrphansSucceededLevelMom	CounterBasedGauge64,
		dynamicnetobjectRemoveOrphansSucceededLevelMax	CounterBasedGauge64
	}

dynamicnetobjectRemoveOrphansSucceededLevelName OBJECT-TYPE
	SYNTAX      DisplayString
	MAX-ACCESS  not-accessible
	STATUS      current
	DESCRIPTION
	"Table entry display string for dynamicnetobjectRemoveOrphansSucceeded"
	::={dynamicnetobjectRemoveOrphansSucceededLevelEntry 1}

dynamicnetobjectRemoveOrphansSucceededLevelVal OBJECT-TYPE
	SYNTAX	 Counter64
	MAX-ACCESS  read-only
	STATUS      current
	DESCRIPTION
	"Table entry attribute for dynamicnetobjectRemoveOrphansSucceeded"
	::={dynamicnetobjectRemoveOrphansSucceededLevelEntry 2}

dynamicnetobjectRemoveOrphansSucceededLevelMom OBJECT-TYPE
	SYNTAX	 CounterBasedGauge64
	MAX-ACCESS  read-only
	STATUS      current
	DESCRIPTION
	"Table entry attribute for dynamicnetobjectRemoveOrphansSucceeded"
	::={dynamicnetobjectRemoveOrphansSucceededLevelEntry 3}

dynamicnetobjectRemoveOrphansSucceededLevelMax OBJECT-TYPE
	SYNTAX	 CounterBasedGauge64
	MAX-ACCESS  read-only
	STATUS      current
	DESCRIPTION
	"Table entry attribute for dynamicnetobjectRemoveOrphansSucceeded"
	::={dynamicnetobjectRemoveOrphansSucceededLevelEntry 4}


dynamicnetobjectCurrentIpNetworkCount	OBJECT IDENTIFIER ::={dynnetobjs 51}

dynamicnetobjectCurrentIpNetworkCountVal	OBJECT-TYPE
	SYNTAX	 CounterBasedGauge64
	MAX-ACCESS read-only
	STATUS obsolete
	DESCRIPTION "IP networks in table"

	::={dynamicnetobjectCurrentIpNetworkCount 1}

dynamicnetobjectCurrentIpNetworkCountMax	OBJECT-TYPE
	SYNTAX	 CounterBasedGauge64
	MAX-ACCESS read-only
	STATUS obsolete
	DESCRIPTION "IP networks in table"

	::={dynamicnetobjectCurrentIpNetworkCount 3}

dynamicnetobjectCurrentIpNetworkCountLevelTable OBJECT-TYPE
	SYNTAX      SEQUENCE OF DynamicnetobjectCurrentIpNetworkCountLevelEntry
	MAX-ACCESS  not-accessible
	STATUS      current
	DESCRIPTION
	"Table for dynamicnetobjectCurrentIpNetworkCount"
	::={dynamicnetobjectCurrentIpNetworkCount 4}

dynamicnetobjectCurrentIpNetworkCountLevelEntry OBJECT-TYPE
	SYNTAX      DynamicnetobjectCurrentIpNetworkCountLevelEntry
	MAX-ACCESS  not-accessible
	STATUS      current
	DESCRIPTION
	"Table entry for dynamicnetobjectCurrentIpNetworkCount"
	INDEX { dynamicnetobjectCurrentIpNetworkCountLevelName }
	::={dynamicnetobjectCurrentIpNetworkCountLevelTable 1}

DynamicnetobjectCurrentIpNetworkCountLevelEntry ::=
	SEQUENCE {
		dynamicnetobjectCurrentIpNetworkCountLevelName	DisplayString,
		dynamicnetobjectCurrentIpNetworkCountLevelVal	CounterBasedGauge64,
		dynamicnetobjectCurrentIpNetworkCountLevelMax	CounterBasedGauge64
	}

dynamicnetobjectCurrentIpNetworkCountLevelName OBJECT-TYPE
	SYNTAX      DisplayString
	MAX-ACCESS  not-accessible
	STATUS      current
	DESCRIPTION
	"Table entry display string for dynamicnetobjectCurrentIpNetworkCount"
	::={dynamicnetobjectCurrentIpNetworkCountLevelEntry 1}

dynamicnetobjectCurrentIpNetworkCountLevelVal OBJECT-TYPE
	SYNTAX	 CounterBasedGauge64
	MAX-ACCESS  read-only
	STATUS      current
	DESCRIPTION
	"Table entry attribute for dynamicnetobjectCurrentIpNetworkCount"
	::={dynamicnetobjectCurrentIpNetworkCountLevelEntry 2}

dynamicnetobjectCurrentIpNetworkCountLevelMax OBJECT-TYPE
	SYNTAX	 CounterBasedGauge64
	MAX-ACCESS  read-only
	STATUS      current
	DESCRIPTION
	"Table entry attribute for dynamicnetobjectCurrentIpNetworkCount"
	::={dynamicnetobjectCurrentIpNetworkCountLevelEntry 4}


dynamicnetobjectListItemsReturned	OBJECT IDENTIFIER ::={dynnetobjs 16}

dynamicnetobjectListItemsReturnedVal	OBJECT-TYPE
	SYNTAX	 Counter64
	MAX-ACCESS read-only
	STATUS obsolete
	DESCRIPTION "Oper LIST: Items returned from list calls"

	::={dynamicnetobjectListItemsReturned 1}

dynamicnetobjectListItemsReturnedMom	OBJECT-TYPE
	SYNTAX	 CounterBasedGauge64
	MAX-ACCESS read-only
	STATUS obsolete
	DESCRIPTION "Oper LIST: Items returned from list calls"

	::={dynamicnetobjectListItemsReturned 2}

dynamicnetobjectListItemsReturnedMax	OBJECT-TYPE
	SYNTAX	 CounterBasedGauge64
	MAX-ACCESS read-only
	STATUS obsolete
	DESCRIPTION "Oper LIST: Items returned from list calls"

	::={dynamicnetobjectListItemsReturned 3}

dynamicnetobjectListItemsReturnedLevelTable OBJECT-TYPE
	SYNTAX      SEQUENCE OF DynamicnetobjectListItemsReturnedLevelEntry
	MAX-ACCESS  not-accessible
	STATUS      current
	DESCRIPTION
	"Table for dynamicnetobjectListItemsReturned"
	::={dynamicnetobjectListItemsReturned 4}

dynamicnetobjectListItemsReturnedLevelEntry OBJECT-TYPE
	SYNTAX      DynamicnetobjectListItemsReturnedLevelEntry
	MAX-ACCESS  not-accessible
	STATUS      current
	DESCRIPTION
	"Table entry for dynamicnetobjectListItemsReturned"
	INDEX { dynamicnetobjectListItemsReturnedLevelName }
	::={dynamicnetobjectListItemsReturnedLevelTable 1}

DynamicnetobjectListItemsReturnedLevelEntry ::=
	SEQUENCE {
		dynamicnetobjectListItemsReturnedLevelName	DisplayString,
		dynamicnetobjectListItemsReturnedLevelVal	Counter64,
		dynamicnetobjectListItemsReturnedLevelMom	CounterBasedGauge64,
		dynamicnetobjectListItemsReturnedLevelMax	CounterBasedGauge64
	}

dynamicnetobjectListItemsReturnedLevelName OBJECT-TYPE
	SYNTAX      DisplayString
	MAX-ACCESS  not-accessible
	STATUS      current
	DESCRIPTION
	"Table entry display string for dynamicnetobjectListItemsReturned"
	::={dynamicnetobjectListItemsReturnedLevelEntry 1}

dynamicnetobjectListItemsReturnedLevelVal OBJECT-TYPE
	SYNTAX	 Counter64
	MAX-ACCESS  read-only
	STATUS      current
	DESCRIPTION
	"Table entry attribute for dynamicnetobjectListItemsReturned"
	::={dynamicnetobjectListItemsReturnedLevelEntry 2}

dynamicnetobjectListItemsReturnedLevelMom OBJECT-TYPE
	SYNTAX	 CounterBasedGauge64
	MAX-ACCESS  read-only
	STATUS      current
	DESCRIPTION
	"Table entry attribute for dynamicnetobjectListItemsReturned"
	::={dynamicnetobjectListItemsReturnedLevelEntry 3}

dynamicnetobjectListItemsReturnedLevelMax OBJECT-TYPE
	SYNTAX	 CounterBasedGauge64
	MAX-ACCESS  read-only
	STATUS      current
	DESCRIPTION
	"Table entry attribute for dynamicnetobjectListItemsReturned"
	::={dynamicnetobjectListItemsReturnedLevelEntry 4}


rulesetCompiler	OBJECT IDENTIFIER ::={sysdiag 147}

rulesetCompilerRulesetStart	OBJECT IDENTIFIER ::={rulesetCompiler 1}

rulesetCompilerRulesetStartVal	OBJECT-TYPE
	SYNTAX	 DateAndTime
	MAX-ACCESS read-only
	STATUS current
	DESCRIPTION "Ruleset compile: Start of ruleset compilation"

	::={rulesetCompilerRulesetStart 1}

rulesetCompilerRulesetStartLevelTable OBJECT-TYPE
	SYNTAX      SEQUENCE OF RulesetCompilerRulesetStartLevelEntry
	MAX-ACCESS  not-accessible
	STATUS      current
	DESCRIPTION
	"Table for rulesetCompilerRulesetStart"
	::={rulesetCompilerRulesetStart 2}

rulesetCompilerRulesetStartLevelEntry OBJECT-TYPE
	SYNTAX      RulesetCompilerRulesetStartLevelEntry
	MAX-ACCESS  not-accessible
	STATUS      current
	DESCRIPTION
	"Table entry for rulesetCompilerRulesetStart"
	INDEX { rulesetCompilerRulesetStartLevelName }
	::={rulesetCompilerRulesetStartLevelTable 1}

RulesetCompilerRulesetStartLevelEntry ::=
	SEQUENCE {
		rulesetCompilerRulesetStartLevelName	DisplayString,
		rulesetCompilerRulesetStartLevelVal	DateAndTime
	}

rulesetCompilerRulesetStartLevelName OBJECT-TYPE
	SYNTAX      DisplayString
	MAX-ACCESS  not-accessible
	STATUS      current
	DESCRIPTION
	"Table entry display string for rulesetCompilerRulesetStart"
	::={rulesetCompilerRulesetStartLevelEntry 1}

rulesetCompilerRulesetStartLevelVal OBJECT-TYPE
	SYNTAX	 DateAndTime
	MAX-ACCESS  read-only
	STATUS      current
	DESCRIPTION
	"Table entry attribute for rulesetCompilerRulesetStart"
	::={rulesetCompilerRulesetStartLevelEntry 2}


rulesetCompilerRulesetEnd	OBJECT IDENTIFIER ::={rulesetCompiler 2}

rulesetCompilerRulesetEndVal	OBJECT-TYPE
	SYNTAX	 DateAndTime
	MAX-ACCESS read-only
	STATUS current
	DESCRIPTION "Ruleset compile: Ruleset compilation is done and sent to engine"

	::={rulesetCompilerRulesetEnd 1}

rulesetCompilerRulesetEndLevelTable OBJECT-TYPE
	SYNTAX      SEQUENCE OF RulesetCompilerRulesetEndLevelEntry
	MAX-ACCESS  not-accessible
	STATUS      current
	DESCRIPTION
	"Table for rulesetCompilerRulesetEnd"
	::={rulesetCompilerRulesetEnd 2}

rulesetCompilerRulesetEndLevelEntry OBJECT-TYPE
	SYNTAX      RulesetCompilerRulesetEndLevelEntry
	MAX-ACCESS  not-accessible
	STATUS      current
	DESCRIPTION
	"Table entry for rulesetCompilerRulesetEnd"
	INDEX { rulesetCompilerRulesetEndLevelName }
	::={rulesetCompilerRulesetEndLevelTable 1}

RulesetCompilerRulesetEndLevelEntry ::=
	SEQUENCE {
		rulesetCompilerRulesetEndLevelName	DisplayString,
		rulesetCompilerRulesetEndLevelVal	DateAndTime
	}

rulesetCompilerRulesetEndLevelName OBJECT-TYPE
	SYNTAX      DisplayString
	MAX-ACCESS  not-accessible
	STATUS      current
	DESCRIPTION
	"Table entry display string for rulesetCompilerRulesetEnd"
	::={rulesetCompilerRulesetEndLevelEntry 1}

rulesetCompilerRulesetEndLevelVal OBJECT-TYPE
	SYNTAX	 DateAndTime
	MAX-ACCESS  read-only
	STATUS      current
	DESCRIPTION
	"Table entry attribute for rulesetCompilerRulesetEnd"
	::={rulesetCompilerRulesetEndLevelEntry 2}


rulesetCompilerRulesetTime	OBJECT IDENTIFIER ::={rulesetCompiler 3}

rulesetCompilerRulesetTimeVal	OBJECT-TYPE
	SYNTAX	 CounterBasedGauge64
	MAX-ACCESS read-only
	STATUS current
	DESCRIPTION "Ruleset compile: Total compile and send time, in ms"

	::={rulesetCompilerRulesetTime 1}

rulesetCompilerRulesetTimeMax	OBJECT-TYPE
	SYNTAX	 CounterBasedGauge64
	MAX-ACCESS read-only
	STATUS current
	DESCRIPTION "Ruleset compile: Total compile and send time, in ms"

	::={rulesetCompilerRulesetTime 3}

rulesetCompilerRulesetTimeLevelTable OBJECT-TYPE
	SYNTAX      SEQUENCE OF RulesetCompilerRulesetTimeLevelEntry
	MAX-ACCESS  not-accessible
	STATUS      current
	DESCRIPTION
	"Table for rulesetCompilerRulesetTime"
	::={rulesetCompilerRulesetTime 4}

rulesetCompilerRulesetTimeLevelEntry OBJECT-TYPE
	SYNTAX      RulesetCompilerRulesetTimeLevelEntry
	MAX-ACCESS  not-accessible
	STATUS      current
	DESCRIPTION
	"Table entry for rulesetCompilerRulesetTime"
	INDEX { rulesetCompilerRulesetTimeLevelName }
	::={rulesetCompilerRulesetTimeLevelTable 1}

RulesetCompilerRulesetTimeLevelEntry ::=
	SEQUENCE {
		rulesetCompilerRulesetTimeLevelName	DisplayString,
		rulesetCompilerRulesetTimeLevelVal	CounterBasedGauge64,
		rulesetCompilerRulesetTimeLevelMax	CounterBasedGauge64
	}

rulesetCompilerRulesetTimeLevelName OBJECT-TYPE
	SYNTAX      DisplayString
	MAX-ACCESS  not-accessible
	STATUS      current
	DESCRIPTION
	"Table entry display string for rulesetCompilerRulesetTime"
	::={rulesetCompilerRulesetTimeLevelEntry 1}

rulesetCompilerRulesetTimeLevelVal OBJECT-TYPE
	SYNTAX	 CounterBasedGauge64
	MAX-ACCESS  read-only
	STATUS      current
	DESCRIPTION
	"Table entry attribute for rulesetCompilerRulesetTime"
	::={rulesetCompilerRulesetTimeLevelEntry 2}

rulesetCompilerRulesetTimeLevelMax OBJECT-TYPE
	SYNTAX	 CounterBasedGauge64
	MAX-ACCESS  read-only
	STATUS      current
	DESCRIPTION
	"Table entry attribute for rulesetCompilerRulesetTime"
	::={rulesetCompilerRulesetTimeLevelEntry 4}


rulesetCompilerRulesetErrors	OBJECT IDENTIFIER ::={rulesetCompiler 4}

rulesetCompilerRulesetErrorsVal	OBJECT-TYPE
	SYNTAX	 CounterBasedGauge64
	MAX-ACCESS read-only
	STATUS current
	DESCRIPTION "Ruleset compile: Compilation errors in last ruleset"

	::={rulesetCompilerRulesetErrors 1}

rulesetCompilerRulesetErrorsMax	OBJECT-TYPE
	SYNTAX	 CounterBasedGauge64
	MAX-ACCESS read-only
	STATUS current
	DESCRIPTION "Ruleset compile: Compilation errors in last ruleset"

	::={rulesetCompilerRulesetErrors 3}

rulesetCompilerRulesetErrorsLevelTable OBJECT-TYPE
	SYNTAX      SEQUENCE OF RulesetCompilerRulesetErrorsLevelEntry
	MAX-ACCESS  not-accessible
	STATUS      current
	DESCRIPTION
	"Table for rulesetCompilerRulesetErrors"
	::={rulesetCompilerRulesetErrors 4}

rulesetCompilerRulesetErrorsLevelEntry OBJECT-TYPE
	SYNTAX      RulesetCompilerRulesetErrorsLevelEntry
	MAX-ACCESS  not-accessible
	STATUS      current
	DESCRIPTION
	"Table entry for rulesetCompilerRulesetErrors"
	INDEX { rulesetCompilerRulesetErrorsLevelName }
	::={rulesetCompilerRulesetErrorsLevelTable 1}

RulesetCompilerRulesetErrorsLevelEntry ::=
	SEQUENCE {
		rulesetCompilerRulesetErrorsLevelName	DisplayString,
		rulesetCompilerRulesetErrorsLevelVal	CounterBasedGauge64,
		rulesetCompilerRulesetErrorsLevelMax	CounterBasedGauge64
	}

rulesetCompilerRulesetErrorsLevelName OBJECT-TYPE
	SYNTAX      DisplayString
	MAX-ACCESS  not-accessible
	STATUS      current
	DESCRIPTION
	"Table entry display string for rulesetCompilerRulesetErrors"
	::={rulesetCompilerRulesetErrorsLevelEntry 1}

rulesetCompilerRulesetErrorsLevelVal OBJECT-TYPE
	SYNTAX	 CounterBasedGauge64
	MAX-ACCESS  read-only
	STATUS      current
	DESCRIPTION
	"Table entry attribute for rulesetCompilerRulesetErrors"
	::={rulesetCompilerRulesetErrorsLevelEntry 2}

rulesetCompilerRulesetErrorsLevelMax OBJECT-TYPE
	SYNTAX	 CounterBasedGauge64
	MAX-ACCESS  read-only
	STATUS      current
	DESCRIPTION
	"Table entry attribute for rulesetCompilerRulesetErrors"
	::={rulesetCompilerRulesetErrorsLevelEntry 4}


rulesetCompilerRulesetWarnings	OBJECT IDENTIFIER ::={rulesetCompiler 5}

rulesetCompilerRulesetWarningsVal	OBJECT-TYPE
	SYNTAX	 CounterBasedGauge64
	MAX-ACCESS read-only
	STATUS current
	DESCRIPTION "Ruleset compile: Compilation warnings in last ruleset"

	::={rulesetCompilerRulesetWarnings 1}

rulesetCompilerRulesetWarningsMax	OBJECT-TYPE
	SYNTAX	 CounterBasedGauge64
	MAX-ACCESS read-only
	STATUS current
	DESCRIPTION "Ruleset compile: Compilation warnings in last ruleset"

	::={rulesetCompilerRulesetWarnings 3}

rulesetCompilerRulesetWarningsLevelTable OBJECT-TYPE
	SYNTAX      SEQUENCE OF RulesetCompilerRulesetWarningsLevelEntry
	MAX-ACCESS  not-accessible
	STATUS      current
	DESCRIPTION
	"Table for rulesetCompilerRulesetWarnings"
	::={rulesetCompilerRulesetWarnings 4}

rulesetCompilerRulesetWarningsLevelEntry OBJECT-TYPE
	SYNTAX      RulesetCompilerRulesetWarningsLevelEntry
	MAX-ACCESS  not-accessible
	STATUS      current
	DESCRIPTION
	"Table entry for rulesetCompilerRulesetWarnings"
	INDEX { rulesetCompilerRulesetWarningsLevelName }
	::={rulesetCompilerRulesetWarningsLevelTable 1}

RulesetCompilerRulesetWarningsLevelEntry ::=
	SEQUENCE {
		rulesetCompilerRulesetWarningsLevelName	DisplayString,
		rulesetCompilerRulesetWarningsLevelVal	CounterBasedGauge64,
		rulesetCompilerRulesetWarningsLevelMax	CounterBasedGauge64
	}

rulesetCompilerRulesetWarningsLevelName OBJECT-TYPE
	SYNTAX      DisplayString
	MAX-ACCESS  not-accessible
	STATUS      current
	DESCRIPTION
	"Table entry display string for rulesetCompilerRulesetWarnings"
	::={rulesetCompilerRulesetWarningsLevelEntry 1}

rulesetCompilerRulesetWarningsLevelVal OBJECT-TYPE
	SYNTAX	 CounterBasedGauge64
	MAX-ACCESS  read-only
	STATUS      current
	DESCRIPTION
	"Table entry attribute for rulesetCompilerRulesetWarnings"
	::={rulesetCompilerRulesetWarningsLevelEntry 2}

rulesetCompilerRulesetWarningsLevelMax OBJECT-TYPE
	SYNTAX	 CounterBasedGauge64
	MAX-ACCESS  read-only
	STATUS      current
	DESCRIPTION
	"Table entry attribute for rulesetCompilerRulesetWarnings"
	::={rulesetCompilerRulesetWarningsLevelEntry 4}


rulesetCompilerConfigRules	OBJECT IDENTIFIER ::={rulesetCompiler 11}

rulesetCompilerConfigRulesVal	OBJECT-TYPE
	SYNTAX	 CounterBasedGauge64
	MAX-ACCESS read-only
	STATUS current
	DESCRIPTION "Config Rules: Number of rules in ruleset config"

	::={rulesetCompilerConfigRules 1}

rulesetCompilerConfigRulesMax	OBJECT-TYPE
	SYNTAX	 CounterBasedGauge64
	MAX-ACCESS read-only
	STATUS current
	DESCRIPTION "Config Rules: Number of rules in ruleset config"

	::={rulesetCompilerConfigRules 3}

rulesetCompilerConfigRulesLevelTable OBJECT-TYPE
	SYNTAX      SEQUENCE OF RulesetCompilerConfigRulesLevelEntry
	MAX-ACCESS  not-accessible
	STATUS      current
	DESCRIPTION
	"Table for rulesetCompilerConfigRules"
	::={rulesetCompilerConfigRules 4}

rulesetCompilerConfigRulesLevelEntry OBJECT-TYPE
	SYNTAX      RulesetCompilerConfigRulesLevelEntry
	MAX-ACCESS  not-accessible
	STATUS      current
	DESCRIPTION
	"Table entry for rulesetCompilerConfigRules"
	INDEX { rulesetCompilerConfigRulesLevelName }
	::={rulesetCompilerConfigRulesLevelTable 1}

RulesetCompilerConfigRulesLevelEntry ::=
	SEQUENCE {
		rulesetCompilerConfigRulesLevelName	DisplayString,
		rulesetCompilerConfigRulesLevelVal	CounterBasedGauge64,
		rulesetCompilerConfigRulesLevelMax	CounterBasedGauge64
	}

rulesetCompilerConfigRulesLevelName OBJECT-TYPE
	SYNTAX      DisplayString
	MAX-ACCESS  not-accessible
	STATUS      current
	DESCRIPTION
	"Table entry display string for rulesetCompilerConfigRules"
	::={rulesetCompilerConfigRulesLevelEntry 1}

rulesetCompilerConfigRulesLevelVal OBJECT-TYPE
	SYNTAX	 CounterBasedGauge64
	MAX-ACCESS  read-only
	STATUS      current
	DESCRIPTION
	"Table entry attribute for rulesetCompilerConfigRules"
	::={rulesetCompilerConfigRulesLevelEntry 2}

rulesetCompilerConfigRulesLevelMax OBJECT-TYPE
	SYNTAX	 CounterBasedGauge64
	MAX-ACCESS  read-only
	STATUS      current
	DESCRIPTION
	"Table entry attribute for rulesetCompilerConfigRules"
	::={rulesetCompilerConfigRulesLevelEntry 4}


rulesetCompilerConfigRulesFilter	OBJECT IDENTIFIER ::={rulesetCompiler 12}

rulesetCompilerConfigRulesFilterVal	OBJECT-TYPE
	SYNTAX	 CounterBasedGauge64
	MAX-ACCESS read-only
	STATUS current
	DESCRIPTION "Config Rules: Number of filter rules in ruleset config"

	::={rulesetCompilerConfigRulesFilter 1}

rulesetCompilerConfigRulesFilterMax	OBJECT-TYPE
	SYNTAX	 CounterBasedGauge64
	MAX-ACCESS read-only
	STATUS current
	DESCRIPTION "Config Rules: Number of filter rules in ruleset config"

	::={rulesetCompilerConfigRulesFilter 3}

rulesetCompilerConfigRulesFilterLevelTable OBJECT-TYPE
	SYNTAX      SEQUENCE OF RulesetCompilerConfigRulesFilterLevelEntry
	MAX-ACCESS  not-accessible
	STATUS      current
	DESCRIPTION
	"Table for rulesetCompilerConfigRulesFilter"
	::={rulesetCompilerConfigRulesFilter 4}

rulesetCompilerConfigRulesFilterLevelEntry OBJECT-TYPE
	SYNTAX      RulesetCompilerConfigRulesFilterLevelEntry
	MAX-ACCESS  not-accessible
	STATUS      current
	DESCRIPTION
	"Table entry for rulesetCompilerConfigRulesFilter"
	INDEX { rulesetCompilerConfigRulesFilterLevelName }
	::={rulesetCompilerConfigRulesFilterLevelTable 1}

RulesetCompilerConfigRulesFilterLevelEntry ::=
	SEQUENCE {
		rulesetCompilerConfigRulesFilterLevelName	DisplayString,
		rulesetCompilerConfigRulesFilterLevelVal	CounterBasedGauge64,
		rulesetCompilerConfigRulesFilterLevelMax	CounterBasedGauge64
	}

rulesetCompilerConfigRulesFilterLevelName OBJECT-TYPE
	SYNTAX      DisplayString
	MAX-ACCESS  not-accessible
	STATUS      current
	DESCRIPTION
	"Table entry display string for rulesetCompilerConfigRulesFilter"
	::={rulesetCompilerConfigRulesFilterLevelEntry 1}

rulesetCompilerConfigRulesFilterLevelVal OBJECT-TYPE
	SYNTAX	 CounterBasedGauge64
	MAX-ACCESS  read-only
	STATUS      current
	DESCRIPTION
	"Table entry attribute for rulesetCompilerConfigRulesFilter"
	::={rulesetCompilerConfigRulesFilterLevelEntry 2}

rulesetCompilerConfigRulesFilterLevelMax OBJECT-TYPE
	SYNTAX	 CounterBasedGauge64
	MAX-ACCESS  read-only
	STATUS      current
	DESCRIPTION
	"Table entry attribute for rulesetCompilerConfigRulesFilter"
	::={rulesetCompilerConfigRulesFilterLevelEntry 4}


rulesetCompilerConfigRulesShaping	OBJECT IDENTIFIER ::={rulesetCompiler 13}

rulesetCompilerConfigRulesShapingVal	OBJECT-TYPE
	SYNTAX	 CounterBasedGauge64
	MAX-ACCESS read-only
	STATUS current
	DESCRIPTION "Config Rules: Number of shaping rules in ruleset config"

	::={rulesetCompilerConfigRulesShaping 1}

rulesetCompilerConfigRulesShapingMax	OBJECT-TYPE
	SYNTAX	 CounterBasedGauge64
	MAX-ACCESS read-only
	STATUS current
	DESCRIPTION "Config Rules: Number of shaping rules in ruleset config"

	::={rulesetCompilerConfigRulesShaping 3}

rulesetCompilerConfigRulesShapingLevelTable OBJECT-TYPE
	SYNTAX      SEQUENCE OF RulesetCompilerConfigRulesShapingLevelEntry
	MAX-ACCESS  not-accessible
	STATUS      current
	DESCRIPTION
	"Table for rulesetCompilerConfigRulesShaping"
	::={rulesetCompilerConfigRulesShaping 4}

rulesetCompilerConfigRulesShapingLevelEntry OBJECT-TYPE
	SYNTAX      RulesetCompilerConfigRulesShapingLevelEntry
	MAX-ACCESS  not-accessible
	STATUS      current
	DESCRIPTION
	"Table entry for rulesetCompilerConfigRulesShaping"
	INDEX { rulesetCompilerConfigRulesShapingLevelName }
	::={rulesetCompilerConfigRulesShapingLevelTable 1}

RulesetCompilerConfigRulesShapingLevelEntry ::=
	SEQUENCE {
		rulesetCompilerConfigRulesShapingLevelName	DisplayString,
		rulesetCompilerConfigRulesShapingLevelVal	CounterBasedGauge64,
		rulesetCompilerConfigRulesShapingLevelMax	CounterBasedGauge64
	}

rulesetCompilerConfigRulesShapingLevelName OBJECT-TYPE
	SYNTAX      DisplayString
	MAX-ACCESS  not-accessible
	STATUS      current
	DESCRIPTION
	"Table entry display string for rulesetCompilerConfigRulesShaping"
	::={rulesetCompilerConfigRulesShapingLevelEntry 1}

rulesetCompilerConfigRulesShapingLevelVal OBJECT-TYPE
	SYNTAX	 CounterBasedGauge64
	MAX-ACCESS  read-only
	STATUS      current
	DESCRIPTION
	"Table entry attribute for rulesetCompilerConfigRulesShaping"
	::={rulesetCompilerConfigRulesShapingLevelEntry 2}

rulesetCompilerConfigRulesShapingLevelMax OBJECT-TYPE
	SYNTAX	 CounterBasedGauge64
	MAX-ACCESS  read-only
	STATUS      current
	DESCRIPTION
	"Table entry attribute for rulesetCompilerConfigRulesShaping"
	::={rulesetCompilerConfigRulesShapingLevelEntry 4}


rulesetCompilerConfigRulesStats	OBJECT IDENTIFIER ::={rulesetCompiler 14}

rulesetCompilerConfigRulesStatsVal	OBJECT-TYPE
	SYNTAX	 CounterBasedGauge64
	MAX-ACCESS read-only
	STATUS current
	DESCRIPTION "Config Rules: Number of stats rules in ruleset config"

	::={rulesetCompilerConfigRulesStats 1}

rulesetCompilerConfigRulesStatsMax	OBJECT-TYPE
	SYNTAX	 CounterBasedGauge64
	MAX-ACCESS read-only
	STATUS current
	DESCRIPTION "Config Rules: Number of stats rules in ruleset config"

	::={rulesetCompilerConfigRulesStats 3}

rulesetCompilerConfigRulesStatsLevelTable OBJECT-TYPE
	SYNTAX      SEQUENCE OF RulesetCompilerConfigRulesStatsLevelEntry
	MAX-ACCESS  not-accessible
	STATUS      current
	DESCRIPTION
	"Table for rulesetCompilerConfigRulesStats"
	::={rulesetCompilerConfigRulesStats 4}

rulesetCompilerConfigRulesStatsLevelEntry OBJECT-TYPE
	SYNTAX      RulesetCompilerConfigRulesStatsLevelEntry
	MAX-ACCESS  not-accessible
	STATUS      current
	DESCRIPTION
	"Table entry for rulesetCompilerConfigRulesStats"
	INDEX { rulesetCompilerConfigRulesStatsLevelName }
	::={rulesetCompilerConfigRulesStatsLevelTable 1}

RulesetCompilerConfigRulesStatsLevelEntry ::=
	SEQUENCE {
		rulesetCompilerConfigRulesStatsLevelName	DisplayString,
		rulesetCompilerConfigRulesStatsLevelVal	CounterBasedGauge64,
		rulesetCompilerConfigRulesStatsLevelMax	CounterBasedGauge64
	}

rulesetCompilerConfigRulesStatsLevelName OBJECT-TYPE
	SYNTAX      DisplayString
	MAX-ACCESS  not-accessible
	STATUS      current
	DESCRIPTION
	"Table entry display string for rulesetCompilerConfigRulesStats"
	::={rulesetCompilerConfigRulesStatsLevelEntry 1}

rulesetCompilerConfigRulesStatsLevelVal OBJECT-TYPE
	SYNTAX	 CounterBasedGauge64
	MAX-ACCESS  read-only
	STATUS      current
	DESCRIPTION
	"Table entry attribute for rulesetCompilerConfigRulesStats"
	::={rulesetCompilerConfigRulesStatsLevelEntry 2}

rulesetCompilerConfigRulesStatsLevelMax OBJECT-TYPE
	SYNTAX	 CounterBasedGauge64
	MAX-ACCESS  read-only
	STATUS      current
	DESCRIPTION
	"Table entry attribute for rulesetCompilerConfigRulesStats"
	::={rulesetCompilerConfigRulesStatsLevelEntry 4}


rulesetCompilerSplitByShapingRules	OBJECT IDENTIFIER ::={rulesetCompiler 21}

rulesetCompilerSplitByShapingRulesVal	OBJECT-TYPE
	SYNTAX	 CounterBasedGauge64
	MAX-ACCESS read-only
	STATUS current
	DESCRIPTION "SplitBy Shaping: Number of shaping rules after splitby"

	::={rulesetCompilerSplitByShapingRules 1}

rulesetCompilerSplitByShapingRulesMax	OBJECT-TYPE
	SYNTAX	 CounterBasedGauge64
	MAX-ACCESS read-only
	STATUS current
	DESCRIPTION "SplitBy Shaping: Number of shaping rules after splitby"

	::={rulesetCompilerSplitByShapingRules 3}

rulesetCompilerSplitByShapingRulesLevelTable OBJECT-TYPE
	SYNTAX      SEQUENCE OF RulesetCompilerSplitByShapingRulesLevelEntry
	MAX-ACCESS  not-accessible
	STATUS      current
	DESCRIPTION
	"Table for rulesetCompilerSplitByShapingRules"
	::={rulesetCompilerSplitByShapingRules 4}

rulesetCompilerSplitByShapingRulesLevelEntry OBJECT-TYPE
	SYNTAX      RulesetCompilerSplitByShapingRulesLevelEntry
	MAX-ACCESS  not-accessible
	STATUS      current
	DESCRIPTION
	"Table entry for rulesetCompilerSplitByShapingRules"
	INDEX { rulesetCompilerSplitByShapingRulesLevelName }
	::={rulesetCompilerSplitByShapingRulesLevelTable 1}

RulesetCompilerSplitByShapingRulesLevelEntry ::=
	SEQUENCE {
		rulesetCompilerSplitByShapingRulesLevelName	DisplayString,
		rulesetCompilerSplitByShapingRulesLevelVal	CounterBasedGauge64,
		rulesetCompilerSplitByShapingRulesLevelMax	CounterBasedGauge64
	}

rulesetCompilerSplitByShapingRulesLevelName OBJECT-TYPE
	SYNTAX      DisplayString
	MAX-ACCESS  not-accessible
	STATUS      current
	DESCRIPTION
	"Table entry display string for rulesetCompilerSplitByShapingRules"
	::={rulesetCompilerSplitByShapingRulesLevelEntry 1}

rulesetCompilerSplitByShapingRulesLevelVal OBJECT-TYPE
	SYNTAX	 CounterBasedGauge64
	MAX-ACCESS  read-only
	STATUS      current
	DESCRIPTION
	"Table entry attribute for rulesetCompilerSplitByShapingRules"
	::={rulesetCompilerSplitByShapingRulesLevelEntry 2}

rulesetCompilerSplitByShapingRulesLevelMax OBJECT-TYPE
	SYNTAX	 CounterBasedGauge64
	MAX-ACCESS  read-only
	STATUS      current
	DESCRIPTION
	"Table entry attribute for rulesetCompilerSplitByShapingRules"
	::={rulesetCompilerSplitByShapingRulesLevelEntry 4}


rulesetCompilerSplitByShapingObjects	OBJECT IDENTIFIER ::={rulesetCompiler 22}

rulesetCompilerSplitByShapingObjectsVal	OBJECT-TYPE
	SYNTAX	 CounterBasedGauge64
	MAX-ACCESS read-only
	STATUS current
	DESCRIPTION "SplitBy Shaping: Number of cloned shaping objects created"

	::={rulesetCompilerSplitByShapingObjects 1}

rulesetCompilerSplitByShapingObjectsMax	OBJECT-TYPE
	SYNTAX	 CounterBasedGauge64
	MAX-ACCESS read-only
	STATUS current
	DESCRIPTION "SplitBy Shaping: Number of cloned shaping objects created"

	::={rulesetCompilerSplitByShapingObjects 3}

rulesetCompilerSplitByShapingObjectsLevelTable OBJECT-TYPE
	SYNTAX      SEQUENCE OF RulesetCompilerSplitByShapingObjectsLevelEntry
	MAX-ACCESS  not-accessible
	STATUS      current
	DESCRIPTION
	"Table for rulesetCompilerSplitByShapingObjects"
	::={rulesetCompilerSplitByShapingObjects 4}

rulesetCompilerSplitByShapingObjectsLevelEntry OBJECT-TYPE
	SYNTAX      RulesetCompilerSplitByShapingObjectsLevelEntry
	MAX-ACCESS  not-accessible
	STATUS      current
	DESCRIPTION
	"Table entry for rulesetCompilerSplitByShapingObjects"
	INDEX { rulesetCompilerSplitByShapingObjectsLevelName }
	::={rulesetCompilerSplitByShapingObjectsLevelTable 1}

RulesetCompilerSplitByShapingObjectsLevelEntry ::=
	SEQUENCE {
		rulesetCompilerSplitByShapingObjectsLevelName	DisplayString,
		rulesetCompilerSplitByShapingObjectsLevelVal	CounterBasedGauge64,
		rulesetCompilerSplitByShapingObjectsLevelMax	CounterBasedGauge64
	}

rulesetCompilerSplitByShapingObjectsLevelName OBJECT-TYPE
	SYNTAX      DisplayString
	MAX-ACCESS  not-accessible
	STATUS      current
	DESCRIPTION
	"Table entry display string for rulesetCompilerSplitByShapingObjects"
	::={rulesetCompilerSplitByShapingObjectsLevelEntry 1}

rulesetCompilerSplitByShapingObjectsLevelVal OBJECT-TYPE
	SYNTAX	 CounterBasedGauge64
	MAX-ACCESS  read-only
	STATUS      current
	DESCRIPTION
	"Table entry attribute for rulesetCompilerSplitByShapingObjects"
	::={rulesetCompilerSplitByShapingObjectsLevelEntry 2}

rulesetCompilerSplitByShapingObjectsLevelMax OBJECT-TYPE
	SYNTAX	 CounterBasedGauge64
	MAX-ACCESS  read-only
	STATUS      current
	DESCRIPTION
	"Table entry attribute for rulesetCompilerSplitByShapingObjects"
	::={rulesetCompilerSplitByShapingObjectsLevelEntry 4}


rulesetCompilerCompiledRules	OBJECT IDENTIFIER ::={rulesetCompiler 31}

rulesetCompilerCompiledRulesVal	OBJECT-TYPE
	SYNTAX	 CounterBasedGauge64
	MAX-ACCESS read-only
	STATUS current
	DESCRIPTION "Compiled Rules: Number of rules in compiled ruleset"

	::={rulesetCompilerCompiledRules 1}

rulesetCompilerCompiledRulesMax	OBJECT-TYPE
	SYNTAX	 CounterBasedGauge64
	MAX-ACCESS read-only
	STATUS current
	DESCRIPTION "Compiled Rules: Number of rules in compiled ruleset"

	::={rulesetCompilerCompiledRules 3}

rulesetCompilerCompiledRulesLevelTable OBJECT-TYPE
	SYNTAX      SEQUENCE OF RulesetCompilerCompiledRulesLevelEntry
	MAX-ACCESS  not-accessible
	STATUS      current
	DESCRIPTION
	"Table for rulesetCompilerCompiledRules"
	::={rulesetCompilerCompiledRules 4}

rulesetCompilerCompiledRulesLevelEntry OBJECT-TYPE
	SYNTAX      RulesetCompilerCompiledRulesLevelEntry
	MAX-ACCESS  not-accessible
	STATUS      current
	DESCRIPTION
	"Table entry for rulesetCompilerCompiledRules"
	INDEX { rulesetCompilerCompiledRulesLevelName }
	::={rulesetCompilerCompiledRulesLevelTable 1}

RulesetCompilerCompiledRulesLevelEntry ::=
	SEQUENCE {
		rulesetCompilerCompiledRulesLevelName	DisplayString,
		rulesetCompilerCompiledRulesLevelVal	CounterBasedGauge64,
		rulesetCompilerCompiledRulesLevelMax	CounterBasedGauge64
	}

rulesetCompilerCompiledRulesLevelName OBJECT-TYPE
	SYNTAX      DisplayString
	MAX-ACCESS  not-accessible
	STATUS      current
	DESCRIPTION
	"Table entry display string for rulesetCompilerCompiledRules"
	::={rulesetCompilerCompiledRulesLevelEntry 1}

rulesetCompilerCompiledRulesLevelVal OBJECT-TYPE
	SYNTAX	 CounterBasedGauge64
	MAX-ACCESS  read-only
	STATUS      current
	DESCRIPTION
	"Table entry attribute for rulesetCompilerCompiledRules"
	::={rulesetCompilerCompiledRulesLevelEntry 2}

rulesetCompilerCompiledRulesLevelMax OBJECT-TYPE
	SYNTAX	 CounterBasedGauge64
	MAX-ACCESS  read-only
	STATUS      current
	DESCRIPTION
	"Table entry attribute for rulesetCompilerCompiledRules"
	::={rulesetCompilerCompiledRulesLevelEntry 4}


rulesetCompilerCompiledRulesFilter	OBJECT IDENTIFIER ::={rulesetCompiler 32}

rulesetCompilerCompiledRulesFilterVal	OBJECT-TYPE
	SYNTAX	 CounterBasedGauge64
	MAX-ACCESS read-only
	STATUS current
	DESCRIPTION "Compiled Rules: Number of filter rules in compiled ruleset"

	::={rulesetCompilerCompiledRulesFilter 1}

rulesetCompilerCompiledRulesFilterMax	OBJECT-TYPE
	SYNTAX	 CounterBasedGauge64
	MAX-ACCESS read-only
	STATUS current
	DESCRIPTION "Compiled Rules: Number of filter rules in compiled ruleset"

	::={rulesetCompilerCompiledRulesFilter 3}

rulesetCompilerCompiledRulesFilterLevelTable OBJECT-TYPE
	SYNTAX      SEQUENCE OF RulesetCompilerCompiledRulesFilterLevelEntry
	MAX-ACCESS  not-accessible
	STATUS      current
	DESCRIPTION
	"Table for rulesetCompilerCompiledRulesFilter"
	::={rulesetCompilerCompiledRulesFilter 4}

rulesetCompilerCompiledRulesFilterLevelEntry OBJECT-TYPE
	SYNTAX      RulesetCompilerCompiledRulesFilterLevelEntry
	MAX-ACCESS  not-accessible
	STATUS      current
	DESCRIPTION
	"Table entry for rulesetCompilerCompiledRulesFilter"
	INDEX { rulesetCompilerCompiledRulesFilterLevelName }
	::={rulesetCompilerCompiledRulesFilterLevelTable 1}

RulesetCompilerCompiledRulesFilterLevelEntry ::=
	SEQUENCE {
		rulesetCompilerCompiledRulesFilterLevelName	DisplayString,
		rulesetCompilerCompiledRulesFilterLevelVal	CounterBasedGauge64,
		rulesetCompilerCompiledRulesFilterLevelMax	CounterBasedGauge64
	}

rulesetCompilerCompiledRulesFilterLevelName OBJECT-TYPE
	SYNTAX      DisplayString
	MAX-ACCESS  not-accessible
	STATUS      current
	DESCRIPTION
	"Table entry display string for rulesetCompilerCompiledRulesFilter"
	::={rulesetCompilerCompiledRulesFilterLevelEntry 1}

rulesetCompilerCompiledRulesFilterLevelVal OBJECT-TYPE
	SYNTAX	 CounterBasedGauge64
	MAX-ACCESS  read-only
	STATUS      current
	DESCRIPTION
	"Table entry attribute for rulesetCompilerCompiledRulesFilter"
	::={rulesetCompilerCompiledRulesFilterLevelEntry 2}

rulesetCompilerCompiledRulesFilterLevelMax OBJECT-TYPE
	SYNTAX	 CounterBasedGauge64
	MAX-ACCESS  read-only
	STATUS      current
	DESCRIPTION
	"Table entry attribute for rulesetCompilerCompiledRulesFilter"
	::={rulesetCompilerCompiledRulesFilterLevelEntry 4}


rulesetCompilerCompiledRulesShaping	OBJECT IDENTIFIER ::={rulesetCompiler 33}

rulesetCompilerCompiledRulesShapingVal	OBJECT-TYPE
	SYNTAX	 CounterBasedGauge64
	MAX-ACCESS read-only
	STATUS current
	DESCRIPTION "Compiled Rules: Number of shaping rules in compiled ruleset"

	::={rulesetCompilerCompiledRulesShaping 1}

rulesetCompilerCompiledRulesShapingMax	OBJECT-TYPE
	SYNTAX	 CounterBasedGauge64
	MAX-ACCESS read-only
	STATUS current
	DESCRIPTION "Compiled Rules: Number of shaping rules in compiled ruleset"

	::={rulesetCompilerCompiledRulesShaping 3}

rulesetCompilerCompiledRulesShapingLevelTable OBJECT-TYPE
	SYNTAX      SEQUENCE OF RulesetCompilerCompiledRulesShapingLevelEntry
	MAX-ACCESS  not-accessible
	STATUS      current
	DESCRIPTION
	"Table for rulesetCompilerCompiledRulesShaping"
	::={rulesetCompilerCompiledRulesShaping 4}

rulesetCompilerCompiledRulesShapingLevelEntry OBJECT-TYPE
	SYNTAX      RulesetCompilerCompiledRulesShapingLevelEntry
	MAX-ACCESS  not-accessible
	STATUS      current
	DESCRIPTION
	"Table entry for rulesetCompilerCompiledRulesShaping"
	INDEX { rulesetCompilerCompiledRulesShapingLevelName }
	::={rulesetCompilerCompiledRulesShapingLevelTable 1}

RulesetCompilerCompiledRulesShapingLevelEntry ::=
	SEQUENCE {
		rulesetCompilerCompiledRulesShapingLevelName	DisplayString,
		rulesetCompilerCompiledRulesShapingLevelVal	CounterBasedGauge64,
		rulesetCompilerCompiledRulesShapingLevelMax	CounterBasedGauge64
	}

rulesetCompilerCompiledRulesShapingLevelName OBJECT-TYPE
	SYNTAX      DisplayString
	MAX-ACCESS  not-accessible
	STATUS      current
	DESCRIPTION
	"Table entry display string for rulesetCompilerCompiledRulesShaping"
	::={rulesetCompilerCompiledRulesShapingLevelEntry 1}

rulesetCompilerCompiledRulesShapingLevelVal OBJECT-TYPE
	SYNTAX	 CounterBasedGauge64
	MAX-ACCESS  read-only
	STATUS      current
	DESCRIPTION
	"Table entry attribute for rulesetCompilerCompiledRulesShaping"
	::={rulesetCompilerCompiledRulesShapingLevelEntry 2}

rulesetCompilerCompiledRulesShapingLevelMax OBJECT-TYPE
	SYNTAX	 CounterBasedGauge64
	MAX-ACCESS  read-only
	STATUS      current
	DESCRIPTION
	"Table entry attribute for rulesetCompilerCompiledRulesShaping"
	::={rulesetCompilerCompiledRulesShapingLevelEntry 4}


rulesetCompilerCompiledRulesStats	OBJECT IDENTIFIER ::={rulesetCompiler 34}

rulesetCompilerCompiledRulesStatsVal	OBJECT-TYPE
	SYNTAX	 CounterBasedGauge64
	MAX-ACCESS read-only
	STATUS current
	DESCRIPTION "Compiled Rules: Number of stats rules in compiled ruleset"

	::={rulesetCompilerCompiledRulesStats 1}

rulesetCompilerCompiledRulesStatsMax	OBJECT-TYPE
	SYNTAX	 CounterBasedGauge64
	MAX-ACCESS read-only
	STATUS current
	DESCRIPTION "Compiled Rules: Number of stats rules in compiled ruleset"

	::={rulesetCompilerCompiledRulesStats 3}

rulesetCompilerCompiledRulesStatsLevelTable OBJECT-TYPE
	SYNTAX      SEQUENCE OF RulesetCompilerCompiledRulesStatsLevelEntry
	MAX-ACCESS  not-accessible
	STATUS      current
	DESCRIPTION
	"Table for rulesetCompilerCompiledRulesStats"
	::={rulesetCompilerCompiledRulesStats 4}

rulesetCompilerCompiledRulesStatsLevelEntry OBJECT-TYPE
	SYNTAX      RulesetCompilerCompiledRulesStatsLevelEntry
	MAX-ACCESS  not-accessible
	STATUS      current
	DESCRIPTION
	"Table entry for rulesetCompilerCompiledRulesStats"
	INDEX { rulesetCompilerCompiledRulesStatsLevelName }
	::={rulesetCompilerCompiledRulesStatsLevelTable 1}

RulesetCompilerCompiledRulesStatsLevelEntry ::=
	SEQUENCE {
		rulesetCompilerCompiledRulesStatsLevelName	DisplayString,
		rulesetCompilerCompiledRulesStatsLevelVal	CounterBasedGauge64,
		rulesetCompilerCompiledRulesStatsLevelMax	CounterBasedGauge64
	}

rulesetCompilerCompiledRulesStatsLevelName OBJECT-TYPE
	SYNTAX      DisplayString
	MAX-ACCESS  not-accessible
	STATUS      current
	DESCRIPTION
	"Table entry display string for rulesetCompilerCompiledRulesStats"
	::={rulesetCompilerCompiledRulesStatsLevelEntry 1}

rulesetCompilerCompiledRulesStatsLevelVal OBJECT-TYPE
	SYNTAX	 CounterBasedGauge64
	MAX-ACCESS  read-only
	STATUS      current
	DESCRIPTION
	"Table entry attribute for rulesetCompilerCompiledRulesStats"
	::={rulesetCompilerCompiledRulesStatsLevelEntry 2}

rulesetCompilerCompiledRulesStatsLevelMax OBJECT-TYPE
	SYNTAX	 CounterBasedGauge64
	MAX-ACCESS  read-only
	STATUS      current
	DESCRIPTION
	"Table entry attribute for rulesetCompilerCompiledRulesStats"
	::={rulesetCompilerCompiledRulesStatsLevelEntry 4}


rulesetCompilerStaticTime	OBJECT IDENTIFIER ::={rulesetCompiler 41}

rulesetCompilerStaticTimeVal	OBJECT-TYPE
	SYNTAX	 CounterBasedGauge64
	MAX-ACCESS read-only
	STATUS current
	DESCRIPTION "Ruleset static: Compile and send time, in ms"

	::={rulesetCompilerStaticTime 1}

rulesetCompilerStaticTimeMax	OBJECT-TYPE
	SYNTAX	 CounterBasedGauge64
	MAX-ACCESS read-only
	STATUS current
	DESCRIPTION "Ruleset static: Compile and send time, in ms"

	::={rulesetCompilerStaticTime 3}

rulesetCompilerStaticTimeLevelTable OBJECT-TYPE
	SYNTAX      SEQUENCE OF RulesetCompilerStaticTimeLevelEntry
	MAX-ACCESS  not-accessible
	STATUS      current
	DESCRIPTION
	"Table for rulesetCompilerStaticTime"
	::={rulesetCompilerStaticTime 4}

rulesetCompilerStaticTimeLevelEntry OBJECT-TYPE
	SYNTAX      RulesetCompilerStaticTimeLevelEntry
	MAX-ACCESS  not-accessible
	STATUS      current
	DESCRIPTION
	"Table entry for rulesetCompilerStaticTime"
	INDEX { rulesetCompilerStaticTimeLevelName }
	::={rulesetCompilerStaticTimeLevelTable 1}

RulesetCompilerStaticTimeLevelEntry ::=
	SEQUENCE {
		rulesetCompilerStaticTimeLevelName	DisplayString,
		rulesetCompilerStaticTimeLevelVal	CounterBasedGauge64,
		rulesetCompilerStaticTimeLevelMax	CounterBasedGauge64
	}

rulesetCompilerStaticTimeLevelName OBJECT-TYPE
	SYNTAX      DisplayString
	MAX-ACCESS  not-accessible
	STATUS      current
	DESCRIPTION
	"Table entry display string for rulesetCompilerStaticTime"
	::={rulesetCompilerStaticTimeLevelEntry 1}

rulesetCompilerStaticTimeLevelVal OBJECT-TYPE
	SYNTAX	 CounterBasedGauge64
	MAX-ACCESS  read-only
	STATUS      current
	DESCRIPTION
	"Table entry attribute for rulesetCompilerStaticTime"
	::={rulesetCompilerStaticTimeLevelEntry 2}

rulesetCompilerStaticTimeLevelMax OBJECT-TYPE
	SYNTAX	 CounterBasedGauge64
	MAX-ACCESS  read-only
	STATUS      current
	DESCRIPTION
	"Table entry attribute for rulesetCompilerStaticTime"
	::={rulesetCompilerStaticTimeLevelEntry 4}


rulesetCalcjobPrefixesIpv4	OBJECT IDENTIFIER ::={rulesetCompiler 51}

rulesetCalcjobPrefixesIpv4Val	OBJECT-TYPE
	SYNTAX	 CounterBasedGauge64
	MAX-ACCESS read-only
	STATUS current
	DESCRIPTION "Ruleset calcjob: Sum of static and dynamic IPv4 prefixes to consider for compile"

	::={rulesetCalcjobPrefixesIpv4 1}

rulesetCalcjobPrefixesIpv4Max	OBJECT-TYPE
	SYNTAX	 CounterBasedGauge64
	MAX-ACCESS read-only
	STATUS current
	DESCRIPTION "Ruleset calcjob: Sum of static and dynamic IPv4 prefixes to consider for compile"

	::={rulesetCalcjobPrefixesIpv4 3}

rulesetCalcjobPrefixesIpv4LevelTable OBJECT-TYPE
	SYNTAX      SEQUENCE OF RulesetCalcjobPrefixesIpv4LevelEntry
	MAX-ACCESS  not-accessible
	STATUS      current
	DESCRIPTION
	"Table for rulesetCalcjobPrefixesIpv4"
	::={rulesetCalcjobPrefixesIpv4 4}

rulesetCalcjobPrefixesIpv4LevelEntry OBJECT-TYPE
	SYNTAX      RulesetCalcjobPrefixesIpv4LevelEntry
	MAX-ACCESS  not-accessible
	STATUS      current
	DESCRIPTION
	"Table entry for rulesetCalcjobPrefixesIpv4"
	INDEX { rulesetCalcjobPrefixesIpv4LevelName }
	::={rulesetCalcjobPrefixesIpv4LevelTable 1}

RulesetCalcjobPrefixesIpv4LevelEntry ::=
	SEQUENCE {
		rulesetCalcjobPrefixesIpv4LevelName	DisplayString,
		rulesetCalcjobPrefixesIpv4LevelVal	CounterBasedGauge64,
		rulesetCalcjobPrefixesIpv4LevelMax	CounterBasedGauge64
	}

rulesetCalcjobPrefixesIpv4LevelName OBJECT-TYPE
	SYNTAX      DisplayString
	MAX-ACCESS  not-accessible
	STATUS      current
	DESCRIPTION
	"Table entry display string for rulesetCalcjobPrefixesIpv4"
	::={rulesetCalcjobPrefixesIpv4LevelEntry 1}

rulesetCalcjobPrefixesIpv4LevelVal OBJECT-TYPE
	SYNTAX	 CounterBasedGauge64
	MAX-ACCESS  read-only
	STATUS      current
	DESCRIPTION
	"Table entry attribute for rulesetCalcjobPrefixesIpv4"
	::={rulesetCalcjobPrefixesIpv4LevelEntry 2}

rulesetCalcjobPrefixesIpv4LevelMax OBJECT-TYPE
	SYNTAX	 CounterBasedGauge64
	MAX-ACCESS  read-only
	STATUS      current
	DESCRIPTION
	"Table entry attribute for rulesetCalcjobPrefixesIpv4"
	::={rulesetCalcjobPrefixesIpv4LevelEntry 4}


rulesetCalcjobPrefixesIpv6	OBJECT IDENTIFIER ::={rulesetCompiler 52}

rulesetCalcjobPrefixesIpv6Val	OBJECT-TYPE
	SYNTAX	 CounterBasedGauge64
	MAX-ACCESS read-only
	STATUS current
	DESCRIPTION "Ruleset calcjob: Sum of static and dynamic IPv6 prefixes to consider for compile"

	::={rulesetCalcjobPrefixesIpv6 1}

rulesetCalcjobPrefixesIpv6Max	OBJECT-TYPE
	SYNTAX	 CounterBasedGauge64
	MAX-ACCESS read-only
	STATUS current
	DESCRIPTION "Ruleset calcjob: Sum of static and dynamic IPv6 prefixes to consider for compile"

	::={rulesetCalcjobPrefixesIpv6 3}

rulesetCalcjobPrefixesIpv6LevelTable OBJECT-TYPE
	SYNTAX      SEQUENCE OF RulesetCalcjobPrefixesIpv6LevelEntry
	MAX-ACCESS  not-accessible
	STATUS      current
	DESCRIPTION
	"Table for rulesetCalcjobPrefixesIpv6"
	::={rulesetCalcjobPrefixesIpv6 4}

rulesetCalcjobPrefixesIpv6LevelEntry OBJECT-TYPE
	SYNTAX      RulesetCalcjobPrefixesIpv6LevelEntry
	MAX-ACCESS  not-accessible
	STATUS      current
	DESCRIPTION
	"Table entry for rulesetCalcjobPrefixesIpv6"
	INDEX { rulesetCalcjobPrefixesIpv6LevelName }
	::={rulesetCalcjobPrefixesIpv6LevelTable 1}

RulesetCalcjobPrefixesIpv6LevelEntry ::=
	SEQUENCE {
		rulesetCalcjobPrefixesIpv6LevelName	DisplayString,
		rulesetCalcjobPrefixesIpv6LevelVal	CounterBasedGauge64,
		rulesetCalcjobPrefixesIpv6LevelMax	CounterBasedGauge64
	}

rulesetCalcjobPrefixesIpv6LevelName OBJECT-TYPE
	SYNTAX      DisplayString
	MAX-ACCESS  not-accessible
	STATUS      current
	DESCRIPTION
	"Table entry display string for rulesetCalcjobPrefixesIpv6"
	::={rulesetCalcjobPrefixesIpv6LevelEntry 1}

rulesetCalcjobPrefixesIpv6LevelVal OBJECT-TYPE
	SYNTAX	 CounterBasedGauge64
	MAX-ACCESS  read-only
	STATUS      current
	DESCRIPTION
	"Table entry attribute for rulesetCalcjobPrefixesIpv6"
	::={rulesetCalcjobPrefixesIpv6LevelEntry 2}

rulesetCalcjobPrefixesIpv6LevelMax OBJECT-TYPE
	SYNTAX	 CounterBasedGauge64
	MAX-ACCESS  read-only
	STATUS      current
	DESCRIPTION
	"Table entry attribute for rulesetCalcjobPrefixesIpv6"
	::={rulesetCalcjobPrefixesIpv6LevelEntry 4}


rulesetCalcjobNumjobs	OBJECT IDENTIFIER ::={rulesetCompiler 53}

rulesetCalcjobNumjobsVal	OBJECT-TYPE
	SYNTAX	 CounterBasedGauge64
	MAX-ACCESS read-only
	STATUS current
	DESCRIPTION "Ruleset calcjob: Number of calc jobs"

	::={rulesetCalcjobNumjobs 1}

rulesetCalcjobNumjobsMax	OBJECT-TYPE
	SYNTAX	 CounterBasedGauge64
	MAX-ACCESS read-only
	STATUS current
	DESCRIPTION "Ruleset calcjob: Number of calc jobs"

	::={rulesetCalcjobNumjobs 3}

rulesetCalcjobNumjobsLevelTable OBJECT-TYPE
	SYNTAX      SEQUENCE OF RulesetCalcjobNumjobsLevelEntry
	MAX-ACCESS  not-accessible
	STATUS      current
	DESCRIPTION
	"Table for rulesetCalcjobNumjobs"
	::={rulesetCalcjobNumjobs 4}

rulesetCalcjobNumjobsLevelEntry OBJECT-TYPE
	SYNTAX      RulesetCalcjobNumjobsLevelEntry
	MAX-ACCESS  not-accessible
	STATUS      current
	DESCRIPTION
	"Table entry for rulesetCalcjobNumjobs"
	INDEX { rulesetCalcjobNumjobsLevelName }
	::={rulesetCalcjobNumjobsLevelTable 1}

RulesetCalcjobNumjobsLevelEntry ::=
	SEQUENCE {
		rulesetCalcjobNumjobsLevelName	DisplayString,
		rulesetCalcjobNumjobsLevelVal	CounterBasedGauge64,
		rulesetCalcjobNumjobsLevelMax	CounterBasedGauge64
	}

rulesetCalcjobNumjobsLevelName OBJECT-TYPE
	SYNTAX      DisplayString
	MAX-ACCESS  not-accessible
	STATUS      current
	DESCRIPTION
	"Table entry display string for rulesetCalcjobNumjobs"
	::={rulesetCalcjobNumjobsLevelEntry 1}

rulesetCalcjobNumjobsLevelVal OBJECT-TYPE
	SYNTAX	 CounterBasedGauge64
	MAX-ACCESS  read-only
	STATUS      current
	DESCRIPTION
	"Table entry attribute for rulesetCalcjobNumjobs"
	::={rulesetCalcjobNumjobsLevelEntry 2}

rulesetCalcjobNumjobsLevelMax OBJECT-TYPE
	SYNTAX	 CounterBasedGauge64
	MAX-ACCESS  read-only
	STATUS      current
	DESCRIPTION
	"Table entry attribute for rulesetCalcjobNumjobs"
	::={rulesetCalcjobNumjobsLevelEntry 4}


rulesetCalcjobNummaxjobs	OBJECT IDENTIFIER ::={rulesetCompiler 54}

rulesetCalcjobNummaxjobsVal	OBJECT-TYPE
	SYNTAX	 CounterBasedGauge64
	MAX-ACCESS read-only
	STATUS current
	DESCRIPTION "Ruleset calcjob: Largest number of calc jobs. Gets reset on each ruleset recompile"

	::={rulesetCalcjobNummaxjobs 1}

rulesetCalcjobNummaxjobsMax	OBJECT-TYPE
	SYNTAX	 CounterBasedGauge64
	MAX-ACCESS read-only
	STATUS current
	DESCRIPTION "Ruleset calcjob: Largest number of calc jobs. Gets reset on each ruleset recompile"

	::={rulesetCalcjobNummaxjobs 3}

rulesetCalcjobNummaxjobsLevelTable OBJECT-TYPE
	SYNTAX      SEQUENCE OF RulesetCalcjobNummaxjobsLevelEntry
	MAX-ACCESS  not-accessible
	STATUS      current
	DESCRIPTION
	"Table for rulesetCalcjobNummaxjobs"
	::={rulesetCalcjobNummaxjobs 4}

rulesetCalcjobNummaxjobsLevelEntry OBJECT-TYPE
	SYNTAX      RulesetCalcjobNummaxjobsLevelEntry
	MAX-ACCESS  not-accessible
	STATUS      current
	DESCRIPTION
	"Table entry for rulesetCalcjobNummaxjobs"
	INDEX { rulesetCalcjobNummaxjobsLevelName }
	::={rulesetCalcjobNummaxjobsLevelTable 1}

RulesetCalcjobNummaxjobsLevelEntry ::=
	SEQUENCE {
		rulesetCalcjobNummaxjobsLevelName	DisplayString,
		rulesetCalcjobNummaxjobsLevelVal	CounterBasedGauge64,
		rulesetCalcjobNummaxjobsLevelMax	CounterBasedGauge64
	}

rulesetCalcjobNummaxjobsLevelName OBJECT-TYPE
	SYNTAX      DisplayString
	MAX-ACCESS  not-accessible
	STATUS      current
	DESCRIPTION
	"Table entry display string for rulesetCalcjobNummaxjobs"
	::={rulesetCalcjobNummaxjobsLevelEntry 1}

rulesetCalcjobNummaxjobsLevelVal OBJECT-TYPE
	SYNTAX	 CounterBasedGauge64
	MAX-ACCESS  read-only
	STATUS      current
	DESCRIPTION
	"Table entry attribute for rulesetCalcjobNummaxjobs"
	::={rulesetCalcjobNummaxjobsLevelEntry 2}

rulesetCalcjobNummaxjobsLevelMax OBJECT-TYPE
	SYNTAX	 CounterBasedGauge64
	MAX-ACCESS  read-only
	STATUS      current
	DESCRIPTION
	"Table entry attribute for rulesetCalcjobNummaxjobs"
	::={rulesetCalcjobNummaxjobsLevelEntry 4}


rulesetCompilerPrefixesTime	OBJECT IDENTIFIER ::={rulesetCompiler 61}

rulesetCompilerPrefixesTimeVal	OBJECT-TYPE
	SYNTAX	 CounterBasedGauge64
	MAX-ACCESS read-only
	STATUS current
	DESCRIPTION "Ruleset prefixes: Compile and send time, in ms"

	::={rulesetCompilerPrefixesTime 1}

rulesetCompilerPrefixesTimeMax	OBJECT-TYPE
	SYNTAX	 CounterBasedGauge64
	MAX-ACCESS read-only
	STATUS current
	DESCRIPTION "Ruleset prefixes: Compile and send time, in ms"

	::={rulesetCompilerPrefixesTime 3}

rulesetCompilerPrefixesTimeLevelTable OBJECT-TYPE
	SYNTAX      SEQUENCE OF RulesetCompilerPrefixesTimeLevelEntry
	MAX-ACCESS  not-accessible
	STATUS      current
	DESCRIPTION
	"Table for rulesetCompilerPrefixesTime"
	::={rulesetCompilerPrefixesTime 4}

rulesetCompilerPrefixesTimeLevelEntry OBJECT-TYPE
	SYNTAX      RulesetCompilerPrefixesTimeLevelEntry
	MAX-ACCESS  not-accessible
	STATUS      current
	DESCRIPTION
	"Table entry for rulesetCompilerPrefixesTime"
	INDEX { rulesetCompilerPrefixesTimeLevelName }
	::={rulesetCompilerPrefixesTimeLevelTable 1}

RulesetCompilerPrefixesTimeLevelEntry ::=
	SEQUENCE {
		rulesetCompilerPrefixesTimeLevelName	DisplayString,
		rulesetCompilerPrefixesTimeLevelVal	CounterBasedGauge64,
		rulesetCompilerPrefixesTimeLevelMax	CounterBasedGauge64
	}

rulesetCompilerPrefixesTimeLevelName OBJECT-TYPE
	SYNTAX      DisplayString
	MAX-ACCESS  not-accessible
	STATUS      current
	DESCRIPTION
	"Table entry display string for rulesetCompilerPrefixesTime"
	::={rulesetCompilerPrefixesTimeLevelEntry 1}

rulesetCompilerPrefixesTimeLevelVal OBJECT-TYPE
	SYNTAX	 CounterBasedGauge64
	MAX-ACCESS  read-only
	STATUS      current
	DESCRIPTION
	"Table entry attribute for rulesetCompilerPrefixesTime"
	::={rulesetCompilerPrefixesTimeLevelEntry 2}

rulesetCompilerPrefixesTimeLevelMax OBJECT-TYPE
	SYNTAX	 CounterBasedGauge64
	MAX-ACCESS  read-only
	STATUS      current
	DESCRIPTION
	"Table entry attribute for rulesetCompilerPrefixesTime"
	::={rulesetCompilerPrefixesTimeLevelEntry 4}


rulesetCompilerPrefixesIPv4	OBJECT IDENTIFIER ::={rulesetCompiler 62}

rulesetCompilerPrefixesIPv4Val	OBJECT-TYPE
	SYNTAX	 CounterBasedGauge64
	MAX-ACCESS read-only
	STATUS current
	DESCRIPTION "Ruleset prefixes: Number of compiled IPv4 prefixes"

	::={rulesetCompilerPrefixesIPv4 1}

rulesetCompilerPrefixesIPv4Max	OBJECT-TYPE
	SYNTAX	 CounterBasedGauge64
	MAX-ACCESS read-only
	STATUS current
	DESCRIPTION "Ruleset prefixes: Number of compiled IPv4 prefixes"

	::={rulesetCompilerPrefixesIPv4 3}

rulesetCompilerPrefixesIPv4LevelTable OBJECT-TYPE
	SYNTAX      SEQUENCE OF RulesetCompilerPrefixesIPv4LevelEntry
	MAX-ACCESS  not-accessible
	STATUS      current
	DESCRIPTION
	"Table for rulesetCompilerPrefixesIPv4"
	::={rulesetCompilerPrefixesIPv4 4}

rulesetCompilerPrefixesIPv4LevelEntry OBJECT-TYPE
	SYNTAX      RulesetCompilerPrefixesIPv4LevelEntry
	MAX-ACCESS  not-accessible
	STATUS      current
	DESCRIPTION
	"Table entry for rulesetCompilerPrefixesIPv4"
	INDEX { rulesetCompilerPrefixesIPv4LevelName }
	::={rulesetCompilerPrefixesIPv4LevelTable 1}

RulesetCompilerPrefixesIPv4LevelEntry ::=
	SEQUENCE {
		rulesetCompilerPrefixesIPv4LevelName	DisplayString,
		rulesetCompilerPrefixesIPv4LevelVal	CounterBasedGauge64,
		rulesetCompilerPrefixesIPv4LevelMax	CounterBasedGauge64
	}

rulesetCompilerPrefixesIPv4LevelName OBJECT-TYPE
	SYNTAX      DisplayString
	MAX-ACCESS  not-accessible
	STATUS      current
	DESCRIPTION
	"Table entry display string for rulesetCompilerPrefixesIPv4"
	::={rulesetCompilerPrefixesIPv4LevelEntry 1}

rulesetCompilerPrefixesIPv4LevelVal OBJECT-TYPE
	SYNTAX	 CounterBasedGauge64
	MAX-ACCESS  read-only
	STATUS      current
	DESCRIPTION
	"Table entry attribute for rulesetCompilerPrefixesIPv4"
	::={rulesetCompilerPrefixesIPv4LevelEntry 2}

rulesetCompilerPrefixesIPv4LevelMax OBJECT-TYPE
	SYNTAX	 CounterBasedGauge64
	MAX-ACCESS  read-only
	STATUS      current
	DESCRIPTION
	"Table entry attribute for rulesetCompilerPrefixesIPv4"
	::={rulesetCompilerPrefixesIPv4LevelEntry 4}


rulesetCompilerPrefixesIPv4Full	OBJECT IDENTIFIER ::={rulesetCompiler 63}

rulesetCompilerPrefixesIPv4FullVal	OBJECT-TYPE
	SYNTAX	 Counter64
	MAX-ACCESS read-only
	STATUS current
	DESCRIPTION "Ruleset prefixes error: Storage for compiled IPv4 prefixes is full"

	::={rulesetCompilerPrefixesIPv4Full 1}

rulesetCompilerPrefixesIPv4FullMom	OBJECT-TYPE
	SYNTAX	 CounterBasedGauge64
	MAX-ACCESS read-only
	STATUS current
	DESCRIPTION "Ruleset prefixes error: Storage for compiled IPv4 prefixes is full"

	::={rulesetCompilerPrefixesIPv4Full 2}

rulesetCompilerPrefixesIPv4FullMax	OBJECT-TYPE
	SYNTAX	 CounterBasedGauge64
	MAX-ACCESS read-only
	STATUS current
	DESCRIPTION "Ruleset prefixes error: Storage for compiled IPv4 prefixes is full"

	::={rulesetCompilerPrefixesIPv4Full 3}

rulesetCompilerPrefixesIPv4FullLevelTable OBJECT-TYPE
	SYNTAX      SEQUENCE OF RulesetCompilerPrefixesIPv4FullLevelEntry
	MAX-ACCESS  not-accessible
	STATUS      current
	DESCRIPTION
	"Table for rulesetCompilerPrefixesIPv4Full"
	::={rulesetCompilerPrefixesIPv4Full 4}

rulesetCompilerPrefixesIPv4FullLevelEntry OBJECT-TYPE
	SYNTAX      RulesetCompilerPrefixesIPv4FullLevelEntry
	MAX-ACCESS  not-accessible
	STATUS      current
	DESCRIPTION
	"Table entry for rulesetCompilerPrefixesIPv4Full"
	INDEX { rulesetCompilerPrefixesIPv4FullLevelName }
	::={rulesetCompilerPrefixesIPv4FullLevelTable 1}

RulesetCompilerPrefixesIPv4FullLevelEntry ::=
	SEQUENCE {
		rulesetCompilerPrefixesIPv4FullLevelName	DisplayString,
		rulesetCompilerPrefixesIPv4FullLevelVal	Counter64,
		rulesetCompilerPrefixesIPv4FullLevelMom	CounterBasedGauge64,
		rulesetCompilerPrefixesIPv4FullLevelMax	CounterBasedGauge64
	}

rulesetCompilerPrefixesIPv4FullLevelName OBJECT-TYPE
	SYNTAX      DisplayString
	MAX-ACCESS  not-accessible
	STATUS      current
	DESCRIPTION
	"Table entry display string for rulesetCompilerPrefixesIPv4Full"
	::={rulesetCompilerPrefixesIPv4FullLevelEntry 1}

rulesetCompilerPrefixesIPv4FullLevelVal OBJECT-TYPE
	SYNTAX	 Counter64
	MAX-ACCESS  read-only
	STATUS      current
	DESCRIPTION
	"Table entry attribute for rulesetCompilerPrefixesIPv4Full"
	::={rulesetCompilerPrefixesIPv4FullLevelEntry 2}

rulesetCompilerPrefixesIPv4FullLevelMom OBJECT-TYPE
	SYNTAX	 CounterBasedGauge64
	MAX-ACCESS  read-only
	STATUS      current
	DESCRIPTION
	"Table entry attribute for rulesetCompilerPrefixesIPv4Full"
	::={rulesetCompilerPrefixesIPv4FullLevelEntry 3}

rulesetCompilerPrefixesIPv4FullLevelMax OBJECT-TYPE
	SYNTAX	 CounterBasedGauge64
	MAX-ACCESS  read-only
	STATUS      current
	DESCRIPTION
	"Table entry attribute for rulesetCompilerPrefixesIPv4Full"
	::={rulesetCompilerPrefixesIPv4FullLevelEntry 4}


rulesetCompilerPrefixesIPv6	OBJECT IDENTIFIER ::={rulesetCompiler 64}

rulesetCompilerPrefixesIPv6Val	OBJECT-TYPE
	SYNTAX	 CounterBasedGauge64
	MAX-ACCESS read-only
	STATUS current
	DESCRIPTION "Ruleset prefixes: Number of compiled IPv6 prefixes"

	::={rulesetCompilerPrefixesIPv6 1}

rulesetCompilerPrefixesIPv6Max	OBJECT-TYPE
	SYNTAX	 CounterBasedGauge64
	MAX-ACCESS read-only
	STATUS current
	DESCRIPTION "Ruleset prefixes: Number of compiled IPv6 prefixes"

	::={rulesetCompilerPrefixesIPv6 3}

rulesetCompilerPrefixesIPv6LevelTable OBJECT-TYPE
	SYNTAX      SEQUENCE OF RulesetCompilerPrefixesIPv6LevelEntry
	MAX-ACCESS  not-accessible
	STATUS      current
	DESCRIPTION
	"Table for rulesetCompilerPrefixesIPv6"
	::={rulesetCompilerPrefixesIPv6 4}

rulesetCompilerPrefixesIPv6LevelEntry OBJECT-TYPE
	SYNTAX      RulesetCompilerPrefixesIPv6LevelEntry
	MAX-ACCESS  not-accessible
	STATUS      current
	DESCRIPTION
	"Table entry for rulesetCompilerPrefixesIPv6"
	INDEX { rulesetCompilerPrefixesIPv6LevelName }
	::={rulesetCompilerPrefixesIPv6LevelTable 1}

RulesetCompilerPrefixesIPv6LevelEntry ::=
	SEQUENCE {
		rulesetCompilerPrefixesIPv6LevelName	DisplayString,
		rulesetCompilerPrefixesIPv6LevelVal	CounterBasedGauge64,
		rulesetCompilerPrefixesIPv6LevelMax	CounterBasedGauge64
	}

rulesetCompilerPrefixesIPv6LevelName OBJECT-TYPE
	SYNTAX      DisplayString
	MAX-ACCESS  not-accessible
	STATUS      current
	DESCRIPTION
	"Table entry display string for rulesetCompilerPrefixesIPv6"
	::={rulesetCompilerPrefixesIPv6LevelEntry 1}

rulesetCompilerPrefixesIPv6LevelVal OBJECT-TYPE
	SYNTAX	 CounterBasedGauge64
	MAX-ACCESS  read-only
	STATUS      current
	DESCRIPTION
	"Table entry attribute for rulesetCompilerPrefixesIPv6"
	::={rulesetCompilerPrefixesIPv6LevelEntry 2}

rulesetCompilerPrefixesIPv6LevelMax OBJECT-TYPE
	SYNTAX	 CounterBasedGauge64
	MAX-ACCESS  read-only
	STATUS      current
	DESCRIPTION
	"Table entry attribute for rulesetCompilerPrefixesIPv6"
	::={rulesetCompilerPrefixesIPv6LevelEntry 4}


rulesetCompilerPrefixesIPv6Full	OBJECT IDENTIFIER ::={rulesetCompiler 65}

rulesetCompilerPrefixesIPv6FullVal	OBJECT-TYPE
	SYNTAX	 Counter64
	MAX-ACCESS read-only
	STATUS current
	DESCRIPTION "Ruleset prefixes error: Storage for compiled IPv6 prefixes is full"

	::={rulesetCompilerPrefixesIPv6Full 1}

rulesetCompilerPrefixesIPv6FullMom	OBJECT-TYPE
	SYNTAX	 CounterBasedGauge64
	MAX-ACCESS read-only
	STATUS current
	DESCRIPTION "Ruleset prefixes error: Storage for compiled IPv6 prefixes is full"

	::={rulesetCompilerPrefixesIPv6Full 2}

rulesetCompilerPrefixesIPv6FullMax	OBJECT-TYPE
	SYNTAX	 CounterBasedGauge64
	MAX-ACCESS read-only
	STATUS current
	DESCRIPTION "Ruleset prefixes error: Storage for compiled IPv6 prefixes is full"

	::={rulesetCompilerPrefixesIPv6Full 3}

rulesetCompilerPrefixesIPv6FullLevelTable OBJECT-TYPE
	SYNTAX      SEQUENCE OF RulesetCompilerPrefixesIPv6FullLevelEntry
	MAX-ACCESS  not-accessible
	STATUS      current
	DESCRIPTION
	"Table for rulesetCompilerPrefixesIPv6Full"
	::={rulesetCompilerPrefixesIPv6Full 4}

rulesetCompilerPrefixesIPv6FullLevelEntry OBJECT-TYPE
	SYNTAX      RulesetCompilerPrefixesIPv6FullLevelEntry
	MAX-ACCESS  not-accessible
	STATUS      current
	DESCRIPTION
	"Table entry for rulesetCompilerPrefixesIPv6Full"
	INDEX { rulesetCompilerPrefixesIPv6FullLevelName }
	::={rulesetCompilerPrefixesIPv6FullLevelTable 1}

RulesetCompilerPrefixesIPv6FullLevelEntry ::=
	SEQUENCE {
		rulesetCompilerPrefixesIPv6FullLevelName	DisplayString,
		rulesetCompilerPrefixesIPv6FullLevelVal	Counter64,
		rulesetCompilerPrefixesIPv6FullLevelMom	CounterBasedGauge64,
		rulesetCompilerPrefixesIPv6FullLevelMax	CounterBasedGauge64
	}

rulesetCompilerPrefixesIPv6FullLevelName OBJECT-TYPE
	SYNTAX      DisplayString
	MAX-ACCESS  not-accessible
	STATUS      current
	DESCRIPTION
	"Table entry display string for rulesetCompilerPrefixesIPv6Full"
	::={rulesetCompilerPrefixesIPv6FullLevelEntry 1}

rulesetCompilerPrefixesIPv6FullLevelVal OBJECT-TYPE
	SYNTAX	 Counter64
	MAX-ACCESS  read-only
	STATUS      current
	DESCRIPTION
	"Table entry attribute for rulesetCompilerPrefixesIPv6Full"
	::={rulesetCompilerPrefixesIPv6FullLevelEntry 2}

rulesetCompilerPrefixesIPv6FullLevelMom OBJECT-TYPE
	SYNTAX	 CounterBasedGauge64
	MAX-ACCESS  read-only
	STATUS      current
	DESCRIPTION
	"Table entry attribute for rulesetCompilerPrefixesIPv6Full"
	::={rulesetCompilerPrefixesIPv6FullLevelEntry 3}

rulesetCompilerPrefixesIPv6FullLevelMax OBJECT-TYPE
	SYNTAX	 CounterBasedGauge64
	MAX-ACCESS  read-only
	STATUS      current
	DESCRIPTION
	"Table entry attribute for rulesetCompilerPrefixesIPv6Full"
	::={rulesetCompilerPrefixesIPv6FullLevelEntry 4}


rulesetCompilerPrefixesBitmasks	OBJECT IDENTIFIER ::={rulesetCompiler 66}

rulesetCompilerPrefixesBitmasksVal	OBJECT-TYPE
	SYNTAX	 CounterBasedGauge64
	MAX-ACCESS read-only
	STATUS current
	DESCRIPTION "Ruleset prefixes: Number of bitmasks"

	::={rulesetCompilerPrefixesBitmasks 1}

rulesetCompilerPrefixesBitmasksMax	OBJECT-TYPE
	SYNTAX	 CounterBasedGauge64
	MAX-ACCESS read-only
	STATUS current
	DESCRIPTION "Ruleset prefixes: Number of bitmasks"

	::={rulesetCompilerPrefixesBitmasks 3}

rulesetCompilerPrefixesBitmasksLevelTable OBJECT-TYPE
	SYNTAX      SEQUENCE OF RulesetCompilerPrefixesBitmasksLevelEntry
	MAX-ACCESS  not-accessible
	STATUS      current
	DESCRIPTION
	"Table for rulesetCompilerPrefixesBitmasks"
	::={rulesetCompilerPrefixesBitmasks 4}

rulesetCompilerPrefixesBitmasksLevelEntry OBJECT-TYPE
	SYNTAX      RulesetCompilerPrefixesBitmasksLevelEntry
	MAX-ACCESS  not-accessible
	STATUS      current
	DESCRIPTION
	"Table entry for rulesetCompilerPrefixesBitmasks"
	INDEX { rulesetCompilerPrefixesBitmasksLevelName }
	::={rulesetCompilerPrefixesBitmasksLevelTable 1}

RulesetCompilerPrefixesBitmasksLevelEntry ::=
	SEQUENCE {
		rulesetCompilerPrefixesBitmasksLevelName	DisplayString,
		rulesetCompilerPrefixesBitmasksLevelVal	CounterBasedGauge64,
		rulesetCompilerPrefixesBitmasksLevelMax	CounterBasedGauge64
	}

rulesetCompilerPrefixesBitmasksLevelName OBJECT-TYPE
	SYNTAX      DisplayString
	MAX-ACCESS  not-accessible
	STATUS      current
	DESCRIPTION
	"Table entry display string for rulesetCompilerPrefixesBitmasks"
	::={rulesetCompilerPrefixesBitmasksLevelEntry 1}

rulesetCompilerPrefixesBitmasksLevelVal OBJECT-TYPE
	SYNTAX	 CounterBasedGauge64
	MAX-ACCESS  read-only
	STATUS      current
	DESCRIPTION
	"Table entry attribute for rulesetCompilerPrefixesBitmasks"
	::={rulesetCompilerPrefixesBitmasksLevelEntry 2}

rulesetCompilerPrefixesBitmasksLevelMax OBJECT-TYPE
	SYNTAX	 CounterBasedGauge64
	MAX-ACCESS  read-only
	STATUS      current
	DESCRIPTION
	"Table entry attribute for rulesetCompilerPrefixesBitmasks"
	::={rulesetCompilerPrefixesBitmasksLevelEntry 4}


rulesetCompilerPrefixesBitmaskFull	OBJECT IDENTIFIER ::={rulesetCompiler 68}

rulesetCompilerPrefixesBitmaskFullVal	OBJECT-TYPE
	SYNTAX	 Counter64
	MAX-ACCESS read-only
	STATUS current
	DESCRIPTION "Ruleset prefixes error: Storage for compiled bitmask used by compiled prefixes is full"

	::={rulesetCompilerPrefixesBitmaskFull 1}

rulesetCompilerPrefixesBitmaskFullMom	OBJECT-TYPE
	SYNTAX	 CounterBasedGauge64
	MAX-ACCESS read-only
	STATUS current
	DESCRIPTION "Ruleset prefixes error: Storage for compiled bitmask used by compiled prefixes is full"

	::={rulesetCompilerPrefixesBitmaskFull 2}

rulesetCompilerPrefixesBitmaskFullMax	OBJECT-TYPE
	SYNTAX	 CounterBasedGauge64
	MAX-ACCESS read-only
	STATUS current
	DESCRIPTION "Ruleset prefixes error: Storage for compiled bitmask used by compiled prefixes is full"

	::={rulesetCompilerPrefixesBitmaskFull 3}

rulesetCompilerPrefixesBitmaskFullLevelTable OBJECT-TYPE
	SYNTAX      SEQUENCE OF RulesetCompilerPrefixesBitmaskFullLevelEntry
	MAX-ACCESS  not-accessible
	STATUS      current
	DESCRIPTION
	"Table for rulesetCompilerPrefixesBitmaskFull"
	::={rulesetCompilerPrefixesBitmaskFull 4}

rulesetCompilerPrefixesBitmaskFullLevelEntry OBJECT-TYPE
	SYNTAX      RulesetCompilerPrefixesBitmaskFullLevelEntry
	MAX-ACCESS  not-accessible
	STATUS      current
	DESCRIPTION
	"Table entry for rulesetCompilerPrefixesBitmaskFull"
	INDEX { rulesetCompilerPrefixesBitmaskFullLevelName }
	::={rulesetCompilerPrefixesBitmaskFullLevelTable 1}

RulesetCompilerPrefixesBitmaskFullLevelEntry ::=
	SEQUENCE {
		rulesetCompilerPrefixesBitmaskFullLevelName	DisplayString,
		rulesetCompilerPrefixesBitmaskFullLevelVal	Counter64,
		rulesetCompilerPrefixesBitmaskFullLevelMom	CounterBasedGauge64,
		rulesetCompilerPrefixesBitmaskFullLevelMax	CounterBasedGauge64
	}

rulesetCompilerPrefixesBitmaskFullLevelName OBJECT-TYPE
	SYNTAX      DisplayString
	MAX-ACCESS  not-accessible
	STATUS      current
	DESCRIPTION
	"Table entry display string for rulesetCompilerPrefixesBitmaskFull"
	::={rulesetCompilerPrefixesBitmaskFullLevelEntry 1}

rulesetCompilerPrefixesBitmaskFullLevelVal OBJECT-TYPE
	SYNTAX	 Counter64
	MAX-ACCESS  read-only
	STATUS      current
	DESCRIPTION
	"Table entry attribute for rulesetCompilerPrefixesBitmaskFull"
	::={rulesetCompilerPrefixesBitmaskFullLevelEntry 2}

rulesetCompilerPrefixesBitmaskFullLevelMom OBJECT-TYPE
	SYNTAX	 CounterBasedGauge64
	MAX-ACCESS  read-only
	STATUS      current
	DESCRIPTION
	"Table entry attribute for rulesetCompilerPrefixesBitmaskFull"
	::={rulesetCompilerPrefixesBitmaskFullLevelEntry 3}

rulesetCompilerPrefixesBitmaskFullLevelMax OBJECT-TYPE
	SYNTAX	 CounterBasedGauge64
	MAX-ACCESS  read-only
	STATUS      current
	DESCRIPTION
	"Table entry attribute for rulesetCompilerPrefixesBitmaskFull"
	::={rulesetCompilerPrefixesBitmaskFullLevelEntry 4}


rulesetCompilerPrefixesBitmasksLargest	OBJECT IDENTIFIER ::={rulesetCompiler 67}

rulesetCompilerPrefixesBitmasksLargestVal	OBJECT-TYPE
	SYNTAX	 CounterBasedGauge64
	MAX-ACCESS read-only
	STATUS current
	DESCRIPTION "Ruleset prefixes: Largest bitmask size seen"

	::={rulesetCompilerPrefixesBitmasksLargest 1}

rulesetCompilerPrefixesBitmasksLargestMax	OBJECT-TYPE
	SYNTAX	 CounterBasedGauge64
	MAX-ACCESS read-only
	STATUS current
	DESCRIPTION "Ruleset prefixes: Largest bitmask size seen"

	::={rulesetCompilerPrefixesBitmasksLargest 3}

rulesetCompilerPrefixesBitmasksLargestLevelTable OBJECT-TYPE
	SYNTAX      SEQUENCE OF RulesetCompilerPrefixesBitmasksLargestLevelEntry
	MAX-ACCESS  not-accessible
	STATUS      current
	DESCRIPTION
	"Table for rulesetCompilerPrefixesBitmasksLargest"
	::={rulesetCompilerPrefixesBitmasksLargest 4}

rulesetCompilerPrefixesBitmasksLargestLevelEntry OBJECT-TYPE
	SYNTAX      RulesetCompilerPrefixesBitmasksLargestLevelEntry
	MAX-ACCESS  not-accessible
	STATUS      current
	DESCRIPTION
	"Table entry for rulesetCompilerPrefixesBitmasksLargest"
	INDEX { rulesetCompilerPrefixesBitmasksLargestLevelName }
	::={rulesetCompilerPrefixesBitmasksLargestLevelTable 1}

RulesetCompilerPrefixesBitmasksLargestLevelEntry ::=
	SEQUENCE {
		rulesetCompilerPrefixesBitmasksLargestLevelName	DisplayString,
		rulesetCompilerPrefixesBitmasksLargestLevelVal	CounterBasedGauge64,
		rulesetCompilerPrefixesBitmasksLargestLevelMax	CounterBasedGauge64
	}

rulesetCompilerPrefixesBitmasksLargestLevelName OBJECT-TYPE
	SYNTAX      DisplayString
	MAX-ACCESS  not-accessible
	STATUS      current
	DESCRIPTION
	"Table entry display string for rulesetCompilerPrefixesBitmasksLargest"
	::={rulesetCompilerPrefixesBitmasksLargestLevelEntry 1}

rulesetCompilerPrefixesBitmasksLargestLevelVal OBJECT-TYPE
	SYNTAX	 CounterBasedGauge64
	MAX-ACCESS  read-only
	STATUS      current
	DESCRIPTION
	"Table entry attribute for rulesetCompilerPrefixesBitmasksLargest"
	::={rulesetCompilerPrefixesBitmasksLargestLevelEntry 2}

rulesetCompilerPrefixesBitmasksLargestLevelMax OBJECT-TYPE
	SYNTAX	 CounterBasedGauge64
	MAX-ACCESS  read-only
	STATUS      current
	DESCRIPTION
	"Table entry attribute for rulesetCompilerPrefixesBitmasksLargest"
	::={rulesetCompilerPrefixesBitmasksLargestLevelEntry 4}


rulesetCompilerPrefixesBitmaskTooLarge	OBJECT IDENTIFIER ::={rulesetCompiler 69}

rulesetCompilerPrefixesBitmaskTooLargeVal	OBJECT-TYPE
	SYNTAX	 Counter64
	MAX-ACCESS read-only
	STATUS current
	DESCRIPTION "Ruleset prefixes error: Number of bitmask that was too large for max bitmask size"

	::={rulesetCompilerPrefixesBitmaskTooLarge 1}

rulesetCompilerPrefixesBitmaskTooLargeMom	OBJECT-TYPE
	SYNTAX	 CounterBasedGauge64
	MAX-ACCESS read-only
	STATUS current
	DESCRIPTION "Ruleset prefixes error: Number of bitmask that was too large for max bitmask size"

	::={rulesetCompilerPrefixesBitmaskTooLarge 2}

rulesetCompilerPrefixesBitmaskTooLargeMax	OBJECT-TYPE
	SYNTAX	 CounterBasedGauge64
	MAX-ACCESS read-only
	STATUS current
	DESCRIPTION "Ruleset prefixes error: Number of bitmask that was too large for max bitmask size"

	::={rulesetCompilerPrefixesBitmaskTooLarge 3}

rulesetCompilerPrefixesBitmaskTooLargeLevelTable OBJECT-TYPE
	SYNTAX      SEQUENCE OF RulesetCompilerPrefixesBitmaskTooLargeLevelEntry
	MAX-ACCESS  not-accessible
	STATUS      current
	DESCRIPTION
	"Table for rulesetCompilerPrefixesBitmaskTooLarge"
	::={rulesetCompilerPrefixesBitmaskTooLarge 4}

rulesetCompilerPrefixesBitmaskTooLargeLevelEntry OBJECT-TYPE
	SYNTAX      RulesetCompilerPrefixesBitmaskTooLargeLevelEntry
	MAX-ACCESS  not-accessible
	STATUS      current
	DESCRIPTION
	"Table entry for rulesetCompilerPrefixesBitmaskTooLarge"
	INDEX { rulesetCompilerPrefixesBitmaskTooLargeLevelName }
	::={rulesetCompilerPrefixesBitmaskTooLargeLevelTable 1}

RulesetCompilerPrefixesBitmaskTooLargeLevelEntry ::=
	SEQUENCE {
		rulesetCompilerPrefixesBitmaskTooLargeLevelName	DisplayString,
		rulesetCompilerPrefixesBitmaskTooLargeLevelVal	Counter64,
		rulesetCompilerPrefixesBitmaskTooLargeLevelMom	CounterBasedGauge64,
		rulesetCompilerPrefixesBitmaskTooLargeLevelMax	CounterBasedGauge64
	}

rulesetCompilerPrefixesBitmaskTooLargeLevelName OBJECT-TYPE
	SYNTAX      DisplayString
	MAX-ACCESS  not-accessible
	STATUS      current
	DESCRIPTION
	"Table entry display string for rulesetCompilerPrefixesBitmaskTooLarge"
	::={rulesetCompilerPrefixesBitmaskTooLargeLevelEntry 1}

rulesetCompilerPrefixesBitmaskTooLargeLevelVal OBJECT-TYPE
	SYNTAX	 Counter64
	MAX-ACCESS  read-only
	STATUS      current
	DESCRIPTION
	"Table entry attribute for rulesetCompilerPrefixesBitmaskTooLarge"
	::={rulesetCompilerPrefixesBitmaskTooLargeLevelEntry 2}

rulesetCompilerPrefixesBitmaskTooLargeLevelMom OBJECT-TYPE
	SYNTAX	 CounterBasedGauge64
	MAX-ACCESS  read-only
	STATUS      current
	DESCRIPTION
	"Table entry attribute for rulesetCompilerPrefixesBitmaskTooLarge"
	::={rulesetCompilerPrefixesBitmaskTooLargeLevelEntry 3}

rulesetCompilerPrefixesBitmaskTooLargeLevelMax OBJECT-TYPE
	SYNTAX	 CounterBasedGauge64
	MAX-ACCESS  read-only
	STATUS      current
	DESCRIPTION
	"Table entry attribute for rulesetCompilerPrefixesBitmaskTooLarge"
	::={rulesetCompilerPrefixesBitmaskTooLargeLevelEntry 4}


rulesetCompilerDynitemsTime	OBJECT IDENTIFIER ::={rulesetCompiler 71}

rulesetCompilerDynitemsTimeVal	OBJECT-TYPE
	SYNTAX	 CounterBasedGauge64
	MAX-ACCESS read-only
	STATUS current
	DESCRIPTION "Ruleset dynitems: Compile and send time, in ms (Subscriber, Enrich, NatCfg)"

	::={rulesetCompilerDynitemsTime 1}

rulesetCompilerDynitemsTimeMax	OBJECT-TYPE
	SYNTAX	 CounterBasedGauge64
	MAX-ACCESS read-only
	STATUS current
	DESCRIPTION "Ruleset dynitems: Compile and send time, in ms (Subscriber, Enrich, NatCfg)"

	::={rulesetCompilerDynitemsTime 3}

rulesetCompilerDynitemsTimeLevelTable OBJECT-TYPE
	SYNTAX      SEQUENCE OF RulesetCompilerDynitemsTimeLevelEntry
	MAX-ACCESS  not-accessible
	STATUS      current
	DESCRIPTION
	"Table for rulesetCompilerDynitemsTime"
	::={rulesetCompilerDynitemsTime 4}

rulesetCompilerDynitemsTimeLevelEntry OBJECT-TYPE
	SYNTAX      RulesetCompilerDynitemsTimeLevelEntry
	MAX-ACCESS  not-accessible
	STATUS      current
	DESCRIPTION
	"Table entry for rulesetCompilerDynitemsTime"
	INDEX { rulesetCompilerDynitemsTimeLevelName }
	::={rulesetCompilerDynitemsTimeLevelTable 1}

RulesetCompilerDynitemsTimeLevelEntry ::=
	SEQUENCE {
		rulesetCompilerDynitemsTimeLevelName	DisplayString,
		rulesetCompilerDynitemsTimeLevelVal	CounterBasedGauge64,
		rulesetCompilerDynitemsTimeLevelMax	CounterBasedGauge64
	}

rulesetCompilerDynitemsTimeLevelName OBJECT-TYPE
	SYNTAX      DisplayString
	MAX-ACCESS  not-accessible
	STATUS      current
	DESCRIPTION
	"Table entry display string for rulesetCompilerDynitemsTime"
	::={rulesetCompilerDynitemsTimeLevelEntry 1}

rulesetCompilerDynitemsTimeLevelVal OBJECT-TYPE
	SYNTAX	 CounterBasedGauge64
	MAX-ACCESS  read-only
	STATUS      current
	DESCRIPTION
	"Table entry attribute for rulesetCompilerDynitemsTime"
	::={rulesetCompilerDynitemsTimeLevelEntry 2}

rulesetCompilerDynitemsTimeLevelMax OBJECT-TYPE
	SYNTAX	 CounterBasedGauge64
	MAX-ACCESS  read-only
	STATUS      current
	DESCRIPTION
	"Table entry attribute for rulesetCompilerDynitemsTime"
	::={rulesetCompilerDynitemsTimeLevelEntry 4}


rulesetCompilerBGPCompleted	OBJECT IDENTIFIER ::={rulesetCompiler 81}

rulesetCompilerBGPCompletedVal	OBJECT-TYPE
	SYNTAX	 DateAndTime
	MAX-ACCESS read-only
	STATUS current
	DESCRIPTION "Ruleset BGP: Subversion updated"

	::={rulesetCompilerBGPCompleted 1}

rulesetCompilerBGPCompletedLevelTable OBJECT-TYPE
	SYNTAX      SEQUENCE OF RulesetCompilerBGPCompletedLevelEntry
	MAX-ACCESS  not-accessible
	STATUS      current
	DESCRIPTION
	"Table for rulesetCompilerBGPCompleted"
	::={rulesetCompilerBGPCompleted 2}

rulesetCompilerBGPCompletedLevelEntry OBJECT-TYPE
	SYNTAX      RulesetCompilerBGPCompletedLevelEntry
	MAX-ACCESS  not-accessible
	STATUS      current
	DESCRIPTION
	"Table entry for rulesetCompilerBGPCompleted"
	INDEX { rulesetCompilerBGPCompletedLevelName }
	::={rulesetCompilerBGPCompletedLevelTable 1}

RulesetCompilerBGPCompletedLevelEntry ::=
	SEQUENCE {
		rulesetCompilerBGPCompletedLevelName	DisplayString,
		rulesetCompilerBGPCompletedLevelVal	DateAndTime
	}

rulesetCompilerBGPCompletedLevelName OBJECT-TYPE
	SYNTAX      DisplayString
	MAX-ACCESS  not-accessible
	STATUS      current
	DESCRIPTION
	"Table entry display string for rulesetCompilerBGPCompleted"
	::={rulesetCompilerBGPCompletedLevelEntry 1}

rulesetCompilerBGPCompletedLevelVal OBJECT-TYPE
	SYNTAX	 DateAndTime
	MAX-ACCESS  read-only
	STATUS      current
	DESCRIPTION
	"Table entry attribute for rulesetCompilerBGPCompleted"
	::={rulesetCompilerBGPCompletedLevelEntry 2}


rulesetCompilerBGPTime	OBJECT IDENTIFIER ::={rulesetCompiler 82}

rulesetCompilerBGPTimeVal	OBJECT-TYPE
	SYNTAX	 CounterBasedGauge64
	MAX-ACCESS read-only
	STATUS current
	DESCRIPTION "Ruleset BGP: Compile and send time, in ms"

	::={rulesetCompilerBGPTime 1}

rulesetCompilerBGPTimeMax	OBJECT-TYPE
	SYNTAX	 CounterBasedGauge64
	MAX-ACCESS read-only
	STATUS current
	DESCRIPTION "Ruleset BGP: Compile and send time, in ms"

	::={rulesetCompilerBGPTime 3}

rulesetCompilerBGPTimeLevelTable OBJECT-TYPE
	SYNTAX      SEQUENCE OF RulesetCompilerBGPTimeLevelEntry
	MAX-ACCESS  not-accessible
	STATUS      current
	DESCRIPTION
	"Table for rulesetCompilerBGPTime"
	::={rulesetCompilerBGPTime 4}

rulesetCompilerBGPTimeLevelEntry OBJECT-TYPE
	SYNTAX      RulesetCompilerBGPTimeLevelEntry
	MAX-ACCESS  not-accessible
	STATUS      current
	DESCRIPTION
	"Table entry for rulesetCompilerBGPTime"
	INDEX { rulesetCompilerBGPTimeLevelName }
	::={rulesetCompilerBGPTimeLevelTable 1}

RulesetCompilerBGPTimeLevelEntry ::=
	SEQUENCE {
		rulesetCompilerBGPTimeLevelName	DisplayString,
		rulesetCompilerBGPTimeLevelVal	CounterBasedGauge64,
		rulesetCompilerBGPTimeLevelMax	CounterBasedGauge64
	}

rulesetCompilerBGPTimeLevelName OBJECT-TYPE
	SYNTAX      DisplayString
	MAX-ACCESS  not-accessible
	STATUS      current
	DESCRIPTION
	"Table entry display string for rulesetCompilerBGPTime"
	::={rulesetCompilerBGPTimeLevelEntry 1}

rulesetCompilerBGPTimeLevelVal OBJECT-TYPE
	SYNTAX	 CounterBasedGauge64
	MAX-ACCESS  read-only
	STATUS      current
	DESCRIPTION
	"Table entry attribute for rulesetCompilerBGPTime"
	::={rulesetCompilerBGPTimeLevelEntry 2}

rulesetCompilerBGPTimeLevelMax OBJECT-TYPE
	SYNTAX	 CounterBasedGauge64
	MAX-ACCESS  read-only
	STATUS      current
	DESCRIPTION
	"Table entry attribute for rulesetCompilerBGPTime"
	::={rulesetCompilerBGPTimeLevelEntry 4}


rulesetCompilerBGPPaths	OBJECT IDENTIFIER ::={rulesetCompiler 83}

rulesetCompilerBGPPathsVal	OBJECT-TYPE
	SYNTAX	 CounterBasedGauge64
	MAX-ACCESS read-only
	STATUS current
	DESCRIPTION "Ruleset BGP: AS paths"

	::={rulesetCompilerBGPPaths 1}

rulesetCompilerBGPPathsMax	OBJECT-TYPE
	SYNTAX	 CounterBasedGauge64
	MAX-ACCESS read-only
	STATUS current
	DESCRIPTION "Ruleset BGP: AS paths"

	::={rulesetCompilerBGPPaths 3}

rulesetCompilerBGPPathsLevelTable OBJECT-TYPE
	SYNTAX      SEQUENCE OF RulesetCompilerBGPPathsLevelEntry
	MAX-ACCESS  not-accessible
	STATUS      current
	DESCRIPTION
	"Table for rulesetCompilerBGPPaths"
	::={rulesetCompilerBGPPaths 4}

rulesetCompilerBGPPathsLevelEntry OBJECT-TYPE
	SYNTAX      RulesetCompilerBGPPathsLevelEntry
	MAX-ACCESS  not-accessible
	STATUS      current
	DESCRIPTION
	"Table entry for rulesetCompilerBGPPaths"
	INDEX { rulesetCompilerBGPPathsLevelName }
	::={rulesetCompilerBGPPathsLevelTable 1}

RulesetCompilerBGPPathsLevelEntry ::=
	SEQUENCE {
		rulesetCompilerBGPPathsLevelName	DisplayString,
		rulesetCompilerBGPPathsLevelVal	CounterBasedGauge64,
		rulesetCompilerBGPPathsLevelMax	CounterBasedGauge64
	}

rulesetCompilerBGPPathsLevelName OBJECT-TYPE
	SYNTAX      DisplayString
	MAX-ACCESS  not-accessible
	STATUS      current
	DESCRIPTION
	"Table entry display string for rulesetCompilerBGPPaths"
	::={rulesetCompilerBGPPathsLevelEntry 1}

rulesetCompilerBGPPathsLevelVal OBJECT-TYPE
	SYNTAX	 CounterBasedGauge64
	MAX-ACCESS  read-only
	STATUS      current
	DESCRIPTION
	"Table entry attribute for rulesetCompilerBGPPaths"
	::={rulesetCompilerBGPPathsLevelEntry 2}

rulesetCompilerBGPPathsLevelMax OBJECT-TYPE
	SYNTAX	 CounterBasedGauge64
	MAX-ACCESS  read-only
	STATUS      current
	DESCRIPTION
	"Table entry attribute for rulesetCompilerBGPPaths"
	::={rulesetCompilerBGPPathsLevelEntry 4}


rulesetCompilerBGPBitmasks	OBJECT IDENTIFIER ::={rulesetCompiler 84}

rulesetCompilerBGPBitmasksVal	OBJECT-TYPE
	SYNTAX	 CounterBasedGauge64
	MAX-ACCESS read-only
	STATUS current
	DESCRIPTION "Ruleset BGP: Bitmasks"

	::={rulesetCompilerBGPBitmasks 1}

rulesetCompilerBGPBitmasksMax	OBJECT-TYPE
	SYNTAX	 CounterBasedGauge64
	MAX-ACCESS read-only
	STATUS current
	DESCRIPTION "Ruleset BGP: Bitmasks"

	::={rulesetCompilerBGPBitmasks 3}

rulesetCompilerBGPBitmasksLevelTable OBJECT-TYPE
	SYNTAX      SEQUENCE OF RulesetCompilerBGPBitmasksLevelEntry
	MAX-ACCESS  not-accessible
	STATUS      current
	DESCRIPTION
	"Table for rulesetCompilerBGPBitmasks"
	::={rulesetCompilerBGPBitmasks 4}

rulesetCompilerBGPBitmasksLevelEntry OBJECT-TYPE
	SYNTAX      RulesetCompilerBGPBitmasksLevelEntry
	MAX-ACCESS  not-accessible
	STATUS      current
	DESCRIPTION
	"Table entry for rulesetCompilerBGPBitmasks"
	INDEX { rulesetCompilerBGPBitmasksLevelName }
	::={rulesetCompilerBGPBitmasksLevelTable 1}

RulesetCompilerBGPBitmasksLevelEntry ::=
	SEQUENCE {
		rulesetCompilerBGPBitmasksLevelName	DisplayString,
		rulesetCompilerBGPBitmasksLevelVal	CounterBasedGauge64,
		rulesetCompilerBGPBitmasksLevelMax	CounterBasedGauge64
	}

rulesetCompilerBGPBitmasksLevelName OBJECT-TYPE
	SYNTAX      DisplayString
	MAX-ACCESS  not-accessible
	STATUS      current
	DESCRIPTION
	"Table entry display string for rulesetCompilerBGPBitmasks"
	::={rulesetCompilerBGPBitmasksLevelEntry 1}

rulesetCompilerBGPBitmasksLevelVal OBJECT-TYPE
	SYNTAX	 CounterBasedGauge64
	MAX-ACCESS  read-only
	STATUS      current
	DESCRIPTION
	"Table entry attribute for rulesetCompilerBGPBitmasks"
	::={rulesetCompilerBGPBitmasksLevelEntry 2}

rulesetCompilerBGPBitmasksLevelMax OBJECT-TYPE
	SYNTAX	 CounterBasedGauge64
	MAX-ACCESS  read-only
	STATUS      current
	DESCRIPTION
	"Table entry attribute for rulesetCompilerBGPBitmasks"
	::={rulesetCompilerBGPBitmasksLevelEntry 4}


rulesetCompilerDynruleCompleted	OBJECT IDENTIFIER ::={rulesetCompiler 91}

rulesetCompilerDynruleCompletedVal	OBJECT-TYPE
	SYNTAX	 DateAndTime
	MAX-ACCESS read-only
	STATUS current
	DESCRIPTION "Ruleset dynrule: Subversion updated (affected by DynamicRule and TimeObject)"

	::={rulesetCompilerDynruleCompleted 1}

rulesetCompilerDynruleCompletedLevelTable OBJECT-TYPE
	SYNTAX      SEQUENCE OF RulesetCompilerDynruleCompletedLevelEntry
	MAX-ACCESS  not-accessible
	STATUS      current
	DESCRIPTION
	"Table for rulesetCompilerDynruleCompleted"
	::={rulesetCompilerDynruleCompleted 2}

rulesetCompilerDynruleCompletedLevelEntry OBJECT-TYPE
	SYNTAX      RulesetCompilerDynruleCompletedLevelEntry
	MAX-ACCESS  not-accessible
	STATUS      current
	DESCRIPTION
	"Table entry for rulesetCompilerDynruleCompleted"
	INDEX { rulesetCompilerDynruleCompletedLevelName }
	::={rulesetCompilerDynruleCompletedLevelTable 1}

RulesetCompilerDynruleCompletedLevelEntry ::=
	SEQUENCE {
		rulesetCompilerDynruleCompletedLevelName	DisplayString,
		rulesetCompilerDynruleCompletedLevelVal	DateAndTime
	}

rulesetCompilerDynruleCompletedLevelName OBJECT-TYPE
	SYNTAX      DisplayString
	MAX-ACCESS  not-accessible
	STATUS      current
	DESCRIPTION
	"Table entry display string for rulesetCompilerDynruleCompleted"
	::={rulesetCompilerDynruleCompletedLevelEntry 1}

rulesetCompilerDynruleCompletedLevelVal OBJECT-TYPE
	SYNTAX	 DateAndTime
	MAX-ACCESS  read-only
	STATUS      current
	DESCRIPTION
	"Table entry attribute for rulesetCompilerDynruleCompleted"
	::={rulesetCompilerDynruleCompletedLevelEntry 2}


bgp	OBJECT IDENTIFIER ::={sysdiag 122}

bgpUpdates	OBJECT IDENTIFIER ::={bgp 1}

bgpUpdatesVal	OBJECT-TYPE
	SYNTAX	 CounterBasedGauge64
	MAX-ACCESS read-only
	STATUS current
	DESCRIPTION "Updates received"

	::={bgpUpdates 1}

bgpUpdatesMax	OBJECT-TYPE
	SYNTAX	 CounterBasedGauge64
	MAX-ACCESS read-only
	STATUS current
	DESCRIPTION "Updates received"

	::={bgpUpdates 3}

bgpUpdatesLevelTable OBJECT-TYPE
	SYNTAX      SEQUENCE OF BgpUpdatesLevelEntry
	MAX-ACCESS  not-accessible
	STATUS      current
	DESCRIPTION
	"Table for bgpUpdates"
	::={bgpUpdates 4}

bgpUpdatesLevelEntry OBJECT-TYPE
	SYNTAX      BgpUpdatesLevelEntry
	MAX-ACCESS  not-accessible
	STATUS      current
	DESCRIPTION
	"Table entry for bgpUpdates"
	INDEX { bgpUpdatesLevelName }
	::={bgpUpdatesLevelTable 1}

BgpUpdatesLevelEntry ::=
	SEQUENCE {
		bgpUpdatesLevelName	DisplayString,
		bgpUpdatesLevelVal	CounterBasedGauge64,
		bgpUpdatesLevelMax	CounterBasedGauge64
	}

bgpUpdatesLevelName OBJECT-TYPE
	SYNTAX      DisplayString
	MAX-ACCESS  not-accessible
	STATUS      current
	DESCRIPTION
	"Table entry display string for bgpUpdates"
	::={bgpUpdatesLevelEntry 1}

bgpUpdatesLevelVal OBJECT-TYPE
	SYNTAX	 CounterBasedGauge64
	MAX-ACCESS  read-only
	STATUS      current
	DESCRIPTION
	"Table entry attribute for bgpUpdates"
	::={bgpUpdatesLevelEntry 2}

bgpUpdatesLevelMax OBJECT-TYPE
	SYNTAX	 CounterBasedGauge64
	MAX-ACCESS  read-only
	STATUS      current
	DESCRIPTION
	"Table entry attribute for bgpUpdates"
	::={bgpUpdatesLevelEntry 4}


bgpPrefixes	OBJECT IDENTIFIER ::={bgp 2}

bgpPrefixesVal	OBJECT-TYPE
	SYNTAX	 CounterBasedGauge64
	MAX-ACCESS read-only
	STATUS current
	DESCRIPTION "Number of prefixes/routes"

	::={bgpPrefixes 1}

bgpPrefixesMax	OBJECT-TYPE
	SYNTAX	 CounterBasedGauge64
	MAX-ACCESS read-only
	STATUS current
	DESCRIPTION "Number of prefixes/routes"

	::={bgpPrefixes 3}

bgpPrefixesLevelTable OBJECT-TYPE
	SYNTAX      SEQUENCE OF BgpPrefixesLevelEntry
	MAX-ACCESS  not-accessible
	STATUS      current
	DESCRIPTION
	"Table for bgpPrefixes"
	::={bgpPrefixes 4}

bgpPrefixesLevelEntry OBJECT-TYPE
	SYNTAX      BgpPrefixesLevelEntry
	MAX-ACCESS  not-accessible
	STATUS      current
	DESCRIPTION
	"Table entry for bgpPrefixes"
	INDEX { bgpPrefixesLevelName }
	::={bgpPrefixesLevelTable 1}

BgpPrefixesLevelEntry ::=
	SEQUENCE {
		bgpPrefixesLevelName	DisplayString,
		bgpPrefixesLevelVal	CounterBasedGauge64,
		bgpPrefixesLevelMax	CounterBasedGauge64
	}

bgpPrefixesLevelName OBJECT-TYPE
	SYNTAX      DisplayString
	MAX-ACCESS  not-accessible
	STATUS      current
	DESCRIPTION
	"Table entry display string for bgpPrefixes"
	::={bgpPrefixesLevelEntry 1}

bgpPrefixesLevelVal OBJECT-TYPE
	SYNTAX	 CounterBasedGauge64
	MAX-ACCESS  read-only
	STATUS      current
	DESCRIPTION
	"Table entry attribute for bgpPrefixes"
	::={bgpPrefixesLevelEntry 2}

bgpPrefixesLevelMax OBJECT-TYPE
	SYNTAX	 CounterBasedGauge64
	MAX-ACCESS  read-only
	STATUS      current
	DESCRIPTION
	"Table entry attribute for bgpPrefixes"
	::={bgpPrefixesLevelEntry 4}


bgpPaths	OBJECT IDENTIFIER ::={bgp 3}

bgpPathsVal	OBJECT-TYPE
	SYNTAX	 CounterBasedGauge64
	MAX-ACCESS read-only
	STATUS current
	DESCRIPTION "Number of unique paths"

	::={bgpPaths 1}

bgpPathsMax	OBJECT-TYPE
	SYNTAX	 CounterBasedGauge64
	MAX-ACCESS read-only
	STATUS current
	DESCRIPTION "Number of unique paths"

	::={bgpPaths 3}

bgpPathsLevelTable OBJECT-TYPE
	SYNTAX      SEQUENCE OF BgpPathsLevelEntry
	MAX-ACCESS  not-accessible
	STATUS      current
	DESCRIPTION
	"Table for bgpPaths"
	::={bgpPaths 4}

bgpPathsLevelEntry OBJECT-TYPE
	SYNTAX      BgpPathsLevelEntry
	MAX-ACCESS  not-accessible
	STATUS      current
	DESCRIPTION
	"Table entry for bgpPaths"
	INDEX { bgpPathsLevelName }
	::={bgpPathsLevelTable 1}

BgpPathsLevelEntry ::=
	SEQUENCE {
		bgpPathsLevelName	DisplayString,
		bgpPathsLevelVal	CounterBasedGauge64,
		bgpPathsLevelMax	CounterBasedGauge64
	}

bgpPathsLevelName OBJECT-TYPE
	SYNTAX      DisplayString
	MAX-ACCESS  not-accessible
	STATUS      current
	DESCRIPTION
	"Table entry display string for bgpPaths"
	::={bgpPathsLevelEntry 1}

bgpPathsLevelVal OBJECT-TYPE
	SYNTAX	 CounterBasedGauge64
	MAX-ACCESS  read-only
	STATUS      current
	DESCRIPTION
	"Table entry attribute for bgpPaths"
	::={bgpPathsLevelEntry 2}

bgpPathsLevelMax OBJECT-TYPE
	SYNTAX	 CounterBasedGauge64
	MAX-ACCESS  read-only
	STATUS      current
	DESCRIPTION
	"Table entry attribute for bgpPaths"
	::={bgpPathsLevelEntry 4}


bgpUptime	OBJECT IDENTIFIER ::={bgp 4}

bgpUptimeVal	OBJECT-TYPE
	SYNTAX	 TimeTicks
	MAX-ACCESS read-only
	STATUS current
	DESCRIPTION "Connection uptime"

	::={bgpUptime 1}

bgpUptimeLevelTable OBJECT-TYPE
	SYNTAX      SEQUENCE OF BgpUptimeLevelEntry
	MAX-ACCESS  not-accessible
	STATUS      current
	DESCRIPTION
	"Table for bgpUptime"
	::={bgpUptime 2}

bgpUptimeLevelEntry OBJECT-TYPE
	SYNTAX      BgpUptimeLevelEntry
	MAX-ACCESS  not-accessible
	STATUS      current
	DESCRIPTION
	"Table entry for bgpUptime"
	INDEX { bgpUptimeLevelName }
	::={bgpUptimeLevelTable 1}

BgpUptimeLevelEntry ::=
	SEQUENCE {
		bgpUptimeLevelName	DisplayString,
		bgpUptimeLevelVal	TimeTicks
	}

bgpUptimeLevelName OBJECT-TYPE
	SYNTAX      DisplayString
	MAX-ACCESS  not-accessible
	STATUS      current
	DESCRIPTION
	"Table entry display string for bgpUptime"
	::={bgpUptimeLevelEntry 1}

bgpUptimeLevelVal OBJECT-TYPE
	SYNTAX	 TimeTicks
	MAX-ACCESS  read-only
	STATUS      current
	DESCRIPTION
	"Table entry attribute for bgpUptime"
	::={bgpUptimeLevelEntry 2}


bgpConvresionTime	OBJECT IDENTIFIER ::={bgp 5}

bgpConvresionTimeVal	OBJECT-TYPE
	SYNTAX	 CounterBasedGauge64
	MAX-ACCESS read-only
	STATUS current
	DESCRIPTION "Time to convert lookup tree"

	::={bgpConvresionTime 1}

bgpConvresionTimeMax	OBJECT-TYPE
	SYNTAX	 CounterBasedGauge64
	MAX-ACCESS read-only
	STATUS current
	DESCRIPTION "Time to convert lookup tree"

	::={bgpConvresionTime 3}

bgpConvresionTimeLevelTable OBJECT-TYPE
	SYNTAX      SEQUENCE OF BgpConvresionTimeLevelEntry
	MAX-ACCESS  not-accessible
	STATUS      current
	DESCRIPTION
	"Table for bgpConvresionTime"
	::={bgpConvresionTime 4}

bgpConvresionTimeLevelEntry OBJECT-TYPE
	SYNTAX      BgpConvresionTimeLevelEntry
	MAX-ACCESS  not-accessible
	STATUS      current
	DESCRIPTION
	"Table entry for bgpConvresionTime"
	INDEX { bgpConvresionTimeLevelName }
	::={bgpConvresionTimeLevelTable 1}

BgpConvresionTimeLevelEntry ::=
	SEQUENCE {
		bgpConvresionTimeLevelName	DisplayString,
		bgpConvresionTimeLevelVal	CounterBasedGauge64,
		bgpConvresionTimeLevelMax	CounterBasedGauge64
	}

bgpConvresionTimeLevelName OBJECT-TYPE
	SYNTAX      DisplayString
	MAX-ACCESS  not-accessible
	STATUS      current
	DESCRIPTION
	"Table entry display string for bgpConvresionTime"
	::={bgpConvresionTimeLevelEntry 1}

bgpConvresionTimeLevelVal OBJECT-TYPE
	SYNTAX	 CounterBasedGauge64
	MAX-ACCESS  read-only
	STATUS      current
	DESCRIPTION
	"Table entry attribute for bgpConvresionTime"
	::={bgpConvresionTimeLevelEntry 2}

bgpConvresionTimeLevelMax OBJECT-TYPE
	SYNTAX	 CounterBasedGauge64
	MAX-ACCESS  read-only
	STATUS      current
	DESCRIPTION
	"Table entry attribute for bgpConvresionTime"
	::={bgpConvresionTimeLevelEntry 4}


bgpSendTime	OBJECT IDENTIFIER ::={bgp 6}

bgpSendTimeVal	OBJECT-TYPE
	SYNTAX	 CounterBasedGauge64
	MAX-ACCESS read-only
	STATUS current
	DESCRIPTION "Time to update lookup tree"

	::={bgpSendTime 1}

bgpSendTimeMax	OBJECT-TYPE
	SYNTAX	 CounterBasedGauge64
	MAX-ACCESS read-only
	STATUS current
	DESCRIPTION "Time to update lookup tree"

	::={bgpSendTime 3}

bgpSendTimeLevelTable OBJECT-TYPE
	SYNTAX      SEQUENCE OF BgpSendTimeLevelEntry
	MAX-ACCESS  not-accessible
	STATUS      current
	DESCRIPTION
	"Table for bgpSendTime"
	::={bgpSendTime 4}

bgpSendTimeLevelEntry OBJECT-TYPE
	SYNTAX      BgpSendTimeLevelEntry
	MAX-ACCESS  not-accessible
	STATUS      current
	DESCRIPTION
	"Table entry for bgpSendTime"
	INDEX { bgpSendTimeLevelName }
	::={bgpSendTimeLevelTable 1}

BgpSendTimeLevelEntry ::=
	SEQUENCE {
		bgpSendTimeLevelName	DisplayString,
		bgpSendTimeLevelVal	CounterBasedGauge64,
		bgpSendTimeLevelMax	CounterBasedGauge64
	}

bgpSendTimeLevelName OBJECT-TYPE
	SYNTAX      DisplayString
	MAX-ACCESS  not-accessible
	STATUS      current
	DESCRIPTION
	"Table entry display string for bgpSendTime"
	::={bgpSendTimeLevelEntry 1}

bgpSendTimeLevelVal OBJECT-TYPE
	SYNTAX	 CounterBasedGauge64
	MAX-ACCESS  read-only
	STATUS      current
	DESCRIPTION
	"Table entry attribute for bgpSendTime"
	::={bgpSendTimeLevelEntry 2}

bgpSendTimeLevelMax OBJECT-TYPE
	SYNTAX	 CounterBasedGauge64
	MAX-ACCESS  read-only
	STATUS      current
	DESCRIPTION
	"Table entry attribute for bgpSendTime"
	::={bgpSendTimeLevelEntry 4}


bgpReplaces	OBJECT IDENTIFIER ::={bgp 7}

bgpReplacesVal	OBJECT-TYPE
	SYNTAX	 CounterBasedGauge64
	MAX-ACCESS read-only
	STATUS current
	DESCRIPTION "Total count of announces without withdraw, replacing an already existing prefix/route"

	::={bgpReplaces 1}

bgpReplacesMax	OBJECT-TYPE
	SYNTAX	 CounterBasedGauge64
	MAX-ACCESS read-only
	STATUS current
	DESCRIPTION "Total count of announces without withdraw, replacing an already existing prefix/route"

	::={bgpReplaces 3}

bgpReplacesLevelTable OBJECT-TYPE
	SYNTAX      SEQUENCE OF BgpReplacesLevelEntry
	MAX-ACCESS  not-accessible
	STATUS      current
	DESCRIPTION
	"Table for bgpReplaces"
	::={bgpReplaces 4}

bgpReplacesLevelEntry OBJECT-TYPE
	SYNTAX      BgpReplacesLevelEntry
	MAX-ACCESS  not-accessible
	STATUS      current
	DESCRIPTION
	"Table entry for bgpReplaces"
	INDEX { bgpReplacesLevelName }
	::={bgpReplacesLevelTable 1}

BgpReplacesLevelEntry ::=
	SEQUENCE {
		bgpReplacesLevelName	DisplayString,
		bgpReplacesLevelVal	CounterBasedGauge64,
		bgpReplacesLevelMax	CounterBasedGauge64
	}

bgpReplacesLevelName OBJECT-TYPE
	SYNTAX      DisplayString
	MAX-ACCESS  not-accessible
	STATUS      current
	DESCRIPTION
	"Table entry display string for bgpReplaces"
	::={bgpReplacesLevelEntry 1}

bgpReplacesLevelVal OBJECT-TYPE
	SYNTAX	 CounterBasedGauge64
	MAX-ACCESS  read-only
	STATUS      current
	DESCRIPTION
	"Table entry attribute for bgpReplaces"
	::={bgpReplacesLevelEntry 2}

bgpReplacesLevelMax OBJECT-TYPE
	SYNTAX	 CounterBasedGauge64
	MAX-ACCESS  read-only
	STATUS      current
	DESCRIPTION
	"Table entry attribute for bgpReplaces"
	::={bgpReplacesLevelEntry 4}


bgpWithdraws	OBJECT IDENTIFIER ::={bgp 8}

bgpWithdrawsVal	OBJECT-TYPE
	SYNTAX	 CounterBasedGauge64
	MAX-ACCESS read-only
	STATUS current
	DESCRIPTION "Total count of withdrawn prefixes/routes"

	::={bgpWithdraws 1}

bgpWithdrawsMax	OBJECT-TYPE
	SYNTAX	 CounterBasedGauge64
	MAX-ACCESS read-only
	STATUS current
	DESCRIPTION "Total count of withdrawn prefixes/routes"

	::={bgpWithdraws 3}

bgpWithdrawsLevelTable OBJECT-TYPE
	SYNTAX      SEQUENCE OF BgpWithdrawsLevelEntry
	MAX-ACCESS  not-accessible
	STATUS      current
	DESCRIPTION
	"Table for bgpWithdraws"
	::={bgpWithdraws 4}

bgpWithdrawsLevelEntry OBJECT-TYPE
	SYNTAX      BgpWithdrawsLevelEntry
	MAX-ACCESS  not-accessible
	STATUS      current
	DESCRIPTION
	"Table entry for bgpWithdraws"
	INDEX { bgpWithdrawsLevelName }
	::={bgpWithdrawsLevelTable 1}

BgpWithdrawsLevelEntry ::=
	SEQUENCE {
		bgpWithdrawsLevelName	DisplayString,
		bgpWithdrawsLevelVal	CounterBasedGauge64,
		bgpWithdrawsLevelMax	CounterBasedGauge64
	}

bgpWithdrawsLevelName OBJECT-TYPE
	SYNTAX      DisplayString
	MAX-ACCESS  not-accessible
	STATUS      current
	DESCRIPTION
	"Table entry display string for bgpWithdraws"
	::={bgpWithdrawsLevelEntry 1}

bgpWithdrawsLevelVal OBJECT-TYPE
	SYNTAX	 CounterBasedGauge64
	MAX-ACCESS  read-only
	STATUS      current
	DESCRIPTION
	"Table entry attribute for bgpWithdraws"
	::={bgpWithdrawsLevelEntry 2}

bgpWithdrawsLevelMax OBJECT-TYPE
	SYNTAX	 CounterBasedGauge64
	MAX-ACCESS  read-only
	STATUS      current
	DESCRIPTION
	"Table entry attribute for bgpWithdraws"
	::={bgpWithdrawsLevelEntry 4}


bgpAnnounces	OBJECT IDENTIFIER ::={bgp 9}

bgpAnnouncesVal	OBJECT-TYPE
	SYNTAX	 CounterBasedGauge64
	MAX-ACCESS read-only
	STATUS current
	DESCRIPTION "Total count of announced prefixes/routes"

	::={bgpAnnounces 1}

bgpAnnouncesMax	OBJECT-TYPE
	SYNTAX	 CounterBasedGauge64
	MAX-ACCESS read-only
	STATUS current
	DESCRIPTION "Total count of announced prefixes/routes"

	::={bgpAnnounces 3}

bgpAnnouncesLevelTable OBJECT-TYPE
	SYNTAX      SEQUENCE OF BgpAnnouncesLevelEntry
	MAX-ACCESS  not-accessible
	STATUS      current
	DESCRIPTION
	"Table for bgpAnnounces"
	::={bgpAnnounces 4}

bgpAnnouncesLevelEntry OBJECT-TYPE
	SYNTAX      BgpAnnouncesLevelEntry
	MAX-ACCESS  not-accessible
	STATUS      current
	DESCRIPTION
	"Table entry for bgpAnnounces"
	INDEX { bgpAnnouncesLevelName }
	::={bgpAnnouncesLevelTable 1}

BgpAnnouncesLevelEntry ::=
	SEQUENCE {
		bgpAnnouncesLevelName	DisplayString,
		bgpAnnouncesLevelVal	CounterBasedGauge64,
		bgpAnnouncesLevelMax	CounterBasedGauge64
	}

bgpAnnouncesLevelName OBJECT-TYPE
	SYNTAX      DisplayString
	MAX-ACCESS  not-accessible
	STATUS      current
	DESCRIPTION
	"Table entry display string for bgpAnnounces"
	::={bgpAnnouncesLevelEntry 1}

bgpAnnouncesLevelVal OBJECT-TYPE
	SYNTAX	 CounterBasedGauge64
	MAX-ACCESS  read-only
	STATUS      current
	DESCRIPTION
	"Table entry attribute for bgpAnnounces"
	::={bgpAnnouncesLevelEntry 2}

bgpAnnouncesLevelMax OBJECT-TYPE
	SYNTAX	 CounterBasedGauge64
	MAX-ACCESS  read-only
	STATUS      current
	DESCRIPTION
	"Table entry attribute for bgpAnnounces"
	::={bgpAnnouncesLevelEntry 4}


bgpReconnects	OBJECT IDENTIFIER ::={bgp 10}

bgpReconnectsVal	OBJECT-TYPE
	SYNTAX	 CounterBasedGauge64
	MAX-ACCESS read-only
	STATUS current
	DESCRIPTION "Total number of reconnects"

	::={bgpReconnects 1}

bgpReconnectsMax	OBJECT-TYPE
	SYNTAX	 CounterBasedGauge64
	MAX-ACCESS read-only
	STATUS current
	DESCRIPTION "Total number of reconnects"

	::={bgpReconnects 3}

bgpReconnectsLevelTable OBJECT-TYPE
	SYNTAX      SEQUENCE OF BgpReconnectsLevelEntry
	MAX-ACCESS  not-accessible
	STATUS      current
	DESCRIPTION
	"Table for bgpReconnects"
	::={bgpReconnects 4}

bgpReconnectsLevelEntry OBJECT-TYPE
	SYNTAX      BgpReconnectsLevelEntry
	MAX-ACCESS  not-accessible
	STATUS      current
	DESCRIPTION
	"Table entry for bgpReconnects"
	INDEX { bgpReconnectsLevelName }
	::={bgpReconnectsLevelTable 1}

BgpReconnectsLevelEntry ::=
	SEQUENCE {
		bgpReconnectsLevelName	DisplayString,
		bgpReconnectsLevelVal	CounterBasedGauge64,
		bgpReconnectsLevelMax	CounterBasedGauge64
	}

bgpReconnectsLevelName OBJECT-TYPE
	SYNTAX      DisplayString
	MAX-ACCESS  not-accessible
	STATUS      current
	DESCRIPTION
	"Table entry display string for bgpReconnects"
	::={bgpReconnectsLevelEntry 1}

bgpReconnectsLevelVal OBJECT-TYPE
	SYNTAX	 CounterBasedGauge64
	MAX-ACCESS  read-only
	STATUS      current
	DESCRIPTION
	"Table entry attribute for bgpReconnects"
	::={bgpReconnectsLevelEntry 2}

bgpReconnectsLevelMax OBJECT-TYPE
	SYNTAX	 CounterBasedGauge64
	MAX-ACCESS  read-only
	STATUS      current
	DESCRIPTION
	"Table entry attribute for bgpReconnects"
	::={bgpReconnectsLevelEntry 4}


bgpRecyclePaths	OBJECT IDENTIFIER ::={bgp 12}

bgpRecyclePathsVal	OBJECT-TYPE
	SYNTAX	 CounterBasedGauge64
	MAX-ACCESS read-only
	STATUS current
	DESCRIPTION "Number of paths waiting for garbage collection"

	::={bgpRecyclePaths 1}

bgpRecyclePathsMax	OBJECT-TYPE
	SYNTAX	 CounterBasedGauge64
	MAX-ACCESS read-only
	STATUS current
	DESCRIPTION "Number of paths waiting for garbage collection"

	::={bgpRecyclePaths 3}

bgpRecyclePathsLevelTable OBJECT-TYPE
	SYNTAX      SEQUENCE OF BgpRecyclePathsLevelEntry
	MAX-ACCESS  not-accessible
	STATUS      current
	DESCRIPTION
	"Table for bgpRecyclePaths"
	::={bgpRecyclePaths 4}

bgpRecyclePathsLevelEntry OBJECT-TYPE
	SYNTAX      BgpRecyclePathsLevelEntry
	MAX-ACCESS  not-accessible
	STATUS      current
	DESCRIPTION
	"Table entry for bgpRecyclePaths"
	INDEX { bgpRecyclePathsLevelName }
	::={bgpRecyclePathsLevelTable 1}

BgpRecyclePathsLevelEntry ::=
	SEQUENCE {
		bgpRecyclePathsLevelName	DisplayString,
		bgpRecyclePathsLevelVal	CounterBasedGauge64,
		bgpRecyclePathsLevelMax	CounterBasedGauge64
	}

bgpRecyclePathsLevelName OBJECT-TYPE
	SYNTAX      DisplayString
	MAX-ACCESS  not-accessible
	STATUS      current
	DESCRIPTION
	"Table entry display string for bgpRecyclePaths"
	::={bgpRecyclePathsLevelEntry 1}

bgpRecyclePathsLevelVal OBJECT-TYPE
	SYNTAX	 CounterBasedGauge64
	MAX-ACCESS  read-only
	STATUS      current
	DESCRIPTION
	"Table entry attribute for bgpRecyclePaths"
	::={bgpRecyclePathsLevelEntry 2}

bgpRecyclePathsLevelMax OBJECT-TYPE
	SYNTAX	 CounterBasedGauge64
	MAX-ACCESS  read-only
	STATUS      current
	DESCRIPTION
	"Table entry attribute for bgpRecyclePaths"
	::={bgpRecyclePathsLevelEntry 4}


bgpFreelistPaths	OBJECT IDENTIFIER ::={bgp 13}

bgpFreelistPathsVal	OBJECT-TYPE
	SYNTAX	 CounterBasedGauge64
	MAX-ACCESS read-only
	STATUS current
	DESCRIPTION "Number of paths in freelist"

	::={bgpFreelistPaths 1}

bgpFreelistPathsMax	OBJECT-TYPE
	SYNTAX	 CounterBasedGauge64
	MAX-ACCESS read-only
	STATUS current
	DESCRIPTION "Number of paths in freelist"

	::={bgpFreelistPaths 3}

bgpFreelistPathsLevelTable OBJECT-TYPE
	SYNTAX      SEQUENCE OF BgpFreelistPathsLevelEntry
	MAX-ACCESS  not-accessible
	STATUS      current
	DESCRIPTION
	"Table for bgpFreelistPaths"
	::={bgpFreelistPaths 4}

bgpFreelistPathsLevelEntry OBJECT-TYPE
	SYNTAX      BgpFreelistPathsLevelEntry
	MAX-ACCESS  not-accessible
	STATUS      current
	DESCRIPTION
	"Table entry for bgpFreelistPaths"
	INDEX { bgpFreelistPathsLevelName }
	::={bgpFreelistPathsLevelTable 1}

BgpFreelistPathsLevelEntry ::=
	SEQUENCE {
		bgpFreelistPathsLevelName	DisplayString,
		bgpFreelistPathsLevelVal	CounterBasedGauge64,
		bgpFreelistPathsLevelMax	CounterBasedGauge64
	}

bgpFreelistPathsLevelName OBJECT-TYPE
	SYNTAX      DisplayString
	MAX-ACCESS  not-accessible
	STATUS      current
	DESCRIPTION
	"Table entry display string for bgpFreelistPaths"
	::={bgpFreelistPathsLevelEntry 1}

bgpFreelistPathsLevelVal OBJECT-TYPE
	SYNTAX	 CounterBasedGauge64
	MAX-ACCESS  read-only
	STATUS      current
	DESCRIPTION
	"Table entry attribute for bgpFreelistPaths"
	::={bgpFreelistPathsLevelEntry 2}

bgpFreelistPathsLevelMax OBJECT-TYPE
	SYNTAX	 CounterBasedGauge64
	MAX-ACCESS  read-only
	STATUS      current
	DESCRIPTION
	"Table entry attribute for bgpFreelistPaths"
	::={bgpFreelistPathsLevelEntry 4}


bgpBalanceTime	OBJECT IDENTIFIER ::={bgp 14}

bgpBalanceTimeVal	OBJECT-TYPE
	SYNTAX	 CounterBasedGauge64
	MAX-ACCESS read-only
	STATUS current
	DESCRIPTION "Time to rebalance tree"

	::={bgpBalanceTime 1}

bgpBalanceTimeMax	OBJECT-TYPE
	SYNTAX	 CounterBasedGauge64
	MAX-ACCESS read-only
	STATUS current
	DESCRIPTION "Time to rebalance tree"

	::={bgpBalanceTime 3}

bgpBalanceTimeLevelTable OBJECT-TYPE
	SYNTAX      SEQUENCE OF BgpBalanceTimeLevelEntry
	MAX-ACCESS  not-accessible
	STATUS      current
	DESCRIPTION
	"Table for bgpBalanceTime"
	::={bgpBalanceTime 4}

bgpBalanceTimeLevelEntry OBJECT-TYPE
	SYNTAX      BgpBalanceTimeLevelEntry
	MAX-ACCESS  not-accessible
	STATUS      current
	DESCRIPTION
	"Table entry for bgpBalanceTime"
	INDEX { bgpBalanceTimeLevelName }
	::={bgpBalanceTimeLevelTable 1}

BgpBalanceTimeLevelEntry ::=
	SEQUENCE {
		bgpBalanceTimeLevelName	DisplayString,
		bgpBalanceTimeLevelVal	CounterBasedGauge64,
		bgpBalanceTimeLevelMax	CounterBasedGauge64
	}

bgpBalanceTimeLevelName OBJECT-TYPE
	SYNTAX      DisplayString
	MAX-ACCESS  not-accessible
	STATUS      current
	DESCRIPTION
	"Table entry display string for bgpBalanceTime"
	::={bgpBalanceTimeLevelEntry 1}

bgpBalanceTimeLevelVal OBJECT-TYPE
	SYNTAX	 CounterBasedGauge64
	MAX-ACCESS  read-only
	STATUS      current
	DESCRIPTION
	"Table entry attribute for bgpBalanceTime"
	::={bgpBalanceTimeLevelEntry 2}

bgpBalanceTimeLevelMax OBJECT-TYPE
	SYNTAX	 CounterBasedGauge64
	MAX-ACCESS  read-only
	STATUS      current
	DESCRIPTION
	"Table entry attribute for bgpBalanceTime"
	::={bgpBalanceTimeLevelEntry 4}


bgpPathTooSmall	OBJECT IDENTIFIER ::={bgp 22}

bgpPathTooSmallVal	OBJECT-TYPE
	SYNTAX	 CounterBasedGauge64
	MAX-ACCESS read-only
	STATUS current
	DESCRIPTION "Number of AS-paths received that exceed PL_CONFIG_BGP_MAX_PATH"

	::={bgpPathTooSmall 1}

bgpPathTooSmallMax	OBJECT-TYPE
	SYNTAX	 CounterBasedGauge64
	MAX-ACCESS read-only
	STATUS current
	DESCRIPTION "Number of AS-paths received that exceed PL_CONFIG_BGP_MAX_PATH"

	::={bgpPathTooSmall 3}

bgpPathTooSmallLevelTable OBJECT-TYPE
	SYNTAX      SEQUENCE OF BgpPathTooSmallLevelEntry
	MAX-ACCESS  not-accessible
	STATUS      current
	DESCRIPTION
	"Table for bgpPathTooSmall"
	::={bgpPathTooSmall 4}

bgpPathTooSmallLevelEntry OBJECT-TYPE
	SYNTAX      BgpPathTooSmallLevelEntry
	MAX-ACCESS  not-accessible
	STATUS      current
	DESCRIPTION
	"Table entry for bgpPathTooSmall"
	INDEX { bgpPathTooSmallLevelName }
	::={bgpPathTooSmallLevelTable 1}

BgpPathTooSmallLevelEntry ::=
	SEQUENCE {
		bgpPathTooSmallLevelName	DisplayString,
		bgpPathTooSmallLevelVal	CounterBasedGauge64,
		bgpPathTooSmallLevelMax	CounterBasedGauge64
	}

bgpPathTooSmallLevelName OBJECT-TYPE
	SYNTAX      DisplayString
	MAX-ACCESS  not-accessible
	STATUS      current
	DESCRIPTION
	"Table entry display string for bgpPathTooSmall"
	::={bgpPathTooSmallLevelEntry 1}

bgpPathTooSmallLevelVal OBJECT-TYPE
	SYNTAX	 CounterBasedGauge64
	MAX-ACCESS  read-only
	STATUS      current
	DESCRIPTION
	"Table entry attribute for bgpPathTooSmall"
	::={bgpPathTooSmallLevelEntry 2}

bgpPathTooSmallLevelMax OBJECT-TYPE
	SYNTAX	 CounterBasedGauge64
	MAX-ACCESS  read-only
	STATUS      current
	DESCRIPTION
	"Table entry attribute for bgpPathTooSmall"
	::={bgpPathTooSmallLevelEntry 4}


bgpPathMaxSeen	OBJECT IDENTIFIER ::={bgp 23}

bgpPathMaxSeenVal	OBJECT-TYPE
	SYNTAX	 CounterBasedGauge64
	MAX-ACCESS read-only
	STATUS current
	DESCRIPTION "Longest AS-path we have seen in a BGP update"

	::={bgpPathMaxSeen 1}

bgpPathMaxSeenMax	OBJECT-TYPE
	SYNTAX	 CounterBasedGauge64
	MAX-ACCESS read-only
	STATUS current
	DESCRIPTION "Longest AS-path we have seen in a BGP update"

	::={bgpPathMaxSeen 3}

bgpPathMaxSeenLevelTable OBJECT-TYPE
	SYNTAX      SEQUENCE OF BgpPathMaxSeenLevelEntry
	MAX-ACCESS  not-accessible
	STATUS      current
	DESCRIPTION
	"Table for bgpPathMaxSeen"
	::={bgpPathMaxSeen 4}

bgpPathMaxSeenLevelEntry OBJECT-TYPE
	SYNTAX      BgpPathMaxSeenLevelEntry
	MAX-ACCESS  not-accessible
	STATUS      current
	DESCRIPTION
	"Table entry for bgpPathMaxSeen"
	INDEX { bgpPathMaxSeenLevelName }
	::={bgpPathMaxSeenLevelTable 1}

BgpPathMaxSeenLevelEntry ::=
	SEQUENCE {
		bgpPathMaxSeenLevelName	DisplayString,
		bgpPathMaxSeenLevelVal	CounterBasedGauge64,
		bgpPathMaxSeenLevelMax	CounterBasedGauge64
	}

bgpPathMaxSeenLevelName OBJECT-TYPE
	SYNTAX      DisplayString
	MAX-ACCESS  not-accessible
	STATUS      current
	DESCRIPTION
	"Table entry display string for bgpPathMaxSeen"
	::={bgpPathMaxSeenLevelEntry 1}

bgpPathMaxSeenLevelVal OBJECT-TYPE
	SYNTAX	 CounterBasedGauge64
	MAX-ACCESS  read-only
	STATUS      current
	DESCRIPTION
	"Table entry attribute for bgpPathMaxSeen"
	::={bgpPathMaxSeenLevelEntry 2}

bgpPathMaxSeenLevelMax OBJECT-TYPE
	SYNTAX	 CounterBasedGauge64
	MAX-ACCESS  read-only
	STATUS      current
	DESCRIPTION
	"Table entry attribute for bgpPathMaxSeen"
	::={bgpPathMaxSeenLevelEntry 4}


bgpCommunityTooSmall	OBJECT IDENTIFIER ::={bgp 24}

bgpCommunityTooSmallVal	OBJECT-TYPE
	SYNTAX	 CounterBasedGauge64
	MAX-ACCESS read-only
	STATUS current
	DESCRIPTION "Number of community updates received that exceed PL_CONFIG_BGP_MAX_COMMUNITIES"

	::={bgpCommunityTooSmall 1}

bgpCommunityTooSmallMax	OBJECT-TYPE
	SYNTAX	 CounterBasedGauge64
	MAX-ACCESS read-only
	STATUS current
	DESCRIPTION "Number of community updates received that exceed PL_CONFIG_BGP_MAX_COMMUNITIES"

	::={bgpCommunityTooSmall 3}

bgpCommunityTooSmallLevelTable OBJECT-TYPE
	SYNTAX      SEQUENCE OF BgpCommunityTooSmallLevelEntry
	MAX-ACCESS  not-accessible
	STATUS      current
	DESCRIPTION
	"Table for bgpCommunityTooSmall"
	::={bgpCommunityTooSmall 4}

bgpCommunityTooSmallLevelEntry OBJECT-TYPE
	SYNTAX      BgpCommunityTooSmallLevelEntry
	MAX-ACCESS  not-accessible
	STATUS      current
	DESCRIPTION
	"Table entry for bgpCommunityTooSmall"
	INDEX { bgpCommunityTooSmallLevelName }
	::={bgpCommunityTooSmallLevelTable 1}

BgpCommunityTooSmallLevelEntry ::=
	SEQUENCE {
		bgpCommunityTooSmallLevelName	DisplayString,
		bgpCommunityTooSmallLevelVal	CounterBasedGauge64,
		bgpCommunityTooSmallLevelMax	CounterBasedGauge64
	}

bgpCommunityTooSmallLevelName OBJECT-TYPE
	SYNTAX      DisplayString
	MAX-ACCESS  not-accessible
	STATUS      current
	DESCRIPTION
	"Table entry display string for bgpCommunityTooSmall"
	::={bgpCommunityTooSmallLevelEntry 1}

bgpCommunityTooSmallLevelVal OBJECT-TYPE
	SYNTAX	 CounterBasedGauge64
	MAX-ACCESS  read-only
	STATUS      current
	DESCRIPTION
	"Table entry attribute for bgpCommunityTooSmall"
	::={bgpCommunityTooSmallLevelEntry 2}

bgpCommunityTooSmallLevelMax OBJECT-TYPE
	SYNTAX	 CounterBasedGauge64
	MAX-ACCESS  read-only
	STATUS      current
	DESCRIPTION
	"Table entry attribute for bgpCommunityTooSmall"
	::={bgpCommunityTooSmallLevelEntry 4}


bgpCommunityMaxSeen	OBJECT IDENTIFIER ::={bgp 25}

bgpCommunityMaxSeenVal	OBJECT-TYPE
	SYNTAX	 CounterBasedGauge64
	MAX-ACCESS read-only
	STATUS current
	DESCRIPTION "Maximum number of communities we have seen in a BGP update"

	::={bgpCommunityMaxSeen 1}

bgpCommunityMaxSeenMax	OBJECT-TYPE
	SYNTAX	 CounterBasedGauge64
	MAX-ACCESS read-only
	STATUS current
	DESCRIPTION "Maximum number of communities we have seen in a BGP update"

	::={bgpCommunityMaxSeen 3}

bgpCommunityMaxSeenLevelTable OBJECT-TYPE
	SYNTAX      SEQUENCE OF BgpCommunityMaxSeenLevelEntry
	MAX-ACCESS  not-accessible
	STATUS      current
	DESCRIPTION
	"Table for bgpCommunityMaxSeen"
	::={bgpCommunityMaxSeen 4}

bgpCommunityMaxSeenLevelEntry OBJECT-TYPE
	SYNTAX      BgpCommunityMaxSeenLevelEntry
	MAX-ACCESS  not-accessible
	STATUS      current
	DESCRIPTION
	"Table entry for bgpCommunityMaxSeen"
	INDEX { bgpCommunityMaxSeenLevelName }
	::={bgpCommunityMaxSeenLevelTable 1}

BgpCommunityMaxSeenLevelEntry ::=
	SEQUENCE {
		bgpCommunityMaxSeenLevelName	DisplayString,
		bgpCommunityMaxSeenLevelVal	CounterBasedGauge64,
		bgpCommunityMaxSeenLevelMax	CounterBasedGauge64
	}

bgpCommunityMaxSeenLevelName OBJECT-TYPE
	SYNTAX      DisplayString
	MAX-ACCESS  not-accessible
	STATUS      current
	DESCRIPTION
	"Table entry display string for bgpCommunityMaxSeen"
	::={bgpCommunityMaxSeenLevelEntry 1}

bgpCommunityMaxSeenLevelVal OBJECT-TYPE
	SYNTAX	 CounterBasedGauge64
	MAX-ACCESS  read-only
	STATUS      current
	DESCRIPTION
	"Table entry attribute for bgpCommunityMaxSeen"
	::={bgpCommunityMaxSeenLevelEntry 2}

bgpCommunityMaxSeenLevelMax OBJECT-TYPE
	SYNTAX	 CounterBasedGauge64
	MAX-ACCESS  read-only
	STATUS      current
	DESCRIPTION
	"Table entry attribute for bgpCommunityMaxSeen"
	::={bgpCommunityMaxSeenLevelEntry 4}


bgpIPv4Prefixes	OBJECT IDENTIFIER ::={bgp 31}

bgpIPv4PrefixesVal	OBJECT-TYPE
	SYNTAX	 CounterBasedGauge64
	MAX-ACCESS read-only
	STATUS current
	DESCRIPTION "Number of IPv4 prefixes/routes"

	::={bgpIPv4Prefixes 1}

bgpIPv4PrefixesMax	OBJECT-TYPE
	SYNTAX	 CounterBasedGauge64
	MAX-ACCESS read-only
	STATUS current
	DESCRIPTION "Number of IPv4 prefixes/routes"

	::={bgpIPv4Prefixes 3}

bgpIPv4PrefixesLevelTable OBJECT-TYPE
	SYNTAX      SEQUENCE OF BgpIPv4PrefixesLevelEntry
	MAX-ACCESS  not-accessible
	STATUS      current
	DESCRIPTION
	"Table for bgpIPv4Prefixes"
	::={bgpIPv4Prefixes 4}

bgpIPv4PrefixesLevelEntry OBJECT-TYPE
	SYNTAX      BgpIPv4PrefixesLevelEntry
	MAX-ACCESS  not-accessible
	STATUS      current
	DESCRIPTION
	"Table entry for bgpIPv4Prefixes"
	INDEX { bgpIPv4PrefixesLevelName }
	::={bgpIPv4PrefixesLevelTable 1}

BgpIPv4PrefixesLevelEntry ::=
	SEQUENCE {
		bgpIPv4PrefixesLevelName	DisplayString,
		bgpIPv4PrefixesLevelVal	CounterBasedGauge64,
		bgpIPv4PrefixesLevelMax	CounterBasedGauge64
	}

bgpIPv4PrefixesLevelName OBJECT-TYPE
	SYNTAX      DisplayString
	MAX-ACCESS  not-accessible
	STATUS      current
	DESCRIPTION
	"Table entry display string for bgpIPv4Prefixes"
	::={bgpIPv4PrefixesLevelEntry 1}

bgpIPv4PrefixesLevelVal OBJECT-TYPE
	SYNTAX	 CounterBasedGauge64
	MAX-ACCESS  read-only
	STATUS      current
	DESCRIPTION
	"Table entry attribute for bgpIPv4Prefixes"
	::={bgpIPv4PrefixesLevelEntry 2}

bgpIPv4PrefixesLevelMax OBJECT-TYPE
	SYNTAX	 CounterBasedGauge64
	MAX-ACCESS  read-only
	STATUS      current
	DESCRIPTION
	"Table entry attribute for bgpIPv4Prefixes"
	::={bgpIPv4PrefixesLevelEntry 4}


bgpIPv4Announces	OBJECT IDENTIFIER ::={bgp 32}

bgpIPv4AnnouncesVal	OBJECT-TYPE
	SYNTAX	 CounterBasedGauge64
	MAX-ACCESS read-only
	STATUS current
	DESCRIPTION "Total count of IPv4 announced prefixes/routes"

	::={bgpIPv4Announces 1}

bgpIPv4AnnouncesMax	OBJECT-TYPE
	SYNTAX	 CounterBasedGauge64
	MAX-ACCESS read-only
	STATUS current
	DESCRIPTION "Total count of IPv4 announced prefixes/routes"

	::={bgpIPv4Announces 3}

bgpIPv4AnnouncesLevelTable OBJECT-TYPE
	SYNTAX      SEQUENCE OF BgpIPv4AnnouncesLevelEntry
	MAX-ACCESS  not-accessible
	STATUS      current
	DESCRIPTION
	"Table for bgpIPv4Announces"
	::={bgpIPv4Announces 4}

bgpIPv4AnnouncesLevelEntry OBJECT-TYPE
	SYNTAX      BgpIPv4AnnouncesLevelEntry
	MAX-ACCESS  not-accessible
	STATUS      current
	DESCRIPTION
	"Table entry for bgpIPv4Announces"
	INDEX { bgpIPv4AnnouncesLevelName }
	::={bgpIPv4AnnouncesLevelTable 1}

BgpIPv4AnnouncesLevelEntry ::=
	SEQUENCE {
		bgpIPv4AnnouncesLevelName	DisplayString,
		bgpIPv4AnnouncesLevelVal	CounterBasedGauge64,
		bgpIPv4AnnouncesLevelMax	CounterBasedGauge64
	}

bgpIPv4AnnouncesLevelName OBJECT-TYPE
	SYNTAX      DisplayString
	MAX-ACCESS  not-accessible
	STATUS      current
	DESCRIPTION
	"Table entry display string for bgpIPv4Announces"
	::={bgpIPv4AnnouncesLevelEntry 1}

bgpIPv4AnnouncesLevelVal OBJECT-TYPE
	SYNTAX	 CounterBasedGauge64
	MAX-ACCESS  read-only
	STATUS      current
	DESCRIPTION
	"Table entry attribute for bgpIPv4Announces"
	::={bgpIPv4AnnouncesLevelEntry 2}

bgpIPv4AnnouncesLevelMax OBJECT-TYPE
	SYNTAX	 CounterBasedGauge64
	MAX-ACCESS  read-only
	STATUS      current
	DESCRIPTION
	"Table entry attribute for bgpIPv4Announces"
	::={bgpIPv4AnnouncesLevelEntry 4}


bgpIPv4Withdraws	OBJECT IDENTIFIER ::={bgp 33}

bgpIPv4WithdrawsVal	OBJECT-TYPE
	SYNTAX	 CounterBasedGauge64
	MAX-ACCESS read-only
	STATUS current
	DESCRIPTION "Total count of IPv4 withdrawn prefixes/routes"

	::={bgpIPv4Withdraws 1}

bgpIPv4WithdrawsMax	OBJECT-TYPE
	SYNTAX	 CounterBasedGauge64
	MAX-ACCESS read-only
	STATUS current
	DESCRIPTION "Total count of IPv4 withdrawn prefixes/routes"

	::={bgpIPv4Withdraws 3}

bgpIPv4WithdrawsLevelTable OBJECT-TYPE
	SYNTAX      SEQUENCE OF BgpIPv4WithdrawsLevelEntry
	MAX-ACCESS  not-accessible
	STATUS      current
	DESCRIPTION
	"Table for bgpIPv4Withdraws"
	::={bgpIPv4Withdraws 4}

bgpIPv4WithdrawsLevelEntry OBJECT-TYPE
	SYNTAX      BgpIPv4WithdrawsLevelEntry
	MAX-ACCESS  not-accessible
	STATUS      current
	DESCRIPTION
	"Table entry for bgpIPv4Withdraws"
	INDEX { bgpIPv4WithdrawsLevelName }
	::={bgpIPv4WithdrawsLevelTable 1}

BgpIPv4WithdrawsLevelEntry ::=
	SEQUENCE {
		bgpIPv4WithdrawsLevelName	DisplayString,
		bgpIPv4WithdrawsLevelVal	CounterBasedGauge64,
		bgpIPv4WithdrawsLevelMax	CounterBasedGauge64
	}

bgpIPv4WithdrawsLevelName OBJECT-TYPE
	SYNTAX      DisplayString
	MAX-ACCESS  not-accessible
	STATUS      current
	DESCRIPTION
	"Table entry display string for bgpIPv4Withdraws"
	::={bgpIPv4WithdrawsLevelEntry 1}

bgpIPv4WithdrawsLevelVal OBJECT-TYPE
	SYNTAX	 CounterBasedGauge64
	MAX-ACCESS  read-only
	STATUS      current
	DESCRIPTION
	"Table entry attribute for bgpIPv4Withdraws"
	::={bgpIPv4WithdrawsLevelEntry 2}

bgpIPv4WithdrawsLevelMax OBJECT-TYPE
	SYNTAX	 CounterBasedGauge64
	MAX-ACCESS  read-only
	STATUS      current
	DESCRIPTION
	"Table entry attribute for bgpIPv4Withdraws"
	::={bgpIPv4WithdrawsLevelEntry 4}


bgpIPv4Replaces	OBJECT IDENTIFIER ::={bgp 34}

bgpIPv4ReplacesVal	OBJECT-TYPE
	SYNTAX	 CounterBasedGauge64
	MAX-ACCESS read-only
	STATUS current
	DESCRIPTION "Total count of IPv4 announces without withdraw, replacing an already existing prefix/route"

	::={bgpIPv4Replaces 1}

bgpIPv4ReplacesMax	OBJECT-TYPE
	SYNTAX	 CounterBasedGauge64
	MAX-ACCESS read-only
	STATUS current
	DESCRIPTION "Total count of IPv4 announces without withdraw, replacing an already existing prefix/route"

	::={bgpIPv4Replaces 3}

bgpIPv4ReplacesLevelTable OBJECT-TYPE
	SYNTAX      SEQUENCE OF BgpIPv4ReplacesLevelEntry
	MAX-ACCESS  not-accessible
	STATUS      current
	DESCRIPTION
	"Table for bgpIPv4Replaces"
	::={bgpIPv4Replaces 4}

bgpIPv4ReplacesLevelEntry OBJECT-TYPE
	SYNTAX      BgpIPv4ReplacesLevelEntry
	MAX-ACCESS  not-accessible
	STATUS      current
	DESCRIPTION
	"Table entry for bgpIPv4Replaces"
	INDEX { bgpIPv4ReplacesLevelName }
	::={bgpIPv4ReplacesLevelTable 1}

BgpIPv4ReplacesLevelEntry ::=
	SEQUENCE {
		bgpIPv4ReplacesLevelName	DisplayString,
		bgpIPv4ReplacesLevelVal	CounterBasedGauge64,
		bgpIPv4ReplacesLevelMax	CounterBasedGauge64
	}

bgpIPv4ReplacesLevelName OBJECT-TYPE
	SYNTAX      DisplayString
	MAX-ACCESS  not-accessible
	STATUS      current
	DESCRIPTION
	"Table entry display string for bgpIPv4Replaces"
	::={bgpIPv4ReplacesLevelEntry 1}

bgpIPv4ReplacesLevelVal OBJECT-TYPE
	SYNTAX	 CounterBasedGauge64
	MAX-ACCESS  read-only
	STATUS      current
	DESCRIPTION
	"Table entry attribute for bgpIPv4Replaces"
	::={bgpIPv4ReplacesLevelEntry 2}

bgpIPv4ReplacesLevelMax OBJECT-TYPE
	SYNTAX	 CounterBasedGauge64
	MAX-ACCESS  read-only
	STATUS      current
	DESCRIPTION
	"Table entry attribute for bgpIPv4Replaces"
	::={bgpIPv4ReplacesLevelEntry 4}


bgpIPv4BalanceTime	OBJECT IDENTIFIER ::={bgp 35}

bgpIPv4BalanceTimeVal	OBJECT-TYPE
	SYNTAX	 CounterBasedGauge64
	MAX-ACCESS read-only
	STATUS current
	DESCRIPTION "Time to balance IPv4 tree"

	::={bgpIPv4BalanceTime 1}

bgpIPv4BalanceTimeMax	OBJECT-TYPE
	SYNTAX	 CounterBasedGauge64
	MAX-ACCESS read-only
	STATUS current
	DESCRIPTION "Time to balance IPv4 tree"

	::={bgpIPv4BalanceTime 3}

bgpIPv4BalanceTimeLevelTable OBJECT-TYPE
	SYNTAX      SEQUENCE OF BgpIPv4BalanceTimeLevelEntry
	MAX-ACCESS  not-accessible
	STATUS      current
	DESCRIPTION
	"Table for bgpIPv4BalanceTime"
	::={bgpIPv4BalanceTime 4}

bgpIPv4BalanceTimeLevelEntry OBJECT-TYPE
	SYNTAX      BgpIPv4BalanceTimeLevelEntry
	MAX-ACCESS  not-accessible
	STATUS      current
	DESCRIPTION
	"Table entry for bgpIPv4BalanceTime"
	INDEX { bgpIPv4BalanceTimeLevelName }
	::={bgpIPv4BalanceTimeLevelTable 1}

BgpIPv4BalanceTimeLevelEntry ::=
	SEQUENCE {
		bgpIPv4BalanceTimeLevelName	DisplayString,
		bgpIPv4BalanceTimeLevelVal	CounterBasedGauge64,
		bgpIPv4BalanceTimeLevelMax	CounterBasedGauge64
	}

bgpIPv4BalanceTimeLevelName OBJECT-TYPE
	SYNTAX      DisplayString
	MAX-ACCESS  not-accessible
	STATUS      current
	DESCRIPTION
	"Table entry display string for bgpIPv4BalanceTime"
	::={bgpIPv4BalanceTimeLevelEntry 1}

bgpIPv4BalanceTimeLevelVal OBJECT-TYPE
	SYNTAX	 CounterBasedGauge64
	MAX-ACCESS  read-only
	STATUS      current
	DESCRIPTION
	"Table entry attribute for bgpIPv4BalanceTime"
	::={bgpIPv4BalanceTimeLevelEntry 2}

bgpIPv4BalanceTimeLevelMax OBJECT-TYPE
	SYNTAX	 CounterBasedGauge64
	MAX-ACCESS  read-only
	STATUS      current
	DESCRIPTION
	"Table entry attribute for bgpIPv4BalanceTime"
	::={bgpIPv4BalanceTimeLevelEntry 4}


bgpIPv4CompileTime	OBJECT IDENTIFIER ::={bgp 36}

bgpIPv4CompileTimeVal	OBJECT-TYPE
	SYNTAX	 CounterBasedGauge64
	MAX-ACCESS read-only
	STATUS current
	DESCRIPTION "Time to compile IPv4 tree to lookup table"

	::={bgpIPv4CompileTime 1}

bgpIPv4CompileTimeMax	OBJECT-TYPE
	SYNTAX	 CounterBasedGauge64
	MAX-ACCESS read-only
	STATUS current
	DESCRIPTION "Time to compile IPv4 tree to lookup table"

	::={bgpIPv4CompileTime 3}

bgpIPv4CompileTimeLevelTable OBJECT-TYPE
	SYNTAX      SEQUENCE OF BgpIPv4CompileTimeLevelEntry
	MAX-ACCESS  not-accessible
	STATUS      current
	DESCRIPTION
	"Table for bgpIPv4CompileTime"
	::={bgpIPv4CompileTime 4}

bgpIPv4CompileTimeLevelEntry OBJECT-TYPE
	SYNTAX      BgpIPv4CompileTimeLevelEntry
	MAX-ACCESS  not-accessible
	STATUS      current
	DESCRIPTION
	"Table entry for bgpIPv4CompileTime"
	INDEX { bgpIPv4CompileTimeLevelName }
	::={bgpIPv4CompileTimeLevelTable 1}

BgpIPv4CompileTimeLevelEntry ::=
	SEQUENCE {
		bgpIPv4CompileTimeLevelName	DisplayString,
		bgpIPv4CompileTimeLevelVal	CounterBasedGauge64,
		bgpIPv4CompileTimeLevelMax	CounterBasedGauge64
	}

bgpIPv4CompileTimeLevelName OBJECT-TYPE
	SYNTAX      DisplayString
	MAX-ACCESS  not-accessible
	STATUS      current
	DESCRIPTION
	"Table entry display string for bgpIPv4CompileTime"
	::={bgpIPv4CompileTimeLevelEntry 1}

bgpIPv4CompileTimeLevelVal OBJECT-TYPE
	SYNTAX	 CounterBasedGauge64
	MAX-ACCESS  read-only
	STATUS      current
	DESCRIPTION
	"Table entry attribute for bgpIPv4CompileTime"
	::={bgpIPv4CompileTimeLevelEntry 2}

bgpIPv4CompileTimeLevelMax OBJECT-TYPE
	SYNTAX	 CounterBasedGauge64
	MAX-ACCESS  read-only
	STATUS      current
	DESCRIPTION
	"Table entry attribute for bgpIPv4CompileTime"
	::={bgpIPv4CompileTimeLevelEntry 4}


bgpIPv4SendTime	OBJECT IDENTIFIER ::={bgp 37}

bgpIPv4SendTimeVal	OBJECT-TYPE
	SYNTAX	 CounterBasedGauge64
	MAX-ACCESS read-only
	STATUS current
	DESCRIPTION "Time to send IPv4 lookup table to engine"

	::={bgpIPv4SendTime 1}

bgpIPv4SendTimeMax	OBJECT-TYPE
	SYNTAX	 CounterBasedGauge64
	MAX-ACCESS read-only
	STATUS current
	DESCRIPTION "Time to send IPv4 lookup table to engine"

	::={bgpIPv4SendTime 3}

bgpIPv4SendTimeLevelTable OBJECT-TYPE
	SYNTAX      SEQUENCE OF BgpIPv4SendTimeLevelEntry
	MAX-ACCESS  not-accessible
	STATUS      current
	DESCRIPTION
	"Table for bgpIPv4SendTime"
	::={bgpIPv4SendTime 4}

bgpIPv4SendTimeLevelEntry OBJECT-TYPE
	SYNTAX      BgpIPv4SendTimeLevelEntry
	MAX-ACCESS  not-accessible
	STATUS      current
	DESCRIPTION
	"Table entry for bgpIPv4SendTime"
	INDEX { bgpIPv4SendTimeLevelName }
	::={bgpIPv4SendTimeLevelTable 1}

BgpIPv4SendTimeLevelEntry ::=
	SEQUENCE {
		bgpIPv4SendTimeLevelName	DisplayString,
		bgpIPv4SendTimeLevelVal	CounterBasedGauge64,
		bgpIPv4SendTimeLevelMax	CounterBasedGauge64
	}

bgpIPv4SendTimeLevelName OBJECT-TYPE
	SYNTAX      DisplayString
	MAX-ACCESS  not-accessible
	STATUS      current
	DESCRIPTION
	"Table entry display string for bgpIPv4SendTime"
	::={bgpIPv4SendTimeLevelEntry 1}

bgpIPv4SendTimeLevelVal OBJECT-TYPE
	SYNTAX	 CounterBasedGauge64
	MAX-ACCESS  read-only
	STATUS      current
	DESCRIPTION
	"Table entry attribute for bgpIPv4SendTime"
	::={bgpIPv4SendTimeLevelEntry 2}

bgpIPv4SendTimeLevelMax OBJECT-TYPE
	SYNTAX	 CounterBasedGauge64
	MAX-ACCESS  read-only
	STATUS      current
	DESCRIPTION
	"Table entry attribute for bgpIPv4SendTime"
	::={bgpIPv4SendTimeLevelEntry 4}


bgpIPv6Prefixes	OBJECT IDENTIFIER ::={bgp 41}

bgpIPv6PrefixesVal	OBJECT-TYPE
	SYNTAX	 CounterBasedGauge64
	MAX-ACCESS read-only
	STATUS current
	DESCRIPTION "Number of IPv6 prefixes/routes"

	::={bgpIPv6Prefixes 1}

bgpIPv6PrefixesMax	OBJECT-TYPE
	SYNTAX	 CounterBasedGauge64
	MAX-ACCESS read-only
	STATUS current
	DESCRIPTION "Number of IPv6 prefixes/routes"

	::={bgpIPv6Prefixes 3}

bgpIPv6PrefixesLevelTable OBJECT-TYPE
	SYNTAX      SEQUENCE OF BgpIPv6PrefixesLevelEntry
	MAX-ACCESS  not-accessible
	STATUS      current
	DESCRIPTION
	"Table for bgpIPv6Prefixes"
	::={bgpIPv6Prefixes 4}

bgpIPv6PrefixesLevelEntry OBJECT-TYPE
	SYNTAX      BgpIPv6PrefixesLevelEntry
	MAX-ACCESS  not-accessible
	STATUS      current
	DESCRIPTION
	"Table entry for bgpIPv6Prefixes"
	INDEX { bgpIPv6PrefixesLevelName }
	::={bgpIPv6PrefixesLevelTable 1}

BgpIPv6PrefixesLevelEntry ::=
	SEQUENCE {
		bgpIPv6PrefixesLevelName	DisplayString,
		bgpIPv6PrefixesLevelVal	CounterBasedGauge64,
		bgpIPv6PrefixesLevelMax	CounterBasedGauge64
	}

bgpIPv6PrefixesLevelName OBJECT-TYPE
	SYNTAX      DisplayString
	MAX-ACCESS  not-accessible
	STATUS      current
	DESCRIPTION
	"Table entry display string for bgpIPv6Prefixes"
	::={bgpIPv6PrefixesLevelEntry 1}

bgpIPv6PrefixesLevelVal OBJECT-TYPE
	SYNTAX	 CounterBasedGauge64
	MAX-ACCESS  read-only
	STATUS      current
	DESCRIPTION
	"Table entry attribute for bgpIPv6Prefixes"
	::={bgpIPv6PrefixesLevelEntry 2}

bgpIPv6PrefixesLevelMax OBJECT-TYPE
	SYNTAX	 CounterBasedGauge64
	MAX-ACCESS  read-only
	STATUS      current
	DESCRIPTION
	"Table entry attribute for bgpIPv6Prefixes"
	::={bgpIPv6PrefixesLevelEntry 4}


bgpIPv6Announces	OBJECT IDENTIFIER ::={bgp 42}

bgpIPv6AnnouncesVal	OBJECT-TYPE
	SYNTAX	 CounterBasedGauge64
	MAX-ACCESS read-only
	STATUS current
	DESCRIPTION "Total count of IPv6 announced prefixes/routes"

	::={bgpIPv6Announces 1}

bgpIPv6AnnouncesMax	OBJECT-TYPE
	SYNTAX	 CounterBasedGauge64
	MAX-ACCESS read-only
	STATUS current
	DESCRIPTION "Total count of IPv6 announced prefixes/routes"

	::={bgpIPv6Announces 3}

bgpIPv6AnnouncesLevelTable OBJECT-TYPE
	SYNTAX      SEQUENCE OF BgpIPv6AnnouncesLevelEntry
	MAX-ACCESS  not-accessible
	STATUS      current
	DESCRIPTION
	"Table for bgpIPv6Announces"
	::={bgpIPv6Announces 4}

bgpIPv6AnnouncesLevelEntry OBJECT-TYPE
	SYNTAX      BgpIPv6AnnouncesLevelEntry
	MAX-ACCESS  not-accessible
	STATUS      current
	DESCRIPTION
	"Table entry for bgpIPv6Announces"
	INDEX { bgpIPv6AnnouncesLevelName }
	::={bgpIPv6AnnouncesLevelTable 1}

BgpIPv6AnnouncesLevelEntry ::=
	SEQUENCE {
		bgpIPv6AnnouncesLevelName	DisplayString,
		bgpIPv6AnnouncesLevelVal	CounterBasedGauge64,
		bgpIPv6AnnouncesLevelMax	CounterBasedGauge64
	}

bgpIPv6AnnouncesLevelName OBJECT-TYPE
	SYNTAX      DisplayString
	MAX-ACCESS  not-accessible
	STATUS      current
	DESCRIPTION
	"Table entry display string for bgpIPv6Announces"
	::={bgpIPv6AnnouncesLevelEntry 1}

bgpIPv6AnnouncesLevelVal OBJECT-TYPE
	SYNTAX	 CounterBasedGauge64
	MAX-ACCESS  read-only
	STATUS      current
	DESCRIPTION
	"Table entry attribute for bgpIPv6Announces"
	::={bgpIPv6AnnouncesLevelEntry 2}

bgpIPv6AnnouncesLevelMax OBJECT-TYPE
	SYNTAX	 CounterBasedGauge64
	MAX-ACCESS  read-only
	STATUS      current
	DESCRIPTION
	"Table entry attribute for bgpIPv6Announces"
	::={bgpIPv6AnnouncesLevelEntry 4}


bgpIPv6Withdraws	OBJECT IDENTIFIER ::={bgp 43}

bgpIPv6WithdrawsVal	OBJECT-TYPE
	SYNTAX	 CounterBasedGauge64
	MAX-ACCESS read-only
	STATUS current
	DESCRIPTION "Total count of IPv6 withdrawn prefixes/routes"

	::={bgpIPv6Withdraws 1}

bgpIPv6WithdrawsMax	OBJECT-TYPE
	SYNTAX	 CounterBasedGauge64
	MAX-ACCESS read-only
	STATUS current
	DESCRIPTION "Total count of IPv6 withdrawn prefixes/routes"

	::={bgpIPv6Withdraws 3}

bgpIPv6WithdrawsLevelTable OBJECT-TYPE
	SYNTAX      SEQUENCE OF BgpIPv6WithdrawsLevelEntry
	MAX-ACCESS  not-accessible
	STATUS      current
	DESCRIPTION
	"Table for bgpIPv6Withdraws"
	::={bgpIPv6Withdraws 4}

bgpIPv6WithdrawsLevelEntry OBJECT-TYPE
	SYNTAX      BgpIPv6WithdrawsLevelEntry
	MAX-ACCESS  not-accessible
	STATUS      current
	DESCRIPTION
	"Table entry for bgpIPv6Withdraws"
	INDEX { bgpIPv6WithdrawsLevelName }
	::={bgpIPv6WithdrawsLevelTable 1}

BgpIPv6WithdrawsLevelEntry ::=
	SEQUENCE {
		bgpIPv6WithdrawsLevelName	DisplayString,
		bgpIPv6WithdrawsLevelVal	CounterBasedGauge64,
		bgpIPv6WithdrawsLevelMax	CounterBasedGauge64
	}

bgpIPv6WithdrawsLevelName OBJECT-TYPE
	SYNTAX      DisplayString
	MAX-ACCESS  not-accessible
	STATUS      current
	DESCRIPTION
	"Table entry display string for bgpIPv6Withdraws"
	::={bgpIPv6WithdrawsLevelEntry 1}

bgpIPv6WithdrawsLevelVal OBJECT-TYPE
	SYNTAX	 CounterBasedGauge64
	MAX-ACCESS  read-only
	STATUS      current
	DESCRIPTION
	"Table entry attribute for bgpIPv6Withdraws"
	::={bgpIPv6WithdrawsLevelEntry 2}

bgpIPv6WithdrawsLevelMax OBJECT-TYPE
	SYNTAX	 CounterBasedGauge64
	MAX-ACCESS  read-only
	STATUS      current
	DESCRIPTION
	"Table entry attribute for bgpIPv6Withdraws"
	::={bgpIPv6WithdrawsLevelEntry 4}


bgpIPv6Replaces	OBJECT IDENTIFIER ::={bgp 44}

bgpIPv6ReplacesVal	OBJECT-TYPE
	SYNTAX	 CounterBasedGauge64
	MAX-ACCESS read-only
	STATUS current
	DESCRIPTION "Total count of IPv6 announces without withdraw, replacing an already existing prefix/route"

	::={bgpIPv6Replaces 1}

bgpIPv6ReplacesMax	OBJECT-TYPE
	SYNTAX	 CounterBasedGauge64
	MAX-ACCESS read-only
	STATUS current
	DESCRIPTION "Total count of IPv6 announces without withdraw, replacing an already existing prefix/route"

	::={bgpIPv6Replaces 3}

bgpIPv6ReplacesLevelTable OBJECT-TYPE
	SYNTAX      SEQUENCE OF BgpIPv6ReplacesLevelEntry
	MAX-ACCESS  not-accessible
	STATUS      current
	DESCRIPTION
	"Table for bgpIPv6Replaces"
	::={bgpIPv6Replaces 4}

bgpIPv6ReplacesLevelEntry OBJECT-TYPE
	SYNTAX      BgpIPv6ReplacesLevelEntry
	MAX-ACCESS  not-accessible
	STATUS      current
	DESCRIPTION
	"Table entry for bgpIPv6Replaces"
	INDEX { bgpIPv6ReplacesLevelName }
	::={bgpIPv6ReplacesLevelTable 1}

BgpIPv6ReplacesLevelEntry ::=
	SEQUENCE {
		bgpIPv6ReplacesLevelName	DisplayString,
		bgpIPv6ReplacesLevelVal	CounterBasedGauge64,
		bgpIPv6ReplacesLevelMax	CounterBasedGauge64
	}

bgpIPv6ReplacesLevelName OBJECT-TYPE
	SYNTAX      DisplayString
	MAX-ACCESS  not-accessible
	STATUS      current
	DESCRIPTION
	"Table entry display string for bgpIPv6Replaces"
	::={bgpIPv6ReplacesLevelEntry 1}

bgpIPv6ReplacesLevelVal OBJECT-TYPE
	SYNTAX	 CounterBasedGauge64
	MAX-ACCESS  read-only
	STATUS      current
	DESCRIPTION
	"Table entry attribute for bgpIPv6Replaces"
	::={bgpIPv6ReplacesLevelEntry 2}

bgpIPv6ReplacesLevelMax OBJECT-TYPE
	SYNTAX	 CounterBasedGauge64
	MAX-ACCESS  read-only
	STATUS      current
	DESCRIPTION
	"Table entry attribute for bgpIPv6Replaces"
	::={bgpIPv6ReplacesLevelEntry 4}


bgpIPv6BalanceTime	OBJECT IDENTIFIER ::={bgp 45}

bgpIPv6BalanceTimeVal	OBJECT-TYPE
	SYNTAX	 CounterBasedGauge64
	MAX-ACCESS read-only
	STATUS current
	DESCRIPTION "Time to balance IPv6 tree"

	::={bgpIPv6BalanceTime 1}

bgpIPv6BalanceTimeMax	OBJECT-TYPE
	SYNTAX	 CounterBasedGauge64
	MAX-ACCESS read-only
	STATUS current
	DESCRIPTION "Time to balance IPv6 tree"

	::={bgpIPv6BalanceTime 3}

bgpIPv6BalanceTimeLevelTable OBJECT-TYPE
	SYNTAX      SEQUENCE OF BgpIPv6BalanceTimeLevelEntry
	MAX-ACCESS  not-accessible
	STATUS      current
	DESCRIPTION
	"Table for bgpIPv6BalanceTime"
	::={bgpIPv6BalanceTime 4}

bgpIPv6BalanceTimeLevelEntry OBJECT-TYPE
	SYNTAX      BgpIPv6BalanceTimeLevelEntry
	MAX-ACCESS  not-accessible
	STATUS      current
	DESCRIPTION
	"Table entry for bgpIPv6BalanceTime"
	INDEX { bgpIPv6BalanceTimeLevelName }
	::={bgpIPv6BalanceTimeLevelTable 1}

BgpIPv6BalanceTimeLevelEntry ::=
	SEQUENCE {
		bgpIPv6BalanceTimeLevelName	DisplayString,
		bgpIPv6BalanceTimeLevelVal	CounterBasedGauge64,
		bgpIPv6BalanceTimeLevelMax	CounterBasedGauge64
	}

bgpIPv6BalanceTimeLevelName OBJECT-TYPE
	SYNTAX      DisplayString
	MAX-ACCESS  not-accessible
	STATUS      current
	DESCRIPTION
	"Table entry display string for bgpIPv6BalanceTime"
	::={bgpIPv6BalanceTimeLevelEntry 1}

bgpIPv6BalanceTimeLevelVal OBJECT-TYPE
	SYNTAX	 CounterBasedGauge64
	MAX-ACCESS  read-only
	STATUS      current
	DESCRIPTION
	"Table entry attribute for bgpIPv6BalanceTime"
	::={bgpIPv6BalanceTimeLevelEntry 2}

bgpIPv6BalanceTimeLevelMax OBJECT-TYPE
	SYNTAX	 CounterBasedGauge64
	MAX-ACCESS  read-only
	STATUS      current
	DESCRIPTION
	"Table entry attribute for bgpIPv6BalanceTime"
	::={bgpIPv6BalanceTimeLevelEntry 4}


bgpIPv6CompileTime	OBJECT IDENTIFIER ::={bgp 46}

bgpIPv6CompileTimeVal	OBJECT-TYPE
	SYNTAX	 CounterBasedGauge64
	MAX-ACCESS read-only
	STATUS current
	DESCRIPTION "Time to compile IPv6 tree to lookup table"

	::={bgpIPv6CompileTime 1}

bgpIPv6CompileTimeMax	OBJECT-TYPE
	SYNTAX	 CounterBasedGauge64
	MAX-ACCESS read-only
	STATUS current
	DESCRIPTION "Time to compile IPv6 tree to lookup table"

	::={bgpIPv6CompileTime 3}

bgpIPv6CompileTimeLevelTable OBJECT-TYPE
	SYNTAX      SEQUENCE OF BgpIPv6CompileTimeLevelEntry
	MAX-ACCESS  not-accessible
	STATUS      current
	DESCRIPTION
	"Table for bgpIPv6CompileTime"
	::={bgpIPv6CompileTime 4}

bgpIPv6CompileTimeLevelEntry OBJECT-TYPE
	SYNTAX      BgpIPv6CompileTimeLevelEntry
	MAX-ACCESS  not-accessible
	STATUS      current
	DESCRIPTION
	"Table entry for bgpIPv6CompileTime"
	INDEX { bgpIPv6CompileTimeLevelName }
	::={bgpIPv6CompileTimeLevelTable 1}

BgpIPv6CompileTimeLevelEntry ::=
	SEQUENCE {
		bgpIPv6CompileTimeLevelName	DisplayString,
		bgpIPv6CompileTimeLevelVal	CounterBasedGauge64,
		bgpIPv6CompileTimeLevelMax	CounterBasedGauge64
	}

bgpIPv6CompileTimeLevelName OBJECT-TYPE
	SYNTAX      DisplayString
	MAX-ACCESS  not-accessible
	STATUS      current
	DESCRIPTION
	"Table entry display string for bgpIPv6CompileTime"
	::={bgpIPv6CompileTimeLevelEntry 1}

bgpIPv6CompileTimeLevelVal OBJECT-TYPE
	SYNTAX	 CounterBasedGauge64
	MAX-ACCESS  read-only
	STATUS      current
	DESCRIPTION
	"Table entry attribute for bgpIPv6CompileTime"
	::={bgpIPv6CompileTimeLevelEntry 2}

bgpIPv6CompileTimeLevelMax OBJECT-TYPE
	SYNTAX	 CounterBasedGauge64
	MAX-ACCESS  read-only
	STATUS      current
	DESCRIPTION
	"Table entry attribute for bgpIPv6CompileTime"
	::={bgpIPv6CompileTimeLevelEntry 4}


bgpIPv6SendTime	OBJECT IDENTIFIER ::={bgp 47}

bgpIPv6SendTimeVal	OBJECT-TYPE
	SYNTAX	 CounterBasedGauge64
	MAX-ACCESS read-only
	STATUS current
	DESCRIPTION "Time to send IPv6 lookup table to engine"

	::={bgpIPv6SendTime 1}

bgpIPv6SendTimeMax	OBJECT-TYPE
	SYNTAX	 CounterBasedGauge64
	MAX-ACCESS read-only
	STATUS current
	DESCRIPTION "Time to send IPv6 lookup table to engine"

	::={bgpIPv6SendTime 3}

bgpIPv6SendTimeLevelTable OBJECT-TYPE
	SYNTAX      SEQUENCE OF BgpIPv6SendTimeLevelEntry
	MAX-ACCESS  not-accessible
	STATUS      current
	DESCRIPTION
	"Table for bgpIPv6SendTime"
	::={bgpIPv6SendTime 4}

bgpIPv6SendTimeLevelEntry OBJECT-TYPE
	SYNTAX      BgpIPv6SendTimeLevelEntry
	MAX-ACCESS  not-accessible
	STATUS      current
	DESCRIPTION
	"Table entry for bgpIPv6SendTime"
	INDEX { bgpIPv6SendTimeLevelName }
	::={bgpIPv6SendTimeLevelTable 1}

BgpIPv6SendTimeLevelEntry ::=
	SEQUENCE {
		bgpIPv6SendTimeLevelName	DisplayString,
		bgpIPv6SendTimeLevelVal	CounterBasedGauge64,
		bgpIPv6SendTimeLevelMax	CounterBasedGauge64
	}

bgpIPv6SendTimeLevelName OBJECT-TYPE
	SYNTAX      DisplayString
	MAX-ACCESS  not-accessible
	STATUS      current
	DESCRIPTION
	"Table entry display string for bgpIPv6SendTime"
	::={bgpIPv6SendTimeLevelEntry 1}

bgpIPv6SendTimeLevelVal OBJECT-TYPE
	SYNTAX	 CounterBasedGauge64
	MAX-ACCESS  read-only
	STATUS      current
	DESCRIPTION
	"Table entry attribute for bgpIPv6SendTime"
	::={bgpIPv6SendTimeLevelEntry 2}

bgpIPv6SendTimeLevelMax OBJECT-TYPE
	SYNTAX	 CounterBasedGauge64
	MAX-ACCESS  read-only
	STATUS      current
	DESCRIPTION
	"Table entry attribute for bgpIPv6SendTime"
	::={bgpIPv6SendTimeLevelEntry 4}


qsync	OBJECT IDENTIFIER ::={sysdiag 123}

qsyncIUpdates	OBJECT IDENTIFIER ::={qsync 1}

qsyncIUpdatesVal	OBJECT-TYPE
	SYNTAX	 Counter64
	MAX-ACCESS read-only
	STATUS current
	DESCRIPTION "Updates received from reapers"

	::={qsyncIUpdates 1}

qsyncIUpdatesMom	OBJECT-TYPE
	SYNTAX	 CounterBasedGauge64
	MAX-ACCESS read-only
	STATUS current
	DESCRIPTION "Updates received from reapers"

	::={qsyncIUpdates 2}

qsyncIUpdatesMax	OBJECT-TYPE
	SYNTAX	 CounterBasedGauge64
	MAX-ACCESS read-only
	STATUS current
	DESCRIPTION "Updates received from reapers"

	::={qsyncIUpdates 3}

qsyncIUpdatesLevelTable OBJECT-TYPE
	SYNTAX      SEQUENCE OF QsyncIUpdatesLevelEntry
	MAX-ACCESS  not-accessible
	STATUS      current
	DESCRIPTION
	"Table for qsyncIUpdates"
	::={qsyncIUpdates 4}

qsyncIUpdatesLevelEntry OBJECT-TYPE
	SYNTAX      QsyncIUpdatesLevelEntry
	MAX-ACCESS  not-accessible
	STATUS      current
	DESCRIPTION
	"Table entry for qsyncIUpdates"
	INDEX { qsyncIUpdatesLevelName }
	::={qsyncIUpdatesLevelTable 1}

QsyncIUpdatesLevelEntry ::=
	SEQUENCE {
		qsyncIUpdatesLevelName	DisplayString,
		qsyncIUpdatesLevelVal	Counter64,
		qsyncIUpdatesLevelMom	CounterBasedGauge64,
		qsyncIUpdatesLevelMax	CounterBasedGauge64
	}

qsyncIUpdatesLevelName OBJECT-TYPE
	SYNTAX      DisplayString
	MAX-ACCESS  not-accessible
	STATUS      current
	DESCRIPTION
	"Table entry display string for qsyncIUpdates"
	::={qsyncIUpdatesLevelEntry 1}

qsyncIUpdatesLevelVal OBJECT-TYPE
	SYNTAX	 Counter64
	MAX-ACCESS  read-only
	STATUS      current
	DESCRIPTION
	"Table entry attribute for qsyncIUpdates"
	::={qsyncIUpdatesLevelEntry 2}

qsyncIUpdatesLevelMom OBJECT-TYPE
	SYNTAX	 CounterBasedGauge64
	MAX-ACCESS  read-only
	STATUS      current
	DESCRIPTION
	"Table entry attribute for qsyncIUpdates"
	::={qsyncIUpdatesLevelEntry 3}

qsyncIUpdatesLevelMax OBJECT-TYPE
	SYNTAX	 CounterBasedGauge64
	MAX-ACCESS  read-only
	STATUS      current
	DESCRIPTION
	"Table entry attribute for qsyncIUpdates"
	::={qsyncIUpdatesLevelEntry 4}


qsyncIUpdatesOldRuleset	OBJECT IDENTIFIER ::={qsync 2}

qsyncIUpdatesOldRulesetVal	OBJECT-TYPE
	SYNTAX	 Counter64
	MAX-ACCESS read-only
	STATUS current
	DESCRIPTION "Updates received from reapers with old ruleset"

	::={qsyncIUpdatesOldRuleset 1}

qsyncIUpdatesOldRulesetMom	OBJECT-TYPE
	SYNTAX	 CounterBasedGauge64
	MAX-ACCESS read-only
	STATUS current
	DESCRIPTION "Updates received from reapers with old ruleset"

	::={qsyncIUpdatesOldRuleset 2}

qsyncIUpdatesOldRulesetMax	OBJECT-TYPE
	SYNTAX	 CounterBasedGauge64
	MAX-ACCESS read-only
	STATUS current
	DESCRIPTION "Updates received from reapers with old ruleset"

	::={qsyncIUpdatesOldRuleset 3}

qsyncIUpdatesOldRulesetLevelTable OBJECT-TYPE
	SYNTAX      SEQUENCE OF QsyncIUpdatesOldRulesetLevelEntry
	MAX-ACCESS  not-accessible
	STATUS      current
	DESCRIPTION
	"Table for qsyncIUpdatesOldRuleset"
	::={qsyncIUpdatesOldRuleset 4}

qsyncIUpdatesOldRulesetLevelEntry OBJECT-TYPE
	SYNTAX      QsyncIUpdatesOldRulesetLevelEntry
	MAX-ACCESS  not-accessible
	STATUS      current
	DESCRIPTION
	"Table entry for qsyncIUpdatesOldRuleset"
	INDEX { qsyncIUpdatesOldRulesetLevelName }
	::={qsyncIUpdatesOldRulesetLevelTable 1}

QsyncIUpdatesOldRulesetLevelEntry ::=
	SEQUENCE {
		qsyncIUpdatesOldRulesetLevelName	DisplayString,
		qsyncIUpdatesOldRulesetLevelVal	Counter64,
		qsyncIUpdatesOldRulesetLevelMom	CounterBasedGauge64,
		qsyncIUpdatesOldRulesetLevelMax	CounterBasedGauge64
	}

qsyncIUpdatesOldRulesetLevelName OBJECT-TYPE
	SYNTAX      DisplayString
	MAX-ACCESS  not-accessible
	STATUS      current
	DESCRIPTION
	"Table entry display string for qsyncIUpdatesOldRuleset"
	::={qsyncIUpdatesOldRulesetLevelEntry 1}

qsyncIUpdatesOldRulesetLevelVal OBJECT-TYPE
	SYNTAX	 Counter64
	MAX-ACCESS  read-only
	STATUS      current
	DESCRIPTION
	"Table entry attribute for qsyncIUpdatesOldRuleset"
	::={qsyncIUpdatesOldRulesetLevelEntry 2}

qsyncIUpdatesOldRulesetLevelMom OBJECT-TYPE
	SYNTAX	 CounterBasedGauge64
	MAX-ACCESS  read-only
	STATUS      current
	DESCRIPTION
	"Table entry attribute for qsyncIUpdatesOldRuleset"
	::={qsyncIUpdatesOldRulesetLevelEntry 3}

qsyncIUpdatesOldRulesetLevelMax OBJECT-TYPE
	SYNTAX	 CounterBasedGauge64
	MAX-ACCESS  read-only
	STATUS      current
	DESCRIPTION
	"Table entry attribute for qsyncIUpdatesOldRuleset"
	::={qsyncIUpdatesOldRulesetLevelEntry 4}


qsyncIUpdatesUnknownObject	OBJECT IDENTIFIER ::={qsync 3}

qsyncIUpdatesUnknownObjectVal	OBJECT-TYPE
	SYNTAX	 Counter64
	MAX-ACCESS read-only
	STATUS current
	DESCRIPTION "Updates received for unknown object"

	::={qsyncIUpdatesUnknownObject 1}

qsyncIUpdatesUnknownObjectMom	OBJECT-TYPE
	SYNTAX	 CounterBasedGauge64
	MAX-ACCESS read-only
	STATUS current
	DESCRIPTION "Updates received for unknown object"

	::={qsyncIUpdatesUnknownObject 2}

qsyncIUpdatesUnknownObjectMax	OBJECT-TYPE
	SYNTAX	 CounterBasedGauge64
	MAX-ACCESS read-only
	STATUS current
	DESCRIPTION "Updates received for unknown object"

	::={qsyncIUpdatesUnknownObject 3}

qsyncIUpdatesUnknownObjectLevelTable OBJECT-TYPE
	SYNTAX      SEQUENCE OF QsyncIUpdatesUnknownObjectLevelEntry
	MAX-ACCESS  not-accessible
	STATUS      current
	DESCRIPTION
	"Table for qsyncIUpdatesUnknownObject"
	::={qsyncIUpdatesUnknownObject 4}

qsyncIUpdatesUnknownObjectLevelEntry OBJECT-TYPE
	SYNTAX      QsyncIUpdatesUnknownObjectLevelEntry
	MAX-ACCESS  not-accessible
	STATUS      current
	DESCRIPTION
	"Table entry for qsyncIUpdatesUnknownObject"
	INDEX { qsyncIUpdatesUnknownObjectLevelName }
	::={qsyncIUpdatesUnknownObjectLevelTable 1}

QsyncIUpdatesUnknownObjectLevelEntry ::=
	SEQUENCE {
		qsyncIUpdatesUnknownObjectLevelName	DisplayString,
		qsyncIUpdatesUnknownObjectLevelVal	Counter64,
		qsyncIUpdatesUnknownObjectLevelMom	CounterBasedGauge64,
		qsyncIUpdatesUnknownObjectLevelMax	CounterBasedGauge64
	}

qsyncIUpdatesUnknownObjectLevelName OBJECT-TYPE
	SYNTAX      DisplayString
	MAX-ACCESS  not-accessible
	STATUS      current
	DESCRIPTION
	"Table entry display string for qsyncIUpdatesUnknownObject"
	::={qsyncIUpdatesUnknownObjectLevelEntry 1}

qsyncIUpdatesUnknownObjectLevelVal OBJECT-TYPE
	SYNTAX	 Counter64
	MAX-ACCESS  read-only
	STATUS      current
	DESCRIPTION
	"Table entry attribute for qsyncIUpdatesUnknownObject"
	::={qsyncIUpdatesUnknownObjectLevelEntry 2}

qsyncIUpdatesUnknownObjectLevelMom OBJECT-TYPE
	SYNTAX	 CounterBasedGauge64
	MAX-ACCESS  read-only
	STATUS      current
	DESCRIPTION
	"Table entry attribute for qsyncIUpdatesUnknownObject"
	::={qsyncIUpdatesUnknownObjectLevelEntry 3}

qsyncIUpdatesUnknownObjectLevelMax OBJECT-TYPE
	SYNTAX	 CounterBasedGauge64
	MAX-ACCESS  read-only
	STATUS      current
	DESCRIPTION
	"Table entry attribute for qsyncIUpdatesUnknownObject"
	::={qsyncIUpdatesUnknownObjectLevelEntry 4}


qsyncIReaperSplitsCreated	OBJECT IDENTIFIER ::={qsync 4}

qsyncIReaperSplitsCreatedVal	OBJECT-TYPE
	SYNTAX	 Counter64
	MAX-ACCESS read-only
	STATUS current
	DESCRIPTION "Split entries created (reaper)"

	::={qsyncIReaperSplitsCreated 1}

qsyncIReaperSplitsCreatedMom	OBJECT-TYPE
	SYNTAX	 CounterBasedGauge64
	MAX-ACCESS read-only
	STATUS current
	DESCRIPTION "Split entries created (reaper)"

	::={qsyncIReaperSplitsCreated 2}

qsyncIReaperSplitsCreatedMax	OBJECT-TYPE
	SYNTAX	 CounterBasedGauge64
	MAX-ACCESS read-only
	STATUS current
	DESCRIPTION "Split entries created (reaper)"

	::={qsyncIReaperSplitsCreated 3}

qsyncIReaperSplitsCreatedLevelTable OBJECT-TYPE
	SYNTAX      SEQUENCE OF QsyncIReaperSplitsCreatedLevelEntry
	MAX-ACCESS  not-accessible
	STATUS      current
	DESCRIPTION
	"Table for qsyncIReaperSplitsCreated"
	::={qsyncIReaperSplitsCreated 4}

qsyncIReaperSplitsCreatedLevelEntry OBJECT-TYPE
	SYNTAX      QsyncIReaperSplitsCreatedLevelEntry
	MAX-ACCESS  not-accessible
	STATUS      current
	DESCRIPTION
	"Table entry for qsyncIReaperSplitsCreated"
	INDEX { qsyncIReaperSplitsCreatedLevelName }
	::={qsyncIReaperSplitsCreatedLevelTable 1}

QsyncIReaperSplitsCreatedLevelEntry ::=
	SEQUENCE {
		qsyncIReaperSplitsCreatedLevelName	DisplayString,
		qsyncIReaperSplitsCreatedLevelVal	Counter64,
		qsyncIReaperSplitsCreatedLevelMom	CounterBasedGauge64,
		qsyncIReaperSplitsCreatedLevelMax	CounterBasedGauge64
	}

qsyncIReaperSplitsCreatedLevelName OBJECT-TYPE
	SYNTAX      DisplayString
	MAX-ACCESS  not-accessible
	STATUS      current
	DESCRIPTION
	"Table entry display string for qsyncIReaperSplitsCreated"
	::={qsyncIReaperSplitsCreatedLevelEntry 1}

qsyncIReaperSplitsCreatedLevelVal OBJECT-TYPE
	SYNTAX	 Counter64
	MAX-ACCESS  read-only
	STATUS      current
	DESCRIPTION
	"Table entry attribute for qsyncIReaperSplitsCreated"
	::={qsyncIReaperSplitsCreatedLevelEntry 2}

qsyncIReaperSplitsCreatedLevelMom OBJECT-TYPE
	SYNTAX	 CounterBasedGauge64
	MAX-ACCESS  read-only
	STATUS      current
	DESCRIPTION
	"Table entry attribute for qsyncIReaperSplitsCreated"
	::={qsyncIReaperSplitsCreatedLevelEntry 3}

qsyncIReaperSplitsCreatedLevelMax OBJECT-TYPE
	SYNTAX	 CounterBasedGauge64
	MAX-ACCESS  read-only
	STATUS      current
	DESCRIPTION
	"Table entry attribute for qsyncIReaperSplitsCreated"
	::={qsyncIReaperSplitsCreatedLevelEntry 4}


qsyncIReaperSplitsActive	OBJECT IDENTIFIER ::={qsync 5}

qsyncIReaperSplitsActiveVal	OBJECT-TYPE
	SYNTAX	 CounterBasedGauge64
	MAX-ACCESS read-only
	STATUS current
	DESCRIPTION "Split entries active (reaper)"

	::={qsyncIReaperSplitsActive 1}

qsyncIReaperSplitsActiveMax	OBJECT-TYPE
	SYNTAX	 CounterBasedGauge64
	MAX-ACCESS read-only
	STATUS current
	DESCRIPTION "Split entries active (reaper)"

	::={qsyncIReaperSplitsActive 3}

qsyncIReaperSplitsActiveLevelTable OBJECT-TYPE
	SYNTAX      SEQUENCE OF QsyncIReaperSplitsActiveLevelEntry
	MAX-ACCESS  not-accessible
	STATUS      current
	DESCRIPTION
	"Table for qsyncIReaperSplitsActive"
	::={qsyncIReaperSplitsActive 4}

qsyncIReaperSplitsActiveLevelEntry OBJECT-TYPE
	SYNTAX      QsyncIReaperSplitsActiveLevelEntry
	MAX-ACCESS  not-accessible
	STATUS      current
	DESCRIPTION
	"Table entry for qsyncIReaperSplitsActive"
	INDEX { qsyncIReaperSplitsActiveLevelName }
	::={qsyncIReaperSplitsActiveLevelTable 1}

QsyncIReaperSplitsActiveLevelEntry ::=
	SEQUENCE {
		qsyncIReaperSplitsActiveLevelName	DisplayString,
		qsyncIReaperSplitsActiveLevelVal	CounterBasedGauge64,
		qsyncIReaperSplitsActiveLevelMax	CounterBasedGauge64
	}

qsyncIReaperSplitsActiveLevelName OBJECT-TYPE
	SYNTAX      DisplayString
	MAX-ACCESS  not-accessible
	STATUS      current
	DESCRIPTION
	"Table entry display string for qsyncIReaperSplitsActive"
	::={qsyncIReaperSplitsActiveLevelEntry 1}

qsyncIReaperSplitsActiveLevelVal OBJECT-TYPE
	SYNTAX	 CounterBasedGauge64
	MAX-ACCESS  read-only
	STATUS      current
	DESCRIPTION
	"Table entry attribute for qsyncIReaperSplitsActive"
	::={qsyncIReaperSplitsActiveLevelEntry 2}

qsyncIReaperSplitsActiveLevelMax OBJECT-TYPE
	SYNTAX	 CounterBasedGauge64
	MAX-ACCESS  read-only
	STATUS      current
	DESCRIPTION
	"Table entry attribute for qsyncIReaperSplitsActive"
	::={qsyncIReaperSplitsActiveLevelEntry 4}


qsyncISumFreelistSize	OBJECT IDENTIFIER ::={qsync 6}

qsyncISumFreelistSizeVal	OBJECT-TYPE
	SYNTAX	 CounterBasedGauge64
	MAX-ACCESS read-only
	STATUS current
	DESCRIPTION "Split entries on free list (sum)"

	::={qsyncISumFreelistSize 1}

qsyncISumFreelistSizeMax	OBJECT-TYPE
	SYNTAX	 CounterBasedGauge64
	MAX-ACCESS read-only
	STATUS current
	DESCRIPTION "Split entries on free list (sum)"

	::={qsyncISumFreelistSize 3}

qsyncISumFreelistSizeLevelTable OBJECT-TYPE
	SYNTAX      SEQUENCE OF QsyncISumFreelistSizeLevelEntry
	MAX-ACCESS  not-accessible
	STATUS      current
	DESCRIPTION
	"Table for qsyncISumFreelistSize"
	::={qsyncISumFreelistSize 4}

qsyncISumFreelistSizeLevelEntry OBJECT-TYPE
	SYNTAX      QsyncISumFreelistSizeLevelEntry
	MAX-ACCESS  not-accessible
	STATUS      current
	DESCRIPTION
	"Table entry for qsyncISumFreelistSize"
	INDEX { qsyncISumFreelistSizeLevelName }
	::={qsyncISumFreelistSizeLevelTable 1}

QsyncISumFreelistSizeLevelEntry ::=
	SEQUENCE {
		qsyncISumFreelistSizeLevelName	DisplayString,
		qsyncISumFreelistSizeLevelVal	CounterBasedGauge64,
		qsyncISumFreelistSizeLevelMax	CounterBasedGauge64
	}

qsyncISumFreelistSizeLevelName OBJECT-TYPE
	SYNTAX      DisplayString
	MAX-ACCESS  not-accessible
	STATUS      current
	DESCRIPTION
	"Table entry display string for qsyncISumFreelistSize"
	::={qsyncISumFreelistSizeLevelEntry 1}

qsyncISumFreelistSizeLevelVal OBJECT-TYPE
	SYNTAX	 CounterBasedGauge64
	MAX-ACCESS  read-only
	STATUS      current
	DESCRIPTION
	"Table entry attribute for qsyncISumFreelistSize"
	::={qsyncISumFreelistSizeLevelEntry 2}

qsyncISumFreelistSizeLevelMax OBJECT-TYPE
	SYNTAX	 CounterBasedGauge64
	MAX-ACCESS  read-only
	STATUS      current
	DESCRIPTION
	"Table entry attribute for qsyncISumFreelistSize"
	::={qsyncISumFreelistSizeLevelEntry 4}


qsyncISumSplitsActive	OBJECT IDENTIFIER ::={qsync 7}

qsyncISumSplitsActiveVal	OBJECT-TYPE
	SYNTAX	 CounterBasedGauge64
	MAX-ACCESS read-only
	STATUS current
	DESCRIPTION "Split entries active (sum)"

	::={qsyncISumSplitsActive 1}

qsyncISumSplitsActiveMax	OBJECT-TYPE
	SYNTAX	 CounterBasedGauge64
	MAX-ACCESS read-only
	STATUS current
	DESCRIPTION "Split entries active (sum)"

	::={qsyncISumSplitsActive 3}

qsyncISumSplitsActiveLevelTable OBJECT-TYPE
	SYNTAX      SEQUENCE OF QsyncISumSplitsActiveLevelEntry
	MAX-ACCESS  not-accessible
	STATUS      current
	DESCRIPTION
	"Table for qsyncISumSplitsActive"
	::={qsyncISumSplitsActive 4}

qsyncISumSplitsActiveLevelEntry OBJECT-TYPE
	SYNTAX      QsyncISumSplitsActiveLevelEntry
	MAX-ACCESS  not-accessible
	STATUS      current
	DESCRIPTION
	"Table entry for qsyncISumSplitsActive"
	INDEX { qsyncISumSplitsActiveLevelName }
	::={qsyncISumSplitsActiveLevelTable 1}

QsyncISumSplitsActiveLevelEntry ::=
	SEQUENCE {
		qsyncISumSplitsActiveLevelName	DisplayString,
		qsyncISumSplitsActiveLevelVal	CounterBasedGauge64,
		qsyncISumSplitsActiveLevelMax	CounterBasedGauge64
	}

qsyncISumSplitsActiveLevelName OBJECT-TYPE
	SYNTAX      DisplayString
	MAX-ACCESS  not-accessible
	STATUS      current
	DESCRIPTION
	"Table entry display string for qsyncISumSplitsActive"
	::={qsyncISumSplitsActiveLevelEntry 1}

qsyncISumSplitsActiveLevelVal OBJECT-TYPE
	SYNTAX	 CounterBasedGauge64
	MAX-ACCESS  read-only
	STATUS      current
	DESCRIPTION
	"Table entry attribute for qsyncISumSplitsActive"
	::={qsyncISumSplitsActiveLevelEntry 2}

qsyncISumSplitsActiveLevelMax OBJECT-TYPE
	SYNTAX	 CounterBasedGauge64
	MAX-ACCESS  read-only
	STATUS      current
	DESCRIPTION
	"Table entry attribute for qsyncISumSplitsActive"
	::={qsyncISumSplitsActiveLevelEntry 4}


qsyncIAdjustmentsSent	OBJECT IDENTIFIER ::={qsync 8}

qsyncIAdjustmentsSentVal	OBJECT-TYPE
	SYNTAX	 Counter64
	MAX-ACCESS read-only
	STATUS current
	DESCRIPTION "Object adjustments sent"

	::={qsyncIAdjustmentsSent 1}

qsyncIAdjustmentsSentMom	OBJECT-TYPE
	SYNTAX	 CounterBasedGauge64
	MAX-ACCESS read-only
	STATUS current
	DESCRIPTION "Object adjustments sent"

	::={qsyncIAdjustmentsSent 2}

qsyncIAdjustmentsSentMax	OBJECT-TYPE
	SYNTAX	 CounterBasedGauge64
	MAX-ACCESS read-only
	STATUS current
	DESCRIPTION "Object adjustments sent"

	::={qsyncIAdjustmentsSent 3}

qsyncIAdjustmentsSentLevelTable OBJECT-TYPE
	SYNTAX      SEQUENCE OF QsyncIAdjustmentsSentLevelEntry
	MAX-ACCESS  not-accessible
	STATUS      current
	DESCRIPTION
	"Table for qsyncIAdjustmentsSent"
	::={qsyncIAdjustmentsSent 4}

qsyncIAdjustmentsSentLevelEntry OBJECT-TYPE
	SYNTAX      QsyncIAdjustmentsSentLevelEntry
	MAX-ACCESS  not-accessible
	STATUS      current
	DESCRIPTION
	"Table entry for qsyncIAdjustmentsSent"
	INDEX { qsyncIAdjustmentsSentLevelName }
	::={qsyncIAdjustmentsSentLevelTable 1}

QsyncIAdjustmentsSentLevelEntry ::=
	SEQUENCE {
		qsyncIAdjustmentsSentLevelName	DisplayString,
		qsyncIAdjustmentsSentLevelVal	Counter64,
		qsyncIAdjustmentsSentLevelMom	CounterBasedGauge64,
		qsyncIAdjustmentsSentLevelMax	CounterBasedGauge64
	}

qsyncIAdjustmentsSentLevelName OBJECT-TYPE
	SYNTAX      DisplayString
	MAX-ACCESS  not-accessible
	STATUS      current
	DESCRIPTION
	"Table entry display string for qsyncIAdjustmentsSent"
	::={qsyncIAdjustmentsSentLevelEntry 1}

qsyncIAdjustmentsSentLevelVal OBJECT-TYPE
	SYNTAX	 Counter64
	MAX-ACCESS  read-only
	STATUS      current
	DESCRIPTION
	"Table entry attribute for qsyncIAdjustmentsSent"
	::={qsyncIAdjustmentsSentLevelEntry 2}

qsyncIAdjustmentsSentLevelMom OBJECT-TYPE
	SYNTAX	 CounterBasedGauge64
	MAX-ACCESS  read-only
	STATUS      current
	DESCRIPTION
	"Table entry attribute for qsyncIAdjustmentsSent"
	::={qsyncIAdjustmentsSentLevelEntry 3}

qsyncIAdjustmentsSentLevelMax OBJECT-TYPE
	SYNTAX	 CounterBasedGauge64
	MAX-ACCESS  read-only
	STATUS      current
	DESCRIPTION
	"Table entry attribute for qsyncIAdjustmentsSent"
	::={qsyncIAdjustmentsSentLevelEntry 4}


qsyncENumPeers	OBJECT IDENTIFIER ::={qsync 9}

qsyncENumPeersVal	OBJECT-TYPE
	SYNTAX	 CounterBasedGauge64
	MAX-ACCESS read-only
	STATUS current
	DESCRIPTION "(ext) Number of peers"

	::={qsyncENumPeers 1}

qsyncENumPeersMax	OBJECT-TYPE
	SYNTAX	 CounterBasedGauge64
	MAX-ACCESS read-only
	STATUS current
	DESCRIPTION "(ext) Number of peers"

	::={qsyncENumPeers 3}

qsyncENumPeersLevelTable OBJECT-TYPE
	SYNTAX      SEQUENCE OF QsyncENumPeersLevelEntry
	MAX-ACCESS  not-accessible
	STATUS      current
	DESCRIPTION
	"Table for qsyncENumPeers"
	::={qsyncENumPeers 4}

qsyncENumPeersLevelEntry OBJECT-TYPE
	SYNTAX      QsyncENumPeersLevelEntry
	MAX-ACCESS  not-accessible
	STATUS      current
	DESCRIPTION
	"Table entry for qsyncENumPeers"
	INDEX { qsyncENumPeersLevelName }
	::={qsyncENumPeersLevelTable 1}

QsyncENumPeersLevelEntry ::=
	SEQUENCE {
		qsyncENumPeersLevelName	DisplayString,
		qsyncENumPeersLevelVal	CounterBasedGauge64,
		qsyncENumPeersLevelMax	CounterBasedGauge64
	}

qsyncENumPeersLevelName OBJECT-TYPE
	SYNTAX      DisplayString
	MAX-ACCESS  not-accessible
	STATUS      current
	DESCRIPTION
	"Table entry display string for qsyncENumPeers"
	::={qsyncENumPeersLevelEntry 1}

qsyncENumPeersLevelVal OBJECT-TYPE
	SYNTAX	 CounterBasedGauge64
	MAX-ACCESS  read-only
	STATUS      current
	DESCRIPTION
	"Table entry attribute for qsyncENumPeers"
	::={qsyncENumPeersLevelEntry 2}

qsyncENumPeersLevelMax OBJECT-TYPE
	SYNTAX	 CounterBasedGauge64
	MAX-ACCESS  read-only
	STATUS      current
	DESCRIPTION
	"Table entry attribute for qsyncENumPeers"
	::={qsyncENumPeersLevelEntry 4}


qsyncEUpdatesMismatch	OBJECT IDENTIFIER ::={qsync 10}

qsyncEUpdatesMismatchVal	OBJECT-TYPE
	SYNTAX	 Counter64
	MAX-ACCESS read-only
	STATUS current
	DESCRIPTION "(ext) Updates with mismatching ruleset"

	::={qsyncEUpdatesMismatch 1}

qsyncEUpdatesMismatchMom	OBJECT-TYPE
	SYNTAX	 CounterBasedGauge64
	MAX-ACCESS read-only
	STATUS current
	DESCRIPTION "(ext) Updates with mismatching ruleset"

	::={qsyncEUpdatesMismatch 2}

qsyncEUpdatesMismatchMax	OBJECT-TYPE
	SYNTAX	 CounterBasedGauge64
	MAX-ACCESS read-only
	STATUS current
	DESCRIPTION "(ext) Updates with mismatching ruleset"

	::={qsyncEUpdatesMismatch 3}

qsyncEUpdatesMismatchLevelTable OBJECT-TYPE
	SYNTAX      SEQUENCE OF QsyncEUpdatesMismatchLevelEntry
	MAX-ACCESS  not-accessible
	STATUS      current
	DESCRIPTION
	"Table for qsyncEUpdatesMismatch"
	::={qsyncEUpdatesMismatch 4}

qsyncEUpdatesMismatchLevelEntry OBJECT-TYPE
	SYNTAX      QsyncEUpdatesMismatchLevelEntry
	MAX-ACCESS  not-accessible
	STATUS      current
	DESCRIPTION
	"Table entry for qsyncEUpdatesMismatch"
	INDEX { qsyncEUpdatesMismatchLevelName }
	::={qsyncEUpdatesMismatchLevelTable 1}

QsyncEUpdatesMismatchLevelEntry ::=
	SEQUENCE {
		qsyncEUpdatesMismatchLevelName	DisplayString,
		qsyncEUpdatesMismatchLevelVal	Counter64,
		qsyncEUpdatesMismatchLevelMom	CounterBasedGauge64,
		qsyncEUpdatesMismatchLevelMax	CounterBasedGauge64
	}

qsyncEUpdatesMismatchLevelName OBJECT-TYPE
	SYNTAX      DisplayString
	MAX-ACCESS  not-accessible
	STATUS      current
	DESCRIPTION
	"Table entry display string for qsyncEUpdatesMismatch"
	::={qsyncEUpdatesMismatchLevelEntry 1}

qsyncEUpdatesMismatchLevelVal OBJECT-TYPE
	SYNTAX	 Counter64
	MAX-ACCESS  read-only
	STATUS      current
	DESCRIPTION
	"Table entry attribute for qsyncEUpdatesMismatch"
	::={qsyncEUpdatesMismatchLevelEntry 2}

qsyncEUpdatesMismatchLevelMom OBJECT-TYPE
	SYNTAX	 CounterBasedGauge64
	MAX-ACCESS  read-only
	STATUS      current
	DESCRIPTION
	"Table entry attribute for qsyncEUpdatesMismatch"
	::={qsyncEUpdatesMismatchLevelEntry 3}

qsyncEUpdatesMismatchLevelMax OBJECT-TYPE
	SYNTAX	 CounterBasedGauge64
	MAX-ACCESS  read-only
	STATUS      current
	DESCRIPTION
	"Table entry attribute for qsyncEUpdatesMismatch"
	::={qsyncEUpdatesMismatchLevelEntry 4}


qsyncEUpdatePackets	OBJECT IDENTIFIER ::={qsync 11}

qsyncEUpdatePacketsVal	OBJECT-TYPE
	SYNTAX	 Counter64
	MAX-ACCESS read-only
	STATUS current
	DESCRIPTION "(ext) Update packets"

	::={qsyncEUpdatePackets 1}

qsyncEUpdatePacketsMom	OBJECT-TYPE
	SYNTAX	 CounterBasedGauge64
	MAX-ACCESS read-only
	STATUS current
	DESCRIPTION "(ext) Update packets"

	::={qsyncEUpdatePackets 2}

qsyncEUpdatePacketsMax	OBJECT-TYPE
	SYNTAX	 CounterBasedGauge64
	MAX-ACCESS read-only
	STATUS current
	DESCRIPTION "(ext) Update packets"

	::={qsyncEUpdatePackets 3}

qsyncEUpdatePacketsLevelTable OBJECT-TYPE
	SYNTAX      SEQUENCE OF QsyncEUpdatePacketsLevelEntry
	MAX-ACCESS  not-accessible
	STATUS      current
	DESCRIPTION
	"Table for qsyncEUpdatePackets"
	::={qsyncEUpdatePackets 4}

qsyncEUpdatePacketsLevelEntry OBJECT-TYPE
	SYNTAX      QsyncEUpdatePacketsLevelEntry
	MAX-ACCESS  not-accessible
	STATUS      current
	DESCRIPTION
	"Table entry for qsyncEUpdatePackets"
	INDEX { qsyncEUpdatePacketsLevelName }
	::={qsyncEUpdatePacketsLevelTable 1}

QsyncEUpdatePacketsLevelEntry ::=
	SEQUENCE {
		qsyncEUpdatePacketsLevelName	DisplayString,
		qsyncEUpdatePacketsLevelVal	Counter64,
		qsyncEUpdatePacketsLevelMom	CounterBasedGauge64,
		qsyncEUpdatePacketsLevelMax	CounterBasedGauge64
	}

qsyncEUpdatePacketsLevelName OBJECT-TYPE
	SYNTAX      DisplayString
	MAX-ACCESS  not-accessible
	STATUS      current
	DESCRIPTION
	"Table entry display string for qsyncEUpdatePackets"
	::={qsyncEUpdatePacketsLevelEntry 1}

qsyncEUpdatePacketsLevelVal OBJECT-TYPE
	SYNTAX	 Counter64
	MAX-ACCESS  read-only
	STATUS      current
	DESCRIPTION
	"Table entry attribute for qsyncEUpdatePackets"
	::={qsyncEUpdatePacketsLevelEntry 2}

qsyncEUpdatePacketsLevelMom OBJECT-TYPE
	SYNTAX	 CounterBasedGauge64
	MAX-ACCESS  read-only
	STATUS      current
	DESCRIPTION
	"Table entry attribute for qsyncEUpdatePackets"
	::={qsyncEUpdatePacketsLevelEntry 3}

qsyncEUpdatePacketsLevelMax OBJECT-TYPE
	SYNTAX	 CounterBasedGauge64
	MAX-ACCESS  read-only
	STATUS      current
	DESCRIPTION
	"Table entry attribute for qsyncEUpdatePackets"
	::={qsyncEUpdatePacketsLevelEntry 4}


qsyncESplitTimeout	OBJECT IDENTIFIER ::={qsync 12}

qsyncESplitTimeoutVal	OBJECT-TYPE
	SYNTAX	 Counter64
	MAX-ACCESS read-only
	STATUS current
	DESCRIPTION "(ext) Split object age timeout"

	::={qsyncESplitTimeout 1}

qsyncESplitTimeoutMom	OBJECT-TYPE
	SYNTAX	 CounterBasedGauge64
	MAX-ACCESS read-only
	STATUS current
	DESCRIPTION "(ext) Split object age timeout"

	::={qsyncESplitTimeout 2}

qsyncESplitTimeoutMax	OBJECT-TYPE
	SYNTAX	 CounterBasedGauge64
	MAX-ACCESS read-only
	STATUS current
	DESCRIPTION "(ext) Split object age timeout"

	::={qsyncESplitTimeout 3}

qsyncESplitTimeoutLevelTable OBJECT-TYPE
	SYNTAX      SEQUENCE OF QsyncESplitTimeoutLevelEntry
	MAX-ACCESS  not-accessible
	STATUS      current
	DESCRIPTION
	"Table for qsyncESplitTimeout"
	::={qsyncESplitTimeout 4}

qsyncESplitTimeoutLevelEntry OBJECT-TYPE
	SYNTAX      QsyncESplitTimeoutLevelEntry
	MAX-ACCESS  not-accessible
	STATUS      current
	DESCRIPTION
	"Table entry for qsyncESplitTimeout"
	INDEX { qsyncESplitTimeoutLevelName }
	::={qsyncESplitTimeoutLevelTable 1}

QsyncESplitTimeoutLevelEntry ::=
	SEQUENCE {
		qsyncESplitTimeoutLevelName	DisplayString,
		qsyncESplitTimeoutLevelVal	Counter64,
		qsyncESplitTimeoutLevelMom	CounterBasedGauge64,
		qsyncESplitTimeoutLevelMax	CounterBasedGauge64
	}

qsyncESplitTimeoutLevelName OBJECT-TYPE
	SYNTAX      DisplayString
	MAX-ACCESS  not-accessible
	STATUS      current
	DESCRIPTION
	"Table entry display string for qsyncESplitTimeout"
	::={qsyncESplitTimeoutLevelEntry 1}

qsyncESplitTimeoutLevelVal OBJECT-TYPE
	SYNTAX	 Counter64
	MAX-ACCESS  read-only
	STATUS      current
	DESCRIPTION
	"Table entry attribute for qsyncESplitTimeout"
	::={qsyncESplitTimeoutLevelEntry 2}

qsyncESplitTimeoutLevelMom OBJECT-TYPE
	SYNTAX	 CounterBasedGauge64
	MAX-ACCESS  read-only
	STATUS      current
	DESCRIPTION
	"Table entry attribute for qsyncESplitTimeout"
	::={qsyncESplitTimeoutLevelEntry 3}

qsyncESplitTimeoutLevelMax OBJECT-TYPE
	SYNTAX	 CounterBasedGauge64
	MAX-ACCESS  read-only
	STATUS      current
	DESCRIPTION
	"Table entry attribute for qsyncESplitTimeout"
	::={qsyncESplitTimeoutLevelEntry 4}


qsyncERecvUpdateEntries	OBJECT IDENTIFIER ::={qsync 13}

qsyncERecvUpdateEntriesVal	OBJECT-TYPE
	SYNTAX	 Counter64
	MAX-ACCESS read-only
	STATUS current
	DESCRIPTION "(ext entries) Received update entries"

	::={qsyncERecvUpdateEntries 1}

qsyncERecvUpdateEntriesMom	OBJECT-TYPE
	SYNTAX	 CounterBasedGauge64
	MAX-ACCESS read-only
	STATUS current
	DESCRIPTION "(ext entries) Received update entries"

	::={qsyncERecvUpdateEntries 2}

qsyncERecvUpdateEntriesMax	OBJECT-TYPE
	SYNTAX	 CounterBasedGauge64
	MAX-ACCESS read-only
	STATUS current
	DESCRIPTION "(ext entries) Received update entries"

	::={qsyncERecvUpdateEntries 3}

qsyncERecvUpdateEntriesLevelTable OBJECT-TYPE
	SYNTAX      SEQUENCE OF QsyncERecvUpdateEntriesLevelEntry
	MAX-ACCESS  not-accessible
	STATUS      current
	DESCRIPTION
	"Table for qsyncERecvUpdateEntries"
	::={qsyncERecvUpdateEntries 4}

qsyncERecvUpdateEntriesLevelEntry OBJECT-TYPE
	SYNTAX      QsyncERecvUpdateEntriesLevelEntry
	MAX-ACCESS  not-accessible
	STATUS      current
	DESCRIPTION
	"Table entry for qsyncERecvUpdateEntries"
	INDEX { qsyncERecvUpdateEntriesLevelName }
	::={qsyncERecvUpdateEntriesLevelTable 1}

QsyncERecvUpdateEntriesLevelEntry ::=
	SEQUENCE {
		qsyncERecvUpdateEntriesLevelName	DisplayString,
		qsyncERecvUpdateEntriesLevelVal	Counter64,
		qsyncERecvUpdateEntriesLevelMom	CounterBasedGauge64,
		qsyncERecvUpdateEntriesLevelMax	CounterBasedGauge64
	}

qsyncERecvUpdateEntriesLevelName OBJECT-TYPE
	SYNTAX      DisplayString
	MAX-ACCESS  not-accessible
	STATUS      current
	DESCRIPTION
	"Table entry display string for qsyncERecvUpdateEntries"
	::={qsyncERecvUpdateEntriesLevelEntry 1}

qsyncERecvUpdateEntriesLevelVal OBJECT-TYPE
	SYNTAX	 Counter64
	MAX-ACCESS  read-only
	STATUS      current
	DESCRIPTION
	"Table entry attribute for qsyncERecvUpdateEntries"
	::={qsyncERecvUpdateEntriesLevelEntry 2}

qsyncERecvUpdateEntriesLevelMom OBJECT-TYPE
	SYNTAX	 CounterBasedGauge64
	MAX-ACCESS  read-only
	STATUS      current
	DESCRIPTION
	"Table entry attribute for qsyncERecvUpdateEntries"
	::={qsyncERecvUpdateEntriesLevelEntry 3}

qsyncERecvUpdateEntriesLevelMax OBJECT-TYPE
	SYNTAX	 CounterBasedGauge64
	MAX-ACCESS  read-only
	STATUS      current
	DESCRIPTION
	"Table entry attribute for qsyncERecvUpdateEntries"
	::={qsyncERecvUpdateEntriesLevelEntry 4}


qsyncESendUpdateEntries	OBJECT IDENTIFIER ::={qsync 14}

qsyncESendUpdateEntriesVal	OBJECT-TYPE
	SYNTAX	 Counter64
	MAX-ACCESS read-only
	STATUS current
	DESCRIPTION "(ext entries) Sent update entries"

	::={qsyncESendUpdateEntries 1}

qsyncESendUpdateEntriesMom	OBJECT-TYPE
	SYNTAX	 CounterBasedGauge64
	MAX-ACCESS read-only
	STATUS current
	DESCRIPTION "(ext entries) Sent update entries"

	::={qsyncESendUpdateEntries 2}

qsyncESendUpdateEntriesMax	OBJECT-TYPE
	SYNTAX	 CounterBasedGauge64
	MAX-ACCESS read-only
	STATUS current
	DESCRIPTION "(ext entries) Sent update entries"

	::={qsyncESendUpdateEntries 3}

qsyncESendUpdateEntriesLevelTable OBJECT-TYPE
	SYNTAX      SEQUENCE OF QsyncESendUpdateEntriesLevelEntry
	MAX-ACCESS  not-accessible
	STATUS      current
	DESCRIPTION
	"Table for qsyncESendUpdateEntries"
	::={qsyncESendUpdateEntries 4}

qsyncESendUpdateEntriesLevelEntry OBJECT-TYPE
	SYNTAX      QsyncESendUpdateEntriesLevelEntry
	MAX-ACCESS  not-accessible
	STATUS      current
	DESCRIPTION
	"Table entry for qsyncESendUpdateEntries"
	INDEX { qsyncESendUpdateEntriesLevelName }
	::={qsyncESendUpdateEntriesLevelTable 1}

QsyncESendUpdateEntriesLevelEntry ::=
	SEQUENCE {
		qsyncESendUpdateEntriesLevelName	DisplayString,
		qsyncESendUpdateEntriesLevelVal	Counter64,
		qsyncESendUpdateEntriesLevelMom	CounterBasedGauge64,
		qsyncESendUpdateEntriesLevelMax	CounterBasedGauge64
	}

qsyncESendUpdateEntriesLevelName OBJECT-TYPE
	SYNTAX      DisplayString
	MAX-ACCESS  not-accessible
	STATUS      current
	DESCRIPTION
	"Table entry display string for qsyncESendUpdateEntries"
	::={qsyncESendUpdateEntriesLevelEntry 1}

qsyncESendUpdateEntriesLevelVal OBJECT-TYPE
	SYNTAX	 Counter64
	MAX-ACCESS  read-only
	STATUS      current
	DESCRIPTION
	"Table entry attribute for qsyncESendUpdateEntries"
	::={qsyncESendUpdateEntriesLevelEntry 2}

qsyncESendUpdateEntriesLevelMom OBJECT-TYPE
	SYNTAX	 CounterBasedGauge64
	MAX-ACCESS  read-only
	STATUS      current
	DESCRIPTION
	"Table entry attribute for qsyncESendUpdateEntries"
	::={qsyncESendUpdateEntriesLevelEntry 3}

qsyncESendUpdateEntriesLevelMax OBJECT-TYPE
	SYNTAX	 CounterBasedGauge64
	MAX-ACCESS  read-only
	STATUS      current
	DESCRIPTION
	"Table entry attribute for qsyncESendUpdateEntries"
	::={qsyncESendUpdateEntriesLevelEntry 4}


qsyncESendUpdatePackets	OBJECT IDENTIFIER ::={qsync 15}

qsyncESendUpdatePacketsVal	OBJECT-TYPE
	SYNTAX	 Counter64
	MAX-ACCESS read-only
	STATUS current
	DESCRIPTION "(ext) Sent update packets"

	::={qsyncESendUpdatePackets 1}

qsyncESendUpdatePacketsMom	OBJECT-TYPE
	SYNTAX	 CounterBasedGauge64
	MAX-ACCESS read-only
	STATUS current
	DESCRIPTION "(ext) Sent update packets"

	::={qsyncESendUpdatePackets 2}

qsyncESendUpdatePacketsMax	OBJECT-TYPE
	SYNTAX	 CounterBasedGauge64
	MAX-ACCESS read-only
	STATUS current
	DESCRIPTION "(ext) Sent update packets"

	::={qsyncESendUpdatePackets 3}

qsyncESendUpdatePacketsLevelTable OBJECT-TYPE
	SYNTAX      SEQUENCE OF QsyncESendUpdatePacketsLevelEntry
	MAX-ACCESS  not-accessible
	STATUS      current
	DESCRIPTION
	"Table for qsyncESendUpdatePackets"
	::={qsyncESendUpdatePackets 4}

qsyncESendUpdatePacketsLevelEntry OBJECT-TYPE
	SYNTAX      QsyncESendUpdatePacketsLevelEntry
	MAX-ACCESS  not-accessible
	STATUS      current
	DESCRIPTION
	"Table entry for qsyncESendUpdatePackets"
	INDEX { qsyncESendUpdatePacketsLevelName }
	::={qsyncESendUpdatePacketsLevelTable 1}

QsyncESendUpdatePacketsLevelEntry ::=
	SEQUENCE {
		qsyncESendUpdatePacketsLevelName	DisplayString,
		qsyncESendUpdatePacketsLevelVal	Counter64,
		qsyncESendUpdatePacketsLevelMom	CounterBasedGauge64,
		qsyncESendUpdatePacketsLevelMax	CounterBasedGauge64
	}

qsyncESendUpdatePacketsLevelName OBJECT-TYPE
	SYNTAX      DisplayString
	MAX-ACCESS  not-accessible
	STATUS      current
	DESCRIPTION
	"Table entry display string for qsyncESendUpdatePackets"
	::={qsyncESendUpdatePacketsLevelEntry 1}

qsyncESendUpdatePacketsLevelVal OBJECT-TYPE
	SYNTAX	 Counter64
	MAX-ACCESS  read-only
	STATUS      current
	DESCRIPTION
	"Table entry attribute for qsyncESendUpdatePackets"
	::={qsyncESendUpdatePacketsLevelEntry 2}

qsyncESendUpdatePacketsLevelMom OBJECT-TYPE
	SYNTAX	 CounterBasedGauge64
	MAX-ACCESS  read-only
	STATUS      current
	DESCRIPTION
	"Table entry attribute for qsyncESendUpdatePackets"
	::={qsyncESendUpdatePacketsLevelEntry 3}

qsyncESendUpdatePacketsLevelMax OBJECT-TYPE
	SYNTAX	 CounterBasedGauge64
	MAX-ACCESS  read-only
	STATUS      current
	DESCRIPTION
	"Table entry attribute for qsyncESendUpdatePackets"
	::={qsyncESendUpdatePacketsLevelEntry 4}


qsyncIUnsync	OBJECT IDENTIFIER ::={qsync 16}

qsyncIUnsyncVal	OBJECT-TYPE
	SYNTAX	 Counter64
	MAX-ACCESS read-only
	STATUS current
	DESCRIPTION "Qsync not run because unsynced objects"

	::={qsyncIUnsync 1}

qsyncIUnsyncMom	OBJECT-TYPE
	SYNTAX	 CounterBasedGauge64
	MAX-ACCESS read-only
	STATUS current
	DESCRIPTION "Qsync not run because unsynced objects"

	::={qsyncIUnsync 2}

qsyncIUnsyncMax	OBJECT-TYPE
	SYNTAX	 CounterBasedGauge64
	MAX-ACCESS read-only
	STATUS current
	DESCRIPTION "Qsync not run because unsynced objects"

	::={qsyncIUnsync 3}

qsyncIUnsyncLevelTable OBJECT-TYPE
	SYNTAX      SEQUENCE OF QsyncIUnsyncLevelEntry
	MAX-ACCESS  not-accessible
	STATUS      current
	DESCRIPTION
	"Table for qsyncIUnsync"
	::={qsyncIUnsync 4}

qsyncIUnsyncLevelEntry OBJECT-TYPE
	SYNTAX      QsyncIUnsyncLevelEntry
	MAX-ACCESS  not-accessible
	STATUS      current
	DESCRIPTION
	"Table entry for qsyncIUnsync"
	INDEX { qsyncIUnsyncLevelName }
	::={qsyncIUnsyncLevelTable 1}

QsyncIUnsyncLevelEntry ::=
	SEQUENCE {
		qsyncIUnsyncLevelName	DisplayString,
		qsyncIUnsyncLevelVal	Counter64,
		qsyncIUnsyncLevelMom	CounterBasedGauge64,
		qsyncIUnsyncLevelMax	CounterBasedGauge64
	}

qsyncIUnsyncLevelName OBJECT-TYPE
	SYNTAX      DisplayString
	MAX-ACCESS  not-accessible
	STATUS      current
	DESCRIPTION
	"Table entry display string for qsyncIUnsync"
	::={qsyncIUnsyncLevelEntry 1}

qsyncIUnsyncLevelVal OBJECT-TYPE
	SYNTAX	 Counter64
	MAX-ACCESS  read-only
	STATUS      current
	DESCRIPTION
	"Table entry attribute for qsyncIUnsync"
	::={qsyncIUnsyncLevelEntry 2}

qsyncIUnsyncLevelMom OBJECT-TYPE
	SYNTAX	 CounterBasedGauge64
	MAX-ACCESS  read-only
	STATUS      current
	DESCRIPTION
	"Table entry attribute for qsyncIUnsync"
	::={qsyncIUnsyncLevelEntry 3}

qsyncIUnsyncLevelMax OBJECT-TYPE
	SYNTAX	 CounterBasedGauge64
	MAX-ACCESS  read-only
	STATUS      current
	DESCRIPTION
	"Table entry attribute for qsyncIUnsync"
	::={qsyncIUnsyncLevelEntry 4}


qsyncESendbufFull	OBJECT IDENTIFIER ::={qsync 17}

qsyncESendbufFullVal	OBJECT-TYPE
	SYNTAX	 Counter64
	MAX-ACCESS read-only
	STATUS current
	DESCRIPTION "(ext sendbuffer) Entries dropped due to full sendbuffer"

	::={qsyncESendbufFull 1}

qsyncESendbufFullMom	OBJECT-TYPE
	SYNTAX	 CounterBasedGauge64
	MAX-ACCESS read-only
	STATUS current
	DESCRIPTION "(ext sendbuffer) Entries dropped due to full sendbuffer"

	::={qsyncESendbufFull 2}

qsyncESendbufFullMax	OBJECT-TYPE
	SYNTAX	 CounterBasedGauge64
	MAX-ACCESS read-only
	STATUS current
	DESCRIPTION "(ext sendbuffer) Entries dropped due to full sendbuffer"

	::={qsyncESendbufFull 3}

qsyncESendbufFullLevelTable OBJECT-TYPE
	SYNTAX      SEQUENCE OF QsyncESendbufFullLevelEntry
	MAX-ACCESS  not-accessible
	STATUS      current
	DESCRIPTION
	"Table for qsyncESendbufFull"
	::={qsyncESendbufFull 4}

qsyncESendbufFullLevelEntry OBJECT-TYPE
	SYNTAX      QsyncESendbufFullLevelEntry
	MAX-ACCESS  not-accessible
	STATUS      current
	DESCRIPTION
	"Table entry for qsyncESendbufFull"
	INDEX { qsyncESendbufFullLevelName }
	::={qsyncESendbufFullLevelTable 1}

QsyncESendbufFullLevelEntry ::=
	SEQUENCE {
		qsyncESendbufFullLevelName	DisplayString,
		qsyncESendbufFullLevelVal	Counter64,
		qsyncESendbufFullLevelMom	CounterBasedGauge64,
		qsyncESendbufFullLevelMax	CounterBasedGauge64
	}

qsyncESendbufFullLevelName OBJECT-TYPE
	SYNTAX      DisplayString
	MAX-ACCESS  not-accessible
	STATUS      current
	DESCRIPTION
	"Table entry display string for qsyncESendbufFull"
	::={qsyncESendbufFullLevelEntry 1}

qsyncESendbufFullLevelVal OBJECT-TYPE
	SYNTAX	 Counter64
	MAX-ACCESS  read-only
	STATUS      current
	DESCRIPTION
	"Table entry attribute for qsyncESendbufFull"
	::={qsyncESendbufFullLevelEntry 2}

qsyncESendbufFullLevelMom OBJECT-TYPE
	SYNTAX	 CounterBasedGauge64
	MAX-ACCESS  read-only
	STATUS      current
	DESCRIPTION
	"Table entry attribute for qsyncESendbufFull"
	::={qsyncESendbufFullLevelEntry 3}

qsyncESendbufFullLevelMax OBJECT-TYPE
	SYNTAX	 CounterBasedGauge64
	MAX-ACCESS  read-only
	STATUS      current
	DESCRIPTION
	"Table entry attribute for qsyncESendbufFull"
	::={qsyncESendbufFullLevelEntry 4}


qsyncESendbufUsage	OBJECT IDENTIFIER ::={qsync 18}

qsyncESendbufUsageVal	OBJECT-TYPE
	SYNTAX	 CounterBasedGauge64
	MAX-ACCESS read-only
	STATUS current
	DESCRIPTION "(ext sendbuffer) Sendbuffer usage"

	::={qsyncESendbufUsage 1}

qsyncESendbufUsageMax	OBJECT-TYPE
	SYNTAX	 CounterBasedGauge64
	MAX-ACCESS read-only
	STATUS current
	DESCRIPTION "(ext sendbuffer) Sendbuffer usage"

	::={qsyncESendbufUsage 3}

qsyncESendbufUsageLevelTable OBJECT-TYPE
	SYNTAX      SEQUENCE OF QsyncESendbufUsageLevelEntry
	MAX-ACCESS  not-accessible
	STATUS      current
	DESCRIPTION
	"Table for qsyncESendbufUsage"
	::={qsyncESendbufUsage 4}

qsyncESendbufUsageLevelEntry OBJECT-TYPE
	SYNTAX      QsyncESendbufUsageLevelEntry
	MAX-ACCESS  not-accessible
	STATUS      current
	DESCRIPTION
	"Table entry for qsyncESendbufUsage"
	INDEX { qsyncESendbufUsageLevelName }
	::={qsyncESendbufUsageLevelTable 1}

QsyncESendbufUsageLevelEntry ::=
	SEQUENCE {
		qsyncESendbufUsageLevelName	DisplayString,
		qsyncESendbufUsageLevelVal	CounterBasedGauge64,
		qsyncESendbufUsageLevelMax	CounterBasedGauge64
	}

qsyncESendbufUsageLevelName OBJECT-TYPE
	SYNTAX      DisplayString
	MAX-ACCESS  not-accessible
	STATUS      current
	DESCRIPTION
	"Table entry display string for qsyncESendbufUsage"
	::={qsyncESendbufUsageLevelEntry 1}

qsyncESendbufUsageLevelVal OBJECT-TYPE
	SYNTAX	 CounterBasedGauge64
	MAX-ACCESS  read-only
	STATUS      current
	DESCRIPTION
	"Table entry attribute for qsyncESendbufUsage"
	::={qsyncESendbufUsageLevelEntry 2}

qsyncESendbufUsageLevelMax OBJECT-TYPE
	SYNTAX	 CounterBasedGauge64
	MAX-ACCESS  read-only
	STATUS      current
	DESCRIPTION
	"Table entry attribute for qsyncESendbufUsage"
	::={qsyncESendbufUsageLevelEntry 4}


qsyncIIgnoredOOO	OBJECT IDENTIFIER ::={qsync 19}

qsyncIIgnoredOOOVal	OBJECT-TYPE
	SYNTAX	 Counter64
	MAX-ACCESS read-only
	STATUS current
	DESCRIPTION "Ignored out of order updates"

	::={qsyncIIgnoredOOO 1}

qsyncIIgnoredOOOMom	OBJECT-TYPE
	SYNTAX	 CounterBasedGauge64
	MAX-ACCESS read-only
	STATUS current
	DESCRIPTION "Ignored out of order updates"

	::={qsyncIIgnoredOOO 2}

qsyncIIgnoredOOOMax	OBJECT-TYPE
	SYNTAX	 CounterBasedGauge64
	MAX-ACCESS read-only
	STATUS current
	DESCRIPTION "Ignored out of order updates"

	::={qsyncIIgnoredOOO 3}

qsyncIIgnoredOOOLevelTable OBJECT-TYPE
	SYNTAX      SEQUENCE OF QsyncIIgnoredOOOLevelEntry
	MAX-ACCESS  not-accessible
	STATUS      current
	DESCRIPTION
	"Table for qsyncIIgnoredOOO"
	::={qsyncIIgnoredOOO 4}

qsyncIIgnoredOOOLevelEntry OBJECT-TYPE
	SYNTAX      QsyncIIgnoredOOOLevelEntry
	MAX-ACCESS  not-accessible
	STATUS      current
	DESCRIPTION
	"Table entry for qsyncIIgnoredOOO"
	INDEX { qsyncIIgnoredOOOLevelName }
	::={qsyncIIgnoredOOOLevelTable 1}

QsyncIIgnoredOOOLevelEntry ::=
	SEQUENCE {
		qsyncIIgnoredOOOLevelName	DisplayString,
		qsyncIIgnoredOOOLevelVal	Counter64,
		qsyncIIgnoredOOOLevelMom	CounterBasedGauge64,
		qsyncIIgnoredOOOLevelMax	CounterBasedGauge64
	}

qsyncIIgnoredOOOLevelName OBJECT-TYPE
	SYNTAX      DisplayString
	MAX-ACCESS  not-accessible
	STATUS      current
	DESCRIPTION
	"Table entry display string for qsyncIIgnoredOOO"
	::={qsyncIIgnoredOOOLevelEntry 1}

qsyncIIgnoredOOOLevelVal OBJECT-TYPE
	SYNTAX	 Counter64
	MAX-ACCESS  read-only
	STATUS      current
	DESCRIPTION
	"Table entry attribute for qsyncIIgnoredOOO"
	::={qsyncIIgnoredOOOLevelEntry 2}

qsyncIIgnoredOOOLevelMom OBJECT-TYPE
	SYNTAX	 CounterBasedGauge64
	MAX-ACCESS  read-only
	STATUS      current
	DESCRIPTION
	"Table entry attribute for qsyncIIgnoredOOO"
	::={qsyncIIgnoredOOOLevelEntry 3}

qsyncIIgnoredOOOLevelMax OBJECT-TYPE
	SYNTAX	 CounterBasedGauge64
	MAX-ACCESS  read-only
	STATUS      current
	DESCRIPTION
	"Table entry attribute for qsyncIIgnoredOOO"
	::={qsyncIIgnoredOOOLevelEntry 4}


qsyncIIgnoredGenWrap	OBJECT IDENTIFIER ::={qsync 20}

qsyncIIgnoredGenWrapVal	OBJECT-TYPE
	SYNTAX	 Counter64
	MAX-ACCESS read-only
	STATUS current
	DESCRIPTION "Ignored updates (generation wrap)"

	::={qsyncIIgnoredGenWrap 1}

qsyncIIgnoredGenWrapMom	OBJECT-TYPE
	SYNTAX	 CounterBasedGauge64
	MAX-ACCESS read-only
	STATUS current
	DESCRIPTION "Ignored updates (generation wrap)"

	::={qsyncIIgnoredGenWrap 2}

qsyncIIgnoredGenWrapMax	OBJECT-TYPE
	SYNTAX	 CounterBasedGauge64
	MAX-ACCESS read-only
	STATUS current
	DESCRIPTION "Ignored updates (generation wrap)"

	::={qsyncIIgnoredGenWrap 3}

qsyncIIgnoredGenWrapLevelTable OBJECT-TYPE
	SYNTAX      SEQUENCE OF QsyncIIgnoredGenWrapLevelEntry
	MAX-ACCESS  not-accessible
	STATUS      current
	DESCRIPTION
	"Table for qsyncIIgnoredGenWrap"
	::={qsyncIIgnoredGenWrap 4}

qsyncIIgnoredGenWrapLevelEntry OBJECT-TYPE
	SYNTAX      QsyncIIgnoredGenWrapLevelEntry
	MAX-ACCESS  not-accessible
	STATUS      current
	DESCRIPTION
	"Table entry for qsyncIIgnoredGenWrap"
	INDEX { qsyncIIgnoredGenWrapLevelName }
	::={qsyncIIgnoredGenWrapLevelTable 1}

QsyncIIgnoredGenWrapLevelEntry ::=
	SEQUENCE {
		qsyncIIgnoredGenWrapLevelName	DisplayString,
		qsyncIIgnoredGenWrapLevelVal	Counter64,
		qsyncIIgnoredGenWrapLevelMom	CounterBasedGauge64,
		qsyncIIgnoredGenWrapLevelMax	CounterBasedGauge64
	}

qsyncIIgnoredGenWrapLevelName OBJECT-TYPE
	SYNTAX      DisplayString
	MAX-ACCESS  not-accessible
	STATUS      current
	DESCRIPTION
	"Table entry display string for qsyncIIgnoredGenWrap"
	::={qsyncIIgnoredGenWrapLevelEntry 1}

qsyncIIgnoredGenWrapLevelVal OBJECT-TYPE
	SYNTAX	 Counter64
	MAX-ACCESS  read-only
	STATUS      current
	DESCRIPTION
	"Table entry attribute for qsyncIIgnoredGenWrap"
	::={qsyncIIgnoredGenWrapLevelEntry 2}

qsyncIIgnoredGenWrapLevelMom OBJECT-TYPE
	SYNTAX	 CounterBasedGauge64
	MAX-ACCESS  read-only
	STATUS      current
	DESCRIPTION
	"Table entry attribute for qsyncIIgnoredGenWrap"
	::={qsyncIIgnoredGenWrapLevelEntry 3}

qsyncIIgnoredGenWrapLevelMax OBJECT-TYPE
	SYNTAX	 CounterBasedGauge64
	MAX-ACCESS  read-only
	STATUS      current
	DESCRIPTION
	"Table entry attribute for qsyncIIgnoredGenWrap"
	::={qsyncIIgnoredGenWrapLevelEntry 4}


qsyncELastseen	OBJECT IDENTIFIER ::={qsync 21}

qsyncELastseenVal	OBJECT-TYPE
	SYNTAX	 DateAndTime
	MAX-ACCESS read-only
	STATUS current
	DESCRIPTION "(ext) Last seen peer"

	::={qsyncELastseen 1}

qsyncELastseenLevelTable OBJECT-TYPE
	SYNTAX      SEQUENCE OF QsyncELastseenLevelEntry
	MAX-ACCESS  not-accessible
	STATUS      current
	DESCRIPTION
	"Table for qsyncELastseen"
	::={qsyncELastseen 2}

qsyncELastseenLevelEntry OBJECT-TYPE
	SYNTAX      QsyncELastseenLevelEntry
	MAX-ACCESS  not-accessible
	STATUS      current
	DESCRIPTION
	"Table entry for qsyncELastseen"
	INDEX { qsyncELastseenLevelName }
	::={qsyncELastseenLevelTable 1}

QsyncELastseenLevelEntry ::=
	SEQUENCE {
		qsyncELastseenLevelName	DisplayString,
		qsyncELastseenLevelVal	DateAndTime
	}

qsyncELastseenLevelName OBJECT-TYPE
	SYNTAX      DisplayString
	MAX-ACCESS  not-accessible
	STATUS      current
	DESCRIPTION
	"Table entry display string for qsyncELastseen"
	::={qsyncELastseenLevelEntry 1}

qsyncELastseenLevelVal OBJECT-TYPE
	SYNTAX	 DateAndTime
	MAX-ACCESS  read-only
	STATUS      current
	DESCRIPTION
	"Table entry attribute for qsyncELastseen"
	::={qsyncELastseenLevelEntry 2}


qsyncEShort	OBJECT IDENTIFIER ::={qsync 22}

qsyncEShortVal	OBJECT-TYPE
	SYNTAX	 Counter64
	MAX-ACCESS read-only
	STATUS current
	DESCRIPTION "(ext) Short erronous packets received"

	::={qsyncEShort 1}

qsyncEShortMom	OBJECT-TYPE
	SYNTAX	 CounterBasedGauge64
	MAX-ACCESS read-only
	STATUS current
	DESCRIPTION "(ext) Short erronous packets received"

	::={qsyncEShort 2}

qsyncEShortMax	OBJECT-TYPE
	SYNTAX	 CounterBasedGauge64
	MAX-ACCESS read-only
	STATUS current
	DESCRIPTION "(ext) Short erronous packets received"

	::={qsyncEShort 3}

qsyncEShortLevelTable OBJECT-TYPE
	SYNTAX      SEQUENCE OF QsyncEShortLevelEntry
	MAX-ACCESS  not-accessible
	STATUS      current
	DESCRIPTION
	"Table for qsyncEShort"
	::={qsyncEShort 4}

qsyncEShortLevelEntry OBJECT-TYPE
	SYNTAX      QsyncEShortLevelEntry
	MAX-ACCESS  not-accessible
	STATUS      current
	DESCRIPTION
	"Table entry for qsyncEShort"
	INDEX { qsyncEShortLevelName }
	::={qsyncEShortLevelTable 1}

QsyncEShortLevelEntry ::=
	SEQUENCE {
		qsyncEShortLevelName	DisplayString,
		qsyncEShortLevelVal	Counter64,
		qsyncEShortLevelMom	CounterBasedGauge64,
		qsyncEShortLevelMax	CounterBasedGauge64
	}

qsyncEShortLevelName OBJECT-TYPE
	SYNTAX      DisplayString
	MAX-ACCESS  not-accessible
	STATUS      current
	DESCRIPTION
	"Table entry display string for qsyncEShort"
	::={qsyncEShortLevelEntry 1}

qsyncEShortLevelVal OBJECT-TYPE
	SYNTAX	 Counter64
	MAX-ACCESS  read-only
	STATUS      current
	DESCRIPTION
	"Table entry attribute for qsyncEShort"
	::={qsyncEShortLevelEntry 2}

qsyncEShortLevelMom OBJECT-TYPE
	SYNTAX	 CounterBasedGauge64
	MAX-ACCESS  read-only
	STATUS      current
	DESCRIPTION
	"Table entry attribute for qsyncEShort"
	::={qsyncEShortLevelEntry 3}

qsyncEShortLevelMax OBJECT-TYPE
	SYNTAX	 CounterBasedGauge64
	MAX-ACCESS  read-only
	STATUS      current
	DESCRIPTION
	"Table entry attribute for qsyncEShort"
	::={qsyncEShortLevelEntry 4}


qsyncEUpdateSent	OBJECT IDENTIFIER ::={qsync 23}

qsyncEUpdateSentVal	OBJECT-TYPE
	SYNTAX	 Counter64
	MAX-ACCESS read-only
	STATUS current
	DESCRIPTION "(ext update) Update packets sent"

	::={qsyncEUpdateSent 1}

qsyncEUpdateSentMom	OBJECT-TYPE
	SYNTAX	 CounterBasedGauge64
	MAX-ACCESS read-only
	STATUS current
	DESCRIPTION "(ext update) Update packets sent"

	::={qsyncEUpdateSent 2}

qsyncEUpdateSentMax	OBJECT-TYPE
	SYNTAX	 CounterBasedGauge64
	MAX-ACCESS read-only
	STATUS current
	DESCRIPTION "(ext update) Update packets sent"

	::={qsyncEUpdateSent 3}

qsyncEUpdateSentLevelTable OBJECT-TYPE
	SYNTAX      SEQUENCE OF QsyncEUpdateSentLevelEntry
	MAX-ACCESS  not-accessible
	STATUS      current
	DESCRIPTION
	"Table for qsyncEUpdateSent"
	::={qsyncEUpdateSent 4}

qsyncEUpdateSentLevelEntry OBJECT-TYPE
	SYNTAX      QsyncEUpdateSentLevelEntry
	MAX-ACCESS  not-accessible
	STATUS      current
	DESCRIPTION
	"Table entry for qsyncEUpdateSent"
	INDEX { qsyncEUpdateSentLevelName }
	::={qsyncEUpdateSentLevelTable 1}

QsyncEUpdateSentLevelEntry ::=
	SEQUENCE {
		qsyncEUpdateSentLevelName	DisplayString,
		qsyncEUpdateSentLevelVal	Counter64,
		qsyncEUpdateSentLevelMom	CounterBasedGauge64,
		qsyncEUpdateSentLevelMax	CounterBasedGauge64
	}

qsyncEUpdateSentLevelName OBJECT-TYPE
	SYNTAX      DisplayString
	MAX-ACCESS  not-accessible
	STATUS      current
	DESCRIPTION
	"Table entry display string for qsyncEUpdateSent"
	::={qsyncEUpdateSentLevelEntry 1}

qsyncEUpdateSentLevelVal OBJECT-TYPE
	SYNTAX	 Counter64
	MAX-ACCESS  read-only
	STATUS      current
	DESCRIPTION
	"Table entry attribute for qsyncEUpdateSent"
	::={qsyncEUpdateSentLevelEntry 2}

qsyncEUpdateSentLevelMom OBJECT-TYPE
	SYNTAX	 CounterBasedGauge64
	MAX-ACCESS  read-only
	STATUS      current
	DESCRIPTION
	"Table entry attribute for qsyncEUpdateSent"
	::={qsyncEUpdateSentLevelEntry 3}

qsyncEUpdateSentLevelMax OBJECT-TYPE
	SYNTAX	 CounterBasedGauge64
	MAX-ACCESS  read-only
	STATUS      current
	DESCRIPTION
	"Table entry attribute for qsyncEUpdateSent"
	::={qsyncEUpdateSentLevelEntry 4}


qsyncEUpdateReceived	OBJECT IDENTIFIER ::={qsync 24}

qsyncEUpdateReceivedVal	OBJECT-TYPE
	SYNTAX	 Counter64
	MAX-ACCESS read-only
	STATUS current
	DESCRIPTION "(ext update) Update packets received"

	::={qsyncEUpdateReceived 1}

qsyncEUpdateReceivedMom	OBJECT-TYPE
	SYNTAX	 CounterBasedGauge64
	MAX-ACCESS read-only
	STATUS current
	DESCRIPTION "(ext update) Update packets received"

	::={qsyncEUpdateReceived 2}

qsyncEUpdateReceivedMax	OBJECT-TYPE
	SYNTAX	 CounterBasedGauge64
	MAX-ACCESS read-only
	STATUS current
	DESCRIPTION "(ext update) Update packets received"

	::={qsyncEUpdateReceived 3}

qsyncEUpdateReceivedLevelTable OBJECT-TYPE
	SYNTAX      SEQUENCE OF QsyncEUpdateReceivedLevelEntry
	MAX-ACCESS  not-accessible
	STATUS      current
	DESCRIPTION
	"Table for qsyncEUpdateReceived"
	::={qsyncEUpdateReceived 4}

qsyncEUpdateReceivedLevelEntry OBJECT-TYPE
	SYNTAX      QsyncEUpdateReceivedLevelEntry
	MAX-ACCESS  not-accessible
	STATUS      current
	DESCRIPTION
	"Table entry for qsyncEUpdateReceived"
	INDEX { qsyncEUpdateReceivedLevelName }
	::={qsyncEUpdateReceivedLevelTable 1}

QsyncEUpdateReceivedLevelEntry ::=
	SEQUENCE {
		qsyncEUpdateReceivedLevelName	DisplayString,
		qsyncEUpdateReceivedLevelVal	Counter64,
		qsyncEUpdateReceivedLevelMom	CounterBasedGauge64,
		qsyncEUpdateReceivedLevelMax	CounterBasedGauge64
	}

qsyncEUpdateReceivedLevelName OBJECT-TYPE
	SYNTAX      DisplayString
	MAX-ACCESS  not-accessible
	STATUS      current
	DESCRIPTION
	"Table entry display string for qsyncEUpdateReceived"
	::={qsyncEUpdateReceivedLevelEntry 1}

qsyncEUpdateReceivedLevelVal OBJECT-TYPE
	SYNTAX	 Counter64
	MAX-ACCESS  read-only
	STATUS      current
	DESCRIPTION
	"Table entry attribute for qsyncEUpdateReceived"
	::={qsyncEUpdateReceivedLevelEntry 2}

qsyncEUpdateReceivedLevelMom OBJECT-TYPE
	SYNTAX	 CounterBasedGauge64
	MAX-ACCESS  read-only
	STATUS      current
	DESCRIPTION
	"Table entry attribute for qsyncEUpdateReceived"
	::={qsyncEUpdateReceivedLevelEntry 3}

qsyncEUpdateReceivedLevelMax OBJECT-TYPE
	SYNTAX	 CounterBasedGauge64
	MAX-ACCESS  read-only
	STATUS      current
	DESCRIPTION
	"Table entry attribute for qsyncEUpdateReceived"
	::={qsyncEUpdateReceivedLevelEntry 4}


qsyncEUpdateMismatch	OBJECT IDENTIFIER ::={qsync 25}

qsyncEUpdateMismatchVal	OBJECT-TYPE
	SYNTAX	 Counter64
	MAX-ACCESS read-only
	STATUS current
	DESCRIPTION "(ext update) Packets with mismatching ruleset received"

	::={qsyncEUpdateMismatch 1}

qsyncEUpdateMismatchMom	OBJECT-TYPE
	SYNTAX	 CounterBasedGauge64
	MAX-ACCESS read-only
	STATUS current
	DESCRIPTION "(ext update) Packets with mismatching ruleset received"

	::={qsyncEUpdateMismatch 2}

qsyncEUpdateMismatchMax	OBJECT-TYPE
	SYNTAX	 CounterBasedGauge64
	MAX-ACCESS read-only
	STATUS current
	DESCRIPTION "(ext update) Packets with mismatching ruleset received"

	::={qsyncEUpdateMismatch 3}

qsyncEUpdateMismatchLevelTable OBJECT-TYPE
	SYNTAX      SEQUENCE OF QsyncEUpdateMismatchLevelEntry
	MAX-ACCESS  not-accessible
	STATUS      current
	DESCRIPTION
	"Table for qsyncEUpdateMismatch"
	::={qsyncEUpdateMismatch 4}

qsyncEUpdateMismatchLevelEntry OBJECT-TYPE
	SYNTAX      QsyncEUpdateMismatchLevelEntry
	MAX-ACCESS  not-accessible
	STATUS      current
	DESCRIPTION
	"Table entry for qsyncEUpdateMismatch"
	INDEX { qsyncEUpdateMismatchLevelName }
	::={qsyncEUpdateMismatchLevelTable 1}

QsyncEUpdateMismatchLevelEntry ::=
	SEQUENCE {
		qsyncEUpdateMismatchLevelName	DisplayString,
		qsyncEUpdateMismatchLevelVal	Counter64,
		qsyncEUpdateMismatchLevelMom	CounterBasedGauge64,
		qsyncEUpdateMismatchLevelMax	CounterBasedGauge64
	}

qsyncEUpdateMismatchLevelName OBJECT-TYPE
	SYNTAX      DisplayString
	MAX-ACCESS  not-accessible
	STATUS      current
	DESCRIPTION
	"Table entry display string for qsyncEUpdateMismatch"
	::={qsyncEUpdateMismatchLevelEntry 1}

qsyncEUpdateMismatchLevelVal OBJECT-TYPE
	SYNTAX	 Counter64
	MAX-ACCESS  read-only
	STATUS      current
	DESCRIPTION
	"Table entry attribute for qsyncEUpdateMismatch"
	::={qsyncEUpdateMismatchLevelEntry 2}

qsyncEUpdateMismatchLevelMom OBJECT-TYPE
	SYNTAX	 CounterBasedGauge64
	MAX-ACCESS  read-only
	STATUS      current
	DESCRIPTION
	"Table entry attribute for qsyncEUpdateMismatch"
	::={qsyncEUpdateMismatchLevelEntry 3}

qsyncEUpdateMismatchLevelMax OBJECT-TYPE
	SYNTAX	 CounterBasedGauge64
	MAX-ACCESS  read-only
	STATUS      current
	DESCRIPTION
	"Table entry attribute for qsyncEUpdateMismatch"
	::={qsyncEUpdateMismatchLevelEntry 4}


qsyncEUpdatePktloss	OBJECT IDENTIFIER ::={qsync 26}

qsyncEUpdatePktlossVal	OBJECT-TYPE
	SYNTAX	 Counter64
	MAX-ACCESS read-only
	STATUS current
	DESCRIPTION "(ext update) Update packets lost"

	::={qsyncEUpdatePktloss 1}

qsyncEUpdatePktlossMom	OBJECT-TYPE
	SYNTAX	 CounterBasedGauge64
	MAX-ACCESS read-only
	STATUS current
	DESCRIPTION "(ext update) Update packets lost"

	::={qsyncEUpdatePktloss 2}

qsyncEUpdatePktlossMax	OBJECT-TYPE
	SYNTAX	 CounterBasedGauge64
	MAX-ACCESS read-only
	STATUS current
	DESCRIPTION "(ext update) Update packets lost"

	::={qsyncEUpdatePktloss 3}

qsyncEUpdatePktlossLevelTable OBJECT-TYPE
	SYNTAX      SEQUENCE OF QsyncEUpdatePktlossLevelEntry
	MAX-ACCESS  not-accessible
	STATUS      current
	DESCRIPTION
	"Table for qsyncEUpdatePktloss"
	::={qsyncEUpdatePktloss 4}

qsyncEUpdatePktlossLevelEntry OBJECT-TYPE
	SYNTAX      QsyncEUpdatePktlossLevelEntry
	MAX-ACCESS  not-accessible
	STATUS      current
	DESCRIPTION
	"Table entry for qsyncEUpdatePktloss"
	INDEX { qsyncEUpdatePktlossLevelName }
	::={qsyncEUpdatePktlossLevelTable 1}

QsyncEUpdatePktlossLevelEntry ::=
	SEQUENCE {
		qsyncEUpdatePktlossLevelName	DisplayString,
		qsyncEUpdatePktlossLevelVal	Counter64,
		qsyncEUpdatePktlossLevelMom	CounterBasedGauge64,
		qsyncEUpdatePktlossLevelMax	CounterBasedGauge64
	}

qsyncEUpdatePktlossLevelName OBJECT-TYPE
	SYNTAX      DisplayString
	MAX-ACCESS  not-accessible
	STATUS      current
	DESCRIPTION
	"Table entry display string for qsyncEUpdatePktloss"
	::={qsyncEUpdatePktlossLevelEntry 1}

qsyncEUpdatePktlossLevelVal OBJECT-TYPE
	SYNTAX	 Counter64
	MAX-ACCESS  read-only
	STATUS      current
	DESCRIPTION
	"Table entry attribute for qsyncEUpdatePktloss"
	::={qsyncEUpdatePktlossLevelEntry 2}

qsyncEUpdatePktlossLevelMom OBJECT-TYPE
	SYNTAX	 CounterBasedGauge64
	MAX-ACCESS  read-only
	STATUS      current
	DESCRIPTION
	"Table entry attribute for qsyncEUpdatePktloss"
	::={qsyncEUpdatePktlossLevelEntry 3}

qsyncEUpdatePktlossLevelMax OBJECT-TYPE
	SYNTAX	 CounterBasedGauge64
	MAX-ACCESS  read-only
	STATUS      current
	DESCRIPTION
	"Table entry attribute for qsyncEUpdatePktloss"
	::={qsyncEUpdatePktlossLevelEntry 4}


qsyncEStatusSent	OBJECT IDENTIFIER ::={qsync 27}

qsyncEStatusSentVal	OBJECT-TYPE
	SYNTAX	 Counter64
	MAX-ACCESS read-only
	STATUS current
	DESCRIPTION "(ext status) Status packets sent"

	::={qsyncEStatusSent 1}

qsyncEStatusSentMom	OBJECT-TYPE
	SYNTAX	 CounterBasedGauge64
	MAX-ACCESS read-only
	STATUS current
	DESCRIPTION "(ext status) Status packets sent"

	::={qsyncEStatusSent 2}

qsyncEStatusSentMax	OBJECT-TYPE
	SYNTAX	 CounterBasedGauge64
	MAX-ACCESS read-only
	STATUS current
	DESCRIPTION "(ext status) Status packets sent"

	::={qsyncEStatusSent 3}

qsyncEStatusSentLevelTable OBJECT-TYPE
	SYNTAX      SEQUENCE OF QsyncEStatusSentLevelEntry
	MAX-ACCESS  not-accessible
	STATUS      current
	DESCRIPTION
	"Table for qsyncEStatusSent"
	::={qsyncEStatusSent 4}

qsyncEStatusSentLevelEntry OBJECT-TYPE
	SYNTAX      QsyncEStatusSentLevelEntry
	MAX-ACCESS  not-accessible
	STATUS      current
	DESCRIPTION
	"Table entry for qsyncEStatusSent"
	INDEX { qsyncEStatusSentLevelName }
	::={qsyncEStatusSentLevelTable 1}

QsyncEStatusSentLevelEntry ::=
	SEQUENCE {
		qsyncEStatusSentLevelName	DisplayString,
		qsyncEStatusSentLevelVal	Counter64,
		qsyncEStatusSentLevelMom	CounterBasedGauge64,
		qsyncEStatusSentLevelMax	CounterBasedGauge64
	}

qsyncEStatusSentLevelName OBJECT-TYPE
	SYNTAX      DisplayString
	MAX-ACCESS  not-accessible
	STATUS      current
	DESCRIPTION
	"Table entry display string for qsyncEStatusSent"
	::={qsyncEStatusSentLevelEntry 1}

qsyncEStatusSentLevelVal OBJECT-TYPE
	SYNTAX	 Counter64
	MAX-ACCESS  read-only
	STATUS      current
	DESCRIPTION
	"Table entry attribute for qsyncEStatusSent"
	::={qsyncEStatusSentLevelEntry 2}

qsyncEStatusSentLevelMom OBJECT-TYPE
	SYNTAX	 CounterBasedGauge64
	MAX-ACCESS  read-only
	STATUS      current
	DESCRIPTION
	"Table entry attribute for qsyncEStatusSent"
	::={qsyncEStatusSentLevelEntry 3}

qsyncEStatusSentLevelMax OBJECT-TYPE
	SYNTAX	 CounterBasedGauge64
	MAX-ACCESS  read-only
	STATUS      current
	DESCRIPTION
	"Table entry attribute for qsyncEStatusSent"
	::={qsyncEStatusSentLevelEntry 4}


qsyncEStatusReceived	OBJECT IDENTIFIER ::={qsync 28}

qsyncEStatusReceivedVal	OBJECT-TYPE
	SYNTAX	 Counter64
	MAX-ACCESS read-only
	STATUS current
	DESCRIPTION "(ext status) Status packets received"

	::={qsyncEStatusReceived 1}

qsyncEStatusReceivedMom	OBJECT-TYPE
	SYNTAX	 CounterBasedGauge64
	MAX-ACCESS read-only
	STATUS current
	DESCRIPTION "(ext status) Status packets received"

	::={qsyncEStatusReceived 2}

qsyncEStatusReceivedMax	OBJECT-TYPE
	SYNTAX	 CounterBasedGauge64
	MAX-ACCESS read-only
	STATUS current
	DESCRIPTION "(ext status) Status packets received"

	::={qsyncEStatusReceived 3}

qsyncEStatusReceivedLevelTable OBJECT-TYPE
	SYNTAX      SEQUENCE OF QsyncEStatusReceivedLevelEntry
	MAX-ACCESS  not-accessible
	STATUS      current
	DESCRIPTION
	"Table for qsyncEStatusReceived"
	::={qsyncEStatusReceived 4}

qsyncEStatusReceivedLevelEntry OBJECT-TYPE
	SYNTAX      QsyncEStatusReceivedLevelEntry
	MAX-ACCESS  not-accessible
	STATUS      current
	DESCRIPTION
	"Table entry for qsyncEStatusReceived"
	INDEX { qsyncEStatusReceivedLevelName }
	::={qsyncEStatusReceivedLevelTable 1}

QsyncEStatusReceivedLevelEntry ::=
	SEQUENCE {
		qsyncEStatusReceivedLevelName	DisplayString,
		qsyncEStatusReceivedLevelVal	Counter64,
		qsyncEStatusReceivedLevelMom	CounterBasedGauge64,
		qsyncEStatusReceivedLevelMax	CounterBasedGauge64
	}

qsyncEStatusReceivedLevelName OBJECT-TYPE
	SYNTAX      DisplayString
	MAX-ACCESS  not-accessible
	STATUS      current
	DESCRIPTION
	"Table entry display string for qsyncEStatusReceived"
	::={qsyncEStatusReceivedLevelEntry 1}

qsyncEStatusReceivedLevelVal OBJECT-TYPE
	SYNTAX	 Counter64
	MAX-ACCESS  read-only
	STATUS      current
	DESCRIPTION
	"Table entry attribute for qsyncEStatusReceived"
	::={qsyncEStatusReceivedLevelEntry 2}

qsyncEStatusReceivedLevelMom OBJECT-TYPE
	SYNTAX	 CounterBasedGauge64
	MAX-ACCESS  read-only
	STATUS      current
	DESCRIPTION
	"Table entry attribute for qsyncEStatusReceived"
	::={qsyncEStatusReceivedLevelEntry 3}

qsyncEStatusReceivedLevelMax OBJECT-TYPE
	SYNTAX	 CounterBasedGauge64
	MAX-ACCESS  read-only
	STATUS      current
	DESCRIPTION
	"Table entry attribute for qsyncEStatusReceived"
	::={qsyncEStatusReceivedLevelEntry 4}


qsyncEStatusVersionMismatch	OBJECT IDENTIFIER ::={qsync 29}

qsyncEStatusVersionMismatchVal	OBJECT-TYPE
	SYNTAX	 Counter64
	MAX-ACCESS read-only
	STATUS current
	DESCRIPTION "(ext status) Version mismatch in status packets received"

	::={qsyncEStatusVersionMismatch 1}

qsyncEStatusVersionMismatchMom	OBJECT-TYPE
	SYNTAX	 CounterBasedGauge64
	MAX-ACCESS read-only
	STATUS current
	DESCRIPTION "(ext status) Version mismatch in status packets received"

	::={qsyncEStatusVersionMismatch 2}

qsyncEStatusVersionMismatchMax	OBJECT-TYPE
	SYNTAX	 CounterBasedGauge64
	MAX-ACCESS read-only
	STATUS current
	DESCRIPTION "(ext status) Version mismatch in status packets received"

	::={qsyncEStatusVersionMismatch 3}

qsyncEStatusVersionMismatchLevelTable OBJECT-TYPE
	SYNTAX      SEQUENCE OF QsyncEStatusVersionMismatchLevelEntry
	MAX-ACCESS  not-accessible
	STATUS      current
	DESCRIPTION
	"Table for qsyncEStatusVersionMismatch"
	::={qsyncEStatusVersionMismatch 4}

qsyncEStatusVersionMismatchLevelEntry OBJECT-TYPE
	SYNTAX      QsyncEStatusVersionMismatchLevelEntry
	MAX-ACCESS  not-accessible
	STATUS      current
	DESCRIPTION
	"Table entry for qsyncEStatusVersionMismatch"
	INDEX { qsyncEStatusVersionMismatchLevelName }
	::={qsyncEStatusVersionMismatchLevelTable 1}

QsyncEStatusVersionMismatchLevelEntry ::=
	SEQUENCE {
		qsyncEStatusVersionMismatchLevelName	DisplayString,
		qsyncEStatusVersionMismatchLevelVal	Counter64,
		qsyncEStatusVersionMismatchLevelMom	CounterBasedGauge64,
		qsyncEStatusVersionMismatchLevelMax	CounterBasedGauge64
	}

qsyncEStatusVersionMismatchLevelName OBJECT-TYPE
	SYNTAX      DisplayString
	MAX-ACCESS  not-accessible
	STATUS      current
	DESCRIPTION
	"Table entry display string for qsyncEStatusVersionMismatch"
	::={qsyncEStatusVersionMismatchLevelEntry 1}

qsyncEStatusVersionMismatchLevelVal OBJECT-TYPE
	SYNTAX	 Counter64
	MAX-ACCESS  read-only
	STATUS      current
	DESCRIPTION
	"Table entry attribute for qsyncEStatusVersionMismatch"
	::={qsyncEStatusVersionMismatchLevelEntry 2}

qsyncEStatusVersionMismatchLevelMom OBJECT-TYPE
	SYNTAX	 CounterBasedGauge64
	MAX-ACCESS  read-only
	STATUS      current
	DESCRIPTION
	"Table entry attribute for qsyncEStatusVersionMismatch"
	::={qsyncEStatusVersionMismatchLevelEntry 3}

qsyncEStatusVersionMismatchLevelMax OBJECT-TYPE
	SYNTAX	 CounterBasedGauge64
	MAX-ACCESS  read-only
	STATUS      current
	DESCRIPTION
	"Table entry attribute for qsyncEStatusVersionMismatch"
	::={qsyncEStatusVersionMismatchLevelEntry 4}


qsyncEStatusInvalid	OBJECT IDENTIFIER ::={qsync 30}

qsyncEStatusInvalidVal	OBJECT-TYPE
	SYNTAX	 Counter64
	MAX-ACCESS read-only
	STATUS current
	DESCRIPTION "(ext status) Invalid packets received"

	::={qsyncEStatusInvalid 1}

qsyncEStatusInvalidMom	OBJECT-TYPE
	SYNTAX	 CounterBasedGauge64
	MAX-ACCESS read-only
	STATUS current
	DESCRIPTION "(ext status) Invalid packets received"

	::={qsyncEStatusInvalid 2}

qsyncEStatusInvalidMax	OBJECT-TYPE
	SYNTAX	 CounterBasedGauge64
	MAX-ACCESS read-only
	STATUS current
	DESCRIPTION "(ext status) Invalid packets received"

	::={qsyncEStatusInvalid 3}

qsyncEStatusInvalidLevelTable OBJECT-TYPE
	SYNTAX      SEQUENCE OF QsyncEStatusInvalidLevelEntry
	MAX-ACCESS  not-accessible
	STATUS      current
	DESCRIPTION
	"Table for qsyncEStatusInvalid"
	::={qsyncEStatusInvalid 4}

qsyncEStatusInvalidLevelEntry OBJECT-TYPE
	SYNTAX      QsyncEStatusInvalidLevelEntry
	MAX-ACCESS  not-accessible
	STATUS      current
	DESCRIPTION
	"Table entry for qsyncEStatusInvalid"
	INDEX { qsyncEStatusInvalidLevelName }
	::={qsyncEStatusInvalidLevelTable 1}

QsyncEStatusInvalidLevelEntry ::=
	SEQUENCE {
		qsyncEStatusInvalidLevelName	DisplayString,
		qsyncEStatusInvalidLevelVal	Counter64,
		qsyncEStatusInvalidLevelMom	CounterBasedGauge64,
		qsyncEStatusInvalidLevelMax	CounterBasedGauge64
	}

qsyncEStatusInvalidLevelName OBJECT-TYPE
	SYNTAX      DisplayString
	MAX-ACCESS  not-accessible
	STATUS      current
	DESCRIPTION
	"Table entry display string for qsyncEStatusInvalid"
	::={qsyncEStatusInvalidLevelEntry 1}

qsyncEStatusInvalidLevelVal OBJECT-TYPE
	SYNTAX	 Counter64
	MAX-ACCESS  read-only
	STATUS      current
	DESCRIPTION
	"Table entry attribute for qsyncEStatusInvalid"
	::={qsyncEStatusInvalidLevelEntry 2}

qsyncEStatusInvalidLevelMom OBJECT-TYPE
	SYNTAX	 CounterBasedGauge64
	MAX-ACCESS  read-only
	STATUS      current
	DESCRIPTION
	"Table entry attribute for qsyncEStatusInvalid"
	::={qsyncEStatusInvalidLevelEntry 3}

qsyncEStatusInvalidLevelMax OBJECT-TYPE
	SYNTAX	 CounterBasedGauge64
	MAX-ACCESS  read-only
	STATUS      current
	DESCRIPTION
	"Table entry attribute for qsyncEStatusInvalid"
	::={qsyncEStatusInvalidLevelEntry 4}


qsyncEStatusPktloss	OBJECT IDENTIFIER ::={qsync 31}

qsyncEStatusPktlossVal	OBJECT-TYPE
	SYNTAX	 Counter64
	MAX-ACCESS read-only
	STATUS current
	DESCRIPTION "(ext status) Status packets lost"

	::={qsyncEStatusPktloss 1}

qsyncEStatusPktlossMom	OBJECT-TYPE
	SYNTAX	 CounterBasedGauge64
	MAX-ACCESS read-only
	STATUS current
	DESCRIPTION "(ext status) Status packets lost"

	::={qsyncEStatusPktloss 2}

qsyncEStatusPktlossMax	OBJECT-TYPE
	SYNTAX	 CounterBasedGauge64
	MAX-ACCESS read-only
	STATUS current
	DESCRIPTION "(ext status) Status packets lost"

	::={qsyncEStatusPktloss 3}

qsyncEStatusPktlossLevelTable OBJECT-TYPE
	SYNTAX      SEQUENCE OF QsyncEStatusPktlossLevelEntry
	MAX-ACCESS  not-accessible
	STATUS      current
	DESCRIPTION
	"Table for qsyncEStatusPktloss"
	::={qsyncEStatusPktloss 4}

qsyncEStatusPktlossLevelEntry OBJECT-TYPE
	SYNTAX      QsyncEStatusPktlossLevelEntry
	MAX-ACCESS  not-accessible
	STATUS      current
	DESCRIPTION
	"Table entry for qsyncEStatusPktloss"
	INDEX { qsyncEStatusPktlossLevelName }
	::={qsyncEStatusPktlossLevelTable 1}

QsyncEStatusPktlossLevelEntry ::=
	SEQUENCE {
		qsyncEStatusPktlossLevelName	DisplayString,
		qsyncEStatusPktlossLevelVal	Counter64,
		qsyncEStatusPktlossLevelMom	CounterBasedGauge64,
		qsyncEStatusPktlossLevelMax	CounterBasedGauge64
	}

qsyncEStatusPktlossLevelName OBJECT-TYPE
	SYNTAX      DisplayString
	MAX-ACCESS  not-accessible
	STATUS      current
	DESCRIPTION
	"Table entry display string for qsyncEStatusPktloss"
	::={qsyncEStatusPktlossLevelEntry 1}

qsyncEStatusPktlossLevelVal OBJECT-TYPE
	SYNTAX	 Counter64
	MAX-ACCESS  read-only
	STATUS      current
	DESCRIPTION
	"Table entry attribute for qsyncEStatusPktloss"
	::={qsyncEStatusPktlossLevelEntry 2}

qsyncEStatusPktlossLevelMom OBJECT-TYPE
	SYNTAX	 CounterBasedGauge64
	MAX-ACCESS  read-only
	STATUS      current
	DESCRIPTION
	"Table entry attribute for qsyncEStatusPktloss"
	::={qsyncEStatusPktlossLevelEntry 3}

qsyncEStatusPktlossLevelMax OBJECT-TYPE
	SYNTAX	 CounterBasedGauge64
	MAX-ACCESS  read-only
	STATUS      current
	DESCRIPTION
	"Table entry attribute for qsyncEStatusPktloss"
	::={qsyncEStatusPktlossLevelEntry 4}


qsyncEStatusOutOfOrder	OBJECT IDENTIFIER ::={qsync 32}

qsyncEStatusOutOfOrderVal	OBJECT-TYPE
	SYNTAX	 Counter64
	MAX-ACCESS read-only
	STATUS current
	DESCRIPTION "(ext status) Status packets late/out of order"

	::={qsyncEStatusOutOfOrder 1}

qsyncEStatusOutOfOrderMom	OBJECT-TYPE
	SYNTAX	 CounterBasedGauge64
	MAX-ACCESS read-only
	STATUS current
	DESCRIPTION "(ext status) Status packets late/out of order"

	::={qsyncEStatusOutOfOrder 2}

qsyncEStatusOutOfOrderMax	OBJECT-TYPE
	SYNTAX	 CounterBasedGauge64
	MAX-ACCESS read-only
	STATUS current
	DESCRIPTION "(ext status) Status packets late/out of order"

	::={qsyncEStatusOutOfOrder 3}

qsyncEStatusOutOfOrderLevelTable OBJECT-TYPE
	SYNTAX      SEQUENCE OF QsyncEStatusOutOfOrderLevelEntry
	MAX-ACCESS  not-accessible
	STATUS      current
	DESCRIPTION
	"Table for qsyncEStatusOutOfOrder"
	::={qsyncEStatusOutOfOrder 4}

qsyncEStatusOutOfOrderLevelEntry OBJECT-TYPE
	SYNTAX      QsyncEStatusOutOfOrderLevelEntry
	MAX-ACCESS  not-accessible
	STATUS      current
	DESCRIPTION
	"Table entry for qsyncEStatusOutOfOrder"
	INDEX { qsyncEStatusOutOfOrderLevelName }
	::={qsyncEStatusOutOfOrderLevelTable 1}

QsyncEStatusOutOfOrderLevelEntry ::=
	SEQUENCE {
		qsyncEStatusOutOfOrderLevelName	DisplayString,
		qsyncEStatusOutOfOrderLevelVal	Counter64,
		qsyncEStatusOutOfOrderLevelMom	CounterBasedGauge64,
		qsyncEStatusOutOfOrderLevelMax	CounterBasedGauge64
	}

qsyncEStatusOutOfOrderLevelName OBJECT-TYPE
	SYNTAX      DisplayString
	MAX-ACCESS  not-accessible
	STATUS      current
	DESCRIPTION
	"Table entry display string for qsyncEStatusOutOfOrder"
	::={qsyncEStatusOutOfOrderLevelEntry 1}

qsyncEStatusOutOfOrderLevelVal OBJECT-TYPE
	SYNTAX	 Counter64
	MAX-ACCESS  read-only
	STATUS      current
	DESCRIPTION
	"Table entry attribute for qsyncEStatusOutOfOrder"
	::={qsyncEStatusOutOfOrderLevelEntry 2}

qsyncEStatusOutOfOrderLevelMom OBJECT-TYPE
	SYNTAX	 CounterBasedGauge64
	MAX-ACCESS  read-only
	STATUS      current
	DESCRIPTION
	"Table entry attribute for qsyncEStatusOutOfOrder"
	::={qsyncEStatusOutOfOrderLevelEntry 3}

qsyncEStatusOutOfOrderLevelMax OBJECT-TYPE
	SYNTAX	 CounterBasedGauge64
	MAX-ACCESS  read-only
	STATUS      current
	DESCRIPTION
	"Table entry attribute for qsyncEStatusOutOfOrder"
	::={qsyncEStatusOutOfOrderLevelEntry 4}


qsyncETimeouts	OBJECT IDENTIFIER ::={qsync 33}

qsyncETimeoutsVal	OBJECT-TYPE
	SYNTAX	 Counter64
	MAX-ACCESS read-only
	STATUS current
	DESCRIPTION "(ext timeout) Number of timeouts of peer"

	::={qsyncETimeouts 1}

qsyncETimeoutsMom	OBJECT-TYPE
	SYNTAX	 CounterBasedGauge64
	MAX-ACCESS read-only
	STATUS current
	DESCRIPTION "(ext timeout) Number of timeouts of peer"

	::={qsyncETimeouts 2}

qsyncETimeoutsMax	OBJECT-TYPE
	SYNTAX	 CounterBasedGauge64
	MAX-ACCESS read-only
	STATUS current
	DESCRIPTION "(ext timeout) Number of timeouts of peer"

	::={qsyncETimeouts 3}

qsyncETimeoutsLevelTable OBJECT-TYPE
	SYNTAX      SEQUENCE OF QsyncETimeoutsLevelEntry
	MAX-ACCESS  not-accessible
	STATUS      current
	DESCRIPTION
	"Table for qsyncETimeouts"
	::={qsyncETimeouts 4}

qsyncETimeoutsLevelEntry OBJECT-TYPE
	SYNTAX      QsyncETimeoutsLevelEntry
	MAX-ACCESS  not-accessible
	STATUS      current
	DESCRIPTION
	"Table entry for qsyncETimeouts"
	INDEX { qsyncETimeoutsLevelName }
	::={qsyncETimeoutsLevelTable 1}

QsyncETimeoutsLevelEntry ::=
	SEQUENCE {
		qsyncETimeoutsLevelName	DisplayString,
		qsyncETimeoutsLevelVal	Counter64,
		qsyncETimeoutsLevelMom	CounterBasedGauge64,
		qsyncETimeoutsLevelMax	CounterBasedGauge64
	}

qsyncETimeoutsLevelName OBJECT-TYPE
	SYNTAX      DisplayString
	MAX-ACCESS  not-accessible
	STATUS      current
	DESCRIPTION
	"Table entry display string for qsyncETimeouts"
	::={qsyncETimeoutsLevelEntry 1}

qsyncETimeoutsLevelVal OBJECT-TYPE
	SYNTAX	 Counter64
	MAX-ACCESS  read-only
	STATUS      current
	DESCRIPTION
	"Table entry attribute for qsyncETimeouts"
	::={qsyncETimeoutsLevelEntry 2}

qsyncETimeoutsLevelMom OBJECT-TYPE
	SYNTAX	 CounterBasedGauge64
	MAX-ACCESS  read-only
	STATUS      current
	DESCRIPTION
	"Table entry attribute for qsyncETimeouts"
	::={qsyncETimeoutsLevelEntry 3}

qsyncETimeoutsLevelMax OBJECT-TYPE
	SYNTAX	 CounterBasedGauge64
	MAX-ACCESS  read-only
	STATUS      current
	DESCRIPTION
	"Table entry attribute for qsyncETimeouts"
	::={qsyncETimeoutsLevelEntry 4}


qsyncELastTimeout	OBJECT IDENTIFIER ::={qsync 34}

qsyncELastTimeoutVal	OBJECT-TYPE
	SYNTAX	 DateAndTime
	MAX-ACCESS read-only
	STATUS current
	DESCRIPTION "(ext timeout) Last timeout of peer"

	::={qsyncELastTimeout 1}

qsyncELastTimeoutLevelTable OBJECT-TYPE
	SYNTAX      SEQUENCE OF QsyncELastTimeoutLevelEntry
	MAX-ACCESS  not-accessible
	STATUS      current
	DESCRIPTION
	"Table for qsyncELastTimeout"
	::={qsyncELastTimeout 2}

qsyncELastTimeoutLevelEntry OBJECT-TYPE
	SYNTAX      QsyncELastTimeoutLevelEntry
	MAX-ACCESS  not-accessible
	STATUS      current
	DESCRIPTION
	"Table entry for qsyncELastTimeout"
	INDEX { qsyncELastTimeoutLevelName }
	::={qsyncELastTimeoutLevelTable 1}

QsyncELastTimeoutLevelEntry ::=
	SEQUENCE {
		qsyncELastTimeoutLevelName	DisplayString,
		qsyncELastTimeoutLevelVal	DateAndTime
	}

qsyncELastTimeoutLevelName OBJECT-TYPE
	SYNTAX      DisplayString
	MAX-ACCESS  not-accessible
	STATUS      current
	DESCRIPTION
	"Table entry display string for qsyncELastTimeout"
	::={qsyncELastTimeoutLevelEntry 1}

qsyncELastTimeoutLevelVal OBJECT-TYPE
	SYNTAX	 DateAndTime
	MAX-ACCESS  read-only
	STATUS      current
	DESCRIPTION
	"Table entry attribute for qsyncELastTimeout"
	::={qsyncELastTimeoutLevelEntry 2}


qsyncEBlacklistedPeerPackets	OBJECT IDENTIFIER ::={qsync 35}

qsyncEBlacklistedPeerPacketsVal	OBJECT-TYPE
	SYNTAX	 Counter64
	MAX-ACCESS read-only
	STATUS current
	DESCRIPTION "(ext) Number of packets from blacklisted peers"

	::={qsyncEBlacklistedPeerPackets 1}

qsyncEBlacklistedPeerPacketsMom	OBJECT-TYPE
	SYNTAX	 CounterBasedGauge64
	MAX-ACCESS read-only
	STATUS current
	DESCRIPTION "(ext) Number of packets from blacklisted peers"

	::={qsyncEBlacklistedPeerPackets 2}

qsyncEBlacklistedPeerPacketsMax	OBJECT-TYPE
	SYNTAX	 CounterBasedGauge64
	MAX-ACCESS read-only
	STATUS current
	DESCRIPTION "(ext) Number of packets from blacklisted peers"

	::={qsyncEBlacklistedPeerPackets 3}

qsyncEBlacklistedPeerPacketsLevelTable OBJECT-TYPE
	SYNTAX      SEQUENCE OF QsyncEBlacklistedPeerPacketsLevelEntry
	MAX-ACCESS  not-accessible
	STATUS      current
	DESCRIPTION
	"Table for qsyncEBlacklistedPeerPackets"
	::={qsyncEBlacklistedPeerPackets 4}

qsyncEBlacklistedPeerPacketsLevelEntry OBJECT-TYPE
	SYNTAX      QsyncEBlacklistedPeerPacketsLevelEntry
	MAX-ACCESS  not-accessible
	STATUS      current
	DESCRIPTION
	"Table entry for qsyncEBlacklistedPeerPackets"
	INDEX { qsyncEBlacklistedPeerPacketsLevelName }
	::={qsyncEBlacklistedPeerPacketsLevelTable 1}

QsyncEBlacklistedPeerPacketsLevelEntry ::=
	SEQUENCE {
		qsyncEBlacklistedPeerPacketsLevelName	DisplayString,
		qsyncEBlacklistedPeerPacketsLevelVal	Counter64,
		qsyncEBlacklistedPeerPacketsLevelMom	CounterBasedGauge64,
		qsyncEBlacklistedPeerPacketsLevelMax	CounterBasedGauge64
	}

qsyncEBlacklistedPeerPacketsLevelName OBJECT-TYPE
	SYNTAX      DisplayString
	MAX-ACCESS  not-accessible
	STATUS      current
	DESCRIPTION
	"Table entry display string for qsyncEBlacklistedPeerPackets"
	::={qsyncEBlacklistedPeerPacketsLevelEntry 1}

qsyncEBlacklistedPeerPacketsLevelVal OBJECT-TYPE
	SYNTAX	 Counter64
	MAX-ACCESS  read-only
	STATUS      current
	DESCRIPTION
	"Table entry attribute for qsyncEBlacklistedPeerPackets"
	::={qsyncEBlacklistedPeerPacketsLevelEntry 2}

qsyncEBlacklistedPeerPacketsLevelMom OBJECT-TYPE
	SYNTAX	 CounterBasedGauge64
	MAX-ACCESS  read-only
	STATUS      current
	DESCRIPTION
	"Table entry attribute for qsyncEBlacklistedPeerPackets"
	::={qsyncEBlacklistedPeerPacketsLevelEntry 3}

qsyncEBlacklistedPeerPacketsLevelMax OBJECT-TYPE
	SYNTAX	 CounterBasedGauge64
	MAX-ACCESS  read-only
	STATUS      current
	DESCRIPTION
	"Table entry attribute for qsyncEBlacklistedPeerPackets"
	::={qsyncEBlacklistedPeerPacketsLevelEntry 4}


shapingcounter	OBJECT IDENTIFIER ::={sysdiag 124}

shapingcounterUpdates	OBJECT IDENTIFIER ::={shapingcounter 1}

shapingcounterUpdatesVal	OBJECT-TYPE
	SYNTAX	 Counter64
	MAX-ACCESS read-only
	STATUS current
	DESCRIPTION "Updates received"

	::={shapingcounterUpdates 1}

shapingcounterUpdatesMom	OBJECT-TYPE
	SYNTAX	 CounterBasedGauge64
	MAX-ACCESS read-only
	STATUS current
	DESCRIPTION "Updates received"

	::={shapingcounterUpdates 2}

shapingcounterUpdatesMax	OBJECT-TYPE
	SYNTAX	 CounterBasedGauge64
	MAX-ACCESS read-only
	STATUS current
	DESCRIPTION "Updates received"

	::={shapingcounterUpdates 3}

shapingcounterUpdatesLevelTable OBJECT-TYPE
	SYNTAX      SEQUENCE OF ShapingcounterUpdatesLevelEntry
	MAX-ACCESS  not-accessible
	STATUS      current
	DESCRIPTION
	"Table for shapingcounterUpdates"
	::={shapingcounterUpdates 4}

shapingcounterUpdatesLevelEntry OBJECT-TYPE
	SYNTAX      ShapingcounterUpdatesLevelEntry
	MAX-ACCESS  not-accessible
	STATUS      current
	DESCRIPTION
	"Table entry for shapingcounterUpdates"
	INDEX { shapingcounterUpdatesLevelName }
	::={shapingcounterUpdatesLevelTable 1}

ShapingcounterUpdatesLevelEntry ::=
	SEQUENCE {
		shapingcounterUpdatesLevelName	DisplayString,
		shapingcounterUpdatesLevelVal	Counter64,
		shapingcounterUpdatesLevelMom	CounterBasedGauge64,
		shapingcounterUpdatesLevelMax	CounterBasedGauge64
	}

shapingcounterUpdatesLevelName OBJECT-TYPE
	SYNTAX      DisplayString
	MAX-ACCESS  not-accessible
	STATUS      current
	DESCRIPTION
	"Table entry display string for shapingcounterUpdates"
	::={shapingcounterUpdatesLevelEntry 1}

shapingcounterUpdatesLevelVal OBJECT-TYPE
	SYNTAX	 Counter64
	MAX-ACCESS  read-only
	STATUS      current
	DESCRIPTION
	"Table entry attribute for shapingcounterUpdates"
	::={shapingcounterUpdatesLevelEntry 2}

shapingcounterUpdatesLevelMom OBJECT-TYPE
	SYNTAX	 CounterBasedGauge64
	MAX-ACCESS  read-only
	STATUS      current
	DESCRIPTION
	"Table entry attribute for shapingcounterUpdates"
	::={shapingcounterUpdatesLevelEntry 3}

shapingcounterUpdatesLevelMax OBJECT-TYPE
	SYNTAX	 CounterBasedGauge64
	MAX-ACCESS  read-only
	STATUS      current
	DESCRIPTION
	"Table entry attribute for shapingcounterUpdates"
	::={shapingcounterUpdatesLevelEntry 4}


shapingcounterActive	OBJECT IDENTIFIER ::={shapingcounter 2}

shapingcounterActiveVal	OBJECT-TYPE
	SYNTAX	 CounterBasedGauge64
	MAX-ACCESS read-only
	STATUS current
	DESCRIPTION "Active counters"

	::={shapingcounterActive 1}

shapingcounterActiveMax	OBJECT-TYPE
	SYNTAX	 CounterBasedGauge64
	MAX-ACCESS read-only
	STATUS current
	DESCRIPTION "Active counters"

	::={shapingcounterActive 3}

shapingcounterActiveLevelTable OBJECT-TYPE
	SYNTAX      SEQUENCE OF ShapingcounterActiveLevelEntry
	MAX-ACCESS  not-accessible
	STATUS      current
	DESCRIPTION
	"Table for shapingcounterActive"
	::={shapingcounterActive 4}

shapingcounterActiveLevelEntry OBJECT-TYPE
	SYNTAX      ShapingcounterActiveLevelEntry
	MAX-ACCESS  not-accessible
	STATUS      current
	DESCRIPTION
	"Table entry for shapingcounterActive"
	INDEX { shapingcounterActiveLevelName }
	::={shapingcounterActiveLevelTable 1}

ShapingcounterActiveLevelEntry ::=
	SEQUENCE {
		shapingcounterActiveLevelName	DisplayString,
		shapingcounterActiveLevelVal	CounterBasedGauge64,
		shapingcounterActiveLevelMax	CounterBasedGauge64
	}

shapingcounterActiveLevelName OBJECT-TYPE
	SYNTAX      DisplayString
	MAX-ACCESS  not-accessible
	STATUS      current
	DESCRIPTION
	"Table entry display string for shapingcounterActive"
	::={shapingcounterActiveLevelEntry 1}

shapingcounterActiveLevelVal OBJECT-TYPE
	SYNTAX	 CounterBasedGauge64
	MAX-ACCESS  read-only
	STATUS      current
	DESCRIPTION
	"Table entry attribute for shapingcounterActive"
	::={shapingcounterActiveLevelEntry 2}

shapingcounterActiveLevelMax OBJECT-TYPE
	SYNTAX	 CounterBasedGauge64
	MAX-ACCESS  read-only
	STATUS      current
	DESCRIPTION
	"Table entry attribute for shapingcounterActive"
	::={shapingcounterActiveLevelEntry 4}


shapingcounterClients	OBJECT IDENTIFIER ::={shapingcounter 3}

shapingcounterClientsVal	OBJECT-TYPE
	SYNTAX	 CounterBasedGauge64
	MAX-ACCESS read-only
	STATUS current
	DESCRIPTION "Active clients"

	::={shapingcounterClients 1}

shapingcounterClientsMax	OBJECT-TYPE
	SYNTAX	 CounterBasedGauge64
	MAX-ACCESS read-only
	STATUS current
	DESCRIPTION "Active clients"

	::={shapingcounterClients 3}

shapingcounterClientsLevelTable OBJECT-TYPE
	SYNTAX      SEQUENCE OF ShapingcounterClientsLevelEntry
	MAX-ACCESS  not-accessible
	STATUS      current
	DESCRIPTION
	"Table for shapingcounterClients"
	::={shapingcounterClients 4}

shapingcounterClientsLevelEntry OBJECT-TYPE
	SYNTAX      ShapingcounterClientsLevelEntry
	MAX-ACCESS  not-accessible
	STATUS      current
	DESCRIPTION
	"Table entry for shapingcounterClients"
	INDEX { shapingcounterClientsLevelName }
	::={shapingcounterClientsLevelTable 1}

ShapingcounterClientsLevelEntry ::=
	SEQUENCE {
		shapingcounterClientsLevelName	DisplayString,
		shapingcounterClientsLevelVal	CounterBasedGauge64,
		shapingcounterClientsLevelMax	CounterBasedGauge64
	}

shapingcounterClientsLevelName OBJECT-TYPE
	SYNTAX      DisplayString
	MAX-ACCESS  not-accessible
	STATUS      current
	DESCRIPTION
	"Table entry display string for shapingcounterClients"
	::={shapingcounterClientsLevelEntry 1}

shapingcounterClientsLevelVal OBJECT-TYPE
	SYNTAX	 CounterBasedGauge64
	MAX-ACCESS  read-only
	STATUS      current
	DESCRIPTION
	"Table entry attribute for shapingcounterClients"
	::={shapingcounterClientsLevelEntry 2}

shapingcounterClientsLevelMax OBJECT-TYPE
	SYNTAX	 CounterBasedGauge64
	MAX-ACCESS  read-only
	STATUS      current
	DESCRIPTION
	"Table entry attribute for shapingcounterClients"
	::={shapingcounterClientsLevelEntry 4}


shapingcounterRecycle	OBJECT IDENTIFIER ::={shapingcounter 4}

shapingcounterRecycleVal	OBJECT-TYPE
	SYNTAX	 Counter64
	MAX-ACCESS read-only
	STATUS current
	DESCRIPTION "Recycles"

	::={shapingcounterRecycle 1}

shapingcounterRecycleMom	OBJECT-TYPE
	SYNTAX	 CounterBasedGauge64
	MAX-ACCESS read-only
	STATUS current
	DESCRIPTION "Recycles"

	::={shapingcounterRecycle 2}

shapingcounterRecycleMax	OBJECT-TYPE
	SYNTAX	 CounterBasedGauge64
	MAX-ACCESS read-only
	STATUS current
	DESCRIPTION "Recycles"

	::={shapingcounterRecycle 3}

shapingcounterRecycleLevelTable OBJECT-TYPE
	SYNTAX      SEQUENCE OF ShapingcounterRecycleLevelEntry
	MAX-ACCESS  not-accessible
	STATUS      current
	DESCRIPTION
	"Table for shapingcounterRecycle"
	::={shapingcounterRecycle 4}

shapingcounterRecycleLevelEntry OBJECT-TYPE
	SYNTAX      ShapingcounterRecycleLevelEntry
	MAX-ACCESS  not-accessible
	STATUS      current
	DESCRIPTION
	"Table entry for shapingcounterRecycle"
	INDEX { shapingcounterRecycleLevelName }
	::={shapingcounterRecycleLevelTable 1}

ShapingcounterRecycleLevelEntry ::=
	SEQUENCE {
		shapingcounterRecycleLevelName	DisplayString,
		shapingcounterRecycleLevelVal	Counter64,
		shapingcounterRecycleLevelMom	CounterBasedGauge64,
		shapingcounterRecycleLevelMax	CounterBasedGauge64
	}

shapingcounterRecycleLevelName OBJECT-TYPE
	SYNTAX      DisplayString
	MAX-ACCESS  not-accessible
	STATUS      current
	DESCRIPTION
	"Table entry display string for shapingcounterRecycle"
	::={shapingcounterRecycleLevelEntry 1}

shapingcounterRecycleLevelVal OBJECT-TYPE
	SYNTAX	 Counter64
	MAX-ACCESS  read-only
	STATUS      current
	DESCRIPTION
	"Table entry attribute for shapingcounterRecycle"
	::={shapingcounterRecycleLevelEntry 2}

shapingcounterRecycleLevelMom OBJECT-TYPE
	SYNTAX	 CounterBasedGauge64
	MAX-ACCESS  read-only
	STATUS      current
	DESCRIPTION
	"Table entry attribute for shapingcounterRecycle"
	::={shapingcounterRecycleLevelEntry 3}

shapingcounterRecycleLevelMax OBJECT-TYPE
	SYNTAX	 CounterBasedGauge64
	MAX-ACCESS  read-only
	STATUS      current
	DESCRIPTION
	"Table entry attribute for shapingcounterRecycle"
	::={shapingcounterRecycleLevelEntry 4}


shapingcounterUpdatesInteresting	OBJECT IDENTIFIER ::={shapingcounter 5}

shapingcounterUpdatesInterestingVal	OBJECT-TYPE
	SYNTAX	 Counter64
	MAX-ACCESS read-only
	STATUS current
	DESCRIPTION "Updates crossing granularity boundary received"

	::={shapingcounterUpdatesInteresting 1}

shapingcounterUpdatesInterestingMom	OBJECT-TYPE
	SYNTAX	 CounterBasedGauge64
	MAX-ACCESS read-only
	STATUS current
	DESCRIPTION "Updates crossing granularity boundary received"

	::={shapingcounterUpdatesInteresting 2}

shapingcounterUpdatesInterestingMax	OBJECT-TYPE
	SYNTAX	 CounterBasedGauge64
	MAX-ACCESS read-only
	STATUS current
	DESCRIPTION "Updates crossing granularity boundary received"

	::={shapingcounterUpdatesInteresting 3}

shapingcounterUpdatesInterestingLevelTable OBJECT-TYPE
	SYNTAX      SEQUENCE OF ShapingcounterUpdatesInterestingLevelEntry
	MAX-ACCESS  not-accessible
	STATUS      current
	DESCRIPTION
	"Table for shapingcounterUpdatesInteresting"
	::={shapingcounterUpdatesInteresting 4}

shapingcounterUpdatesInterestingLevelEntry OBJECT-TYPE
	SYNTAX      ShapingcounterUpdatesInterestingLevelEntry
	MAX-ACCESS  not-accessible
	STATUS      current
	DESCRIPTION
	"Table entry for shapingcounterUpdatesInteresting"
	INDEX { shapingcounterUpdatesInterestingLevelName }
	::={shapingcounterUpdatesInterestingLevelTable 1}

ShapingcounterUpdatesInterestingLevelEntry ::=
	SEQUENCE {
		shapingcounterUpdatesInterestingLevelName	DisplayString,
		shapingcounterUpdatesInterestingLevelVal	Counter64,
		shapingcounterUpdatesInterestingLevelMom	CounterBasedGauge64,
		shapingcounterUpdatesInterestingLevelMax	CounterBasedGauge64
	}

shapingcounterUpdatesInterestingLevelName OBJECT-TYPE
	SYNTAX      DisplayString
	MAX-ACCESS  not-accessible
	STATUS      current
	DESCRIPTION
	"Table entry display string for shapingcounterUpdatesInteresting"
	::={shapingcounterUpdatesInterestingLevelEntry 1}

shapingcounterUpdatesInterestingLevelVal OBJECT-TYPE
	SYNTAX	 Counter64
	MAX-ACCESS  read-only
	STATUS      current
	DESCRIPTION
	"Table entry attribute for shapingcounterUpdatesInteresting"
	::={shapingcounterUpdatesInterestingLevelEntry 2}

shapingcounterUpdatesInterestingLevelMom OBJECT-TYPE
	SYNTAX	 CounterBasedGauge64
	MAX-ACCESS  read-only
	STATUS      current
	DESCRIPTION
	"Table entry attribute for shapingcounterUpdatesInteresting"
	::={shapingcounterUpdatesInterestingLevelEntry 3}

shapingcounterUpdatesInterestingLevelMax OBJECT-TYPE
	SYNTAX	 CounterBasedGauge64
	MAX-ACCESS  read-only
	STATUS      current
	DESCRIPTION
	"Table entry attribute for shapingcounterUpdatesInteresting"
	::={shapingcounterUpdatesInterestingLevelEntry 4}


shapingcounterSubscribers	OBJECT IDENTIFIER ::={shapingcounter 6}

shapingcounterSubscribersVal	OBJECT-TYPE
	SYNTAX	 CounterBasedGauge64
	MAX-ACCESS read-only
	STATUS current
	DESCRIPTION "Number of subscribers in table"

	::={shapingcounterSubscribers 1}

shapingcounterSubscribersMax	OBJECT-TYPE
	SYNTAX	 CounterBasedGauge64
	MAX-ACCESS read-only
	STATUS current
	DESCRIPTION "Number of subscribers in table"

	::={shapingcounterSubscribers 3}

shapingcounterSubscribersLevelTable OBJECT-TYPE
	SYNTAX      SEQUENCE OF ShapingcounterSubscribersLevelEntry
	MAX-ACCESS  not-accessible
	STATUS      current
	DESCRIPTION
	"Table for shapingcounterSubscribers"
	::={shapingcounterSubscribers 4}

shapingcounterSubscribersLevelEntry OBJECT-TYPE
	SYNTAX      ShapingcounterSubscribersLevelEntry
	MAX-ACCESS  not-accessible
	STATUS      current
	DESCRIPTION
	"Table entry for shapingcounterSubscribers"
	INDEX { shapingcounterSubscribersLevelName }
	::={shapingcounterSubscribersLevelTable 1}

ShapingcounterSubscribersLevelEntry ::=
	SEQUENCE {
		shapingcounterSubscribersLevelName	DisplayString,
		shapingcounterSubscribersLevelVal	CounterBasedGauge64,
		shapingcounterSubscribersLevelMax	CounterBasedGauge64
	}

shapingcounterSubscribersLevelName OBJECT-TYPE
	SYNTAX      DisplayString
	MAX-ACCESS  not-accessible
	STATUS      current
	DESCRIPTION
	"Table entry display string for shapingcounterSubscribers"
	::={shapingcounterSubscribersLevelEntry 1}

shapingcounterSubscribersLevelVal OBJECT-TYPE
	SYNTAX	 CounterBasedGauge64
	MAX-ACCESS  read-only
	STATUS      current
	DESCRIPTION
	"Table entry attribute for shapingcounterSubscribers"
	::={shapingcounterSubscribersLevelEntry 2}

shapingcounterSubscribersLevelMax OBJECT-TYPE
	SYNTAX	 CounterBasedGauge64
	MAX-ACCESS  read-only
	STATUS      current
	DESCRIPTION
	"Table entry attribute for shapingcounterSubscribers"
	::={shapingcounterSubscribersLevelEntry 4}


shapingcounterDropped	OBJECT IDENTIFIER ::={shapingcounter 7}

shapingcounterDroppedVal	OBJECT-TYPE
	SYNTAX	 Counter64
	MAX-ACCESS read-only
	STATUS current
	DESCRIPTION "Dropped shaping counter updates"

	::={shapingcounterDropped 1}

shapingcounterDroppedMom	OBJECT-TYPE
	SYNTAX	 CounterBasedGauge64
	MAX-ACCESS read-only
	STATUS current
	DESCRIPTION "Dropped shaping counter updates"

	::={shapingcounterDropped 2}

shapingcounterDroppedMax	OBJECT-TYPE
	SYNTAX	 CounterBasedGauge64
	MAX-ACCESS read-only
	STATUS current
	DESCRIPTION "Dropped shaping counter updates"

	::={shapingcounterDropped 3}

shapingcounterDroppedLevelTable OBJECT-TYPE
	SYNTAX      SEQUENCE OF ShapingcounterDroppedLevelEntry
	MAX-ACCESS  not-accessible
	STATUS      current
	DESCRIPTION
	"Table for shapingcounterDropped"
	::={shapingcounterDropped 4}

shapingcounterDroppedLevelEntry OBJECT-TYPE
	SYNTAX      ShapingcounterDroppedLevelEntry
	MAX-ACCESS  not-accessible
	STATUS      current
	DESCRIPTION
	"Table entry for shapingcounterDropped"
	INDEX { shapingcounterDroppedLevelName }
	::={shapingcounterDroppedLevelTable 1}

ShapingcounterDroppedLevelEntry ::=
	SEQUENCE {
		shapingcounterDroppedLevelName	DisplayString,
		shapingcounterDroppedLevelVal	Counter64,
		shapingcounterDroppedLevelMom	CounterBasedGauge64,
		shapingcounterDroppedLevelMax	CounterBasedGauge64
	}

shapingcounterDroppedLevelName OBJECT-TYPE
	SYNTAX      DisplayString
	MAX-ACCESS  not-accessible
	STATUS      current
	DESCRIPTION
	"Table entry display string for shapingcounterDropped"
	::={shapingcounterDroppedLevelEntry 1}

shapingcounterDroppedLevelVal OBJECT-TYPE
	SYNTAX	 Counter64
	MAX-ACCESS  read-only
	STATUS      current
	DESCRIPTION
	"Table entry attribute for shapingcounterDropped"
	::={shapingcounterDroppedLevelEntry 2}

shapingcounterDroppedLevelMom OBJECT-TYPE
	SYNTAX	 CounterBasedGauge64
	MAX-ACCESS  read-only
	STATUS      current
	DESCRIPTION
	"Table entry attribute for shapingcounterDropped"
	::={shapingcounterDroppedLevelEntry 3}

shapingcounterDroppedLevelMax OBJECT-TYPE
	SYNTAX	 CounterBasedGauge64
	MAX-ACCESS  read-only
	STATUS      current
	DESCRIPTION
	"Table entry attribute for shapingcounterDropped"
	::={shapingcounterDroppedLevelEntry 4}


divert	OBJECT IDENTIFIER ::={sysdiag 125}

divertOutOfHosts	OBJECT IDENTIFIER ::={divert 2}

divertOutOfHostsVal	OBJECT-TYPE
	SYNTAX	 Counter64
	MAX-ACCESS read-only
	STATUS current
	DESCRIPTION "Out of hosts"

	::={divertOutOfHosts 1}

divertOutOfHostsMom	OBJECT-TYPE
	SYNTAX	 CounterBasedGauge64
	MAX-ACCESS read-only
	STATUS current
	DESCRIPTION "Out of hosts"

	::={divertOutOfHosts 2}

divertOutOfHostsMax	OBJECT-TYPE
	SYNTAX	 CounterBasedGauge64
	MAX-ACCESS read-only
	STATUS current
	DESCRIPTION "Out of hosts"

	::={divertOutOfHosts 3}

divertOutOfHostsLevelTable OBJECT-TYPE
	SYNTAX      SEQUENCE OF DivertOutOfHostsLevelEntry
	MAX-ACCESS  not-accessible
	STATUS      current
	DESCRIPTION
	"Table for divertOutOfHosts"
	::={divertOutOfHosts 4}

divertOutOfHostsLevelEntry OBJECT-TYPE
	SYNTAX      DivertOutOfHostsLevelEntry
	MAX-ACCESS  not-accessible
	STATUS      current
	DESCRIPTION
	"Table entry for divertOutOfHosts"
	INDEX { divertOutOfHostsLevelName }
	::={divertOutOfHostsLevelTable 1}

DivertOutOfHostsLevelEntry ::=
	SEQUENCE {
		divertOutOfHostsLevelName	DisplayString,
		divertOutOfHostsLevelVal	Counter64,
		divertOutOfHostsLevelMom	CounterBasedGauge64,
		divertOutOfHostsLevelMax	CounterBasedGauge64
	}

divertOutOfHostsLevelName OBJECT-TYPE
	SYNTAX      DisplayString
	MAX-ACCESS  not-accessible
	STATUS      current
	DESCRIPTION
	"Table entry display string for divertOutOfHosts"
	::={divertOutOfHostsLevelEntry 1}

divertOutOfHostsLevelVal OBJECT-TYPE
	SYNTAX	 Counter64
	MAX-ACCESS  read-only
	STATUS      current
	DESCRIPTION
	"Table entry attribute for divertOutOfHosts"
	::={divertOutOfHostsLevelEntry 2}

divertOutOfHostsLevelMom OBJECT-TYPE
	SYNTAX	 CounterBasedGauge64
	MAX-ACCESS  read-only
	STATUS      current
	DESCRIPTION
	"Table entry attribute for divertOutOfHosts"
	::={divertOutOfHostsLevelEntry 3}

divertOutOfHostsLevelMax OBJECT-TYPE
	SYNTAX	 CounterBasedGauge64
	MAX-ACCESS  read-only
	STATUS      current
	DESCRIPTION
	"Table entry attribute for divertOutOfHosts"
	::={divertOutOfHostsLevelEntry 4}


divertOversizeL2	OBJECT IDENTIFIER ::={divert 3}

divertOversizeL2Val	OBJECT-TYPE
	SYNTAX	 Counter64
	MAX-ACCESS read-only
	STATUS current
	DESCRIPTION "Too large L2-headers"

	::={divertOversizeL2 1}

divertOversizeL2Mom	OBJECT-TYPE
	SYNTAX	 CounterBasedGauge64
	MAX-ACCESS read-only
	STATUS current
	DESCRIPTION "Too large L2-headers"

	::={divertOversizeL2 2}

divertOversizeL2Max	OBJECT-TYPE
	SYNTAX	 CounterBasedGauge64
	MAX-ACCESS read-only
	STATUS current
	DESCRIPTION "Too large L2-headers"

	::={divertOversizeL2 3}

divertOversizeL2LevelTable OBJECT-TYPE
	SYNTAX      SEQUENCE OF DivertOversizeL2LevelEntry
	MAX-ACCESS  not-accessible
	STATUS      current
	DESCRIPTION
	"Table for divertOversizeL2"
	::={divertOversizeL2 4}

divertOversizeL2LevelEntry OBJECT-TYPE
	SYNTAX      DivertOversizeL2LevelEntry
	MAX-ACCESS  not-accessible
	STATUS      current
	DESCRIPTION
	"Table entry for divertOversizeL2"
	INDEX { divertOversizeL2LevelName }
	::={divertOversizeL2LevelTable 1}

DivertOversizeL2LevelEntry ::=
	SEQUENCE {
		divertOversizeL2LevelName	DisplayString,
		divertOversizeL2LevelVal	Counter64,
		divertOversizeL2LevelMom	CounterBasedGauge64,
		divertOversizeL2LevelMax	CounterBasedGauge64
	}

divertOversizeL2LevelName OBJECT-TYPE
	SYNTAX      DisplayString
	MAX-ACCESS  not-accessible
	STATUS      current
	DESCRIPTION
	"Table entry display string for divertOversizeL2"
	::={divertOversizeL2LevelEntry 1}

divertOversizeL2LevelVal OBJECT-TYPE
	SYNTAX	 Counter64
	MAX-ACCESS  read-only
	STATUS      current
	DESCRIPTION
	"Table entry attribute for divertOversizeL2"
	::={divertOversizeL2LevelEntry 2}

divertOversizeL2LevelMom OBJECT-TYPE
	SYNTAX	 CounterBasedGauge64
	MAX-ACCESS  read-only
	STATUS      current
	DESCRIPTION
	"Table entry attribute for divertOversizeL2"
	::={divertOversizeL2LevelEntry 3}

divertOversizeL2LevelMax OBJECT-TYPE
	SYNTAX	 CounterBasedGauge64
	MAX-ACCESS  read-only
	STATUS      current
	DESCRIPTION
	"Table entry attribute for divertOversizeL2"
	::={divertOversizeL2LevelEntry 4}


divertEgressPackets	OBJECT IDENTIFIER ::={divert 4}

divertEgressPacketsVal	OBJECT-TYPE
	SYNTAX	 Counter64
	MAX-ACCESS read-only
	STATUS current
	DESCRIPTION "Egress packets"

	::={divertEgressPackets 1}

divertEgressPacketsMom	OBJECT-TYPE
	SYNTAX	 CounterBasedGauge64
	MAX-ACCESS read-only
	STATUS current
	DESCRIPTION "Egress packets"

	::={divertEgressPackets 2}

divertEgressPacketsMax	OBJECT-TYPE
	SYNTAX	 CounterBasedGauge64
	MAX-ACCESS read-only
	STATUS current
	DESCRIPTION "Egress packets"

	::={divertEgressPackets 3}

divertEgressPacketsLevelTable OBJECT-TYPE
	SYNTAX      SEQUENCE OF DivertEgressPacketsLevelEntry
	MAX-ACCESS  not-accessible
	STATUS      current
	DESCRIPTION
	"Table for divertEgressPackets"
	::={divertEgressPackets 4}

divertEgressPacketsLevelEntry OBJECT-TYPE
	SYNTAX      DivertEgressPacketsLevelEntry
	MAX-ACCESS  not-accessible
	STATUS      current
	DESCRIPTION
	"Table entry for divertEgressPackets"
	INDEX { divertEgressPacketsLevelName }
	::={divertEgressPacketsLevelTable 1}

DivertEgressPacketsLevelEntry ::=
	SEQUENCE {
		divertEgressPacketsLevelName	DisplayString,
		divertEgressPacketsLevelVal	Counter64,
		divertEgressPacketsLevelMom	CounterBasedGauge64,
		divertEgressPacketsLevelMax	CounterBasedGauge64
	}

divertEgressPacketsLevelName OBJECT-TYPE
	SYNTAX      DisplayString
	MAX-ACCESS  not-accessible
	STATUS      current
	DESCRIPTION
	"Table entry display string for divertEgressPackets"
	::={divertEgressPacketsLevelEntry 1}

divertEgressPacketsLevelVal OBJECT-TYPE
	SYNTAX	 Counter64
	MAX-ACCESS  read-only
	STATUS      current
	DESCRIPTION
	"Table entry attribute for divertEgressPackets"
	::={divertEgressPacketsLevelEntry 2}

divertEgressPacketsLevelMom OBJECT-TYPE
	SYNTAX	 CounterBasedGauge64
	MAX-ACCESS  read-only
	STATUS      current
	DESCRIPTION
	"Table entry attribute for divertEgressPackets"
	::={divertEgressPacketsLevelEntry 3}

divertEgressPacketsLevelMax OBJECT-TYPE
	SYNTAX	 CounterBasedGauge64
	MAX-ACCESS  read-only
	STATUS      current
	DESCRIPTION
	"Table entry attribute for divertEgressPackets"
	::={divertEgressPacketsLevelEntry 4}


divertEgressBytes	OBJECT IDENTIFIER ::={divert 5}

divertEgressBytesVal	OBJECT-TYPE
	SYNTAX	 Counter64
	MAX-ACCESS read-only
	STATUS current
	DESCRIPTION "Egress bytes"

	::={divertEgressBytes 1}

divertEgressBytesMom	OBJECT-TYPE
	SYNTAX	 CounterBasedGauge64
	MAX-ACCESS read-only
	STATUS current
	DESCRIPTION "Egress bytes"

	::={divertEgressBytes 2}

divertEgressBytesMax	OBJECT-TYPE
	SYNTAX	 CounterBasedGauge64
	MAX-ACCESS read-only
	STATUS current
	DESCRIPTION "Egress bytes"

	::={divertEgressBytes 3}

divertEgressBytesLevelTable OBJECT-TYPE
	SYNTAX      SEQUENCE OF DivertEgressBytesLevelEntry
	MAX-ACCESS  not-accessible
	STATUS      current
	DESCRIPTION
	"Table for divertEgressBytes"
	::={divertEgressBytes 4}

divertEgressBytesLevelEntry OBJECT-TYPE
	SYNTAX      DivertEgressBytesLevelEntry
	MAX-ACCESS  not-accessible
	STATUS      current
	DESCRIPTION
	"Table entry for divertEgressBytes"
	INDEX { divertEgressBytesLevelName }
	::={divertEgressBytesLevelTable 1}

DivertEgressBytesLevelEntry ::=
	SEQUENCE {
		divertEgressBytesLevelName	DisplayString,
		divertEgressBytesLevelVal	Counter64,
		divertEgressBytesLevelMom	CounterBasedGauge64,
		divertEgressBytesLevelMax	CounterBasedGauge64
	}

divertEgressBytesLevelName OBJECT-TYPE
	SYNTAX      DisplayString
	MAX-ACCESS  not-accessible
	STATUS      current
	DESCRIPTION
	"Table entry display string for divertEgressBytes"
	::={divertEgressBytesLevelEntry 1}

divertEgressBytesLevelVal OBJECT-TYPE
	SYNTAX	 Counter64
	MAX-ACCESS  read-only
	STATUS      current
	DESCRIPTION
	"Table entry attribute for divertEgressBytes"
	::={divertEgressBytesLevelEntry 2}

divertEgressBytesLevelMom OBJECT-TYPE
	SYNTAX	 CounterBasedGauge64
	MAX-ACCESS  read-only
	STATUS      current
	DESCRIPTION
	"Table entry attribute for divertEgressBytes"
	::={divertEgressBytesLevelEntry 3}

divertEgressBytesLevelMax OBJECT-TYPE
	SYNTAX	 CounterBasedGauge64
	MAX-ACCESS  read-only
	STATUS      current
	DESCRIPTION
	"Table entry attribute for divertEgressBytes"
	::={divertEgressBytesLevelEntry 4}


divertIngressPackets	OBJECT IDENTIFIER ::={divert 6}

divertIngressPacketsVal	OBJECT-TYPE
	SYNTAX	 Counter64
	MAX-ACCESS read-only
	STATUS current
	DESCRIPTION "Ingress packets"

	::={divertIngressPackets 1}

divertIngressPacketsMom	OBJECT-TYPE
	SYNTAX	 CounterBasedGauge64
	MAX-ACCESS read-only
	STATUS current
	DESCRIPTION "Ingress packets"

	::={divertIngressPackets 2}

divertIngressPacketsMax	OBJECT-TYPE
	SYNTAX	 CounterBasedGauge64
	MAX-ACCESS read-only
	STATUS current
	DESCRIPTION "Ingress packets"

	::={divertIngressPackets 3}

divertIngressPacketsLevelTable OBJECT-TYPE
	SYNTAX      SEQUENCE OF DivertIngressPacketsLevelEntry
	MAX-ACCESS  not-accessible
	STATUS      current
	DESCRIPTION
	"Table for divertIngressPackets"
	::={divertIngressPackets 4}

divertIngressPacketsLevelEntry OBJECT-TYPE
	SYNTAX      DivertIngressPacketsLevelEntry
	MAX-ACCESS  not-accessible
	STATUS      current
	DESCRIPTION
	"Table entry for divertIngressPackets"
	INDEX { divertIngressPacketsLevelName }
	::={divertIngressPacketsLevelTable 1}

DivertIngressPacketsLevelEntry ::=
	SEQUENCE {
		divertIngressPacketsLevelName	DisplayString,
		divertIngressPacketsLevelVal	Counter64,
		divertIngressPacketsLevelMom	CounterBasedGauge64,
		divertIngressPacketsLevelMax	CounterBasedGauge64
	}

divertIngressPacketsLevelName OBJECT-TYPE
	SYNTAX      DisplayString
	MAX-ACCESS  not-accessible
	STATUS      current
	DESCRIPTION
	"Table entry display string for divertIngressPackets"
	::={divertIngressPacketsLevelEntry 1}

divertIngressPacketsLevelVal OBJECT-TYPE
	SYNTAX	 Counter64
	MAX-ACCESS  read-only
	STATUS      current
	DESCRIPTION
	"Table entry attribute for divertIngressPackets"
	::={divertIngressPacketsLevelEntry 2}

divertIngressPacketsLevelMom OBJECT-TYPE
	SYNTAX	 CounterBasedGauge64
	MAX-ACCESS  read-only
	STATUS      current
	DESCRIPTION
	"Table entry attribute for divertIngressPackets"
	::={divertIngressPacketsLevelEntry 3}

divertIngressPacketsLevelMax OBJECT-TYPE
	SYNTAX	 CounterBasedGauge64
	MAX-ACCESS  read-only
	STATUS      current
	DESCRIPTION
	"Table entry attribute for divertIngressPackets"
	::={divertIngressPacketsLevelEntry 4}


divertIngressBytes	OBJECT IDENTIFIER ::={divert 7}

divertIngressBytesVal	OBJECT-TYPE
	SYNTAX	 Counter64
	MAX-ACCESS read-only
	STATUS current
	DESCRIPTION "Ingress bytes"

	::={divertIngressBytes 1}

divertIngressBytesMom	OBJECT-TYPE
	SYNTAX	 CounterBasedGauge64
	MAX-ACCESS read-only
	STATUS current
	DESCRIPTION "Ingress bytes"

	::={divertIngressBytes 2}

divertIngressBytesMax	OBJECT-TYPE
	SYNTAX	 CounterBasedGauge64
	MAX-ACCESS read-only
	STATUS current
	DESCRIPTION "Ingress bytes"

	::={divertIngressBytes 3}

divertIngressBytesLevelTable OBJECT-TYPE
	SYNTAX      SEQUENCE OF DivertIngressBytesLevelEntry
	MAX-ACCESS  not-accessible
	STATUS      current
	DESCRIPTION
	"Table for divertIngressBytes"
	::={divertIngressBytes 4}

divertIngressBytesLevelEntry OBJECT-TYPE
	SYNTAX      DivertIngressBytesLevelEntry
	MAX-ACCESS  not-accessible
	STATUS      current
	DESCRIPTION
	"Table entry for divertIngressBytes"
	INDEX { divertIngressBytesLevelName }
	::={divertIngressBytesLevelTable 1}

DivertIngressBytesLevelEntry ::=
	SEQUENCE {
		divertIngressBytesLevelName	DisplayString,
		divertIngressBytesLevelVal	Counter64,
		divertIngressBytesLevelMom	CounterBasedGauge64,
		divertIngressBytesLevelMax	CounterBasedGauge64
	}

divertIngressBytesLevelName OBJECT-TYPE
	SYNTAX      DisplayString
	MAX-ACCESS  not-accessible
	STATUS      current
	DESCRIPTION
	"Table entry display string for divertIngressBytes"
	::={divertIngressBytesLevelEntry 1}

divertIngressBytesLevelVal OBJECT-TYPE
	SYNTAX	 Counter64
	MAX-ACCESS  read-only
	STATUS      current
	DESCRIPTION
	"Table entry attribute for divertIngressBytes"
	::={divertIngressBytesLevelEntry 2}

divertIngressBytesLevelMom OBJECT-TYPE
	SYNTAX	 CounterBasedGauge64
	MAX-ACCESS  read-only
	STATUS      current
	DESCRIPTION
	"Table entry attribute for divertIngressBytes"
	::={divertIngressBytesLevelEntry 3}

divertIngressBytesLevelMax OBJECT-TYPE
	SYNTAX	 CounterBasedGauge64
	MAX-ACCESS  read-only
	STATUS      current
	DESCRIPTION
	"Table entry attribute for divertIngressBytes"
	::={divertIngressBytesLevelEntry 4}


divertIngressPacketsNohost	OBJECT IDENTIFIER ::={divert 8}

divertIngressPacketsNohostVal	OBJECT-TYPE
	SYNTAX	 Counter64
	MAX-ACCESS read-only
	STATUS current
	DESCRIPTION "Ingress packets with missing host"

	::={divertIngressPacketsNohost 1}

divertIngressPacketsNohostMom	OBJECT-TYPE
	SYNTAX	 CounterBasedGauge64
	MAX-ACCESS read-only
	STATUS current
	DESCRIPTION "Ingress packets with missing host"

	::={divertIngressPacketsNohost 2}

divertIngressPacketsNohostMax	OBJECT-TYPE
	SYNTAX	 CounterBasedGauge64
	MAX-ACCESS read-only
	STATUS current
	DESCRIPTION "Ingress packets with missing host"

	::={divertIngressPacketsNohost 3}

divertIngressPacketsNohostLevelTable OBJECT-TYPE
	SYNTAX      SEQUENCE OF DivertIngressPacketsNohostLevelEntry
	MAX-ACCESS  not-accessible
	STATUS      current
	DESCRIPTION
	"Table for divertIngressPacketsNohost"
	::={divertIngressPacketsNohost 4}

divertIngressPacketsNohostLevelEntry OBJECT-TYPE
	SYNTAX      DivertIngressPacketsNohostLevelEntry
	MAX-ACCESS  not-accessible
	STATUS      current
	DESCRIPTION
	"Table entry for divertIngressPacketsNohost"
	INDEX { divertIngressPacketsNohostLevelName }
	::={divertIngressPacketsNohostLevelTable 1}

DivertIngressPacketsNohostLevelEntry ::=
	SEQUENCE {
		divertIngressPacketsNohostLevelName	DisplayString,
		divertIngressPacketsNohostLevelVal	Counter64,
		divertIngressPacketsNohostLevelMom	CounterBasedGauge64,
		divertIngressPacketsNohostLevelMax	CounterBasedGauge64
	}

divertIngressPacketsNohostLevelName OBJECT-TYPE
	SYNTAX      DisplayString
	MAX-ACCESS  not-accessible
	STATUS      current
	DESCRIPTION
	"Table entry display string for divertIngressPacketsNohost"
	::={divertIngressPacketsNohostLevelEntry 1}

divertIngressPacketsNohostLevelVal OBJECT-TYPE
	SYNTAX	 Counter64
	MAX-ACCESS  read-only
	STATUS      current
	DESCRIPTION
	"Table entry attribute for divertIngressPacketsNohost"
	::={divertIngressPacketsNohostLevelEntry 2}

divertIngressPacketsNohostLevelMom OBJECT-TYPE
	SYNTAX	 CounterBasedGauge64
	MAX-ACCESS  read-only
	STATUS      current
	DESCRIPTION
	"Table entry attribute for divertIngressPacketsNohost"
	::={divertIngressPacketsNohostLevelEntry 3}

divertIngressPacketsNohostLevelMax OBJECT-TYPE
	SYNTAX	 CounterBasedGauge64
	MAX-ACCESS  read-only
	STATUS      current
	DESCRIPTION
	"Table entry attribute for divertIngressPacketsNohost"
	::={divertIngressPacketsNohostLevelEntry 4}


divertIngressPacketsNol2	OBJECT IDENTIFIER ::={divert 9}

divertIngressPacketsNol2Val	OBJECT-TYPE
	SYNTAX	 Counter64
	MAX-ACCESS read-only
	STATUS current
	DESCRIPTION "Ingress packets with host missing L2-header"

	::={divertIngressPacketsNol2 1}

divertIngressPacketsNol2Mom	OBJECT-TYPE
	SYNTAX	 CounterBasedGauge64
	MAX-ACCESS read-only
	STATUS current
	DESCRIPTION "Ingress packets with host missing L2-header"

	::={divertIngressPacketsNol2 2}

divertIngressPacketsNol2Max	OBJECT-TYPE
	SYNTAX	 CounterBasedGauge64
	MAX-ACCESS read-only
	STATUS current
	DESCRIPTION "Ingress packets with host missing L2-header"

	::={divertIngressPacketsNol2 3}

divertIngressPacketsNol2LevelTable OBJECT-TYPE
	SYNTAX      SEQUENCE OF DivertIngressPacketsNol2LevelEntry
	MAX-ACCESS  not-accessible
	STATUS      current
	DESCRIPTION
	"Table for divertIngressPacketsNol2"
	::={divertIngressPacketsNol2 4}

divertIngressPacketsNol2LevelEntry OBJECT-TYPE
	SYNTAX      DivertIngressPacketsNol2LevelEntry
	MAX-ACCESS  not-accessible
	STATUS      current
	DESCRIPTION
	"Table entry for divertIngressPacketsNol2"
	INDEX { divertIngressPacketsNol2LevelName }
	::={divertIngressPacketsNol2LevelTable 1}

DivertIngressPacketsNol2LevelEntry ::=
	SEQUENCE {
		divertIngressPacketsNol2LevelName	DisplayString,
		divertIngressPacketsNol2LevelVal	Counter64,
		divertIngressPacketsNol2LevelMom	CounterBasedGauge64,
		divertIngressPacketsNol2LevelMax	CounterBasedGauge64
	}

divertIngressPacketsNol2LevelName OBJECT-TYPE
	SYNTAX      DisplayString
	MAX-ACCESS  not-accessible
	STATUS      current
	DESCRIPTION
	"Table entry display string for divertIngressPacketsNol2"
	::={divertIngressPacketsNol2LevelEntry 1}

divertIngressPacketsNol2LevelVal OBJECT-TYPE
	SYNTAX	 Counter64
	MAX-ACCESS  read-only
	STATUS      current
	DESCRIPTION
	"Table entry attribute for divertIngressPacketsNol2"
	::={divertIngressPacketsNol2LevelEntry 2}

divertIngressPacketsNol2LevelMom OBJECT-TYPE
	SYNTAX	 CounterBasedGauge64
	MAX-ACCESS  read-only
	STATUS      current
	DESCRIPTION
	"Table entry attribute for divertIngressPacketsNol2"
	::={divertIngressPacketsNol2LevelEntry 3}

divertIngressPacketsNol2LevelMax OBJECT-TYPE
	SYNTAX	 CounterBasedGauge64
	MAX-ACCESS  read-only
	STATUS      current
	DESCRIPTION
	"Table entry attribute for divertIngressPacketsNol2"
	::={divertIngressPacketsNol2LevelEntry 4}


divertHostsUse	OBJECT IDENTIFIER ::={divert 10}

divertHostsUseVal	OBJECT-TYPE
	SYNTAX	 CounterBasedGauge64
	MAX-ACCESS read-only
	STATUS current
	DESCRIPTION "Hosts"

	::={divertHostsUse 1}

divertHostsUseMax	OBJECT-TYPE
	SYNTAX	 CounterBasedGauge64
	MAX-ACCESS read-only
	STATUS current
	DESCRIPTION "Hosts"

	::={divertHostsUse 3}

divertHostsUseLevelTable OBJECT-TYPE
	SYNTAX      SEQUENCE OF DivertHostsUseLevelEntry
	MAX-ACCESS  not-accessible
	STATUS      current
	DESCRIPTION
	"Table for divertHostsUse"
	::={divertHostsUse 4}

divertHostsUseLevelEntry OBJECT-TYPE
	SYNTAX      DivertHostsUseLevelEntry
	MAX-ACCESS  not-accessible
	STATUS      current
	DESCRIPTION
	"Table entry for divertHostsUse"
	INDEX { divertHostsUseLevelName }
	::={divertHostsUseLevelTable 1}

DivertHostsUseLevelEntry ::=
	SEQUENCE {
		divertHostsUseLevelName	DisplayString,
		divertHostsUseLevelVal	CounterBasedGauge64,
		divertHostsUseLevelMax	CounterBasedGauge64
	}

divertHostsUseLevelName OBJECT-TYPE
	SYNTAX      DisplayString
	MAX-ACCESS  not-accessible
	STATUS      current
	DESCRIPTION
	"Table entry display string for divertHostsUse"
	::={divertHostsUseLevelEntry 1}

divertHostsUseLevelVal OBJECT-TYPE
	SYNTAX	 CounterBasedGauge64
	MAX-ACCESS  read-only
	STATUS      current
	DESCRIPTION
	"Table entry attribute for divertHostsUse"
	::={divertHostsUseLevelEntry 2}

divertHostsUseLevelMax OBJECT-TYPE
	SYNTAX	 CounterBasedGauge64
	MAX-ACCESS  read-only
	STATUS      current
	DESCRIPTION
	"Table entry attribute for divertHostsUse"
	::={divertHostsUseLevelEntry 4}


divertConnections	OBJECT IDENTIFIER ::={divert 11}

divertConnectionsVal	OBJECT-TYPE
	SYNTAX	 CounterBasedGauge64
	MAX-ACCESS read-only
	STATUS current
	DESCRIPTION "Connections"

	::={divertConnections 1}

divertConnectionsMax	OBJECT-TYPE
	SYNTAX	 CounterBasedGauge64
	MAX-ACCESS read-only
	STATUS current
	DESCRIPTION "Connections"

	::={divertConnections 3}

divertConnectionsLevelTable OBJECT-TYPE
	SYNTAX      SEQUENCE OF DivertConnectionsLevelEntry
	MAX-ACCESS  not-accessible
	STATUS      current
	DESCRIPTION
	"Table for divertConnections"
	::={divertConnections 4}

divertConnectionsLevelEntry OBJECT-TYPE
	SYNTAX      DivertConnectionsLevelEntry
	MAX-ACCESS  not-accessible
	STATUS      current
	DESCRIPTION
	"Table entry for divertConnections"
	INDEX { divertConnectionsLevelName }
	::={divertConnectionsLevelTable 1}

DivertConnectionsLevelEntry ::=
	SEQUENCE {
		divertConnectionsLevelName	DisplayString,
		divertConnectionsLevelVal	CounterBasedGauge64,
		divertConnectionsLevelMax	CounterBasedGauge64
	}

divertConnectionsLevelName OBJECT-TYPE
	SYNTAX      DisplayString
	MAX-ACCESS  not-accessible
	STATUS      current
	DESCRIPTION
	"Table entry display string for divertConnections"
	::={divertConnectionsLevelEntry 1}

divertConnectionsLevelVal OBJECT-TYPE
	SYNTAX	 CounterBasedGauge64
	MAX-ACCESS  read-only
	STATUS      current
	DESCRIPTION
	"Table entry attribute for divertConnections"
	::={divertConnectionsLevelEntry 2}

divertConnectionsLevelMax OBJECT-TYPE
	SYNTAX	 CounterBasedGauge64
	MAX-ACCESS  read-only
	STATUS      current
	DESCRIPTION
	"Table entry attribute for divertConnections"
	::={divertConnectionsLevelEntry 4}


divertHbReqSent	OBJECT IDENTIFIER ::={divert 12}

divertHbReqSentVal	OBJECT-TYPE
	SYNTAX	 Counter64
	MAX-ACCESS read-only
	STATUS current
	DESCRIPTION "Heartbeat requests sent"

	::={divertHbReqSent 1}

divertHbReqSentMom	OBJECT-TYPE
	SYNTAX	 CounterBasedGauge64
	MAX-ACCESS read-only
	STATUS current
	DESCRIPTION "Heartbeat requests sent"

	::={divertHbReqSent 2}

divertHbReqSentMax	OBJECT-TYPE
	SYNTAX	 CounterBasedGauge64
	MAX-ACCESS read-only
	STATUS current
	DESCRIPTION "Heartbeat requests sent"

	::={divertHbReqSent 3}

divertHbReqSentLevelTable OBJECT-TYPE
	SYNTAX      SEQUENCE OF DivertHbReqSentLevelEntry
	MAX-ACCESS  not-accessible
	STATUS      current
	DESCRIPTION
	"Table for divertHbReqSent"
	::={divertHbReqSent 4}

divertHbReqSentLevelEntry OBJECT-TYPE
	SYNTAX      DivertHbReqSentLevelEntry
	MAX-ACCESS  not-accessible
	STATUS      current
	DESCRIPTION
	"Table entry for divertHbReqSent"
	INDEX { divertHbReqSentLevelName }
	::={divertHbReqSentLevelTable 1}

DivertHbReqSentLevelEntry ::=
	SEQUENCE {
		divertHbReqSentLevelName	DisplayString,
		divertHbReqSentLevelVal	Counter64,
		divertHbReqSentLevelMom	CounterBasedGauge64,
		divertHbReqSentLevelMax	CounterBasedGauge64
	}

divertHbReqSentLevelName OBJECT-TYPE
	SYNTAX      DisplayString
	MAX-ACCESS  not-accessible
	STATUS      current
	DESCRIPTION
	"Table entry display string for divertHbReqSent"
	::={divertHbReqSentLevelEntry 1}

divertHbReqSentLevelVal OBJECT-TYPE
	SYNTAX	 Counter64
	MAX-ACCESS  read-only
	STATUS      current
	DESCRIPTION
	"Table entry attribute for divertHbReqSent"
	::={divertHbReqSentLevelEntry 2}

divertHbReqSentLevelMom OBJECT-TYPE
	SYNTAX	 CounterBasedGauge64
	MAX-ACCESS  read-only
	STATUS      current
	DESCRIPTION
	"Table entry attribute for divertHbReqSent"
	::={divertHbReqSentLevelEntry 3}

divertHbReqSentLevelMax OBJECT-TYPE
	SYNTAX	 CounterBasedGauge64
	MAX-ACCESS  read-only
	STATUS      current
	DESCRIPTION
	"Table entry attribute for divertHbReqSent"
	::={divertHbReqSentLevelEntry 4}


divertHbReqRecv	OBJECT IDENTIFIER ::={divert 13}

divertHbReqRecvVal	OBJECT-TYPE
	SYNTAX	 Counter64
	MAX-ACCESS read-only
	STATUS current
	DESCRIPTION "Heartbeat requests received"

	::={divertHbReqRecv 1}

divertHbReqRecvMom	OBJECT-TYPE
	SYNTAX	 CounterBasedGauge64
	MAX-ACCESS read-only
	STATUS current
	DESCRIPTION "Heartbeat requests received"

	::={divertHbReqRecv 2}

divertHbReqRecvMax	OBJECT-TYPE
	SYNTAX	 CounterBasedGauge64
	MAX-ACCESS read-only
	STATUS current
	DESCRIPTION "Heartbeat requests received"

	::={divertHbReqRecv 3}

divertHbReqRecvLevelTable OBJECT-TYPE
	SYNTAX      SEQUENCE OF DivertHbReqRecvLevelEntry
	MAX-ACCESS  not-accessible
	STATUS      current
	DESCRIPTION
	"Table for divertHbReqRecv"
	::={divertHbReqRecv 4}

divertHbReqRecvLevelEntry OBJECT-TYPE
	SYNTAX      DivertHbReqRecvLevelEntry
	MAX-ACCESS  not-accessible
	STATUS      current
	DESCRIPTION
	"Table entry for divertHbReqRecv"
	INDEX { divertHbReqRecvLevelName }
	::={divertHbReqRecvLevelTable 1}

DivertHbReqRecvLevelEntry ::=
	SEQUENCE {
		divertHbReqRecvLevelName	DisplayString,
		divertHbReqRecvLevelVal	Counter64,
		divertHbReqRecvLevelMom	CounterBasedGauge64,
		divertHbReqRecvLevelMax	CounterBasedGauge64
	}

divertHbReqRecvLevelName OBJECT-TYPE
	SYNTAX      DisplayString
	MAX-ACCESS  not-accessible
	STATUS      current
	DESCRIPTION
	"Table entry display string for divertHbReqRecv"
	::={divertHbReqRecvLevelEntry 1}

divertHbReqRecvLevelVal OBJECT-TYPE
	SYNTAX	 Counter64
	MAX-ACCESS  read-only
	STATUS      current
	DESCRIPTION
	"Table entry attribute for divertHbReqRecv"
	::={divertHbReqRecvLevelEntry 2}

divertHbReqRecvLevelMom OBJECT-TYPE
	SYNTAX	 CounterBasedGauge64
	MAX-ACCESS  read-only
	STATUS      current
	DESCRIPTION
	"Table entry attribute for divertHbReqRecv"
	::={divertHbReqRecvLevelEntry 3}

divertHbReqRecvLevelMax OBJECT-TYPE
	SYNTAX	 CounterBasedGauge64
	MAX-ACCESS  read-only
	STATUS      current
	DESCRIPTION
	"Table entry attribute for divertHbReqRecv"
	::={divertHbReqRecvLevelEntry 4}


divertHbRepSent	OBJECT IDENTIFIER ::={divert 14}

divertHbRepSentVal	OBJECT-TYPE
	SYNTAX	 Counter64
	MAX-ACCESS read-only
	STATUS current
	DESCRIPTION "Heartbeat replies sent"

	::={divertHbRepSent 1}

divertHbRepSentMom	OBJECT-TYPE
	SYNTAX	 CounterBasedGauge64
	MAX-ACCESS read-only
	STATUS current
	DESCRIPTION "Heartbeat replies sent"

	::={divertHbRepSent 2}

divertHbRepSentMax	OBJECT-TYPE
	SYNTAX	 CounterBasedGauge64
	MAX-ACCESS read-only
	STATUS current
	DESCRIPTION "Heartbeat replies sent"

	::={divertHbRepSent 3}

divertHbRepSentLevelTable OBJECT-TYPE
	SYNTAX      SEQUENCE OF DivertHbRepSentLevelEntry
	MAX-ACCESS  not-accessible
	STATUS      current
	DESCRIPTION
	"Table for divertHbRepSent"
	::={divertHbRepSent 4}

divertHbRepSentLevelEntry OBJECT-TYPE
	SYNTAX      DivertHbRepSentLevelEntry
	MAX-ACCESS  not-accessible
	STATUS      current
	DESCRIPTION
	"Table entry for divertHbRepSent"
	INDEX { divertHbRepSentLevelName }
	::={divertHbRepSentLevelTable 1}

DivertHbRepSentLevelEntry ::=
	SEQUENCE {
		divertHbRepSentLevelName	DisplayString,
		divertHbRepSentLevelVal	Counter64,
		divertHbRepSentLevelMom	CounterBasedGauge64,
		divertHbRepSentLevelMax	CounterBasedGauge64
	}

divertHbRepSentLevelName OBJECT-TYPE
	SYNTAX      DisplayString
	MAX-ACCESS  not-accessible
	STATUS      current
	DESCRIPTION
	"Table entry display string for divertHbRepSent"
	::={divertHbRepSentLevelEntry 1}

divertHbRepSentLevelVal OBJECT-TYPE
	SYNTAX	 Counter64
	MAX-ACCESS  read-only
	STATUS      current
	DESCRIPTION
	"Table entry attribute for divertHbRepSent"
	::={divertHbRepSentLevelEntry 2}

divertHbRepSentLevelMom OBJECT-TYPE
	SYNTAX	 CounterBasedGauge64
	MAX-ACCESS  read-only
	STATUS      current
	DESCRIPTION
	"Table entry attribute for divertHbRepSent"
	::={divertHbRepSentLevelEntry 3}

divertHbRepSentLevelMax OBJECT-TYPE
	SYNTAX	 CounterBasedGauge64
	MAX-ACCESS  read-only
	STATUS      current
	DESCRIPTION
	"Table entry attribute for divertHbRepSent"
	::={divertHbRepSentLevelEntry 4}


divertHbRepRecv	OBJECT IDENTIFIER ::={divert 15}

divertHbRepRecvVal	OBJECT-TYPE
	SYNTAX	 Counter64
	MAX-ACCESS read-only
	STATUS current
	DESCRIPTION "Heartbeat replies received"

	::={divertHbRepRecv 1}

divertHbRepRecvMom	OBJECT-TYPE
	SYNTAX	 CounterBasedGauge64
	MAX-ACCESS read-only
	STATUS current
	DESCRIPTION "Heartbeat replies received"

	::={divertHbRepRecv 2}

divertHbRepRecvMax	OBJECT-TYPE
	SYNTAX	 CounterBasedGauge64
	MAX-ACCESS read-only
	STATUS current
	DESCRIPTION "Heartbeat replies received"

	::={divertHbRepRecv 3}

divertHbRepRecvLevelTable OBJECT-TYPE
	SYNTAX      SEQUENCE OF DivertHbRepRecvLevelEntry
	MAX-ACCESS  not-accessible
	STATUS      current
	DESCRIPTION
	"Table for divertHbRepRecv"
	::={divertHbRepRecv 4}

divertHbRepRecvLevelEntry OBJECT-TYPE
	SYNTAX      DivertHbRepRecvLevelEntry
	MAX-ACCESS  not-accessible
	STATUS      current
	DESCRIPTION
	"Table entry for divertHbRepRecv"
	INDEX { divertHbRepRecvLevelName }
	::={divertHbRepRecvLevelTable 1}

DivertHbRepRecvLevelEntry ::=
	SEQUENCE {
		divertHbRepRecvLevelName	DisplayString,
		divertHbRepRecvLevelVal	Counter64,
		divertHbRepRecvLevelMom	CounterBasedGauge64,
		divertHbRepRecvLevelMax	CounterBasedGauge64
	}

divertHbRepRecvLevelName OBJECT-TYPE
	SYNTAX      DisplayString
	MAX-ACCESS  not-accessible
	STATUS      current
	DESCRIPTION
	"Table entry display string for divertHbRepRecv"
	::={divertHbRepRecvLevelEntry 1}

divertHbRepRecvLevelVal OBJECT-TYPE
	SYNTAX	 Counter64
	MAX-ACCESS  read-only
	STATUS      current
	DESCRIPTION
	"Table entry attribute for divertHbRepRecv"
	::={divertHbRepRecvLevelEntry 2}

divertHbRepRecvLevelMom OBJECT-TYPE
	SYNTAX	 CounterBasedGauge64
	MAX-ACCESS  read-only
	STATUS      current
	DESCRIPTION
	"Table entry attribute for divertHbRepRecv"
	::={divertHbRepRecvLevelEntry 3}

divertHbRepRecvLevelMax OBJECT-TYPE
	SYNTAX	 CounterBasedGauge64
	MAX-ACCESS  read-only
	STATUS      current
	DESCRIPTION
	"Table entry attribute for divertHbRepRecv"
	::={divertHbRepRecvLevelEntry 4}


divertHbLost	OBJECT IDENTIFIER ::={divert 16}

divertHbLostVal	OBJECT-TYPE
	SYNTAX	 Counter64
	MAX-ACCESS read-only
	STATUS current
	DESCRIPTION "Heartbeats lost"

	::={divertHbLost 1}

divertHbLostMom	OBJECT-TYPE
	SYNTAX	 CounterBasedGauge64
	MAX-ACCESS read-only
	STATUS current
	DESCRIPTION "Heartbeats lost"

	::={divertHbLost 2}

divertHbLostMax	OBJECT-TYPE
	SYNTAX	 CounterBasedGauge64
	MAX-ACCESS read-only
	STATUS current
	DESCRIPTION "Heartbeats lost"

	::={divertHbLost 3}

divertHbLostLevelTable OBJECT-TYPE
	SYNTAX      SEQUENCE OF DivertHbLostLevelEntry
	MAX-ACCESS  not-accessible
	STATUS      current
	DESCRIPTION
	"Table for divertHbLost"
	::={divertHbLost 4}

divertHbLostLevelEntry OBJECT-TYPE
	SYNTAX      DivertHbLostLevelEntry
	MAX-ACCESS  not-accessible
	STATUS      current
	DESCRIPTION
	"Table entry for divertHbLost"
	INDEX { divertHbLostLevelName }
	::={divertHbLostLevelTable 1}

DivertHbLostLevelEntry ::=
	SEQUENCE {
		divertHbLostLevelName	DisplayString,
		divertHbLostLevelVal	Counter64,
		divertHbLostLevelMom	CounterBasedGauge64,
		divertHbLostLevelMax	CounterBasedGauge64
	}

divertHbLostLevelName OBJECT-TYPE
	SYNTAX      DisplayString
	MAX-ACCESS  not-accessible
	STATUS      current
	DESCRIPTION
	"Table entry display string for divertHbLost"
	::={divertHbLostLevelEntry 1}

divertHbLostLevelVal OBJECT-TYPE
	SYNTAX	 Counter64
	MAX-ACCESS  read-only
	STATUS      current
	DESCRIPTION
	"Table entry attribute for divertHbLost"
	::={divertHbLostLevelEntry 2}

divertHbLostLevelMom OBJECT-TYPE
	SYNTAX	 CounterBasedGauge64
	MAX-ACCESS  read-only
	STATUS      current
	DESCRIPTION
	"Table entry attribute for divertHbLost"
	::={divertHbLostLevelEntry 3}

divertHbLostLevelMax OBJECT-TYPE
	SYNTAX	 CounterBasedGauge64
	MAX-ACCESS  read-only
	STATUS      current
	DESCRIPTION
	"Table entry attribute for divertHbLost"
	::={divertHbLostLevelEntry 4}


divertBypassPackets	OBJECT IDENTIFIER ::={divert 17}

divertBypassPacketsVal	OBJECT-TYPE
	SYNTAX	 Counter64
	MAX-ACCESS read-only
	STATUS current
	DESCRIPTION "Bypassed packets"

	::={divertBypassPackets 1}

divertBypassPacketsMom	OBJECT-TYPE
	SYNTAX	 CounterBasedGauge64
	MAX-ACCESS read-only
	STATUS current
	DESCRIPTION "Bypassed packets"

	::={divertBypassPackets 2}

divertBypassPacketsMax	OBJECT-TYPE
	SYNTAX	 CounterBasedGauge64
	MAX-ACCESS read-only
	STATUS current
	DESCRIPTION "Bypassed packets"

	::={divertBypassPackets 3}

divertBypassPacketsLevelTable OBJECT-TYPE
	SYNTAX      SEQUENCE OF DivertBypassPacketsLevelEntry
	MAX-ACCESS  not-accessible
	STATUS      current
	DESCRIPTION
	"Table for divertBypassPackets"
	::={divertBypassPackets 4}

divertBypassPacketsLevelEntry OBJECT-TYPE
	SYNTAX      DivertBypassPacketsLevelEntry
	MAX-ACCESS  not-accessible
	STATUS      current
	DESCRIPTION
	"Table entry for divertBypassPackets"
	INDEX { divertBypassPacketsLevelName }
	::={divertBypassPacketsLevelTable 1}

DivertBypassPacketsLevelEntry ::=
	SEQUENCE {
		divertBypassPacketsLevelName	DisplayString,
		divertBypassPacketsLevelVal	Counter64,
		divertBypassPacketsLevelMom	CounterBasedGauge64,
		divertBypassPacketsLevelMax	CounterBasedGauge64
	}

divertBypassPacketsLevelName OBJECT-TYPE
	SYNTAX      DisplayString
	MAX-ACCESS  not-accessible
	STATUS      current
	DESCRIPTION
	"Table entry display string for divertBypassPackets"
	::={divertBypassPacketsLevelEntry 1}

divertBypassPacketsLevelVal OBJECT-TYPE
	SYNTAX	 Counter64
	MAX-ACCESS  read-only
	STATUS      current
	DESCRIPTION
	"Table entry attribute for divertBypassPackets"
	::={divertBypassPacketsLevelEntry 2}

divertBypassPacketsLevelMom OBJECT-TYPE
	SYNTAX	 CounterBasedGauge64
	MAX-ACCESS  read-only
	STATUS      current
	DESCRIPTION
	"Table entry attribute for divertBypassPackets"
	::={divertBypassPacketsLevelEntry 3}

divertBypassPacketsLevelMax OBJECT-TYPE
	SYNTAX	 CounterBasedGauge64
	MAX-ACCESS  read-only
	STATUS      current
	DESCRIPTION
	"Table entry attribute for divertBypassPackets"
	::={divertBypassPacketsLevelEntry 4}


divertDroppedPackets	OBJECT IDENTIFIER ::={divert 18}

divertDroppedPacketsVal	OBJECT-TYPE
	SYNTAX	 Counter64
	MAX-ACCESS read-only
	STATUS current
	DESCRIPTION "Dropped packets"

	::={divertDroppedPackets 1}

divertDroppedPacketsMom	OBJECT-TYPE
	SYNTAX	 CounterBasedGauge64
	MAX-ACCESS read-only
	STATUS current
	DESCRIPTION "Dropped packets"

	::={divertDroppedPackets 2}

divertDroppedPacketsMax	OBJECT-TYPE
	SYNTAX	 CounterBasedGauge64
	MAX-ACCESS read-only
	STATUS current
	DESCRIPTION "Dropped packets"

	::={divertDroppedPackets 3}

divertDroppedPacketsLevelTable OBJECT-TYPE
	SYNTAX      SEQUENCE OF DivertDroppedPacketsLevelEntry
	MAX-ACCESS  not-accessible
	STATUS      current
	DESCRIPTION
	"Table for divertDroppedPackets"
	::={divertDroppedPackets 4}

divertDroppedPacketsLevelEntry OBJECT-TYPE
	SYNTAX      DivertDroppedPacketsLevelEntry
	MAX-ACCESS  not-accessible
	STATUS      current
	DESCRIPTION
	"Table entry for divertDroppedPackets"
	INDEX { divertDroppedPacketsLevelName }
	::={divertDroppedPacketsLevelTable 1}

DivertDroppedPacketsLevelEntry ::=
	SEQUENCE {
		divertDroppedPacketsLevelName	DisplayString,
		divertDroppedPacketsLevelVal	Counter64,
		divertDroppedPacketsLevelMom	CounterBasedGauge64,
		divertDroppedPacketsLevelMax	CounterBasedGauge64
	}

divertDroppedPacketsLevelName OBJECT-TYPE
	SYNTAX      DisplayString
	MAX-ACCESS  not-accessible
	STATUS      current
	DESCRIPTION
	"Table entry display string for divertDroppedPackets"
	::={divertDroppedPacketsLevelEntry 1}

divertDroppedPacketsLevelVal OBJECT-TYPE
	SYNTAX	 Counter64
	MAX-ACCESS  read-only
	STATUS      current
	DESCRIPTION
	"Table entry attribute for divertDroppedPackets"
	::={divertDroppedPacketsLevelEntry 2}

divertDroppedPacketsLevelMom OBJECT-TYPE
	SYNTAX	 CounterBasedGauge64
	MAX-ACCESS  read-only
	STATUS      current
	DESCRIPTION
	"Table entry attribute for divertDroppedPackets"
	::={divertDroppedPacketsLevelEntry 3}

divertDroppedPacketsLevelMax OBJECT-TYPE
	SYNTAX	 CounterBasedGauge64
	MAX-ACCESS  read-only
	STATUS      current
	DESCRIPTION
	"Table entry attribute for divertDroppedPackets"
	::={divertDroppedPacketsLevelEntry 4}


divertProxyConnections	OBJECT IDENTIFIER ::={divert 19}

divertProxyConnectionsVal	OBJECT-TYPE
	SYNTAX	 CounterBasedGauge64
	MAX-ACCESS read-only
	STATUS current
	DESCRIPTION "Proxy connections"

	::={divertProxyConnections 1}

divertProxyConnectionsMax	OBJECT-TYPE
	SYNTAX	 CounterBasedGauge64
	MAX-ACCESS read-only
	STATUS current
	DESCRIPTION "Proxy connections"

	::={divertProxyConnections 3}

divertProxyConnectionsLevelTable OBJECT-TYPE
	SYNTAX      SEQUENCE OF DivertProxyConnectionsLevelEntry
	MAX-ACCESS  not-accessible
	STATUS      current
	DESCRIPTION
	"Table for divertProxyConnections"
	::={divertProxyConnections 4}

divertProxyConnectionsLevelEntry OBJECT-TYPE
	SYNTAX      DivertProxyConnectionsLevelEntry
	MAX-ACCESS  not-accessible
	STATUS      current
	DESCRIPTION
	"Table entry for divertProxyConnections"
	INDEX { divertProxyConnectionsLevelName }
	::={divertProxyConnectionsLevelTable 1}

DivertProxyConnectionsLevelEntry ::=
	SEQUENCE {
		divertProxyConnectionsLevelName	DisplayString,
		divertProxyConnectionsLevelVal	CounterBasedGauge64,
		divertProxyConnectionsLevelMax	CounterBasedGauge64
	}

divertProxyConnectionsLevelName OBJECT-TYPE
	SYNTAX      DisplayString
	MAX-ACCESS  not-accessible
	STATUS      current
	DESCRIPTION
	"Table entry display string for divertProxyConnections"
	::={divertProxyConnectionsLevelEntry 1}

divertProxyConnectionsLevelVal OBJECT-TYPE
	SYNTAX	 CounterBasedGauge64
	MAX-ACCESS  read-only
	STATUS      current
	DESCRIPTION
	"Table entry attribute for divertProxyConnections"
	::={divertProxyConnectionsLevelEntry 2}

divertProxyConnectionsLevelMax OBJECT-TYPE
	SYNTAX	 CounterBasedGauge64
	MAX-ACCESS  read-only
	STATUS      current
	DESCRIPTION
	"Table entry attribute for divertProxyConnections"
	::={divertProxyConnectionsLevelEntry 4}


divertFailedProxyConnections	OBJECT IDENTIFIER ::={divert 20}

divertFailedProxyConnectionsVal	OBJECT-TYPE
	SYNTAX	 Counter64
	MAX-ACCESS read-only
	STATUS current
	DESCRIPTION "Proxy connections failed"

	::={divertFailedProxyConnections 1}

divertFailedProxyConnectionsMom	OBJECT-TYPE
	SYNTAX	 CounterBasedGauge64
	MAX-ACCESS read-only
	STATUS current
	DESCRIPTION "Proxy connections failed"

	::={divertFailedProxyConnections 2}

divertFailedProxyConnectionsMax	OBJECT-TYPE
	SYNTAX	 CounterBasedGauge64
	MAX-ACCESS read-only
	STATUS current
	DESCRIPTION "Proxy connections failed"

	::={divertFailedProxyConnections 3}

divertFailedProxyConnectionsLevelTable OBJECT-TYPE
	SYNTAX      SEQUENCE OF DivertFailedProxyConnectionsLevelEntry
	MAX-ACCESS  not-accessible
	STATUS      current
	DESCRIPTION
	"Table for divertFailedProxyConnections"
	::={divertFailedProxyConnections 4}

divertFailedProxyConnectionsLevelEntry OBJECT-TYPE
	SYNTAX      DivertFailedProxyConnectionsLevelEntry
	MAX-ACCESS  not-accessible
	STATUS      current
	DESCRIPTION
	"Table entry for divertFailedProxyConnections"
	INDEX { divertFailedProxyConnectionsLevelName }
	::={divertFailedProxyConnectionsLevelTable 1}

DivertFailedProxyConnectionsLevelEntry ::=
	SEQUENCE {
		divertFailedProxyConnectionsLevelName	DisplayString,
		divertFailedProxyConnectionsLevelVal	Counter64,
		divertFailedProxyConnectionsLevelMom	CounterBasedGauge64,
		divertFailedProxyConnectionsLevelMax	CounterBasedGauge64
	}

divertFailedProxyConnectionsLevelName OBJECT-TYPE
	SYNTAX      DisplayString
	MAX-ACCESS  not-accessible
	STATUS      current
	DESCRIPTION
	"Table entry display string for divertFailedProxyConnections"
	::={divertFailedProxyConnectionsLevelEntry 1}

divertFailedProxyConnectionsLevelVal OBJECT-TYPE
	SYNTAX	 Counter64
	MAX-ACCESS  read-only
	STATUS      current
	DESCRIPTION
	"Table entry attribute for divertFailedProxyConnections"
	::={divertFailedProxyConnectionsLevelEntry 2}

divertFailedProxyConnectionsLevelMom OBJECT-TYPE
	SYNTAX	 CounterBasedGauge64
	MAX-ACCESS  read-only
	STATUS      current
	DESCRIPTION
	"Table entry attribute for divertFailedProxyConnections"
	::={divertFailedProxyConnectionsLevelEntry 3}

divertFailedProxyConnectionsLevelMax OBJECT-TYPE
	SYNTAX	 CounterBasedGauge64
	MAX-ACCESS  read-only
	STATUS      current
	DESCRIPTION
	"Table entry attribute for divertFailedProxyConnections"
	::={divertFailedProxyConnectionsLevelEntry 4}


divertFailedProxyConnectionsTooManyChannels	OBJECT IDENTIFIER ::={divert 21}

divertFailedProxyConnectionsTooManyChannelsVal	OBJECT-TYPE
	SYNTAX	 Counter64
	MAX-ACCESS read-only
	STATUS current
	DESCRIPTION "Proxy connections failed (too many channels)"

	::={divertFailedProxyConnectionsTooManyChannels 1}

divertFailedProxyConnectionsTooManyChannelsMom	OBJECT-TYPE
	SYNTAX	 CounterBasedGauge64
	MAX-ACCESS read-only
	STATUS current
	DESCRIPTION "Proxy connections failed (too many channels)"

	::={divertFailedProxyConnectionsTooManyChannels 2}

divertFailedProxyConnectionsTooManyChannelsMax	OBJECT-TYPE
	SYNTAX	 CounterBasedGauge64
	MAX-ACCESS read-only
	STATUS current
	DESCRIPTION "Proxy connections failed (too many channels)"

	::={divertFailedProxyConnectionsTooManyChannels 3}

divertFailedProxyConnectionsTooManyChannelsLevelTable OBJECT-TYPE
	SYNTAX      SEQUENCE OF DivertFailedProxyConnectionsTooManyChannelsLevelEntry
	MAX-ACCESS  not-accessible
	STATUS      current
	DESCRIPTION
	"Table for divertFailedProxyConnectionsTooManyChannels"
	::={divertFailedProxyConnectionsTooManyChannels 4}

divertFailedProxyConnectionsTooManyChannelsLevelEntry OBJECT-TYPE
	SYNTAX      DivertFailedProxyConnectionsTooManyChannelsLevelEntry
	MAX-ACCESS  not-accessible
	STATUS      current
	DESCRIPTION
	"Table entry for divertFailedProxyConnectionsTooManyChannels"
	INDEX { divertFailedProxyConnectionsTooManyChannelsLevelName }
	::={divertFailedProxyConnectionsTooManyChannelsLevelTable 1}

DivertFailedProxyConnectionsTooManyChannelsLevelEntry ::=
	SEQUENCE {
		divertFailedProxyConnectionsTooManyChannelsLevelName	DisplayString,
		divertFailedProxyConnectionsTooManyChannelsLevelVal	Counter64,
		divertFailedProxyConnectionsTooManyChannelsLevelMom	CounterBasedGauge64,
		divertFailedProxyConnectionsTooManyChannelsLevelMax	CounterBasedGauge64
	}

divertFailedProxyConnectionsTooManyChannelsLevelName OBJECT-TYPE
	SYNTAX      DisplayString
	MAX-ACCESS  not-accessible
	STATUS      current
	DESCRIPTION
	"Table entry display string for divertFailedProxyConnectionsTooManyChannels"
	::={divertFailedProxyConnectionsTooManyChannelsLevelEntry 1}

divertFailedProxyConnectionsTooManyChannelsLevelVal OBJECT-TYPE
	SYNTAX	 Counter64
	MAX-ACCESS  read-only
	STATUS      current
	DESCRIPTION
	"Table entry attribute for divertFailedProxyConnectionsTooManyChannels"
	::={divertFailedProxyConnectionsTooManyChannelsLevelEntry 2}

divertFailedProxyConnectionsTooManyChannelsLevelMom OBJECT-TYPE
	SYNTAX	 CounterBasedGauge64
	MAX-ACCESS  read-only
	STATUS      current
	DESCRIPTION
	"Table entry attribute for divertFailedProxyConnectionsTooManyChannels"
	::={divertFailedProxyConnectionsTooManyChannelsLevelEntry 3}

divertFailedProxyConnectionsTooManyChannelsLevelMax OBJECT-TYPE
	SYNTAX	 CounterBasedGauge64
	MAX-ACCESS  read-only
	STATUS      current
	DESCRIPTION
	"Table entry attribute for divertFailedProxyConnectionsTooManyChannels"
	::={divertFailedProxyConnectionsTooManyChannelsLevelEntry 4}


divertFailedProxyConnectionsAsymmetric	OBJECT IDENTIFIER ::={divert 22}

divertFailedProxyConnectionsAsymmetricVal	OBJECT-TYPE
	SYNTAX	 Counter64
	MAX-ACCESS read-only
	STATUS current
	DESCRIPTION "Proxy connections failed (asymmetric)"

	::={divertFailedProxyConnectionsAsymmetric 1}

divertFailedProxyConnectionsAsymmetricMom	OBJECT-TYPE
	SYNTAX	 CounterBasedGauge64
	MAX-ACCESS read-only
	STATUS current
	DESCRIPTION "Proxy connections failed (asymmetric)"

	::={divertFailedProxyConnectionsAsymmetric 2}

divertFailedProxyConnectionsAsymmetricMax	OBJECT-TYPE
	SYNTAX	 CounterBasedGauge64
	MAX-ACCESS read-only
	STATUS current
	DESCRIPTION "Proxy connections failed (asymmetric)"

	::={divertFailedProxyConnectionsAsymmetric 3}

divertFailedProxyConnectionsAsymmetricLevelTable OBJECT-TYPE
	SYNTAX      SEQUENCE OF DivertFailedProxyConnectionsAsymmetricLevelEntry
	MAX-ACCESS  not-accessible
	STATUS      current
	DESCRIPTION
	"Table for divertFailedProxyConnectionsAsymmetric"
	::={divertFailedProxyConnectionsAsymmetric 4}

divertFailedProxyConnectionsAsymmetricLevelEntry OBJECT-TYPE
	SYNTAX      DivertFailedProxyConnectionsAsymmetricLevelEntry
	MAX-ACCESS  not-accessible
	STATUS      current
	DESCRIPTION
	"Table entry for divertFailedProxyConnectionsAsymmetric"
	INDEX { divertFailedProxyConnectionsAsymmetricLevelName }
	::={divertFailedProxyConnectionsAsymmetricLevelTable 1}

DivertFailedProxyConnectionsAsymmetricLevelEntry ::=
	SEQUENCE {
		divertFailedProxyConnectionsAsymmetricLevelName	DisplayString,
		divertFailedProxyConnectionsAsymmetricLevelVal	Counter64,
		divertFailedProxyConnectionsAsymmetricLevelMom	CounterBasedGauge64,
		divertFailedProxyConnectionsAsymmetricLevelMax	CounterBasedGauge64
	}

divertFailedProxyConnectionsAsymmetricLevelName OBJECT-TYPE
	SYNTAX      DisplayString
	MAX-ACCESS  not-accessible
	STATUS      current
	DESCRIPTION
	"Table entry display string for divertFailedProxyConnectionsAsymmetric"
	::={divertFailedProxyConnectionsAsymmetricLevelEntry 1}

divertFailedProxyConnectionsAsymmetricLevelVal OBJECT-TYPE
	SYNTAX	 Counter64
	MAX-ACCESS  read-only
	STATUS      current
	DESCRIPTION
	"Table entry attribute for divertFailedProxyConnectionsAsymmetric"
	::={divertFailedProxyConnectionsAsymmetricLevelEntry 2}

divertFailedProxyConnectionsAsymmetricLevelMom OBJECT-TYPE
	SYNTAX	 CounterBasedGauge64
	MAX-ACCESS  read-only
	STATUS      current
	DESCRIPTION
	"Table entry attribute for divertFailedProxyConnectionsAsymmetric"
	::={divertFailedProxyConnectionsAsymmetricLevelEntry 3}

divertFailedProxyConnectionsAsymmetricLevelMax OBJECT-TYPE
	SYNTAX	 CounterBasedGauge64
	MAX-ACCESS  read-only
	STATUS      current
	DESCRIPTION
	"Table entry attribute for divertFailedProxyConnectionsAsymmetric"
	::={divertFailedProxyConnectionsAsymmetricLevelEntry 4}


divertFailedProxyConnectionsOutOfProxies	OBJECT IDENTIFIER ::={divert 23}

divertFailedProxyConnectionsOutOfProxiesVal	OBJECT-TYPE
	SYNTAX	 Counter64
	MAX-ACCESS read-only
	STATUS current
	DESCRIPTION "Proxy connections failed (out of proxies)"

	::={divertFailedProxyConnectionsOutOfProxies 1}

divertFailedProxyConnectionsOutOfProxiesMom	OBJECT-TYPE
	SYNTAX	 CounterBasedGauge64
	MAX-ACCESS read-only
	STATUS current
	DESCRIPTION "Proxy connections failed (out of proxies)"

	::={divertFailedProxyConnectionsOutOfProxies 2}

divertFailedProxyConnectionsOutOfProxiesMax	OBJECT-TYPE
	SYNTAX	 CounterBasedGauge64
	MAX-ACCESS read-only
	STATUS current
	DESCRIPTION "Proxy connections failed (out of proxies)"

	::={divertFailedProxyConnectionsOutOfProxies 3}

divertFailedProxyConnectionsOutOfProxiesLevelTable OBJECT-TYPE
	SYNTAX      SEQUENCE OF DivertFailedProxyConnectionsOutOfProxiesLevelEntry
	MAX-ACCESS  not-accessible
	STATUS      current
	DESCRIPTION
	"Table for divertFailedProxyConnectionsOutOfProxies"
	::={divertFailedProxyConnectionsOutOfProxies 4}

divertFailedProxyConnectionsOutOfProxiesLevelEntry OBJECT-TYPE
	SYNTAX      DivertFailedProxyConnectionsOutOfProxiesLevelEntry
	MAX-ACCESS  not-accessible
	STATUS      current
	DESCRIPTION
	"Table entry for divertFailedProxyConnectionsOutOfProxies"
	INDEX { divertFailedProxyConnectionsOutOfProxiesLevelName }
	::={divertFailedProxyConnectionsOutOfProxiesLevelTable 1}

DivertFailedProxyConnectionsOutOfProxiesLevelEntry ::=
	SEQUENCE {
		divertFailedProxyConnectionsOutOfProxiesLevelName	DisplayString,
		divertFailedProxyConnectionsOutOfProxiesLevelVal	Counter64,
		divertFailedProxyConnectionsOutOfProxiesLevelMom	CounterBasedGauge64,
		divertFailedProxyConnectionsOutOfProxiesLevelMax	CounterBasedGauge64
	}

divertFailedProxyConnectionsOutOfProxiesLevelName OBJECT-TYPE
	SYNTAX      DisplayString
	MAX-ACCESS  not-accessible
	STATUS      current
	DESCRIPTION
	"Table entry display string for divertFailedProxyConnectionsOutOfProxies"
	::={divertFailedProxyConnectionsOutOfProxiesLevelEntry 1}

divertFailedProxyConnectionsOutOfProxiesLevelVal OBJECT-TYPE
	SYNTAX	 Counter64
	MAX-ACCESS  read-only
	STATUS      current
	DESCRIPTION
	"Table entry attribute for divertFailedProxyConnectionsOutOfProxies"
	::={divertFailedProxyConnectionsOutOfProxiesLevelEntry 2}

divertFailedProxyConnectionsOutOfProxiesLevelMom OBJECT-TYPE
	SYNTAX	 CounterBasedGauge64
	MAX-ACCESS  read-only
	STATUS      current
	DESCRIPTION
	"Table entry attribute for divertFailedProxyConnectionsOutOfProxies"
	::={divertFailedProxyConnectionsOutOfProxiesLevelEntry 3}

divertFailedProxyConnectionsOutOfProxiesLevelMax OBJECT-TYPE
	SYNTAX	 CounterBasedGauge64
	MAX-ACCESS  read-only
	STATUS      current
	DESCRIPTION
	"Table entry attribute for divertFailedProxyConnectionsOutOfProxies"
	::={divertFailedProxyConnectionsOutOfProxiesLevelEntry 4}


divertFailedProxyConnectionsApplyL2	OBJECT IDENTIFIER ::={divert 24}

divertFailedProxyConnectionsApplyL2Val	OBJECT-TYPE
	SYNTAX	 Counter64
	MAX-ACCESS read-only
	STATUS current
	DESCRIPTION "Proxy connections failed (apply L2)"

	::={divertFailedProxyConnectionsApplyL2 1}

divertFailedProxyConnectionsApplyL2Mom	OBJECT-TYPE
	SYNTAX	 CounterBasedGauge64
	MAX-ACCESS read-only
	STATUS current
	DESCRIPTION "Proxy connections failed (apply L2)"

	::={divertFailedProxyConnectionsApplyL2 2}

divertFailedProxyConnectionsApplyL2Max	OBJECT-TYPE
	SYNTAX	 CounterBasedGauge64
	MAX-ACCESS read-only
	STATUS current
	DESCRIPTION "Proxy connections failed (apply L2)"

	::={divertFailedProxyConnectionsApplyL2 3}

divertFailedProxyConnectionsApplyL2LevelTable OBJECT-TYPE
	SYNTAX      SEQUENCE OF DivertFailedProxyConnectionsApplyL2LevelEntry
	MAX-ACCESS  not-accessible
	STATUS      current
	DESCRIPTION
	"Table for divertFailedProxyConnectionsApplyL2"
	::={divertFailedProxyConnectionsApplyL2 4}

divertFailedProxyConnectionsApplyL2LevelEntry OBJECT-TYPE
	SYNTAX      DivertFailedProxyConnectionsApplyL2LevelEntry
	MAX-ACCESS  not-accessible
	STATUS      current
	DESCRIPTION
	"Table entry for divertFailedProxyConnectionsApplyL2"
	INDEX { divertFailedProxyConnectionsApplyL2LevelName }
	::={divertFailedProxyConnectionsApplyL2LevelTable 1}

DivertFailedProxyConnectionsApplyL2LevelEntry ::=
	SEQUENCE {
		divertFailedProxyConnectionsApplyL2LevelName	DisplayString,
		divertFailedProxyConnectionsApplyL2LevelVal	Counter64,
		divertFailedProxyConnectionsApplyL2LevelMom	CounterBasedGauge64,
		divertFailedProxyConnectionsApplyL2LevelMax	CounterBasedGauge64
	}

divertFailedProxyConnectionsApplyL2LevelName OBJECT-TYPE
	SYNTAX      DisplayString
	MAX-ACCESS  not-accessible
	STATUS      current
	DESCRIPTION
	"Table entry display string for divertFailedProxyConnectionsApplyL2"
	::={divertFailedProxyConnectionsApplyL2LevelEntry 1}

divertFailedProxyConnectionsApplyL2LevelVal OBJECT-TYPE
	SYNTAX	 Counter64
	MAX-ACCESS  read-only
	STATUS      current
	DESCRIPTION
	"Table entry attribute for divertFailedProxyConnectionsApplyL2"
	::={divertFailedProxyConnectionsApplyL2LevelEntry 2}

divertFailedProxyConnectionsApplyL2LevelMom OBJECT-TYPE
	SYNTAX	 CounterBasedGauge64
	MAX-ACCESS  read-only
	STATUS      current
	DESCRIPTION
	"Table entry attribute for divertFailedProxyConnectionsApplyL2"
	::={divertFailedProxyConnectionsApplyL2LevelEntry 3}

divertFailedProxyConnectionsApplyL2LevelMax OBJECT-TYPE
	SYNTAX	 CounterBasedGauge64
	MAX-ACCESS  read-only
	STATUS      current
	DESCRIPTION
	"Table entry attribute for divertFailedProxyConnectionsApplyL2"
	::={divertFailedProxyConnectionsApplyL2LevelEntry 4}


divertInjectsFailures	OBJECT IDENTIFIER ::={divert 25}

divertInjectsFailuresVal	OBJECT-TYPE
	SYNTAX	 Counter64
	MAX-ACCESS read-only
	STATUS current
	DESCRIPTION "Inject data failures"

	::={divertInjectsFailures 1}

divertInjectsFailuresMom	OBJECT-TYPE
	SYNTAX	 CounterBasedGauge64
	MAX-ACCESS read-only
	STATUS current
	DESCRIPTION "Inject data failures"

	::={divertInjectsFailures 2}

divertInjectsFailuresMax	OBJECT-TYPE
	SYNTAX	 CounterBasedGauge64
	MAX-ACCESS read-only
	STATUS current
	DESCRIPTION "Inject data failures"

	::={divertInjectsFailures 3}

divertInjectsFailuresLevelTable OBJECT-TYPE
	SYNTAX      SEQUENCE OF DivertInjectsFailuresLevelEntry
	MAX-ACCESS  not-accessible
	STATUS      current
	DESCRIPTION
	"Table for divertInjectsFailures"
	::={divertInjectsFailures 4}

divertInjectsFailuresLevelEntry OBJECT-TYPE
	SYNTAX      DivertInjectsFailuresLevelEntry
	MAX-ACCESS  not-accessible
	STATUS      current
	DESCRIPTION
	"Table entry for divertInjectsFailures"
	INDEX { divertInjectsFailuresLevelName }
	::={divertInjectsFailuresLevelTable 1}

DivertInjectsFailuresLevelEntry ::=
	SEQUENCE {
		divertInjectsFailuresLevelName	DisplayString,
		divertInjectsFailuresLevelVal	Counter64,
		divertInjectsFailuresLevelMom	CounterBasedGauge64,
		divertInjectsFailuresLevelMax	CounterBasedGauge64
	}

divertInjectsFailuresLevelName OBJECT-TYPE
	SYNTAX      DisplayString
	MAX-ACCESS  not-accessible
	STATUS      current
	DESCRIPTION
	"Table entry display string for divertInjectsFailures"
	::={divertInjectsFailuresLevelEntry 1}

divertInjectsFailuresLevelVal OBJECT-TYPE
	SYNTAX	 Counter64
	MAX-ACCESS  read-only
	STATUS      current
	DESCRIPTION
	"Table entry attribute for divertInjectsFailures"
	::={divertInjectsFailuresLevelEntry 2}

divertInjectsFailuresLevelMom OBJECT-TYPE
	SYNTAX	 CounterBasedGauge64
	MAX-ACCESS  read-only
	STATUS      current
	DESCRIPTION
	"Table entry attribute for divertInjectsFailures"
	::={divertInjectsFailuresLevelEntry 3}

divertInjectsFailuresLevelMax OBJECT-TYPE
	SYNTAX	 CounterBasedGauge64
	MAX-ACCESS  read-only
	STATUS      current
	DESCRIPTION
	"Table entry attribute for divertInjectsFailures"
	::={divertInjectsFailuresLevelEntry 4}


divertUndersizeL2	OBJECT IDENTIFIER ::={divert 26}

divertUndersizeL2Val	OBJECT-TYPE
	SYNTAX	 Counter64
	MAX-ACCESS read-only
	STATUS current
	DESCRIPTION "Too small L2-headers"

	::={divertUndersizeL2 1}

divertUndersizeL2Mom	OBJECT-TYPE
	SYNTAX	 CounterBasedGauge64
	MAX-ACCESS read-only
	STATUS current
	DESCRIPTION "Too small L2-headers"

	::={divertUndersizeL2 2}

divertUndersizeL2Max	OBJECT-TYPE
	SYNTAX	 CounterBasedGauge64
	MAX-ACCESS read-only
	STATUS current
	DESCRIPTION "Too small L2-headers"

	::={divertUndersizeL2 3}

divertUndersizeL2LevelTable OBJECT-TYPE
	SYNTAX      SEQUENCE OF DivertUndersizeL2LevelEntry
	MAX-ACCESS  not-accessible
	STATUS      current
	DESCRIPTION
	"Table for divertUndersizeL2"
	::={divertUndersizeL2 4}

divertUndersizeL2LevelEntry OBJECT-TYPE
	SYNTAX      DivertUndersizeL2LevelEntry
	MAX-ACCESS  not-accessible
	STATUS      current
	DESCRIPTION
	"Table entry for divertUndersizeL2"
	INDEX { divertUndersizeL2LevelName }
	::={divertUndersizeL2LevelTable 1}

DivertUndersizeL2LevelEntry ::=
	SEQUENCE {
		divertUndersizeL2LevelName	DisplayString,
		divertUndersizeL2LevelVal	Counter64,
		divertUndersizeL2LevelMom	CounterBasedGauge64,
		divertUndersizeL2LevelMax	CounterBasedGauge64
	}

divertUndersizeL2LevelName OBJECT-TYPE
	SYNTAX      DisplayString
	MAX-ACCESS  not-accessible
	STATUS      current
	DESCRIPTION
	"Table entry display string for divertUndersizeL2"
	::={divertUndersizeL2LevelEntry 1}

divertUndersizeL2LevelVal OBJECT-TYPE
	SYNTAX	 Counter64
	MAX-ACCESS  read-only
	STATUS      current
	DESCRIPTION
	"Table entry attribute for divertUndersizeL2"
	::={divertUndersizeL2LevelEntry 2}

divertUndersizeL2LevelMom OBJECT-TYPE
	SYNTAX	 CounterBasedGauge64
	MAX-ACCESS  read-only
	STATUS      current
	DESCRIPTION
	"Table entry attribute for divertUndersizeL2"
	::={divertUndersizeL2LevelEntry 3}

divertUndersizeL2LevelMax OBJECT-TYPE
	SYNTAX	 CounterBasedGauge64
	MAX-ACCESS  read-only
	STATUS      current
	DESCRIPTION
	"Table entry attribute for divertUndersizeL2"
	::={divertUndersizeL2LevelEntry 4}


divertIngressPacketsNoChannel	OBJECT IDENTIFIER ::={divert 27}

divertIngressPacketsNoChannelVal	OBJECT-TYPE
	SYNTAX	 Counter64
	MAX-ACCESS read-only
	STATUS current
	DESCRIPTION "Ingress packets with missing channel"

	::={divertIngressPacketsNoChannel 1}

divertIngressPacketsNoChannelMom	OBJECT-TYPE
	SYNTAX	 CounterBasedGauge64
	MAX-ACCESS read-only
	STATUS current
	DESCRIPTION "Ingress packets with missing channel"

	::={divertIngressPacketsNoChannel 2}

divertIngressPacketsNoChannelMax	OBJECT-TYPE
	SYNTAX	 CounterBasedGauge64
	MAX-ACCESS read-only
	STATUS current
	DESCRIPTION "Ingress packets with missing channel"

	::={divertIngressPacketsNoChannel 3}

divertIngressPacketsNoChannelLevelTable OBJECT-TYPE
	SYNTAX      SEQUENCE OF DivertIngressPacketsNoChannelLevelEntry
	MAX-ACCESS  not-accessible
	STATUS      current
	DESCRIPTION
	"Table for divertIngressPacketsNoChannel"
	::={divertIngressPacketsNoChannel 4}

divertIngressPacketsNoChannelLevelEntry OBJECT-TYPE
	SYNTAX      DivertIngressPacketsNoChannelLevelEntry
	MAX-ACCESS  not-accessible
	STATUS      current
	DESCRIPTION
	"Table entry for divertIngressPacketsNoChannel"
	INDEX { divertIngressPacketsNoChannelLevelName }
	::={divertIngressPacketsNoChannelLevelTable 1}

DivertIngressPacketsNoChannelLevelEntry ::=
	SEQUENCE {
		divertIngressPacketsNoChannelLevelName	DisplayString,
		divertIngressPacketsNoChannelLevelVal	Counter64,
		divertIngressPacketsNoChannelLevelMom	CounterBasedGauge64,
		divertIngressPacketsNoChannelLevelMax	CounterBasedGauge64
	}

divertIngressPacketsNoChannelLevelName OBJECT-TYPE
	SYNTAX      DisplayString
	MAX-ACCESS  not-accessible
	STATUS      current
	DESCRIPTION
	"Table entry display string for divertIngressPacketsNoChannel"
	::={divertIngressPacketsNoChannelLevelEntry 1}

divertIngressPacketsNoChannelLevelVal OBJECT-TYPE
	SYNTAX	 Counter64
	MAX-ACCESS  read-only
	STATUS      current
	DESCRIPTION
	"Table entry attribute for divertIngressPacketsNoChannel"
	::={divertIngressPacketsNoChannelLevelEntry 2}

divertIngressPacketsNoChannelLevelMom OBJECT-TYPE
	SYNTAX	 CounterBasedGauge64
	MAX-ACCESS  read-only
	STATUS      current
	DESCRIPTION
	"Table entry attribute for divertIngressPacketsNoChannel"
	::={divertIngressPacketsNoChannelLevelEntry 3}

divertIngressPacketsNoChannelLevelMax OBJECT-TYPE
	SYNTAX	 CounterBasedGauge64
	MAX-ACCESS  read-only
	STATUS      current
	DESCRIPTION
	"Table entry attribute for divertIngressPacketsNoChannel"
	::={divertIngressPacketsNoChannelLevelEntry 4}


divertProxyAsymRemoteEgressPackets	OBJECT IDENTIFIER ::={divert 28}

divertProxyAsymRemoteEgressPacketsVal	OBJECT-TYPE
	SYNTAX	 Counter64
	MAX-ACCESS read-only
	STATUS current
	DESCRIPTION "Proxy asym remote egress packets"

	::={divertProxyAsymRemoteEgressPackets 1}

divertProxyAsymRemoteEgressPacketsMom	OBJECT-TYPE
	SYNTAX	 CounterBasedGauge64
	MAX-ACCESS read-only
	STATUS current
	DESCRIPTION "Proxy asym remote egress packets"

	::={divertProxyAsymRemoteEgressPackets 2}

divertProxyAsymRemoteEgressPacketsMax	OBJECT-TYPE
	SYNTAX	 CounterBasedGauge64
	MAX-ACCESS read-only
	STATUS current
	DESCRIPTION "Proxy asym remote egress packets"

	::={divertProxyAsymRemoteEgressPackets 3}

divertProxyAsymRemoteEgressPacketsLevelTable OBJECT-TYPE
	SYNTAX      SEQUENCE OF DivertProxyAsymRemoteEgressPacketsLevelEntry
	MAX-ACCESS  not-accessible
	STATUS      current
	DESCRIPTION
	"Table for divertProxyAsymRemoteEgressPackets"
	::={divertProxyAsymRemoteEgressPackets 4}

divertProxyAsymRemoteEgressPacketsLevelEntry OBJECT-TYPE
	SYNTAX      DivertProxyAsymRemoteEgressPacketsLevelEntry
	MAX-ACCESS  not-accessible
	STATUS      current
	DESCRIPTION
	"Table entry for divertProxyAsymRemoteEgressPackets"
	INDEX { divertProxyAsymRemoteEgressPacketsLevelName }
	::={divertProxyAsymRemoteEgressPacketsLevelTable 1}

DivertProxyAsymRemoteEgressPacketsLevelEntry ::=
	SEQUENCE {
		divertProxyAsymRemoteEgressPacketsLevelName	DisplayString,
		divertProxyAsymRemoteEgressPacketsLevelVal	Counter64,
		divertProxyAsymRemoteEgressPacketsLevelMom	CounterBasedGauge64,
		divertProxyAsymRemoteEgressPacketsLevelMax	CounterBasedGauge64
	}

divertProxyAsymRemoteEgressPacketsLevelName OBJECT-TYPE
	SYNTAX      DisplayString
	MAX-ACCESS  not-accessible
	STATUS      current
	DESCRIPTION
	"Table entry display string for divertProxyAsymRemoteEgressPackets"
	::={divertProxyAsymRemoteEgressPacketsLevelEntry 1}

divertProxyAsymRemoteEgressPacketsLevelVal OBJECT-TYPE
	SYNTAX	 Counter64
	MAX-ACCESS  read-only
	STATUS      current
	DESCRIPTION
	"Table entry attribute for divertProxyAsymRemoteEgressPackets"
	::={divertProxyAsymRemoteEgressPacketsLevelEntry 2}

divertProxyAsymRemoteEgressPacketsLevelMom OBJECT-TYPE
	SYNTAX	 CounterBasedGauge64
	MAX-ACCESS  read-only
	STATUS      current
	DESCRIPTION
	"Table entry attribute for divertProxyAsymRemoteEgressPackets"
	::={divertProxyAsymRemoteEgressPacketsLevelEntry 3}

divertProxyAsymRemoteEgressPacketsLevelMax OBJECT-TYPE
	SYNTAX	 CounterBasedGauge64
	MAX-ACCESS  read-only
	STATUS      current
	DESCRIPTION
	"Table entry attribute for divertProxyAsymRemoteEgressPackets"
	::={divertProxyAsymRemoteEgressPacketsLevelEntry 4}


divertProxyAsymRemoteIngressPackets	OBJECT IDENTIFIER ::={divert 29}

divertProxyAsymRemoteIngressPacketsVal	OBJECT-TYPE
	SYNTAX	 Counter64
	MAX-ACCESS read-only
	STATUS current
	DESCRIPTION "Proxy asym remote ingress packets"

	::={divertProxyAsymRemoteIngressPackets 1}

divertProxyAsymRemoteIngressPacketsMom	OBJECT-TYPE
	SYNTAX	 CounterBasedGauge64
	MAX-ACCESS read-only
	STATUS current
	DESCRIPTION "Proxy asym remote ingress packets"

	::={divertProxyAsymRemoteIngressPackets 2}

divertProxyAsymRemoteIngressPacketsMax	OBJECT-TYPE
	SYNTAX	 CounterBasedGauge64
	MAX-ACCESS read-only
	STATUS current
	DESCRIPTION "Proxy asym remote ingress packets"

	::={divertProxyAsymRemoteIngressPackets 3}

divertProxyAsymRemoteIngressPacketsLevelTable OBJECT-TYPE
	SYNTAX      SEQUENCE OF DivertProxyAsymRemoteIngressPacketsLevelEntry
	MAX-ACCESS  not-accessible
	STATUS      current
	DESCRIPTION
	"Table for divertProxyAsymRemoteIngressPackets"
	::={divertProxyAsymRemoteIngressPackets 4}

divertProxyAsymRemoteIngressPacketsLevelEntry OBJECT-TYPE
	SYNTAX      DivertProxyAsymRemoteIngressPacketsLevelEntry
	MAX-ACCESS  not-accessible
	STATUS      current
	DESCRIPTION
	"Table entry for divertProxyAsymRemoteIngressPackets"
	INDEX { divertProxyAsymRemoteIngressPacketsLevelName }
	::={divertProxyAsymRemoteIngressPacketsLevelTable 1}

DivertProxyAsymRemoteIngressPacketsLevelEntry ::=
	SEQUENCE {
		divertProxyAsymRemoteIngressPacketsLevelName	DisplayString,
		divertProxyAsymRemoteIngressPacketsLevelVal	Counter64,
		divertProxyAsymRemoteIngressPacketsLevelMom	CounterBasedGauge64,
		divertProxyAsymRemoteIngressPacketsLevelMax	CounterBasedGauge64
	}

divertProxyAsymRemoteIngressPacketsLevelName OBJECT-TYPE
	SYNTAX      DisplayString
	MAX-ACCESS  not-accessible
	STATUS      current
	DESCRIPTION
	"Table entry display string for divertProxyAsymRemoteIngressPackets"
	::={divertProxyAsymRemoteIngressPacketsLevelEntry 1}

divertProxyAsymRemoteIngressPacketsLevelVal OBJECT-TYPE
	SYNTAX	 Counter64
	MAX-ACCESS  read-only
	STATUS      current
	DESCRIPTION
	"Table entry attribute for divertProxyAsymRemoteIngressPackets"
	::={divertProxyAsymRemoteIngressPacketsLevelEntry 2}

divertProxyAsymRemoteIngressPacketsLevelMom OBJECT-TYPE
	SYNTAX	 CounterBasedGauge64
	MAX-ACCESS  read-only
	STATUS      current
	DESCRIPTION
	"Table entry attribute for divertProxyAsymRemoteIngressPackets"
	::={divertProxyAsymRemoteIngressPacketsLevelEntry 3}

divertProxyAsymRemoteIngressPacketsLevelMax OBJECT-TYPE
	SYNTAX	 CounterBasedGauge64
	MAX-ACCESS  read-only
	STATUS      current
	DESCRIPTION
	"Table entry attribute for divertProxyAsymRemoteIngressPackets"
	::={divertProxyAsymRemoteIngressPacketsLevelEntry 4}


divertProxyAsymRemoteIngressErrors	OBJECT IDENTIFIER ::={divert 30}

divertProxyAsymRemoteIngressErrorsVal	OBJECT-TYPE
	SYNTAX	 Counter64
	MAX-ACCESS read-only
	STATUS current
	DESCRIPTION "Proxy asym remote ingress errors"

	::={divertProxyAsymRemoteIngressErrors 1}

divertProxyAsymRemoteIngressErrorsMom	OBJECT-TYPE
	SYNTAX	 CounterBasedGauge64
	MAX-ACCESS read-only
	STATUS current
	DESCRIPTION "Proxy asym remote ingress errors"

	::={divertProxyAsymRemoteIngressErrors 2}

divertProxyAsymRemoteIngressErrorsMax	OBJECT-TYPE
	SYNTAX	 CounterBasedGauge64
	MAX-ACCESS read-only
	STATUS current
	DESCRIPTION "Proxy asym remote ingress errors"

	::={divertProxyAsymRemoteIngressErrors 3}

divertProxyAsymRemoteIngressErrorsLevelTable OBJECT-TYPE
	SYNTAX      SEQUENCE OF DivertProxyAsymRemoteIngressErrorsLevelEntry
	MAX-ACCESS  not-accessible
	STATUS      current
	DESCRIPTION
	"Table for divertProxyAsymRemoteIngressErrors"
	::={divertProxyAsymRemoteIngressErrors 4}

divertProxyAsymRemoteIngressErrorsLevelEntry OBJECT-TYPE
	SYNTAX      DivertProxyAsymRemoteIngressErrorsLevelEntry
	MAX-ACCESS  not-accessible
	STATUS      current
	DESCRIPTION
	"Table entry for divertProxyAsymRemoteIngressErrors"
	INDEX { divertProxyAsymRemoteIngressErrorsLevelName }
	::={divertProxyAsymRemoteIngressErrorsLevelTable 1}

DivertProxyAsymRemoteIngressErrorsLevelEntry ::=
	SEQUENCE {
		divertProxyAsymRemoteIngressErrorsLevelName	DisplayString,
		divertProxyAsymRemoteIngressErrorsLevelVal	Counter64,
		divertProxyAsymRemoteIngressErrorsLevelMom	CounterBasedGauge64,
		divertProxyAsymRemoteIngressErrorsLevelMax	CounterBasedGauge64
	}

divertProxyAsymRemoteIngressErrorsLevelName OBJECT-TYPE
	SYNTAX      DisplayString
	MAX-ACCESS  not-accessible
	STATUS      current
	DESCRIPTION
	"Table entry display string for divertProxyAsymRemoteIngressErrors"
	::={divertProxyAsymRemoteIngressErrorsLevelEntry 1}

divertProxyAsymRemoteIngressErrorsLevelVal OBJECT-TYPE
	SYNTAX	 Counter64
	MAX-ACCESS  read-only
	STATUS      current
	DESCRIPTION
	"Table entry attribute for divertProxyAsymRemoteIngressErrors"
	::={divertProxyAsymRemoteIngressErrorsLevelEntry 2}

divertProxyAsymRemoteIngressErrorsLevelMom OBJECT-TYPE
	SYNTAX	 CounterBasedGauge64
	MAX-ACCESS  read-only
	STATUS      current
	DESCRIPTION
	"Table entry attribute for divertProxyAsymRemoteIngressErrors"
	::={divertProxyAsymRemoteIngressErrorsLevelEntry 3}

divertProxyAsymRemoteIngressErrorsLevelMax OBJECT-TYPE
	SYNTAX	 CounterBasedGauge64
	MAX-ACCESS  read-only
	STATUS      current
	DESCRIPTION
	"Table entry attribute for divertProxyAsymRemoteIngressErrors"
	::={divertProxyAsymRemoteIngressErrorsLevelEntry 4}


divertProxyAsymRemoteIngressErrorNoRule	OBJECT IDENTIFIER ::={divert 31}

divertProxyAsymRemoteIngressErrorNoRuleVal	OBJECT-TYPE
	SYNTAX	 Counter64
	MAX-ACCESS read-only
	STATUS current
	DESCRIPTION "Proxy asym remote ingress error (no matching divert rule)"

	::={divertProxyAsymRemoteIngressErrorNoRule 1}

divertProxyAsymRemoteIngressErrorNoRuleMom	OBJECT-TYPE
	SYNTAX	 CounterBasedGauge64
	MAX-ACCESS read-only
	STATUS current
	DESCRIPTION "Proxy asym remote ingress error (no matching divert rule)"

	::={divertProxyAsymRemoteIngressErrorNoRule 2}

divertProxyAsymRemoteIngressErrorNoRuleMax	OBJECT-TYPE
	SYNTAX	 CounterBasedGauge64
	MAX-ACCESS read-only
	STATUS current
	DESCRIPTION "Proxy asym remote ingress error (no matching divert rule)"

	::={divertProxyAsymRemoteIngressErrorNoRule 3}

divertProxyAsymRemoteIngressErrorNoRuleLevelTable OBJECT-TYPE
	SYNTAX      SEQUENCE OF DivertProxyAsymRemoteIngressErrorNoRuleLevelEntry
	MAX-ACCESS  not-accessible
	STATUS      current
	DESCRIPTION
	"Table for divertProxyAsymRemoteIngressErrorNoRule"
	::={divertProxyAsymRemoteIngressErrorNoRule 4}

divertProxyAsymRemoteIngressErrorNoRuleLevelEntry OBJECT-TYPE
	SYNTAX      DivertProxyAsymRemoteIngressErrorNoRuleLevelEntry
	MAX-ACCESS  not-accessible
	STATUS      current
	DESCRIPTION
	"Table entry for divertProxyAsymRemoteIngressErrorNoRule"
	INDEX { divertProxyAsymRemoteIngressErrorNoRuleLevelName }
	::={divertProxyAsymRemoteIngressErrorNoRuleLevelTable 1}

DivertProxyAsymRemoteIngressErrorNoRuleLevelEntry ::=
	SEQUENCE {
		divertProxyAsymRemoteIngressErrorNoRuleLevelName	DisplayString,
		divertProxyAsymRemoteIngressErrorNoRuleLevelVal	Counter64,
		divertProxyAsymRemoteIngressErrorNoRuleLevelMom	CounterBasedGauge64,
		divertProxyAsymRemoteIngressErrorNoRuleLevelMax	CounterBasedGauge64
	}

divertProxyAsymRemoteIngressErrorNoRuleLevelName OBJECT-TYPE
	SYNTAX      DisplayString
	MAX-ACCESS  not-accessible
	STATUS      current
	DESCRIPTION
	"Table entry display string for divertProxyAsymRemoteIngressErrorNoRule"
	::={divertProxyAsymRemoteIngressErrorNoRuleLevelEntry 1}

divertProxyAsymRemoteIngressErrorNoRuleLevelVal OBJECT-TYPE
	SYNTAX	 Counter64
	MAX-ACCESS  read-only
	STATUS      current
	DESCRIPTION
	"Table entry attribute for divertProxyAsymRemoteIngressErrorNoRule"
	::={divertProxyAsymRemoteIngressErrorNoRuleLevelEntry 2}

divertProxyAsymRemoteIngressErrorNoRuleLevelMom OBJECT-TYPE
	SYNTAX	 CounterBasedGauge64
	MAX-ACCESS  read-only
	STATUS      current
	DESCRIPTION
	"Table entry attribute for divertProxyAsymRemoteIngressErrorNoRule"
	::={divertProxyAsymRemoteIngressErrorNoRuleLevelEntry 3}

divertProxyAsymRemoteIngressErrorNoRuleLevelMax OBJECT-TYPE
	SYNTAX	 CounterBasedGauge64
	MAX-ACCESS  read-only
	STATUS      current
	DESCRIPTION
	"Table entry attribute for divertProxyAsymRemoteIngressErrorNoRule"
	::={divertProxyAsymRemoteIngressErrorNoRuleLevelEntry 4}


divertProxyAsymRemoteIngressErrorCorruptPacket	OBJECT IDENTIFIER ::={divert 32}

divertProxyAsymRemoteIngressErrorCorruptPacketVal	OBJECT-TYPE
	SYNTAX	 Counter64
	MAX-ACCESS read-only
	STATUS current
	DESCRIPTION "Proxy asym remote ingress error (corrupt packet)"

	::={divertProxyAsymRemoteIngressErrorCorruptPacket 1}

divertProxyAsymRemoteIngressErrorCorruptPacketMom	OBJECT-TYPE
	SYNTAX	 CounterBasedGauge64
	MAX-ACCESS read-only
	STATUS current
	DESCRIPTION "Proxy asym remote ingress error (corrupt packet)"

	::={divertProxyAsymRemoteIngressErrorCorruptPacket 2}

divertProxyAsymRemoteIngressErrorCorruptPacketMax	OBJECT-TYPE
	SYNTAX	 CounterBasedGauge64
	MAX-ACCESS read-only
	STATUS current
	DESCRIPTION "Proxy asym remote ingress error (corrupt packet)"

	::={divertProxyAsymRemoteIngressErrorCorruptPacket 3}

divertProxyAsymRemoteIngressErrorCorruptPacketLevelTable OBJECT-TYPE
	SYNTAX      SEQUENCE OF DivertProxyAsymRemoteIngressErrorCorruptPacketLevelEntry
	MAX-ACCESS  not-accessible
	STATUS      current
	DESCRIPTION
	"Table for divertProxyAsymRemoteIngressErrorCorruptPacket"
	::={divertProxyAsymRemoteIngressErrorCorruptPacket 4}

divertProxyAsymRemoteIngressErrorCorruptPacketLevelEntry OBJECT-TYPE
	SYNTAX      DivertProxyAsymRemoteIngressErrorCorruptPacketLevelEntry
	MAX-ACCESS  not-accessible
	STATUS      current
	DESCRIPTION
	"Table entry for divertProxyAsymRemoteIngressErrorCorruptPacket"
	INDEX { divertProxyAsymRemoteIngressErrorCorruptPacketLevelName }
	::={divertProxyAsymRemoteIngressErrorCorruptPacketLevelTable 1}

DivertProxyAsymRemoteIngressErrorCorruptPacketLevelEntry ::=
	SEQUENCE {
		divertProxyAsymRemoteIngressErrorCorruptPacketLevelName	DisplayString,
		divertProxyAsymRemoteIngressErrorCorruptPacketLevelVal	Counter64,
		divertProxyAsymRemoteIngressErrorCorruptPacketLevelMom	CounterBasedGauge64,
		divertProxyAsymRemoteIngressErrorCorruptPacketLevelMax	CounterBasedGauge64
	}

divertProxyAsymRemoteIngressErrorCorruptPacketLevelName OBJECT-TYPE
	SYNTAX      DisplayString
	MAX-ACCESS  not-accessible
	STATUS      current
	DESCRIPTION
	"Table entry display string for divertProxyAsymRemoteIngressErrorCorruptPacket"
	::={divertProxyAsymRemoteIngressErrorCorruptPacketLevelEntry 1}

divertProxyAsymRemoteIngressErrorCorruptPacketLevelVal OBJECT-TYPE
	SYNTAX	 Counter64
	MAX-ACCESS  read-only
	STATUS      current
	DESCRIPTION
	"Table entry attribute for divertProxyAsymRemoteIngressErrorCorruptPacket"
	::={divertProxyAsymRemoteIngressErrorCorruptPacketLevelEntry 2}

divertProxyAsymRemoteIngressErrorCorruptPacketLevelMom OBJECT-TYPE
	SYNTAX	 CounterBasedGauge64
	MAX-ACCESS  read-only
	STATUS      current
	DESCRIPTION
	"Table entry attribute for divertProxyAsymRemoteIngressErrorCorruptPacket"
	::={divertProxyAsymRemoteIngressErrorCorruptPacketLevelEntry 3}

divertProxyAsymRemoteIngressErrorCorruptPacketLevelMax OBJECT-TYPE
	SYNTAX	 CounterBasedGauge64
	MAX-ACCESS  read-only
	STATUS      current
	DESCRIPTION
	"Table entry attribute for divertProxyAsymRemoteIngressErrorCorruptPacket"
	::={divertProxyAsymRemoteIngressErrorCorruptPacketLevelEntry 4}


divertProxyAsymRemoteIngressErrorUnsupProto	OBJECT IDENTIFIER ::={divert 33}

divertProxyAsymRemoteIngressErrorUnsupProtoVal	OBJECT-TYPE
	SYNTAX	 Counter64
	MAX-ACCESS read-only
	STATUS current
	DESCRIPTION "Proxy asym remote ingress error (unsupported protocol)"

	::={divertProxyAsymRemoteIngressErrorUnsupProto 1}

divertProxyAsymRemoteIngressErrorUnsupProtoMom	OBJECT-TYPE
	SYNTAX	 CounterBasedGauge64
	MAX-ACCESS read-only
	STATUS current
	DESCRIPTION "Proxy asym remote ingress error (unsupported protocol)"

	::={divertProxyAsymRemoteIngressErrorUnsupProto 2}

divertProxyAsymRemoteIngressErrorUnsupProtoMax	OBJECT-TYPE
	SYNTAX	 CounterBasedGauge64
	MAX-ACCESS read-only
	STATUS current
	DESCRIPTION "Proxy asym remote ingress error (unsupported protocol)"

	::={divertProxyAsymRemoteIngressErrorUnsupProto 3}

divertProxyAsymRemoteIngressErrorUnsupProtoLevelTable OBJECT-TYPE
	SYNTAX      SEQUENCE OF DivertProxyAsymRemoteIngressErrorUnsupProtoLevelEntry
	MAX-ACCESS  not-accessible
	STATUS      current
	DESCRIPTION
	"Table for divertProxyAsymRemoteIngressErrorUnsupProto"
	::={divertProxyAsymRemoteIngressErrorUnsupProto 4}

divertProxyAsymRemoteIngressErrorUnsupProtoLevelEntry OBJECT-TYPE
	SYNTAX      DivertProxyAsymRemoteIngressErrorUnsupProtoLevelEntry
	MAX-ACCESS  not-accessible
	STATUS      current
	DESCRIPTION
	"Table entry for divertProxyAsymRemoteIngressErrorUnsupProto"
	INDEX { divertProxyAsymRemoteIngressErrorUnsupProtoLevelName }
	::={divertProxyAsymRemoteIngressErrorUnsupProtoLevelTable 1}

DivertProxyAsymRemoteIngressErrorUnsupProtoLevelEntry ::=
	SEQUENCE {
		divertProxyAsymRemoteIngressErrorUnsupProtoLevelName	DisplayString,
		divertProxyAsymRemoteIngressErrorUnsupProtoLevelVal	Counter64,
		divertProxyAsymRemoteIngressErrorUnsupProtoLevelMom	CounterBasedGauge64,
		divertProxyAsymRemoteIngressErrorUnsupProtoLevelMax	CounterBasedGauge64
	}

divertProxyAsymRemoteIngressErrorUnsupProtoLevelName OBJECT-TYPE
	SYNTAX      DisplayString
	MAX-ACCESS  not-accessible
	STATUS      current
	DESCRIPTION
	"Table entry display string for divertProxyAsymRemoteIngressErrorUnsupProto"
	::={divertProxyAsymRemoteIngressErrorUnsupProtoLevelEntry 1}

divertProxyAsymRemoteIngressErrorUnsupProtoLevelVal OBJECT-TYPE
	SYNTAX	 Counter64
	MAX-ACCESS  read-only
	STATUS      current
	DESCRIPTION
	"Table entry attribute for divertProxyAsymRemoteIngressErrorUnsupProto"
	::={divertProxyAsymRemoteIngressErrorUnsupProtoLevelEntry 2}

divertProxyAsymRemoteIngressErrorUnsupProtoLevelMom OBJECT-TYPE
	SYNTAX	 CounterBasedGauge64
	MAX-ACCESS  read-only
	STATUS      current
	DESCRIPTION
	"Table entry attribute for divertProxyAsymRemoteIngressErrorUnsupProto"
	::={divertProxyAsymRemoteIngressErrorUnsupProtoLevelEntry 3}

divertProxyAsymRemoteIngressErrorUnsupProtoLevelMax OBJECT-TYPE
	SYNTAX	 CounterBasedGauge64
	MAX-ACCESS  read-only
	STATUS      current
	DESCRIPTION
	"Table entry attribute for divertProxyAsymRemoteIngressErrorUnsupProto"
	::={divertProxyAsymRemoteIngressErrorUnsupProtoLevelEntry 4}


divertProxyAsymLocalEgressPackets	OBJECT IDENTIFIER ::={divert 34}

divertProxyAsymLocalEgressPacketsVal	OBJECT-TYPE
	SYNTAX	 Counter64
	MAX-ACCESS read-only
	STATUS current
	DESCRIPTION "Proxy asym local egress packets"

	::={divertProxyAsymLocalEgressPackets 1}

divertProxyAsymLocalEgressPacketsMom	OBJECT-TYPE
	SYNTAX	 CounterBasedGauge64
	MAX-ACCESS read-only
	STATUS current
	DESCRIPTION "Proxy asym local egress packets"

	::={divertProxyAsymLocalEgressPackets 2}

divertProxyAsymLocalEgressPacketsMax	OBJECT-TYPE
	SYNTAX	 CounterBasedGauge64
	MAX-ACCESS read-only
	STATUS current
	DESCRIPTION "Proxy asym local egress packets"

	::={divertProxyAsymLocalEgressPackets 3}

divertProxyAsymLocalEgressPacketsLevelTable OBJECT-TYPE
	SYNTAX      SEQUENCE OF DivertProxyAsymLocalEgressPacketsLevelEntry
	MAX-ACCESS  not-accessible
	STATUS      current
	DESCRIPTION
	"Table for divertProxyAsymLocalEgressPackets"
	::={divertProxyAsymLocalEgressPackets 4}

divertProxyAsymLocalEgressPacketsLevelEntry OBJECT-TYPE
	SYNTAX      DivertProxyAsymLocalEgressPacketsLevelEntry
	MAX-ACCESS  not-accessible
	STATUS      current
	DESCRIPTION
	"Table entry for divertProxyAsymLocalEgressPackets"
	INDEX { divertProxyAsymLocalEgressPacketsLevelName }
	::={divertProxyAsymLocalEgressPacketsLevelTable 1}

DivertProxyAsymLocalEgressPacketsLevelEntry ::=
	SEQUENCE {
		divertProxyAsymLocalEgressPacketsLevelName	DisplayString,
		divertProxyAsymLocalEgressPacketsLevelVal	Counter64,
		divertProxyAsymLocalEgressPacketsLevelMom	CounterBasedGauge64,
		divertProxyAsymLocalEgressPacketsLevelMax	CounterBasedGauge64
	}

divertProxyAsymLocalEgressPacketsLevelName OBJECT-TYPE
	SYNTAX      DisplayString
	MAX-ACCESS  not-accessible
	STATUS      current
	DESCRIPTION
	"Table entry display string for divertProxyAsymLocalEgressPackets"
	::={divertProxyAsymLocalEgressPacketsLevelEntry 1}

divertProxyAsymLocalEgressPacketsLevelVal OBJECT-TYPE
	SYNTAX	 Counter64
	MAX-ACCESS  read-only
	STATUS      current
	DESCRIPTION
	"Table entry attribute for divertProxyAsymLocalEgressPackets"
	::={divertProxyAsymLocalEgressPacketsLevelEntry 2}

divertProxyAsymLocalEgressPacketsLevelMom OBJECT-TYPE
	SYNTAX	 CounterBasedGauge64
	MAX-ACCESS  read-only
	STATUS      current
	DESCRIPTION
	"Table entry attribute for divertProxyAsymLocalEgressPackets"
	::={divertProxyAsymLocalEgressPacketsLevelEntry 3}

divertProxyAsymLocalEgressPacketsLevelMax OBJECT-TYPE
	SYNTAX	 CounterBasedGauge64
	MAX-ACCESS  read-only
	STATUS      current
	DESCRIPTION
	"Table entry attribute for divertProxyAsymLocalEgressPackets"
	::={divertProxyAsymLocalEgressPacketsLevelEntry 4}


divertProxyAsymLocalEgressErrors	OBJECT IDENTIFIER ::={divert 35}

divertProxyAsymLocalEgressErrorsVal	OBJECT-TYPE
	SYNTAX	 Counter64
	MAX-ACCESS read-only
	STATUS current
	DESCRIPTION "Proxy asym local egress errors"

	::={divertProxyAsymLocalEgressErrors 1}

divertProxyAsymLocalEgressErrorsMom	OBJECT-TYPE
	SYNTAX	 CounterBasedGauge64
	MAX-ACCESS read-only
	STATUS current
	DESCRIPTION "Proxy asym local egress errors"

	::={divertProxyAsymLocalEgressErrors 2}

divertProxyAsymLocalEgressErrorsMax	OBJECT-TYPE
	SYNTAX	 CounterBasedGauge64
	MAX-ACCESS read-only
	STATUS current
	DESCRIPTION "Proxy asym local egress errors"

	::={divertProxyAsymLocalEgressErrors 3}

divertProxyAsymLocalEgressErrorsLevelTable OBJECT-TYPE
	SYNTAX      SEQUENCE OF DivertProxyAsymLocalEgressErrorsLevelEntry
	MAX-ACCESS  not-accessible
	STATUS      current
	DESCRIPTION
	"Table for divertProxyAsymLocalEgressErrors"
	::={divertProxyAsymLocalEgressErrors 4}

divertProxyAsymLocalEgressErrorsLevelEntry OBJECT-TYPE
	SYNTAX      DivertProxyAsymLocalEgressErrorsLevelEntry
	MAX-ACCESS  not-accessible
	STATUS      current
	DESCRIPTION
	"Table entry for divertProxyAsymLocalEgressErrors"
	INDEX { divertProxyAsymLocalEgressErrorsLevelName }
	::={divertProxyAsymLocalEgressErrorsLevelTable 1}

DivertProxyAsymLocalEgressErrorsLevelEntry ::=
	SEQUENCE {
		divertProxyAsymLocalEgressErrorsLevelName	DisplayString,
		divertProxyAsymLocalEgressErrorsLevelVal	Counter64,
		divertProxyAsymLocalEgressErrorsLevelMom	CounterBasedGauge64,
		divertProxyAsymLocalEgressErrorsLevelMax	CounterBasedGauge64
	}

divertProxyAsymLocalEgressErrorsLevelName OBJECT-TYPE
	SYNTAX      DisplayString
	MAX-ACCESS  not-accessible
	STATUS      current
	DESCRIPTION
	"Table entry display string for divertProxyAsymLocalEgressErrors"
	::={divertProxyAsymLocalEgressErrorsLevelEntry 1}

divertProxyAsymLocalEgressErrorsLevelVal OBJECT-TYPE
	SYNTAX	 Counter64
	MAX-ACCESS  read-only
	STATUS      current
	DESCRIPTION
	"Table entry attribute for divertProxyAsymLocalEgressErrors"
	::={divertProxyAsymLocalEgressErrorsLevelEntry 2}

divertProxyAsymLocalEgressErrorsLevelMom OBJECT-TYPE
	SYNTAX	 CounterBasedGauge64
	MAX-ACCESS  read-only
	STATUS      current
	DESCRIPTION
	"Table entry attribute for divertProxyAsymLocalEgressErrors"
	::={divertProxyAsymLocalEgressErrorsLevelEntry 3}

divertProxyAsymLocalEgressErrorsLevelMax OBJECT-TYPE
	SYNTAX	 CounterBasedGauge64
	MAX-ACCESS  read-only
	STATUS      current
	DESCRIPTION
	"Table entry attribute for divertProxyAsymLocalEgressErrors"
	::={divertProxyAsymLocalEgressErrorsLevelEntry 4}


divertProxyAsymLocalEgressErrorNoRule	OBJECT IDENTIFIER ::={divert 36}

divertProxyAsymLocalEgressErrorNoRuleVal	OBJECT-TYPE
	SYNTAX	 Counter64
	MAX-ACCESS read-only
	STATUS current
	DESCRIPTION "Proxy asym local egress error packet (no matching divert rule)"

	::={divertProxyAsymLocalEgressErrorNoRule 1}

divertProxyAsymLocalEgressErrorNoRuleMom	OBJECT-TYPE
	SYNTAX	 CounterBasedGauge64
	MAX-ACCESS read-only
	STATUS current
	DESCRIPTION "Proxy asym local egress error packet (no matching divert rule)"

	::={divertProxyAsymLocalEgressErrorNoRule 2}

divertProxyAsymLocalEgressErrorNoRuleMax	OBJECT-TYPE
	SYNTAX	 CounterBasedGauge64
	MAX-ACCESS read-only
	STATUS current
	DESCRIPTION "Proxy asym local egress error packet (no matching divert rule)"

	::={divertProxyAsymLocalEgressErrorNoRule 3}

divertProxyAsymLocalEgressErrorNoRuleLevelTable OBJECT-TYPE
	SYNTAX      SEQUENCE OF DivertProxyAsymLocalEgressErrorNoRuleLevelEntry
	MAX-ACCESS  not-accessible
	STATUS      current
	DESCRIPTION
	"Table for divertProxyAsymLocalEgressErrorNoRule"
	::={divertProxyAsymLocalEgressErrorNoRule 4}

divertProxyAsymLocalEgressErrorNoRuleLevelEntry OBJECT-TYPE
	SYNTAX      DivertProxyAsymLocalEgressErrorNoRuleLevelEntry
	MAX-ACCESS  not-accessible
	STATUS      current
	DESCRIPTION
	"Table entry for divertProxyAsymLocalEgressErrorNoRule"
	INDEX { divertProxyAsymLocalEgressErrorNoRuleLevelName }
	::={divertProxyAsymLocalEgressErrorNoRuleLevelTable 1}

DivertProxyAsymLocalEgressErrorNoRuleLevelEntry ::=
	SEQUENCE {
		divertProxyAsymLocalEgressErrorNoRuleLevelName	DisplayString,
		divertProxyAsymLocalEgressErrorNoRuleLevelVal	Counter64,
		divertProxyAsymLocalEgressErrorNoRuleLevelMom	CounterBasedGauge64,
		divertProxyAsymLocalEgressErrorNoRuleLevelMax	CounterBasedGauge64
	}

divertProxyAsymLocalEgressErrorNoRuleLevelName OBJECT-TYPE
	SYNTAX      DisplayString
	MAX-ACCESS  not-accessible
	STATUS      current
	DESCRIPTION
	"Table entry display string for divertProxyAsymLocalEgressErrorNoRule"
	::={divertProxyAsymLocalEgressErrorNoRuleLevelEntry 1}

divertProxyAsymLocalEgressErrorNoRuleLevelVal OBJECT-TYPE
	SYNTAX	 Counter64
	MAX-ACCESS  read-only
	STATUS      current
	DESCRIPTION
	"Table entry attribute for divertProxyAsymLocalEgressErrorNoRule"
	::={divertProxyAsymLocalEgressErrorNoRuleLevelEntry 2}

divertProxyAsymLocalEgressErrorNoRuleLevelMom OBJECT-TYPE
	SYNTAX	 CounterBasedGauge64
	MAX-ACCESS  read-only
	STATUS      current
	DESCRIPTION
	"Table entry attribute for divertProxyAsymLocalEgressErrorNoRule"
	::={divertProxyAsymLocalEgressErrorNoRuleLevelEntry 3}

divertProxyAsymLocalEgressErrorNoRuleLevelMax OBJECT-TYPE
	SYNTAX	 CounterBasedGauge64
	MAX-ACCESS  read-only
	STATUS      current
	DESCRIPTION
	"Table entry attribute for divertProxyAsymLocalEgressErrorNoRule"
	::={divertProxyAsymLocalEgressErrorNoRuleLevelEntry 4}


divertProxyAsymLocalEgressErrorNotActive	OBJECT IDENTIFIER ::={divert 37}

divertProxyAsymLocalEgressErrorNotActiveVal	OBJECT-TYPE
	SYNTAX	 Counter64
	MAX-ACCESS read-only
	STATUS current
	DESCRIPTION "Proxy asym local egress error packet (divert channel not operational)"

	::={divertProxyAsymLocalEgressErrorNotActive 1}

divertProxyAsymLocalEgressErrorNotActiveMom	OBJECT-TYPE
	SYNTAX	 CounterBasedGauge64
	MAX-ACCESS read-only
	STATUS current
	DESCRIPTION "Proxy asym local egress error packet (divert channel not operational)"

	::={divertProxyAsymLocalEgressErrorNotActive 2}

divertProxyAsymLocalEgressErrorNotActiveMax	OBJECT-TYPE
	SYNTAX	 CounterBasedGauge64
	MAX-ACCESS read-only
	STATUS current
	DESCRIPTION "Proxy asym local egress error packet (divert channel not operational)"

	::={divertProxyAsymLocalEgressErrorNotActive 3}

divertProxyAsymLocalEgressErrorNotActiveLevelTable OBJECT-TYPE
	SYNTAX      SEQUENCE OF DivertProxyAsymLocalEgressErrorNotActiveLevelEntry
	MAX-ACCESS  not-accessible
	STATUS      current
	DESCRIPTION
	"Table for divertProxyAsymLocalEgressErrorNotActive"
	::={divertProxyAsymLocalEgressErrorNotActive 4}

divertProxyAsymLocalEgressErrorNotActiveLevelEntry OBJECT-TYPE
	SYNTAX      DivertProxyAsymLocalEgressErrorNotActiveLevelEntry
	MAX-ACCESS  not-accessible
	STATUS      current
	DESCRIPTION
	"Table entry for divertProxyAsymLocalEgressErrorNotActive"
	INDEX { divertProxyAsymLocalEgressErrorNotActiveLevelName }
	::={divertProxyAsymLocalEgressErrorNotActiveLevelTable 1}

DivertProxyAsymLocalEgressErrorNotActiveLevelEntry ::=
	SEQUENCE {
		divertProxyAsymLocalEgressErrorNotActiveLevelName	DisplayString,
		divertProxyAsymLocalEgressErrorNotActiveLevelVal	Counter64,
		divertProxyAsymLocalEgressErrorNotActiveLevelMom	CounterBasedGauge64,
		divertProxyAsymLocalEgressErrorNotActiveLevelMax	CounterBasedGauge64
	}

divertProxyAsymLocalEgressErrorNotActiveLevelName OBJECT-TYPE
	SYNTAX      DisplayString
	MAX-ACCESS  not-accessible
	STATUS      current
	DESCRIPTION
	"Table entry display string for divertProxyAsymLocalEgressErrorNotActive"
	::={divertProxyAsymLocalEgressErrorNotActiveLevelEntry 1}

divertProxyAsymLocalEgressErrorNotActiveLevelVal OBJECT-TYPE
	SYNTAX	 Counter64
	MAX-ACCESS  read-only
	STATUS      current
	DESCRIPTION
	"Table entry attribute for divertProxyAsymLocalEgressErrorNotActive"
	::={divertProxyAsymLocalEgressErrorNotActiveLevelEntry 2}

divertProxyAsymLocalEgressErrorNotActiveLevelMom OBJECT-TYPE
	SYNTAX	 CounterBasedGauge64
	MAX-ACCESS  read-only
	STATUS      current
	DESCRIPTION
	"Table entry attribute for divertProxyAsymLocalEgressErrorNotActive"
	::={divertProxyAsymLocalEgressErrorNotActiveLevelEntry 3}

divertProxyAsymLocalEgressErrorNotActiveLevelMax OBJECT-TYPE
	SYNTAX	 CounterBasedGauge64
	MAX-ACCESS  read-only
	STATUS      current
	DESCRIPTION
	"Table entry attribute for divertProxyAsymLocalEgressErrorNotActive"
	::={divertProxyAsymLocalEgressErrorNotActiveLevelEntry 4}


divertProxyAsymLocalEgressErrorAlreadyDiverted	OBJECT IDENTIFIER ::={divert 38}

divertProxyAsymLocalEgressErrorAlreadyDivertedVal	OBJECT-TYPE
	SYNTAX	 Counter64
	MAX-ACCESS read-only
	STATUS current
	DESCRIPTION "Proxy asym local egress error packet (already diverted)"

	::={divertProxyAsymLocalEgressErrorAlreadyDiverted 1}

divertProxyAsymLocalEgressErrorAlreadyDivertedMom	OBJECT-TYPE
	SYNTAX	 CounterBasedGauge64
	MAX-ACCESS read-only
	STATUS current
	DESCRIPTION "Proxy asym local egress error packet (already diverted)"

	::={divertProxyAsymLocalEgressErrorAlreadyDiverted 2}

divertProxyAsymLocalEgressErrorAlreadyDivertedMax	OBJECT-TYPE
	SYNTAX	 CounterBasedGauge64
	MAX-ACCESS read-only
	STATUS current
	DESCRIPTION "Proxy asym local egress error packet (already diverted)"

	::={divertProxyAsymLocalEgressErrorAlreadyDiverted 3}

divertProxyAsymLocalEgressErrorAlreadyDivertedLevelTable OBJECT-TYPE
	SYNTAX      SEQUENCE OF DivertProxyAsymLocalEgressErrorAlreadyDivertedLevelEntry
	MAX-ACCESS  not-accessible
	STATUS      current
	DESCRIPTION
	"Table for divertProxyAsymLocalEgressErrorAlreadyDiverted"
	::={divertProxyAsymLocalEgressErrorAlreadyDiverted 4}

divertProxyAsymLocalEgressErrorAlreadyDivertedLevelEntry OBJECT-TYPE
	SYNTAX      DivertProxyAsymLocalEgressErrorAlreadyDivertedLevelEntry
	MAX-ACCESS  not-accessible
	STATUS      current
	DESCRIPTION
	"Table entry for divertProxyAsymLocalEgressErrorAlreadyDiverted"
	INDEX { divertProxyAsymLocalEgressErrorAlreadyDivertedLevelName }
	::={divertProxyAsymLocalEgressErrorAlreadyDivertedLevelTable 1}

DivertProxyAsymLocalEgressErrorAlreadyDivertedLevelEntry ::=
	SEQUENCE {
		divertProxyAsymLocalEgressErrorAlreadyDivertedLevelName	DisplayString,
		divertProxyAsymLocalEgressErrorAlreadyDivertedLevelVal	Counter64,
		divertProxyAsymLocalEgressErrorAlreadyDivertedLevelMom	CounterBasedGauge64,
		divertProxyAsymLocalEgressErrorAlreadyDivertedLevelMax	CounterBasedGauge64
	}

divertProxyAsymLocalEgressErrorAlreadyDivertedLevelName OBJECT-TYPE
	SYNTAX      DisplayString
	MAX-ACCESS  not-accessible
	STATUS      current
	DESCRIPTION
	"Table entry display string for divertProxyAsymLocalEgressErrorAlreadyDiverted"
	::={divertProxyAsymLocalEgressErrorAlreadyDivertedLevelEntry 1}

divertProxyAsymLocalEgressErrorAlreadyDivertedLevelVal OBJECT-TYPE
	SYNTAX	 Counter64
	MAX-ACCESS  read-only
	STATUS      current
	DESCRIPTION
	"Table entry attribute for divertProxyAsymLocalEgressErrorAlreadyDiverted"
	::={divertProxyAsymLocalEgressErrorAlreadyDivertedLevelEntry 2}

divertProxyAsymLocalEgressErrorAlreadyDivertedLevelMom OBJECT-TYPE
	SYNTAX	 CounterBasedGauge64
	MAX-ACCESS  read-only
	STATUS      current
	DESCRIPTION
	"Table entry attribute for divertProxyAsymLocalEgressErrorAlreadyDiverted"
	::={divertProxyAsymLocalEgressErrorAlreadyDivertedLevelEntry 3}

divertProxyAsymLocalEgressErrorAlreadyDivertedLevelMax OBJECT-TYPE
	SYNTAX	 CounterBasedGauge64
	MAX-ACCESS  read-only
	STATUS      current
	DESCRIPTION
	"Table entry attribute for divertProxyAsymLocalEgressErrorAlreadyDiverted"
	::={divertProxyAsymLocalEgressErrorAlreadyDivertedLevelEntry 4}


divertProxyAsymLocalEgressErrorPktTx	OBJECT IDENTIFIER ::={divert 39}

divertProxyAsymLocalEgressErrorPktTxVal	OBJECT-TYPE
	SYNTAX	 Counter64
	MAX-ACCESS read-only
	STATUS current
	DESCRIPTION "Proxy asym local egress error packet (packet transmit)"

	::={divertProxyAsymLocalEgressErrorPktTx 1}

divertProxyAsymLocalEgressErrorPktTxMom	OBJECT-TYPE
	SYNTAX	 CounterBasedGauge64
	MAX-ACCESS read-only
	STATUS current
	DESCRIPTION "Proxy asym local egress error packet (packet transmit)"

	::={divertProxyAsymLocalEgressErrorPktTx 2}

divertProxyAsymLocalEgressErrorPktTxMax	OBJECT-TYPE
	SYNTAX	 CounterBasedGauge64
	MAX-ACCESS read-only
	STATUS current
	DESCRIPTION "Proxy asym local egress error packet (packet transmit)"

	::={divertProxyAsymLocalEgressErrorPktTx 3}

divertProxyAsymLocalEgressErrorPktTxLevelTable OBJECT-TYPE
	SYNTAX      SEQUENCE OF DivertProxyAsymLocalEgressErrorPktTxLevelEntry
	MAX-ACCESS  not-accessible
	STATUS      current
	DESCRIPTION
	"Table for divertProxyAsymLocalEgressErrorPktTx"
	::={divertProxyAsymLocalEgressErrorPktTx 4}

divertProxyAsymLocalEgressErrorPktTxLevelEntry OBJECT-TYPE
	SYNTAX      DivertProxyAsymLocalEgressErrorPktTxLevelEntry
	MAX-ACCESS  not-accessible
	STATUS      current
	DESCRIPTION
	"Table entry for divertProxyAsymLocalEgressErrorPktTx"
	INDEX { divertProxyAsymLocalEgressErrorPktTxLevelName }
	::={divertProxyAsymLocalEgressErrorPktTxLevelTable 1}

DivertProxyAsymLocalEgressErrorPktTxLevelEntry ::=
	SEQUENCE {
		divertProxyAsymLocalEgressErrorPktTxLevelName	DisplayString,
		divertProxyAsymLocalEgressErrorPktTxLevelVal	Counter64,
		divertProxyAsymLocalEgressErrorPktTxLevelMom	CounterBasedGauge64,
		divertProxyAsymLocalEgressErrorPktTxLevelMax	CounterBasedGauge64
	}

divertProxyAsymLocalEgressErrorPktTxLevelName OBJECT-TYPE
	SYNTAX      DisplayString
	MAX-ACCESS  not-accessible
	STATUS      current
	DESCRIPTION
	"Table entry display string for divertProxyAsymLocalEgressErrorPktTx"
	::={divertProxyAsymLocalEgressErrorPktTxLevelEntry 1}

divertProxyAsymLocalEgressErrorPktTxLevelVal OBJECT-TYPE
	SYNTAX	 Counter64
	MAX-ACCESS  read-only
	STATUS      current
	DESCRIPTION
	"Table entry attribute for divertProxyAsymLocalEgressErrorPktTx"
	::={divertProxyAsymLocalEgressErrorPktTxLevelEntry 2}

divertProxyAsymLocalEgressErrorPktTxLevelMom OBJECT-TYPE
	SYNTAX	 CounterBasedGauge64
	MAX-ACCESS  read-only
	STATUS      current
	DESCRIPTION
	"Table entry attribute for divertProxyAsymLocalEgressErrorPktTx"
	::={divertProxyAsymLocalEgressErrorPktTxLevelEntry 3}

divertProxyAsymLocalEgressErrorPktTxLevelMax OBJECT-TYPE
	SYNTAX	 CounterBasedGauge64
	MAX-ACCESS  read-only
	STATUS      current
	DESCRIPTION
	"Table entry attribute for divertProxyAsymLocalEgressErrorPktTx"
	::={divertProxyAsymLocalEgressErrorPktTxLevelEntry 4}


divertProxyAsymLocalIngressPackets	OBJECT IDENTIFIER ::={divert 40}

divertProxyAsymLocalIngressPacketsVal	OBJECT-TYPE
	SYNTAX	 Counter64
	MAX-ACCESS read-only
	STATUS current
	DESCRIPTION "Proxy asym local ingress packets"

	::={divertProxyAsymLocalIngressPackets 1}

divertProxyAsymLocalIngressPacketsMom	OBJECT-TYPE
	SYNTAX	 CounterBasedGauge64
	MAX-ACCESS read-only
	STATUS current
	DESCRIPTION "Proxy asym local ingress packets"

	::={divertProxyAsymLocalIngressPackets 2}

divertProxyAsymLocalIngressPacketsMax	OBJECT-TYPE
	SYNTAX	 CounterBasedGauge64
	MAX-ACCESS read-only
	STATUS current
	DESCRIPTION "Proxy asym local ingress packets"

	::={divertProxyAsymLocalIngressPackets 3}

divertProxyAsymLocalIngressPacketsLevelTable OBJECT-TYPE
	SYNTAX      SEQUENCE OF DivertProxyAsymLocalIngressPacketsLevelEntry
	MAX-ACCESS  not-accessible
	STATUS      current
	DESCRIPTION
	"Table for divertProxyAsymLocalIngressPackets"
	::={divertProxyAsymLocalIngressPackets 4}

divertProxyAsymLocalIngressPacketsLevelEntry OBJECT-TYPE
	SYNTAX      DivertProxyAsymLocalIngressPacketsLevelEntry
	MAX-ACCESS  not-accessible
	STATUS      current
	DESCRIPTION
	"Table entry for divertProxyAsymLocalIngressPackets"
	INDEX { divertProxyAsymLocalIngressPacketsLevelName }
	::={divertProxyAsymLocalIngressPacketsLevelTable 1}

DivertProxyAsymLocalIngressPacketsLevelEntry ::=
	SEQUENCE {
		divertProxyAsymLocalIngressPacketsLevelName	DisplayString,
		divertProxyAsymLocalIngressPacketsLevelVal	Counter64,
		divertProxyAsymLocalIngressPacketsLevelMom	CounterBasedGauge64,
		divertProxyAsymLocalIngressPacketsLevelMax	CounterBasedGauge64
	}

divertProxyAsymLocalIngressPacketsLevelName OBJECT-TYPE
	SYNTAX      DisplayString
	MAX-ACCESS  not-accessible
	STATUS      current
	DESCRIPTION
	"Table entry display string for divertProxyAsymLocalIngressPackets"
	::={divertProxyAsymLocalIngressPacketsLevelEntry 1}

divertProxyAsymLocalIngressPacketsLevelVal OBJECT-TYPE
	SYNTAX	 Counter64
	MAX-ACCESS  read-only
	STATUS      current
	DESCRIPTION
	"Table entry attribute for divertProxyAsymLocalIngressPackets"
	::={divertProxyAsymLocalIngressPacketsLevelEntry 2}

divertProxyAsymLocalIngressPacketsLevelMom OBJECT-TYPE
	SYNTAX	 CounterBasedGauge64
	MAX-ACCESS  read-only
	STATUS      current
	DESCRIPTION
	"Table entry attribute for divertProxyAsymLocalIngressPackets"
	::={divertProxyAsymLocalIngressPacketsLevelEntry 3}

divertProxyAsymLocalIngressPacketsLevelMax OBJECT-TYPE
	SYNTAX	 CounterBasedGauge64
	MAX-ACCESS  read-only
	STATUS      current
	DESCRIPTION
	"Table entry attribute for divertProxyAsymLocalIngressPackets"
	::={divertProxyAsymLocalIngressPacketsLevelEntry 4}


divertProxyAsymConnections	OBJECT IDENTIFIER ::={divert 41}

divertProxyAsymConnectionsVal	OBJECT-TYPE
	SYNTAX	 CounterBasedGauge64
	MAX-ACCESS read-only
	STATUS current
	DESCRIPTION "Proxy asym connections"

	::={divertProxyAsymConnections 1}

divertProxyAsymConnectionsMax	OBJECT-TYPE
	SYNTAX	 CounterBasedGauge64
	MAX-ACCESS read-only
	STATUS current
	DESCRIPTION "Proxy asym connections"

	::={divertProxyAsymConnections 3}

divertProxyAsymConnectionsLevelTable OBJECT-TYPE
	SYNTAX      SEQUENCE OF DivertProxyAsymConnectionsLevelEntry
	MAX-ACCESS  not-accessible
	STATUS      current
	DESCRIPTION
	"Table for divertProxyAsymConnections"
	::={divertProxyAsymConnections 4}

divertProxyAsymConnectionsLevelEntry OBJECT-TYPE
	SYNTAX      DivertProxyAsymConnectionsLevelEntry
	MAX-ACCESS  not-accessible
	STATUS      current
	DESCRIPTION
	"Table entry for divertProxyAsymConnections"
	INDEX { divertProxyAsymConnectionsLevelName }
	::={divertProxyAsymConnectionsLevelTable 1}

DivertProxyAsymConnectionsLevelEntry ::=
	SEQUENCE {
		divertProxyAsymConnectionsLevelName	DisplayString,
		divertProxyAsymConnectionsLevelVal	CounterBasedGauge64,
		divertProxyAsymConnectionsLevelMax	CounterBasedGauge64
	}

divertProxyAsymConnectionsLevelName OBJECT-TYPE
	SYNTAX      DisplayString
	MAX-ACCESS  not-accessible
	STATUS      current
	DESCRIPTION
	"Table entry display string for divertProxyAsymConnections"
	::={divertProxyAsymConnectionsLevelEntry 1}

divertProxyAsymConnectionsLevelVal OBJECT-TYPE
	SYNTAX	 CounterBasedGauge64
	MAX-ACCESS  read-only
	STATUS      current
	DESCRIPTION
	"Table entry attribute for divertProxyAsymConnections"
	::={divertProxyAsymConnectionsLevelEntry 2}

divertProxyAsymConnectionsLevelMax OBJECT-TYPE
	SYNTAX	 CounterBasedGauge64
	MAX-ACCESS  read-only
	STATUS      current
	DESCRIPTION
	"Table entry attribute for divertProxyAsymConnections"
	::={divertProxyAsymConnectionsLevelEntry 4}


divertProxyAsymNotifySnt	OBJECT IDENTIFIER ::={divert 42}

divertProxyAsymNotifySntVal	OBJECT-TYPE
	SYNTAX	 Counter64
	MAX-ACCESS read-only
	STATUS current
	DESCRIPTION "Proxy asym notifications sent"

	::={divertProxyAsymNotifySnt 1}

divertProxyAsymNotifySntMom	OBJECT-TYPE
	SYNTAX	 CounterBasedGauge64
	MAX-ACCESS read-only
	STATUS current
	DESCRIPTION "Proxy asym notifications sent"

	::={divertProxyAsymNotifySnt 2}

divertProxyAsymNotifySntMax	OBJECT-TYPE
	SYNTAX	 CounterBasedGauge64
	MAX-ACCESS read-only
	STATUS current
	DESCRIPTION "Proxy asym notifications sent"

	::={divertProxyAsymNotifySnt 3}

divertProxyAsymNotifySntLevelTable OBJECT-TYPE
	SYNTAX      SEQUENCE OF DivertProxyAsymNotifySntLevelEntry
	MAX-ACCESS  not-accessible
	STATUS      current
	DESCRIPTION
	"Table for divertProxyAsymNotifySnt"
	::={divertProxyAsymNotifySnt 4}

divertProxyAsymNotifySntLevelEntry OBJECT-TYPE
	SYNTAX      DivertProxyAsymNotifySntLevelEntry
	MAX-ACCESS  not-accessible
	STATUS      current
	DESCRIPTION
	"Table entry for divertProxyAsymNotifySnt"
	INDEX { divertProxyAsymNotifySntLevelName }
	::={divertProxyAsymNotifySntLevelTable 1}

DivertProxyAsymNotifySntLevelEntry ::=
	SEQUENCE {
		divertProxyAsymNotifySntLevelName	DisplayString,
		divertProxyAsymNotifySntLevelVal	Counter64,
		divertProxyAsymNotifySntLevelMom	CounterBasedGauge64,
		divertProxyAsymNotifySntLevelMax	CounterBasedGauge64
	}

divertProxyAsymNotifySntLevelName OBJECT-TYPE
	SYNTAX      DisplayString
	MAX-ACCESS  not-accessible
	STATUS      current
	DESCRIPTION
	"Table entry display string for divertProxyAsymNotifySnt"
	::={divertProxyAsymNotifySntLevelEntry 1}

divertProxyAsymNotifySntLevelVal OBJECT-TYPE
	SYNTAX	 Counter64
	MAX-ACCESS  read-only
	STATUS      current
	DESCRIPTION
	"Table entry attribute for divertProxyAsymNotifySnt"
	::={divertProxyAsymNotifySntLevelEntry 2}

divertProxyAsymNotifySntLevelMom OBJECT-TYPE
	SYNTAX	 CounterBasedGauge64
	MAX-ACCESS  read-only
	STATUS      current
	DESCRIPTION
	"Table entry attribute for divertProxyAsymNotifySnt"
	::={divertProxyAsymNotifySntLevelEntry 3}

divertProxyAsymNotifySntLevelMax OBJECT-TYPE
	SYNTAX	 CounterBasedGauge64
	MAX-ACCESS  read-only
	STATUS      current
	DESCRIPTION
	"Table entry attribute for divertProxyAsymNotifySnt"
	::={divertProxyAsymNotifySntLevelEntry 4}


divertProxyAsymNotifySntEst	OBJECT IDENTIFIER ::={divert 43}

divertProxyAsymNotifySntEstVal	OBJECT-TYPE
	SYNTAX	 Counter64
	MAX-ACCESS read-only
	STATUS current
	DESCRIPTION "Proxy asym notifications sent (established)"

	::={divertProxyAsymNotifySntEst 1}

divertProxyAsymNotifySntEstMom	OBJECT-TYPE
	SYNTAX	 CounterBasedGauge64
	MAX-ACCESS read-only
	STATUS current
	DESCRIPTION "Proxy asym notifications sent (established)"

	::={divertProxyAsymNotifySntEst 2}

divertProxyAsymNotifySntEstMax	OBJECT-TYPE
	SYNTAX	 CounterBasedGauge64
	MAX-ACCESS read-only
	STATUS current
	DESCRIPTION "Proxy asym notifications sent (established)"

	::={divertProxyAsymNotifySntEst 3}

divertProxyAsymNotifySntEstLevelTable OBJECT-TYPE
	SYNTAX      SEQUENCE OF DivertProxyAsymNotifySntEstLevelEntry
	MAX-ACCESS  not-accessible
	STATUS      current
	DESCRIPTION
	"Table for divertProxyAsymNotifySntEst"
	::={divertProxyAsymNotifySntEst 4}

divertProxyAsymNotifySntEstLevelEntry OBJECT-TYPE
	SYNTAX      DivertProxyAsymNotifySntEstLevelEntry
	MAX-ACCESS  not-accessible
	STATUS      current
	DESCRIPTION
	"Table entry for divertProxyAsymNotifySntEst"
	INDEX { divertProxyAsymNotifySntEstLevelName }
	::={divertProxyAsymNotifySntEstLevelTable 1}

DivertProxyAsymNotifySntEstLevelEntry ::=
	SEQUENCE {
		divertProxyAsymNotifySntEstLevelName	DisplayString,
		divertProxyAsymNotifySntEstLevelVal	Counter64,
		divertProxyAsymNotifySntEstLevelMom	CounterBasedGauge64,
		divertProxyAsymNotifySntEstLevelMax	CounterBasedGauge64
	}

divertProxyAsymNotifySntEstLevelName OBJECT-TYPE
	SYNTAX      DisplayString
	MAX-ACCESS  not-accessible
	STATUS      current
	DESCRIPTION
	"Table entry display string for divertProxyAsymNotifySntEst"
	::={divertProxyAsymNotifySntEstLevelEntry 1}

divertProxyAsymNotifySntEstLevelVal OBJECT-TYPE
	SYNTAX	 Counter64
	MAX-ACCESS  read-only
	STATUS      current
	DESCRIPTION
	"Table entry attribute for divertProxyAsymNotifySntEst"
	::={divertProxyAsymNotifySntEstLevelEntry 2}

divertProxyAsymNotifySntEstLevelMom OBJECT-TYPE
	SYNTAX	 CounterBasedGauge64
	MAX-ACCESS  read-only
	STATUS      current
	DESCRIPTION
	"Table entry attribute for divertProxyAsymNotifySntEst"
	::={divertProxyAsymNotifySntEstLevelEntry 3}

divertProxyAsymNotifySntEstLevelMax OBJECT-TYPE
	SYNTAX	 CounterBasedGauge64
	MAX-ACCESS  read-only
	STATUS      current
	DESCRIPTION
	"Table entry attribute for divertProxyAsymNotifySntEst"
	::={divertProxyAsymNotifySntEstLevelEntry 4}


divertProxyAsymNotifySntAbort	OBJECT IDENTIFIER ::={divert 44}

divertProxyAsymNotifySntAbortVal	OBJECT-TYPE
	SYNTAX	 Counter64
	MAX-ACCESS read-only
	STATUS current
	DESCRIPTION "Proxy asym notifications sent (abort)"

	::={divertProxyAsymNotifySntAbort 1}

divertProxyAsymNotifySntAbortMom	OBJECT-TYPE
	SYNTAX	 CounterBasedGauge64
	MAX-ACCESS read-only
	STATUS current
	DESCRIPTION "Proxy asym notifications sent (abort)"

	::={divertProxyAsymNotifySntAbort 2}

divertProxyAsymNotifySntAbortMax	OBJECT-TYPE
	SYNTAX	 CounterBasedGauge64
	MAX-ACCESS read-only
	STATUS current
	DESCRIPTION "Proxy asym notifications sent (abort)"

	::={divertProxyAsymNotifySntAbort 3}

divertProxyAsymNotifySntAbortLevelTable OBJECT-TYPE
	SYNTAX      SEQUENCE OF DivertProxyAsymNotifySntAbortLevelEntry
	MAX-ACCESS  not-accessible
	STATUS      current
	DESCRIPTION
	"Table for divertProxyAsymNotifySntAbort"
	::={divertProxyAsymNotifySntAbort 4}

divertProxyAsymNotifySntAbortLevelEntry OBJECT-TYPE
	SYNTAX      DivertProxyAsymNotifySntAbortLevelEntry
	MAX-ACCESS  not-accessible
	STATUS      current
	DESCRIPTION
	"Table entry for divertProxyAsymNotifySntAbort"
	INDEX { divertProxyAsymNotifySntAbortLevelName }
	::={divertProxyAsymNotifySntAbortLevelTable 1}

DivertProxyAsymNotifySntAbortLevelEntry ::=
	SEQUENCE {
		divertProxyAsymNotifySntAbortLevelName	DisplayString,
		divertProxyAsymNotifySntAbortLevelVal	Counter64,
		divertProxyAsymNotifySntAbortLevelMom	CounterBasedGauge64,
		divertProxyAsymNotifySntAbortLevelMax	CounterBasedGauge64
	}

divertProxyAsymNotifySntAbortLevelName OBJECT-TYPE
	SYNTAX      DisplayString
	MAX-ACCESS  not-accessible
	STATUS      current
	DESCRIPTION
	"Table entry display string for divertProxyAsymNotifySntAbort"
	::={divertProxyAsymNotifySntAbortLevelEntry 1}

divertProxyAsymNotifySntAbortLevelVal OBJECT-TYPE
	SYNTAX	 Counter64
	MAX-ACCESS  read-only
	STATUS      current
	DESCRIPTION
	"Table entry attribute for divertProxyAsymNotifySntAbort"
	::={divertProxyAsymNotifySntAbortLevelEntry 2}

divertProxyAsymNotifySntAbortLevelMom OBJECT-TYPE
	SYNTAX	 CounterBasedGauge64
	MAX-ACCESS  read-only
	STATUS      current
	DESCRIPTION
	"Table entry attribute for divertProxyAsymNotifySntAbort"
	::={divertProxyAsymNotifySntAbortLevelEntry 3}

divertProxyAsymNotifySntAbortLevelMax OBJECT-TYPE
	SYNTAX	 CounterBasedGauge64
	MAX-ACCESS  read-only
	STATUS      current
	DESCRIPTION
	"Table entry attribute for divertProxyAsymNotifySntAbort"
	::={divertProxyAsymNotifySntAbortLevelEntry 4}


divertProxyAsymNotifySntErrorResource	OBJECT IDENTIFIER ::={divert 45}

divertProxyAsymNotifySntErrorResourceVal	OBJECT-TYPE
	SYNTAX	 Counter64
	MAX-ACCESS read-only
	STATUS current
	DESCRIPTION "Proxy asym notifications sent error (resource)"

	::={divertProxyAsymNotifySntErrorResource 1}

divertProxyAsymNotifySntErrorResourceMom	OBJECT-TYPE
	SYNTAX	 CounterBasedGauge64
	MAX-ACCESS read-only
	STATUS current
	DESCRIPTION "Proxy asym notifications sent error (resource)"

	::={divertProxyAsymNotifySntErrorResource 2}

divertProxyAsymNotifySntErrorResourceMax	OBJECT-TYPE
	SYNTAX	 CounterBasedGauge64
	MAX-ACCESS read-only
	STATUS current
	DESCRIPTION "Proxy asym notifications sent error (resource)"

	::={divertProxyAsymNotifySntErrorResource 3}

divertProxyAsymNotifySntErrorResourceLevelTable OBJECT-TYPE
	SYNTAX      SEQUENCE OF DivertProxyAsymNotifySntErrorResourceLevelEntry
	MAX-ACCESS  not-accessible
	STATUS      current
	DESCRIPTION
	"Table for divertProxyAsymNotifySntErrorResource"
	::={divertProxyAsymNotifySntErrorResource 4}

divertProxyAsymNotifySntErrorResourceLevelEntry OBJECT-TYPE
	SYNTAX      DivertProxyAsymNotifySntErrorResourceLevelEntry
	MAX-ACCESS  not-accessible
	STATUS      current
	DESCRIPTION
	"Table entry for divertProxyAsymNotifySntErrorResource"
	INDEX { divertProxyAsymNotifySntErrorResourceLevelName }
	::={divertProxyAsymNotifySntErrorResourceLevelTable 1}

DivertProxyAsymNotifySntErrorResourceLevelEntry ::=
	SEQUENCE {
		divertProxyAsymNotifySntErrorResourceLevelName	DisplayString,
		divertProxyAsymNotifySntErrorResourceLevelVal	Counter64,
		divertProxyAsymNotifySntErrorResourceLevelMom	CounterBasedGauge64,
		divertProxyAsymNotifySntErrorResourceLevelMax	CounterBasedGauge64
	}

divertProxyAsymNotifySntErrorResourceLevelName OBJECT-TYPE
	SYNTAX      DisplayString
	MAX-ACCESS  not-accessible
	STATUS      current
	DESCRIPTION
	"Table entry display string for divertProxyAsymNotifySntErrorResource"
	::={divertProxyAsymNotifySntErrorResourceLevelEntry 1}

divertProxyAsymNotifySntErrorResourceLevelVal OBJECT-TYPE
	SYNTAX	 Counter64
	MAX-ACCESS  read-only
	STATUS      current
	DESCRIPTION
	"Table entry attribute for divertProxyAsymNotifySntErrorResource"
	::={divertProxyAsymNotifySntErrorResourceLevelEntry 2}

divertProxyAsymNotifySntErrorResourceLevelMom OBJECT-TYPE
	SYNTAX	 CounterBasedGauge64
	MAX-ACCESS  read-only
	STATUS      current
	DESCRIPTION
	"Table entry attribute for divertProxyAsymNotifySntErrorResource"
	::={divertProxyAsymNotifySntErrorResourceLevelEntry 3}

divertProxyAsymNotifySntErrorResourceLevelMax OBJECT-TYPE
	SYNTAX	 CounterBasedGauge64
	MAX-ACCESS  read-only
	STATUS      current
	DESCRIPTION
	"Table entry attribute for divertProxyAsymNotifySntErrorResource"
	::={divertProxyAsymNotifySntErrorResourceLevelEntry 4}


divertProxyAsymNotifyRcv	OBJECT IDENTIFIER ::={divert 46}

divertProxyAsymNotifyRcvVal	OBJECT-TYPE
	SYNTAX	 Counter64
	MAX-ACCESS read-only
	STATUS current
	DESCRIPTION "Proxy asym notifications received"

	::={divertProxyAsymNotifyRcv 1}

divertProxyAsymNotifyRcvMom	OBJECT-TYPE
	SYNTAX	 CounterBasedGauge64
	MAX-ACCESS read-only
	STATUS current
	DESCRIPTION "Proxy asym notifications received"

	::={divertProxyAsymNotifyRcv 2}

divertProxyAsymNotifyRcvMax	OBJECT-TYPE
	SYNTAX	 CounterBasedGauge64
	MAX-ACCESS read-only
	STATUS current
	DESCRIPTION "Proxy asym notifications received"

	::={divertProxyAsymNotifyRcv 3}

divertProxyAsymNotifyRcvLevelTable OBJECT-TYPE
	SYNTAX      SEQUENCE OF DivertProxyAsymNotifyRcvLevelEntry
	MAX-ACCESS  not-accessible
	STATUS      current
	DESCRIPTION
	"Table for divertProxyAsymNotifyRcv"
	::={divertProxyAsymNotifyRcv 4}

divertProxyAsymNotifyRcvLevelEntry OBJECT-TYPE
	SYNTAX      DivertProxyAsymNotifyRcvLevelEntry
	MAX-ACCESS  not-accessible
	STATUS      current
	DESCRIPTION
	"Table entry for divertProxyAsymNotifyRcv"
	INDEX { divertProxyAsymNotifyRcvLevelName }
	::={divertProxyAsymNotifyRcvLevelTable 1}

DivertProxyAsymNotifyRcvLevelEntry ::=
	SEQUENCE {
		divertProxyAsymNotifyRcvLevelName	DisplayString,
		divertProxyAsymNotifyRcvLevelVal	Counter64,
		divertProxyAsymNotifyRcvLevelMom	CounterBasedGauge64,
		divertProxyAsymNotifyRcvLevelMax	CounterBasedGauge64
	}

divertProxyAsymNotifyRcvLevelName OBJECT-TYPE
	SYNTAX      DisplayString
	MAX-ACCESS  not-accessible
	STATUS      current
	DESCRIPTION
	"Table entry display string for divertProxyAsymNotifyRcv"
	::={divertProxyAsymNotifyRcvLevelEntry 1}

divertProxyAsymNotifyRcvLevelVal OBJECT-TYPE
	SYNTAX	 Counter64
	MAX-ACCESS  read-only
	STATUS      current
	DESCRIPTION
	"Table entry attribute for divertProxyAsymNotifyRcv"
	::={divertProxyAsymNotifyRcvLevelEntry 2}

divertProxyAsymNotifyRcvLevelMom OBJECT-TYPE
	SYNTAX	 CounterBasedGauge64
	MAX-ACCESS  read-only
	STATUS      current
	DESCRIPTION
	"Table entry attribute for divertProxyAsymNotifyRcv"
	::={divertProxyAsymNotifyRcvLevelEntry 3}

divertProxyAsymNotifyRcvLevelMax OBJECT-TYPE
	SYNTAX	 CounterBasedGauge64
	MAX-ACCESS  read-only
	STATUS      current
	DESCRIPTION
	"Table entry attribute for divertProxyAsymNotifyRcv"
	::={divertProxyAsymNotifyRcvLevelEntry 4}


divertProxyAsymNotifyRcvEst	OBJECT IDENTIFIER ::={divert 47}

divertProxyAsymNotifyRcvEstVal	OBJECT-TYPE
	SYNTAX	 Counter64
	MAX-ACCESS read-only
	STATUS current
	DESCRIPTION "Proxy asym notifications received (established)"

	::={divertProxyAsymNotifyRcvEst 1}

divertProxyAsymNotifyRcvEstMom	OBJECT-TYPE
	SYNTAX	 CounterBasedGauge64
	MAX-ACCESS read-only
	STATUS current
	DESCRIPTION "Proxy asym notifications received (established)"

	::={divertProxyAsymNotifyRcvEst 2}

divertProxyAsymNotifyRcvEstMax	OBJECT-TYPE
	SYNTAX	 CounterBasedGauge64
	MAX-ACCESS read-only
	STATUS current
	DESCRIPTION "Proxy asym notifications received (established)"

	::={divertProxyAsymNotifyRcvEst 3}

divertProxyAsymNotifyRcvEstLevelTable OBJECT-TYPE
	SYNTAX      SEQUENCE OF DivertProxyAsymNotifyRcvEstLevelEntry
	MAX-ACCESS  not-accessible
	STATUS      current
	DESCRIPTION
	"Table for divertProxyAsymNotifyRcvEst"
	::={divertProxyAsymNotifyRcvEst 4}

divertProxyAsymNotifyRcvEstLevelEntry OBJECT-TYPE
	SYNTAX      DivertProxyAsymNotifyRcvEstLevelEntry
	MAX-ACCESS  not-accessible
	STATUS      current
	DESCRIPTION
	"Table entry for divertProxyAsymNotifyRcvEst"
	INDEX { divertProxyAsymNotifyRcvEstLevelName }
	::={divertProxyAsymNotifyRcvEstLevelTable 1}

DivertProxyAsymNotifyRcvEstLevelEntry ::=
	SEQUENCE {
		divertProxyAsymNotifyRcvEstLevelName	DisplayString,
		divertProxyAsymNotifyRcvEstLevelVal	Counter64,
		divertProxyAsymNotifyRcvEstLevelMom	CounterBasedGauge64,
		divertProxyAsymNotifyRcvEstLevelMax	CounterBasedGauge64
	}

divertProxyAsymNotifyRcvEstLevelName OBJECT-TYPE
	SYNTAX      DisplayString
	MAX-ACCESS  not-accessible
	STATUS      current
	DESCRIPTION
	"Table entry display string for divertProxyAsymNotifyRcvEst"
	::={divertProxyAsymNotifyRcvEstLevelEntry 1}

divertProxyAsymNotifyRcvEstLevelVal OBJECT-TYPE
	SYNTAX	 Counter64
	MAX-ACCESS  read-only
	STATUS      current
	DESCRIPTION
	"Table entry attribute for divertProxyAsymNotifyRcvEst"
	::={divertProxyAsymNotifyRcvEstLevelEntry 2}

divertProxyAsymNotifyRcvEstLevelMom OBJECT-TYPE
	SYNTAX	 CounterBasedGauge64
	MAX-ACCESS  read-only
	STATUS      current
	DESCRIPTION
	"Table entry attribute for divertProxyAsymNotifyRcvEst"
	::={divertProxyAsymNotifyRcvEstLevelEntry 3}

divertProxyAsymNotifyRcvEstLevelMax OBJECT-TYPE
	SYNTAX	 CounterBasedGauge64
	MAX-ACCESS  read-only
	STATUS      current
	DESCRIPTION
	"Table entry attribute for divertProxyAsymNotifyRcvEst"
	::={divertProxyAsymNotifyRcvEstLevelEntry 4}


divertProxyAsymNotifyRcvAbort	OBJECT IDENTIFIER ::={divert 48}

divertProxyAsymNotifyRcvAbortVal	OBJECT-TYPE
	SYNTAX	 Counter64
	MAX-ACCESS read-only
	STATUS current
	DESCRIPTION "Proxy asym notifications received (abort)"

	::={divertProxyAsymNotifyRcvAbort 1}

divertProxyAsymNotifyRcvAbortMom	OBJECT-TYPE
	SYNTAX	 CounterBasedGauge64
	MAX-ACCESS read-only
	STATUS current
	DESCRIPTION "Proxy asym notifications received (abort)"

	::={divertProxyAsymNotifyRcvAbort 2}

divertProxyAsymNotifyRcvAbortMax	OBJECT-TYPE
	SYNTAX	 CounterBasedGauge64
	MAX-ACCESS read-only
	STATUS current
	DESCRIPTION "Proxy asym notifications received (abort)"

	::={divertProxyAsymNotifyRcvAbort 3}

divertProxyAsymNotifyRcvAbortLevelTable OBJECT-TYPE
	SYNTAX      SEQUENCE OF DivertProxyAsymNotifyRcvAbortLevelEntry
	MAX-ACCESS  not-accessible
	STATUS      current
	DESCRIPTION
	"Table for divertProxyAsymNotifyRcvAbort"
	::={divertProxyAsymNotifyRcvAbort 4}

divertProxyAsymNotifyRcvAbortLevelEntry OBJECT-TYPE
	SYNTAX      DivertProxyAsymNotifyRcvAbortLevelEntry
	MAX-ACCESS  not-accessible
	STATUS      current
	DESCRIPTION
	"Table entry for divertProxyAsymNotifyRcvAbort"
	INDEX { divertProxyAsymNotifyRcvAbortLevelName }
	::={divertProxyAsymNotifyRcvAbortLevelTable 1}

DivertProxyAsymNotifyRcvAbortLevelEntry ::=
	SEQUENCE {
		divertProxyAsymNotifyRcvAbortLevelName	DisplayString,
		divertProxyAsymNotifyRcvAbortLevelVal	Counter64,
		divertProxyAsymNotifyRcvAbortLevelMom	CounterBasedGauge64,
		divertProxyAsymNotifyRcvAbortLevelMax	CounterBasedGauge64
	}

divertProxyAsymNotifyRcvAbortLevelName OBJECT-TYPE
	SYNTAX      DisplayString
	MAX-ACCESS  not-accessible
	STATUS      current
	DESCRIPTION
	"Table entry display string for divertProxyAsymNotifyRcvAbort"
	::={divertProxyAsymNotifyRcvAbortLevelEntry 1}

divertProxyAsymNotifyRcvAbortLevelVal OBJECT-TYPE
	SYNTAX	 Counter64
	MAX-ACCESS  read-only
	STATUS      current
	DESCRIPTION
	"Table entry attribute for divertProxyAsymNotifyRcvAbort"
	::={divertProxyAsymNotifyRcvAbortLevelEntry 2}

divertProxyAsymNotifyRcvAbortLevelMom OBJECT-TYPE
	SYNTAX	 CounterBasedGauge64
	MAX-ACCESS  read-only
	STATUS      current
	DESCRIPTION
	"Table entry attribute for divertProxyAsymNotifyRcvAbort"
	::={divertProxyAsymNotifyRcvAbortLevelEntry 3}

divertProxyAsymNotifyRcvAbortLevelMax OBJECT-TYPE
	SYNTAX	 CounterBasedGauge64
	MAX-ACCESS  read-only
	STATUS      current
	DESCRIPTION
	"Table entry attribute for divertProxyAsymNotifyRcvAbort"
	::={divertProxyAsymNotifyRcvAbortLevelEntry 4}


divertProxyAsymNotifyRcvError	OBJECT IDENTIFIER ::={divert 49}

divertProxyAsymNotifyRcvErrorVal	OBJECT-TYPE
	SYNTAX	 Counter64
	MAX-ACCESS read-only
	STATUS current
	DESCRIPTION "Proxy asym notifications receive error"

	::={divertProxyAsymNotifyRcvError 1}

divertProxyAsymNotifyRcvErrorMom	OBJECT-TYPE
	SYNTAX	 CounterBasedGauge64
	MAX-ACCESS read-only
	STATUS current
	DESCRIPTION "Proxy asym notifications receive error"

	::={divertProxyAsymNotifyRcvError 2}

divertProxyAsymNotifyRcvErrorMax	OBJECT-TYPE
	SYNTAX	 CounterBasedGauge64
	MAX-ACCESS read-only
	STATUS current
	DESCRIPTION "Proxy asym notifications receive error"

	::={divertProxyAsymNotifyRcvError 3}

divertProxyAsymNotifyRcvErrorLevelTable OBJECT-TYPE
	SYNTAX      SEQUENCE OF DivertProxyAsymNotifyRcvErrorLevelEntry
	MAX-ACCESS  not-accessible
	STATUS      current
	DESCRIPTION
	"Table for divertProxyAsymNotifyRcvError"
	::={divertProxyAsymNotifyRcvError 4}

divertProxyAsymNotifyRcvErrorLevelEntry OBJECT-TYPE
	SYNTAX      DivertProxyAsymNotifyRcvErrorLevelEntry
	MAX-ACCESS  not-accessible
	STATUS      current
	DESCRIPTION
	"Table entry for divertProxyAsymNotifyRcvError"
	INDEX { divertProxyAsymNotifyRcvErrorLevelName }
	::={divertProxyAsymNotifyRcvErrorLevelTable 1}

DivertProxyAsymNotifyRcvErrorLevelEntry ::=
	SEQUENCE {
		divertProxyAsymNotifyRcvErrorLevelName	DisplayString,
		divertProxyAsymNotifyRcvErrorLevelVal	Counter64,
		divertProxyAsymNotifyRcvErrorLevelMom	CounterBasedGauge64,
		divertProxyAsymNotifyRcvErrorLevelMax	CounterBasedGauge64
	}

divertProxyAsymNotifyRcvErrorLevelName OBJECT-TYPE
	SYNTAX      DisplayString
	MAX-ACCESS  not-accessible
	STATUS      current
	DESCRIPTION
	"Table entry display string for divertProxyAsymNotifyRcvError"
	::={divertProxyAsymNotifyRcvErrorLevelEntry 1}

divertProxyAsymNotifyRcvErrorLevelVal OBJECT-TYPE
	SYNTAX	 Counter64
	MAX-ACCESS  read-only
	STATUS      current
	DESCRIPTION
	"Table entry attribute for divertProxyAsymNotifyRcvError"
	::={divertProxyAsymNotifyRcvErrorLevelEntry 2}

divertProxyAsymNotifyRcvErrorLevelMom OBJECT-TYPE
	SYNTAX	 CounterBasedGauge64
	MAX-ACCESS  read-only
	STATUS      current
	DESCRIPTION
	"Table entry attribute for divertProxyAsymNotifyRcvError"
	::={divertProxyAsymNotifyRcvErrorLevelEntry 3}

divertProxyAsymNotifyRcvErrorLevelMax OBJECT-TYPE
	SYNTAX	 CounterBasedGauge64
	MAX-ACCESS  read-only
	STATUS      current
	DESCRIPTION
	"Table entry attribute for divertProxyAsymNotifyRcvError"
	::={divertProxyAsymNotifyRcvErrorLevelEntry 4}


divertProxyAsymNotifyRcvErrorNoRule	OBJECT IDENTIFIER ::={divert 50}

divertProxyAsymNotifyRcvErrorNoRuleVal	OBJECT-TYPE
	SYNTAX	 Counter64
	MAX-ACCESS read-only
	STATUS current
	DESCRIPTION "Proxy asym notifications receive error (no matching divert rule)"

	::={divertProxyAsymNotifyRcvErrorNoRule 1}

divertProxyAsymNotifyRcvErrorNoRuleMom	OBJECT-TYPE
	SYNTAX	 CounterBasedGauge64
	MAX-ACCESS read-only
	STATUS current
	DESCRIPTION "Proxy asym notifications receive error (no matching divert rule)"

	::={divertProxyAsymNotifyRcvErrorNoRule 2}

divertProxyAsymNotifyRcvErrorNoRuleMax	OBJECT-TYPE
	SYNTAX	 CounterBasedGauge64
	MAX-ACCESS read-only
	STATUS current
	DESCRIPTION "Proxy asym notifications receive error (no matching divert rule)"

	::={divertProxyAsymNotifyRcvErrorNoRule 3}

divertProxyAsymNotifyRcvErrorNoRuleLevelTable OBJECT-TYPE
	SYNTAX      SEQUENCE OF DivertProxyAsymNotifyRcvErrorNoRuleLevelEntry
	MAX-ACCESS  not-accessible
	STATUS      current
	DESCRIPTION
	"Table for divertProxyAsymNotifyRcvErrorNoRule"
	::={divertProxyAsymNotifyRcvErrorNoRule 4}

divertProxyAsymNotifyRcvErrorNoRuleLevelEntry OBJECT-TYPE
	SYNTAX      DivertProxyAsymNotifyRcvErrorNoRuleLevelEntry
	MAX-ACCESS  not-accessible
	STATUS      current
	DESCRIPTION
	"Table entry for divertProxyAsymNotifyRcvErrorNoRule"
	INDEX { divertProxyAsymNotifyRcvErrorNoRuleLevelName }
	::={divertProxyAsymNotifyRcvErrorNoRuleLevelTable 1}

DivertProxyAsymNotifyRcvErrorNoRuleLevelEntry ::=
	SEQUENCE {
		divertProxyAsymNotifyRcvErrorNoRuleLevelName	DisplayString,
		divertProxyAsymNotifyRcvErrorNoRuleLevelVal	Counter64,
		divertProxyAsymNotifyRcvErrorNoRuleLevelMom	CounterBasedGauge64,
		divertProxyAsymNotifyRcvErrorNoRuleLevelMax	CounterBasedGauge64
	}

divertProxyAsymNotifyRcvErrorNoRuleLevelName OBJECT-TYPE
	SYNTAX      DisplayString
	MAX-ACCESS  not-accessible
	STATUS      current
	DESCRIPTION
	"Table entry display string for divertProxyAsymNotifyRcvErrorNoRule"
	::={divertProxyAsymNotifyRcvErrorNoRuleLevelEntry 1}

divertProxyAsymNotifyRcvErrorNoRuleLevelVal OBJECT-TYPE
	SYNTAX	 Counter64
	MAX-ACCESS  read-only
	STATUS      current
	DESCRIPTION
	"Table entry attribute for divertProxyAsymNotifyRcvErrorNoRule"
	::={divertProxyAsymNotifyRcvErrorNoRuleLevelEntry 2}

divertProxyAsymNotifyRcvErrorNoRuleLevelMom OBJECT-TYPE
	SYNTAX	 CounterBasedGauge64
	MAX-ACCESS  read-only
	STATUS      current
	DESCRIPTION
	"Table entry attribute for divertProxyAsymNotifyRcvErrorNoRule"
	::={divertProxyAsymNotifyRcvErrorNoRuleLevelEntry 3}

divertProxyAsymNotifyRcvErrorNoRuleLevelMax OBJECT-TYPE
	SYNTAX	 CounterBasedGauge64
	MAX-ACCESS  read-only
	STATUS      current
	DESCRIPTION
	"Table entry attribute for divertProxyAsymNotifyRcvErrorNoRule"
	::={divertProxyAsymNotifyRcvErrorNoRuleLevelEntry 4}


divertProxyAsymNotifyRcvErrorCorrupt	OBJECT IDENTIFIER ::={divert 51}

divertProxyAsymNotifyRcvErrorCorruptVal	OBJECT-TYPE
	SYNTAX	 Counter64
	MAX-ACCESS read-only
	STATUS current
	DESCRIPTION "Proxy asym notifications receive error (corrupt packet)"

	::={divertProxyAsymNotifyRcvErrorCorrupt 1}

divertProxyAsymNotifyRcvErrorCorruptMom	OBJECT-TYPE
	SYNTAX	 CounterBasedGauge64
	MAX-ACCESS read-only
	STATUS current
	DESCRIPTION "Proxy asym notifications receive error (corrupt packet)"

	::={divertProxyAsymNotifyRcvErrorCorrupt 2}

divertProxyAsymNotifyRcvErrorCorruptMax	OBJECT-TYPE
	SYNTAX	 CounterBasedGauge64
	MAX-ACCESS read-only
	STATUS current
	DESCRIPTION "Proxy asym notifications receive error (corrupt packet)"

	::={divertProxyAsymNotifyRcvErrorCorrupt 3}

divertProxyAsymNotifyRcvErrorCorruptLevelTable OBJECT-TYPE
	SYNTAX      SEQUENCE OF DivertProxyAsymNotifyRcvErrorCorruptLevelEntry
	MAX-ACCESS  not-accessible
	STATUS      current
	DESCRIPTION
	"Table for divertProxyAsymNotifyRcvErrorCorrupt"
	::={divertProxyAsymNotifyRcvErrorCorrupt 4}

divertProxyAsymNotifyRcvErrorCorruptLevelEntry OBJECT-TYPE
	SYNTAX      DivertProxyAsymNotifyRcvErrorCorruptLevelEntry
	MAX-ACCESS  not-accessible
	STATUS      current
	DESCRIPTION
	"Table entry for divertProxyAsymNotifyRcvErrorCorrupt"
	INDEX { divertProxyAsymNotifyRcvErrorCorruptLevelName }
	::={divertProxyAsymNotifyRcvErrorCorruptLevelTable 1}

DivertProxyAsymNotifyRcvErrorCorruptLevelEntry ::=
	SEQUENCE {
		divertProxyAsymNotifyRcvErrorCorruptLevelName	DisplayString,
		divertProxyAsymNotifyRcvErrorCorruptLevelVal	Counter64,
		divertProxyAsymNotifyRcvErrorCorruptLevelMom	CounterBasedGauge64,
		divertProxyAsymNotifyRcvErrorCorruptLevelMax	CounterBasedGauge64
	}

divertProxyAsymNotifyRcvErrorCorruptLevelName OBJECT-TYPE
	SYNTAX      DisplayString
	MAX-ACCESS  not-accessible
	STATUS      current
	DESCRIPTION
	"Table entry display string for divertProxyAsymNotifyRcvErrorCorrupt"
	::={divertProxyAsymNotifyRcvErrorCorruptLevelEntry 1}

divertProxyAsymNotifyRcvErrorCorruptLevelVal OBJECT-TYPE
	SYNTAX	 Counter64
	MAX-ACCESS  read-only
	STATUS      current
	DESCRIPTION
	"Table entry attribute for divertProxyAsymNotifyRcvErrorCorrupt"
	::={divertProxyAsymNotifyRcvErrorCorruptLevelEntry 2}

divertProxyAsymNotifyRcvErrorCorruptLevelMom OBJECT-TYPE
	SYNTAX	 CounterBasedGauge64
	MAX-ACCESS  read-only
	STATUS      current
	DESCRIPTION
	"Table entry attribute for divertProxyAsymNotifyRcvErrorCorrupt"
	::={divertProxyAsymNotifyRcvErrorCorruptLevelEntry 3}

divertProxyAsymNotifyRcvErrorCorruptLevelMax OBJECT-TYPE
	SYNTAX	 CounterBasedGauge64
	MAX-ACCESS  read-only
	STATUS      current
	DESCRIPTION
	"Table entry attribute for divertProxyAsymNotifyRcvErrorCorrupt"
	::={divertProxyAsymNotifyRcvErrorCorruptLevelEntry 4}


divertProxyAsymNotifyRcvErrorEstAlreadyDiverted	OBJECT IDENTIFIER ::={divert 52}

divertProxyAsymNotifyRcvErrorEstAlreadyDivertedVal	OBJECT-TYPE
	SYNTAX	 Counter64
	MAX-ACCESS read-only
	STATUS current
	DESCRIPTION "Proxy asym notifications receive error (established but already diverted)"

	::={divertProxyAsymNotifyRcvErrorEstAlreadyDiverted 1}

divertProxyAsymNotifyRcvErrorEstAlreadyDivertedMom	OBJECT-TYPE
	SYNTAX	 CounterBasedGauge64
	MAX-ACCESS read-only
	STATUS current
	DESCRIPTION "Proxy asym notifications receive error (established but already diverted)"

	::={divertProxyAsymNotifyRcvErrorEstAlreadyDiverted 2}

divertProxyAsymNotifyRcvErrorEstAlreadyDivertedMax	OBJECT-TYPE
	SYNTAX	 CounterBasedGauge64
	MAX-ACCESS read-only
	STATUS current
	DESCRIPTION "Proxy asym notifications receive error (established but already diverted)"

	::={divertProxyAsymNotifyRcvErrorEstAlreadyDiverted 3}

divertProxyAsymNotifyRcvErrorEstAlreadyDivertedLevelTable OBJECT-TYPE
	SYNTAX      SEQUENCE OF DivertProxyAsymNotifyRcvErrorEstAlreadyDivertedLevelEntry
	MAX-ACCESS  not-accessible
	STATUS      current
	DESCRIPTION
	"Table for divertProxyAsymNotifyRcvErrorEstAlreadyDiverted"
	::={divertProxyAsymNotifyRcvErrorEstAlreadyDiverted 4}

divertProxyAsymNotifyRcvErrorEstAlreadyDivertedLevelEntry OBJECT-TYPE
	SYNTAX      DivertProxyAsymNotifyRcvErrorEstAlreadyDivertedLevelEntry
	MAX-ACCESS  not-accessible
	STATUS      current
	DESCRIPTION
	"Table entry for divertProxyAsymNotifyRcvErrorEstAlreadyDiverted"
	INDEX { divertProxyAsymNotifyRcvErrorEstAlreadyDivertedLevelName }
	::={divertProxyAsymNotifyRcvErrorEstAlreadyDivertedLevelTable 1}

DivertProxyAsymNotifyRcvErrorEstAlreadyDivertedLevelEntry ::=
	SEQUENCE {
		divertProxyAsymNotifyRcvErrorEstAlreadyDivertedLevelName	DisplayString,
		divertProxyAsymNotifyRcvErrorEstAlreadyDivertedLevelVal	Counter64,
		divertProxyAsymNotifyRcvErrorEstAlreadyDivertedLevelMom	CounterBasedGauge64,
		divertProxyAsymNotifyRcvErrorEstAlreadyDivertedLevelMax	CounterBasedGauge64
	}

divertProxyAsymNotifyRcvErrorEstAlreadyDivertedLevelName OBJECT-TYPE
	SYNTAX      DisplayString
	MAX-ACCESS  not-accessible
	STATUS      current
	DESCRIPTION
	"Table entry display string for divertProxyAsymNotifyRcvErrorEstAlreadyDiverted"
	::={divertProxyAsymNotifyRcvErrorEstAlreadyDivertedLevelEntry 1}

divertProxyAsymNotifyRcvErrorEstAlreadyDivertedLevelVal OBJECT-TYPE
	SYNTAX	 Counter64
	MAX-ACCESS  read-only
	STATUS      current
	DESCRIPTION
	"Table entry attribute for divertProxyAsymNotifyRcvErrorEstAlreadyDiverted"
	::={divertProxyAsymNotifyRcvErrorEstAlreadyDivertedLevelEntry 2}

divertProxyAsymNotifyRcvErrorEstAlreadyDivertedLevelMom OBJECT-TYPE
	SYNTAX	 CounterBasedGauge64
	MAX-ACCESS  read-only
	STATUS      current
	DESCRIPTION
	"Table entry attribute for divertProxyAsymNotifyRcvErrorEstAlreadyDiverted"
	::={divertProxyAsymNotifyRcvErrorEstAlreadyDivertedLevelEntry 3}

divertProxyAsymNotifyRcvErrorEstAlreadyDivertedLevelMax OBJECT-TYPE
	SYNTAX	 CounterBasedGauge64
	MAX-ACCESS  read-only
	STATUS      current
	DESCRIPTION
	"Table entry attribute for divertProxyAsymNotifyRcvErrorEstAlreadyDiverted"
	::={divertProxyAsymNotifyRcvErrorEstAlreadyDivertedLevelEntry 4}


divertFailedProxyConnectionsPktAlloc	OBJECT IDENTIFIER ::={divert 53}

divertFailedProxyConnectionsPktAllocVal	OBJECT-TYPE
	SYNTAX	 Counter64
	MAX-ACCESS read-only
	STATUS current
	DESCRIPTION "Proxy connections failed (allocate packet buffer)"

	::={divertFailedProxyConnectionsPktAlloc 1}

divertFailedProxyConnectionsPktAllocMom	OBJECT-TYPE
	SYNTAX	 CounterBasedGauge64
	MAX-ACCESS read-only
	STATUS current
	DESCRIPTION "Proxy connections failed (allocate packet buffer)"

	::={divertFailedProxyConnectionsPktAlloc 2}

divertFailedProxyConnectionsPktAllocMax	OBJECT-TYPE
	SYNTAX	 CounterBasedGauge64
	MAX-ACCESS read-only
	STATUS current
	DESCRIPTION "Proxy connections failed (allocate packet buffer)"

	::={divertFailedProxyConnectionsPktAlloc 3}

divertFailedProxyConnectionsPktAllocLevelTable OBJECT-TYPE
	SYNTAX      SEQUENCE OF DivertFailedProxyConnectionsPktAllocLevelEntry
	MAX-ACCESS  not-accessible
	STATUS      current
	DESCRIPTION
	"Table for divertFailedProxyConnectionsPktAlloc"
	::={divertFailedProxyConnectionsPktAlloc 4}

divertFailedProxyConnectionsPktAllocLevelEntry OBJECT-TYPE
	SYNTAX      DivertFailedProxyConnectionsPktAllocLevelEntry
	MAX-ACCESS  not-accessible
	STATUS      current
	DESCRIPTION
	"Table entry for divertFailedProxyConnectionsPktAlloc"
	INDEX { divertFailedProxyConnectionsPktAllocLevelName }
	::={divertFailedProxyConnectionsPktAllocLevelTable 1}

DivertFailedProxyConnectionsPktAllocLevelEntry ::=
	SEQUENCE {
		divertFailedProxyConnectionsPktAllocLevelName	DisplayString,
		divertFailedProxyConnectionsPktAllocLevelVal	Counter64,
		divertFailedProxyConnectionsPktAllocLevelMom	CounterBasedGauge64,
		divertFailedProxyConnectionsPktAllocLevelMax	CounterBasedGauge64
	}

divertFailedProxyConnectionsPktAllocLevelName OBJECT-TYPE
	SYNTAX      DisplayString
	MAX-ACCESS  not-accessible
	STATUS      current
	DESCRIPTION
	"Table entry display string for divertFailedProxyConnectionsPktAlloc"
	::={divertFailedProxyConnectionsPktAllocLevelEntry 1}

divertFailedProxyConnectionsPktAllocLevelVal OBJECT-TYPE
	SYNTAX	 Counter64
	MAX-ACCESS  read-only
	STATUS      current
	DESCRIPTION
	"Table entry attribute for divertFailedProxyConnectionsPktAlloc"
	::={divertFailedProxyConnectionsPktAllocLevelEntry 2}

divertFailedProxyConnectionsPktAllocLevelMom OBJECT-TYPE
	SYNTAX	 CounterBasedGauge64
	MAX-ACCESS  read-only
	STATUS      current
	DESCRIPTION
	"Table entry attribute for divertFailedProxyConnectionsPktAlloc"
	::={divertFailedProxyConnectionsPktAllocLevelEntry 3}

divertFailedProxyConnectionsPktAllocLevelMax OBJECT-TYPE
	SYNTAX	 CounterBasedGauge64
	MAX-ACCESS  read-only
	STATUS      current
	DESCRIPTION
	"Table entry attribute for divertFailedProxyConnectionsPktAlloc"
	::={divertFailedProxyConnectionsPktAllocLevelEntry 4}


divertFailedProxyConnectionsPktTx	OBJECT IDENTIFIER ::={divert 54}

divertFailedProxyConnectionsPktTxVal	OBJECT-TYPE
	SYNTAX	 Counter64
	MAX-ACCESS read-only
	STATUS current
	DESCRIPTION "Proxy connections failed (transmit packet buffer)"

	::={divertFailedProxyConnectionsPktTx 1}

divertFailedProxyConnectionsPktTxMom	OBJECT-TYPE
	SYNTAX	 CounterBasedGauge64
	MAX-ACCESS read-only
	STATUS current
	DESCRIPTION "Proxy connections failed (transmit packet buffer)"

	::={divertFailedProxyConnectionsPktTx 2}

divertFailedProxyConnectionsPktTxMax	OBJECT-TYPE
	SYNTAX	 CounterBasedGauge64
	MAX-ACCESS read-only
	STATUS current
	DESCRIPTION "Proxy connections failed (transmit packet buffer)"

	::={divertFailedProxyConnectionsPktTx 3}

divertFailedProxyConnectionsPktTxLevelTable OBJECT-TYPE
	SYNTAX      SEQUENCE OF DivertFailedProxyConnectionsPktTxLevelEntry
	MAX-ACCESS  not-accessible
	STATUS      current
	DESCRIPTION
	"Table for divertFailedProxyConnectionsPktTx"
	::={divertFailedProxyConnectionsPktTx 4}

divertFailedProxyConnectionsPktTxLevelEntry OBJECT-TYPE
	SYNTAX      DivertFailedProxyConnectionsPktTxLevelEntry
	MAX-ACCESS  not-accessible
	STATUS      current
	DESCRIPTION
	"Table entry for divertFailedProxyConnectionsPktTx"
	INDEX { divertFailedProxyConnectionsPktTxLevelName }
	::={divertFailedProxyConnectionsPktTxLevelTable 1}

DivertFailedProxyConnectionsPktTxLevelEntry ::=
	SEQUENCE {
		divertFailedProxyConnectionsPktTxLevelName	DisplayString,
		divertFailedProxyConnectionsPktTxLevelVal	Counter64,
		divertFailedProxyConnectionsPktTxLevelMom	CounterBasedGauge64,
		divertFailedProxyConnectionsPktTxLevelMax	CounterBasedGauge64
	}

divertFailedProxyConnectionsPktTxLevelName OBJECT-TYPE
	SYNTAX      DisplayString
	MAX-ACCESS  not-accessible
	STATUS      current
	DESCRIPTION
	"Table entry display string for divertFailedProxyConnectionsPktTx"
	::={divertFailedProxyConnectionsPktTxLevelEntry 1}

divertFailedProxyConnectionsPktTxLevelVal OBJECT-TYPE
	SYNTAX	 Counter64
	MAX-ACCESS  read-only
	STATUS      current
	DESCRIPTION
	"Table entry attribute for divertFailedProxyConnectionsPktTx"
	::={divertFailedProxyConnectionsPktTxLevelEntry 2}

divertFailedProxyConnectionsPktTxLevelMom OBJECT-TYPE
	SYNTAX	 CounterBasedGauge64
	MAX-ACCESS  read-only
	STATUS      current
	DESCRIPTION
	"Table entry attribute for divertFailedProxyConnectionsPktTx"
	::={divertFailedProxyConnectionsPktTxLevelEntry 3}

divertFailedProxyConnectionsPktTxLevelMax OBJECT-TYPE
	SYNTAX	 CounterBasedGauge64
	MAX-ACCESS  read-only
	STATUS      current
	DESCRIPTION
	"Table entry attribute for divertFailedProxyConnectionsPktTx"
	::={divertFailedProxyConnectionsPktTxLevelEntry 4}


divertFailedProxyConnectionsUnexpectedRcv	OBJECT IDENTIFIER ::={divert 55}

divertFailedProxyConnectionsUnexpectedRcvVal	OBJECT-TYPE
	SYNTAX	 Counter64
	MAX-ACCESS read-only
	STATUS current
	DESCRIPTION "Proxy connections failed (unexpected packet received)"

	::={divertFailedProxyConnectionsUnexpectedRcv 1}

divertFailedProxyConnectionsUnexpectedRcvMom	OBJECT-TYPE
	SYNTAX	 CounterBasedGauge64
	MAX-ACCESS read-only
	STATUS current
	DESCRIPTION "Proxy connections failed (unexpected packet received)"

	::={divertFailedProxyConnectionsUnexpectedRcv 2}

divertFailedProxyConnectionsUnexpectedRcvMax	OBJECT-TYPE
	SYNTAX	 CounterBasedGauge64
	MAX-ACCESS read-only
	STATUS current
	DESCRIPTION "Proxy connections failed (unexpected packet received)"

	::={divertFailedProxyConnectionsUnexpectedRcv 3}

divertFailedProxyConnectionsUnexpectedRcvLevelTable OBJECT-TYPE
	SYNTAX      SEQUENCE OF DivertFailedProxyConnectionsUnexpectedRcvLevelEntry
	MAX-ACCESS  not-accessible
	STATUS      current
	DESCRIPTION
	"Table for divertFailedProxyConnectionsUnexpectedRcv"
	::={divertFailedProxyConnectionsUnexpectedRcv 4}

divertFailedProxyConnectionsUnexpectedRcvLevelEntry OBJECT-TYPE
	SYNTAX      DivertFailedProxyConnectionsUnexpectedRcvLevelEntry
	MAX-ACCESS  not-accessible
	STATUS      current
	DESCRIPTION
	"Table entry for divertFailedProxyConnectionsUnexpectedRcv"
	INDEX { divertFailedProxyConnectionsUnexpectedRcvLevelName }
	::={divertFailedProxyConnectionsUnexpectedRcvLevelTable 1}

DivertFailedProxyConnectionsUnexpectedRcvLevelEntry ::=
	SEQUENCE {
		divertFailedProxyConnectionsUnexpectedRcvLevelName	DisplayString,
		divertFailedProxyConnectionsUnexpectedRcvLevelVal	Counter64,
		divertFailedProxyConnectionsUnexpectedRcvLevelMom	CounterBasedGauge64,
		divertFailedProxyConnectionsUnexpectedRcvLevelMax	CounterBasedGauge64
	}

divertFailedProxyConnectionsUnexpectedRcvLevelName OBJECT-TYPE
	SYNTAX      DisplayString
	MAX-ACCESS  not-accessible
	STATUS      current
	DESCRIPTION
	"Table entry display string for divertFailedProxyConnectionsUnexpectedRcv"
	::={divertFailedProxyConnectionsUnexpectedRcvLevelEntry 1}

divertFailedProxyConnectionsUnexpectedRcvLevelVal OBJECT-TYPE
	SYNTAX	 Counter64
	MAX-ACCESS  read-only
	STATUS      current
	DESCRIPTION
	"Table entry attribute for divertFailedProxyConnectionsUnexpectedRcv"
	::={divertFailedProxyConnectionsUnexpectedRcvLevelEntry 2}

divertFailedProxyConnectionsUnexpectedRcvLevelMom OBJECT-TYPE
	SYNTAX	 CounterBasedGauge64
	MAX-ACCESS  read-only
	STATUS      current
	DESCRIPTION
	"Table entry attribute for divertFailedProxyConnectionsUnexpectedRcv"
	::={divertFailedProxyConnectionsUnexpectedRcvLevelEntry 3}

divertFailedProxyConnectionsUnexpectedRcvLevelMax OBJECT-TYPE
	SYNTAX	 CounterBasedGauge64
	MAX-ACCESS  read-only
	STATUS      current
	DESCRIPTION
	"Table entry attribute for divertFailedProxyConnectionsUnexpectedRcv"
	::={divertFailedProxyConnectionsUnexpectedRcvLevelEntry 4}


divertFailedProxyConnectionsTimeout	OBJECT IDENTIFIER ::={divert 56}

divertFailedProxyConnectionsTimeoutVal	OBJECT-TYPE
	SYNTAX	 Counter64
	MAX-ACCESS read-only
	STATUS current
	DESCRIPTION "Proxy connections failed (timeout)"

	::={divertFailedProxyConnectionsTimeout 1}

divertFailedProxyConnectionsTimeoutMom	OBJECT-TYPE
	SYNTAX	 CounterBasedGauge64
	MAX-ACCESS read-only
	STATUS current
	DESCRIPTION "Proxy connections failed (timeout)"

	::={divertFailedProxyConnectionsTimeout 2}

divertFailedProxyConnectionsTimeoutMax	OBJECT-TYPE
	SYNTAX	 CounterBasedGauge64
	MAX-ACCESS read-only
	STATUS current
	DESCRIPTION "Proxy connections failed (timeout)"

	::={divertFailedProxyConnectionsTimeout 3}

divertFailedProxyConnectionsTimeoutLevelTable OBJECT-TYPE
	SYNTAX      SEQUENCE OF DivertFailedProxyConnectionsTimeoutLevelEntry
	MAX-ACCESS  not-accessible
	STATUS      current
	DESCRIPTION
	"Table for divertFailedProxyConnectionsTimeout"
	::={divertFailedProxyConnectionsTimeout 4}

divertFailedProxyConnectionsTimeoutLevelEntry OBJECT-TYPE
	SYNTAX      DivertFailedProxyConnectionsTimeoutLevelEntry
	MAX-ACCESS  not-accessible
	STATUS      current
	DESCRIPTION
	"Table entry for divertFailedProxyConnectionsTimeout"
	INDEX { divertFailedProxyConnectionsTimeoutLevelName }
	::={divertFailedProxyConnectionsTimeoutLevelTable 1}

DivertFailedProxyConnectionsTimeoutLevelEntry ::=
	SEQUENCE {
		divertFailedProxyConnectionsTimeoutLevelName	DisplayString,
		divertFailedProxyConnectionsTimeoutLevelVal	Counter64,
		divertFailedProxyConnectionsTimeoutLevelMom	CounterBasedGauge64,
		divertFailedProxyConnectionsTimeoutLevelMax	CounterBasedGauge64
	}

divertFailedProxyConnectionsTimeoutLevelName OBJECT-TYPE
	SYNTAX      DisplayString
	MAX-ACCESS  not-accessible
	STATUS      current
	DESCRIPTION
	"Table entry display string for divertFailedProxyConnectionsTimeout"
	::={divertFailedProxyConnectionsTimeoutLevelEntry 1}

divertFailedProxyConnectionsTimeoutLevelVal OBJECT-TYPE
	SYNTAX	 Counter64
	MAX-ACCESS  read-only
	STATUS      current
	DESCRIPTION
	"Table entry attribute for divertFailedProxyConnectionsTimeout"
	::={divertFailedProxyConnectionsTimeoutLevelEntry 2}

divertFailedProxyConnectionsTimeoutLevelMom OBJECT-TYPE
	SYNTAX	 CounterBasedGauge64
	MAX-ACCESS  read-only
	STATUS      current
	DESCRIPTION
	"Table entry attribute for divertFailedProxyConnectionsTimeout"
	::={divertFailedProxyConnectionsTimeoutLevelEntry 3}

divertFailedProxyConnectionsTimeoutLevelMax OBJECT-TYPE
	SYNTAX	 CounterBasedGauge64
	MAX-ACCESS  read-only
	STATUS      current
	DESCRIPTION
	"Table entry attribute for divertFailedProxyConnectionsTimeout"
	::={divertFailedProxyConnectionsTimeoutLevelEntry 4}


divertProxyBufferedPkts	OBJECT IDENTIFIER ::={divert 57}

divertProxyBufferedPktsVal	OBJECT-TYPE
	SYNTAX	 CounterBasedGauge64
	MAX-ACCESS read-only
	STATUS current
	DESCRIPTION "Proxy buffered packets"

	::={divertProxyBufferedPkts 1}

divertProxyBufferedPktsMax	OBJECT-TYPE
	SYNTAX	 CounterBasedGauge64
	MAX-ACCESS read-only
	STATUS current
	DESCRIPTION "Proxy buffered packets"

	::={divertProxyBufferedPkts 3}

divertProxyBufferedPktsLevelTable OBJECT-TYPE
	SYNTAX      SEQUENCE OF DivertProxyBufferedPktsLevelEntry
	MAX-ACCESS  not-accessible
	STATUS      current
	DESCRIPTION
	"Table for divertProxyBufferedPkts"
	::={divertProxyBufferedPkts 4}

divertProxyBufferedPktsLevelEntry OBJECT-TYPE
	SYNTAX      DivertProxyBufferedPktsLevelEntry
	MAX-ACCESS  not-accessible
	STATUS      current
	DESCRIPTION
	"Table entry for divertProxyBufferedPkts"
	INDEX { divertProxyBufferedPktsLevelName }
	::={divertProxyBufferedPktsLevelTable 1}

DivertProxyBufferedPktsLevelEntry ::=
	SEQUENCE {
		divertProxyBufferedPktsLevelName	DisplayString,
		divertProxyBufferedPktsLevelVal	CounterBasedGauge64,
		divertProxyBufferedPktsLevelMax	CounterBasedGauge64
	}

divertProxyBufferedPktsLevelName OBJECT-TYPE
	SYNTAX      DisplayString
	MAX-ACCESS  not-accessible
	STATUS      current
	DESCRIPTION
	"Table entry display string for divertProxyBufferedPkts"
	::={divertProxyBufferedPktsLevelEntry 1}

divertProxyBufferedPktsLevelVal OBJECT-TYPE
	SYNTAX	 CounterBasedGauge64
	MAX-ACCESS  read-only
	STATUS      current
	DESCRIPTION
	"Table entry attribute for divertProxyBufferedPkts"
	::={divertProxyBufferedPktsLevelEntry 2}

divertProxyBufferedPktsLevelMax OBJECT-TYPE
	SYNTAX	 CounterBasedGauge64
	MAX-ACCESS  read-only
	STATUS      current
	DESCRIPTION
	"Table entry attribute for divertProxyBufferedPkts"
	::={divertProxyBufferedPktsLevelEntry 4}


divertFailedProxyBufferPktDrop	OBJECT IDENTIFIER ::={divert 58}

divertFailedProxyBufferPktDropVal	OBJECT-TYPE
	SYNTAX	 Counter64
	MAX-ACCESS read-only
	STATUS current
	DESCRIPTION "Proxy buffered packets dropped (resources)"

	::={divertFailedProxyBufferPktDrop 1}

divertFailedProxyBufferPktDropMom	OBJECT-TYPE
	SYNTAX	 CounterBasedGauge64
	MAX-ACCESS read-only
	STATUS current
	DESCRIPTION "Proxy buffered packets dropped (resources)"

	::={divertFailedProxyBufferPktDrop 2}

divertFailedProxyBufferPktDropMax	OBJECT-TYPE
	SYNTAX	 CounterBasedGauge64
	MAX-ACCESS read-only
	STATUS current
	DESCRIPTION "Proxy buffered packets dropped (resources)"

	::={divertFailedProxyBufferPktDrop 3}

divertFailedProxyBufferPktDropLevelTable OBJECT-TYPE
	SYNTAX      SEQUENCE OF DivertFailedProxyBufferPktDropLevelEntry
	MAX-ACCESS  not-accessible
	STATUS      current
	DESCRIPTION
	"Table for divertFailedProxyBufferPktDrop"
	::={divertFailedProxyBufferPktDrop 4}

divertFailedProxyBufferPktDropLevelEntry OBJECT-TYPE
	SYNTAX      DivertFailedProxyBufferPktDropLevelEntry
	MAX-ACCESS  not-accessible
	STATUS      current
	DESCRIPTION
	"Table entry for divertFailedProxyBufferPktDrop"
	INDEX { divertFailedProxyBufferPktDropLevelName }
	::={divertFailedProxyBufferPktDropLevelTable 1}

DivertFailedProxyBufferPktDropLevelEntry ::=
	SEQUENCE {
		divertFailedProxyBufferPktDropLevelName	DisplayString,
		divertFailedProxyBufferPktDropLevelVal	Counter64,
		divertFailedProxyBufferPktDropLevelMom	CounterBasedGauge64,
		divertFailedProxyBufferPktDropLevelMax	CounterBasedGauge64
	}

divertFailedProxyBufferPktDropLevelName OBJECT-TYPE
	SYNTAX      DisplayString
	MAX-ACCESS  not-accessible
	STATUS      current
	DESCRIPTION
	"Table entry display string for divertFailedProxyBufferPktDrop"
	::={divertFailedProxyBufferPktDropLevelEntry 1}

divertFailedProxyBufferPktDropLevelVal OBJECT-TYPE
	SYNTAX	 Counter64
	MAX-ACCESS  read-only
	STATUS      current
	DESCRIPTION
	"Table entry attribute for divertFailedProxyBufferPktDrop"
	::={divertFailedProxyBufferPktDropLevelEntry 2}

divertFailedProxyBufferPktDropLevelMom OBJECT-TYPE
	SYNTAX	 CounterBasedGauge64
	MAX-ACCESS  read-only
	STATUS      current
	DESCRIPTION
	"Table entry attribute for divertFailedProxyBufferPktDrop"
	::={divertFailedProxyBufferPktDropLevelEntry 3}

divertFailedProxyBufferPktDropLevelMax OBJECT-TYPE
	SYNTAX	 CounterBasedGauge64
	MAX-ACCESS  read-only
	STATUS      current
	DESCRIPTION
	"Table entry attribute for divertFailedProxyBufferPktDrop"
	::={divertFailedProxyBufferPktDropLevelEntry 4}


divertProxyAsymRemoteIngressErrorNoProxy	OBJECT IDENTIFIER ::={divert 59}

divertProxyAsymRemoteIngressErrorNoProxyVal	OBJECT-TYPE
	SYNTAX	 Counter64
	MAX-ACCESS read-only
	STATUS current
	DESCRIPTION "Proxy asym remote ingress error (no divert proxy present)"

	::={divertProxyAsymRemoteIngressErrorNoProxy 1}

divertProxyAsymRemoteIngressErrorNoProxyMom	OBJECT-TYPE
	SYNTAX	 CounterBasedGauge64
	MAX-ACCESS read-only
	STATUS current
	DESCRIPTION "Proxy asym remote ingress error (no divert proxy present)"

	::={divertProxyAsymRemoteIngressErrorNoProxy 2}

divertProxyAsymRemoteIngressErrorNoProxyMax	OBJECT-TYPE
	SYNTAX	 CounterBasedGauge64
	MAX-ACCESS read-only
	STATUS current
	DESCRIPTION "Proxy asym remote ingress error (no divert proxy present)"

	::={divertProxyAsymRemoteIngressErrorNoProxy 3}

divertProxyAsymRemoteIngressErrorNoProxyLevelTable OBJECT-TYPE
	SYNTAX      SEQUENCE OF DivertProxyAsymRemoteIngressErrorNoProxyLevelEntry
	MAX-ACCESS  not-accessible
	STATUS      current
	DESCRIPTION
	"Table for divertProxyAsymRemoteIngressErrorNoProxy"
	::={divertProxyAsymRemoteIngressErrorNoProxy 4}

divertProxyAsymRemoteIngressErrorNoProxyLevelEntry OBJECT-TYPE
	SYNTAX      DivertProxyAsymRemoteIngressErrorNoProxyLevelEntry
	MAX-ACCESS  not-accessible
	STATUS      current
	DESCRIPTION
	"Table entry for divertProxyAsymRemoteIngressErrorNoProxy"
	INDEX { divertProxyAsymRemoteIngressErrorNoProxyLevelName }
	::={divertProxyAsymRemoteIngressErrorNoProxyLevelTable 1}

DivertProxyAsymRemoteIngressErrorNoProxyLevelEntry ::=
	SEQUENCE {
		divertProxyAsymRemoteIngressErrorNoProxyLevelName	DisplayString,
		divertProxyAsymRemoteIngressErrorNoProxyLevelVal	Counter64,
		divertProxyAsymRemoteIngressErrorNoProxyLevelMom	CounterBasedGauge64,
		divertProxyAsymRemoteIngressErrorNoProxyLevelMax	CounterBasedGauge64
	}

divertProxyAsymRemoteIngressErrorNoProxyLevelName OBJECT-TYPE
	SYNTAX      DisplayString
	MAX-ACCESS  not-accessible
	STATUS      current
	DESCRIPTION
	"Table entry display string for divertProxyAsymRemoteIngressErrorNoProxy"
	::={divertProxyAsymRemoteIngressErrorNoProxyLevelEntry 1}

divertProxyAsymRemoteIngressErrorNoProxyLevelVal OBJECT-TYPE
	SYNTAX	 Counter64
	MAX-ACCESS  read-only
	STATUS      current
	DESCRIPTION
	"Table entry attribute for divertProxyAsymRemoteIngressErrorNoProxy"
	::={divertProxyAsymRemoteIngressErrorNoProxyLevelEntry 2}

divertProxyAsymRemoteIngressErrorNoProxyLevelMom OBJECT-TYPE
	SYNTAX	 CounterBasedGauge64
	MAX-ACCESS  read-only
	STATUS      current
	DESCRIPTION
	"Table entry attribute for divertProxyAsymRemoteIngressErrorNoProxy"
	::={divertProxyAsymRemoteIngressErrorNoProxyLevelEntry 3}

divertProxyAsymRemoteIngressErrorNoProxyLevelMax OBJECT-TYPE
	SYNTAX	 CounterBasedGauge64
	MAX-ACCESS  read-only
	STATUS      current
	DESCRIPTION
	"Table entry attribute for divertProxyAsymRemoteIngressErrorNoProxy"
	::={divertProxyAsymRemoteIngressErrorNoProxyLevelEntry 4}


divertFailedProxyConnectionsUnexpectedRcvSynAckReply	OBJECT IDENTIFIER ::={divert 60}

divertFailedProxyConnectionsUnexpectedRcvSynAckReplyVal	OBJECT-TYPE
	SYNTAX	 Counter64
	MAX-ACCESS read-only
	STATUS current
	DESCRIPTION "Proxy connections failed (unexpected packet received, SYN/ACK reply expected)"

	::={divertFailedProxyConnectionsUnexpectedRcvSynAckReply 1}

divertFailedProxyConnectionsUnexpectedRcvSynAckReplyMom	OBJECT-TYPE
	SYNTAX	 CounterBasedGauge64
	MAX-ACCESS read-only
	STATUS current
	DESCRIPTION "Proxy connections failed (unexpected packet received, SYN/ACK reply expected)"

	::={divertFailedProxyConnectionsUnexpectedRcvSynAckReply 2}

divertFailedProxyConnectionsUnexpectedRcvSynAckReplyMax	OBJECT-TYPE
	SYNTAX	 CounterBasedGauge64
	MAX-ACCESS read-only
	STATUS current
	DESCRIPTION "Proxy connections failed (unexpected packet received, SYN/ACK reply expected)"

	::={divertFailedProxyConnectionsUnexpectedRcvSynAckReply 3}

divertFailedProxyConnectionsUnexpectedRcvSynAckReplyLevelTable OBJECT-TYPE
	SYNTAX      SEQUENCE OF DivertFailedProxyConnectionsUnexpectedRcvSynAckReplyLevelEntry
	MAX-ACCESS  not-accessible
	STATUS      current
	DESCRIPTION
	"Table for divertFailedProxyConnectionsUnexpectedRcvSynAckReply"
	::={divertFailedProxyConnectionsUnexpectedRcvSynAckReply 4}

divertFailedProxyConnectionsUnexpectedRcvSynAckReplyLevelEntry OBJECT-TYPE
	SYNTAX      DivertFailedProxyConnectionsUnexpectedRcvSynAckReplyLevelEntry
	MAX-ACCESS  not-accessible
	STATUS      current
	DESCRIPTION
	"Table entry for divertFailedProxyConnectionsUnexpectedRcvSynAckReply"
	INDEX { divertFailedProxyConnectionsUnexpectedRcvSynAckReplyLevelName }
	::={divertFailedProxyConnectionsUnexpectedRcvSynAckReplyLevelTable 1}

DivertFailedProxyConnectionsUnexpectedRcvSynAckReplyLevelEntry ::=
	SEQUENCE {
		divertFailedProxyConnectionsUnexpectedRcvSynAckReplyLevelName	DisplayString,
		divertFailedProxyConnectionsUnexpectedRcvSynAckReplyLevelVal	Counter64,
		divertFailedProxyConnectionsUnexpectedRcvSynAckReplyLevelMom	CounterBasedGauge64,
		divertFailedProxyConnectionsUnexpectedRcvSynAckReplyLevelMax	CounterBasedGauge64
	}

divertFailedProxyConnectionsUnexpectedRcvSynAckReplyLevelName OBJECT-TYPE
	SYNTAX      DisplayString
	MAX-ACCESS  not-accessible
	STATUS      current
	DESCRIPTION
	"Table entry display string for divertFailedProxyConnectionsUnexpectedRcvSynAckReply"
	::={divertFailedProxyConnectionsUnexpectedRcvSynAckReplyLevelEntry 1}

divertFailedProxyConnectionsUnexpectedRcvSynAckReplyLevelVal OBJECT-TYPE
	SYNTAX	 Counter64
	MAX-ACCESS  read-only
	STATUS      current
	DESCRIPTION
	"Table entry attribute for divertFailedProxyConnectionsUnexpectedRcvSynAckReply"
	::={divertFailedProxyConnectionsUnexpectedRcvSynAckReplyLevelEntry 2}

divertFailedProxyConnectionsUnexpectedRcvSynAckReplyLevelMom OBJECT-TYPE
	SYNTAX	 CounterBasedGauge64
	MAX-ACCESS  read-only
	STATUS      current
	DESCRIPTION
	"Table entry attribute for divertFailedProxyConnectionsUnexpectedRcvSynAckReply"
	::={divertFailedProxyConnectionsUnexpectedRcvSynAckReplyLevelEntry 3}

divertFailedProxyConnectionsUnexpectedRcvSynAckReplyLevelMax OBJECT-TYPE
	SYNTAX	 CounterBasedGauge64
	MAX-ACCESS  read-only
	STATUS      current
	DESCRIPTION
	"Table entry attribute for divertFailedProxyConnectionsUnexpectedRcvSynAckReply"
	::={divertFailedProxyConnectionsUnexpectedRcvSynAckReplyLevelEntry 4}


divertFailedProxyConnectionsUnexpectedRcvSynOwn	OBJECT IDENTIFIER ::={divert 61}

divertFailedProxyConnectionsUnexpectedRcvSynOwnVal	OBJECT-TYPE
	SYNTAX	 Counter64
	MAX-ACCESS read-only
	STATUS current
	DESCRIPTION "Proxy connections failed (unexpected packet received, own SYN expected)"

	::={divertFailedProxyConnectionsUnexpectedRcvSynOwn 1}

divertFailedProxyConnectionsUnexpectedRcvSynOwnMom	OBJECT-TYPE
	SYNTAX	 CounterBasedGauge64
	MAX-ACCESS read-only
	STATUS current
	DESCRIPTION "Proxy connections failed (unexpected packet received, own SYN expected)"

	::={divertFailedProxyConnectionsUnexpectedRcvSynOwn 2}

divertFailedProxyConnectionsUnexpectedRcvSynOwnMax	OBJECT-TYPE
	SYNTAX	 CounterBasedGauge64
	MAX-ACCESS read-only
	STATUS current
	DESCRIPTION "Proxy connections failed (unexpected packet received, own SYN expected)"

	::={divertFailedProxyConnectionsUnexpectedRcvSynOwn 3}

divertFailedProxyConnectionsUnexpectedRcvSynOwnLevelTable OBJECT-TYPE
	SYNTAX      SEQUENCE OF DivertFailedProxyConnectionsUnexpectedRcvSynOwnLevelEntry
	MAX-ACCESS  not-accessible
	STATUS      current
	DESCRIPTION
	"Table for divertFailedProxyConnectionsUnexpectedRcvSynOwn"
	::={divertFailedProxyConnectionsUnexpectedRcvSynOwn 4}

divertFailedProxyConnectionsUnexpectedRcvSynOwnLevelEntry OBJECT-TYPE
	SYNTAX      DivertFailedProxyConnectionsUnexpectedRcvSynOwnLevelEntry
	MAX-ACCESS  not-accessible
	STATUS      current
	DESCRIPTION
	"Table entry for divertFailedProxyConnectionsUnexpectedRcvSynOwn"
	INDEX { divertFailedProxyConnectionsUnexpectedRcvSynOwnLevelName }
	::={divertFailedProxyConnectionsUnexpectedRcvSynOwnLevelTable 1}

DivertFailedProxyConnectionsUnexpectedRcvSynOwnLevelEntry ::=
	SEQUENCE {
		divertFailedProxyConnectionsUnexpectedRcvSynOwnLevelName	DisplayString,
		divertFailedProxyConnectionsUnexpectedRcvSynOwnLevelVal	Counter64,
		divertFailedProxyConnectionsUnexpectedRcvSynOwnLevelMom	CounterBasedGauge64,
		divertFailedProxyConnectionsUnexpectedRcvSynOwnLevelMax	CounterBasedGauge64
	}

divertFailedProxyConnectionsUnexpectedRcvSynOwnLevelName OBJECT-TYPE
	SYNTAX      DisplayString
	MAX-ACCESS  not-accessible
	STATUS      current
	DESCRIPTION
	"Table entry display string for divertFailedProxyConnectionsUnexpectedRcvSynOwn"
	::={divertFailedProxyConnectionsUnexpectedRcvSynOwnLevelEntry 1}

divertFailedProxyConnectionsUnexpectedRcvSynOwnLevelVal OBJECT-TYPE
	SYNTAX	 Counter64
	MAX-ACCESS  read-only
	STATUS      current
	DESCRIPTION
	"Table entry attribute for divertFailedProxyConnectionsUnexpectedRcvSynOwn"
	::={divertFailedProxyConnectionsUnexpectedRcvSynOwnLevelEntry 2}

divertFailedProxyConnectionsUnexpectedRcvSynOwnLevelMom OBJECT-TYPE
	SYNTAX	 CounterBasedGauge64
	MAX-ACCESS  read-only
	STATUS      current
	DESCRIPTION
	"Table entry attribute for divertFailedProxyConnectionsUnexpectedRcvSynOwn"
	::={divertFailedProxyConnectionsUnexpectedRcvSynOwnLevelEntry 3}

divertFailedProxyConnectionsUnexpectedRcvSynOwnLevelMax OBJECT-TYPE
	SYNTAX	 CounterBasedGauge64
	MAX-ACCESS  read-only
	STATUS      current
	DESCRIPTION
	"Table entry attribute for divertFailedProxyConnectionsUnexpectedRcvSynOwn"
	::={divertFailedProxyConnectionsUnexpectedRcvSynOwnLevelEntry 4}


divertFailedProxyConnectionsUnexpectedRcvSynAckOwn	OBJECT IDENTIFIER ::={divert 62}

divertFailedProxyConnectionsUnexpectedRcvSynAckOwnVal	OBJECT-TYPE
	SYNTAX	 Counter64
	MAX-ACCESS read-only
	STATUS current
	DESCRIPTION "Proxy connections failed (unexpected packet received, own SYN/ACK expected)"

	::={divertFailedProxyConnectionsUnexpectedRcvSynAckOwn 1}

divertFailedProxyConnectionsUnexpectedRcvSynAckOwnMom	OBJECT-TYPE
	SYNTAX	 CounterBasedGauge64
	MAX-ACCESS read-only
	STATUS current
	DESCRIPTION "Proxy connections failed (unexpected packet received, own SYN/ACK expected)"

	::={divertFailedProxyConnectionsUnexpectedRcvSynAckOwn 2}

divertFailedProxyConnectionsUnexpectedRcvSynAckOwnMax	OBJECT-TYPE
	SYNTAX	 CounterBasedGauge64
	MAX-ACCESS read-only
	STATUS current
	DESCRIPTION "Proxy connections failed (unexpected packet received, own SYN/ACK expected)"

	::={divertFailedProxyConnectionsUnexpectedRcvSynAckOwn 3}

divertFailedProxyConnectionsUnexpectedRcvSynAckOwnLevelTable OBJECT-TYPE
	SYNTAX      SEQUENCE OF DivertFailedProxyConnectionsUnexpectedRcvSynAckOwnLevelEntry
	MAX-ACCESS  not-accessible
	STATUS      current
	DESCRIPTION
	"Table for divertFailedProxyConnectionsUnexpectedRcvSynAckOwn"
	::={divertFailedProxyConnectionsUnexpectedRcvSynAckOwn 4}

divertFailedProxyConnectionsUnexpectedRcvSynAckOwnLevelEntry OBJECT-TYPE
	SYNTAX      DivertFailedProxyConnectionsUnexpectedRcvSynAckOwnLevelEntry
	MAX-ACCESS  not-accessible
	STATUS      current
	DESCRIPTION
	"Table entry for divertFailedProxyConnectionsUnexpectedRcvSynAckOwn"
	INDEX { divertFailedProxyConnectionsUnexpectedRcvSynAckOwnLevelName }
	::={divertFailedProxyConnectionsUnexpectedRcvSynAckOwnLevelTable 1}

DivertFailedProxyConnectionsUnexpectedRcvSynAckOwnLevelEntry ::=
	SEQUENCE {
		divertFailedProxyConnectionsUnexpectedRcvSynAckOwnLevelName	DisplayString,
		divertFailedProxyConnectionsUnexpectedRcvSynAckOwnLevelVal	Counter64,
		divertFailedProxyConnectionsUnexpectedRcvSynAckOwnLevelMom	CounterBasedGauge64,
		divertFailedProxyConnectionsUnexpectedRcvSynAckOwnLevelMax	CounterBasedGauge64
	}

divertFailedProxyConnectionsUnexpectedRcvSynAckOwnLevelName OBJECT-TYPE
	SYNTAX      DisplayString
	MAX-ACCESS  not-accessible
	STATUS      current
	DESCRIPTION
	"Table entry display string for divertFailedProxyConnectionsUnexpectedRcvSynAckOwn"
	::={divertFailedProxyConnectionsUnexpectedRcvSynAckOwnLevelEntry 1}

divertFailedProxyConnectionsUnexpectedRcvSynAckOwnLevelVal OBJECT-TYPE
	SYNTAX	 Counter64
	MAX-ACCESS  read-only
	STATUS      current
	DESCRIPTION
	"Table entry attribute for divertFailedProxyConnectionsUnexpectedRcvSynAckOwn"
	::={divertFailedProxyConnectionsUnexpectedRcvSynAckOwnLevelEntry 2}

divertFailedProxyConnectionsUnexpectedRcvSynAckOwnLevelMom OBJECT-TYPE
	SYNTAX	 CounterBasedGauge64
	MAX-ACCESS  read-only
	STATUS      current
	DESCRIPTION
	"Table entry attribute for divertFailedProxyConnectionsUnexpectedRcvSynAckOwn"
	::={divertFailedProxyConnectionsUnexpectedRcvSynAckOwnLevelEntry 3}

divertFailedProxyConnectionsUnexpectedRcvSynAckOwnLevelMax OBJECT-TYPE
	SYNTAX	 CounterBasedGauge64
	MAX-ACCESS  read-only
	STATUS      current
	DESCRIPTION
	"Table entry attribute for divertFailedProxyConnectionsUnexpectedRcvSynAckOwn"
	::={divertFailedProxyConnectionsUnexpectedRcvSynAckOwnLevelEntry 4}


divertFailedProxyConnectionsUnexpectedRcvAckOwn	OBJECT IDENTIFIER ::={divert 63}

divertFailedProxyConnectionsUnexpectedRcvAckOwnVal	OBJECT-TYPE
	SYNTAX	 Counter64
	MAX-ACCESS read-only
	STATUS current
	DESCRIPTION "Proxy connections failed (unexpected packet received, own final ACK expected)"

	::={divertFailedProxyConnectionsUnexpectedRcvAckOwn 1}

divertFailedProxyConnectionsUnexpectedRcvAckOwnMom	OBJECT-TYPE
	SYNTAX	 CounterBasedGauge64
	MAX-ACCESS read-only
	STATUS current
	DESCRIPTION "Proxy connections failed (unexpected packet received, own final ACK expected)"

	::={divertFailedProxyConnectionsUnexpectedRcvAckOwn 2}

divertFailedProxyConnectionsUnexpectedRcvAckOwnMax	OBJECT-TYPE
	SYNTAX	 CounterBasedGauge64
	MAX-ACCESS read-only
	STATUS current
	DESCRIPTION "Proxy connections failed (unexpected packet received, own final ACK expected)"

	::={divertFailedProxyConnectionsUnexpectedRcvAckOwn 3}

divertFailedProxyConnectionsUnexpectedRcvAckOwnLevelTable OBJECT-TYPE
	SYNTAX      SEQUENCE OF DivertFailedProxyConnectionsUnexpectedRcvAckOwnLevelEntry
	MAX-ACCESS  not-accessible
	STATUS      current
	DESCRIPTION
	"Table for divertFailedProxyConnectionsUnexpectedRcvAckOwn"
	::={divertFailedProxyConnectionsUnexpectedRcvAckOwn 4}

divertFailedProxyConnectionsUnexpectedRcvAckOwnLevelEntry OBJECT-TYPE
	SYNTAX      DivertFailedProxyConnectionsUnexpectedRcvAckOwnLevelEntry
	MAX-ACCESS  not-accessible
	STATUS      current
	DESCRIPTION
	"Table entry for divertFailedProxyConnectionsUnexpectedRcvAckOwn"
	INDEX { divertFailedProxyConnectionsUnexpectedRcvAckOwnLevelName }
	::={divertFailedProxyConnectionsUnexpectedRcvAckOwnLevelTable 1}

DivertFailedProxyConnectionsUnexpectedRcvAckOwnLevelEntry ::=
	SEQUENCE {
		divertFailedProxyConnectionsUnexpectedRcvAckOwnLevelName	DisplayString,
		divertFailedProxyConnectionsUnexpectedRcvAckOwnLevelVal	Counter64,
		divertFailedProxyConnectionsUnexpectedRcvAckOwnLevelMom	CounterBasedGauge64,
		divertFailedProxyConnectionsUnexpectedRcvAckOwnLevelMax	CounterBasedGauge64
	}

divertFailedProxyConnectionsUnexpectedRcvAckOwnLevelName OBJECT-TYPE
	SYNTAX      DisplayString
	MAX-ACCESS  not-accessible
	STATUS      current
	DESCRIPTION
	"Table entry display string for divertFailedProxyConnectionsUnexpectedRcvAckOwn"
	::={divertFailedProxyConnectionsUnexpectedRcvAckOwnLevelEntry 1}

divertFailedProxyConnectionsUnexpectedRcvAckOwnLevelVal OBJECT-TYPE
	SYNTAX	 Counter64
	MAX-ACCESS  read-only
	STATUS      current
	DESCRIPTION
	"Table entry attribute for divertFailedProxyConnectionsUnexpectedRcvAckOwn"
	::={divertFailedProxyConnectionsUnexpectedRcvAckOwnLevelEntry 2}

divertFailedProxyConnectionsUnexpectedRcvAckOwnLevelMom OBJECT-TYPE
	SYNTAX	 CounterBasedGauge64
	MAX-ACCESS  read-only
	STATUS      current
	DESCRIPTION
	"Table entry attribute for divertFailedProxyConnectionsUnexpectedRcvAckOwn"
	::={divertFailedProxyConnectionsUnexpectedRcvAckOwnLevelEntry 3}

divertFailedProxyConnectionsUnexpectedRcvAckOwnLevelMax OBJECT-TYPE
	SYNTAX	 CounterBasedGauge64
	MAX-ACCESS  read-only
	STATUS      current
	DESCRIPTION
	"Table entry attribute for divertFailedProxyConnectionsUnexpectedRcvAckOwn"
	::={divertFailedProxyConnectionsUnexpectedRcvAckOwnLevelEntry 4}


divertDroppedPacketsConnection	OBJECT IDENTIFIER ::={divert 64}

divertDroppedPacketsConnectionVal	OBJECT-TYPE
	SYNTAX	 Counter64
	MAX-ACCESS read-only
	STATUS current
	DESCRIPTION "Dropped packets (connection dropped)"

	::={divertDroppedPacketsConnection 1}

divertDroppedPacketsConnectionMom	OBJECT-TYPE
	SYNTAX	 CounterBasedGauge64
	MAX-ACCESS read-only
	STATUS current
	DESCRIPTION "Dropped packets (connection dropped)"

	::={divertDroppedPacketsConnection 2}

divertDroppedPacketsConnectionMax	OBJECT-TYPE
	SYNTAX	 CounterBasedGauge64
	MAX-ACCESS read-only
	STATUS current
	DESCRIPTION "Dropped packets (connection dropped)"

	::={divertDroppedPacketsConnection 3}

divertDroppedPacketsConnectionLevelTable OBJECT-TYPE
	SYNTAX      SEQUENCE OF DivertDroppedPacketsConnectionLevelEntry
	MAX-ACCESS  not-accessible
	STATUS      current
	DESCRIPTION
	"Table for divertDroppedPacketsConnection"
	::={divertDroppedPacketsConnection 4}

divertDroppedPacketsConnectionLevelEntry OBJECT-TYPE
	SYNTAX      DivertDroppedPacketsConnectionLevelEntry
	MAX-ACCESS  not-accessible
	STATUS      current
	DESCRIPTION
	"Table entry for divertDroppedPacketsConnection"
	INDEX { divertDroppedPacketsConnectionLevelName }
	::={divertDroppedPacketsConnectionLevelTable 1}

DivertDroppedPacketsConnectionLevelEntry ::=
	SEQUENCE {
		divertDroppedPacketsConnectionLevelName	DisplayString,
		divertDroppedPacketsConnectionLevelVal	Counter64,
		divertDroppedPacketsConnectionLevelMom	CounterBasedGauge64,
		divertDroppedPacketsConnectionLevelMax	CounterBasedGauge64
	}

divertDroppedPacketsConnectionLevelName OBJECT-TYPE
	SYNTAX      DisplayString
	MAX-ACCESS  not-accessible
	STATUS      current
	DESCRIPTION
	"Table entry display string for divertDroppedPacketsConnection"
	::={divertDroppedPacketsConnectionLevelEntry 1}

divertDroppedPacketsConnectionLevelVal OBJECT-TYPE
	SYNTAX	 Counter64
	MAX-ACCESS  read-only
	STATUS      current
	DESCRIPTION
	"Table entry attribute for divertDroppedPacketsConnection"
	::={divertDroppedPacketsConnectionLevelEntry 2}

divertDroppedPacketsConnectionLevelMom OBJECT-TYPE
	SYNTAX	 CounterBasedGauge64
	MAX-ACCESS  read-only
	STATUS      current
	DESCRIPTION
	"Table entry attribute for divertDroppedPacketsConnection"
	::={divertDroppedPacketsConnectionLevelEntry 3}

divertDroppedPacketsConnectionLevelMax OBJECT-TYPE
	SYNTAX	 CounterBasedGauge64
	MAX-ACCESS  read-only
	STATUS      current
	DESCRIPTION
	"Table entry attribute for divertDroppedPacketsConnection"
	::={divertDroppedPacketsConnectionLevelEntry 4}


divertDroppedPacketsIpv6	OBJECT IDENTIFIER ::={divert 65}

divertDroppedPacketsIpv6Val	OBJECT-TYPE
	SYNTAX	 Counter64
	MAX-ACCESS read-only
	STATUS current
	DESCRIPTION "Dropped packets (IPv6 disabled)"

	::={divertDroppedPacketsIpv6 1}

divertDroppedPacketsIpv6Mom	OBJECT-TYPE
	SYNTAX	 CounterBasedGauge64
	MAX-ACCESS read-only
	STATUS current
	DESCRIPTION "Dropped packets (IPv6 disabled)"

	::={divertDroppedPacketsIpv6 2}

divertDroppedPacketsIpv6Max	OBJECT-TYPE
	SYNTAX	 CounterBasedGauge64
	MAX-ACCESS read-only
	STATUS current
	DESCRIPTION "Dropped packets (IPv6 disabled)"

	::={divertDroppedPacketsIpv6 3}

divertDroppedPacketsIpv6LevelTable OBJECT-TYPE
	SYNTAX      SEQUENCE OF DivertDroppedPacketsIpv6LevelEntry
	MAX-ACCESS  not-accessible
	STATUS      current
	DESCRIPTION
	"Table for divertDroppedPacketsIpv6"
	::={divertDroppedPacketsIpv6 4}

divertDroppedPacketsIpv6LevelEntry OBJECT-TYPE
	SYNTAX      DivertDroppedPacketsIpv6LevelEntry
	MAX-ACCESS  not-accessible
	STATUS      current
	DESCRIPTION
	"Table entry for divertDroppedPacketsIpv6"
	INDEX { divertDroppedPacketsIpv6LevelName }
	::={divertDroppedPacketsIpv6LevelTable 1}

DivertDroppedPacketsIpv6LevelEntry ::=
	SEQUENCE {
		divertDroppedPacketsIpv6LevelName	DisplayString,
		divertDroppedPacketsIpv6LevelVal	Counter64,
		divertDroppedPacketsIpv6LevelMom	CounterBasedGauge64,
		divertDroppedPacketsIpv6LevelMax	CounterBasedGauge64
	}

divertDroppedPacketsIpv6LevelName OBJECT-TYPE
	SYNTAX      DisplayString
	MAX-ACCESS  not-accessible
	STATUS      current
	DESCRIPTION
	"Table entry display string for divertDroppedPacketsIpv6"
	::={divertDroppedPacketsIpv6LevelEntry 1}

divertDroppedPacketsIpv6LevelVal OBJECT-TYPE
	SYNTAX	 Counter64
	MAX-ACCESS  read-only
	STATUS      current
	DESCRIPTION
	"Table entry attribute for divertDroppedPacketsIpv6"
	::={divertDroppedPacketsIpv6LevelEntry 2}

divertDroppedPacketsIpv6LevelMom OBJECT-TYPE
	SYNTAX	 CounterBasedGauge64
	MAX-ACCESS  read-only
	STATUS      current
	DESCRIPTION
	"Table entry attribute for divertDroppedPacketsIpv6"
	::={divertDroppedPacketsIpv6LevelEntry 3}

divertDroppedPacketsIpv6LevelMax OBJECT-TYPE
	SYNTAX	 CounterBasedGauge64
	MAX-ACCESS  read-only
	STATUS      current
	DESCRIPTION
	"Table entry attribute for divertDroppedPacketsIpv6"
	::={divertDroppedPacketsIpv6LevelEntry 4}


divertDroppedPacketsTunnel	OBJECT IDENTIFIER ::={divert 66}

divertDroppedPacketsTunnelVal	OBJECT-TYPE
	SYNTAX	 Counter64
	MAX-ACCESS read-only
	STATUS current
	DESCRIPTION "Dropped packets (received on real channel, connsync tunnel active)"

	::={divertDroppedPacketsTunnel 1}

divertDroppedPacketsTunnelMom	OBJECT-TYPE
	SYNTAX	 CounterBasedGauge64
	MAX-ACCESS read-only
	STATUS current
	DESCRIPTION "Dropped packets (received on real channel, connsync tunnel active)"

	::={divertDroppedPacketsTunnel 2}

divertDroppedPacketsTunnelMax	OBJECT-TYPE
	SYNTAX	 CounterBasedGauge64
	MAX-ACCESS read-only
	STATUS current
	DESCRIPTION "Dropped packets (received on real channel, connsync tunnel active)"

	::={divertDroppedPacketsTunnel 3}

divertDroppedPacketsTunnelLevelTable OBJECT-TYPE
	SYNTAX      SEQUENCE OF DivertDroppedPacketsTunnelLevelEntry
	MAX-ACCESS  not-accessible
	STATUS      current
	DESCRIPTION
	"Table for divertDroppedPacketsTunnel"
	::={divertDroppedPacketsTunnel 4}

divertDroppedPacketsTunnelLevelEntry OBJECT-TYPE
	SYNTAX      DivertDroppedPacketsTunnelLevelEntry
	MAX-ACCESS  not-accessible
	STATUS      current
	DESCRIPTION
	"Table entry for divertDroppedPacketsTunnel"
	INDEX { divertDroppedPacketsTunnelLevelName }
	::={divertDroppedPacketsTunnelLevelTable 1}

DivertDroppedPacketsTunnelLevelEntry ::=
	SEQUENCE {
		divertDroppedPacketsTunnelLevelName	DisplayString,
		divertDroppedPacketsTunnelLevelVal	Counter64,
		divertDroppedPacketsTunnelLevelMom	CounterBasedGauge64,
		divertDroppedPacketsTunnelLevelMax	CounterBasedGauge64
	}

divertDroppedPacketsTunnelLevelName OBJECT-TYPE
	SYNTAX      DisplayString
	MAX-ACCESS  not-accessible
	STATUS      current
	DESCRIPTION
	"Table entry display string for divertDroppedPacketsTunnel"
	::={divertDroppedPacketsTunnelLevelEntry 1}

divertDroppedPacketsTunnelLevelVal OBJECT-TYPE
	SYNTAX	 Counter64
	MAX-ACCESS  read-only
	STATUS      current
	DESCRIPTION
	"Table entry attribute for divertDroppedPacketsTunnel"
	::={divertDroppedPacketsTunnelLevelEntry 2}

divertDroppedPacketsTunnelLevelMom OBJECT-TYPE
	SYNTAX	 CounterBasedGauge64
	MAX-ACCESS  read-only
	STATUS      current
	DESCRIPTION
	"Table entry attribute for divertDroppedPacketsTunnel"
	::={divertDroppedPacketsTunnelLevelEntry 3}

divertDroppedPacketsTunnelLevelMax OBJECT-TYPE
	SYNTAX	 CounterBasedGauge64
	MAX-ACCESS  read-only
	STATUS      current
	DESCRIPTION
	"Table entry attribute for divertDroppedPacketsTunnel"
	::={divertDroppedPacketsTunnelLevelEntry 4}


divertDroppedPacketsNorule	OBJECT IDENTIFIER ::={divert 67}

divertDroppedPacketsNoruleVal	OBJECT-TYPE
	SYNTAX	 Counter64
	MAX-ACCESS read-only
	STATUS current
	DESCRIPTION "Dropped packets (No matching divert rule)"

	::={divertDroppedPacketsNorule 1}

divertDroppedPacketsNoruleMom	OBJECT-TYPE
	SYNTAX	 CounterBasedGauge64
	MAX-ACCESS read-only
	STATUS current
	DESCRIPTION "Dropped packets (No matching divert rule)"

	::={divertDroppedPacketsNorule 2}

divertDroppedPacketsNoruleMax	OBJECT-TYPE
	SYNTAX	 CounterBasedGauge64
	MAX-ACCESS read-only
	STATUS current
	DESCRIPTION "Dropped packets (No matching divert rule)"

	::={divertDroppedPacketsNorule 3}

divertDroppedPacketsNoruleLevelTable OBJECT-TYPE
	SYNTAX      SEQUENCE OF DivertDroppedPacketsNoruleLevelEntry
	MAX-ACCESS  not-accessible
	STATUS      current
	DESCRIPTION
	"Table for divertDroppedPacketsNorule"
	::={divertDroppedPacketsNorule 4}

divertDroppedPacketsNoruleLevelEntry OBJECT-TYPE
	SYNTAX      DivertDroppedPacketsNoruleLevelEntry
	MAX-ACCESS  not-accessible
	STATUS      current
	DESCRIPTION
	"Table entry for divertDroppedPacketsNorule"
	INDEX { divertDroppedPacketsNoruleLevelName }
	::={divertDroppedPacketsNoruleLevelTable 1}

DivertDroppedPacketsNoruleLevelEntry ::=
	SEQUENCE {
		divertDroppedPacketsNoruleLevelName	DisplayString,
		divertDroppedPacketsNoruleLevelVal	Counter64,
		divertDroppedPacketsNoruleLevelMom	CounterBasedGauge64,
		divertDroppedPacketsNoruleLevelMax	CounterBasedGauge64
	}

divertDroppedPacketsNoruleLevelName OBJECT-TYPE
	SYNTAX      DisplayString
	MAX-ACCESS  not-accessible
	STATUS      current
	DESCRIPTION
	"Table entry display string for divertDroppedPacketsNorule"
	::={divertDroppedPacketsNoruleLevelEntry 1}

divertDroppedPacketsNoruleLevelVal OBJECT-TYPE
	SYNTAX	 Counter64
	MAX-ACCESS  read-only
	STATUS      current
	DESCRIPTION
	"Table entry attribute for divertDroppedPacketsNorule"
	::={divertDroppedPacketsNoruleLevelEntry 2}

divertDroppedPacketsNoruleLevelMom OBJECT-TYPE
	SYNTAX	 CounterBasedGauge64
	MAX-ACCESS  read-only
	STATUS      current
	DESCRIPTION
	"Table entry attribute for divertDroppedPacketsNorule"
	::={divertDroppedPacketsNoruleLevelEntry 3}

divertDroppedPacketsNoruleLevelMax OBJECT-TYPE
	SYNTAX	 CounterBasedGauge64
	MAX-ACCESS  read-only
	STATUS      current
	DESCRIPTION
	"Table entry attribute for divertDroppedPacketsNorule"
	::={divertDroppedPacketsNoruleLevelEntry 4}


divertDroppedPacketsFailure	OBJECT IDENTIFIER ::={divert 68}

divertDroppedPacketsFailureVal	OBJECT-TYPE
	SYNTAX	 Counter64
	MAX-ACCESS read-only
	STATUS current
	DESCRIPTION "Dropped packets (unspecificed error)"

	::={divertDroppedPacketsFailure 1}

divertDroppedPacketsFailureMom	OBJECT-TYPE
	SYNTAX	 CounterBasedGauge64
	MAX-ACCESS read-only
	STATUS current
	DESCRIPTION "Dropped packets (unspecificed error)"

	::={divertDroppedPacketsFailure 2}

divertDroppedPacketsFailureMax	OBJECT-TYPE
	SYNTAX	 CounterBasedGauge64
	MAX-ACCESS read-only
	STATUS current
	DESCRIPTION "Dropped packets (unspecificed error)"

	::={divertDroppedPacketsFailure 3}

divertDroppedPacketsFailureLevelTable OBJECT-TYPE
	SYNTAX      SEQUENCE OF DivertDroppedPacketsFailureLevelEntry
	MAX-ACCESS  not-accessible
	STATUS      current
	DESCRIPTION
	"Table for divertDroppedPacketsFailure"
	::={divertDroppedPacketsFailure 4}

divertDroppedPacketsFailureLevelEntry OBJECT-TYPE
	SYNTAX      DivertDroppedPacketsFailureLevelEntry
	MAX-ACCESS  not-accessible
	STATUS      current
	DESCRIPTION
	"Table entry for divertDroppedPacketsFailure"
	INDEX { divertDroppedPacketsFailureLevelName }
	::={divertDroppedPacketsFailureLevelTable 1}

DivertDroppedPacketsFailureLevelEntry ::=
	SEQUENCE {
		divertDroppedPacketsFailureLevelName	DisplayString,
		divertDroppedPacketsFailureLevelVal	Counter64,
		divertDroppedPacketsFailureLevelMom	CounterBasedGauge64,
		divertDroppedPacketsFailureLevelMax	CounterBasedGauge64
	}

divertDroppedPacketsFailureLevelName OBJECT-TYPE
	SYNTAX      DisplayString
	MAX-ACCESS  not-accessible
	STATUS      current
	DESCRIPTION
	"Table entry display string for divertDroppedPacketsFailure"
	::={divertDroppedPacketsFailureLevelEntry 1}

divertDroppedPacketsFailureLevelVal OBJECT-TYPE
	SYNTAX	 Counter64
	MAX-ACCESS  read-only
	STATUS      current
	DESCRIPTION
	"Table entry attribute for divertDroppedPacketsFailure"
	::={divertDroppedPacketsFailureLevelEntry 2}

divertDroppedPacketsFailureLevelMom OBJECT-TYPE
	SYNTAX	 CounterBasedGauge64
	MAX-ACCESS  read-only
	STATUS      current
	DESCRIPTION
	"Table entry attribute for divertDroppedPacketsFailure"
	::={divertDroppedPacketsFailureLevelEntry 3}

divertDroppedPacketsFailureLevelMax OBJECT-TYPE
	SYNTAX	 CounterBasedGauge64
	MAX-ACCESS  read-only
	STATUS      current
	DESCRIPTION
	"Table entry attribute for divertDroppedPacketsFailure"
	::={divertDroppedPacketsFailureLevelEntry 4}


divertProxyAsymNotifyRcvErrorEstOutOfHosts	OBJECT IDENTIFIER ::={divert 69}

divertProxyAsymNotifyRcvErrorEstOutOfHostsVal	OBJECT-TYPE
	SYNTAX	 Counter64
	MAX-ACCESS read-only
	STATUS current
	DESCRIPTION "Proxy asym notifications receive error (host allocation failure)"

	::={divertProxyAsymNotifyRcvErrorEstOutOfHosts 1}

divertProxyAsymNotifyRcvErrorEstOutOfHostsMom	OBJECT-TYPE
	SYNTAX	 CounterBasedGauge64
	MAX-ACCESS read-only
	STATUS current
	DESCRIPTION "Proxy asym notifications receive error (host allocation failure)"

	::={divertProxyAsymNotifyRcvErrorEstOutOfHosts 2}

divertProxyAsymNotifyRcvErrorEstOutOfHostsMax	OBJECT-TYPE
	SYNTAX	 CounterBasedGauge64
	MAX-ACCESS read-only
	STATUS current
	DESCRIPTION "Proxy asym notifications receive error (host allocation failure)"

	::={divertProxyAsymNotifyRcvErrorEstOutOfHosts 3}

divertProxyAsymNotifyRcvErrorEstOutOfHostsLevelTable OBJECT-TYPE
	SYNTAX      SEQUENCE OF DivertProxyAsymNotifyRcvErrorEstOutOfHostsLevelEntry
	MAX-ACCESS  not-accessible
	STATUS      current
	DESCRIPTION
	"Table for divertProxyAsymNotifyRcvErrorEstOutOfHosts"
	::={divertProxyAsymNotifyRcvErrorEstOutOfHosts 4}

divertProxyAsymNotifyRcvErrorEstOutOfHostsLevelEntry OBJECT-TYPE
	SYNTAX      DivertProxyAsymNotifyRcvErrorEstOutOfHostsLevelEntry
	MAX-ACCESS  not-accessible
	STATUS      current
	DESCRIPTION
	"Table entry for divertProxyAsymNotifyRcvErrorEstOutOfHosts"
	INDEX { divertProxyAsymNotifyRcvErrorEstOutOfHostsLevelName }
	::={divertProxyAsymNotifyRcvErrorEstOutOfHostsLevelTable 1}

DivertProxyAsymNotifyRcvErrorEstOutOfHostsLevelEntry ::=
	SEQUENCE {
		divertProxyAsymNotifyRcvErrorEstOutOfHostsLevelName	DisplayString,
		divertProxyAsymNotifyRcvErrorEstOutOfHostsLevelVal	Counter64,
		divertProxyAsymNotifyRcvErrorEstOutOfHostsLevelMom	CounterBasedGauge64,
		divertProxyAsymNotifyRcvErrorEstOutOfHostsLevelMax	CounterBasedGauge64
	}

divertProxyAsymNotifyRcvErrorEstOutOfHostsLevelName OBJECT-TYPE
	SYNTAX      DisplayString
	MAX-ACCESS  not-accessible
	STATUS      current
	DESCRIPTION
	"Table entry display string for divertProxyAsymNotifyRcvErrorEstOutOfHosts"
	::={divertProxyAsymNotifyRcvErrorEstOutOfHostsLevelEntry 1}

divertProxyAsymNotifyRcvErrorEstOutOfHostsLevelVal OBJECT-TYPE
	SYNTAX	 Counter64
	MAX-ACCESS  read-only
	STATUS      current
	DESCRIPTION
	"Table entry attribute for divertProxyAsymNotifyRcvErrorEstOutOfHosts"
	::={divertProxyAsymNotifyRcvErrorEstOutOfHostsLevelEntry 2}

divertProxyAsymNotifyRcvErrorEstOutOfHostsLevelMom OBJECT-TYPE
	SYNTAX	 CounterBasedGauge64
	MAX-ACCESS  read-only
	STATUS      current
	DESCRIPTION
	"Table entry attribute for divertProxyAsymNotifyRcvErrorEstOutOfHosts"
	::={divertProxyAsymNotifyRcvErrorEstOutOfHostsLevelEntry 3}

divertProxyAsymNotifyRcvErrorEstOutOfHostsLevelMax OBJECT-TYPE
	SYNTAX	 CounterBasedGauge64
	MAX-ACCESS  read-only
	STATUS      current
	DESCRIPTION
	"Table entry attribute for divertProxyAsymNotifyRcvErrorEstOutOfHosts"
	::={divertProxyAsymNotifyRcvErrorEstOutOfHostsLevelEntry 4}


divertFailedProxyConnectionsInjectFailed	OBJECT IDENTIFIER ::={divert 70}

divertFailedProxyConnectionsInjectFailedVal	OBJECT-TYPE
	SYNTAX	 Counter64
	MAX-ACCESS read-only
	STATUS current
	DESCRIPTION "Proxy connections failed (inject failed)"

	::={divertFailedProxyConnectionsInjectFailed 1}

divertFailedProxyConnectionsInjectFailedMom	OBJECT-TYPE
	SYNTAX	 CounterBasedGauge64
	MAX-ACCESS read-only
	STATUS current
	DESCRIPTION "Proxy connections failed (inject failed)"

	::={divertFailedProxyConnectionsInjectFailed 2}

divertFailedProxyConnectionsInjectFailedMax	OBJECT-TYPE
	SYNTAX	 CounterBasedGauge64
	MAX-ACCESS read-only
	STATUS current
	DESCRIPTION "Proxy connections failed (inject failed)"

	::={divertFailedProxyConnectionsInjectFailed 3}

divertFailedProxyConnectionsInjectFailedLevelTable OBJECT-TYPE
	SYNTAX      SEQUENCE OF DivertFailedProxyConnectionsInjectFailedLevelEntry
	MAX-ACCESS  not-accessible
	STATUS      current
	DESCRIPTION
	"Table for divertFailedProxyConnectionsInjectFailed"
	::={divertFailedProxyConnectionsInjectFailed 4}

divertFailedProxyConnectionsInjectFailedLevelEntry OBJECT-TYPE
	SYNTAX      DivertFailedProxyConnectionsInjectFailedLevelEntry
	MAX-ACCESS  not-accessible
	STATUS      current
	DESCRIPTION
	"Table entry for divertFailedProxyConnectionsInjectFailed"
	INDEX { divertFailedProxyConnectionsInjectFailedLevelName }
	::={divertFailedProxyConnectionsInjectFailedLevelTable 1}

DivertFailedProxyConnectionsInjectFailedLevelEntry ::=
	SEQUENCE {
		divertFailedProxyConnectionsInjectFailedLevelName	DisplayString,
		divertFailedProxyConnectionsInjectFailedLevelVal	Counter64,
		divertFailedProxyConnectionsInjectFailedLevelMom	CounterBasedGauge64,
		divertFailedProxyConnectionsInjectFailedLevelMax	CounterBasedGauge64
	}

divertFailedProxyConnectionsInjectFailedLevelName OBJECT-TYPE
	SYNTAX      DisplayString
	MAX-ACCESS  not-accessible
	STATUS      current
	DESCRIPTION
	"Table entry display string for divertFailedProxyConnectionsInjectFailed"
	::={divertFailedProxyConnectionsInjectFailedLevelEntry 1}

divertFailedProxyConnectionsInjectFailedLevelVal OBJECT-TYPE
	SYNTAX	 Counter64
	MAX-ACCESS  read-only
	STATUS      current
	DESCRIPTION
	"Table entry attribute for divertFailedProxyConnectionsInjectFailed"
	::={divertFailedProxyConnectionsInjectFailedLevelEntry 2}

divertFailedProxyConnectionsInjectFailedLevelMom OBJECT-TYPE
	SYNTAX	 CounterBasedGauge64
	MAX-ACCESS  read-only
	STATUS      current
	DESCRIPTION
	"Table entry attribute for divertFailedProxyConnectionsInjectFailed"
	::={divertFailedProxyConnectionsInjectFailedLevelEntry 3}

divertFailedProxyConnectionsInjectFailedLevelMax OBJECT-TYPE
	SYNTAX	 CounterBasedGauge64
	MAX-ACCESS  read-only
	STATUS      current
	DESCRIPTION
	"Table entry attribute for divertFailedProxyConnectionsInjectFailed"
	::={divertFailedProxyConnectionsInjectFailedLevelEntry 4}


divertIgnoredProxyConnections	OBJECT IDENTIFIER ::={divert 71}

divertIgnoredProxyConnectionsVal	OBJECT-TYPE
	SYNTAX	 Counter64
	MAX-ACCESS read-only
	STATUS current
	DESCRIPTION "Proxy connections ignored"

	::={divertIgnoredProxyConnections 1}

divertIgnoredProxyConnectionsMom	OBJECT-TYPE
	SYNTAX	 CounterBasedGauge64
	MAX-ACCESS read-only
	STATUS current
	DESCRIPTION "Proxy connections ignored"

	::={divertIgnoredProxyConnections 2}

divertIgnoredProxyConnectionsMax	OBJECT-TYPE
	SYNTAX	 CounterBasedGauge64
	MAX-ACCESS read-only
	STATUS current
	DESCRIPTION "Proxy connections ignored"

	::={divertIgnoredProxyConnections 3}

divertIgnoredProxyConnectionsLevelTable OBJECT-TYPE
	SYNTAX      SEQUENCE OF DivertIgnoredProxyConnectionsLevelEntry
	MAX-ACCESS  not-accessible
	STATUS      current
	DESCRIPTION
	"Table for divertIgnoredProxyConnections"
	::={divertIgnoredProxyConnections 4}

divertIgnoredProxyConnectionsLevelEntry OBJECT-TYPE
	SYNTAX      DivertIgnoredProxyConnectionsLevelEntry
	MAX-ACCESS  not-accessible
	STATUS      current
	DESCRIPTION
	"Table entry for divertIgnoredProxyConnections"
	INDEX { divertIgnoredProxyConnectionsLevelName }
	::={divertIgnoredProxyConnectionsLevelTable 1}

DivertIgnoredProxyConnectionsLevelEntry ::=
	SEQUENCE {
		divertIgnoredProxyConnectionsLevelName	DisplayString,
		divertIgnoredProxyConnectionsLevelVal	Counter64,
		divertIgnoredProxyConnectionsLevelMom	CounterBasedGauge64,
		divertIgnoredProxyConnectionsLevelMax	CounterBasedGauge64
	}

divertIgnoredProxyConnectionsLevelName OBJECT-TYPE
	SYNTAX      DisplayString
	MAX-ACCESS  not-accessible
	STATUS      current
	DESCRIPTION
	"Table entry display string for divertIgnoredProxyConnections"
	::={divertIgnoredProxyConnectionsLevelEntry 1}

divertIgnoredProxyConnectionsLevelVal OBJECT-TYPE
	SYNTAX	 Counter64
	MAX-ACCESS  read-only
	STATUS      current
	DESCRIPTION
	"Table entry attribute for divertIgnoredProxyConnections"
	::={divertIgnoredProxyConnectionsLevelEntry 2}

divertIgnoredProxyConnectionsLevelMom OBJECT-TYPE
	SYNTAX	 CounterBasedGauge64
	MAX-ACCESS  read-only
	STATUS      current
	DESCRIPTION
	"Table entry attribute for divertIgnoredProxyConnections"
	::={divertIgnoredProxyConnectionsLevelEntry 3}

divertIgnoredProxyConnectionsLevelMax OBJECT-TYPE
	SYNTAX	 CounterBasedGauge64
	MAX-ACCESS  read-only
	STATUS      current
	DESCRIPTION
	"Table entry attribute for divertIgnoredProxyConnections"
	::={divertIgnoredProxyConnectionsLevelEntry 4}


divertIgnoredProxyConnectionsLateNewRuleset	OBJECT IDENTIFIER ::={divert 72}

divertIgnoredProxyConnectionsLateNewRulesetVal	OBJECT-TYPE
	SYNTAX	 Counter64
	MAX-ACCESS read-only
	STATUS current
	DESCRIPTION "Proxy connections ignored (too late matching due to new ruleset)"

	::={divertIgnoredProxyConnectionsLateNewRuleset 1}

divertIgnoredProxyConnectionsLateNewRulesetMom	OBJECT-TYPE
	SYNTAX	 CounterBasedGauge64
	MAX-ACCESS read-only
	STATUS current
	DESCRIPTION "Proxy connections ignored (too late matching due to new ruleset)"

	::={divertIgnoredProxyConnectionsLateNewRuleset 2}

divertIgnoredProxyConnectionsLateNewRulesetMax	OBJECT-TYPE
	SYNTAX	 CounterBasedGauge64
	MAX-ACCESS read-only
	STATUS current
	DESCRIPTION "Proxy connections ignored (too late matching due to new ruleset)"

	::={divertIgnoredProxyConnectionsLateNewRuleset 3}

divertIgnoredProxyConnectionsLateNewRulesetLevelTable OBJECT-TYPE
	SYNTAX      SEQUENCE OF DivertIgnoredProxyConnectionsLateNewRulesetLevelEntry
	MAX-ACCESS  not-accessible
	STATUS      current
	DESCRIPTION
	"Table for divertIgnoredProxyConnectionsLateNewRuleset"
	::={divertIgnoredProxyConnectionsLateNewRuleset 4}

divertIgnoredProxyConnectionsLateNewRulesetLevelEntry OBJECT-TYPE
	SYNTAX      DivertIgnoredProxyConnectionsLateNewRulesetLevelEntry
	MAX-ACCESS  not-accessible
	STATUS      current
	DESCRIPTION
	"Table entry for divertIgnoredProxyConnectionsLateNewRuleset"
	INDEX { divertIgnoredProxyConnectionsLateNewRulesetLevelName }
	::={divertIgnoredProxyConnectionsLateNewRulesetLevelTable 1}

DivertIgnoredProxyConnectionsLateNewRulesetLevelEntry ::=
	SEQUENCE {
		divertIgnoredProxyConnectionsLateNewRulesetLevelName	DisplayString,
		divertIgnoredProxyConnectionsLateNewRulesetLevelVal	Counter64,
		divertIgnoredProxyConnectionsLateNewRulesetLevelMom	CounterBasedGauge64,
		divertIgnoredProxyConnectionsLateNewRulesetLevelMax	CounterBasedGauge64
	}

divertIgnoredProxyConnectionsLateNewRulesetLevelName OBJECT-TYPE
	SYNTAX      DisplayString
	MAX-ACCESS  not-accessible
	STATUS      current
	DESCRIPTION
	"Table entry display string for divertIgnoredProxyConnectionsLateNewRuleset"
	::={divertIgnoredProxyConnectionsLateNewRulesetLevelEntry 1}

divertIgnoredProxyConnectionsLateNewRulesetLevelVal OBJECT-TYPE
	SYNTAX	 Counter64
	MAX-ACCESS  read-only
	STATUS      current
	DESCRIPTION
	"Table entry attribute for divertIgnoredProxyConnectionsLateNewRuleset"
	::={divertIgnoredProxyConnectionsLateNewRulesetLevelEntry 2}

divertIgnoredProxyConnectionsLateNewRulesetLevelMom OBJECT-TYPE
	SYNTAX	 CounterBasedGauge64
	MAX-ACCESS  read-only
	STATUS      current
	DESCRIPTION
	"Table entry attribute for divertIgnoredProxyConnectionsLateNewRuleset"
	::={divertIgnoredProxyConnectionsLateNewRulesetLevelEntry 3}

divertIgnoredProxyConnectionsLateNewRulesetLevelMax OBJECT-TYPE
	SYNTAX	 CounterBasedGauge64
	MAX-ACCESS  read-only
	STATUS      current
	DESCRIPTION
	"Table entry attribute for divertIgnoredProxyConnectionsLateNewRuleset"
	::={divertIgnoredProxyConnectionsLateNewRulesetLevelEntry 4}


teredo	OBJECT IDENTIFIER ::={sysdiag 128}

teredoPackets	OBJECT IDENTIFIER ::={teredo 2}

teredoPacketsVal	OBJECT-TYPE
	SYNTAX	 Counter64
	MAX-ACCESS read-only
	STATUS current
	DESCRIPTION "RX packets"

	::={teredoPackets 1}

teredoPacketsMom	OBJECT-TYPE
	SYNTAX	 CounterBasedGauge64
	MAX-ACCESS read-only
	STATUS current
	DESCRIPTION "RX packets"

	::={teredoPackets 2}

teredoPacketsMax	OBJECT-TYPE
	SYNTAX	 CounterBasedGauge64
	MAX-ACCESS read-only
	STATUS current
	DESCRIPTION "RX packets"

	::={teredoPackets 3}

teredoPacketsLevelTable OBJECT-TYPE
	SYNTAX      SEQUENCE OF TeredoPacketsLevelEntry
	MAX-ACCESS  not-accessible
	STATUS      current
	DESCRIPTION
	"Table for teredoPackets"
	::={teredoPackets 4}

teredoPacketsLevelEntry OBJECT-TYPE
	SYNTAX      TeredoPacketsLevelEntry
	MAX-ACCESS  not-accessible
	STATUS      current
	DESCRIPTION
	"Table entry for teredoPackets"
	INDEX { teredoPacketsLevelName }
	::={teredoPacketsLevelTable 1}

TeredoPacketsLevelEntry ::=
	SEQUENCE {
		teredoPacketsLevelName	DisplayString,
		teredoPacketsLevelVal	Counter64,
		teredoPacketsLevelMom	CounterBasedGauge64,
		teredoPacketsLevelMax	CounterBasedGauge64
	}

teredoPacketsLevelName OBJECT-TYPE
	SYNTAX      DisplayString
	MAX-ACCESS  not-accessible
	STATUS      current
	DESCRIPTION
	"Table entry display string for teredoPackets"
	::={teredoPacketsLevelEntry 1}

teredoPacketsLevelVal OBJECT-TYPE
	SYNTAX	 Counter64
	MAX-ACCESS  read-only
	STATUS      current
	DESCRIPTION
	"Table entry attribute for teredoPackets"
	::={teredoPacketsLevelEntry 2}

teredoPacketsLevelMom OBJECT-TYPE
	SYNTAX	 CounterBasedGauge64
	MAX-ACCESS  read-only
	STATUS      current
	DESCRIPTION
	"Table entry attribute for teredoPackets"
	::={teredoPacketsLevelEntry 3}

teredoPacketsLevelMax OBJECT-TYPE
	SYNTAX	 CounterBasedGauge64
	MAX-ACCESS  read-only
	STATUS      current
	DESCRIPTION
	"Table entry attribute for teredoPackets"
	::={teredoPacketsLevelEntry 4}


teredoBytes	OBJECT IDENTIFIER ::={teredo 3}

teredoBytesVal	OBJECT-TYPE
	SYNTAX	 Counter64
	MAX-ACCESS read-only
	STATUS current
	DESCRIPTION "RX data"

	::={teredoBytes 1}

teredoBytesMom	OBJECT-TYPE
	SYNTAX	 CounterBasedGauge64
	MAX-ACCESS read-only
	STATUS current
	DESCRIPTION "RX data"

	::={teredoBytes 2}

teredoBytesMax	OBJECT-TYPE
	SYNTAX	 CounterBasedGauge64
	MAX-ACCESS read-only
	STATUS current
	DESCRIPTION "RX data"

	::={teredoBytes 3}

teredoBytesLevelTable OBJECT-TYPE
	SYNTAX      SEQUENCE OF TeredoBytesLevelEntry
	MAX-ACCESS  not-accessible
	STATUS      current
	DESCRIPTION
	"Table for teredoBytes"
	::={teredoBytes 4}

teredoBytesLevelEntry OBJECT-TYPE
	SYNTAX      TeredoBytesLevelEntry
	MAX-ACCESS  not-accessible
	STATUS      current
	DESCRIPTION
	"Table entry for teredoBytes"
	INDEX { teredoBytesLevelName }
	::={teredoBytesLevelTable 1}

TeredoBytesLevelEntry ::=
	SEQUENCE {
		teredoBytesLevelName	DisplayString,
		teredoBytesLevelVal	Counter64,
		teredoBytesLevelMom	CounterBasedGauge64,
		teredoBytesLevelMax	CounterBasedGauge64
	}

teredoBytesLevelName OBJECT-TYPE
	SYNTAX      DisplayString
	MAX-ACCESS  not-accessible
	STATUS      current
	DESCRIPTION
	"Table entry display string for teredoBytes"
	::={teredoBytesLevelEntry 1}

teredoBytesLevelVal OBJECT-TYPE
	SYNTAX	 Counter64
	MAX-ACCESS  read-only
	STATUS      current
	DESCRIPTION
	"Table entry attribute for teredoBytes"
	::={teredoBytesLevelEntry 2}

teredoBytesLevelMom OBJECT-TYPE
	SYNTAX	 CounterBasedGauge64
	MAX-ACCESS  read-only
	STATUS      current
	DESCRIPTION
	"Table entry attribute for teredoBytes"
	::={teredoBytesLevelEntry 3}

teredoBytesLevelMax OBJECT-TYPE
	SYNTAX	 CounterBasedGauge64
	MAX-ACCESS  read-only
	STATUS      current
	DESCRIPTION
	"Table entry attribute for teredoBytes"
	::={teredoBytesLevelEntry 4}


teredoOrgHeaders	OBJECT IDENTIFIER ::={teredo 4}

teredoOrgHeadersVal	OBJECT-TYPE
	SYNTAX	 Counter64
	MAX-ACCESS read-only
	STATUS current
	DESCRIPTION "Origin indication headers"

	::={teredoOrgHeaders 1}

teredoOrgHeadersMom	OBJECT-TYPE
	SYNTAX	 CounterBasedGauge64
	MAX-ACCESS read-only
	STATUS current
	DESCRIPTION "Origin indication headers"

	::={teredoOrgHeaders 2}

teredoOrgHeadersMax	OBJECT-TYPE
	SYNTAX	 CounterBasedGauge64
	MAX-ACCESS read-only
	STATUS current
	DESCRIPTION "Origin indication headers"

	::={teredoOrgHeaders 3}

teredoOrgHeadersLevelTable OBJECT-TYPE
	SYNTAX      SEQUENCE OF TeredoOrgHeadersLevelEntry
	MAX-ACCESS  not-accessible
	STATUS      current
	DESCRIPTION
	"Table for teredoOrgHeaders"
	::={teredoOrgHeaders 4}

teredoOrgHeadersLevelEntry OBJECT-TYPE
	SYNTAX      TeredoOrgHeadersLevelEntry
	MAX-ACCESS  not-accessible
	STATUS      current
	DESCRIPTION
	"Table entry for teredoOrgHeaders"
	INDEX { teredoOrgHeadersLevelName }
	::={teredoOrgHeadersLevelTable 1}

TeredoOrgHeadersLevelEntry ::=
	SEQUENCE {
		teredoOrgHeadersLevelName	DisplayString,
		teredoOrgHeadersLevelVal	Counter64,
		teredoOrgHeadersLevelMom	CounterBasedGauge64,
		teredoOrgHeadersLevelMax	CounterBasedGauge64
	}

teredoOrgHeadersLevelName OBJECT-TYPE
	SYNTAX      DisplayString
	MAX-ACCESS  not-accessible
	STATUS      current
	DESCRIPTION
	"Table entry display string for teredoOrgHeaders"
	::={teredoOrgHeadersLevelEntry 1}

teredoOrgHeadersLevelVal OBJECT-TYPE
	SYNTAX	 Counter64
	MAX-ACCESS  read-only
	STATUS      current
	DESCRIPTION
	"Table entry attribute for teredoOrgHeaders"
	::={teredoOrgHeadersLevelEntry 2}

teredoOrgHeadersLevelMom OBJECT-TYPE
	SYNTAX	 CounterBasedGauge64
	MAX-ACCESS  read-only
	STATUS      current
	DESCRIPTION
	"Table entry attribute for teredoOrgHeaders"
	::={teredoOrgHeadersLevelEntry 3}

teredoOrgHeadersLevelMax OBJECT-TYPE
	SYNTAX	 CounterBasedGauge64
	MAX-ACCESS  read-only
	STATUS      current
	DESCRIPTION
	"Table entry attribute for teredoOrgHeaders"
	::={teredoOrgHeadersLevelEntry 4}


teredoAuthHeaders	OBJECT IDENTIFIER ::={teredo 5}

teredoAuthHeadersVal	OBJECT-TYPE
	SYNTAX	 Counter64
	MAX-ACCESS read-only
	STATUS current
	DESCRIPTION "Authentication headers"

	::={teredoAuthHeaders 1}

teredoAuthHeadersMom	OBJECT-TYPE
	SYNTAX	 CounterBasedGauge64
	MAX-ACCESS read-only
	STATUS current
	DESCRIPTION "Authentication headers"

	::={teredoAuthHeaders 2}

teredoAuthHeadersMax	OBJECT-TYPE
	SYNTAX	 CounterBasedGauge64
	MAX-ACCESS read-only
	STATUS current
	DESCRIPTION "Authentication headers"

	::={teredoAuthHeaders 3}

teredoAuthHeadersLevelTable OBJECT-TYPE
	SYNTAX      SEQUENCE OF TeredoAuthHeadersLevelEntry
	MAX-ACCESS  not-accessible
	STATUS      current
	DESCRIPTION
	"Table for teredoAuthHeaders"
	::={teredoAuthHeaders 4}

teredoAuthHeadersLevelEntry OBJECT-TYPE
	SYNTAX      TeredoAuthHeadersLevelEntry
	MAX-ACCESS  not-accessible
	STATUS      current
	DESCRIPTION
	"Table entry for teredoAuthHeaders"
	INDEX { teredoAuthHeadersLevelName }
	::={teredoAuthHeadersLevelTable 1}

TeredoAuthHeadersLevelEntry ::=
	SEQUENCE {
		teredoAuthHeadersLevelName	DisplayString,
		teredoAuthHeadersLevelVal	Counter64,
		teredoAuthHeadersLevelMom	CounterBasedGauge64,
		teredoAuthHeadersLevelMax	CounterBasedGauge64
	}

teredoAuthHeadersLevelName OBJECT-TYPE
	SYNTAX      DisplayString
	MAX-ACCESS  not-accessible
	STATUS      current
	DESCRIPTION
	"Table entry display string for teredoAuthHeaders"
	::={teredoAuthHeadersLevelEntry 1}

teredoAuthHeadersLevelVal OBJECT-TYPE
	SYNTAX	 Counter64
	MAX-ACCESS  read-only
	STATUS      current
	DESCRIPTION
	"Table entry attribute for teredoAuthHeaders"
	::={teredoAuthHeadersLevelEntry 2}

teredoAuthHeadersLevelMom OBJECT-TYPE
	SYNTAX	 CounterBasedGauge64
	MAX-ACCESS  read-only
	STATUS      current
	DESCRIPTION
	"Table entry attribute for teredoAuthHeaders"
	::={teredoAuthHeadersLevelEntry 3}

teredoAuthHeadersLevelMax OBJECT-TYPE
	SYNTAX	 CounterBasedGauge64
	MAX-ACCESS  read-only
	STATUS      current
	DESCRIPTION
	"Table entry attribute for teredoAuthHeaders"
	::={teredoAuthHeadersLevelEntry 4}


teredoFrags	OBJECT IDENTIFIER ::={teredo 6}

teredoFragsVal	OBJECT-TYPE
	SYNTAX	 Counter64
	MAX-ACCESS read-only
	STATUS current
	DESCRIPTION "Teredo packets inside fragments"

	::={teredoFrags 1}

teredoFragsMom	OBJECT-TYPE
	SYNTAX	 CounterBasedGauge64
	MAX-ACCESS read-only
	STATUS current
	DESCRIPTION "Teredo packets inside fragments"

	::={teredoFrags 2}

teredoFragsMax	OBJECT-TYPE
	SYNTAX	 CounterBasedGauge64
	MAX-ACCESS read-only
	STATUS current
	DESCRIPTION "Teredo packets inside fragments"

	::={teredoFrags 3}

teredoFragsLevelTable OBJECT-TYPE
	SYNTAX      SEQUENCE OF TeredoFragsLevelEntry
	MAX-ACCESS  not-accessible
	STATUS      current
	DESCRIPTION
	"Table for teredoFrags"
	::={teredoFrags 4}

teredoFragsLevelEntry OBJECT-TYPE
	SYNTAX      TeredoFragsLevelEntry
	MAX-ACCESS  not-accessible
	STATUS      current
	DESCRIPTION
	"Table entry for teredoFrags"
	INDEX { teredoFragsLevelName }
	::={teredoFragsLevelTable 1}

TeredoFragsLevelEntry ::=
	SEQUENCE {
		teredoFragsLevelName	DisplayString,
		teredoFragsLevelVal	Counter64,
		teredoFragsLevelMom	CounterBasedGauge64,
		teredoFragsLevelMax	CounterBasedGauge64
	}

teredoFragsLevelName OBJECT-TYPE
	SYNTAX      DisplayString
	MAX-ACCESS  not-accessible
	STATUS      current
	DESCRIPTION
	"Table entry display string for teredoFrags"
	::={teredoFragsLevelEntry 1}

teredoFragsLevelVal OBJECT-TYPE
	SYNTAX	 Counter64
	MAX-ACCESS  read-only
	STATUS      current
	DESCRIPTION
	"Table entry attribute for teredoFrags"
	::={teredoFragsLevelEntry 2}

teredoFragsLevelMom OBJECT-TYPE
	SYNTAX	 CounterBasedGauge64
	MAX-ACCESS  read-only
	STATUS      current
	DESCRIPTION
	"Table entry attribute for teredoFrags"
	::={teredoFragsLevelEntry 3}

teredoFragsLevelMax OBJECT-TYPE
	SYNTAX	 CounterBasedGauge64
	MAX-ACCESS  read-only
	STATUS      current
	DESCRIPTION
	"Table entry attribute for teredoFrags"
	::={teredoFragsLevelEntry 4}


gtp	OBJECT IDENTIFIER ::={sysdiag 129}

gtpPackets	OBJECT IDENTIFIER ::={gtp 2}

gtpPacketsVal	OBJECT-TYPE
	SYNTAX	 Counter64
	MAX-ACCESS read-only
	STATUS current
	DESCRIPTION "RX packets"

	::={gtpPackets 1}

gtpPacketsMom	OBJECT-TYPE
	SYNTAX	 CounterBasedGauge64
	MAX-ACCESS read-only
	STATUS current
	DESCRIPTION "RX packets"

	::={gtpPackets 2}

gtpPacketsMax	OBJECT-TYPE
	SYNTAX	 CounterBasedGauge64
	MAX-ACCESS read-only
	STATUS current
	DESCRIPTION "RX packets"

	::={gtpPackets 3}

gtpPacketsLevelTable OBJECT-TYPE
	SYNTAX      SEQUENCE OF GtpPacketsLevelEntry
	MAX-ACCESS  not-accessible
	STATUS      current
	DESCRIPTION
	"Table for gtpPackets"
	::={gtpPackets 4}

gtpPacketsLevelEntry OBJECT-TYPE
	SYNTAX      GtpPacketsLevelEntry
	MAX-ACCESS  not-accessible
	STATUS      current
	DESCRIPTION
	"Table entry for gtpPackets"
	INDEX { gtpPacketsLevelName }
	::={gtpPacketsLevelTable 1}

GtpPacketsLevelEntry ::=
	SEQUENCE {
		gtpPacketsLevelName	DisplayString,
		gtpPacketsLevelVal	Counter64,
		gtpPacketsLevelMom	CounterBasedGauge64,
		gtpPacketsLevelMax	CounterBasedGauge64
	}

gtpPacketsLevelName OBJECT-TYPE
	SYNTAX      DisplayString
	MAX-ACCESS  not-accessible
	STATUS      current
	DESCRIPTION
	"Table entry display string for gtpPackets"
	::={gtpPacketsLevelEntry 1}

gtpPacketsLevelVal OBJECT-TYPE
	SYNTAX	 Counter64
	MAX-ACCESS  read-only
	STATUS      current
	DESCRIPTION
	"Table entry attribute for gtpPackets"
	::={gtpPacketsLevelEntry 2}

gtpPacketsLevelMom OBJECT-TYPE
	SYNTAX	 CounterBasedGauge64
	MAX-ACCESS  read-only
	STATUS      current
	DESCRIPTION
	"Table entry attribute for gtpPackets"
	::={gtpPacketsLevelEntry 3}

gtpPacketsLevelMax OBJECT-TYPE
	SYNTAX	 CounterBasedGauge64
	MAX-ACCESS  read-only
	STATUS      current
	DESCRIPTION
	"Table entry attribute for gtpPackets"
	::={gtpPacketsLevelEntry 4}


gtpBytes	OBJECT IDENTIFIER ::={gtp 3}

gtpBytesVal	OBJECT-TYPE
	SYNTAX	 Counter64
	MAX-ACCESS read-only
	STATUS current
	DESCRIPTION "RX data"

	::={gtpBytes 1}

gtpBytesMom	OBJECT-TYPE
	SYNTAX	 CounterBasedGauge64
	MAX-ACCESS read-only
	STATUS current
	DESCRIPTION "RX data"

	::={gtpBytes 2}

gtpBytesMax	OBJECT-TYPE
	SYNTAX	 CounterBasedGauge64
	MAX-ACCESS read-only
	STATUS current
	DESCRIPTION "RX data"

	::={gtpBytes 3}

gtpBytesLevelTable OBJECT-TYPE
	SYNTAX      SEQUENCE OF GtpBytesLevelEntry
	MAX-ACCESS  not-accessible
	STATUS      current
	DESCRIPTION
	"Table for gtpBytes"
	::={gtpBytes 4}

gtpBytesLevelEntry OBJECT-TYPE
	SYNTAX      GtpBytesLevelEntry
	MAX-ACCESS  not-accessible
	STATUS      current
	DESCRIPTION
	"Table entry for gtpBytes"
	INDEX { gtpBytesLevelName }
	::={gtpBytesLevelTable 1}

GtpBytesLevelEntry ::=
	SEQUENCE {
		gtpBytesLevelName	DisplayString,
		gtpBytesLevelVal	Counter64,
		gtpBytesLevelMom	CounterBasedGauge64,
		gtpBytesLevelMax	CounterBasedGauge64
	}

gtpBytesLevelName OBJECT-TYPE
	SYNTAX      DisplayString
	MAX-ACCESS  not-accessible
	STATUS      current
	DESCRIPTION
	"Table entry display string for gtpBytes"
	::={gtpBytesLevelEntry 1}

gtpBytesLevelVal OBJECT-TYPE
	SYNTAX	 Counter64
	MAX-ACCESS  read-only
	STATUS      current
	DESCRIPTION
	"Table entry attribute for gtpBytes"
	::={gtpBytesLevelEntry 2}

gtpBytesLevelMom OBJECT-TYPE
	SYNTAX	 CounterBasedGauge64
	MAX-ACCESS  read-only
	STATUS      current
	DESCRIPTION
	"Table entry attribute for gtpBytes"
	::={gtpBytesLevelEntry 3}

gtpBytesLevelMax OBJECT-TYPE
	SYNTAX	 CounterBasedGauge64
	MAX-ACCESS  read-only
	STATUS      current
	DESCRIPTION
	"Table entry attribute for gtpBytes"
	::={gtpBytesLevelEntry 4}


gtpGpdus	OBJECT IDENTIFIER ::={gtp 4}

gtpGpdusVal	OBJECT-TYPE
	SYNTAX	 Counter64
	MAX-ACCESS read-only
	STATUS current
	DESCRIPTION "G-PDU Packets"

	::={gtpGpdus 1}

gtpGpdusMom	OBJECT-TYPE
	SYNTAX	 CounterBasedGauge64
	MAX-ACCESS read-only
	STATUS current
	DESCRIPTION "G-PDU Packets"

	::={gtpGpdus 2}

gtpGpdusMax	OBJECT-TYPE
	SYNTAX	 CounterBasedGauge64
	MAX-ACCESS read-only
	STATUS current
	DESCRIPTION "G-PDU Packets"

	::={gtpGpdus 3}

gtpGpdusLevelTable OBJECT-TYPE
	SYNTAX      SEQUENCE OF GtpGpdusLevelEntry
	MAX-ACCESS  not-accessible
	STATUS      current
	DESCRIPTION
	"Table for gtpGpdus"
	::={gtpGpdus 4}

gtpGpdusLevelEntry OBJECT-TYPE
	SYNTAX      GtpGpdusLevelEntry
	MAX-ACCESS  not-accessible
	STATUS      current
	DESCRIPTION
	"Table entry for gtpGpdus"
	INDEX { gtpGpdusLevelName }
	::={gtpGpdusLevelTable 1}

GtpGpdusLevelEntry ::=
	SEQUENCE {
		gtpGpdusLevelName	DisplayString,
		gtpGpdusLevelVal	Counter64,
		gtpGpdusLevelMom	CounterBasedGauge64,
		gtpGpdusLevelMax	CounterBasedGauge64
	}

gtpGpdusLevelName OBJECT-TYPE
	SYNTAX      DisplayString
	MAX-ACCESS  not-accessible
	STATUS      current
	DESCRIPTION
	"Table entry display string for gtpGpdus"
	::={gtpGpdusLevelEntry 1}

gtpGpdusLevelVal OBJECT-TYPE
	SYNTAX	 Counter64
	MAX-ACCESS  read-only
	STATUS      current
	DESCRIPTION
	"Table entry attribute for gtpGpdus"
	::={gtpGpdusLevelEntry 2}

gtpGpdusLevelMom OBJECT-TYPE
	SYNTAX	 CounterBasedGauge64
	MAX-ACCESS  read-only
	STATUS      current
	DESCRIPTION
	"Table entry attribute for gtpGpdus"
	::={gtpGpdusLevelEntry 3}

gtpGpdusLevelMax OBJECT-TYPE
	SYNTAX	 CounterBasedGauge64
	MAX-ACCESS  read-only
	STATUS      current
	DESCRIPTION
	"Table entry attribute for gtpGpdus"
	::={gtpGpdusLevelEntry 4}


gtpCreatePdpReq	OBJECT IDENTIFIER ::={gtp 5}

gtpCreatePdpReqVal	OBJECT-TYPE
	SYNTAX	 Counter64
	MAX-ACCESS read-only
	STATUS current
	DESCRIPTION "Create PDP Context Request Packets"

	::={gtpCreatePdpReq 1}

gtpCreatePdpReqMom	OBJECT-TYPE
	SYNTAX	 CounterBasedGauge64
	MAX-ACCESS read-only
	STATUS current
	DESCRIPTION "Create PDP Context Request Packets"

	::={gtpCreatePdpReq 2}

gtpCreatePdpReqMax	OBJECT-TYPE
	SYNTAX	 CounterBasedGauge64
	MAX-ACCESS read-only
	STATUS current
	DESCRIPTION "Create PDP Context Request Packets"

	::={gtpCreatePdpReq 3}

gtpCreatePdpReqLevelTable OBJECT-TYPE
	SYNTAX      SEQUENCE OF GtpCreatePdpReqLevelEntry
	MAX-ACCESS  not-accessible
	STATUS      current
	DESCRIPTION
	"Table for gtpCreatePdpReq"
	::={gtpCreatePdpReq 4}

gtpCreatePdpReqLevelEntry OBJECT-TYPE
	SYNTAX      GtpCreatePdpReqLevelEntry
	MAX-ACCESS  not-accessible
	STATUS      current
	DESCRIPTION
	"Table entry for gtpCreatePdpReq"
	INDEX { gtpCreatePdpReqLevelName }
	::={gtpCreatePdpReqLevelTable 1}

GtpCreatePdpReqLevelEntry ::=
	SEQUENCE {
		gtpCreatePdpReqLevelName	DisplayString,
		gtpCreatePdpReqLevelVal	Counter64,
		gtpCreatePdpReqLevelMom	CounterBasedGauge64,
		gtpCreatePdpReqLevelMax	CounterBasedGauge64
	}

gtpCreatePdpReqLevelName OBJECT-TYPE
	SYNTAX      DisplayString
	MAX-ACCESS  not-accessible
	STATUS      current
	DESCRIPTION
	"Table entry display string for gtpCreatePdpReq"
	::={gtpCreatePdpReqLevelEntry 1}

gtpCreatePdpReqLevelVal OBJECT-TYPE
	SYNTAX	 Counter64
	MAX-ACCESS  read-only
	STATUS      current
	DESCRIPTION
	"Table entry attribute for gtpCreatePdpReq"
	::={gtpCreatePdpReqLevelEntry 2}

gtpCreatePdpReqLevelMom OBJECT-TYPE
	SYNTAX	 CounterBasedGauge64
	MAX-ACCESS  read-only
	STATUS      current
	DESCRIPTION
	"Table entry attribute for gtpCreatePdpReq"
	::={gtpCreatePdpReqLevelEntry 3}

gtpCreatePdpReqLevelMax OBJECT-TYPE
	SYNTAX	 CounterBasedGauge64
	MAX-ACCESS  read-only
	STATUS      current
	DESCRIPTION
	"Table entry attribute for gtpCreatePdpReq"
	::={gtpCreatePdpReqLevelEntry 4}


gtpCreatePdpRsp	OBJECT IDENTIFIER ::={gtp 6}

gtpCreatePdpRspVal	OBJECT-TYPE
	SYNTAX	 Counter64
	MAX-ACCESS read-only
	STATUS current
	DESCRIPTION "Create PDP Context Response Packets"

	::={gtpCreatePdpRsp 1}

gtpCreatePdpRspMom	OBJECT-TYPE
	SYNTAX	 CounterBasedGauge64
	MAX-ACCESS read-only
	STATUS current
	DESCRIPTION "Create PDP Context Response Packets"

	::={gtpCreatePdpRsp 2}

gtpCreatePdpRspMax	OBJECT-TYPE
	SYNTAX	 CounterBasedGauge64
	MAX-ACCESS read-only
	STATUS current
	DESCRIPTION "Create PDP Context Response Packets"

	::={gtpCreatePdpRsp 3}

gtpCreatePdpRspLevelTable OBJECT-TYPE
	SYNTAX      SEQUENCE OF GtpCreatePdpRspLevelEntry
	MAX-ACCESS  not-accessible
	STATUS      current
	DESCRIPTION
	"Table for gtpCreatePdpRsp"
	::={gtpCreatePdpRsp 4}

gtpCreatePdpRspLevelEntry OBJECT-TYPE
	SYNTAX      GtpCreatePdpRspLevelEntry
	MAX-ACCESS  not-accessible
	STATUS      current
	DESCRIPTION
	"Table entry for gtpCreatePdpRsp"
	INDEX { gtpCreatePdpRspLevelName }
	::={gtpCreatePdpRspLevelTable 1}

GtpCreatePdpRspLevelEntry ::=
	SEQUENCE {
		gtpCreatePdpRspLevelName	DisplayString,
		gtpCreatePdpRspLevelVal	Counter64,
		gtpCreatePdpRspLevelMom	CounterBasedGauge64,
		gtpCreatePdpRspLevelMax	CounterBasedGauge64
	}

gtpCreatePdpRspLevelName OBJECT-TYPE
	SYNTAX      DisplayString
	MAX-ACCESS  not-accessible
	STATUS      current
	DESCRIPTION
	"Table entry display string for gtpCreatePdpRsp"
	::={gtpCreatePdpRspLevelEntry 1}

gtpCreatePdpRspLevelVal OBJECT-TYPE
	SYNTAX	 Counter64
	MAX-ACCESS  read-only
	STATUS      current
	DESCRIPTION
	"Table entry attribute for gtpCreatePdpRsp"
	::={gtpCreatePdpRspLevelEntry 2}

gtpCreatePdpRspLevelMom OBJECT-TYPE
	SYNTAX	 CounterBasedGauge64
	MAX-ACCESS  read-only
	STATUS      current
	DESCRIPTION
	"Table entry attribute for gtpCreatePdpRsp"
	::={gtpCreatePdpRspLevelEntry 3}

gtpCreatePdpRspLevelMax OBJECT-TYPE
	SYNTAX	 CounterBasedGauge64
	MAX-ACCESS  read-only
	STATUS      current
	DESCRIPTION
	"Table entry attribute for gtpCreatePdpRsp"
	::={gtpCreatePdpRspLevelEntry 4}


gtpDeletePdpReq	OBJECT IDENTIFIER ::={gtp 7}

gtpDeletePdpReqVal	OBJECT-TYPE
	SYNTAX	 Counter64
	MAX-ACCESS read-only
	STATUS current
	DESCRIPTION "Delete PDP Context Request Packets"

	::={gtpDeletePdpReq 1}

gtpDeletePdpReqMom	OBJECT-TYPE
	SYNTAX	 CounterBasedGauge64
	MAX-ACCESS read-only
	STATUS current
	DESCRIPTION "Delete PDP Context Request Packets"

	::={gtpDeletePdpReq 2}

gtpDeletePdpReqMax	OBJECT-TYPE
	SYNTAX	 CounterBasedGauge64
	MAX-ACCESS read-only
	STATUS current
	DESCRIPTION "Delete PDP Context Request Packets"

	::={gtpDeletePdpReq 3}

gtpDeletePdpReqLevelTable OBJECT-TYPE
	SYNTAX      SEQUENCE OF GtpDeletePdpReqLevelEntry
	MAX-ACCESS  not-accessible
	STATUS      current
	DESCRIPTION
	"Table for gtpDeletePdpReq"
	::={gtpDeletePdpReq 4}

gtpDeletePdpReqLevelEntry OBJECT-TYPE
	SYNTAX      GtpDeletePdpReqLevelEntry
	MAX-ACCESS  not-accessible
	STATUS      current
	DESCRIPTION
	"Table entry for gtpDeletePdpReq"
	INDEX { gtpDeletePdpReqLevelName }
	::={gtpDeletePdpReqLevelTable 1}

GtpDeletePdpReqLevelEntry ::=
	SEQUENCE {
		gtpDeletePdpReqLevelName	DisplayString,
		gtpDeletePdpReqLevelVal	Counter64,
		gtpDeletePdpReqLevelMom	CounterBasedGauge64,
		gtpDeletePdpReqLevelMax	CounterBasedGauge64
	}

gtpDeletePdpReqLevelName OBJECT-TYPE
	SYNTAX      DisplayString
	MAX-ACCESS  not-accessible
	STATUS      current
	DESCRIPTION
	"Table entry display string for gtpDeletePdpReq"
	::={gtpDeletePdpReqLevelEntry 1}

gtpDeletePdpReqLevelVal OBJECT-TYPE
	SYNTAX	 Counter64
	MAX-ACCESS  read-only
	STATUS      current
	DESCRIPTION
	"Table entry attribute for gtpDeletePdpReq"
	::={gtpDeletePdpReqLevelEntry 2}

gtpDeletePdpReqLevelMom OBJECT-TYPE
	SYNTAX	 CounterBasedGauge64
	MAX-ACCESS  read-only
	STATUS      current
	DESCRIPTION
	"Table entry attribute for gtpDeletePdpReq"
	::={gtpDeletePdpReqLevelEntry 3}

gtpDeletePdpReqLevelMax OBJECT-TYPE
	SYNTAX	 CounterBasedGauge64
	MAX-ACCESS  read-only
	STATUS      current
	DESCRIPTION
	"Table entry attribute for gtpDeletePdpReq"
	::={gtpDeletePdpReqLevelEntry 4}


gtpDeletePdpRsp	OBJECT IDENTIFIER ::={gtp 8}

gtpDeletePdpRspVal	OBJECT-TYPE
	SYNTAX	 Counter64
	MAX-ACCESS read-only
	STATUS current
	DESCRIPTION "Delete PDP Context Response Packets"

	::={gtpDeletePdpRsp 1}

gtpDeletePdpRspMom	OBJECT-TYPE
	SYNTAX	 CounterBasedGauge64
	MAX-ACCESS read-only
	STATUS current
	DESCRIPTION "Delete PDP Context Response Packets"

	::={gtpDeletePdpRsp 2}

gtpDeletePdpRspMax	OBJECT-TYPE
	SYNTAX	 CounterBasedGauge64
	MAX-ACCESS read-only
	STATUS current
	DESCRIPTION "Delete PDP Context Response Packets"

	::={gtpDeletePdpRsp 3}

gtpDeletePdpRspLevelTable OBJECT-TYPE
	SYNTAX      SEQUENCE OF GtpDeletePdpRspLevelEntry
	MAX-ACCESS  not-accessible
	STATUS      current
	DESCRIPTION
	"Table for gtpDeletePdpRsp"
	::={gtpDeletePdpRsp 4}

gtpDeletePdpRspLevelEntry OBJECT-TYPE
	SYNTAX      GtpDeletePdpRspLevelEntry
	MAX-ACCESS  not-accessible
	STATUS      current
	DESCRIPTION
	"Table entry for gtpDeletePdpRsp"
	INDEX { gtpDeletePdpRspLevelName }
	::={gtpDeletePdpRspLevelTable 1}

GtpDeletePdpRspLevelEntry ::=
	SEQUENCE {
		gtpDeletePdpRspLevelName	DisplayString,
		gtpDeletePdpRspLevelVal	Counter64,
		gtpDeletePdpRspLevelMom	CounterBasedGauge64,
		gtpDeletePdpRspLevelMax	CounterBasedGauge64
	}

gtpDeletePdpRspLevelName OBJECT-TYPE
	SYNTAX      DisplayString
	MAX-ACCESS  not-accessible
	STATUS      current
	DESCRIPTION
	"Table entry display string for gtpDeletePdpRsp"
	::={gtpDeletePdpRspLevelEntry 1}

gtpDeletePdpRspLevelVal OBJECT-TYPE
	SYNTAX	 Counter64
	MAX-ACCESS  read-only
	STATUS      current
	DESCRIPTION
	"Table entry attribute for gtpDeletePdpRsp"
	::={gtpDeletePdpRspLevelEntry 2}

gtpDeletePdpRspLevelMom OBJECT-TYPE
	SYNTAX	 CounterBasedGauge64
	MAX-ACCESS  read-only
	STATUS      current
	DESCRIPTION
	"Table entry attribute for gtpDeletePdpRsp"
	::={gtpDeletePdpRspLevelEntry 3}

gtpDeletePdpRspLevelMax OBJECT-TYPE
	SYNTAX	 CounterBasedGauge64
	MAX-ACCESS  read-only
	STATUS      current
	DESCRIPTION
	"Table entry attribute for gtpDeletePdpRsp"
	::={gtpDeletePdpRspLevelEntry 4}


gtpErrorInd	OBJECT IDENTIFIER ::={gtp 9}

gtpErrorIndVal	OBJECT-TYPE
	SYNTAX	 Counter64
	MAX-ACCESS read-only
	STATUS current
	DESCRIPTION "Error Indication"

	::={gtpErrorInd 1}

gtpErrorIndMom	OBJECT-TYPE
	SYNTAX	 CounterBasedGauge64
	MAX-ACCESS read-only
	STATUS current
	DESCRIPTION "Error Indication"

	::={gtpErrorInd 2}

gtpErrorIndMax	OBJECT-TYPE
	SYNTAX	 CounterBasedGauge64
	MAX-ACCESS read-only
	STATUS current
	DESCRIPTION "Error Indication"

	::={gtpErrorInd 3}

gtpErrorIndLevelTable OBJECT-TYPE
	SYNTAX      SEQUENCE OF GtpErrorIndLevelEntry
	MAX-ACCESS  not-accessible
	STATUS      current
	DESCRIPTION
	"Table for gtpErrorInd"
	::={gtpErrorInd 4}

gtpErrorIndLevelEntry OBJECT-TYPE
	SYNTAX      GtpErrorIndLevelEntry
	MAX-ACCESS  not-accessible
	STATUS      current
	DESCRIPTION
	"Table entry for gtpErrorInd"
	INDEX { gtpErrorIndLevelName }
	::={gtpErrorIndLevelTable 1}

GtpErrorIndLevelEntry ::=
	SEQUENCE {
		gtpErrorIndLevelName	DisplayString,
		gtpErrorIndLevelVal	Counter64,
		gtpErrorIndLevelMom	CounterBasedGauge64,
		gtpErrorIndLevelMax	CounterBasedGauge64
	}

gtpErrorIndLevelName OBJECT-TYPE
	SYNTAX      DisplayString
	MAX-ACCESS  not-accessible
	STATUS      current
	DESCRIPTION
	"Table entry display string for gtpErrorInd"
	::={gtpErrorIndLevelEntry 1}

gtpErrorIndLevelVal OBJECT-TYPE
	SYNTAX	 Counter64
	MAX-ACCESS  read-only
	STATUS      current
	DESCRIPTION
	"Table entry attribute for gtpErrorInd"
	::={gtpErrorIndLevelEntry 2}

gtpErrorIndLevelMom OBJECT-TYPE
	SYNTAX	 CounterBasedGauge64
	MAX-ACCESS  read-only
	STATUS      current
	DESCRIPTION
	"Table entry attribute for gtpErrorInd"
	::={gtpErrorIndLevelEntry 3}

gtpErrorIndLevelMax OBJECT-TYPE
	SYNTAX	 CounterBasedGauge64
	MAX-ACCESS  read-only
	STATUS      current
	DESCRIPTION
	"Table entry attribute for gtpErrorInd"
	::={gtpErrorIndLevelEntry 4}


gtpUnknown	OBJECT IDENTIFIER ::={gtp 10}

gtpUnknownVal	OBJECT-TYPE
	SYNTAX	 Counter64
	MAX-ACCESS read-only
	STATUS current
	DESCRIPTION "Unkown GTP Type"

	::={gtpUnknown 1}

gtpUnknownMom	OBJECT-TYPE
	SYNTAX	 CounterBasedGauge64
	MAX-ACCESS read-only
	STATUS current
	DESCRIPTION "Unkown GTP Type"

	::={gtpUnknown 2}

gtpUnknownMax	OBJECT-TYPE
	SYNTAX	 CounterBasedGauge64
	MAX-ACCESS read-only
	STATUS current
	DESCRIPTION "Unkown GTP Type"

	::={gtpUnknown 3}

gtpUnknownLevelTable OBJECT-TYPE
	SYNTAX      SEQUENCE OF GtpUnknownLevelEntry
	MAX-ACCESS  not-accessible
	STATUS      current
	DESCRIPTION
	"Table for gtpUnknown"
	::={gtpUnknown 4}

gtpUnknownLevelEntry OBJECT-TYPE
	SYNTAX      GtpUnknownLevelEntry
	MAX-ACCESS  not-accessible
	STATUS      current
	DESCRIPTION
	"Table entry for gtpUnknown"
	INDEX { gtpUnknownLevelName }
	::={gtpUnknownLevelTable 1}

GtpUnknownLevelEntry ::=
	SEQUENCE {
		gtpUnknownLevelName	DisplayString,
		gtpUnknownLevelVal	Counter64,
		gtpUnknownLevelMom	CounterBasedGauge64,
		gtpUnknownLevelMax	CounterBasedGauge64
	}

gtpUnknownLevelName OBJECT-TYPE
	SYNTAX      DisplayString
	MAX-ACCESS  not-accessible
	STATUS      current
	DESCRIPTION
	"Table entry display string for gtpUnknown"
	::={gtpUnknownLevelEntry 1}

gtpUnknownLevelVal OBJECT-TYPE
	SYNTAX	 Counter64
	MAX-ACCESS  read-only
	STATUS      current
	DESCRIPTION
	"Table entry attribute for gtpUnknown"
	::={gtpUnknownLevelEntry 2}

gtpUnknownLevelMom OBJECT-TYPE
	SYNTAX	 CounterBasedGauge64
	MAX-ACCESS  read-only
	STATUS      current
	DESCRIPTION
	"Table entry attribute for gtpUnknown"
	::={gtpUnknownLevelEntry 3}

gtpUnknownLevelMax OBJECT-TYPE
	SYNTAX	 CounterBasedGauge64
	MAX-ACCESS  read-only
	STATUS      current
	DESCRIPTION
	"Table entry attribute for gtpUnknown"
	::={gtpUnknownLevelEntry 4}


gtpUpdatePdpReq	OBJECT IDENTIFIER ::={gtp 11}

gtpUpdatePdpReqVal	OBJECT-TYPE
	SYNTAX	 Counter64
	MAX-ACCESS read-only
	STATUS current
	DESCRIPTION "Update PDP Context Request Packets"

	::={gtpUpdatePdpReq 1}

gtpUpdatePdpReqMom	OBJECT-TYPE
	SYNTAX	 CounterBasedGauge64
	MAX-ACCESS read-only
	STATUS current
	DESCRIPTION "Update PDP Context Request Packets"

	::={gtpUpdatePdpReq 2}

gtpUpdatePdpReqMax	OBJECT-TYPE
	SYNTAX	 CounterBasedGauge64
	MAX-ACCESS read-only
	STATUS current
	DESCRIPTION "Update PDP Context Request Packets"

	::={gtpUpdatePdpReq 3}

gtpUpdatePdpReqLevelTable OBJECT-TYPE
	SYNTAX      SEQUENCE OF GtpUpdatePdpReqLevelEntry
	MAX-ACCESS  not-accessible
	STATUS      current
	DESCRIPTION
	"Table for gtpUpdatePdpReq"
	::={gtpUpdatePdpReq 4}

gtpUpdatePdpReqLevelEntry OBJECT-TYPE
	SYNTAX      GtpUpdatePdpReqLevelEntry
	MAX-ACCESS  not-accessible
	STATUS      current
	DESCRIPTION
	"Table entry for gtpUpdatePdpReq"
	INDEX { gtpUpdatePdpReqLevelName }
	::={gtpUpdatePdpReqLevelTable 1}

GtpUpdatePdpReqLevelEntry ::=
	SEQUENCE {
		gtpUpdatePdpReqLevelName	DisplayString,
		gtpUpdatePdpReqLevelVal	Counter64,
		gtpUpdatePdpReqLevelMom	CounterBasedGauge64,
		gtpUpdatePdpReqLevelMax	CounterBasedGauge64
	}

gtpUpdatePdpReqLevelName OBJECT-TYPE
	SYNTAX      DisplayString
	MAX-ACCESS  not-accessible
	STATUS      current
	DESCRIPTION
	"Table entry display string for gtpUpdatePdpReq"
	::={gtpUpdatePdpReqLevelEntry 1}

gtpUpdatePdpReqLevelVal OBJECT-TYPE
	SYNTAX	 Counter64
	MAX-ACCESS  read-only
	STATUS      current
	DESCRIPTION
	"Table entry attribute for gtpUpdatePdpReq"
	::={gtpUpdatePdpReqLevelEntry 2}

gtpUpdatePdpReqLevelMom OBJECT-TYPE
	SYNTAX	 CounterBasedGauge64
	MAX-ACCESS  read-only
	STATUS      current
	DESCRIPTION
	"Table entry attribute for gtpUpdatePdpReq"
	::={gtpUpdatePdpReqLevelEntry 3}

gtpUpdatePdpReqLevelMax OBJECT-TYPE
	SYNTAX	 CounterBasedGauge64
	MAX-ACCESS  read-only
	STATUS      current
	DESCRIPTION
	"Table entry attribute for gtpUpdatePdpReq"
	::={gtpUpdatePdpReqLevelEntry 4}


gtpUpdatePdpRsp	OBJECT IDENTIFIER ::={gtp 12}

gtpUpdatePdpRspVal	OBJECT-TYPE
	SYNTAX	 Counter64
	MAX-ACCESS read-only
	STATUS current
	DESCRIPTION "Update PDP Context Response Packets"

	::={gtpUpdatePdpRsp 1}

gtpUpdatePdpRspMom	OBJECT-TYPE
	SYNTAX	 CounterBasedGauge64
	MAX-ACCESS read-only
	STATUS current
	DESCRIPTION "Update PDP Context Response Packets"

	::={gtpUpdatePdpRsp 2}

gtpUpdatePdpRspMax	OBJECT-TYPE
	SYNTAX	 CounterBasedGauge64
	MAX-ACCESS read-only
	STATUS current
	DESCRIPTION "Update PDP Context Response Packets"

	::={gtpUpdatePdpRsp 3}

gtpUpdatePdpRspLevelTable OBJECT-TYPE
	SYNTAX      SEQUENCE OF GtpUpdatePdpRspLevelEntry
	MAX-ACCESS  not-accessible
	STATUS      current
	DESCRIPTION
	"Table for gtpUpdatePdpRsp"
	::={gtpUpdatePdpRsp 4}

gtpUpdatePdpRspLevelEntry OBJECT-TYPE
	SYNTAX      GtpUpdatePdpRspLevelEntry
	MAX-ACCESS  not-accessible
	STATUS      current
	DESCRIPTION
	"Table entry for gtpUpdatePdpRsp"
	INDEX { gtpUpdatePdpRspLevelName }
	::={gtpUpdatePdpRspLevelTable 1}

GtpUpdatePdpRspLevelEntry ::=
	SEQUENCE {
		gtpUpdatePdpRspLevelName	DisplayString,
		gtpUpdatePdpRspLevelVal	Counter64,
		gtpUpdatePdpRspLevelMom	CounterBasedGauge64,
		gtpUpdatePdpRspLevelMax	CounterBasedGauge64
	}

gtpUpdatePdpRspLevelName OBJECT-TYPE
	SYNTAX      DisplayString
	MAX-ACCESS  not-accessible
	STATUS      current
	DESCRIPTION
	"Table entry display string for gtpUpdatePdpRsp"
	::={gtpUpdatePdpRspLevelEntry 1}

gtpUpdatePdpRspLevelVal OBJECT-TYPE
	SYNTAX	 Counter64
	MAX-ACCESS  read-only
	STATUS      current
	DESCRIPTION
	"Table entry attribute for gtpUpdatePdpRsp"
	::={gtpUpdatePdpRspLevelEntry 2}

gtpUpdatePdpRspLevelMom OBJECT-TYPE
	SYNTAX	 CounterBasedGauge64
	MAX-ACCESS  read-only
	STATUS      current
	DESCRIPTION
	"Table entry attribute for gtpUpdatePdpRsp"
	::={gtpUpdatePdpRspLevelEntry 3}

gtpUpdatePdpRspLevelMax OBJECT-TYPE
	SYNTAX	 CounterBasedGauge64
	MAX-ACCESS  read-only
	STATUS      current
	DESCRIPTION
	"Table entry attribute for gtpUpdatePdpRsp"
	::={gtpUpdatePdpRspLevelEntry 4}


gtpEchoPdpReq	OBJECT IDENTIFIER ::={gtp 13}

gtpEchoPdpReqVal	OBJECT-TYPE
	SYNTAX	 Counter64
	MAX-ACCESS read-only
	STATUS current
	DESCRIPTION "Echo Request Packets"

	::={gtpEchoPdpReq 1}

gtpEchoPdpReqMom	OBJECT-TYPE
	SYNTAX	 CounterBasedGauge64
	MAX-ACCESS read-only
	STATUS current
	DESCRIPTION "Echo Request Packets"

	::={gtpEchoPdpReq 2}

gtpEchoPdpReqMax	OBJECT-TYPE
	SYNTAX	 CounterBasedGauge64
	MAX-ACCESS read-only
	STATUS current
	DESCRIPTION "Echo Request Packets"

	::={gtpEchoPdpReq 3}

gtpEchoPdpReqLevelTable OBJECT-TYPE
	SYNTAX      SEQUENCE OF GtpEchoPdpReqLevelEntry
	MAX-ACCESS  not-accessible
	STATUS      current
	DESCRIPTION
	"Table for gtpEchoPdpReq"
	::={gtpEchoPdpReq 4}

gtpEchoPdpReqLevelEntry OBJECT-TYPE
	SYNTAX      GtpEchoPdpReqLevelEntry
	MAX-ACCESS  not-accessible
	STATUS      current
	DESCRIPTION
	"Table entry for gtpEchoPdpReq"
	INDEX { gtpEchoPdpReqLevelName }
	::={gtpEchoPdpReqLevelTable 1}

GtpEchoPdpReqLevelEntry ::=
	SEQUENCE {
		gtpEchoPdpReqLevelName	DisplayString,
		gtpEchoPdpReqLevelVal	Counter64,
		gtpEchoPdpReqLevelMom	CounterBasedGauge64,
		gtpEchoPdpReqLevelMax	CounterBasedGauge64
	}

gtpEchoPdpReqLevelName OBJECT-TYPE
	SYNTAX      DisplayString
	MAX-ACCESS  not-accessible
	STATUS      current
	DESCRIPTION
	"Table entry display string for gtpEchoPdpReq"
	::={gtpEchoPdpReqLevelEntry 1}

gtpEchoPdpReqLevelVal OBJECT-TYPE
	SYNTAX	 Counter64
	MAX-ACCESS  read-only
	STATUS      current
	DESCRIPTION
	"Table entry attribute for gtpEchoPdpReq"
	::={gtpEchoPdpReqLevelEntry 2}

gtpEchoPdpReqLevelMom OBJECT-TYPE
	SYNTAX	 CounterBasedGauge64
	MAX-ACCESS  read-only
	STATUS      current
	DESCRIPTION
	"Table entry attribute for gtpEchoPdpReq"
	::={gtpEchoPdpReqLevelEntry 3}

gtpEchoPdpReqLevelMax OBJECT-TYPE
	SYNTAX	 CounterBasedGauge64
	MAX-ACCESS  read-only
	STATUS      current
	DESCRIPTION
	"Table entry attribute for gtpEchoPdpReq"
	::={gtpEchoPdpReqLevelEntry 4}


gtpEchoPdpRsp	OBJECT IDENTIFIER ::={gtp 14}

gtpEchoPdpRspVal	OBJECT-TYPE
	SYNTAX	 Counter64
	MAX-ACCESS read-only
	STATUS current
	DESCRIPTION "Echo Response Packets"

	::={gtpEchoPdpRsp 1}

gtpEchoPdpRspMom	OBJECT-TYPE
	SYNTAX	 CounterBasedGauge64
	MAX-ACCESS read-only
	STATUS current
	DESCRIPTION "Echo Response Packets"

	::={gtpEchoPdpRsp 2}

gtpEchoPdpRspMax	OBJECT-TYPE
	SYNTAX	 CounterBasedGauge64
	MAX-ACCESS read-only
	STATUS current
	DESCRIPTION "Echo Response Packets"

	::={gtpEchoPdpRsp 3}

gtpEchoPdpRspLevelTable OBJECT-TYPE
	SYNTAX      SEQUENCE OF GtpEchoPdpRspLevelEntry
	MAX-ACCESS  not-accessible
	STATUS      current
	DESCRIPTION
	"Table for gtpEchoPdpRsp"
	::={gtpEchoPdpRsp 4}

gtpEchoPdpRspLevelEntry OBJECT-TYPE
	SYNTAX      GtpEchoPdpRspLevelEntry
	MAX-ACCESS  not-accessible
	STATUS      current
	DESCRIPTION
	"Table entry for gtpEchoPdpRsp"
	INDEX { gtpEchoPdpRspLevelName }
	::={gtpEchoPdpRspLevelTable 1}

GtpEchoPdpRspLevelEntry ::=
	SEQUENCE {
		gtpEchoPdpRspLevelName	DisplayString,
		gtpEchoPdpRspLevelVal	Counter64,
		gtpEchoPdpRspLevelMom	CounterBasedGauge64,
		gtpEchoPdpRspLevelMax	CounterBasedGauge64
	}

gtpEchoPdpRspLevelName OBJECT-TYPE
	SYNTAX      DisplayString
	MAX-ACCESS  not-accessible
	STATUS      current
	DESCRIPTION
	"Table entry display string for gtpEchoPdpRsp"
	::={gtpEchoPdpRspLevelEntry 1}

gtpEchoPdpRspLevelVal OBJECT-TYPE
	SYNTAX	 Counter64
	MAX-ACCESS  read-only
	STATUS      current
	DESCRIPTION
	"Table entry attribute for gtpEchoPdpRsp"
	::={gtpEchoPdpRspLevelEntry 2}

gtpEchoPdpRspLevelMom OBJECT-TYPE
	SYNTAX	 CounterBasedGauge64
	MAX-ACCESS  read-only
	STATUS      current
	DESCRIPTION
	"Table entry attribute for gtpEchoPdpRsp"
	::={gtpEchoPdpRspLevelEntry 3}

gtpEchoPdpRspLevelMax OBJECT-TYPE
	SYNTAX	 CounterBasedGauge64
	MAX-ACCESS  read-only
	STATUS      current
	DESCRIPTION
	"Table entry attribute for gtpEchoPdpRsp"
	::={gtpEchoPdpRspLevelEntry 4}


gtpSgsnReq	OBJECT IDENTIFIER ::={gtp 15}

gtpSgsnReqVal	OBJECT-TYPE
	SYNTAX	 Counter64
	MAX-ACCESS read-only
	STATUS current
	DESCRIPTION "SGSN Context Request"

	::={gtpSgsnReq 1}

gtpSgsnReqMom	OBJECT-TYPE
	SYNTAX	 CounterBasedGauge64
	MAX-ACCESS read-only
	STATUS current
	DESCRIPTION "SGSN Context Request"

	::={gtpSgsnReq 2}

gtpSgsnReqMax	OBJECT-TYPE
	SYNTAX	 CounterBasedGauge64
	MAX-ACCESS read-only
	STATUS current
	DESCRIPTION "SGSN Context Request"

	::={gtpSgsnReq 3}

gtpSgsnReqLevelTable OBJECT-TYPE
	SYNTAX      SEQUENCE OF GtpSgsnReqLevelEntry
	MAX-ACCESS  not-accessible
	STATUS      current
	DESCRIPTION
	"Table for gtpSgsnReq"
	::={gtpSgsnReq 4}

gtpSgsnReqLevelEntry OBJECT-TYPE
	SYNTAX      GtpSgsnReqLevelEntry
	MAX-ACCESS  not-accessible
	STATUS      current
	DESCRIPTION
	"Table entry for gtpSgsnReq"
	INDEX { gtpSgsnReqLevelName }
	::={gtpSgsnReqLevelTable 1}

GtpSgsnReqLevelEntry ::=
	SEQUENCE {
		gtpSgsnReqLevelName	DisplayString,
		gtpSgsnReqLevelVal	Counter64,
		gtpSgsnReqLevelMom	CounterBasedGauge64,
		gtpSgsnReqLevelMax	CounterBasedGauge64
	}

gtpSgsnReqLevelName OBJECT-TYPE
	SYNTAX      DisplayString
	MAX-ACCESS  not-accessible
	STATUS      current
	DESCRIPTION
	"Table entry display string for gtpSgsnReq"
	::={gtpSgsnReqLevelEntry 1}

gtpSgsnReqLevelVal OBJECT-TYPE
	SYNTAX	 Counter64
	MAX-ACCESS  read-only
	STATUS      current
	DESCRIPTION
	"Table entry attribute for gtpSgsnReq"
	::={gtpSgsnReqLevelEntry 2}

gtpSgsnReqLevelMom OBJECT-TYPE
	SYNTAX	 CounterBasedGauge64
	MAX-ACCESS  read-only
	STATUS      current
	DESCRIPTION
	"Table entry attribute for gtpSgsnReq"
	::={gtpSgsnReqLevelEntry 3}

gtpSgsnReqLevelMax OBJECT-TYPE
	SYNTAX	 CounterBasedGauge64
	MAX-ACCESS  read-only
	STATUS      current
	DESCRIPTION
	"Table entry attribute for gtpSgsnReq"
	::={gtpSgsnReqLevelEntry 4}


gtpSgsnRsp	OBJECT IDENTIFIER ::={gtp 16}

gtpSgsnRspVal	OBJECT-TYPE
	SYNTAX	 Counter64
	MAX-ACCESS read-only
	STATUS current
	DESCRIPTION "SGSN Context Response"

	::={gtpSgsnRsp 1}

gtpSgsnRspMom	OBJECT-TYPE
	SYNTAX	 CounterBasedGauge64
	MAX-ACCESS read-only
	STATUS current
	DESCRIPTION "SGSN Context Response"

	::={gtpSgsnRsp 2}

gtpSgsnRspMax	OBJECT-TYPE
	SYNTAX	 CounterBasedGauge64
	MAX-ACCESS read-only
	STATUS current
	DESCRIPTION "SGSN Context Response"

	::={gtpSgsnRsp 3}

gtpSgsnRspLevelTable OBJECT-TYPE
	SYNTAX      SEQUENCE OF GtpSgsnRspLevelEntry
	MAX-ACCESS  not-accessible
	STATUS      current
	DESCRIPTION
	"Table for gtpSgsnRsp"
	::={gtpSgsnRsp 4}

gtpSgsnRspLevelEntry OBJECT-TYPE
	SYNTAX      GtpSgsnRspLevelEntry
	MAX-ACCESS  not-accessible
	STATUS      current
	DESCRIPTION
	"Table entry for gtpSgsnRsp"
	INDEX { gtpSgsnRspLevelName }
	::={gtpSgsnRspLevelTable 1}

GtpSgsnRspLevelEntry ::=
	SEQUENCE {
		gtpSgsnRspLevelName	DisplayString,
		gtpSgsnRspLevelVal	Counter64,
		gtpSgsnRspLevelMom	CounterBasedGauge64,
		gtpSgsnRspLevelMax	CounterBasedGauge64
	}

gtpSgsnRspLevelName OBJECT-TYPE
	SYNTAX      DisplayString
	MAX-ACCESS  not-accessible
	STATUS      current
	DESCRIPTION
	"Table entry display string for gtpSgsnRsp"
	::={gtpSgsnRspLevelEntry 1}

gtpSgsnRspLevelVal OBJECT-TYPE
	SYNTAX	 Counter64
	MAX-ACCESS  read-only
	STATUS      current
	DESCRIPTION
	"Table entry attribute for gtpSgsnRsp"
	::={gtpSgsnRspLevelEntry 2}

gtpSgsnRspLevelMom OBJECT-TYPE
	SYNTAX	 CounterBasedGauge64
	MAX-ACCESS  read-only
	STATUS      current
	DESCRIPTION
	"Table entry attribute for gtpSgsnRsp"
	::={gtpSgsnRspLevelEntry 3}

gtpSgsnRspLevelMax OBJECT-TYPE
	SYNTAX	 CounterBasedGauge64
	MAX-ACCESS  read-only
	STATUS      current
	DESCRIPTION
	"Table entry attribute for gtpSgsnRsp"
	::={gtpSgsnRspLevelEntry 4}


tunnel	OBJECT IDENTIFIER ::={sysdiag 130}

tunnelGtp	OBJECT IDENTIFIER ::={tunnel 2}

tunnelGtpVal	OBJECT-TYPE
	SYNTAX	 CounterBasedGauge64
	MAX-ACCESS read-only
	STATUS current
	DESCRIPTION "GTP Tunnel Contexts"

	::={tunnelGtp 1}

tunnelGtpMax	OBJECT-TYPE
	SYNTAX	 CounterBasedGauge64
	MAX-ACCESS read-only
	STATUS current
	DESCRIPTION "GTP Tunnel Contexts"

	::={tunnelGtp 3}

tunnelGtpLevelTable OBJECT-TYPE
	SYNTAX      SEQUENCE OF TunnelGtpLevelEntry
	MAX-ACCESS  not-accessible
	STATUS      current
	DESCRIPTION
	"Table for tunnelGtp"
	::={tunnelGtp 4}

tunnelGtpLevelEntry OBJECT-TYPE
	SYNTAX      TunnelGtpLevelEntry
	MAX-ACCESS  not-accessible
	STATUS      current
	DESCRIPTION
	"Table entry for tunnelGtp"
	INDEX { tunnelGtpLevelName }
	::={tunnelGtpLevelTable 1}

TunnelGtpLevelEntry ::=
	SEQUENCE {
		tunnelGtpLevelName	DisplayString,
		tunnelGtpLevelVal	CounterBasedGauge64,
		tunnelGtpLevelMax	CounterBasedGauge64
	}

tunnelGtpLevelName OBJECT-TYPE
	SYNTAX      DisplayString
	MAX-ACCESS  not-accessible
	STATUS      current
	DESCRIPTION
	"Table entry display string for tunnelGtp"
	::={tunnelGtpLevelEntry 1}

tunnelGtpLevelVal OBJECT-TYPE
	SYNTAX	 CounterBasedGauge64
	MAX-ACCESS  read-only
	STATUS      current
	DESCRIPTION
	"Table entry attribute for tunnelGtp"
	::={tunnelGtpLevelEntry 2}

tunnelGtpLevelMax OBJECT-TYPE
	SYNTAX	 CounterBasedGauge64
	MAX-ACCESS  read-only
	STATUS      current
	DESCRIPTION
	"Table entry attribute for tunnelGtp"
	::={tunnelGtpLevelEntry 4}


tunnelEsp	OBJECT IDENTIFIER ::={tunnel 3}

tunnelEspVal	OBJECT-TYPE
	SYNTAX	 CounterBasedGauge64
	MAX-ACCESS read-only
	STATUS obsolete
	DESCRIPTION "ESP Tunnel Contexts"

	::={tunnelEsp 1}

tunnelEspMax	OBJECT-TYPE
	SYNTAX	 CounterBasedGauge64
	MAX-ACCESS read-only
	STATUS obsolete
	DESCRIPTION "ESP Tunnel Contexts"

	::={tunnelEsp 3}

tunnelEspLevelTable OBJECT-TYPE
	SYNTAX      SEQUENCE OF TunnelEspLevelEntry
	MAX-ACCESS  not-accessible
	STATUS      current
	DESCRIPTION
	"Table for tunnelEsp"
	::={tunnelEsp 4}

tunnelEspLevelEntry OBJECT-TYPE
	SYNTAX      TunnelEspLevelEntry
	MAX-ACCESS  not-accessible
	STATUS      current
	DESCRIPTION
	"Table entry for tunnelEsp"
	INDEX { tunnelEspLevelName }
	::={tunnelEspLevelTable 1}

TunnelEspLevelEntry ::=
	SEQUENCE {
		tunnelEspLevelName	DisplayString,
		tunnelEspLevelVal	CounterBasedGauge64,
		tunnelEspLevelMax	CounterBasedGauge64
	}

tunnelEspLevelName OBJECT-TYPE
	SYNTAX      DisplayString
	MAX-ACCESS  not-accessible
	STATUS      current
	DESCRIPTION
	"Table entry display string for tunnelEsp"
	::={tunnelEspLevelEntry 1}

tunnelEspLevelVal OBJECT-TYPE
	SYNTAX	 CounterBasedGauge64
	MAX-ACCESS  read-only
	STATUS      current
	DESCRIPTION
	"Table entry attribute for tunnelEsp"
	::={tunnelEspLevelEntry 2}

tunnelEspLevelMax OBJECT-TYPE
	SYNTAX	 CounterBasedGauge64
	MAX-ACCESS  read-only
	STATUS      current
	DESCRIPTION
	"Table entry attribute for tunnelEsp"
	::={tunnelEspLevelEntry 4}


tunnelTeredo	OBJECT IDENTIFIER ::={tunnel 4}

tunnelTeredoVal	OBJECT-TYPE
	SYNTAX	 CounterBasedGauge64
	MAX-ACCESS read-only
	STATUS current
	DESCRIPTION "Teredo Tunnel Contexts"

	::={tunnelTeredo 1}

tunnelTeredoMax	OBJECT-TYPE
	SYNTAX	 CounterBasedGauge64
	MAX-ACCESS read-only
	STATUS current
	DESCRIPTION "Teredo Tunnel Contexts"

	::={tunnelTeredo 3}

tunnelTeredoLevelTable OBJECT-TYPE
	SYNTAX      SEQUENCE OF TunnelTeredoLevelEntry
	MAX-ACCESS  not-accessible
	STATUS      current
	DESCRIPTION
	"Table for tunnelTeredo"
	::={tunnelTeredo 4}

tunnelTeredoLevelEntry OBJECT-TYPE
	SYNTAX      TunnelTeredoLevelEntry
	MAX-ACCESS  not-accessible
	STATUS      current
	DESCRIPTION
	"Table entry for tunnelTeredo"
	INDEX { tunnelTeredoLevelName }
	::={tunnelTeredoLevelTable 1}

TunnelTeredoLevelEntry ::=
	SEQUENCE {
		tunnelTeredoLevelName	DisplayString,
		tunnelTeredoLevelVal	CounterBasedGauge64,
		tunnelTeredoLevelMax	CounterBasedGauge64
	}

tunnelTeredoLevelName OBJECT-TYPE
	SYNTAX      DisplayString
	MAX-ACCESS  not-accessible
	STATUS      current
	DESCRIPTION
	"Table entry display string for tunnelTeredo"
	::={tunnelTeredoLevelEntry 1}

tunnelTeredoLevelVal OBJECT-TYPE
	SYNTAX	 CounterBasedGauge64
	MAX-ACCESS  read-only
	STATUS      current
	DESCRIPTION
	"Table entry attribute for tunnelTeredo"
	::={tunnelTeredoLevelEntry 2}

tunnelTeredoLevelMax OBJECT-TYPE
	SYNTAX	 CounterBasedGauge64
	MAX-ACCESS  read-only
	STATUS      current
	DESCRIPTION
	"Table entry attribute for tunnelTeredo"
	::={tunnelTeredoLevelEntry 4}


tunnelGre	OBJECT IDENTIFIER ::={tunnel 5}

tunnelGreVal	OBJECT-TYPE
	SYNTAX	 CounterBasedGauge64
	MAX-ACCESS read-only
	STATUS current
	DESCRIPTION "GRE Tunnel Contexts"

	::={tunnelGre 1}

tunnelGreMax	OBJECT-TYPE
	SYNTAX	 CounterBasedGauge64
	MAX-ACCESS read-only
	STATUS current
	DESCRIPTION "GRE Tunnel Contexts"

	::={tunnelGre 3}

tunnelGreLevelTable OBJECT-TYPE
	SYNTAX      SEQUENCE OF TunnelGreLevelEntry
	MAX-ACCESS  not-accessible
	STATUS      current
	DESCRIPTION
	"Table for tunnelGre"
	::={tunnelGre 4}

tunnelGreLevelEntry OBJECT-TYPE
	SYNTAX      TunnelGreLevelEntry
	MAX-ACCESS  not-accessible
	STATUS      current
	DESCRIPTION
	"Table entry for tunnelGre"
	INDEX { tunnelGreLevelName }
	::={tunnelGreLevelTable 1}

TunnelGreLevelEntry ::=
	SEQUENCE {
		tunnelGreLevelName	DisplayString,
		tunnelGreLevelVal	CounterBasedGauge64,
		tunnelGreLevelMax	CounterBasedGauge64
	}

tunnelGreLevelName OBJECT-TYPE
	SYNTAX      DisplayString
	MAX-ACCESS  not-accessible
	STATUS      current
	DESCRIPTION
	"Table entry display string for tunnelGre"
	::={tunnelGreLevelEntry 1}

tunnelGreLevelVal OBJECT-TYPE
	SYNTAX	 CounterBasedGauge64
	MAX-ACCESS  read-only
	STATUS      current
	DESCRIPTION
	"Table entry attribute for tunnelGre"
	::={tunnelGreLevelEntry 2}

tunnelGreLevelMax OBJECT-TYPE
	SYNTAX	 CounterBasedGauge64
	MAX-ACCESS  read-only
	STATUS      current
	DESCRIPTION
	"Table entry attribute for tunnelGre"
	::={tunnelGreLevelEntry 4}


tunnelUnknownPkts	OBJECT IDENTIFIER ::={tunnel 6}

tunnelUnknownPktsVal	OBJECT-TYPE
	SYNTAX	 Counter64
	MAX-ACCESS read-only
	STATUS current
	DESCRIPTION "Packets For Unknown Tunnels"

	::={tunnelUnknownPkts 1}

tunnelUnknownPktsMom	OBJECT-TYPE
	SYNTAX	 CounterBasedGauge64
	MAX-ACCESS read-only
	STATUS current
	DESCRIPTION "Packets For Unknown Tunnels"

	::={tunnelUnknownPkts 2}

tunnelUnknownPktsMax	OBJECT-TYPE
	SYNTAX	 CounterBasedGauge64
	MAX-ACCESS read-only
	STATUS current
	DESCRIPTION "Packets For Unknown Tunnels"

	::={tunnelUnknownPkts 3}

tunnelUnknownPktsLevelTable OBJECT-TYPE
	SYNTAX      SEQUENCE OF TunnelUnknownPktsLevelEntry
	MAX-ACCESS  not-accessible
	STATUS      current
	DESCRIPTION
	"Table for tunnelUnknownPkts"
	::={tunnelUnknownPkts 4}

tunnelUnknownPktsLevelEntry OBJECT-TYPE
	SYNTAX      TunnelUnknownPktsLevelEntry
	MAX-ACCESS  not-accessible
	STATUS      current
	DESCRIPTION
	"Table entry for tunnelUnknownPkts"
	INDEX { tunnelUnknownPktsLevelName }
	::={tunnelUnknownPktsLevelTable 1}

TunnelUnknownPktsLevelEntry ::=
	SEQUENCE {
		tunnelUnknownPktsLevelName	DisplayString,
		tunnelUnknownPktsLevelVal	Counter64,
		tunnelUnknownPktsLevelMom	CounterBasedGauge64,
		tunnelUnknownPktsLevelMax	CounterBasedGauge64
	}

tunnelUnknownPktsLevelName OBJECT-TYPE
	SYNTAX      DisplayString
	MAX-ACCESS  not-accessible
	STATUS      current
	DESCRIPTION
	"Table entry display string for tunnelUnknownPkts"
	::={tunnelUnknownPktsLevelEntry 1}

tunnelUnknownPktsLevelVal OBJECT-TYPE
	SYNTAX	 Counter64
	MAX-ACCESS  read-only
	STATUS      current
	DESCRIPTION
	"Table entry attribute for tunnelUnknownPkts"
	::={tunnelUnknownPktsLevelEntry 2}

tunnelUnknownPktsLevelMom OBJECT-TYPE
	SYNTAX	 CounterBasedGauge64
	MAX-ACCESS  read-only
	STATUS      current
	DESCRIPTION
	"Table entry attribute for tunnelUnknownPkts"
	::={tunnelUnknownPktsLevelEntry 3}

tunnelUnknownPktsLevelMax OBJECT-TYPE
	SYNTAX	 CounterBasedGauge64
	MAX-ACCESS  read-only
	STATUS      current
	DESCRIPTION
	"Table entry attribute for tunnelUnknownPkts"
	::={tunnelUnknownPktsLevelEntry 4}


tunnelDuplicates	OBJECT IDENTIFIER ::={tunnel 7}

tunnelDuplicatesVal	OBJECT-TYPE
	SYNTAX	 Counter64
	MAX-ACCESS read-only
	STATUS current
	DESCRIPTION "Tunnels With Duplicate Keys"

	::={tunnelDuplicates 1}

tunnelDuplicatesMom	OBJECT-TYPE
	SYNTAX	 CounterBasedGauge64
	MAX-ACCESS read-only
	STATUS current
	DESCRIPTION "Tunnels With Duplicate Keys"

	::={tunnelDuplicates 2}

tunnelDuplicatesMax	OBJECT-TYPE
	SYNTAX	 CounterBasedGauge64
	MAX-ACCESS read-only
	STATUS current
	DESCRIPTION "Tunnels With Duplicate Keys"

	::={tunnelDuplicates 3}

tunnelDuplicatesLevelTable OBJECT-TYPE
	SYNTAX      SEQUENCE OF TunnelDuplicatesLevelEntry
	MAX-ACCESS  not-accessible
	STATUS      current
	DESCRIPTION
	"Table for tunnelDuplicates"
	::={tunnelDuplicates 4}

tunnelDuplicatesLevelEntry OBJECT-TYPE
	SYNTAX      TunnelDuplicatesLevelEntry
	MAX-ACCESS  not-accessible
	STATUS      current
	DESCRIPTION
	"Table entry for tunnelDuplicates"
	INDEX { tunnelDuplicatesLevelName }
	::={tunnelDuplicatesLevelTable 1}

TunnelDuplicatesLevelEntry ::=
	SEQUENCE {
		tunnelDuplicatesLevelName	DisplayString,
		tunnelDuplicatesLevelVal	Counter64,
		tunnelDuplicatesLevelMom	CounterBasedGauge64,
		tunnelDuplicatesLevelMax	CounterBasedGauge64
	}

tunnelDuplicatesLevelName OBJECT-TYPE
	SYNTAX      DisplayString
	MAX-ACCESS  not-accessible
	STATUS      current
	DESCRIPTION
	"Table entry display string for tunnelDuplicates"
	::={tunnelDuplicatesLevelEntry 1}

tunnelDuplicatesLevelVal OBJECT-TYPE
	SYNTAX	 Counter64
	MAX-ACCESS  read-only
	STATUS      current
	DESCRIPTION
	"Table entry attribute for tunnelDuplicates"
	::={tunnelDuplicatesLevelEntry 2}

tunnelDuplicatesLevelMom OBJECT-TYPE
	SYNTAX	 CounterBasedGauge64
	MAX-ACCESS  read-only
	STATUS      current
	DESCRIPTION
	"Table entry attribute for tunnelDuplicates"
	::={tunnelDuplicatesLevelEntry 3}

tunnelDuplicatesLevelMax OBJECT-TYPE
	SYNTAX	 CounterBasedGauge64
	MAX-ACCESS  read-only
	STATUS      current
	DESCRIPTION
	"Table entry attribute for tunnelDuplicates"
	::={tunnelDuplicatesLevelEntry 4}


tunnelGeneric	OBJECT IDENTIFIER ::={tunnel 8}

tunnelGenericVal	OBJECT-TYPE
	SYNTAX	 CounterBasedGauge64
	MAX-ACCESS read-only
	STATUS current
	DESCRIPTION "Generic Tunnel Contexts"

	::={tunnelGeneric 1}

tunnelGenericMax	OBJECT-TYPE
	SYNTAX	 CounterBasedGauge64
	MAX-ACCESS read-only
	STATUS current
	DESCRIPTION "Generic Tunnel Contexts"

	::={tunnelGeneric 3}

tunnelGenericLevelTable OBJECT-TYPE
	SYNTAX      SEQUENCE OF TunnelGenericLevelEntry
	MAX-ACCESS  not-accessible
	STATUS      current
	DESCRIPTION
	"Table for tunnelGeneric"
	::={tunnelGeneric 4}

tunnelGenericLevelEntry OBJECT-TYPE
	SYNTAX      TunnelGenericLevelEntry
	MAX-ACCESS  not-accessible
	STATUS      current
	DESCRIPTION
	"Table entry for tunnelGeneric"
	INDEX { tunnelGenericLevelName }
	::={tunnelGenericLevelTable 1}

TunnelGenericLevelEntry ::=
	SEQUENCE {
		tunnelGenericLevelName	DisplayString,
		tunnelGenericLevelVal	CounterBasedGauge64,
		tunnelGenericLevelMax	CounterBasedGauge64
	}

tunnelGenericLevelName OBJECT-TYPE
	SYNTAX      DisplayString
	MAX-ACCESS  not-accessible
	STATUS      current
	DESCRIPTION
	"Table entry display string for tunnelGeneric"
	::={tunnelGenericLevelEntry 1}

tunnelGenericLevelVal OBJECT-TYPE
	SYNTAX	 CounterBasedGauge64
	MAX-ACCESS  read-only
	STATUS      current
	DESCRIPTION
	"Table entry attribute for tunnelGeneric"
	::={tunnelGenericLevelEntry 2}

tunnelGenericLevelMax OBJECT-TYPE
	SYNTAX	 CounterBasedGauge64
	MAX-ACCESS  read-only
	STATUS      current
	DESCRIPTION
	"Table entry attribute for tunnelGeneric"
	::={tunnelGenericLevelEntry 4}


tunnelKnownPkts	OBJECT IDENTIFIER ::={tunnel 9}

tunnelKnownPktsVal	OBJECT-TYPE
	SYNTAX	 Counter64
	MAX-ACCESS read-only
	STATUS current
	DESCRIPTION "Packets For Known Tunnels"

	::={tunnelKnownPkts 1}

tunnelKnownPktsMom	OBJECT-TYPE
	SYNTAX	 CounterBasedGauge64
	MAX-ACCESS read-only
	STATUS current
	DESCRIPTION "Packets For Known Tunnels"

	::={tunnelKnownPkts 2}

tunnelKnownPktsMax	OBJECT-TYPE
	SYNTAX	 CounterBasedGauge64
	MAX-ACCESS read-only
	STATUS current
	DESCRIPTION "Packets For Known Tunnels"

	::={tunnelKnownPkts 3}

tunnelKnownPktsLevelTable OBJECT-TYPE
	SYNTAX      SEQUENCE OF TunnelKnownPktsLevelEntry
	MAX-ACCESS  not-accessible
	STATUS      current
	DESCRIPTION
	"Table for tunnelKnownPkts"
	::={tunnelKnownPkts 4}

tunnelKnownPktsLevelEntry OBJECT-TYPE
	SYNTAX      TunnelKnownPktsLevelEntry
	MAX-ACCESS  not-accessible
	STATUS      current
	DESCRIPTION
	"Table entry for tunnelKnownPkts"
	INDEX { tunnelKnownPktsLevelName }
	::={tunnelKnownPktsLevelTable 1}

TunnelKnownPktsLevelEntry ::=
	SEQUENCE {
		tunnelKnownPktsLevelName	DisplayString,
		tunnelKnownPktsLevelVal	Counter64,
		tunnelKnownPktsLevelMom	CounterBasedGauge64,
		tunnelKnownPktsLevelMax	CounterBasedGauge64
	}

tunnelKnownPktsLevelName OBJECT-TYPE
	SYNTAX      DisplayString
	MAX-ACCESS  not-accessible
	STATUS      current
	DESCRIPTION
	"Table entry display string for tunnelKnownPkts"
	::={tunnelKnownPktsLevelEntry 1}

tunnelKnownPktsLevelVal OBJECT-TYPE
	SYNTAX	 Counter64
	MAX-ACCESS  read-only
	STATUS      current
	DESCRIPTION
	"Table entry attribute for tunnelKnownPkts"
	::={tunnelKnownPktsLevelEntry 2}

tunnelKnownPktsLevelMom OBJECT-TYPE
	SYNTAX	 CounterBasedGauge64
	MAX-ACCESS  read-only
	STATUS      current
	DESCRIPTION
	"Table entry attribute for tunnelKnownPkts"
	::={tunnelKnownPktsLevelEntry 3}

tunnelKnownPktsLevelMax OBJECT-TYPE
	SYNTAX	 CounterBasedGauge64
	MAX-ACCESS  read-only
	STATUS      current
	DESCRIPTION
	"Table entry attribute for tunnelKnownPkts"
	::={tunnelKnownPktsLevelEntry 4}


tunnelL2tp	OBJECT IDENTIFIER ::={tunnel 10}

tunnelL2tpVal	OBJECT-TYPE
	SYNTAX	 CounterBasedGauge64
	MAX-ACCESS read-only
	STATUS current
	DESCRIPTION "L2TP Tunnel Contexts"

	::={tunnelL2tp 1}

tunnelL2tpMax	OBJECT-TYPE
	SYNTAX	 CounterBasedGauge64
	MAX-ACCESS read-only
	STATUS current
	DESCRIPTION "L2TP Tunnel Contexts"

	::={tunnelL2tp 3}

tunnelL2tpLevelTable OBJECT-TYPE
	SYNTAX      SEQUENCE OF TunnelL2tpLevelEntry
	MAX-ACCESS  not-accessible
	STATUS      current
	DESCRIPTION
	"Table for tunnelL2tp"
	::={tunnelL2tp 4}

tunnelL2tpLevelEntry OBJECT-TYPE
	SYNTAX      TunnelL2tpLevelEntry
	MAX-ACCESS  not-accessible
	STATUS      current
	DESCRIPTION
	"Table entry for tunnelL2tp"
	INDEX { tunnelL2tpLevelName }
	::={tunnelL2tpLevelTable 1}

TunnelL2tpLevelEntry ::=
	SEQUENCE {
		tunnelL2tpLevelName	DisplayString,
		tunnelL2tpLevelVal	CounterBasedGauge64,
		tunnelL2tpLevelMax	CounterBasedGauge64
	}

tunnelL2tpLevelName OBJECT-TYPE
	SYNTAX      DisplayString
	MAX-ACCESS  not-accessible
	STATUS      current
	DESCRIPTION
	"Table entry display string for tunnelL2tp"
	::={tunnelL2tpLevelEntry 1}

tunnelL2tpLevelVal OBJECT-TYPE
	SYNTAX	 CounterBasedGauge64
	MAX-ACCESS  read-only
	STATUS      current
	DESCRIPTION
	"Table entry attribute for tunnelL2tp"
	::={tunnelL2tpLevelEntry 2}

tunnelL2tpLevelMax OBJECT-TYPE
	SYNTAX	 CounterBasedGauge64
	MAX-ACCESS  read-only
	STATUS      current
	DESCRIPTION
	"Table entry attribute for tunnelL2tp"
	::={tunnelL2tpLevelEntry 4}


tunnelContextsUsed	OBJECT IDENTIFIER ::={tunnel 11}

tunnelContextsUsedVal	OBJECT-TYPE
	SYNTAX	 CounterBasedGauge64
	MAX-ACCESS read-only
	STATUS current
	DESCRIPTION "Contexts used"

	::={tunnelContextsUsed 1}

tunnelContextsUsedMax	OBJECT-TYPE
	SYNTAX	 CounterBasedGauge64
	MAX-ACCESS read-only
	STATUS current
	DESCRIPTION "Contexts used"

	::={tunnelContextsUsed 3}

tunnelContextsUsedLevelTable OBJECT-TYPE
	SYNTAX      SEQUENCE OF TunnelContextsUsedLevelEntry
	MAX-ACCESS  not-accessible
	STATUS      current
	DESCRIPTION
	"Table for tunnelContextsUsed"
	::={tunnelContextsUsed 4}

tunnelContextsUsedLevelEntry OBJECT-TYPE
	SYNTAX      TunnelContextsUsedLevelEntry
	MAX-ACCESS  not-accessible
	STATUS      current
	DESCRIPTION
	"Table entry for tunnelContextsUsed"
	INDEX { tunnelContextsUsedLevelName }
	::={tunnelContextsUsedLevelTable 1}

TunnelContextsUsedLevelEntry ::=
	SEQUENCE {
		tunnelContextsUsedLevelName	DisplayString,
		tunnelContextsUsedLevelVal	CounterBasedGauge64,
		tunnelContextsUsedLevelMax	CounterBasedGauge64
	}

tunnelContextsUsedLevelName OBJECT-TYPE
	SYNTAX      DisplayString
	MAX-ACCESS  not-accessible
	STATUS      current
	DESCRIPTION
	"Table entry display string for tunnelContextsUsed"
	::={tunnelContextsUsedLevelEntry 1}

tunnelContextsUsedLevelVal OBJECT-TYPE
	SYNTAX	 CounterBasedGauge64
	MAX-ACCESS  read-only
	STATUS      current
	DESCRIPTION
	"Table entry attribute for tunnelContextsUsed"
	::={tunnelContextsUsedLevelEntry 2}

tunnelContextsUsedLevelMax OBJECT-TYPE
	SYNTAX	 CounterBasedGauge64
	MAX-ACCESS  read-only
	STATUS      current
	DESCRIPTION
	"Table entry attribute for tunnelContextsUsed"
	::={tunnelContextsUsedLevelEntry 4}


tunnelContextAllocationFailures	OBJECT IDENTIFIER ::={tunnel 12}

tunnelContextAllocationFailuresVal	OBJECT-TYPE
	SYNTAX	 Counter64
	MAX-ACCESS read-only
	STATUS current
	DESCRIPTION "Context allocation failures"

	::={tunnelContextAllocationFailures 1}

tunnelContextAllocationFailuresMom	OBJECT-TYPE
	SYNTAX	 CounterBasedGauge64
	MAX-ACCESS read-only
	STATUS current
	DESCRIPTION "Context allocation failures"

	::={tunnelContextAllocationFailures 2}

tunnelContextAllocationFailuresMax	OBJECT-TYPE
	SYNTAX	 CounterBasedGauge64
	MAX-ACCESS read-only
	STATUS current
	DESCRIPTION "Context allocation failures"

	::={tunnelContextAllocationFailures 3}

tunnelContextAllocationFailuresLevelTable OBJECT-TYPE
	SYNTAX      SEQUENCE OF TunnelContextAllocationFailuresLevelEntry
	MAX-ACCESS  not-accessible
	STATUS      current
	DESCRIPTION
	"Table for tunnelContextAllocationFailures"
	::={tunnelContextAllocationFailures 4}

tunnelContextAllocationFailuresLevelEntry OBJECT-TYPE
	SYNTAX      TunnelContextAllocationFailuresLevelEntry
	MAX-ACCESS  not-accessible
	STATUS      current
	DESCRIPTION
	"Table entry for tunnelContextAllocationFailures"
	INDEX { tunnelContextAllocationFailuresLevelName }
	::={tunnelContextAllocationFailuresLevelTable 1}

TunnelContextAllocationFailuresLevelEntry ::=
	SEQUENCE {
		tunnelContextAllocationFailuresLevelName	DisplayString,
		tunnelContextAllocationFailuresLevelVal	Counter64,
		tunnelContextAllocationFailuresLevelMom	CounterBasedGauge64,
		tunnelContextAllocationFailuresLevelMax	CounterBasedGauge64
	}

tunnelContextAllocationFailuresLevelName OBJECT-TYPE
	SYNTAX      DisplayString
	MAX-ACCESS  not-accessible
	STATUS      current
	DESCRIPTION
	"Table entry display string for tunnelContextAllocationFailures"
	::={tunnelContextAllocationFailuresLevelEntry 1}

tunnelContextAllocationFailuresLevelVal OBJECT-TYPE
	SYNTAX	 Counter64
	MAX-ACCESS  read-only
	STATUS      current
	DESCRIPTION
	"Table entry attribute for tunnelContextAllocationFailures"
	::={tunnelContextAllocationFailuresLevelEntry 2}

tunnelContextAllocationFailuresLevelMom OBJECT-TYPE
	SYNTAX	 CounterBasedGauge64
	MAX-ACCESS  read-only
	STATUS      current
	DESCRIPTION
	"Table entry attribute for tunnelContextAllocationFailures"
	::={tunnelContextAllocationFailuresLevelEntry 3}

tunnelContextAllocationFailuresLevelMax OBJECT-TYPE
	SYNTAX	 CounterBasedGauge64
	MAX-ACCESS  read-only
	STATUS      current
	DESCRIPTION
	"Table entry attribute for tunnelContextAllocationFailures"
	::={tunnelContextAllocationFailuresLevelEntry 4}


tunnelL2tpPaired	OBJECT IDENTIFIER ::={tunnel 13}

tunnelL2tpPairedVal	OBJECT-TYPE
	SYNTAX	 CounterBasedGauge64
	MAX-ACCESS read-only
	STATUS current
	DESCRIPTION "L2TP paired Tunnel Contexts"

	::={tunnelL2tpPaired 1}

tunnelL2tpPairedMax	OBJECT-TYPE
	SYNTAX	 CounterBasedGauge64
	MAX-ACCESS read-only
	STATUS current
	DESCRIPTION "L2TP paired Tunnel Contexts"

	::={tunnelL2tpPaired 3}

tunnelL2tpPairedLevelTable OBJECT-TYPE
	SYNTAX      SEQUENCE OF TunnelL2tpPairedLevelEntry
	MAX-ACCESS  not-accessible
	STATUS      current
	DESCRIPTION
	"Table for tunnelL2tpPaired"
	::={tunnelL2tpPaired 4}

tunnelL2tpPairedLevelEntry OBJECT-TYPE
	SYNTAX      TunnelL2tpPairedLevelEntry
	MAX-ACCESS  not-accessible
	STATUS      current
	DESCRIPTION
	"Table entry for tunnelL2tpPaired"
	INDEX { tunnelL2tpPairedLevelName }
	::={tunnelL2tpPairedLevelTable 1}

TunnelL2tpPairedLevelEntry ::=
	SEQUENCE {
		tunnelL2tpPairedLevelName	DisplayString,
		tunnelL2tpPairedLevelVal	CounterBasedGauge64,
		tunnelL2tpPairedLevelMax	CounterBasedGauge64
	}

tunnelL2tpPairedLevelName OBJECT-TYPE
	SYNTAX      DisplayString
	MAX-ACCESS  not-accessible
	STATUS      current
	DESCRIPTION
	"Table entry display string for tunnelL2tpPaired"
	::={tunnelL2tpPairedLevelEntry 1}

tunnelL2tpPairedLevelVal OBJECT-TYPE
	SYNTAX	 CounterBasedGauge64
	MAX-ACCESS  read-only
	STATUS      current
	DESCRIPTION
	"Table entry attribute for tunnelL2tpPaired"
	::={tunnelL2tpPairedLevelEntry 2}

tunnelL2tpPairedLevelMax OBJECT-TYPE
	SYNTAX	 CounterBasedGauge64
	MAX-ACCESS  read-only
	STATUS      current
	DESCRIPTION
	"Table entry attribute for tunnelL2tpPaired"
	::={tunnelL2tpPairedLevelEntry 4}


gre	OBJECT IDENTIFIER ::={sysdiag 131}

grePackets	OBJECT IDENTIFIER ::={gre 2}

grePacketsVal	OBJECT-TYPE
	SYNTAX	 Counter64
	MAX-ACCESS read-only
	STATUS current
	DESCRIPTION "RX packets"

	::={grePackets 1}

grePacketsMom	OBJECT-TYPE
	SYNTAX	 CounterBasedGauge64
	MAX-ACCESS read-only
	STATUS current
	DESCRIPTION "RX packets"

	::={grePackets 2}

grePacketsMax	OBJECT-TYPE
	SYNTAX	 CounterBasedGauge64
	MAX-ACCESS read-only
	STATUS current
	DESCRIPTION "RX packets"

	::={grePackets 3}

grePacketsLevelTable OBJECT-TYPE
	SYNTAX      SEQUENCE OF GrePacketsLevelEntry
	MAX-ACCESS  not-accessible
	STATUS      current
	DESCRIPTION
	"Table for grePackets"
	::={grePackets 4}

grePacketsLevelEntry OBJECT-TYPE
	SYNTAX      GrePacketsLevelEntry
	MAX-ACCESS  not-accessible
	STATUS      current
	DESCRIPTION
	"Table entry for grePackets"
	INDEX { grePacketsLevelName }
	::={grePacketsLevelTable 1}

GrePacketsLevelEntry ::=
	SEQUENCE {
		grePacketsLevelName	DisplayString,
		grePacketsLevelVal	Counter64,
		grePacketsLevelMom	CounterBasedGauge64,
		grePacketsLevelMax	CounterBasedGauge64
	}

grePacketsLevelName OBJECT-TYPE
	SYNTAX      DisplayString
	MAX-ACCESS  not-accessible
	STATUS      current
	DESCRIPTION
	"Table entry display string for grePackets"
	::={grePacketsLevelEntry 1}

grePacketsLevelVal OBJECT-TYPE
	SYNTAX	 Counter64
	MAX-ACCESS  read-only
	STATUS      current
	DESCRIPTION
	"Table entry attribute for grePackets"
	::={grePacketsLevelEntry 2}

grePacketsLevelMom OBJECT-TYPE
	SYNTAX	 CounterBasedGauge64
	MAX-ACCESS  read-only
	STATUS      current
	DESCRIPTION
	"Table entry attribute for grePackets"
	::={grePacketsLevelEntry 3}

grePacketsLevelMax OBJECT-TYPE
	SYNTAX	 CounterBasedGauge64
	MAX-ACCESS  read-only
	STATUS      current
	DESCRIPTION
	"Table entry attribute for grePackets"
	::={grePacketsLevelEntry 4}


greBytes	OBJECT IDENTIFIER ::={gre 3}

greBytesVal	OBJECT-TYPE
	SYNTAX	 Counter64
	MAX-ACCESS read-only
	STATUS current
	DESCRIPTION "RX data"

	::={greBytes 1}

greBytesMom	OBJECT-TYPE
	SYNTAX	 CounterBasedGauge64
	MAX-ACCESS read-only
	STATUS current
	DESCRIPTION "RX data"

	::={greBytes 2}

greBytesMax	OBJECT-TYPE
	SYNTAX	 CounterBasedGauge64
	MAX-ACCESS read-only
	STATUS current
	DESCRIPTION "RX data"

	::={greBytes 3}

greBytesLevelTable OBJECT-TYPE
	SYNTAX      SEQUENCE OF GreBytesLevelEntry
	MAX-ACCESS  not-accessible
	STATUS      current
	DESCRIPTION
	"Table for greBytes"
	::={greBytes 4}

greBytesLevelEntry OBJECT-TYPE
	SYNTAX      GreBytesLevelEntry
	MAX-ACCESS  not-accessible
	STATUS      current
	DESCRIPTION
	"Table entry for greBytes"
	INDEX { greBytesLevelName }
	::={greBytesLevelTable 1}

GreBytesLevelEntry ::=
	SEQUENCE {
		greBytesLevelName	DisplayString,
		greBytesLevelVal	Counter64,
		greBytesLevelMom	CounterBasedGauge64,
		greBytesLevelMax	CounterBasedGauge64
	}

greBytesLevelName OBJECT-TYPE
	SYNTAX      DisplayString
	MAX-ACCESS  not-accessible
	STATUS      current
	DESCRIPTION
	"Table entry display string for greBytes"
	::={greBytesLevelEntry 1}

greBytesLevelVal OBJECT-TYPE
	SYNTAX	 Counter64
	MAX-ACCESS  read-only
	STATUS      current
	DESCRIPTION
	"Table entry attribute for greBytes"
	::={greBytesLevelEntry 2}

greBytesLevelMom OBJECT-TYPE
	SYNTAX	 CounterBasedGauge64
	MAX-ACCESS  read-only
	STATUS      current
	DESCRIPTION
	"Table entry attribute for greBytes"
	::={greBytesLevelEntry 3}

greBytesLevelMax OBJECT-TYPE
	SYNTAX	 CounterBasedGauge64
	MAX-ACCESS  read-only
	STATUS      current
	DESCRIPTION
	"Table entry attribute for greBytes"
	::={greBytesLevelEntry 4}


greUnknownVersion	OBJECT IDENTIFIER ::={gre 4}

greUnknownVersionVal	OBJECT-TYPE
	SYNTAX	 Counter64
	MAX-ACCESS read-only
	STATUS current
	DESCRIPTION "GRE Packets with unknown version"

	::={greUnknownVersion 1}

greUnknownVersionMom	OBJECT-TYPE
	SYNTAX	 CounterBasedGauge64
	MAX-ACCESS read-only
	STATUS current
	DESCRIPTION "GRE Packets with unknown version"

	::={greUnknownVersion 2}

greUnknownVersionMax	OBJECT-TYPE
	SYNTAX	 CounterBasedGauge64
	MAX-ACCESS read-only
	STATUS current
	DESCRIPTION "GRE Packets with unknown version"

	::={greUnknownVersion 3}

greUnknownVersionLevelTable OBJECT-TYPE
	SYNTAX      SEQUENCE OF GreUnknownVersionLevelEntry
	MAX-ACCESS  not-accessible
	STATUS      current
	DESCRIPTION
	"Table for greUnknownVersion"
	::={greUnknownVersion 4}

greUnknownVersionLevelEntry OBJECT-TYPE
	SYNTAX      GreUnknownVersionLevelEntry
	MAX-ACCESS  not-accessible
	STATUS      current
	DESCRIPTION
	"Table entry for greUnknownVersion"
	INDEX { greUnknownVersionLevelName }
	::={greUnknownVersionLevelTable 1}

GreUnknownVersionLevelEntry ::=
	SEQUENCE {
		greUnknownVersionLevelName	DisplayString,
		greUnknownVersionLevelVal	Counter64,
		greUnknownVersionLevelMom	CounterBasedGauge64,
		greUnknownVersionLevelMax	CounterBasedGauge64
	}

greUnknownVersionLevelName OBJECT-TYPE
	SYNTAX      DisplayString
	MAX-ACCESS  not-accessible
	STATUS      current
	DESCRIPTION
	"Table entry display string for greUnknownVersion"
	::={greUnknownVersionLevelEntry 1}

greUnknownVersionLevelVal OBJECT-TYPE
	SYNTAX	 Counter64
	MAX-ACCESS  read-only
	STATUS      current
	DESCRIPTION
	"Table entry attribute for greUnknownVersion"
	::={greUnknownVersionLevelEntry 2}

greUnknownVersionLevelMom OBJECT-TYPE
	SYNTAX	 CounterBasedGauge64
	MAX-ACCESS  read-only
	STATUS      current
	DESCRIPTION
	"Table entry attribute for greUnknownVersion"
	::={greUnknownVersionLevelEntry 3}

greUnknownVersionLevelMax OBJECT-TYPE
	SYNTAX	 CounterBasedGauge64
	MAX-ACCESS  read-only
	STATUS      current
	DESCRIPTION
	"Table entry attribute for greUnknownVersion"
	::={greUnknownVersionLevelEntry 4}


greShortPackets	OBJECT IDENTIFIER ::={gre 5}

greShortPacketsVal	OBJECT-TYPE
	SYNTAX	 Counter64
	MAX-ACCESS read-only
	STATUS current
	DESCRIPTION "Too Short GRE Packets"

	::={greShortPackets 1}

greShortPacketsMom	OBJECT-TYPE
	SYNTAX	 CounterBasedGauge64
	MAX-ACCESS read-only
	STATUS current
	DESCRIPTION "Too Short GRE Packets"

	::={greShortPackets 2}

greShortPacketsMax	OBJECT-TYPE
	SYNTAX	 CounterBasedGauge64
	MAX-ACCESS read-only
	STATUS current
	DESCRIPTION "Too Short GRE Packets"

	::={greShortPackets 3}

greShortPacketsLevelTable OBJECT-TYPE
	SYNTAX      SEQUENCE OF GreShortPacketsLevelEntry
	MAX-ACCESS  not-accessible
	STATUS      current
	DESCRIPTION
	"Table for greShortPackets"
	::={greShortPackets 4}

greShortPacketsLevelEntry OBJECT-TYPE
	SYNTAX      GreShortPacketsLevelEntry
	MAX-ACCESS  not-accessible
	STATUS      current
	DESCRIPTION
	"Table entry for greShortPackets"
	INDEX { greShortPacketsLevelName }
	::={greShortPacketsLevelTable 1}

GreShortPacketsLevelEntry ::=
	SEQUENCE {
		greShortPacketsLevelName	DisplayString,
		greShortPacketsLevelVal	Counter64,
		greShortPacketsLevelMom	CounterBasedGauge64,
		greShortPacketsLevelMax	CounterBasedGauge64
	}

greShortPacketsLevelName OBJECT-TYPE
	SYNTAX      DisplayString
	MAX-ACCESS  not-accessible
	STATUS      current
	DESCRIPTION
	"Table entry display string for greShortPackets"
	::={greShortPacketsLevelEntry 1}

greShortPacketsLevelVal OBJECT-TYPE
	SYNTAX	 Counter64
	MAX-ACCESS  read-only
	STATUS      current
	DESCRIPTION
	"Table entry attribute for greShortPackets"
	::={greShortPacketsLevelEntry 2}

greShortPacketsLevelMom OBJECT-TYPE
	SYNTAX	 CounterBasedGauge64
	MAX-ACCESS  read-only
	STATUS      current
	DESCRIPTION
	"Table entry attribute for greShortPackets"
	::={greShortPacketsLevelEntry 3}

greShortPacketsLevelMax OBJECT-TYPE
	SYNTAX	 CounterBasedGauge64
	MAX-ACCESS  read-only
	STATUS      current
	DESCRIPTION
	"Table entry attribute for greShortPackets"
	::={greShortPacketsLevelEntry 4}


greUnknownType	OBJECT IDENTIFIER ::={gre 6}

greUnknownTypeVal	OBJECT-TYPE
	SYNTAX	 Counter64
	MAX-ACCESS read-only
	STATUS current
	DESCRIPTION "GRE packets with unkown type"

	::={greUnknownType 1}

greUnknownTypeMom	OBJECT-TYPE
	SYNTAX	 CounterBasedGauge64
	MAX-ACCESS read-only
	STATUS current
	DESCRIPTION "GRE packets with unkown type"

	::={greUnknownType 2}

greUnknownTypeMax	OBJECT-TYPE
	SYNTAX	 CounterBasedGauge64
	MAX-ACCESS read-only
	STATUS current
	DESCRIPTION "GRE packets with unkown type"

	::={greUnknownType 3}

greUnknownTypeLevelTable OBJECT-TYPE
	SYNTAX      SEQUENCE OF GreUnknownTypeLevelEntry
	MAX-ACCESS  not-accessible
	STATUS      current
	DESCRIPTION
	"Table for greUnknownType"
	::={greUnknownType 4}

greUnknownTypeLevelEntry OBJECT-TYPE
	SYNTAX      GreUnknownTypeLevelEntry
	MAX-ACCESS  not-accessible
	STATUS      current
	DESCRIPTION
	"Table entry for greUnknownType"
	INDEX { greUnknownTypeLevelName }
	::={greUnknownTypeLevelTable 1}

GreUnknownTypeLevelEntry ::=
	SEQUENCE {
		greUnknownTypeLevelName	DisplayString,
		greUnknownTypeLevelVal	Counter64,
		greUnknownTypeLevelMom	CounterBasedGauge64,
		greUnknownTypeLevelMax	CounterBasedGauge64
	}

greUnknownTypeLevelName OBJECT-TYPE
	SYNTAX      DisplayString
	MAX-ACCESS  not-accessible
	STATUS      current
	DESCRIPTION
	"Table entry display string for greUnknownType"
	::={greUnknownTypeLevelEntry 1}

greUnknownTypeLevelVal OBJECT-TYPE
	SYNTAX	 Counter64
	MAX-ACCESS  read-only
	STATUS      current
	DESCRIPTION
	"Table entry attribute for greUnknownType"
	::={greUnknownTypeLevelEntry 2}

greUnknownTypeLevelMom OBJECT-TYPE
	SYNTAX	 CounterBasedGauge64
	MAX-ACCESS  read-only
	STATUS      current
	DESCRIPTION
	"Table entry attribute for greUnknownType"
	::={greUnknownTypeLevelEntry 3}

greUnknownTypeLevelMax OBJECT-TYPE
	SYNTAX	 CounterBasedGauge64
	MAX-ACCESS  read-only
	STATUS      current
	DESCRIPTION
	"Table entry attribute for greUnknownType"
	::={greUnknownTypeLevelEntry 4}


greRouteFlag	OBJECT IDENTIFIER ::={gre 7}

greRouteFlagVal	OBJECT-TYPE
	SYNTAX	 Counter64
	MAX-ACCESS read-only
	STATUS current
	DESCRIPTION "GRE packets with depricated route flag"

	::={greRouteFlag 1}

greRouteFlagMom	OBJECT-TYPE
	SYNTAX	 CounterBasedGauge64
	MAX-ACCESS read-only
	STATUS current
	DESCRIPTION "GRE packets with depricated route flag"

	::={greRouteFlag 2}

greRouteFlagMax	OBJECT-TYPE
	SYNTAX	 CounterBasedGauge64
	MAX-ACCESS read-only
	STATUS current
	DESCRIPTION "GRE packets with depricated route flag"

	::={greRouteFlag 3}

greRouteFlagLevelTable OBJECT-TYPE
	SYNTAX      SEQUENCE OF GreRouteFlagLevelEntry
	MAX-ACCESS  not-accessible
	STATUS      current
	DESCRIPTION
	"Table for greRouteFlag"
	::={greRouteFlag 4}

greRouteFlagLevelEntry OBJECT-TYPE
	SYNTAX      GreRouteFlagLevelEntry
	MAX-ACCESS  not-accessible
	STATUS      current
	DESCRIPTION
	"Table entry for greRouteFlag"
	INDEX { greRouteFlagLevelName }
	::={greRouteFlagLevelTable 1}

GreRouteFlagLevelEntry ::=
	SEQUENCE {
		greRouteFlagLevelName	DisplayString,
		greRouteFlagLevelVal	Counter64,
		greRouteFlagLevelMom	CounterBasedGauge64,
		greRouteFlagLevelMax	CounterBasedGauge64
	}

greRouteFlagLevelName OBJECT-TYPE
	SYNTAX      DisplayString
	MAX-ACCESS  not-accessible
	STATUS      current
	DESCRIPTION
	"Table entry display string for greRouteFlag"
	::={greRouteFlagLevelEntry 1}

greRouteFlagLevelVal OBJECT-TYPE
	SYNTAX	 Counter64
	MAX-ACCESS  read-only
	STATUS      current
	DESCRIPTION
	"Table entry attribute for greRouteFlag"
	::={greRouteFlagLevelEntry 2}

greRouteFlagLevelMom OBJECT-TYPE
	SYNTAX	 CounterBasedGauge64
	MAX-ACCESS  read-only
	STATUS      current
	DESCRIPTION
	"Table entry attribute for greRouteFlag"
	::={greRouteFlagLevelEntry 3}

greRouteFlagLevelMax OBJECT-TYPE
	SYNTAX	 CounterBasedGauge64
	MAX-ACCESS  read-only
	STATUS      current
	DESCRIPTION
	"Table entry attribute for greRouteFlag"
	::={greRouteFlagLevelEntry 4}


greIpv4Packets	OBJECT IDENTIFIER ::={gre 8}

greIpv4PacketsVal	OBJECT-TYPE
	SYNTAX	 Counter64
	MAX-ACCESS read-only
	STATUS current
	DESCRIPTION "IPv4 Type packets"

	::={greIpv4Packets 1}

greIpv4PacketsMom	OBJECT-TYPE
	SYNTAX	 CounterBasedGauge64
	MAX-ACCESS read-only
	STATUS current
	DESCRIPTION "IPv4 Type packets"

	::={greIpv4Packets 2}

greIpv4PacketsMax	OBJECT-TYPE
	SYNTAX	 CounterBasedGauge64
	MAX-ACCESS read-only
	STATUS current
	DESCRIPTION "IPv4 Type packets"

	::={greIpv4Packets 3}

greIpv4PacketsLevelTable OBJECT-TYPE
	SYNTAX      SEQUENCE OF GreIpv4PacketsLevelEntry
	MAX-ACCESS  not-accessible
	STATUS      current
	DESCRIPTION
	"Table for greIpv4Packets"
	::={greIpv4Packets 4}

greIpv4PacketsLevelEntry OBJECT-TYPE
	SYNTAX      GreIpv4PacketsLevelEntry
	MAX-ACCESS  not-accessible
	STATUS      current
	DESCRIPTION
	"Table entry for greIpv4Packets"
	INDEX { greIpv4PacketsLevelName }
	::={greIpv4PacketsLevelTable 1}

GreIpv4PacketsLevelEntry ::=
	SEQUENCE {
		greIpv4PacketsLevelName	DisplayString,
		greIpv4PacketsLevelVal	Counter64,
		greIpv4PacketsLevelMom	CounterBasedGauge64,
		greIpv4PacketsLevelMax	CounterBasedGauge64
	}

greIpv4PacketsLevelName OBJECT-TYPE
	SYNTAX      DisplayString
	MAX-ACCESS  not-accessible
	STATUS      current
	DESCRIPTION
	"Table entry display string for greIpv4Packets"
	::={greIpv4PacketsLevelEntry 1}

greIpv4PacketsLevelVal OBJECT-TYPE
	SYNTAX	 Counter64
	MAX-ACCESS  read-only
	STATUS      current
	DESCRIPTION
	"Table entry attribute for greIpv4Packets"
	::={greIpv4PacketsLevelEntry 2}

greIpv4PacketsLevelMom OBJECT-TYPE
	SYNTAX	 CounterBasedGauge64
	MAX-ACCESS  read-only
	STATUS      current
	DESCRIPTION
	"Table entry attribute for greIpv4Packets"
	::={greIpv4PacketsLevelEntry 3}

greIpv4PacketsLevelMax OBJECT-TYPE
	SYNTAX	 CounterBasedGauge64
	MAX-ACCESS  read-only
	STATUS      current
	DESCRIPTION
	"Table entry attribute for greIpv4Packets"
	::={greIpv4PacketsLevelEntry 4}


greIpv6Packets	OBJECT IDENTIFIER ::={gre 9}

greIpv6PacketsVal	OBJECT-TYPE
	SYNTAX	 Counter64
	MAX-ACCESS read-only
	STATUS current
	DESCRIPTION "IPv6 Type packets"

	::={greIpv6Packets 1}

greIpv6PacketsMom	OBJECT-TYPE
	SYNTAX	 CounterBasedGauge64
	MAX-ACCESS read-only
	STATUS current
	DESCRIPTION "IPv6 Type packets"

	::={greIpv6Packets 2}

greIpv6PacketsMax	OBJECT-TYPE
	SYNTAX	 CounterBasedGauge64
	MAX-ACCESS read-only
	STATUS current
	DESCRIPTION "IPv6 Type packets"

	::={greIpv6Packets 3}

greIpv6PacketsLevelTable OBJECT-TYPE
	SYNTAX      SEQUENCE OF GreIpv6PacketsLevelEntry
	MAX-ACCESS  not-accessible
	STATUS      current
	DESCRIPTION
	"Table for greIpv6Packets"
	::={greIpv6Packets 4}

greIpv6PacketsLevelEntry OBJECT-TYPE
	SYNTAX      GreIpv6PacketsLevelEntry
	MAX-ACCESS  not-accessible
	STATUS      current
	DESCRIPTION
	"Table entry for greIpv6Packets"
	INDEX { greIpv6PacketsLevelName }
	::={greIpv6PacketsLevelTable 1}

GreIpv6PacketsLevelEntry ::=
	SEQUENCE {
		greIpv6PacketsLevelName	DisplayString,
		greIpv6PacketsLevelVal	Counter64,
		greIpv6PacketsLevelMom	CounterBasedGauge64,
		greIpv6PacketsLevelMax	CounterBasedGauge64
	}

greIpv6PacketsLevelName OBJECT-TYPE
	SYNTAX      DisplayString
	MAX-ACCESS  not-accessible
	STATUS      current
	DESCRIPTION
	"Table entry display string for greIpv6Packets"
	::={greIpv6PacketsLevelEntry 1}

greIpv6PacketsLevelVal OBJECT-TYPE
	SYNTAX	 Counter64
	MAX-ACCESS  read-only
	STATUS      current
	DESCRIPTION
	"Table entry attribute for greIpv6Packets"
	::={greIpv6PacketsLevelEntry 2}

greIpv6PacketsLevelMom OBJECT-TYPE
	SYNTAX	 CounterBasedGauge64
	MAX-ACCESS  read-only
	STATUS      current
	DESCRIPTION
	"Table entry attribute for greIpv6Packets"
	::={greIpv6PacketsLevelEntry 3}

greIpv6PacketsLevelMax OBJECT-TYPE
	SYNTAX	 CounterBasedGauge64
	MAX-ACCESS  read-only
	STATUS      current
	DESCRIPTION
	"Table entry attribute for greIpv6Packets"
	::={greIpv6PacketsLevelEntry 4}


greFfffPackets	OBJECT IDENTIFIER ::={gre 10}

greFfffPacketsVal	OBJECT-TYPE
	SYNTAX	 Counter64
	MAX-ACCESS read-only
	STATUS current
	DESCRIPTION "0xffff Type packets"

	::={greFfffPackets 1}

greFfffPacketsMom	OBJECT-TYPE
	SYNTAX	 CounterBasedGauge64
	MAX-ACCESS read-only
	STATUS current
	DESCRIPTION "0xffff Type packets"

	::={greFfffPackets 2}

greFfffPacketsMax	OBJECT-TYPE
	SYNTAX	 CounterBasedGauge64
	MAX-ACCESS read-only
	STATUS current
	DESCRIPTION "0xffff Type packets"

	::={greFfffPackets 3}

greFfffPacketsLevelTable OBJECT-TYPE
	SYNTAX      SEQUENCE OF GreFfffPacketsLevelEntry
	MAX-ACCESS  not-accessible
	STATUS      current
	DESCRIPTION
	"Table for greFfffPackets"
	::={greFfffPackets 4}

greFfffPacketsLevelEntry OBJECT-TYPE
	SYNTAX      GreFfffPacketsLevelEntry
	MAX-ACCESS  not-accessible
	STATUS      current
	DESCRIPTION
	"Table entry for greFfffPackets"
	INDEX { greFfffPacketsLevelName }
	::={greFfffPacketsLevelTable 1}

GreFfffPacketsLevelEntry ::=
	SEQUENCE {
		greFfffPacketsLevelName	DisplayString,
		greFfffPacketsLevelVal	Counter64,
		greFfffPacketsLevelMom	CounterBasedGauge64,
		greFfffPacketsLevelMax	CounterBasedGauge64
	}

greFfffPacketsLevelName OBJECT-TYPE
	SYNTAX      DisplayString
	MAX-ACCESS  not-accessible
	STATUS      current
	DESCRIPTION
	"Table entry display string for greFfffPackets"
	::={greFfffPacketsLevelEntry 1}

greFfffPacketsLevelVal OBJECT-TYPE
	SYNTAX	 Counter64
	MAX-ACCESS  read-only
	STATUS      current
	DESCRIPTION
	"Table entry attribute for greFfffPackets"
	::={greFfffPacketsLevelEntry 2}

greFfffPacketsLevelMom OBJECT-TYPE
	SYNTAX	 CounterBasedGauge64
	MAX-ACCESS  read-only
	STATUS      current
	DESCRIPTION
	"Table entry attribute for greFfffPackets"
	::={greFfffPacketsLevelEntry 3}

greFfffPacketsLevelMax OBJECT-TYPE
	SYNTAX	 CounterBasedGauge64
	MAX-ACCESS  read-only
	STATUS      current
	DESCRIPTION
	"Table entry attribute for greFfffPackets"
	::={greFfffPacketsLevelEntry 4}


grePptpPackets	OBJECT IDENTIFIER ::={gre 11}

grePptpPacketsVal	OBJECT-TYPE
	SYNTAX	 Counter64
	MAX-ACCESS read-only
	STATUS current
	DESCRIPTION "PPTP Packets"

	::={grePptpPackets 1}

grePptpPacketsMom	OBJECT-TYPE
	SYNTAX	 CounterBasedGauge64
	MAX-ACCESS read-only
	STATUS current
	DESCRIPTION "PPTP Packets"

	::={grePptpPackets 2}

grePptpPacketsMax	OBJECT-TYPE
	SYNTAX	 CounterBasedGauge64
	MAX-ACCESS read-only
	STATUS current
	DESCRIPTION "PPTP Packets"

	::={grePptpPackets 3}

grePptpPacketsLevelTable OBJECT-TYPE
	SYNTAX      SEQUENCE OF GrePptpPacketsLevelEntry
	MAX-ACCESS  not-accessible
	STATUS      current
	DESCRIPTION
	"Table for grePptpPackets"
	::={grePptpPackets 4}

grePptpPacketsLevelEntry OBJECT-TYPE
	SYNTAX      GrePptpPacketsLevelEntry
	MAX-ACCESS  not-accessible
	STATUS      current
	DESCRIPTION
	"Table entry for grePptpPackets"
	INDEX { grePptpPacketsLevelName }
	::={grePptpPacketsLevelTable 1}

GrePptpPacketsLevelEntry ::=
	SEQUENCE {
		grePptpPacketsLevelName	DisplayString,
		grePptpPacketsLevelVal	Counter64,
		grePptpPacketsLevelMom	CounterBasedGauge64,
		grePptpPacketsLevelMax	CounterBasedGauge64
	}

grePptpPacketsLevelName OBJECT-TYPE
	SYNTAX      DisplayString
	MAX-ACCESS  not-accessible
	STATUS      current
	DESCRIPTION
	"Table entry display string for grePptpPackets"
	::={grePptpPacketsLevelEntry 1}

grePptpPacketsLevelVal OBJECT-TYPE
	SYNTAX	 Counter64
	MAX-ACCESS  read-only
	STATUS      current
	DESCRIPTION
	"Table entry attribute for grePptpPackets"
	::={grePptpPacketsLevelEntry 2}

grePptpPacketsLevelMom OBJECT-TYPE
	SYNTAX	 CounterBasedGauge64
	MAX-ACCESS  read-only
	STATUS      current
	DESCRIPTION
	"Table entry attribute for grePptpPackets"
	::={grePptpPacketsLevelEntry 3}

grePptpPacketsLevelMax OBJECT-TYPE
	SYNTAX	 CounterBasedGauge64
	MAX-ACCESS  read-only
	STATUS      current
	DESCRIPTION
	"Table entry attribute for grePptpPackets"
	::={grePptpPacketsLevelEntry 4}


grePppPackets	OBJECT IDENTIFIER ::={gre 12}

grePppPacketsVal	OBJECT-TYPE
	SYNTAX	 Counter64
	MAX-ACCESS read-only
	STATUS current
	DESCRIPTION "PPP Type Packets"

	::={grePppPackets 1}

grePppPacketsMom	OBJECT-TYPE
	SYNTAX	 CounterBasedGauge64
	MAX-ACCESS read-only
	STATUS current
	DESCRIPTION "PPP Type Packets"

	::={grePppPackets 2}

grePppPacketsMax	OBJECT-TYPE
	SYNTAX	 CounterBasedGauge64
	MAX-ACCESS read-only
	STATUS current
	DESCRIPTION "PPP Type Packets"

	::={grePppPackets 3}

grePppPacketsLevelTable OBJECT-TYPE
	SYNTAX      SEQUENCE OF GrePppPacketsLevelEntry
	MAX-ACCESS  not-accessible
	STATUS      current
	DESCRIPTION
	"Table for grePppPackets"
	::={grePppPackets 4}

grePppPacketsLevelEntry OBJECT-TYPE
	SYNTAX      GrePppPacketsLevelEntry
	MAX-ACCESS  not-accessible
	STATUS      current
	DESCRIPTION
	"Table entry for grePppPackets"
	INDEX { grePppPacketsLevelName }
	::={grePppPacketsLevelTable 1}

GrePppPacketsLevelEntry ::=
	SEQUENCE {
		grePppPacketsLevelName	DisplayString,
		grePppPacketsLevelVal	Counter64,
		grePppPacketsLevelMom	CounterBasedGauge64,
		grePppPacketsLevelMax	CounterBasedGauge64
	}

grePppPacketsLevelName OBJECT-TYPE
	SYNTAX      DisplayString
	MAX-ACCESS  not-accessible
	STATUS      current
	DESCRIPTION
	"Table entry display string for grePppPackets"
	::={grePppPacketsLevelEntry 1}

grePppPacketsLevelVal OBJECT-TYPE
	SYNTAX	 Counter64
	MAX-ACCESS  read-only
	STATUS      current
	DESCRIPTION
	"Table entry attribute for grePppPackets"
	::={grePppPacketsLevelEntry 2}

grePppPacketsLevelMom OBJECT-TYPE
	SYNTAX	 CounterBasedGauge64
	MAX-ACCESS  read-only
	STATUS      current
	DESCRIPTION
	"Table entry attribute for grePppPackets"
	::={grePppPacketsLevelEntry 3}

grePppPacketsLevelMax OBJECT-TYPE
	SYNTAX	 CounterBasedGauge64
	MAX-ACCESS  read-only
	STATUS      current
	DESCRIPTION
	"Table entry attribute for grePppPackets"
	::={grePppPacketsLevelEntry 4}


grePppUnknownPackets	OBJECT IDENTIFIER ::={gre 13}

grePppUnknownPacketsVal	OBJECT-TYPE
	SYNTAX	 Counter64
	MAX-ACCESS read-only
	STATUS current
	DESCRIPTION "PPP Type Packets with Unknown Protocol"

	::={grePppUnknownPackets 1}

grePppUnknownPacketsMom	OBJECT-TYPE
	SYNTAX	 CounterBasedGauge64
	MAX-ACCESS read-only
	STATUS current
	DESCRIPTION "PPP Type Packets with Unknown Protocol"

	::={grePppUnknownPackets 2}

grePppUnknownPacketsMax	OBJECT-TYPE
	SYNTAX	 CounterBasedGauge64
	MAX-ACCESS read-only
	STATUS current
	DESCRIPTION "PPP Type Packets with Unknown Protocol"

	::={grePppUnknownPackets 3}

grePppUnknownPacketsLevelTable OBJECT-TYPE
	SYNTAX      SEQUENCE OF GrePppUnknownPacketsLevelEntry
	MAX-ACCESS  not-accessible
	STATUS      current
	DESCRIPTION
	"Table for grePppUnknownPackets"
	::={grePppUnknownPackets 4}

grePppUnknownPacketsLevelEntry OBJECT-TYPE
	SYNTAX      GrePppUnknownPacketsLevelEntry
	MAX-ACCESS  not-accessible
	STATUS      current
	DESCRIPTION
	"Table entry for grePppUnknownPackets"
	INDEX { grePppUnknownPacketsLevelName }
	::={grePppUnknownPacketsLevelTable 1}

GrePppUnknownPacketsLevelEntry ::=
	SEQUENCE {
		grePppUnknownPacketsLevelName	DisplayString,
		grePppUnknownPacketsLevelVal	Counter64,
		grePppUnknownPacketsLevelMom	CounterBasedGauge64,
		grePppUnknownPacketsLevelMax	CounterBasedGauge64
	}

grePppUnknownPacketsLevelName OBJECT-TYPE
	SYNTAX      DisplayString
	MAX-ACCESS  not-accessible
	STATUS      current
	DESCRIPTION
	"Table entry display string for grePppUnknownPackets"
	::={grePppUnknownPacketsLevelEntry 1}

grePppUnknownPacketsLevelVal OBJECT-TYPE
	SYNTAX	 Counter64
	MAX-ACCESS  read-only
	STATUS      current
	DESCRIPTION
	"Table entry attribute for grePppUnknownPackets"
	::={grePppUnknownPacketsLevelEntry 2}

grePppUnknownPacketsLevelMom OBJECT-TYPE
	SYNTAX	 CounterBasedGauge64
	MAX-ACCESS  read-only
	STATUS      current
	DESCRIPTION
	"Table entry attribute for grePppUnknownPackets"
	::={grePppUnknownPacketsLevelEntry 3}

grePppUnknownPacketsLevelMax OBJECT-TYPE
	SYNTAX	 CounterBasedGauge64
	MAX-ACCESS  read-only
	STATUS      current
	DESCRIPTION
	"Table entry attribute for grePppUnknownPackets"
	::={grePppUnknownPacketsLevelEntry 4}


greEthernetPackets	OBJECT IDENTIFIER ::={gre 14}

greEthernetPacketsVal	OBJECT-TYPE
	SYNTAX	 Counter64
	MAX-ACCESS read-only
	STATUS current
	DESCRIPTION "Ethernet type packets"

	::={greEthernetPackets 1}

greEthernetPacketsMom	OBJECT-TYPE
	SYNTAX	 CounterBasedGauge64
	MAX-ACCESS read-only
	STATUS current
	DESCRIPTION "Ethernet type packets"

	::={greEthernetPackets 2}

greEthernetPacketsMax	OBJECT-TYPE
	SYNTAX	 CounterBasedGauge64
	MAX-ACCESS read-only
	STATUS current
	DESCRIPTION "Ethernet type packets"

	::={greEthernetPackets 3}

greEthernetPacketsLevelTable OBJECT-TYPE
	SYNTAX      SEQUENCE OF GreEthernetPacketsLevelEntry
	MAX-ACCESS  not-accessible
	STATUS      current
	DESCRIPTION
	"Table for greEthernetPackets"
	::={greEthernetPackets 4}

greEthernetPacketsLevelEntry OBJECT-TYPE
	SYNTAX      GreEthernetPacketsLevelEntry
	MAX-ACCESS  not-accessible
	STATUS      current
	DESCRIPTION
	"Table entry for greEthernetPackets"
	INDEX { greEthernetPacketsLevelName }
	::={greEthernetPacketsLevelTable 1}

GreEthernetPacketsLevelEntry ::=
	SEQUENCE {
		greEthernetPacketsLevelName	DisplayString,
		greEthernetPacketsLevelVal	Counter64,
		greEthernetPacketsLevelMom	CounterBasedGauge64,
		greEthernetPacketsLevelMax	CounterBasedGauge64
	}

greEthernetPacketsLevelName OBJECT-TYPE
	SYNTAX      DisplayString
	MAX-ACCESS  not-accessible
	STATUS      current
	DESCRIPTION
	"Table entry display string for greEthernetPackets"
	::={greEthernetPacketsLevelEntry 1}

greEthernetPacketsLevelVal OBJECT-TYPE
	SYNTAX	 Counter64
	MAX-ACCESS  read-only
	STATUS      current
	DESCRIPTION
	"Table entry attribute for greEthernetPackets"
	::={greEthernetPacketsLevelEntry 2}

greEthernetPacketsLevelMom OBJECT-TYPE
	SYNTAX	 CounterBasedGauge64
	MAX-ACCESS  read-only
	STATUS      current
	DESCRIPTION
	"Table entry attribute for greEthernetPackets"
	::={greEthernetPacketsLevelEntry 3}

greEthernetPacketsLevelMax OBJECT-TYPE
	SYNTAX	 CounterBasedGauge64
	MAX-ACCESS  read-only
	STATUS      current
	DESCRIPTION
	"Table entry attribute for greEthernetPackets"
	::={greEthernetPacketsLevelEntry 4}


greEthernetUnknownPackets	OBJECT IDENTIFIER ::={gre 15}

greEthernetUnknownPacketsVal	OBJECT-TYPE
	SYNTAX	 Counter64
	MAX-ACCESS read-only
	STATUS current
	DESCRIPTION "Ethernet unknown type packets"

	::={greEthernetUnknownPackets 1}

greEthernetUnknownPacketsMom	OBJECT-TYPE
	SYNTAX	 CounterBasedGauge64
	MAX-ACCESS read-only
	STATUS current
	DESCRIPTION "Ethernet unknown type packets"

	::={greEthernetUnknownPackets 2}

greEthernetUnknownPacketsMax	OBJECT-TYPE
	SYNTAX	 CounterBasedGauge64
	MAX-ACCESS read-only
	STATUS current
	DESCRIPTION "Ethernet unknown type packets"

	::={greEthernetUnknownPackets 3}

greEthernetUnknownPacketsLevelTable OBJECT-TYPE
	SYNTAX      SEQUENCE OF GreEthernetUnknownPacketsLevelEntry
	MAX-ACCESS  not-accessible
	STATUS      current
	DESCRIPTION
	"Table for greEthernetUnknownPackets"
	::={greEthernetUnknownPackets 4}

greEthernetUnknownPacketsLevelEntry OBJECT-TYPE
	SYNTAX      GreEthernetUnknownPacketsLevelEntry
	MAX-ACCESS  not-accessible
	STATUS      current
	DESCRIPTION
	"Table entry for greEthernetUnknownPackets"
	INDEX { greEthernetUnknownPacketsLevelName }
	::={greEthernetUnknownPacketsLevelTable 1}

GreEthernetUnknownPacketsLevelEntry ::=
	SEQUENCE {
		greEthernetUnknownPacketsLevelName	DisplayString,
		greEthernetUnknownPacketsLevelVal	Counter64,
		greEthernetUnknownPacketsLevelMom	CounterBasedGauge64,
		greEthernetUnknownPacketsLevelMax	CounterBasedGauge64
	}

greEthernetUnknownPacketsLevelName OBJECT-TYPE
	SYNTAX      DisplayString
	MAX-ACCESS  not-accessible
	STATUS      current
	DESCRIPTION
	"Table entry display string for greEthernetUnknownPackets"
	::={greEthernetUnknownPacketsLevelEntry 1}

greEthernetUnknownPacketsLevelVal OBJECT-TYPE
	SYNTAX	 Counter64
	MAX-ACCESS  read-only
	STATUS      current
	DESCRIPTION
	"Table entry attribute for greEthernetUnknownPackets"
	::={greEthernetUnknownPacketsLevelEntry 2}

greEthernetUnknownPacketsLevelMom OBJECT-TYPE
	SYNTAX	 CounterBasedGauge64
	MAX-ACCESS  read-only
	STATUS      current
	DESCRIPTION
	"Table entry attribute for greEthernetUnknownPackets"
	::={greEthernetUnknownPacketsLevelEntry 3}

greEthernetUnknownPacketsLevelMax OBJECT-TYPE
	SYNTAX	 CounterBasedGauge64
	MAX-ACCESS  read-only
	STATUS      current
	DESCRIPTION
	"Table entry attribute for greEthernetUnknownPackets"
	::={greEthernetUnknownPacketsLevelEntry 4}


l2tp	OBJECT IDENTIFIER ::={sysdiag 132}

l2tpPackets	OBJECT IDENTIFIER ::={l2tp 2}

l2tpPacketsVal	OBJECT-TYPE
	SYNTAX	 Counter64
	MAX-ACCESS read-only
	STATUS current
	DESCRIPTION "RX packets"

	::={l2tpPackets 1}

l2tpPacketsMom	OBJECT-TYPE
	SYNTAX	 CounterBasedGauge64
	MAX-ACCESS read-only
	STATUS current
	DESCRIPTION "RX packets"

	::={l2tpPackets 2}

l2tpPacketsMax	OBJECT-TYPE
	SYNTAX	 CounterBasedGauge64
	MAX-ACCESS read-only
	STATUS current
	DESCRIPTION "RX packets"

	::={l2tpPackets 3}

l2tpPacketsLevelTable OBJECT-TYPE
	SYNTAX      SEQUENCE OF L2tpPacketsLevelEntry
	MAX-ACCESS  not-accessible
	STATUS      current
	DESCRIPTION
	"Table for l2tpPackets"
	::={l2tpPackets 4}

l2tpPacketsLevelEntry OBJECT-TYPE
	SYNTAX      L2tpPacketsLevelEntry
	MAX-ACCESS  not-accessible
	STATUS      current
	DESCRIPTION
	"Table entry for l2tpPackets"
	INDEX { l2tpPacketsLevelName }
	::={l2tpPacketsLevelTable 1}

L2tpPacketsLevelEntry ::=
	SEQUENCE {
		l2tpPacketsLevelName	DisplayString,
		l2tpPacketsLevelVal	Counter64,
		l2tpPacketsLevelMom	CounterBasedGauge64,
		l2tpPacketsLevelMax	CounterBasedGauge64
	}

l2tpPacketsLevelName OBJECT-TYPE
	SYNTAX      DisplayString
	MAX-ACCESS  not-accessible
	STATUS      current
	DESCRIPTION
	"Table entry display string for l2tpPackets"
	::={l2tpPacketsLevelEntry 1}

l2tpPacketsLevelVal OBJECT-TYPE
	SYNTAX	 Counter64
	MAX-ACCESS  read-only
	STATUS      current
	DESCRIPTION
	"Table entry attribute for l2tpPackets"
	::={l2tpPacketsLevelEntry 2}

l2tpPacketsLevelMom OBJECT-TYPE
	SYNTAX	 CounterBasedGauge64
	MAX-ACCESS  read-only
	STATUS      current
	DESCRIPTION
	"Table entry attribute for l2tpPackets"
	::={l2tpPacketsLevelEntry 3}

l2tpPacketsLevelMax OBJECT-TYPE
	SYNTAX	 CounterBasedGauge64
	MAX-ACCESS  read-only
	STATUS      current
	DESCRIPTION
	"Table entry attribute for l2tpPackets"
	::={l2tpPacketsLevelEntry 4}


l2tpBytes	OBJECT IDENTIFIER ::={l2tp 3}

l2tpBytesVal	OBJECT-TYPE
	SYNTAX	 Counter64
	MAX-ACCESS read-only
	STATUS current
	DESCRIPTION "RX data"

	::={l2tpBytes 1}

l2tpBytesMom	OBJECT-TYPE
	SYNTAX	 CounterBasedGauge64
	MAX-ACCESS read-only
	STATUS current
	DESCRIPTION "RX data"

	::={l2tpBytes 2}

l2tpBytesMax	OBJECT-TYPE
	SYNTAX	 CounterBasedGauge64
	MAX-ACCESS read-only
	STATUS current
	DESCRIPTION "RX data"

	::={l2tpBytes 3}

l2tpBytesLevelTable OBJECT-TYPE
	SYNTAX      SEQUENCE OF L2tpBytesLevelEntry
	MAX-ACCESS  not-accessible
	STATUS      current
	DESCRIPTION
	"Table for l2tpBytes"
	::={l2tpBytes 4}

l2tpBytesLevelEntry OBJECT-TYPE
	SYNTAX      L2tpBytesLevelEntry
	MAX-ACCESS  not-accessible
	STATUS      current
	DESCRIPTION
	"Table entry for l2tpBytes"
	INDEX { l2tpBytesLevelName }
	::={l2tpBytesLevelTable 1}

L2tpBytesLevelEntry ::=
	SEQUENCE {
		l2tpBytesLevelName	DisplayString,
		l2tpBytesLevelVal	Counter64,
		l2tpBytesLevelMom	CounterBasedGauge64,
		l2tpBytesLevelMax	CounterBasedGauge64
	}

l2tpBytesLevelName OBJECT-TYPE
	SYNTAX      DisplayString
	MAX-ACCESS  not-accessible
	STATUS      current
	DESCRIPTION
	"Table entry display string for l2tpBytes"
	::={l2tpBytesLevelEntry 1}

l2tpBytesLevelVal OBJECT-TYPE
	SYNTAX	 Counter64
	MAX-ACCESS  read-only
	STATUS      current
	DESCRIPTION
	"Table entry attribute for l2tpBytes"
	::={l2tpBytesLevelEntry 2}

l2tpBytesLevelMom OBJECT-TYPE
	SYNTAX	 CounterBasedGauge64
	MAX-ACCESS  read-only
	STATUS      current
	DESCRIPTION
	"Table entry attribute for l2tpBytes"
	::={l2tpBytesLevelEntry 3}

l2tpBytesLevelMax OBJECT-TYPE
	SYNTAX	 CounterBasedGauge64
	MAX-ACCESS  read-only
	STATUS      current
	DESCRIPTION
	"Table entry attribute for l2tpBytes"
	::={l2tpBytesLevelEntry 4}


l2tpIpv4Packets	OBJECT IDENTIFIER ::={l2tp 4}

l2tpIpv4PacketsVal	OBJECT-TYPE
	SYNTAX	 Counter64
	MAX-ACCESS read-only
	STATUS current
	DESCRIPTION "PPP IPv4 RX packets"

	::={l2tpIpv4Packets 1}

l2tpIpv4PacketsMom	OBJECT-TYPE
	SYNTAX	 CounterBasedGauge64
	MAX-ACCESS read-only
	STATUS current
	DESCRIPTION "PPP IPv4 RX packets"

	::={l2tpIpv4Packets 2}

l2tpIpv4PacketsMax	OBJECT-TYPE
	SYNTAX	 CounterBasedGauge64
	MAX-ACCESS read-only
	STATUS current
	DESCRIPTION "PPP IPv4 RX packets"

	::={l2tpIpv4Packets 3}

l2tpIpv4PacketsLevelTable OBJECT-TYPE
	SYNTAX      SEQUENCE OF L2tpIpv4PacketsLevelEntry
	MAX-ACCESS  not-accessible
	STATUS      current
	DESCRIPTION
	"Table for l2tpIpv4Packets"
	::={l2tpIpv4Packets 4}

l2tpIpv4PacketsLevelEntry OBJECT-TYPE
	SYNTAX      L2tpIpv4PacketsLevelEntry
	MAX-ACCESS  not-accessible
	STATUS      current
	DESCRIPTION
	"Table entry for l2tpIpv4Packets"
	INDEX { l2tpIpv4PacketsLevelName }
	::={l2tpIpv4PacketsLevelTable 1}

L2tpIpv4PacketsLevelEntry ::=
	SEQUENCE {
		l2tpIpv4PacketsLevelName	DisplayString,
		l2tpIpv4PacketsLevelVal	Counter64,
		l2tpIpv4PacketsLevelMom	CounterBasedGauge64,
		l2tpIpv4PacketsLevelMax	CounterBasedGauge64
	}

l2tpIpv4PacketsLevelName OBJECT-TYPE
	SYNTAX      DisplayString
	MAX-ACCESS  not-accessible
	STATUS      current
	DESCRIPTION
	"Table entry display string for l2tpIpv4Packets"
	::={l2tpIpv4PacketsLevelEntry 1}

l2tpIpv4PacketsLevelVal OBJECT-TYPE
	SYNTAX	 Counter64
	MAX-ACCESS  read-only
	STATUS      current
	DESCRIPTION
	"Table entry attribute for l2tpIpv4Packets"
	::={l2tpIpv4PacketsLevelEntry 2}

l2tpIpv4PacketsLevelMom OBJECT-TYPE
	SYNTAX	 CounterBasedGauge64
	MAX-ACCESS  read-only
	STATUS      current
	DESCRIPTION
	"Table entry attribute for l2tpIpv4Packets"
	::={l2tpIpv4PacketsLevelEntry 3}

l2tpIpv4PacketsLevelMax OBJECT-TYPE
	SYNTAX	 CounterBasedGauge64
	MAX-ACCESS  read-only
	STATUS      current
	DESCRIPTION
	"Table entry attribute for l2tpIpv4Packets"
	::={l2tpIpv4PacketsLevelEntry 4}


l2tpIpv6Packets	OBJECT IDENTIFIER ::={l2tp 5}

l2tpIpv6PacketsVal	OBJECT-TYPE
	SYNTAX	 Counter64
	MAX-ACCESS read-only
	STATUS current
	DESCRIPTION "PPP IPv6 RX packets"

	::={l2tpIpv6Packets 1}

l2tpIpv6PacketsMom	OBJECT-TYPE
	SYNTAX	 CounterBasedGauge64
	MAX-ACCESS read-only
	STATUS current
	DESCRIPTION "PPP IPv6 RX packets"

	::={l2tpIpv6Packets 2}

l2tpIpv6PacketsMax	OBJECT-TYPE
	SYNTAX	 CounterBasedGauge64
	MAX-ACCESS read-only
	STATUS current
	DESCRIPTION "PPP IPv6 RX packets"

	::={l2tpIpv6Packets 3}

l2tpIpv6PacketsLevelTable OBJECT-TYPE
	SYNTAX      SEQUENCE OF L2tpIpv6PacketsLevelEntry
	MAX-ACCESS  not-accessible
	STATUS      current
	DESCRIPTION
	"Table for l2tpIpv6Packets"
	::={l2tpIpv6Packets 4}

l2tpIpv6PacketsLevelEntry OBJECT-TYPE
	SYNTAX      L2tpIpv6PacketsLevelEntry
	MAX-ACCESS  not-accessible
	STATUS      current
	DESCRIPTION
	"Table entry for l2tpIpv6Packets"
	INDEX { l2tpIpv6PacketsLevelName }
	::={l2tpIpv6PacketsLevelTable 1}

L2tpIpv6PacketsLevelEntry ::=
	SEQUENCE {
		l2tpIpv6PacketsLevelName	DisplayString,
		l2tpIpv6PacketsLevelVal	Counter64,
		l2tpIpv6PacketsLevelMom	CounterBasedGauge64,
		l2tpIpv6PacketsLevelMax	CounterBasedGauge64
	}

l2tpIpv6PacketsLevelName OBJECT-TYPE
	SYNTAX      DisplayString
	MAX-ACCESS  not-accessible
	STATUS      current
	DESCRIPTION
	"Table entry display string for l2tpIpv6Packets"
	::={l2tpIpv6PacketsLevelEntry 1}

l2tpIpv6PacketsLevelVal OBJECT-TYPE
	SYNTAX	 Counter64
	MAX-ACCESS  read-only
	STATUS      current
	DESCRIPTION
	"Table entry attribute for l2tpIpv6Packets"
	::={l2tpIpv6PacketsLevelEntry 2}

l2tpIpv6PacketsLevelMom OBJECT-TYPE
	SYNTAX	 CounterBasedGauge64
	MAX-ACCESS  read-only
	STATUS      current
	DESCRIPTION
	"Table entry attribute for l2tpIpv6Packets"
	::={l2tpIpv6PacketsLevelEntry 3}

l2tpIpv6PacketsLevelMax OBJECT-TYPE
	SYNTAX	 CounterBasedGauge64
	MAX-ACCESS  read-only
	STATUS      current
	DESCRIPTION
	"Table entry attribute for l2tpIpv6Packets"
	::={l2tpIpv6PacketsLevelEntry 4}


l2tplcpPackets	OBJECT IDENTIFIER ::={l2tp 6}

l2tplcpPacketsVal	OBJECT-TYPE
	SYNTAX	 Counter64
	MAX-ACCESS read-only
	STATUS current
	DESCRIPTION "PPP LCP RX packets"

	::={l2tplcpPackets 1}

l2tplcpPacketsMom	OBJECT-TYPE
	SYNTAX	 CounterBasedGauge64
	MAX-ACCESS read-only
	STATUS current
	DESCRIPTION "PPP LCP RX packets"

	::={l2tplcpPackets 2}

l2tplcpPacketsMax	OBJECT-TYPE
	SYNTAX	 CounterBasedGauge64
	MAX-ACCESS read-only
	STATUS current
	DESCRIPTION "PPP LCP RX packets"

	::={l2tplcpPackets 3}

l2tplcpPacketsLevelTable OBJECT-TYPE
	SYNTAX      SEQUENCE OF L2tplcpPacketsLevelEntry
	MAX-ACCESS  not-accessible
	STATUS      current
	DESCRIPTION
	"Table for l2tplcpPackets"
	::={l2tplcpPackets 4}

l2tplcpPacketsLevelEntry OBJECT-TYPE
	SYNTAX      L2tplcpPacketsLevelEntry
	MAX-ACCESS  not-accessible
	STATUS      current
	DESCRIPTION
	"Table entry for l2tplcpPackets"
	INDEX { l2tplcpPacketsLevelName }
	::={l2tplcpPacketsLevelTable 1}

L2tplcpPacketsLevelEntry ::=
	SEQUENCE {
		l2tplcpPacketsLevelName	DisplayString,
		l2tplcpPacketsLevelVal	Counter64,
		l2tplcpPacketsLevelMom	CounterBasedGauge64,
		l2tplcpPacketsLevelMax	CounterBasedGauge64
	}

l2tplcpPacketsLevelName OBJECT-TYPE
	SYNTAX      DisplayString
	MAX-ACCESS  not-accessible
	STATUS      current
	DESCRIPTION
	"Table entry display string for l2tplcpPackets"
	::={l2tplcpPacketsLevelEntry 1}

l2tplcpPacketsLevelVal OBJECT-TYPE
	SYNTAX	 Counter64
	MAX-ACCESS  read-only
	STATUS      current
	DESCRIPTION
	"Table entry attribute for l2tplcpPackets"
	::={l2tplcpPacketsLevelEntry 2}

l2tplcpPacketsLevelMom OBJECT-TYPE
	SYNTAX	 CounterBasedGauge64
	MAX-ACCESS  read-only
	STATUS      current
	DESCRIPTION
	"Table entry attribute for l2tplcpPackets"
	::={l2tplcpPacketsLevelEntry 3}

l2tplcpPacketsLevelMax OBJECT-TYPE
	SYNTAX	 CounterBasedGauge64
	MAX-ACCESS  read-only
	STATUS      current
	DESCRIPTION
	"Table entry attribute for l2tplcpPackets"
	::={l2tplcpPacketsLevelEntry 4}


l2tpcipv4Packets	OBJECT IDENTIFIER ::={l2tp 7}

l2tpcipv4PacketsVal	OBJECT-TYPE
	SYNTAX	 Counter64
	MAX-ACCESS read-only
	STATUS current
	DESCRIPTION "PPP CIPv4 RX packets"

	::={l2tpcipv4Packets 1}

l2tpcipv4PacketsMom	OBJECT-TYPE
	SYNTAX	 CounterBasedGauge64
	MAX-ACCESS read-only
	STATUS current
	DESCRIPTION "PPP CIPv4 RX packets"

	::={l2tpcipv4Packets 2}

l2tpcipv4PacketsMax	OBJECT-TYPE
	SYNTAX	 CounterBasedGauge64
	MAX-ACCESS read-only
	STATUS current
	DESCRIPTION "PPP CIPv4 RX packets"

	::={l2tpcipv4Packets 3}

l2tpcipv4PacketsLevelTable OBJECT-TYPE
	SYNTAX      SEQUENCE OF L2tpcipv4PacketsLevelEntry
	MAX-ACCESS  not-accessible
	STATUS      current
	DESCRIPTION
	"Table for l2tpcipv4Packets"
	::={l2tpcipv4Packets 4}

l2tpcipv4PacketsLevelEntry OBJECT-TYPE
	SYNTAX      L2tpcipv4PacketsLevelEntry
	MAX-ACCESS  not-accessible
	STATUS      current
	DESCRIPTION
	"Table entry for l2tpcipv4Packets"
	INDEX { l2tpcipv4PacketsLevelName }
	::={l2tpcipv4PacketsLevelTable 1}

L2tpcipv4PacketsLevelEntry ::=
	SEQUENCE {
		l2tpcipv4PacketsLevelName	DisplayString,
		l2tpcipv4PacketsLevelVal	Counter64,
		l2tpcipv4PacketsLevelMom	CounterBasedGauge64,
		l2tpcipv4PacketsLevelMax	CounterBasedGauge64
	}

l2tpcipv4PacketsLevelName OBJECT-TYPE
	SYNTAX      DisplayString
	MAX-ACCESS  not-accessible
	STATUS      current
	DESCRIPTION
	"Table entry display string for l2tpcipv4Packets"
	::={l2tpcipv4PacketsLevelEntry 1}

l2tpcipv4PacketsLevelVal OBJECT-TYPE
	SYNTAX	 Counter64
	MAX-ACCESS  read-only
	STATUS      current
	DESCRIPTION
	"Table entry attribute for l2tpcipv4Packets"
	::={l2tpcipv4PacketsLevelEntry 2}

l2tpcipv4PacketsLevelMom OBJECT-TYPE
	SYNTAX	 CounterBasedGauge64
	MAX-ACCESS  read-only
	STATUS      current
	DESCRIPTION
	"Table entry attribute for l2tpcipv4Packets"
	::={l2tpcipv4PacketsLevelEntry 3}

l2tpcipv4PacketsLevelMax OBJECT-TYPE
	SYNTAX	 CounterBasedGauge64
	MAX-ACCESS  read-only
	STATUS      current
	DESCRIPTION
	"Table entry attribute for l2tpcipv4Packets"
	::={l2tpcipv4PacketsLevelEntry 4}


l2tpcipv6Packets	OBJECT IDENTIFIER ::={l2tp 8}

l2tpcipv6PacketsVal	OBJECT-TYPE
	SYNTAX	 Counter64
	MAX-ACCESS read-only
	STATUS current
	DESCRIPTION "PPP CIPv6 RX packets"

	::={l2tpcipv6Packets 1}

l2tpcipv6PacketsMom	OBJECT-TYPE
	SYNTAX	 CounterBasedGauge64
	MAX-ACCESS read-only
	STATUS current
	DESCRIPTION "PPP CIPv6 RX packets"

	::={l2tpcipv6Packets 2}

l2tpcipv6PacketsMax	OBJECT-TYPE
	SYNTAX	 CounterBasedGauge64
	MAX-ACCESS read-only
	STATUS current
	DESCRIPTION "PPP CIPv6 RX packets"

	::={l2tpcipv6Packets 3}

l2tpcipv6PacketsLevelTable OBJECT-TYPE
	SYNTAX      SEQUENCE OF L2tpcipv6PacketsLevelEntry
	MAX-ACCESS  not-accessible
	STATUS      current
	DESCRIPTION
	"Table for l2tpcipv6Packets"
	::={l2tpcipv6Packets 4}

l2tpcipv6PacketsLevelEntry OBJECT-TYPE
	SYNTAX      L2tpcipv6PacketsLevelEntry
	MAX-ACCESS  not-accessible
	STATUS      current
	DESCRIPTION
	"Table entry for l2tpcipv6Packets"
	INDEX { l2tpcipv6PacketsLevelName }
	::={l2tpcipv6PacketsLevelTable 1}

L2tpcipv6PacketsLevelEntry ::=
	SEQUENCE {
		l2tpcipv6PacketsLevelName	DisplayString,
		l2tpcipv6PacketsLevelVal	Counter64,
		l2tpcipv6PacketsLevelMom	CounterBasedGauge64,
		l2tpcipv6PacketsLevelMax	CounterBasedGauge64
	}

l2tpcipv6PacketsLevelName OBJECT-TYPE
	SYNTAX      DisplayString
	MAX-ACCESS  not-accessible
	STATUS      current
	DESCRIPTION
	"Table entry display string for l2tpcipv6Packets"
	::={l2tpcipv6PacketsLevelEntry 1}

l2tpcipv6PacketsLevelVal OBJECT-TYPE
	SYNTAX	 Counter64
	MAX-ACCESS  read-only
	STATUS      current
	DESCRIPTION
	"Table entry attribute for l2tpcipv6Packets"
	::={l2tpcipv6PacketsLevelEntry 2}

l2tpcipv6PacketsLevelMom OBJECT-TYPE
	SYNTAX	 CounterBasedGauge64
	MAX-ACCESS  read-only
	STATUS      current
	DESCRIPTION
	"Table entry attribute for l2tpcipv6Packets"
	::={l2tpcipv6PacketsLevelEntry 3}

l2tpcipv6PacketsLevelMax OBJECT-TYPE
	SYNTAX	 CounterBasedGauge64
	MAX-ACCESS  read-only
	STATUS      current
	DESCRIPTION
	"Table entry attribute for l2tpcipv6Packets"
	::={l2tpcipv6PacketsLevelEntry 4}


l2tpchap6Packets	OBJECT IDENTIFIER ::={l2tp 9}

l2tpchap6PacketsVal	OBJECT-TYPE
	SYNTAX	 Counter64
	MAX-ACCESS read-only
	STATUS current
	DESCRIPTION "PPP CHAP RX packets"

	::={l2tpchap6Packets 1}

l2tpchap6PacketsMom	OBJECT-TYPE
	SYNTAX	 CounterBasedGauge64
	MAX-ACCESS read-only
	STATUS current
	DESCRIPTION "PPP CHAP RX packets"

	::={l2tpchap6Packets 2}

l2tpchap6PacketsMax	OBJECT-TYPE
	SYNTAX	 CounterBasedGauge64
	MAX-ACCESS read-only
	STATUS current
	DESCRIPTION "PPP CHAP RX packets"

	::={l2tpchap6Packets 3}

l2tpchap6PacketsLevelTable OBJECT-TYPE
	SYNTAX      SEQUENCE OF L2tpchap6PacketsLevelEntry
	MAX-ACCESS  not-accessible
	STATUS      current
	DESCRIPTION
	"Table for l2tpchap6Packets"
	::={l2tpchap6Packets 4}

l2tpchap6PacketsLevelEntry OBJECT-TYPE
	SYNTAX      L2tpchap6PacketsLevelEntry
	MAX-ACCESS  not-accessible
	STATUS      current
	DESCRIPTION
	"Table entry for l2tpchap6Packets"
	INDEX { l2tpchap6PacketsLevelName }
	::={l2tpchap6PacketsLevelTable 1}

L2tpchap6PacketsLevelEntry ::=
	SEQUENCE {
		l2tpchap6PacketsLevelName	DisplayString,
		l2tpchap6PacketsLevelVal	Counter64,
		l2tpchap6PacketsLevelMom	CounterBasedGauge64,
		l2tpchap6PacketsLevelMax	CounterBasedGauge64
	}

l2tpchap6PacketsLevelName OBJECT-TYPE
	SYNTAX      DisplayString
	MAX-ACCESS  not-accessible
	STATUS      current
	DESCRIPTION
	"Table entry display string for l2tpchap6Packets"
	::={l2tpchap6PacketsLevelEntry 1}

l2tpchap6PacketsLevelVal OBJECT-TYPE
	SYNTAX	 Counter64
	MAX-ACCESS  read-only
	STATUS      current
	DESCRIPTION
	"Table entry attribute for l2tpchap6Packets"
	::={l2tpchap6PacketsLevelEntry 2}

l2tpchap6PacketsLevelMom OBJECT-TYPE
	SYNTAX	 CounterBasedGauge64
	MAX-ACCESS  read-only
	STATUS      current
	DESCRIPTION
	"Table entry attribute for l2tpchap6Packets"
	::={l2tpchap6PacketsLevelEntry 3}

l2tpchap6PacketsLevelMax OBJECT-TYPE
	SYNTAX	 CounterBasedGauge64
	MAX-ACCESS  read-only
	STATUS      current
	DESCRIPTION
	"Table entry attribute for l2tpchap6Packets"
	::={l2tpchap6PacketsLevelEntry 4}


l2tpMapEntries	OBJECT IDENTIFIER ::={l2tp 20}

l2tpMapEntriesVal	OBJECT-TYPE
	SYNTAX	 CounterBasedGauge64
	MAX-ACCESS read-only
	STATUS current
	DESCRIPTION "L2TP map: Number of ENTRIES (outgoing, incoming)-pairs in storage in engine"

	::={l2tpMapEntries 1}

l2tpMapEntriesMax	OBJECT-TYPE
	SYNTAX	 CounterBasedGauge64
	MAX-ACCESS read-only
	STATUS current
	DESCRIPTION "L2TP map: Number of ENTRIES (outgoing, incoming)-pairs in storage in engine"

	::={l2tpMapEntries 3}

l2tpMapEntriesLevelTable OBJECT-TYPE
	SYNTAX      SEQUENCE OF L2tpMapEntriesLevelEntry
	MAX-ACCESS  not-accessible
	STATUS      current
	DESCRIPTION
	"Table for l2tpMapEntries"
	::={l2tpMapEntries 4}

l2tpMapEntriesLevelEntry OBJECT-TYPE
	SYNTAX      L2tpMapEntriesLevelEntry
	MAX-ACCESS  not-accessible
	STATUS      current
	DESCRIPTION
	"Table entry for l2tpMapEntries"
	INDEX { l2tpMapEntriesLevelName }
	::={l2tpMapEntriesLevelTable 1}

L2tpMapEntriesLevelEntry ::=
	SEQUENCE {
		l2tpMapEntriesLevelName	DisplayString,
		l2tpMapEntriesLevelVal	CounterBasedGauge64,
		l2tpMapEntriesLevelMax	CounterBasedGauge64
	}

l2tpMapEntriesLevelName OBJECT-TYPE
	SYNTAX      DisplayString
	MAX-ACCESS  not-accessible
	STATUS      current
	DESCRIPTION
	"Table entry display string for l2tpMapEntries"
	::={l2tpMapEntriesLevelEntry 1}

l2tpMapEntriesLevelVal OBJECT-TYPE
	SYNTAX	 CounterBasedGauge64
	MAX-ACCESS  read-only
	STATUS      current
	DESCRIPTION
	"Table entry attribute for l2tpMapEntries"
	::={l2tpMapEntriesLevelEntry 2}

l2tpMapEntriesLevelMax OBJECT-TYPE
	SYNTAX	 CounterBasedGauge64
	MAX-ACCESS  read-only
	STATUS      current
	DESCRIPTION
	"Table entry attribute for l2tpMapEntries"
	::={l2tpMapEntriesLevelEntry 4}


l2tpMapFull	OBJECT IDENTIFIER ::={l2tp 21}

l2tpMapFullVal	OBJECT-TYPE
	SYNTAX	 Counter64
	MAX-ACCESS read-only
	STATUS current
	DESCRIPTION "L2TP map: Storage in engine is FULL"

	::={l2tpMapFull 1}

l2tpMapFullMom	OBJECT-TYPE
	SYNTAX	 CounterBasedGauge64
	MAX-ACCESS read-only
	STATUS current
	DESCRIPTION "L2TP map: Storage in engine is FULL"

	::={l2tpMapFull 2}

l2tpMapFullMax	OBJECT-TYPE
	SYNTAX	 CounterBasedGauge64
	MAX-ACCESS read-only
	STATUS current
	DESCRIPTION "L2TP map: Storage in engine is FULL"

	::={l2tpMapFull 3}

l2tpMapFullLevelTable OBJECT-TYPE
	SYNTAX      SEQUENCE OF L2tpMapFullLevelEntry
	MAX-ACCESS  not-accessible
	STATUS      current
	DESCRIPTION
	"Table for l2tpMapFull"
	::={l2tpMapFull 4}

l2tpMapFullLevelEntry OBJECT-TYPE
	SYNTAX      L2tpMapFullLevelEntry
	MAX-ACCESS  not-accessible
	STATUS      current
	DESCRIPTION
	"Table entry for l2tpMapFull"
	INDEX { l2tpMapFullLevelName }
	::={l2tpMapFullLevelTable 1}

L2tpMapFullLevelEntry ::=
	SEQUENCE {
		l2tpMapFullLevelName	DisplayString,
		l2tpMapFullLevelVal	Counter64,
		l2tpMapFullLevelMom	CounterBasedGauge64,
		l2tpMapFullLevelMax	CounterBasedGauge64
	}

l2tpMapFullLevelName OBJECT-TYPE
	SYNTAX      DisplayString
	MAX-ACCESS  not-accessible
	STATUS      current
	DESCRIPTION
	"Table entry display string for l2tpMapFull"
	::={l2tpMapFullLevelEntry 1}

l2tpMapFullLevelVal OBJECT-TYPE
	SYNTAX	 Counter64
	MAX-ACCESS  read-only
	STATUS      current
	DESCRIPTION
	"Table entry attribute for l2tpMapFull"
	::={l2tpMapFullLevelEntry 2}

l2tpMapFullLevelMom OBJECT-TYPE
	SYNTAX	 CounterBasedGauge64
	MAX-ACCESS  read-only
	STATUS      current
	DESCRIPTION
	"Table entry attribute for l2tpMapFull"
	::={l2tpMapFullLevelEntry 3}

l2tpMapFullLevelMax OBJECT-TYPE
	SYNTAX	 CounterBasedGauge64
	MAX-ACCESS  read-only
	STATUS      current
	DESCRIPTION
	"Table entry attribute for l2tpMapFull"
	::={l2tpMapFullLevelEntry 4}


l2tpMapInserts	OBJECT IDENTIFIER ::={l2tp 22}

l2tpMapInsertsVal	OBJECT-TYPE
	SYNTAX	 Counter64
	MAX-ACCESS read-only
	STATUS current
	DESCRIPTION "L2TP map: Number of INSERT operations into L2TP map"

	::={l2tpMapInserts 1}

l2tpMapInsertsMom	OBJECT-TYPE
	SYNTAX	 CounterBasedGauge64
	MAX-ACCESS read-only
	STATUS current
	DESCRIPTION "L2TP map: Number of INSERT operations into L2TP map"

	::={l2tpMapInserts 2}

l2tpMapInsertsMax	OBJECT-TYPE
	SYNTAX	 CounterBasedGauge64
	MAX-ACCESS read-only
	STATUS current
	DESCRIPTION "L2TP map: Number of INSERT operations into L2TP map"

	::={l2tpMapInserts 3}

l2tpMapInsertsLevelTable OBJECT-TYPE
	SYNTAX      SEQUENCE OF L2tpMapInsertsLevelEntry
	MAX-ACCESS  not-accessible
	STATUS      current
	DESCRIPTION
	"Table for l2tpMapInserts"
	::={l2tpMapInserts 4}

l2tpMapInsertsLevelEntry OBJECT-TYPE
	SYNTAX      L2tpMapInsertsLevelEntry
	MAX-ACCESS  not-accessible
	STATUS      current
	DESCRIPTION
	"Table entry for l2tpMapInserts"
	INDEX { l2tpMapInsertsLevelName }
	::={l2tpMapInsertsLevelTable 1}

L2tpMapInsertsLevelEntry ::=
	SEQUENCE {
		l2tpMapInsertsLevelName	DisplayString,
		l2tpMapInsertsLevelVal	Counter64,
		l2tpMapInsertsLevelMom	CounterBasedGauge64,
		l2tpMapInsertsLevelMax	CounterBasedGauge64
	}

l2tpMapInsertsLevelName OBJECT-TYPE
	SYNTAX      DisplayString
	MAX-ACCESS  not-accessible
	STATUS      current
	DESCRIPTION
	"Table entry display string for l2tpMapInserts"
	::={l2tpMapInsertsLevelEntry 1}

l2tpMapInsertsLevelVal OBJECT-TYPE
	SYNTAX	 Counter64
	MAX-ACCESS  read-only
	STATUS      current
	DESCRIPTION
	"Table entry attribute for l2tpMapInserts"
	::={l2tpMapInsertsLevelEntry 2}

l2tpMapInsertsLevelMom OBJECT-TYPE
	SYNTAX	 CounterBasedGauge64
	MAX-ACCESS  read-only
	STATUS      current
	DESCRIPTION
	"Table entry attribute for l2tpMapInserts"
	::={l2tpMapInsertsLevelEntry 3}

l2tpMapInsertsLevelMax OBJECT-TYPE
	SYNTAX	 CounterBasedGauge64
	MAX-ACCESS  read-only
	STATUS      current
	DESCRIPTION
	"Table entry attribute for l2tpMapInserts"
	::={l2tpMapInsertsLevelEntry 4}


l2tpMapRemoves	OBJECT IDENTIFIER ::={l2tp 23}

l2tpMapRemovesVal	OBJECT-TYPE
	SYNTAX	 Counter64
	MAX-ACCESS read-only
	STATUS current
	DESCRIPTION "L2TP map: Number of REMOVE operations from L2TP map"

	::={l2tpMapRemoves 1}

l2tpMapRemovesMom	OBJECT-TYPE
	SYNTAX	 CounterBasedGauge64
	MAX-ACCESS read-only
	STATUS current
	DESCRIPTION "L2TP map: Number of REMOVE operations from L2TP map"

	::={l2tpMapRemoves 2}

l2tpMapRemovesMax	OBJECT-TYPE
	SYNTAX	 CounterBasedGauge64
	MAX-ACCESS read-only
	STATUS current
	DESCRIPTION "L2TP map: Number of REMOVE operations from L2TP map"

	::={l2tpMapRemoves 3}

l2tpMapRemovesLevelTable OBJECT-TYPE
	SYNTAX      SEQUENCE OF L2tpMapRemovesLevelEntry
	MAX-ACCESS  not-accessible
	STATUS      current
	DESCRIPTION
	"Table for l2tpMapRemoves"
	::={l2tpMapRemoves 4}

l2tpMapRemovesLevelEntry OBJECT-TYPE
	SYNTAX      L2tpMapRemovesLevelEntry
	MAX-ACCESS  not-accessible
	STATUS      current
	DESCRIPTION
	"Table entry for l2tpMapRemoves"
	INDEX { l2tpMapRemovesLevelName }
	::={l2tpMapRemovesLevelTable 1}

L2tpMapRemovesLevelEntry ::=
	SEQUENCE {
		l2tpMapRemovesLevelName	DisplayString,
		l2tpMapRemovesLevelVal	Counter64,
		l2tpMapRemovesLevelMom	CounterBasedGauge64,
		l2tpMapRemovesLevelMax	CounterBasedGauge64
	}

l2tpMapRemovesLevelName OBJECT-TYPE
	SYNTAX      DisplayString
	MAX-ACCESS  not-accessible
	STATUS      current
	DESCRIPTION
	"Table entry display string for l2tpMapRemoves"
	::={l2tpMapRemovesLevelEntry 1}

l2tpMapRemovesLevelVal OBJECT-TYPE
	SYNTAX	 Counter64
	MAX-ACCESS  read-only
	STATUS      current
	DESCRIPTION
	"Table entry attribute for l2tpMapRemoves"
	::={l2tpMapRemovesLevelEntry 2}

l2tpMapRemovesLevelMom OBJECT-TYPE
	SYNTAX	 CounterBasedGauge64
	MAX-ACCESS  read-only
	STATUS      current
	DESCRIPTION
	"Table entry attribute for l2tpMapRemoves"
	::={l2tpMapRemovesLevelEntry 3}

l2tpMapRemovesLevelMax OBJECT-TYPE
	SYNTAX	 CounterBasedGauge64
	MAX-ACCESS  read-only
	STATUS      current
	DESCRIPTION
	"Table entry attribute for l2tpMapRemoves"
	::={l2tpMapRemovesLevelEntry 4}


l2tpMapLookups	OBJECT IDENTIFIER ::={l2tp 24}

l2tpMapLookupsVal	OBJECT-TYPE
	SYNTAX	 Counter64
	MAX-ACCESS read-only
	STATUS current
	DESCRIPTION "L2TP map: Number of LOOKUP operations in L2TP map"

	::={l2tpMapLookups 1}

l2tpMapLookupsMom	OBJECT-TYPE
	SYNTAX	 CounterBasedGauge64
	MAX-ACCESS read-only
	STATUS current
	DESCRIPTION "L2TP map: Number of LOOKUP operations in L2TP map"

	::={l2tpMapLookups 2}

l2tpMapLookupsMax	OBJECT-TYPE
	SYNTAX	 CounterBasedGauge64
	MAX-ACCESS read-only
	STATUS current
	DESCRIPTION "L2TP map: Number of LOOKUP operations in L2TP map"

	::={l2tpMapLookups 3}

l2tpMapLookupsLevelTable OBJECT-TYPE
	SYNTAX      SEQUENCE OF L2tpMapLookupsLevelEntry
	MAX-ACCESS  not-accessible
	STATUS      current
	DESCRIPTION
	"Table for l2tpMapLookups"
	::={l2tpMapLookups 4}

l2tpMapLookupsLevelEntry OBJECT-TYPE
	SYNTAX      L2tpMapLookupsLevelEntry
	MAX-ACCESS  not-accessible
	STATUS      current
	DESCRIPTION
	"Table entry for l2tpMapLookups"
	INDEX { l2tpMapLookupsLevelName }
	::={l2tpMapLookupsLevelTable 1}

L2tpMapLookupsLevelEntry ::=
	SEQUENCE {
		l2tpMapLookupsLevelName	DisplayString,
		l2tpMapLookupsLevelVal	Counter64,
		l2tpMapLookupsLevelMom	CounterBasedGauge64,
		l2tpMapLookupsLevelMax	CounterBasedGauge64
	}

l2tpMapLookupsLevelName OBJECT-TYPE
	SYNTAX      DisplayString
	MAX-ACCESS  not-accessible
	STATUS      current
	DESCRIPTION
	"Table entry display string for l2tpMapLookups"
	::={l2tpMapLookupsLevelEntry 1}

l2tpMapLookupsLevelVal OBJECT-TYPE
	SYNTAX	 Counter64
	MAX-ACCESS  read-only
	STATUS      current
	DESCRIPTION
	"Table entry attribute for l2tpMapLookups"
	::={l2tpMapLookupsLevelEntry 2}

l2tpMapLookupsLevelMom OBJECT-TYPE
	SYNTAX	 CounterBasedGauge64
	MAX-ACCESS  read-only
	STATUS      current
	DESCRIPTION
	"Table entry attribute for l2tpMapLookups"
	::={l2tpMapLookupsLevelEntry 3}

l2tpMapLookupsLevelMax OBJECT-TYPE
	SYNTAX	 CounterBasedGauge64
	MAX-ACCESS  read-only
	STATUS      current
	DESCRIPTION
	"Table entry attribute for l2tpMapLookups"
	::={l2tpMapLookupsLevelEntry 4}


l2tpMapFound	OBJECT IDENTIFIER ::={l2tp 25}

l2tpMapFoundVal	OBJECT-TYPE
	SYNTAX	 Counter64
	MAX-ACCESS read-only
	STATUS current
	DESCRIPTION "L2TP map: Number of lookup and FOUND operations in L2TP map"

	::={l2tpMapFound 1}

l2tpMapFoundMom	OBJECT-TYPE
	SYNTAX	 CounterBasedGauge64
	MAX-ACCESS read-only
	STATUS current
	DESCRIPTION "L2TP map: Number of lookup and FOUND operations in L2TP map"

	::={l2tpMapFound 2}

l2tpMapFoundMax	OBJECT-TYPE
	SYNTAX	 CounterBasedGauge64
	MAX-ACCESS read-only
	STATUS current
	DESCRIPTION "L2TP map: Number of lookup and FOUND operations in L2TP map"

	::={l2tpMapFound 3}

l2tpMapFoundLevelTable OBJECT-TYPE
	SYNTAX      SEQUENCE OF L2tpMapFoundLevelEntry
	MAX-ACCESS  not-accessible
	STATUS      current
	DESCRIPTION
	"Table for l2tpMapFound"
	::={l2tpMapFound 4}

l2tpMapFoundLevelEntry OBJECT-TYPE
	SYNTAX      L2tpMapFoundLevelEntry
	MAX-ACCESS  not-accessible
	STATUS      current
	DESCRIPTION
	"Table entry for l2tpMapFound"
	INDEX { l2tpMapFoundLevelName }
	::={l2tpMapFoundLevelTable 1}

L2tpMapFoundLevelEntry ::=
	SEQUENCE {
		l2tpMapFoundLevelName	DisplayString,
		l2tpMapFoundLevelVal	Counter64,
		l2tpMapFoundLevelMom	CounterBasedGauge64,
		l2tpMapFoundLevelMax	CounterBasedGauge64
	}

l2tpMapFoundLevelName OBJECT-TYPE
	SYNTAX      DisplayString
	MAX-ACCESS  not-accessible
	STATUS      current
	DESCRIPTION
	"Table entry display string for l2tpMapFound"
	::={l2tpMapFoundLevelEntry 1}

l2tpMapFoundLevelVal OBJECT-TYPE
	SYNTAX	 Counter64
	MAX-ACCESS  read-only
	STATUS      current
	DESCRIPTION
	"Table entry attribute for l2tpMapFound"
	::={l2tpMapFoundLevelEntry 2}

l2tpMapFoundLevelMom OBJECT-TYPE
	SYNTAX	 CounterBasedGauge64
	MAX-ACCESS  read-only
	STATUS      current
	DESCRIPTION
	"Table entry attribute for l2tpMapFound"
	::={l2tpMapFoundLevelEntry 3}

l2tpMapFoundLevelMax OBJECT-TYPE
	SYNTAX	 CounterBasedGauge64
	MAX-ACCESS  read-only
	STATUS      current
	DESCRIPTION
	"Table entry attribute for l2tpMapFound"
	::={l2tpMapFoundLevelEntry 4}


system	OBJECT IDENTIFIER ::={sysdiag 133}

systemCPULoad	OBJECT IDENTIFIER ::={system 1}

systemCPULoadVal	OBJECT-TYPE
	SYNTAX	 Unsigned32
	MAX-ACCESS read-only
	STATUS current
	DESCRIPTION "CPU load"

	::={systemCPULoad 1}

systemCPULoadMax	OBJECT-TYPE
	SYNTAX	 Unsigned32
	MAX-ACCESS read-only
	STATUS current
	DESCRIPTION "CPU load"

	::={systemCPULoad 3}

systemCPULoadLevelTable OBJECT-TYPE
	SYNTAX      SEQUENCE OF SystemCPULoadLevelEntry
	MAX-ACCESS  not-accessible
	STATUS      current
	DESCRIPTION
	"Table for systemCPULoad"
	::={systemCPULoad 4}

systemCPULoadLevelEntry OBJECT-TYPE
	SYNTAX      SystemCPULoadLevelEntry
	MAX-ACCESS  not-accessible
	STATUS      current
	DESCRIPTION
	"Table entry for systemCPULoad"
	INDEX { systemCPULoadLevelName }
	::={systemCPULoadLevelTable 1}

SystemCPULoadLevelEntry ::=
	SEQUENCE {
		systemCPULoadLevelName	DisplayString,
		systemCPULoadLevelVal	Unsigned32,
		systemCPULoadLevelMax	Unsigned32
	}

systemCPULoadLevelName OBJECT-TYPE
	SYNTAX      DisplayString
	MAX-ACCESS  not-accessible
	STATUS      current
	DESCRIPTION
	"Table entry display string for systemCPULoad"
	::={systemCPULoadLevelEntry 1}

systemCPULoadLevelVal OBJECT-TYPE
	SYNTAX	 Unsigned32
	MAX-ACCESS  read-only
	STATUS      current
	DESCRIPTION
	"Table entry attribute for systemCPULoad"
	::={systemCPULoadLevelEntry 2}

systemCPULoadLevelMax OBJECT-TYPE
	SYNTAX	 Unsigned32
	MAX-ACCESS  read-only
	STATUS      current
	DESCRIPTION
	"Table entry attribute for systemCPULoad"
	::={systemCPULoadLevelEntry 4}


systemMemTotal	OBJECT IDENTIFIER ::={system 2}

systemMemTotalVal	OBJECT-TYPE
	SYNTAX	 CounterBasedGauge64
	MAX-ACCESS read-only
	STATUS current
	DESCRIPTION "Total RAM"

	::={systemMemTotal 1}

systemMemTotalMax	OBJECT-TYPE
	SYNTAX	 CounterBasedGauge64
	MAX-ACCESS read-only
	STATUS current
	DESCRIPTION "Total RAM"

	::={systemMemTotal 3}

systemMemTotalLevelTable OBJECT-TYPE
	SYNTAX      SEQUENCE OF SystemMemTotalLevelEntry
	MAX-ACCESS  not-accessible
	STATUS      current
	DESCRIPTION
	"Table for systemMemTotal"
	::={systemMemTotal 4}

systemMemTotalLevelEntry OBJECT-TYPE
	SYNTAX      SystemMemTotalLevelEntry
	MAX-ACCESS  not-accessible
	STATUS      current
	DESCRIPTION
	"Table entry for systemMemTotal"
	INDEX { systemMemTotalLevelName }
	::={systemMemTotalLevelTable 1}

SystemMemTotalLevelEntry ::=
	SEQUENCE {
		systemMemTotalLevelName	DisplayString,
		systemMemTotalLevelVal	CounterBasedGauge64,
		systemMemTotalLevelMax	CounterBasedGauge64
	}

systemMemTotalLevelName OBJECT-TYPE
	SYNTAX      DisplayString
	MAX-ACCESS  not-accessible
	STATUS      current
	DESCRIPTION
	"Table entry display string for systemMemTotal"
	::={systemMemTotalLevelEntry 1}

systemMemTotalLevelVal OBJECT-TYPE
	SYNTAX	 CounterBasedGauge64
	MAX-ACCESS  read-only
	STATUS      current
	DESCRIPTION
	"Table entry attribute for systemMemTotal"
	::={systemMemTotalLevelEntry 2}

systemMemTotalLevelMax OBJECT-TYPE
	SYNTAX	 CounterBasedGauge64
	MAX-ACCESS  read-only
	STATUS      current
	DESCRIPTION
	"Table entry attribute for systemMemTotal"
	::={systemMemTotalLevelEntry 4}


systemMemFree	OBJECT IDENTIFIER ::={system 3}

systemMemFreeVal	OBJECT-TYPE
	SYNTAX	 CounterBasedGauge64
	MAX-ACCESS read-only
	STATUS current
	DESCRIPTION "Free RAM"

	::={systemMemFree 1}

systemMemFreeMax	OBJECT-TYPE
	SYNTAX	 CounterBasedGauge64
	MAX-ACCESS read-only
	STATUS current
	DESCRIPTION "Free RAM"

	::={systemMemFree 3}

systemMemFreeLevelTable OBJECT-TYPE
	SYNTAX      SEQUENCE OF SystemMemFreeLevelEntry
	MAX-ACCESS  not-accessible
	STATUS      current
	DESCRIPTION
	"Table for systemMemFree"
	::={systemMemFree 4}

systemMemFreeLevelEntry OBJECT-TYPE
	SYNTAX      SystemMemFreeLevelEntry
	MAX-ACCESS  not-accessible
	STATUS      current
	DESCRIPTION
	"Table entry for systemMemFree"
	INDEX { systemMemFreeLevelName }
	::={systemMemFreeLevelTable 1}

SystemMemFreeLevelEntry ::=
	SEQUENCE {
		systemMemFreeLevelName	DisplayString,
		systemMemFreeLevelVal	CounterBasedGauge64,
		systemMemFreeLevelMax	CounterBasedGauge64
	}

systemMemFreeLevelName OBJECT-TYPE
	SYNTAX      DisplayString
	MAX-ACCESS  not-accessible
	STATUS      current
	DESCRIPTION
	"Table entry display string for systemMemFree"
	::={systemMemFreeLevelEntry 1}

systemMemFreeLevelVal OBJECT-TYPE
	SYNTAX	 CounterBasedGauge64
	MAX-ACCESS  read-only
	STATUS      current
	DESCRIPTION
	"Table entry attribute for systemMemFree"
	::={systemMemFreeLevelEntry 2}

systemMemFreeLevelMax OBJECT-TYPE
	SYNTAX	 CounterBasedGauge64
	MAX-ACCESS  read-only
	STATUS      current
	DESCRIPTION
	"Table entry attribute for systemMemFree"
	::={systemMemFreeLevelEntry 4}


systemSwapTotal	OBJECT IDENTIFIER ::={system 4}

systemSwapTotalVal	OBJECT-TYPE
	SYNTAX	 CounterBasedGauge64
	MAX-ACCESS read-only
	STATUS current
	DESCRIPTION "Total swap"

	::={systemSwapTotal 1}

systemSwapTotalMax	OBJECT-TYPE
	SYNTAX	 CounterBasedGauge64
	MAX-ACCESS read-only
	STATUS current
	DESCRIPTION "Total swap"

	::={systemSwapTotal 3}

systemSwapTotalLevelTable OBJECT-TYPE
	SYNTAX      SEQUENCE OF SystemSwapTotalLevelEntry
	MAX-ACCESS  not-accessible
	STATUS      current
	DESCRIPTION
	"Table for systemSwapTotal"
	::={systemSwapTotal 4}

systemSwapTotalLevelEntry OBJECT-TYPE
	SYNTAX      SystemSwapTotalLevelEntry
	MAX-ACCESS  not-accessible
	STATUS      current
	DESCRIPTION
	"Table entry for systemSwapTotal"
	INDEX { systemSwapTotalLevelName }
	::={systemSwapTotalLevelTable 1}

SystemSwapTotalLevelEntry ::=
	SEQUENCE {
		systemSwapTotalLevelName	DisplayString,
		systemSwapTotalLevelVal	CounterBasedGauge64,
		systemSwapTotalLevelMax	CounterBasedGauge64
	}

systemSwapTotalLevelName OBJECT-TYPE
	SYNTAX      DisplayString
	MAX-ACCESS  not-accessible
	STATUS      current
	DESCRIPTION
	"Table entry display string for systemSwapTotal"
	::={systemSwapTotalLevelEntry 1}

systemSwapTotalLevelVal OBJECT-TYPE
	SYNTAX	 CounterBasedGauge64
	MAX-ACCESS  read-only
	STATUS      current
	DESCRIPTION
	"Table entry attribute for systemSwapTotal"
	::={systemSwapTotalLevelEntry 2}

systemSwapTotalLevelMax OBJECT-TYPE
	SYNTAX	 CounterBasedGauge64
	MAX-ACCESS  read-only
	STATUS      current
	DESCRIPTION
	"Table entry attribute for systemSwapTotal"
	::={systemSwapTotalLevelEntry 4}


systemSwapFree	OBJECT IDENTIFIER ::={system 5}

systemSwapFreeVal	OBJECT-TYPE
	SYNTAX	 CounterBasedGauge64
	MAX-ACCESS read-only
	STATUS current
	DESCRIPTION "Free swap"

	::={systemSwapFree 1}

systemSwapFreeMax	OBJECT-TYPE
	SYNTAX	 CounterBasedGauge64
	MAX-ACCESS read-only
	STATUS current
	DESCRIPTION "Free swap"

	::={systemSwapFree 3}

systemSwapFreeLevelTable OBJECT-TYPE
	SYNTAX      SEQUENCE OF SystemSwapFreeLevelEntry
	MAX-ACCESS  not-accessible
	STATUS      current
	DESCRIPTION
	"Table for systemSwapFree"
	::={systemSwapFree 4}

systemSwapFreeLevelEntry OBJECT-TYPE
	SYNTAX      SystemSwapFreeLevelEntry
	MAX-ACCESS  not-accessible
	STATUS      current
	DESCRIPTION
	"Table entry for systemSwapFree"
	INDEX { systemSwapFreeLevelName }
	::={systemSwapFreeLevelTable 1}

SystemSwapFreeLevelEntry ::=
	SEQUENCE {
		systemSwapFreeLevelName	DisplayString,
		systemSwapFreeLevelVal	CounterBasedGauge64,
		systemSwapFreeLevelMax	CounterBasedGauge64
	}

systemSwapFreeLevelName OBJECT-TYPE
	SYNTAX      DisplayString
	MAX-ACCESS  not-accessible
	STATUS      current
	DESCRIPTION
	"Table entry display string for systemSwapFree"
	::={systemSwapFreeLevelEntry 1}

systemSwapFreeLevelVal OBJECT-TYPE
	SYNTAX	 CounterBasedGauge64
	MAX-ACCESS  read-only
	STATUS      current
	DESCRIPTION
	"Table entry attribute for systemSwapFree"
	::={systemSwapFreeLevelEntry 2}

systemSwapFreeLevelMax OBJECT-TYPE
	SYNTAX	 CounterBasedGauge64
	MAX-ACCESS  read-only
	STATUS      current
	DESCRIPTION
	"Table entry attribute for systemSwapFree"
	::={systemSwapFreeLevelEntry 4}


systemUptime	OBJECT IDENTIFIER ::={system 6}

systemUptimeVal	OBJECT-TYPE
	SYNTAX	 TimeTicks
	MAX-ACCESS read-only
	STATUS current
	DESCRIPTION "Uptime"

	::={systemUptime 1}

systemUptimeLevelTable OBJECT-TYPE
	SYNTAX      SEQUENCE OF SystemUptimeLevelEntry
	MAX-ACCESS  not-accessible
	STATUS      current
	DESCRIPTION
	"Table for systemUptime"
	::={systemUptime 2}

systemUptimeLevelEntry OBJECT-TYPE
	SYNTAX      SystemUptimeLevelEntry
	MAX-ACCESS  not-accessible
	STATUS      current
	DESCRIPTION
	"Table entry for systemUptime"
	INDEX { systemUptimeLevelName }
	::={systemUptimeLevelTable 1}

SystemUptimeLevelEntry ::=
	SEQUENCE {
		systemUptimeLevelName	DisplayString,
		systemUptimeLevelVal	TimeTicks
	}

systemUptimeLevelName OBJECT-TYPE
	SYNTAX      DisplayString
	MAX-ACCESS  not-accessible
	STATUS      current
	DESCRIPTION
	"Table entry display string for systemUptime"
	::={systemUptimeLevelEntry 1}

systemUptimeLevelVal OBJECT-TYPE
	SYNTAX	 TimeTicks
	MAX-ACCESS  read-only
	STATUS      current
	DESCRIPTION
	"Table entry attribute for systemUptime"
	::={systemUptimeLevelEntry 2}


systemHdUsage	OBJECT IDENTIFIER ::={system 7}

systemHdUsageVal	OBJECT-TYPE
	SYNTAX	 Unsigned32
	MAX-ACCESS read-only
	STATUS current
	DESCRIPTION "System disk usage"

	::={systemHdUsage 1}

systemHdUsageMax	OBJECT-TYPE
	SYNTAX	 Unsigned32
	MAX-ACCESS read-only
	STATUS current
	DESCRIPTION "System disk usage"

	::={systemHdUsage 3}

systemHdUsageLevelTable OBJECT-TYPE
	SYNTAX      SEQUENCE OF SystemHdUsageLevelEntry
	MAX-ACCESS  not-accessible
	STATUS      current
	DESCRIPTION
	"Table for systemHdUsage"
	::={systemHdUsage 4}

systemHdUsageLevelEntry OBJECT-TYPE
	SYNTAX      SystemHdUsageLevelEntry
	MAX-ACCESS  not-accessible
	STATUS      current
	DESCRIPTION
	"Table entry for systemHdUsage"
	INDEX { systemHdUsageLevelName }
	::={systemHdUsageLevelTable 1}

SystemHdUsageLevelEntry ::=
	SEQUENCE {
		systemHdUsageLevelName	DisplayString,
		systemHdUsageLevelVal	Unsigned32,
		systemHdUsageLevelMax	Unsigned32
	}

systemHdUsageLevelName OBJECT-TYPE
	SYNTAX      DisplayString
	MAX-ACCESS  not-accessible
	STATUS      current
	DESCRIPTION
	"Table entry display string for systemHdUsage"
	::={systemHdUsageLevelEntry 1}

systemHdUsageLevelVal OBJECT-TYPE
	SYNTAX	 Unsigned32
	MAX-ACCESS  read-only
	STATUS      current
	DESCRIPTION
	"Table entry attribute for systemHdUsage"
	::={systemHdUsageLevelEntry 2}

systemHdUsageLevelMax OBJECT-TYPE
	SYNTAX	 Unsigned32
	MAX-ACCESS  read-only
	STATUS      current
	DESCRIPTION
	"Table entry attribute for systemHdUsage"
	::={systemHdUsageLevelEntry 4}


systemHdSize	OBJECT IDENTIFIER ::={system 8}

systemHdSizeVal	OBJECT-TYPE
	SYNTAX	 CounterBasedGauge64
	MAX-ACCESS read-only
	STATUS current
	DESCRIPTION "System disk size"

	::={systemHdSize 1}

systemHdSizeMax	OBJECT-TYPE
	SYNTAX	 CounterBasedGauge64
	MAX-ACCESS read-only
	STATUS current
	DESCRIPTION "System disk size"

	::={systemHdSize 3}

systemHdSizeLevelTable OBJECT-TYPE
	SYNTAX      SEQUENCE OF SystemHdSizeLevelEntry
	MAX-ACCESS  not-accessible
	STATUS      current
	DESCRIPTION
	"Table for systemHdSize"
	::={systemHdSize 4}

systemHdSizeLevelEntry OBJECT-TYPE
	SYNTAX      SystemHdSizeLevelEntry
	MAX-ACCESS  not-accessible
	STATUS      current
	DESCRIPTION
	"Table entry for systemHdSize"
	INDEX { systemHdSizeLevelName }
	::={systemHdSizeLevelTable 1}

SystemHdSizeLevelEntry ::=
	SEQUENCE {
		systemHdSizeLevelName	DisplayString,
		systemHdSizeLevelVal	CounterBasedGauge64,
		systemHdSizeLevelMax	CounterBasedGauge64
	}

systemHdSizeLevelName OBJECT-TYPE
	SYNTAX      DisplayString
	MAX-ACCESS  not-accessible
	STATUS      current
	DESCRIPTION
	"Table entry display string for systemHdSize"
	::={systemHdSizeLevelEntry 1}

systemHdSizeLevelVal OBJECT-TYPE
	SYNTAX	 CounterBasedGauge64
	MAX-ACCESS  read-only
	STATUS      current
	DESCRIPTION
	"Table entry attribute for systemHdSize"
	::={systemHdSizeLevelEntry 2}

systemHdSizeLevelMax OBJECT-TYPE
	SYNTAX	 CounterBasedGauge64
	MAX-ACCESS  read-only
	STATUS      current
	DESCRIPTION
	"Table entry attribute for systemHdSize"
	::={systemHdSizeLevelEntry 4}


systemIfRxBytes	OBJECT IDENTIFIER ::={system 9}

systemIfRxBytesVal	OBJECT-TYPE
	SYNTAX	 Counter64
	MAX-ACCESS read-only
	STATUS current
	DESCRIPTION "Interface bytes received"

	::={systemIfRxBytes 1}

systemIfRxBytesMom	OBJECT-TYPE
	SYNTAX	 CounterBasedGauge64
	MAX-ACCESS read-only
	STATUS current
	DESCRIPTION "Interface bytes received"

	::={systemIfRxBytes 2}

systemIfRxBytesMax	OBJECT-TYPE
	SYNTAX	 CounterBasedGauge64
	MAX-ACCESS read-only
	STATUS current
	DESCRIPTION "Interface bytes received"

	::={systemIfRxBytes 3}

systemIfRxBytesLevelTable OBJECT-TYPE
	SYNTAX      SEQUENCE OF SystemIfRxBytesLevelEntry
	MAX-ACCESS  not-accessible
	STATUS      current
	DESCRIPTION
	"Table for systemIfRxBytes"
	::={systemIfRxBytes 4}

systemIfRxBytesLevelEntry OBJECT-TYPE
	SYNTAX      SystemIfRxBytesLevelEntry
	MAX-ACCESS  not-accessible
	STATUS      current
	DESCRIPTION
	"Table entry for systemIfRxBytes"
	INDEX { systemIfRxBytesLevelName }
	::={systemIfRxBytesLevelTable 1}

SystemIfRxBytesLevelEntry ::=
	SEQUENCE {
		systemIfRxBytesLevelName	DisplayString,
		systemIfRxBytesLevelVal	Counter64,
		systemIfRxBytesLevelMom	CounterBasedGauge64,
		systemIfRxBytesLevelMax	CounterBasedGauge64
	}

systemIfRxBytesLevelName OBJECT-TYPE
	SYNTAX      DisplayString
	MAX-ACCESS  not-accessible
	STATUS      current
	DESCRIPTION
	"Table entry display string for systemIfRxBytes"
	::={systemIfRxBytesLevelEntry 1}

systemIfRxBytesLevelVal OBJECT-TYPE
	SYNTAX	 Counter64
	MAX-ACCESS  read-only
	STATUS      current
	DESCRIPTION
	"Table entry attribute for systemIfRxBytes"
	::={systemIfRxBytesLevelEntry 2}

systemIfRxBytesLevelMom OBJECT-TYPE
	SYNTAX	 CounterBasedGauge64
	MAX-ACCESS  read-only
	STATUS      current
	DESCRIPTION
	"Table entry attribute for systemIfRxBytes"
	::={systemIfRxBytesLevelEntry 3}

systemIfRxBytesLevelMax OBJECT-TYPE
	SYNTAX	 CounterBasedGauge64
	MAX-ACCESS  read-only
	STATUS      current
	DESCRIPTION
	"Table entry attribute for systemIfRxBytes"
	::={systemIfRxBytesLevelEntry 4}


systemIfTxBytes	OBJECT IDENTIFIER ::={system 10}

systemIfTxBytesVal	OBJECT-TYPE
	SYNTAX	 Counter64
	MAX-ACCESS read-only
	STATUS current
	DESCRIPTION "Interface bytes sent"

	::={systemIfTxBytes 1}

systemIfTxBytesMom	OBJECT-TYPE
	SYNTAX	 CounterBasedGauge64
	MAX-ACCESS read-only
	STATUS current
	DESCRIPTION "Interface bytes sent"

	::={systemIfTxBytes 2}

systemIfTxBytesMax	OBJECT-TYPE
	SYNTAX	 CounterBasedGauge64
	MAX-ACCESS read-only
	STATUS current
	DESCRIPTION "Interface bytes sent"

	::={systemIfTxBytes 3}

systemIfTxBytesLevelTable OBJECT-TYPE
	SYNTAX      SEQUENCE OF SystemIfTxBytesLevelEntry
	MAX-ACCESS  not-accessible
	STATUS      current
	DESCRIPTION
	"Table for systemIfTxBytes"
	::={systemIfTxBytes 4}

systemIfTxBytesLevelEntry OBJECT-TYPE
	SYNTAX      SystemIfTxBytesLevelEntry
	MAX-ACCESS  not-accessible
	STATUS      current
	DESCRIPTION
	"Table entry for systemIfTxBytes"
	INDEX { systemIfTxBytesLevelName }
	::={systemIfTxBytesLevelTable 1}

SystemIfTxBytesLevelEntry ::=
	SEQUENCE {
		systemIfTxBytesLevelName	DisplayString,
		systemIfTxBytesLevelVal	Counter64,
		systemIfTxBytesLevelMom	CounterBasedGauge64,
		systemIfTxBytesLevelMax	CounterBasedGauge64
	}

systemIfTxBytesLevelName OBJECT-TYPE
	SYNTAX      DisplayString
	MAX-ACCESS  not-accessible
	STATUS      current
	DESCRIPTION
	"Table entry display string for systemIfTxBytes"
	::={systemIfTxBytesLevelEntry 1}

systemIfTxBytesLevelVal OBJECT-TYPE
	SYNTAX	 Counter64
	MAX-ACCESS  read-only
	STATUS      current
	DESCRIPTION
	"Table entry attribute for systemIfTxBytes"
	::={systemIfTxBytesLevelEntry 2}

systemIfTxBytesLevelMom OBJECT-TYPE
	SYNTAX	 CounterBasedGauge64
	MAX-ACCESS  read-only
	STATUS      current
	DESCRIPTION
	"Table entry attribute for systemIfTxBytes"
	::={systemIfTxBytesLevelEntry 3}

systemIfTxBytesLevelMax OBJECT-TYPE
	SYNTAX	 CounterBasedGauge64
	MAX-ACCESS  read-only
	STATUS      current
	DESCRIPTION
	"Table entry attribute for systemIfTxBytes"
	::={systemIfTxBytesLevelEntry 4}


systemIfRxPkts	OBJECT IDENTIFIER ::={system 11}

systemIfRxPktsVal	OBJECT-TYPE
	SYNTAX	 Counter64
	MAX-ACCESS read-only
	STATUS current
	DESCRIPTION "Interface packets received"

	::={systemIfRxPkts 1}

systemIfRxPktsMom	OBJECT-TYPE
	SYNTAX	 CounterBasedGauge64
	MAX-ACCESS read-only
	STATUS current
	DESCRIPTION "Interface packets received"

	::={systemIfRxPkts 2}

systemIfRxPktsMax	OBJECT-TYPE
	SYNTAX	 CounterBasedGauge64
	MAX-ACCESS read-only
	STATUS current
	DESCRIPTION "Interface packets received"

	::={systemIfRxPkts 3}

systemIfRxPktsLevelTable OBJECT-TYPE
	SYNTAX      SEQUENCE OF SystemIfRxPktsLevelEntry
	MAX-ACCESS  not-accessible
	STATUS      current
	DESCRIPTION
	"Table for systemIfRxPkts"
	::={systemIfRxPkts 4}

systemIfRxPktsLevelEntry OBJECT-TYPE
	SYNTAX      SystemIfRxPktsLevelEntry
	MAX-ACCESS  not-accessible
	STATUS      current
	DESCRIPTION
	"Table entry for systemIfRxPkts"
	INDEX { systemIfRxPktsLevelName }
	::={systemIfRxPktsLevelTable 1}

SystemIfRxPktsLevelEntry ::=
	SEQUENCE {
		systemIfRxPktsLevelName	DisplayString,
		systemIfRxPktsLevelVal	Counter64,
		systemIfRxPktsLevelMom	CounterBasedGauge64,
		systemIfRxPktsLevelMax	CounterBasedGauge64
	}

systemIfRxPktsLevelName OBJECT-TYPE
	SYNTAX      DisplayString
	MAX-ACCESS  not-accessible
	STATUS      current
	DESCRIPTION
	"Table entry display string for systemIfRxPkts"
	::={systemIfRxPktsLevelEntry 1}

systemIfRxPktsLevelVal OBJECT-TYPE
	SYNTAX	 Counter64
	MAX-ACCESS  read-only
	STATUS      current
	DESCRIPTION
	"Table entry attribute for systemIfRxPkts"
	::={systemIfRxPktsLevelEntry 2}

systemIfRxPktsLevelMom OBJECT-TYPE
	SYNTAX	 CounterBasedGauge64
	MAX-ACCESS  read-only
	STATUS      current
	DESCRIPTION
	"Table entry attribute for systemIfRxPkts"
	::={systemIfRxPktsLevelEntry 3}

systemIfRxPktsLevelMax OBJECT-TYPE
	SYNTAX	 CounterBasedGauge64
	MAX-ACCESS  read-only
	STATUS      current
	DESCRIPTION
	"Table entry attribute for systemIfRxPkts"
	::={systemIfRxPktsLevelEntry 4}


systemIfTxPkts	OBJECT IDENTIFIER ::={system 12}

systemIfTxPktsVal	OBJECT-TYPE
	SYNTAX	 Counter64
	MAX-ACCESS read-only
	STATUS current
	DESCRIPTION "Interface packets sent"

	::={systemIfTxPkts 1}

systemIfTxPktsMom	OBJECT-TYPE
	SYNTAX	 CounterBasedGauge64
	MAX-ACCESS read-only
	STATUS current
	DESCRIPTION "Interface packets sent"

	::={systemIfTxPkts 2}

systemIfTxPktsMax	OBJECT-TYPE
	SYNTAX	 CounterBasedGauge64
	MAX-ACCESS read-only
	STATUS current
	DESCRIPTION "Interface packets sent"

	::={systemIfTxPkts 3}

systemIfTxPktsLevelTable OBJECT-TYPE
	SYNTAX      SEQUENCE OF SystemIfTxPktsLevelEntry
	MAX-ACCESS  not-accessible
	STATUS      current
	DESCRIPTION
	"Table for systemIfTxPkts"
	::={systemIfTxPkts 4}

systemIfTxPktsLevelEntry OBJECT-TYPE
	SYNTAX      SystemIfTxPktsLevelEntry
	MAX-ACCESS  not-accessible
	STATUS      current
	DESCRIPTION
	"Table entry for systemIfTxPkts"
	INDEX { systemIfTxPktsLevelName }
	::={systemIfTxPktsLevelTable 1}

SystemIfTxPktsLevelEntry ::=
	SEQUENCE {
		systemIfTxPktsLevelName	DisplayString,
		systemIfTxPktsLevelVal	Counter64,
		systemIfTxPktsLevelMom	CounterBasedGauge64,
		systemIfTxPktsLevelMax	CounterBasedGauge64
	}

systemIfTxPktsLevelName OBJECT-TYPE
	SYNTAX      DisplayString
	MAX-ACCESS  not-accessible
	STATUS      current
	DESCRIPTION
	"Table entry display string for systemIfTxPkts"
	::={systemIfTxPktsLevelEntry 1}

systemIfTxPktsLevelVal OBJECT-TYPE
	SYNTAX	 Counter64
	MAX-ACCESS  read-only
	STATUS      current
	DESCRIPTION
	"Table entry attribute for systemIfTxPkts"
	::={systemIfTxPktsLevelEntry 2}

systemIfTxPktsLevelMom OBJECT-TYPE
	SYNTAX	 CounterBasedGauge64
	MAX-ACCESS  read-only
	STATUS      current
	DESCRIPTION
	"Table entry attribute for systemIfTxPkts"
	::={systemIfTxPktsLevelEntry 3}

systemIfTxPktsLevelMax OBJECT-TYPE
	SYNTAX	 CounterBasedGauge64
	MAX-ACCESS  read-only
	STATUS      current
	DESCRIPTION
	"Table entry attribute for systemIfTxPkts"
	::={systemIfTxPktsLevelEntry 4}


systemInterrupts	OBJECT IDENTIFIER ::={system 13}

systemInterruptsVal	OBJECT-TYPE
	SYNTAX	 Counter64
	MAX-ACCESS read-only
	STATUS current
	DESCRIPTION "Interrupts"

	::={systemInterrupts 1}

systemInterruptsMom	OBJECT-TYPE
	SYNTAX	 CounterBasedGauge64
	MAX-ACCESS read-only
	STATUS current
	DESCRIPTION "Interrupts"

	::={systemInterrupts 2}

systemInterruptsMax	OBJECT-TYPE
	SYNTAX	 CounterBasedGauge64
	MAX-ACCESS read-only
	STATUS current
	DESCRIPTION "Interrupts"

	::={systemInterrupts 3}

systemInterruptsLevelTable OBJECT-TYPE
	SYNTAX      SEQUENCE OF SystemInterruptsLevelEntry
	MAX-ACCESS  not-accessible
	STATUS      current
	DESCRIPTION
	"Table for systemInterrupts"
	::={systemInterrupts 4}

systemInterruptsLevelEntry OBJECT-TYPE
	SYNTAX      SystemInterruptsLevelEntry
	MAX-ACCESS  not-accessible
	STATUS      current
	DESCRIPTION
	"Table entry for systemInterrupts"
	INDEX { systemInterruptsLevelName }
	::={systemInterruptsLevelTable 1}

SystemInterruptsLevelEntry ::=
	SEQUENCE {
		systemInterruptsLevelName	DisplayString,
		systemInterruptsLevelVal	Counter64,
		systemInterruptsLevelMom	CounterBasedGauge64,
		systemInterruptsLevelMax	CounterBasedGauge64
	}

systemInterruptsLevelName OBJECT-TYPE
	SYNTAX      DisplayString
	MAX-ACCESS  not-accessible
	STATUS      current
	DESCRIPTION
	"Table entry display string for systemInterrupts"
	::={systemInterruptsLevelEntry 1}

systemInterruptsLevelVal OBJECT-TYPE
	SYNTAX	 Counter64
	MAX-ACCESS  read-only
	STATUS      current
	DESCRIPTION
	"Table entry attribute for systemInterrupts"
	::={systemInterruptsLevelEntry 2}

systemInterruptsLevelMom OBJECT-TYPE
	SYNTAX	 CounterBasedGauge64
	MAX-ACCESS  read-only
	STATUS      current
	DESCRIPTION
	"Table entry attribute for systemInterrupts"
	::={systemInterruptsLevelEntry 3}

systemInterruptsLevelMax OBJECT-TYPE
	SYNTAX	 CounterBasedGauge64
	MAX-ACCESS  read-only
	STATUS      current
	DESCRIPTION
	"Table entry attribute for systemInterrupts"
	::={systemInterruptsLevelEntry 4}


systemContextSwitches	OBJECT IDENTIFIER ::={system 14}

systemContextSwitchesVal	OBJECT-TYPE
	SYNTAX	 Counter64
	MAX-ACCESS read-only
	STATUS current
	DESCRIPTION "Context switches"

	::={systemContextSwitches 1}

systemContextSwitchesMom	OBJECT-TYPE
	SYNTAX	 CounterBasedGauge64
	MAX-ACCESS read-only
	STATUS current
	DESCRIPTION "Context switches"

	::={systemContextSwitches 2}

systemContextSwitchesMax	OBJECT-TYPE
	SYNTAX	 CounterBasedGauge64
	MAX-ACCESS read-only
	STATUS current
	DESCRIPTION "Context switches"

	::={systemContextSwitches 3}

systemContextSwitchesLevelTable OBJECT-TYPE
	SYNTAX      SEQUENCE OF SystemContextSwitchesLevelEntry
	MAX-ACCESS  not-accessible
	STATUS      current
	DESCRIPTION
	"Table for systemContextSwitches"
	::={systemContextSwitches 4}

systemContextSwitchesLevelEntry OBJECT-TYPE
	SYNTAX      SystemContextSwitchesLevelEntry
	MAX-ACCESS  not-accessible
	STATUS      current
	DESCRIPTION
	"Table entry for systemContextSwitches"
	INDEX { systemContextSwitchesLevelName }
	::={systemContextSwitchesLevelTable 1}

SystemContextSwitchesLevelEntry ::=
	SEQUENCE {
		systemContextSwitchesLevelName	DisplayString,
		systemContextSwitchesLevelVal	Counter64,
		systemContextSwitchesLevelMom	CounterBasedGauge64,
		systemContextSwitchesLevelMax	CounterBasedGauge64
	}

systemContextSwitchesLevelName OBJECT-TYPE
	SYNTAX      DisplayString
	MAX-ACCESS  not-accessible
	STATUS      current
	DESCRIPTION
	"Table entry display string for systemContextSwitches"
	::={systemContextSwitchesLevelEntry 1}

systemContextSwitchesLevelVal OBJECT-TYPE
	SYNTAX	 Counter64
	MAX-ACCESS  read-only
	STATUS      current
	DESCRIPTION
	"Table entry attribute for systemContextSwitches"
	::={systemContextSwitchesLevelEntry 2}

systemContextSwitchesLevelMom OBJECT-TYPE
	SYNTAX	 CounterBasedGauge64
	MAX-ACCESS  read-only
	STATUS      current
	DESCRIPTION
	"Table entry attribute for systemContextSwitches"
	::={systemContextSwitchesLevelEntry 3}

systemContextSwitchesLevelMax OBJECT-TYPE
	SYNTAX	 CounterBasedGauge64
	MAX-ACCESS  read-only
	STATUS      current
	DESCRIPTION
	"Table entry attribute for systemContextSwitches"
	::={systemContextSwitchesLevelEntry 4}


systemUdpTxQueue	OBJECT IDENTIFIER ::={system 15}

systemUdpTxQueueVal	OBJECT-TYPE
	SYNTAX	 CounterBasedGauge64
	MAX-ACCESS read-only
	STATUS current
	DESCRIPTION "UDP Tx Queue"

	::={systemUdpTxQueue 1}

systemUdpTxQueueMax	OBJECT-TYPE
	SYNTAX	 CounterBasedGauge64
	MAX-ACCESS read-only
	STATUS current
	DESCRIPTION "UDP Tx Queue"

	::={systemUdpTxQueue 3}

systemUdpTxQueueLevelTable OBJECT-TYPE
	SYNTAX      SEQUENCE OF SystemUdpTxQueueLevelEntry
	MAX-ACCESS  not-accessible
	STATUS      current
	DESCRIPTION
	"Table for systemUdpTxQueue"
	::={systemUdpTxQueue 4}

systemUdpTxQueueLevelEntry OBJECT-TYPE
	SYNTAX      SystemUdpTxQueueLevelEntry
	MAX-ACCESS  not-accessible
	STATUS      current
	DESCRIPTION
	"Table entry for systemUdpTxQueue"
	INDEX { systemUdpTxQueueLevelName }
	::={systemUdpTxQueueLevelTable 1}

SystemUdpTxQueueLevelEntry ::=
	SEQUENCE {
		systemUdpTxQueueLevelName	DisplayString,
		systemUdpTxQueueLevelVal	CounterBasedGauge64,
		systemUdpTxQueueLevelMax	CounterBasedGauge64
	}

systemUdpTxQueueLevelName OBJECT-TYPE
	SYNTAX      DisplayString
	MAX-ACCESS  not-accessible
	STATUS      current
	DESCRIPTION
	"Table entry display string for systemUdpTxQueue"
	::={systemUdpTxQueueLevelEntry 1}

systemUdpTxQueueLevelVal OBJECT-TYPE
	SYNTAX	 CounterBasedGauge64
	MAX-ACCESS  read-only
	STATUS      current
	DESCRIPTION
	"Table entry attribute for systemUdpTxQueue"
	::={systemUdpTxQueueLevelEntry 2}

systemUdpTxQueueLevelMax OBJECT-TYPE
	SYNTAX	 CounterBasedGauge64
	MAX-ACCESS  read-only
	STATUS      current
	DESCRIPTION
	"Table entry attribute for systemUdpTxQueue"
	::={systemUdpTxQueueLevelEntry 4}


systemUdpRxQueue	OBJECT IDENTIFIER ::={system 16}

systemUdpRxQueueVal	OBJECT-TYPE
	SYNTAX	 CounterBasedGauge64
	MAX-ACCESS read-only
	STATUS current
	DESCRIPTION "UDP Rx Queue"

	::={systemUdpRxQueue 1}

systemUdpRxQueueMax	OBJECT-TYPE
	SYNTAX	 CounterBasedGauge64
	MAX-ACCESS read-only
	STATUS current
	DESCRIPTION "UDP Rx Queue"

	::={systemUdpRxQueue 3}

systemUdpRxQueueLevelTable OBJECT-TYPE
	SYNTAX      SEQUENCE OF SystemUdpRxQueueLevelEntry
	MAX-ACCESS  not-accessible
	STATUS      current
	DESCRIPTION
	"Table for systemUdpRxQueue"
	::={systemUdpRxQueue 4}

systemUdpRxQueueLevelEntry OBJECT-TYPE
	SYNTAX      SystemUdpRxQueueLevelEntry
	MAX-ACCESS  not-accessible
	STATUS      current
	DESCRIPTION
	"Table entry for systemUdpRxQueue"
	INDEX { systemUdpRxQueueLevelName }
	::={systemUdpRxQueueLevelTable 1}

SystemUdpRxQueueLevelEntry ::=
	SEQUENCE {
		systemUdpRxQueueLevelName	DisplayString,
		systemUdpRxQueueLevelVal	CounterBasedGauge64,
		systemUdpRxQueueLevelMax	CounterBasedGauge64
	}

systemUdpRxQueueLevelName OBJECT-TYPE
	SYNTAX      DisplayString
	MAX-ACCESS  not-accessible
	STATUS      current
	DESCRIPTION
	"Table entry display string for systemUdpRxQueue"
	::={systemUdpRxQueueLevelEntry 1}

systemUdpRxQueueLevelVal OBJECT-TYPE
	SYNTAX	 CounterBasedGauge64
	MAX-ACCESS  read-only
	STATUS      current
	DESCRIPTION
	"Table entry attribute for systemUdpRxQueue"
	::={systemUdpRxQueueLevelEntry 2}

systemUdpRxQueueLevelMax OBJECT-TYPE
	SYNTAX	 CounterBasedGauge64
	MAX-ACCESS  read-only
	STATUS      current
	DESCRIPTION
	"Table entry attribute for systemUdpRxQueue"
	::={systemUdpRxQueueLevelEntry 4}


systemUdpDrops	OBJECT IDENTIFIER ::={system 17}

systemUdpDropsVal	OBJECT-TYPE
	SYNTAX	 Counter64
	MAX-ACCESS read-only
	STATUS current
	DESCRIPTION "UDP Drops"

	::={systemUdpDrops 1}

systemUdpDropsMom	OBJECT-TYPE
	SYNTAX	 CounterBasedGauge64
	MAX-ACCESS read-only
	STATUS current
	DESCRIPTION "UDP Drops"

	::={systemUdpDrops 2}

systemUdpDropsMax	OBJECT-TYPE
	SYNTAX	 CounterBasedGauge64
	MAX-ACCESS read-only
	STATUS current
	DESCRIPTION "UDP Drops"

	::={systemUdpDrops 3}

systemUdpDropsLevelTable OBJECT-TYPE
	SYNTAX      SEQUENCE OF SystemUdpDropsLevelEntry
	MAX-ACCESS  not-accessible
	STATUS      current
	DESCRIPTION
	"Table for systemUdpDrops"
	::={systemUdpDrops 4}

systemUdpDropsLevelEntry OBJECT-TYPE
	SYNTAX      SystemUdpDropsLevelEntry
	MAX-ACCESS  not-accessible
	STATUS      current
	DESCRIPTION
	"Table entry for systemUdpDrops"
	INDEX { systemUdpDropsLevelName }
	::={systemUdpDropsLevelTable 1}

SystemUdpDropsLevelEntry ::=
	SEQUENCE {
		systemUdpDropsLevelName	DisplayString,
		systemUdpDropsLevelVal	Counter64,
		systemUdpDropsLevelMom	CounterBasedGauge64,
		systemUdpDropsLevelMax	CounterBasedGauge64
	}

systemUdpDropsLevelName OBJECT-TYPE
	SYNTAX      DisplayString
	MAX-ACCESS  not-accessible
	STATUS      current
	DESCRIPTION
	"Table entry display string for systemUdpDrops"
	::={systemUdpDropsLevelEntry 1}

systemUdpDropsLevelVal OBJECT-TYPE
	SYNTAX	 Counter64
	MAX-ACCESS  read-only
	STATUS      current
	DESCRIPTION
	"Table entry attribute for systemUdpDrops"
	::={systemUdpDropsLevelEntry 2}

systemUdpDropsLevelMom OBJECT-TYPE
	SYNTAX	 CounterBasedGauge64
	MAX-ACCESS  read-only
	STATUS      current
	DESCRIPTION
	"Table entry attribute for systemUdpDrops"
	::={systemUdpDropsLevelEntry 3}

systemUdpDropsLevelMax OBJECT-TYPE
	SYNTAX	 CounterBasedGauge64
	MAX-ACCESS  read-only
	STATUS      current
	DESCRIPTION
	"Table entry attribute for systemUdpDrops"
	::={systemUdpDropsLevelEntry 4}


liveview	OBJECT IDENTIFIER ::={sysdiag 134}

liveviewUptime	OBJECT IDENTIFIER ::={liveview 1}

liveviewUptimeVal	OBJECT-TYPE
	SYNTAX	 TimeTicks
	MAX-ACCESS read-only
	STATUS current
	DESCRIPTION "Uptime"

	::={liveviewUptime 1}

liveviewUptimeLevelTable OBJECT-TYPE
	SYNTAX      SEQUENCE OF LiveviewUptimeLevelEntry
	MAX-ACCESS  not-accessible
	STATUS      current
	DESCRIPTION
	"Table for liveviewUptime"
	::={liveviewUptime 2}

liveviewUptimeLevelEntry OBJECT-TYPE
	SYNTAX      LiveviewUptimeLevelEntry
	MAX-ACCESS  not-accessible
	STATUS      current
	DESCRIPTION
	"Table entry for liveviewUptime"
	INDEX { liveviewUptimeLevelName }
	::={liveviewUptimeLevelTable 1}

LiveviewUptimeLevelEntry ::=
	SEQUENCE {
		liveviewUptimeLevelName	DisplayString,
		liveviewUptimeLevelVal	TimeTicks
	}

liveviewUptimeLevelName OBJECT-TYPE
	SYNTAX      DisplayString
	MAX-ACCESS  not-accessible
	STATUS      current
	DESCRIPTION
	"Table entry display string for liveviewUptime"
	::={liveviewUptimeLevelEntry 1}

liveviewUptimeLevelVal OBJECT-TYPE
	SYNTAX	 TimeTicks
	MAX-ACCESS  read-only
	STATUS      current
	DESCRIPTION
	"Table entry attribute for liveviewUptime"
	::={liveviewUptimeLevelEntry 2}


liveviewClients	OBJECT IDENTIFIER ::={liveview 2}

liveviewClientsVal	OBJECT-TYPE
	SYNTAX	 CounterBasedGauge64
	MAX-ACCESS read-only
	STATUS current
	DESCRIPTION "Connected clients"

	::={liveviewClients 1}

liveviewClientsMax	OBJECT-TYPE
	SYNTAX	 CounterBasedGauge64
	MAX-ACCESS read-only
	STATUS current
	DESCRIPTION "Connected clients"

	::={liveviewClients 3}

liveviewClientsLevelTable OBJECT-TYPE
	SYNTAX      SEQUENCE OF LiveviewClientsLevelEntry
	MAX-ACCESS  not-accessible
	STATUS      current
	DESCRIPTION
	"Table for liveviewClients"
	::={liveviewClients 4}

liveviewClientsLevelEntry OBJECT-TYPE
	SYNTAX      LiveviewClientsLevelEntry
	MAX-ACCESS  not-accessible
	STATUS      current
	DESCRIPTION
	"Table entry for liveviewClients"
	INDEX { liveviewClientsLevelName }
	::={liveviewClientsLevelTable 1}

LiveviewClientsLevelEntry ::=
	SEQUENCE {
		liveviewClientsLevelName	DisplayString,
		liveviewClientsLevelVal	CounterBasedGauge64,
		liveviewClientsLevelMax	CounterBasedGauge64
	}

liveviewClientsLevelName OBJECT-TYPE
	SYNTAX      DisplayString
	MAX-ACCESS  not-accessible
	STATUS      current
	DESCRIPTION
	"Table entry display string for liveviewClients"
	::={liveviewClientsLevelEntry 1}

liveviewClientsLevelVal OBJECT-TYPE
	SYNTAX	 CounterBasedGauge64
	MAX-ACCESS  read-only
	STATUS      current
	DESCRIPTION
	"Table entry attribute for liveviewClients"
	::={liveviewClientsLevelEntry 2}

liveviewClientsLevelMax OBJECT-TYPE
	SYNTAX	 CounterBasedGauge64
	MAX-ACCESS  read-only
	STATUS      current
	DESCRIPTION
	"Table entry attribute for liveviewClients"
	::={liveviewClientsLevelEntry 4}


liveviewPLSDClients	OBJECT IDENTIFIER ::={liveview 3}

liveviewPLSDClientsVal	OBJECT-TYPE
	SYNTAX	 CounterBasedGauge64
	MAX-ACCESS read-only
	STATUS current
	DESCRIPTION "Connected PLSD clients"

	::={liveviewPLSDClients 1}

liveviewPLSDClientsMax	OBJECT-TYPE
	SYNTAX	 CounterBasedGauge64
	MAX-ACCESS read-only
	STATUS current
	DESCRIPTION "Connected PLSD clients"

	::={liveviewPLSDClients 3}

liveviewPLSDClientsLevelTable OBJECT-TYPE
	SYNTAX      SEQUENCE OF LiveviewPLSDClientsLevelEntry
	MAX-ACCESS  not-accessible
	STATUS      current
	DESCRIPTION
	"Table for liveviewPLSDClients"
	::={liveviewPLSDClients 4}

liveviewPLSDClientsLevelEntry OBJECT-TYPE
	SYNTAX      LiveviewPLSDClientsLevelEntry
	MAX-ACCESS  not-accessible
	STATUS      current
	DESCRIPTION
	"Table entry for liveviewPLSDClients"
	INDEX { liveviewPLSDClientsLevelName }
	::={liveviewPLSDClientsLevelTable 1}

LiveviewPLSDClientsLevelEntry ::=
	SEQUENCE {
		liveviewPLSDClientsLevelName	DisplayString,
		liveviewPLSDClientsLevelVal	CounterBasedGauge64,
		liveviewPLSDClientsLevelMax	CounterBasedGauge64
	}

liveviewPLSDClientsLevelName OBJECT-TYPE
	SYNTAX      DisplayString
	MAX-ACCESS  not-accessible
	STATUS      current
	DESCRIPTION
	"Table entry display string for liveviewPLSDClients"
	::={liveviewPLSDClientsLevelEntry 1}

liveviewPLSDClientsLevelVal OBJECT-TYPE
	SYNTAX	 CounterBasedGauge64
	MAX-ACCESS  read-only
	STATUS      current
	DESCRIPTION
	"Table entry attribute for liveviewPLSDClients"
	::={liveviewPLSDClientsLevelEntry 2}

liveviewPLSDClientsLevelMax OBJECT-TYPE
	SYNTAX	 CounterBasedGauge64
	MAX-ACCESS  read-only
	STATUS      current
	DESCRIPTION
	"Table entry attribute for liveviewPLSDClients"
	::={liveviewPLSDClientsLevelEntry 4}


liveviewHosts	OBJECT IDENTIFIER ::={liveview 4}

liveviewHostsVal	OBJECT-TYPE
	SYNTAX	 CounterBasedGauge64
	MAX-ACCESS read-only
	STATUS current
	DESCRIPTION "Active hosts"

	::={liveviewHosts 1}

liveviewHostsMax	OBJECT-TYPE
	SYNTAX	 CounterBasedGauge64
	MAX-ACCESS read-only
	STATUS current
	DESCRIPTION "Active hosts"

	::={liveviewHosts 3}

liveviewHostsLevelTable OBJECT-TYPE
	SYNTAX      SEQUENCE OF LiveviewHostsLevelEntry
	MAX-ACCESS  not-accessible
	STATUS      current
	DESCRIPTION
	"Table for liveviewHosts"
	::={liveviewHosts 4}

liveviewHostsLevelEntry OBJECT-TYPE
	SYNTAX      LiveviewHostsLevelEntry
	MAX-ACCESS  not-accessible
	STATUS      current
	DESCRIPTION
	"Table entry for liveviewHosts"
	INDEX { liveviewHostsLevelName }
	::={liveviewHostsLevelTable 1}

LiveviewHostsLevelEntry ::=
	SEQUENCE {
		liveviewHostsLevelName	DisplayString,
		liveviewHostsLevelVal	CounterBasedGauge64,
		liveviewHostsLevelMax	CounterBasedGauge64
	}

liveviewHostsLevelName OBJECT-TYPE
	SYNTAX      DisplayString
	MAX-ACCESS  not-accessible
	STATUS      current
	DESCRIPTION
	"Table entry display string for liveviewHosts"
	::={liveviewHostsLevelEntry 1}

liveviewHostsLevelVal OBJECT-TYPE
	SYNTAX	 CounterBasedGauge64
	MAX-ACCESS  read-only
	STATUS      current
	DESCRIPTION
	"Table entry attribute for liveviewHosts"
	::={liveviewHostsLevelEntry 2}

liveviewHostsLevelMax OBJECT-TYPE
	SYNTAX	 CounterBasedGauge64
	MAX-ACCESS  read-only
	STATUS      current
	DESCRIPTION
	"Table entry attribute for liveviewHosts"
	::={liveviewHostsLevelEntry 4}


liveviewVNOs	OBJECT IDENTIFIER ::={liveview 5}

liveviewVNOsVal	OBJECT-TYPE
	SYNTAX	 CounterBasedGauge64
	MAX-ACCESS read-only
	STATUS current
	DESCRIPTION "Visible NetObjects"

	::={liveviewVNOs 1}

liveviewVNOsMax	OBJECT-TYPE
	SYNTAX	 CounterBasedGauge64
	MAX-ACCESS read-only
	STATUS current
	DESCRIPTION "Visible NetObjects"

	::={liveviewVNOs 3}

liveviewVNOsLevelTable OBJECT-TYPE
	SYNTAX      SEQUENCE OF LiveviewVNOsLevelEntry
	MAX-ACCESS  not-accessible
	STATUS      current
	DESCRIPTION
	"Table for liveviewVNOs"
	::={liveviewVNOs 4}

liveviewVNOsLevelEntry OBJECT-TYPE
	SYNTAX      LiveviewVNOsLevelEntry
	MAX-ACCESS  not-accessible
	STATUS      current
	DESCRIPTION
	"Table entry for liveviewVNOs"
	INDEX { liveviewVNOsLevelName }
	::={liveviewVNOsLevelTable 1}

LiveviewVNOsLevelEntry ::=
	SEQUENCE {
		liveviewVNOsLevelName	DisplayString,
		liveviewVNOsLevelVal	CounterBasedGauge64,
		liveviewVNOsLevelMax	CounterBasedGauge64
	}

liveviewVNOsLevelName OBJECT-TYPE
	SYNTAX      DisplayString
	MAX-ACCESS  not-accessible
	STATUS      current
	DESCRIPTION
	"Table entry display string for liveviewVNOs"
	::={liveviewVNOsLevelEntry 1}

liveviewVNOsLevelVal OBJECT-TYPE
	SYNTAX	 CounterBasedGauge64
	MAX-ACCESS  read-only
	STATUS      current
	DESCRIPTION
	"Table entry attribute for liveviewVNOs"
	::={liveviewVNOsLevelEntry 2}

liveviewVNOsLevelMax OBJECT-TYPE
	SYNTAX	 CounterBasedGauge64
	MAX-ACCESS  read-only
	STATUS      current
	DESCRIPTION
	"Table entry attribute for liveviewVNOs"
	::={liveviewVNOsLevelEntry 4}


liveviewDrdlRevision	OBJECT IDENTIFIER ::={liveview 7}

liveviewDrdlRevisionVal	OBJECT-TYPE
	SYNTAX	 CounterBasedGauge64
	MAX-ACCESS read-only
	STATUS current
	DESCRIPTION "DRDL revision"

	::={liveviewDrdlRevision 1}

liveviewDrdlRevisionLevelTable OBJECT-TYPE
	SYNTAX      SEQUENCE OF LiveviewDrdlRevisionLevelEntry
	MAX-ACCESS  not-accessible
	STATUS      current
	DESCRIPTION
	"Table for liveviewDrdlRevision"
	::={liveviewDrdlRevision 4}

liveviewDrdlRevisionLevelEntry OBJECT-TYPE
	SYNTAX      LiveviewDrdlRevisionLevelEntry
	MAX-ACCESS  not-accessible
	STATUS      current
	DESCRIPTION
	"Table entry for liveviewDrdlRevision"
	INDEX { liveviewDrdlRevisionLevelName }
	::={liveviewDrdlRevisionLevelTable 1}

LiveviewDrdlRevisionLevelEntry ::=
	SEQUENCE {
		liveviewDrdlRevisionLevelName	DisplayString,
		liveviewDrdlRevisionLevelVal	CounterBasedGauge64
	}

liveviewDrdlRevisionLevelName OBJECT-TYPE
	SYNTAX      DisplayString
	MAX-ACCESS  not-accessible
	STATUS      current
	DESCRIPTION
	"Table entry display string for liveviewDrdlRevision"
	::={liveviewDrdlRevisionLevelEntry 1}

liveviewDrdlRevisionLevelVal OBJECT-TYPE
	SYNTAX	 CounterBasedGauge64
	MAX-ACCESS  read-only
	STATUS      current
	DESCRIPTION
	"Table entry attribute for liveviewDrdlRevision"
	::={liveviewDrdlRevisionLevelEntry 2}


liveviewFailedNetobjects	OBJECT IDENTIFIER ::={liveview 8}

liveviewFailedNetobjectsVal	OBJECT-TYPE
	SYNTAX	 Counter64
	MAX-ACCESS read-only
	STATUS current
	DESCRIPTION "Visible netobject pool exhausted"

	::={liveviewFailedNetobjects 1}

liveviewFailedNetobjectsMom	OBJECT-TYPE
	SYNTAX	 CounterBasedGauge64
	MAX-ACCESS read-only
	STATUS current
	DESCRIPTION "Visible netobject pool exhausted"

	::={liveviewFailedNetobjects 2}

liveviewFailedNetobjectsMax	OBJECT-TYPE
	SYNTAX	 CounterBasedGauge64
	MAX-ACCESS read-only
	STATUS current
	DESCRIPTION "Visible netobject pool exhausted"

	::={liveviewFailedNetobjects 3}

liveviewFailedNetobjectsLevelTable OBJECT-TYPE
	SYNTAX      SEQUENCE OF LiveviewFailedNetobjectsLevelEntry
	MAX-ACCESS  not-accessible
	STATUS      current
	DESCRIPTION
	"Table for liveviewFailedNetobjects"
	::={liveviewFailedNetobjects 4}

liveviewFailedNetobjectsLevelEntry OBJECT-TYPE
	SYNTAX      LiveviewFailedNetobjectsLevelEntry
	MAX-ACCESS  not-accessible
	STATUS      current
	DESCRIPTION
	"Table entry for liveviewFailedNetobjects"
	INDEX { liveviewFailedNetobjectsLevelName }
	::={liveviewFailedNetobjectsLevelTable 1}

LiveviewFailedNetobjectsLevelEntry ::=
	SEQUENCE {
		liveviewFailedNetobjectsLevelName	DisplayString,
		liveviewFailedNetobjectsLevelVal	Counter64,
		liveviewFailedNetobjectsLevelMom	CounterBasedGauge64,
		liveviewFailedNetobjectsLevelMax	CounterBasedGauge64
	}

liveviewFailedNetobjectsLevelName OBJECT-TYPE
	SYNTAX      DisplayString
	MAX-ACCESS  not-accessible
	STATUS      current
	DESCRIPTION
	"Table entry display string for liveviewFailedNetobjects"
	::={liveviewFailedNetobjectsLevelEntry 1}

liveviewFailedNetobjectsLevelVal OBJECT-TYPE
	SYNTAX	 Counter64
	MAX-ACCESS  read-only
	STATUS      current
	DESCRIPTION
	"Table entry attribute for liveviewFailedNetobjects"
	::={liveviewFailedNetobjectsLevelEntry 2}

liveviewFailedNetobjectsLevelMom OBJECT-TYPE
	SYNTAX	 CounterBasedGauge64
	MAX-ACCESS  read-only
	STATUS      current
	DESCRIPTION
	"Table entry attribute for liveviewFailedNetobjects"
	::={liveviewFailedNetobjectsLevelEntry 3}

liveviewFailedNetobjectsLevelMax OBJECT-TYPE
	SYNTAX	 CounterBasedGauge64
	MAX-ACCESS  read-only
	STATUS      current
	DESCRIPTION
	"Table entry attribute for liveviewFailedNetobjects"
	::={liveviewFailedNetobjectsLevelEntry 4}


liveviewStringCacheUsage	OBJECT IDENTIFIER ::={liveview 10}

liveviewStringCacheUsageVal	OBJECT-TYPE
	SYNTAX	 CounterBasedGauge64
	MAX-ACCESS read-only
	STATUS current
	DESCRIPTION "String cache usage"

	::={liveviewStringCacheUsage 1}

liveviewStringCacheUsageMax	OBJECT-TYPE
	SYNTAX	 CounterBasedGauge64
	MAX-ACCESS read-only
	STATUS current
	DESCRIPTION "String cache usage"

	::={liveviewStringCacheUsage 3}

liveviewStringCacheUsageLevelTable OBJECT-TYPE
	SYNTAX      SEQUENCE OF LiveviewStringCacheUsageLevelEntry
	MAX-ACCESS  not-accessible
	STATUS      current
	DESCRIPTION
	"Table for liveviewStringCacheUsage"
	::={liveviewStringCacheUsage 4}

liveviewStringCacheUsageLevelEntry OBJECT-TYPE
	SYNTAX      LiveviewStringCacheUsageLevelEntry
	MAX-ACCESS  not-accessible
	STATUS      current
	DESCRIPTION
	"Table entry for liveviewStringCacheUsage"
	INDEX { liveviewStringCacheUsageLevelName }
	::={liveviewStringCacheUsageLevelTable 1}

LiveviewStringCacheUsageLevelEntry ::=
	SEQUENCE {
		liveviewStringCacheUsageLevelName	DisplayString,
		liveviewStringCacheUsageLevelVal	CounterBasedGauge64,
		liveviewStringCacheUsageLevelMax	CounterBasedGauge64
	}

liveviewStringCacheUsageLevelName OBJECT-TYPE
	SYNTAX      DisplayString
	MAX-ACCESS  not-accessible
	STATUS      current
	DESCRIPTION
	"Table entry display string for liveviewStringCacheUsage"
	::={liveviewStringCacheUsageLevelEntry 1}

liveviewStringCacheUsageLevelVal OBJECT-TYPE
	SYNTAX	 CounterBasedGauge64
	MAX-ACCESS  read-only
	STATUS      current
	DESCRIPTION
	"Table entry attribute for liveviewStringCacheUsage"
	::={liveviewStringCacheUsageLevelEntry 2}

liveviewStringCacheUsageLevelMax OBJECT-TYPE
	SYNTAX	 CounterBasedGauge64
	MAX-ACCESS  read-only
	STATUS      current
	DESCRIPTION
	"Table entry attribute for liveviewStringCacheUsage"
	::={liveviewStringCacheUsageLevelEntry 4}


liveviewHostCacheExhausted	OBJECT IDENTIFIER ::={liveview 14}

liveviewHostCacheExhaustedVal	OBJECT-TYPE
	SYNTAX	 Counter64
	MAX-ACCESS read-only
	STATUS current
	DESCRIPTION "Hosts not created due to exhausted cache"

	::={liveviewHostCacheExhausted 1}

liveviewHostCacheExhaustedMom	OBJECT-TYPE
	SYNTAX	 CounterBasedGauge64
	MAX-ACCESS read-only
	STATUS current
	DESCRIPTION "Hosts not created due to exhausted cache"

	::={liveviewHostCacheExhausted 2}

liveviewHostCacheExhaustedMax	OBJECT-TYPE
	SYNTAX	 CounterBasedGauge64
	MAX-ACCESS read-only
	STATUS current
	DESCRIPTION "Hosts not created due to exhausted cache"

	::={liveviewHostCacheExhausted 3}

liveviewHostCacheExhaustedLevelTable OBJECT-TYPE
	SYNTAX      SEQUENCE OF LiveviewHostCacheExhaustedLevelEntry
	MAX-ACCESS  not-accessible
	STATUS      current
	DESCRIPTION
	"Table for liveviewHostCacheExhausted"
	::={liveviewHostCacheExhausted 4}

liveviewHostCacheExhaustedLevelEntry OBJECT-TYPE
	SYNTAX      LiveviewHostCacheExhaustedLevelEntry
	MAX-ACCESS  not-accessible
	STATUS      current
	DESCRIPTION
	"Table entry for liveviewHostCacheExhausted"
	INDEX { liveviewHostCacheExhaustedLevelName }
	::={liveviewHostCacheExhaustedLevelTable 1}

LiveviewHostCacheExhaustedLevelEntry ::=
	SEQUENCE {
		liveviewHostCacheExhaustedLevelName	DisplayString,
		liveviewHostCacheExhaustedLevelVal	Counter64,
		liveviewHostCacheExhaustedLevelMom	CounterBasedGauge64,
		liveviewHostCacheExhaustedLevelMax	CounterBasedGauge64
	}

liveviewHostCacheExhaustedLevelName OBJECT-TYPE
	SYNTAX      DisplayString
	MAX-ACCESS  not-accessible
	STATUS      current
	DESCRIPTION
	"Table entry display string for liveviewHostCacheExhausted"
	::={liveviewHostCacheExhaustedLevelEntry 1}

liveviewHostCacheExhaustedLevelVal OBJECT-TYPE
	SYNTAX	 Counter64
	MAX-ACCESS  read-only
	STATUS      current
	DESCRIPTION
	"Table entry attribute for liveviewHostCacheExhausted"
	::={liveviewHostCacheExhaustedLevelEntry 2}

liveviewHostCacheExhaustedLevelMom OBJECT-TYPE
	SYNTAX	 CounterBasedGauge64
	MAX-ACCESS  read-only
	STATUS      current
	DESCRIPTION
	"Table entry attribute for liveviewHostCacheExhausted"
	::={liveviewHostCacheExhaustedLevelEntry 3}

liveviewHostCacheExhaustedLevelMax OBJECT-TYPE
	SYNTAX	 CounterBasedGauge64
	MAX-ACCESS  read-only
	STATUS      current
	DESCRIPTION
	"Table entry attribute for liveviewHostCacheExhausted"
	::={liveviewHostCacheExhaustedLevelEntry 4}


liveviewPropEntryUsage	OBJECT IDENTIFIER ::={liveview 15}

liveviewPropEntryUsageVal	OBJECT-TYPE
	SYNTAX	 CounterBasedGauge64
	MAX-ACCESS read-only
	STATUS current
	DESCRIPTION "Property entries used"

	::={liveviewPropEntryUsage 1}

liveviewPropEntryUsageMax	OBJECT-TYPE
	SYNTAX	 CounterBasedGauge64
	MAX-ACCESS read-only
	STATUS current
	DESCRIPTION "Property entries used"

	::={liveviewPropEntryUsage 3}

liveviewPropEntryUsageLevelTable OBJECT-TYPE
	SYNTAX      SEQUENCE OF LiveviewPropEntryUsageLevelEntry
	MAX-ACCESS  not-accessible
	STATUS      current
	DESCRIPTION
	"Table for liveviewPropEntryUsage"
	::={liveviewPropEntryUsage 4}

liveviewPropEntryUsageLevelEntry OBJECT-TYPE
	SYNTAX      LiveviewPropEntryUsageLevelEntry
	MAX-ACCESS  not-accessible
	STATUS      current
	DESCRIPTION
	"Table entry for liveviewPropEntryUsage"
	INDEX { liveviewPropEntryUsageLevelName }
	::={liveviewPropEntryUsageLevelTable 1}

LiveviewPropEntryUsageLevelEntry ::=
	SEQUENCE {
		liveviewPropEntryUsageLevelName	DisplayString,
		liveviewPropEntryUsageLevelVal	CounterBasedGauge64,
		liveviewPropEntryUsageLevelMax	CounterBasedGauge64
	}

liveviewPropEntryUsageLevelName OBJECT-TYPE
	SYNTAX      DisplayString
	MAX-ACCESS  not-accessible
	STATUS      current
	DESCRIPTION
	"Table entry display string for liveviewPropEntryUsage"
	::={liveviewPropEntryUsageLevelEntry 1}

liveviewPropEntryUsageLevelVal OBJECT-TYPE
	SYNTAX	 CounterBasedGauge64
	MAX-ACCESS  read-only
	STATUS      current
	DESCRIPTION
	"Table entry attribute for liveviewPropEntryUsage"
	::={liveviewPropEntryUsageLevelEntry 2}

liveviewPropEntryUsageLevelMax OBJECT-TYPE
	SYNTAX	 CounterBasedGauge64
	MAX-ACCESS  read-only
	STATUS      current
	DESCRIPTION
	"Table entry attribute for liveviewPropEntryUsage"
	::={liveviewPropEntryUsageLevelEntry 4}


liveviewPropArrayUsage	OBJECT IDENTIFIER ::={liveview 16}

liveviewPropArrayUsageVal	OBJECT-TYPE
	SYNTAX	 CounterBasedGauge64
	MAX-ACCESS read-only
	STATUS current
	DESCRIPTION "Property arrays used"

	::={liveviewPropArrayUsage 1}

liveviewPropArrayUsageMax	OBJECT-TYPE
	SYNTAX	 CounterBasedGauge64
	MAX-ACCESS read-only
	STATUS current
	DESCRIPTION "Property arrays used"

	::={liveviewPropArrayUsage 3}

liveviewPropArrayUsageLevelTable OBJECT-TYPE
	SYNTAX      SEQUENCE OF LiveviewPropArrayUsageLevelEntry
	MAX-ACCESS  not-accessible
	STATUS      current
	DESCRIPTION
	"Table for liveviewPropArrayUsage"
	::={liveviewPropArrayUsage 4}

liveviewPropArrayUsageLevelEntry OBJECT-TYPE
	SYNTAX      LiveviewPropArrayUsageLevelEntry
	MAX-ACCESS  not-accessible
	STATUS      current
	DESCRIPTION
	"Table entry for liveviewPropArrayUsage"
	INDEX { liveviewPropArrayUsageLevelName }
	::={liveviewPropArrayUsageLevelTable 1}

LiveviewPropArrayUsageLevelEntry ::=
	SEQUENCE {
		liveviewPropArrayUsageLevelName	DisplayString,
		liveviewPropArrayUsageLevelVal	CounterBasedGauge64,
		liveviewPropArrayUsageLevelMax	CounterBasedGauge64
	}

liveviewPropArrayUsageLevelName OBJECT-TYPE
	SYNTAX      DisplayString
	MAX-ACCESS  not-accessible
	STATUS      current
	DESCRIPTION
	"Table entry display string for liveviewPropArrayUsage"
	::={liveviewPropArrayUsageLevelEntry 1}

liveviewPropArrayUsageLevelVal OBJECT-TYPE
	SYNTAX	 CounterBasedGauge64
	MAX-ACCESS  read-only
	STATUS      current
	DESCRIPTION
	"Table entry attribute for liveviewPropArrayUsage"
	::={liveviewPropArrayUsageLevelEntry 2}

liveviewPropArrayUsageLevelMax OBJECT-TYPE
	SYNTAX	 CounterBasedGauge64
	MAX-ACCESS  read-only
	STATUS      current
	DESCRIPTION
	"Table entry attribute for liveviewPropArrayUsage"
	::={liveviewPropArrayUsageLevelEntry 4}


liveviewPropUsage	OBJECT IDENTIFIER ::={liveview 17}

liveviewPropUsageVal	OBJECT-TYPE
	SYNTAX	 CounterBasedGauge64
	MAX-ACCESS read-only
	STATUS current
	DESCRIPTION "Properties stored"

	::={liveviewPropUsage 1}

liveviewPropUsageMax	OBJECT-TYPE
	SYNTAX	 CounterBasedGauge64
	MAX-ACCESS read-only
	STATUS current
	DESCRIPTION "Properties stored"

	::={liveviewPropUsage 3}

liveviewPropUsageLevelTable OBJECT-TYPE
	SYNTAX      SEQUENCE OF LiveviewPropUsageLevelEntry
	MAX-ACCESS  not-accessible
	STATUS      current
	DESCRIPTION
	"Table for liveviewPropUsage"
	::={liveviewPropUsage 4}

liveviewPropUsageLevelEntry OBJECT-TYPE
	SYNTAX      LiveviewPropUsageLevelEntry
	MAX-ACCESS  not-accessible
	STATUS      current
	DESCRIPTION
	"Table entry for liveviewPropUsage"
	INDEX { liveviewPropUsageLevelName }
	::={liveviewPropUsageLevelTable 1}

LiveviewPropUsageLevelEntry ::=
	SEQUENCE {
		liveviewPropUsageLevelName	DisplayString,
		liveviewPropUsageLevelVal	CounterBasedGauge64,
		liveviewPropUsageLevelMax	CounterBasedGauge64
	}

liveviewPropUsageLevelName OBJECT-TYPE
	SYNTAX      DisplayString
	MAX-ACCESS  not-accessible
	STATUS      current
	DESCRIPTION
	"Table entry display string for liveviewPropUsage"
	::={liveviewPropUsageLevelEntry 1}

liveviewPropUsageLevelVal OBJECT-TYPE
	SYNTAX	 CounterBasedGauge64
	MAX-ACCESS  read-only
	STATUS      current
	DESCRIPTION
	"Table entry attribute for liveviewPropUsage"
	::={liveviewPropUsageLevelEntry 2}

liveviewPropUsageLevelMax OBJECT-TYPE
	SYNTAX	 CounterBasedGauge64
	MAX-ACCESS  read-only
	STATUS      current
	DESCRIPTION
	"Table entry attribute for liveviewPropUsage"
	::={liveviewPropUsageLevelEntry 4}


liveviewTooManyNetobjectsOnHost	OBJECT IDENTIFIER ::={liveview 18}

liveviewTooManyNetobjectsOnHostVal	OBJECT-TYPE
	SYNTAX	 Counter64
	MAX-ACCESS read-only
	STATUS current
	DESCRIPTION "Too many netobjects on a single host"

	::={liveviewTooManyNetobjectsOnHost 1}

liveviewTooManyNetobjectsOnHostMom	OBJECT-TYPE
	SYNTAX	 CounterBasedGauge64
	MAX-ACCESS read-only
	STATUS current
	DESCRIPTION "Too many netobjects on a single host"

	::={liveviewTooManyNetobjectsOnHost 2}

liveviewTooManyNetobjectsOnHostMax	OBJECT-TYPE
	SYNTAX	 CounterBasedGauge64
	MAX-ACCESS read-only
	STATUS current
	DESCRIPTION "Too many netobjects on a single host"

	::={liveviewTooManyNetobjectsOnHost 3}

liveviewTooManyNetobjectsOnHostLevelTable OBJECT-TYPE
	SYNTAX      SEQUENCE OF LiveviewTooManyNetobjectsOnHostLevelEntry
	MAX-ACCESS  not-accessible
	STATUS      current
	DESCRIPTION
	"Table for liveviewTooManyNetobjectsOnHost"
	::={liveviewTooManyNetobjectsOnHost 4}

liveviewTooManyNetobjectsOnHostLevelEntry OBJECT-TYPE
	SYNTAX      LiveviewTooManyNetobjectsOnHostLevelEntry
	MAX-ACCESS  not-accessible
	STATUS      current
	DESCRIPTION
	"Table entry for liveviewTooManyNetobjectsOnHost"
	INDEX { liveviewTooManyNetobjectsOnHostLevelName }
	::={liveviewTooManyNetobjectsOnHostLevelTable 1}

LiveviewTooManyNetobjectsOnHostLevelEntry ::=
	SEQUENCE {
		liveviewTooManyNetobjectsOnHostLevelName	DisplayString,
		liveviewTooManyNetobjectsOnHostLevelVal	Counter64,
		liveviewTooManyNetobjectsOnHostLevelMom	CounterBasedGauge64,
		liveviewTooManyNetobjectsOnHostLevelMax	CounterBasedGauge64
	}

liveviewTooManyNetobjectsOnHostLevelName OBJECT-TYPE
	SYNTAX      DisplayString
	MAX-ACCESS  not-accessible
	STATUS      current
	DESCRIPTION
	"Table entry display string for liveviewTooManyNetobjectsOnHost"
	::={liveviewTooManyNetobjectsOnHostLevelEntry 1}

liveviewTooManyNetobjectsOnHostLevelVal OBJECT-TYPE
	SYNTAX	 Counter64
	MAX-ACCESS  read-only
	STATUS      current
	DESCRIPTION
	"Table entry attribute for liveviewTooManyNetobjectsOnHost"
	::={liveviewTooManyNetobjectsOnHostLevelEntry 2}

liveviewTooManyNetobjectsOnHostLevelMom OBJECT-TYPE
	SYNTAX	 CounterBasedGauge64
	MAX-ACCESS  read-only
	STATUS      current
	DESCRIPTION
	"Table entry attribute for liveviewTooManyNetobjectsOnHost"
	::={liveviewTooManyNetobjectsOnHostLevelEntry 3}

liveviewTooManyNetobjectsOnHostLevelMax OBJECT-TYPE
	SYNTAX	 CounterBasedGauge64
	MAX-ACCESS  read-only
	STATUS      current
	DESCRIPTION
	"Table entry attribute for liveviewTooManyNetobjectsOnHost"
	::={liveviewTooManyNetobjectsOnHostLevelEntry 4}


liveviewHostnameAllocs	OBJECT IDENTIFIER ::={liveview 19}

liveviewHostnameAllocsVal	OBJECT-TYPE
	SYNTAX	 CounterBasedGauge64
	MAX-ACCESS read-only
	STATUS current
	DESCRIPTION "Hostname allocations"

	::={liveviewHostnameAllocs 1}

liveviewHostnameAllocsMax	OBJECT-TYPE
	SYNTAX	 CounterBasedGauge64
	MAX-ACCESS read-only
	STATUS current
	DESCRIPTION "Hostname allocations"

	::={liveviewHostnameAllocs 3}

liveviewHostnameAllocsLevelTable OBJECT-TYPE
	SYNTAX      SEQUENCE OF LiveviewHostnameAllocsLevelEntry
	MAX-ACCESS  not-accessible
	STATUS      current
	DESCRIPTION
	"Table for liveviewHostnameAllocs"
	::={liveviewHostnameAllocs 4}

liveviewHostnameAllocsLevelEntry OBJECT-TYPE
	SYNTAX      LiveviewHostnameAllocsLevelEntry
	MAX-ACCESS  not-accessible
	STATUS      current
	DESCRIPTION
	"Table entry for liveviewHostnameAllocs"
	INDEX { liveviewHostnameAllocsLevelName }
	::={liveviewHostnameAllocsLevelTable 1}

LiveviewHostnameAllocsLevelEntry ::=
	SEQUENCE {
		liveviewHostnameAllocsLevelName	DisplayString,
		liveviewHostnameAllocsLevelVal	CounterBasedGauge64,
		liveviewHostnameAllocsLevelMax	CounterBasedGauge64
	}

liveviewHostnameAllocsLevelName OBJECT-TYPE
	SYNTAX      DisplayString
	MAX-ACCESS  not-accessible
	STATUS      current
	DESCRIPTION
	"Table entry display string for liveviewHostnameAllocs"
	::={liveviewHostnameAllocsLevelEntry 1}

liveviewHostnameAllocsLevelVal OBJECT-TYPE
	SYNTAX	 CounterBasedGauge64
	MAX-ACCESS  read-only
	STATUS      current
	DESCRIPTION
	"Table entry attribute for liveviewHostnameAllocs"
	::={liveviewHostnameAllocsLevelEntry 2}

liveviewHostnameAllocsLevelMax OBJECT-TYPE
	SYNTAX	 CounterBasedGauge64
	MAX-ACCESS  read-only
	STATUS      current
	DESCRIPTION
	"Table entry attribute for liveviewHostnameAllocs"
	::={liveviewHostnameAllocsLevelEntry 4}


liveviewHostnameAllocFail	OBJECT IDENTIFIER ::={liveview 20}

liveviewHostnameAllocFailVal	OBJECT-TYPE
	SYNTAX	 Counter64
	MAX-ACCESS read-only
	STATUS current
	DESCRIPTION "Hostname allocation failures"

	::={liveviewHostnameAllocFail 1}

liveviewHostnameAllocFailMom	OBJECT-TYPE
	SYNTAX	 CounterBasedGauge64
	MAX-ACCESS read-only
	STATUS current
	DESCRIPTION "Hostname allocation failures"

	::={liveviewHostnameAllocFail 2}

liveviewHostnameAllocFailMax	OBJECT-TYPE
	SYNTAX	 CounterBasedGauge64
	MAX-ACCESS read-only
	STATUS current
	DESCRIPTION "Hostname allocation failures"

	::={liveviewHostnameAllocFail 3}

liveviewHostnameAllocFailLevelTable OBJECT-TYPE
	SYNTAX      SEQUENCE OF LiveviewHostnameAllocFailLevelEntry
	MAX-ACCESS  not-accessible
	STATUS      current
	DESCRIPTION
	"Table for liveviewHostnameAllocFail"
	::={liveviewHostnameAllocFail 4}

liveviewHostnameAllocFailLevelEntry OBJECT-TYPE
	SYNTAX      LiveviewHostnameAllocFailLevelEntry
	MAX-ACCESS  not-accessible
	STATUS      current
	DESCRIPTION
	"Table entry for liveviewHostnameAllocFail"
	INDEX { liveviewHostnameAllocFailLevelName }
	::={liveviewHostnameAllocFailLevelTable 1}

LiveviewHostnameAllocFailLevelEntry ::=
	SEQUENCE {
		liveviewHostnameAllocFailLevelName	DisplayString,
		liveviewHostnameAllocFailLevelVal	Counter64,
		liveviewHostnameAllocFailLevelMom	CounterBasedGauge64,
		liveviewHostnameAllocFailLevelMax	CounterBasedGauge64
	}

liveviewHostnameAllocFailLevelName OBJECT-TYPE
	SYNTAX      DisplayString
	MAX-ACCESS  not-accessible
	STATUS      current
	DESCRIPTION
	"Table entry display string for liveviewHostnameAllocFail"
	::={liveviewHostnameAllocFailLevelEntry 1}

liveviewHostnameAllocFailLevelVal OBJECT-TYPE
	SYNTAX	 Counter64
	MAX-ACCESS  read-only
	STATUS      current
	DESCRIPTION
	"Table entry attribute for liveviewHostnameAllocFail"
	::={liveviewHostnameAllocFailLevelEntry 2}

liveviewHostnameAllocFailLevelMom OBJECT-TYPE
	SYNTAX	 CounterBasedGauge64
	MAX-ACCESS  read-only
	STATUS      current
	DESCRIPTION
	"Table entry attribute for liveviewHostnameAllocFail"
	::={liveviewHostnameAllocFailLevelEntry 3}

liveviewHostnameAllocFailLevelMax OBJECT-TYPE
	SYNTAX	 CounterBasedGauge64
	MAX-ACCESS  read-only
	STATUS      current
	DESCRIPTION
	"Table entry attribute for liveviewHostnameAllocFail"
	::={liveviewHostnameAllocFailLevelEntry 4}


liveviewReaperRecvBuf	OBJECT IDENTIFIER ::={liveview 21}

liveviewReaperRecvBufVal	OBJECT-TYPE
	SYNTAX	 CounterBasedGauge64
	MAX-ACCESS read-only
	STATUS current
	DESCRIPTION "Reaper receive buffer usage"

	::={liveviewReaperRecvBuf 1}

liveviewReaperRecvBufMax	OBJECT-TYPE
	SYNTAX	 CounterBasedGauge64
	MAX-ACCESS read-only
	STATUS current
	DESCRIPTION "Reaper receive buffer usage"

	::={liveviewReaperRecvBuf 3}

liveviewReaperRecvBufLevelTable OBJECT-TYPE
	SYNTAX      SEQUENCE OF LiveviewReaperRecvBufLevelEntry
	MAX-ACCESS  not-accessible
	STATUS      current
	DESCRIPTION
	"Table for liveviewReaperRecvBuf"
	::={liveviewReaperRecvBuf 4}

liveviewReaperRecvBufLevelEntry OBJECT-TYPE
	SYNTAX      LiveviewReaperRecvBufLevelEntry
	MAX-ACCESS  not-accessible
	STATUS      current
	DESCRIPTION
	"Table entry for liveviewReaperRecvBuf"
	INDEX { liveviewReaperRecvBufLevelName }
	::={liveviewReaperRecvBufLevelTable 1}

LiveviewReaperRecvBufLevelEntry ::=
	SEQUENCE {
		liveviewReaperRecvBufLevelName	DisplayString,
		liveviewReaperRecvBufLevelVal	CounterBasedGauge64,
		liveviewReaperRecvBufLevelMax	CounterBasedGauge64
	}

liveviewReaperRecvBufLevelName OBJECT-TYPE
	SYNTAX      DisplayString
	MAX-ACCESS  not-accessible
	STATUS      current
	DESCRIPTION
	"Table entry display string for liveviewReaperRecvBuf"
	::={liveviewReaperRecvBufLevelEntry 1}

liveviewReaperRecvBufLevelVal OBJECT-TYPE
	SYNTAX	 CounterBasedGauge64
	MAX-ACCESS  read-only
	STATUS      current
	DESCRIPTION
	"Table entry attribute for liveviewReaperRecvBuf"
	::={liveviewReaperRecvBufLevelEntry 2}

liveviewReaperRecvBufLevelMax OBJECT-TYPE
	SYNTAX	 CounterBasedGauge64
	MAX-ACCESS  read-only
	STATUS      current
	DESCRIPTION
	"Table entry attribute for liveviewReaperRecvBuf"
	::={liveviewReaperRecvBufLevelEntry 4}


liveviewReaperSendBuf	OBJECT IDENTIFIER ::={liveview 22}

liveviewReaperSendBufVal	OBJECT-TYPE
	SYNTAX	 CounterBasedGauge64
	MAX-ACCESS read-only
	STATUS current
	DESCRIPTION "Reaper send buffer usage"

	::={liveviewReaperSendBuf 1}

liveviewReaperSendBufMax	OBJECT-TYPE
	SYNTAX	 CounterBasedGauge64
	MAX-ACCESS read-only
	STATUS current
	DESCRIPTION "Reaper send buffer usage"

	::={liveviewReaperSendBuf 3}

liveviewReaperSendBufLevelTable OBJECT-TYPE
	SYNTAX      SEQUENCE OF LiveviewReaperSendBufLevelEntry
	MAX-ACCESS  not-accessible
	STATUS      current
	DESCRIPTION
	"Table for liveviewReaperSendBuf"
	::={liveviewReaperSendBuf 4}

liveviewReaperSendBufLevelEntry OBJECT-TYPE
	SYNTAX      LiveviewReaperSendBufLevelEntry
	MAX-ACCESS  not-accessible
	STATUS      current
	DESCRIPTION
	"Table entry for liveviewReaperSendBuf"
	INDEX { liveviewReaperSendBufLevelName }
	::={liveviewReaperSendBufLevelTable 1}

LiveviewReaperSendBufLevelEntry ::=
	SEQUENCE {
		liveviewReaperSendBufLevelName	DisplayString,
		liveviewReaperSendBufLevelVal	CounterBasedGauge64,
		liveviewReaperSendBufLevelMax	CounterBasedGauge64
	}

liveviewReaperSendBufLevelName OBJECT-TYPE
	SYNTAX      DisplayString
	MAX-ACCESS  not-accessible
	STATUS      current
	DESCRIPTION
	"Table entry display string for liveviewReaperSendBuf"
	::={liveviewReaperSendBufLevelEntry 1}

liveviewReaperSendBufLevelVal OBJECT-TYPE
	SYNTAX	 CounterBasedGauge64
	MAX-ACCESS  read-only
	STATUS      current
	DESCRIPTION
	"Table entry attribute for liveviewReaperSendBuf"
	::={liveviewReaperSendBufLevelEntry 2}

liveviewReaperSendBufLevelMax OBJECT-TYPE
	SYNTAX	 CounterBasedGauge64
	MAX-ACCESS  read-only
	STATUS      current
	DESCRIPTION
	"Table entry attribute for liveviewReaperSendBuf"
	::={liveviewReaperSendBufLevelEntry 4}


liveviewPLSDBuf	OBJECT IDENTIFIER ::={liveview 23}

liveviewPLSDBufVal	OBJECT-TYPE
	SYNTAX	 CounterBasedGauge64
	MAX-ACCESS read-only
	STATUS current
	DESCRIPTION "PLSD buffer usage"

	::={liveviewPLSDBuf 1}

liveviewPLSDBufMax	OBJECT-TYPE
	SYNTAX	 CounterBasedGauge64
	MAX-ACCESS read-only
	STATUS current
	DESCRIPTION "PLSD buffer usage"

	::={liveviewPLSDBuf 3}

liveviewPLSDBufLevelTable OBJECT-TYPE
	SYNTAX      SEQUENCE OF LiveviewPLSDBufLevelEntry
	MAX-ACCESS  not-accessible
	STATUS      current
	DESCRIPTION
	"Table for liveviewPLSDBuf"
	::={liveviewPLSDBuf 4}

liveviewPLSDBufLevelEntry OBJECT-TYPE
	SYNTAX      LiveviewPLSDBufLevelEntry
	MAX-ACCESS  not-accessible
	STATUS      current
	DESCRIPTION
	"Table entry for liveviewPLSDBuf"
	INDEX { liveviewPLSDBufLevelName }
	::={liveviewPLSDBufLevelTable 1}

LiveviewPLSDBufLevelEntry ::=
	SEQUENCE {
		liveviewPLSDBufLevelName	DisplayString,
		liveviewPLSDBufLevelVal	CounterBasedGauge64,
		liveviewPLSDBufLevelMax	CounterBasedGauge64
	}

liveviewPLSDBufLevelName OBJECT-TYPE
	SYNTAX      DisplayString
	MAX-ACCESS  not-accessible
	STATUS      current
	DESCRIPTION
	"Table entry display string for liveviewPLSDBuf"
	::={liveviewPLSDBufLevelEntry 1}

liveviewPLSDBufLevelVal OBJECT-TYPE
	SYNTAX	 CounterBasedGauge64
	MAX-ACCESS  read-only
	STATUS      current
	DESCRIPTION
	"Table entry attribute for liveviewPLSDBuf"
	::={liveviewPLSDBufLevelEntry 2}

liveviewPLSDBufLevelMax OBJECT-TYPE
	SYNTAX	 CounterBasedGauge64
	MAX-ACCESS  read-only
	STATUS      current
	DESCRIPTION
	"Table entry attribute for liveviewPLSDBuf"
	::={liveviewPLSDBufLevelEntry 4}


liveviewMatchingViewRecalc	OBJECT IDENTIFIER ::={liveview 24}

liveviewMatchingViewRecalcVal	OBJECT-TYPE
	SYNTAX	 Counter64
	MAX-ACCESS read-only
	STATUS current
	DESCRIPTION "Matching views recalculations"

	::={liveviewMatchingViewRecalc 1}

liveviewMatchingViewRecalcMom	OBJECT-TYPE
	SYNTAX	 CounterBasedGauge64
	MAX-ACCESS read-only
	STATUS current
	DESCRIPTION "Matching views recalculations"

	::={liveviewMatchingViewRecalc 2}

liveviewMatchingViewRecalcMax	OBJECT-TYPE
	SYNTAX	 CounterBasedGauge64
	MAX-ACCESS read-only
	STATUS current
	DESCRIPTION "Matching views recalculations"

	::={liveviewMatchingViewRecalc 3}

liveviewMatchingViewRecalcLevelTable OBJECT-TYPE
	SYNTAX      SEQUENCE OF LiveviewMatchingViewRecalcLevelEntry
	MAX-ACCESS  not-accessible
	STATUS      current
	DESCRIPTION
	"Table for liveviewMatchingViewRecalc"
	::={liveviewMatchingViewRecalc 4}

liveviewMatchingViewRecalcLevelEntry OBJECT-TYPE
	SYNTAX      LiveviewMatchingViewRecalcLevelEntry
	MAX-ACCESS  not-accessible
	STATUS      current
	DESCRIPTION
	"Table entry for liveviewMatchingViewRecalc"
	INDEX { liveviewMatchingViewRecalcLevelName }
	::={liveviewMatchingViewRecalcLevelTable 1}

LiveviewMatchingViewRecalcLevelEntry ::=
	SEQUENCE {
		liveviewMatchingViewRecalcLevelName	DisplayString,
		liveviewMatchingViewRecalcLevelVal	Counter64,
		liveviewMatchingViewRecalcLevelMom	CounterBasedGauge64,
		liveviewMatchingViewRecalcLevelMax	CounterBasedGauge64
	}

liveviewMatchingViewRecalcLevelName OBJECT-TYPE
	SYNTAX      DisplayString
	MAX-ACCESS  not-accessible
	STATUS      current
	DESCRIPTION
	"Table entry display string for liveviewMatchingViewRecalc"
	::={liveviewMatchingViewRecalcLevelEntry 1}

liveviewMatchingViewRecalcLevelVal OBJECT-TYPE
	SYNTAX	 Counter64
	MAX-ACCESS  read-only
	STATUS      current
	DESCRIPTION
	"Table entry attribute for liveviewMatchingViewRecalc"
	::={liveviewMatchingViewRecalcLevelEntry 2}

liveviewMatchingViewRecalcLevelMom OBJECT-TYPE
	SYNTAX	 CounterBasedGauge64
	MAX-ACCESS  read-only
	STATUS      current
	DESCRIPTION
	"Table entry attribute for liveviewMatchingViewRecalc"
	::={liveviewMatchingViewRecalcLevelEntry 3}

liveviewMatchingViewRecalcLevelMax OBJECT-TYPE
	SYNTAX	 CounterBasedGauge64
	MAX-ACCESS  read-only
	STATUS      current
	DESCRIPTION
	"Table entry attribute for liveviewMatchingViewRecalc"
	::={liveviewMatchingViewRecalcLevelEntry 4}


liveviewViewValueRecalc	OBJECT IDENTIFIER ::={liveview 25}

liveviewViewValueRecalcVal	OBJECT-TYPE
	SYNTAX	 Counter64
	MAX-ACCESS read-only
	STATUS current
	DESCRIPTION "View value recalculations"

	::={liveviewViewValueRecalc 1}

liveviewViewValueRecalcMom	OBJECT-TYPE
	SYNTAX	 CounterBasedGauge64
	MAX-ACCESS read-only
	STATUS current
	DESCRIPTION "View value recalculations"

	::={liveviewViewValueRecalc 2}

liveviewViewValueRecalcMax	OBJECT-TYPE
	SYNTAX	 CounterBasedGauge64
	MAX-ACCESS read-only
	STATUS current
	DESCRIPTION "View value recalculations"

	::={liveviewViewValueRecalc 3}

liveviewViewValueRecalcLevelTable OBJECT-TYPE
	SYNTAX      SEQUENCE OF LiveviewViewValueRecalcLevelEntry
	MAX-ACCESS  not-accessible
	STATUS      current
	DESCRIPTION
	"Table for liveviewViewValueRecalc"
	::={liveviewViewValueRecalc 4}

liveviewViewValueRecalcLevelEntry OBJECT-TYPE
	SYNTAX      LiveviewViewValueRecalcLevelEntry
	MAX-ACCESS  not-accessible
	STATUS      current
	DESCRIPTION
	"Table entry for liveviewViewValueRecalc"
	INDEX { liveviewViewValueRecalcLevelName }
	::={liveviewViewValueRecalcLevelTable 1}

LiveviewViewValueRecalcLevelEntry ::=
	SEQUENCE {
		liveviewViewValueRecalcLevelName	DisplayString,
		liveviewViewValueRecalcLevelVal	Counter64,
		liveviewViewValueRecalcLevelMom	CounterBasedGauge64,
		liveviewViewValueRecalcLevelMax	CounterBasedGauge64
	}

liveviewViewValueRecalcLevelName OBJECT-TYPE
	SYNTAX      DisplayString
	MAX-ACCESS  not-accessible
	STATUS      current
	DESCRIPTION
	"Table entry display string for liveviewViewValueRecalc"
	::={liveviewViewValueRecalcLevelEntry 1}

liveviewViewValueRecalcLevelVal OBJECT-TYPE
	SYNTAX	 Counter64
	MAX-ACCESS  read-only
	STATUS      current
	DESCRIPTION
	"Table entry attribute for liveviewViewValueRecalc"
	::={liveviewViewValueRecalcLevelEntry 2}

liveviewViewValueRecalcLevelMom OBJECT-TYPE
	SYNTAX	 CounterBasedGauge64
	MAX-ACCESS  read-only
	STATUS      current
	DESCRIPTION
	"Table entry attribute for liveviewViewValueRecalc"
	::={liveviewViewValueRecalcLevelEntry 3}

liveviewViewValueRecalcLevelMax OBJECT-TYPE
	SYNTAX	 CounterBasedGauge64
	MAX-ACCESS  read-only
	STATUS      current
	DESCRIPTION
	"Table entry attribute for liveviewViewValueRecalc"
	::={liveviewViewValueRecalcLevelEntry 4}


liveviewDynIpLookups	OBJECT IDENTIFIER ::={liveview 26}

liveviewDynIpLookupsVal	OBJECT-TYPE
	SYNTAX	 Counter64
	MAX-ACCESS read-only
	STATUS current
	DESCRIPTION "Dynamic IP lookups"

	::={liveviewDynIpLookups 1}

liveviewDynIpLookupsMom	OBJECT-TYPE
	SYNTAX	 CounterBasedGauge64
	MAX-ACCESS read-only
	STATUS current
	DESCRIPTION "Dynamic IP lookups"

	::={liveviewDynIpLookups 2}

liveviewDynIpLookupsMax	OBJECT-TYPE
	SYNTAX	 CounterBasedGauge64
	MAX-ACCESS read-only
	STATUS current
	DESCRIPTION "Dynamic IP lookups"

	::={liveviewDynIpLookups 3}

liveviewDynIpLookupsLevelTable OBJECT-TYPE
	SYNTAX      SEQUENCE OF LiveviewDynIpLookupsLevelEntry
	MAX-ACCESS  not-accessible
	STATUS      current
	DESCRIPTION
	"Table for liveviewDynIpLookups"
	::={liveviewDynIpLookups 4}

liveviewDynIpLookupsLevelEntry OBJECT-TYPE
	SYNTAX      LiveviewDynIpLookupsLevelEntry
	MAX-ACCESS  not-accessible
	STATUS      current
	DESCRIPTION
	"Table entry for liveviewDynIpLookups"
	INDEX { liveviewDynIpLookupsLevelName }
	::={liveviewDynIpLookupsLevelTable 1}

LiveviewDynIpLookupsLevelEntry ::=
	SEQUENCE {
		liveviewDynIpLookupsLevelName	DisplayString,
		liveviewDynIpLookupsLevelVal	Counter64,
		liveviewDynIpLookupsLevelMom	CounterBasedGauge64,
		liveviewDynIpLookupsLevelMax	CounterBasedGauge64
	}

liveviewDynIpLookupsLevelName OBJECT-TYPE
	SYNTAX      DisplayString
	MAX-ACCESS  not-accessible
	STATUS      current
	DESCRIPTION
	"Table entry display string for liveviewDynIpLookups"
	::={liveviewDynIpLookupsLevelEntry 1}

liveviewDynIpLookupsLevelVal OBJECT-TYPE
	SYNTAX	 Counter64
	MAX-ACCESS  read-only
	STATUS      current
	DESCRIPTION
	"Table entry attribute for liveviewDynIpLookups"
	::={liveviewDynIpLookupsLevelEntry 2}

liveviewDynIpLookupsLevelMom OBJECT-TYPE
	SYNTAX	 CounterBasedGauge64
	MAX-ACCESS  read-only
	STATUS      current
	DESCRIPTION
	"Table entry attribute for liveviewDynIpLookups"
	::={liveviewDynIpLookupsLevelEntry 3}

liveviewDynIpLookupsLevelMax OBJECT-TYPE
	SYNTAX	 CounterBasedGauge64
	MAX-ACCESS  read-only
	STATUS      current
	DESCRIPTION
	"Table entry attribute for liveviewDynIpLookups"
	::={liveviewDynIpLookupsLevelEntry 4}


liveviewPostProcessTime	OBJECT IDENTIFIER ::={liveview 29}

liveviewPostProcessTimeVal	OBJECT-TYPE
	SYNTAX	 CounterBasedGauge64
	MAX-ACCESS read-only
	STATUS current
	DESCRIPTION "Post-processing time (ms)"

	::={liveviewPostProcessTime 1}

liveviewPostProcessTimeMax	OBJECT-TYPE
	SYNTAX	 CounterBasedGauge64
	MAX-ACCESS read-only
	STATUS current
	DESCRIPTION "Post-processing time (ms)"

	::={liveviewPostProcessTime 3}

liveviewPostProcessTimeLevelTable OBJECT-TYPE
	SYNTAX      SEQUENCE OF LiveviewPostProcessTimeLevelEntry
	MAX-ACCESS  not-accessible
	STATUS      current
	DESCRIPTION
	"Table for liveviewPostProcessTime"
	::={liveviewPostProcessTime 4}

liveviewPostProcessTimeLevelEntry OBJECT-TYPE
	SYNTAX      LiveviewPostProcessTimeLevelEntry
	MAX-ACCESS  not-accessible
	STATUS      current
	DESCRIPTION
	"Table entry for liveviewPostProcessTime"
	INDEX { liveviewPostProcessTimeLevelName }
	::={liveviewPostProcessTimeLevelTable 1}

LiveviewPostProcessTimeLevelEntry ::=
	SEQUENCE {
		liveviewPostProcessTimeLevelName	DisplayString,
		liveviewPostProcessTimeLevelVal	CounterBasedGauge64,
		liveviewPostProcessTimeLevelMax	CounterBasedGauge64
	}

liveviewPostProcessTimeLevelName OBJECT-TYPE
	SYNTAX      DisplayString
	MAX-ACCESS  not-accessible
	STATUS      current
	DESCRIPTION
	"Table entry display string for liveviewPostProcessTime"
	::={liveviewPostProcessTimeLevelEntry 1}

liveviewPostProcessTimeLevelVal OBJECT-TYPE
	SYNTAX	 CounterBasedGauge64
	MAX-ACCESS  read-only
	STATUS      current
	DESCRIPTION
	"Table entry attribute for liveviewPostProcessTime"
	::={liveviewPostProcessTimeLevelEntry 2}

liveviewPostProcessTimeLevelMax OBJECT-TYPE
	SYNTAX	 CounterBasedGauge64
	MAX-ACCESS  read-only
	STATUS      current
	DESCRIPTION
	"Table entry attribute for liveviewPostProcessTime"
	::={liveviewPostProcessTimeLevelEntry 4}


liveviewNOPreProcessTime	OBJECT IDENTIFIER ::={liveview 30}

liveviewNOPreProcessTimeVal	OBJECT-TYPE
	SYNTAX	 CounterBasedGauge64
	MAX-ACCESS read-only
	STATUS current
	DESCRIPTION "Visible NetObjects pre-proccessing time (ms)"

	::={liveviewNOPreProcessTime 1}

liveviewNOPreProcessTimeMax	OBJECT-TYPE
	SYNTAX	 CounterBasedGauge64
	MAX-ACCESS read-only
	STATUS current
	DESCRIPTION "Visible NetObjects pre-proccessing time (ms)"

	::={liveviewNOPreProcessTime 3}

liveviewNOPreProcessTimeLevelTable OBJECT-TYPE
	SYNTAX      SEQUENCE OF LiveviewNOPreProcessTimeLevelEntry
	MAX-ACCESS  not-accessible
	STATUS      current
	DESCRIPTION
	"Table for liveviewNOPreProcessTime"
	::={liveviewNOPreProcessTime 4}

liveviewNOPreProcessTimeLevelEntry OBJECT-TYPE
	SYNTAX      LiveviewNOPreProcessTimeLevelEntry
	MAX-ACCESS  not-accessible
	STATUS      current
	DESCRIPTION
	"Table entry for liveviewNOPreProcessTime"
	INDEX { liveviewNOPreProcessTimeLevelName }
	::={liveviewNOPreProcessTimeLevelTable 1}

LiveviewNOPreProcessTimeLevelEntry ::=
	SEQUENCE {
		liveviewNOPreProcessTimeLevelName	DisplayString,
		liveviewNOPreProcessTimeLevelVal	CounterBasedGauge64,
		liveviewNOPreProcessTimeLevelMax	CounterBasedGauge64
	}

liveviewNOPreProcessTimeLevelName OBJECT-TYPE
	SYNTAX      DisplayString
	MAX-ACCESS  not-accessible
	STATUS      current
	DESCRIPTION
	"Table entry display string for liveviewNOPreProcessTime"
	::={liveviewNOPreProcessTimeLevelEntry 1}

liveviewNOPreProcessTimeLevelVal OBJECT-TYPE
	SYNTAX	 CounterBasedGauge64
	MAX-ACCESS  read-only
	STATUS      current
	DESCRIPTION
	"Table entry attribute for liveviewNOPreProcessTime"
	::={liveviewNOPreProcessTimeLevelEntry 2}

liveviewNOPreProcessTimeLevelMax OBJECT-TYPE
	SYNTAX	 CounterBasedGauge64
	MAX-ACCESS  read-only
	STATUS      current
	DESCRIPTION
	"Table entry attribute for liveviewNOPreProcessTime"
	::={liveviewNOPreProcessTimeLevelEntry 4}


liveviewHostPostProcessTime	OBJECT IDENTIFIER ::={liveview 31}

liveviewHostPostProcessTimeVal	OBJECT-TYPE
	SYNTAX	 CounterBasedGauge64
	MAX-ACCESS read-only
	STATUS current
	DESCRIPTION "Host post-processing time (ms)"

	::={liveviewHostPostProcessTime 1}

liveviewHostPostProcessTimeMax	OBJECT-TYPE
	SYNTAX	 CounterBasedGauge64
	MAX-ACCESS read-only
	STATUS current
	DESCRIPTION "Host post-processing time (ms)"

	::={liveviewHostPostProcessTime 3}

liveviewHostPostProcessTimeLevelTable OBJECT-TYPE
	SYNTAX      SEQUENCE OF LiveviewHostPostProcessTimeLevelEntry
	MAX-ACCESS  not-accessible
	STATUS      current
	DESCRIPTION
	"Table for liveviewHostPostProcessTime"
	::={liveviewHostPostProcessTime 4}

liveviewHostPostProcessTimeLevelEntry OBJECT-TYPE
	SYNTAX      LiveviewHostPostProcessTimeLevelEntry
	MAX-ACCESS  not-accessible
	STATUS      current
	DESCRIPTION
	"Table entry for liveviewHostPostProcessTime"
	INDEX { liveviewHostPostProcessTimeLevelName }
	::={liveviewHostPostProcessTimeLevelTable 1}

LiveviewHostPostProcessTimeLevelEntry ::=
	SEQUENCE {
		liveviewHostPostProcessTimeLevelName	DisplayString,
		liveviewHostPostProcessTimeLevelVal	CounterBasedGauge64,
		liveviewHostPostProcessTimeLevelMax	CounterBasedGauge64
	}

liveviewHostPostProcessTimeLevelName OBJECT-TYPE
	SYNTAX      DisplayString
	MAX-ACCESS  not-accessible
	STATUS      current
	DESCRIPTION
	"Table entry display string for liveviewHostPostProcessTime"
	::={liveviewHostPostProcessTimeLevelEntry 1}

liveviewHostPostProcessTimeLevelVal OBJECT-TYPE
	SYNTAX	 CounterBasedGauge64
	MAX-ACCESS  read-only
	STATUS      current
	DESCRIPTION
	"Table entry attribute for liveviewHostPostProcessTime"
	::={liveviewHostPostProcessTimeLevelEntry 2}

liveviewHostPostProcessTimeLevelMax OBJECT-TYPE
	SYNTAX	 CounterBasedGauge64
	MAX-ACCESS  read-only
	STATUS      current
	DESCRIPTION
	"Table entry attribute for liveviewHostPostProcessTime"
	::={liveviewHostPostProcessTimeLevelEntry 4}


liveviewNOPostProcessTime	OBJECT IDENTIFIER ::={liveview 32}

liveviewNOPostProcessTimeVal	OBJECT-TYPE
	SYNTAX	 CounterBasedGauge64
	MAX-ACCESS read-only
	STATUS current
	DESCRIPTION "Visible NetObjects post-processing time (ms)"

	::={liveviewNOPostProcessTime 1}

liveviewNOPostProcessTimeMax	OBJECT-TYPE
	SYNTAX	 CounterBasedGauge64
	MAX-ACCESS read-only
	STATUS current
	DESCRIPTION "Visible NetObjects post-processing time (ms)"

	::={liveviewNOPostProcessTime 3}

liveviewNOPostProcessTimeLevelTable OBJECT-TYPE
	SYNTAX      SEQUENCE OF LiveviewNOPostProcessTimeLevelEntry
	MAX-ACCESS  not-accessible
	STATUS      current
	DESCRIPTION
	"Table for liveviewNOPostProcessTime"
	::={liveviewNOPostProcessTime 4}

liveviewNOPostProcessTimeLevelEntry OBJECT-TYPE
	SYNTAX      LiveviewNOPostProcessTimeLevelEntry
	MAX-ACCESS  not-accessible
	STATUS      current
	DESCRIPTION
	"Table entry for liveviewNOPostProcessTime"
	INDEX { liveviewNOPostProcessTimeLevelName }
	::={liveviewNOPostProcessTimeLevelTable 1}

LiveviewNOPostProcessTimeLevelEntry ::=
	SEQUENCE {
		liveviewNOPostProcessTimeLevelName	DisplayString,
		liveviewNOPostProcessTimeLevelVal	CounterBasedGauge64,
		liveviewNOPostProcessTimeLevelMax	CounterBasedGauge64
	}

liveviewNOPostProcessTimeLevelName OBJECT-TYPE
	SYNTAX      DisplayString
	MAX-ACCESS  not-accessible
	STATUS      current
	DESCRIPTION
	"Table entry display string for liveviewNOPostProcessTime"
	::={liveviewNOPostProcessTimeLevelEntry 1}

liveviewNOPostProcessTimeLevelVal OBJECT-TYPE
	SYNTAX	 CounterBasedGauge64
	MAX-ACCESS  read-only
	STATUS      current
	DESCRIPTION
	"Table entry attribute for liveviewNOPostProcessTime"
	::={liveviewNOPostProcessTimeLevelEntry 2}

liveviewNOPostProcessTimeLevelMax OBJECT-TYPE
	SYNTAX	 CounterBasedGauge64
	MAX-ACCESS  read-only
	STATUS      current
	DESCRIPTION
	"Table entry attribute for liveviewNOPostProcessTime"
	::={liveviewNOPostProcessTimeLevelEntry 4}


iveviewDynItemCount	OBJECT IDENTIFIER ::={liveview 27}

iveviewDynItemCountVal	OBJECT-TYPE
	SYNTAX	 CounterBasedGauge64
	MAX-ACCESS read-only
	STATUS current
	DESCRIPTION "Dynamic netobject items in visible netobjects"

	::={iveviewDynItemCount 1}

iveviewDynItemCountMax	OBJECT-TYPE
	SYNTAX	 CounterBasedGauge64
	MAX-ACCESS read-only
	STATUS current
	DESCRIPTION "Dynamic netobject items in visible netobjects"

	::={iveviewDynItemCount 3}

iveviewDynItemCountLevelTable OBJECT-TYPE
	SYNTAX      SEQUENCE OF IveviewDynItemCountLevelEntry
	MAX-ACCESS  not-accessible
	STATUS      current
	DESCRIPTION
	"Table for iveviewDynItemCount"
	::={iveviewDynItemCount 4}

iveviewDynItemCountLevelEntry OBJECT-TYPE
	SYNTAX      IveviewDynItemCountLevelEntry
	MAX-ACCESS  not-accessible
	STATUS      current
	DESCRIPTION
	"Table entry for iveviewDynItemCount"
	INDEX { iveviewDynItemCountLevelName }
	::={iveviewDynItemCountLevelTable 1}

IveviewDynItemCountLevelEntry ::=
	SEQUENCE {
		iveviewDynItemCountLevelName	DisplayString,
		iveviewDynItemCountLevelVal	CounterBasedGauge64,
		iveviewDynItemCountLevelMax	CounterBasedGauge64
	}

iveviewDynItemCountLevelName OBJECT-TYPE
	SYNTAX      DisplayString
	MAX-ACCESS  not-accessible
	STATUS      current
	DESCRIPTION
	"Table entry display string for iveviewDynItemCount"
	::={iveviewDynItemCountLevelEntry 1}

iveviewDynItemCountLevelVal OBJECT-TYPE
	SYNTAX	 CounterBasedGauge64
	MAX-ACCESS  read-only
	STATUS      current
	DESCRIPTION
	"Table entry attribute for iveviewDynItemCount"
	::={iveviewDynItemCountLevelEntry 2}

iveviewDynItemCountLevelMax OBJECT-TYPE
	SYNTAX	 CounterBasedGauge64
	MAX-ACCESS  read-only
	STATUS      current
	DESCRIPTION
	"Table entry attribute for iveviewDynItemCount"
	::={iveviewDynItemCountLevelEntry 4}


liveviewDynIpCount	OBJECT IDENTIFIER ::={liveview 28}

liveviewDynIpCountVal	OBJECT-TYPE
	SYNTAX	 CounterBasedGauge64
	MAX-ACCESS read-only
	STATUS current
	DESCRIPTION "Dynamic netobject IPs in visible netobjects"

	::={liveviewDynIpCount 1}

liveviewDynIpCountMax	OBJECT-TYPE
	SYNTAX	 CounterBasedGauge64
	MAX-ACCESS read-only
	STATUS current
	DESCRIPTION "Dynamic netobject IPs in visible netobjects"

	::={liveviewDynIpCount 3}

liveviewDynIpCountLevelTable OBJECT-TYPE
	SYNTAX      SEQUENCE OF LiveviewDynIpCountLevelEntry
	MAX-ACCESS  not-accessible
	STATUS      current
	DESCRIPTION
	"Table for liveviewDynIpCount"
	::={liveviewDynIpCount 4}

liveviewDynIpCountLevelEntry OBJECT-TYPE
	SYNTAX      LiveviewDynIpCountLevelEntry
	MAX-ACCESS  not-accessible
	STATUS      current
	DESCRIPTION
	"Table entry for liveviewDynIpCount"
	INDEX { liveviewDynIpCountLevelName }
	::={liveviewDynIpCountLevelTable 1}

LiveviewDynIpCountLevelEntry ::=
	SEQUENCE {
		liveviewDynIpCountLevelName	DisplayString,
		liveviewDynIpCountLevelVal	CounterBasedGauge64,
		liveviewDynIpCountLevelMax	CounterBasedGauge64
	}

liveviewDynIpCountLevelName OBJECT-TYPE
	SYNTAX      DisplayString
	MAX-ACCESS  not-accessible
	STATUS      current
	DESCRIPTION
	"Table entry display string for liveviewDynIpCount"
	::={liveviewDynIpCountLevelEntry 1}

liveviewDynIpCountLevelVal OBJECT-TYPE
	SYNTAX	 CounterBasedGauge64
	MAX-ACCESS  read-only
	STATUS      current
	DESCRIPTION
	"Table entry attribute for liveviewDynIpCount"
	::={liveviewDynIpCountLevelEntry 2}

liveviewDynIpCountLevelMax OBJECT-TYPE
	SYNTAX	 CounterBasedGauge64
	MAX-ACCESS  read-only
	STATUS      current
	DESCRIPTION
	"Table entry attribute for liveviewDynIpCount"
	::={liveviewDynIpCountLevelEntry 4}


liveviewHostStatsRecordsReceived	OBJECT IDENTIFIER ::={liveview 33}

liveviewHostStatsRecordsReceivedVal	OBJECT-TYPE
	SYNTAX	 Counter64
	MAX-ACCESS read-only
	STATUS current
	DESCRIPTION "Host stats: records received"

	::={liveviewHostStatsRecordsReceived 1}

liveviewHostStatsRecordsReceivedMom	OBJECT-TYPE
	SYNTAX	 CounterBasedGauge64
	MAX-ACCESS read-only
	STATUS current
	DESCRIPTION "Host stats: records received"

	::={liveviewHostStatsRecordsReceived 2}

liveviewHostStatsRecordsReceivedMax	OBJECT-TYPE
	SYNTAX	 CounterBasedGauge64
	MAX-ACCESS read-only
	STATUS current
	DESCRIPTION "Host stats: records received"

	::={liveviewHostStatsRecordsReceived 3}

liveviewHostStatsRecordsReceivedLevelTable OBJECT-TYPE
	SYNTAX      SEQUENCE OF LiveviewHostStatsRecordsReceivedLevelEntry
	MAX-ACCESS  not-accessible
	STATUS      current
	DESCRIPTION
	"Table for liveviewHostStatsRecordsReceived"
	::={liveviewHostStatsRecordsReceived 4}

liveviewHostStatsRecordsReceivedLevelEntry OBJECT-TYPE
	SYNTAX      LiveviewHostStatsRecordsReceivedLevelEntry
	MAX-ACCESS  not-accessible
	STATUS      current
	DESCRIPTION
	"Table entry for liveviewHostStatsRecordsReceived"
	INDEX { liveviewHostStatsRecordsReceivedLevelName }
	::={liveviewHostStatsRecordsReceivedLevelTable 1}

LiveviewHostStatsRecordsReceivedLevelEntry ::=
	SEQUENCE {
		liveviewHostStatsRecordsReceivedLevelName	DisplayString,
		liveviewHostStatsRecordsReceivedLevelVal	Counter64,
		liveviewHostStatsRecordsReceivedLevelMom	CounterBasedGauge64,
		liveviewHostStatsRecordsReceivedLevelMax	CounterBasedGauge64
	}

liveviewHostStatsRecordsReceivedLevelName OBJECT-TYPE
	SYNTAX      DisplayString
	MAX-ACCESS  not-accessible
	STATUS      current
	DESCRIPTION
	"Table entry display string for liveviewHostStatsRecordsReceived"
	::={liveviewHostStatsRecordsReceivedLevelEntry 1}

liveviewHostStatsRecordsReceivedLevelVal OBJECT-TYPE
	SYNTAX	 Counter64
	MAX-ACCESS  read-only
	STATUS      current
	DESCRIPTION
	"Table entry attribute for liveviewHostStatsRecordsReceived"
	::={liveviewHostStatsRecordsReceivedLevelEntry 2}

liveviewHostStatsRecordsReceivedLevelMom OBJECT-TYPE
	SYNTAX	 CounterBasedGauge64
	MAX-ACCESS  read-only
	STATUS      current
	DESCRIPTION
	"Table entry attribute for liveviewHostStatsRecordsReceived"
	::={liveviewHostStatsRecordsReceivedLevelEntry 3}

liveviewHostStatsRecordsReceivedLevelMax OBJECT-TYPE
	SYNTAX	 CounterBasedGauge64
	MAX-ACCESS  read-only
	STATUS      current
	DESCRIPTION
	"Table entry attribute for liveviewHostStatsRecordsReceived"
	::={liveviewHostStatsRecordsReceivedLevelEntry 4}


liveviewHostStatsRecordsDiscarded	OBJECT IDENTIFIER ::={liveview 34}

liveviewHostStatsRecordsDiscardedVal	OBJECT-TYPE
	SYNTAX	 Counter64
	MAX-ACCESS read-only
	STATUS obsolete
	DESCRIPTION "Host stats: records discarded"

	::={liveviewHostStatsRecordsDiscarded 1}

liveviewHostStatsRecordsDiscardedMom	OBJECT-TYPE
	SYNTAX	 CounterBasedGauge64
	MAX-ACCESS read-only
	STATUS obsolete
	DESCRIPTION "Host stats: records discarded"

	::={liveviewHostStatsRecordsDiscarded 2}

liveviewHostStatsRecordsDiscardedMax	OBJECT-TYPE
	SYNTAX	 CounterBasedGauge64
	MAX-ACCESS read-only
	STATUS obsolete
	DESCRIPTION "Host stats: records discarded"

	::={liveviewHostStatsRecordsDiscarded 3}

liveviewHostStatsRecordsDiscardedLevelTable OBJECT-TYPE
	SYNTAX      SEQUENCE OF LiveviewHostStatsRecordsDiscardedLevelEntry
	MAX-ACCESS  not-accessible
	STATUS      current
	DESCRIPTION
	"Table for liveviewHostStatsRecordsDiscarded"
	::={liveviewHostStatsRecordsDiscarded 4}

liveviewHostStatsRecordsDiscardedLevelEntry OBJECT-TYPE
	SYNTAX      LiveviewHostStatsRecordsDiscardedLevelEntry
	MAX-ACCESS  not-accessible
	STATUS      current
	DESCRIPTION
	"Table entry for liveviewHostStatsRecordsDiscarded"
	INDEX { liveviewHostStatsRecordsDiscardedLevelName }
	::={liveviewHostStatsRecordsDiscardedLevelTable 1}

LiveviewHostStatsRecordsDiscardedLevelEntry ::=
	SEQUENCE {
		liveviewHostStatsRecordsDiscardedLevelName	DisplayString,
		liveviewHostStatsRecordsDiscardedLevelVal	Counter64,
		liveviewHostStatsRecordsDiscardedLevelMom	CounterBasedGauge64,
		liveviewHostStatsRecordsDiscardedLevelMax	CounterBasedGauge64
	}

liveviewHostStatsRecordsDiscardedLevelName OBJECT-TYPE
	SYNTAX      DisplayString
	MAX-ACCESS  not-accessible
	STATUS      current
	DESCRIPTION
	"Table entry display string for liveviewHostStatsRecordsDiscarded"
	::={liveviewHostStatsRecordsDiscardedLevelEntry 1}

liveviewHostStatsRecordsDiscardedLevelVal OBJECT-TYPE
	SYNTAX	 Counter64
	MAX-ACCESS  read-only
	STATUS      current
	DESCRIPTION
	"Table entry attribute for liveviewHostStatsRecordsDiscarded"
	::={liveviewHostStatsRecordsDiscardedLevelEntry 2}

liveviewHostStatsRecordsDiscardedLevelMom OBJECT-TYPE
	SYNTAX	 CounterBasedGauge64
	MAX-ACCESS  read-only
	STATUS      current
	DESCRIPTION
	"Table entry attribute for liveviewHostStatsRecordsDiscarded"
	::={liveviewHostStatsRecordsDiscardedLevelEntry 3}

liveviewHostStatsRecordsDiscardedLevelMax OBJECT-TYPE
	SYNTAX	 CounterBasedGauge64
	MAX-ACCESS  read-only
	STATUS      current
	DESCRIPTION
	"Table entry attribute for liveviewHostStatsRecordsDiscarded"
	::={liveviewHostStatsRecordsDiscardedLevelEntry 4}


liveviewHostStatsHostsAdded	OBJECT IDENTIFIER ::={liveview 35}

liveviewHostStatsHostsAddedVal	OBJECT-TYPE
	SYNTAX	 Counter64
	MAX-ACCESS read-only
	STATUS obsolete
	DESCRIPTION "Host stats: hosts added"

	::={liveviewHostStatsHostsAdded 1}

liveviewHostStatsHostsAddedMom	OBJECT-TYPE
	SYNTAX	 CounterBasedGauge64
	MAX-ACCESS read-only
	STATUS obsolete
	DESCRIPTION "Host stats: hosts added"

	::={liveviewHostStatsHostsAdded 2}

liveviewHostStatsHostsAddedMax	OBJECT-TYPE
	SYNTAX	 CounterBasedGauge64
	MAX-ACCESS read-only
	STATUS obsolete
	DESCRIPTION "Host stats: hosts added"

	::={liveviewHostStatsHostsAdded 3}

liveviewHostStatsHostsAddedLevelTable OBJECT-TYPE
	SYNTAX      SEQUENCE OF LiveviewHostStatsHostsAddedLevelEntry
	MAX-ACCESS  not-accessible
	STATUS      current
	DESCRIPTION
	"Table for liveviewHostStatsHostsAdded"
	::={liveviewHostStatsHostsAdded 4}

liveviewHostStatsHostsAddedLevelEntry OBJECT-TYPE
	SYNTAX      LiveviewHostStatsHostsAddedLevelEntry
	MAX-ACCESS  not-accessible
	STATUS      current
	DESCRIPTION
	"Table entry for liveviewHostStatsHostsAdded"
	INDEX { liveviewHostStatsHostsAddedLevelName }
	::={liveviewHostStatsHostsAddedLevelTable 1}

LiveviewHostStatsHostsAddedLevelEntry ::=
	SEQUENCE {
		liveviewHostStatsHostsAddedLevelName	DisplayString,
		liveviewHostStatsHostsAddedLevelVal	Counter64,
		liveviewHostStatsHostsAddedLevelMom	CounterBasedGauge64,
		liveviewHostStatsHostsAddedLevelMax	CounterBasedGauge64
	}

liveviewHostStatsHostsAddedLevelName OBJECT-TYPE
	SYNTAX      DisplayString
	MAX-ACCESS  not-accessible
	STATUS      current
	DESCRIPTION
	"Table entry display string for liveviewHostStatsHostsAdded"
	::={liveviewHostStatsHostsAddedLevelEntry 1}

liveviewHostStatsHostsAddedLevelVal OBJECT-TYPE
	SYNTAX	 Counter64
	MAX-ACCESS  read-only
	STATUS      current
	DESCRIPTION
	"Table entry attribute for liveviewHostStatsHostsAdded"
	::={liveviewHostStatsHostsAddedLevelEntry 2}

liveviewHostStatsHostsAddedLevelMom OBJECT-TYPE
	SYNTAX	 CounterBasedGauge64
	MAX-ACCESS  read-only
	STATUS      current
	DESCRIPTION
	"Table entry attribute for liveviewHostStatsHostsAdded"
	::={liveviewHostStatsHostsAddedLevelEntry 3}

liveviewHostStatsHostsAddedLevelMax OBJECT-TYPE
	SYNTAX	 CounterBasedGauge64
	MAX-ACCESS  read-only
	STATUS      current
	DESCRIPTION
	"Table entry attribute for liveviewHostStatsHostsAdded"
	::={liveviewHostStatsHostsAddedLevelEntry 4}


liveviewHostStatsHostsRemoved	OBJECT IDENTIFIER ::={liveview 36}

liveviewHostStatsHostsRemovedVal	OBJECT-TYPE
	SYNTAX	 Counter64
	MAX-ACCESS read-only
	STATUS obsolete
	DESCRIPTION "Host stats: hosts removed"

	::={liveviewHostStatsHostsRemoved 1}

liveviewHostStatsHostsRemovedMom	OBJECT-TYPE
	SYNTAX	 CounterBasedGauge64
	MAX-ACCESS read-only
	STATUS obsolete
	DESCRIPTION "Host stats: hosts removed"

	::={liveviewHostStatsHostsRemoved 2}

liveviewHostStatsHostsRemovedMax	OBJECT-TYPE
	SYNTAX	 CounterBasedGauge64
	MAX-ACCESS read-only
	STATUS obsolete
	DESCRIPTION "Host stats: hosts removed"

	::={liveviewHostStatsHostsRemoved 3}

liveviewHostStatsHostsRemovedLevelTable OBJECT-TYPE
	SYNTAX      SEQUENCE OF LiveviewHostStatsHostsRemovedLevelEntry
	MAX-ACCESS  not-accessible
	STATUS      current
	DESCRIPTION
	"Table for liveviewHostStatsHostsRemoved"
	::={liveviewHostStatsHostsRemoved 4}

liveviewHostStatsHostsRemovedLevelEntry OBJECT-TYPE
	SYNTAX      LiveviewHostStatsHostsRemovedLevelEntry
	MAX-ACCESS  not-accessible
	STATUS      current
	DESCRIPTION
	"Table entry for liveviewHostStatsHostsRemoved"
	INDEX { liveviewHostStatsHostsRemovedLevelName }
	::={liveviewHostStatsHostsRemovedLevelTable 1}

LiveviewHostStatsHostsRemovedLevelEntry ::=
	SEQUENCE {
		liveviewHostStatsHostsRemovedLevelName	DisplayString,
		liveviewHostStatsHostsRemovedLevelVal	Counter64,
		liveviewHostStatsHostsRemovedLevelMom	CounterBasedGauge64,
		liveviewHostStatsHostsRemovedLevelMax	CounterBasedGauge64
	}

liveviewHostStatsHostsRemovedLevelName OBJECT-TYPE
	SYNTAX      DisplayString
	MAX-ACCESS  not-accessible
	STATUS      current
	DESCRIPTION
	"Table entry display string for liveviewHostStatsHostsRemoved"
	::={liveviewHostStatsHostsRemovedLevelEntry 1}

liveviewHostStatsHostsRemovedLevelVal OBJECT-TYPE
	SYNTAX	 Counter64
	MAX-ACCESS  read-only
	STATUS      current
	DESCRIPTION
	"Table entry attribute for liveviewHostStatsHostsRemoved"
	::={liveviewHostStatsHostsRemovedLevelEntry 2}

liveviewHostStatsHostsRemovedLevelMom OBJECT-TYPE
	SYNTAX	 CounterBasedGauge64
	MAX-ACCESS  read-only
	STATUS      current
	DESCRIPTION
	"Table entry attribute for liveviewHostStatsHostsRemoved"
	::={liveviewHostStatsHostsRemovedLevelEntry 3}

liveviewHostStatsHostsRemovedLevelMax OBJECT-TYPE
	SYNTAX	 CounterBasedGauge64
	MAX-ACCESS  read-only
	STATUS      current
	DESCRIPTION
	"Table entry attribute for liveviewHostStatsHostsRemoved"
	::={liveviewHostStatsHostsRemovedLevelEntry 4}


liveviewHostStatsHostCacheExhausted	OBJECT IDENTIFIER ::={liveview 37}

liveviewHostStatsHostCacheExhaustedVal	OBJECT-TYPE
	SYNTAX	 Counter64
	MAX-ACCESS read-only
	STATUS obsolete
	DESCRIPTION "Host stats: Host cache exhausted"

	::={liveviewHostStatsHostCacheExhausted 1}

liveviewHostStatsHostCacheExhaustedMom	OBJECT-TYPE
	SYNTAX	 CounterBasedGauge64
	MAX-ACCESS read-only
	STATUS obsolete
	DESCRIPTION "Host stats: Host cache exhausted"

	::={liveviewHostStatsHostCacheExhausted 2}

liveviewHostStatsHostCacheExhaustedMax	OBJECT-TYPE
	SYNTAX	 CounterBasedGauge64
	MAX-ACCESS read-only
	STATUS obsolete
	DESCRIPTION "Host stats: Host cache exhausted"

	::={liveviewHostStatsHostCacheExhausted 3}

liveviewHostStatsHostCacheExhaustedLevelTable OBJECT-TYPE
	SYNTAX      SEQUENCE OF LiveviewHostStatsHostCacheExhaustedLevelEntry
	MAX-ACCESS  not-accessible
	STATUS      current
	DESCRIPTION
	"Table for liveviewHostStatsHostCacheExhausted"
	::={liveviewHostStatsHostCacheExhausted 4}

liveviewHostStatsHostCacheExhaustedLevelEntry OBJECT-TYPE
	SYNTAX      LiveviewHostStatsHostCacheExhaustedLevelEntry
	MAX-ACCESS  not-accessible
	STATUS      current
	DESCRIPTION
	"Table entry for liveviewHostStatsHostCacheExhausted"
	INDEX { liveviewHostStatsHostCacheExhaustedLevelName }
	::={liveviewHostStatsHostCacheExhaustedLevelTable 1}

LiveviewHostStatsHostCacheExhaustedLevelEntry ::=
	SEQUENCE {
		liveviewHostStatsHostCacheExhaustedLevelName	DisplayString,
		liveviewHostStatsHostCacheExhaustedLevelVal	Counter64,
		liveviewHostStatsHostCacheExhaustedLevelMom	CounterBasedGauge64,
		liveviewHostStatsHostCacheExhaustedLevelMax	CounterBasedGauge64
	}

liveviewHostStatsHostCacheExhaustedLevelName OBJECT-TYPE
	SYNTAX      DisplayString
	MAX-ACCESS  not-accessible
	STATUS      current
	DESCRIPTION
	"Table entry display string for liveviewHostStatsHostCacheExhausted"
	::={liveviewHostStatsHostCacheExhaustedLevelEntry 1}

liveviewHostStatsHostCacheExhaustedLevelVal OBJECT-TYPE
	SYNTAX	 Counter64
	MAX-ACCESS  read-only
	STATUS      current
	DESCRIPTION
	"Table entry attribute for liveviewHostStatsHostCacheExhausted"
	::={liveviewHostStatsHostCacheExhaustedLevelEntry 2}

liveviewHostStatsHostCacheExhaustedLevelMom OBJECT-TYPE
	SYNTAX	 CounterBasedGauge64
	MAX-ACCESS  read-only
	STATUS      current
	DESCRIPTION
	"Table entry attribute for liveviewHostStatsHostCacheExhausted"
	::={liveviewHostStatsHostCacheExhaustedLevelEntry 3}

liveviewHostStatsHostCacheExhaustedLevelMax OBJECT-TYPE
	SYNTAX	 CounterBasedGauge64
	MAX-ACCESS  read-only
	STATUS      current
	DESCRIPTION
	"Table entry attribute for liveviewHostStatsHostCacheExhausted"
	::={liveviewHostStatsHostCacheExhaustedLevelEntry 4}


liveviewConnUpdateBatches	OBJECT IDENTIFIER ::={liveview 38}

liveviewConnUpdateBatchesVal	OBJECT-TYPE
	SYNTAX	 Counter64
	MAX-ACCESS read-only
	STATUS current
	DESCRIPTION "Connection update batches"

	::={liveviewConnUpdateBatches 1}

liveviewConnUpdateBatchesMom	OBJECT-TYPE
	SYNTAX	 CounterBasedGauge64
	MAX-ACCESS read-only
	STATUS current
	DESCRIPTION "Connection update batches"

	::={liveviewConnUpdateBatches 2}

liveviewConnUpdateBatchesMax	OBJECT-TYPE
	SYNTAX	 CounterBasedGauge64
	MAX-ACCESS read-only
	STATUS current
	DESCRIPTION "Connection update batches"

	::={liveviewConnUpdateBatches 3}

liveviewConnUpdateBatchesLevelTable OBJECT-TYPE
	SYNTAX      SEQUENCE OF LiveviewConnUpdateBatchesLevelEntry
	MAX-ACCESS  not-accessible
	STATUS      current
	DESCRIPTION
	"Table for liveviewConnUpdateBatches"
	::={liveviewConnUpdateBatches 4}

liveviewConnUpdateBatchesLevelEntry OBJECT-TYPE
	SYNTAX      LiveviewConnUpdateBatchesLevelEntry
	MAX-ACCESS  not-accessible
	STATUS      current
	DESCRIPTION
	"Table entry for liveviewConnUpdateBatches"
	INDEX { liveviewConnUpdateBatchesLevelName }
	::={liveviewConnUpdateBatchesLevelTable 1}

LiveviewConnUpdateBatchesLevelEntry ::=
	SEQUENCE {
		liveviewConnUpdateBatchesLevelName	DisplayString,
		liveviewConnUpdateBatchesLevelVal	Counter64,
		liveviewConnUpdateBatchesLevelMom	CounterBasedGauge64,
		liveviewConnUpdateBatchesLevelMax	CounterBasedGauge64
	}

liveviewConnUpdateBatchesLevelName OBJECT-TYPE
	SYNTAX      DisplayString
	MAX-ACCESS  not-accessible
	STATUS      current
	DESCRIPTION
	"Table entry display string for liveviewConnUpdateBatches"
	::={liveviewConnUpdateBatchesLevelEntry 1}

liveviewConnUpdateBatchesLevelVal OBJECT-TYPE
	SYNTAX	 Counter64
	MAX-ACCESS  read-only
	STATUS      current
	DESCRIPTION
	"Table entry attribute for liveviewConnUpdateBatches"
	::={liveviewConnUpdateBatchesLevelEntry 2}

liveviewConnUpdateBatchesLevelMom OBJECT-TYPE
	SYNTAX	 CounterBasedGauge64
	MAX-ACCESS  read-only
	STATUS      current
	DESCRIPTION
	"Table entry attribute for liveviewConnUpdateBatches"
	::={liveviewConnUpdateBatchesLevelEntry 3}

liveviewConnUpdateBatchesLevelMax OBJECT-TYPE
	SYNTAX	 CounterBasedGauge64
	MAX-ACCESS  read-only
	STATUS      current
	DESCRIPTION
	"Table entry attribute for liveviewConnUpdateBatches"
	::={liveviewConnUpdateBatchesLevelEntry 4}


liveviewSessionContextRows	OBJECT IDENTIFIER ::={liveview 39}

liveviewSessionContextRowsVal	OBJECT-TYPE
	SYNTAX	 CounterBasedGauge64
	MAX-ACCESS read-only
	STATUS current
	DESCRIPTION "Session Context Rows"

	::={liveviewSessionContextRows 1}

liveviewSessionContextRowsMax	OBJECT-TYPE
	SYNTAX	 CounterBasedGauge64
	MAX-ACCESS read-only
	STATUS current
	DESCRIPTION "Session Context Rows"

	::={liveviewSessionContextRows 3}

liveviewSessionContextRowsLevelTable OBJECT-TYPE
	SYNTAX      SEQUENCE OF LiveviewSessionContextRowsLevelEntry
	MAX-ACCESS  not-accessible
	STATUS      current
	DESCRIPTION
	"Table for liveviewSessionContextRows"
	::={liveviewSessionContextRows 4}

liveviewSessionContextRowsLevelEntry OBJECT-TYPE
	SYNTAX      LiveviewSessionContextRowsLevelEntry
	MAX-ACCESS  not-accessible
	STATUS      current
	DESCRIPTION
	"Table entry for liveviewSessionContextRows"
	INDEX { liveviewSessionContextRowsLevelName }
	::={liveviewSessionContextRowsLevelTable 1}

LiveviewSessionContextRowsLevelEntry ::=
	SEQUENCE {
		liveviewSessionContextRowsLevelName	DisplayString,
		liveviewSessionContextRowsLevelVal	CounterBasedGauge64,
		liveviewSessionContextRowsLevelMax	CounterBasedGauge64
	}

liveviewSessionContextRowsLevelName OBJECT-TYPE
	SYNTAX      DisplayString
	MAX-ACCESS  not-accessible
	STATUS      current
	DESCRIPTION
	"Table entry display string for liveviewSessionContextRows"
	::={liveviewSessionContextRowsLevelEntry 1}

liveviewSessionContextRowsLevelVal OBJECT-TYPE
	SYNTAX	 CounterBasedGauge64
	MAX-ACCESS  read-only
	STATUS      current
	DESCRIPTION
	"Table entry attribute for liveviewSessionContextRows"
	::={liveviewSessionContextRowsLevelEntry 2}

liveviewSessionContextRowsLevelMax OBJECT-TYPE
	SYNTAX	 CounterBasedGauge64
	MAX-ACCESS  read-only
	STATUS      current
	DESCRIPTION
	"Table entry attribute for liveviewSessionContextRows"
	::={liveviewSessionContextRowsLevelEntry 4}


liveviewSessionContextRowsinTable	OBJECT IDENTIFIER ::={liveview 40}

liveviewSessionContextRowsinTableVal	OBJECT-TYPE
	SYNTAX	 CounterBasedGauge64
	MAX-ACCESS read-only
	STATUS current
	DESCRIPTION "Session Context Rows in Table"

	::={liveviewSessionContextRowsinTable 1}

liveviewSessionContextRowsinTableMax	OBJECT-TYPE
	SYNTAX	 CounterBasedGauge64
	MAX-ACCESS read-only
	STATUS current
	DESCRIPTION "Session Context Rows in Table"

	::={liveviewSessionContextRowsinTable 3}

liveviewSessionContextRowsinTableLevelTable OBJECT-TYPE
	SYNTAX      SEQUENCE OF LiveviewSessionContextRowsinTableLevelEntry
	MAX-ACCESS  not-accessible
	STATUS      current
	DESCRIPTION
	"Table for liveviewSessionContextRowsinTable"
	::={liveviewSessionContextRowsinTable 4}

liveviewSessionContextRowsinTableLevelEntry OBJECT-TYPE
	SYNTAX      LiveviewSessionContextRowsinTableLevelEntry
	MAX-ACCESS  not-accessible
	STATUS      current
	DESCRIPTION
	"Table entry for liveviewSessionContextRowsinTable"
	INDEX { liveviewSessionContextRowsinTableLevelName }
	::={liveviewSessionContextRowsinTableLevelTable 1}

LiveviewSessionContextRowsinTableLevelEntry ::=
	SEQUENCE {
		liveviewSessionContextRowsinTableLevelName	DisplayString,
		liveviewSessionContextRowsinTableLevelVal	CounterBasedGauge64,
		liveviewSessionContextRowsinTableLevelMax	CounterBasedGauge64
	}

liveviewSessionContextRowsinTableLevelName OBJECT-TYPE
	SYNTAX      DisplayString
	MAX-ACCESS  not-accessible
	STATUS      current
	DESCRIPTION
	"Table entry display string for liveviewSessionContextRowsinTable"
	::={liveviewSessionContextRowsinTableLevelEntry 1}

liveviewSessionContextRowsinTableLevelVal OBJECT-TYPE
	SYNTAX	 CounterBasedGauge64
	MAX-ACCESS  read-only
	STATUS      current
	DESCRIPTION
	"Table entry attribute for liveviewSessionContextRowsinTable"
	::={liveviewSessionContextRowsinTableLevelEntry 2}

liveviewSessionContextRowsinTableLevelMax OBJECT-TYPE
	SYNTAX	 CounterBasedGauge64
	MAX-ACCESS  read-only
	STATUS      current
	DESCRIPTION
	"Table entry attribute for liveviewSessionContextRowsinTable"
	::={liveviewSessionContextRowsinTableLevelEntry 4}


liveviewHostStatsBufAliasing	OBJECT IDENTIFIER ::={liveview 41}

liveviewHostStatsBufAliasingVal	OBJECT-TYPE
	SYNTAX	 Counter64
	MAX-ACCESS read-only
	STATUS obsolete
	DESCRIPTION "Host stats: Buffer aliasing count"

	::={liveviewHostStatsBufAliasing 1}

liveviewHostStatsBufAliasingMom	OBJECT-TYPE
	SYNTAX	 CounterBasedGauge64
	MAX-ACCESS read-only
	STATUS obsolete
	DESCRIPTION "Host stats: Buffer aliasing count"

	::={liveviewHostStatsBufAliasing 2}

liveviewHostStatsBufAliasingMax	OBJECT-TYPE
	SYNTAX	 CounterBasedGauge64
	MAX-ACCESS read-only
	STATUS obsolete
	DESCRIPTION "Host stats: Buffer aliasing count"

	::={liveviewHostStatsBufAliasing 3}

liveviewHostStatsBufAliasingLevelTable OBJECT-TYPE
	SYNTAX      SEQUENCE OF LiveviewHostStatsBufAliasingLevelEntry
	MAX-ACCESS  not-accessible
	STATUS      current
	DESCRIPTION
	"Table for liveviewHostStatsBufAliasing"
	::={liveviewHostStatsBufAliasing 4}

liveviewHostStatsBufAliasingLevelEntry OBJECT-TYPE
	SYNTAX      LiveviewHostStatsBufAliasingLevelEntry
	MAX-ACCESS  not-accessible
	STATUS      current
	DESCRIPTION
	"Table entry for liveviewHostStatsBufAliasing"
	INDEX { liveviewHostStatsBufAliasingLevelName }
	::={liveviewHostStatsBufAliasingLevelTable 1}

LiveviewHostStatsBufAliasingLevelEntry ::=
	SEQUENCE {
		liveviewHostStatsBufAliasingLevelName	DisplayString,
		liveviewHostStatsBufAliasingLevelVal	Counter64,
		liveviewHostStatsBufAliasingLevelMom	CounterBasedGauge64,
		liveviewHostStatsBufAliasingLevelMax	CounterBasedGauge64
	}

liveviewHostStatsBufAliasingLevelName OBJECT-TYPE
	SYNTAX      DisplayString
	MAX-ACCESS  not-accessible
	STATUS      current
	DESCRIPTION
	"Table entry display string for liveviewHostStatsBufAliasing"
	::={liveviewHostStatsBufAliasingLevelEntry 1}

liveviewHostStatsBufAliasingLevelVal OBJECT-TYPE
	SYNTAX	 Counter64
	MAX-ACCESS  read-only
	STATUS      current
	DESCRIPTION
	"Table entry attribute for liveviewHostStatsBufAliasing"
	::={liveviewHostStatsBufAliasingLevelEntry 2}

liveviewHostStatsBufAliasingLevelMom OBJECT-TYPE
	SYNTAX	 CounterBasedGauge64
	MAX-ACCESS  read-only
	STATUS      current
	DESCRIPTION
	"Table entry attribute for liveviewHostStatsBufAliasing"
	::={liveviewHostStatsBufAliasingLevelEntry 3}

liveviewHostStatsBufAliasingLevelMax OBJECT-TYPE
	SYNTAX	 CounterBasedGauge64
	MAX-ACCESS  read-only
	STATUS      current
	DESCRIPTION
	"Table entry attribute for liveviewHostStatsBufAliasing"
	::={liveviewHostStatsBufAliasingLevelEntry 4}


liveviewHostStatsVolumeReceived	OBJECT IDENTIFIER ::={liveview 42}

liveviewHostStatsVolumeReceivedVal	OBJECT-TYPE
	SYNTAX	 Counter64
	MAX-ACCESS read-only
	STATUS current
	DESCRIPTION "Host stats: Volume received"

	::={liveviewHostStatsVolumeReceived 1}

liveviewHostStatsVolumeReceivedMom	OBJECT-TYPE
	SYNTAX	 CounterBasedGauge64
	MAX-ACCESS read-only
	STATUS current
	DESCRIPTION "Host stats: Volume received"

	::={liveviewHostStatsVolumeReceived 2}

liveviewHostStatsVolumeReceivedMax	OBJECT-TYPE
	SYNTAX	 CounterBasedGauge64
	MAX-ACCESS read-only
	STATUS current
	DESCRIPTION "Host stats: Volume received"

	::={liveviewHostStatsVolumeReceived 3}

liveviewHostStatsVolumeReceivedLevelTable OBJECT-TYPE
	SYNTAX      SEQUENCE OF LiveviewHostStatsVolumeReceivedLevelEntry
	MAX-ACCESS  not-accessible
	STATUS      current
	DESCRIPTION
	"Table for liveviewHostStatsVolumeReceived"
	::={liveviewHostStatsVolumeReceived 4}

liveviewHostStatsVolumeReceivedLevelEntry OBJECT-TYPE
	SYNTAX      LiveviewHostStatsVolumeReceivedLevelEntry
	MAX-ACCESS  not-accessible
	STATUS      current
	DESCRIPTION
	"Table entry for liveviewHostStatsVolumeReceived"
	INDEX { liveviewHostStatsVolumeReceivedLevelName }
	::={liveviewHostStatsVolumeReceivedLevelTable 1}

LiveviewHostStatsVolumeReceivedLevelEntry ::=
	SEQUENCE {
		liveviewHostStatsVolumeReceivedLevelName	DisplayString,
		liveviewHostStatsVolumeReceivedLevelVal	Counter64,
		liveviewHostStatsVolumeReceivedLevelMom	CounterBasedGauge64,
		liveviewHostStatsVolumeReceivedLevelMax	CounterBasedGauge64
	}

liveviewHostStatsVolumeReceivedLevelName OBJECT-TYPE
	SYNTAX      DisplayString
	MAX-ACCESS  not-accessible
	STATUS      current
	DESCRIPTION
	"Table entry display string for liveviewHostStatsVolumeReceived"
	::={liveviewHostStatsVolumeReceivedLevelEntry 1}

liveviewHostStatsVolumeReceivedLevelVal OBJECT-TYPE
	SYNTAX	 Counter64
	MAX-ACCESS  read-only
	STATUS      current
	DESCRIPTION
	"Table entry attribute for liveviewHostStatsVolumeReceived"
	::={liveviewHostStatsVolumeReceivedLevelEntry 2}

liveviewHostStatsVolumeReceivedLevelMom OBJECT-TYPE
	SYNTAX	 CounterBasedGauge64
	MAX-ACCESS  read-only
	STATUS      current
	DESCRIPTION
	"Table entry attribute for liveviewHostStatsVolumeReceived"
	::={liveviewHostStatsVolumeReceivedLevelEntry 3}

liveviewHostStatsVolumeReceivedLevelMax OBJECT-TYPE
	SYNTAX	 CounterBasedGauge64
	MAX-ACCESS  read-only
	STATUS      current
	DESCRIPTION
	"Table entry attribute for liveviewHostStatsVolumeReceived"
	::={liveviewHostStatsVolumeReceivedLevelEntry 4}


liveviewHostStatsVolumeSent	OBJECT IDENTIFIER ::={liveview 43}

liveviewHostStatsVolumeSentVal	OBJECT-TYPE
	SYNTAX	 Counter64
	MAX-ACCESS read-only
	STATUS current
	DESCRIPTION "Host stats: Volume sent"

	::={liveviewHostStatsVolumeSent 1}

liveviewHostStatsVolumeSentMom	OBJECT-TYPE
	SYNTAX	 CounterBasedGauge64
	MAX-ACCESS read-only
	STATUS current
	DESCRIPTION "Host stats: Volume sent"

	::={liveviewHostStatsVolumeSent 2}

liveviewHostStatsVolumeSentMax	OBJECT-TYPE
	SYNTAX	 CounterBasedGauge64
	MAX-ACCESS read-only
	STATUS current
	DESCRIPTION "Host stats: Volume sent"

	::={liveviewHostStatsVolumeSent 3}

liveviewHostStatsVolumeSentLevelTable OBJECT-TYPE
	SYNTAX      SEQUENCE OF LiveviewHostStatsVolumeSentLevelEntry
	MAX-ACCESS  not-accessible
	STATUS      current
	DESCRIPTION
	"Table for liveviewHostStatsVolumeSent"
	::={liveviewHostStatsVolumeSent 4}

liveviewHostStatsVolumeSentLevelEntry OBJECT-TYPE
	SYNTAX      LiveviewHostStatsVolumeSentLevelEntry
	MAX-ACCESS  not-accessible
	STATUS      current
	DESCRIPTION
	"Table entry for liveviewHostStatsVolumeSent"
	INDEX { liveviewHostStatsVolumeSentLevelName }
	::={liveviewHostStatsVolumeSentLevelTable 1}

LiveviewHostStatsVolumeSentLevelEntry ::=
	SEQUENCE {
		liveviewHostStatsVolumeSentLevelName	DisplayString,
		liveviewHostStatsVolumeSentLevelVal	Counter64,
		liveviewHostStatsVolumeSentLevelMom	CounterBasedGauge64,
		liveviewHostStatsVolumeSentLevelMax	CounterBasedGauge64
	}

liveviewHostStatsVolumeSentLevelName OBJECT-TYPE
	SYNTAX      DisplayString
	MAX-ACCESS  not-accessible
	STATUS      current
	DESCRIPTION
	"Table entry display string for liveviewHostStatsVolumeSent"
	::={liveviewHostStatsVolumeSentLevelEntry 1}

liveviewHostStatsVolumeSentLevelVal OBJECT-TYPE
	SYNTAX	 Counter64
	MAX-ACCESS  read-only
	STATUS      current
	DESCRIPTION
	"Table entry attribute for liveviewHostStatsVolumeSent"
	::={liveviewHostStatsVolumeSentLevelEntry 2}

liveviewHostStatsVolumeSentLevelMom OBJECT-TYPE
	SYNTAX	 CounterBasedGauge64
	MAX-ACCESS  read-only
	STATUS      current
	DESCRIPTION
	"Table entry attribute for liveviewHostStatsVolumeSent"
	::={liveviewHostStatsVolumeSentLevelEntry 3}

liveviewHostStatsVolumeSentLevelMax OBJECT-TYPE
	SYNTAX	 CounterBasedGauge64
	MAX-ACCESS  read-only
	STATUS      current
	DESCRIPTION
	"Table entry attribute for liveviewHostStatsVolumeSent"
	::={liveviewHostStatsVolumeSentLevelEntry 4}


liveviewHostStatsHosts	OBJECT IDENTIFIER ::={liveview 44}

liveviewHostStatsHostsVal	OBJECT-TYPE
	SYNTAX	 CounterBasedGauge64
	MAX-ACCESS read-only
	STATUS obsolete
	DESCRIPTION "Host stats: Number of hosts"

	::={liveviewHostStatsHosts 1}

liveviewHostStatsHostsMax	OBJECT-TYPE
	SYNTAX	 CounterBasedGauge64
	MAX-ACCESS read-only
	STATUS obsolete
	DESCRIPTION "Host stats: Number of hosts"

	::={liveviewHostStatsHosts 3}

liveviewHostStatsHostsLevelTable OBJECT-TYPE
	SYNTAX      SEQUENCE OF LiveviewHostStatsHostsLevelEntry
	MAX-ACCESS  not-accessible
	STATUS      current
	DESCRIPTION
	"Table for liveviewHostStatsHosts"
	::={liveviewHostStatsHosts 4}

liveviewHostStatsHostsLevelEntry OBJECT-TYPE
	SYNTAX      LiveviewHostStatsHostsLevelEntry
	MAX-ACCESS  not-accessible
	STATUS      current
	DESCRIPTION
	"Table entry for liveviewHostStatsHosts"
	INDEX { liveviewHostStatsHostsLevelName }
	::={liveviewHostStatsHostsLevelTable 1}

LiveviewHostStatsHostsLevelEntry ::=
	SEQUENCE {
		liveviewHostStatsHostsLevelName	DisplayString,
		liveviewHostStatsHostsLevelVal	CounterBasedGauge64,
		liveviewHostStatsHostsLevelMax	CounterBasedGauge64
	}

liveviewHostStatsHostsLevelName OBJECT-TYPE
	SYNTAX      DisplayString
	MAX-ACCESS  not-accessible
	STATUS      current
	DESCRIPTION
	"Table entry display string for liveviewHostStatsHosts"
	::={liveviewHostStatsHostsLevelEntry 1}

liveviewHostStatsHostsLevelVal OBJECT-TYPE
	SYNTAX	 CounterBasedGauge64
	MAX-ACCESS  read-only
	STATUS      current
	DESCRIPTION
	"Table entry attribute for liveviewHostStatsHosts"
	::={liveviewHostStatsHostsLevelEntry 2}

liveviewHostStatsHostsLevelMax OBJECT-TYPE
	SYNTAX	 CounterBasedGauge64
	MAX-ACCESS  read-only
	STATUS      current
	DESCRIPTION
	"Table entry attribute for liveviewHostStatsHosts"
	::={liveviewHostStatsHostsLevelEntry 4}


liveviewHostStatsSessionContextLookups	OBJECT IDENTIFIER ::={liveview 45}

liveviewHostStatsSessionContextLookupsVal	OBJECT-TYPE
	SYNTAX	 Counter64
	MAX-ACCESS read-only
	STATUS obsolete
	DESCRIPTION "Host stats: Session Context Lookups"

	::={liveviewHostStatsSessionContextLookups 1}

liveviewHostStatsSessionContextLookupsMom	OBJECT-TYPE
	SYNTAX	 CounterBasedGauge64
	MAX-ACCESS read-only
	STATUS obsolete
	DESCRIPTION "Host stats: Session Context Lookups"

	::={liveviewHostStatsSessionContextLookups 2}

liveviewHostStatsSessionContextLookupsMax	OBJECT-TYPE
	SYNTAX	 CounterBasedGauge64
	MAX-ACCESS read-only
	STATUS obsolete
	DESCRIPTION "Host stats: Session Context Lookups"

	::={liveviewHostStatsSessionContextLookups 3}

liveviewHostStatsSessionContextLookupsLevelTable OBJECT-TYPE
	SYNTAX      SEQUENCE OF LiveviewHostStatsSessionContextLookupsLevelEntry
	MAX-ACCESS  not-accessible
	STATUS      current
	DESCRIPTION
	"Table for liveviewHostStatsSessionContextLookups"
	::={liveviewHostStatsSessionContextLookups 4}

liveviewHostStatsSessionContextLookupsLevelEntry OBJECT-TYPE
	SYNTAX      LiveviewHostStatsSessionContextLookupsLevelEntry
	MAX-ACCESS  not-accessible
	STATUS      current
	DESCRIPTION
	"Table entry for liveviewHostStatsSessionContextLookups"
	INDEX { liveviewHostStatsSessionContextLookupsLevelName }
	::={liveviewHostStatsSessionContextLookupsLevelTable 1}

LiveviewHostStatsSessionContextLookupsLevelEntry ::=
	SEQUENCE {
		liveviewHostStatsSessionContextLookupsLevelName	DisplayString,
		liveviewHostStatsSessionContextLookupsLevelVal	Counter64,
		liveviewHostStatsSessionContextLookupsLevelMom	CounterBasedGauge64,
		liveviewHostStatsSessionContextLookupsLevelMax	CounterBasedGauge64
	}

liveviewHostStatsSessionContextLookupsLevelName OBJECT-TYPE
	SYNTAX      DisplayString
	MAX-ACCESS  not-accessible
	STATUS      current
	DESCRIPTION
	"Table entry display string for liveviewHostStatsSessionContextLookups"
	::={liveviewHostStatsSessionContextLookupsLevelEntry 1}

liveviewHostStatsSessionContextLookupsLevelVal OBJECT-TYPE
	SYNTAX	 Counter64
	MAX-ACCESS  read-only
	STATUS      current
	DESCRIPTION
	"Table entry attribute for liveviewHostStatsSessionContextLookups"
	::={liveviewHostStatsSessionContextLookupsLevelEntry 2}

liveviewHostStatsSessionContextLookupsLevelMom OBJECT-TYPE
	SYNTAX	 CounterBasedGauge64
	MAX-ACCESS  read-only
	STATUS      current
	DESCRIPTION
	"Table entry attribute for liveviewHostStatsSessionContextLookups"
	::={liveviewHostStatsSessionContextLookupsLevelEntry 3}

liveviewHostStatsSessionContextLookupsLevelMax OBJECT-TYPE
	SYNTAX	 CounterBasedGauge64
	MAX-ACCESS  read-only
	STATUS      current
	DESCRIPTION
	"Table entry attribute for liveviewHostStatsSessionContextLookups"
	::={liveviewHostStatsSessionContextLookupsLevelEntry 4}


liveviewHostStatsSessionContextLookupFails	OBJECT IDENTIFIER ::={liveview 46}

liveviewHostStatsSessionContextLookupFailsVal	OBJECT-TYPE
	SYNTAX	 Counter64
	MAX-ACCESS read-only
	STATUS obsolete
	DESCRIPTION "Host stats: Session Context Lookup Failures"

	::={liveviewHostStatsSessionContextLookupFails 1}

liveviewHostStatsSessionContextLookupFailsMom	OBJECT-TYPE
	SYNTAX	 CounterBasedGauge64
	MAX-ACCESS read-only
	STATUS obsolete
	DESCRIPTION "Host stats: Session Context Lookup Failures"

	::={liveviewHostStatsSessionContextLookupFails 2}

liveviewHostStatsSessionContextLookupFailsMax	OBJECT-TYPE
	SYNTAX	 CounterBasedGauge64
	MAX-ACCESS read-only
	STATUS obsolete
	DESCRIPTION "Host stats: Session Context Lookup Failures"

	::={liveviewHostStatsSessionContextLookupFails 3}

liveviewHostStatsSessionContextLookupFailsLevelTable OBJECT-TYPE
	SYNTAX      SEQUENCE OF LiveviewHostStatsSessionContextLookupFailsLevelEntry
	MAX-ACCESS  not-accessible
	STATUS      current
	DESCRIPTION
	"Table for liveviewHostStatsSessionContextLookupFails"
	::={liveviewHostStatsSessionContextLookupFails 4}

liveviewHostStatsSessionContextLookupFailsLevelEntry OBJECT-TYPE
	SYNTAX      LiveviewHostStatsSessionContextLookupFailsLevelEntry
	MAX-ACCESS  not-accessible
	STATUS      current
	DESCRIPTION
	"Table entry for liveviewHostStatsSessionContextLookupFails"
	INDEX { liveviewHostStatsSessionContextLookupFailsLevelName }
	::={liveviewHostStatsSessionContextLookupFailsLevelTable 1}

LiveviewHostStatsSessionContextLookupFailsLevelEntry ::=
	SEQUENCE {
		liveviewHostStatsSessionContextLookupFailsLevelName	DisplayString,
		liveviewHostStatsSessionContextLookupFailsLevelVal	Counter64,
		liveviewHostStatsSessionContextLookupFailsLevelMom	CounterBasedGauge64,
		liveviewHostStatsSessionContextLookupFailsLevelMax	CounterBasedGauge64
	}

liveviewHostStatsSessionContextLookupFailsLevelName OBJECT-TYPE
	SYNTAX      DisplayString
	MAX-ACCESS  not-accessible
	STATUS      current
	DESCRIPTION
	"Table entry display string for liveviewHostStatsSessionContextLookupFails"
	::={liveviewHostStatsSessionContextLookupFailsLevelEntry 1}

liveviewHostStatsSessionContextLookupFailsLevelVal OBJECT-TYPE
	SYNTAX	 Counter64
	MAX-ACCESS  read-only
	STATUS      current
	DESCRIPTION
	"Table entry attribute for liveviewHostStatsSessionContextLookupFails"
	::={liveviewHostStatsSessionContextLookupFailsLevelEntry 2}

liveviewHostStatsSessionContextLookupFailsLevelMom OBJECT-TYPE
	SYNTAX	 CounterBasedGauge64
	MAX-ACCESS  read-only
	STATUS      current
	DESCRIPTION
	"Table entry attribute for liveviewHostStatsSessionContextLookupFails"
	::={liveviewHostStatsSessionContextLookupFailsLevelEntry 3}

liveviewHostStatsSessionContextLookupFailsLevelMax OBJECT-TYPE
	SYNTAX	 CounterBasedGauge64
	MAX-ACCESS  read-only
	STATUS      current
	DESCRIPTION
	"Table entry attribute for liveviewHostStatsSessionContextLookupFails"
	::={liveviewHostStatsSessionContextLookupFailsLevelEntry 4}


liveviewHourlyHosts	OBJECT IDENTIFIER ::={liveview 47}

liveviewHourlyHostsVal	OBJECT-TYPE
	SYNTAX	 CounterBasedGauge64
	MAX-ACCESS read-only
	STATUS current
	DESCRIPTION "Active hosts (hourly)"

	::={liveviewHourlyHosts 1}

liveviewHourlyHostsMax	OBJECT-TYPE
	SYNTAX	 CounterBasedGauge64
	MAX-ACCESS read-only
	STATUS current
	DESCRIPTION "Active hosts (hourly)"

	::={liveviewHourlyHosts 3}

liveviewHourlyHostsLevelTable OBJECT-TYPE
	SYNTAX      SEQUENCE OF LiveviewHourlyHostsLevelEntry
	MAX-ACCESS  not-accessible
	STATUS      current
	DESCRIPTION
	"Table for liveviewHourlyHosts"
	::={liveviewHourlyHosts 4}

liveviewHourlyHostsLevelEntry OBJECT-TYPE
	SYNTAX      LiveviewHourlyHostsLevelEntry
	MAX-ACCESS  not-accessible
	STATUS      current
	DESCRIPTION
	"Table entry for liveviewHourlyHosts"
	INDEX { liveviewHourlyHostsLevelName }
	::={liveviewHourlyHostsLevelTable 1}

LiveviewHourlyHostsLevelEntry ::=
	SEQUENCE {
		liveviewHourlyHostsLevelName	DisplayString,
		liveviewHourlyHostsLevelVal	CounterBasedGauge64,
		liveviewHourlyHostsLevelMax	CounterBasedGauge64
	}

liveviewHourlyHostsLevelName OBJECT-TYPE
	SYNTAX      DisplayString
	MAX-ACCESS  not-accessible
	STATUS      current
	DESCRIPTION
	"Table entry display string for liveviewHourlyHosts"
	::={liveviewHourlyHostsLevelEntry 1}

liveviewHourlyHostsLevelVal OBJECT-TYPE
	SYNTAX	 CounterBasedGauge64
	MAX-ACCESS  read-only
	STATUS      current
	DESCRIPTION
	"Table entry attribute for liveviewHourlyHosts"
	::={liveviewHourlyHostsLevelEntry 2}

liveviewHourlyHostsLevelMax OBJECT-TYPE
	SYNTAX	 CounterBasedGauge64
	MAX-ACCESS  read-only
	STATUS      current
	DESCRIPTION
	"Table entry attribute for liveviewHourlyHosts"
	::={liveviewHourlyHostsLevelEntry 4}


liveviewMaxComplexityAmongActiveViews	OBJECT IDENTIFIER ::={liveview 48}

liveviewMaxComplexityAmongActiveViewsVal	OBJECT-TYPE
	SYNTAX	 CounterBasedGauge64
	MAX-ACCESS read-only
	STATUS current
	DESCRIPTION "Max complexity among active views"

	::={liveviewMaxComplexityAmongActiveViews 1}

liveviewMaxComplexityAmongActiveViewsMax	OBJECT-TYPE
	SYNTAX	 CounterBasedGauge64
	MAX-ACCESS read-only
	STATUS current
	DESCRIPTION "Max complexity among active views"

	::={liveviewMaxComplexityAmongActiveViews 3}

liveviewMaxComplexityAmongActiveViewsLevelTable OBJECT-TYPE
	SYNTAX      SEQUENCE OF LiveviewMaxComplexityAmongActiveViewsLevelEntry
	MAX-ACCESS  not-accessible
	STATUS      current
	DESCRIPTION
	"Table for liveviewMaxComplexityAmongActiveViews"
	::={liveviewMaxComplexityAmongActiveViews 4}

liveviewMaxComplexityAmongActiveViewsLevelEntry OBJECT-TYPE
	SYNTAX      LiveviewMaxComplexityAmongActiveViewsLevelEntry
	MAX-ACCESS  not-accessible
	STATUS      current
	DESCRIPTION
	"Table entry for liveviewMaxComplexityAmongActiveViews"
	INDEX { liveviewMaxComplexityAmongActiveViewsLevelName }
	::={liveviewMaxComplexityAmongActiveViewsLevelTable 1}

LiveviewMaxComplexityAmongActiveViewsLevelEntry ::=
	SEQUENCE {
		liveviewMaxComplexityAmongActiveViewsLevelName	DisplayString,
		liveviewMaxComplexityAmongActiveViewsLevelVal	CounterBasedGauge64,
		liveviewMaxComplexityAmongActiveViewsLevelMax	CounterBasedGauge64
	}

liveviewMaxComplexityAmongActiveViewsLevelName OBJECT-TYPE
	SYNTAX      DisplayString
	MAX-ACCESS  not-accessible
	STATUS      current
	DESCRIPTION
	"Table entry display string for liveviewMaxComplexityAmongActiveViews"
	::={liveviewMaxComplexityAmongActiveViewsLevelEntry 1}

liveviewMaxComplexityAmongActiveViewsLevelVal OBJECT-TYPE
	SYNTAX	 CounterBasedGauge64
	MAX-ACCESS  read-only
	STATUS      current
	DESCRIPTION
	"Table entry attribute for liveviewMaxComplexityAmongActiveViews"
	::={liveviewMaxComplexityAmongActiveViewsLevelEntry 2}

liveviewMaxComplexityAmongActiveViewsLevelMax OBJECT-TYPE
	SYNTAX	 CounterBasedGauge64
	MAX-ACCESS  read-only
	STATUS      current
	DESCRIPTION
	"Table entry attribute for liveviewMaxComplexityAmongActiveViews"
	::={liveviewMaxComplexityAmongActiveViewsLevelEntry 4}


liveviewShapingObjectsAllocs	OBJECT IDENTIFIER ::={liveview 49}

liveviewShapingObjectsAllocsVal	OBJECT-TYPE
	SYNTAX	 CounterBasedGauge64
	MAX-ACCESS read-only
	STATUS current
	DESCRIPTION "ShapingObject array allocations"

	::={liveviewShapingObjectsAllocs 1}

liveviewShapingObjectsAllocsMax	OBJECT-TYPE
	SYNTAX	 CounterBasedGauge64
	MAX-ACCESS read-only
	STATUS current
	DESCRIPTION "ShapingObject array allocations"

	::={liveviewShapingObjectsAllocs 3}

liveviewShapingObjectsAllocsLevelTable OBJECT-TYPE
	SYNTAX      SEQUENCE OF LiveviewShapingObjectsAllocsLevelEntry
	MAX-ACCESS  not-accessible
	STATUS      current
	DESCRIPTION
	"Table for liveviewShapingObjectsAllocs"
	::={liveviewShapingObjectsAllocs 4}

liveviewShapingObjectsAllocsLevelEntry OBJECT-TYPE
	SYNTAX      LiveviewShapingObjectsAllocsLevelEntry
	MAX-ACCESS  not-accessible
	STATUS      current
	DESCRIPTION
	"Table entry for liveviewShapingObjectsAllocs"
	INDEX { liveviewShapingObjectsAllocsLevelName }
	::={liveviewShapingObjectsAllocsLevelTable 1}

LiveviewShapingObjectsAllocsLevelEntry ::=
	SEQUENCE {
		liveviewShapingObjectsAllocsLevelName	DisplayString,
		liveviewShapingObjectsAllocsLevelVal	CounterBasedGauge64,
		liveviewShapingObjectsAllocsLevelMax	CounterBasedGauge64
	}

liveviewShapingObjectsAllocsLevelName OBJECT-TYPE
	SYNTAX      DisplayString
	MAX-ACCESS  not-accessible
	STATUS      current
	DESCRIPTION
	"Table entry display string for liveviewShapingObjectsAllocs"
	::={liveviewShapingObjectsAllocsLevelEntry 1}

liveviewShapingObjectsAllocsLevelVal OBJECT-TYPE
	SYNTAX	 CounterBasedGauge64
	MAX-ACCESS  read-only
	STATUS      current
	DESCRIPTION
	"Table entry attribute for liveviewShapingObjectsAllocs"
	::={liveviewShapingObjectsAllocsLevelEntry 2}

liveviewShapingObjectsAllocsLevelMax OBJECT-TYPE
	SYNTAX	 CounterBasedGauge64
	MAX-ACCESS  read-only
	STATUS      current
	DESCRIPTION
	"Table entry attribute for liveviewShapingObjectsAllocs"
	::={liveviewShapingObjectsAllocsLevelEntry 4}


liveviewShapingObjectsAllocFail	OBJECT IDENTIFIER ::={liveview 50}

liveviewShapingObjectsAllocFailVal	OBJECT-TYPE
	SYNTAX	 Counter64
	MAX-ACCESS read-only
	STATUS current
	DESCRIPTION "ShapingObject array allocation failures"

	::={liveviewShapingObjectsAllocFail 1}

liveviewShapingObjectsAllocFailMom	OBJECT-TYPE
	SYNTAX	 CounterBasedGauge64
	MAX-ACCESS read-only
	STATUS current
	DESCRIPTION "ShapingObject array allocation failures"

	::={liveviewShapingObjectsAllocFail 2}

liveviewShapingObjectsAllocFailMax	OBJECT-TYPE
	SYNTAX	 CounterBasedGauge64
	MAX-ACCESS read-only
	STATUS current
	DESCRIPTION "ShapingObject array allocation failures"

	::={liveviewShapingObjectsAllocFail 3}

liveviewShapingObjectsAllocFailLevelTable OBJECT-TYPE
	SYNTAX      SEQUENCE OF LiveviewShapingObjectsAllocFailLevelEntry
	MAX-ACCESS  not-accessible
	STATUS      current
	DESCRIPTION
	"Table for liveviewShapingObjectsAllocFail"
	::={liveviewShapingObjectsAllocFail 4}

liveviewShapingObjectsAllocFailLevelEntry OBJECT-TYPE
	SYNTAX      LiveviewShapingObjectsAllocFailLevelEntry
	MAX-ACCESS  not-accessible
	STATUS      current
	DESCRIPTION
	"Table entry for liveviewShapingObjectsAllocFail"
	INDEX { liveviewShapingObjectsAllocFailLevelName }
	::={liveviewShapingObjectsAllocFailLevelTable 1}

LiveviewShapingObjectsAllocFailLevelEntry ::=
	SEQUENCE {
		liveviewShapingObjectsAllocFailLevelName	DisplayString,
		liveviewShapingObjectsAllocFailLevelVal	Counter64,
		liveviewShapingObjectsAllocFailLevelMom	CounterBasedGauge64,
		liveviewShapingObjectsAllocFailLevelMax	CounterBasedGauge64
	}

liveviewShapingObjectsAllocFailLevelName OBJECT-TYPE
	SYNTAX      DisplayString
	MAX-ACCESS  not-accessible
	STATUS      current
	DESCRIPTION
	"Table entry display string for liveviewShapingObjectsAllocFail"
	::={liveviewShapingObjectsAllocFailLevelEntry 1}

liveviewShapingObjectsAllocFailLevelVal OBJECT-TYPE
	SYNTAX	 Counter64
	MAX-ACCESS  read-only
	STATUS      current
	DESCRIPTION
	"Table entry attribute for liveviewShapingObjectsAllocFail"
	::={liveviewShapingObjectsAllocFailLevelEntry 2}

liveviewShapingObjectsAllocFailLevelMom OBJECT-TYPE
	SYNTAX	 CounterBasedGauge64
	MAX-ACCESS  read-only
	STATUS      current
	DESCRIPTION
	"Table entry attribute for liveviewShapingObjectsAllocFail"
	::={liveviewShapingObjectsAllocFailLevelEntry 3}

liveviewShapingObjectsAllocFailLevelMax OBJECT-TYPE
	SYNTAX	 CounterBasedGauge64
	MAX-ACCESS  read-only
	STATUS      current
	DESCRIPTION
	"Table entry attribute for liveviewShapingObjectsAllocFail"
	::={liveviewShapingObjectsAllocFailLevelEntry 4}


liveviewShapingObjectsExceedsMax	OBJECT IDENTIFIER ::={liveview 51}

liveviewShapingObjectsExceedsMaxVal	OBJECT-TYPE
	SYNTAX	 Counter64
	MAX-ACCESS read-only
	STATUS current
	DESCRIPTION "Messages with excess ShapingObject"

	::={liveviewShapingObjectsExceedsMax 1}

liveviewShapingObjectsExceedsMaxMom	OBJECT-TYPE
	SYNTAX	 CounterBasedGauge64
	MAX-ACCESS read-only
	STATUS current
	DESCRIPTION "Messages with excess ShapingObject"

	::={liveviewShapingObjectsExceedsMax 2}

liveviewShapingObjectsExceedsMaxMax	OBJECT-TYPE
	SYNTAX	 CounterBasedGauge64
	MAX-ACCESS read-only
	STATUS current
	DESCRIPTION "Messages with excess ShapingObject"

	::={liveviewShapingObjectsExceedsMax 3}

liveviewShapingObjectsExceedsMaxLevelTable OBJECT-TYPE
	SYNTAX      SEQUENCE OF LiveviewShapingObjectsExceedsMaxLevelEntry
	MAX-ACCESS  not-accessible
	STATUS      current
	DESCRIPTION
	"Table for liveviewShapingObjectsExceedsMax"
	::={liveviewShapingObjectsExceedsMax 4}

liveviewShapingObjectsExceedsMaxLevelEntry OBJECT-TYPE
	SYNTAX      LiveviewShapingObjectsExceedsMaxLevelEntry
	MAX-ACCESS  not-accessible
	STATUS      current
	DESCRIPTION
	"Table entry for liveviewShapingObjectsExceedsMax"
	INDEX { liveviewShapingObjectsExceedsMaxLevelName }
	::={liveviewShapingObjectsExceedsMaxLevelTable 1}

LiveviewShapingObjectsExceedsMaxLevelEntry ::=
	SEQUENCE {
		liveviewShapingObjectsExceedsMaxLevelName	DisplayString,
		liveviewShapingObjectsExceedsMaxLevelVal	Counter64,
		liveviewShapingObjectsExceedsMaxLevelMom	CounterBasedGauge64,
		liveviewShapingObjectsExceedsMaxLevelMax	CounterBasedGauge64
	}

liveviewShapingObjectsExceedsMaxLevelName OBJECT-TYPE
	SYNTAX      DisplayString
	MAX-ACCESS  not-accessible
	STATUS      current
	DESCRIPTION
	"Table entry display string for liveviewShapingObjectsExceedsMax"
	::={liveviewShapingObjectsExceedsMaxLevelEntry 1}

liveviewShapingObjectsExceedsMaxLevelVal OBJECT-TYPE
	SYNTAX	 Counter64
	MAX-ACCESS  read-only
	STATUS      current
	DESCRIPTION
	"Table entry attribute for liveviewShapingObjectsExceedsMax"
	::={liveviewShapingObjectsExceedsMaxLevelEntry 2}

liveviewShapingObjectsExceedsMaxLevelMom OBJECT-TYPE
	SYNTAX	 CounterBasedGauge64
	MAX-ACCESS  read-only
	STATUS      current
	DESCRIPTION
	"Table entry attribute for liveviewShapingObjectsExceedsMax"
	::={liveviewShapingObjectsExceedsMaxLevelEntry 3}

liveviewShapingObjectsExceedsMaxLevelMax OBJECT-TYPE
	SYNTAX	 CounterBasedGauge64
	MAX-ACCESS  read-only
	STATUS      current
	DESCRIPTION
	"Table entry attribute for liveviewShapingObjectsExceedsMax"
	::={liveviewShapingObjectsExceedsMaxLevelEntry 4}


liveviewDroppedUpdates	OBJECT IDENTIFIER ::={liveview 52}

liveviewDroppedUpdatesVal	OBJECT-TYPE
	SYNTAX	 CounterBasedGauge64
	MAX-ACCESS read-only
	STATUS current
	DESCRIPTION "Number of liveview updates dropped by PLD"

	::={liveviewDroppedUpdates 1}

liveviewDroppedUpdatesMax	OBJECT-TYPE
	SYNTAX	 CounterBasedGauge64
	MAX-ACCESS read-only
	STATUS current
	DESCRIPTION "Number of liveview updates dropped by PLD"

	::={liveviewDroppedUpdates 3}

liveviewDroppedUpdatesLevelTable OBJECT-TYPE
	SYNTAX      SEQUENCE OF LiveviewDroppedUpdatesLevelEntry
	MAX-ACCESS  not-accessible
	STATUS      current
	DESCRIPTION
	"Table for liveviewDroppedUpdates"
	::={liveviewDroppedUpdates 4}

liveviewDroppedUpdatesLevelEntry OBJECT-TYPE
	SYNTAX      LiveviewDroppedUpdatesLevelEntry
	MAX-ACCESS  not-accessible
	STATUS      current
	DESCRIPTION
	"Table entry for liveviewDroppedUpdates"
	INDEX { liveviewDroppedUpdatesLevelName }
	::={liveviewDroppedUpdatesLevelTable 1}

LiveviewDroppedUpdatesLevelEntry ::=
	SEQUENCE {
		liveviewDroppedUpdatesLevelName	DisplayString,
		liveviewDroppedUpdatesLevelVal	CounterBasedGauge64,
		liveviewDroppedUpdatesLevelMax	CounterBasedGauge64
	}

liveviewDroppedUpdatesLevelName OBJECT-TYPE
	SYNTAX      DisplayString
	MAX-ACCESS  not-accessible
	STATUS      current
	DESCRIPTION
	"Table entry display string for liveviewDroppedUpdates"
	::={liveviewDroppedUpdatesLevelEntry 1}

liveviewDroppedUpdatesLevelVal OBJECT-TYPE
	SYNTAX	 CounterBasedGauge64
	MAX-ACCESS  read-only
	STATUS      current
	DESCRIPTION
	"Table entry attribute for liveviewDroppedUpdates"
	::={liveviewDroppedUpdatesLevelEntry 2}

liveviewDroppedUpdatesLevelMax OBJECT-TYPE
	SYNTAX	 CounterBasedGauge64
	MAX-ACCESS  read-only
	STATUS      current
	DESCRIPTION
	"Table entry attribute for liveviewDroppedUpdates"
	::={liveviewDroppedUpdatesLevelEntry 4}


liveviewClientSendBuf	OBJECT IDENTIFIER ::={liveview 53}

liveviewClientSendBufVal	OBJECT-TYPE
	SYNTAX	 CounterBasedGauge64
	MAX-ACCESS read-only
	STATUS current
	DESCRIPTION "Client send buffer usage"

	::={liveviewClientSendBuf 1}

liveviewClientSendBufMax	OBJECT-TYPE
	SYNTAX	 CounterBasedGauge64
	MAX-ACCESS read-only
	STATUS current
	DESCRIPTION "Client send buffer usage"

	::={liveviewClientSendBuf 3}

liveviewClientSendBufLevelTable OBJECT-TYPE
	SYNTAX      SEQUENCE OF LiveviewClientSendBufLevelEntry
	MAX-ACCESS  not-accessible
	STATUS      current
	DESCRIPTION
	"Table for liveviewClientSendBuf"
	::={liveviewClientSendBuf 4}

liveviewClientSendBufLevelEntry OBJECT-TYPE
	SYNTAX      LiveviewClientSendBufLevelEntry
	MAX-ACCESS  not-accessible
	STATUS      current
	DESCRIPTION
	"Table entry for liveviewClientSendBuf"
	INDEX { liveviewClientSendBufLevelName }
	::={liveviewClientSendBufLevelTable 1}

LiveviewClientSendBufLevelEntry ::=
	SEQUENCE {
		liveviewClientSendBufLevelName	DisplayString,
		liveviewClientSendBufLevelVal	CounterBasedGauge64,
		liveviewClientSendBufLevelMax	CounterBasedGauge64
	}

liveviewClientSendBufLevelName OBJECT-TYPE
	SYNTAX      DisplayString
	MAX-ACCESS  not-accessible
	STATUS      current
	DESCRIPTION
	"Table entry display string for liveviewClientSendBuf"
	::={liveviewClientSendBufLevelEntry 1}

liveviewClientSendBufLevelVal OBJECT-TYPE
	SYNTAX	 CounterBasedGauge64
	MAX-ACCESS  read-only
	STATUS      current
	DESCRIPTION
	"Table entry attribute for liveviewClientSendBuf"
	::={liveviewClientSendBufLevelEntry 2}

liveviewClientSendBufLevelMax OBJECT-TYPE
	SYNTAX	 CounterBasedGauge64
	MAX-ACCESS  read-only
	STATUS      current
	DESCRIPTION
	"Table entry attribute for liveviewClientSendBuf"
	::={liveviewClientSendBufLevelEntry 4}


lb	OBJECT IDENTIFIER ::={sysdiag 135}

lbNumFp	OBJECT IDENTIFIER ::={lb 1}

lbNumFpVal	OBJECT-TYPE
	SYNTAX	 CounterBasedGauge64
	MAX-ACCESS read-only
	STATUS current
	DESCRIPTION "Number of flow processors"

	::={lbNumFp 1}

lbNumFpMax	OBJECT-TYPE
	SYNTAX	 CounterBasedGauge64
	MAX-ACCESS read-only
	STATUS current
	DESCRIPTION "Number of flow processors"

	::={lbNumFp 3}

lbNumFpLevelTable OBJECT-TYPE
	SYNTAX      SEQUENCE OF LbNumFpLevelEntry
	MAX-ACCESS  not-accessible
	STATUS      current
	DESCRIPTION
	"Table for lbNumFp"
	::={lbNumFp 4}

lbNumFpLevelEntry OBJECT-TYPE
	SYNTAX      LbNumFpLevelEntry
	MAX-ACCESS  not-accessible
	STATUS      current
	DESCRIPTION
	"Table entry for lbNumFp"
	INDEX { lbNumFpLevelName }
	::={lbNumFpLevelTable 1}

LbNumFpLevelEntry ::=
	SEQUENCE {
		lbNumFpLevelName	DisplayString,
		lbNumFpLevelVal	CounterBasedGauge64,
		lbNumFpLevelMax	CounterBasedGauge64
	}

lbNumFpLevelName OBJECT-TYPE
	SYNTAX      DisplayString
	MAX-ACCESS  not-accessible
	STATUS      current
	DESCRIPTION
	"Table entry display string for lbNumFp"
	::={lbNumFpLevelEntry 1}

lbNumFpLevelVal OBJECT-TYPE
	SYNTAX	 CounterBasedGauge64
	MAX-ACCESS  read-only
	STATUS      current
	DESCRIPTION
	"Table entry attribute for lbNumFp"
	::={lbNumFpLevelEntry 2}

lbNumFpLevelMax OBJECT-TYPE
	SYNTAX	 CounterBasedGauge64
	MAX-ACCESS  read-only
	STATUS      current
	DESCRIPTION
	"Table entry attribute for lbNumFp"
	::={lbNumFpLevelEntry 4}


lbActiveFp	OBJECT IDENTIFIER ::={lb 2}

lbActiveFpVal	OBJECT-TYPE
	SYNTAX	 CounterBasedGauge64
	MAX-ACCESS read-only
	STATUS current
	DESCRIPTION "Logical flow processors"

	::={lbActiveFp 1}

lbActiveFpMax	OBJECT-TYPE
	SYNTAX	 CounterBasedGauge64
	MAX-ACCESS read-only
	STATUS current
	DESCRIPTION "Logical flow processors"

	::={lbActiveFp 3}

lbActiveFpLevelTable OBJECT-TYPE
	SYNTAX      SEQUENCE OF LbActiveFpLevelEntry
	MAX-ACCESS  not-accessible
	STATUS      current
	DESCRIPTION
	"Table for lbActiveFp"
	::={lbActiveFp 4}

lbActiveFpLevelEntry OBJECT-TYPE
	SYNTAX      LbActiveFpLevelEntry
	MAX-ACCESS  not-accessible
	STATUS      current
	DESCRIPTION
	"Table entry for lbActiveFp"
	INDEX { lbActiveFpLevelName }
	::={lbActiveFpLevelTable 1}

LbActiveFpLevelEntry ::=
	SEQUENCE {
		lbActiveFpLevelName	DisplayString,
		lbActiveFpLevelVal	CounterBasedGauge64,
		lbActiveFpLevelMax	CounterBasedGauge64
	}

lbActiveFpLevelName OBJECT-TYPE
	SYNTAX      DisplayString
	MAX-ACCESS  not-accessible
	STATUS      current
	DESCRIPTION
	"Table entry display string for lbActiveFp"
	::={lbActiveFpLevelEntry 1}

lbActiveFpLevelVal OBJECT-TYPE
	SYNTAX	 CounterBasedGauge64
	MAX-ACCESS  read-only
	STATUS      current
	DESCRIPTION
	"Table entry attribute for lbActiveFp"
	::={lbActiveFpLevelEntry 2}

lbActiveFpLevelMax OBJECT-TYPE
	SYNTAX	 CounterBasedGauge64
	MAX-ACCESS  read-only
	STATUS      current
	DESCRIPTION
	"Table entry attribute for lbActiveFp"
	::={lbActiveFpLevelEntry 4}


lbRunningFp	OBJECT IDENTIFIER ::={lb 3}

lbRunningFpVal	OBJECT-TYPE
	SYNTAX	 Unsigned32
	MAX-ACCESS read-only
	STATUS current
	DESCRIPTION "Online flow processors"

	::={lbRunningFp 1}

lbRunningFpMax	OBJECT-TYPE
	SYNTAX	 Unsigned32
	MAX-ACCESS read-only
	STATUS current
	DESCRIPTION "Online flow processors"

	::={lbRunningFp 3}

lbRunningFpLevelTable OBJECT-TYPE
	SYNTAX      SEQUENCE OF LbRunningFpLevelEntry
	MAX-ACCESS  not-accessible
	STATUS      current
	DESCRIPTION
	"Table for lbRunningFp"
	::={lbRunningFp 4}

lbRunningFpLevelEntry OBJECT-TYPE
	SYNTAX      LbRunningFpLevelEntry
	MAX-ACCESS  not-accessible
	STATUS      current
	DESCRIPTION
	"Table entry for lbRunningFp"
	INDEX { lbRunningFpLevelName }
	::={lbRunningFpLevelTable 1}

LbRunningFpLevelEntry ::=
	SEQUENCE {
		lbRunningFpLevelName	DisplayString,
		lbRunningFpLevelVal	Unsigned32,
		lbRunningFpLevelMax	Unsigned32
	}

lbRunningFpLevelName OBJECT-TYPE
	SYNTAX      DisplayString
	MAX-ACCESS  not-accessible
	STATUS      current
	DESCRIPTION
	"Table entry display string for lbRunningFp"
	::={lbRunningFpLevelEntry 1}

lbRunningFpLevelVal OBJECT-TYPE
	SYNTAX	 Unsigned32
	MAX-ACCESS  read-only
	STATUS      current
	DESCRIPTION
	"Table entry attribute for lbRunningFp"
	::={lbRunningFpLevelEntry 2}

lbRunningFpLevelMax OBJECT-TYPE
	SYNTAX	 Unsigned32
	MAX-ACCESS  read-only
	STATUS      current
	DESCRIPTION
	"Table entry attribute for lbRunningFp"
	::={lbRunningFpLevelEntry 4}


lbRxPktsInt	OBJECT IDENTIFIER ::={lb 4}

lbRxPktsIntVal	OBJECT-TYPE
	SYNTAX	 Counter64
	MAX-ACCESS read-only
	STATUS current
	DESCRIPTION "RX packets internal"

	::={lbRxPktsInt 1}

lbRxPktsIntMom	OBJECT-TYPE
	SYNTAX	 CounterBasedGauge64
	MAX-ACCESS read-only
	STATUS current
	DESCRIPTION "RX packets internal"

	::={lbRxPktsInt 2}

lbRxPktsIntMax	OBJECT-TYPE
	SYNTAX	 CounterBasedGauge64
	MAX-ACCESS read-only
	STATUS current
	DESCRIPTION "RX packets internal"

	::={lbRxPktsInt 3}

lbRxPktsIntLevelTable OBJECT-TYPE
	SYNTAX      SEQUENCE OF LbRxPktsIntLevelEntry
	MAX-ACCESS  not-accessible
	STATUS      current
	DESCRIPTION
	"Table for lbRxPktsInt"
	::={lbRxPktsInt 4}

lbRxPktsIntLevelEntry OBJECT-TYPE
	SYNTAX      LbRxPktsIntLevelEntry
	MAX-ACCESS  not-accessible
	STATUS      current
	DESCRIPTION
	"Table entry for lbRxPktsInt"
	INDEX { lbRxPktsIntLevelName }
	::={lbRxPktsIntLevelTable 1}

LbRxPktsIntLevelEntry ::=
	SEQUENCE {
		lbRxPktsIntLevelName	DisplayString,
		lbRxPktsIntLevelVal	Counter64,
		lbRxPktsIntLevelMom	CounterBasedGauge64,
		lbRxPktsIntLevelMax	CounterBasedGauge64
	}

lbRxPktsIntLevelName OBJECT-TYPE
	SYNTAX      DisplayString
	MAX-ACCESS  not-accessible
	STATUS      current
	DESCRIPTION
	"Table entry display string for lbRxPktsInt"
	::={lbRxPktsIntLevelEntry 1}

lbRxPktsIntLevelVal OBJECT-TYPE
	SYNTAX	 Counter64
	MAX-ACCESS  read-only
	STATUS      current
	DESCRIPTION
	"Table entry attribute for lbRxPktsInt"
	::={lbRxPktsIntLevelEntry 2}

lbRxPktsIntLevelMom OBJECT-TYPE
	SYNTAX	 CounterBasedGauge64
	MAX-ACCESS  read-only
	STATUS      current
	DESCRIPTION
	"Table entry attribute for lbRxPktsInt"
	::={lbRxPktsIntLevelEntry 3}

lbRxPktsIntLevelMax OBJECT-TYPE
	SYNTAX	 CounterBasedGauge64
	MAX-ACCESS  read-only
	STATUS      current
	DESCRIPTION
	"Table entry attribute for lbRxPktsInt"
	::={lbRxPktsIntLevelEntry 4}


lbRxPktsExt	OBJECT IDENTIFIER ::={lb 5}

lbRxPktsExtVal	OBJECT-TYPE
	SYNTAX	 Counter64
	MAX-ACCESS read-only
	STATUS current
	DESCRIPTION "RX packets external"

	::={lbRxPktsExt 1}

lbRxPktsExtMom	OBJECT-TYPE
	SYNTAX	 CounterBasedGauge64
	MAX-ACCESS read-only
	STATUS current
	DESCRIPTION "RX packets external"

	::={lbRxPktsExt 2}

lbRxPktsExtMax	OBJECT-TYPE
	SYNTAX	 CounterBasedGauge64
	MAX-ACCESS read-only
	STATUS current
	DESCRIPTION "RX packets external"

	::={lbRxPktsExt 3}

lbRxPktsExtLevelTable OBJECT-TYPE
	SYNTAX      SEQUENCE OF LbRxPktsExtLevelEntry
	MAX-ACCESS  not-accessible
	STATUS      current
	DESCRIPTION
	"Table for lbRxPktsExt"
	::={lbRxPktsExt 4}

lbRxPktsExtLevelEntry OBJECT-TYPE
	SYNTAX      LbRxPktsExtLevelEntry
	MAX-ACCESS  not-accessible
	STATUS      current
	DESCRIPTION
	"Table entry for lbRxPktsExt"
	INDEX { lbRxPktsExtLevelName }
	::={lbRxPktsExtLevelTable 1}

LbRxPktsExtLevelEntry ::=
	SEQUENCE {
		lbRxPktsExtLevelName	DisplayString,
		lbRxPktsExtLevelVal	Counter64,
		lbRxPktsExtLevelMom	CounterBasedGauge64,
		lbRxPktsExtLevelMax	CounterBasedGauge64
	}

lbRxPktsExtLevelName OBJECT-TYPE
	SYNTAX      DisplayString
	MAX-ACCESS  not-accessible
	STATUS      current
	DESCRIPTION
	"Table entry display string for lbRxPktsExt"
	::={lbRxPktsExtLevelEntry 1}

lbRxPktsExtLevelVal OBJECT-TYPE
	SYNTAX	 Counter64
	MAX-ACCESS  read-only
	STATUS      current
	DESCRIPTION
	"Table entry attribute for lbRxPktsExt"
	::={lbRxPktsExtLevelEntry 2}

lbRxPktsExtLevelMom OBJECT-TYPE
	SYNTAX	 CounterBasedGauge64
	MAX-ACCESS  read-only
	STATUS      current
	DESCRIPTION
	"Table entry attribute for lbRxPktsExt"
	::={lbRxPktsExtLevelEntry 3}

lbRxPktsExtLevelMax OBJECT-TYPE
	SYNTAX	 CounterBasedGauge64
	MAX-ACCESS  read-only
	STATUS      current
	DESCRIPTION
	"Table entry attribute for lbRxPktsExt"
	::={lbRxPktsExtLevelEntry 4}


lbRxBytesInt	OBJECT IDENTIFIER ::={lb 6}

lbRxBytesIntVal	OBJECT-TYPE
	SYNTAX	 Counter64
	MAX-ACCESS read-only
	STATUS current
	DESCRIPTION "RX bytes internal"

	::={lbRxBytesInt 1}

lbRxBytesIntMom	OBJECT-TYPE
	SYNTAX	 CounterBasedGauge64
	MAX-ACCESS read-only
	STATUS current
	DESCRIPTION "RX bytes internal"

	::={lbRxBytesInt 2}

lbRxBytesIntMax	OBJECT-TYPE
	SYNTAX	 CounterBasedGauge64
	MAX-ACCESS read-only
	STATUS current
	DESCRIPTION "RX bytes internal"

	::={lbRxBytesInt 3}

lbRxBytesIntLevelTable OBJECT-TYPE
	SYNTAX      SEQUENCE OF LbRxBytesIntLevelEntry
	MAX-ACCESS  not-accessible
	STATUS      current
	DESCRIPTION
	"Table for lbRxBytesInt"
	::={lbRxBytesInt 4}

lbRxBytesIntLevelEntry OBJECT-TYPE
	SYNTAX      LbRxBytesIntLevelEntry
	MAX-ACCESS  not-accessible
	STATUS      current
	DESCRIPTION
	"Table entry for lbRxBytesInt"
	INDEX { lbRxBytesIntLevelName }
	::={lbRxBytesIntLevelTable 1}

LbRxBytesIntLevelEntry ::=
	SEQUENCE {
		lbRxBytesIntLevelName	DisplayString,
		lbRxBytesIntLevelVal	Counter64,
		lbRxBytesIntLevelMom	CounterBasedGauge64,
		lbRxBytesIntLevelMax	CounterBasedGauge64
	}

lbRxBytesIntLevelName OBJECT-TYPE
	SYNTAX      DisplayString
	MAX-ACCESS  not-accessible
	STATUS      current
	DESCRIPTION
	"Table entry display string for lbRxBytesInt"
	::={lbRxBytesIntLevelEntry 1}

lbRxBytesIntLevelVal OBJECT-TYPE
	SYNTAX	 Counter64
	MAX-ACCESS  read-only
	STATUS      current
	DESCRIPTION
	"Table entry attribute for lbRxBytesInt"
	::={lbRxBytesIntLevelEntry 2}

lbRxBytesIntLevelMom OBJECT-TYPE
	SYNTAX	 CounterBasedGauge64
	MAX-ACCESS  read-only
	STATUS      current
	DESCRIPTION
	"Table entry attribute for lbRxBytesInt"
	::={lbRxBytesIntLevelEntry 3}

lbRxBytesIntLevelMax OBJECT-TYPE
	SYNTAX	 CounterBasedGauge64
	MAX-ACCESS  read-only
	STATUS      current
	DESCRIPTION
	"Table entry attribute for lbRxBytesInt"
	::={lbRxBytesIntLevelEntry 4}


lbRxBytesExt	OBJECT IDENTIFIER ::={lb 7}

lbRxBytesExtVal	OBJECT-TYPE
	SYNTAX	 Counter64
	MAX-ACCESS read-only
	STATUS current
	DESCRIPTION "RX bytes external"

	::={lbRxBytesExt 1}

lbRxBytesExtMom	OBJECT-TYPE
	SYNTAX	 CounterBasedGauge64
	MAX-ACCESS read-only
	STATUS current
	DESCRIPTION "RX bytes external"

	::={lbRxBytesExt 2}

lbRxBytesExtMax	OBJECT-TYPE
	SYNTAX	 CounterBasedGauge64
	MAX-ACCESS read-only
	STATUS current
	DESCRIPTION "RX bytes external"

	::={lbRxBytesExt 3}

lbRxBytesExtLevelTable OBJECT-TYPE
	SYNTAX      SEQUENCE OF LbRxBytesExtLevelEntry
	MAX-ACCESS  not-accessible
	STATUS      current
	DESCRIPTION
	"Table for lbRxBytesExt"
	::={lbRxBytesExt 4}

lbRxBytesExtLevelEntry OBJECT-TYPE
	SYNTAX      LbRxBytesExtLevelEntry
	MAX-ACCESS  not-accessible
	STATUS      current
	DESCRIPTION
	"Table entry for lbRxBytesExt"
	INDEX { lbRxBytesExtLevelName }
	::={lbRxBytesExtLevelTable 1}

LbRxBytesExtLevelEntry ::=
	SEQUENCE {
		lbRxBytesExtLevelName	DisplayString,
		lbRxBytesExtLevelVal	Counter64,
		lbRxBytesExtLevelMom	CounterBasedGauge64,
		lbRxBytesExtLevelMax	CounterBasedGauge64
	}

lbRxBytesExtLevelName OBJECT-TYPE
	SYNTAX      DisplayString
	MAX-ACCESS  not-accessible
	STATUS      current
	DESCRIPTION
	"Table entry display string for lbRxBytesExt"
	::={lbRxBytesExtLevelEntry 1}

lbRxBytesExtLevelVal OBJECT-TYPE
	SYNTAX	 Counter64
	MAX-ACCESS  read-only
	STATUS      current
	DESCRIPTION
	"Table entry attribute for lbRxBytesExt"
	::={lbRxBytesExtLevelEntry 2}

lbRxBytesExtLevelMom OBJECT-TYPE
	SYNTAX	 CounterBasedGauge64
	MAX-ACCESS  read-only
	STATUS      current
	DESCRIPTION
	"Table entry attribute for lbRxBytesExt"
	::={lbRxBytesExtLevelEntry 3}

lbRxBytesExtLevelMax OBJECT-TYPE
	SYNTAX	 CounterBasedGauge64
	MAX-ACCESS  read-only
	STATUS      current
	DESCRIPTION
	"Table entry attribute for lbRxBytesExt"
	::={lbRxBytesExtLevelEntry 4}


lbRxErrorsInt	OBJECT IDENTIFIER ::={lb 8}

lbRxErrorsIntVal	OBJECT-TYPE
	SYNTAX	 Counter64
	MAX-ACCESS read-only
	STATUS current
	DESCRIPTION "RX errors internal"

	::={lbRxErrorsInt 1}

lbRxErrorsIntMom	OBJECT-TYPE
	SYNTAX	 CounterBasedGauge64
	MAX-ACCESS read-only
	STATUS current
	DESCRIPTION "RX errors internal"

	::={lbRxErrorsInt 2}

lbRxErrorsIntMax	OBJECT-TYPE
	SYNTAX	 CounterBasedGauge64
	MAX-ACCESS read-only
	STATUS current
	DESCRIPTION "RX errors internal"

	::={lbRxErrorsInt 3}

lbRxErrorsIntLevelTable OBJECT-TYPE
	SYNTAX      SEQUENCE OF LbRxErrorsIntLevelEntry
	MAX-ACCESS  not-accessible
	STATUS      current
	DESCRIPTION
	"Table for lbRxErrorsInt"
	::={lbRxErrorsInt 4}

lbRxErrorsIntLevelEntry OBJECT-TYPE
	SYNTAX      LbRxErrorsIntLevelEntry
	MAX-ACCESS  not-accessible
	STATUS      current
	DESCRIPTION
	"Table entry for lbRxErrorsInt"
	INDEX { lbRxErrorsIntLevelName }
	::={lbRxErrorsIntLevelTable 1}

LbRxErrorsIntLevelEntry ::=
	SEQUENCE {
		lbRxErrorsIntLevelName	DisplayString,
		lbRxErrorsIntLevelVal	Counter64,
		lbRxErrorsIntLevelMom	CounterBasedGauge64,
		lbRxErrorsIntLevelMax	CounterBasedGauge64
	}

lbRxErrorsIntLevelName OBJECT-TYPE
	SYNTAX      DisplayString
	MAX-ACCESS  not-accessible
	STATUS      current
	DESCRIPTION
	"Table entry display string for lbRxErrorsInt"
	::={lbRxErrorsIntLevelEntry 1}

lbRxErrorsIntLevelVal OBJECT-TYPE
	SYNTAX	 Counter64
	MAX-ACCESS  read-only
	STATUS      current
	DESCRIPTION
	"Table entry attribute for lbRxErrorsInt"
	::={lbRxErrorsIntLevelEntry 2}

lbRxErrorsIntLevelMom OBJECT-TYPE
	SYNTAX	 CounterBasedGauge64
	MAX-ACCESS  read-only
	STATUS      current
	DESCRIPTION
	"Table entry attribute for lbRxErrorsInt"
	::={lbRxErrorsIntLevelEntry 3}

lbRxErrorsIntLevelMax OBJECT-TYPE
	SYNTAX	 CounterBasedGauge64
	MAX-ACCESS  read-only
	STATUS      current
	DESCRIPTION
	"Table entry attribute for lbRxErrorsInt"
	::={lbRxErrorsIntLevelEntry 4}


lbRxErrorsExt	OBJECT IDENTIFIER ::={lb 9}

lbRxErrorsExtVal	OBJECT-TYPE
	SYNTAX	 Counter64
	MAX-ACCESS read-only
	STATUS current
	DESCRIPTION "RX errors external"

	::={lbRxErrorsExt 1}

lbRxErrorsExtMom	OBJECT-TYPE
	SYNTAX	 CounterBasedGauge64
	MAX-ACCESS read-only
	STATUS current
	DESCRIPTION "RX errors external"

	::={lbRxErrorsExt 2}

lbRxErrorsExtMax	OBJECT-TYPE
	SYNTAX	 CounterBasedGauge64
	MAX-ACCESS read-only
	STATUS current
	DESCRIPTION "RX errors external"

	::={lbRxErrorsExt 3}

lbRxErrorsExtLevelTable OBJECT-TYPE
	SYNTAX      SEQUENCE OF LbRxErrorsExtLevelEntry
	MAX-ACCESS  not-accessible
	STATUS      current
	DESCRIPTION
	"Table for lbRxErrorsExt"
	::={lbRxErrorsExt 4}

lbRxErrorsExtLevelEntry OBJECT-TYPE
	SYNTAX      LbRxErrorsExtLevelEntry
	MAX-ACCESS  not-accessible
	STATUS      current
	DESCRIPTION
	"Table entry for lbRxErrorsExt"
	INDEX { lbRxErrorsExtLevelName }
	::={lbRxErrorsExtLevelTable 1}

LbRxErrorsExtLevelEntry ::=
	SEQUENCE {
		lbRxErrorsExtLevelName	DisplayString,
		lbRxErrorsExtLevelVal	Counter64,
		lbRxErrorsExtLevelMom	CounterBasedGauge64,
		lbRxErrorsExtLevelMax	CounterBasedGauge64
	}

lbRxErrorsExtLevelName OBJECT-TYPE
	SYNTAX      DisplayString
	MAX-ACCESS  not-accessible
	STATUS      current
	DESCRIPTION
	"Table entry display string for lbRxErrorsExt"
	::={lbRxErrorsExtLevelEntry 1}

lbRxErrorsExtLevelVal OBJECT-TYPE
	SYNTAX	 Counter64
	MAX-ACCESS  read-only
	STATUS      current
	DESCRIPTION
	"Table entry attribute for lbRxErrorsExt"
	::={lbRxErrorsExtLevelEntry 2}

lbRxErrorsExtLevelMom OBJECT-TYPE
	SYNTAX	 CounterBasedGauge64
	MAX-ACCESS  read-only
	STATUS      current
	DESCRIPTION
	"Table entry attribute for lbRxErrorsExt"
	::={lbRxErrorsExtLevelEntry 3}

lbRxErrorsExtLevelMax OBJECT-TYPE
	SYNTAX	 CounterBasedGauge64
	MAX-ACCESS  read-only
	STATUS      current
	DESCRIPTION
	"Table entry attribute for lbRxErrorsExt"
	::={lbRxErrorsExtLevelEntry 4}


lbTxDirectInt	OBJECT IDENTIFIER ::={lb 10}

lbTxDirectIntVal	OBJECT-TYPE
	SYNTAX	 Counter64
	MAX-ACCESS read-only
	STATUS current
	DESCRIPTION "TX direct internal"

	::={lbTxDirectInt 1}

lbTxDirectIntMom	OBJECT-TYPE
	SYNTAX	 CounterBasedGauge64
	MAX-ACCESS read-only
	STATUS current
	DESCRIPTION "TX direct internal"

	::={lbTxDirectInt 2}

lbTxDirectIntMax	OBJECT-TYPE
	SYNTAX	 CounterBasedGauge64
	MAX-ACCESS read-only
	STATUS current
	DESCRIPTION "TX direct internal"

	::={lbTxDirectInt 3}

lbTxDirectIntLevelTable OBJECT-TYPE
	SYNTAX      SEQUENCE OF LbTxDirectIntLevelEntry
	MAX-ACCESS  not-accessible
	STATUS      current
	DESCRIPTION
	"Table for lbTxDirectInt"
	::={lbTxDirectInt 4}

lbTxDirectIntLevelEntry OBJECT-TYPE
	SYNTAX      LbTxDirectIntLevelEntry
	MAX-ACCESS  not-accessible
	STATUS      current
	DESCRIPTION
	"Table entry for lbTxDirectInt"
	INDEX { lbTxDirectIntLevelName }
	::={lbTxDirectIntLevelTable 1}

LbTxDirectIntLevelEntry ::=
	SEQUENCE {
		lbTxDirectIntLevelName	DisplayString,
		lbTxDirectIntLevelVal	Counter64,
		lbTxDirectIntLevelMom	CounterBasedGauge64,
		lbTxDirectIntLevelMax	CounterBasedGauge64
	}

lbTxDirectIntLevelName OBJECT-TYPE
	SYNTAX      DisplayString
	MAX-ACCESS  not-accessible
	STATUS      current
	DESCRIPTION
	"Table entry display string for lbTxDirectInt"
	::={lbTxDirectIntLevelEntry 1}

lbTxDirectIntLevelVal OBJECT-TYPE
	SYNTAX	 Counter64
	MAX-ACCESS  read-only
	STATUS      current
	DESCRIPTION
	"Table entry attribute for lbTxDirectInt"
	::={lbTxDirectIntLevelEntry 2}

lbTxDirectIntLevelMom OBJECT-TYPE
	SYNTAX	 CounterBasedGauge64
	MAX-ACCESS  read-only
	STATUS      current
	DESCRIPTION
	"Table entry attribute for lbTxDirectInt"
	::={lbTxDirectIntLevelEntry 3}

lbTxDirectIntLevelMax OBJECT-TYPE
	SYNTAX	 CounterBasedGauge64
	MAX-ACCESS  read-only
	STATUS      current
	DESCRIPTION
	"Table entry attribute for lbTxDirectInt"
	::={lbTxDirectIntLevelEntry 4}


lbTxDirectExt	OBJECT IDENTIFIER ::={lb 11}

lbTxDirectExtVal	OBJECT-TYPE
	SYNTAX	 Counter64
	MAX-ACCESS read-only
	STATUS current
	DESCRIPTION "TX direct external"

	::={lbTxDirectExt 1}

lbTxDirectExtMom	OBJECT-TYPE
	SYNTAX	 CounterBasedGauge64
	MAX-ACCESS read-only
	STATUS current
	DESCRIPTION "TX direct external"

	::={lbTxDirectExt 2}

lbTxDirectExtMax	OBJECT-TYPE
	SYNTAX	 CounterBasedGauge64
	MAX-ACCESS read-only
	STATUS current
	DESCRIPTION "TX direct external"

	::={lbTxDirectExt 3}

lbTxDirectExtLevelTable OBJECT-TYPE
	SYNTAX      SEQUENCE OF LbTxDirectExtLevelEntry
	MAX-ACCESS  not-accessible
	STATUS      current
	DESCRIPTION
	"Table for lbTxDirectExt"
	::={lbTxDirectExt 4}

lbTxDirectExtLevelEntry OBJECT-TYPE
	SYNTAX      LbTxDirectExtLevelEntry
	MAX-ACCESS  not-accessible
	STATUS      current
	DESCRIPTION
	"Table entry for lbTxDirectExt"
	INDEX { lbTxDirectExtLevelName }
	::={lbTxDirectExtLevelTable 1}

LbTxDirectExtLevelEntry ::=
	SEQUENCE {
		lbTxDirectExtLevelName	DisplayString,
		lbTxDirectExtLevelVal	Counter64,
		lbTxDirectExtLevelMom	CounterBasedGauge64,
		lbTxDirectExtLevelMax	CounterBasedGauge64
	}

lbTxDirectExtLevelName OBJECT-TYPE
	SYNTAX      DisplayString
	MAX-ACCESS  not-accessible
	STATUS      current
	DESCRIPTION
	"Table entry display string for lbTxDirectExt"
	::={lbTxDirectExtLevelEntry 1}

lbTxDirectExtLevelVal OBJECT-TYPE
	SYNTAX	 Counter64
	MAX-ACCESS  read-only
	STATUS      current
	DESCRIPTION
	"Table entry attribute for lbTxDirectExt"
	::={lbTxDirectExtLevelEntry 2}

lbTxDirectExtLevelMom OBJECT-TYPE
	SYNTAX	 CounterBasedGauge64
	MAX-ACCESS  read-only
	STATUS      current
	DESCRIPTION
	"Table entry attribute for lbTxDirectExt"
	::={lbTxDirectExtLevelEntry 3}

lbTxDirectExtLevelMax OBJECT-TYPE
	SYNTAX	 CounterBasedGauge64
	MAX-ACCESS  read-only
	STATUS      current
	DESCRIPTION
	"Table entry attribute for lbTxDirectExt"
	::={lbTxDirectExtLevelEntry 4}


lbTxDropsInt	OBJECT IDENTIFIER ::={lb 12}

lbTxDropsIntVal	OBJECT-TYPE
	SYNTAX	 Counter64
	MAX-ACCESS read-only
	STATUS current
	DESCRIPTION "TX drops internal"

	::={lbTxDropsInt 1}

lbTxDropsIntMom	OBJECT-TYPE
	SYNTAX	 CounterBasedGauge64
	MAX-ACCESS read-only
	STATUS current
	DESCRIPTION "TX drops internal"

	::={lbTxDropsInt 2}

lbTxDropsIntMax	OBJECT-TYPE
	SYNTAX	 CounterBasedGauge64
	MAX-ACCESS read-only
	STATUS current
	DESCRIPTION "TX drops internal"

	::={lbTxDropsInt 3}

lbTxDropsIntLevelTable OBJECT-TYPE
	SYNTAX      SEQUENCE OF LbTxDropsIntLevelEntry
	MAX-ACCESS  not-accessible
	STATUS      current
	DESCRIPTION
	"Table for lbTxDropsInt"
	::={lbTxDropsInt 4}

lbTxDropsIntLevelEntry OBJECT-TYPE
	SYNTAX      LbTxDropsIntLevelEntry
	MAX-ACCESS  not-accessible
	STATUS      current
	DESCRIPTION
	"Table entry for lbTxDropsInt"
	INDEX { lbTxDropsIntLevelName }
	::={lbTxDropsIntLevelTable 1}

LbTxDropsIntLevelEntry ::=
	SEQUENCE {
		lbTxDropsIntLevelName	DisplayString,
		lbTxDropsIntLevelVal	Counter64,
		lbTxDropsIntLevelMom	CounterBasedGauge64,
		lbTxDropsIntLevelMax	CounterBasedGauge64
	}

lbTxDropsIntLevelName OBJECT-TYPE
	SYNTAX      DisplayString
	MAX-ACCESS  not-accessible
	STATUS      current
	DESCRIPTION
	"Table entry display string for lbTxDropsInt"
	::={lbTxDropsIntLevelEntry 1}

lbTxDropsIntLevelVal OBJECT-TYPE
	SYNTAX	 Counter64
	MAX-ACCESS  read-only
	STATUS      current
	DESCRIPTION
	"Table entry attribute for lbTxDropsInt"
	::={lbTxDropsIntLevelEntry 2}

lbTxDropsIntLevelMom OBJECT-TYPE
	SYNTAX	 CounterBasedGauge64
	MAX-ACCESS  read-only
	STATUS      current
	DESCRIPTION
	"Table entry attribute for lbTxDropsInt"
	::={lbTxDropsIntLevelEntry 3}

lbTxDropsIntLevelMax OBJECT-TYPE
	SYNTAX	 CounterBasedGauge64
	MAX-ACCESS  read-only
	STATUS      current
	DESCRIPTION
	"Table entry attribute for lbTxDropsInt"
	::={lbTxDropsIntLevelEntry 4}


lbTxDropsExt	OBJECT IDENTIFIER ::={lb 13}

lbTxDropsExtVal	OBJECT-TYPE
	SYNTAX	 Counter64
	MAX-ACCESS read-only
	STATUS current
	DESCRIPTION "TX drops external"

	::={lbTxDropsExt 1}

lbTxDropsExtMom	OBJECT-TYPE
	SYNTAX	 CounterBasedGauge64
	MAX-ACCESS read-only
	STATUS current
	DESCRIPTION "TX drops external"

	::={lbTxDropsExt 2}

lbTxDropsExtMax	OBJECT-TYPE
	SYNTAX	 CounterBasedGauge64
	MAX-ACCESS read-only
	STATUS current
	DESCRIPTION "TX drops external"

	::={lbTxDropsExt 3}

lbTxDropsExtLevelTable OBJECT-TYPE
	SYNTAX      SEQUENCE OF LbTxDropsExtLevelEntry
	MAX-ACCESS  not-accessible
	STATUS      current
	DESCRIPTION
	"Table for lbTxDropsExt"
	::={lbTxDropsExt 4}

lbTxDropsExtLevelEntry OBJECT-TYPE
	SYNTAX      LbTxDropsExtLevelEntry
	MAX-ACCESS  not-accessible
	STATUS      current
	DESCRIPTION
	"Table entry for lbTxDropsExt"
	INDEX { lbTxDropsExtLevelName }
	::={lbTxDropsExtLevelTable 1}

LbTxDropsExtLevelEntry ::=
	SEQUENCE {
		lbTxDropsExtLevelName	DisplayString,
		lbTxDropsExtLevelVal	Counter64,
		lbTxDropsExtLevelMom	CounterBasedGauge64,
		lbTxDropsExtLevelMax	CounterBasedGauge64
	}

lbTxDropsExtLevelName OBJECT-TYPE
	SYNTAX      DisplayString
	MAX-ACCESS  not-accessible
	STATUS      current
	DESCRIPTION
	"Table entry display string for lbTxDropsExt"
	::={lbTxDropsExtLevelEntry 1}

lbTxDropsExtLevelVal OBJECT-TYPE
	SYNTAX	 Counter64
	MAX-ACCESS  read-only
	STATUS      current
	DESCRIPTION
	"Table entry attribute for lbTxDropsExt"
	::={lbTxDropsExtLevelEntry 2}

lbTxDropsExtLevelMom OBJECT-TYPE
	SYNTAX	 CounterBasedGauge64
	MAX-ACCESS  read-only
	STATUS      current
	DESCRIPTION
	"Table entry attribute for lbTxDropsExt"
	::={lbTxDropsExtLevelEntry 3}

lbTxDropsExtLevelMax OBJECT-TYPE
	SYNTAX	 CounterBasedGauge64
	MAX-ACCESS  read-only
	STATUS      current
	DESCRIPTION
	"Table entry attribute for lbTxDropsExt"
	::={lbTxDropsExtLevelEntry 4}


lbRxFsInvalidVer	OBJECT IDENTIFIER ::={lb 14}

lbRxFsInvalidVerVal	OBJECT-TYPE
	SYNTAX	 Counter64
	MAX-ACCESS read-only
	STATUS current
	DESCRIPTION "Incompatible flowsync packets"

	::={lbRxFsInvalidVer 1}

lbRxFsInvalidVerMom	OBJECT-TYPE
	SYNTAX	 CounterBasedGauge64
	MAX-ACCESS read-only
	STATUS current
	DESCRIPTION "Incompatible flowsync packets"

	::={lbRxFsInvalidVer 2}

lbRxFsInvalidVerMax	OBJECT-TYPE
	SYNTAX	 CounterBasedGauge64
	MAX-ACCESS read-only
	STATUS current
	DESCRIPTION "Incompatible flowsync packets"

	::={lbRxFsInvalidVer 3}

lbRxFsInvalidVerLevelTable OBJECT-TYPE
	SYNTAX      SEQUENCE OF LbRxFsInvalidVerLevelEntry
	MAX-ACCESS  not-accessible
	STATUS      current
	DESCRIPTION
	"Table for lbRxFsInvalidVer"
	::={lbRxFsInvalidVer 4}

lbRxFsInvalidVerLevelEntry OBJECT-TYPE
	SYNTAX      LbRxFsInvalidVerLevelEntry
	MAX-ACCESS  not-accessible
	STATUS      current
	DESCRIPTION
	"Table entry for lbRxFsInvalidVer"
	INDEX { lbRxFsInvalidVerLevelName }
	::={lbRxFsInvalidVerLevelTable 1}

LbRxFsInvalidVerLevelEntry ::=
	SEQUENCE {
		lbRxFsInvalidVerLevelName	DisplayString,
		lbRxFsInvalidVerLevelVal	Counter64,
		lbRxFsInvalidVerLevelMom	CounterBasedGauge64,
		lbRxFsInvalidVerLevelMax	CounterBasedGauge64
	}

lbRxFsInvalidVerLevelName OBJECT-TYPE
	SYNTAX      DisplayString
	MAX-ACCESS  not-accessible
	STATUS      current
	DESCRIPTION
	"Table entry display string for lbRxFsInvalidVer"
	::={lbRxFsInvalidVerLevelEntry 1}

lbRxFsInvalidVerLevelVal OBJECT-TYPE
	SYNTAX	 Counter64
	MAX-ACCESS  read-only
	STATUS      current
	DESCRIPTION
	"Table entry attribute for lbRxFsInvalidVer"
	::={lbRxFsInvalidVerLevelEntry 2}

lbRxFsInvalidVerLevelMom OBJECT-TYPE
	SYNTAX	 CounterBasedGauge64
	MAX-ACCESS  read-only
	STATUS      current
	DESCRIPTION
	"Table entry attribute for lbRxFsInvalidVer"
	::={lbRxFsInvalidVerLevelEntry 3}

lbRxFsInvalidVerLevelMax OBJECT-TYPE
	SYNTAX	 CounterBasedGauge64
	MAX-ACCESS  read-only
	STATUS      current
	DESCRIPTION
	"Table entry attribute for lbRxFsInvalidVer"
	::={lbRxFsInvalidVerLevelEntry 4}


lbShuntPktIpv4AddrInt	OBJECT IDENTIFIER ::={lb 15}

lbShuntPktIpv4AddrIntVal	OBJECT-TYPE
	SYNTAX	 Counter64
	MAX-ACCESS read-only
	STATUS current
	DESCRIPTION "Shunt packets internal (IPv4 address)"

	::={lbShuntPktIpv4AddrInt 1}

lbShuntPktIpv4AddrIntMom	OBJECT-TYPE
	SYNTAX	 CounterBasedGauge64
	MAX-ACCESS read-only
	STATUS current
	DESCRIPTION "Shunt packets internal (IPv4 address)"

	::={lbShuntPktIpv4AddrInt 2}

lbShuntPktIpv4AddrIntMax	OBJECT-TYPE
	SYNTAX	 CounterBasedGauge64
	MAX-ACCESS read-only
	STATUS current
	DESCRIPTION "Shunt packets internal (IPv4 address)"

	::={lbShuntPktIpv4AddrInt 3}

lbShuntPktIpv4AddrIntLevelTable OBJECT-TYPE
	SYNTAX      SEQUENCE OF LbShuntPktIpv4AddrIntLevelEntry
	MAX-ACCESS  not-accessible
	STATUS      current
	DESCRIPTION
	"Table for lbShuntPktIpv4AddrInt"
	::={lbShuntPktIpv4AddrInt 4}

lbShuntPktIpv4AddrIntLevelEntry OBJECT-TYPE
	SYNTAX      LbShuntPktIpv4AddrIntLevelEntry
	MAX-ACCESS  not-accessible
	STATUS      current
	DESCRIPTION
	"Table entry for lbShuntPktIpv4AddrInt"
	INDEX { lbShuntPktIpv4AddrIntLevelName }
	::={lbShuntPktIpv4AddrIntLevelTable 1}

LbShuntPktIpv4AddrIntLevelEntry ::=
	SEQUENCE {
		lbShuntPktIpv4AddrIntLevelName	DisplayString,
		lbShuntPktIpv4AddrIntLevelVal	Counter64,
		lbShuntPktIpv4AddrIntLevelMom	CounterBasedGauge64,
		lbShuntPktIpv4AddrIntLevelMax	CounterBasedGauge64
	}

lbShuntPktIpv4AddrIntLevelName OBJECT-TYPE
	SYNTAX      DisplayString
	MAX-ACCESS  not-accessible
	STATUS      current
	DESCRIPTION
	"Table entry display string for lbShuntPktIpv4AddrInt"
	::={lbShuntPktIpv4AddrIntLevelEntry 1}

lbShuntPktIpv4AddrIntLevelVal OBJECT-TYPE
	SYNTAX	 Counter64
	MAX-ACCESS  read-only
	STATUS      current
	DESCRIPTION
	"Table entry attribute for lbShuntPktIpv4AddrInt"
	::={lbShuntPktIpv4AddrIntLevelEntry 2}

lbShuntPktIpv4AddrIntLevelMom OBJECT-TYPE
	SYNTAX	 CounterBasedGauge64
	MAX-ACCESS  read-only
	STATUS      current
	DESCRIPTION
	"Table entry attribute for lbShuntPktIpv4AddrInt"
	::={lbShuntPktIpv4AddrIntLevelEntry 3}

lbShuntPktIpv4AddrIntLevelMax OBJECT-TYPE
	SYNTAX	 CounterBasedGauge64
	MAX-ACCESS  read-only
	STATUS      current
	DESCRIPTION
	"Table entry attribute for lbShuntPktIpv4AddrInt"
	::={lbShuntPktIpv4AddrIntLevelEntry 4}


lbShuntPktIpv4AddrExt	OBJECT IDENTIFIER ::={lb 16}

lbShuntPktIpv4AddrExtVal	OBJECT-TYPE
	SYNTAX	 Counter64
	MAX-ACCESS read-only
	STATUS current
	DESCRIPTION "Shunt packets external (IPv4 address)"

	::={lbShuntPktIpv4AddrExt 1}

lbShuntPktIpv4AddrExtMom	OBJECT-TYPE
	SYNTAX	 CounterBasedGauge64
	MAX-ACCESS read-only
	STATUS current
	DESCRIPTION "Shunt packets external (IPv4 address)"

	::={lbShuntPktIpv4AddrExt 2}

lbShuntPktIpv4AddrExtMax	OBJECT-TYPE
	SYNTAX	 CounterBasedGauge64
	MAX-ACCESS read-only
	STATUS current
	DESCRIPTION "Shunt packets external (IPv4 address)"

	::={lbShuntPktIpv4AddrExt 3}

lbShuntPktIpv4AddrExtLevelTable OBJECT-TYPE
	SYNTAX      SEQUENCE OF LbShuntPktIpv4AddrExtLevelEntry
	MAX-ACCESS  not-accessible
	STATUS      current
	DESCRIPTION
	"Table for lbShuntPktIpv4AddrExt"
	::={lbShuntPktIpv4AddrExt 4}

lbShuntPktIpv4AddrExtLevelEntry OBJECT-TYPE
	SYNTAX      LbShuntPktIpv4AddrExtLevelEntry
	MAX-ACCESS  not-accessible
	STATUS      current
	DESCRIPTION
	"Table entry for lbShuntPktIpv4AddrExt"
	INDEX { lbShuntPktIpv4AddrExtLevelName }
	::={lbShuntPktIpv4AddrExtLevelTable 1}

LbShuntPktIpv4AddrExtLevelEntry ::=
	SEQUENCE {
		lbShuntPktIpv4AddrExtLevelName	DisplayString,
		lbShuntPktIpv4AddrExtLevelVal	Counter64,
		lbShuntPktIpv4AddrExtLevelMom	CounterBasedGauge64,
		lbShuntPktIpv4AddrExtLevelMax	CounterBasedGauge64
	}

lbShuntPktIpv4AddrExtLevelName OBJECT-TYPE
	SYNTAX      DisplayString
	MAX-ACCESS  not-accessible
	STATUS      current
	DESCRIPTION
	"Table entry display string for lbShuntPktIpv4AddrExt"
	::={lbShuntPktIpv4AddrExtLevelEntry 1}

lbShuntPktIpv4AddrExtLevelVal OBJECT-TYPE
	SYNTAX	 Counter64
	MAX-ACCESS  read-only
	STATUS      current
	DESCRIPTION
	"Table entry attribute for lbShuntPktIpv4AddrExt"
	::={lbShuntPktIpv4AddrExtLevelEntry 2}

lbShuntPktIpv4AddrExtLevelMom OBJECT-TYPE
	SYNTAX	 CounterBasedGauge64
	MAX-ACCESS  read-only
	STATUS      current
	DESCRIPTION
	"Table entry attribute for lbShuntPktIpv4AddrExt"
	::={lbShuntPktIpv4AddrExtLevelEntry 3}

lbShuntPktIpv4AddrExtLevelMax OBJECT-TYPE
	SYNTAX	 CounterBasedGauge64
	MAX-ACCESS  read-only
	STATUS      current
	DESCRIPTION
	"Table entry attribute for lbShuntPktIpv4AddrExt"
	::={lbShuntPktIpv4AddrExtLevelEntry 4}


lbShuntByteIpv4AddrInt	OBJECT IDENTIFIER ::={lb 17}

lbShuntByteIpv4AddrIntVal	OBJECT-TYPE
	SYNTAX	 Counter64
	MAX-ACCESS read-only
	STATUS current
	DESCRIPTION "Shunt bytes internal (IPv4 address)"

	::={lbShuntByteIpv4AddrInt 1}

lbShuntByteIpv4AddrIntMom	OBJECT-TYPE
	SYNTAX	 CounterBasedGauge64
	MAX-ACCESS read-only
	STATUS current
	DESCRIPTION "Shunt bytes internal (IPv4 address)"

	::={lbShuntByteIpv4AddrInt 2}

lbShuntByteIpv4AddrIntMax	OBJECT-TYPE
	SYNTAX	 CounterBasedGauge64
	MAX-ACCESS read-only
	STATUS current
	DESCRIPTION "Shunt bytes internal (IPv4 address)"

	::={lbShuntByteIpv4AddrInt 3}

lbShuntByteIpv4AddrIntLevelTable OBJECT-TYPE
	SYNTAX      SEQUENCE OF LbShuntByteIpv4AddrIntLevelEntry
	MAX-ACCESS  not-accessible
	STATUS      current
	DESCRIPTION
	"Table for lbShuntByteIpv4AddrInt"
	::={lbShuntByteIpv4AddrInt 4}

lbShuntByteIpv4AddrIntLevelEntry OBJECT-TYPE
	SYNTAX      LbShuntByteIpv4AddrIntLevelEntry
	MAX-ACCESS  not-accessible
	STATUS      current
	DESCRIPTION
	"Table entry for lbShuntByteIpv4AddrInt"
	INDEX { lbShuntByteIpv4AddrIntLevelName }
	::={lbShuntByteIpv4AddrIntLevelTable 1}

LbShuntByteIpv4AddrIntLevelEntry ::=
	SEQUENCE {
		lbShuntByteIpv4AddrIntLevelName	DisplayString,
		lbShuntByteIpv4AddrIntLevelVal	Counter64,
		lbShuntByteIpv4AddrIntLevelMom	CounterBasedGauge64,
		lbShuntByteIpv4AddrIntLevelMax	CounterBasedGauge64
	}

lbShuntByteIpv4AddrIntLevelName OBJECT-TYPE
	SYNTAX      DisplayString
	MAX-ACCESS  not-accessible
	STATUS      current
	DESCRIPTION
	"Table entry display string for lbShuntByteIpv4AddrInt"
	::={lbShuntByteIpv4AddrIntLevelEntry 1}

lbShuntByteIpv4AddrIntLevelVal OBJECT-TYPE
	SYNTAX	 Counter64
	MAX-ACCESS  read-only
	STATUS      current
	DESCRIPTION
	"Table entry attribute for lbShuntByteIpv4AddrInt"
	::={lbShuntByteIpv4AddrIntLevelEntry 2}

lbShuntByteIpv4AddrIntLevelMom OBJECT-TYPE
	SYNTAX	 CounterBasedGauge64
	MAX-ACCESS  read-only
	STATUS      current
	DESCRIPTION
	"Table entry attribute for lbShuntByteIpv4AddrInt"
	::={lbShuntByteIpv4AddrIntLevelEntry 3}

lbShuntByteIpv4AddrIntLevelMax OBJECT-TYPE
	SYNTAX	 CounterBasedGauge64
	MAX-ACCESS  read-only
	STATUS      current
	DESCRIPTION
	"Table entry attribute for lbShuntByteIpv4AddrInt"
	::={lbShuntByteIpv4AddrIntLevelEntry 4}


lbShuntByteIpv4AddrExt	OBJECT IDENTIFIER ::={lb 18}

lbShuntByteIpv4AddrExtVal	OBJECT-TYPE
	SYNTAX	 Counter64
	MAX-ACCESS read-only
	STATUS current
	DESCRIPTION "Shunt bytes external (IPv4 address)"

	::={lbShuntByteIpv4AddrExt 1}

lbShuntByteIpv4AddrExtMom	OBJECT-TYPE
	SYNTAX	 CounterBasedGauge64
	MAX-ACCESS read-only
	STATUS current
	DESCRIPTION "Shunt bytes external (IPv4 address)"

	::={lbShuntByteIpv4AddrExt 2}

lbShuntByteIpv4AddrExtMax	OBJECT-TYPE
	SYNTAX	 CounterBasedGauge64
	MAX-ACCESS read-only
	STATUS current
	DESCRIPTION "Shunt bytes external (IPv4 address)"

	::={lbShuntByteIpv4AddrExt 3}

lbShuntByteIpv4AddrExtLevelTable OBJECT-TYPE
	SYNTAX      SEQUENCE OF LbShuntByteIpv4AddrExtLevelEntry
	MAX-ACCESS  not-accessible
	STATUS      current
	DESCRIPTION
	"Table for lbShuntByteIpv4AddrExt"
	::={lbShuntByteIpv4AddrExt 4}

lbShuntByteIpv4AddrExtLevelEntry OBJECT-TYPE
	SYNTAX      LbShuntByteIpv4AddrExtLevelEntry
	MAX-ACCESS  not-accessible
	STATUS      current
	DESCRIPTION
	"Table entry for lbShuntByteIpv4AddrExt"
	INDEX { lbShuntByteIpv4AddrExtLevelName }
	::={lbShuntByteIpv4AddrExtLevelTable 1}

LbShuntByteIpv4AddrExtLevelEntry ::=
	SEQUENCE {
		lbShuntByteIpv4AddrExtLevelName	DisplayString,
		lbShuntByteIpv4AddrExtLevelVal	Counter64,
		lbShuntByteIpv4AddrExtLevelMom	CounterBasedGauge64,
		lbShuntByteIpv4AddrExtLevelMax	CounterBasedGauge64
	}

lbShuntByteIpv4AddrExtLevelName OBJECT-TYPE
	SYNTAX      DisplayString
	MAX-ACCESS  not-accessible
	STATUS      current
	DESCRIPTION
	"Table entry display string for lbShuntByteIpv4AddrExt"
	::={lbShuntByteIpv4AddrExtLevelEntry 1}

lbShuntByteIpv4AddrExtLevelVal OBJECT-TYPE
	SYNTAX	 Counter64
	MAX-ACCESS  read-only
	STATUS      current
	DESCRIPTION
	"Table entry attribute for lbShuntByteIpv4AddrExt"
	::={lbShuntByteIpv4AddrExtLevelEntry 2}

lbShuntByteIpv4AddrExtLevelMom OBJECT-TYPE
	SYNTAX	 CounterBasedGauge64
	MAX-ACCESS  read-only
	STATUS      current
	DESCRIPTION
	"Table entry attribute for lbShuntByteIpv4AddrExt"
	::={lbShuntByteIpv4AddrExtLevelEntry 3}

lbShuntByteIpv4AddrExtLevelMax OBJECT-TYPE
	SYNTAX	 CounterBasedGauge64
	MAX-ACCESS  read-only
	STATUS      current
	DESCRIPTION
	"Table entry attribute for lbShuntByteIpv4AddrExt"
	::={lbShuntByteIpv4AddrExtLevelEntry 4}


lbShuntPktIpv4ProtoInt	OBJECT IDENTIFIER ::={lb 19}

lbShuntPktIpv4ProtoIntVal	OBJECT-TYPE
	SYNTAX	 Counter64
	MAX-ACCESS read-only
	STATUS current
	DESCRIPTION "Shunt packets internal (IPv4 protocol)"

	::={lbShuntPktIpv4ProtoInt 1}

lbShuntPktIpv4ProtoIntMom	OBJECT-TYPE
	SYNTAX	 CounterBasedGauge64
	MAX-ACCESS read-only
	STATUS current
	DESCRIPTION "Shunt packets internal (IPv4 protocol)"

	::={lbShuntPktIpv4ProtoInt 2}

lbShuntPktIpv4ProtoIntMax	OBJECT-TYPE
	SYNTAX	 CounterBasedGauge64
	MAX-ACCESS read-only
	STATUS current
	DESCRIPTION "Shunt packets internal (IPv4 protocol)"

	::={lbShuntPktIpv4ProtoInt 3}

lbShuntPktIpv4ProtoIntLevelTable OBJECT-TYPE
	SYNTAX      SEQUENCE OF LbShuntPktIpv4ProtoIntLevelEntry
	MAX-ACCESS  not-accessible
	STATUS      current
	DESCRIPTION
	"Table for lbShuntPktIpv4ProtoInt"
	::={lbShuntPktIpv4ProtoInt 4}

lbShuntPktIpv4ProtoIntLevelEntry OBJECT-TYPE
	SYNTAX      LbShuntPktIpv4ProtoIntLevelEntry
	MAX-ACCESS  not-accessible
	STATUS      current
	DESCRIPTION
	"Table entry for lbShuntPktIpv4ProtoInt"
	INDEX { lbShuntPktIpv4ProtoIntLevelName }
	::={lbShuntPktIpv4ProtoIntLevelTable 1}

LbShuntPktIpv4ProtoIntLevelEntry ::=
	SEQUENCE {
		lbShuntPktIpv4ProtoIntLevelName	DisplayString,
		lbShuntPktIpv4ProtoIntLevelVal	Counter64,
		lbShuntPktIpv4ProtoIntLevelMom	CounterBasedGauge64,
		lbShuntPktIpv4ProtoIntLevelMax	CounterBasedGauge64
	}

lbShuntPktIpv4ProtoIntLevelName OBJECT-TYPE
	SYNTAX      DisplayString
	MAX-ACCESS  not-accessible
	STATUS      current
	DESCRIPTION
	"Table entry display string for lbShuntPktIpv4ProtoInt"
	::={lbShuntPktIpv4ProtoIntLevelEntry 1}

lbShuntPktIpv4ProtoIntLevelVal OBJECT-TYPE
	SYNTAX	 Counter64
	MAX-ACCESS  read-only
	STATUS      current
	DESCRIPTION
	"Table entry attribute for lbShuntPktIpv4ProtoInt"
	::={lbShuntPktIpv4ProtoIntLevelEntry 2}

lbShuntPktIpv4ProtoIntLevelMom OBJECT-TYPE
	SYNTAX	 CounterBasedGauge64
	MAX-ACCESS  read-only
	STATUS      current
	DESCRIPTION
	"Table entry attribute for lbShuntPktIpv4ProtoInt"
	::={lbShuntPktIpv4ProtoIntLevelEntry 3}

lbShuntPktIpv4ProtoIntLevelMax OBJECT-TYPE
	SYNTAX	 CounterBasedGauge64
	MAX-ACCESS  read-only
	STATUS      current
	DESCRIPTION
	"Table entry attribute for lbShuntPktIpv4ProtoInt"
	::={lbShuntPktIpv4ProtoIntLevelEntry 4}


lbShuntPktIpv4ProtoExt	OBJECT IDENTIFIER ::={lb 20}

lbShuntPktIpv4ProtoExtVal	OBJECT-TYPE
	SYNTAX	 Counter64
	MAX-ACCESS read-only
	STATUS current
	DESCRIPTION "Shunt packets external (IPv4 protocol)"

	::={lbShuntPktIpv4ProtoExt 1}

lbShuntPktIpv4ProtoExtMom	OBJECT-TYPE
	SYNTAX	 CounterBasedGauge64
	MAX-ACCESS read-only
	STATUS current
	DESCRIPTION "Shunt packets external (IPv4 protocol)"

	::={lbShuntPktIpv4ProtoExt 2}

lbShuntPktIpv4ProtoExtMax	OBJECT-TYPE
	SYNTAX	 CounterBasedGauge64
	MAX-ACCESS read-only
	STATUS current
	DESCRIPTION "Shunt packets external (IPv4 protocol)"

	::={lbShuntPktIpv4ProtoExt 3}

lbShuntPktIpv4ProtoExtLevelTable OBJECT-TYPE
	SYNTAX      SEQUENCE OF LbShuntPktIpv4ProtoExtLevelEntry
	MAX-ACCESS  not-accessible
	STATUS      current
	DESCRIPTION
	"Table for lbShuntPktIpv4ProtoExt"
	::={lbShuntPktIpv4ProtoExt 4}

lbShuntPktIpv4ProtoExtLevelEntry OBJECT-TYPE
	SYNTAX      LbShuntPktIpv4ProtoExtLevelEntry
	MAX-ACCESS  not-accessible
	STATUS      current
	DESCRIPTION
	"Table entry for lbShuntPktIpv4ProtoExt"
	INDEX { lbShuntPktIpv4ProtoExtLevelName }
	::={lbShuntPktIpv4ProtoExtLevelTable 1}

LbShuntPktIpv4ProtoExtLevelEntry ::=
	SEQUENCE {
		lbShuntPktIpv4ProtoExtLevelName	DisplayString,
		lbShuntPktIpv4ProtoExtLevelVal	Counter64,
		lbShuntPktIpv4ProtoExtLevelMom	CounterBasedGauge64,
		lbShuntPktIpv4ProtoExtLevelMax	CounterBasedGauge64
	}

lbShuntPktIpv4ProtoExtLevelName OBJECT-TYPE
	SYNTAX      DisplayString
	MAX-ACCESS  not-accessible
	STATUS      current
	DESCRIPTION
	"Table entry display string for lbShuntPktIpv4ProtoExt"
	::={lbShuntPktIpv4ProtoExtLevelEntry 1}

lbShuntPktIpv4ProtoExtLevelVal OBJECT-TYPE
	SYNTAX	 Counter64
	MAX-ACCESS  read-only
	STATUS      current
	DESCRIPTION
	"Table entry attribute for lbShuntPktIpv4ProtoExt"
	::={lbShuntPktIpv4ProtoExtLevelEntry 2}

lbShuntPktIpv4ProtoExtLevelMom OBJECT-TYPE
	SYNTAX	 CounterBasedGauge64
	MAX-ACCESS  read-only
	STATUS      current
	DESCRIPTION
	"Table entry attribute for lbShuntPktIpv4ProtoExt"
	::={lbShuntPktIpv4ProtoExtLevelEntry 3}

lbShuntPktIpv4ProtoExtLevelMax OBJECT-TYPE
	SYNTAX	 CounterBasedGauge64
	MAX-ACCESS  read-only
	STATUS      current
	DESCRIPTION
	"Table entry attribute for lbShuntPktIpv4ProtoExt"
	::={lbShuntPktIpv4ProtoExtLevelEntry 4}


lbShuntByteIpv4ProtoInt	OBJECT IDENTIFIER ::={lb 21}

lbShuntByteIpv4ProtoIntVal	OBJECT-TYPE
	SYNTAX	 Counter64
	MAX-ACCESS read-only
	STATUS current
	DESCRIPTION "Shunt bytes internal (IPv4 protocol)"

	::={lbShuntByteIpv4ProtoInt 1}

lbShuntByteIpv4ProtoIntMom	OBJECT-TYPE
	SYNTAX	 CounterBasedGauge64
	MAX-ACCESS read-only
	STATUS current
	DESCRIPTION "Shunt bytes internal (IPv4 protocol)"

	::={lbShuntByteIpv4ProtoInt 2}

lbShuntByteIpv4ProtoIntMax	OBJECT-TYPE
	SYNTAX	 CounterBasedGauge64
	MAX-ACCESS read-only
	STATUS current
	DESCRIPTION "Shunt bytes internal (IPv4 protocol)"

	::={lbShuntByteIpv4ProtoInt 3}

lbShuntByteIpv4ProtoIntLevelTable OBJECT-TYPE
	SYNTAX      SEQUENCE OF LbShuntByteIpv4ProtoIntLevelEntry
	MAX-ACCESS  not-accessible
	STATUS      current
	DESCRIPTION
	"Table for lbShuntByteIpv4ProtoInt"
	::={lbShuntByteIpv4ProtoInt 4}

lbShuntByteIpv4ProtoIntLevelEntry OBJECT-TYPE
	SYNTAX      LbShuntByteIpv4ProtoIntLevelEntry
	MAX-ACCESS  not-accessible
	STATUS      current
	DESCRIPTION
	"Table entry for lbShuntByteIpv4ProtoInt"
	INDEX { lbShuntByteIpv4ProtoIntLevelName }
	::={lbShuntByteIpv4ProtoIntLevelTable 1}

LbShuntByteIpv4ProtoIntLevelEntry ::=
	SEQUENCE {
		lbShuntByteIpv4ProtoIntLevelName	DisplayString,
		lbShuntByteIpv4ProtoIntLevelVal	Counter64,
		lbShuntByteIpv4ProtoIntLevelMom	CounterBasedGauge64,
		lbShuntByteIpv4ProtoIntLevelMax	CounterBasedGauge64
	}

lbShuntByteIpv4ProtoIntLevelName OBJECT-TYPE
	SYNTAX      DisplayString
	MAX-ACCESS  not-accessible
	STATUS      current
	DESCRIPTION
	"Table entry display string for lbShuntByteIpv4ProtoInt"
	::={lbShuntByteIpv4ProtoIntLevelEntry 1}

lbShuntByteIpv4ProtoIntLevelVal OBJECT-TYPE
	SYNTAX	 Counter64
	MAX-ACCESS  read-only
	STATUS      current
	DESCRIPTION
	"Table entry attribute for lbShuntByteIpv4ProtoInt"
	::={lbShuntByteIpv4ProtoIntLevelEntry 2}

lbShuntByteIpv4ProtoIntLevelMom OBJECT-TYPE
	SYNTAX	 CounterBasedGauge64
	MAX-ACCESS  read-only
	STATUS      current
	DESCRIPTION
	"Table entry attribute for lbShuntByteIpv4ProtoInt"
	::={lbShuntByteIpv4ProtoIntLevelEntry 3}

lbShuntByteIpv4ProtoIntLevelMax OBJECT-TYPE
	SYNTAX	 CounterBasedGauge64
	MAX-ACCESS  read-only
	STATUS      current
	DESCRIPTION
	"Table entry attribute for lbShuntByteIpv4ProtoInt"
	::={lbShuntByteIpv4ProtoIntLevelEntry 4}


lbShuntByteIpv4ProtoExt	OBJECT IDENTIFIER ::={lb 22}

lbShuntByteIpv4ProtoExtVal	OBJECT-TYPE
	SYNTAX	 Counter64
	MAX-ACCESS read-only
	STATUS current
	DESCRIPTION "Shunt bytes external (IPv4 protocol)"

	::={lbShuntByteIpv4ProtoExt 1}

lbShuntByteIpv4ProtoExtMom	OBJECT-TYPE
	SYNTAX	 CounterBasedGauge64
	MAX-ACCESS read-only
	STATUS current
	DESCRIPTION "Shunt bytes external (IPv4 protocol)"

	::={lbShuntByteIpv4ProtoExt 2}

lbShuntByteIpv4ProtoExtMax	OBJECT-TYPE
	SYNTAX	 CounterBasedGauge64
	MAX-ACCESS read-only
	STATUS current
	DESCRIPTION "Shunt bytes external (IPv4 protocol)"

	::={lbShuntByteIpv4ProtoExt 3}

lbShuntByteIpv4ProtoExtLevelTable OBJECT-TYPE
	SYNTAX      SEQUENCE OF LbShuntByteIpv4ProtoExtLevelEntry
	MAX-ACCESS  not-accessible
	STATUS      current
	DESCRIPTION
	"Table for lbShuntByteIpv4ProtoExt"
	::={lbShuntByteIpv4ProtoExt 4}

lbShuntByteIpv4ProtoExtLevelEntry OBJECT-TYPE
	SYNTAX      LbShuntByteIpv4ProtoExtLevelEntry
	MAX-ACCESS  not-accessible
	STATUS      current
	DESCRIPTION
	"Table entry for lbShuntByteIpv4ProtoExt"
	INDEX { lbShuntByteIpv4ProtoExtLevelName }
	::={lbShuntByteIpv4ProtoExtLevelTable 1}

LbShuntByteIpv4ProtoExtLevelEntry ::=
	SEQUENCE {
		lbShuntByteIpv4ProtoExtLevelName	DisplayString,
		lbShuntByteIpv4ProtoExtLevelVal	Counter64,
		lbShuntByteIpv4ProtoExtLevelMom	CounterBasedGauge64,
		lbShuntByteIpv4ProtoExtLevelMax	CounterBasedGauge64
	}

lbShuntByteIpv4ProtoExtLevelName OBJECT-TYPE
	SYNTAX      DisplayString
	MAX-ACCESS  not-accessible
	STATUS      current
	DESCRIPTION
	"Table entry display string for lbShuntByteIpv4ProtoExt"
	::={lbShuntByteIpv4ProtoExtLevelEntry 1}

lbShuntByteIpv4ProtoExtLevelVal OBJECT-TYPE
	SYNTAX	 Counter64
	MAX-ACCESS  read-only
	STATUS      current
	DESCRIPTION
	"Table entry attribute for lbShuntByteIpv4ProtoExt"
	::={lbShuntByteIpv4ProtoExtLevelEntry 2}

lbShuntByteIpv4ProtoExtLevelMom OBJECT-TYPE
	SYNTAX	 CounterBasedGauge64
	MAX-ACCESS  read-only
	STATUS      current
	DESCRIPTION
	"Table entry attribute for lbShuntByteIpv4ProtoExt"
	::={lbShuntByteIpv4ProtoExtLevelEntry 3}

lbShuntByteIpv4ProtoExtLevelMax OBJECT-TYPE
	SYNTAX	 CounterBasedGauge64
	MAX-ACCESS  read-only
	STATUS      current
	DESCRIPTION
	"Table entry attribute for lbShuntByteIpv4ProtoExt"
	::={lbShuntByteIpv4ProtoExtLevelEntry 4}


lbShuntPktEthertypeInt	OBJECT IDENTIFIER ::={lb 23}

lbShuntPktEthertypeIntVal	OBJECT-TYPE
	SYNTAX	 Counter64
	MAX-ACCESS read-only
	STATUS current
	DESCRIPTION "Shunt packets internal (ethertype)"

	::={lbShuntPktEthertypeInt 1}

lbShuntPktEthertypeIntMom	OBJECT-TYPE
	SYNTAX	 CounterBasedGauge64
	MAX-ACCESS read-only
	STATUS current
	DESCRIPTION "Shunt packets internal (ethertype)"

	::={lbShuntPktEthertypeInt 2}

lbShuntPktEthertypeIntMax	OBJECT-TYPE
	SYNTAX	 CounterBasedGauge64
	MAX-ACCESS read-only
	STATUS current
	DESCRIPTION "Shunt packets internal (ethertype)"

	::={lbShuntPktEthertypeInt 3}

lbShuntPktEthertypeIntLevelTable OBJECT-TYPE
	SYNTAX      SEQUENCE OF LbShuntPktEthertypeIntLevelEntry
	MAX-ACCESS  not-accessible
	STATUS      current
	DESCRIPTION
	"Table for lbShuntPktEthertypeInt"
	::={lbShuntPktEthertypeInt 4}

lbShuntPktEthertypeIntLevelEntry OBJECT-TYPE
	SYNTAX      LbShuntPktEthertypeIntLevelEntry
	MAX-ACCESS  not-accessible
	STATUS      current
	DESCRIPTION
	"Table entry for lbShuntPktEthertypeInt"
	INDEX { lbShuntPktEthertypeIntLevelName }
	::={lbShuntPktEthertypeIntLevelTable 1}

LbShuntPktEthertypeIntLevelEntry ::=
	SEQUENCE {
		lbShuntPktEthertypeIntLevelName	DisplayString,
		lbShuntPktEthertypeIntLevelVal	Counter64,
		lbShuntPktEthertypeIntLevelMom	CounterBasedGauge64,
		lbShuntPktEthertypeIntLevelMax	CounterBasedGauge64
	}

lbShuntPktEthertypeIntLevelName OBJECT-TYPE
	SYNTAX      DisplayString
	MAX-ACCESS  not-accessible
	STATUS      current
	DESCRIPTION
	"Table entry display string for lbShuntPktEthertypeInt"
	::={lbShuntPktEthertypeIntLevelEntry 1}

lbShuntPktEthertypeIntLevelVal OBJECT-TYPE
	SYNTAX	 Counter64
	MAX-ACCESS  read-only
	STATUS      current
	DESCRIPTION
	"Table entry attribute for lbShuntPktEthertypeInt"
	::={lbShuntPktEthertypeIntLevelEntry 2}

lbShuntPktEthertypeIntLevelMom OBJECT-TYPE
	SYNTAX	 CounterBasedGauge64
	MAX-ACCESS  read-only
	STATUS      current
	DESCRIPTION
	"Table entry attribute for lbShuntPktEthertypeInt"
	::={lbShuntPktEthertypeIntLevelEntry 3}

lbShuntPktEthertypeIntLevelMax OBJECT-TYPE
	SYNTAX	 CounterBasedGauge64
	MAX-ACCESS  read-only
	STATUS      current
	DESCRIPTION
	"Table entry attribute for lbShuntPktEthertypeInt"
	::={lbShuntPktEthertypeIntLevelEntry 4}


lbShuntPktEthertypeExt	OBJECT IDENTIFIER ::={lb 24}

lbShuntPktEthertypeExtVal	OBJECT-TYPE
	SYNTAX	 Counter64
	MAX-ACCESS read-only
	STATUS current
	DESCRIPTION "Shunt packets external (ethertype)"

	::={lbShuntPktEthertypeExt 1}

lbShuntPktEthertypeExtMom	OBJECT-TYPE
	SYNTAX	 CounterBasedGauge64
	MAX-ACCESS read-only
	STATUS current
	DESCRIPTION "Shunt packets external (ethertype)"

	::={lbShuntPktEthertypeExt 2}

lbShuntPktEthertypeExtMax	OBJECT-TYPE
	SYNTAX	 CounterBasedGauge64
	MAX-ACCESS read-only
	STATUS current
	DESCRIPTION "Shunt packets external (ethertype)"

	::={lbShuntPktEthertypeExt 3}

lbShuntPktEthertypeExtLevelTable OBJECT-TYPE
	SYNTAX      SEQUENCE OF LbShuntPktEthertypeExtLevelEntry
	MAX-ACCESS  not-accessible
	STATUS      current
	DESCRIPTION
	"Table for lbShuntPktEthertypeExt"
	::={lbShuntPktEthertypeExt 4}

lbShuntPktEthertypeExtLevelEntry OBJECT-TYPE
	SYNTAX      LbShuntPktEthertypeExtLevelEntry
	MAX-ACCESS  not-accessible
	STATUS      current
	DESCRIPTION
	"Table entry for lbShuntPktEthertypeExt"
	INDEX { lbShuntPktEthertypeExtLevelName }
	::={lbShuntPktEthertypeExtLevelTable 1}

LbShuntPktEthertypeExtLevelEntry ::=
	SEQUENCE {
		lbShuntPktEthertypeExtLevelName	DisplayString,
		lbShuntPktEthertypeExtLevelVal	Counter64,
		lbShuntPktEthertypeExtLevelMom	CounterBasedGauge64,
		lbShuntPktEthertypeExtLevelMax	CounterBasedGauge64
	}

lbShuntPktEthertypeExtLevelName OBJECT-TYPE
	SYNTAX      DisplayString
	MAX-ACCESS  not-accessible
	STATUS      current
	DESCRIPTION
	"Table entry display string for lbShuntPktEthertypeExt"
	::={lbShuntPktEthertypeExtLevelEntry 1}

lbShuntPktEthertypeExtLevelVal OBJECT-TYPE
	SYNTAX	 Counter64
	MAX-ACCESS  read-only
	STATUS      current
	DESCRIPTION
	"Table entry attribute for lbShuntPktEthertypeExt"
	::={lbShuntPktEthertypeExtLevelEntry 2}

lbShuntPktEthertypeExtLevelMom OBJECT-TYPE
	SYNTAX	 CounterBasedGauge64
	MAX-ACCESS  read-only
	STATUS      current
	DESCRIPTION
	"Table entry attribute for lbShuntPktEthertypeExt"
	::={lbShuntPktEthertypeExtLevelEntry 3}

lbShuntPktEthertypeExtLevelMax OBJECT-TYPE
	SYNTAX	 CounterBasedGauge64
	MAX-ACCESS  read-only
	STATUS      current
	DESCRIPTION
	"Table entry attribute for lbShuntPktEthertypeExt"
	::={lbShuntPktEthertypeExtLevelEntry 4}


lbShuntByteEthertypeInt	OBJECT IDENTIFIER ::={lb 25}

lbShuntByteEthertypeIntVal	OBJECT-TYPE
	SYNTAX	 Counter64
	MAX-ACCESS read-only
	STATUS current
	DESCRIPTION "Shunt bytes internal (ethertype)"

	::={lbShuntByteEthertypeInt 1}

lbShuntByteEthertypeIntMom	OBJECT-TYPE
	SYNTAX	 CounterBasedGauge64
	MAX-ACCESS read-only
	STATUS current
	DESCRIPTION "Shunt bytes internal (ethertype)"

	::={lbShuntByteEthertypeInt 2}

lbShuntByteEthertypeIntMax	OBJECT-TYPE
	SYNTAX	 CounterBasedGauge64
	MAX-ACCESS read-only
	STATUS current
	DESCRIPTION "Shunt bytes internal (ethertype)"

	::={lbShuntByteEthertypeInt 3}

lbShuntByteEthertypeIntLevelTable OBJECT-TYPE
	SYNTAX      SEQUENCE OF LbShuntByteEthertypeIntLevelEntry
	MAX-ACCESS  not-accessible
	STATUS      current
	DESCRIPTION
	"Table for lbShuntByteEthertypeInt"
	::={lbShuntByteEthertypeInt 4}

lbShuntByteEthertypeIntLevelEntry OBJECT-TYPE
	SYNTAX      LbShuntByteEthertypeIntLevelEntry
	MAX-ACCESS  not-accessible
	STATUS      current
	DESCRIPTION
	"Table entry for lbShuntByteEthertypeInt"
	INDEX { lbShuntByteEthertypeIntLevelName }
	::={lbShuntByteEthertypeIntLevelTable 1}

LbShuntByteEthertypeIntLevelEntry ::=
	SEQUENCE {
		lbShuntByteEthertypeIntLevelName	DisplayString,
		lbShuntByteEthertypeIntLevelVal	Counter64,
		lbShuntByteEthertypeIntLevelMom	CounterBasedGauge64,
		lbShuntByteEthertypeIntLevelMax	CounterBasedGauge64
	}

lbShuntByteEthertypeIntLevelName OBJECT-TYPE
	SYNTAX      DisplayString
	MAX-ACCESS  not-accessible
	STATUS      current
	DESCRIPTION
	"Table entry display string for lbShuntByteEthertypeInt"
	::={lbShuntByteEthertypeIntLevelEntry 1}

lbShuntByteEthertypeIntLevelVal OBJECT-TYPE
	SYNTAX	 Counter64
	MAX-ACCESS  read-only
	STATUS      current
	DESCRIPTION
	"Table entry attribute for lbShuntByteEthertypeInt"
	::={lbShuntByteEthertypeIntLevelEntry 2}

lbShuntByteEthertypeIntLevelMom OBJECT-TYPE
	SYNTAX	 CounterBasedGauge64
	MAX-ACCESS  read-only
	STATUS      current
	DESCRIPTION
	"Table entry attribute for lbShuntByteEthertypeInt"
	::={lbShuntByteEthertypeIntLevelEntry 3}

lbShuntByteEthertypeIntLevelMax OBJECT-TYPE
	SYNTAX	 CounterBasedGauge64
	MAX-ACCESS  read-only
	STATUS      current
	DESCRIPTION
	"Table entry attribute for lbShuntByteEthertypeInt"
	::={lbShuntByteEthertypeIntLevelEntry 4}


lbShuntByteEthertypeExt	OBJECT IDENTIFIER ::={lb 26}

lbShuntByteEthertypeExtVal	OBJECT-TYPE
	SYNTAX	 Counter64
	MAX-ACCESS read-only
	STATUS current
	DESCRIPTION "Shunt bytes external (ethertype)"

	::={lbShuntByteEthertypeExt 1}

lbShuntByteEthertypeExtMom	OBJECT-TYPE
	SYNTAX	 CounterBasedGauge64
	MAX-ACCESS read-only
	STATUS current
	DESCRIPTION "Shunt bytes external (ethertype)"

	::={lbShuntByteEthertypeExt 2}

lbShuntByteEthertypeExtMax	OBJECT-TYPE
	SYNTAX	 CounterBasedGauge64
	MAX-ACCESS read-only
	STATUS current
	DESCRIPTION "Shunt bytes external (ethertype)"

	::={lbShuntByteEthertypeExt 3}

lbShuntByteEthertypeExtLevelTable OBJECT-TYPE
	SYNTAX      SEQUENCE OF LbShuntByteEthertypeExtLevelEntry
	MAX-ACCESS  not-accessible
	STATUS      current
	DESCRIPTION
	"Table for lbShuntByteEthertypeExt"
	::={lbShuntByteEthertypeExt 4}

lbShuntByteEthertypeExtLevelEntry OBJECT-TYPE
	SYNTAX      LbShuntByteEthertypeExtLevelEntry
	MAX-ACCESS  not-accessible
	STATUS      current
	DESCRIPTION
	"Table entry for lbShuntByteEthertypeExt"
	INDEX { lbShuntByteEthertypeExtLevelName }
	::={lbShuntByteEthertypeExtLevelTable 1}

LbShuntByteEthertypeExtLevelEntry ::=
	SEQUENCE {
		lbShuntByteEthertypeExtLevelName	DisplayString,
		lbShuntByteEthertypeExtLevelVal	Counter64,
		lbShuntByteEthertypeExtLevelMom	CounterBasedGauge64,
		lbShuntByteEthertypeExtLevelMax	CounterBasedGauge64
	}

lbShuntByteEthertypeExtLevelName OBJECT-TYPE
	SYNTAX      DisplayString
	MAX-ACCESS  not-accessible
	STATUS      current
	DESCRIPTION
	"Table entry display string for lbShuntByteEthertypeExt"
	::={lbShuntByteEthertypeExtLevelEntry 1}

lbShuntByteEthertypeExtLevelVal OBJECT-TYPE
	SYNTAX	 Counter64
	MAX-ACCESS  read-only
	STATUS      current
	DESCRIPTION
	"Table entry attribute for lbShuntByteEthertypeExt"
	::={lbShuntByteEthertypeExtLevelEntry 2}

lbShuntByteEthertypeExtLevelMom OBJECT-TYPE
	SYNTAX	 CounterBasedGauge64
	MAX-ACCESS  read-only
	STATUS      current
	DESCRIPTION
	"Table entry attribute for lbShuntByteEthertypeExt"
	::={lbShuntByteEthertypeExtLevelEntry 3}

lbShuntByteEthertypeExtLevelMax OBJECT-TYPE
	SYNTAX	 CounterBasedGauge64
	MAX-ACCESS  read-only
	STATUS      current
	DESCRIPTION
	"Table entry attribute for lbShuntByteEthertypeExt"
	::={lbShuntByteEthertypeExtLevelEntry 4}


lbShuntPktDot1qInt	OBJECT IDENTIFIER ::={lb 27}

lbShuntPktDot1qIntVal	OBJECT-TYPE
	SYNTAX	 Counter64
	MAX-ACCESS read-only
	STATUS current
	DESCRIPTION "Shunt packets internal (dot1q)"

	::={lbShuntPktDot1qInt 1}

lbShuntPktDot1qIntMom	OBJECT-TYPE
	SYNTAX	 CounterBasedGauge64
	MAX-ACCESS read-only
	STATUS current
	DESCRIPTION "Shunt packets internal (dot1q)"

	::={lbShuntPktDot1qInt 2}

lbShuntPktDot1qIntMax	OBJECT-TYPE
	SYNTAX	 CounterBasedGauge64
	MAX-ACCESS read-only
	STATUS current
	DESCRIPTION "Shunt packets internal (dot1q)"

	::={lbShuntPktDot1qInt 3}

lbShuntPktDot1qIntLevelTable OBJECT-TYPE
	SYNTAX      SEQUENCE OF LbShuntPktDot1qIntLevelEntry
	MAX-ACCESS  not-accessible
	STATUS      current
	DESCRIPTION
	"Table for lbShuntPktDot1qInt"
	::={lbShuntPktDot1qInt 4}

lbShuntPktDot1qIntLevelEntry OBJECT-TYPE
	SYNTAX      LbShuntPktDot1qIntLevelEntry
	MAX-ACCESS  not-accessible
	STATUS      current
	DESCRIPTION
	"Table entry for lbShuntPktDot1qInt"
	INDEX { lbShuntPktDot1qIntLevelName }
	::={lbShuntPktDot1qIntLevelTable 1}

LbShuntPktDot1qIntLevelEntry ::=
	SEQUENCE {
		lbShuntPktDot1qIntLevelName	DisplayString,
		lbShuntPktDot1qIntLevelVal	Counter64,
		lbShuntPktDot1qIntLevelMom	CounterBasedGauge64,
		lbShuntPktDot1qIntLevelMax	CounterBasedGauge64
	}

lbShuntPktDot1qIntLevelName OBJECT-TYPE
	SYNTAX      DisplayString
	MAX-ACCESS  not-accessible
	STATUS      current
	DESCRIPTION
	"Table entry display string for lbShuntPktDot1qInt"
	::={lbShuntPktDot1qIntLevelEntry 1}

lbShuntPktDot1qIntLevelVal OBJECT-TYPE
	SYNTAX	 Counter64
	MAX-ACCESS  read-only
	STATUS      current
	DESCRIPTION
	"Table entry attribute for lbShuntPktDot1qInt"
	::={lbShuntPktDot1qIntLevelEntry 2}

lbShuntPktDot1qIntLevelMom OBJECT-TYPE
	SYNTAX	 CounterBasedGauge64
	MAX-ACCESS  read-only
	STATUS      current
	DESCRIPTION
	"Table entry attribute for lbShuntPktDot1qInt"
	::={lbShuntPktDot1qIntLevelEntry 3}

lbShuntPktDot1qIntLevelMax OBJECT-TYPE
	SYNTAX	 CounterBasedGauge64
	MAX-ACCESS  read-only
	STATUS      current
	DESCRIPTION
	"Table entry attribute for lbShuntPktDot1qInt"
	::={lbShuntPktDot1qIntLevelEntry 4}


lbShuntPktDot1qExt	OBJECT IDENTIFIER ::={lb 28}

lbShuntPktDot1qExtVal	OBJECT-TYPE
	SYNTAX	 Counter64
	MAX-ACCESS read-only
	STATUS current
	DESCRIPTION "Shunt packets external (dot1q)"

	::={lbShuntPktDot1qExt 1}

lbShuntPktDot1qExtMom	OBJECT-TYPE
	SYNTAX	 CounterBasedGauge64
	MAX-ACCESS read-only
	STATUS current
	DESCRIPTION "Shunt packets external (dot1q)"

	::={lbShuntPktDot1qExt 2}

lbShuntPktDot1qExtMax	OBJECT-TYPE
	SYNTAX	 CounterBasedGauge64
	MAX-ACCESS read-only
	STATUS current
	DESCRIPTION "Shunt packets external (dot1q)"

	::={lbShuntPktDot1qExt 3}

lbShuntPktDot1qExtLevelTable OBJECT-TYPE
	SYNTAX      SEQUENCE OF LbShuntPktDot1qExtLevelEntry
	MAX-ACCESS  not-accessible
	STATUS      current
	DESCRIPTION
	"Table for lbShuntPktDot1qExt"
	::={lbShuntPktDot1qExt 4}

lbShuntPktDot1qExtLevelEntry OBJECT-TYPE
	SYNTAX      LbShuntPktDot1qExtLevelEntry
	MAX-ACCESS  not-accessible
	STATUS      current
	DESCRIPTION
	"Table entry for lbShuntPktDot1qExt"
	INDEX { lbShuntPktDot1qExtLevelName }
	::={lbShuntPktDot1qExtLevelTable 1}

LbShuntPktDot1qExtLevelEntry ::=
	SEQUENCE {
		lbShuntPktDot1qExtLevelName	DisplayString,
		lbShuntPktDot1qExtLevelVal	Counter64,
		lbShuntPktDot1qExtLevelMom	CounterBasedGauge64,
		lbShuntPktDot1qExtLevelMax	CounterBasedGauge64
	}

lbShuntPktDot1qExtLevelName OBJECT-TYPE
	SYNTAX      DisplayString
	MAX-ACCESS  not-accessible
	STATUS      current
	DESCRIPTION
	"Table entry display string for lbShuntPktDot1qExt"
	::={lbShuntPktDot1qExtLevelEntry 1}

lbShuntPktDot1qExtLevelVal OBJECT-TYPE
	SYNTAX	 Counter64
	MAX-ACCESS  read-only
	STATUS      current
	DESCRIPTION
	"Table entry attribute for lbShuntPktDot1qExt"
	::={lbShuntPktDot1qExtLevelEntry 2}

lbShuntPktDot1qExtLevelMom OBJECT-TYPE
	SYNTAX	 CounterBasedGauge64
	MAX-ACCESS  read-only
	STATUS      current
	DESCRIPTION
	"Table entry attribute for lbShuntPktDot1qExt"
	::={lbShuntPktDot1qExtLevelEntry 3}

lbShuntPktDot1qExtLevelMax OBJECT-TYPE
	SYNTAX	 CounterBasedGauge64
	MAX-ACCESS  read-only
	STATUS      current
	DESCRIPTION
	"Table entry attribute for lbShuntPktDot1qExt"
	::={lbShuntPktDot1qExtLevelEntry 4}


lbShuntByteDot1qInt	OBJECT IDENTIFIER ::={lb 29}

lbShuntByteDot1qIntVal	OBJECT-TYPE
	SYNTAX	 Counter64
	MAX-ACCESS read-only
	STATUS current
	DESCRIPTION "Shunt bytes internal (dot1q)"

	::={lbShuntByteDot1qInt 1}

lbShuntByteDot1qIntMom	OBJECT-TYPE
	SYNTAX	 CounterBasedGauge64
	MAX-ACCESS read-only
	STATUS current
	DESCRIPTION "Shunt bytes internal (dot1q)"

	::={lbShuntByteDot1qInt 2}

lbShuntByteDot1qIntMax	OBJECT-TYPE
	SYNTAX	 CounterBasedGauge64
	MAX-ACCESS read-only
	STATUS current
	DESCRIPTION "Shunt bytes internal (dot1q)"

	::={lbShuntByteDot1qInt 3}

lbShuntByteDot1qIntLevelTable OBJECT-TYPE
	SYNTAX      SEQUENCE OF LbShuntByteDot1qIntLevelEntry
	MAX-ACCESS  not-accessible
	STATUS      current
	DESCRIPTION
	"Table for lbShuntByteDot1qInt"
	::={lbShuntByteDot1qInt 4}

lbShuntByteDot1qIntLevelEntry OBJECT-TYPE
	SYNTAX      LbShuntByteDot1qIntLevelEntry
	MAX-ACCESS  not-accessible
	STATUS      current
	DESCRIPTION
	"Table entry for lbShuntByteDot1qInt"
	INDEX { lbShuntByteDot1qIntLevelName }
	::={lbShuntByteDot1qIntLevelTable 1}

LbShuntByteDot1qIntLevelEntry ::=
	SEQUENCE {
		lbShuntByteDot1qIntLevelName	DisplayString,
		lbShuntByteDot1qIntLevelVal	Counter64,
		lbShuntByteDot1qIntLevelMom	CounterBasedGauge64,
		lbShuntByteDot1qIntLevelMax	CounterBasedGauge64
	}

lbShuntByteDot1qIntLevelName OBJECT-TYPE
	SYNTAX      DisplayString
	MAX-ACCESS  not-accessible
	STATUS      current
	DESCRIPTION
	"Table entry display string for lbShuntByteDot1qInt"
	::={lbShuntByteDot1qIntLevelEntry 1}

lbShuntByteDot1qIntLevelVal OBJECT-TYPE
	SYNTAX	 Counter64
	MAX-ACCESS  read-only
	STATUS      current
	DESCRIPTION
	"Table entry attribute for lbShuntByteDot1qInt"
	::={lbShuntByteDot1qIntLevelEntry 2}

lbShuntByteDot1qIntLevelMom OBJECT-TYPE
	SYNTAX	 CounterBasedGauge64
	MAX-ACCESS  read-only
	STATUS      current
	DESCRIPTION
	"Table entry attribute for lbShuntByteDot1qInt"
	::={lbShuntByteDot1qIntLevelEntry 3}

lbShuntByteDot1qIntLevelMax OBJECT-TYPE
	SYNTAX	 CounterBasedGauge64
	MAX-ACCESS  read-only
	STATUS      current
	DESCRIPTION
	"Table entry attribute for lbShuntByteDot1qInt"
	::={lbShuntByteDot1qIntLevelEntry 4}


lbShuntByteDot1qExt	OBJECT IDENTIFIER ::={lb 30}

lbShuntByteDot1qExtVal	OBJECT-TYPE
	SYNTAX	 Counter64
	MAX-ACCESS read-only
	STATUS current
	DESCRIPTION "Shunt bytes external (dot1q)"

	::={lbShuntByteDot1qExt 1}

lbShuntByteDot1qExtMom	OBJECT-TYPE
	SYNTAX	 CounterBasedGauge64
	MAX-ACCESS read-only
	STATUS current
	DESCRIPTION "Shunt bytes external (dot1q)"

	::={lbShuntByteDot1qExt 2}

lbShuntByteDot1qExtMax	OBJECT-TYPE
	SYNTAX	 CounterBasedGauge64
	MAX-ACCESS read-only
	STATUS current
	DESCRIPTION "Shunt bytes external (dot1q)"

	::={lbShuntByteDot1qExt 3}

lbShuntByteDot1qExtLevelTable OBJECT-TYPE
	SYNTAX      SEQUENCE OF LbShuntByteDot1qExtLevelEntry
	MAX-ACCESS  not-accessible
	STATUS      current
	DESCRIPTION
	"Table for lbShuntByteDot1qExt"
	::={lbShuntByteDot1qExt 4}

lbShuntByteDot1qExtLevelEntry OBJECT-TYPE
	SYNTAX      LbShuntByteDot1qExtLevelEntry
	MAX-ACCESS  not-accessible
	STATUS      current
	DESCRIPTION
	"Table entry for lbShuntByteDot1qExt"
	INDEX { lbShuntByteDot1qExtLevelName }
	::={lbShuntByteDot1qExtLevelTable 1}

LbShuntByteDot1qExtLevelEntry ::=
	SEQUENCE {
		lbShuntByteDot1qExtLevelName	DisplayString,
		lbShuntByteDot1qExtLevelVal	Counter64,
		lbShuntByteDot1qExtLevelMom	CounterBasedGauge64,
		lbShuntByteDot1qExtLevelMax	CounterBasedGauge64
	}

lbShuntByteDot1qExtLevelName OBJECT-TYPE
	SYNTAX      DisplayString
	MAX-ACCESS  not-accessible
	STATUS      current
	DESCRIPTION
	"Table entry display string for lbShuntByteDot1qExt"
	::={lbShuntByteDot1qExtLevelEntry 1}

lbShuntByteDot1qExtLevelVal OBJECT-TYPE
	SYNTAX	 Counter64
	MAX-ACCESS  read-only
	STATUS      current
	DESCRIPTION
	"Table entry attribute for lbShuntByteDot1qExt"
	::={lbShuntByteDot1qExtLevelEntry 2}

lbShuntByteDot1qExtLevelMom OBJECT-TYPE
	SYNTAX	 CounterBasedGauge64
	MAX-ACCESS  read-only
	STATUS      current
	DESCRIPTION
	"Table entry attribute for lbShuntByteDot1qExt"
	::={lbShuntByteDot1qExtLevelEntry 3}

lbShuntByteDot1qExtLevelMax OBJECT-TYPE
	SYNTAX	 CounterBasedGauge64
	MAX-ACCESS  read-only
	STATUS      current
	DESCRIPTION
	"Table entry attribute for lbShuntByteDot1qExt"
	::={lbShuntByteDot1qExtLevelEntry 4}


lbShuntPktMplsInt	OBJECT IDENTIFIER ::={lb 31}

lbShuntPktMplsIntVal	OBJECT-TYPE
	SYNTAX	 Counter64
	MAX-ACCESS read-only
	STATUS current
	DESCRIPTION "Shunt packets internal (MPLS)"

	::={lbShuntPktMplsInt 1}

lbShuntPktMplsIntMom	OBJECT-TYPE
	SYNTAX	 CounterBasedGauge64
	MAX-ACCESS read-only
	STATUS current
	DESCRIPTION "Shunt packets internal (MPLS)"

	::={lbShuntPktMplsInt 2}

lbShuntPktMplsIntMax	OBJECT-TYPE
	SYNTAX	 CounterBasedGauge64
	MAX-ACCESS read-only
	STATUS current
	DESCRIPTION "Shunt packets internal (MPLS)"

	::={lbShuntPktMplsInt 3}

lbShuntPktMplsIntLevelTable OBJECT-TYPE
	SYNTAX      SEQUENCE OF LbShuntPktMplsIntLevelEntry
	MAX-ACCESS  not-accessible
	STATUS      current
	DESCRIPTION
	"Table for lbShuntPktMplsInt"
	::={lbShuntPktMplsInt 4}

lbShuntPktMplsIntLevelEntry OBJECT-TYPE
	SYNTAX      LbShuntPktMplsIntLevelEntry
	MAX-ACCESS  not-accessible
	STATUS      current
	DESCRIPTION
	"Table entry for lbShuntPktMplsInt"
	INDEX { lbShuntPktMplsIntLevelName }
	::={lbShuntPktMplsIntLevelTable 1}

LbShuntPktMplsIntLevelEntry ::=
	SEQUENCE {
		lbShuntPktMplsIntLevelName	DisplayString,
		lbShuntPktMplsIntLevelVal	Counter64,
		lbShuntPktMplsIntLevelMom	CounterBasedGauge64,
		lbShuntPktMplsIntLevelMax	CounterBasedGauge64
	}

lbShuntPktMplsIntLevelName OBJECT-TYPE
	SYNTAX      DisplayString
	MAX-ACCESS  not-accessible
	STATUS      current
	DESCRIPTION
	"Table entry display string for lbShuntPktMplsInt"
	::={lbShuntPktMplsIntLevelEntry 1}

lbShuntPktMplsIntLevelVal OBJECT-TYPE
	SYNTAX	 Counter64
	MAX-ACCESS  read-only
	STATUS      current
	DESCRIPTION
	"Table entry attribute for lbShuntPktMplsInt"
	::={lbShuntPktMplsIntLevelEntry 2}

lbShuntPktMplsIntLevelMom OBJECT-TYPE
	SYNTAX	 CounterBasedGauge64
	MAX-ACCESS  read-only
	STATUS      current
	DESCRIPTION
	"Table entry attribute for lbShuntPktMplsInt"
	::={lbShuntPktMplsIntLevelEntry 3}

lbShuntPktMplsIntLevelMax OBJECT-TYPE
	SYNTAX	 CounterBasedGauge64
	MAX-ACCESS  read-only
	STATUS      current
	DESCRIPTION
	"Table entry attribute for lbShuntPktMplsInt"
	::={lbShuntPktMplsIntLevelEntry 4}


lbShuntPktMplsExt	OBJECT IDENTIFIER ::={lb 32}

lbShuntPktMplsExtVal	OBJECT-TYPE
	SYNTAX	 Counter64
	MAX-ACCESS read-only
	STATUS current
	DESCRIPTION "Shunt packets external (MPLS)"

	::={lbShuntPktMplsExt 1}

lbShuntPktMplsExtMom	OBJECT-TYPE
	SYNTAX	 CounterBasedGauge64
	MAX-ACCESS read-only
	STATUS current
	DESCRIPTION "Shunt packets external (MPLS)"

	::={lbShuntPktMplsExt 2}

lbShuntPktMplsExtMax	OBJECT-TYPE
	SYNTAX	 CounterBasedGauge64
	MAX-ACCESS read-only
	STATUS current
	DESCRIPTION "Shunt packets external (MPLS)"

	::={lbShuntPktMplsExt 3}

lbShuntPktMplsExtLevelTable OBJECT-TYPE
	SYNTAX      SEQUENCE OF LbShuntPktMplsExtLevelEntry
	MAX-ACCESS  not-accessible
	STATUS      current
	DESCRIPTION
	"Table for lbShuntPktMplsExt"
	::={lbShuntPktMplsExt 4}

lbShuntPktMplsExtLevelEntry OBJECT-TYPE
	SYNTAX      LbShuntPktMplsExtLevelEntry
	MAX-ACCESS  not-accessible
	STATUS      current
	DESCRIPTION
	"Table entry for lbShuntPktMplsExt"
	INDEX { lbShuntPktMplsExtLevelName }
	::={lbShuntPktMplsExtLevelTable 1}

LbShuntPktMplsExtLevelEntry ::=
	SEQUENCE {
		lbShuntPktMplsExtLevelName	DisplayString,
		lbShuntPktMplsExtLevelVal	Counter64,
		lbShuntPktMplsExtLevelMom	CounterBasedGauge64,
		lbShuntPktMplsExtLevelMax	CounterBasedGauge64
	}

lbShuntPktMplsExtLevelName OBJECT-TYPE
	SYNTAX      DisplayString
	MAX-ACCESS  not-accessible
	STATUS      current
	DESCRIPTION
	"Table entry display string for lbShuntPktMplsExt"
	::={lbShuntPktMplsExtLevelEntry 1}

lbShuntPktMplsExtLevelVal OBJECT-TYPE
	SYNTAX	 Counter64
	MAX-ACCESS  read-only
	STATUS      current
	DESCRIPTION
	"Table entry attribute for lbShuntPktMplsExt"
	::={lbShuntPktMplsExtLevelEntry 2}

lbShuntPktMplsExtLevelMom OBJECT-TYPE
	SYNTAX	 CounterBasedGauge64
	MAX-ACCESS  read-only
	STATUS      current
	DESCRIPTION
	"Table entry attribute for lbShuntPktMplsExt"
	::={lbShuntPktMplsExtLevelEntry 3}

lbShuntPktMplsExtLevelMax OBJECT-TYPE
	SYNTAX	 CounterBasedGauge64
	MAX-ACCESS  read-only
	STATUS      current
	DESCRIPTION
	"Table entry attribute for lbShuntPktMplsExt"
	::={lbShuntPktMplsExtLevelEntry 4}


lbShuntByteMplsInt	OBJECT IDENTIFIER ::={lb 33}

lbShuntByteMplsIntVal	OBJECT-TYPE
	SYNTAX	 Counter64
	MAX-ACCESS read-only
	STATUS current
	DESCRIPTION "Shunt bytes internal (MPLS)"

	::={lbShuntByteMplsInt 1}

lbShuntByteMplsIntMom	OBJECT-TYPE
	SYNTAX	 CounterBasedGauge64
	MAX-ACCESS read-only
	STATUS current
	DESCRIPTION "Shunt bytes internal (MPLS)"

	::={lbShuntByteMplsInt 2}

lbShuntByteMplsIntMax	OBJECT-TYPE
	SYNTAX	 CounterBasedGauge64
	MAX-ACCESS read-only
	STATUS current
	DESCRIPTION "Shunt bytes internal (MPLS)"

	::={lbShuntByteMplsInt 3}

lbShuntByteMplsIntLevelTable OBJECT-TYPE
	SYNTAX      SEQUENCE OF LbShuntByteMplsIntLevelEntry
	MAX-ACCESS  not-accessible
	STATUS      current
	DESCRIPTION
	"Table for lbShuntByteMplsInt"
	::={lbShuntByteMplsInt 4}

lbShuntByteMplsIntLevelEntry OBJECT-TYPE
	SYNTAX      LbShuntByteMplsIntLevelEntry
	MAX-ACCESS  not-accessible
	STATUS      current
	DESCRIPTION
	"Table entry for lbShuntByteMplsInt"
	INDEX { lbShuntByteMplsIntLevelName }
	::={lbShuntByteMplsIntLevelTable 1}

LbShuntByteMplsIntLevelEntry ::=
	SEQUENCE {
		lbShuntByteMplsIntLevelName	DisplayString,
		lbShuntByteMplsIntLevelVal	Counter64,
		lbShuntByteMplsIntLevelMom	CounterBasedGauge64,
		lbShuntByteMplsIntLevelMax	CounterBasedGauge64
	}

lbShuntByteMplsIntLevelName OBJECT-TYPE
	SYNTAX      DisplayString
	MAX-ACCESS  not-accessible
	STATUS      current
	DESCRIPTION
	"Table entry display string for lbShuntByteMplsInt"
	::={lbShuntByteMplsIntLevelEntry 1}

lbShuntByteMplsIntLevelVal OBJECT-TYPE
	SYNTAX	 Counter64
	MAX-ACCESS  read-only
	STATUS      current
	DESCRIPTION
	"Table entry attribute for lbShuntByteMplsInt"
	::={lbShuntByteMplsIntLevelEntry 2}

lbShuntByteMplsIntLevelMom OBJECT-TYPE
	SYNTAX	 CounterBasedGauge64
	MAX-ACCESS  read-only
	STATUS      current
	DESCRIPTION
	"Table entry attribute for lbShuntByteMplsInt"
	::={lbShuntByteMplsIntLevelEntry 3}

lbShuntByteMplsIntLevelMax OBJECT-TYPE
	SYNTAX	 CounterBasedGauge64
	MAX-ACCESS  read-only
	STATUS      current
	DESCRIPTION
	"Table entry attribute for lbShuntByteMplsInt"
	::={lbShuntByteMplsIntLevelEntry 4}


lbShuntByteMplsExt	OBJECT IDENTIFIER ::={lb 34}

lbShuntByteMplsExtVal	OBJECT-TYPE
	SYNTAX	 Counter64
	MAX-ACCESS read-only
	STATUS current
	DESCRIPTION "Shunt bytes external (MPLS)"

	::={lbShuntByteMplsExt 1}

lbShuntByteMplsExtMom	OBJECT-TYPE
	SYNTAX	 CounterBasedGauge64
	MAX-ACCESS read-only
	STATUS current
	DESCRIPTION "Shunt bytes external (MPLS)"

	::={lbShuntByteMplsExt 2}

lbShuntByteMplsExtMax	OBJECT-TYPE
	SYNTAX	 CounterBasedGauge64
	MAX-ACCESS read-only
	STATUS current
	DESCRIPTION "Shunt bytes external (MPLS)"

	::={lbShuntByteMplsExt 3}

lbShuntByteMplsExtLevelTable OBJECT-TYPE
	SYNTAX      SEQUENCE OF LbShuntByteMplsExtLevelEntry
	MAX-ACCESS  not-accessible
	STATUS      current
	DESCRIPTION
	"Table for lbShuntByteMplsExt"
	::={lbShuntByteMplsExt 4}

lbShuntByteMplsExtLevelEntry OBJECT-TYPE
	SYNTAX      LbShuntByteMplsExtLevelEntry
	MAX-ACCESS  not-accessible
	STATUS      current
	DESCRIPTION
	"Table entry for lbShuntByteMplsExt"
	INDEX { lbShuntByteMplsExtLevelName }
	::={lbShuntByteMplsExtLevelTable 1}

LbShuntByteMplsExtLevelEntry ::=
	SEQUENCE {
		lbShuntByteMplsExtLevelName	DisplayString,
		lbShuntByteMplsExtLevelVal	Counter64,
		lbShuntByteMplsExtLevelMom	CounterBasedGauge64,
		lbShuntByteMplsExtLevelMax	CounterBasedGauge64
	}

lbShuntByteMplsExtLevelName OBJECT-TYPE
	SYNTAX      DisplayString
	MAX-ACCESS  not-accessible
	STATUS      current
	DESCRIPTION
	"Table entry display string for lbShuntByteMplsExt"
	::={lbShuntByteMplsExtLevelEntry 1}

lbShuntByteMplsExtLevelVal OBJECT-TYPE
	SYNTAX	 Counter64
	MAX-ACCESS  read-only
	STATUS      current
	DESCRIPTION
	"Table entry attribute for lbShuntByteMplsExt"
	::={lbShuntByteMplsExtLevelEntry 2}

lbShuntByteMplsExtLevelMom OBJECT-TYPE
	SYNTAX	 CounterBasedGauge64
	MAX-ACCESS  read-only
	STATUS      current
	DESCRIPTION
	"Table entry attribute for lbShuntByteMplsExt"
	::={lbShuntByteMplsExtLevelEntry 3}

lbShuntByteMplsExtLevelMax OBJECT-TYPE
	SYNTAX	 CounterBasedGauge64
	MAX-ACCESS  read-only
	STATUS      current
	DESCRIPTION
	"Table entry attribute for lbShuntByteMplsExt"
	::={lbShuntByteMplsExtLevelEntry 4}


lbShuntPktEomplsInt	OBJECT IDENTIFIER ::={lb 35}

lbShuntPktEomplsIntVal	OBJECT-TYPE
	SYNTAX	 Counter64
	MAX-ACCESS read-only
	STATUS current
	DESCRIPTION "Shunt packets internal (EoMPLS)"

	::={lbShuntPktEomplsInt 1}

lbShuntPktEomplsIntMom	OBJECT-TYPE
	SYNTAX	 CounterBasedGauge64
	MAX-ACCESS read-only
	STATUS current
	DESCRIPTION "Shunt packets internal (EoMPLS)"

	::={lbShuntPktEomplsInt 2}

lbShuntPktEomplsIntMax	OBJECT-TYPE
	SYNTAX	 CounterBasedGauge64
	MAX-ACCESS read-only
	STATUS current
	DESCRIPTION "Shunt packets internal (EoMPLS)"

	::={lbShuntPktEomplsInt 3}

lbShuntPktEomplsIntLevelTable OBJECT-TYPE
	SYNTAX      SEQUENCE OF LbShuntPktEomplsIntLevelEntry
	MAX-ACCESS  not-accessible
	STATUS      current
	DESCRIPTION
	"Table for lbShuntPktEomplsInt"
	::={lbShuntPktEomplsInt 4}

lbShuntPktEomplsIntLevelEntry OBJECT-TYPE
	SYNTAX      LbShuntPktEomplsIntLevelEntry
	MAX-ACCESS  not-accessible
	STATUS      current
	DESCRIPTION
	"Table entry for lbShuntPktEomplsInt"
	INDEX { lbShuntPktEomplsIntLevelName }
	::={lbShuntPktEomplsIntLevelTable 1}

LbShuntPktEomplsIntLevelEntry ::=
	SEQUENCE {
		lbShuntPktEomplsIntLevelName	DisplayString,
		lbShuntPktEomplsIntLevelVal	Counter64,
		lbShuntPktEomplsIntLevelMom	CounterBasedGauge64,
		lbShuntPktEomplsIntLevelMax	CounterBasedGauge64
	}

lbShuntPktEomplsIntLevelName OBJECT-TYPE
	SYNTAX      DisplayString
	MAX-ACCESS  not-accessible
	STATUS      current
	DESCRIPTION
	"Table entry display string for lbShuntPktEomplsInt"
	::={lbShuntPktEomplsIntLevelEntry 1}

lbShuntPktEomplsIntLevelVal OBJECT-TYPE
	SYNTAX	 Counter64
	MAX-ACCESS  read-only
	STATUS      current
	DESCRIPTION
	"Table entry attribute for lbShuntPktEomplsInt"
	::={lbShuntPktEomplsIntLevelEntry 2}

lbShuntPktEomplsIntLevelMom OBJECT-TYPE
	SYNTAX	 CounterBasedGauge64
	MAX-ACCESS  read-only
	STATUS      current
	DESCRIPTION
	"Table entry attribute for lbShuntPktEomplsInt"
	::={lbShuntPktEomplsIntLevelEntry 3}

lbShuntPktEomplsIntLevelMax OBJECT-TYPE
	SYNTAX	 CounterBasedGauge64
	MAX-ACCESS  read-only
	STATUS      current
	DESCRIPTION
	"Table entry attribute for lbShuntPktEomplsInt"
	::={lbShuntPktEomplsIntLevelEntry 4}


lbShuntPktEomplsExt	OBJECT IDENTIFIER ::={lb 36}

lbShuntPktEomplsExtVal	OBJECT-TYPE
	SYNTAX	 Counter64
	MAX-ACCESS read-only
	STATUS current
	DESCRIPTION "Shunt packets external (EoMPLS)"

	::={lbShuntPktEomplsExt 1}

lbShuntPktEomplsExtMom	OBJECT-TYPE
	SYNTAX	 CounterBasedGauge64
	MAX-ACCESS read-only
	STATUS current
	DESCRIPTION "Shunt packets external (EoMPLS)"

	::={lbShuntPktEomplsExt 2}

lbShuntPktEomplsExtMax	OBJECT-TYPE
	SYNTAX	 CounterBasedGauge64
	MAX-ACCESS read-only
	STATUS current
	DESCRIPTION "Shunt packets external (EoMPLS)"

	::={lbShuntPktEomplsExt 3}

lbShuntPktEomplsExtLevelTable OBJECT-TYPE
	SYNTAX      SEQUENCE OF LbShuntPktEomplsExtLevelEntry
	MAX-ACCESS  not-accessible
	STATUS      current
	DESCRIPTION
	"Table for lbShuntPktEomplsExt"
	::={lbShuntPktEomplsExt 4}

lbShuntPktEomplsExtLevelEntry OBJECT-TYPE
	SYNTAX      LbShuntPktEomplsExtLevelEntry
	MAX-ACCESS  not-accessible
	STATUS      current
	DESCRIPTION
	"Table entry for lbShuntPktEomplsExt"
	INDEX { lbShuntPktEomplsExtLevelName }
	::={lbShuntPktEomplsExtLevelTable 1}

LbShuntPktEomplsExtLevelEntry ::=
	SEQUENCE {
		lbShuntPktEomplsExtLevelName	DisplayString,
		lbShuntPktEomplsExtLevelVal	Counter64,
		lbShuntPktEomplsExtLevelMom	CounterBasedGauge64,
		lbShuntPktEomplsExtLevelMax	CounterBasedGauge64
	}

lbShuntPktEomplsExtLevelName OBJECT-TYPE
	SYNTAX      DisplayString
	MAX-ACCESS  not-accessible
	STATUS      current
	DESCRIPTION
	"Table entry display string for lbShuntPktEomplsExt"
	::={lbShuntPktEomplsExtLevelEntry 1}

lbShuntPktEomplsExtLevelVal OBJECT-TYPE
	SYNTAX	 Counter64
	MAX-ACCESS  read-only
	STATUS      current
	DESCRIPTION
	"Table entry attribute for lbShuntPktEomplsExt"
	::={lbShuntPktEomplsExtLevelEntry 2}

lbShuntPktEomplsExtLevelMom OBJECT-TYPE
	SYNTAX	 CounterBasedGauge64
	MAX-ACCESS  read-only
	STATUS      current
	DESCRIPTION
	"Table entry attribute for lbShuntPktEomplsExt"
	::={lbShuntPktEomplsExtLevelEntry 3}

lbShuntPktEomplsExtLevelMax OBJECT-TYPE
	SYNTAX	 CounterBasedGauge64
	MAX-ACCESS  read-only
	STATUS      current
	DESCRIPTION
	"Table entry attribute for lbShuntPktEomplsExt"
	::={lbShuntPktEomplsExtLevelEntry 4}


lbShuntByteEomplsInt	OBJECT IDENTIFIER ::={lb 37}

lbShuntByteEomplsIntVal	OBJECT-TYPE
	SYNTAX	 Counter64
	MAX-ACCESS read-only
	STATUS current
	DESCRIPTION "Shunt bytes internal (EoMPLS)"

	::={lbShuntByteEomplsInt 1}

lbShuntByteEomplsIntMom	OBJECT-TYPE
	SYNTAX	 CounterBasedGauge64
	MAX-ACCESS read-only
	STATUS current
	DESCRIPTION "Shunt bytes internal (EoMPLS)"

	::={lbShuntByteEomplsInt 2}

lbShuntByteEomplsIntMax	OBJECT-TYPE
	SYNTAX	 CounterBasedGauge64
	MAX-ACCESS read-only
	STATUS current
	DESCRIPTION "Shunt bytes internal (EoMPLS)"

	::={lbShuntByteEomplsInt 3}

lbShuntByteEomplsIntLevelTable OBJECT-TYPE
	SYNTAX      SEQUENCE OF LbShuntByteEomplsIntLevelEntry
	MAX-ACCESS  not-accessible
	STATUS      current
	DESCRIPTION
	"Table for lbShuntByteEomplsInt"
	::={lbShuntByteEomplsInt 4}

lbShuntByteEomplsIntLevelEntry OBJECT-TYPE
	SYNTAX      LbShuntByteEomplsIntLevelEntry
	MAX-ACCESS  not-accessible
	STATUS      current
	DESCRIPTION
	"Table entry for lbShuntByteEomplsInt"
	INDEX { lbShuntByteEomplsIntLevelName }
	::={lbShuntByteEomplsIntLevelTable 1}

LbShuntByteEomplsIntLevelEntry ::=
	SEQUENCE {
		lbShuntByteEomplsIntLevelName	DisplayString,
		lbShuntByteEomplsIntLevelVal	Counter64,
		lbShuntByteEomplsIntLevelMom	CounterBasedGauge64,
		lbShuntByteEomplsIntLevelMax	CounterBasedGauge64
	}

lbShuntByteEomplsIntLevelName OBJECT-TYPE
	SYNTAX      DisplayString
	MAX-ACCESS  not-accessible
	STATUS      current
	DESCRIPTION
	"Table entry display string for lbShuntByteEomplsInt"
	::={lbShuntByteEomplsIntLevelEntry 1}

lbShuntByteEomplsIntLevelVal OBJECT-TYPE
	SYNTAX	 Counter64
	MAX-ACCESS  read-only
	STATUS      current
	DESCRIPTION
	"Table entry attribute for lbShuntByteEomplsInt"
	::={lbShuntByteEomplsIntLevelEntry 2}

lbShuntByteEomplsIntLevelMom OBJECT-TYPE
	SYNTAX	 CounterBasedGauge64
	MAX-ACCESS  read-only
	STATUS      current
	DESCRIPTION
	"Table entry attribute for lbShuntByteEomplsInt"
	::={lbShuntByteEomplsIntLevelEntry 3}

lbShuntByteEomplsIntLevelMax OBJECT-TYPE
	SYNTAX	 CounterBasedGauge64
	MAX-ACCESS  read-only
	STATUS      current
	DESCRIPTION
	"Table entry attribute for lbShuntByteEomplsInt"
	::={lbShuntByteEomplsIntLevelEntry 4}


lbShuntByteEomplsExt	OBJECT IDENTIFIER ::={lb 38}

lbShuntByteEomplsExtVal	OBJECT-TYPE
	SYNTAX	 Counter64
	MAX-ACCESS read-only
	STATUS current
	DESCRIPTION "Shunt bytes external (EoMPLS)"

	::={lbShuntByteEomplsExt 1}

lbShuntByteEomplsExtMom	OBJECT-TYPE
	SYNTAX	 CounterBasedGauge64
	MAX-ACCESS read-only
	STATUS current
	DESCRIPTION "Shunt bytes external (EoMPLS)"

	::={lbShuntByteEomplsExt 2}

lbShuntByteEomplsExtMax	OBJECT-TYPE
	SYNTAX	 CounterBasedGauge64
	MAX-ACCESS read-only
	STATUS current
	DESCRIPTION "Shunt bytes external (EoMPLS)"

	::={lbShuntByteEomplsExt 3}

lbShuntByteEomplsExtLevelTable OBJECT-TYPE
	SYNTAX      SEQUENCE OF LbShuntByteEomplsExtLevelEntry
	MAX-ACCESS  not-accessible
	STATUS      current
	DESCRIPTION
	"Table for lbShuntByteEomplsExt"
	::={lbShuntByteEomplsExt 4}

lbShuntByteEomplsExtLevelEntry OBJECT-TYPE
	SYNTAX      LbShuntByteEomplsExtLevelEntry
	MAX-ACCESS  not-accessible
	STATUS      current
	DESCRIPTION
	"Table entry for lbShuntByteEomplsExt"
	INDEX { lbShuntByteEomplsExtLevelName }
	::={lbShuntByteEomplsExtLevelTable 1}

LbShuntByteEomplsExtLevelEntry ::=
	SEQUENCE {
		lbShuntByteEomplsExtLevelName	DisplayString,
		lbShuntByteEomplsExtLevelVal	Counter64,
		lbShuntByteEomplsExtLevelMom	CounterBasedGauge64,
		lbShuntByteEomplsExtLevelMax	CounterBasedGauge64
	}

lbShuntByteEomplsExtLevelName OBJECT-TYPE
	SYNTAX      DisplayString
	MAX-ACCESS  not-accessible
	STATUS      current
	DESCRIPTION
	"Table entry display string for lbShuntByteEomplsExt"
	::={lbShuntByteEomplsExtLevelEntry 1}

lbShuntByteEomplsExtLevelVal OBJECT-TYPE
	SYNTAX	 Counter64
	MAX-ACCESS  read-only
	STATUS      current
	DESCRIPTION
	"Table entry attribute for lbShuntByteEomplsExt"
	::={lbShuntByteEomplsExtLevelEntry 2}

lbShuntByteEomplsExtLevelMom OBJECT-TYPE
	SYNTAX	 CounterBasedGauge64
	MAX-ACCESS  read-only
	STATUS      current
	DESCRIPTION
	"Table entry attribute for lbShuntByteEomplsExt"
	::={lbShuntByteEomplsExtLevelEntry 3}

lbShuntByteEomplsExtLevelMax OBJECT-TYPE
	SYNTAX	 CounterBasedGauge64
	MAX-ACCESS  read-only
	STATUS      current
	DESCRIPTION
	"Table entry attribute for lbShuntByteEomplsExt"
	::={lbShuntByteEomplsExtLevelEntry 4}


lbLbUptime	OBJECT IDENTIFIER ::={lb 39}

lbLbUptimeVal	OBJECT-TYPE
	SYNTAX	 TimeTicks
	MAX-ACCESS read-only
	STATUS current
	DESCRIPTION "CPU uptime"

	::={lbLbUptime 1}

lbLbUptimeLevelTable OBJECT-TYPE
	SYNTAX      SEQUENCE OF LbLbUptimeLevelEntry
	MAX-ACCESS  not-accessible
	STATUS      current
	DESCRIPTION
	"Table for lbLbUptime"
	::={lbLbUptime 2}

lbLbUptimeLevelEntry OBJECT-TYPE
	SYNTAX      LbLbUptimeLevelEntry
	MAX-ACCESS  not-accessible
	STATUS      current
	DESCRIPTION
	"Table entry for lbLbUptime"
	INDEX { lbLbUptimeLevelName }
	::={lbLbUptimeLevelTable 1}

LbLbUptimeLevelEntry ::=
	SEQUENCE {
		lbLbUptimeLevelName	DisplayString,
		lbLbUptimeLevelVal	TimeTicks
	}

lbLbUptimeLevelName OBJECT-TYPE
	SYNTAX      DisplayString
	MAX-ACCESS  not-accessible
	STATUS      current
	DESCRIPTION
	"Table entry display string for lbLbUptime"
	::={lbLbUptimeLevelEntry 1}

lbLbUptimeLevelVal OBJECT-TYPE
	SYNTAX	 TimeTicks
	MAX-ACCESS  read-only
	STATUS      current
	DESCRIPTION
	"Table entry attribute for lbLbUptime"
	::={lbLbUptimeLevelEntry 2}


lbCpuLoad	OBJECT IDENTIFIER ::={lb 40}

lbCpuLoadVal	OBJECT-TYPE
	SYNTAX	 Unsigned32
	MAX-ACCESS read-only
	STATUS current
	DESCRIPTION "CPU load"

	::={lbCpuLoad 1}

lbCpuLoadMax	OBJECT-TYPE
	SYNTAX	 Unsigned32
	MAX-ACCESS read-only
	STATUS current
	DESCRIPTION "CPU load"

	::={lbCpuLoad 3}

lbCpuLoadLevelTable OBJECT-TYPE
	SYNTAX      SEQUENCE OF LbCpuLoadLevelEntry
	MAX-ACCESS  not-accessible
	STATUS      current
	DESCRIPTION
	"Table for lbCpuLoad"
	::={lbCpuLoad 4}

lbCpuLoadLevelEntry OBJECT-TYPE
	SYNTAX      LbCpuLoadLevelEntry
	MAX-ACCESS  not-accessible
	STATUS      current
	DESCRIPTION
	"Table entry for lbCpuLoad"
	INDEX { lbCpuLoadLevelName }
	::={lbCpuLoadLevelTable 1}

LbCpuLoadLevelEntry ::=
	SEQUENCE {
		lbCpuLoadLevelName	DisplayString,
		lbCpuLoadLevelVal	Unsigned32,
		lbCpuLoadLevelMax	Unsigned32
	}

lbCpuLoadLevelName OBJECT-TYPE
	SYNTAX      DisplayString
	MAX-ACCESS  not-accessible
	STATUS      current
	DESCRIPTION
	"Table entry display string for lbCpuLoad"
	::={lbCpuLoadLevelEntry 1}

lbCpuLoadLevelVal OBJECT-TYPE
	SYNTAX	 Unsigned32
	MAX-ACCESS  read-only
	STATUS      current
	DESCRIPTION
	"Table entry attribute for lbCpuLoad"
	::={lbCpuLoadLevelEntry 2}

lbCpuLoadLevelMax OBJECT-TYPE
	SYNTAX	 Unsigned32
	MAX-ACCESS  read-only
	STATUS      current
	DESCRIPTION
	"Table entry attribute for lbCpuLoad"
	::={lbCpuLoadLevelEntry 4}


lbShuntPktIpv6AddrInt	OBJECT IDENTIFIER ::={lb 41}

lbShuntPktIpv6AddrIntVal	OBJECT-TYPE
	SYNTAX	 Counter64
	MAX-ACCESS read-only
	STATUS current
	DESCRIPTION "Shunt packets internal (IPv6 address)"

	::={lbShuntPktIpv6AddrInt 1}

lbShuntPktIpv6AddrIntMom	OBJECT-TYPE
	SYNTAX	 CounterBasedGauge64
	MAX-ACCESS read-only
	STATUS current
	DESCRIPTION "Shunt packets internal (IPv6 address)"

	::={lbShuntPktIpv6AddrInt 2}

lbShuntPktIpv6AddrIntMax	OBJECT-TYPE
	SYNTAX	 CounterBasedGauge64
	MAX-ACCESS read-only
	STATUS current
	DESCRIPTION "Shunt packets internal (IPv6 address)"

	::={lbShuntPktIpv6AddrInt 3}

lbShuntPktIpv6AddrIntLevelTable OBJECT-TYPE
	SYNTAX      SEQUENCE OF LbShuntPktIpv6AddrIntLevelEntry
	MAX-ACCESS  not-accessible
	STATUS      current
	DESCRIPTION
	"Table for lbShuntPktIpv6AddrInt"
	::={lbShuntPktIpv6AddrInt 4}

lbShuntPktIpv6AddrIntLevelEntry OBJECT-TYPE
	SYNTAX      LbShuntPktIpv6AddrIntLevelEntry
	MAX-ACCESS  not-accessible
	STATUS      current
	DESCRIPTION
	"Table entry for lbShuntPktIpv6AddrInt"
	INDEX { lbShuntPktIpv6AddrIntLevelName }
	::={lbShuntPktIpv6AddrIntLevelTable 1}

LbShuntPktIpv6AddrIntLevelEntry ::=
	SEQUENCE {
		lbShuntPktIpv6AddrIntLevelName	DisplayString,
		lbShuntPktIpv6AddrIntLevelVal	Counter64,
		lbShuntPktIpv6AddrIntLevelMom	CounterBasedGauge64,
		lbShuntPktIpv6AddrIntLevelMax	CounterBasedGauge64
	}

lbShuntPktIpv6AddrIntLevelName OBJECT-TYPE
	SYNTAX      DisplayString
	MAX-ACCESS  not-accessible
	STATUS      current
	DESCRIPTION
	"Table entry display string for lbShuntPktIpv6AddrInt"
	::={lbShuntPktIpv6AddrIntLevelEntry 1}

lbShuntPktIpv6AddrIntLevelVal OBJECT-TYPE
	SYNTAX	 Counter64
	MAX-ACCESS  read-only
	STATUS      current
	DESCRIPTION
	"Table entry attribute for lbShuntPktIpv6AddrInt"
	::={lbShuntPktIpv6AddrIntLevelEntry 2}

lbShuntPktIpv6AddrIntLevelMom OBJECT-TYPE
	SYNTAX	 CounterBasedGauge64
	MAX-ACCESS  read-only
	STATUS      current
	DESCRIPTION
	"Table entry attribute for lbShuntPktIpv6AddrInt"
	::={lbShuntPktIpv6AddrIntLevelEntry 3}

lbShuntPktIpv6AddrIntLevelMax OBJECT-TYPE
	SYNTAX	 CounterBasedGauge64
	MAX-ACCESS  read-only
	STATUS      current
	DESCRIPTION
	"Table entry attribute for lbShuntPktIpv6AddrInt"
	::={lbShuntPktIpv6AddrIntLevelEntry 4}


lbShuntPktIpv6AddrExt	OBJECT IDENTIFIER ::={lb 42}

lbShuntPktIpv6AddrExtVal	OBJECT-TYPE
	SYNTAX	 Counter64
	MAX-ACCESS read-only
	STATUS current
	DESCRIPTION "Shunt packets external (IPv6 address)"

	::={lbShuntPktIpv6AddrExt 1}

lbShuntPktIpv6AddrExtMom	OBJECT-TYPE
	SYNTAX	 CounterBasedGauge64
	MAX-ACCESS read-only
	STATUS current
	DESCRIPTION "Shunt packets external (IPv6 address)"

	::={lbShuntPktIpv6AddrExt 2}

lbShuntPktIpv6AddrExtMax	OBJECT-TYPE
	SYNTAX	 CounterBasedGauge64
	MAX-ACCESS read-only
	STATUS current
	DESCRIPTION "Shunt packets external (IPv6 address)"

	::={lbShuntPktIpv6AddrExt 3}

lbShuntPktIpv6AddrExtLevelTable OBJECT-TYPE
	SYNTAX      SEQUENCE OF LbShuntPktIpv6AddrExtLevelEntry
	MAX-ACCESS  not-accessible
	STATUS      current
	DESCRIPTION
	"Table for lbShuntPktIpv6AddrExt"
	::={lbShuntPktIpv6AddrExt 4}

lbShuntPktIpv6AddrExtLevelEntry OBJECT-TYPE
	SYNTAX      LbShuntPktIpv6AddrExtLevelEntry
	MAX-ACCESS  not-accessible
	STATUS      current
	DESCRIPTION
	"Table entry for lbShuntPktIpv6AddrExt"
	INDEX { lbShuntPktIpv6AddrExtLevelName }
	::={lbShuntPktIpv6AddrExtLevelTable 1}

LbShuntPktIpv6AddrExtLevelEntry ::=
	SEQUENCE {
		lbShuntPktIpv6AddrExtLevelName	DisplayString,
		lbShuntPktIpv6AddrExtLevelVal	Counter64,
		lbShuntPktIpv6AddrExtLevelMom	CounterBasedGauge64,
		lbShuntPktIpv6AddrExtLevelMax	CounterBasedGauge64
	}

lbShuntPktIpv6AddrExtLevelName OBJECT-TYPE
	SYNTAX      DisplayString
	MAX-ACCESS  not-accessible
	STATUS      current
	DESCRIPTION
	"Table entry display string for lbShuntPktIpv6AddrExt"
	::={lbShuntPktIpv6AddrExtLevelEntry 1}

lbShuntPktIpv6AddrExtLevelVal OBJECT-TYPE
	SYNTAX	 Counter64
	MAX-ACCESS  read-only
	STATUS      current
	DESCRIPTION
	"Table entry attribute for lbShuntPktIpv6AddrExt"
	::={lbShuntPktIpv6AddrExtLevelEntry 2}

lbShuntPktIpv6AddrExtLevelMom OBJECT-TYPE
	SYNTAX	 CounterBasedGauge64
	MAX-ACCESS  read-only
	STATUS      current
	DESCRIPTION
	"Table entry attribute for lbShuntPktIpv6AddrExt"
	::={lbShuntPktIpv6AddrExtLevelEntry 3}

lbShuntPktIpv6AddrExtLevelMax OBJECT-TYPE
	SYNTAX	 CounterBasedGauge64
	MAX-ACCESS  read-only
	STATUS      current
	DESCRIPTION
	"Table entry attribute for lbShuntPktIpv6AddrExt"
	::={lbShuntPktIpv6AddrExtLevelEntry 4}


lbShuntByteIpv6AddrInt	OBJECT IDENTIFIER ::={lb 43}

lbShuntByteIpv6AddrIntVal	OBJECT-TYPE
	SYNTAX	 Counter64
	MAX-ACCESS read-only
	STATUS current
	DESCRIPTION "Shunt bytes internal (IPv6 address)"

	::={lbShuntByteIpv6AddrInt 1}

lbShuntByteIpv6AddrIntMom	OBJECT-TYPE
	SYNTAX	 CounterBasedGauge64
	MAX-ACCESS read-only
	STATUS current
	DESCRIPTION "Shunt bytes internal (IPv6 address)"

	::={lbShuntByteIpv6AddrInt 2}

lbShuntByteIpv6AddrIntMax	OBJECT-TYPE
	SYNTAX	 CounterBasedGauge64
	MAX-ACCESS read-only
	STATUS current
	DESCRIPTION "Shunt bytes internal (IPv6 address)"

	::={lbShuntByteIpv6AddrInt 3}

lbShuntByteIpv6AddrIntLevelTable OBJECT-TYPE
	SYNTAX      SEQUENCE OF LbShuntByteIpv6AddrIntLevelEntry
	MAX-ACCESS  not-accessible
	STATUS      current
	DESCRIPTION
	"Table for lbShuntByteIpv6AddrInt"
	::={lbShuntByteIpv6AddrInt 4}

lbShuntByteIpv6AddrIntLevelEntry OBJECT-TYPE
	SYNTAX      LbShuntByteIpv6AddrIntLevelEntry
	MAX-ACCESS  not-accessible
	STATUS      current
	DESCRIPTION
	"Table entry for lbShuntByteIpv6AddrInt"
	INDEX { lbShuntByteIpv6AddrIntLevelName }
	::={lbShuntByteIpv6AddrIntLevelTable 1}

LbShuntByteIpv6AddrIntLevelEntry ::=
	SEQUENCE {
		lbShuntByteIpv6AddrIntLevelName	DisplayString,
		lbShuntByteIpv6AddrIntLevelVal	Counter64,
		lbShuntByteIpv6AddrIntLevelMom	CounterBasedGauge64,
		lbShuntByteIpv6AddrIntLevelMax	CounterBasedGauge64
	}

lbShuntByteIpv6AddrIntLevelName OBJECT-TYPE
	SYNTAX      DisplayString
	MAX-ACCESS  not-accessible
	STATUS      current
	DESCRIPTION
	"Table entry display string for lbShuntByteIpv6AddrInt"
	::={lbShuntByteIpv6AddrIntLevelEntry 1}

lbShuntByteIpv6AddrIntLevelVal OBJECT-TYPE
	SYNTAX	 Counter64
	MAX-ACCESS  read-only
	STATUS      current
	DESCRIPTION
	"Table entry attribute for lbShuntByteIpv6AddrInt"
	::={lbShuntByteIpv6AddrIntLevelEntry 2}

lbShuntByteIpv6AddrIntLevelMom OBJECT-TYPE
	SYNTAX	 CounterBasedGauge64
	MAX-ACCESS  read-only
	STATUS      current
	DESCRIPTION
	"Table entry attribute for lbShuntByteIpv6AddrInt"
	::={lbShuntByteIpv6AddrIntLevelEntry 3}

lbShuntByteIpv6AddrIntLevelMax OBJECT-TYPE
	SYNTAX	 CounterBasedGauge64
	MAX-ACCESS  read-only
	STATUS      current
	DESCRIPTION
	"Table entry attribute for lbShuntByteIpv6AddrInt"
	::={lbShuntByteIpv6AddrIntLevelEntry 4}


lbShuntByteIpv6AddrExt	OBJECT IDENTIFIER ::={lb 44}

lbShuntByteIpv6AddrExtVal	OBJECT-TYPE
	SYNTAX	 Counter64
	MAX-ACCESS read-only
	STATUS current
	DESCRIPTION "Shunt bytes external (IPv6 address)"

	::={lbShuntByteIpv6AddrExt 1}

lbShuntByteIpv6AddrExtMom	OBJECT-TYPE
	SYNTAX	 CounterBasedGauge64
	MAX-ACCESS read-only
	STATUS current
	DESCRIPTION "Shunt bytes external (IPv6 address)"

	::={lbShuntByteIpv6AddrExt 2}

lbShuntByteIpv6AddrExtMax	OBJECT-TYPE
	SYNTAX	 CounterBasedGauge64
	MAX-ACCESS read-only
	STATUS current
	DESCRIPTION "Shunt bytes external (IPv6 address)"

	::={lbShuntByteIpv6AddrExt 3}

lbShuntByteIpv6AddrExtLevelTable OBJECT-TYPE
	SYNTAX      SEQUENCE OF LbShuntByteIpv6AddrExtLevelEntry
	MAX-ACCESS  not-accessible
	STATUS      current
	DESCRIPTION
	"Table for lbShuntByteIpv6AddrExt"
	::={lbShuntByteIpv6AddrExt 4}

lbShuntByteIpv6AddrExtLevelEntry OBJECT-TYPE
	SYNTAX      LbShuntByteIpv6AddrExtLevelEntry
	MAX-ACCESS  not-accessible
	STATUS      current
	DESCRIPTION
	"Table entry for lbShuntByteIpv6AddrExt"
	INDEX { lbShuntByteIpv6AddrExtLevelName }
	::={lbShuntByteIpv6AddrExtLevelTable 1}

LbShuntByteIpv6AddrExtLevelEntry ::=
	SEQUENCE {
		lbShuntByteIpv6AddrExtLevelName	DisplayString,
		lbShuntByteIpv6AddrExtLevelVal	Counter64,
		lbShuntByteIpv6AddrExtLevelMom	CounterBasedGauge64,
		lbShuntByteIpv6AddrExtLevelMax	CounterBasedGauge64
	}

lbShuntByteIpv6AddrExtLevelName OBJECT-TYPE
	SYNTAX      DisplayString
	MAX-ACCESS  not-accessible
	STATUS      current
	DESCRIPTION
	"Table entry display string for lbShuntByteIpv6AddrExt"
	::={lbShuntByteIpv6AddrExtLevelEntry 1}

lbShuntByteIpv6AddrExtLevelVal OBJECT-TYPE
	SYNTAX	 Counter64
	MAX-ACCESS  read-only
	STATUS      current
	DESCRIPTION
	"Table entry attribute for lbShuntByteIpv6AddrExt"
	::={lbShuntByteIpv6AddrExtLevelEntry 2}

lbShuntByteIpv6AddrExtLevelMom OBJECT-TYPE
	SYNTAX	 CounterBasedGauge64
	MAX-ACCESS  read-only
	STATUS      current
	DESCRIPTION
	"Table entry attribute for lbShuntByteIpv6AddrExt"
	::={lbShuntByteIpv6AddrExtLevelEntry 3}

lbShuntByteIpv6AddrExtLevelMax OBJECT-TYPE
	SYNTAX	 CounterBasedGauge64
	MAX-ACCESS  read-only
	STATUS      current
	DESCRIPTION
	"Table entry attribute for lbShuntByteIpv6AddrExt"
	::={lbShuntByteIpv6AddrExtLevelEntry 4}


lbLogicalFp	OBJECT IDENTIFIER ::={lb 45}

lbLogicalFpVal	OBJECT-TYPE
	SYNTAX	 Unsigned32
	MAX-ACCESS read-only
	STATUS current
	DESCRIPTION "Logical ID"

	::={lbLogicalFp 1}

lbLogicalFpMax	OBJECT-TYPE
	SYNTAX	 Unsigned32
	MAX-ACCESS read-only
	STATUS current
	DESCRIPTION "Logical ID"

	::={lbLogicalFp 3}

lbLogicalFpLevelTable OBJECT-TYPE
	SYNTAX      SEQUENCE OF LbLogicalFpLevelEntry
	MAX-ACCESS  not-accessible
	STATUS      current
	DESCRIPTION
	"Table for lbLogicalFp"
	::={lbLogicalFp 4}

lbLogicalFpLevelEntry OBJECT-TYPE
	SYNTAX      LbLogicalFpLevelEntry
	MAX-ACCESS  not-accessible
	STATUS      current
	DESCRIPTION
	"Table entry for lbLogicalFp"
	INDEX { lbLogicalFpLevelName }
	::={lbLogicalFpLevelTable 1}

LbLogicalFpLevelEntry ::=
	SEQUENCE {
		lbLogicalFpLevelName	DisplayString,
		lbLogicalFpLevelVal	Unsigned32,
		lbLogicalFpLevelMax	Unsigned32
	}

lbLogicalFpLevelName OBJECT-TYPE
	SYNTAX      DisplayString
	MAX-ACCESS  not-accessible
	STATUS      current
	DESCRIPTION
	"Table entry display string for lbLogicalFp"
	::={lbLogicalFpLevelEntry 1}

lbLogicalFpLevelVal OBJECT-TYPE
	SYNTAX	 Unsigned32
	MAX-ACCESS  read-only
	STATUS      current
	DESCRIPTION
	"Table entry attribute for lbLogicalFp"
	::={lbLogicalFpLevelEntry 2}

lbLogicalFpLevelMax OBJECT-TYPE
	SYNTAX	 Unsigned32
	MAX-ACCESS  read-only
	STATUS      current
	DESCRIPTION
	"Table entry attribute for lbLogicalFp"
	::={lbLogicalFpLevelEntry 4}


lbTxFs	OBJECT IDENTIFIER ::={lb 46}

lbTxFsVal	OBJECT-TYPE
	SYNTAX	 Counter64
	MAX-ACCESS read-only
	STATUS current
	DESCRIPTION "TX packets FP flowsync"

	::={lbTxFs 1}

lbTxFsMom	OBJECT-TYPE
	SYNTAX	 CounterBasedGauge64
	MAX-ACCESS read-only
	STATUS current
	DESCRIPTION "TX packets FP flowsync"

	::={lbTxFs 2}

lbTxFsMax	OBJECT-TYPE
	SYNTAX	 CounterBasedGauge64
	MAX-ACCESS read-only
	STATUS current
	DESCRIPTION "TX packets FP flowsync"

	::={lbTxFs 3}

lbTxFsLevelTable OBJECT-TYPE
	SYNTAX      SEQUENCE OF LbTxFsLevelEntry
	MAX-ACCESS  not-accessible
	STATUS      current
	DESCRIPTION
	"Table for lbTxFs"
	::={lbTxFs 4}

lbTxFsLevelEntry OBJECT-TYPE
	SYNTAX      LbTxFsLevelEntry
	MAX-ACCESS  not-accessible
	STATUS      current
	DESCRIPTION
	"Table entry for lbTxFs"
	INDEX { lbTxFsLevelName }
	::={lbTxFsLevelTable 1}

LbTxFsLevelEntry ::=
	SEQUENCE {
		lbTxFsLevelName	DisplayString,
		lbTxFsLevelVal	Counter64,
		lbTxFsLevelMom	CounterBasedGauge64,
		lbTxFsLevelMax	CounterBasedGauge64
	}

lbTxFsLevelName OBJECT-TYPE
	SYNTAX      DisplayString
	MAX-ACCESS  not-accessible
	STATUS      current
	DESCRIPTION
	"Table entry display string for lbTxFs"
	::={lbTxFsLevelEntry 1}

lbTxFsLevelVal OBJECT-TYPE
	SYNTAX	 Counter64
	MAX-ACCESS  read-only
	STATUS      current
	DESCRIPTION
	"Table entry attribute for lbTxFs"
	::={lbTxFsLevelEntry 2}

lbTxFsLevelMom OBJECT-TYPE
	SYNTAX	 CounterBasedGauge64
	MAX-ACCESS  read-only
	STATUS      current
	DESCRIPTION
	"Table entry attribute for lbTxFs"
	::={lbTxFsLevelEntry 3}

lbTxFsLevelMax OBJECT-TYPE
	SYNTAX	 CounterBasedGauge64
	MAX-ACCESS  read-only
	STATUS      current
	DESCRIPTION
	"Table entry attribute for lbTxFs"
	::={lbTxFsLevelEntry 4}


lbTxFpInt	OBJECT IDENTIFIER ::={lb 47}

lbTxFpIntVal	OBJECT-TYPE
	SYNTAX	 Counter64
	MAX-ACCESS read-only
	STATUS current
	DESCRIPTION "TX packets FP internal"

	::={lbTxFpInt 1}

lbTxFpIntMom	OBJECT-TYPE
	SYNTAX	 CounterBasedGauge64
	MAX-ACCESS read-only
	STATUS current
	DESCRIPTION "TX packets FP internal"

	::={lbTxFpInt 2}

lbTxFpIntMax	OBJECT-TYPE
	SYNTAX	 CounterBasedGauge64
	MAX-ACCESS read-only
	STATUS current
	DESCRIPTION "TX packets FP internal"

	::={lbTxFpInt 3}

lbTxFpIntLevelTable OBJECT-TYPE
	SYNTAX      SEQUENCE OF LbTxFpIntLevelEntry
	MAX-ACCESS  not-accessible
	STATUS      current
	DESCRIPTION
	"Table for lbTxFpInt"
	::={lbTxFpInt 4}

lbTxFpIntLevelEntry OBJECT-TYPE
	SYNTAX      LbTxFpIntLevelEntry
	MAX-ACCESS  not-accessible
	STATUS      current
	DESCRIPTION
	"Table entry for lbTxFpInt"
	INDEX { lbTxFpIntLevelName }
	::={lbTxFpIntLevelTable 1}

LbTxFpIntLevelEntry ::=
	SEQUENCE {
		lbTxFpIntLevelName	DisplayString,
		lbTxFpIntLevelVal	Counter64,
		lbTxFpIntLevelMom	CounterBasedGauge64,
		lbTxFpIntLevelMax	CounterBasedGauge64
	}

lbTxFpIntLevelName OBJECT-TYPE
	SYNTAX      DisplayString
	MAX-ACCESS  not-accessible
	STATUS      current
	DESCRIPTION
	"Table entry display string for lbTxFpInt"
	::={lbTxFpIntLevelEntry 1}

lbTxFpIntLevelVal OBJECT-TYPE
	SYNTAX	 Counter64
	MAX-ACCESS  read-only
	STATUS      current
	DESCRIPTION
	"Table entry attribute for lbTxFpInt"
	::={lbTxFpIntLevelEntry 2}

lbTxFpIntLevelMom OBJECT-TYPE
	SYNTAX	 CounterBasedGauge64
	MAX-ACCESS  read-only
	STATUS      current
	DESCRIPTION
	"Table entry attribute for lbTxFpInt"
	::={lbTxFpIntLevelEntry 3}

lbTxFpIntLevelMax OBJECT-TYPE
	SYNTAX	 CounterBasedGauge64
	MAX-ACCESS  read-only
	STATUS      current
	DESCRIPTION
	"Table entry attribute for lbTxFpInt"
	::={lbTxFpIntLevelEntry 4}


lbTxFpExt	OBJECT IDENTIFIER ::={lb 48}

lbTxFpExtVal	OBJECT-TYPE
	SYNTAX	 Counter64
	MAX-ACCESS read-only
	STATUS current
	DESCRIPTION "TX packets FP external"

	::={lbTxFpExt 1}

lbTxFpExtMom	OBJECT-TYPE
	SYNTAX	 CounterBasedGauge64
	MAX-ACCESS read-only
	STATUS current
	DESCRIPTION "TX packets FP external"

	::={lbTxFpExt 2}

lbTxFpExtMax	OBJECT-TYPE
	SYNTAX	 CounterBasedGauge64
	MAX-ACCESS read-only
	STATUS current
	DESCRIPTION "TX packets FP external"

	::={lbTxFpExt 3}

lbTxFpExtLevelTable OBJECT-TYPE
	SYNTAX      SEQUENCE OF LbTxFpExtLevelEntry
	MAX-ACCESS  not-accessible
	STATUS      current
	DESCRIPTION
	"Table for lbTxFpExt"
	::={lbTxFpExt 4}

lbTxFpExtLevelEntry OBJECT-TYPE
	SYNTAX      LbTxFpExtLevelEntry
	MAX-ACCESS  not-accessible
	STATUS      current
	DESCRIPTION
	"Table entry for lbTxFpExt"
	INDEX { lbTxFpExtLevelName }
	::={lbTxFpExtLevelTable 1}

LbTxFpExtLevelEntry ::=
	SEQUENCE {
		lbTxFpExtLevelName	DisplayString,
		lbTxFpExtLevelVal	Counter64,
		lbTxFpExtLevelMom	CounterBasedGauge64,
		lbTxFpExtLevelMax	CounterBasedGauge64
	}

lbTxFpExtLevelName OBJECT-TYPE
	SYNTAX      DisplayString
	MAX-ACCESS  not-accessible
	STATUS      current
	DESCRIPTION
	"Table entry display string for lbTxFpExt"
	::={lbTxFpExtLevelEntry 1}

lbTxFpExtLevelVal OBJECT-TYPE
	SYNTAX	 Counter64
	MAX-ACCESS  read-only
	STATUS      current
	DESCRIPTION
	"Table entry attribute for lbTxFpExt"
	::={lbTxFpExtLevelEntry 2}

lbTxFpExtLevelMom OBJECT-TYPE
	SYNTAX	 CounterBasedGauge64
	MAX-ACCESS  read-only
	STATUS      current
	DESCRIPTION
	"Table entry attribute for lbTxFpExt"
	::={lbTxFpExtLevelEntry 3}

lbTxFpExtLevelMax OBJECT-TYPE
	SYNTAX	 CounterBasedGauge64
	MAX-ACCESS  read-only
	STATUS      current
	DESCRIPTION
	"Table entry attribute for lbTxFpExt"
	::={lbTxFpExtLevelEntry 4}


lbHbLost	OBJECT IDENTIFIER ::={lb 49}

lbHbLostVal	OBJECT-TYPE
	SYNTAX	 Counter64
	MAX-ACCESS read-only
	STATUS current
	DESCRIPTION "Heartbeat packets lost"

	::={lbHbLost 1}

lbHbLostMom	OBJECT-TYPE
	SYNTAX	 CounterBasedGauge64
	MAX-ACCESS read-only
	STATUS current
	DESCRIPTION "Heartbeat packets lost"

	::={lbHbLost 2}

lbHbLostMax	OBJECT-TYPE
	SYNTAX	 CounterBasedGauge64
	MAX-ACCESS read-only
	STATUS current
	DESCRIPTION "Heartbeat packets lost"

	::={lbHbLost 3}

lbHbLostLevelTable OBJECT-TYPE
	SYNTAX      SEQUENCE OF LbHbLostLevelEntry
	MAX-ACCESS  not-accessible
	STATUS      current
	DESCRIPTION
	"Table for lbHbLost"
	::={lbHbLost 4}

lbHbLostLevelEntry OBJECT-TYPE
	SYNTAX      LbHbLostLevelEntry
	MAX-ACCESS  not-accessible
	STATUS      current
	DESCRIPTION
	"Table entry for lbHbLost"
	INDEX { lbHbLostLevelName }
	::={lbHbLostLevelTable 1}

LbHbLostLevelEntry ::=
	SEQUENCE {
		lbHbLostLevelName	DisplayString,
		lbHbLostLevelVal	Counter64,
		lbHbLostLevelMom	CounterBasedGauge64,
		lbHbLostLevelMax	CounterBasedGauge64
	}

lbHbLostLevelName OBJECT-TYPE
	SYNTAX      DisplayString
	MAX-ACCESS  not-accessible
	STATUS      current
	DESCRIPTION
	"Table entry display string for lbHbLost"
	::={lbHbLostLevelEntry 1}

lbHbLostLevelVal OBJECT-TYPE
	SYNTAX	 Counter64
	MAX-ACCESS  read-only
	STATUS      current
	DESCRIPTION
	"Table entry attribute for lbHbLost"
	::={lbHbLostLevelEntry 2}

lbHbLostLevelMom OBJECT-TYPE
	SYNTAX	 CounterBasedGauge64
	MAX-ACCESS  read-only
	STATUS      current
	DESCRIPTION
	"Table entry attribute for lbHbLost"
	::={lbHbLostLevelEntry 3}

lbHbLostLevelMax OBJECT-TYPE
	SYNTAX	 CounterBasedGauge64
	MAX-ACCESS  read-only
	STATUS      current
	DESCRIPTION
	"Table entry attribute for lbHbLost"
	::={lbHbLostLevelEntry 4}


lbBucketMoves	OBJECT IDENTIFIER ::={lb 50}

lbBucketMovesVal	OBJECT-TYPE
	SYNTAX	 Counter64
	MAX-ACCESS read-only
	STATUS current
	DESCRIPTION "Moved buckets"

	::={lbBucketMoves 1}

lbBucketMovesMom	OBJECT-TYPE
	SYNTAX	 CounterBasedGauge64
	MAX-ACCESS read-only
	STATUS current
	DESCRIPTION "Moved buckets"

	::={lbBucketMoves 2}

lbBucketMovesMax	OBJECT-TYPE
	SYNTAX	 CounterBasedGauge64
	MAX-ACCESS read-only
	STATUS current
	DESCRIPTION "Moved buckets"

	::={lbBucketMoves 3}

lbBucketMovesLevelTable OBJECT-TYPE
	SYNTAX      SEQUENCE OF LbBucketMovesLevelEntry
	MAX-ACCESS  not-accessible
	STATUS      current
	DESCRIPTION
	"Table for lbBucketMoves"
	::={lbBucketMoves 4}

lbBucketMovesLevelEntry OBJECT-TYPE
	SYNTAX      LbBucketMovesLevelEntry
	MAX-ACCESS  not-accessible
	STATUS      current
	DESCRIPTION
	"Table entry for lbBucketMoves"
	INDEX { lbBucketMovesLevelName }
	::={lbBucketMovesLevelTable 1}

LbBucketMovesLevelEntry ::=
	SEQUENCE {
		lbBucketMovesLevelName	DisplayString,
		lbBucketMovesLevelVal	Counter64,
		lbBucketMovesLevelMom	CounterBasedGauge64,
		lbBucketMovesLevelMax	CounterBasedGauge64
	}

lbBucketMovesLevelName OBJECT-TYPE
	SYNTAX      DisplayString
	MAX-ACCESS  not-accessible
	STATUS      current
	DESCRIPTION
	"Table entry display string for lbBucketMoves"
	::={lbBucketMovesLevelEntry 1}

lbBucketMovesLevelVal OBJECT-TYPE
	SYNTAX	 Counter64
	MAX-ACCESS  read-only
	STATUS      current
	DESCRIPTION
	"Table entry attribute for lbBucketMoves"
	::={lbBucketMovesLevelEntry 2}

lbBucketMovesLevelMom OBJECT-TYPE
	SYNTAX	 CounterBasedGauge64
	MAX-ACCESS  read-only
	STATUS      current
	DESCRIPTION
	"Table entry attribute for lbBucketMoves"
	::={lbBucketMovesLevelEntry 3}

lbBucketMovesLevelMax OBJECT-TYPE
	SYNTAX	 CounterBasedGauge64
	MAX-ACCESS  read-only
	STATUS      current
	DESCRIPTION
	"Table entry attribute for lbBucketMoves"
	::={lbBucketMovesLevelEntry 4}


lbBlacklistedBuckets	OBJECT IDENTIFIER ::={lb 51}

lbBlacklistedBucketsVal	OBJECT-TYPE
	SYNTAX	 CounterBasedGauge64
	MAX-ACCESS read-only
	STATUS current
	DESCRIPTION "Blacklisted buckets"

	::={lbBlacklistedBuckets 1}

lbBlacklistedBucketsMax	OBJECT-TYPE
	SYNTAX	 CounterBasedGauge64
	MAX-ACCESS read-only
	STATUS current
	DESCRIPTION "Blacklisted buckets"

	::={lbBlacklistedBuckets 3}

lbBlacklistedBucketsLevelTable OBJECT-TYPE
	SYNTAX      SEQUENCE OF LbBlacklistedBucketsLevelEntry
	MAX-ACCESS  not-accessible
	STATUS      current
	DESCRIPTION
	"Table for lbBlacklistedBuckets"
	::={lbBlacklistedBuckets 4}

lbBlacklistedBucketsLevelEntry OBJECT-TYPE
	SYNTAX      LbBlacklistedBucketsLevelEntry
	MAX-ACCESS  not-accessible
	STATUS      current
	DESCRIPTION
	"Table entry for lbBlacklistedBuckets"
	INDEX { lbBlacklistedBucketsLevelName }
	::={lbBlacklistedBucketsLevelTable 1}

LbBlacklistedBucketsLevelEntry ::=
	SEQUENCE {
		lbBlacklistedBucketsLevelName	DisplayString,
		lbBlacklistedBucketsLevelVal	CounterBasedGauge64,
		lbBlacklistedBucketsLevelMax	CounterBasedGauge64
	}

lbBlacklistedBucketsLevelName OBJECT-TYPE
	SYNTAX      DisplayString
	MAX-ACCESS  not-accessible
	STATUS      current
	DESCRIPTION
	"Table entry display string for lbBlacklistedBuckets"
	::={lbBlacklistedBucketsLevelEntry 1}

lbBlacklistedBucketsLevelVal OBJECT-TYPE
	SYNTAX	 CounterBasedGauge64
	MAX-ACCESS  read-only
	STATUS      current
	DESCRIPTION
	"Table entry attribute for lbBlacklistedBuckets"
	::={lbBlacklistedBucketsLevelEntry 2}

lbBlacklistedBucketsLevelMax OBJECT-TYPE
	SYNTAX	 CounterBasedGauge64
	MAX-ACCESS  read-only
	STATUS      current
	DESCRIPTION
	"Table entry attribute for lbBlacklistedBuckets"
	::={lbBlacklistedBucketsLevelEntry 4}


lbBlacklistedPackets	OBJECT IDENTIFIER ::={lb 52}

lbBlacklistedPacketsVal	OBJECT-TYPE
	SYNTAX	 Counter64
	MAX-ACCESS read-only
	STATUS current
	DESCRIPTION "Blacklisted packets"

	::={lbBlacklistedPackets 1}

lbBlacklistedPacketsMom	OBJECT-TYPE
	SYNTAX	 CounterBasedGauge64
	MAX-ACCESS read-only
	STATUS current
	DESCRIPTION "Blacklisted packets"

	::={lbBlacklistedPackets 2}

lbBlacklistedPacketsMax	OBJECT-TYPE
	SYNTAX	 CounterBasedGauge64
	MAX-ACCESS read-only
	STATUS current
	DESCRIPTION "Blacklisted packets"

	::={lbBlacklistedPackets 3}

lbBlacklistedPacketsLevelTable OBJECT-TYPE
	SYNTAX      SEQUENCE OF LbBlacklistedPacketsLevelEntry
	MAX-ACCESS  not-accessible
	STATUS      current
	DESCRIPTION
	"Table for lbBlacklistedPackets"
	::={lbBlacklistedPackets 4}

lbBlacklistedPacketsLevelEntry OBJECT-TYPE
	SYNTAX      LbBlacklistedPacketsLevelEntry
	MAX-ACCESS  not-accessible
	STATUS      current
	DESCRIPTION
	"Table entry for lbBlacklistedPackets"
	INDEX { lbBlacklistedPacketsLevelName }
	::={lbBlacklistedPacketsLevelTable 1}

LbBlacklistedPacketsLevelEntry ::=
	SEQUENCE {
		lbBlacklistedPacketsLevelName	DisplayString,
		lbBlacklistedPacketsLevelVal	Counter64,
		lbBlacklistedPacketsLevelMom	CounterBasedGauge64,
		lbBlacklistedPacketsLevelMax	CounterBasedGauge64
	}

lbBlacklistedPacketsLevelName OBJECT-TYPE
	SYNTAX      DisplayString
	MAX-ACCESS  not-accessible
	STATUS      current
	DESCRIPTION
	"Table entry display string for lbBlacklistedPackets"
	::={lbBlacklistedPacketsLevelEntry 1}

lbBlacklistedPacketsLevelVal OBJECT-TYPE
	SYNTAX	 Counter64
	MAX-ACCESS  read-only
	STATUS      current
	DESCRIPTION
	"Table entry attribute for lbBlacklistedPackets"
	::={lbBlacklistedPacketsLevelEntry 2}

lbBlacklistedPacketsLevelMom OBJECT-TYPE
	SYNTAX	 CounterBasedGauge64
	MAX-ACCESS  read-only
	STATUS      current
	DESCRIPTION
	"Table entry attribute for lbBlacklistedPackets"
	::={lbBlacklistedPacketsLevelEntry 3}

lbBlacklistedPacketsLevelMax OBJECT-TYPE
	SYNTAX	 CounterBasedGauge64
	MAX-ACCESS  read-only
	STATUS      current
	DESCRIPTION
	"Table entry attribute for lbBlacklistedPackets"
	::={lbBlacklistedPacketsLevelEntry 4}


lbRxDropsInt	OBJECT IDENTIFIER ::={lb 53}

lbRxDropsIntVal	OBJECT-TYPE
	SYNTAX	 Counter64
	MAX-ACCESS read-only
	STATUS current
	DESCRIPTION "RX drops internal"

	::={lbRxDropsInt 1}

lbRxDropsIntMom	OBJECT-TYPE
	SYNTAX	 CounterBasedGauge64
	MAX-ACCESS read-only
	STATUS current
	DESCRIPTION "RX drops internal"

	::={lbRxDropsInt 2}

lbRxDropsIntMax	OBJECT-TYPE
	SYNTAX	 CounterBasedGauge64
	MAX-ACCESS read-only
	STATUS current
	DESCRIPTION "RX drops internal"

	::={lbRxDropsInt 3}

lbRxDropsIntLevelTable OBJECT-TYPE
	SYNTAX      SEQUENCE OF LbRxDropsIntLevelEntry
	MAX-ACCESS  not-accessible
	STATUS      current
	DESCRIPTION
	"Table for lbRxDropsInt"
	::={lbRxDropsInt 4}

lbRxDropsIntLevelEntry OBJECT-TYPE
	SYNTAX      LbRxDropsIntLevelEntry
	MAX-ACCESS  not-accessible
	STATUS      current
	DESCRIPTION
	"Table entry for lbRxDropsInt"
	INDEX { lbRxDropsIntLevelName }
	::={lbRxDropsIntLevelTable 1}

LbRxDropsIntLevelEntry ::=
	SEQUENCE {
		lbRxDropsIntLevelName	DisplayString,
		lbRxDropsIntLevelVal	Counter64,
		lbRxDropsIntLevelMom	CounterBasedGauge64,
		lbRxDropsIntLevelMax	CounterBasedGauge64
	}

lbRxDropsIntLevelName OBJECT-TYPE
	SYNTAX      DisplayString
	MAX-ACCESS  not-accessible
	STATUS      current
	DESCRIPTION
	"Table entry display string for lbRxDropsInt"
	::={lbRxDropsIntLevelEntry 1}

lbRxDropsIntLevelVal OBJECT-TYPE
	SYNTAX	 Counter64
	MAX-ACCESS  read-only
	STATUS      current
	DESCRIPTION
	"Table entry attribute for lbRxDropsInt"
	::={lbRxDropsIntLevelEntry 2}

lbRxDropsIntLevelMom OBJECT-TYPE
	SYNTAX	 CounterBasedGauge64
	MAX-ACCESS  read-only
	STATUS      current
	DESCRIPTION
	"Table entry attribute for lbRxDropsInt"
	::={lbRxDropsIntLevelEntry 3}

lbRxDropsIntLevelMax OBJECT-TYPE
	SYNTAX	 CounterBasedGauge64
	MAX-ACCESS  read-only
	STATUS      current
	DESCRIPTION
	"Table entry attribute for lbRxDropsInt"
	::={lbRxDropsIntLevelEntry 4}


lbRxDropsExt	OBJECT IDENTIFIER ::={lb 54}

lbRxDropsExtVal	OBJECT-TYPE
	SYNTAX	 Counter64
	MAX-ACCESS read-only
	STATUS current
	DESCRIPTION "RX drops external"

	::={lbRxDropsExt 1}

lbRxDropsExtMom	OBJECT-TYPE
	SYNTAX	 CounterBasedGauge64
	MAX-ACCESS read-only
	STATUS current
	DESCRIPTION "RX drops external"

	::={lbRxDropsExt 2}

lbRxDropsExtMax	OBJECT-TYPE
	SYNTAX	 CounterBasedGauge64
	MAX-ACCESS read-only
	STATUS current
	DESCRIPTION "RX drops external"

	::={lbRxDropsExt 3}

lbRxDropsExtLevelTable OBJECT-TYPE
	SYNTAX      SEQUENCE OF LbRxDropsExtLevelEntry
	MAX-ACCESS  not-accessible
	STATUS      current
	DESCRIPTION
	"Table for lbRxDropsExt"
	::={lbRxDropsExt 4}

lbRxDropsExtLevelEntry OBJECT-TYPE
	SYNTAX      LbRxDropsExtLevelEntry
	MAX-ACCESS  not-accessible
	STATUS      current
	DESCRIPTION
	"Table entry for lbRxDropsExt"
	INDEX { lbRxDropsExtLevelName }
	::={lbRxDropsExtLevelTable 1}

LbRxDropsExtLevelEntry ::=
	SEQUENCE {
		lbRxDropsExtLevelName	DisplayString,
		lbRxDropsExtLevelVal	Counter64,
		lbRxDropsExtLevelMom	CounterBasedGauge64,
		lbRxDropsExtLevelMax	CounterBasedGauge64
	}

lbRxDropsExtLevelName OBJECT-TYPE
	SYNTAX      DisplayString
	MAX-ACCESS  not-accessible
	STATUS      current
	DESCRIPTION
	"Table entry display string for lbRxDropsExt"
	::={lbRxDropsExtLevelEntry 1}

lbRxDropsExtLevelVal OBJECT-TYPE
	SYNTAX	 Counter64
	MAX-ACCESS  read-only
	STATUS      current
	DESCRIPTION
	"Table entry attribute for lbRxDropsExt"
	::={lbRxDropsExtLevelEntry 2}

lbRxDropsExtLevelMom OBJECT-TYPE
	SYNTAX	 CounterBasedGauge64
	MAX-ACCESS  read-only
	STATUS      current
	DESCRIPTION
	"Table entry attribute for lbRxDropsExt"
	::={lbRxDropsExtLevelEntry 3}

lbRxDropsExtLevelMax OBJECT-TYPE
	SYNTAX	 CounterBasedGauge64
	MAX-ACCESS  read-only
	STATUS      current
	DESCRIPTION
	"Table entry attribute for lbRxDropsExt"
	::={lbRxDropsExtLevelEntry 4}


lbLbChanTxInt	OBJECT IDENTIFIER ::={lb 55}

lbLbChanTxIntVal	OBJECT-TYPE
	SYNTAX	 Counter64
	MAX-ACCESS read-only
	STATUS current
	DESCRIPTION "TX packets SFP channel internal"

	::={lbLbChanTxInt 1}

lbLbChanTxIntMom	OBJECT-TYPE
	SYNTAX	 CounterBasedGauge64
	MAX-ACCESS read-only
	STATUS current
	DESCRIPTION "TX packets SFP channel internal"

	::={lbLbChanTxInt 2}

lbLbChanTxIntMax	OBJECT-TYPE
	SYNTAX	 CounterBasedGauge64
	MAX-ACCESS read-only
	STATUS current
	DESCRIPTION "TX packets SFP channel internal"

	::={lbLbChanTxInt 3}

lbLbChanTxIntLevelTable OBJECT-TYPE
	SYNTAX      SEQUENCE OF LbLbChanTxIntLevelEntry
	MAX-ACCESS  not-accessible
	STATUS      current
	DESCRIPTION
	"Table for lbLbChanTxInt"
	::={lbLbChanTxInt 4}

lbLbChanTxIntLevelEntry OBJECT-TYPE
	SYNTAX      LbLbChanTxIntLevelEntry
	MAX-ACCESS  not-accessible
	STATUS      current
	DESCRIPTION
	"Table entry for lbLbChanTxInt"
	INDEX { lbLbChanTxIntLevelName }
	::={lbLbChanTxIntLevelTable 1}

LbLbChanTxIntLevelEntry ::=
	SEQUENCE {
		lbLbChanTxIntLevelName	DisplayString,
		lbLbChanTxIntLevelVal	Counter64,
		lbLbChanTxIntLevelMom	CounterBasedGauge64,
		lbLbChanTxIntLevelMax	CounterBasedGauge64
	}

lbLbChanTxIntLevelName OBJECT-TYPE
	SYNTAX      DisplayString
	MAX-ACCESS  not-accessible
	STATUS      current
	DESCRIPTION
	"Table entry display string for lbLbChanTxInt"
	::={lbLbChanTxIntLevelEntry 1}

lbLbChanTxIntLevelVal OBJECT-TYPE
	SYNTAX	 Counter64
	MAX-ACCESS  read-only
	STATUS      current
	DESCRIPTION
	"Table entry attribute for lbLbChanTxInt"
	::={lbLbChanTxIntLevelEntry 2}

lbLbChanTxIntLevelMom OBJECT-TYPE
	SYNTAX	 CounterBasedGauge64
	MAX-ACCESS  read-only
	STATUS      current
	DESCRIPTION
	"Table entry attribute for lbLbChanTxInt"
	::={lbLbChanTxIntLevelEntry 3}

lbLbChanTxIntLevelMax OBJECT-TYPE
	SYNTAX	 CounterBasedGauge64
	MAX-ACCESS  read-only
	STATUS      current
	DESCRIPTION
	"Table entry attribute for lbLbChanTxInt"
	::={lbLbChanTxIntLevelEntry 4}


lbLbChanTxExt	OBJECT IDENTIFIER ::={lb 56}

lbLbChanTxExtVal	OBJECT-TYPE
	SYNTAX	 Counter64
	MAX-ACCESS read-only
	STATUS current
	DESCRIPTION "TX packets SFP channel external"

	::={lbLbChanTxExt 1}

lbLbChanTxExtMom	OBJECT-TYPE
	SYNTAX	 CounterBasedGauge64
	MAX-ACCESS read-only
	STATUS current
	DESCRIPTION "TX packets SFP channel external"

	::={lbLbChanTxExt 2}

lbLbChanTxExtMax	OBJECT-TYPE
	SYNTAX	 CounterBasedGauge64
	MAX-ACCESS read-only
	STATUS current
	DESCRIPTION "TX packets SFP channel external"

	::={lbLbChanTxExt 3}

lbLbChanTxExtLevelTable OBJECT-TYPE
	SYNTAX      SEQUENCE OF LbLbChanTxExtLevelEntry
	MAX-ACCESS  not-accessible
	STATUS      current
	DESCRIPTION
	"Table for lbLbChanTxExt"
	::={lbLbChanTxExt 4}

lbLbChanTxExtLevelEntry OBJECT-TYPE
	SYNTAX      LbLbChanTxExtLevelEntry
	MAX-ACCESS  not-accessible
	STATUS      current
	DESCRIPTION
	"Table entry for lbLbChanTxExt"
	INDEX { lbLbChanTxExtLevelName }
	::={lbLbChanTxExtLevelTable 1}

LbLbChanTxExtLevelEntry ::=
	SEQUENCE {
		lbLbChanTxExtLevelName	DisplayString,
		lbLbChanTxExtLevelVal	Counter64,
		lbLbChanTxExtLevelMom	CounterBasedGauge64,
		lbLbChanTxExtLevelMax	CounterBasedGauge64
	}

lbLbChanTxExtLevelName OBJECT-TYPE
	SYNTAX      DisplayString
	MAX-ACCESS  not-accessible
	STATUS      current
	DESCRIPTION
	"Table entry display string for lbLbChanTxExt"
	::={lbLbChanTxExtLevelEntry 1}

lbLbChanTxExtLevelVal OBJECT-TYPE
	SYNTAX	 Counter64
	MAX-ACCESS  read-only
	STATUS      current
	DESCRIPTION
	"Table entry attribute for lbLbChanTxExt"
	::={lbLbChanTxExtLevelEntry 2}

lbLbChanTxExtLevelMom OBJECT-TYPE
	SYNTAX	 CounterBasedGauge64
	MAX-ACCESS  read-only
	STATUS      current
	DESCRIPTION
	"Table entry attribute for lbLbChanTxExt"
	::={lbLbChanTxExtLevelEntry 3}

lbLbChanTxExtLevelMax OBJECT-TYPE
	SYNTAX	 CounterBasedGauge64
	MAX-ACCESS  read-only
	STATUS      current
	DESCRIPTION
	"Table entry attribute for lbLbChanTxExt"
	::={lbLbChanTxExtLevelEntry 4}


lbCpuPowerSave	OBJECT IDENTIFIER ::={lb 57}

lbCpuPowerSaveVal	OBJECT-TYPE
	SYNTAX	 Unsigned32
	MAX-ACCESS read-only
	STATUS current
	DESCRIPTION "CPU power save"

	::={lbCpuPowerSave 1}

lbCpuPowerSaveMax	OBJECT-TYPE
	SYNTAX	 Unsigned32
	MAX-ACCESS read-only
	STATUS current
	DESCRIPTION "CPU power save"

	::={lbCpuPowerSave 3}

lbCpuPowerSaveLevelTable OBJECT-TYPE
	SYNTAX      SEQUENCE OF LbCpuPowerSaveLevelEntry
	MAX-ACCESS  not-accessible
	STATUS      current
	DESCRIPTION
	"Table for lbCpuPowerSave"
	::={lbCpuPowerSave 4}

lbCpuPowerSaveLevelEntry OBJECT-TYPE
	SYNTAX      LbCpuPowerSaveLevelEntry
	MAX-ACCESS  not-accessible
	STATUS      current
	DESCRIPTION
	"Table entry for lbCpuPowerSave"
	INDEX { lbCpuPowerSaveLevelName }
	::={lbCpuPowerSaveLevelTable 1}

LbCpuPowerSaveLevelEntry ::=
	SEQUENCE {
		lbCpuPowerSaveLevelName	DisplayString,
		lbCpuPowerSaveLevelVal	Unsigned32,
		lbCpuPowerSaveLevelMax	Unsigned32
	}

lbCpuPowerSaveLevelName OBJECT-TYPE
	SYNTAX      DisplayString
	MAX-ACCESS  not-accessible
	STATUS      current
	DESCRIPTION
	"Table entry display string for lbCpuPowerSave"
	::={lbCpuPowerSaveLevelEntry 1}

lbCpuPowerSaveLevelVal OBJECT-TYPE
	SYNTAX	 Unsigned32
	MAX-ACCESS  read-only
	STATUS      current
	DESCRIPTION
	"Table entry attribute for lbCpuPowerSave"
	::={lbCpuPowerSaveLevelEntry 2}

lbCpuPowerSaveLevelMax OBJECT-TYPE
	SYNTAX	 Unsigned32
	MAX-ACCESS  read-only
	STATUS      current
	DESCRIPTION
	"Table entry attribute for lbCpuPowerSave"
	::={lbCpuPowerSaveLevelEntry 4}


lbRespondingFpFabric1	OBJECT IDENTIFIER ::={lb 58}

lbRespondingFpFabric1Val	OBJECT-TYPE
	SYNTAX	 Unsigned32
	MAX-ACCESS read-only
	STATUS current
	DESCRIPTION "Responding flow processors (Fabric 1)"

	::={lbRespondingFpFabric1 1}

lbRespondingFpFabric1Max	OBJECT-TYPE
	SYNTAX	 Unsigned32
	MAX-ACCESS read-only
	STATUS current
	DESCRIPTION "Responding flow processors (Fabric 1)"

	::={lbRespondingFpFabric1 3}

lbRespondingFpFabric1LevelTable OBJECT-TYPE
	SYNTAX      SEQUENCE OF LbRespondingFpFabric1LevelEntry
	MAX-ACCESS  not-accessible
	STATUS      current
	DESCRIPTION
	"Table for lbRespondingFpFabric1"
	::={lbRespondingFpFabric1 4}

lbRespondingFpFabric1LevelEntry OBJECT-TYPE
	SYNTAX      LbRespondingFpFabric1LevelEntry
	MAX-ACCESS  not-accessible
	STATUS      current
	DESCRIPTION
	"Table entry for lbRespondingFpFabric1"
	INDEX { lbRespondingFpFabric1LevelName }
	::={lbRespondingFpFabric1LevelTable 1}

LbRespondingFpFabric1LevelEntry ::=
	SEQUENCE {
		lbRespondingFpFabric1LevelName	DisplayString,
		lbRespondingFpFabric1LevelVal	Unsigned32,
		lbRespondingFpFabric1LevelMax	Unsigned32
	}

lbRespondingFpFabric1LevelName OBJECT-TYPE
	SYNTAX      DisplayString
	MAX-ACCESS  not-accessible
	STATUS      current
	DESCRIPTION
	"Table entry display string for lbRespondingFpFabric1"
	::={lbRespondingFpFabric1LevelEntry 1}

lbRespondingFpFabric1LevelVal OBJECT-TYPE
	SYNTAX	 Unsigned32
	MAX-ACCESS  read-only
	STATUS      current
	DESCRIPTION
	"Table entry attribute for lbRespondingFpFabric1"
	::={lbRespondingFpFabric1LevelEntry 2}

lbRespondingFpFabric1LevelMax OBJECT-TYPE
	SYNTAX	 Unsigned32
	MAX-ACCESS  read-only
	STATUS      current
	DESCRIPTION
	"Table entry attribute for lbRespondingFpFabric1"
	::={lbRespondingFpFabric1LevelEntry 4}


lbRespondingFpFabric2	OBJECT IDENTIFIER ::={lb 59}

lbRespondingFpFabric2Val	OBJECT-TYPE
	SYNTAX	 Unsigned32
	MAX-ACCESS read-only
	STATUS current
	DESCRIPTION "Responding flow processors (Fabric 2)"

	::={lbRespondingFpFabric2 1}

lbRespondingFpFabric2Max	OBJECT-TYPE
	SYNTAX	 Unsigned32
	MAX-ACCESS read-only
	STATUS current
	DESCRIPTION "Responding flow processors (Fabric 2)"

	::={lbRespondingFpFabric2 3}

lbRespondingFpFabric2LevelTable OBJECT-TYPE
	SYNTAX      SEQUENCE OF LbRespondingFpFabric2LevelEntry
	MAX-ACCESS  not-accessible
	STATUS      current
	DESCRIPTION
	"Table for lbRespondingFpFabric2"
	::={lbRespondingFpFabric2 4}

lbRespondingFpFabric2LevelEntry OBJECT-TYPE
	SYNTAX      LbRespondingFpFabric2LevelEntry
	MAX-ACCESS  not-accessible
	STATUS      current
	DESCRIPTION
	"Table entry for lbRespondingFpFabric2"
	INDEX { lbRespondingFpFabric2LevelName }
	::={lbRespondingFpFabric2LevelTable 1}

LbRespondingFpFabric2LevelEntry ::=
	SEQUENCE {
		lbRespondingFpFabric2LevelName	DisplayString,
		lbRespondingFpFabric2LevelVal	Unsigned32,
		lbRespondingFpFabric2LevelMax	Unsigned32
	}

lbRespondingFpFabric2LevelName OBJECT-TYPE
	SYNTAX      DisplayString
	MAX-ACCESS  not-accessible
	STATUS      current
	DESCRIPTION
	"Table entry display string for lbRespondingFpFabric2"
	::={lbRespondingFpFabric2LevelEntry 1}

lbRespondingFpFabric2LevelVal OBJECT-TYPE
	SYNTAX	 Unsigned32
	MAX-ACCESS  read-only
	STATUS      current
	DESCRIPTION
	"Table entry attribute for lbRespondingFpFabric2"
	::={lbRespondingFpFabric2LevelEntry 2}

lbRespondingFpFabric2LevelMax OBJECT-TYPE
	SYNTAX	 Unsigned32
	MAX-ACCESS  read-only
	STATUS      current
	DESCRIPTION
	"Table entry attribute for lbRespondingFpFabric2"
	::={lbRespondingFpFabric2LevelEntry 4}


lbHbLostFabric1	OBJECT IDENTIFIER ::={lb 60}

lbHbLostFabric1Val	OBJECT-TYPE
	SYNTAX	 Counter64
	MAX-ACCESS read-only
	STATUS current
	DESCRIPTION "Heartbeat packets lost (Fabric 1)"

	::={lbHbLostFabric1 1}

lbHbLostFabric1Mom	OBJECT-TYPE
	SYNTAX	 CounterBasedGauge64
	MAX-ACCESS read-only
	STATUS current
	DESCRIPTION "Heartbeat packets lost (Fabric 1)"

	::={lbHbLostFabric1 2}

lbHbLostFabric1Max	OBJECT-TYPE
	SYNTAX	 CounterBasedGauge64
	MAX-ACCESS read-only
	STATUS current
	DESCRIPTION "Heartbeat packets lost (Fabric 1)"

	::={lbHbLostFabric1 3}

lbHbLostFabric1LevelTable OBJECT-TYPE
	SYNTAX      SEQUENCE OF LbHbLostFabric1LevelEntry
	MAX-ACCESS  not-accessible
	STATUS      current
	DESCRIPTION
	"Table for lbHbLostFabric1"
	::={lbHbLostFabric1 4}

lbHbLostFabric1LevelEntry OBJECT-TYPE
	SYNTAX      LbHbLostFabric1LevelEntry
	MAX-ACCESS  not-accessible
	STATUS      current
	DESCRIPTION
	"Table entry for lbHbLostFabric1"
	INDEX { lbHbLostFabric1LevelName }
	::={lbHbLostFabric1LevelTable 1}

LbHbLostFabric1LevelEntry ::=
	SEQUENCE {
		lbHbLostFabric1LevelName	DisplayString,
		lbHbLostFabric1LevelVal	Counter64,
		lbHbLostFabric1LevelMom	CounterBasedGauge64,
		lbHbLostFabric1LevelMax	CounterBasedGauge64
	}

lbHbLostFabric1LevelName OBJECT-TYPE
	SYNTAX      DisplayString
	MAX-ACCESS  not-accessible
	STATUS      current
	DESCRIPTION
	"Table entry display string for lbHbLostFabric1"
	::={lbHbLostFabric1LevelEntry 1}

lbHbLostFabric1LevelVal OBJECT-TYPE
	SYNTAX	 Counter64
	MAX-ACCESS  read-only
	STATUS      current
	DESCRIPTION
	"Table entry attribute for lbHbLostFabric1"
	::={lbHbLostFabric1LevelEntry 2}

lbHbLostFabric1LevelMom OBJECT-TYPE
	SYNTAX	 CounterBasedGauge64
	MAX-ACCESS  read-only
	STATUS      current
	DESCRIPTION
	"Table entry attribute for lbHbLostFabric1"
	::={lbHbLostFabric1LevelEntry 3}

lbHbLostFabric1LevelMax OBJECT-TYPE
	SYNTAX	 CounterBasedGauge64
	MAX-ACCESS  read-only
	STATUS      current
	DESCRIPTION
	"Table entry attribute for lbHbLostFabric1"
	::={lbHbLostFabric1LevelEntry 4}


lbHbLostFabric2	OBJECT IDENTIFIER ::={lb 61}

lbHbLostFabric2Val	OBJECT-TYPE
	SYNTAX	 Counter64
	MAX-ACCESS read-only
	STATUS current
	DESCRIPTION "Heartbeat packets lost (Fabric 2)"

	::={lbHbLostFabric2 1}

lbHbLostFabric2Mom	OBJECT-TYPE
	SYNTAX	 CounterBasedGauge64
	MAX-ACCESS read-only
	STATUS current
	DESCRIPTION "Heartbeat packets lost (Fabric 2)"

	::={lbHbLostFabric2 2}

lbHbLostFabric2Max	OBJECT-TYPE
	SYNTAX	 CounterBasedGauge64
	MAX-ACCESS read-only
	STATUS current
	DESCRIPTION "Heartbeat packets lost (Fabric 2)"

	::={lbHbLostFabric2 3}

lbHbLostFabric2LevelTable OBJECT-TYPE
	SYNTAX      SEQUENCE OF LbHbLostFabric2LevelEntry
	MAX-ACCESS  not-accessible
	STATUS      current
	DESCRIPTION
	"Table for lbHbLostFabric2"
	::={lbHbLostFabric2 4}

lbHbLostFabric2LevelEntry OBJECT-TYPE
	SYNTAX      LbHbLostFabric2LevelEntry
	MAX-ACCESS  not-accessible
	STATUS      current
	DESCRIPTION
	"Table entry for lbHbLostFabric2"
	INDEX { lbHbLostFabric2LevelName }
	::={lbHbLostFabric2LevelTable 1}

LbHbLostFabric2LevelEntry ::=
	SEQUENCE {
		lbHbLostFabric2LevelName	DisplayString,
		lbHbLostFabric2LevelVal	Counter64,
		lbHbLostFabric2LevelMom	CounterBasedGauge64,
		lbHbLostFabric2LevelMax	CounterBasedGauge64
	}

lbHbLostFabric2LevelName OBJECT-TYPE
	SYNTAX      DisplayString
	MAX-ACCESS  not-accessible
	STATUS      current
	DESCRIPTION
	"Table entry display string for lbHbLostFabric2"
	::={lbHbLostFabric2LevelEntry 1}

lbHbLostFabric2LevelVal OBJECT-TYPE
	SYNTAX	 Counter64
	MAX-ACCESS  read-only
	STATUS      current
	DESCRIPTION
	"Table entry attribute for lbHbLostFabric2"
	::={lbHbLostFabric2LevelEntry 2}

lbHbLostFabric2LevelMom OBJECT-TYPE
	SYNTAX	 CounterBasedGauge64
	MAX-ACCESS  read-only
	STATUS      current
	DESCRIPTION
	"Table entry attribute for lbHbLostFabric2"
	::={lbHbLostFabric2LevelEntry 3}

lbHbLostFabric2LevelMax OBJECT-TYPE
	SYNTAX	 CounterBasedGauge64
	MAX-ACCESS  read-only
	STATUS      current
	DESCRIPTION
	"Table entry attribute for lbHbLostFabric2"
	::={lbHbLostFabric2LevelEntry 4}


lbAllowedFabric	OBJECT IDENTIFIER ::={lb 62}

lbAllowedFabricVal	OBJECT-TYPE
	SYNTAX	 Unsigned32
	MAX-ACCESS read-only
	STATUS current
	DESCRIPTION "Fabrics allowed"

	::={lbAllowedFabric 1}

lbAllowedFabricMax	OBJECT-TYPE
	SYNTAX	 Unsigned32
	MAX-ACCESS read-only
	STATUS current
	DESCRIPTION "Fabrics allowed"

	::={lbAllowedFabric 3}

lbAllowedFabricLevelTable OBJECT-TYPE
	SYNTAX      SEQUENCE OF LbAllowedFabricLevelEntry
	MAX-ACCESS  not-accessible
	STATUS      current
	DESCRIPTION
	"Table for lbAllowedFabric"
	::={lbAllowedFabric 4}

lbAllowedFabricLevelEntry OBJECT-TYPE
	SYNTAX      LbAllowedFabricLevelEntry
	MAX-ACCESS  not-accessible
	STATUS      current
	DESCRIPTION
	"Table entry for lbAllowedFabric"
	INDEX { lbAllowedFabricLevelName }
	::={lbAllowedFabricLevelTable 1}

LbAllowedFabricLevelEntry ::=
	SEQUENCE {
		lbAllowedFabricLevelName	DisplayString,
		lbAllowedFabricLevelVal	Unsigned32,
		lbAllowedFabricLevelMax	Unsigned32
	}

lbAllowedFabricLevelName OBJECT-TYPE
	SYNTAX      DisplayString
	MAX-ACCESS  not-accessible
	STATUS      current
	DESCRIPTION
	"Table entry display string for lbAllowedFabric"
	::={lbAllowedFabricLevelEntry 1}

lbAllowedFabricLevelVal OBJECT-TYPE
	SYNTAX	 Unsigned32
	MAX-ACCESS  read-only
	STATUS      current
	DESCRIPTION
	"Table entry attribute for lbAllowedFabric"
	::={lbAllowedFabricLevelEntry 2}

lbAllowedFabricLevelMax OBJECT-TYPE
	SYNTAX	 Unsigned32
	MAX-ACCESS  read-only
	STATUS      current
	DESCRIPTION
	"Table entry attribute for lbAllowedFabric"
	::={lbAllowedFabricLevelEntry 4}


lbTxDirectIntNoTx	OBJECT IDENTIFIER ::={lb 63}

lbTxDirectIntNoTxVal	OBJECT-TYPE
	SYNTAX	 Counter64
	MAX-ACCESS read-only
	STATUS current
	DESCRIPTION "TX direct internal not allowed"

	::={lbTxDirectIntNoTx 1}

lbTxDirectIntNoTxMom	OBJECT-TYPE
	SYNTAX	 CounterBasedGauge64
	MAX-ACCESS read-only
	STATUS current
	DESCRIPTION "TX direct internal not allowed"

	::={lbTxDirectIntNoTx 2}

lbTxDirectIntNoTxMax	OBJECT-TYPE
	SYNTAX	 CounterBasedGauge64
	MAX-ACCESS read-only
	STATUS current
	DESCRIPTION "TX direct internal not allowed"

	::={lbTxDirectIntNoTx 3}

lbTxDirectIntNoTxLevelTable OBJECT-TYPE
	SYNTAX      SEQUENCE OF LbTxDirectIntNoTxLevelEntry
	MAX-ACCESS  not-accessible
	STATUS      current
	DESCRIPTION
	"Table for lbTxDirectIntNoTx"
	::={lbTxDirectIntNoTx 4}

lbTxDirectIntNoTxLevelEntry OBJECT-TYPE
	SYNTAX      LbTxDirectIntNoTxLevelEntry
	MAX-ACCESS  not-accessible
	STATUS      current
	DESCRIPTION
	"Table entry for lbTxDirectIntNoTx"
	INDEX { lbTxDirectIntNoTxLevelName }
	::={lbTxDirectIntNoTxLevelTable 1}

LbTxDirectIntNoTxLevelEntry ::=
	SEQUENCE {
		lbTxDirectIntNoTxLevelName	DisplayString,
		lbTxDirectIntNoTxLevelVal	Counter64,
		lbTxDirectIntNoTxLevelMom	CounterBasedGauge64,
		lbTxDirectIntNoTxLevelMax	CounterBasedGauge64
	}

lbTxDirectIntNoTxLevelName OBJECT-TYPE
	SYNTAX      DisplayString
	MAX-ACCESS  not-accessible
	STATUS      current
	DESCRIPTION
	"Table entry display string for lbTxDirectIntNoTx"
	::={lbTxDirectIntNoTxLevelEntry 1}

lbTxDirectIntNoTxLevelVal OBJECT-TYPE
	SYNTAX	 Counter64
	MAX-ACCESS  read-only
	STATUS      current
	DESCRIPTION
	"Table entry attribute for lbTxDirectIntNoTx"
	::={lbTxDirectIntNoTxLevelEntry 2}

lbTxDirectIntNoTxLevelMom OBJECT-TYPE
	SYNTAX	 CounterBasedGauge64
	MAX-ACCESS  read-only
	STATUS      current
	DESCRIPTION
	"Table entry attribute for lbTxDirectIntNoTx"
	::={lbTxDirectIntNoTxLevelEntry 3}

lbTxDirectIntNoTxLevelMax OBJECT-TYPE
	SYNTAX	 CounterBasedGauge64
	MAX-ACCESS  read-only
	STATUS      current
	DESCRIPTION
	"Table entry attribute for lbTxDirectIntNoTx"
	::={lbTxDirectIntNoTxLevelEntry 4}


lbTxDirectExtNoTx	OBJECT IDENTIFIER ::={lb 64}

lbTxDirectExtNoTxVal	OBJECT-TYPE
	SYNTAX	 Counter64
	MAX-ACCESS read-only
	STATUS current
	DESCRIPTION "TX direct external not allowed"

	::={lbTxDirectExtNoTx 1}

lbTxDirectExtNoTxMom	OBJECT-TYPE
	SYNTAX	 CounterBasedGauge64
	MAX-ACCESS read-only
	STATUS current
	DESCRIPTION "TX direct external not allowed"

	::={lbTxDirectExtNoTx 2}

lbTxDirectExtNoTxMax	OBJECT-TYPE
	SYNTAX	 CounterBasedGauge64
	MAX-ACCESS read-only
	STATUS current
	DESCRIPTION "TX direct external not allowed"

	::={lbTxDirectExtNoTx 3}

lbTxDirectExtNoTxLevelTable OBJECT-TYPE
	SYNTAX      SEQUENCE OF LbTxDirectExtNoTxLevelEntry
	MAX-ACCESS  not-accessible
	STATUS      current
	DESCRIPTION
	"Table for lbTxDirectExtNoTx"
	::={lbTxDirectExtNoTx 4}

lbTxDirectExtNoTxLevelEntry OBJECT-TYPE
	SYNTAX      LbTxDirectExtNoTxLevelEntry
	MAX-ACCESS  not-accessible
	STATUS      current
	DESCRIPTION
	"Table entry for lbTxDirectExtNoTx"
	INDEX { lbTxDirectExtNoTxLevelName }
	::={lbTxDirectExtNoTxLevelTable 1}

LbTxDirectExtNoTxLevelEntry ::=
	SEQUENCE {
		lbTxDirectExtNoTxLevelName	DisplayString,
		lbTxDirectExtNoTxLevelVal	Counter64,
		lbTxDirectExtNoTxLevelMom	CounterBasedGauge64,
		lbTxDirectExtNoTxLevelMax	CounterBasedGauge64
	}

lbTxDirectExtNoTxLevelName OBJECT-TYPE
	SYNTAX      DisplayString
	MAX-ACCESS  not-accessible
	STATUS      current
	DESCRIPTION
	"Table entry display string for lbTxDirectExtNoTx"
	::={lbTxDirectExtNoTxLevelEntry 1}

lbTxDirectExtNoTxLevelVal OBJECT-TYPE
	SYNTAX	 Counter64
	MAX-ACCESS  read-only
	STATUS      current
	DESCRIPTION
	"Table entry attribute for lbTxDirectExtNoTx"
	::={lbTxDirectExtNoTxLevelEntry 2}

lbTxDirectExtNoTxLevelMom OBJECT-TYPE
	SYNTAX	 CounterBasedGauge64
	MAX-ACCESS  read-only
	STATUS      current
	DESCRIPTION
	"Table entry attribute for lbTxDirectExtNoTx"
	::={lbTxDirectExtNoTxLevelEntry 3}

lbTxDirectExtNoTxLevelMax OBJECT-TYPE
	SYNTAX	 CounterBasedGauge64
	MAX-ACCESS  read-only
	STATUS      current
	DESCRIPTION
	"Table entry attribute for lbTxDirectExtNoTx"
	::={lbTxDirectExtNoTxLevelEntry 4}


lbPollSlotFatigue	OBJECT IDENTIFIER ::={lb 65}

lbPollSlotFatigueVal	OBJECT-TYPE
	SYNTAX	 Counter64
	MAX-ACCESS read-only
	STATUS current
	DESCRIPTION "Out of poll slots"

	::={lbPollSlotFatigue 1}

lbPollSlotFatigueMom	OBJECT-TYPE
	SYNTAX	 CounterBasedGauge64
	MAX-ACCESS read-only
	STATUS current
	DESCRIPTION "Out of poll slots"

	::={lbPollSlotFatigue 2}

lbPollSlotFatigueMax	OBJECT-TYPE
	SYNTAX	 CounterBasedGauge64
	MAX-ACCESS read-only
	STATUS current
	DESCRIPTION "Out of poll slots"

	::={lbPollSlotFatigue 3}

lbPollSlotFatigueLevelTable OBJECT-TYPE
	SYNTAX      SEQUENCE OF LbPollSlotFatigueLevelEntry
	MAX-ACCESS  not-accessible
	STATUS      current
	DESCRIPTION
	"Table for lbPollSlotFatigue"
	::={lbPollSlotFatigue 4}

lbPollSlotFatigueLevelEntry OBJECT-TYPE
	SYNTAX      LbPollSlotFatigueLevelEntry
	MAX-ACCESS  not-accessible
	STATUS      current
	DESCRIPTION
	"Table entry for lbPollSlotFatigue"
	INDEX { lbPollSlotFatigueLevelName }
	::={lbPollSlotFatigueLevelTable 1}

LbPollSlotFatigueLevelEntry ::=
	SEQUENCE {
		lbPollSlotFatigueLevelName	DisplayString,
		lbPollSlotFatigueLevelVal	Counter64,
		lbPollSlotFatigueLevelMom	CounterBasedGauge64,
		lbPollSlotFatigueLevelMax	CounterBasedGauge64
	}

lbPollSlotFatigueLevelName OBJECT-TYPE
	SYNTAX      DisplayString
	MAX-ACCESS  not-accessible
	STATUS      current
	DESCRIPTION
	"Table entry display string for lbPollSlotFatigue"
	::={lbPollSlotFatigueLevelEntry 1}

lbPollSlotFatigueLevelVal OBJECT-TYPE
	SYNTAX	 Counter64
	MAX-ACCESS  read-only
	STATUS      current
	DESCRIPTION
	"Table entry attribute for lbPollSlotFatigue"
	::={lbPollSlotFatigueLevelEntry 2}

lbPollSlotFatigueLevelMom OBJECT-TYPE
	SYNTAX	 CounterBasedGauge64
	MAX-ACCESS  read-only
	STATUS      current
	DESCRIPTION
	"Table entry attribute for lbPollSlotFatigue"
	::={lbPollSlotFatigueLevelEntry 3}

lbPollSlotFatigueLevelMax OBJECT-TYPE
	SYNTAX	 CounterBasedGauge64
	MAX-ACCESS  read-only
	STATUS      current
	DESCRIPTION
	"Table entry attribute for lbPollSlotFatigue"
	::={lbPollSlotFatigueLevelEntry 4}


lbTxDropsSFPInt	OBJECT IDENTIFIER ::={lb 66}

lbTxDropsSFPIntVal	OBJECT-TYPE
	SYNTAX	 Counter64
	MAX-ACCESS read-only
	STATUS current
	DESCRIPTION "TX drops SFP channel internal"

	::={lbTxDropsSFPInt 1}

lbTxDropsSFPIntMom	OBJECT-TYPE
	SYNTAX	 CounterBasedGauge64
	MAX-ACCESS read-only
	STATUS current
	DESCRIPTION "TX drops SFP channel internal"

	::={lbTxDropsSFPInt 2}

lbTxDropsSFPIntMax	OBJECT-TYPE
	SYNTAX	 CounterBasedGauge64
	MAX-ACCESS read-only
	STATUS current
	DESCRIPTION "TX drops SFP channel internal"

	::={lbTxDropsSFPInt 3}

lbTxDropsSFPIntLevelTable OBJECT-TYPE
	SYNTAX      SEQUENCE OF LbTxDropsSFPIntLevelEntry
	MAX-ACCESS  not-accessible
	STATUS      current
	DESCRIPTION
	"Table for lbTxDropsSFPInt"
	::={lbTxDropsSFPInt 4}

lbTxDropsSFPIntLevelEntry OBJECT-TYPE
	SYNTAX      LbTxDropsSFPIntLevelEntry
	MAX-ACCESS  not-accessible
	STATUS      current
	DESCRIPTION
	"Table entry for lbTxDropsSFPInt"
	INDEX { lbTxDropsSFPIntLevelName }
	::={lbTxDropsSFPIntLevelTable 1}

LbTxDropsSFPIntLevelEntry ::=
	SEQUENCE {
		lbTxDropsSFPIntLevelName	DisplayString,
		lbTxDropsSFPIntLevelVal	Counter64,
		lbTxDropsSFPIntLevelMom	CounterBasedGauge64,
		lbTxDropsSFPIntLevelMax	CounterBasedGauge64
	}

lbTxDropsSFPIntLevelName OBJECT-TYPE
	SYNTAX      DisplayString
	MAX-ACCESS  not-accessible
	STATUS      current
	DESCRIPTION
	"Table entry display string for lbTxDropsSFPInt"
	::={lbTxDropsSFPIntLevelEntry 1}

lbTxDropsSFPIntLevelVal OBJECT-TYPE
	SYNTAX	 Counter64
	MAX-ACCESS  read-only
	STATUS      current
	DESCRIPTION
	"Table entry attribute for lbTxDropsSFPInt"
	::={lbTxDropsSFPIntLevelEntry 2}

lbTxDropsSFPIntLevelMom OBJECT-TYPE
	SYNTAX	 CounterBasedGauge64
	MAX-ACCESS  read-only
	STATUS      current
	DESCRIPTION
	"Table entry attribute for lbTxDropsSFPInt"
	::={lbTxDropsSFPIntLevelEntry 3}

lbTxDropsSFPIntLevelMax OBJECT-TYPE
	SYNTAX	 CounterBasedGauge64
	MAX-ACCESS  read-only
	STATUS      current
	DESCRIPTION
	"Table entry attribute for lbTxDropsSFPInt"
	::={lbTxDropsSFPIntLevelEntry 4}


lbTxDropsSFPExt	OBJECT IDENTIFIER ::={lb 67}

lbTxDropsSFPExtVal	OBJECT-TYPE
	SYNTAX	 Counter64
	MAX-ACCESS read-only
	STATUS current
	DESCRIPTION "TX drops SFP channel external"

	::={lbTxDropsSFPExt 1}

lbTxDropsSFPExtMom	OBJECT-TYPE
	SYNTAX	 CounterBasedGauge64
	MAX-ACCESS read-only
	STATUS current
	DESCRIPTION "TX drops SFP channel external"

	::={lbTxDropsSFPExt 2}

lbTxDropsSFPExtMax	OBJECT-TYPE
	SYNTAX	 CounterBasedGauge64
	MAX-ACCESS read-only
	STATUS current
	DESCRIPTION "TX drops SFP channel external"

	::={lbTxDropsSFPExt 3}

lbTxDropsSFPExtLevelTable OBJECT-TYPE
	SYNTAX      SEQUENCE OF LbTxDropsSFPExtLevelEntry
	MAX-ACCESS  not-accessible
	STATUS      current
	DESCRIPTION
	"Table for lbTxDropsSFPExt"
	::={lbTxDropsSFPExt 4}

lbTxDropsSFPExtLevelEntry OBJECT-TYPE
	SYNTAX      LbTxDropsSFPExtLevelEntry
	MAX-ACCESS  not-accessible
	STATUS      current
	DESCRIPTION
	"Table entry for lbTxDropsSFPExt"
	INDEX { lbTxDropsSFPExtLevelName }
	::={lbTxDropsSFPExtLevelTable 1}

LbTxDropsSFPExtLevelEntry ::=
	SEQUENCE {
		lbTxDropsSFPExtLevelName	DisplayString,
		lbTxDropsSFPExtLevelVal	Counter64,
		lbTxDropsSFPExtLevelMom	CounterBasedGauge64,
		lbTxDropsSFPExtLevelMax	CounterBasedGauge64
	}

lbTxDropsSFPExtLevelName OBJECT-TYPE
	SYNTAX      DisplayString
	MAX-ACCESS  not-accessible
	STATUS      current
	DESCRIPTION
	"Table entry display string for lbTxDropsSFPExt"
	::={lbTxDropsSFPExtLevelEntry 1}

lbTxDropsSFPExtLevelVal OBJECT-TYPE
	SYNTAX	 Counter64
	MAX-ACCESS  read-only
	STATUS      current
	DESCRIPTION
	"Table entry attribute for lbTxDropsSFPExt"
	::={lbTxDropsSFPExtLevelEntry 2}

lbTxDropsSFPExtLevelMom OBJECT-TYPE
	SYNTAX	 CounterBasedGauge64
	MAX-ACCESS  read-only
	STATUS      current
	DESCRIPTION
	"Table entry attribute for lbTxDropsSFPExt"
	::={lbTxDropsSFPExtLevelEntry 3}

lbTxDropsSFPExtLevelMax OBJECT-TYPE
	SYNTAX	 CounterBasedGauge64
	MAX-ACCESS  read-only
	STATUS      current
	DESCRIPTION
	"Table entry attribute for lbTxDropsSFPExt"
	::={lbTxDropsSFPExtLevelEntry 4}


lbTxBytesSFPInt	OBJECT IDENTIFIER ::={lb 68}

lbTxBytesSFPIntVal	OBJECT-TYPE
	SYNTAX	 Counter64
	MAX-ACCESS read-only
	STATUS current
	DESCRIPTION "TX bytes SFP channel internal"

	::={lbTxBytesSFPInt 1}

lbTxBytesSFPIntMom	OBJECT-TYPE
	SYNTAX	 CounterBasedGauge64
	MAX-ACCESS read-only
	STATUS current
	DESCRIPTION "TX bytes SFP channel internal"

	::={lbTxBytesSFPInt 2}

lbTxBytesSFPIntMax	OBJECT-TYPE
	SYNTAX	 CounterBasedGauge64
	MAX-ACCESS read-only
	STATUS current
	DESCRIPTION "TX bytes SFP channel internal"

	::={lbTxBytesSFPInt 3}

lbTxBytesSFPIntLevelTable OBJECT-TYPE
	SYNTAX      SEQUENCE OF LbTxBytesSFPIntLevelEntry
	MAX-ACCESS  not-accessible
	STATUS      current
	DESCRIPTION
	"Table for lbTxBytesSFPInt"
	::={lbTxBytesSFPInt 4}

lbTxBytesSFPIntLevelEntry OBJECT-TYPE
	SYNTAX      LbTxBytesSFPIntLevelEntry
	MAX-ACCESS  not-accessible
	STATUS      current
	DESCRIPTION
	"Table entry for lbTxBytesSFPInt"
	INDEX { lbTxBytesSFPIntLevelName }
	::={lbTxBytesSFPIntLevelTable 1}

LbTxBytesSFPIntLevelEntry ::=
	SEQUENCE {
		lbTxBytesSFPIntLevelName	DisplayString,
		lbTxBytesSFPIntLevelVal	Counter64,
		lbTxBytesSFPIntLevelMom	CounterBasedGauge64,
		lbTxBytesSFPIntLevelMax	CounterBasedGauge64
	}

lbTxBytesSFPIntLevelName OBJECT-TYPE
	SYNTAX      DisplayString
	MAX-ACCESS  not-accessible
	STATUS      current
	DESCRIPTION
	"Table entry display string for lbTxBytesSFPInt"
	::={lbTxBytesSFPIntLevelEntry 1}

lbTxBytesSFPIntLevelVal OBJECT-TYPE
	SYNTAX	 Counter64
	MAX-ACCESS  read-only
	STATUS      current
	DESCRIPTION
	"Table entry attribute for lbTxBytesSFPInt"
	::={lbTxBytesSFPIntLevelEntry 2}

lbTxBytesSFPIntLevelMom OBJECT-TYPE
	SYNTAX	 CounterBasedGauge64
	MAX-ACCESS  read-only
	STATUS      current
	DESCRIPTION
	"Table entry attribute for lbTxBytesSFPInt"
	::={lbTxBytesSFPIntLevelEntry 3}

lbTxBytesSFPIntLevelMax OBJECT-TYPE
	SYNTAX	 CounterBasedGauge64
	MAX-ACCESS  read-only
	STATUS      current
	DESCRIPTION
	"Table entry attribute for lbTxBytesSFPInt"
	::={lbTxBytesSFPIntLevelEntry 4}


lbTxBytesSFPExt	OBJECT IDENTIFIER ::={lb 69}

lbTxBytesSFPExtVal	OBJECT-TYPE
	SYNTAX	 Counter64
	MAX-ACCESS read-only
	STATUS current
	DESCRIPTION "TX bytes SFP channel external"

	::={lbTxBytesSFPExt 1}

lbTxBytesSFPExtMom	OBJECT-TYPE
	SYNTAX	 CounterBasedGauge64
	MAX-ACCESS read-only
	STATUS current
	DESCRIPTION "TX bytes SFP channel external"

	::={lbTxBytesSFPExt 2}

lbTxBytesSFPExtMax	OBJECT-TYPE
	SYNTAX	 CounterBasedGauge64
	MAX-ACCESS read-only
	STATUS current
	DESCRIPTION "TX bytes SFP channel external"

	::={lbTxBytesSFPExt 3}

lbTxBytesSFPExtLevelTable OBJECT-TYPE
	SYNTAX      SEQUENCE OF LbTxBytesSFPExtLevelEntry
	MAX-ACCESS  not-accessible
	STATUS      current
	DESCRIPTION
	"Table for lbTxBytesSFPExt"
	::={lbTxBytesSFPExt 4}

lbTxBytesSFPExtLevelEntry OBJECT-TYPE
	SYNTAX      LbTxBytesSFPExtLevelEntry
	MAX-ACCESS  not-accessible
	STATUS      current
	DESCRIPTION
	"Table entry for lbTxBytesSFPExt"
	INDEX { lbTxBytesSFPExtLevelName }
	::={lbTxBytesSFPExtLevelTable 1}

LbTxBytesSFPExtLevelEntry ::=
	SEQUENCE {
		lbTxBytesSFPExtLevelName	DisplayString,
		lbTxBytesSFPExtLevelVal	Counter64,
		lbTxBytesSFPExtLevelMom	CounterBasedGauge64,
		lbTxBytesSFPExtLevelMax	CounterBasedGauge64
	}

lbTxBytesSFPExtLevelName OBJECT-TYPE
	SYNTAX      DisplayString
	MAX-ACCESS  not-accessible
	STATUS      current
	DESCRIPTION
	"Table entry display string for lbTxBytesSFPExt"
	::={lbTxBytesSFPExtLevelEntry 1}

lbTxBytesSFPExtLevelVal OBJECT-TYPE
	SYNTAX	 Counter64
	MAX-ACCESS  read-only
	STATUS      current
	DESCRIPTION
	"Table entry attribute for lbTxBytesSFPExt"
	::={lbTxBytesSFPExtLevelEntry 2}

lbTxBytesSFPExtLevelMom OBJECT-TYPE
	SYNTAX	 CounterBasedGauge64
	MAX-ACCESS  read-only
	STATUS      current
	DESCRIPTION
	"Table entry attribute for lbTxBytesSFPExt"
	::={lbTxBytesSFPExtLevelEntry 3}

lbTxBytesSFPExtLevelMax OBJECT-TYPE
	SYNTAX	 CounterBasedGauge64
	MAX-ACCESS  read-only
	STATUS      current
	DESCRIPTION
	"Table entry attribute for lbTxBytesSFPExt"
	::={lbTxBytesSFPExtLevelEntry 4}


lbTxDropsFabric1Int	OBJECT IDENTIFIER ::={lb 70}

lbTxDropsFabric1IntVal	OBJECT-TYPE
	SYNTAX	 Counter64
	MAX-ACCESS read-only
	STATUS current
	DESCRIPTION "TX drops Fabric 1 internal"

	::={lbTxDropsFabric1Int 1}

lbTxDropsFabric1IntMom	OBJECT-TYPE
	SYNTAX	 CounterBasedGauge64
	MAX-ACCESS read-only
	STATUS current
	DESCRIPTION "TX drops Fabric 1 internal"

	::={lbTxDropsFabric1Int 2}

lbTxDropsFabric1IntMax	OBJECT-TYPE
	SYNTAX	 CounterBasedGauge64
	MAX-ACCESS read-only
	STATUS current
	DESCRIPTION "TX drops Fabric 1 internal"

	::={lbTxDropsFabric1Int 3}

lbTxDropsFabric1IntLevelTable OBJECT-TYPE
	SYNTAX      SEQUENCE OF LbTxDropsFabric1IntLevelEntry
	MAX-ACCESS  not-accessible
	STATUS      current
	DESCRIPTION
	"Table for lbTxDropsFabric1Int"
	::={lbTxDropsFabric1Int 4}

lbTxDropsFabric1IntLevelEntry OBJECT-TYPE
	SYNTAX      LbTxDropsFabric1IntLevelEntry
	MAX-ACCESS  not-accessible
	STATUS      current
	DESCRIPTION
	"Table entry for lbTxDropsFabric1Int"
	INDEX { lbTxDropsFabric1IntLevelName }
	::={lbTxDropsFabric1IntLevelTable 1}

LbTxDropsFabric1IntLevelEntry ::=
	SEQUENCE {
		lbTxDropsFabric1IntLevelName	DisplayString,
		lbTxDropsFabric1IntLevelVal	Counter64,
		lbTxDropsFabric1IntLevelMom	CounterBasedGauge64,
		lbTxDropsFabric1IntLevelMax	CounterBasedGauge64
	}

lbTxDropsFabric1IntLevelName OBJECT-TYPE
	SYNTAX      DisplayString
	MAX-ACCESS  not-accessible
	STATUS      current
	DESCRIPTION
	"Table entry display string for lbTxDropsFabric1Int"
	::={lbTxDropsFabric1IntLevelEntry 1}

lbTxDropsFabric1IntLevelVal OBJECT-TYPE
	SYNTAX	 Counter64
	MAX-ACCESS  read-only
	STATUS      current
	DESCRIPTION
	"Table entry attribute for lbTxDropsFabric1Int"
	::={lbTxDropsFabric1IntLevelEntry 2}

lbTxDropsFabric1IntLevelMom OBJECT-TYPE
	SYNTAX	 CounterBasedGauge64
	MAX-ACCESS  read-only
	STATUS      current
	DESCRIPTION
	"Table entry attribute for lbTxDropsFabric1Int"
	::={lbTxDropsFabric1IntLevelEntry 3}

lbTxDropsFabric1IntLevelMax OBJECT-TYPE
	SYNTAX	 CounterBasedGauge64
	MAX-ACCESS  read-only
	STATUS      current
	DESCRIPTION
	"Table entry attribute for lbTxDropsFabric1Int"
	::={lbTxDropsFabric1IntLevelEntry 4}


lbTxDropsFabric1Ext	OBJECT IDENTIFIER ::={lb 71}

lbTxDropsFabric1ExtVal	OBJECT-TYPE
	SYNTAX	 Counter64
	MAX-ACCESS read-only
	STATUS current
	DESCRIPTION "TX drops Fabric 1 external"

	::={lbTxDropsFabric1Ext 1}

lbTxDropsFabric1ExtMom	OBJECT-TYPE
	SYNTAX	 CounterBasedGauge64
	MAX-ACCESS read-only
	STATUS current
	DESCRIPTION "TX drops Fabric 1 external"

	::={lbTxDropsFabric1Ext 2}

lbTxDropsFabric1ExtMax	OBJECT-TYPE
	SYNTAX	 CounterBasedGauge64
	MAX-ACCESS read-only
	STATUS current
	DESCRIPTION "TX drops Fabric 1 external"

	::={lbTxDropsFabric1Ext 3}

lbTxDropsFabric1ExtLevelTable OBJECT-TYPE
	SYNTAX      SEQUENCE OF LbTxDropsFabric1ExtLevelEntry
	MAX-ACCESS  not-accessible
	STATUS      current
	DESCRIPTION
	"Table for lbTxDropsFabric1Ext"
	::={lbTxDropsFabric1Ext 4}

lbTxDropsFabric1ExtLevelEntry OBJECT-TYPE
	SYNTAX      LbTxDropsFabric1ExtLevelEntry
	MAX-ACCESS  not-accessible
	STATUS      current
	DESCRIPTION
	"Table entry for lbTxDropsFabric1Ext"
	INDEX { lbTxDropsFabric1ExtLevelName }
	::={lbTxDropsFabric1ExtLevelTable 1}

LbTxDropsFabric1ExtLevelEntry ::=
	SEQUENCE {
		lbTxDropsFabric1ExtLevelName	DisplayString,
		lbTxDropsFabric1ExtLevelVal	Counter64,
		lbTxDropsFabric1ExtLevelMom	CounterBasedGauge64,
		lbTxDropsFabric1ExtLevelMax	CounterBasedGauge64
	}

lbTxDropsFabric1ExtLevelName OBJECT-TYPE
	SYNTAX      DisplayString
	MAX-ACCESS  not-accessible
	STATUS      current
	DESCRIPTION
	"Table entry display string for lbTxDropsFabric1Ext"
	::={lbTxDropsFabric1ExtLevelEntry 1}

lbTxDropsFabric1ExtLevelVal OBJECT-TYPE
	SYNTAX	 Counter64
	MAX-ACCESS  read-only
	STATUS      current
	DESCRIPTION
	"Table entry attribute for lbTxDropsFabric1Ext"
	::={lbTxDropsFabric1ExtLevelEntry 2}

lbTxDropsFabric1ExtLevelMom OBJECT-TYPE
	SYNTAX	 CounterBasedGauge64
	MAX-ACCESS  read-only
	STATUS      current
	DESCRIPTION
	"Table entry attribute for lbTxDropsFabric1Ext"
	::={lbTxDropsFabric1ExtLevelEntry 3}

lbTxDropsFabric1ExtLevelMax OBJECT-TYPE
	SYNTAX	 CounterBasedGauge64
	MAX-ACCESS  read-only
	STATUS      current
	DESCRIPTION
	"Table entry attribute for lbTxDropsFabric1Ext"
	::={lbTxDropsFabric1ExtLevelEntry 4}


lbTxPacketsFabric1Int	OBJECT IDENTIFIER ::={lb 72}

lbTxPacketsFabric1IntVal	OBJECT-TYPE
	SYNTAX	 Counter64
	MAX-ACCESS read-only
	STATUS current
	DESCRIPTION "TX packets Fabric 1 internal"

	::={lbTxPacketsFabric1Int 1}

lbTxPacketsFabric1IntMom	OBJECT-TYPE
	SYNTAX	 CounterBasedGauge64
	MAX-ACCESS read-only
	STATUS current
	DESCRIPTION "TX packets Fabric 1 internal"

	::={lbTxPacketsFabric1Int 2}

lbTxPacketsFabric1IntMax	OBJECT-TYPE
	SYNTAX	 CounterBasedGauge64
	MAX-ACCESS read-only
	STATUS current
	DESCRIPTION "TX packets Fabric 1 internal"

	::={lbTxPacketsFabric1Int 3}

lbTxPacketsFabric1IntLevelTable OBJECT-TYPE
	SYNTAX      SEQUENCE OF LbTxPacketsFabric1IntLevelEntry
	MAX-ACCESS  not-accessible
	STATUS      current
	DESCRIPTION
	"Table for lbTxPacketsFabric1Int"
	::={lbTxPacketsFabric1Int 4}

lbTxPacketsFabric1IntLevelEntry OBJECT-TYPE
	SYNTAX      LbTxPacketsFabric1IntLevelEntry
	MAX-ACCESS  not-accessible
	STATUS      current
	DESCRIPTION
	"Table entry for lbTxPacketsFabric1Int"
	INDEX { lbTxPacketsFabric1IntLevelName }
	::={lbTxPacketsFabric1IntLevelTable 1}

LbTxPacketsFabric1IntLevelEntry ::=
	SEQUENCE {
		lbTxPacketsFabric1IntLevelName	DisplayString,
		lbTxPacketsFabric1IntLevelVal	Counter64,
		lbTxPacketsFabric1IntLevelMom	CounterBasedGauge64,
		lbTxPacketsFabric1IntLevelMax	CounterBasedGauge64
	}

lbTxPacketsFabric1IntLevelName OBJECT-TYPE
	SYNTAX      DisplayString
	MAX-ACCESS  not-accessible
	STATUS      current
	DESCRIPTION
	"Table entry display string for lbTxPacketsFabric1Int"
	::={lbTxPacketsFabric1IntLevelEntry 1}

lbTxPacketsFabric1IntLevelVal OBJECT-TYPE
	SYNTAX	 Counter64
	MAX-ACCESS  read-only
	STATUS      current
	DESCRIPTION
	"Table entry attribute for lbTxPacketsFabric1Int"
	::={lbTxPacketsFabric1IntLevelEntry 2}

lbTxPacketsFabric1IntLevelMom OBJECT-TYPE
	SYNTAX	 CounterBasedGauge64
	MAX-ACCESS  read-only
	STATUS      current
	DESCRIPTION
	"Table entry attribute for lbTxPacketsFabric1Int"
	::={lbTxPacketsFabric1IntLevelEntry 3}

lbTxPacketsFabric1IntLevelMax OBJECT-TYPE
	SYNTAX	 CounterBasedGauge64
	MAX-ACCESS  read-only
	STATUS      current
	DESCRIPTION
	"Table entry attribute for lbTxPacketsFabric1Int"
	::={lbTxPacketsFabric1IntLevelEntry 4}


lbTxPacketsFabric1Ext	OBJECT IDENTIFIER ::={lb 73}

lbTxPacketsFabric1ExtVal	OBJECT-TYPE
	SYNTAX	 Counter64
	MAX-ACCESS read-only
	STATUS current
	DESCRIPTION "TX packets Fabric 1 external"

	::={lbTxPacketsFabric1Ext 1}

lbTxPacketsFabric1ExtMom	OBJECT-TYPE
	SYNTAX	 CounterBasedGauge64
	MAX-ACCESS read-only
	STATUS current
	DESCRIPTION "TX packets Fabric 1 external"

	::={lbTxPacketsFabric1Ext 2}

lbTxPacketsFabric1ExtMax	OBJECT-TYPE
	SYNTAX	 CounterBasedGauge64
	MAX-ACCESS read-only
	STATUS current
	DESCRIPTION "TX packets Fabric 1 external"

	::={lbTxPacketsFabric1Ext 3}

lbTxPacketsFabric1ExtLevelTable OBJECT-TYPE
	SYNTAX      SEQUENCE OF LbTxPacketsFabric1ExtLevelEntry
	MAX-ACCESS  not-accessible
	STATUS      current
	DESCRIPTION
	"Table for lbTxPacketsFabric1Ext"
	::={lbTxPacketsFabric1Ext 4}

lbTxPacketsFabric1ExtLevelEntry OBJECT-TYPE
	SYNTAX      LbTxPacketsFabric1ExtLevelEntry
	MAX-ACCESS  not-accessible
	STATUS      current
	DESCRIPTION
	"Table entry for lbTxPacketsFabric1Ext"
	INDEX { lbTxPacketsFabric1ExtLevelName }
	::={lbTxPacketsFabric1ExtLevelTable 1}

LbTxPacketsFabric1ExtLevelEntry ::=
	SEQUENCE {
		lbTxPacketsFabric1ExtLevelName	DisplayString,
		lbTxPacketsFabric1ExtLevelVal	Counter64,
		lbTxPacketsFabric1ExtLevelMom	CounterBasedGauge64,
		lbTxPacketsFabric1ExtLevelMax	CounterBasedGauge64
	}

lbTxPacketsFabric1ExtLevelName OBJECT-TYPE
	SYNTAX      DisplayString
	MAX-ACCESS  not-accessible
	STATUS      current
	DESCRIPTION
	"Table entry display string for lbTxPacketsFabric1Ext"
	::={lbTxPacketsFabric1ExtLevelEntry 1}

lbTxPacketsFabric1ExtLevelVal OBJECT-TYPE
	SYNTAX	 Counter64
	MAX-ACCESS  read-only
	STATUS      current
	DESCRIPTION
	"Table entry attribute for lbTxPacketsFabric1Ext"
	::={lbTxPacketsFabric1ExtLevelEntry 2}

lbTxPacketsFabric1ExtLevelMom OBJECT-TYPE
	SYNTAX	 CounterBasedGauge64
	MAX-ACCESS  read-only
	STATUS      current
	DESCRIPTION
	"Table entry attribute for lbTxPacketsFabric1Ext"
	::={lbTxPacketsFabric1ExtLevelEntry 3}

lbTxPacketsFabric1ExtLevelMax OBJECT-TYPE
	SYNTAX	 CounterBasedGauge64
	MAX-ACCESS  read-only
	STATUS      current
	DESCRIPTION
	"Table entry attribute for lbTxPacketsFabric1Ext"
	::={lbTxPacketsFabric1ExtLevelEntry 4}


lbTxBytesFabric1Int	OBJECT IDENTIFIER ::={lb 74}

lbTxBytesFabric1IntVal	OBJECT-TYPE
	SYNTAX	 Counter64
	MAX-ACCESS read-only
	STATUS current
	DESCRIPTION "TX bytes Fabric 1 internal"

	::={lbTxBytesFabric1Int 1}

lbTxBytesFabric1IntMom	OBJECT-TYPE
	SYNTAX	 CounterBasedGauge64
	MAX-ACCESS read-only
	STATUS current
	DESCRIPTION "TX bytes Fabric 1 internal"

	::={lbTxBytesFabric1Int 2}

lbTxBytesFabric1IntMax	OBJECT-TYPE
	SYNTAX	 CounterBasedGauge64
	MAX-ACCESS read-only
	STATUS current
	DESCRIPTION "TX bytes Fabric 1 internal"

	::={lbTxBytesFabric1Int 3}

lbTxBytesFabric1IntLevelTable OBJECT-TYPE
	SYNTAX      SEQUENCE OF LbTxBytesFabric1IntLevelEntry
	MAX-ACCESS  not-accessible
	STATUS      current
	DESCRIPTION
	"Table for lbTxBytesFabric1Int"
	::={lbTxBytesFabric1Int 4}

lbTxBytesFabric1IntLevelEntry OBJECT-TYPE
	SYNTAX      LbTxBytesFabric1IntLevelEntry
	MAX-ACCESS  not-accessible
	STATUS      current
	DESCRIPTION
	"Table entry for lbTxBytesFabric1Int"
	INDEX { lbTxBytesFabric1IntLevelName }
	::={lbTxBytesFabric1IntLevelTable 1}

LbTxBytesFabric1IntLevelEntry ::=
	SEQUENCE {
		lbTxBytesFabric1IntLevelName	DisplayString,
		lbTxBytesFabric1IntLevelVal	Counter64,
		lbTxBytesFabric1IntLevelMom	CounterBasedGauge64,
		lbTxBytesFabric1IntLevelMax	CounterBasedGauge64
	}

lbTxBytesFabric1IntLevelName OBJECT-TYPE
	SYNTAX      DisplayString
	MAX-ACCESS  not-accessible
	STATUS      current
	DESCRIPTION
	"Table entry display string for lbTxBytesFabric1Int"
	::={lbTxBytesFabric1IntLevelEntry 1}

lbTxBytesFabric1IntLevelVal OBJECT-TYPE
	SYNTAX	 Counter64
	MAX-ACCESS  read-only
	STATUS      current
	DESCRIPTION
	"Table entry attribute for lbTxBytesFabric1Int"
	::={lbTxBytesFabric1IntLevelEntry 2}

lbTxBytesFabric1IntLevelMom OBJECT-TYPE
	SYNTAX	 CounterBasedGauge64
	MAX-ACCESS  read-only
	STATUS      current
	DESCRIPTION
	"Table entry attribute for lbTxBytesFabric1Int"
	::={lbTxBytesFabric1IntLevelEntry 3}

lbTxBytesFabric1IntLevelMax OBJECT-TYPE
	SYNTAX	 CounterBasedGauge64
	MAX-ACCESS  read-only
	STATUS      current
	DESCRIPTION
	"Table entry attribute for lbTxBytesFabric1Int"
	::={lbTxBytesFabric1IntLevelEntry 4}


lbTxBytesFabric1Ext	OBJECT IDENTIFIER ::={lb 75}

lbTxBytesFabric1ExtVal	OBJECT-TYPE
	SYNTAX	 Counter64
	MAX-ACCESS read-only
	STATUS current
	DESCRIPTION "TX bytes Fabric 1 external"

	::={lbTxBytesFabric1Ext 1}

lbTxBytesFabric1ExtMom	OBJECT-TYPE
	SYNTAX	 CounterBasedGauge64
	MAX-ACCESS read-only
	STATUS current
	DESCRIPTION "TX bytes Fabric 1 external"

	::={lbTxBytesFabric1Ext 2}

lbTxBytesFabric1ExtMax	OBJECT-TYPE
	SYNTAX	 CounterBasedGauge64
	MAX-ACCESS read-only
	STATUS current
	DESCRIPTION "TX bytes Fabric 1 external"

	::={lbTxBytesFabric1Ext 3}

lbTxBytesFabric1ExtLevelTable OBJECT-TYPE
	SYNTAX      SEQUENCE OF LbTxBytesFabric1ExtLevelEntry
	MAX-ACCESS  not-accessible
	STATUS      current
	DESCRIPTION
	"Table for lbTxBytesFabric1Ext"
	::={lbTxBytesFabric1Ext 4}

lbTxBytesFabric1ExtLevelEntry OBJECT-TYPE
	SYNTAX      LbTxBytesFabric1ExtLevelEntry
	MAX-ACCESS  not-accessible
	STATUS      current
	DESCRIPTION
	"Table entry for lbTxBytesFabric1Ext"
	INDEX { lbTxBytesFabric1ExtLevelName }
	::={lbTxBytesFabric1ExtLevelTable 1}

LbTxBytesFabric1ExtLevelEntry ::=
	SEQUENCE {
		lbTxBytesFabric1ExtLevelName	DisplayString,
		lbTxBytesFabric1ExtLevelVal	Counter64,
		lbTxBytesFabric1ExtLevelMom	CounterBasedGauge64,
		lbTxBytesFabric1ExtLevelMax	CounterBasedGauge64
	}

lbTxBytesFabric1ExtLevelName OBJECT-TYPE
	SYNTAX      DisplayString
	MAX-ACCESS  not-accessible
	STATUS      current
	DESCRIPTION
	"Table entry display string for lbTxBytesFabric1Ext"
	::={lbTxBytesFabric1ExtLevelEntry 1}

lbTxBytesFabric1ExtLevelVal OBJECT-TYPE
	SYNTAX	 Counter64
	MAX-ACCESS  read-only
	STATUS      current
	DESCRIPTION
	"Table entry attribute for lbTxBytesFabric1Ext"
	::={lbTxBytesFabric1ExtLevelEntry 2}

lbTxBytesFabric1ExtLevelMom OBJECT-TYPE
	SYNTAX	 CounterBasedGauge64
	MAX-ACCESS  read-only
	STATUS      current
	DESCRIPTION
	"Table entry attribute for lbTxBytesFabric1Ext"
	::={lbTxBytesFabric1ExtLevelEntry 3}

lbTxBytesFabric1ExtLevelMax OBJECT-TYPE
	SYNTAX	 CounterBasedGauge64
	MAX-ACCESS  read-only
	STATUS      current
	DESCRIPTION
	"Table entry attribute for lbTxBytesFabric1Ext"
	::={lbTxBytesFabric1ExtLevelEntry 4}


lbTxDropsFabric2Int	OBJECT IDENTIFIER ::={lb 76}

lbTxDropsFabric2IntVal	OBJECT-TYPE
	SYNTAX	 Counter64
	MAX-ACCESS read-only
	STATUS current
	DESCRIPTION "TX drops Fabric 2 internal"

	::={lbTxDropsFabric2Int 1}

lbTxDropsFabric2IntMom	OBJECT-TYPE
	SYNTAX	 CounterBasedGauge64
	MAX-ACCESS read-only
	STATUS current
	DESCRIPTION "TX drops Fabric 2 internal"

	::={lbTxDropsFabric2Int 2}

lbTxDropsFabric2IntMax	OBJECT-TYPE
	SYNTAX	 CounterBasedGauge64
	MAX-ACCESS read-only
	STATUS current
	DESCRIPTION "TX drops Fabric 2 internal"

	::={lbTxDropsFabric2Int 3}

lbTxDropsFabric2IntLevelTable OBJECT-TYPE
	SYNTAX      SEQUENCE OF LbTxDropsFabric2IntLevelEntry
	MAX-ACCESS  not-accessible
	STATUS      current
	DESCRIPTION
	"Table for lbTxDropsFabric2Int"
	::={lbTxDropsFabric2Int 4}

lbTxDropsFabric2IntLevelEntry OBJECT-TYPE
	SYNTAX      LbTxDropsFabric2IntLevelEntry
	MAX-ACCESS  not-accessible
	STATUS      current
	DESCRIPTION
	"Table entry for lbTxDropsFabric2Int"
	INDEX { lbTxDropsFabric2IntLevelName }
	::={lbTxDropsFabric2IntLevelTable 1}

LbTxDropsFabric2IntLevelEntry ::=
	SEQUENCE {
		lbTxDropsFabric2IntLevelName	DisplayString,
		lbTxDropsFabric2IntLevelVal	Counter64,
		lbTxDropsFabric2IntLevelMom	CounterBasedGauge64,
		lbTxDropsFabric2IntLevelMax	CounterBasedGauge64
	}

lbTxDropsFabric2IntLevelName OBJECT-TYPE
	SYNTAX      DisplayString
	MAX-ACCESS  not-accessible
	STATUS      current
	DESCRIPTION
	"Table entry display string for lbTxDropsFabric2Int"
	::={lbTxDropsFabric2IntLevelEntry 1}

lbTxDropsFabric2IntLevelVal OBJECT-TYPE
	SYNTAX	 Counter64
	MAX-ACCESS  read-only
	STATUS      current
	DESCRIPTION
	"Table entry attribute for lbTxDropsFabric2Int"
	::={lbTxDropsFabric2IntLevelEntry 2}

lbTxDropsFabric2IntLevelMom OBJECT-TYPE
	SYNTAX	 CounterBasedGauge64
	MAX-ACCESS  read-only
	STATUS      current
	DESCRIPTION
	"Table entry attribute for lbTxDropsFabric2Int"
	::={lbTxDropsFabric2IntLevelEntry 3}

lbTxDropsFabric2IntLevelMax OBJECT-TYPE
	SYNTAX	 CounterBasedGauge64
	MAX-ACCESS  read-only
	STATUS      current
	DESCRIPTION
	"Table entry attribute for lbTxDropsFabric2Int"
	::={lbTxDropsFabric2IntLevelEntry 4}


lbTxDropsFabric2Ext	OBJECT IDENTIFIER ::={lb 77}

lbTxDropsFabric2ExtVal	OBJECT-TYPE
	SYNTAX	 Counter64
	MAX-ACCESS read-only
	STATUS current
	DESCRIPTION "TX drops Fabric 2 external"

	::={lbTxDropsFabric2Ext 1}

lbTxDropsFabric2ExtMom	OBJECT-TYPE
	SYNTAX	 CounterBasedGauge64
	MAX-ACCESS read-only
	STATUS current
	DESCRIPTION "TX drops Fabric 2 external"

	::={lbTxDropsFabric2Ext 2}

lbTxDropsFabric2ExtMax	OBJECT-TYPE
	SYNTAX	 CounterBasedGauge64
	MAX-ACCESS read-only
	STATUS current
	DESCRIPTION "TX drops Fabric 2 external"

	::={lbTxDropsFabric2Ext 3}

lbTxDropsFabric2ExtLevelTable OBJECT-TYPE
	SYNTAX      SEQUENCE OF LbTxDropsFabric2ExtLevelEntry
	MAX-ACCESS  not-accessible
	STATUS      current
	DESCRIPTION
	"Table for lbTxDropsFabric2Ext"
	::={lbTxDropsFabric2Ext 4}

lbTxDropsFabric2ExtLevelEntry OBJECT-TYPE
	SYNTAX      LbTxDropsFabric2ExtLevelEntry
	MAX-ACCESS  not-accessible
	STATUS      current
	DESCRIPTION
	"Table entry for lbTxDropsFabric2Ext"
	INDEX { lbTxDropsFabric2ExtLevelName }
	::={lbTxDropsFabric2ExtLevelTable 1}

LbTxDropsFabric2ExtLevelEntry ::=
	SEQUENCE {
		lbTxDropsFabric2ExtLevelName	DisplayString,
		lbTxDropsFabric2ExtLevelVal	Counter64,
		lbTxDropsFabric2ExtLevelMom	CounterBasedGauge64,
		lbTxDropsFabric2ExtLevelMax	CounterBasedGauge64
	}

lbTxDropsFabric2ExtLevelName OBJECT-TYPE
	SYNTAX      DisplayString
	MAX-ACCESS  not-accessible
	STATUS      current
	DESCRIPTION
	"Table entry display string for lbTxDropsFabric2Ext"
	::={lbTxDropsFabric2ExtLevelEntry 1}

lbTxDropsFabric2ExtLevelVal OBJECT-TYPE
	SYNTAX	 Counter64
	MAX-ACCESS  read-only
	STATUS      current
	DESCRIPTION
	"Table entry attribute for lbTxDropsFabric2Ext"
	::={lbTxDropsFabric2ExtLevelEntry 2}

lbTxDropsFabric2ExtLevelMom OBJECT-TYPE
	SYNTAX	 CounterBasedGauge64
	MAX-ACCESS  read-only
	STATUS      current
	DESCRIPTION
	"Table entry attribute for lbTxDropsFabric2Ext"
	::={lbTxDropsFabric2ExtLevelEntry 3}

lbTxDropsFabric2ExtLevelMax OBJECT-TYPE
	SYNTAX	 CounterBasedGauge64
	MAX-ACCESS  read-only
	STATUS      current
	DESCRIPTION
	"Table entry attribute for lbTxDropsFabric2Ext"
	::={lbTxDropsFabric2ExtLevelEntry 4}


lbTxPacketsFabric2Int	OBJECT IDENTIFIER ::={lb 78}

lbTxPacketsFabric2IntVal	OBJECT-TYPE
	SYNTAX	 Counter64
	MAX-ACCESS read-only
	STATUS current
	DESCRIPTION "TX packets Fabric 2 internal"

	::={lbTxPacketsFabric2Int 1}

lbTxPacketsFabric2IntMom	OBJECT-TYPE
	SYNTAX	 CounterBasedGauge64
	MAX-ACCESS read-only
	STATUS current
	DESCRIPTION "TX packets Fabric 2 internal"

	::={lbTxPacketsFabric2Int 2}

lbTxPacketsFabric2IntMax	OBJECT-TYPE
	SYNTAX	 CounterBasedGauge64
	MAX-ACCESS read-only
	STATUS current
	DESCRIPTION "TX packets Fabric 2 internal"

	::={lbTxPacketsFabric2Int 3}

lbTxPacketsFabric2IntLevelTable OBJECT-TYPE
	SYNTAX      SEQUENCE OF LbTxPacketsFabric2IntLevelEntry
	MAX-ACCESS  not-accessible
	STATUS      current
	DESCRIPTION
	"Table for lbTxPacketsFabric2Int"
	::={lbTxPacketsFabric2Int 4}

lbTxPacketsFabric2IntLevelEntry OBJECT-TYPE
	SYNTAX      LbTxPacketsFabric2IntLevelEntry
	MAX-ACCESS  not-accessible
	STATUS      current
	DESCRIPTION
	"Table entry for lbTxPacketsFabric2Int"
	INDEX { lbTxPacketsFabric2IntLevelName }
	::={lbTxPacketsFabric2IntLevelTable 1}

LbTxPacketsFabric2IntLevelEntry ::=
	SEQUENCE {
		lbTxPacketsFabric2IntLevelName	DisplayString,
		lbTxPacketsFabric2IntLevelVal	Counter64,
		lbTxPacketsFabric2IntLevelMom	CounterBasedGauge64,
		lbTxPacketsFabric2IntLevelMax	CounterBasedGauge64
	}

lbTxPacketsFabric2IntLevelName OBJECT-TYPE
	SYNTAX      DisplayString
	MAX-ACCESS  not-accessible
	STATUS      current
	DESCRIPTION
	"Table entry display string for lbTxPacketsFabric2Int"
	::={lbTxPacketsFabric2IntLevelEntry 1}

lbTxPacketsFabric2IntLevelVal OBJECT-TYPE
	SYNTAX	 Counter64
	MAX-ACCESS  read-only
	STATUS      current
	DESCRIPTION
	"Table entry attribute for lbTxPacketsFabric2Int"
	::={lbTxPacketsFabric2IntLevelEntry 2}

lbTxPacketsFabric2IntLevelMom OBJECT-TYPE
	SYNTAX	 CounterBasedGauge64
	MAX-ACCESS  read-only
	STATUS      current
	DESCRIPTION
	"Table entry attribute for lbTxPacketsFabric2Int"
	::={lbTxPacketsFabric2IntLevelEntry 3}

lbTxPacketsFabric2IntLevelMax OBJECT-TYPE
	SYNTAX	 CounterBasedGauge64
	MAX-ACCESS  read-only
	STATUS      current
	DESCRIPTION
	"Table entry attribute for lbTxPacketsFabric2Int"
	::={lbTxPacketsFabric2IntLevelEntry 4}


lbTxPacketsFabric2Ext	OBJECT IDENTIFIER ::={lb 79}

lbTxPacketsFabric2ExtVal	OBJECT-TYPE
	SYNTAX	 Counter64
	MAX-ACCESS read-only
	STATUS current
	DESCRIPTION "TX packets Fabric 2 external"

	::={lbTxPacketsFabric2Ext 1}

lbTxPacketsFabric2ExtMom	OBJECT-TYPE
	SYNTAX	 CounterBasedGauge64
	MAX-ACCESS read-only
	STATUS current
	DESCRIPTION "TX packets Fabric 2 external"

	::={lbTxPacketsFabric2Ext 2}

lbTxPacketsFabric2ExtMax	OBJECT-TYPE
	SYNTAX	 CounterBasedGauge64
	MAX-ACCESS read-only
	STATUS current
	DESCRIPTION "TX packets Fabric 2 external"

	::={lbTxPacketsFabric2Ext 3}

lbTxPacketsFabric2ExtLevelTable OBJECT-TYPE
	SYNTAX      SEQUENCE OF LbTxPacketsFabric2ExtLevelEntry
	MAX-ACCESS  not-accessible
	STATUS      current
	DESCRIPTION
	"Table for lbTxPacketsFabric2Ext"
	::={lbTxPacketsFabric2Ext 4}

lbTxPacketsFabric2ExtLevelEntry OBJECT-TYPE
	SYNTAX      LbTxPacketsFabric2ExtLevelEntry
	MAX-ACCESS  not-accessible
	STATUS      current
	DESCRIPTION
	"Table entry for lbTxPacketsFabric2Ext"
	INDEX { lbTxPacketsFabric2ExtLevelName }
	::={lbTxPacketsFabric2ExtLevelTable 1}

LbTxPacketsFabric2ExtLevelEntry ::=
	SEQUENCE {
		lbTxPacketsFabric2ExtLevelName	DisplayString,
		lbTxPacketsFabric2ExtLevelVal	Counter64,
		lbTxPacketsFabric2ExtLevelMom	CounterBasedGauge64,
		lbTxPacketsFabric2ExtLevelMax	CounterBasedGauge64
	}

lbTxPacketsFabric2ExtLevelName OBJECT-TYPE
	SYNTAX      DisplayString
	MAX-ACCESS  not-accessible
	STATUS      current
	DESCRIPTION
	"Table entry display string for lbTxPacketsFabric2Ext"
	::={lbTxPacketsFabric2ExtLevelEntry 1}

lbTxPacketsFabric2ExtLevelVal OBJECT-TYPE
	SYNTAX	 Counter64
	MAX-ACCESS  read-only
	STATUS      current
	DESCRIPTION
	"Table entry attribute for lbTxPacketsFabric2Ext"
	::={lbTxPacketsFabric2ExtLevelEntry 2}

lbTxPacketsFabric2ExtLevelMom OBJECT-TYPE
	SYNTAX	 CounterBasedGauge64
	MAX-ACCESS  read-only
	STATUS      current
	DESCRIPTION
	"Table entry attribute for lbTxPacketsFabric2Ext"
	::={lbTxPacketsFabric2ExtLevelEntry 3}

lbTxPacketsFabric2ExtLevelMax OBJECT-TYPE
	SYNTAX	 CounterBasedGauge64
	MAX-ACCESS  read-only
	STATUS      current
	DESCRIPTION
	"Table entry attribute for lbTxPacketsFabric2Ext"
	::={lbTxPacketsFabric2ExtLevelEntry 4}


lbTxBytesFabric2Int	OBJECT IDENTIFIER ::={lb 80}

lbTxBytesFabric2IntVal	OBJECT-TYPE
	SYNTAX	 Counter64
	MAX-ACCESS read-only
	STATUS current
	DESCRIPTION "TX bytes Fabric 2 internal"

	::={lbTxBytesFabric2Int 1}

lbTxBytesFabric2IntMom	OBJECT-TYPE
	SYNTAX	 CounterBasedGauge64
	MAX-ACCESS read-only
	STATUS current
	DESCRIPTION "TX bytes Fabric 2 internal"

	::={lbTxBytesFabric2Int 2}

lbTxBytesFabric2IntMax	OBJECT-TYPE
	SYNTAX	 CounterBasedGauge64
	MAX-ACCESS read-only
	STATUS current
	DESCRIPTION "TX bytes Fabric 2 internal"

	::={lbTxBytesFabric2Int 3}

lbTxBytesFabric2IntLevelTable OBJECT-TYPE
	SYNTAX      SEQUENCE OF LbTxBytesFabric2IntLevelEntry
	MAX-ACCESS  not-accessible
	STATUS      current
	DESCRIPTION
	"Table for lbTxBytesFabric2Int"
	::={lbTxBytesFabric2Int 4}

lbTxBytesFabric2IntLevelEntry OBJECT-TYPE
	SYNTAX      LbTxBytesFabric2IntLevelEntry
	MAX-ACCESS  not-accessible
	STATUS      current
	DESCRIPTION
	"Table entry for lbTxBytesFabric2Int"
	INDEX { lbTxBytesFabric2IntLevelName }
	::={lbTxBytesFabric2IntLevelTable 1}

LbTxBytesFabric2IntLevelEntry ::=
	SEQUENCE {
		lbTxBytesFabric2IntLevelName	DisplayString,
		lbTxBytesFabric2IntLevelVal	Counter64,
		lbTxBytesFabric2IntLevelMom	CounterBasedGauge64,
		lbTxBytesFabric2IntLevelMax	CounterBasedGauge64
	}

lbTxBytesFabric2IntLevelName OBJECT-TYPE
	SYNTAX      DisplayString
	MAX-ACCESS  not-accessible
	STATUS      current
	DESCRIPTION
	"Table entry display string for lbTxBytesFabric2Int"
	::={lbTxBytesFabric2IntLevelEntry 1}

lbTxBytesFabric2IntLevelVal OBJECT-TYPE
	SYNTAX	 Counter64
	MAX-ACCESS  read-only
	STATUS      current
	DESCRIPTION
	"Table entry attribute for lbTxBytesFabric2Int"
	::={lbTxBytesFabric2IntLevelEntry 2}

lbTxBytesFabric2IntLevelMom OBJECT-TYPE
	SYNTAX	 CounterBasedGauge64
	MAX-ACCESS  read-only
	STATUS      current
	DESCRIPTION
	"Table entry attribute for lbTxBytesFabric2Int"
	::={lbTxBytesFabric2IntLevelEntry 3}

lbTxBytesFabric2IntLevelMax OBJECT-TYPE
	SYNTAX	 CounterBasedGauge64
	MAX-ACCESS  read-only
	STATUS      current
	DESCRIPTION
	"Table entry attribute for lbTxBytesFabric2Int"
	::={lbTxBytesFabric2IntLevelEntry 4}


lbTxBytesFabric2Ext	OBJECT IDENTIFIER ::={lb 81}

lbTxBytesFabric2ExtVal	OBJECT-TYPE
	SYNTAX	 Counter64
	MAX-ACCESS read-only
	STATUS current
	DESCRIPTION "TX bytes Fabric 2 external"

	::={lbTxBytesFabric2Ext 1}

lbTxBytesFabric2ExtMom	OBJECT-TYPE
	SYNTAX	 CounterBasedGauge64
	MAX-ACCESS read-only
	STATUS current
	DESCRIPTION "TX bytes Fabric 2 external"

	::={lbTxBytesFabric2Ext 2}

lbTxBytesFabric2ExtMax	OBJECT-TYPE
	SYNTAX	 CounterBasedGauge64
	MAX-ACCESS read-only
	STATUS current
	DESCRIPTION "TX bytes Fabric 2 external"

	::={lbTxBytesFabric2Ext 3}

lbTxBytesFabric2ExtLevelTable OBJECT-TYPE
	SYNTAX      SEQUENCE OF LbTxBytesFabric2ExtLevelEntry
	MAX-ACCESS  not-accessible
	STATUS      current
	DESCRIPTION
	"Table for lbTxBytesFabric2Ext"
	::={lbTxBytesFabric2Ext 4}

lbTxBytesFabric2ExtLevelEntry OBJECT-TYPE
	SYNTAX      LbTxBytesFabric2ExtLevelEntry
	MAX-ACCESS  not-accessible
	STATUS      current
	DESCRIPTION
	"Table entry for lbTxBytesFabric2Ext"
	INDEX { lbTxBytesFabric2ExtLevelName }
	::={lbTxBytesFabric2ExtLevelTable 1}

LbTxBytesFabric2ExtLevelEntry ::=
	SEQUENCE {
		lbTxBytesFabric2ExtLevelName	DisplayString,
		lbTxBytesFabric2ExtLevelVal	Counter64,
		lbTxBytesFabric2ExtLevelMom	CounterBasedGauge64,
		lbTxBytesFabric2ExtLevelMax	CounterBasedGauge64
	}

lbTxBytesFabric2ExtLevelName OBJECT-TYPE
	SYNTAX      DisplayString
	MAX-ACCESS  not-accessible
	STATUS      current
	DESCRIPTION
	"Table entry display string for lbTxBytesFabric2Ext"
	::={lbTxBytesFabric2ExtLevelEntry 1}

lbTxBytesFabric2ExtLevelVal OBJECT-TYPE
	SYNTAX	 Counter64
	MAX-ACCESS  read-only
	STATUS      current
	DESCRIPTION
	"Table entry attribute for lbTxBytesFabric2Ext"
	::={lbTxBytesFabric2ExtLevelEntry 2}

lbTxBytesFabric2ExtLevelMom OBJECT-TYPE
	SYNTAX	 CounterBasedGauge64
	MAX-ACCESS  read-only
	STATUS      current
	DESCRIPTION
	"Table entry attribute for lbTxBytesFabric2Ext"
	::={lbTxBytesFabric2ExtLevelEntry 3}

lbTxBytesFabric2ExtLevelMax OBJECT-TYPE
	SYNTAX	 CounterBasedGauge64
	MAX-ACCESS  read-only
	STATUS      current
	DESCRIPTION
	"Table entry attribute for lbTxBytesFabric2Ext"
	::={lbTxBytesFabric2ExtLevelEntry 4}


lbCorruptCpuPkts	OBJECT IDENTIFIER ::={lb 82}

lbCorruptCpuPktsVal	OBJECT-TYPE
	SYNTAX	 Counter64
	MAX-ACCESS read-only
	STATUS current
	DESCRIPTION "Corrupt CPU packets"

	::={lbCorruptCpuPkts 1}

lbCorruptCpuPktsMom	OBJECT-TYPE
	SYNTAX	 CounterBasedGauge64
	MAX-ACCESS read-only
	STATUS current
	DESCRIPTION "Corrupt CPU packets"

	::={lbCorruptCpuPkts 2}

lbCorruptCpuPktsMax	OBJECT-TYPE
	SYNTAX	 CounterBasedGauge64
	MAX-ACCESS read-only
	STATUS current
	DESCRIPTION "Corrupt CPU packets"

	::={lbCorruptCpuPkts 3}

lbCorruptCpuPktsLevelTable OBJECT-TYPE
	SYNTAX      SEQUENCE OF LbCorruptCpuPktsLevelEntry
	MAX-ACCESS  not-accessible
	STATUS      current
	DESCRIPTION
	"Table for lbCorruptCpuPkts"
	::={lbCorruptCpuPkts 4}

lbCorruptCpuPktsLevelEntry OBJECT-TYPE
	SYNTAX      LbCorruptCpuPktsLevelEntry
	MAX-ACCESS  not-accessible
	STATUS      current
	DESCRIPTION
	"Table entry for lbCorruptCpuPkts"
	INDEX { lbCorruptCpuPktsLevelName }
	::={lbCorruptCpuPktsLevelTable 1}

LbCorruptCpuPktsLevelEntry ::=
	SEQUENCE {
		lbCorruptCpuPktsLevelName	DisplayString,
		lbCorruptCpuPktsLevelVal	Counter64,
		lbCorruptCpuPktsLevelMom	CounterBasedGauge64,
		lbCorruptCpuPktsLevelMax	CounterBasedGauge64
	}

lbCorruptCpuPktsLevelName OBJECT-TYPE
	SYNTAX      DisplayString
	MAX-ACCESS  not-accessible
	STATUS      current
	DESCRIPTION
	"Table entry display string for lbCorruptCpuPkts"
	::={lbCorruptCpuPktsLevelEntry 1}

lbCorruptCpuPktsLevelVal OBJECT-TYPE
	SYNTAX	 Counter64
	MAX-ACCESS  read-only
	STATUS      current
	DESCRIPTION
	"Table entry attribute for lbCorruptCpuPkts"
	::={lbCorruptCpuPktsLevelEntry 2}

lbCorruptCpuPktsLevelMom OBJECT-TYPE
	SYNTAX	 CounterBasedGauge64
	MAX-ACCESS  read-only
	STATUS      current
	DESCRIPTION
	"Table entry attribute for lbCorruptCpuPkts"
	::={lbCorruptCpuPktsLevelEntry 3}

lbCorruptCpuPktsLevelMax OBJECT-TYPE
	SYNTAX	 CounterBasedGauge64
	MAX-ACCESS  read-only
	STATUS      current
	DESCRIPTION
	"Table entry attribute for lbCorruptCpuPkts"
	::={lbCorruptCpuPktsLevelEntry 4}


lbCpuPktBufferFailure	OBJECT IDENTIFIER ::={lb 83}

lbCpuPktBufferFailureVal	OBJECT-TYPE
	SYNTAX	 Counter64
	MAX-ACCESS read-only
	STATUS current
	DESCRIPTION "CPU packet buffer failures"

	::={lbCpuPktBufferFailure 1}

lbCpuPktBufferFailureMom	OBJECT-TYPE
	SYNTAX	 CounterBasedGauge64
	MAX-ACCESS read-only
	STATUS current
	DESCRIPTION "CPU packet buffer failures"

	::={lbCpuPktBufferFailure 2}

lbCpuPktBufferFailureMax	OBJECT-TYPE
	SYNTAX	 CounterBasedGauge64
	MAX-ACCESS read-only
	STATUS current
	DESCRIPTION "CPU packet buffer failures"

	::={lbCpuPktBufferFailure 3}

lbCpuPktBufferFailureLevelTable OBJECT-TYPE
	SYNTAX      SEQUENCE OF LbCpuPktBufferFailureLevelEntry
	MAX-ACCESS  not-accessible
	STATUS      current
	DESCRIPTION
	"Table for lbCpuPktBufferFailure"
	::={lbCpuPktBufferFailure 4}

lbCpuPktBufferFailureLevelEntry OBJECT-TYPE
	SYNTAX      LbCpuPktBufferFailureLevelEntry
	MAX-ACCESS  not-accessible
	STATUS      current
	DESCRIPTION
	"Table entry for lbCpuPktBufferFailure"
	INDEX { lbCpuPktBufferFailureLevelName }
	::={lbCpuPktBufferFailureLevelTable 1}

LbCpuPktBufferFailureLevelEntry ::=
	SEQUENCE {
		lbCpuPktBufferFailureLevelName	DisplayString,
		lbCpuPktBufferFailureLevelVal	Counter64,
		lbCpuPktBufferFailureLevelMom	CounterBasedGauge64,
		lbCpuPktBufferFailureLevelMax	CounterBasedGauge64
	}

lbCpuPktBufferFailureLevelName OBJECT-TYPE
	SYNTAX      DisplayString
	MAX-ACCESS  not-accessible
	STATUS      current
	DESCRIPTION
	"Table entry display string for lbCpuPktBufferFailure"
	::={lbCpuPktBufferFailureLevelEntry 1}

lbCpuPktBufferFailureLevelVal OBJECT-TYPE
	SYNTAX	 Counter64
	MAX-ACCESS  read-only
	STATUS      current
	DESCRIPTION
	"Table entry attribute for lbCpuPktBufferFailure"
	::={lbCpuPktBufferFailureLevelEntry 2}

lbCpuPktBufferFailureLevelMom OBJECT-TYPE
	SYNTAX	 CounterBasedGauge64
	MAX-ACCESS  read-only
	STATUS      current
	DESCRIPTION
	"Table entry attribute for lbCpuPktBufferFailure"
	::={lbCpuPktBufferFailureLevelEntry 3}

lbCpuPktBufferFailureLevelMax OBJECT-TYPE
	SYNTAX	 CounterBasedGauge64
	MAX-ACCESS  read-only
	STATUS      current
	DESCRIPTION
	"Table entry attribute for lbCpuPktBufferFailure"
	::={lbCpuPktBufferFailureLevelEntry 4}


lbFPGAFirmwareVersionInt	OBJECT IDENTIFIER ::={lb 84}

lbFPGAFirmwareVersionIntVal	OBJECT-TYPE
	SYNTAX	 CounterBasedGauge64
	MAX-ACCESS read-only
	STATUS current
	DESCRIPTION "FPGA firmware version internal"

	::={lbFPGAFirmwareVersionInt 1}

lbFPGAFirmwareVersionIntMax	OBJECT-TYPE
	SYNTAX	 CounterBasedGauge64
	MAX-ACCESS read-only
	STATUS current
	DESCRIPTION "FPGA firmware version internal"

	::={lbFPGAFirmwareVersionInt 3}

lbFPGAFirmwareVersionIntLevelTable OBJECT-TYPE
	SYNTAX      SEQUENCE OF LbFPGAFirmwareVersionIntLevelEntry
	MAX-ACCESS  not-accessible
	STATUS      current
	DESCRIPTION
	"Table for lbFPGAFirmwareVersionInt"
	::={lbFPGAFirmwareVersionInt 4}

lbFPGAFirmwareVersionIntLevelEntry OBJECT-TYPE
	SYNTAX      LbFPGAFirmwareVersionIntLevelEntry
	MAX-ACCESS  not-accessible
	STATUS      current
	DESCRIPTION
	"Table entry for lbFPGAFirmwareVersionInt"
	INDEX { lbFPGAFirmwareVersionIntLevelName }
	::={lbFPGAFirmwareVersionIntLevelTable 1}

LbFPGAFirmwareVersionIntLevelEntry ::=
	SEQUENCE {
		lbFPGAFirmwareVersionIntLevelName	DisplayString,
		lbFPGAFirmwareVersionIntLevelVal	CounterBasedGauge64,
		lbFPGAFirmwareVersionIntLevelMax	CounterBasedGauge64
	}

lbFPGAFirmwareVersionIntLevelName OBJECT-TYPE
	SYNTAX      DisplayString
	MAX-ACCESS  not-accessible
	STATUS      current
	DESCRIPTION
	"Table entry display string for lbFPGAFirmwareVersionInt"
	::={lbFPGAFirmwareVersionIntLevelEntry 1}

lbFPGAFirmwareVersionIntLevelVal OBJECT-TYPE
	SYNTAX	 CounterBasedGauge64
	MAX-ACCESS  read-only
	STATUS      current
	DESCRIPTION
	"Table entry attribute for lbFPGAFirmwareVersionInt"
	::={lbFPGAFirmwareVersionIntLevelEntry 2}

lbFPGAFirmwareVersionIntLevelMax OBJECT-TYPE
	SYNTAX	 CounterBasedGauge64
	MAX-ACCESS  read-only
	STATUS      current
	DESCRIPTION
	"Table entry attribute for lbFPGAFirmwareVersionInt"
	::={lbFPGAFirmwareVersionIntLevelEntry 4}


lbFPGAFirmwareVersionExt	OBJECT IDENTIFIER ::={lb 85}

lbFPGAFirmwareVersionExtVal	OBJECT-TYPE
	SYNTAX	 CounterBasedGauge64
	MAX-ACCESS read-only
	STATUS current
	DESCRIPTION "FPGA firmware version external"

	::={lbFPGAFirmwareVersionExt 1}

lbFPGAFirmwareVersionExtMax	OBJECT-TYPE
	SYNTAX	 CounterBasedGauge64
	MAX-ACCESS read-only
	STATUS current
	DESCRIPTION "FPGA firmware version external"

	::={lbFPGAFirmwareVersionExt 3}

lbFPGAFirmwareVersionExtLevelTable OBJECT-TYPE
	SYNTAX      SEQUENCE OF LbFPGAFirmwareVersionExtLevelEntry
	MAX-ACCESS  not-accessible
	STATUS      current
	DESCRIPTION
	"Table for lbFPGAFirmwareVersionExt"
	::={lbFPGAFirmwareVersionExt 4}

lbFPGAFirmwareVersionExtLevelEntry OBJECT-TYPE
	SYNTAX      LbFPGAFirmwareVersionExtLevelEntry
	MAX-ACCESS  not-accessible
	STATUS      current
	DESCRIPTION
	"Table entry for lbFPGAFirmwareVersionExt"
	INDEX { lbFPGAFirmwareVersionExtLevelName }
	::={lbFPGAFirmwareVersionExtLevelTable 1}

LbFPGAFirmwareVersionExtLevelEntry ::=
	SEQUENCE {
		lbFPGAFirmwareVersionExtLevelName	DisplayString,
		lbFPGAFirmwareVersionExtLevelVal	CounterBasedGauge64,
		lbFPGAFirmwareVersionExtLevelMax	CounterBasedGauge64
	}

lbFPGAFirmwareVersionExtLevelName OBJECT-TYPE
	SYNTAX      DisplayString
	MAX-ACCESS  not-accessible
	STATUS      current
	DESCRIPTION
	"Table entry display string for lbFPGAFirmwareVersionExt"
	::={lbFPGAFirmwareVersionExtLevelEntry 1}

lbFPGAFirmwareVersionExtLevelVal OBJECT-TYPE
	SYNTAX	 CounterBasedGauge64
	MAX-ACCESS  read-only
	STATUS      current
	DESCRIPTION
	"Table entry attribute for lbFPGAFirmwareVersionExt"
	::={lbFPGAFirmwareVersionExtLevelEntry 2}

lbFPGAFirmwareVersionExtLevelMax OBJECT-TYPE
	SYNTAX	 CounterBasedGauge64
	MAX-ACCESS  read-only
	STATUS      current
	DESCRIPTION
	"Table entry attribute for lbFPGAFirmwareVersionExt"
	::={lbFPGAFirmwareVersionExtLevelEntry 4}


lbShuntPktIpv4DscpInt	OBJECT IDENTIFIER ::={lb 86}

lbShuntPktIpv4DscpIntVal	OBJECT-TYPE
	SYNTAX	 Counter64
	MAX-ACCESS read-only
	STATUS current
	DESCRIPTION "Shunt packets internal (IPv4 DSCP)"

	::={lbShuntPktIpv4DscpInt 1}

lbShuntPktIpv4DscpIntMom	OBJECT-TYPE
	SYNTAX	 CounterBasedGauge64
	MAX-ACCESS read-only
	STATUS current
	DESCRIPTION "Shunt packets internal (IPv4 DSCP)"

	::={lbShuntPktIpv4DscpInt 2}

lbShuntPktIpv4DscpIntMax	OBJECT-TYPE
	SYNTAX	 CounterBasedGauge64
	MAX-ACCESS read-only
	STATUS current
	DESCRIPTION "Shunt packets internal (IPv4 DSCP)"

	::={lbShuntPktIpv4DscpInt 3}

lbShuntPktIpv4DscpIntLevelTable OBJECT-TYPE
	SYNTAX      SEQUENCE OF LbShuntPktIpv4DscpIntLevelEntry
	MAX-ACCESS  not-accessible
	STATUS      current
	DESCRIPTION
	"Table for lbShuntPktIpv4DscpInt"
	::={lbShuntPktIpv4DscpInt 4}

lbShuntPktIpv4DscpIntLevelEntry OBJECT-TYPE
	SYNTAX      LbShuntPktIpv4DscpIntLevelEntry
	MAX-ACCESS  not-accessible
	STATUS      current
	DESCRIPTION
	"Table entry for lbShuntPktIpv4DscpInt"
	INDEX { lbShuntPktIpv4DscpIntLevelName }
	::={lbShuntPktIpv4DscpIntLevelTable 1}

LbShuntPktIpv4DscpIntLevelEntry ::=
	SEQUENCE {
		lbShuntPktIpv4DscpIntLevelName	DisplayString,
		lbShuntPktIpv4DscpIntLevelVal	Counter64,
		lbShuntPktIpv4DscpIntLevelMom	CounterBasedGauge64,
		lbShuntPktIpv4DscpIntLevelMax	CounterBasedGauge64
	}

lbShuntPktIpv4DscpIntLevelName OBJECT-TYPE
	SYNTAX      DisplayString
	MAX-ACCESS  not-accessible
	STATUS      current
	DESCRIPTION
	"Table entry display string for lbShuntPktIpv4DscpInt"
	::={lbShuntPktIpv4DscpIntLevelEntry 1}

lbShuntPktIpv4DscpIntLevelVal OBJECT-TYPE
	SYNTAX	 Counter64
	MAX-ACCESS  read-only
	STATUS      current
	DESCRIPTION
	"Table entry attribute for lbShuntPktIpv4DscpInt"
	::={lbShuntPktIpv4DscpIntLevelEntry 2}

lbShuntPktIpv4DscpIntLevelMom OBJECT-TYPE
	SYNTAX	 CounterBasedGauge64
	MAX-ACCESS  read-only
	STATUS      current
	DESCRIPTION
	"Table entry attribute for lbShuntPktIpv4DscpInt"
	::={lbShuntPktIpv4DscpIntLevelEntry 3}

lbShuntPktIpv4DscpIntLevelMax OBJECT-TYPE
	SYNTAX	 CounterBasedGauge64
	MAX-ACCESS  read-only
	STATUS      current
	DESCRIPTION
	"Table entry attribute for lbShuntPktIpv4DscpInt"
	::={lbShuntPktIpv4DscpIntLevelEntry 4}


lbShuntPktIpv4DscpExt	OBJECT IDENTIFIER ::={lb 87}

lbShuntPktIpv4DscpExtVal	OBJECT-TYPE
	SYNTAX	 Counter64
	MAX-ACCESS read-only
	STATUS current
	DESCRIPTION "Shunt packets external (IPv4 DSCP)"

	::={lbShuntPktIpv4DscpExt 1}

lbShuntPktIpv4DscpExtMom	OBJECT-TYPE
	SYNTAX	 CounterBasedGauge64
	MAX-ACCESS read-only
	STATUS current
	DESCRIPTION "Shunt packets external (IPv4 DSCP)"

	::={lbShuntPktIpv4DscpExt 2}

lbShuntPktIpv4DscpExtMax	OBJECT-TYPE
	SYNTAX	 CounterBasedGauge64
	MAX-ACCESS read-only
	STATUS current
	DESCRIPTION "Shunt packets external (IPv4 DSCP)"

	::={lbShuntPktIpv4DscpExt 3}

lbShuntPktIpv4DscpExtLevelTable OBJECT-TYPE
	SYNTAX      SEQUENCE OF LbShuntPktIpv4DscpExtLevelEntry
	MAX-ACCESS  not-accessible
	STATUS      current
	DESCRIPTION
	"Table for lbShuntPktIpv4DscpExt"
	::={lbShuntPktIpv4DscpExt 4}

lbShuntPktIpv4DscpExtLevelEntry OBJECT-TYPE
	SYNTAX      LbShuntPktIpv4DscpExtLevelEntry
	MAX-ACCESS  not-accessible
	STATUS      current
	DESCRIPTION
	"Table entry for lbShuntPktIpv4DscpExt"
	INDEX { lbShuntPktIpv4DscpExtLevelName }
	::={lbShuntPktIpv4DscpExtLevelTable 1}

LbShuntPktIpv4DscpExtLevelEntry ::=
	SEQUENCE {
		lbShuntPktIpv4DscpExtLevelName	DisplayString,
		lbShuntPktIpv4DscpExtLevelVal	Counter64,
		lbShuntPktIpv4DscpExtLevelMom	CounterBasedGauge64,
		lbShuntPktIpv4DscpExtLevelMax	CounterBasedGauge64
	}

lbShuntPktIpv4DscpExtLevelName OBJECT-TYPE
	SYNTAX      DisplayString
	MAX-ACCESS  not-accessible
	STATUS      current
	DESCRIPTION
	"Table entry display string for lbShuntPktIpv4DscpExt"
	::={lbShuntPktIpv4DscpExtLevelEntry 1}

lbShuntPktIpv4DscpExtLevelVal OBJECT-TYPE
	SYNTAX	 Counter64
	MAX-ACCESS  read-only
	STATUS      current
	DESCRIPTION
	"Table entry attribute for lbShuntPktIpv4DscpExt"
	::={lbShuntPktIpv4DscpExtLevelEntry 2}

lbShuntPktIpv4DscpExtLevelMom OBJECT-TYPE
	SYNTAX	 CounterBasedGauge64
	MAX-ACCESS  read-only
	STATUS      current
	DESCRIPTION
	"Table entry attribute for lbShuntPktIpv4DscpExt"
	::={lbShuntPktIpv4DscpExtLevelEntry 3}

lbShuntPktIpv4DscpExtLevelMax OBJECT-TYPE
	SYNTAX	 CounterBasedGauge64
	MAX-ACCESS  read-only
	STATUS      current
	DESCRIPTION
	"Table entry attribute for lbShuntPktIpv4DscpExt"
	::={lbShuntPktIpv4DscpExtLevelEntry 4}


lbShuntByteIpv4DscpInt	OBJECT IDENTIFIER ::={lb 88}

lbShuntByteIpv4DscpIntVal	OBJECT-TYPE
	SYNTAX	 Counter64
	MAX-ACCESS read-only
	STATUS current
	DESCRIPTION "Shunt bytes internal (IPv4 DSCP)"

	::={lbShuntByteIpv4DscpInt 1}

lbShuntByteIpv4DscpIntMom	OBJECT-TYPE
	SYNTAX	 CounterBasedGauge64
	MAX-ACCESS read-only
	STATUS current
	DESCRIPTION "Shunt bytes internal (IPv4 DSCP)"

	::={lbShuntByteIpv4DscpInt 2}

lbShuntByteIpv4DscpIntMax	OBJECT-TYPE
	SYNTAX	 CounterBasedGauge64
	MAX-ACCESS read-only
	STATUS current
	DESCRIPTION "Shunt bytes internal (IPv4 DSCP)"

	::={lbShuntByteIpv4DscpInt 3}

lbShuntByteIpv4DscpIntLevelTable OBJECT-TYPE
	SYNTAX      SEQUENCE OF LbShuntByteIpv4DscpIntLevelEntry
	MAX-ACCESS  not-accessible
	STATUS      current
	DESCRIPTION
	"Table for lbShuntByteIpv4DscpInt"
	::={lbShuntByteIpv4DscpInt 4}

lbShuntByteIpv4DscpIntLevelEntry OBJECT-TYPE
	SYNTAX      LbShuntByteIpv4DscpIntLevelEntry
	MAX-ACCESS  not-accessible
	STATUS      current
	DESCRIPTION
	"Table entry for lbShuntByteIpv4DscpInt"
	INDEX { lbShuntByteIpv4DscpIntLevelName }
	::={lbShuntByteIpv4DscpIntLevelTable 1}

LbShuntByteIpv4DscpIntLevelEntry ::=
	SEQUENCE {
		lbShuntByteIpv4DscpIntLevelName	DisplayString,
		lbShuntByteIpv4DscpIntLevelVal	Counter64,
		lbShuntByteIpv4DscpIntLevelMom	CounterBasedGauge64,
		lbShuntByteIpv4DscpIntLevelMax	CounterBasedGauge64
	}

lbShuntByteIpv4DscpIntLevelName OBJECT-TYPE
	SYNTAX      DisplayString
	MAX-ACCESS  not-accessible
	STATUS      current
	DESCRIPTION
	"Table entry display string for lbShuntByteIpv4DscpInt"
	::={lbShuntByteIpv4DscpIntLevelEntry 1}

lbShuntByteIpv4DscpIntLevelVal OBJECT-TYPE
	SYNTAX	 Counter64
	MAX-ACCESS  read-only
	STATUS      current
	DESCRIPTION
	"Table entry attribute for lbShuntByteIpv4DscpInt"
	::={lbShuntByteIpv4DscpIntLevelEntry 2}

lbShuntByteIpv4DscpIntLevelMom OBJECT-TYPE
	SYNTAX	 CounterBasedGauge64
	MAX-ACCESS  read-only
	STATUS      current
	DESCRIPTION
	"Table entry attribute for lbShuntByteIpv4DscpInt"
	::={lbShuntByteIpv4DscpIntLevelEntry 3}

lbShuntByteIpv4DscpIntLevelMax OBJECT-TYPE
	SYNTAX	 CounterBasedGauge64
	MAX-ACCESS  read-only
	STATUS      current
	DESCRIPTION
	"Table entry attribute for lbShuntByteIpv4DscpInt"
	::={lbShuntByteIpv4DscpIntLevelEntry 4}


lbShuntByteIpv4DscpExt	OBJECT IDENTIFIER ::={lb 89}

lbShuntByteIpv4DscpExtVal	OBJECT-TYPE
	SYNTAX	 Counter64
	MAX-ACCESS read-only
	STATUS current
	DESCRIPTION "Shunt bytes external (IPv4 DSCP)"

	::={lbShuntByteIpv4DscpExt 1}

lbShuntByteIpv4DscpExtMom	OBJECT-TYPE
	SYNTAX	 CounterBasedGauge64
	MAX-ACCESS read-only
	STATUS current
	DESCRIPTION "Shunt bytes external (IPv4 DSCP)"

	::={lbShuntByteIpv4DscpExt 2}

lbShuntByteIpv4DscpExtMax	OBJECT-TYPE
	SYNTAX	 CounterBasedGauge64
	MAX-ACCESS read-only
	STATUS current
	DESCRIPTION "Shunt bytes external (IPv4 DSCP)"

	::={lbShuntByteIpv4DscpExt 3}

lbShuntByteIpv4DscpExtLevelTable OBJECT-TYPE
	SYNTAX      SEQUENCE OF LbShuntByteIpv4DscpExtLevelEntry
	MAX-ACCESS  not-accessible
	STATUS      current
	DESCRIPTION
	"Table for lbShuntByteIpv4DscpExt"
	::={lbShuntByteIpv4DscpExt 4}

lbShuntByteIpv4DscpExtLevelEntry OBJECT-TYPE
	SYNTAX      LbShuntByteIpv4DscpExtLevelEntry
	MAX-ACCESS  not-accessible
	STATUS      current
	DESCRIPTION
	"Table entry for lbShuntByteIpv4DscpExt"
	INDEX { lbShuntByteIpv4DscpExtLevelName }
	::={lbShuntByteIpv4DscpExtLevelTable 1}

LbShuntByteIpv4DscpExtLevelEntry ::=
	SEQUENCE {
		lbShuntByteIpv4DscpExtLevelName	DisplayString,
		lbShuntByteIpv4DscpExtLevelVal	Counter64,
		lbShuntByteIpv4DscpExtLevelMom	CounterBasedGauge64,
		lbShuntByteIpv4DscpExtLevelMax	CounterBasedGauge64
	}

lbShuntByteIpv4DscpExtLevelName OBJECT-TYPE
	SYNTAX      DisplayString
	MAX-ACCESS  not-accessible
	STATUS      current
	DESCRIPTION
	"Table entry display string for lbShuntByteIpv4DscpExt"
	::={lbShuntByteIpv4DscpExtLevelEntry 1}

lbShuntByteIpv4DscpExtLevelVal OBJECT-TYPE
	SYNTAX	 Counter64
	MAX-ACCESS  read-only
	STATUS      current
	DESCRIPTION
	"Table entry attribute for lbShuntByteIpv4DscpExt"
	::={lbShuntByteIpv4DscpExtLevelEntry 2}

lbShuntByteIpv4DscpExtLevelMom OBJECT-TYPE
	SYNTAX	 CounterBasedGauge64
	MAX-ACCESS  read-only
	STATUS      current
	DESCRIPTION
	"Table entry attribute for lbShuntByteIpv4DscpExt"
	::={lbShuntByteIpv4DscpExtLevelEntry 3}

lbShuntByteIpv4DscpExtLevelMax OBJECT-TYPE
	SYNTAX	 CounterBasedGauge64
	MAX-ACCESS  read-only
	STATUS      current
	DESCRIPTION
	"Table entry attribute for lbShuntByteIpv4DscpExt"
	::={lbShuntByteIpv4DscpExtLevelEntry 4}


lbShuntPktIpv6DscpInt	OBJECT IDENTIFIER ::={lb 90}

lbShuntPktIpv6DscpIntVal	OBJECT-TYPE
	SYNTAX	 Counter64
	MAX-ACCESS read-only
	STATUS current
	DESCRIPTION "Shunt packets internal (IPv6 DSCP)"

	::={lbShuntPktIpv6DscpInt 1}

lbShuntPktIpv6DscpIntMom	OBJECT-TYPE
	SYNTAX	 CounterBasedGauge64
	MAX-ACCESS read-only
	STATUS current
	DESCRIPTION "Shunt packets internal (IPv6 DSCP)"

	::={lbShuntPktIpv6DscpInt 2}

lbShuntPktIpv6DscpIntMax	OBJECT-TYPE
	SYNTAX	 CounterBasedGauge64
	MAX-ACCESS read-only
	STATUS current
	DESCRIPTION "Shunt packets internal (IPv6 DSCP)"

	::={lbShuntPktIpv6DscpInt 3}

lbShuntPktIpv6DscpIntLevelTable OBJECT-TYPE
	SYNTAX      SEQUENCE OF LbShuntPktIpv6DscpIntLevelEntry
	MAX-ACCESS  not-accessible
	STATUS      current
	DESCRIPTION
	"Table for lbShuntPktIpv6DscpInt"
	::={lbShuntPktIpv6DscpInt 4}

lbShuntPktIpv6DscpIntLevelEntry OBJECT-TYPE
	SYNTAX      LbShuntPktIpv6DscpIntLevelEntry
	MAX-ACCESS  not-accessible
	STATUS      current
	DESCRIPTION
	"Table entry for lbShuntPktIpv6DscpInt"
	INDEX { lbShuntPktIpv6DscpIntLevelName }
	::={lbShuntPktIpv6DscpIntLevelTable 1}

LbShuntPktIpv6DscpIntLevelEntry ::=
	SEQUENCE {
		lbShuntPktIpv6DscpIntLevelName	DisplayString,
		lbShuntPktIpv6DscpIntLevelVal	Counter64,
		lbShuntPktIpv6DscpIntLevelMom	CounterBasedGauge64,
		lbShuntPktIpv6DscpIntLevelMax	CounterBasedGauge64
	}

lbShuntPktIpv6DscpIntLevelName OBJECT-TYPE
	SYNTAX      DisplayString
	MAX-ACCESS  not-accessible
	STATUS      current
	DESCRIPTION
	"Table entry display string for lbShuntPktIpv6DscpInt"
	::={lbShuntPktIpv6DscpIntLevelEntry 1}

lbShuntPktIpv6DscpIntLevelVal OBJECT-TYPE
	SYNTAX	 Counter64
	MAX-ACCESS  read-only
	STATUS      current
	DESCRIPTION
	"Table entry attribute for lbShuntPktIpv6DscpInt"
	::={lbShuntPktIpv6DscpIntLevelEntry 2}

lbShuntPktIpv6DscpIntLevelMom OBJECT-TYPE
	SYNTAX	 CounterBasedGauge64
	MAX-ACCESS  read-only
	STATUS      current
	DESCRIPTION
	"Table entry attribute for lbShuntPktIpv6DscpInt"
	::={lbShuntPktIpv6DscpIntLevelEntry 3}

lbShuntPktIpv6DscpIntLevelMax OBJECT-TYPE
	SYNTAX	 CounterBasedGauge64
	MAX-ACCESS  read-only
	STATUS      current
	DESCRIPTION
	"Table entry attribute for lbShuntPktIpv6DscpInt"
	::={lbShuntPktIpv6DscpIntLevelEntry 4}


lbShuntPktIpv6DscpExt	OBJECT IDENTIFIER ::={lb 91}

lbShuntPktIpv6DscpExtVal	OBJECT-TYPE
	SYNTAX	 Counter64
	MAX-ACCESS read-only
	STATUS current
	DESCRIPTION "Shunt packets external (IPv6 DSCP)"

	::={lbShuntPktIpv6DscpExt 1}

lbShuntPktIpv6DscpExtMom	OBJECT-TYPE
	SYNTAX	 CounterBasedGauge64
	MAX-ACCESS read-only
	STATUS current
	DESCRIPTION "Shunt packets external (IPv6 DSCP)"

	::={lbShuntPktIpv6DscpExt 2}

lbShuntPktIpv6DscpExtMax	OBJECT-TYPE
	SYNTAX	 CounterBasedGauge64
	MAX-ACCESS read-only
	STATUS current
	DESCRIPTION "Shunt packets external (IPv6 DSCP)"

	::={lbShuntPktIpv6DscpExt 3}

lbShuntPktIpv6DscpExtLevelTable OBJECT-TYPE
	SYNTAX      SEQUENCE OF LbShuntPktIpv6DscpExtLevelEntry
	MAX-ACCESS  not-accessible
	STATUS      current
	DESCRIPTION
	"Table for lbShuntPktIpv6DscpExt"
	::={lbShuntPktIpv6DscpExt 4}

lbShuntPktIpv6DscpExtLevelEntry OBJECT-TYPE
	SYNTAX      LbShuntPktIpv6DscpExtLevelEntry
	MAX-ACCESS  not-accessible
	STATUS      current
	DESCRIPTION
	"Table entry for lbShuntPktIpv6DscpExt"
	INDEX { lbShuntPktIpv6DscpExtLevelName }
	::={lbShuntPktIpv6DscpExtLevelTable 1}

LbShuntPktIpv6DscpExtLevelEntry ::=
	SEQUENCE {
		lbShuntPktIpv6DscpExtLevelName	DisplayString,
		lbShuntPktIpv6DscpExtLevelVal	Counter64,
		lbShuntPktIpv6DscpExtLevelMom	CounterBasedGauge64,
		lbShuntPktIpv6DscpExtLevelMax	CounterBasedGauge64
	}

lbShuntPktIpv6DscpExtLevelName OBJECT-TYPE
	SYNTAX      DisplayString
	MAX-ACCESS  not-accessible
	STATUS      current
	DESCRIPTION
	"Table entry display string for lbShuntPktIpv6DscpExt"
	::={lbShuntPktIpv6DscpExtLevelEntry 1}

lbShuntPktIpv6DscpExtLevelVal OBJECT-TYPE
	SYNTAX	 Counter64
	MAX-ACCESS  read-only
	STATUS      current
	DESCRIPTION
	"Table entry attribute for lbShuntPktIpv6DscpExt"
	::={lbShuntPktIpv6DscpExtLevelEntry 2}

lbShuntPktIpv6DscpExtLevelMom OBJECT-TYPE
	SYNTAX	 CounterBasedGauge64
	MAX-ACCESS  read-only
	STATUS      current
	DESCRIPTION
	"Table entry attribute for lbShuntPktIpv6DscpExt"
	::={lbShuntPktIpv6DscpExtLevelEntry 3}

lbShuntPktIpv6DscpExtLevelMax OBJECT-TYPE
	SYNTAX	 CounterBasedGauge64
	MAX-ACCESS  read-only
	STATUS      current
	DESCRIPTION
	"Table entry attribute for lbShuntPktIpv6DscpExt"
	::={lbShuntPktIpv6DscpExtLevelEntry 4}


lbShuntByteIpv6DscpInt	OBJECT IDENTIFIER ::={lb 92}

lbShuntByteIpv6DscpIntVal	OBJECT-TYPE
	SYNTAX	 Counter64
	MAX-ACCESS read-only
	STATUS current
	DESCRIPTION "Shunt bytes internal (IPv6 DSCP)"

	::={lbShuntByteIpv6DscpInt 1}

lbShuntByteIpv6DscpIntMom	OBJECT-TYPE
	SYNTAX	 CounterBasedGauge64
	MAX-ACCESS read-only
	STATUS current
	DESCRIPTION "Shunt bytes internal (IPv6 DSCP)"

	::={lbShuntByteIpv6DscpInt 2}

lbShuntByteIpv6DscpIntMax	OBJECT-TYPE
	SYNTAX	 CounterBasedGauge64
	MAX-ACCESS read-only
	STATUS current
	DESCRIPTION "Shunt bytes internal (IPv6 DSCP)"

	::={lbShuntByteIpv6DscpInt 3}

lbShuntByteIpv6DscpIntLevelTable OBJECT-TYPE
	SYNTAX      SEQUENCE OF LbShuntByteIpv6DscpIntLevelEntry
	MAX-ACCESS  not-accessible
	STATUS      current
	DESCRIPTION
	"Table for lbShuntByteIpv6DscpInt"
	::={lbShuntByteIpv6DscpInt 4}

lbShuntByteIpv6DscpIntLevelEntry OBJECT-TYPE
	SYNTAX      LbShuntByteIpv6DscpIntLevelEntry
	MAX-ACCESS  not-accessible
	STATUS      current
	DESCRIPTION
	"Table entry for lbShuntByteIpv6DscpInt"
	INDEX { lbShuntByteIpv6DscpIntLevelName }
	::={lbShuntByteIpv6DscpIntLevelTable 1}

LbShuntByteIpv6DscpIntLevelEntry ::=
	SEQUENCE {
		lbShuntByteIpv6DscpIntLevelName	DisplayString,
		lbShuntByteIpv6DscpIntLevelVal	Counter64,
		lbShuntByteIpv6DscpIntLevelMom	CounterBasedGauge64,
		lbShuntByteIpv6DscpIntLevelMax	CounterBasedGauge64
	}

lbShuntByteIpv6DscpIntLevelName OBJECT-TYPE
	SYNTAX      DisplayString
	MAX-ACCESS  not-accessible
	STATUS      current
	DESCRIPTION
	"Table entry display string for lbShuntByteIpv6DscpInt"
	::={lbShuntByteIpv6DscpIntLevelEntry 1}

lbShuntByteIpv6DscpIntLevelVal OBJECT-TYPE
	SYNTAX	 Counter64
	MAX-ACCESS  read-only
	STATUS      current
	DESCRIPTION
	"Table entry attribute for lbShuntByteIpv6DscpInt"
	::={lbShuntByteIpv6DscpIntLevelEntry 2}

lbShuntByteIpv6DscpIntLevelMom OBJECT-TYPE
	SYNTAX	 CounterBasedGauge64
	MAX-ACCESS  read-only
	STATUS      current
	DESCRIPTION
	"Table entry attribute for lbShuntByteIpv6DscpInt"
	::={lbShuntByteIpv6DscpIntLevelEntry 3}

lbShuntByteIpv6DscpIntLevelMax OBJECT-TYPE
	SYNTAX	 CounterBasedGauge64
	MAX-ACCESS  read-only
	STATUS      current
	DESCRIPTION
	"Table entry attribute for lbShuntByteIpv6DscpInt"
	::={lbShuntByteIpv6DscpIntLevelEntry 4}


lbShuntByteIpv6DscpExt	OBJECT IDENTIFIER ::={lb 93}

lbShuntByteIpv6DscpExtVal	OBJECT-TYPE
	SYNTAX	 Counter64
	MAX-ACCESS read-only
	STATUS current
	DESCRIPTION "Shunt bytes external (IPv6 DSCP)"

	::={lbShuntByteIpv6DscpExt 1}

lbShuntByteIpv6DscpExtMom	OBJECT-TYPE
	SYNTAX	 CounterBasedGauge64
	MAX-ACCESS read-only
	STATUS current
	DESCRIPTION "Shunt bytes external (IPv6 DSCP)"

	::={lbShuntByteIpv6DscpExt 2}

lbShuntByteIpv6DscpExtMax	OBJECT-TYPE
	SYNTAX	 CounterBasedGauge64
	MAX-ACCESS read-only
	STATUS current
	DESCRIPTION "Shunt bytes external (IPv6 DSCP)"

	::={lbShuntByteIpv6DscpExt 3}

lbShuntByteIpv6DscpExtLevelTable OBJECT-TYPE
	SYNTAX      SEQUENCE OF LbShuntByteIpv6DscpExtLevelEntry
	MAX-ACCESS  not-accessible
	STATUS      current
	DESCRIPTION
	"Table for lbShuntByteIpv6DscpExt"
	::={lbShuntByteIpv6DscpExt 4}

lbShuntByteIpv6DscpExtLevelEntry OBJECT-TYPE
	SYNTAX      LbShuntByteIpv6DscpExtLevelEntry
	MAX-ACCESS  not-accessible
	STATUS      current
	DESCRIPTION
	"Table entry for lbShuntByteIpv6DscpExt"
	INDEX { lbShuntByteIpv6DscpExtLevelName }
	::={lbShuntByteIpv6DscpExtLevelTable 1}

LbShuntByteIpv6DscpExtLevelEntry ::=
	SEQUENCE {
		lbShuntByteIpv6DscpExtLevelName	DisplayString,
		lbShuntByteIpv6DscpExtLevelVal	Counter64,
		lbShuntByteIpv6DscpExtLevelMom	CounterBasedGauge64,
		lbShuntByteIpv6DscpExtLevelMax	CounterBasedGauge64
	}

lbShuntByteIpv6DscpExtLevelName OBJECT-TYPE
	SYNTAX      DisplayString
	MAX-ACCESS  not-accessible
	STATUS      current
	DESCRIPTION
	"Table entry display string for lbShuntByteIpv6DscpExt"
	::={lbShuntByteIpv6DscpExtLevelEntry 1}

lbShuntByteIpv6DscpExtLevelVal OBJECT-TYPE
	SYNTAX	 Counter64
	MAX-ACCESS  read-only
	STATUS      current
	DESCRIPTION
	"Table entry attribute for lbShuntByteIpv6DscpExt"
	::={lbShuntByteIpv6DscpExtLevelEntry 2}

lbShuntByteIpv6DscpExtLevelMom OBJECT-TYPE
	SYNTAX	 CounterBasedGauge64
	MAX-ACCESS  read-only
	STATUS      current
	DESCRIPTION
	"Table entry attribute for lbShuntByteIpv6DscpExt"
	::={lbShuntByteIpv6DscpExtLevelEntry 3}

lbShuntByteIpv6DscpExtLevelMax OBJECT-TYPE
	SYNTAX	 CounterBasedGauge64
	MAX-ACCESS  read-only
	STATUS      current
	DESCRIPTION
	"Table entry attribute for lbShuntByteIpv6DscpExt"
	::={lbShuntByteIpv6DscpExtLevelEntry 4}


lbFPGAFirmwareBuildInt	OBJECT IDENTIFIER ::={lb 94}

lbFPGAFirmwareBuildIntVal	OBJECT-TYPE
	SYNTAX	 CounterBasedGauge64
	MAX-ACCESS read-only
	STATUS current
	DESCRIPTION "FPGA firmware build internal"

	::={lbFPGAFirmwareBuildInt 1}

lbFPGAFirmwareBuildIntMax	OBJECT-TYPE
	SYNTAX	 CounterBasedGauge64
	MAX-ACCESS read-only
	STATUS current
	DESCRIPTION "FPGA firmware build internal"

	::={lbFPGAFirmwareBuildInt 3}

lbFPGAFirmwareBuildIntLevelTable OBJECT-TYPE
	SYNTAX      SEQUENCE OF LbFPGAFirmwareBuildIntLevelEntry
	MAX-ACCESS  not-accessible
	STATUS      current
	DESCRIPTION
	"Table for lbFPGAFirmwareBuildInt"
	::={lbFPGAFirmwareBuildInt 4}

lbFPGAFirmwareBuildIntLevelEntry OBJECT-TYPE
	SYNTAX      LbFPGAFirmwareBuildIntLevelEntry
	MAX-ACCESS  not-accessible
	STATUS      current
	DESCRIPTION
	"Table entry for lbFPGAFirmwareBuildInt"
	INDEX { lbFPGAFirmwareBuildIntLevelName }
	::={lbFPGAFirmwareBuildIntLevelTable 1}

LbFPGAFirmwareBuildIntLevelEntry ::=
	SEQUENCE {
		lbFPGAFirmwareBuildIntLevelName	DisplayString,
		lbFPGAFirmwareBuildIntLevelVal	CounterBasedGauge64,
		lbFPGAFirmwareBuildIntLevelMax	CounterBasedGauge64
	}

lbFPGAFirmwareBuildIntLevelName OBJECT-TYPE
	SYNTAX      DisplayString
	MAX-ACCESS  not-accessible
	STATUS      current
	DESCRIPTION
	"Table entry display string for lbFPGAFirmwareBuildInt"
	::={lbFPGAFirmwareBuildIntLevelEntry 1}

lbFPGAFirmwareBuildIntLevelVal OBJECT-TYPE
	SYNTAX	 CounterBasedGauge64
	MAX-ACCESS  read-only
	STATUS      current
	DESCRIPTION
	"Table entry attribute for lbFPGAFirmwareBuildInt"
	::={lbFPGAFirmwareBuildIntLevelEntry 2}

lbFPGAFirmwareBuildIntLevelMax OBJECT-TYPE
	SYNTAX	 CounterBasedGauge64
	MAX-ACCESS  read-only
	STATUS      current
	DESCRIPTION
	"Table entry attribute for lbFPGAFirmwareBuildInt"
	::={lbFPGAFirmwareBuildIntLevelEntry 4}


lbFPGAFirmwareBuildExt	OBJECT IDENTIFIER ::={lb 95}

lbFPGAFirmwareBuildExtVal	OBJECT-TYPE
	SYNTAX	 CounterBasedGauge64
	MAX-ACCESS read-only
	STATUS current
	DESCRIPTION "FPGA firmware build external"

	::={lbFPGAFirmwareBuildExt 1}

lbFPGAFirmwareBuildExtMax	OBJECT-TYPE
	SYNTAX	 CounterBasedGauge64
	MAX-ACCESS read-only
	STATUS current
	DESCRIPTION "FPGA firmware build external"

	::={lbFPGAFirmwareBuildExt 3}

lbFPGAFirmwareBuildExtLevelTable OBJECT-TYPE
	SYNTAX      SEQUENCE OF LbFPGAFirmwareBuildExtLevelEntry
	MAX-ACCESS  not-accessible
	STATUS      current
	DESCRIPTION
	"Table for lbFPGAFirmwareBuildExt"
	::={lbFPGAFirmwareBuildExt 4}

lbFPGAFirmwareBuildExtLevelEntry OBJECT-TYPE
	SYNTAX      LbFPGAFirmwareBuildExtLevelEntry
	MAX-ACCESS  not-accessible
	STATUS      current
	DESCRIPTION
	"Table entry for lbFPGAFirmwareBuildExt"
	INDEX { lbFPGAFirmwareBuildExtLevelName }
	::={lbFPGAFirmwareBuildExtLevelTable 1}

LbFPGAFirmwareBuildExtLevelEntry ::=
	SEQUENCE {
		lbFPGAFirmwareBuildExtLevelName	DisplayString,
		lbFPGAFirmwareBuildExtLevelVal	CounterBasedGauge64,
		lbFPGAFirmwareBuildExtLevelMax	CounterBasedGauge64
	}

lbFPGAFirmwareBuildExtLevelName OBJECT-TYPE
	SYNTAX      DisplayString
	MAX-ACCESS  not-accessible
	STATUS      current
	DESCRIPTION
	"Table entry display string for lbFPGAFirmwareBuildExt"
	::={lbFPGAFirmwareBuildExtLevelEntry 1}

lbFPGAFirmwareBuildExtLevelVal OBJECT-TYPE
	SYNTAX	 CounterBasedGauge64
	MAX-ACCESS  read-only
	STATUS      current
	DESCRIPTION
	"Table entry attribute for lbFPGAFirmwareBuildExt"
	::={lbFPGAFirmwareBuildExtLevelEntry 2}

lbFPGAFirmwareBuildExtLevelMax OBJECT-TYPE
	SYNTAX	 CounterBasedGauge64
	MAX-ACCESS  read-only
	STATUS      current
	DESCRIPTION
	"Table entry attribute for lbFPGAFirmwareBuildExt"
	::={lbFPGAFirmwareBuildExtLevelEntry 4}


lbRxNsInvalidVer	OBJECT IDENTIFIER ::={lb 96}

lbRxNsInvalidVerVal	OBJECT-TYPE
	SYNTAX	 Counter64
	MAX-ACCESS read-only
	STATUS current
	DESCRIPTION "Incompatible natsync packets"

	::={lbRxNsInvalidVer 1}

lbRxNsInvalidVerMom	OBJECT-TYPE
	SYNTAX	 CounterBasedGauge64
	MAX-ACCESS read-only
	STATUS current
	DESCRIPTION "Incompatible natsync packets"

	::={lbRxNsInvalidVer 2}

lbRxNsInvalidVerMax	OBJECT-TYPE
	SYNTAX	 CounterBasedGauge64
	MAX-ACCESS read-only
	STATUS current
	DESCRIPTION "Incompatible natsync packets"

	::={lbRxNsInvalidVer 3}

lbRxNsInvalidVerLevelTable OBJECT-TYPE
	SYNTAX      SEQUENCE OF LbRxNsInvalidVerLevelEntry
	MAX-ACCESS  not-accessible
	STATUS      current
	DESCRIPTION
	"Table for lbRxNsInvalidVer"
	::={lbRxNsInvalidVer 4}

lbRxNsInvalidVerLevelEntry OBJECT-TYPE
	SYNTAX      LbRxNsInvalidVerLevelEntry
	MAX-ACCESS  not-accessible
	STATUS      current
	DESCRIPTION
	"Table entry for lbRxNsInvalidVer"
	INDEX { lbRxNsInvalidVerLevelName }
	::={lbRxNsInvalidVerLevelTable 1}

LbRxNsInvalidVerLevelEntry ::=
	SEQUENCE {
		lbRxNsInvalidVerLevelName	DisplayString,
		lbRxNsInvalidVerLevelVal	Counter64,
		lbRxNsInvalidVerLevelMom	CounterBasedGauge64,
		lbRxNsInvalidVerLevelMax	CounterBasedGauge64
	}

lbRxNsInvalidVerLevelName OBJECT-TYPE
	SYNTAX      DisplayString
	MAX-ACCESS  not-accessible
	STATUS      current
	DESCRIPTION
	"Table entry display string for lbRxNsInvalidVer"
	::={lbRxNsInvalidVerLevelEntry 1}

lbRxNsInvalidVerLevelVal OBJECT-TYPE
	SYNTAX	 Counter64
	MAX-ACCESS  read-only
	STATUS      current
	DESCRIPTION
	"Table entry attribute for lbRxNsInvalidVer"
	::={lbRxNsInvalidVerLevelEntry 2}

lbRxNsInvalidVerLevelMom OBJECT-TYPE
	SYNTAX	 CounterBasedGauge64
	MAX-ACCESS  read-only
	STATUS      current
	DESCRIPTION
	"Table entry attribute for lbRxNsInvalidVer"
	::={lbRxNsInvalidVerLevelEntry 3}

lbRxNsInvalidVerLevelMax OBJECT-TYPE
	SYNTAX	 CounterBasedGauge64
	MAX-ACCESS  read-only
	STATUS      current
	DESCRIPTION
	"Table entry attribute for lbRxNsInvalidVer"
	::={lbRxNsInvalidVerLevelEntry 4}


lbShuntPktChannelRoleInt	OBJECT IDENTIFIER ::={lb 97}

lbShuntPktChannelRoleIntVal	OBJECT-TYPE
	SYNTAX	 Counter64
	MAX-ACCESS read-only
	STATUS current
	DESCRIPTION "Shunt packets internal (Channel role)"

	::={lbShuntPktChannelRoleInt 1}

lbShuntPktChannelRoleIntMom	OBJECT-TYPE
	SYNTAX	 CounterBasedGauge64
	MAX-ACCESS read-only
	STATUS current
	DESCRIPTION "Shunt packets internal (Channel role)"

	::={lbShuntPktChannelRoleInt 2}

lbShuntPktChannelRoleIntMax	OBJECT-TYPE
	SYNTAX	 CounterBasedGauge64
	MAX-ACCESS read-only
	STATUS current
	DESCRIPTION "Shunt packets internal (Channel role)"

	::={lbShuntPktChannelRoleInt 3}

lbShuntPktChannelRoleIntLevelTable OBJECT-TYPE
	SYNTAX      SEQUENCE OF LbShuntPktChannelRoleIntLevelEntry
	MAX-ACCESS  not-accessible
	STATUS      current
	DESCRIPTION
	"Table for lbShuntPktChannelRoleInt"
	::={lbShuntPktChannelRoleInt 4}

lbShuntPktChannelRoleIntLevelEntry OBJECT-TYPE
	SYNTAX      LbShuntPktChannelRoleIntLevelEntry
	MAX-ACCESS  not-accessible
	STATUS      current
	DESCRIPTION
	"Table entry for lbShuntPktChannelRoleInt"
	INDEX { lbShuntPktChannelRoleIntLevelName }
	::={lbShuntPktChannelRoleIntLevelTable 1}

LbShuntPktChannelRoleIntLevelEntry ::=
	SEQUENCE {
		lbShuntPktChannelRoleIntLevelName	DisplayString,
		lbShuntPktChannelRoleIntLevelVal	Counter64,
		lbShuntPktChannelRoleIntLevelMom	CounterBasedGauge64,
		lbShuntPktChannelRoleIntLevelMax	CounterBasedGauge64
	}

lbShuntPktChannelRoleIntLevelName OBJECT-TYPE
	SYNTAX      DisplayString
	MAX-ACCESS  not-accessible
	STATUS      current
	DESCRIPTION
	"Table entry display string for lbShuntPktChannelRoleInt"
	::={lbShuntPktChannelRoleIntLevelEntry 1}

lbShuntPktChannelRoleIntLevelVal OBJECT-TYPE
	SYNTAX	 Counter64
	MAX-ACCESS  read-only
	STATUS      current
	DESCRIPTION
	"Table entry attribute for lbShuntPktChannelRoleInt"
	::={lbShuntPktChannelRoleIntLevelEntry 2}

lbShuntPktChannelRoleIntLevelMom OBJECT-TYPE
	SYNTAX	 CounterBasedGauge64
	MAX-ACCESS  read-only
	STATUS      current
	DESCRIPTION
	"Table entry attribute for lbShuntPktChannelRoleInt"
	::={lbShuntPktChannelRoleIntLevelEntry 3}

lbShuntPktChannelRoleIntLevelMax OBJECT-TYPE
	SYNTAX	 CounterBasedGauge64
	MAX-ACCESS  read-only
	STATUS      current
	DESCRIPTION
	"Table entry attribute for lbShuntPktChannelRoleInt"
	::={lbShuntPktChannelRoleIntLevelEntry 4}


lbShuntPktChannelRoleExt	OBJECT IDENTIFIER ::={lb 98}

lbShuntPktChannelRoleExtVal	OBJECT-TYPE
	SYNTAX	 Counter64
	MAX-ACCESS read-only
	STATUS current
	DESCRIPTION "Shunt packets external (Channel role)"

	::={lbShuntPktChannelRoleExt 1}

lbShuntPktChannelRoleExtMom	OBJECT-TYPE
	SYNTAX	 CounterBasedGauge64
	MAX-ACCESS read-only
	STATUS current
	DESCRIPTION "Shunt packets external (Channel role)"

	::={lbShuntPktChannelRoleExt 2}

lbShuntPktChannelRoleExtMax	OBJECT-TYPE
	SYNTAX	 CounterBasedGauge64
	MAX-ACCESS read-only
	STATUS current
	DESCRIPTION "Shunt packets external (Channel role)"

	::={lbShuntPktChannelRoleExt 3}

lbShuntPktChannelRoleExtLevelTable OBJECT-TYPE
	SYNTAX      SEQUENCE OF LbShuntPktChannelRoleExtLevelEntry
	MAX-ACCESS  not-accessible
	STATUS      current
	DESCRIPTION
	"Table for lbShuntPktChannelRoleExt"
	::={lbShuntPktChannelRoleExt 4}

lbShuntPktChannelRoleExtLevelEntry OBJECT-TYPE
	SYNTAX      LbShuntPktChannelRoleExtLevelEntry
	MAX-ACCESS  not-accessible
	STATUS      current
	DESCRIPTION
	"Table entry for lbShuntPktChannelRoleExt"
	INDEX { lbShuntPktChannelRoleExtLevelName }
	::={lbShuntPktChannelRoleExtLevelTable 1}

LbShuntPktChannelRoleExtLevelEntry ::=
	SEQUENCE {
		lbShuntPktChannelRoleExtLevelName	DisplayString,
		lbShuntPktChannelRoleExtLevelVal	Counter64,
		lbShuntPktChannelRoleExtLevelMom	CounterBasedGauge64,
		lbShuntPktChannelRoleExtLevelMax	CounterBasedGauge64
	}

lbShuntPktChannelRoleExtLevelName OBJECT-TYPE
	SYNTAX      DisplayString
	MAX-ACCESS  not-accessible
	STATUS      current
	DESCRIPTION
	"Table entry display string for lbShuntPktChannelRoleExt"
	::={lbShuntPktChannelRoleExtLevelEntry 1}

lbShuntPktChannelRoleExtLevelVal OBJECT-TYPE
	SYNTAX	 Counter64
	MAX-ACCESS  read-only
	STATUS      current
	DESCRIPTION
	"Table entry attribute for lbShuntPktChannelRoleExt"
	::={lbShuntPktChannelRoleExtLevelEntry 2}

lbShuntPktChannelRoleExtLevelMom OBJECT-TYPE
	SYNTAX	 CounterBasedGauge64
	MAX-ACCESS  read-only
	STATUS      current
	DESCRIPTION
	"Table entry attribute for lbShuntPktChannelRoleExt"
	::={lbShuntPktChannelRoleExtLevelEntry 3}

lbShuntPktChannelRoleExtLevelMax OBJECT-TYPE
	SYNTAX	 CounterBasedGauge64
	MAX-ACCESS  read-only
	STATUS      current
	DESCRIPTION
	"Table entry attribute for lbShuntPktChannelRoleExt"
	::={lbShuntPktChannelRoleExtLevelEntry 4}


lbShuntByteChannelRoleInt	OBJECT IDENTIFIER ::={lb 99}

lbShuntByteChannelRoleIntVal	OBJECT-TYPE
	SYNTAX	 Counter64
	MAX-ACCESS read-only
	STATUS current
	DESCRIPTION "Shunt bytes internal (Channel role)"

	::={lbShuntByteChannelRoleInt 1}

lbShuntByteChannelRoleIntMom	OBJECT-TYPE
	SYNTAX	 CounterBasedGauge64
	MAX-ACCESS read-only
	STATUS current
	DESCRIPTION "Shunt bytes internal (Channel role)"

	::={lbShuntByteChannelRoleInt 2}

lbShuntByteChannelRoleIntMax	OBJECT-TYPE
	SYNTAX	 CounterBasedGauge64
	MAX-ACCESS read-only
	STATUS current
	DESCRIPTION "Shunt bytes internal (Channel role)"

	::={lbShuntByteChannelRoleInt 3}

lbShuntByteChannelRoleIntLevelTable OBJECT-TYPE
	SYNTAX      SEQUENCE OF LbShuntByteChannelRoleIntLevelEntry
	MAX-ACCESS  not-accessible
	STATUS      current
	DESCRIPTION
	"Table for lbShuntByteChannelRoleInt"
	::={lbShuntByteChannelRoleInt 4}

lbShuntByteChannelRoleIntLevelEntry OBJECT-TYPE
	SYNTAX      LbShuntByteChannelRoleIntLevelEntry
	MAX-ACCESS  not-accessible
	STATUS      current
	DESCRIPTION
	"Table entry for lbShuntByteChannelRoleInt"
	INDEX { lbShuntByteChannelRoleIntLevelName }
	::={lbShuntByteChannelRoleIntLevelTable 1}

LbShuntByteChannelRoleIntLevelEntry ::=
	SEQUENCE {
		lbShuntByteChannelRoleIntLevelName	DisplayString,
		lbShuntByteChannelRoleIntLevelVal	Counter64,
		lbShuntByteChannelRoleIntLevelMom	CounterBasedGauge64,
		lbShuntByteChannelRoleIntLevelMax	CounterBasedGauge64
	}

lbShuntByteChannelRoleIntLevelName OBJECT-TYPE
	SYNTAX      DisplayString
	MAX-ACCESS  not-accessible
	STATUS      current
	DESCRIPTION
	"Table entry display string for lbShuntByteChannelRoleInt"
	::={lbShuntByteChannelRoleIntLevelEntry 1}

lbShuntByteChannelRoleIntLevelVal OBJECT-TYPE
	SYNTAX	 Counter64
	MAX-ACCESS  read-only
	STATUS      current
	DESCRIPTION
	"Table entry attribute for lbShuntByteChannelRoleInt"
	::={lbShuntByteChannelRoleIntLevelEntry 2}

lbShuntByteChannelRoleIntLevelMom OBJECT-TYPE
	SYNTAX	 CounterBasedGauge64
	MAX-ACCESS  read-only
	STATUS      current
	DESCRIPTION
	"Table entry attribute for lbShuntByteChannelRoleInt"
	::={lbShuntByteChannelRoleIntLevelEntry 3}

lbShuntByteChannelRoleIntLevelMax OBJECT-TYPE
	SYNTAX	 CounterBasedGauge64
	MAX-ACCESS  read-only
	STATUS      current
	DESCRIPTION
	"Table entry attribute for lbShuntByteChannelRoleInt"
	::={lbShuntByteChannelRoleIntLevelEntry 4}


lbShuntByteChannelRoleExt	OBJECT IDENTIFIER ::={lb 100}

lbShuntByteChannelRoleExtVal	OBJECT-TYPE
	SYNTAX	 Counter64
	MAX-ACCESS read-only
	STATUS current
	DESCRIPTION "Shunt bytes external (Channel role)"

	::={lbShuntByteChannelRoleExt 1}

lbShuntByteChannelRoleExtMom	OBJECT-TYPE
	SYNTAX	 CounterBasedGauge64
	MAX-ACCESS read-only
	STATUS current
	DESCRIPTION "Shunt bytes external (Channel role)"

	::={lbShuntByteChannelRoleExt 2}

lbShuntByteChannelRoleExtMax	OBJECT-TYPE
	SYNTAX	 CounterBasedGauge64
	MAX-ACCESS read-only
	STATUS current
	DESCRIPTION "Shunt bytes external (Channel role)"

	::={lbShuntByteChannelRoleExt 3}

lbShuntByteChannelRoleExtLevelTable OBJECT-TYPE
	SYNTAX      SEQUENCE OF LbShuntByteChannelRoleExtLevelEntry
	MAX-ACCESS  not-accessible
	STATUS      current
	DESCRIPTION
	"Table for lbShuntByteChannelRoleExt"
	::={lbShuntByteChannelRoleExt 4}

lbShuntByteChannelRoleExtLevelEntry OBJECT-TYPE
	SYNTAX      LbShuntByteChannelRoleExtLevelEntry
	MAX-ACCESS  not-accessible
	STATUS      current
	DESCRIPTION
	"Table entry for lbShuntByteChannelRoleExt"
	INDEX { lbShuntByteChannelRoleExtLevelName }
	::={lbShuntByteChannelRoleExtLevelTable 1}

LbShuntByteChannelRoleExtLevelEntry ::=
	SEQUENCE {
		lbShuntByteChannelRoleExtLevelName	DisplayString,
		lbShuntByteChannelRoleExtLevelVal	Counter64,
		lbShuntByteChannelRoleExtLevelMom	CounterBasedGauge64,
		lbShuntByteChannelRoleExtLevelMax	CounterBasedGauge64
	}

lbShuntByteChannelRoleExtLevelName OBJECT-TYPE
	SYNTAX      DisplayString
	MAX-ACCESS  not-accessible
	STATUS      current
	DESCRIPTION
	"Table entry display string for lbShuntByteChannelRoleExt"
	::={lbShuntByteChannelRoleExtLevelEntry 1}

lbShuntByteChannelRoleExtLevelVal OBJECT-TYPE
	SYNTAX	 Counter64
	MAX-ACCESS  read-only
	STATUS      current
	DESCRIPTION
	"Table entry attribute for lbShuntByteChannelRoleExt"
	::={lbShuntByteChannelRoleExtLevelEntry 2}

lbShuntByteChannelRoleExtLevelMom OBJECT-TYPE
	SYNTAX	 CounterBasedGauge64
	MAX-ACCESS  read-only
	STATUS      current
	DESCRIPTION
	"Table entry attribute for lbShuntByteChannelRoleExt"
	::={lbShuntByteChannelRoleExtLevelEntry 3}

lbShuntByteChannelRoleExtLevelMax OBJECT-TYPE
	SYNTAX	 CounterBasedGauge64
	MAX-ACCESS  read-only
	STATUS      current
	DESCRIPTION
	"Table entry attribute for lbShuntByteChannelRoleExt"
	::={lbShuntByteChannelRoleExtLevelEntry 4}


lbMostLoadFpThreadPackets	OBJECT IDENTIFIER ::={lb 101}

lbMostLoadFpThreadPacketsVal	OBJECT-TYPE
	SYNTAX	 Counter64
	MAX-ACCESS read-only
	STATUS current
	DESCRIPTION "Most loaded fp thread packets"

	::={lbMostLoadFpThreadPackets 1}

lbMostLoadFpThreadPacketsMom	OBJECT-TYPE
	SYNTAX	 CounterBasedGauge64
	MAX-ACCESS read-only
	STATUS current
	DESCRIPTION "Most loaded fp thread packets"

	::={lbMostLoadFpThreadPackets 2}

lbMostLoadFpThreadPacketsMax	OBJECT-TYPE
	SYNTAX	 CounterBasedGauge64
	MAX-ACCESS read-only
	STATUS current
	DESCRIPTION "Most loaded fp thread packets"

	::={lbMostLoadFpThreadPackets 3}

lbMostLoadFpThreadPacketsLevelTable OBJECT-TYPE
	SYNTAX      SEQUENCE OF LbMostLoadFpThreadPacketsLevelEntry
	MAX-ACCESS  not-accessible
	STATUS      current
	DESCRIPTION
	"Table for lbMostLoadFpThreadPackets"
	::={lbMostLoadFpThreadPackets 4}

lbMostLoadFpThreadPacketsLevelEntry OBJECT-TYPE
	SYNTAX      LbMostLoadFpThreadPacketsLevelEntry
	MAX-ACCESS  not-accessible
	STATUS      current
	DESCRIPTION
	"Table entry for lbMostLoadFpThreadPackets"
	INDEX { lbMostLoadFpThreadPacketsLevelName }
	::={lbMostLoadFpThreadPacketsLevelTable 1}

LbMostLoadFpThreadPacketsLevelEntry ::=
	SEQUENCE {
		lbMostLoadFpThreadPacketsLevelName	DisplayString,
		lbMostLoadFpThreadPacketsLevelVal	Counter64,
		lbMostLoadFpThreadPacketsLevelMom	CounterBasedGauge64,
		lbMostLoadFpThreadPacketsLevelMax	CounterBasedGauge64
	}

lbMostLoadFpThreadPacketsLevelName OBJECT-TYPE
	SYNTAX      DisplayString
	MAX-ACCESS  not-accessible
	STATUS      current
	DESCRIPTION
	"Table entry display string for lbMostLoadFpThreadPackets"
	::={lbMostLoadFpThreadPacketsLevelEntry 1}

lbMostLoadFpThreadPacketsLevelVal OBJECT-TYPE
	SYNTAX	 Counter64
	MAX-ACCESS  read-only
	STATUS      current
	DESCRIPTION
	"Table entry attribute for lbMostLoadFpThreadPackets"
	::={lbMostLoadFpThreadPacketsLevelEntry 2}

lbMostLoadFpThreadPacketsLevelMom OBJECT-TYPE
	SYNTAX	 CounterBasedGauge64
	MAX-ACCESS  read-only
	STATUS      current
	DESCRIPTION
	"Table entry attribute for lbMostLoadFpThreadPackets"
	::={lbMostLoadFpThreadPacketsLevelEntry 3}

lbMostLoadFpThreadPacketsLevelMax OBJECT-TYPE
	SYNTAX	 CounterBasedGauge64
	MAX-ACCESS  read-only
	STATUS      current
	DESCRIPTION
	"Table entry attribute for lbMostLoadFpThreadPackets"
	::={lbMostLoadFpThreadPacketsLevelEntry 4}


lbMostLoadFpThreadBuckets	OBJECT IDENTIFIER ::={lb 102}

lbMostLoadFpThreadBucketsVal	OBJECT-TYPE
	SYNTAX	 CounterBasedGauge64
	MAX-ACCESS read-only
	STATUS current
	DESCRIPTION "Most loaded fp thread buckets"

	::={lbMostLoadFpThreadBuckets 1}

lbMostLoadFpThreadBucketsMax	OBJECT-TYPE
	SYNTAX	 CounterBasedGauge64
	MAX-ACCESS read-only
	STATUS current
	DESCRIPTION "Most loaded fp thread buckets"

	::={lbMostLoadFpThreadBuckets 3}

lbMostLoadFpThreadBucketsLevelTable OBJECT-TYPE
	SYNTAX      SEQUENCE OF LbMostLoadFpThreadBucketsLevelEntry
	MAX-ACCESS  not-accessible
	STATUS      current
	DESCRIPTION
	"Table for lbMostLoadFpThreadBuckets"
	::={lbMostLoadFpThreadBuckets 4}

lbMostLoadFpThreadBucketsLevelEntry OBJECT-TYPE
	SYNTAX      LbMostLoadFpThreadBucketsLevelEntry
	MAX-ACCESS  not-accessible
	STATUS      current
	DESCRIPTION
	"Table entry for lbMostLoadFpThreadBuckets"
	INDEX { lbMostLoadFpThreadBucketsLevelName }
	::={lbMostLoadFpThreadBucketsLevelTable 1}

LbMostLoadFpThreadBucketsLevelEntry ::=
	SEQUENCE {
		lbMostLoadFpThreadBucketsLevelName	DisplayString,
		lbMostLoadFpThreadBucketsLevelVal	CounterBasedGauge64,
		lbMostLoadFpThreadBucketsLevelMax	CounterBasedGauge64
	}

lbMostLoadFpThreadBucketsLevelName OBJECT-TYPE
	SYNTAX      DisplayString
	MAX-ACCESS  not-accessible
	STATUS      current
	DESCRIPTION
	"Table entry display string for lbMostLoadFpThreadBuckets"
	::={lbMostLoadFpThreadBucketsLevelEntry 1}

lbMostLoadFpThreadBucketsLevelVal OBJECT-TYPE
	SYNTAX	 CounterBasedGauge64
	MAX-ACCESS  read-only
	STATUS      current
	DESCRIPTION
	"Table entry attribute for lbMostLoadFpThreadBuckets"
	::={lbMostLoadFpThreadBucketsLevelEntry 2}

lbMostLoadFpThreadBucketsLevelMax OBJECT-TYPE
	SYNTAX	 CounterBasedGauge64
	MAX-ACCESS  read-only
	STATUS      current
	DESCRIPTION
	"Table entry attribute for lbMostLoadFpThreadBuckets"
	::={lbMostLoadFpThreadBucketsLevelEntry 4}


lbMostLoadFpThreadBlacklistedBuckets	OBJECT IDENTIFIER ::={lb 103}

lbMostLoadFpThreadBlacklistedBucketsVal	OBJECT-TYPE
	SYNTAX	 CounterBasedGauge64
	MAX-ACCESS read-only
	STATUS current
	DESCRIPTION "Most loaded fp thread blacklisted buckets"

	::={lbMostLoadFpThreadBlacklistedBuckets 1}

lbMostLoadFpThreadBlacklistedBucketsMax	OBJECT-TYPE
	SYNTAX	 CounterBasedGauge64
	MAX-ACCESS read-only
	STATUS current
	DESCRIPTION "Most loaded fp thread blacklisted buckets"

	::={lbMostLoadFpThreadBlacklistedBuckets 3}

lbMostLoadFpThreadBlacklistedBucketsLevelTable OBJECT-TYPE
	SYNTAX      SEQUENCE OF LbMostLoadFpThreadBlacklistedBucketsLevelEntry
	MAX-ACCESS  not-accessible
	STATUS      current
	DESCRIPTION
	"Table for lbMostLoadFpThreadBlacklistedBuckets"
	::={lbMostLoadFpThreadBlacklistedBuckets 4}

lbMostLoadFpThreadBlacklistedBucketsLevelEntry OBJECT-TYPE
	SYNTAX      LbMostLoadFpThreadBlacklistedBucketsLevelEntry
	MAX-ACCESS  not-accessible
	STATUS      current
	DESCRIPTION
	"Table entry for lbMostLoadFpThreadBlacklistedBuckets"
	INDEX { lbMostLoadFpThreadBlacklistedBucketsLevelName }
	::={lbMostLoadFpThreadBlacklistedBucketsLevelTable 1}

LbMostLoadFpThreadBlacklistedBucketsLevelEntry ::=
	SEQUENCE {
		lbMostLoadFpThreadBlacklistedBucketsLevelName	DisplayString,
		lbMostLoadFpThreadBlacklistedBucketsLevelVal	CounterBasedGauge64,
		lbMostLoadFpThreadBlacklistedBucketsLevelMax	CounterBasedGauge64
	}

lbMostLoadFpThreadBlacklistedBucketsLevelName OBJECT-TYPE
	SYNTAX      DisplayString
	MAX-ACCESS  not-accessible
	STATUS      current
	DESCRIPTION
	"Table entry display string for lbMostLoadFpThreadBlacklistedBuckets"
	::={lbMostLoadFpThreadBlacklistedBucketsLevelEntry 1}

lbMostLoadFpThreadBlacklistedBucketsLevelVal OBJECT-TYPE
	SYNTAX	 CounterBasedGauge64
	MAX-ACCESS  read-only
	STATUS      current
	DESCRIPTION
	"Table entry attribute for lbMostLoadFpThreadBlacklistedBuckets"
	::={lbMostLoadFpThreadBlacklistedBucketsLevelEntry 2}

lbMostLoadFpThreadBlacklistedBucketsLevelMax OBJECT-TYPE
	SYNTAX	 CounterBasedGauge64
	MAX-ACCESS  read-only
	STATUS      current
	DESCRIPTION
	"Table entry attribute for lbMostLoadFpThreadBlacklistedBuckets"
	::={lbMostLoadFpThreadBlacklistedBucketsLevelEntry 4}


lbMostLoadFpThreadMostLoadBucketPackets	OBJECT IDENTIFIER ::={lb 104}

lbMostLoadFpThreadMostLoadBucketPacketsVal	OBJECT-TYPE
	SYNTAX	 Counter64
	MAX-ACCESS read-only
	STATUS current
	DESCRIPTION "Most loaded fp thread most loaded bucket packets"

	::={lbMostLoadFpThreadMostLoadBucketPackets 1}

lbMostLoadFpThreadMostLoadBucketPacketsMom	OBJECT-TYPE
	SYNTAX	 CounterBasedGauge64
	MAX-ACCESS read-only
	STATUS current
	DESCRIPTION "Most loaded fp thread most loaded bucket packets"

	::={lbMostLoadFpThreadMostLoadBucketPackets 2}

lbMostLoadFpThreadMostLoadBucketPacketsMax	OBJECT-TYPE
	SYNTAX	 CounterBasedGauge64
	MAX-ACCESS read-only
	STATUS current
	DESCRIPTION "Most loaded fp thread most loaded bucket packets"

	::={lbMostLoadFpThreadMostLoadBucketPackets 3}

lbMostLoadFpThreadMostLoadBucketPacketsLevelTable OBJECT-TYPE
	SYNTAX      SEQUENCE OF LbMostLoadFpThreadMostLoadBucketPacketsLevelEntry
	MAX-ACCESS  not-accessible
	STATUS      current
	DESCRIPTION
	"Table for lbMostLoadFpThreadMostLoadBucketPackets"
	::={lbMostLoadFpThreadMostLoadBucketPackets 4}

lbMostLoadFpThreadMostLoadBucketPacketsLevelEntry OBJECT-TYPE
	SYNTAX      LbMostLoadFpThreadMostLoadBucketPacketsLevelEntry
	MAX-ACCESS  not-accessible
	STATUS      current
	DESCRIPTION
	"Table entry for lbMostLoadFpThreadMostLoadBucketPackets"
	INDEX { lbMostLoadFpThreadMostLoadBucketPacketsLevelName }
	::={lbMostLoadFpThreadMostLoadBucketPacketsLevelTable 1}

LbMostLoadFpThreadMostLoadBucketPacketsLevelEntry ::=
	SEQUENCE {
		lbMostLoadFpThreadMostLoadBucketPacketsLevelName	DisplayString,
		lbMostLoadFpThreadMostLoadBucketPacketsLevelVal	Counter64,
		lbMostLoadFpThreadMostLoadBucketPacketsLevelMom	CounterBasedGauge64,
		lbMostLoadFpThreadMostLoadBucketPacketsLevelMax	CounterBasedGauge64
	}

lbMostLoadFpThreadMostLoadBucketPacketsLevelName OBJECT-TYPE
	SYNTAX      DisplayString
	MAX-ACCESS  not-accessible
	STATUS      current
	DESCRIPTION
	"Table entry display string for lbMostLoadFpThreadMostLoadBucketPackets"
	::={lbMostLoadFpThreadMostLoadBucketPacketsLevelEntry 1}

lbMostLoadFpThreadMostLoadBucketPacketsLevelVal OBJECT-TYPE
	SYNTAX	 Counter64
	MAX-ACCESS  read-only
	STATUS      current
	DESCRIPTION
	"Table entry attribute for lbMostLoadFpThreadMostLoadBucketPackets"
	::={lbMostLoadFpThreadMostLoadBucketPacketsLevelEntry 2}

lbMostLoadFpThreadMostLoadBucketPacketsLevelMom OBJECT-TYPE
	SYNTAX	 CounterBasedGauge64
	MAX-ACCESS  read-only
	STATUS      current
	DESCRIPTION
	"Table entry attribute for lbMostLoadFpThreadMostLoadBucketPackets"
	::={lbMostLoadFpThreadMostLoadBucketPacketsLevelEntry 3}

lbMostLoadFpThreadMostLoadBucketPacketsLevelMax OBJECT-TYPE
	SYNTAX	 CounterBasedGauge64
	MAX-ACCESS  read-only
	STATUS      current
	DESCRIPTION
	"Table entry attribute for lbMostLoadFpThreadMostLoadBucketPackets"
	::={lbMostLoadFpThreadMostLoadBucketPacketsLevelEntry 4}


lbLeastLoadFpThreadPackets	OBJECT IDENTIFIER ::={lb 105}

lbLeastLoadFpThreadPacketsVal	OBJECT-TYPE
	SYNTAX	 Counter64
	MAX-ACCESS read-only
	STATUS current
	DESCRIPTION "Least loaded fp thread packets"

	::={lbLeastLoadFpThreadPackets 1}

lbLeastLoadFpThreadPacketsMom	OBJECT-TYPE
	SYNTAX	 CounterBasedGauge64
	MAX-ACCESS read-only
	STATUS current
	DESCRIPTION "Least loaded fp thread packets"

	::={lbLeastLoadFpThreadPackets 2}

lbLeastLoadFpThreadPacketsMax	OBJECT-TYPE
	SYNTAX	 CounterBasedGauge64
	MAX-ACCESS read-only
	STATUS current
	DESCRIPTION "Least loaded fp thread packets"

	::={lbLeastLoadFpThreadPackets 3}

lbLeastLoadFpThreadPacketsLevelTable OBJECT-TYPE
	SYNTAX      SEQUENCE OF LbLeastLoadFpThreadPacketsLevelEntry
	MAX-ACCESS  not-accessible
	STATUS      current
	DESCRIPTION
	"Table for lbLeastLoadFpThreadPackets"
	::={lbLeastLoadFpThreadPackets 4}

lbLeastLoadFpThreadPacketsLevelEntry OBJECT-TYPE
	SYNTAX      LbLeastLoadFpThreadPacketsLevelEntry
	MAX-ACCESS  not-accessible
	STATUS      current
	DESCRIPTION
	"Table entry for lbLeastLoadFpThreadPackets"
	INDEX { lbLeastLoadFpThreadPacketsLevelName }
	::={lbLeastLoadFpThreadPacketsLevelTable 1}

LbLeastLoadFpThreadPacketsLevelEntry ::=
	SEQUENCE {
		lbLeastLoadFpThreadPacketsLevelName	DisplayString,
		lbLeastLoadFpThreadPacketsLevelVal	Counter64,
		lbLeastLoadFpThreadPacketsLevelMom	CounterBasedGauge64,
		lbLeastLoadFpThreadPacketsLevelMax	CounterBasedGauge64
	}

lbLeastLoadFpThreadPacketsLevelName OBJECT-TYPE
	SYNTAX      DisplayString
	MAX-ACCESS  not-accessible
	STATUS      current
	DESCRIPTION
	"Table entry display string for lbLeastLoadFpThreadPackets"
	::={lbLeastLoadFpThreadPacketsLevelEntry 1}

lbLeastLoadFpThreadPacketsLevelVal OBJECT-TYPE
	SYNTAX	 Counter64
	MAX-ACCESS  read-only
	STATUS      current
	DESCRIPTION
	"Table entry attribute for lbLeastLoadFpThreadPackets"
	::={lbLeastLoadFpThreadPacketsLevelEntry 2}

lbLeastLoadFpThreadPacketsLevelMom OBJECT-TYPE
	SYNTAX	 CounterBasedGauge64
	MAX-ACCESS  read-only
	STATUS      current
	DESCRIPTION
	"Table entry attribute for lbLeastLoadFpThreadPackets"
	::={lbLeastLoadFpThreadPacketsLevelEntry 3}

lbLeastLoadFpThreadPacketsLevelMax OBJECT-TYPE
	SYNTAX	 CounterBasedGauge64
	MAX-ACCESS  read-only
	STATUS      current
	DESCRIPTION
	"Table entry attribute for lbLeastLoadFpThreadPackets"
	::={lbLeastLoadFpThreadPacketsLevelEntry 4}


lbLeastLoadFpThreadBuckets	OBJECT IDENTIFIER ::={lb 106}

lbLeastLoadFpThreadBucketsVal	OBJECT-TYPE
	SYNTAX	 CounterBasedGauge64
	MAX-ACCESS read-only
	STATUS current
	DESCRIPTION "Least loaded fp thread buckets"

	::={lbLeastLoadFpThreadBuckets 1}

lbLeastLoadFpThreadBucketsMax	OBJECT-TYPE
	SYNTAX	 CounterBasedGauge64
	MAX-ACCESS read-only
	STATUS current
	DESCRIPTION "Least loaded fp thread buckets"

	::={lbLeastLoadFpThreadBuckets 3}

lbLeastLoadFpThreadBucketsLevelTable OBJECT-TYPE
	SYNTAX      SEQUENCE OF LbLeastLoadFpThreadBucketsLevelEntry
	MAX-ACCESS  not-accessible
	STATUS      current
	DESCRIPTION
	"Table for lbLeastLoadFpThreadBuckets"
	::={lbLeastLoadFpThreadBuckets 4}

lbLeastLoadFpThreadBucketsLevelEntry OBJECT-TYPE
	SYNTAX      LbLeastLoadFpThreadBucketsLevelEntry
	MAX-ACCESS  not-accessible
	STATUS      current
	DESCRIPTION
	"Table entry for lbLeastLoadFpThreadBuckets"
	INDEX { lbLeastLoadFpThreadBucketsLevelName }
	::={lbLeastLoadFpThreadBucketsLevelTable 1}

LbLeastLoadFpThreadBucketsLevelEntry ::=
	SEQUENCE {
		lbLeastLoadFpThreadBucketsLevelName	DisplayString,
		lbLeastLoadFpThreadBucketsLevelVal	CounterBasedGauge64,
		lbLeastLoadFpThreadBucketsLevelMax	CounterBasedGauge64
	}

lbLeastLoadFpThreadBucketsLevelName OBJECT-TYPE
	SYNTAX      DisplayString
	MAX-ACCESS  not-accessible
	STATUS      current
	DESCRIPTION
	"Table entry display string for lbLeastLoadFpThreadBuckets"
	::={lbLeastLoadFpThreadBucketsLevelEntry 1}

lbLeastLoadFpThreadBucketsLevelVal OBJECT-TYPE
	SYNTAX	 CounterBasedGauge64
	MAX-ACCESS  read-only
	STATUS      current
	DESCRIPTION
	"Table entry attribute for lbLeastLoadFpThreadBuckets"
	::={lbLeastLoadFpThreadBucketsLevelEntry 2}

lbLeastLoadFpThreadBucketsLevelMax OBJECT-TYPE
	SYNTAX	 CounterBasedGauge64
	MAX-ACCESS  read-only
	STATUS      current
	DESCRIPTION
	"Table entry attribute for lbLeastLoadFpThreadBuckets"
	::={lbLeastLoadFpThreadBucketsLevelEntry 4}


lbLeastLoadFpThreadBlacklistedBuckets	OBJECT IDENTIFIER ::={lb 107}

lbLeastLoadFpThreadBlacklistedBucketsVal	OBJECT-TYPE
	SYNTAX	 CounterBasedGauge64
	MAX-ACCESS read-only
	STATUS current
	DESCRIPTION "Least loaded fp thread blacklisted buckets"

	::={lbLeastLoadFpThreadBlacklistedBuckets 1}

lbLeastLoadFpThreadBlacklistedBucketsMax	OBJECT-TYPE
	SYNTAX	 CounterBasedGauge64
	MAX-ACCESS read-only
	STATUS current
	DESCRIPTION "Least loaded fp thread blacklisted buckets"

	::={lbLeastLoadFpThreadBlacklistedBuckets 3}

lbLeastLoadFpThreadBlacklistedBucketsLevelTable OBJECT-TYPE
	SYNTAX      SEQUENCE OF LbLeastLoadFpThreadBlacklistedBucketsLevelEntry
	MAX-ACCESS  not-accessible
	STATUS      current
	DESCRIPTION
	"Table for lbLeastLoadFpThreadBlacklistedBuckets"
	::={lbLeastLoadFpThreadBlacklistedBuckets 4}

lbLeastLoadFpThreadBlacklistedBucketsLevelEntry OBJECT-TYPE
	SYNTAX      LbLeastLoadFpThreadBlacklistedBucketsLevelEntry
	MAX-ACCESS  not-accessible
	STATUS      current
	DESCRIPTION
	"Table entry for lbLeastLoadFpThreadBlacklistedBuckets"
	INDEX { lbLeastLoadFpThreadBlacklistedBucketsLevelName }
	::={lbLeastLoadFpThreadBlacklistedBucketsLevelTable 1}

LbLeastLoadFpThreadBlacklistedBucketsLevelEntry ::=
	SEQUENCE {
		lbLeastLoadFpThreadBlacklistedBucketsLevelName	DisplayString,
		lbLeastLoadFpThreadBlacklistedBucketsLevelVal	CounterBasedGauge64,
		lbLeastLoadFpThreadBlacklistedBucketsLevelMax	CounterBasedGauge64
	}

lbLeastLoadFpThreadBlacklistedBucketsLevelName OBJECT-TYPE
	SYNTAX      DisplayString
	MAX-ACCESS  not-accessible
	STATUS      current
	DESCRIPTION
	"Table entry display string for lbLeastLoadFpThreadBlacklistedBuckets"
	::={lbLeastLoadFpThreadBlacklistedBucketsLevelEntry 1}

lbLeastLoadFpThreadBlacklistedBucketsLevelVal OBJECT-TYPE
	SYNTAX	 CounterBasedGauge64
	MAX-ACCESS  read-only
	STATUS      current
	DESCRIPTION
	"Table entry attribute for lbLeastLoadFpThreadBlacklistedBuckets"
	::={lbLeastLoadFpThreadBlacklistedBucketsLevelEntry 2}

lbLeastLoadFpThreadBlacklistedBucketsLevelMax OBJECT-TYPE
	SYNTAX	 CounterBasedGauge64
	MAX-ACCESS  read-only
	STATUS      current
	DESCRIPTION
	"Table entry attribute for lbLeastLoadFpThreadBlacklistedBuckets"
	::={lbLeastLoadFpThreadBlacklistedBucketsLevelEntry 4}


lbLeastLoadFpThreadMostLoadBucketPackets	OBJECT IDENTIFIER ::={lb 108}

lbLeastLoadFpThreadMostLoadBucketPacketsVal	OBJECT-TYPE
	SYNTAX	 Counter64
	MAX-ACCESS read-only
	STATUS current
	DESCRIPTION "Least loaded fp thread most loaded bucket packets"

	::={lbLeastLoadFpThreadMostLoadBucketPackets 1}

lbLeastLoadFpThreadMostLoadBucketPacketsMom	OBJECT-TYPE
	SYNTAX	 CounterBasedGauge64
	MAX-ACCESS read-only
	STATUS current
	DESCRIPTION "Least loaded fp thread most loaded bucket packets"

	::={lbLeastLoadFpThreadMostLoadBucketPackets 2}

lbLeastLoadFpThreadMostLoadBucketPacketsMax	OBJECT-TYPE
	SYNTAX	 CounterBasedGauge64
	MAX-ACCESS read-only
	STATUS current
	DESCRIPTION "Least loaded fp thread most loaded bucket packets"

	::={lbLeastLoadFpThreadMostLoadBucketPackets 3}

lbLeastLoadFpThreadMostLoadBucketPacketsLevelTable OBJECT-TYPE
	SYNTAX      SEQUENCE OF LbLeastLoadFpThreadMostLoadBucketPacketsLevelEntry
	MAX-ACCESS  not-accessible
	STATUS      current
	DESCRIPTION
	"Table for lbLeastLoadFpThreadMostLoadBucketPackets"
	::={lbLeastLoadFpThreadMostLoadBucketPackets 4}

lbLeastLoadFpThreadMostLoadBucketPacketsLevelEntry OBJECT-TYPE
	SYNTAX      LbLeastLoadFpThreadMostLoadBucketPacketsLevelEntry
	MAX-ACCESS  not-accessible
	STATUS      current
	DESCRIPTION
	"Table entry for lbLeastLoadFpThreadMostLoadBucketPackets"
	INDEX { lbLeastLoadFpThreadMostLoadBucketPacketsLevelName }
	::={lbLeastLoadFpThreadMostLoadBucketPacketsLevelTable 1}

LbLeastLoadFpThreadMostLoadBucketPacketsLevelEntry ::=
	SEQUENCE {
		lbLeastLoadFpThreadMostLoadBucketPacketsLevelName	DisplayString,
		lbLeastLoadFpThreadMostLoadBucketPacketsLevelVal	Counter64,
		lbLeastLoadFpThreadMostLoadBucketPacketsLevelMom	CounterBasedGauge64,
		lbLeastLoadFpThreadMostLoadBucketPacketsLevelMax	CounterBasedGauge64
	}

lbLeastLoadFpThreadMostLoadBucketPacketsLevelName OBJECT-TYPE
	SYNTAX      DisplayString
	MAX-ACCESS  not-accessible
	STATUS      current
	DESCRIPTION
	"Table entry display string for lbLeastLoadFpThreadMostLoadBucketPackets"
	::={lbLeastLoadFpThreadMostLoadBucketPacketsLevelEntry 1}

lbLeastLoadFpThreadMostLoadBucketPacketsLevelVal OBJECT-TYPE
	SYNTAX	 Counter64
	MAX-ACCESS  read-only
	STATUS      current
	DESCRIPTION
	"Table entry attribute for lbLeastLoadFpThreadMostLoadBucketPackets"
	::={lbLeastLoadFpThreadMostLoadBucketPacketsLevelEntry 2}

lbLeastLoadFpThreadMostLoadBucketPacketsLevelMom OBJECT-TYPE
	SYNTAX	 CounterBasedGauge64
	MAX-ACCESS  read-only
	STATUS      current
	DESCRIPTION
	"Table entry attribute for lbLeastLoadFpThreadMostLoadBucketPackets"
	::={lbLeastLoadFpThreadMostLoadBucketPacketsLevelEntry 3}

lbLeastLoadFpThreadMostLoadBucketPacketsLevelMax OBJECT-TYPE
	SYNTAX	 CounterBasedGauge64
	MAX-ACCESS  read-only
	STATUS      current
	DESCRIPTION
	"Table entry attribute for lbLeastLoadFpThreadMostLoadBucketPackets"
	::={lbLeastLoadFpThreadMostLoadBucketPacketsLevelEntry 4}


lbPktUnknownEthertypeInternal	OBJECT IDENTIFIER ::={lb 145}

lbPktUnknownEthertypeInternalVal	OBJECT-TYPE
	SYNTAX	 Counter64
	MAX-ACCESS read-only
	STATUS current
	DESCRIPTION "Unknown ethertype internal"

	::={lbPktUnknownEthertypeInternal 1}

lbPktUnknownEthertypeInternalMom	OBJECT-TYPE
	SYNTAX	 CounterBasedGauge64
	MAX-ACCESS read-only
	STATUS current
	DESCRIPTION "Unknown ethertype internal"

	::={lbPktUnknownEthertypeInternal 2}

lbPktUnknownEthertypeInternalMax	OBJECT-TYPE
	SYNTAX	 CounterBasedGauge64
	MAX-ACCESS read-only
	STATUS current
	DESCRIPTION "Unknown ethertype internal"

	::={lbPktUnknownEthertypeInternal 3}

lbPktUnknownEthertypeInternalLevelTable OBJECT-TYPE
	SYNTAX      SEQUENCE OF LbPktUnknownEthertypeInternalLevelEntry
	MAX-ACCESS  not-accessible
	STATUS      current
	DESCRIPTION
	"Table for lbPktUnknownEthertypeInternal"
	::={lbPktUnknownEthertypeInternal 4}

lbPktUnknownEthertypeInternalLevelEntry OBJECT-TYPE
	SYNTAX      LbPktUnknownEthertypeInternalLevelEntry
	MAX-ACCESS  not-accessible
	STATUS      current
	DESCRIPTION
	"Table entry for lbPktUnknownEthertypeInternal"
	INDEX { lbPktUnknownEthertypeInternalLevelName }
	::={lbPktUnknownEthertypeInternalLevelTable 1}

LbPktUnknownEthertypeInternalLevelEntry ::=
	SEQUENCE {
		lbPktUnknownEthertypeInternalLevelName	DisplayString,
		lbPktUnknownEthertypeInternalLevelVal	Counter64,
		lbPktUnknownEthertypeInternalLevelMom	CounterBasedGauge64,
		lbPktUnknownEthertypeInternalLevelMax	CounterBasedGauge64
	}

lbPktUnknownEthertypeInternalLevelName OBJECT-TYPE
	SYNTAX      DisplayString
	MAX-ACCESS  not-accessible
	STATUS      current
	DESCRIPTION
	"Table entry display string for lbPktUnknownEthertypeInternal"
	::={lbPktUnknownEthertypeInternalLevelEntry 1}

lbPktUnknownEthertypeInternalLevelVal OBJECT-TYPE
	SYNTAX	 Counter64
	MAX-ACCESS  read-only
	STATUS      current
	DESCRIPTION
	"Table entry attribute for lbPktUnknownEthertypeInternal"
	::={lbPktUnknownEthertypeInternalLevelEntry 2}

lbPktUnknownEthertypeInternalLevelMom OBJECT-TYPE
	SYNTAX	 CounterBasedGauge64
	MAX-ACCESS  read-only
	STATUS      current
	DESCRIPTION
	"Table entry attribute for lbPktUnknownEthertypeInternal"
	::={lbPktUnknownEthertypeInternalLevelEntry 3}

lbPktUnknownEthertypeInternalLevelMax OBJECT-TYPE
	SYNTAX	 CounterBasedGauge64
	MAX-ACCESS  read-only
	STATUS      current
	DESCRIPTION
	"Table entry attribute for lbPktUnknownEthertypeInternal"
	::={lbPktUnknownEthertypeInternalLevelEntry 4}


lbPktUnknownEthertypeExternal	OBJECT IDENTIFIER ::={lb 146}

lbPktUnknownEthertypeExternalVal	OBJECT-TYPE
	SYNTAX	 Counter64
	MAX-ACCESS read-only
	STATUS current
	DESCRIPTION "Unknown ethertype external"

	::={lbPktUnknownEthertypeExternal 1}

lbPktUnknownEthertypeExternalMom	OBJECT-TYPE
	SYNTAX	 CounterBasedGauge64
	MAX-ACCESS read-only
	STATUS current
	DESCRIPTION "Unknown ethertype external"

	::={lbPktUnknownEthertypeExternal 2}

lbPktUnknownEthertypeExternalMax	OBJECT-TYPE
	SYNTAX	 CounterBasedGauge64
	MAX-ACCESS read-only
	STATUS current
	DESCRIPTION "Unknown ethertype external"

	::={lbPktUnknownEthertypeExternal 3}

lbPktUnknownEthertypeExternalLevelTable OBJECT-TYPE
	SYNTAX      SEQUENCE OF LbPktUnknownEthertypeExternalLevelEntry
	MAX-ACCESS  not-accessible
	STATUS      current
	DESCRIPTION
	"Table for lbPktUnknownEthertypeExternal"
	::={lbPktUnknownEthertypeExternal 4}

lbPktUnknownEthertypeExternalLevelEntry OBJECT-TYPE
	SYNTAX      LbPktUnknownEthertypeExternalLevelEntry
	MAX-ACCESS  not-accessible
	STATUS      current
	DESCRIPTION
	"Table entry for lbPktUnknownEthertypeExternal"
	INDEX { lbPktUnknownEthertypeExternalLevelName }
	::={lbPktUnknownEthertypeExternalLevelTable 1}

LbPktUnknownEthertypeExternalLevelEntry ::=
	SEQUENCE {
		lbPktUnknownEthertypeExternalLevelName	DisplayString,
		lbPktUnknownEthertypeExternalLevelVal	Counter64,
		lbPktUnknownEthertypeExternalLevelMom	CounterBasedGauge64,
		lbPktUnknownEthertypeExternalLevelMax	CounterBasedGauge64
	}

lbPktUnknownEthertypeExternalLevelName OBJECT-TYPE
	SYNTAX      DisplayString
	MAX-ACCESS  not-accessible
	STATUS      current
	DESCRIPTION
	"Table entry display string for lbPktUnknownEthertypeExternal"
	::={lbPktUnknownEthertypeExternalLevelEntry 1}

lbPktUnknownEthertypeExternalLevelVal OBJECT-TYPE
	SYNTAX	 Counter64
	MAX-ACCESS  read-only
	STATUS      current
	DESCRIPTION
	"Table entry attribute for lbPktUnknownEthertypeExternal"
	::={lbPktUnknownEthertypeExternalLevelEntry 2}

lbPktUnknownEthertypeExternalLevelMom OBJECT-TYPE
	SYNTAX	 CounterBasedGauge64
	MAX-ACCESS  read-only
	STATUS      current
	DESCRIPTION
	"Table entry attribute for lbPktUnknownEthertypeExternal"
	::={lbPktUnknownEthertypeExternalLevelEntry 3}

lbPktUnknownEthertypeExternalLevelMax OBJECT-TYPE
	SYNTAX	 CounterBasedGauge64
	MAX-ACCESS  read-only
	STATUS      current
	DESCRIPTION
	"Table entry attribute for lbPktUnknownEthertypeExternal"
	::={lbPktUnknownEthertypeExternalLevelEntry 4}


lbPktPortInvalidInternal	OBJECT IDENTIFIER ::={lb 147}

lbPktPortInvalidInternalVal	OBJECT-TYPE
	SYNTAX	 Counter64
	MAX-ACCESS read-only
	STATUS current
	DESCRIPTION "Invalid port internal"

	::={lbPktPortInvalidInternal 1}

lbPktPortInvalidInternalMom	OBJECT-TYPE
	SYNTAX	 CounterBasedGauge64
	MAX-ACCESS read-only
	STATUS current
	DESCRIPTION "Invalid port internal"

	::={lbPktPortInvalidInternal 2}

lbPktPortInvalidInternalMax	OBJECT-TYPE
	SYNTAX	 CounterBasedGauge64
	MAX-ACCESS read-only
	STATUS current
	DESCRIPTION "Invalid port internal"

	::={lbPktPortInvalidInternal 3}

lbPktPortInvalidInternalLevelTable OBJECT-TYPE
	SYNTAX      SEQUENCE OF LbPktPortInvalidInternalLevelEntry
	MAX-ACCESS  not-accessible
	STATUS      current
	DESCRIPTION
	"Table for lbPktPortInvalidInternal"
	::={lbPktPortInvalidInternal 4}

lbPktPortInvalidInternalLevelEntry OBJECT-TYPE
	SYNTAX      LbPktPortInvalidInternalLevelEntry
	MAX-ACCESS  not-accessible
	STATUS      current
	DESCRIPTION
	"Table entry for lbPktPortInvalidInternal"
	INDEX { lbPktPortInvalidInternalLevelName }
	::={lbPktPortInvalidInternalLevelTable 1}

LbPktPortInvalidInternalLevelEntry ::=
	SEQUENCE {
		lbPktPortInvalidInternalLevelName	DisplayString,
		lbPktPortInvalidInternalLevelVal	Counter64,
		lbPktPortInvalidInternalLevelMom	CounterBasedGauge64,
		lbPktPortInvalidInternalLevelMax	CounterBasedGauge64
	}

lbPktPortInvalidInternalLevelName OBJECT-TYPE
	SYNTAX      DisplayString
	MAX-ACCESS  not-accessible
	STATUS      current
	DESCRIPTION
	"Table entry display string for lbPktPortInvalidInternal"
	::={lbPktPortInvalidInternalLevelEntry 1}

lbPktPortInvalidInternalLevelVal OBJECT-TYPE
	SYNTAX	 Counter64
	MAX-ACCESS  read-only
	STATUS      current
	DESCRIPTION
	"Table entry attribute for lbPktPortInvalidInternal"
	::={lbPktPortInvalidInternalLevelEntry 2}

lbPktPortInvalidInternalLevelMom OBJECT-TYPE
	SYNTAX	 CounterBasedGauge64
	MAX-ACCESS  read-only
	STATUS      current
	DESCRIPTION
	"Table entry attribute for lbPktPortInvalidInternal"
	::={lbPktPortInvalidInternalLevelEntry 3}

lbPktPortInvalidInternalLevelMax OBJECT-TYPE
	SYNTAX	 CounterBasedGauge64
	MAX-ACCESS  read-only
	STATUS      current
	DESCRIPTION
	"Table entry attribute for lbPktPortInvalidInternal"
	::={lbPktPortInvalidInternalLevelEntry 4}


lbPktPortInvalidExternal	OBJECT IDENTIFIER ::={lb 148}

lbPktPortInvalidExternalVal	OBJECT-TYPE
	SYNTAX	 Counter64
	MAX-ACCESS read-only
	STATUS current
	DESCRIPTION "Invalid port external"

	::={lbPktPortInvalidExternal 1}

lbPktPortInvalidExternalMom	OBJECT-TYPE
	SYNTAX	 CounterBasedGauge64
	MAX-ACCESS read-only
	STATUS current
	DESCRIPTION "Invalid port external"

	::={lbPktPortInvalidExternal 2}

lbPktPortInvalidExternalMax	OBJECT-TYPE
	SYNTAX	 CounterBasedGauge64
	MAX-ACCESS read-only
	STATUS current
	DESCRIPTION "Invalid port external"

	::={lbPktPortInvalidExternal 3}

lbPktPortInvalidExternalLevelTable OBJECT-TYPE
	SYNTAX      SEQUENCE OF LbPktPortInvalidExternalLevelEntry
	MAX-ACCESS  not-accessible
	STATUS      current
	DESCRIPTION
	"Table for lbPktPortInvalidExternal"
	::={lbPktPortInvalidExternal 4}

lbPktPortInvalidExternalLevelEntry OBJECT-TYPE
	SYNTAX      LbPktPortInvalidExternalLevelEntry
	MAX-ACCESS  not-accessible
	STATUS      current
	DESCRIPTION
	"Table entry for lbPktPortInvalidExternal"
	INDEX { lbPktPortInvalidExternalLevelName }
	::={lbPktPortInvalidExternalLevelTable 1}

LbPktPortInvalidExternalLevelEntry ::=
	SEQUENCE {
		lbPktPortInvalidExternalLevelName	DisplayString,
		lbPktPortInvalidExternalLevelVal	Counter64,
		lbPktPortInvalidExternalLevelMom	CounterBasedGauge64,
		lbPktPortInvalidExternalLevelMax	CounterBasedGauge64
	}

lbPktPortInvalidExternalLevelName OBJECT-TYPE
	SYNTAX      DisplayString
	MAX-ACCESS  not-accessible
	STATUS      current
	DESCRIPTION
	"Table entry display string for lbPktPortInvalidExternal"
	::={lbPktPortInvalidExternalLevelEntry 1}

lbPktPortInvalidExternalLevelVal OBJECT-TYPE
	SYNTAX	 Counter64
	MAX-ACCESS  read-only
	STATUS      current
	DESCRIPTION
	"Table entry attribute for lbPktPortInvalidExternal"
	::={lbPktPortInvalidExternalLevelEntry 2}

lbPktPortInvalidExternalLevelMom OBJECT-TYPE
	SYNTAX	 CounterBasedGauge64
	MAX-ACCESS  read-only
	STATUS      current
	DESCRIPTION
	"Table entry attribute for lbPktPortInvalidExternal"
	::={lbPktPortInvalidExternalLevelEntry 3}

lbPktPortInvalidExternalLevelMax OBJECT-TYPE
	SYNTAX	 CounterBasedGauge64
	MAX-ACCESS  read-only
	STATUS      current
	DESCRIPTION
	"Table entry attribute for lbPktPortInvalidExternal"
	::={lbPktPortInvalidExternalLevelEntry 4}


plsd	OBJECT IDENTIFIER ::={sysdiag 136}

plsdDumptime	OBJECT IDENTIFIER ::={plsd 1}

plsdDumptimeVal	OBJECT-TYPE
	SYNTAX	 TimeTicks
	MAX-ACCESS read-only
	STATUS current
	DESCRIPTION "Dump time"

	::={plsdDumptime 1}

plsdDumptimeLevelTable OBJECT-TYPE
	SYNTAX      SEQUENCE OF PlsdDumptimeLevelEntry
	MAX-ACCESS  not-accessible
	STATUS      current
	DESCRIPTION
	"Table for plsdDumptime"
	::={plsdDumptime 2}

plsdDumptimeLevelEntry OBJECT-TYPE
	SYNTAX      PlsdDumptimeLevelEntry
	MAX-ACCESS  not-accessible
	STATUS      current
	DESCRIPTION
	"Table entry for plsdDumptime"
	INDEX { plsdDumptimeLevelName }
	::={plsdDumptimeLevelTable 1}

PlsdDumptimeLevelEntry ::=
	SEQUENCE {
		plsdDumptimeLevelName	DisplayString,
		plsdDumptimeLevelVal	TimeTicks
	}

plsdDumptimeLevelName OBJECT-TYPE
	SYNTAX      DisplayString
	MAX-ACCESS  not-accessible
	STATUS      current
	DESCRIPTION
	"Table entry display string for plsdDumptime"
	::={plsdDumptimeLevelEntry 1}

plsdDumptimeLevelVal OBJECT-TYPE
	SYNTAX	 TimeTicks
	MAX-ACCESS  read-only
	STATUS      current
	DESCRIPTION
	"Table entry attribute for plsdDumptime"
	::={plsdDumptimeLevelEntry 2}


plsdValuesDataset	OBJECT IDENTIFIER ::={plsd 2}

plsdValuesDatasetVal	OBJECT-TYPE
	SYNTAX	 CounterBasedGauge64
	MAX-ACCESS read-only
	STATUS current
	DESCRIPTION "Values in dataset"

	::={plsdValuesDataset 1}

plsdValuesDatasetMax	OBJECT-TYPE
	SYNTAX	 CounterBasedGauge64
	MAX-ACCESS read-only
	STATUS current
	DESCRIPTION "Values in dataset"

	::={plsdValuesDataset 3}

plsdValuesDatasetLevelTable OBJECT-TYPE
	SYNTAX      SEQUENCE OF PlsdValuesDatasetLevelEntry
	MAX-ACCESS  not-accessible
	STATUS      current
	DESCRIPTION
	"Table for plsdValuesDataset"
	::={plsdValuesDataset 4}

plsdValuesDatasetLevelEntry OBJECT-TYPE
	SYNTAX      PlsdValuesDatasetLevelEntry
	MAX-ACCESS  not-accessible
	STATUS      current
	DESCRIPTION
	"Table entry for plsdValuesDataset"
	INDEX { plsdValuesDatasetLevelName }
	::={plsdValuesDatasetLevelTable 1}

PlsdValuesDatasetLevelEntry ::=
	SEQUENCE {
		plsdValuesDatasetLevelName	DisplayString,
		plsdValuesDatasetLevelVal	CounterBasedGauge64,
		plsdValuesDatasetLevelMax	CounterBasedGauge64
	}

plsdValuesDatasetLevelName OBJECT-TYPE
	SYNTAX      DisplayString
	MAX-ACCESS  not-accessible
	STATUS      current
	DESCRIPTION
	"Table entry display string for plsdValuesDataset"
	::={plsdValuesDatasetLevelEntry 1}

plsdValuesDatasetLevelVal OBJECT-TYPE
	SYNTAX	 CounterBasedGauge64
	MAX-ACCESS  read-only
	STATUS      current
	DESCRIPTION
	"Table entry attribute for plsdValuesDataset"
	::={plsdValuesDatasetLevelEntry 2}

plsdValuesDatasetLevelMax OBJECT-TYPE
	SYNTAX	 CounterBasedGauge64
	MAX-ACCESS  read-only
	STATUS      current
	DESCRIPTION
	"Table entry attribute for plsdValuesDataset"
	::={plsdValuesDatasetLevelEntry 4}


plsdValuesDelayedExpand	OBJECT IDENTIFIER ::={plsd 3}

plsdValuesDelayedExpandVal	OBJECT-TYPE
	SYNTAX	 CounterBasedGauge64
	MAX-ACCESS read-only
	STATUS current
	DESCRIPTION "Values in dataset (delayed expand)"

	::={plsdValuesDelayedExpand 1}

plsdValuesDelayedExpandMax	OBJECT-TYPE
	SYNTAX	 CounterBasedGauge64
	MAX-ACCESS read-only
	STATUS current
	DESCRIPTION "Values in dataset (delayed expand)"

	::={plsdValuesDelayedExpand 3}

plsdValuesDelayedExpandLevelTable OBJECT-TYPE
	SYNTAX      SEQUENCE OF PlsdValuesDelayedExpandLevelEntry
	MAX-ACCESS  not-accessible
	STATUS      current
	DESCRIPTION
	"Table for plsdValuesDelayedExpand"
	::={plsdValuesDelayedExpand 4}

plsdValuesDelayedExpandLevelEntry OBJECT-TYPE
	SYNTAX      PlsdValuesDelayedExpandLevelEntry
	MAX-ACCESS  not-accessible
	STATUS      current
	DESCRIPTION
	"Table entry for plsdValuesDelayedExpand"
	INDEX { plsdValuesDelayedExpandLevelName }
	::={plsdValuesDelayedExpandLevelTable 1}

PlsdValuesDelayedExpandLevelEntry ::=
	SEQUENCE {
		plsdValuesDelayedExpandLevelName	DisplayString,
		plsdValuesDelayedExpandLevelVal	CounterBasedGauge64,
		plsdValuesDelayedExpandLevelMax	CounterBasedGauge64
	}

plsdValuesDelayedExpandLevelName OBJECT-TYPE
	SYNTAX      DisplayString
	MAX-ACCESS  not-accessible
	STATUS      current
	DESCRIPTION
	"Table entry display string for plsdValuesDelayedExpand"
	::={plsdValuesDelayedExpandLevelEntry 1}

plsdValuesDelayedExpandLevelVal OBJECT-TYPE
	SYNTAX	 CounterBasedGauge64
	MAX-ACCESS  read-only
	STATUS      current
	DESCRIPTION
	"Table entry attribute for plsdValuesDelayedExpand"
	::={plsdValuesDelayedExpandLevelEntry 2}

plsdValuesDelayedExpandLevelMax OBJECT-TYPE
	SYNTAX	 CounterBasedGauge64
	MAX-ACCESS  read-only
	STATUS      current
	DESCRIPTION
	"Table entry attribute for plsdValuesDelayedExpand"
	::={plsdValuesDelayedExpandLevelEntry 4}


plsdLinksDataset	OBJECT IDENTIFIER ::={plsd 4}

plsdLinksDatasetVal	OBJECT-TYPE
	SYNTAX	 CounterBasedGauge64
	MAX-ACCESS read-only
	STATUS current
	DESCRIPTION "Links in dataset"

	::={plsdLinksDataset 1}

plsdLinksDatasetMax	OBJECT-TYPE
	SYNTAX	 CounterBasedGauge64
	MAX-ACCESS read-only
	STATUS current
	DESCRIPTION "Links in dataset"

	::={plsdLinksDataset 3}

plsdLinksDatasetLevelTable OBJECT-TYPE
	SYNTAX      SEQUENCE OF PlsdLinksDatasetLevelEntry
	MAX-ACCESS  not-accessible
	STATUS      current
	DESCRIPTION
	"Table for plsdLinksDataset"
	::={plsdLinksDataset 4}

plsdLinksDatasetLevelEntry OBJECT-TYPE
	SYNTAX      PlsdLinksDatasetLevelEntry
	MAX-ACCESS  not-accessible
	STATUS      current
	DESCRIPTION
	"Table entry for plsdLinksDataset"
	INDEX { plsdLinksDatasetLevelName }
	::={plsdLinksDatasetLevelTable 1}

PlsdLinksDatasetLevelEntry ::=
	SEQUENCE {
		plsdLinksDatasetLevelName	DisplayString,
		plsdLinksDatasetLevelVal	CounterBasedGauge64,
		plsdLinksDatasetLevelMax	CounterBasedGauge64
	}

plsdLinksDatasetLevelName OBJECT-TYPE
	SYNTAX      DisplayString
	MAX-ACCESS  not-accessible
	STATUS      current
	DESCRIPTION
	"Table entry display string for plsdLinksDataset"
	::={plsdLinksDatasetLevelEntry 1}

plsdLinksDatasetLevelVal OBJECT-TYPE
	SYNTAX	 CounterBasedGauge64
	MAX-ACCESS  read-only
	STATUS      current
	DESCRIPTION
	"Table entry attribute for plsdLinksDataset"
	::={plsdLinksDatasetLevelEntry 2}

plsdLinksDatasetLevelMax OBJECT-TYPE
	SYNTAX	 CounterBasedGauge64
	MAX-ACCESS  read-only
	STATUS      current
	DESCRIPTION
	"Table entry attribute for plsdLinksDataset"
	::={plsdLinksDatasetLevelEntry 4}


plsdValuesAggrDataset	OBJECT IDENTIFIER ::={plsd 5}

plsdValuesAggrDatasetVal	OBJECT-TYPE
	SYNTAX	 CounterBasedGauge64
	MAX-ACCESS read-only
	STATUS current
	DESCRIPTION "Values in dataset(Aggregation)"

	::={plsdValuesAggrDataset 1}

plsdValuesAggrDatasetMax	OBJECT-TYPE
	SYNTAX	 CounterBasedGauge64
	MAX-ACCESS read-only
	STATUS current
	DESCRIPTION "Values in dataset(Aggregation)"

	::={plsdValuesAggrDataset 3}

plsdValuesAggrDatasetLevelTable OBJECT-TYPE
	SYNTAX      SEQUENCE OF PlsdValuesAggrDatasetLevelEntry
	MAX-ACCESS  not-accessible
	STATUS      current
	DESCRIPTION
	"Table for plsdValuesAggrDataset"
	::={plsdValuesAggrDataset 4}

plsdValuesAggrDatasetLevelEntry OBJECT-TYPE
	SYNTAX      PlsdValuesAggrDatasetLevelEntry
	MAX-ACCESS  not-accessible
	STATUS      current
	DESCRIPTION
	"Table entry for plsdValuesAggrDataset"
	INDEX { plsdValuesAggrDatasetLevelName }
	::={plsdValuesAggrDatasetLevelTable 1}

PlsdValuesAggrDatasetLevelEntry ::=
	SEQUENCE {
		plsdValuesAggrDatasetLevelName	DisplayString,
		plsdValuesAggrDatasetLevelVal	CounterBasedGauge64,
		plsdValuesAggrDatasetLevelMax	CounterBasedGauge64
	}

plsdValuesAggrDatasetLevelName OBJECT-TYPE
	SYNTAX      DisplayString
	MAX-ACCESS  not-accessible
	STATUS      current
	DESCRIPTION
	"Table entry display string for plsdValuesAggrDataset"
	::={plsdValuesAggrDatasetLevelEntry 1}

plsdValuesAggrDatasetLevelVal OBJECT-TYPE
	SYNTAX	 CounterBasedGauge64
	MAX-ACCESS  read-only
	STATUS      current
	DESCRIPTION
	"Table entry attribute for plsdValuesAggrDataset"
	::={plsdValuesAggrDatasetLevelEntry 2}

plsdValuesAggrDatasetLevelMax OBJECT-TYPE
	SYNTAX	 CounterBasedGauge64
	MAX-ACCESS  read-only
	STATUS      current
	DESCRIPTION
	"Table entry attribute for plsdValuesAggrDataset"
	::={plsdValuesAggrDatasetLevelEntry 4}


plsdValueReject	OBJECT IDENTIFIER ::={plsd 6}

plsdValueRejectVal	OBJECT-TYPE
	SYNTAX	 Counter64
	MAX-ACCESS read-only
	STATUS current
	DESCRIPTION "Values not created, Cache exhausted"

	::={plsdValueReject 1}

plsdValueRejectMom	OBJECT-TYPE
	SYNTAX	 CounterBasedGauge64
	MAX-ACCESS read-only
	STATUS current
	DESCRIPTION "Values not created, Cache exhausted"

	::={plsdValueReject 2}

plsdValueRejectMax	OBJECT-TYPE
	SYNTAX	 CounterBasedGauge64
	MAX-ACCESS read-only
	STATUS current
	DESCRIPTION "Values not created, Cache exhausted"

	::={plsdValueReject 3}

plsdValueRejectLevelTable OBJECT-TYPE
	SYNTAX      SEQUENCE OF PlsdValueRejectLevelEntry
	MAX-ACCESS  not-accessible
	STATUS      current
	DESCRIPTION
	"Table for plsdValueReject"
	::={plsdValueReject 4}

plsdValueRejectLevelEntry OBJECT-TYPE
	SYNTAX      PlsdValueRejectLevelEntry
	MAX-ACCESS  not-accessible
	STATUS      current
	DESCRIPTION
	"Table entry for plsdValueReject"
	INDEX { plsdValueRejectLevelName }
	::={plsdValueRejectLevelTable 1}

PlsdValueRejectLevelEntry ::=
	SEQUENCE {
		plsdValueRejectLevelName	DisplayString,
		plsdValueRejectLevelVal	Counter64,
		plsdValueRejectLevelMom	CounterBasedGauge64,
		plsdValueRejectLevelMax	CounterBasedGauge64
	}

plsdValueRejectLevelName OBJECT-TYPE
	SYNTAX      DisplayString
	MAX-ACCESS  not-accessible
	STATUS      current
	DESCRIPTION
	"Table entry display string for plsdValueReject"
	::={plsdValueRejectLevelEntry 1}

plsdValueRejectLevelVal OBJECT-TYPE
	SYNTAX	 Counter64
	MAX-ACCESS  read-only
	STATUS      current
	DESCRIPTION
	"Table entry attribute for plsdValueReject"
	::={plsdValueRejectLevelEntry 2}

plsdValueRejectLevelMom OBJECT-TYPE
	SYNTAX	 CounterBasedGauge64
	MAX-ACCESS  read-only
	STATUS      current
	DESCRIPTION
	"Table entry attribute for plsdValueReject"
	::={plsdValueRejectLevelEntry 3}

plsdValueRejectLevelMax OBJECT-TYPE
	SYNTAX	 CounterBasedGauge64
	MAX-ACCESS  read-only
	STATUS      current
	DESCRIPTION
	"Table entry attribute for plsdValueReject"
	::={plsdValueRejectLevelEntry 4}


plsdValueRejectPrior	OBJECT IDENTIFIER ::={plsd 7}

plsdValueRejectPriorVal	OBJECT-TYPE
	SYNTAX	 Counter64
	MAX-ACCESS read-only
	STATUS current
	DESCRIPTION "Values not created, Priority Threshold"

	::={plsdValueRejectPrior 1}

plsdValueRejectPriorMom	OBJECT-TYPE
	SYNTAX	 CounterBasedGauge64
	MAX-ACCESS read-only
	STATUS current
	DESCRIPTION "Values not created, Priority Threshold"

	::={plsdValueRejectPrior 2}

plsdValueRejectPriorMax	OBJECT-TYPE
	SYNTAX	 CounterBasedGauge64
	MAX-ACCESS read-only
	STATUS current
	DESCRIPTION "Values not created, Priority Threshold"

	::={plsdValueRejectPrior 3}

plsdValueRejectPriorLevelTable OBJECT-TYPE
	SYNTAX      SEQUENCE OF PlsdValueRejectPriorLevelEntry
	MAX-ACCESS  not-accessible
	STATUS      current
	DESCRIPTION
	"Table for plsdValueRejectPrior"
	::={plsdValueRejectPrior 4}

plsdValueRejectPriorLevelEntry OBJECT-TYPE
	SYNTAX      PlsdValueRejectPriorLevelEntry
	MAX-ACCESS  not-accessible
	STATUS      current
	DESCRIPTION
	"Table entry for plsdValueRejectPrior"
	INDEX { plsdValueRejectPriorLevelName }
	::={plsdValueRejectPriorLevelTable 1}

PlsdValueRejectPriorLevelEntry ::=
	SEQUENCE {
		plsdValueRejectPriorLevelName	DisplayString,
		plsdValueRejectPriorLevelVal	Counter64,
		plsdValueRejectPriorLevelMom	CounterBasedGauge64,
		plsdValueRejectPriorLevelMax	CounterBasedGauge64
	}

plsdValueRejectPriorLevelName OBJECT-TYPE
	SYNTAX      DisplayString
	MAX-ACCESS  not-accessible
	STATUS      current
	DESCRIPTION
	"Table entry display string for plsdValueRejectPrior"
	::={plsdValueRejectPriorLevelEntry 1}

plsdValueRejectPriorLevelVal OBJECT-TYPE
	SYNTAX	 Counter64
	MAX-ACCESS  read-only
	STATUS      current
	DESCRIPTION
	"Table entry attribute for plsdValueRejectPrior"
	::={plsdValueRejectPriorLevelEntry 2}

plsdValueRejectPriorLevelMom OBJECT-TYPE
	SYNTAX	 CounterBasedGauge64
	MAX-ACCESS  read-only
	STATUS      current
	DESCRIPTION
	"Table entry attribute for plsdValueRejectPrior"
	::={plsdValueRejectPriorLevelEntry 3}

plsdValueRejectPriorLevelMax OBJECT-TYPE
	SYNTAX	 CounterBasedGauge64
	MAX-ACCESS  read-only
	STATUS      current
	DESCRIPTION
	"Table entry attribute for plsdValueRejectPrior"
	::={plsdValueRejectPriorLevelEntry 4}


plsdValuesFiltered	OBJECT IDENTIFIER ::={plsd 8}

plsdValuesFilteredVal	OBJECT-TYPE
	SYNTAX	 CounterBasedGauge64
	MAX-ACCESS read-only
	STATUS current
	DESCRIPTION "Values filtered"

	::={plsdValuesFiltered 1}

plsdValuesFilteredMax	OBJECT-TYPE
	SYNTAX	 CounterBasedGauge64
	MAX-ACCESS read-only
	STATUS current
	DESCRIPTION "Values filtered"

	::={plsdValuesFiltered 3}

plsdValuesFilteredLevelTable OBJECT-TYPE
	SYNTAX      SEQUENCE OF PlsdValuesFilteredLevelEntry
	MAX-ACCESS  not-accessible
	STATUS      current
	DESCRIPTION
	"Table for plsdValuesFiltered"
	::={plsdValuesFiltered 4}

plsdValuesFilteredLevelEntry OBJECT-TYPE
	SYNTAX      PlsdValuesFilteredLevelEntry
	MAX-ACCESS  not-accessible
	STATUS      current
	DESCRIPTION
	"Table entry for plsdValuesFiltered"
	INDEX { plsdValuesFilteredLevelName }
	::={plsdValuesFilteredLevelTable 1}

PlsdValuesFilteredLevelEntry ::=
	SEQUENCE {
		plsdValuesFilteredLevelName	DisplayString,
		plsdValuesFilteredLevelVal	CounterBasedGauge64,
		plsdValuesFilteredLevelMax	CounterBasedGauge64
	}

plsdValuesFilteredLevelName OBJECT-TYPE
	SYNTAX      DisplayString
	MAX-ACCESS  not-accessible
	STATUS      current
	DESCRIPTION
	"Table entry display string for plsdValuesFiltered"
	::={plsdValuesFilteredLevelEntry 1}

plsdValuesFilteredLevelVal OBJECT-TYPE
	SYNTAX	 CounterBasedGauge64
	MAX-ACCESS  read-only
	STATUS      current
	DESCRIPTION
	"Table entry attribute for plsdValuesFiltered"
	::={plsdValuesFilteredLevelEntry 2}

plsdValuesFilteredLevelMax OBJECT-TYPE
	SYNTAX	 CounterBasedGauge64
	MAX-ACCESS  read-only
	STATUS      current
	DESCRIPTION
	"Table entry attribute for plsdValuesFiltered"
	::={plsdValuesFilteredLevelEntry 4}


plsdValuesSent	OBJECT IDENTIFIER ::={plsd 9}

plsdValuesSentVal	OBJECT-TYPE
	SYNTAX	 CounterBasedGauge64
	MAX-ACCESS read-only
	STATUS current
	DESCRIPTION "Values sent to Statwriter"

	::={plsdValuesSent 1}

plsdValuesSentMax	OBJECT-TYPE
	SYNTAX	 CounterBasedGauge64
	MAX-ACCESS read-only
	STATUS current
	DESCRIPTION "Values sent to Statwriter"

	::={plsdValuesSent 3}

plsdValuesSentLevelTable OBJECT-TYPE
	SYNTAX      SEQUENCE OF PlsdValuesSentLevelEntry
	MAX-ACCESS  not-accessible
	STATUS      current
	DESCRIPTION
	"Table for plsdValuesSent"
	::={plsdValuesSent 4}

plsdValuesSentLevelEntry OBJECT-TYPE
	SYNTAX      PlsdValuesSentLevelEntry
	MAX-ACCESS  not-accessible
	STATUS      current
	DESCRIPTION
	"Table entry for plsdValuesSent"
	INDEX { plsdValuesSentLevelName }
	::={plsdValuesSentLevelTable 1}

PlsdValuesSentLevelEntry ::=
	SEQUENCE {
		plsdValuesSentLevelName	DisplayString,
		plsdValuesSentLevelVal	CounterBasedGauge64,
		plsdValuesSentLevelMax	CounterBasedGauge64
	}

plsdValuesSentLevelName OBJECT-TYPE
	SYNTAX      DisplayString
	MAX-ACCESS  not-accessible
	STATUS      current
	DESCRIPTION
	"Table entry display string for plsdValuesSent"
	::={plsdValuesSentLevelEntry 1}

plsdValuesSentLevelVal OBJECT-TYPE
	SYNTAX	 CounterBasedGauge64
	MAX-ACCESS  read-only
	STATUS      current
	DESCRIPTION
	"Table entry attribute for plsdValuesSent"
	::={plsdValuesSentLevelEntry 2}

plsdValuesSentLevelMax OBJECT-TYPE
	SYNTAX	 CounterBasedGauge64
	MAX-ACCESS  read-only
	STATUS      current
	DESCRIPTION
	"Table entry attribute for plsdValuesSent"
	::={plsdValuesSentLevelEntry 4}


plsdValueLookups	OBJECT IDENTIFIER ::={plsd 10}

plsdValueLookupsVal	OBJECT-TYPE
	SYNTAX	 Counter64
	MAX-ACCESS read-only
	STATUS current
	DESCRIPTION "Value lookups"

	::={plsdValueLookups 1}

plsdValueLookupsMom	OBJECT-TYPE
	SYNTAX	 CounterBasedGauge64
	MAX-ACCESS read-only
	STATUS current
	DESCRIPTION "Value lookups"

	::={plsdValueLookups 2}

plsdValueLookupsMax	OBJECT-TYPE
	SYNTAX	 CounterBasedGauge64
	MAX-ACCESS read-only
	STATUS current
	DESCRIPTION "Value lookups"

	::={plsdValueLookups 3}

plsdValueLookupsLevelTable OBJECT-TYPE
	SYNTAX      SEQUENCE OF PlsdValueLookupsLevelEntry
	MAX-ACCESS  not-accessible
	STATUS      current
	DESCRIPTION
	"Table for plsdValueLookups"
	::={plsdValueLookups 4}

plsdValueLookupsLevelEntry OBJECT-TYPE
	SYNTAX      PlsdValueLookupsLevelEntry
	MAX-ACCESS  not-accessible
	STATUS      current
	DESCRIPTION
	"Table entry for plsdValueLookups"
	INDEX { plsdValueLookupsLevelName }
	::={plsdValueLookupsLevelTable 1}

PlsdValueLookupsLevelEntry ::=
	SEQUENCE {
		plsdValueLookupsLevelName	DisplayString,
		plsdValueLookupsLevelVal	Counter64,
		plsdValueLookupsLevelMom	CounterBasedGauge64,
		plsdValueLookupsLevelMax	CounterBasedGauge64
	}

plsdValueLookupsLevelName OBJECT-TYPE
	SYNTAX      DisplayString
	MAX-ACCESS  not-accessible
	STATUS      current
	DESCRIPTION
	"Table entry display string for plsdValueLookups"
	::={plsdValueLookupsLevelEntry 1}

plsdValueLookupsLevelVal OBJECT-TYPE
	SYNTAX	 Counter64
	MAX-ACCESS  read-only
	STATUS      current
	DESCRIPTION
	"Table entry attribute for plsdValueLookups"
	::={plsdValueLookupsLevelEntry 2}

plsdValueLookupsLevelMom OBJECT-TYPE
	SYNTAX	 CounterBasedGauge64
	MAX-ACCESS  read-only
	STATUS      current
	DESCRIPTION
	"Table entry attribute for plsdValueLookups"
	::={plsdValueLookupsLevelEntry 3}

plsdValueLookupsLevelMax OBJECT-TYPE
	SYNTAX	 CounterBasedGauge64
	MAX-ACCESS  read-only
	STATUS      current
	DESCRIPTION
	"Table entry attribute for plsdValueLookups"
	::={plsdValueLookupsLevelEntry 4}


plsdValueUpdatesBytes	OBJECT IDENTIFIER ::={plsd 11}

plsdValueUpdatesBytesVal	OBJECT-TYPE
	SYNTAX	 Counter64
	MAX-ACCESS read-only
	STATUS current
	DESCRIPTION "Value updates(Bytes)"

	::={plsdValueUpdatesBytes 1}

plsdValueUpdatesBytesMom	OBJECT-TYPE
	SYNTAX	 CounterBasedGauge64
	MAX-ACCESS read-only
	STATUS current
	DESCRIPTION "Value updates(Bytes)"

	::={plsdValueUpdatesBytes 2}

plsdValueUpdatesBytesMax	OBJECT-TYPE
	SYNTAX	 CounterBasedGauge64
	MAX-ACCESS read-only
	STATUS current
	DESCRIPTION "Value updates(Bytes)"

	::={plsdValueUpdatesBytes 3}

plsdValueUpdatesBytesLevelTable OBJECT-TYPE
	SYNTAX      SEQUENCE OF PlsdValueUpdatesBytesLevelEntry
	MAX-ACCESS  not-accessible
	STATUS      current
	DESCRIPTION
	"Table for plsdValueUpdatesBytes"
	::={plsdValueUpdatesBytes 4}

plsdValueUpdatesBytesLevelEntry OBJECT-TYPE
	SYNTAX      PlsdValueUpdatesBytesLevelEntry
	MAX-ACCESS  not-accessible
	STATUS      current
	DESCRIPTION
	"Table entry for plsdValueUpdatesBytes"
	INDEX { plsdValueUpdatesBytesLevelName }
	::={plsdValueUpdatesBytesLevelTable 1}

PlsdValueUpdatesBytesLevelEntry ::=
	SEQUENCE {
		plsdValueUpdatesBytesLevelName	DisplayString,
		plsdValueUpdatesBytesLevelVal	Counter64,
		plsdValueUpdatesBytesLevelMom	CounterBasedGauge64,
		plsdValueUpdatesBytesLevelMax	CounterBasedGauge64
	}

plsdValueUpdatesBytesLevelName OBJECT-TYPE
	SYNTAX      DisplayString
	MAX-ACCESS  not-accessible
	STATUS      current
	DESCRIPTION
	"Table entry display string for plsdValueUpdatesBytes"
	::={plsdValueUpdatesBytesLevelEntry 1}

plsdValueUpdatesBytesLevelVal OBJECT-TYPE
	SYNTAX	 Counter64
	MAX-ACCESS  read-only
	STATUS      current
	DESCRIPTION
	"Table entry attribute for plsdValueUpdatesBytes"
	::={plsdValueUpdatesBytesLevelEntry 2}

plsdValueUpdatesBytesLevelMom OBJECT-TYPE
	SYNTAX	 CounterBasedGauge64
	MAX-ACCESS  read-only
	STATUS      current
	DESCRIPTION
	"Table entry attribute for plsdValueUpdatesBytes"
	::={plsdValueUpdatesBytesLevelEntry 3}

plsdValueUpdatesBytesLevelMax OBJECT-TYPE
	SYNTAX	 CounterBasedGauge64
	MAX-ACCESS  read-only
	STATUS      current
	DESCRIPTION
	"Table entry attribute for plsdValueUpdatesBytes"
	::={plsdValueUpdatesBytesLevelEntry 4}


plsdValueUpdatesBytesHp	OBJECT IDENTIFIER ::={plsd 12}

plsdValueUpdatesBytesHpVal	OBJECT-TYPE
	SYNTAX	 Counter64
	MAX-ACCESS read-only
	STATUS current
	DESCRIPTION "Value updates, High Priority (Bytes)"

	::={plsdValueUpdatesBytesHp 1}

plsdValueUpdatesBytesHpMom	OBJECT-TYPE
	SYNTAX	 CounterBasedGauge64
	MAX-ACCESS read-only
	STATUS current
	DESCRIPTION "Value updates, High Priority (Bytes)"

	::={plsdValueUpdatesBytesHp 2}

plsdValueUpdatesBytesHpMax	OBJECT-TYPE
	SYNTAX	 CounterBasedGauge64
	MAX-ACCESS read-only
	STATUS current
	DESCRIPTION "Value updates, High Priority (Bytes)"

	::={plsdValueUpdatesBytesHp 3}

plsdValueUpdatesBytesHpLevelTable OBJECT-TYPE
	SYNTAX      SEQUENCE OF PlsdValueUpdatesBytesHpLevelEntry
	MAX-ACCESS  not-accessible
	STATUS      current
	DESCRIPTION
	"Table for plsdValueUpdatesBytesHp"
	::={plsdValueUpdatesBytesHp 4}

plsdValueUpdatesBytesHpLevelEntry OBJECT-TYPE
	SYNTAX      PlsdValueUpdatesBytesHpLevelEntry
	MAX-ACCESS  not-accessible
	STATUS      current
	DESCRIPTION
	"Table entry for plsdValueUpdatesBytesHp"
	INDEX { plsdValueUpdatesBytesHpLevelName }
	::={plsdValueUpdatesBytesHpLevelTable 1}

PlsdValueUpdatesBytesHpLevelEntry ::=
	SEQUENCE {
		plsdValueUpdatesBytesHpLevelName	DisplayString,
		plsdValueUpdatesBytesHpLevelVal	Counter64,
		plsdValueUpdatesBytesHpLevelMom	CounterBasedGauge64,
		plsdValueUpdatesBytesHpLevelMax	CounterBasedGauge64
	}

plsdValueUpdatesBytesHpLevelName OBJECT-TYPE
	SYNTAX      DisplayString
	MAX-ACCESS  not-accessible
	STATUS      current
	DESCRIPTION
	"Table entry display string for plsdValueUpdatesBytesHp"
	::={plsdValueUpdatesBytesHpLevelEntry 1}

plsdValueUpdatesBytesHpLevelVal OBJECT-TYPE
	SYNTAX	 Counter64
	MAX-ACCESS  read-only
	STATUS      current
	DESCRIPTION
	"Table entry attribute for plsdValueUpdatesBytesHp"
	::={plsdValueUpdatesBytesHpLevelEntry 2}

plsdValueUpdatesBytesHpLevelMom OBJECT-TYPE
	SYNTAX	 CounterBasedGauge64
	MAX-ACCESS  read-only
	STATUS      current
	DESCRIPTION
	"Table entry attribute for plsdValueUpdatesBytesHp"
	::={plsdValueUpdatesBytesHpLevelEntry 3}

plsdValueUpdatesBytesHpLevelMax OBJECT-TYPE
	SYNTAX	 CounterBasedGauge64
	MAX-ACCESS  read-only
	STATUS      current
	DESCRIPTION
	"Table entry attribute for plsdValueUpdatesBytesHp"
	::={plsdValueUpdatesBytesHpLevelEntry 4}


plsdValueUpdatesConns	OBJECT IDENTIFIER ::={plsd 13}

plsdValueUpdatesConnsVal	OBJECT-TYPE
	SYNTAX	 Counter64
	MAX-ACCESS read-only
	STATUS current
	DESCRIPTION "Value updates(Conns)"

	::={plsdValueUpdatesConns 1}

plsdValueUpdatesConnsMom	OBJECT-TYPE
	SYNTAX	 CounterBasedGauge64
	MAX-ACCESS read-only
	STATUS current
	DESCRIPTION "Value updates(Conns)"

	::={plsdValueUpdatesConns 2}

plsdValueUpdatesConnsMax	OBJECT-TYPE
	SYNTAX	 CounterBasedGauge64
	MAX-ACCESS read-only
	STATUS current
	DESCRIPTION "Value updates(Conns)"

	::={plsdValueUpdatesConns 3}

plsdValueUpdatesConnsLevelTable OBJECT-TYPE
	SYNTAX      SEQUENCE OF PlsdValueUpdatesConnsLevelEntry
	MAX-ACCESS  not-accessible
	STATUS      current
	DESCRIPTION
	"Table for plsdValueUpdatesConns"
	::={plsdValueUpdatesConns 4}

plsdValueUpdatesConnsLevelEntry OBJECT-TYPE
	SYNTAX      PlsdValueUpdatesConnsLevelEntry
	MAX-ACCESS  not-accessible
	STATUS      current
	DESCRIPTION
	"Table entry for plsdValueUpdatesConns"
	INDEX { plsdValueUpdatesConnsLevelName }
	::={plsdValueUpdatesConnsLevelTable 1}

PlsdValueUpdatesConnsLevelEntry ::=
	SEQUENCE {
		plsdValueUpdatesConnsLevelName	DisplayString,
		plsdValueUpdatesConnsLevelVal	Counter64,
		plsdValueUpdatesConnsLevelMom	CounterBasedGauge64,
		plsdValueUpdatesConnsLevelMax	CounterBasedGauge64
	}

plsdValueUpdatesConnsLevelName OBJECT-TYPE
	SYNTAX      DisplayString
	MAX-ACCESS  not-accessible
	STATUS      current
	DESCRIPTION
	"Table entry display string for plsdValueUpdatesConns"
	::={plsdValueUpdatesConnsLevelEntry 1}

plsdValueUpdatesConnsLevelVal OBJECT-TYPE
	SYNTAX	 Counter64
	MAX-ACCESS  read-only
	STATUS      current
	DESCRIPTION
	"Table entry attribute for plsdValueUpdatesConns"
	::={plsdValueUpdatesConnsLevelEntry 2}

plsdValueUpdatesConnsLevelMom OBJECT-TYPE
	SYNTAX	 CounterBasedGauge64
	MAX-ACCESS  read-only
	STATUS      current
	DESCRIPTION
	"Table entry attribute for plsdValueUpdatesConns"
	::={plsdValueUpdatesConnsLevelEntry 3}

plsdValueUpdatesConnsLevelMax OBJECT-TYPE
	SYNTAX	 CounterBasedGauge64
	MAX-ACCESS  read-only
	STATUS      current
	DESCRIPTION
	"Table entry attribute for plsdValueUpdatesConns"
	::={plsdValueUpdatesConnsLevelEntry 4}


plsdValueUpdatesConnsHp	OBJECT IDENTIFIER ::={plsd 14}

plsdValueUpdatesConnsHpVal	OBJECT-TYPE
	SYNTAX	 Counter64
	MAX-ACCESS read-only
	STATUS current
	DESCRIPTION "Value updates, High Priority (Conns)"

	::={plsdValueUpdatesConnsHp 1}

plsdValueUpdatesConnsHpMom	OBJECT-TYPE
	SYNTAX	 CounterBasedGauge64
	MAX-ACCESS read-only
	STATUS current
	DESCRIPTION "Value updates, High Priority (Conns)"

	::={plsdValueUpdatesConnsHp 2}

plsdValueUpdatesConnsHpMax	OBJECT-TYPE
	SYNTAX	 CounterBasedGauge64
	MAX-ACCESS read-only
	STATUS current
	DESCRIPTION "Value updates, High Priority (Conns)"

	::={plsdValueUpdatesConnsHp 3}

plsdValueUpdatesConnsHpLevelTable OBJECT-TYPE
	SYNTAX      SEQUENCE OF PlsdValueUpdatesConnsHpLevelEntry
	MAX-ACCESS  not-accessible
	STATUS      current
	DESCRIPTION
	"Table for plsdValueUpdatesConnsHp"
	::={plsdValueUpdatesConnsHp 4}

plsdValueUpdatesConnsHpLevelEntry OBJECT-TYPE
	SYNTAX      PlsdValueUpdatesConnsHpLevelEntry
	MAX-ACCESS  not-accessible
	STATUS      current
	DESCRIPTION
	"Table entry for plsdValueUpdatesConnsHp"
	INDEX { plsdValueUpdatesConnsHpLevelName }
	::={plsdValueUpdatesConnsHpLevelTable 1}

PlsdValueUpdatesConnsHpLevelEntry ::=
	SEQUENCE {
		plsdValueUpdatesConnsHpLevelName	DisplayString,
		plsdValueUpdatesConnsHpLevelVal	Counter64,
		plsdValueUpdatesConnsHpLevelMom	CounterBasedGauge64,
		plsdValueUpdatesConnsHpLevelMax	CounterBasedGauge64
	}

plsdValueUpdatesConnsHpLevelName OBJECT-TYPE
	SYNTAX      DisplayString
	MAX-ACCESS  not-accessible
	STATUS      current
	DESCRIPTION
	"Table entry display string for plsdValueUpdatesConnsHp"
	::={plsdValueUpdatesConnsHpLevelEntry 1}

plsdValueUpdatesConnsHpLevelVal OBJECT-TYPE
	SYNTAX	 Counter64
	MAX-ACCESS  read-only
	STATUS      current
	DESCRIPTION
	"Table entry attribute for plsdValueUpdatesConnsHp"
	::={plsdValueUpdatesConnsHpLevelEntry 2}

plsdValueUpdatesConnsHpLevelMom OBJECT-TYPE
	SYNTAX	 CounterBasedGauge64
	MAX-ACCESS  read-only
	STATUS      current
	DESCRIPTION
	"Table entry attribute for plsdValueUpdatesConnsHp"
	::={plsdValueUpdatesConnsHpLevelEntry 3}

plsdValueUpdatesConnsHpLevelMax OBJECT-TYPE
	SYNTAX	 CounterBasedGauge64
	MAX-ACCESS  read-only
	STATUS      current
	DESCRIPTION
	"Table entry attribute for plsdValueUpdatesConnsHp"
	::={plsdValueUpdatesConnsHpLevelEntry 4}


plsdConnections	OBJECT IDENTIFIER ::={plsd 15}

plsdConnectionsVal	OBJECT-TYPE
	SYNTAX	 CounterBasedGauge64
	MAX-ACCESS read-only
	STATUS current
	DESCRIPTION "Connection table size"

	::={plsdConnections 1}

plsdConnectionsMax	OBJECT-TYPE
	SYNTAX	 CounterBasedGauge64
	MAX-ACCESS read-only
	STATUS current
	DESCRIPTION "Connection table size"

	::={plsdConnections 3}

plsdConnectionsLevelTable OBJECT-TYPE
	SYNTAX      SEQUENCE OF PlsdConnectionsLevelEntry
	MAX-ACCESS  not-accessible
	STATUS      current
	DESCRIPTION
	"Table for plsdConnections"
	::={plsdConnections 4}

plsdConnectionsLevelEntry OBJECT-TYPE
	SYNTAX      PlsdConnectionsLevelEntry
	MAX-ACCESS  not-accessible
	STATUS      current
	DESCRIPTION
	"Table entry for plsdConnections"
	INDEX { plsdConnectionsLevelName }
	::={plsdConnectionsLevelTable 1}

PlsdConnectionsLevelEntry ::=
	SEQUENCE {
		plsdConnectionsLevelName	DisplayString,
		plsdConnectionsLevelVal	CounterBasedGauge64,
		plsdConnectionsLevelMax	CounterBasedGauge64
	}

plsdConnectionsLevelName OBJECT-TYPE
	SYNTAX      DisplayString
	MAX-ACCESS  not-accessible
	STATUS      current
	DESCRIPTION
	"Table entry display string for plsdConnections"
	::={plsdConnectionsLevelEntry 1}

plsdConnectionsLevelVal OBJECT-TYPE
	SYNTAX	 CounterBasedGauge64
	MAX-ACCESS  read-only
	STATUS      current
	DESCRIPTION
	"Table entry attribute for plsdConnections"
	::={plsdConnectionsLevelEntry 2}

plsdConnectionsLevelMax OBJECT-TYPE
	SYNTAX	 CounterBasedGauge64
	MAX-ACCESS  read-only
	STATUS      current
	DESCRIPTION
	"Table entry attribute for plsdConnections"
	::={plsdConnectionsLevelEntry 4}


plsdHosts	OBJECT IDENTIFIER ::={plsd 16}

plsdHostsVal	OBJECT-TYPE
	SYNTAX	 CounterBasedGauge64
	MAX-ACCESS read-only
	STATUS current
	DESCRIPTION "Hosts"

	::={plsdHosts 1}

plsdHostsMax	OBJECT-TYPE
	SYNTAX	 CounterBasedGauge64
	MAX-ACCESS read-only
	STATUS current
	DESCRIPTION "Hosts"

	::={plsdHosts 3}

plsdHostsLevelTable OBJECT-TYPE
	SYNTAX      SEQUENCE OF PlsdHostsLevelEntry
	MAX-ACCESS  not-accessible
	STATUS      current
	DESCRIPTION
	"Table for plsdHosts"
	::={plsdHosts 4}

plsdHostsLevelEntry OBJECT-TYPE
	SYNTAX      PlsdHostsLevelEntry
	MAX-ACCESS  not-accessible
	STATUS      current
	DESCRIPTION
	"Table entry for plsdHosts"
	INDEX { plsdHostsLevelName }
	::={plsdHostsLevelTable 1}

PlsdHostsLevelEntry ::=
	SEQUENCE {
		plsdHostsLevelName	DisplayString,
		plsdHostsLevelVal	CounterBasedGauge64,
		plsdHostsLevelMax	CounterBasedGauge64
	}

plsdHostsLevelName OBJECT-TYPE
	SYNTAX      DisplayString
	MAX-ACCESS  not-accessible
	STATUS      current
	DESCRIPTION
	"Table entry display string for plsdHosts"
	::={plsdHostsLevelEntry 1}

plsdHostsLevelVal OBJECT-TYPE
	SYNTAX	 CounterBasedGauge64
	MAX-ACCESS  read-only
	STATUS      current
	DESCRIPTION
	"Table entry attribute for plsdHosts"
	::={plsdHostsLevelEntry 2}

plsdHostsLevelMax OBJECT-TYPE
	SYNTAX	 CounterBasedGauge64
	MAX-ACCESS  read-only
	STATUS      current
	DESCRIPTION
	"Table entry attribute for plsdHosts"
	::={plsdHostsLevelEntry 4}


plsdConnUpdates	OBJECT IDENTIFIER ::={plsd 17}

plsdConnUpdatesVal	OBJECT-TYPE
	SYNTAX	 Counter64
	MAX-ACCESS read-only
	STATUS current
	DESCRIPTION "Connection updates"

	::={plsdConnUpdates 1}

plsdConnUpdatesMom	OBJECT-TYPE
	SYNTAX	 CounterBasedGauge64
	MAX-ACCESS read-only
	STATUS current
	DESCRIPTION "Connection updates"

	::={plsdConnUpdates 2}

plsdConnUpdatesMax	OBJECT-TYPE
	SYNTAX	 CounterBasedGauge64
	MAX-ACCESS read-only
	STATUS current
	DESCRIPTION "Connection updates"

	::={plsdConnUpdates 3}

plsdConnUpdatesLevelTable OBJECT-TYPE
	SYNTAX      SEQUENCE OF PlsdConnUpdatesLevelEntry
	MAX-ACCESS  not-accessible
	STATUS      current
	DESCRIPTION
	"Table for plsdConnUpdates"
	::={plsdConnUpdates 4}

plsdConnUpdatesLevelEntry OBJECT-TYPE
	SYNTAX      PlsdConnUpdatesLevelEntry
	MAX-ACCESS  not-accessible
	STATUS      current
	DESCRIPTION
	"Table entry for plsdConnUpdates"
	INDEX { plsdConnUpdatesLevelName }
	::={plsdConnUpdatesLevelTable 1}

PlsdConnUpdatesLevelEntry ::=
	SEQUENCE {
		plsdConnUpdatesLevelName	DisplayString,
		plsdConnUpdatesLevelVal	Counter64,
		plsdConnUpdatesLevelMom	CounterBasedGauge64,
		plsdConnUpdatesLevelMax	CounterBasedGauge64
	}

plsdConnUpdatesLevelName OBJECT-TYPE
	SYNTAX      DisplayString
	MAX-ACCESS  not-accessible
	STATUS      current
	DESCRIPTION
	"Table entry display string for plsdConnUpdates"
	::={plsdConnUpdatesLevelEntry 1}

plsdConnUpdatesLevelVal OBJECT-TYPE
	SYNTAX	 Counter64
	MAX-ACCESS  read-only
	STATUS      current
	DESCRIPTION
	"Table entry attribute for plsdConnUpdates"
	::={plsdConnUpdatesLevelEntry 2}

plsdConnUpdatesLevelMom OBJECT-TYPE
	SYNTAX	 CounterBasedGauge64
	MAX-ACCESS  read-only
	STATUS      current
	DESCRIPTION
	"Table entry attribute for plsdConnUpdates"
	::={plsdConnUpdatesLevelEntry 3}

plsdConnUpdatesLevelMax OBJECT-TYPE
	SYNTAX	 CounterBasedGauge64
	MAX-ACCESS  read-only
	STATUS      current
	DESCRIPTION
	"Table entry attribute for plsdConnUpdates"
	::={plsdConnUpdatesLevelEntry 4}


plsdConnUpdatesFull	OBJECT IDENTIFIER ::={plsd 18}

plsdConnUpdatesFullVal	OBJECT-TYPE
	SYNTAX	 Counter64
	MAX-ACCESS read-only
	STATUS current
	DESCRIPTION "Connection updates (Full)"

	::={plsdConnUpdatesFull 1}

plsdConnUpdatesFullMom	OBJECT-TYPE
	SYNTAX	 CounterBasedGauge64
	MAX-ACCESS read-only
	STATUS current
	DESCRIPTION "Connection updates (Full)"

	::={plsdConnUpdatesFull 2}

plsdConnUpdatesFullMax	OBJECT-TYPE
	SYNTAX	 CounterBasedGauge64
	MAX-ACCESS read-only
	STATUS current
	DESCRIPTION "Connection updates (Full)"

	::={plsdConnUpdatesFull 3}

plsdConnUpdatesFullLevelTable OBJECT-TYPE
	SYNTAX      SEQUENCE OF PlsdConnUpdatesFullLevelEntry
	MAX-ACCESS  not-accessible
	STATUS      current
	DESCRIPTION
	"Table for plsdConnUpdatesFull"
	::={plsdConnUpdatesFull 4}

plsdConnUpdatesFullLevelEntry OBJECT-TYPE
	SYNTAX      PlsdConnUpdatesFullLevelEntry
	MAX-ACCESS  not-accessible
	STATUS      current
	DESCRIPTION
	"Table entry for plsdConnUpdatesFull"
	INDEX { plsdConnUpdatesFullLevelName }
	::={plsdConnUpdatesFullLevelTable 1}

PlsdConnUpdatesFullLevelEntry ::=
	SEQUENCE {
		plsdConnUpdatesFullLevelName	DisplayString,
		plsdConnUpdatesFullLevelVal	Counter64,
		plsdConnUpdatesFullLevelMom	CounterBasedGauge64,
		plsdConnUpdatesFullLevelMax	CounterBasedGauge64
	}

plsdConnUpdatesFullLevelName OBJECT-TYPE
	SYNTAX      DisplayString
	MAX-ACCESS  not-accessible
	STATUS      current
	DESCRIPTION
	"Table entry display string for plsdConnUpdatesFull"
	::={plsdConnUpdatesFullLevelEntry 1}

plsdConnUpdatesFullLevelVal OBJECT-TYPE
	SYNTAX	 Counter64
	MAX-ACCESS  read-only
	STATUS      current
	DESCRIPTION
	"Table entry attribute for plsdConnUpdatesFull"
	::={plsdConnUpdatesFullLevelEntry 2}

plsdConnUpdatesFullLevelMom OBJECT-TYPE
	SYNTAX	 CounterBasedGauge64
	MAX-ACCESS  read-only
	STATUS      current
	DESCRIPTION
	"Table entry attribute for plsdConnUpdatesFull"
	::={plsdConnUpdatesFullLevelEntry 3}

plsdConnUpdatesFullLevelMax OBJECT-TYPE
	SYNTAX	 CounterBasedGauge64
	MAX-ACCESS  read-only
	STATUS      current
	DESCRIPTION
	"Table entry attribute for plsdConnUpdatesFull"
	::={plsdConnUpdatesFullLevelEntry 4}


plsdConnUpdatesNew	OBJECT IDENTIFIER ::={plsd 19}

plsdConnUpdatesNewVal	OBJECT-TYPE
	SYNTAX	 Counter64
	MAX-ACCESS read-only
	STATUS current
	DESCRIPTION "Connection updates (New)"

	::={plsdConnUpdatesNew 1}

plsdConnUpdatesNewMom	OBJECT-TYPE
	SYNTAX	 CounterBasedGauge64
	MAX-ACCESS read-only
	STATUS current
	DESCRIPTION "Connection updates (New)"

	::={plsdConnUpdatesNew 2}

plsdConnUpdatesNewMax	OBJECT-TYPE
	SYNTAX	 CounterBasedGauge64
	MAX-ACCESS read-only
	STATUS current
	DESCRIPTION "Connection updates (New)"

	::={plsdConnUpdatesNew 3}

plsdConnUpdatesNewLevelTable OBJECT-TYPE
	SYNTAX      SEQUENCE OF PlsdConnUpdatesNewLevelEntry
	MAX-ACCESS  not-accessible
	STATUS      current
	DESCRIPTION
	"Table for plsdConnUpdatesNew"
	::={plsdConnUpdatesNew 4}

plsdConnUpdatesNewLevelEntry OBJECT-TYPE
	SYNTAX      PlsdConnUpdatesNewLevelEntry
	MAX-ACCESS  not-accessible
	STATUS      current
	DESCRIPTION
	"Table entry for plsdConnUpdatesNew"
	INDEX { plsdConnUpdatesNewLevelName }
	::={plsdConnUpdatesNewLevelTable 1}

PlsdConnUpdatesNewLevelEntry ::=
	SEQUENCE {
		plsdConnUpdatesNewLevelName	DisplayString,
		plsdConnUpdatesNewLevelVal	Counter64,
		plsdConnUpdatesNewLevelMom	CounterBasedGauge64,
		plsdConnUpdatesNewLevelMax	CounterBasedGauge64
	}

plsdConnUpdatesNewLevelName OBJECT-TYPE
	SYNTAX      DisplayString
	MAX-ACCESS  not-accessible
	STATUS      current
	DESCRIPTION
	"Table entry display string for plsdConnUpdatesNew"
	::={plsdConnUpdatesNewLevelEntry 1}

plsdConnUpdatesNewLevelVal OBJECT-TYPE
	SYNTAX	 Counter64
	MAX-ACCESS  read-only
	STATUS      current
	DESCRIPTION
	"Table entry attribute for plsdConnUpdatesNew"
	::={plsdConnUpdatesNewLevelEntry 2}

plsdConnUpdatesNewLevelMom OBJECT-TYPE
	SYNTAX	 CounterBasedGauge64
	MAX-ACCESS  read-only
	STATUS      current
	DESCRIPTION
	"Table entry attribute for plsdConnUpdatesNew"
	::={plsdConnUpdatesNewLevelEntry 3}

plsdConnUpdatesNewLevelMax OBJECT-TYPE
	SYNTAX	 CounterBasedGauge64
	MAX-ACCESS  read-only
	STATUS      current
	DESCRIPTION
	"Table entry attribute for plsdConnUpdatesNew"
	::={plsdConnUpdatesNewLevelEntry 4}


plsdConnUpdatesFiltered	OBJECT IDENTIFIER ::={plsd 20}

plsdConnUpdatesFilteredVal	OBJECT-TYPE
	SYNTAX	 Counter64
	MAX-ACCESS read-only
	STATUS current
	DESCRIPTION "Connection updates (Threshold Filtered)"

	::={plsdConnUpdatesFiltered 1}

plsdConnUpdatesFilteredMom	OBJECT-TYPE
	SYNTAX	 CounterBasedGauge64
	MAX-ACCESS read-only
	STATUS current
	DESCRIPTION "Connection updates (Threshold Filtered)"

	::={plsdConnUpdatesFiltered 2}

plsdConnUpdatesFilteredMax	OBJECT-TYPE
	SYNTAX	 CounterBasedGauge64
	MAX-ACCESS read-only
	STATUS current
	DESCRIPTION "Connection updates (Threshold Filtered)"

	::={plsdConnUpdatesFiltered 3}

plsdConnUpdatesFilteredLevelTable OBJECT-TYPE
	SYNTAX      SEQUENCE OF PlsdConnUpdatesFilteredLevelEntry
	MAX-ACCESS  not-accessible
	STATUS      current
	DESCRIPTION
	"Table for plsdConnUpdatesFiltered"
	::={plsdConnUpdatesFiltered 4}

plsdConnUpdatesFilteredLevelEntry OBJECT-TYPE
	SYNTAX      PlsdConnUpdatesFilteredLevelEntry
	MAX-ACCESS  not-accessible
	STATUS      current
	DESCRIPTION
	"Table entry for plsdConnUpdatesFiltered"
	INDEX { plsdConnUpdatesFilteredLevelName }
	::={plsdConnUpdatesFilteredLevelTable 1}

PlsdConnUpdatesFilteredLevelEntry ::=
	SEQUENCE {
		plsdConnUpdatesFilteredLevelName	DisplayString,
		plsdConnUpdatesFilteredLevelVal	Counter64,
		plsdConnUpdatesFilteredLevelMom	CounterBasedGauge64,
		plsdConnUpdatesFilteredLevelMax	CounterBasedGauge64
	}

plsdConnUpdatesFilteredLevelName OBJECT-TYPE
	SYNTAX      DisplayString
	MAX-ACCESS  not-accessible
	STATUS      current
	DESCRIPTION
	"Table entry display string for plsdConnUpdatesFiltered"
	::={plsdConnUpdatesFilteredLevelEntry 1}

plsdConnUpdatesFilteredLevelVal OBJECT-TYPE
	SYNTAX	 Counter64
	MAX-ACCESS  read-only
	STATUS      current
	DESCRIPTION
	"Table entry attribute for plsdConnUpdatesFiltered"
	::={plsdConnUpdatesFilteredLevelEntry 2}

plsdConnUpdatesFilteredLevelMom OBJECT-TYPE
	SYNTAX	 CounterBasedGauge64
	MAX-ACCESS  read-only
	STATUS      current
	DESCRIPTION
	"Table entry attribute for plsdConnUpdatesFiltered"
	::={plsdConnUpdatesFilteredLevelEntry 3}

plsdConnUpdatesFilteredLevelMax OBJECT-TYPE
	SYNTAX	 CounterBasedGauge64
	MAX-ACCESS  read-only
	STATUS      current
	DESCRIPTION
	"Table entry attribute for plsdConnUpdatesFiltered"
	::={plsdConnUpdatesFilteredLevelEntry 4}


plsdConnsDropped	OBJECT IDENTIFIER ::={plsd 21}

plsdConnsDroppedVal	OBJECT-TYPE
	SYNTAX	 Counter64
	MAX-ACCESS read-only
	STATUS current
	DESCRIPTION "Connections dropped (Cache Exhausted)"

	::={plsdConnsDropped 1}

plsdConnsDroppedMom	OBJECT-TYPE
	SYNTAX	 CounterBasedGauge64
	MAX-ACCESS read-only
	STATUS current
	DESCRIPTION "Connections dropped (Cache Exhausted)"

	::={plsdConnsDropped 2}

plsdConnsDroppedMax	OBJECT-TYPE
	SYNTAX	 CounterBasedGauge64
	MAX-ACCESS read-only
	STATUS current
	DESCRIPTION "Connections dropped (Cache Exhausted)"

	::={plsdConnsDropped 3}

plsdConnsDroppedLevelTable OBJECT-TYPE
	SYNTAX      SEQUENCE OF PlsdConnsDroppedLevelEntry
	MAX-ACCESS  not-accessible
	STATUS      current
	DESCRIPTION
	"Table for plsdConnsDropped"
	::={plsdConnsDropped 4}

plsdConnsDroppedLevelEntry OBJECT-TYPE
	SYNTAX      PlsdConnsDroppedLevelEntry
	MAX-ACCESS  not-accessible
	STATUS      current
	DESCRIPTION
	"Table entry for plsdConnsDropped"
	INDEX { plsdConnsDroppedLevelName }
	::={plsdConnsDroppedLevelTable 1}

PlsdConnsDroppedLevelEntry ::=
	SEQUENCE {
		plsdConnsDroppedLevelName	DisplayString,
		plsdConnsDroppedLevelVal	Counter64,
		plsdConnsDroppedLevelMom	CounterBasedGauge64,
		plsdConnsDroppedLevelMax	CounterBasedGauge64
	}

plsdConnsDroppedLevelName OBJECT-TYPE
	SYNTAX      DisplayString
	MAX-ACCESS  not-accessible
	STATUS      current
	DESCRIPTION
	"Table entry display string for plsdConnsDropped"
	::={plsdConnsDroppedLevelEntry 1}

plsdConnsDroppedLevelVal OBJECT-TYPE
	SYNTAX	 Counter64
	MAX-ACCESS  read-only
	STATUS      current
	DESCRIPTION
	"Table entry attribute for plsdConnsDropped"
	::={plsdConnsDroppedLevelEntry 2}

plsdConnsDroppedLevelMom OBJECT-TYPE
	SYNTAX	 CounterBasedGauge64
	MAX-ACCESS  read-only
	STATUS      current
	DESCRIPTION
	"Table entry attribute for plsdConnsDropped"
	::={plsdConnsDroppedLevelEntry 3}

plsdConnsDroppedLevelMax OBJECT-TYPE
	SYNTAX	 CounterBasedGauge64
	MAX-ACCESS  read-only
	STATUS      current
	DESCRIPTION
	"Table entry attribute for plsdConnsDropped"
	::={plsdConnsDroppedLevelEntry 4}


plsdConnlogConns	OBJECT IDENTIFIER ::={plsd 22}

plsdConnlogConnsVal	OBJECT-TYPE
	SYNTAX	 CounterBasedGauge64
	MAX-ACCESS read-only
	STATUS current
	DESCRIPTION "Connlog connections stored"

	::={plsdConnlogConns 1}

plsdConnlogConnsMax	OBJECT-TYPE
	SYNTAX	 CounterBasedGauge64
	MAX-ACCESS read-only
	STATUS current
	DESCRIPTION "Connlog connections stored"

	::={plsdConnlogConns 3}

plsdConnlogConnsLevelTable OBJECT-TYPE
	SYNTAX      SEQUENCE OF PlsdConnlogConnsLevelEntry
	MAX-ACCESS  not-accessible
	STATUS      current
	DESCRIPTION
	"Table for plsdConnlogConns"
	::={plsdConnlogConns 4}

plsdConnlogConnsLevelEntry OBJECT-TYPE
	SYNTAX      PlsdConnlogConnsLevelEntry
	MAX-ACCESS  not-accessible
	STATUS      current
	DESCRIPTION
	"Table entry for plsdConnlogConns"
	INDEX { plsdConnlogConnsLevelName }
	::={plsdConnlogConnsLevelTable 1}

PlsdConnlogConnsLevelEntry ::=
	SEQUENCE {
		plsdConnlogConnsLevelName	DisplayString,
		plsdConnlogConnsLevelVal	CounterBasedGauge64,
		plsdConnlogConnsLevelMax	CounterBasedGauge64
	}

plsdConnlogConnsLevelName OBJECT-TYPE
	SYNTAX      DisplayString
	MAX-ACCESS  not-accessible
	STATUS      current
	DESCRIPTION
	"Table entry display string for plsdConnlogConns"
	::={plsdConnlogConnsLevelEntry 1}

plsdConnlogConnsLevelVal OBJECT-TYPE
	SYNTAX	 CounterBasedGauge64
	MAX-ACCESS  read-only
	STATUS      current
	DESCRIPTION
	"Table entry attribute for plsdConnlogConns"
	::={plsdConnlogConnsLevelEntry 2}

plsdConnlogConnsLevelMax OBJECT-TYPE
	SYNTAX	 CounterBasedGauge64
	MAX-ACCESS  read-only
	STATUS      current
	DESCRIPTION
	"Table entry attribute for plsdConnlogConns"
	::={plsdConnlogConnsLevelEntry 4}


plsdConnlogConnsAdded	OBJECT IDENTIFIER ::={plsd 23}

plsdConnlogConnsAddedVal	OBJECT-TYPE
	SYNTAX	 Counter64
	MAX-ACCESS read-only
	STATUS current
	DESCRIPTION "Connlog connections added"

	::={plsdConnlogConnsAdded 1}

plsdConnlogConnsAddedMom	OBJECT-TYPE
	SYNTAX	 CounterBasedGauge64
	MAX-ACCESS read-only
	STATUS current
	DESCRIPTION "Connlog connections added"

	::={plsdConnlogConnsAdded 2}

plsdConnlogConnsAddedMax	OBJECT-TYPE
	SYNTAX	 CounterBasedGauge64
	MAX-ACCESS read-only
	STATUS current
	DESCRIPTION "Connlog connections added"

	::={plsdConnlogConnsAdded 3}

plsdConnlogConnsAddedLevelTable OBJECT-TYPE
	SYNTAX      SEQUENCE OF PlsdConnlogConnsAddedLevelEntry
	MAX-ACCESS  not-accessible
	STATUS      current
	DESCRIPTION
	"Table for plsdConnlogConnsAdded"
	::={plsdConnlogConnsAdded 4}

plsdConnlogConnsAddedLevelEntry OBJECT-TYPE
	SYNTAX      PlsdConnlogConnsAddedLevelEntry
	MAX-ACCESS  not-accessible
	STATUS      current
	DESCRIPTION
	"Table entry for plsdConnlogConnsAdded"
	INDEX { plsdConnlogConnsAddedLevelName }
	::={plsdConnlogConnsAddedLevelTable 1}

PlsdConnlogConnsAddedLevelEntry ::=
	SEQUENCE {
		plsdConnlogConnsAddedLevelName	DisplayString,
		plsdConnlogConnsAddedLevelVal	Counter64,
		plsdConnlogConnsAddedLevelMom	CounterBasedGauge64,
		plsdConnlogConnsAddedLevelMax	CounterBasedGauge64
	}

plsdConnlogConnsAddedLevelName OBJECT-TYPE
	SYNTAX      DisplayString
	MAX-ACCESS  not-accessible
	STATUS      current
	DESCRIPTION
	"Table entry display string for plsdConnlogConnsAdded"
	::={plsdConnlogConnsAddedLevelEntry 1}

plsdConnlogConnsAddedLevelVal OBJECT-TYPE
	SYNTAX	 Counter64
	MAX-ACCESS  read-only
	STATUS      current
	DESCRIPTION
	"Table entry attribute for plsdConnlogConnsAdded"
	::={plsdConnlogConnsAddedLevelEntry 2}

plsdConnlogConnsAddedLevelMom OBJECT-TYPE
	SYNTAX	 CounterBasedGauge64
	MAX-ACCESS  read-only
	STATUS      current
	DESCRIPTION
	"Table entry attribute for plsdConnlogConnsAdded"
	::={plsdConnlogConnsAddedLevelEntry 3}

plsdConnlogConnsAddedLevelMax OBJECT-TYPE
	SYNTAX	 CounterBasedGauge64
	MAX-ACCESS  read-only
	STATUS      current
	DESCRIPTION
	"Table entry attribute for plsdConnlogConnsAdded"
	::={plsdConnlogConnsAddedLevelEntry 4}


plsdConnlogDumptimeRemaining	OBJECT IDENTIFIER ::={plsd 24}

plsdConnlogDumptimeRemainingVal	OBJECT-TYPE
	SYNTAX	 TimeTicks
	MAX-ACCESS read-only
	STATUS current
	DESCRIPTION "Connlog time remaining"

	::={plsdConnlogDumptimeRemaining 1}

plsdConnlogDumptimeRemainingLevelTable OBJECT-TYPE
	SYNTAX      SEQUENCE OF PlsdConnlogDumptimeRemainingLevelEntry
	MAX-ACCESS  not-accessible
	STATUS      current
	DESCRIPTION
	"Table for plsdConnlogDumptimeRemaining"
	::={plsdConnlogDumptimeRemaining 2}

plsdConnlogDumptimeRemainingLevelEntry OBJECT-TYPE
	SYNTAX      PlsdConnlogDumptimeRemainingLevelEntry
	MAX-ACCESS  not-accessible
	STATUS      current
	DESCRIPTION
	"Table entry for plsdConnlogDumptimeRemaining"
	INDEX { plsdConnlogDumptimeRemainingLevelName }
	::={plsdConnlogDumptimeRemainingLevelTable 1}

PlsdConnlogDumptimeRemainingLevelEntry ::=
	SEQUENCE {
		plsdConnlogDumptimeRemainingLevelName	DisplayString,
		plsdConnlogDumptimeRemainingLevelVal	TimeTicks
	}

plsdConnlogDumptimeRemainingLevelName OBJECT-TYPE
	SYNTAX      DisplayString
	MAX-ACCESS  not-accessible
	STATUS      current
	DESCRIPTION
	"Table entry display string for plsdConnlogDumptimeRemaining"
	::={plsdConnlogDumptimeRemainingLevelEntry 1}

plsdConnlogDumptimeRemainingLevelVal OBJECT-TYPE
	SYNTAX	 TimeTicks
	MAX-ACCESS  read-only
	STATUS      current
	DESCRIPTION
	"Table entry attribute for plsdConnlogDumptimeRemaining"
	::={plsdConnlogDumptimeRemainingLevelEntry 2}


plsdConnlogConnsDumped	OBJECT IDENTIFIER ::={plsd 25}

plsdConnlogConnsDumpedVal	OBJECT-TYPE
	SYNTAX	 CounterBasedGauge64
	MAX-ACCESS read-only
	STATUS current
	DESCRIPTION "Connlog connections dumped"

	::={plsdConnlogConnsDumped 1}

plsdConnlogConnsDumpedMax	OBJECT-TYPE
	SYNTAX	 CounterBasedGauge64
	MAX-ACCESS read-only
	STATUS current
	DESCRIPTION "Connlog connections dumped"

	::={plsdConnlogConnsDumped 3}

plsdConnlogConnsDumpedLevelTable OBJECT-TYPE
	SYNTAX      SEQUENCE OF PlsdConnlogConnsDumpedLevelEntry
	MAX-ACCESS  not-accessible
	STATUS      current
	DESCRIPTION
	"Table for plsdConnlogConnsDumped"
	::={plsdConnlogConnsDumped 4}

plsdConnlogConnsDumpedLevelEntry OBJECT-TYPE
	SYNTAX      PlsdConnlogConnsDumpedLevelEntry
	MAX-ACCESS  not-accessible
	STATUS      current
	DESCRIPTION
	"Table entry for plsdConnlogConnsDumped"
	INDEX { plsdConnlogConnsDumpedLevelName }
	::={plsdConnlogConnsDumpedLevelTable 1}

PlsdConnlogConnsDumpedLevelEntry ::=
	SEQUENCE {
		plsdConnlogConnsDumpedLevelName	DisplayString,
		plsdConnlogConnsDumpedLevelVal	CounterBasedGauge64,
		plsdConnlogConnsDumpedLevelMax	CounterBasedGauge64
	}

plsdConnlogConnsDumpedLevelName OBJECT-TYPE
	SYNTAX      DisplayString
	MAX-ACCESS  not-accessible
	STATUS      current
	DESCRIPTION
	"Table entry display string for plsdConnlogConnsDumped"
	::={plsdConnlogConnsDumpedLevelEntry 1}

plsdConnlogConnsDumpedLevelVal OBJECT-TYPE
	SYNTAX	 CounterBasedGauge64
	MAX-ACCESS  read-only
	STATUS      current
	DESCRIPTION
	"Table entry attribute for plsdConnlogConnsDumped"
	::={plsdConnlogConnsDumpedLevelEntry 2}

plsdConnlogConnsDumpedLevelMax OBJECT-TYPE
	SYNTAX	 CounterBasedGauge64
	MAX-ACCESS  read-only
	STATUS      current
	DESCRIPTION
	"Table entry attribute for plsdConnlogConnsDumped"
	::={plsdConnlogConnsDumpedLevelEntry 4}


plsdConnlogDumptime	OBJECT IDENTIFIER ::={plsd 26}

plsdConnlogDumptimeVal	OBJECT-TYPE
	SYNTAX	 TimeTicks
	MAX-ACCESS read-only
	STATUS current
	DESCRIPTION "Connlog dumptime"

	::={plsdConnlogDumptime 1}

plsdConnlogDumptimeLevelTable OBJECT-TYPE
	SYNTAX      SEQUENCE OF PlsdConnlogDumptimeLevelEntry
	MAX-ACCESS  not-accessible
	STATUS      current
	DESCRIPTION
	"Table for plsdConnlogDumptime"
	::={plsdConnlogDumptime 2}

plsdConnlogDumptimeLevelEntry OBJECT-TYPE
	SYNTAX      PlsdConnlogDumptimeLevelEntry
	MAX-ACCESS  not-accessible
	STATUS      current
	DESCRIPTION
	"Table entry for plsdConnlogDumptime"
	INDEX { plsdConnlogDumptimeLevelName }
	::={plsdConnlogDumptimeLevelTable 1}

PlsdConnlogDumptimeLevelEntry ::=
	SEQUENCE {
		plsdConnlogDumptimeLevelName	DisplayString,
		plsdConnlogDumptimeLevelVal	TimeTicks
	}

plsdConnlogDumptimeLevelName OBJECT-TYPE
	SYNTAX      DisplayString
	MAX-ACCESS  not-accessible
	STATUS      current
	DESCRIPTION
	"Table entry display string for plsdConnlogDumptime"
	::={plsdConnlogDumptimeLevelEntry 1}

plsdConnlogDumptimeLevelVal OBJECT-TYPE
	SYNTAX	 TimeTicks
	MAX-ACCESS  read-only
	STATUS      current
	DESCRIPTION
	"Table entry attribute for plsdConnlogDumptime"
	::={plsdConnlogDumptimeLevelEntry 2}


plsdLastdump	OBJECT IDENTIFIER ::={plsd 27}

plsdLastdumpVal	OBJECT-TYPE
	SYNTAX	 DateAndTime
	MAX-ACCESS read-only
	STATUS current
	DESCRIPTION "Time of last dump"

	::={plsdLastdump 1}

plsdLastdumpLevelTable OBJECT-TYPE
	SYNTAX      SEQUENCE OF PlsdLastdumpLevelEntry
	MAX-ACCESS  not-accessible
	STATUS      current
	DESCRIPTION
	"Table for plsdLastdump"
	::={plsdLastdump 2}

plsdLastdumpLevelEntry OBJECT-TYPE
	SYNTAX      PlsdLastdumpLevelEntry
	MAX-ACCESS  not-accessible
	STATUS      current
	DESCRIPTION
	"Table entry for plsdLastdump"
	INDEX { plsdLastdumpLevelName }
	::={plsdLastdumpLevelTable 1}

PlsdLastdumpLevelEntry ::=
	SEQUENCE {
		plsdLastdumpLevelName	DisplayString,
		plsdLastdumpLevelVal	DateAndTime
	}

plsdLastdumpLevelName OBJECT-TYPE
	SYNTAX      DisplayString
	MAX-ACCESS  not-accessible
	STATUS      current
	DESCRIPTION
	"Table entry display string for plsdLastdump"
	::={plsdLastdumpLevelEntry 1}

plsdLastdumpLevelVal OBJECT-TYPE
	SYNTAX	 DateAndTime
	MAX-ACCESS  read-only
	STATUS      current
	DESCRIPTION
	"Table entry attribute for plsdLastdump"
	::={plsdLastdumpLevelEntry 2}


plsdRingbufUsage	OBJECT IDENTIFIER ::={plsd 28}

plsdRingbufUsageVal	OBJECT-TYPE
	SYNTAX	 CounterBasedGauge64
	MAX-ACCESS read-only
	STATUS current
	DESCRIPTION "Recv Ringbuf usage (Collector)"

	::={plsdRingbufUsage 1}

plsdRingbufUsageMax	OBJECT-TYPE
	SYNTAX	 CounterBasedGauge64
	MAX-ACCESS read-only
	STATUS current
	DESCRIPTION "Recv Ringbuf usage (Collector)"

	::={plsdRingbufUsage 3}

plsdRingbufUsageLevelTable OBJECT-TYPE
	SYNTAX      SEQUENCE OF PlsdRingbufUsageLevelEntry
	MAX-ACCESS  not-accessible
	STATUS      current
	DESCRIPTION
	"Table for plsdRingbufUsage"
	::={plsdRingbufUsage 4}

plsdRingbufUsageLevelEntry OBJECT-TYPE
	SYNTAX      PlsdRingbufUsageLevelEntry
	MAX-ACCESS  not-accessible
	STATUS      current
	DESCRIPTION
	"Table entry for plsdRingbufUsage"
	INDEX { plsdRingbufUsageLevelName }
	::={plsdRingbufUsageLevelTable 1}

PlsdRingbufUsageLevelEntry ::=
	SEQUENCE {
		plsdRingbufUsageLevelName	DisplayString,
		plsdRingbufUsageLevelVal	CounterBasedGauge64,
		plsdRingbufUsageLevelMax	CounterBasedGauge64
	}

plsdRingbufUsageLevelName OBJECT-TYPE
	SYNTAX      DisplayString
	MAX-ACCESS  not-accessible
	STATUS      current
	DESCRIPTION
	"Table entry display string for plsdRingbufUsage"
	::={plsdRingbufUsageLevelEntry 1}

plsdRingbufUsageLevelVal OBJECT-TYPE
	SYNTAX	 CounterBasedGauge64
	MAX-ACCESS  read-only
	STATUS      current
	DESCRIPTION
	"Table entry attribute for plsdRingbufUsage"
	::={plsdRingbufUsageLevelEntry 2}

plsdRingbufUsageLevelMax OBJECT-TYPE
	SYNTAX	 CounterBasedGauge64
	MAX-ACCESS  read-only
	STATUS      current
	DESCRIPTION
	"Table entry attribute for plsdRingbufUsage"
	::={plsdRingbufUsageLevelEntry 4}


plsdConnlogDrops	OBJECT IDENTIFIER ::={plsd 30}

plsdConnlogDropsVal	OBJECT-TYPE
	SYNTAX	 CounterBasedGauge64
	MAX-ACCESS read-only
	STATUS current
	DESCRIPTION "Connlog entries dropped"

	::={plsdConnlogDrops 1}

plsdConnlogDropsMax	OBJECT-TYPE
	SYNTAX	 CounterBasedGauge64
	MAX-ACCESS read-only
	STATUS current
	DESCRIPTION "Connlog entries dropped"

	::={plsdConnlogDrops 3}

plsdConnlogDropsLevelTable OBJECT-TYPE
	SYNTAX      SEQUENCE OF PlsdConnlogDropsLevelEntry
	MAX-ACCESS  not-accessible
	STATUS      current
	DESCRIPTION
	"Table for plsdConnlogDrops"
	::={plsdConnlogDrops 4}

plsdConnlogDropsLevelEntry OBJECT-TYPE
	SYNTAX      PlsdConnlogDropsLevelEntry
	MAX-ACCESS  not-accessible
	STATUS      current
	DESCRIPTION
	"Table entry for plsdConnlogDrops"
	INDEX { plsdConnlogDropsLevelName }
	::={plsdConnlogDropsLevelTable 1}

PlsdConnlogDropsLevelEntry ::=
	SEQUENCE {
		plsdConnlogDropsLevelName	DisplayString,
		plsdConnlogDropsLevelVal	CounterBasedGauge64,
		plsdConnlogDropsLevelMax	CounterBasedGauge64
	}

plsdConnlogDropsLevelName OBJECT-TYPE
	SYNTAX      DisplayString
	MAX-ACCESS  not-accessible
	STATUS      current
	DESCRIPTION
	"Table entry display string for plsdConnlogDrops"
	::={plsdConnlogDropsLevelEntry 1}

plsdConnlogDropsLevelVal OBJECT-TYPE
	SYNTAX	 CounterBasedGauge64
	MAX-ACCESS  read-only
	STATUS      current
	DESCRIPTION
	"Table entry attribute for plsdConnlogDrops"
	::={plsdConnlogDropsLevelEntry 2}

plsdConnlogDropsLevelMax OBJECT-TYPE
	SYNTAX	 CounterBasedGauge64
	MAX-ACCESS  read-only
	STATUS      current
	DESCRIPTION
	"Table entry attribute for plsdConnlogDrops"
	::={plsdConnlogDropsLevelEntry 4}


plsdBwUsed	OBJECT IDENTIFIER ::={plsd 31}

plsdBwUsedVal	OBJECT-TYPE
	SYNTAX	 Counter64
	MAX-ACCESS read-only
	STATUS current
	DESCRIPTION "Bandwidth used (Packetlogicd Communication)"

	::={plsdBwUsed 1}

plsdBwUsedMom	OBJECT-TYPE
	SYNTAX	 CounterBasedGauge64
	MAX-ACCESS read-only
	STATUS current
	DESCRIPTION "Bandwidth used (Packetlogicd Communication)"

	::={plsdBwUsed 2}

plsdBwUsedMax	OBJECT-TYPE
	SYNTAX	 CounterBasedGauge64
	MAX-ACCESS read-only
	STATUS current
	DESCRIPTION "Bandwidth used (Packetlogicd Communication)"

	::={plsdBwUsed 3}

plsdBwUsedLevelTable OBJECT-TYPE
	SYNTAX      SEQUENCE OF PlsdBwUsedLevelEntry
	MAX-ACCESS  not-accessible
	STATUS      current
	DESCRIPTION
	"Table for plsdBwUsed"
	::={plsdBwUsed 4}

plsdBwUsedLevelEntry OBJECT-TYPE
	SYNTAX      PlsdBwUsedLevelEntry
	MAX-ACCESS  not-accessible
	STATUS      current
	DESCRIPTION
	"Table entry for plsdBwUsed"
	INDEX { plsdBwUsedLevelName }
	::={plsdBwUsedLevelTable 1}

PlsdBwUsedLevelEntry ::=
	SEQUENCE {
		plsdBwUsedLevelName	DisplayString,
		plsdBwUsedLevelVal	Counter64,
		plsdBwUsedLevelMom	CounterBasedGauge64,
		plsdBwUsedLevelMax	CounterBasedGauge64
	}

plsdBwUsedLevelName OBJECT-TYPE
	SYNTAX      DisplayString
	MAX-ACCESS  not-accessible
	STATUS      current
	DESCRIPTION
	"Table entry display string for plsdBwUsed"
	::={plsdBwUsedLevelEntry 1}

plsdBwUsedLevelVal OBJECT-TYPE
	SYNTAX	 Counter64
	MAX-ACCESS  read-only
	STATUS      current
	DESCRIPTION
	"Table entry attribute for plsdBwUsed"
	::={plsdBwUsedLevelEntry 2}

plsdBwUsedLevelMom OBJECT-TYPE
	SYNTAX	 CounterBasedGauge64
	MAX-ACCESS  read-only
	STATUS      current
	DESCRIPTION
	"Table entry attribute for plsdBwUsed"
	::={plsdBwUsedLevelEntry 3}

plsdBwUsedLevelMax OBJECT-TYPE
	SYNTAX	 CounterBasedGauge64
	MAX-ACCESS  read-only
	STATUS      current
	DESCRIPTION
	"Table entry attribute for plsdBwUsed"
	::={plsdBwUsedLevelEntry 4}


plsdTimeConnected	OBJECT IDENTIFIER ::={plsd 32}

plsdTimeConnectedVal	OBJECT-TYPE
	SYNTAX	 TimeTicks
	MAX-ACCESS read-only
	STATUS current
	DESCRIPTION "Time connected"

	::={plsdTimeConnected 1}

plsdTimeConnectedLevelTable OBJECT-TYPE
	SYNTAX      SEQUENCE OF PlsdTimeConnectedLevelEntry
	MAX-ACCESS  not-accessible
	STATUS      current
	DESCRIPTION
	"Table for plsdTimeConnected"
	::={plsdTimeConnected 2}

plsdTimeConnectedLevelEntry OBJECT-TYPE
	SYNTAX      PlsdTimeConnectedLevelEntry
	MAX-ACCESS  not-accessible
	STATUS      current
	DESCRIPTION
	"Table entry for plsdTimeConnected"
	INDEX { plsdTimeConnectedLevelName }
	::={plsdTimeConnectedLevelTable 1}

PlsdTimeConnectedLevelEntry ::=
	SEQUENCE {
		plsdTimeConnectedLevelName	DisplayString,
		plsdTimeConnectedLevelVal	TimeTicks
	}

plsdTimeConnectedLevelName OBJECT-TYPE
	SYNTAX      DisplayString
	MAX-ACCESS  not-accessible
	STATUS      current
	DESCRIPTION
	"Table entry display string for plsdTimeConnected"
	::={plsdTimeConnectedLevelEntry 1}

plsdTimeConnectedLevelVal OBJECT-TYPE
	SYNTAX	 TimeTicks
	MAX-ACCESS  read-only
	STATUS      current
	DESCRIPTION
	"Table entry attribute for plsdTimeConnected"
	::={plsdTimeConnectedLevelEntry 2}


plsdConnects	OBJECT IDENTIFIER ::={plsd 33}

plsdConnectsVal	OBJECT-TYPE
	SYNTAX	 CounterBasedGauge64
	MAX-ACCESS read-only
	STATUS current
	DESCRIPTION "Connects"

	::={plsdConnects 1}

plsdConnectsMax	OBJECT-TYPE
	SYNTAX	 CounterBasedGauge64
	MAX-ACCESS read-only
	STATUS current
	DESCRIPTION "Connects"

	::={plsdConnects 3}

plsdConnectsLevelTable OBJECT-TYPE
	SYNTAX      SEQUENCE OF PlsdConnectsLevelEntry
	MAX-ACCESS  not-accessible
	STATUS      current
	DESCRIPTION
	"Table for plsdConnects"
	::={plsdConnects 4}

plsdConnectsLevelEntry OBJECT-TYPE
	SYNTAX      PlsdConnectsLevelEntry
	MAX-ACCESS  not-accessible
	STATUS      current
	DESCRIPTION
	"Table entry for plsdConnects"
	INDEX { plsdConnectsLevelName }
	::={plsdConnectsLevelTable 1}

PlsdConnectsLevelEntry ::=
	SEQUENCE {
		plsdConnectsLevelName	DisplayString,
		plsdConnectsLevelVal	CounterBasedGauge64,
		plsdConnectsLevelMax	CounterBasedGauge64
	}

plsdConnectsLevelName OBJECT-TYPE
	SYNTAX      DisplayString
	MAX-ACCESS  not-accessible
	STATUS      current
	DESCRIPTION
	"Table entry display string for plsdConnects"
	::={plsdConnectsLevelEntry 1}

plsdConnectsLevelVal OBJECT-TYPE
	SYNTAX	 CounterBasedGauge64
	MAX-ACCESS  read-only
	STATUS      current
	DESCRIPTION
	"Table entry attribute for plsdConnects"
	::={plsdConnectsLevelEntry 2}

plsdConnectsLevelMax OBJECT-TYPE
	SYNTAX	 CounterBasedGauge64
	MAX-ACCESS  read-only
	STATUS      current
	DESCRIPTION
	"Table entry attribute for plsdConnects"
	::={plsdConnectsLevelEntry 4}


plsdVmsize	OBJECT IDENTIFIER ::={plsd 34}

plsdVmsizeVal	OBJECT-TYPE
	SYNTAX	 CounterBasedGauge64
	MAX-ACCESS read-only
	STATUS current
	DESCRIPTION "Memory usage (Virtual)"

	::={plsdVmsize 1}

plsdVmsizeMax	OBJECT-TYPE
	SYNTAX	 CounterBasedGauge64
	MAX-ACCESS read-only
	STATUS current
	DESCRIPTION "Memory usage (Virtual)"

	::={plsdVmsize 3}

plsdVmsizeLevelTable OBJECT-TYPE
	SYNTAX      SEQUENCE OF PlsdVmsizeLevelEntry
	MAX-ACCESS  not-accessible
	STATUS      current
	DESCRIPTION
	"Table for plsdVmsize"
	::={plsdVmsize 4}

plsdVmsizeLevelEntry OBJECT-TYPE
	SYNTAX      PlsdVmsizeLevelEntry
	MAX-ACCESS  not-accessible
	STATUS      current
	DESCRIPTION
	"Table entry for plsdVmsize"
	INDEX { plsdVmsizeLevelName }
	::={plsdVmsizeLevelTable 1}

PlsdVmsizeLevelEntry ::=
	SEQUENCE {
		plsdVmsizeLevelName	DisplayString,
		plsdVmsizeLevelVal	CounterBasedGauge64,
		plsdVmsizeLevelMax	CounterBasedGauge64
	}

plsdVmsizeLevelName OBJECT-TYPE
	SYNTAX      DisplayString
	MAX-ACCESS  not-accessible
	STATUS      current
	DESCRIPTION
	"Table entry display string for plsdVmsize"
	::={plsdVmsizeLevelEntry 1}

plsdVmsizeLevelVal OBJECT-TYPE
	SYNTAX	 CounterBasedGauge64
	MAX-ACCESS  read-only
	STATUS      current
	DESCRIPTION
	"Table entry attribute for plsdVmsize"
	::={plsdVmsizeLevelEntry 2}

plsdVmsizeLevelMax OBJECT-TYPE
	SYNTAX	 CounterBasedGauge64
	MAX-ACCESS  read-only
	STATUS      current
	DESCRIPTION
	"Table entry attribute for plsdVmsize"
	::={plsdVmsizeLevelEntry 4}


plsdVmrss	OBJECT IDENTIFIER ::={plsd 35}

plsdVmrssVal	OBJECT-TYPE
	SYNTAX	 CounterBasedGauge64
	MAX-ACCESS read-only
	STATUS current
	DESCRIPTION "Memory usage (RAM)"

	::={plsdVmrss 1}

plsdVmrssMax	OBJECT-TYPE
	SYNTAX	 CounterBasedGauge64
	MAX-ACCESS read-only
	STATUS current
	DESCRIPTION "Memory usage (RAM)"

	::={plsdVmrss 3}

plsdVmrssLevelTable OBJECT-TYPE
	SYNTAX      SEQUENCE OF PlsdVmrssLevelEntry
	MAX-ACCESS  not-accessible
	STATUS      current
	DESCRIPTION
	"Table for plsdVmrss"
	::={plsdVmrss 4}

plsdVmrssLevelEntry OBJECT-TYPE
	SYNTAX      PlsdVmrssLevelEntry
	MAX-ACCESS  not-accessible
	STATUS      current
	DESCRIPTION
	"Table entry for plsdVmrss"
	INDEX { plsdVmrssLevelName }
	::={plsdVmrssLevelTable 1}

PlsdVmrssLevelEntry ::=
	SEQUENCE {
		plsdVmrssLevelName	DisplayString,
		plsdVmrssLevelVal	CounterBasedGauge64,
		plsdVmrssLevelMax	CounterBasedGauge64
	}

plsdVmrssLevelName OBJECT-TYPE
	SYNTAX      DisplayString
	MAX-ACCESS  not-accessible
	STATUS      current
	DESCRIPTION
	"Table entry display string for plsdVmrss"
	::={plsdVmrssLevelEntry 1}

plsdVmrssLevelVal OBJECT-TYPE
	SYNTAX	 CounterBasedGauge64
	MAX-ACCESS  read-only
	STATUS      current
	DESCRIPTION
	"Table entry attribute for plsdVmrss"
	::={plsdVmrssLevelEntry 2}

plsdVmrssLevelMax OBJECT-TYPE
	SYNTAX	 CounterBasedGauge64
	MAX-ACCESS  read-only
	STATUS      current
	DESCRIPTION
	"Table entry attribute for plsdVmrss"
	::={plsdVmrssLevelEntry 4}


plsdConnlogIncomplete	OBJECT IDENTIFIER ::={plsd 36}

plsdConnlogIncompleteVal	OBJECT-TYPE
	SYNTAX	 CounterBasedGauge64
	MAX-ACCESS read-only
	STATUS current
	DESCRIPTION "Connlog entries incomplete"

	::={plsdConnlogIncomplete 1}

plsdConnlogIncompleteMax	OBJECT-TYPE
	SYNTAX	 CounterBasedGauge64
	MAX-ACCESS read-only
	STATUS current
	DESCRIPTION "Connlog entries incomplete"

	::={plsdConnlogIncomplete 3}

plsdConnlogIncompleteLevelTable OBJECT-TYPE
	SYNTAX      SEQUENCE OF PlsdConnlogIncompleteLevelEntry
	MAX-ACCESS  not-accessible
	STATUS      current
	DESCRIPTION
	"Table for plsdConnlogIncomplete"
	::={plsdConnlogIncomplete 4}

plsdConnlogIncompleteLevelEntry OBJECT-TYPE
	SYNTAX      PlsdConnlogIncompleteLevelEntry
	MAX-ACCESS  not-accessible
	STATUS      current
	DESCRIPTION
	"Table entry for plsdConnlogIncomplete"
	INDEX { plsdConnlogIncompleteLevelName }
	::={plsdConnlogIncompleteLevelTable 1}

PlsdConnlogIncompleteLevelEntry ::=
	SEQUENCE {
		plsdConnlogIncompleteLevelName	DisplayString,
		plsdConnlogIncompleteLevelVal	CounterBasedGauge64,
		plsdConnlogIncompleteLevelMax	CounterBasedGauge64
	}

plsdConnlogIncompleteLevelName OBJECT-TYPE
	SYNTAX      DisplayString
	MAX-ACCESS  not-accessible
	STATUS      current
	DESCRIPTION
	"Table entry display string for plsdConnlogIncomplete"
	::={plsdConnlogIncompleteLevelEntry 1}

plsdConnlogIncompleteLevelVal OBJECT-TYPE
	SYNTAX	 CounterBasedGauge64
	MAX-ACCESS  read-only
	STATUS      current
	DESCRIPTION
	"Table entry attribute for plsdConnlogIncomplete"
	::={plsdConnlogIncompleteLevelEntry 2}

plsdConnlogIncompleteLevelMax OBJECT-TYPE
	SYNTAX	 CounterBasedGauge64
	MAX-ACCESS  read-only
	STATUS      current
	DESCRIPTION
	"Table entry attribute for plsdConnlogIncomplete"
	::={plsdConnlogIncompleteLevelEntry 4}


plsdConnProp	OBJECT IDENTIFIER ::={plsd 37}

plsdConnPropVal	OBJECT-TYPE
	SYNTAX	 CounterBasedGauge64
	MAX-ACCESS read-only
	STATUS current
	DESCRIPTION "Connection Properties count"

	::={plsdConnProp 1}

plsdConnPropMax	OBJECT-TYPE
	SYNTAX	 CounterBasedGauge64
	MAX-ACCESS read-only
	STATUS current
	DESCRIPTION "Connection Properties count"

	::={plsdConnProp 3}

plsdConnPropLevelTable OBJECT-TYPE
	SYNTAX      SEQUENCE OF PlsdConnPropLevelEntry
	MAX-ACCESS  not-accessible
	STATUS      current
	DESCRIPTION
	"Table for plsdConnProp"
	::={plsdConnProp 4}

plsdConnPropLevelEntry OBJECT-TYPE
	SYNTAX      PlsdConnPropLevelEntry
	MAX-ACCESS  not-accessible
	STATUS      current
	DESCRIPTION
	"Table entry for plsdConnProp"
	INDEX { plsdConnPropLevelName }
	::={plsdConnPropLevelTable 1}

PlsdConnPropLevelEntry ::=
	SEQUENCE {
		plsdConnPropLevelName	DisplayString,
		plsdConnPropLevelVal	CounterBasedGauge64,
		plsdConnPropLevelMax	CounterBasedGauge64
	}

plsdConnPropLevelName OBJECT-TYPE
	SYNTAX      DisplayString
	MAX-ACCESS  not-accessible
	STATUS      current
	DESCRIPTION
	"Table entry display string for plsdConnProp"
	::={plsdConnPropLevelEntry 1}

plsdConnPropLevelVal OBJECT-TYPE
	SYNTAX	 CounterBasedGauge64
	MAX-ACCESS  read-only
	STATUS      current
	DESCRIPTION
	"Table entry attribute for plsdConnProp"
	::={plsdConnPropLevelEntry 2}

plsdConnPropLevelMax OBJECT-TYPE
	SYNTAX	 CounterBasedGauge64
	MAX-ACCESS  read-only
	STATUS      current
	DESCRIPTION
	"Table entry attribute for plsdConnProp"
	::={plsdConnPropLevelEntry 4}


plsdConnPropHash	OBJECT IDENTIFIER ::={plsd 38}

plsdConnPropHashVal	OBJECT-TYPE
	SYNTAX	 CounterBasedGauge64
	MAX-ACCESS read-only
	STATUS obsolete
	DESCRIPTION "Connection Properties Hashtables"

	::={plsdConnPropHash 1}

plsdConnPropHashMax	OBJECT-TYPE
	SYNTAX	 CounterBasedGauge64
	MAX-ACCESS read-only
	STATUS obsolete
	DESCRIPTION "Connection Properties Hashtables"

	::={plsdConnPropHash 3}

plsdConnPropHashLevelTable OBJECT-TYPE
	SYNTAX      SEQUENCE OF PlsdConnPropHashLevelEntry
	MAX-ACCESS  not-accessible
	STATUS      current
	DESCRIPTION
	"Table for plsdConnPropHash"
	::={plsdConnPropHash 4}

plsdConnPropHashLevelEntry OBJECT-TYPE
	SYNTAX      PlsdConnPropHashLevelEntry
	MAX-ACCESS  not-accessible
	STATUS      current
	DESCRIPTION
	"Table entry for plsdConnPropHash"
	INDEX { plsdConnPropHashLevelName }
	::={plsdConnPropHashLevelTable 1}

PlsdConnPropHashLevelEntry ::=
	SEQUENCE {
		plsdConnPropHashLevelName	DisplayString,
		plsdConnPropHashLevelVal	CounterBasedGauge64,
		plsdConnPropHashLevelMax	CounterBasedGauge64
	}

plsdConnPropHashLevelName OBJECT-TYPE
	SYNTAX      DisplayString
	MAX-ACCESS  not-accessible
	STATUS      current
	DESCRIPTION
	"Table entry display string for plsdConnPropHash"
	::={plsdConnPropHashLevelEntry 1}

plsdConnPropHashLevelVal OBJECT-TYPE
	SYNTAX	 CounterBasedGauge64
	MAX-ACCESS  read-only
	STATUS      current
	DESCRIPTION
	"Table entry attribute for plsdConnPropHash"
	::={plsdConnPropHashLevelEntry 2}

plsdConnPropHashLevelMax OBJECT-TYPE
	SYNTAX	 CounterBasedGauge64
	MAX-ACCESS  read-only
	STATUS      current
	DESCRIPTION
	"Table entry attribute for plsdConnPropHash"
	::={plsdConnPropHashLevelEntry 4}


plsdBytesAccountedIn	OBJECT IDENTIFIER ::={plsd 39}

plsdBytesAccountedInVal	OBJECT-TYPE
	SYNTAX	 Counter64
	MAX-ACCESS read-only
	STATUS current
	DESCRIPTION "Connection Bytes Accounted In"

	::={plsdBytesAccountedIn 1}

plsdBytesAccountedInMom	OBJECT-TYPE
	SYNTAX	 CounterBasedGauge64
	MAX-ACCESS read-only
	STATUS current
	DESCRIPTION "Connection Bytes Accounted In"

	::={plsdBytesAccountedIn 2}

plsdBytesAccountedInMax	OBJECT-TYPE
	SYNTAX	 CounterBasedGauge64
	MAX-ACCESS read-only
	STATUS current
	DESCRIPTION "Connection Bytes Accounted In"

	::={plsdBytesAccountedIn 3}

plsdBytesAccountedInLevelTable OBJECT-TYPE
	SYNTAX      SEQUENCE OF PlsdBytesAccountedInLevelEntry
	MAX-ACCESS  not-accessible
	STATUS      current
	DESCRIPTION
	"Table for plsdBytesAccountedIn"
	::={plsdBytesAccountedIn 4}

plsdBytesAccountedInLevelEntry OBJECT-TYPE
	SYNTAX      PlsdBytesAccountedInLevelEntry
	MAX-ACCESS  not-accessible
	STATUS      current
	DESCRIPTION
	"Table entry for plsdBytesAccountedIn"
	INDEX { plsdBytesAccountedInLevelName }
	::={plsdBytesAccountedInLevelTable 1}

PlsdBytesAccountedInLevelEntry ::=
	SEQUENCE {
		plsdBytesAccountedInLevelName	DisplayString,
		plsdBytesAccountedInLevelVal	Counter64,
		plsdBytesAccountedInLevelMom	CounterBasedGauge64,
		plsdBytesAccountedInLevelMax	CounterBasedGauge64
	}

plsdBytesAccountedInLevelName OBJECT-TYPE
	SYNTAX      DisplayString
	MAX-ACCESS  not-accessible
	STATUS      current
	DESCRIPTION
	"Table entry display string for plsdBytesAccountedIn"
	::={plsdBytesAccountedInLevelEntry 1}

plsdBytesAccountedInLevelVal OBJECT-TYPE
	SYNTAX	 Counter64
	MAX-ACCESS  read-only
	STATUS      current
	DESCRIPTION
	"Table entry attribute for plsdBytesAccountedIn"
	::={plsdBytesAccountedInLevelEntry 2}

plsdBytesAccountedInLevelMom OBJECT-TYPE
	SYNTAX	 CounterBasedGauge64
	MAX-ACCESS  read-only
	STATUS      current
	DESCRIPTION
	"Table entry attribute for plsdBytesAccountedIn"
	::={plsdBytesAccountedInLevelEntry 3}

plsdBytesAccountedInLevelMax OBJECT-TYPE
	SYNTAX	 CounterBasedGauge64
	MAX-ACCESS  read-only
	STATUS      current
	DESCRIPTION
	"Table entry attribute for plsdBytesAccountedIn"
	::={plsdBytesAccountedInLevelEntry 4}


plsdBytesAccountedOut	OBJECT IDENTIFIER ::={plsd 40}

plsdBytesAccountedOutVal	OBJECT-TYPE
	SYNTAX	 Counter64
	MAX-ACCESS read-only
	STATUS current
	DESCRIPTION "Connection Bytes Accounted Out"

	::={plsdBytesAccountedOut 1}

plsdBytesAccountedOutMom	OBJECT-TYPE
	SYNTAX	 CounterBasedGauge64
	MAX-ACCESS read-only
	STATUS current
	DESCRIPTION "Connection Bytes Accounted Out"

	::={plsdBytesAccountedOut 2}

plsdBytesAccountedOutMax	OBJECT-TYPE
	SYNTAX	 CounterBasedGauge64
	MAX-ACCESS read-only
	STATUS current
	DESCRIPTION "Connection Bytes Accounted Out"

	::={plsdBytesAccountedOut 3}

plsdBytesAccountedOutLevelTable OBJECT-TYPE
	SYNTAX      SEQUENCE OF PlsdBytesAccountedOutLevelEntry
	MAX-ACCESS  not-accessible
	STATUS      current
	DESCRIPTION
	"Table for plsdBytesAccountedOut"
	::={plsdBytesAccountedOut 4}

plsdBytesAccountedOutLevelEntry OBJECT-TYPE
	SYNTAX      PlsdBytesAccountedOutLevelEntry
	MAX-ACCESS  not-accessible
	STATUS      current
	DESCRIPTION
	"Table entry for plsdBytesAccountedOut"
	INDEX { plsdBytesAccountedOutLevelName }
	::={plsdBytesAccountedOutLevelTable 1}

PlsdBytesAccountedOutLevelEntry ::=
	SEQUENCE {
		plsdBytesAccountedOutLevelName	DisplayString,
		plsdBytesAccountedOutLevelVal	Counter64,
		plsdBytesAccountedOutLevelMom	CounterBasedGauge64,
		plsdBytesAccountedOutLevelMax	CounterBasedGauge64
	}

plsdBytesAccountedOutLevelName OBJECT-TYPE
	SYNTAX      DisplayString
	MAX-ACCESS  not-accessible
	STATUS      current
	DESCRIPTION
	"Table entry display string for plsdBytesAccountedOut"
	::={plsdBytesAccountedOutLevelEntry 1}

plsdBytesAccountedOutLevelVal OBJECT-TYPE
	SYNTAX	 Counter64
	MAX-ACCESS  read-only
	STATUS      current
	DESCRIPTION
	"Table entry attribute for plsdBytesAccountedOut"
	::={plsdBytesAccountedOutLevelEntry 2}

plsdBytesAccountedOutLevelMom OBJECT-TYPE
	SYNTAX	 CounterBasedGauge64
	MAX-ACCESS  read-only
	STATUS      current
	DESCRIPTION
	"Table entry attribute for plsdBytesAccountedOut"
	::={plsdBytesAccountedOutLevelEntry 3}

plsdBytesAccountedOutLevelMax OBJECT-TYPE
	SYNTAX	 CounterBasedGauge64
	MAX-ACCESS  read-only
	STATUS      current
	DESCRIPTION
	"Table entry attribute for plsdBytesAccountedOut"
	::={plsdBytesAccountedOutLevelEntry 4}


plsdBytesUnAccountedIn	OBJECT IDENTIFIER ::={plsd 41}

plsdBytesUnAccountedInVal	OBJECT-TYPE
	SYNTAX	 Counter64
	MAX-ACCESS read-only
	STATUS current
	DESCRIPTION "Connection Bytes Unaccounted In"

	::={plsdBytesUnAccountedIn 1}

plsdBytesUnAccountedInMom	OBJECT-TYPE
	SYNTAX	 CounterBasedGauge64
	MAX-ACCESS read-only
	STATUS current
	DESCRIPTION "Connection Bytes Unaccounted In"

	::={plsdBytesUnAccountedIn 2}

plsdBytesUnAccountedInMax	OBJECT-TYPE
	SYNTAX	 CounterBasedGauge64
	MAX-ACCESS read-only
	STATUS current
	DESCRIPTION "Connection Bytes Unaccounted In"

	::={plsdBytesUnAccountedIn 3}

plsdBytesUnAccountedInLevelTable OBJECT-TYPE
	SYNTAX      SEQUENCE OF PlsdBytesUnAccountedInLevelEntry
	MAX-ACCESS  not-accessible
	STATUS      current
	DESCRIPTION
	"Table for plsdBytesUnAccountedIn"
	::={plsdBytesUnAccountedIn 4}

plsdBytesUnAccountedInLevelEntry OBJECT-TYPE
	SYNTAX      PlsdBytesUnAccountedInLevelEntry
	MAX-ACCESS  not-accessible
	STATUS      current
	DESCRIPTION
	"Table entry for plsdBytesUnAccountedIn"
	INDEX { plsdBytesUnAccountedInLevelName }
	::={plsdBytesUnAccountedInLevelTable 1}

PlsdBytesUnAccountedInLevelEntry ::=
	SEQUENCE {
		plsdBytesUnAccountedInLevelName	DisplayString,
		plsdBytesUnAccountedInLevelVal	Counter64,
		plsdBytesUnAccountedInLevelMom	CounterBasedGauge64,
		plsdBytesUnAccountedInLevelMax	CounterBasedGauge64
	}

plsdBytesUnAccountedInLevelName OBJECT-TYPE
	SYNTAX      DisplayString
	MAX-ACCESS  not-accessible
	STATUS      current
	DESCRIPTION
	"Table entry display string for plsdBytesUnAccountedIn"
	::={plsdBytesUnAccountedInLevelEntry 1}

plsdBytesUnAccountedInLevelVal OBJECT-TYPE
	SYNTAX	 Counter64
	MAX-ACCESS  read-only
	STATUS      current
	DESCRIPTION
	"Table entry attribute for plsdBytesUnAccountedIn"
	::={plsdBytesUnAccountedInLevelEntry 2}

plsdBytesUnAccountedInLevelMom OBJECT-TYPE
	SYNTAX	 CounterBasedGauge64
	MAX-ACCESS  read-only
	STATUS      current
	DESCRIPTION
	"Table entry attribute for plsdBytesUnAccountedIn"
	::={plsdBytesUnAccountedInLevelEntry 3}

plsdBytesUnAccountedInLevelMax OBJECT-TYPE
	SYNTAX	 CounterBasedGauge64
	MAX-ACCESS  read-only
	STATUS      current
	DESCRIPTION
	"Table entry attribute for plsdBytesUnAccountedIn"
	::={plsdBytesUnAccountedInLevelEntry 4}


plsdBytesUnAccountedOut	OBJECT IDENTIFIER ::={plsd 42}

plsdBytesUnAccountedOutVal	OBJECT-TYPE
	SYNTAX	 Counter64
	MAX-ACCESS read-only
	STATUS current
	DESCRIPTION "Connection Bytes Unaccounted Out"

	::={plsdBytesUnAccountedOut 1}

plsdBytesUnAccountedOutMom	OBJECT-TYPE
	SYNTAX	 CounterBasedGauge64
	MAX-ACCESS read-only
	STATUS current
	DESCRIPTION "Connection Bytes Unaccounted Out"

	::={plsdBytesUnAccountedOut 2}

plsdBytesUnAccountedOutMax	OBJECT-TYPE
	SYNTAX	 CounterBasedGauge64
	MAX-ACCESS read-only
	STATUS current
	DESCRIPTION "Connection Bytes Unaccounted Out"

	::={plsdBytesUnAccountedOut 3}

plsdBytesUnAccountedOutLevelTable OBJECT-TYPE
	SYNTAX      SEQUENCE OF PlsdBytesUnAccountedOutLevelEntry
	MAX-ACCESS  not-accessible
	STATUS      current
	DESCRIPTION
	"Table for plsdBytesUnAccountedOut"
	::={plsdBytesUnAccountedOut 4}

plsdBytesUnAccountedOutLevelEntry OBJECT-TYPE
	SYNTAX      PlsdBytesUnAccountedOutLevelEntry
	MAX-ACCESS  not-accessible
	STATUS      current
	DESCRIPTION
	"Table entry for plsdBytesUnAccountedOut"
	INDEX { plsdBytesUnAccountedOutLevelName }
	::={plsdBytesUnAccountedOutLevelTable 1}

PlsdBytesUnAccountedOutLevelEntry ::=
	SEQUENCE {
		plsdBytesUnAccountedOutLevelName	DisplayString,
		plsdBytesUnAccountedOutLevelVal	Counter64,
		plsdBytesUnAccountedOutLevelMom	CounterBasedGauge64,
		plsdBytesUnAccountedOutLevelMax	CounterBasedGauge64
	}

plsdBytesUnAccountedOutLevelName OBJECT-TYPE
	SYNTAX      DisplayString
	MAX-ACCESS  not-accessible
	STATUS      current
	DESCRIPTION
	"Table entry display string for plsdBytesUnAccountedOut"
	::={plsdBytesUnAccountedOutLevelEntry 1}

plsdBytesUnAccountedOutLevelVal OBJECT-TYPE
	SYNTAX	 Counter64
	MAX-ACCESS  read-only
	STATUS      current
	DESCRIPTION
	"Table entry attribute for plsdBytesUnAccountedOut"
	::={plsdBytesUnAccountedOutLevelEntry 2}

plsdBytesUnAccountedOutLevelMom OBJECT-TYPE
	SYNTAX	 CounterBasedGauge64
	MAX-ACCESS  read-only
	STATUS      current
	DESCRIPTION
	"Table entry attribute for plsdBytesUnAccountedOut"
	::={plsdBytesUnAccountedOutLevelEntry 3}

plsdBytesUnAccountedOutLevelMax OBJECT-TYPE
	SYNTAX	 CounterBasedGauge64
	MAX-ACCESS  read-only
	STATUS      current
	DESCRIPTION
	"Table entry attribute for plsdBytesUnAccountedOut"
	::={plsdBytesUnAccountedOutLevelEntry 4}


plsdCorruptPath	OBJECT IDENTIFIER ::={plsd 43}

plsdCorruptPathVal	OBJECT-TYPE
	SYNTAX	 Counter64
	MAX-ACCESS read-only
	STATUS current
	DESCRIPTION "Corrupted value paths"

	::={plsdCorruptPath 1}

plsdCorruptPathMom	OBJECT-TYPE
	SYNTAX	 CounterBasedGauge64
	MAX-ACCESS read-only
	STATUS current
	DESCRIPTION "Corrupted value paths"

	::={plsdCorruptPath 2}

plsdCorruptPathMax	OBJECT-TYPE
	SYNTAX	 CounterBasedGauge64
	MAX-ACCESS read-only
	STATUS current
	DESCRIPTION "Corrupted value paths"

	::={plsdCorruptPath 3}

plsdCorruptPathLevelTable OBJECT-TYPE
	SYNTAX      SEQUENCE OF PlsdCorruptPathLevelEntry
	MAX-ACCESS  not-accessible
	STATUS      current
	DESCRIPTION
	"Table for plsdCorruptPath"
	::={plsdCorruptPath 4}

plsdCorruptPathLevelEntry OBJECT-TYPE
	SYNTAX      PlsdCorruptPathLevelEntry
	MAX-ACCESS  not-accessible
	STATUS      current
	DESCRIPTION
	"Table entry for plsdCorruptPath"
	INDEX { plsdCorruptPathLevelName }
	::={plsdCorruptPathLevelTable 1}

PlsdCorruptPathLevelEntry ::=
	SEQUENCE {
		plsdCorruptPathLevelName	DisplayString,
		plsdCorruptPathLevelVal	Counter64,
		plsdCorruptPathLevelMom	CounterBasedGauge64,
		plsdCorruptPathLevelMax	CounterBasedGauge64
	}

plsdCorruptPathLevelName OBJECT-TYPE
	SYNTAX      DisplayString
	MAX-ACCESS  not-accessible
	STATUS      current
	DESCRIPTION
	"Table entry display string for plsdCorruptPath"
	::={plsdCorruptPathLevelEntry 1}

plsdCorruptPathLevelVal OBJECT-TYPE
	SYNTAX	 Counter64
	MAX-ACCESS  read-only
	STATUS      current
	DESCRIPTION
	"Table entry attribute for plsdCorruptPath"
	::={plsdCorruptPathLevelEntry 2}

plsdCorruptPathLevelMom OBJECT-TYPE
	SYNTAX	 CounterBasedGauge64
	MAX-ACCESS  read-only
	STATUS      current
	DESCRIPTION
	"Table entry attribute for plsdCorruptPath"
	::={plsdCorruptPathLevelEntry 3}

plsdCorruptPathLevelMax OBJECT-TYPE
	SYNTAX	 CounterBasedGauge64
	MAX-ACCESS  read-only
	STATUS      current
	DESCRIPTION
	"Table entry attribute for plsdCorruptPath"
	::={plsdCorruptPathLevelEntry 4}


plsdSubscribersMerged	OBJECT IDENTIFIER ::={plsd 44}

plsdSubscribersMergedVal	OBJECT-TYPE
	SYNTAX	 CounterBasedGauge64
	MAX-ACCESS read-only
	STATUS current
	DESCRIPTION "Dataset, Subscribers"

	::={plsdSubscribersMerged 1}

plsdSubscribersMergedMax	OBJECT-TYPE
	SYNTAX	 CounterBasedGauge64
	MAX-ACCESS read-only
	STATUS current
	DESCRIPTION "Dataset, Subscribers"

	::={plsdSubscribersMerged 3}

plsdSubscribersMergedLevelTable OBJECT-TYPE
	SYNTAX      SEQUENCE OF PlsdSubscribersMergedLevelEntry
	MAX-ACCESS  not-accessible
	STATUS      current
	DESCRIPTION
	"Table for plsdSubscribersMerged"
	::={plsdSubscribersMerged 4}

plsdSubscribersMergedLevelEntry OBJECT-TYPE
	SYNTAX      PlsdSubscribersMergedLevelEntry
	MAX-ACCESS  not-accessible
	STATUS      current
	DESCRIPTION
	"Table entry for plsdSubscribersMerged"
	INDEX { plsdSubscribersMergedLevelName }
	::={plsdSubscribersMergedLevelTable 1}

PlsdSubscribersMergedLevelEntry ::=
	SEQUENCE {
		plsdSubscribersMergedLevelName	DisplayString,
		plsdSubscribersMergedLevelVal	CounterBasedGauge64,
		plsdSubscribersMergedLevelMax	CounterBasedGauge64
	}

plsdSubscribersMergedLevelName OBJECT-TYPE
	SYNTAX      DisplayString
	MAX-ACCESS  not-accessible
	STATUS      current
	DESCRIPTION
	"Table entry display string for plsdSubscribersMerged"
	::={plsdSubscribersMergedLevelEntry 1}

plsdSubscribersMergedLevelVal OBJECT-TYPE
	SYNTAX	 CounterBasedGauge64
	MAX-ACCESS  read-only
	STATUS      current
	DESCRIPTION
	"Table entry attribute for plsdSubscribersMerged"
	::={plsdSubscribersMergedLevelEntry 2}

plsdSubscribersMergedLevelMax OBJECT-TYPE
	SYNTAX	 CounterBasedGauge64
	MAX-ACCESS  read-only
	STATUS      current
	DESCRIPTION
	"Table entry attribute for plsdSubscribersMerged"
	::={plsdSubscribersMergedLevelEntry 4}


plsdSubscribersSent	OBJECT IDENTIFIER ::={plsd 45}

plsdSubscribersSentVal	OBJECT-TYPE
	SYNTAX	 CounterBasedGauge64
	MAX-ACCESS read-only
	STATUS current
	DESCRIPTION "Dataset, Subscribers sent"

	::={plsdSubscribersSent 1}

plsdSubscribersSentMax	OBJECT-TYPE
	SYNTAX	 CounterBasedGauge64
	MAX-ACCESS read-only
	STATUS current
	DESCRIPTION "Dataset, Subscribers sent"

	::={plsdSubscribersSent 3}

plsdSubscribersSentLevelTable OBJECT-TYPE
	SYNTAX      SEQUENCE OF PlsdSubscribersSentLevelEntry
	MAX-ACCESS  not-accessible
	STATUS      current
	DESCRIPTION
	"Table for plsdSubscribersSent"
	::={plsdSubscribersSent 4}

plsdSubscribersSentLevelEntry OBJECT-TYPE
	SYNTAX      PlsdSubscribersSentLevelEntry
	MAX-ACCESS  not-accessible
	STATUS      current
	DESCRIPTION
	"Table entry for plsdSubscribersSent"
	INDEX { plsdSubscribersSentLevelName }
	::={plsdSubscribersSentLevelTable 1}

PlsdSubscribersSentLevelEntry ::=
	SEQUENCE {
		plsdSubscribersSentLevelName	DisplayString,
		plsdSubscribersSentLevelVal	CounterBasedGauge64,
		plsdSubscribersSentLevelMax	CounterBasedGauge64
	}

plsdSubscribersSentLevelName OBJECT-TYPE
	SYNTAX      DisplayString
	MAX-ACCESS  not-accessible
	STATUS      current
	DESCRIPTION
	"Table entry display string for plsdSubscribersSent"
	::={plsdSubscribersSentLevelEntry 1}

plsdSubscribersSentLevelVal OBJECT-TYPE
	SYNTAX	 CounterBasedGauge64
	MAX-ACCESS  read-only
	STATUS      current
	DESCRIPTION
	"Table entry attribute for plsdSubscribersSent"
	::={plsdSubscribersSentLevelEntry 2}

plsdSubscribersSentLevelMax OBJECT-TYPE
	SYNTAX	 CounterBasedGauge64
	MAX-ACCESS  read-only
	STATUS      current
	DESCRIPTION
	"Table entry attribute for plsdSubscribersSent"
	::={plsdSubscribersSentLevelEntry 4}


plsdSubscribersAgg	OBJECT IDENTIFIER ::={plsd 46}

plsdSubscribersAggVal	OBJECT-TYPE
	SYNTAX	 CounterBasedGauge64
	MAX-ACCESS read-only
	STATUS current
	DESCRIPTION "Dataset, Subscribers aggregate"

	::={plsdSubscribersAgg 1}

plsdSubscribersAggMax	OBJECT-TYPE
	SYNTAX	 CounterBasedGauge64
	MAX-ACCESS read-only
	STATUS current
	DESCRIPTION "Dataset, Subscribers aggregate"

	::={plsdSubscribersAgg 3}

plsdSubscribersAggLevelTable OBJECT-TYPE
	SYNTAX      SEQUENCE OF PlsdSubscribersAggLevelEntry
	MAX-ACCESS  not-accessible
	STATUS      current
	DESCRIPTION
	"Table for plsdSubscribersAgg"
	::={plsdSubscribersAgg 4}

plsdSubscribersAggLevelEntry OBJECT-TYPE
	SYNTAX      PlsdSubscribersAggLevelEntry
	MAX-ACCESS  not-accessible
	STATUS      current
	DESCRIPTION
	"Table entry for plsdSubscribersAgg"
	INDEX { plsdSubscribersAggLevelName }
	::={plsdSubscribersAggLevelTable 1}

PlsdSubscribersAggLevelEntry ::=
	SEQUENCE {
		plsdSubscribersAggLevelName	DisplayString,
		plsdSubscribersAggLevelVal	CounterBasedGauge64,
		plsdSubscribersAggLevelMax	CounterBasedGauge64
	}

plsdSubscribersAggLevelName OBJECT-TYPE
	SYNTAX      DisplayString
	MAX-ACCESS  not-accessible
	STATUS      current
	DESCRIPTION
	"Table entry display string for plsdSubscribersAgg"
	::={plsdSubscribersAggLevelEntry 1}

plsdSubscribersAggLevelVal OBJECT-TYPE
	SYNTAX	 CounterBasedGauge64
	MAX-ACCESS  read-only
	STATUS      current
	DESCRIPTION
	"Table entry attribute for plsdSubscribersAgg"
	::={plsdSubscribersAggLevelEntry 2}

plsdSubscribersAggLevelMax OBJECT-TYPE
	SYNTAX	 CounterBasedGauge64
	MAX-ACCESS  read-only
	STATUS      current
	DESCRIPTION
	"Table entry attribute for plsdSubscribersAgg"
	::={plsdSubscribersAggLevelEntry 4}


plsdDatasetSize	OBJECT IDENTIFIER ::={plsd 47}

plsdDatasetSizeVal	OBJECT-TYPE
	SYNTAX	 CounterBasedGauge64
	MAX-ACCESS read-only
	STATUS current
	DESCRIPTION "Dataset, size"

	::={plsdDatasetSize 1}

plsdDatasetSizeMax	OBJECT-TYPE
	SYNTAX	 CounterBasedGauge64
	MAX-ACCESS read-only
	STATUS current
	DESCRIPTION "Dataset, size"

	::={plsdDatasetSize 3}

plsdDatasetSizeLevelTable OBJECT-TYPE
	SYNTAX      SEQUENCE OF PlsdDatasetSizeLevelEntry
	MAX-ACCESS  not-accessible
	STATUS      current
	DESCRIPTION
	"Table for plsdDatasetSize"
	::={plsdDatasetSize 4}

plsdDatasetSizeLevelEntry OBJECT-TYPE
	SYNTAX      PlsdDatasetSizeLevelEntry
	MAX-ACCESS  not-accessible
	STATUS      current
	DESCRIPTION
	"Table entry for plsdDatasetSize"
	INDEX { plsdDatasetSizeLevelName }
	::={plsdDatasetSizeLevelTable 1}

PlsdDatasetSizeLevelEntry ::=
	SEQUENCE {
		plsdDatasetSizeLevelName	DisplayString,
		plsdDatasetSizeLevelVal	CounterBasedGauge64,
		plsdDatasetSizeLevelMax	CounterBasedGauge64
	}

plsdDatasetSizeLevelName OBJECT-TYPE
	SYNTAX      DisplayString
	MAX-ACCESS  not-accessible
	STATUS      current
	DESCRIPTION
	"Table entry display string for plsdDatasetSize"
	::={plsdDatasetSizeLevelEntry 1}

plsdDatasetSizeLevelVal OBJECT-TYPE
	SYNTAX	 CounterBasedGauge64
	MAX-ACCESS  read-only
	STATUS      current
	DESCRIPTION
	"Table entry attribute for plsdDatasetSize"
	::={plsdDatasetSizeLevelEntry 2}

plsdDatasetSizeLevelMax OBJECT-TYPE
	SYNTAX	 CounterBasedGauge64
	MAX-ACCESS  read-only
	STATUS      current
	DESCRIPTION
	"Table entry attribute for plsdDatasetSize"
	::={plsdDatasetSizeLevelEntry 4}


plsdValueCacheUsage	OBJECT IDENTIFIER ::={plsd 48}

plsdValueCacheUsageVal	OBJECT-TYPE
	SYNTAX	 CounterBasedGauge64
	MAX-ACCESS read-only
	STATUS current
	DESCRIPTION "Value Cache Usage"

	::={plsdValueCacheUsage 1}

plsdValueCacheUsageMax	OBJECT-TYPE
	SYNTAX	 CounterBasedGauge64
	MAX-ACCESS read-only
	STATUS current
	DESCRIPTION "Value Cache Usage"

	::={plsdValueCacheUsage 3}

plsdValueCacheUsageLevelTable OBJECT-TYPE
	SYNTAX      SEQUENCE OF PlsdValueCacheUsageLevelEntry
	MAX-ACCESS  not-accessible
	STATUS      current
	DESCRIPTION
	"Table for plsdValueCacheUsage"
	::={plsdValueCacheUsage 4}

plsdValueCacheUsageLevelEntry OBJECT-TYPE
	SYNTAX      PlsdValueCacheUsageLevelEntry
	MAX-ACCESS  not-accessible
	STATUS      current
	DESCRIPTION
	"Table entry for plsdValueCacheUsage"
	INDEX { plsdValueCacheUsageLevelName }
	::={plsdValueCacheUsageLevelTable 1}

PlsdValueCacheUsageLevelEntry ::=
	SEQUENCE {
		plsdValueCacheUsageLevelName	DisplayString,
		plsdValueCacheUsageLevelVal	CounterBasedGauge64,
		plsdValueCacheUsageLevelMax	CounterBasedGauge64
	}

plsdValueCacheUsageLevelName OBJECT-TYPE
	SYNTAX      DisplayString
	MAX-ACCESS  not-accessible
	STATUS      current
	DESCRIPTION
	"Table entry display string for plsdValueCacheUsage"
	::={plsdValueCacheUsageLevelEntry 1}

plsdValueCacheUsageLevelVal OBJECT-TYPE
	SYNTAX	 CounterBasedGauge64
	MAX-ACCESS  read-only
	STATUS      current
	DESCRIPTION
	"Table entry attribute for plsdValueCacheUsage"
	::={plsdValueCacheUsageLevelEntry 2}

plsdValueCacheUsageLevelMax OBJECT-TYPE
	SYNTAX	 CounterBasedGauge64
	MAX-ACCESS  read-only
	STATUS      current
	DESCRIPTION
	"Table entry attribute for plsdValueCacheUsage"
	::={plsdValueCacheUsageLevelEntry 4}


plsdMsgs	OBJECT IDENTIFIER ::={plsd 49}

plsdMsgsVal	OBJECT-TYPE
	SYNTAX	 Counter64
	MAX-ACCESS read-only
	STATUS current
	DESCRIPTION "Messages"

	::={plsdMsgs 1}

plsdMsgsMom	OBJECT-TYPE
	SYNTAX	 CounterBasedGauge64
	MAX-ACCESS read-only
	STATUS current
	DESCRIPTION "Messages"

	::={plsdMsgs 2}

plsdMsgsMax	OBJECT-TYPE
	SYNTAX	 CounterBasedGauge64
	MAX-ACCESS read-only
	STATUS current
	DESCRIPTION "Messages"

	::={plsdMsgs 3}

plsdMsgsLevelTable OBJECT-TYPE
	SYNTAX      SEQUENCE OF PlsdMsgsLevelEntry
	MAX-ACCESS  not-accessible
	STATUS      current
	DESCRIPTION
	"Table for plsdMsgs"
	::={plsdMsgs 4}

plsdMsgsLevelEntry OBJECT-TYPE
	SYNTAX      PlsdMsgsLevelEntry
	MAX-ACCESS  not-accessible
	STATUS      current
	DESCRIPTION
	"Table entry for plsdMsgs"
	INDEX { plsdMsgsLevelName }
	::={plsdMsgsLevelTable 1}

PlsdMsgsLevelEntry ::=
	SEQUENCE {
		plsdMsgsLevelName	DisplayString,
		plsdMsgsLevelVal	Counter64,
		plsdMsgsLevelMom	CounterBasedGauge64,
		plsdMsgsLevelMax	CounterBasedGauge64
	}

plsdMsgsLevelName OBJECT-TYPE
	SYNTAX      DisplayString
	MAX-ACCESS  not-accessible
	STATUS      current
	DESCRIPTION
	"Table entry display string for plsdMsgs"
	::={plsdMsgsLevelEntry 1}

plsdMsgsLevelVal OBJECT-TYPE
	SYNTAX	 Counter64
	MAX-ACCESS  read-only
	STATUS      current
	DESCRIPTION
	"Table entry attribute for plsdMsgs"
	::={plsdMsgsLevelEntry 2}

plsdMsgsLevelMom OBJECT-TYPE
	SYNTAX	 CounterBasedGauge64
	MAX-ACCESS  read-only
	STATUS      current
	DESCRIPTION
	"Table entry attribute for plsdMsgs"
	::={plsdMsgsLevelEntry 3}

plsdMsgsLevelMax OBJECT-TYPE
	SYNTAX	 CounterBasedGauge64
	MAX-ACCESS  read-only
	STATUS      current
	DESCRIPTION
	"Table entry attribute for plsdMsgs"
	::={plsdMsgsLevelEntry 4}


plsdConnMsgs	OBJECT IDENTIFIER ::={plsd 50}

plsdConnMsgsVal	OBJECT-TYPE
	SYNTAX	 Counter64
	MAX-ACCESS read-only
	STATUS current
	DESCRIPTION "Messages, Connections"

	::={plsdConnMsgs 1}

plsdConnMsgsMom	OBJECT-TYPE
	SYNTAX	 CounterBasedGauge64
	MAX-ACCESS read-only
	STATUS current
	DESCRIPTION "Messages, Connections"

	::={plsdConnMsgs 2}

plsdConnMsgsMax	OBJECT-TYPE
	SYNTAX	 CounterBasedGauge64
	MAX-ACCESS read-only
	STATUS current
	DESCRIPTION "Messages, Connections"

	::={plsdConnMsgs 3}

plsdConnMsgsLevelTable OBJECT-TYPE
	SYNTAX      SEQUENCE OF PlsdConnMsgsLevelEntry
	MAX-ACCESS  not-accessible
	STATUS      current
	DESCRIPTION
	"Table for plsdConnMsgs"
	::={plsdConnMsgs 4}

plsdConnMsgsLevelEntry OBJECT-TYPE
	SYNTAX      PlsdConnMsgsLevelEntry
	MAX-ACCESS  not-accessible
	STATUS      current
	DESCRIPTION
	"Table entry for plsdConnMsgs"
	INDEX { plsdConnMsgsLevelName }
	::={plsdConnMsgsLevelTable 1}

PlsdConnMsgsLevelEntry ::=
	SEQUENCE {
		plsdConnMsgsLevelName	DisplayString,
		plsdConnMsgsLevelVal	Counter64,
		plsdConnMsgsLevelMom	CounterBasedGauge64,
		plsdConnMsgsLevelMax	CounterBasedGauge64
	}

plsdConnMsgsLevelName OBJECT-TYPE
	SYNTAX      DisplayString
	MAX-ACCESS  not-accessible
	STATUS      current
	DESCRIPTION
	"Table entry display string for plsdConnMsgs"
	::={plsdConnMsgsLevelEntry 1}

plsdConnMsgsLevelVal OBJECT-TYPE
	SYNTAX	 Counter64
	MAX-ACCESS  read-only
	STATUS      current
	DESCRIPTION
	"Table entry attribute for plsdConnMsgs"
	::={plsdConnMsgsLevelEntry 2}

plsdConnMsgsLevelMom OBJECT-TYPE
	SYNTAX	 CounterBasedGauge64
	MAX-ACCESS  read-only
	STATUS      current
	DESCRIPTION
	"Table entry attribute for plsdConnMsgs"
	::={plsdConnMsgsLevelEntry 3}

plsdConnMsgsLevelMax OBJECT-TYPE
	SYNTAX	 CounterBasedGauge64
	MAX-ACCESS  read-only
	STATUS      current
	DESCRIPTION
	"Table entry attribute for plsdConnMsgs"
	::={plsdConnMsgsLevelEntry 4}


plsdNoMsgs	OBJECT IDENTIFIER ::={plsd 51}

plsdNoMsgsVal	OBJECT-TYPE
	SYNTAX	 Counter64
	MAX-ACCESS read-only
	STATUS current
	DESCRIPTION "Messages, Netobjects"

	::={plsdNoMsgs 1}

plsdNoMsgsMom	OBJECT-TYPE
	SYNTAX	 CounterBasedGauge64
	MAX-ACCESS read-only
	STATUS current
	DESCRIPTION "Messages, Netobjects"

	::={plsdNoMsgs 2}

plsdNoMsgsMax	OBJECT-TYPE
	SYNTAX	 CounterBasedGauge64
	MAX-ACCESS read-only
	STATUS current
	DESCRIPTION "Messages, Netobjects"

	::={plsdNoMsgs 3}

plsdNoMsgsLevelTable OBJECT-TYPE
	SYNTAX      SEQUENCE OF PlsdNoMsgsLevelEntry
	MAX-ACCESS  not-accessible
	STATUS      current
	DESCRIPTION
	"Table for plsdNoMsgs"
	::={plsdNoMsgs 4}

plsdNoMsgsLevelEntry OBJECT-TYPE
	SYNTAX      PlsdNoMsgsLevelEntry
	MAX-ACCESS  not-accessible
	STATUS      current
	DESCRIPTION
	"Table entry for plsdNoMsgs"
	INDEX { plsdNoMsgsLevelName }
	::={plsdNoMsgsLevelTable 1}

PlsdNoMsgsLevelEntry ::=
	SEQUENCE {
		plsdNoMsgsLevelName	DisplayString,
		plsdNoMsgsLevelVal	Counter64,
		plsdNoMsgsLevelMom	CounterBasedGauge64,
		plsdNoMsgsLevelMax	CounterBasedGauge64
	}

plsdNoMsgsLevelName OBJECT-TYPE
	SYNTAX      DisplayString
	MAX-ACCESS  not-accessible
	STATUS      current
	DESCRIPTION
	"Table entry display string for plsdNoMsgs"
	::={plsdNoMsgsLevelEntry 1}

plsdNoMsgsLevelVal OBJECT-TYPE
	SYNTAX	 Counter64
	MAX-ACCESS  read-only
	STATUS      current
	DESCRIPTION
	"Table entry attribute for plsdNoMsgs"
	::={plsdNoMsgsLevelEntry 2}

plsdNoMsgsLevelMom OBJECT-TYPE
	SYNTAX	 CounterBasedGauge64
	MAX-ACCESS  read-only
	STATUS      current
	DESCRIPTION
	"Table entry attribute for plsdNoMsgs"
	::={plsdNoMsgsLevelEntry 3}

plsdNoMsgsLevelMax OBJECT-TYPE
	SYNTAX	 CounterBasedGauge64
	MAX-ACCESS  read-only
	STATUS      current
	DESCRIPTION
	"Table entry attribute for plsdNoMsgs"
	::={plsdNoMsgsLevelEntry 4}


plsdHostMsgs	OBJECT IDENTIFIER ::={plsd 52}

plsdHostMsgsVal	OBJECT-TYPE
	SYNTAX	 Counter64
	MAX-ACCESS read-only
	STATUS current
	DESCRIPTION "Messages, Hosts"

	::={plsdHostMsgs 1}

plsdHostMsgsMom	OBJECT-TYPE
	SYNTAX	 CounterBasedGauge64
	MAX-ACCESS read-only
	STATUS current
	DESCRIPTION "Messages, Hosts"

	::={plsdHostMsgs 2}

plsdHostMsgsMax	OBJECT-TYPE
	SYNTAX	 CounterBasedGauge64
	MAX-ACCESS read-only
	STATUS current
	DESCRIPTION "Messages, Hosts"

	::={plsdHostMsgs 3}

plsdHostMsgsLevelTable OBJECT-TYPE
	SYNTAX      SEQUENCE OF PlsdHostMsgsLevelEntry
	MAX-ACCESS  not-accessible
	STATUS      current
	DESCRIPTION
	"Table for plsdHostMsgs"
	::={plsdHostMsgs 4}

plsdHostMsgsLevelEntry OBJECT-TYPE
	SYNTAX      PlsdHostMsgsLevelEntry
	MAX-ACCESS  not-accessible
	STATUS      current
	DESCRIPTION
	"Table entry for plsdHostMsgs"
	INDEX { plsdHostMsgsLevelName }
	::={plsdHostMsgsLevelTable 1}

PlsdHostMsgsLevelEntry ::=
	SEQUENCE {
		plsdHostMsgsLevelName	DisplayString,
		plsdHostMsgsLevelVal	Counter64,
		plsdHostMsgsLevelMom	CounterBasedGauge64,
		plsdHostMsgsLevelMax	CounterBasedGauge64
	}

plsdHostMsgsLevelName OBJECT-TYPE
	SYNTAX      DisplayString
	MAX-ACCESS  not-accessible
	STATUS      current
	DESCRIPTION
	"Table entry display string for plsdHostMsgs"
	::={plsdHostMsgsLevelEntry 1}

plsdHostMsgsLevelVal OBJECT-TYPE
	SYNTAX	 Counter64
	MAX-ACCESS  read-only
	STATUS      current
	DESCRIPTION
	"Table entry attribute for plsdHostMsgs"
	::={plsdHostMsgsLevelEntry 2}

plsdHostMsgsLevelMom OBJECT-TYPE
	SYNTAX	 CounterBasedGauge64
	MAX-ACCESS  read-only
	STATUS      current
	DESCRIPTION
	"Table entry attribute for plsdHostMsgs"
	::={plsdHostMsgsLevelEntry 3}

plsdHostMsgsLevelMax OBJECT-TYPE
	SYNTAX	 CounterBasedGauge64
	MAX-ACCESS  read-only
	STATUS      current
	DESCRIPTION
	"Table entry attribute for plsdHostMsgs"
	::={plsdHostMsgsLevelEntry 4}


plsdStringCacheSize	OBJECT IDENTIFIER ::={plsd 53}

plsdStringCacheSizeVal	OBJECT-TYPE
	SYNTAX	 CounterBasedGauge64
	MAX-ACCESS read-only
	STATUS current
	DESCRIPTION "String Cache, Size"

	::={plsdStringCacheSize 1}

plsdStringCacheSizeMax	OBJECT-TYPE
	SYNTAX	 CounterBasedGauge64
	MAX-ACCESS read-only
	STATUS current
	DESCRIPTION "String Cache, Size"

	::={plsdStringCacheSize 3}

plsdStringCacheSizeLevelTable OBJECT-TYPE
	SYNTAX      SEQUENCE OF PlsdStringCacheSizeLevelEntry
	MAX-ACCESS  not-accessible
	STATUS      current
	DESCRIPTION
	"Table for plsdStringCacheSize"
	::={plsdStringCacheSize 4}

plsdStringCacheSizeLevelEntry OBJECT-TYPE
	SYNTAX      PlsdStringCacheSizeLevelEntry
	MAX-ACCESS  not-accessible
	STATUS      current
	DESCRIPTION
	"Table entry for plsdStringCacheSize"
	INDEX { plsdStringCacheSizeLevelName }
	::={plsdStringCacheSizeLevelTable 1}

PlsdStringCacheSizeLevelEntry ::=
	SEQUENCE {
		plsdStringCacheSizeLevelName	DisplayString,
		plsdStringCacheSizeLevelVal	CounterBasedGauge64,
		plsdStringCacheSizeLevelMax	CounterBasedGauge64
	}

plsdStringCacheSizeLevelName OBJECT-TYPE
	SYNTAX      DisplayString
	MAX-ACCESS  not-accessible
	STATUS      current
	DESCRIPTION
	"Table entry display string for plsdStringCacheSize"
	::={plsdStringCacheSizeLevelEntry 1}

plsdStringCacheSizeLevelVal OBJECT-TYPE
	SYNTAX	 CounterBasedGauge64
	MAX-ACCESS  read-only
	STATUS      current
	DESCRIPTION
	"Table entry attribute for plsdStringCacheSize"
	::={plsdStringCacheSizeLevelEntry 2}

plsdStringCacheSizeLevelMax OBJECT-TYPE
	SYNTAX	 CounterBasedGauge64
	MAX-ACCESS  read-only
	STATUS      current
	DESCRIPTION
	"Table entry attribute for plsdStringCacheSize"
	::={plsdStringCacheSizeLevelEntry 4}


plsdStringCacheUsage	OBJECT IDENTIFIER ::={plsd 54}

plsdStringCacheUsageVal	OBJECT-TYPE
	SYNTAX	 CounterBasedGauge64
	MAX-ACCESS read-only
	STATUS current
	DESCRIPTION "String Cache, Usage"

	::={plsdStringCacheUsage 1}

plsdStringCacheUsageMax	OBJECT-TYPE
	SYNTAX	 CounterBasedGauge64
	MAX-ACCESS read-only
	STATUS current
	DESCRIPTION "String Cache, Usage"

	::={plsdStringCacheUsage 3}

plsdStringCacheUsageLevelTable OBJECT-TYPE
	SYNTAX      SEQUENCE OF PlsdStringCacheUsageLevelEntry
	MAX-ACCESS  not-accessible
	STATUS      current
	DESCRIPTION
	"Table for plsdStringCacheUsage"
	::={plsdStringCacheUsage 4}

plsdStringCacheUsageLevelEntry OBJECT-TYPE
	SYNTAX      PlsdStringCacheUsageLevelEntry
	MAX-ACCESS  not-accessible
	STATUS      current
	DESCRIPTION
	"Table entry for plsdStringCacheUsage"
	INDEX { plsdStringCacheUsageLevelName }
	::={plsdStringCacheUsageLevelTable 1}

PlsdStringCacheUsageLevelEntry ::=
	SEQUENCE {
		plsdStringCacheUsageLevelName	DisplayString,
		plsdStringCacheUsageLevelVal	CounterBasedGauge64,
		plsdStringCacheUsageLevelMax	CounterBasedGauge64
	}

plsdStringCacheUsageLevelName OBJECT-TYPE
	SYNTAX      DisplayString
	MAX-ACCESS  not-accessible
	STATUS      current
	DESCRIPTION
	"Table entry display string for plsdStringCacheUsage"
	::={plsdStringCacheUsageLevelEntry 1}

plsdStringCacheUsageLevelVal OBJECT-TYPE
	SYNTAX	 CounterBasedGauge64
	MAX-ACCESS  read-only
	STATUS      current
	DESCRIPTION
	"Table entry attribute for plsdStringCacheUsage"
	::={plsdStringCacheUsageLevelEntry 2}

plsdStringCacheUsageLevelMax OBJECT-TYPE
	SYNTAX	 CounterBasedGauge64
	MAX-ACCESS  read-only
	STATUS      current
	DESCRIPTION
	"Table entry attribute for plsdStringCacheUsage"
	::={plsdStringCacheUsageLevelEntry 4}


plsdDynIPs	OBJECT IDENTIFIER ::={plsd 55}

plsdDynIPsVal	OBJECT-TYPE
	SYNTAX	 CounterBasedGauge64
	MAX-ACCESS read-only
	STATUS current
	DESCRIPTION "Dynamic IP count"

	::={plsdDynIPs 1}

plsdDynIPsMax	OBJECT-TYPE
	SYNTAX	 CounterBasedGauge64
	MAX-ACCESS read-only
	STATUS current
	DESCRIPTION "Dynamic IP count"

	::={plsdDynIPs 3}

plsdDynIPsLevelTable OBJECT-TYPE
	SYNTAX      SEQUENCE OF PlsdDynIPsLevelEntry
	MAX-ACCESS  not-accessible
	STATUS      current
	DESCRIPTION
	"Table for plsdDynIPs"
	::={plsdDynIPs 4}

plsdDynIPsLevelEntry OBJECT-TYPE
	SYNTAX      PlsdDynIPsLevelEntry
	MAX-ACCESS  not-accessible
	STATUS      current
	DESCRIPTION
	"Table entry for plsdDynIPs"
	INDEX { plsdDynIPsLevelName }
	::={plsdDynIPsLevelTable 1}

PlsdDynIPsLevelEntry ::=
	SEQUENCE {
		plsdDynIPsLevelName	DisplayString,
		plsdDynIPsLevelVal	CounterBasedGauge64,
		plsdDynIPsLevelMax	CounterBasedGauge64
	}

plsdDynIPsLevelName OBJECT-TYPE
	SYNTAX      DisplayString
	MAX-ACCESS  not-accessible
	STATUS      current
	DESCRIPTION
	"Table entry display string for plsdDynIPs"
	::={plsdDynIPsLevelEntry 1}

plsdDynIPsLevelVal OBJECT-TYPE
	SYNTAX	 CounterBasedGauge64
	MAX-ACCESS  read-only
	STATUS      current
	DESCRIPTION
	"Table entry attribute for plsdDynIPs"
	::={plsdDynIPsLevelEntry 2}

plsdDynIPsLevelMax OBJECT-TYPE
	SYNTAX	 CounterBasedGauge64
	MAX-ACCESS  read-only
	STATUS      current
	DESCRIPTION
	"Table entry attribute for plsdDynIPs"
	::={plsdDynIPsLevelEntry 4}


plsdDynAdds	OBJECT IDENTIFIER ::={plsd 56}

plsdDynAddsVal	OBJECT-TYPE
	SYNTAX	 Counter64
	MAX-ACCESS read-only
	STATUS current
	DESCRIPTION "Dynamic Netobject Adds"

	::={plsdDynAdds 1}

plsdDynAddsMom	OBJECT-TYPE
	SYNTAX	 CounterBasedGauge64
	MAX-ACCESS read-only
	STATUS current
	DESCRIPTION "Dynamic Netobject Adds"

	::={plsdDynAdds 2}

plsdDynAddsMax	OBJECT-TYPE
	SYNTAX	 CounterBasedGauge64
	MAX-ACCESS read-only
	STATUS current
	DESCRIPTION "Dynamic Netobject Adds"

	::={plsdDynAdds 3}

plsdDynAddsLevelTable OBJECT-TYPE
	SYNTAX      SEQUENCE OF PlsdDynAddsLevelEntry
	MAX-ACCESS  not-accessible
	STATUS      current
	DESCRIPTION
	"Table for plsdDynAdds"
	::={plsdDynAdds 4}

plsdDynAddsLevelEntry OBJECT-TYPE
	SYNTAX      PlsdDynAddsLevelEntry
	MAX-ACCESS  not-accessible
	STATUS      current
	DESCRIPTION
	"Table entry for plsdDynAdds"
	INDEX { plsdDynAddsLevelName }
	::={plsdDynAddsLevelTable 1}

PlsdDynAddsLevelEntry ::=
	SEQUENCE {
		plsdDynAddsLevelName	DisplayString,
		plsdDynAddsLevelVal	Counter64,
		plsdDynAddsLevelMom	CounterBasedGauge64,
		plsdDynAddsLevelMax	CounterBasedGauge64
	}

plsdDynAddsLevelName OBJECT-TYPE
	SYNTAX      DisplayString
	MAX-ACCESS  not-accessible
	STATUS      current
	DESCRIPTION
	"Table entry display string for plsdDynAdds"
	::={plsdDynAddsLevelEntry 1}

plsdDynAddsLevelVal OBJECT-TYPE
	SYNTAX	 Counter64
	MAX-ACCESS  read-only
	STATUS      current
	DESCRIPTION
	"Table entry attribute for plsdDynAdds"
	::={plsdDynAddsLevelEntry 2}

plsdDynAddsLevelMom OBJECT-TYPE
	SYNTAX	 CounterBasedGauge64
	MAX-ACCESS  read-only
	STATUS      current
	DESCRIPTION
	"Table entry attribute for plsdDynAdds"
	::={plsdDynAddsLevelEntry 3}

plsdDynAddsLevelMax OBJECT-TYPE
	SYNTAX	 CounterBasedGauge64
	MAX-ACCESS  read-only
	STATUS      current
	DESCRIPTION
	"Table entry attribute for plsdDynAdds"
	::={plsdDynAddsLevelEntry 4}


plsdDynRemoves	OBJECT IDENTIFIER ::={plsd 57}

plsdDynRemovesVal	OBJECT-TYPE
	SYNTAX	 Counter64
	MAX-ACCESS read-only
	STATUS current
	DESCRIPTION "Dynamic Netobject Removes"

	::={plsdDynRemoves 1}

plsdDynRemovesMom	OBJECT-TYPE
	SYNTAX	 CounterBasedGauge64
	MAX-ACCESS read-only
	STATUS current
	DESCRIPTION "Dynamic Netobject Removes"

	::={plsdDynRemoves 2}

plsdDynRemovesMax	OBJECT-TYPE
	SYNTAX	 CounterBasedGauge64
	MAX-ACCESS read-only
	STATUS current
	DESCRIPTION "Dynamic Netobject Removes"

	::={plsdDynRemoves 3}

plsdDynRemovesLevelTable OBJECT-TYPE
	SYNTAX      SEQUENCE OF PlsdDynRemovesLevelEntry
	MAX-ACCESS  not-accessible
	STATUS      current
	DESCRIPTION
	"Table for plsdDynRemoves"
	::={plsdDynRemoves 4}

plsdDynRemovesLevelEntry OBJECT-TYPE
	SYNTAX      PlsdDynRemovesLevelEntry
	MAX-ACCESS  not-accessible
	STATUS      current
	DESCRIPTION
	"Table entry for plsdDynRemoves"
	INDEX { plsdDynRemovesLevelName }
	::={plsdDynRemovesLevelTable 1}

PlsdDynRemovesLevelEntry ::=
	SEQUENCE {
		plsdDynRemovesLevelName	DisplayString,
		plsdDynRemovesLevelVal	Counter64,
		plsdDynRemovesLevelMom	CounterBasedGauge64,
		plsdDynRemovesLevelMax	CounterBasedGauge64
	}

plsdDynRemovesLevelName OBJECT-TYPE
	SYNTAX      DisplayString
	MAX-ACCESS  not-accessible
	STATUS      current
	DESCRIPTION
	"Table entry display string for plsdDynRemoves"
	::={plsdDynRemovesLevelEntry 1}

plsdDynRemovesLevelVal OBJECT-TYPE
	SYNTAX	 Counter64
	MAX-ACCESS  read-only
	STATUS      current
	DESCRIPTION
	"Table entry attribute for plsdDynRemoves"
	::={plsdDynRemovesLevelEntry 2}

plsdDynRemovesLevelMom OBJECT-TYPE
	SYNTAX	 CounterBasedGauge64
	MAX-ACCESS  read-only
	STATUS      current
	DESCRIPTION
	"Table entry attribute for plsdDynRemoves"
	::={plsdDynRemovesLevelEntry 3}

plsdDynRemovesLevelMax OBJECT-TYPE
	SYNTAX	 CounterBasedGauge64
	MAX-ACCESS  read-only
	STATUS      current
	DESCRIPTION
	"Table entry attribute for plsdDynRemoves"
	::={plsdDynRemovesLevelEntry 4}


plsdDynIPLookups	OBJECT IDENTIFIER ::={plsd 58}

plsdDynIPLookupsVal	OBJECT-TYPE
	SYNTAX	 Counter64
	MAX-ACCESS read-only
	STATUS current
	DESCRIPTION "Dynamic IP lookups"

	::={plsdDynIPLookups 1}

plsdDynIPLookupsMom	OBJECT-TYPE
	SYNTAX	 CounterBasedGauge64
	MAX-ACCESS read-only
	STATUS current
	DESCRIPTION "Dynamic IP lookups"

	::={plsdDynIPLookups 2}

plsdDynIPLookupsMax	OBJECT-TYPE
	SYNTAX	 CounterBasedGauge64
	MAX-ACCESS read-only
	STATUS current
	DESCRIPTION "Dynamic IP lookups"

	::={plsdDynIPLookups 3}

plsdDynIPLookupsLevelTable OBJECT-TYPE
	SYNTAX      SEQUENCE OF PlsdDynIPLookupsLevelEntry
	MAX-ACCESS  not-accessible
	STATUS      current
	DESCRIPTION
	"Table for plsdDynIPLookups"
	::={plsdDynIPLookups 4}

plsdDynIPLookupsLevelEntry OBJECT-TYPE
	SYNTAX      PlsdDynIPLookupsLevelEntry
	MAX-ACCESS  not-accessible
	STATUS      current
	DESCRIPTION
	"Table entry for plsdDynIPLookups"
	INDEX { plsdDynIPLookupsLevelName }
	::={plsdDynIPLookupsLevelTable 1}

PlsdDynIPLookupsLevelEntry ::=
	SEQUENCE {
		plsdDynIPLookupsLevelName	DisplayString,
		plsdDynIPLookupsLevelVal	Counter64,
		plsdDynIPLookupsLevelMom	CounterBasedGauge64,
		plsdDynIPLookupsLevelMax	CounterBasedGauge64
	}

plsdDynIPLookupsLevelName OBJECT-TYPE
	SYNTAX      DisplayString
	MAX-ACCESS  not-accessible
	STATUS      current
	DESCRIPTION
	"Table entry display string for plsdDynIPLookups"
	::={plsdDynIPLookupsLevelEntry 1}

plsdDynIPLookupsLevelVal OBJECT-TYPE
	SYNTAX	 Counter64
	MAX-ACCESS  read-only
	STATUS      current
	DESCRIPTION
	"Table entry attribute for plsdDynIPLookups"
	::={plsdDynIPLookupsLevelEntry 2}

plsdDynIPLookupsLevelMom OBJECT-TYPE
	SYNTAX	 CounterBasedGauge64
	MAX-ACCESS  read-only
	STATUS      current
	DESCRIPTION
	"Table entry attribute for plsdDynIPLookups"
	::={plsdDynIPLookupsLevelEntry 3}

plsdDynIPLookupsLevelMax OBJECT-TYPE
	SYNTAX	 CounterBasedGauge64
	MAX-ACCESS  read-only
	STATUS      current
	DESCRIPTION
	"Table entry attribute for plsdDynIPLookups"
	::={plsdDynIPLookupsLevelEntry 4}


plsdNetobjects	OBJECT IDENTIFIER ::={plsd 59}

plsdNetobjectsVal	OBJECT-TYPE
	SYNTAX	 CounterBasedGauge64
	MAX-ACCESS read-only
	STATUS current
	DESCRIPTION "NetObject Count"

	::={plsdNetobjects 1}

plsdNetobjectsMax	OBJECT-TYPE
	SYNTAX	 CounterBasedGauge64
	MAX-ACCESS read-only
	STATUS current
	DESCRIPTION "NetObject Count"

	::={plsdNetobjects 3}

plsdNetobjectsLevelTable OBJECT-TYPE
	SYNTAX      SEQUENCE OF PlsdNetobjectsLevelEntry
	MAX-ACCESS  not-accessible
	STATUS      current
	DESCRIPTION
	"Table for plsdNetobjects"
	::={plsdNetobjects 4}

plsdNetobjectsLevelEntry OBJECT-TYPE
	SYNTAX      PlsdNetobjectsLevelEntry
	MAX-ACCESS  not-accessible
	STATUS      current
	DESCRIPTION
	"Table entry for plsdNetobjects"
	INDEX { plsdNetobjectsLevelName }
	::={plsdNetobjectsLevelTable 1}

PlsdNetobjectsLevelEntry ::=
	SEQUENCE {
		plsdNetobjectsLevelName	DisplayString,
		plsdNetobjectsLevelVal	CounterBasedGauge64,
		plsdNetobjectsLevelMax	CounterBasedGauge64
	}

plsdNetobjectsLevelName OBJECT-TYPE
	SYNTAX      DisplayString
	MAX-ACCESS  not-accessible
	STATUS      current
	DESCRIPTION
	"Table entry display string for plsdNetobjects"
	::={plsdNetobjectsLevelEntry 1}

plsdNetobjectsLevelVal OBJECT-TYPE
	SYNTAX	 CounterBasedGauge64
	MAX-ACCESS  read-only
	STATUS      current
	DESCRIPTION
	"Table entry attribute for plsdNetobjects"
	::={plsdNetobjectsLevelEntry 2}

plsdNetobjectsLevelMax OBJECT-TYPE
	SYNTAX	 CounterBasedGauge64
	MAX-ACCESS  read-only
	STATUS      current
	DESCRIPTION
	"Table entry attribute for plsdNetobjects"
	::={plsdNetobjectsLevelEntry 4}


plsdConnUpdateCount1	OBJECT IDENTIFIER ::={plsd 60}

plsdConnUpdateCount1Val	OBJECT-TYPE
	SYNTAX	 Counter64
	MAX-ACCESS read-only
	STATUS current
	DESCRIPTION "Connection updates (1 per connection)"

	::={plsdConnUpdateCount1 1}

plsdConnUpdateCount1Mom	OBJECT-TYPE
	SYNTAX	 CounterBasedGauge64
	MAX-ACCESS read-only
	STATUS current
	DESCRIPTION "Connection updates (1 per connection)"

	::={plsdConnUpdateCount1 2}

plsdConnUpdateCount1Max	OBJECT-TYPE
	SYNTAX	 CounterBasedGauge64
	MAX-ACCESS read-only
	STATUS current
	DESCRIPTION "Connection updates (1 per connection)"

	::={plsdConnUpdateCount1 3}

plsdConnUpdateCount1LevelTable OBJECT-TYPE
	SYNTAX      SEQUENCE OF PlsdConnUpdateCount1LevelEntry
	MAX-ACCESS  not-accessible
	STATUS      current
	DESCRIPTION
	"Table for plsdConnUpdateCount1"
	::={plsdConnUpdateCount1 4}

plsdConnUpdateCount1LevelEntry OBJECT-TYPE
	SYNTAX      PlsdConnUpdateCount1LevelEntry
	MAX-ACCESS  not-accessible
	STATUS      current
	DESCRIPTION
	"Table entry for plsdConnUpdateCount1"
	INDEX { plsdConnUpdateCount1LevelName }
	::={plsdConnUpdateCount1LevelTable 1}

PlsdConnUpdateCount1LevelEntry ::=
	SEQUENCE {
		plsdConnUpdateCount1LevelName	DisplayString,
		plsdConnUpdateCount1LevelVal	Counter64,
		plsdConnUpdateCount1LevelMom	CounterBasedGauge64,
		plsdConnUpdateCount1LevelMax	CounterBasedGauge64
	}

plsdConnUpdateCount1LevelName OBJECT-TYPE
	SYNTAX      DisplayString
	MAX-ACCESS  not-accessible
	STATUS      current
	DESCRIPTION
	"Table entry display string for plsdConnUpdateCount1"
	::={plsdConnUpdateCount1LevelEntry 1}

plsdConnUpdateCount1LevelVal OBJECT-TYPE
	SYNTAX	 Counter64
	MAX-ACCESS  read-only
	STATUS      current
	DESCRIPTION
	"Table entry attribute for plsdConnUpdateCount1"
	::={plsdConnUpdateCount1LevelEntry 2}

plsdConnUpdateCount1LevelMom OBJECT-TYPE
	SYNTAX	 CounterBasedGauge64
	MAX-ACCESS  read-only
	STATUS      current
	DESCRIPTION
	"Table entry attribute for plsdConnUpdateCount1"
	::={plsdConnUpdateCount1LevelEntry 3}

plsdConnUpdateCount1LevelMax OBJECT-TYPE
	SYNTAX	 CounterBasedGauge64
	MAX-ACCESS  read-only
	STATUS      current
	DESCRIPTION
	"Table entry attribute for plsdConnUpdateCount1"
	::={plsdConnUpdateCount1LevelEntry 4}


plsdConnUpdateCount2	OBJECT IDENTIFIER ::={plsd 61}

plsdConnUpdateCount2Val	OBJECT-TYPE
	SYNTAX	 Counter64
	MAX-ACCESS read-only
	STATUS current
	DESCRIPTION "Connection updates (2 per connection)"

	::={plsdConnUpdateCount2 1}

plsdConnUpdateCount2Mom	OBJECT-TYPE
	SYNTAX	 CounterBasedGauge64
	MAX-ACCESS read-only
	STATUS current
	DESCRIPTION "Connection updates (2 per connection)"

	::={plsdConnUpdateCount2 2}

plsdConnUpdateCount2Max	OBJECT-TYPE
	SYNTAX	 CounterBasedGauge64
	MAX-ACCESS read-only
	STATUS current
	DESCRIPTION "Connection updates (2 per connection)"

	::={plsdConnUpdateCount2 3}

plsdConnUpdateCount2LevelTable OBJECT-TYPE
	SYNTAX      SEQUENCE OF PlsdConnUpdateCount2LevelEntry
	MAX-ACCESS  not-accessible
	STATUS      current
	DESCRIPTION
	"Table for plsdConnUpdateCount2"
	::={plsdConnUpdateCount2 4}

plsdConnUpdateCount2LevelEntry OBJECT-TYPE
	SYNTAX      PlsdConnUpdateCount2LevelEntry
	MAX-ACCESS  not-accessible
	STATUS      current
	DESCRIPTION
	"Table entry for plsdConnUpdateCount2"
	INDEX { plsdConnUpdateCount2LevelName }
	::={plsdConnUpdateCount2LevelTable 1}

PlsdConnUpdateCount2LevelEntry ::=
	SEQUENCE {
		plsdConnUpdateCount2LevelName	DisplayString,
		plsdConnUpdateCount2LevelVal	Counter64,
		plsdConnUpdateCount2LevelMom	CounterBasedGauge64,
		plsdConnUpdateCount2LevelMax	CounterBasedGauge64
	}

plsdConnUpdateCount2LevelName OBJECT-TYPE
	SYNTAX      DisplayString
	MAX-ACCESS  not-accessible
	STATUS      current
	DESCRIPTION
	"Table entry display string for plsdConnUpdateCount2"
	::={plsdConnUpdateCount2LevelEntry 1}

plsdConnUpdateCount2LevelVal OBJECT-TYPE
	SYNTAX	 Counter64
	MAX-ACCESS  read-only
	STATUS      current
	DESCRIPTION
	"Table entry attribute for plsdConnUpdateCount2"
	::={plsdConnUpdateCount2LevelEntry 2}

plsdConnUpdateCount2LevelMom OBJECT-TYPE
	SYNTAX	 CounterBasedGauge64
	MAX-ACCESS  read-only
	STATUS      current
	DESCRIPTION
	"Table entry attribute for plsdConnUpdateCount2"
	::={plsdConnUpdateCount2LevelEntry 3}

plsdConnUpdateCount2LevelMax OBJECT-TYPE
	SYNTAX	 CounterBasedGauge64
	MAX-ACCESS  read-only
	STATUS      current
	DESCRIPTION
	"Table entry attribute for plsdConnUpdateCount2"
	::={plsdConnUpdateCount2LevelEntry 4}


plsdConnUpdateCount3	OBJECT IDENTIFIER ::={plsd 62}

plsdConnUpdateCount3Val	OBJECT-TYPE
	SYNTAX	 Counter64
	MAX-ACCESS read-only
	STATUS current
	DESCRIPTION "Connection updates (3 per connection)"

	::={plsdConnUpdateCount3 1}

plsdConnUpdateCount3Mom	OBJECT-TYPE
	SYNTAX	 CounterBasedGauge64
	MAX-ACCESS read-only
	STATUS current
	DESCRIPTION "Connection updates (3 per connection)"

	::={plsdConnUpdateCount3 2}

plsdConnUpdateCount3Max	OBJECT-TYPE
	SYNTAX	 CounterBasedGauge64
	MAX-ACCESS read-only
	STATUS current
	DESCRIPTION "Connection updates (3 per connection)"

	::={plsdConnUpdateCount3 3}

plsdConnUpdateCount3LevelTable OBJECT-TYPE
	SYNTAX      SEQUENCE OF PlsdConnUpdateCount3LevelEntry
	MAX-ACCESS  not-accessible
	STATUS      current
	DESCRIPTION
	"Table for plsdConnUpdateCount3"
	::={plsdConnUpdateCount3 4}

plsdConnUpdateCount3LevelEntry OBJECT-TYPE
	SYNTAX      PlsdConnUpdateCount3LevelEntry
	MAX-ACCESS  not-accessible
	STATUS      current
	DESCRIPTION
	"Table entry for plsdConnUpdateCount3"
	INDEX { plsdConnUpdateCount3LevelName }
	::={plsdConnUpdateCount3LevelTable 1}

PlsdConnUpdateCount3LevelEntry ::=
	SEQUENCE {
		plsdConnUpdateCount3LevelName	DisplayString,
		plsdConnUpdateCount3LevelVal	Counter64,
		plsdConnUpdateCount3LevelMom	CounterBasedGauge64,
		plsdConnUpdateCount3LevelMax	CounterBasedGauge64
	}

plsdConnUpdateCount3LevelName OBJECT-TYPE
	SYNTAX      DisplayString
	MAX-ACCESS  not-accessible
	STATUS      current
	DESCRIPTION
	"Table entry display string for plsdConnUpdateCount3"
	::={plsdConnUpdateCount3LevelEntry 1}

plsdConnUpdateCount3LevelVal OBJECT-TYPE
	SYNTAX	 Counter64
	MAX-ACCESS  read-only
	STATUS      current
	DESCRIPTION
	"Table entry attribute for plsdConnUpdateCount3"
	::={plsdConnUpdateCount3LevelEntry 2}

plsdConnUpdateCount3LevelMom OBJECT-TYPE
	SYNTAX	 CounterBasedGauge64
	MAX-ACCESS  read-only
	STATUS      current
	DESCRIPTION
	"Table entry attribute for plsdConnUpdateCount3"
	::={plsdConnUpdateCount3LevelEntry 3}

plsdConnUpdateCount3LevelMax OBJECT-TYPE
	SYNTAX	 CounterBasedGauge64
	MAX-ACCESS  read-only
	STATUS      current
	DESCRIPTION
	"Table entry attribute for plsdConnUpdateCount3"
	::={plsdConnUpdateCount3LevelEntry 4}


plsdConnUpdateCount4	OBJECT IDENTIFIER ::={plsd 63}

plsdConnUpdateCount4Val	OBJECT-TYPE
	SYNTAX	 Counter64
	MAX-ACCESS read-only
	STATUS current
	DESCRIPTION "Connection updates (4 per connection)"

	::={plsdConnUpdateCount4 1}

plsdConnUpdateCount4Mom	OBJECT-TYPE
	SYNTAX	 CounterBasedGauge64
	MAX-ACCESS read-only
	STATUS current
	DESCRIPTION "Connection updates (4 per connection)"

	::={plsdConnUpdateCount4 2}

plsdConnUpdateCount4Max	OBJECT-TYPE
	SYNTAX	 CounterBasedGauge64
	MAX-ACCESS read-only
	STATUS current
	DESCRIPTION "Connection updates (4 per connection)"

	::={plsdConnUpdateCount4 3}

plsdConnUpdateCount4LevelTable OBJECT-TYPE
	SYNTAX      SEQUENCE OF PlsdConnUpdateCount4LevelEntry
	MAX-ACCESS  not-accessible
	STATUS      current
	DESCRIPTION
	"Table for plsdConnUpdateCount4"
	::={plsdConnUpdateCount4 4}

plsdConnUpdateCount4LevelEntry OBJECT-TYPE
	SYNTAX      PlsdConnUpdateCount4LevelEntry
	MAX-ACCESS  not-accessible
	STATUS      current
	DESCRIPTION
	"Table entry for plsdConnUpdateCount4"
	INDEX { plsdConnUpdateCount4LevelName }
	::={plsdConnUpdateCount4LevelTable 1}

PlsdConnUpdateCount4LevelEntry ::=
	SEQUENCE {
		plsdConnUpdateCount4LevelName	DisplayString,
		plsdConnUpdateCount4LevelVal	Counter64,
		plsdConnUpdateCount4LevelMom	CounterBasedGauge64,
		plsdConnUpdateCount4LevelMax	CounterBasedGauge64
	}

plsdConnUpdateCount4LevelName OBJECT-TYPE
	SYNTAX      DisplayString
	MAX-ACCESS  not-accessible
	STATUS      current
	DESCRIPTION
	"Table entry display string for plsdConnUpdateCount4"
	::={plsdConnUpdateCount4LevelEntry 1}

plsdConnUpdateCount4LevelVal OBJECT-TYPE
	SYNTAX	 Counter64
	MAX-ACCESS  read-only
	STATUS      current
	DESCRIPTION
	"Table entry attribute for plsdConnUpdateCount4"
	::={plsdConnUpdateCount4LevelEntry 2}

plsdConnUpdateCount4LevelMom OBJECT-TYPE
	SYNTAX	 CounterBasedGauge64
	MAX-ACCESS  read-only
	STATUS      current
	DESCRIPTION
	"Table entry attribute for plsdConnUpdateCount4"
	::={plsdConnUpdateCount4LevelEntry 3}

plsdConnUpdateCount4LevelMax OBJECT-TYPE
	SYNTAX	 CounterBasedGauge64
	MAX-ACCESS  read-only
	STATUS      current
	DESCRIPTION
	"Table entry attribute for plsdConnUpdateCount4"
	::={plsdConnUpdateCount4LevelEntry 4}


plsdConnUpdateCountGreaterThan4	OBJECT IDENTIFIER ::={plsd 64}

plsdConnUpdateCountGreaterThan4Val	OBJECT-TYPE
	SYNTAX	 Counter64
	MAX-ACCESS read-only
	STATUS current
	DESCRIPTION "Connection updates (5 or more per connection)"

	::={plsdConnUpdateCountGreaterThan4 1}

plsdConnUpdateCountGreaterThan4Mom	OBJECT-TYPE
	SYNTAX	 CounterBasedGauge64
	MAX-ACCESS read-only
	STATUS current
	DESCRIPTION "Connection updates (5 or more per connection)"

	::={plsdConnUpdateCountGreaterThan4 2}

plsdConnUpdateCountGreaterThan4Max	OBJECT-TYPE
	SYNTAX	 CounterBasedGauge64
	MAX-ACCESS read-only
	STATUS current
	DESCRIPTION "Connection updates (5 or more per connection)"

	::={plsdConnUpdateCountGreaterThan4 3}

plsdConnUpdateCountGreaterThan4LevelTable OBJECT-TYPE
	SYNTAX      SEQUENCE OF PlsdConnUpdateCountGreaterThan4LevelEntry
	MAX-ACCESS  not-accessible
	STATUS      current
	DESCRIPTION
	"Table for plsdConnUpdateCountGreaterThan4"
	::={plsdConnUpdateCountGreaterThan4 4}

plsdConnUpdateCountGreaterThan4LevelEntry OBJECT-TYPE
	SYNTAX      PlsdConnUpdateCountGreaterThan4LevelEntry
	MAX-ACCESS  not-accessible
	STATUS      current
	DESCRIPTION
	"Table entry for plsdConnUpdateCountGreaterThan4"
	INDEX { plsdConnUpdateCountGreaterThan4LevelName }
	::={plsdConnUpdateCountGreaterThan4LevelTable 1}

PlsdConnUpdateCountGreaterThan4LevelEntry ::=
	SEQUENCE {
		plsdConnUpdateCountGreaterThan4LevelName	DisplayString,
		plsdConnUpdateCountGreaterThan4LevelVal	Counter64,
		plsdConnUpdateCountGreaterThan4LevelMom	CounterBasedGauge64,
		plsdConnUpdateCountGreaterThan4LevelMax	CounterBasedGauge64
	}

plsdConnUpdateCountGreaterThan4LevelName OBJECT-TYPE
	SYNTAX      DisplayString
	MAX-ACCESS  not-accessible
	STATUS      current
	DESCRIPTION
	"Table entry display string for plsdConnUpdateCountGreaterThan4"
	::={plsdConnUpdateCountGreaterThan4LevelEntry 1}

plsdConnUpdateCountGreaterThan4LevelVal OBJECT-TYPE
	SYNTAX	 Counter64
	MAX-ACCESS  read-only
	STATUS      current
	DESCRIPTION
	"Table entry attribute for plsdConnUpdateCountGreaterThan4"
	::={plsdConnUpdateCountGreaterThan4LevelEntry 2}

plsdConnUpdateCountGreaterThan4LevelMom OBJECT-TYPE
	SYNTAX	 CounterBasedGauge64
	MAX-ACCESS  read-only
	STATUS      current
	DESCRIPTION
	"Table entry attribute for plsdConnUpdateCountGreaterThan4"
	::={plsdConnUpdateCountGreaterThan4LevelEntry 3}

plsdConnUpdateCountGreaterThan4LevelMax OBJECT-TYPE
	SYNTAX	 CounterBasedGauge64
	MAX-ACCESS  read-only
	STATUS      current
	DESCRIPTION
	"Table entry attribute for plsdConnUpdateCountGreaterThan4"
	::={plsdConnUpdateCountGreaterThan4LevelEntry 4}


plsdDynamicNoCount	OBJECT IDENTIFIER ::={plsd 65}

plsdDynamicNoCountVal	OBJECT-TYPE
	SYNTAX	 CounterBasedGauge64
	MAX-ACCESS read-only
	STATUS current
	DESCRIPTION "NetObject Count, Dynamic"

	::={plsdDynamicNoCount 1}

plsdDynamicNoCountMax	OBJECT-TYPE
	SYNTAX	 CounterBasedGauge64
	MAX-ACCESS read-only
	STATUS current
	DESCRIPTION "NetObject Count, Dynamic"

	::={plsdDynamicNoCount 3}

plsdDynamicNoCountLevelTable OBJECT-TYPE
	SYNTAX      SEQUENCE OF PlsdDynamicNoCountLevelEntry
	MAX-ACCESS  not-accessible
	STATUS      current
	DESCRIPTION
	"Table for plsdDynamicNoCount"
	::={plsdDynamicNoCount 4}

plsdDynamicNoCountLevelEntry OBJECT-TYPE
	SYNTAX      PlsdDynamicNoCountLevelEntry
	MAX-ACCESS  not-accessible
	STATUS      current
	DESCRIPTION
	"Table entry for plsdDynamicNoCount"
	INDEX { plsdDynamicNoCountLevelName }
	::={plsdDynamicNoCountLevelTable 1}

PlsdDynamicNoCountLevelEntry ::=
	SEQUENCE {
		plsdDynamicNoCountLevelName	DisplayString,
		plsdDynamicNoCountLevelVal	CounterBasedGauge64,
		plsdDynamicNoCountLevelMax	CounterBasedGauge64
	}

plsdDynamicNoCountLevelName OBJECT-TYPE
	SYNTAX      DisplayString
	MAX-ACCESS  not-accessible
	STATUS      current
	DESCRIPTION
	"Table entry display string for plsdDynamicNoCount"
	::={plsdDynamicNoCountLevelEntry 1}

plsdDynamicNoCountLevelVal OBJECT-TYPE
	SYNTAX	 CounterBasedGauge64
	MAX-ACCESS  read-only
	STATUS      current
	DESCRIPTION
	"Table entry attribute for plsdDynamicNoCount"
	::={plsdDynamicNoCountLevelEntry 2}

plsdDynamicNoCountLevelMax OBJECT-TYPE
	SYNTAX	 CounterBasedGauge64
	MAX-ACCESS  read-only
	STATUS      current
	DESCRIPTION
	"Table entry attribute for plsdDynamicNoCount"
	::={plsdDynamicNoCountLevelEntry 4}


plsdThresholdBytesIn	OBJECT IDENTIFIER ::={plsd 66}

plsdThresholdBytesInVal	OBJECT-TYPE
	SYNTAX	 Counter64
	MAX-ACCESS read-only
	STATUS current
	DESCRIPTION "Threshold filtered, Bytes In"

	::={plsdThresholdBytesIn 1}

plsdThresholdBytesInMom	OBJECT-TYPE
	SYNTAX	 CounterBasedGauge64
	MAX-ACCESS read-only
	STATUS current
	DESCRIPTION "Threshold filtered, Bytes In"

	::={plsdThresholdBytesIn 2}

plsdThresholdBytesInMax	OBJECT-TYPE
	SYNTAX	 CounterBasedGauge64
	MAX-ACCESS read-only
	STATUS current
	DESCRIPTION "Threshold filtered, Bytes In"

	::={plsdThresholdBytesIn 3}

plsdThresholdBytesInLevelTable OBJECT-TYPE
	SYNTAX      SEQUENCE OF PlsdThresholdBytesInLevelEntry
	MAX-ACCESS  not-accessible
	STATUS      current
	DESCRIPTION
	"Table for plsdThresholdBytesIn"
	::={plsdThresholdBytesIn 4}

plsdThresholdBytesInLevelEntry OBJECT-TYPE
	SYNTAX      PlsdThresholdBytesInLevelEntry
	MAX-ACCESS  not-accessible
	STATUS      current
	DESCRIPTION
	"Table entry for plsdThresholdBytesIn"
	INDEX { plsdThresholdBytesInLevelName }
	::={plsdThresholdBytesInLevelTable 1}

PlsdThresholdBytesInLevelEntry ::=
	SEQUENCE {
		plsdThresholdBytesInLevelName	DisplayString,
		plsdThresholdBytesInLevelVal	Counter64,
		plsdThresholdBytesInLevelMom	CounterBasedGauge64,
		plsdThresholdBytesInLevelMax	CounterBasedGauge64
	}

plsdThresholdBytesInLevelName OBJECT-TYPE
	SYNTAX      DisplayString
	MAX-ACCESS  not-accessible
	STATUS      current
	DESCRIPTION
	"Table entry display string for plsdThresholdBytesIn"
	::={plsdThresholdBytesInLevelEntry 1}

plsdThresholdBytesInLevelVal OBJECT-TYPE
	SYNTAX	 Counter64
	MAX-ACCESS  read-only
	STATUS      current
	DESCRIPTION
	"Table entry attribute for plsdThresholdBytesIn"
	::={plsdThresholdBytesInLevelEntry 2}

plsdThresholdBytesInLevelMom OBJECT-TYPE
	SYNTAX	 CounterBasedGauge64
	MAX-ACCESS  read-only
	STATUS      current
	DESCRIPTION
	"Table entry attribute for plsdThresholdBytesIn"
	::={plsdThresholdBytesInLevelEntry 3}

plsdThresholdBytesInLevelMax OBJECT-TYPE
	SYNTAX	 CounterBasedGauge64
	MAX-ACCESS  read-only
	STATUS      current
	DESCRIPTION
	"Table entry attribute for plsdThresholdBytesIn"
	::={plsdThresholdBytesInLevelEntry 4}


plsdThresholdBytesOut	OBJECT IDENTIFIER ::={plsd 67}

plsdThresholdBytesOutVal	OBJECT-TYPE
	SYNTAX	 Counter64
	MAX-ACCESS read-only
	STATUS current
	DESCRIPTION "Threshold filtered, Bytes Out"

	::={plsdThresholdBytesOut 1}

plsdThresholdBytesOutMom	OBJECT-TYPE
	SYNTAX	 CounterBasedGauge64
	MAX-ACCESS read-only
	STATUS current
	DESCRIPTION "Threshold filtered, Bytes Out"

	::={plsdThresholdBytesOut 2}

plsdThresholdBytesOutMax	OBJECT-TYPE
	SYNTAX	 CounterBasedGauge64
	MAX-ACCESS read-only
	STATUS current
	DESCRIPTION "Threshold filtered, Bytes Out"

	::={plsdThresholdBytesOut 3}

plsdThresholdBytesOutLevelTable OBJECT-TYPE
	SYNTAX      SEQUENCE OF PlsdThresholdBytesOutLevelEntry
	MAX-ACCESS  not-accessible
	STATUS      current
	DESCRIPTION
	"Table for plsdThresholdBytesOut"
	::={plsdThresholdBytesOut 4}

plsdThresholdBytesOutLevelEntry OBJECT-TYPE
	SYNTAX      PlsdThresholdBytesOutLevelEntry
	MAX-ACCESS  not-accessible
	STATUS      current
	DESCRIPTION
	"Table entry for plsdThresholdBytesOut"
	INDEX { plsdThresholdBytesOutLevelName }
	::={plsdThresholdBytesOutLevelTable 1}

PlsdThresholdBytesOutLevelEntry ::=
	SEQUENCE {
		plsdThresholdBytesOutLevelName	DisplayString,
		plsdThresholdBytesOutLevelVal	Counter64,
		plsdThresholdBytesOutLevelMom	CounterBasedGauge64,
		plsdThresholdBytesOutLevelMax	CounterBasedGauge64
	}

plsdThresholdBytesOutLevelName OBJECT-TYPE
	SYNTAX      DisplayString
	MAX-ACCESS  not-accessible
	STATUS      current
	DESCRIPTION
	"Table entry display string for plsdThresholdBytesOut"
	::={plsdThresholdBytesOutLevelEntry 1}

plsdThresholdBytesOutLevelVal OBJECT-TYPE
	SYNTAX	 Counter64
	MAX-ACCESS  read-only
	STATUS      current
	DESCRIPTION
	"Table entry attribute for plsdThresholdBytesOut"
	::={plsdThresholdBytesOutLevelEntry 2}

plsdThresholdBytesOutLevelMom OBJECT-TYPE
	SYNTAX	 CounterBasedGauge64
	MAX-ACCESS  read-only
	STATUS      current
	DESCRIPTION
	"Table entry attribute for plsdThresholdBytesOut"
	::={plsdThresholdBytesOutLevelEntry 3}

plsdThresholdBytesOutLevelMax OBJECT-TYPE
	SYNTAX	 CounterBasedGauge64
	MAX-ACCESS  read-only
	STATUS      current
	DESCRIPTION
	"Table entry attribute for plsdThresholdBytesOut"
	::={plsdThresholdBytesOutLevelEntry 4}


plsdBytesUnAccountedInNoRules	OBJECT IDENTIFIER ::={plsd 68}

plsdBytesUnAccountedInNoRulesVal	OBJECT-TYPE
	SYNTAX	 Counter64
	MAX-ACCESS read-only
	STATUS current
	DESCRIPTION "Connection Bytes Unaccounted In, No Matching Rules"

	::={plsdBytesUnAccountedInNoRules 1}

plsdBytesUnAccountedInNoRulesMom	OBJECT-TYPE
	SYNTAX	 CounterBasedGauge64
	MAX-ACCESS read-only
	STATUS current
	DESCRIPTION "Connection Bytes Unaccounted In, No Matching Rules"

	::={plsdBytesUnAccountedInNoRules 2}

plsdBytesUnAccountedInNoRulesMax	OBJECT-TYPE
	SYNTAX	 CounterBasedGauge64
	MAX-ACCESS read-only
	STATUS current
	DESCRIPTION "Connection Bytes Unaccounted In, No Matching Rules"

	::={plsdBytesUnAccountedInNoRules 3}

plsdBytesUnAccountedInNoRulesLevelTable OBJECT-TYPE
	SYNTAX      SEQUENCE OF PlsdBytesUnAccountedInNoRulesLevelEntry
	MAX-ACCESS  not-accessible
	STATUS      current
	DESCRIPTION
	"Table for plsdBytesUnAccountedInNoRules"
	::={plsdBytesUnAccountedInNoRules 4}

plsdBytesUnAccountedInNoRulesLevelEntry OBJECT-TYPE
	SYNTAX      PlsdBytesUnAccountedInNoRulesLevelEntry
	MAX-ACCESS  not-accessible
	STATUS      current
	DESCRIPTION
	"Table entry for plsdBytesUnAccountedInNoRules"
	INDEX { plsdBytesUnAccountedInNoRulesLevelName }
	::={plsdBytesUnAccountedInNoRulesLevelTable 1}

PlsdBytesUnAccountedInNoRulesLevelEntry ::=
	SEQUENCE {
		plsdBytesUnAccountedInNoRulesLevelName	DisplayString,
		plsdBytesUnAccountedInNoRulesLevelVal	Counter64,
		plsdBytesUnAccountedInNoRulesLevelMom	CounterBasedGauge64,
		plsdBytesUnAccountedInNoRulesLevelMax	CounterBasedGauge64
	}

plsdBytesUnAccountedInNoRulesLevelName OBJECT-TYPE
	SYNTAX      DisplayString
	MAX-ACCESS  not-accessible
	STATUS      current
	DESCRIPTION
	"Table entry display string for plsdBytesUnAccountedInNoRules"
	::={plsdBytesUnAccountedInNoRulesLevelEntry 1}

plsdBytesUnAccountedInNoRulesLevelVal OBJECT-TYPE
	SYNTAX	 Counter64
	MAX-ACCESS  read-only
	STATUS      current
	DESCRIPTION
	"Table entry attribute for plsdBytesUnAccountedInNoRules"
	::={plsdBytesUnAccountedInNoRulesLevelEntry 2}

plsdBytesUnAccountedInNoRulesLevelMom OBJECT-TYPE
	SYNTAX	 CounterBasedGauge64
	MAX-ACCESS  read-only
	STATUS      current
	DESCRIPTION
	"Table entry attribute for plsdBytesUnAccountedInNoRules"
	::={plsdBytesUnAccountedInNoRulesLevelEntry 3}

plsdBytesUnAccountedInNoRulesLevelMax OBJECT-TYPE
	SYNTAX	 CounterBasedGauge64
	MAX-ACCESS  read-only
	STATUS      current
	DESCRIPTION
	"Table entry attribute for plsdBytesUnAccountedInNoRules"
	::={plsdBytesUnAccountedInNoRulesLevelEntry 4}


plsdBytesUnAccountedOutNoRules	OBJECT IDENTIFIER ::={plsd 69}

plsdBytesUnAccountedOutNoRulesVal	OBJECT-TYPE
	SYNTAX	 Counter64
	MAX-ACCESS read-only
	STATUS current
	DESCRIPTION "Connection Bytes Unaccounted Out, No Matching Rules"

	::={plsdBytesUnAccountedOutNoRules 1}

plsdBytesUnAccountedOutNoRulesMom	OBJECT-TYPE
	SYNTAX	 CounterBasedGauge64
	MAX-ACCESS read-only
	STATUS current
	DESCRIPTION "Connection Bytes Unaccounted Out, No Matching Rules"

	::={plsdBytesUnAccountedOutNoRules 2}

plsdBytesUnAccountedOutNoRulesMax	OBJECT-TYPE
	SYNTAX	 CounterBasedGauge64
	MAX-ACCESS read-only
	STATUS current
	DESCRIPTION "Connection Bytes Unaccounted Out, No Matching Rules"

	::={plsdBytesUnAccountedOutNoRules 3}

plsdBytesUnAccountedOutNoRulesLevelTable OBJECT-TYPE
	SYNTAX      SEQUENCE OF PlsdBytesUnAccountedOutNoRulesLevelEntry
	MAX-ACCESS  not-accessible
	STATUS      current
	DESCRIPTION
	"Table for plsdBytesUnAccountedOutNoRules"
	::={plsdBytesUnAccountedOutNoRules 4}

plsdBytesUnAccountedOutNoRulesLevelEntry OBJECT-TYPE
	SYNTAX      PlsdBytesUnAccountedOutNoRulesLevelEntry
	MAX-ACCESS  not-accessible
	STATUS      current
	DESCRIPTION
	"Table entry for plsdBytesUnAccountedOutNoRules"
	INDEX { plsdBytesUnAccountedOutNoRulesLevelName }
	::={plsdBytesUnAccountedOutNoRulesLevelTable 1}

PlsdBytesUnAccountedOutNoRulesLevelEntry ::=
	SEQUENCE {
		plsdBytesUnAccountedOutNoRulesLevelName	DisplayString,
		plsdBytesUnAccountedOutNoRulesLevelVal	Counter64,
		plsdBytesUnAccountedOutNoRulesLevelMom	CounterBasedGauge64,
		plsdBytesUnAccountedOutNoRulesLevelMax	CounterBasedGauge64
	}

plsdBytesUnAccountedOutNoRulesLevelName OBJECT-TYPE
	SYNTAX      DisplayString
	MAX-ACCESS  not-accessible
	STATUS      current
	DESCRIPTION
	"Table entry display string for plsdBytesUnAccountedOutNoRules"
	::={plsdBytesUnAccountedOutNoRulesLevelEntry 1}

plsdBytesUnAccountedOutNoRulesLevelVal OBJECT-TYPE
	SYNTAX	 Counter64
	MAX-ACCESS  read-only
	STATUS      current
	DESCRIPTION
	"Table entry attribute for plsdBytesUnAccountedOutNoRules"
	::={plsdBytesUnAccountedOutNoRulesLevelEntry 2}

plsdBytesUnAccountedOutNoRulesLevelMom OBJECT-TYPE
	SYNTAX	 CounterBasedGauge64
	MAX-ACCESS  read-only
	STATUS      current
	DESCRIPTION
	"Table entry attribute for plsdBytesUnAccountedOutNoRules"
	::={plsdBytesUnAccountedOutNoRulesLevelEntry 3}

plsdBytesUnAccountedOutNoRulesLevelMax OBJECT-TYPE
	SYNTAX	 CounterBasedGauge64
	MAX-ACCESS  read-only
	STATUS      current
	DESCRIPTION
	"Table entry attribute for plsdBytesUnAccountedOutNoRules"
	::={plsdBytesUnAccountedOutNoRulesLevelEntry 4}


plsdUpdateBatchProcessTime	OBJECT IDENTIFIER ::={plsd 70}

plsdUpdateBatchProcessTimeVal	OBJECT-TYPE
	SYNTAX	 TimeTicks
	MAX-ACCESS read-only
	STATUS current
	DESCRIPTION "Connection update batch process time"

	::={plsdUpdateBatchProcessTime 1}

plsdUpdateBatchProcessTimeLevelTable OBJECT-TYPE
	SYNTAX      SEQUENCE OF PlsdUpdateBatchProcessTimeLevelEntry
	MAX-ACCESS  not-accessible
	STATUS      current
	DESCRIPTION
	"Table for plsdUpdateBatchProcessTime"
	::={plsdUpdateBatchProcessTime 2}

plsdUpdateBatchProcessTimeLevelEntry OBJECT-TYPE
	SYNTAX      PlsdUpdateBatchProcessTimeLevelEntry
	MAX-ACCESS  not-accessible
	STATUS      current
	DESCRIPTION
	"Table entry for plsdUpdateBatchProcessTime"
	INDEX { plsdUpdateBatchProcessTimeLevelName }
	::={plsdUpdateBatchProcessTimeLevelTable 1}

PlsdUpdateBatchProcessTimeLevelEntry ::=
	SEQUENCE {
		plsdUpdateBatchProcessTimeLevelName	DisplayString,
		plsdUpdateBatchProcessTimeLevelVal	TimeTicks
	}

plsdUpdateBatchProcessTimeLevelName OBJECT-TYPE
	SYNTAX      DisplayString
	MAX-ACCESS  not-accessible
	STATUS      current
	DESCRIPTION
	"Table entry display string for plsdUpdateBatchProcessTime"
	::={plsdUpdateBatchProcessTimeLevelEntry 1}

plsdUpdateBatchProcessTimeLevelVal OBJECT-TYPE
	SYNTAX	 TimeTicks
	MAX-ACCESS  read-only
	STATUS      current
	DESCRIPTION
	"Table entry attribute for plsdUpdateBatchProcessTime"
	::={plsdUpdateBatchProcessTimeLevelEntry 2}


plsdCachedDatasets	OBJECT IDENTIFIER ::={plsd 71}

plsdCachedDatasetsVal	OBJECT-TYPE
	SYNTAX	 CounterBasedGauge64
	MAX-ACCESS read-only
	STATUS current
	DESCRIPTION "Cached datasets"

	::={plsdCachedDatasets 1}

plsdCachedDatasetsMax	OBJECT-TYPE
	SYNTAX	 CounterBasedGauge64
	MAX-ACCESS read-only
	STATUS current
	DESCRIPTION "Cached datasets"

	::={plsdCachedDatasets 3}

plsdCachedDatasetsLevelTable OBJECT-TYPE
	SYNTAX      SEQUENCE OF PlsdCachedDatasetsLevelEntry
	MAX-ACCESS  not-accessible
	STATUS      current
	DESCRIPTION
	"Table for plsdCachedDatasets"
	::={plsdCachedDatasets 4}

plsdCachedDatasetsLevelEntry OBJECT-TYPE
	SYNTAX      PlsdCachedDatasetsLevelEntry
	MAX-ACCESS  not-accessible
	STATUS      current
	DESCRIPTION
	"Table entry for plsdCachedDatasets"
	INDEX { plsdCachedDatasetsLevelName }
	::={plsdCachedDatasetsLevelTable 1}

PlsdCachedDatasetsLevelEntry ::=
	SEQUENCE {
		plsdCachedDatasetsLevelName	DisplayString,
		plsdCachedDatasetsLevelVal	CounterBasedGauge64,
		plsdCachedDatasetsLevelMax	CounterBasedGauge64
	}

plsdCachedDatasetsLevelName OBJECT-TYPE
	SYNTAX      DisplayString
	MAX-ACCESS  not-accessible
	STATUS      current
	DESCRIPTION
	"Table entry display string for plsdCachedDatasets"
	::={plsdCachedDatasetsLevelEntry 1}

plsdCachedDatasetsLevelVal OBJECT-TYPE
	SYNTAX	 CounterBasedGauge64
	MAX-ACCESS  read-only
	STATUS      current
	DESCRIPTION
	"Table entry attribute for plsdCachedDatasets"
	::={plsdCachedDatasetsLevelEntry 2}

plsdCachedDatasetsLevelMax OBJECT-TYPE
	SYNTAX	 CounterBasedGauge64
	MAX-ACCESS  read-only
	STATUS      current
	DESCRIPTION
	"Table entry attribute for plsdCachedDatasets"
	::={plsdCachedDatasetsLevelEntry 4}


plsdHostStatsVertica	OBJECT IDENTIFIER ::={plsd 72}

plsdHostStatsVerticaVal	OBJECT-TYPE
	SYNTAX	 Counter64
	MAX-ACCESS read-only
	STATUS obsolete
	DESCRIPTION "Host stats: Number of bytes sent to the local ZMQ buffer"

	::={plsdHostStatsVertica 1}

plsdHostStatsVerticaMom	OBJECT-TYPE
	SYNTAX	 CounterBasedGauge64
	MAX-ACCESS read-only
	STATUS obsolete
	DESCRIPTION "Host stats: Number of bytes sent to the local ZMQ buffer"

	::={plsdHostStatsVertica 2}

plsdHostStatsVerticaMax	OBJECT-TYPE
	SYNTAX	 CounterBasedGauge64
	MAX-ACCESS read-only
	STATUS obsolete
	DESCRIPTION "Host stats: Number of bytes sent to the local ZMQ buffer"

	::={plsdHostStatsVertica 3}

plsdHostStatsVerticaLevelTable OBJECT-TYPE
	SYNTAX      SEQUENCE OF PlsdHostStatsVerticaLevelEntry
	MAX-ACCESS  not-accessible
	STATUS      current
	DESCRIPTION
	"Table for plsdHostStatsVertica"
	::={plsdHostStatsVertica 4}

plsdHostStatsVerticaLevelEntry OBJECT-TYPE
	SYNTAX      PlsdHostStatsVerticaLevelEntry
	MAX-ACCESS  not-accessible
	STATUS      current
	DESCRIPTION
	"Table entry for plsdHostStatsVertica"
	INDEX { plsdHostStatsVerticaLevelName }
	::={plsdHostStatsVerticaLevelTable 1}

PlsdHostStatsVerticaLevelEntry ::=
	SEQUENCE {
		plsdHostStatsVerticaLevelName	DisplayString,
		plsdHostStatsVerticaLevelVal	Counter64,
		plsdHostStatsVerticaLevelMom	CounterBasedGauge64,
		plsdHostStatsVerticaLevelMax	CounterBasedGauge64
	}

plsdHostStatsVerticaLevelName OBJECT-TYPE
	SYNTAX      DisplayString
	MAX-ACCESS  not-accessible
	STATUS      current
	DESCRIPTION
	"Table entry display string for plsdHostStatsVertica"
	::={plsdHostStatsVerticaLevelEntry 1}

plsdHostStatsVerticaLevelVal OBJECT-TYPE
	SYNTAX	 Counter64
	MAX-ACCESS  read-only
	STATUS      current
	DESCRIPTION
	"Table entry attribute for plsdHostStatsVertica"
	::={plsdHostStatsVerticaLevelEntry 2}

plsdHostStatsVerticaLevelMom OBJECT-TYPE
	SYNTAX	 CounterBasedGauge64
	MAX-ACCESS  read-only
	STATUS      current
	DESCRIPTION
	"Table entry attribute for plsdHostStatsVertica"
	::={plsdHostStatsVerticaLevelEntry 3}

plsdHostStatsVerticaLevelMax OBJECT-TYPE
	SYNTAX	 CounterBasedGauge64
	MAX-ACCESS  read-only
	STATUS      current
	DESCRIPTION
	"Table entry attribute for plsdHostStatsVertica"
	::={plsdHostStatsVerticaLevelEntry 4}


plsdHostStatsFoundSubscriber	OBJECT IDENTIFIER ::={plsd 73}

plsdHostStatsFoundSubscriberVal	OBJECT-TYPE
	SYNTAX	 Counter64
	MAX-ACCESS read-only
	STATUS obsolete
	DESCRIPTION "Host stats: Number of times subscriber ID has been found"

	::={plsdHostStatsFoundSubscriber 1}

plsdHostStatsFoundSubscriberMom	OBJECT-TYPE
	SYNTAX	 CounterBasedGauge64
	MAX-ACCESS read-only
	STATUS obsolete
	DESCRIPTION "Host stats: Number of times subscriber ID has been found"

	::={plsdHostStatsFoundSubscriber 2}

plsdHostStatsFoundSubscriberMax	OBJECT-TYPE
	SYNTAX	 CounterBasedGauge64
	MAX-ACCESS read-only
	STATUS obsolete
	DESCRIPTION "Host stats: Number of times subscriber ID has been found"

	::={plsdHostStatsFoundSubscriber 3}

plsdHostStatsFoundSubscriberLevelTable OBJECT-TYPE
	SYNTAX      SEQUENCE OF PlsdHostStatsFoundSubscriberLevelEntry
	MAX-ACCESS  not-accessible
	STATUS      current
	DESCRIPTION
	"Table for plsdHostStatsFoundSubscriber"
	::={plsdHostStatsFoundSubscriber 4}

plsdHostStatsFoundSubscriberLevelEntry OBJECT-TYPE
	SYNTAX      PlsdHostStatsFoundSubscriberLevelEntry
	MAX-ACCESS  not-accessible
	STATUS      current
	DESCRIPTION
	"Table entry for plsdHostStatsFoundSubscriber"
	INDEX { plsdHostStatsFoundSubscriberLevelName }
	::={plsdHostStatsFoundSubscriberLevelTable 1}

PlsdHostStatsFoundSubscriberLevelEntry ::=
	SEQUENCE {
		plsdHostStatsFoundSubscriberLevelName	DisplayString,
		plsdHostStatsFoundSubscriberLevelVal	Counter64,
		plsdHostStatsFoundSubscriberLevelMom	CounterBasedGauge64,
		plsdHostStatsFoundSubscriberLevelMax	CounterBasedGauge64
	}

plsdHostStatsFoundSubscriberLevelName OBJECT-TYPE
	SYNTAX      DisplayString
	MAX-ACCESS  not-accessible
	STATUS      current
	DESCRIPTION
	"Table entry display string for plsdHostStatsFoundSubscriber"
	::={plsdHostStatsFoundSubscriberLevelEntry 1}

plsdHostStatsFoundSubscriberLevelVal OBJECT-TYPE
	SYNTAX	 Counter64
	MAX-ACCESS  read-only
	STATUS      current
	DESCRIPTION
	"Table entry attribute for plsdHostStatsFoundSubscriber"
	::={plsdHostStatsFoundSubscriberLevelEntry 2}

plsdHostStatsFoundSubscriberLevelMom OBJECT-TYPE
	SYNTAX	 CounterBasedGauge64
	MAX-ACCESS  read-only
	STATUS      current
	DESCRIPTION
	"Table entry attribute for plsdHostStatsFoundSubscriber"
	::={plsdHostStatsFoundSubscriberLevelEntry 3}

plsdHostStatsFoundSubscriberLevelMax OBJECT-TYPE
	SYNTAX	 CounterBasedGauge64
	MAX-ACCESS  read-only
	STATUS      current
	DESCRIPTION
	"Table entry attribute for plsdHostStatsFoundSubscriber"
	::={plsdHostStatsFoundSubscriberLevelEntry 4}


plsdHostStatsFoundDevice	OBJECT IDENTIFIER ::={plsd 74}

plsdHostStatsFoundDeviceVal	OBJECT-TYPE
	SYNTAX	 Counter64
	MAX-ACCESS read-only
	STATUS obsolete
	DESCRIPTION "Host stats: Number of times device has been found"

	::={plsdHostStatsFoundDevice 1}

plsdHostStatsFoundDeviceMom	OBJECT-TYPE
	SYNTAX	 CounterBasedGauge64
	MAX-ACCESS read-only
	STATUS obsolete
	DESCRIPTION "Host stats: Number of times device has been found"

	::={plsdHostStatsFoundDevice 2}

plsdHostStatsFoundDeviceMax	OBJECT-TYPE
	SYNTAX	 CounterBasedGauge64
	MAX-ACCESS read-only
	STATUS obsolete
	DESCRIPTION "Host stats: Number of times device has been found"

	::={plsdHostStatsFoundDevice 3}

plsdHostStatsFoundDeviceLevelTable OBJECT-TYPE
	SYNTAX      SEQUENCE OF PlsdHostStatsFoundDeviceLevelEntry
	MAX-ACCESS  not-accessible
	STATUS      current
	DESCRIPTION
	"Table for plsdHostStatsFoundDevice"
	::={plsdHostStatsFoundDevice 4}

plsdHostStatsFoundDeviceLevelEntry OBJECT-TYPE
	SYNTAX      PlsdHostStatsFoundDeviceLevelEntry
	MAX-ACCESS  not-accessible
	STATUS      current
	DESCRIPTION
	"Table entry for plsdHostStatsFoundDevice"
	INDEX { plsdHostStatsFoundDeviceLevelName }
	::={plsdHostStatsFoundDeviceLevelTable 1}

PlsdHostStatsFoundDeviceLevelEntry ::=
	SEQUENCE {
		plsdHostStatsFoundDeviceLevelName	DisplayString,
		plsdHostStatsFoundDeviceLevelVal	Counter64,
		plsdHostStatsFoundDeviceLevelMom	CounterBasedGauge64,
		plsdHostStatsFoundDeviceLevelMax	CounterBasedGauge64
	}

plsdHostStatsFoundDeviceLevelName OBJECT-TYPE
	SYNTAX      DisplayString
	MAX-ACCESS  not-accessible
	STATUS      current
	DESCRIPTION
	"Table entry display string for plsdHostStatsFoundDevice"
	::={plsdHostStatsFoundDeviceLevelEntry 1}

plsdHostStatsFoundDeviceLevelVal OBJECT-TYPE
	SYNTAX	 Counter64
	MAX-ACCESS  read-only
	STATUS      current
	DESCRIPTION
	"Table entry attribute for plsdHostStatsFoundDevice"
	::={plsdHostStatsFoundDeviceLevelEntry 2}

plsdHostStatsFoundDeviceLevelMom OBJECT-TYPE
	SYNTAX	 CounterBasedGauge64
	MAX-ACCESS  read-only
	STATUS      current
	DESCRIPTION
	"Table entry attribute for plsdHostStatsFoundDevice"
	::={plsdHostStatsFoundDeviceLevelEntry 3}

plsdHostStatsFoundDeviceLevelMax OBJECT-TYPE
	SYNTAX	 CounterBasedGauge64
	MAX-ACCESS  read-only
	STATUS      current
	DESCRIPTION
	"Table entry attribute for plsdHostStatsFoundDevice"
	::={plsdHostStatsFoundDeviceLevelEntry 4}


plsdHostStatsFoundLocation	OBJECT IDENTIFIER ::={plsd 75}

plsdHostStatsFoundLocationVal	OBJECT-TYPE
	SYNTAX	 Counter64
	MAX-ACCESS read-only
	STATUS obsolete
	DESCRIPTION "Host stats: Number of times location has been found"

	::={plsdHostStatsFoundLocation 1}

plsdHostStatsFoundLocationMom	OBJECT-TYPE
	SYNTAX	 CounterBasedGauge64
	MAX-ACCESS read-only
	STATUS obsolete
	DESCRIPTION "Host stats: Number of times location has been found"

	::={plsdHostStatsFoundLocation 2}

plsdHostStatsFoundLocationMax	OBJECT-TYPE
	SYNTAX	 CounterBasedGauge64
	MAX-ACCESS read-only
	STATUS obsolete
	DESCRIPTION "Host stats: Number of times location has been found"

	::={plsdHostStatsFoundLocation 3}

plsdHostStatsFoundLocationLevelTable OBJECT-TYPE
	SYNTAX      SEQUENCE OF PlsdHostStatsFoundLocationLevelEntry
	MAX-ACCESS  not-accessible
	STATUS      current
	DESCRIPTION
	"Table for plsdHostStatsFoundLocation"
	::={plsdHostStatsFoundLocation 4}

plsdHostStatsFoundLocationLevelEntry OBJECT-TYPE
	SYNTAX      PlsdHostStatsFoundLocationLevelEntry
	MAX-ACCESS  not-accessible
	STATUS      current
	DESCRIPTION
	"Table entry for plsdHostStatsFoundLocation"
	INDEX { plsdHostStatsFoundLocationLevelName }
	::={plsdHostStatsFoundLocationLevelTable 1}

PlsdHostStatsFoundLocationLevelEntry ::=
	SEQUENCE {
		plsdHostStatsFoundLocationLevelName	DisplayString,
		plsdHostStatsFoundLocationLevelVal	Counter64,
		plsdHostStatsFoundLocationLevelMom	CounterBasedGauge64,
		plsdHostStatsFoundLocationLevelMax	CounterBasedGauge64
	}

plsdHostStatsFoundLocationLevelName OBJECT-TYPE
	SYNTAX      DisplayString
	MAX-ACCESS  not-accessible
	STATUS      current
	DESCRIPTION
	"Table entry display string for plsdHostStatsFoundLocation"
	::={plsdHostStatsFoundLocationLevelEntry 1}

plsdHostStatsFoundLocationLevelVal OBJECT-TYPE
	SYNTAX	 Counter64
	MAX-ACCESS  read-only
	STATUS      current
	DESCRIPTION
	"Table entry attribute for plsdHostStatsFoundLocation"
	::={plsdHostStatsFoundLocationLevelEntry 2}

plsdHostStatsFoundLocationLevelMom OBJECT-TYPE
	SYNTAX	 CounterBasedGauge64
	MAX-ACCESS  read-only
	STATUS      current
	DESCRIPTION
	"Table entry attribute for plsdHostStatsFoundLocation"
	::={plsdHostStatsFoundLocationLevelEntry 3}

plsdHostStatsFoundLocationLevelMax OBJECT-TYPE
	SYNTAX	 CounterBasedGauge64
	MAX-ACCESS  read-only
	STATUS      current
	DESCRIPTION
	"Table entry attribute for plsdHostStatsFoundLocation"
	::={plsdHostStatsFoundLocationLevelEntry 4}


plsdHostStatsFoundTier	OBJECT IDENTIFIER ::={plsd 76}

plsdHostStatsFoundTierVal	OBJECT-TYPE
	SYNTAX	 Counter64
	MAX-ACCESS read-only
	STATUS obsolete
	DESCRIPTION "Host stats: Number of times tier has been found"

	::={plsdHostStatsFoundTier 1}

plsdHostStatsFoundTierMom	OBJECT-TYPE
	SYNTAX	 CounterBasedGauge64
	MAX-ACCESS read-only
	STATUS obsolete
	DESCRIPTION "Host stats: Number of times tier has been found"

	::={plsdHostStatsFoundTier 2}

plsdHostStatsFoundTierMax	OBJECT-TYPE
	SYNTAX	 CounterBasedGauge64
	MAX-ACCESS read-only
	STATUS obsolete
	DESCRIPTION "Host stats: Number of times tier has been found"

	::={plsdHostStatsFoundTier 3}

plsdHostStatsFoundTierLevelTable OBJECT-TYPE
	SYNTAX      SEQUENCE OF PlsdHostStatsFoundTierLevelEntry
	MAX-ACCESS  not-accessible
	STATUS      current
	DESCRIPTION
	"Table for plsdHostStatsFoundTier"
	::={plsdHostStatsFoundTier 4}

plsdHostStatsFoundTierLevelEntry OBJECT-TYPE
	SYNTAX      PlsdHostStatsFoundTierLevelEntry
	MAX-ACCESS  not-accessible
	STATUS      current
	DESCRIPTION
	"Table entry for plsdHostStatsFoundTier"
	INDEX { plsdHostStatsFoundTierLevelName }
	::={plsdHostStatsFoundTierLevelTable 1}

PlsdHostStatsFoundTierLevelEntry ::=
	SEQUENCE {
		plsdHostStatsFoundTierLevelName	DisplayString,
		plsdHostStatsFoundTierLevelVal	Counter64,
		plsdHostStatsFoundTierLevelMom	CounterBasedGauge64,
		plsdHostStatsFoundTierLevelMax	CounterBasedGauge64
	}

plsdHostStatsFoundTierLevelName OBJECT-TYPE
	SYNTAX      DisplayString
	MAX-ACCESS  not-accessible
	STATUS      current
	DESCRIPTION
	"Table entry display string for plsdHostStatsFoundTier"
	::={plsdHostStatsFoundTierLevelEntry 1}

plsdHostStatsFoundTierLevelVal OBJECT-TYPE
	SYNTAX	 Counter64
	MAX-ACCESS  read-only
	STATUS      current
	DESCRIPTION
	"Table entry attribute for plsdHostStatsFoundTier"
	::={plsdHostStatsFoundTierLevelEntry 2}

plsdHostStatsFoundTierLevelMom OBJECT-TYPE
	SYNTAX	 CounterBasedGauge64
	MAX-ACCESS  read-only
	STATUS      current
	DESCRIPTION
	"Table entry attribute for plsdHostStatsFoundTier"
	::={plsdHostStatsFoundTierLevelEntry 3}

plsdHostStatsFoundTierLevelMax OBJECT-TYPE
	SYNTAX	 CounterBasedGauge64
	MAX-ACCESS  read-only
	STATUS      current
	DESCRIPTION
	"Table entry attribute for plsdHostStatsFoundTier"
	::={plsdHostStatsFoundTierLevelEntry 4}


plsdHostStatsSentRecords	OBJECT IDENTIFIER ::={plsd 77}

plsdHostStatsSentRecordsVal	OBJECT-TYPE
	SYNTAX	 Counter64
	MAX-ACCESS read-only
	STATUS obsolete
	DESCRIPTION "Host stats: Number of records sent to Vertica"

	::={plsdHostStatsSentRecords 1}

plsdHostStatsSentRecordsMom	OBJECT-TYPE
	SYNTAX	 CounterBasedGauge64
	MAX-ACCESS read-only
	STATUS obsolete
	DESCRIPTION "Host stats: Number of records sent to Vertica"

	::={plsdHostStatsSentRecords 2}

plsdHostStatsSentRecordsMax	OBJECT-TYPE
	SYNTAX	 CounterBasedGauge64
	MAX-ACCESS read-only
	STATUS obsolete
	DESCRIPTION "Host stats: Number of records sent to Vertica"

	::={plsdHostStatsSentRecords 3}

plsdHostStatsSentRecordsLevelTable OBJECT-TYPE
	SYNTAX      SEQUENCE OF PlsdHostStatsSentRecordsLevelEntry
	MAX-ACCESS  not-accessible
	STATUS      current
	DESCRIPTION
	"Table for plsdHostStatsSentRecords"
	::={plsdHostStatsSentRecords 4}

plsdHostStatsSentRecordsLevelEntry OBJECT-TYPE
	SYNTAX      PlsdHostStatsSentRecordsLevelEntry
	MAX-ACCESS  not-accessible
	STATUS      current
	DESCRIPTION
	"Table entry for plsdHostStatsSentRecords"
	INDEX { plsdHostStatsSentRecordsLevelName }
	::={plsdHostStatsSentRecordsLevelTable 1}

PlsdHostStatsSentRecordsLevelEntry ::=
	SEQUENCE {
		plsdHostStatsSentRecordsLevelName	DisplayString,
		plsdHostStatsSentRecordsLevelVal	Counter64,
		plsdHostStatsSentRecordsLevelMom	CounterBasedGauge64,
		plsdHostStatsSentRecordsLevelMax	CounterBasedGauge64
	}

plsdHostStatsSentRecordsLevelName OBJECT-TYPE
	SYNTAX      DisplayString
	MAX-ACCESS  not-accessible
	STATUS      current
	DESCRIPTION
	"Table entry display string for plsdHostStatsSentRecords"
	::={plsdHostStatsSentRecordsLevelEntry 1}

plsdHostStatsSentRecordsLevelVal OBJECT-TYPE
	SYNTAX	 Counter64
	MAX-ACCESS  read-only
	STATUS      current
	DESCRIPTION
	"Table entry attribute for plsdHostStatsSentRecords"
	::={plsdHostStatsSentRecordsLevelEntry 2}

plsdHostStatsSentRecordsLevelMom OBJECT-TYPE
	SYNTAX	 CounterBasedGauge64
	MAX-ACCESS  read-only
	STATUS      current
	DESCRIPTION
	"Table entry attribute for plsdHostStatsSentRecords"
	::={plsdHostStatsSentRecordsLevelEntry 3}

plsdHostStatsSentRecordsLevelMax OBJECT-TYPE
	SYNTAX	 CounterBasedGauge64
	MAX-ACCESS  read-only
	STATUS      current
	DESCRIPTION
	"Table entry attribute for plsdHostStatsSentRecords"
	::={plsdHostStatsSentRecordsLevelEntry 4}


plsdHostStatsReceivedRecords	OBJECT IDENTIFIER ::={plsd 78}

plsdHostStatsReceivedRecordsVal	OBJECT-TYPE
	SYNTAX	 Counter64
	MAX-ACCESS read-only
	STATUS obsolete
	DESCRIPTION "Host stats: Number of records received from PLD"

	::={plsdHostStatsReceivedRecords 1}

plsdHostStatsReceivedRecordsMom	OBJECT-TYPE
	SYNTAX	 CounterBasedGauge64
	MAX-ACCESS read-only
	STATUS obsolete
	DESCRIPTION "Host stats: Number of records received from PLD"

	::={plsdHostStatsReceivedRecords 2}

plsdHostStatsReceivedRecordsMax	OBJECT-TYPE
	SYNTAX	 CounterBasedGauge64
	MAX-ACCESS read-only
	STATUS obsolete
	DESCRIPTION "Host stats: Number of records received from PLD"

	::={plsdHostStatsReceivedRecords 3}

plsdHostStatsReceivedRecordsLevelTable OBJECT-TYPE
	SYNTAX      SEQUENCE OF PlsdHostStatsReceivedRecordsLevelEntry
	MAX-ACCESS  not-accessible
	STATUS      current
	DESCRIPTION
	"Table for plsdHostStatsReceivedRecords"
	::={plsdHostStatsReceivedRecords 4}

plsdHostStatsReceivedRecordsLevelEntry OBJECT-TYPE
	SYNTAX      PlsdHostStatsReceivedRecordsLevelEntry
	MAX-ACCESS  not-accessible
	STATUS      current
	DESCRIPTION
	"Table entry for plsdHostStatsReceivedRecords"
	INDEX { plsdHostStatsReceivedRecordsLevelName }
	::={plsdHostStatsReceivedRecordsLevelTable 1}

PlsdHostStatsReceivedRecordsLevelEntry ::=
	SEQUENCE {
		plsdHostStatsReceivedRecordsLevelName	DisplayString,
		plsdHostStatsReceivedRecordsLevelVal	Counter64,
		plsdHostStatsReceivedRecordsLevelMom	CounterBasedGauge64,
		plsdHostStatsReceivedRecordsLevelMax	CounterBasedGauge64
	}

plsdHostStatsReceivedRecordsLevelName OBJECT-TYPE
	SYNTAX      DisplayString
	MAX-ACCESS  not-accessible
	STATUS      current
	DESCRIPTION
	"Table entry display string for plsdHostStatsReceivedRecords"
	::={plsdHostStatsReceivedRecordsLevelEntry 1}

plsdHostStatsReceivedRecordsLevelVal OBJECT-TYPE
	SYNTAX	 Counter64
	MAX-ACCESS  read-only
	STATUS      current
	DESCRIPTION
	"Table entry attribute for plsdHostStatsReceivedRecords"
	::={plsdHostStatsReceivedRecordsLevelEntry 2}

plsdHostStatsReceivedRecordsLevelMom OBJECT-TYPE
	SYNTAX	 CounterBasedGauge64
	MAX-ACCESS  read-only
	STATUS      current
	DESCRIPTION
	"Table entry attribute for plsdHostStatsReceivedRecords"
	::={plsdHostStatsReceivedRecordsLevelEntry 3}

plsdHostStatsReceivedRecordsLevelMax OBJECT-TYPE
	SYNTAX	 CounterBasedGauge64
	MAX-ACCESS  read-only
	STATUS      current
	DESCRIPTION
	"Table entry attribute for plsdHostStatsReceivedRecords"
	::={plsdHostStatsReceivedRecordsLevelEntry 4}


plsdHostStatsDumpsSkipped	OBJECT IDENTIFIER ::={plsd 79}

plsdHostStatsDumpsSkippedVal	OBJECT-TYPE
	SYNTAX	 CounterBasedGauge64
	MAX-ACCESS read-only
	STATUS obsolete
	DESCRIPTION "Host stats: Dumps skipped"

	::={plsdHostStatsDumpsSkipped 1}

plsdHostStatsDumpsSkippedMax	OBJECT-TYPE
	SYNTAX	 CounterBasedGauge64
	MAX-ACCESS read-only
	STATUS obsolete
	DESCRIPTION "Host stats: Dumps skipped"

	::={plsdHostStatsDumpsSkipped 3}

plsdHostStatsDumpsSkippedLevelTable OBJECT-TYPE
	SYNTAX      SEQUENCE OF PlsdHostStatsDumpsSkippedLevelEntry
	MAX-ACCESS  not-accessible
	STATUS      current
	DESCRIPTION
	"Table for plsdHostStatsDumpsSkipped"
	::={plsdHostStatsDumpsSkipped 4}

plsdHostStatsDumpsSkippedLevelEntry OBJECT-TYPE
	SYNTAX      PlsdHostStatsDumpsSkippedLevelEntry
	MAX-ACCESS  not-accessible
	STATUS      current
	DESCRIPTION
	"Table entry for plsdHostStatsDumpsSkipped"
	INDEX { plsdHostStatsDumpsSkippedLevelName }
	::={plsdHostStatsDumpsSkippedLevelTable 1}

PlsdHostStatsDumpsSkippedLevelEntry ::=
	SEQUENCE {
		plsdHostStatsDumpsSkippedLevelName	DisplayString,
		plsdHostStatsDumpsSkippedLevelVal	CounterBasedGauge64,
		plsdHostStatsDumpsSkippedLevelMax	CounterBasedGauge64
	}

plsdHostStatsDumpsSkippedLevelName OBJECT-TYPE
	SYNTAX      DisplayString
	MAX-ACCESS  not-accessible
	STATUS      current
	DESCRIPTION
	"Table entry display string for plsdHostStatsDumpsSkipped"
	::={plsdHostStatsDumpsSkippedLevelEntry 1}

plsdHostStatsDumpsSkippedLevelVal OBJECT-TYPE
	SYNTAX	 CounterBasedGauge64
	MAX-ACCESS  read-only
	STATUS      current
	DESCRIPTION
	"Table entry attribute for plsdHostStatsDumpsSkipped"
	::={plsdHostStatsDumpsSkippedLevelEntry 2}

plsdHostStatsDumpsSkippedLevelMax OBJECT-TYPE
	SYNTAX	 CounterBasedGauge64
	MAX-ACCESS  read-only
	STATUS      current
	DESCRIPTION
	"Table entry attribute for plsdHostStatsDumpsSkipped"
	::={plsdHostStatsDumpsSkippedLevelEntry 4}


plsdMaxValueDepth	OBJECT IDENTIFIER ::={plsd 80}

plsdMaxValueDepthVal	OBJECT-TYPE
	SYNTAX	 CounterBasedGauge64
	MAX-ACCESS read-only
	STATUS current
	DESCRIPTION "Values max depth"

	::={plsdMaxValueDepth 1}

plsdMaxValueDepthMax	OBJECT-TYPE
	SYNTAX	 CounterBasedGauge64
	MAX-ACCESS read-only
	STATUS current
	DESCRIPTION "Values max depth"

	::={plsdMaxValueDepth 3}

plsdMaxValueDepthLevelTable OBJECT-TYPE
	SYNTAX      SEQUENCE OF PlsdMaxValueDepthLevelEntry
	MAX-ACCESS  not-accessible
	STATUS      current
	DESCRIPTION
	"Table for plsdMaxValueDepth"
	::={plsdMaxValueDepth 4}

plsdMaxValueDepthLevelEntry OBJECT-TYPE
	SYNTAX      PlsdMaxValueDepthLevelEntry
	MAX-ACCESS  not-accessible
	STATUS      current
	DESCRIPTION
	"Table entry for plsdMaxValueDepth"
	INDEX { plsdMaxValueDepthLevelName }
	::={plsdMaxValueDepthLevelTable 1}

PlsdMaxValueDepthLevelEntry ::=
	SEQUENCE {
		plsdMaxValueDepthLevelName	DisplayString,
		plsdMaxValueDepthLevelVal	CounterBasedGauge64,
		plsdMaxValueDepthLevelMax	CounterBasedGauge64
	}

plsdMaxValueDepthLevelName OBJECT-TYPE
	SYNTAX      DisplayString
	MAX-ACCESS  not-accessible
	STATUS      current
	DESCRIPTION
	"Table entry display string for plsdMaxValueDepth"
	::={plsdMaxValueDepthLevelEntry 1}

plsdMaxValueDepthLevelVal OBJECT-TYPE
	SYNTAX	 CounterBasedGauge64
	MAX-ACCESS  read-only
	STATUS      current
	DESCRIPTION
	"Table entry attribute for plsdMaxValueDepth"
	::={plsdMaxValueDepthLevelEntry 2}

plsdMaxValueDepthLevelMax OBJECT-TYPE
	SYNTAX	 CounterBasedGauge64
	MAX-ACCESS  read-only
	STATUS      current
	DESCRIPTION
	"Table entry attribute for plsdMaxValueDepth"
	::={plsdMaxValueDepthLevelEntry 4}


plsdSesssionContextSchemas	OBJECT IDENTIFIER ::={plsd 81}

plsdSesssionContextSchemasVal	OBJECT-TYPE
	SYNTAX	 CounterBasedGauge64
	MAX-ACCESS read-only
	STATUS current
	DESCRIPTION "Session Context Schemas"

	::={plsdSesssionContextSchemas 1}

plsdSesssionContextSchemasMax	OBJECT-TYPE
	SYNTAX	 CounterBasedGauge64
	MAX-ACCESS read-only
	STATUS current
	DESCRIPTION "Session Context Schemas"

	::={plsdSesssionContextSchemas 3}

plsdSesssionContextSchemasLevelTable OBJECT-TYPE
	SYNTAX      SEQUENCE OF PlsdSesssionContextSchemasLevelEntry
	MAX-ACCESS  not-accessible
	STATUS      current
	DESCRIPTION
	"Table for plsdSesssionContextSchemas"
	::={plsdSesssionContextSchemas 4}

plsdSesssionContextSchemasLevelEntry OBJECT-TYPE
	SYNTAX      PlsdSesssionContextSchemasLevelEntry
	MAX-ACCESS  not-accessible
	STATUS      current
	DESCRIPTION
	"Table entry for plsdSesssionContextSchemas"
	INDEX { plsdSesssionContextSchemasLevelName }
	::={plsdSesssionContextSchemasLevelTable 1}

PlsdSesssionContextSchemasLevelEntry ::=
	SEQUENCE {
		plsdSesssionContextSchemasLevelName	DisplayString,
		plsdSesssionContextSchemasLevelVal	CounterBasedGauge64,
		plsdSesssionContextSchemasLevelMax	CounterBasedGauge64
	}

plsdSesssionContextSchemasLevelName OBJECT-TYPE
	SYNTAX      DisplayString
	MAX-ACCESS  not-accessible
	STATUS      current
	DESCRIPTION
	"Table entry display string for plsdSesssionContextSchemas"
	::={plsdSesssionContextSchemasLevelEntry 1}

plsdSesssionContextSchemasLevelVal OBJECT-TYPE
	SYNTAX	 CounterBasedGauge64
	MAX-ACCESS  read-only
	STATUS      current
	DESCRIPTION
	"Table entry attribute for plsdSesssionContextSchemas"
	::={plsdSesssionContextSchemasLevelEntry 2}

plsdSesssionContextSchemasLevelMax OBJECT-TYPE
	SYNTAX	 CounterBasedGauge64
	MAX-ACCESS  read-only
	STATUS      current
	DESCRIPTION
	"Table entry attribute for plsdSesssionContextSchemas"
	::={plsdSesssionContextSchemasLevelEntry 4}


plsdSesssionContextRows	OBJECT IDENTIFIER ::={plsd 82}

plsdSesssionContextRowsVal	OBJECT-TYPE
	SYNTAX	 CounterBasedGauge64
	MAX-ACCESS read-only
	STATUS current
	DESCRIPTION "Session Context Rows"

	::={plsdSesssionContextRows 1}

plsdSesssionContextRowsMax	OBJECT-TYPE
	SYNTAX	 CounterBasedGauge64
	MAX-ACCESS read-only
	STATUS current
	DESCRIPTION "Session Context Rows"

	::={plsdSesssionContextRows 3}

plsdSesssionContextRowsLevelTable OBJECT-TYPE
	SYNTAX      SEQUENCE OF PlsdSesssionContextRowsLevelEntry
	MAX-ACCESS  not-accessible
	STATUS      current
	DESCRIPTION
	"Table for plsdSesssionContextRows"
	::={plsdSesssionContextRows 4}

plsdSesssionContextRowsLevelEntry OBJECT-TYPE
	SYNTAX      PlsdSesssionContextRowsLevelEntry
	MAX-ACCESS  not-accessible
	STATUS      current
	DESCRIPTION
	"Table entry for plsdSesssionContextRows"
	INDEX { plsdSesssionContextRowsLevelName }
	::={plsdSesssionContextRowsLevelTable 1}

PlsdSesssionContextRowsLevelEntry ::=
	SEQUENCE {
		plsdSesssionContextRowsLevelName	DisplayString,
		plsdSesssionContextRowsLevelVal	CounterBasedGauge64,
		plsdSesssionContextRowsLevelMax	CounterBasedGauge64
	}

plsdSesssionContextRowsLevelName OBJECT-TYPE
	SYNTAX      DisplayString
	MAX-ACCESS  not-accessible
	STATUS      current
	DESCRIPTION
	"Table entry display string for plsdSesssionContextRows"
	::={plsdSesssionContextRowsLevelEntry 1}

plsdSesssionContextRowsLevelVal OBJECT-TYPE
	SYNTAX	 CounterBasedGauge64
	MAX-ACCESS  read-only
	STATUS      current
	DESCRIPTION
	"Table entry attribute for plsdSesssionContextRows"
	::={plsdSesssionContextRowsLevelEntry 2}

plsdSesssionContextRowsLevelMax OBJECT-TYPE
	SYNTAX	 CounterBasedGauge64
	MAX-ACCESS  read-only
	STATUS      current
	DESCRIPTION
	"Table entry attribute for plsdSesssionContextRows"
	::={plsdSesssionContextRowsLevelEntry 4}


plsdSesssionContextRowDrops	OBJECT IDENTIFIER ::={plsd 83}

plsdSesssionContextRowDropsVal	OBJECT-TYPE
	SYNTAX	 CounterBasedGauge64
	MAX-ACCESS read-only
	STATUS current
	DESCRIPTION "Session Context Row Drops"

	::={plsdSesssionContextRowDrops 1}

plsdSesssionContextRowDropsMax	OBJECT-TYPE
	SYNTAX	 CounterBasedGauge64
	MAX-ACCESS read-only
	STATUS current
	DESCRIPTION "Session Context Row Drops"

	::={plsdSesssionContextRowDrops 3}

plsdSesssionContextRowDropsLevelTable OBJECT-TYPE
	SYNTAX      SEQUENCE OF PlsdSesssionContextRowDropsLevelEntry
	MAX-ACCESS  not-accessible
	STATUS      current
	DESCRIPTION
	"Table for plsdSesssionContextRowDrops"
	::={plsdSesssionContextRowDrops 4}

plsdSesssionContextRowDropsLevelEntry OBJECT-TYPE
	SYNTAX      PlsdSesssionContextRowDropsLevelEntry
	MAX-ACCESS  not-accessible
	STATUS      current
	DESCRIPTION
	"Table entry for plsdSesssionContextRowDrops"
	INDEX { plsdSesssionContextRowDropsLevelName }
	::={plsdSesssionContextRowDropsLevelTable 1}

PlsdSesssionContextRowDropsLevelEntry ::=
	SEQUENCE {
		plsdSesssionContextRowDropsLevelName	DisplayString,
		plsdSesssionContextRowDropsLevelVal	CounterBasedGauge64,
		plsdSesssionContextRowDropsLevelMax	CounterBasedGauge64
	}

plsdSesssionContextRowDropsLevelName OBJECT-TYPE
	SYNTAX      DisplayString
	MAX-ACCESS  not-accessible
	STATUS      current
	DESCRIPTION
	"Table entry display string for plsdSesssionContextRowDrops"
	::={plsdSesssionContextRowDropsLevelEntry 1}

plsdSesssionContextRowDropsLevelVal OBJECT-TYPE
	SYNTAX	 CounterBasedGauge64
	MAX-ACCESS  read-only
	STATUS      current
	DESCRIPTION
	"Table entry attribute for plsdSesssionContextRowDrops"
	::={plsdSesssionContextRowDropsLevelEntry 2}

plsdSesssionContextRowDropsLevelMax OBJECT-TYPE
	SYNTAX	 CounterBasedGauge64
	MAX-ACCESS  read-only
	STATUS      current
	DESCRIPTION
	"Table entry attribute for plsdSesssionContextRowDrops"
	::={plsdSesssionContextRowDropsLevelEntry 4}


plsdDynRemoveOfNonExistantIp	OBJECT IDENTIFIER ::={plsd 84}

plsdDynRemoveOfNonExistantIpVal	OBJECT-TYPE
	SYNTAX	 Counter64
	MAX-ACCESS read-only
	STATUS current
	DESCRIPTION "Dynamic Netobject Removes - Non existant IP address"

	::={plsdDynRemoveOfNonExistantIp 1}

plsdDynRemoveOfNonExistantIpMom	OBJECT-TYPE
	SYNTAX	 CounterBasedGauge64
	MAX-ACCESS read-only
	STATUS current
	DESCRIPTION "Dynamic Netobject Removes - Non existant IP address"

	::={plsdDynRemoveOfNonExistantIp 2}

plsdDynRemoveOfNonExistantIpMax	OBJECT-TYPE
	SYNTAX	 CounterBasedGauge64
	MAX-ACCESS read-only
	STATUS current
	DESCRIPTION "Dynamic Netobject Removes - Non existant IP address"

	::={plsdDynRemoveOfNonExistantIp 3}

plsdDynRemoveOfNonExistantIpLevelTable OBJECT-TYPE
	SYNTAX      SEQUENCE OF PlsdDynRemoveOfNonExistantIpLevelEntry
	MAX-ACCESS  not-accessible
	STATUS      current
	DESCRIPTION
	"Table for plsdDynRemoveOfNonExistantIp"
	::={plsdDynRemoveOfNonExistantIp 4}

plsdDynRemoveOfNonExistantIpLevelEntry OBJECT-TYPE
	SYNTAX      PlsdDynRemoveOfNonExistantIpLevelEntry
	MAX-ACCESS  not-accessible
	STATUS      current
	DESCRIPTION
	"Table entry for plsdDynRemoveOfNonExistantIp"
	INDEX { plsdDynRemoveOfNonExistantIpLevelName }
	::={plsdDynRemoveOfNonExistantIpLevelTable 1}

PlsdDynRemoveOfNonExistantIpLevelEntry ::=
	SEQUENCE {
		plsdDynRemoveOfNonExistantIpLevelName	DisplayString,
		plsdDynRemoveOfNonExistantIpLevelVal	Counter64,
		plsdDynRemoveOfNonExistantIpLevelMom	CounterBasedGauge64,
		plsdDynRemoveOfNonExistantIpLevelMax	CounterBasedGauge64
	}

plsdDynRemoveOfNonExistantIpLevelName OBJECT-TYPE
	SYNTAX      DisplayString
	MAX-ACCESS  not-accessible
	STATUS      current
	DESCRIPTION
	"Table entry display string for plsdDynRemoveOfNonExistantIp"
	::={plsdDynRemoveOfNonExistantIpLevelEntry 1}

plsdDynRemoveOfNonExistantIpLevelVal OBJECT-TYPE
	SYNTAX	 Counter64
	MAX-ACCESS  read-only
	STATUS      current
	DESCRIPTION
	"Table entry attribute for plsdDynRemoveOfNonExistantIp"
	::={plsdDynRemoveOfNonExistantIpLevelEntry 2}

plsdDynRemoveOfNonExistantIpLevelMom OBJECT-TYPE
	SYNTAX	 CounterBasedGauge64
	MAX-ACCESS  read-only
	STATUS      current
	DESCRIPTION
	"Table entry attribute for plsdDynRemoveOfNonExistantIp"
	::={plsdDynRemoveOfNonExistantIpLevelEntry 3}

plsdDynRemoveOfNonExistantIpLevelMax OBJECT-TYPE
	SYNTAX	 CounterBasedGauge64
	MAX-ACCESS  read-only
	STATUS      current
	DESCRIPTION
	"Table entry attribute for plsdDynRemoveOfNonExistantIp"
	::={plsdDynRemoveOfNonExistantIpLevelEntry 4}


plsdDynRemoveOfNonExistantItem	OBJECT IDENTIFIER ::={plsd 85}

plsdDynRemoveOfNonExistantItemVal	OBJECT-TYPE
	SYNTAX	 Counter64
	MAX-ACCESS read-only
	STATUS current
	DESCRIPTION "Dynamic Netobject Removes - Non existant item"

	::={plsdDynRemoveOfNonExistantItem 1}

plsdDynRemoveOfNonExistantItemMom	OBJECT-TYPE
	SYNTAX	 CounterBasedGauge64
	MAX-ACCESS read-only
	STATUS current
	DESCRIPTION "Dynamic Netobject Removes - Non existant item"

	::={plsdDynRemoveOfNonExistantItem 2}

plsdDynRemoveOfNonExistantItemMax	OBJECT-TYPE
	SYNTAX	 CounterBasedGauge64
	MAX-ACCESS read-only
	STATUS current
	DESCRIPTION "Dynamic Netobject Removes - Non existant item"

	::={plsdDynRemoveOfNonExistantItem 3}

plsdDynRemoveOfNonExistantItemLevelTable OBJECT-TYPE
	SYNTAX      SEQUENCE OF PlsdDynRemoveOfNonExistantItemLevelEntry
	MAX-ACCESS  not-accessible
	STATUS      current
	DESCRIPTION
	"Table for plsdDynRemoveOfNonExistantItem"
	::={plsdDynRemoveOfNonExistantItem 4}

plsdDynRemoveOfNonExistantItemLevelEntry OBJECT-TYPE
	SYNTAX      PlsdDynRemoveOfNonExistantItemLevelEntry
	MAX-ACCESS  not-accessible
	STATUS      current
	DESCRIPTION
	"Table entry for plsdDynRemoveOfNonExistantItem"
	INDEX { plsdDynRemoveOfNonExistantItemLevelName }
	::={plsdDynRemoveOfNonExistantItemLevelTable 1}

PlsdDynRemoveOfNonExistantItemLevelEntry ::=
	SEQUENCE {
		plsdDynRemoveOfNonExistantItemLevelName	DisplayString,
		plsdDynRemoveOfNonExistantItemLevelVal	Counter64,
		plsdDynRemoveOfNonExistantItemLevelMom	CounterBasedGauge64,
		plsdDynRemoveOfNonExistantItemLevelMax	CounterBasedGauge64
	}

plsdDynRemoveOfNonExistantItemLevelName OBJECT-TYPE
	SYNTAX      DisplayString
	MAX-ACCESS  not-accessible
	STATUS      current
	DESCRIPTION
	"Table entry display string for plsdDynRemoveOfNonExistantItem"
	::={plsdDynRemoveOfNonExistantItemLevelEntry 1}

plsdDynRemoveOfNonExistantItemLevelVal OBJECT-TYPE
	SYNTAX	 Counter64
	MAX-ACCESS  read-only
	STATUS      current
	DESCRIPTION
	"Table entry attribute for plsdDynRemoveOfNonExistantItem"
	::={plsdDynRemoveOfNonExistantItemLevelEntry 2}

plsdDynRemoveOfNonExistantItemLevelMom OBJECT-TYPE
	SYNTAX	 CounterBasedGauge64
	MAX-ACCESS  read-only
	STATUS      current
	DESCRIPTION
	"Table entry attribute for plsdDynRemoveOfNonExistantItem"
	::={plsdDynRemoveOfNonExistantItemLevelEntry 3}

plsdDynRemoveOfNonExistantItemLevelMax OBJECT-TYPE
	SYNTAX	 CounterBasedGauge64
	MAX-ACCESS  read-only
	STATUS      current
	DESCRIPTION
	"Table entry attribute for plsdDynRemoveOfNonExistantItem"
	::={plsdDynRemoveOfNonExistantItemLevelEntry 4}


plsdDatasetBwUsed	OBJECT IDENTIFIER ::={plsd 86}

plsdDatasetBwUsedVal	OBJECT-TYPE
	SYNTAX	 Counter64
	MAX-ACCESS read-only
	STATUS current
	DESCRIPTION "Bandwidth used (Dataset Transfer)"

	::={plsdDatasetBwUsed 1}

plsdDatasetBwUsedMom	OBJECT-TYPE
	SYNTAX	 CounterBasedGauge64
	MAX-ACCESS read-only
	STATUS current
	DESCRIPTION "Bandwidth used (Dataset Transfer)"

	::={plsdDatasetBwUsed 2}

plsdDatasetBwUsedMax	OBJECT-TYPE
	SYNTAX	 CounterBasedGauge64
	MAX-ACCESS read-only
	STATUS current
	DESCRIPTION "Bandwidth used (Dataset Transfer)"

	::={plsdDatasetBwUsed 3}

plsdDatasetBwUsedLevelTable OBJECT-TYPE
	SYNTAX      SEQUENCE OF PlsdDatasetBwUsedLevelEntry
	MAX-ACCESS  not-accessible
	STATUS      current
	DESCRIPTION
	"Table for plsdDatasetBwUsed"
	::={plsdDatasetBwUsed 4}

plsdDatasetBwUsedLevelEntry OBJECT-TYPE
	SYNTAX      PlsdDatasetBwUsedLevelEntry
	MAX-ACCESS  not-accessible
	STATUS      current
	DESCRIPTION
	"Table entry for plsdDatasetBwUsed"
	INDEX { plsdDatasetBwUsedLevelName }
	::={plsdDatasetBwUsedLevelTable 1}

PlsdDatasetBwUsedLevelEntry ::=
	SEQUENCE {
		plsdDatasetBwUsedLevelName	DisplayString,
		plsdDatasetBwUsedLevelVal	Counter64,
		plsdDatasetBwUsedLevelMom	CounterBasedGauge64,
		plsdDatasetBwUsedLevelMax	CounterBasedGauge64
	}

plsdDatasetBwUsedLevelName OBJECT-TYPE
	SYNTAX      DisplayString
	MAX-ACCESS  not-accessible
	STATUS      current
	DESCRIPTION
	"Table entry display string for plsdDatasetBwUsed"
	::={plsdDatasetBwUsedLevelEntry 1}

plsdDatasetBwUsedLevelVal OBJECT-TYPE
	SYNTAX	 Counter64
	MAX-ACCESS  read-only
	STATUS      current
	DESCRIPTION
	"Table entry attribute for plsdDatasetBwUsed"
	::={plsdDatasetBwUsedLevelEntry 2}

plsdDatasetBwUsedLevelMom OBJECT-TYPE
	SYNTAX	 CounterBasedGauge64
	MAX-ACCESS  read-only
	STATUS      current
	DESCRIPTION
	"Table entry attribute for plsdDatasetBwUsed"
	::={plsdDatasetBwUsedLevelEntry 3}

plsdDatasetBwUsedLevelMax OBJECT-TYPE
	SYNTAX	 CounterBasedGauge64
	MAX-ACCESS  read-only
	STATUS      current
	DESCRIPTION
	"Table entry attribute for plsdDatasetBwUsed"
	::={plsdDatasetBwUsedLevelEntry 4}


plsdDatasetGraphValues	OBJECT IDENTIFIER ::={plsd 87}

plsdDatasetGraphValuesVal	OBJECT-TYPE
	SYNTAX	 CounterBasedGauge64
	MAX-ACCESS read-only
	STATUS current
	DESCRIPTION "Dataset, Value graphs"

	::={plsdDatasetGraphValues 1}

plsdDatasetGraphValuesMax	OBJECT-TYPE
	SYNTAX	 CounterBasedGauge64
	MAX-ACCESS read-only
	STATUS current
	DESCRIPTION "Dataset, Value graphs"

	::={plsdDatasetGraphValues 3}

plsdDatasetGraphValuesLevelTable OBJECT-TYPE
	SYNTAX      SEQUENCE OF PlsdDatasetGraphValuesLevelEntry
	MAX-ACCESS  not-accessible
	STATUS      current
	DESCRIPTION
	"Table for plsdDatasetGraphValues"
	::={plsdDatasetGraphValues 4}

plsdDatasetGraphValuesLevelEntry OBJECT-TYPE
	SYNTAX      PlsdDatasetGraphValuesLevelEntry
	MAX-ACCESS  not-accessible
	STATUS      current
	DESCRIPTION
	"Table entry for plsdDatasetGraphValues"
	INDEX { plsdDatasetGraphValuesLevelName }
	::={plsdDatasetGraphValuesLevelTable 1}

PlsdDatasetGraphValuesLevelEntry ::=
	SEQUENCE {
		plsdDatasetGraphValuesLevelName	DisplayString,
		plsdDatasetGraphValuesLevelVal	CounterBasedGauge64,
		plsdDatasetGraphValuesLevelMax	CounterBasedGauge64
	}

plsdDatasetGraphValuesLevelName OBJECT-TYPE
	SYNTAX      DisplayString
	MAX-ACCESS  not-accessible
	STATUS      current
	DESCRIPTION
	"Table entry display string for plsdDatasetGraphValues"
	::={plsdDatasetGraphValuesLevelEntry 1}

plsdDatasetGraphValuesLevelVal OBJECT-TYPE
	SYNTAX	 CounterBasedGauge64
	MAX-ACCESS  read-only
	STATUS      current
	DESCRIPTION
	"Table entry attribute for plsdDatasetGraphValues"
	::={plsdDatasetGraphValuesLevelEntry 2}

plsdDatasetGraphValuesLevelMax OBJECT-TYPE
	SYNTAX	 CounterBasedGauge64
	MAX-ACCESS  read-only
	STATUS      current
	DESCRIPTION
	"Table entry attribute for plsdDatasetGraphValues"
	::={plsdDatasetGraphValuesLevelEntry 4}


plsdDatasetGraphDatapoints	OBJECT IDENTIFIER ::={plsd 88}

plsdDatasetGraphDatapointsVal	OBJECT-TYPE
	SYNTAX	 CounterBasedGauge64
	MAX-ACCESS read-only
	STATUS current
	DESCRIPTION "Dataset, Value graph datapoints"

	::={plsdDatasetGraphDatapoints 1}

plsdDatasetGraphDatapointsMax	OBJECT-TYPE
	SYNTAX	 CounterBasedGauge64
	MAX-ACCESS read-only
	STATUS current
	DESCRIPTION "Dataset, Value graph datapoints"

	::={plsdDatasetGraphDatapoints 3}

plsdDatasetGraphDatapointsLevelTable OBJECT-TYPE
	SYNTAX      SEQUENCE OF PlsdDatasetGraphDatapointsLevelEntry
	MAX-ACCESS  not-accessible
	STATUS      current
	DESCRIPTION
	"Table for plsdDatasetGraphDatapoints"
	::={plsdDatasetGraphDatapoints 4}

plsdDatasetGraphDatapointsLevelEntry OBJECT-TYPE
	SYNTAX      PlsdDatasetGraphDatapointsLevelEntry
	MAX-ACCESS  not-accessible
	STATUS      current
	DESCRIPTION
	"Table entry for plsdDatasetGraphDatapoints"
	INDEX { plsdDatasetGraphDatapointsLevelName }
	::={plsdDatasetGraphDatapointsLevelTable 1}

PlsdDatasetGraphDatapointsLevelEntry ::=
	SEQUENCE {
		plsdDatasetGraphDatapointsLevelName	DisplayString,
		plsdDatasetGraphDatapointsLevelVal	CounterBasedGauge64,
		plsdDatasetGraphDatapointsLevelMax	CounterBasedGauge64
	}

plsdDatasetGraphDatapointsLevelName OBJECT-TYPE
	SYNTAX      DisplayString
	MAX-ACCESS  not-accessible
	STATUS      current
	DESCRIPTION
	"Table entry display string for plsdDatasetGraphDatapoints"
	::={plsdDatasetGraphDatapointsLevelEntry 1}

plsdDatasetGraphDatapointsLevelVal OBJECT-TYPE
	SYNTAX	 CounterBasedGauge64
	MAX-ACCESS  read-only
	STATUS      current
	DESCRIPTION
	"Table entry attribute for plsdDatasetGraphDatapoints"
	::={plsdDatasetGraphDatapointsLevelEntry 2}

plsdDatasetGraphDatapointsLevelMax OBJECT-TYPE
	SYNTAX	 CounterBasedGauge64
	MAX-ACCESS  read-only
	STATUS      current
	DESCRIPTION
	"Table entry attribute for plsdDatasetGraphDatapoints"
	::={plsdDatasetGraphDatapointsLevelEntry 4}


plsdSesssionContextMsgsRowAdds	OBJECT IDENTIFIER ::={plsd 89}

plsdSesssionContextMsgsRowAddsVal	OBJECT-TYPE
	SYNTAX	 Counter64
	MAX-ACCESS read-only
	STATUS current
	DESCRIPTION "Session Context Row Add Messages"

	::={plsdSesssionContextMsgsRowAdds 1}

plsdSesssionContextMsgsRowAddsMom	OBJECT-TYPE
	SYNTAX	 CounterBasedGauge64
	MAX-ACCESS read-only
	STATUS current
	DESCRIPTION "Session Context Row Add Messages"

	::={plsdSesssionContextMsgsRowAdds 2}

plsdSesssionContextMsgsRowAddsMax	OBJECT-TYPE
	SYNTAX	 CounterBasedGauge64
	MAX-ACCESS read-only
	STATUS current
	DESCRIPTION "Session Context Row Add Messages"

	::={plsdSesssionContextMsgsRowAdds 3}

plsdSesssionContextMsgsRowAddsLevelTable OBJECT-TYPE
	SYNTAX      SEQUENCE OF PlsdSesssionContextMsgsRowAddsLevelEntry
	MAX-ACCESS  not-accessible
	STATUS      current
	DESCRIPTION
	"Table for plsdSesssionContextMsgsRowAdds"
	::={plsdSesssionContextMsgsRowAdds 4}

plsdSesssionContextMsgsRowAddsLevelEntry OBJECT-TYPE
	SYNTAX      PlsdSesssionContextMsgsRowAddsLevelEntry
	MAX-ACCESS  not-accessible
	STATUS      current
	DESCRIPTION
	"Table entry for plsdSesssionContextMsgsRowAdds"
	INDEX { plsdSesssionContextMsgsRowAddsLevelName }
	::={plsdSesssionContextMsgsRowAddsLevelTable 1}

PlsdSesssionContextMsgsRowAddsLevelEntry ::=
	SEQUENCE {
		plsdSesssionContextMsgsRowAddsLevelName	DisplayString,
		plsdSesssionContextMsgsRowAddsLevelVal	Counter64,
		plsdSesssionContextMsgsRowAddsLevelMom	CounterBasedGauge64,
		plsdSesssionContextMsgsRowAddsLevelMax	CounterBasedGauge64
	}

plsdSesssionContextMsgsRowAddsLevelName OBJECT-TYPE
	SYNTAX      DisplayString
	MAX-ACCESS  not-accessible
	STATUS      current
	DESCRIPTION
	"Table entry display string for plsdSesssionContextMsgsRowAdds"
	::={plsdSesssionContextMsgsRowAddsLevelEntry 1}

plsdSesssionContextMsgsRowAddsLevelVal OBJECT-TYPE
	SYNTAX	 Counter64
	MAX-ACCESS  read-only
	STATUS      current
	DESCRIPTION
	"Table entry attribute for plsdSesssionContextMsgsRowAdds"
	::={plsdSesssionContextMsgsRowAddsLevelEntry 2}

plsdSesssionContextMsgsRowAddsLevelMom OBJECT-TYPE
	SYNTAX	 CounterBasedGauge64
	MAX-ACCESS  read-only
	STATUS      current
	DESCRIPTION
	"Table entry attribute for plsdSesssionContextMsgsRowAdds"
	::={plsdSesssionContextMsgsRowAddsLevelEntry 3}

plsdSesssionContextMsgsRowAddsLevelMax OBJECT-TYPE
	SYNTAX	 CounterBasedGauge64
	MAX-ACCESS  read-only
	STATUS      current
	DESCRIPTION
	"Table entry attribute for plsdSesssionContextMsgsRowAdds"
	::={plsdSesssionContextMsgsRowAddsLevelEntry 4}


plsdSesssionContextMsgsRowRems	OBJECT IDENTIFIER ::={plsd 90}

plsdSesssionContextMsgsRowRemsVal	OBJECT-TYPE
	SYNTAX	 Counter64
	MAX-ACCESS read-only
	STATUS current
	DESCRIPTION "Session Context Row Remove Messages"

	::={plsdSesssionContextMsgsRowRems 1}

plsdSesssionContextMsgsRowRemsMom	OBJECT-TYPE
	SYNTAX	 CounterBasedGauge64
	MAX-ACCESS read-only
	STATUS current
	DESCRIPTION "Session Context Row Remove Messages"

	::={plsdSesssionContextMsgsRowRems 2}

plsdSesssionContextMsgsRowRemsMax	OBJECT-TYPE
	SYNTAX	 CounterBasedGauge64
	MAX-ACCESS read-only
	STATUS current
	DESCRIPTION "Session Context Row Remove Messages"

	::={plsdSesssionContextMsgsRowRems 3}

plsdSesssionContextMsgsRowRemsLevelTable OBJECT-TYPE
	SYNTAX      SEQUENCE OF PlsdSesssionContextMsgsRowRemsLevelEntry
	MAX-ACCESS  not-accessible
	STATUS      current
	DESCRIPTION
	"Table for plsdSesssionContextMsgsRowRems"
	::={plsdSesssionContextMsgsRowRems 4}

plsdSesssionContextMsgsRowRemsLevelEntry OBJECT-TYPE
	SYNTAX      PlsdSesssionContextMsgsRowRemsLevelEntry
	MAX-ACCESS  not-accessible
	STATUS      current
	DESCRIPTION
	"Table entry for plsdSesssionContextMsgsRowRems"
	INDEX { plsdSesssionContextMsgsRowRemsLevelName }
	::={plsdSesssionContextMsgsRowRemsLevelTable 1}

PlsdSesssionContextMsgsRowRemsLevelEntry ::=
	SEQUENCE {
		plsdSesssionContextMsgsRowRemsLevelName	DisplayString,
		plsdSesssionContextMsgsRowRemsLevelVal	Counter64,
		plsdSesssionContextMsgsRowRemsLevelMom	CounterBasedGauge64,
		plsdSesssionContextMsgsRowRemsLevelMax	CounterBasedGauge64
	}

plsdSesssionContextMsgsRowRemsLevelName OBJECT-TYPE
	SYNTAX      DisplayString
	MAX-ACCESS  not-accessible
	STATUS      current
	DESCRIPTION
	"Table entry display string for plsdSesssionContextMsgsRowRems"
	::={plsdSesssionContextMsgsRowRemsLevelEntry 1}

plsdSesssionContextMsgsRowRemsLevelVal OBJECT-TYPE
	SYNTAX	 Counter64
	MAX-ACCESS  read-only
	STATUS      current
	DESCRIPTION
	"Table entry attribute for plsdSesssionContextMsgsRowRems"
	::={plsdSesssionContextMsgsRowRemsLevelEntry 2}

plsdSesssionContextMsgsRowRemsLevelMom OBJECT-TYPE
	SYNTAX	 CounterBasedGauge64
	MAX-ACCESS  read-only
	STATUS      current
	DESCRIPTION
	"Table entry attribute for plsdSesssionContextMsgsRowRems"
	::={plsdSesssionContextMsgsRowRemsLevelEntry 3}

plsdSesssionContextMsgsRowRemsLevelMax OBJECT-TYPE
	SYNTAX	 CounterBasedGauge64
	MAX-ACCESS  read-only
	STATUS      current
	DESCRIPTION
	"Table entry attribute for plsdSesssionContextMsgsRowRems"
	::={plsdSesssionContextMsgsRowRemsLevelEntry 4}


plsdSesssionContextRowParseErrs	OBJECT IDENTIFIER ::={plsd 91}

plsdSesssionContextRowParseErrsVal	OBJECT-TYPE
	SYNTAX	 Counter64
	MAX-ACCESS read-only
	STATUS current
	DESCRIPTION "Session Context Row Parse Errors"

	::={plsdSesssionContextRowParseErrs 1}

plsdSesssionContextRowParseErrsMom	OBJECT-TYPE
	SYNTAX	 CounterBasedGauge64
	MAX-ACCESS read-only
	STATUS current
	DESCRIPTION "Session Context Row Parse Errors"

	::={plsdSesssionContextRowParseErrs 2}

plsdSesssionContextRowParseErrsMax	OBJECT-TYPE
	SYNTAX	 CounterBasedGauge64
	MAX-ACCESS read-only
	STATUS current
	DESCRIPTION "Session Context Row Parse Errors"

	::={plsdSesssionContextRowParseErrs 3}

plsdSesssionContextRowParseErrsLevelTable OBJECT-TYPE
	SYNTAX      SEQUENCE OF PlsdSesssionContextRowParseErrsLevelEntry
	MAX-ACCESS  not-accessible
	STATUS      current
	DESCRIPTION
	"Table for plsdSesssionContextRowParseErrs"
	::={plsdSesssionContextRowParseErrs 4}

plsdSesssionContextRowParseErrsLevelEntry OBJECT-TYPE
	SYNTAX      PlsdSesssionContextRowParseErrsLevelEntry
	MAX-ACCESS  not-accessible
	STATUS      current
	DESCRIPTION
	"Table entry for plsdSesssionContextRowParseErrs"
	INDEX { plsdSesssionContextRowParseErrsLevelName }
	::={plsdSesssionContextRowParseErrsLevelTable 1}

PlsdSesssionContextRowParseErrsLevelEntry ::=
	SEQUENCE {
		plsdSesssionContextRowParseErrsLevelName	DisplayString,
		plsdSesssionContextRowParseErrsLevelVal	Counter64,
		plsdSesssionContextRowParseErrsLevelMom	CounterBasedGauge64,
		plsdSesssionContextRowParseErrsLevelMax	CounterBasedGauge64
	}

plsdSesssionContextRowParseErrsLevelName OBJECT-TYPE
	SYNTAX      DisplayString
	MAX-ACCESS  not-accessible
	STATUS      current
	DESCRIPTION
	"Table entry display string for plsdSesssionContextRowParseErrs"
	::={plsdSesssionContextRowParseErrsLevelEntry 1}

plsdSesssionContextRowParseErrsLevelVal OBJECT-TYPE
	SYNTAX	 Counter64
	MAX-ACCESS  read-only
	STATUS      current
	DESCRIPTION
	"Table entry attribute for plsdSesssionContextRowParseErrs"
	::={plsdSesssionContextRowParseErrsLevelEntry 2}

plsdSesssionContextRowParseErrsLevelMom OBJECT-TYPE
	SYNTAX	 CounterBasedGauge64
	MAX-ACCESS  read-only
	STATUS      current
	DESCRIPTION
	"Table entry attribute for plsdSesssionContextRowParseErrs"
	::={plsdSesssionContextRowParseErrsLevelEntry 3}

plsdSesssionContextRowParseErrsLevelMax OBJECT-TYPE
	SYNTAX	 CounterBasedGauge64
	MAX-ACCESS  read-only
	STATUS      current
	DESCRIPTION
	"Table entry attribute for plsdSesssionContextRowParseErrs"
	::={plsdSesssionContextRowParseErrsLevelEntry 4}


plsdSesssionContextRowRemoveErrs	OBJECT IDENTIFIER ::={plsd 92}

plsdSesssionContextRowRemoveErrsVal	OBJECT-TYPE
	SYNTAX	 Counter64
	MAX-ACCESS read-only
	STATUS current
	DESCRIPTION "Session Context Row Remove Errors"

	::={plsdSesssionContextRowRemoveErrs 1}

plsdSesssionContextRowRemoveErrsMom	OBJECT-TYPE
	SYNTAX	 CounterBasedGauge64
	MAX-ACCESS read-only
	STATUS current
	DESCRIPTION "Session Context Row Remove Errors"

	::={plsdSesssionContextRowRemoveErrs 2}

plsdSesssionContextRowRemoveErrsMax	OBJECT-TYPE
	SYNTAX	 CounterBasedGauge64
	MAX-ACCESS read-only
	STATUS current
	DESCRIPTION "Session Context Row Remove Errors"

	::={plsdSesssionContextRowRemoveErrs 3}

plsdSesssionContextRowRemoveErrsLevelTable OBJECT-TYPE
	SYNTAX      SEQUENCE OF PlsdSesssionContextRowRemoveErrsLevelEntry
	MAX-ACCESS  not-accessible
	STATUS      current
	DESCRIPTION
	"Table for plsdSesssionContextRowRemoveErrs"
	::={plsdSesssionContextRowRemoveErrs 4}

plsdSesssionContextRowRemoveErrsLevelEntry OBJECT-TYPE
	SYNTAX      PlsdSesssionContextRowRemoveErrsLevelEntry
	MAX-ACCESS  not-accessible
	STATUS      current
	DESCRIPTION
	"Table entry for plsdSesssionContextRowRemoveErrs"
	INDEX { plsdSesssionContextRowRemoveErrsLevelName }
	::={plsdSesssionContextRowRemoveErrsLevelTable 1}

PlsdSesssionContextRowRemoveErrsLevelEntry ::=
	SEQUENCE {
		plsdSesssionContextRowRemoveErrsLevelName	DisplayString,
		plsdSesssionContextRowRemoveErrsLevelVal	Counter64,
		plsdSesssionContextRowRemoveErrsLevelMom	CounterBasedGauge64,
		plsdSesssionContextRowRemoveErrsLevelMax	CounterBasedGauge64
	}

plsdSesssionContextRowRemoveErrsLevelName OBJECT-TYPE
	SYNTAX      DisplayString
	MAX-ACCESS  not-accessible
	STATUS      current
	DESCRIPTION
	"Table entry display string for plsdSesssionContextRowRemoveErrs"
	::={plsdSesssionContextRowRemoveErrsLevelEntry 1}

plsdSesssionContextRowRemoveErrsLevelVal OBJECT-TYPE
	SYNTAX	 Counter64
	MAX-ACCESS  read-only
	STATUS      current
	DESCRIPTION
	"Table entry attribute for plsdSesssionContextRowRemoveErrs"
	::={plsdSesssionContextRowRemoveErrsLevelEntry 2}

plsdSesssionContextRowRemoveErrsLevelMom OBJECT-TYPE
	SYNTAX	 CounterBasedGauge64
	MAX-ACCESS  read-only
	STATUS      current
	DESCRIPTION
	"Table entry attribute for plsdSesssionContextRowRemoveErrs"
	::={plsdSesssionContextRowRemoveErrsLevelEntry 3}

plsdSesssionContextRowRemoveErrsLevelMax OBJECT-TYPE
	SYNTAX	 CounterBasedGauge64
	MAX-ACCESS  read-only
	STATUS      current
	DESCRIPTION
	"Table entry attribute for plsdSesssionContextRowRemoveErrs"
	::={plsdSesssionContextRowRemoveErrsLevelEntry 4}


plsdSesssionContextRowLookupFails	OBJECT IDENTIFIER ::={plsd 93}

plsdSesssionContextRowLookupFailsVal	OBJECT-TYPE
	SYNTAX	 Counter64
	MAX-ACCESS read-only
	STATUS current
	DESCRIPTION "Session Context Row Failed Lookups"

	::={plsdSesssionContextRowLookupFails 1}

plsdSesssionContextRowLookupFailsMom	OBJECT-TYPE
	SYNTAX	 CounterBasedGauge64
	MAX-ACCESS read-only
	STATUS current
	DESCRIPTION "Session Context Row Failed Lookups"

	::={plsdSesssionContextRowLookupFails 2}

plsdSesssionContextRowLookupFailsMax	OBJECT-TYPE
	SYNTAX	 CounterBasedGauge64
	MAX-ACCESS read-only
	STATUS current
	DESCRIPTION "Session Context Row Failed Lookups"

	::={plsdSesssionContextRowLookupFails 3}

plsdSesssionContextRowLookupFailsLevelTable OBJECT-TYPE
	SYNTAX      SEQUENCE OF PlsdSesssionContextRowLookupFailsLevelEntry
	MAX-ACCESS  not-accessible
	STATUS      current
	DESCRIPTION
	"Table for plsdSesssionContextRowLookupFails"
	::={plsdSesssionContextRowLookupFails 4}

plsdSesssionContextRowLookupFailsLevelEntry OBJECT-TYPE
	SYNTAX      PlsdSesssionContextRowLookupFailsLevelEntry
	MAX-ACCESS  not-accessible
	STATUS      current
	DESCRIPTION
	"Table entry for plsdSesssionContextRowLookupFails"
	INDEX { plsdSesssionContextRowLookupFailsLevelName }
	::={plsdSesssionContextRowLookupFailsLevelTable 1}

PlsdSesssionContextRowLookupFailsLevelEntry ::=
	SEQUENCE {
		plsdSesssionContextRowLookupFailsLevelName	DisplayString,
		plsdSesssionContextRowLookupFailsLevelVal	Counter64,
		plsdSesssionContextRowLookupFailsLevelMom	CounterBasedGauge64,
		plsdSesssionContextRowLookupFailsLevelMax	CounterBasedGauge64
	}

plsdSesssionContextRowLookupFailsLevelName OBJECT-TYPE
	SYNTAX      DisplayString
	MAX-ACCESS  not-accessible
	STATUS      current
	DESCRIPTION
	"Table entry display string for plsdSesssionContextRowLookupFails"
	::={plsdSesssionContextRowLookupFailsLevelEntry 1}

plsdSesssionContextRowLookupFailsLevelVal OBJECT-TYPE
	SYNTAX	 Counter64
	MAX-ACCESS  read-only
	STATUS      current
	DESCRIPTION
	"Table entry attribute for plsdSesssionContextRowLookupFails"
	::={plsdSesssionContextRowLookupFailsLevelEntry 2}

plsdSesssionContextRowLookupFailsLevelMom OBJECT-TYPE
	SYNTAX	 CounterBasedGauge64
	MAX-ACCESS  read-only
	STATUS      current
	DESCRIPTION
	"Table entry attribute for plsdSesssionContextRowLookupFails"
	::={plsdSesssionContextRowLookupFailsLevelEntry 3}

plsdSesssionContextRowLookupFailsLevelMax OBJECT-TYPE
	SYNTAX	 CounterBasedGauge64
	MAX-ACCESS  read-only
	STATUS      current
	DESCRIPTION
	"Table entry attribute for plsdSesssionContextRowLookupFails"
	::={plsdSesssionContextRowLookupFailsLevelEntry 4}


plsdSesssionContextRowLookups	OBJECT IDENTIFIER ::={plsd 94}

plsdSesssionContextRowLookupsVal	OBJECT-TYPE
	SYNTAX	 Counter64
	MAX-ACCESS read-only
	STATUS current
	DESCRIPTION "Session Context Row Lookups"

	::={plsdSesssionContextRowLookups 1}

plsdSesssionContextRowLookupsMom	OBJECT-TYPE
	SYNTAX	 CounterBasedGauge64
	MAX-ACCESS read-only
	STATUS current
	DESCRIPTION "Session Context Row Lookups"

	::={plsdSesssionContextRowLookups 2}

plsdSesssionContextRowLookupsMax	OBJECT-TYPE
	SYNTAX	 CounterBasedGauge64
	MAX-ACCESS read-only
	STATUS current
	DESCRIPTION "Session Context Row Lookups"

	::={plsdSesssionContextRowLookups 3}

plsdSesssionContextRowLookupsLevelTable OBJECT-TYPE
	SYNTAX      SEQUENCE OF PlsdSesssionContextRowLookupsLevelEntry
	MAX-ACCESS  not-accessible
	STATUS      current
	DESCRIPTION
	"Table for plsdSesssionContextRowLookups"
	::={plsdSesssionContextRowLookups 4}

plsdSesssionContextRowLookupsLevelEntry OBJECT-TYPE
	SYNTAX      PlsdSesssionContextRowLookupsLevelEntry
	MAX-ACCESS  not-accessible
	STATUS      current
	DESCRIPTION
	"Table entry for plsdSesssionContextRowLookups"
	INDEX { plsdSesssionContextRowLookupsLevelName }
	::={plsdSesssionContextRowLookupsLevelTable 1}

PlsdSesssionContextRowLookupsLevelEntry ::=
	SEQUENCE {
		plsdSesssionContextRowLookupsLevelName	DisplayString,
		plsdSesssionContextRowLookupsLevelVal	Counter64,
		plsdSesssionContextRowLookupsLevelMom	CounterBasedGauge64,
		plsdSesssionContextRowLookupsLevelMax	CounterBasedGauge64
	}

plsdSesssionContextRowLookupsLevelName OBJECT-TYPE
	SYNTAX      DisplayString
	MAX-ACCESS  not-accessible
	STATUS      current
	DESCRIPTION
	"Table entry display string for plsdSesssionContextRowLookups"
	::={plsdSesssionContextRowLookupsLevelEntry 1}

plsdSesssionContextRowLookupsLevelVal OBJECT-TYPE
	SYNTAX	 Counter64
	MAX-ACCESS  read-only
	STATUS      current
	DESCRIPTION
	"Table entry attribute for plsdSesssionContextRowLookups"
	::={plsdSesssionContextRowLookupsLevelEntry 2}

plsdSesssionContextRowLookupsLevelMom OBJECT-TYPE
	SYNTAX	 CounterBasedGauge64
	MAX-ACCESS  read-only
	STATUS      current
	DESCRIPTION
	"Table entry attribute for plsdSesssionContextRowLookups"
	::={plsdSesssionContextRowLookupsLevelEntry 3}

plsdSesssionContextRowLookupsLevelMax OBJECT-TYPE
	SYNTAX	 CounterBasedGauge64
	MAX-ACCESS  read-only
	STATUS      current
	DESCRIPTION
	"Table entry attribute for plsdSesssionContextRowLookups"
	::={plsdSesssionContextRowLookupsLevelEntry 4}


plsdBytesUnAccountedInNoDataset	OBJECT IDENTIFIER ::={plsd 95}

plsdBytesUnAccountedInNoDatasetVal	OBJECT-TYPE
	SYNTAX	 Counter64
	MAX-ACCESS read-only
	STATUS current
	DESCRIPTION "Connection Bytes Unaccounted In, Dataset unavailable"

	::={plsdBytesUnAccountedInNoDataset 1}

plsdBytesUnAccountedInNoDatasetMom	OBJECT-TYPE
	SYNTAX	 CounterBasedGauge64
	MAX-ACCESS read-only
	STATUS current
	DESCRIPTION "Connection Bytes Unaccounted In, Dataset unavailable"

	::={plsdBytesUnAccountedInNoDataset 2}

plsdBytesUnAccountedInNoDatasetMax	OBJECT-TYPE
	SYNTAX	 CounterBasedGauge64
	MAX-ACCESS read-only
	STATUS current
	DESCRIPTION "Connection Bytes Unaccounted In, Dataset unavailable"

	::={plsdBytesUnAccountedInNoDataset 3}

plsdBytesUnAccountedInNoDatasetLevelTable OBJECT-TYPE
	SYNTAX      SEQUENCE OF PlsdBytesUnAccountedInNoDatasetLevelEntry
	MAX-ACCESS  not-accessible
	STATUS      current
	DESCRIPTION
	"Table for plsdBytesUnAccountedInNoDataset"
	::={plsdBytesUnAccountedInNoDataset 4}

plsdBytesUnAccountedInNoDatasetLevelEntry OBJECT-TYPE
	SYNTAX      PlsdBytesUnAccountedInNoDatasetLevelEntry
	MAX-ACCESS  not-accessible
	STATUS      current
	DESCRIPTION
	"Table entry for plsdBytesUnAccountedInNoDataset"
	INDEX { plsdBytesUnAccountedInNoDatasetLevelName }
	::={plsdBytesUnAccountedInNoDatasetLevelTable 1}

PlsdBytesUnAccountedInNoDatasetLevelEntry ::=
	SEQUENCE {
		plsdBytesUnAccountedInNoDatasetLevelName	DisplayString,
		plsdBytesUnAccountedInNoDatasetLevelVal	Counter64,
		plsdBytesUnAccountedInNoDatasetLevelMom	CounterBasedGauge64,
		plsdBytesUnAccountedInNoDatasetLevelMax	CounterBasedGauge64
	}

plsdBytesUnAccountedInNoDatasetLevelName OBJECT-TYPE
	SYNTAX      DisplayString
	MAX-ACCESS  not-accessible
	STATUS      current
	DESCRIPTION
	"Table entry display string for plsdBytesUnAccountedInNoDataset"
	::={plsdBytesUnAccountedInNoDatasetLevelEntry 1}

plsdBytesUnAccountedInNoDatasetLevelVal OBJECT-TYPE
	SYNTAX	 Counter64
	MAX-ACCESS  read-only
	STATUS      current
	DESCRIPTION
	"Table entry attribute for plsdBytesUnAccountedInNoDataset"
	::={plsdBytesUnAccountedInNoDatasetLevelEntry 2}

plsdBytesUnAccountedInNoDatasetLevelMom OBJECT-TYPE
	SYNTAX	 CounterBasedGauge64
	MAX-ACCESS  read-only
	STATUS      current
	DESCRIPTION
	"Table entry attribute for plsdBytesUnAccountedInNoDataset"
	::={plsdBytesUnAccountedInNoDatasetLevelEntry 3}

plsdBytesUnAccountedInNoDatasetLevelMax OBJECT-TYPE
	SYNTAX	 CounterBasedGauge64
	MAX-ACCESS  read-only
	STATUS      current
	DESCRIPTION
	"Table entry attribute for plsdBytesUnAccountedInNoDataset"
	::={plsdBytesUnAccountedInNoDatasetLevelEntry 4}


plsdBytesUnAccountedOutNoDataset	OBJECT IDENTIFIER ::={plsd 96}

plsdBytesUnAccountedOutNoDatasetVal	OBJECT-TYPE
	SYNTAX	 Counter64
	MAX-ACCESS read-only
	STATUS current
	DESCRIPTION "Connection Bytes Unaccounted Out, Dataset unavailable"

	::={plsdBytesUnAccountedOutNoDataset 1}

plsdBytesUnAccountedOutNoDatasetMom	OBJECT-TYPE
	SYNTAX	 CounterBasedGauge64
	MAX-ACCESS read-only
	STATUS current
	DESCRIPTION "Connection Bytes Unaccounted Out, Dataset unavailable"

	::={plsdBytesUnAccountedOutNoDataset 2}

plsdBytesUnAccountedOutNoDatasetMax	OBJECT-TYPE
	SYNTAX	 CounterBasedGauge64
	MAX-ACCESS read-only
	STATUS current
	DESCRIPTION "Connection Bytes Unaccounted Out, Dataset unavailable"

	::={plsdBytesUnAccountedOutNoDataset 3}

plsdBytesUnAccountedOutNoDatasetLevelTable OBJECT-TYPE
	SYNTAX      SEQUENCE OF PlsdBytesUnAccountedOutNoDatasetLevelEntry
	MAX-ACCESS  not-accessible
	STATUS      current
	DESCRIPTION
	"Table for plsdBytesUnAccountedOutNoDataset"
	::={plsdBytesUnAccountedOutNoDataset 4}

plsdBytesUnAccountedOutNoDatasetLevelEntry OBJECT-TYPE
	SYNTAX      PlsdBytesUnAccountedOutNoDatasetLevelEntry
	MAX-ACCESS  not-accessible
	STATUS      current
	DESCRIPTION
	"Table entry for plsdBytesUnAccountedOutNoDataset"
	INDEX { plsdBytesUnAccountedOutNoDatasetLevelName }
	::={plsdBytesUnAccountedOutNoDatasetLevelTable 1}

PlsdBytesUnAccountedOutNoDatasetLevelEntry ::=
	SEQUENCE {
		plsdBytesUnAccountedOutNoDatasetLevelName	DisplayString,
		plsdBytesUnAccountedOutNoDatasetLevelVal	Counter64,
		plsdBytesUnAccountedOutNoDatasetLevelMom	CounterBasedGauge64,
		plsdBytesUnAccountedOutNoDatasetLevelMax	CounterBasedGauge64
	}

plsdBytesUnAccountedOutNoDatasetLevelName OBJECT-TYPE
	SYNTAX      DisplayString
	MAX-ACCESS  not-accessible
	STATUS      current
	DESCRIPTION
	"Table entry display string for plsdBytesUnAccountedOutNoDataset"
	::={plsdBytesUnAccountedOutNoDatasetLevelEntry 1}

plsdBytesUnAccountedOutNoDatasetLevelVal OBJECT-TYPE
	SYNTAX	 Counter64
	MAX-ACCESS  read-only
	STATUS      current
	DESCRIPTION
	"Table entry attribute for plsdBytesUnAccountedOutNoDataset"
	::={plsdBytesUnAccountedOutNoDatasetLevelEntry 2}

plsdBytesUnAccountedOutNoDatasetLevelMom OBJECT-TYPE
	SYNTAX	 CounterBasedGauge64
	MAX-ACCESS  read-only
	STATUS      current
	DESCRIPTION
	"Table entry attribute for plsdBytesUnAccountedOutNoDataset"
	::={plsdBytesUnAccountedOutNoDatasetLevelEntry 3}

plsdBytesUnAccountedOutNoDatasetLevelMax OBJECT-TYPE
	SYNTAX	 CounterBasedGauge64
	MAX-ACCESS  read-only
	STATUS      current
	DESCRIPTION
	"Table entry attribute for plsdBytesUnAccountedOutNoDataset"
	::={plsdBytesUnAccountedOutNoDatasetLevelEntry 4}


plsdConnectionUnsupportedHostnames	OBJECT IDENTIFIER ::={plsd 97}

plsdConnectionUnsupportedHostnamesVal	OBJECT-TYPE
	SYNTAX	 Counter64
	MAX-ACCESS read-only
	STATUS current
	DESCRIPTION "Connection updates with unsupported hostnames"

	::={plsdConnectionUnsupportedHostnames 1}

plsdConnectionUnsupportedHostnamesMom	OBJECT-TYPE
	SYNTAX	 CounterBasedGauge64
	MAX-ACCESS read-only
	STATUS current
	DESCRIPTION "Connection updates with unsupported hostnames"

	::={plsdConnectionUnsupportedHostnames 2}

plsdConnectionUnsupportedHostnamesMax	OBJECT-TYPE
	SYNTAX	 CounterBasedGauge64
	MAX-ACCESS read-only
	STATUS current
	DESCRIPTION "Connection updates with unsupported hostnames"

	::={plsdConnectionUnsupportedHostnames 3}

plsdConnectionUnsupportedHostnamesLevelTable OBJECT-TYPE
	SYNTAX      SEQUENCE OF PlsdConnectionUnsupportedHostnamesLevelEntry
	MAX-ACCESS  not-accessible
	STATUS      current
	DESCRIPTION
	"Table for plsdConnectionUnsupportedHostnames"
	::={plsdConnectionUnsupportedHostnames 4}

plsdConnectionUnsupportedHostnamesLevelEntry OBJECT-TYPE
	SYNTAX      PlsdConnectionUnsupportedHostnamesLevelEntry
	MAX-ACCESS  not-accessible
	STATUS      current
	DESCRIPTION
	"Table entry for plsdConnectionUnsupportedHostnames"
	INDEX { plsdConnectionUnsupportedHostnamesLevelName }
	::={plsdConnectionUnsupportedHostnamesLevelTable 1}

PlsdConnectionUnsupportedHostnamesLevelEntry ::=
	SEQUENCE {
		plsdConnectionUnsupportedHostnamesLevelName	DisplayString,
		plsdConnectionUnsupportedHostnamesLevelVal	Counter64,
		plsdConnectionUnsupportedHostnamesLevelMom	CounterBasedGauge64,
		plsdConnectionUnsupportedHostnamesLevelMax	CounterBasedGauge64
	}

plsdConnectionUnsupportedHostnamesLevelName OBJECT-TYPE
	SYNTAX      DisplayString
	MAX-ACCESS  not-accessible
	STATUS      current
	DESCRIPTION
	"Table entry display string for plsdConnectionUnsupportedHostnames"
	::={plsdConnectionUnsupportedHostnamesLevelEntry 1}

plsdConnectionUnsupportedHostnamesLevelVal OBJECT-TYPE
	SYNTAX	 Counter64
	MAX-ACCESS  read-only
	STATUS      current
	DESCRIPTION
	"Table entry attribute for plsdConnectionUnsupportedHostnames"
	::={plsdConnectionUnsupportedHostnamesLevelEntry 2}

plsdConnectionUnsupportedHostnamesLevelMom OBJECT-TYPE
	SYNTAX	 CounterBasedGauge64
	MAX-ACCESS  read-only
	STATUS      current
	DESCRIPTION
	"Table entry attribute for plsdConnectionUnsupportedHostnames"
	::={plsdConnectionUnsupportedHostnamesLevelEntry 3}

plsdConnectionUnsupportedHostnamesLevelMax OBJECT-TYPE
	SYNTAX	 CounterBasedGauge64
	MAX-ACCESS  read-only
	STATUS      current
	DESCRIPTION
	"Table entry attribute for plsdConnectionUnsupportedHostnames"
	::={plsdConnectionUnsupportedHostnamesLevelEntry 4}


plsdHostStatsNetobjectLookups	OBJECT IDENTIFIER ::={plsd 98}

plsdHostStatsNetobjectLookupsVal	OBJECT-TYPE
	SYNTAX	 Counter64
	MAX-ACCESS read-only
	STATUS obsolete
	DESCRIPTION "Host stats: NetObject Lookups"

	::={plsdHostStatsNetobjectLookups 1}

plsdHostStatsNetobjectLookupsMom	OBJECT-TYPE
	SYNTAX	 CounterBasedGauge64
	MAX-ACCESS read-only
	STATUS obsolete
	DESCRIPTION "Host stats: NetObject Lookups"

	::={plsdHostStatsNetobjectLookups 2}

plsdHostStatsNetobjectLookupsMax	OBJECT-TYPE
	SYNTAX	 CounterBasedGauge64
	MAX-ACCESS read-only
	STATUS obsolete
	DESCRIPTION "Host stats: NetObject Lookups"

	::={plsdHostStatsNetobjectLookups 3}

plsdHostStatsNetobjectLookupsLevelTable OBJECT-TYPE
	SYNTAX      SEQUENCE OF PlsdHostStatsNetobjectLookupsLevelEntry
	MAX-ACCESS  not-accessible
	STATUS      current
	DESCRIPTION
	"Table for plsdHostStatsNetobjectLookups"
	::={plsdHostStatsNetobjectLookups 4}

plsdHostStatsNetobjectLookupsLevelEntry OBJECT-TYPE
	SYNTAX      PlsdHostStatsNetobjectLookupsLevelEntry
	MAX-ACCESS  not-accessible
	STATUS      current
	DESCRIPTION
	"Table entry for plsdHostStatsNetobjectLookups"
	INDEX { plsdHostStatsNetobjectLookupsLevelName }
	::={plsdHostStatsNetobjectLookupsLevelTable 1}

PlsdHostStatsNetobjectLookupsLevelEntry ::=
	SEQUENCE {
		plsdHostStatsNetobjectLookupsLevelName	DisplayString,
		plsdHostStatsNetobjectLookupsLevelVal	Counter64,
		plsdHostStatsNetobjectLookupsLevelMom	CounterBasedGauge64,
		plsdHostStatsNetobjectLookupsLevelMax	CounterBasedGauge64
	}

plsdHostStatsNetobjectLookupsLevelName OBJECT-TYPE
	SYNTAX      DisplayString
	MAX-ACCESS  not-accessible
	STATUS      current
	DESCRIPTION
	"Table entry display string for plsdHostStatsNetobjectLookups"
	::={plsdHostStatsNetobjectLookupsLevelEntry 1}

plsdHostStatsNetobjectLookupsLevelVal OBJECT-TYPE
	SYNTAX	 Counter64
	MAX-ACCESS  read-only
	STATUS      current
	DESCRIPTION
	"Table entry attribute for plsdHostStatsNetobjectLookups"
	::={plsdHostStatsNetobjectLookupsLevelEntry 2}

plsdHostStatsNetobjectLookupsLevelMom OBJECT-TYPE
	SYNTAX	 CounterBasedGauge64
	MAX-ACCESS  read-only
	STATUS      current
	DESCRIPTION
	"Table entry attribute for plsdHostStatsNetobjectLookups"
	::={plsdHostStatsNetobjectLookupsLevelEntry 3}

plsdHostStatsNetobjectLookupsLevelMax OBJECT-TYPE
	SYNTAX	 CounterBasedGauge64
	MAX-ACCESS  read-only
	STATUS      current
	DESCRIPTION
	"Table entry attribute for plsdHostStatsNetobjectLookups"
	::={plsdHostStatsNetobjectLookupsLevelEntry 4}


plsdHostStatsNetobjectLookupFails	OBJECT IDENTIFIER ::={plsd 99}

plsdHostStatsNetobjectLookupFailsVal	OBJECT-TYPE
	SYNTAX	 Counter64
	MAX-ACCESS read-only
	STATUS obsolete
	DESCRIPTION "Host stats: NetObject Lookup Fails"

	::={plsdHostStatsNetobjectLookupFails 1}

plsdHostStatsNetobjectLookupFailsMom	OBJECT-TYPE
	SYNTAX	 CounterBasedGauge64
	MAX-ACCESS read-only
	STATUS obsolete
	DESCRIPTION "Host stats: NetObject Lookup Fails"

	::={plsdHostStatsNetobjectLookupFails 2}

plsdHostStatsNetobjectLookupFailsMax	OBJECT-TYPE
	SYNTAX	 CounterBasedGauge64
	MAX-ACCESS read-only
	STATUS obsolete
	DESCRIPTION "Host stats: NetObject Lookup Fails"

	::={plsdHostStatsNetobjectLookupFails 3}

plsdHostStatsNetobjectLookupFailsLevelTable OBJECT-TYPE
	SYNTAX      SEQUENCE OF PlsdHostStatsNetobjectLookupFailsLevelEntry
	MAX-ACCESS  not-accessible
	STATUS      current
	DESCRIPTION
	"Table for plsdHostStatsNetobjectLookupFails"
	::={plsdHostStatsNetobjectLookupFails 4}

plsdHostStatsNetobjectLookupFailsLevelEntry OBJECT-TYPE
	SYNTAX      PlsdHostStatsNetobjectLookupFailsLevelEntry
	MAX-ACCESS  not-accessible
	STATUS      current
	DESCRIPTION
	"Table entry for plsdHostStatsNetobjectLookupFails"
	INDEX { plsdHostStatsNetobjectLookupFailsLevelName }
	::={plsdHostStatsNetobjectLookupFailsLevelTable 1}

PlsdHostStatsNetobjectLookupFailsLevelEntry ::=
	SEQUENCE {
		plsdHostStatsNetobjectLookupFailsLevelName	DisplayString,
		plsdHostStatsNetobjectLookupFailsLevelVal	Counter64,
		plsdHostStatsNetobjectLookupFailsLevelMom	CounterBasedGauge64,
		plsdHostStatsNetobjectLookupFailsLevelMax	CounterBasedGauge64
	}

plsdHostStatsNetobjectLookupFailsLevelName OBJECT-TYPE
	SYNTAX      DisplayString
	MAX-ACCESS  not-accessible
	STATUS      current
	DESCRIPTION
	"Table entry display string for plsdHostStatsNetobjectLookupFails"
	::={plsdHostStatsNetobjectLookupFailsLevelEntry 1}

plsdHostStatsNetobjectLookupFailsLevelVal OBJECT-TYPE
	SYNTAX	 Counter64
	MAX-ACCESS  read-only
	STATUS      current
	DESCRIPTION
	"Table entry attribute for plsdHostStatsNetobjectLookupFails"
	::={plsdHostStatsNetobjectLookupFailsLevelEntry 2}

plsdHostStatsNetobjectLookupFailsLevelMom OBJECT-TYPE
	SYNTAX	 CounterBasedGauge64
	MAX-ACCESS  read-only
	STATUS      current
	DESCRIPTION
	"Table entry attribute for plsdHostStatsNetobjectLookupFails"
	::={plsdHostStatsNetobjectLookupFailsLevelEntry 3}

plsdHostStatsNetobjectLookupFailsLevelMax OBJECT-TYPE
	SYNTAX	 CounterBasedGauge64
	MAX-ACCESS  read-only
	STATUS      current
	DESCRIPTION
	"Table entry attribute for plsdHostStatsNetobjectLookupFails"
	::={plsdHostStatsNetobjectLookupFailsLevelEntry 4}


plsdSesssionContextRowMaxColumnsExceeded	OBJECT IDENTIFIER ::={plsd 100}

plsdSesssionContextRowMaxColumnsExceededVal	OBJECT-TYPE
	SYNTAX	 CounterBasedGauge64
	MAX-ACCESS read-only
	STATUS current
	DESCRIPTION "Session Context Rows, Max Columns Exceeded"

	::={plsdSesssionContextRowMaxColumnsExceeded 1}

plsdSesssionContextRowMaxColumnsExceededMax	OBJECT-TYPE
	SYNTAX	 CounterBasedGauge64
	MAX-ACCESS read-only
	STATUS current
	DESCRIPTION "Session Context Rows, Max Columns Exceeded"

	::={plsdSesssionContextRowMaxColumnsExceeded 3}

plsdSesssionContextRowMaxColumnsExceededLevelTable OBJECT-TYPE
	SYNTAX      SEQUENCE OF PlsdSesssionContextRowMaxColumnsExceededLevelEntry
	MAX-ACCESS  not-accessible
	STATUS      current
	DESCRIPTION
	"Table for plsdSesssionContextRowMaxColumnsExceeded"
	::={plsdSesssionContextRowMaxColumnsExceeded 4}

plsdSesssionContextRowMaxColumnsExceededLevelEntry OBJECT-TYPE
	SYNTAX      PlsdSesssionContextRowMaxColumnsExceededLevelEntry
	MAX-ACCESS  not-accessible
	STATUS      current
	DESCRIPTION
	"Table entry for plsdSesssionContextRowMaxColumnsExceeded"
	INDEX { plsdSesssionContextRowMaxColumnsExceededLevelName }
	::={plsdSesssionContextRowMaxColumnsExceededLevelTable 1}

PlsdSesssionContextRowMaxColumnsExceededLevelEntry ::=
	SEQUENCE {
		plsdSesssionContextRowMaxColumnsExceededLevelName	DisplayString,
		plsdSesssionContextRowMaxColumnsExceededLevelVal	CounterBasedGauge64,
		plsdSesssionContextRowMaxColumnsExceededLevelMax	CounterBasedGauge64
	}

plsdSesssionContextRowMaxColumnsExceededLevelName OBJECT-TYPE
	SYNTAX      DisplayString
	MAX-ACCESS  not-accessible
	STATUS      current
	DESCRIPTION
	"Table entry display string for plsdSesssionContextRowMaxColumnsExceeded"
	::={plsdSesssionContextRowMaxColumnsExceededLevelEntry 1}

plsdSesssionContextRowMaxColumnsExceededLevelVal OBJECT-TYPE
	SYNTAX	 CounterBasedGauge64
	MAX-ACCESS  read-only
	STATUS      current
	DESCRIPTION
	"Table entry attribute for plsdSesssionContextRowMaxColumnsExceeded"
	::={plsdSesssionContextRowMaxColumnsExceededLevelEntry 2}

plsdSesssionContextRowMaxColumnsExceededLevelMax OBJECT-TYPE
	SYNTAX	 CounterBasedGauge64
	MAX-ACCESS  read-only
	STATUS      current
	DESCRIPTION
	"Table entry attribute for plsdSesssionContextRowMaxColumnsExceeded"
	::={plsdSesssionContextRowMaxColumnsExceededLevelEntry 4}


plsdSesssionContextRowColumnLookupFail	OBJECT IDENTIFIER ::={plsd 101}

plsdSesssionContextRowColumnLookupFailVal	OBJECT-TYPE
	SYNTAX	 Counter64
	MAX-ACCESS read-only
	STATUS current
	DESCRIPTION "Session Context Row Column Failed Lookups"

	::={plsdSesssionContextRowColumnLookupFail 1}

plsdSesssionContextRowColumnLookupFailMom	OBJECT-TYPE
	SYNTAX	 CounterBasedGauge64
	MAX-ACCESS read-only
	STATUS current
	DESCRIPTION "Session Context Row Column Failed Lookups"

	::={plsdSesssionContextRowColumnLookupFail 2}

plsdSesssionContextRowColumnLookupFailMax	OBJECT-TYPE
	SYNTAX	 CounterBasedGauge64
	MAX-ACCESS read-only
	STATUS current
	DESCRIPTION "Session Context Row Column Failed Lookups"

	::={plsdSesssionContextRowColumnLookupFail 3}

plsdSesssionContextRowColumnLookupFailLevelTable OBJECT-TYPE
	SYNTAX      SEQUENCE OF PlsdSesssionContextRowColumnLookupFailLevelEntry
	MAX-ACCESS  not-accessible
	STATUS      current
	DESCRIPTION
	"Table for plsdSesssionContextRowColumnLookupFail"
	::={plsdSesssionContextRowColumnLookupFail 4}

plsdSesssionContextRowColumnLookupFailLevelEntry OBJECT-TYPE
	SYNTAX      PlsdSesssionContextRowColumnLookupFailLevelEntry
	MAX-ACCESS  not-accessible
	STATUS      current
	DESCRIPTION
	"Table entry for plsdSesssionContextRowColumnLookupFail"
	INDEX { plsdSesssionContextRowColumnLookupFailLevelName }
	::={plsdSesssionContextRowColumnLookupFailLevelTable 1}

PlsdSesssionContextRowColumnLookupFailLevelEntry ::=
	SEQUENCE {
		plsdSesssionContextRowColumnLookupFailLevelName	DisplayString,
		plsdSesssionContextRowColumnLookupFailLevelVal	Counter64,
		plsdSesssionContextRowColumnLookupFailLevelMom	CounterBasedGauge64,
		plsdSesssionContextRowColumnLookupFailLevelMax	CounterBasedGauge64
	}

plsdSesssionContextRowColumnLookupFailLevelName OBJECT-TYPE
	SYNTAX      DisplayString
	MAX-ACCESS  not-accessible
	STATUS      current
	DESCRIPTION
	"Table entry display string for plsdSesssionContextRowColumnLookupFail"
	::={plsdSesssionContextRowColumnLookupFailLevelEntry 1}

plsdSesssionContextRowColumnLookupFailLevelVal OBJECT-TYPE
	SYNTAX	 Counter64
	MAX-ACCESS  read-only
	STATUS      current
	DESCRIPTION
	"Table entry attribute for plsdSesssionContextRowColumnLookupFail"
	::={plsdSesssionContextRowColumnLookupFailLevelEntry 2}

plsdSesssionContextRowColumnLookupFailLevelMom OBJECT-TYPE
	SYNTAX	 CounterBasedGauge64
	MAX-ACCESS  read-only
	STATUS      current
	DESCRIPTION
	"Table entry attribute for plsdSesssionContextRowColumnLookupFail"
	::={plsdSesssionContextRowColumnLookupFailLevelEntry 3}

plsdSesssionContextRowColumnLookupFailLevelMax OBJECT-TYPE
	SYNTAX	 CounterBasedGauge64
	MAX-ACCESS  read-only
	STATUS      current
	DESCRIPTION
	"Table entry attribute for plsdSesssionContextRowColumnLookupFail"
	::={plsdSesssionContextRowColumnLookupFailLevelEntry 4}


plsdSessionContextRemovesbeforeAdds	OBJECT IDENTIFIER ::={plsd 102}

plsdSessionContextRemovesbeforeAddsVal	OBJECT-TYPE
	SYNTAX	 Counter64
	MAX-ACCESS read-only
	STATUS current
	DESCRIPTION "Session Context: Row removes received before Row Added"

	::={plsdSessionContextRemovesbeforeAdds 1}

plsdSessionContextRemovesbeforeAddsMom	OBJECT-TYPE
	SYNTAX	 CounterBasedGauge64
	MAX-ACCESS read-only
	STATUS current
	DESCRIPTION "Session Context: Row removes received before Row Added"

	::={plsdSessionContextRemovesbeforeAdds 2}

plsdSessionContextRemovesbeforeAddsMax	OBJECT-TYPE
	SYNTAX	 CounterBasedGauge64
	MAX-ACCESS read-only
	STATUS current
	DESCRIPTION "Session Context: Row removes received before Row Added"

	::={plsdSessionContextRemovesbeforeAdds 3}

plsdSessionContextRemovesbeforeAddsLevelTable OBJECT-TYPE
	SYNTAX      SEQUENCE OF PlsdSessionContextRemovesbeforeAddsLevelEntry
	MAX-ACCESS  not-accessible
	STATUS      current
	DESCRIPTION
	"Table for plsdSessionContextRemovesbeforeAdds"
	::={plsdSessionContextRemovesbeforeAdds 4}

plsdSessionContextRemovesbeforeAddsLevelEntry OBJECT-TYPE
	SYNTAX      PlsdSessionContextRemovesbeforeAddsLevelEntry
	MAX-ACCESS  not-accessible
	STATUS      current
	DESCRIPTION
	"Table entry for plsdSessionContextRemovesbeforeAdds"
	INDEX { plsdSessionContextRemovesbeforeAddsLevelName }
	::={plsdSessionContextRemovesbeforeAddsLevelTable 1}

PlsdSessionContextRemovesbeforeAddsLevelEntry ::=
	SEQUENCE {
		plsdSessionContextRemovesbeforeAddsLevelName	DisplayString,
		plsdSessionContextRemovesbeforeAddsLevelVal	Counter64,
		plsdSessionContextRemovesbeforeAddsLevelMom	CounterBasedGauge64,
		plsdSessionContextRemovesbeforeAddsLevelMax	CounterBasedGauge64
	}

plsdSessionContextRemovesbeforeAddsLevelName OBJECT-TYPE
	SYNTAX      DisplayString
	MAX-ACCESS  not-accessible
	STATUS      current
	DESCRIPTION
	"Table entry display string for plsdSessionContextRemovesbeforeAdds"
	::={plsdSessionContextRemovesbeforeAddsLevelEntry 1}

plsdSessionContextRemovesbeforeAddsLevelVal OBJECT-TYPE
	SYNTAX	 Counter64
	MAX-ACCESS  read-only
	STATUS      current
	DESCRIPTION
	"Table entry attribute for plsdSessionContextRemovesbeforeAdds"
	::={plsdSessionContextRemovesbeforeAddsLevelEntry 2}

plsdSessionContextRemovesbeforeAddsLevelMom OBJECT-TYPE
	SYNTAX	 CounterBasedGauge64
	MAX-ACCESS  read-only
	STATUS      current
	DESCRIPTION
	"Table entry attribute for plsdSessionContextRemovesbeforeAdds"
	::={plsdSessionContextRemovesbeforeAddsLevelEntry 3}

plsdSessionContextRemovesbeforeAddsLevelMax OBJECT-TYPE
	SYNTAX	 CounterBasedGauge64
	MAX-ACCESS  read-only
	STATUS      current
	DESCRIPTION
	"Table entry attribute for plsdSessionContextRemovesbeforeAdds"
	::={plsdSessionContextRemovesbeforeAddsLevelEntry 4}


plsdStringCacheHashedItems	OBJECT IDENTIFIER ::={plsd 103}

plsdStringCacheHashedItemsVal	OBJECT-TYPE
	SYNTAX	 CounterBasedGauge64
	MAX-ACCESS read-only
	STATUS current
	DESCRIPTION "String Cache, Hashed strings"

	::={plsdStringCacheHashedItems 1}

plsdStringCacheHashedItemsMax	OBJECT-TYPE
	SYNTAX	 CounterBasedGauge64
	MAX-ACCESS read-only
	STATUS current
	DESCRIPTION "String Cache, Hashed strings"

	::={plsdStringCacheHashedItems 3}

plsdStringCacheHashedItemsLevelTable OBJECT-TYPE
	SYNTAX      SEQUENCE OF PlsdStringCacheHashedItemsLevelEntry
	MAX-ACCESS  not-accessible
	STATUS      current
	DESCRIPTION
	"Table for plsdStringCacheHashedItems"
	::={plsdStringCacheHashedItems 4}

plsdStringCacheHashedItemsLevelEntry OBJECT-TYPE
	SYNTAX      PlsdStringCacheHashedItemsLevelEntry
	MAX-ACCESS  not-accessible
	STATUS      current
	DESCRIPTION
	"Table entry for plsdStringCacheHashedItems"
	INDEX { plsdStringCacheHashedItemsLevelName }
	::={plsdStringCacheHashedItemsLevelTable 1}

PlsdStringCacheHashedItemsLevelEntry ::=
	SEQUENCE {
		plsdStringCacheHashedItemsLevelName	DisplayString,
		plsdStringCacheHashedItemsLevelVal	CounterBasedGauge64,
		plsdStringCacheHashedItemsLevelMax	CounterBasedGauge64
	}

plsdStringCacheHashedItemsLevelName OBJECT-TYPE
	SYNTAX      DisplayString
	MAX-ACCESS  not-accessible
	STATUS      current
	DESCRIPTION
	"Table entry display string for plsdStringCacheHashedItems"
	::={plsdStringCacheHashedItemsLevelEntry 1}

plsdStringCacheHashedItemsLevelVal OBJECT-TYPE
	SYNTAX	 CounterBasedGauge64
	MAX-ACCESS  read-only
	STATUS      current
	DESCRIPTION
	"Table entry attribute for plsdStringCacheHashedItems"
	::={plsdStringCacheHashedItemsLevelEntry 2}

plsdStringCacheHashedItemsLevelMax OBJECT-TYPE
	SYNTAX	 CounterBasedGauge64
	MAX-ACCESS  read-only
	STATUS      current
	DESCRIPTION
	"Table entry attribute for plsdStringCacheHashedItems"
	::={plsdStringCacheHashedItemsLevelEntry 4}


plsdValueHashes	OBJECT IDENTIFIER ::={plsd 104}

plsdValueHashesVal	OBJECT-TYPE
	SYNTAX	 Counter64
	MAX-ACCESS read-only
	STATUS current
	DESCRIPTION "Value Hashes"

	::={plsdValueHashes 1}

plsdValueHashesMom	OBJECT-TYPE
	SYNTAX	 CounterBasedGauge64
	MAX-ACCESS read-only
	STATUS current
	DESCRIPTION "Value Hashes"

	::={plsdValueHashes 2}

plsdValueHashesMax	OBJECT-TYPE
	SYNTAX	 CounterBasedGauge64
	MAX-ACCESS read-only
	STATUS current
	DESCRIPTION "Value Hashes"

	::={plsdValueHashes 3}

plsdValueHashesLevelTable OBJECT-TYPE
	SYNTAX      SEQUENCE OF PlsdValueHashesLevelEntry
	MAX-ACCESS  not-accessible
	STATUS      current
	DESCRIPTION
	"Table for plsdValueHashes"
	::={plsdValueHashes 4}

plsdValueHashesLevelEntry OBJECT-TYPE
	SYNTAX      PlsdValueHashesLevelEntry
	MAX-ACCESS  not-accessible
	STATUS      current
	DESCRIPTION
	"Table entry for plsdValueHashes"
	INDEX { plsdValueHashesLevelName }
	::={plsdValueHashesLevelTable 1}

PlsdValueHashesLevelEntry ::=
	SEQUENCE {
		plsdValueHashesLevelName	DisplayString,
		plsdValueHashesLevelVal	Counter64,
		plsdValueHashesLevelMom	CounterBasedGauge64,
		plsdValueHashesLevelMax	CounterBasedGauge64
	}

plsdValueHashesLevelName OBJECT-TYPE
	SYNTAX      DisplayString
	MAX-ACCESS  not-accessible
	STATUS      current
	DESCRIPTION
	"Table entry display string for plsdValueHashes"
	::={plsdValueHashesLevelEntry 1}

plsdValueHashesLevelVal OBJECT-TYPE
	SYNTAX	 Counter64
	MAX-ACCESS  read-only
	STATUS      current
	DESCRIPTION
	"Table entry attribute for plsdValueHashes"
	::={plsdValueHashesLevelEntry 2}

plsdValueHashesLevelMom OBJECT-TYPE
	SYNTAX	 CounterBasedGauge64
	MAX-ACCESS  read-only
	STATUS      current
	DESCRIPTION
	"Table entry attribute for plsdValueHashes"
	::={plsdValueHashesLevelEntry 3}

plsdValueHashesLevelMax OBJECT-TYPE
	SYNTAX	 CounterBasedGauge64
	MAX-ACCESS  read-only
	STATUS      current
	DESCRIPTION
	"Table entry attribute for plsdValueHashes"
	::={plsdValueHashesLevelEntry 4}


plsw	OBJECT IDENTIFIER ::={sysdiag 137}

plswDatasetStart	OBJECT IDENTIFIER ::={plsw 1}

plswDatasetStartVal	OBJECT-TYPE
	SYNTAX	 DateAndTime
	MAX-ACCESS read-only
	STATUS current
	DESCRIPTION "Dataset, Begin"

	::={plswDatasetStart 1}

plswDatasetStartLevelTable OBJECT-TYPE
	SYNTAX      SEQUENCE OF PlswDatasetStartLevelEntry
	MAX-ACCESS  not-accessible
	STATUS      current
	DESCRIPTION
	"Table for plswDatasetStart"
	::={plswDatasetStart 2}

plswDatasetStartLevelEntry OBJECT-TYPE
	SYNTAX      PlswDatasetStartLevelEntry
	MAX-ACCESS  not-accessible
	STATUS      current
	DESCRIPTION
	"Table entry for plswDatasetStart"
	INDEX { plswDatasetStartLevelName }
	::={plswDatasetStartLevelTable 1}

PlswDatasetStartLevelEntry ::=
	SEQUENCE {
		plswDatasetStartLevelName	DisplayString,
		plswDatasetStartLevelVal	DateAndTime
	}

plswDatasetStartLevelName OBJECT-TYPE
	SYNTAX      DisplayString
	MAX-ACCESS  not-accessible
	STATUS      current
	DESCRIPTION
	"Table entry display string for plswDatasetStart"
	::={plswDatasetStartLevelEntry 1}

plswDatasetStartLevelVal OBJECT-TYPE
	SYNTAX	 DateAndTime
	MAX-ACCESS  read-only
	STATUS      current
	DESCRIPTION
	"Table entry attribute for plswDatasetStart"
	::={plswDatasetStartLevelEntry 2}


plswDatasetEnd	OBJECT IDENTIFIER ::={plsw 2}

plswDatasetEndVal	OBJECT-TYPE
	SYNTAX	 DateAndTime
	MAX-ACCESS read-only
	STATUS current
	DESCRIPTION "Dataset, End"

	::={plswDatasetEnd 1}

plswDatasetEndLevelTable OBJECT-TYPE
	SYNTAX      SEQUENCE OF PlswDatasetEndLevelEntry
	MAX-ACCESS  not-accessible
	STATUS      current
	DESCRIPTION
	"Table for plswDatasetEnd"
	::={plswDatasetEnd 2}

plswDatasetEndLevelEntry OBJECT-TYPE
	SYNTAX      PlswDatasetEndLevelEntry
	MAX-ACCESS  not-accessible
	STATUS      current
	DESCRIPTION
	"Table entry for plswDatasetEnd"
	INDEX { plswDatasetEndLevelName }
	::={plswDatasetEndLevelTable 1}

PlswDatasetEndLevelEntry ::=
	SEQUENCE {
		plswDatasetEndLevelName	DisplayString,
		plswDatasetEndLevelVal	DateAndTime
	}

plswDatasetEndLevelName OBJECT-TYPE
	SYNTAX      DisplayString
	MAX-ACCESS  not-accessible
	STATUS      current
	DESCRIPTION
	"Table entry display string for plswDatasetEnd"
	::={plswDatasetEndLevelEntry 1}

plswDatasetEndLevelVal OBJECT-TYPE
	SYNTAX	 DateAndTime
	MAX-ACCESS  read-only
	STATUS      current
	DESCRIPTION
	"Table entry attribute for plswDatasetEnd"
	::={plswDatasetEndLevelEntry 2}


plswSessions	OBJECT IDENTIFIER ::={plsw 3}

plswSessionsVal	OBJECT-TYPE
	SYNTAX	 CounterBasedGauge64
	MAX-ACCESS read-only
	STATUS current
	DESCRIPTION "Dataset, Sessions"

	::={plswSessions 1}

plswSessionsMax	OBJECT-TYPE
	SYNTAX	 CounterBasedGauge64
	MAX-ACCESS read-only
	STATUS current
	DESCRIPTION "Dataset, Sessions"

	::={plswSessions 3}

plswSessionsLevelTable OBJECT-TYPE
	SYNTAX      SEQUENCE OF PlswSessionsLevelEntry
	MAX-ACCESS  not-accessible
	STATUS      current
	DESCRIPTION
	"Table for plswSessions"
	::={plswSessions 4}

plswSessionsLevelEntry OBJECT-TYPE
	SYNTAX      PlswSessionsLevelEntry
	MAX-ACCESS  not-accessible
	STATUS      current
	DESCRIPTION
	"Table entry for plswSessions"
	INDEX { plswSessionsLevelName }
	::={plswSessionsLevelTable 1}

PlswSessionsLevelEntry ::=
	SEQUENCE {
		plswSessionsLevelName	DisplayString,
		plswSessionsLevelVal	CounterBasedGauge64,
		plswSessionsLevelMax	CounterBasedGauge64
	}

plswSessionsLevelName OBJECT-TYPE
	SYNTAX      DisplayString
	MAX-ACCESS  not-accessible
	STATUS      current
	DESCRIPTION
	"Table entry display string for plswSessions"
	::={plswSessionsLevelEntry 1}

plswSessionsLevelVal OBJECT-TYPE
	SYNTAX	 CounterBasedGauge64
	MAX-ACCESS  read-only
	STATUS      current
	DESCRIPTION
	"Table entry attribute for plswSessions"
	::={plswSessionsLevelEntry 2}

plswSessionsLevelMax OBJECT-TYPE
	SYNTAX	 CounterBasedGauge64
	MAX-ACCESS  read-only
	STATUS      current
	DESCRIPTION
	"Table entry attribute for plswSessions"
	::={plswSessionsLevelEntry 4}


plswValues	OBJECT IDENTIFIER ::={plsw 4}

plswValuesVal	OBJECT-TYPE
	SYNTAX	 CounterBasedGauge64
	MAX-ACCESS read-only
	STATUS current
	DESCRIPTION "Dataset Values"

	::={plswValues 1}

plswValuesMax	OBJECT-TYPE
	SYNTAX	 CounterBasedGauge64
	MAX-ACCESS read-only
	STATUS current
	DESCRIPTION "Dataset Values"

	::={plswValues 3}

plswValuesLevelTable OBJECT-TYPE
	SYNTAX      SEQUENCE OF PlswValuesLevelEntry
	MAX-ACCESS  not-accessible
	STATUS      current
	DESCRIPTION
	"Table for plswValues"
	::={plswValues 4}

plswValuesLevelEntry OBJECT-TYPE
	SYNTAX      PlswValuesLevelEntry
	MAX-ACCESS  not-accessible
	STATUS      current
	DESCRIPTION
	"Table entry for plswValues"
	INDEX { plswValuesLevelName }
	::={plswValuesLevelTable 1}

PlswValuesLevelEntry ::=
	SEQUENCE {
		plswValuesLevelName	DisplayString,
		plswValuesLevelVal	CounterBasedGauge64,
		plswValuesLevelMax	CounterBasedGauge64
	}

plswValuesLevelName OBJECT-TYPE
	SYNTAX      DisplayString
	MAX-ACCESS  not-accessible
	STATUS      current
	DESCRIPTION
	"Table entry display string for plswValues"
	::={plswValuesLevelEntry 1}

plswValuesLevelVal OBJECT-TYPE
	SYNTAX	 CounterBasedGauge64
	MAX-ACCESS  read-only
	STATUS      current
	DESCRIPTION
	"Table entry attribute for plswValues"
	::={plswValuesLevelEntry 2}

plswValuesLevelMax OBJECT-TYPE
	SYNTAX	 CounterBasedGauge64
	MAX-ACCESS  read-only
	STATUS      current
	DESCRIPTION
	"Table entry attribute for plswValues"
	::={plswValuesLevelEntry 4}


plswValuesDropped1	OBJECT IDENTIFIER ::={plsw 5}

plswValuesDropped1Val	OBJECT-TYPE
	SYNTAX	 CounterBasedGauge64
	MAX-ACCESS read-only
	STATUS current
	DESCRIPTION "Dataset Values Dropped (cache exhausted)"

	::={plswValuesDropped1 1}

plswValuesDropped1Max	OBJECT-TYPE
	SYNTAX	 CounterBasedGauge64
	MAX-ACCESS read-only
	STATUS current
	DESCRIPTION "Dataset Values Dropped (cache exhausted)"

	::={plswValuesDropped1 3}

plswValuesDropped1LevelTable OBJECT-TYPE
	SYNTAX      SEQUENCE OF PlswValuesDropped1LevelEntry
	MAX-ACCESS  not-accessible
	STATUS      current
	DESCRIPTION
	"Table for plswValuesDropped1"
	::={plswValuesDropped1 4}

plswValuesDropped1LevelEntry OBJECT-TYPE
	SYNTAX      PlswValuesDropped1LevelEntry
	MAX-ACCESS  not-accessible
	STATUS      current
	DESCRIPTION
	"Table entry for plswValuesDropped1"
	INDEX { plswValuesDropped1LevelName }
	::={plswValuesDropped1LevelTable 1}

PlswValuesDropped1LevelEntry ::=
	SEQUENCE {
		plswValuesDropped1LevelName	DisplayString,
		plswValuesDropped1LevelVal	CounterBasedGauge64,
		plswValuesDropped1LevelMax	CounterBasedGauge64
	}

plswValuesDropped1LevelName OBJECT-TYPE
	SYNTAX      DisplayString
	MAX-ACCESS  not-accessible
	STATUS      current
	DESCRIPTION
	"Table entry display string for plswValuesDropped1"
	::={plswValuesDropped1LevelEntry 1}

plswValuesDropped1LevelVal OBJECT-TYPE
	SYNTAX	 CounterBasedGauge64
	MAX-ACCESS  read-only
	STATUS      current
	DESCRIPTION
	"Table entry attribute for plswValuesDropped1"
	::={plswValuesDropped1LevelEntry 2}

plswValuesDropped1LevelMax OBJECT-TYPE
	SYNTAX	 CounterBasedGauge64
	MAX-ACCESS  read-only
	STATUS      current
	DESCRIPTION
	"Table entry attribute for plswValuesDropped1"
	::={plswValuesDropped1LevelEntry 4}


plswValuesDropped2	OBJECT IDENTIFIER ::={plsw 6}

plswValuesDropped2Val	OBJECT-TYPE
	SYNTAX	 CounterBasedGauge64
	MAX-ACCESS read-only
	STATUS current
	DESCRIPTION "Dataset Values Dropped (malformed name)"

	::={plswValuesDropped2 1}

plswValuesDropped2Max	OBJECT-TYPE
	SYNTAX	 CounterBasedGauge64
	MAX-ACCESS read-only
	STATUS current
	DESCRIPTION "Dataset Values Dropped (malformed name)"

	::={plswValuesDropped2 3}

plswValuesDropped2LevelTable OBJECT-TYPE
	SYNTAX      SEQUENCE OF PlswValuesDropped2LevelEntry
	MAX-ACCESS  not-accessible
	STATUS      current
	DESCRIPTION
	"Table for plswValuesDropped2"
	::={plswValuesDropped2 4}

plswValuesDropped2LevelEntry OBJECT-TYPE
	SYNTAX      PlswValuesDropped2LevelEntry
	MAX-ACCESS  not-accessible
	STATUS      current
	DESCRIPTION
	"Table entry for plswValuesDropped2"
	INDEX { plswValuesDropped2LevelName }
	::={plswValuesDropped2LevelTable 1}

PlswValuesDropped2LevelEntry ::=
	SEQUENCE {
		plswValuesDropped2LevelName	DisplayString,
		plswValuesDropped2LevelVal	CounterBasedGauge64,
		plswValuesDropped2LevelMax	CounterBasedGauge64
	}

plswValuesDropped2LevelName OBJECT-TYPE
	SYNTAX      DisplayString
	MAX-ACCESS  not-accessible
	STATUS      current
	DESCRIPTION
	"Table entry display string for plswValuesDropped2"
	::={plswValuesDropped2LevelEntry 1}

plswValuesDropped2LevelVal OBJECT-TYPE
	SYNTAX	 CounterBasedGauge64
	MAX-ACCESS  read-only
	STATUS      current
	DESCRIPTION
	"Table entry attribute for plswValuesDropped2"
	::={plswValuesDropped2LevelEntry 2}

plswValuesDropped2LevelMax OBJECT-TYPE
	SYNTAX	 CounterBasedGauge64
	MAX-ACCESS  read-only
	STATUS      current
	DESCRIPTION
	"Table entry attribute for plswValuesDropped2"
	::={plswValuesDropped2LevelEntry 4}


plswValuesDropped3	OBJECT IDENTIFIER ::={plsw 7}

plswValuesDropped3Val	OBJECT-TYPE
	SYNTAX	 CounterBasedGauge64
	MAX-ACCESS read-only
	STATUS current
	DESCRIPTION "Dataset Values Dropped (Global Index exhausted)"

	::={plswValuesDropped3 1}

plswValuesDropped3Max	OBJECT-TYPE
	SYNTAX	 CounterBasedGauge64
	MAX-ACCESS read-only
	STATUS current
	DESCRIPTION "Dataset Values Dropped (Global Index exhausted)"

	::={plswValuesDropped3 3}

plswValuesDropped3LevelTable OBJECT-TYPE
	SYNTAX      SEQUENCE OF PlswValuesDropped3LevelEntry
	MAX-ACCESS  not-accessible
	STATUS      current
	DESCRIPTION
	"Table for plswValuesDropped3"
	::={plswValuesDropped3 4}

plswValuesDropped3LevelEntry OBJECT-TYPE
	SYNTAX      PlswValuesDropped3LevelEntry
	MAX-ACCESS  not-accessible
	STATUS      current
	DESCRIPTION
	"Table entry for plswValuesDropped3"
	INDEX { plswValuesDropped3LevelName }
	::={plswValuesDropped3LevelTable 1}

PlswValuesDropped3LevelEntry ::=
	SEQUENCE {
		plswValuesDropped3LevelName	DisplayString,
		plswValuesDropped3LevelVal	CounterBasedGauge64,
		plswValuesDropped3LevelMax	CounterBasedGauge64
	}

plswValuesDropped3LevelName OBJECT-TYPE
	SYNTAX      DisplayString
	MAX-ACCESS  not-accessible
	STATUS      current
	DESCRIPTION
	"Table entry display string for plswValuesDropped3"
	::={plswValuesDropped3LevelEntry 1}

plswValuesDropped3LevelVal OBJECT-TYPE
	SYNTAX	 CounterBasedGauge64
	MAX-ACCESS  read-only
	STATUS      current
	DESCRIPTION
	"Table entry attribute for plswValuesDropped3"
	::={plswValuesDropped3LevelEntry 2}

plswValuesDropped3LevelMax OBJECT-TYPE
	SYNTAX	 CounterBasedGauge64
	MAX-ACCESS  read-only
	STATUS      current
	DESCRIPTION
	"Table entry attribute for plswValuesDropped3"
	::={plswValuesDropped3LevelEntry 4}


plswValuesDropped4	OBJECT IDENTIFIER ::={plsw 8}

plswValuesDropped4Val	OBJECT-TYPE
	SYNTAX	 CounterBasedGauge64
	MAX-ACCESS read-only
	STATUS current
	DESCRIPTION "Dataset Values Dropped (Symlink target not found)"

	::={plswValuesDropped4 1}

plswValuesDropped4Max	OBJECT-TYPE
	SYNTAX	 CounterBasedGauge64
	MAX-ACCESS read-only
	STATUS current
	DESCRIPTION "Dataset Values Dropped (Symlink target not found)"

	::={plswValuesDropped4 3}

plswValuesDropped4LevelTable OBJECT-TYPE
	SYNTAX      SEQUENCE OF PlswValuesDropped4LevelEntry
	MAX-ACCESS  not-accessible
	STATUS      current
	DESCRIPTION
	"Table for plswValuesDropped4"
	::={plswValuesDropped4 4}

plswValuesDropped4LevelEntry OBJECT-TYPE
	SYNTAX      PlswValuesDropped4LevelEntry
	MAX-ACCESS  not-accessible
	STATUS      current
	DESCRIPTION
	"Table entry for plswValuesDropped4"
	INDEX { plswValuesDropped4LevelName }
	::={plswValuesDropped4LevelTable 1}

PlswValuesDropped4LevelEntry ::=
	SEQUENCE {
		plswValuesDropped4LevelName	DisplayString,
		plswValuesDropped4LevelVal	CounterBasedGauge64,
		plswValuesDropped4LevelMax	CounterBasedGauge64
	}

plswValuesDropped4LevelName OBJECT-TYPE
	SYNTAX      DisplayString
	MAX-ACCESS  not-accessible
	STATUS      current
	DESCRIPTION
	"Table entry display string for plswValuesDropped4"
	::={plswValuesDropped4LevelEntry 1}

plswValuesDropped4LevelVal OBJECT-TYPE
	SYNTAX	 CounterBasedGauge64
	MAX-ACCESS  read-only
	STATUS      current
	DESCRIPTION
	"Table entry attribute for plswValuesDropped4"
	::={plswValuesDropped4LevelEntry 2}

plswValuesDropped4LevelMax OBJECT-TYPE
	SYNTAX	 CounterBasedGauge64
	MAX-ACCESS  read-only
	STATUS      current
	DESCRIPTION
	"Table entry attribute for plswValuesDropped4"
	::={plswValuesDropped4LevelEntry 4}


plswNewglobal	OBJECT IDENTIFIER ::={plsw 9}

plswNewglobalVal	OBJECT-TYPE
	SYNTAX	 CounterBasedGauge64
	MAX-ACCESS read-only
	STATUS current
	DESCRIPTION "Dataset values, New Global Indexes"

	::={plswNewglobal 1}

plswNewglobalMax	OBJECT-TYPE
	SYNTAX	 CounterBasedGauge64
	MAX-ACCESS read-only
	STATUS current
	DESCRIPTION "Dataset values, New Global Indexes"

	::={plswNewglobal 3}

plswNewglobalLevelTable OBJECT-TYPE
	SYNTAX      SEQUENCE OF PlswNewglobalLevelEntry
	MAX-ACCESS  not-accessible
	STATUS      current
	DESCRIPTION
	"Table for plswNewglobal"
	::={plswNewglobal 4}

plswNewglobalLevelEntry OBJECT-TYPE
	SYNTAX      PlswNewglobalLevelEntry
	MAX-ACCESS  not-accessible
	STATUS      current
	DESCRIPTION
	"Table entry for plswNewglobal"
	INDEX { plswNewglobalLevelName }
	::={plswNewglobalLevelTable 1}

PlswNewglobalLevelEntry ::=
	SEQUENCE {
		plswNewglobalLevelName	DisplayString,
		plswNewglobalLevelVal	CounterBasedGauge64,
		plswNewglobalLevelMax	CounterBasedGauge64
	}

plswNewglobalLevelName OBJECT-TYPE
	SYNTAX      DisplayString
	MAX-ACCESS  not-accessible
	STATUS      current
	DESCRIPTION
	"Table entry display string for plswNewglobal"
	::={plswNewglobalLevelEntry 1}

plswNewglobalLevelVal OBJECT-TYPE
	SYNTAX	 CounterBasedGauge64
	MAX-ACCESS  read-only
	STATUS      current
	DESCRIPTION
	"Table entry attribute for plswNewglobal"
	::={plswNewglobalLevelEntry 2}

plswNewglobalLevelMax OBJECT-TYPE
	SYNTAX	 CounterBasedGauge64
	MAX-ACCESS  read-only
	STATUS      current
	DESCRIPTION
	"Table entry attribute for plswNewglobal"
	::={plswNewglobalLevelEntry 4}


plswNewcoll	OBJECT IDENTIFIER ::={plsw 10}

plswNewcollVal	OBJECT-TYPE
	SYNTAX	 CounterBasedGauge64
	MAX-ACCESS read-only
	STATUS current
	DESCRIPTION "Dataset values, New Global collisions"

	::={plswNewcoll 1}

plswNewcollMax	OBJECT-TYPE
	SYNTAX	 CounterBasedGauge64
	MAX-ACCESS read-only
	STATUS current
	DESCRIPTION "Dataset values, New Global collisions"

	::={plswNewcoll 3}

plswNewcollLevelTable OBJECT-TYPE
	SYNTAX      SEQUENCE OF PlswNewcollLevelEntry
	MAX-ACCESS  not-accessible
	STATUS      current
	DESCRIPTION
	"Table for plswNewcoll"
	::={plswNewcoll 4}

plswNewcollLevelEntry OBJECT-TYPE
	SYNTAX      PlswNewcollLevelEntry
	MAX-ACCESS  not-accessible
	STATUS      current
	DESCRIPTION
	"Table entry for plswNewcoll"
	INDEX { plswNewcollLevelName }
	::={plswNewcollLevelTable 1}

PlswNewcollLevelEntry ::=
	SEQUENCE {
		plswNewcollLevelName	DisplayString,
		plswNewcollLevelVal	CounterBasedGauge64,
		plswNewcollLevelMax	CounterBasedGauge64
	}

plswNewcollLevelName OBJECT-TYPE
	SYNTAX      DisplayString
	MAX-ACCESS  not-accessible
	STATUS      current
	DESCRIPTION
	"Table entry display string for plswNewcoll"
	::={plswNewcollLevelEntry 1}

plswNewcollLevelVal OBJECT-TYPE
	SYNTAX	 CounterBasedGauge64
	MAX-ACCESS  read-only
	STATUS      current
	DESCRIPTION
	"Table entry attribute for plswNewcoll"
	::={plswNewcollLevelEntry 2}

plswNewcollLevelMax OBJECT-TYPE
	SYNTAX	 CounterBasedGauge64
	MAX-ACCESS  read-only
	STATUS      current
	DESCRIPTION
	"Table entry attribute for plswNewcoll"
	::={plswNewcollLevelEntry 4}


plswNewdaily	OBJECT IDENTIFIER ::={plsw 11}

plswNewdailyVal	OBJECT-TYPE
	SYNTAX	 CounterBasedGauge64
	MAX-ACCESS read-only
	STATUS current
	DESCRIPTION "Dataset values, New Daily Indexes"

	::={plswNewdaily 1}

plswNewdailyMax	OBJECT-TYPE
	SYNTAX	 CounterBasedGauge64
	MAX-ACCESS read-only
	STATUS current
	DESCRIPTION "Dataset values, New Daily Indexes"

	::={plswNewdaily 3}

plswNewdailyLevelTable OBJECT-TYPE
	SYNTAX      SEQUENCE OF PlswNewdailyLevelEntry
	MAX-ACCESS  not-accessible
	STATUS      current
	DESCRIPTION
	"Table for plswNewdaily"
	::={plswNewdaily 4}

plswNewdailyLevelEntry OBJECT-TYPE
	SYNTAX      PlswNewdailyLevelEntry
	MAX-ACCESS  not-accessible
	STATUS      current
	DESCRIPTION
	"Table entry for plswNewdaily"
	INDEX { plswNewdailyLevelName }
	::={plswNewdailyLevelTable 1}

PlswNewdailyLevelEntry ::=
	SEQUENCE {
		plswNewdailyLevelName	DisplayString,
		plswNewdailyLevelVal	CounterBasedGauge64,
		plswNewdailyLevelMax	CounterBasedGauge64
	}

plswNewdailyLevelName OBJECT-TYPE
	SYNTAX      DisplayString
	MAX-ACCESS  not-accessible
	STATUS      current
	DESCRIPTION
	"Table entry display string for plswNewdaily"
	::={plswNewdailyLevelEntry 1}

plswNewdailyLevelVal OBJECT-TYPE
	SYNTAX	 CounterBasedGauge64
	MAX-ACCESS  read-only
	STATUS      current
	DESCRIPTION
	"Table entry attribute for plswNewdaily"
	::={plswNewdailyLevelEntry 2}

plswNewdailyLevelMax OBJECT-TYPE
	SYNTAX	 CounterBasedGauge64
	MAX-ACCESS  read-only
	STATUS      current
	DESCRIPTION
	"Table entry attribute for plswNewdaily"
	::={plswNewdailyLevelEntry 4}


plswTupdate	OBJECT IDENTIFIER ::={plsw 12}

plswTupdateVal	OBJECT-TYPE
	SYNTAX	 CounterBasedGauge64
	MAX-ACCESS read-only
	STATUS current
	DESCRIPTION "Dataset values, Updates (Totals)"

	::={plswTupdate 1}

plswTupdateMax	OBJECT-TYPE
	SYNTAX	 CounterBasedGauge64
	MAX-ACCESS read-only
	STATUS current
	DESCRIPTION "Dataset values, Updates (Totals)"

	::={plswTupdate 3}

plswTupdateLevelTable OBJECT-TYPE
	SYNTAX      SEQUENCE OF PlswTupdateLevelEntry
	MAX-ACCESS  not-accessible
	STATUS      current
	DESCRIPTION
	"Table for plswTupdate"
	::={plswTupdate 4}

plswTupdateLevelEntry OBJECT-TYPE
	SYNTAX      PlswTupdateLevelEntry
	MAX-ACCESS  not-accessible
	STATUS      current
	DESCRIPTION
	"Table entry for plswTupdate"
	INDEX { plswTupdateLevelName }
	::={plswTupdateLevelTable 1}

PlswTupdateLevelEntry ::=
	SEQUENCE {
		plswTupdateLevelName	DisplayString,
		plswTupdateLevelVal	CounterBasedGauge64,
		plswTupdateLevelMax	CounterBasedGauge64
	}

plswTupdateLevelName OBJECT-TYPE
	SYNTAX      DisplayString
	MAX-ACCESS  not-accessible
	STATUS      current
	DESCRIPTION
	"Table entry display string for plswTupdate"
	::={plswTupdateLevelEntry 1}

plswTupdateLevelVal OBJECT-TYPE
	SYNTAX	 CounterBasedGauge64
	MAX-ACCESS  read-only
	STATUS      current
	DESCRIPTION
	"Table entry attribute for plswTupdate"
	::={plswTupdateLevelEntry 2}

plswTupdateLevelMax OBJECT-TYPE
	SYNTAX	 CounterBasedGauge64
	MAX-ACCESS  read-only
	STATUS      current
	DESCRIPTION
	"Table entry attribute for plswTupdate"
	::={plswTupdateLevelEntry 4}


plswGupdate	OBJECT IDENTIFIER ::={plsw 13}

plswGupdateVal	OBJECT-TYPE
	SYNTAX	 CounterBasedGauge64
	MAX-ACCESS read-only
	STATUS current
	DESCRIPTION "Dataset values, Updates (Graphs)"

	::={plswGupdate 1}

plswGupdateMax	OBJECT-TYPE
	SYNTAX	 CounterBasedGauge64
	MAX-ACCESS read-only
	STATUS current
	DESCRIPTION "Dataset values, Updates (Graphs)"

	::={plswGupdate 3}

plswGupdateLevelTable OBJECT-TYPE
	SYNTAX      SEQUENCE OF PlswGupdateLevelEntry
	MAX-ACCESS  not-accessible
	STATUS      current
	DESCRIPTION
	"Table for plswGupdate"
	::={plswGupdate 4}

plswGupdateLevelEntry OBJECT-TYPE
	SYNTAX      PlswGupdateLevelEntry
	MAX-ACCESS  not-accessible
	STATUS      current
	DESCRIPTION
	"Table entry for plswGupdate"
	INDEX { plswGupdateLevelName }
	::={plswGupdateLevelTable 1}

PlswGupdateLevelEntry ::=
	SEQUENCE {
		plswGupdateLevelName	DisplayString,
		plswGupdateLevelVal	CounterBasedGauge64,
		plswGupdateLevelMax	CounterBasedGauge64
	}

plswGupdateLevelName OBJECT-TYPE
	SYNTAX      DisplayString
	MAX-ACCESS  not-accessible
	STATUS      current
	DESCRIPTION
	"Table entry display string for plswGupdate"
	::={plswGupdateLevelEntry 1}

plswGupdateLevelVal OBJECT-TYPE
	SYNTAX	 CounterBasedGauge64
	MAX-ACCESS  read-only
	STATUS      current
	DESCRIPTION
	"Table entry attribute for plswGupdate"
	::={plswGupdateLevelEntry 2}

plswGupdateLevelMax OBJECT-TYPE
	SYNTAX	 CounterBasedGauge64
	MAX-ACCESS  read-only
	STATUS      current
	DESCRIPTION
	"Table entry attribute for plswGupdate"
	::={plswGupdateLevelEntry 4}


plswTimeDataset	OBJECT IDENTIFIER ::={plsw 14}

plswTimeDatasetVal	OBJECT-TYPE
	SYNTAX	 TimeTicks
	MAX-ACCESS read-only
	STATUS current
	DESCRIPTION "Dataset, Total Write time"

	::={plswTimeDataset 1}

plswTimeDatasetLevelTable OBJECT-TYPE
	SYNTAX      SEQUENCE OF PlswTimeDatasetLevelEntry
	MAX-ACCESS  not-accessible
	STATUS      current
	DESCRIPTION
	"Table for plswTimeDataset"
	::={plswTimeDataset 2}

plswTimeDatasetLevelEntry OBJECT-TYPE
	SYNTAX      PlswTimeDatasetLevelEntry
	MAX-ACCESS  not-accessible
	STATUS      current
	DESCRIPTION
	"Table entry for plswTimeDataset"
	INDEX { plswTimeDatasetLevelName }
	::={plswTimeDatasetLevelTable 1}

PlswTimeDatasetLevelEntry ::=
	SEQUENCE {
		plswTimeDatasetLevelName	DisplayString,
		plswTimeDatasetLevelVal	TimeTicks
	}

plswTimeDatasetLevelName OBJECT-TYPE
	SYNTAX      DisplayString
	MAX-ACCESS  not-accessible
	STATUS      current
	DESCRIPTION
	"Table entry display string for plswTimeDataset"
	::={plswTimeDatasetLevelEntry 1}

plswTimeDatasetLevelVal OBJECT-TYPE
	SYNTAX	 TimeTicks
	MAX-ACCESS  read-only
	STATUS      current
	DESCRIPTION
	"Table entry attribute for plswTimeDataset"
	::={plswTimeDatasetLevelEntry 2}


plswTimeGlobal	OBJECT IDENTIFIER ::={plsw 15}

plswTimeGlobalVal	OBJECT-TYPE
	SYNTAX	 TimeTicks
	MAX-ACCESS read-only
	STATUS current
	DESCRIPTION "Dataset, Time for Globals file I/O"

	::={plswTimeGlobal 1}

plswTimeGlobalLevelTable OBJECT-TYPE
	SYNTAX      SEQUENCE OF PlswTimeGlobalLevelEntry
	MAX-ACCESS  not-accessible
	STATUS      current
	DESCRIPTION
	"Table for plswTimeGlobal"
	::={plswTimeGlobal 2}

plswTimeGlobalLevelEntry OBJECT-TYPE
	SYNTAX      PlswTimeGlobalLevelEntry
	MAX-ACCESS  not-accessible
	STATUS      current
	DESCRIPTION
	"Table entry for plswTimeGlobal"
	INDEX { plswTimeGlobalLevelName }
	::={plswTimeGlobalLevelTable 1}

PlswTimeGlobalLevelEntry ::=
	SEQUENCE {
		plswTimeGlobalLevelName	DisplayString,
		plswTimeGlobalLevelVal	TimeTicks
	}

plswTimeGlobalLevelName OBJECT-TYPE
	SYNTAX      DisplayString
	MAX-ACCESS  not-accessible
	STATUS      current
	DESCRIPTION
	"Table entry display string for plswTimeGlobal"
	::={plswTimeGlobalLevelEntry 1}

plswTimeGlobalLevelVal OBJECT-TYPE
	SYNTAX	 TimeTicks
	MAX-ACCESS  read-only
	STATUS      current
	DESCRIPTION
	"Table entry attribute for plswTimeGlobal"
	::={plswTimeGlobalLevelEntry 2}


plswTimeDaily	OBJECT IDENTIFIER ::={plsw 16}

plswTimeDailyVal	OBJECT-TYPE
	SYNTAX	 TimeTicks
	MAX-ACCESS read-only
	STATUS current
	DESCRIPTION "Dataset, Time for Daily Index file I/O"

	::={plswTimeDaily 1}

plswTimeDailyLevelTable OBJECT-TYPE
	SYNTAX      SEQUENCE OF PlswTimeDailyLevelEntry
	MAX-ACCESS  not-accessible
	STATUS      current
	DESCRIPTION
	"Table for plswTimeDaily"
	::={plswTimeDaily 2}

plswTimeDailyLevelEntry OBJECT-TYPE
	SYNTAX      PlswTimeDailyLevelEntry
	MAX-ACCESS  not-accessible
	STATUS      current
	DESCRIPTION
	"Table entry for plswTimeDaily"
	INDEX { plswTimeDailyLevelName }
	::={plswTimeDailyLevelTable 1}

PlswTimeDailyLevelEntry ::=
	SEQUENCE {
		plswTimeDailyLevelName	DisplayString,
		plswTimeDailyLevelVal	TimeTicks
	}

plswTimeDailyLevelName OBJECT-TYPE
	SYNTAX      DisplayString
	MAX-ACCESS  not-accessible
	STATUS      current
	DESCRIPTION
	"Table entry display string for plswTimeDaily"
	::={plswTimeDailyLevelEntry 1}

plswTimeDailyLevelVal OBJECT-TYPE
	SYNTAX	 TimeTicks
	MAX-ACCESS  read-only
	STATUS      current
	DESCRIPTION
	"Table entry attribute for plswTimeDaily"
	::={plswTimeDailyLevelEntry 2}


plswTimeTotal	OBJECT IDENTIFIER ::={plsw 17}

plswTimeTotalVal	OBJECT-TYPE
	SYNTAX	 TimeTicks
	MAX-ACCESS read-only
	STATUS current
	DESCRIPTION "Dataset, Time for Totals file I/O"

	::={plswTimeTotal 1}

plswTimeTotalLevelTable OBJECT-TYPE
	SYNTAX      SEQUENCE OF PlswTimeTotalLevelEntry
	MAX-ACCESS  not-accessible
	STATUS      current
	DESCRIPTION
	"Table for plswTimeTotal"
	::={plswTimeTotal 2}

plswTimeTotalLevelEntry OBJECT-TYPE
	SYNTAX      PlswTimeTotalLevelEntry
	MAX-ACCESS  not-accessible
	STATUS      current
	DESCRIPTION
	"Table entry for plswTimeTotal"
	INDEX { plswTimeTotalLevelName }
	::={plswTimeTotalLevelTable 1}

PlswTimeTotalLevelEntry ::=
	SEQUENCE {
		plswTimeTotalLevelName	DisplayString,
		plswTimeTotalLevelVal	TimeTicks
	}

plswTimeTotalLevelName OBJECT-TYPE
	SYNTAX      DisplayString
	MAX-ACCESS  not-accessible
	STATUS      current
	DESCRIPTION
	"Table entry display string for plswTimeTotal"
	::={plswTimeTotalLevelEntry 1}

plswTimeTotalLevelVal OBJECT-TYPE
	SYNTAX	 TimeTicks
	MAX-ACCESS  read-only
	STATUS      current
	DESCRIPTION
	"Table entry attribute for plswTimeTotal"
	::={plswTimeTotalLevelEntry 2}


plswTimeGraph	OBJECT IDENTIFIER ::={plsw 18}

plswTimeGraphVal	OBJECT-TYPE
	SYNTAX	 TimeTicks
	MAX-ACCESS read-only
	STATUS current
	DESCRIPTION "Dataset, Time for Graph file I/O"

	::={plswTimeGraph 1}

plswTimeGraphLevelTable OBJECT-TYPE
	SYNTAX      SEQUENCE OF PlswTimeGraphLevelEntry
	MAX-ACCESS  not-accessible
	STATUS      current
	DESCRIPTION
	"Table for plswTimeGraph"
	::={plswTimeGraph 2}

plswTimeGraphLevelEntry OBJECT-TYPE
	SYNTAX      PlswTimeGraphLevelEntry
	MAX-ACCESS  not-accessible
	STATUS      current
	DESCRIPTION
	"Table entry for plswTimeGraph"
	INDEX { plswTimeGraphLevelName }
	::={plswTimeGraphLevelTable 1}

PlswTimeGraphLevelEntry ::=
	SEQUENCE {
		plswTimeGraphLevelName	DisplayString,
		plswTimeGraphLevelVal	TimeTicks
	}

plswTimeGraphLevelName OBJECT-TYPE
	SYNTAX      DisplayString
	MAX-ACCESS  not-accessible
	STATUS      current
	DESCRIPTION
	"Table entry display string for plswTimeGraph"
	::={plswTimeGraphLevelEntry 1}

plswTimeGraphLevelVal OBJECT-TYPE
	SYNTAX	 TimeTicks
	MAX-ACCESS  read-only
	STATUS      current
	DESCRIPTION
	"Table entry attribute for plswTimeGraph"
	::={plswTimeGraphLevelEntry 2}


plswGlobals	OBJECT IDENTIFIER ::={plsw 19}

plswGlobalsVal	OBJECT-TYPE
	SYNTAX	 CounterBasedGauge64
	MAX-ACCESS read-only
	STATUS current
	DESCRIPTION "Statisticsfs, Values (Global Indexes)"

	::={plswGlobals 1}

plswGlobalsMax	OBJECT-TYPE
	SYNTAX	 CounterBasedGauge64
	MAX-ACCESS read-only
	STATUS current
	DESCRIPTION "Statisticsfs, Values (Global Indexes)"

	::={plswGlobals 3}

plswGlobalsLevelTable OBJECT-TYPE
	SYNTAX      SEQUENCE OF PlswGlobalsLevelEntry
	MAX-ACCESS  not-accessible
	STATUS      current
	DESCRIPTION
	"Table for plswGlobals"
	::={plswGlobals 4}

plswGlobalsLevelEntry OBJECT-TYPE
	SYNTAX      PlswGlobalsLevelEntry
	MAX-ACCESS  not-accessible
	STATUS      current
	DESCRIPTION
	"Table entry for plswGlobals"
	INDEX { plswGlobalsLevelName }
	::={plswGlobalsLevelTable 1}

PlswGlobalsLevelEntry ::=
	SEQUENCE {
		plswGlobalsLevelName	DisplayString,
		plswGlobalsLevelVal	CounterBasedGauge64,
		plswGlobalsLevelMax	CounterBasedGauge64
	}

plswGlobalsLevelName OBJECT-TYPE
	SYNTAX      DisplayString
	MAX-ACCESS  not-accessible
	STATUS      current
	DESCRIPTION
	"Table entry display string for plswGlobals"
	::={plswGlobalsLevelEntry 1}

plswGlobalsLevelVal OBJECT-TYPE
	SYNTAX	 CounterBasedGauge64
	MAX-ACCESS  read-only
	STATUS      current
	DESCRIPTION
	"Table entry attribute for plswGlobals"
	::={plswGlobalsLevelEntry 2}

plswGlobalsLevelMax OBJECT-TYPE
	SYNTAX	 CounterBasedGauge64
	MAX-ACCESS  read-only
	STATUS      current
	DESCRIPTION
	"Table entry attribute for plswGlobals"
	::={plswGlobalsLevelEntry 4}


plswColls	OBJECT IDENTIFIER ::={plsw 20}

plswCollsVal	OBJECT-TYPE
	SYNTAX	 CounterBasedGauge64
	MAX-ACCESS read-only
	STATUS current
	DESCRIPTION "Statisticsfs, Values (Global Collisions)"

	::={plswColls 1}

plswCollsMax	OBJECT-TYPE
	SYNTAX	 CounterBasedGauge64
	MAX-ACCESS read-only
	STATUS current
	DESCRIPTION "Statisticsfs, Values (Global Collisions)"

	::={plswColls 3}

plswCollsLevelTable OBJECT-TYPE
	SYNTAX      SEQUENCE OF PlswCollsLevelEntry
	MAX-ACCESS  not-accessible
	STATUS      current
	DESCRIPTION
	"Table for plswColls"
	::={plswColls 4}

plswCollsLevelEntry OBJECT-TYPE
	SYNTAX      PlswCollsLevelEntry
	MAX-ACCESS  not-accessible
	STATUS      current
	DESCRIPTION
	"Table entry for plswColls"
	INDEX { plswCollsLevelName }
	::={plswCollsLevelTable 1}

PlswCollsLevelEntry ::=
	SEQUENCE {
		plswCollsLevelName	DisplayString,
		plswCollsLevelVal	CounterBasedGauge64,
		plswCollsLevelMax	CounterBasedGauge64
	}

plswCollsLevelName OBJECT-TYPE
	SYNTAX      DisplayString
	MAX-ACCESS  not-accessible
	STATUS      current
	DESCRIPTION
	"Table entry display string for plswColls"
	::={plswCollsLevelEntry 1}

plswCollsLevelVal OBJECT-TYPE
	SYNTAX	 CounterBasedGauge64
	MAX-ACCESS  read-only
	STATUS      current
	DESCRIPTION
	"Table entry attribute for plswColls"
	::={plswCollsLevelEntry 2}

plswCollsLevelMax OBJECT-TYPE
	SYNTAX	 CounterBasedGauge64
	MAX-ACCESS  read-only
	STATUS      current
	DESCRIPTION
	"Table entry attribute for plswColls"
	::={plswCollsLevelEntry 4}


plswDailys	OBJECT IDENTIFIER ::={plsw 21}

plswDailysVal	OBJECT-TYPE
	SYNTAX	 CounterBasedGauge64
	MAX-ACCESS read-only
	STATUS current
	DESCRIPTION "Statisticsfs, Values (Daily Indexes)"

	::={plswDailys 1}

plswDailysMax	OBJECT-TYPE
	SYNTAX	 CounterBasedGauge64
	MAX-ACCESS read-only
	STATUS current
	DESCRIPTION "Statisticsfs, Values (Daily Indexes)"

	::={plswDailys 3}

plswDailysLevelTable OBJECT-TYPE
	SYNTAX      SEQUENCE OF PlswDailysLevelEntry
	MAX-ACCESS  not-accessible
	STATUS      current
	DESCRIPTION
	"Table for plswDailys"
	::={plswDailys 4}

plswDailysLevelEntry OBJECT-TYPE
	SYNTAX      PlswDailysLevelEntry
	MAX-ACCESS  not-accessible
	STATUS      current
	DESCRIPTION
	"Table entry for plswDailys"
	INDEX { plswDailysLevelName }
	::={plswDailysLevelTable 1}

PlswDailysLevelEntry ::=
	SEQUENCE {
		plswDailysLevelName	DisplayString,
		plswDailysLevelVal	CounterBasedGauge64,
		plswDailysLevelMax	CounterBasedGauge64
	}

plswDailysLevelName OBJECT-TYPE
	SYNTAX      DisplayString
	MAX-ACCESS  not-accessible
	STATUS      current
	DESCRIPTION
	"Table entry display string for plswDailys"
	::={plswDailysLevelEntry 1}

plswDailysLevelVal OBJECT-TYPE
	SYNTAX	 CounterBasedGauge64
	MAX-ACCESS  read-only
	STATUS      current
	DESCRIPTION
	"Table entry attribute for plswDailys"
	::={plswDailysLevelEntry 2}

plswDailysLevelMax OBJECT-TYPE
	SYNTAX	 CounterBasedGauge64
	MAX-ACCESS  read-only
	STATUS      current
	DESCRIPTION
	"Table entry attribute for plswDailys"
	::={plswDailysLevelEntry 4}


plswBlocks	OBJECT IDENTIFIER ::={plsw 22}

plswBlocksVal	OBJECT-TYPE
	SYNTAX	 CounterBasedGauge64
	MAX-ACCESS read-only
	STATUS current
	DESCRIPTION "Statisticsfs, Daily Totals file blocks"

	::={plswBlocks 1}

plswBlocksMax	OBJECT-TYPE
	SYNTAX	 CounterBasedGauge64
	MAX-ACCESS read-only
	STATUS current
	DESCRIPTION "Statisticsfs, Daily Totals file blocks"

	::={plswBlocks 3}

plswBlocksLevelTable OBJECT-TYPE
	SYNTAX      SEQUENCE OF PlswBlocksLevelEntry
	MAX-ACCESS  not-accessible
	STATUS      current
	DESCRIPTION
	"Table for plswBlocks"
	::={plswBlocks 4}

plswBlocksLevelEntry OBJECT-TYPE
	SYNTAX      PlswBlocksLevelEntry
	MAX-ACCESS  not-accessible
	STATUS      current
	DESCRIPTION
	"Table entry for plswBlocks"
	INDEX { plswBlocksLevelName }
	::={plswBlocksLevelTable 1}

PlswBlocksLevelEntry ::=
	SEQUENCE {
		plswBlocksLevelName	DisplayString,
		plswBlocksLevelVal	CounterBasedGauge64,
		plswBlocksLevelMax	CounterBasedGauge64
	}

plswBlocksLevelName OBJECT-TYPE
	SYNTAX      DisplayString
	MAX-ACCESS  not-accessible
	STATUS      current
	DESCRIPTION
	"Table entry display string for plswBlocks"
	::={plswBlocksLevelEntry 1}

plswBlocksLevelVal OBJECT-TYPE
	SYNTAX	 CounterBasedGauge64
	MAX-ACCESS  read-only
	STATUS      current
	DESCRIPTION
	"Table entry attribute for plswBlocks"
	::={plswBlocksLevelEntry 2}

plswBlocksLevelMax OBJECT-TYPE
	SYNTAX	 CounterBasedGauge64
	MAX-ACCESS  read-only
	STATUS      current
	DESCRIPTION
	"Table entry attribute for plswBlocks"
	::={plswBlocksLevelEntry 4}


plswGraphs	OBJECT IDENTIFIER ::={plsw 23}

plswGraphsVal	OBJECT-TYPE
	SYNTAX	 CounterBasedGauge64
	MAX-ACCESS read-only
	STATUS current
	DESCRIPTION "Statisticsfs, Daily Graph data usage (Bytes)"

	::={plswGraphs 1}

plswGraphsMax	OBJECT-TYPE
	SYNTAX	 CounterBasedGauge64
	MAX-ACCESS read-only
	STATUS current
	DESCRIPTION "Statisticsfs, Daily Graph data usage (Bytes)"

	::={plswGraphs 3}

plswGraphsLevelTable OBJECT-TYPE
	SYNTAX      SEQUENCE OF PlswGraphsLevelEntry
	MAX-ACCESS  not-accessible
	STATUS      current
	DESCRIPTION
	"Table for plswGraphs"
	::={plswGraphs 4}

plswGraphsLevelEntry OBJECT-TYPE
	SYNTAX      PlswGraphsLevelEntry
	MAX-ACCESS  not-accessible
	STATUS      current
	DESCRIPTION
	"Table entry for plswGraphs"
	INDEX { plswGraphsLevelName }
	::={plswGraphsLevelTable 1}

PlswGraphsLevelEntry ::=
	SEQUENCE {
		plswGraphsLevelName	DisplayString,
		plswGraphsLevelVal	CounterBasedGauge64,
		plswGraphsLevelMax	CounterBasedGauge64
	}

plswGraphsLevelName OBJECT-TYPE
	SYNTAX      DisplayString
	MAX-ACCESS  not-accessible
	STATUS      current
	DESCRIPTION
	"Table entry display string for plswGraphs"
	::={plswGraphsLevelEntry 1}

plswGraphsLevelVal OBJECT-TYPE
	SYNTAX	 CounterBasedGauge64
	MAX-ACCESS  read-only
	STATUS      current
	DESCRIPTION
	"Table entry attribute for plswGraphs"
	::={plswGraphsLevelEntry 2}

plswGraphsLevelMax OBJECT-TYPE
	SYNTAX	 CounterBasedGauge64
	MAX-ACCESS  read-only
	STATUS      current
	DESCRIPTION
	"Table entry attribute for plswGraphs"
	::={plswGraphsLevelEntry 4}


plswSysdiagHdUsage	OBJECT IDENTIFIER ::={plsw 24}

plswSysdiagHdUsageVal	OBJECT-TYPE
	SYNTAX	 Unsigned32
	MAX-ACCESS read-only
	STATUS current
	DESCRIPTION "Statisticsfs, Disk Usage"

	::={plswSysdiagHdUsage 1}

plswSysdiagHdUsageMax	OBJECT-TYPE
	SYNTAX	 Unsigned32
	MAX-ACCESS read-only
	STATUS current
	DESCRIPTION "Statisticsfs, Disk Usage"

	::={plswSysdiagHdUsage 3}

plswSysdiagHdUsageLevelTable OBJECT-TYPE
	SYNTAX      SEQUENCE OF PlswSysdiagHdUsageLevelEntry
	MAX-ACCESS  not-accessible
	STATUS      current
	DESCRIPTION
	"Table for plswSysdiagHdUsage"
	::={plswSysdiagHdUsage 4}

plswSysdiagHdUsageLevelEntry OBJECT-TYPE
	SYNTAX      PlswSysdiagHdUsageLevelEntry
	MAX-ACCESS  not-accessible
	STATUS      current
	DESCRIPTION
	"Table entry for plswSysdiagHdUsage"
	INDEX { plswSysdiagHdUsageLevelName }
	::={plswSysdiagHdUsageLevelTable 1}

PlswSysdiagHdUsageLevelEntry ::=
	SEQUENCE {
		plswSysdiagHdUsageLevelName	DisplayString,
		plswSysdiagHdUsageLevelVal	Unsigned32,
		plswSysdiagHdUsageLevelMax	Unsigned32
	}

plswSysdiagHdUsageLevelName OBJECT-TYPE
	SYNTAX      DisplayString
	MAX-ACCESS  not-accessible
	STATUS      current
	DESCRIPTION
	"Table entry display string for plswSysdiagHdUsage"
	::={plswSysdiagHdUsageLevelEntry 1}

plswSysdiagHdUsageLevelVal OBJECT-TYPE
	SYNTAX	 Unsigned32
	MAX-ACCESS  read-only
	STATUS      current
	DESCRIPTION
	"Table entry attribute for plswSysdiagHdUsage"
	::={plswSysdiagHdUsageLevelEntry 2}

plswSysdiagHdUsageLevelMax OBJECT-TYPE
	SYNTAX	 Unsigned32
	MAX-ACCESS  read-only
	STATUS      current
	DESCRIPTION
	"Table entry attribute for plswSysdiagHdUsage"
	::={plswSysdiagHdUsageLevelEntry 4}


plswSysdiagHdSize	OBJECT IDENTIFIER ::={plsw 25}

plswSysdiagHdSizeVal	OBJECT-TYPE
	SYNTAX	 CounterBasedGauge64
	MAX-ACCESS read-only
	STATUS current
	DESCRIPTION "Statisticsfs, Disk Size"

	::={plswSysdiagHdSize 1}

plswSysdiagHdSizeMax	OBJECT-TYPE
	SYNTAX	 CounterBasedGauge64
	MAX-ACCESS read-only
	STATUS current
	DESCRIPTION "Statisticsfs, Disk Size"

	::={plswSysdiagHdSize 3}

plswSysdiagHdSizeLevelTable OBJECT-TYPE
	SYNTAX      SEQUENCE OF PlswSysdiagHdSizeLevelEntry
	MAX-ACCESS  not-accessible
	STATUS      current
	DESCRIPTION
	"Table for plswSysdiagHdSize"
	::={plswSysdiagHdSize 4}

plswSysdiagHdSizeLevelEntry OBJECT-TYPE
	SYNTAX      PlswSysdiagHdSizeLevelEntry
	MAX-ACCESS  not-accessible
	STATUS      current
	DESCRIPTION
	"Table entry for plswSysdiagHdSize"
	INDEX { plswSysdiagHdSizeLevelName }
	::={plswSysdiagHdSizeLevelTable 1}

PlswSysdiagHdSizeLevelEntry ::=
	SEQUENCE {
		plswSysdiagHdSizeLevelName	DisplayString,
		plswSysdiagHdSizeLevelVal	CounterBasedGauge64,
		plswSysdiagHdSizeLevelMax	CounterBasedGauge64
	}

plswSysdiagHdSizeLevelName OBJECT-TYPE
	SYNTAX      DisplayString
	MAX-ACCESS  not-accessible
	STATUS      current
	DESCRIPTION
	"Table entry display string for plswSysdiagHdSize"
	::={plswSysdiagHdSizeLevelEntry 1}

plswSysdiagHdSizeLevelVal OBJECT-TYPE
	SYNTAX	 CounterBasedGauge64
	MAX-ACCESS  read-only
	STATUS      current
	DESCRIPTION
	"Table entry attribute for plswSysdiagHdSize"
	::={plswSysdiagHdSizeLevelEntry 2}

plswSysdiagHdSizeLevelMax OBJECT-TYPE
	SYNTAX	 CounterBasedGauge64
	MAX-ACCESS  read-only
	STATUS      current
	DESCRIPTION
	"Table entry attribute for plswSysdiagHdSize"
	::={plswSysdiagHdSizeLevelEntry 4}


plswSystemHdUsage	OBJECT IDENTIFIER ::={plsw 26}

plswSystemHdUsageVal	OBJECT-TYPE
	SYNTAX	 Unsigned32
	MAX-ACCESS read-only
	STATUS current
	DESCRIPTION "System, Disk Usage"

	::={plswSystemHdUsage 1}

plswSystemHdUsageMax	OBJECT-TYPE
	SYNTAX	 Unsigned32
	MAX-ACCESS read-only
	STATUS current
	DESCRIPTION "System, Disk Usage"

	::={plswSystemHdUsage 3}

plswSystemHdUsageLevelTable OBJECT-TYPE
	SYNTAX      SEQUENCE OF PlswSystemHdUsageLevelEntry
	MAX-ACCESS  not-accessible
	STATUS      current
	DESCRIPTION
	"Table for plswSystemHdUsage"
	::={plswSystemHdUsage 4}

plswSystemHdUsageLevelEntry OBJECT-TYPE
	SYNTAX      PlswSystemHdUsageLevelEntry
	MAX-ACCESS  not-accessible
	STATUS      current
	DESCRIPTION
	"Table entry for plswSystemHdUsage"
	INDEX { plswSystemHdUsageLevelName }
	::={plswSystemHdUsageLevelTable 1}

PlswSystemHdUsageLevelEntry ::=
	SEQUENCE {
		plswSystemHdUsageLevelName	DisplayString,
		plswSystemHdUsageLevelVal	Unsigned32,
		plswSystemHdUsageLevelMax	Unsigned32
	}

plswSystemHdUsageLevelName OBJECT-TYPE
	SYNTAX      DisplayString
	MAX-ACCESS  not-accessible
	STATUS      current
	DESCRIPTION
	"Table entry display string for plswSystemHdUsage"
	::={plswSystemHdUsageLevelEntry 1}

plswSystemHdUsageLevelVal OBJECT-TYPE
	SYNTAX	 Unsigned32
	MAX-ACCESS  read-only
	STATUS      current
	DESCRIPTION
	"Table entry attribute for plswSystemHdUsage"
	::={plswSystemHdUsageLevelEntry 2}

plswSystemHdUsageLevelMax OBJECT-TYPE
	SYNTAX	 Unsigned32
	MAX-ACCESS  read-only
	STATUS      current
	DESCRIPTION
	"Table entry attribute for plswSystemHdUsage"
	::={plswSystemHdUsageLevelEntry 4}


plswSystemHdSize	OBJECT IDENTIFIER ::={plsw 27}

plswSystemHdSizeVal	OBJECT-TYPE
	SYNTAX	 CounterBasedGauge64
	MAX-ACCESS read-only
	STATUS current
	DESCRIPTION "System, Disk Size"

	::={plswSystemHdSize 1}

plswSystemHdSizeMax	OBJECT-TYPE
	SYNTAX	 CounterBasedGauge64
	MAX-ACCESS read-only
	STATUS current
	DESCRIPTION "System, Disk Size"

	::={plswSystemHdSize 3}

plswSystemHdSizeLevelTable OBJECT-TYPE
	SYNTAX      SEQUENCE OF PlswSystemHdSizeLevelEntry
	MAX-ACCESS  not-accessible
	STATUS      current
	DESCRIPTION
	"Table for plswSystemHdSize"
	::={plswSystemHdSize 4}

plswSystemHdSizeLevelEntry OBJECT-TYPE
	SYNTAX      PlswSystemHdSizeLevelEntry
	MAX-ACCESS  not-accessible
	STATUS      current
	DESCRIPTION
	"Table entry for plswSystemHdSize"
	INDEX { plswSystemHdSizeLevelName }
	::={plswSystemHdSizeLevelTable 1}

PlswSystemHdSizeLevelEntry ::=
	SEQUENCE {
		plswSystemHdSizeLevelName	DisplayString,
		plswSystemHdSizeLevelVal	CounterBasedGauge64,
		plswSystemHdSizeLevelMax	CounterBasedGauge64
	}

plswSystemHdSizeLevelName OBJECT-TYPE
	SYNTAX      DisplayString
	MAX-ACCESS  not-accessible
	STATUS      current
	DESCRIPTION
	"Table entry display string for plswSystemHdSize"
	::={plswSystemHdSizeLevelEntry 1}

plswSystemHdSizeLevelVal OBJECT-TYPE
	SYNTAX	 CounterBasedGauge64
	MAX-ACCESS  read-only
	STATUS      current
	DESCRIPTION
	"Table entry attribute for plswSystemHdSize"
	::={plswSystemHdSizeLevelEntry 2}

plswSystemHdSizeLevelMax OBJECT-TYPE
	SYNTAX	 CounterBasedGauge64
	MAX-ACCESS  read-only
	STATUS      current
	DESCRIPTION
	"Table entry attribute for plswSystemHdSize"
	::={plswSystemHdSizeLevelEntry 4}


plswSysdiagDaySize	OBJECT IDENTIFIER ::={plsw 28}

plswSysdiagDaySizeVal	OBJECT-TYPE
	SYNTAX	 CounterBasedGauge64
	MAX-ACCESS read-only
	STATUS obsolete
	DESCRIPTION "Statisticsfs, Disk Usage Per Day"

	::={plswSysdiagDaySize 1}

plswSysdiagDaySizeMax	OBJECT-TYPE
	SYNTAX	 CounterBasedGauge64
	MAX-ACCESS read-only
	STATUS obsolete
	DESCRIPTION "Statisticsfs, Disk Usage Per Day"

	::={plswSysdiagDaySize 3}

plswSysdiagDaySizeLevelTable OBJECT-TYPE
	SYNTAX      SEQUENCE OF PlswSysdiagDaySizeLevelEntry
	MAX-ACCESS  not-accessible
	STATUS      current
	DESCRIPTION
	"Table for plswSysdiagDaySize"
	::={plswSysdiagDaySize 4}

plswSysdiagDaySizeLevelEntry OBJECT-TYPE
	SYNTAX      PlswSysdiagDaySizeLevelEntry
	MAX-ACCESS  not-accessible
	STATUS      current
	DESCRIPTION
	"Table entry for plswSysdiagDaySize"
	INDEX { plswSysdiagDaySizeLevelName }
	::={plswSysdiagDaySizeLevelTable 1}

PlswSysdiagDaySizeLevelEntry ::=
	SEQUENCE {
		plswSysdiagDaySizeLevelName	DisplayString,
		plswSysdiagDaySizeLevelVal	CounterBasedGauge64,
		plswSysdiagDaySizeLevelMax	CounterBasedGauge64
	}

plswSysdiagDaySizeLevelName OBJECT-TYPE
	SYNTAX      DisplayString
	MAX-ACCESS  not-accessible
	STATUS      current
	DESCRIPTION
	"Table entry display string for plswSysdiagDaySize"
	::={plswSysdiagDaySizeLevelEntry 1}

plswSysdiagDaySizeLevelVal OBJECT-TYPE
	SYNTAX	 CounterBasedGauge64
	MAX-ACCESS  read-only
	STATUS      current
	DESCRIPTION
	"Table entry attribute for plswSysdiagDaySize"
	::={plswSysdiagDaySizeLevelEntry 2}

plswSysdiagDaySizeLevelMax OBJECT-TYPE
	SYNTAX	 CounterBasedGauge64
	MAX-ACCESS  read-only
	STATUS      current
	DESCRIPTION
	"Table entry attribute for plswSysdiagDaySize"
	::={plswSysdiagDaySizeLevelEntry 4}


plswMemused	OBJECT IDENTIFIER ::={plsw 29}

plswMemusedVal	OBJECT-TYPE
	SYNTAX	 CounterBasedGauge64
	MAX-ACCESS read-only
	STATUS current
	DESCRIPTION "Statwriter, Peak memory usage"

	::={plswMemused 1}

plswMemusedMax	OBJECT-TYPE
	SYNTAX	 CounterBasedGauge64
	MAX-ACCESS read-only
	STATUS current
	DESCRIPTION "Statwriter, Peak memory usage"

	::={plswMemused 3}

plswMemusedLevelTable OBJECT-TYPE
	SYNTAX      SEQUENCE OF PlswMemusedLevelEntry
	MAX-ACCESS  not-accessible
	STATUS      current
	DESCRIPTION
	"Table for plswMemused"
	::={plswMemused 4}

plswMemusedLevelEntry OBJECT-TYPE
	SYNTAX      PlswMemusedLevelEntry
	MAX-ACCESS  not-accessible
	STATUS      current
	DESCRIPTION
	"Table entry for plswMemused"
	INDEX { plswMemusedLevelName }
	::={plswMemusedLevelTable 1}

PlswMemusedLevelEntry ::=
	SEQUENCE {
		plswMemusedLevelName	DisplayString,
		plswMemusedLevelVal	CounterBasedGauge64,
		plswMemusedLevelMax	CounterBasedGauge64
	}

plswMemusedLevelName OBJECT-TYPE
	SYNTAX      DisplayString
	MAX-ACCESS  not-accessible
	STATUS      current
	DESCRIPTION
	"Table entry display string for plswMemused"
	::={plswMemusedLevelEntry 1}

plswMemusedLevelVal OBJECT-TYPE
	SYNTAX	 CounterBasedGauge64
	MAX-ACCESS  read-only
	STATUS      current
	DESCRIPTION
	"Table entry attribute for plswMemused"
	::={plswMemusedLevelEntry 2}

plswMemusedLevelMax OBJECT-TYPE
	SYNTAX	 CounterBasedGauge64
	MAX-ACCESS  read-only
	STATUS      current
	DESCRIPTION
	"Table entry attribute for plswMemused"
	::={plswMemusedLevelEntry 4}


plswDatasetsubs	OBJECT IDENTIFIER ::={plsw 30}

plswDatasetsubsVal	OBJECT-TYPE
	SYNTAX	 CounterBasedGauge64
	MAX-ACCESS read-only
	STATUS current
	DESCRIPTION "Dataset, Subscriber count"

	::={plswDatasetsubs 1}

plswDatasetsubsMax	OBJECT-TYPE
	SYNTAX	 CounterBasedGauge64
	MAX-ACCESS read-only
	STATUS current
	DESCRIPTION "Dataset, Subscriber count"

	::={plswDatasetsubs 3}

plswDatasetsubsLevelTable OBJECT-TYPE
	SYNTAX      SEQUENCE OF PlswDatasetsubsLevelEntry
	MAX-ACCESS  not-accessible
	STATUS      current
	DESCRIPTION
	"Table for plswDatasetsubs"
	::={plswDatasetsubs 4}

plswDatasetsubsLevelEntry OBJECT-TYPE
	SYNTAX      PlswDatasetsubsLevelEntry
	MAX-ACCESS  not-accessible
	STATUS      current
	DESCRIPTION
	"Table entry for plswDatasetsubs"
	INDEX { plswDatasetsubsLevelName }
	::={plswDatasetsubsLevelTable 1}

PlswDatasetsubsLevelEntry ::=
	SEQUENCE {
		plswDatasetsubsLevelName	DisplayString,
		plswDatasetsubsLevelVal	CounterBasedGauge64,
		plswDatasetsubsLevelMax	CounterBasedGauge64
	}

plswDatasetsubsLevelName OBJECT-TYPE
	SYNTAX      DisplayString
	MAX-ACCESS  not-accessible
	STATUS      current
	DESCRIPTION
	"Table entry display string for plswDatasetsubs"
	::={plswDatasetsubsLevelEntry 1}

plswDatasetsubsLevelVal OBJECT-TYPE
	SYNTAX	 CounterBasedGauge64
	MAX-ACCESS  read-only
	STATUS      current
	DESCRIPTION
	"Table entry attribute for plswDatasetsubs"
	::={plswDatasetsubsLevelEntry 2}

plswDatasetsubsLevelMax OBJECT-TYPE
	SYNTAX	 CounterBasedGauge64
	MAX-ACCESS  read-only
	STATUS      current
	DESCRIPTION
	"Table entry attribute for plswDatasetsubs"
	::={plswDatasetsubsLevelEntry 4}


plswValuesread	OBJECT IDENTIFIER ::={plsw 31}

plswValuesreadVal	OBJECT-TYPE
	SYNTAX	 CounterBasedGauge64
	MAX-ACCESS read-only
	STATUS current
	DESCRIPTION "Dataset Values read"

	::={plswValuesread 1}

plswValuesreadMax	OBJECT-TYPE
	SYNTAX	 CounterBasedGauge64
	MAX-ACCESS read-only
	STATUS current
	DESCRIPTION "Dataset Values read"

	::={plswValuesread 3}

plswValuesreadLevelTable OBJECT-TYPE
	SYNTAX      SEQUENCE OF PlswValuesreadLevelEntry
	MAX-ACCESS  not-accessible
	STATUS      current
	DESCRIPTION
	"Table for plswValuesread"
	::={plswValuesread 4}

plswValuesreadLevelEntry OBJECT-TYPE
	SYNTAX      PlswValuesreadLevelEntry
	MAX-ACCESS  not-accessible
	STATUS      current
	DESCRIPTION
	"Table entry for plswValuesread"
	INDEX { plswValuesreadLevelName }
	::={plswValuesreadLevelTable 1}

PlswValuesreadLevelEntry ::=
	SEQUENCE {
		plswValuesreadLevelName	DisplayString,
		plswValuesreadLevelVal	CounterBasedGauge64,
		plswValuesreadLevelMax	CounterBasedGauge64
	}

plswValuesreadLevelName OBJECT-TYPE
	SYNTAX      DisplayString
	MAX-ACCESS  not-accessible
	STATUS      current
	DESCRIPTION
	"Table entry display string for plswValuesread"
	::={plswValuesreadLevelEntry 1}

plswValuesreadLevelVal OBJECT-TYPE
	SYNTAX	 CounterBasedGauge64
	MAX-ACCESS  read-only
	STATUS      current
	DESCRIPTION
	"Table entry attribute for plswValuesread"
	::={plswValuesreadLevelEntry 2}

plswValuesreadLevelMax OBJECT-TYPE
	SYNTAX	 CounterBasedGauge64
	MAX-ACCESS  read-only
	STATUS      current
	DESCRIPTION
	"Table entry attribute for plswValuesread"
	::={plswValuesreadLevelEntry 4}


plswDatasetSize	OBJECT IDENTIFIER ::={plsw 32}

plswDatasetSizeVal	OBJECT-TYPE
	SYNTAX	 CounterBasedGauge64
	MAX-ACCESS read-only
	STATUS current
	DESCRIPTION "Dataset, Size"

	::={plswDatasetSize 1}

plswDatasetSizeMax	OBJECT-TYPE
	SYNTAX	 CounterBasedGauge64
	MAX-ACCESS read-only
	STATUS current
	DESCRIPTION "Dataset, Size"

	::={plswDatasetSize 3}

plswDatasetSizeLevelTable OBJECT-TYPE
	SYNTAX      SEQUENCE OF PlswDatasetSizeLevelEntry
	MAX-ACCESS  not-accessible
	STATUS      current
	DESCRIPTION
	"Table for plswDatasetSize"
	::={plswDatasetSize 4}

plswDatasetSizeLevelEntry OBJECT-TYPE
	SYNTAX      PlswDatasetSizeLevelEntry
	MAX-ACCESS  not-accessible
	STATUS      current
	DESCRIPTION
	"Table entry for plswDatasetSize"
	INDEX { plswDatasetSizeLevelName }
	::={plswDatasetSizeLevelTable 1}

PlswDatasetSizeLevelEntry ::=
	SEQUENCE {
		plswDatasetSizeLevelName	DisplayString,
		plswDatasetSizeLevelVal	CounterBasedGauge64,
		plswDatasetSizeLevelMax	CounterBasedGauge64
	}

plswDatasetSizeLevelName OBJECT-TYPE
	SYNTAX      DisplayString
	MAX-ACCESS  not-accessible
	STATUS      current
	DESCRIPTION
	"Table entry display string for plswDatasetSize"
	::={plswDatasetSizeLevelEntry 1}

plswDatasetSizeLevelVal OBJECT-TYPE
	SYNTAX	 CounterBasedGauge64
	MAX-ACCESS  read-only
	STATUS      current
	DESCRIPTION
	"Table entry attribute for plswDatasetSize"
	::={plswDatasetSizeLevelEntry 2}

plswDatasetSizeLevelMax OBJECT-TYPE
	SYNTAX	 CounterBasedGauge64
	MAX-ACCESS  read-only
	STATUS      current
	DESCRIPTION
	"Table entry attribute for plswDatasetSize"
	::={plswDatasetSizeLevelEntry 4}


plswStatsDaySize	OBJECT IDENTIFIER ::={plsw 33}

plswStatsDaySizeVal	OBJECT-TYPE
	SYNTAX	 CounterBasedGauge64
	MAX-ACCESS read-only
	STATUS current
	DESCRIPTION "Statisticsfs, Disk Usage Per Day (Statistics)"

	::={plswStatsDaySize 1}

plswStatsDaySizeMax	OBJECT-TYPE
	SYNTAX	 CounterBasedGauge64
	MAX-ACCESS read-only
	STATUS current
	DESCRIPTION "Statisticsfs, Disk Usage Per Day (Statistics)"

	::={plswStatsDaySize 3}

plswStatsDaySizeLevelTable OBJECT-TYPE
	SYNTAX      SEQUENCE OF PlswStatsDaySizeLevelEntry
	MAX-ACCESS  not-accessible
	STATUS      current
	DESCRIPTION
	"Table for plswStatsDaySize"
	::={plswStatsDaySize 4}

plswStatsDaySizeLevelEntry OBJECT-TYPE
	SYNTAX      PlswStatsDaySizeLevelEntry
	MAX-ACCESS  not-accessible
	STATUS      current
	DESCRIPTION
	"Table entry for plswStatsDaySize"
	INDEX { plswStatsDaySizeLevelName }
	::={plswStatsDaySizeLevelTable 1}

PlswStatsDaySizeLevelEntry ::=
	SEQUENCE {
		plswStatsDaySizeLevelName	DisplayString,
		plswStatsDaySizeLevelVal	CounterBasedGauge64,
		plswStatsDaySizeLevelMax	CounterBasedGauge64
	}

plswStatsDaySizeLevelName OBJECT-TYPE
	SYNTAX      DisplayString
	MAX-ACCESS  not-accessible
	STATUS      current
	DESCRIPTION
	"Table entry display string for plswStatsDaySize"
	::={plswStatsDaySizeLevelEntry 1}

plswStatsDaySizeLevelVal OBJECT-TYPE
	SYNTAX	 CounterBasedGauge64
	MAX-ACCESS  read-only
	STATUS      current
	DESCRIPTION
	"Table entry attribute for plswStatsDaySize"
	::={plswStatsDaySizeLevelEntry 2}

plswStatsDaySizeLevelMax OBJECT-TYPE
	SYNTAX	 CounterBasedGauge64
	MAX-ACCESS  read-only
	STATUS      current
	DESCRIPTION
	"Table entry attribute for plswStatsDaySize"
	::={plswStatsDaySizeLevelEntry 4}


plswConnlogDaySize	OBJECT IDENTIFIER ::={plsw 34}

plswConnlogDaySizeVal	OBJECT-TYPE
	SYNTAX	 CounterBasedGauge64
	MAX-ACCESS read-only
	STATUS current
	DESCRIPTION "Statisticsfs, Disk Usage Per Day (Connlog)"

	::={plswConnlogDaySize 1}

plswConnlogDaySizeMax	OBJECT-TYPE
	SYNTAX	 CounterBasedGauge64
	MAX-ACCESS read-only
	STATUS current
	DESCRIPTION "Statisticsfs, Disk Usage Per Day (Connlog)"

	::={plswConnlogDaySize 3}

plswConnlogDaySizeLevelTable OBJECT-TYPE
	SYNTAX      SEQUENCE OF PlswConnlogDaySizeLevelEntry
	MAX-ACCESS  not-accessible
	STATUS      current
	DESCRIPTION
	"Table for plswConnlogDaySize"
	::={plswConnlogDaySize 4}

plswConnlogDaySizeLevelEntry OBJECT-TYPE
	SYNTAX      PlswConnlogDaySizeLevelEntry
	MAX-ACCESS  not-accessible
	STATUS      current
	DESCRIPTION
	"Table entry for plswConnlogDaySize"
	INDEX { plswConnlogDaySizeLevelName }
	::={plswConnlogDaySizeLevelTable 1}

PlswConnlogDaySizeLevelEntry ::=
	SEQUENCE {
		plswConnlogDaySizeLevelName	DisplayString,
		plswConnlogDaySizeLevelVal	CounterBasedGauge64,
		plswConnlogDaySizeLevelMax	CounterBasedGauge64
	}

plswConnlogDaySizeLevelName OBJECT-TYPE
	SYNTAX      DisplayString
	MAX-ACCESS  not-accessible
	STATUS      current
	DESCRIPTION
	"Table entry display string for plswConnlogDaySize"
	::={plswConnlogDaySizeLevelEntry 1}

plswConnlogDaySizeLevelVal OBJECT-TYPE
	SYNTAX	 CounterBasedGauge64
	MAX-ACCESS  read-only
	STATUS      current
	DESCRIPTION
	"Table entry attribute for plswConnlogDaySize"
	::={plswConnlogDaySizeLevelEntry 2}

plswConnlogDaySizeLevelMax OBJECT-TYPE
	SYNTAX	 CounterBasedGauge64
	MAX-ACCESS  read-only
	STATUS      current
	DESCRIPTION
	"Table entry attribute for plswConnlogDaySize"
	::={plswConnlogDaySizeLevelEntry 4}


plswDatasetSizeInflated	OBJECT IDENTIFIER ::={plsw 35}

plswDatasetSizeInflatedVal	OBJECT-TYPE
	SYNTAX	 CounterBasedGauge64
	MAX-ACCESS read-only
	STATUS current
	DESCRIPTION "Dataset, Size (decompressed)"

	::={plswDatasetSizeInflated 1}

plswDatasetSizeInflatedMax	OBJECT-TYPE
	SYNTAX	 CounterBasedGauge64
	MAX-ACCESS read-only
	STATUS current
	DESCRIPTION "Dataset, Size (decompressed)"

	::={plswDatasetSizeInflated 3}

plswDatasetSizeInflatedLevelTable OBJECT-TYPE
	SYNTAX      SEQUENCE OF PlswDatasetSizeInflatedLevelEntry
	MAX-ACCESS  not-accessible
	STATUS      current
	DESCRIPTION
	"Table for plswDatasetSizeInflated"
	::={plswDatasetSizeInflated 4}

plswDatasetSizeInflatedLevelEntry OBJECT-TYPE
	SYNTAX      PlswDatasetSizeInflatedLevelEntry
	MAX-ACCESS  not-accessible
	STATUS      current
	DESCRIPTION
	"Table entry for plswDatasetSizeInflated"
	INDEX { plswDatasetSizeInflatedLevelName }
	::={plswDatasetSizeInflatedLevelTable 1}

PlswDatasetSizeInflatedLevelEntry ::=
	SEQUENCE {
		plswDatasetSizeInflatedLevelName	DisplayString,
		plswDatasetSizeInflatedLevelVal	CounterBasedGauge64,
		plswDatasetSizeInflatedLevelMax	CounterBasedGauge64
	}

plswDatasetSizeInflatedLevelName OBJECT-TYPE
	SYNTAX      DisplayString
	MAX-ACCESS  not-accessible
	STATUS      current
	DESCRIPTION
	"Table entry display string for plswDatasetSizeInflated"
	::={plswDatasetSizeInflatedLevelEntry 1}

plswDatasetSizeInflatedLevelVal OBJECT-TYPE
	SYNTAX	 CounterBasedGauge64
	MAX-ACCESS  read-only
	STATUS      current
	DESCRIPTION
	"Table entry attribute for plswDatasetSizeInflated"
	::={plswDatasetSizeInflatedLevelEntry 2}

plswDatasetSizeInflatedLevelMax OBJECT-TYPE
	SYNTAX	 CounterBasedGauge64
	MAX-ACCESS  read-only
	STATUS      current
	DESCRIPTION
	"Table entry attribute for plswDatasetSizeInflated"
	::={plswDatasetSizeInflatedLevelEntry 4}


plswGlobalsCurrentOpenTime	OBJECT IDENTIFIER ::={plsw 36}

plswGlobalsCurrentOpenTimeVal	OBJECT-TYPE
	SYNTAX	 DateAndTime
	MAX-ACCESS read-only
	STATUS current
	DESCRIPTION "Statisticsfs current globals, Open date"

	::={plswGlobalsCurrentOpenTime 1}

plswGlobalsCurrentOpenTimeLevelTable OBJECT-TYPE
	SYNTAX      SEQUENCE OF PlswGlobalsCurrentOpenTimeLevelEntry
	MAX-ACCESS  not-accessible
	STATUS      current
	DESCRIPTION
	"Table for plswGlobalsCurrentOpenTime"
	::={plswGlobalsCurrentOpenTime 2}

plswGlobalsCurrentOpenTimeLevelEntry OBJECT-TYPE
	SYNTAX      PlswGlobalsCurrentOpenTimeLevelEntry
	MAX-ACCESS  not-accessible
	STATUS      current
	DESCRIPTION
	"Table entry for plswGlobalsCurrentOpenTime"
	INDEX { plswGlobalsCurrentOpenTimeLevelName }
	::={plswGlobalsCurrentOpenTimeLevelTable 1}

PlswGlobalsCurrentOpenTimeLevelEntry ::=
	SEQUENCE {
		plswGlobalsCurrentOpenTimeLevelName	DisplayString,
		plswGlobalsCurrentOpenTimeLevelVal	DateAndTime
	}

plswGlobalsCurrentOpenTimeLevelName OBJECT-TYPE
	SYNTAX      DisplayString
	MAX-ACCESS  not-accessible
	STATUS      current
	DESCRIPTION
	"Table entry display string for plswGlobalsCurrentOpenTime"
	::={plswGlobalsCurrentOpenTimeLevelEntry 1}

plswGlobalsCurrentOpenTimeLevelVal OBJECT-TYPE
	SYNTAX	 DateAndTime
	MAX-ACCESS  read-only
	STATUS      current
	DESCRIPTION
	"Table entry attribute for plswGlobalsCurrentOpenTime"
	::={plswGlobalsCurrentOpenTimeLevelEntry 2}


plswGlobalsCurrentUtilization	OBJECT IDENTIFIER ::={plsw 37}

plswGlobalsCurrentUtilizationVal	OBJECT-TYPE
	SYNTAX	 Unsigned32
	MAX-ACCESS read-only
	STATUS current
	DESCRIPTION "Statisticsfs current globals, Utilization"

	::={plswGlobalsCurrentUtilization 1}

plswGlobalsCurrentUtilizationMax	OBJECT-TYPE
	SYNTAX	 Unsigned32
	MAX-ACCESS read-only
	STATUS current
	DESCRIPTION "Statisticsfs current globals, Utilization"

	::={plswGlobalsCurrentUtilization 3}

plswGlobalsCurrentUtilizationLevelTable OBJECT-TYPE
	SYNTAX      SEQUENCE OF PlswGlobalsCurrentUtilizationLevelEntry
	MAX-ACCESS  not-accessible
	STATUS      current
	DESCRIPTION
	"Table for plswGlobalsCurrentUtilization"
	::={plswGlobalsCurrentUtilization 4}

plswGlobalsCurrentUtilizationLevelEntry OBJECT-TYPE
	SYNTAX      PlswGlobalsCurrentUtilizationLevelEntry
	MAX-ACCESS  not-accessible
	STATUS      current
	DESCRIPTION
	"Table entry for plswGlobalsCurrentUtilization"
	INDEX { plswGlobalsCurrentUtilizationLevelName }
	::={plswGlobalsCurrentUtilizationLevelTable 1}

PlswGlobalsCurrentUtilizationLevelEntry ::=
	SEQUENCE {
		plswGlobalsCurrentUtilizationLevelName	DisplayString,
		plswGlobalsCurrentUtilizationLevelVal	Unsigned32,
		plswGlobalsCurrentUtilizationLevelMax	Unsigned32
	}

plswGlobalsCurrentUtilizationLevelName OBJECT-TYPE
	SYNTAX      DisplayString
	MAX-ACCESS  not-accessible
	STATUS      current
	DESCRIPTION
	"Table entry display string for plswGlobalsCurrentUtilization"
	::={plswGlobalsCurrentUtilizationLevelEntry 1}

plswGlobalsCurrentUtilizationLevelVal OBJECT-TYPE
	SYNTAX	 Unsigned32
	MAX-ACCESS  read-only
	STATUS      current
	DESCRIPTION
	"Table entry attribute for plswGlobalsCurrentUtilization"
	::={plswGlobalsCurrentUtilizationLevelEntry 2}

plswGlobalsCurrentUtilizationLevelMax OBJECT-TYPE
	SYNTAX	 Unsigned32
	MAX-ACCESS  read-only
	STATUS      current
	DESCRIPTION
	"Table entry attribute for plswGlobalsCurrentUtilization"
	::={plswGlobalsCurrentUtilizationLevelEntry 4}


plswGlobalsCurrentDiskUsage	OBJECT IDENTIFIER ::={plsw 38}

plswGlobalsCurrentDiskUsageVal	OBJECT-TYPE
	SYNTAX	 CounterBasedGauge64
	MAX-ACCESS read-only
	STATUS current
	DESCRIPTION "Statisticsfs current globals, Disk usage"

	::={plswGlobalsCurrentDiskUsage 1}

plswGlobalsCurrentDiskUsageMax	OBJECT-TYPE
	SYNTAX	 CounterBasedGauge64
	MAX-ACCESS read-only
	STATUS current
	DESCRIPTION "Statisticsfs current globals, Disk usage"

	::={plswGlobalsCurrentDiskUsage 3}

plswGlobalsCurrentDiskUsageLevelTable OBJECT-TYPE
	SYNTAX      SEQUENCE OF PlswGlobalsCurrentDiskUsageLevelEntry
	MAX-ACCESS  not-accessible
	STATUS      current
	DESCRIPTION
	"Table for plswGlobalsCurrentDiskUsage"
	::={plswGlobalsCurrentDiskUsage 4}

plswGlobalsCurrentDiskUsageLevelEntry OBJECT-TYPE
	SYNTAX      PlswGlobalsCurrentDiskUsageLevelEntry
	MAX-ACCESS  not-accessible
	STATUS      current
	DESCRIPTION
	"Table entry for plswGlobalsCurrentDiskUsage"
	INDEX { plswGlobalsCurrentDiskUsageLevelName }
	::={plswGlobalsCurrentDiskUsageLevelTable 1}

PlswGlobalsCurrentDiskUsageLevelEntry ::=
	SEQUENCE {
		plswGlobalsCurrentDiskUsageLevelName	DisplayString,
		plswGlobalsCurrentDiskUsageLevelVal	CounterBasedGauge64,
		plswGlobalsCurrentDiskUsageLevelMax	CounterBasedGauge64
	}

plswGlobalsCurrentDiskUsageLevelName OBJECT-TYPE
	SYNTAX      DisplayString
	MAX-ACCESS  not-accessible
	STATUS      current
	DESCRIPTION
	"Table entry display string for plswGlobalsCurrentDiskUsage"
	::={plswGlobalsCurrentDiskUsageLevelEntry 1}

plswGlobalsCurrentDiskUsageLevelVal OBJECT-TYPE
	SYNTAX	 CounterBasedGauge64
	MAX-ACCESS  read-only
	STATUS      current
	DESCRIPTION
	"Table entry attribute for plswGlobalsCurrentDiskUsage"
	::={plswGlobalsCurrentDiskUsageLevelEntry 2}

plswGlobalsCurrentDiskUsageLevelMax OBJECT-TYPE
	SYNTAX	 CounterBasedGauge64
	MAX-ACCESS  read-only
	STATUS      current
	DESCRIPTION
	"Table entry attribute for plswGlobalsCurrentDiskUsage"
	::={plswGlobalsCurrentDiskUsageLevelEntry 4}


plswGlobalsPreviousDuration	OBJECT IDENTIFIER ::={plsw 39}

plswGlobalsPreviousDurationVal	OBJECT-TYPE
	SYNTAX	 TimeTicks
	MAX-ACCESS read-only
	STATUS current
	DESCRIPTION "Statisticsfs previous globals, Duration"

	::={plswGlobalsPreviousDuration 1}

plswGlobalsPreviousDurationLevelTable OBJECT-TYPE
	SYNTAX      SEQUENCE OF PlswGlobalsPreviousDurationLevelEntry
	MAX-ACCESS  not-accessible
	STATUS      current
	DESCRIPTION
	"Table for plswGlobalsPreviousDuration"
	::={plswGlobalsPreviousDuration 2}

plswGlobalsPreviousDurationLevelEntry OBJECT-TYPE
	SYNTAX      PlswGlobalsPreviousDurationLevelEntry
	MAX-ACCESS  not-accessible
	STATUS      current
	DESCRIPTION
	"Table entry for plswGlobalsPreviousDuration"
	INDEX { plswGlobalsPreviousDurationLevelName }
	::={plswGlobalsPreviousDurationLevelTable 1}

PlswGlobalsPreviousDurationLevelEntry ::=
	SEQUENCE {
		plswGlobalsPreviousDurationLevelName	DisplayString,
		plswGlobalsPreviousDurationLevelVal	TimeTicks
	}

plswGlobalsPreviousDurationLevelName OBJECT-TYPE
	SYNTAX      DisplayString
	MAX-ACCESS  not-accessible
	STATUS      current
	DESCRIPTION
	"Table entry display string for plswGlobalsPreviousDuration"
	::={plswGlobalsPreviousDurationLevelEntry 1}

plswGlobalsPreviousDurationLevelVal OBJECT-TYPE
	SYNTAX	 TimeTicks
	MAX-ACCESS  read-only
	STATUS      current
	DESCRIPTION
	"Table entry attribute for plswGlobalsPreviousDuration"
	::={plswGlobalsPreviousDurationLevelEntry 2}


plswGlobalsCount	OBJECT IDENTIFIER ::={plsw 40}

plswGlobalsCountVal	OBJECT-TYPE
	SYNTAX	 CounterBasedGauge64
	MAX-ACCESS read-only
	STATUS current
	DESCRIPTION "Statisticsfs globals, Count"

	::={plswGlobalsCount 1}

plswGlobalsCountMax	OBJECT-TYPE
	SYNTAX	 CounterBasedGauge64
	MAX-ACCESS read-only
	STATUS current
	DESCRIPTION "Statisticsfs globals, Count"

	::={plswGlobalsCount 3}

plswGlobalsCountLevelTable OBJECT-TYPE
	SYNTAX      SEQUENCE OF PlswGlobalsCountLevelEntry
	MAX-ACCESS  not-accessible
	STATUS      current
	DESCRIPTION
	"Table for plswGlobalsCount"
	::={plswGlobalsCount 4}

plswGlobalsCountLevelEntry OBJECT-TYPE
	SYNTAX      PlswGlobalsCountLevelEntry
	MAX-ACCESS  not-accessible
	STATUS      current
	DESCRIPTION
	"Table entry for plswGlobalsCount"
	INDEX { plswGlobalsCountLevelName }
	::={plswGlobalsCountLevelTable 1}

PlswGlobalsCountLevelEntry ::=
	SEQUENCE {
		plswGlobalsCountLevelName	DisplayString,
		plswGlobalsCountLevelVal	CounterBasedGauge64,
		plswGlobalsCountLevelMax	CounterBasedGauge64
	}

plswGlobalsCountLevelName OBJECT-TYPE
	SYNTAX      DisplayString
	MAX-ACCESS  not-accessible
	STATUS      current
	DESCRIPTION
	"Table entry display string for plswGlobalsCount"
	::={plswGlobalsCountLevelEntry 1}

plswGlobalsCountLevelVal OBJECT-TYPE
	SYNTAX	 CounterBasedGauge64
	MAX-ACCESS  read-only
	STATUS      current
	DESCRIPTION
	"Table entry attribute for plswGlobalsCount"
	::={plswGlobalsCountLevelEntry 2}

plswGlobalsCountLevelMax OBJECT-TYPE
	SYNTAX	 CounterBasedGauge64
	MAX-ACCESS  read-only
	STATUS      current
	DESCRIPTION
	"Table entry attribute for plswGlobalsCount"
	::={plswGlobalsCountLevelEntry 4}


plswDatasetBacklog	OBJECT IDENTIFIER ::={plsw 41}

plswDatasetBacklogVal	OBJECT-TYPE
	SYNTAX	 CounterBasedGauge64
	MAX-ACCESS read-only
	STATUS current
	DESCRIPTION "Dataset Backlog count"

	::={plswDatasetBacklog 1}

plswDatasetBacklogMax	OBJECT-TYPE
	SYNTAX	 CounterBasedGauge64
	MAX-ACCESS read-only
	STATUS current
	DESCRIPTION "Dataset Backlog count"

	::={plswDatasetBacklog 3}

plswDatasetBacklogLevelTable OBJECT-TYPE
	SYNTAX      SEQUENCE OF PlswDatasetBacklogLevelEntry
	MAX-ACCESS  not-accessible
	STATUS      current
	DESCRIPTION
	"Table for plswDatasetBacklog"
	::={plswDatasetBacklog 4}

plswDatasetBacklogLevelEntry OBJECT-TYPE
	SYNTAX      PlswDatasetBacklogLevelEntry
	MAX-ACCESS  not-accessible
	STATUS      current
	DESCRIPTION
	"Table entry for plswDatasetBacklog"
	INDEX { plswDatasetBacklogLevelName }
	::={plswDatasetBacklogLevelTable 1}

PlswDatasetBacklogLevelEntry ::=
	SEQUENCE {
		plswDatasetBacklogLevelName	DisplayString,
		plswDatasetBacklogLevelVal	CounterBasedGauge64,
		plswDatasetBacklogLevelMax	CounterBasedGauge64
	}

plswDatasetBacklogLevelName OBJECT-TYPE
	SYNTAX      DisplayString
	MAX-ACCESS  not-accessible
	STATUS      current
	DESCRIPTION
	"Table entry display string for plswDatasetBacklog"
	::={plswDatasetBacklogLevelEntry 1}

plswDatasetBacklogLevelVal OBJECT-TYPE
	SYNTAX	 CounterBasedGauge64
	MAX-ACCESS  read-only
	STATUS      current
	DESCRIPTION
	"Table entry attribute for plswDatasetBacklog"
	::={plswDatasetBacklogLevelEntry 2}

plswDatasetBacklogLevelMax OBJECT-TYPE
	SYNTAX	 CounterBasedGauge64
	MAX-ACCESS  read-only
	STATUS      current
	DESCRIPTION
	"Table entry attribute for plswDatasetBacklog"
	::={plswDatasetBacklogLevelEntry 4}


plswDatasetError	OBJECT IDENTIFIER ::={plsw 42}

plswDatasetErrorVal	OBJECT-TYPE
	SYNTAX	 CounterBasedGauge64
	MAX-ACCESS read-only
	STATUS current
	DESCRIPTION "Dataset Backlog Error count"

	::={plswDatasetError 1}

plswDatasetErrorMax	OBJECT-TYPE
	SYNTAX	 CounterBasedGauge64
	MAX-ACCESS read-only
	STATUS current
	DESCRIPTION "Dataset Backlog Error count"

	::={plswDatasetError 3}

plswDatasetErrorLevelTable OBJECT-TYPE
	SYNTAX      SEQUENCE OF PlswDatasetErrorLevelEntry
	MAX-ACCESS  not-accessible
	STATUS      current
	DESCRIPTION
	"Table for plswDatasetError"
	::={plswDatasetError 4}

plswDatasetErrorLevelEntry OBJECT-TYPE
	SYNTAX      PlswDatasetErrorLevelEntry
	MAX-ACCESS  not-accessible
	STATUS      current
	DESCRIPTION
	"Table entry for plswDatasetError"
	INDEX { plswDatasetErrorLevelName }
	::={plswDatasetErrorLevelTable 1}

PlswDatasetErrorLevelEntry ::=
	SEQUENCE {
		plswDatasetErrorLevelName	DisplayString,
		plswDatasetErrorLevelVal	CounterBasedGauge64,
		plswDatasetErrorLevelMax	CounterBasedGauge64
	}

plswDatasetErrorLevelName OBJECT-TYPE
	SYNTAX      DisplayString
	MAX-ACCESS  not-accessible
	STATUS      current
	DESCRIPTION
	"Table entry display string for plswDatasetError"
	::={plswDatasetErrorLevelEntry 1}

plswDatasetErrorLevelVal OBJECT-TYPE
	SYNTAX	 CounterBasedGauge64
	MAX-ACCESS  read-only
	STATUS      current
	DESCRIPTION
	"Table entry attribute for plswDatasetError"
	::={plswDatasetErrorLevelEntry 2}

plswDatasetErrorLevelMax OBJECT-TYPE
	SYNTAX	 CounterBasedGauge64
	MAX-ACCESS  read-only
	STATUS      current
	DESCRIPTION
	"Table entry attribute for plswDatasetError"
	::={plswDatasetErrorLevelEntry 4}


plswTotalsFiles	OBJECT IDENTIFIER ::={plsw 43}

plswTotalsFilesVal	OBJECT-TYPE
	SYNTAX	 CounterBasedGauge64
	MAX-ACCESS read-only
	STATUS current
	DESCRIPTION "Statisticsfs, Totals files"

	::={plswTotalsFiles 1}

plswTotalsFilesMax	OBJECT-TYPE
	SYNTAX	 CounterBasedGauge64
	MAX-ACCESS read-only
	STATUS current
	DESCRIPTION "Statisticsfs, Totals files"

	::={plswTotalsFiles 3}

plswTotalsFilesLevelTable OBJECT-TYPE
	SYNTAX      SEQUENCE OF PlswTotalsFilesLevelEntry
	MAX-ACCESS  not-accessible
	STATUS      current
	DESCRIPTION
	"Table for plswTotalsFiles"
	::={plswTotalsFiles 4}

plswTotalsFilesLevelEntry OBJECT-TYPE
	SYNTAX      PlswTotalsFilesLevelEntry
	MAX-ACCESS  not-accessible
	STATUS      current
	DESCRIPTION
	"Table entry for plswTotalsFiles"
	INDEX { plswTotalsFilesLevelName }
	::={plswTotalsFilesLevelTable 1}

PlswTotalsFilesLevelEntry ::=
	SEQUENCE {
		plswTotalsFilesLevelName	DisplayString,
		plswTotalsFilesLevelVal	CounterBasedGauge64,
		plswTotalsFilesLevelMax	CounterBasedGauge64
	}

plswTotalsFilesLevelName OBJECT-TYPE
	SYNTAX      DisplayString
	MAX-ACCESS  not-accessible
	STATUS      current
	DESCRIPTION
	"Table entry display string for plswTotalsFiles"
	::={plswTotalsFilesLevelEntry 1}

plswTotalsFilesLevelVal OBJECT-TYPE
	SYNTAX	 CounterBasedGauge64
	MAX-ACCESS  read-only
	STATUS      current
	DESCRIPTION
	"Table entry attribute for plswTotalsFiles"
	::={plswTotalsFilesLevelEntry 2}

plswTotalsFilesLevelMax OBJECT-TYPE
	SYNTAX	 CounterBasedGauge64
	MAX-ACCESS  read-only
	STATUS      current
	DESCRIPTION
	"Table entry attribute for plswTotalsFiles"
	::={plswTotalsFilesLevelEntry 4}


plswGraphsFiles	OBJECT IDENTIFIER ::={plsw 44}

plswGraphsFilesVal	OBJECT-TYPE
	SYNTAX	 CounterBasedGauge64
	MAX-ACCESS read-only
	STATUS current
	DESCRIPTION "Statisticsfs, Graphs files"

	::={plswGraphsFiles 1}

plswGraphsFilesMax	OBJECT-TYPE
	SYNTAX	 CounterBasedGauge64
	MAX-ACCESS read-only
	STATUS current
	DESCRIPTION "Statisticsfs, Graphs files"

	::={plswGraphsFiles 3}

plswGraphsFilesLevelTable OBJECT-TYPE
	SYNTAX      SEQUENCE OF PlswGraphsFilesLevelEntry
	MAX-ACCESS  not-accessible
	STATUS      current
	DESCRIPTION
	"Table for plswGraphsFiles"
	::={plswGraphsFiles 4}

plswGraphsFilesLevelEntry OBJECT-TYPE
	SYNTAX      PlswGraphsFilesLevelEntry
	MAX-ACCESS  not-accessible
	STATUS      current
	DESCRIPTION
	"Table entry for plswGraphsFiles"
	INDEX { plswGraphsFilesLevelName }
	::={plswGraphsFilesLevelTable 1}

PlswGraphsFilesLevelEntry ::=
	SEQUENCE {
		plswGraphsFilesLevelName	DisplayString,
		plswGraphsFilesLevelVal	CounterBasedGauge64,
		plswGraphsFilesLevelMax	CounterBasedGauge64
	}

plswGraphsFilesLevelName OBJECT-TYPE
	SYNTAX      DisplayString
	MAX-ACCESS  not-accessible
	STATUS      current
	DESCRIPTION
	"Table entry display string for plswGraphsFiles"
	::={plswGraphsFilesLevelEntry 1}

plswGraphsFilesLevelVal OBJECT-TYPE
	SYNTAX	 CounterBasedGauge64
	MAX-ACCESS  read-only
	STATUS      current
	DESCRIPTION
	"Table entry attribute for plswGraphsFiles"
	::={plswGraphsFilesLevelEntry 2}

plswGraphsFilesLevelMax OBJECT-TYPE
	SYNTAX	 CounterBasedGauge64
	MAX-ACCESS  read-only
	STATUS      current
	DESCRIPTION
	"Table entry attribute for plswGraphsFiles"
	::={plswGraphsFilesLevelEntry 4}


plswTotalsFilesUpdated	OBJECT IDENTIFIER ::={plsw 45}

plswTotalsFilesUpdatedVal	OBJECT-TYPE
	SYNTAX	 CounterBasedGauge64
	MAX-ACCESS read-only
	STATUS current
	DESCRIPTION "Statisticsfs, Totals files updated"

	::={plswTotalsFilesUpdated 1}

plswTotalsFilesUpdatedMax	OBJECT-TYPE
	SYNTAX	 CounterBasedGauge64
	MAX-ACCESS read-only
	STATUS current
	DESCRIPTION "Statisticsfs, Totals files updated"

	::={plswTotalsFilesUpdated 3}

plswTotalsFilesUpdatedLevelTable OBJECT-TYPE
	SYNTAX      SEQUENCE OF PlswTotalsFilesUpdatedLevelEntry
	MAX-ACCESS  not-accessible
	STATUS      current
	DESCRIPTION
	"Table for plswTotalsFilesUpdated"
	::={plswTotalsFilesUpdated 4}

plswTotalsFilesUpdatedLevelEntry OBJECT-TYPE
	SYNTAX      PlswTotalsFilesUpdatedLevelEntry
	MAX-ACCESS  not-accessible
	STATUS      current
	DESCRIPTION
	"Table entry for plswTotalsFilesUpdated"
	INDEX { plswTotalsFilesUpdatedLevelName }
	::={plswTotalsFilesUpdatedLevelTable 1}

PlswTotalsFilesUpdatedLevelEntry ::=
	SEQUENCE {
		plswTotalsFilesUpdatedLevelName	DisplayString,
		plswTotalsFilesUpdatedLevelVal	CounterBasedGauge64,
		plswTotalsFilesUpdatedLevelMax	CounterBasedGauge64
	}

plswTotalsFilesUpdatedLevelName OBJECT-TYPE
	SYNTAX      DisplayString
	MAX-ACCESS  not-accessible
	STATUS      current
	DESCRIPTION
	"Table entry display string for plswTotalsFilesUpdated"
	::={plswTotalsFilesUpdatedLevelEntry 1}

plswTotalsFilesUpdatedLevelVal OBJECT-TYPE
	SYNTAX	 CounterBasedGauge64
	MAX-ACCESS  read-only
	STATUS      current
	DESCRIPTION
	"Table entry attribute for plswTotalsFilesUpdated"
	::={plswTotalsFilesUpdatedLevelEntry 2}

plswTotalsFilesUpdatedLevelMax OBJECT-TYPE
	SYNTAX	 CounterBasedGauge64
	MAX-ACCESS  read-only
	STATUS      current
	DESCRIPTION
	"Table entry attribute for plswTotalsFilesUpdated"
	::={plswTotalsFilesUpdatedLevelEntry 4}


plswGraphsFilesUpdated	OBJECT IDENTIFIER ::={plsw 46}

plswGraphsFilesUpdatedVal	OBJECT-TYPE
	SYNTAX	 CounterBasedGauge64
	MAX-ACCESS read-only
	STATUS current
	DESCRIPTION "Statisticsfs, Graphs files updated"

	::={plswGraphsFilesUpdated 1}

plswGraphsFilesUpdatedMax	OBJECT-TYPE
	SYNTAX	 CounterBasedGauge64
	MAX-ACCESS read-only
	STATUS current
	DESCRIPTION "Statisticsfs, Graphs files updated"

	::={plswGraphsFilesUpdated 3}

plswGraphsFilesUpdatedLevelTable OBJECT-TYPE
	SYNTAX      SEQUENCE OF PlswGraphsFilesUpdatedLevelEntry
	MAX-ACCESS  not-accessible
	STATUS      current
	DESCRIPTION
	"Table for plswGraphsFilesUpdated"
	::={plswGraphsFilesUpdated 4}

plswGraphsFilesUpdatedLevelEntry OBJECT-TYPE
	SYNTAX      PlswGraphsFilesUpdatedLevelEntry
	MAX-ACCESS  not-accessible
	STATUS      current
	DESCRIPTION
	"Table entry for plswGraphsFilesUpdated"
	INDEX { plswGraphsFilesUpdatedLevelName }
	::={plswGraphsFilesUpdatedLevelTable 1}

PlswGraphsFilesUpdatedLevelEntry ::=
	SEQUENCE {
		plswGraphsFilesUpdatedLevelName	DisplayString,
		plswGraphsFilesUpdatedLevelVal	CounterBasedGauge64,
		plswGraphsFilesUpdatedLevelMax	CounterBasedGauge64
	}

plswGraphsFilesUpdatedLevelName OBJECT-TYPE
	SYNTAX      DisplayString
	MAX-ACCESS  not-accessible
	STATUS      current
	DESCRIPTION
	"Table entry display string for plswGraphsFilesUpdated"
	::={plswGraphsFilesUpdatedLevelEntry 1}

plswGraphsFilesUpdatedLevelVal OBJECT-TYPE
	SYNTAX	 CounterBasedGauge64
	MAX-ACCESS  read-only
	STATUS      current
	DESCRIPTION
	"Table entry attribute for plswGraphsFilesUpdated"
	::={plswGraphsFilesUpdatedLevelEntry 2}

plswGraphsFilesUpdatedLevelMax OBJECT-TYPE
	SYNTAX	 CounterBasedGauge64
	MAX-ACCESS  read-only
	STATUS      current
	DESCRIPTION
	"Table entry attribute for plswGraphsFilesUpdated"
	::={plswGraphsFilesUpdatedLevelEntry 4}


plswDatasetNewSubs	OBJECT IDENTIFIER ::={plsw 47}

plswDatasetNewSubsVal	OBJECT-TYPE
	SYNTAX	 CounterBasedGauge64
	MAX-ACCESS read-only
	STATUS current
	DESCRIPTION "Dataset, New Subscribers"

	::={plswDatasetNewSubs 1}

plswDatasetNewSubsMax	OBJECT-TYPE
	SYNTAX	 CounterBasedGauge64
	MAX-ACCESS read-only
	STATUS current
	DESCRIPTION "Dataset, New Subscribers"

	::={plswDatasetNewSubs 3}

plswDatasetNewSubsLevelTable OBJECT-TYPE
	SYNTAX      SEQUENCE OF PlswDatasetNewSubsLevelEntry
	MAX-ACCESS  not-accessible
	STATUS      current
	DESCRIPTION
	"Table for plswDatasetNewSubs"
	::={plswDatasetNewSubs 4}

plswDatasetNewSubsLevelEntry OBJECT-TYPE
	SYNTAX      PlswDatasetNewSubsLevelEntry
	MAX-ACCESS  not-accessible
	STATUS      current
	DESCRIPTION
	"Table entry for plswDatasetNewSubs"
	INDEX { plswDatasetNewSubsLevelName }
	::={plswDatasetNewSubsLevelTable 1}

PlswDatasetNewSubsLevelEntry ::=
	SEQUENCE {
		plswDatasetNewSubsLevelName	DisplayString,
		plswDatasetNewSubsLevelVal	CounterBasedGauge64,
		plswDatasetNewSubsLevelMax	CounterBasedGauge64
	}

plswDatasetNewSubsLevelName OBJECT-TYPE
	SYNTAX      DisplayString
	MAX-ACCESS  not-accessible
	STATUS      current
	DESCRIPTION
	"Table entry display string for plswDatasetNewSubs"
	::={plswDatasetNewSubsLevelEntry 1}

plswDatasetNewSubsLevelVal OBJECT-TYPE
	SYNTAX	 CounterBasedGauge64
	MAX-ACCESS  read-only
	STATUS      current
	DESCRIPTION
	"Table entry attribute for plswDatasetNewSubs"
	::={plswDatasetNewSubsLevelEntry 2}

plswDatasetNewSubsLevelMax OBJECT-TYPE
	SYNTAX	 CounterBasedGauge64
	MAX-ACCESS  read-only
	STATUS      current
	DESCRIPTION
	"Table entry attribute for plswDatasetNewSubs"
	::={plswDatasetNewSubsLevelEntry 4}


plswTimeDatasetLoad	OBJECT IDENTIFIER ::={plsw 48}

plswTimeDatasetLoadVal	OBJECT-TYPE
	SYNTAX	 TimeTicks
	MAX-ACCESS read-only
	STATUS current
	DESCRIPTION "Dataset, Time for loading"

	::={plswTimeDatasetLoad 1}

plswTimeDatasetLoadLevelTable OBJECT-TYPE
	SYNTAX      SEQUENCE OF PlswTimeDatasetLoadLevelEntry
	MAX-ACCESS  not-accessible
	STATUS      current
	DESCRIPTION
	"Table for plswTimeDatasetLoad"
	::={plswTimeDatasetLoad 2}

plswTimeDatasetLoadLevelEntry OBJECT-TYPE
	SYNTAX      PlswTimeDatasetLoadLevelEntry
	MAX-ACCESS  not-accessible
	STATUS      current
	DESCRIPTION
	"Table entry for plswTimeDatasetLoad"
	INDEX { plswTimeDatasetLoadLevelName }
	::={plswTimeDatasetLoadLevelTable 1}

PlswTimeDatasetLoadLevelEntry ::=
	SEQUENCE {
		plswTimeDatasetLoadLevelName	DisplayString,
		plswTimeDatasetLoadLevelVal	TimeTicks
	}

plswTimeDatasetLoadLevelName OBJECT-TYPE
	SYNTAX      DisplayString
	MAX-ACCESS  not-accessible
	STATUS      current
	DESCRIPTION
	"Table entry display string for plswTimeDatasetLoad"
	::={plswTimeDatasetLoadLevelEntry 1}

plswTimeDatasetLoadLevelVal OBJECT-TYPE
	SYNTAX	 TimeTicks
	MAX-ACCESS  read-only
	STATUS      current
	DESCRIPTION
	"Table entry attribute for plswTimeDatasetLoad"
	::={plswTimeDatasetLoadLevelEntry 2}


plswTimeDatasetSubitemAndSubscriberCount	OBJECT IDENTIFIER ::={plsw 49}

plswTimeDatasetSubitemAndSubscriberCountVal	OBJECT-TYPE
	SYNTAX	 TimeTicks
	MAX-ACCESS read-only
	STATUS current
	DESCRIPTION "Dataset, Time for counting subitems and subscribers"

	::={plswTimeDatasetSubitemAndSubscriberCount 1}

plswTimeDatasetSubitemAndSubscriberCountLevelTable OBJECT-TYPE
	SYNTAX      SEQUENCE OF PlswTimeDatasetSubitemAndSubscriberCountLevelEntry
	MAX-ACCESS  not-accessible
	STATUS      current
	DESCRIPTION
	"Table for plswTimeDatasetSubitemAndSubscriberCount"
	::={plswTimeDatasetSubitemAndSubscriberCount 2}

plswTimeDatasetSubitemAndSubscriberCountLevelEntry OBJECT-TYPE
	SYNTAX      PlswTimeDatasetSubitemAndSubscriberCountLevelEntry
	MAX-ACCESS  not-accessible
	STATUS      current
	DESCRIPTION
	"Table entry for plswTimeDatasetSubitemAndSubscriberCount"
	INDEX { plswTimeDatasetSubitemAndSubscriberCountLevelName }
	::={plswTimeDatasetSubitemAndSubscriberCountLevelTable 1}

PlswTimeDatasetSubitemAndSubscriberCountLevelEntry ::=
	SEQUENCE {
		plswTimeDatasetSubitemAndSubscriberCountLevelName	DisplayString,
		plswTimeDatasetSubitemAndSubscriberCountLevelVal	TimeTicks
	}

plswTimeDatasetSubitemAndSubscriberCountLevelName OBJECT-TYPE
	SYNTAX      DisplayString
	MAX-ACCESS  not-accessible
	STATUS      current
	DESCRIPTION
	"Table entry display string for plswTimeDatasetSubitemAndSubscriberCount"
	::={plswTimeDatasetSubitemAndSubscriberCountLevelEntry 1}

plswTimeDatasetSubitemAndSubscriberCountLevelVal OBJECT-TYPE
	SYNTAX	 TimeTicks
	MAX-ACCESS  read-only
	STATUS      current
	DESCRIPTION
	"Table entry attribute for plswTimeDatasetSubitemAndSubscriberCount"
	::={plswTimeDatasetSubitemAndSubscriberCountLevelEntry 2}


rulesetDaemon	OBJECT IDENTIFIER ::={sysdiag 138}

rulesetDaemonReaperRecvBuf	OBJECT IDENTIFIER ::={rulesetDaemon 1}

rulesetDaemonReaperRecvBufVal	OBJECT-TYPE
	SYNTAX	 CounterBasedGauge64
	MAX-ACCESS read-only
	STATUS current
	DESCRIPTION "Reaper receive buffer usage"

	::={rulesetDaemonReaperRecvBuf 1}

rulesetDaemonReaperRecvBufMax	OBJECT-TYPE
	SYNTAX	 CounterBasedGauge64
	MAX-ACCESS read-only
	STATUS current
	DESCRIPTION "Reaper receive buffer usage"

	::={rulesetDaemonReaperRecvBuf 3}

rulesetDaemonReaperRecvBufLevelTable OBJECT-TYPE
	SYNTAX      SEQUENCE OF RulesetDaemonReaperRecvBufLevelEntry
	MAX-ACCESS  not-accessible
	STATUS      current
	DESCRIPTION
	"Table for rulesetDaemonReaperRecvBuf"
	::={rulesetDaemonReaperRecvBuf 4}

rulesetDaemonReaperRecvBufLevelEntry OBJECT-TYPE
	SYNTAX      RulesetDaemonReaperRecvBufLevelEntry
	MAX-ACCESS  not-accessible
	STATUS      current
	DESCRIPTION
	"Table entry for rulesetDaemonReaperRecvBuf"
	INDEX { rulesetDaemonReaperRecvBufLevelName }
	::={rulesetDaemonReaperRecvBufLevelTable 1}

RulesetDaemonReaperRecvBufLevelEntry ::=
	SEQUENCE {
		rulesetDaemonReaperRecvBufLevelName	DisplayString,
		rulesetDaemonReaperRecvBufLevelVal	CounterBasedGauge64,
		rulesetDaemonReaperRecvBufLevelMax	CounterBasedGauge64
	}

rulesetDaemonReaperRecvBufLevelName OBJECT-TYPE
	SYNTAX      DisplayString
	MAX-ACCESS  not-accessible
	STATUS      current
	DESCRIPTION
	"Table entry display string for rulesetDaemonReaperRecvBuf"
	::={rulesetDaemonReaperRecvBufLevelEntry 1}

rulesetDaemonReaperRecvBufLevelVal OBJECT-TYPE
	SYNTAX	 CounterBasedGauge64
	MAX-ACCESS  read-only
	STATUS      current
	DESCRIPTION
	"Table entry attribute for rulesetDaemonReaperRecvBuf"
	::={rulesetDaemonReaperRecvBufLevelEntry 2}

rulesetDaemonReaperRecvBufLevelMax OBJECT-TYPE
	SYNTAX	 CounterBasedGauge64
	MAX-ACCESS  read-only
	STATUS      current
	DESCRIPTION
	"Table entry attribute for rulesetDaemonReaperRecvBuf"
	::={rulesetDaemonReaperRecvBufLevelEntry 4}


rulesetDaemonReaperSendBuf	OBJECT IDENTIFIER ::={rulesetDaemon 2}

rulesetDaemonReaperSendBufVal	OBJECT-TYPE
	SYNTAX	 CounterBasedGauge64
	MAX-ACCESS read-only
	STATUS current
	DESCRIPTION "Reaper send buffer usage"

	::={rulesetDaemonReaperSendBuf 1}

rulesetDaemonReaperSendBufMax	OBJECT-TYPE
	SYNTAX	 CounterBasedGauge64
	MAX-ACCESS read-only
	STATUS current
	DESCRIPTION "Reaper send buffer usage"

	::={rulesetDaemonReaperSendBuf 3}

rulesetDaemonReaperSendBufLevelTable OBJECT-TYPE
	SYNTAX      SEQUENCE OF RulesetDaemonReaperSendBufLevelEntry
	MAX-ACCESS  not-accessible
	STATUS      current
	DESCRIPTION
	"Table for rulesetDaemonReaperSendBuf"
	::={rulesetDaemonReaperSendBuf 4}

rulesetDaemonReaperSendBufLevelEntry OBJECT-TYPE
	SYNTAX      RulesetDaemonReaperSendBufLevelEntry
	MAX-ACCESS  not-accessible
	STATUS      current
	DESCRIPTION
	"Table entry for rulesetDaemonReaperSendBuf"
	INDEX { rulesetDaemonReaperSendBufLevelName }
	::={rulesetDaemonReaperSendBufLevelTable 1}

RulesetDaemonReaperSendBufLevelEntry ::=
	SEQUENCE {
		rulesetDaemonReaperSendBufLevelName	DisplayString,
		rulesetDaemonReaperSendBufLevelVal	CounterBasedGauge64,
		rulesetDaemonReaperSendBufLevelMax	CounterBasedGauge64
	}

rulesetDaemonReaperSendBufLevelName OBJECT-TYPE
	SYNTAX      DisplayString
	MAX-ACCESS  not-accessible
	STATUS      current
	DESCRIPTION
	"Table entry display string for rulesetDaemonReaperSendBuf"
	::={rulesetDaemonReaperSendBufLevelEntry 1}

rulesetDaemonReaperSendBufLevelVal OBJECT-TYPE
	SYNTAX	 CounterBasedGauge64
	MAX-ACCESS  read-only
	STATUS      current
	DESCRIPTION
	"Table entry attribute for rulesetDaemonReaperSendBuf"
	::={rulesetDaemonReaperSendBufLevelEntry 2}

rulesetDaemonReaperSendBufLevelMax OBJECT-TYPE
	SYNTAX	 CounterBasedGauge64
	MAX-ACCESS  read-only
	STATUS      current
	DESCRIPTION
	"Table entry attribute for rulesetDaemonReaperSendBuf"
	::={rulesetDaemonReaperSendBufLevelEntry 4}


rulesetDaemonPldbIoHandlers	OBJECT IDENTIFIER ::={rulesetDaemon 3}

rulesetDaemonPldbIoHandlersVal	OBJECT-TYPE
	SYNTAX	 CounterBasedGauge64
	MAX-ACCESS read-only
	STATUS current
	DESCRIPTION "PLDB IO Handlers"

	::={rulesetDaemonPldbIoHandlers 1}

rulesetDaemonPldbIoHandlersMax	OBJECT-TYPE
	SYNTAX	 CounterBasedGauge64
	MAX-ACCESS read-only
	STATUS current
	DESCRIPTION "PLDB IO Handlers"

	::={rulesetDaemonPldbIoHandlers 3}

rulesetDaemonPldbIoHandlersLevelTable OBJECT-TYPE
	SYNTAX      SEQUENCE OF RulesetDaemonPldbIoHandlersLevelEntry
	MAX-ACCESS  not-accessible
	STATUS      current
	DESCRIPTION
	"Table for rulesetDaemonPldbIoHandlers"
	::={rulesetDaemonPldbIoHandlers 4}

rulesetDaemonPldbIoHandlersLevelEntry OBJECT-TYPE
	SYNTAX      RulesetDaemonPldbIoHandlersLevelEntry
	MAX-ACCESS  not-accessible
	STATUS      current
	DESCRIPTION
	"Table entry for rulesetDaemonPldbIoHandlers"
	INDEX { rulesetDaemonPldbIoHandlersLevelName }
	::={rulesetDaemonPldbIoHandlersLevelTable 1}

RulesetDaemonPldbIoHandlersLevelEntry ::=
	SEQUENCE {
		rulesetDaemonPldbIoHandlersLevelName	DisplayString,
		rulesetDaemonPldbIoHandlersLevelVal	CounterBasedGauge64,
		rulesetDaemonPldbIoHandlersLevelMax	CounterBasedGauge64
	}

rulesetDaemonPldbIoHandlersLevelName OBJECT-TYPE
	SYNTAX      DisplayString
	MAX-ACCESS  not-accessible
	STATUS      current
	DESCRIPTION
	"Table entry display string for rulesetDaemonPldbIoHandlers"
	::={rulesetDaemonPldbIoHandlersLevelEntry 1}

rulesetDaemonPldbIoHandlersLevelVal OBJECT-TYPE
	SYNTAX	 CounterBasedGauge64
	MAX-ACCESS  read-only
	STATUS      current
	DESCRIPTION
	"Table entry attribute for rulesetDaemonPldbIoHandlers"
	::={rulesetDaemonPldbIoHandlersLevelEntry 2}

rulesetDaemonPldbIoHandlersLevelMax OBJECT-TYPE
	SYNTAX	 CounterBasedGauge64
	MAX-ACCESS  read-only
	STATUS      current
	DESCRIPTION
	"Table entry attribute for rulesetDaemonPldbIoHandlers"
	::={rulesetDaemonPldbIoHandlersLevelEntry 4}


ipfix	OBJECT IDENTIFIER ::={sysdiag 139}

ipfixConnections	OBJECT IDENTIFIER ::={ipfix 1}

ipfixConnectionsVal	OBJECT-TYPE
	SYNTAX	 CounterBasedGauge64
	MAX-ACCESS read-only
	STATUS current
	DESCRIPTION "Connection table size"

	::={ipfixConnections 1}

ipfixConnectionsMax	OBJECT-TYPE
	SYNTAX	 CounterBasedGauge64
	MAX-ACCESS read-only
	STATUS current
	DESCRIPTION "Connection table size"

	::={ipfixConnections 3}

ipfixConnectionsLevelTable OBJECT-TYPE
	SYNTAX      SEQUENCE OF IpfixConnectionsLevelEntry
	MAX-ACCESS  not-accessible
	STATUS      current
	DESCRIPTION
	"Table for ipfixConnections"
	::={ipfixConnections 4}

ipfixConnectionsLevelEntry OBJECT-TYPE
	SYNTAX      IpfixConnectionsLevelEntry
	MAX-ACCESS  not-accessible
	STATUS      current
	DESCRIPTION
	"Table entry for ipfixConnections"
	INDEX { ipfixConnectionsLevelName }
	::={ipfixConnectionsLevelTable 1}

IpfixConnectionsLevelEntry ::=
	SEQUENCE {
		ipfixConnectionsLevelName	DisplayString,
		ipfixConnectionsLevelVal	CounterBasedGauge64,
		ipfixConnectionsLevelMax	CounterBasedGauge64
	}

ipfixConnectionsLevelName OBJECT-TYPE
	SYNTAX      DisplayString
	MAX-ACCESS  not-accessible
	STATUS      current
	DESCRIPTION
	"Table entry display string for ipfixConnections"
	::={ipfixConnectionsLevelEntry 1}

ipfixConnectionsLevelVal OBJECT-TYPE
	SYNTAX	 CounterBasedGauge64
	MAX-ACCESS  read-only
	STATUS      current
	DESCRIPTION
	"Table entry attribute for ipfixConnections"
	::={ipfixConnectionsLevelEntry 2}

ipfixConnectionsLevelMax OBJECT-TYPE
	SYNTAX	 CounterBasedGauge64
	MAX-ACCESS  read-only
	STATUS      current
	DESCRIPTION
	"Table entry attribute for ipfixConnections"
	::={ipfixConnectionsLevelEntry 4}


ipfixConnUpdates	OBJECT IDENTIFIER ::={ipfix 2}

ipfixConnUpdatesVal	OBJECT-TYPE
	SYNTAX	 Counter64
	MAX-ACCESS read-only
	STATUS current
	DESCRIPTION "Connection updates"

	::={ipfixConnUpdates 1}

ipfixConnUpdatesMom	OBJECT-TYPE
	SYNTAX	 CounterBasedGauge64
	MAX-ACCESS read-only
	STATUS current
	DESCRIPTION "Connection updates"

	::={ipfixConnUpdates 2}

ipfixConnUpdatesMax	OBJECT-TYPE
	SYNTAX	 CounterBasedGauge64
	MAX-ACCESS read-only
	STATUS current
	DESCRIPTION "Connection updates"

	::={ipfixConnUpdates 3}

ipfixConnUpdatesLevelTable OBJECT-TYPE
	SYNTAX      SEQUENCE OF IpfixConnUpdatesLevelEntry
	MAX-ACCESS  not-accessible
	STATUS      current
	DESCRIPTION
	"Table for ipfixConnUpdates"
	::={ipfixConnUpdates 4}

ipfixConnUpdatesLevelEntry OBJECT-TYPE
	SYNTAX      IpfixConnUpdatesLevelEntry
	MAX-ACCESS  not-accessible
	STATUS      current
	DESCRIPTION
	"Table entry for ipfixConnUpdates"
	INDEX { ipfixConnUpdatesLevelName }
	::={ipfixConnUpdatesLevelTable 1}

IpfixConnUpdatesLevelEntry ::=
	SEQUENCE {
		ipfixConnUpdatesLevelName	DisplayString,
		ipfixConnUpdatesLevelVal	Counter64,
		ipfixConnUpdatesLevelMom	CounterBasedGauge64,
		ipfixConnUpdatesLevelMax	CounterBasedGauge64
	}

ipfixConnUpdatesLevelName OBJECT-TYPE
	SYNTAX      DisplayString
	MAX-ACCESS  not-accessible
	STATUS      current
	DESCRIPTION
	"Table entry display string for ipfixConnUpdates"
	::={ipfixConnUpdatesLevelEntry 1}

ipfixConnUpdatesLevelVal OBJECT-TYPE
	SYNTAX	 Counter64
	MAX-ACCESS  read-only
	STATUS      current
	DESCRIPTION
	"Table entry attribute for ipfixConnUpdates"
	::={ipfixConnUpdatesLevelEntry 2}

ipfixConnUpdatesLevelMom OBJECT-TYPE
	SYNTAX	 CounterBasedGauge64
	MAX-ACCESS  read-only
	STATUS      current
	DESCRIPTION
	"Table entry attribute for ipfixConnUpdates"
	::={ipfixConnUpdatesLevelEntry 3}

ipfixConnUpdatesLevelMax OBJECT-TYPE
	SYNTAX	 CounterBasedGauge64
	MAX-ACCESS  read-only
	STATUS      current
	DESCRIPTION
	"Table entry attribute for ipfixConnUpdates"
	::={ipfixConnUpdatesLevelEntry 4}


ipfixExportedIpv4Records	OBJECT IDENTIFIER ::={ipfix 3}

ipfixExportedIpv4RecordsVal	OBJECT-TYPE
	SYNTAX	 Counter64
	MAX-ACCESS read-only
	STATUS obsolete
	DESCRIPTION "Exported Records IPv4"

	::={ipfixExportedIpv4Records 1}

ipfixExportedIpv4RecordsMom	OBJECT-TYPE
	SYNTAX	 CounterBasedGauge64
	MAX-ACCESS read-only
	STATUS obsolete
	DESCRIPTION "Exported Records IPv4"

	::={ipfixExportedIpv4Records 2}

ipfixExportedIpv4RecordsMax	OBJECT-TYPE
	SYNTAX	 CounterBasedGauge64
	MAX-ACCESS read-only
	STATUS obsolete
	DESCRIPTION "Exported Records IPv4"

	::={ipfixExportedIpv4Records 3}

ipfixExportedIpv4RecordsLevelTable OBJECT-TYPE
	SYNTAX      SEQUENCE OF IpfixExportedIpv4RecordsLevelEntry
	MAX-ACCESS  not-accessible
	STATUS      current
	DESCRIPTION
	"Table for ipfixExportedIpv4Records"
	::={ipfixExportedIpv4Records 4}

ipfixExportedIpv4RecordsLevelEntry OBJECT-TYPE
	SYNTAX      IpfixExportedIpv4RecordsLevelEntry
	MAX-ACCESS  not-accessible
	STATUS      current
	DESCRIPTION
	"Table entry for ipfixExportedIpv4Records"
	INDEX { ipfixExportedIpv4RecordsLevelName }
	::={ipfixExportedIpv4RecordsLevelTable 1}

IpfixExportedIpv4RecordsLevelEntry ::=
	SEQUENCE {
		ipfixExportedIpv4RecordsLevelName	DisplayString,
		ipfixExportedIpv4RecordsLevelVal	Counter64,
		ipfixExportedIpv4RecordsLevelMom	CounterBasedGauge64,
		ipfixExportedIpv4RecordsLevelMax	CounterBasedGauge64
	}

ipfixExportedIpv4RecordsLevelName OBJECT-TYPE
	SYNTAX      DisplayString
	MAX-ACCESS  not-accessible
	STATUS      current
	DESCRIPTION
	"Table entry display string for ipfixExportedIpv4Records"
	::={ipfixExportedIpv4RecordsLevelEntry 1}

ipfixExportedIpv4RecordsLevelVal OBJECT-TYPE
	SYNTAX	 Counter64
	MAX-ACCESS  read-only
	STATUS      current
	DESCRIPTION
	"Table entry attribute for ipfixExportedIpv4Records"
	::={ipfixExportedIpv4RecordsLevelEntry 2}

ipfixExportedIpv4RecordsLevelMom OBJECT-TYPE
	SYNTAX	 CounterBasedGauge64
	MAX-ACCESS  read-only
	STATUS      current
	DESCRIPTION
	"Table entry attribute for ipfixExportedIpv4Records"
	::={ipfixExportedIpv4RecordsLevelEntry 3}

ipfixExportedIpv4RecordsLevelMax OBJECT-TYPE
	SYNTAX	 CounterBasedGauge64
	MAX-ACCESS  read-only
	STATUS      current
	DESCRIPTION
	"Table entry attribute for ipfixExportedIpv4Records"
	::={ipfixExportedIpv4RecordsLevelEntry 4}


ipfixExportedIpv6Records	OBJECT IDENTIFIER ::={ipfix 4}

ipfixExportedIpv6RecordsVal	OBJECT-TYPE
	SYNTAX	 Counter64
	MAX-ACCESS read-only
	STATUS obsolete
	DESCRIPTION "Exported Records IPv6"

	::={ipfixExportedIpv6Records 1}

ipfixExportedIpv6RecordsMom	OBJECT-TYPE
	SYNTAX	 CounterBasedGauge64
	MAX-ACCESS read-only
	STATUS obsolete
	DESCRIPTION "Exported Records IPv6"

	::={ipfixExportedIpv6Records 2}

ipfixExportedIpv6RecordsMax	OBJECT-TYPE
	SYNTAX	 CounterBasedGauge64
	MAX-ACCESS read-only
	STATUS obsolete
	DESCRIPTION "Exported Records IPv6"

	::={ipfixExportedIpv6Records 3}

ipfixExportedIpv6RecordsLevelTable OBJECT-TYPE
	SYNTAX      SEQUENCE OF IpfixExportedIpv6RecordsLevelEntry
	MAX-ACCESS  not-accessible
	STATUS      current
	DESCRIPTION
	"Table for ipfixExportedIpv6Records"
	::={ipfixExportedIpv6Records 4}

ipfixExportedIpv6RecordsLevelEntry OBJECT-TYPE
	SYNTAX      IpfixExportedIpv6RecordsLevelEntry
	MAX-ACCESS  not-accessible
	STATUS      current
	DESCRIPTION
	"Table entry for ipfixExportedIpv6Records"
	INDEX { ipfixExportedIpv6RecordsLevelName }
	::={ipfixExportedIpv6RecordsLevelTable 1}

IpfixExportedIpv6RecordsLevelEntry ::=
	SEQUENCE {
		ipfixExportedIpv6RecordsLevelName	DisplayString,
		ipfixExportedIpv6RecordsLevelVal	Counter64,
		ipfixExportedIpv6RecordsLevelMom	CounterBasedGauge64,
		ipfixExportedIpv6RecordsLevelMax	CounterBasedGauge64
	}

ipfixExportedIpv6RecordsLevelName OBJECT-TYPE
	SYNTAX      DisplayString
	MAX-ACCESS  not-accessible
	STATUS      current
	DESCRIPTION
	"Table entry display string for ipfixExportedIpv6Records"
	::={ipfixExportedIpv6RecordsLevelEntry 1}

ipfixExportedIpv6RecordsLevelVal OBJECT-TYPE
	SYNTAX	 Counter64
	MAX-ACCESS  read-only
	STATUS      current
	DESCRIPTION
	"Table entry attribute for ipfixExportedIpv6Records"
	::={ipfixExportedIpv6RecordsLevelEntry 2}

ipfixExportedIpv6RecordsLevelMom OBJECT-TYPE
	SYNTAX	 CounterBasedGauge64
	MAX-ACCESS  read-only
	STATUS      current
	DESCRIPTION
	"Table entry attribute for ipfixExportedIpv6Records"
	::={ipfixExportedIpv6RecordsLevelEntry 3}

ipfixExportedIpv6RecordsLevelMax OBJECT-TYPE
	SYNTAX	 CounterBasedGauge64
	MAX-ACCESS  read-only
	STATUS      current
	DESCRIPTION
	"Table entry attribute for ipfixExportedIpv6Records"
	::={ipfixExportedIpv6RecordsLevelEntry 4}


ipfixExportedIpv4Sets	OBJECT IDENTIFIER ::={ipfix 5}

ipfixExportedIpv4SetsVal	OBJECT-TYPE
	SYNTAX	 Counter64
	MAX-ACCESS read-only
	STATUS obsolete
	DESCRIPTION "Exported Sets IPv4"

	::={ipfixExportedIpv4Sets 1}

ipfixExportedIpv4SetsMom	OBJECT-TYPE
	SYNTAX	 CounterBasedGauge64
	MAX-ACCESS read-only
	STATUS obsolete
	DESCRIPTION "Exported Sets IPv4"

	::={ipfixExportedIpv4Sets 2}

ipfixExportedIpv4SetsMax	OBJECT-TYPE
	SYNTAX	 CounterBasedGauge64
	MAX-ACCESS read-only
	STATUS obsolete
	DESCRIPTION "Exported Sets IPv4"

	::={ipfixExportedIpv4Sets 3}

ipfixExportedIpv4SetsLevelTable OBJECT-TYPE
	SYNTAX      SEQUENCE OF IpfixExportedIpv4SetsLevelEntry
	MAX-ACCESS  not-accessible
	STATUS      current
	DESCRIPTION
	"Table for ipfixExportedIpv4Sets"
	::={ipfixExportedIpv4Sets 4}

ipfixExportedIpv4SetsLevelEntry OBJECT-TYPE
	SYNTAX      IpfixExportedIpv4SetsLevelEntry
	MAX-ACCESS  not-accessible
	STATUS      current
	DESCRIPTION
	"Table entry for ipfixExportedIpv4Sets"
	INDEX { ipfixExportedIpv4SetsLevelName }
	::={ipfixExportedIpv4SetsLevelTable 1}

IpfixExportedIpv4SetsLevelEntry ::=
	SEQUENCE {
		ipfixExportedIpv4SetsLevelName	DisplayString,
		ipfixExportedIpv4SetsLevelVal	Counter64,
		ipfixExportedIpv4SetsLevelMom	CounterBasedGauge64,
		ipfixExportedIpv4SetsLevelMax	CounterBasedGauge64
	}

ipfixExportedIpv4SetsLevelName OBJECT-TYPE
	SYNTAX      DisplayString
	MAX-ACCESS  not-accessible
	STATUS      current
	DESCRIPTION
	"Table entry display string for ipfixExportedIpv4Sets"
	::={ipfixExportedIpv4SetsLevelEntry 1}

ipfixExportedIpv4SetsLevelVal OBJECT-TYPE
	SYNTAX	 Counter64
	MAX-ACCESS  read-only
	STATUS      current
	DESCRIPTION
	"Table entry attribute for ipfixExportedIpv4Sets"
	::={ipfixExportedIpv4SetsLevelEntry 2}

ipfixExportedIpv4SetsLevelMom OBJECT-TYPE
	SYNTAX	 CounterBasedGauge64
	MAX-ACCESS  read-only
	STATUS      current
	DESCRIPTION
	"Table entry attribute for ipfixExportedIpv4Sets"
	::={ipfixExportedIpv4SetsLevelEntry 3}

ipfixExportedIpv4SetsLevelMax OBJECT-TYPE
	SYNTAX	 CounterBasedGauge64
	MAX-ACCESS  read-only
	STATUS      current
	DESCRIPTION
	"Table entry attribute for ipfixExportedIpv4Sets"
	::={ipfixExportedIpv4SetsLevelEntry 4}


ipfixExportedIpv6Sets	OBJECT IDENTIFIER ::={ipfix 6}

ipfixExportedIpv6SetsVal	OBJECT-TYPE
	SYNTAX	 Counter64
	MAX-ACCESS read-only
	STATUS obsolete
	DESCRIPTION "Exported Sets IPv6"

	::={ipfixExportedIpv6Sets 1}

ipfixExportedIpv6SetsMom	OBJECT-TYPE
	SYNTAX	 CounterBasedGauge64
	MAX-ACCESS read-only
	STATUS obsolete
	DESCRIPTION "Exported Sets IPv6"

	::={ipfixExportedIpv6Sets 2}

ipfixExportedIpv6SetsMax	OBJECT-TYPE
	SYNTAX	 CounterBasedGauge64
	MAX-ACCESS read-only
	STATUS obsolete
	DESCRIPTION "Exported Sets IPv6"

	::={ipfixExportedIpv6Sets 3}

ipfixExportedIpv6SetsLevelTable OBJECT-TYPE
	SYNTAX      SEQUENCE OF IpfixExportedIpv6SetsLevelEntry
	MAX-ACCESS  not-accessible
	STATUS      current
	DESCRIPTION
	"Table for ipfixExportedIpv6Sets"
	::={ipfixExportedIpv6Sets 4}

ipfixExportedIpv6SetsLevelEntry OBJECT-TYPE
	SYNTAX      IpfixExportedIpv6SetsLevelEntry
	MAX-ACCESS  not-accessible
	STATUS      current
	DESCRIPTION
	"Table entry for ipfixExportedIpv6Sets"
	INDEX { ipfixExportedIpv6SetsLevelName }
	::={ipfixExportedIpv6SetsLevelTable 1}

IpfixExportedIpv6SetsLevelEntry ::=
	SEQUENCE {
		ipfixExportedIpv6SetsLevelName	DisplayString,
		ipfixExportedIpv6SetsLevelVal	Counter64,
		ipfixExportedIpv6SetsLevelMom	CounterBasedGauge64,
		ipfixExportedIpv6SetsLevelMax	CounterBasedGauge64
	}

ipfixExportedIpv6SetsLevelName OBJECT-TYPE
	SYNTAX      DisplayString
	MAX-ACCESS  not-accessible
	STATUS      current
	DESCRIPTION
	"Table entry display string for ipfixExportedIpv6Sets"
	::={ipfixExportedIpv6SetsLevelEntry 1}

ipfixExportedIpv6SetsLevelVal OBJECT-TYPE
	SYNTAX	 Counter64
	MAX-ACCESS  read-only
	STATUS      current
	DESCRIPTION
	"Table entry attribute for ipfixExportedIpv6Sets"
	::={ipfixExportedIpv6SetsLevelEntry 2}

ipfixExportedIpv6SetsLevelMom OBJECT-TYPE
	SYNTAX	 CounterBasedGauge64
	MAX-ACCESS  read-only
	STATUS      current
	DESCRIPTION
	"Table entry attribute for ipfixExportedIpv6Sets"
	::={ipfixExportedIpv6SetsLevelEntry 3}

ipfixExportedIpv6SetsLevelMax OBJECT-TYPE
	SYNTAX	 CounterBasedGauge64
	MAX-ACCESS  read-only
	STATUS      current
	DESCRIPTION
	"Table entry attribute for ipfixExportedIpv6Sets"
	::={ipfixExportedIpv6SetsLevelEntry 4}


ipfixExportedMsgs	OBJECT IDENTIFIER ::={ipfix 7}

ipfixExportedMsgsVal	OBJECT-TYPE
	SYNTAX	 Counter64
	MAX-ACCESS read-only
	STATUS current
	DESCRIPTION "Exported Ipfix Messages"

	::={ipfixExportedMsgs 1}

ipfixExportedMsgsMom	OBJECT-TYPE
	SYNTAX	 CounterBasedGauge64
	MAX-ACCESS read-only
	STATUS current
	DESCRIPTION "Exported Ipfix Messages"

	::={ipfixExportedMsgs 2}

ipfixExportedMsgsMax	OBJECT-TYPE
	SYNTAX	 CounterBasedGauge64
	MAX-ACCESS read-only
	STATUS current
	DESCRIPTION "Exported Ipfix Messages"

	::={ipfixExportedMsgs 3}

ipfixExportedMsgsLevelTable OBJECT-TYPE
	SYNTAX      SEQUENCE OF IpfixExportedMsgsLevelEntry
	MAX-ACCESS  not-accessible
	STATUS      current
	DESCRIPTION
	"Table for ipfixExportedMsgs"
	::={ipfixExportedMsgs 4}

ipfixExportedMsgsLevelEntry OBJECT-TYPE
	SYNTAX      IpfixExportedMsgsLevelEntry
	MAX-ACCESS  not-accessible
	STATUS      current
	DESCRIPTION
	"Table entry for ipfixExportedMsgs"
	INDEX { ipfixExportedMsgsLevelName }
	::={ipfixExportedMsgsLevelTable 1}

IpfixExportedMsgsLevelEntry ::=
	SEQUENCE {
		ipfixExportedMsgsLevelName	DisplayString,
		ipfixExportedMsgsLevelVal	Counter64,
		ipfixExportedMsgsLevelMom	CounterBasedGauge64,
		ipfixExportedMsgsLevelMax	CounterBasedGauge64
	}

ipfixExportedMsgsLevelName OBJECT-TYPE
	SYNTAX      DisplayString
	MAX-ACCESS  not-accessible
	STATUS      current
	DESCRIPTION
	"Table entry display string for ipfixExportedMsgs"
	::={ipfixExportedMsgsLevelEntry 1}

ipfixExportedMsgsLevelVal OBJECT-TYPE
	SYNTAX	 Counter64
	MAX-ACCESS  read-only
	STATUS      current
	DESCRIPTION
	"Table entry attribute for ipfixExportedMsgs"
	::={ipfixExportedMsgsLevelEntry 2}

ipfixExportedMsgsLevelMom OBJECT-TYPE
	SYNTAX	 CounterBasedGauge64
	MAX-ACCESS  read-only
	STATUS      current
	DESCRIPTION
	"Table entry attribute for ipfixExportedMsgs"
	::={ipfixExportedMsgsLevelEntry 3}

ipfixExportedMsgsLevelMax OBJECT-TYPE
	SYNTAX	 CounterBasedGauge64
	MAX-ACCESS  read-only
	STATUS      current
	DESCRIPTION
	"Table entry attribute for ipfixExportedMsgs"
	::={ipfixExportedMsgsLevelEntry 4}


ipfixDroppedRecords	OBJECT IDENTIFIER ::={ipfix 8}

ipfixDroppedRecordsVal	OBJECT-TYPE
	SYNTAX	 Counter64
	MAX-ACCESS read-only
	STATUS current
	DESCRIPTION "Dropped records"

	::={ipfixDroppedRecords 1}

ipfixDroppedRecordsMom	OBJECT-TYPE
	SYNTAX	 CounterBasedGauge64
	MAX-ACCESS read-only
	STATUS current
	DESCRIPTION "Dropped records"

	::={ipfixDroppedRecords 2}

ipfixDroppedRecordsMax	OBJECT-TYPE
	SYNTAX	 CounterBasedGauge64
	MAX-ACCESS read-only
	STATUS current
	DESCRIPTION "Dropped records"

	::={ipfixDroppedRecords 3}

ipfixDroppedRecordsLevelTable OBJECT-TYPE
	SYNTAX      SEQUENCE OF IpfixDroppedRecordsLevelEntry
	MAX-ACCESS  not-accessible
	STATUS      current
	DESCRIPTION
	"Table for ipfixDroppedRecords"
	::={ipfixDroppedRecords 4}

ipfixDroppedRecordsLevelEntry OBJECT-TYPE
	SYNTAX      IpfixDroppedRecordsLevelEntry
	MAX-ACCESS  not-accessible
	STATUS      current
	DESCRIPTION
	"Table entry for ipfixDroppedRecords"
	INDEX { ipfixDroppedRecordsLevelName }
	::={ipfixDroppedRecordsLevelTable 1}

IpfixDroppedRecordsLevelEntry ::=
	SEQUENCE {
		ipfixDroppedRecordsLevelName	DisplayString,
		ipfixDroppedRecordsLevelVal	Counter64,
		ipfixDroppedRecordsLevelMom	CounterBasedGauge64,
		ipfixDroppedRecordsLevelMax	CounterBasedGauge64
	}

ipfixDroppedRecordsLevelName OBJECT-TYPE
	SYNTAX      DisplayString
	MAX-ACCESS  not-accessible
	STATUS      current
	DESCRIPTION
	"Table entry display string for ipfixDroppedRecords"
	::={ipfixDroppedRecordsLevelEntry 1}

ipfixDroppedRecordsLevelVal OBJECT-TYPE
	SYNTAX	 Counter64
	MAX-ACCESS  read-only
	STATUS      current
	DESCRIPTION
	"Table entry attribute for ipfixDroppedRecords"
	::={ipfixDroppedRecordsLevelEntry 2}

ipfixDroppedRecordsLevelMom OBJECT-TYPE
	SYNTAX	 CounterBasedGauge64
	MAX-ACCESS  read-only
	STATUS      current
	DESCRIPTION
	"Table entry attribute for ipfixDroppedRecords"
	::={ipfixDroppedRecordsLevelEntry 3}

ipfixDroppedRecordsLevelMax OBJECT-TYPE
	SYNTAX	 CounterBasedGauge64
	MAX-ACCESS  read-only
	STATUS      current
	DESCRIPTION
	"Table entry attribute for ipfixDroppedRecords"
	::={ipfixDroppedRecordsLevelEntry 4}


ipfixExportBwUsed	OBJECT IDENTIFIER ::={ipfix 9}

ipfixExportBwUsedVal	OBJECT-TYPE
	SYNTAX	 Counter64
	MAX-ACCESS read-only
	STATUS current
	DESCRIPTION "Export Bandwidth used"

	::={ipfixExportBwUsed 1}

ipfixExportBwUsedMom	OBJECT-TYPE
	SYNTAX	 CounterBasedGauge64
	MAX-ACCESS read-only
	STATUS current
	DESCRIPTION "Export Bandwidth used"

	::={ipfixExportBwUsed 2}

ipfixExportBwUsedMax	OBJECT-TYPE
	SYNTAX	 CounterBasedGauge64
	MAX-ACCESS read-only
	STATUS current
	DESCRIPTION "Export Bandwidth used"

	::={ipfixExportBwUsed 3}

ipfixExportBwUsedLevelTable OBJECT-TYPE
	SYNTAX      SEQUENCE OF IpfixExportBwUsedLevelEntry
	MAX-ACCESS  not-accessible
	STATUS      current
	DESCRIPTION
	"Table for ipfixExportBwUsed"
	::={ipfixExportBwUsed 4}

ipfixExportBwUsedLevelEntry OBJECT-TYPE
	SYNTAX      IpfixExportBwUsedLevelEntry
	MAX-ACCESS  not-accessible
	STATUS      current
	DESCRIPTION
	"Table entry for ipfixExportBwUsed"
	INDEX { ipfixExportBwUsedLevelName }
	::={ipfixExportBwUsedLevelTable 1}

IpfixExportBwUsedLevelEntry ::=
	SEQUENCE {
		ipfixExportBwUsedLevelName	DisplayString,
		ipfixExportBwUsedLevelVal	Counter64,
		ipfixExportBwUsedLevelMom	CounterBasedGauge64,
		ipfixExportBwUsedLevelMax	CounterBasedGauge64
	}

ipfixExportBwUsedLevelName OBJECT-TYPE
	SYNTAX      DisplayString
	MAX-ACCESS  not-accessible
	STATUS      current
	DESCRIPTION
	"Table entry display string for ipfixExportBwUsed"
	::={ipfixExportBwUsedLevelEntry 1}

ipfixExportBwUsedLevelVal OBJECT-TYPE
	SYNTAX	 Counter64
	MAX-ACCESS  read-only
	STATUS      current
	DESCRIPTION
	"Table entry attribute for ipfixExportBwUsed"
	::={ipfixExportBwUsedLevelEntry 2}

ipfixExportBwUsedLevelMom OBJECT-TYPE
	SYNTAX	 CounterBasedGauge64
	MAX-ACCESS  read-only
	STATUS      current
	DESCRIPTION
	"Table entry attribute for ipfixExportBwUsed"
	::={ipfixExportBwUsedLevelEntry 3}

ipfixExportBwUsedLevelMax OBJECT-TYPE
	SYNTAX	 CounterBasedGauge64
	MAX-ACCESS  read-only
	STATUS      current
	DESCRIPTION
	"Table entry attribute for ipfixExportBwUsed"
	::={ipfixExportBwUsedLevelEntry 4}


ipfixExportedRecords	OBJECT IDENTIFIER ::={ipfix 10}

ipfixExportedRecordsVal	OBJECT-TYPE
	SYNTAX	 Counter64
	MAX-ACCESS read-only
	STATUS current
	DESCRIPTION "Exported Records"

	::={ipfixExportedRecords 1}

ipfixExportedRecordsMom	OBJECT-TYPE
	SYNTAX	 CounterBasedGauge64
	MAX-ACCESS read-only
	STATUS current
	DESCRIPTION "Exported Records"

	::={ipfixExportedRecords 2}

ipfixExportedRecordsMax	OBJECT-TYPE
	SYNTAX	 CounterBasedGauge64
	MAX-ACCESS read-only
	STATUS current
	DESCRIPTION "Exported Records"

	::={ipfixExportedRecords 3}

ipfixExportedRecordsLevelTable OBJECT-TYPE
	SYNTAX      SEQUENCE OF IpfixExportedRecordsLevelEntry
	MAX-ACCESS  not-accessible
	STATUS      current
	DESCRIPTION
	"Table for ipfixExportedRecords"
	::={ipfixExportedRecords 4}

ipfixExportedRecordsLevelEntry OBJECT-TYPE
	SYNTAX      IpfixExportedRecordsLevelEntry
	MAX-ACCESS  not-accessible
	STATUS      current
	DESCRIPTION
	"Table entry for ipfixExportedRecords"
	INDEX { ipfixExportedRecordsLevelName }
	::={ipfixExportedRecordsLevelTable 1}

IpfixExportedRecordsLevelEntry ::=
	SEQUENCE {
		ipfixExportedRecordsLevelName	DisplayString,
		ipfixExportedRecordsLevelVal	Counter64,
		ipfixExportedRecordsLevelMom	CounterBasedGauge64,
		ipfixExportedRecordsLevelMax	CounterBasedGauge64
	}

ipfixExportedRecordsLevelName OBJECT-TYPE
	SYNTAX      DisplayString
	MAX-ACCESS  not-accessible
	STATUS      current
	DESCRIPTION
	"Table entry display string for ipfixExportedRecords"
	::={ipfixExportedRecordsLevelEntry 1}

ipfixExportedRecordsLevelVal OBJECT-TYPE
	SYNTAX	 Counter64
	MAX-ACCESS  read-only
	STATUS      current
	DESCRIPTION
	"Table entry attribute for ipfixExportedRecords"
	::={ipfixExportedRecordsLevelEntry 2}

ipfixExportedRecordsLevelMom OBJECT-TYPE
	SYNTAX	 CounterBasedGauge64
	MAX-ACCESS  read-only
	STATUS      current
	DESCRIPTION
	"Table entry attribute for ipfixExportedRecords"
	::={ipfixExportedRecordsLevelEntry 3}

ipfixExportedRecordsLevelMax OBJECT-TYPE
	SYNTAX	 CounterBasedGauge64
	MAX-ACCESS  read-only
	STATUS      current
	DESCRIPTION
	"Table entry attribute for ipfixExportedRecords"
	::={ipfixExportedRecordsLevelEntry 4}


ipfixRingbufUsage	OBJECT IDENTIFIER ::={ipfix 11}

ipfixRingbufUsageVal	OBJECT-TYPE
	SYNTAX	 CounterBasedGauge64
	MAX-ACCESS read-only
	STATUS current
	DESCRIPTION "Receive Ringbuffer usage"

	::={ipfixRingbufUsage 1}

ipfixRingbufUsageMax	OBJECT-TYPE
	SYNTAX	 CounterBasedGauge64
	MAX-ACCESS read-only
	STATUS current
	DESCRIPTION "Receive Ringbuffer usage"

	::={ipfixRingbufUsage 3}

ipfixRingbufUsageLevelTable OBJECT-TYPE
	SYNTAX      SEQUENCE OF IpfixRingbufUsageLevelEntry
	MAX-ACCESS  not-accessible
	STATUS      current
	DESCRIPTION
	"Table for ipfixRingbufUsage"
	::={ipfixRingbufUsage 4}

ipfixRingbufUsageLevelEntry OBJECT-TYPE
	SYNTAX      IpfixRingbufUsageLevelEntry
	MAX-ACCESS  not-accessible
	STATUS      current
	DESCRIPTION
	"Table entry for ipfixRingbufUsage"
	INDEX { ipfixRingbufUsageLevelName }
	::={ipfixRingbufUsageLevelTable 1}

IpfixRingbufUsageLevelEntry ::=
	SEQUENCE {
		ipfixRingbufUsageLevelName	DisplayString,
		ipfixRingbufUsageLevelVal	CounterBasedGauge64,
		ipfixRingbufUsageLevelMax	CounterBasedGauge64
	}

ipfixRingbufUsageLevelName OBJECT-TYPE
	SYNTAX      DisplayString
	MAX-ACCESS  not-accessible
	STATUS      current
	DESCRIPTION
	"Table entry display string for ipfixRingbufUsage"
	::={ipfixRingbufUsageLevelEntry 1}

ipfixRingbufUsageLevelVal OBJECT-TYPE
	SYNTAX	 CounterBasedGauge64
	MAX-ACCESS  read-only
	STATUS      current
	DESCRIPTION
	"Table entry attribute for ipfixRingbufUsage"
	::={ipfixRingbufUsageLevelEntry 2}

ipfixRingbufUsageLevelMax OBJECT-TYPE
	SYNTAX	 CounterBasedGauge64
	MAX-ACCESS  read-only
	STATUS      current
	DESCRIPTION
	"Table entry attribute for ipfixRingbufUsage"
	::={ipfixRingbufUsageLevelEntry 4}


ipfixConnects	OBJECT IDENTIFIER ::={ipfix 12}

ipfixConnectsVal	OBJECT-TYPE
	SYNTAX	 CounterBasedGauge64
	MAX-ACCESS read-only
	STATUS current
	DESCRIPTION "Connects"

	::={ipfixConnects 1}

ipfixConnectsMax	OBJECT-TYPE
	SYNTAX	 CounterBasedGauge64
	MAX-ACCESS read-only
	STATUS current
	DESCRIPTION "Connects"

	::={ipfixConnects 3}

ipfixConnectsLevelTable OBJECT-TYPE
	SYNTAX      SEQUENCE OF IpfixConnectsLevelEntry
	MAX-ACCESS  not-accessible
	STATUS      current
	DESCRIPTION
	"Table for ipfixConnects"
	::={ipfixConnects 4}

ipfixConnectsLevelEntry OBJECT-TYPE
	SYNTAX      IpfixConnectsLevelEntry
	MAX-ACCESS  not-accessible
	STATUS      current
	DESCRIPTION
	"Table entry for ipfixConnects"
	INDEX { ipfixConnectsLevelName }
	::={ipfixConnectsLevelTable 1}

IpfixConnectsLevelEntry ::=
	SEQUENCE {
		ipfixConnectsLevelName	DisplayString,
		ipfixConnectsLevelVal	CounterBasedGauge64,
		ipfixConnectsLevelMax	CounterBasedGauge64
	}

ipfixConnectsLevelName OBJECT-TYPE
	SYNTAX      DisplayString
	MAX-ACCESS  not-accessible
	STATUS      current
	DESCRIPTION
	"Table entry display string for ipfixConnects"
	::={ipfixConnectsLevelEntry 1}

ipfixConnectsLevelVal OBJECT-TYPE
	SYNTAX	 CounterBasedGauge64
	MAX-ACCESS  read-only
	STATUS      current
	DESCRIPTION
	"Table entry attribute for ipfixConnects"
	::={ipfixConnectsLevelEntry 2}

ipfixConnectsLevelMax OBJECT-TYPE
	SYNTAX	 CounterBasedGauge64
	MAX-ACCESS  read-only
	STATUS      current
	DESCRIPTION
	"Table entry attribute for ipfixConnects"
	::={ipfixConnectsLevelEntry 4}


dynIPs	OBJECT IDENTIFIER ::={ipfix 13}

dynIPsVal	OBJECT-TYPE
	SYNTAX	 CounterBasedGauge64
	MAX-ACCESS read-only
	STATUS obsolete
	DESCRIPTION "Dynamic IP count"

	::={dynIPs 1}

dynIPsMax	OBJECT-TYPE
	SYNTAX	 CounterBasedGauge64
	MAX-ACCESS read-only
	STATUS obsolete
	DESCRIPTION "Dynamic IP count"

	::={dynIPs 3}

dynIPsLevelTable OBJECT-TYPE
	SYNTAX      SEQUENCE OF DynIPsLevelEntry
	MAX-ACCESS  not-accessible
	STATUS      current
	DESCRIPTION
	"Table for dynIPs"
	::={dynIPs 4}

dynIPsLevelEntry OBJECT-TYPE
	SYNTAX      DynIPsLevelEntry
	MAX-ACCESS  not-accessible
	STATUS      current
	DESCRIPTION
	"Table entry for dynIPs"
	INDEX { dynIPsLevelName }
	::={dynIPsLevelTable 1}

DynIPsLevelEntry ::=
	SEQUENCE {
		dynIPsLevelName	DisplayString,
		dynIPsLevelVal	CounterBasedGauge64,
		dynIPsLevelMax	CounterBasedGauge64
	}

dynIPsLevelName OBJECT-TYPE
	SYNTAX      DisplayString
	MAX-ACCESS  not-accessible
	STATUS      current
	DESCRIPTION
	"Table entry display string for dynIPs"
	::={dynIPsLevelEntry 1}

dynIPsLevelVal OBJECT-TYPE
	SYNTAX	 CounterBasedGauge64
	MAX-ACCESS  read-only
	STATUS      current
	DESCRIPTION
	"Table entry attribute for dynIPs"
	::={dynIPsLevelEntry 2}

dynIPsLevelMax OBJECT-TYPE
	SYNTAX	 CounterBasedGauge64
	MAX-ACCESS  read-only
	STATUS      current
	DESCRIPTION
	"Table entry attribute for dynIPs"
	::={dynIPsLevelEntry 4}


dynAdds	OBJECT IDENTIFIER ::={ipfix 14}

dynAddsVal	OBJECT-TYPE
	SYNTAX	 Counter64
	MAX-ACCESS read-only
	STATUS obsolete
	DESCRIPTION "Dynamic Netobject Adds"

	::={dynAdds 1}

dynAddsMom	OBJECT-TYPE
	SYNTAX	 CounterBasedGauge64
	MAX-ACCESS read-only
	STATUS obsolete
	DESCRIPTION "Dynamic Netobject Adds"

	::={dynAdds 2}

dynAddsMax	OBJECT-TYPE
	SYNTAX	 CounterBasedGauge64
	MAX-ACCESS read-only
	STATUS obsolete
	DESCRIPTION "Dynamic Netobject Adds"

	::={dynAdds 3}

dynAddsLevelTable OBJECT-TYPE
	SYNTAX      SEQUENCE OF DynAddsLevelEntry
	MAX-ACCESS  not-accessible
	STATUS      current
	DESCRIPTION
	"Table for dynAdds"
	::={dynAdds 4}

dynAddsLevelEntry OBJECT-TYPE
	SYNTAX      DynAddsLevelEntry
	MAX-ACCESS  not-accessible
	STATUS      current
	DESCRIPTION
	"Table entry for dynAdds"
	INDEX { dynAddsLevelName }
	::={dynAddsLevelTable 1}

DynAddsLevelEntry ::=
	SEQUENCE {
		dynAddsLevelName	DisplayString,
		dynAddsLevelVal	Counter64,
		dynAddsLevelMom	CounterBasedGauge64,
		dynAddsLevelMax	CounterBasedGauge64
	}

dynAddsLevelName OBJECT-TYPE
	SYNTAX      DisplayString
	MAX-ACCESS  not-accessible
	STATUS      current
	DESCRIPTION
	"Table entry display string for dynAdds"
	::={dynAddsLevelEntry 1}

dynAddsLevelVal OBJECT-TYPE
	SYNTAX	 Counter64
	MAX-ACCESS  read-only
	STATUS      current
	DESCRIPTION
	"Table entry attribute for dynAdds"
	::={dynAddsLevelEntry 2}

dynAddsLevelMom OBJECT-TYPE
	SYNTAX	 CounterBasedGauge64
	MAX-ACCESS  read-only
	STATUS      current
	DESCRIPTION
	"Table entry attribute for dynAdds"
	::={dynAddsLevelEntry 3}

dynAddsLevelMax OBJECT-TYPE
	SYNTAX	 CounterBasedGauge64
	MAX-ACCESS  read-only
	STATUS      current
	DESCRIPTION
	"Table entry attribute for dynAdds"
	::={dynAddsLevelEntry 4}


dynRemoves	OBJECT IDENTIFIER ::={ipfix 15}

dynRemovesVal	OBJECT-TYPE
	SYNTAX	 Counter64
	MAX-ACCESS read-only
	STATUS obsolete
	DESCRIPTION "Dynamic Netobject Removes"

	::={dynRemoves 1}

dynRemovesMom	OBJECT-TYPE
	SYNTAX	 CounterBasedGauge64
	MAX-ACCESS read-only
	STATUS obsolete
	DESCRIPTION "Dynamic Netobject Removes"

	::={dynRemoves 2}

dynRemovesMax	OBJECT-TYPE
	SYNTAX	 CounterBasedGauge64
	MAX-ACCESS read-only
	STATUS obsolete
	DESCRIPTION "Dynamic Netobject Removes"

	::={dynRemoves 3}

dynRemovesLevelTable OBJECT-TYPE
	SYNTAX      SEQUENCE OF DynRemovesLevelEntry
	MAX-ACCESS  not-accessible
	STATUS      current
	DESCRIPTION
	"Table for dynRemoves"
	::={dynRemoves 4}

dynRemovesLevelEntry OBJECT-TYPE
	SYNTAX      DynRemovesLevelEntry
	MAX-ACCESS  not-accessible
	STATUS      current
	DESCRIPTION
	"Table entry for dynRemoves"
	INDEX { dynRemovesLevelName }
	::={dynRemovesLevelTable 1}

DynRemovesLevelEntry ::=
	SEQUENCE {
		dynRemovesLevelName	DisplayString,
		dynRemovesLevelVal	Counter64,
		dynRemovesLevelMom	CounterBasedGauge64,
		dynRemovesLevelMax	CounterBasedGauge64
	}

dynRemovesLevelName OBJECT-TYPE
	SYNTAX      DisplayString
	MAX-ACCESS  not-accessible
	STATUS      current
	DESCRIPTION
	"Table entry display string for dynRemoves"
	::={dynRemovesLevelEntry 1}

dynRemovesLevelVal OBJECT-TYPE
	SYNTAX	 Counter64
	MAX-ACCESS  read-only
	STATUS      current
	DESCRIPTION
	"Table entry attribute for dynRemoves"
	::={dynRemovesLevelEntry 2}

dynRemovesLevelMom OBJECT-TYPE
	SYNTAX	 CounterBasedGauge64
	MAX-ACCESS  read-only
	STATUS      current
	DESCRIPTION
	"Table entry attribute for dynRemoves"
	::={dynRemovesLevelEntry 3}

dynRemovesLevelMax OBJECT-TYPE
	SYNTAX	 CounterBasedGauge64
	MAX-ACCESS  read-only
	STATUS      current
	DESCRIPTION
	"Table entry attribute for dynRemoves"
	::={dynRemovesLevelEntry 4}


dynIPLookups	OBJECT IDENTIFIER ::={ipfix 16}

dynIPLookupsVal	OBJECT-TYPE
	SYNTAX	 Counter64
	MAX-ACCESS read-only
	STATUS obsolete
	DESCRIPTION "Dynamic IP lookups"

	::={dynIPLookups 1}

dynIPLookupsMom	OBJECT-TYPE
	SYNTAX	 CounterBasedGauge64
	MAX-ACCESS read-only
	STATUS obsolete
	DESCRIPTION "Dynamic IP lookups"

	::={dynIPLookups 2}

dynIPLookupsMax	OBJECT-TYPE
	SYNTAX	 CounterBasedGauge64
	MAX-ACCESS read-only
	STATUS obsolete
	DESCRIPTION "Dynamic IP lookups"

	::={dynIPLookups 3}

dynIPLookupsLevelTable OBJECT-TYPE
	SYNTAX      SEQUENCE OF DynIPLookupsLevelEntry
	MAX-ACCESS  not-accessible
	STATUS      current
	DESCRIPTION
	"Table for dynIPLookups"
	::={dynIPLookups 4}

dynIPLookupsLevelEntry OBJECT-TYPE
	SYNTAX      DynIPLookupsLevelEntry
	MAX-ACCESS  not-accessible
	STATUS      current
	DESCRIPTION
	"Table entry for dynIPLookups"
	INDEX { dynIPLookupsLevelName }
	::={dynIPLookupsLevelTable 1}

DynIPLookupsLevelEntry ::=
	SEQUENCE {
		dynIPLookupsLevelName	DisplayString,
		dynIPLookupsLevelVal	Counter64,
		dynIPLookupsLevelMom	CounterBasedGauge64,
		dynIPLookupsLevelMax	CounterBasedGauge64
	}

dynIPLookupsLevelName OBJECT-TYPE
	SYNTAX      DisplayString
	MAX-ACCESS  not-accessible
	STATUS      current
	DESCRIPTION
	"Table entry display string for dynIPLookups"
	::={dynIPLookupsLevelEntry 1}

dynIPLookupsLevelVal OBJECT-TYPE
	SYNTAX	 Counter64
	MAX-ACCESS  read-only
	STATUS      current
	DESCRIPTION
	"Table entry attribute for dynIPLookups"
	::={dynIPLookupsLevelEntry 2}

dynIPLookupsLevelMom OBJECT-TYPE
	SYNTAX	 CounterBasedGauge64
	MAX-ACCESS  read-only
	STATUS      current
	DESCRIPTION
	"Table entry attribute for dynIPLookups"
	::={dynIPLookupsLevelEntry 3}

dynIPLookupsLevelMax OBJECT-TYPE
	SYNTAX	 CounterBasedGauge64
	MAX-ACCESS  read-only
	STATUS      current
	DESCRIPTION
	"Table entry attribute for dynIPLookups"
	::={dynIPLookupsLevelEntry 4}


netobjects	OBJECT IDENTIFIER ::={ipfix 17}

netobjectsVal	OBJECT-TYPE
	SYNTAX	 CounterBasedGauge64
	MAX-ACCESS read-only
	STATUS obsolete
	DESCRIPTION "NetObject Count"

	::={netobjects 1}

netobjectsMax	OBJECT-TYPE
	SYNTAX	 CounterBasedGauge64
	MAX-ACCESS read-only
	STATUS obsolete
	DESCRIPTION "NetObject Count"

	::={netobjects 3}

netobjectsLevelTable OBJECT-TYPE
	SYNTAX      SEQUENCE OF NetobjectsLevelEntry
	MAX-ACCESS  not-accessible
	STATUS      current
	DESCRIPTION
	"Table for netobjects"
	::={netobjects 4}

netobjectsLevelEntry OBJECT-TYPE
	SYNTAX      NetobjectsLevelEntry
	MAX-ACCESS  not-accessible
	STATUS      current
	DESCRIPTION
	"Table entry for netobjects"
	INDEX { netobjectsLevelName }
	::={netobjectsLevelTable 1}

NetobjectsLevelEntry ::=
	SEQUENCE {
		netobjectsLevelName	DisplayString,
		netobjectsLevelVal	CounterBasedGauge64,
		netobjectsLevelMax	CounterBasedGauge64
	}

netobjectsLevelName OBJECT-TYPE
	SYNTAX      DisplayString
	MAX-ACCESS  not-accessible
	STATUS      current
	DESCRIPTION
	"Table entry display string for netobjects"
	::={netobjectsLevelEntry 1}

netobjectsLevelVal OBJECT-TYPE
	SYNTAX	 CounterBasedGauge64
	MAX-ACCESS  read-only
	STATUS      current
	DESCRIPTION
	"Table entry attribute for netobjects"
	::={netobjectsLevelEntry 2}

netobjectsLevelMax OBJECT-TYPE
	SYNTAX	 CounterBasedGauge64
	MAX-ACCESS  read-only
	STATUS      current
	DESCRIPTION
	"Table entry attribute for netobjects"
	::={netobjectsLevelEntry 4}


ipfixDroppedMsgsCongestion	OBJECT IDENTIFIER ::={ipfix 18}

ipfixDroppedMsgsCongestionVal	OBJECT-TYPE
	SYNTAX	 Counter64
	MAX-ACCESS read-only
	STATUS current
	DESCRIPTION "Dropped messages, congestion"

	::={ipfixDroppedMsgsCongestion 1}

ipfixDroppedMsgsCongestionMom	OBJECT-TYPE
	SYNTAX	 CounterBasedGauge64
	MAX-ACCESS read-only
	STATUS current
	DESCRIPTION "Dropped messages, congestion"

	::={ipfixDroppedMsgsCongestion 2}

ipfixDroppedMsgsCongestionMax	OBJECT-TYPE
	SYNTAX	 CounterBasedGauge64
	MAX-ACCESS read-only
	STATUS current
	DESCRIPTION "Dropped messages, congestion"

	::={ipfixDroppedMsgsCongestion 3}

ipfixDroppedMsgsCongestionLevelTable OBJECT-TYPE
	SYNTAX      SEQUENCE OF IpfixDroppedMsgsCongestionLevelEntry
	MAX-ACCESS  not-accessible
	STATUS      current
	DESCRIPTION
	"Table for ipfixDroppedMsgsCongestion"
	::={ipfixDroppedMsgsCongestion 4}

ipfixDroppedMsgsCongestionLevelEntry OBJECT-TYPE
	SYNTAX      IpfixDroppedMsgsCongestionLevelEntry
	MAX-ACCESS  not-accessible
	STATUS      current
	DESCRIPTION
	"Table entry for ipfixDroppedMsgsCongestion"
	INDEX { ipfixDroppedMsgsCongestionLevelName }
	::={ipfixDroppedMsgsCongestionLevelTable 1}

IpfixDroppedMsgsCongestionLevelEntry ::=
	SEQUENCE {
		ipfixDroppedMsgsCongestionLevelName	DisplayString,
		ipfixDroppedMsgsCongestionLevelVal	Counter64,
		ipfixDroppedMsgsCongestionLevelMom	CounterBasedGauge64,
		ipfixDroppedMsgsCongestionLevelMax	CounterBasedGauge64
	}

ipfixDroppedMsgsCongestionLevelName OBJECT-TYPE
	SYNTAX      DisplayString
	MAX-ACCESS  not-accessible
	STATUS      current
	DESCRIPTION
	"Table entry display string for ipfixDroppedMsgsCongestion"
	::={ipfixDroppedMsgsCongestionLevelEntry 1}

ipfixDroppedMsgsCongestionLevelVal OBJECT-TYPE
	SYNTAX	 Counter64
	MAX-ACCESS  read-only
	STATUS      current
	DESCRIPTION
	"Table entry attribute for ipfixDroppedMsgsCongestion"
	::={ipfixDroppedMsgsCongestionLevelEntry 2}

ipfixDroppedMsgsCongestionLevelMom OBJECT-TYPE
	SYNTAX	 CounterBasedGauge64
	MAX-ACCESS  read-only
	STATUS      current
	DESCRIPTION
	"Table entry attribute for ipfixDroppedMsgsCongestion"
	::={ipfixDroppedMsgsCongestionLevelEntry 3}

ipfixDroppedMsgsCongestionLevelMax OBJECT-TYPE
	SYNTAX	 CounterBasedGauge64
	MAX-ACCESS  read-only
	STATUS      current
	DESCRIPTION
	"Table entry attribute for ipfixDroppedMsgsCongestion"
	::={ipfixDroppedMsgsCongestionLevelEntry 4}


ipfixNonExportedMsgs	OBJECT IDENTIFIER ::={ipfix 19}

ipfixNonExportedMsgsVal	OBJECT-TYPE
	SYNTAX	 Counter64
	MAX-ACCESS read-only
	STATUS current
	DESCRIPTION "Dropped messages, connection error"

	::={ipfixNonExportedMsgs 1}

ipfixNonExportedMsgsMom	OBJECT-TYPE
	SYNTAX	 CounterBasedGauge64
	MAX-ACCESS read-only
	STATUS current
	DESCRIPTION "Dropped messages, connection error"

	::={ipfixNonExportedMsgs 2}

ipfixNonExportedMsgsMax	OBJECT-TYPE
	SYNTAX	 CounterBasedGauge64
	MAX-ACCESS read-only
	STATUS current
	DESCRIPTION "Dropped messages, connection error"

	::={ipfixNonExportedMsgs 3}

ipfixNonExportedMsgsLevelTable OBJECT-TYPE
	SYNTAX      SEQUENCE OF IpfixNonExportedMsgsLevelEntry
	MAX-ACCESS  not-accessible
	STATUS      current
	DESCRIPTION
	"Table for ipfixNonExportedMsgs"
	::={ipfixNonExportedMsgs 4}

ipfixNonExportedMsgsLevelEntry OBJECT-TYPE
	SYNTAX      IpfixNonExportedMsgsLevelEntry
	MAX-ACCESS  not-accessible
	STATUS      current
	DESCRIPTION
	"Table entry for ipfixNonExportedMsgs"
	INDEX { ipfixNonExportedMsgsLevelName }
	::={ipfixNonExportedMsgsLevelTable 1}

IpfixNonExportedMsgsLevelEntry ::=
	SEQUENCE {
		ipfixNonExportedMsgsLevelName	DisplayString,
		ipfixNonExportedMsgsLevelVal	Counter64,
		ipfixNonExportedMsgsLevelMom	CounterBasedGauge64,
		ipfixNonExportedMsgsLevelMax	CounterBasedGauge64
	}

ipfixNonExportedMsgsLevelName OBJECT-TYPE
	SYNTAX      DisplayString
	MAX-ACCESS  not-accessible
	STATUS      current
	DESCRIPTION
	"Table entry display string for ipfixNonExportedMsgs"
	::={ipfixNonExportedMsgsLevelEntry 1}

ipfixNonExportedMsgsLevelVal OBJECT-TYPE
	SYNTAX	 Counter64
	MAX-ACCESS  read-only
	STATUS      current
	DESCRIPTION
	"Table entry attribute for ipfixNonExportedMsgs"
	::={ipfixNonExportedMsgsLevelEntry 2}

ipfixNonExportedMsgsLevelMom OBJECT-TYPE
	SYNTAX	 CounterBasedGauge64
	MAX-ACCESS  read-only
	STATUS      current
	DESCRIPTION
	"Table entry attribute for ipfixNonExportedMsgs"
	::={ipfixNonExportedMsgsLevelEntry 3}

ipfixNonExportedMsgsLevelMax OBJECT-TYPE
	SYNTAX	 CounterBasedGauge64
	MAX-ACCESS  read-only
	STATUS      current
	DESCRIPTION
	"Table entry attribute for ipfixNonExportedMsgs"
	::={ipfixNonExportedMsgsLevelEntry 4}


ipfixDroppedMsgsInternal	OBJECT IDENTIFIER ::={ipfix 20}

ipfixDroppedMsgsInternalVal	OBJECT-TYPE
	SYNTAX	 Counter64
	MAX-ACCESS read-only
	STATUS current
	DESCRIPTION "Dropped messages, internal buffer exhaustion"

	::={ipfixDroppedMsgsInternal 1}

ipfixDroppedMsgsInternalMom	OBJECT-TYPE
	SYNTAX	 CounterBasedGauge64
	MAX-ACCESS read-only
	STATUS current
	DESCRIPTION "Dropped messages, internal buffer exhaustion"

	::={ipfixDroppedMsgsInternal 2}

ipfixDroppedMsgsInternalMax	OBJECT-TYPE
	SYNTAX	 CounterBasedGauge64
	MAX-ACCESS read-only
	STATUS current
	DESCRIPTION "Dropped messages, internal buffer exhaustion"

	::={ipfixDroppedMsgsInternal 3}

ipfixDroppedMsgsInternalLevelTable OBJECT-TYPE
	SYNTAX      SEQUENCE OF IpfixDroppedMsgsInternalLevelEntry
	MAX-ACCESS  not-accessible
	STATUS      current
	DESCRIPTION
	"Table for ipfixDroppedMsgsInternal"
	::={ipfixDroppedMsgsInternal 4}

ipfixDroppedMsgsInternalLevelEntry OBJECT-TYPE
	SYNTAX      IpfixDroppedMsgsInternalLevelEntry
	MAX-ACCESS  not-accessible
	STATUS      current
	DESCRIPTION
	"Table entry for ipfixDroppedMsgsInternal"
	INDEX { ipfixDroppedMsgsInternalLevelName }
	::={ipfixDroppedMsgsInternalLevelTable 1}

IpfixDroppedMsgsInternalLevelEntry ::=
	SEQUENCE {
		ipfixDroppedMsgsInternalLevelName	DisplayString,
		ipfixDroppedMsgsInternalLevelVal	Counter64,
		ipfixDroppedMsgsInternalLevelMom	CounterBasedGauge64,
		ipfixDroppedMsgsInternalLevelMax	CounterBasedGauge64
	}

ipfixDroppedMsgsInternalLevelName OBJECT-TYPE
	SYNTAX      DisplayString
	MAX-ACCESS  not-accessible
	STATUS      current
	DESCRIPTION
	"Table entry display string for ipfixDroppedMsgsInternal"
	::={ipfixDroppedMsgsInternalLevelEntry 1}

ipfixDroppedMsgsInternalLevelVal OBJECT-TYPE
	SYNTAX	 Counter64
	MAX-ACCESS  read-only
	STATUS      current
	DESCRIPTION
	"Table entry attribute for ipfixDroppedMsgsInternal"
	::={ipfixDroppedMsgsInternalLevelEntry 2}

ipfixDroppedMsgsInternalLevelMom OBJECT-TYPE
	SYNTAX	 CounterBasedGauge64
	MAX-ACCESS  read-only
	STATUS      current
	DESCRIPTION
	"Table entry attribute for ipfixDroppedMsgsInternal"
	::={ipfixDroppedMsgsInternalLevelEntry 3}

ipfixDroppedMsgsInternalLevelMax OBJECT-TYPE
	SYNTAX	 CounterBasedGauge64
	MAX-ACCESS  read-only
	STATUS      current
	DESCRIPTION
	"Table entry attribute for ipfixDroppedMsgsInternal"
	::={ipfixDroppedMsgsInternalLevelEntry 4}


ipfixCollectors	OBJECT IDENTIFIER ::={ipfix 21}

ipfixCollectorsVal	OBJECT-TYPE
	SYNTAX	 CounterBasedGauge64
	MAX-ACCESS read-only
	STATUS current
	DESCRIPTION "Collectors"

	::={ipfixCollectors 1}

ipfixCollectorsMax	OBJECT-TYPE
	SYNTAX	 CounterBasedGauge64
	MAX-ACCESS read-only
	STATUS current
	DESCRIPTION "Collectors"

	::={ipfixCollectors 3}

ipfixCollectorsLevelTable OBJECT-TYPE
	SYNTAX      SEQUENCE OF IpfixCollectorsLevelEntry
	MAX-ACCESS  not-accessible
	STATUS      current
	DESCRIPTION
	"Table for ipfixCollectors"
	::={ipfixCollectors 4}

ipfixCollectorsLevelEntry OBJECT-TYPE
	SYNTAX      IpfixCollectorsLevelEntry
	MAX-ACCESS  not-accessible
	STATUS      current
	DESCRIPTION
	"Table entry for ipfixCollectors"
	INDEX { ipfixCollectorsLevelName }
	::={ipfixCollectorsLevelTable 1}

IpfixCollectorsLevelEntry ::=
	SEQUENCE {
		ipfixCollectorsLevelName	DisplayString,
		ipfixCollectorsLevelVal	CounterBasedGauge64,
		ipfixCollectorsLevelMax	CounterBasedGauge64
	}

ipfixCollectorsLevelName OBJECT-TYPE
	SYNTAX      DisplayString
	MAX-ACCESS  not-accessible
	STATUS      current
	DESCRIPTION
	"Table entry display string for ipfixCollectors"
	::={ipfixCollectorsLevelEntry 1}

ipfixCollectorsLevelVal OBJECT-TYPE
	SYNTAX	 CounterBasedGauge64
	MAX-ACCESS  read-only
	STATUS      current
	DESCRIPTION
	"Table entry attribute for ipfixCollectors"
	::={ipfixCollectorsLevelEntry 2}

ipfixCollectorsLevelMax OBJECT-TYPE
	SYNTAX	 CounterBasedGauge64
	MAX-ACCESS  read-only
	STATUS      current
	DESCRIPTION
	"Table entry attribute for ipfixCollectors"
	::={ipfixCollectorsLevelEntry 4}


contentLogic	OBJECT IDENTIFIER ::={sysdiag 140}

contentLogicTableLoad	OBJECT IDENTIFIER ::={contentLogic 2}

contentLogicTableLoadVal	OBJECT-TYPE
	SYNTAX	 Unsigned32
	MAX-ACCESS read-only
	STATUS current
	DESCRIPTION "Current table load ratio"

	::={contentLogicTableLoad 1}

contentLogicTableLoadMax	OBJECT-TYPE
	SYNTAX	 Unsigned32
	MAX-ACCESS read-only
	STATUS current
	DESCRIPTION "Current table load ratio"

	::={contentLogicTableLoad 3}

contentLogicTableLoadLevelTable OBJECT-TYPE
	SYNTAX      SEQUENCE OF ContentLogicTableLoadLevelEntry
	MAX-ACCESS  not-accessible
	STATUS      current
	DESCRIPTION
	"Table for contentLogicTableLoad"
	::={contentLogicTableLoad 4}

contentLogicTableLoadLevelEntry OBJECT-TYPE
	SYNTAX      ContentLogicTableLoadLevelEntry
	MAX-ACCESS  not-accessible
	STATUS      current
	DESCRIPTION
	"Table entry for contentLogicTableLoad"
	INDEX { contentLogicTableLoadLevelName }
	::={contentLogicTableLoadLevelTable 1}

ContentLogicTableLoadLevelEntry ::=
	SEQUENCE {
		contentLogicTableLoadLevelName	DisplayString,
		contentLogicTableLoadLevelVal	Unsigned32,
		contentLogicTableLoadLevelMax	Unsigned32
	}

contentLogicTableLoadLevelName OBJECT-TYPE
	SYNTAX      DisplayString
	MAX-ACCESS  not-accessible
	STATUS      current
	DESCRIPTION
	"Table entry display string for contentLogicTableLoad"
	::={contentLogicTableLoadLevelEntry 1}

contentLogicTableLoadLevelVal OBJECT-TYPE
	SYNTAX	 Unsigned32
	MAX-ACCESS  read-only
	STATUS      current
	DESCRIPTION
	"Table entry attribute for contentLogicTableLoad"
	::={contentLogicTableLoadLevelEntry 2}

contentLogicTableLoadLevelMax OBJECT-TYPE
	SYNTAX	 Unsigned32
	MAX-ACCESS  read-only
	STATUS      current
	DESCRIPTION
	"Table entry attribute for contentLogicTableLoad"
	::={contentLogicTableLoadLevelEntry 4}


contentLogicCategoriesLoad	OBJECT IDENTIFIER ::={contentLogic 6}

contentLogicCategoriesLoadVal	OBJECT-TYPE
	SYNTAX	 Unsigned32
	MAX-ACCESS read-only
	STATUS current
	DESCRIPTION "Current categories load ratio"

	::={contentLogicCategoriesLoad 1}

contentLogicCategoriesLoadMax	OBJECT-TYPE
	SYNTAX	 Unsigned32
	MAX-ACCESS read-only
	STATUS current
	DESCRIPTION "Current categories load ratio"

	::={contentLogicCategoriesLoad 3}

contentLogicCategoriesLoadLevelTable OBJECT-TYPE
	SYNTAX      SEQUENCE OF ContentLogicCategoriesLoadLevelEntry
	MAX-ACCESS  not-accessible
	STATUS      current
	DESCRIPTION
	"Table for contentLogicCategoriesLoad"
	::={contentLogicCategoriesLoad 4}

contentLogicCategoriesLoadLevelEntry OBJECT-TYPE
	SYNTAX      ContentLogicCategoriesLoadLevelEntry
	MAX-ACCESS  not-accessible
	STATUS      current
	DESCRIPTION
	"Table entry for contentLogicCategoriesLoad"
	INDEX { contentLogicCategoriesLoadLevelName }
	::={contentLogicCategoriesLoadLevelTable 1}

ContentLogicCategoriesLoadLevelEntry ::=
	SEQUENCE {
		contentLogicCategoriesLoadLevelName	DisplayString,
		contentLogicCategoriesLoadLevelVal	Unsigned32,
		contentLogicCategoriesLoadLevelMax	Unsigned32
	}

contentLogicCategoriesLoadLevelName OBJECT-TYPE
	SYNTAX      DisplayString
	MAX-ACCESS  not-accessible
	STATUS      current
	DESCRIPTION
	"Table entry display string for contentLogicCategoriesLoad"
	::={contentLogicCategoriesLoadLevelEntry 1}

contentLogicCategoriesLoadLevelVal OBJECT-TYPE
	SYNTAX	 Unsigned32
	MAX-ACCESS  read-only
	STATUS      current
	DESCRIPTION
	"Table entry attribute for contentLogicCategoriesLoad"
	::={contentLogicCategoriesLoadLevelEntry 2}

contentLogicCategoriesLoadLevelMax OBJECT-TYPE
	SYNTAX	 Unsigned32
	MAX-ACCESS  read-only
	STATUS      current
	DESCRIPTION
	"Table entry attribute for contentLogicCategoriesLoad"
	::={contentLogicCategoriesLoadLevelEntry 4}


contentLogicRevision	OBJECT IDENTIFIER ::={contentLogic 9}

contentLogicRevisionVal	OBJECT-TYPE
	SYNTAX	 CounterBasedGauge64
	MAX-ACCESS read-only
	STATUS current
	DESCRIPTION "Last revision loaded"

	::={contentLogicRevision 1}

contentLogicRevisionLevelTable OBJECT-TYPE
	SYNTAX      SEQUENCE OF ContentLogicRevisionLevelEntry
	MAX-ACCESS  not-accessible
	STATUS      current
	DESCRIPTION
	"Table for contentLogicRevision"
	::={contentLogicRevision 4}

contentLogicRevisionLevelEntry OBJECT-TYPE
	SYNTAX      ContentLogicRevisionLevelEntry
	MAX-ACCESS  not-accessible
	STATUS      current
	DESCRIPTION
	"Table entry for contentLogicRevision"
	INDEX { contentLogicRevisionLevelName }
	::={contentLogicRevisionLevelTable 1}

ContentLogicRevisionLevelEntry ::=
	SEQUENCE {
		contentLogicRevisionLevelName	DisplayString,
		contentLogicRevisionLevelVal	CounterBasedGauge64
	}

contentLogicRevisionLevelName OBJECT-TYPE
	SYNTAX      DisplayString
	MAX-ACCESS  not-accessible
	STATUS      current
	DESCRIPTION
	"Table entry display string for contentLogicRevision"
	::={contentLogicRevisionLevelEntry 1}

contentLogicRevisionLevelVal OBJECT-TYPE
	SYNTAX	 CounterBasedGauge64
	MAX-ACCESS  read-only
	STATUS      current
	DESCRIPTION
	"Table entry attribute for contentLogicRevision"
	::={contentLogicRevisionLevelEntry 2}


contentLogicUrls	OBJECT IDENTIFIER ::={contentLogic 10}

contentLogicUrlsVal	OBJECT-TYPE
	SYNTAX	 CounterBasedGauge64
	MAX-ACCESS read-only
	STATUS current
	DESCRIPTION "Current number of URLs loaded"

	::={contentLogicUrls 1}

contentLogicUrlsMax	OBJECT-TYPE
	SYNTAX	 CounterBasedGauge64
	MAX-ACCESS read-only
	STATUS current
	DESCRIPTION "Current number of URLs loaded"

	::={contentLogicUrls 3}

contentLogicUrlsLevelTable OBJECT-TYPE
	SYNTAX      SEQUENCE OF ContentLogicUrlsLevelEntry
	MAX-ACCESS  not-accessible
	STATUS      current
	DESCRIPTION
	"Table for contentLogicUrls"
	::={contentLogicUrls 4}

contentLogicUrlsLevelEntry OBJECT-TYPE
	SYNTAX      ContentLogicUrlsLevelEntry
	MAX-ACCESS  not-accessible
	STATUS      current
	DESCRIPTION
	"Table entry for contentLogicUrls"
	INDEX { contentLogicUrlsLevelName }
	::={contentLogicUrlsLevelTable 1}

ContentLogicUrlsLevelEntry ::=
	SEQUENCE {
		contentLogicUrlsLevelName	DisplayString,
		contentLogicUrlsLevelVal	CounterBasedGauge64,
		contentLogicUrlsLevelMax	CounterBasedGauge64
	}

contentLogicUrlsLevelName OBJECT-TYPE
	SYNTAX      DisplayString
	MAX-ACCESS  not-accessible
	STATUS      current
	DESCRIPTION
	"Table entry display string for contentLogicUrls"
	::={contentLogicUrlsLevelEntry 1}

contentLogicUrlsLevelVal OBJECT-TYPE
	SYNTAX	 CounterBasedGauge64
	MAX-ACCESS  read-only
	STATUS      current
	DESCRIPTION
	"Table entry attribute for contentLogicUrls"
	::={contentLogicUrlsLevelEntry 2}

contentLogicUrlsLevelMax OBJECT-TYPE
	SYNTAX	 CounterBasedGauge64
	MAX-ACCESS  read-only
	STATUS      current
	DESCRIPTION
	"Table entry attribute for contentLogicUrls"
	::={contentLogicUrlsLevelEntry 4}


contentLogicLookups	OBJECT IDENTIFIER ::={contentLogic 11}

contentLogicLookupsVal	OBJECT-TYPE
	SYNTAX	 Counter64
	MAX-ACCESS read-only
	STATUS current
	DESCRIPTION "Number of lookups"

	::={contentLogicLookups 1}

contentLogicLookupsMom	OBJECT-TYPE
	SYNTAX	 CounterBasedGauge64
	MAX-ACCESS read-only
	STATUS current
	DESCRIPTION "Number of lookups"

	::={contentLogicLookups 2}

contentLogicLookupsMax	OBJECT-TYPE
	SYNTAX	 CounterBasedGauge64
	MAX-ACCESS read-only
	STATUS current
	DESCRIPTION "Number of lookups"

	::={contentLogicLookups 3}

contentLogicLookupsLevelTable OBJECT-TYPE
	SYNTAX      SEQUENCE OF ContentLogicLookupsLevelEntry
	MAX-ACCESS  not-accessible
	STATUS      current
	DESCRIPTION
	"Table for contentLogicLookups"
	::={contentLogicLookups 4}

contentLogicLookupsLevelEntry OBJECT-TYPE
	SYNTAX      ContentLogicLookupsLevelEntry
	MAX-ACCESS  not-accessible
	STATUS      current
	DESCRIPTION
	"Table entry for contentLogicLookups"
	INDEX { contentLogicLookupsLevelName }
	::={contentLogicLookupsLevelTable 1}

ContentLogicLookupsLevelEntry ::=
	SEQUENCE {
		contentLogicLookupsLevelName	DisplayString,
		contentLogicLookupsLevelVal	Counter64,
		contentLogicLookupsLevelMom	CounterBasedGauge64,
		contentLogicLookupsLevelMax	CounterBasedGauge64
	}

contentLogicLookupsLevelName OBJECT-TYPE
	SYNTAX      DisplayString
	MAX-ACCESS  not-accessible
	STATUS      current
	DESCRIPTION
	"Table entry display string for contentLogicLookups"
	::={contentLogicLookupsLevelEntry 1}

contentLogicLookupsLevelVal OBJECT-TYPE
	SYNTAX	 Counter64
	MAX-ACCESS  read-only
	STATUS      current
	DESCRIPTION
	"Table entry attribute for contentLogicLookups"
	::={contentLogicLookupsLevelEntry 2}

contentLogicLookupsLevelMom OBJECT-TYPE
	SYNTAX	 CounterBasedGauge64
	MAX-ACCESS  read-only
	STATUS      current
	DESCRIPTION
	"Table entry attribute for contentLogicLookups"
	::={contentLogicLookupsLevelEntry 3}

contentLogicLookupsLevelMax OBJECT-TYPE
	SYNTAX	 CounterBasedGauge64
	MAX-ACCESS  read-only
	STATUS      current
	DESCRIPTION
	"Table entry attribute for contentLogicLookups"
	::={contentLogicLookupsLevelEntry 4}


contentLogicMatches	OBJECT IDENTIFIER ::={contentLogic 12}

contentLogicMatchesVal	OBJECT-TYPE
	SYNTAX	 Counter64
	MAX-ACCESS read-only
	STATUS current
	DESCRIPTION "Number of matching lookups"

	::={contentLogicMatches 1}

contentLogicMatchesMom	OBJECT-TYPE
	SYNTAX	 CounterBasedGauge64
	MAX-ACCESS read-only
	STATUS current
	DESCRIPTION "Number of matching lookups"

	::={contentLogicMatches 2}

contentLogicMatchesMax	OBJECT-TYPE
	SYNTAX	 CounterBasedGauge64
	MAX-ACCESS read-only
	STATUS current
	DESCRIPTION "Number of matching lookups"

	::={contentLogicMatches 3}

contentLogicMatchesLevelTable OBJECT-TYPE
	SYNTAX      SEQUENCE OF ContentLogicMatchesLevelEntry
	MAX-ACCESS  not-accessible
	STATUS      current
	DESCRIPTION
	"Table for contentLogicMatches"
	::={contentLogicMatches 4}

contentLogicMatchesLevelEntry OBJECT-TYPE
	SYNTAX      ContentLogicMatchesLevelEntry
	MAX-ACCESS  not-accessible
	STATUS      current
	DESCRIPTION
	"Table entry for contentLogicMatches"
	INDEX { contentLogicMatchesLevelName }
	::={contentLogicMatchesLevelTable 1}

ContentLogicMatchesLevelEntry ::=
	SEQUENCE {
		contentLogicMatchesLevelName	DisplayString,
		contentLogicMatchesLevelVal	Counter64,
		contentLogicMatchesLevelMom	CounterBasedGauge64,
		contentLogicMatchesLevelMax	CounterBasedGauge64
	}

contentLogicMatchesLevelName OBJECT-TYPE
	SYNTAX      DisplayString
	MAX-ACCESS  not-accessible
	STATUS      current
	DESCRIPTION
	"Table entry display string for contentLogicMatches"
	::={contentLogicMatchesLevelEntry 1}

contentLogicMatchesLevelVal OBJECT-TYPE
	SYNTAX	 Counter64
	MAX-ACCESS  read-only
	STATUS      current
	DESCRIPTION
	"Table entry attribute for contentLogicMatches"
	::={contentLogicMatchesLevelEntry 2}

contentLogicMatchesLevelMom OBJECT-TYPE
	SYNTAX	 CounterBasedGauge64
	MAX-ACCESS  read-only
	STATUS      current
	DESCRIPTION
	"Table entry attribute for contentLogicMatches"
	::={contentLogicMatchesLevelEntry 3}

contentLogicMatchesLevelMax OBJECT-TYPE
	SYNTAX	 CounterBasedGauge64
	MAX-ACCESS  read-only
	STATUS      current
	DESCRIPTION
	"Table entry attribute for contentLogicMatches"
	::={contentLogicMatchesLevelEntry 4}


rewrite	OBJECT IDENTIFIER ::={sysdiag 141}

rewriteMappingsCreated	OBJECT IDENTIFIER ::={rewrite 1}

rewriteMappingsCreatedVal	OBJECT-TYPE
	SYNTAX	 Counter64
	MAX-ACCESS read-only
	STATUS current
	DESCRIPTION "Mappings created"

	::={rewriteMappingsCreated 1}

rewriteMappingsCreatedMom	OBJECT-TYPE
	SYNTAX	 CounterBasedGauge64
	MAX-ACCESS read-only
	STATUS current
	DESCRIPTION "Mappings created"

	::={rewriteMappingsCreated 2}

rewriteMappingsCreatedMax	OBJECT-TYPE
	SYNTAX	 CounterBasedGauge64
	MAX-ACCESS read-only
	STATUS current
	DESCRIPTION "Mappings created"

	::={rewriteMappingsCreated 3}

rewriteMappingsCreatedLevelTable OBJECT-TYPE
	SYNTAX      SEQUENCE OF RewriteMappingsCreatedLevelEntry
	MAX-ACCESS  not-accessible
	STATUS      current
	DESCRIPTION
	"Table for rewriteMappingsCreated"
	::={rewriteMappingsCreated 4}

rewriteMappingsCreatedLevelEntry OBJECT-TYPE
	SYNTAX      RewriteMappingsCreatedLevelEntry
	MAX-ACCESS  not-accessible
	STATUS      current
	DESCRIPTION
	"Table entry for rewriteMappingsCreated"
	INDEX { rewriteMappingsCreatedLevelName }
	::={rewriteMappingsCreatedLevelTable 1}

RewriteMappingsCreatedLevelEntry ::=
	SEQUENCE {
		rewriteMappingsCreatedLevelName	DisplayString,
		rewriteMappingsCreatedLevelVal	Counter64,
		rewriteMappingsCreatedLevelMom	CounterBasedGauge64,
		rewriteMappingsCreatedLevelMax	CounterBasedGauge64
	}

rewriteMappingsCreatedLevelName OBJECT-TYPE
	SYNTAX      DisplayString
	MAX-ACCESS  not-accessible
	STATUS      current
	DESCRIPTION
	"Table entry display string for rewriteMappingsCreated"
	::={rewriteMappingsCreatedLevelEntry 1}

rewriteMappingsCreatedLevelVal OBJECT-TYPE
	SYNTAX	 Counter64
	MAX-ACCESS  read-only
	STATUS      current
	DESCRIPTION
	"Table entry attribute for rewriteMappingsCreated"
	::={rewriteMappingsCreatedLevelEntry 2}

rewriteMappingsCreatedLevelMom OBJECT-TYPE
	SYNTAX	 CounterBasedGauge64
	MAX-ACCESS  read-only
	STATUS      current
	DESCRIPTION
	"Table entry attribute for rewriteMappingsCreated"
	::={rewriteMappingsCreatedLevelEntry 3}

rewriteMappingsCreatedLevelMax OBJECT-TYPE
	SYNTAX	 CounterBasedGauge64
	MAX-ACCESS  read-only
	STATUS      current
	DESCRIPTION
	"Table entry attribute for rewriteMappingsCreated"
	::={rewriteMappingsCreatedLevelEntry 4}


rewriteMappingsCreatedTcp	OBJECT IDENTIFIER ::={rewrite 2}

rewriteMappingsCreatedTcpVal	OBJECT-TYPE
	SYNTAX	 Counter64
	MAX-ACCESS read-only
	STATUS current
	DESCRIPTION "Mappings created - TCP"

	::={rewriteMappingsCreatedTcp 1}

rewriteMappingsCreatedTcpMom	OBJECT-TYPE
	SYNTAX	 CounterBasedGauge64
	MAX-ACCESS read-only
	STATUS current
	DESCRIPTION "Mappings created - TCP"

	::={rewriteMappingsCreatedTcp 2}

rewriteMappingsCreatedTcpMax	OBJECT-TYPE
	SYNTAX	 CounterBasedGauge64
	MAX-ACCESS read-only
	STATUS current
	DESCRIPTION "Mappings created - TCP"

	::={rewriteMappingsCreatedTcp 3}

rewriteMappingsCreatedTcpLevelTable OBJECT-TYPE
	SYNTAX      SEQUENCE OF RewriteMappingsCreatedTcpLevelEntry
	MAX-ACCESS  not-accessible
	STATUS      current
	DESCRIPTION
	"Table for rewriteMappingsCreatedTcp"
	::={rewriteMappingsCreatedTcp 4}

rewriteMappingsCreatedTcpLevelEntry OBJECT-TYPE
	SYNTAX      RewriteMappingsCreatedTcpLevelEntry
	MAX-ACCESS  not-accessible
	STATUS      current
	DESCRIPTION
	"Table entry for rewriteMappingsCreatedTcp"
	INDEX { rewriteMappingsCreatedTcpLevelName }
	::={rewriteMappingsCreatedTcpLevelTable 1}

RewriteMappingsCreatedTcpLevelEntry ::=
	SEQUENCE {
		rewriteMappingsCreatedTcpLevelName	DisplayString,
		rewriteMappingsCreatedTcpLevelVal	Counter64,
		rewriteMappingsCreatedTcpLevelMom	CounterBasedGauge64,
		rewriteMappingsCreatedTcpLevelMax	CounterBasedGauge64
	}

rewriteMappingsCreatedTcpLevelName OBJECT-TYPE
	SYNTAX      DisplayString
	MAX-ACCESS  not-accessible
	STATUS      current
	DESCRIPTION
	"Table entry display string for rewriteMappingsCreatedTcp"
	::={rewriteMappingsCreatedTcpLevelEntry 1}

rewriteMappingsCreatedTcpLevelVal OBJECT-TYPE
	SYNTAX	 Counter64
	MAX-ACCESS  read-only
	STATUS      current
	DESCRIPTION
	"Table entry attribute for rewriteMappingsCreatedTcp"
	::={rewriteMappingsCreatedTcpLevelEntry 2}

rewriteMappingsCreatedTcpLevelMom OBJECT-TYPE
	SYNTAX	 CounterBasedGauge64
	MAX-ACCESS  read-only
	STATUS      current
	DESCRIPTION
	"Table entry attribute for rewriteMappingsCreatedTcp"
	::={rewriteMappingsCreatedTcpLevelEntry 3}

rewriteMappingsCreatedTcpLevelMax OBJECT-TYPE
	SYNTAX	 CounterBasedGauge64
	MAX-ACCESS  read-only
	STATUS      current
	DESCRIPTION
	"Table entry attribute for rewriteMappingsCreatedTcp"
	::={rewriteMappingsCreatedTcpLevelEntry 4}


rewriteMappingsCreatedUdp	OBJECT IDENTIFIER ::={rewrite 3}

rewriteMappingsCreatedUdpVal	OBJECT-TYPE
	SYNTAX	 Counter64
	MAX-ACCESS read-only
	STATUS current
	DESCRIPTION "Mappings created - UDP"

	::={rewriteMappingsCreatedUdp 1}

rewriteMappingsCreatedUdpMom	OBJECT-TYPE
	SYNTAX	 CounterBasedGauge64
	MAX-ACCESS read-only
	STATUS current
	DESCRIPTION "Mappings created - UDP"

	::={rewriteMappingsCreatedUdp 2}

rewriteMappingsCreatedUdpMax	OBJECT-TYPE
	SYNTAX	 CounterBasedGauge64
	MAX-ACCESS read-only
	STATUS current
	DESCRIPTION "Mappings created - UDP"

	::={rewriteMappingsCreatedUdp 3}

rewriteMappingsCreatedUdpLevelTable OBJECT-TYPE
	SYNTAX      SEQUENCE OF RewriteMappingsCreatedUdpLevelEntry
	MAX-ACCESS  not-accessible
	STATUS      current
	DESCRIPTION
	"Table for rewriteMappingsCreatedUdp"
	::={rewriteMappingsCreatedUdp 4}

rewriteMappingsCreatedUdpLevelEntry OBJECT-TYPE
	SYNTAX      RewriteMappingsCreatedUdpLevelEntry
	MAX-ACCESS  not-accessible
	STATUS      current
	DESCRIPTION
	"Table entry for rewriteMappingsCreatedUdp"
	INDEX { rewriteMappingsCreatedUdpLevelName }
	::={rewriteMappingsCreatedUdpLevelTable 1}

RewriteMappingsCreatedUdpLevelEntry ::=
	SEQUENCE {
		rewriteMappingsCreatedUdpLevelName	DisplayString,
		rewriteMappingsCreatedUdpLevelVal	Counter64,
		rewriteMappingsCreatedUdpLevelMom	CounterBasedGauge64,
		rewriteMappingsCreatedUdpLevelMax	CounterBasedGauge64
	}

rewriteMappingsCreatedUdpLevelName OBJECT-TYPE
	SYNTAX      DisplayString
	MAX-ACCESS  not-accessible
	STATUS      current
	DESCRIPTION
	"Table entry display string for rewriteMappingsCreatedUdp"
	::={rewriteMappingsCreatedUdpLevelEntry 1}

rewriteMappingsCreatedUdpLevelVal OBJECT-TYPE
	SYNTAX	 Counter64
	MAX-ACCESS  read-only
	STATUS      current
	DESCRIPTION
	"Table entry attribute for rewriteMappingsCreatedUdp"
	::={rewriteMappingsCreatedUdpLevelEntry 2}

rewriteMappingsCreatedUdpLevelMom OBJECT-TYPE
	SYNTAX	 CounterBasedGauge64
	MAX-ACCESS  read-only
	STATUS      current
	DESCRIPTION
	"Table entry attribute for rewriteMappingsCreatedUdp"
	::={rewriteMappingsCreatedUdpLevelEntry 3}

rewriteMappingsCreatedUdpLevelMax OBJECT-TYPE
	SYNTAX	 CounterBasedGauge64
	MAX-ACCESS  read-only
	STATUS      current
	DESCRIPTION
	"Table entry attribute for rewriteMappingsCreatedUdp"
	::={rewriteMappingsCreatedUdpLevelEntry 4}


rewriteMappingsCreatedIcmp	OBJECT IDENTIFIER ::={rewrite 4}

rewriteMappingsCreatedIcmpVal	OBJECT-TYPE
	SYNTAX	 Counter64
	MAX-ACCESS read-only
	STATUS current
	DESCRIPTION "Mappings created - ICMP"

	::={rewriteMappingsCreatedIcmp 1}

rewriteMappingsCreatedIcmpMom	OBJECT-TYPE
	SYNTAX	 CounterBasedGauge64
	MAX-ACCESS read-only
	STATUS current
	DESCRIPTION "Mappings created - ICMP"

	::={rewriteMappingsCreatedIcmp 2}

rewriteMappingsCreatedIcmpMax	OBJECT-TYPE
	SYNTAX	 CounterBasedGauge64
	MAX-ACCESS read-only
	STATUS current
	DESCRIPTION "Mappings created - ICMP"

	::={rewriteMappingsCreatedIcmp 3}

rewriteMappingsCreatedIcmpLevelTable OBJECT-TYPE
	SYNTAX      SEQUENCE OF RewriteMappingsCreatedIcmpLevelEntry
	MAX-ACCESS  not-accessible
	STATUS      current
	DESCRIPTION
	"Table for rewriteMappingsCreatedIcmp"
	::={rewriteMappingsCreatedIcmp 4}

rewriteMappingsCreatedIcmpLevelEntry OBJECT-TYPE
	SYNTAX      RewriteMappingsCreatedIcmpLevelEntry
	MAX-ACCESS  not-accessible
	STATUS      current
	DESCRIPTION
	"Table entry for rewriteMappingsCreatedIcmp"
	INDEX { rewriteMappingsCreatedIcmpLevelName }
	::={rewriteMappingsCreatedIcmpLevelTable 1}

RewriteMappingsCreatedIcmpLevelEntry ::=
	SEQUENCE {
		rewriteMappingsCreatedIcmpLevelName	DisplayString,
		rewriteMappingsCreatedIcmpLevelVal	Counter64,
		rewriteMappingsCreatedIcmpLevelMom	CounterBasedGauge64,
		rewriteMappingsCreatedIcmpLevelMax	CounterBasedGauge64
	}

rewriteMappingsCreatedIcmpLevelName OBJECT-TYPE
	SYNTAX      DisplayString
	MAX-ACCESS  not-accessible
	STATUS      current
	DESCRIPTION
	"Table entry display string for rewriteMappingsCreatedIcmp"
	::={rewriteMappingsCreatedIcmpLevelEntry 1}

rewriteMappingsCreatedIcmpLevelVal OBJECT-TYPE
	SYNTAX	 Counter64
	MAX-ACCESS  read-only
	STATUS      current
	DESCRIPTION
	"Table entry attribute for rewriteMappingsCreatedIcmp"
	::={rewriteMappingsCreatedIcmpLevelEntry 2}

rewriteMappingsCreatedIcmpLevelMom OBJECT-TYPE
	SYNTAX	 CounterBasedGauge64
	MAX-ACCESS  read-only
	STATUS      current
	DESCRIPTION
	"Table entry attribute for rewriteMappingsCreatedIcmp"
	::={rewriteMappingsCreatedIcmpLevelEntry 3}

rewriteMappingsCreatedIcmpLevelMax OBJECT-TYPE
	SYNTAX	 CounterBasedGauge64
	MAX-ACCESS  read-only
	STATUS      current
	DESCRIPTION
	"Table entry attribute for rewriteMappingsCreatedIcmp"
	::={rewriteMappingsCreatedIcmpLevelEntry 4}


rewriteMappingsReused	OBJECT IDENTIFIER ::={rewrite 5}

rewriteMappingsReusedVal	OBJECT-TYPE
	SYNTAX	 Counter64
	MAX-ACCESS read-only
	STATUS current
	DESCRIPTION "Mappings reused"

	::={rewriteMappingsReused 1}

rewriteMappingsReusedMom	OBJECT-TYPE
	SYNTAX	 CounterBasedGauge64
	MAX-ACCESS read-only
	STATUS current
	DESCRIPTION "Mappings reused"

	::={rewriteMappingsReused 2}

rewriteMappingsReusedMax	OBJECT-TYPE
	SYNTAX	 CounterBasedGauge64
	MAX-ACCESS read-only
	STATUS current
	DESCRIPTION "Mappings reused"

	::={rewriteMappingsReused 3}

rewriteMappingsReusedLevelTable OBJECT-TYPE
	SYNTAX      SEQUENCE OF RewriteMappingsReusedLevelEntry
	MAX-ACCESS  not-accessible
	STATUS      current
	DESCRIPTION
	"Table for rewriteMappingsReused"
	::={rewriteMappingsReused 4}

rewriteMappingsReusedLevelEntry OBJECT-TYPE
	SYNTAX      RewriteMappingsReusedLevelEntry
	MAX-ACCESS  not-accessible
	STATUS      current
	DESCRIPTION
	"Table entry for rewriteMappingsReused"
	INDEX { rewriteMappingsReusedLevelName }
	::={rewriteMappingsReusedLevelTable 1}

RewriteMappingsReusedLevelEntry ::=
	SEQUENCE {
		rewriteMappingsReusedLevelName	DisplayString,
		rewriteMappingsReusedLevelVal	Counter64,
		rewriteMappingsReusedLevelMom	CounterBasedGauge64,
		rewriteMappingsReusedLevelMax	CounterBasedGauge64
	}

rewriteMappingsReusedLevelName OBJECT-TYPE
	SYNTAX      DisplayString
	MAX-ACCESS  not-accessible
	STATUS      current
	DESCRIPTION
	"Table entry display string for rewriteMappingsReused"
	::={rewriteMappingsReusedLevelEntry 1}

rewriteMappingsReusedLevelVal OBJECT-TYPE
	SYNTAX	 Counter64
	MAX-ACCESS  read-only
	STATUS      current
	DESCRIPTION
	"Table entry attribute for rewriteMappingsReused"
	::={rewriteMappingsReusedLevelEntry 2}

rewriteMappingsReusedLevelMom OBJECT-TYPE
	SYNTAX	 CounterBasedGauge64
	MAX-ACCESS  read-only
	STATUS      current
	DESCRIPTION
	"Table entry attribute for rewriteMappingsReused"
	::={rewriteMappingsReusedLevelEntry 3}

rewriteMappingsReusedLevelMax OBJECT-TYPE
	SYNTAX	 CounterBasedGauge64
	MAX-ACCESS  read-only
	STATUS      current
	DESCRIPTION
	"Table entry attribute for rewriteMappingsReused"
	::={rewriteMappingsReusedLevelEntry 4}


rewriteMappingsReusedTcp	OBJECT IDENTIFIER ::={rewrite 6}

rewriteMappingsReusedTcpVal	OBJECT-TYPE
	SYNTAX	 Counter64
	MAX-ACCESS read-only
	STATUS current
	DESCRIPTION "Mappings reused - TCP"

	::={rewriteMappingsReusedTcp 1}

rewriteMappingsReusedTcpMom	OBJECT-TYPE
	SYNTAX	 CounterBasedGauge64
	MAX-ACCESS read-only
	STATUS current
	DESCRIPTION "Mappings reused - TCP"

	::={rewriteMappingsReusedTcp 2}

rewriteMappingsReusedTcpMax	OBJECT-TYPE
	SYNTAX	 CounterBasedGauge64
	MAX-ACCESS read-only
	STATUS current
	DESCRIPTION "Mappings reused - TCP"

	::={rewriteMappingsReusedTcp 3}

rewriteMappingsReusedTcpLevelTable OBJECT-TYPE
	SYNTAX      SEQUENCE OF RewriteMappingsReusedTcpLevelEntry
	MAX-ACCESS  not-accessible
	STATUS      current
	DESCRIPTION
	"Table for rewriteMappingsReusedTcp"
	::={rewriteMappingsReusedTcp 4}

rewriteMappingsReusedTcpLevelEntry OBJECT-TYPE
	SYNTAX      RewriteMappingsReusedTcpLevelEntry
	MAX-ACCESS  not-accessible
	STATUS      current
	DESCRIPTION
	"Table entry for rewriteMappingsReusedTcp"
	INDEX { rewriteMappingsReusedTcpLevelName }
	::={rewriteMappingsReusedTcpLevelTable 1}

RewriteMappingsReusedTcpLevelEntry ::=
	SEQUENCE {
		rewriteMappingsReusedTcpLevelName	DisplayString,
		rewriteMappingsReusedTcpLevelVal	Counter64,
		rewriteMappingsReusedTcpLevelMom	CounterBasedGauge64,
		rewriteMappingsReusedTcpLevelMax	CounterBasedGauge64
	}

rewriteMappingsReusedTcpLevelName OBJECT-TYPE
	SYNTAX      DisplayString
	MAX-ACCESS  not-accessible
	STATUS      current
	DESCRIPTION
	"Table entry display string for rewriteMappingsReusedTcp"
	::={rewriteMappingsReusedTcpLevelEntry 1}

rewriteMappingsReusedTcpLevelVal OBJECT-TYPE
	SYNTAX	 Counter64
	MAX-ACCESS  read-only
	STATUS      current
	DESCRIPTION
	"Table entry attribute for rewriteMappingsReusedTcp"
	::={rewriteMappingsReusedTcpLevelEntry 2}

rewriteMappingsReusedTcpLevelMom OBJECT-TYPE
	SYNTAX	 CounterBasedGauge64
	MAX-ACCESS  read-only
	STATUS      current
	DESCRIPTION
	"Table entry attribute for rewriteMappingsReusedTcp"
	::={rewriteMappingsReusedTcpLevelEntry 3}

rewriteMappingsReusedTcpLevelMax OBJECT-TYPE
	SYNTAX	 CounterBasedGauge64
	MAX-ACCESS  read-only
	STATUS      current
	DESCRIPTION
	"Table entry attribute for rewriteMappingsReusedTcp"
	::={rewriteMappingsReusedTcpLevelEntry 4}


rewriteMappingsReusedUdp	OBJECT IDENTIFIER ::={rewrite 7}

rewriteMappingsReusedUdpVal	OBJECT-TYPE
	SYNTAX	 Counter64
	MAX-ACCESS read-only
	STATUS current
	DESCRIPTION "Mappings reused - UDP"

	::={rewriteMappingsReusedUdp 1}

rewriteMappingsReusedUdpMom	OBJECT-TYPE
	SYNTAX	 CounterBasedGauge64
	MAX-ACCESS read-only
	STATUS current
	DESCRIPTION "Mappings reused - UDP"

	::={rewriteMappingsReusedUdp 2}

rewriteMappingsReusedUdpMax	OBJECT-TYPE
	SYNTAX	 CounterBasedGauge64
	MAX-ACCESS read-only
	STATUS current
	DESCRIPTION "Mappings reused - UDP"

	::={rewriteMappingsReusedUdp 3}

rewriteMappingsReusedUdpLevelTable OBJECT-TYPE
	SYNTAX      SEQUENCE OF RewriteMappingsReusedUdpLevelEntry
	MAX-ACCESS  not-accessible
	STATUS      current
	DESCRIPTION
	"Table for rewriteMappingsReusedUdp"
	::={rewriteMappingsReusedUdp 4}

rewriteMappingsReusedUdpLevelEntry OBJECT-TYPE
	SYNTAX      RewriteMappingsReusedUdpLevelEntry
	MAX-ACCESS  not-accessible
	STATUS      current
	DESCRIPTION
	"Table entry for rewriteMappingsReusedUdp"
	INDEX { rewriteMappingsReusedUdpLevelName }
	::={rewriteMappingsReusedUdpLevelTable 1}

RewriteMappingsReusedUdpLevelEntry ::=
	SEQUENCE {
		rewriteMappingsReusedUdpLevelName	DisplayString,
		rewriteMappingsReusedUdpLevelVal	Counter64,
		rewriteMappingsReusedUdpLevelMom	CounterBasedGauge64,
		rewriteMappingsReusedUdpLevelMax	CounterBasedGauge64
	}

rewriteMappingsReusedUdpLevelName OBJECT-TYPE
	SYNTAX      DisplayString
	MAX-ACCESS  not-accessible
	STATUS      current
	DESCRIPTION
	"Table entry display string for rewriteMappingsReusedUdp"
	::={rewriteMappingsReusedUdpLevelEntry 1}

rewriteMappingsReusedUdpLevelVal OBJECT-TYPE
	SYNTAX	 Counter64
	MAX-ACCESS  read-only
	STATUS      current
	DESCRIPTION
	"Table entry attribute for rewriteMappingsReusedUdp"
	::={rewriteMappingsReusedUdpLevelEntry 2}

rewriteMappingsReusedUdpLevelMom OBJECT-TYPE
	SYNTAX	 CounterBasedGauge64
	MAX-ACCESS  read-only
	STATUS      current
	DESCRIPTION
	"Table entry attribute for rewriteMappingsReusedUdp"
	::={rewriteMappingsReusedUdpLevelEntry 3}

rewriteMappingsReusedUdpLevelMax OBJECT-TYPE
	SYNTAX	 CounterBasedGauge64
	MAX-ACCESS  read-only
	STATUS      current
	DESCRIPTION
	"Table entry attribute for rewriteMappingsReusedUdp"
	::={rewriteMappingsReusedUdpLevelEntry 4}


rewriteMappingsReusedIcmp	OBJECT IDENTIFIER ::={rewrite 8}

rewriteMappingsReusedIcmpVal	OBJECT-TYPE
	SYNTAX	 Counter64
	MAX-ACCESS read-only
	STATUS current
	DESCRIPTION "Mappings reused - ICMP"

	::={rewriteMappingsReusedIcmp 1}

rewriteMappingsReusedIcmpMom	OBJECT-TYPE
	SYNTAX	 CounterBasedGauge64
	MAX-ACCESS read-only
	STATUS current
	DESCRIPTION "Mappings reused - ICMP"

	::={rewriteMappingsReusedIcmp 2}

rewriteMappingsReusedIcmpMax	OBJECT-TYPE
	SYNTAX	 CounterBasedGauge64
	MAX-ACCESS read-only
	STATUS current
	DESCRIPTION "Mappings reused - ICMP"

	::={rewriteMappingsReusedIcmp 3}

rewriteMappingsReusedIcmpLevelTable OBJECT-TYPE
	SYNTAX      SEQUENCE OF RewriteMappingsReusedIcmpLevelEntry
	MAX-ACCESS  not-accessible
	STATUS      current
	DESCRIPTION
	"Table for rewriteMappingsReusedIcmp"
	::={rewriteMappingsReusedIcmp 4}

rewriteMappingsReusedIcmpLevelEntry OBJECT-TYPE
	SYNTAX      RewriteMappingsReusedIcmpLevelEntry
	MAX-ACCESS  not-accessible
	STATUS      current
	DESCRIPTION
	"Table entry for rewriteMappingsReusedIcmp"
	INDEX { rewriteMappingsReusedIcmpLevelName }
	::={rewriteMappingsReusedIcmpLevelTable 1}

RewriteMappingsReusedIcmpLevelEntry ::=
	SEQUENCE {
		rewriteMappingsReusedIcmpLevelName	DisplayString,
		rewriteMappingsReusedIcmpLevelVal	Counter64,
		rewriteMappingsReusedIcmpLevelMom	CounterBasedGauge64,
		rewriteMappingsReusedIcmpLevelMax	CounterBasedGauge64
	}

rewriteMappingsReusedIcmpLevelName OBJECT-TYPE
	SYNTAX      DisplayString
	MAX-ACCESS  not-accessible
	STATUS      current
	DESCRIPTION
	"Table entry display string for rewriteMappingsReusedIcmp"
	::={rewriteMappingsReusedIcmpLevelEntry 1}

rewriteMappingsReusedIcmpLevelVal OBJECT-TYPE
	SYNTAX	 Counter64
	MAX-ACCESS  read-only
	STATUS      current
	DESCRIPTION
	"Table entry attribute for rewriteMappingsReusedIcmp"
	::={rewriteMappingsReusedIcmpLevelEntry 2}

rewriteMappingsReusedIcmpLevelMom OBJECT-TYPE
	SYNTAX	 CounterBasedGauge64
	MAX-ACCESS  read-only
	STATUS      current
	DESCRIPTION
	"Table entry attribute for rewriteMappingsReusedIcmp"
	::={rewriteMappingsReusedIcmpLevelEntry 3}

rewriteMappingsReusedIcmpLevelMax OBJECT-TYPE
	SYNTAX	 CounterBasedGauge64
	MAX-ACCESS  read-only
	STATUS      current
	DESCRIPTION
	"Table entry attribute for rewriteMappingsReusedIcmp"
	::={rewriteMappingsReusedIcmpLevelEntry 4}


rewriteMappingsDeleted	OBJECT IDENTIFIER ::={rewrite 9}

rewriteMappingsDeletedVal	OBJECT-TYPE
	SYNTAX	 Counter64
	MAX-ACCESS read-only
	STATUS current
	DESCRIPTION "Mappings deleted"

	::={rewriteMappingsDeleted 1}

rewriteMappingsDeletedMom	OBJECT-TYPE
	SYNTAX	 CounterBasedGauge64
	MAX-ACCESS read-only
	STATUS current
	DESCRIPTION "Mappings deleted"

	::={rewriteMappingsDeleted 2}

rewriteMappingsDeletedMax	OBJECT-TYPE
	SYNTAX	 CounterBasedGauge64
	MAX-ACCESS read-only
	STATUS current
	DESCRIPTION "Mappings deleted"

	::={rewriteMappingsDeleted 3}

rewriteMappingsDeletedLevelTable OBJECT-TYPE
	SYNTAX      SEQUENCE OF RewriteMappingsDeletedLevelEntry
	MAX-ACCESS  not-accessible
	STATUS      current
	DESCRIPTION
	"Table for rewriteMappingsDeleted"
	::={rewriteMappingsDeleted 4}

rewriteMappingsDeletedLevelEntry OBJECT-TYPE
	SYNTAX      RewriteMappingsDeletedLevelEntry
	MAX-ACCESS  not-accessible
	STATUS      current
	DESCRIPTION
	"Table entry for rewriteMappingsDeleted"
	INDEX { rewriteMappingsDeletedLevelName }
	::={rewriteMappingsDeletedLevelTable 1}

RewriteMappingsDeletedLevelEntry ::=
	SEQUENCE {
		rewriteMappingsDeletedLevelName	DisplayString,
		rewriteMappingsDeletedLevelVal	Counter64,
		rewriteMappingsDeletedLevelMom	CounterBasedGauge64,
		rewriteMappingsDeletedLevelMax	CounterBasedGauge64
	}

rewriteMappingsDeletedLevelName OBJECT-TYPE
	SYNTAX      DisplayString
	MAX-ACCESS  not-accessible
	STATUS      current
	DESCRIPTION
	"Table entry display string for rewriteMappingsDeleted"
	::={rewriteMappingsDeletedLevelEntry 1}

rewriteMappingsDeletedLevelVal OBJECT-TYPE
	SYNTAX	 Counter64
	MAX-ACCESS  read-only
	STATUS      current
	DESCRIPTION
	"Table entry attribute for rewriteMappingsDeleted"
	::={rewriteMappingsDeletedLevelEntry 2}

rewriteMappingsDeletedLevelMom OBJECT-TYPE
	SYNTAX	 CounterBasedGauge64
	MAX-ACCESS  read-only
	STATUS      current
	DESCRIPTION
	"Table entry attribute for rewriteMappingsDeleted"
	::={rewriteMappingsDeletedLevelEntry 3}

rewriteMappingsDeletedLevelMax OBJECT-TYPE
	SYNTAX	 CounterBasedGauge64
	MAX-ACCESS  read-only
	STATUS      current
	DESCRIPTION
	"Table entry attribute for rewriteMappingsDeleted"
	::={rewriteMappingsDeletedLevelEntry 4}


rewriteMappingsCount	OBJECT IDENTIFIER ::={rewrite 10}

rewriteMappingsCountVal	OBJECT-TYPE
	SYNTAX	 CounterBasedGauge64
	MAX-ACCESS read-only
	STATUS current
	DESCRIPTION "Mappings count"

	::={rewriteMappingsCount 1}

rewriteMappingsCountMax	OBJECT-TYPE
	SYNTAX	 CounterBasedGauge64
	MAX-ACCESS read-only
	STATUS current
	DESCRIPTION "Mappings count"

	::={rewriteMappingsCount 3}

rewriteMappingsCountLevelTable OBJECT-TYPE
	SYNTAX      SEQUENCE OF RewriteMappingsCountLevelEntry
	MAX-ACCESS  not-accessible
	STATUS      current
	DESCRIPTION
	"Table for rewriteMappingsCount"
	::={rewriteMappingsCount 4}

rewriteMappingsCountLevelEntry OBJECT-TYPE
	SYNTAX      RewriteMappingsCountLevelEntry
	MAX-ACCESS  not-accessible
	STATUS      current
	DESCRIPTION
	"Table entry for rewriteMappingsCount"
	INDEX { rewriteMappingsCountLevelName }
	::={rewriteMappingsCountLevelTable 1}

RewriteMappingsCountLevelEntry ::=
	SEQUENCE {
		rewriteMappingsCountLevelName	DisplayString,
		rewriteMappingsCountLevelVal	CounterBasedGauge64,
		rewriteMappingsCountLevelMax	CounterBasedGauge64
	}

rewriteMappingsCountLevelName OBJECT-TYPE
	SYNTAX      DisplayString
	MAX-ACCESS  not-accessible
	STATUS      current
	DESCRIPTION
	"Table entry display string for rewriteMappingsCount"
	::={rewriteMappingsCountLevelEntry 1}

rewriteMappingsCountLevelVal OBJECT-TYPE
	SYNTAX	 CounterBasedGauge64
	MAX-ACCESS  read-only
	STATUS      current
	DESCRIPTION
	"Table entry attribute for rewriteMappingsCount"
	::={rewriteMappingsCountLevelEntry 2}

rewriteMappingsCountLevelMax OBJECT-TYPE
	SYNTAX	 CounterBasedGauge64
	MAX-ACCESS  read-only
	STATUS      current
	DESCRIPTION
	"Table entry attribute for rewriteMappingsCount"
	::={rewriteMappingsCountLevelEntry 4}


rewriteMappingsCountTcp	OBJECT IDENTIFIER ::={rewrite 11}

rewriteMappingsCountTcpVal	OBJECT-TYPE
	SYNTAX	 CounterBasedGauge64
	MAX-ACCESS read-only
	STATUS current
	DESCRIPTION "Mappings count - TCP"

	::={rewriteMappingsCountTcp 1}

rewriteMappingsCountTcpMax	OBJECT-TYPE
	SYNTAX	 CounterBasedGauge64
	MAX-ACCESS read-only
	STATUS current
	DESCRIPTION "Mappings count - TCP"

	::={rewriteMappingsCountTcp 3}

rewriteMappingsCountTcpLevelTable OBJECT-TYPE
	SYNTAX      SEQUENCE OF RewriteMappingsCountTcpLevelEntry
	MAX-ACCESS  not-accessible
	STATUS      current
	DESCRIPTION
	"Table for rewriteMappingsCountTcp"
	::={rewriteMappingsCountTcp 4}

rewriteMappingsCountTcpLevelEntry OBJECT-TYPE
	SYNTAX      RewriteMappingsCountTcpLevelEntry
	MAX-ACCESS  not-accessible
	STATUS      current
	DESCRIPTION
	"Table entry for rewriteMappingsCountTcp"
	INDEX { rewriteMappingsCountTcpLevelName }
	::={rewriteMappingsCountTcpLevelTable 1}

RewriteMappingsCountTcpLevelEntry ::=
	SEQUENCE {
		rewriteMappingsCountTcpLevelName	DisplayString,
		rewriteMappingsCountTcpLevelVal	CounterBasedGauge64,
		rewriteMappingsCountTcpLevelMax	CounterBasedGauge64
	}

rewriteMappingsCountTcpLevelName OBJECT-TYPE
	SYNTAX      DisplayString
	MAX-ACCESS  not-accessible
	STATUS      current
	DESCRIPTION
	"Table entry display string for rewriteMappingsCountTcp"
	::={rewriteMappingsCountTcpLevelEntry 1}

rewriteMappingsCountTcpLevelVal OBJECT-TYPE
	SYNTAX	 CounterBasedGauge64
	MAX-ACCESS  read-only
	STATUS      current
	DESCRIPTION
	"Table entry attribute for rewriteMappingsCountTcp"
	::={rewriteMappingsCountTcpLevelEntry 2}

rewriteMappingsCountTcpLevelMax OBJECT-TYPE
	SYNTAX	 CounterBasedGauge64
	MAX-ACCESS  read-only
	STATUS      current
	DESCRIPTION
	"Table entry attribute for rewriteMappingsCountTcp"
	::={rewriteMappingsCountTcpLevelEntry 4}


rewriteMappingsCountUdp	OBJECT IDENTIFIER ::={rewrite 12}

rewriteMappingsCountUdpVal	OBJECT-TYPE
	SYNTAX	 CounterBasedGauge64
	MAX-ACCESS read-only
	STATUS current
	DESCRIPTION "Mappings count - UDP"

	::={rewriteMappingsCountUdp 1}

rewriteMappingsCountUdpMax	OBJECT-TYPE
	SYNTAX	 CounterBasedGauge64
	MAX-ACCESS read-only
	STATUS current
	DESCRIPTION "Mappings count - UDP"

	::={rewriteMappingsCountUdp 3}

rewriteMappingsCountUdpLevelTable OBJECT-TYPE
	SYNTAX      SEQUENCE OF RewriteMappingsCountUdpLevelEntry
	MAX-ACCESS  not-accessible
	STATUS      current
	DESCRIPTION
	"Table for rewriteMappingsCountUdp"
	::={rewriteMappingsCountUdp 4}

rewriteMappingsCountUdpLevelEntry OBJECT-TYPE
	SYNTAX      RewriteMappingsCountUdpLevelEntry
	MAX-ACCESS  not-accessible
	STATUS      current
	DESCRIPTION
	"Table entry for rewriteMappingsCountUdp"
	INDEX { rewriteMappingsCountUdpLevelName }
	::={rewriteMappingsCountUdpLevelTable 1}

RewriteMappingsCountUdpLevelEntry ::=
	SEQUENCE {
		rewriteMappingsCountUdpLevelName	DisplayString,
		rewriteMappingsCountUdpLevelVal	CounterBasedGauge64,
		rewriteMappingsCountUdpLevelMax	CounterBasedGauge64
	}

rewriteMappingsCountUdpLevelName OBJECT-TYPE
	SYNTAX      DisplayString
	MAX-ACCESS  not-accessible
	STATUS      current
	DESCRIPTION
	"Table entry display string for rewriteMappingsCountUdp"
	::={rewriteMappingsCountUdpLevelEntry 1}

rewriteMappingsCountUdpLevelVal OBJECT-TYPE
	SYNTAX	 CounterBasedGauge64
	MAX-ACCESS  read-only
	STATUS      current
	DESCRIPTION
	"Table entry attribute for rewriteMappingsCountUdp"
	::={rewriteMappingsCountUdpLevelEntry 2}

rewriteMappingsCountUdpLevelMax OBJECT-TYPE
	SYNTAX	 CounterBasedGauge64
	MAX-ACCESS  read-only
	STATUS      current
	DESCRIPTION
	"Table entry attribute for rewriteMappingsCountUdp"
	::={rewriteMappingsCountUdpLevelEntry 4}


rewriteMappingsCountIcmp	OBJECT IDENTIFIER ::={rewrite 13}

rewriteMappingsCountIcmpVal	OBJECT-TYPE
	SYNTAX	 CounterBasedGauge64
	MAX-ACCESS read-only
	STATUS current
	DESCRIPTION "Mappings count - ICMP"

	::={rewriteMappingsCountIcmp 1}

rewriteMappingsCountIcmpMax	OBJECT-TYPE
	SYNTAX	 CounterBasedGauge64
	MAX-ACCESS read-only
	STATUS current
	DESCRIPTION "Mappings count - ICMP"

	::={rewriteMappingsCountIcmp 3}

rewriteMappingsCountIcmpLevelTable OBJECT-TYPE
	SYNTAX      SEQUENCE OF RewriteMappingsCountIcmpLevelEntry
	MAX-ACCESS  not-accessible
	STATUS      current
	DESCRIPTION
	"Table for rewriteMappingsCountIcmp"
	::={rewriteMappingsCountIcmp 4}

rewriteMappingsCountIcmpLevelEntry OBJECT-TYPE
	SYNTAX      RewriteMappingsCountIcmpLevelEntry
	MAX-ACCESS  not-accessible
	STATUS      current
	DESCRIPTION
	"Table entry for rewriteMappingsCountIcmp"
	INDEX { rewriteMappingsCountIcmpLevelName }
	::={rewriteMappingsCountIcmpLevelTable 1}

RewriteMappingsCountIcmpLevelEntry ::=
	SEQUENCE {
		rewriteMappingsCountIcmpLevelName	DisplayString,
		rewriteMappingsCountIcmpLevelVal	CounterBasedGauge64,
		rewriteMappingsCountIcmpLevelMax	CounterBasedGauge64
	}

rewriteMappingsCountIcmpLevelName OBJECT-TYPE
	SYNTAX      DisplayString
	MAX-ACCESS  not-accessible
	STATUS      current
	DESCRIPTION
	"Table entry display string for rewriteMappingsCountIcmp"
	::={rewriteMappingsCountIcmpLevelEntry 1}

rewriteMappingsCountIcmpLevelVal OBJECT-TYPE
	SYNTAX	 CounterBasedGauge64
	MAX-ACCESS  read-only
	STATUS      current
	DESCRIPTION
	"Table entry attribute for rewriteMappingsCountIcmp"
	::={rewriteMappingsCountIcmpLevelEntry 2}

rewriteMappingsCountIcmpLevelMax OBJECT-TYPE
	SYNTAX	 CounterBasedGauge64
	MAX-ACCESS  read-only
	STATUS      current
	DESCRIPTION
	"Table entry attribute for rewriteMappingsCountIcmp"
	::={rewriteMappingsCountIcmpLevelEntry 4}


rewriteMappingCreationFailureResources	OBJECT IDENTIFIER ::={rewrite 14}

rewriteMappingCreationFailureResourcesVal	OBJECT-TYPE
	SYNTAX	 Counter64
	MAX-ACCESS read-only
	STATUS current
	DESCRIPTION "Mapping creation failure (resources)"

	::={rewriteMappingCreationFailureResources 1}

rewriteMappingCreationFailureResourcesMom	OBJECT-TYPE
	SYNTAX	 CounterBasedGauge64
	MAX-ACCESS read-only
	STATUS current
	DESCRIPTION "Mapping creation failure (resources)"

	::={rewriteMappingCreationFailureResources 2}

rewriteMappingCreationFailureResourcesMax	OBJECT-TYPE
	SYNTAX	 CounterBasedGauge64
	MAX-ACCESS read-only
	STATUS current
	DESCRIPTION "Mapping creation failure (resources)"

	::={rewriteMappingCreationFailureResources 3}

rewriteMappingCreationFailureResourcesLevelTable OBJECT-TYPE
	SYNTAX      SEQUENCE OF RewriteMappingCreationFailureResourcesLevelEntry
	MAX-ACCESS  not-accessible
	STATUS      current
	DESCRIPTION
	"Table for rewriteMappingCreationFailureResources"
	::={rewriteMappingCreationFailureResources 4}

rewriteMappingCreationFailureResourcesLevelEntry OBJECT-TYPE
	SYNTAX      RewriteMappingCreationFailureResourcesLevelEntry
	MAX-ACCESS  not-accessible
	STATUS      current
	DESCRIPTION
	"Table entry for rewriteMappingCreationFailureResources"
	INDEX { rewriteMappingCreationFailureResourcesLevelName }
	::={rewriteMappingCreationFailureResourcesLevelTable 1}

RewriteMappingCreationFailureResourcesLevelEntry ::=
	SEQUENCE {
		rewriteMappingCreationFailureResourcesLevelName	DisplayString,
		rewriteMappingCreationFailureResourcesLevelVal	Counter64,
		rewriteMappingCreationFailureResourcesLevelMom	CounterBasedGauge64,
		rewriteMappingCreationFailureResourcesLevelMax	CounterBasedGauge64
	}

rewriteMappingCreationFailureResourcesLevelName OBJECT-TYPE
	SYNTAX      DisplayString
	MAX-ACCESS  not-accessible
	STATUS      current
	DESCRIPTION
	"Table entry display string for rewriteMappingCreationFailureResources"
	::={rewriteMappingCreationFailureResourcesLevelEntry 1}

rewriteMappingCreationFailureResourcesLevelVal OBJECT-TYPE
	SYNTAX	 Counter64
	MAX-ACCESS  read-only
	STATUS      current
	DESCRIPTION
	"Table entry attribute for rewriteMappingCreationFailureResources"
	::={rewriteMappingCreationFailureResourcesLevelEntry 2}

rewriteMappingCreationFailureResourcesLevelMom OBJECT-TYPE
	SYNTAX	 CounterBasedGauge64
	MAX-ACCESS  read-only
	STATUS      current
	DESCRIPTION
	"Table entry attribute for rewriteMappingCreationFailureResources"
	::={rewriteMappingCreationFailureResourcesLevelEntry 3}

rewriteMappingCreationFailureResourcesLevelMax OBJECT-TYPE
	SYNTAX	 CounterBasedGauge64
	MAX-ACCESS  read-only
	STATUS      current
	DESCRIPTION
	"Table entry attribute for rewriteMappingCreationFailureResources"
	::={rewriteMappingCreationFailureResourcesLevelEntry 4}


rewriteMappingCreationFailurePorts	OBJECT IDENTIFIER ::={rewrite 15}

rewriteMappingCreationFailurePortsVal	OBJECT-TYPE
	SYNTAX	 Counter64
	MAX-ACCESS read-only
	STATUS current
	DESCRIPTION "Mapping creation failure (no available ports in port blocks)"

	::={rewriteMappingCreationFailurePorts 1}

rewriteMappingCreationFailurePortsMom	OBJECT-TYPE
	SYNTAX	 CounterBasedGauge64
	MAX-ACCESS read-only
	STATUS current
	DESCRIPTION "Mapping creation failure (no available ports in port blocks)"

	::={rewriteMappingCreationFailurePorts 2}

rewriteMappingCreationFailurePortsMax	OBJECT-TYPE
	SYNTAX	 CounterBasedGauge64
	MAX-ACCESS read-only
	STATUS current
	DESCRIPTION "Mapping creation failure (no available ports in port blocks)"

	::={rewriteMappingCreationFailurePorts 3}

rewriteMappingCreationFailurePortsLevelTable OBJECT-TYPE
	SYNTAX      SEQUENCE OF RewriteMappingCreationFailurePortsLevelEntry
	MAX-ACCESS  not-accessible
	STATUS      current
	DESCRIPTION
	"Table for rewriteMappingCreationFailurePorts"
	::={rewriteMappingCreationFailurePorts 4}

rewriteMappingCreationFailurePortsLevelEntry OBJECT-TYPE
	SYNTAX      RewriteMappingCreationFailurePortsLevelEntry
	MAX-ACCESS  not-accessible
	STATUS      current
	DESCRIPTION
	"Table entry for rewriteMappingCreationFailurePorts"
	INDEX { rewriteMappingCreationFailurePortsLevelName }
	::={rewriteMappingCreationFailurePortsLevelTable 1}

RewriteMappingCreationFailurePortsLevelEntry ::=
	SEQUENCE {
		rewriteMappingCreationFailurePortsLevelName	DisplayString,
		rewriteMappingCreationFailurePortsLevelVal	Counter64,
		rewriteMappingCreationFailurePortsLevelMom	CounterBasedGauge64,
		rewriteMappingCreationFailurePortsLevelMax	CounterBasedGauge64
	}

rewriteMappingCreationFailurePortsLevelName OBJECT-TYPE
	SYNTAX      DisplayString
	MAX-ACCESS  not-accessible
	STATUS      current
	DESCRIPTION
	"Table entry display string for rewriteMappingCreationFailurePorts"
	::={rewriteMappingCreationFailurePortsLevelEntry 1}

rewriteMappingCreationFailurePortsLevelVal OBJECT-TYPE
	SYNTAX	 Counter64
	MAX-ACCESS  read-only
	STATUS      current
	DESCRIPTION
	"Table entry attribute for rewriteMappingCreationFailurePorts"
	::={rewriteMappingCreationFailurePortsLevelEntry 2}

rewriteMappingCreationFailurePortsLevelMom OBJECT-TYPE
	SYNTAX	 CounterBasedGauge64
	MAX-ACCESS  read-only
	STATUS      current
	DESCRIPTION
	"Table entry attribute for rewriteMappingCreationFailurePorts"
	::={rewriteMappingCreationFailurePortsLevelEntry 3}

rewriteMappingCreationFailurePortsLevelMax OBJECT-TYPE
	SYNTAX	 CounterBasedGauge64
	MAX-ACCESS  read-only
	STATUS      current
	DESCRIPTION
	"Table entry attribute for rewriteMappingCreationFailurePorts"
	::={rewriteMappingCreationFailurePortsLevelEntry 4}


rewriteMappingCreationFailurePortsTcp	OBJECT IDENTIFIER ::={rewrite 16}

rewriteMappingCreationFailurePortsTcpVal	OBJECT-TYPE
	SYNTAX	 Counter64
	MAX-ACCESS read-only
	STATUS current
	DESCRIPTION "Mapping creation failure - TCP (no available ports in port blocks)"

	::={rewriteMappingCreationFailurePortsTcp 1}

rewriteMappingCreationFailurePortsTcpMom	OBJECT-TYPE
	SYNTAX	 CounterBasedGauge64
	MAX-ACCESS read-only
	STATUS current
	DESCRIPTION "Mapping creation failure - TCP (no available ports in port blocks)"

	::={rewriteMappingCreationFailurePortsTcp 2}

rewriteMappingCreationFailurePortsTcpMax	OBJECT-TYPE
	SYNTAX	 CounterBasedGauge64
	MAX-ACCESS read-only
	STATUS current
	DESCRIPTION "Mapping creation failure - TCP (no available ports in port blocks)"

	::={rewriteMappingCreationFailurePortsTcp 3}

rewriteMappingCreationFailurePortsTcpLevelTable OBJECT-TYPE
	SYNTAX      SEQUENCE OF RewriteMappingCreationFailurePortsTcpLevelEntry
	MAX-ACCESS  not-accessible
	STATUS      current
	DESCRIPTION
	"Table for rewriteMappingCreationFailurePortsTcp"
	::={rewriteMappingCreationFailurePortsTcp 4}

rewriteMappingCreationFailurePortsTcpLevelEntry OBJECT-TYPE
	SYNTAX      RewriteMappingCreationFailurePortsTcpLevelEntry
	MAX-ACCESS  not-accessible
	STATUS      current
	DESCRIPTION
	"Table entry for rewriteMappingCreationFailurePortsTcp"
	INDEX { rewriteMappingCreationFailurePortsTcpLevelName }
	::={rewriteMappingCreationFailurePortsTcpLevelTable 1}

RewriteMappingCreationFailurePortsTcpLevelEntry ::=
	SEQUENCE {
		rewriteMappingCreationFailurePortsTcpLevelName	DisplayString,
		rewriteMappingCreationFailurePortsTcpLevelVal	Counter64,
		rewriteMappingCreationFailurePortsTcpLevelMom	CounterBasedGauge64,
		rewriteMappingCreationFailurePortsTcpLevelMax	CounterBasedGauge64
	}

rewriteMappingCreationFailurePortsTcpLevelName OBJECT-TYPE
	SYNTAX      DisplayString
	MAX-ACCESS  not-accessible
	STATUS      current
	DESCRIPTION
	"Table entry display string for rewriteMappingCreationFailurePortsTcp"
	::={rewriteMappingCreationFailurePortsTcpLevelEntry 1}

rewriteMappingCreationFailurePortsTcpLevelVal OBJECT-TYPE
	SYNTAX	 Counter64
	MAX-ACCESS  read-only
	STATUS      current
	DESCRIPTION
	"Table entry attribute for rewriteMappingCreationFailurePortsTcp"
	::={rewriteMappingCreationFailurePortsTcpLevelEntry 2}

rewriteMappingCreationFailurePortsTcpLevelMom OBJECT-TYPE
	SYNTAX	 CounterBasedGauge64
	MAX-ACCESS  read-only
	STATUS      current
	DESCRIPTION
	"Table entry attribute for rewriteMappingCreationFailurePortsTcp"
	::={rewriteMappingCreationFailurePortsTcpLevelEntry 3}

rewriteMappingCreationFailurePortsTcpLevelMax OBJECT-TYPE
	SYNTAX	 CounterBasedGauge64
	MAX-ACCESS  read-only
	STATUS      current
	DESCRIPTION
	"Table entry attribute for rewriteMappingCreationFailurePortsTcp"
	::={rewriteMappingCreationFailurePortsTcpLevelEntry 4}


rewriteMappingCreationFailurePortsUdp	OBJECT IDENTIFIER ::={rewrite 17}

rewriteMappingCreationFailurePortsUdpVal	OBJECT-TYPE
	SYNTAX	 Counter64
	MAX-ACCESS read-only
	STATUS current
	DESCRIPTION "Mapping creation failure - UDP (no available ports in port blocks)"

	::={rewriteMappingCreationFailurePortsUdp 1}

rewriteMappingCreationFailurePortsUdpMom	OBJECT-TYPE
	SYNTAX	 CounterBasedGauge64
	MAX-ACCESS read-only
	STATUS current
	DESCRIPTION "Mapping creation failure - UDP (no available ports in port blocks)"

	::={rewriteMappingCreationFailurePortsUdp 2}

rewriteMappingCreationFailurePortsUdpMax	OBJECT-TYPE
	SYNTAX	 CounterBasedGauge64
	MAX-ACCESS read-only
	STATUS current
	DESCRIPTION "Mapping creation failure - UDP (no available ports in port blocks)"

	::={rewriteMappingCreationFailurePortsUdp 3}

rewriteMappingCreationFailurePortsUdpLevelTable OBJECT-TYPE
	SYNTAX      SEQUENCE OF RewriteMappingCreationFailurePortsUdpLevelEntry
	MAX-ACCESS  not-accessible
	STATUS      current
	DESCRIPTION
	"Table for rewriteMappingCreationFailurePortsUdp"
	::={rewriteMappingCreationFailurePortsUdp 4}

rewriteMappingCreationFailurePortsUdpLevelEntry OBJECT-TYPE
	SYNTAX      RewriteMappingCreationFailurePortsUdpLevelEntry
	MAX-ACCESS  not-accessible
	STATUS      current
	DESCRIPTION
	"Table entry for rewriteMappingCreationFailurePortsUdp"
	INDEX { rewriteMappingCreationFailurePortsUdpLevelName }
	::={rewriteMappingCreationFailurePortsUdpLevelTable 1}

RewriteMappingCreationFailurePortsUdpLevelEntry ::=
	SEQUENCE {
		rewriteMappingCreationFailurePortsUdpLevelName	DisplayString,
		rewriteMappingCreationFailurePortsUdpLevelVal	Counter64,
		rewriteMappingCreationFailurePortsUdpLevelMom	CounterBasedGauge64,
		rewriteMappingCreationFailurePortsUdpLevelMax	CounterBasedGauge64
	}

rewriteMappingCreationFailurePortsUdpLevelName OBJECT-TYPE
	SYNTAX      DisplayString
	MAX-ACCESS  not-accessible
	STATUS      current
	DESCRIPTION
	"Table entry display string for rewriteMappingCreationFailurePortsUdp"
	::={rewriteMappingCreationFailurePortsUdpLevelEntry 1}

rewriteMappingCreationFailurePortsUdpLevelVal OBJECT-TYPE
	SYNTAX	 Counter64
	MAX-ACCESS  read-only
	STATUS      current
	DESCRIPTION
	"Table entry attribute for rewriteMappingCreationFailurePortsUdp"
	::={rewriteMappingCreationFailurePortsUdpLevelEntry 2}

rewriteMappingCreationFailurePortsUdpLevelMom OBJECT-TYPE
	SYNTAX	 CounterBasedGauge64
	MAX-ACCESS  read-only
	STATUS      current
	DESCRIPTION
	"Table entry attribute for rewriteMappingCreationFailurePortsUdp"
	::={rewriteMappingCreationFailurePortsUdpLevelEntry 3}

rewriteMappingCreationFailurePortsUdpLevelMax OBJECT-TYPE
	SYNTAX	 CounterBasedGauge64
	MAX-ACCESS  read-only
	STATUS      current
	DESCRIPTION
	"Table entry attribute for rewriteMappingCreationFailurePortsUdp"
	::={rewriteMappingCreationFailurePortsUdpLevelEntry 4}


rewriteMappingCreationFailurePortsIcmp	OBJECT IDENTIFIER ::={rewrite 18}

rewriteMappingCreationFailurePortsIcmpVal	OBJECT-TYPE
	SYNTAX	 Counter64
	MAX-ACCESS read-only
	STATUS current
	DESCRIPTION "Mapping creation failure - ICMP (no available ports in port blocks)"

	::={rewriteMappingCreationFailurePortsIcmp 1}

rewriteMappingCreationFailurePortsIcmpMom	OBJECT-TYPE
	SYNTAX	 CounterBasedGauge64
	MAX-ACCESS read-only
	STATUS current
	DESCRIPTION "Mapping creation failure - ICMP (no available ports in port blocks)"

	::={rewriteMappingCreationFailurePortsIcmp 2}

rewriteMappingCreationFailurePortsIcmpMax	OBJECT-TYPE
	SYNTAX	 CounterBasedGauge64
	MAX-ACCESS read-only
	STATUS current
	DESCRIPTION "Mapping creation failure - ICMP (no available ports in port blocks)"

	::={rewriteMappingCreationFailurePortsIcmp 3}

rewriteMappingCreationFailurePortsIcmpLevelTable OBJECT-TYPE
	SYNTAX      SEQUENCE OF RewriteMappingCreationFailurePortsIcmpLevelEntry
	MAX-ACCESS  not-accessible
	STATUS      current
	DESCRIPTION
	"Table for rewriteMappingCreationFailurePortsIcmp"
	::={rewriteMappingCreationFailurePortsIcmp 4}

rewriteMappingCreationFailurePortsIcmpLevelEntry OBJECT-TYPE
	SYNTAX      RewriteMappingCreationFailurePortsIcmpLevelEntry
	MAX-ACCESS  not-accessible
	STATUS      current
	DESCRIPTION
	"Table entry for rewriteMappingCreationFailurePortsIcmp"
	INDEX { rewriteMappingCreationFailurePortsIcmpLevelName }
	::={rewriteMappingCreationFailurePortsIcmpLevelTable 1}

RewriteMappingCreationFailurePortsIcmpLevelEntry ::=
	SEQUENCE {
		rewriteMappingCreationFailurePortsIcmpLevelName	DisplayString,
		rewriteMappingCreationFailurePortsIcmpLevelVal	Counter64,
		rewriteMappingCreationFailurePortsIcmpLevelMom	CounterBasedGauge64,
		rewriteMappingCreationFailurePortsIcmpLevelMax	CounterBasedGauge64
	}

rewriteMappingCreationFailurePortsIcmpLevelName OBJECT-TYPE
	SYNTAX      DisplayString
	MAX-ACCESS  not-accessible
	STATUS      current
	DESCRIPTION
	"Table entry display string for rewriteMappingCreationFailurePortsIcmp"
	::={rewriteMappingCreationFailurePortsIcmpLevelEntry 1}

rewriteMappingCreationFailurePortsIcmpLevelVal OBJECT-TYPE
	SYNTAX	 Counter64
	MAX-ACCESS  read-only
	STATUS      current
	DESCRIPTION
	"Table entry attribute for rewriteMappingCreationFailurePortsIcmp"
	::={rewriteMappingCreationFailurePortsIcmpLevelEntry 2}

rewriteMappingCreationFailurePortsIcmpLevelMom OBJECT-TYPE
	SYNTAX	 CounterBasedGauge64
	MAX-ACCESS  read-only
	STATUS      current
	DESCRIPTION
	"Table entry attribute for rewriteMappingCreationFailurePortsIcmp"
	::={rewriteMappingCreationFailurePortsIcmpLevelEntry 3}

rewriteMappingCreationFailurePortsIcmpLevelMax OBJECT-TYPE
	SYNTAX	 CounterBasedGauge64
	MAX-ACCESS  read-only
	STATUS      current
	DESCRIPTION
	"Table entry attribute for rewriteMappingCreationFailurePortsIcmp"
	::={rewriteMappingCreationFailurePortsIcmpLevelEntry 4}


rewriteMappingSubscribersCount	OBJECT IDENTIFIER ::={rewrite 19}

rewriteMappingSubscribersCountVal	OBJECT-TYPE
	SYNTAX	 CounterBasedGauge64
	MAX-ACCESS read-only
	STATUS current
	DESCRIPTION "Mapping - subscriber count"

	::={rewriteMappingSubscribersCount 1}

rewriteMappingSubscribersCountMax	OBJECT-TYPE
	SYNTAX	 CounterBasedGauge64
	MAX-ACCESS read-only
	STATUS current
	DESCRIPTION "Mapping - subscriber count"

	::={rewriteMappingSubscribersCount 3}

rewriteMappingSubscribersCountLevelTable OBJECT-TYPE
	SYNTAX      SEQUENCE OF RewriteMappingSubscribersCountLevelEntry
	MAX-ACCESS  not-accessible
	STATUS      current
	DESCRIPTION
	"Table for rewriteMappingSubscribersCount"
	::={rewriteMappingSubscribersCount 4}

rewriteMappingSubscribersCountLevelEntry OBJECT-TYPE
	SYNTAX      RewriteMappingSubscribersCountLevelEntry
	MAX-ACCESS  not-accessible
	STATUS      current
	DESCRIPTION
	"Table entry for rewriteMappingSubscribersCount"
	INDEX { rewriteMappingSubscribersCountLevelName }
	::={rewriteMappingSubscribersCountLevelTable 1}

RewriteMappingSubscribersCountLevelEntry ::=
	SEQUENCE {
		rewriteMappingSubscribersCountLevelName	DisplayString,
		rewriteMappingSubscribersCountLevelVal	CounterBasedGauge64,
		rewriteMappingSubscribersCountLevelMax	CounterBasedGauge64
	}

rewriteMappingSubscribersCountLevelName OBJECT-TYPE
	SYNTAX      DisplayString
	MAX-ACCESS  not-accessible
	STATUS      current
	DESCRIPTION
	"Table entry display string for rewriteMappingSubscribersCount"
	::={rewriteMappingSubscribersCountLevelEntry 1}

rewriteMappingSubscribersCountLevelVal OBJECT-TYPE
	SYNTAX	 CounterBasedGauge64
	MAX-ACCESS  read-only
	STATUS      current
	DESCRIPTION
	"Table entry attribute for rewriteMappingSubscribersCount"
	::={rewriteMappingSubscribersCountLevelEntry 2}

rewriteMappingSubscribersCountLevelMax OBJECT-TYPE
	SYNTAX	 CounterBasedGauge64
	MAX-ACCESS  read-only
	STATUS      current
	DESCRIPTION
	"Table entry attribute for rewriteMappingSubscribersCount"
	::={rewriteMappingSubscribersCountLevelEntry 4}


rewriteMappingIPCount	OBJECT IDENTIFIER ::={rewrite 20}

rewriteMappingIPCountVal	OBJECT-TYPE
	SYNTAX	 CounterBasedGauge64
	MAX-ACCESS read-only
	STATUS current
	DESCRIPTION "Mapping - IP-address count"

	::={rewriteMappingIPCount 1}

rewriteMappingIPCountMax	OBJECT-TYPE
	SYNTAX	 CounterBasedGauge64
	MAX-ACCESS read-only
	STATUS current
	DESCRIPTION "Mapping - IP-address count"

	::={rewriteMappingIPCount 3}

rewriteMappingIPCountLevelTable OBJECT-TYPE
	SYNTAX      SEQUENCE OF RewriteMappingIPCountLevelEntry
	MAX-ACCESS  not-accessible
	STATUS      current
	DESCRIPTION
	"Table for rewriteMappingIPCount"
	::={rewriteMappingIPCount 4}

rewriteMappingIPCountLevelEntry OBJECT-TYPE
	SYNTAX      RewriteMappingIPCountLevelEntry
	MAX-ACCESS  not-accessible
	STATUS      current
	DESCRIPTION
	"Table entry for rewriteMappingIPCount"
	INDEX { rewriteMappingIPCountLevelName }
	::={rewriteMappingIPCountLevelTable 1}

RewriteMappingIPCountLevelEntry ::=
	SEQUENCE {
		rewriteMappingIPCountLevelName	DisplayString,
		rewriteMappingIPCountLevelVal	CounterBasedGauge64,
		rewriteMappingIPCountLevelMax	CounterBasedGauge64
	}

rewriteMappingIPCountLevelName OBJECT-TYPE
	SYNTAX      DisplayString
	MAX-ACCESS  not-accessible
	STATUS      current
	DESCRIPTION
	"Table entry display string for rewriteMappingIPCount"
	::={rewriteMappingIPCountLevelEntry 1}

rewriteMappingIPCountLevelVal OBJECT-TYPE
	SYNTAX	 CounterBasedGauge64
	MAX-ACCESS  read-only
	STATUS      current
	DESCRIPTION
	"Table entry attribute for rewriteMappingIPCount"
	::={rewriteMappingIPCountLevelEntry 2}

rewriteMappingIPCountLevelMax OBJECT-TYPE
	SYNTAX	 CounterBasedGauge64
	MAX-ACCESS  read-only
	STATUS      current
	DESCRIPTION
	"Table entry attribute for rewriteMappingIPCount"
	::={rewriteMappingIPCountLevelEntry 4}


rewriteMappingsCreatedGre	OBJECT IDENTIFIER ::={rewrite 21}

rewriteMappingsCreatedGreVal	OBJECT-TYPE
	SYNTAX	 Counter64
	MAX-ACCESS read-only
	STATUS current
	DESCRIPTION "Mappings created - GRE"

	::={rewriteMappingsCreatedGre 1}

rewriteMappingsCreatedGreMom	OBJECT-TYPE
	SYNTAX	 CounterBasedGauge64
	MAX-ACCESS read-only
	STATUS current
	DESCRIPTION "Mappings created - GRE"

	::={rewriteMappingsCreatedGre 2}

rewriteMappingsCreatedGreMax	OBJECT-TYPE
	SYNTAX	 CounterBasedGauge64
	MAX-ACCESS read-only
	STATUS current
	DESCRIPTION "Mappings created - GRE"

	::={rewriteMappingsCreatedGre 3}

rewriteMappingsCreatedGreLevelTable OBJECT-TYPE
	SYNTAX      SEQUENCE OF RewriteMappingsCreatedGreLevelEntry
	MAX-ACCESS  not-accessible
	STATUS      current
	DESCRIPTION
	"Table for rewriteMappingsCreatedGre"
	::={rewriteMappingsCreatedGre 4}

rewriteMappingsCreatedGreLevelEntry OBJECT-TYPE
	SYNTAX      RewriteMappingsCreatedGreLevelEntry
	MAX-ACCESS  not-accessible
	STATUS      current
	DESCRIPTION
	"Table entry for rewriteMappingsCreatedGre"
	INDEX { rewriteMappingsCreatedGreLevelName }
	::={rewriteMappingsCreatedGreLevelTable 1}

RewriteMappingsCreatedGreLevelEntry ::=
	SEQUENCE {
		rewriteMappingsCreatedGreLevelName	DisplayString,
		rewriteMappingsCreatedGreLevelVal	Counter64,
		rewriteMappingsCreatedGreLevelMom	CounterBasedGauge64,
		rewriteMappingsCreatedGreLevelMax	CounterBasedGauge64
	}

rewriteMappingsCreatedGreLevelName OBJECT-TYPE
	SYNTAX      DisplayString
	MAX-ACCESS  not-accessible
	STATUS      current
	DESCRIPTION
	"Table entry display string for rewriteMappingsCreatedGre"
	::={rewriteMappingsCreatedGreLevelEntry 1}

rewriteMappingsCreatedGreLevelVal OBJECT-TYPE
	SYNTAX	 Counter64
	MAX-ACCESS  read-only
	STATUS      current
	DESCRIPTION
	"Table entry attribute for rewriteMappingsCreatedGre"
	::={rewriteMappingsCreatedGreLevelEntry 2}

rewriteMappingsCreatedGreLevelMom OBJECT-TYPE
	SYNTAX	 CounterBasedGauge64
	MAX-ACCESS  read-only
	STATUS      current
	DESCRIPTION
	"Table entry attribute for rewriteMappingsCreatedGre"
	::={rewriteMappingsCreatedGreLevelEntry 3}

rewriteMappingsCreatedGreLevelMax OBJECT-TYPE
	SYNTAX	 CounterBasedGauge64
	MAX-ACCESS  read-only
	STATUS      current
	DESCRIPTION
	"Table entry attribute for rewriteMappingsCreatedGre"
	::={rewriteMappingsCreatedGreLevelEntry 4}


rewriteMappingsReusedGre	OBJECT IDENTIFIER ::={rewrite 22}

rewriteMappingsReusedGreVal	OBJECT-TYPE
	SYNTAX	 Counter64
	MAX-ACCESS read-only
	STATUS current
	DESCRIPTION "Mappings reused - GRE"

	::={rewriteMappingsReusedGre 1}

rewriteMappingsReusedGreMom	OBJECT-TYPE
	SYNTAX	 CounterBasedGauge64
	MAX-ACCESS read-only
	STATUS current
	DESCRIPTION "Mappings reused - GRE"

	::={rewriteMappingsReusedGre 2}

rewriteMappingsReusedGreMax	OBJECT-TYPE
	SYNTAX	 CounterBasedGauge64
	MAX-ACCESS read-only
	STATUS current
	DESCRIPTION "Mappings reused - GRE"

	::={rewriteMappingsReusedGre 3}

rewriteMappingsReusedGreLevelTable OBJECT-TYPE
	SYNTAX      SEQUENCE OF RewriteMappingsReusedGreLevelEntry
	MAX-ACCESS  not-accessible
	STATUS      current
	DESCRIPTION
	"Table for rewriteMappingsReusedGre"
	::={rewriteMappingsReusedGre 4}

rewriteMappingsReusedGreLevelEntry OBJECT-TYPE
	SYNTAX      RewriteMappingsReusedGreLevelEntry
	MAX-ACCESS  not-accessible
	STATUS      current
	DESCRIPTION
	"Table entry for rewriteMappingsReusedGre"
	INDEX { rewriteMappingsReusedGreLevelName }
	::={rewriteMappingsReusedGreLevelTable 1}

RewriteMappingsReusedGreLevelEntry ::=
	SEQUENCE {
		rewriteMappingsReusedGreLevelName	DisplayString,
		rewriteMappingsReusedGreLevelVal	Counter64,
		rewriteMappingsReusedGreLevelMom	CounterBasedGauge64,
		rewriteMappingsReusedGreLevelMax	CounterBasedGauge64
	}

rewriteMappingsReusedGreLevelName OBJECT-TYPE
	SYNTAX      DisplayString
	MAX-ACCESS  not-accessible
	STATUS      current
	DESCRIPTION
	"Table entry display string for rewriteMappingsReusedGre"
	::={rewriteMappingsReusedGreLevelEntry 1}

rewriteMappingsReusedGreLevelVal OBJECT-TYPE
	SYNTAX	 Counter64
	MAX-ACCESS  read-only
	STATUS      current
	DESCRIPTION
	"Table entry attribute for rewriteMappingsReusedGre"
	::={rewriteMappingsReusedGreLevelEntry 2}

rewriteMappingsReusedGreLevelMom OBJECT-TYPE
	SYNTAX	 CounterBasedGauge64
	MAX-ACCESS  read-only
	STATUS      current
	DESCRIPTION
	"Table entry attribute for rewriteMappingsReusedGre"
	::={rewriteMappingsReusedGreLevelEntry 3}

rewriteMappingsReusedGreLevelMax OBJECT-TYPE
	SYNTAX	 CounterBasedGauge64
	MAX-ACCESS  read-only
	STATUS      current
	DESCRIPTION
	"Table entry attribute for rewriteMappingsReusedGre"
	::={rewriteMappingsReusedGreLevelEntry 4}


rewriteMappingsCountGre	OBJECT IDENTIFIER ::={rewrite 23}

rewriteMappingsCountGreVal	OBJECT-TYPE
	SYNTAX	 CounterBasedGauge64
	MAX-ACCESS read-only
	STATUS current
	DESCRIPTION "Mappings count - GRE"

	::={rewriteMappingsCountGre 1}

rewriteMappingsCountGreMax	OBJECT-TYPE
	SYNTAX	 CounterBasedGauge64
	MAX-ACCESS read-only
	STATUS current
	DESCRIPTION "Mappings count - GRE"

	::={rewriteMappingsCountGre 3}

rewriteMappingsCountGreLevelTable OBJECT-TYPE
	SYNTAX      SEQUENCE OF RewriteMappingsCountGreLevelEntry
	MAX-ACCESS  not-accessible
	STATUS      current
	DESCRIPTION
	"Table for rewriteMappingsCountGre"
	::={rewriteMappingsCountGre 4}

rewriteMappingsCountGreLevelEntry OBJECT-TYPE
	SYNTAX      RewriteMappingsCountGreLevelEntry
	MAX-ACCESS  not-accessible
	STATUS      current
	DESCRIPTION
	"Table entry for rewriteMappingsCountGre"
	INDEX { rewriteMappingsCountGreLevelName }
	::={rewriteMappingsCountGreLevelTable 1}

RewriteMappingsCountGreLevelEntry ::=
	SEQUENCE {
		rewriteMappingsCountGreLevelName	DisplayString,
		rewriteMappingsCountGreLevelVal	CounterBasedGauge64,
		rewriteMappingsCountGreLevelMax	CounterBasedGauge64
	}

rewriteMappingsCountGreLevelName OBJECT-TYPE
	SYNTAX      DisplayString
	MAX-ACCESS  not-accessible
	STATUS      current
	DESCRIPTION
	"Table entry display string for rewriteMappingsCountGre"
	::={rewriteMappingsCountGreLevelEntry 1}

rewriteMappingsCountGreLevelVal OBJECT-TYPE
	SYNTAX	 CounterBasedGauge64
	MAX-ACCESS  read-only
	STATUS      current
	DESCRIPTION
	"Table entry attribute for rewriteMappingsCountGre"
	::={rewriteMappingsCountGreLevelEntry 2}

rewriteMappingsCountGreLevelMax OBJECT-TYPE
	SYNTAX	 CounterBasedGauge64
	MAX-ACCESS  read-only
	STATUS      current
	DESCRIPTION
	"Table entry attribute for rewriteMappingsCountGre"
	::={rewriteMappingsCountGreLevelEntry 4}


rewriteMappingCreationFailurePortsGre	OBJECT IDENTIFIER ::={rewrite 24}

rewriteMappingCreationFailurePortsGreVal	OBJECT-TYPE
	SYNTAX	 Counter64
	MAX-ACCESS read-only
	STATUS current
	DESCRIPTION "Mapping creation failure - GRE (no available ports in port blocks)"

	::={rewriteMappingCreationFailurePortsGre 1}

rewriteMappingCreationFailurePortsGreMom	OBJECT-TYPE
	SYNTAX	 CounterBasedGauge64
	MAX-ACCESS read-only
	STATUS current
	DESCRIPTION "Mapping creation failure - GRE (no available ports in port blocks)"

	::={rewriteMappingCreationFailurePortsGre 2}

rewriteMappingCreationFailurePortsGreMax	OBJECT-TYPE
	SYNTAX	 CounterBasedGauge64
	MAX-ACCESS read-only
	STATUS current
	DESCRIPTION "Mapping creation failure - GRE (no available ports in port blocks)"

	::={rewriteMappingCreationFailurePortsGre 3}

rewriteMappingCreationFailurePortsGreLevelTable OBJECT-TYPE
	SYNTAX      SEQUENCE OF RewriteMappingCreationFailurePortsGreLevelEntry
	MAX-ACCESS  not-accessible
	STATUS      current
	DESCRIPTION
	"Table for rewriteMappingCreationFailurePortsGre"
	::={rewriteMappingCreationFailurePortsGre 4}

rewriteMappingCreationFailurePortsGreLevelEntry OBJECT-TYPE
	SYNTAX      RewriteMappingCreationFailurePortsGreLevelEntry
	MAX-ACCESS  not-accessible
	STATUS      current
	DESCRIPTION
	"Table entry for rewriteMappingCreationFailurePortsGre"
	INDEX { rewriteMappingCreationFailurePortsGreLevelName }
	::={rewriteMappingCreationFailurePortsGreLevelTable 1}

RewriteMappingCreationFailurePortsGreLevelEntry ::=
	SEQUENCE {
		rewriteMappingCreationFailurePortsGreLevelName	DisplayString,
		rewriteMappingCreationFailurePortsGreLevelVal	Counter64,
		rewriteMappingCreationFailurePortsGreLevelMom	CounterBasedGauge64,
		rewriteMappingCreationFailurePortsGreLevelMax	CounterBasedGauge64
	}

rewriteMappingCreationFailurePortsGreLevelName OBJECT-TYPE
	SYNTAX      DisplayString
	MAX-ACCESS  not-accessible
	STATUS      current
	DESCRIPTION
	"Table entry display string for rewriteMappingCreationFailurePortsGre"
	::={rewriteMappingCreationFailurePortsGreLevelEntry 1}

rewriteMappingCreationFailurePortsGreLevelVal OBJECT-TYPE
	SYNTAX	 Counter64
	MAX-ACCESS  read-only
	STATUS      current
	DESCRIPTION
	"Table entry attribute for rewriteMappingCreationFailurePortsGre"
	::={rewriteMappingCreationFailurePortsGreLevelEntry 2}

rewriteMappingCreationFailurePortsGreLevelMom OBJECT-TYPE
	SYNTAX	 CounterBasedGauge64
	MAX-ACCESS  read-only
	STATUS      current
	DESCRIPTION
	"Table entry attribute for rewriteMappingCreationFailurePortsGre"
	::={rewriteMappingCreationFailurePortsGreLevelEntry 3}

rewriteMappingCreationFailurePortsGreLevelMax OBJECT-TYPE
	SYNTAX	 CounterBasedGauge64
	MAX-ACCESS  read-only
	STATUS      current
	DESCRIPTION
	"Table entry attribute for rewriteMappingCreationFailurePortsGre"
	::={rewriteMappingCreationFailurePortsGreLevelEntry 4}


rewriteMappingCreationFailureRewriteAddress	OBJECT IDENTIFIER ::={rewrite 25}

rewriteMappingCreationFailureRewriteAddressVal	OBJECT-TYPE
	SYNTAX	 Counter64
	MAX-ACCESS read-only
	STATUS current
	DESCRIPTION "Mapping creation failure - No rewrite address"

	::={rewriteMappingCreationFailureRewriteAddress 1}

rewriteMappingCreationFailureRewriteAddressMom	OBJECT-TYPE
	SYNTAX	 CounterBasedGauge64
	MAX-ACCESS read-only
	STATUS current
	DESCRIPTION "Mapping creation failure - No rewrite address"

	::={rewriteMappingCreationFailureRewriteAddress 2}

rewriteMappingCreationFailureRewriteAddressMax	OBJECT-TYPE
	SYNTAX	 CounterBasedGauge64
	MAX-ACCESS read-only
	STATUS current
	DESCRIPTION "Mapping creation failure - No rewrite address"

	::={rewriteMappingCreationFailureRewriteAddress 3}

rewriteMappingCreationFailureRewriteAddressLevelTable OBJECT-TYPE
	SYNTAX      SEQUENCE OF RewriteMappingCreationFailureRewriteAddressLevelEntry
	MAX-ACCESS  not-accessible
	STATUS      current
	DESCRIPTION
	"Table for rewriteMappingCreationFailureRewriteAddress"
	::={rewriteMappingCreationFailureRewriteAddress 4}

rewriteMappingCreationFailureRewriteAddressLevelEntry OBJECT-TYPE
	SYNTAX      RewriteMappingCreationFailureRewriteAddressLevelEntry
	MAX-ACCESS  not-accessible
	STATUS      current
	DESCRIPTION
	"Table entry for rewriteMappingCreationFailureRewriteAddress"
	INDEX { rewriteMappingCreationFailureRewriteAddressLevelName }
	::={rewriteMappingCreationFailureRewriteAddressLevelTable 1}

RewriteMappingCreationFailureRewriteAddressLevelEntry ::=
	SEQUENCE {
		rewriteMappingCreationFailureRewriteAddressLevelName	DisplayString,
		rewriteMappingCreationFailureRewriteAddressLevelVal	Counter64,
		rewriteMappingCreationFailureRewriteAddressLevelMom	CounterBasedGauge64,
		rewriteMappingCreationFailureRewriteAddressLevelMax	CounterBasedGauge64
	}

rewriteMappingCreationFailureRewriteAddressLevelName OBJECT-TYPE
	SYNTAX      DisplayString
	MAX-ACCESS  not-accessible
	STATUS      current
	DESCRIPTION
	"Table entry display string for rewriteMappingCreationFailureRewriteAddress"
	::={rewriteMappingCreationFailureRewriteAddressLevelEntry 1}

rewriteMappingCreationFailureRewriteAddressLevelVal OBJECT-TYPE
	SYNTAX	 Counter64
	MAX-ACCESS  read-only
	STATUS      current
	DESCRIPTION
	"Table entry attribute for rewriteMappingCreationFailureRewriteAddress"
	::={rewriteMappingCreationFailureRewriteAddressLevelEntry 2}

rewriteMappingCreationFailureRewriteAddressLevelMom OBJECT-TYPE
	SYNTAX	 CounterBasedGauge64
	MAX-ACCESS  read-only
	STATUS      current
	DESCRIPTION
	"Table entry attribute for rewriteMappingCreationFailureRewriteAddress"
	::={rewriteMappingCreationFailureRewriteAddressLevelEntry 3}

rewriteMappingCreationFailureRewriteAddressLevelMax OBJECT-TYPE
	SYNTAX	 CounterBasedGauge64
	MAX-ACCESS  read-only
	STATUS      current
	DESCRIPTION
	"Table entry attribute for rewriteMappingCreationFailureRewriteAddress"
	::={rewriteMappingCreationFailureRewriteAddressLevelEntry 4}


rewriteMappingCreationFailureNatsyncExternalCollision	OBJECT IDENTIFIER ::={rewrite 26}

rewriteMappingCreationFailureNatsyncExternalCollisionVal	OBJECT-TYPE
	SYNTAX	 Counter64
	MAX-ACCESS read-only
	STATUS current
	DESCRIPTION "Mapping creation failure - Natsync external collision"

	::={rewriteMappingCreationFailureNatsyncExternalCollision 1}

rewriteMappingCreationFailureNatsyncExternalCollisionMom	OBJECT-TYPE
	SYNTAX	 CounterBasedGauge64
	MAX-ACCESS read-only
	STATUS current
	DESCRIPTION "Mapping creation failure - Natsync external collision"

	::={rewriteMappingCreationFailureNatsyncExternalCollision 2}

rewriteMappingCreationFailureNatsyncExternalCollisionMax	OBJECT-TYPE
	SYNTAX	 CounterBasedGauge64
	MAX-ACCESS read-only
	STATUS current
	DESCRIPTION "Mapping creation failure - Natsync external collision"

	::={rewriteMappingCreationFailureNatsyncExternalCollision 3}

rewriteMappingCreationFailureNatsyncExternalCollisionLevelTable OBJECT-TYPE
	SYNTAX      SEQUENCE OF RewriteMappingCreationFailureNatsyncExternalCollisionLevelEntry
	MAX-ACCESS  not-accessible
	STATUS      current
	DESCRIPTION
	"Table for rewriteMappingCreationFailureNatsyncExternalCollision"
	::={rewriteMappingCreationFailureNatsyncExternalCollision 4}

rewriteMappingCreationFailureNatsyncExternalCollisionLevelEntry OBJECT-TYPE
	SYNTAX      RewriteMappingCreationFailureNatsyncExternalCollisionLevelEntry
	MAX-ACCESS  not-accessible
	STATUS      current
	DESCRIPTION
	"Table entry for rewriteMappingCreationFailureNatsyncExternalCollision"
	INDEX { rewriteMappingCreationFailureNatsyncExternalCollisionLevelName }
	::={rewriteMappingCreationFailureNatsyncExternalCollisionLevelTable 1}

RewriteMappingCreationFailureNatsyncExternalCollisionLevelEntry ::=
	SEQUENCE {
		rewriteMappingCreationFailureNatsyncExternalCollisionLevelName	DisplayString,
		rewriteMappingCreationFailureNatsyncExternalCollisionLevelVal	Counter64,
		rewriteMappingCreationFailureNatsyncExternalCollisionLevelMom	CounterBasedGauge64,
		rewriteMappingCreationFailureNatsyncExternalCollisionLevelMax	CounterBasedGauge64
	}

rewriteMappingCreationFailureNatsyncExternalCollisionLevelName OBJECT-TYPE
	SYNTAX      DisplayString
	MAX-ACCESS  not-accessible
	STATUS      current
	DESCRIPTION
	"Table entry display string for rewriteMappingCreationFailureNatsyncExternalCollision"
	::={rewriteMappingCreationFailureNatsyncExternalCollisionLevelEntry 1}

rewriteMappingCreationFailureNatsyncExternalCollisionLevelVal OBJECT-TYPE
	SYNTAX	 Counter64
	MAX-ACCESS  read-only
	STATUS      current
	DESCRIPTION
	"Table entry attribute for rewriteMappingCreationFailureNatsyncExternalCollision"
	::={rewriteMappingCreationFailureNatsyncExternalCollisionLevelEntry 2}

rewriteMappingCreationFailureNatsyncExternalCollisionLevelMom OBJECT-TYPE
	SYNTAX	 CounterBasedGauge64
	MAX-ACCESS  read-only
	STATUS      current
	DESCRIPTION
	"Table entry attribute for rewriteMappingCreationFailureNatsyncExternalCollision"
	::={rewriteMappingCreationFailureNatsyncExternalCollisionLevelEntry 3}

rewriteMappingCreationFailureNatsyncExternalCollisionLevelMax OBJECT-TYPE
	SYNTAX	 CounterBasedGauge64
	MAX-ACCESS  read-only
	STATUS      current
	DESCRIPTION
	"Table entry attribute for rewriteMappingCreationFailureNatsyncExternalCollision"
	::={rewriteMappingCreationFailureNatsyncExternalCollisionLevelEntry 4}


rewriteMappingCreationFailureNatsyncPortblock	OBJECT IDENTIFIER ::={rewrite 27}

rewriteMappingCreationFailureNatsyncPortblockVal	OBJECT-TYPE
	SYNTAX	 Counter64
	MAX-ACCESS read-only
	STATUS current
	DESCRIPTION "Mapping creation failure - Natsync portblock not found"

	::={rewriteMappingCreationFailureNatsyncPortblock 1}

rewriteMappingCreationFailureNatsyncPortblockMom	OBJECT-TYPE
	SYNTAX	 CounterBasedGauge64
	MAX-ACCESS read-only
	STATUS current
	DESCRIPTION "Mapping creation failure - Natsync portblock not found"

	::={rewriteMappingCreationFailureNatsyncPortblock 2}

rewriteMappingCreationFailureNatsyncPortblockMax	OBJECT-TYPE
	SYNTAX	 CounterBasedGauge64
	MAX-ACCESS read-only
	STATUS current
	DESCRIPTION "Mapping creation failure - Natsync portblock not found"

	::={rewriteMappingCreationFailureNatsyncPortblock 3}

rewriteMappingCreationFailureNatsyncPortblockLevelTable OBJECT-TYPE
	SYNTAX      SEQUENCE OF RewriteMappingCreationFailureNatsyncPortblockLevelEntry
	MAX-ACCESS  not-accessible
	STATUS      current
	DESCRIPTION
	"Table for rewriteMappingCreationFailureNatsyncPortblock"
	::={rewriteMappingCreationFailureNatsyncPortblock 4}

rewriteMappingCreationFailureNatsyncPortblockLevelEntry OBJECT-TYPE
	SYNTAX      RewriteMappingCreationFailureNatsyncPortblockLevelEntry
	MAX-ACCESS  not-accessible
	STATUS      current
	DESCRIPTION
	"Table entry for rewriteMappingCreationFailureNatsyncPortblock"
	INDEX { rewriteMappingCreationFailureNatsyncPortblockLevelName }
	::={rewriteMappingCreationFailureNatsyncPortblockLevelTable 1}

RewriteMappingCreationFailureNatsyncPortblockLevelEntry ::=
	SEQUENCE {
		rewriteMappingCreationFailureNatsyncPortblockLevelName	DisplayString,
		rewriteMappingCreationFailureNatsyncPortblockLevelVal	Counter64,
		rewriteMappingCreationFailureNatsyncPortblockLevelMom	CounterBasedGauge64,
		rewriteMappingCreationFailureNatsyncPortblockLevelMax	CounterBasedGauge64
	}

rewriteMappingCreationFailureNatsyncPortblockLevelName OBJECT-TYPE
	SYNTAX      DisplayString
	MAX-ACCESS  not-accessible
	STATUS      current
	DESCRIPTION
	"Table entry display string for rewriteMappingCreationFailureNatsyncPortblock"
	::={rewriteMappingCreationFailureNatsyncPortblockLevelEntry 1}

rewriteMappingCreationFailureNatsyncPortblockLevelVal OBJECT-TYPE
	SYNTAX	 Counter64
	MAX-ACCESS  read-only
	STATUS      current
	DESCRIPTION
	"Table entry attribute for rewriteMappingCreationFailureNatsyncPortblock"
	::={rewriteMappingCreationFailureNatsyncPortblockLevelEntry 2}

rewriteMappingCreationFailureNatsyncPortblockLevelMom OBJECT-TYPE
	SYNTAX	 CounterBasedGauge64
	MAX-ACCESS  read-only
	STATUS      current
	DESCRIPTION
	"Table entry attribute for rewriteMappingCreationFailureNatsyncPortblock"
	::={rewriteMappingCreationFailureNatsyncPortblockLevelEntry 3}

rewriteMappingCreationFailureNatsyncPortblockLevelMax OBJECT-TYPE
	SYNTAX	 CounterBasedGauge64
	MAX-ACCESS  read-only
	STATUS      current
	DESCRIPTION
	"Table entry attribute for rewriteMappingCreationFailureNatsyncPortblock"
	::={rewriteMappingCreationFailureNatsyncPortblockLevelEntry 4}


rewriteMappingCreationFailureNoNatcfgPptp	OBJECT IDENTIFIER ::={rewrite 28}

rewriteMappingCreationFailureNoNatcfgPptpVal	OBJECT-TYPE
	SYNTAX	 Counter64
	MAX-ACCESS read-only
	STATUS current
	DESCRIPTION "Mapping creation failure - No available natcfg (PPTP)"

	::={rewriteMappingCreationFailureNoNatcfgPptp 1}

rewriteMappingCreationFailureNoNatcfgPptpMom	OBJECT-TYPE
	SYNTAX	 CounterBasedGauge64
	MAX-ACCESS read-only
	STATUS current
	DESCRIPTION "Mapping creation failure - No available natcfg (PPTP)"

	::={rewriteMappingCreationFailureNoNatcfgPptp 2}

rewriteMappingCreationFailureNoNatcfgPptpMax	OBJECT-TYPE
	SYNTAX	 CounterBasedGauge64
	MAX-ACCESS read-only
	STATUS current
	DESCRIPTION "Mapping creation failure - No available natcfg (PPTP)"

	::={rewriteMappingCreationFailureNoNatcfgPptp 3}

rewriteMappingCreationFailureNoNatcfgPptpLevelTable OBJECT-TYPE
	SYNTAX      SEQUENCE OF RewriteMappingCreationFailureNoNatcfgPptpLevelEntry
	MAX-ACCESS  not-accessible
	STATUS      current
	DESCRIPTION
	"Table for rewriteMappingCreationFailureNoNatcfgPptp"
	::={rewriteMappingCreationFailureNoNatcfgPptp 4}

rewriteMappingCreationFailureNoNatcfgPptpLevelEntry OBJECT-TYPE
	SYNTAX      RewriteMappingCreationFailureNoNatcfgPptpLevelEntry
	MAX-ACCESS  not-accessible
	STATUS      current
	DESCRIPTION
	"Table entry for rewriteMappingCreationFailureNoNatcfgPptp"
	INDEX { rewriteMappingCreationFailureNoNatcfgPptpLevelName }
	::={rewriteMappingCreationFailureNoNatcfgPptpLevelTable 1}

RewriteMappingCreationFailureNoNatcfgPptpLevelEntry ::=
	SEQUENCE {
		rewriteMappingCreationFailureNoNatcfgPptpLevelName	DisplayString,
		rewriteMappingCreationFailureNoNatcfgPptpLevelVal	Counter64,
		rewriteMappingCreationFailureNoNatcfgPptpLevelMom	CounterBasedGauge64,
		rewriteMappingCreationFailureNoNatcfgPptpLevelMax	CounterBasedGauge64
	}

rewriteMappingCreationFailureNoNatcfgPptpLevelName OBJECT-TYPE
	SYNTAX      DisplayString
	MAX-ACCESS  not-accessible
	STATUS      current
	DESCRIPTION
	"Table entry display string for rewriteMappingCreationFailureNoNatcfgPptp"
	::={rewriteMappingCreationFailureNoNatcfgPptpLevelEntry 1}

rewriteMappingCreationFailureNoNatcfgPptpLevelVal OBJECT-TYPE
	SYNTAX	 Counter64
	MAX-ACCESS  read-only
	STATUS      current
	DESCRIPTION
	"Table entry attribute for rewriteMappingCreationFailureNoNatcfgPptp"
	::={rewriteMappingCreationFailureNoNatcfgPptpLevelEntry 2}

rewriteMappingCreationFailureNoNatcfgPptpLevelMom OBJECT-TYPE
	SYNTAX	 CounterBasedGauge64
	MAX-ACCESS  read-only
	STATUS      current
	DESCRIPTION
	"Table entry attribute for rewriteMappingCreationFailureNoNatcfgPptp"
	::={rewriteMappingCreationFailureNoNatcfgPptpLevelEntry 3}

rewriteMappingCreationFailureNoNatcfgPptpLevelMax OBJECT-TYPE
	SYNTAX	 CounterBasedGauge64
	MAX-ACCESS  read-only
	STATUS      current
	DESCRIPTION
	"Table entry attribute for rewriteMappingCreationFailureNoNatcfgPptp"
	::={rewriteMappingCreationFailureNoNatcfgPptpLevelEntry 4}


rewriteMappingCreationFailureNoNatcfgFtp	OBJECT IDENTIFIER ::={rewrite 29}

rewriteMappingCreationFailureNoNatcfgFtpVal	OBJECT-TYPE
	SYNTAX	 Counter64
	MAX-ACCESS read-only
	STATUS current
	DESCRIPTION "Mapping creation failure - No available natcfg (FTP)"

	::={rewriteMappingCreationFailureNoNatcfgFtp 1}

rewriteMappingCreationFailureNoNatcfgFtpMom	OBJECT-TYPE
	SYNTAX	 CounterBasedGauge64
	MAX-ACCESS read-only
	STATUS current
	DESCRIPTION "Mapping creation failure - No available natcfg (FTP)"

	::={rewriteMappingCreationFailureNoNatcfgFtp 2}

rewriteMappingCreationFailureNoNatcfgFtpMax	OBJECT-TYPE
	SYNTAX	 CounterBasedGauge64
	MAX-ACCESS read-only
	STATUS current
	DESCRIPTION "Mapping creation failure - No available natcfg (FTP)"

	::={rewriteMappingCreationFailureNoNatcfgFtp 3}

rewriteMappingCreationFailureNoNatcfgFtpLevelTable OBJECT-TYPE
	SYNTAX      SEQUENCE OF RewriteMappingCreationFailureNoNatcfgFtpLevelEntry
	MAX-ACCESS  not-accessible
	STATUS      current
	DESCRIPTION
	"Table for rewriteMappingCreationFailureNoNatcfgFtp"
	::={rewriteMappingCreationFailureNoNatcfgFtp 4}

rewriteMappingCreationFailureNoNatcfgFtpLevelEntry OBJECT-TYPE
	SYNTAX      RewriteMappingCreationFailureNoNatcfgFtpLevelEntry
	MAX-ACCESS  not-accessible
	STATUS      current
	DESCRIPTION
	"Table entry for rewriteMappingCreationFailureNoNatcfgFtp"
	INDEX { rewriteMappingCreationFailureNoNatcfgFtpLevelName }
	::={rewriteMappingCreationFailureNoNatcfgFtpLevelTable 1}

RewriteMappingCreationFailureNoNatcfgFtpLevelEntry ::=
	SEQUENCE {
		rewriteMappingCreationFailureNoNatcfgFtpLevelName	DisplayString,
		rewriteMappingCreationFailureNoNatcfgFtpLevelVal	Counter64,
		rewriteMappingCreationFailureNoNatcfgFtpLevelMom	CounterBasedGauge64,
		rewriteMappingCreationFailureNoNatcfgFtpLevelMax	CounterBasedGauge64
	}

rewriteMappingCreationFailureNoNatcfgFtpLevelName OBJECT-TYPE
	SYNTAX      DisplayString
	MAX-ACCESS  not-accessible
	STATUS      current
	DESCRIPTION
	"Table entry display string for rewriteMappingCreationFailureNoNatcfgFtp"
	::={rewriteMappingCreationFailureNoNatcfgFtpLevelEntry 1}

rewriteMappingCreationFailureNoNatcfgFtpLevelVal OBJECT-TYPE
	SYNTAX	 Counter64
	MAX-ACCESS  read-only
	STATUS      current
	DESCRIPTION
	"Table entry attribute for rewriteMappingCreationFailureNoNatcfgFtp"
	::={rewriteMappingCreationFailureNoNatcfgFtpLevelEntry 2}

rewriteMappingCreationFailureNoNatcfgFtpLevelMom OBJECT-TYPE
	SYNTAX	 CounterBasedGauge64
	MAX-ACCESS  read-only
	STATUS      current
	DESCRIPTION
	"Table entry attribute for rewriteMappingCreationFailureNoNatcfgFtp"
	::={rewriteMappingCreationFailureNoNatcfgFtpLevelEntry 3}

rewriteMappingCreationFailureNoNatcfgFtpLevelMax OBJECT-TYPE
	SYNTAX	 CounterBasedGauge64
	MAX-ACCESS  read-only
	STATUS      current
	DESCRIPTION
	"Table entry attribute for rewriteMappingCreationFailureNoNatcfgFtp"
	::={rewriteMappingCreationFailureNoNatcfgFtpLevelEntry 4}


rewriteMappingCreationFailureNoNatcfgRtsp	OBJECT IDENTIFIER ::={rewrite 30}

rewriteMappingCreationFailureNoNatcfgRtspVal	OBJECT-TYPE
	SYNTAX	 Counter64
	MAX-ACCESS read-only
	STATUS current
	DESCRIPTION "Mapping creation failure - No available natcfg (RTSP)"

	::={rewriteMappingCreationFailureNoNatcfgRtsp 1}

rewriteMappingCreationFailureNoNatcfgRtspMom	OBJECT-TYPE
	SYNTAX	 CounterBasedGauge64
	MAX-ACCESS read-only
	STATUS current
	DESCRIPTION "Mapping creation failure - No available natcfg (RTSP)"

	::={rewriteMappingCreationFailureNoNatcfgRtsp 2}

rewriteMappingCreationFailureNoNatcfgRtspMax	OBJECT-TYPE
	SYNTAX	 CounterBasedGauge64
	MAX-ACCESS read-only
	STATUS current
	DESCRIPTION "Mapping creation failure - No available natcfg (RTSP)"

	::={rewriteMappingCreationFailureNoNatcfgRtsp 3}

rewriteMappingCreationFailureNoNatcfgRtspLevelTable OBJECT-TYPE
	SYNTAX      SEQUENCE OF RewriteMappingCreationFailureNoNatcfgRtspLevelEntry
	MAX-ACCESS  not-accessible
	STATUS      current
	DESCRIPTION
	"Table for rewriteMappingCreationFailureNoNatcfgRtsp"
	::={rewriteMappingCreationFailureNoNatcfgRtsp 4}

rewriteMappingCreationFailureNoNatcfgRtspLevelEntry OBJECT-TYPE
	SYNTAX      RewriteMappingCreationFailureNoNatcfgRtspLevelEntry
	MAX-ACCESS  not-accessible
	STATUS      current
	DESCRIPTION
	"Table entry for rewriteMappingCreationFailureNoNatcfgRtsp"
	INDEX { rewriteMappingCreationFailureNoNatcfgRtspLevelName }
	::={rewriteMappingCreationFailureNoNatcfgRtspLevelTable 1}

RewriteMappingCreationFailureNoNatcfgRtspLevelEntry ::=
	SEQUENCE {
		rewriteMappingCreationFailureNoNatcfgRtspLevelName	DisplayString,
		rewriteMappingCreationFailureNoNatcfgRtspLevelVal	Counter64,
		rewriteMappingCreationFailureNoNatcfgRtspLevelMom	CounterBasedGauge64,
		rewriteMappingCreationFailureNoNatcfgRtspLevelMax	CounterBasedGauge64
	}

rewriteMappingCreationFailureNoNatcfgRtspLevelName OBJECT-TYPE
	SYNTAX      DisplayString
	MAX-ACCESS  not-accessible
	STATUS      current
	DESCRIPTION
	"Table entry display string for rewriteMappingCreationFailureNoNatcfgRtsp"
	::={rewriteMappingCreationFailureNoNatcfgRtspLevelEntry 1}

rewriteMappingCreationFailureNoNatcfgRtspLevelVal OBJECT-TYPE
	SYNTAX	 Counter64
	MAX-ACCESS  read-only
	STATUS      current
	DESCRIPTION
	"Table entry attribute for rewriteMappingCreationFailureNoNatcfgRtsp"
	::={rewriteMappingCreationFailureNoNatcfgRtspLevelEntry 2}

rewriteMappingCreationFailureNoNatcfgRtspLevelMom OBJECT-TYPE
	SYNTAX	 CounterBasedGauge64
	MAX-ACCESS  read-only
	STATUS      current
	DESCRIPTION
	"Table entry attribute for rewriteMappingCreationFailureNoNatcfgRtsp"
	::={rewriteMappingCreationFailureNoNatcfgRtspLevelEntry 3}

rewriteMappingCreationFailureNoNatcfgRtspLevelMax OBJECT-TYPE
	SYNTAX	 CounterBasedGauge64
	MAX-ACCESS  read-only
	STATUS      current
	DESCRIPTION
	"Table entry attribute for rewriteMappingCreationFailureNoNatcfgRtsp"
	::={rewriteMappingCreationFailureNoNatcfgRtspLevelEntry 4}


rewriteTranslationsCreated	OBJECT IDENTIFIER ::={rewrite 31}

rewriteTranslationsCreatedVal	OBJECT-TYPE
	SYNTAX	 Counter64
	MAX-ACCESS read-only
	STATUS current
	DESCRIPTION "Translations created (total)"

	::={rewriteTranslationsCreated 1}

rewriteTranslationsCreatedMom	OBJECT-TYPE
	SYNTAX	 CounterBasedGauge64
	MAX-ACCESS read-only
	STATUS current
	DESCRIPTION "Translations created (total)"

	::={rewriteTranslationsCreated 2}

rewriteTranslationsCreatedMax	OBJECT-TYPE
	SYNTAX	 CounterBasedGauge64
	MAX-ACCESS read-only
	STATUS current
	DESCRIPTION "Translations created (total)"

	::={rewriteTranslationsCreated 3}

rewriteTranslationsCreatedLevelTable OBJECT-TYPE
	SYNTAX      SEQUENCE OF RewriteTranslationsCreatedLevelEntry
	MAX-ACCESS  not-accessible
	STATUS      current
	DESCRIPTION
	"Table for rewriteTranslationsCreated"
	::={rewriteTranslationsCreated 4}

rewriteTranslationsCreatedLevelEntry OBJECT-TYPE
	SYNTAX      RewriteTranslationsCreatedLevelEntry
	MAX-ACCESS  not-accessible
	STATUS      current
	DESCRIPTION
	"Table entry for rewriteTranslationsCreated"
	INDEX { rewriteTranslationsCreatedLevelName }
	::={rewriteTranslationsCreatedLevelTable 1}

RewriteTranslationsCreatedLevelEntry ::=
	SEQUENCE {
		rewriteTranslationsCreatedLevelName	DisplayString,
		rewriteTranslationsCreatedLevelVal	Counter64,
		rewriteTranslationsCreatedLevelMom	CounterBasedGauge64,
		rewriteTranslationsCreatedLevelMax	CounterBasedGauge64
	}

rewriteTranslationsCreatedLevelName OBJECT-TYPE
	SYNTAX      DisplayString
	MAX-ACCESS  not-accessible
	STATUS      current
	DESCRIPTION
	"Table entry display string for rewriteTranslationsCreated"
	::={rewriteTranslationsCreatedLevelEntry 1}

rewriteTranslationsCreatedLevelVal OBJECT-TYPE
	SYNTAX	 Counter64
	MAX-ACCESS  read-only
	STATUS      current
	DESCRIPTION
	"Table entry attribute for rewriteTranslationsCreated"
	::={rewriteTranslationsCreatedLevelEntry 2}

rewriteTranslationsCreatedLevelMom OBJECT-TYPE
	SYNTAX	 CounterBasedGauge64
	MAX-ACCESS  read-only
	STATUS      current
	DESCRIPTION
	"Table entry attribute for rewriteTranslationsCreated"
	::={rewriteTranslationsCreatedLevelEntry 3}

rewriteTranslationsCreatedLevelMax OBJECT-TYPE
	SYNTAX	 CounterBasedGauge64
	MAX-ACCESS  read-only
	STATUS      current
	DESCRIPTION
	"Table entry attribute for rewriteTranslationsCreated"
	::={rewriteTranslationsCreatedLevelEntry 4}


rewriteTranslationsCreatedTcp	OBJECT IDENTIFIER ::={rewrite 32}

rewriteTranslationsCreatedTcpVal	OBJECT-TYPE
	SYNTAX	 Counter64
	MAX-ACCESS read-only
	STATUS current
	DESCRIPTION "Translations created - TCP (total)"

	::={rewriteTranslationsCreatedTcp 1}

rewriteTranslationsCreatedTcpMom	OBJECT-TYPE
	SYNTAX	 CounterBasedGauge64
	MAX-ACCESS read-only
	STATUS current
	DESCRIPTION "Translations created - TCP (total)"

	::={rewriteTranslationsCreatedTcp 2}

rewriteTranslationsCreatedTcpMax	OBJECT-TYPE
	SYNTAX	 CounterBasedGauge64
	MAX-ACCESS read-only
	STATUS current
	DESCRIPTION "Translations created - TCP (total)"

	::={rewriteTranslationsCreatedTcp 3}

rewriteTranslationsCreatedTcpLevelTable OBJECT-TYPE
	SYNTAX      SEQUENCE OF RewriteTranslationsCreatedTcpLevelEntry
	MAX-ACCESS  not-accessible
	STATUS      current
	DESCRIPTION
	"Table for rewriteTranslationsCreatedTcp"
	::={rewriteTranslationsCreatedTcp 4}

rewriteTranslationsCreatedTcpLevelEntry OBJECT-TYPE
	SYNTAX      RewriteTranslationsCreatedTcpLevelEntry
	MAX-ACCESS  not-accessible
	STATUS      current
	DESCRIPTION
	"Table entry for rewriteTranslationsCreatedTcp"
	INDEX { rewriteTranslationsCreatedTcpLevelName }
	::={rewriteTranslationsCreatedTcpLevelTable 1}

RewriteTranslationsCreatedTcpLevelEntry ::=
	SEQUENCE {
		rewriteTranslationsCreatedTcpLevelName	DisplayString,
		rewriteTranslationsCreatedTcpLevelVal	Counter64,
		rewriteTranslationsCreatedTcpLevelMom	CounterBasedGauge64,
		rewriteTranslationsCreatedTcpLevelMax	CounterBasedGauge64
	}

rewriteTranslationsCreatedTcpLevelName OBJECT-TYPE
	SYNTAX      DisplayString
	MAX-ACCESS  not-accessible
	STATUS      current
	DESCRIPTION
	"Table entry display string for rewriteTranslationsCreatedTcp"
	::={rewriteTranslationsCreatedTcpLevelEntry 1}

rewriteTranslationsCreatedTcpLevelVal OBJECT-TYPE
	SYNTAX	 Counter64
	MAX-ACCESS  read-only
	STATUS      current
	DESCRIPTION
	"Table entry attribute for rewriteTranslationsCreatedTcp"
	::={rewriteTranslationsCreatedTcpLevelEntry 2}

rewriteTranslationsCreatedTcpLevelMom OBJECT-TYPE
	SYNTAX	 CounterBasedGauge64
	MAX-ACCESS  read-only
	STATUS      current
	DESCRIPTION
	"Table entry attribute for rewriteTranslationsCreatedTcp"
	::={rewriteTranslationsCreatedTcpLevelEntry 3}

rewriteTranslationsCreatedTcpLevelMax OBJECT-TYPE
	SYNTAX	 CounterBasedGauge64
	MAX-ACCESS  read-only
	STATUS      current
	DESCRIPTION
	"Table entry attribute for rewriteTranslationsCreatedTcp"
	::={rewriteTranslationsCreatedTcpLevelEntry 4}


rewriteTranslationsCreatedUdp	OBJECT IDENTIFIER ::={rewrite 33}

rewriteTranslationsCreatedUdpVal	OBJECT-TYPE
	SYNTAX	 Counter64
	MAX-ACCESS read-only
	STATUS current
	DESCRIPTION "Translations created - UDP (total)"

	::={rewriteTranslationsCreatedUdp 1}

rewriteTranslationsCreatedUdpMom	OBJECT-TYPE
	SYNTAX	 CounterBasedGauge64
	MAX-ACCESS read-only
	STATUS current
	DESCRIPTION "Translations created - UDP (total)"

	::={rewriteTranslationsCreatedUdp 2}

rewriteTranslationsCreatedUdpMax	OBJECT-TYPE
	SYNTAX	 CounterBasedGauge64
	MAX-ACCESS read-only
	STATUS current
	DESCRIPTION "Translations created - UDP (total)"

	::={rewriteTranslationsCreatedUdp 3}

rewriteTranslationsCreatedUdpLevelTable OBJECT-TYPE
	SYNTAX      SEQUENCE OF RewriteTranslationsCreatedUdpLevelEntry
	MAX-ACCESS  not-accessible
	STATUS      current
	DESCRIPTION
	"Table for rewriteTranslationsCreatedUdp"
	::={rewriteTranslationsCreatedUdp 4}

rewriteTranslationsCreatedUdpLevelEntry OBJECT-TYPE
	SYNTAX      RewriteTranslationsCreatedUdpLevelEntry
	MAX-ACCESS  not-accessible
	STATUS      current
	DESCRIPTION
	"Table entry for rewriteTranslationsCreatedUdp"
	INDEX { rewriteTranslationsCreatedUdpLevelName }
	::={rewriteTranslationsCreatedUdpLevelTable 1}

RewriteTranslationsCreatedUdpLevelEntry ::=
	SEQUENCE {
		rewriteTranslationsCreatedUdpLevelName	DisplayString,
		rewriteTranslationsCreatedUdpLevelVal	Counter64,
		rewriteTranslationsCreatedUdpLevelMom	CounterBasedGauge64,
		rewriteTranslationsCreatedUdpLevelMax	CounterBasedGauge64
	}

rewriteTranslationsCreatedUdpLevelName OBJECT-TYPE
	SYNTAX      DisplayString
	MAX-ACCESS  not-accessible
	STATUS      current
	DESCRIPTION
	"Table entry display string for rewriteTranslationsCreatedUdp"
	::={rewriteTranslationsCreatedUdpLevelEntry 1}

rewriteTranslationsCreatedUdpLevelVal OBJECT-TYPE
	SYNTAX	 Counter64
	MAX-ACCESS  read-only
	STATUS      current
	DESCRIPTION
	"Table entry attribute for rewriteTranslationsCreatedUdp"
	::={rewriteTranslationsCreatedUdpLevelEntry 2}

rewriteTranslationsCreatedUdpLevelMom OBJECT-TYPE
	SYNTAX	 CounterBasedGauge64
	MAX-ACCESS  read-only
	STATUS      current
	DESCRIPTION
	"Table entry attribute for rewriteTranslationsCreatedUdp"
	::={rewriteTranslationsCreatedUdpLevelEntry 3}

rewriteTranslationsCreatedUdpLevelMax OBJECT-TYPE
	SYNTAX	 CounterBasedGauge64
	MAX-ACCESS  read-only
	STATUS      current
	DESCRIPTION
	"Table entry attribute for rewriteTranslationsCreatedUdp"
	::={rewriteTranslationsCreatedUdpLevelEntry 4}


rewriteTranslationsCreatedIcmp	OBJECT IDENTIFIER ::={rewrite 34}

rewriteTranslationsCreatedIcmpVal	OBJECT-TYPE
	SYNTAX	 Counter64
	MAX-ACCESS read-only
	STATUS current
	DESCRIPTION "Translations created - ICMP (total)"

	::={rewriteTranslationsCreatedIcmp 1}

rewriteTranslationsCreatedIcmpMom	OBJECT-TYPE
	SYNTAX	 CounterBasedGauge64
	MAX-ACCESS read-only
	STATUS current
	DESCRIPTION "Translations created - ICMP (total)"

	::={rewriteTranslationsCreatedIcmp 2}

rewriteTranslationsCreatedIcmpMax	OBJECT-TYPE
	SYNTAX	 CounterBasedGauge64
	MAX-ACCESS read-only
	STATUS current
	DESCRIPTION "Translations created - ICMP (total)"

	::={rewriteTranslationsCreatedIcmp 3}

rewriteTranslationsCreatedIcmpLevelTable OBJECT-TYPE
	SYNTAX      SEQUENCE OF RewriteTranslationsCreatedIcmpLevelEntry
	MAX-ACCESS  not-accessible
	STATUS      current
	DESCRIPTION
	"Table for rewriteTranslationsCreatedIcmp"
	::={rewriteTranslationsCreatedIcmp 4}

rewriteTranslationsCreatedIcmpLevelEntry OBJECT-TYPE
	SYNTAX      RewriteTranslationsCreatedIcmpLevelEntry
	MAX-ACCESS  not-accessible
	STATUS      current
	DESCRIPTION
	"Table entry for rewriteTranslationsCreatedIcmp"
	INDEX { rewriteTranslationsCreatedIcmpLevelName }
	::={rewriteTranslationsCreatedIcmpLevelTable 1}

RewriteTranslationsCreatedIcmpLevelEntry ::=
	SEQUENCE {
		rewriteTranslationsCreatedIcmpLevelName	DisplayString,
		rewriteTranslationsCreatedIcmpLevelVal	Counter64,
		rewriteTranslationsCreatedIcmpLevelMom	CounterBasedGauge64,
		rewriteTranslationsCreatedIcmpLevelMax	CounterBasedGauge64
	}

rewriteTranslationsCreatedIcmpLevelName OBJECT-TYPE
	SYNTAX      DisplayString
	MAX-ACCESS  not-accessible
	STATUS      current
	DESCRIPTION
	"Table entry display string for rewriteTranslationsCreatedIcmp"
	::={rewriteTranslationsCreatedIcmpLevelEntry 1}

rewriteTranslationsCreatedIcmpLevelVal OBJECT-TYPE
	SYNTAX	 Counter64
	MAX-ACCESS  read-only
	STATUS      current
	DESCRIPTION
	"Table entry attribute for rewriteTranslationsCreatedIcmp"
	::={rewriteTranslationsCreatedIcmpLevelEntry 2}

rewriteTranslationsCreatedIcmpLevelMom OBJECT-TYPE
	SYNTAX	 CounterBasedGauge64
	MAX-ACCESS  read-only
	STATUS      current
	DESCRIPTION
	"Table entry attribute for rewriteTranslationsCreatedIcmp"
	::={rewriteTranslationsCreatedIcmpLevelEntry 3}

rewriteTranslationsCreatedIcmpLevelMax OBJECT-TYPE
	SYNTAX	 CounterBasedGauge64
	MAX-ACCESS  read-only
	STATUS      current
	DESCRIPTION
	"Table entry attribute for rewriteTranslationsCreatedIcmp"
	::={rewriteTranslationsCreatedIcmpLevelEntry 4}


rewriteTranslationsDeleted	OBJECT IDENTIFIER ::={rewrite 35}

rewriteTranslationsDeletedVal	OBJECT-TYPE
	SYNTAX	 Counter64
	MAX-ACCESS read-only
	STATUS current
	DESCRIPTION "Translations deleted (total)"

	::={rewriteTranslationsDeleted 1}

rewriteTranslationsDeletedMom	OBJECT-TYPE
	SYNTAX	 CounterBasedGauge64
	MAX-ACCESS read-only
	STATUS current
	DESCRIPTION "Translations deleted (total)"

	::={rewriteTranslationsDeleted 2}

rewriteTranslationsDeletedMax	OBJECT-TYPE
	SYNTAX	 CounterBasedGauge64
	MAX-ACCESS read-only
	STATUS current
	DESCRIPTION "Translations deleted (total)"

	::={rewriteTranslationsDeleted 3}

rewriteTranslationsDeletedLevelTable OBJECT-TYPE
	SYNTAX      SEQUENCE OF RewriteTranslationsDeletedLevelEntry
	MAX-ACCESS  not-accessible
	STATUS      current
	DESCRIPTION
	"Table for rewriteTranslationsDeleted"
	::={rewriteTranslationsDeleted 4}

rewriteTranslationsDeletedLevelEntry OBJECT-TYPE
	SYNTAX      RewriteTranslationsDeletedLevelEntry
	MAX-ACCESS  not-accessible
	STATUS      current
	DESCRIPTION
	"Table entry for rewriteTranslationsDeleted"
	INDEX { rewriteTranslationsDeletedLevelName }
	::={rewriteTranslationsDeletedLevelTable 1}

RewriteTranslationsDeletedLevelEntry ::=
	SEQUENCE {
		rewriteTranslationsDeletedLevelName	DisplayString,
		rewriteTranslationsDeletedLevelVal	Counter64,
		rewriteTranslationsDeletedLevelMom	CounterBasedGauge64,
		rewriteTranslationsDeletedLevelMax	CounterBasedGauge64
	}

rewriteTranslationsDeletedLevelName OBJECT-TYPE
	SYNTAX      DisplayString
	MAX-ACCESS  not-accessible
	STATUS      current
	DESCRIPTION
	"Table entry display string for rewriteTranslationsDeleted"
	::={rewriteTranslationsDeletedLevelEntry 1}

rewriteTranslationsDeletedLevelVal OBJECT-TYPE
	SYNTAX	 Counter64
	MAX-ACCESS  read-only
	STATUS      current
	DESCRIPTION
	"Table entry attribute for rewriteTranslationsDeleted"
	::={rewriteTranslationsDeletedLevelEntry 2}

rewriteTranslationsDeletedLevelMom OBJECT-TYPE
	SYNTAX	 CounterBasedGauge64
	MAX-ACCESS  read-only
	STATUS      current
	DESCRIPTION
	"Table entry attribute for rewriteTranslationsDeleted"
	::={rewriteTranslationsDeletedLevelEntry 3}

rewriteTranslationsDeletedLevelMax OBJECT-TYPE
	SYNTAX	 CounterBasedGauge64
	MAX-ACCESS  read-only
	STATUS      current
	DESCRIPTION
	"Table entry attribute for rewriteTranslationsDeleted"
	::={rewriteTranslationsDeletedLevelEntry 4}


rewriteTranslationsCount	OBJECT IDENTIFIER ::={rewrite 36}

rewriteTranslationsCountVal	OBJECT-TYPE
	SYNTAX	 CounterBasedGauge64
	MAX-ACCESS read-only
	STATUS current
	DESCRIPTION "Translations count (total)"

	::={rewriteTranslationsCount 1}

rewriteTranslationsCountMax	OBJECT-TYPE
	SYNTAX	 CounterBasedGauge64
	MAX-ACCESS read-only
	STATUS current
	DESCRIPTION "Translations count (total)"

	::={rewriteTranslationsCount 3}

rewriteTranslationsCountLevelTable OBJECT-TYPE
	SYNTAX      SEQUENCE OF RewriteTranslationsCountLevelEntry
	MAX-ACCESS  not-accessible
	STATUS      current
	DESCRIPTION
	"Table for rewriteTranslationsCount"
	::={rewriteTranslationsCount 4}

rewriteTranslationsCountLevelEntry OBJECT-TYPE
	SYNTAX      RewriteTranslationsCountLevelEntry
	MAX-ACCESS  not-accessible
	STATUS      current
	DESCRIPTION
	"Table entry for rewriteTranslationsCount"
	INDEX { rewriteTranslationsCountLevelName }
	::={rewriteTranslationsCountLevelTable 1}

RewriteTranslationsCountLevelEntry ::=
	SEQUENCE {
		rewriteTranslationsCountLevelName	DisplayString,
		rewriteTranslationsCountLevelVal	CounterBasedGauge64,
		rewriteTranslationsCountLevelMax	CounterBasedGauge64
	}

rewriteTranslationsCountLevelName OBJECT-TYPE
	SYNTAX      DisplayString
	MAX-ACCESS  not-accessible
	STATUS      current
	DESCRIPTION
	"Table entry display string for rewriteTranslationsCount"
	::={rewriteTranslationsCountLevelEntry 1}

rewriteTranslationsCountLevelVal OBJECT-TYPE
	SYNTAX	 CounterBasedGauge64
	MAX-ACCESS  read-only
	STATUS      current
	DESCRIPTION
	"Table entry attribute for rewriteTranslationsCount"
	::={rewriteTranslationsCountLevelEntry 2}

rewriteTranslationsCountLevelMax OBJECT-TYPE
	SYNTAX	 CounterBasedGauge64
	MAX-ACCESS  read-only
	STATUS      current
	DESCRIPTION
	"Table entry attribute for rewriteTranslationsCount"
	::={rewriteTranslationsCountLevelEntry 4}


rewriteTranslationsCountTcp	OBJECT IDENTIFIER ::={rewrite 37}

rewriteTranslationsCountTcpVal	OBJECT-TYPE
	SYNTAX	 CounterBasedGauge64
	MAX-ACCESS read-only
	STATUS current
	DESCRIPTION "Translations count - TCP (total)"

	::={rewriteTranslationsCountTcp 1}

rewriteTranslationsCountTcpMax	OBJECT-TYPE
	SYNTAX	 CounterBasedGauge64
	MAX-ACCESS read-only
	STATUS current
	DESCRIPTION "Translations count - TCP (total)"

	::={rewriteTranslationsCountTcp 3}

rewriteTranslationsCountTcpLevelTable OBJECT-TYPE
	SYNTAX      SEQUENCE OF RewriteTranslationsCountTcpLevelEntry
	MAX-ACCESS  not-accessible
	STATUS      current
	DESCRIPTION
	"Table for rewriteTranslationsCountTcp"
	::={rewriteTranslationsCountTcp 4}

rewriteTranslationsCountTcpLevelEntry OBJECT-TYPE
	SYNTAX      RewriteTranslationsCountTcpLevelEntry
	MAX-ACCESS  not-accessible
	STATUS      current
	DESCRIPTION
	"Table entry for rewriteTranslationsCountTcp"
	INDEX { rewriteTranslationsCountTcpLevelName }
	::={rewriteTranslationsCountTcpLevelTable 1}

RewriteTranslationsCountTcpLevelEntry ::=
	SEQUENCE {
		rewriteTranslationsCountTcpLevelName	DisplayString,
		rewriteTranslationsCountTcpLevelVal	CounterBasedGauge64,
		rewriteTranslationsCountTcpLevelMax	CounterBasedGauge64
	}

rewriteTranslationsCountTcpLevelName OBJECT-TYPE
	SYNTAX      DisplayString
	MAX-ACCESS  not-accessible
	STATUS      current
	DESCRIPTION
	"Table entry display string for rewriteTranslationsCountTcp"
	::={rewriteTranslationsCountTcpLevelEntry 1}

rewriteTranslationsCountTcpLevelVal OBJECT-TYPE
	SYNTAX	 CounterBasedGauge64
	MAX-ACCESS  read-only
	STATUS      current
	DESCRIPTION
	"Table entry attribute for rewriteTranslationsCountTcp"
	::={rewriteTranslationsCountTcpLevelEntry 2}

rewriteTranslationsCountTcpLevelMax OBJECT-TYPE
	SYNTAX	 CounterBasedGauge64
	MAX-ACCESS  read-only
	STATUS      current
	DESCRIPTION
	"Table entry attribute for rewriteTranslationsCountTcp"
	::={rewriteTranslationsCountTcpLevelEntry 4}


rewriteTranslationsCountUdp	OBJECT IDENTIFIER ::={rewrite 38}

rewriteTranslationsCountUdpVal	OBJECT-TYPE
	SYNTAX	 CounterBasedGauge64
	MAX-ACCESS read-only
	STATUS current
	DESCRIPTION "Translations count - UDP (total)"

	::={rewriteTranslationsCountUdp 1}

rewriteTranslationsCountUdpMax	OBJECT-TYPE
	SYNTAX	 CounterBasedGauge64
	MAX-ACCESS read-only
	STATUS current
	DESCRIPTION "Translations count - UDP (total)"

	::={rewriteTranslationsCountUdp 3}

rewriteTranslationsCountUdpLevelTable OBJECT-TYPE
	SYNTAX      SEQUENCE OF RewriteTranslationsCountUdpLevelEntry
	MAX-ACCESS  not-accessible
	STATUS      current
	DESCRIPTION
	"Table for rewriteTranslationsCountUdp"
	::={rewriteTranslationsCountUdp 4}

rewriteTranslationsCountUdpLevelEntry OBJECT-TYPE
	SYNTAX      RewriteTranslationsCountUdpLevelEntry
	MAX-ACCESS  not-accessible
	STATUS      current
	DESCRIPTION
	"Table entry for rewriteTranslationsCountUdp"
	INDEX { rewriteTranslationsCountUdpLevelName }
	::={rewriteTranslationsCountUdpLevelTable 1}

RewriteTranslationsCountUdpLevelEntry ::=
	SEQUENCE {
		rewriteTranslationsCountUdpLevelName	DisplayString,
		rewriteTranslationsCountUdpLevelVal	CounterBasedGauge64,
		rewriteTranslationsCountUdpLevelMax	CounterBasedGauge64
	}

rewriteTranslationsCountUdpLevelName OBJECT-TYPE
	SYNTAX      DisplayString
	MAX-ACCESS  not-accessible
	STATUS      current
	DESCRIPTION
	"Table entry display string for rewriteTranslationsCountUdp"
	::={rewriteTranslationsCountUdpLevelEntry 1}

rewriteTranslationsCountUdpLevelVal OBJECT-TYPE
	SYNTAX	 CounterBasedGauge64
	MAX-ACCESS  read-only
	STATUS      current
	DESCRIPTION
	"Table entry attribute for rewriteTranslationsCountUdp"
	::={rewriteTranslationsCountUdpLevelEntry 2}

rewriteTranslationsCountUdpLevelMax OBJECT-TYPE
	SYNTAX	 CounterBasedGauge64
	MAX-ACCESS  read-only
	STATUS      current
	DESCRIPTION
	"Table entry attribute for rewriteTranslationsCountUdp"
	::={rewriteTranslationsCountUdpLevelEntry 4}


rewriteTranslationsCountIcmp	OBJECT IDENTIFIER ::={rewrite 39}

rewriteTranslationsCountIcmpVal	OBJECT-TYPE
	SYNTAX	 CounterBasedGauge64
	MAX-ACCESS read-only
	STATUS current
	DESCRIPTION "Translations count - ICMP (total)"

	::={rewriteTranslationsCountIcmp 1}

rewriteTranslationsCountIcmpMax	OBJECT-TYPE
	SYNTAX	 CounterBasedGauge64
	MAX-ACCESS read-only
	STATUS current
	DESCRIPTION "Translations count - ICMP (total)"

	::={rewriteTranslationsCountIcmp 3}

rewriteTranslationsCountIcmpLevelTable OBJECT-TYPE
	SYNTAX      SEQUENCE OF RewriteTranslationsCountIcmpLevelEntry
	MAX-ACCESS  not-accessible
	STATUS      current
	DESCRIPTION
	"Table for rewriteTranslationsCountIcmp"
	::={rewriteTranslationsCountIcmp 4}

rewriteTranslationsCountIcmpLevelEntry OBJECT-TYPE
	SYNTAX      RewriteTranslationsCountIcmpLevelEntry
	MAX-ACCESS  not-accessible
	STATUS      current
	DESCRIPTION
	"Table entry for rewriteTranslationsCountIcmp"
	INDEX { rewriteTranslationsCountIcmpLevelName }
	::={rewriteTranslationsCountIcmpLevelTable 1}

RewriteTranslationsCountIcmpLevelEntry ::=
	SEQUENCE {
		rewriteTranslationsCountIcmpLevelName	DisplayString,
		rewriteTranslationsCountIcmpLevelVal	CounterBasedGauge64,
		rewriteTranslationsCountIcmpLevelMax	CounterBasedGauge64
	}

rewriteTranslationsCountIcmpLevelName OBJECT-TYPE
	SYNTAX      DisplayString
	MAX-ACCESS  not-accessible
	STATUS      current
	DESCRIPTION
	"Table entry display string for rewriteTranslationsCountIcmp"
	::={rewriteTranslationsCountIcmpLevelEntry 1}

rewriteTranslationsCountIcmpLevelVal OBJECT-TYPE
	SYNTAX	 CounterBasedGauge64
	MAX-ACCESS  read-only
	STATUS      current
	DESCRIPTION
	"Table entry attribute for rewriteTranslationsCountIcmp"
	::={rewriteTranslationsCountIcmpLevelEntry 2}

rewriteTranslationsCountIcmpLevelMax OBJECT-TYPE
	SYNTAX	 CounterBasedGauge64
	MAX-ACCESS  read-only
	STATUS      current
	DESCRIPTION
	"Table entry attribute for rewriteTranslationsCountIcmp"
	::={rewriteTranslationsCountIcmpLevelEntry 4}


rewriteTranslationCreationFailureNoObject	OBJECT IDENTIFIER ::={rewrite 40}

rewriteTranslationCreationFailureNoObjectVal	OBJECT-TYPE
	SYNTAX	 Counter64
	MAX-ACCESS read-only
	STATUS current
	DESCRIPTION "Translation creation failure (no object, total)"

	::={rewriteTranslationCreationFailureNoObject 1}

rewriteTranslationCreationFailureNoObjectMom	OBJECT-TYPE
	SYNTAX	 CounterBasedGauge64
	MAX-ACCESS read-only
	STATUS current
	DESCRIPTION "Translation creation failure (no object, total)"

	::={rewriteTranslationCreationFailureNoObject 2}

rewriteTranslationCreationFailureNoObjectMax	OBJECT-TYPE
	SYNTAX	 CounterBasedGauge64
	MAX-ACCESS read-only
	STATUS current
	DESCRIPTION "Translation creation failure (no object, total)"

	::={rewriteTranslationCreationFailureNoObject 3}

rewriteTranslationCreationFailureNoObjectLevelTable OBJECT-TYPE
	SYNTAX      SEQUENCE OF RewriteTranslationCreationFailureNoObjectLevelEntry
	MAX-ACCESS  not-accessible
	STATUS      current
	DESCRIPTION
	"Table for rewriteTranslationCreationFailureNoObject"
	::={rewriteTranslationCreationFailureNoObject 4}

rewriteTranslationCreationFailureNoObjectLevelEntry OBJECT-TYPE
	SYNTAX      RewriteTranslationCreationFailureNoObjectLevelEntry
	MAX-ACCESS  not-accessible
	STATUS      current
	DESCRIPTION
	"Table entry for rewriteTranslationCreationFailureNoObject"
	INDEX { rewriteTranslationCreationFailureNoObjectLevelName }
	::={rewriteTranslationCreationFailureNoObjectLevelTable 1}

RewriteTranslationCreationFailureNoObjectLevelEntry ::=
	SEQUENCE {
		rewriteTranslationCreationFailureNoObjectLevelName	DisplayString,
		rewriteTranslationCreationFailureNoObjectLevelVal	Counter64,
		rewriteTranslationCreationFailureNoObjectLevelMom	CounterBasedGauge64,
		rewriteTranslationCreationFailureNoObjectLevelMax	CounterBasedGauge64
	}

rewriteTranslationCreationFailureNoObjectLevelName OBJECT-TYPE
	SYNTAX      DisplayString
	MAX-ACCESS  not-accessible
	STATUS      current
	DESCRIPTION
	"Table entry display string for rewriteTranslationCreationFailureNoObject"
	::={rewriteTranslationCreationFailureNoObjectLevelEntry 1}

rewriteTranslationCreationFailureNoObjectLevelVal OBJECT-TYPE
	SYNTAX	 Counter64
	MAX-ACCESS  read-only
	STATUS      current
	DESCRIPTION
	"Table entry attribute for rewriteTranslationCreationFailureNoObject"
	::={rewriteTranslationCreationFailureNoObjectLevelEntry 2}

rewriteTranslationCreationFailureNoObjectLevelMom OBJECT-TYPE
	SYNTAX	 CounterBasedGauge64
	MAX-ACCESS  read-only
	STATUS      current
	DESCRIPTION
	"Table entry attribute for rewriteTranslationCreationFailureNoObject"
	::={rewriteTranslationCreationFailureNoObjectLevelEntry 3}

rewriteTranslationCreationFailureNoObjectLevelMax OBJECT-TYPE
	SYNTAX	 CounterBasedGauge64
	MAX-ACCESS  read-only
	STATUS      current
	DESCRIPTION
	"Table entry attribute for rewriteTranslationCreationFailureNoObject"
	::={rewriteTranslationCreationFailureNoObjectLevelEntry 4}


rewriteTranslationCreationFailureResources	OBJECT IDENTIFIER ::={rewrite 41}

rewriteTranslationCreationFailureResourcesVal	OBJECT-TYPE
	SYNTAX	 Counter64
	MAX-ACCESS read-only
	STATUS current
	DESCRIPTION "Translation creation failure (resources, total)"

	::={rewriteTranslationCreationFailureResources 1}

rewriteTranslationCreationFailureResourcesMom	OBJECT-TYPE
	SYNTAX	 CounterBasedGauge64
	MAX-ACCESS read-only
	STATUS current
	DESCRIPTION "Translation creation failure (resources, total)"

	::={rewriteTranslationCreationFailureResources 2}

rewriteTranslationCreationFailureResourcesMax	OBJECT-TYPE
	SYNTAX	 CounterBasedGauge64
	MAX-ACCESS read-only
	STATUS current
	DESCRIPTION "Translation creation failure (resources, total)"

	::={rewriteTranslationCreationFailureResources 3}

rewriteTranslationCreationFailureResourcesLevelTable OBJECT-TYPE
	SYNTAX      SEQUENCE OF RewriteTranslationCreationFailureResourcesLevelEntry
	MAX-ACCESS  not-accessible
	STATUS      current
	DESCRIPTION
	"Table for rewriteTranslationCreationFailureResources"
	::={rewriteTranslationCreationFailureResources 4}

rewriteTranslationCreationFailureResourcesLevelEntry OBJECT-TYPE
	SYNTAX      RewriteTranslationCreationFailureResourcesLevelEntry
	MAX-ACCESS  not-accessible
	STATUS      current
	DESCRIPTION
	"Table entry for rewriteTranslationCreationFailureResources"
	INDEX { rewriteTranslationCreationFailureResourcesLevelName }
	::={rewriteTranslationCreationFailureResourcesLevelTable 1}

RewriteTranslationCreationFailureResourcesLevelEntry ::=
	SEQUENCE {
		rewriteTranslationCreationFailureResourcesLevelName	DisplayString,
		rewriteTranslationCreationFailureResourcesLevelVal	Counter64,
		rewriteTranslationCreationFailureResourcesLevelMom	CounterBasedGauge64,
		rewriteTranslationCreationFailureResourcesLevelMax	CounterBasedGauge64
	}

rewriteTranslationCreationFailureResourcesLevelName OBJECT-TYPE
	SYNTAX      DisplayString
	MAX-ACCESS  not-accessible
	STATUS      current
	DESCRIPTION
	"Table entry display string for rewriteTranslationCreationFailureResources"
	::={rewriteTranslationCreationFailureResourcesLevelEntry 1}

rewriteTranslationCreationFailureResourcesLevelVal OBJECT-TYPE
	SYNTAX	 Counter64
	MAX-ACCESS  read-only
	STATUS      current
	DESCRIPTION
	"Table entry attribute for rewriteTranslationCreationFailureResources"
	::={rewriteTranslationCreationFailureResourcesLevelEntry 2}

rewriteTranslationCreationFailureResourcesLevelMom OBJECT-TYPE
	SYNTAX	 CounterBasedGauge64
	MAX-ACCESS  read-only
	STATUS      current
	DESCRIPTION
	"Table entry attribute for rewriteTranslationCreationFailureResources"
	::={rewriteTranslationCreationFailureResourcesLevelEntry 3}

rewriteTranslationCreationFailureResourcesLevelMax OBJECT-TYPE
	SYNTAX	 CounterBasedGauge64
	MAX-ACCESS  read-only
	STATUS      current
	DESCRIPTION
	"Table entry attribute for rewriteTranslationCreationFailureResources"
	::={rewriteTranslationCreationFailureResourcesLevelEntry 4}


rewriteTranslationCreationFailureProtocol	OBJECT IDENTIFIER ::={rewrite 42}

rewriteTranslationCreationFailureProtocolVal	OBJECT-TYPE
	SYNTAX	 Counter64
	MAX-ACCESS read-only
	STATUS current
	DESCRIPTION "Translation creation failure (incompatible L4 protocol, total)"

	::={rewriteTranslationCreationFailureProtocol 1}

rewriteTranslationCreationFailureProtocolMom	OBJECT-TYPE
	SYNTAX	 CounterBasedGauge64
	MAX-ACCESS read-only
	STATUS current
	DESCRIPTION "Translation creation failure (incompatible L4 protocol, total)"

	::={rewriteTranslationCreationFailureProtocol 2}

rewriteTranslationCreationFailureProtocolMax	OBJECT-TYPE
	SYNTAX	 CounterBasedGauge64
	MAX-ACCESS read-only
	STATUS current
	DESCRIPTION "Translation creation failure (incompatible L4 protocol, total)"

	::={rewriteTranslationCreationFailureProtocol 3}

rewriteTranslationCreationFailureProtocolLevelTable OBJECT-TYPE
	SYNTAX      SEQUENCE OF RewriteTranslationCreationFailureProtocolLevelEntry
	MAX-ACCESS  not-accessible
	STATUS      current
	DESCRIPTION
	"Table for rewriteTranslationCreationFailureProtocol"
	::={rewriteTranslationCreationFailureProtocol 4}

rewriteTranslationCreationFailureProtocolLevelEntry OBJECT-TYPE
	SYNTAX      RewriteTranslationCreationFailureProtocolLevelEntry
	MAX-ACCESS  not-accessible
	STATUS      current
	DESCRIPTION
	"Table entry for rewriteTranslationCreationFailureProtocol"
	INDEX { rewriteTranslationCreationFailureProtocolLevelName }
	::={rewriteTranslationCreationFailureProtocolLevelTable 1}

RewriteTranslationCreationFailureProtocolLevelEntry ::=
	SEQUENCE {
		rewriteTranslationCreationFailureProtocolLevelName	DisplayString,
		rewriteTranslationCreationFailureProtocolLevelVal	Counter64,
		rewriteTranslationCreationFailureProtocolLevelMom	CounterBasedGauge64,
		rewriteTranslationCreationFailureProtocolLevelMax	CounterBasedGauge64
	}

rewriteTranslationCreationFailureProtocolLevelName OBJECT-TYPE
	SYNTAX      DisplayString
	MAX-ACCESS  not-accessible
	STATUS      current
	DESCRIPTION
	"Table entry display string for rewriteTranslationCreationFailureProtocol"
	::={rewriteTranslationCreationFailureProtocolLevelEntry 1}

rewriteTranslationCreationFailureProtocolLevelVal OBJECT-TYPE
	SYNTAX	 Counter64
	MAX-ACCESS  read-only
	STATUS      current
	DESCRIPTION
	"Table entry attribute for rewriteTranslationCreationFailureProtocol"
	::={rewriteTranslationCreationFailureProtocolLevelEntry 2}

rewriteTranslationCreationFailureProtocolLevelMom OBJECT-TYPE
	SYNTAX	 CounterBasedGauge64
	MAX-ACCESS  read-only
	STATUS      current
	DESCRIPTION
	"Table entry attribute for rewriteTranslationCreationFailureProtocol"
	::={rewriteTranslationCreationFailureProtocolLevelEntry 3}

rewriteTranslationCreationFailureProtocolLevelMax OBJECT-TYPE
	SYNTAX	 CounterBasedGauge64
	MAX-ACCESS  read-only
	STATUS      current
	DESCRIPTION
	"Table entry attribute for rewriteTranslationCreationFailureProtocol"
	::={rewriteTranslationCreationFailureProtocolLevelEntry 4}


rewriteTranslationCreationFailureCollision	OBJECT IDENTIFIER ::={rewrite 43}

rewriteTranslationCreationFailureCollisionVal	OBJECT-TYPE
	SYNTAX	 Counter64
	MAX-ACCESS read-only
	STATUS current
	DESCRIPTION "Translation creation failure (collision, total)"

	::={rewriteTranslationCreationFailureCollision 1}

rewriteTranslationCreationFailureCollisionMom	OBJECT-TYPE
	SYNTAX	 CounterBasedGauge64
	MAX-ACCESS read-only
	STATUS current
	DESCRIPTION "Translation creation failure (collision, total)"

	::={rewriteTranslationCreationFailureCollision 2}

rewriteTranslationCreationFailureCollisionMax	OBJECT-TYPE
	SYNTAX	 CounterBasedGauge64
	MAX-ACCESS read-only
	STATUS current
	DESCRIPTION "Translation creation failure (collision, total)"

	::={rewriteTranslationCreationFailureCollision 3}

rewriteTranslationCreationFailureCollisionLevelTable OBJECT-TYPE
	SYNTAX      SEQUENCE OF RewriteTranslationCreationFailureCollisionLevelEntry
	MAX-ACCESS  not-accessible
	STATUS      current
	DESCRIPTION
	"Table for rewriteTranslationCreationFailureCollision"
	::={rewriteTranslationCreationFailureCollision 4}

rewriteTranslationCreationFailureCollisionLevelEntry OBJECT-TYPE
	SYNTAX      RewriteTranslationCreationFailureCollisionLevelEntry
	MAX-ACCESS  not-accessible
	STATUS      current
	DESCRIPTION
	"Table entry for rewriteTranslationCreationFailureCollision"
	INDEX { rewriteTranslationCreationFailureCollisionLevelName }
	::={rewriteTranslationCreationFailureCollisionLevelTable 1}

RewriteTranslationCreationFailureCollisionLevelEntry ::=
	SEQUENCE {
		rewriteTranslationCreationFailureCollisionLevelName	DisplayString,
		rewriteTranslationCreationFailureCollisionLevelVal	Counter64,
		rewriteTranslationCreationFailureCollisionLevelMom	CounterBasedGauge64,
		rewriteTranslationCreationFailureCollisionLevelMax	CounterBasedGauge64
	}

rewriteTranslationCreationFailureCollisionLevelName OBJECT-TYPE
	SYNTAX      DisplayString
	MAX-ACCESS  not-accessible
	STATUS      current
	DESCRIPTION
	"Table entry display string for rewriteTranslationCreationFailureCollision"
	::={rewriteTranslationCreationFailureCollisionLevelEntry 1}

rewriteTranslationCreationFailureCollisionLevelVal OBJECT-TYPE
	SYNTAX	 Counter64
	MAX-ACCESS  read-only
	STATUS      current
	DESCRIPTION
	"Table entry attribute for rewriteTranslationCreationFailureCollision"
	::={rewriteTranslationCreationFailureCollisionLevelEntry 2}

rewriteTranslationCreationFailureCollisionLevelMom OBJECT-TYPE
	SYNTAX	 CounterBasedGauge64
	MAX-ACCESS  read-only
	STATUS      current
	DESCRIPTION
	"Table entry attribute for rewriteTranslationCreationFailureCollision"
	::={rewriteTranslationCreationFailureCollisionLevelEntry 3}

rewriteTranslationCreationFailureCollisionLevelMax OBJECT-TYPE
	SYNTAX	 CounterBasedGauge64
	MAX-ACCESS  read-only
	STATUS      current
	DESCRIPTION
	"Table entry attribute for rewriteTranslationCreationFailureCollision"
	::={rewriteTranslationCreationFailureCollisionLevelEntry 4}


rewriteTranslationCreationCollisionResolutions	OBJECT IDENTIFIER ::={rewrite 44}

rewriteTranslationCreationCollisionResolutionsVal	OBJECT-TYPE
	SYNTAX	 Counter64
	MAX-ACCESS read-only
	STATUS current
	DESCRIPTION "Translation creation collisions resolved (total)"

	::={rewriteTranslationCreationCollisionResolutions 1}

rewriteTranslationCreationCollisionResolutionsMom	OBJECT-TYPE
	SYNTAX	 CounterBasedGauge64
	MAX-ACCESS read-only
	STATUS current
	DESCRIPTION "Translation creation collisions resolved (total)"

	::={rewriteTranslationCreationCollisionResolutions 2}

rewriteTranslationCreationCollisionResolutionsMax	OBJECT-TYPE
	SYNTAX	 CounterBasedGauge64
	MAX-ACCESS read-only
	STATUS current
	DESCRIPTION "Translation creation collisions resolved (total)"

	::={rewriteTranslationCreationCollisionResolutions 3}

rewriteTranslationCreationCollisionResolutionsLevelTable OBJECT-TYPE
	SYNTAX      SEQUENCE OF RewriteTranslationCreationCollisionResolutionsLevelEntry
	MAX-ACCESS  not-accessible
	STATUS      current
	DESCRIPTION
	"Table for rewriteTranslationCreationCollisionResolutions"
	::={rewriteTranslationCreationCollisionResolutions 4}

rewriteTranslationCreationCollisionResolutionsLevelEntry OBJECT-TYPE
	SYNTAX      RewriteTranslationCreationCollisionResolutionsLevelEntry
	MAX-ACCESS  not-accessible
	STATUS      current
	DESCRIPTION
	"Table entry for rewriteTranslationCreationCollisionResolutions"
	INDEX { rewriteTranslationCreationCollisionResolutionsLevelName }
	::={rewriteTranslationCreationCollisionResolutionsLevelTable 1}

RewriteTranslationCreationCollisionResolutionsLevelEntry ::=
	SEQUENCE {
		rewriteTranslationCreationCollisionResolutionsLevelName	DisplayString,
		rewriteTranslationCreationCollisionResolutionsLevelVal	Counter64,
		rewriteTranslationCreationCollisionResolutionsLevelMom	CounterBasedGauge64,
		rewriteTranslationCreationCollisionResolutionsLevelMax	CounterBasedGauge64
	}

rewriteTranslationCreationCollisionResolutionsLevelName OBJECT-TYPE
	SYNTAX      DisplayString
	MAX-ACCESS  not-accessible
	STATUS      current
	DESCRIPTION
	"Table entry display string for rewriteTranslationCreationCollisionResolutions"
	::={rewriteTranslationCreationCollisionResolutionsLevelEntry 1}

rewriteTranslationCreationCollisionResolutionsLevelVal OBJECT-TYPE
	SYNTAX	 Counter64
	MAX-ACCESS  read-only
	STATUS      current
	DESCRIPTION
	"Table entry attribute for rewriteTranslationCreationCollisionResolutions"
	::={rewriteTranslationCreationCollisionResolutionsLevelEntry 2}

rewriteTranslationCreationCollisionResolutionsLevelMom OBJECT-TYPE
	SYNTAX	 CounterBasedGauge64
	MAX-ACCESS  read-only
	STATUS      current
	DESCRIPTION
	"Table entry attribute for rewriteTranslationCreationCollisionResolutions"
	::={rewriteTranslationCreationCollisionResolutionsLevelEntry 3}

rewriteTranslationCreationCollisionResolutionsLevelMax OBJECT-TYPE
	SYNTAX	 CounterBasedGauge64
	MAX-ACCESS  read-only
	STATUS      current
	DESCRIPTION
	"Table entry attribute for rewriteTranslationCreationCollisionResolutions"
	::={rewriteTranslationCreationCollisionResolutionsLevelEntry 4}


rewriteTranslatedInboundPackets	OBJECT IDENTIFIER ::={rewrite 46}

rewriteTranslatedInboundPacketsVal	OBJECT-TYPE
	SYNTAX	 Counter64
	MAX-ACCESS read-only
	STATUS current
	DESCRIPTION "Translated inbound packets (total)"

	::={rewriteTranslatedInboundPackets 1}

rewriteTranslatedInboundPacketsMom	OBJECT-TYPE
	SYNTAX	 CounterBasedGauge64
	MAX-ACCESS read-only
	STATUS current
	DESCRIPTION "Translated inbound packets (total)"

	::={rewriteTranslatedInboundPackets 2}

rewriteTranslatedInboundPacketsMax	OBJECT-TYPE
	SYNTAX	 CounterBasedGauge64
	MAX-ACCESS read-only
	STATUS current
	DESCRIPTION "Translated inbound packets (total)"

	::={rewriteTranslatedInboundPackets 3}

rewriteTranslatedInboundPacketsLevelTable OBJECT-TYPE
	SYNTAX      SEQUENCE OF RewriteTranslatedInboundPacketsLevelEntry
	MAX-ACCESS  not-accessible
	STATUS      current
	DESCRIPTION
	"Table for rewriteTranslatedInboundPackets"
	::={rewriteTranslatedInboundPackets 4}

rewriteTranslatedInboundPacketsLevelEntry OBJECT-TYPE
	SYNTAX      RewriteTranslatedInboundPacketsLevelEntry
	MAX-ACCESS  not-accessible
	STATUS      current
	DESCRIPTION
	"Table entry for rewriteTranslatedInboundPackets"
	INDEX { rewriteTranslatedInboundPacketsLevelName }
	::={rewriteTranslatedInboundPacketsLevelTable 1}

RewriteTranslatedInboundPacketsLevelEntry ::=
	SEQUENCE {
		rewriteTranslatedInboundPacketsLevelName	DisplayString,
		rewriteTranslatedInboundPacketsLevelVal	Counter64,
		rewriteTranslatedInboundPacketsLevelMom	CounterBasedGauge64,
		rewriteTranslatedInboundPacketsLevelMax	CounterBasedGauge64
	}

rewriteTranslatedInboundPacketsLevelName OBJECT-TYPE
	SYNTAX      DisplayString
	MAX-ACCESS  not-accessible
	STATUS      current
	DESCRIPTION
	"Table entry display string for rewriteTranslatedInboundPackets"
	::={rewriteTranslatedInboundPacketsLevelEntry 1}

rewriteTranslatedInboundPacketsLevelVal OBJECT-TYPE
	SYNTAX	 Counter64
	MAX-ACCESS  read-only
	STATUS      current
	DESCRIPTION
	"Table entry attribute for rewriteTranslatedInboundPackets"
	::={rewriteTranslatedInboundPacketsLevelEntry 2}

rewriteTranslatedInboundPacketsLevelMom OBJECT-TYPE
	SYNTAX	 CounterBasedGauge64
	MAX-ACCESS  read-only
	STATUS      current
	DESCRIPTION
	"Table entry attribute for rewriteTranslatedInboundPackets"
	::={rewriteTranslatedInboundPacketsLevelEntry 3}

rewriteTranslatedInboundPacketsLevelMax OBJECT-TYPE
	SYNTAX	 CounterBasedGauge64
	MAX-ACCESS  read-only
	STATUS      current
	DESCRIPTION
	"Table entry attribute for rewriteTranslatedInboundPackets"
	::={rewriteTranslatedInboundPacketsLevelEntry 4}


rewriteTranslatedInboundBytes	OBJECT IDENTIFIER ::={rewrite 47}

rewriteTranslatedInboundBytesVal	OBJECT-TYPE
	SYNTAX	 Counter64
	MAX-ACCESS read-only
	STATUS current
	DESCRIPTION "Translated inbound bytes (total)"

	::={rewriteTranslatedInboundBytes 1}

rewriteTranslatedInboundBytesMom	OBJECT-TYPE
	SYNTAX	 CounterBasedGauge64
	MAX-ACCESS read-only
	STATUS current
	DESCRIPTION "Translated inbound bytes (total)"

	::={rewriteTranslatedInboundBytes 2}

rewriteTranslatedInboundBytesMax	OBJECT-TYPE
	SYNTAX	 CounterBasedGauge64
	MAX-ACCESS read-only
	STATUS current
	DESCRIPTION "Translated inbound bytes (total)"

	::={rewriteTranslatedInboundBytes 3}

rewriteTranslatedInboundBytesLevelTable OBJECT-TYPE
	SYNTAX      SEQUENCE OF RewriteTranslatedInboundBytesLevelEntry
	MAX-ACCESS  not-accessible
	STATUS      current
	DESCRIPTION
	"Table for rewriteTranslatedInboundBytes"
	::={rewriteTranslatedInboundBytes 4}

rewriteTranslatedInboundBytesLevelEntry OBJECT-TYPE
	SYNTAX      RewriteTranslatedInboundBytesLevelEntry
	MAX-ACCESS  not-accessible
	STATUS      current
	DESCRIPTION
	"Table entry for rewriteTranslatedInboundBytes"
	INDEX { rewriteTranslatedInboundBytesLevelName }
	::={rewriteTranslatedInboundBytesLevelTable 1}

RewriteTranslatedInboundBytesLevelEntry ::=
	SEQUENCE {
		rewriteTranslatedInboundBytesLevelName	DisplayString,
		rewriteTranslatedInboundBytesLevelVal	Counter64,
		rewriteTranslatedInboundBytesLevelMom	CounterBasedGauge64,
		rewriteTranslatedInboundBytesLevelMax	CounterBasedGauge64
	}

rewriteTranslatedInboundBytesLevelName OBJECT-TYPE
	SYNTAX      DisplayString
	MAX-ACCESS  not-accessible
	STATUS      current
	DESCRIPTION
	"Table entry display string for rewriteTranslatedInboundBytes"
	::={rewriteTranslatedInboundBytesLevelEntry 1}

rewriteTranslatedInboundBytesLevelVal OBJECT-TYPE
	SYNTAX	 Counter64
	MAX-ACCESS  read-only
	STATUS      current
	DESCRIPTION
	"Table entry attribute for rewriteTranslatedInboundBytes"
	::={rewriteTranslatedInboundBytesLevelEntry 2}

rewriteTranslatedInboundBytesLevelMom OBJECT-TYPE
	SYNTAX	 CounterBasedGauge64
	MAX-ACCESS  read-only
	STATUS      current
	DESCRIPTION
	"Table entry attribute for rewriteTranslatedInboundBytes"
	::={rewriteTranslatedInboundBytesLevelEntry 3}

rewriteTranslatedInboundBytesLevelMax OBJECT-TYPE
	SYNTAX	 CounterBasedGauge64
	MAX-ACCESS  read-only
	STATUS      current
	DESCRIPTION
	"Table entry attribute for rewriteTranslatedInboundBytes"
	::={rewriteTranslatedInboundBytesLevelEntry 4}


rewriteTranslatedOutboundPackets	OBJECT IDENTIFIER ::={rewrite 48}

rewriteTranslatedOutboundPacketsVal	OBJECT-TYPE
	SYNTAX	 Counter64
	MAX-ACCESS read-only
	STATUS current
	DESCRIPTION "Translated outbound packets (total)"

	::={rewriteTranslatedOutboundPackets 1}

rewriteTranslatedOutboundPacketsMom	OBJECT-TYPE
	SYNTAX	 CounterBasedGauge64
	MAX-ACCESS read-only
	STATUS current
	DESCRIPTION "Translated outbound packets (total)"

	::={rewriteTranslatedOutboundPackets 2}

rewriteTranslatedOutboundPacketsMax	OBJECT-TYPE
	SYNTAX	 CounterBasedGauge64
	MAX-ACCESS read-only
	STATUS current
	DESCRIPTION "Translated outbound packets (total)"

	::={rewriteTranslatedOutboundPackets 3}

rewriteTranslatedOutboundPacketsLevelTable OBJECT-TYPE
	SYNTAX      SEQUENCE OF RewriteTranslatedOutboundPacketsLevelEntry
	MAX-ACCESS  not-accessible
	STATUS      current
	DESCRIPTION
	"Table for rewriteTranslatedOutboundPackets"
	::={rewriteTranslatedOutboundPackets 4}

rewriteTranslatedOutboundPacketsLevelEntry OBJECT-TYPE
	SYNTAX      RewriteTranslatedOutboundPacketsLevelEntry
	MAX-ACCESS  not-accessible
	STATUS      current
	DESCRIPTION
	"Table entry for rewriteTranslatedOutboundPackets"
	INDEX { rewriteTranslatedOutboundPacketsLevelName }
	::={rewriteTranslatedOutboundPacketsLevelTable 1}

RewriteTranslatedOutboundPacketsLevelEntry ::=
	SEQUENCE {
		rewriteTranslatedOutboundPacketsLevelName	DisplayString,
		rewriteTranslatedOutboundPacketsLevelVal	Counter64,
		rewriteTranslatedOutboundPacketsLevelMom	CounterBasedGauge64,
		rewriteTranslatedOutboundPacketsLevelMax	CounterBasedGauge64
	}

rewriteTranslatedOutboundPacketsLevelName OBJECT-TYPE
	SYNTAX      DisplayString
	MAX-ACCESS  not-accessible
	STATUS      current
	DESCRIPTION
	"Table entry display string for rewriteTranslatedOutboundPackets"
	::={rewriteTranslatedOutboundPacketsLevelEntry 1}

rewriteTranslatedOutboundPacketsLevelVal OBJECT-TYPE
	SYNTAX	 Counter64
	MAX-ACCESS  read-only
	STATUS      current
	DESCRIPTION
	"Table entry attribute for rewriteTranslatedOutboundPackets"
	::={rewriteTranslatedOutboundPacketsLevelEntry 2}

rewriteTranslatedOutboundPacketsLevelMom OBJECT-TYPE
	SYNTAX	 CounterBasedGauge64
	MAX-ACCESS  read-only
	STATUS      current
	DESCRIPTION
	"Table entry attribute for rewriteTranslatedOutboundPackets"
	::={rewriteTranslatedOutboundPacketsLevelEntry 3}

rewriteTranslatedOutboundPacketsLevelMax OBJECT-TYPE
	SYNTAX	 CounterBasedGauge64
	MAX-ACCESS  read-only
	STATUS      current
	DESCRIPTION
	"Table entry attribute for rewriteTranslatedOutboundPackets"
	::={rewriteTranslatedOutboundPacketsLevelEntry 4}


rewriteTranslatedOutboundBytes	OBJECT IDENTIFIER ::={rewrite 49}

rewriteTranslatedOutboundBytesVal	OBJECT-TYPE
	SYNTAX	 Counter64
	MAX-ACCESS read-only
	STATUS current
	DESCRIPTION "Translated outbound bytes (total)"

	::={rewriteTranslatedOutboundBytes 1}

rewriteTranslatedOutboundBytesMom	OBJECT-TYPE
	SYNTAX	 CounterBasedGauge64
	MAX-ACCESS read-only
	STATUS current
	DESCRIPTION "Translated outbound bytes (total)"

	::={rewriteTranslatedOutboundBytes 2}

rewriteTranslatedOutboundBytesMax	OBJECT-TYPE
	SYNTAX	 CounterBasedGauge64
	MAX-ACCESS read-only
	STATUS current
	DESCRIPTION "Translated outbound bytes (total)"

	::={rewriteTranslatedOutboundBytes 3}

rewriteTranslatedOutboundBytesLevelTable OBJECT-TYPE
	SYNTAX      SEQUENCE OF RewriteTranslatedOutboundBytesLevelEntry
	MAX-ACCESS  not-accessible
	STATUS      current
	DESCRIPTION
	"Table for rewriteTranslatedOutboundBytes"
	::={rewriteTranslatedOutboundBytes 4}

rewriteTranslatedOutboundBytesLevelEntry OBJECT-TYPE
	SYNTAX      RewriteTranslatedOutboundBytesLevelEntry
	MAX-ACCESS  not-accessible
	STATUS      current
	DESCRIPTION
	"Table entry for rewriteTranslatedOutboundBytes"
	INDEX { rewriteTranslatedOutboundBytesLevelName }
	::={rewriteTranslatedOutboundBytesLevelTable 1}

RewriteTranslatedOutboundBytesLevelEntry ::=
	SEQUENCE {
		rewriteTranslatedOutboundBytesLevelName	DisplayString,
		rewriteTranslatedOutboundBytesLevelVal	Counter64,
		rewriteTranslatedOutboundBytesLevelMom	CounterBasedGauge64,
		rewriteTranslatedOutboundBytesLevelMax	CounterBasedGauge64
	}

rewriteTranslatedOutboundBytesLevelName OBJECT-TYPE
	SYNTAX      DisplayString
	MAX-ACCESS  not-accessible
	STATUS      current
	DESCRIPTION
	"Table entry display string for rewriteTranslatedOutboundBytes"
	::={rewriteTranslatedOutboundBytesLevelEntry 1}

rewriteTranslatedOutboundBytesLevelVal OBJECT-TYPE
	SYNTAX	 Counter64
	MAX-ACCESS  read-only
	STATUS      current
	DESCRIPTION
	"Table entry attribute for rewriteTranslatedOutboundBytes"
	::={rewriteTranslatedOutboundBytesLevelEntry 2}

rewriteTranslatedOutboundBytesLevelMom OBJECT-TYPE
	SYNTAX	 CounterBasedGauge64
	MAX-ACCESS  read-only
	STATUS      current
	DESCRIPTION
	"Table entry attribute for rewriteTranslatedOutboundBytes"
	::={rewriteTranslatedOutboundBytesLevelEntry 3}

rewriteTranslatedOutboundBytesLevelMax OBJECT-TYPE
	SYNTAX	 CounterBasedGauge64
	MAX-ACCESS  read-only
	STATUS      current
	DESCRIPTION
	"Table entry attribute for rewriteTranslatedOutboundBytes"
	::={rewriteTranslatedOutboundBytesLevelEntry 4}


rewriteTranslationCreationFailureRewriteAddress	OBJECT IDENTIFIER ::={rewrite 50}

rewriteTranslationCreationFailureRewriteAddressVal	OBJECT-TYPE
	SYNTAX	 Counter64
	MAX-ACCESS read-only
	STATUS current
	DESCRIPTION "Translation creation failure (No rewrite address, total)"

	::={rewriteTranslationCreationFailureRewriteAddress 1}

rewriteTranslationCreationFailureRewriteAddressMom	OBJECT-TYPE
	SYNTAX	 CounterBasedGauge64
	MAX-ACCESS read-only
	STATUS current
	DESCRIPTION "Translation creation failure (No rewrite address, total)"

	::={rewriteTranslationCreationFailureRewriteAddress 2}

rewriteTranslationCreationFailureRewriteAddressMax	OBJECT-TYPE
	SYNTAX	 CounterBasedGauge64
	MAX-ACCESS read-only
	STATUS current
	DESCRIPTION "Translation creation failure (No rewrite address, total)"

	::={rewriteTranslationCreationFailureRewriteAddress 3}

rewriteTranslationCreationFailureRewriteAddressLevelTable OBJECT-TYPE
	SYNTAX      SEQUENCE OF RewriteTranslationCreationFailureRewriteAddressLevelEntry
	MAX-ACCESS  not-accessible
	STATUS      current
	DESCRIPTION
	"Table for rewriteTranslationCreationFailureRewriteAddress"
	::={rewriteTranslationCreationFailureRewriteAddress 4}

rewriteTranslationCreationFailureRewriteAddressLevelEntry OBJECT-TYPE
	SYNTAX      RewriteTranslationCreationFailureRewriteAddressLevelEntry
	MAX-ACCESS  not-accessible
	STATUS      current
	DESCRIPTION
	"Table entry for rewriteTranslationCreationFailureRewriteAddress"
	INDEX { rewriteTranslationCreationFailureRewriteAddressLevelName }
	::={rewriteTranslationCreationFailureRewriteAddressLevelTable 1}

RewriteTranslationCreationFailureRewriteAddressLevelEntry ::=
	SEQUENCE {
		rewriteTranslationCreationFailureRewriteAddressLevelName	DisplayString,
		rewriteTranslationCreationFailureRewriteAddressLevelVal	Counter64,
		rewriteTranslationCreationFailureRewriteAddressLevelMom	CounterBasedGauge64,
		rewriteTranslationCreationFailureRewriteAddressLevelMax	CounterBasedGauge64
	}

rewriteTranslationCreationFailureRewriteAddressLevelName OBJECT-TYPE
	SYNTAX      DisplayString
	MAX-ACCESS  not-accessible
	STATUS      current
	DESCRIPTION
	"Table entry display string for rewriteTranslationCreationFailureRewriteAddress"
	::={rewriteTranslationCreationFailureRewriteAddressLevelEntry 1}

rewriteTranslationCreationFailureRewriteAddressLevelVal OBJECT-TYPE
	SYNTAX	 Counter64
	MAX-ACCESS  read-only
	STATUS      current
	DESCRIPTION
	"Table entry attribute for rewriteTranslationCreationFailureRewriteAddress"
	::={rewriteTranslationCreationFailureRewriteAddressLevelEntry 2}

rewriteTranslationCreationFailureRewriteAddressLevelMom OBJECT-TYPE
	SYNTAX	 CounterBasedGauge64
	MAX-ACCESS  read-only
	STATUS      current
	DESCRIPTION
	"Table entry attribute for rewriteTranslationCreationFailureRewriteAddress"
	::={rewriteTranslationCreationFailureRewriteAddressLevelEntry 3}

rewriteTranslationCreationFailureRewriteAddressLevelMax OBJECT-TYPE
	SYNTAX	 CounterBasedGauge64
	MAX-ACCESS  read-only
	STATUS      current
	DESCRIPTION
	"Table entry attribute for rewriteTranslationCreationFailureRewriteAddress"
	::={rewriteTranslationCreationFailureRewriteAddressLevelEntry 4}


rewriteTranslationsCreatedInboundTransl	OBJECT IDENTIFIER ::={rewrite 60}

rewriteTranslationsCreatedInboundTranslVal	OBJECT-TYPE
	SYNTAX	 Counter64
	MAX-ACCESS read-only
	STATUS current
	DESCRIPTION "Translations created (inbound)"

	::={rewriteTranslationsCreatedInboundTransl 1}

rewriteTranslationsCreatedInboundTranslMom	OBJECT-TYPE
	SYNTAX	 CounterBasedGauge64
	MAX-ACCESS read-only
	STATUS current
	DESCRIPTION "Translations created (inbound)"

	::={rewriteTranslationsCreatedInboundTransl 2}

rewriteTranslationsCreatedInboundTranslMax	OBJECT-TYPE
	SYNTAX	 CounterBasedGauge64
	MAX-ACCESS read-only
	STATUS current
	DESCRIPTION "Translations created (inbound)"

	::={rewriteTranslationsCreatedInboundTransl 3}

rewriteTranslationsCreatedInboundTranslLevelTable OBJECT-TYPE
	SYNTAX      SEQUENCE OF RewriteTranslationsCreatedInboundTranslLevelEntry
	MAX-ACCESS  not-accessible
	STATUS      current
	DESCRIPTION
	"Table for rewriteTranslationsCreatedInboundTransl"
	::={rewriteTranslationsCreatedInboundTransl 4}

rewriteTranslationsCreatedInboundTranslLevelEntry OBJECT-TYPE
	SYNTAX      RewriteTranslationsCreatedInboundTranslLevelEntry
	MAX-ACCESS  not-accessible
	STATUS      current
	DESCRIPTION
	"Table entry for rewriteTranslationsCreatedInboundTransl"
	INDEX { rewriteTranslationsCreatedInboundTranslLevelName }
	::={rewriteTranslationsCreatedInboundTranslLevelTable 1}

RewriteTranslationsCreatedInboundTranslLevelEntry ::=
	SEQUENCE {
		rewriteTranslationsCreatedInboundTranslLevelName	DisplayString,
		rewriteTranslationsCreatedInboundTranslLevelVal	Counter64,
		rewriteTranslationsCreatedInboundTranslLevelMom	CounterBasedGauge64,
		rewriteTranslationsCreatedInboundTranslLevelMax	CounterBasedGauge64
	}

rewriteTranslationsCreatedInboundTranslLevelName OBJECT-TYPE
	SYNTAX      DisplayString
	MAX-ACCESS  not-accessible
	STATUS      current
	DESCRIPTION
	"Table entry display string for rewriteTranslationsCreatedInboundTransl"
	::={rewriteTranslationsCreatedInboundTranslLevelEntry 1}

rewriteTranslationsCreatedInboundTranslLevelVal OBJECT-TYPE
	SYNTAX	 Counter64
	MAX-ACCESS  read-only
	STATUS      current
	DESCRIPTION
	"Table entry attribute for rewriteTranslationsCreatedInboundTransl"
	::={rewriteTranslationsCreatedInboundTranslLevelEntry 2}

rewriteTranslationsCreatedInboundTranslLevelMom OBJECT-TYPE
	SYNTAX	 CounterBasedGauge64
	MAX-ACCESS  read-only
	STATUS      current
	DESCRIPTION
	"Table entry attribute for rewriteTranslationsCreatedInboundTransl"
	::={rewriteTranslationsCreatedInboundTranslLevelEntry 3}

rewriteTranslationsCreatedInboundTranslLevelMax OBJECT-TYPE
	SYNTAX	 CounterBasedGauge64
	MAX-ACCESS  read-only
	STATUS      current
	DESCRIPTION
	"Table entry attribute for rewriteTranslationsCreatedInboundTransl"
	::={rewriteTranslationsCreatedInboundTranslLevelEntry 4}


rewriteTranslationsCreatedTcpInboundTransl	OBJECT IDENTIFIER ::={rewrite 61}

rewriteTranslationsCreatedTcpInboundTranslVal	OBJECT-TYPE
	SYNTAX	 Counter64
	MAX-ACCESS read-only
	STATUS current
	DESCRIPTION "Translations created - TCP (inbound)"

	::={rewriteTranslationsCreatedTcpInboundTransl 1}

rewriteTranslationsCreatedTcpInboundTranslMom	OBJECT-TYPE
	SYNTAX	 CounterBasedGauge64
	MAX-ACCESS read-only
	STATUS current
	DESCRIPTION "Translations created - TCP (inbound)"

	::={rewriteTranslationsCreatedTcpInboundTransl 2}

rewriteTranslationsCreatedTcpInboundTranslMax	OBJECT-TYPE
	SYNTAX	 CounterBasedGauge64
	MAX-ACCESS read-only
	STATUS current
	DESCRIPTION "Translations created - TCP (inbound)"

	::={rewriteTranslationsCreatedTcpInboundTransl 3}

rewriteTranslationsCreatedTcpInboundTranslLevelTable OBJECT-TYPE
	SYNTAX      SEQUENCE OF RewriteTranslationsCreatedTcpInboundTranslLevelEntry
	MAX-ACCESS  not-accessible
	STATUS      current
	DESCRIPTION
	"Table for rewriteTranslationsCreatedTcpInboundTransl"
	::={rewriteTranslationsCreatedTcpInboundTransl 4}

rewriteTranslationsCreatedTcpInboundTranslLevelEntry OBJECT-TYPE
	SYNTAX      RewriteTranslationsCreatedTcpInboundTranslLevelEntry
	MAX-ACCESS  not-accessible
	STATUS      current
	DESCRIPTION
	"Table entry for rewriteTranslationsCreatedTcpInboundTransl"
	INDEX { rewriteTranslationsCreatedTcpInboundTranslLevelName }
	::={rewriteTranslationsCreatedTcpInboundTranslLevelTable 1}

RewriteTranslationsCreatedTcpInboundTranslLevelEntry ::=
	SEQUENCE {
		rewriteTranslationsCreatedTcpInboundTranslLevelName	DisplayString,
		rewriteTranslationsCreatedTcpInboundTranslLevelVal	Counter64,
		rewriteTranslationsCreatedTcpInboundTranslLevelMom	CounterBasedGauge64,
		rewriteTranslationsCreatedTcpInboundTranslLevelMax	CounterBasedGauge64
	}

rewriteTranslationsCreatedTcpInboundTranslLevelName OBJECT-TYPE
	SYNTAX      DisplayString
	MAX-ACCESS  not-accessible
	STATUS      current
	DESCRIPTION
	"Table entry display string for rewriteTranslationsCreatedTcpInboundTransl"
	::={rewriteTranslationsCreatedTcpInboundTranslLevelEntry 1}

rewriteTranslationsCreatedTcpInboundTranslLevelVal OBJECT-TYPE
	SYNTAX	 Counter64
	MAX-ACCESS  read-only
	STATUS      current
	DESCRIPTION
	"Table entry attribute for rewriteTranslationsCreatedTcpInboundTransl"
	::={rewriteTranslationsCreatedTcpInboundTranslLevelEntry 2}

rewriteTranslationsCreatedTcpInboundTranslLevelMom OBJECT-TYPE
	SYNTAX	 CounterBasedGauge64
	MAX-ACCESS  read-only
	STATUS      current
	DESCRIPTION
	"Table entry attribute for rewriteTranslationsCreatedTcpInboundTransl"
	::={rewriteTranslationsCreatedTcpInboundTranslLevelEntry 3}

rewriteTranslationsCreatedTcpInboundTranslLevelMax OBJECT-TYPE
	SYNTAX	 CounterBasedGauge64
	MAX-ACCESS  read-only
	STATUS      current
	DESCRIPTION
	"Table entry attribute for rewriteTranslationsCreatedTcpInboundTransl"
	::={rewriteTranslationsCreatedTcpInboundTranslLevelEntry 4}


rewriteTranslationsCreatedUdpInboundTransl	OBJECT IDENTIFIER ::={rewrite 62}

rewriteTranslationsCreatedUdpInboundTranslVal	OBJECT-TYPE
	SYNTAX	 Counter64
	MAX-ACCESS read-only
	STATUS current
	DESCRIPTION "Translations created - UDP (inbound)"

	::={rewriteTranslationsCreatedUdpInboundTransl 1}

rewriteTranslationsCreatedUdpInboundTranslMom	OBJECT-TYPE
	SYNTAX	 CounterBasedGauge64
	MAX-ACCESS read-only
	STATUS current
	DESCRIPTION "Translations created - UDP (inbound)"

	::={rewriteTranslationsCreatedUdpInboundTransl 2}

rewriteTranslationsCreatedUdpInboundTranslMax	OBJECT-TYPE
	SYNTAX	 CounterBasedGauge64
	MAX-ACCESS read-only
	STATUS current
	DESCRIPTION "Translations created - UDP (inbound)"

	::={rewriteTranslationsCreatedUdpInboundTransl 3}

rewriteTranslationsCreatedUdpInboundTranslLevelTable OBJECT-TYPE
	SYNTAX      SEQUENCE OF RewriteTranslationsCreatedUdpInboundTranslLevelEntry
	MAX-ACCESS  not-accessible
	STATUS      current
	DESCRIPTION
	"Table for rewriteTranslationsCreatedUdpInboundTransl"
	::={rewriteTranslationsCreatedUdpInboundTransl 4}

rewriteTranslationsCreatedUdpInboundTranslLevelEntry OBJECT-TYPE
	SYNTAX      RewriteTranslationsCreatedUdpInboundTranslLevelEntry
	MAX-ACCESS  not-accessible
	STATUS      current
	DESCRIPTION
	"Table entry for rewriteTranslationsCreatedUdpInboundTransl"
	INDEX { rewriteTranslationsCreatedUdpInboundTranslLevelName }
	::={rewriteTranslationsCreatedUdpInboundTranslLevelTable 1}

RewriteTranslationsCreatedUdpInboundTranslLevelEntry ::=
	SEQUENCE {
		rewriteTranslationsCreatedUdpInboundTranslLevelName	DisplayString,
		rewriteTranslationsCreatedUdpInboundTranslLevelVal	Counter64,
		rewriteTranslationsCreatedUdpInboundTranslLevelMom	CounterBasedGauge64,
		rewriteTranslationsCreatedUdpInboundTranslLevelMax	CounterBasedGauge64
	}

rewriteTranslationsCreatedUdpInboundTranslLevelName OBJECT-TYPE
	SYNTAX      DisplayString
	MAX-ACCESS  not-accessible
	STATUS      current
	DESCRIPTION
	"Table entry display string for rewriteTranslationsCreatedUdpInboundTransl"
	::={rewriteTranslationsCreatedUdpInboundTranslLevelEntry 1}

rewriteTranslationsCreatedUdpInboundTranslLevelVal OBJECT-TYPE
	SYNTAX	 Counter64
	MAX-ACCESS  read-only
	STATUS      current
	DESCRIPTION
	"Table entry attribute for rewriteTranslationsCreatedUdpInboundTransl"
	::={rewriteTranslationsCreatedUdpInboundTranslLevelEntry 2}

rewriteTranslationsCreatedUdpInboundTranslLevelMom OBJECT-TYPE
	SYNTAX	 CounterBasedGauge64
	MAX-ACCESS  read-only
	STATUS      current
	DESCRIPTION
	"Table entry attribute for rewriteTranslationsCreatedUdpInboundTransl"
	::={rewriteTranslationsCreatedUdpInboundTranslLevelEntry 3}

rewriteTranslationsCreatedUdpInboundTranslLevelMax OBJECT-TYPE
	SYNTAX	 CounterBasedGauge64
	MAX-ACCESS  read-only
	STATUS      current
	DESCRIPTION
	"Table entry attribute for rewriteTranslationsCreatedUdpInboundTransl"
	::={rewriteTranslationsCreatedUdpInboundTranslLevelEntry 4}


rewriteTranslationsCreatedIcmpInboundTransl	OBJECT IDENTIFIER ::={rewrite 63}

rewriteTranslationsCreatedIcmpInboundTranslVal	OBJECT-TYPE
	SYNTAX	 Counter64
	MAX-ACCESS read-only
	STATUS current
	DESCRIPTION "Translations created - ICMP (inbound)"

	::={rewriteTranslationsCreatedIcmpInboundTransl 1}

rewriteTranslationsCreatedIcmpInboundTranslMom	OBJECT-TYPE
	SYNTAX	 CounterBasedGauge64
	MAX-ACCESS read-only
	STATUS current
	DESCRIPTION "Translations created - ICMP (inbound)"

	::={rewriteTranslationsCreatedIcmpInboundTransl 2}

rewriteTranslationsCreatedIcmpInboundTranslMax	OBJECT-TYPE
	SYNTAX	 CounterBasedGauge64
	MAX-ACCESS read-only
	STATUS current
	DESCRIPTION "Translations created - ICMP (inbound)"

	::={rewriteTranslationsCreatedIcmpInboundTransl 3}

rewriteTranslationsCreatedIcmpInboundTranslLevelTable OBJECT-TYPE
	SYNTAX      SEQUENCE OF RewriteTranslationsCreatedIcmpInboundTranslLevelEntry
	MAX-ACCESS  not-accessible
	STATUS      current
	DESCRIPTION
	"Table for rewriteTranslationsCreatedIcmpInboundTransl"
	::={rewriteTranslationsCreatedIcmpInboundTransl 4}

rewriteTranslationsCreatedIcmpInboundTranslLevelEntry OBJECT-TYPE
	SYNTAX      RewriteTranslationsCreatedIcmpInboundTranslLevelEntry
	MAX-ACCESS  not-accessible
	STATUS      current
	DESCRIPTION
	"Table entry for rewriteTranslationsCreatedIcmpInboundTransl"
	INDEX { rewriteTranslationsCreatedIcmpInboundTranslLevelName }
	::={rewriteTranslationsCreatedIcmpInboundTranslLevelTable 1}

RewriteTranslationsCreatedIcmpInboundTranslLevelEntry ::=
	SEQUENCE {
		rewriteTranslationsCreatedIcmpInboundTranslLevelName	DisplayString,
		rewriteTranslationsCreatedIcmpInboundTranslLevelVal	Counter64,
		rewriteTranslationsCreatedIcmpInboundTranslLevelMom	CounterBasedGauge64,
		rewriteTranslationsCreatedIcmpInboundTranslLevelMax	CounterBasedGauge64
	}

rewriteTranslationsCreatedIcmpInboundTranslLevelName OBJECT-TYPE
	SYNTAX      DisplayString
	MAX-ACCESS  not-accessible
	STATUS      current
	DESCRIPTION
	"Table entry display string for rewriteTranslationsCreatedIcmpInboundTransl"
	::={rewriteTranslationsCreatedIcmpInboundTranslLevelEntry 1}

rewriteTranslationsCreatedIcmpInboundTranslLevelVal OBJECT-TYPE
	SYNTAX	 Counter64
	MAX-ACCESS  read-only
	STATUS      current
	DESCRIPTION
	"Table entry attribute for rewriteTranslationsCreatedIcmpInboundTransl"
	::={rewriteTranslationsCreatedIcmpInboundTranslLevelEntry 2}

rewriteTranslationsCreatedIcmpInboundTranslLevelMom OBJECT-TYPE
	SYNTAX	 CounterBasedGauge64
	MAX-ACCESS  read-only
	STATUS      current
	DESCRIPTION
	"Table entry attribute for rewriteTranslationsCreatedIcmpInboundTransl"
	::={rewriteTranslationsCreatedIcmpInboundTranslLevelEntry 3}

rewriteTranslationsCreatedIcmpInboundTranslLevelMax OBJECT-TYPE
	SYNTAX	 CounterBasedGauge64
	MAX-ACCESS  read-only
	STATUS      current
	DESCRIPTION
	"Table entry attribute for rewriteTranslationsCreatedIcmpInboundTransl"
	::={rewriteTranslationsCreatedIcmpInboundTranslLevelEntry 4}


rewriteTranslationsDeletedInboundTransl	OBJECT IDENTIFIER ::={rewrite 64}

rewriteTranslationsDeletedInboundTranslVal	OBJECT-TYPE
	SYNTAX	 Counter64
	MAX-ACCESS read-only
	STATUS current
	DESCRIPTION "Translations deleted (inbound)"

	::={rewriteTranslationsDeletedInboundTransl 1}

rewriteTranslationsDeletedInboundTranslMom	OBJECT-TYPE
	SYNTAX	 CounterBasedGauge64
	MAX-ACCESS read-only
	STATUS current
	DESCRIPTION "Translations deleted (inbound)"

	::={rewriteTranslationsDeletedInboundTransl 2}

rewriteTranslationsDeletedInboundTranslMax	OBJECT-TYPE
	SYNTAX	 CounterBasedGauge64
	MAX-ACCESS read-only
	STATUS current
	DESCRIPTION "Translations deleted (inbound)"

	::={rewriteTranslationsDeletedInboundTransl 3}

rewriteTranslationsDeletedInboundTranslLevelTable OBJECT-TYPE
	SYNTAX      SEQUENCE OF RewriteTranslationsDeletedInboundTranslLevelEntry
	MAX-ACCESS  not-accessible
	STATUS      current
	DESCRIPTION
	"Table for rewriteTranslationsDeletedInboundTransl"
	::={rewriteTranslationsDeletedInboundTransl 4}

rewriteTranslationsDeletedInboundTranslLevelEntry OBJECT-TYPE
	SYNTAX      RewriteTranslationsDeletedInboundTranslLevelEntry
	MAX-ACCESS  not-accessible
	STATUS      current
	DESCRIPTION
	"Table entry for rewriteTranslationsDeletedInboundTransl"
	INDEX { rewriteTranslationsDeletedInboundTranslLevelName }
	::={rewriteTranslationsDeletedInboundTranslLevelTable 1}

RewriteTranslationsDeletedInboundTranslLevelEntry ::=
	SEQUENCE {
		rewriteTranslationsDeletedInboundTranslLevelName	DisplayString,
		rewriteTranslationsDeletedInboundTranslLevelVal	Counter64,
		rewriteTranslationsDeletedInboundTranslLevelMom	CounterBasedGauge64,
		rewriteTranslationsDeletedInboundTranslLevelMax	CounterBasedGauge64
	}

rewriteTranslationsDeletedInboundTranslLevelName OBJECT-TYPE
	SYNTAX      DisplayString
	MAX-ACCESS  not-accessible
	STATUS      current
	DESCRIPTION
	"Table entry display string for rewriteTranslationsDeletedInboundTransl"
	::={rewriteTranslationsDeletedInboundTranslLevelEntry 1}

rewriteTranslationsDeletedInboundTranslLevelVal OBJECT-TYPE
	SYNTAX	 Counter64
	MAX-ACCESS  read-only
	STATUS      current
	DESCRIPTION
	"Table entry attribute for rewriteTranslationsDeletedInboundTransl"
	::={rewriteTranslationsDeletedInboundTranslLevelEntry 2}

rewriteTranslationsDeletedInboundTranslLevelMom OBJECT-TYPE
	SYNTAX	 CounterBasedGauge64
	MAX-ACCESS  read-only
	STATUS      current
	DESCRIPTION
	"Table entry attribute for rewriteTranslationsDeletedInboundTransl"
	::={rewriteTranslationsDeletedInboundTranslLevelEntry 3}

rewriteTranslationsDeletedInboundTranslLevelMax OBJECT-TYPE
	SYNTAX	 CounterBasedGauge64
	MAX-ACCESS  read-only
	STATUS      current
	DESCRIPTION
	"Table entry attribute for rewriteTranslationsDeletedInboundTransl"
	::={rewriteTranslationsDeletedInboundTranslLevelEntry 4}


rewriteTranslationsCountInboundTransl	OBJECT IDENTIFIER ::={rewrite 65}

rewriteTranslationsCountInboundTranslVal	OBJECT-TYPE
	SYNTAX	 CounterBasedGauge64
	MAX-ACCESS read-only
	STATUS current
	DESCRIPTION "Translations count (inbound)"

	::={rewriteTranslationsCountInboundTransl 1}

rewriteTranslationsCountInboundTranslMax	OBJECT-TYPE
	SYNTAX	 CounterBasedGauge64
	MAX-ACCESS read-only
	STATUS current
	DESCRIPTION "Translations count (inbound)"

	::={rewriteTranslationsCountInboundTransl 3}

rewriteTranslationsCountInboundTranslLevelTable OBJECT-TYPE
	SYNTAX      SEQUENCE OF RewriteTranslationsCountInboundTranslLevelEntry
	MAX-ACCESS  not-accessible
	STATUS      current
	DESCRIPTION
	"Table for rewriteTranslationsCountInboundTransl"
	::={rewriteTranslationsCountInboundTransl 4}

rewriteTranslationsCountInboundTranslLevelEntry OBJECT-TYPE
	SYNTAX      RewriteTranslationsCountInboundTranslLevelEntry
	MAX-ACCESS  not-accessible
	STATUS      current
	DESCRIPTION
	"Table entry for rewriteTranslationsCountInboundTransl"
	INDEX { rewriteTranslationsCountInboundTranslLevelName }
	::={rewriteTranslationsCountInboundTranslLevelTable 1}

RewriteTranslationsCountInboundTranslLevelEntry ::=
	SEQUENCE {
		rewriteTranslationsCountInboundTranslLevelName	DisplayString,
		rewriteTranslationsCountInboundTranslLevelVal	CounterBasedGauge64,
		rewriteTranslationsCountInboundTranslLevelMax	CounterBasedGauge64
	}

rewriteTranslationsCountInboundTranslLevelName OBJECT-TYPE
	SYNTAX      DisplayString
	MAX-ACCESS  not-accessible
	STATUS      current
	DESCRIPTION
	"Table entry display string for rewriteTranslationsCountInboundTransl"
	::={rewriteTranslationsCountInboundTranslLevelEntry 1}

rewriteTranslationsCountInboundTranslLevelVal OBJECT-TYPE
	SYNTAX	 CounterBasedGauge64
	MAX-ACCESS  read-only
	STATUS      current
	DESCRIPTION
	"Table entry attribute for rewriteTranslationsCountInboundTransl"
	::={rewriteTranslationsCountInboundTranslLevelEntry 2}

rewriteTranslationsCountInboundTranslLevelMax OBJECT-TYPE
	SYNTAX	 CounterBasedGauge64
	MAX-ACCESS  read-only
	STATUS      current
	DESCRIPTION
	"Table entry attribute for rewriteTranslationsCountInboundTransl"
	::={rewriteTranslationsCountInboundTranslLevelEntry 4}


rewriteTranslationsCountTcpInboundTransl	OBJECT IDENTIFIER ::={rewrite 66}

rewriteTranslationsCountTcpInboundTranslVal	OBJECT-TYPE
	SYNTAX	 CounterBasedGauge64
	MAX-ACCESS read-only
	STATUS current
	DESCRIPTION "Translations count - TCP (inbound)"

	::={rewriteTranslationsCountTcpInboundTransl 1}

rewriteTranslationsCountTcpInboundTranslMax	OBJECT-TYPE
	SYNTAX	 CounterBasedGauge64
	MAX-ACCESS read-only
	STATUS current
	DESCRIPTION "Translations count - TCP (inbound)"

	::={rewriteTranslationsCountTcpInboundTransl 3}

rewriteTranslationsCountTcpInboundTranslLevelTable OBJECT-TYPE
	SYNTAX      SEQUENCE OF RewriteTranslationsCountTcpInboundTranslLevelEntry
	MAX-ACCESS  not-accessible
	STATUS      current
	DESCRIPTION
	"Table for rewriteTranslationsCountTcpInboundTransl"
	::={rewriteTranslationsCountTcpInboundTransl 4}

rewriteTranslationsCountTcpInboundTranslLevelEntry OBJECT-TYPE
	SYNTAX      RewriteTranslationsCountTcpInboundTranslLevelEntry
	MAX-ACCESS  not-accessible
	STATUS      current
	DESCRIPTION
	"Table entry for rewriteTranslationsCountTcpInboundTransl"
	INDEX { rewriteTranslationsCountTcpInboundTranslLevelName }
	::={rewriteTranslationsCountTcpInboundTranslLevelTable 1}

RewriteTranslationsCountTcpInboundTranslLevelEntry ::=
	SEQUENCE {
		rewriteTranslationsCountTcpInboundTranslLevelName	DisplayString,
		rewriteTranslationsCountTcpInboundTranslLevelVal	CounterBasedGauge64,
		rewriteTranslationsCountTcpInboundTranslLevelMax	CounterBasedGauge64
	}

rewriteTranslationsCountTcpInboundTranslLevelName OBJECT-TYPE
	SYNTAX      DisplayString
	MAX-ACCESS  not-accessible
	STATUS      current
	DESCRIPTION
	"Table entry display string for rewriteTranslationsCountTcpInboundTransl"
	::={rewriteTranslationsCountTcpInboundTranslLevelEntry 1}

rewriteTranslationsCountTcpInboundTranslLevelVal OBJECT-TYPE
	SYNTAX	 CounterBasedGauge64
	MAX-ACCESS  read-only
	STATUS      current
	DESCRIPTION
	"Table entry attribute for rewriteTranslationsCountTcpInboundTransl"
	::={rewriteTranslationsCountTcpInboundTranslLevelEntry 2}

rewriteTranslationsCountTcpInboundTranslLevelMax OBJECT-TYPE
	SYNTAX	 CounterBasedGauge64
	MAX-ACCESS  read-only
	STATUS      current
	DESCRIPTION
	"Table entry attribute for rewriteTranslationsCountTcpInboundTransl"
	::={rewriteTranslationsCountTcpInboundTranslLevelEntry 4}


rewriteTranslationsCountUdpInboundTransl	OBJECT IDENTIFIER ::={rewrite 67}

rewriteTranslationsCountUdpInboundTranslVal	OBJECT-TYPE
	SYNTAX	 CounterBasedGauge64
	MAX-ACCESS read-only
	STATUS current
	DESCRIPTION "Translations count - UDP (inbound)"

	::={rewriteTranslationsCountUdpInboundTransl 1}

rewriteTranslationsCountUdpInboundTranslMax	OBJECT-TYPE
	SYNTAX	 CounterBasedGauge64
	MAX-ACCESS read-only
	STATUS current
	DESCRIPTION "Translations count - UDP (inbound)"

	::={rewriteTranslationsCountUdpInboundTransl 3}

rewriteTranslationsCountUdpInboundTranslLevelTable OBJECT-TYPE
	SYNTAX      SEQUENCE OF RewriteTranslationsCountUdpInboundTranslLevelEntry
	MAX-ACCESS  not-accessible
	STATUS      current
	DESCRIPTION
	"Table for rewriteTranslationsCountUdpInboundTransl"
	::={rewriteTranslationsCountUdpInboundTransl 4}

rewriteTranslationsCountUdpInboundTranslLevelEntry OBJECT-TYPE
	SYNTAX      RewriteTranslationsCountUdpInboundTranslLevelEntry
	MAX-ACCESS  not-accessible
	STATUS      current
	DESCRIPTION
	"Table entry for rewriteTranslationsCountUdpInboundTransl"
	INDEX { rewriteTranslationsCountUdpInboundTranslLevelName }
	::={rewriteTranslationsCountUdpInboundTranslLevelTable 1}

RewriteTranslationsCountUdpInboundTranslLevelEntry ::=
	SEQUENCE {
		rewriteTranslationsCountUdpInboundTranslLevelName	DisplayString,
		rewriteTranslationsCountUdpInboundTranslLevelVal	CounterBasedGauge64,
		rewriteTranslationsCountUdpInboundTranslLevelMax	CounterBasedGauge64
	}

rewriteTranslationsCountUdpInboundTranslLevelName OBJECT-TYPE
	SYNTAX      DisplayString
	MAX-ACCESS  not-accessible
	STATUS      current
	DESCRIPTION
	"Table entry display string for rewriteTranslationsCountUdpInboundTransl"
	::={rewriteTranslationsCountUdpInboundTranslLevelEntry 1}

rewriteTranslationsCountUdpInboundTranslLevelVal OBJECT-TYPE
	SYNTAX	 CounterBasedGauge64
	MAX-ACCESS  read-only
	STATUS      current
	DESCRIPTION
	"Table entry attribute for rewriteTranslationsCountUdpInboundTransl"
	::={rewriteTranslationsCountUdpInboundTranslLevelEntry 2}

rewriteTranslationsCountUdpInboundTranslLevelMax OBJECT-TYPE
	SYNTAX	 CounterBasedGauge64
	MAX-ACCESS  read-only
	STATUS      current
	DESCRIPTION
	"Table entry attribute for rewriteTranslationsCountUdpInboundTransl"
	::={rewriteTranslationsCountUdpInboundTranslLevelEntry 4}


rewriteTranslationsCountIcmpInboundTransl	OBJECT IDENTIFIER ::={rewrite 68}

rewriteTranslationsCountIcmpInboundTranslVal	OBJECT-TYPE
	SYNTAX	 CounterBasedGauge64
	MAX-ACCESS read-only
	STATUS current
	DESCRIPTION "Translations count - ICMP (inbound)"

	::={rewriteTranslationsCountIcmpInboundTransl 1}

rewriteTranslationsCountIcmpInboundTranslMax	OBJECT-TYPE
	SYNTAX	 CounterBasedGauge64
	MAX-ACCESS read-only
	STATUS current
	DESCRIPTION "Translations count - ICMP (inbound)"

	::={rewriteTranslationsCountIcmpInboundTransl 3}

rewriteTranslationsCountIcmpInboundTranslLevelTable OBJECT-TYPE
	SYNTAX      SEQUENCE OF RewriteTranslationsCountIcmpInboundTranslLevelEntry
	MAX-ACCESS  not-accessible
	STATUS      current
	DESCRIPTION
	"Table for rewriteTranslationsCountIcmpInboundTransl"
	::={rewriteTranslationsCountIcmpInboundTransl 4}

rewriteTranslationsCountIcmpInboundTranslLevelEntry OBJECT-TYPE
	SYNTAX      RewriteTranslationsCountIcmpInboundTranslLevelEntry
	MAX-ACCESS  not-accessible
	STATUS      current
	DESCRIPTION
	"Table entry for rewriteTranslationsCountIcmpInboundTransl"
	INDEX { rewriteTranslationsCountIcmpInboundTranslLevelName }
	::={rewriteTranslationsCountIcmpInboundTranslLevelTable 1}

RewriteTranslationsCountIcmpInboundTranslLevelEntry ::=
	SEQUENCE {
		rewriteTranslationsCountIcmpInboundTranslLevelName	DisplayString,
		rewriteTranslationsCountIcmpInboundTranslLevelVal	CounterBasedGauge64,
		rewriteTranslationsCountIcmpInboundTranslLevelMax	CounterBasedGauge64
	}

rewriteTranslationsCountIcmpInboundTranslLevelName OBJECT-TYPE
	SYNTAX      DisplayString
	MAX-ACCESS  not-accessible
	STATUS      current
	DESCRIPTION
	"Table entry display string for rewriteTranslationsCountIcmpInboundTransl"
	::={rewriteTranslationsCountIcmpInboundTranslLevelEntry 1}

rewriteTranslationsCountIcmpInboundTranslLevelVal OBJECT-TYPE
	SYNTAX	 CounterBasedGauge64
	MAX-ACCESS  read-only
	STATUS      current
	DESCRIPTION
	"Table entry attribute for rewriteTranslationsCountIcmpInboundTransl"
	::={rewriteTranslationsCountIcmpInboundTranslLevelEntry 2}

rewriteTranslationsCountIcmpInboundTranslLevelMax OBJECT-TYPE
	SYNTAX	 CounterBasedGauge64
	MAX-ACCESS  read-only
	STATUS      current
	DESCRIPTION
	"Table entry attribute for rewriteTranslationsCountIcmpInboundTransl"
	::={rewriteTranslationsCountIcmpInboundTranslLevelEntry 4}


rewriteTranslationCreationFailureNoObjectInboundTransl	OBJECT IDENTIFIER ::={rewrite 69}

rewriteTranslationCreationFailureNoObjectInboundTranslVal	OBJECT-TYPE
	SYNTAX	 Counter64
	MAX-ACCESS read-only
	STATUS current
	DESCRIPTION "Translation creation failure (no object, inbound)"

	::={rewriteTranslationCreationFailureNoObjectInboundTransl 1}

rewriteTranslationCreationFailureNoObjectInboundTranslMom	OBJECT-TYPE
	SYNTAX	 CounterBasedGauge64
	MAX-ACCESS read-only
	STATUS current
	DESCRIPTION "Translation creation failure (no object, inbound)"

	::={rewriteTranslationCreationFailureNoObjectInboundTransl 2}

rewriteTranslationCreationFailureNoObjectInboundTranslMax	OBJECT-TYPE
	SYNTAX	 CounterBasedGauge64
	MAX-ACCESS read-only
	STATUS current
	DESCRIPTION "Translation creation failure (no object, inbound)"

	::={rewriteTranslationCreationFailureNoObjectInboundTransl 3}

rewriteTranslationCreationFailureNoObjectInboundTranslLevelTable OBJECT-TYPE
	SYNTAX      SEQUENCE OF RewriteTranslationCreationFailureNoObjectInboundTranslLevelEntry
	MAX-ACCESS  not-accessible
	STATUS      current
	DESCRIPTION
	"Table for rewriteTranslationCreationFailureNoObjectInboundTransl"
	::={rewriteTranslationCreationFailureNoObjectInboundTransl 4}

rewriteTranslationCreationFailureNoObjectInboundTranslLevelEntry OBJECT-TYPE
	SYNTAX      RewriteTranslationCreationFailureNoObjectInboundTranslLevelEntry
	MAX-ACCESS  not-accessible
	STATUS      current
	DESCRIPTION
	"Table entry for rewriteTranslationCreationFailureNoObjectInboundTransl"
	INDEX { rewriteTranslationCreationFailureNoObjectInboundTranslLevelName }
	::={rewriteTranslationCreationFailureNoObjectInboundTranslLevelTable 1}

RewriteTranslationCreationFailureNoObjectInboundTranslLevelEntry ::=
	SEQUENCE {
		rewriteTranslationCreationFailureNoObjectInboundTranslLevelName	DisplayString,
		rewriteTranslationCreationFailureNoObjectInboundTranslLevelVal	Counter64,
		rewriteTranslationCreationFailureNoObjectInboundTranslLevelMom	CounterBasedGauge64,
		rewriteTranslationCreationFailureNoObjectInboundTranslLevelMax	CounterBasedGauge64
	}

rewriteTranslationCreationFailureNoObjectInboundTranslLevelName OBJECT-TYPE
	SYNTAX      DisplayString
	MAX-ACCESS  not-accessible
	STATUS      current
	DESCRIPTION
	"Table entry display string for rewriteTranslationCreationFailureNoObjectInboundTransl"
	::={rewriteTranslationCreationFailureNoObjectInboundTranslLevelEntry 1}

rewriteTranslationCreationFailureNoObjectInboundTranslLevelVal OBJECT-TYPE
	SYNTAX	 Counter64
	MAX-ACCESS  read-only
	STATUS      current
	DESCRIPTION
	"Table entry attribute for rewriteTranslationCreationFailureNoObjectInboundTransl"
	::={rewriteTranslationCreationFailureNoObjectInboundTranslLevelEntry 2}

rewriteTranslationCreationFailureNoObjectInboundTranslLevelMom OBJECT-TYPE
	SYNTAX	 CounterBasedGauge64
	MAX-ACCESS  read-only
	STATUS      current
	DESCRIPTION
	"Table entry attribute for rewriteTranslationCreationFailureNoObjectInboundTransl"
	::={rewriteTranslationCreationFailureNoObjectInboundTranslLevelEntry 3}

rewriteTranslationCreationFailureNoObjectInboundTranslLevelMax OBJECT-TYPE
	SYNTAX	 CounterBasedGauge64
	MAX-ACCESS  read-only
	STATUS      current
	DESCRIPTION
	"Table entry attribute for rewriteTranslationCreationFailureNoObjectInboundTransl"
	::={rewriteTranslationCreationFailureNoObjectInboundTranslLevelEntry 4}


rewriteTransCreateFailResInbTrans	OBJECT IDENTIFIER ::={rewrite 70}

rewriteTransCreateFailResInbTransVal	OBJECT-TYPE
	SYNTAX	 Counter64
	MAX-ACCESS read-only
	STATUS current
	DESCRIPTION "Translation creation failure (resources, inbound)"

	::={rewriteTransCreateFailResInbTrans 1}

rewriteTransCreateFailResInbTransMom	OBJECT-TYPE
	SYNTAX	 CounterBasedGauge64
	MAX-ACCESS read-only
	STATUS current
	DESCRIPTION "Translation creation failure (resources, inbound)"

	::={rewriteTransCreateFailResInbTrans 2}

rewriteTransCreateFailResInbTransMax	OBJECT-TYPE
	SYNTAX	 CounterBasedGauge64
	MAX-ACCESS read-only
	STATUS current
	DESCRIPTION "Translation creation failure (resources, inbound)"

	::={rewriteTransCreateFailResInbTrans 3}

rewriteTransCreateFailResInbTransLevelTable OBJECT-TYPE
	SYNTAX      SEQUENCE OF RewriteTransCreateFailResInbTransLevelEntry
	MAX-ACCESS  not-accessible
	STATUS      current
	DESCRIPTION
	"Table for rewriteTransCreateFailResInbTrans"
	::={rewriteTransCreateFailResInbTrans 4}

rewriteTransCreateFailResInbTransLevelEntry OBJECT-TYPE
	SYNTAX      RewriteTransCreateFailResInbTransLevelEntry
	MAX-ACCESS  not-accessible
	STATUS      current
	DESCRIPTION
	"Table entry for rewriteTransCreateFailResInbTrans"
	INDEX { rewriteTransCreateFailResInbTransLevelName }
	::={rewriteTransCreateFailResInbTransLevelTable 1}

RewriteTransCreateFailResInbTransLevelEntry ::=
	SEQUENCE {
		rewriteTransCreateFailResInbTransLevelName	DisplayString,
		rewriteTransCreateFailResInbTransLevelVal	Counter64,
		rewriteTransCreateFailResInbTransLevelMom	CounterBasedGauge64,
		rewriteTransCreateFailResInbTransLevelMax	CounterBasedGauge64
	}

rewriteTransCreateFailResInbTransLevelName OBJECT-TYPE
	SYNTAX      DisplayString
	MAX-ACCESS  not-accessible
	STATUS      current
	DESCRIPTION
	"Table entry display string for rewriteTransCreateFailResInbTrans"
	::={rewriteTransCreateFailResInbTransLevelEntry 1}

rewriteTransCreateFailResInbTransLevelVal OBJECT-TYPE
	SYNTAX	 Counter64
	MAX-ACCESS  read-only
	STATUS      current
	DESCRIPTION
	"Table entry attribute for rewriteTransCreateFailResInbTrans"
	::={rewriteTransCreateFailResInbTransLevelEntry 2}

rewriteTransCreateFailResInbTransLevelMom OBJECT-TYPE
	SYNTAX	 CounterBasedGauge64
	MAX-ACCESS  read-only
	STATUS      current
	DESCRIPTION
	"Table entry attribute for rewriteTransCreateFailResInbTrans"
	::={rewriteTransCreateFailResInbTransLevelEntry 3}

rewriteTransCreateFailResInbTransLevelMax OBJECT-TYPE
	SYNTAX	 CounterBasedGauge64
	MAX-ACCESS  read-only
	STATUS      current
	DESCRIPTION
	"Table entry attribute for rewriteTransCreateFailResInbTrans"
	::={rewriteTransCreateFailResInbTransLevelEntry 4}


rewriteTranslationCreationFailureProtocolInboundTransl	OBJECT IDENTIFIER ::={rewrite 71}

rewriteTranslationCreationFailureProtocolInboundTranslVal	OBJECT-TYPE
	SYNTAX	 Counter64
	MAX-ACCESS read-only
	STATUS current
	DESCRIPTION "Translation creation failure (incompatible L4 protocol, inbound)"

	::={rewriteTranslationCreationFailureProtocolInboundTransl 1}

rewriteTranslationCreationFailureProtocolInboundTranslMom	OBJECT-TYPE
	SYNTAX	 CounterBasedGauge64
	MAX-ACCESS read-only
	STATUS current
	DESCRIPTION "Translation creation failure (incompatible L4 protocol, inbound)"

	::={rewriteTranslationCreationFailureProtocolInboundTransl 2}

rewriteTranslationCreationFailureProtocolInboundTranslMax	OBJECT-TYPE
	SYNTAX	 CounterBasedGauge64
	MAX-ACCESS read-only
	STATUS current
	DESCRIPTION "Translation creation failure (incompatible L4 protocol, inbound)"

	::={rewriteTranslationCreationFailureProtocolInboundTransl 3}

rewriteTranslationCreationFailureProtocolInboundTranslLevelTable OBJECT-TYPE
	SYNTAX      SEQUENCE OF RewriteTranslationCreationFailureProtocolInboundTranslLevelEntry
	MAX-ACCESS  not-accessible
	STATUS      current
	DESCRIPTION
	"Table for rewriteTranslationCreationFailureProtocolInboundTransl"
	::={rewriteTranslationCreationFailureProtocolInboundTransl 4}

rewriteTranslationCreationFailureProtocolInboundTranslLevelEntry OBJECT-TYPE
	SYNTAX      RewriteTranslationCreationFailureProtocolInboundTranslLevelEntry
	MAX-ACCESS  not-accessible
	STATUS      current
	DESCRIPTION
	"Table entry for rewriteTranslationCreationFailureProtocolInboundTransl"
	INDEX { rewriteTranslationCreationFailureProtocolInboundTranslLevelName }
	::={rewriteTranslationCreationFailureProtocolInboundTranslLevelTable 1}

RewriteTranslationCreationFailureProtocolInboundTranslLevelEntry ::=
	SEQUENCE {
		rewriteTranslationCreationFailureProtocolInboundTranslLevelName	DisplayString,
		rewriteTranslationCreationFailureProtocolInboundTranslLevelVal	Counter64,
		rewriteTranslationCreationFailureProtocolInboundTranslLevelMom	CounterBasedGauge64,
		rewriteTranslationCreationFailureProtocolInboundTranslLevelMax	CounterBasedGauge64
	}

rewriteTranslationCreationFailureProtocolInboundTranslLevelName OBJECT-TYPE
	SYNTAX      DisplayString
	MAX-ACCESS  not-accessible
	STATUS      current
	DESCRIPTION
	"Table entry display string for rewriteTranslationCreationFailureProtocolInboundTransl"
	::={rewriteTranslationCreationFailureProtocolInboundTranslLevelEntry 1}

rewriteTranslationCreationFailureProtocolInboundTranslLevelVal OBJECT-TYPE
	SYNTAX	 Counter64
	MAX-ACCESS  read-only
	STATUS      current
	DESCRIPTION
	"Table entry attribute for rewriteTranslationCreationFailureProtocolInboundTransl"
	::={rewriteTranslationCreationFailureProtocolInboundTranslLevelEntry 2}

rewriteTranslationCreationFailureProtocolInboundTranslLevelMom OBJECT-TYPE
	SYNTAX	 CounterBasedGauge64
	MAX-ACCESS  read-only
	STATUS      current
	DESCRIPTION
	"Table entry attribute for rewriteTranslationCreationFailureProtocolInboundTransl"
	::={rewriteTranslationCreationFailureProtocolInboundTranslLevelEntry 3}

rewriteTranslationCreationFailureProtocolInboundTranslLevelMax OBJECT-TYPE
	SYNTAX	 CounterBasedGauge64
	MAX-ACCESS  read-only
	STATUS      current
	DESCRIPTION
	"Table entry attribute for rewriteTranslationCreationFailureProtocolInboundTransl"
	::={rewriteTranslationCreationFailureProtocolInboundTranslLevelEntry 4}


rewriteTransCreateFailCollInbTrans	OBJECT IDENTIFIER ::={rewrite 72}

rewriteTransCreateFailCollInbTransVal	OBJECT-TYPE
	SYNTAX	 Counter64
	MAX-ACCESS read-only
	STATUS current
	DESCRIPTION "Translation creation failure (collision, inbound)"

	::={rewriteTransCreateFailCollInbTrans 1}

rewriteTransCreateFailCollInbTransMom	OBJECT-TYPE
	SYNTAX	 CounterBasedGauge64
	MAX-ACCESS read-only
	STATUS current
	DESCRIPTION "Translation creation failure (collision, inbound)"

	::={rewriteTransCreateFailCollInbTrans 2}

rewriteTransCreateFailCollInbTransMax	OBJECT-TYPE
	SYNTAX	 CounterBasedGauge64
	MAX-ACCESS read-only
	STATUS current
	DESCRIPTION "Translation creation failure (collision, inbound)"

	::={rewriteTransCreateFailCollInbTrans 3}

rewriteTransCreateFailCollInbTransLevelTable OBJECT-TYPE
	SYNTAX      SEQUENCE OF RewriteTransCreateFailCollInbTransLevelEntry
	MAX-ACCESS  not-accessible
	STATUS      current
	DESCRIPTION
	"Table for rewriteTransCreateFailCollInbTrans"
	::={rewriteTransCreateFailCollInbTrans 4}

rewriteTransCreateFailCollInbTransLevelEntry OBJECT-TYPE
	SYNTAX      RewriteTransCreateFailCollInbTransLevelEntry
	MAX-ACCESS  not-accessible
	STATUS      current
	DESCRIPTION
	"Table entry for rewriteTransCreateFailCollInbTrans"
	INDEX { rewriteTransCreateFailCollInbTransLevelName }
	::={rewriteTransCreateFailCollInbTransLevelTable 1}

RewriteTransCreateFailCollInbTransLevelEntry ::=
	SEQUENCE {
		rewriteTransCreateFailCollInbTransLevelName	DisplayString,
		rewriteTransCreateFailCollInbTransLevelVal	Counter64,
		rewriteTransCreateFailCollInbTransLevelMom	CounterBasedGauge64,
		rewriteTransCreateFailCollInbTransLevelMax	CounterBasedGauge64
	}

rewriteTransCreateFailCollInbTransLevelName OBJECT-TYPE
	SYNTAX      DisplayString
	MAX-ACCESS  not-accessible
	STATUS      current
	DESCRIPTION
	"Table entry display string for rewriteTransCreateFailCollInbTrans"
	::={rewriteTransCreateFailCollInbTransLevelEntry 1}

rewriteTransCreateFailCollInbTransLevelVal OBJECT-TYPE
	SYNTAX	 Counter64
	MAX-ACCESS  read-only
	STATUS      current
	DESCRIPTION
	"Table entry attribute for rewriteTransCreateFailCollInbTrans"
	::={rewriteTransCreateFailCollInbTransLevelEntry 2}

rewriteTransCreateFailCollInbTransLevelMom OBJECT-TYPE
	SYNTAX	 CounterBasedGauge64
	MAX-ACCESS  read-only
	STATUS      current
	DESCRIPTION
	"Table entry attribute for rewriteTransCreateFailCollInbTrans"
	::={rewriteTransCreateFailCollInbTransLevelEntry 3}

rewriteTransCreateFailCollInbTransLevelMax OBJECT-TYPE
	SYNTAX	 CounterBasedGauge64
	MAX-ACCESS  read-only
	STATUS      current
	DESCRIPTION
	"Table entry attribute for rewriteTransCreateFailCollInbTrans"
	::={rewriteTransCreateFailCollInbTransLevelEntry 4}


rewriteTransCreateFailNoMapInbTrans	OBJECT IDENTIFIER ::={rewrite 73}

rewriteTransCreateFailNoMapInbTransVal	OBJECT-TYPE
	SYNTAX	 Counter64
	MAX-ACCESS read-only
	STATUS current
	DESCRIPTION "Translation creation failure (No mapping found, inbound)"

	::={rewriteTransCreateFailNoMapInbTrans 1}

rewriteTransCreateFailNoMapInbTransMom	OBJECT-TYPE
	SYNTAX	 CounterBasedGauge64
	MAX-ACCESS read-only
	STATUS current
	DESCRIPTION "Translation creation failure (No mapping found, inbound)"

	::={rewriteTransCreateFailNoMapInbTrans 2}

rewriteTransCreateFailNoMapInbTransMax	OBJECT-TYPE
	SYNTAX	 CounterBasedGauge64
	MAX-ACCESS read-only
	STATUS current
	DESCRIPTION "Translation creation failure (No mapping found, inbound)"

	::={rewriteTransCreateFailNoMapInbTrans 3}

rewriteTransCreateFailNoMapInbTransLevelTable OBJECT-TYPE
	SYNTAX      SEQUENCE OF RewriteTransCreateFailNoMapInbTransLevelEntry
	MAX-ACCESS  not-accessible
	STATUS      current
	DESCRIPTION
	"Table for rewriteTransCreateFailNoMapInbTrans"
	::={rewriteTransCreateFailNoMapInbTrans 4}

rewriteTransCreateFailNoMapInbTransLevelEntry OBJECT-TYPE
	SYNTAX      RewriteTransCreateFailNoMapInbTransLevelEntry
	MAX-ACCESS  not-accessible
	STATUS      current
	DESCRIPTION
	"Table entry for rewriteTransCreateFailNoMapInbTrans"
	INDEX { rewriteTransCreateFailNoMapInbTransLevelName }
	::={rewriteTransCreateFailNoMapInbTransLevelTable 1}

RewriteTransCreateFailNoMapInbTransLevelEntry ::=
	SEQUENCE {
		rewriteTransCreateFailNoMapInbTransLevelName	DisplayString,
		rewriteTransCreateFailNoMapInbTransLevelVal	Counter64,
		rewriteTransCreateFailNoMapInbTransLevelMom	CounterBasedGauge64,
		rewriteTransCreateFailNoMapInbTransLevelMax	CounterBasedGauge64
	}

rewriteTransCreateFailNoMapInbTransLevelName OBJECT-TYPE
	SYNTAX      DisplayString
	MAX-ACCESS  not-accessible
	STATUS      current
	DESCRIPTION
	"Table entry display string for rewriteTransCreateFailNoMapInbTrans"
	::={rewriteTransCreateFailNoMapInbTransLevelEntry 1}

rewriteTransCreateFailNoMapInbTransLevelVal OBJECT-TYPE
	SYNTAX	 Counter64
	MAX-ACCESS  read-only
	STATUS      current
	DESCRIPTION
	"Table entry attribute for rewriteTransCreateFailNoMapInbTrans"
	::={rewriteTransCreateFailNoMapInbTransLevelEntry 2}

rewriteTransCreateFailNoMapInbTransLevelMom OBJECT-TYPE
	SYNTAX	 CounterBasedGauge64
	MAX-ACCESS  read-only
	STATUS      current
	DESCRIPTION
	"Table entry attribute for rewriteTransCreateFailNoMapInbTrans"
	::={rewriteTransCreateFailNoMapInbTransLevelEntry 3}

rewriteTransCreateFailNoMapInbTransLevelMax OBJECT-TYPE
	SYNTAX	 CounterBasedGauge64
	MAX-ACCESS  read-only
	STATUS      current
	DESCRIPTION
	"Table entry attribute for rewriteTransCreateFailNoMapInbTrans"
	::={rewriteTransCreateFailNoMapInbTransLevelEntry 4}


rewriteTransCreateFailNotAllowInbTrans	OBJECT IDENTIFIER ::={rewrite 74}

rewriteTransCreateFailNotAllowInbTransVal	OBJECT-TYPE
	SYNTAX	 Counter64
	MAX-ACCESS read-only
	STATUS current
	DESCRIPTION "Translation creation failure (not allowed, inbound)"

	::={rewriteTransCreateFailNotAllowInbTrans 1}

rewriteTransCreateFailNotAllowInbTransMom	OBJECT-TYPE
	SYNTAX	 CounterBasedGauge64
	MAX-ACCESS read-only
	STATUS current
	DESCRIPTION "Translation creation failure (not allowed, inbound)"

	::={rewriteTransCreateFailNotAllowInbTrans 2}

rewriteTransCreateFailNotAllowInbTransMax	OBJECT-TYPE
	SYNTAX	 CounterBasedGauge64
	MAX-ACCESS read-only
	STATUS current
	DESCRIPTION "Translation creation failure (not allowed, inbound)"

	::={rewriteTransCreateFailNotAllowInbTrans 3}

rewriteTransCreateFailNotAllowInbTransLevelTable OBJECT-TYPE
	SYNTAX      SEQUENCE OF RewriteTransCreateFailNotAllowInbTransLevelEntry
	MAX-ACCESS  not-accessible
	STATUS      current
	DESCRIPTION
	"Table for rewriteTransCreateFailNotAllowInbTrans"
	::={rewriteTransCreateFailNotAllowInbTrans 4}

rewriteTransCreateFailNotAllowInbTransLevelEntry OBJECT-TYPE
	SYNTAX      RewriteTransCreateFailNotAllowInbTransLevelEntry
	MAX-ACCESS  not-accessible
	STATUS      current
	DESCRIPTION
	"Table entry for rewriteTransCreateFailNotAllowInbTrans"
	INDEX { rewriteTransCreateFailNotAllowInbTransLevelName }
	::={rewriteTransCreateFailNotAllowInbTransLevelTable 1}

RewriteTransCreateFailNotAllowInbTransLevelEntry ::=
	SEQUENCE {
		rewriteTransCreateFailNotAllowInbTransLevelName	DisplayString,
		rewriteTransCreateFailNotAllowInbTransLevelVal	Counter64,
		rewriteTransCreateFailNotAllowInbTransLevelMom	CounterBasedGauge64,
		rewriteTransCreateFailNotAllowInbTransLevelMax	CounterBasedGauge64
	}

rewriteTransCreateFailNotAllowInbTransLevelName OBJECT-TYPE
	SYNTAX      DisplayString
	MAX-ACCESS  not-accessible
	STATUS      current
	DESCRIPTION
	"Table entry display string for rewriteTransCreateFailNotAllowInbTrans"
	::={rewriteTransCreateFailNotAllowInbTransLevelEntry 1}

rewriteTransCreateFailNotAllowInbTransLevelVal OBJECT-TYPE
	SYNTAX	 Counter64
	MAX-ACCESS  read-only
	STATUS      current
	DESCRIPTION
	"Table entry attribute for rewriteTransCreateFailNotAllowInbTrans"
	::={rewriteTransCreateFailNotAllowInbTransLevelEntry 2}

rewriteTransCreateFailNotAllowInbTransLevelMom OBJECT-TYPE
	SYNTAX	 CounterBasedGauge64
	MAX-ACCESS  read-only
	STATUS      current
	DESCRIPTION
	"Table entry attribute for rewriteTransCreateFailNotAllowInbTrans"
	::={rewriteTransCreateFailNotAllowInbTransLevelEntry 3}

rewriteTransCreateFailNotAllowInbTransLevelMax OBJECT-TYPE
	SYNTAX	 CounterBasedGauge64
	MAX-ACCESS  read-only
	STATUS      current
	DESCRIPTION
	"Table entry attribute for rewriteTransCreateFailNotAllowInbTrans"
	::={rewriteTransCreateFailNotAllowInbTransLevelEntry 4}


rewriteTranslatedInboundPacketsInboundTransl	OBJECT IDENTIFIER ::={rewrite 76}

rewriteTranslatedInboundPacketsInboundTranslVal	OBJECT-TYPE
	SYNTAX	 Counter64
	MAX-ACCESS read-only
	STATUS current
	DESCRIPTION "Translated inbound packets (inbound)"

	::={rewriteTranslatedInboundPacketsInboundTransl 1}

rewriteTranslatedInboundPacketsInboundTranslMom	OBJECT-TYPE
	SYNTAX	 CounterBasedGauge64
	MAX-ACCESS read-only
	STATUS current
	DESCRIPTION "Translated inbound packets (inbound)"

	::={rewriteTranslatedInboundPacketsInboundTransl 2}

rewriteTranslatedInboundPacketsInboundTranslMax	OBJECT-TYPE
	SYNTAX	 CounterBasedGauge64
	MAX-ACCESS read-only
	STATUS current
	DESCRIPTION "Translated inbound packets (inbound)"

	::={rewriteTranslatedInboundPacketsInboundTransl 3}

rewriteTranslatedInboundPacketsInboundTranslLevelTable OBJECT-TYPE
	SYNTAX      SEQUENCE OF RewriteTranslatedInboundPacketsInboundTranslLevelEntry
	MAX-ACCESS  not-accessible
	STATUS      current
	DESCRIPTION
	"Table for rewriteTranslatedInboundPacketsInboundTransl"
	::={rewriteTranslatedInboundPacketsInboundTransl 4}

rewriteTranslatedInboundPacketsInboundTranslLevelEntry OBJECT-TYPE
	SYNTAX      RewriteTranslatedInboundPacketsInboundTranslLevelEntry
	MAX-ACCESS  not-accessible
	STATUS      current
	DESCRIPTION
	"Table entry for rewriteTranslatedInboundPacketsInboundTransl"
	INDEX { rewriteTranslatedInboundPacketsInboundTranslLevelName }
	::={rewriteTranslatedInboundPacketsInboundTranslLevelTable 1}

RewriteTranslatedInboundPacketsInboundTranslLevelEntry ::=
	SEQUENCE {
		rewriteTranslatedInboundPacketsInboundTranslLevelName	DisplayString,
		rewriteTranslatedInboundPacketsInboundTranslLevelVal	Counter64,
		rewriteTranslatedInboundPacketsInboundTranslLevelMom	CounterBasedGauge64,
		rewriteTranslatedInboundPacketsInboundTranslLevelMax	CounterBasedGauge64
	}

rewriteTranslatedInboundPacketsInboundTranslLevelName OBJECT-TYPE
	SYNTAX      DisplayString
	MAX-ACCESS  not-accessible
	STATUS      current
	DESCRIPTION
	"Table entry display string for rewriteTranslatedInboundPacketsInboundTransl"
	::={rewriteTranslatedInboundPacketsInboundTranslLevelEntry 1}

rewriteTranslatedInboundPacketsInboundTranslLevelVal OBJECT-TYPE
	SYNTAX	 Counter64
	MAX-ACCESS  read-only
	STATUS      current
	DESCRIPTION
	"Table entry attribute for rewriteTranslatedInboundPacketsInboundTransl"
	::={rewriteTranslatedInboundPacketsInboundTranslLevelEntry 2}

rewriteTranslatedInboundPacketsInboundTranslLevelMom OBJECT-TYPE
	SYNTAX	 CounterBasedGauge64
	MAX-ACCESS  read-only
	STATUS      current
	DESCRIPTION
	"Table entry attribute for rewriteTranslatedInboundPacketsInboundTransl"
	::={rewriteTranslatedInboundPacketsInboundTranslLevelEntry 3}

rewriteTranslatedInboundPacketsInboundTranslLevelMax OBJECT-TYPE
	SYNTAX	 CounterBasedGauge64
	MAX-ACCESS  read-only
	STATUS      current
	DESCRIPTION
	"Table entry attribute for rewriteTranslatedInboundPacketsInboundTransl"
	::={rewriteTranslatedInboundPacketsInboundTranslLevelEntry 4}


rewriteTranslatedInboundBytesInboundTransl	OBJECT IDENTIFIER ::={rewrite 77}

rewriteTranslatedInboundBytesInboundTranslVal	OBJECT-TYPE
	SYNTAX	 Counter64
	MAX-ACCESS read-only
	STATUS current
	DESCRIPTION "Translated inbound bytes (inbound)"

	::={rewriteTranslatedInboundBytesInboundTransl 1}

rewriteTranslatedInboundBytesInboundTranslMom	OBJECT-TYPE
	SYNTAX	 CounterBasedGauge64
	MAX-ACCESS read-only
	STATUS current
	DESCRIPTION "Translated inbound bytes (inbound)"

	::={rewriteTranslatedInboundBytesInboundTransl 2}

rewriteTranslatedInboundBytesInboundTranslMax	OBJECT-TYPE
	SYNTAX	 CounterBasedGauge64
	MAX-ACCESS read-only
	STATUS current
	DESCRIPTION "Translated inbound bytes (inbound)"

	::={rewriteTranslatedInboundBytesInboundTransl 3}

rewriteTranslatedInboundBytesInboundTranslLevelTable OBJECT-TYPE
	SYNTAX      SEQUENCE OF RewriteTranslatedInboundBytesInboundTranslLevelEntry
	MAX-ACCESS  not-accessible
	STATUS      current
	DESCRIPTION
	"Table for rewriteTranslatedInboundBytesInboundTransl"
	::={rewriteTranslatedInboundBytesInboundTransl 4}

rewriteTranslatedInboundBytesInboundTranslLevelEntry OBJECT-TYPE
	SYNTAX      RewriteTranslatedInboundBytesInboundTranslLevelEntry
	MAX-ACCESS  not-accessible
	STATUS      current
	DESCRIPTION
	"Table entry for rewriteTranslatedInboundBytesInboundTransl"
	INDEX { rewriteTranslatedInboundBytesInboundTranslLevelName }
	::={rewriteTranslatedInboundBytesInboundTranslLevelTable 1}

RewriteTranslatedInboundBytesInboundTranslLevelEntry ::=
	SEQUENCE {
		rewriteTranslatedInboundBytesInboundTranslLevelName	DisplayString,
		rewriteTranslatedInboundBytesInboundTranslLevelVal	Counter64,
		rewriteTranslatedInboundBytesInboundTranslLevelMom	CounterBasedGauge64,
		rewriteTranslatedInboundBytesInboundTranslLevelMax	CounterBasedGauge64
	}

rewriteTranslatedInboundBytesInboundTranslLevelName OBJECT-TYPE
	SYNTAX      DisplayString
	MAX-ACCESS  not-accessible
	STATUS      current
	DESCRIPTION
	"Table entry display string for rewriteTranslatedInboundBytesInboundTransl"
	::={rewriteTranslatedInboundBytesInboundTranslLevelEntry 1}

rewriteTranslatedInboundBytesInboundTranslLevelVal OBJECT-TYPE
	SYNTAX	 Counter64
	MAX-ACCESS  read-only
	STATUS      current
	DESCRIPTION
	"Table entry attribute for rewriteTranslatedInboundBytesInboundTransl"
	::={rewriteTranslatedInboundBytesInboundTranslLevelEntry 2}

rewriteTranslatedInboundBytesInboundTranslLevelMom OBJECT-TYPE
	SYNTAX	 CounterBasedGauge64
	MAX-ACCESS  read-only
	STATUS      current
	DESCRIPTION
	"Table entry attribute for rewriteTranslatedInboundBytesInboundTransl"
	::={rewriteTranslatedInboundBytesInboundTranslLevelEntry 3}

rewriteTranslatedInboundBytesInboundTranslLevelMax OBJECT-TYPE
	SYNTAX	 CounterBasedGauge64
	MAX-ACCESS  read-only
	STATUS      current
	DESCRIPTION
	"Table entry attribute for rewriteTranslatedInboundBytesInboundTransl"
	::={rewriteTranslatedInboundBytesInboundTranslLevelEntry 4}


rewriteTranslatedOutboundPacketsInboundTransl	OBJECT IDENTIFIER ::={rewrite 78}

rewriteTranslatedOutboundPacketsInboundTranslVal	OBJECT-TYPE
	SYNTAX	 Counter64
	MAX-ACCESS read-only
	STATUS current
	DESCRIPTION "Translated outbound packets (inbound)"

	::={rewriteTranslatedOutboundPacketsInboundTransl 1}

rewriteTranslatedOutboundPacketsInboundTranslMom	OBJECT-TYPE
	SYNTAX	 CounterBasedGauge64
	MAX-ACCESS read-only
	STATUS current
	DESCRIPTION "Translated outbound packets (inbound)"

	::={rewriteTranslatedOutboundPacketsInboundTransl 2}

rewriteTranslatedOutboundPacketsInboundTranslMax	OBJECT-TYPE
	SYNTAX	 CounterBasedGauge64
	MAX-ACCESS read-only
	STATUS current
	DESCRIPTION "Translated outbound packets (inbound)"

	::={rewriteTranslatedOutboundPacketsInboundTransl 3}

rewriteTranslatedOutboundPacketsInboundTranslLevelTable OBJECT-TYPE
	SYNTAX      SEQUENCE OF RewriteTranslatedOutboundPacketsInboundTranslLevelEntry
	MAX-ACCESS  not-accessible
	STATUS      current
	DESCRIPTION
	"Table for rewriteTranslatedOutboundPacketsInboundTransl"
	::={rewriteTranslatedOutboundPacketsInboundTransl 4}

rewriteTranslatedOutboundPacketsInboundTranslLevelEntry OBJECT-TYPE
	SYNTAX      RewriteTranslatedOutboundPacketsInboundTranslLevelEntry
	MAX-ACCESS  not-accessible
	STATUS      current
	DESCRIPTION
	"Table entry for rewriteTranslatedOutboundPacketsInboundTransl"
	INDEX { rewriteTranslatedOutboundPacketsInboundTranslLevelName }
	::={rewriteTranslatedOutboundPacketsInboundTranslLevelTable 1}

RewriteTranslatedOutboundPacketsInboundTranslLevelEntry ::=
	SEQUENCE {
		rewriteTranslatedOutboundPacketsInboundTranslLevelName	DisplayString,
		rewriteTranslatedOutboundPacketsInboundTranslLevelVal	Counter64,
		rewriteTranslatedOutboundPacketsInboundTranslLevelMom	CounterBasedGauge64,
		rewriteTranslatedOutboundPacketsInboundTranslLevelMax	CounterBasedGauge64
	}

rewriteTranslatedOutboundPacketsInboundTranslLevelName OBJECT-TYPE
	SYNTAX      DisplayString
	MAX-ACCESS  not-accessible
	STATUS      current
	DESCRIPTION
	"Table entry display string for rewriteTranslatedOutboundPacketsInboundTransl"
	::={rewriteTranslatedOutboundPacketsInboundTranslLevelEntry 1}

rewriteTranslatedOutboundPacketsInboundTranslLevelVal OBJECT-TYPE
	SYNTAX	 Counter64
	MAX-ACCESS  read-only
	STATUS      current
	DESCRIPTION
	"Table entry attribute for rewriteTranslatedOutboundPacketsInboundTransl"
	::={rewriteTranslatedOutboundPacketsInboundTranslLevelEntry 2}

rewriteTranslatedOutboundPacketsInboundTranslLevelMom OBJECT-TYPE
	SYNTAX	 CounterBasedGauge64
	MAX-ACCESS  read-only
	STATUS      current
	DESCRIPTION
	"Table entry attribute for rewriteTranslatedOutboundPacketsInboundTransl"
	::={rewriteTranslatedOutboundPacketsInboundTranslLevelEntry 3}

rewriteTranslatedOutboundPacketsInboundTranslLevelMax OBJECT-TYPE
	SYNTAX	 CounterBasedGauge64
	MAX-ACCESS  read-only
	STATUS      current
	DESCRIPTION
	"Table entry attribute for rewriteTranslatedOutboundPacketsInboundTransl"
	::={rewriteTranslatedOutboundPacketsInboundTranslLevelEntry 4}


rewriteTranslatedOutboundBytesInboundTransl	OBJECT IDENTIFIER ::={rewrite 79}

rewriteTranslatedOutboundBytesInboundTranslVal	OBJECT-TYPE
	SYNTAX	 Counter64
	MAX-ACCESS read-only
	STATUS current
	DESCRIPTION "Translated outbound bytes (inbound)"

	::={rewriteTranslatedOutboundBytesInboundTransl 1}

rewriteTranslatedOutboundBytesInboundTranslMom	OBJECT-TYPE
	SYNTAX	 CounterBasedGauge64
	MAX-ACCESS read-only
	STATUS current
	DESCRIPTION "Translated outbound bytes (inbound)"

	::={rewriteTranslatedOutboundBytesInboundTransl 2}

rewriteTranslatedOutboundBytesInboundTranslMax	OBJECT-TYPE
	SYNTAX	 CounterBasedGauge64
	MAX-ACCESS read-only
	STATUS current
	DESCRIPTION "Translated outbound bytes (inbound)"

	::={rewriteTranslatedOutboundBytesInboundTransl 3}

rewriteTranslatedOutboundBytesInboundTranslLevelTable OBJECT-TYPE
	SYNTAX      SEQUENCE OF RewriteTranslatedOutboundBytesInboundTranslLevelEntry
	MAX-ACCESS  not-accessible
	STATUS      current
	DESCRIPTION
	"Table for rewriteTranslatedOutboundBytesInboundTransl"
	::={rewriteTranslatedOutboundBytesInboundTransl 4}

rewriteTranslatedOutboundBytesInboundTranslLevelEntry OBJECT-TYPE
	SYNTAX      RewriteTranslatedOutboundBytesInboundTranslLevelEntry
	MAX-ACCESS  not-accessible
	STATUS      current
	DESCRIPTION
	"Table entry for rewriteTranslatedOutboundBytesInboundTransl"
	INDEX { rewriteTranslatedOutboundBytesInboundTranslLevelName }
	::={rewriteTranslatedOutboundBytesInboundTranslLevelTable 1}

RewriteTranslatedOutboundBytesInboundTranslLevelEntry ::=
	SEQUENCE {
		rewriteTranslatedOutboundBytesInboundTranslLevelName	DisplayString,
		rewriteTranslatedOutboundBytesInboundTranslLevelVal	Counter64,
		rewriteTranslatedOutboundBytesInboundTranslLevelMom	CounterBasedGauge64,
		rewriteTranslatedOutboundBytesInboundTranslLevelMax	CounterBasedGauge64
	}

rewriteTranslatedOutboundBytesInboundTranslLevelName OBJECT-TYPE
	SYNTAX      DisplayString
	MAX-ACCESS  not-accessible
	STATUS      current
	DESCRIPTION
	"Table entry display string for rewriteTranslatedOutboundBytesInboundTransl"
	::={rewriteTranslatedOutboundBytesInboundTranslLevelEntry 1}

rewriteTranslatedOutboundBytesInboundTranslLevelVal OBJECT-TYPE
	SYNTAX	 Counter64
	MAX-ACCESS  read-only
	STATUS      current
	DESCRIPTION
	"Table entry attribute for rewriteTranslatedOutboundBytesInboundTransl"
	::={rewriteTranslatedOutboundBytesInboundTranslLevelEntry 2}

rewriteTranslatedOutboundBytesInboundTranslLevelMom OBJECT-TYPE
	SYNTAX	 CounterBasedGauge64
	MAX-ACCESS  read-only
	STATUS      current
	DESCRIPTION
	"Table entry attribute for rewriteTranslatedOutboundBytesInboundTransl"
	::={rewriteTranslatedOutboundBytesInboundTranslLevelEntry 3}

rewriteTranslatedOutboundBytesInboundTranslLevelMax OBJECT-TYPE
	SYNTAX	 CounterBasedGauge64
	MAX-ACCESS  read-only
	STATUS      current
	DESCRIPTION
	"Table entry attribute for rewriteTranslatedOutboundBytesInboundTransl"
	::={rewriteTranslatedOutboundBytesInboundTranslLevelEntry 4}


rewriteSyncedMappingsCount	OBJECT IDENTIFIER ::={rewrite 80}

rewriteSyncedMappingsCountVal	OBJECT-TYPE
	SYNTAX	 CounterBasedGauge64
	MAX-ACCESS read-only
	STATUS current
	DESCRIPTION "Synchronized mappings count"

	::={rewriteSyncedMappingsCount 1}

rewriteSyncedMappingsCountMax	OBJECT-TYPE
	SYNTAX	 CounterBasedGauge64
	MAX-ACCESS read-only
	STATUS current
	DESCRIPTION "Synchronized mappings count"

	::={rewriteSyncedMappingsCount 3}

rewriteSyncedMappingsCountLevelTable OBJECT-TYPE
	SYNTAX      SEQUENCE OF RewriteSyncedMappingsCountLevelEntry
	MAX-ACCESS  not-accessible
	STATUS      current
	DESCRIPTION
	"Table for rewriteSyncedMappingsCount"
	::={rewriteSyncedMappingsCount 4}

rewriteSyncedMappingsCountLevelEntry OBJECT-TYPE
	SYNTAX      RewriteSyncedMappingsCountLevelEntry
	MAX-ACCESS  not-accessible
	STATUS      current
	DESCRIPTION
	"Table entry for rewriteSyncedMappingsCount"
	INDEX { rewriteSyncedMappingsCountLevelName }
	::={rewriteSyncedMappingsCountLevelTable 1}

RewriteSyncedMappingsCountLevelEntry ::=
	SEQUENCE {
		rewriteSyncedMappingsCountLevelName	DisplayString,
		rewriteSyncedMappingsCountLevelVal	CounterBasedGauge64,
		rewriteSyncedMappingsCountLevelMax	CounterBasedGauge64
	}

rewriteSyncedMappingsCountLevelName OBJECT-TYPE
	SYNTAX      DisplayString
	MAX-ACCESS  not-accessible
	STATUS      current
	DESCRIPTION
	"Table entry display string for rewriteSyncedMappingsCount"
	::={rewriteSyncedMappingsCountLevelEntry 1}

rewriteSyncedMappingsCountLevelVal OBJECT-TYPE
	SYNTAX	 CounterBasedGauge64
	MAX-ACCESS  read-only
	STATUS      current
	DESCRIPTION
	"Table entry attribute for rewriteSyncedMappingsCount"
	::={rewriteSyncedMappingsCountLevelEntry 2}

rewriteSyncedMappingsCountLevelMax OBJECT-TYPE
	SYNTAX	 CounterBasedGauge64
	MAX-ACCESS  read-only
	STATUS      current
	DESCRIPTION
	"Table entry attribute for rewriteSyncedMappingsCount"
	::={rewriteSyncedMappingsCountLevelEntry 4}


rewriteSyncedMappingsCountTcp	OBJECT IDENTIFIER ::={rewrite 81}

rewriteSyncedMappingsCountTcpVal	OBJECT-TYPE
	SYNTAX	 CounterBasedGauge64
	MAX-ACCESS read-only
	STATUS current
	DESCRIPTION "Synchronized mappings count - TCP"

	::={rewriteSyncedMappingsCountTcp 1}

rewriteSyncedMappingsCountTcpMax	OBJECT-TYPE
	SYNTAX	 CounterBasedGauge64
	MAX-ACCESS read-only
	STATUS current
	DESCRIPTION "Synchronized mappings count - TCP"

	::={rewriteSyncedMappingsCountTcp 3}

rewriteSyncedMappingsCountTcpLevelTable OBJECT-TYPE
	SYNTAX      SEQUENCE OF RewriteSyncedMappingsCountTcpLevelEntry
	MAX-ACCESS  not-accessible
	STATUS      current
	DESCRIPTION
	"Table for rewriteSyncedMappingsCountTcp"
	::={rewriteSyncedMappingsCountTcp 4}

rewriteSyncedMappingsCountTcpLevelEntry OBJECT-TYPE
	SYNTAX      RewriteSyncedMappingsCountTcpLevelEntry
	MAX-ACCESS  not-accessible
	STATUS      current
	DESCRIPTION
	"Table entry for rewriteSyncedMappingsCountTcp"
	INDEX { rewriteSyncedMappingsCountTcpLevelName }
	::={rewriteSyncedMappingsCountTcpLevelTable 1}

RewriteSyncedMappingsCountTcpLevelEntry ::=
	SEQUENCE {
		rewriteSyncedMappingsCountTcpLevelName	DisplayString,
		rewriteSyncedMappingsCountTcpLevelVal	CounterBasedGauge64,
		rewriteSyncedMappingsCountTcpLevelMax	CounterBasedGauge64
	}

rewriteSyncedMappingsCountTcpLevelName OBJECT-TYPE
	SYNTAX      DisplayString
	MAX-ACCESS  not-accessible
	STATUS      current
	DESCRIPTION
	"Table entry display string for rewriteSyncedMappingsCountTcp"
	::={rewriteSyncedMappingsCountTcpLevelEntry 1}

rewriteSyncedMappingsCountTcpLevelVal OBJECT-TYPE
	SYNTAX	 CounterBasedGauge64
	MAX-ACCESS  read-only
	STATUS      current
	DESCRIPTION
	"Table entry attribute for rewriteSyncedMappingsCountTcp"
	::={rewriteSyncedMappingsCountTcpLevelEntry 2}

rewriteSyncedMappingsCountTcpLevelMax OBJECT-TYPE
	SYNTAX	 CounterBasedGauge64
	MAX-ACCESS  read-only
	STATUS      current
	DESCRIPTION
	"Table entry attribute for rewriteSyncedMappingsCountTcp"
	::={rewriteSyncedMappingsCountTcpLevelEntry 4}


rewriteSyncedMappingsCountUdp	OBJECT IDENTIFIER ::={rewrite 82}

rewriteSyncedMappingsCountUdpVal	OBJECT-TYPE
	SYNTAX	 CounterBasedGauge64
	MAX-ACCESS read-only
	STATUS current
	DESCRIPTION "Synchronized mappings count - UDP"

	::={rewriteSyncedMappingsCountUdp 1}

rewriteSyncedMappingsCountUdpMax	OBJECT-TYPE
	SYNTAX	 CounterBasedGauge64
	MAX-ACCESS read-only
	STATUS current
	DESCRIPTION "Synchronized mappings count - UDP"

	::={rewriteSyncedMappingsCountUdp 3}

rewriteSyncedMappingsCountUdpLevelTable OBJECT-TYPE
	SYNTAX      SEQUENCE OF RewriteSyncedMappingsCountUdpLevelEntry
	MAX-ACCESS  not-accessible
	STATUS      current
	DESCRIPTION
	"Table for rewriteSyncedMappingsCountUdp"
	::={rewriteSyncedMappingsCountUdp 4}

rewriteSyncedMappingsCountUdpLevelEntry OBJECT-TYPE
	SYNTAX      RewriteSyncedMappingsCountUdpLevelEntry
	MAX-ACCESS  not-accessible
	STATUS      current
	DESCRIPTION
	"Table entry for rewriteSyncedMappingsCountUdp"
	INDEX { rewriteSyncedMappingsCountUdpLevelName }
	::={rewriteSyncedMappingsCountUdpLevelTable 1}

RewriteSyncedMappingsCountUdpLevelEntry ::=
	SEQUENCE {
		rewriteSyncedMappingsCountUdpLevelName	DisplayString,
		rewriteSyncedMappingsCountUdpLevelVal	CounterBasedGauge64,
		rewriteSyncedMappingsCountUdpLevelMax	CounterBasedGauge64
	}

rewriteSyncedMappingsCountUdpLevelName OBJECT-TYPE
	SYNTAX      DisplayString
	MAX-ACCESS  not-accessible
	STATUS      current
	DESCRIPTION
	"Table entry display string for rewriteSyncedMappingsCountUdp"
	::={rewriteSyncedMappingsCountUdpLevelEntry 1}

rewriteSyncedMappingsCountUdpLevelVal OBJECT-TYPE
	SYNTAX	 CounterBasedGauge64
	MAX-ACCESS  read-only
	STATUS      current
	DESCRIPTION
	"Table entry attribute for rewriteSyncedMappingsCountUdp"
	::={rewriteSyncedMappingsCountUdpLevelEntry 2}

rewriteSyncedMappingsCountUdpLevelMax OBJECT-TYPE
	SYNTAX	 CounterBasedGauge64
	MAX-ACCESS  read-only
	STATUS      current
	DESCRIPTION
	"Table entry attribute for rewriteSyncedMappingsCountUdp"
	::={rewriteSyncedMappingsCountUdpLevelEntry 4}


rewriteSyncedMappingsCountIcmp	OBJECT IDENTIFIER ::={rewrite 83}

rewriteSyncedMappingsCountIcmpVal	OBJECT-TYPE
	SYNTAX	 CounterBasedGauge64
	MAX-ACCESS read-only
	STATUS current
	DESCRIPTION "Synchronized mappings count - ICMP"

	::={rewriteSyncedMappingsCountIcmp 1}

rewriteSyncedMappingsCountIcmpMax	OBJECT-TYPE
	SYNTAX	 CounterBasedGauge64
	MAX-ACCESS read-only
	STATUS current
	DESCRIPTION "Synchronized mappings count - ICMP"

	::={rewriteSyncedMappingsCountIcmp 3}

rewriteSyncedMappingsCountIcmpLevelTable OBJECT-TYPE
	SYNTAX      SEQUENCE OF RewriteSyncedMappingsCountIcmpLevelEntry
	MAX-ACCESS  not-accessible
	STATUS      current
	DESCRIPTION
	"Table for rewriteSyncedMappingsCountIcmp"
	::={rewriteSyncedMappingsCountIcmp 4}

rewriteSyncedMappingsCountIcmpLevelEntry OBJECT-TYPE
	SYNTAX      RewriteSyncedMappingsCountIcmpLevelEntry
	MAX-ACCESS  not-accessible
	STATUS      current
	DESCRIPTION
	"Table entry for rewriteSyncedMappingsCountIcmp"
	INDEX { rewriteSyncedMappingsCountIcmpLevelName }
	::={rewriteSyncedMappingsCountIcmpLevelTable 1}

RewriteSyncedMappingsCountIcmpLevelEntry ::=
	SEQUENCE {
		rewriteSyncedMappingsCountIcmpLevelName	DisplayString,
		rewriteSyncedMappingsCountIcmpLevelVal	CounterBasedGauge64,
		rewriteSyncedMappingsCountIcmpLevelMax	CounterBasedGauge64
	}

rewriteSyncedMappingsCountIcmpLevelName OBJECT-TYPE
	SYNTAX      DisplayString
	MAX-ACCESS  not-accessible
	STATUS      current
	DESCRIPTION
	"Table entry display string for rewriteSyncedMappingsCountIcmp"
	::={rewriteSyncedMappingsCountIcmpLevelEntry 1}

rewriteSyncedMappingsCountIcmpLevelVal OBJECT-TYPE
	SYNTAX	 CounterBasedGauge64
	MAX-ACCESS  read-only
	STATUS      current
	DESCRIPTION
	"Table entry attribute for rewriteSyncedMappingsCountIcmp"
	::={rewriteSyncedMappingsCountIcmpLevelEntry 2}

rewriteSyncedMappingsCountIcmpLevelMax OBJECT-TYPE
	SYNTAX	 CounterBasedGauge64
	MAX-ACCESS  read-only
	STATUS      current
	DESCRIPTION
	"Table entry attribute for rewriteSyncedMappingsCountIcmp"
	::={rewriteSyncedMappingsCountIcmpLevelEntry 4}


rewriteSyncedMappingsCountGre	OBJECT IDENTIFIER ::={rewrite 84}

rewriteSyncedMappingsCountGreVal	OBJECT-TYPE
	SYNTAX	 CounterBasedGauge64
	MAX-ACCESS read-only
	STATUS current
	DESCRIPTION "Synchronized mappings count - GRE"

	::={rewriteSyncedMappingsCountGre 1}

rewriteSyncedMappingsCountGreMax	OBJECT-TYPE
	SYNTAX	 CounterBasedGauge64
	MAX-ACCESS read-only
	STATUS current
	DESCRIPTION "Synchronized mappings count - GRE"

	::={rewriteSyncedMappingsCountGre 3}

rewriteSyncedMappingsCountGreLevelTable OBJECT-TYPE
	SYNTAX      SEQUENCE OF RewriteSyncedMappingsCountGreLevelEntry
	MAX-ACCESS  not-accessible
	STATUS      current
	DESCRIPTION
	"Table for rewriteSyncedMappingsCountGre"
	::={rewriteSyncedMappingsCountGre 4}

rewriteSyncedMappingsCountGreLevelEntry OBJECT-TYPE
	SYNTAX      RewriteSyncedMappingsCountGreLevelEntry
	MAX-ACCESS  not-accessible
	STATUS      current
	DESCRIPTION
	"Table entry for rewriteSyncedMappingsCountGre"
	INDEX { rewriteSyncedMappingsCountGreLevelName }
	::={rewriteSyncedMappingsCountGreLevelTable 1}

RewriteSyncedMappingsCountGreLevelEntry ::=
	SEQUENCE {
		rewriteSyncedMappingsCountGreLevelName	DisplayString,
		rewriteSyncedMappingsCountGreLevelVal	CounterBasedGauge64,
		rewriteSyncedMappingsCountGreLevelMax	CounterBasedGauge64
	}

rewriteSyncedMappingsCountGreLevelName OBJECT-TYPE
	SYNTAX      DisplayString
	MAX-ACCESS  not-accessible
	STATUS      current
	DESCRIPTION
	"Table entry display string for rewriteSyncedMappingsCountGre"
	::={rewriteSyncedMappingsCountGreLevelEntry 1}

rewriteSyncedMappingsCountGreLevelVal OBJECT-TYPE
	SYNTAX	 CounterBasedGauge64
	MAX-ACCESS  read-only
	STATUS      current
	DESCRIPTION
	"Table entry attribute for rewriteSyncedMappingsCountGre"
	::={rewriteSyncedMappingsCountGreLevelEntry 2}

rewriteSyncedMappingsCountGreLevelMax OBJECT-TYPE
	SYNTAX	 CounterBasedGauge64
	MAX-ACCESS  read-only
	STATUS      current
	DESCRIPTION
	"Table entry attribute for rewriteSyncedMappingsCountGre"
	::={rewriteSyncedMappingsCountGreLevelEntry 4}


rewriteSyncedMappingsCreated	OBJECT IDENTIFIER ::={rewrite 85}

rewriteSyncedMappingsCreatedVal	OBJECT-TYPE
	SYNTAX	 Counter64
	MAX-ACCESS read-only
	STATUS current
	DESCRIPTION "Synchronized mappings created"

	::={rewriteSyncedMappingsCreated 1}

rewriteSyncedMappingsCreatedMom	OBJECT-TYPE
	SYNTAX	 CounterBasedGauge64
	MAX-ACCESS read-only
	STATUS current
	DESCRIPTION "Synchronized mappings created"

	::={rewriteSyncedMappingsCreated 2}

rewriteSyncedMappingsCreatedMax	OBJECT-TYPE
	SYNTAX	 CounterBasedGauge64
	MAX-ACCESS read-only
	STATUS current
	DESCRIPTION "Synchronized mappings created"

	::={rewriteSyncedMappingsCreated 3}

rewriteSyncedMappingsCreatedLevelTable OBJECT-TYPE
	SYNTAX      SEQUENCE OF RewriteSyncedMappingsCreatedLevelEntry
	MAX-ACCESS  not-accessible
	STATUS      current
	DESCRIPTION
	"Table for rewriteSyncedMappingsCreated"
	::={rewriteSyncedMappingsCreated 4}

rewriteSyncedMappingsCreatedLevelEntry OBJECT-TYPE
	SYNTAX      RewriteSyncedMappingsCreatedLevelEntry
	MAX-ACCESS  not-accessible
	STATUS      current
	DESCRIPTION
	"Table entry for rewriteSyncedMappingsCreated"
	INDEX { rewriteSyncedMappingsCreatedLevelName }
	::={rewriteSyncedMappingsCreatedLevelTable 1}

RewriteSyncedMappingsCreatedLevelEntry ::=
	SEQUENCE {
		rewriteSyncedMappingsCreatedLevelName	DisplayString,
		rewriteSyncedMappingsCreatedLevelVal	Counter64,
		rewriteSyncedMappingsCreatedLevelMom	CounterBasedGauge64,
		rewriteSyncedMappingsCreatedLevelMax	CounterBasedGauge64
	}

rewriteSyncedMappingsCreatedLevelName OBJECT-TYPE
	SYNTAX      DisplayString
	MAX-ACCESS  not-accessible
	STATUS      current
	DESCRIPTION
	"Table entry display string for rewriteSyncedMappingsCreated"
	::={rewriteSyncedMappingsCreatedLevelEntry 1}

rewriteSyncedMappingsCreatedLevelVal OBJECT-TYPE
	SYNTAX	 Counter64
	MAX-ACCESS  read-only
	STATUS      current
	DESCRIPTION
	"Table entry attribute for rewriteSyncedMappingsCreated"
	::={rewriteSyncedMappingsCreatedLevelEntry 2}

rewriteSyncedMappingsCreatedLevelMom OBJECT-TYPE
	SYNTAX	 CounterBasedGauge64
	MAX-ACCESS  read-only
	STATUS      current
	DESCRIPTION
	"Table entry attribute for rewriteSyncedMappingsCreated"
	::={rewriteSyncedMappingsCreatedLevelEntry 3}

rewriteSyncedMappingsCreatedLevelMax OBJECT-TYPE
	SYNTAX	 CounterBasedGauge64
	MAX-ACCESS  read-only
	STATUS      current
	DESCRIPTION
	"Table entry attribute for rewriteSyncedMappingsCreated"
	::={rewriteSyncedMappingsCreatedLevelEntry 4}


rewriteSyncedMappingsCreatedTcp	OBJECT IDENTIFIER ::={rewrite 86}

rewriteSyncedMappingsCreatedTcpVal	OBJECT-TYPE
	SYNTAX	 Counter64
	MAX-ACCESS read-only
	STATUS current
	DESCRIPTION "Synchronized mappings created - TCP"

	::={rewriteSyncedMappingsCreatedTcp 1}

rewriteSyncedMappingsCreatedTcpMom	OBJECT-TYPE
	SYNTAX	 CounterBasedGauge64
	MAX-ACCESS read-only
	STATUS current
	DESCRIPTION "Synchronized mappings created - TCP"

	::={rewriteSyncedMappingsCreatedTcp 2}

rewriteSyncedMappingsCreatedTcpMax	OBJECT-TYPE
	SYNTAX	 CounterBasedGauge64
	MAX-ACCESS read-only
	STATUS current
	DESCRIPTION "Synchronized mappings created - TCP"

	::={rewriteSyncedMappingsCreatedTcp 3}

rewriteSyncedMappingsCreatedTcpLevelTable OBJECT-TYPE
	SYNTAX      SEQUENCE OF RewriteSyncedMappingsCreatedTcpLevelEntry
	MAX-ACCESS  not-accessible
	STATUS      current
	DESCRIPTION
	"Table for rewriteSyncedMappingsCreatedTcp"
	::={rewriteSyncedMappingsCreatedTcp 4}

rewriteSyncedMappingsCreatedTcpLevelEntry OBJECT-TYPE
	SYNTAX      RewriteSyncedMappingsCreatedTcpLevelEntry
	MAX-ACCESS  not-accessible
	STATUS      current
	DESCRIPTION
	"Table entry for rewriteSyncedMappingsCreatedTcp"
	INDEX { rewriteSyncedMappingsCreatedTcpLevelName }
	::={rewriteSyncedMappingsCreatedTcpLevelTable 1}

RewriteSyncedMappingsCreatedTcpLevelEntry ::=
	SEQUENCE {
		rewriteSyncedMappingsCreatedTcpLevelName	DisplayString,
		rewriteSyncedMappingsCreatedTcpLevelVal	Counter64,
		rewriteSyncedMappingsCreatedTcpLevelMom	CounterBasedGauge64,
		rewriteSyncedMappingsCreatedTcpLevelMax	CounterBasedGauge64
	}

rewriteSyncedMappingsCreatedTcpLevelName OBJECT-TYPE
	SYNTAX      DisplayString
	MAX-ACCESS  not-accessible
	STATUS      current
	DESCRIPTION
	"Table entry display string for rewriteSyncedMappingsCreatedTcp"
	::={rewriteSyncedMappingsCreatedTcpLevelEntry 1}

rewriteSyncedMappingsCreatedTcpLevelVal OBJECT-TYPE
	SYNTAX	 Counter64
	MAX-ACCESS  read-only
	STATUS      current
	DESCRIPTION
	"Table entry attribute for rewriteSyncedMappingsCreatedTcp"
	::={rewriteSyncedMappingsCreatedTcpLevelEntry 2}

rewriteSyncedMappingsCreatedTcpLevelMom OBJECT-TYPE
	SYNTAX	 CounterBasedGauge64
	MAX-ACCESS  read-only
	STATUS      current
	DESCRIPTION
	"Table entry attribute for rewriteSyncedMappingsCreatedTcp"
	::={rewriteSyncedMappingsCreatedTcpLevelEntry 3}

rewriteSyncedMappingsCreatedTcpLevelMax OBJECT-TYPE
	SYNTAX	 CounterBasedGauge64
	MAX-ACCESS  read-only
	STATUS      current
	DESCRIPTION
	"Table entry attribute for rewriteSyncedMappingsCreatedTcp"
	::={rewriteSyncedMappingsCreatedTcpLevelEntry 4}


rewriteSyncedMappingsCreatedUdp	OBJECT IDENTIFIER ::={rewrite 87}

rewriteSyncedMappingsCreatedUdpVal	OBJECT-TYPE
	SYNTAX	 Counter64
	MAX-ACCESS read-only
	STATUS current
	DESCRIPTION "Synchronized mappings created - UDP"

	::={rewriteSyncedMappingsCreatedUdp 1}

rewriteSyncedMappingsCreatedUdpMom	OBJECT-TYPE
	SYNTAX	 CounterBasedGauge64
	MAX-ACCESS read-only
	STATUS current
	DESCRIPTION "Synchronized mappings created - UDP"

	::={rewriteSyncedMappingsCreatedUdp 2}

rewriteSyncedMappingsCreatedUdpMax	OBJECT-TYPE
	SYNTAX	 CounterBasedGauge64
	MAX-ACCESS read-only
	STATUS current
	DESCRIPTION "Synchronized mappings created - UDP"

	::={rewriteSyncedMappingsCreatedUdp 3}

rewriteSyncedMappingsCreatedUdpLevelTable OBJECT-TYPE
	SYNTAX      SEQUENCE OF RewriteSyncedMappingsCreatedUdpLevelEntry
	MAX-ACCESS  not-accessible
	STATUS      current
	DESCRIPTION
	"Table for rewriteSyncedMappingsCreatedUdp"
	::={rewriteSyncedMappingsCreatedUdp 4}

rewriteSyncedMappingsCreatedUdpLevelEntry OBJECT-TYPE
	SYNTAX      RewriteSyncedMappingsCreatedUdpLevelEntry
	MAX-ACCESS  not-accessible
	STATUS      current
	DESCRIPTION
	"Table entry for rewriteSyncedMappingsCreatedUdp"
	INDEX { rewriteSyncedMappingsCreatedUdpLevelName }
	::={rewriteSyncedMappingsCreatedUdpLevelTable 1}

RewriteSyncedMappingsCreatedUdpLevelEntry ::=
	SEQUENCE {
		rewriteSyncedMappingsCreatedUdpLevelName	DisplayString,
		rewriteSyncedMappingsCreatedUdpLevelVal	Counter64,
		rewriteSyncedMappingsCreatedUdpLevelMom	CounterBasedGauge64,
		rewriteSyncedMappingsCreatedUdpLevelMax	CounterBasedGauge64
	}

rewriteSyncedMappingsCreatedUdpLevelName OBJECT-TYPE
	SYNTAX      DisplayString
	MAX-ACCESS  not-accessible
	STATUS      current
	DESCRIPTION
	"Table entry display string for rewriteSyncedMappingsCreatedUdp"
	::={rewriteSyncedMappingsCreatedUdpLevelEntry 1}

rewriteSyncedMappingsCreatedUdpLevelVal OBJECT-TYPE
	SYNTAX	 Counter64
	MAX-ACCESS  read-only
	STATUS      current
	DESCRIPTION
	"Table entry attribute for rewriteSyncedMappingsCreatedUdp"
	::={rewriteSyncedMappingsCreatedUdpLevelEntry 2}

rewriteSyncedMappingsCreatedUdpLevelMom OBJECT-TYPE
	SYNTAX	 CounterBasedGauge64
	MAX-ACCESS  read-only
	STATUS      current
	DESCRIPTION
	"Table entry attribute for rewriteSyncedMappingsCreatedUdp"
	::={rewriteSyncedMappingsCreatedUdpLevelEntry 3}

rewriteSyncedMappingsCreatedUdpLevelMax OBJECT-TYPE
	SYNTAX	 CounterBasedGauge64
	MAX-ACCESS  read-only
	STATUS      current
	DESCRIPTION
	"Table entry attribute for rewriteSyncedMappingsCreatedUdp"
	::={rewriteSyncedMappingsCreatedUdpLevelEntry 4}


rewriteSyncedMappingsCreatedIcmp	OBJECT IDENTIFIER ::={rewrite 88}

rewriteSyncedMappingsCreatedIcmpVal	OBJECT-TYPE
	SYNTAX	 Counter64
	MAX-ACCESS read-only
	STATUS current
	DESCRIPTION "Synchronized mappings created - ICMP"

	::={rewriteSyncedMappingsCreatedIcmp 1}

rewriteSyncedMappingsCreatedIcmpMom	OBJECT-TYPE
	SYNTAX	 CounterBasedGauge64
	MAX-ACCESS read-only
	STATUS current
	DESCRIPTION "Synchronized mappings created - ICMP"

	::={rewriteSyncedMappingsCreatedIcmp 2}

rewriteSyncedMappingsCreatedIcmpMax	OBJECT-TYPE
	SYNTAX	 CounterBasedGauge64
	MAX-ACCESS read-only
	STATUS current
	DESCRIPTION "Synchronized mappings created - ICMP"

	::={rewriteSyncedMappingsCreatedIcmp 3}

rewriteSyncedMappingsCreatedIcmpLevelTable OBJECT-TYPE
	SYNTAX      SEQUENCE OF RewriteSyncedMappingsCreatedIcmpLevelEntry
	MAX-ACCESS  not-accessible
	STATUS      current
	DESCRIPTION
	"Table for rewriteSyncedMappingsCreatedIcmp"
	::={rewriteSyncedMappingsCreatedIcmp 4}

rewriteSyncedMappingsCreatedIcmpLevelEntry OBJECT-TYPE
	SYNTAX      RewriteSyncedMappingsCreatedIcmpLevelEntry
	MAX-ACCESS  not-accessible
	STATUS      current
	DESCRIPTION
	"Table entry for rewriteSyncedMappingsCreatedIcmp"
	INDEX { rewriteSyncedMappingsCreatedIcmpLevelName }
	::={rewriteSyncedMappingsCreatedIcmpLevelTable 1}

RewriteSyncedMappingsCreatedIcmpLevelEntry ::=
	SEQUENCE {
		rewriteSyncedMappingsCreatedIcmpLevelName	DisplayString,
		rewriteSyncedMappingsCreatedIcmpLevelVal	Counter64,
		rewriteSyncedMappingsCreatedIcmpLevelMom	CounterBasedGauge64,
		rewriteSyncedMappingsCreatedIcmpLevelMax	CounterBasedGauge64
	}

rewriteSyncedMappingsCreatedIcmpLevelName OBJECT-TYPE
	SYNTAX      DisplayString
	MAX-ACCESS  not-accessible
	STATUS      current
	DESCRIPTION
	"Table entry display string for rewriteSyncedMappingsCreatedIcmp"
	::={rewriteSyncedMappingsCreatedIcmpLevelEntry 1}

rewriteSyncedMappingsCreatedIcmpLevelVal OBJECT-TYPE
	SYNTAX	 Counter64
	MAX-ACCESS  read-only
	STATUS      current
	DESCRIPTION
	"Table entry attribute for rewriteSyncedMappingsCreatedIcmp"
	::={rewriteSyncedMappingsCreatedIcmpLevelEntry 2}

rewriteSyncedMappingsCreatedIcmpLevelMom OBJECT-TYPE
	SYNTAX	 CounterBasedGauge64
	MAX-ACCESS  read-only
	STATUS      current
	DESCRIPTION
	"Table entry attribute for rewriteSyncedMappingsCreatedIcmp"
	::={rewriteSyncedMappingsCreatedIcmpLevelEntry 3}

rewriteSyncedMappingsCreatedIcmpLevelMax OBJECT-TYPE
	SYNTAX	 CounterBasedGauge64
	MAX-ACCESS  read-only
	STATUS      current
	DESCRIPTION
	"Table entry attribute for rewriteSyncedMappingsCreatedIcmp"
	::={rewriteSyncedMappingsCreatedIcmpLevelEntry 4}


rewriteSyncedMappingsCreatedGre	OBJECT IDENTIFIER ::={rewrite 89}

rewriteSyncedMappingsCreatedGreVal	OBJECT-TYPE
	SYNTAX	 Counter64
	MAX-ACCESS read-only
	STATUS current
	DESCRIPTION "Synchronized mappings created - GRE"

	::={rewriteSyncedMappingsCreatedGre 1}

rewriteSyncedMappingsCreatedGreMom	OBJECT-TYPE
	SYNTAX	 CounterBasedGauge64
	MAX-ACCESS read-only
	STATUS current
	DESCRIPTION "Synchronized mappings created - GRE"

	::={rewriteSyncedMappingsCreatedGre 2}

rewriteSyncedMappingsCreatedGreMax	OBJECT-TYPE
	SYNTAX	 CounterBasedGauge64
	MAX-ACCESS read-only
	STATUS current
	DESCRIPTION "Synchronized mappings created - GRE"

	::={rewriteSyncedMappingsCreatedGre 3}

rewriteSyncedMappingsCreatedGreLevelTable OBJECT-TYPE
	SYNTAX      SEQUENCE OF RewriteSyncedMappingsCreatedGreLevelEntry
	MAX-ACCESS  not-accessible
	STATUS      current
	DESCRIPTION
	"Table for rewriteSyncedMappingsCreatedGre"
	::={rewriteSyncedMappingsCreatedGre 4}

rewriteSyncedMappingsCreatedGreLevelEntry OBJECT-TYPE
	SYNTAX      RewriteSyncedMappingsCreatedGreLevelEntry
	MAX-ACCESS  not-accessible
	STATUS      current
	DESCRIPTION
	"Table entry for rewriteSyncedMappingsCreatedGre"
	INDEX { rewriteSyncedMappingsCreatedGreLevelName }
	::={rewriteSyncedMappingsCreatedGreLevelTable 1}

RewriteSyncedMappingsCreatedGreLevelEntry ::=
	SEQUENCE {
		rewriteSyncedMappingsCreatedGreLevelName	DisplayString,
		rewriteSyncedMappingsCreatedGreLevelVal	Counter64,
		rewriteSyncedMappingsCreatedGreLevelMom	CounterBasedGauge64,
		rewriteSyncedMappingsCreatedGreLevelMax	CounterBasedGauge64
	}

rewriteSyncedMappingsCreatedGreLevelName OBJECT-TYPE
	SYNTAX      DisplayString
	MAX-ACCESS  not-accessible
	STATUS      current
	DESCRIPTION
	"Table entry display string for rewriteSyncedMappingsCreatedGre"
	::={rewriteSyncedMappingsCreatedGreLevelEntry 1}

rewriteSyncedMappingsCreatedGreLevelVal OBJECT-TYPE
	SYNTAX	 Counter64
	MAX-ACCESS  read-only
	STATUS      current
	DESCRIPTION
	"Table entry attribute for rewriteSyncedMappingsCreatedGre"
	::={rewriteSyncedMappingsCreatedGreLevelEntry 2}

rewriteSyncedMappingsCreatedGreLevelMom OBJECT-TYPE
	SYNTAX	 CounterBasedGauge64
	MAX-ACCESS  read-only
	STATUS      current
	DESCRIPTION
	"Table entry attribute for rewriteSyncedMappingsCreatedGre"
	::={rewriteSyncedMappingsCreatedGreLevelEntry 3}

rewriteSyncedMappingsCreatedGreLevelMax OBJECT-TYPE
	SYNTAX	 CounterBasedGauge64
	MAX-ACCESS  read-only
	STATUS      current
	DESCRIPTION
	"Table entry attribute for rewriteSyncedMappingsCreatedGre"
	::={rewriteSyncedMappingsCreatedGreLevelEntry 4}


rewriteTranslationsCreatedOutboundTransl	OBJECT IDENTIFIER ::={rewrite 91}

rewriteTranslationsCreatedOutboundTranslVal	OBJECT-TYPE
	SYNTAX	 Counter64
	MAX-ACCESS read-only
	STATUS current
	DESCRIPTION "Translations created (outbound)"

	::={rewriteTranslationsCreatedOutboundTransl 1}

rewriteTranslationsCreatedOutboundTranslMom	OBJECT-TYPE
	SYNTAX	 CounterBasedGauge64
	MAX-ACCESS read-only
	STATUS current
	DESCRIPTION "Translations created (outbound)"

	::={rewriteTranslationsCreatedOutboundTransl 2}

rewriteTranslationsCreatedOutboundTranslMax	OBJECT-TYPE
	SYNTAX	 CounterBasedGauge64
	MAX-ACCESS read-only
	STATUS current
	DESCRIPTION "Translations created (outbound)"

	::={rewriteTranslationsCreatedOutboundTransl 3}

rewriteTranslationsCreatedOutboundTranslLevelTable OBJECT-TYPE
	SYNTAX      SEQUENCE OF RewriteTranslationsCreatedOutboundTranslLevelEntry
	MAX-ACCESS  not-accessible
	STATUS      current
	DESCRIPTION
	"Table for rewriteTranslationsCreatedOutboundTransl"
	::={rewriteTranslationsCreatedOutboundTransl 4}

rewriteTranslationsCreatedOutboundTranslLevelEntry OBJECT-TYPE
	SYNTAX      RewriteTranslationsCreatedOutboundTranslLevelEntry
	MAX-ACCESS  not-accessible
	STATUS      current
	DESCRIPTION
	"Table entry for rewriteTranslationsCreatedOutboundTransl"
	INDEX { rewriteTranslationsCreatedOutboundTranslLevelName }
	::={rewriteTranslationsCreatedOutboundTranslLevelTable 1}

RewriteTranslationsCreatedOutboundTranslLevelEntry ::=
	SEQUENCE {
		rewriteTranslationsCreatedOutboundTranslLevelName	DisplayString,
		rewriteTranslationsCreatedOutboundTranslLevelVal	Counter64,
		rewriteTranslationsCreatedOutboundTranslLevelMom	CounterBasedGauge64,
		rewriteTranslationsCreatedOutboundTranslLevelMax	CounterBasedGauge64
	}

rewriteTranslationsCreatedOutboundTranslLevelName OBJECT-TYPE
	SYNTAX      DisplayString
	MAX-ACCESS  not-accessible
	STATUS      current
	DESCRIPTION
	"Table entry display string for rewriteTranslationsCreatedOutboundTransl"
	::={rewriteTranslationsCreatedOutboundTranslLevelEntry 1}

rewriteTranslationsCreatedOutboundTranslLevelVal OBJECT-TYPE
	SYNTAX	 Counter64
	MAX-ACCESS  read-only
	STATUS      current
	DESCRIPTION
	"Table entry attribute for rewriteTranslationsCreatedOutboundTransl"
	::={rewriteTranslationsCreatedOutboundTranslLevelEntry 2}

rewriteTranslationsCreatedOutboundTranslLevelMom OBJECT-TYPE
	SYNTAX	 CounterBasedGauge64
	MAX-ACCESS  read-only
	STATUS      current
	DESCRIPTION
	"Table entry attribute for rewriteTranslationsCreatedOutboundTransl"
	::={rewriteTranslationsCreatedOutboundTranslLevelEntry 3}

rewriteTranslationsCreatedOutboundTranslLevelMax OBJECT-TYPE
	SYNTAX	 CounterBasedGauge64
	MAX-ACCESS  read-only
	STATUS      current
	DESCRIPTION
	"Table entry attribute for rewriteTranslationsCreatedOutboundTransl"
	::={rewriteTranslationsCreatedOutboundTranslLevelEntry 4}


rewriteTranslationsCreatedTcpOutboundTransl	OBJECT IDENTIFIER ::={rewrite 92}

rewriteTranslationsCreatedTcpOutboundTranslVal	OBJECT-TYPE
	SYNTAX	 Counter64
	MAX-ACCESS read-only
	STATUS current
	DESCRIPTION "Translations created - TCP (outbound)"

	::={rewriteTranslationsCreatedTcpOutboundTransl 1}

rewriteTranslationsCreatedTcpOutboundTranslMom	OBJECT-TYPE
	SYNTAX	 CounterBasedGauge64
	MAX-ACCESS read-only
	STATUS current
	DESCRIPTION "Translations created - TCP (outbound)"

	::={rewriteTranslationsCreatedTcpOutboundTransl 2}

rewriteTranslationsCreatedTcpOutboundTranslMax	OBJECT-TYPE
	SYNTAX	 CounterBasedGauge64
	MAX-ACCESS read-only
	STATUS current
	DESCRIPTION "Translations created - TCP (outbound)"

	::={rewriteTranslationsCreatedTcpOutboundTransl 3}

rewriteTranslationsCreatedTcpOutboundTranslLevelTable OBJECT-TYPE
	SYNTAX      SEQUENCE OF RewriteTranslationsCreatedTcpOutboundTranslLevelEntry
	MAX-ACCESS  not-accessible
	STATUS      current
	DESCRIPTION
	"Table for rewriteTranslationsCreatedTcpOutboundTransl"
	::={rewriteTranslationsCreatedTcpOutboundTransl 4}

rewriteTranslationsCreatedTcpOutboundTranslLevelEntry OBJECT-TYPE
	SYNTAX      RewriteTranslationsCreatedTcpOutboundTranslLevelEntry
	MAX-ACCESS  not-accessible
	STATUS      current
	DESCRIPTION
	"Table entry for rewriteTranslationsCreatedTcpOutboundTransl"
	INDEX { rewriteTranslationsCreatedTcpOutboundTranslLevelName }
	::={rewriteTranslationsCreatedTcpOutboundTranslLevelTable 1}

RewriteTranslationsCreatedTcpOutboundTranslLevelEntry ::=
	SEQUENCE {
		rewriteTranslationsCreatedTcpOutboundTranslLevelName	DisplayString,
		rewriteTranslationsCreatedTcpOutboundTranslLevelVal	Counter64,
		rewriteTranslationsCreatedTcpOutboundTranslLevelMom	CounterBasedGauge64,
		rewriteTranslationsCreatedTcpOutboundTranslLevelMax	CounterBasedGauge64
	}

rewriteTranslationsCreatedTcpOutboundTranslLevelName OBJECT-TYPE
	SYNTAX      DisplayString
	MAX-ACCESS  not-accessible
	STATUS      current
	DESCRIPTION
	"Table entry display string for rewriteTranslationsCreatedTcpOutboundTransl"
	::={rewriteTranslationsCreatedTcpOutboundTranslLevelEntry 1}

rewriteTranslationsCreatedTcpOutboundTranslLevelVal OBJECT-TYPE
	SYNTAX	 Counter64
	MAX-ACCESS  read-only
	STATUS      current
	DESCRIPTION
	"Table entry attribute for rewriteTranslationsCreatedTcpOutboundTransl"
	::={rewriteTranslationsCreatedTcpOutboundTranslLevelEntry 2}

rewriteTranslationsCreatedTcpOutboundTranslLevelMom OBJECT-TYPE
	SYNTAX	 CounterBasedGauge64
	MAX-ACCESS  read-only
	STATUS      current
	DESCRIPTION
	"Table entry attribute for rewriteTranslationsCreatedTcpOutboundTransl"
	::={rewriteTranslationsCreatedTcpOutboundTranslLevelEntry 3}

rewriteTranslationsCreatedTcpOutboundTranslLevelMax OBJECT-TYPE
	SYNTAX	 CounterBasedGauge64
	MAX-ACCESS  read-only
	STATUS      current
	DESCRIPTION
	"Table entry attribute for rewriteTranslationsCreatedTcpOutboundTransl"
	::={rewriteTranslationsCreatedTcpOutboundTranslLevelEntry 4}


rewriteTranslationsCreatedUdpOutboundTransl	OBJECT IDENTIFIER ::={rewrite 93}

rewriteTranslationsCreatedUdpOutboundTranslVal	OBJECT-TYPE
	SYNTAX	 Counter64
	MAX-ACCESS read-only
	STATUS current
	DESCRIPTION "Translations created - UDP (outbound)"

	::={rewriteTranslationsCreatedUdpOutboundTransl 1}

rewriteTranslationsCreatedUdpOutboundTranslMom	OBJECT-TYPE
	SYNTAX	 CounterBasedGauge64
	MAX-ACCESS read-only
	STATUS current
	DESCRIPTION "Translations created - UDP (outbound)"

	::={rewriteTranslationsCreatedUdpOutboundTransl 2}

rewriteTranslationsCreatedUdpOutboundTranslMax	OBJECT-TYPE
	SYNTAX	 CounterBasedGauge64
	MAX-ACCESS read-only
	STATUS current
	DESCRIPTION "Translations created - UDP (outbound)"

	::={rewriteTranslationsCreatedUdpOutboundTransl 3}

rewriteTranslationsCreatedUdpOutboundTranslLevelTable OBJECT-TYPE
	SYNTAX      SEQUENCE OF RewriteTranslationsCreatedUdpOutboundTranslLevelEntry
	MAX-ACCESS  not-accessible
	STATUS      current
	DESCRIPTION
	"Table for rewriteTranslationsCreatedUdpOutboundTransl"
	::={rewriteTranslationsCreatedUdpOutboundTransl 4}

rewriteTranslationsCreatedUdpOutboundTranslLevelEntry OBJECT-TYPE
	SYNTAX      RewriteTranslationsCreatedUdpOutboundTranslLevelEntry
	MAX-ACCESS  not-accessible
	STATUS      current
	DESCRIPTION
	"Table entry for rewriteTranslationsCreatedUdpOutboundTransl"
	INDEX { rewriteTranslationsCreatedUdpOutboundTranslLevelName }
	::={rewriteTranslationsCreatedUdpOutboundTranslLevelTable 1}

RewriteTranslationsCreatedUdpOutboundTranslLevelEntry ::=
	SEQUENCE {
		rewriteTranslationsCreatedUdpOutboundTranslLevelName	DisplayString,
		rewriteTranslationsCreatedUdpOutboundTranslLevelVal	Counter64,
		rewriteTranslationsCreatedUdpOutboundTranslLevelMom	CounterBasedGauge64,
		rewriteTranslationsCreatedUdpOutboundTranslLevelMax	CounterBasedGauge64
	}

rewriteTranslationsCreatedUdpOutboundTranslLevelName OBJECT-TYPE
	SYNTAX      DisplayString
	MAX-ACCESS  not-accessible
	STATUS      current
	DESCRIPTION
	"Table entry display string for rewriteTranslationsCreatedUdpOutboundTransl"
	::={rewriteTranslationsCreatedUdpOutboundTranslLevelEntry 1}

rewriteTranslationsCreatedUdpOutboundTranslLevelVal OBJECT-TYPE
	SYNTAX	 Counter64
	MAX-ACCESS  read-only
	STATUS      current
	DESCRIPTION
	"Table entry attribute for rewriteTranslationsCreatedUdpOutboundTransl"
	::={rewriteTranslationsCreatedUdpOutboundTranslLevelEntry 2}

rewriteTranslationsCreatedUdpOutboundTranslLevelMom OBJECT-TYPE
	SYNTAX	 CounterBasedGauge64
	MAX-ACCESS  read-only
	STATUS      current
	DESCRIPTION
	"Table entry attribute for rewriteTranslationsCreatedUdpOutboundTransl"
	::={rewriteTranslationsCreatedUdpOutboundTranslLevelEntry 3}

rewriteTranslationsCreatedUdpOutboundTranslLevelMax OBJECT-TYPE
	SYNTAX	 CounterBasedGauge64
	MAX-ACCESS  read-only
	STATUS      current
	DESCRIPTION
	"Table entry attribute for rewriteTranslationsCreatedUdpOutboundTransl"
	::={rewriteTranslationsCreatedUdpOutboundTranslLevelEntry 4}


rewriteTranslationsCreatedIcmpOutboundTransl	OBJECT IDENTIFIER ::={rewrite 94}

rewriteTranslationsCreatedIcmpOutboundTranslVal	OBJECT-TYPE
	SYNTAX	 Counter64
	MAX-ACCESS read-only
	STATUS current
	DESCRIPTION "Translations created - ICMP (outbound)"

	::={rewriteTranslationsCreatedIcmpOutboundTransl 1}

rewriteTranslationsCreatedIcmpOutboundTranslMom	OBJECT-TYPE
	SYNTAX	 CounterBasedGauge64
	MAX-ACCESS read-only
	STATUS current
	DESCRIPTION "Translations created - ICMP (outbound)"

	::={rewriteTranslationsCreatedIcmpOutboundTransl 2}

rewriteTranslationsCreatedIcmpOutboundTranslMax	OBJECT-TYPE
	SYNTAX	 CounterBasedGauge64
	MAX-ACCESS read-only
	STATUS current
	DESCRIPTION "Translations created - ICMP (outbound)"

	::={rewriteTranslationsCreatedIcmpOutboundTransl 3}

rewriteTranslationsCreatedIcmpOutboundTranslLevelTable OBJECT-TYPE
	SYNTAX      SEQUENCE OF RewriteTranslationsCreatedIcmpOutboundTranslLevelEntry
	MAX-ACCESS  not-accessible
	STATUS      current
	DESCRIPTION
	"Table for rewriteTranslationsCreatedIcmpOutboundTransl"
	::={rewriteTranslationsCreatedIcmpOutboundTransl 4}

rewriteTranslationsCreatedIcmpOutboundTranslLevelEntry OBJECT-TYPE
	SYNTAX      RewriteTranslationsCreatedIcmpOutboundTranslLevelEntry
	MAX-ACCESS  not-accessible
	STATUS      current
	DESCRIPTION
	"Table entry for rewriteTranslationsCreatedIcmpOutboundTransl"
	INDEX { rewriteTranslationsCreatedIcmpOutboundTranslLevelName }
	::={rewriteTranslationsCreatedIcmpOutboundTranslLevelTable 1}

RewriteTranslationsCreatedIcmpOutboundTranslLevelEntry ::=
	SEQUENCE {
		rewriteTranslationsCreatedIcmpOutboundTranslLevelName	DisplayString,
		rewriteTranslationsCreatedIcmpOutboundTranslLevelVal	Counter64,
		rewriteTranslationsCreatedIcmpOutboundTranslLevelMom	CounterBasedGauge64,
		rewriteTranslationsCreatedIcmpOutboundTranslLevelMax	CounterBasedGauge64
	}

rewriteTranslationsCreatedIcmpOutboundTranslLevelName OBJECT-TYPE
	SYNTAX      DisplayString
	MAX-ACCESS  not-accessible
	STATUS      current
	DESCRIPTION
	"Table entry display string for rewriteTranslationsCreatedIcmpOutboundTransl"
	::={rewriteTranslationsCreatedIcmpOutboundTranslLevelEntry 1}

rewriteTranslationsCreatedIcmpOutboundTranslLevelVal OBJECT-TYPE
	SYNTAX	 Counter64
	MAX-ACCESS  read-only
	STATUS      current
	DESCRIPTION
	"Table entry attribute for rewriteTranslationsCreatedIcmpOutboundTransl"
	::={rewriteTranslationsCreatedIcmpOutboundTranslLevelEntry 2}

rewriteTranslationsCreatedIcmpOutboundTranslLevelMom OBJECT-TYPE
	SYNTAX	 CounterBasedGauge64
	MAX-ACCESS  read-only
	STATUS      current
	DESCRIPTION
	"Table entry attribute for rewriteTranslationsCreatedIcmpOutboundTransl"
	::={rewriteTranslationsCreatedIcmpOutboundTranslLevelEntry 3}

rewriteTranslationsCreatedIcmpOutboundTranslLevelMax OBJECT-TYPE
	SYNTAX	 CounterBasedGauge64
	MAX-ACCESS  read-only
	STATUS      current
	DESCRIPTION
	"Table entry attribute for rewriteTranslationsCreatedIcmpOutboundTransl"
	::={rewriteTranslationsCreatedIcmpOutboundTranslLevelEntry 4}


rewriteTranslationsDeletedOutboundTransl	OBJECT IDENTIFIER ::={rewrite 95}

rewriteTranslationsDeletedOutboundTranslVal	OBJECT-TYPE
	SYNTAX	 Counter64
	MAX-ACCESS read-only
	STATUS current
	DESCRIPTION "Translations deleted (outbound)"

	::={rewriteTranslationsDeletedOutboundTransl 1}

rewriteTranslationsDeletedOutboundTranslMom	OBJECT-TYPE
	SYNTAX	 CounterBasedGauge64
	MAX-ACCESS read-only
	STATUS current
	DESCRIPTION "Translations deleted (outbound)"

	::={rewriteTranslationsDeletedOutboundTransl 2}

rewriteTranslationsDeletedOutboundTranslMax	OBJECT-TYPE
	SYNTAX	 CounterBasedGauge64
	MAX-ACCESS read-only
	STATUS current
	DESCRIPTION "Translations deleted (outbound)"

	::={rewriteTranslationsDeletedOutboundTransl 3}

rewriteTranslationsDeletedOutboundTranslLevelTable OBJECT-TYPE
	SYNTAX      SEQUENCE OF RewriteTranslationsDeletedOutboundTranslLevelEntry
	MAX-ACCESS  not-accessible
	STATUS      current
	DESCRIPTION
	"Table for rewriteTranslationsDeletedOutboundTransl"
	::={rewriteTranslationsDeletedOutboundTransl 4}

rewriteTranslationsDeletedOutboundTranslLevelEntry OBJECT-TYPE
	SYNTAX      RewriteTranslationsDeletedOutboundTranslLevelEntry
	MAX-ACCESS  not-accessible
	STATUS      current
	DESCRIPTION
	"Table entry for rewriteTranslationsDeletedOutboundTransl"
	INDEX { rewriteTranslationsDeletedOutboundTranslLevelName }
	::={rewriteTranslationsDeletedOutboundTranslLevelTable 1}

RewriteTranslationsDeletedOutboundTranslLevelEntry ::=
	SEQUENCE {
		rewriteTranslationsDeletedOutboundTranslLevelName	DisplayString,
		rewriteTranslationsDeletedOutboundTranslLevelVal	Counter64,
		rewriteTranslationsDeletedOutboundTranslLevelMom	CounterBasedGauge64,
		rewriteTranslationsDeletedOutboundTranslLevelMax	CounterBasedGauge64
	}

rewriteTranslationsDeletedOutboundTranslLevelName OBJECT-TYPE
	SYNTAX      DisplayString
	MAX-ACCESS  not-accessible
	STATUS      current
	DESCRIPTION
	"Table entry display string for rewriteTranslationsDeletedOutboundTransl"
	::={rewriteTranslationsDeletedOutboundTranslLevelEntry 1}

rewriteTranslationsDeletedOutboundTranslLevelVal OBJECT-TYPE
	SYNTAX	 Counter64
	MAX-ACCESS  read-only
	STATUS      current
	DESCRIPTION
	"Table entry attribute for rewriteTranslationsDeletedOutboundTransl"
	::={rewriteTranslationsDeletedOutboundTranslLevelEntry 2}

rewriteTranslationsDeletedOutboundTranslLevelMom OBJECT-TYPE
	SYNTAX	 CounterBasedGauge64
	MAX-ACCESS  read-only
	STATUS      current
	DESCRIPTION
	"Table entry attribute for rewriteTranslationsDeletedOutboundTransl"
	::={rewriteTranslationsDeletedOutboundTranslLevelEntry 3}

rewriteTranslationsDeletedOutboundTranslLevelMax OBJECT-TYPE
	SYNTAX	 CounterBasedGauge64
	MAX-ACCESS  read-only
	STATUS      current
	DESCRIPTION
	"Table entry attribute for rewriteTranslationsDeletedOutboundTransl"
	::={rewriteTranslationsDeletedOutboundTranslLevelEntry 4}


rewriteTranslationsCountOutboundTransl	OBJECT IDENTIFIER ::={rewrite 96}

rewriteTranslationsCountOutboundTranslVal	OBJECT-TYPE
	SYNTAX	 CounterBasedGauge64
	MAX-ACCESS read-only
	STATUS current
	DESCRIPTION "Translations count (outbound)"

	::={rewriteTranslationsCountOutboundTransl 1}

rewriteTranslationsCountOutboundTranslMax	OBJECT-TYPE
	SYNTAX	 CounterBasedGauge64
	MAX-ACCESS read-only
	STATUS current
	DESCRIPTION "Translations count (outbound)"

	::={rewriteTranslationsCountOutboundTransl 3}

rewriteTranslationsCountOutboundTranslLevelTable OBJECT-TYPE
	SYNTAX      SEQUENCE OF RewriteTranslationsCountOutboundTranslLevelEntry
	MAX-ACCESS  not-accessible
	STATUS      current
	DESCRIPTION
	"Table for rewriteTranslationsCountOutboundTransl"
	::={rewriteTranslationsCountOutboundTransl 4}

rewriteTranslationsCountOutboundTranslLevelEntry OBJECT-TYPE
	SYNTAX      RewriteTranslationsCountOutboundTranslLevelEntry
	MAX-ACCESS  not-accessible
	STATUS      current
	DESCRIPTION
	"Table entry for rewriteTranslationsCountOutboundTransl"
	INDEX { rewriteTranslationsCountOutboundTranslLevelName }
	::={rewriteTranslationsCountOutboundTranslLevelTable 1}

RewriteTranslationsCountOutboundTranslLevelEntry ::=
	SEQUENCE {
		rewriteTranslationsCountOutboundTranslLevelName	DisplayString,
		rewriteTranslationsCountOutboundTranslLevelVal	CounterBasedGauge64,
		rewriteTranslationsCountOutboundTranslLevelMax	CounterBasedGauge64
	}

rewriteTranslationsCountOutboundTranslLevelName OBJECT-TYPE
	SYNTAX      DisplayString
	MAX-ACCESS  not-accessible
	STATUS      current
	DESCRIPTION
	"Table entry display string for rewriteTranslationsCountOutboundTransl"
	::={rewriteTranslationsCountOutboundTranslLevelEntry 1}

rewriteTranslationsCountOutboundTranslLevelVal OBJECT-TYPE
	SYNTAX	 CounterBasedGauge64
	MAX-ACCESS  read-only
	STATUS      current
	DESCRIPTION
	"Table entry attribute for rewriteTranslationsCountOutboundTransl"
	::={rewriteTranslationsCountOutboundTranslLevelEntry 2}

rewriteTranslationsCountOutboundTranslLevelMax OBJECT-TYPE
	SYNTAX	 CounterBasedGauge64
	MAX-ACCESS  read-only
	STATUS      current
	DESCRIPTION
	"Table entry attribute for rewriteTranslationsCountOutboundTransl"
	::={rewriteTranslationsCountOutboundTranslLevelEntry 4}


rewriteTranslationsCountTcpOutboundTransl	OBJECT IDENTIFIER ::={rewrite 97}

rewriteTranslationsCountTcpOutboundTranslVal	OBJECT-TYPE
	SYNTAX	 CounterBasedGauge64
	MAX-ACCESS read-only
	STATUS current
	DESCRIPTION "Translations count - TCP (outbound)"

	::={rewriteTranslationsCountTcpOutboundTransl 1}

rewriteTranslationsCountTcpOutboundTranslMax	OBJECT-TYPE
	SYNTAX	 CounterBasedGauge64
	MAX-ACCESS read-only
	STATUS current
	DESCRIPTION "Translations count - TCP (outbound)"

	::={rewriteTranslationsCountTcpOutboundTransl 3}

rewriteTranslationsCountTcpOutboundTranslLevelTable OBJECT-TYPE
	SYNTAX      SEQUENCE OF RewriteTranslationsCountTcpOutboundTranslLevelEntry
	MAX-ACCESS  not-accessible
	STATUS      current
	DESCRIPTION
	"Table for rewriteTranslationsCountTcpOutboundTransl"
	::={rewriteTranslationsCountTcpOutboundTransl 4}

rewriteTranslationsCountTcpOutboundTranslLevelEntry OBJECT-TYPE
	SYNTAX      RewriteTranslationsCountTcpOutboundTranslLevelEntry
	MAX-ACCESS  not-accessible
	STATUS      current
	DESCRIPTION
	"Table entry for rewriteTranslationsCountTcpOutboundTransl"
	INDEX { rewriteTranslationsCountTcpOutboundTranslLevelName }
	::={rewriteTranslationsCountTcpOutboundTranslLevelTable 1}

RewriteTranslationsCountTcpOutboundTranslLevelEntry ::=
	SEQUENCE {
		rewriteTranslationsCountTcpOutboundTranslLevelName	DisplayString,
		rewriteTranslationsCountTcpOutboundTranslLevelVal	CounterBasedGauge64,
		rewriteTranslationsCountTcpOutboundTranslLevelMax	CounterBasedGauge64
	}

rewriteTranslationsCountTcpOutboundTranslLevelName OBJECT-TYPE
	SYNTAX      DisplayString
	MAX-ACCESS  not-accessible
	STATUS      current
	DESCRIPTION
	"Table entry display string for rewriteTranslationsCountTcpOutboundTransl"
	::={rewriteTranslationsCountTcpOutboundTranslLevelEntry 1}

rewriteTranslationsCountTcpOutboundTranslLevelVal OBJECT-TYPE
	SYNTAX	 CounterBasedGauge64
	MAX-ACCESS  read-only
	STATUS      current
	DESCRIPTION
	"Table entry attribute for rewriteTranslationsCountTcpOutboundTransl"
	::={rewriteTranslationsCountTcpOutboundTranslLevelEntry 2}

rewriteTranslationsCountTcpOutboundTranslLevelMax OBJECT-TYPE
	SYNTAX	 CounterBasedGauge64
	MAX-ACCESS  read-only
	STATUS      current
	DESCRIPTION
	"Table entry attribute for rewriteTranslationsCountTcpOutboundTransl"
	::={rewriteTranslationsCountTcpOutboundTranslLevelEntry 4}


rewriteTranslationsCountUdpOutboundTransl	OBJECT IDENTIFIER ::={rewrite 98}

rewriteTranslationsCountUdpOutboundTranslVal	OBJECT-TYPE
	SYNTAX	 CounterBasedGauge64
	MAX-ACCESS read-only
	STATUS current
	DESCRIPTION "Translations count - UDP (outbound)"

	::={rewriteTranslationsCountUdpOutboundTransl 1}

rewriteTranslationsCountUdpOutboundTranslMax	OBJECT-TYPE
	SYNTAX	 CounterBasedGauge64
	MAX-ACCESS read-only
	STATUS current
	DESCRIPTION "Translations count - UDP (outbound)"

	::={rewriteTranslationsCountUdpOutboundTransl 3}

rewriteTranslationsCountUdpOutboundTranslLevelTable OBJECT-TYPE
	SYNTAX      SEQUENCE OF RewriteTranslationsCountUdpOutboundTranslLevelEntry
	MAX-ACCESS  not-accessible
	STATUS      current
	DESCRIPTION
	"Table for rewriteTranslationsCountUdpOutboundTransl"
	::={rewriteTranslationsCountUdpOutboundTransl 4}

rewriteTranslationsCountUdpOutboundTranslLevelEntry OBJECT-TYPE
	SYNTAX      RewriteTranslationsCountUdpOutboundTranslLevelEntry
	MAX-ACCESS  not-accessible
	STATUS      current
	DESCRIPTION
	"Table entry for rewriteTranslationsCountUdpOutboundTransl"
	INDEX { rewriteTranslationsCountUdpOutboundTranslLevelName }
	::={rewriteTranslationsCountUdpOutboundTranslLevelTable 1}

RewriteTranslationsCountUdpOutboundTranslLevelEntry ::=
	SEQUENCE {
		rewriteTranslationsCountUdpOutboundTranslLevelName	DisplayString,
		rewriteTranslationsCountUdpOutboundTranslLevelVal	CounterBasedGauge64,
		rewriteTranslationsCountUdpOutboundTranslLevelMax	CounterBasedGauge64
	}

rewriteTranslationsCountUdpOutboundTranslLevelName OBJECT-TYPE
	SYNTAX      DisplayString
	MAX-ACCESS  not-accessible
	STATUS      current
	DESCRIPTION
	"Table entry display string for rewriteTranslationsCountUdpOutboundTransl"
	::={rewriteTranslationsCountUdpOutboundTranslLevelEntry 1}

rewriteTranslationsCountUdpOutboundTranslLevelVal OBJECT-TYPE
	SYNTAX	 CounterBasedGauge64
	MAX-ACCESS  read-only
	STATUS      current
	DESCRIPTION
	"Table entry attribute for rewriteTranslationsCountUdpOutboundTransl"
	::={rewriteTranslationsCountUdpOutboundTranslLevelEntry 2}

rewriteTranslationsCountUdpOutboundTranslLevelMax OBJECT-TYPE
	SYNTAX	 CounterBasedGauge64
	MAX-ACCESS  read-only
	STATUS      current
	DESCRIPTION
	"Table entry attribute for rewriteTranslationsCountUdpOutboundTransl"
	::={rewriteTranslationsCountUdpOutboundTranslLevelEntry 4}


rewriteTranslationsCountIcmpOutboundTransl	OBJECT IDENTIFIER ::={rewrite 99}

rewriteTranslationsCountIcmpOutboundTranslVal	OBJECT-TYPE
	SYNTAX	 CounterBasedGauge64
	MAX-ACCESS read-only
	STATUS current
	DESCRIPTION "Translations count - ICMP (outbound)"

	::={rewriteTranslationsCountIcmpOutboundTransl 1}

rewriteTranslationsCountIcmpOutboundTranslMax	OBJECT-TYPE
	SYNTAX	 CounterBasedGauge64
	MAX-ACCESS read-only
	STATUS current
	DESCRIPTION "Translations count - ICMP (outbound)"

	::={rewriteTranslationsCountIcmpOutboundTransl 3}

rewriteTranslationsCountIcmpOutboundTranslLevelTable OBJECT-TYPE
	SYNTAX      SEQUENCE OF RewriteTranslationsCountIcmpOutboundTranslLevelEntry
	MAX-ACCESS  not-accessible
	STATUS      current
	DESCRIPTION
	"Table for rewriteTranslationsCountIcmpOutboundTransl"
	::={rewriteTranslationsCountIcmpOutboundTransl 4}

rewriteTranslationsCountIcmpOutboundTranslLevelEntry OBJECT-TYPE
	SYNTAX      RewriteTranslationsCountIcmpOutboundTranslLevelEntry
	MAX-ACCESS  not-accessible
	STATUS      current
	DESCRIPTION
	"Table entry for rewriteTranslationsCountIcmpOutboundTransl"
	INDEX { rewriteTranslationsCountIcmpOutboundTranslLevelName }
	::={rewriteTranslationsCountIcmpOutboundTranslLevelTable 1}

RewriteTranslationsCountIcmpOutboundTranslLevelEntry ::=
	SEQUENCE {
		rewriteTranslationsCountIcmpOutboundTranslLevelName	DisplayString,
		rewriteTranslationsCountIcmpOutboundTranslLevelVal	CounterBasedGauge64,
		rewriteTranslationsCountIcmpOutboundTranslLevelMax	CounterBasedGauge64
	}

rewriteTranslationsCountIcmpOutboundTranslLevelName OBJECT-TYPE
	SYNTAX      DisplayString
	MAX-ACCESS  not-accessible
	STATUS      current
	DESCRIPTION
	"Table entry display string for rewriteTranslationsCountIcmpOutboundTransl"
	::={rewriteTranslationsCountIcmpOutboundTranslLevelEntry 1}

rewriteTranslationsCountIcmpOutboundTranslLevelVal OBJECT-TYPE
	SYNTAX	 CounterBasedGauge64
	MAX-ACCESS  read-only
	STATUS      current
	DESCRIPTION
	"Table entry attribute for rewriteTranslationsCountIcmpOutboundTransl"
	::={rewriteTranslationsCountIcmpOutboundTranslLevelEntry 2}

rewriteTranslationsCountIcmpOutboundTranslLevelMax OBJECT-TYPE
	SYNTAX	 CounterBasedGauge64
	MAX-ACCESS  read-only
	STATUS      current
	DESCRIPTION
	"Table entry attribute for rewriteTranslationsCountIcmpOutboundTransl"
	::={rewriteTranslationsCountIcmpOutboundTranslLevelEntry 4}


rewritetrCreateFailNoObjOutbTrans	OBJECT IDENTIFIER ::={rewrite 100}

rewritetrCreateFailNoObjOutbTransVal	OBJECT-TYPE
	SYNTAX	 Counter64
	MAX-ACCESS read-only
	STATUS current
	DESCRIPTION "Translation creation failure (no object, outbound)"

	::={rewritetrCreateFailNoObjOutbTrans 1}

rewritetrCreateFailNoObjOutbTransMom	OBJECT-TYPE
	SYNTAX	 CounterBasedGauge64
	MAX-ACCESS read-only
	STATUS current
	DESCRIPTION "Translation creation failure (no object, outbound)"

	::={rewritetrCreateFailNoObjOutbTrans 2}

rewritetrCreateFailNoObjOutbTransMax	OBJECT-TYPE
	SYNTAX	 CounterBasedGauge64
	MAX-ACCESS read-only
	STATUS current
	DESCRIPTION "Translation creation failure (no object, outbound)"

	::={rewritetrCreateFailNoObjOutbTrans 3}

rewritetrCreateFailNoObjOutbTransLevelTable OBJECT-TYPE
	SYNTAX      SEQUENCE OF RewritetrCreateFailNoObjOutbTransLevelEntry
	MAX-ACCESS  not-accessible
	STATUS      current
	DESCRIPTION
	"Table for rewritetrCreateFailNoObjOutbTrans"
	::={rewritetrCreateFailNoObjOutbTrans 4}

rewritetrCreateFailNoObjOutbTransLevelEntry OBJECT-TYPE
	SYNTAX      RewritetrCreateFailNoObjOutbTransLevelEntry
	MAX-ACCESS  not-accessible
	STATUS      current
	DESCRIPTION
	"Table entry for rewritetrCreateFailNoObjOutbTrans"
	INDEX { rewritetrCreateFailNoObjOutbTransLevelName }
	::={rewritetrCreateFailNoObjOutbTransLevelTable 1}

RewritetrCreateFailNoObjOutbTransLevelEntry ::=
	SEQUENCE {
		rewritetrCreateFailNoObjOutbTransLevelName	DisplayString,
		rewritetrCreateFailNoObjOutbTransLevelVal	Counter64,
		rewritetrCreateFailNoObjOutbTransLevelMom	CounterBasedGauge64,
		rewritetrCreateFailNoObjOutbTransLevelMax	CounterBasedGauge64
	}

rewritetrCreateFailNoObjOutbTransLevelName OBJECT-TYPE
	SYNTAX      DisplayString
	MAX-ACCESS  not-accessible
	STATUS      current
	DESCRIPTION
	"Table entry display string for rewritetrCreateFailNoObjOutbTrans"
	::={rewritetrCreateFailNoObjOutbTransLevelEntry 1}

rewritetrCreateFailNoObjOutbTransLevelVal OBJECT-TYPE
	SYNTAX	 Counter64
	MAX-ACCESS  read-only
	STATUS      current
	DESCRIPTION
	"Table entry attribute for rewritetrCreateFailNoObjOutbTrans"
	::={rewritetrCreateFailNoObjOutbTransLevelEntry 2}

rewritetrCreateFailNoObjOutbTransLevelMom OBJECT-TYPE
	SYNTAX	 CounterBasedGauge64
	MAX-ACCESS  read-only
	STATUS      current
	DESCRIPTION
	"Table entry attribute for rewritetrCreateFailNoObjOutbTrans"
	::={rewritetrCreateFailNoObjOutbTransLevelEntry 3}

rewritetrCreateFailNoObjOutbTransLevelMax OBJECT-TYPE
	SYNTAX	 CounterBasedGauge64
	MAX-ACCESS  read-only
	STATUS      current
	DESCRIPTION
	"Table entry attribute for rewritetrCreateFailNoObjOutbTrans"
	::={rewritetrCreateFailNoObjOutbTransLevelEntry 4}


rewriteTransCreateFailResOutbTrans	OBJECT IDENTIFIER ::={rewrite 101}

rewriteTransCreateFailResOutbTransVal	OBJECT-TYPE
	SYNTAX	 Counter64
	MAX-ACCESS read-only
	STATUS current
	DESCRIPTION "Translation creation failure (resources, outbound)"

	::={rewriteTransCreateFailResOutbTrans 1}

rewriteTransCreateFailResOutbTransMom	OBJECT-TYPE
	SYNTAX	 CounterBasedGauge64
	MAX-ACCESS read-only
	STATUS current
	DESCRIPTION "Translation creation failure (resources, outbound)"

	::={rewriteTransCreateFailResOutbTrans 2}

rewriteTransCreateFailResOutbTransMax	OBJECT-TYPE
	SYNTAX	 CounterBasedGauge64
	MAX-ACCESS read-only
	STATUS current
	DESCRIPTION "Translation creation failure (resources, outbound)"

	::={rewriteTransCreateFailResOutbTrans 3}

rewriteTransCreateFailResOutbTransLevelTable OBJECT-TYPE
	SYNTAX      SEQUENCE OF RewriteTransCreateFailResOutbTransLevelEntry
	MAX-ACCESS  not-accessible
	STATUS      current
	DESCRIPTION
	"Table for rewriteTransCreateFailResOutbTrans"
	::={rewriteTransCreateFailResOutbTrans 4}

rewriteTransCreateFailResOutbTransLevelEntry OBJECT-TYPE
	SYNTAX      RewriteTransCreateFailResOutbTransLevelEntry
	MAX-ACCESS  not-accessible
	STATUS      current
	DESCRIPTION
	"Table entry for rewriteTransCreateFailResOutbTrans"
	INDEX { rewriteTransCreateFailResOutbTransLevelName }
	::={rewriteTransCreateFailResOutbTransLevelTable 1}

RewriteTransCreateFailResOutbTransLevelEntry ::=
	SEQUENCE {
		rewriteTransCreateFailResOutbTransLevelName	DisplayString,
		rewriteTransCreateFailResOutbTransLevelVal	Counter64,
		rewriteTransCreateFailResOutbTransLevelMom	CounterBasedGauge64,
		rewriteTransCreateFailResOutbTransLevelMax	CounterBasedGauge64
	}

rewriteTransCreateFailResOutbTransLevelName OBJECT-TYPE
	SYNTAX      DisplayString
	MAX-ACCESS  not-accessible
	STATUS      current
	DESCRIPTION
	"Table entry display string for rewriteTransCreateFailResOutbTrans"
	::={rewriteTransCreateFailResOutbTransLevelEntry 1}

rewriteTransCreateFailResOutbTransLevelVal OBJECT-TYPE
	SYNTAX	 Counter64
	MAX-ACCESS  read-only
	STATUS      current
	DESCRIPTION
	"Table entry attribute for rewriteTransCreateFailResOutbTrans"
	::={rewriteTransCreateFailResOutbTransLevelEntry 2}

rewriteTransCreateFailResOutbTransLevelMom OBJECT-TYPE
	SYNTAX	 CounterBasedGauge64
	MAX-ACCESS  read-only
	STATUS      current
	DESCRIPTION
	"Table entry attribute for rewriteTransCreateFailResOutbTrans"
	::={rewriteTransCreateFailResOutbTransLevelEntry 3}

rewriteTransCreateFailResOutbTransLevelMax OBJECT-TYPE
	SYNTAX	 CounterBasedGauge64
	MAX-ACCESS  read-only
	STATUS      current
	DESCRIPTION
	"Table entry attribute for rewriteTransCreateFailResOutbTrans"
	::={rewriteTransCreateFailResOutbTransLevelEntry 4}


rewriteTransCreateFailProtOutbTrans	OBJECT IDENTIFIER ::={rewrite 102}

rewriteTransCreateFailProtOutbTransVal	OBJECT-TYPE
	SYNTAX	 Counter64
	MAX-ACCESS read-only
	STATUS current
	DESCRIPTION "Translation creation failure (incompatible L4 protocol, outbound)"

	::={rewriteTransCreateFailProtOutbTrans 1}

rewriteTransCreateFailProtOutbTransMom	OBJECT-TYPE
	SYNTAX	 CounterBasedGauge64
	MAX-ACCESS read-only
	STATUS current
	DESCRIPTION "Translation creation failure (incompatible L4 protocol, outbound)"

	::={rewriteTransCreateFailProtOutbTrans 2}

rewriteTransCreateFailProtOutbTransMax	OBJECT-TYPE
	SYNTAX	 CounterBasedGauge64
	MAX-ACCESS read-only
	STATUS current
	DESCRIPTION "Translation creation failure (incompatible L4 protocol, outbound)"

	::={rewriteTransCreateFailProtOutbTrans 3}

rewriteTransCreateFailProtOutbTransLevelTable OBJECT-TYPE
	SYNTAX      SEQUENCE OF RewriteTransCreateFailProtOutbTransLevelEntry
	MAX-ACCESS  not-accessible
	STATUS      current
	DESCRIPTION
	"Table for rewriteTransCreateFailProtOutbTrans"
	::={rewriteTransCreateFailProtOutbTrans 4}

rewriteTransCreateFailProtOutbTransLevelEntry OBJECT-TYPE
	SYNTAX      RewriteTransCreateFailProtOutbTransLevelEntry
	MAX-ACCESS  not-accessible
	STATUS      current
	DESCRIPTION
	"Table entry for rewriteTransCreateFailProtOutbTrans"
	INDEX { rewriteTransCreateFailProtOutbTransLevelName }
	::={rewriteTransCreateFailProtOutbTransLevelTable 1}

RewriteTransCreateFailProtOutbTransLevelEntry ::=
	SEQUENCE {
		rewriteTransCreateFailProtOutbTransLevelName	DisplayString,
		rewriteTransCreateFailProtOutbTransLevelVal	Counter64,
		rewriteTransCreateFailProtOutbTransLevelMom	CounterBasedGauge64,
		rewriteTransCreateFailProtOutbTransLevelMax	CounterBasedGauge64
	}

rewriteTransCreateFailProtOutbTransLevelName OBJECT-TYPE
	SYNTAX      DisplayString
	MAX-ACCESS  not-accessible
	STATUS      current
	DESCRIPTION
	"Table entry display string for rewriteTransCreateFailProtOutbTrans"
	::={rewriteTransCreateFailProtOutbTransLevelEntry 1}

rewriteTransCreateFailProtOutbTransLevelVal OBJECT-TYPE
	SYNTAX	 Counter64
	MAX-ACCESS  read-only
	STATUS      current
	DESCRIPTION
	"Table entry attribute for rewriteTransCreateFailProtOutbTrans"
	::={rewriteTransCreateFailProtOutbTransLevelEntry 2}

rewriteTransCreateFailProtOutbTransLevelMom OBJECT-TYPE
	SYNTAX	 CounterBasedGauge64
	MAX-ACCESS  read-only
	STATUS      current
	DESCRIPTION
	"Table entry attribute for rewriteTransCreateFailProtOutbTrans"
	::={rewriteTransCreateFailProtOutbTransLevelEntry 3}

rewriteTransCreateFailProtOutbTransLevelMax OBJECT-TYPE
	SYNTAX	 CounterBasedGauge64
	MAX-ACCESS  read-only
	STATUS      current
	DESCRIPTION
	"Table entry attribute for rewriteTransCreateFailProtOutbTrans"
	::={rewriteTransCreateFailProtOutbTransLevelEntry 4}


rewriteTransCreateFailCollOutbTrans	OBJECT IDENTIFIER ::={rewrite 103}

rewriteTransCreateFailCollOutbTransVal	OBJECT-TYPE
	SYNTAX	 Counter64
	MAX-ACCESS read-only
	STATUS current
	DESCRIPTION "Translation creation failure (collision, outbound)"

	::={rewriteTransCreateFailCollOutbTrans 1}

rewriteTransCreateFailCollOutbTransMom	OBJECT-TYPE
	SYNTAX	 CounterBasedGauge64
	MAX-ACCESS read-only
	STATUS current
	DESCRIPTION "Translation creation failure (collision, outbound)"

	::={rewriteTransCreateFailCollOutbTrans 2}

rewriteTransCreateFailCollOutbTransMax	OBJECT-TYPE
	SYNTAX	 CounterBasedGauge64
	MAX-ACCESS read-only
	STATUS current
	DESCRIPTION "Translation creation failure (collision, outbound)"

	::={rewriteTransCreateFailCollOutbTrans 3}

rewriteTransCreateFailCollOutbTransLevelTable OBJECT-TYPE
	SYNTAX      SEQUENCE OF RewriteTransCreateFailCollOutbTransLevelEntry
	MAX-ACCESS  not-accessible
	STATUS      current
	DESCRIPTION
	"Table for rewriteTransCreateFailCollOutbTrans"
	::={rewriteTransCreateFailCollOutbTrans 4}

rewriteTransCreateFailCollOutbTransLevelEntry OBJECT-TYPE
	SYNTAX      RewriteTransCreateFailCollOutbTransLevelEntry
	MAX-ACCESS  not-accessible
	STATUS      current
	DESCRIPTION
	"Table entry for rewriteTransCreateFailCollOutbTrans"
	INDEX { rewriteTransCreateFailCollOutbTransLevelName }
	::={rewriteTransCreateFailCollOutbTransLevelTable 1}

RewriteTransCreateFailCollOutbTransLevelEntry ::=
	SEQUENCE {
		rewriteTransCreateFailCollOutbTransLevelName	DisplayString,
		rewriteTransCreateFailCollOutbTransLevelVal	Counter64,
		rewriteTransCreateFailCollOutbTransLevelMom	CounterBasedGauge64,
		rewriteTransCreateFailCollOutbTransLevelMax	CounterBasedGauge64
	}

rewriteTransCreateFailCollOutbTransLevelName OBJECT-TYPE
	SYNTAX      DisplayString
	MAX-ACCESS  not-accessible
	STATUS      current
	DESCRIPTION
	"Table entry display string for rewriteTransCreateFailCollOutbTrans"
	::={rewriteTransCreateFailCollOutbTransLevelEntry 1}

rewriteTransCreateFailCollOutbTransLevelVal OBJECT-TYPE
	SYNTAX	 Counter64
	MAX-ACCESS  read-only
	STATUS      current
	DESCRIPTION
	"Table entry attribute for rewriteTransCreateFailCollOutbTrans"
	::={rewriteTransCreateFailCollOutbTransLevelEntry 2}

rewriteTransCreateFailCollOutbTransLevelMom OBJECT-TYPE
	SYNTAX	 CounterBasedGauge64
	MAX-ACCESS  read-only
	STATUS      current
	DESCRIPTION
	"Table entry attribute for rewriteTransCreateFailCollOutbTrans"
	::={rewriteTransCreateFailCollOutbTransLevelEntry 3}

rewriteTransCreateFailCollOutbTransLevelMax OBJECT-TYPE
	SYNTAX	 CounterBasedGauge64
	MAX-ACCESS  read-only
	STATUS      current
	DESCRIPTION
	"Table entry attribute for rewriteTransCreateFailCollOutbTrans"
	::={rewriteTransCreateFailCollOutbTransLevelEntry 4}


rewriteTransCreateCollResOutbTrans	OBJECT IDENTIFIER ::={rewrite 104}

rewriteTransCreateCollResOutbTransVal	OBJECT-TYPE
	SYNTAX	 Counter64
	MAX-ACCESS read-only
	STATUS current
	DESCRIPTION "Translation creation collisions resolved (outbound)"

	::={rewriteTransCreateCollResOutbTrans 1}

rewriteTransCreateCollResOutbTransMom	OBJECT-TYPE
	SYNTAX	 CounterBasedGauge64
	MAX-ACCESS read-only
	STATUS current
	DESCRIPTION "Translation creation collisions resolved (outbound)"

	::={rewriteTransCreateCollResOutbTrans 2}

rewriteTransCreateCollResOutbTransMax	OBJECT-TYPE
	SYNTAX	 CounterBasedGauge64
	MAX-ACCESS read-only
	STATUS current
	DESCRIPTION "Translation creation collisions resolved (outbound)"

	::={rewriteTransCreateCollResOutbTrans 3}

rewriteTransCreateCollResOutbTransLevelTable OBJECT-TYPE
	SYNTAX      SEQUENCE OF RewriteTransCreateCollResOutbTransLevelEntry
	MAX-ACCESS  not-accessible
	STATUS      current
	DESCRIPTION
	"Table for rewriteTransCreateCollResOutbTrans"
	::={rewriteTransCreateCollResOutbTrans 4}

rewriteTransCreateCollResOutbTransLevelEntry OBJECT-TYPE
	SYNTAX      RewriteTransCreateCollResOutbTransLevelEntry
	MAX-ACCESS  not-accessible
	STATUS      current
	DESCRIPTION
	"Table entry for rewriteTransCreateCollResOutbTrans"
	INDEX { rewriteTransCreateCollResOutbTransLevelName }
	::={rewriteTransCreateCollResOutbTransLevelTable 1}

RewriteTransCreateCollResOutbTransLevelEntry ::=
	SEQUENCE {
		rewriteTransCreateCollResOutbTransLevelName	DisplayString,
		rewriteTransCreateCollResOutbTransLevelVal	Counter64,
		rewriteTransCreateCollResOutbTransLevelMom	CounterBasedGauge64,
		rewriteTransCreateCollResOutbTransLevelMax	CounterBasedGauge64
	}

rewriteTransCreateCollResOutbTransLevelName OBJECT-TYPE
	SYNTAX      DisplayString
	MAX-ACCESS  not-accessible
	STATUS      current
	DESCRIPTION
	"Table entry display string for rewriteTransCreateCollResOutbTrans"
	::={rewriteTransCreateCollResOutbTransLevelEntry 1}

rewriteTransCreateCollResOutbTransLevelVal OBJECT-TYPE
	SYNTAX	 Counter64
	MAX-ACCESS  read-only
	STATUS      current
	DESCRIPTION
	"Table entry attribute for rewriteTransCreateCollResOutbTrans"
	::={rewriteTransCreateCollResOutbTransLevelEntry 2}

rewriteTransCreateCollResOutbTransLevelMom OBJECT-TYPE
	SYNTAX	 CounterBasedGauge64
	MAX-ACCESS  read-only
	STATUS      current
	DESCRIPTION
	"Table entry attribute for rewriteTransCreateCollResOutbTrans"
	::={rewriteTransCreateCollResOutbTransLevelEntry 3}

rewriteTransCreateCollResOutbTransLevelMax OBJECT-TYPE
	SYNTAX	 CounterBasedGauge64
	MAX-ACCESS  read-only
	STATUS      current
	DESCRIPTION
	"Table entry attribute for rewriteTransCreateCollResOutbTrans"
	::={rewriteTransCreateCollResOutbTransLevelEntry 4}


rewriteTranslatedInboundPacketsOutboundTransl	OBJECT IDENTIFIER ::={rewrite 106}

rewriteTranslatedInboundPacketsOutboundTranslVal	OBJECT-TYPE
	SYNTAX	 Counter64
	MAX-ACCESS read-only
	STATUS current
	DESCRIPTION "Translated inbound packets (outbound)"

	::={rewriteTranslatedInboundPacketsOutboundTransl 1}

rewriteTranslatedInboundPacketsOutboundTranslMom	OBJECT-TYPE
	SYNTAX	 CounterBasedGauge64
	MAX-ACCESS read-only
	STATUS current
	DESCRIPTION "Translated inbound packets (outbound)"

	::={rewriteTranslatedInboundPacketsOutboundTransl 2}

rewriteTranslatedInboundPacketsOutboundTranslMax	OBJECT-TYPE
	SYNTAX	 CounterBasedGauge64
	MAX-ACCESS read-only
	STATUS current
	DESCRIPTION "Translated inbound packets (outbound)"

	::={rewriteTranslatedInboundPacketsOutboundTransl 3}

rewriteTranslatedInboundPacketsOutboundTranslLevelTable OBJECT-TYPE
	SYNTAX      SEQUENCE OF RewriteTranslatedInboundPacketsOutboundTranslLevelEntry
	MAX-ACCESS  not-accessible
	STATUS      current
	DESCRIPTION
	"Table for rewriteTranslatedInboundPacketsOutboundTransl"
	::={rewriteTranslatedInboundPacketsOutboundTransl 4}

rewriteTranslatedInboundPacketsOutboundTranslLevelEntry OBJECT-TYPE
	SYNTAX      RewriteTranslatedInboundPacketsOutboundTranslLevelEntry
	MAX-ACCESS  not-accessible
	STATUS      current
	DESCRIPTION
	"Table entry for rewriteTranslatedInboundPacketsOutboundTransl"
	INDEX { rewriteTranslatedInboundPacketsOutboundTranslLevelName }
	::={rewriteTranslatedInboundPacketsOutboundTranslLevelTable 1}

RewriteTranslatedInboundPacketsOutboundTranslLevelEntry ::=
	SEQUENCE {
		rewriteTranslatedInboundPacketsOutboundTranslLevelName	DisplayString,
		rewriteTranslatedInboundPacketsOutboundTranslLevelVal	Counter64,
		rewriteTranslatedInboundPacketsOutboundTranslLevelMom	CounterBasedGauge64,
		rewriteTranslatedInboundPacketsOutboundTranslLevelMax	CounterBasedGauge64
	}

rewriteTranslatedInboundPacketsOutboundTranslLevelName OBJECT-TYPE
	SYNTAX      DisplayString
	MAX-ACCESS  not-accessible
	STATUS      current
	DESCRIPTION
	"Table entry display string for rewriteTranslatedInboundPacketsOutboundTransl"
	::={rewriteTranslatedInboundPacketsOutboundTranslLevelEntry 1}

rewriteTranslatedInboundPacketsOutboundTranslLevelVal OBJECT-TYPE
	SYNTAX	 Counter64
	MAX-ACCESS  read-only
	STATUS      current
	DESCRIPTION
	"Table entry attribute for rewriteTranslatedInboundPacketsOutboundTransl"
	::={rewriteTranslatedInboundPacketsOutboundTranslLevelEntry 2}

rewriteTranslatedInboundPacketsOutboundTranslLevelMom OBJECT-TYPE
	SYNTAX	 CounterBasedGauge64
	MAX-ACCESS  read-only
	STATUS      current
	DESCRIPTION
	"Table entry attribute for rewriteTranslatedInboundPacketsOutboundTransl"
	::={rewriteTranslatedInboundPacketsOutboundTranslLevelEntry 3}

rewriteTranslatedInboundPacketsOutboundTranslLevelMax OBJECT-TYPE
	SYNTAX	 CounterBasedGauge64
	MAX-ACCESS  read-only
	STATUS      current
	DESCRIPTION
	"Table entry attribute for rewriteTranslatedInboundPacketsOutboundTransl"
	::={rewriteTranslatedInboundPacketsOutboundTranslLevelEntry 4}


rewriteTranslatedInboundBytesOutboundTransl	OBJECT IDENTIFIER ::={rewrite 107}

rewriteTranslatedInboundBytesOutboundTranslVal	OBJECT-TYPE
	SYNTAX	 Counter64
	MAX-ACCESS read-only
	STATUS current
	DESCRIPTION "Translated inbound bytes (outbound)"

	::={rewriteTranslatedInboundBytesOutboundTransl 1}

rewriteTranslatedInboundBytesOutboundTranslMom	OBJECT-TYPE
	SYNTAX	 CounterBasedGauge64
	MAX-ACCESS read-only
	STATUS current
	DESCRIPTION "Translated inbound bytes (outbound)"

	::={rewriteTranslatedInboundBytesOutboundTransl 2}

rewriteTranslatedInboundBytesOutboundTranslMax	OBJECT-TYPE
	SYNTAX	 CounterBasedGauge64
	MAX-ACCESS read-only
	STATUS current
	DESCRIPTION "Translated inbound bytes (outbound)"

	::={rewriteTranslatedInboundBytesOutboundTransl 3}

rewriteTranslatedInboundBytesOutboundTranslLevelTable OBJECT-TYPE
	SYNTAX      SEQUENCE OF RewriteTranslatedInboundBytesOutboundTranslLevelEntry
	MAX-ACCESS  not-accessible
	STATUS      current
	DESCRIPTION
	"Table for rewriteTranslatedInboundBytesOutboundTransl"
	::={rewriteTranslatedInboundBytesOutboundTransl 4}

rewriteTranslatedInboundBytesOutboundTranslLevelEntry OBJECT-TYPE
	SYNTAX      RewriteTranslatedInboundBytesOutboundTranslLevelEntry
	MAX-ACCESS  not-accessible
	STATUS      current
	DESCRIPTION
	"Table entry for rewriteTranslatedInboundBytesOutboundTransl"
	INDEX { rewriteTranslatedInboundBytesOutboundTranslLevelName }
	::={rewriteTranslatedInboundBytesOutboundTranslLevelTable 1}

RewriteTranslatedInboundBytesOutboundTranslLevelEntry ::=
	SEQUENCE {
		rewriteTranslatedInboundBytesOutboundTranslLevelName	DisplayString,
		rewriteTranslatedInboundBytesOutboundTranslLevelVal	Counter64,
		rewriteTranslatedInboundBytesOutboundTranslLevelMom	CounterBasedGauge64,
		rewriteTranslatedInboundBytesOutboundTranslLevelMax	CounterBasedGauge64
	}

rewriteTranslatedInboundBytesOutboundTranslLevelName OBJECT-TYPE
	SYNTAX      DisplayString
	MAX-ACCESS  not-accessible
	STATUS      current
	DESCRIPTION
	"Table entry display string for rewriteTranslatedInboundBytesOutboundTransl"
	::={rewriteTranslatedInboundBytesOutboundTranslLevelEntry 1}

rewriteTranslatedInboundBytesOutboundTranslLevelVal OBJECT-TYPE
	SYNTAX	 Counter64
	MAX-ACCESS  read-only
	STATUS      current
	DESCRIPTION
	"Table entry attribute for rewriteTranslatedInboundBytesOutboundTransl"
	::={rewriteTranslatedInboundBytesOutboundTranslLevelEntry 2}

rewriteTranslatedInboundBytesOutboundTranslLevelMom OBJECT-TYPE
	SYNTAX	 CounterBasedGauge64
	MAX-ACCESS  read-only
	STATUS      current
	DESCRIPTION
	"Table entry attribute for rewriteTranslatedInboundBytesOutboundTransl"
	::={rewriteTranslatedInboundBytesOutboundTranslLevelEntry 3}

rewriteTranslatedInboundBytesOutboundTranslLevelMax OBJECT-TYPE
	SYNTAX	 CounterBasedGauge64
	MAX-ACCESS  read-only
	STATUS      current
	DESCRIPTION
	"Table entry attribute for rewriteTranslatedInboundBytesOutboundTransl"
	::={rewriteTranslatedInboundBytesOutboundTranslLevelEntry 4}


rewriteTranslatedOutboundPacketsOutboundTransl	OBJECT IDENTIFIER ::={rewrite 108}

rewriteTranslatedOutboundPacketsOutboundTranslVal	OBJECT-TYPE
	SYNTAX	 Counter64
	MAX-ACCESS read-only
	STATUS current
	DESCRIPTION "Translated outbound packets (outbound)"

	::={rewriteTranslatedOutboundPacketsOutboundTransl 1}

rewriteTranslatedOutboundPacketsOutboundTranslMom	OBJECT-TYPE
	SYNTAX	 CounterBasedGauge64
	MAX-ACCESS read-only
	STATUS current
	DESCRIPTION "Translated outbound packets (outbound)"

	::={rewriteTranslatedOutboundPacketsOutboundTransl 2}

rewriteTranslatedOutboundPacketsOutboundTranslMax	OBJECT-TYPE
	SYNTAX	 CounterBasedGauge64
	MAX-ACCESS read-only
	STATUS current
	DESCRIPTION "Translated outbound packets (outbound)"

	::={rewriteTranslatedOutboundPacketsOutboundTransl 3}

rewriteTranslatedOutboundPacketsOutboundTranslLevelTable OBJECT-TYPE
	SYNTAX      SEQUENCE OF RewriteTranslatedOutboundPacketsOutboundTranslLevelEntry
	MAX-ACCESS  not-accessible
	STATUS      current
	DESCRIPTION
	"Table for rewriteTranslatedOutboundPacketsOutboundTransl"
	::={rewriteTranslatedOutboundPacketsOutboundTransl 4}

rewriteTranslatedOutboundPacketsOutboundTranslLevelEntry OBJECT-TYPE
	SYNTAX      RewriteTranslatedOutboundPacketsOutboundTranslLevelEntry
	MAX-ACCESS  not-accessible
	STATUS      current
	DESCRIPTION
	"Table entry for rewriteTranslatedOutboundPacketsOutboundTransl"
	INDEX { rewriteTranslatedOutboundPacketsOutboundTranslLevelName }
	::={rewriteTranslatedOutboundPacketsOutboundTranslLevelTable 1}

RewriteTranslatedOutboundPacketsOutboundTranslLevelEntry ::=
	SEQUENCE {
		rewriteTranslatedOutboundPacketsOutboundTranslLevelName	DisplayString,
		rewriteTranslatedOutboundPacketsOutboundTranslLevelVal	Counter64,
		rewriteTranslatedOutboundPacketsOutboundTranslLevelMom	CounterBasedGauge64,
		rewriteTranslatedOutboundPacketsOutboundTranslLevelMax	CounterBasedGauge64
	}

rewriteTranslatedOutboundPacketsOutboundTranslLevelName OBJECT-TYPE
	SYNTAX      DisplayString
	MAX-ACCESS  not-accessible
	STATUS      current
	DESCRIPTION
	"Table entry display string for rewriteTranslatedOutboundPacketsOutboundTransl"
	::={rewriteTranslatedOutboundPacketsOutboundTranslLevelEntry 1}

rewriteTranslatedOutboundPacketsOutboundTranslLevelVal OBJECT-TYPE
	SYNTAX	 Counter64
	MAX-ACCESS  read-only
	STATUS      current
	DESCRIPTION
	"Table entry attribute for rewriteTranslatedOutboundPacketsOutboundTransl"
	::={rewriteTranslatedOutboundPacketsOutboundTranslLevelEntry 2}

rewriteTranslatedOutboundPacketsOutboundTranslLevelMom OBJECT-TYPE
	SYNTAX	 CounterBasedGauge64
	MAX-ACCESS  read-only
	STATUS      current
	DESCRIPTION
	"Table entry attribute for rewriteTranslatedOutboundPacketsOutboundTransl"
	::={rewriteTranslatedOutboundPacketsOutboundTranslLevelEntry 3}

rewriteTranslatedOutboundPacketsOutboundTranslLevelMax OBJECT-TYPE
	SYNTAX	 CounterBasedGauge64
	MAX-ACCESS  read-only
	STATUS      current
	DESCRIPTION
	"Table entry attribute for rewriteTranslatedOutboundPacketsOutboundTransl"
	::={rewriteTranslatedOutboundPacketsOutboundTranslLevelEntry 4}


rewriteTranslatedOutboundBytesOutboundTransl	OBJECT IDENTIFIER ::={rewrite 109}

rewriteTranslatedOutboundBytesOutboundTranslVal	OBJECT-TYPE
	SYNTAX	 Counter64
	MAX-ACCESS read-only
	STATUS current
	DESCRIPTION "Translated outbound bytes (outbound)"

	::={rewriteTranslatedOutboundBytesOutboundTransl 1}

rewriteTranslatedOutboundBytesOutboundTranslMom	OBJECT-TYPE
	SYNTAX	 CounterBasedGauge64
	MAX-ACCESS read-only
	STATUS current
	DESCRIPTION "Translated outbound bytes (outbound)"

	::={rewriteTranslatedOutboundBytesOutboundTransl 2}

rewriteTranslatedOutboundBytesOutboundTranslMax	OBJECT-TYPE
	SYNTAX	 CounterBasedGauge64
	MAX-ACCESS read-only
	STATUS current
	DESCRIPTION "Translated outbound bytes (outbound)"

	::={rewriteTranslatedOutboundBytesOutboundTransl 3}

rewriteTranslatedOutboundBytesOutboundTranslLevelTable OBJECT-TYPE
	SYNTAX      SEQUENCE OF RewriteTranslatedOutboundBytesOutboundTranslLevelEntry
	MAX-ACCESS  not-accessible
	STATUS      current
	DESCRIPTION
	"Table for rewriteTranslatedOutboundBytesOutboundTransl"
	::={rewriteTranslatedOutboundBytesOutboundTransl 4}

rewriteTranslatedOutboundBytesOutboundTranslLevelEntry OBJECT-TYPE
	SYNTAX      RewriteTranslatedOutboundBytesOutboundTranslLevelEntry
	MAX-ACCESS  not-accessible
	STATUS      current
	DESCRIPTION
	"Table entry for rewriteTranslatedOutboundBytesOutboundTransl"
	INDEX { rewriteTranslatedOutboundBytesOutboundTranslLevelName }
	::={rewriteTranslatedOutboundBytesOutboundTranslLevelTable 1}

RewriteTranslatedOutboundBytesOutboundTranslLevelEntry ::=
	SEQUENCE {
		rewriteTranslatedOutboundBytesOutboundTranslLevelName	DisplayString,
		rewriteTranslatedOutboundBytesOutboundTranslLevelVal	Counter64,
		rewriteTranslatedOutboundBytesOutboundTranslLevelMom	CounterBasedGauge64,
		rewriteTranslatedOutboundBytesOutboundTranslLevelMax	CounterBasedGauge64
	}

rewriteTranslatedOutboundBytesOutboundTranslLevelName OBJECT-TYPE
	SYNTAX      DisplayString
	MAX-ACCESS  not-accessible
	STATUS      current
	DESCRIPTION
	"Table entry display string for rewriteTranslatedOutboundBytesOutboundTransl"
	::={rewriteTranslatedOutboundBytesOutboundTranslLevelEntry 1}

rewriteTranslatedOutboundBytesOutboundTranslLevelVal OBJECT-TYPE
	SYNTAX	 Counter64
	MAX-ACCESS  read-only
	STATUS      current
	DESCRIPTION
	"Table entry attribute for rewriteTranslatedOutboundBytesOutboundTransl"
	::={rewriteTranslatedOutboundBytesOutboundTranslLevelEntry 2}

rewriteTranslatedOutboundBytesOutboundTranslLevelMom OBJECT-TYPE
	SYNTAX	 CounterBasedGauge64
	MAX-ACCESS  read-only
	STATUS      current
	DESCRIPTION
	"Table entry attribute for rewriteTranslatedOutboundBytesOutboundTransl"
	::={rewriteTranslatedOutboundBytesOutboundTranslLevelEntry 3}

rewriteTranslatedOutboundBytesOutboundTranslLevelMax OBJECT-TYPE
	SYNTAX	 CounterBasedGauge64
	MAX-ACCESS  read-only
	STATUS      current
	DESCRIPTION
	"Table entry attribute for rewriteTranslatedOutboundBytesOutboundTransl"
	::={rewriteTranslatedOutboundBytesOutboundTranslLevelEntry 4}


rewriteTranslationRefusedStalePassback	OBJECT IDENTIFIER ::={rewrite 110}

rewriteTranslationRefusedStalePassbackVal	OBJECT-TYPE
	SYNTAX	 Counter64
	MAX-ACCESS read-only
	STATUS current
	DESCRIPTION "Translation refused on stale passback"

	::={rewriteTranslationRefusedStalePassback 1}

rewriteTranslationRefusedStalePassbackMom	OBJECT-TYPE
	SYNTAX	 CounterBasedGauge64
	MAX-ACCESS read-only
	STATUS current
	DESCRIPTION "Translation refused on stale passback"

	::={rewriteTranslationRefusedStalePassback 2}

rewriteTranslationRefusedStalePassbackMax	OBJECT-TYPE
	SYNTAX	 CounterBasedGauge64
	MAX-ACCESS read-only
	STATUS current
	DESCRIPTION "Translation refused on stale passback"

	::={rewriteTranslationRefusedStalePassback 3}

rewriteTranslationRefusedStalePassbackLevelTable OBJECT-TYPE
	SYNTAX      SEQUENCE OF RewriteTranslationRefusedStalePassbackLevelEntry
	MAX-ACCESS  not-accessible
	STATUS      current
	DESCRIPTION
	"Table for rewriteTranslationRefusedStalePassback"
	::={rewriteTranslationRefusedStalePassback 4}

rewriteTranslationRefusedStalePassbackLevelEntry OBJECT-TYPE
	SYNTAX      RewriteTranslationRefusedStalePassbackLevelEntry
	MAX-ACCESS  not-accessible
	STATUS      current
	DESCRIPTION
	"Table entry for rewriteTranslationRefusedStalePassback"
	INDEX { rewriteTranslationRefusedStalePassbackLevelName }
	::={rewriteTranslationRefusedStalePassbackLevelTable 1}

RewriteTranslationRefusedStalePassbackLevelEntry ::=
	SEQUENCE {
		rewriteTranslationRefusedStalePassbackLevelName	DisplayString,
		rewriteTranslationRefusedStalePassbackLevelVal	Counter64,
		rewriteTranslationRefusedStalePassbackLevelMom	CounterBasedGauge64,
		rewriteTranslationRefusedStalePassbackLevelMax	CounterBasedGauge64
	}

rewriteTranslationRefusedStalePassbackLevelName OBJECT-TYPE
	SYNTAX      DisplayString
	MAX-ACCESS  not-accessible
	STATUS      current
	DESCRIPTION
	"Table entry display string for rewriteTranslationRefusedStalePassback"
	::={rewriteTranslationRefusedStalePassbackLevelEntry 1}

rewriteTranslationRefusedStalePassbackLevelVal OBJECT-TYPE
	SYNTAX	 Counter64
	MAX-ACCESS  read-only
	STATUS      current
	DESCRIPTION
	"Table entry attribute for rewriteTranslationRefusedStalePassback"
	::={rewriteTranslationRefusedStalePassbackLevelEntry 2}

rewriteTranslationRefusedStalePassbackLevelMom OBJECT-TYPE
	SYNTAX	 CounterBasedGauge64
	MAX-ACCESS  read-only
	STATUS      current
	DESCRIPTION
	"Table entry attribute for rewriteTranslationRefusedStalePassback"
	::={rewriteTranslationRefusedStalePassbackLevelEntry 3}

rewriteTranslationRefusedStalePassbackLevelMax OBJECT-TYPE
	SYNTAX	 CounterBasedGauge64
	MAX-ACCESS  read-only
	STATUS      current
	DESCRIPTION
	"Table entry attribute for rewriteTranslationRefusedStalePassback"
	::={rewriteTranslationRefusedStalePassbackLevelEntry 4}


rewritePortBlockCreationFailures	OBJECT IDENTIFIER ::={rewrite 121}

rewritePortBlockCreationFailuresVal	OBJECT-TYPE
	SYNTAX	 Counter64
	MAX-ACCESS read-only
	STATUS current
	DESCRIPTION "Port block creation failures"

	::={rewritePortBlockCreationFailures 1}

rewritePortBlockCreationFailuresMom	OBJECT-TYPE
	SYNTAX	 CounterBasedGauge64
	MAX-ACCESS read-only
	STATUS current
	DESCRIPTION "Port block creation failures"

	::={rewritePortBlockCreationFailures 2}

rewritePortBlockCreationFailuresMax	OBJECT-TYPE
	SYNTAX	 CounterBasedGauge64
	MAX-ACCESS read-only
	STATUS current
	DESCRIPTION "Port block creation failures"

	::={rewritePortBlockCreationFailures 3}

rewritePortBlockCreationFailuresLevelTable OBJECT-TYPE
	SYNTAX      SEQUENCE OF RewritePortBlockCreationFailuresLevelEntry
	MAX-ACCESS  not-accessible
	STATUS      current
	DESCRIPTION
	"Table for rewritePortBlockCreationFailures"
	::={rewritePortBlockCreationFailures 4}

rewritePortBlockCreationFailuresLevelEntry OBJECT-TYPE
	SYNTAX      RewritePortBlockCreationFailuresLevelEntry
	MAX-ACCESS  not-accessible
	STATUS      current
	DESCRIPTION
	"Table entry for rewritePortBlockCreationFailures"
	INDEX { rewritePortBlockCreationFailuresLevelName }
	::={rewritePortBlockCreationFailuresLevelTable 1}

RewritePortBlockCreationFailuresLevelEntry ::=
	SEQUENCE {
		rewritePortBlockCreationFailuresLevelName	DisplayString,
		rewritePortBlockCreationFailuresLevelVal	Counter64,
		rewritePortBlockCreationFailuresLevelMom	CounterBasedGauge64,
		rewritePortBlockCreationFailuresLevelMax	CounterBasedGauge64
	}

rewritePortBlockCreationFailuresLevelName OBJECT-TYPE
	SYNTAX      DisplayString
	MAX-ACCESS  not-accessible
	STATUS      current
	DESCRIPTION
	"Table entry display string for rewritePortBlockCreationFailures"
	::={rewritePortBlockCreationFailuresLevelEntry 1}

rewritePortBlockCreationFailuresLevelVal OBJECT-TYPE
	SYNTAX	 Counter64
	MAX-ACCESS  read-only
	STATUS      current
	DESCRIPTION
	"Table entry attribute for rewritePortBlockCreationFailures"
	::={rewritePortBlockCreationFailuresLevelEntry 2}

rewritePortBlockCreationFailuresLevelMom OBJECT-TYPE
	SYNTAX	 CounterBasedGauge64
	MAX-ACCESS  read-only
	STATUS      current
	DESCRIPTION
	"Table entry attribute for rewritePortBlockCreationFailures"
	::={rewritePortBlockCreationFailuresLevelEntry 3}

rewritePortBlockCreationFailuresLevelMax OBJECT-TYPE
	SYNTAX	 CounterBasedGauge64
	MAX-ACCESS  read-only
	STATUS      current
	DESCRIPTION
	"Table entry attribute for rewritePortBlockCreationFailures"
	::={rewritePortBlockCreationFailuresLevelEntry 4}


rewritePortBlockCreationFailuresResources	OBJECT IDENTIFIER ::={rewrite 122}

rewritePortBlockCreationFailuresResourcesVal	OBJECT-TYPE
	SYNTAX	 Counter64
	MAX-ACCESS read-only
	STATUS current
	DESCRIPTION "Port block creation failures (resources)"

	::={rewritePortBlockCreationFailuresResources 1}

rewritePortBlockCreationFailuresResourcesMom	OBJECT-TYPE
	SYNTAX	 CounterBasedGauge64
	MAX-ACCESS read-only
	STATUS current
	DESCRIPTION "Port block creation failures (resources)"

	::={rewritePortBlockCreationFailuresResources 2}

rewritePortBlockCreationFailuresResourcesMax	OBJECT-TYPE
	SYNTAX	 CounterBasedGauge64
	MAX-ACCESS read-only
	STATUS current
	DESCRIPTION "Port block creation failures (resources)"

	::={rewritePortBlockCreationFailuresResources 3}

rewritePortBlockCreationFailuresResourcesLevelTable OBJECT-TYPE
	SYNTAX      SEQUENCE OF RewritePortBlockCreationFailuresResourcesLevelEntry
	MAX-ACCESS  not-accessible
	STATUS      current
	DESCRIPTION
	"Table for rewritePortBlockCreationFailuresResources"
	::={rewritePortBlockCreationFailuresResources 4}

rewritePortBlockCreationFailuresResourcesLevelEntry OBJECT-TYPE
	SYNTAX      RewritePortBlockCreationFailuresResourcesLevelEntry
	MAX-ACCESS  not-accessible
	STATUS      current
	DESCRIPTION
	"Table entry for rewritePortBlockCreationFailuresResources"
	INDEX { rewritePortBlockCreationFailuresResourcesLevelName }
	::={rewritePortBlockCreationFailuresResourcesLevelTable 1}

RewritePortBlockCreationFailuresResourcesLevelEntry ::=
	SEQUENCE {
		rewritePortBlockCreationFailuresResourcesLevelName	DisplayString,
		rewritePortBlockCreationFailuresResourcesLevelVal	Counter64,
		rewritePortBlockCreationFailuresResourcesLevelMom	CounterBasedGauge64,
		rewritePortBlockCreationFailuresResourcesLevelMax	CounterBasedGauge64
	}

rewritePortBlockCreationFailuresResourcesLevelName OBJECT-TYPE
	SYNTAX      DisplayString
	MAX-ACCESS  not-accessible
	STATUS      current
	DESCRIPTION
	"Table entry display string for rewritePortBlockCreationFailuresResources"
	::={rewritePortBlockCreationFailuresResourcesLevelEntry 1}

rewritePortBlockCreationFailuresResourcesLevelVal OBJECT-TYPE
	SYNTAX	 Counter64
	MAX-ACCESS  read-only
	STATUS      current
	DESCRIPTION
	"Table entry attribute for rewritePortBlockCreationFailuresResources"
	::={rewritePortBlockCreationFailuresResourcesLevelEntry 2}

rewritePortBlockCreationFailuresResourcesLevelMom OBJECT-TYPE
	SYNTAX	 CounterBasedGauge64
	MAX-ACCESS  read-only
	STATUS      current
	DESCRIPTION
	"Table entry attribute for rewritePortBlockCreationFailuresResources"
	::={rewritePortBlockCreationFailuresResourcesLevelEntry 3}

rewritePortBlockCreationFailuresResourcesLevelMax OBJECT-TYPE
	SYNTAX	 CounterBasedGauge64
	MAX-ACCESS  read-only
	STATUS      current
	DESCRIPTION
	"Table entry attribute for rewritePortBlockCreationFailuresResources"
	::={rewritePortBlockCreationFailuresResourcesLevelEntry 4}


rewritePortBlockCreationFailuresStartGtEnd	OBJECT IDENTIFIER ::={rewrite 123}

rewritePortBlockCreationFailuresStartGtEndVal	OBJECT-TYPE
	SYNTAX	 Counter64
	MAX-ACCESS read-only
	STATUS current
	DESCRIPTION "Port block creation failures (start > end)"

	::={rewritePortBlockCreationFailuresStartGtEnd 1}

rewritePortBlockCreationFailuresStartGtEndMom	OBJECT-TYPE
	SYNTAX	 CounterBasedGauge64
	MAX-ACCESS read-only
	STATUS current
	DESCRIPTION "Port block creation failures (start > end)"

	::={rewritePortBlockCreationFailuresStartGtEnd 2}

rewritePortBlockCreationFailuresStartGtEndMax	OBJECT-TYPE
	SYNTAX	 CounterBasedGauge64
	MAX-ACCESS read-only
	STATUS current
	DESCRIPTION "Port block creation failures (start > end)"

	::={rewritePortBlockCreationFailuresStartGtEnd 3}

rewritePortBlockCreationFailuresStartGtEndLevelTable OBJECT-TYPE
	SYNTAX      SEQUENCE OF RewritePortBlockCreationFailuresStartGtEndLevelEntry
	MAX-ACCESS  not-accessible
	STATUS      current
	DESCRIPTION
	"Table for rewritePortBlockCreationFailuresStartGtEnd"
	::={rewritePortBlockCreationFailuresStartGtEnd 4}

rewritePortBlockCreationFailuresStartGtEndLevelEntry OBJECT-TYPE
	SYNTAX      RewritePortBlockCreationFailuresStartGtEndLevelEntry
	MAX-ACCESS  not-accessible
	STATUS      current
	DESCRIPTION
	"Table entry for rewritePortBlockCreationFailuresStartGtEnd"
	INDEX { rewritePortBlockCreationFailuresStartGtEndLevelName }
	::={rewritePortBlockCreationFailuresStartGtEndLevelTable 1}

RewritePortBlockCreationFailuresStartGtEndLevelEntry ::=
	SEQUENCE {
		rewritePortBlockCreationFailuresStartGtEndLevelName	DisplayString,
		rewritePortBlockCreationFailuresStartGtEndLevelVal	Counter64,
		rewritePortBlockCreationFailuresStartGtEndLevelMom	CounterBasedGauge64,
		rewritePortBlockCreationFailuresStartGtEndLevelMax	CounterBasedGauge64
	}

rewritePortBlockCreationFailuresStartGtEndLevelName OBJECT-TYPE
	SYNTAX      DisplayString
	MAX-ACCESS  not-accessible
	STATUS      current
	DESCRIPTION
	"Table entry display string for rewritePortBlockCreationFailuresStartGtEnd"
	::={rewritePortBlockCreationFailuresStartGtEndLevelEntry 1}

rewritePortBlockCreationFailuresStartGtEndLevelVal OBJECT-TYPE
	SYNTAX	 Counter64
	MAX-ACCESS  read-only
	STATUS      current
	DESCRIPTION
	"Table entry attribute for rewritePortBlockCreationFailuresStartGtEnd"
	::={rewritePortBlockCreationFailuresStartGtEndLevelEntry 2}

rewritePortBlockCreationFailuresStartGtEndLevelMom OBJECT-TYPE
	SYNTAX	 CounterBasedGauge64
	MAX-ACCESS  read-only
	STATUS      current
	DESCRIPTION
	"Table entry attribute for rewritePortBlockCreationFailuresStartGtEnd"
	::={rewritePortBlockCreationFailuresStartGtEndLevelEntry 3}

rewritePortBlockCreationFailuresStartGtEndLevelMax OBJECT-TYPE
	SYNTAX	 CounterBasedGauge64
	MAX-ACCESS  read-only
	STATUS      current
	DESCRIPTION
	"Table entry attribute for rewritePortBlockCreationFailuresStartGtEnd"
	::={rewritePortBlockCreationFailuresStartGtEndLevelEntry 4}


rewritePortBlockCreationFailuresSplitLowHigh	OBJECT IDENTIFIER ::={rewrite 124}

rewritePortBlockCreationFailuresSplitLowHighVal	OBJECT-TYPE
	SYNTAX	 Counter64
	MAX-ACCESS read-only
	STATUS current
	DESCRIPTION "Port block creation failures (low and high)"

	::={rewritePortBlockCreationFailuresSplitLowHigh 1}

rewritePortBlockCreationFailuresSplitLowHighMom	OBJECT-TYPE
	SYNTAX	 CounterBasedGauge64
	MAX-ACCESS read-only
	STATUS current
	DESCRIPTION "Port block creation failures (low and high)"

	::={rewritePortBlockCreationFailuresSplitLowHigh 2}

rewritePortBlockCreationFailuresSplitLowHighMax	OBJECT-TYPE
	SYNTAX	 CounterBasedGauge64
	MAX-ACCESS read-only
	STATUS current
	DESCRIPTION "Port block creation failures (low and high)"

	::={rewritePortBlockCreationFailuresSplitLowHigh 3}

rewritePortBlockCreationFailuresSplitLowHighLevelTable OBJECT-TYPE
	SYNTAX      SEQUENCE OF RewritePortBlockCreationFailuresSplitLowHighLevelEntry
	MAX-ACCESS  not-accessible
	STATUS      current
	DESCRIPTION
	"Table for rewritePortBlockCreationFailuresSplitLowHigh"
	::={rewritePortBlockCreationFailuresSplitLowHigh 4}

rewritePortBlockCreationFailuresSplitLowHighLevelEntry OBJECT-TYPE
	SYNTAX      RewritePortBlockCreationFailuresSplitLowHighLevelEntry
	MAX-ACCESS  not-accessible
	STATUS      current
	DESCRIPTION
	"Table entry for rewritePortBlockCreationFailuresSplitLowHigh"
	INDEX { rewritePortBlockCreationFailuresSplitLowHighLevelName }
	::={rewritePortBlockCreationFailuresSplitLowHighLevelTable 1}

RewritePortBlockCreationFailuresSplitLowHighLevelEntry ::=
	SEQUENCE {
		rewritePortBlockCreationFailuresSplitLowHighLevelName	DisplayString,
		rewritePortBlockCreationFailuresSplitLowHighLevelVal	Counter64,
		rewritePortBlockCreationFailuresSplitLowHighLevelMom	CounterBasedGauge64,
		rewritePortBlockCreationFailuresSplitLowHighLevelMax	CounterBasedGauge64
	}

rewritePortBlockCreationFailuresSplitLowHighLevelName OBJECT-TYPE
	SYNTAX      DisplayString
	MAX-ACCESS  not-accessible
	STATUS      current
	DESCRIPTION
	"Table entry display string for rewritePortBlockCreationFailuresSplitLowHigh"
	::={rewritePortBlockCreationFailuresSplitLowHighLevelEntry 1}

rewritePortBlockCreationFailuresSplitLowHighLevelVal OBJECT-TYPE
	SYNTAX	 Counter64
	MAX-ACCESS  read-only
	STATUS      current
	DESCRIPTION
	"Table entry attribute for rewritePortBlockCreationFailuresSplitLowHigh"
	::={rewritePortBlockCreationFailuresSplitLowHighLevelEntry 2}

rewritePortBlockCreationFailuresSplitLowHighLevelMom OBJECT-TYPE
	SYNTAX	 CounterBasedGauge64
	MAX-ACCESS  read-only
	STATUS      current
	DESCRIPTION
	"Table entry attribute for rewritePortBlockCreationFailuresSplitLowHigh"
	::={rewritePortBlockCreationFailuresSplitLowHighLevelEntry 3}

rewritePortBlockCreationFailuresSplitLowHighLevelMax OBJECT-TYPE
	SYNTAX	 CounterBasedGauge64
	MAX-ACCESS  read-only
	STATUS      current
	DESCRIPTION
	"Table entry attribute for rewritePortBlockCreationFailuresSplitLowHigh"
	::={rewritePortBlockCreationFailuresSplitLowHighLevelEntry 4}


rewritePortBlockCreationAbortionCacheFull	OBJECT IDENTIFIER ::={rewrite 125}

rewritePortBlockCreationAbortionCacheFullVal	OBJECT-TYPE
	SYNTAX	 Counter64
	MAX-ACCESS read-only
	STATUS current
	DESCRIPTION "Port block creation abortion (cache full)"

	::={rewritePortBlockCreationAbortionCacheFull 1}

rewritePortBlockCreationAbortionCacheFullMom	OBJECT-TYPE
	SYNTAX	 CounterBasedGauge64
	MAX-ACCESS read-only
	STATUS current
	DESCRIPTION "Port block creation abortion (cache full)"

	::={rewritePortBlockCreationAbortionCacheFull 2}

rewritePortBlockCreationAbortionCacheFullMax	OBJECT-TYPE
	SYNTAX	 CounterBasedGauge64
	MAX-ACCESS read-only
	STATUS current
	DESCRIPTION "Port block creation abortion (cache full)"

	::={rewritePortBlockCreationAbortionCacheFull 3}

rewritePortBlockCreationAbortionCacheFullLevelTable OBJECT-TYPE
	SYNTAX      SEQUENCE OF RewritePortBlockCreationAbortionCacheFullLevelEntry
	MAX-ACCESS  not-accessible
	STATUS      current
	DESCRIPTION
	"Table for rewritePortBlockCreationAbortionCacheFull"
	::={rewritePortBlockCreationAbortionCacheFull 4}

rewritePortBlockCreationAbortionCacheFullLevelEntry OBJECT-TYPE
	SYNTAX      RewritePortBlockCreationAbortionCacheFullLevelEntry
	MAX-ACCESS  not-accessible
	STATUS      current
	DESCRIPTION
	"Table entry for rewritePortBlockCreationAbortionCacheFull"
	INDEX { rewritePortBlockCreationAbortionCacheFullLevelName }
	::={rewritePortBlockCreationAbortionCacheFullLevelTable 1}

RewritePortBlockCreationAbortionCacheFullLevelEntry ::=
	SEQUENCE {
		rewritePortBlockCreationAbortionCacheFullLevelName	DisplayString,
		rewritePortBlockCreationAbortionCacheFullLevelVal	Counter64,
		rewritePortBlockCreationAbortionCacheFullLevelMom	CounterBasedGauge64,
		rewritePortBlockCreationAbortionCacheFullLevelMax	CounterBasedGauge64
	}

rewritePortBlockCreationAbortionCacheFullLevelName OBJECT-TYPE
	SYNTAX      DisplayString
	MAX-ACCESS  not-accessible
	STATUS      current
	DESCRIPTION
	"Table entry display string for rewritePortBlockCreationAbortionCacheFull"
	::={rewritePortBlockCreationAbortionCacheFullLevelEntry 1}

rewritePortBlockCreationAbortionCacheFullLevelVal OBJECT-TYPE
	SYNTAX	 Counter64
	MAX-ACCESS  read-only
	STATUS      current
	DESCRIPTION
	"Table entry attribute for rewritePortBlockCreationAbortionCacheFull"
	::={rewritePortBlockCreationAbortionCacheFullLevelEntry 2}

rewritePortBlockCreationAbortionCacheFullLevelMom OBJECT-TYPE
	SYNTAX	 CounterBasedGauge64
	MAX-ACCESS  read-only
	STATUS      current
	DESCRIPTION
	"Table entry attribute for rewritePortBlockCreationAbortionCacheFull"
	::={rewritePortBlockCreationAbortionCacheFullLevelEntry 3}

rewritePortBlockCreationAbortionCacheFullLevelMax OBJECT-TYPE
	SYNTAX	 CounterBasedGauge64
	MAX-ACCESS  read-only
	STATUS      current
	DESCRIPTION
	"Table entry attribute for rewritePortBlockCreationAbortionCacheFull"
	::={rewritePortBlockCreationAbortionCacheFullLevelEntry 4}


rewritePortBlockAssignmentFailures	OBJECT IDENTIFIER ::={rewrite 126}

rewritePortBlockAssignmentFailuresVal	OBJECT-TYPE
	SYNTAX	 Counter64
	MAX-ACCESS read-only
	STATUS current
	DESCRIPTION "Port block assignment failures"

	::={rewritePortBlockAssignmentFailures 1}

rewritePortBlockAssignmentFailuresMom	OBJECT-TYPE
	SYNTAX	 CounterBasedGauge64
	MAX-ACCESS read-only
	STATUS current
	DESCRIPTION "Port block assignment failures"

	::={rewritePortBlockAssignmentFailures 2}

rewritePortBlockAssignmentFailuresMax	OBJECT-TYPE
	SYNTAX	 CounterBasedGauge64
	MAX-ACCESS read-only
	STATUS current
	DESCRIPTION "Port block assignment failures"

	::={rewritePortBlockAssignmentFailures 3}

rewritePortBlockAssignmentFailuresLevelTable OBJECT-TYPE
	SYNTAX      SEQUENCE OF RewritePortBlockAssignmentFailuresLevelEntry
	MAX-ACCESS  not-accessible
	STATUS      current
	DESCRIPTION
	"Table for rewritePortBlockAssignmentFailures"
	::={rewritePortBlockAssignmentFailures 4}

rewritePortBlockAssignmentFailuresLevelEntry OBJECT-TYPE
	SYNTAX      RewritePortBlockAssignmentFailuresLevelEntry
	MAX-ACCESS  not-accessible
	STATUS      current
	DESCRIPTION
	"Table entry for rewritePortBlockAssignmentFailures"
	INDEX { rewritePortBlockAssignmentFailuresLevelName }
	::={rewritePortBlockAssignmentFailuresLevelTable 1}

RewritePortBlockAssignmentFailuresLevelEntry ::=
	SEQUENCE {
		rewritePortBlockAssignmentFailuresLevelName	DisplayString,
		rewritePortBlockAssignmentFailuresLevelVal	Counter64,
		rewritePortBlockAssignmentFailuresLevelMom	CounterBasedGauge64,
		rewritePortBlockAssignmentFailuresLevelMax	CounterBasedGauge64
	}

rewritePortBlockAssignmentFailuresLevelName OBJECT-TYPE
	SYNTAX      DisplayString
	MAX-ACCESS  not-accessible
	STATUS      current
	DESCRIPTION
	"Table entry display string for rewritePortBlockAssignmentFailures"
	::={rewritePortBlockAssignmentFailuresLevelEntry 1}

rewritePortBlockAssignmentFailuresLevelVal OBJECT-TYPE
	SYNTAX	 Counter64
	MAX-ACCESS  read-only
	STATUS      current
	DESCRIPTION
	"Table entry attribute for rewritePortBlockAssignmentFailures"
	::={rewritePortBlockAssignmentFailuresLevelEntry 2}

rewritePortBlockAssignmentFailuresLevelMom OBJECT-TYPE
	SYNTAX	 CounterBasedGauge64
	MAX-ACCESS  read-only
	STATUS      current
	DESCRIPTION
	"Table entry attribute for rewritePortBlockAssignmentFailures"
	::={rewritePortBlockAssignmentFailuresLevelEntry 3}

rewritePortBlockAssignmentFailuresLevelMax OBJECT-TYPE
	SYNTAX	 CounterBasedGauge64
	MAX-ACCESS  read-only
	STATUS      current
	DESCRIPTION
	"Table entry attribute for rewritePortBlockAssignmentFailures"
	::={rewritePortBlockAssignmentFailuresLevelEntry 4}


rewritePortBlockAssFailSubLimReached	OBJECT IDENTIFIER ::={rewrite 127}

rewritePortBlockAssFailSubLimReachedVal	OBJECT-TYPE
	SYNTAX	 Counter64
	MAX-ACCESS read-only
	STATUS current
	DESCRIPTION "Port block assignment failures (subscriber limit reached)"

	::={rewritePortBlockAssFailSubLimReached 1}

rewritePortBlockAssFailSubLimReachedMom	OBJECT-TYPE
	SYNTAX	 CounterBasedGauge64
	MAX-ACCESS read-only
	STATUS current
	DESCRIPTION "Port block assignment failures (subscriber limit reached)"

	::={rewritePortBlockAssFailSubLimReached 2}

rewritePortBlockAssFailSubLimReachedMax	OBJECT-TYPE
	SYNTAX	 CounterBasedGauge64
	MAX-ACCESS read-only
	STATUS current
	DESCRIPTION "Port block assignment failures (subscriber limit reached)"

	::={rewritePortBlockAssFailSubLimReached 3}

rewritePortBlockAssFailSubLimReachedLevelTable OBJECT-TYPE
	SYNTAX      SEQUENCE OF RewritePortBlockAssFailSubLimReachedLevelEntry
	MAX-ACCESS  not-accessible
	STATUS      current
	DESCRIPTION
	"Table for rewritePortBlockAssFailSubLimReached"
	::={rewritePortBlockAssFailSubLimReached 4}

rewritePortBlockAssFailSubLimReachedLevelEntry OBJECT-TYPE
	SYNTAX      RewritePortBlockAssFailSubLimReachedLevelEntry
	MAX-ACCESS  not-accessible
	STATUS      current
	DESCRIPTION
	"Table entry for rewritePortBlockAssFailSubLimReached"
	INDEX { rewritePortBlockAssFailSubLimReachedLevelName }
	::={rewritePortBlockAssFailSubLimReachedLevelTable 1}

RewritePortBlockAssFailSubLimReachedLevelEntry ::=
	SEQUENCE {
		rewritePortBlockAssFailSubLimReachedLevelName	DisplayString,
		rewritePortBlockAssFailSubLimReachedLevelVal	Counter64,
		rewritePortBlockAssFailSubLimReachedLevelMom	CounterBasedGauge64,
		rewritePortBlockAssFailSubLimReachedLevelMax	CounterBasedGauge64
	}

rewritePortBlockAssFailSubLimReachedLevelName OBJECT-TYPE
	SYNTAX      DisplayString
	MAX-ACCESS  not-accessible
	STATUS      current
	DESCRIPTION
	"Table entry display string for rewritePortBlockAssFailSubLimReached"
	::={rewritePortBlockAssFailSubLimReachedLevelEntry 1}

rewritePortBlockAssFailSubLimReachedLevelVal OBJECT-TYPE
	SYNTAX	 Counter64
	MAX-ACCESS  read-only
	STATUS      current
	DESCRIPTION
	"Table entry attribute for rewritePortBlockAssFailSubLimReached"
	::={rewritePortBlockAssFailSubLimReachedLevelEntry 2}

rewritePortBlockAssFailSubLimReachedLevelMom OBJECT-TYPE
	SYNTAX	 CounterBasedGauge64
	MAX-ACCESS  read-only
	STATUS      current
	DESCRIPTION
	"Table entry attribute for rewritePortBlockAssFailSubLimReached"
	::={rewritePortBlockAssFailSubLimReachedLevelEntry 3}

rewritePortBlockAssFailSubLimReachedLevelMax OBJECT-TYPE
	SYNTAX	 CounterBasedGauge64
	MAX-ACCESS  read-only
	STATUS      current
	DESCRIPTION
	"Table entry attribute for rewritePortBlockAssFailSubLimReached"
	::={rewritePortBlockAssFailSubLimReachedLevelEntry 4}


rewritePortBlockAssignmentFailuresCacheEmpty	OBJECT IDENTIFIER ::={rewrite 128}

rewritePortBlockAssignmentFailuresCacheEmptyVal	OBJECT-TYPE
	SYNTAX	 Counter64
	MAX-ACCESS read-only
	STATUS current
	DESCRIPTION "Port block assignment failures (cache empty)"

	::={rewritePortBlockAssignmentFailuresCacheEmpty 1}

rewritePortBlockAssignmentFailuresCacheEmptyMom	OBJECT-TYPE
	SYNTAX	 CounterBasedGauge64
	MAX-ACCESS read-only
	STATUS current
	DESCRIPTION "Port block assignment failures (cache empty)"

	::={rewritePortBlockAssignmentFailuresCacheEmpty 2}

rewritePortBlockAssignmentFailuresCacheEmptyMax	OBJECT-TYPE
	SYNTAX	 CounterBasedGauge64
	MAX-ACCESS read-only
	STATUS current
	DESCRIPTION "Port block assignment failures (cache empty)"

	::={rewritePortBlockAssignmentFailuresCacheEmpty 3}

rewritePortBlockAssignmentFailuresCacheEmptyLevelTable OBJECT-TYPE
	SYNTAX      SEQUENCE OF RewritePortBlockAssignmentFailuresCacheEmptyLevelEntry
	MAX-ACCESS  not-accessible
	STATUS      current
	DESCRIPTION
	"Table for rewritePortBlockAssignmentFailuresCacheEmpty"
	::={rewritePortBlockAssignmentFailuresCacheEmpty 4}

rewritePortBlockAssignmentFailuresCacheEmptyLevelEntry OBJECT-TYPE
	SYNTAX      RewritePortBlockAssignmentFailuresCacheEmptyLevelEntry
	MAX-ACCESS  not-accessible
	STATUS      current
	DESCRIPTION
	"Table entry for rewritePortBlockAssignmentFailuresCacheEmpty"
	INDEX { rewritePortBlockAssignmentFailuresCacheEmptyLevelName }
	::={rewritePortBlockAssignmentFailuresCacheEmptyLevelTable 1}

RewritePortBlockAssignmentFailuresCacheEmptyLevelEntry ::=
	SEQUENCE {
		rewritePortBlockAssignmentFailuresCacheEmptyLevelName	DisplayString,
		rewritePortBlockAssignmentFailuresCacheEmptyLevelVal	Counter64,
		rewritePortBlockAssignmentFailuresCacheEmptyLevelMom	CounterBasedGauge64,
		rewritePortBlockAssignmentFailuresCacheEmptyLevelMax	CounterBasedGauge64
	}

rewritePortBlockAssignmentFailuresCacheEmptyLevelName OBJECT-TYPE
	SYNTAX      DisplayString
	MAX-ACCESS  not-accessible
	STATUS      current
	DESCRIPTION
	"Table entry display string for rewritePortBlockAssignmentFailuresCacheEmpty"
	::={rewritePortBlockAssignmentFailuresCacheEmptyLevelEntry 1}

rewritePortBlockAssignmentFailuresCacheEmptyLevelVal OBJECT-TYPE
	SYNTAX	 Counter64
	MAX-ACCESS  read-only
	STATUS      current
	DESCRIPTION
	"Table entry attribute for rewritePortBlockAssignmentFailuresCacheEmpty"
	::={rewritePortBlockAssignmentFailuresCacheEmptyLevelEntry 2}

rewritePortBlockAssignmentFailuresCacheEmptyLevelMom OBJECT-TYPE
	SYNTAX	 CounterBasedGauge64
	MAX-ACCESS  read-only
	STATUS      current
	DESCRIPTION
	"Table entry attribute for rewritePortBlockAssignmentFailuresCacheEmpty"
	::={rewritePortBlockAssignmentFailuresCacheEmptyLevelEntry 3}

rewritePortBlockAssignmentFailuresCacheEmptyLevelMax OBJECT-TYPE
	SYNTAX	 CounterBasedGauge64
	MAX-ACCESS  read-only
	STATUS      current
	DESCRIPTION
	"Table entry attribute for rewritePortBlockAssignmentFailuresCacheEmpty"
	::={rewritePortBlockAssignmentFailuresCacheEmptyLevelEntry 4}


rewritePortBlockLowAssignmentFailures	OBJECT IDENTIFIER ::={rewrite 129}

rewritePortBlockLowAssignmentFailuresVal	OBJECT-TYPE
	SYNTAX	 Counter64
	MAX-ACCESS read-only
	STATUS current
	DESCRIPTION "Port block assignment failures - low (retry with high)"

	::={rewritePortBlockLowAssignmentFailures 1}

rewritePortBlockLowAssignmentFailuresMom	OBJECT-TYPE
	SYNTAX	 CounterBasedGauge64
	MAX-ACCESS read-only
	STATUS current
	DESCRIPTION "Port block assignment failures - low (retry with high)"

	::={rewritePortBlockLowAssignmentFailures 2}

rewritePortBlockLowAssignmentFailuresMax	OBJECT-TYPE
	SYNTAX	 CounterBasedGauge64
	MAX-ACCESS read-only
	STATUS current
	DESCRIPTION "Port block assignment failures - low (retry with high)"

	::={rewritePortBlockLowAssignmentFailures 3}

rewritePortBlockLowAssignmentFailuresLevelTable OBJECT-TYPE
	SYNTAX      SEQUENCE OF RewritePortBlockLowAssignmentFailuresLevelEntry
	MAX-ACCESS  not-accessible
	STATUS      current
	DESCRIPTION
	"Table for rewritePortBlockLowAssignmentFailures"
	::={rewritePortBlockLowAssignmentFailures 4}

rewritePortBlockLowAssignmentFailuresLevelEntry OBJECT-TYPE
	SYNTAX      RewritePortBlockLowAssignmentFailuresLevelEntry
	MAX-ACCESS  not-accessible
	STATUS      current
	DESCRIPTION
	"Table entry for rewritePortBlockLowAssignmentFailures"
	INDEX { rewritePortBlockLowAssignmentFailuresLevelName }
	::={rewritePortBlockLowAssignmentFailuresLevelTable 1}

RewritePortBlockLowAssignmentFailuresLevelEntry ::=
	SEQUENCE {
		rewritePortBlockLowAssignmentFailuresLevelName	DisplayString,
		rewritePortBlockLowAssignmentFailuresLevelVal	Counter64,
		rewritePortBlockLowAssignmentFailuresLevelMom	CounterBasedGauge64,
		rewritePortBlockLowAssignmentFailuresLevelMax	CounterBasedGauge64
	}

rewritePortBlockLowAssignmentFailuresLevelName OBJECT-TYPE
	SYNTAX      DisplayString
	MAX-ACCESS  not-accessible
	STATUS      current
	DESCRIPTION
	"Table entry display string for rewritePortBlockLowAssignmentFailures"
	::={rewritePortBlockLowAssignmentFailuresLevelEntry 1}

rewritePortBlockLowAssignmentFailuresLevelVal OBJECT-TYPE
	SYNTAX	 Counter64
	MAX-ACCESS  read-only
	STATUS      current
	DESCRIPTION
	"Table entry attribute for rewritePortBlockLowAssignmentFailures"
	::={rewritePortBlockLowAssignmentFailuresLevelEntry 2}

rewritePortBlockLowAssignmentFailuresLevelMom OBJECT-TYPE
	SYNTAX	 CounterBasedGauge64
	MAX-ACCESS  read-only
	STATUS      current
	DESCRIPTION
	"Table entry attribute for rewritePortBlockLowAssignmentFailures"
	::={rewritePortBlockLowAssignmentFailuresLevelEntry 3}

rewritePortBlockLowAssignmentFailuresLevelMax OBJECT-TYPE
	SYNTAX	 CounterBasedGauge64
	MAX-ACCESS  read-only
	STATUS      current
	DESCRIPTION
	"Table entry attribute for rewritePortBlockLowAssignmentFailures"
	::={rewritePortBlockLowAssignmentFailuresLevelEntry 4}


rewritePortBlockLowAssFailSusbLimReached	OBJECT IDENTIFIER ::={rewrite 130}

rewritePortBlockLowAssFailSusbLimReachedVal	OBJECT-TYPE
	SYNTAX	 Counter64
	MAX-ACCESS read-only
	STATUS current
	DESCRIPTION "Port block assignment failures - low (subscriber limit reached, retry with high)"

	::={rewritePortBlockLowAssFailSusbLimReached 1}

rewritePortBlockLowAssFailSusbLimReachedMom	OBJECT-TYPE
	SYNTAX	 CounterBasedGauge64
	MAX-ACCESS read-only
	STATUS current
	DESCRIPTION "Port block assignment failures - low (subscriber limit reached, retry with high)"

	::={rewritePortBlockLowAssFailSusbLimReached 2}

rewritePortBlockLowAssFailSusbLimReachedMax	OBJECT-TYPE
	SYNTAX	 CounterBasedGauge64
	MAX-ACCESS read-only
	STATUS current
	DESCRIPTION "Port block assignment failures - low (subscriber limit reached, retry with high)"

	::={rewritePortBlockLowAssFailSusbLimReached 3}

rewritePortBlockLowAssFailSusbLimReachedLevelTable OBJECT-TYPE
	SYNTAX      SEQUENCE OF RewritePortBlockLowAssFailSusbLimReachedLevelEntry
	MAX-ACCESS  not-accessible
	STATUS      current
	DESCRIPTION
	"Table for rewritePortBlockLowAssFailSusbLimReached"
	::={rewritePortBlockLowAssFailSusbLimReached 4}

rewritePortBlockLowAssFailSusbLimReachedLevelEntry OBJECT-TYPE
	SYNTAX      RewritePortBlockLowAssFailSusbLimReachedLevelEntry
	MAX-ACCESS  not-accessible
	STATUS      current
	DESCRIPTION
	"Table entry for rewritePortBlockLowAssFailSusbLimReached"
	INDEX { rewritePortBlockLowAssFailSusbLimReachedLevelName }
	::={rewritePortBlockLowAssFailSusbLimReachedLevelTable 1}

RewritePortBlockLowAssFailSusbLimReachedLevelEntry ::=
	SEQUENCE {
		rewritePortBlockLowAssFailSusbLimReachedLevelName	DisplayString,
		rewritePortBlockLowAssFailSusbLimReachedLevelVal	Counter64,
		rewritePortBlockLowAssFailSusbLimReachedLevelMom	CounterBasedGauge64,
		rewritePortBlockLowAssFailSusbLimReachedLevelMax	CounterBasedGauge64
	}

rewritePortBlockLowAssFailSusbLimReachedLevelName OBJECT-TYPE
	SYNTAX      DisplayString
	MAX-ACCESS  not-accessible
	STATUS      current
	DESCRIPTION
	"Table entry display string for rewritePortBlockLowAssFailSusbLimReached"
	::={rewritePortBlockLowAssFailSusbLimReachedLevelEntry 1}

rewritePortBlockLowAssFailSusbLimReachedLevelVal OBJECT-TYPE
	SYNTAX	 Counter64
	MAX-ACCESS  read-only
	STATUS      current
	DESCRIPTION
	"Table entry attribute for rewritePortBlockLowAssFailSusbLimReached"
	::={rewritePortBlockLowAssFailSusbLimReachedLevelEntry 2}

rewritePortBlockLowAssFailSusbLimReachedLevelMom OBJECT-TYPE
	SYNTAX	 CounterBasedGauge64
	MAX-ACCESS  read-only
	STATUS      current
	DESCRIPTION
	"Table entry attribute for rewritePortBlockLowAssFailSusbLimReached"
	::={rewritePortBlockLowAssFailSusbLimReachedLevelEntry 3}

rewritePortBlockLowAssFailSusbLimReachedLevelMax OBJECT-TYPE
	SYNTAX	 CounterBasedGauge64
	MAX-ACCESS  read-only
	STATUS      current
	DESCRIPTION
	"Table entry attribute for rewritePortBlockLowAssFailSusbLimReached"
	::={rewritePortBlockLowAssFailSusbLimReachedLevelEntry 4}


rewritePortBlockLowAssignmentFailuresCacheEmpty	OBJECT IDENTIFIER ::={rewrite 131}

rewritePortBlockLowAssignmentFailuresCacheEmptyVal	OBJECT-TYPE
	SYNTAX	 Counter64
	MAX-ACCESS read-only
	STATUS current
	DESCRIPTION "Port block assignment failures - low (cache empty, retry with high)"

	::={rewritePortBlockLowAssignmentFailuresCacheEmpty 1}

rewritePortBlockLowAssignmentFailuresCacheEmptyMom	OBJECT-TYPE
	SYNTAX	 CounterBasedGauge64
	MAX-ACCESS read-only
	STATUS current
	DESCRIPTION "Port block assignment failures - low (cache empty, retry with high)"

	::={rewritePortBlockLowAssignmentFailuresCacheEmpty 2}

rewritePortBlockLowAssignmentFailuresCacheEmptyMax	OBJECT-TYPE
	SYNTAX	 CounterBasedGauge64
	MAX-ACCESS read-only
	STATUS current
	DESCRIPTION "Port block assignment failures - low (cache empty, retry with high)"

	::={rewritePortBlockLowAssignmentFailuresCacheEmpty 3}

rewritePortBlockLowAssignmentFailuresCacheEmptyLevelTable OBJECT-TYPE
	SYNTAX      SEQUENCE OF RewritePortBlockLowAssignmentFailuresCacheEmptyLevelEntry
	MAX-ACCESS  not-accessible
	STATUS      current
	DESCRIPTION
	"Table for rewritePortBlockLowAssignmentFailuresCacheEmpty"
	::={rewritePortBlockLowAssignmentFailuresCacheEmpty 4}

rewritePortBlockLowAssignmentFailuresCacheEmptyLevelEntry OBJECT-TYPE
	SYNTAX      RewritePortBlockLowAssignmentFailuresCacheEmptyLevelEntry
	MAX-ACCESS  not-accessible
	STATUS      current
	DESCRIPTION
	"Table entry for rewritePortBlockLowAssignmentFailuresCacheEmpty"
	INDEX { rewritePortBlockLowAssignmentFailuresCacheEmptyLevelName }
	::={rewritePortBlockLowAssignmentFailuresCacheEmptyLevelTable 1}

RewritePortBlockLowAssignmentFailuresCacheEmptyLevelEntry ::=
	SEQUENCE {
		rewritePortBlockLowAssignmentFailuresCacheEmptyLevelName	DisplayString,
		rewritePortBlockLowAssignmentFailuresCacheEmptyLevelVal	Counter64,
		rewritePortBlockLowAssignmentFailuresCacheEmptyLevelMom	CounterBasedGauge64,
		rewritePortBlockLowAssignmentFailuresCacheEmptyLevelMax	CounterBasedGauge64
	}

rewritePortBlockLowAssignmentFailuresCacheEmptyLevelName OBJECT-TYPE
	SYNTAX      DisplayString
	MAX-ACCESS  not-accessible
	STATUS      current
	DESCRIPTION
	"Table entry display string for rewritePortBlockLowAssignmentFailuresCacheEmpty"
	::={rewritePortBlockLowAssignmentFailuresCacheEmptyLevelEntry 1}

rewritePortBlockLowAssignmentFailuresCacheEmptyLevelVal OBJECT-TYPE
	SYNTAX	 Counter64
	MAX-ACCESS  read-only
	STATUS      current
	DESCRIPTION
	"Table entry attribute for rewritePortBlockLowAssignmentFailuresCacheEmpty"
	::={rewritePortBlockLowAssignmentFailuresCacheEmptyLevelEntry 2}

rewritePortBlockLowAssignmentFailuresCacheEmptyLevelMom OBJECT-TYPE
	SYNTAX	 CounterBasedGauge64
	MAX-ACCESS  read-only
	STATUS      current
	DESCRIPTION
	"Table entry attribute for rewritePortBlockLowAssignmentFailuresCacheEmpty"
	::={rewritePortBlockLowAssignmentFailuresCacheEmptyLevelEntry 3}

rewritePortBlockLowAssignmentFailuresCacheEmptyLevelMax OBJECT-TYPE
	SYNTAX	 CounterBasedGauge64
	MAX-ACCESS  read-only
	STATUS      current
	DESCRIPTION
	"Table entry attribute for rewritePortBlockLowAssignmentFailuresCacheEmpty"
	::={rewritePortBlockLowAssignmentFailuresCacheEmptyLevelEntry 4}


rewritePortBlockHighAssignmentFailures	OBJECT IDENTIFIER ::={rewrite 132}

rewritePortBlockHighAssignmentFailuresVal	OBJECT-TYPE
	SYNTAX	 Counter64
	MAX-ACCESS read-only
	STATUS current
	DESCRIPTION "Port block assignment failures - high"

	::={rewritePortBlockHighAssignmentFailures 1}

rewritePortBlockHighAssignmentFailuresMom	OBJECT-TYPE
	SYNTAX	 CounterBasedGauge64
	MAX-ACCESS read-only
	STATUS current
	DESCRIPTION "Port block assignment failures - high"

	::={rewritePortBlockHighAssignmentFailures 2}

rewritePortBlockHighAssignmentFailuresMax	OBJECT-TYPE
	SYNTAX	 CounterBasedGauge64
	MAX-ACCESS read-only
	STATUS current
	DESCRIPTION "Port block assignment failures - high"

	::={rewritePortBlockHighAssignmentFailures 3}

rewritePortBlockHighAssignmentFailuresLevelTable OBJECT-TYPE
	SYNTAX      SEQUENCE OF RewritePortBlockHighAssignmentFailuresLevelEntry
	MAX-ACCESS  not-accessible
	STATUS      current
	DESCRIPTION
	"Table for rewritePortBlockHighAssignmentFailures"
	::={rewritePortBlockHighAssignmentFailures 4}

rewritePortBlockHighAssignmentFailuresLevelEntry OBJECT-TYPE
	SYNTAX      RewritePortBlockHighAssignmentFailuresLevelEntry
	MAX-ACCESS  not-accessible
	STATUS      current
	DESCRIPTION
	"Table entry for rewritePortBlockHighAssignmentFailures"
	INDEX { rewritePortBlockHighAssignmentFailuresLevelName }
	::={rewritePortBlockHighAssignmentFailuresLevelTable 1}

RewritePortBlockHighAssignmentFailuresLevelEntry ::=
	SEQUENCE {
		rewritePortBlockHighAssignmentFailuresLevelName	DisplayString,
		rewritePortBlockHighAssignmentFailuresLevelVal	Counter64,
		rewritePortBlockHighAssignmentFailuresLevelMom	CounterBasedGauge64,
		rewritePortBlockHighAssignmentFailuresLevelMax	CounterBasedGauge64
	}

rewritePortBlockHighAssignmentFailuresLevelName OBJECT-TYPE
	SYNTAX      DisplayString
	MAX-ACCESS  not-accessible
	STATUS      current
	DESCRIPTION
	"Table entry display string for rewritePortBlockHighAssignmentFailures"
	::={rewritePortBlockHighAssignmentFailuresLevelEntry 1}

rewritePortBlockHighAssignmentFailuresLevelVal OBJECT-TYPE
	SYNTAX	 Counter64
	MAX-ACCESS  read-only
	STATUS      current
	DESCRIPTION
	"Table entry attribute for rewritePortBlockHighAssignmentFailures"
	::={rewritePortBlockHighAssignmentFailuresLevelEntry 2}

rewritePortBlockHighAssignmentFailuresLevelMom OBJECT-TYPE
	SYNTAX	 CounterBasedGauge64
	MAX-ACCESS  read-only
	STATUS      current
	DESCRIPTION
	"Table entry attribute for rewritePortBlockHighAssignmentFailures"
	::={rewritePortBlockHighAssignmentFailuresLevelEntry 3}

rewritePortBlockHighAssignmentFailuresLevelMax OBJECT-TYPE
	SYNTAX	 CounterBasedGauge64
	MAX-ACCESS  read-only
	STATUS      current
	DESCRIPTION
	"Table entry attribute for rewritePortBlockHighAssignmentFailures"
	::={rewritePortBlockHighAssignmentFailuresLevelEntry 4}


rewritePortBlockHiAssFailSubLimReached	OBJECT IDENTIFIER ::={rewrite 133}

rewritePortBlockHiAssFailSubLimReachedVal	OBJECT-TYPE
	SYNTAX	 Counter64
	MAX-ACCESS read-only
	STATUS current
	DESCRIPTION "Port block assignment failures - high (subscriber limit reached)"

	::={rewritePortBlockHiAssFailSubLimReached 1}

rewritePortBlockHiAssFailSubLimReachedMom	OBJECT-TYPE
	SYNTAX	 CounterBasedGauge64
	MAX-ACCESS read-only
	STATUS current
	DESCRIPTION "Port block assignment failures - high (subscriber limit reached)"

	::={rewritePortBlockHiAssFailSubLimReached 2}

rewritePortBlockHiAssFailSubLimReachedMax	OBJECT-TYPE
	SYNTAX	 CounterBasedGauge64
	MAX-ACCESS read-only
	STATUS current
	DESCRIPTION "Port block assignment failures - high (subscriber limit reached)"

	::={rewritePortBlockHiAssFailSubLimReached 3}

rewritePortBlockHiAssFailSubLimReachedLevelTable OBJECT-TYPE
	SYNTAX      SEQUENCE OF RewritePortBlockHiAssFailSubLimReachedLevelEntry
	MAX-ACCESS  not-accessible
	STATUS      current
	DESCRIPTION
	"Table for rewritePortBlockHiAssFailSubLimReached"
	::={rewritePortBlockHiAssFailSubLimReached 4}

rewritePortBlockHiAssFailSubLimReachedLevelEntry OBJECT-TYPE
	SYNTAX      RewritePortBlockHiAssFailSubLimReachedLevelEntry
	MAX-ACCESS  not-accessible
	STATUS      current
	DESCRIPTION
	"Table entry for rewritePortBlockHiAssFailSubLimReached"
	INDEX { rewritePortBlockHiAssFailSubLimReachedLevelName }
	::={rewritePortBlockHiAssFailSubLimReachedLevelTable 1}

RewritePortBlockHiAssFailSubLimReachedLevelEntry ::=
	SEQUENCE {
		rewritePortBlockHiAssFailSubLimReachedLevelName	DisplayString,
		rewritePortBlockHiAssFailSubLimReachedLevelVal	Counter64,
		rewritePortBlockHiAssFailSubLimReachedLevelMom	CounterBasedGauge64,
		rewritePortBlockHiAssFailSubLimReachedLevelMax	CounterBasedGauge64
	}

rewritePortBlockHiAssFailSubLimReachedLevelName OBJECT-TYPE
	SYNTAX      DisplayString
	MAX-ACCESS  not-accessible
	STATUS      current
	DESCRIPTION
	"Table entry display string for rewritePortBlockHiAssFailSubLimReached"
	::={rewritePortBlockHiAssFailSubLimReachedLevelEntry 1}

rewritePortBlockHiAssFailSubLimReachedLevelVal OBJECT-TYPE
	SYNTAX	 Counter64
	MAX-ACCESS  read-only
	STATUS      current
	DESCRIPTION
	"Table entry attribute for rewritePortBlockHiAssFailSubLimReached"
	::={rewritePortBlockHiAssFailSubLimReachedLevelEntry 2}

rewritePortBlockHiAssFailSubLimReachedLevelMom OBJECT-TYPE
	SYNTAX	 CounterBasedGauge64
	MAX-ACCESS  read-only
	STATUS      current
	DESCRIPTION
	"Table entry attribute for rewritePortBlockHiAssFailSubLimReached"
	::={rewritePortBlockHiAssFailSubLimReachedLevelEntry 3}

rewritePortBlockHiAssFailSubLimReachedLevelMax OBJECT-TYPE
	SYNTAX	 CounterBasedGauge64
	MAX-ACCESS  read-only
	STATUS      current
	DESCRIPTION
	"Table entry attribute for rewritePortBlockHiAssFailSubLimReached"
	::={rewritePortBlockHiAssFailSubLimReachedLevelEntry 4}


rewritePortBlockHighAssignmentFailuresCacheEmpty	OBJECT IDENTIFIER ::={rewrite 134}

rewritePortBlockHighAssignmentFailuresCacheEmptyVal	OBJECT-TYPE
	SYNTAX	 Counter64
	MAX-ACCESS read-only
	STATUS current
	DESCRIPTION "Port block assignment failures - high (cache empty)"

	::={rewritePortBlockHighAssignmentFailuresCacheEmpty 1}

rewritePortBlockHighAssignmentFailuresCacheEmptyMom	OBJECT-TYPE
	SYNTAX	 CounterBasedGauge64
	MAX-ACCESS read-only
	STATUS current
	DESCRIPTION "Port block assignment failures - high (cache empty)"

	::={rewritePortBlockHighAssignmentFailuresCacheEmpty 2}

rewritePortBlockHighAssignmentFailuresCacheEmptyMax	OBJECT-TYPE
	SYNTAX	 CounterBasedGauge64
	MAX-ACCESS read-only
	STATUS current
	DESCRIPTION "Port block assignment failures - high (cache empty)"

	::={rewritePortBlockHighAssignmentFailuresCacheEmpty 3}

rewritePortBlockHighAssignmentFailuresCacheEmptyLevelTable OBJECT-TYPE
	SYNTAX      SEQUENCE OF RewritePortBlockHighAssignmentFailuresCacheEmptyLevelEntry
	MAX-ACCESS  not-accessible
	STATUS      current
	DESCRIPTION
	"Table for rewritePortBlockHighAssignmentFailuresCacheEmpty"
	::={rewritePortBlockHighAssignmentFailuresCacheEmpty 4}

rewritePortBlockHighAssignmentFailuresCacheEmptyLevelEntry OBJECT-TYPE
	SYNTAX      RewritePortBlockHighAssignmentFailuresCacheEmptyLevelEntry
	MAX-ACCESS  not-accessible
	STATUS      current
	DESCRIPTION
	"Table entry for rewritePortBlockHighAssignmentFailuresCacheEmpty"
	INDEX { rewritePortBlockHighAssignmentFailuresCacheEmptyLevelName }
	::={rewritePortBlockHighAssignmentFailuresCacheEmptyLevelTable 1}

RewritePortBlockHighAssignmentFailuresCacheEmptyLevelEntry ::=
	SEQUENCE {
		rewritePortBlockHighAssignmentFailuresCacheEmptyLevelName	DisplayString,
		rewritePortBlockHighAssignmentFailuresCacheEmptyLevelVal	Counter64,
		rewritePortBlockHighAssignmentFailuresCacheEmptyLevelMom	CounterBasedGauge64,
		rewritePortBlockHighAssignmentFailuresCacheEmptyLevelMax	CounterBasedGauge64
	}

rewritePortBlockHighAssignmentFailuresCacheEmptyLevelName OBJECT-TYPE
	SYNTAX      DisplayString
	MAX-ACCESS  not-accessible
	STATUS      current
	DESCRIPTION
	"Table entry display string for rewritePortBlockHighAssignmentFailuresCacheEmpty"
	::={rewritePortBlockHighAssignmentFailuresCacheEmptyLevelEntry 1}

rewritePortBlockHighAssignmentFailuresCacheEmptyLevelVal OBJECT-TYPE
	SYNTAX	 Counter64
	MAX-ACCESS  read-only
	STATUS      current
	DESCRIPTION
	"Table entry attribute for rewritePortBlockHighAssignmentFailuresCacheEmpty"
	::={rewritePortBlockHighAssignmentFailuresCacheEmptyLevelEntry 2}

rewritePortBlockHighAssignmentFailuresCacheEmptyLevelMom OBJECT-TYPE
	SYNTAX	 CounterBasedGauge64
	MAX-ACCESS  read-only
	STATUS      current
	DESCRIPTION
	"Table entry attribute for rewritePortBlockHighAssignmentFailuresCacheEmpty"
	::={rewritePortBlockHighAssignmentFailuresCacheEmptyLevelEntry 3}

rewritePortBlockHighAssignmentFailuresCacheEmptyLevelMax OBJECT-TYPE
	SYNTAX	 CounterBasedGauge64
	MAX-ACCESS  read-only
	STATUS      current
	DESCRIPTION
	"Table entry attribute for rewritePortBlockHighAssignmentFailuresCacheEmpty"
	::={rewritePortBlockHighAssignmentFailuresCacheEmptyLevelEntry 4}


rewritePortBlockCountLow	OBJECT IDENTIFIER ::={rewrite 135}

rewritePortBlockCountLowVal	OBJECT-TYPE
	SYNTAX	 Counter64
	MAX-ACCESS read-only
	STATUS current
	DESCRIPTION "Port block count - low"

	::={rewritePortBlockCountLow 1}

rewritePortBlockCountLowMom	OBJECT-TYPE
	SYNTAX	 CounterBasedGauge64
	MAX-ACCESS read-only
	STATUS current
	DESCRIPTION "Port block count - low"

	::={rewritePortBlockCountLow 2}

rewritePortBlockCountLowMax	OBJECT-TYPE
	SYNTAX	 CounterBasedGauge64
	MAX-ACCESS read-only
	STATUS current
	DESCRIPTION "Port block count - low"

	::={rewritePortBlockCountLow 3}

rewritePortBlockCountLowLevelTable OBJECT-TYPE
	SYNTAX      SEQUENCE OF RewritePortBlockCountLowLevelEntry
	MAX-ACCESS  not-accessible
	STATUS      current
	DESCRIPTION
	"Table for rewritePortBlockCountLow"
	::={rewritePortBlockCountLow 4}

rewritePortBlockCountLowLevelEntry OBJECT-TYPE
	SYNTAX      RewritePortBlockCountLowLevelEntry
	MAX-ACCESS  not-accessible
	STATUS      current
	DESCRIPTION
	"Table entry for rewritePortBlockCountLow"
	INDEX { rewritePortBlockCountLowLevelName }
	::={rewritePortBlockCountLowLevelTable 1}

RewritePortBlockCountLowLevelEntry ::=
	SEQUENCE {
		rewritePortBlockCountLowLevelName	DisplayString,
		rewritePortBlockCountLowLevelVal	Counter64,
		rewritePortBlockCountLowLevelMom	CounterBasedGauge64,
		rewritePortBlockCountLowLevelMax	CounterBasedGauge64
	}

rewritePortBlockCountLowLevelName OBJECT-TYPE
	SYNTAX      DisplayString
	MAX-ACCESS  not-accessible
	STATUS      current
	DESCRIPTION
	"Table entry display string for rewritePortBlockCountLow"
	::={rewritePortBlockCountLowLevelEntry 1}

rewritePortBlockCountLowLevelVal OBJECT-TYPE
	SYNTAX	 Counter64
	MAX-ACCESS  read-only
	STATUS      current
	DESCRIPTION
	"Table entry attribute for rewritePortBlockCountLow"
	::={rewritePortBlockCountLowLevelEntry 2}

rewritePortBlockCountLowLevelMom OBJECT-TYPE
	SYNTAX	 CounterBasedGauge64
	MAX-ACCESS  read-only
	STATUS      current
	DESCRIPTION
	"Table entry attribute for rewritePortBlockCountLow"
	::={rewritePortBlockCountLowLevelEntry 3}

rewritePortBlockCountLowLevelMax OBJECT-TYPE
	SYNTAX	 CounterBasedGauge64
	MAX-ACCESS  read-only
	STATUS      current
	DESCRIPTION
	"Table entry attribute for rewritePortBlockCountLow"
	::={rewritePortBlockCountLowLevelEntry 4}


rewritePortBlockCountHigh	OBJECT IDENTIFIER ::={rewrite 136}

rewritePortBlockCountHighVal	OBJECT-TYPE
	SYNTAX	 Counter64
	MAX-ACCESS read-only
	STATUS current
	DESCRIPTION "Port block count - high"

	::={rewritePortBlockCountHigh 1}

rewritePortBlockCountHighMom	OBJECT-TYPE
	SYNTAX	 CounterBasedGauge64
	MAX-ACCESS read-only
	STATUS current
	DESCRIPTION "Port block count - high"

	::={rewritePortBlockCountHigh 2}

rewritePortBlockCountHighMax	OBJECT-TYPE
	SYNTAX	 CounterBasedGauge64
	MAX-ACCESS read-only
	STATUS current
	DESCRIPTION "Port block count - high"

	::={rewritePortBlockCountHigh 3}

rewritePortBlockCountHighLevelTable OBJECT-TYPE
	SYNTAX      SEQUENCE OF RewritePortBlockCountHighLevelEntry
	MAX-ACCESS  not-accessible
	STATUS      current
	DESCRIPTION
	"Table for rewritePortBlockCountHigh"
	::={rewritePortBlockCountHigh 4}

rewritePortBlockCountHighLevelEntry OBJECT-TYPE
	SYNTAX      RewritePortBlockCountHighLevelEntry
	MAX-ACCESS  not-accessible
	STATUS      current
	DESCRIPTION
	"Table entry for rewritePortBlockCountHigh"
	INDEX { rewritePortBlockCountHighLevelName }
	::={rewritePortBlockCountHighLevelTable 1}

RewritePortBlockCountHighLevelEntry ::=
	SEQUENCE {
		rewritePortBlockCountHighLevelName	DisplayString,
		rewritePortBlockCountHighLevelVal	Counter64,
		rewritePortBlockCountHighLevelMom	CounterBasedGauge64,
		rewritePortBlockCountHighLevelMax	CounterBasedGauge64
	}

rewritePortBlockCountHighLevelName OBJECT-TYPE
	SYNTAX      DisplayString
	MAX-ACCESS  not-accessible
	STATUS      current
	DESCRIPTION
	"Table entry display string for rewritePortBlockCountHigh"
	::={rewritePortBlockCountHighLevelEntry 1}

rewritePortBlockCountHighLevelVal OBJECT-TYPE
	SYNTAX	 Counter64
	MAX-ACCESS  read-only
	STATUS      current
	DESCRIPTION
	"Table entry attribute for rewritePortBlockCountHigh"
	::={rewritePortBlockCountHighLevelEntry 2}

rewritePortBlockCountHighLevelMom OBJECT-TYPE
	SYNTAX	 CounterBasedGauge64
	MAX-ACCESS  read-only
	STATUS      current
	DESCRIPTION
	"Table entry attribute for rewritePortBlockCountHigh"
	::={rewritePortBlockCountHighLevelEntry 3}

rewritePortBlockCountHighLevelMax OBJECT-TYPE
	SYNTAX	 CounterBasedGauge64
	MAX-ACCESS  read-only
	STATUS      current
	DESCRIPTION
	"Table entry attribute for rewritePortBlockCountHigh"
	::={rewritePortBlockCountHighLevelEntry 4}


rewritePortBlockCountFreeLow	OBJECT IDENTIFIER ::={rewrite 137}

rewritePortBlockCountFreeLowVal	OBJECT-TYPE
	SYNTAX	 Counter64
	MAX-ACCESS read-only
	STATUS current
	DESCRIPTION "Number of free port blocks - low"

	::={rewritePortBlockCountFreeLow 1}

rewritePortBlockCountFreeLowMom	OBJECT-TYPE
	SYNTAX	 CounterBasedGauge64
	MAX-ACCESS read-only
	STATUS current
	DESCRIPTION "Number of free port blocks - low"

	::={rewritePortBlockCountFreeLow 2}

rewritePortBlockCountFreeLowMax	OBJECT-TYPE
	SYNTAX	 CounterBasedGauge64
	MAX-ACCESS read-only
	STATUS current
	DESCRIPTION "Number of free port blocks - low"

	::={rewritePortBlockCountFreeLow 3}

rewritePortBlockCountFreeLowLevelTable OBJECT-TYPE
	SYNTAX      SEQUENCE OF RewritePortBlockCountFreeLowLevelEntry
	MAX-ACCESS  not-accessible
	STATUS      current
	DESCRIPTION
	"Table for rewritePortBlockCountFreeLow"
	::={rewritePortBlockCountFreeLow 4}

rewritePortBlockCountFreeLowLevelEntry OBJECT-TYPE
	SYNTAX      RewritePortBlockCountFreeLowLevelEntry
	MAX-ACCESS  not-accessible
	STATUS      current
	DESCRIPTION
	"Table entry for rewritePortBlockCountFreeLow"
	INDEX { rewritePortBlockCountFreeLowLevelName }
	::={rewritePortBlockCountFreeLowLevelTable 1}

RewritePortBlockCountFreeLowLevelEntry ::=
	SEQUENCE {
		rewritePortBlockCountFreeLowLevelName	DisplayString,
		rewritePortBlockCountFreeLowLevelVal	Counter64,
		rewritePortBlockCountFreeLowLevelMom	CounterBasedGauge64,
		rewritePortBlockCountFreeLowLevelMax	CounterBasedGauge64
	}

rewritePortBlockCountFreeLowLevelName OBJECT-TYPE
	SYNTAX      DisplayString
	MAX-ACCESS  not-accessible
	STATUS      current
	DESCRIPTION
	"Table entry display string for rewritePortBlockCountFreeLow"
	::={rewritePortBlockCountFreeLowLevelEntry 1}

rewritePortBlockCountFreeLowLevelVal OBJECT-TYPE
	SYNTAX	 Counter64
	MAX-ACCESS  read-only
	STATUS      current
	DESCRIPTION
	"Table entry attribute for rewritePortBlockCountFreeLow"
	::={rewritePortBlockCountFreeLowLevelEntry 2}

rewritePortBlockCountFreeLowLevelMom OBJECT-TYPE
	SYNTAX	 CounterBasedGauge64
	MAX-ACCESS  read-only
	STATUS      current
	DESCRIPTION
	"Table entry attribute for rewritePortBlockCountFreeLow"
	::={rewritePortBlockCountFreeLowLevelEntry 3}

rewritePortBlockCountFreeLowLevelMax OBJECT-TYPE
	SYNTAX	 CounterBasedGauge64
	MAX-ACCESS  read-only
	STATUS      current
	DESCRIPTION
	"Table entry attribute for rewritePortBlockCountFreeLow"
	::={rewritePortBlockCountFreeLowLevelEntry 4}


rewritePortBlockCountFreeHigh	OBJECT IDENTIFIER ::={rewrite 138}

rewritePortBlockCountFreeHighVal	OBJECT-TYPE
	SYNTAX	 Counter64
	MAX-ACCESS read-only
	STATUS current
	DESCRIPTION "Number of free port blocks - high"

	::={rewritePortBlockCountFreeHigh 1}

rewritePortBlockCountFreeHighMom	OBJECT-TYPE
	SYNTAX	 CounterBasedGauge64
	MAX-ACCESS read-only
	STATUS current
	DESCRIPTION "Number of free port blocks - high"

	::={rewritePortBlockCountFreeHigh 2}

rewritePortBlockCountFreeHighMax	OBJECT-TYPE
	SYNTAX	 CounterBasedGauge64
	MAX-ACCESS read-only
	STATUS current
	DESCRIPTION "Number of free port blocks - high"

	::={rewritePortBlockCountFreeHigh 3}

rewritePortBlockCountFreeHighLevelTable OBJECT-TYPE
	SYNTAX      SEQUENCE OF RewritePortBlockCountFreeHighLevelEntry
	MAX-ACCESS  not-accessible
	STATUS      current
	DESCRIPTION
	"Table for rewritePortBlockCountFreeHigh"
	::={rewritePortBlockCountFreeHigh 4}

rewritePortBlockCountFreeHighLevelEntry OBJECT-TYPE
	SYNTAX      RewritePortBlockCountFreeHighLevelEntry
	MAX-ACCESS  not-accessible
	STATUS      current
	DESCRIPTION
	"Table entry for rewritePortBlockCountFreeHigh"
	INDEX { rewritePortBlockCountFreeHighLevelName }
	::={rewritePortBlockCountFreeHighLevelTable 1}

RewritePortBlockCountFreeHighLevelEntry ::=
	SEQUENCE {
		rewritePortBlockCountFreeHighLevelName	DisplayString,
		rewritePortBlockCountFreeHighLevelVal	Counter64,
		rewritePortBlockCountFreeHighLevelMom	CounterBasedGauge64,
		rewritePortBlockCountFreeHighLevelMax	CounterBasedGauge64
	}

rewritePortBlockCountFreeHighLevelName OBJECT-TYPE
	SYNTAX      DisplayString
	MAX-ACCESS  not-accessible
	STATUS      current
	DESCRIPTION
	"Table entry display string for rewritePortBlockCountFreeHigh"
	::={rewritePortBlockCountFreeHighLevelEntry 1}

rewritePortBlockCountFreeHighLevelVal OBJECT-TYPE
	SYNTAX	 Counter64
	MAX-ACCESS  read-only
	STATUS      current
	DESCRIPTION
	"Table entry attribute for rewritePortBlockCountFreeHigh"
	::={rewritePortBlockCountFreeHighLevelEntry 2}

rewritePortBlockCountFreeHighLevelMom OBJECT-TYPE
	SYNTAX	 CounterBasedGauge64
	MAX-ACCESS  read-only
	STATUS      current
	DESCRIPTION
	"Table entry attribute for rewritePortBlockCountFreeHigh"
	::={rewritePortBlockCountFreeHighLevelEntry 3}

rewritePortBlockCountFreeHighLevelMax OBJECT-TYPE
	SYNTAX	 CounterBasedGauge64
	MAX-ACCESS  read-only
	STATUS      current
	DESCRIPTION
	"Table entry attribute for rewritePortBlockCountFreeHigh"
	::={rewritePortBlockCountFreeHighLevelEntry 4}


rewritePortBlockCountAssignedLow	OBJECT IDENTIFIER ::={rewrite 139}

rewritePortBlockCountAssignedLowVal	OBJECT-TYPE
	SYNTAX	 Counter64
	MAX-ACCESS read-only
	STATUS current
	DESCRIPTION "Number of assigned port blocks - low"

	::={rewritePortBlockCountAssignedLow 1}

rewritePortBlockCountAssignedLowMom	OBJECT-TYPE
	SYNTAX	 CounterBasedGauge64
	MAX-ACCESS read-only
	STATUS current
	DESCRIPTION "Number of assigned port blocks - low"

	::={rewritePortBlockCountAssignedLow 2}

rewritePortBlockCountAssignedLowMax	OBJECT-TYPE
	SYNTAX	 CounterBasedGauge64
	MAX-ACCESS read-only
	STATUS current
	DESCRIPTION "Number of assigned port blocks - low"

	::={rewritePortBlockCountAssignedLow 3}

rewritePortBlockCountAssignedLowLevelTable OBJECT-TYPE
	SYNTAX      SEQUENCE OF RewritePortBlockCountAssignedLowLevelEntry
	MAX-ACCESS  not-accessible
	STATUS      current
	DESCRIPTION
	"Table for rewritePortBlockCountAssignedLow"
	::={rewritePortBlockCountAssignedLow 4}

rewritePortBlockCountAssignedLowLevelEntry OBJECT-TYPE
	SYNTAX      RewritePortBlockCountAssignedLowLevelEntry
	MAX-ACCESS  not-accessible
	STATUS      current
	DESCRIPTION
	"Table entry for rewritePortBlockCountAssignedLow"
	INDEX { rewritePortBlockCountAssignedLowLevelName }
	::={rewritePortBlockCountAssignedLowLevelTable 1}

RewritePortBlockCountAssignedLowLevelEntry ::=
	SEQUENCE {
		rewritePortBlockCountAssignedLowLevelName	DisplayString,
		rewritePortBlockCountAssignedLowLevelVal	Counter64,
		rewritePortBlockCountAssignedLowLevelMom	CounterBasedGauge64,
		rewritePortBlockCountAssignedLowLevelMax	CounterBasedGauge64
	}

rewritePortBlockCountAssignedLowLevelName OBJECT-TYPE
	SYNTAX      DisplayString
	MAX-ACCESS  not-accessible
	STATUS      current
	DESCRIPTION
	"Table entry display string for rewritePortBlockCountAssignedLow"
	::={rewritePortBlockCountAssignedLowLevelEntry 1}

rewritePortBlockCountAssignedLowLevelVal OBJECT-TYPE
	SYNTAX	 Counter64
	MAX-ACCESS  read-only
	STATUS      current
	DESCRIPTION
	"Table entry attribute for rewritePortBlockCountAssignedLow"
	::={rewritePortBlockCountAssignedLowLevelEntry 2}

rewritePortBlockCountAssignedLowLevelMom OBJECT-TYPE
	SYNTAX	 CounterBasedGauge64
	MAX-ACCESS  read-only
	STATUS      current
	DESCRIPTION
	"Table entry attribute for rewritePortBlockCountAssignedLow"
	::={rewritePortBlockCountAssignedLowLevelEntry 3}

rewritePortBlockCountAssignedLowLevelMax OBJECT-TYPE
	SYNTAX	 CounterBasedGauge64
	MAX-ACCESS  read-only
	STATUS      current
	DESCRIPTION
	"Table entry attribute for rewritePortBlockCountAssignedLow"
	::={rewritePortBlockCountAssignedLowLevelEntry 4}


rewritePortBlockCountAssignedHigh	OBJECT IDENTIFIER ::={rewrite 140}

rewritePortBlockCountAssignedHighVal	OBJECT-TYPE
	SYNTAX	 Counter64
	MAX-ACCESS read-only
	STATUS current
	DESCRIPTION "Number of assigned port blocks - high"

	::={rewritePortBlockCountAssignedHigh 1}

rewritePortBlockCountAssignedHighMom	OBJECT-TYPE
	SYNTAX	 CounterBasedGauge64
	MAX-ACCESS read-only
	STATUS current
	DESCRIPTION "Number of assigned port blocks - high"

	::={rewritePortBlockCountAssignedHigh 2}

rewritePortBlockCountAssignedHighMax	OBJECT-TYPE
	SYNTAX	 CounterBasedGauge64
	MAX-ACCESS read-only
	STATUS current
	DESCRIPTION "Number of assigned port blocks - high"

	::={rewritePortBlockCountAssignedHigh 3}

rewritePortBlockCountAssignedHighLevelTable OBJECT-TYPE
	SYNTAX      SEQUENCE OF RewritePortBlockCountAssignedHighLevelEntry
	MAX-ACCESS  not-accessible
	STATUS      current
	DESCRIPTION
	"Table for rewritePortBlockCountAssignedHigh"
	::={rewritePortBlockCountAssignedHigh 4}

rewritePortBlockCountAssignedHighLevelEntry OBJECT-TYPE
	SYNTAX      RewritePortBlockCountAssignedHighLevelEntry
	MAX-ACCESS  not-accessible
	STATUS      current
	DESCRIPTION
	"Table entry for rewritePortBlockCountAssignedHigh"
	INDEX { rewritePortBlockCountAssignedHighLevelName }
	::={rewritePortBlockCountAssignedHighLevelTable 1}

RewritePortBlockCountAssignedHighLevelEntry ::=
	SEQUENCE {
		rewritePortBlockCountAssignedHighLevelName	DisplayString,
		rewritePortBlockCountAssignedHighLevelVal	Counter64,
		rewritePortBlockCountAssignedHighLevelMom	CounterBasedGauge64,
		rewritePortBlockCountAssignedHighLevelMax	CounterBasedGauge64
	}

rewritePortBlockCountAssignedHighLevelName OBJECT-TYPE
	SYNTAX      DisplayString
	MAX-ACCESS  not-accessible
	STATUS      current
	DESCRIPTION
	"Table entry display string for rewritePortBlockCountAssignedHigh"
	::={rewritePortBlockCountAssignedHighLevelEntry 1}

rewritePortBlockCountAssignedHighLevelVal OBJECT-TYPE
	SYNTAX	 Counter64
	MAX-ACCESS  read-only
	STATUS      current
	DESCRIPTION
	"Table entry attribute for rewritePortBlockCountAssignedHigh"
	::={rewritePortBlockCountAssignedHighLevelEntry 2}

rewritePortBlockCountAssignedHighLevelMom OBJECT-TYPE
	SYNTAX	 CounterBasedGauge64
	MAX-ACCESS  read-only
	STATUS      current
	DESCRIPTION
	"Table entry attribute for rewritePortBlockCountAssignedHigh"
	::={rewritePortBlockCountAssignedHighLevelEntry 3}

rewritePortBlockCountAssignedHighLevelMax OBJECT-TYPE
	SYNTAX	 CounterBasedGauge64
	MAX-ACCESS  read-only
	STATUS      current
	DESCRIPTION
	"Table entry attribute for rewritePortBlockCountAssignedHigh"
	::={rewritePortBlockCountAssignedHighLevelEntry 4}


rewritePoolNum	OBJECT IDENTIFIER ::={rewrite 151}

rewritePoolNumVal	OBJECT-TYPE
	SYNTAX	 CounterBasedGauge64
	MAX-ACCESS read-only
	STATUS current
	DESCRIPTION "Pools"

	::={rewritePoolNum 1}

rewritePoolNumMax	OBJECT-TYPE
	SYNTAX	 CounterBasedGauge64
	MAX-ACCESS read-only
	STATUS current
	DESCRIPTION "Pools"

	::={rewritePoolNum 3}

rewritePoolNumLevelTable OBJECT-TYPE
	SYNTAX      SEQUENCE OF RewritePoolNumLevelEntry
	MAX-ACCESS  not-accessible
	STATUS      current
	DESCRIPTION
	"Table for rewritePoolNum"
	::={rewritePoolNum 4}

rewritePoolNumLevelEntry OBJECT-TYPE
	SYNTAX      RewritePoolNumLevelEntry
	MAX-ACCESS  not-accessible
	STATUS      current
	DESCRIPTION
	"Table entry for rewritePoolNum"
	INDEX { rewritePoolNumLevelName }
	::={rewritePoolNumLevelTable 1}

RewritePoolNumLevelEntry ::=
	SEQUENCE {
		rewritePoolNumLevelName	DisplayString,
		rewritePoolNumLevelVal	CounterBasedGauge64,
		rewritePoolNumLevelMax	CounterBasedGauge64
	}

rewritePoolNumLevelName OBJECT-TYPE
	SYNTAX      DisplayString
	MAX-ACCESS  not-accessible
	STATUS      current
	DESCRIPTION
	"Table entry display string for rewritePoolNum"
	::={rewritePoolNumLevelEntry 1}

rewritePoolNumLevelVal OBJECT-TYPE
	SYNTAX	 CounterBasedGauge64
	MAX-ACCESS  read-only
	STATUS      current
	DESCRIPTION
	"Table entry attribute for rewritePoolNum"
	::={rewritePoolNumLevelEntry 2}

rewritePoolNumLevelMax OBJECT-TYPE
	SYNTAX	 CounterBasedGauge64
	MAX-ACCESS  read-only
	STATUS      current
	DESCRIPTION
	"Table entry attribute for rewritePoolNum"
	::={rewritePoolNumLevelEntry 4}


rewritePoolNumAddresses	OBJECT IDENTIFIER ::={rewrite 152}

rewritePoolNumAddressesVal	OBJECT-TYPE
	SYNTAX	 CounterBasedGauge64
	MAX-ACCESS read-only
	STATUS current
	DESCRIPTION "Pool - Number of IP-addresses"

	::={rewritePoolNumAddresses 1}

rewritePoolNumAddressesMax	OBJECT-TYPE
	SYNTAX	 CounterBasedGauge64
	MAX-ACCESS read-only
	STATUS current
	DESCRIPTION "Pool - Number of IP-addresses"

	::={rewritePoolNumAddresses 3}

rewritePoolNumAddressesLevelTable OBJECT-TYPE
	SYNTAX      SEQUENCE OF RewritePoolNumAddressesLevelEntry
	MAX-ACCESS  not-accessible
	STATUS      current
	DESCRIPTION
	"Table for rewritePoolNumAddresses"
	::={rewritePoolNumAddresses 4}

rewritePoolNumAddressesLevelEntry OBJECT-TYPE
	SYNTAX      RewritePoolNumAddressesLevelEntry
	MAX-ACCESS  not-accessible
	STATUS      current
	DESCRIPTION
	"Table entry for rewritePoolNumAddresses"
	INDEX { rewritePoolNumAddressesLevelName }
	::={rewritePoolNumAddressesLevelTable 1}

RewritePoolNumAddressesLevelEntry ::=
	SEQUENCE {
		rewritePoolNumAddressesLevelName	DisplayString,
		rewritePoolNumAddressesLevelVal	CounterBasedGauge64,
		rewritePoolNumAddressesLevelMax	CounterBasedGauge64
	}

rewritePoolNumAddressesLevelName OBJECT-TYPE
	SYNTAX      DisplayString
	MAX-ACCESS  not-accessible
	STATUS      current
	DESCRIPTION
	"Table entry display string for rewritePoolNumAddresses"
	::={rewritePoolNumAddressesLevelEntry 1}

rewritePoolNumAddressesLevelVal OBJECT-TYPE
	SYNTAX	 CounterBasedGauge64
	MAX-ACCESS  read-only
	STATUS      current
	DESCRIPTION
	"Table entry attribute for rewritePoolNumAddresses"
	::={rewritePoolNumAddressesLevelEntry 2}

rewritePoolNumAddressesLevelMax OBJECT-TYPE
	SYNTAX	 CounterBasedGauge64
	MAX-ACCESS  read-only
	STATUS      current
	DESCRIPTION
	"Table entry attribute for rewritePoolNumAddresses"
	::={rewritePoolNumAddressesLevelEntry 4}


rewritePoolPortBlockAllocationReqSent	OBJECT IDENTIFIER ::={rewrite 153}

rewritePoolPortBlockAllocationReqSentVal	OBJECT-TYPE
	SYNTAX	 Counter64
	MAX-ACCESS read-only
	STATUS obsolete
	DESCRIPTION "Pool - port block allocation requests sent"

	::={rewritePoolPortBlockAllocationReqSent 1}

rewritePoolPortBlockAllocationReqSentMom	OBJECT-TYPE
	SYNTAX	 CounterBasedGauge64
	MAX-ACCESS read-only
	STATUS obsolete
	DESCRIPTION "Pool - port block allocation requests sent"

	::={rewritePoolPortBlockAllocationReqSent 2}

rewritePoolPortBlockAllocationReqSentMax	OBJECT-TYPE
	SYNTAX	 CounterBasedGauge64
	MAX-ACCESS read-only
	STATUS obsolete
	DESCRIPTION "Pool - port block allocation requests sent"

	::={rewritePoolPortBlockAllocationReqSent 3}

rewritePoolPortBlockAllocationReqSentLevelTable OBJECT-TYPE
	SYNTAX      SEQUENCE OF RewritePoolPortBlockAllocationReqSentLevelEntry
	MAX-ACCESS  not-accessible
	STATUS      current
	DESCRIPTION
	"Table for rewritePoolPortBlockAllocationReqSent"
	::={rewritePoolPortBlockAllocationReqSent 4}

rewritePoolPortBlockAllocationReqSentLevelEntry OBJECT-TYPE
	SYNTAX      RewritePoolPortBlockAllocationReqSentLevelEntry
	MAX-ACCESS  not-accessible
	STATUS      current
	DESCRIPTION
	"Table entry for rewritePoolPortBlockAllocationReqSent"
	INDEX { rewritePoolPortBlockAllocationReqSentLevelName }
	::={rewritePoolPortBlockAllocationReqSentLevelTable 1}

RewritePoolPortBlockAllocationReqSentLevelEntry ::=
	SEQUENCE {
		rewritePoolPortBlockAllocationReqSentLevelName	DisplayString,
		rewritePoolPortBlockAllocationReqSentLevelVal	Counter64,
		rewritePoolPortBlockAllocationReqSentLevelMom	CounterBasedGauge64,
		rewritePoolPortBlockAllocationReqSentLevelMax	CounterBasedGauge64
	}

rewritePoolPortBlockAllocationReqSentLevelName OBJECT-TYPE
	SYNTAX      DisplayString
	MAX-ACCESS  not-accessible
	STATUS      current
	DESCRIPTION
	"Table entry display string for rewritePoolPortBlockAllocationReqSent"
	::={rewritePoolPortBlockAllocationReqSentLevelEntry 1}

rewritePoolPortBlockAllocationReqSentLevelVal OBJECT-TYPE
	SYNTAX	 Counter64
	MAX-ACCESS  read-only
	STATUS      current
	DESCRIPTION
	"Table entry attribute for rewritePoolPortBlockAllocationReqSent"
	::={rewritePoolPortBlockAllocationReqSentLevelEntry 2}

rewritePoolPortBlockAllocationReqSentLevelMom OBJECT-TYPE
	SYNTAX	 CounterBasedGauge64
	MAX-ACCESS  read-only
	STATUS      current
	DESCRIPTION
	"Table entry attribute for rewritePoolPortBlockAllocationReqSent"
	::={rewritePoolPortBlockAllocationReqSentLevelEntry 3}

rewritePoolPortBlockAllocationReqSentLevelMax OBJECT-TYPE
	SYNTAX	 CounterBasedGauge64
	MAX-ACCESS  read-only
	STATUS      current
	DESCRIPTION
	"Table entry attribute for rewritePoolPortBlockAllocationReqSent"
	::={rewritePoolPortBlockAllocationReqSentLevelEntry 4}


rewritePoolPortBlockLowAllocationReqSent	OBJECT IDENTIFIER ::={rewrite 154}

rewritePoolPortBlockLowAllocationReqSentVal	OBJECT-TYPE
	SYNTAX	 Counter64
	MAX-ACCESS read-only
	STATUS obsolete
	DESCRIPTION "Pool - port block allocation requests sent - low"

	::={rewritePoolPortBlockLowAllocationReqSent 1}

rewritePoolPortBlockLowAllocationReqSentMom	OBJECT-TYPE
	SYNTAX	 CounterBasedGauge64
	MAX-ACCESS read-only
	STATUS obsolete
	DESCRIPTION "Pool - port block allocation requests sent - low"

	::={rewritePoolPortBlockLowAllocationReqSent 2}

rewritePoolPortBlockLowAllocationReqSentMax	OBJECT-TYPE
	SYNTAX	 CounterBasedGauge64
	MAX-ACCESS read-only
	STATUS obsolete
	DESCRIPTION "Pool - port block allocation requests sent - low"

	::={rewritePoolPortBlockLowAllocationReqSent 3}

rewritePoolPortBlockLowAllocationReqSentLevelTable OBJECT-TYPE
	SYNTAX      SEQUENCE OF RewritePoolPortBlockLowAllocationReqSentLevelEntry
	MAX-ACCESS  not-accessible
	STATUS      current
	DESCRIPTION
	"Table for rewritePoolPortBlockLowAllocationReqSent"
	::={rewritePoolPortBlockLowAllocationReqSent 4}

rewritePoolPortBlockLowAllocationReqSentLevelEntry OBJECT-TYPE
	SYNTAX      RewritePoolPortBlockLowAllocationReqSentLevelEntry
	MAX-ACCESS  not-accessible
	STATUS      current
	DESCRIPTION
	"Table entry for rewritePoolPortBlockLowAllocationReqSent"
	INDEX { rewritePoolPortBlockLowAllocationReqSentLevelName }
	::={rewritePoolPortBlockLowAllocationReqSentLevelTable 1}

RewritePoolPortBlockLowAllocationReqSentLevelEntry ::=
	SEQUENCE {
		rewritePoolPortBlockLowAllocationReqSentLevelName	DisplayString,
		rewritePoolPortBlockLowAllocationReqSentLevelVal	Counter64,
		rewritePoolPortBlockLowAllocationReqSentLevelMom	CounterBasedGauge64,
		rewritePoolPortBlockLowAllocationReqSentLevelMax	CounterBasedGauge64
	}

rewritePoolPortBlockLowAllocationReqSentLevelName OBJECT-TYPE
	SYNTAX      DisplayString
	MAX-ACCESS  not-accessible
	STATUS      current
	DESCRIPTION
	"Table entry display string for rewritePoolPortBlockLowAllocationReqSent"
	::={rewritePoolPortBlockLowAllocationReqSentLevelEntry 1}

rewritePoolPortBlockLowAllocationReqSentLevelVal OBJECT-TYPE
	SYNTAX	 Counter64
	MAX-ACCESS  read-only
	STATUS      current
	DESCRIPTION
	"Table entry attribute for rewritePoolPortBlockLowAllocationReqSent"
	::={rewritePoolPortBlockLowAllocationReqSentLevelEntry 2}

rewritePoolPortBlockLowAllocationReqSentLevelMom OBJECT-TYPE
	SYNTAX	 CounterBasedGauge64
	MAX-ACCESS  read-only
	STATUS      current
	DESCRIPTION
	"Table entry attribute for rewritePoolPortBlockLowAllocationReqSent"
	::={rewritePoolPortBlockLowAllocationReqSentLevelEntry 3}

rewritePoolPortBlockLowAllocationReqSentLevelMax OBJECT-TYPE
	SYNTAX	 CounterBasedGauge64
	MAX-ACCESS  read-only
	STATUS      current
	DESCRIPTION
	"Table entry attribute for rewritePoolPortBlockLowAllocationReqSent"
	::={rewritePoolPortBlockLowAllocationReqSentLevelEntry 4}


rewritePoolPortBlockHighAllocationReqSent	OBJECT IDENTIFIER ::={rewrite 155}

rewritePoolPortBlockHighAllocationReqSentVal	OBJECT-TYPE
	SYNTAX	 Counter64
	MAX-ACCESS read-only
	STATUS obsolete
	DESCRIPTION "Pool - port block allocation requests sent - high"

	::={rewritePoolPortBlockHighAllocationReqSent 1}

rewritePoolPortBlockHighAllocationReqSentMom	OBJECT-TYPE
	SYNTAX	 CounterBasedGauge64
	MAX-ACCESS read-only
	STATUS obsolete
	DESCRIPTION "Pool - port block allocation requests sent - high"

	::={rewritePoolPortBlockHighAllocationReqSent 2}

rewritePoolPortBlockHighAllocationReqSentMax	OBJECT-TYPE
	SYNTAX	 CounterBasedGauge64
	MAX-ACCESS read-only
	STATUS obsolete
	DESCRIPTION "Pool - port block allocation requests sent - high"

	::={rewritePoolPortBlockHighAllocationReqSent 3}

rewritePoolPortBlockHighAllocationReqSentLevelTable OBJECT-TYPE
	SYNTAX      SEQUENCE OF RewritePoolPortBlockHighAllocationReqSentLevelEntry
	MAX-ACCESS  not-accessible
	STATUS      current
	DESCRIPTION
	"Table for rewritePoolPortBlockHighAllocationReqSent"
	::={rewritePoolPortBlockHighAllocationReqSent 4}

rewritePoolPortBlockHighAllocationReqSentLevelEntry OBJECT-TYPE
	SYNTAX      RewritePoolPortBlockHighAllocationReqSentLevelEntry
	MAX-ACCESS  not-accessible
	STATUS      current
	DESCRIPTION
	"Table entry for rewritePoolPortBlockHighAllocationReqSent"
	INDEX { rewritePoolPortBlockHighAllocationReqSentLevelName }
	::={rewritePoolPortBlockHighAllocationReqSentLevelTable 1}

RewritePoolPortBlockHighAllocationReqSentLevelEntry ::=
	SEQUENCE {
		rewritePoolPortBlockHighAllocationReqSentLevelName	DisplayString,
		rewritePoolPortBlockHighAllocationReqSentLevelVal	Counter64,
		rewritePoolPortBlockHighAllocationReqSentLevelMom	CounterBasedGauge64,
		rewritePoolPortBlockHighAllocationReqSentLevelMax	CounterBasedGauge64
	}

rewritePoolPortBlockHighAllocationReqSentLevelName OBJECT-TYPE
	SYNTAX      DisplayString
	MAX-ACCESS  not-accessible
	STATUS      current
	DESCRIPTION
	"Table entry display string for rewritePoolPortBlockHighAllocationReqSent"
	::={rewritePoolPortBlockHighAllocationReqSentLevelEntry 1}

rewritePoolPortBlockHighAllocationReqSentLevelVal OBJECT-TYPE
	SYNTAX	 Counter64
	MAX-ACCESS  read-only
	STATUS      current
	DESCRIPTION
	"Table entry attribute for rewritePoolPortBlockHighAllocationReqSent"
	::={rewritePoolPortBlockHighAllocationReqSentLevelEntry 2}

rewritePoolPortBlockHighAllocationReqSentLevelMom OBJECT-TYPE
	SYNTAX	 CounterBasedGauge64
	MAX-ACCESS  read-only
	STATUS      current
	DESCRIPTION
	"Table entry attribute for rewritePoolPortBlockHighAllocationReqSent"
	::={rewritePoolPortBlockHighAllocationReqSentLevelEntry 3}

rewritePoolPortBlockHighAllocationReqSentLevelMax OBJECT-TYPE
	SYNTAX	 CounterBasedGauge64
	MAX-ACCESS  read-only
	STATUS      current
	DESCRIPTION
	"Table entry attribute for rewritePoolPortBlockHighAllocationReqSent"
	::={rewritePoolPortBlockHighAllocationReqSentLevelEntry 4}


rewritePoolPortBlockDeallocationEventsSent	OBJECT IDENTIFIER ::={rewrite 156}

rewritePoolPortBlockDeallocationEventsSentVal	OBJECT-TYPE
	SYNTAX	 Counter64
	MAX-ACCESS read-only
	STATUS obsolete
	DESCRIPTION "Pool - port block deallocation events sent"

	::={rewritePoolPortBlockDeallocationEventsSent 1}

rewritePoolPortBlockDeallocationEventsSentMom	OBJECT-TYPE
	SYNTAX	 CounterBasedGauge64
	MAX-ACCESS read-only
	STATUS obsolete
	DESCRIPTION "Pool - port block deallocation events sent"

	::={rewritePoolPortBlockDeallocationEventsSent 2}

rewritePoolPortBlockDeallocationEventsSentMax	OBJECT-TYPE
	SYNTAX	 CounterBasedGauge64
	MAX-ACCESS read-only
	STATUS obsolete
	DESCRIPTION "Pool - port block deallocation events sent"

	::={rewritePoolPortBlockDeallocationEventsSent 3}

rewritePoolPortBlockDeallocationEventsSentLevelTable OBJECT-TYPE
	SYNTAX      SEQUENCE OF RewritePoolPortBlockDeallocationEventsSentLevelEntry
	MAX-ACCESS  not-accessible
	STATUS      current
	DESCRIPTION
	"Table for rewritePoolPortBlockDeallocationEventsSent"
	::={rewritePoolPortBlockDeallocationEventsSent 4}

rewritePoolPortBlockDeallocationEventsSentLevelEntry OBJECT-TYPE
	SYNTAX      RewritePoolPortBlockDeallocationEventsSentLevelEntry
	MAX-ACCESS  not-accessible
	STATUS      current
	DESCRIPTION
	"Table entry for rewritePoolPortBlockDeallocationEventsSent"
	INDEX { rewritePoolPortBlockDeallocationEventsSentLevelName }
	::={rewritePoolPortBlockDeallocationEventsSentLevelTable 1}

RewritePoolPortBlockDeallocationEventsSentLevelEntry ::=
	SEQUENCE {
		rewritePoolPortBlockDeallocationEventsSentLevelName	DisplayString,
		rewritePoolPortBlockDeallocationEventsSentLevelVal	Counter64,
		rewritePoolPortBlockDeallocationEventsSentLevelMom	CounterBasedGauge64,
		rewritePoolPortBlockDeallocationEventsSentLevelMax	CounterBasedGauge64
	}

rewritePoolPortBlockDeallocationEventsSentLevelName OBJECT-TYPE
	SYNTAX      DisplayString
	MAX-ACCESS  not-accessible
	STATUS      current
	DESCRIPTION
	"Table entry display string for rewritePoolPortBlockDeallocationEventsSent"
	::={rewritePoolPortBlockDeallocationEventsSentLevelEntry 1}

rewritePoolPortBlockDeallocationEventsSentLevelVal OBJECT-TYPE
	SYNTAX	 Counter64
	MAX-ACCESS  read-only
	STATUS      current
	DESCRIPTION
	"Table entry attribute for rewritePoolPortBlockDeallocationEventsSent"
	::={rewritePoolPortBlockDeallocationEventsSentLevelEntry 2}

rewritePoolPortBlockDeallocationEventsSentLevelMom OBJECT-TYPE
	SYNTAX	 CounterBasedGauge64
	MAX-ACCESS  read-only
	STATUS      current
	DESCRIPTION
	"Table entry attribute for rewritePoolPortBlockDeallocationEventsSent"
	::={rewritePoolPortBlockDeallocationEventsSentLevelEntry 3}

rewritePoolPortBlockDeallocationEventsSentLevelMax OBJECT-TYPE
	SYNTAX	 CounterBasedGauge64
	MAX-ACCESS  read-only
	STATUS      current
	DESCRIPTION
	"Table entry attribute for rewritePoolPortBlockDeallocationEventsSent"
	::={rewritePoolPortBlockDeallocationEventsSentLevelEntry 4}


rewritePoolPortBlockLowDeallocationEventsSent	OBJECT IDENTIFIER ::={rewrite 157}

rewritePoolPortBlockLowDeallocationEventsSentVal	OBJECT-TYPE
	SYNTAX	 Counter64
	MAX-ACCESS read-only
	STATUS obsolete
	DESCRIPTION "Pool - port block deallocation events sent - low"

	::={rewritePoolPortBlockLowDeallocationEventsSent 1}

rewritePoolPortBlockLowDeallocationEventsSentMom	OBJECT-TYPE
	SYNTAX	 CounterBasedGauge64
	MAX-ACCESS read-only
	STATUS obsolete
	DESCRIPTION "Pool - port block deallocation events sent - low"

	::={rewritePoolPortBlockLowDeallocationEventsSent 2}

rewritePoolPortBlockLowDeallocationEventsSentMax	OBJECT-TYPE
	SYNTAX	 CounterBasedGauge64
	MAX-ACCESS read-only
	STATUS obsolete
	DESCRIPTION "Pool - port block deallocation events sent - low"

	::={rewritePoolPortBlockLowDeallocationEventsSent 3}

rewritePoolPortBlockLowDeallocationEventsSentLevelTable OBJECT-TYPE
	SYNTAX      SEQUENCE OF RewritePoolPortBlockLowDeallocationEventsSentLevelEntry
	MAX-ACCESS  not-accessible
	STATUS      current
	DESCRIPTION
	"Table for rewritePoolPortBlockLowDeallocationEventsSent"
	::={rewritePoolPortBlockLowDeallocationEventsSent 4}

rewritePoolPortBlockLowDeallocationEventsSentLevelEntry OBJECT-TYPE
	SYNTAX      RewritePoolPortBlockLowDeallocationEventsSentLevelEntry
	MAX-ACCESS  not-accessible
	STATUS      current
	DESCRIPTION
	"Table entry for rewritePoolPortBlockLowDeallocationEventsSent"
	INDEX { rewritePoolPortBlockLowDeallocationEventsSentLevelName }
	::={rewritePoolPortBlockLowDeallocationEventsSentLevelTable 1}

RewritePoolPortBlockLowDeallocationEventsSentLevelEntry ::=
	SEQUENCE {
		rewritePoolPortBlockLowDeallocationEventsSentLevelName	DisplayString,
		rewritePoolPortBlockLowDeallocationEventsSentLevelVal	Counter64,
		rewritePoolPortBlockLowDeallocationEventsSentLevelMom	CounterBasedGauge64,
		rewritePoolPortBlockLowDeallocationEventsSentLevelMax	CounterBasedGauge64
	}

rewritePoolPortBlockLowDeallocationEventsSentLevelName OBJECT-TYPE
	SYNTAX      DisplayString
	MAX-ACCESS  not-accessible
	STATUS      current
	DESCRIPTION
	"Table entry display string for rewritePoolPortBlockLowDeallocationEventsSent"
	::={rewritePoolPortBlockLowDeallocationEventsSentLevelEntry 1}

rewritePoolPortBlockLowDeallocationEventsSentLevelVal OBJECT-TYPE
	SYNTAX	 Counter64
	MAX-ACCESS  read-only
	STATUS      current
	DESCRIPTION
	"Table entry attribute for rewritePoolPortBlockLowDeallocationEventsSent"
	::={rewritePoolPortBlockLowDeallocationEventsSentLevelEntry 2}

rewritePoolPortBlockLowDeallocationEventsSentLevelMom OBJECT-TYPE
	SYNTAX	 CounterBasedGauge64
	MAX-ACCESS  read-only
	STATUS      current
	DESCRIPTION
	"Table entry attribute for rewritePoolPortBlockLowDeallocationEventsSent"
	::={rewritePoolPortBlockLowDeallocationEventsSentLevelEntry 3}

rewritePoolPortBlockLowDeallocationEventsSentLevelMax OBJECT-TYPE
	SYNTAX	 CounterBasedGauge64
	MAX-ACCESS  read-only
	STATUS      current
	DESCRIPTION
	"Table entry attribute for rewritePoolPortBlockLowDeallocationEventsSent"
	::={rewritePoolPortBlockLowDeallocationEventsSentLevelEntry 4}


rewritePoolPortBlockHighDeallocationEventsSent	OBJECT IDENTIFIER ::={rewrite 158}

rewritePoolPortBlockHighDeallocationEventsSentVal	OBJECT-TYPE
	SYNTAX	 Counter64
	MAX-ACCESS read-only
	STATUS obsolete
	DESCRIPTION "Pool - port block deallocation events sent - high"

	::={rewritePoolPortBlockHighDeallocationEventsSent 1}

rewritePoolPortBlockHighDeallocationEventsSentMom	OBJECT-TYPE
	SYNTAX	 CounterBasedGauge64
	MAX-ACCESS read-only
	STATUS obsolete
	DESCRIPTION "Pool - port block deallocation events sent - high"

	::={rewritePoolPortBlockHighDeallocationEventsSent 2}

rewritePoolPortBlockHighDeallocationEventsSentMax	OBJECT-TYPE
	SYNTAX	 CounterBasedGauge64
	MAX-ACCESS read-only
	STATUS obsolete
	DESCRIPTION "Pool - port block deallocation events sent - high"

	::={rewritePoolPortBlockHighDeallocationEventsSent 3}

rewritePoolPortBlockHighDeallocationEventsSentLevelTable OBJECT-TYPE
	SYNTAX      SEQUENCE OF RewritePoolPortBlockHighDeallocationEventsSentLevelEntry
	MAX-ACCESS  not-accessible
	STATUS      current
	DESCRIPTION
	"Table for rewritePoolPortBlockHighDeallocationEventsSent"
	::={rewritePoolPortBlockHighDeallocationEventsSent 4}

rewritePoolPortBlockHighDeallocationEventsSentLevelEntry OBJECT-TYPE
	SYNTAX      RewritePoolPortBlockHighDeallocationEventsSentLevelEntry
	MAX-ACCESS  not-accessible
	STATUS      current
	DESCRIPTION
	"Table entry for rewritePoolPortBlockHighDeallocationEventsSent"
	INDEX { rewritePoolPortBlockHighDeallocationEventsSentLevelName }
	::={rewritePoolPortBlockHighDeallocationEventsSentLevelTable 1}

RewritePoolPortBlockHighDeallocationEventsSentLevelEntry ::=
	SEQUENCE {
		rewritePoolPortBlockHighDeallocationEventsSentLevelName	DisplayString,
		rewritePoolPortBlockHighDeallocationEventsSentLevelVal	Counter64,
		rewritePoolPortBlockHighDeallocationEventsSentLevelMom	CounterBasedGauge64,
		rewritePoolPortBlockHighDeallocationEventsSentLevelMax	CounterBasedGauge64
	}

rewritePoolPortBlockHighDeallocationEventsSentLevelName OBJECT-TYPE
	SYNTAX      DisplayString
	MAX-ACCESS  not-accessible
	STATUS      current
	DESCRIPTION
	"Table entry display string for rewritePoolPortBlockHighDeallocationEventsSent"
	::={rewritePoolPortBlockHighDeallocationEventsSentLevelEntry 1}

rewritePoolPortBlockHighDeallocationEventsSentLevelVal OBJECT-TYPE
	SYNTAX	 Counter64
	MAX-ACCESS  read-only
	STATUS      current
	DESCRIPTION
	"Table entry attribute for rewritePoolPortBlockHighDeallocationEventsSent"
	::={rewritePoolPortBlockHighDeallocationEventsSentLevelEntry 2}

rewritePoolPortBlockHighDeallocationEventsSentLevelMom OBJECT-TYPE
	SYNTAX	 CounterBasedGauge64
	MAX-ACCESS  read-only
	STATUS      current
	DESCRIPTION
	"Table entry attribute for rewritePoolPortBlockHighDeallocationEventsSent"
	::={rewritePoolPortBlockHighDeallocationEventsSentLevelEntry 3}

rewritePoolPortBlockHighDeallocationEventsSentLevelMax OBJECT-TYPE
	SYNTAX	 CounterBasedGauge64
	MAX-ACCESS  read-only
	STATUS      current
	DESCRIPTION
	"Table entry attribute for rewritePoolPortBlockHighDeallocationEventsSent"
	::={rewritePoolPortBlockHighDeallocationEventsSentLevelEntry 4}


rewritePoolPortBlockAssociationEventsSent	OBJECT IDENTIFIER ::={rewrite 159}

rewritePoolPortBlockAssociationEventsSentVal	OBJECT-TYPE
	SYNTAX	 Counter64
	MAX-ACCESS read-only
	STATUS current
	DESCRIPTION "Pool - port block association events sent"

	::={rewritePoolPortBlockAssociationEventsSent 1}

rewritePoolPortBlockAssociationEventsSentMom	OBJECT-TYPE
	SYNTAX	 CounterBasedGauge64
	MAX-ACCESS read-only
	STATUS current
	DESCRIPTION "Pool - port block association events sent"

	::={rewritePoolPortBlockAssociationEventsSent 2}

rewritePoolPortBlockAssociationEventsSentMax	OBJECT-TYPE
	SYNTAX	 CounterBasedGauge64
	MAX-ACCESS read-only
	STATUS current
	DESCRIPTION "Pool - port block association events sent"

	::={rewritePoolPortBlockAssociationEventsSent 3}

rewritePoolPortBlockAssociationEventsSentLevelTable OBJECT-TYPE
	SYNTAX      SEQUENCE OF RewritePoolPortBlockAssociationEventsSentLevelEntry
	MAX-ACCESS  not-accessible
	STATUS      current
	DESCRIPTION
	"Table for rewritePoolPortBlockAssociationEventsSent"
	::={rewritePoolPortBlockAssociationEventsSent 4}

rewritePoolPortBlockAssociationEventsSentLevelEntry OBJECT-TYPE
	SYNTAX      RewritePoolPortBlockAssociationEventsSentLevelEntry
	MAX-ACCESS  not-accessible
	STATUS      current
	DESCRIPTION
	"Table entry for rewritePoolPortBlockAssociationEventsSent"
	INDEX { rewritePoolPortBlockAssociationEventsSentLevelName }
	::={rewritePoolPortBlockAssociationEventsSentLevelTable 1}

RewritePoolPortBlockAssociationEventsSentLevelEntry ::=
	SEQUENCE {
		rewritePoolPortBlockAssociationEventsSentLevelName	DisplayString,
		rewritePoolPortBlockAssociationEventsSentLevelVal	Counter64,
		rewritePoolPortBlockAssociationEventsSentLevelMom	CounterBasedGauge64,
		rewritePoolPortBlockAssociationEventsSentLevelMax	CounterBasedGauge64
	}

rewritePoolPortBlockAssociationEventsSentLevelName OBJECT-TYPE
	SYNTAX      DisplayString
	MAX-ACCESS  not-accessible
	STATUS      current
	DESCRIPTION
	"Table entry display string for rewritePoolPortBlockAssociationEventsSent"
	::={rewritePoolPortBlockAssociationEventsSentLevelEntry 1}

rewritePoolPortBlockAssociationEventsSentLevelVal OBJECT-TYPE
	SYNTAX	 Counter64
	MAX-ACCESS  read-only
	STATUS      current
	DESCRIPTION
	"Table entry attribute for rewritePoolPortBlockAssociationEventsSent"
	::={rewritePoolPortBlockAssociationEventsSentLevelEntry 2}

rewritePoolPortBlockAssociationEventsSentLevelMom OBJECT-TYPE
	SYNTAX	 CounterBasedGauge64
	MAX-ACCESS  read-only
	STATUS      current
	DESCRIPTION
	"Table entry attribute for rewritePoolPortBlockAssociationEventsSent"
	::={rewritePoolPortBlockAssociationEventsSentLevelEntry 3}

rewritePoolPortBlockAssociationEventsSentLevelMax OBJECT-TYPE
	SYNTAX	 CounterBasedGauge64
	MAX-ACCESS  read-only
	STATUS      current
	DESCRIPTION
	"Table entry attribute for rewritePoolPortBlockAssociationEventsSent"
	::={rewritePoolPortBlockAssociationEventsSentLevelEntry 4}


rewritePoolPortBlockLowAssociationEventsSent	OBJECT IDENTIFIER ::={rewrite 160}

rewritePoolPortBlockLowAssociationEventsSentVal	OBJECT-TYPE
	SYNTAX	 Counter64
	MAX-ACCESS read-only
	STATUS current
	DESCRIPTION "Pool - port block association events sent - low"

	::={rewritePoolPortBlockLowAssociationEventsSent 1}

rewritePoolPortBlockLowAssociationEventsSentMom	OBJECT-TYPE
	SYNTAX	 CounterBasedGauge64
	MAX-ACCESS read-only
	STATUS current
	DESCRIPTION "Pool - port block association events sent - low"

	::={rewritePoolPortBlockLowAssociationEventsSent 2}

rewritePoolPortBlockLowAssociationEventsSentMax	OBJECT-TYPE
	SYNTAX	 CounterBasedGauge64
	MAX-ACCESS read-only
	STATUS current
	DESCRIPTION "Pool - port block association events sent - low"

	::={rewritePoolPortBlockLowAssociationEventsSent 3}

rewritePoolPortBlockLowAssociationEventsSentLevelTable OBJECT-TYPE
	SYNTAX      SEQUENCE OF RewritePoolPortBlockLowAssociationEventsSentLevelEntry
	MAX-ACCESS  not-accessible
	STATUS      current
	DESCRIPTION
	"Table for rewritePoolPortBlockLowAssociationEventsSent"
	::={rewritePoolPortBlockLowAssociationEventsSent 4}

rewritePoolPortBlockLowAssociationEventsSentLevelEntry OBJECT-TYPE
	SYNTAX      RewritePoolPortBlockLowAssociationEventsSentLevelEntry
	MAX-ACCESS  not-accessible
	STATUS      current
	DESCRIPTION
	"Table entry for rewritePoolPortBlockLowAssociationEventsSent"
	INDEX { rewritePoolPortBlockLowAssociationEventsSentLevelName }
	::={rewritePoolPortBlockLowAssociationEventsSentLevelTable 1}

RewritePoolPortBlockLowAssociationEventsSentLevelEntry ::=
	SEQUENCE {
		rewritePoolPortBlockLowAssociationEventsSentLevelName	DisplayString,
		rewritePoolPortBlockLowAssociationEventsSentLevelVal	Counter64,
		rewritePoolPortBlockLowAssociationEventsSentLevelMom	CounterBasedGauge64,
		rewritePoolPortBlockLowAssociationEventsSentLevelMax	CounterBasedGauge64
	}

rewritePoolPortBlockLowAssociationEventsSentLevelName OBJECT-TYPE
	SYNTAX      DisplayString
	MAX-ACCESS  not-accessible
	STATUS      current
	DESCRIPTION
	"Table entry display string for rewritePoolPortBlockLowAssociationEventsSent"
	::={rewritePoolPortBlockLowAssociationEventsSentLevelEntry 1}

rewritePoolPortBlockLowAssociationEventsSentLevelVal OBJECT-TYPE
	SYNTAX	 Counter64
	MAX-ACCESS  read-only
	STATUS      current
	DESCRIPTION
	"Table entry attribute for rewritePoolPortBlockLowAssociationEventsSent"
	::={rewritePoolPortBlockLowAssociationEventsSentLevelEntry 2}

rewritePoolPortBlockLowAssociationEventsSentLevelMom OBJECT-TYPE
	SYNTAX	 CounterBasedGauge64
	MAX-ACCESS  read-only
	STATUS      current
	DESCRIPTION
	"Table entry attribute for rewritePoolPortBlockLowAssociationEventsSent"
	::={rewritePoolPortBlockLowAssociationEventsSentLevelEntry 3}

rewritePoolPortBlockLowAssociationEventsSentLevelMax OBJECT-TYPE
	SYNTAX	 CounterBasedGauge64
	MAX-ACCESS  read-only
	STATUS      current
	DESCRIPTION
	"Table entry attribute for rewritePoolPortBlockLowAssociationEventsSent"
	::={rewritePoolPortBlockLowAssociationEventsSentLevelEntry 4}


rewritePoolPortBlockHighAssociationEventsSent	OBJECT IDENTIFIER ::={rewrite 161}

rewritePoolPortBlockHighAssociationEventsSentVal	OBJECT-TYPE
	SYNTAX	 Counter64
	MAX-ACCESS read-only
	STATUS current
	DESCRIPTION "Pool - port block association events sent - high"

	::={rewritePoolPortBlockHighAssociationEventsSent 1}

rewritePoolPortBlockHighAssociationEventsSentMom	OBJECT-TYPE
	SYNTAX	 CounterBasedGauge64
	MAX-ACCESS read-only
	STATUS current
	DESCRIPTION "Pool - port block association events sent - high"

	::={rewritePoolPortBlockHighAssociationEventsSent 2}

rewritePoolPortBlockHighAssociationEventsSentMax	OBJECT-TYPE
	SYNTAX	 CounterBasedGauge64
	MAX-ACCESS read-only
	STATUS current
	DESCRIPTION "Pool - port block association events sent - high"

	::={rewritePoolPortBlockHighAssociationEventsSent 3}

rewritePoolPortBlockHighAssociationEventsSentLevelTable OBJECT-TYPE
	SYNTAX      SEQUENCE OF RewritePoolPortBlockHighAssociationEventsSentLevelEntry
	MAX-ACCESS  not-accessible
	STATUS      current
	DESCRIPTION
	"Table for rewritePoolPortBlockHighAssociationEventsSent"
	::={rewritePoolPortBlockHighAssociationEventsSent 4}

rewritePoolPortBlockHighAssociationEventsSentLevelEntry OBJECT-TYPE
	SYNTAX      RewritePoolPortBlockHighAssociationEventsSentLevelEntry
	MAX-ACCESS  not-accessible
	STATUS      current
	DESCRIPTION
	"Table entry for rewritePoolPortBlockHighAssociationEventsSent"
	INDEX { rewritePoolPortBlockHighAssociationEventsSentLevelName }
	::={rewritePoolPortBlockHighAssociationEventsSentLevelTable 1}

RewritePoolPortBlockHighAssociationEventsSentLevelEntry ::=
	SEQUENCE {
		rewritePoolPortBlockHighAssociationEventsSentLevelName	DisplayString,
		rewritePoolPortBlockHighAssociationEventsSentLevelVal	Counter64,
		rewritePoolPortBlockHighAssociationEventsSentLevelMom	CounterBasedGauge64,
		rewritePoolPortBlockHighAssociationEventsSentLevelMax	CounterBasedGauge64
	}

rewritePoolPortBlockHighAssociationEventsSentLevelName OBJECT-TYPE
	SYNTAX      DisplayString
	MAX-ACCESS  not-accessible
	STATUS      current
	DESCRIPTION
	"Table entry display string for rewritePoolPortBlockHighAssociationEventsSent"
	::={rewritePoolPortBlockHighAssociationEventsSentLevelEntry 1}

rewritePoolPortBlockHighAssociationEventsSentLevelVal OBJECT-TYPE
	SYNTAX	 Counter64
	MAX-ACCESS  read-only
	STATUS      current
	DESCRIPTION
	"Table entry attribute for rewritePoolPortBlockHighAssociationEventsSent"
	::={rewritePoolPortBlockHighAssociationEventsSentLevelEntry 2}

rewritePoolPortBlockHighAssociationEventsSentLevelMom OBJECT-TYPE
	SYNTAX	 CounterBasedGauge64
	MAX-ACCESS  read-only
	STATUS      current
	DESCRIPTION
	"Table entry attribute for rewritePoolPortBlockHighAssociationEventsSent"
	::={rewritePoolPortBlockHighAssociationEventsSentLevelEntry 3}

rewritePoolPortBlockHighAssociationEventsSentLevelMax OBJECT-TYPE
	SYNTAX	 CounterBasedGauge64
	MAX-ACCESS  read-only
	STATUS      current
	DESCRIPTION
	"Table entry attribute for rewritePoolPortBlockHighAssociationEventsSent"
	::={rewritePoolPortBlockHighAssociationEventsSentLevelEntry 4}


rewritePoolPortBlockDeassociationEventsSent	OBJECT IDENTIFIER ::={rewrite 162}

rewritePoolPortBlockDeassociationEventsSentVal	OBJECT-TYPE
	SYNTAX	 Counter64
	MAX-ACCESS read-only
	STATUS current
	DESCRIPTION "Pool - port block deassociation events sent"

	::={rewritePoolPortBlockDeassociationEventsSent 1}

rewritePoolPortBlockDeassociationEventsSentMom	OBJECT-TYPE
	SYNTAX	 CounterBasedGauge64
	MAX-ACCESS read-only
	STATUS current
	DESCRIPTION "Pool - port block deassociation events sent"

	::={rewritePoolPortBlockDeassociationEventsSent 2}

rewritePoolPortBlockDeassociationEventsSentMax	OBJECT-TYPE
	SYNTAX	 CounterBasedGauge64
	MAX-ACCESS read-only
	STATUS current
	DESCRIPTION "Pool - port block deassociation events sent"

	::={rewritePoolPortBlockDeassociationEventsSent 3}

rewritePoolPortBlockDeassociationEventsSentLevelTable OBJECT-TYPE
	SYNTAX      SEQUENCE OF RewritePoolPortBlockDeassociationEventsSentLevelEntry
	MAX-ACCESS  not-accessible
	STATUS      current
	DESCRIPTION
	"Table for rewritePoolPortBlockDeassociationEventsSent"
	::={rewritePoolPortBlockDeassociationEventsSent 4}

rewritePoolPortBlockDeassociationEventsSentLevelEntry OBJECT-TYPE
	SYNTAX      RewritePoolPortBlockDeassociationEventsSentLevelEntry
	MAX-ACCESS  not-accessible
	STATUS      current
	DESCRIPTION
	"Table entry for rewritePoolPortBlockDeassociationEventsSent"
	INDEX { rewritePoolPortBlockDeassociationEventsSentLevelName }
	::={rewritePoolPortBlockDeassociationEventsSentLevelTable 1}

RewritePoolPortBlockDeassociationEventsSentLevelEntry ::=
	SEQUENCE {
		rewritePoolPortBlockDeassociationEventsSentLevelName	DisplayString,
		rewritePoolPortBlockDeassociationEventsSentLevelVal	Counter64,
		rewritePoolPortBlockDeassociationEventsSentLevelMom	CounterBasedGauge64,
		rewritePoolPortBlockDeassociationEventsSentLevelMax	CounterBasedGauge64
	}

rewritePoolPortBlockDeassociationEventsSentLevelName OBJECT-TYPE
	SYNTAX      DisplayString
	MAX-ACCESS  not-accessible
	STATUS      current
	DESCRIPTION
	"Table entry display string for rewritePoolPortBlockDeassociationEventsSent"
	::={rewritePoolPortBlockDeassociationEventsSentLevelEntry 1}

rewritePoolPortBlockDeassociationEventsSentLevelVal OBJECT-TYPE
	SYNTAX	 Counter64
	MAX-ACCESS  read-only
	STATUS      current
	DESCRIPTION
	"Table entry attribute for rewritePoolPortBlockDeassociationEventsSent"
	::={rewritePoolPortBlockDeassociationEventsSentLevelEntry 2}

rewritePoolPortBlockDeassociationEventsSentLevelMom OBJECT-TYPE
	SYNTAX	 CounterBasedGauge64
	MAX-ACCESS  read-only
	STATUS      current
	DESCRIPTION
	"Table entry attribute for rewritePoolPortBlockDeassociationEventsSent"
	::={rewritePoolPortBlockDeassociationEventsSentLevelEntry 3}

rewritePoolPortBlockDeassociationEventsSentLevelMax OBJECT-TYPE
	SYNTAX	 CounterBasedGauge64
	MAX-ACCESS  read-only
	STATUS      current
	DESCRIPTION
	"Table entry attribute for rewritePoolPortBlockDeassociationEventsSent"
	::={rewritePoolPortBlockDeassociationEventsSentLevelEntry 4}


rewritePoolPortBlockLowDeassociationEventsSent	OBJECT IDENTIFIER ::={rewrite 163}

rewritePoolPortBlockLowDeassociationEventsSentVal	OBJECT-TYPE
	SYNTAX	 Counter64
	MAX-ACCESS read-only
	STATUS current
	DESCRIPTION "Pool - port block deassociation events sent - low"

	::={rewritePoolPortBlockLowDeassociationEventsSent 1}

rewritePoolPortBlockLowDeassociationEventsSentMom	OBJECT-TYPE
	SYNTAX	 CounterBasedGauge64
	MAX-ACCESS read-only
	STATUS current
	DESCRIPTION "Pool - port block deassociation events sent - low"

	::={rewritePoolPortBlockLowDeassociationEventsSent 2}

rewritePoolPortBlockLowDeassociationEventsSentMax	OBJECT-TYPE
	SYNTAX	 CounterBasedGauge64
	MAX-ACCESS read-only
	STATUS current
	DESCRIPTION "Pool - port block deassociation events sent - low"

	::={rewritePoolPortBlockLowDeassociationEventsSent 3}

rewritePoolPortBlockLowDeassociationEventsSentLevelTable OBJECT-TYPE
	SYNTAX      SEQUENCE OF RewritePoolPortBlockLowDeassociationEventsSentLevelEntry
	MAX-ACCESS  not-accessible
	STATUS      current
	DESCRIPTION
	"Table for rewritePoolPortBlockLowDeassociationEventsSent"
	::={rewritePoolPortBlockLowDeassociationEventsSent 4}

rewritePoolPortBlockLowDeassociationEventsSentLevelEntry OBJECT-TYPE
	SYNTAX      RewritePoolPortBlockLowDeassociationEventsSentLevelEntry
	MAX-ACCESS  not-accessible
	STATUS      current
	DESCRIPTION
	"Table entry for rewritePoolPortBlockLowDeassociationEventsSent"
	INDEX { rewritePoolPortBlockLowDeassociationEventsSentLevelName }
	::={rewritePoolPortBlockLowDeassociationEventsSentLevelTable 1}

RewritePoolPortBlockLowDeassociationEventsSentLevelEntry ::=
	SEQUENCE {
		rewritePoolPortBlockLowDeassociationEventsSentLevelName	DisplayString,
		rewritePoolPortBlockLowDeassociationEventsSentLevelVal	Counter64,
		rewritePoolPortBlockLowDeassociationEventsSentLevelMom	CounterBasedGauge64,
		rewritePoolPortBlockLowDeassociationEventsSentLevelMax	CounterBasedGauge64
	}

rewritePoolPortBlockLowDeassociationEventsSentLevelName OBJECT-TYPE
	SYNTAX      DisplayString
	MAX-ACCESS  not-accessible
	STATUS      current
	DESCRIPTION
	"Table entry display string for rewritePoolPortBlockLowDeassociationEventsSent"
	::={rewritePoolPortBlockLowDeassociationEventsSentLevelEntry 1}

rewritePoolPortBlockLowDeassociationEventsSentLevelVal OBJECT-TYPE
	SYNTAX	 Counter64
	MAX-ACCESS  read-only
	STATUS      current
	DESCRIPTION
	"Table entry attribute for rewritePoolPortBlockLowDeassociationEventsSent"
	::={rewritePoolPortBlockLowDeassociationEventsSentLevelEntry 2}

rewritePoolPortBlockLowDeassociationEventsSentLevelMom OBJECT-TYPE
	SYNTAX	 CounterBasedGauge64
	MAX-ACCESS  read-only
	STATUS      current
	DESCRIPTION
	"Table entry attribute for rewritePoolPortBlockLowDeassociationEventsSent"
	::={rewritePoolPortBlockLowDeassociationEventsSentLevelEntry 3}

rewritePoolPortBlockLowDeassociationEventsSentLevelMax OBJECT-TYPE
	SYNTAX	 CounterBasedGauge64
	MAX-ACCESS  read-only
	STATUS      current
	DESCRIPTION
	"Table entry attribute for rewritePoolPortBlockLowDeassociationEventsSent"
	::={rewritePoolPortBlockLowDeassociationEventsSentLevelEntry 4}


rewritePoolPortBlockHighDeassociationEventsSent	OBJECT IDENTIFIER ::={rewrite 164}

rewritePoolPortBlockHighDeassociationEventsSentVal	OBJECT-TYPE
	SYNTAX	 Counter64
	MAX-ACCESS read-only
	STATUS current
	DESCRIPTION "Pool - port block deassociation events sent - high"

	::={rewritePoolPortBlockHighDeassociationEventsSent 1}

rewritePoolPortBlockHighDeassociationEventsSentMom	OBJECT-TYPE
	SYNTAX	 CounterBasedGauge64
	MAX-ACCESS read-only
	STATUS current
	DESCRIPTION "Pool - port block deassociation events sent - high"

	::={rewritePoolPortBlockHighDeassociationEventsSent 2}

rewritePoolPortBlockHighDeassociationEventsSentMax	OBJECT-TYPE
	SYNTAX	 CounterBasedGauge64
	MAX-ACCESS read-only
	STATUS current
	DESCRIPTION "Pool - port block deassociation events sent - high"

	::={rewritePoolPortBlockHighDeassociationEventsSent 3}

rewritePoolPortBlockHighDeassociationEventsSentLevelTable OBJECT-TYPE
	SYNTAX      SEQUENCE OF RewritePoolPortBlockHighDeassociationEventsSentLevelEntry
	MAX-ACCESS  not-accessible
	STATUS      current
	DESCRIPTION
	"Table for rewritePoolPortBlockHighDeassociationEventsSent"
	::={rewritePoolPortBlockHighDeassociationEventsSent 4}

rewritePoolPortBlockHighDeassociationEventsSentLevelEntry OBJECT-TYPE
	SYNTAX      RewritePoolPortBlockHighDeassociationEventsSentLevelEntry
	MAX-ACCESS  not-accessible
	STATUS      current
	DESCRIPTION
	"Table entry for rewritePoolPortBlockHighDeassociationEventsSent"
	INDEX { rewritePoolPortBlockHighDeassociationEventsSentLevelName }
	::={rewritePoolPortBlockHighDeassociationEventsSentLevelTable 1}

RewritePoolPortBlockHighDeassociationEventsSentLevelEntry ::=
	SEQUENCE {
		rewritePoolPortBlockHighDeassociationEventsSentLevelName	DisplayString,
		rewritePoolPortBlockHighDeassociationEventsSentLevelVal	Counter64,
		rewritePoolPortBlockHighDeassociationEventsSentLevelMom	CounterBasedGauge64,
		rewritePoolPortBlockHighDeassociationEventsSentLevelMax	CounterBasedGauge64
	}

rewritePoolPortBlockHighDeassociationEventsSentLevelName OBJECT-TYPE
	SYNTAX      DisplayString
	MAX-ACCESS  not-accessible
	STATUS      current
	DESCRIPTION
	"Table entry display string for rewritePoolPortBlockHighDeassociationEventsSent"
	::={rewritePoolPortBlockHighDeassociationEventsSentLevelEntry 1}

rewritePoolPortBlockHighDeassociationEventsSentLevelVal OBJECT-TYPE
	SYNTAX	 Counter64
	MAX-ACCESS  read-only
	STATUS      current
	DESCRIPTION
	"Table entry attribute for rewritePoolPortBlockHighDeassociationEventsSent"
	::={rewritePoolPortBlockHighDeassociationEventsSentLevelEntry 2}

rewritePoolPortBlockHighDeassociationEventsSentLevelMom OBJECT-TYPE
	SYNTAX	 CounterBasedGauge64
	MAX-ACCESS  read-only
	STATUS      current
	DESCRIPTION
	"Table entry attribute for rewritePoolPortBlockHighDeassociationEventsSent"
	::={rewritePoolPortBlockHighDeassociationEventsSentLevelEntry 3}

rewritePoolPortBlockHighDeassociationEventsSentLevelMax OBJECT-TYPE
	SYNTAX	 CounterBasedGauge64
	MAX-ACCESS  read-only
	STATUS      current
	DESCRIPTION
	"Table entry attribute for rewritePoolPortBlockHighDeassociationEventsSent"
	::={rewritePoolPortBlockHighDeassociationEventsSentLevelEntry 4}


rewritePoolPortBlockDeassociationAllEventsSent	OBJECT IDENTIFIER ::={rewrite 165}

rewritePoolPortBlockDeassociationAllEventsSentVal	OBJECT-TYPE
	SYNTAX	 Counter64
	MAX-ACCESS read-only
	STATUS current
	DESCRIPTION "Pool - port block deassociation all events sent"

	::={rewritePoolPortBlockDeassociationAllEventsSent 1}

rewritePoolPortBlockDeassociationAllEventsSentMom	OBJECT-TYPE
	SYNTAX	 CounterBasedGauge64
	MAX-ACCESS read-only
	STATUS current
	DESCRIPTION "Pool - port block deassociation all events sent"

	::={rewritePoolPortBlockDeassociationAllEventsSent 2}

rewritePoolPortBlockDeassociationAllEventsSentMax	OBJECT-TYPE
	SYNTAX	 CounterBasedGauge64
	MAX-ACCESS read-only
	STATUS current
	DESCRIPTION "Pool - port block deassociation all events sent"

	::={rewritePoolPortBlockDeassociationAllEventsSent 3}

rewritePoolPortBlockDeassociationAllEventsSentLevelTable OBJECT-TYPE
	SYNTAX      SEQUENCE OF RewritePoolPortBlockDeassociationAllEventsSentLevelEntry
	MAX-ACCESS  not-accessible
	STATUS      current
	DESCRIPTION
	"Table for rewritePoolPortBlockDeassociationAllEventsSent"
	::={rewritePoolPortBlockDeassociationAllEventsSent 4}

rewritePoolPortBlockDeassociationAllEventsSentLevelEntry OBJECT-TYPE
	SYNTAX      RewritePoolPortBlockDeassociationAllEventsSentLevelEntry
	MAX-ACCESS  not-accessible
	STATUS      current
	DESCRIPTION
	"Table entry for rewritePoolPortBlockDeassociationAllEventsSent"
	INDEX { rewritePoolPortBlockDeassociationAllEventsSentLevelName }
	::={rewritePoolPortBlockDeassociationAllEventsSentLevelTable 1}

RewritePoolPortBlockDeassociationAllEventsSentLevelEntry ::=
	SEQUENCE {
		rewritePoolPortBlockDeassociationAllEventsSentLevelName	DisplayString,
		rewritePoolPortBlockDeassociationAllEventsSentLevelVal	Counter64,
		rewritePoolPortBlockDeassociationAllEventsSentLevelMom	CounterBasedGauge64,
		rewritePoolPortBlockDeassociationAllEventsSentLevelMax	CounterBasedGauge64
	}

rewritePoolPortBlockDeassociationAllEventsSentLevelName OBJECT-TYPE
	SYNTAX      DisplayString
	MAX-ACCESS  not-accessible
	STATUS      current
	DESCRIPTION
	"Table entry display string for rewritePoolPortBlockDeassociationAllEventsSent"
	::={rewritePoolPortBlockDeassociationAllEventsSentLevelEntry 1}

rewritePoolPortBlockDeassociationAllEventsSentLevelVal OBJECT-TYPE
	SYNTAX	 Counter64
	MAX-ACCESS  read-only
	STATUS      current
	DESCRIPTION
	"Table entry attribute for rewritePoolPortBlockDeassociationAllEventsSent"
	::={rewritePoolPortBlockDeassociationAllEventsSentLevelEntry 2}

rewritePoolPortBlockDeassociationAllEventsSentLevelMom OBJECT-TYPE
	SYNTAX	 CounterBasedGauge64
	MAX-ACCESS  read-only
	STATUS      current
	DESCRIPTION
	"Table entry attribute for rewritePoolPortBlockDeassociationAllEventsSent"
	::={rewritePoolPortBlockDeassociationAllEventsSentLevelEntry 3}

rewritePoolPortBlockDeassociationAllEventsSentLevelMax OBJECT-TYPE
	SYNTAX	 CounterBasedGauge64
	MAX-ACCESS  read-only
	STATUS      current
	DESCRIPTION
	"Table entry attribute for rewritePoolPortBlockDeassociationAllEventsSent"
	::={rewritePoolPortBlockDeassociationAllEventsSentLevelEntry 4}


rewritePoolPortBlockReceivedLow	OBJECT IDENTIFIER ::={rewrite 166}

rewritePoolPortBlockReceivedLowVal	OBJECT-TYPE
	SYNTAX	 Counter64
	MAX-ACCESS read-only
	STATUS current
	DESCRIPTION "Pool - port block received low"

	::={rewritePoolPortBlockReceivedLow 1}

rewritePoolPortBlockReceivedLowMom	OBJECT-TYPE
	SYNTAX	 CounterBasedGauge64
	MAX-ACCESS read-only
	STATUS current
	DESCRIPTION "Pool - port block received low"

	::={rewritePoolPortBlockReceivedLow 2}

rewritePoolPortBlockReceivedLowMax	OBJECT-TYPE
	SYNTAX	 CounterBasedGauge64
	MAX-ACCESS read-only
	STATUS current
	DESCRIPTION "Pool - port block received low"

	::={rewritePoolPortBlockReceivedLow 3}

rewritePoolPortBlockReceivedLowLevelTable OBJECT-TYPE
	SYNTAX      SEQUENCE OF RewritePoolPortBlockReceivedLowLevelEntry
	MAX-ACCESS  not-accessible
	STATUS      current
	DESCRIPTION
	"Table for rewritePoolPortBlockReceivedLow"
	::={rewritePoolPortBlockReceivedLow 4}

rewritePoolPortBlockReceivedLowLevelEntry OBJECT-TYPE
	SYNTAX      RewritePoolPortBlockReceivedLowLevelEntry
	MAX-ACCESS  not-accessible
	STATUS      current
	DESCRIPTION
	"Table entry for rewritePoolPortBlockReceivedLow"
	INDEX { rewritePoolPortBlockReceivedLowLevelName }
	::={rewritePoolPortBlockReceivedLowLevelTable 1}

RewritePoolPortBlockReceivedLowLevelEntry ::=
	SEQUENCE {
		rewritePoolPortBlockReceivedLowLevelName	DisplayString,
		rewritePoolPortBlockReceivedLowLevelVal	Counter64,
		rewritePoolPortBlockReceivedLowLevelMom	CounterBasedGauge64,
		rewritePoolPortBlockReceivedLowLevelMax	CounterBasedGauge64
	}

rewritePoolPortBlockReceivedLowLevelName OBJECT-TYPE
	SYNTAX      DisplayString
	MAX-ACCESS  not-accessible
	STATUS      current
	DESCRIPTION
	"Table entry display string for rewritePoolPortBlockReceivedLow"
	::={rewritePoolPortBlockReceivedLowLevelEntry 1}

rewritePoolPortBlockReceivedLowLevelVal OBJECT-TYPE
	SYNTAX	 Counter64
	MAX-ACCESS  read-only
	STATUS      current
	DESCRIPTION
	"Table entry attribute for rewritePoolPortBlockReceivedLow"
	::={rewritePoolPortBlockReceivedLowLevelEntry 2}

rewritePoolPortBlockReceivedLowLevelMom OBJECT-TYPE
	SYNTAX	 CounterBasedGauge64
	MAX-ACCESS  read-only
	STATUS      current
	DESCRIPTION
	"Table entry attribute for rewritePoolPortBlockReceivedLow"
	::={rewritePoolPortBlockReceivedLowLevelEntry 3}

rewritePoolPortBlockReceivedLowLevelMax OBJECT-TYPE
	SYNTAX	 CounterBasedGauge64
	MAX-ACCESS  read-only
	STATUS      current
	DESCRIPTION
	"Table entry attribute for rewritePoolPortBlockReceivedLow"
	::={rewritePoolPortBlockReceivedLowLevelEntry 4}


rewritePoolPortBlockReceivedHigh	OBJECT IDENTIFIER ::={rewrite 167}

rewritePoolPortBlockReceivedHighVal	OBJECT-TYPE
	SYNTAX	 Counter64
	MAX-ACCESS read-only
	STATUS current
	DESCRIPTION "Pool - port block received high"

	::={rewritePoolPortBlockReceivedHigh 1}

rewritePoolPortBlockReceivedHighMom	OBJECT-TYPE
	SYNTAX	 CounterBasedGauge64
	MAX-ACCESS read-only
	STATUS current
	DESCRIPTION "Pool - port block received high"

	::={rewritePoolPortBlockReceivedHigh 2}

rewritePoolPortBlockReceivedHighMax	OBJECT-TYPE
	SYNTAX	 CounterBasedGauge64
	MAX-ACCESS read-only
	STATUS current
	DESCRIPTION "Pool - port block received high"

	::={rewritePoolPortBlockReceivedHigh 3}

rewritePoolPortBlockReceivedHighLevelTable OBJECT-TYPE
	SYNTAX      SEQUENCE OF RewritePoolPortBlockReceivedHighLevelEntry
	MAX-ACCESS  not-accessible
	STATUS      current
	DESCRIPTION
	"Table for rewritePoolPortBlockReceivedHigh"
	::={rewritePoolPortBlockReceivedHigh 4}

rewritePoolPortBlockReceivedHighLevelEntry OBJECT-TYPE
	SYNTAX      RewritePoolPortBlockReceivedHighLevelEntry
	MAX-ACCESS  not-accessible
	STATUS      current
	DESCRIPTION
	"Table entry for rewritePoolPortBlockReceivedHigh"
	INDEX { rewritePoolPortBlockReceivedHighLevelName }
	::={rewritePoolPortBlockReceivedHighLevelTable 1}

RewritePoolPortBlockReceivedHighLevelEntry ::=
	SEQUENCE {
		rewritePoolPortBlockReceivedHighLevelName	DisplayString,
		rewritePoolPortBlockReceivedHighLevelVal	Counter64,
		rewritePoolPortBlockReceivedHighLevelMom	CounterBasedGauge64,
		rewritePoolPortBlockReceivedHighLevelMax	CounterBasedGauge64
	}

rewritePoolPortBlockReceivedHighLevelName OBJECT-TYPE
	SYNTAX      DisplayString
	MAX-ACCESS  not-accessible
	STATUS      current
	DESCRIPTION
	"Table entry display string for rewritePoolPortBlockReceivedHigh"
	::={rewritePoolPortBlockReceivedHighLevelEntry 1}

rewritePoolPortBlockReceivedHighLevelVal OBJECT-TYPE
	SYNTAX	 Counter64
	MAX-ACCESS  read-only
	STATUS      current
	DESCRIPTION
	"Table entry attribute for rewritePoolPortBlockReceivedHigh"
	::={rewritePoolPortBlockReceivedHighLevelEntry 2}

rewritePoolPortBlockReceivedHighLevelMom OBJECT-TYPE
	SYNTAX	 CounterBasedGauge64
	MAX-ACCESS  read-only
	STATUS      current
	DESCRIPTION
	"Table entry attribute for rewritePoolPortBlockReceivedHigh"
	::={rewritePoolPortBlockReceivedHighLevelEntry 3}

rewritePoolPortBlockReceivedHighLevelMax OBJECT-TYPE
	SYNTAX	 CounterBasedGauge64
	MAX-ACCESS  read-only
	STATUS      current
	DESCRIPTION
	"Table entry attribute for rewritePoolPortBlockReceivedHigh"
	::={rewritePoolPortBlockReceivedHighLevelEntry 4}


rewritePoolAddressAddCollision	OBJECT IDENTIFIER ::={rewrite 168}

rewritePoolAddressAddCollisionVal	OBJECT-TYPE
	SYNTAX	 CounterBasedGauge64
	MAX-ACCESS read-only
	STATUS current
	DESCRIPTION "Pool - collision when adding address"

	::={rewritePoolAddressAddCollision 1}

rewritePoolAddressAddCollisionMax	OBJECT-TYPE
	SYNTAX	 CounterBasedGauge64
	MAX-ACCESS read-only
	STATUS current
	DESCRIPTION "Pool - collision when adding address"

	::={rewritePoolAddressAddCollision 3}

rewritePoolAddressAddCollisionLevelTable OBJECT-TYPE
	SYNTAX      SEQUENCE OF RewritePoolAddressAddCollisionLevelEntry
	MAX-ACCESS  not-accessible
	STATUS      current
	DESCRIPTION
	"Table for rewritePoolAddressAddCollision"
	::={rewritePoolAddressAddCollision 4}

rewritePoolAddressAddCollisionLevelEntry OBJECT-TYPE
	SYNTAX      RewritePoolAddressAddCollisionLevelEntry
	MAX-ACCESS  not-accessible
	STATUS      current
	DESCRIPTION
	"Table entry for rewritePoolAddressAddCollision"
	INDEX { rewritePoolAddressAddCollisionLevelName }
	::={rewritePoolAddressAddCollisionLevelTable 1}

RewritePoolAddressAddCollisionLevelEntry ::=
	SEQUENCE {
		rewritePoolAddressAddCollisionLevelName	DisplayString,
		rewritePoolAddressAddCollisionLevelVal	CounterBasedGauge64,
		rewritePoolAddressAddCollisionLevelMax	CounterBasedGauge64
	}

rewritePoolAddressAddCollisionLevelName OBJECT-TYPE
	SYNTAX      DisplayString
	MAX-ACCESS  not-accessible
	STATUS      current
	DESCRIPTION
	"Table entry display string for rewritePoolAddressAddCollision"
	::={rewritePoolAddressAddCollisionLevelEntry 1}

rewritePoolAddressAddCollisionLevelVal OBJECT-TYPE
	SYNTAX	 CounterBasedGauge64
	MAX-ACCESS  read-only
	STATUS      current
	DESCRIPTION
	"Table entry attribute for rewritePoolAddressAddCollision"
	::={rewritePoolAddressAddCollisionLevelEntry 2}

rewritePoolAddressAddCollisionLevelMax OBJECT-TYPE
	SYNTAX	 CounterBasedGauge64
	MAX-ACCESS  read-only
	STATUS      current
	DESCRIPTION
	"Table entry attribute for rewritePoolAddressAddCollision"
	::={rewritePoolAddressAddCollisionLevelEntry 4}


rewritePoolPortBlockAssociationUpdateEventsSent	OBJECT IDENTIFIER ::={rewrite 169}

rewritePoolPortBlockAssociationUpdateEventsSentVal	OBJECT-TYPE
	SYNTAX	 Counter64
	MAX-ACCESS read-only
	STATUS current
	DESCRIPTION "Pool - port block association update events sent"

	::={rewritePoolPortBlockAssociationUpdateEventsSent 1}

rewritePoolPortBlockAssociationUpdateEventsSentMom	OBJECT-TYPE
	SYNTAX	 CounterBasedGauge64
	MAX-ACCESS read-only
	STATUS current
	DESCRIPTION "Pool - port block association update events sent"

	::={rewritePoolPortBlockAssociationUpdateEventsSent 2}

rewritePoolPortBlockAssociationUpdateEventsSentMax	OBJECT-TYPE
	SYNTAX	 CounterBasedGauge64
	MAX-ACCESS read-only
	STATUS current
	DESCRIPTION "Pool - port block association update events sent"

	::={rewritePoolPortBlockAssociationUpdateEventsSent 3}

rewritePoolPortBlockAssociationUpdateEventsSentLevelTable OBJECT-TYPE
	SYNTAX      SEQUENCE OF RewritePoolPortBlockAssociationUpdateEventsSentLevelEntry
	MAX-ACCESS  not-accessible
	STATUS      current
	DESCRIPTION
	"Table for rewritePoolPortBlockAssociationUpdateEventsSent"
	::={rewritePoolPortBlockAssociationUpdateEventsSent 4}

rewritePoolPortBlockAssociationUpdateEventsSentLevelEntry OBJECT-TYPE
	SYNTAX      RewritePoolPortBlockAssociationUpdateEventsSentLevelEntry
	MAX-ACCESS  not-accessible
	STATUS      current
	DESCRIPTION
	"Table entry for rewritePoolPortBlockAssociationUpdateEventsSent"
	INDEX { rewritePoolPortBlockAssociationUpdateEventsSentLevelName }
	::={rewritePoolPortBlockAssociationUpdateEventsSentLevelTable 1}

RewritePoolPortBlockAssociationUpdateEventsSentLevelEntry ::=
	SEQUENCE {
		rewritePoolPortBlockAssociationUpdateEventsSentLevelName	DisplayString,
		rewritePoolPortBlockAssociationUpdateEventsSentLevelVal	Counter64,
		rewritePoolPortBlockAssociationUpdateEventsSentLevelMom	CounterBasedGauge64,
		rewritePoolPortBlockAssociationUpdateEventsSentLevelMax	CounterBasedGauge64
	}

rewritePoolPortBlockAssociationUpdateEventsSentLevelName OBJECT-TYPE
	SYNTAX      DisplayString
	MAX-ACCESS  not-accessible
	STATUS      current
	DESCRIPTION
	"Table entry display string for rewritePoolPortBlockAssociationUpdateEventsSent"
	::={rewritePoolPortBlockAssociationUpdateEventsSentLevelEntry 1}

rewritePoolPortBlockAssociationUpdateEventsSentLevelVal OBJECT-TYPE
	SYNTAX	 Counter64
	MAX-ACCESS  read-only
	STATUS      current
	DESCRIPTION
	"Table entry attribute for rewritePoolPortBlockAssociationUpdateEventsSent"
	::={rewritePoolPortBlockAssociationUpdateEventsSentLevelEntry 2}

rewritePoolPortBlockAssociationUpdateEventsSentLevelMom OBJECT-TYPE
	SYNTAX	 CounterBasedGauge64
	MAX-ACCESS  read-only
	STATUS      current
	DESCRIPTION
	"Table entry attribute for rewritePoolPortBlockAssociationUpdateEventsSent"
	::={rewritePoolPortBlockAssociationUpdateEventsSentLevelEntry 3}

rewritePoolPortBlockAssociationUpdateEventsSentLevelMax OBJECT-TYPE
	SYNTAX	 CounterBasedGauge64
	MAX-ACCESS  read-only
	STATUS      current
	DESCRIPTION
	"Table entry attribute for rewritePoolPortBlockAssociationUpdateEventsSent"
	::={rewritePoolPortBlockAssociationUpdateEventsSentLevelEntry 4}


rewritePoolPortBlockLowAssociationUpdateEventsSent	OBJECT IDENTIFIER ::={rewrite 170}

rewritePoolPortBlockLowAssociationUpdateEventsSentVal	OBJECT-TYPE
	SYNTAX	 Counter64
	MAX-ACCESS read-only
	STATUS current
	DESCRIPTION "Pool - port block association update events sent - low"

	::={rewritePoolPortBlockLowAssociationUpdateEventsSent 1}

rewritePoolPortBlockLowAssociationUpdateEventsSentMom	OBJECT-TYPE
	SYNTAX	 CounterBasedGauge64
	MAX-ACCESS read-only
	STATUS current
	DESCRIPTION "Pool - port block association update events sent - low"

	::={rewritePoolPortBlockLowAssociationUpdateEventsSent 2}

rewritePoolPortBlockLowAssociationUpdateEventsSentMax	OBJECT-TYPE
	SYNTAX	 CounterBasedGauge64
	MAX-ACCESS read-only
	STATUS current
	DESCRIPTION "Pool - port block association update events sent - low"

	::={rewritePoolPortBlockLowAssociationUpdateEventsSent 3}

rewritePoolPortBlockLowAssociationUpdateEventsSentLevelTable OBJECT-TYPE
	SYNTAX      SEQUENCE OF RewritePoolPortBlockLowAssociationUpdateEventsSentLevelEntry
	MAX-ACCESS  not-accessible
	STATUS      current
	DESCRIPTION
	"Table for rewritePoolPortBlockLowAssociationUpdateEventsSent"
	::={rewritePoolPortBlockLowAssociationUpdateEventsSent 4}

rewritePoolPortBlockLowAssociationUpdateEventsSentLevelEntry OBJECT-TYPE
	SYNTAX      RewritePoolPortBlockLowAssociationUpdateEventsSentLevelEntry
	MAX-ACCESS  not-accessible
	STATUS      current
	DESCRIPTION
	"Table entry for rewritePoolPortBlockLowAssociationUpdateEventsSent"
	INDEX { rewritePoolPortBlockLowAssociationUpdateEventsSentLevelName }
	::={rewritePoolPortBlockLowAssociationUpdateEventsSentLevelTable 1}

RewritePoolPortBlockLowAssociationUpdateEventsSentLevelEntry ::=
	SEQUENCE {
		rewritePoolPortBlockLowAssociationUpdateEventsSentLevelName	DisplayString,
		rewritePoolPortBlockLowAssociationUpdateEventsSentLevelVal	Counter64,
		rewritePoolPortBlockLowAssociationUpdateEventsSentLevelMom	CounterBasedGauge64,
		rewritePoolPortBlockLowAssociationUpdateEventsSentLevelMax	CounterBasedGauge64
	}

rewritePoolPortBlockLowAssociationUpdateEventsSentLevelName OBJECT-TYPE
	SYNTAX      DisplayString
	MAX-ACCESS  not-accessible
	STATUS      current
	DESCRIPTION
	"Table entry display string for rewritePoolPortBlockLowAssociationUpdateEventsSent"
	::={rewritePoolPortBlockLowAssociationUpdateEventsSentLevelEntry 1}

rewritePoolPortBlockLowAssociationUpdateEventsSentLevelVal OBJECT-TYPE
	SYNTAX	 Counter64
	MAX-ACCESS  read-only
	STATUS      current
	DESCRIPTION
	"Table entry attribute for rewritePoolPortBlockLowAssociationUpdateEventsSent"
	::={rewritePoolPortBlockLowAssociationUpdateEventsSentLevelEntry 2}

rewritePoolPortBlockLowAssociationUpdateEventsSentLevelMom OBJECT-TYPE
	SYNTAX	 CounterBasedGauge64
	MAX-ACCESS  read-only
	STATUS      current
	DESCRIPTION
	"Table entry attribute for rewritePoolPortBlockLowAssociationUpdateEventsSent"
	::={rewritePoolPortBlockLowAssociationUpdateEventsSentLevelEntry 3}

rewritePoolPortBlockLowAssociationUpdateEventsSentLevelMax OBJECT-TYPE
	SYNTAX	 CounterBasedGauge64
	MAX-ACCESS  read-only
	STATUS      current
	DESCRIPTION
	"Table entry attribute for rewritePoolPortBlockLowAssociationUpdateEventsSent"
	::={rewritePoolPortBlockLowAssociationUpdateEventsSentLevelEntry 4}


rewritePoolPortBlockHighAssociationUpdateEventsSent	OBJECT IDENTIFIER ::={rewrite 171}

rewritePoolPortBlockHighAssociationUpdateEventsSentVal	OBJECT-TYPE
	SYNTAX	 Counter64
	MAX-ACCESS read-only
	STATUS current
	DESCRIPTION "Pool - port block association update events sent - high"

	::={rewritePoolPortBlockHighAssociationUpdateEventsSent 1}

rewritePoolPortBlockHighAssociationUpdateEventsSentMom	OBJECT-TYPE
	SYNTAX	 CounterBasedGauge64
	MAX-ACCESS read-only
	STATUS current
	DESCRIPTION "Pool - port block association update events sent - high"

	::={rewritePoolPortBlockHighAssociationUpdateEventsSent 2}

rewritePoolPortBlockHighAssociationUpdateEventsSentMax	OBJECT-TYPE
	SYNTAX	 CounterBasedGauge64
	MAX-ACCESS read-only
	STATUS current
	DESCRIPTION "Pool - port block association update events sent - high"

	::={rewritePoolPortBlockHighAssociationUpdateEventsSent 3}

rewritePoolPortBlockHighAssociationUpdateEventsSentLevelTable OBJECT-TYPE
	SYNTAX      SEQUENCE OF RewritePoolPortBlockHighAssociationUpdateEventsSentLevelEntry
	MAX-ACCESS  not-accessible
	STATUS      current
	DESCRIPTION
	"Table for rewritePoolPortBlockHighAssociationUpdateEventsSent"
	::={rewritePoolPortBlockHighAssociationUpdateEventsSent 4}

rewritePoolPortBlockHighAssociationUpdateEventsSentLevelEntry OBJECT-TYPE
	SYNTAX      RewritePoolPortBlockHighAssociationUpdateEventsSentLevelEntry
	MAX-ACCESS  not-accessible
	STATUS      current
	DESCRIPTION
	"Table entry for rewritePoolPortBlockHighAssociationUpdateEventsSent"
	INDEX { rewritePoolPortBlockHighAssociationUpdateEventsSentLevelName }
	::={rewritePoolPortBlockHighAssociationUpdateEventsSentLevelTable 1}

RewritePoolPortBlockHighAssociationUpdateEventsSentLevelEntry ::=
	SEQUENCE {
		rewritePoolPortBlockHighAssociationUpdateEventsSentLevelName	DisplayString,
		rewritePoolPortBlockHighAssociationUpdateEventsSentLevelVal	Counter64,
		rewritePoolPortBlockHighAssociationUpdateEventsSentLevelMom	CounterBasedGauge64,
		rewritePoolPortBlockHighAssociationUpdateEventsSentLevelMax	CounterBasedGauge64
	}

rewritePoolPortBlockHighAssociationUpdateEventsSentLevelName OBJECT-TYPE
	SYNTAX      DisplayString
	MAX-ACCESS  not-accessible
	STATUS      current
	DESCRIPTION
	"Table entry display string for rewritePoolPortBlockHighAssociationUpdateEventsSent"
	::={rewritePoolPortBlockHighAssociationUpdateEventsSentLevelEntry 1}

rewritePoolPortBlockHighAssociationUpdateEventsSentLevelVal OBJECT-TYPE
	SYNTAX	 Counter64
	MAX-ACCESS  read-only
	STATUS      current
	DESCRIPTION
	"Table entry attribute for rewritePoolPortBlockHighAssociationUpdateEventsSent"
	::={rewritePoolPortBlockHighAssociationUpdateEventsSentLevelEntry 2}

rewritePoolPortBlockHighAssociationUpdateEventsSentLevelMom OBJECT-TYPE
	SYNTAX	 CounterBasedGauge64
	MAX-ACCESS  read-only
	STATUS      current
	DESCRIPTION
	"Table entry attribute for rewritePoolPortBlockHighAssociationUpdateEventsSent"
	::={rewritePoolPortBlockHighAssociationUpdateEventsSentLevelEntry 3}

rewritePoolPortBlockHighAssociationUpdateEventsSentLevelMax OBJECT-TYPE
	SYNTAX	 CounterBasedGauge64
	MAX-ACCESS  read-only
	STATUS      current
	DESCRIPTION
	"Table entry attribute for rewritePoolPortBlockHighAssociationUpdateEventsSent"
	::={rewritePoolPortBlockHighAssociationUpdateEventsSentLevelEntry 4}


rewritePoolSubscribersCount	OBJECT IDENTIFIER ::={rewrite 172}

rewritePoolSubscribersCountVal	OBJECT-TYPE
	SYNTAX	 Counter64
	MAX-ACCESS read-only
	STATUS current
	DESCRIPTION "Pool - number of subscribers"

	::={rewritePoolSubscribersCount 1}

rewritePoolSubscribersCountMom	OBJECT-TYPE
	SYNTAX	 CounterBasedGauge64
	MAX-ACCESS read-only
	STATUS current
	DESCRIPTION "Pool - number of subscribers"

	::={rewritePoolSubscribersCount 2}

rewritePoolSubscribersCountMax	OBJECT-TYPE
	SYNTAX	 CounterBasedGauge64
	MAX-ACCESS read-only
	STATUS current
	DESCRIPTION "Pool - number of subscribers"

	::={rewritePoolSubscribersCount 3}

rewritePoolSubscribersCountLevelTable OBJECT-TYPE
	SYNTAX      SEQUENCE OF RewritePoolSubscribersCountLevelEntry
	MAX-ACCESS  not-accessible
	STATUS      current
	DESCRIPTION
	"Table for rewritePoolSubscribersCount"
	::={rewritePoolSubscribersCount 4}

rewritePoolSubscribersCountLevelEntry OBJECT-TYPE
	SYNTAX      RewritePoolSubscribersCountLevelEntry
	MAX-ACCESS  not-accessible
	STATUS      current
	DESCRIPTION
	"Table entry for rewritePoolSubscribersCount"
	INDEX { rewritePoolSubscribersCountLevelName }
	::={rewritePoolSubscribersCountLevelTable 1}

RewritePoolSubscribersCountLevelEntry ::=
	SEQUENCE {
		rewritePoolSubscribersCountLevelName	DisplayString,
		rewritePoolSubscribersCountLevelVal	Counter64,
		rewritePoolSubscribersCountLevelMom	CounterBasedGauge64,
		rewritePoolSubscribersCountLevelMax	CounterBasedGauge64
	}

rewritePoolSubscribersCountLevelName OBJECT-TYPE
	SYNTAX      DisplayString
	MAX-ACCESS  not-accessible
	STATUS      current
	DESCRIPTION
	"Table entry display string for rewritePoolSubscribersCount"
	::={rewritePoolSubscribersCountLevelEntry 1}

rewritePoolSubscribersCountLevelVal OBJECT-TYPE
	SYNTAX	 Counter64
	MAX-ACCESS  read-only
	STATUS      current
	DESCRIPTION
	"Table entry attribute for rewritePoolSubscribersCount"
	::={rewritePoolSubscribersCountLevelEntry 2}

rewritePoolSubscribersCountLevelMom OBJECT-TYPE
	SYNTAX	 CounterBasedGauge64
	MAX-ACCESS  read-only
	STATUS      current
	DESCRIPTION
	"Table entry attribute for rewritePoolSubscribersCount"
	::={rewritePoolSubscribersCountLevelEntry 3}

rewritePoolSubscribersCountLevelMax OBJECT-TYPE
	SYNTAX	 CounterBasedGauge64
	MAX-ACCESS  read-only
	STATUS      current
	DESCRIPTION
	"Table entry attribute for rewritePoolSubscribersCount"
	::={rewritePoolSubscribersCountLevelEntry 4}


rewritePoolSrcIPCount	OBJECT IDENTIFIER ::={rewrite 173}

rewritePoolSrcIPCountVal	OBJECT-TYPE
	SYNTAX	 Counter64
	MAX-ACCESS read-only
	STATUS current
	DESCRIPTION "Pool - Src IP-address count"

	::={rewritePoolSrcIPCount 1}

rewritePoolSrcIPCountMom	OBJECT-TYPE
	SYNTAX	 CounterBasedGauge64
	MAX-ACCESS read-only
	STATUS current
	DESCRIPTION "Pool - Src IP-address count"

	::={rewritePoolSrcIPCount 2}

rewritePoolSrcIPCountMax	OBJECT-TYPE
	SYNTAX	 CounterBasedGauge64
	MAX-ACCESS read-only
	STATUS current
	DESCRIPTION "Pool - Src IP-address count"

	::={rewritePoolSrcIPCount 3}

rewritePoolSrcIPCountLevelTable OBJECT-TYPE
	SYNTAX      SEQUENCE OF RewritePoolSrcIPCountLevelEntry
	MAX-ACCESS  not-accessible
	STATUS      current
	DESCRIPTION
	"Table for rewritePoolSrcIPCount"
	::={rewritePoolSrcIPCount 4}

rewritePoolSrcIPCountLevelEntry OBJECT-TYPE
	SYNTAX      RewritePoolSrcIPCountLevelEntry
	MAX-ACCESS  not-accessible
	STATUS      current
	DESCRIPTION
	"Table entry for rewritePoolSrcIPCount"
	INDEX { rewritePoolSrcIPCountLevelName }
	::={rewritePoolSrcIPCountLevelTable 1}

RewritePoolSrcIPCountLevelEntry ::=
	SEQUENCE {
		rewritePoolSrcIPCountLevelName	DisplayString,
		rewritePoolSrcIPCountLevelVal	Counter64,
		rewritePoolSrcIPCountLevelMom	CounterBasedGauge64,
		rewritePoolSrcIPCountLevelMax	CounterBasedGauge64
	}

rewritePoolSrcIPCountLevelName OBJECT-TYPE
	SYNTAX      DisplayString
	MAX-ACCESS  not-accessible
	STATUS      current
	DESCRIPTION
	"Table entry display string for rewritePoolSrcIPCount"
	::={rewritePoolSrcIPCountLevelEntry 1}

rewritePoolSrcIPCountLevelVal OBJECT-TYPE
	SYNTAX	 Counter64
	MAX-ACCESS  read-only
	STATUS      current
	DESCRIPTION
	"Table entry attribute for rewritePoolSrcIPCount"
	::={rewritePoolSrcIPCountLevelEntry 2}

rewritePoolSrcIPCountLevelMom OBJECT-TYPE
	SYNTAX	 CounterBasedGauge64
	MAX-ACCESS  read-only
	STATUS      current
	DESCRIPTION
	"Table entry attribute for rewritePoolSrcIPCount"
	::={rewritePoolSrcIPCountLevelEntry 3}

rewritePoolSrcIPCountLevelMax OBJECT-TYPE
	SYNTAX	 CounterBasedGauge64
	MAX-ACCESS  read-only
	STATUS      current
	DESCRIPTION
	"Table entry attribute for rewritePoolSrcIPCount"
	::={rewritePoolSrcIPCountLevelEntry 4}


rewriteFragmentedHeaderIgnoredGre	OBJECT IDENTIFIER ::={rewrite 181}

rewriteFragmentedHeaderIgnoredGreVal	OBJECT-TYPE
	SYNTAX	 Counter64
	MAX-ACCESS read-only
	STATUS current
	DESCRIPTION "Fragmented header ignored (GRE)"

	::={rewriteFragmentedHeaderIgnoredGre 1}

rewriteFragmentedHeaderIgnoredGreMom	OBJECT-TYPE
	SYNTAX	 CounterBasedGauge64
	MAX-ACCESS read-only
	STATUS current
	DESCRIPTION "Fragmented header ignored (GRE)"

	::={rewriteFragmentedHeaderIgnoredGre 2}

rewriteFragmentedHeaderIgnoredGreMax	OBJECT-TYPE
	SYNTAX	 CounterBasedGauge64
	MAX-ACCESS read-only
	STATUS current
	DESCRIPTION "Fragmented header ignored (GRE)"

	::={rewriteFragmentedHeaderIgnoredGre 3}

rewriteFragmentedHeaderIgnoredGreLevelTable OBJECT-TYPE
	SYNTAX      SEQUENCE OF RewriteFragmentedHeaderIgnoredGreLevelEntry
	MAX-ACCESS  not-accessible
	STATUS      current
	DESCRIPTION
	"Table for rewriteFragmentedHeaderIgnoredGre"
	::={rewriteFragmentedHeaderIgnoredGre 4}

rewriteFragmentedHeaderIgnoredGreLevelEntry OBJECT-TYPE
	SYNTAX      RewriteFragmentedHeaderIgnoredGreLevelEntry
	MAX-ACCESS  not-accessible
	STATUS      current
	DESCRIPTION
	"Table entry for rewriteFragmentedHeaderIgnoredGre"
	INDEX { rewriteFragmentedHeaderIgnoredGreLevelName }
	::={rewriteFragmentedHeaderIgnoredGreLevelTable 1}

RewriteFragmentedHeaderIgnoredGreLevelEntry ::=
	SEQUENCE {
		rewriteFragmentedHeaderIgnoredGreLevelName	DisplayString,
		rewriteFragmentedHeaderIgnoredGreLevelVal	Counter64,
		rewriteFragmentedHeaderIgnoredGreLevelMom	CounterBasedGauge64,
		rewriteFragmentedHeaderIgnoredGreLevelMax	CounterBasedGauge64
	}

rewriteFragmentedHeaderIgnoredGreLevelName OBJECT-TYPE
	SYNTAX      DisplayString
	MAX-ACCESS  not-accessible
	STATUS      current
	DESCRIPTION
	"Table entry display string for rewriteFragmentedHeaderIgnoredGre"
	::={rewriteFragmentedHeaderIgnoredGreLevelEntry 1}

rewriteFragmentedHeaderIgnoredGreLevelVal OBJECT-TYPE
	SYNTAX	 Counter64
	MAX-ACCESS  read-only
	STATUS      current
	DESCRIPTION
	"Table entry attribute for rewriteFragmentedHeaderIgnoredGre"
	::={rewriteFragmentedHeaderIgnoredGreLevelEntry 2}

rewriteFragmentedHeaderIgnoredGreLevelMom OBJECT-TYPE
	SYNTAX	 CounterBasedGauge64
	MAX-ACCESS  read-only
	STATUS      current
	DESCRIPTION
	"Table entry attribute for rewriteFragmentedHeaderIgnoredGre"
	::={rewriteFragmentedHeaderIgnoredGreLevelEntry 3}

rewriteFragmentedHeaderIgnoredGreLevelMax OBJECT-TYPE
	SYNTAX	 CounterBasedGauge64
	MAX-ACCESS  read-only
	STATUS      current
	DESCRIPTION
	"Table entry attribute for rewriteFragmentedHeaderIgnoredGre"
	::={rewriteFragmentedHeaderIgnoredGreLevelEntry 4}


rewriteFragmentedHeaderIgnoredPptp	OBJECT IDENTIFIER ::={rewrite 182}

rewriteFragmentedHeaderIgnoredPptpVal	OBJECT-TYPE
	SYNTAX	 Counter64
	MAX-ACCESS read-only
	STATUS current
	DESCRIPTION "Fragmented header ignored (PPTP)"

	::={rewriteFragmentedHeaderIgnoredPptp 1}

rewriteFragmentedHeaderIgnoredPptpMom	OBJECT-TYPE
	SYNTAX	 CounterBasedGauge64
	MAX-ACCESS read-only
	STATUS current
	DESCRIPTION "Fragmented header ignored (PPTP)"

	::={rewriteFragmentedHeaderIgnoredPptp 2}

rewriteFragmentedHeaderIgnoredPptpMax	OBJECT-TYPE
	SYNTAX	 CounterBasedGauge64
	MAX-ACCESS read-only
	STATUS current
	DESCRIPTION "Fragmented header ignored (PPTP)"

	::={rewriteFragmentedHeaderIgnoredPptp 3}

rewriteFragmentedHeaderIgnoredPptpLevelTable OBJECT-TYPE
	SYNTAX      SEQUENCE OF RewriteFragmentedHeaderIgnoredPptpLevelEntry
	MAX-ACCESS  not-accessible
	STATUS      current
	DESCRIPTION
	"Table for rewriteFragmentedHeaderIgnoredPptp"
	::={rewriteFragmentedHeaderIgnoredPptp 4}

rewriteFragmentedHeaderIgnoredPptpLevelEntry OBJECT-TYPE
	SYNTAX      RewriteFragmentedHeaderIgnoredPptpLevelEntry
	MAX-ACCESS  not-accessible
	STATUS      current
	DESCRIPTION
	"Table entry for rewriteFragmentedHeaderIgnoredPptp"
	INDEX { rewriteFragmentedHeaderIgnoredPptpLevelName }
	::={rewriteFragmentedHeaderIgnoredPptpLevelTable 1}

RewriteFragmentedHeaderIgnoredPptpLevelEntry ::=
	SEQUENCE {
		rewriteFragmentedHeaderIgnoredPptpLevelName	DisplayString,
		rewriteFragmentedHeaderIgnoredPptpLevelVal	Counter64,
		rewriteFragmentedHeaderIgnoredPptpLevelMom	CounterBasedGauge64,
		rewriteFragmentedHeaderIgnoredPptpLevelMax	CounterBasedGauge64
	}

rewriteFragmentedHeaderIgnoredPptpLevelName OBJECT-TYPE
	SYNTAX      DisplayString
	MAX-ACCESS  not-accessible
	STATUS      current
	DESCRIPTION
	"Table entry display string for rewriteFragmentedHeaderIgnoredPptp"
	::={rewriteFragmentedHeaderIgnoredPptpLevelEntry 1}

rewriteFragmentedHeaderIgnoredPptpLevelVal OBJECT-TYPE
	SYNTAX	 Counter64
	MAX-ACCESS  read-only
	STATUS      current
	DESCRIPTION
	"Table entry attribute for rewriteFragmentedHeaderIgnoredPptp"
	::={rewriteFragmentedHeaderIgnoredPptpLevelEntry 2}

rewriteFragmentedHeaderIgnoredPptpLevelMom OBJECT-TYPE
	SYNTAX	 CounterBasedGauge64
	MAX-ACCESS  read-only
	STATUS      current
	DESCRIPTION
	"Table entry attribute for rewriteFragmentedHeaderIgnoredPptp"
	::={rewriteFragmentedHeaderIgnoredPptpLevelEntry 3}

rewriteFragmentedHeaderIgnoredPptpLevelMax OBJECT-TYPE
	SYNTAX	 CounterBasedGauge64
	MAX-ACCESS  read-only
	STATUS      current
	DESCRIPTION
	"Table entry attribute for rewriteFragmentedHeaderIgnoredPptp"
	::={rewriteFragmentedHeaderIgnoredPptpLevelEntry 4}


rewriteTranslationFailedMaxCallsPptp	OBJECT IDENTIFIER ::={rewrite 183}

rewriteTranslationFailedMaxCallsPptpVal	OBJECT-TYPE
	SYNTAX	 Counter64
	MAX-ACCESS read-only
	STATUS current
	DESCRIPTION "Translation failed - max calls reached (PPTP)"

	::={rewriteTranslationFailedMaxCallsPptp 1}

rewriteTranslationFailedMaxCallsPptpMom	OBJECT-TYPE
	SYNTAX	 CounterBasedGauge64
	MAX-ACCESS read-only
	STATUS current
	DESCRIPTION "Translation failed - max calls reached (PPTP)"

	::={rewriteTranslationFailedMaxCallsPptp 2}

rewriteTranslationFailedMaxCallsPptpMax	OBJECT-TYPE
	SYNTAX	 CounterBasedGauge64
	MAX-ACCESS read-only
	STATUS current
	DESCRIPTION "Translation failed - max calls reached (PPTP)"

	::={rewriteTranslationFailedMaxCallsPptp 3}

rewriteTranslationFailedMaxCallsPptpLevelTable OBJECT-TYPE
	SYNTAX      SEQUENCE OF RewriteTranslationFailedMaxCallsPptpLevelEntry
	MAX-ACCESS  not-accessible
	STATUS      current
	DESCRIPTION
	"Table for rewriteTranslationFailedMaxCallsPptp"
	::={rewriteTranslationFailedMaxCallsPptp 4}

rewriteTranslationFailedMaxCallsPptpLevelEntry OBJECT-TYPE
	SYNTAX      RewriteTranslationFailedMaxCallsPptpLevelEntry
	MAX-ACCESS  not-accessible
	STATUS      current
	DESCRIPTION
	"Table entry for rewriteTranslationFailedMaxCallsPptp"
	INDEX { rewriteTranslationFailedMaxCallsPptpLevelName }
	::={rewriteTranslationFailedMaxCallsPptpLevelTable 1}

RewriteTranslationFailedMaxCallsPptpLevelEntry ::=
	SEQUENCE {
		rewriteTranslationFailedMaxCallsPptpLevelName	DisplayString,
		rewriteTranslationFailedMaxCallsPptpLevelVal	Counter64,
		rewriteTranslationFailedMaxCallsPptpLevelMom	CounterBasedGauge64,
		rewriteTranslationFailedMaxCallsPptpLevelMax	CounterBasedGauge64
	}

rewriteTranslationFailedMaxCallsPptpLevelName OBJECT-TYPE
	SYNTAX      DisplayString
	MAX-ACCESS  not-accessible
	STATUS      current
	DESCRIPTION
	"Table entry display string for rewriteTranslationFailedMaxCallsPptp"
	::={rewriteTranslationFailedMaxCallsPptpLevelEntry 1}

rewriteTranslationFailedMaxCallsPptpLevelVal OBJECT-TYPE
	SYNTAX	 Counter64
	MAX-ACCESS  read-only
	STATUS      current
	DESCRIPTION
	"Table entry attribute for rewriteTranslationFailedMaxCallsPptp"
	::={rewriteTranslationFailedMaxCallsPptpLevelEntry 2}

rewriteTranslationFailedMaxCallsPptpLevelMom OBJECT-TYPE
	SYNTAX	 CounterBasedGauge64
	MAX-ACCESS  read-only
	STATUS      current
	DESCRIPTION
	"Table entry attribute for rewriteTranslationFailedMaxCallsPptp"
	::={rewriteTranslationFailedMaxCallsPptpLevelEntry 3}

rewriteTranslationFailedMaxCallsPptpLevelMax OBJECT-TYPE
	SYNTAX	 CounterBasedGauge64
	MAX-ACCESS  read-only
	STATUS      current
	DESCRIPTION
	"Table entry attribute for rewriteTranslationFailedMaxCallsPptp"
	::={rewriteTranslationFailedMaxCallsPptpLevelEntry 4}


rewriteTranslationFailedMaxDataConnectionsFtp	OBJECT IDENTIFIER ::={rewrite 184}

rewriteTranslationFailedMaxDataConnectionsFtpVal	OBJECT-TYPE
	SYNTAX	 Counter64
	MAX-ACCESS read-only
	STATUS current
	DESCRIPTION "Translation failed - max data connections reached (FTP)"

	::={rewriteTranslationFailedMaxDataConnectionsFtp 1}

rewriteTranslationFailedMaxDataConnectionsFtpMom	OBJECT-TYPE
	SYNTAX	 CounterBasedGauge64
	MAX-ACCESS read-only
	STATUS current
	DESCRIPTION "Translation failed - max data connections reached (FTP)"

	::={rewriteTranslationFailedMaxDataConnectionsFtp 2}

rewriteTranslationFailedMaxDataConnectionsFtpMax	OBJECT-TYPE
	SYNTAX	 CounterBasedGauge64
	MAX-ACCESS read-only
	STATUS current
	DESCRIPTION "Translation failed - max data connections reached (FTP)"

	::={rewriteTranslationFailedMaxDataConnectionsFtp 3}

rewriteTranslationFailedMaxDataConnectionsFtpLevelTable OBJECT-TYPE
	SYNTAX      SEQUENCE OF RewriteTranslationFailedMaxDataConnectionsFtpLevelEntry
	MAX-ACCESS  not-accessible
	STATUS      current
	DESCRIPTION
	"Table for rewriteTranslationFailedMaxDataConnectionsFtp"
	::={rewriteTranslationFailedMaxDataConnectionsFtp 4}

rewriteTranslationFailedMaxDataConnectionsFtpLevelEntry OBJECT-TYPE
	SYNTAX      RewriteTranslationFailedMaxDataConnectionsFtpLevelEntry
	MAX-ACCESS  not-accessible
	STATUS      current
	DESCRIPTION
	"Table entry for rewriteTranslationFailedMaxDataConnectionsFtp"
	INDEX { rewriteTranslationFailedMaxDataConnectionsFtpLevelName }
	::={rewriteTranslationFailedMaxDataConnectionsFtpLevelTable 1}

RewriteTranslationFailedMaxDataConnectionsFtpLevelEntry ::=
	SEQUENCE {
		rewriteTranslationFailedMaxDataConnectionsFtpLevelName	DisplayString,
		rewriteTranslationFailedMaxDataConnectionsFtpLevelVal	Counter64,
		rewriteTranslationFailedMaxDataConnectionsFtpLevelMom	CounterBasedGauge64,
		rewriteTranslationFailedMaxDataConnectionsFtpLevelMax	CounterBasedGauge64
	}

rewriteTranslationFailedMaxDataConnectionsFtpLevelName OBJECT-TYPE
	SYNTAX      DisplayString
	MAX-ACCESS  not-accessible
	STATUS      current
	DESCRIPTION
	"Table entry display string for rewriteTranslationFailedMaxDataConnectionsFtp"
	::={rewriteTranslationFailedMaxDataConnectionsFtpLevelEntry 1}

rewriteTranslationFailedMaxDataConnectionsFtpLevelVal OBJECT-TYPE
	SYNTAX	 Counter64
	MAX-ACCESS  read-only
	STATUS      current
	DESCRIPTION
	"Table entry attribute for rewriteTranslationFailedMaxDataConnectionsFtp"
	::={rewriteTranslationFailedMaxDataConnectionsFtpLevelEntry 2}

rewriteTranslationFailedMaxDataConnectionsFtpLevelMom OBJECT-TYPE
	SYNTAX	 CounterBasedGauge64
	MAX-ACCESS  read-only
	STATUS      current
	DESCRIPTION
	"Table entry attribute for rewriteTranslationFailedMaxDataConnectionsFtp"
	::={rewriteTranslationFailedMaxDataConnectionsFtpLevelEntry 3}

rewriteTranslationFailedMaxDataConnectionsFtpLevelMax OBJECT-TYPE
	SYNTAX	 CounterBasedGauge64
	MAX-ACCESS  read-only
	STATUS      current
	DESCRIPTION
	"Table entry attribute for rewriteTranslationFailedMaxDataConnectionsFtp"
	::={rewriteTranslationFailedMaxDataConnectionsFtpLevelEntry 4}


rewriteTranslationFailedMaxStreamChannelsRtsp	OBJECT IDENTIFIER ::={rewrite 185}

rewriteTranslationFailedMaxStreamChannelsRtspVal	OBJECT-TYPE
	SYNTAX	 Counter64
	MAX-ACCESS read-only
	STATUS current
	DESCRIPTION "Translation failed - max stream channels reached (RTP)"

	::={rewriteTranslationFailedMaxStreamChannelsRtsp 1}

rewriteTranslationFailedMaxStreamChannelsRtspMom	OBJECT-TYPE
	SYNTAX	 CounterBasedGauge64
	MAX-ACCESS read-only
	STATUS current
	DESCRIPTION "Translation failed - max stream channels reached (RTP)"

	::={rewriteTranslationFailedMaxStreamChannelsRtsp 2}

rewriteTranslationFailedMaxStreamChannelsRtspMax	OBJECT-TYPE
	SYNTAX	 CounterBasedGauge64
	MAX-ACCESS read-only
	STATUS current
	DESCRIPTION "Translation failed - max stream channels reached (RTP)"

	::={rewriteTranslationFailedMaxStreamChannelsRtsp 3}

rewriteTranslationFailedMaxStreamChannelsRtspLevelTable OBJECT-TYPE
	SYNTAX      SEQUENCE OF RewriteTranslationFailedMaxStreamChannelsRtspLevelEntry
	MAX-ACCESS  not-accessible
	STATUS      current
	DESCRIPTION
	"Table for rewriteTranslationFailedMaxStreamChannelsRtsp"
	::={rewriteTranslationFailedMaxStreamChannelsRtsp 4}

rewriteTranslationFailedMaxStreamChannelsRtspLevelEntry OBJECT-TYPE
	SYNTAX      RewriteTranslationFailedMaxStreamChannelsRtspLevelEntry
	MAX-ACCESS  not-accessible
	STATUS      current
	DESCRIPTION
	"Table entry for rewriteTranslationFailedMaxStreamChannelsRtsp"
	INDEX { rewriteTranslationFailedMaxStreamChannelsRtspLevelName }
	::={rewriteTranslationFailedMaxStreamChannelsRtspLevelTable 1}

RewriteTranslationFailedMaxStreamChannelsRtspLevelEntry ::=
	SEQUENCE {
		rewriteTranslationFailedMaxStreamChannelsRtspLevelName	DisplayString,
		rewriteTranslationFailedMaxStreamChannelsRtspLevelVal	Counter64,
		rewriteTranslationFailedMaxStreamChannelsRtspLevelMom	CounterBasedGauge64,
		rewriteTranslationFailedMaxStreamChannelsRtspLevelMax	CounterBasedGauge64
	}

rewriteTranslationFailedMaxStreamChannelsRtspLevelName OBJECT-TYPE
	SYNTAX      DisplayString
	MAX-ACCESS  not-accessible
	STATUS      current
	DESCRIPTION
	"Table entry display string for rewriteTranslationFailedMaxStreamChannelsRtsp"
	::={rewriteTranslationFailedMaxStreamChannelsRtspLevelEntry 1}

rewriteTranslationFailedMaxStreamChannelsRtspLevelVal OBJECT-TYPE
	SYNTAX	 Counter64
	MAX-ACCESS  read-only
	STATUS      current
	DESCRIPTION
	"Table entry attribute for rewriteTranslationFailedMaxStreamChannelsRtsp"
	::={rewriteTranslationFailedMaxStreamChannelsRtspLevelEntry 2}

rewriteTranslationFailedMaxStreamChannelsRtspLevelMom OBJECT-TYPE
	SYNTAX	 CounterBasedGauge64
	MAX-ACCESS  read-only
	STATUS      current
	DESCRIPTION
	"Table entry attribute for rewriteTranslationFailedMaxStreamChannelsRtsp"
	::={rewriteTranslationFailedMaxStreamChannelsRtspLevelEntry 3}

rewriteTranslationFailedMaxStreamChannelsRtspLevelMax OBJECT-TYPE
	SYNTAX	 CounterBasedGauge64
	MAX-ACCESS  read-only
	STATUS      current
	DESCRIPTION
	"Table entry attribute for rewriteTranslationFailedMaxStreamChannelsRtsp"
	::={rewriteTranslationFailedMaxStreamChannelsRtspLevelEntry 4}


rewriteSrcIpCount	OBJECT IDENTIFIER ::={rewrite 200}

rewriteSrcIpCountVal	OBJECT-TYPE
	SYNTAX	 CounterBasedGauge64
	MAX-ACCESS read-only
	STATUS current
	DESCRIPTION "Src IP-address count"

	::={rewriteSrcIpCount 1}

rewriteSrcIpCountMax	OBJECT-TYPE
	SYNTAX	 CounterBasedGauge64
	MAX-ACCESS read-only
	STATUS current
	DESCRIPTION "Src IP-address count"

	::={rewriteSrcIpCount 3}

rewriteSrcIpCountLevelTable OBJECT-TYPE
	SYNTAX      SEQUENCE OF RewriteSrcIpCountLevelEntry
	MAX-ACCESS  not-accessible
	STATUS      current
	DESCRIPTION
	"Table for rewriteSrcIpCount"
	::={rewriteSrcIpCount 4}

rewriteSrcIpCountLevelEntry OBJECT-TYPE
	SYNTAX      RewriteSrcIpCountLevelEntry
	MAX-ACCESS  not-accessible
	STATUS      current
	DESCRIPTION
	"Table entry for rewriteSrcIpCount"
	INDEX { rewriteSrcIpCountLevelName }
	::={rewriteSrcIpCountLevelTable 1}

RewriteSrcIpCountLevelEntry ::=
	SEQUENCE {
		rewriteSrcIpCountLevelName	DisplayString,
		rewriteSrcIpCountLevelVal	CounterBasedGauge64,
		rewriteSrcIpCountLevelMax	CounterBasedGauge64
	}

rewriteSrcIpCountLevelName OBJECT-TYPE
	SYNTAX      DisplayString
	MAX-ACCESS  not-accessible
	STATUS      current
	DESCRIPTION
	"Table entry display string for rewriteSrcIpCount"
	::={rewriteSrcIpCountLevelEntry 1}

rewriteSrcIpCountLevelVal OBJECT-TYPE
	SYNTAX	 CounterBasedGauge64
	MAX-ACCESS  read-only
	STATUS      current
	DESCRIPTION
	"Table entry attribute for rewriteSrcIpCount"
	::={rewriteSrcIpCountLevelEntry 2}

rewriteSrcIpCountLevelMax OBJECT-TYPE
	SYNTAX	 CounterBasedGauge64
	MAX-ACCESS  read-only
	STATUS      current
	DESCRIPTION
	"Table entry attribute for rewriteSrcIpCount"
	::={rewriteSrcIpCountLevelEntry 4}


rewriteSrcIpCreationFailures	OBJECT IDENTIFIER ::={rewrite 201}

rewriteSrcIpCreationFailuresVal	OBJECT-TYPE
	SYNTAX	 Counter64
	MAX-ACCESS read-only
	STATUS current
	DESCRIPTION "Src IP-address creation failures"

	::={rewriteSrcIpCreationFailures 1}

rewriteSrcIpCreationFailuresMom	OBJECT-TYPE
	SYNTAX	 CounterBasedGauge64
	MAX-ACCESS read-only
	STATUS current
	DESCRIPTION "Src IP-address creation failures"

	::={rewriteSrcIpCreationFailures 2}

rewriteSrcIpCreationFailuresMax	OBJECT-TYPE
	SYNTAX	 CounterBasedGauge64
	MAX-ACCESS read-only
	STATUS current
	DESCRIPTION "Src IP-address creation failures"

	::={rewriteSrcIpCreationFailures 3}

rewriteSrcIpCreationFailuresLevelTable OBJECT-TYPE
	SYNTAX      SEQUENCE OF RewriteSrcIpCreationFailuresLevelEntry
	MAX-ACCESS  not-accessible
	STATUS      current
	DESCRIPTION
	"Table for rewriteSrcIpCreationFailures"
	::={rewriteSrcIpCreationFailures 4}

rewriteSrcIpCreationFailuresLevelEntry OBJECT-TYPE
	SYNTAX      RewriteSrcIpCreationFailuresLevelEntry
	MAX-ACCESS  not-accessible
	STATUS      current
	DESCRIPTION
	"Table entry for rewriteSrcIpCreationFailures"
	INDEX { rewriteSrcIpCreationFailuresLevelName }
	::={rewriteSrcIpCreationFailuresLevelTable 1}

RewriteSrcIpCreationFailuresLevelEntry ::=
	SEQUENCE {
		rewriteSrcIpCreationFailuresLevelName	DisplayString,
		rewriteSrcIpCreationFailuresLevelVal	Counter64,
		rewriteSrcIpCreationFailuresLevelMom	CounterBasedGauge64,
		rewriteSrcIpCreationFailuresLevelMax	CounterBasedGauge64
	}

rewriteSrcIpCreationFailuresLevelName OBJECT-TYPE
	SYNTAX      DisplayString
	MAX-ACCESS  not-accessible
	STATUS      current
	DESCRIPTION
	"Table entry display string for rewriteSrcIpCreationFailures"
	::={rewriteSrcIpCreationFailuresLevelEntry 1}

rewriteSrcIpCreationFailuresLevelVal OBJECT-TYPE
	SYNTAX	 Counter64
	MAX-ACCESS  read-only
	STATUS      current
	DESCRIPTION
	"Table entry attribute for rewriteSrcIpCreationFailures"
	::={rewriteSrcIpCreationFailuresLevelEntry 2}

rewriteSrcIpCreationFailuresLevelMom OBJECT-TYPE
	SYNTAX	 CounterBasedGauge64
	MAX-ACCESS  read-only
	STATUS      current
	DESCRIPTION
	"Table entry attribute for rewriteSrcIpCreationFailures"
	::={rewriteSrcIpCreationFailuresLevelEntry 3}

rewriteSrcIpCreationFailuresLevelMax OBJECT-TYPE
	SYNTAX	 CounterBasedGauge64
	MAX-ACCESS  read-only
	STATUS      current
	DESCRIPTION
	"Table entry attribute for rewriteSrcIpCreationFailures"
	::={rewriteSrcIpCreationFailuresLevelEntry 4}


rewriteSrcIpCreationFailuresResources	OBJECT IDENTIFIER ::={rewrite 202}

rewriteSrcIpCreationFailuresResourcesVal	OBJECT-TYPE
	SYNTAX	 Counter64
	MAX-ACCESS read-only
	STATUS current
	DESCRIPTION "Src IP-address creation failures (resources)"

	::={rewriteSrcIpCreationFailuresResources 1}

rewriteSrcIpCreationFailuresResourcesMom	OBJECT-TYPE
	SYNTAX	 CounterBasedGauge64
	MAX-ACCESS read-only
	STATUS current
	DESCRIPTION "Src IP-address creation failures (resources)"

	::={rewriteSrcIpCreationFailuresResources 2}

rewriteSrcIpCreationFailuresResourcesMax	OBJECT-TYPE
	SYNTAX	 CounterBasedGauge64
	MAX-ACCESS read-only
	STATUS current
	DESCRIPTION "Src IP-address creation failures (resources)"

	::={rewriteSrcIpCreationFailuresResources 3}

rewriteSrcIpCreationFailuresResourcesLevelTable OBJECT-TYPE
	SYNTAX      SEQUENCE OF RewriteSrcIpCreationFailuresResourcesLevelEntry
	MAX-ACCESS  not-accessible
	STATUS      current
	DESCRIPTION
	"Table for rewriteSrcIpCreationFailuresResources"
	::={rewriteSrcIpCreationFailuresResources 4}

rewriteSrcIpCreationFailuresResourcesLevelEntry OBJECT-TYPE
	SYNTAX      RewriteSrcIpCreationFailuresResourcesLevelEntry
	MAX-ACCESS  not-accessible
	STATUS      current
	DESCRIPTION
	"Table entry for rewriteSrcIpCreationFailuresResources"
	INDEX { rewriteSrcIpCreationFailuresResourcesLevelName }
	::={rewriteSrcIpCreationFailuresResourcesLevelTable 1}

RewriteSrcIpCreationFailuresResourcesLevelEntry ::=
	SEQUENCE {
		rewriteSrcIpCreationFailuresResourcesLevelName	DisplayString,
		rewriteSrcIpCreationFailuresResourcesLevelVal	Counter64,
		rewriteSrcIpCreationFailuresResourcesLevelMom	CounterBasedGauge64,
		rewriteSrcIpCreationFailuresResourcesLevelMax	CounterBasedGauge64
	}

rewriteSrcIpCreationFailuresResourcesLevelName OBJECT-TYPE
	SYNTAX      DisplayString
	MAX-ACCESS  not-accessible
	STATUS      current
	DESCRIPTION
	"Table entry display string for rewriteSrcIpCreationFailuresResources"
	::={rewriteSrcIpCreationFailuresResourcesLevelEntry 1}

rewriteSrcIpCreationFailuresResourcesLevelVal OBJECT-TYPE
	SYNTAX	 Counter64
	MAX-ACCESS  read-only
	STATUS      current
	DESCRIPTION
	"Table entry attribute for rewriteSrcIpCreationFailuresResources"
	::={rewriteSrcIpCreationFailuresResourcesLevelEntry 2}

rewriteSrcIpCreationFailuresResourcesLevelMom OBJECT-TYPE
	SYNTAX	 CounterBasedGauge64
	MAX-ACCESS  read-only
	STATUS      current
	DESCRIPTION
	"Table entry attribute for rewriteSrcIpCreationFailuresResources"
	::={rewriteSrcIpCreationFailuresResourcesLevelEntry 3}

rewriteSrcIpCreationFailuresResourcesLevelMax OBJECT-TYPE
	SYNTAX	 CounterBasedGauge64
	MAX-ACCESS  read-only
	STATUS      current
	DESCRIPTION
	"Table entry attribute for rewriteSrcIpCreationFailuresResources"
	::={rewriteSrcIpCreationFailuresResourcesLevelEntry 4}


rewriteDeterministicSrcIpTooFewInPool	OBJECT IDENTIFIER ::={rewrite 203}

rewriteDeterministicSrcIpTooFewInPoolVal	OBJECT-TYPE
	SYNTAX	 Counter64
	MAX-ACCESS read-only
	STATUS current
	DESCRIPTION "Too few src IP-addresses in loading pool."

	::={rewriteDeterministicSrcIpTooFewInPool 1}

rewriteDeterministicSrcIpTooFewInPoolMom	OBJECT-TYPE
	SYNTAX	 CounterBasedGauge64
	MAX-ACCESS read-only
	STATUS current
	DESCRIPTION "Too few src IP-addresses in loading pool."

	::={rewriteDeterministicSrcIpTooFewInPool 2}

rewriteDeterministicSrcIpTooFewInPoolMax	OBJECT-TYPE
	SYNTAX	 CounterBasedGauge64
	MAX-ACCESS read-only
	STATUS current
	DESCRIPTION "Too few src IP-addresses in loading pool."

	::={rewriteDeterministicSrcIpTooFewInPool 3}

rewriteDeterministicSrcIpTooFewInPoolLevelTable OBJECT-TYPE
	SYNTAX      SEQUENCE OF RewriteDeterministicSrcIpTooFewInPoolLevelEntry
	MAX-ACCESS  not-accessible
	STATUS      current
	DESCRIPTION
	"Table for rewriteDeterministicSrcIpTooFewInPool"
	::={rewriteDeterministicSrcIpTooFewInPool 4}

rewriteDeterministicSrcIpTooFewInPoolLevelEntry OBJECT-TYPE
	SYNTAX      RewriteDeterministicSrcIpTooFewInPoolLevelEntry
	MAX-ACCESS  not-accessible
	STATUS      current
	DESCRIPTION
	"Table entry for rewriteDeterministicSrcIpTooFewInPool"
	INDEX { rewriteDeterministicSrcIpTooFewInPoolLevelName }
	::={rewriteDeterministicSrcIpTooFewInPoolLevelTable 1}

RewriteDeterministicSrcIpTooFewInPoolLevelEntry ::=
	SEQUENCE {
		rewriteDeterministicSrcIpTooFewInPoolLevelName	DisplayString,
		rewriteDeterministicSrcIpTooFewInPoolLevelVal	Counter64,
		rewriteDeterministicSrcIpTooFewInPoolLevelMom	CounterBasedGauge64,
		rewriteDeterministicSrcIpTooFewInPoolLevelMax	CounterBasedGauge64
	}

rewriteDeterministicSrcIpTooFewInPoolLevelName OBJECT-TYPE
	SYNTAX      DisplayString
	MAX-ACCESS  not-accessible
	STATUS      current
	DESCRIPTION
	"Table entry display string for rewriteDeterministicSrcIpTooFewInPool"
	::={rewriteDeterministicSrcIpTooFewInPoolLevelEntry 1}

rewriteDeterministicSrcIpTooFewInPoolLevelVal OBJECT-TYPE
	SYNTAX	 Counter64
	MAX-ACCESS  read-only
	STATUS      current
	DESCRIPTION
	"Table entry attribute for rewriteDeterministicSrcIpTooFewInPool"
	::={rewriteDeterministicSrcIpTooFewInPoolLevelEntry 2}

rewriteDeterministicSrcIpTooFewInPoolLevelMom OBJECT-TYPE
	SYNTAX	 CounterBasedGauge64
	MAX-ACCESS  read-only
	STATUS      current
	DESCRIPTION
	"Table entry attribute for rewriteDeterministicSrcIpTooFewInPool"
	::={rewriteDeterministicSrcIpTooFewInPoolLevelEntry 3}

rewriteDeterministicSrcIpTooFewInPoolLevelMax OBJECT-TYPE
	SYNTAX	 CounterBasedGauge64
	MAX-ACCESS  read-only
	STATUS      current
	DESCRIPTION
	"Table entry attribute for rewriteDeterministicSrcIpTooFewInPool"
	::={rewriteDeterministicSrcIpTooFewInPoolLevelEntry 4}


rewriteRedirectHeaderCount	OBJECT IDENTIFIER ::={rewrite 204}

rewriteRedirectHeaderCountVal	OBJECT-TYPE
	SYNTAX	 CounterBasedGauge64
	MAX-ACCESS read-only
	STATUS current
	DESCRIPTION "Number of redirect headers created"

	::={rewriteRedirectHeaderCount 1}

rewriteRedirectHeaderCountMax	OBJECT-TYPE
	SYNTAX	 CounterBasedGauge64
	MAX-ACCESS read-only
	STATUS current
	DESCRIPTION "Number of redirect headers created"

	::={rewriteRedirectHeaderCount 3}

rewriteRedirectHeaderCountLevelTable OBJECT-TYPE
	SYNTAX      SEQUENCE OF RewriteRedirectHeaderCountLevelEntry
	MAX-ACCESS  not-accessible
	STATUS      current
	DESCRIPTION
	"Table for rewriteRedirectHeaderCount"
	::={rewriteRedirectHeaderCount 4}

rewriteRedirectHeaderCountLevelEntry OBJECT-TYPE
	SYNTAX      RewriteRedirectHeaderCountLevelEntry
	MAX-ACCESS  not-accessible
	STATUS      current
	DESCRIPTION
	"Table entry for rewriteRedirectHeaderCount"
	INDEX { rewriteRedirectHeaderCountLevelName }
	::={rewriteRedirectHeaderCountLevelTable 1}

RewriteRedirectHeaderCountLevelEntry ::=
	SEQUENCE {
		rewriteRedirectHeaderCountLevelName	DisplayString,
		rewriteRedirectHeaderCountLevelVal	CounterBasedGauge64,
		rewriteRedirectHeaderCountLevelMax	CounterBasedGauge64
	}

rewriteRedirectHeaderCountLevelName OBJECT-TYPE
	SYNTAX      DisplayString
	MAX-ACCESS  not-accessible
	STATUS      current
	DESCRIPTION
	"Table entry display string for rewriteRedirectHeaderCount"
	::={rewriteRedirectHeaderCountLevelEntry 1}

rewriteRedirectHeaderCountLevelVal OBJECT-TYPE
	SYNTAX	 CounterBasedGauge64
	MAX-ACCESS  read-only
	STATUS      current
	DESCRIPTION
	"Table entry attribute for rewriteRedirectHeaderCount"
	::={rewriteRedirectHeaderCountLevelEntry 2}

rewriteRedirectHeaderCountLevelMax OBJECT-TYPE
	SYNTAX	 CounterBasedGauge64
	MAX-ACCESS  read-only
	STATUS      current
	DESCRIPTION
	"Table entry attribute for rewriteRedirectHeaderCount"
	::={rewriteRedirectHeaderCountLevelEntry 4}


rewriteRedirectHeaderAvailable	OBJECT IDENTIFIER ::={rewrite 205}

rewriteRedirectHeaderAvailableVal	OBJECT-TYPE
	SYNTAX	 CounterBasedGauge64
	MAX-ACCESS read-only
	STATUS current
	DESCRIPTION "Number of redirect headers available for use"

	::={rewriteRedirectHeaderAvailable 1}

rewriteRedirectHeaderAvailableMax	OBJECT-TYPE
	SYNTAX	 CounterBasedGauge64
	MAX-ACCESS read-only
	STATUS current
	DESCRIPTION "Number of redirect headers available for use"

	::={rewriteRedirectHeaderAvailable 3}

rewriteRedirectHeaderAvailableLevelTable OBJECT-TYPE
	SYNTAX      SEQUENCE OF RewriteRedirectHeaderAvailableLevelEntry
	MAX-ACCESS  not-accessible
	STATUS      current
	DESCRIPTION
	"Table for rewriteRedirectHeaderAvailable"
	::={rewriteRedirectHeaderAvailable 4}

rewriteRedirectHeaderAvailableLevelEntry OBJECT-TYPE
	SYNTAX      RewriteRedirectHeaderAvailableLevelEntry
	MAX-ACCESS  not-accessible
	STATUS      current
	DESCRIPTION
	"Table entry for rewriteRedirectHeaderAvailable"
	INDEX { rewriteRedirectHeaderAvailableLevelName }
	::={rewriteRedirectHeaderAvailableLevelTable 1}

RewriteRedirectHeaderAvailableLevelEntry ::=
	SEQUENCE {
		rewriteRedirectHeaderAvailableLevelName	DisplayString,
		rewriteRedirectHeaderAvailableLevelVal	CounterBasedGauge64,
		rewriteRedirectHeaderAvailableLevelMax	CounterBasedGauge64
	}

rewriteRedirectHeaderAvailableLevelName OBJECT-TYPE
	SYNTAX      DisplayString
	MAX-ACCESS  not-accessible
	STATUS      current
	DESCRIPTION
	"Table entry display string for rewriteRedirectHeaderAvailable"
	::={rewriteRedirectHeaderAvailableLevelEntry 1}

rewriteRedirectHeaderAvailableLevelVal OBJECT-TYPE
	SYNTAX	 CounterBasedGauge64
	MAX-ACCESS  read-only
	STATUS      current
	DESCRIPTION
	"Table entry attribute for rewriteRedirectHeaderAvailable"
	::={rewriteRedirectHeaderAvailableLevelEntry 2}

rewriteRedirectHeaderAvailableLevelMax OBJECT-TYPE
	SYNTAX	 CounterBasedGauge64
	MAX-ACCESS  read-only
	STATUS      current
	DESCRIPTION
	"Table entry attribute for rewriteRedirectHeaderAvailable"
	::={rewriteRedirectHeaderAvailableLevelEntry 4}


rewriteRedirectHeaderInUse	OBJECT IDENTIFIER ::={rewrite 206}

rewriteRedirectHeaderInUseVal	OBJECT-TYPE
	SYNTAX	 CounterBasedGauge64
	MAX-ACCESS read-only
	STATUS current
	DESCRIPTION "Number of redirect headers currently in use"

	::={rewriteRedirectHeaderInUse 1}

rewriteRedirectHeaderInUseMax	OBJECT-TYPE
	SYNTAX	 CounterBasedGauge64
	MAX-ACCESS read-only
	STATUS current
	DESCRIPTION "Number of redirect headers currently in use"

	::={rewriteRedirectHeaderInUse 3}

rewriteRedirectHeaderInUseLevelTable OBJECT-TYPE
	SYNTAX      SEQUENCE OF RewriteRedirectHeaderInUseLevelEntry
	MAX-ACCESS  not-accessible
	STATUS      current
	DESCRIPTION
	"Table for rewriteRedirectHeaderInUse"
	::={rewriteRedirectHeaderInUse 4}

rewriteRedirectHeaderInUseLevelEntry OBJECT-TYPE
	SYNTAX      RewriteRedirectHeaderInUseLevelEntry
	MAX-ACCESS  not-accessible
	STATUS      current
	DESCRIPTION
	"Table entry for rewriteRedirectHeaderInUse"
	INDEX { rewriteRedirectHeaderInUseLevelName }
	::={rewriteRedirectHeaderInUseLevelTable 1}

RewriteRedirectHeaderInUseLevelEntry ::=
	SEQUENCE {
		rewriteRedirectHeaderInUseLevelName	DisplayString,
		rewriteRedirectHeaderInUseLevelVal	CounterBasedGauge64,
		rewriteRedirectHeaderInUseLevelMax	CounterBasedGauge64
	}

rewriteRedirectHeaderInUseLevelName OBJECT-TYPE
	SYNTAX      DisplayString
	MAX-ACCESS  not-accessible
	STATUS      current
	DESCRIPTION
	"Table entry display string for rewriteRedirectHeaderInUse"
	::={rewriteRedirectHeaderInUseLevelEntry 1}

rewriteRedirectHeaderInUseLevelVal OBJECT-TYPE
	SYNTAX	 CounterBasedGauge64
	MAX-ACCESS  read-only
	STATUS      current
	DESCRIPTION
	"Table entry attribute for rewriteRedirectHeaderInUse"
	::={rewriteRedirectHeaderInUseLevelEntry 2}

rewriteRedirectHeaderInUseLevelMax OBJECT-TYPE
	SYNTAX	 CounterBasedGauge64
	MAX-ACCESS  read-only
	STATUS      current
	DESCRIPTION
	"Table entry attribute for rewriteRedirectHeaderInUse"
	::={rewriteRedirectHeaderInUseLevelEntry 4}


rewriteMappingsTotal	OBJECT IDENTIFIER ::={rewrite 207}

rewriteMappingsTotalVal	OBJECT-TYPE
	SYNTAX	 CounterBasedGauge64
	MAX-ACCESS read-only
	STATUS current
	DESCRIPTION "Total number of mappings"

	::={rewriteMappingsTotal 1}

rewriteMappingsTotalMax	OBJECT-TYPE
	SYNTAX	 CounterBasedGauge64
	MAX-ACCESS read-only
	STATUS current
	DESCRIPTION "Total number of mappings"

	::={rewriteMappingsTotal 3}

rewriteMappingsTotalLevelTable OBJECT-TYPE
	SYNTAX      SEQUENCE OF RewriteMappingsTotalLevelEntry
	MAX-ACCESS  not-accessible
	STATUS      current
	DESCRIPTION
	"Table for rewriteMappingsTotal"
	::={rewriteMappingsTotal 4}

rewriteMappingsTotalLevelEntry OBJECT-TYPE
	SYNTAX      RewriteMappingsTotalLevelEntry
	MAX-ACCESS  not-accessible
	STATUS      current
	DESCRIPTION
	"Table entry for rewriteMappingsTotal"
	INDEX { rewriteMappingsTotalLevelName }
	::={rewriteMappingsTotalLevelTable 1}

RewriteMappingsTotalLevelEntry ::=
	SEQUENCE {
		rewriteMappingsTotalLevelName	DisplayString,
		rewriteMappingsTotalLevelVal	CounterBasedGauge64,
		rewriteMappingsTotalLevelMax	CounterBasedGauge64
	}

rewriteMappingsTotalLevelName OBJECT-TYPE
	SYNTAX      DisplayString
	MAX-ACCESS  not-accessible
	STATUS      current
	DESCRIPTION
	"Table entry display string for rewriteMappingsTotal"
	::={rewriteMappingsTotalLevelEntry 1}

rewriteMappingsTotalLevelVal OBJECT-TYPE
	SYNTAX	 CounterBasedGauge64
	MAX-ACCESS  read-only
	STATUS      current
	DESCRIPTION
	"Table entry attribute for rewriteMappingsTotal"
	::={rewriteMappingsTotalLevelEntry 2}

rewriteMappingsTotalLevelMax OBJECT-TYPE
	SYNTAX	 CounterBasedGauge64
	MAX-ACCESS  read-only
	STATUS      current
	DESCRIPTION
	"Table entry attribute for rewriteMappingsTotal"
	::={rewriteMappingsTotalLevelEntry 4}


rewriteMappingsUsed	OBJECT IDENTIFIER ::={rewrite 208}

rewriteMappingsUsedVal	OBJECT-TYPE
	SYNTAX	 CounterBasedGauge64
	MAX-ACCESS read-only
	STATUS current
	DESCRIPTION "Number of mappings used"

	::={rewriteMappingsUsed 1}

rewriteMappingsUsedMax	OBJECT-TYPE
	SYNTAX	 CounterBasedGauge64
	MAX-ACCESS read-only
	STATUS current
	DESCRIPTION "Number of mappings used"

	::={rewriteMappingsUsed 3}

rewriteMappingsUsedLevelTable OBJECT-TYPE
	SYNTAX      SEQUENCE OF RewriteMappingsUsedLevelEntry
	MAX-ACCESS  not-accessible
	STATUS      current
	DESCRIPTION
	"Table for rewriteMappingsUsed"
	::={rewriteMappingsUsed 4}

rewriteMappingsUsedLevelEntry OBJECT-TYPE
	SYNTAX      RewriteMappingsUsedLevelEntry
	MAX-ACCESS  not-accessible
	STATUS      current
	DESCRIPTION
	"Table entry for rewriteMappingsUsed"
	INDEX { rewriteMappingsUsedLevelName }
	::={rewriteMappingsUsedLevelTable 1}

RewriteMappingsUsedLevelEntry ::=
	SEQUENCE {
		rewriteMappingsUsedLevelName	DisplayString,
		rewriteMappingsUsedLevelVal	CounterBasedGauge64,
		rewriteMappingsUsedLevelMax	CounterBasedGauge64
	}

rewriteMappingsUsedLevelName OBJECT-TYPE
	SYNTAX      DisplayString
	MAX-ACCESS  not-accessible
	STATUS      current
	DESCRIPTION
	"Table entry display string for rewriteMappingsUsed"
	::={rewriteMappingsUsedLevelEntry 1}

rewriteMappingsUsedLevelVal OBJECT-TYPE
	SYNTAX	 CounterBasedGauge64
	MAX-ACCESS  read-only
	STATUS      current
	DESCRIPTION
	"Table entry attribute for rewriteMappingsUsed"
	::={rewriteMappingsUsedLevelEntry 2}

rewriteMappingsUsedLevelMax OBJECT-TYPE
	SYNTAX	 CounterBasedGauge64
	MAX-ACCESS  read-only
	STATUS      current
	DESCRIPTION
	"Table entry attribute for rewriteMappingsUsed"
	::={rewriteMappingsUsedLevelEntry 4}


nat	OBJECT IDENTIFIER ::={sysdiag 142}

natNumPortBlocksMaxLow	OBJECT IDENTIFIER ::={nat 1}

natNumPortBlocksMaxLowVal	OBJECT-TYPE
	SYNTAX	 CounterBasedGauge64
	MAX-ACCESS read-only
	STATUS current
	DESCRIPTION "Number of port blocks (low)"

	::={natNumPortBlocksMaxLow 1}

natNumPortBlocksMaxLowMax	OBJECT-TYPE
	SYNTAX	 CounterBasedGauge64
	MAX-ACCESS read-only
	STATUS current
	DESCRIPTION "Number of port blocks (low)"

	::={natNumPortBlocksMaxLow 3}

natNumPortBlocksMaxLowLevelTable OBJECT-TYPE
	SYNTAX      SEQUENCE OF NatNumPortBlocksMaxLowLevelEntry
	MAX-ACCESS  not-accessible
	STATUS      current
	DESCRIPTION
	"Table for natNumPortBlocksMaxLow"
	::={natNumPortBlocksMaxLow 4}

natNumPortBlocksMaxLowLevelEntry OBJECT-TYPE
	SYNTAX      NatNumPortBlocksMaxLowLevelEntry
	MAX-ACCESS  not-accessible
	STATUS      current
	DESCRIPTION
	"Table entry for natNumPortBlocksMaxLow"
	INDEX { natNumPortBlocksMaxLowLevelName }
	::={natNumPortBlocksMaxLowLevelTable 1}

NatNumPortBlocksMaxLowLevelEntry ::=
	SEQUENCE {
		natNumPortBlocksMaxLowLevelName	DisplayString,
		natNumPortBlocksMaxLowLevelVal	CounterBasedGauge64,
		natNumPortBlocksMaxLowLevelMax	CounterBasedGauge64
	}

natNumPortBlocksMaxLowLevelName OBJECT-TYPE
	SYNTAX      DisplayString
	MAX-ACCESS  not-accessible
	STATUS      current
	DESCRIPTION
	"Table entry display string for natNumPortBlocksMaxLow"
	::={natNumPortBlocksMaxLowLevelEntry 1}

natNumPortBlocksMaxLowLevelVal OBJECT-TYPE
	SYNTAX	 CounterBasedGauge64
	MAX-ACCESS  read-only
	STATUS      current
	DESCRIPTION
	"Table entry attribute for natNumPortBlocksMaxLow"
	::={natNumPortBlocksMaxLowLevelEntry 2}

natNumPortBlocksMaxLowLevelMax OBJECT-TYPE
	SYNTAX	 CounterBasedGauge64
	MAX-ACCESS  read-only
	STATUS      current
	DESCRIPTION
	"Table entry attribute for natNumPortBlocksMaxLow"
	::={natNumPortBlocksMaxLowLevelEntry 4}


natNumPortBlocksFreeLow	OBJECT IDENTIFIER ::={nat 2}

natNumPortBlocksFreeLowVal	OBJECT-TYPE
	SYNTAX	 CounterBasedGauge64
	MAX-ACCESS read-only
	STATUS obsolete
	DESCRIPTION "Current number of free port blocks (low)"

	::={natNumPortBlocksFreeLow 1}

natNumPortBlocksFreeLowMax	OBJECT-TYPE
	SYNTAX	 CounterBasedGauge64
	MAX-ACCESS read-only
	STATUS obsolete
	DESCRIPTION "Current number of free port blocks (low)"

	::={natNumPortBlocksFreeLow 3}

natNumPortBlocksFreeLowLevelTable OBJECT-TYPE
	SYNTAX      SEQUENCE OF NatNumPortBlocksFreeLowLevelEntry
	MAX-ACCESS  not-accessible
	STATUS      current
	DESCRIPTION
	"Table for natNumPortBlocksFreeLow"
	::={natNumPortBlocksFreeLow 4}

natNumPortBlocksFreeLowLevelEntry OBJECT-TYPE
	SYNTAX      NatNumPortBlocksFreeLowLevelEntry
	MAX-ACCESS  not-accessible
	STATUS      current
	DESCRIPTION
	"Table entry for natNumPortBlocksFreeLow"
	INDEX { natNumPortBlocksFreeLowLevelName }
	::={natNumPortBlocksFreeLowLevelTable 1}

NatNumPortBlocksFreeLowLevelEntry ::=
	SEQUENCE {
		natNumPortBlocksFreeLowLevelName	DisplayString,
		natNumPortBlocksFreeLowLevelVal	CounterBasedGauge64,
		natNumPortBlocksFreeLowLevelMax	CounterBasedGauge64
	}

natNumPortBlocksFreeLowLevelName OBJECT-TYPE
	SYNTAX      DisplayString
	MAX-ACCESS  not-accessible
	STATUS      current
	DESCRIPTION
	"Table entry display string for natNumPortBlocksFreeLow"
	::={natNumPortBlocksFreeLowLevelEntry 1}

natNumPortBlocksFreeLowLevelVal OBJECT-TYPE
	SYNTAX	 CounterBasedGauge64
	MAX-ACCESS  read-only
	STATUS      current
	DESCRIPTION
	"Table entry attribute for natNumPortBlocksFreeLow"
	::={natNumPortBlocksFreeLowLevelEntry 2}

natNumPortBlocksFreeLowLevelMax OBJECT-TYPE
	SYNTAX	 CounterBasedGauge64
	MAX-ACCESS  read-only
	STATUS      current
	DESCRIPTION
	"Table entry attribute for natNumPortBlocksFreeLow"
	::={natNumPortBlocksFreeLowLevelEntry 4}


natNumPortBlocksMaxHigh	OBJECT IDENTIFIER ::={nat 3}

natNumPortBlocksMaxHighVal	OBJECT-TYPE
	SYNTAX	 CounterBasedGauge64
	MAX-ACCESS read-only
	STATUS current
	DESCRIPTION "Number of port blocks (high)"

	::={natNumPortBlocksMaxHigh 1}

natNumPortBlocksMaxHighMax	OBJECT-TYPE
	SYNTAX	 CounterBasedGauge64
	MAX-ACCESS read-only
	STATUS current
	DESCRIPTION "Number of port blocks (high)"

	::={natNumPortBlocksMaxHigh 3}

natNumPortBlocksMaxHighLevelTable OBJECT-TYPE
	SYNTAX      SEQUENCE OF NatNumPortBlocksMaxHighLevelEntry
	MAX-ACCESS  not-accessible
	STATUS      current
	DESCRIPTION
	"Table for natNumPortBlocksMaxHigh"
	::={natNumPortBlocksMaxHigh 4}

natNumPortBlocksMaxHighLevelEntry OBJECT-TYPE
	SYNTAX      NatNumPortBlocksMaxHighLevelEntry
	MAX-ACCESS  not-accessible
	STATUS      current
	DESCRIPTION
	"Table entry for natNumPortBlocksMaxHigh"
	INDEX { natNumPortBlocksMaxHighLevelName }
	::={natNumPortBlocksMaxHighLevelTable 1}

NatNumPortBlocksMaxHighLevelEntry ::=
	SEQUENCE {
		natNumPortBlocksMaxHighLevelName	DisplayString,
		natNumPortBlocksMaxHighLevelVal	CounterBasedGauge64,
		natNumPortBlocksMaxHighLevelMax	CounterBasedGauge64
	}

natNumPortBlocksMaxHighLevelName OBJECT-TYPE
	SYNTAX      DisplayString
	MAX-ACCESS  not-accessible
	STATUS      current
	DESCRIPTION
	"Table entry display string for natNumPortBlocksMaxHigh"
	::={natNumPortBlocksMaxHighLevelEntry 1}

natNumPortBlocksMaxHighLevelVal OBJECT-TYPE
	SYNTAX	 CounterBasedGauge64
	MAX-ACCESS  read-only
	STATUS      current
	DESCRIPTION
	"Table entry attribute for natNumPortBlocksMaxHigh"
	::={natNumPortBlocksMaxHighLevelEntry 2}

natNumPortBlocksMaxHighLevelMax OBJECT-TYPE
	SYNTAX	 CounterBasedGauge64
	MAX-ACCESS  read-only
	STATUS      current
	DESCRIPTION
	"Table entry attribute for natNumPortBlocksMaxHigh"
	::={natNumPortBlocksMaxHighLevelEntry 4}


natNumPortBlocksFreeHigh	OBJECT IDENTIFIER ::={nat 4}

natNumPortBlocksFreeHighVal	OBJECT-TYPE
	SYNTAX	 CounterBasedGauge64
	MAX-ACCESS read-only
	STATUS obsolete
	DESCRIPTION "Current number of free port blocks (high)"

	::={natNumPortBlocksFreeHigh 1}

natNumPortBlocksFreeHighMax	OBJECT-TYPE
	SYNTAX	 CounterBasedGauge64
	MAX-ACCESS read-only
	STATUS obsolete
	DESCRIPTION "Current number of free port blocks (high)"

	::={natNumPortBlocksFreeHigh 3}

natNumPortBlocksFreeHighLevelTable OBJECT-TYPE
	SYNTAX      SEQUENCE OF NatNumPortBlocksFreeHighLevelEntry
	MAX-ACCESS  not-accessible
	STATUS      current
	DESCRIPTION
	"Table for natNumPortBlocksFreeHigh"
	::={natNumPortBlocksFreeHigh 4}

natNumPortBlocksFreeHighLevelEntry OBJECT-TYPE
	SYNTAX      NatNumPortBlocksFreeHighLevelEntry
	MAX-ACCESS  not-accessible
	STATUS      current
	DESCRIPTION
	"Table entry for natNumPortBlocksFreeHigh"
	INDEX { natNumPortBlocksFreeHighLevelName }
	::={natNumPortBlocksFreeHighLevelTable 1}

NatNumPortBlocksFreeHighLevelEntry ::=
	SEQUENCE {
		natNumPortBlocksFreeHighLevelName	DisplayString,
		natNumPortBlocksFreeHighLevelVal	CounterBasedGauge64,
		natNumPortBlocksFreeHighLevelMax	CounterBasedGauge64
	}

natNumPortBlocksFreeHighLevelName OBJECT-TYPE
	SYNTAX      DisplayString
	MAX-ACCESS  not-accessible
	STATUS      current
	DESCRIPTION
	"Table entry display string for natNumPortBlocksFreeHigh"
	::={natNumPortBlocksFreeHighLevelEntry 1}

natNumPortBlocksFreeHighLevelVal OBJECT-TYPE
	SYNTAX	 CounterBasedGauge64
	MAX-ACCESS  read-only
	STATUS      current
	DESCRIPTION
	"Table entry attribute for natNumPortBlocksFreeHigh"
	::={natNumPortBlocksFreeHighLevelEntry 2}

natNumPortBlocksFreeHighLevelMax OBJECT-TYPE
	SYNTAX	 CounterBasedGauge64
	MAX-ACCESS  read-only
	STATUS      current
	DESCRIPTION
	"Table entry attribute for natNumPortBlocksFreeHigh"
	::={natNumPortBlocksFreeHighLevelEntry 4}


natNumPools	OBJECT IDENTIFIER ::={nat 5}

natNumPoolsVal	OBJECT-TYPE
	SYNTAX	 CounterBasedGauge64
	MAX-ACCESS read-only
	STATUS current
	DESCRIPTION "Number of pools"

	::={natNumPools 1}

natNumPoolsMax	OBJECT-TYPE
	SYNTAX	 CounterBasedGauge64
	MAX-ACCESS read-only
	STATUS current
	DESCRIPTION "Number of pools"

	::={natNumPools 3}

natNumPoolsLevelTable OBJECT-TYPE
	SYNTAX      SEQUENCE OF NatNumPoolsLevelEntry
	MAX-ACCESS  not-accessible
	STATUS      current
	DESCRIPTION
	"Table for natNumPools"
	::={natNumPools 4}

natNumPoolsLevelEntry OBJECT-TYPE
	SYNTAX      NatNumPoolsLevelEntry
	MAX-ACCESS  not-accessible
	STATUS      current
	DESCRIPTION
	"Table entry for natNumPools"
	INDEX { natNumPoolsLevelName }
	::={natNumPoolsLevelTable 1}

NatNumPoolsLevelEntry ::=
	SEQUENCE {
		natNumPoolsLevelName	DisplayString,
		natNumPoolsLevelVal	CounterBasedGauge64,
		natNumPoolsLevelMax	CounterBasedGauge64
	}

natNumPoolsLevelName OBJECT-TYPE
	SYNTAX      DisplayString
	MAX-ACCESS  not-accessible
	STATUS      current
	DESCRIPTION
	"Table entry display string for natNumPools"
	::={natNumPoolsLevelEntry 1}

natNumPoolsLevelVal OBJECT-TYPE
	SYNTAX	 CounterBasedGauge64
	MAX-ACCESS  read-only
	STATUS      current
	DESCRIPTION
	"Table entry attribute for natNumPools"
	::={natNumPoolsLevelEntry 2}

natNumPoolsLevelMax OBJECT-TYPE
	SYNTAX	 CounterBasedGauge64
	MAX-ACCESS  read-only
	STATUS      current
	DESCRIPTION
	"Table entry attribute for natNumPools"
	::={natNumPoolsLevelEntry 4}


natNumNATAddresses	OBJECT IDENTIFIER ::={nat 6}

natNumNATAddressesVal	OBJECT-TYPE
	SYNTAX	 CounterBasedGauge64
	MAX-ACCESS read-only
	STATUS current
	DESCRIPTION "Number of NAT IP-addresses"

	::={natNumNATAddresses 1}

natNumNATAddressesMax	OBJECT-TYPE
	SYNTAX	 CounterBasedGauge64
	MAX-ACCESS read-only
	STATUS current
	DESCRIPTION "Number of NAT IP-addresses"

	::={natNumNATAddresses 3}

natNumNATAddressesLevelTable OBJECT-TYPE
	SYNTAX      SEQUENCE OF NatNumNATAddressesLevelEntry
	MAX-ACCESS  not-accessible
	STATUS      current
	DESCRIPTION
	"Table for natNumNATAddresses"
	::={natNumNATAddresses 4}

natNumNATAddressesLevelEntry OBJECT-TYPE
	SYNTAX      NatNumNATAddressesLevelEntry
	MAX-ACCESS  not-accessible
	STATUS      current
	DESCRIPTION
	"Table entry for natNumNATAddresses"
	INDEX { natNumNATAddressesLevelName }
	::={natNumNATAddressesLevelTable 1}

NatNumNATAddressesLevelEntry ::=
	SEQUENCE {
		natNumNATAddressesLevelName	DisplayString,
		natNumNATAddressesLevelVal	CounterBasedGauge64,
		natNumNATAddressesLevelMax	CounterBasedGauge64
	}

natNumNATAddressesLevelName OBJECT-TYPE
	SYNTAX      DisplayString
	MAX-ACCESS  not-accessible
	STATUS      current
	DESCRIPTION
	"Table entry display string for natNumNATAddresses"
	::={natNumNATAddressesLevelEntry 1}

natNumNATAddressesLevelVal OBJECT-TYPE
	SYNTAX	 CounterBasedGauge64
	MAX-ACCESS  read-only
	STATUS      current
	DESCRIPTION
	"Table entry attribute for natNumNATAddresses"
	::={natNumNATAddressesLevelEntry 2}

natNumNATAddressesLevelMax OBJECT-TYPE
	SYNTAX	 CounterBasedGauge64
	MAX-ACCESS  read-only
	STATUS      current
	DESCRIPTION
	"Table entry attribute for natNumNATAddresses"
	::={natNumNATAddressesLevelEntry 4}


natNumPoolsExceeded	OBJECT IDENTIFIER ::={nat 7}

natNumPoolsExceededVal	OBJECT-TYPE
	SYNTAX	 Counter64
	MAX-ACCESS read-only
	STATUS obsolete
	DESCRIPTION "Number of configured NAT pools exceeded"

	::={natNumPoolsExceeded 1}

natNumPoolsExceededMom	OBJECT-TYPE
	SYNTAX	 CounterBasedGauge64
	MAX-ACCESS read-only
	STATUS obsolete
	DESCRIPTION "Number of configured NAT pools exceeded"

	::={natNumPoolsExceeded 2}

natNumPoolsExceededMax	OBJECT-TYPE
	SYNTAX	 CounterBasedGauge64
	MAX-ACCESS read-only
	STATUS obsolete
	DESCRIPTION "Number of configured NAT pools exceeded"

	::={natNumPoolsExceeded 3}

natNumPoolsExceededLevelTable OBJECT-TYPE
	SYNTAX      SEQUENCE OF NatNumPoolsExceededLevelEntry
	MAX-ACCESS  not-accessible
	STATUS      current
	DESCRIPTION
	"Table for natNumPoolsExceeded"
	::={natNumPoolsExceeded 4}

natNumPoolsExceededLevelEntry OBJECT-TYPE
	SYNTAX      NatNumPoolsExceededLevelEntry
	MAX-ACCESS  not-accessible
	STATUS      current
	DESCRIPTION
	"Table entry for natNumPoolsExceeded"
	INDEX { natNumPoolsExceededLevelName }
	::={natNumPoolsExceededLevelTable 1}

NatNumPoolsExceededLevelEntry ::=
	SEQUENCE {
		natNumPoolsExceededLevelName	DisplayString,
		natNumPoolsExceededLevelVal	Counter64,
		natNumPoolsExceededLevelMom	CounterBasedGauge64,
		natNumPoolsExceededLevelMax	CounterBasedGauge64
	}

natNumPoolsExceededLevelName OBJECT-TYPE
	SYNTAX      DisplayString
	MAX-ACCESS  not-accessible
	STATUS      current
	DESCRIPTION
	"Table entry display string for natNumPoolsExceeded"
	::={natNumPoolsExceededLevelEntry 1}

natNumPoolsExceededLevelVal OBJECT-TYPE
	SYNTAX	 Counter64
	MAX-ACCESS  read-only
	STATUS      current
	DESCRIPTION
	"Table entry attribute for natNumPoolsExceeded"
	::={natNumPoolsExceededLevelEntry 2}

natNumPoolsExceededLevelMom OBJECT-TYPE
	SYNTAX	 CounterBasedGauge64
	MAX-ACCESS  read-only
	STATUS      current
	DESCRIPTION
	"Table entry attribute for natNumPoolsExceeded"
	::={natNumPoolsExceededLevelEntry 3}

natNumPoolsExceededLevelMax OBJECT-TYPE
	SYNTAX	 CounterBasedGauge64
	MAX-ACCESS  read-only
	STATUS      current
	DESCRIPTION
	"Table entry attribute for natNumPoolsExceeded"
	::={natNumPoolsExceededLevelEntry 4}


natNumSrcAddressesExceeded	OBJECT IDENTIFIER ::={nat 8}

natNumSrcAddressesExceededVal	OBJECT-TYPE
	SYNTAX	 Counter64
	MAX-ACCESS read-only
	STATUS obsolete
	DESCRIPTION "Number of configured NAT IP addresses exceeded"

	::={natNumSrcAddressesExceeded 1}

natNumSrcAddressesExceededMom	OBJECT-TYPE
	SYNTAX	 CounterBasedGauge64
	MAX-ACCESS read-only
	STATUS obsolete
	DESCRIPTION "Number of configured NAT IP addresses exceeded"

	::={natNumSrcAddressesExceeded 2}

natNumSrcAddressesExceededMax	OBJECT-TYPE
	SYNTAX	 CounterBasedGauge64
	MAX-ACCESS read-only
	STATUS obsolete
	DESCRIPTION "Number of configured NAT IP addresses exceeded"

	::={natNumSrcAddressesExceeded 3}

natNumSrcAddressesExceededLevelTable OBJECT-TYPE
	SYNTAX      SEQUENCE OF NatNumSrcAddressesExceededLevelEntry
	MAX-ACCESS  not-accessible
	STATUS      current
	DESCRIPTION
	"Table for natNumSrcAddressesExceeded"
	::={natNumSrcAddressesExceeded 4}

natNumSrcAddressesExceededLevelEntry OBJECT-TYPE
	SYNTAX      NatNumSrcAddressesExceededLevelEntry
	MAX-ACCESS  not-accessible
	STATUS      current
	DESCRIPTION
	"Table entry for natNumSrcAddressesExceeded"
	INDEX { natNumSrcAddressesExceededLevelName }
	::={natNumSrcAddressesExceededLevelTable 1}

NatNumSrcAddressesExceededLevelEntry ::=
	SEQUENCE {
		natNumSrcAddressesExceededLevelName	DisplayString,
		natNumSrcAddressesExceededLevelVal	Counter64,
		natNumSrcAddressesExceededLevelMom	CounterBasedGauge64,
		natNumSrcAddressesExceededLevelMax	CounterBasedGauge64
	}

natNumSrcAddressesExceededLevelName OBJECT-TYPE
	SYNTAX      DisplayString
	MAX-ACCESS  not-accessible
	STATUS      current
	DESCRIPTION
	"Table entry display string for natNumSrcAddressesExceeded"
	::={natNumSrcAddressesExceededLevelEntry 1}

natNumSrcAddressesExceededLevelVal OBJECT-TYPE
	SYNTAX	 Counter64
	MAX-ACCESS  read-only
	STATUS      current
	DESCRIPTION
	"Table entry attribute for natNumSrcAddressesExceeded"
	::={natNumSrcAddressesExceededLevelEntry 2}

natNumSrcAddressesExceededLevelMom OBJECT-TYPE
	SYNTAX	 CounterBasedGauge64
	MAX-ACCESS  read-only
	STATUS      current
	DESCRIPTION
	"Table entry attribute for natNumSrcAddressesExceeded"
	::={natNumSrcAddressesExceededLevelEntry 3}

natNumSrcAddressesExceededLevelMax OBJECT-TYPE
	SYNTAX	 CounterBasedGauge64
	MAX-ACCESS  read-only
	STATUS      current
	DESCRIPTION
	"Table entry attribute for natNumSrcAddressesExceeded"
	::={natNumSrcAddressesExceededLevelEntry 4}


natNumPoolsFillPercent	OBJECT IDENTIFIER ::={nat 10}

natNumPoolsFillPercentVal	OBJECT-TYPE
	SYNTAX	 Unsigned32
	MAX-ACCESS read-only
	STATUS current
	DESCRIPTION "Total usage of NAT pools"

	::={natNumPoolsFillPercent 1}

natNumPoolsFillPercentMax	OBJECT-TYPE
	SYNTAX	 Unsigned32
	MAX-ACCESS read-only
	STATUS current
	DESCRIPTION "Total usage of NAT pools"

	::={natNumPoolsFillPercent 3}

natNumPoolsFillPercentLevelTable OBJECT-TYPE
	SYNTAX      SEQUENCE OF NatNumPoolsFillPercentLevelEntry
	MAX-ACCESS  not-accessible
	STATUS      current
	DESCRIPTION
	"Table for natNumPoolsFillPercent"
	::={natNumPoolsFillPercent 4}

natNumPoolsFillPercentLevelEntry OBJECT-TYPE
	SYNTAX      NatNumPoolsFillPercentLevelEntry
	MAX-ACCESS  not-accessible
	STATUS      current
	DESCRIPTION
	"Table entry for natNumPoolsFillPercent"
	INDEX { natNumPoolsFillPercentLevelName }
	::={natNumPoolsFillPercentLevelTable 1}

NatNumPoolsFillPercentLevelEntry ::=
	SEQUENCE {
		natNumPoolsFillPercentLevelName	DisplayString,
		natNumPoolsFillPercentLevelVal	Unsigned32,
		natNumPoolsFillPercentLevelMax	Unsigned32
	}

natNumPoolsFillPercentLevelName OBJECT-TYPE
	SYNTAX      DisplayString
	MAX-ACCESS  not-accessible
	STATUS      current
	DESCRIPTION
	"Table entry display string for natNumPoolsFillPercent"
	::={natNumPoolsFillPercentLevelEntry 1}

natNumPoolsFillPercentLevelVal OBJECT-TYPE
	SYNTAX	 Unsigned32
	MAX-ACCESS  read-only
	STATUS      current
	DESCRIPTION
	"Table entry attribute for natNumPoolsFillPercent"
	::={natNumPoolsFillPercentLevelEntry 2}

natNumPoolsFillPercentLevelMax OBJECT-TYPE
	SYNTAX	 Unsigned32
	MAX-ACCESS  read-only
	STATUS      current
	DESCRIPTION
	"Table entry attribute for natNumPoolsFillPercent"
	::={natNumPoolsFillPercentLevelEntry 4}


natNumSrcAddressesFillPercent	OBJECT IDENTIFIER ::={nat 11}

natNumSrcAddressesFillPercentVal	OBJECT-TYPE
	SYNTAX	 Unsigned32
	MAX-ACCESS read-only
	STATUS current
	DESCRIPTION "Total usage of NAT IP addresses"

	::={natNumSrcAddressesFillPercent 1}

natNumSrcAddressesFillPercentMax	OBJECT-TYPE
	SYNTAX	 Unsigned32
	MAX-ACCESS read-only
	STATUS current
	DESCRIPTION "Total usage of NAT IP addresses"

	::={natNumSrcAddressesFillPercent 3}

natNumSrcAddressesFillPercentLevelTable OBJECT-TYPE
	SYNTAX      SEQUENCE OF NatNumSrcAddressesFillPercentLevelEntry
	MAX-ACCESS  not-accessible
	STATUS      current
	DESCRIPTION
	"Table for natNumSrcAddressesFillPercent"
	::={natNumSrcAddressesFillPercent 4}

natNumSrcAddressesFillPercentLevelEntry OBJECT-TYPE
	SYNTAX      NatNumSrcAddressesFillPercentLevelEntry
	MAX-ACCESS  not-accessible
	STATUS      current
	DESCRIPTION
	"Table entry for natNumSrcAddressesFillPercent"
	INDEX { natNumSrcAddressesFillPercentLevelName }
	::={natNumSrcAddressesFillPercentLevelTable 1}

NatNumSrcAddressesFillPercentLevelEntry ::=
	SEQUENCE {
		natNumSrcAddressesFillPercentLevelName	DisplayString,
		natNumSrcAddressesFillPercentLevelVal	Unsigned32,
		natNumSrcAddressesFillPercentLevelMax	Unsigned32
	}

natNumSrcAddressesFillPercentLevelName OBJECT-TYPE
	SYNTAX      DisplayString
	MAX-ACCESS  not-accessible
	STATUS      current
	DESCRIPTION
	"Table entry display string for natNumSrcAddressesFillPercent"
	::={natNumSrcAddressesFillPercentLevelEntry 1}

natNumSrcAddressesFillPercentLevelVal OBJECT-TYPE
	SYNTAX	 Unsigned32
	MAX-ACCESS  read-only
	STATUS      current
	DESCRIPTION
	"Table entry attribute for natNumSrcAddressesFillPercent"
	::={natNumSrcAddressesFillPercentLevelEntry 2}

natNumSrcAddressesFillPercentLevelMax OBJECT-TYPE
	SYNTAX	 Unsigned32
	MAX-ACCESS  read-only
	STATUS      current
	DESCRIPTION
	"Table entry attribute for natNumSrcAddressesFillPercent"
	::={natNumSrcAddressesFillPercentLevelEntry 4}


natPoolConfigGranularityMaxPbLowFail	OBJECT IDENTIFIER ::={nat 9}

natPoolConfigGranularityMaxPbLowFailVal	OBJECT-TYPE
	SYNTAX	 Counter64
	MAX-ACCESS read-only
	STATUS current
	DESCRIPTION "Faulty pool configuration of low port blocks"

	::={natPoolConfigGranularityMaxPbLowFail 1}

natPoolConfigGranularityMaxPbLowFailMom	OBJECT-TYPE
	SYNTAX	 CounterBasedGauge64
	MAX-ACCESS read-only
	STATUS current
	DESCRIPTION "Faulty pool configuration of low port blocks"

	::={natPoolConfigGranularityMaxPbLowFail 2}

natPoolConfigGranularityMaxPbLowFailMax	OBJECT-TYPE
	SYNTAX	 CounterBasedGauge64
	MAX-ACCESS read-only
	STATUS current
	DESCRIPTION "Faulty pool configuration of low port blocks"

	::={natPoolConfigGranularityMaxPbLowFail 3}

natPoolConfigGranularityMaxPbLowFailLevelTable OBJECT-TYPE
	SYNTAX      SEQUENCE OF NatPoolConfigGranularityMaxPbLowFailLevelEntry
	MAX-ACCESS  not-accessible
	STATUS      current
	DESCRIPTION
	"Table for natPoolConfigGranularityMaxPbLowFail"
	::={natPoolConfigGranularityMaxPbLowFail 4}

natPoolConfigGranularityMaxPbLowFailLevelEntry OBJECT-TYPE
	SYNTAX      NatPoolConfigGranularityMaxPbLowFailLevelEntry
	MAX-ACCESS  not-accessible
	STATUS      current
	DESCRIPTION
	"Table entry for natPoolConfigGranularityMaxPbLowFail"
	INDEX { natPoolConfigGranularityMaxPbLowFailLevelName }
	::={natPoolConfigGranularityMaxPbLowFailLevelTable 1}

NatPoolConfigGranularityMaxPbLowFailLevelEntry ::=
	SEQUENCE {
		natPoolConfigGranularityMaxPbLowFailLevelName	DisplayString,
		natPoolConfigGranularityMaxPbLowFailLevelVal	Counter64,
		natPoolConfigGranularityMaxPbLowFailLevelMom	CounterBasedGauge64,
		natPoolConfigGranularityMaxPbLowFailLevelMax	CounterBasedGauge64
	}

natPoolConfigGranularityMaxPbLowFailLevelName OBJECT-TYPE
	SYNTAX      DisplayString
	MAX-ACCESS  not-accessible
	STATUS      current
	DESCRIPTION
	"Table entry display string for natPoolConfigGranularityMaxPbLowFail"
	::={natPoolConfigGranularityMaxPbLowFailLevelEntry 1}

natPoolConfigGranularityMaxPbLowFailLevelVal OBJECT-TYPE
	SYNTAX	 Counter64
	MAX-ACCESS  read-only
	STATUS      current
	DESCRIPTION
	"Table entry attribute for natPoolConfigGranularityMaxPbLowFail"
	::={natPoolConfigGranularityMaxPbLowFailLevelEntry 2}

natPoolConfigGranularityMaxPbLowFailLevelMom OBJECT-TYPE
	SYNTAX	 CounterBasedGauge64
	MAX-ACCESS  read-only
	STATUS      current
	DESCRIPTION
	"Table entry attribute for natPoolConfigGranularityMaxPbLowFail"
	::={natPoolConfigGranularityMaxPbLowFailLevelEntry 3}

natPoolConfigGranularityMaxPbLowFailLevelMax OBJECT-TYPE
	SYNTAX	 CounterBasedGauge64
	MAX-ACCESS  read-only
	STATUS      current
	DESCRIPTION
	"Table entry attribute for natPoolConfigGranularityMaxPbLowFail"
	::={natPoolConfigGranularityMaxPbLowFailLevelEntry 4}


enrichment	OBJECT IDENTIFIER ::={sysdiag 143}

enrichmentAddedPackets	OBJECT IDENTIFIER ::={enrichment 1}

enrichmentAddedPacketsVal	OBJECT-TYPE
	SYNTAX	 Counter64
	MAX-ACCESS read-only
	STATUS current
	DESCRIPTION "Number of packets enrichment has added"

	::={enrichmentAddedPackets 1}

enrichmentAddedPacketsMom	OBJECT-TYPE
	SYNTAX	 CounterBasedGauge64
	MAX-ACCESS read-only
	STATUS current
	DESCRIPTION "Number of packets enrichment has added"

	::={enrichmentAddedPackets 2}

enrichmentAddedPacketsMax	OBJECT-TYPE
	SYNTAX	 CounterBasedGauge64
	MAX-ACCESS read-only
	STATUS current
	DESCRIPTION "Number of packets enrichment has added"

	::={enrichmentAddedPackets 3}

enrichmentAddedPacketsLevelTable OBJECT-TYPE
	SYNTAX      SEQUENCE OF EnrichmentAddedPacketsLevelEntry
	MAX-ACCESS  not-accessible
	STATUS      current
	DESCRIPTION
	"Table for enrichmentAddedPackets"
	::={enrichmentAddedPackets 4}

enrichmentAddedPacketsLevelEntry OBJECT-TYPE
	SYNTAX      EnrichmentAddedPacketsLevelEntry
	MAX-ACCESS  not-accessible
	STATUS      current
	DESCRIPTION
	"Table entry for enrichmentAddedPackets"
	INDEX { enrichmentAddedPacketsLevelName }
	::={enrichmentAddedPacketsLevelTable 1}

EnrichmentAddedPacketsLevelEntry ::=
	SEQUENCE {
		enrichmentAddedPacketsLevelName	DisplayString,
		enrichmentAddedPacketsLevelVal	Counter64,
		enrichmentAddedPacketsLevelMom	CounterBasedGauge64,
		enrichmentAddedPacketsLevelMax	CounterBasedGauge64
	}

enrichmentAddedPacketsLevelName OBJECT-TYPE
	SYNTAX      DisplayString
	MAX-ACCESS  not-accessible
	STATUS      current
	DESCRIPTION
	"Table entry display string for enrichmentAddedPackets"
	::={enrichmentAddedPacketsLevelEntry 1}

enrichmentAddedPacketsLevelVal OBJECT-TYPE
	SYNTAX	 Counter64
	MAX-ACCESS  read-only
	STATUS      current
	DESCRIPTION
	"Table entry attribute for enrichmentAddedPackets"
	::={enrichmentAddedPacketsLevelEntry 2}

enrichmentAddedPacketsLevelMom OBJECT-TYPE
	SYNTAX	 CounterBasedGauge64
	MAX-ACCESS  read-only
	STATUS      current
	DESCRIPTION
	"Table entry attribute for enrichmentAddedPackets"
	::={enrichmentAddedPacketsLevelEntry 3}

enrichmentAddedPacketsLevelMax OBJECT-TYPE
	SYNTAX	 CounterBasedGauge64
	MAX-ACCESS  read-only
	STATUS      current
	DESCRIPTION
	"Table entry attribute for enrichmentAddedPackets"
	::={enrichmentAddedPacketsLevelEntry 4}


enrichmentDataAllocationFailure	OBJECT IDENTIFIER ::={enrichment 2}

enrichmentDataAllocationFailureVal	OBJECT-TYPE
	SYNTAX	 Counter64
	MAX-ACCESS read-only
	STATUS current
	DESCRIPTION "Number of enrichment data allocation failures"

	::={enrichmentDataAllocationFailure 1}

enrichmentDataAllocationFailureMom	OBJECT-TYPE
	SYNTAX	 CounterBasedGauge64
	MAX-ACCESS read-only
	STATUS current
	DESCRIPTION "Number of enrichment data allocation failures"

	::={enrichmentDataAllocationFailure 2}

enrichmentDataAllocationFailureMax	OBJECT-TYPE
	SYNTAX	 CounterBasedGauge64
	MAX-ACCESS read-only
	STATUS current
	DESCRIPTION "Number of enrichment data allocation failures"

	::={enrichmentDataAllocationFailure 3}

enrichmentDataAllocationFailureLevelTable OBJECT-TYPE
	SYNTAX      SEQUENCE OF EnrichmentDataAllocationFailureLevelEntry
	MAX-ACCESS  not-accessible
	STATUS      current
	DESCRIPTION
	"Table for enrichmentDataAllocationFailure"
	::={enrichmentDataAllocationFailure 4}

enrichmentDataAllocationFailureLevelEntry OBJECT-TYPE
	SYNTAX      EnrichmentDataAllocationFailureLevelEntry
	MAX-ACCESS  not-accessible
	STATUS      current
	DESCRIPTION
	"Table entry for enrichmentDataAllocationFailure"
	INDEX { enrichmentDataAllocationFailureLevelName }
	::={enrichmentDataAllocationFailureLevelTable 1}

EnrichmentDataAllocationFailureLevelEntry ::=
	SEQUENCE {
		enrichmentDataAllocationFailureLevelName	DisplayString,
		enrichmentDataAllocationFailureLevelVal	Counter64,
		enrichmentDataAllocationFailureLevelMom	CounterBasedGauge64,
		enrichmentDataAllocationFailureLevelMax	CounterBasedGauge64
	}

enrichmentDataAllocationFailureLevelName OBJECT-TYPE
	SYNTAX      DisplayString
	MAX-ACCESS  not-accessible
	STATUS      current
	DESCRIPTION
	"Table entry display string for enrichmentDataAllocationFailure"
	::={enrichmentDataAllocationFailureLevelEntry 1}

enrichmentDataAllocationFailureLevelVal OBJECT-TYPE
	SYNTAX	 Counter64
	MAX-ACCESS  read-only
	STATUS      current
	DESCRIPTION
	"Table entry attribute for enrichmentDataAllocationFailure"
	::={enrichmentDataAllocationFailureLevelEntry 2}

enrichmentDataAllocationFailureLevelMom OBJECT-TYPE
	SYNTAX	 CounterBasedGauge64
	MAX-ACCESS  read-only
	STATUS      current
	DESCRIPTION
	"Table entry attribute for enrichmentDataAllocationFailure"
	::={enrichmentDataAllocationFailureLevelEntry 3}

enrichmentDataAllocationFailureLevelMax OBJECT-TYPE
	SYNTAX	 CounterBasedGauge64
	MAX-ACCESS  read-only
	STATUS      current
	DESCRIPTION
	"Table entry attribute for enrichmentDataAllocationFailure"
	::={enrichmentDataAllocationFailureLevelEntry 4}


enrichmentConnectionCount	OBJECT IDENTIFIER ::={enrichment 3}

enrichmentConnectionCountVal	OBJECT-TYPE
	SYNTAX	 CounterBasedGauge64
	MAX-ACCESS read-only
	STATUS current
	DESCRIPTION "Number of currently enriched connections"

	::={enrichmentConnectionCount 1}

enrichmentConnectionCountMax	OBJECT-TYPE
	SYNTAX	 CounterBasedGauge64
	MAX-ACCESS read-only
	STATUS current
	DESCRIPTION "Number of currently enriched connections"

	::={enrichmentConnectionCount 3}

enrichmentConnectionCountLevelTable OBJECT-TYPE
	SYNTAX      SEQUENCE OF EnrichmentConnectionCountLevelEntry
	MAX-ACCESS  not-accessible
	STATUS      current
	DESCRIPTION
	"Table for enrichmentConnectionCount"
	::={enrichmentConnectionCount 4}

enrichmentConnectionCountLevelEntry OBJECT-TYPE
	SYNTAX      EnrichmentConnectionCountLevelEntry
	MAX-ACCESS  not-accessible
	STATUS      current
	DESCRIPTION
	"Table entry for enrichmentConnectionCount"
	INDEX { enrichmentConnectionCountLevelName }
	::={enrichmentConnectionCountLevelTable 1}

EnrichmentConnectionCountLevelEntry ::=
	SEQUENCE {
		enrichmentConnectionCountLevelName	DisplayString,
		enrichmentConnectionCountLevelVal	CounterBasedGauge64,
		enrichmentConnectionCountLevelMax	CounterBasedGauge64
	}

enrichmentConnectionCountLevelName OBJECT-TYPE
	SYNTAX      DisplayString
	MAX-ACCESS  not-accessible
	STATUS      current
	DESCRIPTION
	"Table entry display string for enrichmentConnectionCount"
	::={enrichmentConnectionCountLevelEntry 1}

enrichmentConnectionCountLevelVal OBJECT-TYPE
	SYNTAX	 CounterBasedGauge64
	MAX-ACCESS  read-only
	STATUS      current
	DESCRIPTION
	"Table entry attribute for enrichmentConnectionCount"
	::={enrichmentConnectionCountLevelEntry 2}

enrichmentConnectionCountLevelMax OBJECT-TYPE
	SYNTAX	 CounterBasedGauge64
	MAX-ACCESS  read-only
	STATUS      current
	DESCRIPTION
	"Table entry attribute for enrichmentConnectionCount"
	::={enrichmentConnectionCountLevelEntry 4}


enrichmentDroppedToClient	OBJECT IDENTIFIER ::={enrichment 4}

enrichmentDroppedToClientVal	OBJECT-TYPE
	SYNTAX	 Counter64
	MAX-ACCESS read-only
	STATUS current
	DESCRIPTION "Number of packets dropped by enrichment (to client)"

	::={enrichmentDroppedToClient 1}

enrichmentDroppedToClientMom	OBJECT-TYPE
	SYNTAX	 CounterBasedGauge64
	MAX-ACCESS read-only
	STATUS current
	DESCRIPTION "Number of packets dropped by enrichment (to client)"

	::={enrichmentDroppedToClient 2}

enrichmentDroppedToClientMax	OBJECT-TYPE
	SYNTAX	 CounterBasedGauge64
	MAX-ACCESS read-only
	STATUS current
	DESCRIPTION "Number of packets dropped by enrichment (to client)"

	::={enrichmentDroppedToClient 3}

enrichmentDroppedToClientLevelTable OBJECT-TYPE
	SYNTAX      SEQUENCE OF EnrichmentDroppedToClientLevelEntry
	MAX-ACCESS  not-accessible
	STATUS      current
	DESCRIPTION
	"Table for enrichmentDroppedToClient"
	::={enrichmentDroppedToClient 4}

enrichmentDroppedToClientLevelEntry OBJECT-TYPE
	SYNTAX      EnrichmentDroppedToClientLevelEntry
	MAX-ACCESS  not-accessible
	STATUS      current
	DESCRIPTION
	"Table entry for enrichmentDroppedToClient"
	INDEX { enrichmentDroppedToClientLevelName }
	::={enrichmentDroppedToClientLevelTable 1}

EnrichmentDroppedToClientLevelEntry ::=
	SEQUENCE {
		enrichmentDroppedToClientLevelName	DisplayString,
		enrichmentDroppedToClientLevelVal	Counter64,
		enrichmentDroppedToClientLevelMom	CounterBasedGauge64,
		enrichmentDroppedToClientLevelMax	CounterBasedGauge64
	}

enrichmentDroppedToClientLevelName OBJECT-TYPE
	SYNTAX      DisplayString
	MAX-ACCESS  not-accessible
	STATUS      current
	DESCRIPTION
	"Table entry display string for enrichmentDroppedToClient"
	::={enrichmentDroppedToClientLevelEntry 1}

enrichmentDroppedToClientLevelVal OBJECT-TYPE
	SYNTAX	 Counter64
	MAX-ACCESS  read-only
	STATUS      current
	DESCRIPTION
	"Table entry attribute for enrichmentDroppedToClient"
	::={enrichmentDroppedToClientLevelEntry 2}

enrichmentDroppedToClientLevelMom OBJECT-TYPE
	SYNTAX	 CounterBasedGauge64
	MAX-ACCESS  read-only
	STATUS      current
	DESCRIPTION
	"Table entry attribute for enrichmentDroppedToClient"
	::={enrichmentDroppedToClientLevelEntry 3}

enrichmentDroppedToClientLevelMax OBJECT-TYPE
	SYNTAX	 CounterBasedGauge64
	MAX-ACCESS  read-only
	STATUS      current
	DESCRIPTION
	"Table entry attribute for enrichmentDroppedToClient"
	::={enrichmentDroppedToClientLevelEntry 4}


enrichmentDroppedToServer	OBJECT IDENTIFIER ::={enrichment 5}

enrichmentDroppedToServerVal	OBJECT-TYPE
	SYNTAX	 Counter64
	MAX-ACCESS read-only
	STATUS current
	DESCRIPTION "Number of packets dropped by enrichment (to server)"

	::={enrichmentDroppedToServer 1}

enrichmentDroppedToServerMom	OBJECT-TYPE
	SYNTAX	 CounterBasedGauge64
	MAX-ACCESS read-only
	STATUS current
	DESCRIPTION "Number of packets dropped by enrichment (to server)"

	::={enrichmentDroppedToServer 2}

enrichmentDroppedToServerMax	OBJECT-TYPE
	SYNTAX	 CounterBasedGauge64
	MAX-ACCESS read-only
	STATUS current
	DESCRIPTION "Number of packets dropped by enrichment (to server)"

	::={enrichmentDroppedToServer 3}

enrichmentDroppedToServerLevelTable OBJECT-TYPE
	SYNTAX      SEQUENCE OF EnrichmentDroppedToServerLevelEntry
	MAX-ACCESS  not-accessible
	STATUS      current
	DESCRIPTION
	"Table for enrichmentDroppedToServer"
	::={enrichmentDroppedToServer 4}

enrichmentDroppedToServerLevelEntry OBJECT-TYPE
	SYNTAX      EnrichmentDroppedToServerLevelEntry
	MAX-ACCESS  not-accessible
	STATUS      current
	DESCRIPTION
	"Table entry for enrichmentDroppedToServer"
	INDEX { enrichmentDroppedToServerLevelName }
	::={enrichmentDroppedToServerLevelTable 1}

EnrichmentDroppedToServerLevelEntry ::=
	SEQUENCE {
		enrichmentDroppedToServerLevelName	DisplayString,
		enrichmentDroppedToServerLevelVal	Counter64,
		enrichmentDroppedToServerLevelMom	CounterBasedGauge64,
		enrichmentDroppedToServerLevelMax	CounterBasedGauge64
	}

enrichmentDroppedToServerLevelName OBJECT-TYPE
	SYNTAX      DisplayString
	MAX-ACCESS  not-accessible
	STATUS      current
	DESCRIPTION
	"Table entry display string for enrichmentDroppedToServer"
	::={enrichmentDroppedToServerLevelEntry 1}

enrichmentDroppedToServerLevelVal OBJECT-TYPE
	SYNTAX	 Counter64
	MAX-ACCESS  read-only
	STATUS      current
	DESCRIPTION
	"Table entry attribute for enrichmentDroppedToServer"
	::={enrichmentDroppedToServerLevelEntry 2}

enrichmentDroppedToServerLevelMom OBJECT-TYPE
	SYNTAX	 CounterBasedGauge64
	MAX-ACCESS  read-only
	STATUS      current
	DESCRIPTION
	"Table entry attribute for enrichmentDroppedToServer"
	::={enrichmentDroppedToServerLevelEntry 3}

enrichmentDroppedToServerLevelMax OBJECT-TYPE
	SYNTAX	 CounterBasedGauge64
	MAX-ACCESS  read-only
	STATUS      current
	DESCRIPTION
	"Table entry attribute for enrichmentDroppedToServer"
	::={enrichmentDroppedToServerLevelEntry 4}


enrichmentHeaderOverwrite	OBJECT IDENTIFIER ::={enrichment 6}

enrichmentHeaderOverwriteVal	OBJECT-TYPE
	SYNTAX	 Counter64
	MAX-ACCESS read-only
	STATUS current
	DESCRIPTION "Number of headers overwritten"

	::={enrichmentHeaderOverwrite 1}

enrichmentHeaderOverwriteMom	OBJECT-TYPE
	SYNTAX	 CounterBasedGauge64
	MAX-ACCESS read-only
	STATUS current
	DESCRIPTION "Number of headers overwritten"

	::={enrichmentHeaderOverwrite 2}

enrichmentHeaderOverwriteMax	OBJECT-TYPE
	SYNTAX	 CounterBasedGauge64
	MAX-ACCESS read-only
	STATUS current
	DESCRIPTION "Number of headers overwritten"

	::={enrichmentHeaderOverwrite 3}

enrichmentHeaderOverwriteLevelTable OBJECT-TYPE
	SYNTAX      SEQUENCE OF EnrichmentHeaderOverwriteLevelEntry
	MAX-ACCESS  not-accessible
	STATUS      current
	DESCRIPTION
	"Table for enrichmentHeaderOverwrite"
	::={enrichmentHeaderOverwrite 4}

enrichmentHeaderOverwriteLevelEntry OBJECT-TYPE
	SYNTAX      EnrichmentHeaderOverwriteLevelEntry
	MAX-ACCESS  not-accessible
	STATUS      current
	DESCRIPTION
	"Table entry for enrichmentHeaderOverwrite"
	INDEX { enrichmentHeaderOverwriteLevelName }
	::={enrichmentHeaderOverwriteLevelTable 1}

EnrichmentHeaderOverwriteLevelEntry ::=
	SEQUENCE {
		enrichmentHeaderOverwriteLevelName	DisplayString,
		enrichmentHeaderOverwriteLevelVal	Counter64,
		enrichmentHeaderOverwriteLevelMom	CounterBasedGauge64,
		enrichmentHeaderOverwriteLevelMax	CounterBasedGauge64
	}

enrichmentHeaderOverwriteLevelName OBJECT-TYPE
	SYNTAX      DisplayString
	MAX-ACCESS  not-accessible
	STATUS      current
	DESCRIPTION
	"Table entry display string for enrichmentHeaderOverwrite"
	::={enrichmentHeaderOverwriteLevelEntry 1}

enrichmentHeaderOverwriteLevelVal OBJECT-TYPE
	SYNTAX	 Counter64
	MAX-ACCESS  read-only
	STATUS      current
	DESCRIPTION
	"Table entry attribute for enrichmentHeaderOverwrite"
	::={enrichmentHeaderOverwriteLevelEntry 2}

enrichmentHeaderOverwriteLevelMom OBJECT-TYPE
	SYNTAX	 CounterBasedGauge64
	MAX-ACCESS  read-only
	STATUS      current
	DESCRIPTION
	"Table entry attribute for enrichmentHeaderOverwrite"
	::={enrichmentHeaderOverwriteLevelEntry 3}

enrichmentHeaderOverwriteLevelMax OBJECT-TYPE
	SYNTAX	 CounterBasedGauge64
	MAX-ACCESS  read-only
	STATUS      current
	DESCRIPTION
	"Table entry attribute for enrichmentHeaderOverwrite"
	::={enrichmentHeaderOverwriteLevelEntry 4}


enrichmentHeaderRemove	OBJECT IDENTIFIER ::={enrichment 7}

enrichmentHeaderRemoveVal	OBJECT-TYPE
	SYNTAX	 Counter64
	MAX-ACCESS read-only
	STATUS current
	DESCRIPTION "Number of headers removed"

	::={enrichmentHeaderRemove 1}

enrichmentHeaderRemoveMom	OBJECT-TYPE
	SYNTAX	 CounterBasedGauge64
	MAX-ACCESS read-only
	STATUS current
	DESCRIPTION "Number of headers removed"

	::={enrichmentHeaderRemove 2}

enrichmentHeaderRemoveMax	OBJECT-TYPE
	SYNTAX	 CounterBasedGauge64
	MAX-ACCESS read-only
	STATUS current
	DESCRIPTION "Number of headers removed"

	::={enrichmentHeaderRemove 3}

enrichmentHeaderRemoveLevelTable OBJECT-TYPE
	SYNTAX      SEQUENCE OF EnrichmentHeaderRemoveLevelEntry
	MAX-ACCESS  not-accessible
	STATUS      current
	DESCRIPTION
	"Table for enrichmentHeaderRemove"
	::={enrichmentHeaderRemove 4}

enrichmentHeaderRemoveLevelEntry OBJECT-TYPE
	SYNTAX      EnrichmentHeaderRemoveLevelEntry
	MAX-ACCESS  not-accessible
	STATUS      current
	DESCRIPTION
	"Table entry for enrichmentHeaderRemove"
	INDEX { enrichmentHeaderRemoveLevelName }
	::={enrichmentHeaderRemoveLevelTable 1}

EnrichmentHeaderRemoveLevelEntry ::=
	SEQUENCE {
		enrichmentHeaderRemoveLevelName	DisplayString,
		enrichmentHeaderRemoveLevelVal	Counter64,
		enrichmentHeaderRemoveLevelMom	CounterBasedGauge64,
		enrichmentHeaderRemoveLevelMax	CounterBasedGauge64
	}

enrichmentHeaderRemoveLevelName OBJECT-TYPE
	SYNTAX      DisplayString
	MAX-ACCESS  not-accessible
	STATUS      current
	DESCRIPTION
	"Table entry display string for enrichmentHeaderRemove"
	::={enrichmentHeaderRemoveLevelEntry 1}

enrichmentHeaderRemoveLevelVal OBJECT-TYPE
	SYNTAX	 Counter64
	MAX-ACCESS  read-only
	STATUS      current
	DESCRIPTION
	"Table entry attribute for enrichmentHeaderRemove"
	::={enrichmentHeaderRemoveLevelEntry 2}

enrichmentHeaderRemoveLevelMom OBJECT-TYPE
	SYNTAX	 CounterBasedGauge64
	MAX-ACCESS  read-only
	STATUS      current
	DESCRIPTION
	"Table entry attribute for enrichmentHeaderRemove"
	::={enrichmentHeaderRemoveLevelEntry 3}

enrichmentHeaderRemoveLevelMax OBJECT-TYPE
	SYNTAX	 CounterBasedGauge64
	MAX-ACCESS  read-only
	STATUS      current
	DESCRIPTION
	"Table entry attribute for enrichmentHeaderRemove"
	::={enrichmentHeaderRemoveLevelEntry 4}


enrichmentMapOverflow	OBJECT IDENTIFIER ::={enrichment 8}

enrichmentMapOverflowVal	OBJECT-TYPE
	SYNTAX	 Counter64
	MAX-ACCESS read-only
	STATUS current
	DESCRIPTION "Number of sequence map overflows"

	::={enrichmentMapOverflow 1}

enrichmentMapOverflowMom	OBJECT-TYPE
	SYNTAX	 CounterBasedGauge64
	MAX-ACCESS read-only
	STATUS current
	DESCRIPTION "Number of sequence map overflows"

	::={enrichmentMapOverflow 2}

enrichmentMapOverflowMax	OBJECT-TYPE
	SYNTAX	 CounterBasedGauge64
	MAX-ACCESS read-only
	STATUS current
	DESCRIPTION "Number of sequence map overflows"

	::={enrichmentMapOverflow 3}

enrichmentMapOverflowLevelTable OBJECT-TYPE
	SYNTAX      SEQUENCE OF EnrichmentMapOverflowLevelEntry
	MAX-ACCESS  not-accessible
	STATUS      current
	DESCRIPTION
	"Table for enrichmentMapOverflow"
	::={enrichmentMapOverflow 4}

enrichmentMapOverflowLevelEntry OBJECT-TYPE
	SYNTAX      EnrichmentMapOverflowLevelEntry
	MAX-ACCESS  not-accessible
	STATUS      current
	DESCRIPTION
	"Table entry for enrichmentMapOverflow"
	INDEX { enrichmentMapOverflowLevelName }
	::={enrichmentMapOverflowLevelTable 1}

EnrichmentMapOverflowLevelEntry ::=
	SEQUENCE {
		enrichmentMapOverflowLevelName	DisplayString,
		enrichmentMapOverflowLevelVal	Counter64,
		enrichmentMapOverflowLevelMom	CounterBasedGauge64,
		enrichmentMapOverflowLevelMax	CounterBasedGauge64
	}

enrichmentMapOverflowLevelName OBJECT-TYPE
	SYNTAX      DisplayString
	MAX-ACCESS  not-accessible
	STATUS      current
	DESCRIPTION
	"Table entry display string for enrichmentMapOverflow"
	::={enrichmentMapOverflowLevelEntry 1}

enrichmentMapOverflowLevelVal OBJECT-TYPE
	SYNTAX	 Counter64
	MAX-ACCESS  read-only
	STATUS      current
	DESCRIPTION
	"Table entry attribute for enrichmentMapOverflow"
	::={enrichmentMapOverflowLevelEntry 2}

enrichmentMapOverflowLevelMom OBJECT-TYPE
	SYNTAX	 CounterBasedGauge64
	MAX-ACCESS  read-only
	STATUS      current
	DESCRIPTION
	"Table entry attribute for enrichmentMapOverflow"
	::={enrichmentMapOverflowLevelEntry 3}

enrichmentMapOverflowLevelMax OBJECT-TYPE
	SYNTAX	 CounterBasedGauge64
	MAX-ACCESS  read-only
	STATUS      current
	DESCRIPTION
	"Table entry attribute for enrichmentMapOverflow"
	::={enrichmentMapOverflowLevelEntry 4}


enrichmentPacketsToClient	OBJECT IDENTIFIER ::={enrichment 9}

enrichmentPacketsToClientVal	OBJECT-TYPE
	SYNTAX	 Counter64
	MAX-ACCESS read-only
	STATUS current
	DESCRIPTION "Number of packets handled by enrichment (to client)"

	::={enrichmentPacketsToClient 1}

enrichmentPacketsToClientMom	OBJECT-TYPE
	SYNTAX	 CounterBasedGauge64
	MAX-ACCESS read-only
	STATUS current
	DESCRIPTION "Number of packets handled by enrichment (to client)"

	::={enrichmentPacketsToClient 2}

enrichmentPacketsToClientMax	OBJECT-TYPE
	SYNTAX	 CounterBasedGauge64
	MAX-ACCESS read-only
	STATUS current
	DESCRIPTION "Number of packets handled by enrichment (to client)"

	::={enrichmentPacketsToClient 3}

enrichmentPacketsToClientLevelTable OBJECT-TYPE
	SYNTAX      SEQUENCE OF EnrichmentPacketsToClientLevelEntry
	MAX-ACCESS  not-accessible
	STATUS      current
	DESCRIPTION
	"Table for enrichmentPacketsToClient"
	::={enrichmentPacketsToClient 4}

enrichmentPacketsToClientLevelEntry OBJECT-TYPE
	SYNTAX      EnrichmentPacketsToClientLevelEntry
	MAX-ACCESS  not-accessible
	STATUS      current
	DESCRIPTION
	"Table entry for enrichmentPacketsToClient"
	INDEX { enrichmentPacketsToClientLevelName }
	::={enrichmentPacketsToClientLevelTable 1}

EnrichmentPacketsToClientLevelEntry ::=
	SEQUENCE {
		enrichmentPacketsToClientLevelName	DisplayString,
		enrichmentPacketsToClientLevelVal	Counter64,
		enrichmentPacketsToClientLevelMom	CounterBasedGauge64,
		enrichmentPacketsToClientLevelMax	CounterBasedGauge64
	}

enrichmentPacketsToClientLevelName OBJECT-TYPE
	SYNTAX      DisplayString
	MAX-ACCESS  not-accessible
	STATUS      current
	DESCRIPTION
	"Table entry display string for enrichmentPacketsToClient"
	::={enrichmentPacketsToClientLevelEntry 1}

enrichmentPacketsToClientLevelVal OBJECT-TYPE
	SYNTAX	 Counter64
	MAX-ACCESS  read-only
	STATUS      current
	DESCRIPTION
	"Table entry attribute for enrichmentPacketsToClient"
	::={enrichmentPacketsToClientLevelEntry 2}

enrichmentPacketsToClientLevelMom OBJECT-TYPE
	SYNTAX	 CounterBasedGauge64
	MAX-ACCESS  read-only
	STATUS      current
	DESCRIPTION
	"Table entry attribute for enrichmentPacketsToClient"
	::={enrichmentPacketsToClientLevelEntry 3}

enrichmentPacketsToClientLevelMax OBJECT-TYPE
	SYNTAX	 CounterBasedGauge64
	MAX-ACCESS  read-only
	STATUS      current
	DESCRIPTION
	"Table entry attribute for enrichmentPacketsToClient"
	::={enrichmentPacketsToClientLevelEntry 4}


enrichmentPacketsToServer	OBJECT IDENTIFIER ::={enrichment 10}

enrichmentPacketsToServerVal	OBJECT-TYPE
	SYNTAX	 Counter64
	MAX-ACCESS read-only
	STATUS current
	DESCRIPTION "Number of packets handled by enrichment (to server)"

	::={enrichmentPacketsToServer 1}

enrichmentPacketsToServerMom	OBJECT-TYPE
	SYNTAX	 CounterBasedGauge64
	MAX-ACCESS read-only
	STATUS current
	DESCRIPTION "Number of packets handled by enrichment (to server)"

	::={enrichmentPacketsToServer 2}

enrichmentPacketsToServerMax	OBJECT-TYPE
	SYNTAX	 CounterBasedGauge64
	MAX-ACCESS read-only
	STATUS current
	DESCRIPTION "Number of packets handled by enrichment (to server)"

	::={enrichmentPacketsToServer 3}

enrichmentPacketsToServerLevelTable OBJECT-TYPE
	SYNTAX      SEQUENCE OF EnrichmentPacketsToServerLevelEntry
	MAX-ACCESS  not-accessible
	STATUS      current
	DESCRIPTION
	"Table for enrichmentPacketsToServer"
	::={enrichmentPacketsToServer 4}

enrichmentPacketsToServerLevelEntry OBJECT-TYPE
	SYNTAX      EnrichmentPacketsToServerLevelEntry
	MAX-ACCESS  not-accessible
	STATUS      current
	DESCRIPTION
	"Table entry for enrichmentPacketsToServer"
	INDEX { enrichmentPacketsToServerLevelName }
	::={enrichmentPacketsToServerLevelTable 1}

EnrichmentPacketsToServerLevelEntry ::=
	SEQUENCE {
		enrichmentPacketsToServerLevelName	DisplayString,
		enrichmentPacketsToServerLevelVal	Counter64,
		enrichmentPacketsToServerLevelMom	CounterBasedGauge64,
		enrichmentPacketsToServerLevelMax	CounterBasedGauge64
	}

enrichmentPacketsToServerLevelName OBJECT-TYPE
	SYNTAX      DisplayString
	MAX-ACCESS  not-accessible
	STATUS      current
	DESCRIPTION
	"Table entry display string for enrichmentPacketsToServer"
	::={enrichmentPacketsToServerLevelEntry 1}

enrichmentPacketsToServerLevelVal OBJECT-TYPE
	SYNTAX	 Counter64
	MAX-ACCESS  read-only
	STATUS      current
	DESCRIPTION
	"Table entry attribute for enrichmentPacketsToServer"
	::={enrichmentPacketsToServerLevelEntry 2}

enrichmentPacketsToServerLevelMom OBJECT-TYPE
	SYNTAX	 CounterBasedGauge64
	MAX-ACCESS  read-only
	STATUS      current
	DESCRIPTION
	"Table entry attribute for enrichmentPacketsToServer"
	::={enrichmentPacketsToServerLevelEntry 3}

enrichmentPacketsToServerLevelMax OBJECT-TYPE
	SYNTAX	 CounterBasedGauge64
	MAX-ACCESS  read-only
	STATUS      current
	DESCRIPTION
	"Table entry attribute for enrichmentPacketsToServer"
	::={enrichmentPacketsToServerLevelEntry 4}


enrichmentPacketsRetransmitted	OBJECT IDENTIFIER ::={enrichment 11}

enrichmentPacketsRetransmittedVal	OBJECT-TYPE
	SYNTAX	 Counter64
	MAX-ACCESS read-only
	STATUS current
	DESCRIPTION "Number of packets retransmitted"

	::={enrichmentPacketsRetransmitted 1}

enrichmentPacketsRetransmittedMom	OBJECT-TYPE
	SYNTAX	 CounterBasedGauge64
	MAX-ACCESS read-only
	STATUS current
	DESCRIPTION "Number of packets retransmitted"

	::={enrichmentPacketsRetransmitted 2}

enrichmentPacketsRetransmittedMax	OBJECT-TYPE
	SYNTAX	 CounterBasedGauge64
	MAX-ACCESS read-only
	STATUS current
	DESCRIPTION "Number of packets retransmitted"

	::={enrichmentPacketsRetransmitted 3}

enrichmentPacketsRetransmittedLevelTable OBJECT-TYPE
	SYNTAX      SEQUENCE OF EnrichmentPacketsRetransmittedLevelEntry
	MAX-ACCESS  not-accessible
	STATUS      current
	DESCRIPTION
	"Table for enrichmentPacketsRetransmitted"
	::={enrichmentPacketsRetransmitted 4}

enrichmentPacketsRetransmittedLevelEntry OBJECT-TYPE
	SYNTAX      EnrichmentPacketsRetransmittedLevelEntry
	MAX-ACCESS  not-accessible
	STATUS      current
	DESCRIPTION
	"Table entry for enrichmentPacketsRetransmitted"
	INDEX { enrichmentPacketsRetransmittedLevelName }
	::={enrichmentPacketsRetransmittedLevelTable 1}

EnrichmentPacketsRetransmittedLevelEntry ::=
	SEQUENCE {
		enrichmentPacketsRetransmittedLevelName	DisplayString,
		enrichmentPacketsRetransmittedLevelVal	Counter64,
		enrichmentPacketsRetransmittedLevelMom	CounterBasedGauge64,
		enrichmentPacketsRetransmittedLevelMax	CounterBasedGauge64
	}

enrichmentPacketsRetransmittedLevelName OBJECT-TYPE
	SYNTAX      DisplayString
	MAX-ACCESS  not-accessible
	STATUS      current
	DESCRIPTION
	"Table entry display string for enrichmentPacketsRetransmitted"
	::={enrichmentPacketsRetransmittedLevelEntry 1}

enrichmentPacketsRetransmittedLevelVal OBJECT-TYPE
	SYNTAX	 Counter64
	MAX-ACCESS  read-only
	STATUS      current
	DESCRIPTION
	"Table entry attribute for enrichmentPacketsRetransmitted"
	::={enrichmentPacketsRetransmittedLevelEntry 2}

enrichmentPacketsRetransmittedLevelMom OBJECT-TYPE
	SYNTAX	 CounterBasedGauge64
	MAX-ACCESS  read-only
	STATUS      current
	DESCRIPTION
	"Table entry attribute for enrichmentPacketsRetransmitted"
	::={enrichmentPacketsRetransmittedLevelEntry 3}

enrichmentPacketsRetransmittedLevelMax OBJECT-TYPE
	SYNTAX	 CounterBasedGauge64
	MAX-ACCESS  read-only
	STATUS      current
	DESCRIPTION
	"Table entry attribute for enrichmentPacketsRetransmitted"
	::={enrichmentPacketsRetransmittedLevelEntry 4}


enrichmentPacketBufferOverflow	OBJECT IDENTIFIER ::={enrichment 12}

enrichmentPacketBufferOverflowVal	OBJECT-TYPE
	SYNTAX	 Counter64
	MAX-ACCESS read-only
	STATUS current
	DESCRIPTION "Number of packet buffer overflows"

	::={enrichmentPacketBufferOverflow 1}

enrichmentPacketBufferOverflowMom	OBJECT-TYPE
	SYNTAX	 CounterBasedGauge64
	MAX-ACCESS read-only
	STATUS current
	DESCRIPTION "Number of packet buffer overflows"

	::={enrichmentPacketBufferOverflow 2}

enrichmentPacketBufferOverflowMax	OBJECT-TYPE
	SYNTAX	 CounterBasedGauge64
	MAX-ACCESS read-only
	STATUS current
	DESCRIPTION "Number of packet buffer overflows"

	::={enrichmentPacketBufferOverflow 3}

enrichmentPacketBufferOverflowLevelTable OBJECT-TYPE
	SYNTAX      SEQUENCE OF EnrichmentPacketBufferOverflowLevelEntry
	MAX-ACCESS  not-accessible
	STATUS      current
	DESCRIPTION
	"Table for enrichmentPacketBufferOverflow"
	::={enrichmentPacketBufferOverflow 4}

enrichmentPacketBufferOverflowLevelEntry OBJECT-TYPE
	SYNTAX      EnrichmentPacketBufferOverflowLevelEntry
	MAX-ACCESS  not-accessible
	STATUS      current
	DESCRIPTION
	"Table entry for enrichmentPacketBufferOverflow"
	INDEX { enrichmentPacketBufferOverflowLevelName }
	::={enrichmentPacketBufferOverflowLevelTable 1}

EnrichmentPacketBufferOverflowLevelEntry ::=
	SEQUENCE {
		enrichmentPacketBufferOverflowLevelName	DisplayString,
		enrichmentPacketBufferOverflowLevelVal	Counter64,
		enrichmentPacketBufferOverflowLevelMom	CounterBasedGauge64,
		enrichmentPacketBufferOverflowLevelMax	CounterBasedGauge64
	}

enrichmentPacketBufferOverflowLevelName OBJECT-TYPE
	SYNTAX      DisplayString
	MAX-ACCESS  not-accessible
	STATUS      current
	DESCRIPTION
	"Table entry display string for enrichmentPacketBufferOverflow"
	::={enrichmentPacketBufferOverflowLevelEntry 1}

enrichmentPacketBufferOverflowLevelVal OBJECT-TYPE
	SYNTAX	 Counter64
	MAX-ACCESS  read-only
	STATUS      current
	DESCRIPTION
	"Table entry attribute for enrichmentPacketBufferOverflow"
	::={enrichmentPacketBufferOverflowLevelEntry 2}

enrichmentPacketBufferOverflowLevelMom OBJECT-TYPE
	SYNTAX	 CounterBasedGauge64
	MAX-ACCESS  read-only
	STATUS      current
	DESCRIPTION
	"Table entry attribute for enrichmentPacketBufferOverflow"
	::={enrichmentPacketBufferOverflowLevelEntry 3}

enrichmentPacketBufferOverflowLevelMax OBJECT-TYPE
	SYNTAX	 CounterBasedGauge64
	MAX-ACCESS  read-only
	STATUS      current
	DESCRIPTION
	"Table entry attribute for enrichmentPacketBufferOverflow"
	::={enrichmentPacketBufferOverflowLevelEntry 4}


enrichmentPacketsBuffered	OBJECT IDENTIFIER ::={enrichment 13}

enrichmentPacketsBufferedVal	OBJECT-TYPE
	SYNTAX	 CounterBasedGauge64
	MAX-ACCESS read-only
	STATUS current
	DESCRIPTION "Number of packets buffered"

	::={enrichmentPacketsBuffered 1}

enrichmentPacketsBufferedMax	OBJECT-TYPE
	SYNTAX	 CounterBasedGauge64
	MAX-ACCESS read-only
	STATUS current
	DESCRIPTION "Number of packets buffered"

	::={enrichmentPacketsBuffered 3}

enrichmentPacketsBufferedLevelTable OBJECT-TYPE
	SYNTAX      SEQUENCE OF EnrichmentPacketsBufferedLevelEntry
	MAX-ACCESS  not-accessible
	STATUS      current
	DESCRIPTION
	"Table for enrichmentPacketsBuffered"
	::={enrichmentPacketsBuffered 4}

enrichmentPacketsBufferedLevelEntry OBJECT-TYPE
	SYNTAX      EnrichmentPacketsBufferedLevelEntry
	MAX-ACCESS  not-accessible
	STATUS      current
	DESCRIPTION
	"Table entry for enrichmentPacketsBuffered"
	INDEX { enrichmentPacketsBufferedLevelName }
	::={enrichmentPacketsBufferedLevelTable 1}

EnrichmentPacketsBufferedLevelEntry ::=
	SEQUENCE {
		enrichmentPacketsBufferedLevelName	DisplayString,
		enrichmentPacketsBufferedLevelVal	CounterBasedGauge64,
		enrichmentPacketsBufferedLevelMax	CounterBasedGauge64
	}

enrichmentPacketsBufferedLevelName OBJECT-TYPE
	SYNTAX      DisplayString
	MAX-ACCESS  not-accessible
	STATUS      current
	DESCRIPTION
	"Table entry display string for enrichmentPacketsBuffered"
	::={enrichmentPacketsBufferedLevelEntry 1}

enrichmentPacketsBufferedLevelVal OBJECT-TYPE
	SYNTAX	 CounterBasedGauge64
	MAX-ACCESS  read-only
	STATUS      current
	DESCRIPTION
	"Table entry attribute for enrichmentPacketsBuffered"
	::={enrichmentPacketsBufferedLevelEntry 2}

enrichmentPacketsBufferedLevelMax OBJECT-TYPE
	SYNTAX	 CounterBasedGauge64
	MAX-ACCESS  read-only
	STATUS      current
	DESCRIPTION
	"Table entry attribute for enrichmentPacketsBuffered"
	::={enrichmentPacketsBufferedLevelEntry 4}


enrichmentHeaderInsert	OBJECT IDENTIFIER ::={enrichment 14}

enrichmentHeaderInsertVal	OBJECT-TYPE
	SYNTAX	 Counter64
	MAX-ACCESS read-only
	STATUS current
	DESCRIPTION "Number of headers inserted"

	::={enrichmentHeaderInsert 1}

enrichmentHeaderInsertMom	OBJECT-TYPE
	SYNTAX	 CounterBasedGauge64
	MAX-ACCESS read-only
	STATUS current
	DESCRIPTION "Number of headers inserted"

	::={enrichmentHeaderInsert 2}

enrichmentHeaderInsertMax	OBJECT-TYPE
	SYNTAX	 CounterBasedGauge64
	MAX-ACCESS read-only
	STATUS current
	DESCRIPTION "Number of headers inserted"

	::={enrichmentHeaderInsert 3}

enrichmentHeaderInsertLevelTable OBJECT-TYPE
	SYNTAX      SEQUENCE OF EnrichmentHeaderInsertLevelEntry
	MAX-ACCESS  not-accessible
	STATUS      current
	DESCRIPTION
	"Table for enrichmentHeaderInsert"
	::={enrichmentHeaderInsert 4}

enrichmentHeaderInsertLevelEntry OBJECT-TYPE
	SYNTAX      EnrichmentHeaderInsertLevelEntry
	MAX-ACCESS  not-accessible
	STATUS      current
	DESCRIPTION
	"Table entry for enrichmentHeaderInsert"
	INDEX { enrichmentHeaderInsertLevelName }
	::={enrichmentHeaderInsertLevelTable 1}

EnrichmentHeaderInsertLevelEntry ::=
	SEQUENCE {
		enrichmentHeaderInsertLevelName	DisplayString,
		enrichmentHeaderInsertLevelVal	Counter64,
		enrichmentHeaderInsertLevelMom	CounterBasedGauge64,
		enrichmentHeaderInsertLevelMax	CounterBasedGauge64
	}

enrichmentHeaderInsertLevelName OBJECT-TYPE
	SYNTAX      DisplayString
	MAX-ACCESS  not-accessible
	STATUS      current
	DESCRIPTION
	"Table entry display string for enrichmentHeaderInsert"
	::={enrichmentHeaderInsertLevelEntry 1}

enrichmentHeaderInsertLevelVal OBJECT-TYPE
	SYNTAX	 Counter64
	MAX-ACCESS  read-only
	STATUS      current
	DESCRIPTION
	"Table entry attribute for enrichmentHeaderInsert"
	::={enrichmentHeaderInsertLevelEntry 2}

enrichmentHeaderInsertLevelMom OBJECT-TYPE
	SYNTAX	 CounterBasedGauge64
	MAX-ACCESS  read-only
	STATUS      current
	DESCRIPTION
	"Table entry attribute for enrichmentHeaderInsert"
	::={enrichmentHeaderInsertLevelEntry 3}

enrichmentHeaderInsertLevelMax OBJECT-TYPE
	SYNTAX	 CounterBasedGauge64
	MAX-ACCESS  read-only
	STATUS      current
	DESCRIPTION
	"Table entry attribute for enrichmentHeaderInsert"
	::={enrichmentHeaderInsertLevelEntry 4}


enrichmentOutOfBufferSpace	OBJECT IDENTIFIER ::={enrichment 15}

enrichmentOutOfBufferSpaceVal	OBJECT-TYPE
	SYNTAX	 Counter64
	MAX-ACCESS read-only
	STATUS current
	DESCRIPTION "Out of temporary buffer space"

	::={enrichmentOutOfBufferSpace 1}

enrichmentOutOfBufferSpaceMom	OBJECT-TYPE
	SYNTAX	 CounterBasedGauge64
	MAX-ACCESS read-only
	STATUS current
	DESCRIPTION "Out of temporary buffer space"

	::={enrichmentOutOfBufferSpace 2}

enrichmentOutOfBufferSpaceMax	OBJECT-TYPE
	SYNTAX	 CounterBasedGauge64
	MAX-ACCESS read-only
	STATUS current
	DESCRIPTION "Out of temporary buffer space"

	::={enrichmentOutOfBufferSpace 3}

enrichmentOutOfBufferSpaceLevelTable OBJECT-TYPE
	SYNTAX      SEQUENCE OF EnrichmentOutOfBufferSpaceLevelEntry
	MAX-ACCESS  not-accessible
	STATUS      current
	DESCRIPTION
	"Table for enrichmentOutOfBufferSpace"
	::={enrichmentOutOfBufferSpace 4}

enrichmentOutOfBufferSpaceLevelEntry OBJECT-TYPE
	SYNTAX      EnrichmentOutOfBufferSpaceLevelEntry
	MAX-ACCESS  not-accessible
	STATUS      current
	DESCRIPTION
	"Table entry for enrichmentOutOfBufferSpace"
	INDEX { enrichmentOutOfBufferSpaceLevelName }
	::={enrichmentOutOfBufferSpaceLevelTable 1}

EnrichmentOutOfBufferSpaceLevelEntry ::=
	SEQUENCE {
		enrichmentOutOfBufferSpaceLevelName	DisplayString,
		enrichmentOutOfBufferSpaceLevelVal	Counter64,
		enrichmentOutOfBufferSpaceLevelMom	CounterBasedGauge64,
		enrichmentOutOfBufferSpaceLevelMax	CounterBasedGauge64
	}

enrichmentOutOfBufferSpaceLevelName OBJECT-TYPE
	SYNTAX      DisplayString
	MAX-ACCESS  not-accessible
	STATUS      current
	DESCRIPTION
	"Table entry display string for enrichmentOutOfBufferSpace"
	::={enrichmentOutOfBufferSpaceLevelEntry 1}

enrichmentOutOfBufferSpaceLevelVal OBJECT-TYPE
	SYNTAX	 Counter64
	MAX-ACCESS  read-only
	STATUS      current
	DESCRIPTION
	"Table entry attribute for enrichmentOutOfBufferSpace"
	::={enrichmentOutOfBufferSpaceLevelEntry 2}

enrichmentOutOfBufferSpaceLevelMom OBJECT-TYPE
	SYNTAX	 CounterBasedGauge64
	MAX-ACCESS  read-only
	STATUS      current
	DESCRIPTION
	"Table entry attribute for enrichmentOutOfBufferSpace"
	::={enrichmentOutOfBufferSpaceLevelEntry 3}

enrichmentOutOfBufferSpaceLevelMax OBJECT-TYPE
	SYNTAX	 CounterBasedGauge64
	MAX-ACCESS  read-only
	STATUS      current
	DESCRIPTION
	"Table entry attribute for enrichmentOutOfBufferSpace"
	::={enrichmentOutOfBufferSpaceLevelEntry 4}


webliveview	OBJECT IDENTIFIER ::={sysdiag 144}

webliveviewUptime	OBJECT IDENTIFIER ::={webliveview 1}

webliveviewUptimeVal	OBJECT-TYPE
	SYNTAX	 TimeTicks
	MAX-ACCESS read-only
	STATUS current
	DESCRIPTION "Uptime"

	::={webliveviewUptime 1}

webliveviewUptimeLevelTable OBJECT-TYPE
	SYNTAX      SEQUENCE OF WebliveviewUptimeLevelEntry
	MAX-ACCESS  not-accessible
	STATUS      current
	DESCRIPTION
	"Table for webliveviewUptime"
	::={webliveviewUptime 2}

webliveviewUptimeLevelEntry OBJECT-TYPE
	SYNTAX      WebliveviewUptimeLevelEntry
	MAX-ACCESS  not-accessible
	STATUS      current
	DESCRIPTION
	"Table entry for webliveviewUptime"
	INDEX { webliveviewUptimeLevelName }
	::={webliveviewUptimeLevelTable 1}

WebliveviewUptimeLevelEntry ::=
	SEQUENCE {
		webliveviewUptimeLevelName	DisplayString,
		webliveviewUptimeLevelVal	TimeTicks
	}

webliveviewUptimeLevelName OBJECT-TYPE
	SYNTAX      DisplayString
	MAX-ACCESS  not-accessible
	STATUS      current
	DESCRIPTION
	"Table entry display string for webliveviewUptime"
	::={webliveviewUptimeLevelEntry 1}

webliveviewUptimeLevelVal OBJECT-TYPE
	SYNTAX	 TimeTicks
	MAX-ACCESS  read-only
	STATUS      current
	DESCRIPTION
	"Table entry attribute for webliveviewUptime"
	::={webliveviewUptimeLevelEntry 2}


webliveviewHttpConnections	OBJECT IDENTIFIER ::={webliveview 2}

webliveviewHttpConnectionsVal	OBJECT-TYPE
	SYNTAX	 CounterBasedGauge64
	MAX-ACCESS read-only
	STATUS current
	DESCRIPTION "Number of http connections"

	::={webliveviewHttpConnections 1}

webliveviewHttpConnectionsMax	OBJECT-TYPE
	SYNTAX	 CounterBasedGauge64
	MAX-ACCESS read-only
	STATUS current
	DESCRIPTION "Number of http connections"

	::={webliveviewHttpConnections 3}

webliveviewHttpConnectionsLevelTable OBJECT-TYPE
	SYNTAX      SEQUENCE OF WebliveviewHttpConnectionsLevelEntry
	MAX-ACCESS  not-accessible
	STATUS      current
	DESCRIPTION
	"Table for webliveviewHttpConnections"
	::={webliveviewHttpConnections 4}

webliveviewHttpConnectionsLevelEntry OBJECT-TYPE
	SYNTAX      WebliveviewHttpConnectionsLevelEntry
	MAX-ACCESS  not-accessible
	STATUS      current
	DESCRIPTION
	"Table entry for webliveviewHttpConnections"
	INDEX { webliveviewHttpConnectionsLevelName }
	::={webliveviewHttpConnectionsLevelTable 1}

WebliveviewHttpConnectionsLevelEntry ::=
	SEQUENCE {
		webliveviewHttpConnectionsLevelName	DisplayString,
		webliveviewHttpConnectionsLevelVal	CounterBasedGauge64,
		webliveviewHttpConnectionsLevelMax	CounterBasedGauge64
	}

webliveviewHttpConnectionsLevelName OBJECT-TYPE
	SYNTAX      DisplayString
	MAX-ACCESS  not-accessible
	STATUS      current
	DESCRIPTION
	"Table entry display string for webliveviewHttpConnections"
	::={webliveviewHttpConnectionsLevelEntry 1}

webliveviewHttpConnectionsLevelVal OBJECT-TYPE
	SYNTAX	 CounterBasedGauge64
	MAX-ACCESS  read-only
	STATUS      current
	DESCRIPTION
	"Table entry attribute for webliveviewHttpConnections"
	::={webliveviewHttpConnectionsLevelEntry 2}

webliveviewHttpConnectionsLevelMax OBJECT-TYPE
	SYNTAX	 CounterBasedGauge64
	MAX-ACCESS  read-only
	STATUS      current
	DESCRIPTION
	"Table entry attribute for webliveviewHttpConnections"
	::={webliveviewHttpConnectionsLevelEntry 4}


webliveviewWebsockets	OBJECT IDENTIFIER ::={webliveview 3}

webliveviewWebsocketsVal	OBJECT-TYPE
	SYNTAX	 CounterBasedGauge64
	MAX-ACCESS read-only
	STATUS current
	DESCRIPTION "Number of web sockets"

	::={webliveviewWebsockets 1}

webliveviewWebsocketsMax	OBJECT-TYPE
	SYNTAX	 CounterBasedGauge64
	MAX-ACCESS read-only
	STATUS current
	DESCRIPTION "Number of web sockets"

	::={webliveviewWebsockets 3}

webliveviewWebsocketsLevelTable OBJECT-TYPE
	SYNTAX      SEQUENCE OF WebliveviewWebsocketsLevelEntry
	MAX-ACCESS  not-accessible
	STATUS      current
	DESCRIPTION
	"Table for webliveviewWebsockets"
	::={webliveviewWebsockets 4}

webliveviewWebsocketsLevelEntry OBJECT-TYPE
	SYNTAX      WebliveviewWebsocketsLevelEntry
	MAX-ACCESS  not-accessible
	STATUS      current
	DESCRIPTION
	"Table entry for webliveviewWebsockets"
	INDEX { webliveviewWebsocketsLevelName }
	::={webliveviewWebsocketsLevelTable 1}

WebliveviewWebsocketsLevelEntry ::=
	SEQUENCE {
		webliveviewWebsocketsLevelName	DisplayString,
		webliveviewWebsocketsLevelVal	CounterBasedGauge64,
		webliveviewWebsocketsLevelMax	CounterBasedGauge64
	}

webliveviewWebsocketsLevelName OBJECT-TYPE
	SYNTAX      DisplayString
	MAX-ACCESS  not-accessible
	STATUS      current
	DESCRIPTION
	"Table entry display string for webliveviewWebsockets"
	::={webliveviewWebsocketsLevelEntry 1}

webliveviewWebsocketsLevelVal OBJECT-TYPE
	SYNTAX	 CounterBasedGauge64
	MAX-ACCESS  read-only
	STATUS      current
	DESCRIPTION
	"Table entry attribute for webliveviewWebsockets"
	::={webliveviewWebsocketsLevelEntry 2}

webliveviewWebsocketsLevelMax OBJECT-TYPE
	SYNTAX	 CounterBasedGauge64
	MAX-ACCESS  read-only
	STATUS      current
	DESCRIPTION
	"Table entry attribute for webliveviewWebsockets"
	::={webliveviewWebsocketsLevelEntry 4}


webliveviewViews	OBJECT IDENTIFIER ::={webliveview 4}

webliveviewViewsVal	OBJECT-TYPE
	SYNTAX	 CounterBasedGauge64
	MAX-ACCESS read-only
	STATUS current
	DESCRIPTION "Number of views"

	::={webliveviewViews 1}

webliveviewViewsMax	OBJECT-TYPE
	SYNTAX	 CounterBasedGauge64
	MAX-ACCESS read-only
	STATUS current
	DESCRIPTION "Number of views"

	::={webliveviewViews 3}

webliveviewViewsLevelTable OBJECT-TYPE
	SYNTAX      SEQUENCE OF WebliveviewViewsLevelEntry
	MAX-ACCESS  not-accessible
	STATUS      current
	DESCRIPTION
	"Table for webliveviewViews"
	::={webliveviewViews 4}

webliveviewViewsLevelEntry OBJECT-TYPE
	SYNTAX      WebliveviewViewsLevelEntry
	MAX-ACCESS  not-accessible
	STATUS      current
	DESCRIPTION
	"Table entry for webliveviewViews"
	INDEX { webliveviewViewsLevelName }
	::={webliveviewViewsLevelTable 1}

WebliveviewViewsLevelEntry ::=
	SEQUENCE {
		webliveviewViewsLevelName	DisplayString,
		webliveviewViewsLevelVal	CounterBasedGauge64,
		webliveviewViewsLevelMax	CounterBasedGauge64
	}

webliveviewViewsLevelName OBJECT-TYPE
	SYNTAX      DisplayString
	MAX-ACCESS  not-accessible
	STATUS      current
	DESCRIPTION
	"Table entry display string for webliveviewViews"
	::={webliveviewViewsLevelEntry 1}

webliveviewViewsLevelVal OBJECT-TYPE
	SYNTAX	 CounterBasedGauge64
	MAX-ACCESS  read-only
	STATUS      current
	DESCRIPTION
	"Table entry attribute for webliveviewViews"
	::={webliveviewViewsLevelEntry 2}

webliveviewViewsLevelMax OBJECT-TYPE
	SYNTAX	 CounterBasedGauge64
	MAX-ACCESS  read-only
	STATUS      current
	DESCRIPTION
	"Table entry attribute for webliveviewViews"
	::={webliveviewViewsLevelEntry 4}


webliveviewViewUpdates	OBJECT IDENTIFIER ::={webliveview 5}

webliveviewViewUpdatesVal	OBJECT-TYPE
	SYNTAX	 Counter64
	MAX-ACCESS read-only
	STATUS current
	DESCRIPTION "Number of view updates received"

	::={webliveviewViewUpdates 1}

webliveviewViewUpdatesMom	OBJECT-TYPE
	SYNTAX	 CounterBasedGauge64
	MAX-ACCESS read-only
	STATUS current
	DESCRIPTION "Number of view updates received"

	::={webliveviewViewUpdates 2}

webliveviewViewUpdatesMax	OBJECT-TYPE
	SYNTAX	 CounterBasedGauge64
	MAX-ACCESS read-only
	STATUS current
	DESCRIPTION "Number of view updates received"

	::={webliveviewViewUpdates 3}

webliveviewViewUpdatesLevelTable OBJECT-TYPE
	SYNTAX      SEQUENCE OF WebliveviewViewUpdatesLevelEntry
	MAX-ACCESS  not-accessible
	STATUS      current
	DESCRIPTION
	"Table for webliveviewViewUpdates"
	::={webliveviewViewUpdates 4}

webliveviewViewUpdatesLevelEntry OBJECT-TYPE
	SYNTAX      WebliveviewViewUpdatesLevelEntry
	MAX-ACCESS  not-accessible
	STATUS      current
	DESCRIPTION
	"Table entry for webliveviewViewUpdates"
	INDEX { webliveviewViewUpdatesLevelName }
	::={webliveviewViewUpdatesLevelTable 1}

WebliveviewViewUpdatesLevelEntry ::=
	SEQUENCE {
		webliveviewViewUpdatesLevelName	DisplayString,
		webliveviewViewUpdatesLevelVal	Counter64,
		webliveviewViewUpdatesLevelMom	CounterBasedGauge64,
		webliveviewViewUpdatesLevelMax	CounterBasedGauge64
	}

webliveviewViewUpdatesLevelName OBJECT-TYPE
	SYNTAX      DisplayString
	MAX-ACCESS  not-accessible
	STATUS      current
	DESCRIPTION
	"Table entry display string for webliveviewViewUpdates"
	::={webliveviewViewUpdatesLevelEntry 1}

webliveviewViewUpdatesLevelVal OBJECT-TYPE
	SYNTAX	 Counter64
	MAX-ACCESS  read-only
	STATUS      current
	DESCRIPTION
	"Table entry attribute for webliveviewViewUpdates"
	::={webliveviewViewUpdatesLevelEntry 2}

webliveviewViewUpdatesLevelMom OBJECT-TYPE
	SYNTAX	 CounterBasedGauge64
	MAX-ACCESS  read-only
	STATUS      current
	DESCRIPTION
	"Table entry attribute for webliveviewViewUpdates"
	::={webliveviewViewUpdatesLevelEntry 3}

webliveviewViewUpdatesLevelMax OBJECT-TYPE
	SYNTAX	 CounterBasedGauge64
	MAX-ACCESS  read-only
	STATUS      current
	DESCRIPTION
	"Table entry attribute for webliveviewViewUpdates"
	::={webliveviewViewUpdatesLevelEntry 4}


webliveviewObjectUpdates	OBJECT IDENTIFIER ::={webliveview 6}

webliveviewObjectUpdatesVal	OBJECT-TYPE
	SYNTAX	 Counter64
	MAX-ACCESS read-only
	STATUS current
	DESCRIPTION "Number of netobject/serviceobject updates received"

	::={webliveviewObjectUpdates 1}

webliveviewObjectUpdatesMom	OBJECT-TYPE
	SYNTAX	 CounterBasedGauge64
	MAX-ACCESS read-only
	STATUS current
	DESCRIPTION "Number of netobject/serviceobject updates received"

	::={webliveviewObjectUpdates 2}

webliveviewObjectUpdatesMax	OBJECT-TYPE
	SYNTAX	 CounterBasedGauge64
	MAX-ACCESS read-only
	STATUS current
	DESCRIPTION "Number of netobject/serviceobject updates received"

	::={webliveviewObjectUpdates 3}

webliveviewObjectUpdatesLevelTable OBJECT-TYPE
	SYNTAX      SEQUENCE OF WebliveviewObjectUpdatesLevelEntry
	MAX-ACCESS  not-accessible
	STATUS      current
	DESCRIPTION
	"Table for webliveviewObjectUpdates"
	::={webliveviewObjectUpdates 4}

webliveviewObjectUpdatesLevelEntry OBJECT-TYPE
	SYNTAX      WebliveviewObjectUpdatesLevelEntry
	MAX-ACCESS  not-accessible
	STATUS      current
	DESCRIPTION
	"Table entry for webliveviewObjectUpdates"
	INDEX { webliveviewObjectUpdatesLevelName }
	::={webliveviewObjectUpdatesLevelTable 1}

WebliveviewObjectUpdatesLevelEntry ::=
	SEQUENCE {
		webliveviewObjectUpdatesLevelName	DisplayString,
		webliveviewObjectUpdatesLevelVal	Counter64,
		webliveviewObjectUpdatesLevelMom	CounterBasedGauge64,
		webliveviewObjectUpdatesLevelMax	CounterBasedGauge64
	}

webliveviewObjectUpdatesLevelName OBJECT-TYPE
	SYNTAX      DisplayString
	MAX-ACCESS  not-accessible
	STATUS      current
	DESCRIPTION
	"Table entry display string for webliveviewObjectUpdates"
	::={webliveviewObjectUpdatesLevelEntry 1}

webliveviewObjectUpdatesLevelVal OBJECT-TYPE
	SYNTAX	 Counter64
	MAX-ACCESS  read-only
	STATUS      current
	DESCRIPTION
	"Table entry attribute for webliveviewObjectUpdates"
	::={webliveviewObjectUpdatesLevelEntry 2}

webliveviewObjectUpdatesLevelMom OBJECT-TYPE
	SYNTAX	 CounterBasedGauge64
	MAX-ACCESS  read-only
	STATUS      current
	DESCRIPTION
	"Table entry attribute for webliveviewObjectUpdates"
	::={webliveviewObjectUpdatesLevelEntry 3}

webliveviewObjectUpdatesLevelMax OBJECT-TYPE
	SYNTAX	 CounterBasedGauge64
	MAX-ACCESS  read-only
	STATUS      current
	DESCRIPTION
	"Table entry attribute for webliveviewObjectUpdates"
	::={webliveviewObjectUpdatesLevelEntry 4}


webliveviewHttpFileRequests	OBJECT IDENTIFIER ::={webliveview 7}

webliveviewHttpFileRequestsVal	OBJECT-TYPE
	SYNTAX	 Counter64
	MAX-ACCESS read-only
	STATUS current
	DESCRIPTION "Number of http file requests received"

	::={webliveviewHttpFileRequests 1}

webliveviewHttpFileRequestsMom	OBJECT-TYPE
	SYNTAX	 CounterBasedGauge64
	MAX-ACCESS read-only
	STATUS current
	DESCRIPTION "Number of http file requests received"

	::={webliveviewHttpFileRequests 2}

webliveviewHttpFileRequestsMax	OBJECT-TYPE
	SYNTAX	 CounterBasedGauge64
	MAX-ACCESS read-only
	STATUS current
	DESCRIPTION "Number of http file requests received"

	::={webliveviewHttpFileRequests 3}

webliveviewHttpFileRequestsLevelTable OBJECT-TYPE
	SYNTAX      SEQUENCE OF WebliveviewHttpFileRequestsLevelEntry
	MAX-ACCESS  not-accessible
	STATUS      current
	DESCRIPTION
	"Table for webliveviewHttpFileRequests"
	::={webliveviewHttpFileRequests 4}

webliveviewHttpFileRequestsLevelEntry OBJECT-TYPE
	SYNTAX      WebliveviewHttpFileRequestsLevelEntry
	MAX-ACCESS  not-accessible
	STATUS      current
	DESCRIPTION
	"Table entry for webliveviewHttpFileRequests"
	INDEX { webliveviewHttpFileRequestsLevelName }
	::={webliveviewHttpFileRequestsLevelTable 1}

WebliveviewHttpFileRequestsLevelEntry ::=
	SEQUENCE {
		webliveviewHttpFileRequestsLevelName	DisplayString,
		webliveviewHttpFileRequestsLevelVal	Counter64,
		webliveviewHttpFileRequestsLevelMom	CounterBasedGauge64,
		webliveviewHttpFileRequestsLevelMax	CounterBasedGauge64
	}

webliveviewHttpFileRequestsLevelName OBJECT-TYPE
	SYNTAX      DisplayString
	MAX-ACCESS  not-accessible
	STATUS      current
	DESCRIPTION
	"Table entry display string for webliveviewHttpFileRequests"
	::={webliveviewHttpFileRequestsLevelEntry 1}

webliveviewHttpFileRequestsLevelVal OBJECT-TYPE
	SYNTAX	 Counter64
	MAX-ACCESS  read-only
	STATUS      current
	DESCRIPTION
	"Table entry attribute for webliveviewHttpFileRequests"
	::={webliveviewHttpFileRequestsLevelEntry 2}

webliveviewHttpFileRequestsLevelMom OBJECT-TYPE
	SYNTAX	 CounterBasedGauge64
	MAX-ACCESS  read-only
	STATUS      current
	DESCRIPTION
	"Table entry attribute for webliveviewHttpFileRequests"
	::={webliveviewHttpFileRequestsLevelEntry 3}

webliveviewHttpFileRequestsLevelMax OBJECT-TYPE
	SYNTAX	 CounterBasedGauge64
	MAX-ACCESS  read-only
	STATUS      current
	DESCRIPTION
	"Table entry attribute for webliveviewHttpFileRequests"
	::={webliveviewHttpFileRequestsLevelEntry 4}


webliveviewUpgradeRequests	OBJECT IDENTIFIER ::={webliveview 8}

webliveviewUpgradeRequestsVal	OBJECT-TYPE
	SYNTAX	 Counter64
	MAX-ACCESS read-only
	STATUS current
	DESCRIPTION "Number of http upgrade requests received"

	::={webliveviewUpgradeRequests 1}

webliveviewUpgradeRequestsMom	OBJECT-TYPE
	SYNTAX	 CounterBasedGauge64
	MAX-ACCESS read-only
	STATUS current
	DESCRIPTION "Number of http upgrade requests received"

	::={webliveviewUpgradeRequests 2}

webliveviewUpgradeRequestsMax	OBJECT-TYPE
	SYNTAX	 CounterBasedGauge64
	MAX-ACCESS read-only
	STATUS current
	DESCRIPTION "Number of http upgrade requests received"

	::={webliveviewUpgradeRequests 3}

webliveviewUpgradeRequestsLevelTable OBJECT-TYPE
	SYNTAX      SEQUENCE OF WebliveviewUpgradeRequestsLevelEntry
	MAX-ACCESS  not-accessible
	STATUS      current
	DESCRIPTION
	"Table for webliveviewUpgradeRequests"
	::={webliveviewUpgradeRequests 4}

webliveviewUpgradeRequestsLevelEntry OBJECT-TYPE
	SYNTAX      WebliveviewUpgradeRequestsLevelEntry
	MAX-ACCESS  not-accessible
	STATUS      current
	DESCRIPTION
	"Table entry for webliveviewUpgradeRequests"
	INDEX { webliveviewUpgradeRequestsLevelName }
	::={webliveviewUpgradeRequestsLevelTable 1}

WebliveviewUpgradeRequestsLevelEntry ::=
	SEQUENCE {
		webliveviewUpgradeRequestsLevelName	DisplayString,
		webliveviewUpgradeRequestsLevelVal	Counter64,
		webliveviewUpgradeRequestsLevelMom	CounterBasedGauge64,
		webliveviewUpgradeRequestsLevelMax	CounterBasedGauge64
	}

webliveviewUpgradeRequestsLevelName OBJECT-TYPE
	SYNTAX      DisplayString
	MAX-ACCESS  not-accessible
	STATUS      current
	DESCRIPTION
	"Table entry display string for webliveviewUpgradeRequests"
	::={webliveviewUpgradeRequestsLevelEntry 1}

webliveviewUpgradeRequestsLevelVal OBJECT-TYPE
	SYNTAX	 Counter64
	MAX-ACCESS  read-only
	STATUS      current
	DESCRIPTION
	"Table entry attribute for webliveviewUpgradeRequests"
	::={webliveviewUpgradeRequestsLevelEntry 2}

webliveviewUpgradeRequestsLevelMom OBJECT-TYPE
	SYNTAX	 CounterBasedGauge64
	MAX-ACCESS  read-only
	STATUS      current
	DESCRIPTION
	"Table entry attribute for webliveviewUpgradeRequests"
	::={webliveviewUpgradeRequestsLevelEntry 3}

webliveviewUpgradeRequestsLevelMax OBJECT-TYPE
	SYNTAX	 CounterBasedGauge64
	MAX-ACCESS  read-only
	STATUS      current
	DESCRIPTION
	"Table entry attribute for webliveviewUpgradeRequests"
	::={webliveviewUpgradeRequestsLevelEntry 4}


webliveviewStringCacheUsage	OBJECT IDENTIFIER ::={webliveview 9}

webliveviewStringCacheUsageVal	OBJECT-TYPE
	SYNTAX	 CounterBasedGauge64
	MAX-ACCESS read-only
	STATUS current
	DESCRIPTION "String cache usage"

	::={webliveviewStringCacheUsage 1}

webliveviewStringCacheUsageMax	OBJECT-TYPE
	SYNTAX	 CounterBasedGauge64
	MAX-ACCESS read-only
	STATUS current
	DESCRIPTION "String cache usage"

	::={webliveviewStringCacheUsage 3}

webliveviewStringCacheUsageLevelTable OBJECT-TYPE
	SYNTAX      SEQUENCE OF WebliveviewStringCacheUsageLevelEntry
	MAX-ACCESS  not-accessible
	STATUS      current
	DESCRIPTION
	"Table for webliveviewStringCacheUsage"
	::={webliveviewStringCacheUsage 4}

webliveviewStringCacheUsageLevelEntry OBJECT-TYPE
	SYNTAX      WebliveviewStringCacheUsageLevelEntry
	MAX-ACCESS  not-accessible
	STATUS      current
	DESCRIPTION
	"Table entry for webliveviewStringCacheUsage"
	INDEX { webliveviewStringCacheUsageLevelName }
	::={webliveviewStringCacheUsageLevelTable 1}

WebliveviewStringCacheUsageLevelEntry ::=
	SEQUENCE {
		webliveviewStringCacheUsageLevelName	DisplayString,
		webliveviewStringCacheUsageLevelVal	CounterBasedGauge64,
		webliveviewStringCacheUsageLevelMax	CounterBasedGauge64
	}

webliveviewStringCacheUsageLevelName OBJECT-TYPE
	SYNTAX      DisplayString
	MAX-ACCESS  not-accessible
	STATUS      current
	DESCRIPTION
	"Table entry display string for webliveviewStringCacheUsage"
	::={webliveviewStringCacheUsageLevelEntry 1}

webliveviewStringCacheUsageLevelVal OBJECT-TYPE
	SYNTAX	 CounterBasedGauge64
	MAX-ACCESS  read-only
	STATUS      current
	DESCRIPTION
	"Table entry attribute for webliveviewStringCacheUsage"
	::={webliveviewStringCacheUsageLevelEntry 2}

webliveviewStringCacheUsageLevelMax OBJECT-TYPE
	SYNTAX	 CounterBasedGauge64
	MAX-ACCESS  read-only
	STATUS      current
	DESCRIPTION
	"Table entry attribute for webliveviewStringCacheUsage"
	::={webliveviewStringCacheUsageLevelEntry 4}


insights	OBJECT IDENTIFIER ::={sysdiag 145}

insightsTrafficRecordsQueued	OBJECT IDENTIFIER ::={insights 1}

insightsTrafficRecordsQueuedVal	OBJECT-TYPE
	SYNTAX	 Counter64
	MAX-ACCESS read-only
	STATUS obsolete
	DESCRIPTION "Traffic: Records queued"

	::={insightsTrafficRecordsQueued 1}

insightsTrafficRecordsQueuedMom	OBJECT-TYPE
	SYNTAX	 CounterBasedGauge64
	MAX-ACCESS read-only
	STATUS obsolete
	DESCRIPTION "Traffic: Records queued"

	::={insightsTrafficRecordsQueued 2}

insightsTrafficRecordsQueuedMax	OBJECT-TYPE
	SYNTAX	 CounterBasedGauge64
	MAX-ACCESS read-only
	STATUS obsolete
	DESCRIPTION "Traffic: Records queued"

	::={insightsTrafficRecordsQueued 3}

insightsTrafficRecordsQueuedLevelTable OBJECT-TYPE
	SYNTAX      SEQUENCE OF InsightsTrafficRecordsQueuedLevelEntry
	MAX-ACCESS  not-accessible
	STATUS      current
	DESCRIPTION
	"Table for insightsTrafficRecordsQueued"
	::={insightsTrafficRecordsQueued 4}

insightsTrafficRecordsQueuedLevelEntry OBJECT-TYPE
	SYNTAX      InsightsTrafficRecordsQueuedLevelEntry
	MAX-ACCESS  not-accessible
	STATUS      current
	DESCRIPTION
	"Table entry for insightsTrafficRecordsQueued"
	INDEX { insightsTrafficRecordsQueuedLevelName }
	::={insightsTrafficRecordsQueuedLevelTable 1}

InsightsTrafficRecordsQueuedLevelEntry ::=
	SEQUENCE {
		insightsTrafficRecordsQueuedLevelName	DisplayString,
		insightsTrafficRecordsQueuedLevelVal	Counter64,
		insightsTrafficRecordsQueuedLevelMom	CounterBasedGauge64,
		insightsTrafficRecordsQueuedLevelMax	CounterBasedGauge64
	}

insightsTrafficRecordsQueuedLevelName OBJECT-TYPE
	SYNTAX      DisplayString
	MAX-ACCESS  not-accessible
	STATUS      current
	DESCRIPTION
	"Table entry display string for insightsTrafficRecordsQueued"
	::={insightsTrafficRecordsQueuedLevelEntry 1}

insightsTrafficRecordsQueuedLevelVal OBJECT-TYPE
	SYNTAX	 Counter64
	MAX-ACCESS  read-only
	STATUS      current
	DESCRIPTION
	"Table entry attribute for insightsTrafficRecordsQueued"
	::={insightsTrafficRecordsQueuedLevelEntry 2}

insightsTrafficRecordsQueuedLevelMom OBJECT-TYPE
	SYNTAX	 CounterBasedGauge64
	MAX-ACCESS  read-only
	STATUS      current
	DESCRIPTION
	"Table entry attribute for insightsTrafficRecordsQueued"
	::={insightsTrafficRecordsQueuedLevelEntry 3}

insightsTrafficRecordsQueuedLevelMax OBJECT-TYPE
	SYNTAX	 CounterBasedGauge64
	MAX-ACCESS  read-only
	STATUS      current
	DESCRIPTION
	"Table entry attribute for insightsTrafficRecordsQueued"
	::={insightsTrafficRecordsQueuedLevelEntry 4}


insightsTrafficNumDumpsSkipped	OBJECT IDENTIFIER ::={insights 2}

insightsTrafficNumDumpsSkippedVal	OBJECT-TYPE
	SYNTAX	 CounterBasedGauge64
	MAX-ACCESS read-only
	STATUS obsolete
	DESCRIPTION "Traffic: Number of dumps skipped"

	::={insightsTrafficNumDumpsSkipped 1}

insightsTrafficNumDumpsSkippedMax	OBJECT-TYPE
	SYNTAX	 CounterBasedGauge64
	MAX-ACCESS read-only
	STATUS obsolete
	DESCRIPTION "Traffic: Number of dumps skipped"

	::={insightsTrafficNumDumpsSkipped 3}

insightsTrafficNumDumpsSkippedLevelTable OBJECT-TYPE
	SYNTAX      SEQUENCE OF InsightsTrafficNumDumpsSkippedLevelEntry
	MAX-ACCESS  not-accessible
	STATUS      current
	DESCRIPTION
	"Table for insightsTrafficNumDumpsSkipped"
	::={insightsTrafficNumDumpsSkipped 4}

insightsTrafficNumDumpsSkippedLevelEntry OBJECT-TYPE
	SYNTAX      InsightsTrafficNumDumpsSkippedLevelEntry
	MAX-ACCESS  not-accessible
	STATUS      current
	DESCRIPTION
	"Table entry for insightsTrafficNumDumpsSkipped"
	INDEX { insightsTrafficNumDumpsSkippedLevelName }
	::={insightsTrafficNumDumpsSkippedLevelTable 1}

InsightsTrafficNumDumpsSkippedLevelEntry ::=
	SEQUENCE {
		insightsTrafficNumDumpsSkippedLevelName	DisplayString,
		insightsTrafficNumDumpsSkippedLevelVal	CounterBasedGauge64,
		insightsTrafficNumDumpsSkippedLevelMax	CounterBasedGauge64
	}

insightsTrafficNumDumpsSkippedLevelName OBJECT-TYPE
	SYNTAX      DisplayString
	MAX-ACCESS  not-accessible
	STATUS      current
	DESCRIPTION
	"Table entry display string for insightsTrafficNumDumpsSkipped"
	::={insightsTrafficNumDumpsSkippedLevelEntry 1}

insightsTrafficNumDumpsSkippedLevelVal OBJECT-TYPE
	SYNTAX	 CounterBasedGauge64
	MAX-ACCESS  read-only
	STATUS      current
	DESCRIPTION
	"Table entry attribute for insightsTrafficNumDumpsSkipped"
	::={insightsTrafficNumDumpsSkippedLevelEntry 2}

insightsTrafficNumDumpsSkippedLevelMax OBJECT-TYPE
	SYNTAX	 CounterBasedGauge64
	MAX-ACCESS  read-only
	STATUS      current
	DESCRIPTION
	"Table entry attribute for insightsTrafficNumDumpsSkipped"
	::={insightsTrafficNumDumpsSkippedLevelEntry 4}


insightsDatacoreMessagesSent	OBJECT IDENTIFIER ::={insights 3}

insightsDatacoreMessagesSentVal	OBJECT-TYPE
	SYNTAX	 Counter64
	MAX-ACCESS read-only
	STATUS obsolete
	DESCRIPTION "Datacore: Messages sent"

	::={insightsDatacoreMessagesSent 1}

insightsDatacoreMessagesSentMom	OBJECT-TYPE
	SYNTAX	 CounterBasedGauge64
	MAX-ACCESS read-only
	STATUS obsolete
	DESCRIPTION "Datacore: Messages sent"

	::={insightsDatacoreMessagesSent 2}

insightsDatacoreMessagesSentMax	OBJECT-TYPE
	SYNTAX	 CounterBasedGauge64
	MAX-ACCESS read-only
	STATUS obsolete
	DESCRIPTION "Datacore: Messages sent"

	::={insightsDatacoreMessagesSent 3}

insightsDatacoreMessagesSentLevelTable OBJECT-TYPE
	SYNTAX      SEQUENCE OF InsightsDatacoreMessagesSentLevelEntry
	MAX-ACCESS  not-accessible
	STATUS      current
	DESCRIPTION
	"Table for insightsDatacoreMessagesSent"
	::={insightsDatacoreMessagesSent 4}

insightsDatacoreMessagesSentLevelEntry OBJECT-TYPE
	SYNTAX      InsightsDatacoreMessagesSentLevelEntry
	MAX-ACCESS  not-accessible
	STATUS      current
	DESCRIPTION
	"Table entry for insightsDatacoreMessagesSent"
	INDEX { insightsDatacoreMessagesSentLevelName }
	::={insightsDatacoreMessagesSentLevelTable 1}

InsightsDatacoreMessagesSentLevelEntry ::=
	SEQUENCE {
		insightsDatacoreMessagesSentLevelName	DisplayString,
		insightsDatacoreMessagesSentLevelVal	Counter64,
		insightsDatacoreMessagesSentLevelMom	CounterBasedGauge64,
		insightsDatacoreMessagesSentLevelMax	CounterBasedGauge64
	}

insightsDatacoreMessagesSentLevelName OBJECT-TYPE
	SYNTAX      DisplayString
	MAX-ACCESS  not-accessible
	STATUS      current
	DESCRIPTION
	"Table entry display string for insightsDatacoreMessagesSent"
	::={insightsDatacoreMessagesSentLevelEntry 1}

insightsDatacoreMessagesSentLevelVal OBJECT-TYPE
	SYNTAX	 Counter64
	MAX-ACCESS  read-only
	STATUS      current
	DESCRIPTION
	"Table entry attribute for insightsDatacoreMessagesSent"
	::={insightsDatacoreMessagesSentLevelEntry 2}

insightsDatacoreMessagesSentLevelMom OBJECT-TYPE
	SYNTAX	 CounterBasedGauge64
	MAX-ACCESS  read-only
	STATUS      current
	DESCRIPTION
	"Table entry attribute for insightsDatacoreMessagesSent"
	::={insightsDatacoreMessagesSentLevelEntry 3}

insightsDatacoreMessagesSentLevelMax OBJECT-TYPE
	SYNTAX	 CounterBasedGauge64
	MAX-ACCESS  read-only
	STATUS      current
	DESCRIPTION
	"Table entry attribute for insightsDatacoreMessagesSent"
	::={insightsDatacoreMessagesSentLevelEntry 4}


insightsDatacoreRecordsSent	OBJECT IDENTIFIER ::={insights 4}

insightsDatacoreRecordsSentVal	OBJECT-TYPE
	SYNTAX	 Counter64
	MAX-ACCESS read-only
	STATUS current
	DESCRIPTION "Datacore: Records sent"

	::={insightsDatacoreRecordsSent 1}

insightsDatacoreRecordsSentMom	OBJECT-TYPE
	SYNTAX	 CounterBasedGauge64
	MAX-ACCESS read-only
	STATUS current
	DESCRIPTION "Datacore: Records sent"

	::={insightsDatacoreRecordsSent 2}

insightsDatacoreRecordsSentMax	OBJECT-TYPE
	SYNTAX	 CounterBasedGauge64
	MAX-ACCESS read-only
	STATUS current
	DESCRIPTION "Datacore: Records sent"

	::={insightsDatacoreRecordsSent 3}

insightsDatacoreRecordsSentLevelTable OBJECT-TYPE
	SYNTAX      SEQUENCE OF InsightsDatacoreRecordsSentLevelEntry
	MAX-ACCESS  not-accessible
	STATUS      current
	DESCRIPTION
	"Table for insightsDatacoreRecordsSent"
	::={insightsDatacoreRecordsSent 4}

insightsDatacoreRecordsSentLevelEntry OBJECT-TYPE
	SYNTAX      InsightsDatacoreRecordsSentLevelEntry
	MAX-ACCESS  not-accessible
	STATUS      current
	DESCRIPTION
	"Table entry for insightsDatacoreRecordsSent"
	INDEX { insightsDatacoreRecordsSentLevelName }
	::={insightsDatacoreRecordsSentLevelTable 1}

InsightsDatacoreRecordsSentLevelEntry ::=
	SEQUENCE {
		insightsDatacoreRecordsSentLevelName	DisplayString,
		insightsDatacoreRecordsSentLevelVal	Counter64,
		insightsDatacoreRecordsSentLevelMom	CounterBasedGauge64,
		insightsDatacoreRecordsSentLevelMax	CounterBasedGauge64
	}

insightsDatacoreRecordsSentLevelName OBJECT-TYPE
	SYNTAX      DisplayString
	MAX-ACCESS  not-accessible
	STATUS      current
	DESCRIPTION
	"Table entry display string for insightsDatacoreRecordsSent"
	::={insightsDatacoreRecordsSentLevelEntry 1}

insightsDatacoreRecordsSentLevelVal OBJECT-TYPE
	SYNTAX	 Counter64
	MAX-ACCESS  read-only
	STATUS      current
	DESCRIPTION
	"Table entry attribute for insightsDatacoreRecordsSent"
	::={insightsDatacoreRecordsSentLevelEntry 2}

insightsDatacoreRecordsSentLevelMom OBJECT-TYPE
	SYNTAX	 CounterBasedGauge64
	MAX-ACCESS  read-only
	STATUS      current
	DESCRIPTION
	"Table entry attribute for insightsDatacoreRecordsSent"
	::={insightsDatacoreRecordsSentLevelEntry 3}

insightsDatacoreRecordsSentLevelMax OBJECT-TYPE
	SYNTAX	 CounterBasedGauge64
	MAX-ACCESS  read-only
	STATUS      current
	DESCRIPTION
	"Table entry attribute for insightsDatacoreRecordsSent"
	::={insightsDatacoreRecordsSentLevelEntry 4}


insightsDatacoreBytesSent	OBJECT IDENTIFIER ::={insights 5}

insightsDatacoreBytesSentVal	OBJECT-TYPE
	SYNTAX	 Counter64
	MAX-ACCESS read-only
	STATUS current
	DESCRIPTION "Datacore: Bytes sent"

	::={insightsDatacoreBytesSent 1}

insightsDatacoreBytesSentMom	OBJECT-TYPE
	SYNTAX	 CounterBasedGauge64
	MAX-ACCESS read-only
	STATUS current
	DESCRIPTION "Datacore: Bytes sent"

	::={insightsDatacoreBytesSent 2}

insightsDatacoreBytesSentMax	OBJECT-TYPE
	SYNTAX	 CounterBasedGauge64
	MAX-ACCESS read-only
	STATUS current
	DESCRIPTION "Datacore: Bytes sent"

	::={insightsDatacoreBytesSent 3}

insightsDatacoreBytesSentLevelTable OBJECT-TYPE
	SYNTAX      SEQUENCE OF InsightsDatacoreBytesSentLevelEntry
	MAX-ACCESS  not-accessible
	STATUS      current
	DESCRIPTION
	"Table for insightsDatacoreBytesSent"
	::={insightsDatacoreBytesSent 4}

insightsDatacoreBytesSentLevelEntry OBJECT-TYPE
	SYNTAX      InsightsDatacoreBytesSentLevelEntry
	MAX-ACCESS  not-accessible
	STATUS      current
	DESCRIPTION
	"Table entry for insightsDatacoreBytesSent"
	INDEX { insightsDatacoreBytesSentLevelName }
	::={insightsDatacoreBytesSentLevelTable 1}

InsightsDatacoreBytesSentLevelEntry ::=
	SEQUENCE {
		insightsDatacoreBytesSentLevelName	DisplayString,
		insightsDatacoreBytesSentLevelVal	Counter64,
		insightsDatacoreBytesSentLevelMom	CounterBasedGauge64,
		insightsDatacoreBytesSentLevelMax	CounterBasedGauge64
	}

insightsDatacoreBytesSentLevelName OBJECT-TYPE
	SYNTAX      DisplayString
	MAX-ACCESS  not-accessible
	STATUS      current
	DESCRIPTION
	"Table entry display string for insightsDatacoreBytesSent"
	::={insightsDatacoreBytesSentLevelEntry 1}

insightsDatacoreBytesSentLevelVal OBJECT-TYPE
	SYNTAX	 Counter64
	MAX-ACCESS  read-only
	STATUS      current
	DESCRIPTION
	"Table entry attribute for insightsDatacoreBytesSent"
	::={insightsDatacoreBytesSentLevelEntry 2}

insightsDatacoreBytesSentLevelMom OBJECT-TYPE
	SYNTAX	 CounterBasedGauge64
	MAX-ACCESS  read-only
	STATUS      current
	DESCRIPTION
	"Table entry attribute for insightsDatacoreBytesSent"
	::={insightsDatacoreBytesSentLevelEntry 3}

insightsDatacoreBytesSentLevelMax OBJECT-TYPE
	SYNTAX	 CounterBasedGauge64
	MAX-ACCESS  read-only
	STATUS      current
	DESCRIPTION
	"Table entry attribute for insightsDatacoreBytesSent"
	::={insightsDatacoreBytesSentLevelEntry 4}


insightsDatacoreZBytesSent	OBJECT IDENTIFIER ::={insights 6}

insightsDatacoreZBytesSentVal	OBJECT-TYPE
	SYNTAX	 Counter64
	MAX-ACCESS read-only
	STATUS obsolete
	DESCRIPTION "Datacore: Compressed bytes sent"

	::={insightsDatacoreZBytesSent 1}

insightsDatacoreZBytesSentMom	OBJECT-TYPE
	SYNTAX	 CounterBasedGauge64
	MAX-ACCESS read-only
	STATUS obsolete
	DESCRIPTION "Datacore: Compressed bytes sent"

	::={insightsDatacoreZBytesSent 2}

insightsDatacoreZBytesSentMax	OBJECT-TYPE
	SYNTAX	 CounterBasedGauge64
	MAX-ACCESS read-only
	STATUS obsolete
	DESCRIPTION "Datacore: Compressed bytes sent"

	::={insightsDatacoreZBytesSent 3}

insightsDatacoreZBytesSentLevelTable OBJECT-TYPE
	SYNTAX      SEQUENCE OF InsightsDatacoreZBytesSentLevelEntry
	MAX-ACCESS  not-accessible
	STATUS      current
	DESCRIPTION
	"Table for insightsDatacoreZBytesSent"
	::={insightsDatacoreZBytesSent 4}

insightsDatacoreZBytesSentLevelEntry OBJECT-TYPE
	SYNTAX      InsightsDatacoreZBytesSentLevelEntry
	MAX-ACCESS  not-accessible
	STATUS      current
	DESCRIPTION
	"Table entry for insightsDatacoreZBytesSent"
	INDEX { insightsDatacoreZBytesSentLevelName }
	::={insightsDatacoreZBytesSentLevelTable 1}

InsightsDatacoreZBytesSentLevelEntry ::=
	SEQUENCE {
		insightsDatacoreZBytesSentLevelName	DisplayString,
		insightsDatacoreZBytesSentLevelVal	Counter64,
		insightsDatacoreZBytesSentLevelMom	CounterBasedGauge64,
		insightsDatacoreZBytesSentLevelMax	CounterBasedGauge64
	}

insightsDatacoreZBytesSentLevelName OBJECT-TYPE
	SYNTAX      DisplayString
	MAX-ACCESS  not-accessible
	STATUS      current
	DESCRIPTION
	"Table entry display string for insightsDatacoreZBytesSent"
	::={insightsDatacoreZBytesSentLevelEntry 1}

insightsDatacoreZBytesSentLevelVal OBJECT-TYPE
	SYNTAX	 Counter64
	MAX-ACCESS  read-only
	STATUS      current
	DESCRIPTION
	"Table entry attribute for insightsDatacoreZBytesSent"
	::={insightsDatacoreZBytesSentLevelEntry 2}

insightsDatacoreZBytesSentLevelMom OBJECT-TYPE
	SYNTAX	 CounterBasedGauge64
	MAX-ACCESS  read-only
	STATUS      current
	DESCRIPTION
	"Table entry attribute for insightsDatacoreZBytesSent"
	::={insightsDatacoreZBytesSentLevelEntry 3}

insightsDatacoreZBytesSentLevelMax OBJECT-TYPE
	SYNTAX	 CounterBasedGauge64
	MAX-ACCESS  read-only
	STATUS      current
	DESCRIPTION
	"Table entry attribute for insightsDatacoreZBytesSent"
	::={insightsDatacoreZBytesSentLevelEntry 4}


insightsDatacoreRecordsDropped	OBJECT IDENTIFIER ::={insights 7}

insightsDatacoreRecordsDroppedVal	OBJECT-TYPE
	SYNTAX	 Counter64
	MAX-ACCESS read-only
	STATUS obsolete
	DESCRIPTION "Datacore: Records dropped"

	::={insightsDatacoreRecordsDropped 1}

insightsDatacoreRecordsDroppedMom	OBJECT-TYPE
	SYNTAX	 CounterBasedGauge64
	MAX-ACCESS read-only
	STATUS obsolete
	DESCRIPTION "Datacore: Records dropped"

	::={insightsDatacoreRecordsDropped 2}

insightsDatacoreRecordsDroppedMax	OBJECT-TYPE
	SYNTAX	 CounterBasedGauge64
	MAX-ACCESS read-only
	STATUS obsolete
	DESCRIPTION "Datacore: Records dropped"

	::={insightsDatacoreRecordsDropped 3}

insightsDatacoreRecordsDroppedLevelTable OBJECT-TYPE
	SYNTAX      SEQUENCE OF InsightsDatacoreRecordsDroppedLevelEntry
	MAX-ACCESS  not-accessible
	STATUS      current
	DESCRIPTION
	"Table for insightsDatacoreRecordsDropped"
	::={insightsDatacoreRecordsDropped 4}

insightsDatacoreRecordsDroppedLevelEntry OBJECT-TYPE
	SYNTAX      InsightsDatacoreRecordsDroppedLevelEntry
	MAX-ACCESS  not-accessible
	STATUS      current
	DESCRIPTION
	"Table entry for insightsDatacoreRecordsDropped"
	INDEX { insightsDatacoreRecordsDroppedLevelName }
	::={insightsDatacoreRecordsDroppedLevelTable 1}

InsightsDatacoreRecordsDroppedLevelEntry ::=
	SEQUENCE {
		insightsDatacoreRecordsDroppedLevelName	DisplayString,
		insightsDatacoreRecordsDroppedLevelVal	Counter64,
		insightsDatacoreRecordsDroppedLevelMom	CounterBasedGauge64,
		insightsDatacoreRecordsDroppedLevelMax	CounterBasedGauge64
	}

insightsDatacoreRecordsDroppedLevelName OBJECT-TYPE
	SYNTAX      DisplayString
	MAX-ACCESS  not-accessible
	STATUS      current
	DESCRIPTION
	"Table entry display string for insightsDatacoreRecordsDropped"
	::={insightsDatacoreRecordsDroppedLevelEntry 1}

insightsDatacoreRecordsDroppedLevelVal OBJECT-TYPE
	SYNTAX	 Counter64
	MAX-ACCESS  read-only
	STATUS      current
	DESCRIPTION
	"Table entry attribute for insightsDatacoreRecordsDropped"
	::={insightsDatacoreRecordsDroppedLevelEntry 2}

insightsDatacoreRecordsDroppedLevelMom OBJECT-TYPE
	SYNTAX	 CounterBasedGauge64
	MAX-ACCESS  read-only
	STATUS      current
	DESCRIPTION
	"Table entry attribute for insightsDatacoreRecordsDropped"
	::={insightsDatacoreRecordsDroppedLevelEntry 3}

insightsDatacoreRecordsDroppedLevelMax OBJECT-TYPE
	SYNTAX	 CounterBasedGauge64
	MAX-ACCESS  read-only
	STATUS      current
	DESCRIPTION
	"Table entry attribute for insightsDatacoreRecordsDropped"
	::={insightsDatacoreRecordsDroppedLevelEntry 4}


insightsTrafficPreviousDumpDuration	OBJECT IDENTIFIER ::={insights 8}

insightsTrafficPreviousDumpDurationVal	OBJECT-TYPE
	SYNTAX	 TimeTicks
	MAX-ACCESS read-only
	STATUS current
	DESCRIPTION "Traffic: Previous dump duration"

	::={insightsTrafficPreviousDumpDuration 1}

insightsTrafficPreviousDumpDurationLevelTable OBJECT-TYPE
	SYNTAX      SEQUENCE OF InsightsTrafficPreviousDumpDurationLevelEntry
	MAX-ACCESS  not-accessible
	STATUS      current
	DESCRIPTION
	"Table for insightsTrafficPreviousDumpDuration"
	::={insightsTrafficPreviousDumpDuration 2}

insightsTrafficPreviousDumpDurationLevelEntry OBJECT-TYPE
	SYNTAX      InsightsTrafficPreviousDumpDurationLevelEntry
	MAX-ACCESS  not-accessible
	STATUS      current
	DESCRIPTION
	"Table entry for insightsTrafficPreviousDumpDuration"
	INDEX { insightsTrafficPreviousDumpDurationLevelName }
	::={insightsTrafficPreviousDumpDurationLevelTable 1}

InsightsTrafficPreviousDumpDurationLevelEntry ::=
	SEQUENCE {
		insightsTrafficPreviousDumpDurationLevelName	DisplayString,
		insightsTrafficPreviousDumpDurationLevelVal	TimeTicks
	}

insightsTrafficPreviousDumpDurationLevelName OBJECT-TYPE
	SYNTAX      DisplayString
	MAX-ACCESS  not-accessible
	STATUS      current
	DESCRIPTION
	"Table entry display string for insightsTrafficPreviousDumpDuration"
	::={insightsTrafficPreviousDumpDurationLevelEntry 1}

insightsTrafficPreviousDumpDurationLevelVal OBJECT-TYPE
	SYNTAX	 TimeTicks
	MAX-ACCESS  read-only
	STATUS      current
	DESCRIPTION
	"Table entry attribute for insightsTrafficPreviousDumpDuration"
	::={insightsTrafficPreviousDumpDurationLevelEntry 2}


insightsTrafficAccumulatorKeysAllocated	OBJECT IDENTIFIER ::={insights 9}

insightsTrafficAccumulatorKeysAllocatedVal	OBJECT-TYPE
	SYNTAX	 CounterBasedGauge64
	MAX-ACCESS read-only
	STATUS current
	DESCRIPTION "Traffic: Accumulator row keys allocated"

	::={insightsTrafficAccumulatorKeysAllocated 1}

insightsTrafficAccumulatorKeysAllocatedMax	OBJECT-TYPE
	SYNTAX	 CounterBasedGauge64
	MAX-ACCESS read-only
	STATUS current
	DESCRIPTION "Traffic: Accumulator row keys allocated"

	::={insightsTrafficAccumulatorKeysAllocated 3}

insightsTrafficAccumulatorKeysAllocatedLevelTable OBJECT-TYPE
	SYNTAX      SEQUENCE OF InsightsTrafficAccumulatorKeysAllocatedLevelEntry
	MAX-ACCESS  not-accessible
	STATUS      current
	DESCRIPTION
	"Table for insightsTrafficAccumulatorKeysAllocated"
	::={insightsTrafficAccumulatorKeysAllocated 4}

insightsTrafficAccumulatorKeysAllocatedLevelEntry OBJECT-TYPE
	SYNTAX      InsightsTrafficAccumulatorKeysAllocatedLevelEntry
	MAX-ACCESS  not-accessible
	STATUS      current
	DESCRIPTION
	"Table entry for insightsTrafficAccumulatorKeysAllocated"
	INDEX { insightsTrafficAccumulatorKeysAllocatedLevelName }
	::={insightsTrafficAccumulatorKeysAllocatedLevelTable 1}

InsightsTrafficAccumulatorKeysAllocatedLevelEntry ::=
	SEQUENCE {
		insightsTrafficAccumulatorKeysAllocatedLevelName	DisplayString,
		insightsTrafficAccumulatorKeysAllocatedLevelVal	CounterBasedGauge64,
		insightsTrafficAccumulatorKeysAllocatedLevelMax	CounterBasedGauge64
	}

insightsTrafficAccumulatorKeysAllocatedLevelName OBJECT-TYPE
	SYNTAX      DisplayString
	MAX-ACCESS  not-accessible
	STATUS      current
	DESCRIPTION
	"Table entry display string for insightsTrafficAccumulatorKeysAllocated"
	::={insightsTrafficAccumulatorKeysAllocatedLevelEntry 1}

insightsTrafficAccumulatorKeysAllocatedLevelVal OBJECT-TYPE
	SYNTAX	 CounterBasedGauge64
	MAX-ACCESS  read-only
	STATUS      current
	DESCRIPTION
	"Table entry attribute for insightsTrafficAccumulatorKeysAllocated"
	::={insightsTrafficAccumulatorKeysAllocatedLevelEntry 2}

insightsTrafficAccumulatorKeysAllocatedLevelMax OBJECT-TYPE
	SYNTAX	 CounterBasedGauge64
	MAX-ACCESS  read-only
	STATUS      current
	DESCRIPTION
	"Table entry attribute for insightsTrafficAccumulatorKeysAllocated"
	::={insightsTrafficAccumulatorKeysAllocatedLevelEntry 4}


insightsTrafficAccumulatorKeysUsed	OBJECT IDENTIFIER ::={insights 10}

insightsTrafficAccumulatorKeysUsedVal	OBJECT-TYPE
	SYNTAX	 CounterBasedGauge64
	MAX-ACCESS read-only
	STATUS current
	DESCRIPTION "Traffic: Accumulator row keys used"

	::={insightsTrafficAccumulatorKeysUsed 1}

insightsTrafficAccumulatorKeysUsedMax	OBJECT-TYPE
	SYNTAX	 CounterBasedGauge64
	MAX-ACCESS read-only
	STATUS current
	DESCRIPTION "Traffic: Accumulator row keys used"

	::={insightsTrafficAccumulatorKeysUsed 3}

insightsTrafficAccumulatorKeysUsedLevelTable OBJECT-TYPE
	SYNTAX      SEQUENCE OF InsightsTrafficAccumulatorKeysUsedLevelEntry
	MAX-ACCESS  not-accessible
	STATUS      current
	DESCRIPTION
	"Table for insightsTrafficAccumulatorKeysUsed"
	::={insightsTrafficAccumulatorKeysUsed 4}

insightsTrafficAccumulatorKeysUsedLevelEntry OBJECT-TYPE
	SYNTAX      InsightsTrafficAccumulatorKeysUsedLevelEntry
	MAX-ACCESS  not-accessible
	STATUS      current
	DESCRIPTION
	"Table entry for insightsTrafficAccumulatorKeysUsed"
	INDEX { insightsTrafficAccumulatorKeysUsedLevelName }
	::={insightsTrafficAccumulatorKeysUsedLevelTable 1}

InsightsTrafficAccumulatorKeysUsedLevelEntry ::=
	SEQUENCE {
		insightsTrafficAccumulatorKeysUsedLevelName	DisplayString,
		insightsTrafficAccumulatorKeysUsedLevelVal	CounterBasedGauge64,
		insightsTrafficAccumulatorKeysUsedLevelMax	CounterBasedGauge64
	}

insightsTrafficAccumulatorKeysUsedLevelName OBJECT-TYPE
	SYNTAX      DisplayString
	MAX-ACCESS  not-accessible
	STATUS      current
	DESCRIPTION
	"Table entry display string for insightsTrafficAccumulatorKeysUsed"
	::={insightsTrafficAccumulatorKeysUsedLevelEntry 1}

insightsTrafficAccumulatorKeysUsedLevelVal OBJECT-TYPE
	SYNTAX	 CounterBasedGauge64
	MAX-ACCESS  read-only
	STATUS      current
	DESCRIPTION
	"Table entry attribute for insightsTrafficAccumulatorKeysUsed"
	::={insightsTrafficAccumulatorKeysUsedLevelEntry 2}

insightsTrafficAccumulatorKeysUsedLevelMax OBJECT-TYPE
	SYNTAX	 CounterBasedGauge64
	MAX-ACCESS  read-only
	STATUS      current
	DESCRIPTION
	"Table entry attribute for insightsTrafficAccumulatorKeysUsed"
	::={insightsTrafficAccumulatorKeysUsedLevelEntry 4}


insightsTrafficAccumulatorKeysFree	OBJECT IDENTIFIER ::={insights 11}

insightsTrafficAccumulatorKeysFreeVal	OBJECT-TYPE
	SYNTAX	 CounterBasedGauge64
	MAX-ACCESS read-only
	STATUS current
	DESCRIPTION "Traffic: Accumulator row keys free"

	::={insightsTrafficAccumulatorKeysFree 1}

insightsTrafficAccumulatorKeysFreeMax	OBJECT-TYPE
	SYNTAX	 CounterBasedGauge64
	MAX-ACCESS read-only
	STATUS current
	DESCRIPTION "Traffic: Accumulator row keys free"

	::={insightsTrafficAccumulatorKeysFree 3}

insightsTrafficAccumulatorKeysFreeLevelTable OBJECT-TYPE
	SYNTAX      SEQUENCE OF InsightsTrafficAccumulatorKeysFreeLevelEntry
	MAX-ACCESS  not-accessible
	STATUS      current
	DESCRIPTION
	"Table for insightsTrafficAccumulatorKeysFree"
	::={insightsTrafficAccumulatorKeysFree 4}

insightsTrafficAccumulatorKeysFreeLevelEntry OBJECT-TYPE
	SYNTAX      InsightsTrafficAccumulatorKeysFreeLevelEntry
	MAX-ACCESS  not-accessible
	STATUS      current
	DESCRIPTION
	"Table entry for insightsTrafficAccumulatorKeysFree"
	INDEX { insightsTrafficAccumulatorKeysFreeLevelName }
	::={insightsTrafficAccumulatorKeysFreeLevelTable 1}

InsightsTrafficAccumulatorKeysFreeLevelEntry ::=
	SEQUENCE {
		insightsTrafficAccumulatorKeysFreeLevelName	DisplayString,
		insightsTrafficAccumulatorKeysFreeLevelVal	CounterBasedGauge64,
		insightsTrafficAccumulatorKeysFreeLevelMax	CounterBasedGauge64
	}

insightsTrafficAccumulatorKeysFreeLevelName OBJECT-TYPE
	SYNTAX      DisplayString
	MAX-ACCESS  not-accessible
	STATUS      current
	DESCRIPTION
	"Table entry display string for insightsTrafficAccumulatorKeysFree"
	::={insightsTrafficAccumulatorKeysFreeLevelEntry 1}

insightsTrafficAccumulatorKeysFreeLevelVal OBJECT-TYPE
	SYNTAX	 CounterBasedGauge64
	MAX-ACCESS  read-only
	STATUS      current
	DESCRIPTION
	"Table entry attribute for insightsTrafficAccumulatorKeysFree"
	::={insightsTrafficAccumulatorKeysFreeLevelEntry 2}

insightsTrafficAccumulatorKeysFreeLevelMax OBJECT-TYPE
	SYNTAX	 CounterBasedGauge64
	MAX-ACCESS  read-only
	STATUS      current
	DESCRIPTION
	"Table entry attribute for insightsTrafficAccumulatorKeysFree"
	::={insightsTrafficAccumulatorKeysFreeLevelEntry 4}


insightsTrafficAccumulatorsLost	OBJECT IDENTIFIER ::={insights 12}

insightsTrafficAccumulatorsLostVal	OBJECT-TYPE
	SYNTAX	 CounterBasedGauge64
	MAX-ACCESS read-only
	STATUS obsolete
	DESCRIPTION "Traffic: Accumulators lost"

	::={insightsTrafficAccumulatorsLost 1}

insightsTrafficAccumulatorsLostMax	OBJECT-TYPE
	SYNTAX	 CounterBasedGauge64
	MAX-ACCESS read-only
	STATUS obsolete
	DESCRIPTION "Traffic: Accumulators lost"

	::={insightsTrafficAccumulatorsLost 3}

insightsTrafficAccumulatorsLostLevelTable OBJECT-TYPE
	SYNTAX      SEQUENCE OF InsightsTrafficAccumulatorsLostLevelEntry
	MAX-ACCESS  not-accessible
	STATUS      current
	DESCRIPTION
	"Table for insightsTrafficAccumulatorsLost"
	::={insightsTrafficAccumulatorsLost 4}

insightsTrafficAccumulatorsLostLevelEntry OBJECT-TYPE
	SYNTAX      InsightsTrafficAccumulatorsLostLevelEntry
	MAX-ACCESS  not-accessible
	STATUS      current
	DESCRIPTION
	"Table entry for insightsTrafficAccumulatorsLost"
	INDEX { insightsTrafficAccumulatorsLostLevelName }
	::={insightsTrafficAccumulatorsLostLevelTable 1}

InsightsTrafficAccumulatorsLostLevelEntry ::=
	SEQUENCE {
		insightsTrafficAccumulatorsLostLevelName	DisplayString,
		insightsTrafficAccumulatorsLostLevelVal	CounterBasedGauge64,
		insightsTrafficAccumulatorsLostLevelMax	CounterBasedGauge64
	}

insightsTrafficAccumulatorsLostLevelName OBJECT-TYPE
	SYNTAX      DisplayString
	MAX-ACCESS  not-accessible
	STATUS      current
	DESCRIPTION
	"Table entry display string for insightsTrafficAccumulatorsLost"
	::={insightsTrafficAccumulatorsLostLevelEntry 1}

insightsTrafficAccumulatorsLostLevelVal OBJECT-TYPE
	SYNTAX	 CounterBasedGauge64
	MAX-ACCESS  read-only
	STATUS      current
	DESCRIPTION
	"Table entry attribute for insightsTrafficAccumulatorsLost"
	::={insightsTrafficAccumulatorsLostLevelEntry 2}

insightsTrafficAccumulatorsLostLevelMax OBJECT-TYPE
	SYNTAX	 CounterBasedGauge64
	MAX-ACCESS  read-only
	STATUS      current
	DESCRIPTION
	"Table entry attribute for insightsTrafficAccumulatorsLost"
	::={insightsTrafficAccumulatorsLostLevelEntry 4}


insightsTrafficAccumulatorsInactive	OBJECT IDENTIFIER ::={insights 13}

insightsTrafficAccumulatorsInactiveVal	OBJECT-TYPE
	SYNTAX	 CounterBasedGauge64
	MAX-ACCESS read-only
	STATUS obsolete
	DESCRIPTION "Traffic: Accumulators inactive"

	::={insightsTrafficAccumulatorsInactive 1}

insightsTrafficAccumulatorsInactiveMax	OBJECT-TYPE
	SYNTAX	 CounterBasedGauge64
	MAX-ACCESS read-only
	STATUS obsolete
	DESCRIPTION "Traffic: Accumulators inactive"

	::={insightsTrafficAccumulatorsInactive 3}

insightsTrafficAccumulatorsInactiveLevelTable OBJECT-TYPE
	SYNTAX      SEQUENCE OF InsightsTrafficAccumulatorsInactiveLevelEntry
	MAX-ACCESS  not-accessible
	STATUS      current
	DESCRIPTION
	"Table for insightsTrafficAccumulatorsInactive"
	::={insightsTrafficAccumulatorsInactive 4}

insightsTrafficAccumulatorsInactiveLevelEntry OBJECT-TYPE
	SYNTAX      InsightsTrafficAccumulatorsInactiveLevelEntry
	MAX-ACCESS  not-accessible
	STATUS      current
	DESCRIPTION
	"Table entry for insightsTrafficAccumulatorsInactive"
	INDEX { insightsTrafficAccumulatorsInactiveLevelName }
	::={insightsTrafficAccumulatorsInactiveLevelTable 1}

InsightsTrafficAccumulatorsInactiveLevelEntry ::=
	SEQUENCE {
		insightsTrafficAccumulatorsInactiveLevelName	DisplayString,
		insightsTrafficAccumulatorsInactiveLevelVal	CounterBasedGauge64,
		insightsTrafficAccumulatorsInactiveLevelMax	CounterBasedGauge64
	}

insightsTrafficAccumulatorsInactiveLevelName OBJECT-TYPE
	SYNTAX      DisplayString
	MAX-ACCESS  not-accessible
	STATUS      current
	DESCRIPTION
	"Table entry display string for insightsTrafficAccumulatorsInactive"
	::={insightsTrafficAccumulatorsInactiveLevelEntry 1}

insightsTrafficAccumulatorsInactiveLevelVal OBJECT-TYPE
	SYNTAX	 CounterBasedGauge64
	MAX-ACCESS  read-only
	STATUS      current
	DESCRIPTION
	"Table entry attribute for insightsTrafficAccumulatorsInactive"
	::={insightsTrafficAccumulatorsInactiveLevelEntry 2}

insightsTrafficAccumulatorsInactiveLevelMax OBJECT-TYPE
	SYNTAX	 CounterBasedGauge64
	MAX-ACCESS  read-only
	STATUS      current
	DESCRIPTION
	"Table entry attribute for insightsTrafficAccumulatorsInactive"
	::={insightsTrafficAccumulatorsInactiveLevelEntry 4}


insightsTrafficAccumulatorsPruned	OBJECT IDENTIFIER ::={insights 14}

insightsTrafficAccumulatorsPrunedVal	OBJECT-TYPE
	SYNTAX	 Counter64
	MAX-ACCESS read-only
	STATUS obsolete
	DESCRIPTION "Traffic: Accumulators pruned"

	::={insightsTrafficAccumulatorsPruned 1}

insightsTrafficAccumulatorsPrunedMom	OBJECT-TYPE
	SYNTAX	 CounterBasedGauge64
	MAX-ACCESS read-only
	STATUS obsolete
	DESCRIPTION "Traffic: Accumulators pruned"

	::={insightsTrafficAccumulatorsPruned 2}

insightsTrafficAccumulatorsPrunedMax	OBJECT-TYPE
	SYNTAX	 CounterBasedGauge64
	MAX-ACCESS read-only
	STATUS obsolete
	DESCRIPTION "Traffic: Accumulators pruned"

	::={insightsTrafficAccumulatorsPruned 3}

insightsTrafficAccumulatorsPrunedLevelTable OBJECT-TYPE
	SYNTAX      SEQUENCE OF InsightsTrafficAccumulatorsPrunedLevelEntry
	MAX-ACCESS  not-accessible
	STATUS      current
	DESCRIPTION
	"Table for insightsTrafficAccumulatorsPruned"
	::={insightsTrafficAccumulatorsPruned 4}

insightsTrafficAccumulatorsPrunedLevelEntry OBJECT-TYPE
	SYNTAX      InsightsTrafficAccumulatorsPrunedLevelEntry
	MAX-ACCESS  not-accessible
	STATUS      current
	DESCRIPTION
	"Table entry for insightsTrafficAccumulatorsPruned"
	INDEX { insightsTrafficAccumulatorsPrunedLevelName }
	::={insightsTrafficAccumulatorsPrunedLevelTable 1}

InsightsTrafficAccumulatorsPrunedLevelEntry ::=
	SEQUENCE {
		insightsTrafficAccumulatorsPrunedLevelName	DisplayString,
		insightsTrafficAccumulatorsPrunedLevelVal	Counter64,
		insightsTrafficAccumulatorsPrunedLevelMom	CounterBasedGauge64,
		insightsTrafficAccumulatorsPrunedLevelMax	CounterBasedGauge64
	}

insightsTrafficAccumulatorsPrunedLevelName OBJECT-TYPE
	SYNTAX      DisplayString
	MAX-ACCESS  not-accessible
	STATUS      current
	DESCRIPTION
	"Table entry display string for insightsTrafficAccumulatorsPruned"
	::={insightsTrafficAccumulatorsPrunedLevelEntry 1}

insightsTrafficAccumulatorsPrunedLevelVal OBJECT-TYPE
	SYNTAX	 Counter64
	MAX-ACCESS  read-only
	STATUS      current
	DESCRIPTION
	"Table entry attribute for insightsTrafficAccumulatorsPruned"
	::={insightsTrafficAccumulatorsPrunedLevelEntry 2}

insightsTrafficAccumulatorsPrunedLevelMom OBJECT-TYPE
	SYNTAX	 CounterBasedGauge64
	MAX-ACCESS  read-only
	STATUS      current
	DESCRIPTION
	"Table entry attribute for insightsTrafficAccumulatorsPruned"
	::={insightsTrafficAccumulatorsPrunedLevelEntry 3}

insightsTrafficAccumulatorsPrunedLevelMax OBJECT-TYPE
	SYNTAX	 CounterBasedGauge64
	MAX-ACCESS  read-only
	STATUS      current
	DESCRIPTION
	"Table entry attribute for insightsTrafficAccumulatorsPruned"
	::={insightsTrafficAccumulatorsPrunedLevelEntry 4}


insightsTrafficAccumulatorsRevived	OBJECT IDENTIFIER ::={insights 15}

insightsTrafficAccumulatorsRevivedVal	OBJECT-TYPE
	SYNTAX	 Counter64
	MAX-ACCESS read-only
	STATUS obsolete
	DESCRIPTION "Traffic: Accumulators revived"

	::={insightsTrafficAccumulatorsRevived 1}

insightsTrafficAccumulatorsRevivedMom	OBJECT-TYPE
	SYNTAX	 CounterBasedGauge64
	MAX-ACCESS read-only
	STATUS obsolete
	DESCRIPTION "Traffic: Accumulators revived"

	::={insightsTrafficAccumulatorsRevived 2}

insightsTrafficAccumulatorsRevivedMax	OBJECT-TYPE
	SYNTAX	 CounterBasedGauge64
	MAX-ACCESS read-only
	STATUS obsolete
	DESCRIPTION "Traffic: Accumulators revived"

	::={insightsTrafficAccumulatorsRevived 3}

insightsTrafficAccumulatorsRevivedLevelTable OBJECT-TYPE
	SYNTAX      SEQUENCE OF InsightsTrafficAccumulatorsRevivedLevelEntry
	MAX-ACCESS  not-accessible
	STATUS      current
	DESCRIPTION
	"Table for insightsTrafficAccumulatorsRevived"
	::={insightsTrafficAccumulatorsRevived 4}

insightsTrafficAccumulatorsRevivedLevelEntry OBJECT-TYPE
	SYNTAX      InsightsTrafficAccumulatorsRevivedLevelEntry
	MAX-ACCESS  not-accessible
	STATUS      current
	DESCRIPTION
	"Table entry for insightsTrafficAccumulatorsRevived"
	INDEX { insightsTrafficAccumulatorsRevivedLevelName }
	::={insightsTrafficAccumulatorsRevivedLevelTable 1}

InsightsTrafficAccumulatorsRevivedLevelEntry ::=
	SEQUENCE {
		insightsTrafficAccumulatorsRevivedLevelName	DisplayString,
		insightsTrafficAccumulatorsRevivedLevelVal	Counter64,
		insightsTrafficAccumulatorsRevivedLevelMom	CounterBasedGauge64,
		insightsTrafficAccumulatorsRevivedLevelMax	CounterBasedGauge64
	}

insightsTrafficAccumulatorsRevivedLevelName OBJECT-TYPE
	SYNTAX      DisplayString
	MAX-ACCESS  not-accessible
	STATUS      current
	DESCRIPTION
	"Table entry display string for insightsTrafficAccumulatorsRevived"
	::={insightsTrafficAccumulatorsRevivedLevelEntry 1}

insightsTrafficAccumulatorsRevivedLevelVal OBJECT-TYPE
	SYNTAX	 Counter64
	MAX-ACCESS  read-only
	STATUS      current
	DESCRIPTION
	"Table entry attribute for insightsTrafficAccumulatorsRevived"
	::={insightsTrafficAccumulatorsRevivedLevelEntry 2}

insightsTrafficAccumulatorsRevivedLevelMom OBJECT-TYPE
	SYNTAX	 CounterBasedGauge64
	MAX-ACCESS  read-only
	STATUS      current
	DESCRIPTION
	"Table entry attribute for insightsTrafficAccumulatorsRevived"
	::={insightsTrafficAccumulatorsRevivedLevelEntry 3}

insightsTrafficAccumulatorsRevivedLevelMax OBJECT-TYPE
	SYNTAX	 CounterBasedGauge64
	MAX-ACCESS  read-only
	STATUS      current
	DESCRIPTION
	"Table entry attribute for insightsTrafficAccumulatorsRevived"
	::={insightsTrafficAccumulatorsRevivedLevelEntry 4}


insightsTrafficBytesQueued	OBJECT IDENTIFIER ::={insights 16}

insightsTrafficBytesQueuedVal	OBJECT-TYPE
	SYNTAX	 Counter64
	MAX-ACCESS read-only
	STATUS obsolete
	DESCRIPTION "Traffic: Bytes queued"

	::={insightsTrafficBytesQueued 1}

insightsTrafficBytesQueuedMom	OBJECT-TYPE
	SYNTAX	 CounterBasedGauge64
	MAX-ACCESS read-only
	STATUS obsolete
	DESCRIPTION "Traffic: Bytes queued"

	::={insightsTrafficBytesQueued 2}

insightsTrafficBytesQueuedMax	OBJECT-TYPE
	SYNTAX	 CounterBasedGauge64
	MAX-ACCESS read-only
	STATUS obsolete
	DESCRIPTION "Traffic: Bytes queued"

	::={insightsTrafficBytesQueued 3}

insightsTrafficBytesQueuedLevelTable OBJECT-TYPE
	SYNTAX      SEQUENCE OF InsightsTrafficBytesQueuedLevelEntry
	MAX-ACCESS  not-accessible
	STATUS      current
	DESCRIPTION
	"Table for insightsTrafficBytesQueued"
	::={insightsTrafficBytesQueued 4}

insightsTrafficBytesQueuedLevelEntry OBJECT-TYPE
	SYNTAX      InsightsTrafficBytesQueuedLevelEntry
	MAX-ACCESS  not-accessible
	STATUS      current
	DESCRIPTION
	"Table entry for insightsTrafficBytesQueued"
	INDEX { insightsTrafficBytesQueuedLevelName }
	::={insightsTrafficBytesQueuedLevelTable 1}

InsightsTrafficBytesQueuedLevelEntry ::=
	SEQUENCE {
		insightsTrafficBytesQueuedLevelName	DisplayString,
		insightsTrafficBytesQueuedLevelVal	Counter64,
		insightsTrafficBytesQueuedLevelMom	CounterBasedGauge64,
		insightsTrafficBytesQueuedLevelMax	CounterBasedGauge64
	}

insightsTrafficBytesQueuedLevelName OBJECT-TYPE
	SYNTAX      DisplayString
	MAX-ACCESS  not-accessible
	STATUS      current
	DESCRIPTION
	"Table entry display string for insightsTrafficBytesQueued"
	::={insightsTrafficBytesQueuedLevelEntry 1}

insightsTrafficBytesQueuedLevelVal OBJECT-TYPE
	SYNTAX	 Counter64
	MAX-ACCESS  read-only
	STATUS      current
	DESCRIPTION
	"Table entry attribute for insightsTrafficBytesQueued"
	::={insightsTrafficBytesQueuedLevelEntry 2}

insightsTrafficBytesQueuedLevelMom OBJECT-TYPE
	SYNTAX	 CounterBasedGauge64
	MAX-ACCESS  read-only
	STATUS      current
	DESCRIPTION
	"Table entry attribute for insightsTrafficBytesQueued"
	::={insightsTrafficBytesQueuedLevelEntry 3}

insightsTrafficBytesQueuedLevelMax OBJECT-TYPE
	SYNTAX	 CounterBasedGauge64
	MAX-ACCESS  read-only
	STATUS      current
	DESCRIPTION
	"Table entry attribute for insightsTrafficBytesQueued"
	::={insightsTrafficBytesQueuedLevelEntry 4}


insightsTrafficMessagesSent	OBJECT IDENTIFIER ::={insights 17}

insightsTrafficMessagesSentVal	OBJECT-TYPE
	SYNTAX	 Counter64
	MAX-ACCESS read-only
	STATUS obsolete
	DESCRIPTION "Traffic: Messages sent"

	::={insightsTrafficMessagesSent 1}

insightsTrafficMessagesSentMom	OBJECT-TYPE
	SYNTAX	 CounterBasedGauge64
	MAX-ACCESS read-only
	STATUS obsolete
	DESCRIPTION "Traffic: Messages sent"

	::={insightsTrafficMessagesSent 2}

insightsTrafficMessagesSentMax	OBJECT-TYPE
	SYNTAX	 CounterBasedGauge64
	MAX-ACCESS read-only
	STATUS obsolete
	DESCRIPTION "Traffic: Messages sent"

	::={insightsTrafficMessagesSent 3}

insightsTrafficMessagesSentLevelTable OBJECT-TYPE
	SYNTAX      SEQUENCE OF InsightsTrafficMessagesSentLevelEntry
	MAX-ACCESS  not-accessible
	STATUS      current
	DESCRIPTION
	"Table for insightsTrafficMessagesSent"
	::={insightsTrafficMessagesSent 4}

insightsTrafficMessagesSentLevelEntry OBJECT-TYPE
	SYNTAX      InsightsTrafficMessagesSentLevelEntry
	MAX-ACCESS  not-accessible
	STATUS      current
	DESCRIPTION
	"Table entry for insightsTrafficMessagesSent"
	INDEX { insightsTrafficMessagesSentLevelName }
	::={insightsTrafficMessagesSentLevelTable 1}

InsightsTrafficMessagesSentLevelEntry ::=
	SEQUENCE {
		insightsTrafficMessagesSentLevelName	DisplayString,
		insightsTrafficMessagesSentLevelVal	Counter64,
		insightsTrafficMessagesSentLevelMom	CounterBasedGauge64,
		insightsTrafficMessagesSentLevelMax	CounterBasedGauge64
	}

insightsTrafficMessagesSentLevelName OBJECT-TYPE
	SYNTAX      DisplayString
	MAX-ACCESS  not-accessible
	STATUS      current
	DESCRIPTION
	"Table entry display string for insightsTrafficMessagesSent"
	::={insightsTrafficMessagesSentLevelEntry 1}

insightsTrafficMessagesSentLevelVal OBJECT-TYPE
	SYNTAX	 Counter64
	MAX-ACCESS  read-only
	STATUS      current
	DESCRIPTION
	"Table entry attribute for insightsTrafficMessagesSent"
	::={insightsTrafficMessagesSentLevelEntry 2}

insightsTrafficMessagesSentLevelMom OBJECT-TYPE
	SYNTAX	 CounterBasedGauge64
	MAX-ACCESS  read-only
	STATUS      current
	DESCRIPTION
	"Table entry attribute for insightsTrafficMessagesSent"
	::={insightsTrafficMessagesSentLevelEntry 3}

insightsTrafficMessagesSentLevelMax OBJECT-TYPE
	SYNTAX	 CounterBasedGauge64
	MAX-ACCESS  read-only
	STATUS      current
	DESCRIPTION
	"Table entry attribute for insightsTrafficMessagesSent"
	::={insightsTrafficMessagesSentLevelEntry 4}


insightsTrafficRecordsSent	OBJECT IDENTIFIER ::={insights 18}

insightsTrafficRecordsSentVal	OBJECT-TYPE
	SYNTAX	 Counter64
	MAX-ACCESS read-only
	STATUS current
	DESCRIPTION "Traffic: Records sent"

	::={insightsTrafficRecordsSent 1}

insightsTrafficRecordsSentMom	OBJECT-TYPE
	SYNTAX	 CounterBasedGauge64
	MAX-ACCESS read-only
	STATUS current
	DESCRIPTION "Traffic: Records sent"

	::={insightsTrafficRecordsSent 2}

insightsTrafficRecordsSentMax	OBJECT-TYPE
	SYNTAX	 CounterBasedGauge64
	MAX-ACCESS read-only
	STATUS current
	DESCRIPTION "Traffic: Records sent"

	::={insightsTrafficRecordsSent 3}

insightsTrafficRecordsSentLevelTable OBJECT-TYPE
	SYNTAX      SEQUENCE OF InsightsTrafficRecordsSentLevelEntry
	MAX-ACCESS  not-accessible
	STATUS      current
	DESCRIPTION
	"Table for insightsTrafficRecordsSent"
	::={insightsTrafficRecordsSent 4}

insightsTrafficRecordsSentLevelEntry OBJECT-TYPE
	SYNTAX      InsightsTrafficRecordsSentLevelEntry
	MAX-ACCESS  not-accessible
	STATUS      current
	DESCRIPTION
	"Table entry for insightsTrafficRecordsSent"
	INDEX { insightsTrafficRecordsSentLevelName }
	::={insightsTrafficRecordsSentLevelTable 1}

InsightsTrafficRecordsSentLevelEntry ::=
	SEQUENCE {
		insightsTrafficRecordsSentLevelName	DisplayString,
		insightsTrafficRecordsSentLevelVal	Counter64,
		insightsTrafficRecordsSentLevelMom	CounterBasedGauge64,
		insightsTrafficRecordsSentLevelMax	CounterBasedGauge64
	}

insightsTrafficRecordsSentLevelName OBJECT-TYPE
	SYNTAX      DisplayString
	MAX-ACCESS  not-accessible
	STATUS      current
	DESCRIPTION
	"Table entry display string for insightsTrafficRecordsSent"
	::={insightsTrafficRecordsSentLevelEntry 1}

insightsTrafficRecordsSentLevelVal OBJECT-TYPE
	SYNTAX	 Counter64
	MAX-ACCESS  read-only
	STATUS      current
	DESCRIPTION
	"Table entry attribute for insightsTrafficRecordsSent"
	::={insightsTrafficRecordsSentLevelEntry 2}

insightsTrafficRecordsSentLevelMom OBJECT-TYPE
	SYNTAX	 CounterBasedGauge64
	MAX-ACCESS  read-only
	STATUS      current
	DESCRIPTION
	"Table entry attribute for insightsTrafficRecordsSent"
	::={insightsTrafficRecordsSentLevelEntry 3}

insightsTrafficRecordsSentLevelMax OBJECT-TYPE
	SYNTAX	 CounterBasedGauge64
	MAX-ACCESS  read-only
	STATUS      current
	DESCRIPTION
	"Table entry attribute for insightsTrafficRecordsSent"
	::={insightsTrafficRecordsSentLevelEntry 4}


insightsTrafficBytesSent	OBJECT IDENTIFIER ::={insights 19}

insightsTrafficBytesSentVal	OBJECT-TYPE
	SYNTAX	 Counter64
	MAX-ACCESS read-only
	STATUS current
	DESCRIPTION "Traffic: Bytes sent"

	::={insightsTrafficBytesSent 1}

insightsTrafficBytesSentMom	OBJECT-TYPE
	SYNTAX	 CounterBasedGauge64
	MAX-ACCESS read-only
	STATUS current
	DESCRIPTION "Traffic: Bytes sent"

	::={insightsTrafficBytesSent 2}

insightsTrafficBytesSentMax	OBJECT-TYPE
	SYNTAX	 CounterBasedGauge64
	MAX-ACCESS read-only
	STATUS current
	DESCRIPTION "Traffic: Bytes sent"

	::={insightsTrafficBytesSent 3}

insightsTrafficBytesSentLevelTable OBJECT-TYPE
	SYNTAX      SEQUENCE OF InsightsTrafficBytesSentLevelEntry
	MAX-ACCESS  not-accessible
	STATUS      current
	DESCRIPTION
	"Table for insightsTrafficBytesSent"
	::={insightsTrafficBytesSent 4}

insightsTrafficBytesSentLevelEntry OBJECT-TYPE
	SYNTAX      InsightsTrafficBytesSentLevelEntry
	MAX-ACCESS  not-accessible
	STATUS      current
	DESCRIPTION
	"Table entry for insightsTrafficBytesSent"
	INDEX { insightsTrafficBytesSentLevelName }
	::={insightsTrafficBytesSentLevelTable 1}

InsightsTrafficBytesSentLevelEntry ::=
	SEQUENCE {
		insightsTrafficBytesSentLevelName	DisplayString,
		insightsTrafficBytesSentLevelVal	Counter64,
		insightsTrafficBytesSentLevelMom	CounterBasedGauge64,
		insightsTrafficBytesSentLevelMax	CounterBasedGauge64
	}

insightsTrafficBytesSentLevelName OBJECT-TYPE
	SYNTAX      DisplayString
	MAX-ACCESS  not-accessible
	STATUS      current
	DESCRIPTION
	"Table entry display string for insightsTrafficBytesSent"
	::={insightsTrafficBytesSentLevelEntry 1}

insightsTrafficBytesSentLevelVal OBJECT-TYPE
	SYNTAX	 Counter64
	MAX-ACCESS  read-only
	STATUS      current
	DESCRIPTION
	"Table entry attribute for insightsTrafficBytesSent"
	::={insightsTrafficBytesSentLevelEntry 2}

insightsTrafficBytesSentLevelMom OBJECT-TYPE
	SYNTAX	 CounterBasedGauge64
	MAX-ACCESS  read-only
	STATUS      current
	DESCRIPTION
	"Table entry attribute for insightsTrafficBytesSent"
	::={insightsTrafficBytesSentLevelEntry 3}

insightsTrafficBytesSentLevelMax OBJECT-TYPE
	SYNTAX	 CounterBasedGauge64
	MAX-ACCESS  read-only
	STATUS      current
	DESCRIPTION
	"Table entry attribute for insightsTrafficBytesSent"
	::={insightsTrafficBytesSentLevelEntry 4}


insightsTrafficZBytesSent	OBJECT IDENTIFIER ::={insights 20}

insightsTrafficZBytesSentVal	OBJECT-TYPE
	SYNTAX	 Counter64
	MAX-ACCESS read-only
	STATUS obsolete
	DESCRIPTION "Traffic: Compressed bytes sent"

	::={insightsTrafficZBytesSent 1}

insightsTrafficZBytesSentMom	OBJECT-TYPE
	SYNTAX	 CounterBasedGauge64
	MAX-ACCESS read-only
	STATUS obsolete
	DESCRIPTION "Traffic: Compressed bytes sent"

	::={insightsTrafficZBytesSent 2}

insightsTrafficZBytesSentMax	OBJECT-TYPE
	SYNTAX	 CounterBasedGauge64
	MAX-ACCESS read-only
	STATUS obsolete
	DESCRIPTION "Traffic: Compressed bytes sent"

	::={insightsTrafficZBytesSent 3}

insightsTrafficZBytesSentLevelTable OBJECT-TYPE
	SYNTAX      SEQUENCE OF InsightsTrafficZBytesSentLevelEntry
	MAX-ACCESS  not-accessible
	STATUS      current
	DESCRIPTION
	"Table for insightsTrafficZBytesSent"
	::={insightsTrafficZBytesSent 4}

insightsTrafficZBytesSentLevelEntry OBJECT-TYPE
	SYNTAX      InsightsTrafficZBytesSentLevelEntry
	MAX-ACCESS  not-accessible
	STATUS      current
	DESCRIPTION
	"Table entry for insightsTrafficZBytesSent"
	INDEX { insightsTrafficZBytesSentLevelName }
	::={insightsTrafficZBytesSentLevelTable 1}

InsightsTrafficZBytesSentLevelEntry ::=
	SEQUENCE {
		insightsTrafficZBytesSentLevelName	DisplayString,
		insightsTrafficZBytesSentLevelVal	Counter64,
		insightsTrafficZBytesSentLevelMom	CounterBasedGauge64,
		insightsTrafficZBytesSentLevelMax	CounterBasedGauge64
	}

insightsTrafficZBytesSentLevelName OBJECT-TYPE
	SYNTAX      DisplayString
	MAX-ACCESS  not-accessible
	STATUS      current
	DESCRIPTION
	"Table entry display string for insightsTrafficZBytesSent"
	::={insightsTrafficZBytesSentLevelEntry 1}

insightsTrafficZBytesSentLevelVal OBJECT-TYPE
	SYNTAX	 Counter64
	MAX-ACCESS  read-only
	STATUS      current
	DESCRIPTION
	"Table entry attribute for insightsTrafficZBytesSent"
	::={insightsTrafficZBytesSentLevelEntry 2}

insightsTrafficZBytesSentLevelMom OBJECT-TYPE
	SYNTAX	 CounterBasedGauge64
	MAX-ACCESS  read-only
	STATUS      current
	DESCRIPTION
	"Table entry attribute for insightsTrafficZBytesSent"
	::={insightsTrafficZBytesSentLevelEntry 3}

insightsTrafficZBytesSentLevelMax OBJECT-TYPE
	SYNTAX	 CounterBasedGauge64
	MAX-ACCESS  read-only
	STATUS      current
	DESCRIPTION
	"Table entry attribute for insightsTrafficZBytesSent"
	::={insightsTrafficZBytesSentLevelEntry 4}


insightsTrafficRecordsDropped	OBJECT IDENTIFIER ::={insights 21}

insightsTrafficRecordsDroppedVal	OBJECT-TYPE
	SYNTAX	 Counter64
	MAX-ACCESS read-only
	STATUS obsolete
	DESCRIPTION "Traffic: Records dropped"

	::={insightsTrafficRecordsDropped 1}

insightsTrafficRecordsDroppedMom	OBJECT-TYPE
	SYNTAX	 CounterBasedGauge64
	MAX-ACCESS read-only
	STATUS obsolete
	DESCRIPTION "Traffic: Records dropped"

	::={insightsTrafficRecordsDropped 2}

insightsTrafficRecordsDroppedMax	OBJECT-TYPE
	SYNTAX	 CounterBasedGauge64
	MAX-ACCESS read-only
	STATUS obsolete
	DESCRIPTION "Traffic: Records dropped"

	::={insightsTrafficRecordsDropped 3}

insightsTrafficRecordsDroppedLevelTable OBJECT-TYPE
	SYNTAX      SEQUENCE OF InsightsTrafficRecordsDroppedLevelEntry
	MAX-ACCESS  not-accessible
	STATUS      current
	DESCRIPTION
	"Table for insightsTrafficRecordsDropped"
	::={insightsTrafficRecordsDropped 4}

insightsTrafficRecordsDroppedLevelEntry OBJECT-TYPE
	SYNTAX      InsightsTrafficRecordsDroppedLevelEntry
	MAX-ACCESS  not-accessible
	STATUS      current
	DESCRIPTION
	"Table entry for insightsTrafficRecordsDropped"
	INDEX { insightsTrafficRecordsDroppedLevelName }
	::={insightsTrafficRecordsDroppedLevelTable 1}

InsightsTrafficRecordsDroppedLevelEntry ::=
	SEQUENCE {
		insightsTrafficRecordsDroppedLevelName	DisplayString,
		insightsTrafficRecordsDroppedLevelVal	Counter64,
		insightsTrafficRecordsDroppedLevelMom	CounterBasedGauge64,
		insightsTrafficRecordsDroppedLevelMax	CounterBasedGauge64
	}

insightsTrafficRecordsDroppedLevelName OBJECT-TYPE
	SYNTAX      DisplayString
	MAX-ACCESS  not-accessible
	STATUS      current
	DESCRIPTION
	"Table entry display string for insightsTrafficRecordsDropped"
	::={insightsTrafficRecordsDroppedLevelEntry 1}

insightsTrafficRecordsDroppedLevelVal OBJECT-TYPE
	SYNTAX	 Counter64
	MAX-ACCESS  read-only
	STATUS      current
	DESCRIPTION
	"Table entry attribute for insightsTrafficRecordsDropped"
	::={insightsTrafficRecordsDroppedLevelEntry 2}

insightsTrafficRecordsDroppedLevelMom OBJECT-TYPE
	SYNTAX	 CounterBasedGauge64
	MAX-ACCESS  read-only
	STATUS      current
	DESCRIPTION
	"Table entry attribute for insightsTrafficRecordsDropped"
	::={insightsTrafficRecordsDroppedLevelEntry 3}

insightsTrafficRecordsDroppedLevelMax OBJECT-TYPE
	SYNTAX	 CounterBasedGauge64
	MAX-ACCESS  read-only
	STATUS      current
	DESCRIPTION
	"Table entry attribute for insightsTrafficRecordsDropped"
	::={insightsTrafficRecordsDroppedLevelEntry 4}


insightsTrafficQueueSize	OBJECT IDENTIFIER ::={insights 22}

insightsTrafficQueueSizeVal	OBJECT-TYPE
	SYNTAX	 CounterBasedGauge64
	MAX-ACCESS read-only
	STATUS obsolete
	DESCRIPTION "Traffic: Queue size"

	::={insightsTrafficQueueSize 1}

insightsTrafficQueueSizeMax	OBJECT-TYPE
	SYNTAX	 CounterBasedGauge64
	MAX-ACCESS read-only
	STATUS obsolete
	DESCRIPTION "Traffic: Queue size"

	::={insightsTrafficQueueSize 3}

insightsTrafficQueueSizeLevelTable OBJECT-TYPE
	SYNTAX      SEQUENCE OF InsightsTrafficQueueSizeLevelEntry
	MAX-ACCESS  not-accessible
	STATUS      current
	DESCRIPTION
	"Table for insightsTrafficQueueSize"
	::={insightsTrafficQueueSize 4}

insightsTrafficQueueSizeLevelEntry OBJECT-TYPE
	SYNTAX      InsightsTrafficQueueSizeLevelEntry
	MAX-ACCESS  not-accessible
	STATUS      current
	DESCRIPTION
	"Table entry for insightsTrafficQueueSize"
	INDEX { insightsTrafficQueueSizeLevelName }
	::={insightsTrafficQueueSizeLevelTable 1}

InsightsTrafficQueueSizeLevelEntry ::=
	SEQUENCE {
		insightsTrafficQueueSizeLevelName	DisplayString,
		insightsTrafficQueueSizeLevelVal	CounterBasedGauge64,
		insightsTrafficQueueSizeLevelMax	CounterBasedGauge64
	}

insightsTrafficQueueSizeLevelName OBJECT-TYPE
	SYNTAX      DisplayString
	MAX-ACCESS  not-accessible
	STATUS      current
	DESCRIPTION
	"Table entry display string for insightsTrafficQueueSize"
	::={insightsTrafficQueueSizeLevelEntry 1}

insightsTrafficQueueSizeLevelVal OBJECT-TYPE
	SYNTAX	 CounterBasedGauge64
	MAX-ACCESS  read-only
	STATUS      current
	DESCRIPTION
	"Table entry attribute for insightsTrafficQueueSize"
	::={insightsTrafficQueueSizeLevelEntry 2}

insightsTrafficQueueSizeLevelMax OBJECT-TYPE
	SYNTAX	 CounterBasedGauge64
	MAX-ACCESS  read-only
	STATUS      current
	DESCRIPTION
	"Table entry attribute for insightsTrafficQueueSize"
	::={insightsTrafficQueueSizeLevelEntry 4}


insightsTrafficQueueUsage	OBJECT IDENTIFIER ::={insights 23}

insightsTrafficQueueUsageVal	OBJECT-TYPE
	SYNTAX	 Unsigned32
	MAX-ACCESS read-only
	STATUS obsolete
	DESCRIPTION "Traffic: Queue usage"

	::={insightsTrafficQueueUsage 1}

insightsTrafficQueueUsageMax	OBJECT-TYPE
	SYNTAX	 Unsigned32
	MAX-ACCESS read-only
	STATUS obsolete
	DESCRIPTION "Traffic: Queue usage"

	::={insightsTrafficQueueUsage 3}

insightsTrafficQueueUsageLevelTable OBJECT-TYPE
	SYNTAX      SEQUENCE OF InsightsTrafficQueueUsageLevelEntry
	MAX-ACCESS  not-accessible
	STATUS      current
	DESCRIPTION
	"Table for insightsTrafficQueueUsage"
	::={insightsTrafficQueueUsage 4}

insightsTrafficQueueUsageLevelEntry OBJECT-TYPE
	SYNTAX      InsightsTrafficQueueUsageLevelEntry
	MAX-ACCESS  not-accessible
	STATUS      current
	DESCRIPTION
	"Table entry for insightsTrafficQueueUsage"
	INDEX { insightsTrafficQueueUsageLevelName }
	::={insightsTrafficQueueUsageLevelTable 1}

InsightsTrafficQueueUsageLevelEntry ::=
	SEQUENCE {
		insightsTrafficQueueUsageLevelName	DisplayString,
		insightsTrafficQueueUsageLevelVal	Unsigned32,
		insightsTrafficQueueUsageLevelMax	Unsigned32
	}

insightsTrafficQueueUsageLevelName OBJECT-TYPE
	SYNTAX      DisplayString
	MAX-ACCESS  not-accessible
	STATUS      current
	DESCRIPTION
	"Table entry display string for insightsTrafficQueueUsage"
	::={insightsTrafficQueueUsageLevelEntry 1}

insightsTrafficQueueUsageLevelVal OBJECT-TYPE
	SYNTAX	 Unsigned32
	MAX-ACCESS  read-only
	STATUS      current
	DESCRIPTION
	"Table entry attribute for insightsTrafficQueueUsage"
	::={insightsTrafficQueueUsageLevelEntry 2}

insightsTrafficQueueUsageLevelMax OBJECT-TYPE
	SYNTAX	 Unsigned32
	MAX-ACCESS  read-only
	STATUS      current
	DESCRIPTION
	"Table entry attribute for insightsTrafficQueueUsage"
	::={insightsTrafficQueueUsageLevelEntry 4}


insightsScoreRecordsReceived	OBJECT IDENTIFIER ::={insights 24}

insightsScoreRecordsReceivedVal	OBJECT-TYPE
	SYNTAX	 Counter64
	MAX-ACCESS read-only
	STATUS current
	DESCRIPTION "Score: Host stats records received"

	::={insightsScoreRecordsReceived 1}

insightsScoreRecordsReceivedMom	OBJECT-TYPE
	SYNTAX	 CounterBasedGauge64
	MAX-ACCESS read-only
	STATUS current
	DESCRIPTION "Score: Host stats records received"

	::={insightsScoreRecordsReceived 2}

insightsScoreRecordsReceivedMax	OBJECT-TYPE
	SYNTAX	 CounterBasedGauge64
	MAX-ACCESS read-only
	STATUS current
	DESCRIPTION "Score: Host stats records received"

	::={insightsScoreRecordsReceived 3}

insightsScoreRecordsReceivedLevelTable OBJECT-TYPE
	SYNTAX      SEQUENCE OF InsightsScoreRecordsReceivedLevelEntry
	MAX-ACCESS  not-accessible
	STATUS      current
	DESCRIPTION
	"Table for insightsScoreRecordsReceived"
	::={insightsScoreRecordsReceived 4}

insightsScoreRecordsReceivedLevelEntry OBJECT-TYPE
	SYNTAX      InsightsScoreRecordsReceivedLevelEntry
	MAX-ACCESS  not-accessible
	STATUS      current
	DESCRIPTION
	"Table entry for insightsScoreRecordsReceived"
	INDEX { insightsScoreRecordsReceivedLevelName }
	::={insightsScoreRecordsReceivedLevelTable 1}

InsightsScoreRecordsReceivedLevelEntry ::=
	SEQUENCE {
		insightsScoreRecordsReceivedLevelName	DisplayString,
		insightsScoreRecordsReceivedLevelVal	Counter64,
		insightsScoreRecordsReceivedLevelMom	CounterBasedGauge64,
		insightsScoreRecordsReceivedLevelMax	CounterBasedGauge64
	}

insightsScoreRecordsReceivedLevelName OBJECT-TYPE
	SYNTAX      DisplayString
	MAX-ACCESS  not-accessible
	STATUS      current
	DESCRIPTION
	"Table entry display string for insightsScoreRecordsReceived"
	::={insightsScoreRecordsReceivedLevelEntry 1}

insightsScoreRecordsReceivedLevelVal OBJECT-TYPE
	SYNTAX	 Counter64
	MAX-ACCESS  read-only
	STATUS      current
	DESCRIPTION
	"Table entry attribute for insightsScoreRecordsReceived"
	::={insightsScoreRecordsReceivedLevelEntry 2}

insightsScoreRecordsReceivedLevelMom OBJECT-TYPE
	SYNTAX	 CounterBasedGauge64
	MAX-ACCESS  read-only
	STATUS      current
	DESCRIPTION
	"Table entry attribute for insightsScoreRecordsReceived"
	::={insightsScoreRecordsReceivedLevelEntry 3}

insightsScoreRecordsReceivedLevelMax OBJECT-TYPE
	SYNTAX	 CounterBasedGauge64
	MAX-ACCESS  read-only
	STATUS      current
	DESCRIPTION
	"Table entry attribute for insightsScoreRecordsReceived"
	::={insightsScoreRecordsReceivedLevelEntry 4}


insightsScoreSubscriberFound	OBJECT IDENTIFIER ::={insights 25}

insightsScoreSubscriberFoundVal	OBJECT-TYPE
	SYNTAX	 Counter64
	MAX-ACCESS read-only
	STATUS obsolete
	DESCRIPTION "Score: Number of times subscriber ID has been found"

	::={insightsScoreSubscriberFound 1}

insightsScoreSubscriberFoundMom	OBJECT-TYPE
	SYNTAX	 CounterBasedGauge64
	MAX-ACCESS read-only
	STATUS obsolete
	DESCRIPTION "Score: Number of times subscriber ID has been found"

	::={insightsScoreSubscriberFound 2}

insightsScoreSubscriberFoundMax	OBJECT-TYPE
	SYNTAX	 CounterBasedGauge64
	MAX-ACCESS read-only
	STATUS obsolete
	DESCRIPTION "Score: Number of times subscriber ID has been found"

	::={insightsScoreSubscriberFound 3}

insightsScoreSubscriberFoundLevelTable OBJECT-TYPE
	SYNTAX      SEQUENCE OF InsightsScoreSubscriberFoundLevelEntry
	MAX-ACCESS  not-accessible
	STATUS      current
	DESCRIPTION
	"Table for insightsScoreSubscriberFound"
	::={insightsScoreSubscriberFound 4}

insightsScoreSubscriberFoundLevelEntry OBJECT-TYPE
	SYNTAX      InsightsScoreSubscriberFoundLevelEntry
	MAX-ACCESS  not-accessible
	STATUS      current
	DESCRIPTION
	"Table entry for insightsScoreSubscriberFound"
	INDEX { insightsScoreSubscriberFoundLevelName }
	::={insightsScoreSubscriberFoundLevelTable 1}

InsightsScoreSubscriberFoundLevelEntry ::=
	SEQUENCE {
		insightsScoreSubscriberFoundLevelName	DisplayString,
		insightsScoreSubscriberFoundLevelVal	Counter64,
		insightsScoreSubscriberFoundLevelMom	CounterBasedGauge64,
		insightsScoreSubscriberFoundLevelMax	CounterBasedGauge64
	}

insightsScoreSubscriberFoundLevelName OBJECT-TYPE
	SYNTAX      DisplayString
	MAX-ACCESS  not-accessible
	STATUS      current
	DESCRIPTION
	"Table entry display string for insightsScoreSubscriberFound"
	::={insightsScoreSubscriberFoundLevelEntry 1}

insightsScoreSubscriberFoundLevelVal OBJECT-TYPE
	SYNTAX	 Counter64
	MAX-ACCESS  read-only
	STATUS      current
	DESCRIPTION
	"Table entry attribute for insightsScoreSubscriberFound"
	::={insightsScoreSubscriberFoundLevelEntry 2}

insightsScoreSubscriberFoundLevelMom OBJECT-TYPE
	SYNTAX	 CounterBasedGauge64
	MAX-ACCESS  read-only
	STATUS      current
	DESCRIPTION
	"Table entry attribute for insightsScoreSubscriberFound"
	::={insightsScoreSubscriberFoundLevelEntry 3}

insightsScoreSubscriberFoundLevelMax OBJECT-TYPE
	SYNTAX	 CounterBasedGauge64
	MAX-ACCESS  read-only
	STATUS      current
	DESCRIPTION
	"Table entry attribute for insightsScoreSubscriberFound"
	::={insightsScoreSubscriberFoundLevelEntry 4}


insightsScoreDeviceFound	OBJECT IDENTIFIER ::={insights 26}

insightsScoreDeviceFoundVal	OBJECT-TYPE
	SYNTAX	 Counter64
	MAX-ACCESS read-only
	STATUS obsolete
	DESCRIPTION "Score: Number of times device has been found"

	::={insightsScoreDeviceFound 1}

insightsScoreDeviceFoundMom	OBJECT-TYPE
	SYNTAX	 CounterBasedGauge64
	MAX-ACCESS read-only
	STATUS obsolete
	DESCRIPTION "Score: Number of times device has been found"

	::={insightsScoreDeviceFound 2}

insightsScoreDeviceFoundMax	OBJECT-TYPE
	SYNTAX	 CounterBasedGauge64
	MAX-ACCESS read-only
	STATUS obsolete
	DESCRIPTION "Score: Number of times device has been found"

	::={insightsScoreDeviceFound 3}

insightsScoreDeviceFoundLevelTable OBJECT-TYPE
	SYNTAX      SEQUENCE OF InsightsScoreDeviceFoundLevelEntry
	MAX-ACCESS  not-accessible
	STATUS      current
	DESCRIPTION
	"Table for insightsScoreDeviceFound"
	::={insightsScoreDeviceFound 4}

insightsScoreDeviceFoundLevelEntry OBJECT-TYPE
	SYNTAX      InsightsScoreDeviceFoundLevelEntry
	MAX-ACCESS  not-accessible
	STATUS      current
	DESCRIPTION
	"Table entry for insightsScoreDeviceFound"
	INDEX { insightsScoreDeviceFoundLevelName }
	::={insightsScoreDeviceFoundLevelTable 1}

InsightsScoreDeviceFoundLevelEntry ::=
	SEQUENCE {
		insightsScoreDeviceFoundLevelName	DisplayString,
		insightsScoreDeviceFoundLevelVal	Counter64,
		insightsScoreDeviceFoundLevelMom	CounterBasedGauge64,
		insightsScoreDeviceFoundLevelMax	CounterBasedGauge64
	}

insightsScoreDeviceFoundLevelName OBJECT-TYPE
	SYNTAX      DisplayString
	MAX-ACCESS  not-accessible
	STATUS      current
	DESCRIPTION
	"Table entry display string for insightsScoreDeviceFound"
	::={insightsScoreDeviceFoundLevelEntry 1}

insightsScoreDeviceFoundLevelVal OBJECT-TYPE
	SYNTAX	 Counter64
	MAX-ACCESS  read-only
	STATUS      current
	DESCRIPTION
	"Table entry attribute for insightsScoreDeviceFound"
	::={insightsScoreDeviceFoundLevelEntry 2}

insightsScoreDeviceFoundLevelMom OBJECT-TYPE
	SYNTAX	 CounterBasedGauge64
	MAX-ACCESS  read-only
	STATUS      current
	DESCRIPTION
	"Table entry attribute for insightsScoreDeviceFound"
	::={insightsScoreDeviceFoundLevelEntry 3}

insightsScoreDeviceFoundLevelMax OBJECT-TYPE
	SYNTAX	 CounterBasedGauge64
	MAX-ACCESS  read-only
	STATUS      current
	DESCRIPTION
	"Table entry attribute for insightsScoreDeviceFound"
	::={insightsScoreDeviceFoundLevelEntry 4}


insightsScoreLocationFound	OBJECT IDENTIFIER ::={insights 27}

insightsScoreLocationFoundVal	OBJECT-TYPE
	SYNTAX	 Counter64
	MAX-ACCESS read-only
	STATUS obsolete
	DESCRIPTION "Score: Number of times location has been found"

	::={insightsScoreLocationFound 1}

insightsScoreLocationFoundMom	OBJECT-TYPE
	SYNTAX	 CounterBasedGauge64
	MAX-ACCESS read-only
	STATUS obsolete
	DESCRIPTION "Score: Number of times location has been found"

	::={insightsScoreLocationFound 2}

insightsScoreLocationFoundMax	OBJECT-TYPE
	SYNTAX	 CounterBasedGauge64
	MAX-ACCESS read-only
	STATUS obsolete
	DESCRIPTION "Score: Number of times location has been found"

	::={insightsScoreLocationFound 3}

insightsScoreLocationFoundLevelTable OBJECT-TYPE
	SYNTAX      SEQUENCE OF InsightsScoreLocationFoundLevelEntry
	MAX-ACCESS  not-accessible
	STATUS      current
	DESCRIPTION
	"Table for insightsScoreLocationFound"
	::={insightsScoreLocationFound 4}

insightsScoreLocationFoundLevelEntry OBJECT-TYPE
	SYNTAX      InsightsScoreLocationFoundLevelEntry
	MAX-ACCESS  not-accessible
	STATUS      current
	DESCRIPTION
	"Table entry for insightsScoreLocationFound"
	INDEX { insightsScoreLocationFoundLevelName }
	::={insightsScoreLocationFoundLevelTable 1}

InsightsScoreLocationFoundLevelEntry ::=
	SEQUENCE {
		insightsScoreLocationFoundLevelName	DisplayString,
		insightsScoreLocationFoundLevelVal	Counter64,
		insightsScoreLocationFoundLevelMom	CounterBasedGauge64,
		insightsScoreLocationFoundLevelMax	CounterBasedGauge64
	}

insightsScoreLocationFoundLevelName OBJECT-TYPE
	SYNTAX      DisplayString
	MAX-ACCESS  not-accessible
	STATUS      current
	DESCRIPTION
	"Table entry display string for insightsScoreLocationFound"
	::={insightsScoreLocationFoundLevelEntry 1}

insightsScoreLocationFoundLevelVal OBJECT-TYPE
	SYNTAX	 Counter64
	MAX-ACCESS  read-only
	STATUS      current
	DESCRIPTION
	"Table entry attribute for insightsScoreLocationFound"
	::={insightsScoreLocationFoundLevelEntry 2}

insightsScoreLocationFoundLevelMom OBJECT-TYPE
	SYNTAX	 CounterBasedGauge64
	MAX-ACCESS  read-only
	STATUS      current
	DESCRIPTION
	"Table entry attribute for insightsScoreLocationFound"
	::={insightsScoreLocationFoundLevelEntry 3}

insightsScoreLocationFoundLevelMax OBJECT-TYPE
	SYNTAX	 CounterBasedGauge64
	MAX-ACCESS  read-only
	STATUS      current
	DESCRIPTION
	"Table entry attribute for insightsScoreLocationFound"
	::={insightsScoreLocationFoundLevelEntry 4}


insightsScoreTierFound	OBJECT IDENTIFIER ::={insights 28}

insightsScoreTierFoundVal	OBJECT-TYPE
	SYNTAX	 Counter64
	MAX-ACCESS read-only
	STATUS obsolete
	DESCRIPTION "Score: Number of times tier has been found"

	::={insightsScoreTierFound 1}

insightsScoreTierFoundMom	OBJECT-TYPE
	SYNTAX	 CounterBasedGauge64
	MAX-ACCESS read-only
	STATUS obsolete
	DESCRIPTION "Score: Number of times tier has been found"

	::={insightsScoreTierFound 2}

insightsScoreTierFoundMax	OBJECT-TYPE
	SYNTAX	 CounterBasedGauge64
	MAX-ACCESS read-only
	STATUS obsolete
	DESCRIPTION "Score: Number of times tier has been found"

	::={insightsScoreTierFound 3}

insightsScoreTierFoundLevelTable OBJECT-TYPE
	SYNTAX      SEQUENCE OF InsightsScoreTierFoundLevelEntry
	MAX-ACCESS  not-accessible
	STATUS      current
	DESCRIPTION
	"Table for insightsScoreTierFound"
	::={insightsScoreTierFound 4}

insightsScoreTierFoundLevelEntry OBJECT-TYPE
	SYNTAX      InsightsScoreTierFoundLevelEntry
	MAX-ACCESS  not-accessible
	STATUS      current
	DESCRIPTION
	"Table entry for insightsScoreTierFound"
	INDEX { insightsScoreTierFoundLevelName }
	::={insightsScoreTierFoundLevelTable 1}

InsightsScoreTierFoundLevelEntry ::=
	SEQUENCE {
		insightsScoreTierFoundLevelName	DisplayString,
		insightsScoreTierFoundLevelVal	Counter64,
		insightsScoreTierFoundLevelMom	CounterBasedGauge64,
		insightsScoreTierFoundLevelMax	CounterBasedGauge64
	}

insightsScoreTierFoundLevelName OBJECT-TYPE
	SYNTAX      DisplayString
	MAX-ACCESS  not-accessible
	STATUS      current
	DESCRIPTION
	"Table entry display string for insightsScoreTierFound"
	::={insightsScoreTierFoundLevelEntry 1}

insightsScoreTierFoundLevelVal OBJECT-TYPE
	SYNTAX	 Counter64
	MAX-ACCESS  read-only
	STATUS      current
	DESCRIPTION
	"Table entry attribute for insightsScoreTierFound"
	::={insightsScoreTierFoundLevelEntry 2}

insightsScoreTierFoundLevelMom OBJECT-TYPE
	SYNTAX	 CounterBasedGauge64
	MAX-ACCESS  read-only
	STATUS      current
	DESCRIPTION
	"Table entry attribute for insightsScoreTierFound"
	::={insightsScoreTierFoundLevelEntry 3}

insightsScoreTierFoundLevelMax OBJECT-TYPE
	SYNTAX	 CounterBasedGauge64
	MAX-ACCESS  read-only
	STATUS      current
	DESCRIPTION
	"Table entry attribute for insightsScoreTierFound"
	::={insightsScoreTierFoundLevelEntry 4}


insightsScoreNumDumpsSkipped	OBJECT IDENTIFIER ::={insights 29}

insightsScoreNumDumpsSkippedVal	OBJECT-TYPE
	SYNTAX	 CounterBasedGauge64
	MAX-ACCESS read-only
	STATUS obsolete
	DESCRIPTION "Score: Number of dumps skipped"

	::={insightsScoreNumDumpsSkipped 1}

insightsScoreNumDumpsSkippedMax	OBJECT-TYPE
	SYNTAX	 CounterBasedGauge64
	MAX-ACCESS read-only
	STATUS obsolete
	DESCRIPTION "Score: Number of dumps skipped"

	::={insightsScoreNumDumpsSkipped 3}

insightsScoreNumDumpsSkippedLevelTable OBJECT-TYPE
	SYNTAX      SEQUENCE OF InsightsScoreNumDumpsSkippedLevelEntry
	MAX-ACCESS  not-accessible
	STATUS      current
	DESCRIPTION
	"Table for insightsScoreNumDumpsSkipped"
	::={insightsScoreNumDumpsSkipped 4}

insightsScoreNumDumpsSkippedLevelEntry OBJECT-TYPE
	SYNTAX      InsightsScoreNumDumpsSkippedLevelEntry
	MAX-ACCESS  not-accessible
	STATUS      current
	DESCRIPTION
	"Table entry for insightsScoreNumDumpsSkipped"
	INDEX { insightsScoreNumDumpsSkippedLevelName }
	::={insightsScoreNumDumpsSkippedLevelTable 1}

InsightsScoreNumDumpsSkippedLevelEntry ::=
	SEQUENCE {
		insightsScoreNumDumpsSkippedLevelName	DisplayString,
		insightsScoreNumDumpsSkippedLevelVal	CounterBasedGauge64,
		insightsScoreNumDumpsSkippedLevelMax	CounterBasedGauge64
	}

insightsScoreNumDumpsSkippedLevelName OBJECT-TYPE
	SYNTAX      DisplayString
	MAX-ACCESS  not-accessible
	STATUS      current
	DESCRIPTION
	"Table entry display string for insightsScoreNumDumpsSkipped"
	::={insightsScoreNumDumpsSkippedLevelEntry 1}

insightsScoreNumDumpsSkippedLevelVal OBJECT-TYPE
	SYNTAX	 CounterBasedGauge64
	MAX-ACCESS  read-only
	STATUS      current
	DESCRIPTION
	"Table entry attribute for insightsScoreNumDumpsSkipped"
	::={insightsScoreNumDumpsSkippedLevelEntry 2}

insightsScoreNumDumpsSkippedLevelMax OBJECT-TYPE
	SYNTAX	 CounterBasedGauge64
	MAX-ACCESS  read-only
	STATUS      current
	DESCRIPTION
	"Table entry attribute for insightsScoreNumDumpsSkipped"
	::={insightsScoreNumDumpsSkippedLevelEntry 4}


insightsScoreLowFreqRecordsQueued	OBJECT IDENTIFIER ::={insights 30}

insightsScoreLowFreqRecordsQueuedVal	OBJECT-TYPE
	SYNTAX	 Counter64
	MAX-ACCESS read-only
	STATUS obsolete
	DESCRIPTION "Score: Low frequency records queued"

	::={insightsScoreLowFreqRecordsQueued 1}

insightsScoreLowFreqRecordsQueuedMom	OBJECT-TYPE
	SYNTAX	 CounterBasedGauge64
	MAX-ACCESS read-only
	STATUS obsolete
	DESCRIPTION "Score: Low frequency records queued"

	::={insightsScoreLowFreqRecordsQueued 2}

insightsScoreLowFreqRecordsQueuedMax	OBJECT-TYPE
	SYNTAX	 CounterBasedGauge64
	MAX-ACCESS read-only
	STATUS obsolete
	DESCRIPTION "Score: Low frequency records queued"

	::={insightsScoreLowFreqRecordsQueued 3}

insightsScoreLowFreqRecordsQueuedLevelTable OBJECT-TYPE
	SYNTAX      SEQUENCE OF InsightsScoreLowFreqRecordsQueuedLevelEntry
	MAX-ACCESS  not-accessible
	STATUS      current
	DESCRIPTION
	"Table for insightsScoreLowFreqRecordsQueued"
	::={insightsScoreLowFreqRecordsQueued 4}

insightsScoreLowFreqRecordsQueuedLevelEntry OBJECT-TYPE
	SYNTAX      InsightsScoreLowFreqRecordsQueuedLevelEntry
	MAX-ACCESS  not-accessible
	STATUS      current
	DESCRIPTION
	"Table entry for insightsScoreLowFreqRecordsQueued"
	INDEX { insightsScoreLowFreqRecordsQueuedLevelName }
	::={insightsScoreLowFreqRecordsQueuedLevelTable 1}

InsightsScoreLowFreqRecordsQueuedLevelEntry ::=
	SEQUENCE {
		insightsScoreLowFreqRecordsQueuedLevelName	DisplayString,
		insightsScoreLowFreqRecordsQueuedLevelVal	Counter64,
		insightsScoreLowFreqRecordsQueuedLevelMom	CounterBasedGauge64,
		insightsScoreLowFreqRecordsQueuedLevelMax	CounterBasedGauge64
	}

insightsScoreLowFreqRecordsQueuedLevelName OBJECT-TYPE
	SYNTAX      DisplayString
	MAX-ACCESS  not-accessible
	STATUS      current
	DESCRIPTION
	"Table entry display string for insightsScoreLowFreqRecordsQueued"
	::={insightsScoreLowFreqRecordsQueuedLevelEntry 1}

insightsScoreLowFreqRecordsQueuedLevelVal OBJECT-TYPE
	SYNTAX	 Counter64
	MAX-ACCESS  read-only
	STATUS      current
	DESCRIPTION
	"Table entry attribute for insightsScoreLowFreqRecordsQueued"
	::={insightsScoreLowFreqRecordsQueuedLevelEntry 2}

insightsScoreLowFreqRecordsQueuedLevelMom OBJECT-TYPE
	SYNTAX	 CounterBasedGauge64
	MAX-ACCESS  read-only
	STATUS      current
	DESCRIPTION
	"Table entry attribute for insightsScoreLowFreqRecordsQueued"
	::={insightsScoreLowFreqRecordsQueuedLevelEntry 3}

insightsScoreLowFreqRecordsQueuedLevelMax OBJECT-TYPE
	SYNTAX	 CounterBasedGauge64
	MAX-ACCESS  read-only
	STATUS      current
	DESCRIPTION
	"Table entry attribute for insightsScoreLowFreqRecordsQueued"
	::={insightsScoreLowFreqRecordsQueuedLevelEntry 4}


insightsScoreLowFreqBytesQueued	OBJECT IDENTIFIER ::={insights 31}

insightsScoreLowFreqBytesQueuedVal	OBJECT-TYPE
	SYNTAX	 Counter64
	MAX-ACCESS read-only
	STATUS obsolete
	DESCRIPTION "Score: Low frequency bytes queued"

	::={insightsScoreLowFreqBytesQueued 1}

insightsScoreLowFreqBytesQueuedMom	OBJECT-TYPE
	SYNTAX	 CounterBasedGauge64
	MAX-ACCESS read-only
	STATUS obsolete
	DESCRIPTION "Score: Low frequency bytes queued"

	::={insightsScoreLowFreqBytesQueued 2}

insightsScoreLowFreqBytesQueuedMax	OBJECT-TYPE
	SYNTAX	 CounterBasedGauge64
	MAX-ACCESS read-only
	STATUS obsolete
	DESCRIPTION "Score: Low frequency bytes queued"

	::={insightsScoreLowFreqBytesQueued 3}

insightsScoreLowFreqBytesQueuedLevelTable OBJECT-TYPE
	SYNTAX      SEQUENCE OF InsightsScoreLowFreqBytesQueuedLevelEntry
	MAX-ACCESS  not-accessible
	STATUS      current
	DESCRIPTION
	"Table for insightsScoreLowFreqBytesQueued"
	::={insightsScoreLowFreqBytesQueued 4}

insightsScoreLowFreqBytesQueuedLevelEntry OBJECT-TYPE
	SYNTAX      InsightsScoreLowFreqBytesQueuedLevelEntry
	MAX-ACCESS  not-accessible
	STATUS      current
	DESCRIPTION
	"Table entry for insightsScoreLowFreqBytesQueued"
	INDEX { insightsScoreLowFreqBytesQueuedLevelName }
	::={insightsScoreLowFreqBytesQueuedLevelTable 1}

InsightsScoreLowFreqBytesQueuedLevelEntry ::=
	SEQUENCE {
		insightsScoreLowFreqBytesQueuedLevelName	DisplayString,
		insightsScoreLowFreqBytesQueuedLevelVal	Counter64,
		insightsScoreLowFreqBytesQueuedLevelMom	CounterBasedGauge64,
		insightsScoreLowFreqBytesQueuedLevelMax	CounterBasedGauge64
	}

insightsScoreLowFreqBytesQueuedLevelName OBJECT-TYPE
	SYNTAX      DisplayString
	MAX-ACCESS  not-accessible
	STATUS      current
	DESCRIPTION
	"Table entry display string for insightsScoreLowFreqBytesQueued"
	::={insightsScoreLowFreqBytesQueuedLevelEntry 1}

insightsScoreLowFreqBytesQueuedLevelVal OBJECT-TYPE
	SYNTAX	 Counter64
	MAX-ACCESS  read-only
	STATUS      current
	DESCRIPTION
	"Table entry attribute for insightsScoreLowFreqBytesQueued"
	::={insightsScoreLowFreqBytesQueuedLevelEntry 2}

insightsScoreLowFreqBytesQueuedLevelMom OBJECT-TYPE
	SYNTAX	 CounterBasedGauge64
	MAX-ACCESS  read-only
	STATUS      current
	DESCRIPTION
	"Table entry attribute for insightsScoreLowFreqBytesQueued"
	::={insightsScoreLowFreqBytesQueuedLevelEntry 3}

insightsScoreLowFreqBytesQueuedLevelMax OBJECT-TYPE
	SYNTAX	 CounterBasedGauge64
	MAX-ACCESS  read-only
	STATUS      current
	DESCRIPTION
	"Table entry attribute for insightsScoreLowFreqBytesQueued"
	::={insightsScoreLowFreqBytesQueuedLevelEntry 4}


insightsScoreHighFreqRecordsQueued	OBJECT IDENTIFIER ::={insights 32}

insightsScoreHighFreqRecordsQueuedVal	OBJECT-TYPE
	SYNTAX	 Counter64
	MAX-ACCESS read-only
	STATUS obsolete
	DESCRIPTION "Score: High frequency records queued"

	::={insightsScoreHighFreqRecordsQueued 1}

insightsScoreHighFreqRecordsQueuedMom	OBJECT-TYPE
	SYNTAX	 CounterBasedGauge64
	MAX-ACCESS read-only
	STATUS obsolete
	DESCRIPTION "Score: High frequency records queued"

	::={insightsScoreHighFreqRecordsQueued 2}

insightsScoreHighFreqRecordsQueuedMax	OBJECT-TYPE
	SYNTAX	 CounterBasedGauge64
	MAX-ACCESS read-only
	STATUS obsolete
	DESCRIPTION "Score: High frequency records queued"

	::={insightsScoreHighFreqRecordsQueued 3}

insightsScoreHighFreqRecordsQueuedLevelTable OBJECT-TYPE
	SYNTAX      SEQUENCE OF InsightsScoreHighFreqRecordsQueuedLevelEntry
	MAX-ACCESS  not-accessible
	STATUS      current
	DESCRIPTION
	"Table for insightsScoreHighFreqRecordsQueued"
	::={insightsScoreHighFreqRecordsQueued 4}

insightsScoreHighFreqRecordsQueuedLevelEntry OBJECT-TYPE
	SYNTAX      InsightsScoreHighFreqRecordsQueuedLevelEntry
	MAX-ACCESS  not-accessible
	STATUS      current
	DESCRIPTION
	"Table entry for insightsScoreHighFreqRecordsQueued"
	INDEX { insightsScoreHighFreqRecordsQueuedLevelName }
	::={insightsScoreHighFreqRecordsQueuedLevelTable 1}

InsightsScoreHighFreqRecordsQueuedLevelEntry ::=
	SEQUENCE {
		insightsScoreHighFreqRecordsQueuedLevelName	DisplayString,
		insightsScoreHighFreqRecordsQueuedLevelVal	Counter64,
		insightsScoreHighFreqRecordsQueuedLevelMom	CounterBasedGauge64,
		insightsScoreHighFreqRecordsQueuedLevelMax	CounterBasedGauge64
	}

insightsScoreHighFreqRecordsQueuedLevelName OBJECT-TYPE
	SYNTAX      DisplayString
	MAX-ACCESS  not-accessible
	STATUS      current
	DESCRIPTION
	"Table entry display string for insightsScoreHighFreqRecordsQueued"
	::={insightsScoreHighFreqRecordsQueuedLevelEntry 1}

insightsScoreHighFreqRecordsQueuedLevelVal OBJECT-TYPE
	SYNTAX	 Counter64
	MAX-ACCESS  read-only
	STATUS      current
	DESCRIPTION
	"Table entry attribute for insightsScoreHighFreqRecordsQueued"
	::={insightsScoreHighFreqRecordsQueuedLevelEntry 2}

insightsScoreHighFreqRecordsQueuedLevelMom OBJECT-TYPE
	SYNTAX	 CounterBasedGauge64
	MAX-ACCESS  read-only
	STATUS      current
	DESCRIPTION
	"Table entry attribute for insightsScoreHighFreqRecordsQueued"
	::={insightsScoreHighFreqRecordsQueuedLevelEntry 3}

insightsScoreHighFreqRecordsQueuedLevelMax OBJECT-TYPE
	SYNTAX	 CounterBasedGauge64
	MAX-ACCESS  read-only
	STATUS      current
	DESCRIPTION
	"Table entry attribute for insightsScoreHighFreqRecordsQueued"
	::={insightsScoreHighFreqRecordsQueuedLevelEntry 4}


insightsScoreHighFreqBytesQueued	OBJECT IDENTIFIER ::={insights 33}

insightsScoreHighFreqBytesQueuedVal	OBJECT-TYPE
	SYNTAX	 Counter64
	MAX-ACCESS read-only
	STATUS obsolete
	DESCRIPTION "Score: High frequency bytes queued"

	::={insightsScoreHighFreqBytesQueued 1}

insightsScoreHighFreqBytesQueuedMom	OBJECT-TYPE
	SYNTAX	 CounterBasedGauge64
	MAX-ACCESS read-only
	STATUS obsolete
	DESCRIPTION "Score: High frequency bytes queued"

	::={insightsScoreHighFreqBytesQueued 2}

insightsScoreHighFreqBytesQueuedMax	OBJECT-TYPE
	SYNTAX	 CounterBasedGauge64
	MAX-ACCESS read-only
	STATUS obsolete
	DESCRIPTION "Score: High frequency bytes queued"

	::={insightsScoreHighFreqBytesQueued 3}

insightsScoreHighFreqBytesQueuedLevelTable OBJECT-TYPE
	SYNTAX      SEQUENCE OF InsightsScoreHighFreqBytesQueuedLevelEntry
	MAX-ACCESS  not-accessible
	STATUS      current
	DESCRIPTION
	"Table for insightsScoreHighFreqBytesQueued"
	::={insightsScoreHighFreqBytesQueued 4}

insightsScoreHighFreqBytesQueuedLevelEntry OBJECT-TYPE
	SYNTAX      InsightsScoreHighFreqBytesQueuedLevelEntry
	MAX-ACCESS  not-accessible
	STATUS      current
	DESCRIPTION
	"Table entry for insightsScoreHighFreqBytesQueued"
	INDEX { insightsScoreHighFreqBytesQueuedLevelName }
	::={insightsScoreHighFreqBytesQueuedLevelTable 1}

InsightsScoreHighFreqBytesQueuedLevelEntry ::=
	SEQUENCE {
		insightsScoreHighFreqBytesQueuedLevelName	DisplayString,
		insightsScoreHighFreqBytesQueuedLevelVal	Counter64,
		insightsScoreHighFreqBytesQueuedLevelMom	CounterBasedGauge64,
		insightsScoreHighFreqBytesQueuedLevelMax	CounterBasedGauge64
	}

insightsScoreHighFreqBytesQueuedLevelName OBJECT-TYPE
	SYNTAX      DisplayString
	MAX-ACCESS  not-accessible
	STATUS      current
	DESCRIPTION
	"Table entry display string for insightsScoreHighFreqBytesQueued"
	::={insightsScoreHighFreqBytesQueuedLevelEntry 1}

insightsScoreHighFreqBytesQueuedLevelVal OBJECT-TYPE
	SYNTAX	 Counter64
	MAX-ACCESS  read-only
	STATUS      current
	DESCRIPTION
	"Table entry attribute for insightsScoreHighFreqBytesQueued"
	::={insightsScoreHighFreqBytesQueuedLevelEntry 2}

insightsScoreHighFreqBytesQueuedLevelMom OBJECT-TYPE
	SYNTAX	 CounterBasedGauge64
	MAX-ACCESS  read-only
	STATUS      current
	DESCRIPTION
	"Table entry attribute for insightsScoreHighFreqBytesQueued"
	::={insightsScoreHighFreqBytesQueuedLevelEntry 3}

insightsScoreHighFreqBytesQueuedLevelMax OBJECT-TYPE
	SYNTAX	 CounterBasedGauge64
	MAX-ACCESS  read-only
	STATUS      current
	DESCRIPTION
	"Table entry attribute for insightsScoreHighFreqBytesQueued"
	::={insightsScoreHighFreqBytesQueuedLevelEntry 4}


insightsScoreLowFreqMessagesSent	OBJECT IDENTIFIER ::={insights 34}

insightsScoreLowFreqMessagesSentVal	OBJECT-TYPE
	SYNTAX	 Counter64
	MAX-ACCESS read-only
	STATUS obsolete
	DESCRIPTION "Score: Low frequency messages sent"

	::={insightsScoreLowFreqMessagesSent 1}

insightsScoreLowFreqMessagesSentMom	OBJECT-TYPE
	SYNTAX	 CounterBasedGauge64
	MAX-ACCESS read-only
	STATUS obsolete
	DESCRIPTION "Score: Low frequency messages sent"

	::={insightsScoreLowFreqMessagesSent 2}

insightsScoreLowFreqMessagesSentMax	OBJECT-TYPE
	SYNTAX	 CounterBasedGauge64
	MAX-ACCESS read-only
	STATUS obsolete
	DESCRIPTION "Score: Low frequency messages sent"

	::={insightsScoreLowFreqMessagesSent 3}

insightsScoreLowFreqMessagesSentLevelTable OBJECT-TYPE
	SYNTAX      SEQUENCE OF InsightsScoreLowFreqMessagesSentLevelEntry
	MAX-ACCESS  not-accessible
	STATUS      current
	DESCRIPTION
	"Table for insightsScoreLowFreqMessagesSent"
	::={insightsScoreLowFreqMessagesSent 4}

insightsScoreLowFreqMessagesSentLevelEntry OBJECT-TYPE
	SYNTAX      InsightsScoreLowFreqMessagesSentLevelEntry
	MAX-ACCESS  not-accessible
	STATUS      current
	DESCRIPTION
	"Table entry for insightsScoreLowFreqMessagesSent"
	INDEX { insightsScoreLowFreqMessagesSentLevelName }
	::={insightsScoreLowFreqMessagesSentLevelTable 1}

InsightsScoreLowFreqMessagesSentLevelEntry ::=
	SEQUENCE {
		insightsScoreLowFreqMessagesSentLevelName	DisplayString,
		insightsScoreLowFreqMessagesSentLevelVal	Counter64,
		insightsScoreLowFreqMessagesSentLevelMom	CounterBasedGauge64,
		insightsScoreLowFreqMessagesSentLevelMax	CounterBasedGauge64
	}

insightsScoreLowFreqMessagesSentLevelName OBJECT-TYPE
	SYNTAX      DisplayString
	MAX-ACCESS  not-accessible
	STATUS      current
	DESCRIPTION
	"Table entry display string for insightsScoreLowFreqMessagesSent"
	::={insightsScoreLowFreqMessagesSentLevelEntry 1}

insightsScoreLowFreqMessagesSentLevelVal OBJECT-TYPE
	SYNTAX	 Counter64
	MAX-ACCESS  read-only
	STATUS      current
	DESCRIPTION
	"Table entry attribute for insightsScoreLowFreqMessagesSent"
	::={insightsScoreLowFreqMessagesSentLevelEntry 2}

insightsScoreLowFreqMessagesSentLevelMom OBJECT-TYPE
	SYNTAX	 CounterBasedGauge64
	MAX-ACCESS  read-only
	STATUS      current
	DESCRIPTION
	"Table entry attribute for insightsScoreLowFreqMessagesSent"
	::={insightsScoreLowFreqMessagesSentLevelEntry 3}

insightsScoreLowFreqMessagesSentLevelMax OBJECT-TYPE
	SYNTAX	 CounterBasedGauge64
	MAX-ACCESS  read-only
	STATUS      current
	DESCRIPTION
	"Table entry attribute for insightsScoreLowFreqMessagesSent"
	::={insightsScoreLowFreqMessagesSentLevelEntry 4}


insightsScoreLowFreqRecordsSent	OBJECT IDENTIFIER ::={insights 35}

insightsScoreLowFreqRecordsSentVal	OBJECT-TYPE
	SYNTAX	 Counter64
	MAX-ACCESS read-only
	STATUS obsolete
	DESCRIPTION "Score: Low frequency records sent"

	::={insightsScoreLowFreqRecordsSent 1}

insightsScoreLowFreqRecordsSentMom	OBJECT-TYPE
	SYNTAX	 CounterBasedGauge64
	MAX-ACCESS read-only
	STATUS obsolete
	DESCRIPTION "Score: Low frequency records sent"

	::={insightsScoreLowFreqRecordsSent 2}

insightsScoreLowFreqRecordsSentMax	OBJECT-TYPE
	SYNTAX	 CounterBasedGauge64
	MAX-ACCESS read-only
	STATUS obsolete
	DESCRIPTION "Score: Low frequency records sent"

	::={insightsScoreLowFreqRecordsSent 3}

insightsScoreLowFreqRecordsSentLevelTable OBJECT-TYPE
	SYNTAX      SEQUENCE OF InsightsScoreLowFreqRecordsSentLevelEntry
	MAX-ACCESS  not-accessible
	STATUS      current
	DESCRIPTION
	"Table for insightsScoreLowFreqRecordsSent"
	::={insightsScoreLowFreqRecordsSent 4}

insightsScoreLowFreqRecordsSentLevelEntry OBJECT-TYPE
	SYNTAX      InsightsScoreLowFreqRecordsSentLevelEntry
	MAX-ACCESS  not-accessible
	STATUS      current
	DESCRIPTION
	"Table entry for insightsScoreLowFreqRecordsSent"
	INDEX { insightsScoreLowFreqRecordsSentLevelName }
	::={insightsScoreLowFreqRecordsSentLevelTable 1}

InsightsScoreLowFreqRecordsSentLevelEntry ::=
	SEQUENCE {
		insightsScoreLowFreqRecordsSentLevelName	DisplayString,
		insightsScoreLowFreqRecordsSentLevelVal	Counter64,
		insightsScoreLowFreqRecordsSentLevelMom	CounterBasedGauge64,
		insightsScoreLowFreqRecordsSentLevelMax	CounterBasedGauge64
	}

insightsScoreLowFreqRecordsSentLevelName OBJECT-TYPE
	SYNTAX      DisplayString
	MAX-ACCESS  not-accessible
	STATUS      current
	DESCRIPTION
	"Table entry display string for insightsScoreLowFreqRecordsSent"
	::={insightsScoreLowFreqRecordsSentLevelEntry 1}

insightsScoreLowFreqRecordsSentLevelVal OBJECT-TYPE
	SYNTAX	 Counter64
	MAX-ACCESS  read-only
	STATUS      current
	DESCRIPTION
	"Table entry attribute for insightsScoreLowFreqRecordsSent"
	::={insightsScoreLowFreqRecordsSentLevelEntry 2}

insightsScoreLowFreqRecordsSentLevelMom OBJECT-TYPE
	SYNTAX	 CounterBasedGauge64
	MAX-ACCESS  read-only
	STATUS      current
	DESCRIPTION
	"Table entry attribute for insightsScoreLowFreqRecordsSent"
	::={insightsScoreLowFreqRecordsSentLevelEntry 3}

insightsScoreLowFreqRecordsSentLevelMax OBJECT-TYPE
	SYNTAX	 CounterBasedGauge64
	MAX-ACCESS  read-only
	STATUS      current
	DESCRIPTION
	"Table entry attribute for insightsScoreLowFreqRecordsSent"
	::={insightsScoreLowFreqRecordsSentLevelEntry 4}


insightsScoreLowFreqBytesSent	OBJECT IDENTIFIER ::={insights 36}

insightsScoreLowFreqBytesSentVal	OBJECT-TYPE
	SYNTAX	 Counter64
	MAX-ACCESS read-only
	STATUS obsolete
	DESCRIPTION "Score: Low frequency bytes sent"

	::={insightsScoreLowFreqBytesSent 1}

insightsScoreLowFreqBytesSentMom	OBJECT-TYPE
	SYNTAX	 CounterBasedGauge64
	MAX-ACCESS read-only
	STATUS obsolete
	DESCRIPTION "Score: Low frequency bytes sent"

	::={insightsScoreLowFreqBytesSent 2}

insightsScoreLowFreqBytesSentMax	OBJECT-TYPE
	SYNTAX	 CounterBasedGauge64
	MAX-ACCESS read-only
	STATUS obsolete
	DESCRIPTION "Score: Low frequency bytes sent"

	::={insightsScoreLowFreqBytesSent 3}

insightsScoreLowFreqBytesSentLevelTable OBJECT-TYPE
	SYNTAX      SEQUENCE OF InsightsScoreLowFreqBytesSentLevelEntry
	MAX-ACCESS  not-accessible
	STATUS      current
	DESCRIPTION
	"Table for insightsScoreLowFreqBytesSent"
	::={insightsScoreLowFreqBytesSent 4}

insightsScoreLowFreqBytesSentLevelEntry OBJECT-TYPE
	SYNTAX      InsightsScoreLowFreqBytesSentLevelEntry
	MAX-ACCESS  not-accessible
	STATUS      current
	DESCRIPTION
	"Table entry for insightsScoreLowFreqBytesSent"
	INDEX { insightsScoreLowFreqBytesSentLevelName }
	::={insightsScoreLowFreqBytesSentLevelTable 1}

InsightsScoreLowFreqBytesSentLevelEntry ::=
	SEQUENCE {
		insightsScoreLowFreqBytesSentLevelName	DisplayString,
		insightsScoreLowFreqBytesSentLevelVal	Counter64,
		insightsScoreLowFreqBytesSentLevelMom	CounterBasedGauge64,
		insightsScoreLowFreqBytesSentLevelMax	CounterBasedGauge64
	}

insightsScoreLowFreqBytesSentLevelName OBJECT-TYPE
	SYNTAX      DisplayString
	MAX-ACCESS  not-accessible
	STATUS      current
	DESCRIPTION
	"Table entry display string for insightsScoreLowFreqBytesSent"
	::={insightsScoreLowFreqBytesSentLevelEntry 1}

insightsScoreLowFreqBytesSentLevelVal OBJECT-TYPE
	SYNTAX	 Counter64
	MAX-ACCESS  read-only
	STATUS      current
	DESCRIPTION
	"Table entry attribute for insightsScoreLowFreqBytesSent"
	::={insightsScoreLowFreqBytesSentLevelEntry 2}

insightsScoreLowFreqBytesSentLevelMom OBJECT-TYPE
	SYNTAX	 CounterBasedGauge64
	MAX-ACCESS  read-only
	STATUS      current
	DESCRIPTION
	"Table entry attribute for insightsScoreLowFreqBytesSent"
	::={insightsScoreLowFreqBytesSentLevelEntry 3}

insightsScoreLowFreqBytesSentLevelMax OBJECT-TYPE
	SYNTAX	 CounterBasedGauge64
	MAX-ACCESS  read-only
	STATUS      current
	DESCRIPTION
	"Table entry attribute for insightsScoreLowFreqBytesSent"
	::={insightsScoreLowFreqBytesSentLevelEntry 4}


insightsScoreLowFreqZBytesSent	OBJECT IDENTIFIER ::={insights 37}

insightsScoreLowFreqZBytesSentVal	OBJECT-TYPE
	SYNTAX	 Counter64
	MAX-ACCESS read-only
	STATUS obsolete
	DESCRIPTION "Score: Low frequency bytes sent"

	::={insightsScoreLowFreqZBytesSent 1}

insightsScoreLowFreqZBytesSentMom	OBJECT-TYPE
	SYNTAX	 CounterBasedGauge64
	MAX-ACCESS read-only
	STATUS obsolete
	DESCRIPTION "Score: Low frequency bytes sent"

	::={insightsScoreLowFreqZBytesSent 2}

insightsScoreLowFreqZBytesSentMax	OBJECT-TYPE
	SYNTAX	 CounterBasedGauge64
	MAX-ACCESS read-only
	STATUS obsolete
	DESCRIPTION "Score: Low frequency bytes sent"

	::={insightsScoreLowFreqZBytesSent 3}

insightsScoreLowFreqZBytesSentLevelTable OBJECT-TYPE
	SYNTAX      SEQUENCE OF InsightsScoreLowFreqZBytesSentLevelEntry
	MAX-ACCESS  not-accessible
	STATUS      current
	DESCRIPTION
	"Table for insightsScoreLowFreqZBytesSent"
	::={insightsScoreLowFreqZBytesSent 4}

insightsScoreLowFreqZBytesSentLevelEntry OBJECT-TYPE
	SYNTAX      InsightsScoreLowFreqZBytesSentLevelEntry
	MAX-ACCESS  not-accessible
	STATUS      current
	DESCRIPTION
	"Table entry for insightsScoreLowFreqZBytesSent"
	INDEX { insightsScoreLowFreqZBytesSentLevelName }
	::={insightsScoreLowFreqZBytesSentLevelTable 1}

InsightsScoreLowFreqZBytesSentLevelEntry ::=
	SEQUENCE {
		insightsScoreLowFreqZBytesSentLevelName	DisplayString,
		insightsScoreLowFreqZBytesSentLevelVal	Counter64,
		insightsScoreLowFreqZBytesSentLevelMom	CounterBasedGauge64,
		insightsScoreLowFreqZBytesSentLevelMax	CounterBasedGauge64
	}

insightsScoreLowFreqZBytesSentLevelName OBJECT-TYPE
	SYNTAX      DisplayString
	MAX-ACCESS  not-accessible
	STATUS      current
	DESCRIPTION
	"Table entry display string for insightsScoreLowFreqZBytesSent"
	::={insightsScoreLowFreqZBytesSentLevelEntry 1}

insightsScoreLowFreqZBytesSentLevelVal OBJECT-TYPE
	SYNTAX	 Counter64
	MAX-ACCESS  read-only
	STATUS      current
	DESCRIPTION
	"Table entry attribute for insightsScoreLowFreqZBytesSent"
	::={insightsScoreLowFreqZBytesSentLevelEntry 2}

insightsScoreLowFreqZBytesSentLevelMom OBJECT-TYPE
	SYNTAX	 CounterBasedGauge64
	MAX-ACCESS  read-only
	STATUS      current
	DESCRIPTION
	"Table entry attribute for insightsScoreLowFreqZBytesSent"
	::={insightsScoreLowFreqZBytesSentLevelEntry 3}

insightsScoreLowFreqZBytesSentLevelMax OBJECT-TYPE
	SYNTAX	 CounterBasedGauge64
	MAX-ACCESS  read-only
	STATUS      current
	DESCRIPTION
	"Table entry attribute for insightsScoreLowFreqZBytesSent"
	::={insightsScoreLowFreqZBytesSentLevelEntry 4}


insightsScoreLowFreqRecordsDropped	OBJECT IDENTIFIER ::={insights 38}

insightsScoreLowFreqRecordsDroppedVal	OBJECT-TYPE
	SYNTAX	 Counter64
	MAX-ACCESS read-only
	STATUS obsolete
	DESCRIPTION "Score: Low frequency records dropped"

	::={insightsScoreLowFreqRecordsDropped 1}

insightsScoreLowFreqRecordsDroppedMom	OBJECT-TYPE
	SYNTAX	 CounterBasedGauge64
	MAX-ACCESS read-only
	STATUS obsolete
	DESCRIPTION "Score: Low frequency records dropped"

	::={insightsScoreLowFreqRecordsDropped 2}

insightsScoreLowFreqRecordsDroppedMax	OBJECT-TYPE
	SYNTAX	 CounterBasedGauge64
	MAX-ACCESS read-only
	STATUS obsolete
	DESCRIPTION "Score: Low frequency records dropped"

	::={insightsScoreLowFreqRecordsDropped 3}

insightsScoreLowFreqRecordsDroppedLevelTable OBJECT-TYPE
	SYNTAX      SEQUENCE OF InsightsScoreLowFreqRecordsDroppedLevelEntry
	MAX-ACCESS  not-accessible
	STATUS      current
	DESCRIPTION
	"Table for insightsScoreLowFreqRecordsDropped"
	::={insightsScoreLowFreqRecordsDropped 4}

insightsScoreLowFreqRecordsDroppedLevelEntry OBJECT-TYPE
	SYNTAX      InsightsScoreLowFreqRecordsDroppedLevelEntry
	MAX-ACCESS  not-accessible
	STATUS      current
	DESCRIPTION
	"Table entry for insightsScoreLowFreqRecordsDropped"
	INDEX { insightsScoreLowFreqRecordsDroppedLevelName }
	::={insightsScoreLowFreqRecordsDroppedLevelTable 1}

InsightsScoreLowFreqRecordsDroppedLevelEntry ::=
	SEQUENCE {
		insightsScoreLowFreqRecordsDroppedLevelName	DisplayString,
		insightsScoreLowFreqRecordsDroppedLevelVal	Counter64,
		insightsScoreLowFreqRecordsDroppedLevelMom	CounterBasedGauge64,
		insightsScoreLowFreqRecordsDroppedLevelMax	CounterBasedGauge64
	}

insightsScoreLowFreqRecordsDroppedLevelName OBJECT-TYPE
	SYNTAX      DisplayString
	MAX-ACCESS  not-accessible
	STATUS      current
	DESCRIPTION
	"Table entry display string for insightsScoreLowFreqRecordsDropped"
	::={insightsScoreLowFreqRecordsDroppedLevelEntry 1}

insightsScoreLowFreqRecordsDroppedLevelVal OBJECT-TYPE
	SYNTAX	 Counter64
	MAX-ACCESS  read-only
	STATUS      current
	DESCRIPTION
	"Table entry attribute for insightsScoreLowFreqRecordsDropped"
	::={insightsScoreLowFreqRecordsDroppedLevelEntry 2}

insightsScoreLowFreqRecordsDroppedLevelMom OBJECT-TYPE
	SYNTAX	 CounterBasedGauge64
	MAX-ACCESS  read-only
	STATUS      current
	DESCRIPTION
	"Table entry attribute for insightsScoreLowFreqRecordsDropped"
	::={insightsScoreLowFreqRecordsDroppedLevelEntry 3}

insightsScoreLowFreqRecordsDroppedLevelMax OBJECT-TYPE
	SYNTAX	 CounterBasedGauge64
	MAX-ACCESS  read-only
	STATUS      current
	DESCRIPTION
	"Table entry attribute for insightsScoreLowFreqRecordsDropped"
	::={insightsScoreLowFreqRecordsDroppedLevelEntry 4}


insightsScoreLowFreqQueueSize	OBJECT IDENTIFIER ::={insights 39}

insightsScoreLowFreqQueueSizeVal	OBJECT-TYPE
	SYNTAX	 CounterBasedGauge64
	MAX-ACCESS read-only
	STATUS obsolete
	DESCRIPTION "Score: Low frequency queue size"

	::={insightsScoreLowFreqQueueSize 1}

insightsScoreLowFreqQueueSizeMax	OBJECT-TYPE
	SYNTAX	 CounterBasedGauge64
	MAX-ACCESS read-only
	STATUS obsolete
	DESCRIPTION "Score: Low frequency queue size"

	::={insightsScoreLowFreqQueueSize 3}

insightsScoreLowFreqQueueSizeLevelTable OBJECT-TYPE
	SYNTAX      SEQUENCE OF InsightsScoreLowFreqQueueSizeLevelEntry
	MAX-ACCESS  not-accessible
	STATUS      current
	DESCRIPTION
	"Table for insightsScoreLowFreqQueueSize"
	::={insightsScoreLowFreqQueueSize 4}

insightsScoreLowFreqQueueSizeLevelEntry OBJECT-TYPE
	SYNTAX      InsightsScoreLowFreqQueueSizeLevelEntry
	MAX-ACCESS  not-accessible
	STATUS      current
	DESCRIPTION
	"Table entry for insightsScoreLowFreqQueueSize"
	INDEX { insightsScoreLowFreqQueueSizeLevelName }
	::={insightsScoreLowFreqQueueSizeLevelTable 1}

InsightsScoreLowFreqQueueSizeLevelEntry ::=
	SEQUENCE {
		insightsScoreLowFreqQueueSizeLevelName	DisplayString,
		insightsScoreLowFreqQueueSizeLevelVal	CounterBasedGauge64,
		insightsScoreLowFreqQueueSizeLevelMax	CounterBasedGauge64
	}

insightsScoreLowFreqQueueSizeLevelName OBJECT-TYPE
	SYNTAX      DisplayString
	MAX-ACCESS  not-accessible
	STATUS      current
	DESCRIPTION
	"Table entry display string for insightsScoreLowFreqQueueSize"
	::={insightsScoreLowFreqQueueSizeLevelEntry 1}

insightsScoreLowFreqQueueSizeLevelVal OBJECT-TYPE
	SYNTAX	 CounterBasedGauge64
	MAX-ACCESS  read-only
	STATUS      current
	DESCRIPTION
	"Table entry attribute for insightsScoreLowFreqQueueSize"
	::={insightsScoreLowFreqQueueSizeLevelEntry 2}

insightsScoreLowFreqQueueSizeLevelMax OBJECT-TYPE
	SYNTAX	 CounterBasedGauge64
	MAX-ACCESS  read-only
	STATUS      current
	DESCRIPTION
	"Table entry attribute for insightsScoreLowFreqQueueSize"
	::={insightsScoreLowFreqQueueSizeLevelEntry 4}


insightsScoreLowFreqQueueUsage	OBJECT IDENTIFIER ::={insights 40}

insightsScoreLowFreqQueueUsageVal	OBJECT-TYPE
	SYNTAX	 Unsigned32
	MAX-ACCESS read-only
	STATUS obsolete
	DESCRIPTION "Score: Low frequency queue usage"

	::={insightsScoreLowFreqQueueUsage 1}

insightsScoreLowFreqQueueUsageMax	OBJECT-TYPE
	SYNTAX	 Unsigned32
	MAX-ACCESS read-only
	STATUS obsolete
	DESCRIPTION "Score: Low frequency queue usage"

	::={insightsScoreLowFreqQueueUsage 3}

insightsScoreLowFreqQueueUsageLevelTable OBJECT-TYPE
	SYNTAX      SEQUENCE OF InsightsScoreLowFreqQueueUsageLevelEntry
	MAX-ACCESS  not-accessible
	STATUS      current
	DESCRIPTION
	"Table for insightsScoreLowFreqQueueUsage"
	::={insightsScoreLowFreqQueueUsage 4}

insightsScoreLowFreqQueueUsageLevelEntry OBJECT-TYPE
	SYNTAX      InsightsScoreLowFreqQueueUsageLevelEntry
	MAX-ACCESS  not-accessible
	STATUS      current
	DESCRIPTION
	"Table entry for insightsScoreLowFreqQueueUsage"
	INDEX { insightsScoreLowFreqQueueUsageLevelName }
	::={insightsScoreLowFreqQueueUsageLevelTable 1}

InsightsScoreLowFreqQueueUsageLevelEntry ::=
	SEQUENCE {
		insightsScoreLowFreqQueueUsageLevelName	DisplayString,
		insightsScoreLowFreqQueueUsageLevelVal	Unsigned32,
		insightsScoreLowFreqQueueUsageLevelMax	Unsigned32
	}

insightsScoreLowFreqQueueUsageLevelName OBJECT-TYPE
	SYNTAX      DisplayString
	MAX-ACCESS  not-accessible
	STATUS      current
	DESCRIPTION
	"Table entry display string for insightsScoreLowFreqQueueUsage"
	::={insightsScoreLowFreqQueueUsageLevelEntry 1}

insightsScoreLowFreqQueueUsageLevelVal OBJECT-TYPE
	SYNTAX	 Unsigned32
	MAX-ACCESS  read-only
	STATUS      current
	DESCRIPTION
	"Table entry attribute for insightsScoreLowFreqQueueUsage"
	::={insightsScoreLowFreqQueueUsageLevelEntry 2}

insightsScoreLowFreqQueueUsageLevelMax OBJECT-TYPE
	SYNTAX	 Unsigned32
	MAX-ACCESS  read-only
	STATUS      current
	DESCRIPTION
	"Table entry attribute for insightsScoreLowFreqQueueUsage"
	::={insightsScoreLowFreqQueueUsageLevelEntry 4}


insightsScoreHighFreqMessagesSent	OBJECT IDENTIFIER ::={insights 41}

insightsScoreHighFreqMessagesSentVal	OBJECT-TYPE
	SYNTAX	 Counter64
	MAX-ACCESS read-only
	STATUS obsolete
	DESCRIPTION "Score: High frequency messages sent"

	::={insightsScoreHighFreqMessagesSent 1}

insightsScoreHighFreqMessagesSentMom	OBJECT-TYPE
	SYNTAX	 CounterBasedGauge64
	MAX-ACCESS read-only
	STATUS obsolete
	DESCRIPTION "Score: High frequency messages sent"

	::={insightsScoreHighFreqMessagesSent 2}

insightsScoreHighFreqMessagesSentMax	OBJECT-TYPE
	SYNTAX	 CounterBasedGauge64
	MAX-ACCESS read-only
	STATUS obsolete
	DESCRIPTION "Score: High frequency messages sent"

	::={insightsScoreHighFreqMessagesSent 3}

insightsScoreHighFreqMessagesSentLevelTable OBJECT-TYPE
	SYNTAX      SEQUENCE OF InsightsScoreHighFreqMessagesSentLevelEntry
	MAX-ACCESS  not-accessible
	STATUS      current
	DESCRIPTION
	"Table for insightsScoreHighFreqMessagesSent"
	::={insightsScoreHighFreqMessagesSent 4}

insightsScoreHighFreqMessagesSentLevelEntry OBJECT-TYPE
	SYNTAX      InsightsScoreHighFreqMessagesSentLevelEntry
	MAX-ACCESS  not-accessible
	STATUS      current
	DESCRIPTION
	"Table entry for insightsScoreHighFreqMessagesSent"
	INDEX { insightsScoreHighFreqMessagesSentLevelName }
	::={insightsScoreHighFreqMessagesSentLevelTable 1}

InsightsScoreHighFreqMessagesSentLevelEntry ::=
	SEQUENCE {
		insightsScoreHighFreqMessagesSentLevelName	DisplayString,
		insightsScoreHighFreqMessagesSentLevelVal	Counter64,
		insightsScoreHighFreqMessagesSentLevelMom	CounterBasedGauge64,
		insightsScoreHighFreqMessagesSentLevelMax	CounterBasedGauge64
	}

insightsScoreHighFreqMessagesSentLevelName OBJECT-TYPE
	SYNTAX      DisplayString
	MAX-ACCESS  not-accessible
	STATUS      current
	DESCRIPTION
	"Table entry display string for insightsScoreHighFreqMessagesSent"
	::={insightsScoreHighFreqMessagesSentLevelEntry 1}

insightsScoreHighFreqMessagesSentLevelVal OBJECT-TYPE
	SYNTAX	 Counter64
	MAX-ACCESS  read-only
	STATUS      current
	DESCRIPTION
	"Table entry attribute for insightsScoreHighFreqMessagesSent"
	::={insightsScoreHighFreqMessagesSentLevelEntry 2}

insightsScoreHighFreqMessagesSentLevelMom OBJECT-TYPE
	SYNTAX	 CounterBasedGauge64
	MAX-ACCESS  read-only
	STATUS      current
	DESCRIPTION
	"Table entry attribute for insightsScoreHighFreqMessagesSent"
	::={insightsScoreHighFreqMessagesSentLevelEntry 3}

insightsScoreHighFreqMessagesSentLevelMax OBJECT-TYPE
	SYNTAX	 CounterBasedGauge64
	MAX-ACCESS  read-only
	STATUS      current
	DESCRIPTION
	"Table entry attribute for insightsScoreHighFreqMessagesSent"
	::={insightsScoreHighFreqMessagesSentLevelEntry 4}


insightsScoreRecordsSent	OBJECT IDENTIFIER ::={insights 42}

insightsScoreRecordsSentVal	OBJECT-TYPE
	SYNTAX	 Counter64
	MAX-ACCESS read-only
	STATUS current
	DESCRIPTION "Score: Records sent"

	::={insightsScoreRecordsSent 1}

insightsScoreRecordsSentMom	OBJECT-TYPE
	SYNTAX	 CounterBasedGauge64
	MAX-ACCESS read-only
	STATUS current
	DESCRIPTION "Score: Records sent"

	::={insightsScoreRecordsSent 2}

insightsScoreRecordsSentMax	OBJECT-TYPE
	SYNTAX	 CounterBasedGauge64
	MAX-ACCESS read-only
	STATUS current
	DESCRIPTION "Score: Records sent"

	::={insightsScoreRecordsSent 3}

insightsScoreRecordsSentLevelTable OBJECT-TYPE
	SYNTAX      SEQUENCE OF InsightsScoreRecordsSentLevelEntry
	MAX-ACCESS  not-accessible
	STATUS      current
	DESCRIPTION
	"Table for insightsScoreRecordsSent"
	::={insightsScoreRecordsSent 4}

insightsScoreRecordsSentLevelEntry OBJECT-TYPE
	SYNTAX      InsightsScoreRecordsSentLevelEntry
	MAX-ACCESS  not-accessible
	STATUS      current
	DESCRIPTION
	"Table entry for insightsScoreRecordsSent"
	INDEX { insightsScoreRecordsSentLevelName }
	::={insightsScoreRecordsSentLevelTable 1}

InsightsScoreRecordsSentLevelEntry ::=
	SEQUENCE {
		insightsScoreRecordsSentLevelName	DisplayString,
		insightsScoreRecordsSentLevelVal	Counter64,
		insightsScoreRecordsSentLevelMom	CounterBasedGauge64,
		insightsScoreRecordsSentLevelMax	CounterBasedGauge64
	}

insightsScoreRecordsSentLevelName OBJECT-TYPE
	SYNTAX      DisplayString
	MAX-ACCESS  not-accessible
	STATUS      current
	DESCRIPTION
	"Table entry display string for insightsScoreRecordsSent"
	::={insightsScoreRecordsSentLevelEntry 1}

insightsScoreRecordsSentLevelVal OBJECT-TYPE
	SYNTAX	 Counter64
	MAX-ACCESS  read-only
	STATUS      current
	DESCRIPTION
	"Table entry attribute for insightsScoreRecordsSent"
	::={insightsScoreRecordsSentLevelEntry 2}

insightsScoreRecordsSentLevelMom OBJECT-TYPE
	SYNTAX	 CounterBasedGauge64
	MAX-ACCESS  read-only
	STATUS      current
	DESCRIPTION
	"Table entry attribute for insightsScoreRecordsSent"
	::={insightsScoreRecordsSentLevelEntry 3}

insightsScoreRecordsSentLevelMax OBJECT-TYPE
	SYNTAX	 CounterBasedGauge64
	MAX-ACCESS  read-only
	STATUS      current
	DESCRIPTION
	"Table entry attribute for insightsScoreRecordsSent"
	::={insightsScoreRecordsSentLevelEntry 4}


insightsScoreBytesSent	OBJECT IDENTIFIER ::={insights 43}

insightsScoreBytesSentVal	OBJECT-TYPE
	SYNTAX	 Counter64
	MAX-ACCESS read-only
	STATUS current
	DESCRIPTION "Score: Bytes sent"

	::={insightsScoreBytesSent 1}

insightsScoreBytesSentMom	OBJECT-TYPE
	SYNTAX	 CounterBasedGauge64
	MAX-ACCESS read-only
	STATUS current
	DESCRIPTION "Score: Bytes sent"

	::={insightsScoreBytesSent 2}

insightsScoreBytesSentMax	OBJECT-TYPE
	SYNTAX	 CounterBasedGauge64
	MAX-ACCESS read-only
	STATUS current
	DESCRIPTION "Score: Bytes sent"

	::={insightsScoreBytesSent 3}

insightsScoreBytesSentLevelTable OBJECT-TYPE
	SYNTAX      SEQUENCE OF InsightsScoreBytesSentLevelEntry
	MAX-ACCESS  not-accessible
	STATUS      current
	DESCRIPTION
	"Table for insightsScoreBytesSent"
	::={insightsScoreBytesSent 4}

insightsScoreBytesSentLevelEntry OBJECT-TYPE
	SYNTAX      InsightsScoreBytesSentLevelEntry
	MAX-ACCESS  not-accessible
	STATUS      current
	DESCRIPTION
	"Table entry for insightsScoreBytesSent"
	INDEX { insightsScoreBytesSentLevelName }
	::={insightsScoreBytesSentLevelTable 1}

InsightsScoreBytesSentLevelEntry ::=
	SEQUENCE {
		insightsScoreBytesSentLevelName	DisplayString,
		insightsScoreBytesSentLevelVal	Counter64,
		insightsScoreBytesSentLevelMom	CounterBasedGauge64,
		insightsScoreBytesSentLevelMax	CounterBasedGauge64
	}

insightsScoreBytesSentLevelName OBJECT-TYPE
	SYNTAX      DisplayString
	MAX-ACCESS  not-accessible
	STATUS      current
	DESCRIPTION
	"Table entry display string for insightsScoreBytesSent"
	::={insightsScoreBytesSentLevelEntry 1}

insightsScoreBytesSentLevelVal OBJECT-TYPE
	SYNTAX	 Counter64
	MAX-ACCESS  read-only
	STATUS      current
	DESCRIPTION
	"Table entry attribute for insightsScoreBytesSent"
	::={insightsScoreBytesSentLevelEntry 2}

insightsScoreBytesSentLevelMom OBJECT-TYPE
	SYNTAX	 CounterBasedGauge64
	MAX-ACCESS  read-only
	STATUS      current
	DESCRIPTION
	"Table entry attribute for insightsScoreBytesSent"
	::={insightsScoreBytesSentLevelEntry 3}

insightsScoreBytesSentLevelMax OBJECT-TYPE
	SYNTAX	 CounterBasedGauge64
	MAX-ACCESS  read-only
	STATUS      current
	DESCRIPTION
	"Table entry attribute for insightsScoreBytesSent"
	::={insightsScoreBytesSentLevelEntry 4}


insightsScoreHighFreqZBytesSent	OBJECT IDENTIFIER ::={insights 44}

insightsScoreHighFreqZBytesSentVal	OBJECT-TYPE
	SYNTAX	 Counter64
	MAX-ACCESS read-only
	STATUS obsolete
	DESCRIPTION "Score: High frequency compressed bytes sent"

	::={insightsScoreHighFreqZBytesSent 1}

insightsScoreHighFreqZBytesSentMom	OBJECT-TYPE
	SYNTAX	 CounterBasedGauge64
	MAX-ACCESS read-only
	STATUS obsolete
	DESCRIPTION "Score: High frequency compressed bytes sent"

	::={insightsScoreHighFreqZBytesSent 2}

insightsScoreHighFreqZBytesSentMax	OBJECT-TYPE
	SYNTAX	 CounterBasedGauge64
	MAX-ACCESS read-only
	STATUS obsolete
	DESCRIPTION "Score: High frequency compressed bytes sent"

	::={insightsScoreHighFreqZBytesSent 3}

insightsScoreHighFreqZBytesSentLevelTable OBJECT-TYPE
	SYNTAX      SEQUENCE OF InsightsScoreHighFreqZBytesSentLevelEntry
	MAX-ACCESS  not-accessible
	STATUS      current
	DESCRIPTION
	"Table for insightsScoreHighFreqZBytesSent"
	::={insightsScoreHighFreqZBytesSent 4}

insightsScoreHighFreqZBytesSentLevelEntry OBJECT-TYPE
	SYNTAX      InsightsScoreHighFreqZBytesSentLevelEntry
	MAX-ACCESS  not-accessible
	STATUS      current
	DESCRIPTION
	"Table entry for insightsScoreHighFreqZBytesSent"
	INDEX { insightsScoreHighFreqZBytesSentLevelName }
	::={insightsScoreHighFreqZBytesSentLevelTable 1}

InsightsScoreHighFreqZBytesSentLevelEntry ::=
	SEQUENCE {
		insightsScoreHighFreqZBytesSentLevelName	DisplayString,
		insightsScoreHighFreqZBytesSentLevelVal	Counter64,
		insightsScoreHighFreqZBytesSentLevelMom	CounterBasedGauge64,
		insightsScoreHighFreqZBytesSentLevelMax	CounterBasedGauge64
	}

insightsScoreHighFreqZBytesSentLevelName OBJECT-TYPE
	SYNTAX      DisplayString
	MAX-ACCESS  not-accessible
	STATUS      current
	DESCRIPTION
	"Table entry display string for insightsScoreHighFreqZBytesSent"
	::={insightsScoreHighFreqZBytesSentLevelEntry 1}

insightsScoreHighFreqZBytesSentLevelVal OBJECT-TYPE
	SYNTAX	 Counter64
	MAX-ACCESS  read-only
	STATUS      current
	DESCRIPTION
	"Table entry attribute for insightsScoreHighFreqZBytesSent"
	::={insightsScoreHighFreqZBytesSentLevelEntry 2}

insightsScoreHighFreqZBytesSentLevelMom OBJECT-TYPE
	SYNTAX	 CounterBasedGauge64
	MAX-ACCESS  read-only
	STATUS      current
	DESCRIPTION
	"Table entry attribute for insightsScoreHighFreqZBytesSent"
	::={insightsScoreHighFreqZBytesSentLevelEntry 3}

insightsScoreHighFreqZBytesSentLevelMax OBJECT-TYPE
	SYNTAX	 CounterBasedGauge64
	MAX-ACCESS  read-only
	STATUS      current
	DESCRIPTION
	"Table entry attribute for insightsScoreHighFreqZBytesSent"
	::={insightsScoreHighFreqZBytesSentLevelEntry 4}


insightsScoreRecordsDropped	OBJECT IDENTIFIER ::={insights 45}

insightsScoreRecordsDroppedVal	OBJECT-TYPE
	SYNTAX	 Counter64
	MAX-ACCESS read-only
	STATUS current
	DESCRIPTION "Score: Records dropped"

	::={insightsScoreRecordsDropped 1}

insightsScoreRecordsDroppedMom	OBJECT-TYPE
	SYNTAX	 CounterBasedGauge64
	MAX-ACCESS read-only
	STATUS current
	DESCRIPTION "Score: Records dropped"

	::={insightsScoreRecordsDropped 2}

insightsScoreRecordsDroppedMax	OBJECT-TYPE
	SYNTAX	 CounterBasedGauge64
	MAX-ACCESS read-only
	STATUS current
	DESCRIPTION "Score: Records dropped"

	::={insightsScoreRecordsDropped 3}

insightsScoreRecordsDroppedLevelTable OBJECT-TYPE
	SYNTAX      SEQUENCE OF InsightsScoreRecordsDroppedLevelEntry
	MAX-ACCESS  not-accessible
	STATUS      current
	DESCRIPTION
	"Table for insightsScoreRecordsDropped"
	::={insightsScoreRecordsDropped 4}

insightsScoreRecordsDroppedLevelEntry OBJECT-TYPE
	SYNTAX      InsightsScoreRecordsDroppedLevelEntry
	MAX-ACCESS  not-accessible
	STATUS      current
	DESCRIPTION
	"Table entry for insightsScoreRecordsDropped"
	INDEX { insightsScoreRecordsDroppedLevelName }
	::={insightsScoreRecordsDroppedLevelTable 1}

InsightsScoreRecordsDroppedLevelEntry ::=
	SEQUENCE {
		insightsScoreRecordsDroppedLevelName	DisplayString,
		insightsScoreRecordsDroppedLevelVal	Counter64,
		insightsScoreRecordsDroppedLevelMom	CounterBasedGauge64,
		insightsScoreRecordsDroppedLevelMax	CounterBasedGauge64
	}

insightsScoreRecordsDroppedLevelName OBJECT-TYPE
	SYNTAX      DisplayString
	MAX-ACCESS  not-accessible
	STATUS      current
	DESCRIPTION
	"Table entry display string for insightsScoreRecordsDropped"
	::={insightsScoreRecordsDroppedLevelEntry 1}

insightsScoreRecordsDroppedLevelVal OBJECT-TYPE
	SYNTAX	 Counter64
	MAX-ACCESS  read-only
	STATUS      current
	DESCRIPTION
	"Table entry attribute for insightsScoreRecordsDropped"
	::={insightsScoreRecordsDroppedLevelEntry 2}

insightsScoreRecordsDroppedLevelMom OBJECT-TYPE
	SYNTAX	 CounterBasedGauge64
	MAX-ACCESS  read-only
	STATUS      current
	DESCRIPTION
	"Table entry attribute for insightsScoreRecordsDropped"
	::={insightsScoreRecordsDroppedLevelEntry 3}

insightsScoreRecordsDroppedLevelMax OBJECT-TYPE
	SYNTAX	 CounterBasedGauge64
	MAX-ACCESS  read-only
	STATUS      current
	DESCRIPTION
	"Table entry attribute for insightsScoreRecordsDropped"
	::={insightsScoreRecordsDroppedLevelEntry 4}


insightsScoreHighFreqQueueSize	OBJECT IDENTIFIER ::={insights 46}

insightsScoreHighFreqQueueSizeVal	OBJECT-TYPE
	SYNTAX	 CounterBasedGauge64
	MAX-ACCESS read-only
	STATUS obsolete
	DESCRIPTION "Score: High frequency queue size"

	::={insightsScoreHighFreqQueueSize 1}

insightsScoreHighFreqQueueSizeMax	OBJECT-TYPE
	SYNTAX	 CounterBasedGauge64
	MAX-ACCESS read-only
	STATUS obsolete
	DESCRIPTION "Score: High frequency queue size"

	::={insightsScoreHighFreqQueueSize 3}

insightsScoreHighFreqQueueSizeLevelTable OBJECT-TYPE
	SYNTAX      SEQUENCE OF InsightsScoreHighFreqQueueSizeLevelEntry
	MAX-ACCESS  not-accessible
	STATUS      current
	DESCRIPTION
	"Table for insightsScoreHighFreqQueueSize"
	::={insightsScoreHighFreqQueueSize 4}

insightsScoreHighFreqQueueSizeLevelEntry OBJECT-TYPE
	SYNTAX      InsightsScoreHighFreqQueueSizeLevelEntry
	MAX-ACCESS  not-accessible
	STATUS      current
	DESCRIPTION
	"Table entry for insightsScoreHighFreqQueueSize"
	INDEX { insightsScoreHighFreqQueueSizeLevelName }
	::={insightsScoreHighFreqQueueSizeLevelTable 1}

InsightsScoreHighFreqQueueSizeLevelEntry ::=
	SEQUENCE {
		insightsScoreHighFreqQueueSizeLevelName	DisplayString,
		insightsScoreHighFreqQueueSizeLevelVal	CounterBasedGauge64,
		insightsScoreHighFreqQueueSizeLevelMax	CounterBasedGauge64
	}

insightsScoreHighFreqQueueSizeLevelName OBJECT-TYPE
	SYNTAX      DisplayString
	MAX-ACCESS  not-accessible
	STATUS      current
	DESCRIPTION
	"Table entry display string for insightsScoreHighFreqQueueSize"
	::={insightsScoreHighFreqQueueSizeLevelEntry 1}

insightsScoreHighFreqQueueSizeLevelVal OBJECT-TYPE
	SYNTAX	 CounterBasedGauge64
	MAX-ACCESS  read-only
	STATUS      current
	DESCRIPTION
	"Table entry attribute for insightsScoreHighFreqQueueSize"
	::={insightsScoreHighFreqQueueSizeLevelEntry 2}

insightsScoreHighFreqQueueSizeLevelMax OBJECT-TYPE
	SYNTAX	 CounterBasedGauge64
	MAX-ACCESS  read-only
	STATUS      current
	DESCRIPTION
	"Table entry attribute for insightsScoreHighFreqQueueSize"
	::={insightsScoreHighFreqQueueSizeLevelEntry 4}


insightsScoreHighFreqQueueUsage	OBJECT IDENTIFIER ::={insights 47}

insightsScoreHighFreqQueueUsageVal	OBJECT-TYPE
	SYNTAX	 Unsigned32
	MAX-ACCESS read-only
	STATUS obsolete
	DESCRIPTION "Score: High frequency queue usage"

	::={insightsScoreHighFreqQueueUsage 1}

insightsScoreHighFreqQueueUsageMax	OBJECT-TYPE
	SYNTAX	 Unsigned32
	MAX-ACCESS read-only
	STATUS obsolete
	DESCRIPTION "Score: High frequency queue usage"

	::={insightsScoreHighFreqQueueUsage 3}

insightsScoreHighFreqQueueUsageLevelTable OBJECT-TYPE
	SYNTAX      SEQUENCE OF InsightsScoreHighFreqQueueUsageLevelEntry
	MAX-ACCESS  not-accessible
	STATUS      current
	DESCRIPTION
	"Table for insightsScoreHighFreqQueueUsage"
	::={insightsScoreHighFreqQueueUsage 4}

insightsScoreHighFreqQueueUsageLevelEntry OBJECT-TYPE
	SYNTAX      InsightsScoreHighFreqQueueUsageLevelEntry
	MAX-ACCESS  not-accessible
	STATUS      current
	DESCRIPTION
	"Table entry for insightsScoreHighFreqQueueUsage"
	INDEX { insightsScoreHighFreqQueueUsageLevelName }
	::={insightsScoreHighFreqQueueUsageLevelTable 1}

InsightsScoreHighFreqQueueUsageLevelEntry ::=
	SEQUENCE {
		insightsScoreHighFreqQueueUsageLevelName	DisplayString,
		insightsScoreHighFreqQueueUsageLevelVal	Unsigned32,
		insightsScoreHighFreqQueueUsageLevelMax	Unsigned32
	}

insightsScoreHighFreqQueueUsageLevelName OBJECT-TYPE
	SYNTAX      DisplayString
	MAX-ACCESS  not-accessible
	STATUS      current
	DESCRIPTION
	"Table entry display string for insightsScoreHighFreqQueueUsage"
	::={insightsScoreHighFreqQueueUsageLevelEntry 1}

insightsScoreHighFreqQueueUsageLevelVal OBJECT-TYPE
	SYNTAX	 Unsigned32
	MAX-ACCESS  read-only
	STATUS      current
	DESCRIPTION
	"Table entry attribute for insightsScoreHighFreqQueueUsage"
	::={insightsScoreHighFreqQueueUsageLevelEntry 2}

insightsScoreHighFreqQueueUsageLevelMax OBJECT-TYPE
	SYNTAX	 Unsigned32
	MAX-ACCESS  read-only
	STATUS      current
	DESCRIPTION
	"Table entry attribute for insightsScoreHighFreqQueueUsage"
	::={insightsScoreHighFreqQueueUsageLevelEntry 4}


insightsTrafficCurrentDumpSkipped	OBJECT IDENTIFIER ::={insights 48}

insightsTrafficCurrentDumpSkippedVal	OBJECT-TYPE
	SYNTAX	 CounterBasedGauge64
	MAX-ACCESS read-only
	STATUS obsolete
	DESCRIPTION "Traffic: Current dump skipped"

	::={insightsTrafficCurrentDumpSkipped 1}

insightsTrafficCurrentDumpSkippedMax	OBJECT-TYPE
	SYNTAX	 CounterBasedGauge64
	MAX-ACCESS read-only
	STATUS obsolete
	DESCRIPTION "Traffic: Current dump skipped"

	::={insightsTrafficCurrentDumpSkipped 3}

insightsTrafficCurrentDumpSkippedLevelTable OBJECT-TYPE
	SYNTAX      SEQUENCE OF InsightsTrafficCurrentDumpSkippedLevelEntry
	MAX-ACCESS  not-accessible
	STATUS      current
	DESCRIPTION
	"Table for insightsTrafficCurrentDumpSkipped"
	::={insightsTrafficCurrentDumpSkipped 4}

insightsTrafficCurrentDumpSkippedLevelEntry OBJECT-TYPE
	SYNTAX      InsightsTrafficCurrentDumpSkippedLevelEntry
	MAX-ACCESS  not-accessible
	STATUS      current
	DESCRIPTION
	"Table entry for insightsTrafficCurrentDumpSkipped"
	INDEX { insightsTrafficCurrentDumpSkippedLevelName }
	::={insightsTrafficCurrentDumpSkippedLevelTable 1}

InsightsTrafficCurrentDumpSkippedLevelEntry ::=
	SEQUENCE {
		insightsTrafficCurrentDumpSkippedLevelName	DisplayString,
		insightsTrafficCurrentDumpSkippedLevelVal	CounterBasedGauge64,
		insightsTrafficCurrentDumpSkippedLevelMax	CounterBasedGauge64
	}

insightsTrafficCurrentDumpSkippedLevelName OBJECT-TYPE
	SYNTAX      DisplayString
	MAX-ACCESS  not-accessible
	STATUS      current
	DESCRIPTION
	"Table entry display string for insightsTrafficCurrentDumpSkipped"
	::={insightsTrafficCurrentDumpSkippedLevelEntry 1}

insightsTrafficCurrentDumpSkippedLevelVal OBJECT-TYPE
	SYNTAX	 CounterBasedGauge64
	MAX-ACCESS  read-only
	STATUS      current
	DESCRIPTION
	"Table entry attribute for insightsTrafficCurrentDumpSkipped"
	::={insightsTrafficCurrentDumpSkippedLevelEntry 2}

insightsTrafficCurrentDumpSkippedLevelMax OBJECT-TYPE
	SYNTAX	 CounterBasedGauge64
	MAX-ACCESS  read-only
	STATUS      current
	DESCRIPTION
	"Table entry attribute for insightsTrafficCurrentDumpSkipped"
	::={insightsTrafficCurrentDumpSkippedLevelEntry 4}


insightsScoreCurrentDumpSkipped	OBJECT IDENTIFIER ::={insights 49}

insightsScoreCurrentDumpSkippedVal	OBJECT-TYPE
	SYNTAX	 CounterBasedGauge64
	MAX-ACCESS read-only
	STATUS obsolete
	DESCRIPTION "Score: Current dump skipped"

	::={insightsScoreCurrentDumpSkipped 1}

insightsScoreCurrentDumpSkippedMax	OBJECT-TYPE
	SYNTAX	 CounterBasedGauge64
	MAX-ACCESS read-only
	STATUS obsolete
	DESCRIPTION "Score: Current dump skipped"

	::={insightsScoreCurrentDumpSkipped 3}

insightsScoreCurrentDumpSkippedLevelTable OBJECT-TYPE
	SYNTAX      SEQUENCE OF InsightsScoreCurrentDumpSkippedLevelEntry
	MAX-ACCESS  not-accessible
	STATUS      current
	DESCRIPTION
	"Table for insightsScoreCurrentDumpSkipped"
	::={insightsScoreCurrentDumpSkipped 4}

insightsScoreCurrentDumpSkippedLevelEntry OBJECT-TYPE
	SYNTAX      InsightsScoreCurrentDumpSkippedLevelEntry
	MAX-ACCESS  not-accessible
	STATUS      current
	DESCRIPTION
	"Table entry for insightsScoreCurrentDumpSkipped"
	INDEX { insightsScoreCurrentDumpSkippedLevelName }
	::={insightsScoreCurrentDumpSkippedLevelTable 1}

InsightsScoreCurrentDumpSkippedLevelEntry ::=
	SEQUENCE {
		insightsScoreCurrentDumpSkippedLevelName	DisplayString,
		insightsScoreCurrentDumpSkippedLevelVal	CounterBasedGauge64,
		insightsScoreCurrentDumpSkippedLevelMax	CounterBasedGauge64
	}

insightsScoreCurrentDumpSkippedLevelName OBJECT-TYPE
	SYNTAX      DisplayString
	MAX-ACCESS  not-accessible
	STATUS      current
	DESCRIPTION
	"Table entry display string for insightsScoreCurrentDumpSkipped"
	::={insightsScoreCurrentDumpSkippedLevelEntry 1}

insightsScoreCurrentDumpSkippedLevelVal OBJECT-TYPE
	SYNTAX	 CounterBasedGauge64
	MAX-ACCESS  read-only
	STATUS      current
	DESCRIPTION
	"Table entry attribute for insightsScoreCurrentDumpSkipped"
	::={insightsScoreCurrentDumpSkippedLevelEntry 2}

insightsScoreCurrentDumpSkippedLevelMax OBJECT-TYPE
	SYNTAX	 CounterBasedGauge64
	MAX-ACCESS  read-only
	STATUS      current
	DESCRIPTION
	"Table entry attribute for insightsScoreCurrentDumpSkipped"
	::={insightsScoreCurrentDumpSkippedLevelEntry 4}


insightsDimensionLookups	OBJECT IDENTIFIER ::={insights 50}

insightsDimensionLookupsVal	OBJECT-TYPE
	SYNTAX	 Counter64
	MAX-ACCESS read-only
	STATUS current
	DESCRIPTION "Dimension lookups"

	::={insightsDimensionLookups 1}

insightsDimensionLookupsMom	OBJECT-TYPE
	SYNTAX	 CounterBasedGauge64
	MAX-ACCESS read-only
	STATUS current
	DESCRIPTION "Dimension lookups"

	::={insightsDimensionLookups 2}

insightsDimensionLookupsMax	OBJECT-TYPE
	SYNTAX	 CounterBasedGauge64
	MAX-ACCESS read-only
	STATUS current
	DESCRIPTION "Dimension lookups"

	::={insightsDimensionLookups 3}

insightsDimensionLookupsLevelTable OBJECT-TYPE
	SYNTAX      SEQUENCE OF InsightsDimensionLookupsLevelEntry
	MAX-ACCESS  not-accessible
	STATUS      current
	DESCRIPTION
	"Table for insightsDimensionLookups"
	::={insightsDimensionLookups 4}

insightsDimensionLookupsLevelEntry OBJECT-TYPE
	SYNTAX      InsightsDimensionLookupsLevelEntry
	MAX-ACCESS  not-accessible
	STATUS      current
	DESCRIPTION
	"Table entry for insightsDimensionLookups"
	INDEX { insightsDimensionLookupsLevelName }
	::={insightsDimensionLookupsLevelTable 1}

InsightsDimensionLookupsLevelEntry ::=
	SEQUENCE {
		insightsDimensionLookupsLevelName	DisplayString,
		insightsDimensionLookupsLevelVal	Counter64,
		insightsDimensionLookupsLevelMom	CounterBasedGauge64,
		insightsDimensionLookupsLevelMax	CounterBasedGauge64
	}

insightsDimensionLookupsLevelName OBJECT-TYPE
	SYNTAX      DisplayString
	MAX-ACCESS  not-accessible
	STATUS      current
	DESCRIPTION
	"Table entry display string for insightsDimensionLookups"
	::={insightsDimensionLookupsLevelEntry 1}

insightsDimensionLookupsLevelVal OBJECT-TYPE
	SYNTAX	 Counter64
	MAX-ACCESS  read-only
	STATUS      current
	DESCRIPTION
	"Table entry attribute for insightsDimensionLookups"
	::={insightsDimensionLookupsLevelEntry 2}

insightsDimensionLookupsLevelMom OBJECT-TYPE
	SYNTAX	 CounterBasedGauge64
	MAX-ACCESS  read-only
	STATUS      current
	DESCRIPTION
	"Table entry attribute for insightsDimensionLookups"
	::={insightsDimensionLookupsLevelEntry 3}

insightsDimensionLookupsLevelMax OBJECT-TYPE
	SYNTAX	 CounterBasedGauge64
	MAX-ACCESS  read-only
	STATUS      current
	DESCRIPTION
	"Table entry attribute for insightsDimensionLookups"
	::={insightsDimensionLookupsLevelEntry 4}


insightsDimensionLookupFails	OBJECT IDENTIFIER ::={insights 51}

insightsDimensionLookupFailsVal	OBJECT-TYPE
	SYNTAX	 Counter64
	MAX-ACCESS read-only
	STATUS current
	DESCRIPTION "Dimension lookup failures"

	::={insightsDimensionLookupFails 1}

insightsDimensionLookupFailsMom	OBJECT-TYPE
	SYNTAX	 CounterBasedGauge64
	MAX-ACCESS read-only
	STATUS current
	DESCRIPTION "Dimension lookup failures"

	::={insightsDimensionLookupFails 2}

insightsDimensionLookupFailsMax	OBJECT-TYPE
	SYNTAX	 CounterBasedGauge64
	MAX-ACCESS read-only
	STATUS current
	DESCRIPTION "Dimension lookup failures"

	::={insightsDimensionLookupFails 3}

insightsDimensionLookupFailsLevelTable OBJECT-TYPE
	SYNTAX      SEQUENCE OF InsightsDimensionLookupFailsLevelEntry
	MAX-ACCESS  not-accessible
	STATUS      current
	DESCRIPTION
	"Table for insightsDimensionLookupFails"
	::={insightsDimensionLookupFails 4}

insightsDimensionLookupFailsLevelEntry OBJECT-TYPE
	SYNTAX      InsightsDimensionLookupFailsLevelEntry
	MAX-ACCESS  not-accessible
	STATUS      current
	DESCRIPTION
	"Table entry for insightsDimensionLookupFails"
	INDEX { insightsDimensionLookupFailsLevelName }
	::={insightsDimensionLookupFailsLevelTable 1}

InsightsDimensionLookupFailsLevelEntry ::=
	SEQUENCE {
		insightsDimensionLookupFailsLevelName	DisplayString,
		insightsDimensionLookupFailsLevelVal	Counter64,
		insightsDimensionLookupFailsLevelMom	CounterBasedGauge64,
		insightsDimensionLookupFailsLevelMax	CounterBasedGauge64
	}

insightsDimensionLookupFailsLevelName OBJECT-TYPE
	SYNTAX      DisplayString
	MAX-ACCESS  not-accessible
	STATUS      current
	DESCRIPTION
	"Table entry display string for insightsDimensionLookupFails"
	::={insightsDimensionLookupFailsLevelEntry 1}

insightsDimensionLookupFailsLevelVal OBJECT-TYPE
	SYNTAX	 Counter64
	MAX-ACCESS  read-only
	STATUS      current
	DESCRIPTION
	"Table entry attribute for insightsDimensionLookupFails"
	::={insightsDimensionLookupFailsLevelEntry 2}

insightsDimensionLookupFailsLevelMom OBJECT-TYPE
	SYNTAX	 CounterBasedGauge64
	MAX-ACCESS  read-only
	STATUS      current
	DESCRIPTION
	"Table entry attribute for insightsDimensionLookupFails"
	::={insightsDimensionLookupFailsLevelEntry 3}

insightsDimensionLookupFailsLevelMax OBJECT-TYPE
	SYNTAX	 CounterBasedGauge64
	MAX-ACCESS  read-only
	STATUS      current
	DESCRIPTION
	"Table entry attribute for insightsDimensionLookupFails"
	::={insightsDimensionLookupFailsLevelEntry 4}


insightsScoreVolumeReceived	OBJECT IDENTIFIER ::={insights 52}

insightsScoreVolumeReceivedVal	OBJECT-TYPE
	SYNTAX	 Counter64
	MAX-ACCESS read-only
	STATUS current
	DESCRIPTION "Score: Volume received"

	::={insightsScoreVolumeReceived 1}

insightsScoreVolumeReceivedMom	OBJECT-TYPE
	SYNTAX	 CounterBasedGauge64
	MAX-ACCESS read-only
	STATUS current
	DESCRIPTION "Score: Volume received"

	::={insightsScoreVolumeReceived 2}

insightsScoreVolumeReceivedMax	OBJECT-TYPE
	SYNTAX	 CounterBasedGauge64
	MAX-ACCESS read-only
	STATUS current
	DESCRIPTION "Score: Volume received"

	::={insightsScoreVolumeReceived 3}

insightsScoreVolumeReceivedLevelTable OBJECT-TYPE
	SYNTAX      SEQUENCE OF InsightsScoreVolumeReceivedLevelEntry
	MAX-ACCESS  not-accessible
	STATUS      current
	DESCRIPTION
	"Table for insightsScoreVolumeReceived"
	::={insightsScoreVolumeReceived 4}

insightsScoreVolumeReceivedLevelEntry OBJECT-TYPE
	SYNTAX      InsightsScoreVolumeReceivedLevelEntry
	MAX-ACCESS  not-accessible
	STATUS      current
	DESCRIPTION
	"Table entry for insightsScoreVolumeReceived"
	INDEX { insightsScoreVolumeReceivedLevelName }
	::={insightsScoreVolumeReceivedLevelTable 1}

InsightsScoreVolumeReceivedLevelEntry ::=
	SEQUENCE {
		insightsScoreVolumeReceivedLevelName	DisplayString,
		insightsScoreVolumeReceivedLevelVal	Counter64,
		insightsScoreVolumeReceivedLevelMom	CounterBasedGauge64,
		insightsScoreVolumeReceivedLevelMax	CounterBasedGauge64
	}

insightsScoreVolumeReceivedLevelName OBJECT-TYPE
	SYNTAX      DisplayString
	MAX-ACCESS  not-accessible
	STATUS      current
	DESCRIPTION
	"Table entry display string for insightsScoreVolumeReceived"
	::={insightsScoreVolumeReceivedLevelEntry 1}

insightsScoreVolumeReceivedLevelVal OBJECT-TYPE
	SYNTAX	 Counter64
	MAX-ACCESS  read-only
	STATUS      current
	DESCRIPTION
	"Table entry attribute for insightsScoreVolumeReceived"
	::={insightsScoreVolumeReceivedLevelEntry 2}

insightsScoreVolumeReceivedLevelMom OBJECT-TYPE
	SYNTAX	 CounterBasedGauge64
	MAX-ACCESS  read-only
	STATUS      current
	DESCRIPTION
	"Table entry attribute for insightsScoreVolumeReceived"
	::={insightsScoreVolumeReceivedLevelEntry 3}

insightsScoreVolumeReceivedLevelMax OBJECT-TYPE
	SYNTAX	 CounterBasedGauge64
	MAX-ACCESS  read-only
	STATUS      current
	DESCRIPTION
	"Table entry attribute for insightsScoreVolumeReceived"
	::={insightsScoreVolumeReceivedLevelEntry 4}


insightsDatacoreConnections	OBJECT IDENTIFIER ::={insights 53}

insightsDatacoreConnectionsVal	OBJECT-TYPE
	SYNTAX	 CounterBasedGauge64
	MAX-ACCESS read-only
	STATUS current
	DESCRIPTION "Datacore: Insights storage connections"

	::={insightsDatacoreConnections 1}

insightsDatacoreConnectionsMax	OBJECT-TYPE
	SYNTAX	 CounterBasedGauge64
	MAX-ACCESS read-only
	STATUS current
	DESCRIPTION "Datacore: Insights storage connections"

	::={insightsDatacoreConnections 3}

insightsDatacoreConnectionsLevelTable OBJECT-TYPE
	SYNTAX      SEQUENCE OF InsightsDatacoreConnectionsLevelEntry
	MAX-ACCESS  not-accessible
	STATUS      current
	DESCRIPTION
	"Table for insightsDatacoreConnections"
	::={insightsDatacoreConnections 4}

insightsDatacoreConnectionsLevelEntry OBJECT-TYPE
	SYNTAX      InsightsDatacoreConnectionsLevelEntry
	MAX-ACCESS  not-accessible
	STATUS      current
	DESCRIPTION
	"Table entry for insightsDatacoreConnections"
	INDEX { insightsDatacoreConnectionsLevelName }
	::={insightsDatacoreConnectionsLevelTable 1}

InsightsDatacoreConnectionsLevelEntry ::=
	SEQUENCE {
		insightsDatacoreConnectionsLevelName	DisplayString,
		insightsDatacoreConnectionsLevelVal	CounterBasedGauge64,
		insightsDatacoreConnectionsLevelMax	CounterBasedGauge64
	}

insightsDatacoreConnectionsLevelName OBJECT-TYPE
	SYNTAX      DisplayString
	MAX-ACCESS  not-accessible
	STATUS      current
	DESCRIPTION
	"Table entry display string for insightsDatacoreConnections"
	::={insightsDatacoreConnectionsLevelEntry 1}

insightsDatacoreConnectionsLevelVal OBJECT-TYPE
	SYNTAX	 CounterBasedGauge64
	MAX-ACCESS  read-only
	STATUS      current
	DESCRIPTION
	"Table entry attribute for insightsDatacoreConnections"
	::={insightsDatacoreConnectionsLevelEntry 2}

insightsDatacoreConnectionsLevelMax OBJECT-TYPE
	SYNTAX	 CounterBasedGauge64
	MAX-ACCESS  read-only
	STATUS      current
	DESCRIPTION
	"Table entry attribute for insightsDatacoreConnections"
	::={insightsDatacoreConnectionsLevelEntry 4}


insightsTrafficPreviousDumpBytes	OBJECT IDENTIFIER ::={insights 54}

insightsTrafficPreviousDumpBytesVal	OBJECT-TYPE
	SYNTAX	 CounterBasedGauge64
	MAX-ACCESS read-only
	STATUS current
	DESCRIPTION "Traffic: Previous dump bytes"

	::={insightsTrafficPreviousDumpBytes 1}

insightsTrafficPreviousDumpBytesMax	OBJECT-TYPE
	SYNTAX	 CounterBasedGauge64
	MAX-ACCESS read-only
	STATUS current
	DESCRIPTION "Traffic: Previous dump bytes"

	::={insightsTrafficPreviousDumpBytes 3}

insightsTrafficPreviousDumpBytesLevelTable OBJECT-TYPE
	SYNTAX      SEQUENCE OF InsightsTrafficPreviousDumpBytesLevelEntry
	MAX-ACCESS  not-accessible
	STATUS      current
	DESCRIPTION
	"Table for insightsTrafficPreviousDumpBytes"
	::={insightsTrafficPreviousDumpBytes 4}

insightsTrafficPreviousDumpBytesLevelEntry OBJECT-TYPE
	SYNTAX      InsightsTrafficPreviousDumpBytesLevelEntry
	MAX-ACCESS  not-accessible
	STATUS      current
	DESCRIPTION
	"Table entry for insightsTrafficPreviousDumpBytes"
	INDEX { insightsTrafficPreviousDumpBytesLevelName }
	::={insightsTrafficPreviousDumpBytesLevelTable 1}

InsightsTrafficPreviousDumpBytesLevelEntry ::=
	SEQUENCE {
		insightsTrafficPreviousDumpBytesLevelName	DisplayString,
		insightsTrafficPreviousDumpBytesLevelVal	CounterBasedGauge64,
		insightsTrafficPreviousDumpBytesLevelMax	CounterBasedGauge64
	}

insightsTrafficPreviousDumpBytesLevelName OBJECT-TYPE
	SYNTAX      DisplayString
	MAX-ACCESS  not-accessible
	STATUS      current
	DESCRIPTION
	"Table entry display string for insightsTrafficPreviousDumpBytes"
	::={insightsTrafficPreviousDumpBytesLevelEntry 1}

insightsTrafficPreviousDumpBytesLevelVal OBJECT-TYPE
	SYNTAX	 CounterBasedGauge64
	MAX-ACCESS  read-only
	STATUS      current
	DESCRIPTION
	"Table entry attribute for insightsTrafficPreviousDumpBytes"
	::={insightsTrafficPreviousDumpBytesLevelEntry 2}

insightsTrafficPreviousDumpBytesLevelMax OBJECT-TYPE
	SYNTAX	 CounterBasedGauge64
	MAX-ACCESS  read-only
	STATUS      current
	DESCRIPTION
	"Table entry attribute for insightsTrafficPreviousDumpBytes"
	::={insightsTrafficPreviousDumpBytesLevelEntry 4}


insightsTrafficPreviousDumpRecords	OBJECT IDENTIFIER ::={insights 55}

insightsTrafficPreviousDumpRecordsVal	OBJECT-TYPE
	SYNTAX	 CounterBasedGauge64
	MAX-ACCESS read-only
	STATUS current
	DESCRIPTION "Traffic: Previous dump records"

	::={insightsTrafficPreviousDumpRecords 1}

insightsTrafficPreviousDumpRecordsMax	OBJECT-TYPE
	SYNTAX	 CounterBasedGauge64
	MAX-ACCESS read-only
	STATUS current
	DESCRIPTION "Traffic: Previous dump records"

	::={insightsTrafficPreviousDumpRecords 3}

insightsTrafficPreviousDumpRecordsLevelTable OBJECT-TYPE
	SYNTAX      SEQUENCE OF InsightsTrafficPreviousDumpRecordsLevelEntry
	MAX-ACCESS  not-accessible
	STATUS      current
	DESCRIPTION
	"Table for insightsTrafficPreviousDumpRecords"
	::={insightsTrafficPreviousDumpRecords 4}

insightsTrafficPreviousDumpRecordsLevelEntry OBJECT-TYPE
	SYNTAX      InsightsTrafficPreviousDumpRecordsLevelEntry
	MAX-ACCESS  not-accessible
	STATUS      current
	DESCRIPTION
	"Table entry for insightsTrafficPreviousDumpRecords"
	INDEX { insightsTrafficPreviousDumpRecordsLevelName }
	::={insightsTrafficPreviousDumpRecordsLevelTable 1}

InsightsTrafficPreviousDumpRecordsLevelEntry ::=
	SEQUENCE {
		insightsTrafficPreviousDumpRecordsLevelName	DisplayString,
		insightsTrafficPreviousDumpRecordsLevelVal	CounterBasedGauge64,
		insightsTrafficPreviousDumpRecordsLevelMax	CounterBasedGauge64
	}

insightsTrafficPreviousDumpRecordsLevelName OBJECT-TYPE
	SYNTAX      DisplayString
	MAX-ACCESS  not-accessible
	STATUS      current
	DESCRIPTION
	"Table entry display string for insightsTrafficPreviousDumpRecords"
	::={insightsTrafficPreviousDumpRecordsLevelEntry 1}

insightsTrafficPreviousDumpRecordsLevelVal OBJECT-TYPE
	SYNTAX	 CounterBasedGauge64
	MAX-ACCESS  read-only
	STATUS      current
	DESCRIPTION
	"Table entry attribute for insightsTrafficPreviousDumpRecords"
	::={insightsTrafficPreviousDumpRecordsLevelEntry 2}

insightsTrafficPreviousDumpRecordsLevelMax OBJECT-TYPE
	SYNTAX	 CounterBasedGauge64
	MAX-ACCESS  read-only
	STATUS      current
	DESCRIPTION
	"Table entry attribute for insightsTrafficPreviousDumpRecords"
	::={insightsTrafficPreviousDumpRecordsLevelEntry 4}


insightsTrafficRecordsRejected	OBJECT IDENTIFIER ::={insights 56}

insightsTrafficRecordsRejectedVal	OBJECT-TYPE
	SYNTAX	 Counter64
	MAX-ACCESS read-only
	STATUS current
	DESCRIPTION "Traffic: Records rejected"

	::={insightsTrafficRecordsRejected 1}

insightsTrafficRecordsRejectedMom	OBJECT-TYPE
	SYNTAX	 CounterBasedGauge64
	MAX-ACCESS read-only
	STATUS current
	DESCRIPTION "Traffic: Records rejected"

	::={insightsTrafficRecordsRejected 2}

insightsTrafficRecordsRejectedMax	OBJECT-TYPE
	SYNTAX	 CounterBasedGauge64
	MAX-ACCESS read-only
	STATUS current
	DESCRIPTION "Traffic: Records rejected"

	::={insightsTrafficRecordsRejected 3}

insightsTrafficRecordsRejectedLevelTable OBJECT-TYPE
	SYNTAX      SEQUENCE OF InsightsTrafficRecordsRejectedLevelEntry
	MAX-ACCESS  not-accessible
	STATUS      current
	DESCRIPTION
	"Table for insightsTrafficRecordsRejected"
	::={insightsTrafficRecordsRejected 4}

insightsTrafficRecordsRejectedLevelEntry OBJECT-TYPE
	SYNTAX      InsightsTrafficRecordsRejectedLevelEntry
	MAX-ACCESS  not-accessible
	STATUS      current
	DESCRIPTION
	"Table entry for insightsTrafficRecordsRejected"
	INDEX { insightsTrafficRecordsRejectedLevelName }
	::={insightsTrafficRecordsRejectedLevelTable 1}

InsightsTrafficRecordsRejectedLevelEntry ::=
	SEQUENCE {
		insightsTrafficRecordsRejectedLevelName	DisplayString,
		insightsTrafficRecordsRejectedLevelVal	Counter64,
		insightsTrafficRecordsRejectedLevelMom	CounterBasedGauge64,
		insightsTrafficRecordsRejectedLevelMax	CounterBasedGauge64
	}

insightsTrafficRecordsRejectedLevelName OBJECT-TYPE
	SYNTAX      DisplayString
	MAX-ACCESS  not-accessible
	STATUS      current
	DESCRIPTION
	"Table entry display string for insightsTrafficRecordsRejected"
	::={insightsTrafficRecordsRejectedLevelEntry 1}

insightsTrafficRecordsRejectedLevelVal OBJECT-TYPE
	SYNTAX	 Counter64
	MAX-ACCESS  read-only
	STATUS      current
	DESCRIPTION
	"Table entry attribute for insightsTrafficRecordsRejected"
	::={insightsTrafficRecordsRejectedLevelEntry 2}

insightsTrafficRecordsRejectedLevelMom OBJECT-TYPE
	SYNTAX	 CounterBasedGauge64
	MAX-ACCESS  read-only
	STATUS      current
	DESCRIPTION
	"Table entry attribute for insightsTrafficRecordsRejected"
	::={insightsTrafficRecordsRejectedLevelEntry 3}

insightsTrafficRecordsRejectedLevelMax OBJECT-TYPE
	SYNTAX	 CounterBasedGauge64
	MAX-ACCESS  read-only
	STATUS      current
	DESCRIPTION
	"Table entry attribute for insightsTrafficRecordsRejected"
	::={insightsTrafficRecordsRejectedLevelEntry 4}


insightsScoreLowFreqRecordsRejected	OBJECT IDENTIFIER ::={insights 57}

insightsScoreLowFreqRecordsRejectedVal	OBJECT-TYPE
	SYNTAX	 Counter64
	MAX-ACCESS read-only
	STATUS obsolete
	DESCRIPTION "Score: Low frequency records rejected"

	::={insightsScoreLowFreqRecordsRejected 1}

insightsScoreLowFreqRecordsRejectedMom	OBJECT-TYPE
	SYNTAX	 CounterBasedGauge64
	MAX-ACCESS read-only
	STATUS obsolete
	DESCRIPTION "Score: Low frequency records rejected"

	::={insightsScoreLowFreqRecordsRejected 2}

insightsScoreLowFreqRecordsRejectedMax	OBJECT-TYPE
	SYNTAX	 CounterBasedGauge64
	MAX-ACCESS read-only
	STATUS obsolete
	DESCRIPTION "Score: Low frequency records rejected"

	::={insightsScoreLowFreqRecordsRejected 3}

insightsScoreLowFreqRecordsRejectedLevelTable OBJECT-TYPE
	SYNTAX      SEQUENCE OF InsightsScoreLowFreqRecordsRejectedLevelEntry
	MAX-ACCESS  not-accessible
	STATUS      current
	DESCRIPTION
	"Table for insightsScoreLowFreqRecordsRejected"
	::={insightsScoreLowFreqRecordsRejected 4}

insightsScoreLowFreqRecordsRejectedLevelEntry OBJECT-TYPE
	SYNTAX      InsightsScoreLowFreqRecordsRejectedLevelEntry
	MAX-ACCESS  not-accessible
	STATUS      current
	DESCRIPTION
	"Table entry for insightsScoreLowFreqRecordsRejected"
	INDEX { insightsScoreLowFreqRecordsRejectedLevelName }
	::={insightsScoreLowFreqRecordsRejectedLevelTable 1}

InsightsScoreLowFreqRecordsRejectedLevelEntry ::=
	SEQUENCE {
		insightsScoreLowFreqRecordsRejectedLevelName	DisplayString,
		insightsScoreLowFreqRecordsRejectedLevelVal	Counter64,
		insightsScoreLowFreqRecordsRejectedLevelMom	CounterBasedGauge64,
		insightsScoreLowFreqRecordsRejectedLevelMax	CounterBasedGauge64
	}

insightsScoreLowFreqRecordsRejectedLevelName OBJECT-TYPE
	SYNTAX      DisplayString
	MAX-ACCESS  not-accessible
	STATUS      current
	DESCRIPTION
	"Table entry display string for insightsScoreLowFreqRecordsRejected"
	::={insightsScoreLowFreqRecordsRejectedLevelEntry 1}

insightsScoreLowFreqRecordsRejectedLevelVal OBJECT-TYPE
	SYNTAX	 Counter64
	MAX-ACCESS  read-only
	STATUS      current
	DESCRIPTION
	"Table entry attribute for insightsScoreLowFreqRecordsRejected"
	::={insightsScoreLowFreqRecordsRejectedLevelEntry 2}

insightsScoreLowFreqRecordsRejectedLevelMom OBJECT-TYPE
	SYNTAX	 CounterBasedGauge64
	MAX-ACCESS  read-only
	STATUS      current
	DESCRIPTION
	"Table entry attribute for insightsScoreLowFreqRecordsRejected"
	::={insightsScoreLowFreqRecordsRejectedLevelEntry 3}

insightsScoreLowFreqRecordsRejectedLevelMax OBJECT-TYPE
	SYNTAX	 CounterBasedGauge64
	MAX-ACCESS  read-only
	STATUS      current
	DESCRIPTION
	"Table entry attribute for insightsScoreLowFreqRecordsRejected"
	::={insightsScoreLowFreqRecordsRejectedLevelEntry 4}


insightsScoreRecordsRejected	OBJECT IDENTIFIER ::={insights 58}

insightsScoreRecordsRejectedVal	OBJECT-TYPE
	SYNTAX	 Counter64
	MAX-ACCESS read-only
	STATUS current
	DESCRIPTION "Score: Records rejected"

	::={insightsScoreRecordsRejected 1}

insightsScoreRecordsRejectedMom	OBJECT-TYPE
	SYNTAX	 CounterBasedGauge64
	MAX-ACCESS read-only
	STATUS current
	DESCRIPTION "Score: Records rejected"

	::={insightsScoreRecordsRejected 2}

insightsScoreRecordsRejectedMax	OBJECT-TYPE
	SYNTAX	 CounterBasedGauge64
	MAX-ACCESS read-only
	STATUS current
	DESCRIPTION "Score: Records rejected"

	::={insightsScoreRecordsRejected 3}

insightsScoreRecordsRejectedLevelTable OBJECT-TYPE
	SYNTAX      SEQUENCE OF InsightsScoreRecordsRejectedLevelEntry
	MAX-ACCESS  not-accessible
	STATUS      current
	DESCRIPTION
	"Table for insightsScoreRecordsRejected"
	::={insightsScoreRecordsRejected 4}

insightsScoreRecordsRejectedLevelEntry OBJECT-TYPE
	SYNTAX      InsightsScoreRecordsRejectedLevelEntry
	MAX-ACCESS  not-accessible
	STATUS      current
	DESCRIPTION
	"Table entry for insightsScoreRecordsRejected"
	INDEX { insightsScoreRecordsRejectedLevelName }
	::={insightsScoreRecordsRejectedLevelTable 1}

InsightsScoreRecordsRejectedLevelEntry ::=
	SEQUENCE {
		insightsScoreRecordsRejectedLevelName	DisplayString,
		insightsScoreRecordsRejectedLevelVal	Counter64,
		insightsScoreRecordsRejectedLevelMom	CounterBasedGauge64,
		insightsScoreRecordsRejectedLevelMax	CounterBasedGauge64
	}

insightsScoreRecordsRejectedLevelName OBJECT-TYPE
	SYNTAX      DisplayString
	MAX-ACCESS  not-accessible
	STATUS      current
	DESCRIPTION
	"Table entry display string for insightsScoreRecordsRejected"
	::={insightsScoreRecordsRejectedLevelEntry 1}

insightsScoreRecordsRejectedLevelVal OBJECT-TYPE
	SYNTAX	 Counter64
	MAX-ACCESS  read-only
	STATUS      current
	DESCRIPTION
	"Table entry attribute for insightsScoreRecordsRejected"
	::={insightsScoreRecordsRejectedLevelEntry 2}

insightsScoreRecordsRejectedLevelMom OBJECT-TYPE
	SYNTAX	 CounterBasedGauge64
	MAX-ACCESS  read-only
	STATUS      current
	DESCRIPTION
	"Table entry attribute for insightsScoreRecordsRejected"
	::={insightsScoreRecordsRejectedLevelEntry 3}

insightsScoreRecordsRejectedLevelMax OBJECT-TYPE
	SYNTAX	 CounterBasedGauge64
	MAX-ACCESS  read-only
	STATUS      current
	DESCRIPTION
	"Table entry attribute for insightsScoreRecordsRejected"
	::={insightsScoreRecordsRejectedLevelEntry 4}


insightsTrafficBatchesDropped	OBJECT IDENTIFIER ::={insights 59}

insightsTrafficBatchesDroppedVal	OBJECT-TYPE
	SYNTAX	 Counter64
	MAX-ACCESS read-only
	STATUS current
	DESCRIPTION "Traffic: Batches dropped"

	::={insightsTrafficBatchesDropped 1}

insightsTrafficBatchesDroppedMom	OBJECT-TYPE
	SYNTAX	 CounterBasedGauge64
	MAX-ACCESS read-only
	STATUS current
	DESCRIPTION "Traffic: Batches dropped"

	::={insightsTrafficBatchesDropped 2}

insightsTrafficBatchesDroppedMax	OBJECT-TYPE
	SYNTAX	 CounterBasedGauge64
	MAX-ACCESS read-only
	STATUS current
	DESCRIPTION "Traffic: Batches dropped"

	::={insightsTrafficBatchesDropped 3}

insightsTrafficBatchesDroppedLevelTable OBJECT-TYPE
	SYNTAX      SEQUENCE OF InsightsTrafficBatchesDroppedLevelEntry
	MAX-ACCESS  not-accessible
	STATUS      current
	DESCRIPTION
	"Table for insightsTrafficBatchesDropped"
	::={insightsTrafficBatchesDropped 4}

insightsTrafficBatchesDroppedLevelEntry OBJECT-TYPE
	SYNTAX      InsightsTrafficBatchesDroppedLevelEntry
	MAX-ACCESS  not-accessible
	STATUS      current
	DESCRIPTION
	"Table entry for insightsTrafficBatchesDropped"
	INDEX { insightsTrafficBatchesDroppedLevelName }
	::={insightsTrafficBatchesDroppedLevelTable 1}

InsightsTrafficBatchesDroppedLevelEntry ::=
	SEQUENCE {
		insightsTrafficBatchesDroppedLevelName	DisplayString,
		insightsTrafficBatchesDroppedLevelVal	Counter64,
		insightsTrafficBatchesDroppedLevelMom	CounterBasedGauge64,
		insightsTrafficBatchesDroppedLevelMax	CounterBasedGauge64
	}

insightsTrafficBatchesDroppedLevelName OBJECT-TYPE
	SYNTAX      DisplayString
	MAX-ACCESS  not-accessible
	STATUS      current
	DESCRIPTION
	"Table entry display string for insightsTrafficBatchesDropped"
	::={insightsTrafficBatchesDroppedLevelEntry 1}

insightsTrafficBatchesDroppedLevelVal OBJECT-TYPE
	SYNTAX	 Counter64
	MAX-ACCESS  read-only
	STATUS      current
	DESCRIPTION
	"Table entry attribute for insightsTrafficBatchesDropped"
	::={insightsTrafficBatchesDroppedLevelEntry 2}

insightsTrafficBatchesDroppedLevelMom OBJECT-TYPE
	SYNTAX	 CounterBasedGauge64
	MAX-ACCESS  read-only
	STATUS      current
	DESCRIPTION
	"Table entry attribute for insightsTrafficBatchesDropped"
	::={insightsTrafficBatchesDroppedLevelEntry 3}

insightsTrafficBatchesDroppedLevelMax OBJECT-TYPE
	SYNTAX	 CounterBasedGauge64
	MAX-ACCESS  read-only
	STATUS      current
	DESCRIPTION
	"Table entry attribute for insightsTrafficBatchesDropped"
	::={insightsTrafficBatchesDroppedLevelEntry 4}


insightsScoreLowFreqBatchesDropped	OBJECT IDENTIFIER ::={insights 60}

insightsScoreLowFreqBatchesDroppedVal	OBJECT-TYPE
	SYNTAX	 Counter64
	MAX-ACCESS read-only
	STATUS obsolete
	DESCRIPTION "Score: Low frequency batches dropped"

	::={insightsScoreLowFreqBatchesDropped 1}

insightsScoreLowFreqBatchesDroppedMom	OBJECT-TYPE
	SYNTAX	 CounterBasedGauge64
	MAX-ACCESS read-only
	STATUS obsolete
	DESCRIPTION "Score: Low frequency batches dropped"

	::={insightsScoreLowFreqBatchesDropped 2}

insightsScoreLowFreqBatchesDroppedMax	OBJECT-TYPE
	SYNTAX	 CounterBasedGauge64
	MAX-ACCESS read-only
	STATUS obsolete
	DESCRIPTION "Score: Low frequency batches dropped"

	::={insightsScoreLowFreqBatchesDropped 3}

insightsScoreLowFreqBatchesDroppedLevelTable OBJECT-TYPE
	SYNTAX      SEQUENCE OF InsightsScoreLowFreqBatchesDroppedLevelEntry
	MAX-ACCESS  not-accessible
	STATUS      current
	DESCRIPTION
	"Table for insightsScoreLowFreqBatchesDropped"
	::={insightsScoreLowFreqBatchesDropped 4}

insightsScoreLowFreqBatchesDroppedLevelEntry OBJECT-TYPE
	SYNTAX      InsightsScoreLowFreqBatchesDroppedLevelEntry
	MAX-ACCESS  not-accessible
	STATUS      current
	DESCRIPTION
	"Table entry for insightsScoreLowFreqBatchesDropped"
	INDEX { insightsScoreLowFreqBatchesDroppedLevelName }
	::={insightsScoreLowFreqBatchesDroppedLevelTable 1}

InsightsScoreLowFreqBatchesDroppedLevelEntry ::=
	SEQUENCE {
		insightsScoreLowFreqBatchesDroppedLevelName	DisplayString,
		insightsScoreLowFreqBatchesDroppedLevelVal	Counter64,
		insightsScoreLowFreqBatchesDroppedLevelMom	CounterBasedGauge64,
		insightsScoreLowFreqBatchesDroppedLevelMax	CounterBasedGauge64
	}

insightsScoreLowFreqBatchesDroppedLevelName OBJECT-TYPE
	SYNTAX      DisplayString
	MAX-ACCESS  not-accessible
	STATUS      current
	DESCRIPTION
	"Table entry display string for insightsScoreLowFreqBatchesDropped"
	::={insightsScoreLowFreqBatchesDroppedLevelEntry 1}

insightsScoreLowFreqBatchesDroppedLevelVal OBJECT-TYPE
	SYNTAX	 Counter64
	MAX-ACCESS  read-only
	STATUS      current
	DESCRIPTION
	"Table entry attribute for insightsScoreLowFreqBatchesDropped"
	::={insightsScoreLowFreqBatchesDroppedLevelEntry 2}

insightsScoreLowFreqBatchesDroppedLevelMom OBJECT-TYPE
	SYNTAX	 CounterBasedGauge64
	MAX-ACCESS  read-only
	STATUS      current
	DESCRIPTION
	"Table entry attribute for insightsScoreLowFreqBatchesDropped"
	::={insightsScoreLowFreqBatchesDroppedLevelEntry 3}

insightsScoreLowFreqBatchesDroppedLevelMax OBJECT-TYPE
	SYNTAX	 CounterBasedGauge64
	MAX-ACCESS  read-only
	STATUS      current
	DESCRIPTION
	"Table entry attribute for insightsScoreLowFreqBatchesDropped"
	::={insightsScoreLowFreqBatchesDroppedLevelEntry 4}


insightsScoreBatchesDropped	OBJECT IDENTIFIER ::={insights 61}

insightsScoreBatchesDroppedVal	OBJECT-TYPE
	SYNTAX	 Counter64
	MAX-ACCESS read-only
	STATUS current
	DESCRIPTION "Score: Batches dropped"

	::={insightsScoreBatchesDropped 1}

insightsScoreBatchesDroppedMom	OBJECT-TYPE
	SYNTAX	 CounterBasedGauge64
	MAX-ACCESS read-only
	STATUS current
	DESCRIPTION "Score: Batches dropped"

	::={insightsScoreBatchesDropped 2}

insightsScoreBatchesDroppedMax	OBJECT-TYPE
	SYNTAX	 CounterBasedGauge64
	MAX-ACCESS read-only
	STATUS current
	DESCRIPTION "Score: Batches dropped"

	::={insightsScoreBatchesDropped 3}

insightsScoreBatchesDroppedLevelTable OBJECT-TYPE
	SYNTAX      SEQUENCE OF InsightsScoreBatchesDroppedLevelEntry
	MAX-ACCESS  not-accessible
	STATUS      current
	DESCRIPTION
	"Table for insightsScoreBatchesDropped"
	::={insightsScoreBatchesDropped 4}

insightsScoreBatchesDroppedLevelEntry OBJECT-TYPE
	SYNTAX      InsightsScoreBatchesDroppedLevelEntry
	MAX-ACCESS  not-accessible
	STATUS      current
	DESCRIPTION
	"Table entry for insightsScoreBatchesDropped"
	INDEX { insightsScoreBatchesDroppedLevelName }
	::={insightsScoreBatchesDroppedLevelTable 1}

InsightsScoreBatchesDroppedLevelEntry ::=
	SEQUENCE {
		insightsScoreBatchesDroppedLevelName	DisplayString,
		insightsScoreBatchesDroppedLevelVal	Counter64,
		insightsScoreBatchesDroppedLevelMom	CounterBasedGauge64,
		insightsScoreBatchesDroppedLevelMax	CounterBasedGauge64
	}

insightsScoreBatchesDroppedLevelName OBJECT-TYPE
	SYNTAX      DisplayString
	MAX-ACCESS  not-accessible
	STATUS      current
	DESCRIPTION
	"Table entry display string for insightsScoreBatchesDropped"
	::={insightsScoreBatchesDroppedLevelEntry 1}

insightsScoreBatchesDroppedLevelVal OBJECT-TYPE
	SYNTAX	 Counter64
	MAX-ACCESS  read-only
	STATUS      current
	DESCRIPTION
	"Table entry attribute for insightsScoreBatchesDropped"
	::={insightsScoreBatchesDroppedLevelEntry 2}

insightsScoreBatchesDroppedLevelMom OBJECT-TYPE
	SYNTAX	 CounterBasedGauge64
	MAX-ACCESS  read-only
	STATUS      current
	DESCRIPTION
	"Table entry attribute for insightsScoreBatchesDropped"
	::={insightsScoreBatchesDroppedLevelEntry 3}

insightsScoreBatchesDroppedLevelMax OBJECT-TYPE
	SYNTAX	 CounterBasedGauge64
	MAX-ACCESS  read-only
	STATUS      current
	DESCRIPTION
	"Table entry attribute for insightsScoreBatchesDropped"
	::={insightsScoreBatchesDroppedLevelEntry 4}


insightsDatacoreUncompressedBytesSent	OBJECT IDENTIFIER ::={insights 62}

insightsDatacoreUncompressedBytesSentVal	OBJECT-TYPE
	SYNTAX	 Counter64
	MAX-ACCESS read-only
	STATUS current
	DESCRIPTION "Datacore: Uncompressed bytes sent"

	::={insightsDatacoreUncompressedBytesSent 1}

insightsDatacoreUncompressedBytesSentMom	OBJECT-TYPE
	SYNTAX	 CounterBasedGauge64
	MAX-ACCESS read-only
	STATUS current
	DESCRIPTION "Datacore: Uncompressed bytes sent"

	::={insightsDatacoreUncompressedBytesSent 2}

insightsDatacoreUncompressedBytesSentMax	OBJECT-TYPE
	SYNTAX	 CounterBasedGauge64
	MAX-ACCESS read-only
	STATUS current
	DESCRIPTION "Datacore: Uncompressed bytes sent"

	::={insightsDatacoreUncompressedBytesSent 3}

insightsDatacoreUncompressedBytesSentLevelTable OBJECT-TYPE
	SYNTAX      SEQUENCE OF InsightsDatacoreUncompressedBytesSentLevelEntry
	MAX-ACCESS  not-accessible
	STATUS      current
	DESCRIPTION
	"Table for insightsDatacoreUncompressedBytesSent"
	::={insightsDatacoreUncompressedBytesSent 4}

insightsDatacoreUncompressedBytesSentLevelEntry OBJECT-TYPE
	SYNTAX      InsightsDatacoreUncompressedBytesSentLevelEntry
	MAX-ACCESS  not-accessible
	STATUS      current
	DESCRIPTION
	"Table entry for insightsDatacoreUncompressedBytesSent"
	INDEX { insightsDatacoreUncompressedBytesSentLevelName }
	::={insightsDatacoreUncompressedBytesSentLevelTable 1}

InsightsDatacoreUncompressedBytesSentLevelEntry ::=
	SEQUENCE {
		insightsDatacoreUncompressedBytesSentLevelName	DisplayString,
		insightsDatacoreUncompressedBytesSentLevelVal	Counter64,
		insightsDatacoreUncompressedBytesSentLevelMom	CounterBasedGauge64,
		insightsDatacoreUncompressedBytesSentLevelMax	CounterBasedGauge64
	}

insightsDatacoreUncompressedBytesSentLevelName OBJECT-TYPE
	SYNTAX      DisplayString
	MAX-ACCESS  not-accessible
	STATUS      current
	DESCRIPTION
	"Table entry display string for insightsDatacoreUncompressedBytesSent"
	::={insightsDatacoreUncompressedBytesSentLevelEntry 1}

insightsDatacoreUncompressedBytesSentLevelVal OBJECT-TYPE
	SYNTAX	 Counter64
	MAX-ACCESS  read-only
	STATUS      current
	DESCRIPTION
	"Table entry attribute for insightsDatacoreUncompressedBytesSent"
	::={insightsDatacoreUncompressedBytesSentLevelEntry 2}

insightsDatacoreUncompressedBytesSentLevelMom OBJECT-TYPE
	SYNTAX	 CounterBasedGauge64
	MAX-ACCESS  read-only
	STATUS      current
	DESCRIPTION
	"Table entry attribute for insightsDatacoreUncompressedBytesSent"
	::={insightsDatacoreUncompressedBytesSentLevelEntry 3}

insightsDatacoreUncompressedBytesSentLevelMax OBJECT-TYPE
	SYNTAX	 CounterBasedGauge64
	MAX-ACCESS  read-only
	STATUS      current
	DESCRIPTION
	"Table entry attribute for insightsDatacoreUncompressedBytesSent"
	::={insightsDatacoreUncompressedBytesSentLevelEntry 4}


insightsTrafficUncompressedBytesSent	OBJECT IDENTIFIER ::={insights 63}

insightsTrafficUncompressedBytesSentVal	OBJECT-TYPE
	SYNTAX	 Counter64
	MAX-ACCESS read-only
	STATUS current
	DESCRIPTION "Traffic: Uncompressed bytes sent"

	::={insightsTrafficUncompressedBytesSent 1}

insightsTrafficUncompressedBytesSentMom	OBJECT-TYPE
	SYNTAX	 CounterBasedGauge64
	MAX-ACCESS read-only
	STATUS current
	DESCRIPTION "Traffic: Uncompressed bytes sent"

	::={insightsTrafficUncompressedBytesSent 2}

insightsTrafficUncompressedBytesSentMax	OBJECT-TYPE
	SYNTAX	 CounterBasedGauge64
	MAX-ACCESS read-only
	STATUS current
	DESCRIPTION "Traffic: Uncompressed bytes sent"

	::={insightsTrafficUncompressedBytesSent 3}

insightsTrafficUncompressedBytesSentLevelTable OBJECT-TYPE
	SYNTAX      SEQUENCE OF InsightsTrafficUncompressedBytesSentLevelEntry
	MAX-ACCESS  not-accessible
	STATUS      current
	DESCRIPTION
	"Table for insightsTrafficUncompressedBytesSent"
	::={insightsTrafficUncompressedBytesSent 4}

insightsTrafficUncompressedBytesSentLevelEntry OBJECT-TYPE
	SYNTAX      InsightsTrafficUncompressedBytesSentLevelEntry
	MAX-ACCESS  not-accessible
	STATUS      current
	DESCRIPTION
	"Table entry for insightsTrafficUncompressedBytesSent"
	INDEX { insightsTrafficUncompressedBytesSentLevelName }
	::={insightsTrafficUncompressedBytesSentLevelTable 1}

InsightsTrafficUncompressedBytesSentLevelEntry ::=
	SEQUENCE {
		insightsTrafficUncompressedBytesSentLevelName	DisplayString,
		insightsTrafficUncompressedBytesSentLevelVal	Counter64,
		insightsTrafficUncompressedBytesSentLevelMom	CounterBasedGauge64,
		insightsTrafficUncompressedBytesSentLevelMax	CounterBasedGauge64
	}

insightsTrafficUncompressedBytesSentLevelName OBJECT-TYPE
	SYNTAX      DisplayString
	MAX-ACCESS  not-accessible
	STATUS      current
	DESCRIPTION
	"Table entry display string for insightsTrafficUncompressedBytesSent"
	::={insightsTrafficUncompressedBytesSentLevelEntry 1}

insightsTrafficUncompressedBytesSentLevelVal OBJECT-TYPE
	SYNTAX	 Counter64
	MAX-ACCESS  read-only
	STATUS      current
	DESCRIPTION
	"Table entry attribute for insightsTrafficUncompressedBytesSent"
	::={insightsTrafficUncompressedBytesSentLevelEntry 2}

insightsTrafficUncompressedBytesSentLevelMom OBJECT-TYPE
	SYNTAX	 CounterBasedGauge64
	MAX-ACCESS  read-only
	STATUS      current
	DESCRIPTION
	"Table entry attribute for insightsTrafficUncompressedBytesSent"
	::={insightsTrafficUncompressedBytesSentLevelEntry 3}

insightsTrafficUncompressedBytesSentLevelMax OBJECT-TYPE
	SYNTAX	 CounterBasedGauge64
	MAX-ACCESS  read-only
	STATUS      current
	DESCRIPTION
	"Table entry attribute for insightsTrafficUncompressedBytesSent"
	::={insightsTrafficUncompressedBytesSentLevelEntry 4}


insightsScoreLowFreqUncompressedBytesSent	OBJECT IDENTIFIER ::={insights 64}

insightsScoreLowFreqUncompressedBytesSentVal	OBJECT-TYPE
	SYNTAX	 Counter64
	MAX-ACCESS read-only
	STATUS obsolete
	DESCRIPTION "Score: Low frequency uncompressed bytes sent"

	::={insightsScoreLowFreqUncompressedBytesSent 1}

insightsScoreLowFreqUncompressedBytesSentMom	OBJECT-TYPE
	SYNTAX	 CounterBasedGauge64
	MAX-ACCESS read-only
	STATUS obsolete
	DESCRIPTION "Score: Low frequency uncompressed bytes sent"

	::={insightsScoreLowFreqUncompressedBytesSent 2}

insightsScoreLowFreqUncompressedBytesSentMax	OBJECT-TYPE
	SYNTAX	 CounterBasedGauge64
	MAX-ACCESS read-only
	STATUS obsolete
	DESCRIPTION "Score: Low frequency uncompressed bytes sent"

	::={insightsScoreLowFreqUncompressedBytesSent 3}

insightsScoreLowFreqUncompressedBytesSentLevelTable OBJECT-TYPE
	SYNTAX      SEQUENCE OF InsightsScoreLowFreqUncompressedBytesSentLevelEntry
	MAX-ACCESS  not-accessible
	STATUS      current
	DESCRIPTION
	"Table for insightsScoreLowFreqUncompressedBytesSent"
	::={insightsScoreLowFreqUncompressedBytesSent 4}

insightsScoreLowFreqUncompressedBytesSentLevelEntry OBJECT-TYPE
	SYNTAX      InsightsScoreLowFreqUncompressedBytesSentLevelEntry
	MAX-ACCESS  not-accessible
	STATUS      current
	DESCRIPTION
	"Table entry for insightsScoreLowFreqUncompressedBytesSent"
	INDEX { insightsScoreLowFreqUncompressedBytesSentLevelName }
	::={insightsScoreLowFreqUncompressedBytesSentLevelTable 1}

InsightsScoreLowFreqUncompressedBytesSentLevelEntry ::=
	SEQUENCE {
		insightsScoreLowFreqUncompressedBytesSentLevelName	DisplayString,
		insightsScoreLowFreqUncompressedBytesSentLevelVal	Counter64,
		insightsScoreLowFreqUncompressedBytesSentLevelMom	CounterBasedGauge64,
		insightsScoreLowFreqUncompressedBytesSentLevelMax	CounterBasedGauge64
	}

insightsScoreLowFreqUncompressedBytesSentLevelName OBJECT-TYPE
	SYNTAX      DisplayString
	MAX-ACCESS  not-accessible
	STATUS      current
	DESCRIPTION
	"Table entry display string for insightsScoreLowFreqUncompressedBytesSent"
	::={insightsScoreLowFreqUncompressedBytesSentLevelEntry 1}

insightsScoreLowFreqUncompressedBytesSentLevelVal OBJECT-TYPE
	SYNTAX	 Counter64
	MAX-ACCESS  read-only
	STATUS      current
	DESCRIPTION
	"Table entry attribute for insightsScoreLowFreqUncompressedBytesSent"
	::={insightsScoreLowFreqUncompressedBytesSentLevelEntry 2}

insightsScoreLowFreqUncompressedBytesSentLevelMom OBJECT-TYPE
	SYNTAX	 CounterBasedGauge64
	MAX-ACCESS  read-only
	STATUS      current
	DESCRIPTION
	"Table entry attribute for insightsScoreLowFreqUncompressedBytesSent"
	::={insightsScoreLowFreqUncompressedBytesSentLevelEntry 3}

insightsScoreLowFreqUncompressedBytesSentLevelMax OBJECT-TYPE
	SYNTAX	 CounterBasedGauge64
	MAX-ACCESS  read-only
	STATUS      current
	DESCRIPTION
	"Table entry attribute for insightsScoreLowFreqUncompressedBytesSent"
	::={insightsScoreLowFreqUncompressedBytesSentLevelEntry 4}


insightsScoreUncompressedBytesSent	OBJECT IDENTIFIER ::={insights 65}

insightsScoreUncompressedBytesSentVal	OBJECT-TYPE
	SYNTAX	 Counter64
	MAX-ACCESS read-only
	STATUS current
	DESCRIPTION "Score: Uncompressed bytes sent"

	::={insightsScoreUncompressedBytesSent 1}

insightsScoreUncompressedBytesSentMom	OBJECT-TYPE
	SYNTAX	 CounterBasedGauge64
	MAX-ACCESS read-only
	STATUS current
	DESCRIPTION "Score: Uncompressed bytes sent"

	::={insightsScoreUncompressedBytesSent 2}

insightsScoreUncompressedBytesSentMax	OBJECT-TYPE
	SYNTAX	 CounterBasedGauge64
	MAX-ACCESS read-only
	STATUS current
	DESCRIPTION "Score: Uncompressed bytes sent"

	::={insightsScoreUncompressedBytesSent 3}

insightsScoreUncompressedBytesSentLevelTable OBJECT-TYPE
	SYNTAX      SEQUENCE OF InsightsScoreUncompressedBytesSentLevelEntry
	MAX-ACCESS  not-accessible
	STATUS      current
	DESCRIPTION
	"Table for insightsScoreUncompressedBytesSent"
	::={insightsScoreUncompressedBytesSent 4}

insightsScoreUncompressedBytesSentLevelEntry OBJECT-TYPE
	SYNTAX      InsightsScoreUncompressedBytesSentLevelEntry
	MAX-ACCESS  not-accessible
	STATUS      current
	DESCRIPTION
	"Table entry for insightsScoreUncompressedBytesSent"
	INDEX { insightsScoreUncompressedBytesSentLevelName }
	::={insightsScoreUncompressedBytesSentLevelTable 1}

InsightsScoreUncompressedBytesSentLevelEntry ::=
	SEQUENCE {
		insightsScoreUncompressedBytesSentLevelName	DisplayString,
		insightsScoreUncompressedBytesSentLevelVal	Counter64,
		insightsScoreUncompressedBytesSentLevelMom	CounterBasedGauge64,
		insightsScoreUncompressedBytesSentLevelMax	CounterBasedGauge64
	}

insightsScoreUncompressedBytesSentLevelName OBJECT-TYPE
	SYNTAX      DisplayString
	MAX-ACCESS  not-accessible
	STATUS      current
	DESCRIPTION
	"Table entry display string for insightsScoreUncompressedBytesSent"
	::={insightsScoreUncompressedBytesSentLevelEntry 1}

insightsScoreUncompressedBytesSentLevelVal OBJECT-TYPE
	SYNTAX	 Counter64
	MAX-ACCESS  read-only
	STATUS      current
	DESCRIPTION
	"Table entry attribute for insightsScoreUncompressedBytesSent"
	::={insightsScoreUncompressedBytesSentLevelEntry 2}

insightsScoreUncompressedBytesSentLevelMom OBJECT-TYPE
	SYNTAX	 CounterBasedGauge64
	MAX-ACCESS  read-only
	STATUS      current
	DESCRIPTION
	"Table entry attribute for insightsScoreUncompressedBytesSent"
	::={insightsScoreUncompressedBytesSentLevelEntry 3}

insightsScoreUncompressedBytesSentLevelMax OBJECT-TYPE
	SYNTAX	 CounterBasedGauge64
	MAX-ACCESS  read-only
	STATUS      current
	DESCRIPTION
	"Table entry attribute for insightsScoreUncompressedBytesSent"
	::={insightsScoreUncompressedBytesSentLevelEntry 4}


insightsScoreDumpTime	OBJECT IDENTIFIER ::={insights 66}

insightsScoreDumpTimeVal	OBJECT-TYPE
	SYNTAX	 TimeTicks
	MAX-ACCESS read-only
	STATUS current
	DESCRIPTION "Score: Dump duration"

	::={insightsScoreDumpTime 1}

insightsScoreDumpTimeLevelTable OBJECT-TYPE
	SYNTAX      SEQUENCE OF InsightsScoreDumpTimeLevelEntry
	MAX-ACCESS  not-accessible
	STATUS      current
	DESCRIPTION
	"Table for insightsScoreDumpTime"
	::={insightsScoreDumpTime 2}

insightsScoreDumpTimeLevelEntry OBJECT-TYPE
	SYNTAX      InsightsScoreDumpTimeLevelEntry
	MAX-ACCESS  not-accessible
	STATUS      current
	DESCRIPTION
	"Table entry for insightsScoreDumpTime"
	INDEX { insightsScoreDumpTimeLevelName }
	::={insightsScoreDumpTimeLevelTable 1}

InsightsScoreDumpTimeLevelEntry ::=
	SEQUENCE {
		insightsScoreDumpTimeLevelName	DisplayString,
		insightsScoreDumpTimeLevelVal	TimeTicks
	}

insightsScoreDumpTimeLevelName OBJECT-TYPE
	SYNTAX      DisplayString
	MAX-ACCESS  not-accessible
	STATUS      current
	DESCRIPTION
	"Table entry display string for insightsScoreDumpTime"
	::={insightsScoreDumpTimeLevelEntry 1}

insightsScoreDumpTimeLevelVal OBJECT-TYPE
	SYNTAX	 TimeTicks
	MAX-ACCESS  read-only
	STATUS      current
	DESCRIPTION
	"Table entry attribute for insightsScoreDumpTime"
	::={insightsScoreDumpTimeLevelEntry 2}


insightsScoreDumpBacklog	OBJECT IDENTIFIER ::={insights 67}

insightsScoreDumpBacklogVal	OBJECT-TYPE
	SYNTAX	 CounterBasedGauge64
	MAX-ACCESS read-only
	STATUS current
	DESCRIPTION "Score: Dump backlog"

	::={insightsScoreDumpBacklog 1}

insightsScoreDumpBacklogMax	OBJECT-TYPE
	SYNTAX	 CounterBasedGauge64
	MAX-ACCESS read-only
	STATUS current
	DESCRIPTION "Score: Dump backlog"

	::={insightsScoreDumpBacklog 3}

insightsScoreDumpBacklogLevelTable OBJECT-TYPE
	SYNTAX      SEQUENCE OF InsightsScoreDumpBacklogLevelEntry
	MAX-ACCESS  not-accessible
	STATUS      current
	DESCRIPTION
	"Table for insightsScoreDumpBacklog"
	::={insightsScoreDumpBacklog 4}

insightsScoreDumpBacklogLevelEntry OBJECT-TYPE
	SYNTAX      InsightsScoreDumpBacklogLevelEntry
	MAX-ACCESS  not-accessible
	STATUS      current
	DESCRIPTION
	"Table entry for insightsScoreDumpBacklog"
	INDEX { insightsScoreDumpBacklogLevelName }
	::={insightsScoreDumpBacklogLevelTable 1}

InsightsScoreDumpBacklogLevelEntry ::=
	SEQUENCE {
		insightsScoreDumpBacklogLevelName	DisplayString,
		insightsScoreDumpBacklogLevelVal	CounterBasedGauge64,
		insightsScoreDumpBacklogLevelMax	CounterBasedGauge64
	}

insightsScoreDumpBacklogLevelName OBJECT-TYPE
	SYNTAX      DisplayString
	MAX-ACCESS  not-accessible
	STATUS      current
	DESCRIPTION
	"Table entry display string for insightsScoreDumpBacklog"
	::={insightsScoreDumpBacklogLevelEntry 1}

insightsScoreDumpBacklogLevelVal OBJECT-TYPE
	SYNTAX	 CounterBasedGauge64
	MAX-ACCESS  read-only
	STATUS      current
	DESCRIPTION
	"Table entry attribute for insightsScoreDumpBacklog"
	::={insightsScoreDumpBacklogLevelEntry 2}

insightsScoreDumpBacklogLevelMax OBJECT-TYPE
	SYNTAX	 CounterBasedGauge64
	MAX-ACCESS  read-only
	STATUS      current
	DESCRIPTION
	"Table entry attribute for insightsScoreDumpBacklog"
	::={insightsScoreDumpBacklogLevelEntry 4}


insightsTrafficRowSkippedEmptySub	OBJECT IDENTIFIER ::={insights 68}

insightsTrafficRowSkippedEmptySubVal	OBJECT-TYPE
	SYNTAX	 Counter64
	MAX-ACCESS read-only
	STATUS current
	DESCRIPTION "Traffic: Rows Skipped, Empty Subscriber"

	::={insightsTrafficRowSkippedEmptySub 1}

insightsTrafficRowSkippedEmptySubMom	OBJECT-TYPE
	SYNTAX	 CounterBasedGauge64
	MAX-ACCESS read-only
	STATUS current
	DESCRIPTION "Traffic: Rows Skipped, Empty Subscriber"

	::={insightsTrafficRowSkippedEmptySub 2}

insightsTrafficRowSkippedEmptySubMax	OBJECT-TYPE
	SYNTAX	 CounterBasedGauge64
	MAX-ACCESS read-only
	STATUS current
	DESCRIPTION "Traffic: Rows Skipped, Empty Subscriber"

	::={insightsTrafficRowSkippedEmptySub 3}

insightsTrafficRowSkippedEmptySubLevelTable OBJECT-TYPE
	SYNTAX      SEQUENCE OF InsightsTrafficRowSkippedEmptySubLevelEntry
	MAX-ACCESS  not-accessible
	STATUS      current
	DESCRIPTION
	"Table for insightsTrafficRowSkippedEmptySub"
	::={insightsTrafficRowSkippedEmptySub 4}

insightsTrafficRowSkippedEmptySubLevelEntry OBJECT-TYPE
	SYNTAX      InsightsTrafficRowSkippedEmptySubLevelEntry
	MAX-ACCESS  not-accessible
	STATUS      current
	DESCRIPTION
	"Table entry for insightsTrafficRowSkippedEmptySub"
	INDEX { insightsTrafficRowSkippedEmptySubLevelName }
	::={insightsTrafficRowSkippedEmptySubLevelTable 1}

InsightsTrafficRowSkippedEmptySubLevelEntry ::=
	SEQUENCE {
		insightsTrafficRowSkippedEmptySubLevelName	DisplayString,
		insightsTrafficRowSkippedEmptySubLevelVal	Counter64,
		insightsTrafficRowSkippedEmptySubLevelMom	CounterBasedGauge64,
		insightsTrafficRowSkippedEmptySubLevelMax	CounterBasedGauge64
	}

insightsTrafficRowSkippedEmptySubLevelName OBJECT-TYPE
	SYNTAX      DisplayString
	MAX-ACCESS  not-accessible
	STATUS      current
	DESCRIPTION
	"Table entry display string for insightsTrafficRowSkippedEmptySub"
	::={insightsTrafficRowSkippedEmptySubLevelEntry 1}

insightsTrafficRowSkippedEmptySubLevelVal OBJECT-TYPE
	SYNTAX	 Counter64
	MAX-ACCESS  read-only
	STATUS      current
	DESCRIPTION
	"Table entry attribute for insightsTrafficRowSkippedEmptySub"
	::={insightsTrafficRowSkippedEmptySubLevelEntry 2}

insightsTrafficRowSkippedEmptySubLevelMom OBJECT-TYPE
	SYNTAX	 CounterBasedGauge64
	MAX-ACCESS  read-only
	STATUS      current
	DESCRIPTION
	"Table entry attribute for insightsTrafficRowSkippedEmptySub"
	::={insightsTrafficRowSkippedEmptySubLevelEntry 3}

insightsTrafficRowSkippedEmptySubLevelMax OBJECT-TYPE
	SYNTAX	 CounterBasedGauge64
	MAX-ACCESS  read-only
	STATUS      current
	DESCRIPTION
	"Table entry attribute for insightsTrafficRowSkippedEmptySub"
	::={insightsTrafficRowSkippedEmptySubLevelEntry 4}


insightsScoreRowSkippedEmptySub	OBJECT IDENTIFIER ::={insights 69}

insightsScoreRowSkippedEmptySubVal	OBJECT-TYPE
	SYNTAX	 Counter64
	MAX-ACCESS read-only
	STATUS current
	DESCRIPTION "Score: Rows Skipped, Empty Subscriber"

	::={insightsScoreRowSkippedEmptySub 1}

insightsScoreRowSkippedEmptySubMom	OBJECT-TYPE
	SYNTAX	 CounterBasedGauge64
	MAX-ACCESS read-only
	STATUS current
	DESCRIPTION "Score: Rows Skipped, Empty Subscriber"

	::={insightsScoreRowSkippedEmptySub 2}

insightsScoreRowSkippedEmptySubMax	OBJECT-TYPE
	SYNTAX	 CounterBasedGauge64
	MAX-ACCESS read-only
	STATUS current
	DESCRIPTION "Score: Rows Skipped, Empty Subscriber"

	::={insightsScoreRowSkippedEmptySub 3}

insightsScoreRowSkippedEmptySubLevelTable OBJECT-TYPE
	SYNTAX      SEQUENCE OF InsightsScoreRowSkippedEmptySubLevelEntry
	MAX-ACCESS  not-accessible
	STATUS      current
	DESCRIPTION
	"Table for insightsScoreRowSkippedEmptySub"
	::={insightsScoreRowSkippedEmptySub 4}

insightsScoreRowSkippedEmptySubLevelEntry OBJECT-TYPE
	SYNTAX      InsightsScoreRowSkippedEmptySubLevelEntry
	MAX-ACCESS  not-accessible
	STATUS      current
	DESCRIPTION
	"Table entry for insightsScoreRowSkippedEmptySub"
	INDEX { insightsScoreRowSkippedEmptySubLevelName }
	::={insightsScoreRowSkippedEmptySubLevelTable 1}

InsightsScoreRowSkippedEmptySubLevelEntry ::=
	SEQUENCE {
		insightsScoreRowSkippedEmptySubLevelName	DisplayString,
		insightsScoreRowSkippedEmptySubLevelVal	Counter64,
		insightsScoreRowSkippedEmptySubLevelMom	CounterBasedGauge64,
		insightsScoreRowSkippedEmptySubLevelMax	CounterBasedGauge64
	}

insightsScoreRowSkippedEmptySubLevelName OBJECT-TYPE
	SYNTAX      DisplayString
	MAX-ACCESS  not-accessible
	STATUS      current
	DESCRIPTION
	"Table entry display string for insightsScoreRowSkippedEmptySub"
	::={insightsScoreRowSkippedEmptySubLevelEntry 1}

insightsScoreRowSkippedEmptySubLevelVal OBJECT-TYPE
	SYNTAX	 Counter64
	MAX-ACCESS  read-only
	STATUS      current
	DESCRIPTION
	"Table entry attribute for insightsScoreRowSkippedEmptySub"
	::={insightsScoreRowSkippedEmptySubLevelEntry 2}

insightsScoreRowSkippedEmptySubLevelMom OBJECT-TYPE
	SYNTAX	 CounterBasedGauge64
	MAX-ACCESS  read-only
	STATUS      current
	DESCRIPTION
	"Table entry attribute for insightsScoreRowSkippedEmptySub"
	::={insightsScoreRowSkippedEmptySubLevelEntry 3}

insightsScoreRowSkippedEmptySubLevelMax OBJECT-TYPE
	SYNTAX	 CounterBasedGauge64
	MAX-ACCESS  read-only
	STATUS      current
	DESCRIPTION
	"Table entry attribute for insightsScoreRowSkippedEmptySub"
	::={insightsScoreRowSkippedEmptySubLevelEntry 4}


insightsTrafficCurrentBatchSpilledToDisk	OBJECT IDENTIFIER ::={insights 70}

insightsTrafficCurrentBatchSpilledToDiskVal	OBJECT-TYPE
	SYNTAX	 CounterBasedGauge64
	MAX-ACCESS read-only
	STATUS current
	DESCRIPTION "Traffic: Current batch spilled to disk"

	::={insightsTrafficCurrentBatchSpilledToDisk 1}

insightsTrafficCurrentBatchSpilledToDiskMax	OBJECT-TYPE
	SYNTAX	 CounterBasedGauge64
	MAX-ACCESS read-only
	STATUS current
	DESCRIPTION "Traffic: Current batch spilled to disk"

	::={insightsTrafficCurrentBatchSpilledToDisk 3}

insightsTrafficCurrentBatchSpilledToDiskLevelTable OBJECT-TYPE
	SYNTAX      SEQUENCE OF InsightsTrafficCurrentBatchSpilledToDiskLevelEntry
	MAX-ACCESS  not-accessible
	STATUS      current
	DESCRIPTION
	"Table for insightsTrafficCurrentBatchSpilledToDisk"
	::={insightsTrafficCurrentBatchSpilledToDisk 4}

insightsTrafficCurrentBatchSpilledToDiskLevelEntry OBJECT-TYPE
	SYNTAX      InsightsTrafficCurrentBatchSpilledToDiskLevelEntry
	MAX-ACCESS  not-accessible
	STATUS      current
	DESCRIPTION
	"Table entry for insightsTrafficCurrentBatchSpilledToDisk"
	INDEX { insightsTrafficCurrentBatchSpilledToDiskLevelName }
	::={insightsTrafficCurrentBatchSpilledToDiskLevelTable 1}

InsightsTrafficCurrentBatchSpilledToDiskLevelEntry ::=
	SEQUENCE {
		insightsTrafficCurrentBatchSpilledToDiskLevelName	DisplayString,
		insightsTrafficCurrentBatchSpilledToDiskLevelVal	CounterBasedGauge64,
		insightsTrafficCurrentBatchSpilledToDiskLevelMax	CounterBasedGauge64
	}

insightsTrafficCurrentBatchSpilledToDiskLevelName OBJECT-TYPE
	SYNTAX      DisplayString
	MAX-ACCESS  not-accessible
	STATUS      current
	DESCRIPTION
	"Table entry display string for insightsTrafficCurrentBatchSpilledToDisk"
	::={insightsTrafficCurrentBatchSpilledToDiskLevelEntry 1}

insightsTrafficCurrentBatchSpilledToDiskLevelVal OBJECT-TYPE
	SYNTAX	 CounterBasedGauge64
	MAX-ACCESS  read-only
	STATUS      current
	DESCRIPTION
	"Table entry attribute for insightsTrafficCurrentBatchSpilledToDisk"
	::={insightsTrafficCurrentBatchSpilledToDiskLevelEntry 2}

insightsTrafficCurrentBatchSpilledToDiskLevelMax OBJECT-TYPE
	SYNTAX	 CounterBasedGauge64
	MAX-ACCESS  read-only
	STATUS      current
	DESCRIPTION
	"Table entry attribute for insightsTrafficCurrentBatchSpilledToDisk"
	::={insightsTrafficCurrentBatchSpilledToDiskLevelEntry 4}


insightsScoreCurrentBatchSpilledToDisk	OBJECT IDENTIFIER ::={insights 71}

insightsScoreCurrentBatchSpilledToDiskVal	OBJECT-TYPE
	SYNTAX	 CounterBasedGauge64
	MAX-ACCESS read-only
	STATUS current
	DESCRIPTION "Score: Current batch spilled to disk"

	::={insightsScoreCurrentBatchSpilledToDisk 1}

insightsScoreCurrentBatchSpilledToDiskMax	OBJECT-TYPE
	SYNTAX	 CounterBasedGauge64
	MAX-ACCESS read-only
	STATUS current
	DESCRIPTION "Score: Current batch spilled to disk"

	::={insightsScoreCurrentBatchSpilledToDisk 3}

insightsScoreCurrentBatchSpilledToDiskLevelTable OBJECT-TYPE
	SYNTAX      SEQUENCE OF InsightsScoreCurrentBatchSpilledToDiskLevelEntry
	MAX-ACCESS  not-accessible
	STATUS      current
	DESCRIPTION
	"Table for insightsScoreCurrentBatchSpilledToDisk"
	::={insightsScoreCurrentBatchSpilledToDisk 4}

insightsScoreCurrentBatchSpilledToDiskLevelEntry OBJECT-TYPE
	SYNTAX      InsightsScoreCurrentBatchSpilledToDiskLevelEntry
	MAX-ACCESS  not-accessible
	STATUS      current
	DESCRIPTION
	"Table entry for insightsScoreCurrentBatchSpilledToDisk"
	INDEX { insightsScoreCurrentBatchSpilledToDiskLevelName }
	::={insightsScoreCurrentBatchSpilledToDiskLevelTable 1}

InsightsScoreCurrentBatchSpilledToDiskLevelEntry ::=
	SEQUENCE {
		insightsScoreCurrentBatchSpilledToDiskLevelName	DisplayString,
		insightsScoreCurrentBatchSpilledToDiskLevelVal	CounterBasedGauge64,
		insightsScoreCurrentBatchSpilledToDiskLevelMax	CounterBasedGauge64
	}

insightsScoreCurrentBatchSpilledToDiskLevelName OBJECT-TYPE
	SYNTAX      DisplayString
	MAX-ACCESS  not-accessible
	STATUS      current
	DESCRIPTION
	"Table entry display string for insightsScoreCurrentBatchSpilledToDisk"
	::={insightsScoreCurrentBatchSpilledToDiskLevelEntry 1}

insightsScoreCurrentBatchSpilledToDiskLevelVal OBJECT-TYPE
	SYNTAX	 CounterBasedGauge64
	MAX-ACCESS  read-only
	STATUS      current
	DESCRIPTION
	"Table entry attribute for insightsScoreCurrentBatchSpilledToDisk"
	::={insightsScoreCurrentBatchSpilledToDiskLevelEntry 2}

insightsScoreCurrentBatchSpilledToDiskLevelMax OBJECT-TYPE
	SYNTAX	 CounterBasedGauge64
	MAX-ACCESS  read-only
	STATUS      current
	DESCRIPTION
	"Table entry attribute for insightsScoreCurrentBatchSpilledToDisk"
	::={insightsScoreCurrentBatchSpilledToDiskLevelEntry 4}


insightsTrafficAccumulatorStatsAllocated	OBJECT IDENTIFIER ::={insights 72}

insightsTrafficAccumulatorStatsAllocatedVal	OBJECT-TYPE
	SYNTAX	 CounterBasedGauge64
	MAX-ACCESS read-only
	STATUS current
	DESCRIPTION "Traffic: Accumulator row stats allocated"

	::={insightsTrafficAccumulatorStatsAllocated 1}

insightsTrafficAccumulatorStatsAllocatedMax	OBJECT-TYPE
	SYNTAX	 CounterBasedGauge64
	MAX-ACCESS read-only
	STATUS current
	DESCRIPTION "Traffic: Accumulator row stats allocated"

	::={insightsTrafficAccumulatorStatsAllocated 3}

insightsTrafficAccumulatorStatsAllocatedLevelTable OBJECT-TYPE
	SYNTAX      SEQUENCE OF InsightsTrafficAccumulatorStatsAllocatedLevelEntry
	MAX-ACCESS  not-accessible
	STATUS      current
	DESCRIPTION
	"Table for insightsTrafficAccumulatorStatsAllocated"
	::={insightsTrafficAccumulatorStatsAllocated 4}

insightsTrafficAccumulatorStatsAllocatedLevelEntry OBJECT-TYPE
	SYNTAX      InsightsTrafficAccumulatorStatsAllocatedLevelEntry
	MAX-ACCESS  not-accessible
	STATUS      current
	DESCRIPTION
	"Table entry for insightsTrafficAccumulatorStatsAllocated"
	INDEX { insightsTrafficAccumulatorStatsAllocatedLevelName }
	::={insightsTrafficAccumulatorStatsAllocatedLevelTable 1}

InsightsTrafficAccumulatorStatsAllocatedLevelEntry ::=
	SEQUENCE {
		insightsTrafficAccumulatorStatsAllocatedLevelName	DisplayString,
		insightsTrafficAccumulatorStatsAllocatedLevelVal	CounterBasedGauge64,
		insightsTrafficAccumulatorStatsAllocatedLevelMax	CounterBasedGauge64
	}

insightsTrafficAccumulatorStatsAllocatedLevelName OBJECT-TYPE
	SYNTAX      DisplayString
	MAX-ACCESS  not-accessible
	STATUS      current
	DESCRIPTION
	"Table entry display string for insightsTrafficAccumulatorStatsAllocated"
	::={insightsTrafficAccumulatorStatsAllocatedLevelEntry 1}

insightsTrafficAccumulatorStatsAllocatedLevelVal OBJECT-TYPE
	SYNTAX	 CounterBasedGauge64
	MAX-ACCESS  read-only
	STATUS      current
	DESCRIPTION
	"Table entry attribute for insightsTrafficAccumulatorStatsAllocated"
	::={insightsTrafficAccumulatorStatsAllocatedLevelEntry 2}

insightsTrafficAccumulatorStatsAllocatedLevelMax OBJECT-TYPE
	SYNTAX	 CounterBasedGauge64
	MAX-ACCESS  read-only
	STATUS      current
	DESCRIPTION
	"Table entry attribute for insightsTrafficAccumulatorStatsAllocated"
	::={insightsTrafficAccumulatorStatsAllocatedLevelEntry 4}


insightsTrafficAccumulatorStatsUsed	OBJECT IDENTIFIER ::={insights 73}

insightsTrafficAccumulatorStatsUsedVal	OBJECT-TYPE
	SYNTAX	 CounterBasedGauge64
	MAX-ACCESS read-only
	STATUS current
	DESCRIPTION "Traffic: Accumulator row stats used"

	::={insightsTrafficAccumulatorStatsUsed 1}

insightsTrafficAccumulatorStatsUsedMax	OBJECT-TYPE
	SYNTAX	 CounterBasedGauge64
	MAX-ACCESS read-only
	STATUS current
	DESCRIPTION "Traffic: Accumulator row stats used"

	::={insightsTrafficAccumulatorStatsUsed 3}

insightsTrafficAccumulatorStatsUsedLevelTable OBJECT-TYPE
	SYNTAX      SEQUENCE OF InsightsTrafficAccumulatorStatsUsedLevelEntry
	MAX-ACCESS  not-accessible
	STATUS      current
	DESCRIPTION
	"Table for insightsTrafficAccumulatorStatsUsed"
	::={insightsTrafficAccumulatorStatsUsed 4}

insightsTrafficAccumulatorStatsUsedLevelEntry OBJECT-TYPE
	SYNTAX      InsightsTrafficAccumulatorStatsUsedLevelEntry
	MAX-ACCESS  not-accessible
	STATUS      current
	DESCRIPTION
	"Table entry for insightsTrafficAccumulatorStatsUsed"
	INDEX { insightsTrafficAccumulatorStatsUsedLevelName }
	::={insightsTrafficAccumulatorStatsUsedLevelTable 1}

InsightsTrafficAccumulatorStatsUsedLevelEntry ::=
	SEQUENCE {
		insightsTrafficAccumulatorStatsUsedLevelName	DisplayString,
		insightsTrafficAccumulatorStatsUsedLevelVal	CounterBasedGauge64,
		insightsTrafficAccumulatorStatsUsedLevelMax	CounterBasedGauge64
	}

insightsTrafficAccumulatorStatsUsedLevelName OBJECT-TYPE
	SYNTAX      DisplayString
	MAX-ACCESS  not-accessible
	STATUS      current
	DESCRIPTION
	"Table entry display string for insightsTrafficAccumulatorStatsUsed"
	::={insightsTrafficAccumulatorStatsUsedLevelEntry 1}

insightsTrafficAccumulatorStatsUsedLevelVal OBJECT-TYPE
	SYNTAX	 CounterBasedGauge64
	MAX-ACCESS  read-only
	STATUS      current
	DESCRIPTION
	"Table entry attribute for insightsTrafficAccumulatorStatsUsed"
	::={insightsTrafficAccumulatorStatsUsedLevelEntry 2}

insightsTrafficAccumulatorStatsUsedLevelMax OBJECT-TYPE
	SYNTAX	 CounterBasedGauge64
	MAX-ACCESS  read-only
	STATUS      current
	DESCRIPTION
	"Table entry attribute for insightsTrafficAccumulatorStatsUsed"
	::={insightsTrafficAccumulatorStatsUsedLevelEntry 4}


insightsTrafficAccumulatorStatsFree	OBJECT IDENTIFIER ::={insights 74}

insightsTrafficAccumulatorStatsFreeVal	OBJECT-TYPE
	SYNTAX	 CounterBasedGauge64
	MAX-ACCESS read-only
	STATUS current
	DESCRIPTION "Traffic: Accumulator row stats free"

	::={insightsTrafficAccumulatorStatsFree 1}

insightsTrafficAccumulatorStatsFreeMax	OBJECT-TYPE
	SYNTAX	 CounterBasedGauge64
	MAX-ACCESS read-only
	STATUS current
	DESCRIPTION "Traffic: Accumulator row stats free"

	::={insightsTrafficAccumulatorStatsFree 3}

insightsTrafficAccumulatorStatsFreeLevelTable OBJECT-TYPE
	SYNTAX      SEQUENCE OF InsightsTrafficAccumulatorStatsFreeLevelEntry
	MAX-ACCESS  not-accessible
	STATUS      current
	DESCRIPTION
	"Table for insightsTrafficAccumulatorStatsFree"
	::={insightsTrafficAccumulatorStatsFree 4}

insightsTrafficAccumulatorStatsFreeLevelEntry OBJECT-TYPE
	SYNTAX      InsightsTrafficAccumulatorStatsFreeLevelEntry
	MAX-ACCESS  not-accessible
	STATUS      current
	DESCRIPTION
	"Table entry for insightsTrafficAccumulatorStatsFree"
	INDEX { insightsTrafficAccumulatorStatsFreeLevelName }
	::={insightsTrafficAccumulatorStatsFreeLevelTable 1}

InsightsTrafficAccumulatorStatsFreeLevelEntry ::=
	SEQUENCE {
		insightsTrafficAccumulatorStatsFreeLevelName	DisplayString,
		insightsTrafficAccumulatorStatsFreeLevelVal	CounterBasedGauge64,
		insightsTrafficAccumulatorStatsFreeLevelMax	CounterBasedGauge64
	}

insightsTrafficAccumulatorStatsFreeLevelName OBJECT-TYPE
	SYNTAX      DisplayString
	MAX-ACCESS  not-accessible
	STATUS      current
	DESCRIPTION
	"Table entry display string for insightsTrafficAccumulatorStatsFree"
	::={insightsTrafficAccumulatorStatsFreeLevelEntry 1}

insightsTrafficAccumulatorStatsFreeLevelVal OBJECT-TYPE
	SYNTAX	 CounterBasedGauge64
	MAX-ACCESS  read-only
	STATUS      current
	DESCRIPTION
	"Table entry attribute for insightsTrafficAccumulatorStatsFree"
	::={insightsTrafficAccumulatorStatsFreeLevelEntry 2}

insightsTrafficAccumulatorStatsFreeLevelMax OBJECT-TYPE
	SYNTAX	 CounterBasedGauge64
	MAX-ACCESS  read-only
	STATUS      current
	DESCRIPTION
	"Table entry attribute for insightsTrafficAccumulatorStatsFree"
	::={insightsTrafficAccumulatorStatsFreeLevelEntry 4}


insightsTrafficSpilledBatchesOnDisk	OBJECT IDENTIFIER ::={insights 75}

insightsTrafficSpilledBatchesOnDiskVal	OBJECT-TYPE
	SYNTAX	 CounterBasedGauge64
	MAX-ACCESS read-only
	STATUS current
	DESCRIPTION "Traffic: Spilled batches on disk"

	::={insightsTrafficSpilledBatchesOnDisk 1}

insightsTrafficSpilledBatchesOnDiskMax	OBJECT-TYPE
	SYNTAX	 CounterBasedGauge64
	MAX-ACCESS read-only
	STATUS current
	DESCRIPTION "Traffic: Spilled batches on disk"

	::={insightsTrafficSpilledBatchesOnDisk 3}

insightsTrafficSpilledBatchesOnDiskLevelTable OBJECT-TYPE
	SYNTAX      SEQUENCE OF InsightsTrafficSpilledBatchesOnDiskLevelEntry
	MAX-ACCESS  not-accessible
	STATUS      current
	DESCRIPTION
	"Table for insightsTrafficSpilledBatchesOnDisk"
	::={insightsTrafficSpilledBatchesOnDisk 4}

insightsTrafficSpilledBatchesOnDiskLevelEntry OBJECT-TYPE
	SYNTAX      InsightsTrafficSpilledBatchesOnDiskLevelEntry
	MAX-ACCESS  not-accessible
	STATUS      current
	DESCRIPTION
	"Table entry for insightsTrafficSpilledBatchesOnDisk"
	INDEX { insightsTrafficSpilledBatchesOnDiskLevelName }
	::={insightsTrafficSpilledBatchesOnDiskLevelTable 1}

InsightsTrafficSpilledBatchesOnDiskLevelEntry ::=
	SEQUENCE {
		insightsTrafficSpilledBatchesOnDiskLevelName	DisplayString,
		insightsTrafficSpilledBatchesOnDiskLevelVal	CounterBasedGauge64,
		insightsTrafficSpilledBatchesOnDiskLevelMax	CounterBasedGauge64
	}

insightsTrafficSpilledBatchesOnDiskLevelName OBJECT-TYPE
	SYNTAX      DisplayString
	MAX-ACCESS  not-accessible
	STATUS      current
	DESCRIPTION
	"Table entry display string for insightsTrafficSpilledBatchesOnDisk"
	::={insightsTrafficSpilledBatchesOnDiskLevelEntry 1}

insightsTrafficSpilledBatchesOnDiskLevelVal OBJECT-TYPE
	SYNTAX	 CounterBasedGauge64
	MAX-ACCESS  read-only
	STATUS      current
	DESCRIPTION
	"Table entry attribute for insightsTrafficSpilledBatchesOnDisk"
	::={insightsTrafficSpilledBatchesOnDiskLevelEntry 2}

insightsTrafficSpilledBatchesOnDiskLevelMax OBJECT-TYPE
	SYNTAX	 CounterBasedGauge64
	MAX-ACCESS  read-only
	STATUS      current
	DESCRIPTION
	"Table entry attribute for insightsTrafficSpilledBatchesOnDisk"
	::={insightsTrafficSpilledBatchesOnDiskLevelEntry 4}


insightsScoreSpilledBatchesOnDisk	OBJECT IDENTIFIER ::={insights 76}

insightsScoreSpilledBatchesOnDiskVal	OBJECT-TYPE
	SYNTAX	 CounterBasedGauge64
	MAX-ACCESS read-only
	STATUS current
	DESCRIPTION "Score: Spilled batches on disk"

	::={insightsScoreSpilledBatchesOnDisk 1}

insightsScoreSpilledBatchesOnDiskMax	OBJECT-TYPE
	SYNTAX	 CounterBasedGauge64
	MAX-ACCESS read-only
	STATUS current
	DESCRIPTION "Score: Spilled batches on disk"

	::={insightsScoreSpilledBatchesOnDisk 3}

insightsScoreSpilledBatchesOnDiskLevelTable OBJECT-TYPE
	SYNTAX      SEQUENCE OF InsightsScoreSpilledBatchesOnDiskLevelEntry
	MAX-ACCESS  not-accessible
	STATUS      current
	DESCRIPTION
	"Table for insightsScoreSpilledBatchesOnDisk"
	::={insightsScoreSpilledBatchesOnDisk 4}

insightsScoreSpilledBatchesOnDiskLevelEntry OBJECT-TYPE
	SYNTAX      InsightsScoreSpilledBatchesOnDiskLevelEntry
	MAX-ACCESS  not-accessible
	STATUS      current
	DESCRIPTION
	"Table entry for insightsScoreSpilledBatchesOnDisk"
	INDEX { insightsScoreSpilledBatchesOnDiskLevelName }
	::={insightsScoreSpilledBatchesOnDiskLevelTable 1}

InsightsScoreSpilledBatchesOnDiskLevelEntry ::=
	SEQUENCE {
		insightsScoreSpilledBatchesOnDiskLevelName	DisplayString,
		insightsScoreSpilledBatchesOnDiskLevelVal	CounterBasedGauge64,
		insightsScoreSpilledBatchesOnDiskLevelMax	CounterBasedGauge64
	}

insightsScoreSpilledBatchesOnDiskLevelName OBJECT-TYPE
	SYNTAX      DisplayString
	MAX-ACCESS  not-accessible
	STATUS      current
	DESCRIPTION
	"Table entry display string for insightsScoreSpilledBatchesOnDisk"
	::={insightsScoreSpilledBatchesOnDiskLevelEntry 1}

insightsScoreSpilledBatchesOnDiskLevelVal OBJECT-TYPE
	SYNTAX	 CounterBasedGauge64
	MAX-ACCESS  read-only
	STATUS      current
	DESCRIPTION
	"Table entry attribute for insightsScoreSpilledBatchesOnDisk"
	::={insightsScoreSpilledBatchesOnDiskLevelEntry 2}

insightsScoreSpilledBatchesOnDiskLevelMax OBJECT-TYPE
	SYNTAX	 CounterBasedGauge64
	MAX-ACCESS  read-only
	STATUS      current
	DESCRIPTION
	"Table entry attribute for insightsScoreSpilledBatchesOnDisk"
	::={insightsScoreSpilledBatchesOnDiskLevelEntry 4}


insightsScoreAccumulatorKeysAllocated	OBJECT IDENTIFIER ::={insights 77}

insightsScoreAccumulatorKeysAllocatedVal	OBJECT-TYPE
	SYNTAX	 CounterBasedGauge64
	MAX-ACCESS read-only
	STATUS current
	DESCRIPTION "Score: Accumulator row keys allocated"

	::={insightsScoreAccumulatorKeysAllocated 1}

insightsScoreAccumulatorKeysAllocatedMax	OBJECT-TYPE
	SYNTAX	 CounterBasedGauge64
	MAX-ACCESS read-only
	STATUS current
	DESCRIPTION "Score: Accumulator row keys allocated"

	::={insightsScoreAccumulatorKeysAllocated 3}

insightsScoreAccumulatorKeysAllocatedLevelTable OBJECT-TYPE
	SYNTAX      SEQUENCE OF InsightsScoreAccumulatorKeysAllocatedLevelEntry
	MAX-ACCESS  not-accessible
	STATUS      current
	DESCRIPTION
	"Table for insightsScoreAccumulatorKeysAllocated"
	::={insightsScoreAccumulatorKeysAllocated 4}

insightsScoreAccumulatorKeysAllocatedLevelEntry OBJECT-TYPE
	SYNTAX      InsightsScoreAccumulatorKeysAllocatedLevelEntry
	MAX-ACCESS  not-accessible
	STATUS      current
	DESCRIPTION
	"Table entry for insightsScoreAccumulatorKeysAllocated"
	INDEX { insightsScoreAccumulatorKeysAllocatedLevelName }
	::={insightsScoreAccumulatorKeysAllocatedLevelTable 1}

InsightsScoreAccumulatorKeysAllocatedLevelEntry ::=
	SEQUENCE {
		insightsScoreAccumulatorKeysAllocatedLevelName	DisplayString,
		insightsScoreAccumulatorKeysAllocatedLevelVal	CounterBasedGauge64,
		insightsScoreAccumulatorKeysAllocatedLevelMax	CounterBasedGauge64
	}

insightsScoreAccumulatorKeysAllocatedLevelName OBJECT-TYPE
	SYNTAX      DisplayString
	MAX-ACCESS  not-accessible
	STATUS      current
	DESCRIPTION
	"Table entry display string for insightsScoreAccumulatorKeysAllocated"
	::={insightsScoreAccumulatorKeysAllocatedLevelEntry 1}

insightsScoreAccumulatorKeysAllocatedLevelVal OBJECT-TYPE
	SYNTAX	 CounterBasedGauge64
	MAX-ACCESS  read-only
	STATUS      current
	DESCRIPTION
	"Table entry attribute for insightsScoreAccumulatorKeysAllocated"
	::={insightsScoreAccumulatorKeysAllocatedLevelEntry 2}

insightsScoreAccumulatorKeysAllocatedLevelMax OBJECT-TYPE
	SYNTAX	 CounterBasedGauge64
	MAX-ACCESS  read-only
	STATUS      current
	DESCRIPTION
	"Table entry attribute for insightsScoreAccumulatorKeysAllocated"
	::={insightsScoreAccumulatorKeysAllocatedLevelEntry 4}


insightsScoreAccumulatorKeysUsed	OBJECT IDENTIFIER ::={insights 78}

insightsScoreAccumulatorKeysUsedVal	OBJECT-TYPE
	SYNTAX	 CounterBasedGauge64
	MAX-ACCESS read-only
	STATUS current
	DESCRIPTION "Score: Accumulator row keys used"

	::={insightsScoreAccumulatorKeysUsed 1}

insightsScoreAccumulatorKeysUsedMax	OBJECT-TYPE
	SYNTAX	 CounterBasedGauge64
	MAX-ACCESS read-only
	STATUS current
	DESCRIPTION "Score: Accumulator row keys used"

	::={insightsScoreAccumulatorKeysUsed 3}

insightsScoreAccumulatorKeysUsedLevelTable OBJECT-TYPE
	SYNTAX      SEQUENCE OF InsightsScoreAccumulatorKeysUsedLevelEntry
	MAX-ACCESS  not-accessible
	STATUS      current
	DESCRIPTION
	"Table for insightsScoreAccumulatorKeysUsed"
	::={insightsScoreAccumulatorKeysUsed 4}

insightsScoreAccumulatorKeysUsedLevelEntry OBJECT-TYPE
	SYNTAX      InsightsScoreAccumulatorKeysUsedLevelEntry
	MAX-ACCESS  not-accessible
	STATUS      current
	DESCRIPTION
	"Table entry for insightsScoreAccumulatorKeysUsed"
	INDEX { insightsScoreAccumulatorKeysUsedLevelName }
	::={insightsScoreAccumulatorKeysUsedLevelTable 1}

InsightsScoreAccumulatorKeysUsedLevelEntry ::=
	SEQUENCE {
		insightsScoreAccumulatorKeysUsedLevelName	DisplayString,
		insightsScoreAccumulatorKeysUsedLevelVal	CounterBasedGauge64,
		insightsScoreAccumulatorKeysUsedLevelMax	CounterBasedGauge64
	}

insightsScoreAccumulatorKeysUsedLevelName OBJECT-TYPE
	SYNTAX      DisplayString
	MAX-ACCESS  not-accessible
	STATUS      current
	DESCRIPTION
	"Table entry display string for insightsScoreAccumulatorKeysUsed"
	::={insightsScoreAccumulatorKeysUsedLevelEntry 1}

insightsScoreAccumulatorKeysUsedLevelVal OBJECT-TYPE
	SYNTAX	 CounterBasedGauge64
	MAX-ACCESS  read-only
	STATUS      current
	DESCRIPTION
	"Table entry attribute for insightsScoreAccumulatorKeysUsed"
	::={insightsScoreAccumulatorKeysUsedLevelEntry 2}

insightsScoreAccumulatorKeysUsedLevelMax OBJECT-TYPE
	SYNTAX	 CounterBasedGauge64
	MAX-ACCESS  read-only
	STATUS      current
	DESCRIPTION
	"Table entry attribute for insightsScoreAccumulatorKeysUsed"
	::={insightsScoreAccumulatorKeysUsedLevelEntry 4}


insightsScoreAccumulatorKeysFree	OBJECT IDENTIFIER ::={insights 79}

insightsScoreAccumulatorKeysFreeVal	OBJECT-TYPE
	SYNTAX	 CounterBasedGauge64
	MAX-ACCESS read-only
	STATUS current
	DESCRIPTION "Score: Accumulator row keys free"

	::={insightsScoreAccumulatorKeysFree 1}

insightsScoreAccumulatorKeysFreeMax	OBJECT-TYPE
	SYNTAX	 CounterBasedGauge64
	MAX-ACCESS read-only
	STATUS current
	DESCRIPTION "Score: Accumulator row keys free"

	::={insightsScoreAccumulatorKeysFree 3}

insightsScoreAccumulatorKeysFreeLevelTable OBJECT-TYPE
	SYNTAX      SEQUENCE OF InsightsScoreAccumulatorKeysFreeLevelEntry
	MAX-ACCESS  not-accessible
	STATUS      current
	DESCRIPTION
	"Table for insightsScoreAccumulatorKeysFree"
	::={insightsScoreAccumulatorKeysFree 4}

insightsScoreAccumulatorKeysFreeLevelEntry OBJECT-TYPE
	SYNTAX      InsightsScoreAccumulatorKeysFreeLevelEntry
	MAX-ACCESS  not-accessible
	STATUS      current
	DESCRIPTION
	"Table entry for insightsScoreAccumulatorKeysFree"
	INDEX { insightsScoreAccumulatorKeysFreeLevelName }
	::={insightsScoreAccumulatorKeysFreeLevelTable 1}

InsightsScoreAccumulatorKeysFreeLevelEntry ::=
	SEQUENCE {
		insightsScoreAccumulatorKeysFreeLevelName	DisplayString,
		insightsScoreAccumulatorKeysFreeLevelVal	CounterBasedGauge64,
		insightsScoreAccumulatorKeysFreeLevelMax	CounterBasedGauge64
	}

insightsScoreAccumulatorKeysFreeLevelName OBJECT-TYPE
	SYNTAX      DisplayString
	MAX-ACCESS  not-accessible
	STATUS      current
	DESCRIPTION
	"Table entry display string for insightsScoreAccumulatorKeysFree"
	::={insightsScoreAccumulatorKeysFreeLevelEntry 1}

insightsScoreAccumulatorKeysFreeLevelVal OBJECT-TYPE
	SYNTAX	 CounterBasedGauge64
	MAX-ACCESS  read-only
	STATUS      current
	DESCRIPTION
	"Table entry attribute for insightsScoreAccumulatorKeysFree"
	::={insightsScoreAccumulatorKeysFreeLevelEntry 2}

insightsScoreAccumulatorKeysFreeLevelMax OBJECT-TYPE
	SYNTAX	 CounterBasedGauge64
	MAX-ACCESS  read-only
	STATUS      current
	DESCRIPTION
	"Table entry attribute for insightsScoreAccumulatorKeysFree"
	::={insightsScoreAccumulatorKeysFreeLevelEntry 4}


insightsScoreAccumulatorStatsAllocated	OBJECT IDENTIFIER ::={insights 80}

insightsScoreAccumulatorStatsAllocatedVal	OBJECT-TYPE
	SYNTAX	 CounterBasedGauge64
	MAX-ACCESS read-only
	STATUS current
	DESCRIPTION "Score: Accumulator row stats allocated"

	::={insightsScoreAccumulatorStatsAllocated 1}

insightsScoreAccumulatorStatsAllocatedMax	OBJECT-TYPE
	SYNTAX	 CounterBasedGauge64
	MAX-ACCESS read-only
	STATUS current
	DESCRIPTION "Score: Accumulator row stats allocated"

	::={insightsScoreAccumulatorStatsAllocated 3}

insightsScoreAccumulatorStatsAllocatedLevelTable OBJECT-TYPE
	SYNTAX      SEQUENCE OF InsightsScoreAccumulatorStatsAllocatedLevelEntry
	MAX-ACCESS  not-accessible
	STATUS      current
	DESCRIPTION
	"Table for insightsScoreAccumulatorStatsAllocated"
	::={insightsScoreAccumulatorStatsAllocated 4}

insightsScoreAccumulatorStatsAllocatedLevelEntry OBJECT-TYPE
	SYNTAX      InsightsScoreAccumulatorStatsAllocatedLevelEntry
	MAX-ACCESS  not-accessible
	STATUS      current
	DESCRIPTION
	"Table entry for insightsScoreAccumulatorStatsAllocated"
	INDEX { insightsScoreAccumulatorStatsAllocatedLevelName }
	::={insightsScoreAccumulatorStatsAllocatedLevelTable 1}

InsightsScoreAccumulatorStatsAllocatedLevelEntry ::=
	SEQUENCE {
		insightsScoreAccumulatorStatsAllocatedLevelName	DisplayString,
		insightsScoreAccumulatorStatsAllocatedLevelVal	CounterBasedGauge64,
		insightsScoreAccumulatorStatsAllocatedLevelMax	CounterBasedGauge64
	}

insightsScoreAccumulatorStatsAllocatedLevelName OBJECT-TYPE
	SYNTAX      DisplayString
	MAX-ACCESS  not-accessible
	STATUS      current
	DESCRIPTION
	"Table entry display string for insightsScoreAccumulatorStatsAllocated"
	::={insightsScoreAccumulatorStatsAllocatedLevelEntry 1}

insightsScoreAccumulatorStatsAllocatedLevelVal OBJECT-TYPE
	SYNTAX	 CounterBasedGauge64
	MAX-ACCESS  read-only
	STATUS      current
	DESCRIPTION
	"Table entry attribute for insightsScoreAccumulatorStatsAllocated"
	::={insightsScoreAccumulatorStatsAllocatedLevelEntry 2}

insightsScoreAccumulatorStatsAllocatedLevelMax OBJECT-TYPE
	SYNTAX	 CounterBasedGauge64
	MAX-ACCESS  read-only
	STATUS      current
	DESCRIPTION
	"Table entry attribute for insightsScoreAccumulatorStatsAllocated"
	::={insightsScoreAccumulatorStatsAllocatedLevelEntry 4}


insightsScoreAccumulatorStatsUsed	OBJECT IDENTIFIER ::={insights 81}

insightsScoreAccumulatorStatsUsedVal	OBJECT-TYPE
	SYNTAX	 CounterBasedGauge64
	MAX-ACCESS read-only
	STATUS current
	DESCRIPTION "Score: Accumulator row stats used"

	::={insightsScoreAccumulatorStatsUsed 1}

insightsScoreAccumulatorStatsUsedMax	OBJECT-TYPE
	SYNTAX	 CounterBasedGauge64
	MAX-ACCESS read-only
	STATUS current
	DESCRIPTION "Score: Accumulator row stats used"

	::={insightsScoreAccumulatorStatsUsed 3}

insightsScoreAccumulatorStatsUsedLevelTable OBJECT-TYPE
	SYNTAX      SEQUENCE OF InsightsScoreAccumulatorStatsUsedLevelEntry
	MAX-ACCESS  not-accessible
	STATUS      current
	DESCRIPTION
	"Table for insightsScoreAccumulatorStatsUsed"
	::={insightsScoreAccumulatorStatsUsed 4}

insightsScoreAccumulatorStatsUsedLevelEntry OBJECT-TYPE
	SYNTAX      InsightsScoreAccumulatorStatsUsedLevelEntry
	MAX-ACCESS  not-accessible
	STATUS      current
	DESCRIPTION
	"Table entry for insightsScoreAccumulatorStatsUsed"
	INDEX { insightsScoreAccumulatorStatsUsedLevelName }
	::={insightsScoreAccumulatorStatsUsedLevelTable 1}

InsightsScoreAccumulatorStatsUsedLevelEntry ::=
	SEQUENCE {
		insightsScoreAccumulatorStatsUsedLevelName	DisplayString,
		insightsScoreAccumulatorStatsUsedLevelVal	CounterBasedGauge64,
		insightsScoreAccumulatorStatsUsedLevelMax	CounterBasedGauge64
	}

insightsScoreAccumulatorStatsUsedLevelName OBJECT-TYPE
	SYNTAX      DisplayString
	MAX-ACCESS  not-accessible
	STATUS      current
	DESCRIPTION
	"Table entry display string for insightsScoreAccumulatorStatsUsed"
	::={insightsScoreAccumulatorStatsUsedLevelEntry 1}

insightsScoreAccumulatorStatsUsedLevelVal OBJECT-TYPE
	SYNTAX	 CounterBasedGauge64
	MAX-ACCESS  read-only
	STATUS      current
	DESCRIPTION
	"Table entry attribute for insightsScoreAccumulatorStatsUsed"
	::={insightsScoreAccumulatorStatsUsedLevelEntry 2}

insightsScoreAccumulatorStatsUsedLevelMax OBJECT-TYPE
	SYNTAX	 CounterBasedGauge64
	MAX-ACCESS  read-only
	STATUS      current
	DESCRIPTION
	"Table entry attribute for insightsScoreAccumulatorStatsUsed"
	::={insightsScoreAccumulatorStatsUsedLevelEntry 4}


insightsScoreAccumulatorStatsFree	OBJECT IDENTIFIER ::={insights 82}

insightsScoreAccumulatorStatsFreeVal	OBJECT-TYPE
	SYNTAX	 CounterBasedGauge64
	MAX-ACCESS read-only
	STATUS current
	DESCRIPTION "Score: Accumulator row stats free"

	::={insightsScoreAccumulatorStatsFree 1}

insightsScoreAccumulatorStatsFreeMax	OBJECT-TYPE
	SYNTAX	 CounterBasedGauge64
	MAX-ACCESS read-only
	STATUS current
	DESCRIPTION "Score: Accumulator row stats free"

	::={insightsScoreAccumulatorStatsFree 3}

insightsScoreAccumulatorStatsFreeLevelTable OBJECT-TYPE
	SYNTAX      SEQUENCE OF InsightsScoreAccumulatorStatsFreeLevelEntry
	MAX-ACCESS  not-accessible
	STATUS      current
	DESCRIPTION
	"Table for insightsScoreAccumulatorStatsFree"
	::={insightsScoreAccumulatorStatsFree 4}

insightsScoreAccumulatorStatsFreeLevelEntry OBJECT-TYPE
	SYNTAX      InsightsScoreAccumulatorStatsFreeLevelEntry
	MAX-ACCESS  not-accessible
	STATUS      current
	DESCRIPTION
	"Table entry for insightsScoreAccumulatorStatsFree"
	INDEX { insightsScoreAccumulatorStatsFreeLevelName }
	::={insightsScoreAccumulatorStatsFreeLevelTable 1}

InsightsScoreAccumulatorStatsFreeLevelEntry ::=
	SEQUENCE {
		insightsScoreAccumulatorStatsFreeLevelName	DisplayString,
		insightsScoreAccumulatorStatsFreeLevelVal	CounterBasedGauge64,
		insightsScoreAccumulatorStatsFreeLevelMax	CounterBasedGauge64
	}

insightsScoreAccumulatorStatsFreeLevelName OBJECT-TYPE
	SYNTAX      DisplayString
	MAX-ACCESS  not-accessible
	STATUS      current
	DESCRIPTION
	"Table entry display string for insightsScoreAccumulatorStatsFree"
	::={insightsScoreAccumulatorStatsFreeLevelEntry 1}

insightsScoreAccumulatorStatsFreeLevelVal OBJECT-TYPE
	SYNTAX	 CounterBasedGauge64
	MAX-ACCESS  read-only
	STATUS      current
	DESCRIPTION
	"Table entry attribute for insightsScoreAccumulatorStatsFree"
	::={insightsScoreAccumulatorStatsFreeLevelEntry 2}

insightsScoreAccumulatorStatsFreeLevelMax OBJECT-TYPE
	SYNTAX	 CounterBasedGauge64
	MAX-ACCESS  read-only
	STATUS      current
	DESCRIPTION
	"Table entry attribute for insightsScoreAccumulatorStatsFree"
	::={insightsScoreAccumulatorStatsFreeLevelEntry 4}


insightsScoreBytesUnAccountedIn	OBJECT IDENTIFIER ::={insights 83}

insightsScoreBytesUnAccountedInVal	OBJECT-TYPE
	SYNTAX	 Counter64
	MAX-ACCESS read-only
	STATUS current
	DESCRIPTION "Score: Bytes unaccounted in"

	::={insightsScoreBytesUnAccountedIn 1}

insightsScoreBytesUnAccountedInMom	OBJECT-TYPE
	SYNTAX	 CounterBasedGauge64
	MAX-ACCESS read-only
	STATUS current
	DESCRIPTION "Score: Bytes unaccounted in"

	::={insightsScoreBytesUnAccountedIn 2}

insightsScoreBytesUnAccountedInMax	OBJECT-TYPE
	SYNTAX	 CounterBasedGauge64
	MAX-ACCESS read-only
	STATUS current
	DESCRIPTION "Score: Bytes unaccounted in"

	::={insightsScoreBytesUnAccountedIn 3}

insightsScoreBytesUnAccountedInLevelTable OBJECT-TYPE
	SYNTAX      SEQUENCE OF InsightsScoreBytesUnAccountedInLevelEntry
	MAX-ACCESS  not-accessible
	STATUS      current
	DESCRIPTION
	"Table for insightsScoreBytesUnAccountedIn"
	::={insightsScoreBytesUnAccountedIn 4}

insightsScoreBytesUnAccountedInLevelEntry OBJECT-TYPE
	SYNTAX      InsightsScoreBytesUnAccountedInLevelEntry
	MAX-ACCESS  not-accessible
	STATUS      current
	DESCRIPTION
	"Table entry for insightsScoreBytesUnAccountedIn"
	INDEX { insightsScoreBytesUnAccountedInLevelName }
	::={insightsScoreBytesUnAccountedInLevelTable 1}

InsightsScoreBytesUnAccountedInLevelEntry ::=
	SEQUENCE {
		insightsScoreBytesUnAccountedInLevelName	DisplayString,
		insightsScoreBytesUnAccountedInLevelVal	Counter64,
		insightsScoreBytesUnAccountedInLevelMom	CounterBasedGauge64,
		insightsScoreBytesUnAccountedInLevelMax	CounterBasedGauge64
	}

insightsScoreBytesUnAccountedInLevelName OBJECT-TYPE
	SYNTAX      DisplayString
	MAX-ACCESS  not-accessible
	STATUS      current
	DESCRIPTION
	"Table entry display string for insightsScoreBytesUnAccountedIn"
	::={insightsScoreBytesUnAccountedInLevelEntry 1}

insightsScoreBytesUnAccountedInLevelVal OBJECT-TYPE
	SYNTAX	 Counter64
	MAX-ACCESS  read-only
	STATUS      current
	DESCRIPTION
	"Table entry attribute for insightsScoreBytesUnAccountedIn"
	::={insightsScoreBytesUnAccountedInLevelEntry 2}

insightsScoreBytesUnAccountedInLevelMom OBJECT-TYPE
	SYNTAX	 CounterBasedGauge64
	MAX-ACCESS  read-only
	STATUS      current
	DESCRIPTION
	"Table entry attribute for insightsScoreBytesUnAccountedIn"
	::={insightsScoreBytesUnAccountedInLevelEntry 3}

insightsScoreBytesUnAccountedInLevelMax OBJECT-TYPE
	SYNTAX	 CounterBasedGauge64
	MAX-ACCESS  read-only
	STATUS      current
	DESCRIPTION
	"Table entry attribute for insightsScoreBytesUnAccountedIn"
	::={insightsScoreBytesUnAccountedInLevelEntry 4}


insightsScoreBytesUnAccountedOut	OBJECT IDENTIFIER ::={insights 84}

insightsScoreBytesUnAccountedOutVal	OBJECT-TYPE
	SYNTAX	 Counter64
	MAX-ACCESS read-only
	STATUS current
	DESCRIPTION "Score: Bytes unaccounted out"

	::={insightsScoreBytesUnAccountedOut 1}

insightsScoreBytesUnAccountedOutMom	OBJECT-TYPE
	SYNTAX	 CounterBasedGauge64
	MAX-ACCESS read-only
	STATUS current
	DESCRIPTION "Score: Bytes unaccounted out"

	::={insightsScoreBytesUnAccountedOut 2}

insightsScoreBytesUnAccountedOutMax	OBJECT-TYPE
	SYNTAX	 CounterBasedGauge64
	MAX-ACCESS read-only
	STATUS current
	DESCRIPTION "Score: Bytes unaccounted out"

	::={insightsScoreBytesUnAccountedOut 3}

insightsScoreBytesUnAccountedOutLevelTable OBJECT-TYPE
	SYNTAX      SEQUENCE OF InsightsScoreBytesUnAccountedOutLevelEntry
	MAX-ACCESS  not-accessible
	STATUS      current
	DESCRIPTION
	"Table for insightsScoreBytesUnAccountedOut"
	::={insightsScoreBytesUnAccountedOut 4}

insightsScoreBytesUnAccountedOutLevelEntry OBJECT-TYPE
	SYNTAX      InsightsScoreBytesUnAccountedOutLevelEntry
	MAX-ACCESS  not-accessible
	STATUS      current
	DESCRIPTION
	"Table entry for insightsScoreBytesUnAccountedOut"
	INDEX { insightsScoreBytesUnAccountedOutLevelName }
	::={insightsScoreBytesUnAccountedOutLevelTable 1}

InsightsScoreBytesUnAccountedOutLevelEntry ::=
	SEQUENCE {
		insightsScoreBytesUnAccountedOutLevelName	DisplayString,
		insightsScoreBytesUnAccountedOutLevelVal	Counter64,
		insightsScoreBytesUnAccountedOutLevelMom	CounterBasedGauge64,
		insightsScoreBytesUnAccountedOutLevelMax	CounterBasedGauge64
	}

insightsScoreBytesUnAccountedOutLevelName OBJECT-TYPE
	SYNTAX      DisplayString
	MAX-ACCESS  not-accessible
	STATUS      current
	DESCRIPTION
	"Table entry display string for insightsScoreBytesUnAccountedOut"
	::={insightsScoreBytesUnAccountedOutLevelEntry 1}

insightsScoreBytesUnAccountedOutLevelVal OBJECT-TYPE
	SYNTAX	 Counter64
	MAX-ACCESS  read-only
	STATUS      current
	DESCRIPTION
	"Table entry attribute for insightsScoreBytesUnAccountedOut"
	::={insightsScoreBytesUnAccountedOutLevelEntry 2}

insightsScoreBytesUnAccountedOutLevelMom OBJECT-TYPE
	SYNTAX	 CounterBasedGauge64
	MAX-ACCESS  read-only
	STATUS      current
	DESCRIPTION
	"Table entry attribute for insightsScoreBytesUnAccountedOut"
	::={insightsScoreBytesUnAccountedOutLevelEntry 3}

insightsScoreBytesUnAccountedOutLevelMax OBJECT-TYPE
	SYNTAX	 CounterBasedGauge64
	MAX-ACCESS  read-only
	STATUS      current
	DESCRIPTION
	"Table entry attribute for insightsScoreBytesUnAccountedOut"
	::={insightsScoreBytesUnAccountedOutLevelEntry 4}


insightsTrafficCsvRowDropped	OBJECT IDENTIFIER ::={insights 85}

insightsTrafficCsvRowDroppedVal	OBJECT-TYPE
	SYNTAX	 Counter64
	MAX-ACCESS read-only
	STATUS current
	DESCRIPTION "Traffic: CSV rows dropped"

	::={insightsTrafficCsvRowDropped 1}

insightsTrafficCsvRowDroppedMom	OBJECT-TYPE
	SYNTAX	 CounterBasedGauge64
	MAX-ACCESS read-only
	STATUS current
	DESCRIPTION "Traffic: CSV rows dropped"

	::={insightsTrafficCsvRowDropped 2}

insightsTrafficCsvRowDroppedMax	OBJECT-TYPE
	SYNTAX	 CounterBasedGauge64
	MAX-ACCESS read-only
	STATUS current
	DESCRIPTION "Traffic: CSV rows dropped"

	::={insightsTrafficCsvRowDropped 3}

insightsTrafficCsvRowDroppedLevelTable OBJECT-TYPE
	SYNTAX      SEQUENCE OF InsightsTrafficCsvRowDroppedLevelEntry
	MAX-ACCESS  not-accessible
	STATUS      current
	DESCRIPTION
	"Table for insightsTrafficCsvRowDropped"
	::={insightsTrafficCsvRowDropped 4}

insightsTrafficCsvRowDroppedLevelEntry OBJECT-TYPE
	SYNTAX      InsightsTrafficCsvRowDroppedLevelEntry
	MAX-ACCESS  not-accessible
	STATUS      current
	DESCRIPTION
	"Table entry for insightsTrafficCsvRowDropped"
	INDEX { insightsTrafficCsvRowDroppedLevelName }
	::={insightsTrafficCsvRowDroppedLevelTable 1}

InsightsTrafficCsvRowDroppedLevelEntry ::=
	SEQUENCE {
		insightsTrafficCsvRowDroppedLevelName	DisplayString,
		insightsTrafficCsvRowDroppedLevelVal	Counter64,
		insightsTrafficCsvRowDroppedLevelMom	CounterBasedGauge64,
		insightsTrafficCsvRowDroppedLevelMax	CounterBasedGauge64
	}

insightsTrafficCsvRowDroppedLevelName OBJECT-TYPE
	SYNTAX      DisplayString
	MAX-ACCESS  not-accessible
	STATUS      current
	DESCRIPTION
	"Table entry display string for insightsTrafficCsvRowDropped"
	::={insightsTrafficCsvRowDroppedLevelEntry 1}

insightsTrafficCsvRowDroppedLevelVal OBJECT-TYPE
	SYNTAX	 Counter64
	MAX-ACCESS  read-only
	STATUS      current
	DESCRIPTION
	"Table entry attribute for insightsTrafficCsvRowDropped"
	::={insightsTrafficCsvRowDroppedLevelEntry 2}

insightsTrafficCsvRowDroppedLevelMom OBJECT-TYPE
	SYNTAX	 CounterBasedGauge64
	MAX-ACCESS  read-only
	STATUS      current
	DESCRIPTION
	"Table entry attribute for insightsTrafficCsvRowDropped"
	::={insightsTrafficCsvRowDroppedLevelEntry 3}

insightsTrafficCsvRowDroppedLevelMax OBJECT-TYPE
	SYNTAX	 CounterBasedGauge64
	MAX-ACCESS  read-only
	STATUS      current
	DESCRIPTION
	"Table entry attribute for insightsTrafficCsvRowDropped"
	::={insightsTrafficCsvRowDroppedLevelEntry 4}


insightsScoreCsvRowDropped	OBJECT IDENTIFIER ::={insights 86}

insightsScoreCsvRowDroppedVal	OBJECT-TYPE
	SYNTAX	 Counter64
	MAX-ACCESS read-only
	STATUS current
	DESCRIPTION "Score: CSV rows dropped"

	::={insightsScoreCsvRowDropped 1}

insightsScoreCsvRowDroppedMom	OBJECT-TYPE
	SYNTAX	 CounterBasedGauge64
	MAX-ACCESS read-only
	STATUS current
	DESCRIPTION "Score: CSV rows dropped"

	::={insightsScoreCsvRowDropped 2}

insightsScoreCsvRowDroppedMax	OBJECT-TYPE
	SYNTAX	 CounterBasedGauge64
	MAX-ACCESS read-only
	STATUS current
	DESCRIPTION "Score: CSV rows dropped"

	::={insightsScoreCsvRowDropped 3}

insightsScoreCsvRowDroppedLevelTable OBJECT-TYPE
	SYNTAX      SEQUENCE OF InsightsScoreCsvRowDroppedLevelEntry
	MAX-ACCESS  not-accessible
	STATUS      current
	DESCRIPTION
	"Table for insightsScoreCsvRowDropped"
	::={insightsScoreCsvRowDropped 4}

insightsScoreCsvRowDroppedLevelEntry OBJECT-TYPE
	SYNTAX      InsightsScoreCsvRowDroppedLevelEntry
	MAX-ACCESS  not-accessible
	STATUS      current
	DESCRIPTION
	"Table entry for insightsScoreCsvRowDropped"
	INDEX { insightsScoreCsvRowDroppedLevelName }
	::={insightsScoreCsvRowDroppedLevelTable 1}

InsightsScoreCsvRowDroppedLevelEntry ::=
	SEQUENCE {
		insightsScoreCsvRowDroppedLevelName	DisplayString,
		insightsScoreCsvRowDroppedLevelVal	Counter64,
		insightsScoreCsvRowDroppedLevelMom	CounterBasedGauge64,
		insightsScoreCsvRowDroppedLevelMax	CounterBasedGauge64
	}

insightsScoreCsvRowDroppedLevelName OBJECT-TYPE
	SYNTAX      DisplayString
	MAX-ACCESS  not-accessible
	STATUS      current
	DESCRIPTION
	"Table entry display string for insightsScoreCsvRowDropped"
	::={insightsScoreCsvRowDroppedLevelEntry 1}

insightsScoreCsvRowDroppedLevelVal OBJECT-TYPE
	SYNTAX	 Counter64
	MAX-ACCESS  read-only
	STATUS      current
	DESCRIPTION
	"Table entry attribute for insightsScoreCsvRowDropped"
	::={insightsScoreCsvRowDroppedLevelEntry 2}

insightsScoreCsvRowDroppedLevelMom OBJECT-TYPE
	SYNTAX	 CounterBasedGauge64
	MAX-ACCESS  read-only
	STATUS      current
	DESCRIPTION
	"Table entry attribute for insightsScoreCsvRowDropped"
	::={insightsScoreCsvRowDroppedLevelEntry 3}

insightsScoreCsvRowDroppedLevelMax OBJECT-TYPE
	SYNTAX	 CounterBasedGauge64
	MAX-ACCESS  read-only
	STATUS      current
	DESCRIPTION
	"Table entry attribute for insightsScoreCsvRowDropped"
	::={insightsScoreCsvRowDroppedLevelEntry 4}


insightsScoreCsvFilesOnDisk	OBJECT IDENTIFIER ::={insights 87}

insightsScoreCsvFilesOnDiskVal	OBJECT-TYPE
	SYNTAX	 CounterBasedGauge64
	MAX-ACCESS read-only
	STATUS current
	DESCRIPTION "Score: CSV files on disk"

	::={insightsScoreCsvFilesOnDisk 1}

insightsScoreCsvFilesOnDiskMax	OBJECT-TYPE
	SYNTAX	 CounterBasedGauge64
	MAX-ACCESS read-only
	STATUS current
	DESCRIPTION "Score: CSV files on disk"

	::={insightsScoreCsvFilesOnDisk 3}

insightsScoreCsvFilesOnDiskLevelTable OBJECT-TYPE
	SYNTAX      SEQUENCE OF InsightsScoreCsvFilesOnDiskLevelEntry
	MAX-ACCESS  not-accessible
	STATUS      current
	DESCRIPTION
	"Table for insightsScoreCsvFilesOnDisk"
	::={insightsScoreCsvFilesOnDisk 4}

insightsScoreCsvFilesOnDiskLevelEntry OBJECT-TYPE
	SYNTAX      InsightsScoreCsvFilesOnDiskLevelEntry
	MAX-ACCESS  not-accessible
	STATUS      current
	DESCRIPTION
	"Table entry for insightsScoreCsvFilesOnDisk"
	INDEX { insightsScoreCsvFilesOnDiskLevelName }
	::={insightsScoreCsvFilesOnDiskLevelTable 1}

InsightsScoreCsvFilesOnDiskLevelEntry ::=
	SEQUENCE {
		insightsScoreCsvFilesOnDiskLevelName	DisplayString,
		insightsScoreCsvFilesOnDiskLevelVal	CounterBasedGauge64,
		insightsScoreCsvFilesOnDiskLevelMax	CounterBasedGauge64
	}

insightsScoreCsvFilesOnDiskLevelName OBJECT-TYPE
	SYNTAX      DisplayString
	MAX-ACCESS  not-accessible
	STATUS      current
	DESCRIPTION
	"Table entry display string for insightsScoreCsvFilesOnDisk"
	::={insightsScoreCsvFilesOnDiskLevelEntry 1}

insightsScoreCsvFilesOnDiskLevelVal OBJECT-TYPE
	SYNTAX	 CounterBasedGauge64
	MAX-ACCESS  read-only
	STATUS      current
	DESCRIPTION
	"Table entry attribute for insightsScoreCsvFilesOnDisk"
	::={insightsScoreCsvFilesOnDiskLevelEntry 2}

insightsScoreCsvFilesOnDiskLevelMax OBJECT-TYPE
	SYNTAX	 CounterBasedGauge64
	MAX-ACCESS  read-only
	STATUS      current
	DESCRIPTION
	"Table entry attribute for insightsScoreCsvFilesOnDisk"
	::={insightsScoreCsvFilesOnDiskLevelEntry 4}


insightsTrafficCsvFilesOnDisk	OBJECT IDENTIFIER ::={insights 88}

insightsTrafficCsvFilesOnDiskVal	OBJECT-TYPE
	SYNTAX	 CounterBasedGauge64
	MAX-ACCESS read-only
	STATUS current
	DESCRIPTION "Traffic: CSV files on disk"

	::={insightsTrafficCsvFilesOnDisk 1}

insightsTrafficCsvFilesOnDiskMax	OBJECT-TYPE
	SYNTAX	 CounterBasedGauge64
	MAX-ACCESS read-only
	STATUS current
	DESCRIPTION "Traffic: CSV files on disk"

	::={insightsTrafficCsvFilesOnDisk 3}

insightsTrafficCsvFilesOnDiskLevelTable OBJECT-TYPE
	SYNTAX      SEQUENCE OF InsightsTrafficCsvFilesOnDiskLevelEntry
	MAX-ACCESS  not-accessible
	STATUS      current
	DESCRIPTION
	"Table for insightsTrafficCsvFilesOnDisk"
	::={insightsTrafficCsvFilesOnDisk 4}

insightsTrafficCsvFilesOnDiskLevelEntry OBJECT-TYPE
	SYNTAX      InsightsTrafficCsvFilesOnDiskLevelEntry
	MAX-ACCESS  not-accessible
	STATUS      current
	DESCRIPTION
	"Table entry for insightsTrafficCsvFilesOnDisk"
	INDEX { insightsTrafficCsvFilesOnDiskLevelName }
	::={insightsTrafficCsvFilesOnDiskLevelTable 1}

InsightsTrafficCsvFilesOnDiskLevelEntry ::=
	SEQUENCE {
		insightsTrafficCsvFilesOnDiskLevelName	DisplayString,
		insightsTrafficCsvFilesOnDiskLevelVal	CounterBasedGauge64,
		insightsTrafficCsvFilesOnDiskLevelMax	CounterBasedGauge64
	}

insightsTrafficCsvFilesOnDiskLevelName OBJECT-TYPE
	SYNTAX      DisplayString
	MAX-ACCESS  not-accessible
	STATUS      current
	DESCRIPTION
	"Table entry display string for insightsTrafficCsvFilesOnDisk"
	::={insightsTrafficCsvFilesOnDiskLevelEntry 1}

insightsTrafficCsvFilesOnDiskLevelVal OBJECT-TYPE
	SYNTAX	 CounterBasedGauge64
	MAX-ACCESS  read-only
	STATUS      current
	DESCRIPTION
	"Table entry attribute for insightsTrafficCsvFilesOnDisk"
	::={insightsTrafficCsvFilesOnDiskLevelEntry 2}

insightsTrafficCsvFilesOnDiskLevelMax OBJECT-TYPE
	SYNTAX	 CounterBasedGauge64
	MAX-ACCESS  read-only
	STATUS      current
	DESCRIPTION
	"Table entry attribute for insightsTrafficCsvFilesOnDisk"
	::={insightsTrafficCsvFilesOnDiskLevelEntry 4}


insightsScoreRecords	OBJECT IDENTIFIER ::={insights 89}

insightsScoreRecordsVal	OBJECT-TYPE
	SYNTAX	 CounterBasedGauge64
	MAX-ACCESS read-only
	STATUS current
	DESCRIPTION "Score: Total buffered records"

	::={insightsScoreRecords 1}

insightsScoreRecordsMax	OBJECT-TYPE
	SYNTAX	 CounterBasedGauge64
	MAX-ACCESS read-only
	STATUS current
	DESCRIPTION "Score: Total buffered records"

	::={insightsScoreRecords 3}

insightsScoreRecordsLevelTable OBJECT-TYPE
	SYNTAX      SEQUENCE OF InsightsScoreRecordsLevelEntry
	MAX-ACCESS  not-accessible
	STATUS      current
	DESCRIPTION
	"Table for insightsScoreRecords"
	::={insightsScoreRecords 4}

insightsScoreRecordsLevelEntry OBJECT-TYPE
	SYNTAX      InsightsScoreRecordsLevelEntry
	MAX-ACCESS  not-accessible
	STATUS      current
	DESCRIPTION
	"Table entry for insightsScoreRecords"
	INDEX { insightsScoreRecordsLevelName }
	::={insightsScoreRecordsLevelTable 1}

InsightsScoreRecordsLevelEntry ::=
	SEQUENCE {
		insightsScoreRecordsLevelName	DisplayString,
		insightsScoreRecordsLevelVal	CounterBasedGauge64,
		insightsScoreRecordsLevelMax	CounterBasedGauge64
	}

insightsScoreRecordsLevelName OBJECT-TYPE
	SYNTAX      DisplayString
	MAX-ACCESS  not-accessible
	STATUS      current
	DESCRIPTION
	"Table entry display string for insightsScoreRecords"
	::={insightsScoreRecordsLevelEntry 1}

insightsScoreRecordsLevelVal OBJECT-TYPE
	SYNTAX	 CounterBasedGauge64
	MAX-ACCESS  read-only
	STATUS      current
	DESCRIPTION
	"Table entry attribute for insightsScoreRecords"
	::={insightsScoreRecordsLevelEntry 2}

insightsScoreRecordsLevelMax OBJECT-TYPE
	SYNTAX	 CounterBasedGauge64
	MAX-ACCESS  read-only
	STATUS      current
	DESCRIPTION
	"Table entry attribute for insightsScoreRecords"
	::={insightsScoreRecordsLevelEntry 4}


insightsScoreBytesBuffer	OBJECT IDENTIFIER ::={insights 90}

insightsScoreBytesBufferVal	OBJECT-TYPE
	SYNTAX	 CounterBasedGauge64
	MAX-ACCESS read-only
	STATUS current
	DESCRIPTION "Score: Total buffer bytes used"

	::={insightsScoreBytesBuffer 1}

insightsScoreBytesBufferMax	OBJECT-TYPE
	SYNTAX	 CounterBasedGauge64
	MAX-ACCESS read-only
	STATUS current
	DESCRIPTION "Score: Total buffer bytes used"

	::={insightsScoreBytesBuffer 3}

insightsScoreBytesBufferLevelTable OBJECT-TYPE
	SYNTAX      SEQUENCE OF InsightsScoreBytesBufferLevelEntry
	MAX-ACCESS  not-accessible
	STATUS      current
	DESCRIPTION
	"Table for insightsScoreBytesBuffer"
	::={insightsScoreBytesBuffer 4}

insightsScoreBytesBufferLevelEntry OBJECT-TYPE
	SYNTAX      InsightsScoreBytesBufferLevelEntry
	MAX-ACCESS  not-accessible
	STATUS      current
	DESCRIPTION
	"Table entry for insightsScoreBytesBuffer"
	INDEX { insightsScoreBytesBufferLevelName }
	::={insightsScoreBytesBufferLevelTable 1}

InsightsScoreBytesBufferLevelEntry ::=
	SEQUENCE {
		insightsScoreBytesBufferLevelName	DisplayString,
		insightsScoreBytesBufferLevelVal	CounterBasedGauge64,
		insightsScoreBytesBufferLevelMax	CounterBasedGauge64
	}

insightsScoreBytesBufferLevelName OBJECT-TYPE
	SYNTAX      DisplayString
	MAX-ACCESS  not-accessible
	STATUS      current
	DESCRIPTION
	"Table entry display string for insightsScoreBytesBuffer"
	::={insightsScoreBytesBufferLevelEntry 1}

insightsScoreBytesBufferLevelVal OBJECT-TYPE
	SYNTAX	 CounterBasedGauge64
	MAX-ACCESS  read-only
	STATUS      current
	DESCRIPTION
	"Table entry attribute for insightsScoreBytesBuffer"
	::={insightsScoreBytesBufferLevelEntry 2}

insightsScoreBytesBufferLevelMax OBJECT-TYPE
	SYNTAX	 CounterBasedGauge64
	MAX-ACCESS  read-only
	STATUS      current
	DESCRIPTION
	"Table entry attribute for insightsScoreBytesBuffer"
	::={insightsScoreBytesBufferLevelEntry 4}


insightsScoreRecordsperThread	OBJECT IDENTIFIER ::={insights 91}

insightsScoreRecordsperThreadVal	OBJECT-TYPE
	SYNTAX	 CounterBasedGauge64
	MAX-ACCESS read-only
	STATUS current
	DESCRIPTION "Score: Max buffered records per builder thread"

	::={insightsScoreRecordsperThread 1}

insightsScoreRecordsperThreadMax	OBJECT-TYPE
	SYNTAX	 CounterBasedGauge64
	MAX-ACCESS read-only
	STATUS current
	DESCRIPTION "Score: Max buffered records per builder thread"

	::={insightsScoreRecordsperThread 3}

insightsScoreRecordsperThreadLevelTable OBJECT-TYPE
	SYNTAX      SEQUENCE OF InsightsScoreRecordsperThreadLevelEntry
	MAX-ACCESS  not-accessible
	STATUS      current
	DESCRIPTION
	"Table for insightsScoreRecordsperThread"
	::={insightsScoreRecordsperThread 4}

insightsScoreRecordsperThreadLevelEntry OBJECT-TYPE
	SYNTAX      InsightsScoreRecordsperThreadLevelEntry
	MAX-ACCESS  not-accessible
	STATUS      current
	DESCRIPTION
	"Table entry for insightsScoreRecordsperThread"
	INDEX { insightsScoreRecordsperThreadLevelName }
	::={insightsScoreRecordsperThreadLevelTable 1}

InsightsScoreRecordsperThreadLevelEntry ::=
	SEQUENCE {
		insightsScoreRecordsperThreadLevelName	DisplayString,
		insightsScoreRecordsperThreadLevelVal	CounterBasedGauge64,
		insightsScoreRecordsperThreadLevelMax	CounterBasedGauge64
	}

insightsScoreRecordsperThreadLevelName OBJECT-TYPE
	SYNTAX      DisplayString
	MAX-ACCESS  not-accessible
	STATUS      current
	DESCRIPTION
	"Table entry display string for insightsScoreRecordsperThread"
	::={insightsScoreRecordsperThreadLevelEntry 1}

insightsScoreRecordsperThreadLevelVal OBJECT-TYPE
	SYNTAX	 CounterBasedGauge64
	MAX-ACCESS  read-only
	STATUS      current
	DESCRIPTION
	"Table entry attribute for insightsScoreRecordsperThread"
	::={insightsScoreRecordsperThreadLevelEntry 2}

insightsScoreRecordsperThreadLevelMax OBJECT-TYPE
	SYNTAX	 CounterBasedGauge64
	MAX-ACCESS  read-only
	STATUS      current
	DESCRIPTION
	"Table entry attribute for insightsScoreRecordsperThread"
	::={insightsScoreRecordsperThreadLevelEntry 4}


insightsScoreBytesBufferperThread	OBJECT IDENTIFIER ::={insights 92}

insightsScoreBytesBufferperThreadVal	OBJECT-TYPE
	SYNTAX	 CounterBasedGauge64
	MAX-ACCESS read-only
	STATUS current
	DESCRIPTION "Score: Max buffer bytes used per builder thread"

	::={insightsScoreBytesBufferperThread 1}

insightsScoreBytesBufferperThreadMax	OBJECT-TYPE
	SYNTAX	 CounterBasedGauge64
	MAX-ACCESS read-only
	STATUS current
	DESCRIPTION "Score: Max buffer bytes used per builder thread"

	::={insightsScoreBytesBufferperThread 3}

insightsScoreBytesBufferperThreadLevelTable OBJECT-TYPE
	SYNTAX      SEQUENCE OF InsightsScoreBytesBufferperThreadLevelEntry
	MAX-ACCESS  not-accessible
	STATUS      current
	DESCRIPTION
	"Table for insightsScoreBytesBufferperThread"
	::={insightsScoreBytesBufferperThread 4}

insightsScoreBytesBufferperThreadLevelEntry OBJECT-TYPE
	SYNTAX      InsightsScoreBytesBufferperThreadLevelEntry
	MAX-ACCESS  not-accessible
	STATUS      current
	DESCRIPTION
	"Table entry for insightsScoreBytesBufferperThread"
	INDEX { insightsScoreBytesBufferperThreadLevelName }
	::={insightsScoreBytesBufferperThreadLevelTable 1}

InsightsScoreBytesBufferperThreadLevelEntry ::=
	SEQUENCE {
		insightsScoreBytesBufferperThreadLevelName	DisplayString,
		insightsScoreBytesBufferperThreadLevelVal	CounterBasedGauge64,
		insightsScoreBytesBufferperThreadLevelMax	CounterBasedGauge64
	}

insightsScoreBytesBufferperThreadLevelName OBJECT-TYPE
	SYNTAX      DisplayString
	MAX-ACCESS  not-accessible
	STATUS      current
	DESCRIPTION
	"Table entry display string for insightsScoreBytesBufferperThread"
	::={insightsScoreBytesBufferperThreadLevelEntry 1}

insightsScoreBytesBufferperThreadLevelVal OBJECT-TYPE
	SYNTAX	 CounterBasedGauge64
	MAX-ACCESS  read-only
	STATUS      current
	DESCRIPTION
	"Table entry attribute for insightsScoreBytesBufferperThread"
	::={insightsScoreBytesBufferperThreadLevelEntry 2}

insightsScoreBytesBufferperThreadLevelMax OBJECT-TYPE
	SYNTAX	 CounterBasedGauge64
	MAX-ACCESS  read-only
	STATUS      current
	DESCRIPTION
	"Table entry attribute for insightsScoreBytesBufferperThread"
	::={insightsScoreBytesBufferperThreadLevelEntry 4}


hoststats	OBJECT IDENTIFIER ::={sysdiag 146}

hostStatsInterfaceTraffic	OBJECT IDENTIFIER ::={hoststats 1}

hostStatsInterfaceTrafficVal	OBJECT-TYPE
	SYNTAX	 Counter64
	MAX-ACCESS read-only
	STATUS current
	DESCRIPTION "Host stats traffic sent over the interface"

	::={hostStatsInterfaceTraffic 1}

hostStatsInterfaceTrafficMom	OBJECT-TYPE
	SYNTAX	 CounterBasedGauge64
	MAX-ACCESS read-only
	STATUS current
	DESCRIPTION "Host stats traffic sent over the interface"

	::={hostStatsInterfaceTraffic 2}

hostStatsInterfaceTrafficMax	OBJECT-TYPE
	SYNTAX	 CounterBasedGauge64
	MAX-ACCESS read-only
	STATUS current
	DESCRIPTION "Host stats traffic sent over the interface"

	::={hostStatsInterfaceTraffic 3}

hostStatsInterfaceTrafficLevelTable OBJECT-TYPE
	SYNTAX      SEQUENCE OF HostStatsInterfaceTrafficLevelEntry
	MAX-ACCESS  not-accessible
	STATUS      current
	DESCRIPTION
	"Table for hostStatsInterfaceTraffic"
	::={hostStatsInterfaceTraffic 4}

hostStatsInterfaceTrafficLevelEntry OBJECT-TYPE
	SYNTAX      HostStatsInterfaceTrafficLevelEntry
	MAX-ACCESS  not-accessible
	STATUS      current
	DESCRIPTION
	"Table entry for hostStatsInterfaceTraffic"
	INDEX { hostStatsInterfaceTrafficLevelName }
	::={hostStatsInterfaceTrafficLevelTable 1}

HostStatsInterfaceTrafficLevelEntry ::=
	SEQUENCE {
		hostStatsInterfaceTrafficLevelName	DisplayString,
		hostStatsInterfaceTrafficLevelVal	Counter64,
		hostStatsInterfaceTrafficLevelMom	CounterBasedGauge64,
		hostStatsInterfaceTrafficLevelMax	CounterBasedGauge64
	}

hostStatsInterfaceTrafficLevelName OBJECT-TYPE
	SYNTAX      DisplayString
	MAX-ACCESS  not-accessible
	STATUS      current
	DESCRIPTION
	"Table entry display string for hostStatsInterfaceTraffic"
	::={hostStatsInterfaceTrafficLevelEntry 1}

hostStatsInterfaceTrafficLevelVal OBJECT-TYPE
	SYNTAX	 Counter64
	MAX-ACCESS  read-only
	STATUS      current
	DESCRIPTION
	"Table entry attribute for hostStatsInterfaceTraffic"
	::={hostStatsInterfaceTrafficLevelEntry 2}

hostStatsInterfaceTrafficLevelMom OBJECT-TYPE
	SYNTAX	 CounterBasedGauge64
	MAX-ACCESS  read-only
	STATUS      current
	DESCRIPTION
	"Table entry attribute for hostStatsInterfaceTraffic"
	::={hostStatsInterfaceTrafficLevelEntry 3}

hostStatsInterfaceTrafficLevelMax OBJECT-TYPE
	SYNTAX	 CounterBasedGauge64
	MAX-ACCESS  read-only
	STATUS      current
	DESCRIPTION
	"Table entry attribute for hostStatsInterfaceTraffic"
	::={hostStatsInterfaceTrafficLevelEntry 4}


hostStatsNumHosts	OBJECT IDENTIFIER ::={hoststats 2}

hostStatsNumHostsVal	OBJECT-TYPE
	SYNTAX	 CounterBasedGauge64
	MAX-ACCESS read-only
	STATUS current
	DESCRIPTION "Number of hosts"

	::={hostStatsNumHosts 1}

hostStatsNumHostsMax	OBJECT-TYPE
	SYNTAX	 CounterBasedGauge64
	MAX-ACCESS read-only
	STATUS current
	DESCRIPTION "Number of hosts"

	::={hostStatsNumHosts 3}

hostStatsNumHostsLevelTable OBJECT-TYPE
	SYNTAX      SEQUENCE OF HostStatsNumHostsLevelEntry
	MAX-ACCESS  not-accessible
	STATUS      current
	DESCRIPTION
	"Table for hostStatsNumHosts"
	::={hostStatsNumHosts 4}

hostStatsNumHostsLevelEntry OBJECT-TYPE
	SYNTAX      HostStatsNumHostsLevelEntry
	MAX-ACCESS  not-accessible
	STATUS      current
	DESCRIPTION
	"Table entry for hostStatsNumHosts"
	INDEX { hostStatsNumHostsLevelName }
	::={hostStatsNumHostsLevelTable 1}

HostStatsNumHostsLevelEntry ::=
	SEQUENCE {
		hostStatsNumHostsLevelName	DisplayString,
		hostStatsNumHostsLevelVal	CounterBasedGauge64,
		hostStatsNumHostsLevelMax	CounterBasedGauge64
	}

hostStatsNumHostsLevelName OBJECT-TYPE
	SYNTAX      DisplayString
	MAX-ACCESS  not-accessible
	STATUS      current
	DESCRIPTION
	"Table entry display string for hostStatsNumHosts"
	::={hostStatsNumHostsLevelEntry 1}

hostStatsNumHostsLevelVal OBJECT-TYPE
	SYNTAX	 CounterBasedGauge64
	MAX-ACCESS  read-only
	STATUS      current
	DESCRIPTION
	"Table entry attribute for hostStatsNumHosts"
	::={hostStatsNumHostsLevelEntry 2}

hostStatsNumHostsLevelMax OBJECT-TYPE
	SYNTAX	 CounterBasedGauge64
	MAX-ACCESS  read-only
	STATUS      current
	DESCRIPTION
	"Table entry attribute for hostStatsNumHosts"
	::={hostStatsNumHostsLevelEntry 4}


hostStatsBufAliasing	OBJECT IDENTIFIER ::={hoststats 3}

hostStatsBufAliasingVal	OBJECT-TYPE
	SYNTAX	 Counter64
	MAX-ACCESS read-only
	STATUS current
	DESCRIPTION "Buffer aliasing count"

	::={hostStatsBufAliasing 1}

hostStatsBufAliasingMom	OBJECT-TYPE
	SYNTAX	 CounterBasedGauge64
	MAX-ACCESS read-only
	STATUS current
	DESCRIPTION "Buffer aliasing count"

	::={hostStatsBufAliasing 2}

hostStatsBufAliasingMax	OBJECT-TYPE
	SYNTAX	 CounterBasedGauge64
	MAX-ACCESS read-only
	STATUS current
	DESCRIPTION "Buffer aliasing count"

	::={hostStatsBufAliasing 3}

hostStatsBufAliasingLevelTable OBJECT-TYPE
	SYNTAX      SEQUENCE OF HostStatsBufAliasingLevelEntry
	MAX-ACCESS  not-accessible
	STATUS      current
	DESCRIPTION
	"Table for hostStatsBufAliasing"
	::={hostStatsBufAliasing 4}

hostStatsBufAliasingLevelEntry OBJECT-TYPE
	SYNTAX      HostStatsBufAliasingLevelEntry
	MAX-ACCESS  not-accessible
	STATUS      current
	DESCRIPTION
	"Table entry for hostStatsBufAliasing"
	INDEX { hostStatsBufAliasingLevelName }
	::={hostStatsBufAliasingLevelTable 1}

HostStatsBufAliasingLevelEntry ::=
	SEQUENCE {
		hostStatsBufAliasingLevelName	DisplayString,
		hostStatsBufAliasingLevelVal	Counter64,
		hostStatsBufAliasingLevelMom	CounterBasedGauge64,
		hostStatsBufAliasingLevelMax	CounterBasedGauge64
	}

hostStatsBufAliasingLevelName OBJECT-TYPE
	SYNTAX      DisplayString
	MAX-ACCESS  not-accessible
	STATUS      current
	DESCRIPTION
	"Table entry display string for hostStatsBufAliasing"
	::={hostStatsBufAliasingLevelEntry 1}

hostStatsBufAliasingLevelVal OBJECT-TYPE
	SYNTAX	 Counter64
	MAX-ACCESS  read-only
	STATUS      current
	DESCRIPTION
	"Table entry attribute for hostStatsBufAliasing"
	::={hostStatsBufAliasingLevelEntry 2}

hostStatsBufAliasingLevelMom OBJECT-TYPE
	SYNTAX	 CounterBasedGauge64
	MAX-ACCESS  read-only
	STATUS      current
	DESCRIPTION
	"Table entry attribute for hostStatsBufAliasing"
	::={hostStatsBufAliasingLevelEntry 3}

hostStatsBufAliasingLevelMax OBJECT-TYPE
	SYNTAX	 CounterBasedGauge64
	MAX-ACCESS  read-only
	STATUS      current
	DESCRIPTION
	"Table entry attribute for hostStatsBufAliasing"
	::={hostStatsBufAliasingLevelEntry 4}


hostStatsMissedDeadline	OBJECT IDENTIFIER ::={hoststats 4}

hostStatsMissedDeadlineVal	OBJECT-TYPE
	SYNTAX	 Counter64
	MAX-ACCESS read-only
	STATUS current
	DESCRIPTION "Missed send-deadlines"

	::={hostStatsMissedDeadline 1}

hostStatsMissedDeadlineMom	OBJECT-TYPE
	SYNTAX	 CounterBasedGauge64
	MAX-ACCESS read-only
	STATUS current
	DESCRIPTION "Missed send-deadlines"

	::={hostStatsMissedDeadline 2}

hostStatsMissedDeadlineMax	OBJECT-TYPE
	SYNTAX	 CounterBasedGauge64
	MAX-ACCESS read-only
	STATUS current
	DESCRIPTION "Missed send-deadlines"

	::={hostStatsMissedDeadline 3}

hostStatsMissedDeadlineLevelTable OBJECT-TYPE
	SYNTAX      SEQUENCE OF HostStatsMissedDeadlineLevelEntry
	MAX-ACCESS  not-accessible
	STATUS      current
	DESCRIPTION
	"Table for hostStatsMissedDeadline"
	::={hostStatsMissedDeadline 4}

hostStatsMissedDeadlineLevelEntry OBJECT-TYPE
	SYNTAX      HostStatsMissedDeadlineLevelEntry
	MAX-ACCESS  not-accessible
	STATUS      current
	DESCRIPTION
	"Table entry for hostStatsMissedDeadline"
	INDEX { hostStatsMissedDeadlineLevelName }
	::={hostStatsMissedDeadlineLevelTable 1}

HostStatsMissedDeadlineLevelEntry ::=
	SEQUENCE {
		hostStatsMissedDeadlineLevelName	DisplayString,
		hostStatsMissedDeadlineLevelVal	Counter64,
		hostStatsMissedDeadlineLevelMom	CounterBasedGauge64,
		hostStatsMissedDeadlineLevelMax	CounterBasedGauge64
	}

hostStatsMissedDeadlineLevelName OBJECT-TYPE
	SYNTAX      DisplayString
	MAX-ACCESS  not-accessible
	STATUS      current
	DESCRIPTION
	"Table entry display string for hostStatsMissedDeadline"
	::={hostStatsMissedDeadlineLevelEntry 1}

hostStatsMissedDeadlineLevelVal OBJECT-TYPE
	SYNTAX	 Counter64
	MAX-ACCESS  read-only
	STATUS      current
	DESCRIPTION
	"Table entry attribute for hostStatsMissedDeadline"
	::={hostStatsMissedDeadlineLevelEntry 2}

hostStatsMissedDeadlineLevelMom OBJECT-TYPE
	SYNTAX	 CounterBasedGauge64
	MAX-ACCESS  read-only
	STATUS      current
	DESCRIPTION
	"Table entry attribute for hostStatsMissedDeadline"
	::={hostStatsMissedDeadlineLevelEntry 3}

hostStatsMissedDeadlineLevelMax OBJECT-TYPE
	SYNTAX	 CounterBasedGauge64
	MAX-ACCESS  read-only
	STATUS      current
	DESCRIPTION
	"Table entry attribute for hostStatsMissedDeadline"
	::={hostStatsMissedDeadlineLevelEntry 4}


hostStatsTimerHosts	OBJECT IDENTIFIER ::={hoststats 5}

hostStatsTimerHostsVal	OBJECT-TYPE
	SYNTAX	 Counter64
	MAX-ACCESS read-only
	STATUS current
	DESCRIPTION "Hosts processed in timer func"

	::={hostStatsTimerHosts 1}

hostStatsTimerHostsMom	OBJECT-TYPE
	SYNTAX	 CounterBasedGauge64
	MAX-ACCESS read-only
	STATUS current
	DESCRIPTION "Hosts processed in timer func"

	::={hostStatsTimerHosts 2}

hostStatsTimerHostsMax	OBJECT-TYPE
	SYNTAX	 CounterBasedGauge64
	MAX-ACCESS read-only
	STATUS current
	DESCRIPTION "Hosts processed in timer func"

	::={hostStatsTimerHosts 3}

hostStatsTimerHostsLevelTable OBJECT-TYPE
	SYNTAX      SEQUENCE OF HostStatsTimerHostsLevelEntry
	MAX-ACCESS  not-accessible
	STATUS      current
	DESCRIPTION
	"Table for hostStatsTimerHosts"
	::={hostStatsTimerHosts 4}

hostStatsTimerHostsLevelEntry OBJECT-TYPE
	SYNTAX      HostStatsTimerHostsLevelEntry
	MAX-ACCESS  not-accessible
	STATUS      current
	DESCRIPTION
	"Table entry for hostStatsTimerHosts"
	INDEX { hostStatsTimerHostsLevelName }
	::={hostStatsTimerHostsLevelTable 1}

HostStatsTimerHostsLevelEntry ::=
	SEQUENCE {
		hostStatsTimerHostsLevelName	DisplayString,
		hostStatsTimerHostsLevelVal	Counter64,
		hostStatsTimerHostsLevelMom	CounterBasedGauge64,
		hostStatsTimerHostsLevelMax	CounterBasedGauge64
	}

hostStatsTimerHostsLevelName OBJECT-TYPE
	SYNTAX      DisplayString
	MAX-ACCESS  not-accessible
	STATUS      current
	DESCRIPTION
	"Table entry display string for hostStatsTimerHosts"
	::={hostStatsTimerHostsLevelEntry 1}

hostStatsTimerHostsLevelVal OBJECT-TYPE
	SYNTAX	 Counter64
	MAX-ACCESS  read-only
	STATUS      current
	DESCRIPTION
	"Table entry attribute for hostStatsTimerHosts"
	::={hostStatsTimerHostsLevelEntry 2}

hostStatsTimerHostsLevelMom OBJECT-TYPE
	SYNTAX	 CounterBasedGauge64
	MAX-ACCESS  read-only
	STATUS      current
	DESCRIPTION
	"Table entry attribute for hostStatsTimerHosts"
	::={hostStatsTimerHostsLevelEntry 3}

hostStatsTimerHostsLevelMax OBJECT-TYPE
	SYNTAX	 CounterBasedGauge64
	MAX-ACCESS  read-only
	STATUS      current
	DESCRIPTION
	"Table entry attribute for hostStatsTimerHosts"
	::={hostStatsTimerHostsLevelEntry 4}


hostStatsTimerRuns	OBJECT IDENTIFIER ::={hoststats 6}

hostStatsTimerRunsVal	OBJECT-TYPE
	SYNTAX	 Counter64
	MAX-ACCESS read-only
	STATUS current
	DESCRIPTION "Host stats timer runs"

	::={hostStatsTimerRuns 1}

hostStatsTimerRunsMom	OBJECT-TYPE
	SYNTAX	 CounterBasedGauge64
	MAX-ACCESS read-only
	STATUS current
	DESCRIPTION "Host stats timer runs"

	::={hostStatsTimerRuns 2}

hostStatsTimerRunsMax	OBJECT-TYPE
	SYNTAX	 CounterBasedGauge64
	MAX-ACCESS read-only
	STATUS current
	DESCRIPTION "Host stats timer runs"

	::={hostStatsTimerRuns 3}

hostStatsTimerRunsLevelTable OBJECT-TYPE
	SYNTAX      SEQUENCE OF HostStatsTimerRunsLevelEntry
	MAX-ACCESS  not-accessible
	STATUS      current
	DESCRIPTION
	"Table for hostStatsTimerRuns"
	::={hostStatsTimerRuns 4}

hostStatsTimerRunsLevelEntry OBJECT-TYPE
	SYNTAX      HostStatsTimerRunsLevelEntry
	MAX-ACCESS  not-accessible
	STATUS      current
	DESCRIPTION
	"Table entry for hostStatsTimerRuns"
	INDEX { hostStatsTimerRunsLevelName }
	::={hostStatsTimerRunsLevelTable 1}

HostStatsTimerRunsLevelEntry ::=
	SEQUENCE {
		hostStatsTimerRunsLevelName	DisplayString,
		hostStatsTimerRunsLevelVal	Counter64,
		hostStatsTimerRunsLevelMom	CounterBasedGauge64,
		hostStatsTimerRunsLevelMax	CounterBasedGauge64
	}

hostStatsTimerRunsLevelName OBJECT-TYPE
	SYNTAX      DisplayString
	MAX-ACCESS  not-accessible
	STATUS      current
	DESCRIPTION
	"Table entry display string for hostStatsTimerRuns"
	::={hostStatsTimerRunsLevelEntry 1}

hostStatsTimerRunsLevelVal OBJECT-TYPE
	SYNTAX	 Counter64
	MAX-ACCESS  read-only
	STATUS      current
	DESCRIPTION
	"Table entry attribute for hostStatsTimerRuns"
	::={hostStatsTimerRunsLevelEntry 2}

hostStatsTimerRunsLevelMom OBJECT-TYPE
	SYNTAX	 CounterBasedGauge64
	MAX-ACCESS  read-only
	STATUS      current
	DESCRIPTION
	"Table entry attribute for hostStatsTimerRuns"
	::={hostStatsTimerRunsLevelEntry 3}

hostStatsTimerRunsLevelMax OBJECT-TYPE
	SYNTAX	 CounterBasedGauge64
	MAX-ACCESS  read-only
	STATUS      current
	DESCRIPTION
	"Table entry attribute for hostStatsTimerRuns"
	::={hostStatsTimerRunsLevelEntry 4}


hostStatsHostPoolExhausted	OBJECT IDENTIFIER ::={hoststats 7}

hostStatsHostPoolExhaustedVal	OBJECT-TYPE
	SYNTAX	 Counter64
	MAX-ACCESS read-only
	STATUS current
	DESCRIPTION "Host stats host pool exhausted"

	::={hostStatsHostPoolExhausted 1}

hostStatsHostPoolExhaustedMom	OBJECT-TYPE
	SYNTAX	 CounterBasedGauge64
	MAX-ACCESS read-only
	STATUS current
	DESCRIPTION "Host stats host pool exhausted"

	::={hostStatsHostPoolExhausted 2}

hostStatsHostPoolExhaustedMax	OBJECT-TYPE
	SYNTAX	 CounterBasedGauge64
	MAX-ACCESS read-only
	STATUS current
	DESCRIPTION "Host stats host pool exhausted"

	::={hostStatsHostPoolExhausted 3}

hostStatsHostPoolExhaustedLevelTable OBJECT-TYPE
	SYNTAX      SEQUENCE OF HostStatsHostPoolExhaustedLevelEntry
	MAX-ACCESS  not-accessible
	STATUS      current
	DESCRIPTION
	"Table for hostStatsHostPoolExhausted"
	::={hostStatsHostPoolExhausted 4}

hostStatsHostPoolExhaustedLevelEntry OBJECT-TYPE
	SYNTAX      HostStatsHostPoolExhaustedLevelEntry
	MAX-ACCESS  not-accessible
	STATUS      current
	DESCRIPTION
	"Table entry for hostStatsHostPoolExhausted"
	INDEX { hostStatsHostPoolExhaustedLevelName }
	::={hostStatsHostPoolExhaustedLevelTable 1}

HostStatsHostPoolExhaustedLevelEntry ::=
	SEQUENCE {
		hostStatsHostPoolExhaustedLevelName	DisplayString,
		hostStatsHostPoolExhaustedLevelVal	Counter64,
		hostStatsHostPoolExhaustedLevelMom	CounterBasedGauge64,
		hostStatsHostPoolExhaustedLevelMax	CounterBasedGauge64
	}

hostStatsHostPoolExhaustedLevelName OBJECT-TYPE
	SYNTAX      DisplayString
	MAX-ACCESS  not-accessible
	STATUS      current
	DESCRIPTION
	"Table entry display string for hostStatsHostPoolExhausted"
	::={hostStatsHostPoolExhaustedLevelEntry 1}

hostStatsHostPoolExhaustedLevelVal OBJECT-TYPE
	SYNTAX	 Counter64
	MAX-ACCESS  read-only
	STATUS      current
	DESCRIPTION
	"Table entry attribute for hostStatsHostPoolExhausted"
	::={hostStatsHostPoolExhaustedLevelEntry 2}

hostStatsHostPoolExhaustedLevelMom OBJECT-TYPE
	SYNTAX	 CounterBasedGauge64
	MAX-ACCESS  read-only
	STATUS      current
	DESCRIPTION
	"Table entry attribute for hostStatsHostPoolExhausted"
	::={hostStatsHostPoolExhaustedLevelEntry 3}

hostStatsHostPoolExhaustedLevelMax OBJECT-TYPE
	SYNTAX	 CounterBasedGauge64
	MAX-ACCESS  read-only
	STATUS      current
	DESCRIPTION
	"Table entry attribute for hostStatsHostPoolExhausted"
	::={hostStatsHostPoolExhaustedLevelEntry 4}


hostStatsHostsAdded	OBJECT IDENTIFIER ::={hoststats 8}

hostStatsHostsAddedVal	OBJECT-TYPE
	SYNTAX	 Counter64
	MAX-ACCESS read-only
	STATUS current
	DESCRIPTION "Number of hosts added"

	::={hostStatsHostsAdded 1}

hostStatsHostsAddedMom	OBJECT-TYPE
	SYNTAX	 CounterBasedGauge64
	MAX-ACCESS read-only
	STATUS current
	DESCRIPTION "Number of hosts added"

	::={hostStatsHostsAdded 2}

hostStatsHostsAddedMax	OBJECT-TYPE
	SYNTAX	 CounterBasedGauge64
	MAX-ACCESS read-only
	STATUS current
	DESCRIPTION "Number of hosts added"

	::={hostStatsHostsAdded 3}

hostStatsHostsAddedLevelTable OBJECT-TYPE
	SYNTAX      SEQUENCE OF HostStatsHostsAddedLevelEntry
	MAX-ACCESS  not-accessible
	STATUS      current
	DESCRIPTION
	"Table for hostStatsHostsAdded"
	::={hostStatsHostsAdded 4}

hostStatsHostsAddedLevelEntry OBJECT-TYPE
	SYNTAX      HostStatsHostsAddedLevelEntry
	MAX-ACCESS  not-accessible
	STATUS      current
	DESCRIPTION
	"Table entry for hostStatsHostsAdded"
	INDEX { hostStatsHostsAddedLevelName }
	::={hostStatsHostsAddedLevelTable 1}

HostStatsHostsAddedLevelEntry ::=
	SEQUENCE {
		hostStatsHostsAddedLevelName	DisplayString,
		hostStatsHostsAddedLevelVal	Counter64,
		hostStatsHostsAddedLevelMom	CounterBasedGauge64,
		hostStatsHostsAddedLevelMax	CounterBasedGauge64
	}

hostStatsHostsAddedLevelName OBJECT-TYPE
	SYNTAX      DisplayString
	MAX-ACCESS  not-accessible
	STATUS      current
	DESCRIPTION
	"Table entry display string for hostStatsHostsAdded"
	::={hostStatsHostsAddedLevelEntry 1}

hostStatsHostsAddedLevelVal OBJECT-TYPE
	SYNTAX	 Counter64
	MAX-ACCESS  read-only
	STATUS      current
	DESCRIPTION
	"Table entry attribute for hostStatsHostsAdded"
	::={hostStatsHostsAddedLevelEntry 2}

hostStatsHostsAddedLevelMom OBJECT-TYPE
	SYNTAX	 CounterBasedGauge64
	MAX-ACCESS  read-only
	STATUS      current
	DESCRIPTION
	"Table entry attribute for hostStatsHostsAdded"
	::={hostStatsHostsAddedLevelEntry 3}

hostStatsHostsAddedLevelMax OBJECT-TYPE
	SYNTAX	 CounterBasedGauge64
	MAX-ACCESS  read-only
	STATUS      current
	DESCRIPTION
	"Table entry attribute for hostStatsHostsAdded"
	::={hostStatsHostsAddedLevelEntry 4}


hostStatsHostsRemoved	OBJECT IDENTIFIER ::={hoststats 9}

hostStatsHostsRemovedVal	OBJECT-TYPE
	SYNTAX	 Counter64
	MAX-ACCESS read-only
	STATUS current
	DESCRIPTION "Number of hosts removed"

	::={hostStatsHostsRemoved 1}

hostStatsHostsRemovedMom	OBJECT-TYPE
	SYNTAX	 CounterBasedGauge64
	MAX-ACCESS read-only
	STATUS current
	DESCRIPTION "Number of hosts removed"

	::={hostStatsHostsRemoved 2}

hostStatsHostsRemovedMax	OBJECT-TYPE
	SYNTAX	 CounterBasedGauge64
	MAX-ACCESS read-only
	STATUS current
	DESCRIPTION "Number of hosts removed"

	::={hostStatsHostsRemoved 3}

hostStatsHostsRemovedLevelTable OBJECT-TYPE
	SYNTAX      SEQUENCE OF HostStatsHostsRemovedLevelEntry
	MAX-ACCESS  not-accessible
	STATUS      current
	DESCRIPTION
	"Table for hostStatsHostsRemoved"
	::={hostStatsHostsRemoved 4}

hostStatsHostsRemovedLevelEntry OBJECT-TYPE
	SYNTAX      HostStatsHostsRemovedLevelEntry
	MAX-ACCESS  not-accessible
	STATUS      current
	DESCRIPTION
	"Table entry for hostStatsHostsRemoved"
	INDEX { hostStatsHostsRemovedLevelName }
	::={hostStatsHostsRemovedLevelTable 1}

HostStatsHostsRemovedLevelEntry ::=
	SEQUENCE {
		hostStatsHostsRemovedLevelName	DisplayString,
		hostStatsHostsRemovedLevelVal	Counter64,
		hostStatsHostsRemovedLevelMom	CounterBasedGauge64,
		hostStatsHostsRemovedLevelMax	CounterBasedGauge64
	}

hostStatsHostsRemovedLevelName OBJECT-TYPE
	SYNTAX      DisplayString
	MAX-ACCESS  not-accessible
	STATUS      current
	DESCRIPTION
	"Table entry display string for hostStatsHostsRemoved"
	::={hostStatsHostsRemovedLevelEntry 1}

hostStatsHostsRemovedLevelVal OBJECT-TYPE
	SYNTAX	 Counter64
	MAX-ACCESS  read-only
	STATUS      current
	DESCRIPTION
	"Table entry attribute for hostStatsHostsRemoved"
	::={hostStatsHostsRemovedLevelEntry 2}

hostStatsHostsRemovedLevelMom OBJECT-TYPE
	SYNTAX	 CounterBasedGauge64
	MAX-ACCESS  read-only
	STATUS      current
	DESCRIPTION
	"Table entry attribute for hostStatsHostsRemoved"
	::={hostStatsHostsRemovedLevelEntry 3}

hostStatsHostsRemovedLevelMax OBJECT-TYPE
	SYNTAX	 CounterBasedGauge64
	MAX-ACCESS  read-only
	STATUS      current
	DESCRIPTION
	"Table entry attribute for hostStatsHostsRemoved"
	::={hostStatsHostsRemovedLevelEntry 4}


hostStatsVolumeSent	OBJECT IDENTIFIER ::={hoststats 10}

hostStatsVolumeSentVal	OBJECT-TYPE
	SYNTAX	 Counter64
	MAX-ACCESS read-only
	STATUS current
	DESCRIPTION "Volume sent"

	::={hostStatsVolumeSent 1}

hostStatsVolumeSentMom	OBJECT-TYPE
	SYNTAX	 CounterBasedGauge64
	MAX-ACCESS read-only
	STATUS current
	DESCRIPTION "Volume sent"

	::={hostStatsVolumeSent 2}

hostStatsVolumeSentMax	OBJECT-TYPE
	SYNTAX	 CounterBasedGauge64
	MAX-ACCESS read-only
	STATUS current
	DESCRIPTION "Volume sent"

	::={hostStatsVolumeSent 3}

hostStatsVolumeSentLevelTable OBJECT-TYPE
	SYNTAX      SEQUENCE OF HostStatsVolumeSentLevelEntry
	MAX-ACCESS  not-accessible
	STATUS      current
	DESCRIPTION
	"Table for hostStatsVolumeSent"
	::={hostStatsVolumeSent 4}

hostStatsVolumeSentLevelEntry OBJECT-TYPE
	SYNTAX      HostStatsVolumeSentLevelEntry
	MAX-ACCESS  not-accessible
	STATUS      current
	DESCRIPTION
	"Table entry for hostStatsVolumeSent"
	INDEX { hostStatsVolumeSentLevelName }
	::={hostStatsVolumeSentLevelTable 1}

HostStatsVolumeSentLevelEntry ::=
	SEQUENCE {
		hostStatsVolumeSentLevelName	DisplayString,
		hostStatsVolumeSentLevelVal	Counter64,
		hostStatsVolumeSentLevelMom	CounterBasedGauge64,
		hostStatsVolumeSentLevelMax	CounterBasedGauge64
	}

hostStatsVolumeSentLevelName OBJECT-TYPE
	SYNTAX      DisplayString
	MAX-ACCESS  not-accessible
	STATUS      current
	DESCRIPTION
	"Table entry display string for hostStatsVolumeSent"
	::={hostStatsVolumeSentLevelEntry 1}

hostStatsVolumeSentLevelVal OBJECT-TYPE
	SYNTAX	 Counter64
	MAX-ACCESS  read-only
	STATUS      current
	DESCRIPTION
	"Table entry attribute for hostStatsVolumeSent"
	::={hostStatsVolumeSentLevelEntry 2}

hostStatsVolumeSentLevelMom OBJECT-TYPE
	SYNTAX	 CounterBasedGauge64
	MAX-ACCESS  read-only
	STATUS      current
	DESCRIPTION
	"Table entry attribute for hostStatsVolumeSent"
	::={hostStatsVolumeSentLevelEntry 3}

hostStatsVolumeSentLevelMax OBJECT-TYPE
	SYNTAX	 CounterBasedGauge64
	MAX-ACCESS  read-only
	STATUS      current
	DESCRIPTION
	"Table entry attribute for hostStatsVolumeSent"
	::={hostStatsVolumeSentLevelEntry 4}


hostStatsFilteredVolume	OBJECT IDENTIFIER ::={hoststats 11}

hostStatsFilteredVolumeVal	OBJECT-TYPE
	SYNTAX	 Counter64
	MAX-ACCESS read-only
	STATUS current
	DESCRIPTION "Volume filtered"

	::={hostStatsFilteredVolume 1}

hostStatsFilteredVolumeMom	OBJECT-TYPE
	SYNTAX	 CounterBasedGauge64
	MAX-ACCESS read-only
	STATUS current
	DESCRIPTION "Volume filtered"

	::={hostStatsFilteredVolume 2}

hostStatsFilteredVolumeMax	OBJECT-TYPE
	SYNTAX	 CounterBasedGauge64
	MAX-ACCESS read-only
	STATUS current
	DESCRIPTION "Volume filtered"

	::={hostStatsFilteredVolume 3}

hostStatsFilteredVolumeLevelTable OBJECT-TYPE
	SYNTAX      SEQUENCE OF HostStatsFilteredVolumeLevelEntry
	MAX-ACCESS  not-accessible
	STATUS      current
	DESCRIPTION
	"Table for hostStatsFilteredVolume"
	::={hostStatsFilteredVolume 4}

hostStatsFilteredVolumeLevelEntry OBJECT-TYPE
	SYNTAX      HostStatsFilteredVolumeLevelEntry
	MAX-ACCESS  not-accessible
	STATUS      current
	DESCRIPTION
	"Table entry for hostStatsFilteredVolume"
	INDEX { hostStatsFilteredVolumeLevelName }
	::={hostStatsFilteredVolumeLevelTable 1}

HostStatsFilteredVolumeLevelEntry ::=
	SEQUENCE {
		hostStatsFilteredVolumeLevelName	DisplayString,
		hostStatsFilteredVolumeLevelVal	Counter64,
		hostStatsFilteredVolumeLevelMom	CounterBasedGauge64,
		hostStatsFilteredVolumeLevelMax	CounterBasedGauge64
	}

hostStatsFilteredVolumeLevelName OBJECT-TYPE
	SYNTAX      DisplayString
	MAX-ACCESS  not-accessible
	STATUS      current
	DESCRIPTION
	"Table entry display string for hostStatsFilteredVolume"
	::={hostStatsFilteredVolumeLevelEntry 1}

hostStatsFilteredVolumeLevelVal OBJECT-TYPE
	SYNTAX	 Counter64
	MAX-ACCESS  read-only
	STATUS      current
	DESCRIPTION
	"Table entry attribute for hostStatsFilteredVolume"
	::={hostStatsFilteredVolumeLevelEntry 2}

hostStatsFilteredVolumeLevelMom OBJECT-TYPE
	SYNTAX	 CounterBasedGauge64
	MAX-ACCESS  read-only
	STATUS      current
	DESCRIPTION
	"Table entry attribute for hostStatsFilteredVolume"
	::={hostStatsFilteredVolumeLevelEntry 3}

hostStatsFilteredVolumeLevelMax OBJECT-TYPE
	SYNTAX	 CounterBasedGauge64
	MAX-ACCESS  read-only
	STATUS      current
	DESCRIPTION
	"Table entry attribute for hostStatsFilteredVolume"
	::={hostStatsFilteredVolumeLevelEntry 4}


hostStatsMessagesSent	OBJECT IDENTIFIER ::={hoststats 12}

hostStatsMessagesSentVal	OBJECT-TYPE
	SYNTAX	 Counter64
	MAX-ACCESS read-only
	STATUS current
	DESCRIPTION "Messages sent"

	::={hostStatsMessagesSent 1}

hostStatsMessagesSentMom	OBJECT-TYPE
	SYNTAX	 CounterBasedGauge64
	MAX-ACCESS read-only
	STATUS current
	DESCRIPTION "Messages sent"

	::={hostStatsMessagesSent 2}

hostStatsMessagesSentMax	OBJECT-TYPE
	SYNTAX	 CounterBasedGauge64
	MAX-ACCESS read-only
	STATUS current
	DESCRIPTION "Messages sent"

	::={hostStatsMessagesSent 3}

hostStatsMessagesSentLevelTable OBJECT-TYPE
	SYNTAX      SEQUENCE OF HostStatsMessagesSentLevelEntry
	MAX-ACCESS  not-accessible
	STATUS      current
	DESCRIPTION
	"Table for hostStatsMessagesSent"
	::={hostStatsMessagesSent 4}

hostStatsMessagesSentLevelEntry OBJECT-TYPE
	SYNTAX      HostStatsMessagesSentLevelEntry
	MAX-ACCESS  not-accessible
	STATUS      current
	DESCRIPTION
	"Table entry for hostStatsMessagesSent"
	INDEX { hostStatsMessagesSentLevelName }
	::={hostStatsMessagesSentLevelTable 1}

HostStatsMessagesSentLevelEntry ::=
	SEQUENCE {
		hostStatsMessagesSentLevelName	DisplayString,
		hostStatsMessagesSentLevelVal	Counter64,
		hostStatsMessagesSentLevelMom	CounterBasedGauge64,
		hostStatsMessagesSentLevelMax	CounterBasedGauge64
	}

hostStatsMessagesSentLevelName OBJECT-TYPE
	SYNTAX      DisplayString
	MAX-ACCESS  not-accessible
	STATUS      current
	DESCRIPTION
	"Table entry display string for hostStatsMessagesSent"
	::={hostStatsMessagesSentLevelEntry 1}

hostStatsMessagesSentLevelVal OBJECT-TYPE
	SYNTAX	 Counter64
	MAX-ACCESS  read-only
	STATUS      current
	DESCRIPTION
	"Table entry attribute for hostStatsMessagesSent"
	::={hostStatsMessagesSentLevelEntry 2}

hostStatsMessagesSentLevelMom OBJECT-TYPE
	SYNTAX	 CounterBasedGauge64
	MAX-ACCESS  read-only
	STATUS      current
	DESCRIPTION
	"Table entry attribute for hostStatsMessagesSent"
	::={hostStatsMessagesSentLevelEntry 3}

hostStatsMessagesSentLevelMax OBJECT-TYPE
	SYNTAX	 CounterBasedGauge64
	MAX-ACCESS  read-only
	STATUS      current
	DESCRIPTION
	"Table entry attribute for hostStatsMessagesSent"
	::={hostStatsMessagesSentLevelEntry 4}


hostStatsAddConnectionScFails	OBJECT IDENTIFIER ::={hoststats 13}

hostStatsAddConnectionScFailsVal	OBJECT-TYPE
	SYNTAX	 Counter64
	MAX-ACCESS read-only
	STATUS current
	DESCRIPTION "Add connection SC failures"

	::={hostStatsAddConnectionScFails 1}

hostStatsAddConnectionScFailsMom	OBJECT-TYPE
	SYNTAX	 CounterBasedGauge64
	MAX-ACCESS read-only
	STATUS current
	DESCRIPTION "Add connection SC failures"

	::={hostStatsAddConnectionScFails 2}

hostStatsAddConnectionScFailsMax	OBJECT-TYPE
	SYNTAX	 CounterBasedGauge64
	MAX-ACCESS read-only
	STATUS current
	DESCRIPTION "Add connection SC failures"

	::={hostStatsAddConnectionScFails 3}

hostStatsAddConnectionScFailsLevelTable OBJECT-TYPE
	SYNTAX      SEQUENCE OF HostStatsAddConnectionScFailsLevelEntry
	MAX-ACCESS  not-accessible
	STATUS      current
	DESCRIPTION
	"Table for hostStatsAddConnectionScFails"
	::={hostStatsAddConnectionScFails 4}

hostStatsAddConnectionScFailsLevelEntry OBJECT-TYPE
	SYNTAX      HostStatsAddConnectionScFailsLevelEntry
	MAX-ACCESS  not-accessible
	STATUS      current
	DESCRIPTION
	"Table entry for hostStatsAddConnectionScFails"
	INDEX { hostStatsAddConnectionScFailsLevelName }
	::={hostStatsAddConnectionScFailsLevelTable 1}

HostStatsAddConnectionScFailsLevelEntry ::=
	SEQUENCE {
		hostStatsAddConnectionScFailsLevelName	DisplayString,
		hostStatsAddConnectionScFailsLevelVal	Counter64,
		hostStatsAddConnectionScFailsLevelMom	CounterBasedGauge64,
		hostStatsAddConnectionScFailsLevelMax	CounterBasedGauge64
	}

hostStatsAddConnectionScFailsLevelName OBJECT-TYPE
	SYNTAX      DisplayString
	MAX-ACCESS  not-accessible
	STATUS      current
	DESCRIPTION
	"Table entry display string for hostStatsAddConnectionScFails"
	::={hostStatsAddConnectionScFailsLevelEntry 1}

hostStatsAddConnectionScFailsLevelVal OBJECT-TYPE
	SYNTAX	 Counter64
	MAX-ACCESS  read-only
	STATUS      current
	DESCRIPTION
	"Table entry attribute for hostStatsAddConnectionScFails"
	::={hostStatsAddConnectionScFailsLevelEntry 2}

hostStatsAddConnectionScFailsLevelMom OBJECT-TYPE
	SYNTAX	 CounterBasedGauge64
	MAX-ACCESS  read-only
	STATUS      current
	DESCRIPTION
	"Table entry attribute for hostStatsAddConnectionScFails"
	::={hostStatsAddConnectionScFailsLevelEntry 3}

hostStatsAddConnectionScFailsLevelMax OBJECT-TYPE
	SYNTAX	 CounterBasedGauge64
	MAX-ACCESS  read-only
	STATUS      current
	DESCRIPTION
	"Table entry attribute for hostStatsAddConnectionScFails"
	::={hostStatsAddConnectionScFailsLevelEntry 4}


comm	OBJECT IDENTIFIER ::={sysdiag 148}

commServerChannelsOpen	OBJECT IDENTIFIER ::={comm 1}

commServerChannelsOpenVal	OBJECT-TYPE
	SYNTAX	 CounterBasedGauge64
	MAX-ACCESS read-only
	STATUS current
	DESCRIPTION "SERVER: Number of ssh channels open"

	::={commServerChannelsOpen 1}

commServerChannelsOpenMax	OBJECT-TYPE
	SYNTAX	 CounterBasedGauge64
	MAX-ACCESS read-only
	STATUS current
	DESCRIPTION "SERVER: Number of ssh channels open"

	::={commServerChannelsOpen 3}

commServerChannelsOpenLevelTable OBJECT-TYPE
	SYNTAX      SEQUENCE OF CommServerChannelsOpenLevelEntry
	MAX-ACCESS  not-accessible
	STATUS      current
	DESCRIPTION
	"Table for commServerChannelsOpen"
	::={commServerChannelsOpen 4}

commServerChannelsOpenLevelEntry OBJECT-TYPE
	SYNTAX      CommServerChannelsOpenLevelEntry
	MAX-ACCESS  not-accessible
	STATUS      current
	DESCRIPTION
	"Table entry for commServerChannelsOpen"
	INDEX { commServerChannelsOpenLevelName }
	::={commServerChannelsOpenLevelTable 1}

CommServerChannelsOpenLevelEntry ::=
	SEQUENCE {
		commServerChannelsOpenLevelName	DisplayString,
		commServerChannelsOpenLevelVal	CounterBasedGauge64,
		commServerChannelsOpenLevelMax	CounterBasedGauge64
	}

commServerChannelsOpenLevelName OBJECT-TYPE
	SYNTAX      DisplayString
	MAX-ACCESS  not-accessible
	STATUS      current
	DESCRIPTION
	"Table entry display string for commServerChannelsOpen"
	::={commServerChannelsOpenLevelEntry 1}

commServerChannelsOpenLevelVal OBJECT-TYPE
	SYNTAX	 CounterBasedGauge64
	MAX-ACCESS  read-only
	STATUS      current
	DESCRIPTION
	"Table entry attribute for commServerChannelsOpen"
	::={commServerChannelsOpenLevelEntry 2}

commServerChannelsOpenLevelMax OBJECT-TYPE
	SYNTAX	 CounterBasedGauge64
	MAX-ACCESS  read-only
	STATUS      current
	DESCRIPTION
	"Table entry attribute for commServerChannelsOpen"
	::={commServerChannelsOpenLevelEntry 4}


commServerDataTransferred	OBJECT IDENTIFIER ::={comm 2}

commServerDataTransferredVal	OBJECT-TYPE
	SYNTAX	 Counter64
	MAX-ACCESS read-only
	STATUS current
	DESCRIPTION "SERVER: Data transferred by daemon"

	::={commServerDataTransferred 1}

commServerDataTransferredMom	OBJECT-TYPE
	SYNTAX	 CounterBasedGauge64
	MAX-ACCESS read-only
	STATUS current
	DESCRIPTION "SERVER: Data transferred by daemon"

	::={commServerDataTransferred 2}

commServerDataTransferredMax	OBJECT-TYPE
	SYNTAX	 CounterBasedGauge64
	MAX-ACCESS read-only
	STATUS current
	DESCRIPTION "SERVER: Data transferred by daemon"

	::={commServerDataTransferred 3}

commServerDataTransferredLevelTable OBJECT-TYPE
	SYNTAX      SEQUENCE OF CommServerDataTransferredLevelEntry
	MAX-ACCESS  not-accessible
	STATUS      current
	DESCRIPTION
	"Table for commServerDataTransferred"
	::={commServerDataTransferred 4}

commServerDataTransferredLevelEntry OBJECT-TYPE
	SYNTAX      CommServerDataTransferredLevelEntry
	MAX-ACCESS  not-accessible
	STATUS      current
	DESCRIPTION
	"Table entry for commServerDataTransferred"
	INDEX { commServerDataTransferredLevelName }
	::={commServerDataTransferredLevelTable 1}

CommServerDataTransferredLevelEntry ::=
	SEQUENCE {
		commServerDataTransferredLevelName	DisplayString,
		commServerDataTransferredLevelVal	Counter64,
		commServerDataTransferredLevelMom	CounterBasedGauge64,
		commServerDataTransferredLevelMax	CounterBasedGauge64
	}

commServerDataTransferredLevelName OBJECT-TYPE
	SYNTAX      DisplayString
	MAX-ACCESS  not-accessible
	STATUS      current
	DESCRIPTION
	"Table entry display string for commServerDataTransferred"
	::={commServerDataTransferredLevelEntry 1}

commServerDataTransferredLevelVal OBJECT-TYPE
	SYNTAX	 Counter64
	MAX-ACCESS  read-only
	STATUS      current
	DESCRIPTION
	"Table entry attribute for commServerDataTransferred"
	::={commServerDataTransferredLevelEntry 2}

commServerDataTransferredLevelMom OBJECT-TYPE
	SYNTAX	 CounterBasedGauge64
	MAX-ACCESS  read-only
	STATUS      current
	DESCRIPTION
	"Table entry attribute for commServerDataTransferred"
	::={commServerDataTransferredLevelEntry 3}

commServerDataTransferredLevelMax OBJECT-TYPE
	SYNTAX	 CounterBasedGauge64
	MAX-ACCESS  read-only
	STATUS      current
	DESCRIPTION
	"Table entry attribute for commServerDataTransferred"
	::={commServerDataTransferredLevelEntry 4}


commServerClientsConnected	OBJECT IDENTIFIER ::={comm 3}

commServerClientsConnectedVal	OBJECT-TYPE
	SYNTAX	 CounterBasedGauge64
	MAX-ACCESS read-only
	STATUS current
	DESCRIPTION "SERVER: Number of clients connected"

	::={commServerClientsConnected 1}

commServerClientsConnectedMax	OBJECT-TYPE
	SYNTAX	 CounterBasedGauge64
	MAX-ACCESS read-only
	STATUS current
	DESCRIPTION "SERVER: Number of clients connected"

	::={commServerClientsConnected 3}

commServerClientsConnectedLevelTable OBJECT-TYPE
	SYNTAX      SEQUENCE OF CommServerClientsConnectedLevelEntry
	MAX-ACCESS  not-accessible
	STATUS      current
	DESCRIPTION
	"Table for commServerClientsConnected"
	::={commServerClientsConnected 4}

commServerClientsConnectedLevelEntry OBJECT-TYPE
	SYNTAX      CommServerClientsConnectedLevelEntry
	MAX-ACCESS  not-accessible
	STATUS      current
	DESCRIPTION
	"Table entry for commServerClientsConnected"
	INDEX { commServerClientsConnectedLevelName }
	::={commServerClientsConnectedLevelTable 1}

CommServerClientsConnectedLevelEntry ::=
	SEQUENCE {
		commServerClientsConnectedLevelName	DisplayString,
		commServerClientsConnectedLevelVal	CounterBasedGauge64,
		commServerClientsConnectedLevelMax	CounterBasedGauge64
	}

commServerClientsConnectedLevelName OBJECT-TYPE
	SYNTAX      DisplayString
	MAX-ACCESS  not-accessible
	STATUS      current
	DESCRIPTION
	"Table entry display string for commServerClientsConnected"
	::={commServerClientsConnectedLevelEntry 1}

commServerClientsConnectedLevelVal OBJECT-TYPE
	SYNTAX	 CounterBasedGauge64
	MAX-ACCESS  read-only
	STATUS      current
	DESCRIPTION
	"Table entry attribute for commServerClientsConnected"
	::={commServerClientsConnectedLevelEntry 2}

commServerClientsConnectedLevelMax OBJECT-TYPE
	SYNTAX	 CounterBasedGauge64
	MAX-ACCESS  read-only
	STATUS      current
	DESCRIPTION
	"Table entry attribute for commServerClientsConnected"
	::={commServerClientsConnectedLevelEntry 4}


commClientChannelsOpen	OBJECT IDENTIFIER ::={comm 4}

commClientChannelsOpenVal	OBJECT-TYPE
	SYNTAX	 CounterBasedGauge64
	MAX-ACCESS read-only
	STATUS current
	DESCRIPTION "CLIENT: Number of ssh channels open"

	::={commClientChannelsOpen 1}

commClientChannelsOpenMax	OBJECT-TYPE
	SYNTAX	 CounterBasedGauge64
	MAX-ACCESS read-only
	STATUS current
	DESCRIPTION "CLIENT: Number of ssh channels open"

	::={commClientChannelsOpen 3}

commClientChannelsOpenLevelTable OBJECT-TYPE
	SYNTAX      SEQUENCE OF CommClientChannelsOpenLevelEntry
	MAX-ACCESS  not-accessible
	STATUS      current
	DESCRIPTION
	"Table for commClientChannelsOpen"
	::={commClientChannelsOpen 4}

commClientChannelsOpenLevelEntry OBJECT-TYPE
	SYNTAX      CommClientChannelsOpenLevelEntry
	MAX-ACCESS  not-accessible
	STATUS      current
	DESCRIPTION
	"Table entry for commClientChannelsOpen"
	INDEX { commClientChannelsOpenLevelName }
	::={commClientChannelsOpenLevelTable 1}

CommClientChannelsOpenLevelEntry ::=
	SEQUENCE {
		commClientChannelsOpenLevelName	DisplayString,
		commClientChannelsOpenLevelVal	CounterBasedGauge64,
		commClientChannelsOpenLevelMax	CounterBasedGauge64
	}

commClientChannelsOpenLevelName OBJECT-TYPE
	SYNTAX      DisplayString
	MAX-ACCESS  not-accessible
	STATUS      current
	DESCRIPTION
	"Table entry display string for commClientChannelsOpen"
	::={commClientChannelsOpenLevelEntry 1}

commClientChannelsOpenLevelVal OBJECT-TYPE
	SYNTAX	 CounterBasedGauge64
	MAX-ACCESS  read-only
	STATUS      current
	DESCRIPTION
	"Table entry attribute for commClientChannelsOpen"
	::={commClientChannelsOpenLevelEntry 2}

commClientChannelsOpenLevelMax OBJECT-TYPE
	SYNTAX	 CounterBasedGauge64
	MAX-ACCESS  read-only
	STATUS      current
	DESCRIPTION
	"Table entry attribute for commClientChannelsOpen"
	::={commClientChannelsOpenLevelEntry 4}


commClientDataTransferred	OBJECT IDENTIFIER ::={comm 5}

commClientDataTransferredVal	OBJECT-TYPE
	SYNTAX	 Counter64
	MAX-ACCESS read-only
	STATUS current
	DESCRIPTION "CLIENT: Data transferred by daemon"

	::={commClientDataTransferred 1}

commClientDataTransferredMom	OBJECT-TYPE
	SYNTAX	 CounterBasedGauge64
	MAX-ACCESS read-only
	STATUS current
	DESCRIPTION "CLIENT: Data transferred by daemon"

	::={commClientDataTransferred 2}

commClientDataTransferredMax	OBJECT-TYPE
	SYNTAX	 CounterBasedGauge64
	MAX-ACCESS read-only
	STATUS current
	DESCRIPTION "CLIENT: Data transferred by daemon"

	::={commClientDataTransferred 3}

commClientDataTransferredLevelTable OBJECT-TYPE
	SYNTAX      SEQUENCE OF CommClientDataTransferredLevelEntry
	MAX-ACCESS  not-accessible
	STATUS      current
	DESCRIPTION
	"Table for commClientDataTransferred"
	::={commClientDataTransferred 4}

commClientDataTransferredLevelEntry OBJECT-TYPE
	SYNTAX      CommClientDataTransferredLevelEntry
	MAX-ACCESS  not-accessible
	STATUS      current
	DESCRIPTION
	"Table entry for commClientDataTransferred"
	INDEX { commClientDataTransferredLevelName }
	::={commClientDataTransferredLevelTable 1}

CommClientDataTransferredLevelEntry ::=
	SEQUENCE {
		commClientDataTransferredLevelName	DisplayString,
		commClientDataTransferredLevelVal	Counter64,
		commClientDataTransferredLevelMom	CounterBasedGauge64,
		commClientDataTransferredLevelMax	CounterBasedGauge64
	}

commClientDataTransferredLevelName OBJECT-TYPE
	SYNTAX      DisplayString
	MAX-ACCESS  not-accessible
	STATUS      current
	DESCRIPTION
	"Table entry display string for commClientDataTransferred"
	::={commClientDataTransferredLevelEntry 1}

commClientDataTransferredLevelVal OBJECT-TYPE
	SYNTAX	 Counter64
	MAX-ACCESS  read-only
	STATUS      current
	DESCRIPTION
	"Table entry attribute for commClientDataTransferred"
	::={commClientDataTransferredLevelEntry 2}

commClientDataTransferredLevelMom OBJECT-TYPE
	SYNTAX	 CounterBasedGauge64
	MAX-ACCESS  read-only
	STATUS      current
	DESCRIPTION
	"Table entry attribute for commClientDataTransferred"
	::={commClientDataTransferredLevelEntry 3}

commClientDataTransferredLevelMax OBJECT-TYPE
	SYNTAX	 CounterBasedGauge64
	MAX-ACCESS  read-only
	STATUS      current
	DESCRIPTION
	"Table entry attribute for commClientDataTransferred"
	::={commClientDataTransferredLevelEntry 4}


commClientAuthenticationFailures	OBJECT IDENTIFIER ::={comm 6}

commClientAuthenticationFailuresVal	OBJECT-TYPE
	SYNTAX	 Counter64
	MAX-ACCESS read-only
	STATUS current
	DESCRIPTION "CLIENT: Authentication failures"

	::={commClientAuthenticationFailures 1}

commClientAuthenticationFailuresMom	OBJECT-TYPE
	SYNTAX	 CounterBasedGauge64
	MAX-ACCESS read-only
	STATUS current
	DESCRIPTION "CLIENT: Authentication failures"

	::={commClientAuthenticationFailures 2}

commClientAuthenticationFailuresMax	OBJECT-TYPE
	SYNTAX	 CounterBasedGauge64
	MAX-ACCESS read-only
	STATUS current
	DESCRIPTION "CLIENT: Authentication failures"

	::={commClientAuthenticationFailures 3}

commClientAuthenticationFailuresLevelTable OBJECT-TYPE
	SYNTAX      SEQUENCE OF CommClientAuthenticationFailuresLevelEntry
	MAX-ACCESS  not-accessible
	STATUS      current
	DESCRIPTION
	"Table for commClientAuthenticationFailures"
	::={commClientAuthenticationFailures 4}

commClientAuthenticationFailuresLevelEntry OBJECT-TYPE
	SYNTAX      CommClientAuthenticationFailuresLevelEntry
	MAX-ACCESS  not-accessible
	STATUS      current
	DESCRIPTION
	"Table entry for commClientAuthenticationFailures"
	INDEX { commClientAuthenticationFailuresLevelName }
	::={commClientAuthenticationFailuresLevelTable 1}

CommClientAuthenticationFailuresLevelEntry ::=
	SEQUENCE {
		commClientAuthenticationFailuresLevelName	DisplayString,
		commClientAuthenticationFailuresLevelVal	Counter64,
		commClientAuthenticationFailuresLevelMom	CounterBasedGauge64,
		commClientAuthenticationFailuresLevelMax	CounterBasedGauge64
	}

commClientAuthenticationFailuresLevelName OBJECT-TYPE
	SYNTAX      DisplayString
	MAX-ACCESS  not-accessible
	STATUS      current
	DESCRIPTION
	"Table entry display string for commClientAuthenticationFailures"
	::={commClientAuthenticationFailuresLevelEntry 1}

commClientAuthenticationFailuresLevelVal OBJECT-TYPE
	SYNTAX	 Counter64
	MAX-ACCESS  read-only
	STATUS      current
	DESCRIPTION
	"Table entry attribute for commClientAuthenticationFailures"
	::={commClientAuthenticationFailuresLevelEntry 2}

commClientAuthenticationFailuresLevelMom OBJECT-TYPE
	SYNTAX	 CounterBasedGauge64
	MAX-ACCESS  read-only
	STATUS      current
	DESCRIPTION
	"Table entry attribute for commClientAuthenticationFailures"
	::={commClientAuthenticationFailuresLevelEntry 3}

commClientAuthenticationFailuresLevelMax OBJECT-TYPE
	SYNTAX	 CounterBasedGauge64
	MAX-ACCESS  read-only
	STATUS      current
	DESCRIPTION
	"Table entry attribute for commClientAuthenticationFailures"
	::={commClientAuthenticationFailuresLevelEntry 4}


commClientHostKeyFailures	OBJECT IDENTIFIER ::={comm 7}

commClientHostKeyFailuresVal	OBJECT-TYPE
	SYNTAX	 Counter64
	MAX-ACCESS read-only
	STATUS current
	DESCRIPTION "CLIENT: Host key verification failures"

	::={commClientHostKeyFailures 1}

commClientHostKeyFailuresMom	OBJECT-TYPE
	SYNTAX	 CounterBasedGauge64
	MAX-ACCESS read-only
	STATUS current
	DESCRIPTION "CLIENT: Host key verification failures"

	::={commClientHostKeyFailures 2}

commClientHostKeyFailuresMax	OBJECT-TYPE
	SYNTAX	 CounterBasedGauge64
	MAX-ACCESS read-only
	STATUS current
	DESCRIPTION "CLIENT: Host key verification failures"

	::={commClientHostKeyFailures 3}

commClientHostKeyFailuresLevelTable OBJECT-TYPE
	SYNTAX      SEQUENCE OF CommClientHostKeyFailuresLevelEntry
	MAX-ACCESS  not-accessible
	STATUS      current
	DESCRIPTION
	"Table for commClientHostKeyFailures"
	::={commClientHostKeyFailures 4}

commClientHostKeyFailuresLevelEntry OBJECT-TYPE
	SYNTAX      CommClientHostKeyFailuresLevelEntry
	MAX-ACCESS  not-accessible
	STATUS      current
	DESCRIPTION
	"Table entry for commClientHostKeyFailures"
	INDEX { commClientHostKeyFailuresLevelName }
	::={commClientHostKeyFailuresLevelTable 1}

CommClientHostKeyFailuresLevelEntry ::=
	SEQUENCE {
		commClientHostKeyFailuresLevelName	DisplayString,
		commClientHostKeyFailuresLevelVal	Counter64,
		commClientHostKeyFailuresLevelMom	CounterBasedGauge64,
		commClientHostKeyFailuresLevelMax	CounterBasedGauge64
	}

commClientHostKeyFailuresLevelName OBJECT-TYPE
	SYNTAX      DisplayString
	MAX-ACCESS  not-accessible
	STATUS      current
	DESCRIPTION
	"Table entry display string for commClientHostKeyFailures"
	::={commClientHostKeyFailuresLevelEntry 1}

commClientHostKeyFailuresLevelVal OBJECT-TYPE
	SYNTAX	 Counter64
	MAX-ACCESS  read-only
	STATUS      current
	DESCRIPTION
	"Table entry attribute for commClientHostKeyFailures"
	::={commClientHostKeyFailuresLevelEntry 2}

commClientHostKeyFailuresLevelMom OBJECT-TYPE
	SYNTAX	 CounterBasedGauge64
	MAX-ACCESS  read-only
	STATUS      current
	DESCRIPTION
	"Table entry attribute for commClientHostKeyFailures"
	::={commClientHostKeyFailuresLevelEntry 3}

commClientHostKeyFailuresLevelMax OBJECT-TYPE
	SYNTAX	 CounterBasedGauge64
	MAX-ACCESS  read-only
	STATUS      current
	DESCRIPTION
	"Table entry attribute for commClientHostKeyFailures"
	::={commClientHostKeyFailuresLevelEntry 4}


commClientConnectFailures	OBJECT IDENTIFIER ::={comm 8}

commClientConnectFailuresVal	OBJECT-TYPE
	SYNTAX	 Counter64
	MAX-ACCESS read-only
	STATUS current
	DESCRIPTION "CLIENT: Connect failures"

	::={commClientConnectFailures 1}

commClientConnectFailuresMom	OBJECT-TYPE
	SYNTAX	 CounterBasedGauge64
	MAX-ACCESS read-only
	STATUS current
	DESCRIPTION "CLIENT: Connect failures"

	::={commClientConnectFailures 2}

commClientConnectFailuresMax	OBJECT-TYPE
	SYNTAX	 CounterBasedGauge64
	MAX-ACCESS read-only
	STATUS current
	DESCRIPTION "CLIENT: Connect failures"

	::={commClientConnectFailures 3}

commClientConnectFailuresLevelTable OBJECT-TYPE
	SYNTAX      SEQUENCE OF CommClientConnectFailuresLevelEntry
	MAX-ACCESS  not-accessible
	STATUS      current
	DESCRIPTION
	"Table for commClientConnectFailures"
	::={commClientConnectFailures 4}

commClientConnectFailuresLevelEntry OBJECT-TYPE
	SYNTAX      CommClientConnectFailuresLevelEntry
	MAX-ACCESS  not-accessible
	STATUS      current
	DESCRIPTION
	"Table entry for commClientConnectFailures"
	INDEX { commClientConnectFailuresLevelName }
	::={commClientConnectFailuresLevelTable 1}

CommClientConnectFailuresLevelEntry ::=
	SEQUENCE {
		commClientConnectFailuresLevelName	DisplayString,
		commClientConnectFailuresLevelVal	Counter64,
		commClientConnectFailuresLevelMom	CounterBasedGauge64,
		commClientConnectFailuresLevelMax	CounterBasedGauge64
	}

commClientConnectFailuresLevelName OBJECT-TYPE
	SYNTAX      DisplayString
	MAX-ACCESS  not-accessible
	STATUS      current
	DESCRIPTION
	"Table entry display string for commClientConnectFailures"
	::={commClientConnectFailuresLevelEntry 1}

commClientConnectFailuresLevelVal OBJECT-TYPE
	SYNTAX	 Counter64
	MAX-ACCESS  read-only
	STATUS      current
	DESCRIPTION
	"Table entry attribute for commClientConnectFailures"
	::={commClientConnectFailuresLevelEntry 2}

commClientConnectFailuresLevelMom OBJECT-TYPE
	SYNTAX	 CounterBasedGauge64
	MAX-ACCESS  read-only
	STATUS      current
	DESCRIPTION
	"Table entry attribute for commClientConnectFailures"
	::={commClientConnectFailuresLevelEntry 3}

commClientConnectFailuresLevelMax OBJECT-TYPE
	SYNTAX	 CounterBasedGauge64
	MAX-ACCESS  read-only
	STATUS      current
	DESCRIPTION
	"Table entry attribute for commClientConnectFailures"
	::={commClientConnectFailuresLevelEntry 4}


sessionContextEngine	OBJECT IDENTIFIER ::={sysdiag 150}

sessionContextEngineActiveSchema	OBJECT IDENTIFIER ::={sessionContextEngine 1}

sessionContextEngineActiveSchemaVal	OBJECT-TYPE
	SYNTAX	 CounterBasedGauge64
	MAX-ACCESS read-only
	STATUS current
	DESCRIPTION "Active schema"

	::={sessionContextEngineActiveSchema 1}

sessionContextEngineActiveSchemaMax	OBJECT-TYPE
	SYNTAX	 CounterBasedGauge64
	MAX-ACCESS read-only
	STATUS current
	DESCRIPTION "Active schema"

	::={sessionContextEngineActiveSchema 3}

sessionContextEngineActiveSchemaLevelTable OBJECT-TYPE
	SYNTAX      SEQUENCE OF SessionContextEngineActiveSchemaLevelEntry
	MAX-ACCESS  not-accessible
	STATUS      current
	DESCRIPTION
	"Table for sessionContextEngineActiveSchema"
	::={sessionContextEngineActiveSchema 4}

sessionContextEngineActiveSchemaLevelEntry OBJECT-TYPE
	SYNTAX      SessionContextEngineActiveSchemaLevelEntry
	MAX-ACCESS  not-accessible
	STATUS      current
	DESCRIPTION
	"Table entry for sessionContextEngineActiveSchema"
	INDEX { sessionContextEngineActiveSchemaLevelName }
	::={sessionContextEngineActiveSchemaLevelTable 1}

SessionContextEngineActiveSchemaLevelEntry ::=
	SEQUENCE {
		sessionContextEngineActiveSchemaLevelName	DisplayString,
		sessionContextEngineActiveSchemaLevelVal	CounterBasedGauge64,
		sessionContextEngineActiveSchemaLevelMax	CounterBasedGauge64
	}

sessionContextEngineActiveSchemaLevelName OBJECT-TYPE
	SYNTAX      DisplayString
	MAX-ACCESS  not-accessible
	STATUS      current
	DESCRIPTION
	"Table entry display string for sessionContextEngineActiveSchema"
	::={sessionContextEngineActiveSchemaLevelEntry 1}

sessionContextEngineActiveSchemaLevelVal OBJECT-TYPE
	SYNTAX	 CounterBasedGauge64
	MAX-ACCESS  read-only
	STATUS      current
	DESCRIPTION
	"Table entry attribute for sessionContextEngineActiveSchema"
	::={sessionContextEngineActiveSchemaLevelEntry 2}

sessionContextEngineActiveSchemaLevelMax OBJECT-TYPE
	SYNTAX	 CounterBasedGauge64
	MAX-ACCESS  read-only
	STATUS      current
	DESCRIPTION
	"Table entry attribute for sessionContextEngineActiveSchema"
	::={sessionContextEngineActiveSchemaLevelEntry 4}


sessionContextEngineRowsTotal	OBJECT IDENTIFIER ::={sessionContextEngine 2}

sessionContextEngineRowsTotalVal	OBJECT-TYPE
	SYNTAX	 CounterBasedGauge64
	MAX-ACCESS read-only
	STATUS current
	DESCRIPTION "Row count (total)"

	::={sessionContextEngineRowsTotal 1}

sessionContextEngineRowsTotalMax	OBJECT-TYPE
	SYNTAX	 CounterBasedGauge64
	MAX-ACCESS read-only
	STATUS current
	DESCRIPTION "Row count (total)"

	::={sessionContextEngineRowsTotal 3}

sessionContextEngineRowsTotalLevelTable OBJECT-TYPE
	SYNTAX      SEQUENCE OF SessionContextEngineRowsTotalLevelEntry
	MAX-ACCESS  not-accessible
	STATUS      current
	DESCRIPTION
	"Table for sessionContextEngineRowsTotal"
	::={sessionContextEngineRowsTotal 4}

sessionContextEngineRowsTotalLevelEntry OBJECT-TYPE
	SYNTAX      SessionContextEngineRowsTotalLevelEntry
	MAX-ACCESS  not-accessible
	STATUS      current
	DESCRIPTION
	"Table entry for sessionContextEngineRowsTotal"
	INDEX { sessionContextEngineRowsTotalLevelName }
	::={sessionContextEngineRowsTotalLevelTable 1}

SessionContextEngineRowsTotalLevelEntry ::=
	SEQUENCE {
		sessionContextEngineRowsTotalLevelName	DisplayString,
		sessionContextEngineRowsTotalLevelVal	CounterBasedGauge64,
		sessionContextEngineRowsTotalLevelMax	CounterBasedGauge64
	}

sessionContextEngineRowsTotalLevelName OBJECT-TYPE
	SYNTAX      DisplayString
	MAX-ACCESS  not-accessible
	STATUS      current
	DESCRIPTION
	"Table entry display string for sessionContextEngineRowsTotal"
	::={sessionContextEngineRowsTotalLevelEntry 1}

sessionContextEngineRowsTotalLevelVal OBJECT-TYPE
	SYNTAX	 CounterBasedGauge64
	MAX-ACCESS  read-only
	STATUS      current
	DESCRIPTION
	"Table entry attribute for sessionContextEngineRowsTotal"
	::={sessionContextEngineRowsTotalLevelEntry 2}

sessionContextEngineRowsTotalLevelMax OBJECT-TYPE
	SYNTAX	 CounterBasedGauge64
	MAX-ACCESS  read-only
	STATUS      current
	DESCRIPTION
	"Table entry attribute for sessionContextEngineRowsTotal"
	::={sessionContextEngineRowsTotalLevelEntry 4}


sessionContextEngineRowsInTable	OBJECT IDENTIFIER ::={sessionContextEngine 3}

sessionContextEngineRowsInTableVal	OBJECT-TYPE
	SYNTAX	 CounterBasedGauge64
	MAX-ACCESS read-only
	STATUS current
	DESCRIPTION "Row count (in table)"

	::={sessionContextEngineRowsInTable 1}

sessionContextEngineRowsInTableMax	OBJECT-TYPE
	SYNTAX	 CounterBasedGauge64
	MAX-ACCESS read-only
	STATUS current
	DESCRIPTION "Row count (in table)"

	::={sessionContextEngineRowsInTable 3}

sessionContextEngineRowsInTableLevelTable OBJECT-TYPE
	SYNTAX      SEQUENCE OF SessionContextEngineRowsInTableLevelEntry
	MAX-ACCESS  not-accessible
	STATUS      current
	DESCRIPTION
	"Table for sessionContextEngineRowsInTable"
	::={sessionContextEngineRowsInTable 4}

sessionContextEngineRowsInTableLevelEntry OBJECT-TYPE
	SYNTAX      SessionContextEngineRowsInTableLevelEntry
	MAX-ACCESS  not-accessible
	STATUS      current
	DESCRIPTION
	"Table entry for sessionContextEngineRowsInTable"
	INDEX { sessionContextEngineRowsInTableLevelName }
	::={sessionContextEngineRowsInTableLevelTable 1}

SessionContextEngineRowsInTableLevelEntry ::=
	SEQUENCE {
		sessionContextEngineRowsInTableLevelName	DisplayString,
		sessionContextEngineRowsInTableLevelVal	CounterBasedGauge64,
		sessionContextEngineRowsInTableLevelMax	CounterBasedGauge64
	}

sessionContextEngineRowsInTableLevelName OBJECT-TYPE
	SYNTAX      DisplayString
	MAX-ACCESS  not-accessible
	STATUS      current
	DESCRIPTION
	"Table entry display string for sessionContextEngineRowsInTable"
	::={sessionContextEngineRowsInTableLevelEntry 1}

sessionContextEngineRowsInTableLevelVal OBJECT-TYPE
	SYNTAX	 CounterBasedGauge64
	MAX-ACCESS  read-only
	STATUS      current
	DESCRIPTION
	"Table entry attribute for sessionContextEngineRowsInTable"
	::={sessionContextEngineRowsInTableLevelEntry 2}

sessionContextEngineRowsInTableLevelMax OBJECT-TYPE
	SYNTAX	 CounterBasedGauge64
	MAX-ACCESS  read-only
	STATUS      current
	DESCRIPTION
	"Table entry attribute for sessionContextEngineRowsInTable"
	::={sessionContextEngineRowsInTableLevelEntry 4}


sessionContextEngineTooManyOnConnection	OBJECT IDENTIFIER ::={sessionContextEngine 4}

sessionContextEngineTooManyOnConnectionVal	OBJECT-TYPE
	SYNTAX	 Counter64
	MAX-ACCESS read-only
	STATUS current
	DESCRIPTION "Too many sessions context entries matching single connection"

	::={sessionContextEngineTooManyOnConnection 1}

sessionContextEngineTooManyOnConnectionMom	OBJECT-TYPE
	SYNTAX	 CounterBasedGauge64
	MAX-ACCESS read-only
	STATUS current
	DESCRIPTION "Too many sessions context entries matching single connection"

	::={sessionContextEngineTooManyOnConnection 2}

sessionContextEngineTooManyOnConnectionMax	OBJECT-TYPE
	SYNTAX	 CounterBasedGauge64
	MAX-ACCESS read-only
	STATUS current
	DESCRIPTION "Too many sessions context entries matching single connection"

	::={sessionContextEngineTooManyOnConnection 3}

sessionContextEngineTooManyOnConnectionLevelTable OBJECT-TYPE
	SYNTAX      SEQUENCE OF SessionContextEngineTooManyOnConnectionLevelEntry
	MAX-ACCESS  not-accessible
	STATUS      current
	DESCRIPTION
	"Table for sessionContextEngineTooManyOnConnection"
	::={sessionContextEngineTooManyOnConnection 4}

sessionContextEngineTooManyOnConnectionLevelEntry OBJECT-TYPE
	SYNTAX      SessionContextEngineTooManyOnConnectionLevelEntry
	MAX-ACCESS  not-accessible
	STATUS      current
	DESCRIPTION
	"Table entry for sessionContextEngineTooManyOnConnection"
	INDEX { sessionContextEngineTooManyOnConnectionLevelName }
	::={sessionContextEngineTooManyOnConnectionLevelTable 1}

SessionContextEngineTooManyOnConnectionLevelEntry ::=
	SEQUENCE {
		sessionContextEngineTooManyOnConnectionLevelName	DisplayString,
		sessionContextEngineTooManyOnConnectionLevelVal	Counter64,
		sessionContextEngineTooManyOnConnectionLevelMom	CounterBasedGauge64,
		sessionContextEngineTooManyOnConnectionLevelMax	CounterBasedGauge64
	}

sessionContextEngineTooManyOnConnectionLevelName OBJECT-TYPE
	SYNTAX      DisplayString
	MAX-ACCESS  not-accessible
	STATUS      current
	DESCRIPTION
	"Table entry display string for sessionContextEngineTooManyOnConnection"
	::={sessionContextEngineTooManyOnConnectionLevelEntry 1}

sessionContextEngineTooManyOnConnectionLevelVal OBJECT-TYPE
	SYNTAX	 Counter64
	MAX-ACCESS  read-only
	STATUS      current
	DESCRIPTION
	"Table entry attribute for sessionContextEngineTooManyOnConnection"
	::={sessionContextEngineTooManyOnConnectionLevelEntry 2}

sessionContextEngineTooManyOnConnectionLevelMom OBJECT-TYPE
	SYNTAX	 CounterBasedGauge64
	MAX-ACCESS  read-only
	STATUS      current
	DESCRIPTION
	"Table entry attribute for sessionContextEngineTooManyOnConnection"
	::={sessionContextEngineTooManyOnConnectionLevelEntry 3}

sessionContextEngineTooManyOnConnectionLevelMax OBJECT-TYPE
	SYNTAX	 CounterBasedGauge64
	MAX-ACCESS  read-only
	STATUS      current
	DESCRIPTION
	"Table entry attribute for sessionContextEngineTooManyOnConnection"
	::={sessionContextEngineTooManyOnConnectionLevelEntry 4}


sessionContextEngineBlobstoreEntries32	OBJECT IDENTIFIER ::={sessionContextEngine 5}

sessionContextEngineBlobstoreEntries32Val	OBJECT-TYPE
	SYNTAX	 CounterBasedGauge64
	MAX-ACCESS read-only
	STATUS current
	DESCRIPTION "Blobstore - used entries (32)"

	::={sessionContextEngineBlobstoreEntries32 1}

sessionContextEngineBlobstoreEntries32Max	OBJECT-TYPE
	SYNTAX	 CounterBasedGauge64
	MAX-ACCESS read-only
	STATUS current
	DESCRIPTION "Blobstore - used entries (32)"

	::={sessionContextEngineBlobstoreEntries32 3}

sessionContextEngineBlobstoreEntries32LevelTable OBJECT-TYPE
	SYNTAX      SEQUENCE OF SessionContextEngineBlobstoreEntries32LevelEntry
	MAX-ACCESS  not-accessible
	STATUS      current
	DESCRIPTION
	"Table for sessionContextEngineBlobstoreEntries32"
	::={sessionContextEngineBlobstoreEntries32 4}

sessionContextEngineBlobstoreEntries32LevelEntry OBJECT-TYPE
	SYNTAX      SessionContextEngineBlobstoreEntries32LevelEntry
	MAX-ACCESS  not-accessible
	STATUS      current
	DESCRIPTION
	"Table entry for sessionContextEngineBlobstoreEntries32"
	INDEX { sessionContextEngineBlobstoreEntries32LevelName }
	::={sessionContextEngineBlobstoreEntries32LevelTable 1}

SessionContextEngineBlobstoreEntries32LevelEntry ::=
	SEQUENCE {
		sessionContextEngineBlobstoreEntries32LevelName	DisplayString,
		sessionContextEngineBlobstoreEntries32LevelVal	CounterBasedGauge64,
		sessionContextEngineBlobstoreEntries32LevelMax	CounterBasedGauge64
	}

sessionContextEngineBlobstoreEntries32LevelName OBJECT-TYPE
	SYNTAX      DisplayString
	MAX-ACCESS  not-accessible
	STATUS      current
	DESCRIPTION
	"Table entry display string for sessionContextEngineBlobstoreEntries32"
	::={sessionContextEngineBlobstoreEntries32LevelEntry 1}

sessionContextEngineBlobstoreEntries32LevelVal OBJECT-TYPE
	SYNTAX	 CounterBasedGauge64
	MAX-ACCESS  read-only
	STATUS      current
	DESCRIPTION
	"Table entry attribute for sessionContextEngineBlobstoreEntries32"
	::={sessionContextEngineBlobstoreEntries32LevelEntry 2}

sessionContextEngineBlobstoreEntries32LevelMax OBJECT-TYPE
	SYNTAX	 CounterBasedGauge64
	MAX-ACCESS  read-only
	STATUS      current
	DESCRIPTION
	"Table entry attribute for sessionContextEngineBlobstoreEntries32"
	::={sessionContextEngineBlobstoreEntries32LevelEntry 4}


sessionContextEngineBlobstoreEntries64	OBJECT IDENTIFIER ::={sessionContextEngine 6}

sessionContextEngineBlobstoreEntries64Val	OBJECT-TYPE
	SYNTAX	 CounterBasedGauge64
	MAX-ACCESS read-only
	STATUS current
	DESCRIPTION "Blobstore - used entries (64)"

	::={sessionContextEngineBlobstoreEntries64 1}

sessionContextEngineBlobstoreEntries64Max	OBJECT-TYPE
	SYNTAX	 CounterBasedGauge64
	MAX-ACCESS read-only
	STATUS current
	DESCRIPTION "Blobstore - used entries (64)"

	::={sessionContextEngineBlobstoreEntries64 3}

sessionContextEngineBlobstoreEntries64LevelTable OBJECT-TYPE
	SYNTAX      SEQUENCE OF SessionContextEngineBlobstoreEntries64LevelEntry
	MAX-ACCESS  not-accessible
	STATUS      current
	DESCRIPTION
	"Table for sessionContextEngineBlobstoreEntries64"
	::={sessionContextEngineBlobstoreEntries64 4}

sessionContextEngineBlobstoreEntries64LevelEntry OBJECT-TYPE
	SYNTAX      SessionContextEngineBlobstoreEntries64LevelEntry
	MAX-ACCESS  not-accessible
	STATUS      current
	DESCRIPTION
	"Table entry for sessionContextEngineBlobstoreEntries64"
	INDEX { sessionContextEngineBlobstoreEntries64LevelName }
	::={sessionContextEngineBlobstoreEntries64LevelTable 1}

SessionContextEngineBlobstoreEntries64LevelEntry ::=
	SEQUENCE {
		sessionContextEngineBlobstoreEntries64LevelName	DisplayString,
		sessionContextEngineBlobstoreEntries64LevelVal	CounterBasedGauge64,
		sessionContextEngineBlobstoreEntries64LevelMax	CounterBasedGauge64
	}

sessionContextEngineBlobstoreEntries64LevelName OBJECT-TYPE
	SYNTAX      DisplayString
	MAX-ACCESS  not-accessible
	STATUS      current
	DESCRIPTION
	"Table entry display string for sessionContextEngineBlobstoreEntries64"
	::={sessionContextEngineBlobstoreEntries64LevelEntry 1}

sessionContextEngineBlobstoreEntries64LevelVal OBJECT-TYPE
	SYNTAX	 CounterBasedGauge64
	MAX-ACCESS  read-only
	STATUS      current
	DESCRIPTION
	"Table entry attribute for sessionContextEngineBlobstoreEntries64"
	::={sessionContextEngineBlobstoreEntries64LevelEntry 2}

sessionContextEngineBlobstoreEntries64LevelMax OBJECT-TYPE
	SYNTAX	 CounterBasedGauge64
	MAX-ACCESS  read-only
	STATUS      current
	DESCRIPTION
	"Table entry attribute for sessionContextEngineBlobstoreEntries64"
	::={sessionContextEngineBlobstoreEntries64LevelEntry 4}


sessionContextEngineBlobstoreEntries512	OBJECT IDENTIFIER ::={sessionContextEngine 7}

sessionContextEngineBlobstoreEntries512Val	OBJECT-TYPE
	SYNTAX	 CounterBasedGauge64
	MAX-ACCESS read-only
	STATUS current
	DESCRIPTION "Blobstore - used entries (512)"

	::={sessionContextEngineBlobstoreEntries512 1}

sessionContextEngineBlobstoreEntries512Max	OBJECT-TYPE
	SYNTAX	 CounterBasedGauge64
	MAX-ACCESS read-only
	STATUS current
	DESCRIPTION "Blobstore - used entries (512)"

	::={sessionContextEngineBlobstoreEntries512 3}

sessionContextEngineBlobstoreEntries512LevelTable OBJECT-TYPE
	SYNTAX      SEQUENCE OF SessionContextEngineBlobstoreEntries512LevelEntry
	MAX-ACCESS  not-accessible
	STATUS      current
	DESCRIPTION
	"Table for sessionContextEngineBlobstoreEntries512"
	::={sessionContextEngineBlobstoreEntries512 4}

sessionContextEngineBlobstoreEntries512LevelEntry OBJECT-TYPE
	SYNTAX      SessionContextEngineBlobstoreEntries512LevelEntry
	MAX-ACCESS  not-accessible
	STATUS      current
	DESCRIPTION
	"Table entry for sessionContextEngineBlobstoreEntries512"
	INDEX { sessionContextEngineBlobstoreEntries512LevelName }
	::={sessionContextEngineBlobstoreEntries512LevelTable 1}

SessionContextEngineBlobstoreEntries512LevelEntry ::=
	SEQUENCE {
		sessionContextEngineBlobstoreEntries512LevelName	DisplayString,
		sessionContextEngineBlobstoreEntries512LevelVal	CounterBasedGauge64,
		sessionContextEngineBlobstoreEntries512LevelMax	CounterBasedGauge64
	}

sessionContextEngineBlobstoreEntries512LevelName OBJECT-TYPE
	SYNTAX      DisplayString
	MAX-ACCESS  not-accessible
	STATUS      current
	DESCRIPTION
	"Table entry display string for sessionContextEngineBlobstoreEntries512"
	::={sessionContextEngineBlobstoreEntries512LevelEntry 1}

sessionContextEngineBlobstoreEntries512LevelVal OBJECT-TYPE
	SYNTAX	 CounterBasedGauge64
	MAX-ACCESS  read-only
	STATUS      current
	DESCRIPTION
	"Table entry attribute for sessionContextEngineBlobstoreEntries512"
	::={sessionContextEngineBlobstoreEntries512LevelEntry 2}

sessionContextEngineBlobstoreEntries512LevelMax OBJECT-TYPE
	SYNTAX	 CounterBasedGauge64
	MAX-ACCESS  read-only
	STATUS      current
	DESCRIPTION
	"Table entry attribute for sessionContextEngineBlobstoreEntries512"
	::={sessionContextEngineBlobstoreEntries512LevelEntry 4}


sessionContextEngineLookups	OBJECT IDENTIFIER ::={sessionContextEngine 8}

sessionContextEngineLookupsVal	OBJECT-TYPE
	SYNTAX	 Counter64
	MAX-ACCESS read-only
	STATUS current
	DESCRIPTION "Lookups"

	::={sessionContextEngineLookups 1}

sessionContextEngineLookupsMom	OBJECT-TYPE
	SYNTAX	 CounterBasedGauge64
	MAX-ACCESS read-only
	STATUS current
	DESCRIPTION "Lookups"

	::={sessionContextEngineLookups 2}

sessionContextEngineLookupsMax	OBJECT-TYPE
	SYNTAX	 CounterBasedGauge64
	MAX-ACCESS read-only
	STATUS current
	DESCRIPTION "Lookups"

	::={sessionContextEngineLookups 3}

sessionContextEngineLookupsLevelTable OBJECT-TYPE
	SYNTAX      SEQUENCE OF SessionContextEngineLookupsLevelEntry
	MAX-ACCESS  not-accessible
	STATUS      current
	DESCRIPTION
	"Table for sessionContextEngineLookups"
	::={sessionContextEngineLookups 4}

sessionContextEngineLookupsLevelEntry OBJECT-TYPE
	SYNTAX      SessionContextEngineLookupsLevelEntry
	MAX-ACCESS  not-accessible
	STATUS      current
	DESCRIPTION
	"Table entry for sessionContextEngineLookups"
	INDEX { sessionContextEngineLookupsLevelName }
	::={sessionContextEngineLookupsLevelTable 1}

SessionContextEngineLookupsLevelEntry ::=
	SEQUENCE {
		sessionContextEngineLookupsLevelName	DisplayString,
		sessionContextEngineLookupsLevelVal	Counter64,
		sessionContextEngineLookupsLevelMom	CounterBasedGauge64,
		sessionContextEngineLookupsLevelMax	CounterBasedGauge64
	}

sessionContextEngineLookupsLevelName OBJECT-TYPE
	SYNTAX      DisplayString
	MAX-ACCESS  not-accessible
	STATUS      current
	DESCRIPTION
	"Table entry display string for sessionContextEngineLookups"
	::={sessionContextEngineLookupsLevelEntry 1}

sessionContextEngineLookupsLevelVal OBJECT-TYPE
	SYNTAX	 Counter64
	MAX-ACCESS  read-only
	STATUS      current
	DESCRIPTION
	"Table entry attribute for sessionContextEngineLookups"
	::={sessionContextEngineLookupsLevelEntry 2}

sessionContextEngineLookupsLevelMom OBJECT-TYPE
	SYNTAX	 CounterBasedGauge64
	MAX-ACCESS  read-only
	STATUS      current
	DESCRIPTION
	"Table entry attribute for sessionContextEngineLookups"
	::={sessionContextEngineLookupsLevelEntry 3}

sessionContextEngineLookupsLevelMax OBJECT-TYPE
	SYNTAX	 CounterBasedGauge64
	MAX-ACCESS  read-only
	STATUS      current
	DESCRIPTION
	"Table entry attribute for sessionContextEngineLookups"
	::={sessionContextEngineLookupsLevelEntry 4}


sessionContextEngineCountersSent	OBJECT IDENTIFIER ::={sessionContextEngine 9}

sessionContextEngineCountersSentVal	OBJECT-TYPE
	SYNTAX	 Counter64
	MAX-ACCESS read-only
	STATUS current
	DESCRIPTION "Counter messages sent"

	::={sessionContextEngineCountersSent 1}

sessionContextEngineCountersSentMom	OBJECT-TYPE
	SYNTAX	 CounterBasedGauge64
	MAX-ACCESS read-only
	STATUS current
	DESCRIPTION "Counter messages sent"

	::={sessionContextEngineCountersSent 2}

sessionContextEngineCountersSentMax	OBJECT-TYPE
	SYNTAX	 CounterBasedGauge64
	MAX-ACCESS read-only
	STATUS current
	DESCRIPTION "Counter messages sent"

	::={sessionContextEngineCountersSent 3}

sessionContextEngineCountersSentLevelTable OBJECT-TYPE
	SYNTAX      SEQUENCE OF SessionContextEngineCountersSentLevelEntry
	MAX-ACCESS  not-accessible
	STATUS      current
	DESCRIPTION
	"Table for sessionContextEngineCountersSent"
	::={sessionContextEngineCountersSent 4}

sessionContextEngineCountersSentLevelEntry OBJECT-TYPE
	SYNTAX      SessionContextEngineCountersSentLevelEntry
	MAX-ACCESS  not-accessible
	STATUS      current
	DESCRIPTION
	"Table entry for sessionContextEngineCountersSent"
	INDEX { sessionContextEngineCountersSentLevelName }
	::={sessionContextEngineCountersSentLevelTable 1}

SessionContextEngineCountersSentLevelEntry ::=
	SEQUENCE {
		sessionContextEngineCountersSentLevelName	DisplayString,
		sessionContextEngineCountersSentLevelVal	Counter64,
		sessionContextEngineCountersSentLevelMom	CounterBasedGauge64,
		sessionContextEngineCountersSentLevelMax	CounterBasedGauge64
	}

sessionContextEngineCountersSentLevelName OBJECT-TYPE
	SYNTAX      DisplayString
	MAX-ACCESS  not-accessible
	STATUS      current
	DESCRIPTION
	"Table entry display string for sessionContextEngineCountersSent"
	::={sessionContextEngineCountersSentLevelEntry 1}

sessionContextEngineCountersSentLevelVal OBJECT-TYPE
	SYNTAX	 Counter64
	MAX-ACCESS  read-only
	STATUS      current
	DESCRIPTION
	"Table entry attribute for sessionContextEngineCountersSent"
	::={sessionContextEngineCountersSentLevelEntry 2}

sessionContextEngineCountersSentLevelMom OBJECT-TYPE
	SYNTAX	 CounterBasedGauge64
	MAX-ACCESS  read-only
	STATUS      current
	DESCRIPTION
	"Table entry attribute for sessionContextEngineCountersSent"
	::={sessionContextEngineCountersSentLevelEntry 3}

sessionContextEngineCountersSentLevelMax OBJECT-TYPE
	SYNTAX	 CounterBasedGauge64
	MAX-ACCESS  read-only
	STATUS      current
	DESCRIPTION
	"Table entry attribute for sessionContextEngineCountersSent"
	::={sessionContextEngineCountersSentLevelEntry 4}


sessionContextEngineRowsOnFreelist	OBJECT IDENTIFIER ::={sessionContextEngine 12}

sessionContextEngineRowsOnFreelistVal	OBJECT-TYPE
	SYNTAX	 CounterBasedGauge64
	MAX-ACCESS read-only
	STATUS current
	DESCRIPTION "Rows on freelist"

	::={sessionContextEngineRowsOnFreelist 1}

sessionContextEngineRowsOnFreelistMax	OBJECT-TYPE
	SYNTAX	 CounterBasedGauge64
	MAX-ACCESS read-only
	STATUS current
	DESCRIPTION "Rows on freelist"

	::={sessionContextEngineRowsOnFreelist 3}

sessionContextEngineRowsOnFreelistLevelTable OBJECT-TYPE
	SYNTAX      SEQUENCE OF SessionContextEngineRowsOnFreelistLevelEntry
	MAX-ACCESS  not-accessible
	STATUS      current
	DESCRIPTION
	"Table for sessionContextEngineRowsOnFreelist"
	::={sessionContextEngineRowsOnFreelist 4}

sessionContextEngineRowsOnFreelistLevelEntry OBJECT-TYPE
	SYNTAX      SessionContextEngineRowsOnFreelistLevelEntry
	MAX-ACCESS  not-accessible
	STATUS      current
	DESCRIPTION
	"Table entry for sessionContextEngineRowsOnFreelist"
	INDEX { sessionContextEngineRowsOnFreelistLevelName }
	::={sessionContextEngineRowsOnFreelistLevelTable 1}

SessionContextEngineRowsOnFreelistLevelEntry ::=
	SEQUENCE {
		sessionContextEngineRowsOnFreelistLevelName	DisplayString,
		sessionContextEngineRowsOnFreelistLevelVal	CounterBasedGauge64,
		sessionContextEngineRowsOnFreelistLevelMax	CounterBasedGauge64
	}

sessionContextEngineRowsOnFreelistLevelName OBJECT-TYPE
	SYNTAX      DisplayString
	MAX-ACCESS  not-accessible
	STATUS      current
	DESCRIPTION
	"Table entry display string for sessionContextEngineRowsOnFreelist"
	::={sessionContextEngineRowsOnFreelistLevelEntry 1}

sessionContextEngineRowsOnFreelistLevelVal OBJECT-TYPE
	SYNTAX	 CounterBasedGauge64
	MAX-ACCESS  read-only
	STATUS      current
	DESCRIPTION
	"Table entry attribute for sessionContextEngineRowsOnFreelist"
	::={sessionContextEngineRowsOnFreelistLevelEntry 2}

sessionContextEngineRowsOnFreelistLevelMax OBJECT-TYPE
	SYNTAX	 CounterBasedGauge64
	MAX-ACCESS  read-only
	STATUS      current
	DESCRIPTION
	"Table entry attribute for sessionContextEngineRowsOnFreelist"
	::={sessionContextEngineRowsOnFreelistLevelEntry 4}


sessionContextEngineUnmatchedConnections	OBJECT IDENTIFIER ::={sessionContextEngine 10}

sessionContextEngineUnmatchedConnectionsVal	OBJECT-TYPE
	SYNTAX	 CounterBasedGauge64
	MAX-ACCESS read-only
	STATUS current
	DESCRIPTION "Unmatched connections"

	::={sessionContextEngineUnmatchedConnections 1}

sessionContextEngineUnmatchedConnectionsMax	OBJECT-TYPE
	SYNTAX	 CounterBasedGauge64
	MAX-ACCESS read-only
	STATUS current
	DESCRIPTION "Unmatched connections"

	::={sessionContextEngineUnmatchedConnections 3}

sessionContextEngineUnmatchedConnectionsLevelTable OBJECT-TYPE
	SYNTAX      SEQUENCE OF SessionContextEngineUnmatchedConnectionsLevelEntry
	MAX-ACCESS  not-accessible
	STATUS      current
	DESCRIPTION
	"Table for sessionContextEngineUnmatchedConnections"
	::={sessionContextEngineUnmatchedConnections 4}

sessionContextEngineUnmatchedConnectionsLevelEntry OBJECT-TYPE
	SYNTAX      SessionContextEngineUnmatchedConnectionsLevelEntry
	MAX-ACCESS  not-accessible
	STATUS      current
	DESCRIPTION
	"Table entry for sessionContextEngineUnmatchedConnections"
	INDEX { sessionContextEngineUnmatchedConnectionsLevelName }
	::={sessionContextEngineUnmatchedConnectionsLevelTable 1}

SessionContextEngineUnmatchedConnectionsLevelEntry ::=
	SEQUENCE {
		sessionContextEngineUnmatchedConnectionsLevelName	DisplayString,
		sessionContextEngineUnmatchedConnectionsLevelVal	CounterBasedGauge64,
		sessionContextEngineUnmatchedConnectionsLevelMax	CounterBasedGauge64
	}

sessionContextEngineUnmatchedConnectionsLevelName OBJECT-TYPE
	SYNTAX      DisplayString
	MAX-ACCESS  not-accessible
	STATUS      current
	DESCRIPTION
	"Table entry display string for sessionContextEngineUnmatchedConnections"
	::={sessionContextEngineUnmatchedConnectionsLevelEntry 1}

sessionContextEngineUnmatchedConnectionsLevelVal OBJECT-TYPE
	SYNTAX	 CounterBasedGauge64
	MAX-ACCESS  read-only
	STATUS      current
	DESCRIPTION
	"Table entry attribute for sessionContextEngineUnmatchedConnections"
	::={sessionContextEngineUnmatchedConnectionsLevelEntry 2}

sessionContextEngineUnmatchedConnectionsLevelMax OBJECT-TYPE
	SYNTAX	 CounterBasedGauge64
	MAX-ACCESS  read-only
	STATUS      current
	DESCRIPTION
	"Table entry attribute for sessionContextEngineUnmatchedConnections"
	::={sessionContextEngineUnmatchedConnectionsLevelEntry 4}


sessionContextEngineUnmatchedBytes	OBJECT IDENTIFIER ::={sessionContextEngine 11}

sessionContextEngineUnmatchedBytesVal	OBJECT-TYPE
	SYNTAX	 Counter64
	MAX-ACCESS read-only
	STATUS current
	DESCRIPTION "Unmatched bytes"

	::={sessionContextEngineUnmatchedBytes 1}

sessionContextEngineUnmatchedBytesMom	OBJECT-TYPE
	SYNTAX	 CounterBasedGauge64
	MAX-ACCESS read-only
	STATUS current
	DESCRIPTION "Unmatched bytes"

	::={sessionContextEngineUnmatchedBytes 2}

sessionContextEngineUnmatchedBytesMax	OBJECT-TYPE
	SYNTAX	 CounterBasedGauge64
	MAX-ACCESS read-only
	STATUS current
	DESCRIPTION "Unmatched bytes"

	::={sessionContextEngineUnmatchedBytes 3}

sessionContextEngineUnmatchedBytesLevelTable OBJECT-TYPE
	SYNTAX      SEQUENCE OF SessionContextEngineUnmatchedBytesLevelEntry
	MAX-ACCESS  not-accessible
	STATUS      current
	DESCRIPTION
	"Table for sessionContextEngineUnmatchedBytes"
	::={sessionContextEngineUnmatchedBytes 4}

sessionContextEngineUnmatchedBytesLevelEntry OBJECT-TYPE
	SYNTAX      SessionContextEngineUnmatchedBytesLevelEntry
	MAX-ACCESS  not-accessible
	STATUS      current
	DESCRIPTION
	"Table entry for sessionContextEngineUnmatchedBytes"
	INDEX { sessionContextEngineUnmatchedBytesLevelName }
	::={sessionContextEngineUnmatchedBytesLevelTable 1}

SessionContextEngineUnmatchedBytesLevelEntry ::=
	SEQUENCE {
		sessionContextEngineUnmatchedBytesLevelName	DisplayString,
		sessionContextEngineUnmatchedBytesLevelVal	Counter64,
		sessionContextEngineUnmatchedBytesLevelMom	CounterBasedGauge64,
		sessionContextEngineUnmatchedBytesLevelMax	CounterBasedGauge64
	}

sessionContextEngineUnmatchedBytesLevelName OBJECT-TYPE
	SYNTAX      DisplayString
	MAX-ACCESS  not-accessible
	STATUS      current
	DESCRIPTION
	"Table entry display string for sessionContextEngineUnmatchedBytes"
	::={sessionContextEngineUnmatchedBytesLevelEntry 1}

sessionContextEngineUnmatchedBytesLevelVal OBJECT-TYPE
	SYNTAX	 Counter64
	MAX-ACCESS  read-only
	STATUS      current
	DESCRIPTION
	"Table entry attribute for sessionContextEngineUnmatchedBytes"
	::={sessionContextEngineUnmatchedBytesLevelEntry 2}

sessionContextEngineUnmatchedBytesLevelMom OBJECT-TYPE
	SYNTAX	 CounterBasedGauge64
	MAX-ACCESS  read-only
	STATUS      current
	DESCRIPTION
	"Table entry attribute for sessionContextEngineUnmatchedBytes"
	::={sessionContextEngineUnmatchedBytesLevelEntry 3}

sessionContextEngineUnmatchedBytesLevelMax OBJECT-TYPE
	SYNTAX	 CounterBasedGauge64
	MAX-ACCESS  read-only
	STATUS      current
	DESCRIPTION
	"Table entry attribute for sessionContextEngineUnmatchedBytes"
	::={sessionContextEngineUnmatchedBytesLevelEntry 4}


sessionContextDaemon	OBJECT IDENTIFIER ::={sysdiag 152}

sessionContextDaemonRegisteredSchema	OBJECT IDENTIFIER ::={sessionContextDaemon 1}

sessionContextDaemonRegisteredSchemaVal	OBJECT-TYPE
	SYNTAX	 CounterBasedGauge64
	MAX-ACCESS read-only
	STATUS current
	DESCRIPTION "Registered schema"

	::={sessionContextDaemonRegisteredSchema 1}

sessionContextDaemonRegisteredSchemaMax	OBJECT-TYPE
	SYNTAX	 CounterBasedGauge64
	MAX-ACCESS read-only
	STATUS current
	DESCRIPTION "Registered schema"

	::={sessionContextDaemonRegisteredSchema 3}

sessionContextDaemonRegisteredSchemaLevelTable OBJECT-TYPE
	SYNTAX      SEQUENCE OF SessionContextDaemonRegisteredSchemaLevelEntry
	MAX-ACCESS  not-accessible
	STATUS      current
	DESCRIPTION
	"Table for sessionContextDaemonRegisteredSchema"
	::={sessionContextDaemonRegisteredSchema 4}

sessionContextDaemonRegisteredSchemaLevelEntry OBJECT-TYPE
	SYNTAX      SessionContextDaemonRegisteredSchemaLevelEntry
	MAX-ACCESS  not-accessible
	STATUS      current
	DESCRIPTION
	"Table entry for sessionContextDaemonRegisteredSchema"
	INDEX { sessionContextDaemonRegisteredSchemaLevelName }
	::={sessionContextDaemonRegisteredSchemaLevelTable 1}

SessionContextDaemonRegisteredSchemaLevelEntry ::=
	SEQUENCE {
		sessionContextDaemonRegisteredSchemaLevelName	DisplayString,
		sessionContextDaemonRegisteredSchemaLevelVal	CounterBasedGauge64,
		sessionContextDaemonRegisteredSchemaLevelMax	CounterBasedGauge64
	}

sessionContextDaemonRegisteredSchemaLevelName OBJECT-TYPE
	SYNTAX      DisplayString
	MAX-ACCESS  not-accessible
	STATUS      current
	DESCRIPTION
	"Table entry display string for sessionContextDaemonRegisteredSchema"
	::={sessionContextDaemonRegisteredSchemaLevelEntry 1}

sessionContextDaemonRegisteredSchemaLevelVal OBJECT-TYPE
	SYNTAX	 CounterBasedGauge64
	MAX-ACCESS  read-only
	STATUS      current
	DESCRIPTION
	"Table entry attribute for sessionContextDaemonRegisteredSchema"
	::={sessionContextDaemonRegisteredSchemaLevelEntry 2}

sessionContextDaemonRegisteredSchemaLevelMax OBJECT-TYPE
	SYNTAX	 CounterBasedGauge64
	MAX-ACCESS  read-only
	STATUS      current
	DESCRIPTION
	"Table entry attribute for sessionContextDaemonRegisteredSchema"
	::={sessionContextDaemonRegisteredSchemaLevelEntry 4}


sessionContextDaemonAcquiredSchema	OBJECT IDENTIFIER ::={sessionContextDaemon 2}

sessionContextDaemonAcquiredSchemaVal	OBJECT-TYPE
	SYNTAX	 CounterBasedGauge64
	MAX-ACCESS read-only
	STATUS current
	DESCRIPTION "Schema with connected client"

	::={sessionContextDaemonAcquiredSchema 1}

sessionContextDaemonAcquiredSchemaMax	OBJECT-TYPE
	SYNTAX	 CounterBasedGauge64
	MAX-ACCESS read-only
	STATUS current
	DESCRIPTION "Schema with connected client"

	::={sessionContextDaemonAcquiredSchema 3}

sessionContextDaemonAcquiredSchemaLevelTable OBJECT-TYPE
	SYNTAX      SEQUENCE OF SessionContextDaemonAcquiredSchemaLevelEntry
	MAX-ACCESS  not-accessible
	STATUS      current
	DESCRIPTION
	"Table for sessionContextDaemonAcquiredSchema"
	::={sessionContextDaemonAcquiredSchema 4}

sessionContextDaemonAcquiredSchemaLevelEntry OBJECT-TYPE
	SYNTAX      SessionContextDaemonAcquiredSchemaLevelEntry
	MAX-ACCESS  not-accessible
	STATUS      current
	DESCRIPTION
	"Table entry for sessionContextDaemonAcquiredSchema"
	INDEX { sessionContextDaemonAcquiredSchemaLevelName }
	::={sessionContextDaemonAcquiredSchemaLevelTable 1}

SessionContextDaemonAcquiredSchemaLevelEntry ::=
	SEQUENCE {
		sessionContextDaemonAcquiredSchemaLevelName	DisplayString,
		sessionContextDaemonAcquiredSchemaLevelVal	CounterBasedGauge64,
		sessionContextDaemonAcquiredSchemaLevelMax	CounterBasedGauge64
	}

sessionContextDaemonAcquiredSchemaLevelName OBJECT-TYPE
	SYNTAX      DisplayString
	MAX-ACCESS  not-accessible
	STATUS      current
	DESCRIPTION
	"Table entry display string for sessionContextDaemonAcquiredSchema"
	::={sessionContextDaemonAcquiredSchemaLevelEntry 1}

sessionContextDaemonAcquiredSchemaLevelVal OBJECT-TYPE
	SYNTAX	 CounterBasedGauge64
	MAX-ACCESS  read-only
	STATUS      current
	DESCRIPTION
	"Table entry attribute for sessionContextDaemonAcquiredSchema"
	::={sessionContextDaemonAcquiredSchemaLevelEntry 2}

sessionContextDaemonAcquiredSchemaLevelMax OBJECT-TYPE
	SYNTAX	 CounterBasedGauge64
	MAX-ACCESS  read-only
	STATUS      current
	DESCRIPTION
	"Table entry attribute for sessionContextDaemonAcquiredSchema"
	::={sessionContextDaemonAcquiredSchemaLevelEntry 4}


sessionContextDaemonConnectedClients	OBJECT IDENTIFIER ::={sessionContextDaemon 3}

sessionContextDaemonConnectedClientsVal	OBJECT-TYPE
	SYNTAX	 CounterBasedGauge64
	MAX-ACCESS read-only
	STATUS current
	DESCRIPTION "Connected clients"

	::={sessionContextDaemonConnectedClients 1}

sessionContextDaemonConnectedClientsMax	OBJECT-TYPE
	SYNTAX	 CounterBasedGauge64
	MAX-ACCESS read-only
	STATUS current
	DESCRIPTION "Connected clients"

	::={sessionContextDaemonConnectedClients 3}

sessionContextDaemonConnectedClientsLevelTable OBJECT-TYPE
	SYNTAX      SEQUENCE OF SessionContextDaemonConnectedClientsLevelEntry
	MAX-ACCESS  not-accessible
	STATUS      current
	DESCRIPTION
	"Table for sessionContextDaemonConnectedClients"
	::={sessionContextDaemonConnectedClients 4}

sessionContextDaemonConnectedClientsLevelEntry OBJECT-TYPE
	SYNTAX      SessionContextDaemonConnectedClientsLevelEntry
	MAX-ACCESS  not-accessible
	STATUS      current
	DESCRIPTION
	"Table entry for sessionContextDaemonConnectedClients"
	INDEX { sessionContextDaemonConnectedClientsLevelName }
	::={sessionContextDaemonConnectedClientsLevelTable 1}

SessionContextDaemonConnectedClientsLevelEntry ::=
	SEQUENCE {
		sessionContextDaemonConnectedClientsLevelName	DisplayString,
		sessionContextDaemonConnectedClientsLevelVal	CounterBasedGauge64,
		sessionContextDaemonConnectedClientsLevelMax	CounterBasedGauge64
	}

sessionContextDaemonConnectedClientsLevelName OBJECT-TYPE
	SYNTAX      DisplayString
	MAX-ACCESS  not-accessible
	STATUS      current
	DESCRIPTION
	"Table entry display string for sessionContextDaemonConnectedClients"
	::={sessionContextDaemonConnectedClientsLevelEntry 1}

sessionContextDaemonConnectedClientsLevelVal OBJECT-TYPE
	SYNTAX	 CounterBasedGauge64
	MAX-ACCESS  read-only
	STATUS      current
	DESCRIPTION
	"Table entry attribute for sessionContextDaemonConnectedClients"
	::={sessionContextDaemonConnectedClientsLevelEntry 2}

sessionContextDaemonConnectedClientsLevelMax OBJECT-TYPE
	SYNTAX	 CounterBasedGauge64
	MAX-ACCESS  read-only
	STATUS      current
	DESCRIPTION
	"Table entry attribute for sessionContextDaemonConnectedClients"
	::={sessionContextDaemonConnectedClientsLevelEntry 4}


sessionContextDaemonBarrierMessages	OBJECT IDENTIFIER ::={sessionContextDaemon 4}

sessionContextDaemonBarrierMessagesVal	OBJECT-TYPE
	SYNTAX	 Counter64
	MAX-ACCESS read-only
	STATUS current
	DESCRIPTION "Barrier messages received"

	::={sessionContextDaemonBarrierMessages 1}

sessionContextDaemonBarrierMessagesMom	OBJECT-TYPE
	SYNTAX	 CounterBasedGauge64
	MAX-ACCESS read-only
	STATUS current
	DESCRIPTION "Barrier messages received"

	::={sessionContextDaemonBarrierMessages 2}

sessionContextDaemonBarrierMessagesMax	OBJECT-TYPE
	SYNTAX	 CounterBasedGauge64
	MAX-ACCESS read-only
	STATUS current
	DESCRIPTION "Barrier messages received"

	::={sessionContextDaemonBarrierMessages 3}

sessionContextDaemonBarrierMessagesLevelTable OBJECT-TYPE
	SYNTAX      SEQUENCE OF SessionContextDaemonBarrierMessagesLevelEntry
	MAX-ACCESS  not-accessible
	STATUS      current
	DESCRIPTION
	"Table for sessionContextDaemonBarrierMessages"
	::={sessionContextDaemonBarrierMessages 4}

sessionContextDaemonBarrierMessagesLevelEntry OBJECT-TYPE
	SYNTAX      SessionContextDaemonBarrierMessagesLevelEntry
	MAX-ACCESS  not-accessible
	STATUS      current
	DESCRIPTION
	"Table entry for sessionContextDaemonBarrierMessages"
	INDEX { sessionContextDaemonBarrierMessagesLevelName }
	::={sessionContextDaemonBarrierMessagesLevelTable 1}

SessionContextDaemonBarrierMessagesLevelEntry ::=
	SEQUENCE {
		sessionContextDaemonBarrierMessagesLevelName	DisplayString,
		sessionContextDaemonBarrierMessagesLevelVal	Counter64,
		sessionContextDaemonBarrierMessagesLevelMom	CounterBasedGauge64,
		sessionContextDaemonBarrierMessagesLevelMax	CounterBasedGauge64
	}

sessionContextDaemonBarrierMessagesLevelName OBJECT-TYPE
	SYNTAX      DisplayString
	MAX-ACCESS  not-accessible
	STATUS      current
	DESCRIPTION
	"Table entry display string for sessionContextDaemonBarrierMessages"
	::={sessionContextDaemonBarrierMessagesLevelEntry 1}

sessionContextDaemonBarrierMessagesLevelVal OBJECT-TYPE
	SYNTAX	 Counter64
	MAX-ACCESS  read-only
	STATUS      current
	DESCRIPTION
	"Table entry attribute for sessionContextDaemonBarrierMessages"
	::={sessionContextDaemonBarrierMessagesLevelEntry 2}

sessionContextDaemonBarrierMessagesLevelMom OBJECT-TYPE
	SYNTAX	 CounterBasedGauge64
	MAX-ACCESS  read-only
	STATUS      current
	DESCRIPTION
	"Table entry attribute for sessionContextDaemonBarrierMessages"
	::={sessionContextDaemonBarrierMessagesLevelEntry 3}

sessionContextDaemonBarrierMessagesLevelMax OBJECT-TYPE
	SYNTAX	 CounterBasedGauge64
	MAX-ACCESS  read-only
	STATUS      current
	DESCRIPTION
	"Table entry attribute for sessionContextDaemonBarrierMessages"
	::={sessionContextDaemonBarrierMessagesLevelEntry 4}


sessionContextDaemonCreateMessages	OBJECT IDENTIFIER ::={sessionContextDaemon 5}

sessionContextDaemonCreateMessagesVal	OBJECT-TYPE
	SYNTAX	 Counter64
	MAX-ACCESS read-only
	STATUS current
	DESCRIPTION "Create messages received"

	::={sessionContextDaemonCreateMessages 1}

sessionContextDaemonCreateMessagesMom	OBJECT-TYPE
	SYNTAX	 CounterBasedGauge64
	MAX-ACCESS read-only
	STATUS current
	DESCRIPTION "Create messages received"

	::={sessionContextDaemonCreateMessages 2}

sessionContextDaemonCreateMessagesMax	OBJECT-TYPE
	SYNTAX	 CounterBasedGauge64
	MAX-ACCESS read-only
	STATUS current
	DESCRIPTION "Create messages received"

	::={sessionContextDaemonCreateMessages 3}

sessionContextDaemonCreateMessagesLevelTable OBJECT-TYPE
	SYNTAX      SEQUENCE OF SessionContextDaemonCreateMessagesLevelEntry
	MAX-ACCESS  not-accessible
	STATUS      current
	DESCRIPTION
	"Table for sessionContextDaemonCreateMessages"
	::={sessionContextDaemonCreateMessages 4}

sessionContextDaemonCreateMessagesLevelEntry OBJECT-TYPE
	SYNTAX      SessionContextDaemonCreateMessagesLevelEntry
	MAX-ACCESS  not-accessible
	STATUS      current
	DESCRIPTION
	"Table entry for sessionContextDaemonCreateMessages"
	INDEX { sessionContextDaemonCreateMessagesLevelName }
	::={sessionContextDaemonCreateMessagesLevelTable 1}

SessionContextDaemonCreateMessagesLevelEntry ::=
	SEQUENCE {
		sessionContextDaemonCreateMessagesLevelName	DisplayString,
		sessionContextDaemonCreateMessagesLevelVal	Counter64,
		sessionContextDaemonCreateMessagesLevelMom	CounterBasedGauge64,
		sessionContextDaemonCreateMessagesLevelMax	CounterBasedGauge64
	}

sessionContextDaemonCreateMessagesLevelName OBJECT-TYPE
	SYNTAX      DisplayString
	MAX-ACCESS  not-accessible
	STATUS      current
	DESCRIPTION
	"Table entry display string for sessionContextDaemonCreateMessages"
	::={sessionContextDaemonCreateMessagesLevelEntry 1}

sessionContextDaemonCreateMessagesLevelVal OBJECT-TYPE
	SYNTAX	 Counter64
	MAX-ACCESS  read-only
	STATUS      current
	DESCRIPTION
	"Table entry attribute for sessionContextDaemonCreateMessages"
	::={sessionContextDaemonCreateMessagesLevelEntry 2}

sessionContextDaemonCreateMessagesLevelMom OBJECT-TYPE
	SYNTAX	 CounterBasedGauge64
	MAX-ACCESS  read-only
	STATUS      current
	DESCRIPTION
	"Table entry attribute for sessionContextDaemonCreateMessages"
	::={sessionContextDaemonCreateMessagesLevelEntry 3}

sessionContextDaemonCreateMessagesLevelMax OBJECT-TYPE
	SYNTAX	 CounterBasedGauge64
	MAX-ACCESS  read-only
	STATUS      current
	DESCRIPTION
	"Table entry attribute for sessionContextDaemonCreateMessages"
	::={sessionContextDaemonCreateMessagesLevelEntry 4}


sessionContextDaemonDeltaMessages	OBJECT IDENTIFIER ::={sessionContextDaemon 6}

sessionContextDaemonDeltaMessagesVal	OBJECT-TYPE
	SYNTAX	 Counter64
	MAX-ACCESS read-only
	STATUS current
	DESCRIPTION "Delta messages received"

	::={sessionContextDaemonDeltaMessages 1}

sessionContextDaemonDeltaMessagesMom	OBJECT-TYPE
	SYNTAX	 CounterBasedGauge64
	MAX-ACCESS read-only
	STATUS current
	DESCRIPTION "Delta messages received"

	::={sessionContextDaemonDeltaMessages 2}

sessionContextDaemonDeltaMessagesMax	OBJECT-TYPE
	SYNTAX	 CounterBasedGauge64
	MAX-ACCESS read-only
	STATUS current
	DESCRIPTION "Delta messages received"

	::={sessionContextDaemonDeltaMessages 3}

sessionContextDaemonDeltaMessagesLevelTable OBJECT-TYPE
	SYNTAX      SEQUENCE OF SessionContextDaemonDeltaMessagesLevelEntry
	MAX-ACCESS  not-accessible
	STATUS      current
	DESCRIPTION
	"Table for sessionContextDaemonDeltaMessages"
	::={sessionContextDaemonDeltaMessages 4}

sessionContextDaemonDeltaMessagesLevelEntry OBJECT-TYPE
	SYNTAX      SessionContextDaemonDeltaMessagesLevelEntry
	MAX-ACCESS  not-accessible
	STATUS      current
	DESCRIPTION
	"Table entry for sessionContextDaemonDeltaMessages"
	INDEX { sessionContextDaemonDeltaMessagesLevelName }
	::={sessionContextDaemonDeltaMessagesLevelTable 1}

SessionContextDaemonDeltaMessagesLevelEntry ::=
	SEQUENCE {
		sessionContextDaemonDeltaMessagesLevelName	DisplayString,
		sessionContextDaemonDeltaMessagesLevelVal	Counter64,
		sessionContextDaemonDeltaMessagesLevelMom	CounterBasedGauge64,
		sessionContextDaemonDeltaMessagesLevelMax	CounterBasedGauge64
	}

sessionContextDaemonDeltaMessagesLevelName OBJECT-TYPE
	SYNTAX      DisplayString
	MAX-ACCESS  not-accessible
	STATUS      current
	DESCRIPTION
	"Table entry display string for sessionContextDaemonDeltaMessages"
	::={sessionContextDaemonDeltaMessagesLevelEntry 1}

sessionContextDaemonDeltaMessagesLevelVal OBJECT-TYPE
	SYNTAX	 Counter64
	MAX-ACCESS  read-only
	STATUS      current
	DESCRIPTION
	"Table entry attribute for sessionContextDaemonDeltaMessages"
	::={sessionContextDaemonDeltaMessagesLevelEntry 2}

sessionContextDaemonDeltaMessagesLevelMom OBJECT-TYPE
	SYNTAX	 CounterBasedGauge64
	MAX-ACCESS  read-only
	STATUS      current
	DESCRIPTION
	"Table entry attribute for sessionContextDaemonDeltaMessages"
	::={sessionContextDaemonDeltaMessagesLevelEntry 3}

sessionContextDaemonDeltaMessagesLevelMax OBJECT-TYPE
	SYNTAX	 CounterBasedGauge64
	MAX-ACCESS  read-only
	STATUS      current
	DESCRIPTION
	"Table entry attribute for sessionContextDaemonDeltaMessages"
	::={sessionContextDaemonDeltaMessagesLevelEntry 4}


sessionContextDaemonDeleteMessages	OBJECT IDENTIFIER ::={sessionContextDaemon 7}

sessionContextDaemonDeleteMessagesVal	OBJECT-TYPE
	SYNTAX	 Counter64
	MAX-ACCESS read-only
	STATUS current
	DESCRIPTION "Delete messages received"

	::={sessionContextDaemonDeleteMessages 1}

sessionContextDaemonDeleteMessagesMom	OBJECT-TYPE
	SYNTAX	 CounterBasedGauge64
	MAX-ACCESS read-only
	STATUS current
	DESCRIPTION "Delete messages received"

	::={sessionContextDaemonDeleteMessages 2}

sessionContextDaemonDeleteMessagesMax	OBJECT-TYPE
	SYNTAX	 CounterBasedGauge64
	MAX-ACCESS read-only
	STATUS current
	DESCRIPTION "Delete messages received"

	::={sessionContextDaemonDeleteMessages 3}

sessionContextDaemonDeleteMessagesLevelTable OBJECT-TYPE
	SYNTAX      SEQUENCE OF SessionContextDaemonDeleteMessagesLevelEntry
	MAX-ACCESS  not-accessible
	STATUS      current
	DESCRIPTION
	"Table for sessionContextDaemonDeleteMessages"
	::={sessionContextDaemonDeleteMessages 4}

sessionContextDaemonDeleteMessagesLevelEntry OBJECT-TYPE
	SYNTAX      SessionContextDaemonDeleteMessagesLevelEntry
	MAX-ACCESS  not-accessible
	STATUS      current
	DESCRIPTION
	"Table entry for sessionContextDaemonDeleteMessages"
	INDEX { sessionContextDaemonDeleteMessagesLevelName }
	::={sessionContextDaemonDeleteMessagesLevelTable 1}

SessionContextDaemonDeleteMessagesLevelEntry ::=
	SEQUENCE {
		sessionContextDaemonDeleteMessagesLevelName	DisplayString,
		sessionContextDaemonDeleteMessagesLevelVal	Counter64,
		sessionContextDaemonDeleteMessagesLevelMom	CounterBasedGauge64,
		sessionContextDaemonDeleteMessagesLevelMax	CounterBasedGauge64
	}

sessionContextDaemonDeleteMessagesLevelName OBJECT-TYPE
	SYNTAX      DisplayString
	MAX-ACCESS  not-accessible
	STATUS      current
	DESCRIPTION
	"Table entry display string for sessionContextDaemonDeleteMessages"
	::={sessionContextDaemonDeleteMessagesLevelEntry 1}

sessionContextDaemonDeleteMessagesLevelVal OBJECT-TYPE
	SYNTAX	 Counter64
	MAX-ACCESS  read-only
	STATUS      current
	DESCRIPTION
	"Table entry attribute for sessionContextDaemonDeleteMessages"
	::={sessionContextDaemonDeleteMessagesLevelEntry 2}

sessionContextDaemonDeleteMessagesLevelMom OBJECT-TYPE
	SYNTAX	 CounterBasedGauge64
	MAX-ACCESS  read-only
	STATUS      current
	DESCRIPTION
	"Table entry attribute for sessionContextDaemonDeleteMessages"
	::={sessionContextDaemonDeleteMessagesLevelEntry 3}

sessionContextDaemonDeleteMessagesLevelMax OBJECT-TYPE
	SYNTAX	 CounterBasedGauge64
	MAX-ACCESS  read-only
	STATUS      current
	DESCRIPTION
	"Table entry attribute for sessionContextDaemonDeleteMessages"
	::={sessionContextDaemonDeleteMessagesLevelEntry 4}


sessionContextDaemonCountersSent	OBJECT IDENTIFIER ::={sessionContextDaemon 8}

sessionContextDaemonCountersSentVal	OBJECT-TYPE
	SYNTAX	 Counter64
	MAX-ACCESS read-only
	STATUS current
	DESCRIPTION "Counters sent"

	::={sessionContextDaemonCountersSent 1}

sessionContextDaemonCountersSentMom	OBJECT-TYPE
	SYNTAX	 CounterBasedGauge64
	MAX-ACCESS read-only
	STATUS current
	DESCRIPTION "Counters sent"

	::={sessionContextDaemonCountersSent 2}

sessionContextDaemonCountersSentMax	OBJECT-TYPE
	SYNTAX	 CounterBasedGauge64
	MAX-ACCESS read-only
	STATUS current
	DESCRIPTION "Counters sent"

	::={sessionContextDaemonCountersSent 3}

sessionContextDaemonCountersSentLevelTable OBJECT-TYPE
	SYNTAX      SEQUENCE OF SessionContextDaemonCountersSentLevelEntry
	MAX-ACCESS  not-accessible
	STATUS      current
	DESCRIPTION
	"Table for sessionContextDaemonCountersSent"
	::={sessionContextDaemonCountersSent 4}

sessionContextDaemonCountersSentLevelEntry OBJECT-TYPE
	SYNTAX      SessionContextDaemonCountersSentLevelEntry
	MAX-ACCESS  not-accessible
	STATUS      current
	DESCRIPTION
	"Table entry for sessionContextDaemonCountersSent"
	INDEX { sessionContextDaemonCountersSentLevelName }
	::={sessionContextDaemonCountersSentLevelTable 1}

SessionContextDaemonCountersSentLevelEntry ::=
	SEQUENCE {
		sessionContextDaemonCountersSentLevelName	DisplayString,
		sessionContextDaemonCountersSentLevelVal	Counter64,
		sessionContextDaemonCountersSentLevelMom	CounterBasedGauge64,
		sessionContextDaemonCountersSentLevelMax	CounterBasedGauge64
	}

sessionContextDaemonCountersSentLevelName OBJECT-TYPE
	SYNTAX      DisplayString
	MAX-ACCESS  not-accessible
	STATUS      current
	DESCRIPTION
	"Table entry display string for sessionContextDaemonCountersSent"
	::={sessionContextDaemonCountersSentLevelEntry 1}

sessionContextDaemonCountersSentLevelVal OBJECT-TYPE
	SYNTAX	 Counter64
	MAX-ACCESS  read-only
	STATUS      current
	DESCRIPTION
	"Table entry attribute for sessionContextDaemonCountersSent"
	::={sessionContextDaemonCountersSentLevelEntry 2}

sessionContextDaemonCountersSentLevelMom OBJECT-TYPE
	SYNTAX	 CounterBasedGauge64
	MAX-ACCESS  read-only
	STATUS      current
	DESCRIPTION
	"Table entry attribute for sessionContextDaemonCountersSent"
	::={sessionContextDaemonCountersSentLevelEntry 3}

sessionContextDaemonCountersSentLevelMax OBJECT-TYPE
	SYNTAX	 CounterBasedGauge64
	MAX-ACCESS  read-only
	STATUS      current
	DESCRIPTION
	"Table entry attribute for sessionContextDaemonCountersSent"
	::={sessionContextDaemonCountersSentLevelEntry 4}


sessionContextDaemonCountersInFlight	OBJECT IDENTIFIER ::={sessionContextDaemon 9}

sessionContextDaemonCountersInFlightVal	OBJECT-TYPE
	SYNTAX	 CounterBasedGauge64
	MAX-ACCESS read-only
	STATUS current
	DESCRIPTION "Counters in flight"

	::={sessionContextDaemonCountersInFlight 1}

sessionContextDaemonCountersInFlightMax	OBJECT-TYPE
	SYNTAX	 CounterBasedGauge64
	MAX-ACCESS read-only
	STATUS current
	DESCRIPTION "Counters in flight"

	::={sessionContextDaemonCountersInFlight 3}

sessionContextDaemonCountersInFlightLevelTable OBJECT-TYPE
	SYNTAX      SEQUENCE OF SessionContextDaemonCountersInFlightLevelEntry
	MAX-ACCESS  not-accessible
	STATUS      current
	DESCRIPTION
	"Table for sessionContextDaemonCountersInFlight"
	::={sessionContextDaemonCountersInFlight 4}

sessionContextDaemonCountersInFlightLevelEntry OBJECT-TYPE
	SYNTAX      SessionContextDaemonCountersInFlightLevelEntry
	MAX-ACCESS  not-accessible
	STATUS      current
	DESCRIPTION
	"Table entry for sessionContextDaemonCountersInFlight"
	INDEX { sessionContextDaemonCountersInFlightLevelName }
	::={sessionContextDaemonCountersInFlightLevelTable 1}

SessionContextDaemonCountersInFlightLevelEntry ::=
	SEQUENCE {
		sessionContextDaemonCountersInFlightLevelName	DisplayString,
		sessionContextDaemonCountersInFlightLevelVal	CounterBasedGauge64,
		sessionContextDaemonCountersInFlightLevelMax	CounterBasedGauge64
	}

sessionContextDaemonCountersInFlightLevelName OBJECT-TYPE
	SYNTAX      DisplayString
	MAX-ACCESS  not-accessible
	STATUS      current
	DESCRIPTION
	"Table entry display string for sessionContextDaemonCountersInFlight"
	::={sessionContextDaemonCountersInFlightLevelEntry 1}

sessionContextDaemonCountersInFlightLevelVal OBJECT-TYPE
	SYNTAX	 CounterBasedGauge64
	MAX-ACCESS  read-only
	STATUS      current
	DESCRIPTION
	"Table entry attribute for sessionContextDaemonCountersInFlight"
	::={sessionContextDaemonCountersInFlightLevelEntry 2}

sessionContextDaemonCountersInFlightLevelMax OBJECT-TYPE
	SYNTAX	 CounterBasedGauge64
	MAX-ACCESS  read-only
	STATUS      current
	DESCRIPTION
	"Table entry attribute for sessionContextDaemonCountersInFlight"
	::={sessionContextDaemonCountersInFlightLevelEntry 4}


sessionContextDaemonCurrentOverlappedRows	OBJECT IDENTIFIER ::={sessionContextDaemon 10}

sessionContextDaemonCurrentOverlappedRowsVal	OBJECT-TYPE
	SYNTAX	 CounterBasedGauge64
	MAX-ACCESS read-only
	STATUS current
	DESCRIPTION "Current number of disabled items (covered)"

	::={sessionContextDaemonCurrentOverlappedRows 1}

sessionContextDaemonCurrentOverlappedRowsMax	OBJECT-TYPE
	SYNTAX	 CounterBasedGauge64
	MAX-ACCESS read-only
	STATUS current
	DESCRIPTION "Current number of disabled items (covered)"

	::={sessionContextDaemonCurrentOverlappedRows 3}

sessionContextDaemonCurrentOverlappedRowsLevelTable OBJECT-TYPE
	SYNTAX      SEQUENCE OF SessionContextDaemonCurrentOverlappedRowsLevelEntry
	MAX-ACCESS  not-accessible
	STATUS      current
	DESCRIPTION
	"Table for sessionContextDaemonCurrentOverlappedRows"
	::={sessionContextDaemonCurrentOverlappedRows 4}

sessionContextDaemonCurrentOverlappedRowsLevelEntry OBJECT-TYPE
	SYNTAX      SessionContextDaemonCurrentOverlappedRowsLevelEntry
	MAX-ACCESS  not-accessible
	STATUS      current
	DESCRIPTION
	"Table entry for sessionContextDaemonCurrentOverlappedRows"
	INDEX { sessionContextDaemonCurrentOverlappedRowsLevelName }
	::={sessionContextDaemonCurrentOverlappedRowsLevelTable 1}

SessionContextDaemonCurrentOverlappedRowsLevelEntry ::=
	SEQUENCE {
		sessionContextDaemonCurrentOverlappedRowsLevelName	DisplayString,
		sessionContextDaemonCurrentOverlappedRowsLevelVal	CounterBasedGauge64,
		sessionContextDaemonCurrentOverlappedRowsLevelMax	CounterBasedGauge64
	}

sessionContextDaemonCurrentOverlappedRowsLevelName OBJECT-TYPE
	SYNTAX      DisplayString
	MAX-ACCESS  not-accessible
	STATUS      current
	DESCRIPTION
	"Table entry display string for sessionContextDaemonCurrentOverlappedRows"
	::={sessionContextDaemonCurrentOverlappedRowsLevelEntry 1}

sessionContextDaemonCurrentOverlappedRowsLevelVal OBJECT-TYPE
	SYNTAX	 CounterBasedGauge64
	MAX-ACCESS  read-only
	STATUS      current
	DESCRIPTION
	"Table entry attribute for sessionContextDaemonCurrentOverlappedRows"
	::={sessionContextDaemonCurrentOverlappedRowsLevelEntry 2}

sessionContextDaemonCurrentOverlappedRowsLevelMax OBJECT-TYPE
	SYNTAX	 CounterBasedGauge64
	MAX-ACCESS  read-only
	STATUS      current
	DESCRIPTION
	"Table entry attribute for sessionContextDaemonCurrentOverlappedRows"
	::={sessionContextDaemonCurrentOverlappedRowsLevelEntry 4}


sessionContextDaemonOverlappingRows	OBJECT IDENTIFIER ::={sessionContextDaemon 11}

sessionContextDaemonOverlappingRowsVal	OBJECT-TYPE
	SYNTAX	 Counter64
	MAX-ACCESS read-only
	STATUS current
	DESCRIPTION "Overlapping provisioning"

	::={sessionContextDaemonOverlappingRows 1}

sessionContextDaemonOverlappingRowsMom	OBJECT-TYPE
	SYNTAX	 CounterBasedGauge64
	MAX-ACCESS read-only
	STATUS current
	DESCRIPTION "Overlapping provisioning"

	::={sessionContextDaemonOverlappingRows 2}

sessionContextDaemonOverlappingRowsMax	OBJECT-TYPE
	SYNTAX	 CounterBasedGauge64
	MAX-ACCESS read-only
	STATUS current
	DESCRIPTION "Overlapping provisioning"

	::={sessionContextDaemonOverlappingRows 3}

sessionContextDaemonOverlappingRowsLevelTable OBJECT-TYPE
	SYNTAX      SEQUENCE OF SessionContextDaemonOverlappingRowsLevelEntry
	MAX-ACCESS  not-accessible
	STATUS      current
	DESCRIPTION
	"Table for sessionContextDaemonOverlappingRows"
	::={sessionContextDaemonOverlappingRows 4}

sessionContextDaemonOverlappingRowsLevelEntry OBJECT-TYPE
	SYNTAX      SessionContextDaemonOverlappingRowsLevelEntry
	MAX-ACCESS  not-accessible
	STATUS      current
	DESCRIPTION
	"Table entry for sessionContextDaemonOverlappingRows"
	INDEX { sessionContextDaemonOverlappingRowsLevelName }
	::={sessionContextDaemonOverlappingRowsLevelTable 1}

SessionContextDaemonOverlappingRowsLevelEntry ::=
	SEQUENCE {
		sessionContextDaemonOverlappingRowsLevelName	DisplayString,
		sessionContextDaemonOverlappingRowsLevelVal	Counter64,
		sessionContextDaemonOverlappingRowsLevelMom	CounterBasedGauge64,
		sessionContextDaemonOverlappingRowsLevelMax	CounterBasedGauge64
	}

sessionContextDaemonOverlappingRowsLevelName OBJECT-TYPE
	SYNTAX      DisplayString
	MAX-ACCESS  not-accessible
	STATUS      current
	DESCRIPTION
	"Table entry display string for sessionContextDaemonOverlappingRows"
	::={sessionContextDaemonOverlappingRowsLevelEntry 1}

sessionContextDaemonOverlappingRowsLevelVal OBJECT-TYPE
	SYNTAX	 Counter64
	MAX-ACCESS  read-only
	STATUS      current
	DESCRIPTION
	"Table entry attribute for sessionContextDaemonOverlappingRows"
	::={sessionContextDaemonOverlappingRowsLevelEntry 2}

sessionContextDaemonOverlappingRowsLevelMom OBJECT-TYPE
	SYNTAX	 CounterBasedGauge64
	MAX-ACCESS  read-only
	STATUS      current
	DESCRIPTION
	"Table entry attribute for sessionContextDaemonOverlappingRows"
	::={sessionContextDaemonOverlappingRowsLevelEntry 3}

sessionContextDaemonOverlappingRowsLevelMax OBJECT-TYPE
	SYNTAX	 CounterBasedGauge64
	MAX-ACCESS  read-only
	STATUS      current
	DESCRIPTION
	"Table entry attribute for sessionContextDaemonOverlappingRows"
	::={sessionContextDaemonOverlappingRowsLevelEntry 4}


sessionContextDaemonAccountedInboundData	OBJECT IDENTIFIER ::={sessionContextDaemon 12}

sessionContextDaemonAccountedInboundDataVal	OBJECT-TYPE
	SYNTAX	 Counter64
	MAX-ACCESS read-only
	STATUS current
	DESCRIPTION "Accounted inbound data"

	::={sessionContextDaemonAccountedInboundData 1}

sessionContextDaemonAccountedInboundDataMom	OBJECT-TYPE
	SYNTAX	 CounterBasedGauge64
	MAX-ACCESS read-only
	STATUS current
	DESCRIPTION "Accounted inbound data"

	::={sessionContextDaemonAccountedInboundData 2}

sessionContextDaemonAccountedInboundDataMax	OBJECT-TYPE
	SYNTAX	 CounterBasedGauge64
	MAX-ACCESS read-only
	STATUS current
	DESCRIPTION "Accounted inbound data"

	::={sessionContextDaemonAccountedInboundData 3}

sessionContextDaemonAccountedInboundDataLevelTable OBJECT-TYPE
	SYNTAX      SEQUENCE OF SessionContextDaemonAccountedInboundDataLevelEntry
	MAX-ACCESS  not-accessible
	STATUS      current
	DESCRIPTION
	"Table for sessionContextDaemonAccountedInboundData"
	::={sessionContextDaemonAccountedInboundData 4}

sessionContextDaemonAccountedInboundDataLevelEntry OBJECT-TYPE
	SYNTAX      SessionContextDaemonAccountedInboundDataLevelEntry
	MAX-ACCESS  not-accessible
	STATUS      current
	DESCRIPTION
	"Table entry for sessionContextDaemonAccountedInboundData"
	INDEX { sessionContextDaemonAccountedInboundDataLevelName }
	::={sessionContextDaemonAccountedInboundDataLevelTable 1}

SessionContextDaemonAccountedInboundDataLevelEntry ::=
	SEQUENCE {
		sessionContextDaemonAccountedInboundDataLevelName	DisplayString,
		sessionContextDaemonAccountedInboundDataLevelVal	Counter64,
		sessionContextDaemonAccountedInboundDataLevelMom	CounterBasedGauge64,
		sessionContextDaemonAccountedInboundDataLevelMax	CounterBasedGauge64
	}

sessionContextDaemonAccountedInboundDataLevelName OBJECT-TYPE
	SYNTAX      DisplayString
	MAX-ACCESS  not-accessible
	STATUS      current
	DESCRIPTION
	"Table entry display string for sessionContextDaemonAccountedInboundData"
	::={sessionContextDaemonAccountedInboundDataLevelEntry 1}

sessionContextDaemonAccountedInboundDataLevelVal OBJECT-TYPE
	SYNTAX	 Counter64
	MAX-ACCESS  read-only
	STATUS      current
	DESCRIPTION
	"Table entry attribute for sessionContextDaemonAccountedInboundData"
	::={sessionContextDaemonAccountedInboundDataLevelEntry 2}

sessionContextDaemonAccountedInboundDataLevelMom OBJECT-TYPE
	SYNTAX	 CounterBasedGauge64
	MAX-ACCESS  read-only
	STATUS      current
	DESCRIPTION
	"Table entry attribute for sessionContextDaemonAccountedInboundData"
	::={sessionContextDaemonAccountedInboundDataLevelEntry 3}

sessionContextDaemonAccountedInboundDataLevelMax OBJECT-TYPE
	SYNTAX	 CounterBasedGauge64
	MAX-ACCESS  read-only
	STATUS      current
	DESCRIPTION
	"Table entry attribute for sessionContextDaemonAccountedInboundData"
	::={sessionContextDaemonAccountedInboundDataLevelEntry 4}


sessionContextDaemonAccountedOutboundData	OBJECT IDENTIFIER ::={sessionContextDaemon 13}

sessionContextDaemonAccountedOutboundDataVal	OBJECT-TYPE
	SYNTAX	 Counter64
	MAX-ACCESS read-only
	STATUS current
	DESCRIPTION "Accounted outbound data"

	::={sessionContextDaemonAccountedOutboundData 1}

sessionContextDaemonAccountedOutboundDataMom	OBJECT-TYPE
	SYNTAX	 CounterBasedGauge64
	MAX-ACCESS read-only
	STATUS current
	DESCRIPTION "Accounted outbound data"

	::={sessionContextDaemonAccountedOutboundData 2}

sessionContextDaemonAccountedOutboundDataMax	OBJECT-TYPE
	SYNTAX	 CounterBasedGauge64
	MAX-ACCESS read-only
	STATUS current
	DESCRIPTION "Accounted outbound data"

	::={sessionContextDaemonAccountedOutboundData 3}

sessionContextDaemonAccountedOutboundDataLevelTable OBJECT-TYPE
	SYNTAX      SEQUENCE OF SessionContextDaemonAccountedOutboundDataLevelEntry
	MAX-ACCESS  not-accessible
	STATUS      current
	DESCRIPTION
	"Table for sessionContextDaemonAccountedOutboundData"
	::={sessionContextDaemonAccountedOutboundData 4}

sessionContextDaemonAccountedOutboundDataLevelEntry OBJECT-TYPE
	SYNTAX      SessionContextDaemonAccountedOutboundDataLevelEntry
	MAX-ACCESS  not-accessible
	STATUS      current
	DESCRIPTION
	"Table entry for sessionContextDaemonAccountedOutboundData"
	INDEX { sessionContextDaemonAccountedOutboundDataLevelName }
	::={sessionContextDaemonAccountedOutboundDataLevelTable 1}

SessionContextDaemonAccountedOutboundDataLevelEntry ::=
	SEQUENCE {
		sessionContextDaemonAccountedOutboundDataLevelName	DisplayString,
		sessionContextDaemonAccountedOutboundDataLevelVal	Counter64,
		sessionContextDaemonAccountedOutboundDataLevelMom	CounterBasedGauge64,
		sessionContextDaemonAccountedOutboundDataLevelMax	CounterBasedGauge64
	}

sessionContextDaemonAccountedOutboundDataLevelName OBJECT-TYPE
	SYNTAX      DisplayString
	MAX-ACCESS  not-accessible
	STATUS      current
	DESCRIPTION
	"Table entry display string for sessionContextDaemonAccountedOutboundData"
	::={sessionContextDaemonAccountedOutboundDataLevelEntry 1}

sessionContextDaemonAccountedOutboundDataLevelVal OBJECT-TYPE
	SYNTAX	 Counter64
	MAX-ACCESS  read-only
	STATUS      current
	DESCRIPTION
	"Table entry attribute for sessionContextDaemonAccountedOutboundData"
	::={sessionContextDaemonAccountedOutboundDataLevelEntry 2}

sessionContextDaemonAccountedOutboundDataLevelMom OBJECT-TYPE
	SYNTAX	 CounterBasedGauge64
	MAX-ACCESS  read-only
	STATUS      current
	DESCRIPTION
	"Table entry attribute for sessionContextDaemonAccountedOutboundData"
	::={sessionContextDaemonAccountedOutboundDataLevelEntry 3}

sessionContextDaemonAccountedOutboundDataLevelMax OBJECT-TYPE
	SYNTAX	 CounterBasedGauge64
	MAX-ACCESS  read-only
	STATUS      current
	DESCRIPTION
	"Table entry attribute for sessionContextDaemonAccountedOutboundData"
	::={sessionContextDaemonAccountedOutboundDataLevelEntry 4}


sessionContextDaemonWorkQueueSize	OBJECT IDENTIFIER ::={sessionContextDaemon 14}

sessionContextDaemonWorkQueueSizeVal	OBJECT-TYPE
	SYNTAX	 CounterBasedGauge64
	MAX-ACCESS read-only
	STATUS current
	DESCRIPTION "Work queue size"

	::={sessionContextDaemonWorkQueueSize 1}

sessionContextDaemonWorkQueueSizeMax	OBJECT-TYPE
	SYNTAX	 CounterBasedGauge64
	MAX-ACCESS read-only
	STATUS current
	DESCRIPTION "Work queue size"

	::={sessionContextDaemonWorkQueueSize 3}

sessionContextDaemonWorkQueueSizeLevelTable OBJECT-TYPE
	SYNTAX      SEQUENCE OF SessionContextDaemonWorkQueueSizeLevelEntry
	MAX-ACCESS  not-accessible
	STATUS      current
	DESCRIPTION
	"Table for sessionContextDaemonWorkQueueSize"
	::={sessionContextDaemonWorkQueueSize 4}

sessionContextDaemonWorkQueueSizeLevelEntry OBJECT-TYPE
	SYNTAX      SessionContextDaemonWorkQueueSizeLevelEntry
	MAX-ACCESS  not-accessible
	STATUS      current
	DESCRIPTION
	"Table entry for sessionContextDaemonWorkQueueSize"
	INDEX { sessionContextDaemonWorkQueueSizeLevelName }
	::={sessionContextDaemonWorkQueueSizeLevelTable 1}

SessionContextDaemonWorkQueueSizeLevelEntry ::=
	SEQUENCE {
		sessionContextDaemonWorkQueueSizeLevelName	DisplayString,
		sessionContextDaemonWorkQueueSizeLevelVal	CounterBasedGauge64,
		sessionContextDaemonWorkQueueSizeLevelMax	CounterBasedGauge64
	}

sessionContextDaemonWorkQueueSizeLevelName OBJECT-TYPE
	SYNTAX      DisplayString
	MAX-ACCESS  not-accessible
	STATUS      current
	DESCRIPTION
	"Table entry display string for sessionContextDaemonWorkQueueSize"
	::={sessionContextDaemonWorkQueueSizeLevelEntry 1}

sessionContextDaemonWorkQueueSizeLevelVal OBJECT-TYPE
	SYNTAX	 CounterBasedGauge64
	MAX-ACCESS  read-only
	STATUS      current
	DESCRIPTION
	"Table entry attribute for sessionContextDaemonWorkQueueSize"
	::={sessionContextDaemonWorkQueueSizeLevelEntry 2}

sessionContextDaemonWorkQueueSizeLevelMax OBJECT-TYPE
	SYNTAX	 CounterBasedGauge64
	MAX-ACCESS  read-only
	STATUS      current
	DESCRIPTION
	"Table entry attribute for sessionContextDaemonWorkQueueSize"
	::={sessionContextDaemonWorkQueueSizeLevelEntry 4}


sessionContextDaemonCountersDropped	OBJECT IDENTIFIER ::={sessionContextDaemon 15}

sessionContextDaemonCountersDroppedVal	OBJECT-TYPE
	SYNTAX	 CounterBasedGauge64
	MAX-ACCESS read-only
	STATUS current
	DESCRIPTION "Counters Dropped"

	::={sessionContextDaemonCountersDropped 1}

sessionContextDaemonCountersDroppedMax	OBJECT-TYPE
	SYNTAX	 CounterBasedGauge64
	MAX-ACCESS read-only
	STATUS current
	DESCRIPTION "Counters Dropped"

	::={sessionContextDaemonCountersDropped 3}

sessionContextDaemonCountersDroppedLevelTable OBJECT-TYPE
	SYNTAX      SEQUENCE OF SessionContextDaemonCountersDroppedLevelEntry
	MAX-ACCESS  not-accessible
	STATUS      current
	DESCRIPTION
	"Table for sessionContextDaemonCountersDropped"
	::={sessionContextDaemonCountersDropped 4}

sessionContextDaemonCountersDroppedLevelEntry OBJECT-TYPE
	SYNTAX      SessionContextDaemonCountersDroppedLevelEntry
	MAX-ACCESS  not-accessible
	STATUS      current
	DESCRIPTION
	"Table entry for sessionContextDaemonCountersDropped"
	INDEX { sessionContextDaemonCountersDroppedLevelName }
	::={sessionContextDaemonCountersDroppedLevelTable 1}

SessionContextDaemonCountersDroppedLevelEntry ::=
	SEQUENCE {
		sessionContextDaemonCountersDroppedLevelName	DisplayString,
		sessionContextDaemonCountersDroppedLevelVal	CounterBasedGauge64,
		sessionContextDaemonCountersDroppedLevelMax	CounterBasedGauge64
	}

sessionContextDaemonCountersDroppedLevelName OBJECT-TYPE
	SYNTAX      DisplayString
	MAX-ACCESS  not-accessible
	STATUS      current
	DESCRIPTION
	"Table entry display string for sessionContextDaemonCountersDropped"
	::={sessionContextDaemonCountersDroppedLevelEntry 1}

sessionContextDaemonCountersDroppedLevelVal OBJECT-TYPE
	SYNTAX	 CounterBasedGauge64
	MAX-ACCESS  read-only
	STATUS      current
	DESCRIPTION
	"Table entry attribute for sessionContextDaemonCountersDropped"
	::={sessionContextDaemonCountersDroppedLevelEntry 2}

sessionContextDaemonCountersDroppedLevelMax OBJECT-TYPE
	SYNTAX	 CounterBasedGauge64
	MAX-ACCESS  read-only
	STATUS      current
	DESCRIPTION
	"Table entry attribute for sessionContextDaemonCountersDropped"
	::={sessionContextDaemonCountersDroppedLevelEntry 4}


sessionContextDaemonBarrierMessagesAcked	OBJECT IDENTIFIER ::={sessionContextDaemon 16}

sessionContextDaemonBarrierMessagesAckedVal	OBJECT-TYPE
	SYNTAX	 Counter64
	MAX-ACCESS read-only
	STATUS current
	DESCRIPTION "Barrier messages acked"

	::={sessionContextDaemonBarrierMessagesAcked 1}

sessionContextDaemonBarrierMessagesAckedMom	OBJECT-TYPE
	SYNTAX	 CounterBasedGauge64
	MAX-ACCESS read-only
	STATUS current
	DESCRIPTION "Barrier messages acked"

	::={sessionContextDaemonBarrierMessagesAcked 2}

sessionContextDaemonBarrierMessagesAckedMax	OBJECT-TYPE
	SYNTAX	 CounterBasedGauge64
	MAX-ACCESS read-only
	STATUS current
	DESCRIPTION "Barrier messages acked"

	::={sessionContextDaemonBarrierMessagesAcked 3}

sessionContextDaemonBarrierMessagesAckedLevelTable OBJECT-TYPE
	SYNTAX      SEQUENCE OF SessionContextDaemonBarrierMessagesAckedLevelEntry
	MAX-ACCESS  not-accessible
	STATUS      current
	DESCRIPTION
	"Table for sessionContextDaemonBarrierMessagesAcked"
	::={sessionContextDaemonBarrierMessagesAcked 4}

sessionContextDaemonBarrierMessagesAckedLevelEntry OBJECT-TYPE
	SYNTAX      SessionContextDaemonBarrierMessagesAckedLevelEntry
	MAX-ACCESS  not-accessible
	STATUS      current
	DESCRIPTION
	"Table entry for sessionContextDaemonBarrierMessagesAcked"
	INDEX { sessionContextDaemonBarrierMessagesAckedLevelName }
	::={sessionContextDaemonBarrierMessagesAckedLevelTable 1}

SessionContextDaemonBarrierMessagesAckedLevelEntry ::=
	SEQUENCE {
		sessionContextDaemonBarrierMessagesAckedLevelName	DisplayString,
		sessionContextDaemonBarrierMessagesAckedLevelVal	Counter64,
		sessionContextDaemonBarrierMessagesAckedLevelMom	CounterBasedGauge64,
		sessionContextDaemonBarrierMessagesAckedLevelMax	CounterBasedGauge64
	}

sessionContextDaemonBarrierMessagesAckedLevelName OBJECT-TYPE
	SYNTAX      DisplayString
	MAX-ACCESS  not-accessible
	STATUS      current
	DESCRIPTION
	"Table entry display string for sessionContextDaemonBarrierMessagesAcked"
	::={sessionContextDaemonBarrierMessagesAckedLevelEntry 1}

sessionContextDaemonBarrierMessagesAckedLevelVal OBJECT-TYPE
	SYNTAX	 Counter64
	MAX-ACCESS  read-only
	STATUS      current
	DESCRIPTION
	"Table entry attribute for sessionContextDaemonBarrierMessagesAcked"
	::={sessionContextDaemonBarrierMessagesAckedLevelEntry 2}

sessionContextDaemonBarrierMessagesAckedLevelMom OBJECT-TYPE
	SYNTAX	 CounterBasedGauge64
	MAX-ACCESS  read-only
	STATUS      current
	DESCRIPTION
	"Table entry attribute for sessionContextDaemonBarrierMessagesAcked"
	::={sessionContextDaemonBarrierMessagesAckedLevelEntry 3}

sessionContextDaemonBarrierMessagesAckedLevelMax OBJECT-TYPE
	SYNTAX	 CounterBasedGauge64
	MAX-ACCESS  read-only
	STATUS      current
	DESCRIPTION
	"Table entry attribute for sessionContextDaemonBarrierMessagesAcked"
	::={sessionContextDaemonBarrierMessagesAckedLevelEntry 4}


sessionContextDaemonCountersSplit	OBJECT IDENTIFIER ::={sessionContextDaemon 17}

sessionContextDaemonCountersSplitVal	OBJECT-TYPE
	SYNTAX	 CounterBasedGauge64
	MAX-ACCESS read-only
	STATUS current
	DESCRIPTION "Splitted counter updates"

	::={sessionContextDaemonCountersSplit 1}

sessionContextDaemonCountersSplitMax	OBJECT-TYPE
	SYNTAX	 CounterBasedGauge64
	MAX-ACCESS read-only
	STATUS current
	DESCRIPTION "Splitted counter updates"

	::={sessionContextDaemonCountersSplit 3}

sessionContextDaemonCountersSplitLevelTable OBJECT-TYPE
	SYNTAX      SEQUENCE OF SessionContextDaemonCountersSplitLevelEntry
	MAX-ACCESS  not-accessible
	STATUS      current
	DESCRIPTION
	"Table for sessionContextDaemonCountersSplit"
	::={sessionContextDaemonCountersSplit 4}

sessionContextDaemonCountersSplitLevelEntry OBJECT-TYPE
	SYNTAX      SessionContextDaemonCountersSplitLevelEntry
	MAX-ACCESS  not-accessible
	STATUS      current
	DESCRIPTION
	"Table entry for sessionContextDaemonCountersSplit"
	INDEX { sessionContextDaemonCountersSplitLevelName }
	::={sessionContextDaemonCountersSplitLevelTable 1}

SessionContextDaemonCountersSplitLevelEntry ::=
	SEQUENCE {
		sessionContextDaemonCountersSplitLevelName	DisplayString,
		sessionContextDaemonCountersSplitLevelVal	CounterBasedGauge64,
		sessionContextDaemonCountersSplitLevelMax	CounterBasedGauge64
	}

sessionContextDaemonCountersSplitLevelName OBJECT-TYPE
	SYNTAX      DisplayString
	MAX-ACCESS  not-accessible
	STATUS      current
	DESCRIPTION
	"Table entry display string for sessionContextDaemonCountersSplit"
	::={sessionContextDaemonCountersSplitLevelEntry 1}

sessionContextDaemonCountersSplitLevelVal OBJECT-TYPE
	SYNTAX	 CounterBasedGauge64
	MAX-ACCESS  read-only
	STATUS      current
	DESCRIPTION
	"Table entry attribute for sessionContextDaemonCountersSplit"
	::={sessionContextDaemonCountersSplitLevelEntry 2}

sessionContextDaemonCountersSplitLevelMax OBJECT-TYPE
	SYNTAX	 CounterBasedGauge64
	MAX-ACCESS  read-only
	STATUS      current
	DESCRIPTION
	"Table entry attribute for sessionContextDaemonCountersSplit"
	::={sessionContextDaemonCountersSplitLevelEntry 4}


linesharing	OBJECT IDENTIFIER ::={sysdiag 153}

linesharingHosts	OBJECT IDENTIFIER ::={linesharing 1}

linesharingHostsVal	OBJECT-TYPE
	SYNTAX	 CounterBasedGauge64
	MAX-ACCESS read-only
	STATUS current
	DESCRIPTION "Number of Hosts"

	::={linesharingHosts 1}

linesharingHostsMax	OBJECT-TYPE
	SYNTAX	 CounterBasedGauge64
	MAX-ACCESS read-only
	STATUS current
	DESCRIPTION "Number of Hosts"

	::={linesharingHosts 3}

linesharingHostsLevelTable OBJECT-TYPE
	SYNTAX      SEQUENCE OF LinesharingHostsLevelEntry
	MAX-ACCESS  not-accessible
	STATUS      current
	DESCRIPTION
	"Table for linesharingHosts"
	::={linesharingHosts 4}

linesharingHostsLevelEntry OBJECT-TYPE
	SYNTAX      LinesharingHostsLevelEntry
	MAX-ACCESS  not-accessible
	STATUS      current
	DESCRIPTION
	"Table entry for linesharingHosts"
	INDEX { linesharingHostsLevelName }
	::={linesharingHostsLevelTable 1}

LinesharingHostsLevelEntry ::=
	SEQUENCE {
		linesharingHostsLevelName	DisplayString,
		linesharingHostsLevelVal	CounterBasedGauge64,
		linesharingHostsLevelMax	CounterBasedGauge64
	}

linesharingHostsLevelName OBJECT-TYPE
	SYNTAX      DisplayString
	MAX-ACCESS  not-accessible
	STATUS      current
	DESCRIPTION
	"Table entry display string for linesharingHosts"
	::={linesharingHostsLevelEntry 1}

linesharingHostsLevelVal OBJECT-TYPE
	SYNTAX	 CounterBasedGauge64
	MAX-ACCESS  read-only
	STATUS      current
	DESCRIPTION
	"Table entry attribute for linesharingHosts"
	::={linesharingHostsLevelEntry 2}

linesharingHostsLevelMax OBJECT-TYPE
	SYNTAX	 CounterBasedGauge64
	MAX-ACCESS  read-only
	STATUS      current
	DESCRIPTION
	"Table entry attribute for linesharingHosts"
	::={linesharingHostsLevelEntry 4}


linesharingHostsCreated	OBJECT IDENTIFIER ::={linesharing 2}

linesharingHostsCreatedVal	OBJECT-TYPE
	SYNTAX	 Counter64
	MAX-ACCESS read-only
	STATUS current
	DESCRIPTION "Hosts Created"

	::={linesharingHostsCreated 1}

linesharingHostsCreatedMom	OBJECT-TYPE
	SYNTAX	 CounterBasedGauge64
	MAX-ACCESS read-only
	STATUS current
	DESCRIPTION "Hosts Created"

	::={linesharingHostsCreated 2}

linesharingHostsCreatedMax	OBJECT-TYPE
	SYNTAX	 CounterBasedGauge64
	MAX-ACCESS read-only
	STATUS current
	DESCRIPTION "Hosts Created"

	::={linesharingHostsCreated 3}

linesharingHostsCreatedLevelTable OBJECT-TYPE
	SYNTAX      SEQUENCE OF LinesharingHostsCreatedLevelEntry
	MAX-ACCESS  not-accessible
	STATUS      current
	DESCRIPTION
	"Table for linesharingHostsCreated"
	::={linesharingHostsCreated 4}

linesharingHostsCreatedLevelEntry OBJECT-TYPE
	SYNTAX      LinesharingHostsCreatedLevelEntry
	MAX-ACCESS  not-accessible
	STATUS      current
	DESCRIPTION
	"Table entry for linesharingHostsCreated"
	INDEX { linesharingHostsCreatedLevelName }
	::={linesharingHostsCreatedLevelTable 1}

LinesharingHostsCreatedLevelEntry ::=
	SEQUENCE {
		linesharingHostsCreatedLevelName	DisplayString,
		linesharingHostsCreatedLevelVal	Counter64,
		linesharingHostsCreatedLevelMom	CounterBasedGauge64,
		linesharingHostsCreatedLevelMax	CounterBasedGauge64
	}

linesharingHostsCreatedLevelName OBJECT-TYPE
	SYNTAX      DisplayString
	MAX-ACCESS  not-accessible
	STATUS      current
	DESCRIPTION
	"Table entry display string for linesharingHostsCreated"
	::={linesharingHostsCreatedLevelEntry 1}

linesharingHostsCreatedLevelVal OBJECT-TYPE
	SYNTAX	 Counter64
	MAX-ACCESS  read-only
	STATUS      current
	DESCRIPTION
	"Table entry attribute for linesharingHostsCreated"
	::={linesharingHostsCreatedLevelEntry 2}

linesharingHostsCreatedLevelMom OBJECT-TYPE
	SYNTAX	 CounterBasedGauge64
	MAX-ACCESS  read-only
	STATUS      current
	DESCRIPTION
	"Table entry attribute for linesharingHostsCreated"
	::={linesharingHostsCreatedLevelEntry 3}

linesharingHostsCreatedLevelMax OBJECT-TYPE
	SYNTAX	 CounterBasedGauge64
	MAX-ACCESS  read-only
	STATUS      current
	DESCRIPTION
	"Table entry attribute for linesharingHostsCreated"
	::={linesharingHostsCreatedLevelEntry 4}


linesharingHostsDeleted	OBJECT IDENTIFIER ::={linesharing 3}

linesharingHostsDeletedVal	OBJECT-TYPE
	SYNTAX	 Counter64
	MAX-ACCESS read-only
	STATUS current
	DESCRIPTION "Hosts Deleted"

	::={linesharingHostsDeleted 1}

linesharingHostsDeletedMom	OBJECT-TYPE
	SYNTAX	 CounterBasedGauge64
	MAX-ACCESS read-only
	STATUS current
	DESCRIPTION "Hosts Deleted"

	::={linesharingHostsDeleted 2}

linesharingHostsDeletedMax	OBJECT-TYPE
	SYNTAX	 CounterBasedGauge64
	MAX-ACCESS read-only
	STATUS current
	DESCRIPTION "Hosts Deleted"

	::={linesharingHostsDeleted 3}

linesharingHostsDeletedLevelTable OBJECT-TYPE
	SYNTAX      SEQUENCE OF LinesharingHostsDeletedLevelEntry
	MAX-ACCESS  not-accessible
	STATUS      current
	DESCRIPTION
	"Table for linesharingHostsDeleted"
	::={linesharingHostsDeleted 4}

linesharingHostsDeletedLevelEntry OBJECT-TYPE
	SYNTAX      LinesharingHostsDeletedLevelEntry
	MAX-ACCESS  not-accessible
	STATUS      current
	DESCRIPTION
	"Table entry for linesharingHostsDeleted"
	INDEX { linesharingHostsDeletedLevelName }
	::={linesharingHostsDeletedLevelTable 1}

LinesharingHostsDeletedLevelEntry ::=
	SEQUENCE {
		linesharingHostsDeletedLevelName	DisplayString,
		linesharingHostsDeletedLevelVal	Counter64,
		linesharingHostsDeletedLevelMom	CounterBasedGauge64,
		linesharingHostsDeletedLevelMax	CounterBasedGauge64
	}

linesharingHostsDeletedLevelName OBJECT-TYPE
	SYNTAX      DisplayString
	MAX-ACCESS  not-accessible
	STATUS      current
	DESCRIPTION
	"Table entry display string for linesharingHostsDeleted"
	::={linesharingHostsDeletedLevelEntry 1}

linesharingHostsDeletedLevelVal OBJECT-TYPE
	SYNTAX	 Counter64
	MAX-ACCESS  read-only
	STATUS      current
	DESCRIPTION
	"Table entry attribute for linesharingHostsDeleted"
	::={linesharingHostsDeletedLevelEntry 2}

linesharingHostsDeletedLevelMom OBJECT-TYPE
	SYNTAX	 CounterBasedGauge64
	MAX-ACCESS  read-only
	STATUS      current
	DESCRIPTION
	"Table entry attribute for linesharingHostsDeleted"
	::={linesharingHostsDeletedLevelEntry 3}

linesharingHostsDeletedLevelMax OBJECT-TYPE
	SYNTAX	 CounterBasedGauge64
	MAX-ACCESS  read-only
	STATUS      current
	DESCRIPTION
	"Table entry attribute for linesharingHostsDeleted"
	::={linesharingHostsDeletedLevelEntry 4}


linesharingDevicesTs	OBJECT IDENTIFIER ::={linesharing 4}

linesharingDevicesTsVal	OBJECT-TYPE
	SYNTAX	 CounterBasedGauge64
	MAX-ACCESS read-only
	STATUS current
	DESCRIPTION "Timestamp Devices"

	::={linesharingDevicesTs 1}

linesharingDevicesTsMax	OBJECT-TYPE
	SYNTAX	 CounterBasedGauge64
	MAX-ACCESS read-only
	STATUS current
	DESCRIPTION "Timestamp Devices"

	::={linesharingDevicesTs 3}

linesharingDevicesTsLevelTable OBJECT-TYPE
	SYNTAX      SEQUENCE OF LinesharingDevicesTsLevelEntry
	MAX-ACCESS  not-accessible
	STATUS      current
	DESCRIPTION
	"Table for linesharingDevicesTs"
	::={linesharingDevicesTs 4}

linesharingDevicesTsLevelEntry OBJECT-TYPE
	SYNTAX      LinesharingDevicesTsLevelEntry
	MAX-ACCESS  not-accessible
	STATUS      current
	DESCRIPTION
	"Table entry for linesharingDevicesTs"
	INDEX { linesharingDevicesTsLevelName }
	::={linesharingDevicesTsLevelTable 1}

LinesharingDevicesTsLevelEntry ::=
	SEQUENCE {
		linesharingDevicesTsLevelName	DisplayString,
		linesharingDevicesTsLevelVal	CounterBasedGauge64,
		linesharingDevicesTsLevelMax	CounterBasedGauge64
	}

linesharingDevicesTsLevelName OBJECT-TYPE
	SYNTAX      DisplayString
	MAX-ACCESS  not-accessible
	STATUS      current
	DESCRIPTION
	"Table entry display string for linesharingDevicesTs"
	::={linesharingDevicesTsLevelEntry 1}

linesharingDevicesTsLevelVal OBJECT-TYPE
	SYNTAX	 CounterBasedGauge64
	MAX-ACCESS  read-only
	STATUS      current
	DESCRIPTION
	"Table entry attribute for linesharingDevicesTs"
	::={linesharingDevicesTsLevelEntry 2}

linesharingDevicesTsLevelMax OBJECT-TYPE
	SYNTAX	 CounterBasedGauge64
	MAX-ACCESS  read-only
	STATUS      current
	DESCRIPTION
	"Table entry attribute for linesharingDevicesTs"
	::={linesharingDevicesTsLevelEntry 4}


linesharingDevicesTsCreated	OBJECT IDENTIFIER ::={linesharing 5}

linesharingDevicesTsCreatedVal	OBJECT-TYPE
	SYNTAX	 Counter64
	MAX-ACCESS read-only
	STATUS current
	DESCRIPTION "Timestamp Devices Created"

	::={linesharingDevicesTsCreated 1}

linesharingDevicesTsCreatedMom	OBJECT-TYPE
	SYNTAX	 CounterBasedGauge64
	MAX-ACCESS read-only
	STATUS current
	DESCRIPTION "Timestamp Devices Created"

	::={linesharingDevicesTsCreated 2}

linesharingDevicesTsCreatedMax	OBJECT-TYPE
	SYNTAX	 CounterBasedGauge64
	MAX-ACCESS read-only
	STATUS current
	DESCRIPTION "Timestamp Devices Created"

	::={linesharingDevicesTsCreated 3}

linesharingDevicesTsCreatedLevelTable OBJECT-TYPE
	SYNTAX      SEQUENCE OF LinesharingDevicesTsCreatedLevelEntry
	MAX-ACCESS  not-accessible
	STATUS      current
	DESCRIPTION
	"Table for linesharingDevicesTsCreated"
	::={linesharingDevicesTsCreated 4}

linesharingDevicesTsCreatedLevelEntry OBJECT-TYPE
	SYNTAX      LinesharingDevicesTsCreatedLevelEntry
	MAX-ACCESS  not-accessible
	STATUS      current
	DESCRIPTION
	"Table entry for linesharingDevicesTsCreated"
	INDEX { linesharingDevicesTsCreatedLevelName }
	::={linesharingDevicesTsCreatedLevelTable 1}

LinesharingDevicesTsCreatedLevelEntry ::=
	SEQUENCE {
		linesharingDevicesTsCreatedLevelName	DisplayString,
		linesharingDevicesTsCreatedLevelVal	Counter64,
		linesharingDevicesTsCreatedLevelMom	CounterBasedGauge64,
		linesharingDevicesTsCreatedLevelMax	CounterBasedGauge64
	}

linesharingDevicesTsCreatedLevelName OBJECT-TYPE
	SYNTAX      DisplayString
	MAX-ACCESS  not-accessible
	STATUS      current
	DESCRIPTION
	"Table entry display string for linesharingDevicesTsCreated"
	::={linesharingDevicesTsCreatedLevelEntry 1}

linesharingDevicesTsCreatedLevelVal OBJECT-TYPE
	SYNTAX	 Counter64
	MAX-ACCESS  read-only
	STATUS      current
	DESCRIPTION
	"Table entry attribute for linesharingDevicesTsCreated"
	::={linesharingDevicesTsCreatedLevelEntry 2}

linesharingDevicesTsCreatedLevelMom OBJECT-TYPE
	SYNTAX	 CounterBasedGauge64
	MAX-ACCESS  read-only
	STATUS      current
	DESCRIPTION
	"Table entry attribute for linesharingDevicesTsCreated"
	::={linesharingDevicesTsCreatedLevelEntry 3}

linesharingDevicesTsCreatedLevelMax OBJECT-TYPE
	SYNTAX	 CounterBasedGauge64
	MAX-ACCESS  read-only
	STATUS      current
	DESCRIPTION
	"Table entry attribute for linesharingDevicesTsCreated"
	::={linesharingDevicesTsCreatedLevelEntry 4}


linesharingDevicesTsDeleted	OBJECT IDENTIFIER ::={linesharing 6}

linesharingDevicesTsDeletedVal	OBJECT-TYPE
	SYNTAX	 Counter64
	MAX-ACCESS read-only
	STATUS current
	DESCRIPTION "Timestamp Devices Deleted"

	::={linesharingDevicesTsDeleted 1}

linesharingDevicesTsDeletedMom	OBJECT-TYPE
	SYNTAX	 CounterBasedGauge64
	MAX-ACCESS read-only
	STATUS current
	DESCRIPTION "Timestamp Devices Deleted"

	::={linesharingDevicesTsDeleted 2}

linesharingDevicesTsDeletedMax	OBJECT-TYPE
	SYNTAX	 CounterBasedGauge64
	MAX-ACCESS read-only
	STATUS current
	DESCRIPTION "Timestamp Devices Deleted"

	::={linesharingDevicesTsDeleted 3}

linesharingDevicesTsDeletedLevelTable OBJECT-TYPE
	SYNTAX      SEQUENCE OF LinesharingDevicesTsDeletedLevelEntry
	MAX-ACCESS  not-accessible
	STATUS      current
	DESCRIPTION
	"Table for linesharingDevicesTsDeleted"
	::={linesharingDevicesTsDeleted 4}

linesharingDevicesTsDeletedLevelEntry OBJECT-TYPE
	SYNTAX      LinesharingDevicesTsDeletedLevelEntry
	MAX-ACCESS  not-accessible
	STATUS      current
	DESCRIPTION
	"Table entry for linesharingDevicesTsDeleted"
	INDEX { linesharingDevicesTsDeletedLevelName }
	::={linesharingDevicesTsDeletedLevelTable 1}

LinesharingDevicesTsDeletedLevelEntry ::=
	SEQUENCE {
		linesharingDevicesTsDeletedLevelName	DisplayString,
		linesharingDevicesTsDeletedLevelVal	Counter64,
		linesharingDevicesTsDeletedLevelMom	CounterBasedGauge64,
		linesharingDevicesTsDeletedLevelMax	CounterBasedGauge64
	}

linesharingDevicesTsDeletedLevelName OBJECT-TYPE
	SYNTAX      DisplayString
	MAX-ACCESS  not-accessible
	STATUS      current
	DESCRIPTION
	"Table entry display string for linesharingDevicesTsDeleted"
	::={linesharingDevicesTsDeletedLevelEntry 1}

linesharingDevicesTsDeletedLevelVal OBJECT-TYPE
	SYNTAX	 Counter64
	MAX-ACCESS  read-only
	STATUS      current
	DESCRIPTION
	"Table entry attribute for linesharingDevicesTsDeleted"
	::={linesharingDevicesTsDeletedLevelEntry 2}

linesharingDevicesTsDeletedLevelMom OBJECT-TYPE
	SYNTAX	 CounterBasedGauge64
	MAX-ACCESS  read-only
	STATUS      current
	DESCRIPTION
	"Table entry attribute for linesharingDevicesTsDeleted"
	::={linesharingDevicesTsDeletedLevelEntry 3}

linesharingDevicesTsDeletedLevelMax OBJECT-TYPE
	SYNTAX	 CounterBasedGauge64
	MAX-ACCESS  read-only
	STATUS      current
	DESCRIPTION
	"Table entry attribute for linesharingDevicesTsDeleted"
	::={linesharingDevicesTsDeletedLevelEntry 4}


linesharingDevicesTsVisible	OBJECT IDENTIFIER ::={linesharing 7}

linesharingDevicesTsVisibleVal	OBJECT-TYPE
	SYNTAX	 CounterBasedGauge64
	MAX-ACCESS read-only
	STATUS current
	DESCRIPTION "Timestamp Visible Devices"

	::={linesharingDevicesTsVisible 1}

linesharingDevicesTsVisibleMax	OBJECT-TYPE
	SYNTAX	 CounterBasedGauge64
	MAX-ACCESS read-only
	STATUS current
	DESCRIPTION "Timestamp Visible Devices"

	::={linesharingDevicesTsVisible 3}

linesharingDevicesTsVisibleLevelTable OBJECT-TYPE
	SYNTAX      SEQUENCE OF LinesharingDevicesTsVisibleLevelEntry
	MAX-ACCESS  not-accessible
	STATUS      current
	DESCRIPTION
	"Table for linesharingDevicesTsVisible"
	::={linesharingDevicesTsVisible 4}

linesharingDevicesTsVisibleLevelEntry OBJECT-TYPE
	SYNTAX      LinesharingDevicesTsVisibleLevelEntry
	MAX-ACCESS  not-accessible
	STATUS      current
	DESCRIPTION
	"Table entry for linesharingDevicesTsVisible"
	INDEX { linesharingDevicesTsVisibleLevelName }
	::={linesharingDevicesTsVisibleLevelTable 1}

LinesharingDevicesTsVisibleLevelEntry ::=
	SEQUENCE {
		linesharingDevicesTsVisibleLevelName	DisplayString,
		linesharingDevicesTsVisibleLevelVal	CounterBasedGauge64,
		linesharingDevicesTsVisibleLevelMax	CounterBasedGauge64
	}

linesharingDevicesTsVisibleLevelName OBJECT-TYPE
	SYNTAX      DisplayString
	MAX-ACCESS  not-accessible
	STATUS      current
	DESCRIPTION
	"Table entry display string for linesharingDevicesTsVisible"
	::={linesharingDevicesTsVisibleLevelEntry 1}

linesharingDevicesTsVisibleLevelVal OBJECT-TYPE
	SYNTAX	 CounterBasedGauge64
	MAX-ACCESS  read-only
	STATUS      current
	DESCRIPTION
	"Table entry attribute for linesharingDevicesTsVisible"
	::={linesharingDevicesTsVisibleLevelEntry 2}

linesharingDevicesTsVisibleLevelMax OBJECT-TYPE
	SYNTAX	 CounterBasedGauge64
	MAX-ACCESS  read-only
	STATUS      current
	DESCRIPTION
	"Table entry attribute for linesharingDevicesTsVisible"
	::={linesharingDevicesTsVisibleLevelEntry 4}


linesharingDevicesTsNoSpace	OBJECT IDENTIFIER ::={linesharing 8}

linesharingDevicesTsNoSpaceVal	OBJECT-TYPE
	SYNTAX	 Counter64
	MAX-ACCESS read-only
	STATUS current
	DESCRIPTION "Timestamp Failure - No space in array"

	::={linesharingDevicesTsNoSpace 1}

linesharingDevicesTsNoSpaceMom	OBJECT-TYPE
	SYNTAX	 CounterBasedGauge64
	MAX-ACCESS read-only
	STATUS current
	DESCRIPTION "Timestamp Failure - No space in array"

	::={linesharingDevicesTsNoSpace 2}

linesharingDevicesTsNoSpaceMax	OBJECT-TYPE
	SYNTAX	 CounterBasedGauge64
	MAX-ACCESS read-only
	STATUS current
	DESCRIPTION "Timestamp Failure - No space in array"

	::={linesharingDevicesTsNoSpace 3}

linesharingDevicesTsNoSpaceLevelTable OBJECT-TYPE
	SYNTAX      SEQUENCE OF LinesharingDevicesTsNoSpaceLevelEntry
	MAX-ACCESS  not-accessible
	STATUS      current
	DESCRIPTION
	"Table for linesharingDevicesTsNoSpace"
	::={linesharingDevicesTsNoSpace 4}

linesharingDevicesTsNoSpaceLevelEntry OBJECT-TYPE
	SYNTAX      LinesharingDevicesTsNoSpaceLevelEntry
	MAX-ACCESS  not-accessible
	STATUS      current
	DESCRIPTION
	"Table entry for linesharingDevicesTsNoSpace"
	INDEX { linesharingDevicesTsNoSpaceLevelName }
	::={linesharingDevicesTsNoSpaceLevelTable 1}

LinesharingDevicesTsNoSpaceLevelEntry ::=
	SEQUENCE {
		linesharingDevicesTsNoSpaceLevelName	DisplayString,
		linesharingDevicesTsNoSpaceLevelVal	Counter64,
		linesharingDevicesTsNoSpaceLevelMom	CounterBasedGauge64,
		linesharingDevicesTsNoSpaceLevelMax	CounterBasedGauge64
	}

linesharingDevicesTsNoSpaceLevelName OBJECT-TYPE
	SYNTAX      DisplayString
	MAX-ACCESS  not-accessible
	STATUS      current
	DESCRIPTION
	"Table entry display string for linesharingDevicesTsNoSpace"
	::={linesharingDevicesTsNoSpaceLevelEntry 1}

linesharingDevicesTsNoSpaceLevelVal OBJECT-TYPE
	SYNTAX	 Counter64
	MAX-ACCESS  read-only
	STATUS      current
	DESCRIPTION
	"Table entry attribute for linesharingDevicesTsNoSpace"
	::={linesharingDevicesTsNoSpaceLevelEntry 2}

linesharingDevicesTsNoSpaceLevelMom OBJECT-TYPE
	SYNTAX	 CounterBasedGauge64
	MAX-ACCESS  read-only
	STATUS      current
	DESCRIPTION
	"Table entry attribute for linesharingDevicesTsNoSpace"
	::={linesharingDevicesTsNoSpaceLevelEntry 3}

linesharingDevicesTsNoSpaceLevelMax OBJECT-TYPE
	SYNTAX	 CounterBasedGauge64
	MAX-ACCESS  read-only
	STATUS      current
	DESCRIPTION
	"Table entry attribute for linesharingDevicesTsNoSpace"
	::={linesharingDevicesTsNoSpaceLevelEntry 4}


linesharingDevicesPort	OBJECT IDENTIFIER ::={linesharing 9}

linesharingDevicesPortVal	OBJECT-TYPE
	SYNTAX	 CounterBasedGauge64
	MAX-ACCESS read-only
	STATUS current
	DESCRIPTION "Port Devices"

	::={linesharingDevicesPort 1}

linesharingDevicesPortMax	OBJECT-TYPE
	SYNTAX	 CounterBasedGauge64
	MAX-ACCESS read-only
	STATUS current
	DESCRIPTION "Port Devices"

	::={linesharingDevicesPort 3}

linesharingDevicesPortLevelTable OBJECT-TYPE
	SYNTAX      SEQUENCE OF LinesharingDevicesPortLevelEntry
	MAX-ACCESS  not-accessible
	STATUS      current
	DESCRIPTION
	"Table for linesharingDevicesPort"
	::={linesharingDevicesPort 4}

linesharingDevicesPortLevelEntry OBJECT-TYPE
	SYNTAX      LinesharingDevicesPortLevelEntry
	MAX-ACCESS  not-accessible
	STATUS      current
	DESCRIPTION
	"Table entry for linesharingDevicesPort"
	INDEX { linesharingDevicesPortLevelName }
	::={linesharingDevicesPortLevelTable 1}

LinesharingDevicesPortLevelEntry ::=
	SEQUENCE {
		linesharingDevicesPortLevelName	DisplayString,
		linesharingDevicesPortLevelVal	CounterBasedGauge64,
		linesharingDevicesPortLevelMax	CounterBasedGauge64
	}

linesharingDevicesPortLevelName OBJECT-TYPE
	SYNTAX      DisplayString
	MAX-ACCESS  not-accessible
	STATUS      current
	DESCRIPTION
	"Table entry display string for linesharingDevicesPort"
	::={linesharingDevicesPortLevelEntry 1}

linesharingDevicesPortLevelVal OBJECT-TYPE
	SYNTAX	 CounterBasedGauge64
	MAX-ACCESS  read-only
	STATUS      current
	DESCRIPTION
	"Table entry attribute for linesharingDevicesPort"
	::={linesharingDevicesPortLevelEntry 2}

linesharingDevicesPortLevelMax OBJECT-TYPE
	SYNTAX	 CounterBasedGauge64
	MAX-ACCESS  read-only
	STATUS      current
	DESCRIPTION
	"Table entry attribute for linesharingDevicesPort"
	::={linesharingDevicesPortLevelEntry 4}


linesharingDevicesPortCreated	OBJECT IDENTIFIER ::={linesharing 10}

linesharingDevicesPortCreatedVal	OBJECT-TYPE
	SYNTAX	 Counter64
	MAX-ACCESS read-only
	STATUS current
	DESCRIPTION "Port Devices Created"

	::={linesharingDevicesPortCreated 1}

linesharingDevicesPortCreatedMom	OBJECT-TYPE
	SYNTAX	 CounterBasedGauge64
	MAX-ACCESS read-only
	STATUS current
	DESCRIPTION "Port Devices Created"

	::={linesharingDevicesPortCreated 2}

linesharingDevicesPortCreatedMax	OBJECT-TYPE
	SYNTAX	 CounterBasedGauge64
	MAX-ACCESS read-only
	STATUS current
	DESCRIPTION "Port Devices Created"

	::={linesharingDevicesPortCreated 3}

linesharingDevicesPortCreatedLevelTable OBJECT-TYPE
	SYNTAX      SEQUENCE OF LinesharingDevicesPortCreatedLevelEntry
	MAX-ACCESS  not-accessible
	STATUS      current
	DESCRIPTION
	"Table for linesharingDevicesPortCreated"
	::={linesharingDevicesPortCreated 4}

linesharingDevicesPortCreatedLevelEntry OBJECT-TYPE
	SYNTAX      LinesharingDevicesPortCreatedLevelEntry
	MAX-ACCESS  not-accessible
	STATUS      current
	DESCRIPTION
	"Table entry for linesharingDevicesPortCreated"
	INDEX { linesharingDevicesPortCreatedLevelName }
	::={linesharingDevicesPortCreatedLevelTable 1}

LinesharingDevicesPortCreatedLevelEntry ::=
	SEQUENCE {
		linesharingDevicesPortCreatedLevelName	DisplayString,
		linesharingDevicesPortCreatedLevelVal	Counter64,
		linesharingDevicesPortCreatedLevelMom	CounterBasedGauge64,
		linesharingDevicesPortCreatedLevelMax	CounterBasedGauge64
	}

linesharingDevicesPortCreatedLevelName OBJECT-TYPE
	SYNTAX      DisplayString
	MAX-ACCESS  not-accessible
	STATUS      current
	DESCRIPTION
	"Table entry display string for linesharingDevicesPortCreated"
	::={linesharingDevicesPortCreatedLevelEntry 1}

linesharingDevicesPortCreatedLevelVal OBJECT-TYPE
	SYNTAX	 Counter64
	MAX-ACCESS  read-only
	STATUS      current
	DESCRIPTION
	"Table entry attribute for linesharingDevicesPortCreated"
	::={linesharingDevicesPortCreatedLevelEntry 2}

linesharingDevicesPortCreatedLevelMom OBJECT-TYPE
	SYNTAX	 CounterBasedGauge64
	MAX-ACCESS  read-only
	STATUS      current
	DESCRIPTION
	"Table entry attribute for linesharingDevicesPortCreated"
	::={linesharingDevicesPortCreatedLevelEntry 3}

linesharingDevicesPortCreatedLevelMax OBJECT-TYPE
	SYNTAX	 CounterBasedGauge64
	MAX-ACCESS  read-only
	STATUS      current
	DESCRIPTION
	"Table entry attribute for linesharingDevicesPortCreated"
	::={linesharingDevicesPortCreatedLevelEntry 4}


linesharingDevicesPortDeleted	OBJECT IDENTIFIER ::={linesharing 11}

linesharingDevicesPortDeletedVal	OBJECT-TYPE
	SYNTAX	 Counter64
	MAX-ACCESS read-only
	STATUS current
	DESCRIPTION "Port Devices Deleted"

	::={linesharingDevicesPortDeleted 1}

linesharingDevicesPortDeletedMom	OBJECT-TYPE
	SYNTAX	 CounterBasedGauge64
	MAX-ACCESS read-only
	STATUS current
	DESCRIPTION "Port Devices Deleted"

	::={linesharingDevicesPortDeleted 2}

linesharingDevicesPortDeletedMax	OBJECT-TYPE
	SYNTAX	 CounterBasedGauge64
	MAX-ACCESS read-only
	STATUS current
	DESCRIPTION "Port Devices Deleted"

	::={linesharingDevicesPortDeleted 3}

linesharingDevicesPortDeletedLevelTable OBJECT-TYPE
	SYNTAX      SEQUENCE OF LinesharingDevicesPortDeletedLevelEntry
	MAX-ACCESS  not-accessible
	STATUS      current
	DESCRIPTION
	"Table for linesharingDevicesPortDeleted"
	::={linesharingDevicesPortDeleted 4}

linesharingDevicesPortDeletedLevelEntry OBJECT-TYPE
	SYNTAX      LinesharingDevicesPortDeletedLevelEntry
	MAX-ACCESS  not-accessible
	STATUS      current
	DESCRIPTION
	"Table entry for linesharingDevicesPortDeleted"
	INDEX { linesharingDevicesPortDeletedLevelName }
	::={linesharingDevicesPortDeletedLevelTable 1}

LinesharingDevicesPortDeletedLevelEntry ::=
	SEQUENCE {
		linesharingDevicesPortDeletedLevelName	DisplayString,
		linesharingDevicesPortDeletedLevelVal	Counter64,
		linesharingDevicesPortDeletedLevelMom	CounterBasedGauge64,
		linesharingDevicesPortDeletedLevelMax	CounterBasedGauge64
	}

linesharingDevicesPortDeletedLevelName OBJECT-TYPE
	SYNTAX      DisplayString
	MAX-ACCESS  not-accessible
	STATUS      current
	DESCRIPTION
	"Table entry display string for linesharingDevicesPortDeleted"
	::={linesharingDevicesPortDeletedLevelEntry 1}

linesharingDevicesPortDeletedLevelVal OBJECT-TYPE
	SYNTAX	 Counter64
	MAX-ACCESS  read-only
	STATUS      current
	DESCRIPTION
	"Table entry attribute for linesharingDevicesPortDeleted"
	::={linesharingDevicesPortDeletedLevelEntry 2}

linesharingDevicesPortDeletedLevelMom OBJECT-TYPE
	SYNTAX	 CounterBasedGauge64
	MAX-ACCESS  read-only
	STATUS      current
	DESCRIPTION
	"Table entry attribute for linesharingDevicesPortDeleted"
	::={linesharingDevicesPortDeletedLevelEntry 3}

linesharingDevicesPortDeletedLevelMax OBJECT-TYPE
	SYNTAX	 CounterBasedGauge64
	MAX-ACCESS  read-only
	STATUS      current
	DESCRIPTION
	"Table entry attribute for linesharingDevicesPortDeleted"
	::={linesharingDevicesPortDeletedLevelEntry 4}


linesharingDevicesPortVisible	OBJECT IDENTIFIER ::={linesharing 12}

linesharingDevicesPortVisibleVal	OBJECT-TYPE
	SYNTAX	 CounterBasedGauge64
	MAX-ACCESS read-only
	STATUS current
	DESCRIPTION "Port Visible Devices"

	::={linesharingDevicesPortVisible 1}

linesharingDevicesPortVisibleMax	OBJECT-TYPE
	SYNTAX	 CounterBasedGauge64
	MAX-ACCESS read-only
	STATUS current
	DESCRIPTION "Port Visible Devices"

	::={linesharingDevicesPortVisible 3}

linesharingDevicesPortVisibleLevelTable OBJECT-TYPE
	SYNTAX      SEQUENCE OF LinesharingDevicesPortVisibleLevelEntry
	MAX-ACCESS  not-accessible
	STATUS      current
	DESCRIPTION
	"Table for linesharingDevicesPortVisible"
	::={linesharingDevicesPortVisible 4}

linesharingDevicesPortVisibleLevelEntry OBJECT-TYPE
	SYNTAX      LinesharingDevicesPortVisibleLevelEntry
	MAX-ACCESS  not-accessible
	STATUS      current
	DESCRIPTION
	"Table entry for linesharingDevicesPortVisible"
	INDEX { linesharingDevicesPortVisibleLevelName }
	::={linesharingDevicesPortVisibleLevelTable 1}

LinesharingDevicesPortVisibleLevelEntry ::=
	SEQUENCE {
		linesharingDevicesPortVisibleLevelName	DisplayString,
		linesharingDevicesPortVisibleLevelVal	CounterBasedGauge64,
		linesharingDevicesPortVisibleLevelMax	CounterBasedGauge64
	}

linesharingDevicesPortVisibleLevelName OBJECT-TYPE
	SYNTAX      DisplayString
	MAX-ACCESS  not-accessible
	STATUS      current
	DESCRIPTION
	"Table entry display string for linesharingDevicesPortVisible"
	::={linesharingDevicesPortVisibleLevelEntry 1}

linesharingDevicesPortVisibleLevelVal OBJECT-TYPE
	SYNTAX	 CounterBasedGauge64
	MAX-ACCESS  read-only
	STATUS      current
	DESCRIPTION
	"Table entry attribute for linesharingDevicesPortVisible"
	::={linesharingDevicesPortVisibleLevelEntry 2}

linesharingDevicesPortVisibleLevelMax OBJECT-TYPE
	SYNTAX	 CounterBasedGauge64
	MAX-ACCESS  read-only
	STATUS      current
	DESCRIPTION
	"Table entry attribute for linesharingDevicesPortVisible"
	::={linesharingDevicesPortVisibleLevelEntry 4}


linesharingDevicesPortNoSpace	OBJECT IDENTIFIER ::={linesharing 13}

linesharingDevicesPortNoSpaceVal	OBJECT-TYPE
	SYNTAX	 Counter64
	MAX-ACCESS read-only
	STATUS current
	DESCRIPTION "Port Failure - No space in array"

	::={linesharingDevicesPortNoSpace 1}

linesharingDevicesPortNoSpaceMom	OBJECT-TYPE
	SYNTAX	 CounterBasedGauge64
	MAX-ACCESS read-only
	STATUS current
	DESCRIPTION "Port Failure - No space in array"

	::={linesharingDevicesPortNoSpace 2}

linesharingDevicesPortNoSpaceMax	OBJECT-TYPE
	SYNTAX	 CounterBasedGauge64
	MAX-ACCESS read-only
	STATUS current
	DESCRIPTION "Port Failure - No space in array"

	::={linesharingDevicesPortNoSpace 3}

linesharingDevicesPortNoSpaceLevelTable OBJECT-TYPE
	SYNTAX      SEQUENCE OF LinesharingDevicesPortNoSpaceLevelEntry
	MAX-ACCESS  not-accessible
	STATUS      current
	DESCRIPTION
	"Table for linesharingDevicesPortNoSpace"
	::={linesharingDevicesPortNoSpace 4}

linesharingDevicesPortNoSpaceLevelEntry OBJECT-TYPE
	SYNTAX      LinesharingDevicesPortNoSpaceLevelEntry
	MAX-ACCESS  not-accessible
	STATUS      current
	DESCRIPTION
	"Table entry for linesharingDevicesPortNoSpace"
	INDEX { linesharingDevicesPortNoSpaceLevelName }
	::={linesharingDevicesPortNoSpaceLevelTable 1}

LinesharingDevicesPortNoSpaceLevelEntry ::=
	SEQUENCE {
		linesharingDevicesPortNoSpaceLevelName	DisplayString,
		linesharingDevicesPortNoSpaceLevelVal	Counter64,
		linesharingDevicesPortNoSpaceLevelMom	CounterBasedGauge64,
		linesharingDevicesPortNoSpaceLevelMax	CounterBasedGauge64
	}

linesharingDevicesPortNoSpaceLevelName OBJECT-TYPE
	SYNTAX      DisplayString
	MAX-ACCESS  not-accessible
	STATUS      current
	DESCRIPTION
	"Table entry display string for linesharingDevicesPortNoSpace"
	::={linesharingDevicesPortNoSpaceLevelEntry 1}

linesharingDevicesPortNoSpaceLevelVal OBJECT-TYPE
	SYNTAX	 Counter64
	MAX-ACCESS  read-only
	STATUS      current
	DESCRIPTION
	"Table entry attribute for linesharingDevicesPortNoSpace"
	::={linesharingDevicesPortNoSpaceLevelEntry 2}

linesharingDevicesPortNoSpaceLevelMom OBJECT-TYPE
	SYNTAX	 CounterBasedGauge64
	MAX-ACCESS  read-only
	STATUS      current
	DESCRIPTION
	"Table entry attribute for linesharingDevicesPortNoSpace"
	::={linesharingDevicesPortNoSpaceLevelEntry 3}

linesharingDevicesPortNoSpaceLevelMax OBJECT-TYPE
	SYNTAX	 CounterBasedGauge64
	MAX-ACCESS  read-only
	STATUS      current
	DESCRIPTION
	"Table entry attribute for linesharingDevicesPortNoSpace"
	::={linesharingDevicesPortNoSpaceLevelEntry 4}


linesharingHostsPoolDepleted	OBJECT IDENTIFIER ::={linesharing 14}

linesharingHostsPoolDepletedVal	OBJECT-TYPE
	SYNTAX	 Counter64
	MAX-ACCESS read-only
	STATUS current
	DESCRIPTION "Host pool is depleted"

	::={linesharingHostsPoolDepleted 1}

linesharingHostsPoolDepletedMom	OBJECT-TYPE
	SYNTAX	 CounterBasedGauge64
	MAX-ACCESS read-only
	STATUS current
	DESCRIPTION "Host pool is depleted"

	::={linesharingHostsPoolDepleted 2}

linesharingHostsPoolDepletedMax	OBJECT-TYPE
	SYNTAX	 CounterBasedGauge64
	MAX-ACCESS read-only
	STATUS current
	DESCRIPTION "Host pool is depleted"

	::={linesharingHostsPoolDepleted 3}

linesharingHostsPoolDepletedLevelTable OBJECT-TYPE
	SYNTAX      SEQUENCE OF LinesharingHostsPoolDepletedLevelEntry
	MAX-ACCESS  not-accessible
	STATUS      current
	DESCRIPTION
	"Table for linesharingHostsPoolDepleted"
	::={linesharingHostsPoolDepleted 4}

linesharingHostsPoolDepletedLevelEntry OBJECT-TYPE
	SYNTAX      LinesharingHostsPoolDepletedLevelEntry
	MAX-ACCESS  not-accessible
	STATUS      current
	DESCRIPTION
	"Table entry for linesharingHostsPoolDepleted"
	INDEX { linesharingHostsPoolDepletedLevelName }
	::={linesharingHostsPoolDepletedLevelTable 1}

LinesharingHostsPoolDepletedLevelEntry ::=
	SEQUENCE {
		linesharingHostsPoolDepletedLevelName	DisplayString,
		linesharingHostsPoolDepletedLevelVal	Counter64,
		linesharingHostsPoolDepletedLevelMom	CounterBasedGauge64,
		linesharingHostsPoolDepletedLevelMax	CounterBasedGauge64
	}

linesharingHostsPoolDepletedLevelName OBJECT-TYPE
	SYNTAX      DisplayString
	MAX-ACCESS  not-accessible
	STATUS      current
	DESCRIPTION
	"Table entry display string for linesharingHostsPoolDepleted"
	::={linesharingHostsPoolDepletedLevelEntry 1}

linesharingHostsPoolDepletedLevelVal OBJECT-TYPE
	SYNTAX	 Counter64
	MAX-ACCESS  read-only
	STATUS      current
	DESCRIPTION
	"Table entry attribute for linesharingHostsPoolDepleted"
	::={linesharingHostsPoolDepletedLevelEntry 2}

linesharingHostsPoolDepletedLevelMom OBJECT-TYPE
	SYNTAX	 CounterBasedGauge64
	MAX-ACCESS  read-only
	STATUS      current
	DESCRIPTION
	"Table entry attribute for linesharingHostsPoolDepleted"
	::={linesharingHostsPoolDepletedLevelEntry 3}

linesharingHostsPoolDepletedLevelMax OBJECT-TYPE
	SYNTAX	 CounterBasedGauge64
	MAX-ACCESS  read-only
	STATUS      current
	DESCRIPTION
	"Table entry attribute for linesharingHostsPoolDepleted"
	::={linesharingHostsPoolDepletedLevelEntry 4}





END
