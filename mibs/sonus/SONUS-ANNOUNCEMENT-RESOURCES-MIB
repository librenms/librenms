--
-- This SMIv2 module has been generated by smidump 0.2-cvs. Do not edit.
--

SONUS-ANNOUNCEMENT-RESOURCES-MIB DEFINITIONS ::= BEGIN

IMPORTS
    Counter64, Integer32, MODULE-IDENTITY, NOTIFICATION-TYPE, 
    OBJECT-TYPE
        FROM SNMPv2-SMI
    DisplayString
        FROM SNMPv2-TC
    sonusEventClass, sonusEventDescription, sonusEventLevel, 
    sonusEventTime, sonusSequenceId, sonusShelfIndex, sonusSlotIndex
        FROM SONUS-COMMON-MIB
    sonusResourcesMIBs
        FROM SONUS-SMI
    SonusBoolean, SonusShelfIndex, SonusSlotIndex
        FROM SONUS-TC;

sonusAnnouncementResourcesMIB MODULE-IDENTITY
    LAST-UPDATED    "200703280000Z"
    ORGANIZATION    
            "Sonus Networks, Inc."
    CONTACT-INFO    
            "   Customer Support    
             Sonus Networks, Inc.
             7 Technology Park Drive
             Westford, MA 01886
             USA
             
             Tel: 978-614-8100
             Fax: 978-614-8609"
    DESCRIPTION     
            "The MIB Module for Announcements."
    ::= { sonusResourcesMIBs 5 }


sonusAnnouncementResourcesMIBObjects OBJECT IDENTIFIER
    ::= { sonusAnnouncementResourcesMIB 1 }

sonusAnnSegStatTable OBJECT-TYPE
    SYNTAX          SEQUENCE OF SonusAnnSegStatEntry
    MAX-ACCESS      not-accessible
    STATUS          current
    DESCRIPTION     
            "This table contains Announcement Segment File statistics"
    ::= { sonusAnnouncementResourcesMIBObjects 1 }

sonusAnnSegStatEntry OBJECT-TYPE
    SYNTAX          SonusAnnSegStatEntry
    MAX-ACCESS      not-accessible
    STATUS          current
    DESCRIPTION     
            ""
    INDEX           { sonusAnnSegStatSegId }
    ::= { sonusAnnSegStatTable 1 }

SonusAnnSegStatEntry ::=
    SEQUENCE {
        sonusAnnSegStatSegId            Integer32,
        sonusAnnSegStatLength           Integer32,
        sonusAnnSegStatVersion          Integer32,
        sonusAnnSegStatPreload          SonusBoolean,
        sonusAnnSegStatNfsPath          DisplayString
    }

sonusAnnSegStatSegId OBJECT-TYPE
    SYNTAX          Integer32
    MAX-ACCESS      read-only
    STATUS          current
    DESCRIPTION     
            "Represents the segment identity"
    ::= { sonusAnnSegStatEntry 1 }

sonusAnnSegStatLength OBJECT-TYPE
    SYNTAX          Integer32
    MAX-ACCESS      read-only
    STATUS          current
    DESCRIPTION     
            "Represents segment length in bytes"
    ::= { sonusAnnSegStatEntry 2 }

sonusAnnSegStatVersion OBJECT-TYPE
    SYNTAX          Integer32
    MAX-ACCESS      read-only
    STATUS          current
    DESCRIPTION     
            "Represents number of segment file modifications detected"
    ::= { sonusAnnSegStatEntry 3 }

sonusAnnSegStatPreload OBJECT-TYPE
    SYNTAX          SonusBoolean
    MAX-ACCESS      read-only
    STATUS          current
    DESCRIPTION     
            "If TRUE, servers load segment during initialization rather
             than at first playback"
    ::= { sonusAnnSegStatEntry 4 }

sonusAnnSegStatNfsPath OBJECT-TYPE
    SYNTAX          DisplayString (SIZE(0..63))
    MAX-ACCESS      read-only
    STATUS          current
    DESCRIPTION     
            "Represents the NFS pathname of the segment file"
    ::= { sonusAnnSegStatEntry 5 }

sonusAnnSegMemStatTable OBJECT-TYPE
    SYNTAX          SEQUENCE OF SonusAnnSegMemStatEntry
    MAX-ACCESS      not-accessible
    STATUS          current
    DESCRIPTION     
            "This table contains Announcement Segment Memory statistics"
    ::= { sonusAnnouncementResourcesMIBObjects 2 }

sonusAnnSegMemStatEntry OBJECT-TYPE
    SYNTAX          SonusAnnSegMemStatEntry
    MAX-ACCESS      not-accessible
    STATUS          current
    DESCRIPTION     
            ""
    INDEX           { sonusAnnSegMemStatShelfIndex, 
                      sonusAnnSegMemStatSlotIndex }
    ::= { sonusAnnSegMemStatTable 1 }

SonusAnnSegMemStatEntry ::=
    SEQUENCE {
        sonusAnnSegMemStatShelfIndex    SonusShelfIndex,
        sonusAnnSegMemStatSlotIndex     SonusSlotIndex,
        sonusAnnSegMemStatNumSegs       Integer32,
        sonusAnnSegMemStatTotalBytes    Integer32,
        sonusAnnSegMemStatUsedBytes     Integer32
    }

sonusAnnSegMemStatShelfIndex OBJECT-TYPE
    SYNTAX          SonusShelfIndex
    MAX-ACCESS      read-only
    STATUS          current
    DESCRIPTION     
            "Shelf index for this table"
    ::= { sonusAnnSegMemStatEntry 1 }

sonusAnnSegMemStatSlotIndex OBJECT-TYPE
    SYNTAX          SonusSlotIndex
    MAX-ACCESS      read-only
    STATUS          current
    DESCRIPTION     
            "Slot index for this table"
    ::= { sonusAnnSegMemStatEntry 2 }

sonusAnnSegMemStatNumSegs OBJECT-TYPE
    SYNTAX          Integer32
    MAX-ACCESS      read-only
    STATUS          current
    DESCRIPTION     
            "Represents the number of segments server has loaded"
    ::= { sonusAnnSegMemStatEntry 3 }

sonusAnnSegMemStatTotalBytes OBJECT-TYPE
    SYNTAX          Integer32
    MAX-ACCESS      read-only
    STATUS          current
    DESCRIPTION     
            "Represents the server's segment memory size in bytes"
    ::= { sonusAnnSegMemStatEntry 4 }

sonusAnnSegMemStatUsedBytes OBJECT-TYPE
    SYNTAX          Integer32
    MAX-ACCESS      read-only
    STATUS          current
    DESCRIPTION     
            "Represents the number of segment memory bytes used by
             all loaded segments.  Segment memory is composed of 2K
             byte blocks.  Therefore the actual number of bytes used by
             each segment is equal to the segment length rounded up to
             the next 2K byte boundary."
    ::= { sonusAnnSegMemStatEntry 5 }

sonusAnnSegPlayStatTable OBJECT-TYPE
    SYNTAX          SEQUENCE OF SonusAnnSegPlayStatEntry
    MAX-ACCESS      not-accessible
    STATUS          current
    DESCRIPTION     
            "This table contains Announcement Segment Playback statistics"
    ::= { sonusAnnouncementResourcesMIBObjects 3 }

sonusAnnSegPlayStatEntry OBJECT-TYPE
    SYNTAX          SonusAnnSegPlayStatEntry
    MAX-ACCESS      not-accessible
    STATUS          current
    DESCRIPTION     
            ""
    INDEX           { sonusAnnSegPlayStatShelfIndex, 
                      sonusAnnSegPlayStatSlotIndex, 
                      sonusAnnSegPlayStatSegId }
    ::= { sonusAnnSegPlayStatTable 1 }

SonusAnnSegPlayStatEntry ::=
    SEQUENCE {
        sonusAnnSegPlayStatShelfIndex   SonusShelfIndex,
        sonusAnnSegPlayStatSlotIndex    SonusSlotIndex,
        sonusAnnSegPlayStatSegId        Integer32,
        sonusAnnSegPlayStatVersion      Integer32,
        sonusAnnSegPlayStatState        INTEGER,
        sonusAnnSegPlayStatDelOnceFree  SonusBoolean,
        sonusAnnSegPlayStatUseCount     Integer32,
        sonusAnnSegPlayStatTotalPlays   Counter64
    }

sonusAnnSegPlayStatShelfIndex OBJECT-TYPE
    SYNTAX          SonusShelfIndex
    MAX-ACCESS      read-only
    STATUS          current
    DESCRIPTION     
            "Shelf index for this table"
    ::= { sonusAnnSegPlayStatEntry 1 }

sonusAnnSegPlayStatSlotIndex OBJECT-TYPE
    SYNTAX          SonusSlotIndex
    MAX-ACCESS      read-only
    STATUS          current
    DESCRIPTION     
            "Slot index for this table"
    ::= { sonusAnnSegPlayStatEntry 2 }

sonusAnnSegPlayStatSegId OBJECT-TYPE
    SYNTAX          Integer32
    MAX-ACCESS      read-only
    STATUS          current
    DESCRIPTION     
            "SegId index for this table"
    ::= { sonusAnnSegPlayStatEntry 3 }

sonusAnnSegPlayStatVersion OBJECT-TYPE
    SYNTAX          Integer32
    MAX-ACCESS      read-only
    STATUS          current
    DESCRIPTION     
            "Represents version of segment currently loaded"
    ::= { sonusAnnSegPlayStatEntry 4 }

sonusAnnSegPlayStatState OBJECT-TYPE
    SYNTAX          INTEGER { notPresent(0), loading(1), loaded(2), 
                        updatePending(3) }
    MAX-ACCESS      read-only
    STATUS          current
    DESCRIPTION     
            "Represents current state of the segment"
    ::= { sonusAnnSegPlayStatEntry 5 }

sonusAnnSegPlayStatDelOnceFree OBJECT-TYPE
    SYNTAX          SonusBoolean
    MAX-ACCESS      read-only
    STATUS          current
    DESCRIPTION     
            "If TRUE, the current version of segment data will be
             deleted from memory once sonusAnnSegPlayStatUseCount
             drops to zero.  If a new version of the segment exists,
             then the new segment data will be automatically loaded."
    ::= { sonusAnnSegPlayStatEntry 6 }

sonusAnnSegPlayStatUseCount OBJECT-TYPE
    SYNTAX          Integer32
    MAX-ACCESS      read-only
    STATUS          current
    DESCRIPTION     
            "Represents the number of calls currently playing this
             segment"
    ::= { sonusAnnSegPlayStatEntry 7 }

sonusAnnSegPlayStatTotalPlays OBJECT-TYPE
    SYNTAX          Counter64
    MAX-ACCESS      read-only
    STATUS          current
    DESCRIPTION     
            "Represents the cumulative number of times this version of
             the segment has been played since it was loaded"
    ::= { sonusAnnSegPlayStatEntry 8 }

sonusAnnouncementAdmnObjects OBJECT IDENTIFIER
    ::= { sonusAnnouncementResourcesMIBObjects 4 }

sonusAnnouncementDisk OBJECT-TYPE
    SYNTAX          INTEGER { nfsServer(1), localDisk(2) }
    MAX-ACCESS      read-write
    STATUS          current
    DESCRIPTION     
            "Selects the disk location where announcement files are obtained from.
             The local disk option is available for MNS modules with a local
             disk physically present."
    ::= { sonusAnnouncementAdmnObjects 1 }

sonusAnnouncementDirectory OBJECT-TYPE
    SYNTAX          DisplayString (SIZE(1..63))
    MAX-ACCESS      read-write
    STATUS          current
    DESCRIPTION     
            "Controls the directory under the disk mount point where announcement
             files are obtained from."
    ::= { sonusAnnouncementAdmnObjects 2 }

sonusAnnouncementResourcesMIBNotifications OBJECT IDENTIFIER
    ::= { sonusAnnouncementResourcesMIB 2 }

sonusAnnouncementResourcesMIBNotificationsPrefix OBJECT IDENTIFIER
    ::= { sonusAnnouncementResourcesMIBNotifications 0 }

sonusAnnouncementResourcesMIBNotificationsObjects OBJECT IDENTIFIER
    ::= { sonusAnnouncementResourcesMIBNotifications 1 }

sonusAresUnavailCount OBJECT-TYPE
    SYNTAX          Integer32
    MAX-ACCESS      read-only
    STATUS          current
    DESCRIPTION     
            "Represents number of announcement resource allocate failures
             since the rising threshold was met."
    ::= { sonusAnnouncementResourcesMIBNotificationsObjects 1 }

sonusAnnSegMemFullCount OBJECT-TYPE
    SYNTAX          Integer32
    MAX-ACCESS      read-only
    STATUS          current
    DESCRIPTION     
            "Represents number of times an announcement cound not be
             loaded because segment memory was full for a given slot."
    ::= { sonusAnnouncementResourcesMIBNotificationsObjects 2 }

sonusAnnouncementFileNotFoundNotification NOTIFICATION-TYPE
    OBJECTS         { sonusAnnSegStatSegId, sonusShelfIndex, 
                      sonusSlotIndex, sonusEventDescription, 
                      sonusEventClass, sonusEventLevel, sonusSequenceId, 
                      sonusEventTime }
    STATUS          current
    DESCRIPTION     
            "This trap indicates that the requested segment file
             could not be found.  The segment file must be copied
             into either the <node>/announcement/preload or
             or <node>/announcement/ondemand directory."
    ::= { sonusAnnouncementResourcesMIBNotificationsPrefix 1 }

sonusAnnouncementFileFoundNotification NOTIFICATION-TYPE
    OBJECTS         { sonusAnnSegStatSegId, sonusAnnSegStatNfsPath, 
                      sonusShelfIndex, sonusSlotIndex, 
                      sonusEventDescription, sonusEventClass, 
                      sonusEventLevel }
    STATUS          deprecated
    DESCRIPTION     
            "This trap had been replaced by sonusAnnounceFileFoundNotification
             in V04.01.03R000 & beyond."
    ::= { sonusAnnouncementResourcesMIBNotificationsPrefix 2 }

sonusAnnouncementFileInvalidNotification NOTIFICATION-TYPE
    OBJECTS         { sonusAnnSegStatSegId, sonusAnnSegStatNfsPath, 
                      sonusEventDescription, sonusEventClass, 
                      sonusEventLevel, sonusSequenceId, sonusEventTime }
    STATUS          current
    DESCRIPTION     
            "This trap indicates that the specified segment file contains
             one or more format errors.  Check SYS log for more detail."
    ::= { sonusAnnouncementResourcesMIBNotificationsPrefix 3 }

sonusAnnouncementFileValidNotification NOTIFICATION-TYPE
    OBJECTS         { sonusAnnSegStatNfsPath, sonusEventDescription, 
                      sonusEventClass, sonusEventLevel, 
                      sonusAnnSegStatSegId, sonusSequenceId, 
                      sonusEventTime }
    STATUS          current
    DESCRIPTION     
            "This trap indicates that previously invalid segment file
             has been replaced by a valid segment file."
    ::= { sonusAnnouncementResourcesMIBNotificationsPrefix 4 }

sonusAnnouncementSegmentLoadFailureNotification NOTIFICATION-TYPE
    OBJECTS         { sonusShelfIndex, sonusSlotIndex, 
                      sonusAnnSegStatSegId, sonusAnnSegStatVersion, 
                      sonusAnnSegStatLength, sonusAnnSegMemFullCount, 
                      sonusEventDescription, sonusEventClass, 
                      sonusEventLevel, sonusSequenceId, sonusEventTime }
    STATUS          current
    DESCRIPTION     
            "This trap indicates that announcement segment could not
             be loaded because segment memory on the specified card is
             full.  Segment ID, Version and Length pertain to the most
             		 recent segment load failure.  Verify the length of this
             		 segment is within reason."
    ::= { sonusAnnouncementResourcesMIBNotificationsPrefix 5 }

sonusAnnouncementResUnavailRisingThresholdNotification NOTIFICATION-TYPE
    OBJECTS         { sonusShelfIndex, sonusSlotIndex, 
                      sonusEventDescription, sonusEventClass, 
                      sonusEventLevel, sonusSequenceId, sonusEventTime }
    STATUS          current
    DESCRIPTION     
            "This trap indicates that all announcement resources on
             the specified card are in use."
    ::= { sonusAnnouncementResourcesMIBNotificationsPrefix 6 }

sonusAnnouncementResUnavailFallingThresholdNotification NOTIFICATION-TYPE
    OBJECTS         { sonusShelfIndex, sonusSlotIndex, 
                      sonusAresUnavailCount, sonusEventDescription, 
                      sonusEventClass, sonusEventLevel, sonusSequenceId, 
                      sonusEventTime }
    STATUS          current
    DESCRIPTION     
            "This trap indicates that announcement resource usage on
             the specified card has dropped below a threshold."
    ::= { sonusAnnouncementResourcesMIBNotificationsPrefix 7 }

sonusAnnounceFileFoundNotification NOTIFICATION-TYPE
    OBJECTS         { sonusAnnSegStatSegId, sonusAnnSegStatNfsPath, 
                      sonusEventDescription, sonusEventClass, 
                      sonusEventLevel, sonusSequenceId, sonusEventTime }
    STATUS          current
    DESCRIPTION     
            "This trap indicates that a segment file, which
             previously cound not be found, was found."
    ::= { sonusAnnouncementResourcesMIBNotificationsPrefix 8 }

END -- end of module SONUS-ANNOUNCEMENT-RESOURCES-MIB.
