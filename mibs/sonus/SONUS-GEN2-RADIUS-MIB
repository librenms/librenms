--
-- This SMIv2 module has been generated by smidump 0.2-cvs. Do not edit.
--

SONUS-GEN2-RADIUS-MIB DEFINITIONS ::= BEGIN

IMPORTS
    Counter32, Counter64, Gauge32, Integer32, IpAddress, MODULE-IDENTITY, 
    OBJECT-TYPE, Unsigned32
        FROM SNMPv2-SMI
    DateAndTime, RowStatus, TEXTUAL-CONVENTION, TruthValue
        FROM SNMPv2-TC
    sonusCommonSoftwarePlatformServicesMIBs
        FROM SONUS-SMI;

sonusGen2RadiusMIB MODULE-IDENTITY
    LAST-UPDATED    "201212310000Z"
    ORGANIZATION    
            "Sonus Networks, Inc."
    CONTACT-INFO    
            "Customer Support        
             Sonus Networks, Inc.    
             4 Technology Park Drive 
             Westford, MA 01886      
             USA                     
                                     
             Tel: 978-614-8100       
             Fax: 978-614-8609"
    DESCRIPTION     
            "The MIB Module for RADIUS Server Management."
    REVISION        "201212310000Z"
    DESCRIPTION     
            "Auto generated MIB."
    ::= { sonusCommonSoftwarePlatformServicesMIBs 14 }


UnsignedShort ::= TEXTUAL-CONVENTION
    DISPLAY-HINT    "d"
    STATUS          current
    DESCRIPTION     
            "xs:unsignedShort"
    SYNTAX          Unsigned32 (0..65535)

ConfdString ::= TEXTUAL-CONVENTION
    DISPLAY-HINT    "1t"
    STATUS          current
    DESCRIPTION     
            "xs: and confd: types mapped to strings"
    SYNTAX          OCTET STRING

InetAddressIP ::= TEXTUAL-CONVENTION
    STATUS          current
    DESCRIPTION     
            "confd:inetAddressIP"
    SYNTAX          OCTET STRING (SIZE(4 | 16))

String ::= TEXTUAL-CONVENTION
    DISPLAY-HINT    "1t"
    STATUS          current
    DESCRIPTION     
            "xs:string"
    SYNTAX          OCTET STRING

SonusRadiusFailoverPolicyType ::= TEXTUAL-CONVENTION
    STATUS          current
    DESCRIPTION     
            ""
    SYNTAX          INTEGER { roundRobin(1), prioritizedSelection(2) }

SonusRadiusServerPriorityType ::= TEXTUAL-CONVENTION
    STATUS          current
    DESCRIPTION     
            ""
    SYNTAX          Integer32 (1..8)

SonusRadiusAdminStateType ::= TEXTUAL-CONVENTION
    STATUS          current
    DESCRIPTION     
            ""
    SYNTAX          INTEGER { disabled(1), enabled(2) }

SonusMaxNoResponseTimeType ::= TEXTUAL-CONVENTION
    STATUS          current
    DESCRIPTION     
            ""
    SYNTAX          Integer32 (1000..10000)

SonusRadiusMaxQueuedPacketsInMemoryType ::= TEXTUAL-CONVENTION
    STATUS          current
    DESCRIPTION     
            ""
    SYNTAX          Unsigned32 (10000..4294967295)

SonusRadiusProtocolValueString ::= TEXTUAL-CONVENTION
    DISPLAY-HINT    "1t"
    STATUS          current
    DESCRIPTION     
            "
             Used to store a value that will be passed via a Radius protocol string value.
             The value must be between 1 and 253 characters inclusive
             "
    SYNTAX          OCTET STRING (SIZE(0..253))

SonusRadiusServerPortType ::= TEXTUAL-CONVENTION
    DISPLAY-HINT    "1t"
    STATUS          current
    DESCRIPTION     
            "
             Used to store the Radius network service name
             "
    SYNTAX          OCTET STRING (SIZE(0..32))

SonusRadiusRetryCountType ::= TEXTUAL-CONVENTION
    STATUS          current
    DESCRIPTION     
            ""
    SYNTAX          Integer32 (5..25)

SonusRadiusCleanupDelayType ::= TEXTUAL-CONVENTION
    STATUS          current
    DESCRIPTION     
            ""
    SYNTAX          Integer32 (1..30)

SonusRadiusSharedSecretType ::= TEXTUAL-CONVENTION
    DISPLAY-HINT    "1t"
    STATUS          current
    DESCRIPTION     
            "
             Used to store the Radius shared secret.
             "
    SYNTAX          OCTET STRING

SonusRadiusServerStatusType ::= TEXTUAL-CONVENTION
    STATUS          current
    DESCRIPTION     
            ""
    SYNTAX          INTEGER { active(1), enabled(2), disabled(3), 
                        failed(4) }

SonusRadiusMaxErrorRateType ::= TEXTUAL-CONVENTION
    STATUS          current
    DESCRIPTION     
            ""
    SYNTAX          Integer32 (0..100)

RadiusSharedSecretType ::= TEXTUAL-CONVENTION
    DISPLAY-HINT    "1t"
    STATUS          current
    DESCRIPTION     
            "                                                                
             Used to store the Radius Shared Secret.Value must be in range [8-128]    
             "
    SYNTAX          OCTET STRING

sonusRadius OBJECT IDENTIFIER
    ::= { sonusGen2RadiusMIB 1 }

sonusRadiusAccountingAdmin OBJECT IDENTIFIER
    ::= { sonusRadius 1 }

sonusRadiusAccountingAdminState OBJECT-TYPE
    SYNTAX          SonusRadiusAdminStateType
    MAX-ACCESS      read-write
    STATUS          current
    DESCRIPTION     
            "
             The administrative state of the Radius subsystem.
             "
    ::= { sonusRadiusAccountingAdmin 1 }

sonusRadiusAccountingAdminFailoverPolicy OBJECT-TYPE
    SYNTAX          SonusRadiusFailoverPolicyType
    MAX-ACCESS      read-write
    STATUS          current
    DESCRIPTION     
            "
             The failover policy for the radius servers upon error detection.
             roundRobin           - select the server with the next lower priority.
             prioritizedSelection - select the server with the highest priority that
             is not marked as failed.
             "
    ::= { sonusRadiusAccountingAdmin 2 }

sonusRadiusAccountingAdminNasIpAddress OBJECT-TYPE
    SYNTAX          InetAddressIP
    MAX-ACCESS      read-write
    STATUS          current
    DESCRIPTION     
            "
             The  NAS-IP-Address that will be sent to the Radius Server.   If an IPV6 address is sent, then 
             then the NAS-IPv6-Address attribute will be sent
             "
    ::= { sonusRadiusAccountingAdmin 3 }

sonusRadiusAccountingAdminNasIdentifier OBJECT-TYPE
    SYNTAX          SonusRadiusProtocolValueString
    MAX-ACCESS      read-write
    STATUS          current
    DESCRIPTION     
            "
             NAS-Identifier to be sent to the Radius server.
             "
    ::= { sonusRadiusAccountingAdmin 4 }

sonusRadiusAccountingAdminMaxPacketRetryCount OBJECT-TYPE
    SYNTAX          SonusRadiusRetryCountType
    MAX-ACCESS      read-write
    STATUS          current
    DESCRIPTION     
            "
             The maximum number of times a packet will be retransmitted before the packet is dropped.
             "
    ::= { sonusRadiusAccountingAdmin 5 }

sonusRadiusAccountingAdminMaxErrorRate OBJECT-TYPE
    SYNTAX          SonusRadiusMaxErrorRateType
    MAX-ACCESS      read-write
    STATUS          current
    DESCRIPTION     
            "
             The maximum percentage of timed out transactions allowed. If this percentage is exceeded, the
             Radius server is considered failed.
             "
    ::= { sonusRadiusAccountingAdmin 6 }

sonusRadiusAccountingAdminMaxNoResponseTime OBJECT-TYPE
    SYNTAX          SonusMaxNoResponseTimeType
    MAX-ACCESS      read-write
    STATUS          current
    DESCRIPTION     
            "
             The maximum time allowed to wait (in milliseconds) for any response from the server.   If no responses are received from a 
             Radius server within this time, the server is considered failed.
             "
    ::= { sonusRadiusAccountingAdmin 7 }

sonusRadiusAccountingAdminSendNasIdentifier OBJECT-TYPE
    SYNTAX          TruthValue
    MAX-ACCESS      read-write
    STATUS          current
    DESCRIPTION     
            "
             If true, send NAS-Identifier to the Radius server.
             "
    ::= { sonusRadiusAccountingAdmin 8 }

sonusRadiusAccountingAdminSendNasIpAddress OBJECT-TYPE
    SYNTAX          TruthValue
    MAX-ACCESS      read-write
    STATUS          current
    DESCRIPTION     
            "
             If true, send NAS-IP-Address to the Radius server.
             "
    ::= { sonusRadiusAccountingAdmin 9 }

sonusRadiusAccountingAdminMaxQueuedPacketsInMemory OBJECT-TYPE
    SYNTAX          SonusRadiusMaxQueuedPacketsInMemoryType
    MAX-ACCESS      read-write
    STATUS          current
    DESCRIPTION     
            "
             The maximum number of radius packets queued up in memory allowed before they are flushed to disk.  Packets are queued up
             in memory if no radius servers are available.
             "
    ::= { sonusRadiusAccountingAdmin 10 }

sonusRadiusRadiusServerStatusTable OBJECT-TYPE
    SYNTAX          SEQUENCE OF SonusRadiusRadiusServerStatusEntry
    MAX-ACCESS      not-accessible
    STATUS          current
    DESCRIPTION     
            ""
    ::= { sonusRadius 3 }

sonusRadiusRadiusServerStatusEntry OBJECT-TYPE
    SYNTAX          SonusRadiusRadiusServerStatusEntry
    MAX-ACCESS      not-accessible
    STATUS          current
    DESCRIPTION     
            ""
    INDEX           { sonusRadiusRadiusServerStatusServerName }
    ::= { sonusRadiusRadiusServerStatusTable 1 }

SonusRadiusRadiusServerStatusEntry ::=
    SEQUENCE {
        sonusRadiusRadiusServerStatusServerName       String,
        sonusRadiusRadiusServerStatusServerStatus         SonusRadiusServerStatusType,
        sonusRadiusRadiusServerStatusTotalRequests          Integer32,
        sonusRadiusRadiusServerStatusRequestRate        Integer32,
        sonusRadiusRadiusServerStatusErrorRate      Integer32,
        sonusRadiusRadiusServerStatusTimedOutRequests             Integer32,
        sonusRadiusRadiusServerStatusRejectedRequests             Integer32,
        sonusRadiusRadiusServerStatusSpuriousResponses              Integer32,
        sonusRadiusRadiusServerStatusResponsesWithAttributes                    Integer32
    }

sonusRadiusRadiusServerStatusServerName OBJECT-TYPE
    SYNTAX          String (SIZE(0..255))
    MAX-ACCESS      not-accessible
    STATUS          current
    DESCRIPTION     
            "
             The current status of a specific Radius server.
             "
    ::= { sonusRadiusRadiusServerStatusEntry 1 }

sonusRadiusRadiusServerStatusServerStatus OBJECT-TYPE
    SYNTAX          SonusRadiusServerStatusType
    MAX-ACCESS      read-only
    STATUS          current
    DESCRIPTION     
            "
             The operational state of the server.
             "
    ::= { sonusRadiusRadiusServerStatusEntry 2 }

sonusRadiusRadiusServerStatusTotalRequests OBJECT-TYPE
    SYNTAX          Integer32
    MAX-ACCESS      read-only
    STATUS          current
    DESCRIPTION     
            "
             The number of requests that have been made to the server.
             "
    ::= { sonusRadiusRadiusServerStatusEntry 3 }

sonusRadiusRadiusServerStatusRequestRate OBJECT-TYPE
    SYNTAX          Integer32
    MAX-ACCESS      read-only
    STATUS          current
    DESCRIPTION     
            "
             The average number of requests per second to the server. 
             "
    ::= { sonusRadiusRadiusServerStatusEntry 4 }

sonusRadiusRadiusServerStatusErrorRate OBJECT-TYPE
    SYNTAX          Integer32
    MAX-ACCESS      read-only
    STATUS          current
    DESCRIPTION     
            "
             The percentage of requests that were retried at least once due to a timeout.
             "
    ::= { sonusRadiusRadiusServerStatusEntry 5 }

sonusRadiusRadiusServerStatusTimedOutRequests OBJECT-TYPE
    SYNTAX          Integer32
    MAX-ACCESS      read-only
    STATUS          current
    DESCRIPTION     
            "
             The number of requests that resulted in a timeout.
             "
    ::= { sonusRadiusRadiusServerStatusEntry 6 }

sonusRadiusRadiusServerStatusRejectedRequests OBJECT-TYPE
    SYNTAX          Integer32
    MAX-ACCESS      read-only
    STATUS          current
    DESCRIPTION     
            "
             The number of requests that were not responded to by the server and presumed to have been rejected.
             "
    ::= { sonusRadiusRadiusServerStatusEntry 7 }

sonusRadiusRadiusServerStatusSpuriousResponses OBJECT-TYPE
    SYNTAX          Integer32
    MAX-ACCESS      read-only
    STATUS          current
    DESCRIPTION     
            "
             The number of responses without a corresponding request.
             "
    ::= { sonusRadiusRadiusServerStatusEntry 8 }

sonusRadiusRadiusServerStatusResponsesWithAttributes OBJECT-TYPE
    SYNTAX          Integer32
    MAX-ACCESS      read-only
    STATUS          current
    DESCRIPTION     
            "
             The number of responses containing attributes.
             "
    ::= { sonusRadiusRadiusServerStatusEntry 9 }

sonusRadiusRadiusAuthentication OBJECT IDENTIFIER
    ::= { sonusRadius 4 }

sonusRadiusRadiusAuthenticationRadiusServerIp OBJECT-TYPE
    SYNTAX          InetAddressIP
    MAX-ACCESS      read-write
    STATUS          current
    DESCRIPTION     
            "
             The radius server IP used for authentication.
             "
    ::= { sonusRadiusRadiusAuthentication 1 }

sonusRadiusRadiusAuthenticationRadiusServerPort OBJECT-TYPE
    SYNTAX          UnsignedShort (1..65535)
    MAX-ACCESS      read-write
    STATUS          current
    DESCRIPTION     
            "
             The radius server IP port used for authentication.
             "
    ::= { sonusRadiusRadiusAuthentication 2 }

sonusRadiusRadiusAuthenticationRadiusNasIp OBJECT-TYPE
    SYNTAX          InetAddressIP
    MAX-ACCESS      read-write
    STATUS          current
    DESCRIPTION     
            "
             The NAS IP which uses authentication authentication.
             "
    ::= { sonusRadiusRadiusAuthentication 3 }

sonusRadiusRadiusAuthenticationRadiusSharedSecret OBJECT-TYPE
    SYNTAX          RadiusSharedSecretType
    MAX-ACCESS      read-write
    STATUS          current
    DESCRIPTION     
            "
             The radius server shared key,The length of the shared secret should be in range 8-128 characters. 
             "
    ::= { sonusRadiusRadiusAuthentication 4 }

sonusRadiusRadiusServerTable OBJECT-TYPE
    SYNTAX          SEQUENCE OF SonusRadiusRadiusServerEntry
    MAX-ACCESS      not-accessible
    STATUS          current
    DESCRIPTION     
            "
             Per-server configuration.
             "
    ::= { sonusRadius 5 }

sonusRadiusRadiusServerEntry OBJECT-TYPE
    SYNTAX          SonusRadiusRadiusServerEntry
    MAX-ACCESS      not-accessible
    STATUS          current
    DESCRIPTION     
            ""
    INDEX           { sonusRadiusRadiusServerServerName }
    ::= { sonusRadiusRadiusServerTable 1 }

SonusRadiusRadiusServerEntry ::=
    SEQUENCE {
        sonusRadiusRadiusServerServerName String,
        sonusRadiusRadiusServerPriority SonusRadiusServerPriorityType,
        sonusRadiusRadiusServerState    SonusRadiusAdminStateType,
        sonusRadiusRadiusServerServerAddress    String,
        sonusRadiusRadiusServerServerPort SonusRadiusServerPortType,
        sonusRadiusRadiusServerSharedSecret   SonusRadiusSharedSecretType,
        sonusRadiusRadiusServerCleanupDelay   SonusRadiusCleanupDelayType,
        sonusRadiusRadiusServerRowstatus RowStatus
    }

sonusRadiusRadiusServerServerName OBJECT-TYPE
    SYNTAX          String (SIZE(0..255))
    MAX-ACCESS      not-accessible
    STATUS          current
    DESCRIPTION     
            "
             The name used to reference this server
             "
    ::= { sonusRadiusRadiusServerEntry 1 }

sonusRadiusRadiusServerPriority OBJECT-TYPE
    SYNTAX          SonusRadiusServerPriorityType
    MAX-ACCESS      read-create
    STATUS          current
    DESCRIPTION     
            "
             The server selection priority for this server. The lower the numerical
             value, the higher the priority for the server.
             "
    ::= { sonusRadiusRadiusServerEntry 2 }

sonusRadiusRadiusServerState OBJECT-TYPE
    SYNTAX          SonusRadiusAdminStateType
    MAX-ACCESS      read-create
    STATUS          current
    DESCRIPTION     
            "
             The administrative state of the Radius server.
             "
    DEFVAL          { disabled }
    ::= { sonusRadiusRadiusServerEntry 3 }

sonusRadiusRadiusServerServerAddress OBJECT-TYPE
    SYNTAX          String (SIZE(0..255))
    MAX-ACCESS      read-create
    STATUS          current
    DESCRIPTION     
            "
             The IPv4 or IPv6 ipaddress of the server as either a hostname, an IPv4 address in dot notation, or an IPv6 address in hex-colon notation.
             "
    ::= { sonusRadiusRadiusServerEntry 4 }

sonusRadiusRadiusServerServerPort OBJECT-TYPE
    SYNTAX          SonusRadiusServerPortType
    MAX-ACCESS      read-create
    STATUS          current
    DESCRIPTION     
            "
             Target UDP port used to send requests to the radius server. This can be either a service name to be
             to be looked up in the services file, or an integer value.
             "
    DEFVAL          { "radius-acct" }
    ::= { sonusRadiusRadiusServerEntry 5 }

sonusRadiusRadiusServerSharedSecret OBJECT-TYPE
    SYNTAX          SonusRadiusSharedSecretType
    MAX-ACCESS      read-create
    STATUS          current
    DESCRIPTION     
            "
             The shared secret used to authenticate the packet. The length of the shared secret is
             1-128 characters, though shared secrets of at least 16 characters should be used.
             "
    ::= { sonusRadiusRadiusServerEntry 6 }

sonusRadiusRadiusServerCleanupDelay OBJECT-TYPE
    SYNTAX          SonusRadiusCleanupDelayType
    MAX-ACCESS      read-create
    STATUS          current
    DESCRIPTION     
            "
             The time for which the Radius server maintains the received requests after they are 
             acknowledged, so that retries set to the server can be detected.
             "
    DEFVAL          { 5 }
    ::= { sonusRadiusRadiusServerEntry 7 }

sonusRadiusRadiusServerRowstatus OBJECT-TYPE
    SYNTAX          RowStatus
    MAX-ACCESS      read-create
    STATUS          current
    DESCRIPTION     
            ""
    ::= { sonusRadiusRadiusServerEntry 8 }

END -- end of module SONUS-GEN2-RADIUS-MIB.
