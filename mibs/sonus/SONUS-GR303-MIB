--
-- This SMIv2 module has been generated by smidump 0.2-cvs. Do not edit.
--

SONUS-GR303-MIB DEFINITIONS ::= BEGIN

IMPORTS
    Counter32, Integer32, MODULE-IDENTITY, NOTIFICATION-TYPE, 
    OBJECT-TYPE, Unsigned32
        FROM SNMPv2-SMI
    DisplayString, RowStatus
        FROM SNMPv2-TC
    sonusEventClass, sonusEventDescription, sonusEventLevel, 
    sonusEventTime, sonusSequenceId
        FROM SONUS-COMMON-MIB
    sonusSignallingMIBs
        FROM SONUS-SMI
    SonusAdminState, SonusBoolean, SonusName, SonusServiceState, 
    SonusShelfIndex, SonusSlotIndex
        FROM SONUS-TC;

sonusGr303MIB MODULE-IDENTITY
    LAST-UPDATED    "201110090000Z"
    ORGANIZATION    
            "Sonus Networks, Inc."
    CONTACT-INFO    
            "   Customer Support    
             Sonus Networks, Inc.
             7 Technology Park Drive
             Westford, MA 01886
             USA
             
             Tel: 978-614-8100
             Fax: 978-614-8609
             E-mail: cs.snmp@sonusnet.com"
    DESCRIPTION     
            "The MIB Module for GR-303 Interface."
    ::= { sonusSignallingMIBs 12 }


sonusGr303MIBObjects OBJECT IDENTIFIER
    ::= { sonusGr303MIB 1 }

sonusGr303NodeAdmn OBJECT IDENTIFIER
    ::= { sonusGr303MIBObjects 1 }

sonusGr303NodeAdmnSubProvState OBJECT-TYPE
    SYNTAX          SonusAdminState
    MAX-ACCESS      read-write
    STATUS          current
    DESCRIPTION     
            "The field specifies whether the provisioning of subscribers is enabled or
             disabled.  When disabled provisioning of subscribers is prohibited.  This
             field must be set to disabled to modify other node level attributes"
    DEFVAL          { disabled }
    ::= { sonusGr303NodeAdmn 1 }

sonusGr303NodeAdmnSubProvDataSrc OBJECT-TYPE
    SYNTAX          INTEGER { cli(1), psx(2) }
    MAX-ACCESS      read-write
    STATUS          current
    DESCRIPTION     
            "Controls the subscriber provisioning data source for the node.  The Subscriber
             provisioning state must be set to disabled before this attribute can be
             modified."
    DEFVAL          { psx }
    ::= { sonusGr303NodeAdmn 2 }

sonusGr303NodeAdmnSubProvFullNow OBJECT-TYPE
    SYNTAX          SonusBoolean
    MAX-ACCESS      read-write
    STATUS          current
    DESCRIPTION     
            "Initiate a full reprovisioning of the subscriber data from the PSX.  This
             action is only valid when the subscriber provisioning data source is PSX
             and the subscriber provisioning state is enabled."
    ::= { sonusGr303NodeAdmn 3 }

sonusGr303NodeAdmnSubProvUpdateNow OBJECT-TYPE
    SYNTAX          SonusBoolean
    MAX-ACCESS      read-write
    STATUS          current
    DESCRIPTION     
            "Initiate an update of the subscriber provisioning data from the PSX.  This
             action is only valid when the subscriber provisioning data source is PSX
             and the subscriber provisioning state is enabled."
    ::= { sonusGr303NodeAdmn 4 }

sonusGr303NodeAdmnSubProvIntervalValue OBJECT-TYPE
    SYNTAX          Unsigned32 (0..7200)
    MAX-ACCESS      read-write
    STATUS          current
    DESCRIPTION     
            "Subscriber Provisioning interval timer controls the rate at which we 
             poll the PSX for subscriber updates in seconds."
    DEFVAL          { 300 }
    ::= { sonusGr303NodeAdmn 5 }

sonusGr303Command OBJECT IDENTIFIER
    ::= { sonusGr303MIBObjects 2 }

sonusGr303CmdIgIndex OBJECT-TYPE
    SYNTAX          Unsigned32 (1..500)
    MAX-ACCESS      read-write
    STATUS          current
    DESCRIPTION     
            "The index of the GR303 Interface Group to be operated on."
    ::= { sonusGr303Command 1 }

sonusGr303CmdIgEocSwitchTarget OBJECT-TYPE
    SYNTAX          INTEGER { primary(1), secondary(2) }
    MAX-ACCESS      read-write
    STATUS          current
    DESCRIPTION     
            "The target of this EOC switchover."
    ::= { sonusGr303Command 2 }

sonusGr303CmdIgTmcSwitchTarget OBJECT-TYPE
    SYNTAX          INTEGER { primary(1), secondary(2) }
    MAX-ACCESS      read-write
    STATUS          current
    DESCRIPTION     
            "The target of this TMC switchover."
    ::= { sonusGr303Command 3 }

sonusGr303CmdIgSwitchForced OBJECT-TYPE
    SYNTAX          SonusBoolean
    MAX-ACCESS      read-write
    STATUS          current
    DESCRIPTION     
            "Is this switchover forced?"
    ::= { sonusGr303Command 4 }

sonusGr303CmdIgCounterReset OBJECT-TYPE
    SYNTAX          SonusBoolean
    MAX-ACCESS      read-write
    STATUS          current
    DESCRIPTION     
            "Reset all counters in this GR303 Interface Group?"
    ::= { sonusGr303Command 5 }

sonusGr303CmdIgAuditEocNow OBJECT-TYPE
    SYNTAX          SonusBoolean
    MAX-ACCESS      read-write
    STATUS          current
    DESCRIPTION     
            "Initiate EOC audit immediately in this GR303 Interface Group?"
    ::= { sonusGr303Command 6 }

sonusGr303CmdIgAuditTmcNow OBJECT-TYPE
    SYNTAX          SonusBoolean
    MAX-ACCESS      read-write
    STATUS          current
    DESCRIPTION     
            "Initiate TMC audit immediately in this GR303 Interface Group?"
    ::= { sonusGr303Command 7 }

sonusGr303IgTableNextIndex OBJECT-TYPE
    SYNTAX          Unsigned32
    MAX-ACCESS      not-accessible
    STATUS          current
    DESCRIPTION     
            "The next valid index to use when creating a new GR303 Interface Group."
    ::= { sonusGr303MIBObjects 3 }

sonusGr303IgTable OBJECT-TYPE
    SYNTAX          SEQUENCE OF SonusGr303IgTableEntry
    MAX-ACCESS      not-accessible
    STATUS          current
    DESCRIPTION     
            "This MIB table is used to create GR303 Interface Groups."
    ::= { sonusGr303MIBObjects 4 }

sonusGr303IgTableEntry OBJECT-TYPE
    SYNTAX          SonusGr303IgTableEntry
    MAX-ACCESS      not-accessible
    STATUS          current
    DESCRIPTION     
            "This MIB table is used to create a GR303 Interface Group."
    INDEX           { sonusGr303IgIndex }
    ::= { sonusGr303IgTable 1 }

SonusGr303IgTableEntry ::=
    SEQUENCE {
        sonusGr303IgIndex               Unsigned32,
        sonusGr303IgName                SonusName,
        sonusGr303IgSwitchType          INTEGER,
        sonusGr303IgAdminState          SonusAdminState,
        sonusGr303IgMode                SonusServiceState,
        sonusGr303IgAction              INTEGER,
        sonusGr303IgDryupTimeout        Unsigned32,
        sonusGr303IgSecPort             Unsigned32,
        sonusGr303IgControlSlot         Unsigned32,
        sonusGr303IgEocCmdPacingMeasIntvl Unsigned32,
        sonusGr303IgEocCmdPacingMsgAllowance    Unsigned32,
        sonusGr303IgInhibitPpsTo        INTEGER,
        sonusGr303IgEocShortAuditInterval Unsigned32,
        sonusGr303IgEocDailyAuditHour   Unsigned32,
        sonusGr303IgEocDailyAuditMinute Unsigned32,
        sonusGr303IgTmcAuditInterval    Unsigned32,
        sonusGr303IgShoweringLineAllowance  Unsigned32,
        sonusGr303IgTmcT303             Unsigned32,
        sonusGr303IgTmcT313             Unsigned32,
        sonusGr303IgLapdSapi0K          Unsigned32,
        sonusGr303IgLapdSapi0N200       Unsigned32,
        sonusGr303IgLapdSapi0T200       Unsigned32,
        sonusGr303IgLapdSapi0T203       Unsigned32,
        sonusGr303IgLapdSapi1K          Unsigned32,
        sonusGr303IgLapdSapi1N200       Unsigned32,
        sonusGr303IgLapdSapi1T200       Unsigned32,
        sonusGr303IgLapdSapi1T203       Unsigned32,
        sonusGr303IgRowStatus           RowStatus,
        sonusGr303IgControlShelf        Unsigned32,
        sonusGr303IgFlowThroughProvisioning   SonusAdminState,
        sonusGr303IgShoweringLineWindow Unsigned32,
        sonusGr303IgShoweringLineServiceTimeout       Unsigned32,
        sonusGr303IgMgcDisconnectDropRdt SonusAdminState,
        sonusGr303IgLoadTestOriginateCalls  SonusAdminState,
        sonusGr303IgLoadTestTerminateCalls  SonusAdminState,
        sonusGr303IgLoadTestOriginateDigitReplacement             DisplayString,
        sonusGr303IgLoadTestOriginateWaitToDialMin          Unsigned32,
        sonusGr303IgLoadTestOriginateWaitToDialMax          Unsigned32,
        sonusGr303IgLoadTestTerminateWaitToAnswerMin            Unsigned32,
        sonusGr303IgLoadTestTerminateWaitToAnswerMax            Unsigned32,
        sonusGr303IgLoadTestDroppedWaitToHangUpMin          Unsigned32,
        sonusGr303IgLoadTestDroppedWaitToHangUpMax          Unsigned32,
        sonusGr303IgLoadTestBenchmarkDelayToDialTone            Unsigned32,
        sonusGr303IgLoadTestBenchmarkDelayToRingback            Unsigned32,
        sonusGr303IgLoadTestBenchmarkDelayToAnswered            Unsigned32,
        sonusGr303IgLoadTestBenchmarkDelayToOrigDropped               Unsigned32,
        sonusGr303IgLoadTestBenchmarkDelayToTermDropped               Unsigned32,
        sonusGr303IgLoadTestExclusion   SonusAdminState
    }

sonusGr303IgIndex OBJECT-TYPE
    SYNTAX          Unsigned32
    MAX-ACCESS      read-only
    STATUS          current
    DESCRIPTION     
            "A unique index for this GR303 Interface Group."
    ::= { sonusGr303IgTableEntry 1 }

sonusGr303IgName OBJECT-TYPE
    SYNTAX          SonusName
    MAX-ACCESS      read-write
    STATUS          current
    DESCRIPTION     
            "The name of this GR303 Interface Group."
    ::= { sonusGr303IgTableEntry 2 }

sonusGr303IgSwitchType OBJECT-TYPE
    SYNTAX          INTEGER { dms100(1) }
    MAX-ACCESS      read-write
    STATUS          current
    DESCRIPTION     
            "The switch type that this GR303 Interface Group will emulate
             towards the Remote Data Terminal (RDT)."
    DEFVAL          { dms100 }
    ::= { sonusGr303IgTableEntry 3 }

sonusGr303IgAdminState OBJECT-TYPE
    SYNTAX          SonusAdminState
    MAX-ACCESS      read-write
    STATUS          current
    DESCRIPTION     
            "The administration state of this GR303 Interface Group."
    DEFVAL          { disabled }
    ::= { sonusGr303IgTableEntry 4 }

sonusGr303IgMode OBJECT-TYPE
    SYNTAX          SonusServiceState
    MAX-ACCESS      read-write
    STATUS          current
    DESCRIPTION     
            "The service mode of this GR303 Interface Group."
    DEFVAL          { outOfService }
    ::= { sonusGr303IgTableEntry 5 }

sonusGr303IgAction OBJECT-TYPE
    SYNTAX          INTEGER { dryup(1), force(2) }
    MAX-ACCESS      read-write
    STATUS          current
    DESCRIPTION     
            "The action taken on calls for this GR303 Interface Group when administratively
             going out-of-service."
    DEFVAL          { dryup }
    ::= { sonusGr303IgTableEntry 6 }

sonusGr303IgDryupTimeout OBJECT-TYPE
    SYNTAX          Unsigned32 (0..1440)
    MAX-ACCESS      read-write
    STATUS          current
    DESCRIPTION     
            "The time in minutes allowed for dryup of this GR303 Interface Group.
             If zero, wait indefinitely for calls to end."
    DEFVAL          { 5 }
    ::= { sonusGr303IgTableEntry 7 }

sonusGr303IgSecPort OBJECT-TYPE
    SYNTAX          Unsigned32 (0..28)
    MAX-ACCESS      read-write
    STATUS          current
    DESCRIPTION     
            "The secondary port number of this GR303 Interface Group.
             The valid range is 2-28.  Port number 1 is the primary port.
             If this value is set to zero, there is no secondary port."
    ::= { sonusGr303IgTableEntry 8 }

sonusGr303IgControlSlot OBJECT-TYPE
    SYNTAX          Unsigned32
    MAX-ACCESS      read-only
    STATUS          current
    DESCRIPTION     
            "The card slot hosting the control task for this GR303 Interface Group."
    ::= { sonusGr303IgTableEntry 9 }

sonusGr303IgEocCmdPacingMeasIntvl OBJECT-TYPE
    SYNTAX          Unsigned32 (0..1000)
    MAX-ACCESS      read-write
    STATUS          current
    DESCRIPTION     
            "The EOC command pacing measurement interval of this GR303 Interface Group."
    DEFVAL          { 1 }
    ::= { sonusGr303IgTableEntry 10 }

sonusGr303IgEocCmdPacingMsgAllowance OBJECT-TYPE
    SYNTAX          Unsigned32 (0..1000)
    MAX-ACCESS      read-write
    STATUS          current
    DESCRIPTION     
            "The EOC command pacing message allowance of this GR303 Interface Group."
    DEFVAL          { 4 }
    ::= { sonusGr303IgTableEntry 11 }

sonusGr303IgInhibitPpsTo OBJECT-TYPE
    SYNTAX          INTEGER { none(1), primary(2), secondary(3) }
    MAX-ACCESS      read-write
    STATUS          current
    DESCRIPTION     
            "This field specifies if a Path Protection Switch will be inhibited to
             primary port, secondary port, or none.  It applies to both TMC and EOC."
    DEFVAL          { none }
    ::= { sonusGr303IgTableEntry 12 }

sonusGr303IgEocShortAuditInterval OBJECT-TYPE
    SYNTAX          Unsigned32 (0..60)
    MAX-ACCESS      read-write
    STATUS          current
    DESCRIPTION     
            "The EOC short audit interval (minutes) of this GR303 Interface Group.
             If zero, the EOC short audit is disabled."
    DEFVAL          { 15 }
    ::= { sonusGr303IgTableEntry 13 }

sonusGr303IgEocDailyAuditHour OBJECT-TYPE
    SYNTAX          Unsigned32 (0..23)
    MAX-ACCESS      read-write
    STATUS          current
    DESCRIPTION     
            "The hour portion of EOC daily audit time of this GR303 Interface Group."
    DEFVAL          { 2 }
    ::= { sonusGr303IgTableEntry 14 }

sonusGr303IgEocDailyAuditMinute OBJECT-TYPE
    SYNTAX          Unsigned32 (0..59)
    MAX-ACCESS      read-write
    STATUS          current
    DESCRIPTION     
            "The minute portion of EOC daily audit time of this GR303 Interface Group."
    DEFVAL          { 30 }
    ::= { sonusGr303IgTableEntry 15 }

sonusGr303IgTmcAuditInterval OBJECT-TYPE
    SYNTAX          Unsigned32 (0..10000)
    MAX-ACCESS      read-write
    STATUS          current
    DESCRIPTION     
            "The TMC audit interval (minutes) of this GR303 Interface Group.
             If zero, the automatic auditing of call states is disabled."
    DEFVAL          { 60 }
    ::= { sonusGr303IgTableEntry 16 }

sonusGr303IgShoweringLineAllowance OBJECT-TYPE
    SYNTAX          Unsigned32 (0..1000)
    MAX-ACCESS      read-write
    STATUS          current
    DESCRIPTION     
            "The showering line allowance for a CRV in this GR303 Interface Group.
             If this allowance is set to zero, showering line detection is disabled.
             The showering line count for a CRV increments if successive ingresses
             are aborted by the RDT without the RDT accepting a DS0 connection.
             If the count exceeds this allowance within the time interval of the 
             showering line window, the CRV is marked as a showering line and service 
             is denied until either the service restoration timeout expires or the CRV 
             is configured again as in service. The showering line count is cleared 
             when any DS0 connection is accepted and otherwise decays over the interval
             of the showering line window."
    DEFVAL          { 12 }
    ::= { sonusGr303IgTableEntry 17 }

sonusGr303IgTmcT303 OBJECT-TYPE
    SYNTAX          Unsigned32 (700..4000)
    MAX-ACCESS      read-write
    STATUS          current
    DESCRIPTION     
            "The TMC T303 timer value (msecs) for this GR303 Interface Group."
    DEFVAL          { 700 }
    ::= { sonusGr303IgTableEntry 18 }

sonusGr303IgTmcT313 OBJECT-TYPE
    SYNTAX          Unsigned32 (400..4000)
    MAX-ACCESS      read-write
    STATUS          current
    DESCRIPTION     
            "The TMC T313 timer value (msecs) for this GR303 Interface Group."
    DEFVAL          { 400 }
    ::= { sonusGr303IgTableEntry 19 }

sonusGr303IgLapdSapi0K OBJECT-TYPE
    SYNTAX          Unsigned32 (1..7)
    MAX-ACCESS      read-write
    STATUS          current
    DESCRIPTION     
            "The LAPD K value for SAPI 0 of this GR303 Interface Group."
    DEFVAL          { 7 }
    ::= { sonusGr303IgTableEntry 20 }

sonusGr303IgLapdSapi0N200 OBJECT-TYPE
    SYNTAX          Unsigned32 (1..10)
    MAX-ACCESS      read-write
    STATUS          current
    DESCRIPTION     
            "The LAPD N200 value for SAPI 0 of this GR303 Interface Group."
    DEFVAL          { 3 }
    ::= { sonusGr303IgTableEntry 21 }

sonusGr303IgLapdSapi0T200 OBJECT-TYPE
    SYNTAX          Unsigned32 (100..350)
    MAX-ACCESS      read-write
    STATUS          current
    DESCRIPTION     
            "The LAPD SAPI0 T200 timer value (msecs) for this GR303 Interface Group."
    DEFVAL          { 150 }
    ::= { sonusGr303IgTableEntry 22 }

sonusGr303IgLapdSapi0T203 OBJECT-TYPE
    SYNTAX          Unsigned32 (10..300)
    MAX-ACCESS      read-write
    STATUS          current
    DESCRIPTION     
            "The LAPD SAPI0 T203 timer value (secs) for this GR303 Interface Group."
    DEFVAL          { 30 }
    ::= { sonusGr303IgTableEntry 23 }

sonusGr303IgLapdSapi1K OBJECT-TYPE
    SYNTAX          Unsigned32 (1..7)
    MAX-ACCESS      read-write
    STATUS          current
    DESCRIPTION     
            "The LAPD K value for SAPI 0 of this GR303 Interface Group."
    DEFVAL          { 7 }
    ::= { sonusGr303IgTableEntry 24 }

sonusGr303IgLapdSapi1N200 OBJECT-TYPE
    SYNTAX          Unsigned32 (1..10)
    MAX-ACCESS      read-write
    STATUS          current
    DESCRIPTION     
            "The LAPD N200 value for SAPI 0 of this GR303 Interface Group."
    DEFVAL          { 3 }
    ::= { sonusGr303IgTableEntry 25 }

sonusGr303IgLapdSapi1T200 OBJECT-TYPE
    SYNTAX          Unsigned32 (100..350)
    MAX-ACCESS      read-write
    STATUS          current
    DESCRIPTION     
            "The LAPD SAPI1 T200 timer value (msecs) for this GR303 Interface Group."
    DEFVAL          { 150 }
    ::= { sonusGr303IgTableEntry 26 }

sonusGr303IgLapdSapi1T203 OBJECT-TYPE
    SYNTAX          Unsigned32 (10..300)
    MAX-ACCESS      read-write
    STATUS          current
    DESCRIPTION     
            "The LAPD SAPI1 T203 timer value (secs) for this GR303 Interface Group."
    DEFVAL          { 30 }
    ::= { sonusGr303IgTableEntry 27 }

sonusGr303IgRowStatus OBJECT-TYPE
    SYNTAX          RowStatus
    MAX-ACCESS      read-write
    STATUS          current
    DESCRIPTION     
            "This is for SNMP use."
    ::= { sonusGr303IgTableEntry 28 }

sonusGr303IgControlShelf OBJECT-TYPE
    SYNTAX          Unsigned32
    MAX-ACCESS      read-only
    STATUS          current
    DESCRIPTION     
            "The shelf hosting this GR303 Interface Group."
    ::= { sonusGr303IgTableEntry 29 }

sonusGr303IgFlowThroughProvisioning OBJECT-TYPE
    SYNTAX          SonusAdminState
    MAX-ACCESS      read-write
    STATUS          current
    DESCRIPTION     
            "This field specifies the admin state of flow through provisioning of 
             the RDT for this GR303 Interface Group."
    DEFVAL          { disabled }
    ::= { sonusGr303IgTableEntry 30 }

sonusGr303IgShoweringLineWindow OBJECT-TYPE
    SYNTAX          Unsigned32 (0..60)
    MAX-ACCESS      read-write
    STATUS          current
    DESCRIPTION     
            "The time interval (in seconds) to measure the showering line allowance.
             If this interval is set to zero, there is no limit on how long the showering
             line count may take to increment beyond the showering line allowance."
    DEFVAL          { 5 }
    ::= { sonusGr303IgTableEntry 31 }

sonusGr303IgShoweringLineServiceTimeout OBJECT-TYPE
    SYNTAX          Unsigned32 (0..60)
    MAX-ACCESS      read-write
    STATUS          current
    DESCRIPTION     
            "The time (in minutes) after which a showering line is tentatively restored
             to service.  If the CRV is then detected still to be showering, it will be 
             taken out of service again.  If this timeout is set to zero, no action is taken
             automatically and the CRV must be reconfigured to be restored to service."
    DEFVAL          { 15 }
    ::= { sonusGr303IgTableEntry 32 }

sonusGr303IgMgcDisconnectDropRdt OBJECT-TYPE
    SYNTAX          SonusAdminState
    MAX-ACCESS      read-write
    STATUS          current
    DESCRIPTION     
            "The field specifies whether the GR-303 control links (LAPD) to the RDT device
             should be dropped when the H.248 association with the Media Gateway Controller
             is in a disconnected state.  The control links will be reestablished when
             the association is restored."
    DEFVAL          { enabled }
    ::= { sonusGr303IgTableEntry 33 }

sonusGr303IgLoadTestOriginateCalls OBJECT-TYPE
    SYNTAX          SonusAdminState
    MAX-ACCESS      read-write
    STATUS          current
    DESCRIPTION     
            "Specifies whether the CRVs of this Interface Group shall originate
             load test calls.  This field, like other load test fields, is not
             settable and is ignored in normal GR303 operation."
    DEFVAL          { enabled }
    ::= { sonusGr303IgTableEntry 34 }

sonusGr303IgLoadTestTerminateCalls OBJECT-TYPE
    SYNTAX          SonusAdminState
    MAX-ACCESS      read-write
    STATUS          current
    DESCRIPTION     
            "Specifies whether the CRVs of this Interface Group shall terminate
             load test calls.  This field, like other load test fields, is not
             settable and is ignored in normal GR303 operation."
    DEFVAL          { enabled }
    ::= { sonusGr303IgTableEntry 35 }

sonusGr303IgLoadTestOriginateDigitReplacement OBJECT-TYPE
    SYNTAX          DisplayString (SIZE(0..31))
    MAX-ACCESS      read-write
    STATUS          current
    DESCRIPTION     
            "An optional digit string to replace equally many initial digits
             of the called Directory Number in load test calls made from this
             Interface Group.  May be used to vary call routing.  Must ultimately
             be reversed by complementary PSX digit maniuplation."
    ::= { sonusGr303IgTableEntry 36 }

sonusGr303IgLoadTestOriginateWaitToDialMin OBJECT-TYPE
    SYNTAX          Unsigned32 (0..60)
    MAX-ACCESS      read-write
    STATUS          current
    DESCRIPTION     
            "The time (in seconds) from dial tone detected until digits are out-pulsed.
             For each load test call, a random value is chosen between Min and Max.
             When dialing commences, the inter-digit time will be small."
    DEFVAL          { 5 }
    ::= { sonusGr303IgTableEntry 37 }

sonusGr303IgLoadTestOriginateWaitToDialMax OBJECT-TYPE
    SYNTAX          Unsigned32 (0..60)
    MAX-ACCESS      read-write
    STATUS          current
    DESCRIPTION     
            "The time (in seconds) from dial tone detected until digits are out-pulsed.
             For each load test call, a random value is chosen between Min and Max.
             When dialing commences, the inter-digit time will be small."
    DEFVAL          { 10 }
    ::= { sonusGr303IgTableEntry 38 }

sonusGr303IgLoadTestTerminateWaitToAnswerMin OBJECT-TYPE
    SYNTAX          Unsigned32 (0..60)
    MAX-ACCESS      read-write
    STATUS          current
    DESCRIPTION     
            "The time (in seconds) from ringing received until taken off hook.
             For each load test call, a random value is chosen between Min and Max."
    DEFVAL          { 5 }
    ::= { sonusGr303IgTableEntry 39 }

sonusGr303IgLoadTestTerminateWaitToAnswerMax OBJECT-TYPE
    SYNTAX          Unsigned32 (0..60)
    MAX-ACCESS      read-write
    STATUS          current
    DESCRIPTION     
            "The time (in seconds) from ringing received until taken off hook.
             For each load test call, a random value is chosen between Min and Max."
    DEFVAL          { 15 }
    ::= { sonusGr303IgTableEntry 40 }

sonusGr303IgLoadTestDroppedWaitToHangUpMin OBJECT-TYPE
    SYNTAX          Unsigned32 (0..60)
    MAX-ACCESS      read-write
    STATUS          current
    DESCRIPTION     
            "The time (in seconds) from disconnect received until placed on hook.
             For each load test call, a random value is chosen between Min and Max."
    DEFVAL          { 2 }
    ::= { sonusGr303IgTableEntry 41 }

sonusGr303IgLoadTestDroppedWaitToHangUpMax OBJECT-TYPE
    SYNTAX          Unsigned32 (0..60)
    MAX-ACCESS      read-write
    STATUS          current
    DESCRIPTION     
            "The time (in seconds) from disconnect received until placed on hook.
             For each load test call, a random value is chosen between Min and Max."
    DEFVAL          { 5 }
    ::= { sonusGr303IgTableEntry 42 }

sonusGr303IgLoadTestBenchmarkDelayToDialTone OBJECT-TYPE
    SYNTAX          Unsigned32 (0..65535)
    MAX-ACCESS      read-write
    STATUS          current
    DESCRIPTION     
            "An objective (in milliseconds) from originator off hook to originator dial tone detected.
             Statistics are incremented according to the delay experienced.
             Included in this delay is the minimum tone time.
             The benchmark value configured at the originating Interface Group applies."
    DEFVAL          { 1700 }
    ::= { sonusGr303IgTableEntry 43 }

sonusGr303IgLoadTestBenchmarkDelayToRingback OBJECT-TYPE
    SYNTAX          Unsigned32 (0..65535)
    MAX-ACCESS      read-write
    STATUS          current
    DESCRIPTION     
            "An objective (in milliseconds) from originator dialing to originator ringback detected.
             Statistics are incremented according to the delay experienced.
             Included in this delay are digit out-pulsing and the minimum tone time.
             The benchmark value configured at the originating Interface Group applies."
    DEFVAL          { 4000 }
    ::= { sonusGr303IgTableEntry 44 }

sonusGr303IgLoadTestBenchmarkDelayToAnswered OBJECT-TYPE
    SYNTAX          Unsigned32 (0..65535)
    MAX-ACCESS      read-write
    STATUS          current
    DESCRIPTION     
            "An objective (in milliseconds) from terminator off hook to originator answer supervision.
             Statistics are incremented according to the delay experienced.
             The benchmark value configured at the originating Interface Group applies."
    DEFVAL          { 500 }
    ::= { sonusGr303IgTableEntry 45 }

sonusGr303IgLoadTestBenchmarkDelayToOrigDropped OBJECT-TYPE
    SYNTAX          Unsigned32 (0..65535)
    MAX-ACCESS      read-write
    STATUS          current
    DESCRIPTION     
            "An objective (in milliseconds) from terminator on hook to originator disconnected.
             Statistics are incremented according to the delay experienced.
             Included in this delay may be a timed disconnect interval.
             The benchmark value configured at the originating Interface Group applies."
    DEFVAL          { 13000 }
    ::= { sonusGr303IgTableEntry 46 }

sonusGr303IgLoadTestBenchmarkDelayToTermDropped OBJECT-TYPE
    SYNTAX          Unsigned32 (0..65535)
    MAX-ACCESS      read-write
    STATUS          current
    DESCRIPTION     
            "An objective (in milliseconds) from originator on hook to terminator disconnected.
             Statistics are incremented according to the delay experienced.
             The benchmark value configured at the originating Interface Group applies."
    DEFVAL          { 2000 }
    ::= { sonusGr303IgTableEntry 47 }

sonusGr303IgLoadTestExclusion OBJECT-TYPE
    SYNTAX          SonusAdminState
    MAX-ACCESS      read-write
    STATUS          current
    DESCRIPTION     
            "Specifies whether this Interface Group shall be excluded from load testing
             (RDT role) and shall be kept under normal media gateway control (IDT role).
             With interconnected T1 ports, both roles can be hosted on a single system."
    DEFVAL          { disabled }
    ::= { sonusGr303IgTableEntry 48 }

sonusGr303IgPortTable OBJECT-TYPE
    SYNTAX          SEQUENCE OF SonusGr303IgPortEntry
    MAX-ACCESS      not-accessible
    STATUS          current
    DESCRIPTION     
            "This MIB table is for GR303 Interface Group port entries."
    ::= { sonusGr303MIBObjects 5 }

sonusGr303IgPortEntry OBJECT-TYPE
    SYNTAX          SonusGr303IgPortEntry
    MAX-ACCESS      not-accessible
    STATUS          current
    DESCRIPTION     
            "This MIB table defines a GR303 Interface Group port entry."
    INDEX           { sonusGr303IgPortIgIndex, sonusGr303IgPortIndex }
    ::= { sonusGr303IgPortTable 1 }

SonusGr303IgPortEntry ::=
    SEQUENCE {
        sonusGr303IgPortIgIndex         Unsigned32,
        sonusGr303IgPortIndex           Unsigned32,
        sonusGr303IgPortDs1Shelf        SonusShelfIndex,
        sonusGr303IgPortDs1Slot         SonusSlotIndex,
        sonusGr303IgPortDs1Port         Integer32,
        sonusGr303IgPortDs1Index        Integer32,
        sonusGr303IgPortAdminState      SonusAdminState,
        sonusGr303IgPortMode            SonusServiceState,
        sonusGr303IgPortAction          INTEGER,
        sonusGr303IgPortRowStatus       RowStatus,
        sonusGr303IgPortDryupTimeout    Unsigned32
    }

sonusGr303IgPortIgIndex OBJECT-TYPE
    SYNTAX          Unsigned32
    MAX-ACCESS      not-accessible
    STATUS          current
    DESCRIPTION     
            "The index of the GR303 Interface Group that this port belongs to."
    ::= { sonusGr303IgPortEntry 1 }

sonusGr303IgPortIndex OBJECT-TYPE
    SYNTAX          Unsigned32 (1..28)
    MAX-ACCESS      read-write
    STATUS          current
    DESCRIPTION     
            "The logical DS1 number of this GR303 port."
    DEFVAL          { 1 }
    ::= { sonusGr303IgPortEntry 2 }

sonusGr303IgPortDs1Shelf OBJECT-TYPE
    SYNTAX          SonusShelfIndex
    MAX-ACCESS      read-write
    STATUS          current
    DESCRIPTION     
            "Shelf index for the T1 circuit assigned to this GR303 port."
    ::= { sonusGr303IgPortEntry 3 }

sonusGr303IgPortDs1Slot OBJECT-TYPE
    SYNTAX          SonusSlotIndex
    MAX-ACCESS      read-write
    STATUS          current
    DESCRIPTION     
            "Slot index for the T1 circuit assigned to this GR303 port."
    ::= { sonusGr303IgPortEntry 4 }

sonusGr303IgPortDs1Port OBJECT-TYPE
    SYNTAX          Integer32 (1..100)
    MAX-ACCESS      read-write
    STATUS          current
    DESCRIPTION     
            "Port Number for the T1 circuit assigned to this GR303 port."
    ::= { sonusGr303IgPortEntry 5 }

sonusGr303IgPortDs1Index OBJECT-TYPE
    SYNTAX          Integer32 (1..100)
    MAX-ACCESS      read-write
    STATUS          current
    DESCRIPTION     
            "Ds1 Index for the T1 circuit assigned to this GR303 port."
    ::= { sonusGr303IgPortEntry 6 }

sonusGr303IgPortAdminState OBJECT-TYPE
    SYNTAX          SonusAdminState
    MAX-ACCESS      read-write
    STATUS          current
    DESCRIPTION     
            "The administration state of this GR303 port."
    DEFVAL          { disabled }
    ::= { sonusGr303IgPortEntry 7 }

sonusGr303IgPortMode OBJECT-TYPE
    SYNTAX          SonusServiceState
    MAX-ACCESS      read-write
    STATUS          current
    DESCRIPTION     
            "The service mode of this GR303 port."
    DEFVAL          { outOfService }
    ::= { sonusGr303IgPortEntry 8 }

sonusGr303IgPortAction OBJECT-TYPE
    SYNTAX          INTEGER { dryup(1), force(2) }
    MAX-ACCESS      read-write
    STATUS          current
    DESCRIPTION     
            "The action taken on calls for this GR303 port when administratively
             going out-of-service."
    DEFVAL          { dryup }
    ::= { sonusGr303IgPortEntry 9 }

sonusGr303IgPortRowStatus OBJECT-TYPE
    SYNTAX          RowStatus
    MAX-ACCESS      read-write
    STATUS          current
    DESCRIPTION     
            "This is for SNMP use."
    ::= { sonusGr303IgPortEntry 10 }

sonusGr303IgPortDryupTimeout OBJECT-TYPE
    SYNTAX          Unsigned32 (0..1440)
    MAX-ACCESS      read-write
    STATUS          current
    DESCRIPTION     
            "The time in minutes allowed for dryup of this GR303 port.
             If zero, wait indefinitely for calls to end."
    DEFVAL          { 5 }
    ::= { sonusGr303IgPortEntry 11 }

sonusGr303IgCrvTable OBJECT-TYPE
    SYNTAX          SEQUENCE OF SonusGr303IgCrvEntry
    MAX-ACCESS      not-accessible
    STATUS          current
    DESCRIPTION     
            "This MIB table is for GR303 Interface Group CRV entries."
    ::= { sonusGr303MIBObjects 6 }

sonusGr303IgCrvEntry OBJECT-TYPE
    SYNTAX          SonusGr303IgCrvEntry
    MAX-ACCESS      not-accessible
    STATUS          current
    DESCRIPTION     
            "This MIB table defines a GR303 Interface Group CRV entry."
    INDEX           { sonusGr303IgCrvIgIndex, sonusGr303IgCrvIndex }
    ::= { sonusGr303IgCrvTable 1 }

SonusGr303IgCrvEntry ::=
    SEQUENCE {
        sonusGr303IgCrvIgIndex          Unsigned32,
        sonusGr303IgCrvIndex            Unsigned32,
        sonusGr303IgCrvMode             SonusServiceState,
        sonusGr303IgCrvNumWire          INTEGER,
        sonusGr303IgCrvProtoCode        INTEGER,
        sonusGr303IgCrvRowStatus        RowStatus,
        sonusGr303IgCrvDn               DisplayString,
        sonusGr303IgCrvAdminState       SonusAdminState
    }

sonusGr303IgCrvIgIndex OBJECT-TYPE
    SYNTAX          Unsigned32
    MAX-ACCESS      not-accessible
    STATUS          current
    DESCRIPTION     
            "The GR303 Interface Group index that this CRV belongs to."
    ::= { sonusGr303IgCrvEntry 1 }

sonusGr303IgCrvIndex OBJECT-TYPE
    SYNTAX          Unsigned32 (1..2048)
    MAX-ACCESS      read-write
    STATUS          current
    DESCRIPTION     
            "The Call Reference Value that designates this subscriber."
    DEFVAL          { 1 }
    ::= { sonusGr303IgCrvEntry 2 }

sonusGr303IgCrvMode OBJECT-TYPE
    SYNTAX          SonusServiceState
    MAX-ACCESS      read-write
    STATUS          current
    DESCRIPTION     
            "The service mode of this CRV."
    DEFVAL          { outOfService }
    ::= { sonusGr303IgCrvEntry 3 }

sonusGr303IgCrvNumWire OBJECT-TYPE
    SYNTAX          INTEGER { two(1), four(2) }
    MAX-ACCESS      read-write
    STATUS          current
    DESCRIPTION     
            "The number of wires of the analog line connected to the Remote Digital
             Terminal (RDT) for this CRV."
    DEFVAL          { two }
    ::= { sonusGr303IgCrvEntry 4 }

sonusGr303IgCrvProtoCode OBJECT-TYPE
    SYNTAX          INTEGER { loopstart(1), groundstart(2) }
    MAX-ACCESS      read-write
    STATUS          current
    DESCRIPTION     
            "The protocol code of the analog line connected to the Remote Digital
             Terminal (RDT) for this CRV."
    DEFVAL          { loopstart }
    ::= { sonusGr303IgCrvEntry 5 }

sonusGr303IgCrvRowStatus OBJECT-TYPE
    SYNTAX          RowStatus
    MAX-ACCESS      read-write
    STATUS          current
    DESCRIPTION     
            "This is for SNMP use."
    ::= { sonusGr303IgCrvEntry 6 }

sonusGr303IgCrvDn OBJECT-TYPE
    SYNTAX          DisplayString (SIZE(0..31))
    MAX-ACCESS      read-write
    STATUS          current
    DESCRIPTION     
            "The Directory Number of this CRV."
    ::= { sonusGr303IgCrvEntry 7 }

sonusGr303IgCrvAdminState OBJECT-TYPE
    SYNTAX          SonusAdminState
    MAX-ACCESS      read-write
    STATUS          current
    DESCRIPTION     
            "The adminstration state of this CRV."
    DEFVAL          { disabled }
    ::= { sonusGr303IgCrvEntry 8 }

sonusGr303IgStatusTable OBJECT-TYPE
    SYNTAX          SEQUENCE OF SonusGr303IgStatusEntry
    MAX-ACCESS      not-accessible
    STATUS          current
    DESCRIPTION     
            "This table presents the GR303 Interface Group status."
    ::= { sonusGr303MIBObjects 7 }

sonusGr303IgStatusEntry OBJECT-TYPE
    SYNTAX          SonusGr303IgStatusEntry
    MAX-ACCESS      not-accessible
    STATUS          current
    DESCRIPTION     
            "This entry presents the status of a GR303 Interface Group."
    INDEX           { sonusGr303StatIgIndex }
    ::= { sonusGr303IgStatusTable 1 }

SonusGr303IgStatusEntry ::=
    SEQUENCE {
        sonusGr303StatIgIndex           Unsigned32,
        sonusGr303StatIgName            DisplayString,
        sonusGr303StatIgStatus          INTEGER,
        sonusGr303StatIgControlShelf    Unsigned32,
        sonusGr303StatIgControlSlot     Unsigned32,
        sonusGr303StatIgEocPriChanStatus INTEGER,
        sonusGr303StatIgEocPriChanPpsLinkStatus       INTEGER,
        sonusGr303StatIgEocPriChanActivePath    SonusBoolean,
        sonusGr303StatIgEocSecChanStatus INTEGER,
        sonusGr303StatIgEocSecChanPpsLinkStatus       INTEGER,
        sonusGr303StatIgEocSecChanActivePath    SonusBoolean,
        sonusGr303StatIgTmcPriChanStatus INTEGER,
        sonusGr303StatIgTmcPriChanPpsLinkStatus       INTEGER,
        sonusGr303StatIgTmcPriChanActivePath    SonusBoolean,
        sonusGr303StatIgTmcSecChanStatus INTEGER,
        sonusGr303StatIgTmcSecChanPpsLinkStatus       INTEGER,
        sonusGr303StatIgTmcSecChanActivePath    SonusBoolean,
        sonusGr303StatIgDs0UsageCounterIngress      Counter32,
        sonusGr303StatIgDs0UsageCounterEgress     Counter32,
        sonusGr303StatIgDs0UsageCounterAvailable        Counter32,
        sonusGr303StatIgDs0UsageCounterDisabled       Counter32
    }

sonusGr303StatIgIndex OBJECT-TYPE
    SYNTAX          Unsigned32
    MAX-ACCESS      read-only
    STATUS          current
    DESCRIPTION     
            "The unique index of this GR303 Interface Group."
    ::= { sonusGr303IgStatusEntry 1 }

sonusGr303StatIgName OBJECT-TYPE
    SYNTAX          DisplayString (SIZE(0..23))
    MAX-ACCESS      read-only
    STATUS          current
    DESCRIPTION     
            "The name of this GR303 Interface Group."
    ::= { sonusGr303IgStatusEntry 2 }

sonusGr303StatIgStatus OBJECT-TYPE
    SYNTAX          INTEGER { down(1), up(2) }
    MAX-ACCESS      read-only
    STATUS          current
    DESCRIPTION     
            "The GR303 Interface Group operational status."
    ::= { sonusGr303IgStatusEntry 3 }

sonusGr303StatIgControlShelf OBJECT-TYPE
    SYNTAX          Unsigned32
    MAX-ACCESS      read-only
    STATUS          current
    DESCRIPTION     
            "The control shelf of this GR303 Interface Group."
    ::= { sonusGr303IgStatusEntry 4 }

sonusGr303StatIgControlSlot OBJECT-TYPE
    SYNTAX          Unsigned32
    MAX-ACCESS      read-only
    STATUS          current
    DESCRIPTION     
            "The control slot of this GR303 Interface Group."
    ::= { sonusGr303IgStatusEntry 5 }

sonusGr303StatIgEocPriChanStatus OBJECT-TYPE
    SYNTAX          INTEGER { down(1), up(2) }
    MAX-ACCESS      read-only
    STATUS          current
    DESCRIPTION     
            "The primary EOC payload link status of this GR303 Interface Group."
    ::= { sonusGr303IgStatusEntry 6 }

sonusGr303StatIgEocPriChanPpsLinkStatus OBJECT-TYPE
    SYNTAX          INTEGER { down(1), up(2) }
    MAX-ACCESS      read-only
    STATUS          current
    DESCRIPTION     
            "The primary EOC PPS link status of this GR303 Interface Group."
    ::= { sonusGr303IgStatusEntry 7 }

sonusGr303StatIgEocPriChanActivePath OBJECT-TYPE
    SYNTAX          SonusBoolean
    MAX-ACCESS      read-only
    STATUS          current
    DESCRIPTION     
            "Is the primary EOC path active for this GR303 Interface Group?"
    ::= { sonusGr303IgStatusEntry 8 }

sonusGr303StatIgEocSecChanStatus OBJECT-TYPE
    SYNTAX          INTEGER { down(1), up(2) }
    MAX-ACCESS      read-only
    STATUS          current
    DESCRIPTION     
            "The secondary EOC payload link status of this GR303 Interface Group."
    ::= { sonusGr303IgStatusEntry 9 }

sonusGr303StatIgEocSecChanPpsLinkStatus OBJECT-TYPE
    SYNTAX          INTEGER { down(1), up(2) }
    MAX-ACCESS      read-only
    STATUS          current
    DESCRIPTION     
            "The secondary EOC PPS link status of this GR303 Interface Group."
    ::= { sonusGr303IgStatusEntry 10 }

sonusGr303StatIgEocSecChanActivePath OBJECT-TYPE
    SYNTAX          SonusBoolean
    MAX-ACCESS      read-only
    STATUS          current
    DESCRIPTION     
            "Is the secondary EOC path active for this GR303 Interface Group?"
    ::= { sonusGr303IgStatusEntry 11 }

sonusGr303StatIgTmcPriChanStatus OBJECT-TYPE
    SYNTAX          INTEGER { down(1), up(2) }
    MAX-ACCESS      read-only
    STATUS          current
    DESCRIPTION     
            "The primary TMC payload link status of this GR303 Interface Group."
    ::= { sonusGr303IgStatusEntry 12 }

sonusGr303StatIgTmcPriChanPpsLinkStatus OBJECT-TYPE
    SYNTAX          INTEGER { down(1), up(2) }
    MAX-ACCESS      read-only
    STATUS          current
    DESCRIPTION     
            "The primary TMC PPS link status of this GR303 Interface Group."
    ::= { sonusGr303IgStatusEntry 13 }

sonusGr303StatIgTmcPriChanActivePath OBJECT-TYPE
    SYNTAX          SonusBoolean
    MAX-ACCESS      read-only
    STATUS          current
    DESCRIPTION     
            "Is the primary TMC path active for this GR303 Interface Group?"
    ::= { sonusGr303IgStatusEntry 14 }

sonusGr303StatIgTmcSecChanStatus OBJECT-TYPE
    SYNTAX          INTEGER { down(1), up(2) }
    MAX-ACCESS      read-only
    STATUS          current
    DESCRIPTION     
            "The secondary TMC payload link status of this GR303 Interface Group."
    ::= { sonusGr303IgStatusEntry 15 }

sonusGr303StatIgTmcSecChanPpsLinkStatus OBJECT-TYPE
    SYNTAX          INTEGER { down(1), up(2) }
    MAX-ACCESS      read-only
    STATUS          current
    DESCRIPTION     
            "The secondary TMC PPS link status of this GR303 Interface Group."
    ::= { sonusGr303IgStatusEntry 16 }

sonusGr303StatIgTmcSecChanActivePath OBJECT-TYPE
    SYNTAX          SonusBoolean
    MAX-ACCESS      read-only
    STATUS          current
    DESCRIPTION     
            "Is the secondary TMC path active for this GR303 Interface Group?"
    ::= { sonusGr303IgStatusEntry 17 }

sonusGr303StatIgDs0UsageCounterIngress OBJECT-TYPE
    SYNTAX          Counter32
    MAX-ACCESS      read-only
    STATUS          current
    DESCRIPTION     
            "The current number of ingress DS0 channels in this GR303 Interface Group."
    ::= { sonusGr303IgStatusEntry 18 }

sonusGr303StatIgDs0UsageCounterEgress OBJECT-TYPE
    SYNTAX          Counter32
    MAX-ACCESS      read-only
    STATUS          current
    DESCRIPTION     
            "The current number of egress DS0 channels in this GR303 Interface Group."
    ::= { sonusGr303IgStatusEntry 19 }

sonusGr303StatIgDs0UsageCounterAvailable OBJECT-TYPE
    SYNTAX          Counter32
    MAX-ACCESS      read-only
    STATUS          current
    DESCRIPTION     
            "The current number of idle DS0 channels available for calls in this GR303 Interface Group."
    ::= { sonusGr303IgStatusEntry 20 }

sonusGr303StatIgDs0UsageCounterDisabled OBJECT-TYPE
    SYNTAX          Counter32
    MAX-ACCESS      read-only
    STATUS          current
    DESCRIPTION     
            "The current number of disabled DS0 channels in this GR303 Interface Group."
    ::= { sonusGr303IgStatusEntry 21 }

sonusGr303IgPortStatusTable OBJECT-TYPE
    SYNTAX          SEQUENCE OF SonusGr303IgPortStatusEntry
    MAX-ACCESS      not-accessible
    STATUS          current
    DESCRIPTION     
            "This table presents the GR303 Interface Group Port status."
    ::= { sonusGr303MIBObjects 8 }

sonusGr303IgPortStatusEntry OBJECT-TYPE
    SYNTAX          SonusGr303IgPortStatusEntry
    MAX-ACCESS      not-accessible
    STATUS          current
    DESCRIPTION     
            "This entry presents the status of a GR303 Interface Group Port."
    INDEX           { sonusGr303StatIgPortIgIndex, 
                      sonusGr303StatIgPortIndex }
    ::= { sonusGr303IgPortStatusTable 1 }

SonusGr303IgPortStatusEntry ::=
    SEQUENCE {
        sonusGr303StatIgPortIgIndex     Unsigned32,
        sonusGr303StatIgPortIndex       Unsigned32,
        sonusGr303StatIgPortServerState INTEGER,
        sonusGr303StatIgPortServerMode  INTEGER,
        sonusGr303StatIgPortChannelInService    DisplayString,
        sonusGr303StatIgPortChannelOperational      DisplayString,
        sonusGr303StatIgPortChannelAllocated    DisplayString
    }

sonusGr303StatIgPortIgIndex OBJECT-TYPE
    SYNTAX          Unsigned32
    MAX-ACCESS      not-accessible
    STATUS          current
    DESCRIPTION     
            "The GR303 Interface Group index that this port belongs to."
    ::= { sonusGr303IgPortStatusEntry 1 }

sonusGr303StatIgPortIndex OBJECT-TYPE
    SYNTAX          Unsigned32
    MAX-ACCESS      read-only
    STATUS          current
    DESCRIPTION     
            "The logical DS1 number of this GR303 port."
    ::= { sonusGr303IgPortStatusEntry 2 }

sonusGr303StatIgPortServerState OBJECT-TYPE
    SYNTAX          INTEGER { active(1), inactive(2) }
    MAX-ACCESS      read-only
    STATUS          current
    DESCRIPTION     
            "The operational status of the server hosting this GR303 port."
    ::= { sonusGr303IgPortStatusEntry 3 }

sonusGr303StatIgPortServerMode OBJECT-TYPE
    SYNTAX          INTEGER { inservice(1), dryup(2), outofservice(3) }
    MAX-ACCESS      read-only
    STATUS          current
    DESCRIPTION     
            "The mode of the server hosting this GR303 port."
    ::= { sonusGr303IgPortStatusEntry 4 }

sonusGr303StatIgPortChannelInService OBJECT-TYPE
    SYNTAX          DisplayString (SIZE(0..32))
    MAX-ACCESS      read-only
    STATUS          current
    DESCRIPTION     
            "A string displaying which DS0 channels of this GR303 port
             are in-service for new calls. The channels run left to right
             from 1 to 24.  The key is:
             0 - out-of-service
             1 - in-service"
    ::= { sonusGr303IgPortStatusEntry 5 }

sonusGr303StatIgPortChannelOperational OBJECT-TYPE
    SYNTAX          DisplayString (SIZE(0..32))
    MAX-ACCESS      read-only
    STATUS          current
    DESCRIPTION     
            "A string displaying which DS0 channels of this GR303 port
             are operational from a hardware point of view.  The channels
             run left to right from 1 to 24. The key is:
             0 - inoperational
             1 - operational"
    ::= { sonusGr303IgPortStatusEntry 6 }

sonusGr303StatIgPortChannelAllocated OBJECT-TYPE
    SYNTAX          DisplayString (SIZE(0..32))
    MAX-ACCESS      read-only
    STATUS          current
    DESCRIPTION     
            "A string displaying which DS0 channels of this GR303 port
             are currently in use. The channels run left to right from
             1 to 24. The key is:
             0 - unallocated
             1 - allocated"
    ::= { sonusGr303IgPortStatusEntry 7 }

sonusGr303IgPortCountTable OBJECT-TYPE
    SYNTAX          SEQUENCE OF SonusGr303IgPortCountEntry
    MAX-ACCESS      not-accessible
    STATUS          current
    DESCRIPTION     
            "This table presents the GR303 Interface Group port counters."
    ::= { sonusGr303MIBObjects 10 }

sonusGr303IgPortCountEntry OBJECT-TYPE
    SYNTAX          SonusGr303IgPortCountEntry
    MAX-ACCESS      not-accessible
    STATUS          current
    DESCRIPTION     
            "This entry presents the counters of a GR303 Interface Group port."
    INDEX           { sonusGr303CountIgPortIgIndex, 
                      sonusGr303CountIgPortIndex }
    ::= { sonusGr303IgPortCountTable 1 }

SonusGr303IgPortCountEntry ::=
    SEQUENCE {
        sonusGr303CountIgPortIgIndex    Unsigned32,
        sonusGr303CountIgPortIndex      Unsigned32,
        sonusGr303CountIgPortHourlyProratedCallSeconds              Unsigned32,
        sonusGr303CountIgPortPercentageUtilization          Unsigned32,
        sonusGr303CountIgPortMaximumSimultaneousAssignments2Ds0                       Unsigned32,
        sonusGr303CountIgPortAverageDurationOfIngressAssignments2Ds0                            Unsigned32,
        sonusGr303CountIgPortAverageDurationOfEgressAssignments2Ds0                           Unsigned32,
        sonusGr303CountIgPortIngressCalls Counter32,
        sonusGr303CountIgPortEgressCalls Counter32
    }

sonusGr303CountIgPortIgIndex OBJECT-TYPE
    SYNTAX          Unsigned32
    MAX-ACCESS      read-only
    STATUS          current
    DESCRIPTION     
            "The GR303 Interface Group index that this port belongs to."
    ::= { sonusGr303IgPortCountEntry 1 }

sonusGr303CountIgPortIndex OBJECT-TYPE
    SYNTAX          Unsigned32
    MAX-ACCESS      read-only
    STATUS          current
    DESCRIPTION     
            "The logical DS1 number of this GR303 port."
    ::= { sonusGr303IgPortCountEntry 2 }

sonusGr303CountIgPortHourlyProratedCallSeconds OBJECT-TYPE
    SYNTAX          Unsigned32
    MAX-ACCESS      read-only
    STATUS          current
    DESCRIPTION     
            "The traffic in Call Seconds on this port prorated to an hourly basis
             from the time the GR303 Interface Group counters were last cleared.
             Full utilization would be 36 CCS times the number of DS0 channels."
    ::= { sonusGr303IgPortCountEntry 3 }

sonusGr303CountIgPortPercentageUtilization OBJECT-TYPE
    SYNTAX          Unsigned32
    MAX-ACCESS      read-only
    STATUS          current
    DESCRIPTION     
            "The percentage utilization of this port relative to its peak capacity
             since the GR303 Interface Group counters were last cleared."
    ::= { sonusGr303IgPortCountEntry 4 }

sonusGr303CountIgPortMaximumSimultaneousAssignments2Ds0 OBJECT-TYPE
    SYNTAX          Unsigned32
    MAX-ACCESS      read-only
    STATUS          current
    DESCRIPTION     
            "The maximum number of simultaneous DS0 assignments on this port
             since the GR303 Interface Group counters were last cleared."
    ::= { sonusGr303IgPortCountEntry 5 }

sonusGr303CountIgPortAverageDurationOfIngressAssignments2Ds0 OBJECT-TYPE
    SYNTAX          Unsigned32
    MAX-ACCESS      read-only
    STATUS          current
    DESCRIPTION     
            "The average duration (seconds) of ingress DS0 assignments on this port
             since the GR303 Interface Group counters were last cleared."
    ::= { sonusGr303IgPortCountEntry 6 }

sonusGr303CountIgPortAverageDurationOfEgressAssignments2Ds0 OBJECT-TYPE
    SYNTAX          Unsigned32
    MAX-ACCESS      read-only
    STATUS          current
    DESCRIPTION     
            "The average duration (seconds) of egress DS0 assignments on this port
             since the GR303 Interface Group counters were last cleared."
    ::= { sonusGr303IgPortCountEntry 7 }

sonusGr303CountIgPortIngressCalls OBJECT-TYPE
    SYNTAX          Counter32
    MAX-ACCESS      read-only
    STATUS          current
    DESCRIPTION     
            "The number of ingress DS0 assignments on this GR303 port."
    ::= { sonusGr303IgPortCountEntry 8 }

sonusGr303CountIgPortEgressCalls OBJECT-TYPE
    SYNTAX          Counter32
    MAX-ACCESS      read-only
    STATUS          current
    DESCRIPTION     
            "The number of egress DS0 assignments on this GR303 port."
    ::= { sonusGr303IgPortCountEntry 9 }

sonusGr303IgCrvCountTable OBJECT-TYPE
    SYNTAX          SEQUENCE OF SonusGr303IgCrvCountEntry
    MAX-ACCESS      not-accessible
    STATUS          current
    DESCRIPTION     
            "This table presents the GR303 Interface Group CRV counters."
    ::= { sonusGr303MIBObjects 11 }

sonusGr303IgCrvCountEntry OBJECT-TYPE
    SYNTAX          SonusGr303IgCrvCountEntry
    MAX-ACCESS      not-accessible
    STATUS          current
    DESCRIPTION     
            "This entry presents the counters of a GR303 Interface Group CRV."
    INDEX           { sonusGr303CountIgCrvIgIndex, 
                      sonusGr303CountIgCrvIndex }
    ::= { sonusGr303IgCrvCountTable 1 }

SonusGr303IgCrvCountEntry ::=
    SEQUENCE {
        sonusGr303CountIgCrvIgIndex     Unsigned32,
        sonusGr303CountIgCrvIndex       Unsigned32,
        sonusGr303CountIgCrvHourlyProratedCallSeconds             Unsigned32,
        sonusGr303CountIgCrvPercentageUtilization         Unsigned32,
        sonusGr303CountIgCrvAverageDurationOfIngressAssignments2Ds0                           Unsigned32,
        sonusGr303CountIgCrvAverageDurationOfEgressAssignments2Ds0                          Unsigned32,
        sonusGr303CountIgCrvIngressAttempts   Counter32,
        sonusGr303CountIgCrvIngressAttemptsBlocked          Counter32,
        sonusGr303CountIgCrvEgressCalls Counter32,
        sonusGr303CountIgCrvEgressCallsBlocked      Counter32
    }

sonusGr303CountIgCrvIgIndex OBJECT-TYPE
    SYNTAX          Unsigned32
    MAX-ACCESS      not-accessible
    STATUS          current
    DESCRIPTION     
            "The GR303 Interface Group index that this CRV belongs to."
    ::= { sonusGr303IgCrvCountEntry 1 }

sonusGr303CountIgCrvIndex OBJECT-TYPE
    SYNTAX          Unsigned32
    MAX-ACCESS      read-only
    STATUS          current
    DESCRIPTION     
            "The Call Reference Value that designates this subscriber."
    ::= { sonusGr303IgCrvCountEntry 2 }

sonusGr303CountIgCrvHourlyProratedCallSeconds OBJECT-TYPE
    SYNTAX          Unsigned32
    MAX-ACCESS      read-only
    STATUS          current
    DESCRIPTION     
            "The traffic in Call Seconds on this CRV prorated to an hourly basis
             from the time the GR303 Interface Group counters were last cleared.
             Full utilization would be 36 CCS."
    ::= { sonusGr303IgCrvCountEntry 3 }

sonusGr303CountIgCrvPercentageUtilization OBJECT-TYPE
    SYNTAX          Unsigned32
    MAX-ACCESS      read-only
    STATUS          current
    DESCRIPTION     
            "The percentage utilization of this CRV
             since the GR303 Interface Group counters were last cleared."
    ::= { sonusGr303IgCrvCountEntry 4 }

sonusGr303CountIgCrvAverageDurationOfIngressAssignments2Ds0 OBJECT-TYPE
    SYNTAX          Unsigned32
    MAX-ACCESS      read-only
    STATUS          current
    DESCRIPTION     
            "The average duration (seconds) of ingress DS0 assignments to this CRV
             since the GR303 Interface Group counters were last cleared."
    ::= { sonusGr303IgCrvCountEntry 5 }

sonusGr303CountIgCrvAverageDurationOfEgressAssignments2Ds0 OBJECT-TYPE
    SYNTAX          Unsigned32
    MAX-ACCESS      read-only
    STATUS          current
    DESCRIPTION     
            "The average duration (seconds) of egress DS0 assignments to this CRV
             since the GR303 Interface Group counters were last cleared."
    ::= { sonusGr303IgCrvCountEntry 6 }

sonusGr303CountIgCrvIngressAttempts OBJECT-TYPE
    SYNTAX          Counter32
    MAX-ACCESS      read-only
    STATUS          current
    DESCRIPTION     
            "The number of ingress attempts on this CRV."
    ::= { sonusGr303IgCrvCountEntry 7 }

sonusGr303CountIgCrvIngressAttemptsBlocked OBJECT-TYPE
    SYNTAX          Counter32
    MAX-ACCESS      read-only
    STATUS          current
    DESCRIPTION     
            "The number of ingress attempts blocked on this CRV."
    ::= { sonusGr303IgCrvCountEntry 8 }

sonusGr303CountIgCrvEgressCalls OBJECT-TYPE
    SYNTAX          Counter32
    MAX-ACCESS      read-only
    STATUS          current
    DESCRIPTION     
            "The number of egress attempts on this CRV."
    ::= { sonusGr303IgCrvCountEntry 9 }

sonusGr303CountIgCrvEgressCallsBlocked OBJECT-TYPE
    SYNTAX          Counter32
    MAX-ACCESS      read-only
    STATUS          current
    DESCRIPTION     
            "The number of egress attempts blocked on this CRV."
    ::= { sonusGr303IgCrvCountEntry 10 }

sonusGr303CountIgLapdTable OBJECT-TYPE
    SYNTAX          SEQUENCE OF SonusGr303CountIgLapdEntry
    MAX-ACCESS      not-accessible
    STATUS          current
    DESCRIPTION     
            "The Sonus GR303 Interface Group LAPD Counter table."
    ::= { sonusGr303MIBObjects 12 }

sonusGr303CountIgLapdEntry OBJECT-TYPE
    SYNTAX          SonusGr303CountIgLapdEntry
    MAX-ACCESS      not-accessible
    STATUS          current
    DESCRIPTION     
            "An entry in the Sonus Interface Group LAPD Counter table."
    INDEX           { sonusGr303CountIgLapdIgIndex, 
                      sonusGr303CountIgLapdLinkNum }
    ::= { sonusGr303CountIgLapdTable 1 }

SonusGr303CountIgLapdEntry ::=
    SEQUENCE {
        sonusGr303CountIgLapdIgIndex    Unsigned32,
        sonusGr303CountIgLapdLinkNum    Unsigned32,
        sonusGr303CountIgLapdTxPackets  Counter32,
        sonusGr303CountIgLapdRxPackets  Counter32,
        sonusGr303CountIgLapdT200Timeouts Counter32,
        sonusGr303CountIgLapdLinkEstSuccesses     Counter32,
        sonusGr303CountIgLapdLinkEstFailures    Counter32,
        sonusGr303CountIgLapdAckedPackets Counter32,
        sonusGr303CountIgLapdRcvdInvalidFrames      Counter32,
        sonusGr303CountIgLapdTimesOwnRcvrBusy     Counter32,
        sonusGr303CountIgLapdTimesPeerRcvrBusy      Counter32,
        sonusGr303CountIgLapdReturnStatus INTEGER
    }

sonusGr303CountIgLapdIgIndex OBJECT-TYPE
    SYNTAX          Unsigned32
    MAX-ACCESS      read-only
    STATUS          current
    DESCRIPTION     
            "The index of the GR303 Interface Group that this LAPD link belongs to."
    ::= { sonusGr303CountIgLapdEntry 1 }

sonusGr303CountIgLapdLinkNum OBJECT-TYPE
    SYNTAX          Unsigned32
    MAX-ACCESS      read-only
    STATUS          current
    DESCRIPTION     
            "The link number of this LAPD link.
             The meaning is as follows:
             1 - Primary,   TMC
             2 - Primary,   TMC, PPS
             3 - Primary,   EOC
             4 - Primary,   EOC, PPS
             5 - Secondary, TMC
             6 - Secondary, TMC, PPS
             7 - Secondary, EOC
             8 - Secondary, EOC, PPS"
    ::= { sonusGr303CountIgLapdEntry 2 }

sonusGr303CountIgLapdTxPackets OBJECT-TYPE
    SYNTAX          Counter32
    MAX-ACCESS      read-only
    STATUS          current
    DESCRIPTION     
            "The number of transmitted packets on this LAPD link."
    ::= { sonusGr303CountIgLapdEntry 3 }

sonusGr303CountIgLapdRxPackets OBJECT-TYPE
    SYNTAX          Counter32
    MAX-ACCESS      read-only
    STATUS          current
    DESCRIPTION     
            "The number of received packets on this LAPD link."
    ::= { sonusGr303CountIgLapdEntry 4 }

sonusGr303CountIgLapdT200Timeouts OBJECT-TYPE
    SYNTAX          Counter32
    MAX-ACCESS      read-only
    STATUS          current
    DESCRIPTION     
            "The number of T200 timeouts on this LAPD link."
    ::= { sonusGr303CountIgLapdEntry 5 }

sonusGr303CountIgLapdLinkEstSuccesses OBJECT-TYPE
    SYNTAX          Counter32
    MAX-ACCESS      read-only
    STATUS          current
    DESCRIPTION     
            "The number of link establishment successes on this LAPD link."
    ::= { sonusGr303CountIgLapdEntry 6 }

sonusGr303CountIgLapdLinkEstFailures OBJECT-TYPE
    SYNTAX          Counter32
    MAX-ACCESS      read-only
    STATUS          current
    DESCRIPTION     
            "The number of link establishment failures on this LAPD link."
    ::= { sonusGr303CountIgLapdEntry 7 }

sonusGr303CountIgLapdAckedPackets OBJECT-TYPE
    SYNTAX          Counter32
    MAX-ACCESS      read-only
    STATUS          current
    DESCRIPTION     
            "The number of acknowledged packets on this LAPD link."
    ::= { sonusGr303CountIgLapdEntry 8 }

sonusGr303CountIgLapdRcvdInvalidFrames OBJECT-TYPE
    SYNTAX          Counter32
    MAX-ACCESS      read-only
    STATUS          current
    DESCRIPTION     
            "The number of invalid frames received on this LAPD link."
    ::= { sonusGr303CountIgLapdEntry 9 }

sonusGr303CountIgLapdTimesOwnRcvrBusy OBJECT-TYPE
    SYNTAX          Counter32
    MAX-ACCESS      read-only
    STATUS          current
    DESCRIPTION     
            "The number of times own receiver became busy on this LAPD link."
    ::= { sonusGr303CountIgLapdEntry 10 }

sonusGr303CountIgLapdTimesPeerRcvrBusy OBJECT-TYPE
    SYNTAX          Counter32
    MAX-ACCESS      read-only
    STATUS          current
    DESCRIPTION     
            "The number of times peer receiver became busy on this LAPD link."
    ::= { sonusGr303CountIgLapdEntry 11 }

sonusGr303CountIgLapdReturnStatus OBJECT-TYPE
    SYNTAX          INTEGER { valid(1), notvalid(2) }
    MAX-ACCESS      read-only
    STATUS          current
    DESCRIPTION     
            "The validity of the LAPD counters.
             If not valid, ignore the numbers."
    ::= { sonusGr303CountIgLapdEntry 12 }

sonusGr303CountIgHdlcTable OBJECT-TYPE
    SYNTAX          SEQUENCE OF SonusGr303CountIgHdlcEntry
    MAX-ACCESS      not-accessible
    STATUS          current
    DESCRIPTION     
            "The Sonus GR303 Interface Group HDLC Counter table."
    ::= { sonusGr303MIBObjects 13 }

sonusGr303CountIgHdlcEntry OBJECT-TYPE
    SYNTAX          SonusGr303CountIgHdlcEntry
    MAX-ACCESS      not-accessible
    STATUS          current
    DESCRIPTION     
            "An entry in the Sonus Interface Group HDLC Counter table."
    INDEX           { sonusGr303CountIgHdlcIgIndex }
    ::= { sonusGr303CountIgHdlcTable 1 }

SonusGr303CountIgHdlcEntry ::=
    SEQUENCE {
        sonusGr303CountIgHdlcIgIndex    Unsigned32,
        sonusGr303CountIgHdlcEocPriChanTxFrames       Counter32,
        sonusGr303CountIgHdlcEocPriChanTxOctets       Counter32,
        sonusGr303CountIgHdlcEocPriChanTxErrors       Counter32,
        sonusGr303CountIgHdlcEocPriChanRxFrames       Counter32,
        sonusGr303CountIgHdlcEocPriChanRxOctets       Counter32,
        sonusGr303CountIgHdlcEocPriChanRxErrors       Counter32,
        sonusGr303CountIgHdlcEocSecChanTxFrames       Counter32,
        sonusGr303CountIgHdlcEocSecChanTxOctets       Counter32,
        sonusGr303CountIgHdlcEocSecChanTxErrors       Counter32,
        sonusGr303CountIgHdlcEocSecChanRxFrames       Counter32,
        sonusGr303CountIgHdlcEocSecChanRxOctets       Counter32,
        sonusGr303CountIgHdlcEocSecChanRxErrors       Counter32,
        sonusGr303CountIgHdlcTmcPriChanTxFrames       Counter32,
        sonusGr303CountIgHdlcTmcPriChanTxOctets       Counter32,
        sonusGr303CountIgHdlcTmcPriChanTxErrors       Counter32,
        sonusGr303CountIgHdlcTmcPriChanRxFrames       Counter32,
        sonusGr303CountIgHdlcTmcPriChanRxOctets       Counter32,
        sonusGr303CountIgHdlcTmcPriChanRxErrors       Counter32,
        sonusGr303CountIgHdlcTmcSecChanTxFrames       Counter32,
        sonusGr303CountIgHdlcTmcSecChanTxOctets       Counter32,
        sonusGr303CountIgHdlcTmcSecChanTxErrors       Counter32,
        sonusGr303CountIgHdlcTmcSecChanRxFrames       Counter32,
        sonusGr303CountIgHdlcTmcSecChanRxOctets       Counter32,
        sonusGr303CountIgHdlcTmcSecChanRxErrors       Counter32,
        sonusGr303CountIgHdlcEocPriStatus INTEGER,
        sonusGr303CountIgHdlcEocSecStatus INTEGER,
        sonusGr303CountIgHdlcTmcPriStatus INTEGER,
        sonusGr303CountIgHdlcTmcSecStatus INTEGER
    }

sonusGr303CountIgHdlcIgIndex OBJECT-TYPE
    SYNTAX          Unsigned32
    MAX-ACCESS      read-only
    STATUS          current
    DESCRIPTION     
            "The index of the GR303 Interface Group that the HDLC channels belong to."
    ::= { sonusGr303CountIgHdlcEntry 1 }

sonusGr303CountIgHdlcEocPriChanTxFrames OBJECT-TYPE
    SYNTAX          Counter32
    MAX-ACCESS      read-only
    STATUS          current
    DESCRIPTION     
            "The number of transmitted frames on the primary EOC path."
    ::= { sonusGr303CountIgHdlcEntry 2 }

sonusGr303CountIgHdlcEocPriChanTxOctets OBJECT-TYPE
    SYNTAX          Counter32
    MAX-ACCESS      read-only
    STATUS          current
    DESCRIPTION     
            "The number of transmitted octets on the primary EOC path."
    ::= { sonusGr303CountIgHdlcEntry 3 }

sonusGr303CountIgHdlcEocPriChanTxErrors OBJECT-TYPE
    SYNTAX          Counter32
    MAX-ACCESS      read-only
    STATUS          current
    DESCRIPTION     
            "The number of transmission errors on the primary EOC path."
    ::= { sonusGr303CountIgHdlcEntry 4 }

sonusGr303CountIgHdlcEocPriChanRxFrames OBJECT-TYPE
    SYNTAX          Counter32
    MAX-ACCESS      read-only
    STATUS          current
    DESCRIPTION     
            "The number of frames received on the primary EOC path."
    ::= { sonusGr303CountIgHdlcEntry 5 }

sonusGr303CountIgHdlcEocPriChanRxOctets OBJECT-TYPE
    SYNTAX          Counter32
    MAX-ACCESS      read-only
    STATUS          current
    DESCRIPTION     
            "The number of octets received on the primary EOC path."
    ::= { sonusGr303CountIgHdlcEntry 6 }

sonusGr303CountIgHdlcEocPriChanRxErrors OBJECT-TYPE
    SYNTAX          Counter32
    MAX-ACCESS      read-only
    STATUS          current
    DESCRIPTION     
            "The number of error frames received on the primary EOC path."
    ::= { sonusGr303CountIgHdlcEntry 7 }

sonusGr303CountIgHdlcEocSecChanTxFrames OBJECT-TYPE
    SYNTAX          Counter32
    MAX-ACCESS      read-only
    STATUS          current
    DESCRIPTION     
            "The number of transmitted frames on the secondary EOC path."
    ::= { sonusGr303CountIgHdlcEntry 8 }

sonusGr303CountIgHdlcEocSecChanTxOctets OBJECT-TYPE
    SYNTAX          Counter32
    MAX-ACCESS      read-only
    STATUS          current
    DESCRIPTION     
            "The number of transmitted octets on the secondary EOC path."
    ::= { sonusGr303CountIgHdlcEntry 9 }

sonusGr303CountIgHdlcEocSecChanTxErrors OBJECT-TYPE
    SYNTAX          Counter32
    MAX-ACCESS      read-only
    STATUS          current
    DESCRIPTION     
            "The number of transmission errors on the secondary EOC path."
    ::= { sonusGr303CountIgHdlcEntry 10 }

sonusGr303CountIgHdlcEocSecChanRxFrames OBJECT-TYPE
    SYNTAX          Counter32
    MAX-ACCESS      read-only
    STATUS          current
    DESCRIPTION     
            "The number of frames received on the secondary EOC path."
    ::= { sonusGr303CountIgHdlcEntry 11 }

sonusGr303CountIgHdlcEocSecChanRxOctets OBJECT-TYPE
    SYNTAX          Counter32
    MAX-ACCESS      read-only
    STATUS          current
    DESCRIPTION     
            "The number of octets received on the secondary EOC path."
    ::= { sonusGr303CountIgHdlcEntry 12 }

sonusGr303CountIgHdlcEocSecChanRxErrors OBJECT-TYPE
    SYNTAX          Counter32
    MAX-ACCESS      read-only
    STATUS          current
    DESCRIPTION     
            "The number of error frames received on the secondary EOC path."
    ::= { sonusGr303CountIgHdlcEntry 13 }

sonusGr303CountIgHdlcTmcPriChanTxFrames OBJECT-TYPE
    SYNTAX          Counter32
    MAX-ACCESS      read-only
    STATUS          current
    DESCRIPTION     
            "The number of transmitted frames on the primary TMC path."
    ::= { sonusGr303CountIgHdlcEntry 14 }

sonusGr303CountIgHdlcTmcPriChanTxOctets OBJECT-TYPE
    SYNTAX          Counter32
    MAX-ACCESS      read-only
    STATUS          current
    DESCRIPTION     
            "The number of transmitted octets on the primary TMC path."
    ::= { sonusGr303CountIgHdlcEntry 15 }

sonusGr303CountIgHdlcTmcPriChanTxErrors OBJECT-TYPE
    SYNTAX          Counter32
    MAX-ACCESS      read-only
    STATUS          current
    DESCRIPTION     
            "The number of transmission errors on the primary TMC path."
    ::= { sonusGr303CountIgHdlcEntry 16 }

sonusGr303CountIgHdlcTmcPriChanRxFrames OBJECT-TYPE
    SYNTAX          Counter32
    MAX-ACCESS      read-only
    STATUS          current
    DESCRIPTION     
            "The number of frames received on the primary TMC path."
    ::= { sonusGr303CountIgHdlcEntry 17 }

sonusGr303CountIgHdlcTmcPriChanRxOctets OBJECT-TYPE
    SYNTAX          Counter32
    MAX-ACCESS      read-only
    STATUS          current
    DESCRIPTION     
            "The number of octets received on the primary TMC path."
    ::= { sonusGr303CountIgHdlcEntry 18 }

sonusGr303CountIgHdlcTmcPriChanRxErrors OBJECT-TYPE
    SYNTAX          Counter32
    MAX-ACCESS      read-only
    STATUS          current
    DESCRIPTION     
            "The number of error frames received on the primary TMC path."
    ::= { sonusGr303CountIgHdlcEntry 19 }

sonusGr303CountIgHdlcTmcSecChanTxFrames OBJECT-TYPE
    SYNTAX          Counter32
    MAX-ACCESS      read-only
    STATUS          current
    DESCRIPTION     
            "The number of transmitted frames on the secondary TMC path."
    ::= { sonusGr303CountIgHdlcEntry 20 }

sonusGr303CountIgHdlcTmcSecChanTxOctets OBJECT-TYPE
    SYNTAX          Counter32
    MAX-ACCESS      read-only
    STATUS          current
    DESCRIPTION     
            "The number of transmitted octets on the secondary TMC path."
    ::= { sonusGr303CountIgHdlcEntry 21 }

sonusGr303CountIgHdlcTmcSecChanTxErrors OBJECT-TYPE
    SYNTAX          Counter32
    MAX-ACCESS      read-only
    STATUS          current
    DESCRIPTION     
            "The number of transmission errors on the secondary TMC path."
    ::= { sonusGr303CountIgHdlcEntry 22 }

sonusGr303CountIgHdlcTmcSecChanRxFrames OBJECT-TYPE
    SYNTAX          Counter32
    MAX-ACCESS      read-only
    STATUS          current
    DESCRIPTION     
            "The number of frames received on the secondary TMC path."
    ::= { sonusGr303CountIgHdlcEntry 23 }

sonusGr303CountIgHdlcTmcSecChanRxOctets OBJECT-TYPE
    SYNTAX          Counter32
    MAX-ACCESS      read-only
    STATUS          current
    DESCRIPTION     
            "The number of octets received on the secondary TMC path."
    ::= { sonusGr303CountIgHdlcEntry 24 }

sonusGr303CountIgHdlcTmcSecChanRxErrors OBJECT-TYPE
    SYNTAX          Counter32
    MAX-ACCESS      read-only
    STATUS          current
    DESCRIPTION     
            "The number of error frames received on the secondary TMC path."
    ::= { sonusGr303CountIgHdlcEntry 25 }

sonusGr303CountIgHdlcEocPriStatus OBJECT-TYPE
    SYNTAX          INTEGER { valid(1), notConfigured(2), 
                        outOfService(3), serverInactive(4), 
                        channelUnusable(5), inaccessible(6), 
                        mgcNotConnected(7) }
    MAX-ACCESS      read-only
    STATUS          current
    DESCRIPTION     
            "The status of the HDLC counters for the primary EOC path.
             If the counters are invalid, the reason may be:
             	- the path is not configured for the Interface Group
             	- some element is administered to be out of service
             	- the server hosting the port is inactive
             	- the DS0 channel presents an unusable signal
             	- the HDLC resouce is inaccessible"
    ::= { sonusGr303CountIgHdlcEntry 26 }

sonusGr303CountIgHdlcEocSecStatus OBJECT-TYPE
    SYNTAX          INTEGER { valid(1), notConfigured(2), 
                        outOfService(3), serverInactive(4), 
                        channelUnusable(5), inaccessible(6), 
                        mgcNotConnected(7) }
    MAX-ACCESS      read-only
    STATUS          current
    DESCRIPTION     
            "The status of the HDLC counters for the secondary EOC path.
             If the counters are invalid, the reason may be:
             	- the path is not configured for the Interface Group
             	- some element is administered to be out of service
             	- the server hosting the port is inactive
             	- the DS0 channel presents an unusable signal
             	- the HDLC resouce is inaccessible"
    ::= { sonusGr303CountIgHdlcEntry 27 }

sonusGr303CountIgHdlcTmcPriStatus OBJECT-TYPE
    SYNTAX          INTEGER { valid(1), notConfigured(2), 
                        outOfService(3), serverInactive(4), 
                        channelUnusable(5), inaccessible(6), 
                        mgcNotConnected(7) }
    MAX-ACCESS      read-only
    STATUS          current
    DESCRIPTION     
            "The status of the HDLC counters for the primary TMC path.
             If the counters are invalid, the reason may be:
             	- the path is not configured for the Interface Group
             	- some element is administered to be out of service
             	- the server hosting the port is inactive
             	- the DS0 channel presents an unusable signal
             	- the HDLC resouce is inaccessible"
    ::= { sonusGr303CountIgHdlcEntry 28 }

sonusGr303CountIgHdlcTmcSecStatus OBJECT-TYPE
    SYNTAX          INTEGER { valid(1), notConfigured(2), 
                        outOfService(3), serverInactive(4), 
                        channelUnusable(5), inaccessible(6), 
                        mgcNotConnected(7) }
    MAX-ACCESS      read-only
    STATUS          current
    DESCRIPTION     
            "The status of the HDLC counters for the secondary TMC path.
             If the counters are invalid, the reason may be:
             	- the path is not configured for the Interface Group
             	- some element is administered to be out of service
             	- the server hosting the port is inactive
             	- the DS0 channel presents an unusable signal
             	- the HDLC resouce is inaccessible"
    ::= { sonusGr303CountIgHdlcEntry 29 }

sonusGr303IgCrvStatusTable OBJECT-TYPE
    SYNTAX          SEQUENCE OF SonusGr303IgCrvStatusEntry
    MAX-ACCESS      not-accessible
    STATUS          current
    DESCRIPTION     
            "This table presents the GR303 Interface Group CRV status."
    ::= { sonusGr303MIBObjects 14 }

sonusGr303IgCrvStatusEntry OBJECT-TYPE
    SYNTAX          SonusGr303IgCrvStatusEntry
    MAX-ACCESS      not-accessible
    STATUS          current
    DESCRIPTION     
            "This entry presents the status of a GR303 Interface Group CRV."
    INDEX           { sonusGr303StatIgCrvIgIndex, 
                      sonusGr303StatIgCrvIndex }
    ::= { sonusGr303IgCrvStatusTable 1 }

SonusGr303IgCrvStatusEntry ::=
    SEQUENCE {
        sonusGr303StatIgCrvIgIndex      Unsigned32,
        sonusGr303StatIgCrvIndex        Unsigned32,
        sonusGr303StatIgCrvShoweringLine SonusBoolean,
        sonusGr303StatIgCrvHookState    INTEGER,
        sonusGr303StatIgCrvLineState    INTEGER,
        sonusGr303StatIgCrvDirection    INTEGER,
        sonusGr303StatIgCrvGcid         Unsigned32,
        sonusGr303StatIgCrvDs1Num       Unsigned32,
        sonusGr303StatIgCrvDs0Num       Unsigned32,
        sonusGr303StatIgCrvLastCauseCode4Crv    Unsigned32,
        sonusGr303StatIgCrvEocPriServiceState     INTEGER,
        sonusGr303StatIgCrvEocSecServiceState     BITS,
        sonusGr303StatIgCrvEocLineCircuitAddress        DisplayString,
        sonusGr303StatIgCrvDuration     Unsigned32,
        sonusGr303StatIgCrvEocReturnStatus  INTEGER
    }

sonusGr303StatIgCrvIgIndex OBJECT-TYPE
    SYNTAX          Unsigned32
    MAX-ACCESS      not-accessible
    STATUS          current
    DESCRIPTION     
            "The GR303 Interface Group index that this CRV belongs to."
    ::= { sonusGr303IgCrvStatusEntry 1 }

sonusGr303StatIgCrvIndex OBJECT-TYPE
    SYNTAX          Unsigned32
    MAX-ACCESS      read-only
    STATUS          current
    DESCRIPTION     
            "The Call Reference Value that designates this subscriber."
    ::= { sonusGr303IgCrvStatusEntry 2 }

sonusGr303StatIgCrvShoweringLine OBJECT-TYPE
    SYNTAX          SonusBoolean
    MAX-ACCESS      read-only
    STATUS          current
    DESCRIPTION     
            "Is this CRV denied service because it is marked as a showering line?"
    ::= { sonusGr303IgCrvStatusEntry 3 }

sonusGr303StatIgCrvHookState OBJECT-TYPE
    SYNTAX          INTEGER { onhook(1), offhook(2) }
    MAX-ACCESS      read-only
    STATUS          current
    DESCRIPTION     
            "The switch-hook state of the analog phone for this CRV.
             A ringing line is prematurely reported as off-hook."
    ::= { sonusGr303IgCrvStatusEntry 4 }

sonusGr303StatIgCrvLineState OBJECT-TYPE
    SYNTAX          INTEGER { idle(1), connecting(2), connected(3), 
                        releasing(4) }
    MAX-ACCESS      read-only
    STATUS          current
    DESCRIPTION     
            "The state of a DS0 channel assignment for this CRV."
    ::= { sonusGr303IgCrvStatusEntry 5 }

sonusGr303StatIgCrvDirection OBJECT-TYPE
    SYNTAX          INTEGER { egress(1), ingress(2) }
    MAX-ACCESS      read-only
    STATUS          current
    DESCRIPTION     
            "The reason for a DS0 channel assignment to this CRV."
    ::= { sonusGr303IgCrvStatusEntry 6 }

sonusGr303StatIgCrvGcid OBJECT-TYPE
    SYNTAX          Unsigned32
    MAX-ACCESS      read-only
    STATUS          current
    DESCRIPTION     
            "The call identifier (GCID or null) that contains this CRV."
    ::= { sonusGr303IgCrvStatusEntry 7 }

sonusGr303StatIgCrvDs1Num OBJECT-TYPE
    SYNTAX          Unsigned32
    MAX-ACCESS      read-only
    STATUS          current
    DESCRIPTION     
            "The logical DS1 number to which this CRV is assigned."
    ::= { sonusGr303IgCrvStatusEntry 8 }

sonusGr303StatIgCrvDs0Num OBJECT-TYPE
    SYNTAX          Unsigned32
    MAX-ACCESS      read-only
    STATUS          current
    DESCRIPTION     
            "The DS0 channel to which this CRV is assigned."
    ::= { sonusGr303IgCrvStatusEntry 9 }

sonusGr303StatIgCrvLastCauseCode4Crv OBJECT-TYPE
    SYNTAX          Unsigned32
    MAX-ACCESS      read-only
    STATUS          current
    DESCRIPTION     
            "The cause code of the last connection cleared on this CRV."
    ::= { sonusGr303IgCrvStatusEntry 10 }

sonusGr303StatIgCrvEocPriServiceState OBJECT-TYPE
    SYNTAX          INTEGER { is(1), oos(2) }
    MAX-ACCESS      read-only
    STATUS          current
    DESCRIPTION     
            "The primary service state of this CRV as reported by the RDT."
    ::= { sonusGr303IgCrvStatusEntry 11 }

sonusGr303StatIgCrvEocSecServiceState OBJECT-TYPE
    SYNTAX          BITS { ts(0), mt(1), ma(2), anr(3), ueq(4), fef(5), 
                        busy(6), lpbk(7), mea(8), mon(9), pwr(10), 
                        sea(11), act(12), ccsf(13), comb(14), dgn(15), 
                        dsbld(16), erranal(17), ex(18), faf(19), 
                        fepro(20), flt(21), frcd(22), hd(23), hw(24), 
                        inhip(25), lkdo(26), lock(27), mtce(28), 
                        mtcelim(29), nm(30), pctf(31), pri(32), 
                        prtcl(33), sec(34), stby(35), termf(36), tmt(37), 
                        trd(38), tstf(39), sof(40), swtch(41) }
    MAX-ACCESS      read-only
    STATUS          current
    DESCRIPTION     
            "The secondary service state of this CRV as reported by the RDT."
    ::= { sonusGr303IgCrvStatusEntry 12 }

sonusGr303StatIgCrvEocLineCircuitAddress OBJECT-TYPE
    SYNTAX          DisplayString (SIZE(0..31))
    MAX-ACCESS      read-only
    STATUS          current
    DESCRIPTION     
            "The line circuit address assigned to this CRV as reported by the RDT."
    ::= { sonusGr303IgCrvStatusEntry 13 }

sonusGr303StatIgCrvDuration OBJECT-TYPE
    SYNTAX          Unsigned32
    MAX-ACCESS      read-only
    STATUS          current
    DESCRIPTION     
            "The duration (seconds) of the current Ds0 channel assignment for this CRV
             or the duration of its permanent signaling or showering line condition."
    ::= { sonusGr303IgCrvStatusEntry 14 }

sonusGr303StatIgCrvEocReturnStatus OBJECT-TYPE
    SYNTAX          INTEGER { valid(1), notOperational(2), 
                        conflictingOperation(3), notSupplied(4), 
                        timedOut(5) }
    MAX-ACCESS      read-only
    STATUS          current
    DESCRIPTION     
            "The validity of the RDT service states and line circuit address.
             If not valid, ignore the information."
    ::= { sonusGr303IgCrvStatusEntry 15 }

sonusGr303IgRdtAlarmCountTable OBJECT-TYPE
    SYNTAX          SEQUENCE OF SonusGr303IgRdtAlarmCountEntry
    MAX-ACCESS      not-accessible
    STATUS          current
    DESCRIPTION     
            "This table presents the RDT alarm counters reported to a GR303 Interface Group."
    ::= { sonusGr303MIBObjects 15 }

sonusGr303IgRdtAlarmCountEntry OBJECT-TYPE
    SYNTAX          SonusGr303IgRdtAlarmCountEntry
    MAX-ACCESS      not-accessible
    STATUS          current
    DESCRIPTION     
            "This entry presents the RDT alarm counters reported to a GR303 Interface Group."
    INDEX           { sonusGr303IgRdtAlarmIgIndex }
    ::= { sonusGr303IgRdtAlarmCountTable 1 }

SonusGr303IgRdtAlarmCountEntry ::=
    SEQUENCE {
        sonusGr303IgRdtAlarmIgIndex     Unsigned32,
        sonusGr303IgRdtAlarmIndeterminateIndeterminate              Unsigned32,
        sonusGr303IgRdtAlarmIndeterminateWarning        Unsigned32,
        sonusGr303IgRdtAlarmIndeterminateMinor      Unsigned32,
        sonusGr303IgRdtAlarmIndeterminateMajor      Unsigned32,
        sonusGr303IgRdtAlarmIndeterminateCritical         Unsigned32,
        sonusGr303IgRdtAlarmEquipmentIndeterminate          Unsigned32,
        sonusGr303IgRdtAlarmEquipmentWarning    Unsigned32,
        sonusGr303IgRdtAlarmEquipmentMinor  Unsigned32,
        sonusGr303IgRdtAlarmEquipmentMajor  Unsigned32,
        sonusGr303IgRdtAlarmEquipmentCritical     Unsigned32,
        sonusGr303IgRdtAlarmTransmissionIndeterminate             Unsigned32,
        sonusGr303IgRdtAlarmTransmissionWarning       Unsigned32,
        sonusGr303IgRdtAlarmTransmissionMinor     Unsigned32,
        sonusGr303IgRdtAlarmTransmissionMajor     Unsigned32,
        sonusGr303IgRdtAlarmTransmissionCritical        Unsigned32,
        sonusGr303IgRdtAlarmEnvironmentalIndeterminate              Unsigned32,
        sonusGr303IgRdtAlarmEnvironmentalWarning        Unsigned32,
        sonusGr303IgRdtAlarmEnvironmentalMinor      Unsigned32,
        sonusGr303IgRdtAlarmEnvironmentalMajor      Unsigned32,
        sonusGr303IgRdtAlarmEnvironmentalCritical         Unsigned32,
        sonusGr303IgRdtAlarmSoftwareIndeterminate         Unsigned32,
        sonusGr303IgRdtAlarmSoftwareWarning   Unsigned32,
        sonusGr303IgRdtAlarmSoftwareMinor Unsigned32,
        sonusGr303IgRdtAlarmSoftwareMajor Unsigned32,
        sonusGr303IgRdtAlarmSoftwareCritical    Unsigned32,
        sonusGr303IgRdtAlarmServiceIndeterminate        Unsigned32,
        sonusGr303IgRdtAlarmServiceWarning  Unsigned32,
        sonusGr303IgRdtAlarmServiceMinor Unsigned32,
        sonusGr303IgRdtAlarmServiceMajor Unsigned32,
        sonusGr303IgRdtAlarmServiceCritical   Unsigned32,
        sonusGr303IgRdtAlarmThresholdAlertIndeterminate               Unsigned32,
        sonusGr303IgRdtAlarmThresholdAlertWarning         Unsigned32,
        sonusGr303IgRdtAlarmThresholdAlertMinor       Unsigned32,
        sonusGr303IgRdtAlarmThresholdAlertMajor       Unsigned32,
        sonusGr303IgRdtAlarmThresholdAlertCritical          Unsigned32,
        sonusGr303IgRdtAlarmScheduledManagementOperationsIndeterminate                              Unsigned32,
        sonusGr303IgRdtAlarmScheduledManagementOperationsWarning                        Unsigned32,
        sonusGr303IgRdtAlarmScheduledManagementOperationsMinor                      Unsigned32,
        sonusGr303IgRdtAlarmScheduledManagementOperationsMajor                      Unsigned32,
        sonusGr303IgRdtAlarmScheduledManagementOperationsCritical                         Unsigned32,
        sonusGr303IgRdtAlarmReturnStatus INTEGER
    }

sonusGr303IgRdtAlarmIgIndex OBJECT-TYPE
    SYNTAX          Unsigned32
    MAX-ACCESS      not-accessible
    STATUS          current
    DESCRIPTION     
            "The GR303 Interface Group index for this RDT alarm counter table."
    ::= { sonusGr303IgRdtAlarmCountEntry 1 }

sonusGr303IgRdtAlarmIndeterminateIndeterminate OBJECT-TYPE
    SYNTAX          Unsigned32
    MAX-ACCESS      read-only
    STATUS          current
    DESCRIPTION     
            "The alarm count for the Indeterminate category and Indeterminate
             severity as reported from the RDT associated with this GR303
             interface group."
    ::= { sonusGr303IgRdtAlarmCountEntry 3 }

sonusGr303IgRdtAlarmIndeterminateWarning OBJECT-TYPE
    SYNTAX          Unsigned32
    MAX-ACCESS      read-only
    STATUS          current
    DESCRIPTION     
            "The alarm count for the Indeterminate category and Warning
             severity as reported from the RDT associated with this GR303
             interface group."
    ::= { sonusGr303IgRdtAlarmCountEntry 4 }

sonusGr303IgRdtAlarmIndeterminateMinor OBJECT-TYPE
    SYNTAX          Unsigned32
    MAX-ACCESS      read-only
    STATUS          current
    DESCRIPTION     
            "The alarm count for the Indeterminate category and Minor
             severity as reported from the RDT associated with this GR303
             interface group."
    ::= { sonusGr303IgRdtAlarmCountEntry 5 }

sonusGr303IgRdtAlarmIndeterminateMajor OBJECT-TYPE
    SYNTAX          Unsigned32
    MAX-ACCESS      read-only
    STATUS          current
    DESCRIPTION     
            "The alarm count for the Indeterminate category and Major
             severity as reported from the RDT associated with this GR303
             interface group."
    ::= { sonusGr303IgRdtAlarmCountEntry 6 }

sonusGr303IgRdtAlarmIndeterminateCritical OBJECT-TYPE
    SYNTAX          Unsigned32
    MAX-ACCESS      read-only
    STATUS          current
    DESCRIPTION     
            "The alarm count for the Indeterminate category and Critical
             severity as reported from the RDT associated with this GR303
             interface group."
    ::= { sonusGr303IgRdtAlarmCountEntry 7 }

sonusGr303IgRdtAlarmEquipmentIndeterminate OBJECT-TYPE
    SYNTAX          Unsigned32
    MAX-ACCESS      read-only
    STATUS          current
    DESCRIPTION     
            "The alarm count for the Equipment category and Indeterminate
             severity as reported from the RDT associated with this GR303
             interface group."
    ::= { sonusGr303IgRdtAlarmCountEntry 8 }

sonusGr303IgRdtAlarmEquipmentWarning OBJECT-TYPE
    SYNTAX          Unsigned32
    MAX-ACCESS      read-only
    STATUS          current
    DESCRIPTION     
            "The alarm count for the Equipment category and Warning
             severity as reported from the RDT associated with this GR303
             interface group."
    ::= { sonusGr303IgRdtAlarmCountEntry 9 }

sonusGr303IgRdtAlarmEquipmentMinor OBJECT-TYPE
    SYNTAX          Unsigned32
    MAX-ACCESS      read-only
    STATUS          current
    DESCRIPTION     
            "The alarm count for the Eqipment category and Minor
             severity as reported from the RDT associated with this GR303
             interface group."
    ::= { sonusGr303IgRdtAlarmCountEntry 10 }

sonusGr303IgRdtAlarmEquipmentMajor OBJECT-TYPE
    SYNTAX          Unsigned32
    MAX-ACCESS      read-only
    STATUS          current
    DESCRIPTION     
            "The alarm count for the Equipment category and Major
             severity as reported from the RDT associated with this GR303
             interface group."
    ::= { sonusGr303IgRdtAlarmCountEntry 11 }

sonusGr303IgRdtAlarmEquipmentCritical OBJECT-TYPE
    SYNTAX          Unsigned32
    MAX-ACCESS      read-only
    STATUS          current
    DESCRIPTION     
            "The alarm count for the Equipment category and Critical
             severity as reported from the RDT associated with this GR303
             interface group."
    ::= { sonusGr303IgRdtAlarmCountEntry 12 }

sonusGr303IgRdtAlarmTransmissionIndeterminate OBJECT-TYPE
    SYNTAX          Unsigned32
    MAX-ACCESS      read-only
    STATUS          current
    DESCRIPTION     
            "The alarm count for the Transmission category and Indeterminate
             severity as reported from the RDT associated with this GR303
             interface group."
    ::= { sonusGr303IgRdtAlarmCountEntry 13 }

sonusGr303IgRdtAlarmTransmissionWarning OBJECT-TYPE
    SYNTAX          Unsigned32
    MAX-ACCESS      read-only
    STATUS          current
    DESCRIPTION     
            "The alarm count for the Transmission category and Warning
             severity as reported from the RDT associated with this GR303
             interface group."
    ::= { sonusGr303IgRdtAlarmCountEntry 14 }

sonusGr303IgRdtAlarmTransmissionMinor OBJECT-TYPE
    SYNTAX          Unsigned32
    MAX-ACCESS      read-only
    STATUS          current
    DESCRIPTION     
            "The alarm count for the Transmission category and Minor
             severity as reported from the RDT associated with this GR303
             interface group."
    ::= { sonusGr303IgRdtAlarmCountEntry 15 }

sonusGr303IgRdtAlarmTransmissionMajor OBJECT-TYPE
    SYNTAX          Unsigned32
    MAX-ACCESS      read-only
    STATUS          current
    DESCRIPTION     
            "The alarm count for the Transmission category and Major
             severity as reported from the RDT associated with this GR303
             interface group."
    ::= { sonusGr303IgRdtAlarmCountEntry 16 }

sonusGr303IgRdtAlarmTransmissionCritical OBJECT-TYPE
    SYNTAX          Unsigned32
    MAX-ACCESS      read-only
    STATUS          current
    DESCRIPTION     
            "The alarm count for the Transmission category and Critical
             severity as reported from the RDT associated with this GR303
             interface group."
    ::= { sonusGr303IgRdtAlarmCountEntry 17 }

sonusGr303IgRdtAlarmEnvironmentalIndeterminate OBJECT-TYPE
    SYNTAX          Unsigned32
    MAX-ACCESS      read-only
    STATUS          current
    DESCRIPTION     
            "The alarm count for the Environmental category and Indeterminate
             severity as reported from the RDT associated with this GR303
             interface group."
    ::= { sonusGr303IgRdtAlarmCountEntry 18 }

sonusGr303IgRdtAlarmEnvironmentalWarning OBJECT-TYPE
    SYNTAX          Unsigned32
    MAX-ACCESS      read-only
    STATUS          current
    DESCRIPTION     
            "The alarm count for the Environmental category and Warning
             severity as reported from the RDT associated with this GR303
             interface group."
    ::= { sonusGr303IgRdtAlarmCountEntry 19 }

sonusGr303IgRdtAlarmEnvironmentalMinor OBJECT-TYPE
    SYNTAX          Unsigned32
    MAX-ACCESS      read-only
    STATUS          current
    DESCRIPTION     
            "The alarm count for the Environmental category and Minor
             severity as reported from the RDT associated with this GR303
             interface group."
    ::= { sonusGr303IgRdtAlarmCountEntry 20 }

sonusGr303IgRdtAlarmEnvironmentalMajor OBJECT-TYPE
    SYNTAX          Unsigned32
    MAX-ACCESS      read-only
    STATUS          current
    DESCRIPTION     
            "The alarm count for the Environmental category and Major
             severity as reported from the RDT associated with this GR303
             interface group."
    ::= { sonusGr303IgRdtAlarmCountEntry 21 }

sonusGr303IgRdtAlarmEnvironmentalCritical OBJECT-TYPE
    SYNTAX          Unsigned32
    MAX-ACCESS      read-only
    STATUS          current
    DESCRIPTION     
            "The alarm count for the Environmental category and Critical
             severity as reported from the RDT associated with this GR303
             interface group."
    ::= { sonusGr303IgRdtAlarmCountEntry 22 }

sonusGr303IgRdtAlarmSoftwareIndeterminate OBJECT-TYPE
    SYNTAX          Unsigned32
    MAX-ACCESS      read-only
    STATUS          current
    DESCRIPTION     
            "The alarm count for the Software category and Indeterminate
             severity as reported from the RDT associated with this GR303
             interface group."
    ::= { sonusGr303IgRdtAlarmCountEntry 23 }

sonusGr303IgRdtAlarmSoftwareWarning OBJECT-TYPE
    SYNTAX          Unsigned32
    MAX-ACCESS      read-only
    STATUS          current
    DESCRIPTION     
            "The alarm count for the Software category and Warning
             severity as reported from the RDT associated with this GR303
             interface group."
    ::= { sonusGr303IgRdtAlarmCountEntry 24 }

sonusGr303IgRdtAlarmSoftwareMinor OBJECT-TYPE
    SYNTAX          Unsigned32
    MAX-ACCESS      read-only
    STATUS          current
    DESCRIPTION     
            "The alarm count for the Software category and Minor
             severity as reported from the RDT associated with this GR303
             interface group."
    ::= { sonusGr303IgRdtAlarmCountEntry 25 }

sonusGr303IgRdtAlarmSoftwareMajor OBJECT-TYPE
    SYNTAX          Unsigned32
    MAX-ACCESS      read-only
    STATUS          current
    DESCRIPTION     
            "The alarm count for the Software category and Major
             severity as reported from the RDT associated with this GR303
             interface group."
    ::= { sonusGr303IgRdtAlarmCountEntry 26 }

sonusGr303IgRdtAlarmSoftwareCritical OBJECT-TYPE
    SYNTAX          Unsigned32
    MAX-ACCESS      read-only
    STATUS          current
    DESCRIPTION     
            "The alarm count for the Software category and Critical
             severity as reported from the RDT associated with this GR303
             interface group."
    ::= { sonusGr303IgRdtAlarmCountEntry 27 }

sonusGr303IgRdtAlarmServiceIndeterminate OBJECT-TYPE
    SYNTAX          Unsigned32
    MAX-ACCESS      read-only
    STATUS          current
    DESCRIPTION     
            "The alarm count for the Service category and Indeterminate
             severity as reported from the RDT associated with this GR303
             interface group."
    ::= { sonusGr303IgRdtAlarmCountEntry 28 }

sonusGr303IgRdtAlarmServiceWarning OBJECT-TYPE
    SYNTAX          Unsigned32
    MAX-ACCESS      read-only
    STATUS          current
    DESCRIPTION     
            "The alarm count for the Service category and Warning
             severity as reported from the RDT associated with this GR303
             interface group."
    ::= { sonusGr303IgRdtAlarmCountEntry 29 }

sonusGr303IgRdtAlarmServiceMinor OBJECT-TYPE
    SYNTAX          Unsigned32
    MAX-ACCESS      read-only
    STATUS          current
    DESCRIPTION     
            "The alarm count for the Service category and Minor
             severity as reported from the RDT associated with this GR303
             interface group."
    ::= { sonusGr303IgRdtAlarmCountEntry 30 }

sonusGr303IgRdtAlarmServiceMajor OBJECT-TYPE
    SYNTAX          Unsigned32
    MAX-ACCESS      read-only
    STATUS          current
    DESCRIPTION     
            "The alarm count for the Service category and Major
             severity as reported from the RDT associated with this GR303
             interface group."
    ::= { sonusGr303IgRdtAlarmCountEntry 31 }

sonusGr303IgRdtAlarmServiceCritical OBJECT-TYPE
    SYNTAX          Unsigned32
    MAX-ACCESS      read-only
    STATUS          current
    DESCRIPTION     
            "The alarm count for the Service category and Critical
             severity as reported from the RDT associated with this GR303
             interface group."
    ::= { sonusGr303IgRdtAlarmCountEntry 32 }

sonusGr303IgRdtAlarmThresholdAlertIndeterminate OBJECT-TYPE
    SYNTAX          Unsigned32
    MAX-ACCESS      read-only
    STATUS          current
    DESCRIPTION     
            "The alarm count for the ThresholdAlert category and Indeterminate
             severity as reported from the RDT associated with this GR303
             interface group."
    ::= { sonusGr303IgRdtAlarmCountEntry 33 }

sonusGr303IgRdtAlarmThresholdAlertWarning OBJECT-TYPE
    SYNTAX          Unsigned32
    MAX-ACCESS      read-only
    STATUS          current
    DESCRIPTION     
            "The alarm count for the ThresholdAlert category and Warning
             severity as reported from the RDT associated with this GR303
             interface group."
    ::= { sonusGr303IgRdtAlarmCountEntry 34 }

sonusGr303IgRdtAlarmThresholdAlertMinor OBJECT-TYPE
    SYNTAX          Unsigned32
    MAX-ACCESS      read-only
    STATUS          current
    DESCRIPTION     
            "The alarm count for the ThresholdAlert category and Minor
             severity as reported from the RDT associated with this GR303
             interface group."
    ::= { sonusGr303IgRdtAlarmCountEntry 35 }

sonusGr303IgRdtAlarmThresholdAlertMajor OBJECT-TYPE
    SYNTAX          Unsigned32
    MAX-ACCESS      read-only
    STATUS          current
    DESCRIPTION     
            "The alarm count for the ThresholdAlert category and Major
             severity as reported from the RDT associated with this GR303
             interface group."
    ::= { sonusGr303IgRdtAlarmCountEntry 36 }

sonusGr303IgRdtAlarmThresholdAlertCritical OBJECT-TYPE
    SYNTAX          Unsigned32
    MAX-ACCESS      read-only
    STATUS          current
    DESCRIPTION     
            "The alarm count for the ThresholdAlert category and Critical
             severity as reported from the RDT associated with this GR303
             interface group."
    ::= { sonusGr303IgRdtAlarmCountEntry 37 }

sonusGr303IgRdtAlarmScheduledManagementOperationsIndeterminate OBJECT-TYPE
    SYNTAX          Unsigned32
    MAX-ACCESS      read-only
    STATUS          current
    DESCRIPTION     
            "The alarm count for the ScheduledManagementOperations category and Indeterminate
             severity as reported from the RDT associated with this GR303
             interface group."
    ::= { sonusGr303IgRdtAlarmCountEntry 38 }

sonusGr303IgRdtAlarmScheduledManagementOperationsWarning OBJECT-TYPE
    SYNTAX          Unsigned32
    MAX-ACCESS      read-only
    STATUS          current
    DESCRIPTION     
            "The alarm count for the ScheduledManagementOperations category and Warning
             severity as reported from the RDT associated with this GR303
             interface group."
    ::= { sonusGr303IgRdtAlarmCountEntry 39 }

sonusGr303IgRdtAlarmScheduledManagementOperationsMinor OBJECT-TYPE
    SYNTAX          Unsigned32
    MAX-ACCESS      read-only
    STATUS          current
    DESCRIPTION     
            "The alarm count for the ScheduledManagementOperations category and Minor
             severity as reported from the RDT associated with this GR303
             interface group."
    ::= { sonusGr303IgRdtAlarmCountEntry 40 }

sonusGr303IgRdtAlarmScheduledManagementOperationsMajor OBJECT-TYPE
    SYNTAX          Unsigned32
    MAX-ACCESS      read-only
    STATUS          current
    DESCRIPTION     
            "The alarm count for the ScheduledManagementOperations category and Major
             severity as reported from the RDT associated with this GR303
             interface group."
    ::= { sonusGr303IgRdtAlarmCountEntry 41 }

sonusGr303IgRdtAlarmScheduledManagementOperationsCritical OBJECT-TYPE
    SYNTAX          Unsigned32
    MAX-ACCESS      read-only
    STATUS          current
    DESCRIPTION     
            "The alarm count for the ScheduledManagementOperations category and Critical
             severity as reported from the RDT associated with this GR303
             interface group."
    ::= { sonusGr303IgRdtAlarmCountEntry 42 }

sonusGr303IgRdtAlarmReturnStatus OBJECT-TYPE
    SYNTAX          INTEGER { valid(1), notvalid(2) }
    MAX-ACCESS      read-only
    STATUS          current
    DESCRIPTION     
            "The validity of these alarm counts.
             If not valid, ignore the numbers."
    ::= { sonusGr303IgRdtAlarmCountEntry 43 }

sonusGr303NodeStatus OBJECT IDENTIFIER
    ::= { sonusGr303MIBObjects 16 }

sonusGr303NodeStatSubProvIntervalRemaining OBJECT-TYPE
    SYNTAX          Unsigned32 (0..65535)
    MAX-ACCESS      read-write
    STATUS          current
    DESCRIPTION     
            "This is the time remaining in the current Subscriber Provisioning 
             interval timer passed down by the PSX in the last polling operation"
    ::= { sonusGr303NodeStatus 1 }

sonusGr303NodeStatSubProvPsxPolls OBJECT-TYPE
    SYNTAX          Unsigned32 (0..4294967295)
    MAX-ACCESS      read-write
    STATUS          current
    DESCRIPTION     
            "Number of times the GSX has polled the PSX for Subscriber info"
    ::= { sonusGr303NodeStatus 2 }

sonusGr303NodeStatSubProvPsxPartialUpdates OBJECT-TYPE
    SYNTAX          Unsigned32 (0..4294967295)
    MAX-ACCESS      read-write
    STATUS          current
    DESCRIPTION     
            "Number of times the GSX has polled the PSX for partial subscriber info"
    ::= { sonusGr303NodeStatus 3 }

sonusGr303NodeStatSubProvPsxFullUpdates OBJECT-TYPE
    SYNTAX          Unsigned32 (0..4294967295)
    MAX-ACCESS      read-write
    STATUS          current
    DESCRIPTION     
            "Number of times the GSX has polled the PSX for all the data"
    ::= { sonusGr303NodeStatus 4 }

sonusGr303NodeStatSubProvPsxPollFailures OBJECT-TYPE
    SYNTAX          Unsigned32 (0..4294967295)
    MAX-ACCESS      read-write
    STATUS          current
    DESCRIPTION     
            "Number of times the GSX timed out waiting for a response to a poll message from the PSX"
    ::= { sonusGr303NodeStatus 5 }

sonusGr303NodeStatSubProvPsxPollRetries OBJECT-TYPE
    SYNTAX          Unsigned32 (0..4294967295)
    MAX-ACCESS      read-write
    STATUS          current
    DESCRIPTION     
            "Number of times the GSX retried sending a poll message to the PSX"
    ::= { sonusGr303NodeStatus 6 }

sonusGr303MIBNotifications OBJECT IDENTIFIER
    ::= { sonusGr303MIBObjects 50 }

sonusGr303MIBNotificationsPrefix OBJECT IDENTIFIER
    ::= { sonusGr303MIBNotifications 0 }

sonusGr303MIBNotificationsObjects OBJECT IDENTIFIER
    ::= { sonusGr303MIBNotifications 1 }

sonusGr303TerminationId OBJECT-TYPE
    SYNTAX          DisplayString (SIZE(1..46))
    MAX-ACCESS      read-only
    STATUS          current
    DESCRIPTION     
            "The unknown Gr303 termination ID."
    ::= { sonusGr303MIBNotificationsObjects 1 }

sonusGr303EocRdtAlarmCategory OBJECT-TYPE
    SYNTAX          INTEGER { indeterminate(0), equipment(1), 
                        transmission(2), environmental(3), software(4), 
                        service(5), thresholdAlert(6), 
                        scheduledManagementOperations(7) }
    MAX-ACCESS      read-only
    STATUS          current
    DESCRIPTION     
            "The EOC RDT alarm cateogry."
    ::= { sonusGr303MIBNotificationsObjects 2 }

sonusGr303EocRdtAlarmSeverity OBJECT-TYPE
    SYNTAX          INTEGER { cleared(0), indeterminate(1), warning(2), 
                        minor(3), major(4), critical(5) }
    MAX-ACCESS      read-only
    STATUS          current
    DESCRIPTION     
            "The EOC RDT alarm severity."
    ::= { sonusGr303MIBNotificationsObjects 3 }

sonusGr303MgcDownNotification NOTIFICATION-TYPE
    OBJECTS         { sonusEventDescription, sonusEventClass, 
                      sonusEventLevel, sonusSequenceId, sonusEventTime }
    STATUS          current
    DESCRIPTION     
            "This trap indicates that this node has lost communications with
             its Media Gateway Controller (MGC) and all attempts to regain
             communications have expired."
    ::= { sonusGr303MIBNotificationsPrefix 1 }

sonusGr303MgcUpNotification NOTIFICATION-TYPE
    OBJECTS         { sonusEventDescription, sonusEventClass, 
                      sonusEventLevel, sonusSequenceId, sonusEventTime }
    STATUS          current
    DESCRIPTION     
            "This trap indicates that this node has just regained
             communication with its Media Gateway Controller (MGC)."
    ::= { sonusGr303MIBNotificationsPrefix 2 }

sonusGr303ShoweringLineNotification NOTIFICATION-TYPE
    OBJECTS         { sonusGr303IgName, sonusGr303IgCrvIndex, 
                      sonusEventDescription, sonusEventClass, 
                      sonusEventLevel, sonusSequenceId, sonusEventTime }
    STATUS          current
    DESCRIPTION     
            "This trap indicates that a showering line condition has
             been detected on a GR303 Interface Group subscrivber CRV."
    ::= { sonusGr303MIBNotificationsPrefix 3 }

sonusGr303ShoweringLineClearedNotification NOTIFICATION-TYPE
    OBJECTS         { sonusGr303IgName, sonusGr303IgCrvIndex, 
                      sonusEventDescription, sonusEventClass, 
                      sonusEventLevel, sonusSequenceId, sonusEventTime }
    STATUS          current
    DESCRIPTION     
            "This trap indicates that a showering line condition has
             been cleared on a GR303 Interface Group subscriber CRV."
    ::= { sonusGr303MIBNotificationsPrefix 4 }

sonusGr303TmcDownNotification NOTIFICATION-TYPE
    OBJECTS         { sonusGr303IgName, sonusEventDescription, 
                      sonusEventClass, sonusEventLevel, sonusSequenceId, 
                      sonusEventTime }
    STATUS          current
    DESCRIPTION     
            "This trap indicates that this GR303 Interface Group lacks
             an active TMC path with an established LAPD payload link."
    ::= { sonusGr303MIBNotificationsPrefix 5 }

sonusGr303TmcUpNotification NOTIFICATION-TYPE
    OBJECTS         { sonusGr303IgName, sonusEventDescription, 
                      sonusEventClass, sonusEventLevel, sonusSequenceId, 
                      sonusEventTime }
    STATUS          current
    DESCRIPTION     
            "This trap indicates that a LAPD payload link is established
             on the active TMC path of this GR303 Interface Group."
    ::= { sonusGr303MIBNotificationsPrefix 6 }

sonusGr303UnknownTerminationIdNotification NOTIFICATION-TYPE
    OBJECTS         { sonusGr303TerminationId, sonusEventDescription, 
                      sonusEventClass, sonusEventLevel, sonusSequenceId, 
                      sonusEventTime }
    STATUS          current
    DESCRIPTION     
            "This trap indicates that an Unknown Termination ID cause code
             (430) for a termination id is received from Media Gateway
             Controller (MGC) in response to a H.248 message sent by this GSX."
    ::= { sonusGr303MIBNotificationsPrefix 7 }

sonusGr303UnknownTerminationIdClearedNotification NOTIFICATION-TYPE
    OBJECTS         { sonusGr303TerminationId, sonusEventDescription, 
                      sonusEventClass, sonusEventLevel, sonusSequenceId, 
                      sonusEventTime }
    STATUS          current
    DESCRIPTION     
            "This trap indicates that this Unknown Termination ID cause code
             (430) for a termination id is cleared."
    ::= { sonusGr303MIBNotificationsPrefix 8 }

sonusGr303EocRdtAlarmNotification NOTIFICATION-TYPE
    OBJECTS         { sonusGr303IgName, sonusGr303EocRdtAlarmCategory, 
                      sonusGr303EocRdtAlarmSeverity, 
                      sonusEventDescription, sonusEventClass, 
                      sonusEventLevel, sonusSequenceId, sonusEventTime }
    STATUS          current
    DESCRIPTION     
            "This trap reports a GR303 Interface Group's EOC RDT alarm severity
             of a specified category."
    ::= { sonusGr303MIBNotificationsPrefix 9 }

END -- end of module SONUS-GR303-MIB.
