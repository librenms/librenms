--
-- This SMIv2 module has been generated by smidump 0.2-cvs. Do not edit.
--

SONUS-ISUP-SERVICE-GROUP-MIB DEFINITIONS ::= BEGIN

IMPORTS
    Integer32, MODULE-IDENTITY, NOTIFICATION-TYPE, OBJECT-TYPE, 
    Unsigned32
        FROM SNMPv2-SMI
    DateAndTime, DisplayString, RowStatus
        FROM SNMPv2-TC
    sonusEventClass, sonusEventDescription, sonusEventLevel, 
    sonusEventTime, sonusSequenceId, sonusShelfIndex, sonusSlotIndex
        FROM SONUS-COMMON-MIB
    sonusSignallingMIBs
        FROM SONUS-SMI
    PointCode, SonusAdminState, SonusName, SonusNameReference, 
    SonusPointCode, SonusShelfIndex, SonusSlotIndex, SonusSupportFlag
        FROM SONUS-TC;

sonusIsupServiceGroupMIB MODULE-IDENTITY
    LAST-UPDATED    "201212190000Z"
    ORGANIZATION    
            "Sonus Networks, Inc."
    CONTACT-INFO    
            "   Customer Support    
             Sonus Networks, Inc.
             7 Technology Park Drive
             Westford, MA 01886
             USA
             
             Tel: 978-614-8100
             Fax: 978-614-8609"
    DESCRIPTION     
            "The MIB Module for ISUP Service Group Management."
    ::= { sonusSignallingMIBs 1 }


sonusIsupServiceGroupMIBObjects OBJECT IDENTIFIER
    ::= { sonusIsupServiceGroupMIB 1 }

sonusIsupsgServiceGroup OBJECT IDENTIFIER
    ::= { sonusIsupServiceGroupMIBObjects 1 }

sonusIsupsgServiceGroupNextIndex OBJECT-TYPE
    SYNTAX          Integer32
    MAX-ACCESS      read-only
    STATUS          current
    DESCRIPTION     
            "The next valid index to use when creating a new sonusIsupsgServiceGroupEntry"
    ::= { sonusIsupsgServiceGroup 1 }

sonusIsupsgServiceGroupTable OBJECT-TYPE
    SYNTAX          SEQUENCE OF SonusIsupsgServiceGroupEntry
    MAX-ACCESS      not-accessible
    STATUS          current
    DESCRIPTION     
            "This table contains information about each ISUP Service Group
             configured to be a member of the node. 
             
             A management entity may create rows for Service Group that are
             anticipated to be supported in the future."
    ::= { sonusIsupsgServiceGroup 2 }

sonusIsupsgServiceGroupEntry OBJECT-TYPE
    SYNTAX          SonusIsupsgServiceGroupEntry
    MAX-ACCESS      not-accessible
    STATUS          current
    DESCRIPTION     
            "This table describes the ISUP Service Groups that are configured as
             members of the GSX9000 ISUP Service Group."
    INDEX           { sonusIsupsgServiceGroupListIndex }
    ::= { sonusIsupsgServiceGroupTable 1 }

SonusIsupsgServiceGroupEntry ::=
    SEQUENCE {
        sonusIsupsgServiceGroupListIndex Integer32,
        sonusIsupsgServiceGroupName     SonusName,
        sonusIsupsgServiceGroupRemotePointCode      PointCode,
        sonusIsupsgServiceGroupTG       SonusNameReference,
        sonusIsupsgServiceGroupSwitchType INTEGER,
        sonusIsupsgServiceGroupRevision INTEGER,
        sonusIsupsgServiceGroupHuntAlgorithm    INTEGER,
        sonusIsupsgServiceGroupCost     Integer32,
        sonusIsupsgServiceGroupCicControl INTEGER,
        sonusIsupsgServiceGroupContTestFreq   Integer32,
        sonusIsupsgServiceGroupOperation INTEGER,
        sonusIsupsgServiceGroupMode     INTEGER,
        sonusIsupsgServiceGroupAction   INTEGER,
        sonusIsupsgServiceGroupTimeout  Integer32,
        sonusIsupsgServiceGroupAdminState SonusAdminState,
        sonusIsupsgServiceGroupProfileName  DisplayString,
        sonusIsupsgServiceGroupRowStatus RowStatus,
        sonusIsupsgServiceGroupHopCounterState      SonusAdminState,
        sonusIsupsgServiceGroupHopCounterValue      Integer32,
        sonusIsupsgServiceGroupDiscTreatmentProfileName               SonusNameReference,
        sonusIsupsgServiceGroupTonePackageName      SonusNameReference,
        sonusIsupsgServiceGroupGrsStartup INTEGER,
        sonusIsupsgServiceGroupOlipCheck INTEGER,
        sonusIsupsgServiceGroupRemPc    SonusPointCode,
        sonusIsupsgServiceGroupExchangeType   INTEGER,
        sonusIsupsgServiceGroupInspectionTime     DateAndTime,
        sonusIsupsgServiceGroupInspectionFreq     INTEGER,
        sonusIsupsgServiceGroupInspectionState      SonusAdminState,
        sonusIsupsgServiceGroupSignalingProfileName           SonusNameReference,
        sonusIsupsgServiceGroupAccRespProcess     INTEGER,
        sonusIsupsgServiceGroupAccL1ARCancelpercentage              Integer32,
        sonusIsupsgServiceGroupAccL1DRCancelpercentage              Integer32,
        sonusIsupsgServiceGroupAccL2ARCancelpercentage              Integer32,
        sonusIsupsgServiceGroupAccL2DRCancelpercentage              Integer32,
        sonusIsupsgServiceGroupAccL3ARCancelpercentage              Integer32,
        sonusIsupsgServiceGroupAccL3DRCancelpercentage              Integer32,
        sonusIsupsgServiceGroupAccSendACL Integer32,
        sonusIsupsgServiceGroupGatewayOutage    INTEGER,
        sonusIsupsgServiceGroupInrInfProfileName        SonusNameReference,
        sonusIsupsgServiceGroupAlertToneName    SonusNameReference,
        sonusIsupsgServiceGroupFarEndTestType     INTEGER,
        sonusIsupsgServiceGroupSatelliteCircuits        INTEGER,
        sonusIsupsgServiceGroupClliTown DisplayString,
        sonusIsupsgServiceGroupClliState DisplayString,
        sonusIsupsgServiceGroupClliBuilding   DisplayString,
        sonusIsupsgServiceGroupClliBuildingSubDiv         DisplayString,
        sonusIsupsgServiceGroupClusterRouting     INTEGER,
        sonusIsupsgServiceGroupSendingOlipCheck       INTEGER,
        sonusIsupsgServiceGroupMinDigitsForQuery        Integer32,
        sonusIsupsgServiceGroupConfirmationToneName           SonusNameReference,
        sonusIsupsgServiceGroupConfirmationToneOverride               INTEGER,
        sonusIsupsgServiceGroupAnsSupervisionTimeout            Integer32,
        sonusIsupsgServiceGroupAnsSupervisionTimeoutAction                  INTEGER,
        sonusIsupsgServiceGroupOverrideCutThruOnRcvAcmWithBciIw                       INTEGER,
        sonusIsupsgServiceGroupSwitchId Integer32,
        sonusIsupsgServiceGroupCarrierId Integer32,
        sonusIsupsgServiceGroupCrankBackProfile       Integer32,
        sonusIsupsgServiceGroupSequentialGRS    SonusSupportFlag,
        sonusIsupsgServiceGroupCongRelTimeout     Integer32,
        sonusIsupsgServiceGroupMessageThrottling        SonusSupportFlag,
        sonusIsupsgServiceGroupMessageThrottlingTimer             Integer32,
        sonusIsupsgServiceGroupCallCleanupCallsPerSegment                 Integer32,
        sonusIsupsgServiceGroupCallCleanupInterSegmentTimer                   Integer32,
        sonusIsupsgServiceGroupLdcTimeout Integer32,
        sonusIsupsgServiceGroupLdcAction INTEGER,
        sonusIsupsgServiceGroupLdcRelCause  Integer32,
        sonusIsupsgServiceGroupLdcEmergencyCalls        INTEGER,
        sonusIsupsgServiceGroupChargeArea DisplayString,
        sonusIsupsgServiceGroupMessagePriorityReset           INTEGER,
        sonusIsupsgServiceGroupLookAheadForBusy       INTEGER,
        sonusIsupsgServiceGroupNetworkIdentity      DisplayString,
        sonusIsupsgServiceGroupNodeIdentity   Integer32,
        sonusIsupsgServiceGroupLocationOfREL34      INTEGER,
        sonusIsupsgServiceGroupLocationOfREL42      INTEGER,
        sonusIsupsgServiceGroupTandemLimitCounter         Integer32,
        sonusIsupsgServiceGroupSvsSwitchType    INTEGER,
        sonusIsupsgServiceGroupLocationOfREL    INTEGER,
        sonusIsupsgServiceGroupDeleteIxcTcCode      DisplayString,
        sonusIsupsgServiceGroupSkipCrankBackProfile           Unsigned32,
        sonusIsupsgServiceGroupCRLRelCause  Integer32,
        sonusIsupsgServiceGroupEarlyMediaCutThrough           INTEGER,
        sonusIsupsgServiceGroupPddTimeout Integer32,
        sonusIsupsgServiceGroupPddRelCause  Integer32,
        sonusIsupsgServiceGroupCustomerOrCarrierIdentificationNumber                            Integer32,
        sonusIsupsgServiceGroupServiceTypeIdentifier            Integer32
    }

sonusIsupsgServiceGroupListIndex OBJECT-TYPE
    SYNTAX          Integer32 (1..3500)
    MAX-ACCESS      read-only
    STATUS          current
    DESCRIPTION     
            "The index of the ISUP Service Group entry."
    ::= { sonusIsupsgServiceGroupEntry 1 }

sonusIsupsgServiceGroupName OBJECT-TYPE
    SYNTAX          SonusName
    MAX-ACCESS      read-write
    STATUS          current
    DESCRIPTION     
            "The name of the ISUP Service Group."
    ::= { sonusIsupsgServiceGroupEntry 2 }

sonusIsupsgServiceGroupRemotePointCode OBJECT-TYPE
    SYNTAX          PointCode
    MAX-ACCESS      read-write
    STATUS          current
    DESCRIPTION     
            "Identifies the SS7 Point Code of the ISUP Service Group in decimal format,
             the least significant three bytes representing Network-Cluster-Member values."
    ::= { sonusIsupsgServiceGroupEntry 3 }

sonusIsupsgServiceGroupTG OBJECT-TYPE
    SYNTAX          SonusNameReference
    MAX-ACCESS      read-write
    STATUS          current
    DESCRIPTION     
            "The Trunk Group, which the ISUP Service Group belongs to."
    ::= { sonusIsupsgServiceGroupEntry 4 }

sonusIsupsgServiceGroupSwitchType OBJECT-TYPE
    SYNTAX          INTEGER { dms500(1), dms250(2), dms200(3), dms100(4), 
                        lucent5ESS(5), lucent4ESS(6) }
    MAX-ACCESS      read-write
    STATUS          obsolete
    DESCRIPTION     
            "This field is not used in 6.1 onwards."
    ::= { sonusIsupsgServiceGroupEntry 5 }

sonusIsupsgServiceGroupRevision OBJECT-TYPE
    SYNTAX          INTEGER { ansi1992(1), ansi1995(2), itu1993(3), 
                        etsi2(4), nttfcc(5), itu1997(6), itu1988(7), 
                        ituq767(8), belgacom(9), nttcom(10), spirou(12), 
                        mexicoic(13), italy(14), denmarkic(15), 
                        hongkongic(16), singapore(17), etsi3(18), 
                        peru(19), chile(20), portugaloni(21), 
                        argentina(22), argentinaidt(23), spain(24), 
                        brazil(25), india(26), chinacnc(27), korea(28), 
                        ukisup(29), etsi2plus(30), ansiatt(31), 
                        israel(32), slovak2(33), russia(34) }
    MAX-ACCESS      read-write
    STATUS          current
    DESCRIPTION     
            "The revision of the ISUP protocol supported on this Service Group."
    ::= { sonusIsupsgServiceGroupEntry 6 }

sonusIsupsgServiceGroupHuntAlgorithm OBJECT-TYPE
    SYNTAX          INTEGER { bottom2top(1), top2bottom(2), 
                        circuithi2lo(3), circuitlo2hi(4), 
                        mostnleastidle(5), circularbottom2top(6), 
                        circulartop2bottom(7) }
    MAX-ACCESS      read-write
    STATUS          current
    DESCRIPTION     
            "The hunting method used to select circuits for calls destined
             to the Service Group destination."
    ::= { sonusIsupsgServiceGroupEntry 7 }

sonusIsupsgServiceGroupCost OBJECT-TYPE
    SYNTAX          Integer32 (0..100)
    MAX-ACCESS      read-write
    STATUS          current
    DESCRIPTION     
            "The routing cost to the ISUP Service Group."
    ::= { sonusIsupsgServiceGroupEntry 8 }

sonusIsupsgServiceGroupCicControl OBJECT-TYPE
    SYNTAX          INTEGER { noCics(1), oddCics(2), evenCics(3), 
                        allCics(4) }
    MAX-ACCESS      read-write
    STATUS          current
    DESCRIPTION     
            "The CICs being controlled to resolve dual seizure."
    ::= { sonusIsupsgServiceGroupEntry 9 }

sonusIsupsgServiceGroupContTestFreq OBJECT-TYPE
    SYNTAX          Integer32 (0..16)
    MAX-ACCESS      read-write
    STATUS          current
    DESCRIPTION     
            "Identifies the frequency of continuity test to be performed on each circuit."
    ::= { sonusIsupsgServiceGroupEntry 10 }

sonusIsupsgServiceGroupOperation OBJECT-TYPE
    SYNTAX          INTEGER { block(1), unblock(2), reset(3), 
                        undefined(4) }
    MAX-ACCESS      read-write
    STATUS          current
    DESCRIPTION     
            "The operation to be applied to the circuits in the ISUP Service Group."
    ::= { sonusIsupsgServiceGroupEntry 11 }

sonusIsupsgServiceGroupMode OBJECT-TYPE
    SYNTAX          INTEGER { outOfService(1), inService(2) }
    MAX-ACCESS      read-write
    STATUS          current
    DESCRIPTION     
            "The mode of operation of circuits in the ISUP Service Group."
    ::= { sonusIsupsgServiceGroupEntry 12 }

sonusIsupsgServiceGroupAction OBJECT-TYPE
    SYNTAX          INTEGER { dryUp(1), force(2), undefined(3) }
    MAX-ACCESS      read-write
    STATUS          current
    DESCRIPTION     
            "The action taken on the circuits in the ISUP Service Group."
    ::= { sonusIsupsgServiceGroupEntry 13 }

sonusIsupsgServiceGroupTimeout OBJECT-TYPE
    SYNTAX          Integer32 (0..1440)
    MAX-ACCESS      read-write
    STATUS          current
    DESCRIPTION     
            "The timeout value in minutes for dryup action on the ISUP Service Group."
    ::= { sonusIsupsgServiceGroupEntry 14 }

sonusIsupsgServiceGroupAdminState OBJECT-TYPE
    SYNTAX          SonusAdminState
    MAX-ACCESS      read-write
    STATUS          current
    DESCRIPTION     
            "The admin state of the ISUP Service Group."
    ::= { sonusIsupsgServiceGroupEntry 15 }

sonusIsupsgServiceGroupProfileName OBJECT-TYPE
    SYNTAX          DisplayString (SIZE(0..23))
    MAX-ACCESS      read-write
    STATUS          current
    DESCRIPTION     
            "The ISUP Service Group profile name."
    ::= { sonusIsupsgServiceGroupEntry 16 }

sonusIsupsgServiceGroupRowStatus OBJECT-TYPE
    SYNTAX          RowStatus
    MAX-ACCESS      read-write
    STATUS          current
    DESCRIPTION     
            ""
    ::= { sonusIsupsgServiceGroupEntry 17 }

sonusIsupsgServiceGroupHopCounterState OBJECT-TYPE
    SYNTAX          SonusAdminState
    MAX-ACCESS      read-write
    STATUS          current
    DESCRIPTION     
            "The Hop Counter state for the ISUP Service Group."
    ::= { sonusIsupsgServiceGroupEntry 18 }

sonusIsupsgServiceGroupHopCounterValue OBJECT-TYPE
    SYNTAX          Integer32 (0..31)
    MAX-ACCESS      read-write
    STATUS          current
    DESCRIPTION     
            "Specifies the value of the Hop Counter if initiated by the switch."
    ::= { sonusIsupsgServiceGroupEntry 19 }

sonusIsupsgServiceGroupDiscTreatmentProfileName OBJECT-TYPE
    SYNTAX          SonusNameReference
    MAX-ACCESS      read-write
    STATUS          current
    DESCRIPTION     
            "The disconnect treatment profile to be used for this service."
    ::= { sonusIsupsgServiceGroupEntry 20 }

sonusIsupsgServiceGroupTonePackageName OBJECT-TYPE
    SYNTAX          SonusNameReference
    MAX-ACCESS      read-write
    STATUS          current
    DESCRIPTION     
            "The tone package to be used for this service."
    ::= { sonusIsupsgServiceGroupEntry 21 }

sonusIsupsgServiceGroupGrsStartup OBJECT-TYPE
    SYNTAX          INTEGER { disabled(1), enabled(2) }
    MAX-ACCESS      read-write
    STATUS          current
    DESCRIPTION     
            "Specifies whether support is enabled or disabled for
             GRS/GRA at Startup for the ISUP Service Group."
    ::= { sonusIsupsgServiceGroupEntry 22 }

sonusIsupsgServiceGroupOlipCheck OBJECT-TYPE
    SYNTAX          INTEGER { on(1), off(0) }
    MAX-ACCESS      read-write
    STATUS          current
    DESCRIPTION     
            "Specifies whether or not to check for the presence of an OLIP when determing
             that a call is invalid."
    ::= { sonusIsupsgServiceGroupEntry 23 }

sonusIsupsgServiceGroupRemPc OBJECT-TYPE
    SYNTAX          SonusPointCode
    MAX-ACCESS      read-write
    STATUS          current
    DESCRIPTION     
            "The Remote point code is not maintained as an OCTET STRING"
    ::= { sonusIsupsgServiceGroupEntry 24 }

sonusIsupsgServiceGroupExchangeType OBJECT-TYPE
    SYNTAX          INTEGER { none(1), typeA(2), typeB(3) }
    MAX-ACCESS      read-write
    STATUS          obsolete
    DESCRIPTION     
            "This field is not used in 6.1 onwards."
    ::= { sonusIsupsgServiceGroupEntry 25 }

sonusIsupsgServiceGroupInspectionTime OBJECT-TYPE
    SYNTAX          DateAndTime
    MAX-ACCESS      read-write
    STATUS          current
    DESCRIPTION     
            "Octet string that identifies the GMT time and date
             to start Periodic Circuit Inspection.
             
             	field  octects  contents    			  range
             	-----  -------  --------      			  -----
             1      1-2    year                      0..65536
             2       3     month                     1..12
             3       4     day                       1..31
             4       5     hour                      0..23
              5       6     minutes                   0..59
             6       7     seconds                   0..60
                        (use 60 for leap-second)
             7       8     deci-seconds              0..9
             8       9     direction from UTC        '+' / '-'
             9      10     hours from UTC            0..11
             10      11     minutes from UTC          0..59
             
             For example, Tuesday May 26, 1992 at 1:30:15 PM EDT would be
             displayed as:
             
             1992-5-26,13:30:15.0,-4:0
             
             * Notes:
             - the value of year is in network-byte order"
    ::= { sonusIsupsgServiceGroupEntry 26 }

sonusIsupsgServiceGroupInspectionFreq OBJECT-TYPE
    SYNTAX          INTEGER { onehour(1), threehours(2), sixhours(3), 
                        twelvehours(4), oneday(5), twodays(6) }
    MAX-ACCESS      read-write
    STATUS          current
    DESCRIPTION     
            ""
    DEFVAL          { oneday }
    ::= { sonusIsupsgServiceGroupEntry 27 }

sonusIsupsgServiceGroupInspectionState OBJECT-TYPE
    SYNTAX          SonusAdminState
    MAX-ACCESS      read-write
    STATUS          current
    DESCRIPTION     
            ""
    DEFVAL          { disabled }
    ::= { sonusIsupsgServiceGroupEntry 28 }

sonusIsupsgServiceGroupSignalingProfileName OBJECT-TYPE
    SYNTAX          SonusNameReference
    MAX-ACCESS      read-write
    STATUS          current
    DESCRIPTION     
            "The ISUP Signaling Profile to be used for this service."
    ::= { sonusIsupsgServiceGroupEntry 29 }

sonusIsupsgServiceGroupAccRespProcess OBJECT-TYPE
    SYNTAX          INTEGER { disabled(1), enabled(2) }
    MAX-ACCESS      read-write
    STATUS          current
    DESCRIPTION     
            "The ACC Processing state for the ISUP Service Group."
    ::= { sonusIsupsgServiceGroupEntry 30 }

sonusIsupsgServiceGroupAccL1ARCancelpercentage OBJECT-TYPE
    SYNTAX          Integer32 (0..100)
    MAX-ACCESS      read-write
    STATUS          current
    DESCRIPTION     
            "Specifies the percentage of Alternate Routed call to be cancel at Congestion Level 1."
    ::= { sonusIsupsgServiceGroupEntry 31 }

sonusIsupsgServiceGroupAccL1DRCancelpercentage OBJECT-TYPE
    SYNTAX          Integer32 (0..100)
    MAX-ACCESS      read-write
    STATUS          current
    DESCRIPTION     
            "Specifies the percentage of Direct Routed call to be cancel at Congestion Level 1."
    ::= { sonusIsupsgServiceGroupEntry 32 }

sonusIsupsgServiceGroupAccL2ARCancelpercentage OBJECT-TYPE
    SYNTAX          Integer32 (0..100)
    MAX-ACCESS      read-write
    STATUS          current
    DESCRIPTION     
            "Specifies the percentage of Alternate Routed call to be cancel at Congestion Level 2."
    ::= { sonusIsupsgServiceGroupEntry 33 }

sonusIsupsgServiceGroupAccL2DRCancelpercentage OBJECT-TYPE
    SYNTAX          Integer32 (0..100)
    MAX-ACCESS      read-write
    STATUS          current
    DESCRIPTION     
            "Specifies the percentage of Direct Routed call to be cancel at Congestion Level 2."
    ::= { sonusIsupsgServiceGroupEntry 34 }

sonusIsupsgServiceGroupAccL3ARCancelpercentage OBJECT-TYPE
    SYNTAX          Integer32 (0..100)
    MAX-ACCESS      read-write
    STATUS          current
    DESCRIPTION     
            "Specifies the percentage of Alternate Routed call to be cancel at Congestion Level 3."
    ::= { sonusIsupsgServiceGroupEntry 35 }

sonusIsupsgServiceGroupAccL3DRCancelpercentage OBJECT-TYPE
    SYNTAX          Integer32 (0..100)
    MAX-ACCESS      read-write
    STATUS          current
    DESCRIPTION     
            "Specifies the percentage of Direct Routed call to be cancel at Congestion Level 3."
    ::= { sonusIsupsgServiceGroupEntry 36 }

sonusIsupsgServiceGroupAccSendACL OBJECT-TYPE
    SYNTAX          Integer32 (0..3)
    MAX-ACCESS      read-write
    STATUS          current
    DESCRIPTION     
            "specifies the Max ACL value send to remote node for the ISUP Service Group. 0 means disabled"
    ::= { sonusIsupsgServiceGroupEntry 37 }

sonusIsupsgServiceGroupGatewayOutage OBJECT-TYPE
    SYNTAX          INTEGER { keepCalls(1), removeCalls(2) }
    MAX-ACCESS      read-write
    STATUS          obsolete
    DESCRIPTION     
            "specifies if the service group should try to keep active calls when the ss7 gateway disconnects.
             Not used from 6.5 onwards"
    ::= { sonusIsupsgServiceGroupEntry 38 }

sonusIsupsgServiceGroupInrInfProfileName OBJECT-TYPE
    SYNTAX          SonusNameReference
    MAX-ACCESS      read-write
    STATUS          current
    DESCRIPTION     
            "The ISUP INR INF Profile to be used for this service."
    ::= { sonusIsupsgServiceGroupEntry 39 }

sonusIsupsgServiceGroupAlertToneName OBJECT-TYPE
    SYNTAX          SonusNameReference
    MAX-ACCESS      read-write
    STATUS          obsolete
    DESCRIPTION     
            "Specifies a named reference to a tone to play for ring back.
             This object is not used and was made obsolete in GSX
             release 6.0. Local Ring Back Tone Configuration has
             now moved to PSX."
    ::= { sonusIsupsgServiceGroupEntry 40 }

sonusIsupsgServiceGroupFarEndTestType OBJECT-TYPE
    SYNTAX          INTEGER { cqm(1), cvt(2), reset(3), undefined(4) }
    MAX-ACCESS      read-write
    STATUS          current
    DESCRIPTION     
            "The far end action taken on all ISUP Circuit."
    ::= { sonusIsupsgServiceGroupEntry 41 }

sonusIsupsgServiceGroupSatelliteCircuits OBJECT-TYPE
    SYNTAX          INTEGER { disabled(1), enabled(2) }
    MAX-ACCESS      read-write
    STATUS          obsolete
    DESCRIPTION     
            "This field is not used in 6.1 onwards"
    ::= { sonusIsupsgServiceGroupEntry 42 }

sonusIsupsgServiceGroupClliTown OBJECT-TYPE
    SYNTAX          DisplayString (SIZE(4))
    MAX-ACCESS      read-write
    STATUS          current
    DESCRIPTION     
            "Town code to be used in the CLLI parameter for ANSI GR317 circuit
             validation test failure."
    DEFVAL          { "0000" }
    ::= { sonusIsupsgServiceGroupEntry 43 }

sonusIsupsgServiceGroupClliState OBJECT-TYPE
    SYNTAX          DisplayString (SIZE(2))
    MAX-ACCESS      read-write
    STATUS          current
    DESCRIPTION     
            "State code to be used in the CLLI parameter for ANSI GR317 circuit
             validation test failure."
    DEFVAL          { "00" }
    ::= { sonusIsupsgServiceGroupEntry 44 }

sonusIsupsgServiceGroupClliBuilding OBJECT-TYPE
    SYNTAX          DisplayString (SIZE(2))
    MAX-ACCESS      read-write
    STATUS          current
    DESCRIPTION     
            "Building code to be used in the CLLI parameter for ANSI GR317 circuit
             validation test failure."
    DEFVAL          { "00" }
    ::= { sonusIsupsgServiceGroupEntry 45 }

sonusIsupsgServiceGroupClliBuildingSubDiv OBJECT-TYPE
    SYNTAX          DisplayString (SIZE(3))
    MAX-ACCESS      read-write
    STATUS          current
    DESCRIPTION     
            "Building sub division code to be used in the CLLI parameter for ANSI GR317 
             circuit validation test failure."
    DEFVAL          { "000" }
    ::= { sonusIsupsgServiceGroupEntry 46 }

sonusIsupsgServiceGroupClusterRouting OBJECT-TYPE
    SYNTAX          INTEGER { disabled(1), enabled(2) }
    MAX-ACCESS      read-write
    STATUS          current
    DESCRIPTION     
            "Specifies whether this DPC supports cluster routing or member routing."
    DEFVAL          { disabled }
    ::= { sonusIsupsgServiceGroupEntry 47 }

sonusIsupsgServiceGroupSendingOlipCheck OBJECT-TYPE
    SYNTAX          INTEGER { on(1), off(0) }
    MAX-ACCESS      read-write
    STATUS          current
    DESCRIPTION     
            "Specifies whether or not to check for the presence of an OLIP when sending an IAM."
    ::= { sonusIsupsgServiceGroupEntry 48 }

sonusIsupsgServiceGroupMinDigitsForQuery OBJECT-TYPE
    SYNTAX          Integer32 (0..30)
    MAX-ACCESS      read-write
    STATUS          current
    DESCRIPTION     
            "If Overlap Receiving is supported and CalledAddress
             received is not complete, then minimum number of
             CalledAddress Digits to receive before we go for Route
             Query."
    DEFVAL          { 0 }
    ::= { sonusIsupsgServiceGroupEntry 49 }

sonusIsupsgServiceGroupConfirmationToneName OBJECT-TYPE
    SYNTAX          SonusNameReference
    MAX-ACCESS      read-write
    STATUS          current
    DESCRIPTION     
            "Specifies a named reference to a tone to play for connection confirmation."
    ::= { sonusIsupsgServiceGroupEntry 50 }

sonusIsupsgServiceGroupConfirmationToneOverride OBJECT-TYPE
    SYNTAX          INTEGER { disabled(1), enabled(2) }
    MAX-ACCESS      read-write
    STATUS          current
    DESCRIPTION     
            "If supported, informs CC to play a C-Tone for all
             calls using this service group.  If unsupported, 
             informs CC to use the enable flag from the PSX to
             decide whether or not to play a C-Tone."
    DEFVAL          { disabled }
    ::= { sonusIsupsgServiceGroupEntry 51 }

sonusIsupsgServiceGroupAnsSupervisionTimeout OBJECT-TYPE
    SYNTAX          Integer32 (0..1000)
    MAX-ACCESS      read-write
    STATUS          current
    DESCRIPTION     
            "This is the time from egress call setup to egress receiving an answer."
    DEFVAL          { 300 }
    ::= { sonusIsupsgServiceGroupEntry 52 }

sonusIsupsgServiceGroupAnsSupervisionTimeoutAction OBJECT-TYPE
    SYNTAX          INTEGER { release(1), softanswer(2), 
                        trapAndRestart(3) }
    MAX-ACCESS      read-write
    STATUS          current
    DESCRIPTION     
            "This is the action to take if the answer supervision timer
             expires.  The call may be released, assumed to be answered or
             a trap can be fired and the timer restarted."
    DEFVAL          { release }
    ::= { sonusIsupsgServiceGroupEntry 53 }

sonusIsupsgServiceGroupOverrideCutThruOnRcvAcmWithBciIw OBJECT-TYPE
    SYNTAX          INTEGER { unsupported(1), backwardscutthru(2), 
                        fullduplexcutthru(3), nocutthru(4), ignore(5) }
    MAX-ACCESS      read-write
    STATUS          current
    DESCRIPTION     
            "Specifies whether to override protocol specific cut thru direction
             when ACM is received with BCI of Interworking Encountered.  If the
             override is set to unsupported, no override will occur.  If the 
             the override is set to fullduplexcutthru, full duplex cut through will
             occur.  If the override is set to nocutthru, no cut through change will
             be made. If this is set to ignore then no cutthru will be sent."
    DEFVAL          { unsupported }
    ::= { sonusIsupsgServiceGroupEntry 54 }

sonusIsupsgServiceGroupSwitchId OBJECT-TYPE
    SYNTAX          Integer32 (0..99)
    MAX-ACCESS      read-write
    STATUS          obsolete
    DESCRIPTION     
            "This field is not used in 6.1 onwards"
    DEFVAL          { 0 }
    ::= { sonusIsupsgServiceGroupEntry 55 }

sonusIsupsgServiceGroupCarrierId OBJECT-TYPE
    SYNTAX          Integer32 (0..99)
    MAX-ACCESS      read-write
    STATUS          obsolete
    DESCRIPTION     
            "This field is not used in 6.1 onwards"
    DEFVAL          { 0 }
    ::= { sonusIsupsgServiceGroupEntry 56 }

sonusIsupsgServiceGroupCrankBackProfile OBJECT-TYPE
    SYNTAX          Integer32 (1..20)
    MAX-ACCESS      read-write
    STATUS          current
    DESCRIPTION     
            "The Crank Back Profile to be used for this Service."
    DEFVAL          { 1 }
    ::= { sonusIsupsgServiceGroupEntry 57 }

sonusIsupsgServiceGroupSequentialGRS OBJECT-TYPE
    SYNTAX          SonusSupportFlag
    MAX-ACCESS      read-write
    STATUS          current
    DESCRIPTION     
            "Is Sequential GRS Procedures Supported by this Service."
    DEFVAL          { unsupported }
    ::= { sonusIsupsgServiceGroupEntry 58 }

sonusIsupsgServiceGroupCongRelTimeout OBJECT-TYPE
    SYNTAX          Integer32 (0..5)
    MAX-ACCESS      read-write
    STATUS          current
    DESCRIPTION     
            "Time to delay sending of release during congestion."
    DEFVAL          { 0 }
    ::= { sonusIsupsgServiceGroupEntry 59 }

sonusIsupsgServiceGroupMessageThrottling OBJECT-TYPE
    SYNTAX          SonusSupportFlag
    MAX-ACCESS      read-write
    STATUS          current
    DESCRIPTION     
            "Is the procedure to throttle automatic message generation active for
             this service."
    DEFVAL          { unsupported }
    ::= { sonusIsupsgServiceGroupEntry 60 }

sonusIsupsgServiceGroupMessageThrottlingTimer OBJECT-TYPE
    SYNTAX          Integer32 (0..1000)
    MAX-ACCESS      read-write
    STATUS          current
    DESCRIPTION     
            "Time in miliseconds used by the message throttling inserted between messages
             which would otherwise be simultaneous."
    DEFVAL          { 0 }
    ::= { sonusIsupsgServiceGroupEntry 61 }

sonusIsupsgServiceGroupCallCleanupCallsPerSegment OBJECT-TYPE
    SYNTAX          Integer32 (1..25)
    MAX-ACCESS      read-write
    STATUS          current
    DESCRIPTION     
            "The number of calls to be cleaned up in before suspending."
    DEFVAL          { 25 }
    ::= { sonusIsupsgServiceGroupEntry 62 }

sonusIsupsgServiceGroupCallCleanupInterSegmentTimer OBJECT-TYPE
    SYNTAX          Integer32 (10..1000)
    MAX-ACCESS      read-write
    STATUS          current
    DESCRIPTION     
            "Time in miliseconds between cleaning up each consecutive group of calls."
    DEFVAL          { 100 }
    ::= { sonusIsupsgServiceGroupEntry 63 }

sonusIsupsgServiceGroupLdcTimeout OBJECT-TYPE
    SYNTAX          Integer32 (0..2880)
    MAX-ACCESS      read-write
    STATUS          current
    DESCRIPTION     
            "The timeout value of the long duration call timer in minutes.
             Allowed values are 0 to disable the timer, 60-2880 minutes to set the timer."
    DEFVAL          { 0 }
    ::= { sonusIsupsgServiceGroupEntry 64 }

sonusIsupsgServiceGroupLdcAction OBJECT-TYPE
    SYNTAX          INTEGER { noAction(0), trap(1), release(2), 
                        trapAndRelease(3) }
    MAX-ACCESS      read-write
    STATUS          current
    DESCRIPTION     
            "This is the action to take if the long duration call timer
             expires.  The call may be released or a trap fired, or both."
    DEFVAL          { noAction }
    ::= { sonusIsupsgServiceGroupEntry 65 }

sonusIsupsgServiceGroupLdcRelCause OBJECT-TYPE
    SYNTAX          Integer32 (1..127)
    MAX-ACCESS      read-write
    STATUS          current
    DESCRIPTION     
            "The Q.850 release value to use should the call be released 
             due to long duration call timer expiry"
    DEFVAL          { 41 }
    ::= { sonusIsupsgServiceGroupEntry 66 }

sonusIsupsgServiceGroupLdcEmergencyCalls OBJECT-TYPE
    SYNTAX          INTEGER { include(0), exclude(1) }
    MAX-ACCESS      read-write
    STATUS          current
    DESCRIPTION     
            "Whether Emergency Calls should be excluded from or included 
             in Long Duration Call Disconnect procedures"
    DEFVAL          { exclude }
    ::= { sonusIsupsgServiceGroupEntry 67 }

sonusIsupsgServiceGroupChargeArea OBJECT-TYPE
    SYNTAX          DisplayString (SIZE(0..5))
    MAX-ACCESS      read-write
    STATUS          current
    DESCRIPTION     
            "This Service Control is used to populate the Charge Area if it contains
             a valid 5 digit Charge Area. The Charge Area will be set in the ACM or
             CPG message if a script is returned from the PSX or for Disconnect
             treatment"
    ::= { sonusIsupsgServiceGroupEntry 68 }

sonusIsupsgServiceGroupMessagePriorityReset OBJECT-TYPE
    SYNTAX          INTEGER { off(0), on(1) }
    MAX-ACCESS      read-write
    STATUS          current
    DESCRIPTION     
            "The behavior applied to setting the Message Priority field in a transmitted IAM. 
             'on' specifies compliance with NCS standards, where, Message Transfer Priority 
             will be set to 1 for HPC calls and 0 for non HPC calls. 'off' specifies that 
             Message Transfer Priority value will be passed through from ingress to egress 
             if it is greater than 0."
    DEFVAL          { off }
    ::= { sonusIsupsgServiceGroupEntry 69 }

sonusIsupsgServiceGroupLookAheadForBusy OBJECT-TYPE
    SYNTAX          INTEGER { allowed(0), pathReserved(1), notAllowed(2) }
    MAX-ACCESS      read-write
    STATUS          current
    DESCRIPTION     
            "The default value used in the look ahead for busy field in the ISUP Precedence parameter."
    DEFVAL          { notAllowed }
    ::= { sonusIsupsgServiceGroupEntry 70 }

sonusIsupsgServiceGroupNetworkIdentity OBJECT-TYPE
    SYNTAX          DisplayString (SIZE(4))
    MAX-ACCESS      read-write
    STATUS          current
    DESCRIPTION     
            "The default value used for the 4 digit Network Identity field in the ISUP precedence parameter."
    DEFVAL          { "0100" }
    ::= { sonusIsupsgServiceGroupEntry 71 }

sonusIsupsgServiceGroupNodeIdentity OBJECT-TYPE
    SYNTAX          Integer32 (0..65535)
    MAX-ACCESS      read-write
    STATUS          current
    DESCRIPTION     
            "The Node ID value to use in the Advice Of Charge (AOC) feature.
             Allowed values are 0 to disable the feature, 1-65535."
    DEFVAL          { 0 }
    ::= { sonusIsupsgServiceGroupEntry 72 }

sonusIsupsgServiceGroupLocationOfREL34 OBJECT-TYPE
    SYNTAX          INTEGER { notUsed(0), user(1), privateLocal(2), 
                        publicLocal(3), transitNet(4), publicRemote(5), 
                        privateRemote(6), natReserved6(7), 
                        internationalNet(8), natReserved8(9), 
                        natReserved9(10), netBeyondInterPoint(11), 
                        natReserved11(12), natReserved12(13), 
                        natReserved13(14), natReserved14(15), 
                        natReserved15(16) }
    MAX-ACCESS      read-write
    STATUS          current
    DESCRIPTION     
            "Update the Location in the REL if Cause Value is 34"
    DEFVAL          { notUsed }
    ::= { sonusIsupsgServiceGroupEntry 73 }

sonusIsupsgServiceGroupLocationOfREL42 OBJECT-TYPE
    SYNTAX          INTEGER { notUsed(0), user(1), privateLocal(2), 
                        publicLocal(3), transitNet(4), publicRemote(5), 
                        privateRemote(6), natReserved6(7), 
                        internationalNet(8), natReserved8(9), 
                        natReserved9(10), netBeyondInterPoint(11), 
                        natReserved11(12), natReserved12(13), 
                        natReserved13(14), natReserved14(15), 
                        natReserved15(16) }
    MAX-ACCESS      read-write
    STATUS          current
    DESCRIPTION     
            "Update the Location in the REL if Cause Value is 42"
    DEFVAL          { notUsed }
    ::= { sonusIsupsgServiceGroupEntry 74 }

sonusIsupsgServiceGroupTandemLimitCounter OBJECT-TYPE
    SYNTAX          Integer32 (0..15)
    MAX-ACCESS      read-write
    STATUS          current
    DESCRIPTION     
            "Limit Counter to be set in outgoing IAM in Tandem Call Counter parameter in SBTM Network"
    DEFVAL          { 0 }
    ::= { sonusIsupsgServiceGroupEntry 75 }

sonusIsupsgServiceGroupSvsSwitchType OBJECT-TYPE
    SYNTAX          INTEGER { none(0), axe(1), nec(2), t9000(3) }
    MAX-ACCESS      read-write
    STATUS          obsolete
    DESCRIPTION     
            "Switch type from which the call is received by GSX. Each will have a different logic
             for routing and cdr generation. Not deployed and obsoleted in GSX Release 7.2.2, as
             PCR 1338 is superseded by PCR 1624"
    ::= { sonusIsupsgServiceGroupEntry 76 }

sonusIsupsgServiceGroupLocationOfREL OBJECT-TYPE
    SYNTAX          INTEGER { notUsed(0), user(1), privateLocal(2), 
                        publicLocal(3), transitNet(4), publicRemote(5), 
                        privateRemote(6), natReserved6(7), 
                        internationalNet(8), natReserved8(9), 
                        natReserved9(10), netBeyondInterPoint(11), 
                        natReserved11(12), natReserved12(13), 
                        natReserved13(14), natReserved14(15), 
                        natReserved15(16) }
    MAX-ACCESS      read-write
    STATUS          current
    DESCRIPTION     
            "Update the Location in the REL"
    DEFVAL          { notUsed }
    ::= { sonusIsupsgServiceGroupEntry 77 }

sonusIsupsgServiceGroupDeleteIxcTcCode OBJECT-TYPE
    SYNTAX          DisplayString (SIZE(0..4))
    MAX-ACCESS      read-write
    STATUS          current
    DESCRIPTION     
            "Delete the IXC/TC code in the CIT"
    ::= { sonusIsupsgServiceGroupEntry 78 }

sonusIsupsgServiceGroupSkipCrankBackProfile OBJECT-TYPE
    SYNTAX          Unsigned32 (0..20)
    MAX-ACCESS      read-write
    STATUS          current
    DESCRIPTION     
            "The Skip Crankback Profile to be used for this Service."
    DEFVAL          { 0 }
    ::= { sonusIsupsgServiceGroupEntry 79 }

sonusIsupsgServiceGroupCRLRelCause OBJECT-TYPE
    SYNTAX          Integer32 (1..127)
    MAX-ACCESS      read-write
    STATUS          current
    DESCRIPTION     
            "The Q.850 release value to use should the call be released 
             due to call rate limiting"
    DEFVAL          { 42 }
    ::= { sonusIsupsgServiceGroupEntry 80 }

sonusIsupsgServiceGroupEarlyMediaCutThrough OBJECT-TYPE
    SYNTAX          INTEGER { disabled(1), enabled(2) }
    MAX-ACCESS      read-write
    STATUS          current
    DESCRIPTION     
            "Specifies whether support is enabled or disabled for
             Early Media Cut through when SS7 IAM is generated."
    ::= { sonusIsupsgServiceGroupEntry 81 }

sonusIsupsgServiceGroupPddTimeout OBJECT-TYPE
    SYNTAX          Integer32 (0..20)
    MAX-ACCESS      read-write
    STATUS          current
    DESCRIPTION     
            "Post Dial Delay timeout in seconds."
    DEFVAL          { 0 }
    ::= { sonusIsupsgServiceGroupEntry 82 }

sonusIsupsgServiceGroupPddRelCause OBJECT-TYPE
    SYNTAX          Integer32 (1..127)
    MAX-ACCESS      read-write
    STATUS          current
    DESCRIPTION     
            "The Q.850 release value to use should the call be released 
             due to PDD timer expiry"
    DEFVAL          { 42 }
    ::= { sonusIsupsgServiceGroupEntry 83 }

sonusIsupsgServiceGroupCustomerOrCarrierIdentificationNumber OBJECT-TYPE
    SYNTAX          Integer32 (0..16383)
    MAX-ACCESS      read-write
    STATUS          current
    DESCRIPTION     
            "This indicates the customer or carrier identifier"
    DEFVAL          { 0 }
    ::= { sonusIsupsgServiceGroupEntry 84 }

sonusIsupsgServiceGroupServiceTypeIdentifier OBJECT-TYPE
    SYNTAX          Integer32 (0..127)
    MAX-ACCESS      read-write
    STATUS          current
    DESCRIPTION     
            "This indicates the service type identifier associated with the service"
    DEFVAL          { 0 }
    ::= { sonusIsupsgServiceGroupEntry 85 }

sonusIsupsgServiceGroupStatTable OBJECT-TYPE
    SYNTAX          SEQUENCE OF SonusIsupsgServiceGroupStatEntry
    MAX-ACCESS      not-accessible
    STATUS          current
    DESCRIPTION     
            "This table contains status information about each ISUP access point
             in the GSX9000 Switch node.  ISUP Service Groups within the node can
             can be configured before SS7 connections is physically attached to
             the node.  The remote ISUP user part may be unavailable or the SS7
             links to the destination may not be connected or correctly configured.
             Therefore, it is possible that an access point can be unavailable,
             and is absent."
    ::= { sonusIsupServiceGroupMIBObjects 2 }

sonusIsupsgServiceGroupStatEntry OBJECT-TYPE
    SYNTAX          SonusIsupsgServiceGroupStatEntry
    MAX-ACCESS      not-accessible
    STATUS          current
    DESCRIPTION     
            "This table describes the status of the Service Groups that are configured
             as destinations ISUP nodes for the GSX9000 Switch node."
    INDEX           { sonusIsupsgServiceGroupStatListIndex }
    ::= { sonusIsupsgServiceGroupStatTable 1 }

SonusIsupsgServiceGroupStatEntry ::=
    SEQUENCE {
        sonusIsupsgServiceGroupStatListIndex    Integer32,
        sonusIsupsgServiceGroupStatName SonusNameReference,
        sonusIsupsgServiceGroupStatStatus INTEGER,
        sonusIsupsgServiceGroupStatLastInspectionTime             DateAndTime,
        sonusIsupsgServiceGroupStatNextInspectionTime             DateAndTime
    }

sonusIsupsgServiceGroupStatListIndex OBJECT-TYPE
    SYNTAX          Integer32 (0..3500)
    MAX-ACCESS      read-only
    STATUS          current
    DESCRIPTION     
            "The index of the ISUP Service Group."
    ::= { sonusIsupsgServiceGroupStatEntry 1 }

sonusIsupsgServiceGroupStatName OBJECT-TYPE
    SYNTAX          SonusNameReference
    MAX-ACCESS      read-only
    STATUS          current
    DESCRIPTION     
            "The name of the ISUP Service Group."
    ::= { sonusIsupsgServiceGroupStatEntry 2 }

sonusIsupsgServiceGroupStatStatus OBJECT-TYPE
    SYNTAX          INTEGER { available(1), unavailable(2), congested(3), 
                        congested2(4), congested3(5) }
    MAX-ACCESS      read-only
    STATUS          current
    DESCRIPTION     
            "The state of the ISUP Service Group."
    ::= { sonusIsupsgServiceGroupStatEntry 3 }

sonusIsupsgServiceGroupStatLastInspectionTime OBJECT-TYPE
    SYNTAX          DateAndTime
    MAX-ACCESS      read-write
    STATUS          current
    DESCRIPTION     
            "Octet string that identifies the GMT time and date
             of the last Periodic Circuit Inspection.
             
             	field  octects  contents    			  range
             	-----  -------  --------      			  -----
             1      1-2    year                      0..65536
             2       3     month                     1..12
             3       4     day                       1..31
             4       5     hour                      0..23
              5       6     minutes                   0..59
             6       7     seconds                   0..60
                        (use 60 for leap-second)
             7       8     deci-seconds              0..9
             8       9     direction from UTC        '+' / '-'
             9      10     hours from UTC            0..11
             10      11     minutes from UTC          0..59
             
             For example, Tuesday May 26, 1992 at 1:30:15 PM EDT would be
             displayed as:
             
             1992-5-26,13:30:15.0,-4:0
             
             * Notes:
             - the value of year is in network-byte order"
    ::= { sonusIsupsgServiceGroupStatEntry 4 }

sonusIsupsgServiceGroupStatNextInspectionTime OBJECT-TYPE
    SYNTAX          DateAndTime
    MAX-ACCESS      read-write
    STATUS          current
    DESCRIPTION     
            "Octet string that identifies the GMT time and date
             of the next Periodic Circuit Inspection.
             
             	field  octects  contents    			  range
             	-----  -------  --------      			  -----
             1      1-2    year                      0..65536
             2       3     month                     1..12
             3       4     day                       1..31
             4       5     hour                      0..23
              5       6     minutes                   0..59
             6       7     seconds                   0..60
                        (use 60 for leap-second)
             7       8     deci-seconds              0..9
             8       9     direction from UTC        '+' / '-'
             9      10     hours from UTC            0..11
             10      11     minutes from UTC          0..59
             
             For example, Tuesday May 26, 1992 at 1:30:15 PM EDT would be
             displayed as:
             
             1992-5-26,13:30:15.0,-4:0
             
             * Notes:
             - the value of year is in network-byte order"
    ::= { sonusIsupsgServiceGroupStatEntry 5 }

sonusIsupsgSvcGrpProfile OBJECT IDENTIFIER
    ::= { sonusIsupServiceGroupMIBObjects 3 }

sonusIsupsgSvcGrpProfileNextIndex OBJECT-TYPE
    SYNTAX          Integer32
    MAX-ACCESS      read-only
    STATUS          current
    DESCRIPTION     
            "The next valid index to use when creating a new sonusIsupsgSvcGrpProfileEntry"
    ::= { sonusIsupsgSvcGrpProfile 1 }

sonusIsupsgSvcGrpProfileTable OBJECT-TYPE
    SYNTAX          SEQUENCE OF SonusIsupsgSvcGrpProfileEntry
    MAX-ACCESS      not-accessible
    STATUS          current
    DESCRIPTION     
            "This table contains ISUP Service Group profiles."
    ::= { sonusIsupsgSvcGrpProfile 2 }

sonusIsupsgSvcGrpProfileEntry OBJECT-TYPE
    SYNTAX          SonusIsupsgSvcGrpProfileEntry
    MAX-ACCESS      not-accessible
    STATUS          current
    DESCRIPTION     
            "This table describes the Service Group profile."
    INDEX           { sonusIsupsgSvcGrpProfileListIndex }
    ::= { sonusIsupsgSvcGrpProfileTable 1 }

SonusIsupsgSvcGrpProfileEntry ::=
    SEQUENCE {
        sonusIsupsgSvcGrpProfileListIndex Integer32,
        sonusIsupsgSvcGrpProfileName    SonusName,
        sonusIsupsgSvcGrpProfileTG      SonusNameReference,
        sonusIsupsgSvcGrpProfileSwitchType  INTEGER,
        sonusIsupsgSvcGrpProfileRevision INTEGER,
        sonusIsupsgSvcGrpProfileHuntAlgorithm     INTEGER,
        sonusIsupsgSvcGrpProfileCost    Integer32,
        sonusIsupsgSvcGrpProfileCicControl  INTEGER,
        sonusIsupsgSvcGrpProfileContTestFreq    Integer32,
        sonusIsupsgSvcGrpProfileAdminState  SonusAdminState,
        sonusIsupsgSvcGrpProfileRowStatus RowStatus,
        sonusIsupsgSvcGrpProfileHopCounterState       SonusAdminState,
        sonusIsupsgSvcGrpProfileHopCounterValue       Integer32,
        sonusIsupsgSvcGrpProfileDiscTreatmentProfileName                SonusNameReference,
        sonusIsupsgSvcGrpProfileTonePackageName       SonusNameReference,
        sonusIsupsgSvcGrpProfileGrsStartup  INTEGER,
        sonusIsupsgSvcGrpProfileOlipCheck INTEGER,
        sonusIsupsgSvcGrpProfileExchangeType    INTEGER,
        sonusIsupsgSvcGrpProfileInspectionTime      DateAndTime,
        sonusIsupsgSvcGrpProfileInspectionFreq      INTEGER,
        sonusIsupsgSvcGrpProfileInspectionState       SonusAdminState,
        sonusIsupsgSvcGrpProfileSignalingProfileName            SonusNameReference,
        sonusIsupsgSvcGrpProfileAccRespProcess      INTEGER,
        sonusIsupsgSvcGrpProfileAccL1ARCancelpercentage               Integer32,
        sonusIsupsgSvcGrpProfileAccL1DRCancelpercentage               Integer32,
        sonusIsupsgSvcGrpProfileAccL2ARCancelpercentage               Integer32,
        sonusIsupsgSvcGrpProfileAccL2DRCancelpercentage               Integer32,
        sonusIsupsgSvcGrpProfileAccL3ARCancelpercentage               Integer32,
        sonusIsupsgSvcGrpProfileAccL3DRCancelpercentage               Integer32,
        sonusIsupsgSvcGrpProfileAccSendACL  Integer32,
        sonusIsupsgSvcGrpProfileInrInfProfileName         SonusNameReference,
        sonusIsupsgSvcGrpProfileAlertToneName     SonusNameReference,
        sonusIsupsgSvcGrpProfileSatelliteCircuits         INTEGER,
        sonusIsupsgSvcGrpProfileClliTown DisplayString,
        sonusIsupsgSvcGrpProfileClliState DisplayString,
        sonusIsupsgSvcGrpProfileClliBuilding    DisplayString,
        sonusIsupsgSvcGrpProfileClliBuildingSubDiv          DisplayString,
        sonusIsupsgSvcGrpProfileClusterRouting      INTEGER,
        sonusIsupsgSvcGrpProfileSendingOlipCheck        INTEGER,
        sonusIsupsgSvcGrpProfileMinDigitsForQuery         Integer32,
        sonusIsupsgSvcGrpProfileConfirmationToneName            SonusNameReference,
        sonusIsupsgSvcGrpProfileConfirmationToneOverride                INTEGER,
        sonusIsupsgSvcGrpProfileAnsSupervisionTimeout             Integer32,
        sonusIsupsgSvcGrpProfileAnsSupervisionTimeoutAction                   INTEGER,
        sonusIsupsgSvcGrpProfileOverrideCutThruOnRcvAcmWithBciIw                        INTEGER,
        sonusIsupsgSvcGrpProfileSwitchId Integer32,
        sonusIsupsgSvcGrpProfileCarrierId Integer32,
        sonusIsupsgSvcGrpProfileCrankBackProfile        Integer32,
        sonusIsupsgSvcGrpProfileSequentialGRS     SonusSupportFlag,
        sonusIsupsgSvcGrpProfileCongRelTimeout      Integer32,
        sonusIsupsgSvcGrpProfileMessageThrottling         SonusSupportFlag,
        sonusIsupsgSvcGrpProfileMessageThrottlingTimer              Integer32,
        sonusIsupsgSvcGrpProfileCallCleanupCallsPerSegment                  Integer32,
        sonusIsupsgSvcGrpProfileCallCleanupInterSegmentTimer                    Integer32,
        sonusIsupsgSvcGrpProfileLdcTimeout  Integer32,
        sonusIsupsgSvcGrpProfileLdcAction INTEGER,
        sonusIsupsgSvcGrpProfileLdcRelCause   Integer32,
        sonusIsupsgSvcGrpProfileLdcEmergencyCalls         INTEGER,
        sonusIsupsgSvcGrpProfileChargeArea  DisplayString,
        sonusIsupsgSvcGrpProfileMessagePriorityReset            INTEGER,
        sonusIsupsgSvcGrpProfileLookAheadForBusy        INTEGER,
        sonusIsupsgSvcGrpProfileNetworkIdentity       DisplayString,
        sonusIsupsgSvcGrpProfileNodeIdentity    Integer32,
        sonusIsupsgSvcGrpProfileLocationOfREL34       INTEGER,
        sonusIsupsgSvcGrpProfileLocationOfREL42       INTEGER,
        sonusIsupsgSvcGrpProfileTandemLimitCounter          Integer32,
        sonusIsupsgSvcGrpProfileSvsSwitchType     INTEGER,
        sonusIsupsgSvcGrpProfileLocationOfREL     INTEGER,
        sonusIsupsgSvcGrpProfileDeleteIxcTcCode       DisplayString,
        sonusIsupsgSvcGrpProfileSkipCrankBackProfile            Unsigned32,
        sonusIsupsgSvcGrpProfileCRLRelCause   Integer32,
        sonusIsupsgSvcGrpProfileEarlyMediaCutThrough            INTEGER,
        sonusIsupsgSvcGrpProfilePddTimeout  Integer32,
        sonusIsupsgSvcGrpProfilePddRelCause   Integer32,
        sonusIsupsgSvcGrpProfileCustomerOrCarrierIdentifier                   Integer32,
        sonusIsupsgSvcGrpProfileServiceTypeIdentifier             Integer32
    }

sonusIsupsgSvcGrpProfileListIndex OBJECT-TYPE
    SYNTAX          Integer32 (0..127)
    MAX-ACCESS      read-only
    STATUS          current
    DESCRIPTION     
            "The index of the ISUP Service Group Profile."
    ::= { sonusIsupsgSvcGrpProfileEntry 1 }

sonusIsupsgSvcGrpProfileName OBJECT-TYPE
    SYNTAX          SonusName
    MAX-ACCESS      read-write
    STATUS          current
    DESCRIPTION     
            "The name of the ISUP Service Group Profile."
    ::= { sonusIsupsgSvcGrpProfileEntry 2 }

sonusIsupsgSvcGrpProfileTG OBJECT-TYPE
    SYNTAX          SonusNameReference
    MAX-ACCESS      read-write
    STATUS          current
    DESCRIPTION     
            "The Trunk Group, which the ISUP Service Group belongs to."
    ::= { sonusIsupsgSvcGrpProfileEntry 3 }

sonusIsupsgSvcGrpProfileSwitchType OBJECT-TYPE
    SYNTAX          INTEGER { dms500(1), dms250(2), dms200(3), dms100(4), 
                        lucent5ESS(5), lucent4ESS(6) }
    MAX-ACCESS      read-write
    STATUS          obsolete
    DESCRIPTION     
            "This field is not used in 6.1 onwards"
    ::= { sonusIsupsgSvcGrpProfileEntry 4 }

sonusIsupsgSvcGrpProfileRevision OBJECT-TYPE
    SYNTAX          INTEGER { ansi1992(1), ansi1995(2), itu1993(3), 
                        etsi2(4), nttfcc(5), itu1997(6), itu1988(7), 
                        ituq767(8), belgacom(9), nttcom(10), spirou(12), 
                        mexicoic(13), italy(14), denmarkic(15), 
                        hongkongic(16), singapore(17), etsi3(18), 
                        peru(19), chile(20), portugaloni(21), 
                        argentina(22), argentinaidt(23), spain(24), 
                        brazil(25), india(26), chinacnc(27), korea(28), 
                        ukisup(29), etsi2plus(30), ansiatt(31), 
                        israel(32), slovak2(33), russia(34) }
    MAX-ACCESS      read-write
    STATUS          current
    DESCRIPTION     
            "The revision of the ISUP protocol supported on this Service Group."
    ::= { sonusIsupsgSvcGrpProfileEntry 5 }

sonusIsupsgSvcGrpProfileHuntAlgorithm OBJECT-TYPE
    SYNTAX          INTEGER { bottom2top(1), top2bottom(2), 
                        circuithi2lo(3), circuitlo2hi(4), 
                        mostnleastidle(5), circularbottom2top(6), 
                        circulartop2bottom(7) }
    MAX-ACCESS      read-write
    STATUS          current
    DESCRIPTION     
            "The hunting method used to select circuits for calls destined
             to the Service Group destination."
    ::= { sonusIsupsgSvcGrpProfileEntry 6 }

sonusIsupsgSvcGrpProfileCost OBJECT-TYPE
    SYNTAX          Integer32 (0..100)
    MAX-ACCESS      read-write
    STATUS          current
    DESCRIPTION     
            "The routing cost to the ISUP Service Group."
    ::= { sonusIsupsgSvcGrpProfileEntry 7 }

sonusIsupsgSvcGrpProfileCicControl OBJECT-TYPE
    SYNTAX          INTEGER { noCics(1), oddCics(2), evenCics(3), 
                        allCics(4) }
    MAX-ACCESS      read-write
    STATUS          current
    DESCRIPTION     
            "The CICs being controlled to resolve dual seizure."
    ::= { sonusIsupsgSvcGrpProfileEntry 8 }

sonusIsupsgSvcGrpProfileContTestFreq OBJECT-TYPE
    SYNTAX          Integer32 (0..16)
    MAX-ACCESS      read-write
    STATUS          current
    DESCRIPTION     
            "Identifies the frequency of continuity test to be performed on each circuit."
    ::= { sonusIsupsgSvcGrpProfileEntry 9 }

sonusIsupsgSvcGrpProfileAdminState OBJECT-TYPE
    SYNTAX          SonusAdminState
    MAX-ACCESS      read-write
    STATUS          current
    DESCRIPTION     
            "The admin state of the ISUP Service Group Profile."
    ::= { sonusIsupsgSvcGrpProfileEntry 10 }

sonusIsupsgSvcGrpProfileRowStatus OBJECT-TYPE
    SYNTAX          RowStatus
    MAX-ACCESS      read-write
    STATUS          current
    DESCRIPTION     
            ""
    ::= { sonusIsupsgSvcGrpProfileEntry 11 }

sonusIsupsgSvcGrpProfileHopCounterState OBJECT-TYPE
    SYNTAX          SonusAdminState
    MAX-ACCESS      read-write
    STATUS          current
    DESCRIPTION     
            "The Hop Counter state of the ISUP Service Group Profile."
    ::= { sonusIsupsgSvcGrpProfileEntry 12 }

sonusIsupsgSvcGrpProfileHopCounterValue OBJECT-TYPE
    SYNTAX          Integer32 (0..31)
    MAX-ACCESS      read-write
    STATUS          current
    DESCRIPTION     
            "Specifies the value of the Hop Counter if initiated by the switch."
    ::= { sonusIsupsgSvcGrpProfileEntry 13 }

sonusIsupsgSvcGrpProfileDiscTreatmentProfileName OBJECT-TYPE
    SYNTAX          SonusNameReference
    MAX-ACCESS      read-write
    STATUS          current
    DESCRIPTION     
            "The disconnect treatment profile to be used for this service."
    ::= { sonusIsupsgSvcGrpProfileEntry 14 }

sonusIsupsgSvcGrpProfileTonePackageName OBJECT-TYPE
    SYNTAX          SonusNameReference
    MAX-ACCESS      read-write
    STATUS          current
    DESCRIPTION     
            "The tone package to be used for this service."
    ::= { sonusIsupsgSvcGrpProfileEntry 15 }

sonusIsupsgSvcGrpProfileGrsStartup OBJECT-TYPE
    SYNTAX          INTEGER { disabled(1), enabled(2) }
    MAX-ACCESS      read-write
    STATUS          current
    DESCRIPTION     
            "Specifies whether support is enabled or disabled for
             GRS/GRA at Startup for the ISUP Service Group."
    ::= { sonusIsupsgSvcGrpProfileEntry 16 }

sonusIsupsgSvcGrpProfileOlipCheck OBJECT-TYPE
    SYNTAX          INTEGER { on(1), off(0) }
    MAX-ACCESS      read-write
    STATUS          current
    DESCRIPTION     
            "Specifies the value of the Hop Counter if initiated by the switch."
    ::= { sonusIsupsgSvcGrpProfileEntry 17 }

sonusIsupsgSvcGrpProfileExchangeType OBJECT-TYPE
    SYNTAX          INTEGER { none(1), typeA(2), typeB(3) }
    MAX-ACCESS      read-write
    STATUS          obsolete
    DESCRIPTION     
            "This field is not used in 6.1 onwards"
    ::= { sonusIsupsgSvcGrpProfileEntry 18 }

sonusIsupsgSvcGrpProfileInspectionTime OBJECT-TYPE
    SYNTAX          DateAndTime
    MAX-ACCESS      read-write
    STATUS          current
    DESCRIPTION     
            "Octet string that identifies the GMT time and date
             to start Periodic Circuit Inspection.
             
             	field  octects  contents    			  range
             	-----  -------  --------      			  -----
             1      1-2    year                      0..65536
             2       3     month                     1..12
             3       4     day                       1..31
             4       5     hour                      0..23
              5       6     minutes                   0..59
             6       7     seconds                   0..60
                        (use 60 for leap-second)
             7       8     deci-seconds              0..9
             8       9     direction from UTC        '+' / '-'
             9      10     hours from UTC            0..11
             10      11     minutes from UTC          0..59
             
             For example, Tuesday May 26, 1992 at 1:30:15 PM EDT would be
             displayed as:
             
             1992-5-26,13:30:15.0,-4:0
             
             * Notes:
             - the value of year is in network-byte order"
    ::= { sonusIsupsgSvcGrpProfileEntry 19 }

sonusIsupsgSvcGrpProfileInspectionFreq OBJECT-TYPE
    SYNTAX          INTEGER { onehour(1), threehours(2), sixhours(3), 
                        twelvehours(4), oneday(5), twodays(6) }
    MAX-ACCESS      read-write
    STATUS          current
    DESCRIPTION     
            ""
    DEFVAL          { oneday }
    ::= { sonusIsupsgSvcGrpProfileEntry 20 }

sonusIsupsgSvcGrpProfileInspectionState OBJECT-TYPE
    SYNTAX          SonusAdminState
    MAX-ACCESS      read-write
    STATUS          current
    DESCRIPTION     
            ""
    DEFVAL          { disabled }
    ::= { sonusIsupsgSvcGrpProfileEntry 21 }

sonusIsupsgSvcGrpProfileSignalingProfileName OBJECT-TYPE
    SYNTAX          SonusNameReference
    MAX-ACCESS      read-write
    STATUS          current
    DESCRIPTION     
            "The ISUP Signaling Profile to be used for this service."
    ::= { sonusIsupsgSvcGrpProfileEntry 22 }

sonusIsupsgSvcGrpProfileAccRespProcess OBJECT-TYPE
    SYNTAX          INTEGER { disabled(1), enabled(2) }
    MAX-ACCESS      read-write
    STATUS          current
    DESCRIPTION     
            "The ACC Processing state for the ISUP Service Group Profile."
    ::= { sonusIsupsgSvcGrpProfileEntry 23 }

sonusIsupsgSvcGrpProfileAccL1ARCancelpercentage OBJECT-TYPE
    SYNTAX          Integer32 (1..100)
    MAX-ACCESS      read-write
    STATUS          current
    DESCRIPTION     
            "Specifies the percentage of Alternate Routed call to be cancel at Congestion Level 1."
    ::= { sonusIsupsgSvcGrpProfileEntry 24 }

sonusIsupsgSvcGrpProfileAccL1DRCancelpercentage OBJECT-TYPE
    SYNTAX          Integer32 (1..100)
    MAX-ACCESS      read-write
    STATUS          current
    DESCRIPTION     
            "Specifies the percentage of Direct Routed call to be cancel at Congestion Level 1."
    ::= { sonusIsupsgSvcGrpProfileEntry 25 }

sonusIsupsgSvcGrpProfileAccL2ARCancelpercentage OBJECT-TYPE
    SYNTAX          Integer32 (1..100)
    MAX-ACCESS      read-write
    STATUS          current
    DESCRIPTION     
            "Specifies the percentage of Alternate Routed call to be cancel at Congestion Level 2."
    ::= { sonusIsupsgSvcGrpProfileEntry 26 }

sonusIsupsgSvcGrpProfileAccL2DRCancelpercentage OBJECT-TYPE
    SYNTAX          Integer32 (1..100)
    MAX-ACCESS      read-write
    STATUS          current
    DESCRIPTION     
            "Specifies the percentage of Direct Routed call to be cancel at Congestion Level 2."
    ::= { sonusIsupsgSvcGrpProfileEntry 27 }

sonusIsupsgSvcGrpProfileAccL3ARCancelpercentage OBJECT-TYPE
    SYNTAX          Integer32 (1..100)
    MAX-ACCESS      read-write
    STATUS          current
    DESCRIPTION     
            "Specifies the percentage of Alternate Routed call to be cancel at Congestion Level 3."
    ::= { sonusIsupsgSvcGrpProfileEntry 28 }

sonusIsupsgSvcGrpProfileAccL3DRCancelpercentage OBJECT-TYPE
    SYNTAX          Integer32 (1..100)
    MAX-ACCESS      read-write
    STATUS          current
    DESCRIPTION     
            "Specifies the percentage of Direct Routed call to be cancel at Congestion Level 3."
    ::= { sonusIsupsgSvcGrpProfileEntry 29 }

sonusIsupsgSvcGrpProfileAccSendACL OBJECT-TYPE
    SYNTAX          Integer32 (0..3)
    MAX-ACCESS      read-write
    STATUS          current
    DESCRIPTION     
            "specifies the Max ACL value send to remote node for the ISUP Service Group. 0 means disabled"
    ::= { sonusIsupsgSvcGrpProfileEntry 30 }

sonusIsupsgSvcGrpProfileInrInfProfileName OBJECT-TYPE
    SYNTAX          SonusNameReference
    MAX-ACCESS      read-write
    STATUS          current
    DESCRIPTION     
            "The ISUP INR INF Profile to be used for this service."
    ::= { sonusIsupsgSvcGrpProfileEntry 31 }

sonusIsupsgSvcGrpProfileAlertToneName OBJECT-TYPE
    SYNTAX          SonusNameReference
    MAX-ACCESS      read-write
    STATUS          obsolete
    DESCRIPTION     
            "Specifies a named reference to a tone to play for ring back.
             This object is not used and was made obsolete in GSX
             release 6.0. Local Ring Back Tone Configuration has
             now moved to PSX."
    ::= { sonusIsupsgSvcGrpProfileEntry 32 }

sonusIsupsgSvcGrpProfileSatelliteCircuits OBJECT-TYPE
    SYNTAX          INTEGER { disabled(1), enabled(2) }
    MAX-ACCESS      read-write
    STATUS          obsolete
    DESCRIPTION     
            "This field is not used in 6.1 onwards"
    ::= { sonusIsupsgSvcGrpProfileEntry 33 }

sonusIsupsgSvcGrpProfileClliTown OBJECT-TYPE
    SYNTAX          DisplayString (SIZE(4))
    MAX-ACCESS      read-write
    STATUS          current
    DESCRIPTION     
            "Town code to be used in the CLLI parameter for ANSI GR317 circuit
             validation test failure."
    DEFVAL          { "0000" }
    ::= { sonusIsupsgSvcGrpProfileEntry 34 }

sonusIsupsgSvcGrpProfileClliState OBJECT-TYPE
    SYNTAX          DisplayString (SIZE(2))
    MAX-ACCESS      read-write
    STATUS          current
    DESCRIPTION     
            "State code to be used in the CLLI parameter for ANSI GR317 circuit
             validation test failure."
    DEFVAL          { "00" }
    ::= { sonusIsupsgSvcGrpProfileEntry 35 }

sonusIsupsgSvcGrpProfileClliBuilding OBJECT-TYPE
    SYNTAX          DisplayString (SIZE(2))
    MAX-ACCESS      read-write
    STATUS          current
    DESCRIPTION     
            "Building code to be used in the CLLI parameter for ANSI GR317 circuit
             validation test failure."
    DEFVAL          { "00" }
    ::= { sonusIsupsgSvcGrpProfileEntry 36 }

sonusIsupsgSvcGrpProfileClliBuildingSubDiv OBJECT-TYPE
    SYNTAX          DisplayString (SIZE(3))
    MAX-ACCESS      read-write
    STATUS          current
    DESCRIPTION     
            "Building sub division code to be used in the CLLI parameter for ANSI GR317 
             circuit validation test failure."
    DEFVAL          { "000" }
    ::= { sonusIsupsgSvcGrpProfileEntry 37 }

sonusIsupsgSvcGrpProfileClusterRouting OBJECT-TYPE
    SYNTAX          INTEGER { disabled(1), enabled(2) }
    MAX-ACCESS      read-write
    STATUS          current
    DESCRIPTION     
            "Specifies whether this DPC supports cluster routing or member routing"
    DEFVAL          { disabled }
    ::= { sonusIsupsgSvcGrpProfileEntry 38 }

sonusIsupsgSvcGrpProfileSendingOlipCheck OBJECT-TYPE
    SYNTAX          INTEGER { on(1), off(0) }
    MAX-ACCESS      read-write
    STATUS          current
    DESCRIPTION     
            "Specifies whether OLIP checking will be performed when sending an IAM"
    ::= { sonusIsupsgSvcGrpProfileEntry 39 }

sonusIsupsgSvcGrpProfileMinDigitsForQuery OBJECT-TYPE
    SYNTAX          Integer32 (0..30)
    MAX-ACCESS      read-write
    STATUS          current
    DESCRIPTION     
            "If Overlap Receiving is supported and CalledAddress
             received is not complete, then minimum number of
             CalledAddress Digits to receive before we go for Route
             Query."
    DEFVAL          { 0 }
    ::= { sonusIsupsgSvcGrpProfileEntry 40 }

sonusIsupsgSvcGrpProfileConfirmationToneName OBJECT-TYPE
    SYNTAX          SonusNameReference
    MAX-ACCESS      read-write
    STATUS          current
    DESCRIPTION     
            "Specifies a named reference to a tone to play for connection confirmation."
    ::= { sonusIsupsgSvcGrpProfileEntry 41 }

sonusIsupsgSvcGrpProfileConfirmationToneOverride OBJECT-TYPE
    SYNTAX          INTEGER { disabled(1), enabled(2) }
    MAX-ACCESS      read-write
    STATUS          current
    DESCRIPTION     
            "Override for Confirmation Tone.  If supported, 
             informs CC to play a C-Tone for all
             		calls using this service group.  If unsupported, 
             		informs CC to use the enable flag from the PSX to
             		decide whether or not to play a C-Tone."
    DEFVAL          { disabled }
    ::= { sonusIsupsgSvcGrpProfileEntry 42 }

sonusIsupsgSvcGrpProfileAnsSupervisionTimeout OBJECT-TYPE
    SYNTAX          Integer32 (0..1000)
    MAX-ACCESS      read-write
    STATUS          current
    DESCRIPTION     
            "This is the time from egress call setup to egress receiving an answer,
             used for both user and network sides."
    DEFVAL          { 300 }
    ::= { sonusIsupsgSvcGrpProfileEntry 43 }

sonusIsupsgSvcGrpProfileAnsSupervisionTimeoutAction OBJECT-TYPE
    SYNTAX          INTEGER { release(1), softanswer(2), 
                        trapAndRestart(3) }
    MAX-ACCESS      read-write
    STATUS          current
    DESCRIPTION     
            "This is the action to take if the answer supervision timer
             expires.  The call may be released, assumed to be answered or
             a trap can be fired and the timer restarted."
    DEFVAL          { release }
    ::= { sonusIsupsgSvcGrpProfileEntry 44 }

sonusIsupsgSvcGrpProfileOverrideCutThruOnRcvAcmWithBciIw OBJECT-TYPE
    SYNTAX          INTEGER { unsupported(1), backwardscutthru(2), 
                        fullduplexcutthru(3), nocutthru(4) }
    MAX-ACCESS      read-write
    STATUS          current
    DESCRIPTION     
            "Specifies whether to override protocol specific cut thru direction
             when ACM is received with BCI of Interworking Encountered.  If the
             override is set to unsupported, no override will occur.  If the 
             the override is set to fullduplexcutthru, full duplex cut through will
             occur.  If the override is set to nocutthru, no cut through change will
             be made."
    DEFVAL          { unsupported }
    ::= { sonusIsupsgSvcGrpProfileEntry 45 }

sonusIsupsgSvcGrpProfileSwitchId OBJECT-TYPE
    SYNTAX          Integer32 (0..99)
    MAX-ACCESS      read-write
    STATUS          obsolete
    DESCRIPTION     
            "This field is not used in 6.1 onwards"
    DEFVAL          { 0 }
    ::= { sonusIsupsgSvcGrpProfileEntry 46 }

sonusIsupsgSvcGrpProfileCarrierId OBJECT-TYPE
    SYNTAX          Integer32 (0..99)
    MAX-ACCESS      read-write
    STATUS          obsolete
    DESCRIPTION     
            "This field is not used in 6.1 onwards"
    DEFVAL          { 0 }
    ::= { sonusIsupsgSvcGrpProfileEntry 47 }

sonusIsupsgSvcGrpProfileCrankBackProfile OBJECT-TYPE
    SYNTAX          Integer32 (1..20)
    MAX-ACCESS      read-write
    STATUS          current
    DESCRIPTION     
            "The Crank Back Profile to be used for this Service."
    DEFVAL          { 1 }
    ::= { sonusIsupsgSvcGrpProfileEntry 48 }

sonusIsupsgSvcGrpProfileSequentialGRS OBJECT-TYPE
    SYNTAX          SonusSupportFlag
    MAX-ACCESS      read-write
    STATUS          current
    DESCRIPTION     
            "Is Sequential GRS Procedures Supported by this Service."
    DEFVAL          { unsupported }
    ::= { sonusIsupsgSvcGrpProfileEntry 49 }

sonusIsupsgSvcGrpProfileCongRelTimeout OBJECT-TYPE
    SYNTAX          Integer32 (0..5)
    MAX-ACCESS      read-write
    STATUS          current
    DESCRIPTION     
            "Time to delay sending of release during congestion."
    DEFVAL          { 0 }
    ::= { sonusIsupsgSvcGrpProfileEntry 50 }

sonusIsupsgSvcGrpProfileMessageThrottling OBJECT-TYPE
    SYNTAX          SonusSupportFlag
    MAX-ACCESS      read-write
    STATUS          current
    DESCRIPTION     
            "Is the procedure to throttle automatic message generation active for
             this service."
    DEFVAL          { unsupported }
    ::= { sonusIsupsgSvcGrpProfileEntry 51 }

sonusIsupsgSvcGrpProfileMessageThrottlingTimer OBJECT-TYPE
    SYNTAX          Integer32 (0..1000)
    MAX-ACCESS      read-write
    STATUS          current
    DESCRIPTION     
            "Time in miliseconds used by the message throttling - inserted between messages
             which would otherwise be simultaneous."
    DEFVAL          { 0 }
    ::= { sonusIsupsgSvcGrpProfileEntry 52 }

sonusIsupsgSvcGrpProfileCallCleanupCallsPerSegment OBJECT-TYPE
    SYNTAX          Integer32 (1..25)
    MAX-ACCESS      read-write
    STATUS          current
    DESCRIPTION     
            "The number of calls to be cleaned up before suspending."
    DEFVAL          { 25 }
    ::= { sonusIsupsgSvcGrpProfileEntry 53 }

sonusIsupsgSvcGrpProfileCallCleanupInterSegmentTimer OBJECT-TYPE
    SYNTAX          Integer32 (10..1000)
    MAX-ACCESS      read-write
    STATUS          current
    DESCRIPTION     
            "Time in miliseconds between cleaning up each consecutive group of calls."
    DEFVAL          { 100 }
    ::= { sonusIsupsgSvcGrpProfileEntry 54 }

sonusIsupsgSvcGrpProfileLdcTimeout OBJECT-TYPE
    SYNTAX          Integer32 (0..2880)
    MAX-ACCESS      read-write
    STATUS          current
    DESCRIPTION     
            "The timeout value of the long duration call timer in minutes. 
             Allowed values are 0 to disable the timer, 60-2880 minutes to set the timer."
    DEFVAL          { 0 }
    ::= { sonusIsupsgSvcGrpProfileEntry 55 }

sonusIsupsgSvcGrpProfileLdcAction OBJECT-TYPE
    SYNTAX          INTEGER { noAction(0), trap(1), release(2), 
                        trapAndRelease(3) }
    MAX-ACCESS      read-write
    STATUS          current
    DESCRIPTION     
            "This is the action to take if the long duration call timer
             expires.  The call may be released or a trap fired, or both."
    DEFVAL          { noAction }
    ::= { sonusIsupsgSvcGrpProfileEntry 56 }

sonusIsupsgSvcGrpProfileLdcRelCause OBJECT-TYPE
    SYNTAX          Integer32 (1..127)
    MAX-ACCESS      read-write
    STATUS          current
    DESCRIPTION     
            "The Q.850 release value to use should the call be released 
             due to long duration call timer expiry"
    DEFVAL          { 41 }
    ::= { sonusIsupsgSvcGrpProfileEntry 57 }

sonusIsupsgSvcGrpProfileLdcEmergencyCalls OBJECT-TYPE
    SYNTAX          INTEGER { include(0), exclude(1) }
    MAX-ACCESS      read-write
    STATUS          current
    DESCRIPTION     
            "Whether Emergency Calls should be excluded from or included 
             in Long Duration Call Disconnect procedures"
    DEFVAL          { exclude }
    ::= { sonusIsupsgSvcGrpProfileEntry 58 }

sonusIsupsgSvcGrpProfileChargeArea OBJECT-TYPE
    SYNTAX          DisplayString (SIZE(0..5))
    MAX-ACCESS      read-write
    STATUS          current
    DESCRIPTION     
            "This Service Control is used to populate the Charge Area if it contains
             a valid 5 digit Charge Area. The Charge Area will be set in the ACM or
             CPG message if a script is returned from the PSX or for Disconnect
             treatment"
    ::= { sonusIsupsgSvcGrpProfileEntry 59 }

sonusIsupsgSvcGrpProfileMessagePriorityReset OBJECT-TYPE
    SYNTAX          INTEGER { off(0), on(1) }
    MAX-ACCESS      read-write
    STATUS          current
    DESCRIPTION     
            "The behavior applied to setting the Message Priority field in a transmitted IAM. 
             'on' specifies compliance with NCS standards, where, Message Transfer Priority 
             will be set to 1 for HPC calls and 0 for non HPC calls. 'off' specifies that 
             Message Transfer Priority value will be passed through from ingress to egress 
             if it is greater than 0."
    DEFVAL          { off }
    ::= { sonusIsupsgSvcGrpProfileEntry 60 }

sonusIsupsgSvcGrpProfileLookAheadForBusy OBJECT-TYPE
    SYNTAX          INTEGER { allowed(0), pathReserved(1), notAllowed(2) }
    MAX-ACCESS      read-write
    STATUS          current
    DESCRIPTION     
            "The default value used in the look ahead for busy field in the ISUP Precedence parameter."
    DEFVAL          { notAllowed }
    ::= { sonusIsupsgSvcGrpProfileEntry 61 }

sonusIsupsgSvcGrpProfileNetworkIdentity OBJECT-TYPE
    SYNTAX          DisplayString (SIZE(4))
    MAX-ACCESS      read-write
    STATUS          current
    DESCRIPTION     
            "The default value used for the 4 digit Network Identity field in the ISUP precedence parameter."
    DEFVAL          { "0100" }
    ::= { sonusIsupsgSvcGrpProfileEntry 62 }

sonusIsupsgSvcGrpProfileNodeIdentity OBJECT-TYPE
    SYNTAX          Integer32 (0..65535)
    MAX-ACCESS      read-write
    STATUS          current
    DESCRIPTION     
            "The Node ID value to use in the Advice Of Charge (AOC) feature.
             Allowed values are 0 to disable the feature, 1-65535."
    DEFVAL          { 0 }
    ::= { sonusIsupsgSvcGrpProfileEntry 63 }

sonusIsupsgSvcGrpProfileLocationOfREL34 OBJECT-TYPE
    SYNTAX          INTEGER { notUsed(0), user(1), privateLocal(2), 
                        publicLocal(3), transitNet(4), publicRemote(5), 
                        privateRemote(6), natReserved6(7), 
                        internationalNet(8), natReserved8(9), 
                        natReserved9(10), netBeyondInterPoint(11), 
                        natReserved11(12), natReserved12(13), 
                        natReserved13(14), natReserved14(15), 
                        natReserved15(16) }
    MAX-ACCESS      read-write
    STATUS          current
    DESCRIPTION     
            "Update the Location in the REL if Cause Value is 34"
    DEFVAL          { notUsed }
    ::= { sonusIsupsgSvcGrpProfileEntry 64 }

sonusIsupsgSvcGrpProfileLocationOfREL42 OBJECT-TYPE
    SYNTAX          INTEGER { notUsed(0), user(1), privateLocal(2), 
                        publicLocal(3), transitNet(4), publicRemote(5), 
                        privateRemote(6), natReserved6(7), 
                        internationalNet(8), natReserved8(9), 
                        natReserved9(10), netBeyondInterPoint(11), 
                        natReserved11(12), natReserved12(13), 
                        natReserved13(14), natReserved14(15), 
                        natReserved15(16) }
    MAX-ACCESS      read-write
    STATUS          current
    DESCRIPTION     
            "Update the Location in the REL if Cause Value is 42"
    DEFVAL          { notUsed }
    ::= { sonusIsupsgSvcGrpProfileEntry 65 }

sonusIsupsgSvcGrpProfileTandemLimitCounter OBJECT-TYPE
    SYNTAX          Integer32 (0..15)
    MAX-ACCESS      read-write
    STATUS          current
    DESCRIPTION     
            "Limit Counter to be set in outgoing IAM in Tandem Call Counter parameter in SBTM Network"
    DEFVAL          { 0 }
    ::= { sonusIsupsgSvcGrpProfileEntry 66 }

sonusIsupsgSvcGrpProfileSvsSwitchType OBJECT-TYPE
    SYNTAX          INTEGER { none(0), axe(1), nec(2), t9000(3) }
    MAX-ACCESS      read-write
    STATUS          obsolete
    DESCRIPTION     
            "Switch type from which the call is received by GSX. Each will have a different logic
             for routing and cdr generation. Not deployed and obsoleted in GSX Release 7.2.2, as
             PCR 1338 is superseded by PCR 1624"
    ::= { sonusIsupsgSvcGrpProfileEntry 67 }

sonusIsupsgSvcGrpProfileLocationOfREL OBJECT-TYPE
    SYNTAX          INTEGER { notUsed(0), user(1), privateLocal(2), 
                        publicLocal(3), transitNet(4), publicRemote(5), 
                        privateRemote(6), natReserved6(7), 
                        internationalNet(8), natReserved8(9), 
                        natReserved9(10), netBeyondInterPoint(11), 
                        natReserved11(12), natReserved12(13), 
                        natReserved13(14), natReserved14(15), 
                        natReserved15(16) }
    MAX-ACCESS      read-write
    STATUS          current
    DESCRIPTION     
            "Update the Location in the REL"
    DEFVAL          { notUsed }
    ::= { sonusIsupsgSvcGrpProfileEntry 68 }

sonusIsupsgSvcGrpProfileDeleteIxcTcCode OBJECT-TYPE
    SYNTAX          DisplayString (SIZE(0..4))
    MAX-ACCESS      read-write
    STATUS          current
    DESCRIPTION     
            "Delete the IXC/TC code in the CIT"
    ::= { sonusIsupsgSvcGrpProfileEntry 69 }

sonusIsupsgSvcGrpProfileSkipCrankBackProfile OBJECT-TYPE
    SYNTAX          Unsigned32 (0..20)
    MAX-ACCESS      read-write
    STATUS          current
    DESCRIPTION     
            "The Skip Crankback Profile to be used for this Service."
    DEFVAL          { 0 }
    ::= { sonusIsupsgSvcGrpProfileEntry 70 }

sonusIsupsgSvcGrpProfileCRLRelCause OBJECT-TYPE
    SYNTAX          Integer32 (1..127)
    MAX-ACCESS      read-write
    STATUS          current
    DESCRIPTION     
            "The Q.850 release value to use should the call be released 
             due to call rate limiting"
    DEFVAL          { 42 }
    ::= { sonusIsupsgSvcGrpProfileEntry 71 }

sonusIsupsgSvcGrpProfileEarlyMediaCutThrough OBJECT-TYPE
    SYNTAX          INTEGER { disabled(1), enabled(2) }
    MAX-ACCESS      read-write
    STATUS          current
    DESCRIPTION     
            "Specifies whether support is enabled or disabled for
             Early Media Cut through when SS7 IAM is generated."
    ::= { sonusIsupsgSvcGrpProfileEntry 72 }

sonusIsupsgSvcGrpProfilePddTimeout OBJECT-TYPE
    SYNTAX          Integer32 (0..20)
    MAX-ACCESS      read-write
    STATUS          current
    DESCRIPTION     
            "Post Dial Delay timeout in seconds."
    DEFVAL          { 0 }
    ::= { sonusIsupsgSvcGrpProfileEntry 73 }

sonusIsupsgSvcGrpProfilePddRelCause OBJECT-TYPE
    SYNTAX          Integer32 (1..127)
    MAX-ACCESS      read-write
    STATUS          current
    DESCRIPTION     
            "The Q.850 release value to use should the call be released 
             due to PDD timer expiry"
    DEFVAL          { 42 }
    ::= { sonusIsupsgSvcGrpProfileEntry 74 }

sonusIsupsgSvcGrpProfileCustomerOrCarrierIdentifier OBJECT-TYPE
    SYNTAX          Integer32 (0..16383)
    MAX-ACCESS      read-write
    STATUS          current
    DESCRIPTION     
            "This indicates the customer or carrier identifier"
    DEFVAL          { 0 }
    ::= { sonusIsupsgSvcGrpProfileEntry 75 }

sonusIsupsgSvcGrpProfileServiceTypeIdentifier OBJECT-TYPE
    SYNTAX          Integer32 (0..127)
    MAX-ACCESS      read-write
    STATUS          current
    DESCRIPTION     
            "This indicates the service type identifier associated with the service"
    DEFVAL          { 0 }
    ::= { sonusIsupsgSvcGrpProfileEntry 76 }

sonusIsupsgCircuitTable OBJECT-TYPE
    SYNTAX          SEQUENCE OF SonusIsupsgCircuitEntry
    MAX-ACCESS      not-accessible
    STATUS          current
    DESCRIPTION     
            "The Isupsg Circuit table describes the circuits in the indexed Access
             Point. This table is unavailable if the sonusisupsgServiceGroupStatStatus
             object indicates that this access point is unavailable.
             
             If the sonusNodeServerType object returns either 'absent' or 
             'unknown' the value of all other objects within this table are 
             indeterministic."
    ::= { sonusIsupServiceGroupMIBObjects 4 }

sonusIsupsgCircuitEntry OBJECT-TYPE
    SYNTAX          SonusIsupsgCircuitEntry
    MAX-ACCESS      not-accessible
    STATUS          current
    DESCRIPTION     
            ""
    INDEX           { sonusIsupsgCircuitServiceListIndex, 
                      sonusIsupsgCircuitIdentityCode }
    ::= { sonusIsupsgCircuitTable 1 }

SonusIsupsgCircuitEntry ::=
    SEQUENCE {
        sonusIsupsgCircuitServiceListIndex  Integer32,
        sonusIsupsgCircuitIdentityCode  Integer32,
        sonusIsupsgCircuitServiceName   SonusNameReference,
        sonusIsupsgCircuitPortName      SonusNameReference,
        sonusIsupsgCircuitChannel       Integer32,
        sonusIsupsgCircuitDirection     INTEGER,
        sonusIsupsgCircuitMode          INTEGER,
        sonusIsupsgCircuitAction        INTEGER,
        sonusIsupsgCircuitTimeout       Integer32,
        sonusIsupsgCircuitAdminState    SonusAdminState,
        sonusIsupsgCircuitProfileName   SonusNameReference,
        sonusIsupsgCircuitRowStatus     RowStatus,
        sonusIsupsgCircuitTrunkMember   Integer32,
        sonusIsupsgCircuitFarEndTestType INTEGER,
        sonusIsupsgCircuitStatusBits    Integer32,
        sonusIsupsgCircuitPortId        Integer32,
        sonusIsupsgCircuitShelf         SonusShelfIndex,
        sonusIsupsgCircuitSlot          SonusSlotIndex
    }

sonusIsupsgCircuitServiceListIndex OBJECT-TYPE
    SYNTAX          Integer32
    MAX-ACCESS      read-only
    STATUS          current
    DESCRIPTION     
            "The index of the ISUP Service Group circuit is defined for.."
    ::= { sonusIsupsgCircuitEntry 1 }

sonusIsupsgCircuitIdentityCode OBJECT-TYPE
    SYNTAX          Integer32 (0..16383)
    MAX-ACCESS      read-only
    STATUS          current
    DESCRIPTION     
            "Identifies the circuit identity code (CIC) for the circuit."
    ::= { sonusIsupsgCircuitEntry 2 }

sonusIsupsgCircuitServiceName OBJECT-TYPE
    SYNTAX          SonusNameReference
    MAX-ACCESS      read-write
    STATUS          current
    DESCRIPTION     
            "The name of the ISUP Service Group circuit is under."
    ::= { sonusIsupsgCircuitEntry 3 }

sonusIsupsgCircuitPortName OBJECT-TYPE
    SYNTAX          SonusNameReference
    MAX-ACCESS      read-write
    STATUS          current
    DESCRIPTION     
            "The name of the port circuit is on."
    ::= { sonusIsupsgCircuitEntry 4 }

sonusIsupsgCircuitChannel OBJECT-TYPE
    SYNTAX          Integer32 (1..32)
    MAX-ACCESS      read-write
    STATUS          current
    DESCRIPTION     
            "Identifies the channel the circuit represents."
    ::= { sonusIsupsgCircuitEntry 5 }

sonusIsupsgCircuitDirection OBJECT-TYPE
    SYNTAX          INTEGER { twoWay(1), oneWayIn(2), oneWayOut(3) }
    MAX-ACCESS      read-write
    STATUS          current
    DESCRIPTION     
            "Identifies the direction of traffic to be allowed on the circuit."
    ::= { sonusIsupsgCircuitEntry 6 }

sonusIsupsgCircuitMode OBJECT-TYPE
    SYNTAX          INTEGER { block(1), unblock(2), reset(3), cot(4) }
    MAX-ACCESS      read-write
    STATUS          current
    DESCRIPTION     
            "The mode of operation of the ISUP Circuit."
    ::= { sonusIsupsgCircuitEntry 7 }

sonusIsupsgCircuitAction OBJECT-TYPE
    SYNTAX          INTEGER { dryUp(1), force(2), undefined(3) }
    MAX-ACCESS      read-write
    STATUS          current
    DESCRIPTION     
            "The action taken on the ISUP Circuit."
    ::= { sonusIsupsgCircuitEntry 8 }

sonusIsupsgCircuitTimeout OBJECT-TYPE
    SYNTAX          Integer32 (0..1440)
    MAX-ACCESS      read-write
    STATUS          current
    DESCRIPTION     
            "The timeout value in minutes for dryup action on the ISUP Circuit."
    ::= { sonusIsupsgCircuitEntry 9 }

sonusIsupsgCircuitAdminState OBJECT-TYPE
    SYNTAX          SonusAdminState
    MAX-ACCESS      read-write
    STATUS          current
    DESCRIPTION     
            "The admin state of the ISUP Circuit."
    ::= { sonusIsupsgCircuitEntry 10 }

sonusIsupsgCircuitProfileName OBJECT-TYPE
    SYNTAX          SonusNameReference
    MAX-ACCESS      read-write
    STATUS          current
    DESCRIPTION     
            "The circuit profile name assigned to the ISUP circuit."
    ::= { sonusIsupsgCircuitEntry 11 }

sonusIsupsgCircuitRowStatus OBJECT-TYPE
    SYNTAX          RowStatus
    MAX-ACCESS      read-write
    STATUS          current
    DESCRIPTION     
            ""
    ::= { sonusIsupsgCircuitEntry 12 }

sonusIsupsgCircuitTrunkMember OBJECT-TYPE
    SYNTAX          Integer32 (0..65536)
    MAX-ACCESS      read-write
    STATUS          current
    DESCRIPTION     
            "Identifies the Trunk Member number assigned to the circuit.
             The value 65536 indicates no trunk member number is assigned. "
    DEFVAL          { 65536 }
    ::= { sonusIsupsgCircuitEntry 13 }

sonusIsupsgCircuitFarEndTestType OBJECT-TYPE
    SYNTAX          INTEGER { cqm(1), cvt(2), reset(3), undefined(4) }
    MAX-ACCESS      read-write
    STATUS          current
    DESCRIPTION     
            "The far end action taken on the ISUP Circuit."
    ::= { sonusIsupsgCircuitEntry 14 }

sonusIsupsgCircuitStatusBits OBJECT-TYPE
    SYNTAX          Integer32 (0..255)
    MAX-ACCESS      read-only
    STATUS          current
    DESCRIPTION     
            "Internal Status bits"
    DEFVAL          { 0 }
    ::= { sonusIsupsgCircuitEntry 15 }

sonusIsupsgCircuitPortId OBJECT-TYPE
    SYNTAX          Integer32 (0..16383)
    MAX-ACCESS      read-write
    STATUS          current
    DESCRIPTION     
            "Port Id identifies the port number on the slot."
    ::= { sonusIsupsgCircuitEntry 16 }

sonusIsupsgCircuitShelf OBJECT-TYPE
    SYNTAX          SonusShelfIndex
    MAX-ACCESS      read-write
    STATUS          current
    DESCRIPTION     
            "Identifies the shelf the circuit belongs to."
    ::= { sonusIsupsgCircuitEntry 17 }

sonusIsupsgCircuitSlot OBJECT-TYPE
    SYNTAX          SonusSlotIndex
    MAX-ACCESS      read-write
    STATUS          current
    DESCRIPTION     
            "Identifies the slot the circuit belongs to."
    ::= { sonusIsupsgCircuitEntry 18 }

sonusIsupsgCircuitStatTable OBJECT-TYPE
    SYNTAX          SEQUENCE OF SonusIsupsgCircuitStatEntry
    MAX-ACCESS      not-accessible
    STATUS          current
    DESCRIPTION     
            "This table contains status information about each ISUP circuit 
             in the GSX9000 Switch node.  ISUP circuits within the node can
             can be configured before SS7 connections is physically attached to
             the node.  The remote ISUP circuit may not be equipped or configured.
             Therefore, it is possible that an ISUP circuit can be unavailable,
             and is absent."
    ::= { sonusIsupServiceGroupMIBObjects 5 }

sonusIsupsgCircuitStatEntry OBJECT-TYPE
    SYNTAX          SonusIsupsgCircuitStatEntry
    MAX-ACCESS      not-accessible
    STATUS          current
    DESCRIPTION     
            "This table describes the status of the configured ISUP circuits."
    INDEX           { sonusIsupsgCircuitStatServiceListIndex, 
                      sonusIsupsgCircuitStatIdentityCode }
    ::= { sonusIsupsgCircuitStatTable 1 }

SonusIsupsgCircuitStatEntry ::=
    SEQUENCE {
        sonusIsupsgCircuitStatServiceListIndex      Integer32,
        sonusIsupsgCircuitStatIdentityCode  Integer32,
        sonusIsupsgCircuitStatUsage     INTEGER,
        sonusIsupsgCircuitStatLocalMaint INTEGER,
        sonusIsupsgCircuitStatLocalHw   INTEGER,
        sonusIsupsgCircuitStatRemoteMaint INTEGER,
        sonusIsupsgCircuitStatRemoteHw  INTEGER,
        sonusIsupsgCircuitStatManualCot INTEGER
    }

sonusIsupsgCircuitStatServiceListIndex OBJECT-TYPE
    SYNTAX          Integer32
    MAX-ACCESS      read-only
    STATUS          current
    DESCRIPTION     
            "The index of the ISUP Service Group circuit is defined for.."
    ::= { sonusIsupsgCircuitStatEntry 1 }

sonusIsupsgCircuitStatIdentityCode OBJECT-TYPE
    SYNTAX          Integer32 (0..16383)
    MAX-ACCESS      read-only
    STATUS          current
    DESCRIPTION     
            "Identifies the circuit identity code (CIC) for the circuit."
    ::= { sonusIsupsgCircuitStatEntry 2 }

sonusIsupsgCircuitStatUsage OBJECT-TYPE
    SYNTAX          INTEGER { unequipped(1), idle(2), inBusy(3), 
                        outBusy(4), transientSetup(5), 
                        transientRelease(6), inContinuity(7), 
                        outContinuity(8) }
    MAX-ACCESS      read-only
    STATUS          current
    DESCRIPTION     
            "The usage state of the ISUP circuit."
    ::= { sonusIsupsgCircuitStatEntry 3 }

sonusIsupsgCircuitStatLocalMaint OBJECT-TYPE
    SYNTAX          INTEGER { unblocked(1), blocked(2), 
                        transientUnblock(3), transientBlock(4), 
                        notAvailable(5) }
    MAX-ACCESS      read-only
    STATUS          current
    DESCRIPTION     
            "The local maintenance state of the ISUP circuit."
    ::= { sonusIsupsgCircuitStatEntry 4 }

sonusIsupsgCircuitStatLocalHw OBJECT-TYPE
    SYNTAX          INTEGER { unblocked(1), blocked(2), 
                        transientUnblock(3), transientBlock(4), 
                        notAvailable(5) }
    MAX-ACCESS      read-only
    STATUS          current
    DESCRIPTION     
            "The local hardware state of the ISUP circuit."
    ::= { sonusIsupsgCircuitStatEntry 5 }

sonusIsupsgCircuitStatRemoteMaint OBJECT-TYPE
    SYNTAX          INTEGER { unblocked(1), blocked(2), 
                        transientUnblock(3), transientBlock(4), 
                        notAvailable(5) }
    MAX-ACCESS      read-only
    STATUS          current
    DESCRIPTION     
            "The remote maintenance state of the ISUP circuit."
    ::= { sonusIsupsgCircuitStatEntry 6 }

sonusIsupsgCircuitStatRemoteHw OBJECT-TYPE
    SYNTAX          INTEGER { unblocked(1), blocked(2), 
                        transientUnblock(3), transientBlock(4), 
                        notAvailable(5) }
    MAX-ACCESS      read-only
    STATUS          current
    DESCRIPTION     
            "The remote hardware state of the ISUP circuit."
    ::= { sonusIsupsgCircuitStatEntry 7 }

sonusIsupsgCircuitStatManualCot OBJECT-TYPE
    SYNTAX          INTEGER { notAvailable(1), pending(2), inProgress(3), 
                        pass(4), fail(5), abort(6), lpaFail(7) }
    MAX-ACCESS      read-only
    STATUS          current
    DESCRIPTION     
            "The manual continuity test state of the ISUP circuit."
    ::= { sonusIsupsgCircuitStatEntry 8 }

sonusIsupsgFarEndCircuitAdminTable OBJECT-TYPE
    SYNTAX          SEQUENCE OF SonusIsupsgFarEndCircuitAdminEntry
    MAX-ACCESS      not-accessible
    STATUS          current
    DESCRIPTION     
            "This table contains administrative information of ISUP circuits on the 
             far end switch GSX is connected to. ISUP circuits should be configured
             on the GSX node to get the corresponding far end circuit admin info. The
             far end ISUP circuit may be not equipped or not configured. Therefore,
             it is possible that the far end info of an ISUP circuit would be unavailable."
    ::= { sonusIsupServiceGroupMIBObjects 6 }

sonusIsupsgFarEndCircuitAdminEntry OBJECT-TYPE
    SYNTAX          SonusIsupsgFarEndCircuitAdminEntry
    MAX-ACCESS      not-accessible
    STATUS          current
    DESCRIPTION     
            "This table describes the far end status of the ISUP circuits."
    INDEX           { sonusIsupsgFarEndCircuitServiceListIndex, 
                      sonusIsupsgFarEndCircuitIdentityCode }
    ::= { sonusIsupsgFarEndCircuitAdminTable 1 }

SonusIsupsgFarEndCircuitAdminEntry ::=
    SEQUENCE {
        sonusIsupsgFarEndCircuitServiceListIndex        Integer32,
        sonusIsupsgFarEndCircuitIdentityCode    Integer32,
        sonusIsupsgFarEndCircuitValidationTestResult            INTEGER,
        sonusIsupsgFarEndCircuitGroupCarrier    INTEGER,
        sonusIsupsgFarEndCircuitCicControl  INTEGER,
        sonusIsupsgFarEndCircuitAlarmCarrier    INTEGER,
        sonusIsupsgFarEndCircuitContinuityRequirement             INTEGER,
        sonusIsupsgFarEndCircuitIdentificationTrunkNumber                 SonusNameReference,
        sonusIsupsgFarEndCircuitIdentificationOfficeA             SonusNameReference,
        sonusIsupsgFarEndCircuitIdentificationOfficeZ             SonusNameReference,
        sonusIsupsgFarEndCircuitLocationIdentification              SonusNameReference,
        sonusIsupsgFarEndCircuitCicControlConflict          INTEGER,
        sonusIsupsgFarEndCircuitCmdInProgress     INTEGER,
        sonusIsupsgFarEndCircuitNumFailedCmds     Integer32,
        sonusIsupsgFarEndCircuitTimeStamp DateAndTime,
        sonusIsupsgFarEndCircuitLocalTrunkNumber        DisplayString
    }

sonusIsupsgFarEndCircuitServiceListIndex OBJECT-TYPE
    SYNTAX          Integer32
    MAX-ACCESS      read-only
    STATUS          current
    DESCRIPTION     
            "The index of the ISUP Service Group far end circuit is defined for."
    ::= { sonusIsupsgFarEndCircuitAdminEntry 1 }

sonusIsupsgFarEndCircuitIdentityCode OBJECT-TYPE
    SYNTAX          Integer32 (0..16383)
    MAX-ACCESS      read-only
    STATUS          current
    DESCRIPTION     
            "Identifies the circuit identity code (CIC) for the circuit."
    ::= { sonusIsupsgFarEndCircuitAdminEntry 2 }

sonusIsupsgFarEndCircuitValidationTestResult OBJECT-TYPE
    SYNTAX          INTEGER { noResponse(0), successful(1), failure(2), 
                        notAvailable(3) }
    MAX-ACCESS      read-only
    STATUS          current
    DESCRIPTION     
            "Result of the far end validation test on the circuit."
    ::= { sonusIsupsgFarEndCircuitAdminEntry 3 }

sonusIsupsgFarEndCircuitGroupCarrier OBJECT-TYPE
    SYNTAX          INTEGER { noResponse(0), unknown(1), analog(2), 
                        digital(3), digitalAndAnalog(4) }
    MAX-ACCESS      read-only
    STATUS          current
    DESCRIPTION     
            "Circuit group carrier indicator of the far end circuit."
    ::= { sonusIsupsgFarEndCircuitAdminEntry 4 }

sonusIsupsgFarEndCircuitCicControl OBJECT-TYPE
    SYNTAX          INTEGER { noResponse(0), noCics(1), oddCics(2), 
                        evenCics(3), allCics(4) }
    MAX-ACCESS      read-only
    STATUS          current
    DESCRIPTION     
            "Double seizing control indicator of the far end circuit group."
    ::= { sonusIsupsgFarEndCircuitAdminEntry 5 }

sonusIsupsgFarEndCircuitAlarmCarrier OBJECT-TYPE
    SYNTAX          INTEGER { noResponse(0), unknown(1), 
                        softwareCarrier(2), hardwareCarrier(3) }
    MAX-ACCESS      read-only
    STATUS          current
    DESCRIPTION     
            "Alarm carrier indicator of the far end circuit group."
    ::= { sonusIsupsgFarEndCircuitAdminEntry 6 }

sonusIsupsgFarEndCircuitContinuityRequirement OBJECT-TYPE
    SYNTAX          INTEGER { noResponse(0), unknown(1), none(2), 
                        statistical(3), perCall(4) }
    MAX-ACCESS      read-only
    STATUS          current
    DESCRIPTION     
            "Continuity check requirements of the far end circuit group."
    ::= { sonusIsupsgFarEndCircuitAdminEntry 7 }

sonusIsupsgFarEndCircuitIdentificationTrunkNumber OBJECT-TYPE
    SYNTAX          SonusNameReference
    MAX-ACCESS      read-only
    STATUS          current
    DESCRIPTION     
            "Trunk number of the far end circuit identification."
    ::= { sonusIsupsgFarEndCircuitAdminEntry 8 }

sonusIsupsgFarEndCircuitIdentificationOfficeA OBJECT-TYPE
    SYNTAX          SonusNameReference
    MAX-ACCESS      read-only
    STATUS          current
    DESCRIPTION     
            "Office identification for the far end circuit. [ Ref: ANSI T1.113/3.11A ]
             With respect to offices A and Z the following conventions are used:
             (a) For one-way trunk groups, the originating switch that offers traffic to the trunk group is office A.
             (b) For two-way trunk groups, the switch with the lower alphanumeric CLLI code is designated office A.
             (c) For one-way subgroups of a divided trunk group, the originating switch is designated office A.
             (d) For two-way subgroups of a divided trunk group, the switch with the lower alphanumeric CLLI code is designated office A."
    ::= { sonusIsupsgFarEndCircuitAdminEntry 9 }

sonusIsupsgFarEndCircuitIdentificationOfficeZ OBJECT-TYPE
    SYNTAX          SonusNameReference
    MAX-ACCESS      read-only
    STATUS          current
    DESCRIPTION     
            "Office identification for the far end circuit. [ Ref: ANSI T1.113/3.11A ]
             With respect to offices A and Z the following conventions are used:
             (a) For one-way trunk groups, the originating switch that offers traffic to the trunk group is office A.
             (b) For two-way trunk groups, the switch with the lower alphanumeric CLLI code is designated office A.
             (c) For one-way subgroups of a divided trunk group, the originating switch is designated office A.
             (d) For two-way subgroups of a divided trunk group, the switch with the lower alphanumeric CLLI code is designated office A."
    ::= { sonusIsupsgFarEndCircuitAdminEntry 10 }

sonusIsupsgFarEndCircuitLocationIdentification OBJECT-TYPE
    SYNTAX          SonusNameReference
    MAX-ACCESS      read-only
    STATUS          current
    DESCRIPTION     
            "Location identification of the far end circuit in CLLI( town/state/building/subdivision ) format."
    ::= { sonusIsupsgFarEndCircuitAdminEntry 11 }

sonusIsupsgFarEndCircuitCicControlConflict OBJECT-TYPE
    SYNTAX          INTEGER { noResponse(0), yes(1), no(2) }
    MAX-ACCESS      read-only
    STATUS          current
    DESCRIPTION     
            "Double seizing control for farend and nearend conflict indicator of the circuit group."
    ::= { sonusIsupsgFarEndCircuitAdminEntry 12 }

sonusIsupsgFarEndCircuitCmdInProgress OBJECT-TYPE
    SYNTAX          INTEGER { cmdComplete(0), cmdProgress(1) }
    MAX-ACCESS      read-only
    STATUS          current
    DESCRIPTION     
            "Status of last far end command (complete / processing )"
    ::= { sonusIsupsgFarEndCircuitAdminEntry 13 }

sonusIsupsgFarEndCircuitNumFailedCmds OBJECT-TYPE
    SYNTAX          Integer32
    MAX-ACCESS      read-only
    STATUS          current
    DESCRIPTION     
            "Number of no responses to far end admin commands."
    ::= { sonusIsupsgFarEndCircuitAdminEntry 14 }

sonusIsupsgFarEndCircuitTimeStamp OBJECT-TYPE
    SYNTAX          DateAndTime
    MAX-ACCESS      read-only
    STATUS          current
    DESCRIPTION     
            "Octet string that identifies the GMT time and date
             when the Far end admin command was issued.
             
             	field  octects  contents    			  range
             	-----  -------  --------      			  -----
             1      1-2    year                      0..65536
             2       3     month                     1..12
             3       4     day                       1..31
             4       5     hour                      0..23
              5       6     minutes                   0..59
             6       7     seconds                   0..60
                        (use 60 for leap-second)
             7       8     deci-seconds              0..9
             8       9     direction from UTC        '+' / '-'
             9      10     hours from UTC            0..11
             10      11     minutes from UTC          0..59
             
             For example, Tuesday May 26, 1992 at 1:30:15 PM EDT would be
             displayed as:
             
             1992-5-26,13:30:15.0,-4:0
             
             * Notes:
             - the value of year is in network-byte order"
    ::= { sonusIsupsgFarEndCircuitAdminEntry 15 }

sonusIsupsgFarEndCircuitLocalTrunkNumber OBJECT-TYPE
    SYNTAX          DisplayString (SIZE(4))
    MAX-ACCESS      read-only
    STATUS          current
    DESCRIPTION     
            "A unique number assigned to the trunk group by the customer, used for circuit 
             validation testing purposes. This is the local trunk number and is here for display only"
    ::= { sonusIsupsgFarEndCircuitAdminEntry 16 }

sonusIsupsgFarEndCircuitStatTable OBJECT-TYPE
    SYNTAX          SEQUENCE OF SonusIsupsgFarEndCircuitStatEntry
    MAX-ACCESS      not-accessible
    STATUS          current
    DESCRIPTION     
            "This table contains status information of ISUP circuits on the 
             far end switch GSX is connected to. ISUP circuits should be configured
             on the GSX node to get the corresponding far end circuit status. The
             far end ISUP circuit may be not equipped or not configured. Therefore,
             it is possible that the far end status of an ISUP circuit would be unavailable."
    ::= { sonusIsupServiceGroupMIBObjects 7 }

sonusIsupsgFarEndCircuitStatEntry OBJECT-TYPE
    SYNTAX          SonusIsupsgFarEndCircuitStatEntry
    MAX-ACCESS      not-accessible
    STATUS          current
    DESCRIPTION     
            "This table describes the far end status of the ISUP circuits."
    INDEX           { sonusIsupsgFarEndCircuitStatServiceListIndex, 
                      sonusIsupsgFarEndCircuitStatIdentityCode }
    ::= { sonusIsupsgFarEndCircuitStatTable 1 }

SonusIsupsgFarEndCircuitStatEntry ::=
    SEQUENCE {
        sonusIsupsgFarEndCircuitStatServiceListIndex            Integer32,
        sonusIsupsgFarEndCircuitStatIdentityCode        Integer32,
        sonusIsupsgFarEndCircuitStatStatus  INTEGER,
        sonusIsupsgFarEndCircuitStatLocalMaint      INTEGER,
        sonusIsupsgFarEndCircuitStatCmdInProgress         INTEGER,
        sonusIsupsgFarEndCircuitStatNumFailedCmds         Integer32,
        sonusIsupsgFarEndCircuitStatTimeStamp     DateAndTime
    }

sonusIsupsgFarEndCircuitStatServiceListIndex OBJECT-TYPE
    SYNTAX          Integer32
    MAX-ACCESS      read-only
    STATUS          current
    DESCRIPTION     
            "The index of the ISUP Service Group far end circuit is defined for."
    ::= { sonusIsupsgFarEndCircuitStatEntry 1 }

sonusIsupsgFarEndCircuitStatIdentityCode OBJECT-TYPE
    SYNTAX          Integer32 (0..16383)
    MAX-ACCESS      read-only
    STATUS          current
    DESCRIPTION     
            "Identifies the circuit identity code (CIC) for the circuit."
    ::= { sonusIsupsgFarEndCircuitStatEntry 2 }

sonusIsupsgFarEndCircuitStatStatus OBJECT-TYPE
    SYNTAX          INTEGER { noResponse(0), transient(1), unequipped(2), 
                        inbusyActive(3), inbusyLocalBlocked(4), 
                        inbusyRemoteBlocked(5), 
                        inbusyLocalRemoteBlocked(6), outbusyActive(7), 
                        outbusyLocalBlocked(8), outbusyRemoteBlocked(9), 
                        outbusyLocalRemoteBlocked(10), idle(11), 
                        idleLocalBlocked(12), idleRemoteBlocked(13), 
                        idleLocalRemoteBlocked(14), notAvailable(15), 
                        idleLocalHWBlocked(16), idleRemoteHWBlocked(17), 
                        idleLocalRemoteHWBlocked(18), 
                        idleLocalHWAndLocalMaintBlocked(19), 
                        idleRemoteHWAndLocalMaintBlocked(20), 
                        idleLocalRemoteHWAndLocalMaintBlocked(21), 
                        idleLocalHWAndRemoteMaintBlocked(22), 
                        idleRemoteHWAndRemoteMaintBlocked(23), 
                        idleLocalRemoteHWAndRemoteMaintBlocked(24), 
                        idleLocalHWAndLocalRemoteMaintBlocked(25), 
                        idleRemoteHWAndLocalRemoteMaintBlocked(26), 
                        idleLocalRemoteHWAndLocalRemoteMaintBlocked(27) }
    MAX-ACCESS      read-only
    STATUS          current
    DESCRIPTION     
            "The far end status of the ISUP circuit."
    ::= { sonusIsupsgFarEndCircuitStatEntry 3 }

sonusIsupsgFarEndCircuitStatLocalMaint OBJECT-TYPE
    SYNTAX          INTEGER { unblocked(1), blocked(2), 
                        transientUnblock(3), transientBlock(4), 
                        notAvailable(5) }
    MAX-ACCESS      read-only
    STATUS          current
    DESCRIPTION     
            "The local maintenance state of the ISUP circuit."
    ::= { sonusIsupsgFarEndCircuitStatEntry 4 }

sonusIsupsgFarEndCircuitStatCmdInProgress OBJECT-TYPE
    SYNTAX          INTEGER { cmdComplete(0), cmdProgress(1) }
    MAX-ACCESS      read-only
    STATUS          current
    DESCRIPTION     
            "Status of last far end command (complete / processing )"
    ::= { sonusIsupsgFarEndCircuitStatEntry 5 }

sonusIsupsgFarEndCircuitStatNumFailedCmds OBJECT-TYPE
    SYNTAX          Integer32
    MAX-ACCESS      read-only
    STATUS          current
    DESCRIPTION     
            "Number of failed  far end admin commands since last completed command."
    ::= { sonusIsupsgFarEndCircuitStatEntry 6 }

sonusIsupsgFarEndCircuitStatTimeStamp OBJECT-TYPE
    SYNTAX          DateAndTime
    MAX-ACCESS      read-only
    STATUS          current
    DESCRIPTION     
            "Octet string that identifies the GMT time and date
             when the Far end status command was issued.
             
             	field  octects  contents    			  range
             	-----  -------  --------      			  -----
             1      1-2    year                      0..65536
             2       3     month                     1..12
             3       4     day                       1..31
             4       5     hour                      0..23
              5       6     minutes                   0..59
             6       7     seconds                   0..60
                        (use 60 for leap-second)
             7       8     deci-seconds              0..9
             8       9     direction from UTC        '+' / '-'
             9      10     hours from UTC            0..11
             10      11     minutes from UTC          0..59
             
             For example, Tuesday May 26, 1992 at 1:30:15 PM EDT would be
             displayed as:
             
             1992-5-26,13:30:15.0,-4:0
             
             * Notes:
             - the value of year is in network-byte order"
    ::= { sonusIsupsgFarEndCircuitStatEntry 7 }

sonusIsupsgSignalingProfile OBJECT IDENTIFIER
    ::= { sonusIsupServiceGroupMIBObjects 8 }

sonusIsupsgSignalingProfileNextIndex OBJECT-TYPE
    SYNTAX          Integer32
    MAX-ACCESS      read-only
    STATUS          current
    DESCRIPTION     
            "The next valid index to use when creating a new sonusIsupsgSignalingProfileEntry"
    ::= { sonusIsupsgSignalingProfile 1 }

sonusIsupsgSignalingProfileTable OBJECT-TYPE
    SYNTAX          SEQUENCE OF SonusIsupsgSignalingProfileEntry
    MAX-ACCESS      not-accessible
    STATUS          current
    DESCRIPTION     
            "This table contains information about each ISUP Signaling Profile
             configured to be a member of the node. 
             A management entity may create rows for Signaling Profile that are
             anticipated to be supported in the future."
    ::= { sonusIsupsgSignalingProfile 2 }

sonusIsupsgSignalingProfileEntry OBJECT-TYPE
    SYNTAX          SonusIsupsgSignalingProfileEntry
    MAX-ACCESS      not-accessible
    STATUS          current
    DESCRIPTION     
            "This table describes the ISUP Signaling Profile that are configured."
    INDEX           { sonusIsupsgSignalingProfileListIndex }
    ::= { sonusIsupsgSignalingProfileTable 1 }

SonusIsupsgSignalingProfileEntry ::=
    SEQUENCE {
        sonusIsupsgSignalingProfileListIndex    Integer32,
        sonusIsupsgSignalingProfileName SonusName,
        sonusIsupsgSignalingProfileCompat SonusSupportFlag,
        sonusIsupsgSignalingProfileAccessDel    SonusSupportFlag,
        sonusIsupsgSignalingProfileGenNum SonusSupportFlag,
        sonusIsupsgSignalingProfileGenNotif   SonusSupportFlag,
        sonusIsupsgSignalingProfileGenDigs  SonusSupportFlag,
        sonusIsupsgSignalingProfileLocNum SonusSupportFlag,
        sonusIsupsgSignalingProfileOrigIscPC    SonusSupportFlag,
        sonusIsupsgSignalingProfileUserTeleService          SonusSupportFlag,
        sonusIsupsgSignalingProfileSegmentation       SonusSupportFlag,
        sonusIsupsgSignalingProfileFallback   SonusSupportFlag,
        sonusIsupsgSignalingProfilePropDelay    SonusSupportFlag,
        sonusIsupsgSignalingProfileEMcid SonusSupportFlag,
        sonusIsupsgSignalingProfileHopCounter     SonusSupportFlag,
        sonusIsupsgSignalingProfileSubPriorityCls         SonusSupportFlag,
        sonusIsupsgSignalingProfileAPM  SonusSupportFlag,
        sonusIsupsgSignalingProfileConNumInAcm      SonusSupportFlag,
        sonusIsupsgSignalingProfileCauseInCpg     SonusSupportFlag,
        sonusIsupsgSignalingProfileMultiCarrierEnv          SonusSupportFlag,
        sonusIsupsgSignalingProfileCarrierSelection           SonusSupportFlag,
        sonusIsupsgSignalingProfileInrInf SonusSupportFlag,
        sonusIsupsgSignalingProfileCqmCqr SonusSupportFlag,
        sonusIsupsgSignalingProfileCallRef  SonusSupportFlag,
        sonusIsupsgSignalingProfileCfn  SonusSupportFlag,
        sonusIsupsgSignalingProfileFacility   SonusSupportFlag,
        sonusIsupsgSignalingProfilePam  SonusSupportFlag,
        sonusIsupsgSignalingProfileObciAnm  SonusSupportFlag,
        sonusIsupsgSignalingProfileDrs  SonusSupportFlag,
        sonusIsupsgSignalingProfileRedNum SonusSupportFlag,
        sonusIsupsgSignalingProfileLpa  SonusSupportFlag,
        sonusIsupsgSignalingProfileUcic SonusSupportFlag,
        sonusIsupsgSignalingProfileOlm  SonusSupportFlag,
        sonusIsupsgSignalingProfileBBRel SonusSupportFlag,
        sonusIsupsgSignalingProfileUsr  SonusSupportFlag,
        sonusIsupsgSignalingProfileBBIam SonusSupportFlag,
        sonusIsupsgSignalingProfileCallModMsgs      SonusSupportFlag,
        sonusIsupsgSignalingProfileCallDiv  SonusSupportFlag,
        sonusIsupsgSignalingProfileCallHist   SonusSupportFlag,
        sonusIsupsgSignalingProfileGenRef SonusSupportFlag,
        sonusIsupsgSignalingProfileMLPP SonusSupportFlag,
        sonusIsupsgSignalingProfileNSF  SonusSupportFlag,
        sonusIsupsgSignalingProfileRedNumRist     SonusSupportFlag,
        sonusIsupsgSignalingProfileRemoteOp   SonusSupportFlag,
        sonusIsupsgSignalingProfileServActv   SonusSupportFlag,
        sonusIsupsgSignalingProfileSigPointCode       SonusSupportFlag,
        sonusIsupsgSignalingProfileTmrPrime   SonusSupportFlag,
        sonusIsupsgSignalingProfileTransMedUsed       SonusSupportFlag,
        sonusIsupsgSignalingProfileUsiPrime   SonusSupportFlag,
        sonusIsupsgSignalingProfileRedNumInAcm      SonusSupportFlag,
        sonusIsupsgSignalingProfileRedNumInAnm      SonusSupportFlag,
        sonusIsupsgSignalingProfileUuiInRel   SonusSupportFlag,
        sonusIsupsgSignalingProfileConReqInFaa      SonusSupportFlag,
        sonusIsupsgSignalingProfileConReqInFar      SonusSupportFlag,
        sonusIsupsgSignalingProfileFac  SonusSupportFlag,
        sonusIsupsgSignalingProfileEchoControl      SonusSupportFlag,
        sonusIsupsgSignalingProfileBackwardGVNS       SonusSupportFlag,
        sonusIsupsgSignalingProfileCircAssMap     SonusSupportFlag,
        sonusIsupsgSignalingProfileCCSS SonusSupportFlag,
        sonusIsupsgSignalingProfileCallDivTreat       SonusSupportFlag,
        sonusIsupsgSignalingProfileCalledInNum      SonusSupportFlag,
        sonusIsupsgSignalingProfileCollectCallReq         SonusSupportFlag,
        sonusIsupsgSignalingProfileConfTreat    SonusSupportFlag,
        sonusIsupsgSignalingProfileCorrelationId        SonusSupportFlag,
        sonusIsupsgSignalingProfileCallOfrTreat       SonusSupportFlag,
        sonusIsupsgSignalingProfileCallTransNum       SonusSupportFlag,
        sonusIsupsgSignalingProfileCallTransRef       SonusSupportFlag,
        sonusIsupsgSignalingProfileDispInfo   SonusSupportFlag,
        sonusIsupsgSignalingProfileForwardGVNS      SonusSupportFlag,
        sonusIsupsgSignalingProfileLoopPrevention         SonusSupportFlag,
        sonusIsupsgSignalingProfileNetworkMgmt      SonusSupportFlag,
        sonusIsupsgSignalingProfileSCFId SonusSupportFlag,
        sonusIsupsgSignalingProfileUIDActionInd       SonusSupportFlag,
        sonusIsupsgSignalingProfileUIDCapInd    SonusSupportFlag,
        sonusIsupsgSignalingProfileConNumInCpg      SonusSupportFlag,
        sonusIsupsgSignalingProfileGenNumInCpg      SonusSupportFlag,
        sonusIsupsgSignalingProfileEchoCntrlInIam         SonusSupportFlag,
        sonusIsupsgSignalingProfileRemoteOpInRel        SonusSupportFlag,
        sonusIsupsgSignalingProfileAccessTransInFac           SonusSupportFlag,
        sonusIsupsgSignalingProfileGenNotifInFac        SonusSupportFlag,
        sonusIsupsgSignalingProfileUuindAnm   SonusSupportFlag,
        sonusIsupsgSignalingProfileUuindCpg   SonusSupportFlag,
        sonusIsupsgSignalingProfileNrmSupport     SonusSupportFlag,
        sonusIsupsgSignalingProfileCseInRlc   SonusSupportFlag,
        sonusIsupsgSignalingProfileUpaUpt SonusSupportFlag,
        sonusIsupsgSignalingProfileRecInCai   SonusSupportFlag,
        sonusIsupsgSignalingProfileTransitUnrec       SonusSupportFlag,
        sonusIsupsgSignalingProfileCcRaw SonusSupportFlag,
        sonusIsupsgSignalingProfileCctGrpBlockFlag          SonusSupportFlag,
        sonusIsupsgSignalingProfileCctGrpResetFlag          SonusSupportFlag,
        sonusIsupsgSignalingProfileBaseProfileName          SonusNameReference,
        sonusIsupsgSignalingProfileAdminState     SonusAdminState,
        sonusIsupsgSignalingProfileRowStatus    RowStatus,
        sonusIsupsgSignalingProfilePropDelayValue         Integer32,
        sonusIsupsgSignalingProfileU2USrvcLevel       INTEGER,
        sonusIsupsgSignalingProfileSAM  SonusSupportFlag,
        sonusIsupsgSignalingProfileFOT  SonusSupportFlag,
        sonusIsupsgSignalingProfileSpecialDigits        BITS,
        sonusIsupsgSignalingProfileTNS  SonusSupportFlag,
        sonusIsupsgSignalingProfileAwaitDigits      SonusSupportFlag,
        sonusIsupsgSignalingProfileAccessTrans      SonusSupportFlag,
        sonusIsupsgSignalingProfileJurisdiction       SonusSupportFlag,
        sonusIsupsgSignalingProfileOCN  SonusSupportFlag,
        sonusIsupsgSignalingProfileBusinessGrp      SonusSupportFlag,
        sonusIsupsgSignalingProfileConReq SonusSupportFlag,
        sonusIsupsgSignalingProfileInfoInd  SonusSupportFlag,
        sonusIsupsgSignalingProfileNtp  SonusSupportFlag,
        sonusIsupsgSignalingProfileNotifInd   SonusSupportFlag,
        sonusIsupsgSignalingProfileRedInfoAcm     SonusSupportFlag,
        sonusIsupsgSignalingProfileEgressService        SonusSupportFlag,
        sonusIsupsgSignalingProfileServCodeInd      SonusSupportFlag,
        sonusIsupsgSignalingProfileSpecProcReq      SonusSupportFlag,
        sonusIsupsgSignalingProfileTransReq   SonusSupportFlag,
        sonusIsupsgSignalingProfileChgNum SonusSupportFlag,
        sonusIsupsgSignalingProfileGenAddressREL        SonusSupportFlag,
        sonusIsupsgSignalingProfileUUIndAcm   SonusSupportFlag,
        sonusIsupsgSignalingProfileUUInfo SonusSupportFlag,
        sonusIsupsgSignalingProfileOperatorServInfo           SonusSupportFlag,
        sonusIsupsgSignalingProfileCvtCvr SonusSupportFlag,
        sonusIsupsgSignalingProfileGenName  SonusSupportFlag,
        sonusIsupsgSignalingProfileRedCap SonusSupportFlag,
        sonusIsupsgSignalingProfileRedCount   SonusSupportFlag,
        sonusIsupsgSignalingProfileSendTwoGrpMsgs         SonusSupportFlag,
        sonusIsupsgSignalingProfileAwaitTwoGrpMsgs          SonusSupportFlag,
        sonusIsupsgSignalingProfileCqmOnCardSwap        SonusSupportFlag,
        sonusIsupsgSignalingProfileAnsi95Grs    SonusSupportFlag,
        sonusIsupsgSignalingProfileCpgBeforeAcm       SonusSupportFlag,
        sonusIsupsgSignalingProfileMapDmsFeParameter            SonusSupportFlag,
        sonusIsupsgSignalingProfileTKOsupport     SonusSupportFlag,
        sonusIsupsgSignalingProfileOPSELIsupport        SonusSupportFlag,
        sonusIsupsgSignalingProfileMaxCallingPartyDigits                Integer32,
        sonusIsupsgSignalingProfileMaxCalledPartyDigits               Integer32,
        sonusIsupsgSignalingProfileFreephoneInd       SonusSupportFlag,
        sonusIsupsgSignalingProfileItxTxa SonusSupportFlag,
        sonusIsupsgSignalingProfileSCCPProcedure        SonusSupportFlag,
        sonusIsupsgSignalingProfileCnrInIAM   SonusSupportFlag,
        sonusIsupsgSignalingProfileCcnr SonusSupportFlag,
        sonusIsupsgSignalingProfileTransitCFN     SonusSupportFlag,
        sonusIsupsgSignalingProfileHoldingInd     SonusSupportFlag,
        sonusIsupsgSignalingProfileDispInfoInAcm        SonusSupportFlag,
        sonusIsupsgSignalingProfileDispInfoInCon        SonusSupportFlag,
        sonusIsupsgSignalingProfileDispInfoInCpg        SonusSupportFlag,
        sonusIsupsgSignalingProfileDispInfoInIam        SonusSupportFlag,
        sonusIsupsgSignalingProfileGenNumInAcm      SonusSupportFlag,
        sonusIsupsgSignalingProfileGenNumInFac      SonusSupportFlag,
        sonusIsupsgSignalingProfileGenNumInInf      SonusSupportFlag,
        sonusIsupsgSignalingProfileConfTreatInAnm         SonusSupportFlag,
        sonusIsupsgSignalingProfileContinuity     SonusSupportFlag,
        sonusIsupsgSignalingProfileUSI  SonusSupportFlag,
        sonusIsupsgSignalingProfileConnectedNum       SonusSupportFlag,
        sonusIsupsgSignalingProfileDiagnostics      SonusSupportFlag,
        sonusIsupsgSignalingProfileOptionalFCI      SonusSupportFlag,
        sonusIsupsgSignalingProfileClosedUserGroupIC            SonusSupportFlag,
        sonusIsupsgSignalingProfileCom  SonusSupportFlag,
        sonusIsupsgSignalingProfileCon  SonusSupportFlag,
        sonusIsupsgSignalingProfileIriOriRcv    SonusSupportFlag,
        sonusIsupsgSignalingProfileIriOriSent     SonusSupportFlag,
        sonusIsupsgSignalingProfileT11Active    SonusSupportFlag,
        sonusIsupsgSignalingProfileIriOri SonusSupportFlag,
        sonusIsupsgSignalingProfileTransMedUsedInNrm            SonusSupportFlag,
        sonusIsupsgSignalingProfileRlcAckGrs    SonusSupportFlag,
        sonusIsupsgSignalingProfileIncomingTrunkIdCode              SonusSupportFlag,
        sonusIsupsgSignalingProfileSpcInIrs   SonusSupportFlag,
        sonusIsupsgSignalingProfileRedInfoIam     SonusSupportFlag,
        sonusIsupsgSignalingProfileRedirectingNum         SonusSupportFlag,
        sonusIsupsgSignalingProfileSendBloAfterSetup            SonusSupportFlag,
        sonusIsupsgSignalingProfileCalledDirectoryNum             SonusSupportFlag,
        sonusIsupsgSignalingProfileT6Release    Integer32,
        sonusIsupsgSignalingProfileT7Release    Integer32,
        sonusIsupsgSignalingProfileFwdCpg SonusSupportFlag,
        sonusIsupsgSignalingProfileFwdSus SonusSupportFlag,
        sonusIsupsgSignalingProfileUUInfoAcm    SonusSupportFlag,
        sonusIsupsgSignalingProfileATRel SonusSupportFlag,
        sonusIsupsgSignalingProfileUUIndRel   SonusSupportFlag,
        sonusIsupsgSignalingProfileEIT  SonusSupportFlag,
        sonusIsupsgSignalingProfileGI   SonusSupportFlag,
        sonusIsupsgSignalingProfileTIT  SonusSupportFlag,
        sonusIsupsgSignalingProfileAIT  SonusSupportFlag,
        sonusIsupsgSignalingProfileTCI  SonusSupportFlag,
        sonusIsupsgSignalingProfileNFT  SonusSupportFlag,
        sonusIsupsgSignalingProfileCPNRel SonusSupportFlag,
        sonusIsupsgSignalingProfileBCIRel SonusSupportFlag,
        sonusIsupsgSignalingProfileCI   SonusSupportFlag,
        sonusIsupsgSignalingProfileIUI  SonusSupportFlag,
        sonusIsupsgSignalingProfileNROP SonusSupportFlag,
        sonusIsupsgSignalingProfileMSI  SonusSupportFlag,
        sonusIsupsgSignalingProfileRR   SonusSupportFlag,
        sonusIsupsgSignalingProfileMI   SonusSupportFlag,
        sonusIsupsgSignalingProfileSPC6 SonusSupportFlag,
        sonusIsupsgSignalingProfileMARel SonusSupportFlag,
        sonusIsupsgSignalingProfileConReqInInf      SonusSupportFlag,
        sonusIsupsgSignalingProfileSgmPci SonusSupportFlag,
        sonusIsupsgSignalingProfileGR317ScreeningInd            SonusSupportFlag,
        sonusIsupsgSignalingProfileOpr  SonusSupportFlag,
        sonusIsupsgSignalingProfileCcl  SonusSupportFlag,
        sonusIsupsgSignalingProfileOtherDigitStringSpecialDigitF                        SonusSupportFlag,
        sonusIsupsgSignalingProfileCallRefFrj     SonusSupportFlag,
        sonusIsupsgSignalingProfilePCIPassOnDefault           INTEGER,
        sonusIsupsgSignalingProfileOTGNAnsi92     SonusSupportFlag,
        sonusIsupsgSignalingProfileMsgSendDelay       Integer32,
        sonusIsupsgSignalingProfileDropCauseInAcmWhenIwk                SonusSupportFlag,
        sonusIsupsgSignalingProfileChargeIndSetting           INTEGER,
        sonusIsupsgSignalingProfileT11EarlyAcm      SonusSupportFlag,
        sonusIsupsgSignalingProfileDmsFe SonusSupportFlag,
        sonusIsupsgSignalingProfileCqmForResync       SonusSupportFlag,
        sonusIsupsgSignalingProfileNCR  SonusSupportFlag,
        sonusIsupsgSignalingProfileSLIInIAM   SonusSupportFlag,
        sonusIsupsgSignalingProfileReleaseLinkTrunking              SonusSupportFlag,
        sonusIsupsgSignalingProfileAccessTransInFAR           SonusSupportFlag,
        sonusIsupsgSignalingProfileUUIndInFAR     SonusSupportFlag,
        sonusIsupsgSignalingProfileTGNumSource      INTEGER,
        sonusIsupsgSignalingProfileUPVExchangeRoles           BITS,
        sonusIsupsgSignalingProfileCdBsm SonusSupportFlag,
        sonusIsupsgSignalingProfileCgBsm SonusSupportFlag,
        sonusIsupsgSignalingProfileCgOfm SonusSupportFlag,
        sonusIsupsgSignalingProfileCdTfm SonusSupportFlag,
        sonusIsupsgSignalingProfileNii  SonusSupportFlag,
        sonusIsupsgSignalingProfileNiri SonusSupportFlag,
        sonusIsupsgSignalingProfileNfci SonusSupportFlag,
        sonusIsupsgSignalingProfilePresNum  SonusSupportFlag,
        sonusIsupsgSignalingProfileLdli SonusSupportFlag,
        sonusIsupsgSignalingProfilePcli SonusSupportFlag,
        sonusIsupsgSignalingProfileNfciLnk  SonusSupportFlag,
        sonusIsupsgSignalingProfileInrInAllStates         SonusSupportFlag,
        sonusIsupsgSignalingProfileNfciLnkProc      SonusSupportFlag,
        sonusIsupsgSignalingProfileAnsi95Cfn    SonusSupportFlag,
        sonusIsupsgSignalingProfileAllianceScreenInd            SonusSupportFlag,
        sonusIsupsgSignalingProfileAnnouncementInd          SonusSupportFlag,
        sonusIsupsgSignalingProfileDialedNumber       SonusSupportFlag,
        sonusIsupsgSignalingProfileForwardNetworkSpecificInfo                     SonusSupportFlag,
        sonusIsupsgSignalingProfileGenericOperation           SonusSupportFlag,
        sonusIsupsgSignalingProfileHardToReachInd         SonusSupportFlag,
        sonusIsupsgSignalingProfileNetworkManagementInfo                SonusSupportFlag,
        sonusIsupsgSignalingProfileNetworkSwitchNumber              SonusSupportFlag,
        sonusIsupsgSignalingProfileRoutingInformationInd                SonusSupportFlag,
        sonusIsupsgSignalingProfileSdnIncrement       SonusSupportFlag,
        sonusIsupsgSignalingProfileAnsi95Cqm    SonusSupportFlag,
        sonusIsupsgSignalingProfileBCM  SonusSupportFlag,
        sonusIsupsgSignalingProfileJpnEmergencyCall           SonusSupportFlag,
        sonusIsupsgSignalingProfileGenNumRepeatable           SonusSupportFlag,
        sonusIsupsgSignalingProfileGenNumIamRepeatable              SonusSupportFlag,
        sonusIsupsgSignalingProfileGenNotifRepeatable             SonusSupportFlag,
        sonusIsupsgSignalingProfileServActvInRel        SonusSupportFlag,
        sonusIsupsgSignalingProfileUuindCon   SonusSupportFlag,
        sonusIsupsgSignalingProfileUuiInInf   SonusSupportFlag,
        sonusIsupsgSignalingProfileChargeMsgInSpeech            SonusSupportFlag,
        sonusIsupsgSignalingProfileEmergencyCallInf           SonusSupportFlag,
        sonusIsupsgSignalingProfileT7Transit    SonusSupportFlag,
        sonusIsupsgSignalingProfileNSA  SonusSupportFlag,
        sonusIsupsgSignalingProfileInvTNSRelease        SonusSupportFlag,
        sonusIsupsgSignalingProfileJTSpecificParam          SonusSupportFlag,
        sonusIsupsgSignalingProfileIsdnUserPartIwk          SonusSupportFlag,
        sonusIsupsgSignalingProfileIsdnUserPartTrans            SonusSupportFlag,
        sonusIsupsgSignalingProfileConnectionPointTrunkType                   SonusSupportFlag,
        sonusIsupsgSignalingProfileIsdnUserPartChosenCarrier                    SonusSupportFlag,
        sonusIsupsgSignalingProfileMaxCqmRange      Integer32,
        sonusIsupsgSignalingProfileTruncateCDPN       SonusSupportFlag,
        sonusIsupsgSignalingProfileNoIPEchoInd      SonusSupportFlag,
        sonusIsupsgSignalingProfileVisitorMA    SonusSupportFlag,
        sonusIsupsgSignalingProfileSendBLOOnHwBlock           SonusSupportFlag,
        sonusIsupsgSignalingProfileAllowCallsOnHwBlock              SonusSupportFlag,
        sonusIsupsgSignalingProfileOBCIPreSubscriptionOnly                  SonusSupportFlag,
        sonusIsupsgSignalingProfileSendRSCForCallsOnHwBlock                   SonusSupportFlag,
        sonusIsupsgSignalingProfileAllowUnscreenedCIN             SonusSupportFlag,
        sonusIsupsgSignalingProfileIAMGenCarrierCodeInCDR                 SonusSupportFlag,
        sonusIsupsgSignalingProfileDropUSIFromNonIsup             SonusSupportFlag,
        sonusIsupsgSignalingProfileAssumeOgDeviceIncluded                 SonusSupportFlag,
        sonusIsupsgSignalingProfilePreventACMtoCPGMapping                 SonusSupportFlag,
        sonusIsupsgSignalingProfileSignalOnlySipAlert             SonusSupportFlag,
        sonusIsupsgSignalingProfileDontMapToHeaderToOCN               SonusSupportFlag,
        sonusIsupsgSignalingProfileNoINNumberUpdates            SonusSupportFlag,
        sonusIsupsgSignalingProfileUsePSXChgIndForCpgInPresubCall                         SonusSupportFlag,
        sonusIsupsgSignalingProfileAlwaysAddOptionalPtr               SonusSupportFlag,
        sonusIsupsgSignalingProfileSuppressCITForPreSubACM                  SonusSupportFlag,
        sonusIsupsgSignalingProfileSendOnlyACMFor181            SonusSupportFlag,
        sonusIsupsgSignalingProfileDontSendEXM      SonusSupportFlag,
        sonusIsupsgSignalingProfileCITTermExchangeLogic               SonusSupportFlag,
        sonusIsupsgSignalingProfileBCIinCPGwithCIT          SonusSupportFlag,
        sonusIsupsgSignalingProfileReaffirmBlockAfterReset                  SonusSupportFlag,
        sonusIsupsgSignalingProfileDontGenerateDiags            SonusSupportFlag,
        sonusIsupsgSignalingProfileOnlyCPGInbandBeforeACM                 SonusSupportFlag,
        sonusIsupsgSignalingProfileSimpleEcBCIInAllBkMsg                SonusSupportFlag,
        sonusIsupsgSignalingProfileAllowCAForAnnouncements                  SonusSupportFlag,
        sonusIsupsgSignalingProfileUniqueTransitCIT           SonusSupportFlag,
        sonusIsupsgSignalingProfileValidateISUBFromSIP              SonusSupportFlag,
        sonusIsupsgSignalingProfileISUBTypeFromSIP          INTEGER,
        sonusIsupsgSignalingProfileQOR  SonusSupportFlag,
        sonusIsupsgSignalingProfileNPFI SonusSupportFlag,
        sonusIsupsgSignalingProfileChgMsgBeforeAcm          SonusSupportFlag,
        sonusIsupsgSignalingProfileForceEchoCntrl         SonusSupportFlag,
        sonusIsupsgSignalingProfileNoObciSipAcm       SonusSupportFlag,
        sonusIsupsgSignalingProfileBuildRdiForSipIwk            SonusSupportFlag,
        sonusIsupsgSignalingProfileNoAcmObciForSipApn             SonusSupportFlag,
        sonusIsupsgSignalingProfileNetworkData      SonusSupportFlag,
        sonusIsupsgSignalingProfileAlwaysAddCNID        SonusSupportFlag,
        sonusIsupsgSignalingProfileCHGBetweenACMandANM              SonusSupportFlag,
        sonusIsupsgSignalingProfileItuCAI24   SonusSupportFlag,
        sonusIsupsgSignalingProfileCellularCPCs       SonusSupportFlag,
        sonusIsupsgSignalingProfileIepsCPC  SonusSupportFlag,
        sonusIsupsgSignalingProfileTandemCallCounter            SonusSupportFlag,
        sonusIsupsgSignalingProfileRouteInformation           SonusSupportFlag,
        sonusIsupsgSignalingProfileNoCHGCountIfFlexChgRate                  SonusSupportFlag,
        sonusIsupsgSignalingProfileRemoveHlcIfNoLlc           SonusSupportFlag,
        sonusIsupsgSignalingProfileUpdateANMBCI       SonusSupportFlag,
        sonusIsupsgSignalingProfileDiscardContractorNum               SonusSupportFlag,
        sonusIsupsgSignalingProfileAddInfoTransfer          SonusSupportFlag,
        sonusIsupsgSignalingProfileADPNumber    SonusSupportFlag,
        sonusIsupsgSignalingProfileTransferInfo       SonusSupportFlag,
        sonusIsupsgSignalingProfileDPC  SonusSupportFlag,
        sonusIsupsgSignalingProfileUUIRestrictions          SonusSupportFlag,
        sonusIsupsgSignalingProfileCalledNoa8ForNp          SonusSupportFlag,
        sonusIsupsgSignalingProfileDontClearCdrFields             SonusSupportFlag,
        sonusIsupsgSignalingProfileSaveIamCIT     SonusSupportFlag,
        sonusIsupsgSignalingProfileStoreChargeForIXCTCTypeAndPayPhone                             SonusSupportFlag,
        sonusIsupsgSignalingProfileDPCInfo  SonusSupportFlag,
        sonusIsupsgSignalingProfileRELForDuplicateIAM             SonusSupportFlag,
        sonusIsupsgSignalingProfileRELforEarlyANM         SonusSupportFlag,
        sonusIsupsgSignalingProfileForceEchoCntrlNoUpdate                 SonusSupportFlag,
        sonusIsupsgSignalingProfileEarlyACMChgNoInd           SonusSupportFlag,
        sonusIsupsgSignalingProfileTransitReceivedCIT             SonusSupportFlag,
        sonusIsupsgSignalingProfileOnlyScreenCITGen           SonusSupportFlag,
        sonusIsupsgSignalingProfileSlovakChargeMessage              SonusSupportFlag,
        sonusIsupsgSignalingProfileECITrap  SonusSupportFlag,
        sonusIsupsgSignalingProfileCheckIXCAgainstTLEC              SonusSupportFlag,
        sonusIsupsgSignalingProfileRedNumRistInRel          SonusSupportFlag,
        sonusIsupsgSignalingProfileScreenCITBeforeCDR             SonusSupportFlag,
        sonusIsupsgSignalingProfileRussiaRng    SonusSupportFlag,
        sonusIsupsgSignalingProfileOverrideInband         SonusSupportFlag,
        sonusIsupsgSignalingProfileSendingEnbloc        SonusSupportFlag,
        sonusIsupsgSignalingProfileBloUbl SonusSupportFlag,
        sonusIsupsgSignalingProfileBillableCallForConwithNonCharge                          SonusSupportFlag,
        sonusIsupsgSignalingProfileINNWithinCdPN        INTEGER,
        sonusIsupsgSignalingProfileNIWithinCgPN       INTEGER,
        sonusIsupsgSignalingProfileUpdateChargeInd          INTEGER,
        sonusIsupsgSignalingProfileColpColrIGW      SonusSupportFlag,
        sonusIsupsgSignalingProfileForeignSpecialRoutingIndicator                         INTEGER,
        sonusIsupsgSignalingProfileInternationCarrierRoutingIndicator                             INTEGER,
        sonusIsupsgSignalingProfileNumberRangeBlockingIndicator                       INTEGER,
        sonusIsupsgSignalingProfileNpUkkSupportedInEgress                 SonusSupportFlag,
        sonusIsupsgSignalingProfileNpSspSupportedInEgress                 SonusSupportFlag,
        sonusIsupsgSignalingProfileNpUkkSupportedInIngress                  SonusSupportFlag,
        sonusIsupsgSignalingProfileNpSspSupportedInIngress                  SonusSupportFlag,
        sonusIsupsgSignalingProfileChargeInfoITXCdr           SonusSupportFlag,
        sonusIsupsgSignalingProfileGCR  SonusSupportFlag,
        sonusIsupsgSignalingProfileRemoteMnpDip       SonusSupportFlag,
        sonusIsupsgSignalingProfileDropAPPinIAM       SonusSupportFlag,
        sonusIsupsgSignalingProfileNIWithinCgPNDirection                INTEGER,
        sonusIsupsgSignalingProfileAllowSgdInGdp        INTEGER,
        sonusIsupsgSignalingProfileRNRInACM   SonusSupportFlag,
        sonusIsupsgSignalingProfileRNRInCPG   SonusSupportFlag,
        sonusIsupsgSignalingProfileRNRInANM   SonusSupportFlag,
        sonusIsupsgSignalingProfileHistInfo   SonusSupportFlag,
        sonusIsupsgSignalingProfileStoreChargeRateInformation                     SonusSupportFlag,
        sonusIsupsgSignalingProfileMnpTransferMethod            SonusSupportFlag
    }

sonusIsupsgSignalingProfileListIndex OBJECT-TYPE
    SYNTAX          Integer32 (1..128)
    MAX-ACCESS      read-only
    STATUS          current
    DESCRIPTION     
            "The index of the ISUP Signaling Profile entry."
    ::= { sonusIsupsgSignalingProfileEntry 1 }

sonusIsupsgSignalingProfileName OBJECT-TYPE
    SYNTAX          SonusName
    MAX-ACCESS      read-write
    STATUS          current
    DESCRIPTION     
            "The name of the ISUP Signaling Profile."
    ::= { sonusIsupsgSignalingProfileEntry 2 }

sonusIsupsgSignalingProfileCompat OBJECT-TYPE
    SYNTAX          SonusSupportFlag
    MAX-ACCESS      read-write
    STATUS          current
    DESCRIPTION     
            "Is compatibility supported for the ISUP Signaling Profile."
    ::= { sonusIsupsgSignalingProfileEntry 3 }

sonusIsupsgSignalingProfileAccessDel OBJECT-TYPE
    SYNTAX          SonusSupportFlag
    MAX-ACCESS      read-write
    STATUS          current
    DESCRIPTION     
            "Is Access Delivery Information supported for the ISUP Signaling Profile."
    ::= { sonusIsupsgSignalingProfileEntry 4 }

sonusIsupsgSignalingProfileGenNum OBJECT-TYPE
    SYNTAX          SonusSupportFlag
    MAX-ACCESS      read-write
    STATUS          current
    DESCRIPTION     
            "Is the generic number parameter supported for the ISUP Signaling Profile."
    ::= { sonusIsupsgSignalingProfileEntry 5 }

sonusIsupsgSignalingProfileGenNotif OBJECT-TYPE
    SYNTAX          SonusSupportFlag
    MAX-ACCESS      read-write
    STATUS          current
    DESCRIPTION     
            "Is the generic notification parameter supported for the ISUP Signaling Profile."
    ::= { sonusIsupsgSignalingProfileEntry 6 }

sonusIsupsgSignalingProfileGenDigs OBJECT-TYPE
    SYNTAX          SonusSupportFlag
    MAX-ACCESS      read-write
    STATUS          current
    DESCRIPTION     
            "Is the generic digits parameter supported for the ISUP Signaling Profile."
    ::= { sonusIsupsgSignalingProfileEntry 7 }

sonusIsupsgSignalingProfileLocNum OBJECT-TYPE
    SYNTAX          SonusSupportFlag
    MAX-ACCESS      read-write
    STATUS          current
    DESCRIPTION     
            "Is the location number parameter supported for the ISUP Signaling Profile."
    ::= { sonusIsupsgSignalingProfileEntry 8 }

sonusIsupsgSignalingProfileOrigIscPC OBJECT-TYPE
    SYNTAX          SonusSupportFlag
    MAX-ACCESS      read-write
    STATUS          current
    DESCRIPTION     
            "Is the originating ISC point code parameter supported for the ISUP Signaling Profile."
    ::= { sonusIsupsgSignalingProfileEntry 9 }

sonusIsupsgSignalingProfileUserTeleService OBJECT-TYPE
    SYNTAX          SonusSupportFlag
    MAX-ACCESS      read-write
    STATUS          current
    DESCRIPTION     
            "Is the user teleservice parameter supported for the ISUP Signaling Profile."
    ::= { sonusIsupsgSignalingProfileEntry 10 }

sonusIsupsgSignalingProfileSegmentation OBJECT-TYPE
    SYNTAX          SonusSupportFlag
    MAX-ACCESS      read-write
    STATUS          current
    DESCRIPTION     
            "Is segmentation supported for the ISUP Signaling Profile."
    ::= { sonusIsupsgSignalingProfileEntry 11 }

sonusIsupsgSignalingProfileFallback OBJECT-TYPE
    SYNTAX          SonusSupportFlag
    MAX-ACCESS      read-write
    STATUS          current
    DESCRIPTION     
            "Is fallback supported for the ISUP Signaling Profile."
    ::= { sonusIsupsgSignalingProfileEntry 12 }

sonusIsupsgSignalingProfilePropDelay OBJECT-TYPE
    SYNTAX          SonusSupportFlag
    MAX-ACCESS      read-write
    STATUS          current
    DESCRIPTION     
            "Is propagation delay supported for the ISUP Signaling Profile."
    ::= { sonusIsupsgSignalingProfileEntry 13 }

sonusIsupsgSignalingProfileEMcid OBJECT-TYPE
    SYNTAX          SonusSupportFlag
    MAX-ACCESS      read-write
    STATUS          current
    DESCRIPTION     
            "Is MCID supported for the ISUP Signaling Profile."
    ::= { sonusIsupsgSignalingProfileEntry 14 }

sonusIsupsgSignalingProfileHopCounter OBJECT-TYPE
    SYNTAX          SonusSupportFlag
    MAX-ACCESS      read-write
    STATUS          current
    DESCRIPTION     
            "Is the hop counter supported for the ISUP Signaling Profile."
    ::= { sonusIsupsgSignalingProfileEntry 15 }

sonusIsupsgSignalingProfileSubPriorityCls OBJECT-TYPE
    SYNTAX          SonusSupportFlag
    MAX-ACCESS      read-write
    STATUS          current
    DESCRIPTION     
            "Is the subscriber priority class parameter supported for the ISUP Signaling Profile."
    ::= { sonusIsupsgSignalingProfileEntry 16 }

sonusIsupsgSignalingProfileAPM OBJECT-TYPE
    SYNTAX          SonusSupportFlag
    MAX-ACCESS      read-write
    STATUS          current
    DESCRIPTION     
            "Is APM supported for the ISUP Signaling Profile."
    ::= { sonusIsupsgSignalingProfileEntry 17 }

sonusIsupsgSignalingProfileConNumInAcm OBJECT-TYPE
    SYNTAX          SonusSupportFlag
    MAX-ACCESS      read-write
    STATUS          current
    DESCRIPTION     
            "Is the connected number parameter supported in the ACM for the ISUP Signaling Profile."
    ::= { sonusIsupsgSignalingProfileEntry 18 }

sonusIsupsgSignalingProfileCauseInCpg OBJECT-TYPE
    SYNTAX          SonusSupportFlag
    MAX-ACCESS      read-write
    STATUS          current
    DESCRIPTION     
            "Is the cause parameter supported in the CPG for the ISUP Signaling Profile."
    ::= { sonusIsupsgSignalingProfileEntry 19 }

sonusIsupsgSignalingProfileMultiCarrierEnv OBJECT-TYPE
    SYNTAX          SonusSupportFlag
    MAX-ACCESS      read-write
    STATUS          current
    DESCRIPTION     
            "Is the multi carrier environment parameter supported for the ISUP Signaling Profile."
    ::= { sonusIsupsgSignalingProfileEntry 20 }

sonusIsupsgSignalingProfileCarrierSelection OBJECT-TYPE
    SYNTAX          SonusSupportFlag
    MAX-ACCESS      read-write
    STATUS          current
    DESCRIPTION     
            "Is carrier selection supported for the ISUP Signaling Profile."
    ::= { sonusIsupsgSignalingProfileEntry 21 }

sonusIsupsgSignalingProfileInrInf OBJECT-TYPE
    SYNTAX          SonusSupportFlag
    MAX-ACCESS      read-write
    STATUS          current
    DESCRIPTION     
            "Is INR/INF supported for the ISUP Signaling Profile."
    ::= { sonusIsupsgSignalingProfileEntry 22 }

sonusIsupsgSignalingProfileCqmCqr OBJECT-TYPE
    SYNTAX          SonusSupportFlag
    MAX-ACCESS      read-write
    STATUS          current
    DESCRIPTION     
            "Is CQM/CQR supported for the ISUP Signaling Profile."
    ::= { sonusIsupsgSignalingProfileEntry 23 }

sonusIsupsgSignalingProfileCallRef OBJECT-TYPE
    SYNTAX          SonusSupportFlag
    MAX-ACCESS      read-write
    STATUS          current
    DESCRIPTION     
            "Is the call reference parameter supported for the ISUP Signaling Profile."
    ::= { sonusIsupsgSignalingProfileEntry 24 }

sonusIsupsgSignalingProfileCfn OBJECT-TYPE
    SYNTAX          SonusSupportFlag
    MAX-ACCESS      read-write
    STATUS          current
    DESCRIPTION     
            "Is CFN supported for the ISUP Signaling Profile."
    ::= { sonusIsupsgSignalingProfileEntry 25 }

sonusIsupsgSignalingProfileFacility OBJECT-TYPE
    SYNTAX          SonusSupportFlag
    MAX-ACCESS      read-write
    STATUS          current
    DESCRIPTION     
            "Are FAA, FAR and FRJ supported for the ISUP Signaling Profile."
    ::= { sonusIsupsgSignalingProfileEntry 26 }

sonusIsupsgSignalingProfilePam OBJECT-TYPE
    SYNTAX          SonusSupportFlag
    MAX-ACCESS      read-write
    STATUS          current
    DESCRIPTION     
            "Is PAM supported for the ISUP Signaling Profile."
    ::= { sonusIsupsgSignalingProfileEntry 27 }

sonusIsupsgSignalingProfileObciAnm OBJECT-TYPE
    SYNTAX          SonusSupportFlag
    MAX-ACCESS      read-write
    STATUS          current
    DESCRIPTION     
            "Is the OBCI parameter supported in the ANM for the ISUP Signaling Profile."
    ::= { sonusIsupsgSignalingProfileEntry 28 }

sonusIsupsgSignalingProfileDrs OBJECT-TYPE
    SYNTAX          SonusSupportFlag
    MAX-ACCESS      read-write
    STATUS          current
    DESCRIPTION     
            "Is DRS supported the ISUP Signaling Profile."
    ::= { sonusIsupsgSignalingProfileEntry 29 }

sonusIsupsgSignalingProfileRedNum OBJECT-TYPE
    SYNTAX          SonusSupportFlag
    MAX-ACCESS      read-write
    STATUS          current
    DESCRIPTION     
            "Is the redirection number parameter supported for the ISUP Signaling Profile."
    ::= { sonusIsupsgSignalingProfileEntry 30 }

sonusIsupsgSignalingProfileLpa OBJECT-TYPE
    SYNTAX          SonusSupportFlag
    MAX-ACCESS      read-write
    STATUS          current
    DESCRIPTION     
            "Is LPA supported for the ISUP Signaling Profile."
    ::= { sonusIsupsgSignalingProfileEntry 31 }

sonusIsupsgSignalingProfileUcic OBJECT-TYPE
    SYNTAX          SonusSupportFlag
    MAX-ACCESS      read-write
    STATUS          current
    DESCRIPTION     
            "Is UCIC supported for the ISUP Signaling Profile."
    ::= { sonusIsupsgSignalingProfileEntry 32 }

sonusIsupsgSignalingProfileOlm OBJECT-TYPE
    SYNTAX          SonusSupportFlag
    MAX-ACCESS      read-write
    STATUS          current
    DESCRIPTION     
            "Is OLM supported for the ISUP Signaling Profile."
    ::= { sonusIsupsgSignalingProfileEntry 33 }

sonusIsupsgSignalingProfileBBRel OBJECT-TYPE
    SYNTAX          SonusSupportFlag
    MAX-ACCESS      read-write
    STATUS          current
    DESCRIPTION     
            "Are Blue Book parameters supported in REL for the ISUP Signaling Profile."
    ::= { sonusIsupsgSignalingProfileEntry 34 }

sonusIsupsgSignalingProfileUsr OBJECT-TYPE
    SYNTAX          SonusSupportFlag
    MAX-ACCESS      read-write
    STATUS          current
    DESCRIPTION     
            "Is USR supported for the ISUP Signaling Profile."
    ::= { sonusIsupsgSignalingProfileEntry 35 }

sonusIsupsgSignalingProfileBBIam OBJECT-TYPE
    SYNTAX          SonusSupportFlag
    MAX-ACCESS      read-write
    STATUS          current
    DESCRIPTION     
            "Is User-To-User ind parameter supported in IAM for the ISUP Signaling Profile."
    ::= { sonusIsupsgSignalingProfileEntry 36 }

sonusIsupsgSignalingProfileCallModMsgs OBJECT-TYPE
    SYNTAX          SonusSupportFlag
    MAX-ACCESS      read-write
    STATUS          current
    DESCRIPTION     
            "Are CMR, CMA and CMRJ supported for the ISUP Signaling Profile."
    ::= { sonusIsupsgSignalingProfileEntry 37 }

sonusIsupsgSignalingProfileCallDiv OBJECT-TYPE
    SYNTAX          SonusSupportFlag
    MAX-ACCESS      read-write
    STATUS          current
    DESCRIPTION     
            "Is call diversion supported for the ISUP Signaling Profile."
    ::= { sonusIsupsgSignalingProfileEntry 38 }

sonusIsupsgSignalingProfileCallHist OBJECT-TYPE
    SYNTAX          SonusSupportFlag
    MAX-ACCESS      read-write
    STATUS          current
    DESCRIPTION     
            "Is the call history parameter supported for the ISUP Signaling Profile."
    ::= { sonusIsupsgSignalingProfileEntry 39 }

sonusIsupsgSignalingProfileGenRef OBJECT-TYPE
    SYNTAX          SonusSupportFlag
    MAX-ACCESS      read-write
    STATUS          current
    DESCRIPTION     
            "Is the generic reference parameter supported for the ISUP Signaling Profile."
    ::= { sonusIsupsgSignalingProfileEntry 40 }

sonusIsupsgSignalingProfileMLPP OBJECT-TYPE
    SYNTAX          SonusSupportFlag
    MAX-ACCESS      read-write
    STATUS          current
    DESCRIPTION     
            "Is the MLPP parameter supported for the ISUP Signaling Profile."
    ::= { sonusIsupsgSignalingProfileEntry 41 }

sonusIsupsgSignalingProfileNSF OBJECT-TYPE
    SYNTAX          SonusSupportFlag
    MAX-ACCESS      read-write
    STATUS          current
    DESCRIPTION     
            "Is the NSF parameter supported for the ISUP Signaling Profile."
    ::= { sonusIsupsgSignalingProfileEntry 42 }

sonusIsupsgSignalingProfileRedNumRist OBJECT-TYPE
    SYNTAX          SonusSupportFlag
    MAX-ACCESS      read-write
    STATUS          current
    DESCRIPTION     
            "Is the redirection number restriction parameter supported for the ISUP Signaling Profile."
    ::= { sonusIsupsgSignalingProfileEntry 43 }

sonusIsupsgSignalingProfileRemoteOp OBJECT-TYPE
    SYNTAX          SonusSupportFlag
    MAX-ACCESS      read-write
    STATUS          current
    DESCRIPTION     
            "Is the remote operations parameter supported for the ISUP Signaling Profile."
    ::= { sonusIsupsgSignalingProfileEntry 44 }

sonusIsupsgSignalingProfileServActv OBJECT-TYPE
    SYNTAX          SonusSupportFlag
    MAX-ACCESS      read-write
    STATUS          current
    DESCRIPTION     
            "Is the service activation parameter supported for the ISUP Signaling Profile."
    ::= { sonusIsupsgSignalingProfileEntry 45 }

sonusIsupsgSignalingProfileSigPointCode OBJECT-TYPE
    SYNTAX          SonusSupportFlag
    MAX-ACCESS      read-write
    STATUS          current
    DESCRIPTION     
            "Is the signaling point code parameter supported for the ISUP Signaling Profile."
    ::= { sonusIsupsgSignalingProfileEntry 46 }

sonusIsupsgSignalingProfileTmrPrime OBJECT-TYPE
    SYNTAX          SonusSupportFlag
    MAX-ACCESS      read-write
    STATUS          current
    DESCRIPTION     
            "Is the TMR prime parameter supported for the ISUP Signaling Profile."
    ::= { sonusIsupsgSignalingProfileEntry 47 }

sonusIsupsgSignalingProfileTransMedUsed OBJECT-TYPE
    SYNTAX          SonusSupportFlag
    MAX-ACCESS      read-write
    STATUS          current
    DESCRIPTION     
            "Is the transimission medium used parameter supported for the ISUP Signaling Profile."
    ::= { sonusIsupsgSignalingProfileEntry 48 }

sonusIsupsgSignalingProfileUsiPrime OBJECT-TYPE
    SYNTAX          SonusSupportFlag
    MAX-ACCESS      read-write
    STATUS          current
    DESCRIPTION     
            "Is the USI prime parameter supported for the ISUP Signaling Profile."
    ::= { sonusIsupsgSignalingProfileEntry 49 }

sonusIsupsgSignalingProfileRedNumInAcm OBJECT-TYPE
    SYNTAX          SonusSupportFlag
    MAX-ACCESS      read-write
    STATUS          current
    DESCRIPTION     
            "Is the rediction number supported in the ACM for the ISUP Signaling Profile."
    ::= { sonusIsupsgSignalingProfileEntry 50 }

sonusIsupsgSignalingProfileRedNumInAnm OBJECT-TYPE
    SYNTAX          SonusSupportFlag
    MAX-ACCESS      read-write
    STATUS          current
    DESCRIPTION     
            "Is the rediretion number supported in the ANM for the ISUP Signaling Profile."
    ::= { sonusIsupsgSignalingProfileEntry 51 }

sonusIsupsgSignalingProfileUuiInRel OBJECT-TYPE
    SYNTAX          SonusSupportFlag
    MAX-ACCESS      read-write
    STATUS          deprecated
    DESCRIPTION     
            "This field is only required in 6.1 onwards for parameter loading upgrade"
    ::= { sonusIsupsgSignalingProfileEntry 52 }

sonusIsupsgSignalingProfileConReqInFaa OBJECT-TYPE
    SYNTAX          SonusSupportFlag
    MAX-ACCESS      read-write
    STATUS          current
    DESCRIPTION     
            "Is the connection request parameter supported in the FAA for the ISUP Signaling Profile."
    ::= { sonusIsupsgSignalingProfileEntry 53 }

sonusIsupsgSignalingProfileConReqInFar OBJECT-TYPE
    SYNTAX          SonusSupportFlag
    MAX-ACCESS      read-write
    STATUS          current
    DESCRIPTION     
            "Is the connection request parameter supported in the FAR for the ISUP Signaling Profile."
    ::= { sonusIsupsgSignalingProfileEntry 54 }

sonusIsupsgSignalingProfileFac OBJECT-TYPE
    SYNTAX          SonusSupportFlag
    MAX-ACCESS      read-write
    STATUS          current
    DESCRIPTION     
            "Is the FAC supported for the ISUP Signaling Profile."
    ::= { sonusIsupsgSignalingProfileEntry 55 }

sonusIsupsgSignalingProfileEchoControl OBJECT-TYPE
    SYNTAX          SonusSupportFlag
    MAX-ACCESS      read-write
    STATUS          current
    DESCRIPTION     
            "Is the echo control parameter supported for the ISUP Signaling Profile."
    ::= { sonusIsupsgSignalingProfileEntry 56 }

sonusIsupsgSignalingProfileBackwardGVNS OBJECT-TYPE
    SYNTAX          SonusSupportFlag
    MAX-ACCESS      read-write
    STATUS          current
    DESCRIPTION     
            "Is the backward GVNS parameter supported for the ISUP Signaling Profile."
    ::= { sonusIsupsgSignalingProfileEntry 57 }

sonusIsupsgSignalingProfileCircAssMap OBJECT-TYPE
    SYNTAX          SonusSupportFlag
    MAX-ACCESS      read-write
    STATUS          current
    DESCRIPTION     
            "Is the circuit assignment map parameter supported for the ISUP Signaling Profile."
    ::= { sonusIsupsgSignalingProfileEntry 58 }

sonusIsupsgSignalingProfileCCSS OBJECT-TYPE
    SYNTAX          SonusSupportFlag
    MAX-ACCESS      read-write
    STATUS          current
    DESCRIPTION     
            "Is the CCSS parameter supported for the ISUP Signaling Profile."
    ::= { sonusIsupsgSignalingProfileEntry 59 }

sonusIsupsgSignalingProfileCallDivTreat OBJECT-TYPE
    SYNTAX          SonusSupportFlag
    MAX-ACCESS      read-write
    STATUS          current
    DESCRIPTION     
            "Is the call diversion treatment parameter supported for the ISUP Signaling Profile."
    ::= { sonusIsupsgSignalingProfileEntry 60 }

sonusIsupsgSignalingProfileCalledInNum OBJECT-TYPE
    SYNTAX          SonusSupportFlag
    MAX-ACCESS      read-write
    STATUS          current
    DESCRIPTION     
            "Is the called IN number parameter supported for the ISUP Signaling Profile."
    ::= { sonusIsupsgSignalingProfileEntry 61 }

sonusIsupsgSignalingProfileCollectCallReq OBJECT-TYPE
    SYNTAX          SonusSupportFlag
    MAX-ACCESS      read-write
    STATUS          current
    DESCRIPTION     
            "Is the collect call request parameter supported for the ISUP Signaling Profile."
    ::= { sonusIsupsgSignalingProfileEntry 62 }

sonusIsupsgSignalingProfileConfTreat OBJECT-TYPE
    SYNTAX          SonusSupportFlag
    MAX-ACCESS      read-write
    STATUS          current
    DESCRIPTION     
            "Is the conference treatment parameter supported for the ISUP Signaling Profile."
    ::= { sonusIsupsgSignalingProfileEntry 63 }

sonusIsupsgSignalingProfileCorrelationId OBJECT-TYPE
    SYNTAX          SonusSupportFlag
    MAX-ACCESS      read-write
    STATUS          current
    DESCRIPTION     
            "Is the correlation ID parameter supported for the ISUP Signaling Profile."
    ::= { sonusIsupsgSignalingProfileEntry 64 }

sonusIsupsgSignalingProfileCallOfrTreat OBJECT-TYPE
    SYNTAX          SonusSupportFlag
    MAX-ACCESS      read-write
    STATUS          current
    DESCRIPTION     
            "Is the call offering treatment parameter supported for the ISUP Signaling Profile."
    ::= { sonusIsupsgSignalingProfileEntry 65 }

sonusIsupsgSignalingProfileCallTransNum OBJECT-TYPE
    SYNTAX          SonusSupportFlag
    MAX-ACCESS      read-write
    STATUS          current
    DESCRIPTION     
            "Is the call transfer number paramaeter supported for the ISUP Signaling Profile."
    ::= { sonusIsupsgSignalingProfileEntry 66 }

sonusIsupsgSignalingProfileCallTransRef OBJECT-TYPE
    SYNTAX          SonusSupportFlag
    MAX-ACCESS      read-write
    STATUS          current
    DESCRIPTION     
            "Is the call transfer reference parameter supported for the ISUP Signaling Profile."
    ::= { sonusIsupsgSignalingProfileEntry 67 }

sonusIsupsgSignalingProfileDispInfo OBJECT-TYPE
    SYNTAX          SonusSupportFlag
    MAX-ACCESS      read-write
    STATUS          current
    DESCRIPTION     
            "Is the display information parameter supported for the ISUP Signaling Profile."
    ::= { sonusIsupsgSignalingProfileEntry 68 }

sonusIsupsgSignalingProfileForwardGVNS OBJECT-TYPE
    SYNTAX          SonusSupportFlag
    MAX-ACCESS      read-write
    STATUS          current
    DESCRIPTION     
            "Is the forward GVNS parameter supported for the ISUP Signaling Profile."
    ::= { sonusIsupsgSignalingProfileEntry 69 }

sonusIsupsgSignalingProfileLoopPrevention OBJECT-TYPE
    SYNTAX          SonusSupportFlag
    MAX-ACCESS      read-write
    STATUS          current
    DESCRIPTION     
            "Is the loop prevention indicators parameter supported for the ISUP Signaling Profile."
    ::= { sonusIsupsgSignalingProfileEntry 70 }

sonusIsupsgSignalingProfileNetworkMgmt OBJECT-TYPE
    SYNTAX          SonusSupportFlag
    MAX-ACCESS      read-write
    STATUS          current
    DESCRIPTION     
            "Is network management controls parameter supported for the ISUP Signaling Profile."
    ::= { sonusIsupsgSignalingProfileEntry 71 }

sonusIsupsgSignalingProfileSCFId OBJECT-TYPE
    SYNTAX          SonusSupportFlag
    MAX-ACCESS      read-write
    STATUS          current
    DESCRIPTION     
            "Is the SCF ID parameter supported for the ISUP Signaling Profile."
    ::= { sonusIsupsgSignalingProfileEntry 72 }

sonusIsupsgSignalingProfileUIDActionInd OBJECT-TYPE
    SYNTAX          SonusSupportFlag
    MAX-ACCESS      read-write
    STATUS          current
    DESCRIPTION     
            "Is the UID action indicators parameter supported for the ISUP Signaling Profile."
    ::= { sonusIsupsgSignalingProfileEntry 73 }

sonusIsupsgSignalingProfileUIDCapInd OBJECT-TYPE
    SYNTAX          SonusSupportFlag
    MAX-ACCESS      read-write
    STATUS          current
    DESCRIPTION     
            "Is the UID capabilities parameter supported for the ISUP Signaling Profile."
    ::= { sonusIsupsgSignalingProfileEntry 74 }

sonusIsupsgSignalingProfileConNumInCpg OBJECT-TYPE
    SYNTAX          SonusSupportFlag
    MAX-ACCESS      read-write
    STATUS          current
    DESCRIPTION     
            "Is the connected number parameter supported in the CPG for the ISUP Signaling Profile."
    ::= { sonusIsupsgSignalingProfileEntry 75 }

sonusIsupsgSignalingProfileGenNumInCpg OBJECT-TYPE
    SYNTAX          SonusSupportFlag
    MAX-ACCESS      read-write
    STATUS          current
    DESCRIPTION     
            "Is the generic number parameter supported in the CPG for  the ISUP Signaling Profile."
    ::= { sonusIsupsgSignalingProfileEntry 76 }

sonusIsupsgSignalingProfileEchoCntrlInIam OBJECT-TYPE
    SYNTAX          SonusSupportFlag
    MAX-ACCESS      read-write
    STATUS          current
    DESCRIPTION     
            "Is the echo control parameter supported in the IAM for the ISUP Signaling Profile."
    ::= { sonusIsupsgSignalingProfileEntry 77 }

sonusIsupsgSignalingProfileRemoteOpInRel OBJECT-TYPE
    SYNTAX          SonusSupportFlag
    MAX-ACCESS      read-write
    STATUS          current
    DESCRIPTION     
            "Is the remote operations parameter supported in the REL for the ISUP Signaling Profile."
    ::= { sonusIsupsgSignalingProfileEntry 78 }

sonusIsupsgSignalingProfileAccessTransInFac OBJECT-TYPE
    SYNTAX          SonusSupportFlag
    MAX-ACCESS      read-write
    STATUS          current
    DESCRIPTION     
            "Is the access transport parameter supported in the FAC for the ISUP Signaling Profile."
    ::= { sonusIsupsgSignalingProfileEntry 79 }

sonusIsupsgSignalingProfileGenNotifInFac OBJECT-TYPE
    SYNTAX          SonusSupportFlag
    MAX-ACCESS      read-write
    STATUS          current
    DESCRIPTION     
            "Is the generic notification parameter supported for the ISUP Signaling Profile."
    ::= { sonusIsupsgSignalingProfileEntry 80 }

sonusIsupsgSignalingProfileUuindAnm OBJECT-TYPE
    SYNTAX          SonusSupportFlag
    MAX-ACCESS      read-write
    STATUS          current
    DESCRIPTION     
            "Is the UUI parameter supported in the ANM for the ISUP Signaling Profile."
    ::= { sonusIsupsgSignalingProfileEntry 81 }

sonusIsupsgSignalingProfileUuindCpg OBJECT-TYPE
    SYNTAX          SonusSupportFlag
    MAX-ACCESS      read-write
    STATUS          current
    DESCRIPTION     
            "Is the UUI parameter supported in the CPG for the ISUP Signaling Profile."
    ::= { sonusIsupsgSignalingProfileEntry 82 }

sonusIsupsgSignalingProfileNrmSupport OBJECT-TYPE
    SYNTAX          SonusSupportFlag
    MAX-ACCESS      read-write
    STATUS          current
    DESCRIPTION     
            "Is the NRM supported for the ISUP Signaling Profile."
    ::= { sonusIsupsgSignalingProfileEntry 83 }

sonusIsupsgSignalingProfileCseInRlc OBJECT-TYPE
    SYNTAX          SonusSupportFlag
    MAX-ACCESS      read-write
    STATUS          current
    DESCRIPTION     
            "Is the cause parameter supported in the RLC for the ISUP Signaling Profile."
    ::= { sonusIsupsgSignalingProfileEntry 84 }

sonusIsupsgSignalingProfileUpaUpt OBJECT-TYPE
    SYNTAX          SonusSupportFlag
    MAX-ACCESS      read-write
    STATUS          current
    DESCRIPTION     
            "Are UPA/UPT supported for the ISUP Signaling Profile."
    ::= { sonusIsupsgSignalingProfileEntry 85 }

sonusIsupsgSignalingProfileRecInCai OBJECT-TYPE
    SYNTAX          SonusSupportFlag
    MAX-ACCESS      read-write
    STATUS          current
    DESCRIPTION     
            "Is the recommnedation field supported in the cause parameter for the ISUP Signaling Profile."
    ::= { sonusIsupsgSignalingProfileEntry 86 }

sonusIsupsgSignalingProfileTransitUnrec OBJECT-TYPE
    SYNTAX          SonusSupportFlag
    MAX-ACCESS      read-write
    STATUS          current
    DESCRIPTION     
            "Is the transiting of unrecognised parameters supported for the ISUP service Group."
    ::= { sonusIsupsgSignalingProfileEntry 87 }

sonusIsupsgSignalingProfileCcRaw OBJECT-TYPE
    SYNTAX          SonusSupportFlag
    MAX-ACCESS      read-write
    STATUS          obsolete
    DESCRIPTION     
            "Should raw ISUP messages be sent to CC for the ISUP Signaling Profile - Obsolete version 7.2 onwards."
    ::= { sonusIsupsgSignalingProfileEntry 88 }

sonusIsupsgSignalingProfileCctGrpBlockFlag OBJECT-TYPE
    SYNTAX          SonusSupportFlag
    MAX-ACCESS      read-write
    STATUS          current
    DESCRIPTION     
            "The flag to be set to allow CGB and CGU messages in the ISUP Signaling Profile."
    DEFVAL          { supported }
    ::= { sonusIsupsgSignalingProfileEntry 89 }

sonusIsupsgSignalingProfileCctGrpResetFlag OBJECT-TYPE
    SYNTAX          SonusSupportFlag
    MAX-ACCESS      read-write
    STATUS          current
    DESCRIPTION     
            "The flag to be set to allow GRS messages in the ISUP Signaling Profile."
    DEFVAL          { supported }
    ::= { sonusIsupsgSignalingProfileEntry 90 }

sonusIsupsgSignalingProfileBaseProfileName OBJECT-TYPE
    SYNTAX          SonusNameReference
    MAX-ACCESS      read-write
    STATUS          current
    DESCRIPTION     
            "The ISUP Signaling Profile used as a base for the settings of this Signaling Profile."
    ::= { sonusIsupsgSignalingProfileEntry 91 }

sonusIsupsgSignalingProfileAdminState OBJECT-TYPE
    SYNTAX          SonusAdminState
    MAX-ACCESS      read-write
    STATUS          current
    DESCRIPTION     
            "The admin state of the ISUP Signaling Profile."
    ::= { sonusIsupsgSignalingProfileEntry 92 }

sonusIsupsgSignalingProfileRowStatus OBJECT-TYPE
    SYNTAX          RowStatus
    MAX-ACCESS      read-write
    STATUS          current
    DESCRIPTION     
            ""
    ::= { sonusIsupsgSignalingProfileEntry 93 }

sonusIsupsgSignalingProfilePropDelayValue OBJECT-TYPE
    SYNTAX          Integer32 (0..400)
    MAX-ACCESS      read-write
    STATUS          current
    DESCRIPTION     
            "The propagation delay value in milliseconds for this ISUP signaling profile."
    DEFVAL          { 0 }
    ::= { sonusIsupsgSignalingProfileEntry 94 }

sonusIsupsgSignalingProfileU2USrvcLevel OBJECT-TYPE
    SYNTAX          INTEGER { none(0), level1(1), level2(2), level3(3), 
                        implicit(4) }
    MAX-ACCESS      read-write
    STATUS          current
    DESCRIPTION     
            "The level of user to user services supported in the the ISUP Signaling Profile."
    DEFVAL          { none }
    ::= { sonusIsupsgSignalingProfileEntry 95 }

sonusIsupsgSignalingProfileSAM OBJECT-TYPE
    SYNTAX          SonusSupportFlag
    MAX-ACCESS      read-write
    STATUS          current
    DESCRIPTION     
            "Is the Subsequent Address Message supported for the ISUP Signaling Profile."
    DEFVAL          { unsupported }
    ::= { sonusIsupsgSignalingProfileEntry 96 }

sonusIsupsgSignalingProfileFOT OBJECT-TYPE
    SYNTAX          SonusSupportFlag
    MAX-ACCESS      read-write
    STATUS          current
    DESCRIPTION     
            "Is the Forward Transfer Message supported for the ISUP Signaling Profile."
    DEFVAL          { unsupported }
    ::= { sonusIsupsgSignalingProfileEntry 97 }

sonusIsupsgSignalingProfileSpecialDigits OBJECT-TYPE
    SYNTAX          BITS { digitA(0), digitB(1), digitC(2), digitD(3), 
                        digitE(4), digitF(5), none(6) }
    MAX-ACCESS      read-write
    STATUS          current
    DESCRIPTION     
            "Indicates the special digits which can appear in dialed digit strings 
             
             BIT 0 - Is digit A allowed in the digit string 
             BIT 1 - Is digit B allowed in the digit string 
             BIT 2 - Is digit C allowed in the digit string 
             BIT 3 - Is digit D allowed in the digit string 
             BIT 4 - Is digit E allowed in the digit string 
             BIT 5 - Is digit F allowed in the digit string 
             BIT 6 - No special digits in the digit string"
    ::= { sonusIsupsgSignalingProfileEntry 98 }

sonusIsupsgSignalingProfileTNS OBJECT-TYPE
    SYNTAX          SonusSupportFlag
    MAX-ACCESS      read-write
    STATUS          current
    DESCRIPTION     
            "Is the Transit Network Selection Parameter supported for the ISUP Signaling Profile."
    DEFVAL          { unsupported }
    ::= { sonusIsupsgSignalingProfileEntry 99 }

sonusIsupsgSignalingProfileAwaitDigits OBJECT-TYPE
    SYNTAX          SonusSupportFlag
    MAX-ACCESS      read-write
    STATUS          current
    DESCRIPTION     
            "Is Await Digits supported for this ISUP Signaling Profile."
    DEFVAL          { unsupported }
    ::= { sonusIsupsgSignalingProfileEntry 100 }

sonusIsupsgSignalingProfileAccessTrans OBJECT-TYPE
    SYNTAX          SonusSupportFlag
    MAX-ACCESS      read-write
    STATUS          current
    DESCRIPTION     
            "Is the Access Transport parameter supported for the ISUP Signaling Profile."
    DEFVAL          { supported }
    ::= { sonusIsupsgSignalingProfileEntry 101 }

sonusIsupsgSignalingProfileJurisdiction OBJECT-TYPE
    SYNTAX          SonusSupportFlag
    MAX-ACCESS      read-write
    STATUS          current
    DESCRIPTION     
            "Is the Jurisdiction parameter supported for the ISUP Signaling Profile."
    DEFVAL          { supported }
    ::= { sonusIsupsgSignalingProfileEntry 102 }

sonusIsupsgSignalingProfileOCN OBJECT-TYPE
    SYNTAX          SonusSupportFlag
    MAX-ACCESS      read-write
    STATUS          current
    DESCRIPTION     
            "Is the Original Called Number  parameter supported for the ISUP Signaling Profile."
    DEFVAL          { supported }
    ::= { sonusIsupsgSignalingProfileEntry 103 }

sonusIsupsgSignalingProfileBusinessGrp OBJECT-TYPE
    SYNTAX          SonusSupportFlag
    MAX-ACCESS      read-write
    STATUS          current
    DESCRIPTION     
            "Is the Business Group parameter supported for the ISUP Signaling Profile."
    DEFVAL          { supported }
    ::= { sonusIsupsgSignalingProfileEntry 104 }

sonusIsupsgSignalingProfileConReq OBJECT-TYPE
    SYNTAX          SonusSupportFlag
    MAX-ACCESS      read-write
    STATUS          current
    DESCRIPTION     
            "Is the Conection Request parameter supported for the ISUP Signaling Profile."
    DEFVAL          { supported }
    ::= { sonusIsupsgSignalingProfileEntry 105 }

sonusIsupsgSignalingProfileInfoInd OBJECT-TYPE
    SYNTAX          SonusSupportFlag
    MAX-ACCESS      read-write
    STATUS          current
    DESCRIPTION     
            "Is the Information Indicator parameter supported for the ISUP Signaling Profile."
    DEFVAL          { supported }
    ::= { sonusIsupsgSignalingProfileEntry 106 }

sonusIsupsgSignalingProfileNtp OBJECT-TYPE
    SYNTAX          SonusSupportFlag
    MAX-ACCESS      read-write
    STATUS          current
    DESCRIPTION     
            "Is the Network Transport supported for the ISUP Signaling Profile."
    DEFVAL          { supported }
    ::= { sonusIsupsgSignalingProfileEntry 107 }

sonusIsupsgSignalingProfileNotifInd OBJECT-TYPE
    SYNTAX          SonusSupportFlag
    MAX-ACCESS      read-write
    STATUS          current
    DESCRIPTION     
            "Is the Notification Indicator parameter supported for the ISUP Signaling Profile."
    DEFVAL          { supported }
    ::= { sonusIsupsgSignalingProfileEntry 108 }

sonusIsupsgSignalingProfileRedInfoAcm OBJECT-TYPE
    SYNTAX          SonusSupportFlag
    MAX-ACCESS      read-write
    STATUS          current
    DESCRIPTION     
            "Is the Redirection Information parameter supported in the ACM message
             for the ISUP Signaling Profile."
    DEFVAL          { supported }
    ::= { sonusIsupsgSignalingProfileEntry 109 }

sonusIsupsgSignalingProfileEgressService OBJECT-TYPE
    SYNTAX          SonusSupportFlag
    MAX-ACCESS      read-write
    STATUS          current
    DESCRIPTION     
            "Is the Egress Service parameter supported for the ISUP Signaling Profile."
    DEFVAL          { supported }
    ::= { sonusIsupsgSignalingProfileEntry 110 }

sonusIsupsgSignalingProfileServCodeInd OBJECT-TYPE
    SYNTAX          SonusSupportFlag
    MAX-ACCESS      read-write
    STATUS          current
    DESCRIPTION     
            "Is the Service Code Indicator parameter supported for the ISUP Signaling Profile."
    DEFVAL          { supported }
    ::= { sonusIsupsgSignalingProfileEntry 111 }

sonusIsupsgSignalingProfileSpecProcReq OBJECT-TYPE
    SYNTAX          SonusSupportFlag
    MAX-ACCESS      read-write
    STATUS          current
    DESCRIPTION     
            "Is the Special Processing Request parameter supported for the ISUP Signaling Profile."
    DEFVAL          { supported }
    ::= { sonusIsupsgSignalingProfileEntry 112 }

sonusIsupsgSignalingProfileTransReq OBJECT-TYPE
    SYNTAX          SonusSupportFlag
    MAX-ACCESS      read-write
    STATUS          current
    DESCRIPTION     
            "Is the Transaction Request parameter supported for the
             ISUP Signaling Profile."
    DEFVAL          { supported }
    ::= { sonusIsupsgSignalingProfileEntry 113 }

sonusIsupsgSignalingProfileChgNum OBJECT-TYPE
    SYNTAX          SonusSupportFlag
    MAX-ACCESS      read-write
    STATUS          current
    DESCRIPTION     
            "Is the Charge Number parameter supported for the ISUP Signaling Profile."
    DEFVAL          { supported }
    ::= { sonusIsupsgSignalingProfileEntry 114 }

sonusIsupsgSignalingProfileGenAddressREL OBJECT-TYPE
    SYNTAX          SonusSupportFlag
    MAX-ACCESS      read-write
    STATUS          current
    DESCRIPTION     
            "Is the Generic Address parameter supported in the REL message for the
             ISUP Signaling Profile."
    DEFVAL          { supported }
    ::= { sonusIsupsgSignalingProfileEntry 115 }

sonusIsupsgSignalingProfileUUIndAcm OBJECT-TYPE
    SYNTAX          SonusSupportFlag
    MAX-ACCESS      read-write
    STATUS          current
    DESCRIPTION     
            "Is the User to User Indicators parameter supported for the ISUP Signaling Profile."
    DEFVAL          { supported }
    ::= { sonusIsupsgSignalingProfileEntry 116 }

sonusIsupsgSignalingProfileUUInfo OBJECT-TYPE
    SYNTAX          SonusSupportFlag
    MAX-ACCESS      read-write
    STATUS          current
    DESCRIPTION     
            "Is the User to User Information parameter supported for the ISUP Signaling Profile."
    DEFVAL          { supported }
    ::= { sonusIsupsgSignalingProfileEntry 117 }

sonusIsupsgSignalingProfileOperatorServInfo OBJECT-TYPE
    SYNTAX          SonusSupportFlag
    MAX-ACCESS      read-write
    STATUS          current
    DESCRIPTION     
            "Is the Operator Service Information parameter supported for the ISUP Signaling Profile."
    DEFVAL          { supported }
    ::= { sonusIsupsgSignalingProfileEntry 118 }

sonusIsupsgSignalingProfileCvtCvr OBJECT-TYPE
    SYNTAX          SonusSupportFlag
    MAX-ACCESS      read-write
    STATUS          current
    DESCRIPTION     
            "Are the Circuit Validation Test/Response procedures supported for
             the ISUP Signaling Profile."
    DEFVAL          { supported }
    ::= { sonusIsupsgSignalingProfileEntry 119 }

sonusIsupsgSignalingProfileGenName OBJECT-TYPE
    SYNTAX          SonusSupportFlag
    MAX-ACCESS      read-write
    STATUS          current
    DESCRIPTION     
            "Is the Generic Name parameter supported for the ISUP Signaling Profile."
    DEFVAL          { supported }
    ::= { sonusIsupsgSignalingProfileEntry 120 }

sonusIsupsgSignalingProfileRedCap OBJECT-TYPE
    SYNTAX          SonusSupportFlag
    MAX-ACCESS      read-write
    STATUS          current
    DESCRIPTION     
            "Is the Redirection Capability parameter supported for the ISUP Signaling Profile."
    DEFVAL          { supported }
    ::= { sonusIsupsgSignalingProfileEntry 121 }

sonusIsupsgSignalingProfileRedCount OBJECT-TYPE
    SYNTAX          SonusSupportFlag
    MAX-ACCESS      read-write
    STATUS          current
    DESCRIPTION     
            "Is the Group Redirection Count parameter supported for the ISUP Signaling Profile."
    DEFVAL          { supported }
    ::= { sonusIsupsgSignalingProfileEntry 122 }

sonusIsupsgSignalingProfileSendTwoGrpMsgs OBJECT-TYPE
    SYNTAX          SonusSupportFlag
    MAX-ACCESS      read-write
    STATUS          current
    DESCRIPTION     
            "Set the Flag to Send Two Group Messages in the ISUP Signaling Profile."
    DEFVAL          { supported }
    ::= { sonusIsupsgSignalingProfileEntry 123 }

sonusIsupsgSignalingProfileAwaitTwoGrpMsgs OBJECT-TYPE
    SYNTAX          SonusSupportFlag
    MAX-ACCESS      read-write
    STATUS          current
    DESCRIPTION     
            "Set the Flag to Await Two Group Messages in the ISUP Signaling Profile."
    DEFVAL          { supported }
    ::= { sonusIsupsgSignalingProfileEntry 124 }

sonusIsupsgSignalingProfileCqmOnCardSwap OBJECT-TYPE
    SYNTAX          SonusSupportFlag
    MAX-ACCESS      read-write
    STATUS          current
    DESCRIPTION     
            "Set the Flag to perform CQM on Card Swap in the ISUP Signaling Profile."
    DEFVAL          { supported }
    ::= { sonusIsupsgSignalingProfileEntry 125 }

sonusIsupsgSignalingProfileAnsi95Grs OBJECT-TYPE
    SYNTAX          SonusSupportFlag
    MAX-ACCESS      read-write
    STATUS          current
    DESCRIPTION     
            "Should the ANSI-95 format for Group Reset Circuit (GRS), which includes
             optional parameters, be used."
    DEFVAL          { supported }
    ::= { sonusIsupsgSignalingProfileEntry 126 }

sonusIsupsgSignalingProfileCpgBeforeAcm OBJECT-TYPE
    SYNTAX          SonusSupportFlag
    MAX-ACCESS      read-write
    STATUS          current
    DESCRIPTION     
            "Should a CPG arriving before an ACM be transited."
    DEFVAL          { supported }
    ::= { sonusIsupsgSignalingProfileEntry 127 }

sonusIsupsgSignalingProfileMapDmsFeParameter OBJECT-TYPE
    SYNTAX          SonusSupportFlag
    MAX-ACCESS      read-write
    STATUS          current
    DESCRIPTION     
            "Specifies if the service group should perform mapping of the 
             Completion Code in the DMS FE parameter (ANSI ISUP only)"
    DEFVAL          { supported }
    ::= { sonusIsupsgSignalingProfileEntry 128 }

sonusIsupsgSignalingProfileTKOsupport OBJECT-TYPE
    SYNTAX          SonusSupportFlag
    MAX-ACCESS      read-write
    STATUS          current
    DESCRIPTION     
            "Describes if the trunk offering messages can,fan,ofr,rcl are supported,
             at the moment this is just for mexico. But as sure as eggs is eggs 
             other international variants are going to want tko as well at some time"
    DEFVAL          { unsupported }
    ::= { sonusIsupsgSignalingProfileEntry 129 }

sonusIsupsgSignalingProfileOPSELIsupport OBJECT-TYPE
    SYNTAX          SonusSupportFlag
    MAX-ACCESS      read-write
    STATUS          current
    DESCRIPTION     
            "Describes if the operator selection parameter is supported"
    DEFVAL          { unsupported }
    ::= { sonusIsupsgSignalingProfileEntry 130 }

sonusIsupsgSignalingProfileMaxCallingPartyDigits OBJECT-TYPE
    SYNTAX          Integer32 (1..30)
    MAX-ACCESS      read-write
    STATUS          current
    DESCRIPTION     
            "The maxium digit string length for the Calling Party Number parameter supported for this ISUP Signalling Profile"
    DEFVAL          { 30 }
    ::= { sonusIsupsgSignalingProfileEntry 131 }

sonusIsupsgSignalingProfileMaxCalledPartyDigits OBJECT-TYPE
    SYNTAX          Integer32 (1..30)
    MAX-ACCESS      read-write
    STATUS          current
    DESCRIPTION     
            "The maxium digit string length for the Called Party Number parameter supported for this ISUP Signalling Profile"
    DEFVAL          { 30 }
    ::= { sonusIsupsgSignalingProfileEntry 132 }

sonusIsupsgSignalingProfileFreephoneInd OBJECT-TYPE
    SYNTAX          SonusSupportFlag
    MAX-ACCESS      read-write
    STATUS          current
    DESCRIPTION     
            "Is the Freephone Indicators parameter supported for this ISUP Signalling Profile."
    DEFVAL          { supported }
    ::= { sonusIsupsgSignalingProfileEntry 133 }

sonusIsupsgSignalingProfileItxTxa OBJECT-TYPE
    SYNTAX          SonusSupportFlag
    MAX-ACCESS      read-write
    STATUS          current
    DESCRIPTION     
            "Are the ITX and TXA  messages supported for the ISUP Signaling Profile."
    DEFVAL          { supported }
    ::= { sonusIsupsgSignalingProfileEntry 134 }

sonusIsupsgSignalingProfileSCCPProcedure OBJECT-TYPE
    SYNTAX          SonusSupportFlag
    MAX-ACCESS      read-write
    STATUS          current
    DESCRIPTION     
            "Is the SCCP Procedure supported for the ISUP Signaling Profile."
    DEFVAL          { supported }
    ::= { sonusIsupsgSignalingProfileEntry 135 }

sonusIsupsgSignalingProfileCnrInIAM OBJECT-TYPE
    SYNTAX          SonusSupportFlag
    MAX-ACCESS      read-write
    STATUS          current
    DESCRIPTION     
            "Is the Connection Request parameter supported in the IAM for the ISUP Signaling Profile."
    DEFVAL          { supported }
    ::= { sonusIsupsgSignalingProfileEntry 136 }

sonusIsupsgSignalingProfileCcnr OBJECT-TYPE
    SYNTAX          SonusSupportFlag
    MAX-ACCESS      read-write
    STATUS          current
    DESCRIPTION     
            "Is the CCNR Possible Indicator parameter supported for the ISUP Signaling Profile."
    DEFVAL          { supported }
    ::= { sonusIsupsgSignalingProfileEntry 137 }

sonusIsupsgSignalingProfileTransitCFN OBJECT-TYPE
    SYNTAX          SonusSupportFlag
    MAX-ACCESS      read-write
    STATUS          current
    DESCRIPTION     
            "Should the CFN message be transitted for the ISUP Signaling Profile."
    DEFVAL          { supported }
    ::= { sonusIsupsgSignalingProfileEntry 138 }

sonusIsupsgSignalingProfileHoldingInd OBJECT-TYPE
    SYNTAX          SonusSupportFlag
    MAX-ACCESS      read-write
    STATUS          current
    DESCRIPTION     
            "Should the Holding Indicator be supported for the ISUP Signaling Profile."
    DEFVAL          { supported }
    ::= { sonusIsupsgSignalingProfileEntry 139 }

sonusIsupsgSignalingProfileDispInfoInAcm OBJECT-TYPE
    SYNTAX          SonusSupportFlag
    MAX-ACCESS      read-write
    STATUS          current
    DESCRIPTION     
            "Should the Display Information parameter in the ACM be supported for the ISUP Signaling Profile."
    DEFVAL          { supported }
    ::= { sonusIsupsgSignalingProfileEntry 140 }

sonusIsupsgSignalingProfileDispInfoInCon OBJECT-TYPE
    SYNTAX          SonusSupportFlag
    MAX-ACCESS      read-write
    STATUS          current
    DESCRIPTION     
            "Should the Display Information parameter in the CON be supported for the ISUP Signaling Profile."
    DEFVAL          { supported }
    ::= { sonusIsupsgSignalingProfileEntry 141 }

sonusIsupsgSignalingProfileDispInfoInCpg OBJECT-TYPE
    SYNTAX          SonusSupportFlag
    MAX-ACCESS      read-write
    STATUS          current
    DESCRIPTION     
            "Should the Display Information parameter in the CPG be supported for the ISUP Signaling Profile."
    DEFVAL          { supported }
    ::= { sonusIsupsgSignalingProfileEntry 142 }

sonusIsupsgSignalingProfileDispInfoInIam OBJECT-TYPE
    SYNTAX          SonusSupportFlag
    MAX-ACCESS      read-write
    STATUS          current
    DESCRIPTION     
            "Should the Display Information parameter in the IAM be supported for the ISUP Signaling Profile."
    DEFVAL          { supported }
    ::= { sonusIsupsgSignalingProfileEntry 143 }

sonusIsupsgSignalingProfileGenNumInAcm OBJECT-TYPE
    SYNTAX          SonusSupportFlag
    MAX-ACCESS      read-write
    STATUS          current
    DESCRIPTION     
            "Should the Generic Number parameter in the ACM be supported for the ISUP Signaling Profile."
    DEFVAL          { supported }
    ::= { sonusIsupsgSignalingProfileEntry 144 }

sonusIsupsgSignalingProfileGenNumInFac OBJECT-TYPE
    SYNTAX          SonusSupportFlag
    MAX-ACCESS      read-write
    STATUS          current
    DESCRIPTION     
            "Should the Generic Number parameter in the FAC be supported for the ISUP Signaling Profile."
    DEFVAL          { supported }
    ::= { sonusIsupsgSignalingProfileEntry 145 }

sonusIsupsgSignalingProfileGenNumInInf OBJECT-TYPE
    SYNTAX          SonusSupportFlag
    MAX-ACCESS      read-write
    STATUS          current
    DESCRIPTION     
            "Should the Generic Number parameter in the INF be supported for the ISUP Signaling Profile."
    DEFVAL          { supported }
    ::= { sonusIsupsgSignalingProfileEntry 146 }

sonusIsupsgSignalingProfileConfTreatInAnm OBJECT-TYPE
    SYNTAX          SonusSupportFlag
    MAX-ACCESS      read-write
    STATUS          current
    DESCRIPTION     
            "Should the Conference Treatment parameter in the ANM be supported for the ISUP Signaling Profile."
    DEFVAL          { supported }
    ::= { sonusIsupsgSignalingProfileEntry 147 }

sonusIsupsgSignalingProfileContinuity OBJECT-TYPE
    SYNTAX          SonusSupportFlag
    MAX-ACCESS      read-write
    STATUS          current
    DESCRIPTION     
            "Should the Continuity procedures be supported for the ISUP Signaling Profile."
    DEFVAL          { supported }
    ::= { sonusIsupsgSignalingProfileEntry 148 }

sonusIsupsgSignalingProfileUSI OBJECT-TYPE
    SYNTAX          SonusSupportFlag
    MAX-ACCESS      read-write
    STATUS          current
    DESCRIPTION     
            "Should User service information be supported for the ISUP signaling profile"
    DEFVAL          { supported }
    ::= { sonusIsupsgSignalingProfileEntry 149 }

sonusIsupsgSignalingProfileConnectedNum OBJECT-TYPE
    SYNTAX          SonusSupportFlag
    MAX-ACCESS      read-write
    STATUS          current
    DESCRIPTION     
            "Should connected number be supported for the ISUP signaling profile"
    DEFVAL          { supported }
    ::= { sonusIsupsgSignalingProfileEntry 150 }

sonusIsupsgSignalingProfileDiagnostics OBJECT-TYPE
    SYNTAX          SonusSupportFlag
    MAX-ACCESS      read-write
    STATUS          current
    DESCRIPTION     
            "Should the Diagnostics field be supported for the ISUP signaling profile"
    DEFVAL          { supported }
    ::= { sonusIsupsgSignalingProfileEntry 151 }

sonusIsupsgSignalingProfileOptionalFCI OBJECT-TYPE
    SYNTAX          SonusSupportFlag
    MAX-ACCESS      read-write
    STATUS          current
    DESCRIPTION     
            "Should the Optional Forward Call Indicators be supported for the ISUP signaling profile"
    DEFVAL          { supported }
    ::= { sonusIsupsgSignalingProfileEntry 152 }

sonusIsupsgSignalingProfileClosedUserGroupIC OBJECT-TYPE
    SYNTAX          SonusSupportFlag
    MAX-ACCESS      read-write
    STATUS          current
    DESCRIPTION     
            "Should Closed User Group Interlock Code be supported for the ISUP signaling profile"
    DEFVAL          { supported }
    ::= { sonusIsupsgSignalingProfileEntry 153 }

sonusIsupsgSignalingProfileCom OBJECT-TYPE
    SYNTAX          SonusSupportFlag
    MAX-ACCESS      read-write
    STATUS          current
    DESCRIPTION     
            "Should the COM message be supported for the ISUP Signaling Profile."
    DEFVAL          { supported }
    ::= { sonusIsupsgSignalingProfileEntry 154 }

sonusIsupsgSignalingProfileCon OBJECT-TYPE
    SYNTAX          SonusSupportFlag
    MAX-ACCESS      read-write
    STATUS          current
    DESCRIPTION     
            "Describes if the CON message is supported"
    DEFVAL          { supported }
    ::= { sonusIsupsgSignalingProfileEntry 155 }

sonusIsupsgSignalingProfileIriOriRcv OBJECT-TYPE
    SYNTAX          SonusSupportFlag
    MAX-ACCESS      read-write
    STATUS          current
    DESCRIPTION     
            "Is the IRI/ORI expected for the ISUP Signaling Profile."
    ::= { sonusIsupsgSignalingProfileEntry 156 }

sonusIsupsgSignalingProfileIriOriSent OBJECT-TYPE
    SYNTAX          SonusSupportFlag
    MAX-ACCESS      read-write
    STATUS          current
    DESCRIPTION     
            "Is the IRI/ORI to be sent out for the ISUP Signaling Profile."
    ::= { sonusIsupsgSignalingProfileEntry 157 }

sonusIsupsgSignalingProfileT11Active OBJECT-TYPE
    SYNTAX          SonusSupportFlag
    MAX-ACCESS      read-write
    STATUS          current
    DESCRIPTION     
            "Is ISUP T11 timing active at interworking exchanges for Signaling Profile."
    ::= { sonusIsupsgSignalingProfileEntry 158 }

sonusIsupsgSignalingProfileIriOri OBJECT-TYPE
    SYNTAX          SonusSupportFlag
    MAX-ACCESS      read-write
    STATUS          current
    DESCRIPTION     
            "Is the IRI/ORI supported for the ISUP Signaling Profile."
    ::= { sonusIsupsgSignalingProfileEntry 159 }

sonusIsupsgSignalingProfileTransMedUsedInNrm OBJECT-TYPE
    SYNTAX          SonusSupportFlag
    MAX-ACCESS      read-write
    STATUS          current
    DESCRIPTION     
            "Is the TMU parameter within the NRM Message supported for the ISUP Signaling Profile."
    ::= { sonusIsupsgSignalingProfileEntry 160 }

sonusIsupsgSignalingProfileRlcAckGrs OBJECT-TYPE
    SYNTAX          SonusSupportFlag
    MAX-ACCESS      read-write
    STATUS          current
    DESCRIPTION     
            "Is acknowledging a GRS with an RLC supported."
    ::= { sonusIsupsgSignalingProfileEntry 161 }

sonusIsupsgSignalingProfileIncomingTrunkIdCode OBJECT-TYPE
    SYNTAX          SonusSupportFlag
    MAX-ACCESS      read-write
    STATUS          current
    DESCRIPTION     
            "Is the Incoming Trunk Identity Code parameter supported for the Signaling Profile."
    ::= { sonusIsupsgSignalingProfileEntry 162 }

sonusIsupsgSignalingProfileSpcInIrs OBJECT-TYPE
    SYNTAX          SonusSupportFlag
    MAX-ACCESS      read-write
    STATUS          current
    DESCRIPTION     
            "Is the SPC parameter with the IRS message supported for the ISUP Signaling Profile."
    ::= { sonusIsupsgSignalingProfileEntry 163 }

sonusIsupsgSignalingProfileRedInfoIam OBJECT-TYPE
    SYNTAX          SonusSupportFlag
    MAX-ACCESS      read-write
    STATUS          current
    DESCRIPTION     
            "Is the Redirection Information parameter supported within the IAM message foe the ISUP Signaling Profile."
    ::= { sonusIsupsgSignalingProfileEntry 164 }

sonusIsupsgSignalingProfileRedirectingNum OBJECT-TYPE
    SYNTAX          SonusSupportFlag
    MAX-ACCESS      read-write
    STATUS          current
    DESCRIPTION     
            "Is the Redirecting Number parameter supported for the ISUP Signaling Profile."
    ::= { sonusIsupsgSignalingProfileEntry 165 }

sonusIsupsgSignalingProfileSendBloAfterSetup OBJECT-TYPE
    SYNTAX          SonusSupportFlag
    MAX-ACCESS      read-write
    STATUS          current
    DESCRIPTION     
            "For some ANSI protocols a BLO message should be sent when blocking a circuit, after a 
             backwards message has been received during the call."
    ::= { sonusIsupsgSignalingProfileEntry 166 }

sonusIsupsgSignalingProfileCalledDirectoryNum OBJECT-TYPE
    SYNTAX          SonusSupportFlag
    MAX-ACCESS      read-write
    STATUS          current
    DESCRIPTION     
            "Is the called directory number parameter supported for the ISUP signaling Profile."
    ::= { sonusIsupsgSignalingProfileEntry 167 }

sonusIsupsgSignalingProfileT6Release OBJECT-TYPE
    SYNTAX          Integer32 (1..127)
    MAX-ACCESS      read-write
    STATUS          current
    DESCRIPTION     
            "The T6 timer default release cause value used by all ITU protocols."
    DEFVAL          { 16 }
    ::= { sonusIsupsgSignalingProfileEntry 168 }

sonusIsupsgSignalingProfileT7Release OBJECT-TYPE
    SYNTAX          Integer32 (1..127)
    MAX-ACCESS      read-write
    STATUS          current
    DESCRIPTION     
            "The T7 timer default release cause value used by all ITU protocols."
    DEFVAL          { 31 }
    ::= { sonusIsupsgSignalingProfileEntry 169 }

sonusIsupsgSignalingProfileFwdCpg OBJECT-TYPE
    SYNTAX          SonusSupportFlag
    MAX-ACCESS      read-write
    STATUS          current
    DESCRIPTION     
            "Is the Call Progress (CPG) message supported in the forwards direction."
    ::= { sonusIsupsgSignalingProfileEntry 170 }

sonusIsupsgSignalingProfileFwdSus OBJECT-TYPE
    SYNTAX          SonusSupportFlag
    MAX-ACCESS      read-write
    STATUS          current
    DESCRIPTION     
            "Is the Suspend (SUS) message supported in the forwards direction."
    ::= { sonusIsupsgSignalingProfileEntry 171 }

sonusIsupsgSignalingProfileUUInfoAcm OBJECT-TYPE
    SYNTAX          SonusSupportFlag
    MAX-ACCESS      read-write
    STATUS          current
    DESCRIPTION     
            "Is the UU Information supported in the ACM for the ISUP Signaling Profile."
    ::= { sonusIsupsgSignalingProfileEntry 172 }

sonusIsupsgSignalingProfileATRel OBJECT-TYPE
    SYNTAX          SonusSupportFlag
    MAX-ACCESS      read-write
    STATUS          current
    DESCRIPTION     
            "Is the AT supported in the REL for the ISUP Signaling Profile."
    ::= { sonusIsupsgSignalingProfileEntry 173 }

sonusIsupsgSignalingProfileUUIndRel OBJECT-TYPE
    SYNTAX          SonusSupportFlag
    MAX-ACCESS      read-write
    STATUS          current
    DESCRIPTION     
            "Is the UU Indicator supported in the REL for the ISUP Signaling Profile."
    ::= { sonusIsupsgSignalingProfileEntry 174 }

sonusIsupsgSignalingProfileEIT OBJECT-TYPE
    SYNTAX          SonusSupportFlag
    MAX-ACCESS      read-write
    STATUS          current
    DESCRIPTION     
            "Is the EIT supported for the ISUP Signaling Profile."
    ::= { sonusIsupsgSignalingProfileEntry 175 }

sonusIsupsgSignalingProfileGI OBJECT-TYPE
    SYNTAX          SonusSupportFlag
    MAX-ACCESS      read-write
    STATUS          current
    DESCRIPTION     
            "Is the GI supported for the ISUP Signaling Profile."
    ::= { sonusIsupsgSignalingProfileEntry 176 }

sonusIsupsgSignalingProfileTIT OBJECT-TYPE
    SYNTAX          SonusSupportFlag
    MAX-ACCESS      read-write
    STATUS          current
    DESCRIPTION     
            "Is the TIT supported for the ISUP Signaling Profile."
    ::= { sonusIsupsgSignalingProfileEntry 177 }

sonusIsupsgSignalingProfileAIT OBJECT-TYPE
    SYNTAX          SonusSupportFlag
    MAX-ACCESS      read-write
    STATUS          current
    DESCRIPTION     
            "Is the AIT supported for the ISUP Signaling Profile."
    ::= { sonusIsupsgSignalingProfileEntry 178 }

sonusIsupsgSignalingProfileTCI OBJECT-TYPE
    SYNTAX          SonusSupportFlag
    MAX-ACCESS      read-write
    STATUS          current
    DESCRIPTION     
            "Is the TCI supported for the ISUP Signaling Profile."
    ::= { sonusIsupsgSignalingProfileEntry 179 }

sonusIsupsgSignalingProfileNFT OBJECT-TYPE
    SYNTAX          SonusSupportFlag
    MAX-ACCESS      read-write
    STATUS          current
    DESCRIPTION     
            "Is the NFT supported for the ISUP Signaling Profile."
    ::= { sonusIsupsgSignalingProfileEntry 180 }

sonusIsupsgSignalingProfileCPNRel OBJECT-TYPE
    SYNTAX          SonusSupportFlag
    MAX-ACCESS      read-write
    STATUS          current
    DESCRIPTION     
            "Is the CPN supported in the REL for the ISUP Signaling Profile."
    ::= { sonusIsupsgSignalingProfileEntry 181 }

sonusIsupsgSignalingProfileBCIRel OBJECT-TYPE
    SYNTAX          SonusSupportFlag
    MAX-ACCESS      read-write
    STATUS          current
    DESCRIPTION     
            "Is the BCI supported in the REL for the ISUP Signaling Profile."
    ::= { sonusIsupsgSignalingProfileEntry 182 }

sonusIsupsgSignalingProfileCI OBJECT-TYPE
    SYNTAX          SonusSupportFlag
    MAX-ACCESS      read-write
    STATUS          current
    DESCRIPTION     
            "Is the CI6 supported in the ISUP Signaling Profile."
    ::= { sonusIsupsgSignalingProfileEntry 183 }

sonusIsupsgSignalingProfileIUI OBJECT-TYPE
    SYNTAX          SonusSupportFlag
    MAX-ACCESS      read-write
    STATUS          current
    DESCRIPTION     
            "Is the IUI6 supported in the ISUP Signaling Profile."
    ::= { sonusIsupsgSignalingProfileEntry 184 }

sonusIsupsgSignalingProfileNROP OBJECT-TYPE
    SYNTAX          SonusSupportFlag
    MAX-ACCESS      read-write
    STATUS          current
    DESCRIPTION     
            "Is the NROP6 supported in the ISUP Signaling Profile."
    ::= { sonusIsupsgSignalingProfileEntry 185 }

sonusIsupsgSignalingProfileMSI OBJECT-TYPE
    SYNTAX          SonusSupportFlag
    MAX-ACCESS      read-write
    STATUS          current
    DESCRIPTION     
            "Is the MSI6 supported in the ISUP Signaling Profile."
    ::= { sonusIsupsgSignalingProfileEntry 186 }

sonusIsupsgSignalingProfileRR OBJECT-TYPE
    SYNTAX          SonusSupportFlag
    MAX-ACCESS      read-write
    STATUS          current
    DESCRIPTION     
            "Is the RR6 supported in the ISUP Signaling Profile."
    ::= { sonusIsupsgSignalingProfileEntry 187 }

sonusIsupsgSignalingProfileMI OBJECT-TYPE
    SYNTAX          SonusSupportFlag
    MAX-ACCESS      read-write
    STATUS          current
    DESCRIPTION     
            "Is the MI6 supported in the ISUP Signaling Profile."
    ::= { sonusIsupsgSignalingProfileEntry 188 }

sonusIsupsgSignalingProfileSPC6 OBJECT-TYPE
    SYNTAX          SonusSupportFlag
    MAX-ACCESS      read-write
    STATUS          current
    DESCRIPTION     
            "Is the SPC6 supported in the ISUP Signaling Profile."
    ::= { sonusIsupsgSignalingProfileEntry 189 }

sonusIsupsgSignalingProfileMARel OBJECT-TYPE
    SYNTAX          SonusSupportFlag
    MAX-ACCESS      read-write
    STATUS          current
    DESCRIPTION     
            "Is the MA6 supported in the REL message for the ISUP Signaling Profile."
    ::= { sonusIsupsgSignalingProfileEntry 190 }

sonusIsupsgSignalingProfileConReqInInf OBJECT-TYPE
    SYNTAX          SonusSupportFlag
    MAX-ACCESS      read-write
    STATUS          current
    DESCRIPTION     
            "Is the Connection Request supported in the INF for the ISUP Signaling Profile."
    ::= { sonusIsupsgSignalingProfileEntry 191 }

sonusIsupsgSignalingProfileSgmPci OBJECT-TYPE
    SYNTAX          SonusSupportFlag
    MAX-ACCESS      read-write
    STATUS          current
    DESCRIPTION     
            "Is the PCI parameter supported in the SGM for the ISUP Signaling Profile."
    ::= { sonusIsupsgSignalingProfileEntry 192 }

sonusIsupsgSignalingProfileGR317ScreeningInd OBJECT-TYPE
    SYNTAX          SonusSupportFlag
    MAX-ACCESS      read-write
    STATUS          current
    DESCRIPTION     
            "Turns on various screening indicators for GR317 parameter compliancy."
    ::= { sonusIsupsgSignalingProfileEntry 193 }

sonusIsupsgSignalingProfileOpr OBJECT-TYPE
    SYNTAX          SonusSupportFlag
    MAX-ACCESS      read-write
    STATUS          current
    DESCRIPTION     
            "Is the Operator (OPR) messsage supported."
    ::= { sonusIsupsgSignalingProfileEntry 194 }

sonusIsupsgSignalingProfileCcl OBJECT-TYPE
    SYNTAX          SonusSupportFlag
    MAX-ACCESS      read-write
    STATUS          current
    DESCRIPTION     
            "Is the Calling Party Clearing (CCL) messsage supported."
    ::= { sonusIsupsgSignalingProfileEntry 195 }

sonusIsupsgSignalingProfileOtherDigitStringSpecialDigitF OBJECT-TYPE
    SYNTAX          SonusSupportFlag
    MAX-ACCESS      read-write
    STATUS          current
    DESCRIPTION     
            "Is the Special Digit F supported in digit strings other than the Called Party."
    ::= { sonusIsupsgSignalingProfileEntry 196 }

sonusIsupsgSignalingProfileCallRefFrj OBJECT-TYPE
    SYNTAX          SonusSupportFlag
    MAX-ACCESS      read-write
    STATUS          current
    DESCRIPTION     
            "Is the Call Reference Parameter supported in the FRJ message."
    ::= { sonusIsupsgSignalingProfileEntry 197 }

sonusIsupsgSignalingProfilePCIPassOnDefault OBJECT-TYPE
    SYNTAX          INTEGER { unsupported(0), discardParameter(1), 
                        discardMessage(2), releaseCall(3) }
    MAX-ACCESS      read-write
    STATUS          current
    DESCRIPTION     
            "The handling required when received an unrecognised PCI Pass On Not Possible
             value in the ISUP Signaling Profile."
    DEFVAL          { unsupported }
    ::= { sonusIsupsgSignalingProfileEntry 198 }

sonusIsupsgSignalingProfileOTGNAnsi92 OBJECT-TYPE
    SYNTAX          SonusSupportFlag
    MAX-ACCESS      read-write
    STATUS          current
    DESCRIPTION     
            "Is the OTGN Parameter, upto 5 octets supported in the EXM message."
    ::= { sonusIsupsgSignalingProfileEntry 199 }

sonusIsupsgSignalingProfileMsgSendDelay OBJECT-TYPE
    SYNTAX          Integer32 (0..255)
    MAX-ACCESS      read-write
    STATUS          current
    DESCRIPTION     
            "The delay to be inserted between sending two consecutive ISUP messages
             on any given circuit (Milliseconds)."
    DEFVAL          { 0 }
    ::= { sonusIsupsgSignalingProfileEntry 200 }

sonusIsupsgSignalingProfileDropCauseInAcmWhenIwk OBJECT-TYPE
    SYNTAX          SonusSupportFlag
    MAX-ACCESS      read-write
    STATUS          current
    DESCRIPTION     
            "Should CAUSE parameter in ACM be suppressed if announcement played after interworking."
    ::= { sonusIsupsgSignalingProfileEntry 201 }

sonusIsupsgSignalingProfileChargeIndSetting OBJECT-TYPE
    SYNTAX          INTEGER { transit(1), charge(2), nocharge(3), 
                        noindication(4) }
    MAX-ACCESS      read-write
    STATUS          current
    DESCRIPTION     
            "Sets the BCI charge indicator to either charge or no charge, or will 
             transit whatever is received from the sending side (egress of network).
             This can be nothing at all in the case of ISDN - defaults to 0,
             or whatever we received in the case of ISUP."
    DEFVAL          { 1 }
    ::= { sonusIsupsgSignalingProfileEntry 202 }

sonusIsupsgSignalingProfileT11EarlyAcm OBJECT-TYPE
    SYNTAX          SonusSupportFlag
    MAX-ACCESS      read-write
    STATUS          current
    DESCRIPTION     
            "Is ISUP T11 Early ACM guard timer started for the ISUP Signaling Profile."
    ::= { sonusIsupsgSignalingProfileEntry 203 }

sonusIsupsgSignalingProfileDmsFe OBJECT-TYPE
    SYNTAX          SonusSupportFlag
    MAX-ACCESS      read-write
    STATUS          current
    DESCRIPTION     
            "Should the DMS FE field be supported for the ISUP signaling profile"
    ::= { sonusIsupsgSignalingProfileEntry 204 }

sonusIsupsgSignalingProfileCqmForResync OBJECT-TYPE
    SYNTAX          SonusSupportFlag
    MAX-ACCESS      read-write
    STATUS          current
    DESCRIPTION     
            "Send a Cqm pdu to resync when transitioning from Mtp Pause to Resume State"
    ::= { sonusIsupsgSignalingProfileEntry 205 }

sonusIsupsgSignalingProfileNCR OBJECT-TYPE
    SYNTAX          SonusSupportFlag
    MAX-ACCESS      read-write
    STATUS          current
    DESCRIPTION     
            "Is the Network Call Reference (NCR) Parameter Supported."
    ::= { sonusIsupsgSignalingProfileEntry 206 }

sonusIsupsgSignalingProfileSLIInIAM OBJECT-TYPE
    SYNTAX          SonusSupportFlag
    MAX-ACCESS      read-write
    STATUS          current
    DESCRIPTION     
            "Is the Supplementary Line Info Parameter Supported in the IAM."
    ::= { sonusIsupsgSignalingProfileEntry 207 }

sonusIsupsgSignalingProfileReleaseLinkTrunking OBJECT-TYPE
    SYNTAX          SonusSupportFlag
    MAX-ACCESS      read-write
    STATUS          current
    DESCRIPTION     
            "Is the Release Link Trunking (RLT) Service Supported."
    ::= { sonusIsupsgSignalingProfileEntry 208 }

sonusIsupsgSignalingProfileAccessTransInFAR OBJECT-TYPE
    SYNTAX          SonusSupportFlag
    MAX-ACCESS      read-write
    STATUS          current
    DESCRIPTION     
            "Is the Access Transport Parameter Supported in the FAR."
    ::= { sonusIsupsgSignalingProfileEntry 209 }

sonusIsupsgSignalingProfileUUIndInFAR OBJECT-TYPE
    SYNTAX          SonusSupportFlag
    MAX-ACCESS      read-write
    STATUS          current
    DESCRIPTION     
            "Is the User-to-User Indicators Parameter Supported in the FAR."
    ::= { sonusIsupsgSignalingProfileEntry 210 }

sonusIsupsgSignalingProfileTGNumSource OBJECT-TYPE
    SYNTAX          INTEGER { trunkgroup(0), cic(1) }
    MAX-ACCESS      read-write
    STATUS          current
    DESCRIPTION     
            "Is the trunk number field populated from the trunk group or cic."
    DEFVAL          { 0 }
    ::= { sonusIsupsgSignalingProfileEntry 211 }

sonusIsupsgSignalingProfileUPVExchangeRoles OBJECT-TYPE
    SYNTAX          BITS { orig(0), term(1), intwk(2), trans(3), 
                        intnl(4), unknown(5), none(6) }
    MAX-ACCESS      read-write
    STATUS          current
    DESCRIPTION     
            "Indicates the exchange roles which can perform unrecognised parameter value handling
             
             BIT 0 - Is the originating exchange allowed to perform UPV
             BIT 1 - Is the terminating exchange allowed to perform UPV
             BIT 2 - Is the interworking exchange allowed to perform UPV
             BIT 3 - Is the transit exchange allowed to perform UPV
             BIT 4 - Is the international exchange allowed to perform UPV
             BIT 5 - Is the unknown exchange role allowed to perform UPV
             BIT 6 - No exchange roles are allowed to perform UPV"
    ::= { sonusIsupsgSignalingProfileEntry 212 }

sonusIsupsgSignalingProfileCdBsm OBJECT-TYPE
    SYNTAX          SonusSupportFlag
    MAX-ACCESS      read-write
    STATUS          current
    DESCRIPTION     
            "Is the Called Subs Basic Service Marks parameter supported for the ISUP Signaling Profile."
    ::= { sonusIsupsgSignalingProfileEntry 213 }

sonusIsupsgSignalingProfileCgBsm OBJECT-TYPE
    SYNTAX          SonusSupportFlag
    MAX-ACCESS      read-write
    STATUS          current
    DESCRIPTION     
            "Is the Calling Subs Basic Service Marks parameter supported for the ISUP Signaling Profile."
    ::= { sonusIsupsgSignalingProfileEntry 214 }

sonusIsupsgSignalingProfileCgOfm OBJECT-TYPE
    SYNTAX          SonusSupportFlag
    MAX-ACCESS      read-write
    STATUS          current
    DESCRIPTION     
            "Is the Calling Subs Orig Facility Marks parameter supported for the ISUP Signaling Profile."
    ::= { sonusIsupsgSignalingProfileEntry 215 }

sonusIsupsgSignalingProfileCdTfm OBJECT-TYPE
    SYNTAX          SonusSupportFlag
    MAX-ACCESS      read-write
    STATUS          current
    DESCRIPTION     
            "Is the Called Subs Term Facility Marks parameter supported for the ISUP Signaling Profile."
    ::= { sonusIsupsgSignalingProfileEntry 216 }

sonusIsupsgSignalingProfileNii OBJECT-TYPE
    SYNTAX          SonusSupportFlag
    MAX-ACCESS      read-write
    STATUS          current
    DESCRIPTION     
            "Is the National Information Indicators parameter supported for the ISUP Signaling Profile."
    ::= { sonusIsupsgSignalingProfileEntry 217 }

sonusIsupsgSignalingProfileNiri OBJECT-TYPE
    SYNTAX          SonusSupportFlag
    MAX-ACCESS      read-write
    STATUS          current
    DESCRIPTION     
            "Is the National Information Request Indicators parameter supported for the ISUP Signaling Profile."
    ::= { sonusIsupsgSignalingProfileEntry 218 }

sonusIsupsgSignalingProfileNfci OBJECT-TYPE
    SYNTAX          SonusSupportFlag
    MAX-ACCESS      read-write
    STATUS          current
    DESCRIPTION     
            "Is the National Forward Call Indicators parameter supported for the ISUP Signaling Profile."
    ::= { sonusIsupsgSignalingProfileEntry 219 }

sonusIsupsgSignalingProfilePresNum OBJECT-TYPE
    SYNTAX          SonusSupportFlag
    MAX-ACCESS      read-write
    STATUS          current
    DESCRIPTION     
            "Is the Presentation Number parameter supported for the ISUP Signaling Profile."
    ::= { sonusIsupsgSignalingProfileEntry 220 }

sonusIsupsgSignalingProfileLdli OBJECT-TYPE
    SYNTAX          SonusSupportFlag
    MAX-ACCESS      read-write
    STATUS          current
    DESCRIPTION     
            "Is the Last Diverted Line Identity parameter supported for the ISUP Signaling Profile."
    ::= { sonusIsupsgSignalingProfileEntry 221 }

sonusIsupsgSignalingProfilePcli OBJECT-TYPE
    SYNTAX          SonusSupportFlag
    MAX-ACCESS      read-write
    STATUS          current
    DESCRIPTION     
            "Is the Partial Calling Line Identity parameter supported for the ISUP Signaling Profile."
    ::= { sonusIsupsgSignalingProfileEntry 222 }

sonusIsupsgSignalingProfileNfciLnk OBJECT-TYPE
    SYNTAX          SonusSupportFlag
    MAX-ACCESS      read-write
    STATUS          current
    DESCRIPTION     
            "Is the National Forward Call Indicators Link-by-Link parameter supported for the ISUP Signaling Profile."
    ::= { sonusIsupsgSignalingProfileEntry 223 }

sonusIsupsgSignalingProfileInrInAllStates OBJECT-TYPE
    SYNTAX          SonusSupportFlag
    MAX-ACCESS      read-write
    STATUS          current
    DESCRIPTION     
            "Are the INR and INF messages supported supported in all states for the ISUP Signaling Profile."
    ::= { sonusIsupsgSignalingProfileEntry 224 }

sonusIsupsgSignalingProfileNfciLnkProc OBJECT-TYPE
    SYNTAX          SonusSupportFlag
    MAX-ACCESS      read-write
    STATUS          current
    DESCRIPTION     
            "Is the National Forward Call Indicators Link-by-Link parameter procedure supported for the ISUP Signaling Profile."
    ::= { sonusIsupsgSignalingProfileEntry 225 }

sonusIsupsgSignalingProfileAnsi95Cfn OBJECT-TYPE
    SYNTAX          SonusSupportFlag
    MAX-ACCESS      read-write
    STATUS          current
    DESCRIPTION     
            "Should the ANSI-95 format for Confusion (CFN), which includes 
             optional parameters, be used."
    DEFVAL          { supported }
    ::= { sonusIsupsgSignalingProfileEntry 226 }

sonusIsupsgSignalingProfileAllianceScreenInd OBJECT-TYPE
    SYNTAX          SonusSupportFlag
    MAX-ACCESS      read-write
    STATUS          current
    DESCRIPTION     
            "Is the Alliance Screen Indicator parameter supported for the ISUP Signaling Profile"
    DEFVAL          { supported }
    ::= { sonusIsupsgSignalingProfileEntry 227 }

sonusIsupsgSignalingProfileAnnouncementInd OBJECT-TYPE
    SYNTAX          SonusSupportFlag
    MAX-ACCESS      read-write
    STATUS          current
    DESCRIPTION     
            "Is the Announcement Indicator parameter supported for the ISUP Signaling Profile."
    DEFVAL          { supported }
    ::= { sonusIsupsgSignalingProfileEntry 228 }

sonusIsupsgSignalingProfileDialedNumber OBJECT-TYPE
    SYNTAX          SonusSupportFlag
    MAX-ACCESS      read-write
    STATUS          current
    DESCRIPTION     
            "Is the Dialed Number parameter supported for the ISUP Signaling Profile."
    DEFVAL          { supported }
    ::= { sonusIsupsgSignalingProfileEntry 229 }

sonusIsupsgSignalingProfileForwardNetworkSpecificInfo OBJECT-TYPE
    SYNTAX          SonusSupportFlag
    MAX-ACCESS      read-write
    STATUS          current
    DESCRIPTION     
            "Is the Forward Network Specific Information parameter supported for the ISUP Signaling Profile."
    DEFVAL          { supported }
    ::= { sonusIsupsgSignalingProfileEntry 230 }

sonusIsupsgSignalingProfileGenericOperation OBJECT-TYPE
    SYNTAX          SonusSupportFlag
    MAX-ACCESS      read-write
    STATUS          current
    DESCRIPTION     
            "Is the Generic Operation parameter supported for the ISUP Signaling Profile."
    DEFVAL          { supported }
    ::= { sonusIsupsgSignalingProfileEntry 231 }

sonusIsupsgSignalingProfileHardToReachInd OBJECT-TYPE
    SYNTAX          SonusSupportFlag
    MAX-ACCESS      read-write
    STATUS          current
    DESCRIPTION     
            "Is the Hard To Reach Indicator parameter supported for the ISUP Signaling Profile."
    DEFVAL          { supported }
    ::= { sonusIsupsgSignalingProfileEntry 232 }

sonusIsupsgSignalingProfileNetworkManagementInfo OBJECT-TYPE
    SYNTAX          SonusSupportFlag
    MAX-ACCESS      read-write
    STATUS          current
    DESCRIPTION     
            "Is the Network Management Information parameter supported for the ISUP Signaling Profile."
    DEFVAL          { supported }
    ::= { sonusIsupsgSignalingProfileEntry 233 }

sonusIsupsgSignalingProfileNetworkSwitchNumber OBJECT-TYPE
    SYNTAX          SonusSupportFlag
    MAX-ACCESS      read-write
    STATUS          current
    DESCRIPTION     
            "Is the Network Switch Number parameter supported for the ISUP Signaling Profile."
    DEFVAL          { supported }
    ::= { sonusIsupsgSignalingProfileEntry 234 }

sonusIsupsgSignalingProfileRoutingInformationInd OBJECT-TYPE
    SYNTAX          SonusSupportFlag
    MAX-ACCESS      read-write
    STATUS          current
    DESCRIPTION     
            "Is the Routing Information Indicator parameter supported for the ISUP Signaling Profile."
    DEFVAL          { supported }
    ::= { sonusIsupsgSignalingProfileEntry 235 }

sonusIsupsgSignalingProfileSdnIncrement OBJECT-TYPE
    SYNTAX          SonusSupportFlag
    MAX-ACCESS      read-write
    STATUS          current
    DESCRIPTION     
            "Is the SDN SID/ANI Increment Message supported for the ISUP Signaling Profile."
    DEFVAL          { supported }
    ::= { sonusIsupsgSignalingProfileEntry 236 }

sonusIsupsgSignalingProfileAnsi95Cqm OBJECT-TYPE
    SYNTAX          SonusSupportFlag
    MAX-ACCESS      read-write
    STATUS          current
    DESCRIPTION     
            "Is the ANSI 95 version of the CQM message containing the optional pointer supported for the ISUP Signaling Profile."
    DEFVAL          { supported }
    ::= { sonusIsupsgSignalingProfileEntry 237 }

sonusIsupsgSignalingProfileBCM OBJECT-TYPE
    SYNTAX          SonusSupportFlag
    MAX-ACCESS      read-write
    STATUS          current
    DESCRIPTION     
            "Is the Bacwards Charging Message supported for the ISUP Signaling Profile."
    DEFVAL          { unsupported }
    ::= { sonusIsupsgSignalingProfileEntry 238 }

sonusIsupsgSignalingProfileJpnEmergencyCall OBJECT-TYPE
    SYNTAX          SonusSupportFlag
    MAX-ACCESS      read-write
    STATUS          current
    DESCRIPTION     
            "Is the Japan Emergency Indicator parameter supported for the ISUP Signaling Profile."
    ::= { sonusIsupsgSignalingProfileEntry 239 }

sonusIsupsgSignalingProfileGenNumRepeatable OBJECT-TYPE
    SYNTAX          SonusSupportFlag
    MAX-ACCESS      read-write
    STATUS          current
    DESCRIPTION     
            "Is the Generic Number a Repeatable Parameter."
    ::= { sonusIsupsgSignalingProfileEntry 240 }

sonusIsupsgSignalingProfileGenNumIamRepeatable OBJECT-TYPE
    SYNTAX          SonusSupportFlag
    MAX-ACCESS      read-write
    STATUS          current
    DESCRIPTION     
            "Is the Generic Number a Repeatable Parameter in the IAM Message."
    ::= { sonusIsupsgSignalingProfileEntry 241 }

sonusIsupsgSignalingProfileGenNotifRepeatable OBJECT-TYPE
    SYNTAX          SonusSupportFlag
    MAX-ACCESS      read-write
    STATUS          current
    DESCRIPTION     
            "Is the Generic Notification a Repeatable Parameter."
    ::= { sonusIsupsgSignalingProfileEntry 242 }

sonusIsupsgSignalingProfileServActvInRel OBJECT-TYPE
    SYNTAX          SonusSupportFlag
    MAX-ACCESS      read-write
    STATUS          current
    DESCRIPTION     
            "Is the Service Activation Parameter supported in the REL message."
    ::= { sonusIsupsgSignalingProfileEntry 243 }

sonusIsupsgSignalingProfileUuindCon OBJECT-TYPE
    SYNTAX          SonusSupportFlag
    MAX-ACCESS      read-write
    STATUS          current
    DESCRIPTION     
            "Is the User-to-User Indicators Parameter Supported in the CON."
    ::= { sonusIsupsgSignalingProfileEntry 244 }

sonusIsupsgSignalingProfileUuiInInf OBJECT-TYPE
    SYNTAX          SonusSupportFlag
    MAX-ACCESS      read-write
    STATUS          current
    DESCRIPTION     
            "Is the User-to-User Information Parameter Supported in the INF."
    ::= { sonusIsupsgSignalingProfileEntry 245 }

sonusIsupsgSignalingProfileChargeMsgInSpeech OBJECT-TYPE
    SYNTAX          SonusSupportFlag
    MAX-ACCESS      read-write
    STATUS          current
    DESCRIPTION     
            "Is the Charge Message In Speech Parameter supported for the ISUP Signaling Profile."
    ::= { sonusIsupsgSignalingProfileEntry 246 }

sonusIsupsgSignalingProfileEmergencyCallInf OBJECT-TYPE
    SYNTAX          SonusSupportFlag
    MAX-ACCESS      read-write
    STATUS          current
    DESCRIPTION     
            "Is the Emergency Call Information Parameter supported in the CPG."
    ::= { sonusIsupsgSignalingProfileEntry 247 }

sonusIsupsgSignalingProfileT7Transit OBJECT-TYPE
    SYNTAX          SonusSupportFlag
    MAX-ACCESS      read-write
    STATUS          current
    DESCRIPTION     
            "Is the T7 Timer run for a Transit Call in the ISUP Signaling Profile."
    ::= { sonusIsupsgSignalingProfileEntry 248 }

sonusIsupsgSignalingProfileNSA OBJECT-TYPE
    SYNTAX          SonusSupportFlag
    MAX-ACCESS      read-write
    STATUS          current
    DESCRIPTION     
            "Is the Network Specific ANM Parameter Supported in the ANM."
    ::= { sonusIsupsgSignalingProfileEntry 249 }

sonusIsupsgSignalingProfileInvTNSRelease OBJECT-TYPE
    SYNTAX          SonusSupportFlag
    MAX-ACCESS      read-write
    STATUS          current
    DESCRIPTION     
            "Should the Q931 Release handling for invalid TNS be applied."
    ::= { sonusIsupsgSignalingProfileEntry 250 }

sonusIsupsgSignalingProfileJTSpecificParam OBJECT-TYPE
    SYNTAX          SonusSupportFlag
    MAX-ACCESS      read-write
    STATUS          current
    DESCRIPTION     
            "Is the JT Specific ISUP Parameter Supported in the ISUP Signaling Profile."
    ::= { sonusIsupsgSignalingProfileEntry 251 }

sonusIsupsgSignalingProfileIsdnUserPartIwk OBJECT-TYPE
    SYNTAX          SonusSupportFlag
    MAX-ACCESS      read-write
    STATUS          current
    DESCRIPTION     
            "Should the FCI ISDN User Part indicator be overwritten for NON-ISUP to ISUP calls."
    ::= { sonusIsupsgSignalingProfileEntry 252 }

sonusIsupsgSignalingProfileIsdnUserPartTrans OBJECT-TYPE
    SYNTAX          SonusSupportFlag
    MAX-ACCESS      read-write
    STATUS          current
    DESCRIPTION     
            "Should the FCI ISDN User Part indicator be overwritten for ISUP to ISUP calls."
    ::= { sonusIsupsgSignalingProfileEntry 253 }

sonusIsupsgSignalingProfileConnectionPointTrunkType OBJECT-TYPE
    SYNTAX          SonusSupportFlag
    MAX-ACCESS      read-write
    STATUS          current
    DESCRIPTION     
            "Is the Connection Point Trunk Type supported for the ISUP Signaling Profile."
    ::= { sonusIsupsgSignalingProfileEntry 254 }

sonusIsupsgSignalingProfileIsdnUserPartChosenCarrier OBJECT-TYPE
    SYNTAX          SonusSupportFlag
    MAX-ACCESS      read-write
    STATUS          current
    DESCRIPTION     
            "Should the FCI ISDN User Part indicator be overwritten based on the Chosen Carrier."
    ::= { sonusIsupsgSignalingProfileEntry 255 }

sonusIsupsgSignalingProfileMaxCqmRange OBJECT-TYPE
    SYNTAX          Integer32 (0..31)
    MAX-ACCESS      read-write
    STATUS          current
    DESCRIPTION     
            "The maximum value for the Range field in the CQM message generated by the GSX"
    DEFVAL          { 31 }
    ::= { sonusIsupsgSignalingProfileEntry 256 }

sonusIsupsgSignalingProfileTruncateCDPN OBJECT-TYPE
    SYNTAX          SonusSupportFlag
    MAX-ACCESS      read-write
    STATUS          current
    DESCRIPTION     
            "If the CDPN is greater than the MaxCalledPartyDigits should it be truncated or the call released"
    ::= { sonusIsupsgSignalingProfileEntry 257 }

sonusIsupsgSignalingProfileNoIPEchoInd OBJECT-TYPE
    SYNTAX          SonusSupportFlag
    MAX-ACCESS      read-write
    STATUS          current
    DESCRIPTION     
            "If the Echo Control indication should be set for an IP to PSTN call"
    ::= { sonusIsupsgSignalingProfileEntry 258 }

sonusIsupsgSignalingProfileVisitorMA OBJECT-TYPE
    SYNTAX          SonusSupportFlag
    MAX-ACCESS      read-write
    STATUS          current
    DESCRIPTION     
            "If the Visitor MA parameter is supported"
    ::= { sonusIsupsgSignalingProfileEntry 259 }

sonusIsupsgSignalingProfileSendBLOOnHwBlock OBJECT-TYPE
    SYNTAX          SonusSupportFlag
    MAX-ACCESS      read-write
    STATUS          current
    DESCRIPTION     
            "Send BLO when a circuit is hardware blocked."
    ::= { sonusIsupsgSignalingProfileEntry 260 }

sonusIsupsgSignalingProfileAllowCallsOnHwBlock OBJECT-TYPE
    SYNTAX          SonusSupportFlag
    MAX-ACCESS      read-write
    STATUS          current
    DESCRIPTION     
            "Do not reject calls on a hardware blocked circuit."
    ::= { sonusIsupsgSignalingProfileEntry 261 }

sonusIsupsgSignalingProfileOBCIPreSubscriptionOnly OBJECT-TYPE
    SYNTAX          SonusSupportFlag
    MAX-ACCESS      read-write
    STATUS          obsolete
    DESCRIPTION     
            "Generate OBCI in early ACM for pre-subscription call only - obsolete in 6.5 onwards"
    ::= { sonusIsupsgSignalingProfileEntry 262 }

sonusIsupsgSignalingProfileSendRSCForCallsOnHwBlock OBJECT-TYPE
    SYNTAX          SonusSupportFlag
    MAX-ACCESS      read-write
    STATUS          current
    DESCRIPTION     
            "Send RSC for when a call is impacted by a hardware blockage on a circuit."
    ::= { sonusIsupsgSignalingProfileEntry 263 }

sonusIsupsgSignalingProfileAllowUnscreenedCIN OBJECT-TYPE
    SYNTAX          SonusSupportFlag
    MAX-ACCESS      read-write
    STATUS          current
    DESCRIPTION     
            "Should the values 0 and 2 of Screening Indicator be allowed in ISUP."
    ::= { sonusIsupsgSignalingProfileEntry 264 }

sonusIsupsgSignalingProfileIAMGenCarrierCodeInCDR OBJECT-TYPE
    SYNTAX          SonusSupportFlag
    MAX-ACCESS      read-write
    STATUS          current
    DESCRIPTION     
            "Should the IAM-Generated Carrier Code always be populated in the CDR for Japan regardless of type."
    ::= { sonusIsupsgSignalingProfileEntry 265 }

sonusIsupsgSignalingProfileDropUSIFromNonIsup OBJECT-TYPE
    SYNTAX          SonusSupportFlag
    MAX-ACCESS      read-write
    STATUS          current
    DESCRIPTION     
            "If the USI parameter is supported when the far-side is not ISUP."
    ::= { sonusIsupsgSignalingProfileEntry 266 }

sonusIsupsgSignalingProfileAssumeOgDeviceIncluded OBJECT-TYPE
    SYNTAX          SonusSupportFlag
    MAX-ACCESS      read-write
    STATUS          current
    DESCRIPTION     
            "Should the egress echo cancellation software assume for an
             ISUP transit call that an outgoing device has been included,
             regardless of the NCI setting."
    ::= { sonusIsupsgSignalingProfileEntry 267 }

sonusIsupsgSignalingProfilePreventACMtoCPGMapping OBJECT-TYPE
    SYNTAX          SonusSupportFlag
    MAX-ACCESS      read-write
    STATUS          current
    DESCRIPTION     
            "If an ACM has already been sent on the ingress trunk group
             due to a script, T11 timer expiry or some other event and an
             ACM is received on the egress trunk group it is usually converted
             into a CPG message on the ingress trunk group. When this control
             is set to supported the ACM to CPG mapping is prevented and the
             received ACM is silently discarded on the ingress side."
    ::= { sonusIsupsgSignalingProfileEntry 268 }

sonusIsupsgSignalingProfileSignalOnlySipAlert OBJECT-TYPE
    SYNTAX          SonusSupportFlag
    MAX-ACCESS      read-write
    STATUS          current
    DESCRIPTION     
            "On an ISUP-SIP call, only generate the ACM/CPG message in response to
             an 180 message - alerting. No ACM/CPG should be generated for other
             18x messages or 300 messages."
    ::= { sonusIsupsgSignalingProfileEntry 269 }

sonusIsupsgSignalingProfileDontMapToHeaderToOCN OBJECT-TYPE
    SYNTAX          SonusSupportFlag
    MAX-ACCESS      read-write
    STATUS          current
    DESCRIPTION     
            "When interworking between SIP and ISUP the To header field should not be
             interworked to the ISUP original called number parameter."
    ::= { sonusIsupsgSignalingProfileEntry 270 }

sonusIsupsgSignalingProfileNoINNumberUpdates OBJECT-TYPE
    SYNTAX          SonusSupportFlag
    MAX-ACCESS      read-write
    STATUS          current
    DESCRIPTION     
            "When the PSX performs a TOLL FREE number translation the called IN and
             original called IN number parameters used in Japan should not be updated
             based on the new called party number parameter."
    ::= { sonusIsupsgSignalingProfileEntry 271 }

sonusIsupsgSignalingProfileUsePSXChgIndForCpgInPresubCall OBJECT-TYPE
    SYNTAX          SonusSupportFlag
    MAX-ACCESS      read-write
    STATUS          current
    DESCRIPTION     
            "Should the PSX ACM charge indicator be used to overwrite the charge 
             indicator field of the BCI for CPG messages or should the value 
             received be transited."
    ::= { sonusIsupsgSignalingProfileEntry 272 }

sonusIsupsgSignalingProfileAlwaysAddOptionalPtr OBJECT-TYPE
    SYNTAX          SonusSupportFlag
    MAX-ACCESS      read-write
    STATUS          current
    DESCRIPTION     
            "Should the optional parameter pointer always be added into ISUP
             messages even when no optional parameters are defined"
    ::= { sonusIsupsgSignalingProfileEntry 273 }

sonusIsupsgSignalingProfileSuppressCITForPreSubACM OBJECT-TYPE
    SYNTAX          SonusSupportFlag
    MAX-ACCESS      read-write
    STATUS          current
    DESCRIPTION     
            "Ensure the Carrier Information Transfer parameter is suppressed in
             an Early ACM for Pre-Subscription call."
    ::= { sonusIsupsgSignalingProfileEntry 274 }

sonusIsupsgSignalingProfileSendOnlyACMFor181 OBJECT-TYPE
    SYNTAX          SonusSupportFlag
    MAX-ACCESS      read-write
    STATUS          current
    DESCRIPTION     
            "For an ISUP-SIP call, only send an ACM message if a 181 is received
             before an ACM is sent. In this case we do not want to send an ACM
             and CPG. If an ACM has already been sent then the 181 is mapped to a
             CPG"
    ::= { sonusIsupsgSignalingProfileEntry 275 }

sonusIsupsgSignalingProfileDontSendEXM OBJECT-TYPE
    SYNTAX          SonusSupportFlag
    MAX-ACCESS      read-write
    STATUS          current
    DESCRIPTION     
            "Specifies whether its ok to send EXM messages on a trunk
             group"
    ::= { sonusIsupsgSignalingProfileEntry 276 }

sonusIsupsgSignalingProfileCITTermExchangeLogic OBJECT-TYPE
    SYNTAX          SonusSupportFlag
    MAX-ACCESS      read-write
    STATUS          current
    DESCRIPTION     
            "CIT and CAI only in first backward message when terminating exchange"
    ::= { sonusIsupsgSignalingProfileEntry 277 }

sonusIsupsgSignalingProfileBCIinCPGwithCIT OBJECT-TYPE
    SYNTAX          SonusSupportFlag
    MAX-ACCESS      read-write
    STATUS          current
    DESCRIPTION     
            "BCI only in CPG if CIT is in the msg"
    ::= { sonusIsupsgSignalingProfileEntry 278 }

sonusIsupsgSignalingProfileReaffirmBlockAfterReset OBJECT-TYPE
    SYNTAX          SonusSupportFlag
    MAX-ACCESS      read-write
    STATUS          current
    DESCRIPTION     
            "When RSC or GRS is sent on a locally blocked circuit, BLO
             will also be sent to reaffirm the blocking."
    ::= { sonusIsupsgSignalingProfileEntry 279 }

sonusIsupsgSignalingProfileDontGenerateDiags OBJECT-TYPE
    SYNTAX          SonusSupportFlag
    MAX-ACCESS      read-write
    STATUS          current
    DESCRIPTION     
            "Specifies if diagnositcs should not be generated for JAPAN"
    ::= { sonusIsupsgSignalingProfileEntry 280 }

sonusIsupsgSignalingProfileOnlyCPGInbandBeforeACM OBJECT-TYPE
    SYNTAX          SonusSupportFlag
    MAX-ACCESS      read-write
    STATUS          current
    DESCRIPTION     
            "Should a CPG containing an inband information event arriving 
             before an ACM be transited. If set CPG without an inband information 
             event arriving before ACM will be discarded"
    ::= { sonusIsupsgSignalingProfileEntry 281 }

sonusIsupsgSignalingProfileSimpleEcBCIInAllBkMsg OBJECT-TYPE
    SYNTAX          SonusSupportFlag
    MAX-ACCESS      read-write
    STATUS          current
    DESCRIPTION     
            "For simple echo control, examine every backward message 
             for the BCI echo control indication field and act accordingly"
    ::= { sonusIsupsgSignalingProfileEntry 282 }

sonusIsupsgSignalingProfileAllowCAForAnnouncements OBJECT-TYPE
    SYNTAX          SonusSupportFlag
    MAX-ACCESS      read-write
    STATUS          current
    DESCRIPTION     
            "Allow charge area parameter for announcements"
    ::= { sonusIsupsgSignalingProfileEntry 283 }

sonusIsupsgSignalingProfileUniqueTransitCIT OBJECT-TYPE
    SYNTAX          SonusSupportFlag
    MAX-ACCESS      read-write
    STATUS          current
    DESCRIPTION     
            "PROTOCOLS   - Japan only
             DEFAULT	 - UNSUPPORTED
             UNSUPPORTED - The GSX will add in transit carrier data with the same carrier
             			   code as the previous code if configured by the PSX
             SUPPORTED   - The GSX will compare the transit carrier code configured on the
             			   PSX with the last carrier code add by the previous exchange and 
             			   if they are both transit and both have the same carrier code the
             			   GSX will not add in duplicate information. The ingress signaling
             			   profile controls checking the backward messages and the egress
             			   signaling profile controls checking the forward messages.
             CMD		 - UNIQUE TRANSIT CIT
             SCREEN		 - Services - Unique Transit CIT
             CONTROL	 - SS7_CONTROL_UNIQUE_TRANSIT_CIT
             REQS		 - PCR710 CQID51235"
    ::= { sonusIsupsgSignalingProfileEntry 284 }

sonusIsupsgSignalingProfileValidateISUBFromSIP OBJECT-TYPE
    SYNTAX          SonusSupportFlag
    MAX-ACCESS      read-write
    STATUS          current
    DESCRIPTION     
            "PROTOCOLS	 - Japan Only
             DEFAULT	 - UNSUPPORTED
             UNSUPPORTED - The GSX will not check the ISUB digits
             SUPPORTED	 - The GSX will ensure that only digits
             			   0-9 are allowed in the NSAP ISUB
             			   from SIP
             CMD		 - VALIDATEISUBFROMSIP
             SCREEN		 - Services - Validate ISUB
             CONTROL	 - SS7_CONTROL_VALIDATE_ISUB_FROM_SIP
             REQS		 - WILLCOM PCR 151 and PCR 152"
    ::= { sonusIsupsgSignalingProfileEntry 285 }

sonusIsupsgSignalingProfileISUBTypeFromSIP OBJECT-TYPE
    SYNTAX          INTEGER { nsap(0), userspec(1), both(2), none(3) }
    MAX-ACCESS      read-write
    STATUS          current
    DESCRIPTION     
            "PROTOCOLS	 - Japan Only
             DEFAULT	 - NSAP
             NSAP		 - only ISUB of type NSAP from SIP supported
             USERSPEC	 - only ISUB of type USER SPECIFIC from SIP supported
             BOTH		 - NSAP and USER SPECIFIC ISUB from SIP supported
             NONE		 - No ISUB types from SIP supported
             CMD		 - ISUBTYPEFROMSIP
             SCREEN		 - Services - ISUB Type from SIP
             CONTROL	 - SS7_CONTROL_ISUB_TYPE_NSAP
             			   SS7_CONTROL_ISUB_TYPE_USER_SPEC
             			   SS7_CONTROL_ISUB_TYPE_NONE
             			   SS7_CONTROL_ISUB_TYPE_BOTH
             REQS		 - WILLCOM PCR 151 and PCR 152"
    DEFVAL          { 0 }
    ::= { sonusIsupsgSignalingProfileEntry 286 }

sonusIsupsgSignalingProfileQOR OBJECT-TYPE
    SYNTAX          SonusSupportFlag
    MAX-ACCESS      read-write
    STATUS          current
    DESCRIPTION     
            "PROTOCOLS   - ITU + CHINA
             DEFAULT     - UNSUPPORTED
             UNSUPPORTED - The Query on release capability parameter will not be supported
                  		 SUPPORTED	 - The Query on release capability parameter will be supported
             CMD         - QOR
             SCREEN      - Parameter - Query on Release
             CONTROL     - SS7_CONTROL_QOR
             REQS        - Q763 section 3.91 for supporting number portability"
    ::= { sonusIsupsgSignalingProfileEntry 288 }

sonusIsupsgSignalingProfileNPFI OBJECT-TYPE
    SYNTAX          SonusSupportFlag
    MAX-ACCESS      read-write
    STATUS          current
    DESCRIPTION     
            "PROTOCOLS   - ITU + CHINA
             DEFAULT     - UNSUPPORTED
             UNSUPPORTED - The Number Portability Forward Information parameter will not be supported
                  		 SUPPORTED	 - The Number Portability Forward Information parameter will be supported
             CMD         - NPFI
             SCREEN      - Parameter - NPFI
             CONTROL     - SS7_CONTROL_NPFI
             REQS        - Q763 section 3.101 for supporting number portability"
    ::= { sonusIsupsgSignalingProfileEntry 289 }

sonusIsupsgSignalingProfileChgMsgBeforeAcm OBJECT-TYPE
    SYNTAX          SonusSupportFlag
    MAX-ACCESS      read-write
    STATUS          current
    DESCRIPTION     
            "PROTOCOLS   - Japan only
             DEFAULT     - UNSUPPORTED
             UNSUPPORTED - The GSX will not transit the CHG message in the backward direction
             						   before an ACM has been received.
             SUPPORTED   - The GSX will transit the CHG message in the backward direction
             						   before an ACM has been received.
             CMD         - CHGBEFOREACM
             SCREEN      - Messages - CHG before ACM
             CONTROL     - SS7_CONTROL_CHG_BEFORE_ACM"
    ::= { sonusIsupsgSignalingProfileEntry 290 }

sonusIsupsgSignalingProfileForceEchoCntrl OBJECT-TYPE
    SYNTAX          SonusSupportFlag
    MAX-ACCESS      read-write
    STATUS          current
    DESCRIPTION     
            "Indicated that echo cancellation will be applied on calls regardless of
             information contained in signalling messages with the exception of
             			 data calls"
    ::= { sonusIsupsgSignalingProfileEntry 291 }

sonusIsupsgSignalingProfileNoObciSipAcm OBJECT-TYPE
    SYNTAX          SonusSupportFlag
    MAX-ACCESS      read-write
    STATUS          current
    DESCRIPTION     
            "PROTOCOLS   - Generic
             DEFAULT     - UNSUPPORTED
             UNSUPPORTED - The GSX will not include the OBCI parameter in the ACM in all 
             						   the existing scenarios.
             SUPPORTED   - The GSX will not include the OBCI parameter in the ACM message
             						   when interworking with SIP
             CMD         - NOOBCISIPACM
             SCREEN      - Services - No OBCI SIP ACM
             CONTROL     - SS7_CONTROL_NO_OBCI_SIP_ACM"
    ::= { sonusIsupsgSignalingProfileEntry 292 }

sonusIsupsgSignalingProfileBuildRdiForSipIwk OBJECT-TYPE
    SYNTAX          SonusSupportFlag
    MAX-ACCESS      read-write
    STATUS          current
    DESCRIPTION     
            "PROTOCOLS   - All
             DEFAULT     - UNSUPPORTED
             			 SUPPORTED   - when interworking with SIP and the IAM
             						   contains the original called number
             						   and redirecting number parameters but
             						   no redirecting information parameter
             						   the GSX will generated one with the 
             						   following values.
             
             						redirecting indicator (3) call forwarded
             						redirecting counter (1)
             						original redirection reason (2) no reply
             					 	redirection reason (2) no reply
             
             			 UNSUPPORTED - no RDI is generated.
             CMD         - BUILDRDIFORSIPIWK
             SCREEN      - Services - Build RDI for SIP IWK
             CONTROL     - SS7_CONTROL_BUILD_RDI_FOR_SIP_IWK
             REQS        - WILLCOM PCR 982"
    ::= { sonusIsupsgSignalingProfileEntry 293 }

sonusIsupsgSignalingProfileNoAcmObciForSipApn OBJECT-TYPE
    SYNTAX          SonusSupportFlag
    MAX-ACCESS      read-write
    STATUS          current
    DESCRIPTION     
            "PROTOCOLS   - Generic
             DEFAULT     - UNSUPPORTED
             UNSUPPORTED - The GSX will include the OBCI parameter in the ACM.
             SUPPORTED   - The GSX will not include the OBCI parameter in the ACM message
                              when interworking to SIP and the NOA is 0x78 (APN). When
                              interworking with SIP-I with MIME containing ACM with OBCI
                              the ACM is transited with OBCI.
             CMD         - NO OBCI FOR SIP APN
             SCREEN      - Services - No OBCI FOR SIP APN
             CONTROL     - SS7_CONTROL_NO_OBCI_FOR_SIP_APN"
    ::= { sonusIsupsgSignalingProfileEntry 294 }

sonusIsupsgSignalingProfileNetworkData OBJECT-TYPE
    SYNTAX          SonusSupportFlag
    MAX-ACCESS      read-write
    STATUS          current
    DESCRIPTION     
            "PROTOCOLS   - ANSI, ITU
             DEFAULT     - UNSUPPORTED
             UNSUPPORTED - Network Data is not Supported in the IAM message.
             SUPPORTED   - Network Data is Supported in the IAM message.
             CMD         - NETWORK DATA
             SCREEN      - Parameters - Network Data
             CONTROL     - SS7_CONTROL_NETWORK_DATA"
    ::= { sonusIsupsgSignalingProfileEntry 295 }

sonusIsupsgSignalingProfileAlwaysAddCNID OBJECT-TYPE
    SYNTAX          SonusSupportFlag
    MAX-ACCESS      read-write
    STATUS          current
    DESCRIPTION     
            "PROTOCOLS   - Japan
             DEFAULT     - UNSUPPORTED
             			 SUPPORTED   - when interworking with SIP and the 
             						   calling party number is restricted then
             						   the cause of no ID parameter is included
             						   in the IAM even if there is no 
             						   parameter data received from SIP.
             
             			 UNSUPPORTED - CNID is only generated if received from
             						   SIP.
             CMD         - CNID ALWAYS ADDED
             SCREEN      - Services - CNID always added
             CONTROL     - SS7_CONTROL_ALWAYS_ADD_CNID
             REQS        - CQ60811"
    ::= { sonusIsupsgSignalingProfileEntry 296 }

sonusIsupsgSignalingProfileCHGBetweenACMandANM OBJECT-TYPE
    SYNTAX          SonusSupportFlag
    MAX-ACCESS      read-write
    STATUS          current
    DESCRIPTION     
            "PROTOCOLS   - Japan
             DEFAULT     - SUPPORTED. 
             UNSUPPORTED - The GSX will not transit the CHG message in the backward direction
             						   between an ACM and ANM. 
             SUPPORTED   - The GSX will transit the CHG message in the backward direction
             						   between an ACM and ANM.
             CMD         - CHGBETWEENACMANDANM
             SCREEN      - Messages - CHG between ACM-ANM
             CONTROL     - SS7_CONTROL_CHG_BETWEEN_ACM_AND_ANM
             REQS        - CQ63302,CQ63184"
    ::= { sonusIsupsgSignalingProfileEntry 297 }

sonusIsupsgSignalingProfileItuCAI24 OBJECT-TYPE
    SYNTAX          SonusSupportFlag
    MAX-ACCESS      read-write
    STATUS          current
    DESCRIPTION     
            "PROTOCOLS   - ITU, CHINA
             DEFAULT     - UNSUPPORTED
             UNSUPPORTED - ITU Cause Value 24 - Call Rejected due to
                           Feature at Destination - is not recognized.
             SUPPORTED   - ITU Cause Value 24 is recognized.
             CMD         - ITUCAI24
             SCREEN      - Services - ITU CAI 24
             CONTROL     - SS7_CONTROL_ITU_CAI_24_SUPPORT
             REQS        - MGCF TS29.163"
    ::= { sonusIsupsgSignalingProfileEntry 298 }

sonusIsupsgSignalingProfileCellularCPCs OBJECT-TYPE
    SYNTAX          SonusSupportFlag
    MAX-ACCESS      read-write
    STATUS          current
    DESCRIPTION     
            "PROTOCOLS   - ITU, CHINA
             DEFAULT     - UNSUPPORTED
             UNSUPPORTED - Calling Party Category values Cellular and
                           Cellular Roaming are not recognized.
             SUPPORTED   - Calling Party Category values Cellular and
                           Cellular Roaming are recognized.
             CMD         - CELLULARCPCS
             SCREEN      - Services - Cellular CPCs
             CONTROL     - SS7_CONTROL_CELLULAR_CPCS_SUPPORT
             REQS        - MGCF TS29.163"
    ::= { sonusIsupsgSignalingProfileEntry 299 }

sonusIsupsgSignalingProfileIepsCPC OBJECT-TYPE
    SYNTAX          SonusSupportFlag
    MAX-ACCESS      read-write
    STATUS          current
    DESCRIPTION     
            "PROTOCOLS   - ITU, CHINA
             DEFAULT     - UNSUPPORTED
             UNSUPPORTED - Calling Party Category value IEPS is not
                           recognized.
             SUPPORTED   - Calling Party Category value IEPS is recognized.
             CMD         - IEPSCPC
             SCREEN      - Services - IEPS CPC
             CONTROL     - SS7_CONTROL_IEPS_CPC_SUPPORT
             REQS        - MGCF TS29.163"
    ::= { sonusIsupsgSignalingProfileEntry 300 }

sonusIsupsgSignalingProfileTandemCallCounter OBJECT-TYPE
    SYNTAX          SonusSupportFlag
    MAX-ACCESS      read-write
    STATUS          current
    DESCRIPTION     
            "PROTOCOLS   - JAPAN
             DEFAULT	 - UNSUPPORTED
             UNSUPPORTED - The GSX will not be able to decode and transit 
                           the Tandem Call Counter parameter received in
                           IAM message.
             SUPPORTED   - The GSX will decode/encode, increment  and transit the Tandem
                           Call Counter parameter received in IAM message.
             CMD		 - TANDEMCALLCOUNTER
             SCREEN		 - Parameters - Tandem Call Counter
             CONTROL	 - SS7_CONTROL_TANDEM_CALL_COUNTER_SUPPORT
             REQS        - SBTM - PCR1404"
    ::= { sonusIsupsgSignalingProfileEntry 301 }

sonusIsupsgSignalingProfileRouteInformation OBJECT-TYPE
    SYNTAX          SonusSupportFlag
    MAX-ACCESS      read-write
    STATUS          current
    DESCRIPTION     
            "PROTOCOLS   - ITU
             DEFAULT     - UNSUPPORTED. 
             UNSUPPORTED - GSX will not process the Route Information parameter received
                           in the IAM message. KGL-specific routing is not enabled
             SUPPORTED   - GSX will process the Route Information parameter received in
                           the IAM message. KGL-specific routing is enabled
             CMD         - ROUTEINFORMATION
             SCREEN      - Parameters - RouteInformation 
             CONTROL     - SS7_CONTROL_ROUTE_INFORMATION_SUPPORT
             REQS        - KDDI - PCR1624"
    ::= { sonusIsupsgSignalingProfileEntry 302 }

sonusIsupsgSignalingProfileNoCHGCountIfFlexChgRate OBJECT-TYPE
    SYNTAX          SonusSupportFlag
    MAX-ACCESS      read-write
    STATUS          current
    DESCRIPTION     
            "PROTOCOLS   - JAPAN
             DEFAULT     - UNSUPPORTED
             UNSUPPORTED - CHG count is incremented if there is Flexible Charge Rate 
             SUPPORTED   - CHG count is not incremented if there is Flexible Charge Rate 
             			 CMD         - NOCHGCOUNTIFFLEXCHGRATE
             SCREEN      - Services - No CHG Count If Flex Chg Rate 
             CONTROL     - SS7_CONTROL_NO_CHG_COUNT_IF_FLEX_CHG_RATE
             REQS        - PCR1411"
    ::= { sonusIsupsgSignalingProfileEntry 303 }

sonusIsupsgSignalingProfileRemoveHlcIfNoLlc OBJECT-TYPE
    SYNTAX          SonusSupportFlag
    MAX-ACCESS      read-write
    STATUS          current
    DESCRIPTION     
            "PROTOCOLS   - ALL
             DEFAULT     - UNSUPPORTED
             UNSUPPORTED - HLC is not removed if there is no LLC
             SUPPORTED   - HLC is removed if there is no LLC 
             CMD         - REMHLCIFNOLLC
             SCREEN      - Services - Remove HLC If No LLC
             CONTROL     - SS7_CONTROL_REMOVE_HLC_IF_NO_LLC
             REQS        - PCR1409"
    ::= { sonusIsupsgSignalingProfileEntry 304 }

sonusIsupsgSignalingProfileUpdateANMBCI OBJECT-TYPE
    SYNTAX          SonusSupportFlag
    MAX-ACCESS      read-write
    STATUS          current
    DESCRIPTION     
            "PROTOCOLS	 - JAPAN
             DEFAULT     - UNSUPPORTED
             UNSUPPORTED - BCI in ANM defaulted if not present
             SUPPORTED   - BCI in ANM taken from last received in ACM or
             			   CPG and the charge indicator is updated.
             CMD		 - UPDATEANMBCI
             SCREEN 	 - Services - ANM BCI from ACM/CPG 
             CONTROL	 - SS7_CONTROL_UPDATE_ANM_BCI_SUPPORT
             REQS		 - Pcr1407-SBTM"
    ::= { sonusIsupsgSignalingProfileEntry 305 }

sonusIsupsgSignalingProfileDiscardContractorNum OBJECT-TYPE
    SYNTAX          SonusSupportFlag
    MAX-ACCESS      read-write
    STATUS          current
    DESCRIPTION     
            "PROTOCOLS   - JAPAN
             DEFAULT	 - UNSUPPORTED
             UNSUPPORTED - The GSX will not discard the Contractor number 
                           parameter in the IAM (SBB specific)
                           IAM message.
             SUPPORTED   - The GSX will discard the contractor number
             						   parameter in the IAM (SBB specific) 
             CMD		 - DISCARDCONTRACTORNUM 
             SCREEN		 - Services - Discard Contractor Num 
             CONTROL	 - SS7_CONTROL_DISCARD_CONTRACTOR_NUM_SUPPORT"
    ::= { sonusIsupsgSignalingProfileEntry 306 }

sonusIsupsgSignalingProfileAddInfoTransfer OBJECT-TYPE
    SYNTAX          SonusSupportFlag
    MAX-ACCESS      read-write
    STATUS          current
    DESCRIPTION     
            "PROTOCOLS   - JAPAN
             DEFAULT     - UNSUPPORTED
             UNSUPPORTED - Additional Info Transfer Parameters are not decoded and transited 
             SUPPORTED   - Additional Info Transfer Parameters are decoded and transited
             			 CMD         - AITE0
             SCREEN      - Parameters - Add Info Transfer 
             CONTROL     - SS7_CONTROL_ADDITIONAL_INFO_TRANSFER_SUPPORT
             REQS        - PCR1402"
    ::= { sonusIsupsgSignalingProfileEntry 307 }

sonusIsupsgSignalingProfileADPNumber OBJECT-TYPE
    SYNTAX          SonusSupportFlag
    MAX-ACCESS      read-write
    STATUS          current
    DESCRIPTION     
            "PROTOCOLS   - JAPAN
             DEFAULT     - UNSUPPORTED
             UNSUPPORTED - ADP Number Parameters are not decoded and transited 
             SUPPORTED   - ADP Number Parameters are decoded and transited
             			 CMD         - ADP NUMBER
             SCREEN      - Parameters - ADP Number 
             CONTROL     - SS7_CONTROL_ADP_NUMBER_SUPPORT
             REQS        - PCR1402"
    ::= { sonusIsupsgSignalingProfileEntry 308 }

sonusIsupsgSignalingProfileTransferInfo OBJECT-TYPE
    SYNTAX          SonusSupportFlag
    MAX-ACCESS      read-write
    STATUS          current
    DESCRIPTION     
            "PROTOCOLS   - JAPAN
             DEFAULT     - UNSUPPORTED
             UNSUPPORTED - Transfer Info Parameters are not decoded and transited 
             SUPPORTED   - Transfer Info Parameters are decoded and transited
             			 CMD         - TRANSFER INFO
             SCREEN      - Parameters - Transfer Info 
             CONTROL     - SS7_CONTROL_TRANSFER_INFO_SUPPORT
             REQS        - PCR1402"
    ::= { sonusIsupsgSignalingProfileEntry 309 }

sonusIsupsgSignalingProfileDPC OBJECT-TYPE
    SYNTAX          SonusSupportFlag
    MAX-ACCESS      read-write
    STATUS          current
    DESCRIPTION     
            "PROTOCOLS   - JAPAN
             DEFAULT     - UNSUPPORTED
             UNSUPPORTED - DPC Parameters are not decoded and transited 
             SUPPORTED   - DPC Parameters are decoded and transited
             			 CMD         - DPC
             SCREEN      - Parameters - DPC 
             CONTROL     - SS7_CONTROL_DPC_SUPPORT
             REQS        - PCR1402"
    ::= { sonusIsupsgSignalingProfileEntry 310 }

sonusIsupsgSignalingProfileUUIRestrictions OBJECT-TYPE
    SYNTAX          SonusSupportFlag
    MAX-ACCESS      read-write
    STATUS          current
    DESCRIPTION     
            "PROTOCOLS   - JAPAN
             DEFAULT     - UNSUPPORTED
             UNSUPPORTED - Do not discard subsequent UUIs based on BCI field values
             						   received in ACM/CPG. 
             SUPPORTED   - Discard subsequent UUIs based on BCI field values
             						   received in ACM/CPG. 
             			 CMD         - UUIRESTRICTIONS
             SCREEN      - Services - UUI Restrictions 
             CONTROL     - SS7_CONTROL_UUI_RESTRICTIONS
             REQS        - SBTM - PCR1496"
    ::= { sonusIsupsgSignalingProfileEntry 311 }

sonusIsupsgSignalingProfileCalledNoa8ForNp OBJECT-TYPE
    SYNTAX          SonusSupportFlag
    MAX-ACCESS      read-write
    STATUS          current
    DESCRIPTION     
            "PROTOCOLS   - ITU + CHINA
             DEFAULT     - UNSUPPORTED
             UNSUPPORTED - The Called Noa value 8 will not be supported
                  		 SUPPORTED	 - The Called Noa value 8 will be supported
             CMD         - CALLEDNOA8FORNP
             SCREEN      - Services - Called NOA 8 for NP
             CONTROL     - SS7_CONTROL_CALLED_NOA_8_FOR_NP
             REQS  	     - Q763 section 3.9 (b) for supporting number portability"
    ::= { sonusIsupsgSignalingProfileEntry 312 }

sonusIsupsgSignalingProfileDontClearCdrFields OBJECT-TYPE
    SYNTAX          SonusSupportFlag
    MAX-ACCESS      read-write
    STATUS          current
    DESCRIPTION     
            "PROTOCOLS   - JAPAN
             DEFAULT     - UNSUPPORTED
             			 UNSUPPORTED - Clear called Charge Area and/or Charging
             						   Rate when Charge Information delay
             						   parameter is recieved in ACM or CPG.		
             		     SUPPORTED   - Do not clear Called Charge Area and/or
             						   Charging Rate when Charge Information
             						   Delay parameter is recieved in ACM or CPG.
             			 CMD         - DONTCLEARCDRFIELDS
             			 SCREEN      - SERVICES - Dont Clear Cdr Fields
             			 CONTROL     - SS7_CONTROL_DONT_CLEAR_CDR_FIELDS
             			 REQS        - SBTM-PCR1560,PCR1570"
    ::= { sonusIsupsgSignalingProfileEntry 313 }

sonusIsupsgSignalingProfileSaveIamCIT OBJECT-TYPE
    SYNTAX          SonusSupportFlag
    MAX-ACCESS      read-write
    STATUS          current
    DESCRIPTION     
            "PROTOCOLS   - JAPAN
             DEFAULT     - UNSUPPORTED
             			 UNSUPPORTED - existing functionality and IAM CIT can be overwritten 
             		     SUPPORTED   - CIT information in the IAM will not be overwritten
             						   by backwards information.	
             			 CMD         - SAVEIAMCIT 
             			 SCREEN      - SERVICES - Save IAM CIT 
             			 CONTROL     - SS7_CONTROL_SAVE_IAM_CIT_SUPPORT
             			 REQS        - SBTM - PCR1560"
    ::= { sonusIsupsgSignalingProfileEntry 314 }

sonusIsupsgSignalingProfileStoreChargeForIXCTCTypeAndPayPhone OBJECT-TYPE
    SYNTAX          SonusSupportFlag
    MAX-ACCESS      read-write
    STATUS          current
    DESCRIPTION     
            "PROTOCOLS   - JAPAN
             DEFAULT     - UNSUPPORTED
             UNSUPPORTED - The Last Charge Information is stored in the CDR Records 
             SUPPORTED   - The First Charge Information is stored in the CDR Records
             			 CMD         - STORE CHARGE FOR IXC TC TYPE AND PAYPHONE
             SCREEN      - Services -  Store Charge for IXC/TC Type and Payphone
             CONTROL     - SS7_CONTROL_STORE_SHARGE_FOR_IXC_TC_TYPE_AND_PAYPHONE
             REQS        - PCR1411"
    ::= { sonusIsupsgSignalingProfileEntry 315 }

sonusIsupsgSignalingProfileDPCInfo OBJECT-TYPE
    SYNTAX          SonusSupportFlag
    MAX-ACCESS      read-write
    STATUS          current
    DESCRIPTION     
            "PROTOCOLS   - JAPAN
             DEFAULT     - UNSUPPORTED
             UNSUPPORTED - The GSX will not generate/transit DPC Information parameter 
             						   in the IAM   
             SUPPORTED   - The GSX will generate/transit or discard the DPC Information parameter in the IAM
             			 CMD         - DPCINFORMATION 
             SCREEN      - Parameters - DPC Information  
             CONTROL     - SS7_CONTROL_DPC_INFORMATION_SUPPORT
             REQS        - PCR1405"
    ::= { sonusIsupsgSignalingProfileEntry 316 }

sonusIsupsgSignalingProfileRELForDuplicateIAM OBJECT-TYPE
    SYNTAX          SonusSupportFlag
    MAX-ACCESS      read-write
    STATUS          current
    DESCRIPTION     
            "PROTOCOLS   - ALL
             DEFAULT     - UNSUPPORTED
             UNSUPPORTED - When a misplaced call is detected, send an RSC 
                           to clear the circuit. 
             SUPPORTED   - When a misplaced call is detected, send a REL
                           with CV=31 to clear the circuit.
             			 CMD         - RELFORDUPLICATEIAM
             SCREEN      - Services -  REL for Duplicate IAM
             CONTROL     - SS7_CONTROL_REL_FOR_DUPLICATE_IAM
             REQS        - PCR1573"
    ::= { sonusIsupsgSignalingProfileEntry 317 }

sonusIsupsgSignalingProfileRELforEarlyANM OBJECT-TYPE
    SYNTAX          SonusSupportFlag
    MAX-ACCESS      read-write
    STATUS          current
    DESCRIPTION     
            "PROTOCOLS	 - JAPAN, ITU, CHINA
             DEFAULT	 - UNSUPPORTED
             UNSUPPORTED - Call reattempted.
             SUPPORTED 	 - If an ANM is received before a backward message, 
             			   send REL cause 31 in both directions.
             CMD		 - RELFOREARLYANM
             SCREEN		 - Services -- REL for early ANM
             CONTROL	 - SS7_CONTROL_REL_FOR_EARLY_ANM_SUPPORT
             REQS		 - SBTM -- PCR1569"
    ::= { sonusIsupsgSignalingProfileEntry 318 }

sonusIsupsgSignalingProfileForceEchoCntrlNoUpdate OBJECT-TYPE
    SYNTAX          SonusSupportFlag
    MAX-ACCESS      read-write
    STATUS          current
    DESCRIPTION     
            "PROTOCOLS	 - ALL
             DEFAULT	 - UNSUPPORTED
             UNSUPPORTED - Echo Cancelling will be enabled dependent 
             	   on ECI bit.
             SUPPORTED 	 - Echo Cancelling will be enabled but ECI  
             			   bit will not be updated.	
             CMD		 - FORCEECHOCNTRLNOUPDATE
             SCREEN		 - Services -- Force Echo Control No Update
             CONTROL	 - SS7_CONTROL_FORCE_ECHO_CNTRL_NO_UPDATE
             REQS		 - PCR1652"
    ::= { sonusIsupsgSignalingProfileEntry 319 }

sonusIsupsgSignalingProfileEarlyACMChgNoInd OBJECT-TYPE
    SYNTAX          SonusSupportFlag
    MAX-ACCESS      read-write
    STATUS          current
    DESCRIPTION     
            "PROTOCOLS	 - ALL
             DEFAULT	 - UNSUPPORTED
             UNSUPPORTED - Charge Indication in Early ACM will not always
             be No Indication.
             SUPPORTED 	 - Charge Indication in Early ACM will always
             be No Indication. 
             CMD		 - EARLYACMCHGNOIND
             SCREEN		 - Services -- Early ACM Chg No Ind
             CONTROL	 - SS7_CONTROL_EARLY_ACM_CHG_NO_IND
             REQS		 - SBTM -- PCR1649"
    ::= { sonusIsupsgSignalingProfileEntry 320 }

sonusIsupsgSignalingProfileTransitReceivedCIT OBJECT-TYPE
    SYNTAX          SonusSupportFlag
    MAX-ACCESS      read-write
    STATUS          current
    DESCRIPTION     
            "PROTOCOLS   - JAPAN
             DEFAULT     - UNSUPPORTED
             UNSUPPORTED - Modify received CIT parameter as usual
             SUPPORTED   - Transit received CIT parameter unchanged
             CMD         - TRANSITRCVDCIT
             SCREEN      - Services - Transit Received CIT 
             CONTROL     - SS7_CONTROL_TRANSIT_RECEIVED_CIT
             REQS        - SBTM - PCR1499"
    ::= { sonusIsupsgSignalingProfileEntry 321 }

sonusIsupsgSignalingProfileOnlyScreenCITGen OBJECT-TYPE
    SYNTAX          SonusSupportFlag
    MAX-ACCESS      read-write
    STATUS          current
    DESCRIPTION     
            "PROTOCOLS   - JAPAN
             DEFAULT     - UNSUPPORTED
             UNSUPPORTED - Generate sub-parameters in CIT without restrictions
             SUPPORTED   - Screen sub-parameters generated in CIT
             CMD         - ONLYSCREENCITGEN
             SCREEN      - Services - Only Screen CIT Gen 
             CONTROL     - SS7_CONTROL_ONLY_SCREEN_CIT_GEN
             REQS        - SBTM - PCR1499"
    ::= { sonusIsupsgSignalingProfileEntry 322 }

sonusIsupsgSignalingProfileSlovakChargeMessage OBJECT-TYPE
    SYNTAX          SonusSupportFlag
    MAX-ACCESS      read-write
    STATUS          current
    DESCRIPTION     
            "PROTOCOLS   - Slovak Only
             DEFAULT     - UNSUPPORTED
             UNSUPPORTED - The Slovak charge message will not be supported
                      	 SUPPORTED	 - The Slovak charge message will be supported
             CMD         - SLOVAK CHARGE MESSAGE
             SCREEN      - Messages - CRG (Slovak)
             CONTROL     - SS7_CONTROL_SLOVAK_CRG_SUPPORT
             REQS        - Slovak Telecom - PCR1676"
    ::= { sonusIsupsgSignalingProfileEntry 323 }

sonusIsupsgSignalingProfileECITrap OBJECT-TYPE
    SYNTAX          SonusSupportFlag
    MAX-ACCESS      read-write
    STATUS          current
    DESCRIPTION     
            "PROTOCOLS   - JAPAN
             DEFAULT     - UNSUPPORTED
             UNSUPPORTED - No traps for ECI
             SUPPORTED   - If ECI is recieved in the IAM, the call will
                           be marked as an emergency call and a trap will
                           be generated.
             CMD         - ECITRAP
             SCREEN      - Services - ECI Trap
             CONTROL     - SS7_CONTROL_ECI_TRAP
             REQS        - SBTM - PCR1685"
    ::= { sonusIsupsgSignalingProfileEntry 324 }

sonusIsupsgSignalingProfileCheckIXCAgainstTLEC OBJECT-TYPE
    SYNTAX          SonusSupportFlag
    MAX-ACCESS      read-write
    STATUS          current
    DESCRIPTION     
            "PROTOCOLS   - JAPAN
             DEFAULT     - UNSUPPORTED
             UNSUPPORTED - GSX will add in IXC data with the same carrier
                           code as the TLEC info, if configured by PSX
             SUPPORTED   - GSX will compare the IXC code configured on
                           PSX with the TLEC carrier code added by the
                           terminating exchange and if they are the same,
                           GSX will not add in duplicate information.
             CMD         - CHECKIXCAGAINSTTLEC
             SCREEN      - Services - Check IXC Against TLEC 
             CONTROL     - SS7_CONTROL_CHECK_IXC_AGAINST_TLEC
             REQS        - SBTM - PCR1827"
    ::= { sonusIsupsgSignalingProfileEntry 325 }

sonusIsupsgSignalingProfileRedNumRistInRel OBJECT-TYPE
    SYNTAX          SonusSupportFlag
    MAX-ACCESS      read-write
    STATUS          current
    DESCRIPTION     
            "PROTOCOLS   - ITU, CHINA
             DEFAULT     - UNSUPPORTED
             UNSUPPORTED - Redirection Number Restriction Parameter will 
             			   not be supported in the REL message.
             SUPPORTED	 - Redirection Number Restriction Parameter will 
             			   be supported in the REL message.
             CMD         - REDNUMRISTINREL
             SCREEN      - Parameter - RedNumRistInRel
             CONTROL     - SS7_CONTROL_RNR_REL
             REQS        - SONUS00079696"
    ::= { sonusIsupsgSignalingProfileEntry 326 }

sonusIsupsgSignalingProfileScreenCITBeforeCDR OBJECT-TYPE
    SYNTAX          SonusSupportFlag
    MAX-ACCESS      read-write
    STATUS          current
    DESCRIPTION     
            "PROTOCOLS   - JAPAN
             DEFAULT     - UNSUPPORTED
             UNSUPPORTED - GSX will add all the carrier information transfer 
             						   parameter data to the CDR and then screen out any
             						   unneeded data before generating the signaling message
             SUPPORTED   - GSX will screen out any carrier information transfer
             						   data that will not be sent in the signaling message
             						   and then store the carrier information transfer
             						   parameter in the CDR.
             CMD         - SCREEN CIT BEFORE CDR
             SCREEN      - Services - Screen CIT before CDR 
             CONTROL     - SS7_CONTROL_SCREEN_CIT_BEFORE_CDR
             REQS        - SBTM - PCR1935"
    ::= { sonusIsupsgSignalingProfileEntry 327 }

sonusIsupsgSignalingProfileRussiaRng OBJECT-TYPE
    SYNTAX          SonusSupportFlag
    MAX-ACCESS      read-write
    STATUS          current
    DESCRIPTION     
            "PROTOCOLS   - Russia Only
             DEFAULT     - UNSUPPORTED
             UNSUPPORTED - The Russia RNG message will not be supported
                      	 SUPPORTED	 - The Russia RNG message will be supported
             CMD         - RNG
             SCREEN      - Messages - RNG (Russia)
             CONTROL     - SS7_CONTROL_RUSSIA_RNG_SUPPORT
             REQS        - ISUP-R-2000 - PCR1223"
    ::= { sonusIsupsgSignalingProfileEntry 328 }

sonusIsupsgSignalingProfileOverrideInband OBJECT-TYPE
    SYNTAX          SonusSupportFlag
    MAX-ACCESS      read-write
    STATUS          current
    DESCRIPTION     
            "PROTOCOLS   - ALL
             DEFAULT     - UNSUPPORTED
             UNSUPPORTED - Normal behaviour			         	 
             SUPPORTED	 - Inband indicator in OBCI or Event Indicator in CPG  
             			   message will be ignored unless BCI has Interworking
             			   Indicator Set
             CMD         - OVERRIDE INBAND
             SCREEN      - Services - Override Inband
             CONTROL     - SS7_CONTROL_OVERRIDE_INBAND
             REQS        - ATT - PCR2034"
    ::= { sonusIsupsgSignalingProfileEntry 329 }

sonusIsupsgSignalingProfileSendingEnbloc OBJECT-TYPE
    SYNTAX          SonusSupportFlag
    MAX-ACCESS      read-write
    STATUS          current
    DESCRIPTION     
            "PROTOCOLS   - ITU/CHINA
             DEFAULT     - Dependent on SAM control
             		 UNSUPPORTED - The Trunkgroup is able to send overlap 
                       and enbloc.
             		 SUPPORTED   - The Trunkgroup is only able to send enbloc.
             		 CMD         - SENDING ENBLOC
             SCREEN      - Services - Sending Enbloc
             CONTROL     - SS7_CONTROL_SENDING_ENBLOC                   
             REQS        - PCR2062"
    ::= { sonusIsupsgSignalingProfileEntry 330 }

sonusIsupsgSignalingProfileBloUbl OBJECT-TYPE
    SYNTAX          SonusSupportFlag
    MAX-ACCESS      read-write
    STATUS          current
    DESCRIPTION     
            "PROTOCOLS   - BICC
             DEFAULT     - UNSUPPORTED
             		 UNSUPPORTED - Individual BLO and UBL message will not be sent for each circuit. 
             		 SUPPORTED   - Individual BLO and UBL message allowed to be sent for each circuit.
             		 CMD         - BLO UBL
             SCREEN      - Messages
             CONTROL     - SS7_CONTROL_SENDING_BLOUBL"
    ::= { sonusIsupsgSignalingProfileEntry 331 }

sonusIsupsgSignalingProfileBillableCallForConwithNonCharge OBJECT-TYPE
    SYNTAX          SonusSupportFlag
    MAX-ACCESS      read-write
    STATUS          current
    DESCRIPTION     
            "This parameter is used to send ACM and ANM messages even when a CON message with
             Charge Indicator set to Non-Charge (i.e. other than Charge) is received. If this parameter
             is set to UNSUPPORTED, then ACM and CPG messages will be sent. Subsequent SUSPEND and
             RESUME messages will be blocked. "
    DEFVAL          { supported }
    ::= { sonusIsupsgSignalingProfileEntry 339 }

sonusIsupsgSignalingProfileINNWithinCdPN OBJECT-TYPE
    SYNTAX          INTEGER { transit(0), allowed(1), notAllowed(2) }
    MAX-ACCESS      read-write
    STATUS          current
    DESCRIPTION     
            "This parameter is used to update the Internal Network Indicator in the 
             Called Party Number. Is set to TRANSIT, the value received
             is unchanged, otherwise the value configured (ALLOWED/NOTALLOWED) is sent."
    DEFVAL          { transit }
    ::= { sonusIsupsgSignalingProfileEntry 340 }

sonusIsupsgSignalingProfileNIWithinCgPN OBJECT-TYPE
    SYNTAX          INTEGER { transit(0), complete(1), incomplete(2) }
    MAX-ACCESS      read-write
    STATUS          current
    DESCRIPTION     
            "This parameter is used to update the Number incomplete Indicator in the 
             Calling Party Number. Is set to TRANSIT, the value received
             is unchanged, otherwise the value configured (COMPLETE/INCOMPLETE) is sent."
    DEFVAL          { transit }
    ::= { sonusIsupsgSignalingProfileEntry 341 }

sonusIsupsgSignalingProfileUpdateChargeInd OBJECT-TYPE
    SYNTAX          INTEGER { unsupported(0), supported(1) }
    MAX-ACCESS      read-write
    STATUS          current
    DESCRIPTION     
            "This parameter is used to update the charge indicator parameter."
    DEFVAL          { unsupported }
    ::= { sonusIsupsgSignalingProfileEntry 342 }

sonusIsupsgSignalingProfileColpColrIGW OBJECT-TYPE
    SYNTAX          SonusSupportFlag
    MAX-ACCESS      read-write
    STATUS          current
    DESCRIPTION     
            "PROTOCOLS   - ITU/ANSI
             DEFAULT     - UNSUPPORTED 
             		 UNSUPPORTED - Connect Number will not have support COLP-COLR  functionality
             		 SUPPORTED   - Connect Number will have support for COLP-COLR and IGW functionality.  
             		 CMD         - COLPCOLRIGW 
             SCREEN      - Services - COLPCOLRIGW
             CONTROL     - SS7_CONTROL_COLPCOLRIGW_SUPPORT                   
             REQS        - PCR3816"
    DEFVAL          { unsupported }
    ::= { sonusIsupsgSignalingProfileEntry 343 }

sonusIsupsgSignalingProfileForeignSpecialRoutingIndicator OBJECT-TYPE
    SYNTAX          INTEGER { off(0), on(1) }
    MAX-ACCESS      read-write
    STATUS          current
    DESCRIPTION     
            "This indicates if customer identifier based routing is required"
    DEFVAL          { off }
    ::= { sonusIsupsgSignalingProfileEntry 344 }

sonusIsupsgSignalingProfileInternationCarrierRoutingIndicator OBJECT-TYPE
    SYNTAX          INTEGER { off(0), on(1) }
    MAX-ACCESS      read-write
    STATUS          current
    DESCRIPTION     
            "This indicates if carrier identifier based routing is required"
    DEFVAL          { off }
    ::= { sonusIsupsgSignalingProfileEntry 345 }

sonusIsupsgSignalingProfileNumberRangeBlockingIndicator OBJECT-TYPE
    SYNTAX          INTEGER { off(0), on(1) }
    MAX-ACCESS      read-write
    STATUS          current
    DESCRIPTION     
            "This indicates if number range blocking over ride is required"
    DEFVAL          { off }
    ::= { sonusIsupsgSignalingProfileEntry 346 }

sonusIsupsgSignalingProfileNpUkkSupportedInEgress OBJECT-TYPE
    SYNTAX          SonusSupportFlag
    MAX-ACCESS      read-write
    STATUS          current
    DESCRIPTION     
            "This indicates if NP.UKK is to be sent or dropped on the EGRESS IAM."
    DEFVAL          { unsupported }
    ::= { sonusIsupsgSignalingProfileEntry 347 }

sonusIsupsgSignalingProfileNpSspSupportedInEgress OBJECT-TYPE
    SYNTAX          SonusSupportFlag
    MAX-ACCESS      read-write
    STATUS          current
    DESCRIPTION     
            "This indicates if NP.SSP is to be sent or dropped on the EGRESS IAM."
    DEFVAL          { unsupported }
    ::= { sonusIsupsgSignalingProfileEntry 348 }

sonusIsupsgSignalingProfileNpUkkSupportedInIngress OBJECT-TYPE
    SYNTAX          SonusSupportFlag
    MAX-ACCESS      read-write
    STATUS          current
    DESCRIPTION     
            "This indicates if NP.UKK is to be processed in INGRESS IAM."
    DEFVAL          { unsupported }
    ::= { sonusIsupsgSignalingProfileEntry 349 }

sonusIsupsgSignalingProfileNpSspSupportedInIngress OBJECT-TYPE
    SYNTAX          SonusSupportFlag
    MAX-ACCESS      read-write
    STATUS          current
    DESCRIPTION     
            "This indicates if NP.SSP is to be processed in INGRESS IAM."
    DEFVAL          { unsupported }
    ::= { sonusIsupsgSignalingProfileEntry 350 }

sonusIsupsgSignalingProfileChargeInfoITXCdr OBJECT-TYPE
    SYNTAX          SonusSupportFlag
    MAX-ACCESS      read-write
    STATUS          current
    DESCRIPTION     
            "This parameter is used to log charge posting domain info in ITX messages in Intermediate and stop CDR "
    DEFVAL          { unsupported }
    ::= { sonusIsupsgSignalingProfileEntry 351 }

sonusIsupsgSignalingProfileGCR OBJECT-TYPE
    SYNTAX          SonusSupportFlag
    MAX-ACCESS      read-write
    STATUS          current
    DESCRIPTION     
            "Is the Global Charge Reference (GCR) Parameter Supported."
    DEFVAL          { unsupported }
    ::= { sonusIsupsgSignalingProfileEntry 352 }

sonusIsupsgSignalingProfileRemoteMnpDip OBJECT-TYPE
    SYNTAX          SonusSupportFlag
    MAX-ACCESS      read-write
    STATUS          current
    DESCRIPTION     
            "This parameter is used to support remote MNP Dipping service"
    DEFVAL          { unsupported }
    ::= { sonusIsupsgSignalingProfileEntry 353 }

sonusIsupsgSignalingProfileDropAPPinIAM OBJECT-TYPE
    SYNTAX          SonusSupportFlag
    MAX-ACCESS      read-write
    STATUS          current
    DESCRIPTION     
            "This parameter is used to  drop the APP with context ID = 0x3FFF in IAM for ANSI "
    DEFVAL          { unsupported }
    ::= { sonusIsupsgSignalingProfileEntry 354 }

sonusIsupsgSignalingProfileNIWithinCgPNDirection OBJECT-TYPE
    SYNTAX          INTEGER { egress(0), ingress(1), both(2) }
    MAX-ACCESS      read-write
    STATUS          current
    DESCRIPTION     
            "This parameter is used to choose the direction for update the Number incomplete Indicator in the
             Calling Party Number. egress(0) means handling NI indicator on outgoing call side,ingress(1) means
             handling NI indicator on incoming call side."
    DEFVAL          { egress }
    ::= { sonusIsupsgSignalingProfileEntry 355 }

sonusIsupsgSignalingProfileAllowSgdInGdp OBJECT-TYPE
    SYNTAX          INTEGER { unsupported(0), supported(1) }
    MAX-ACCESS      read-write
    STATUS          current
    DESCRIPTION     
            "This parameter is used to specify wheather Mapping of SDG  to GDP parameter(digit type 25) of IAM should needed or not ."
    DEFVAL          { unsupported }
    ::= { sonusIsupsgSignalingProfileEntry 356 }

sonusIsupsgSignalingProfileRNRInACM OBJECT-TYPE
    SYNTAX          SonusSupportFlag
    MAX-ACCESS      read-write
    STATUS          current
    DESCRIPTION     
            "Is the RNR present in the ACM for the ISUP Signaling Profile."
    ::= { sonusIsupsgSignalingProfileEntry 357 }

sonusIsupsgSignalingProfileRNRInCPG OBJECT-TYPE
    SYNTAX          SonusSupportFlag
    MAX-ACCESS      read-write
    STATUS          current
    DESCRIPTION     
            "Is the RNR present in the CPG for the ISUP Signaling Profile."
    ::= { sonusIsupsgSignalingProfileEntry 358 }

sonusIsupsgSignalingProfileRNRInANM OBJECT-TYPE
    SYNTAX          SonusSupportFlag
    MAX-ACCESS      read-write
    STATUS          current
    DESCRIPTION     
            "Is the RNR present in the ANM for the ISUP Signaling Profile."
    ::= { sonusIsupsgSignalingProfileEntry 359 }

sonusIsupsgSignalingProfileHistInfo OBJECT-TYPE
    SYNTAX          SonusSupportFlag
    MAX-ACCESS      read-write
    STATUS          current
    DESCRIPTION     
            "Is the RNR present in the ANM for the ISUP Signaling Profile."
    ::= { sonusIsupsgSignalingProfileEntry 360 }

sonusIsupsgSignalingProfileStoreChargeRateInformation OBJECT-TYPE
    SYNTAX          SonusSupportFlag
    MAX-ACCESS      read-write
    STATUS          current
    DESCRIPTION     
            "PCR6243 This parameter will populate the ISUP PVSD 
             charge rate information fields with the charge rate
             received from any protocol."
    DEFVAL          { unsupported }
    ::= { sonusIsupsgSignalingProfileEntry 361 }

sonusIsupsgSignalingProfileMnpTransferMethod OBJECT-TYPE
    SYNTAX          SonusSupportFlag
    MAX-ACCESS      read-write
    STATUS          current
    DESCRIPTION     
            "PCR6243 If this control is set to supported then UUI 
             will be dropped if transit convert convert carrier code
             is received from the PSX"
    DEFVAL          { unsupported }
    ::= { sonusIsupsgSignalingProfileEntry 362 }

sonusIsupsgInrInfProfile OBJECT IDENTIFIER
    ::= { sonusIsupServiceGroupMIBObjects 9 }

sonusIsupsgInrInfProfileNextIndex OBJECT-TYPE
    SYNTAX          Integer32
    MAX-ACCESS      read-only
    STATUS          current
    DESCRIPTION     
            "The next valid index to use when creating a new sonusIsupsgInrInfProfileEntry"
    ::= { sonusIsupsgInrInfProfile 1 }

sonusIsupsgInrInfProfileTable OBJECT-TYPE
    SYNTAX          SEQUENCE OF SonusIsupsgInrInfProfileEntry
    MAX-ACCESS      not-accessible
    STATUS          current
    DESCRIPTION     
            "This table contains information about each ISUP information request
             and information received ( inr/inf ) Profile configured to be a member 
             of the node. 
             A management entity may create rows for inr inf Profile that are
             anticipated to be supported in the future."
    ::= { sonusIsupsgInrInfProfile 2 }

sonusIsupsgInrInfProfileEntry OBJECT-TYPE
    SYNTAX          SonusIsupsgInrInfProfileEntry
    MAX-ACCESS      not-accessible
    STATUS          current
    DESCRIPTION     
            "This table describes the ISUP inr inf Profiles that are configured."
    INDEX           { sonusIsupsgInrInfProfileListIndex }
    ::= { sonusIsupsgInrInfProfileTable 1 }

SonusIsupsgInrInfProfileEntry ::=
    SEQUENCE {
        sonusIsupsgInrInfProfileListIndex Integer32,
        sonusIsupsgInrInfProfileName    SonusNameReference,
        sonusIsupsgInrInfProfileRequestCPC  SonusSupportFlag,
        sonusIsupsgInrInfProfileRequestCLI  SonusSupportFlag,
        sonusIsupsgInrInfProfileRequestCrgInfo      SonusSupportFlag,
        sonusIsupsgInrInfProfileCPCnotRcvd  SonusSupportFlag,
        sonusIsupsgInrInfProfileCLInotRcvd  INTEGER,
        sonusIsupsgInrInfProfileCrgInfonotRcvd      SonusSupportFlag,
        sonusIsupsgInrInfProfileSolicitedInfoOnly         SonusSupportFlag,
        sonusIsupsgInrInfProfileAdminState  SonusAdminState,
        sonusIsupsgInrInfProfileRowStatus RowStatus
    }

sonusIsupsgInrInfProfileListIndex OBJECT-TYPE
    SYNTAX          Integer32
    MAX-ACCESS      read-only
    STATUS          current
    DESCRIPTION     
            "The index of the ISUP inr inf profile table is defined for"
    ::= { sonusIsupsgInrInfProfileEntry 1 }

sonusIsupsgInrInfProfileName OBJECT-TYPE
    SYNTAX          SonusNameReference
    MAX-ACCESS      read-write
    STATUS          current
    DESCRIPTION     
            "The name of the signaling profile this table is associated with"
    ::= { sonusIsupsgInrInfProfileEntry 2 }

sonusIsupsgInrInfProfileRequestCPC OBJECT-TYPE
    SYNTAX          SonusSupportFlag
    MAX-ACCESS      read-write
    STATUS          current
    DESCRIPTION     
            "States whether a CPC should be requested if the value received was
             unknown"
    ::= { sonusIsupsgInrInfProfileEntry 3 }

sonusIsupsgInrInfProfileRequestCLI OBJECT-TYPE
    SYNTAX          SonusSupportFlag
    MAX-ACCESS      read-write
    STATUS          current
    DESCRIPTION     
            "States whether a CLI should be requested if not received"
    ::= { sonusIsupsgInrInfProfileEntry 4 }

sonusIsupsgInrInfProfileRequestCrgInfo OBJECT-TYPE
    SYNTAX          SonusSupportFlag
    MAX-ACCESS      read-write
    STATUS          current
    DESCRIPTION     
            "States whether charge information should be requested if not received"
    ::= { sonusIsupsgInrInfProfileEntry 5 }

sonusIsupsgInrInfProfileCPCnotRcvd OBJECT-TYPE
    SYNTAX          SonusSupportFlag
    MAX-ACCESS      read-write
    STATUS          current
    DESCRIPTION     
            "States what happens to the call if we request this info and it
             doesn't arrive"
    ::= { sonusIsupsgInrInfProfileEntry 6 }

sonusIsupsgInrInfProfileCLInotRcvd OBJECT-TYPE
    SYNTAX          INTEGER { unsupported(1), supported(2), national(3) }
    MAX-ACCESS      read-write
    STATUS          current
    DESCRIPTION     
            "States what happens to the call if we request this info and it
             doesn't arrive"
    DEFVAL          { unsupported }
    ::= { sonusIsupsgInrInfProfileEntry 7 }

sonusIsupsgInrInfProfileCrgInfonotRcvd OBJECT-TYPE
    SYNTAX          SonusSupportFlag
    MAX-ACCESS      read-write
    STATUS          current
    DESCRIPTION     
            "States what happens to the call if we request this info and it
             doesn't arrive"
    ::= { sonusIsupsgInrInfProfileEntry 8 }

sonusIsupsgInrInfProfileSolicitedInfoOnly OBJECT-TYPE
    SYNTAX          SonusSupportFlag
    MAX-ACCESS      read-write
    STATUS          current
    DESCRIPTION     
            "States if we should ignore unsolicited INF messages"
    ::= { sonusIsupsgInrInfProfileEntry 9 }

sonusIsupsgInrInfProfileAdminState OBJECT-TYPE
    SYNTAX          SonusAdminState
    MAX-ACCESS      read-write
    STATUS          current
    DESCRIPTION     
            "The admin state of the INR INF profile"
    ::= { sonusIsupsgInrInfProfileEntry 10 }

sonusIsupsgInrInfProfileRowStatus OBJECT-TYPE
    SYNTAX          RowStatus
    MAX-ACCESS      read-write
    STATUS          current
    DESCRIPTION     
            ""
    ::= { sonusIsupsgInrInfProfileEntry 11 }

sonusIsupsgSignalingGroup OBJECT IDENTIFIER
    ::= { sonusIsupServiceGroupMIBObjects 10 }

sonusIsupsgSignalingGroupNextIndex OBJECT-TYPE
    SYNTAX          Integer32
    MAX-ACCESS      read-only
    STATUS          current
    DESCRIPTION     
            "The next valid index to use when creating a new sonusIsupsgSignalingGroupEntry"
    ::= { sonusIsupsgSignalingGroup 1 }

sonusIsupsgSignalingGroupTable OBJECT-TYPE
    SYNTAX          SEQUENCE OF SonusIsupsgSignalingGroupEntry
    MAX-ACCESS      not-accessible
    STATUS          current
    DESCRIPTION     
            "This table contains information about each ISUP Signaling Group
             configured to be a member of the node. 
             
             A management entity may create rows for Signaling Group that are
             anticipated to be supported in the future."
    ::= { sonusIsupsgSignalingGroup 2 }

sonusIsupsgSignalingGroupEntry OBJECT-TYPE
    SYNTAX          SonusIsupsgSignalingGroupEntry
    MAX-ACCESS      not-accessible
    STATUS          current
    DESCRIPTION     
            "This table describes the ISUP Signaling Groups. "
    INDEX           { sonusIsupsgSigGrpListIndex }
    ::= { sonusIsupsgSignalingGroupTable 1 }

SonusIsupsgSignalingGroupEntry ::=
    SEQUENCE {
        sonusIsupsgSigGrpListIndex      Integer32,
        sonusIsupsgSigGrpName           SonusName,
        sonusIsupsgSigGrpVersionId      Integer32,
        sonusIsupsgSigGrpOlipCheck      INTEGER,
        sonusIsupsgSigGrpSignalingProfileName     SonusNameReference,
        sonusIsupsgSigGrpBaseSigGrpName SonusNameReference,
        sonusIsupsgSigGrpHopCounterValue Integer32,
        sonusIsupsgSigGrpHopCounterState SonusAdminState,
        sonusIsupsgSigGrpSigBase        INTEGER,
        sonusIsupsgSigGrpRevision       INTEGER,
        sonusIsupsgSigGrpAdminState     SonusAdminState,
        sonusIsupsgSigGrpRowStatus      RowStatus,
        sonusIsupsgSigGrpSendingOlipCheck INTEGER,
        sonusIsupsgSigGrpNetworkInd     INTEGER,
        sonusIsupsgSigGrpPropDelay      Integer32,
        sonusIsupsgSigGrpLookAheadForBusy INTEGER,
        sonusIsupsgSigGrpNetworkIdentity DisplayString,
        sonusIsupsgSigGrpGenerateJapanIcsParams       INTEGER,
        sonusIsupsgSigGrpTandemLimitCounter   Integer32,
        sonusIsupsgSigGrpChargeArea     DisplayString,
        sonusIsupsgSigGrpDeleteIxcTcCode DisplayString,
        sonusIsupsgSigGrpLocationOfRel  INTEGER,
        sonusIsupsgSigGrpLocationOfRel34 INTEGER,
        sonusIsupsgSigGrpLocationOfRel42 INTEGER
    }

sonusIsupsgSigGrpListIndex OBJECT-TYPE
    SYNTAX          Integer32 (1..128)
    MAX-ACCESS      read-only
    STATUS          current
    DESCRIPTION     
            "The index of the ISUP Signaling Group entry."
    ::= { sonusIsupsgSignalingGroupEntry 1 }

sonusIsupsgSigGrpName OBJECT-TYPE
    SYNTAX          SonusName
    MAX-ACCESS      read-write
    STATUS          current
    DESCRIPTION     
            "The name of the ISUP Signaling Group."
    ::= { sonusIsupsgSignalingGroupEntry 2 }

sonusIsupsgSigGrpVersionId OBJECT-TYPE
    SYNTAX          Integer32 (0..65536)
    MAX-ACCESS      read-write
    STATUS          current
    DESCRIPTION     
            "The version ID as given by the PSX to identify a signaling group"
    ::= { sonusIsupsgSignalingGroupEntry 3 }

sonusIsupsgSigGrpOlipCheck OBJECT-TYPE
    SYNTAX          INTEGER { on(1), off(0) }
    MAX-ACCESS      read-write
    STATUS          current
    DESCRIPTION     
            "Specifies whether or not to check for the presence of an OLIP when determining
             that a call is invalid."
    ::= { sonusIsupsgSignalingGroupEntry 4 }

sonusIsupsgSigGrpSignalingProfileName OBJECT-TYPE
    SYNTAX          SonusNameReference
    MAX-ACCESS      read-write
    STATUS          current
    DESCRIPTION     
            "The Signaling Profile Name associated with this signaling group."
    ::= { sonusIsupsgSignalingGroupEntry 5 }

sonusIsupsgSigGrpBaseSigGrpName OBJECT-TYPE
    SYNTAX          SonusNameReference
    MAX-ACCESS      read-write
    STATUS          current
    DESCRIPTION     
            "The Base Signaling group name."
    ::= { sonusIsupsgSignalingGroupEntry 6 }

sonusIsupsgSigGrpHopCounterValue OBJECT-TYPE
    SYNTAX          Integer32 (10..31)
    MAX-ACCESS      read-write
    STATUS          current
    DESCRIPTION     
            "Specifies the value of the Hop Counter if initiated by the switch."
    ::= { sonusIsupsgSignalingGroupEntry 7 }

sonusIsupsgSigGrpHopCounterState OBJECT-TYPE
    SYNTAX          SonusAdminState
    MAX-ACCESS      read-write
    STATUS          current
    DESCRIPTION     
            "The Hop Counter state for the Signaling Group."
    ::= { sonusIsupsgSignalingGroupEntry 8 }

sonusIsupsgSigGrpSigBase OBJECT-TYPE
    SYNTAX          INTEGER { none(1), itu-t88(2), itu-t92(3), ansi88(4), 
                        ansi00(5), etsi121(6), etsi356(7), gr317(8), 
                        ttc87(9), ttc93(10) }
    MAX-ACCESS      read-write
    STATUS          current
    DESCRIPTION     
            "The Base Signaling group from rfc3204."
    ::= { sonusIsupsgSignalingGroupEntry 9 }

sonusIsupsgSigGrpRevision OBJECT-TYPE
    SYNTAX          INTEGER { ansi1992(1), ansi1995(2), itu1993(3), 
                        etsi2(4), nttfcc(5), itu1997(6), itu1988(7), 
                        ituq767(8), belgacom(9), nttcom(10), spirou(12), 
                        mexicoic(13), italy(14), denmarkic(15), 
                        hongkongic(16), singapore(17), etsi3(18), 
                        peru(19), chile(20), portugaloni(21), 
                        argentina(22), argentinaidt(23), spain(24), 
                        brazil(25), india(26), chinacnc(27), korea(28), 
                        ukisup(29), etsi2plus(30), ansiatt(31), 
                        israel(32), slovak2(33), russia(34) }
    MAX-ACCESS      read-write
    STATUS          current
    DESCRIPTION     
            "The revision of the ISUP protocol supported on this Signaling Group."
    ::= { sonusIsupsgSignalingGroupEntry 10 }

sonusIsupsgSigGrpAdminState OBJECT-TYPE
    SYNTAX          SonusAdminState
    MAX-ACCESS      read-write
    STATUS          current
    DESCRIPTION     
            "The admin state of the ISUP Signaling Group."
    ::= { sonusIsupsgSignalingGroupEntry 11 }

sonusIsupsgSigGrpRowStatus OBJECT-TYPE
    SYNTAX          RowStatus
    MAX-ACCESS      read-write
    STATUS          current
    DESCRIPTION     
            ""
    ::= { sonusIsupsgSignalingGroupEntry 12 }

sonusIsupsgSigGrpSendingOlipCheck OBJECT-TYPE
    SYNTAX          INTEGER { on(1), off(0) }
    MAX-ACCESS      read-write
    STATUS          current
    DESCRIPTION     
            "Specifies whether or not to check for the presence of an OLIP whein sending an IAM."
    ::= { sonusIsupsgSignalingGroupEntry 13 }

sonusIsupsgSigGrpNetworkInd OBJECT-TYPE
    SYNTAX          INTEGER { intl0(1), intl1(2), natl0(3), natl1(4) }
    MAX-ACCESS      read-write
    STATUS          current
    DESCRIPTION     
            "The setting of the Network Indicator as it would be for ISUP if the
             SIP-T link were an ISUP link. This is here to prevent unneccesary interworking
             only, and is not really applicable to SIP-T."
    DEFVAL          { natl0 }
    ::= { sonusIsupsgSignalingGroupEntry 14 }

sonusIsupsgSigGrpPropDelay OBJECT-TYPE
    SYNTAX          Integer32 (0..400)
    MAX-ACCESS      read-write
    STATUS          current
    DESCRIPTION     
            "The propagation delay value in milliseconds for this SIP-T signaling group."
    DEFVAL          { 0 }
    ::= { sonusIsupsgSignalingGroupEntry 15 }

sonusIsupsgSigGrpLookAheadForBusy OBJECT-TYPE
    SYNTAX          INTEGER { allowed(0), pathReserved(1), notAllowed(2) }
    MAX-ACCESS      read-write
    STATUS          current
    DESCRIPTION     
            "The default value used in the look ahead for busy field in the ISUP Precedence 
             parameter within SIP-T."
    DEFVAL          { notAllowed }
    ::= { sonusIsupsgSignalingGroupEntry 16 }

sonusIsupsgSigGrpNetworkIdentity OBJECT-TYPE
    SYNTAX          DisplayString (SIZE(4))
    MAX-ACCESS      read-write
    STATUS          current
    DESCRIPTION     
            "The default value used for the 4 digit Network Identity field in the ISUP precedence 
             parameter within SIP-T."
    DEFVAL          { "0100" }
    ::= { sonusIsupsgSignalingGroupEntry 17 }

sonusIsupsgSigGrpGenerateJapanIcsParams OBJECT-TYPE
    SYNTAX          INTEGER { disabled(1), enabled(2) }
    MAX-ACCESS      read-write
    STATUS          current
    DESCRIPTION     
            "Specifies whether support of generating ICS information
             in SIP MIME case is enabled or disabled for the signalling group"
    DEFVAL          { disabled }
    ::= { sonusIsupsgSignalingGroupEntry 18 }

sonusIsupsgSigGrpTandemLimitCounter OBJECT-TYPE
    SYNTAX          Integer32 (0..15)
    MAX-ACCESS      read-write
    STATUS          current
    DESCRIPTION     
            "Limit Counter to be set in outgoing IAM in Tandem Call Counter parameter in SIP MIME case"
    DEFVAL          { 0 }
    ::= { sonusIsupsgSignalingGroupEntry 19 }

sonusIsupsgSigGrpChargeArea OBJECT-TYPE
    SYNTAX          DisplayString (SIZE(0..5))
    MAX-ACCESS      read-write
    STATUS          current
    DESCRIPTION     
            "This Service Control is used to populate the Charge Area if it contains
             a valid 5 digit Charge Area. The Charge Area will be set in the ACM or
             CPG message if a script is returned from the PSX or for Disconnect
             treatment for SIP MIME case"
    ::= { sonusIsupsgSignalingGroupEntry 20 }

sonusIsupsgSigGrpDeleteIxcTcCode OBJECT-TYPE
    SYNTAX          DisplayString (SIZE(0..4))
    MAX-ACCESS      read-write
    STATUS          current
    DESCRIPTION     
            "Delete the IXC/TC code in the CIT for SIP MIME case"
    ::= { sonusIsupsgSignalingGroupEntry 21 }

sonusIsupsgSigGrpLocationOfRel OBJECT-TYPE
    SYNTAX          INTEGER { notUsed(0), user(1), privateLocal(2), 
                        publicLocal(3), transitNet(4), publicRemote(5), 
                        privateRemote(6), natReserved6(7), 
                        internationalNet(8), natReserved8(9), 
                        natReserved9(10), netBeyondInterPoint(11), 
                        natReserved11(12), natReserved12(13), 
                        natReserved13(14), natReserved14(15), 
                        natReserved15(16) }
    MAX-ACCESS      read-write
    STATUS          current
    DESCRIPTION     
            "Update the Location in the REL for SIP MIME case"
    DEFVAL          { notUsed }
    ::= { sonusIsupsgSignalingGroupEntry 22 }

sonusIsupsgSigGrpLocationOfRel34 OBJECT-TYPE
    SYNTAX          INTEGER { notUsed(0), user(1), privateLocal(2), 
                        publicLocal(3), transitNet(4), publicRemote(5), 
                        privateRemote(6), natReserved6(7), 
                        internationalNet(8), natReserved8(9), 
                        natReserved9(10), netBeyondInterPoint(11), 
                        natReserved11(12), natReserved12(13), 
                        natReserved13(14), natReserved14(15), 
                        natReserved15(16) }
    MAX-ACCESS      read-write
    STATUS          current
    DESCRIPTION     
            "Update the Location in the REL if Cause Value is 34 for SIP MIME case"
    DEFVAL          { notUsed }
    ::= { sonusIsupsgSignalingGroupEntry 23 }

sonusIsupsgSigGrpLocationOfRel42 OBJECT-TYPE
    SYNTAX          INTEGER { notUsed(0), user(1), privateLocal(2), 
                        publicLocal(3), transitNet(4), publicRemote(5), 
                        privateRemote(6), natReserved6(7), 
                        internationalNet(8), natReserved8(9), 
                        natReserved9(10), netBeyondInterPoint(11), 
                        natReserved11(12), natReserved12(13), 
                        natReserved13(14), natReserved14(15), 
                        natReserved15(16) }
    MAX-ACCESS      read-write
    STATUS          current
    DESCRIPTION     
            "Update the Location in the REL if Cause Value is 42 for SIP MIME case"
    DEFVAL          { notUsed }
    ::= { sonusIsupsgSignalingGroupEntry 24 }

sonusIsupsgCircuitStatByPortTable OBJECT-TYPE
    SYNTAX          SEQUENCE OF SonusIsupsgCircuitStatByPortEntry
    MAX-ACCESS      not-accessible
    STATUS          current
    DESCRIPTION     
            "This table contains status information about each ISUP circuit 
             in the GSX9000 Switch node using the shelf, slot, port and cic as keys."
    ::= { sonusIsupServiceGroupMIBObjects 11 }

sonusIsupsgCircuitStatByPortEntry OBJECT-TYPE
    SYNTAX          SonusIsupsgCircuitStatByPortEntry
    MAX-ACCESS      not-accessible
    STATUS          current
    DESCRIPTION     
            "This table describes the status of the configured ISUP circuits."
    INDEX           { sonusIsupsgCircuitStatByPortShelfIndex, 
                      sonusIsupsgCircuitStatByPortSlotIndex, 
                      sonusIsupsgCircuitStatByPortPortIndex, 
                      sonusIsupsgCircuitStatByPortDS1, 
                      sonusIsupsgCircuitStatByPortChannel }
    ::= { sonusIsupsgCircuitStatByPortTable 1 }

SonusIsupsgCircuitStatByPortEntry ::=
    SEQUENCE {
        sonusIsupsgCircuitStatByPortShelfIndex      SonusShelfIndex,
        sonusIsupsgCircuitStatByPortSlotIndex     SonusSlotIndex,
        sonusIsupsgCircuitStatByPortPortIndex     Integer32,
        sonusIsupsgCircuitStatByPortDS1 Integer32,
        sonusIsupsgCircuitStatByPortChannel   Integer32,
        sonusIsupsgCircuitStatByPortSvcGrpIndex       Integer32,
        sonusIsupsgCircuitStatByPortIdentityCode        Integer32,
        sonusIsupsgCircuitStatByPortUsage INTEGER,
        sonusIsupsgCircuitStatByPortLocalMaint      INTEGER,
        sonusIsupsgCircuitStatByPortLocalHw   INTEGER,
        sonusIsupsgCircuitStatByPortRemoteMaint       INTEGER,
        sonusIsupsgCircuitStatByPortRemoteHw    INTEGER,
        sonusIsupsgCircuitStatByPortManualCot     INTEGER
    }

sonusIsupsgCircuitStatByPortShelfIndex OBJECT-TYPE
    SYNTAX          SonusShelfIndex
    MAX-ACCESS      read-only
    STATUS          current
    DESCRIPTION     
            "The Shelf the circuit is defined for and an Index into the table."
    ::= { sonusIsupsgCircuitStatByPortEntry 1 }

sonusIsupsgCircuitStatByPortSlotIndex OBJECT-TYPE
    SYNTAX          SonusSlotIndex
    MAX-ACCESS      read-only
    STATUS          current
    DESCRIPTION     
            "The Slot the circuit is defined for and an index into the table."
    ::= { sonusIsupsgCircuitStatByPortEntry 2 }

sonusIsupsgCircuitStatByPortPortIndex OBJECT-TYPE
    SYNTAX          Integer32
    MAX-ACCESS      read-only
    STATUS          current
    DESCRIPTION     
            "The Port the circuit is defined for and an index into the table."
    ::= { sonusIsupsgCircuitStatByPortEntry 3 }

sonusIsupsgCircuitStatByPortDS1 OBJECT-TYPE
    SYNTAX          Integer32
    MAX-ACCESS      read-only
    STATUS          current
    DESCRIPTION     
            "The DS1 the circuit is defined for and an index into the table."
    ::= { sonusIsupsgCircuitStatByPortEntry 4 }

sonusIsupsgCircuitStatByPortChannel OBJECT-TYPE
    SYNTAX          Integer32 (1..32)
    MAX-ACCESS      read-only
    STATUS          current
    DESCRIPTION     
            "Identifies the channel the circuit represents and is an index into the table."
    ::= { sonusIsupsgCircuitStatByPortEntry 5 }

sonusIsupsgCircuitStatByPortSvcGrpIndex OBJECT-TYPE
    SYNTAX          Integer32 (1..3500)
    MAX-ACCESS      read-only
    STATUS          current
    DESCRIPTION     
            "Index of the service group the circuit is defined for."
    ::= { sonusIsupsgCircuitStatByPortEntry 6 }

sonusIsupsgCircuitStatByPortIdentityCode OBJECT-TYPE
    SYNTAX          Integer32 (0..16383)
    MAX-ACCESS      read-only
    STATUS          current
    DESCRIPTION     
            "Identifies the circuit identity code (CIC) for the circuit."
    ::= { sonusIsupsgCircuitStatByPortEntry 7 }

sonusIsupsgCircuitStatByPortUsage OBJECT-TYPE
    SYNTAX          INTEGER { unequipped(1), idle(2), inBusy(3), 
                        outBusy(4), transientSetup(5), 
                        transientRelease(6), inContinuity(7), 
                        outContinuity(8) }
    MAX-ACCESS      read-only
    STATUS          current
    DESCRIPTION     
            "The usage state of the ISUP circuit."
    ::= { sonusIsupsgCircuitStatByPortEntry 8 }

sonusIsupsgCircuitStatByPortLocalMaint OBJECT-TYPE
    SYNTAX          INTEGER { unblocked(1), blocked(2), 
                        transientUnblock(3), transientBlock(4), 
                        notAvailable(5) }
    MAX-ACCESS      read-only
    STATUS          current
    DESCRIPTION     
            "The local maintenance state of the ISUP circuit."
    ::= { sonusIsupsgCircuitStatByPortEntry 9 }

sonusIsupsgCircuitStatByPortLocalHw OBJECT-TYPE
    SYNTAX          INTEGER { unblocked(1), blocked(2), 
                        transientUnblock(3), transientBlock(4), 
                        notAvailable(5) }
    MAX-ACCESS      read-only
    STATUS          current
    DESCRIPTION     
            "The local hardware state of the ISUP circuit."
    ::= { sonusIsupsgCircuitStatByPortEntry 10 }

sonusIsupsgCircuitStatByPortRemoteMaint OBJECT-TYPE
    SYNTAX          INTEGER { unblocked(1), blocked(2), 
                        transientUnblock(3), transientBlock(4), 
                        notAvailable(5) }
    MAX-ACCESS      read-only
    STATUS          current
    DESCRIPTION     
            "The remote maintenance state of the ISUP circuit."
    ::= { sonusIsupsgCircuitStatByPortEntry 11 }

sonusIsupsgCircuitStatByPortRemoteHw OBJECT-TYPE
    SYNTAX          INTEGER { unblocked(1), blocked(2), 
                        transientUnblock(3), transientBlock(4), 
                        notAvailable(5) }
    MAX-ACCESS      read-only
    STATUS          current
    DESCRIPTION     
            "The remote hardware state of the ISUP circuit."
    ::= { sonusIsupsgCircuitStatByPortEntry 12 }

sonusIsupsgCircuitStatByPortManualCot OBJECT-TYPE
    SYNTAX          INTEGER { notAvailable(1), pending(2), inProgress(3), 
                        pass(4), fail(5), abort(6), lpaFail(7) }
    MAX-ACCESS      read-only
    STATUS          current
    DESCRIPTION     
            "The manual continuity test state of the ISUP circuit."
    ::= { sonusIsupsgCircuitStatByPortEntry 13 }

sonusIsupServiceGroupMIBNotifications OBJECT IDENTIFIER
    ::= { sonusIsupServiceGroupMIB 2 }

sonusIsupServiceGroupMIBNotificationsPrefix OBJECT IDENTIFIER
    ::= { sonusIsupServiceGroupMIBNotifications 0 }

sonusIsupServiceGroupMIBNotificationsObjects OBJECT IDENTIFIER
    ::= { sonusIsupServiceGroupMIBNotifications 1 }

sonusIsupSvcGrpName OBJECT-TYPE
    SYNTAX          DisplayString (SIZE(0..23))
    MAX-ACCESS      read-only
    STATUS          current
    DESCRIPTION     
            "Name of the ISUP service group."
    ::= { sonusIsupServiceGroupMIBNotificationsObjects 1 }

sonusIsupMaintReason OBJECT-TYPE
    SYNTAX          INTEGER { ss7GwRegistration(1), 
                        remoteSs7PointCodeAccess(2), trunkGroupMode(3), 
                        serviceGroupMode(4), circuitMode(5), ds1Mode(6), 
                        serverMode(7), localHardware(8), 
                        remoteMaintenance(9), remoteHardware(10), 
                        remoteUnequipped(11), ss7GwResynchronization(12), 
                        localMaintenance(13) }
    MAX-ACCESS      read-only
    STATUS          current
    DESCRIPTION     
            "Maintenance reason for blocking/unblocking of the circuit."
    ::= { sonusIsupServiceGroupMIBNotificationsObjects 2 }

sonusIsupTrunkGrpName OBJECT-TYPE
    SYNTAX          DisplayString (SIZE(0..23))
    MAX-ACCESS      read-only
    STATUS          current
    DESCRIPTION     
            "Name of the trunk group."
    ::= { sonusIsupServiceGroupMIBNotificationsObjects 3 }

sonusIsupCircuit OBJECT-TYPE
    SYNTAX          Integer32 (0..16383)
    MAX-ACCESS      read-only
    STATUS          current
    DESCRIPTION     
            "Base circuit identity code (CIC) for the circuit."
    ::= { sonusIsupServiceGroupMIBNotificationsObjects 4 }

sonusIsupCircuitOffsets OBJECT-TYPE
    SYNTAX          BITS { cicOffset0(0), cicOffset1(1), cicOffset2(2), 
                        cicOffset3(3), cicOffset4(4), cicOffset5(5), 
                        cicOffset6(6), cicOffset7(7), cicOffset8(8), 
                        cicOffset9(9), cicOffset10(10), cicOffset11(11), 
                        cicOffset12(12), cicOffset13(13), 
                        cicOffset14(14), cicOffset15(15), 
                        cicOffset16(16), cicOffset17(17), 
                        cicOffset18(18), cicOffset19(19), 
                        cicOffset20(20), cicOffset21(21), 
                        cicOffset22(22), cicOffset23(23) }
    MAX-ACCESS      read-only
    STATUS          current
    DESCRIPTION     
            "Circuit maintenance status bitmap for CIC range. A 32 bit field is used in which the MSB is offset 0 from base"
    ::= { sonusIsupServiceGroupMIBNotificationsObjects 5 }

sonusIsupCalledPartyNumber OBJECT-TYPE
    SYNTAX          DisplayString (SIZE(0..31))
    MAX-ACCESS      read-only
    STATUS          current
    DESCRIPTION     
            "Called Party Number."
    ::= { sonusIsupServiceGroupMIBNotificationsObjects 6 }

sonusIsupCallingPartyNumber OBJECT-TYPE
    SYNTAX          DisplayString (SIZE(0..31))
    MAX-ACCESS      read-only
    STATUS          current
    DESCRIPTION     
            "Calling Party Number."
    ::= { sonusIsupServiceGroupMIBNotificationsObjects 7 }

sonusIsupMaintCode OBJECT-TYPE
    SYNTAX          DisplayString (SIZE(0..31))
    MAX-ACCESS      read-only
    STATUS          current
    DESCRIPTION     
            "Maintainence code."
    ::= { sonusIsupServiceGroupMIBNotificationsObjects 8 }

sonusIsupLocalPointCode OBJECT-TYPE
    SYNTAX          Integer32 (0..16777215)
    MAX-ACCESS      read-only
    STATUS          current
    DESCRIPTION     
            "Local Point Code."
    ::= { sonusIsupServiceGroupMIBNotificationsObjects 9 }

sonusIsupRemotePointCode OBJECT-TYPE
    SYNTAX          Integer32 (0..16777215)
    MAX-ACCESS      read-only
    STATUS          current
    DESCRIPTION     
            "Remote Point Code."
    ::= { sonusIsupServiceGroupMIBNotificationsObjects 10 }

sonusIsupTimerName OBJECT-TYPE
    SYNTAX          DisplayString (SIZE(0..7))
    MAX-ACCESS      read-only
    STATUS          current
    DESCRIPTION     
            "ISUP Protocol Timer ID."
    ::= { sonusIsupServiceGroupMIBNotificationsObjects 11 }

sonusServiceGroupACCObject OBJECT-TYPE
    SYNTAX          INTEGER { sonusSgAccRespProcess(1), 
                        sonusSgAccL1ARCancelpercentage(2), 
                        sonusSgAccL1DRCancelpercentage(3), 
                        sonusSgAccL2ARCancelpercentage(4), 
                        sonusSgAccL2DRCancelpercentage(5), 
                        sonusSgAccL3ARCancelpercentage(6), 
                        sonusSgAccL3DRCancelpercentage(7), 
                        sonusSgAccSendACL(8) }
    MAX-ACCESS      read-only
    STATUS          current
    DESCRIPTION     
            "This object is an enumeration that indicates what ACC
             object in the service group table has changed."
    ::= { sonusIsupServiceGroupMIBNotificationsObjects 12 }

sonusIsupNodeIndex OBJECT-TYPE
    SYNTAX          Integer32 (0..16777215)
    MAX-ACCESS      read-only
    STATUS          current
    DESCRIPTION     
            "The index value of the node."
    ::= { sonusIsupServiceGroupMIBNotificationsObjects 13 }

sonusIsupDialedNumber OBJECT-TYPE
    SYNTAX          DisplayString (SIZE(0..31))
    MAX-ACCESS      read-only
    STATUS          current
    DESCRIPTION     
            "Dialed Number."
    ::= { sonusIsupServiceGroupMIBNotificationsObjects 14 }

sonusIsupCircuitBlockedTrapsSuppressed OBJECT-TYPE
    SYNTAX          Unsigned32 (0..4294967295)
    MAX-ACCESS      read-only
    STATUS          current
    DESCRIPTION     
            "The number of ISUP circuit Blocked traps Suppressed"
    ::= { sonusIsupServiceGroupMIBNotificationsObjects 15 }

sonusIsupCircuitBlockedCount OBJECT-TYPE
    SYNTAX          Unsigned32 (0..4294967295)
    MAX-ACCESS      read-only
    STATUS          current
    DESCRIPTION     
            "The number of ISUP circuits Blocked relating to the traps Suppressed"
    ::= { sonusIsupServiceGroupMIBNotificationsObjects 16 }

sonusIsupCircuitUnblockedTrapsSuppressed OBJECT-TYPE
    SYNTAX          Unsigned32 (0..4294967295)
    MAX-ACCESS      read-only
    STATUS          current
    DESCRIPTION     
            "The number of ISUP circuit Unblocked traps Suppressed"
    ::= { sonusIsupServiceGroupMIBNotificationsObjects 17 }

sonusIsupCircuitUnblockedCount OBJECT-TYPE
    SYNTAX          Unsigned32 (0..4294967295)
    MAX-ACCESS      read-only
    STATUS          current
    DESCRIPTION     
            "The number of ISUP circuits Unblocked relating to the traps Suppressed"
    ::= { sonusIsupServiceGroupMIBNotificationsObjects 18 }

sonusIsupCircuitResetTrapsSuppressed OBJECT-TYPE
    SYNTAX          Unsigned32 (0..4294967295)
    MAX-ACCESS      read-only
    STATUS          current
    DESCRIPTION     
            "The number of ISUP circuit reset traps Suppressed"
    ::= { sonusIsupServiceGroupMIBNotificationsObjects 19 }

sonusIsupCircuitResetCount OBJECT-TYPE
    SYNTAX          Unsigned32 (0..4294967295)
    MAX-ACCESS      read-only
    STATUS          current
    DESCRIPTION     
            "The number of ISUP circuits reset relating to the traps Suppressed"
    ::= { sonusIsupServiceGroupMIBNotificationsObjects 20 }

sonusIsupT13ExpiryEvents OBJECT-TYPE
    SYNTAX          Unsigned32 (0..4294967295)
    MAX-ACCESS      read-only
    STATUS          current
    DESCRIPTION     
            "The number of ISUP T13 expiry events during consolidation period"
    ::= { sonusIsupServiceGroupMIBNotificationsObjects 21 }

sonusIsupT15ExpiryEvents OBJECT-TYPE
    SYNTAX          Unsigned32 (0..4294967295)
    MAX-ACCESS      read-only
    STATUS          current
    DESCRIPTION     
            "The number of ISUP T15 expiry events during consolidation period"
    ::= { sonusIsupServiceGroupMIBNotificationsObjects 22 }

sonusIsupT17ExpiryEvents OBJECT-TYPE
    SYNTAX          Unsigned32 (0..4294967295)
    MAX-ACCESS      read-only
    STATUS          current
    DESCRIPTION     
            "The number of ISUP T17 expiry events during consolidation period"
    ::= { sonusIsupServiceGroupMIBNotificationsObjects 23 }

sonusIsupT19ExpiryEvents OBJECT-TYPE
    SYNTAX          Unsigned32 (0..4294967295)
    MAX-ACCESS      read-only
    STATUS          current
    DESCRIPTION     
            "The number of ISUP T19 expiry events during consolidation period"
    ::= { sonusIsupServiceGroupMIBNotificationsObjects 24 }

sonusIsupT21ExpiryEvents OBJECT-TYPE
    SYNTAX          Unsigned32 (0..4294967295)
    MAX-ACCESS      read-only
    STATUS          current
    DESCRIPTION     
            "The number of ISUP T21 expiry events during consolidation period"
    ::= { sonusIsupServiceGroupMIBNotificationsObjects 25 }

sonusIsupT23ExpiryEvents OBJECT-TYPE
    SYNTAX          Unsigned32 (0..4294967295)
    MAX-ACCESS      read-only
    STATUS          current
    DESCRIPTION     
            "The number of ISUP T23 expiry events during consolidation period"
    ::= { sonusIsupServiceGroupMIBNotificationsObjects 26 }

sonusIsupT33ExpiryEvents OBJECT-TYPE
    SYNTAX          Unsigned32 (0..4294967295)
    MAX-ACCESS      read-only
    STATUS          current
    DESCRIPTION     
            "The number of ISUP T33 expiry events during consolidation period"
    ::= { sonusIsupServiceGroupMIBNotificationsObjects 27 }

sonusIsupT5ExpiryEvents OBJECT-TYPE
    SYNTAX          Unsigned32 (0..4294967295)
    MAX-ACCESS      read-only
    STATUS          current
    DESCRIPTION     
            "The number of ISUP T5 expiry events during consolidation period"
    ::= { sonusIsupServiceGroupMIBNotificationsObjects 28 }

sonusIsupTCVTExpiryEvents OBJECT-TYPE
    SYNTAX          Unsigned32 (0..4294967295)
    MAX-ACCESS      read-only
    STATUS          current
    DESCRIPTION     
            "The number of ISUP TCVT expiry events during consolidation period"
    ::= { sonusIsupServiceGroupMIBNotificationsObjects 29 }

sonusIsupTCQMExpiryEvents OBJECT-TYPE
    SYNTAX          Unsigned32 (0..4294967295)
    MAX-ACCESS      read-only
    STATUS          current
    DESCRIPTION     
            "The number of ISUP TCQM expiry events during consolidation period"
    ::= { sonusIsupServiceGroupMIBNotificationsObjects 30 }

sonusIsupSvcGrpInServiceNotification NOTIFICATION-TYPE
    OBJECTS         { sonusIsupSvcGrpName, sonusEventDescription, 
                      sonusEventClass, sonusEventLevel, sonusSequenceId, 
                      sonusEventTime }
    STATUS          current
    DESCRIPTION     
            "This trap indicates that the ISUP Service Group was put in service by maintenance staff."
    ::= { sonusIsupServiceGroupMIBNotificationsPrefix 1 }

sonusIsupSvcGrpOutOfServiceNotification NOTIFICATION-TYPE
    OBJECTS         { sonusIsupSvcGrpName, sonusEventDescription, 
                      sonusEventClass, sonusEventLevel, sonusSequenceId, 
                      sonusEventTime }
    STATUS          current
    DESCRIPTION     
            "This trap indicates that the ISUP Service Group was taken out of service by maintenance staff."
    ::= { sonusIsupServiceGroupMIBNotificationsPrefix 2 }

sonusIsupCircuitBlockedNotification NOTIFICATION-TYPE
    OBJECTS         { sonusIsupSvcGrpName, sonusIsupMaintReason, 
                      sonusIsupTrunkGrpName, sonusIsupCircuit, 
                      sonusIsupCircuitOffsets, sonusEventDescription, 
                      sonusEventClass, sonusEventLevel, sonusSequenceId, 
                      sonusEventTime }
    STATUS          current
    DESCRIPTION     
            "This trap indicates that the ISUP Circuit(s) were blocked."
    ::= { sonusIsupServiceGroupMIBNotificationsPrefix 3 }

sonusIsupCircuitUnblockedNotification NOTIFICATION-TYPE
    OBJECTS         { sonusIsupSvcGrpName, sonusIsupMaintReason, 
                      sonusIsupTrunkGrpName, sonusIsupCircuit, 
                      sonusIsupCircuitOffsets, sonusEventDescription, 
                      sonusEventClass, sonusEventLevel, sonusSequenceId, 
                      sonusEventTime }
    STATUS          current
    DESCRIPTION     
            "This trap indicates that the ISUP Circuit(s) were unblocked."
    ::= { sonusIsupServiceGroupMIBNotificationsPrefix 4 }

sonusIsupCircuitResetNotification NOTIFICATION-TYPE
    OBJECTS         { sonusIsupSvcGrpName, sonusIsupTrunkGrpName, 
                      sonusIsupCircuit, sonusIsupCircuitOffsets, 
                      sonusEventDescription, sonusEventClass, 
                      sonusEventLevel, sonusSequenceId, sonusEventTime }
    STATUS          current
    DESCRIPTION     
            "This trap indicates that the ISUP Circuit(s) were reset."
    ::= { sonusIsupServiceGroupMIBNotificationsPrefix 5 }

sonusIsupContinuityRecheckFailureNotification NOTIFICATION-TYPE
    OBJECTS         { sonusIsupSvcGrpName, sonusIsupCircuit, 
                      sonusEventDescription, sonusEventClass, 
                      sonusEventLevel, sonusSequenceId, sonusEventTime }
    STATUS          current
    DESCRIPTION     
            "This trap indicates that the Continuity Recheck on the ISUP circuit failed."
    ::= { sonusIsupServiceGroupMIBNotificationsPrefix 6 }

sonusIsupCicRegistrationFailedNotification NOTIFICATION-TYPE
    OBJECTS         { sonusIsupCircuit, sonusEventDescription, 
                      sonusEventClass, sonusEventLevel, sonusSequenceId, 
                      sonusEventTime, sonusIsupCircuit, 
                      sonusIsupLocalPointCode, sonusIsupRemotePointCode, 
                      sonusIsupSvcGrpName, sonusIsupTrunkGrpName }
    STATUS          current
    DESCRIPTION     
            "This trap indicates that the CIC Registration failed after multiple retries."
    ::= { sonusIsupServiceGroupMIBNotificationsPrefix 7 }

sonusIsupHopCounterExhaustedNotification NOTIFICATION-TYPE
    OBJECTS         { sonusIsupSvcGrpName, sonusIsupCircuit, 
                      sonusIsupCalledPartyNumber, 
                      sonusIsupCallingPartyNumber, sonusEventDescription, 
                      sonusEventClass, sonusEventLevel, sonusSequenceId, 
                      sonusEventTime }
    STATUS          current
    DESCRIPTION     
            "This trap indicates that the Hop Counter value received in IAM is zero."
    ::= { sonusIsupServiceGroupMIBNotificationsPrefix 8 }

sonusIsupRelWithExchangeRoutingErrorNotification NOTIFICATION-TYPE
    OBJECTS         { sonusIsupSvcGrpName, sonusIsupCircuit, 
                      sonusIsupCalledPartyNumber, 
                      sonusIsupCallingPartyNumber, sonusEventDescription, 
                      sonusEventClass, sonusEventLevel, sonusSequenceId, 
                      sonusEventTime }
    STATUS          current
    DESCRIPTION     
            "This trap indicates that a REL message is received with Exchange Routing Error cause value."
    ::= { sonusIsupServiceGroupMIBNotificationsPrefix 9 }

sonusIsupCqmTimeoutNotification NOTIFICATION-TYPE
    OBJECTS         { sonusIsupCircuit, sonusEventDescription, 
                      sonusEventClass, sonusEventLevel, sonusSequenceId, 
                      sonusEventTime }
    STATUS          current
    DESCRIPTION     
            "This trap indicates that the timed out has occured waiting for CQM response"
    ::= { sonusIsupServiceGroupMIBNotificationsPrefix 10 }

sonusIsupCvtTimeoutNotification NOTIFICATION-TYPE
    OBJECTS         { sonusIsupCircuit, sonusEventDescription, 
                      sonusEventClass, sonusEventLevel, sonusSequenceId, 
                      sonusEventTime }
    STATUS          current
    DESCRIPTION     
            "This trap indicates that the timed out has occured waiting for CVT response"
    ::= { sonusIsupServiceGroupMIBNotificationsPrefix 11 }

sonusIsupFarendCircuitStateMismatchedNotification NOTIFICATION-TYPE
    OBJECTS         { sonusIsupCircuit, sonusEventDescription, 
                      sonusEventClass, sonusEventLevel, sonusSequenceId, 
                      sonusEventTime }
    STATUS          current
    DESCRIPTION     
            "This trap indicates that the circuit/block state is mismatched as report by CQR"
    ::= { sonusIsupServiceGroupMIBNotificationsPrefix 12 }

sonusIsupCircuitTimerExpired NOTIFICATION-TYPE
    OBJECTS         { sonusIsupTrunkGrpName, sonusIsupSvcGrpName, 
                      sonusIsupCircuit, sonusIsupMaintCode, 
                      sonusEventDescription, sonusEventClass, 
                      sonusEventLevel, sonusSequenceId, sonusEventTime }
    STATUS          current
    DESCRIPTION     
            "This trap indicates that the ISUP Circuit had a timer expire."
    ::= { sonusIsupServiceGroupMIBNotificationsPrefix 13 }

sonusIsupCircuitCgbaStatusMismatchNotification NOTIFICATION-TYPE
    OBJECTS         { sonusIsupSvcGrpName, sonusIsupMaintReason, 
                      sonusIsupTrunkGrpName, sonusIsupCircuit, 
                      sonusIsupCircuitOffsets, sonusEventDescription, 
                      sonusEventClass, sonusEventLevel, sonusSequenceId, 
                      sonusEventTime }
    STATUS          current
    DESCRIPTION     
            "This trap indicates that expected status bits for some ISUP Circuit(s)
             in a CGBA were not set."
    ::= { sonusIsupServiceGroupMIBNotificationsPrefix 14 }

sonusIsupCircuitCguaStatusMismatchNotification NOTIFICATION-TYPE
    OBJECTS         { sonusIsupSvcGrpName, sonusIsupMaintReason, 
                      sonusIsupTrunkGrpName, sonusIsupCircuit, 
                      sonusIsupCircuitOffsets, sonusEventDescription, 
                      sonusEventClass, sonusEventLevel, sonusSequenceId, 
                      sonusEventTime }
    STATUS          current
    DESCRIPTION     
            "This trap indicates that expected status bits for some ISUP Circuit(s)
             in a CGUA were not set."
    ::= { sonusIsupServiceGroupMIBNotificationsPrefix 15 }

sonusIsupSvcGrpCircuitsUnblockedNotification NOTIFICATION-TYPE
    OBJECTS         { sonusIsupSvcGrpName, sonusIsupMaintReason, 
                      sonusIsupTrunkGrpName, sonusEventDescription, 
                      sonusEventClass, sonusEventLevel, sonusSequenceId, 
                      sonusEventTime }
    STATUS          current
    DESCRIPTION     
            "This trap indicates that the all ISUP Circuits in the
             Service Group were unblocked."
    ::= { sonusIsupServiceGroupMIBNotificationsPrefix 16 }

sonusIsupProtocolTimerExpiryNotification NOTIFICATION-TYPE
    OBJECTS         { sonusIsupLocalPointCode, sonusIsupRemotePointCode, 
                      sonusIsupCircuit, sonusIsupTimerName, 
                      sonusEventDescription, sonusEventClass, 
                      sonusEventLevel, sonusSequenceId, sonusEventTime }
    STATUS          current
    DESCRIPTION     
            "This trap indicates ISUP Protocol timer expiries."
    ::= { sonusIsupServiceGroupMIBNotificationsPrefix 17 }

sonusIsupSvcGrpACCConfNotification NOTIFICATION-TYPE
    OBJECTS         { sonusIsupSvcGrpName, sonusIsupTrunkGrpName, 
                      sonusServiceGroupACCObject, sonusEventDescription, 
                      sonusEventClass, sonusEventLevel, sonusSequenceId, 
                      sonusEventTime }
    STATUS          current
    DESCRIPTION     
            "This trap indicates that a ACC Control
             configuration object in 
             the service group table has changed.  The 
             sonusServiceGroupACCObject parameter indicates what 
             object or objects have changed."
    ::= { sonusIsupServiceGroupMIBNotificationsPrefix 18 }

sonusIsupUCICNotification NOTIFICATION-TYPE
    OBJECTS         { sonusIsupLocalPointCode, sonusIsupRemotePointCode, 
                      sonusIsupCircuit, sonusEventDescription, 
                      sonusEventClass, sonusEventLevel, sonusSequenceId, 
                      sonusEventTime, sonusIsupNodeIndex }
    STATUS          current
    DESCRIPTION     
            "This trap indicates that a UCIC message has been received."
    ::= { sonusIsupServiceGroupMIBNotificationsPrefix 19 }

sonusIsupEmergencyCallDialedNotification NOTIFICATION-TYPE
    OBJECTS         { sonusIsupCircuit, sonusIsupSvcGrpName, 
                      sonusIsupTrunkGrpName, sonusIsupCallingPartyNumber, 
                      sonusIsupCalledPartyNumber, sonusIsupDialedNumber, 
                      sonusEventDescription, sonusEventClass, 
                      sonusEventLevel, sonusSequenceId, sonusEventTime }
    STATUS          current
    DESCRIPTION     
            "This trap indicates that an emergency call has been received at the GSX."
    ::= { sonusIsupServiceGroupMIBNotificationsPrefix 20 }

sonusIsupECSRExpiredNotification NOTIFICATION-TYPE
    OBJECTS         { sonusIsupCircuit, sonusIsupSvcGrpName, 
                      sonusIsupTrunkGrpName, sonusIsupCallingPartyNumber, 
                      sonusIsupCalledPartyNumber, sonusIsupDialedNumber, 
                      sonusEventDescription, sonusEventClass, 
                      sonusEventLevel, sonusSequenceId, sonusEventTime }
    STATUS          current
    DESCRIPTION     
            "This trap indicates that an emergency call has
             not been answered within the time specified by
             timer ECSR."
    ::= { sonusIsupServiceGroupMIBNotificationsPrefix 21 }

sonusIsupSgConsolidatedCctBlockedNotification NOTIFICATION-TYPE
    OBJECTS         { sonusShelfIndex, sonusSlotIndex, 
                      sonusIsupSvcGrpName, sonusIsupTrunkGrpName, 
                      sonusIsupCircuitBlockedTrapsSuppressed, 
                      sonusIsupCircuitBlockedCount, 
                      sonusEventDescription, sonusEventClass, 
                      sonusEventLevel, sonusSequenceId, sonusEventTime }
    STATUS          current
    DESCRIPTION     
            "This trap indicates that ISUP circuit blocked event data has been consolidated"
    ::= { sonusIsupServiceGroupMIBNotificationsPrefix 22 }

sonusIsupSgConsolidatedCctUnblockedNotification NOTIFICATION-TYPE
    OBJECTS         { sonusShelfIndex, sonusSlotIndex, 
                      sonusIsupSvcGrpName, sonusIsupTrunkGrpName, 
                      sonusIsupCircuitUnblockedTrapsSuppressed, 
                      sonusIsupCircuitUnblockedCount, 
                      sonusEventDescription, sonusEventClass, 
                      sonusEventLevel, sonusSequenceId, sonusEventTime }
    STATUS          current
    DESCRIPTION     
            "This trap indicates that ISUP circuit unblocked event data has been consolidated"
    ::= { sonusIsupServiceGroupMIBNotificationsPrefix 23 }

sonusIsupSgConsolidatedCctResetNotification NOTIFICATION-TYPE
    OBJECTS         { sonusShelfIndex, sonusSlotIndex, 
                      sonusIsupSvcGrpName, sonusIsupTrunkGrpName, 
                      sonusIsupCircuitResetTrapsSuppressed, 
                      sonusIsupCircuitResetCount, sonusEventDescription, 
                      sonusEventClass, sonusEventLevel, sonusSequenceId, 
                      sonusEventTime }
    STATUS          current
    DESCRIPTION     
            "This trap indicates that ISUP circuit reset event data has been consolidated"
    ::= { sonusIsupServiceGroupMIBNotificationsPrefix 24 }

sonusIsupSgT13ExpiryNotification NOTIFICATION-TYPE
    OBJECTS         { sonusShelfIndex, sonusSlotIndex, 
                      sonusIsupSvcGrpName, sonusIsupTrunkGrpName, 
                      sonusIsupT13ExpiryEvents, sonusEventDescription, 
                      sonusEventClass, sonusEventLevel, sonusSequenceId, 
                      sonusEventTime }
    STATUS          current
    DESCRIPTION     
            "This trap indicates that ISUP T13 timer expiry event data has been consolidated"
    ::= { sonusIsupServiceGroupMIBNotificationsPrefix 25 }

sonusIsupSgT15ExpiryNotification NOTIFICATION-TYPE
    OBJECTS         { sonusShelfIndex, sonusSlotIndex, 
                      sonusIsupSvcGrpName, sonusIsupTrunkGrpName, 
                      sonusIsupT15ExpiryEvents, sonusEventDescription, 
                      sonusEventClass, sonusEventLevel, sonusSequenceId, 
                      sonusEventTime }
    STATUS          current
    DESCRIPTION     
            "This trap indicates that ISUP T15 timer expiry event data has been consolidated"
    ::= { sonusIsupServiceGroupMIBNotificationsPrefix 26 }

sonusIsupSgT17ExpiryNotification NOTIFICATION-TYPE
    OBJECTS         { sonusShelfIndex, sonusSlotIndex, 
                      sonusIsupSvcGrpName, sonusIsupTrunkGrpName, 
                      sonusIsupT17ExpiryEvents, sonusEventDescription, 
                      sonusEventClass, sonusEventLevel, sonusSequenceId, 
                      sonusEventTime }
    STATUS          current
    DESCRIPTION     
            "This trap indicates that ISUP T17 timer expiry event data has been consolidated"
    ::= { sonusIsupServiceGroupMIBNotificationsPrefix 27 }

sonusIsupSgT19ExpiryNotification NOTIFICATION-TYPE
    OBJECTS         { sonusShelfIndex, sonusSlotIndex, 
                      sonusIsupSvcGrpName, sonusIsupTrunkGrpName, 
                      sonusIsupT19ExpiryEvents, sonusEventDescription, 
                      sonusEventClass, sonusEventLevel, sonusSequenceId, 
                      sonusEventTime }
    STATUS          current
    DESCRIPTION     
            "This trap indicates that ISUP T19 timer expiry event data has been consolidated"
    ::= { sonusIsupServiceGroupMIBNotificationsPrefix 28 }

sonusIsupSgT21ExpiryNotification NOTIFICATION-TYPE
    OBJECTS         { sonusShelfIndex, sonusSlotIndex, 
                      sonusIsupSvcGrpName, sonusIsupTrunkGrpName, 
                      sonusIsupT21ExpiryEvents, sonusEventDescription, 
                      sonusEventClass, sonusEventLevel, sonusSequenceId, 
                      sonusEventTime }
    STATUS          current
    DESCRIPTION     
            "This trap indicates that ISUP T21 timer expiry event data has been consolidated"
    ::= { sonusIsupServiceGroupMIBNotificationsPrefix 29 }

sonusIsupSgT23ExpiryNotification NOTIFICATION-TYPE
    OBJECTS         { sonusShelfIndex, sonusSlotIndex, 
                      sonusIsupSvcGrpName, sonusIsupTrunkGrpName, 
                      sonusIsupT23ExpiryEvents, sonusEventDescription, 
                      sonusEventClass, sonusEventLevel, sonusSequenceId, 
                      sonusEventTime }
    STATUS          current
    DESCRIPTION     
            "This trap indicates that ISUP T23 timer expiry event data has been consolidated"
    ::= { sonusIsupServiceGroupMIBNotificationsPrefix 30 }

sonusIsupSgT33ExpiryNotification NOTIFICATION-TYPE
    OBJECTS         { sonusShelfIndex, sonusSlotIndex, 
                      sonusIsupSvcGrpName, sonusIsupTrunkGrpName, 
                      sonusIsupT33ExpiryEvents, sonusEventDescription, 
                      sonusEventClass, sonusEventLevel, sonusSequenceId, 
                      sonusEventTime }
    STATUS          current
    DESCRIPTION     
            "This trap indicates that ISUP T33 timer expiry event data has been consolidated"
    ::= { sonusIsupServiceGroupMIBNotificationsPrefix 31 }

sonusIsupSgT5ExpiryNotification NOTIFICATION-TYPE
    OBJECTS         { sonusShelfIndex, sonusSlotIndex, 
                      sonusIsupSvcGrpName, sonusIsupTrunkGrpName, 
                      sonusIsupT5ExpiryEvents, sonusEventDescription, 
                      sonusEventClass, sonusEventLevel, sonusSequenceId, 
                      sonusEventTime }
    STATUS          current
    DESCRIPTION     
            "This trap indicates that ISUP T5 timer expiry event data has been consolidated"
    ::= { sonusIsupServiceGroupMIBNotificationsPrefix 32 }

sonusIsupSgTCVTExpiryNotification NOTIFICATION-TYPE
    OBJECTS         { sonusShelfIndex, sonusSlotIndex, 
                      sonusIsupSvcGrpName, sonusIsupTrunkGrpName, 
                      sonusIsupTCVTExpiryEvents, sonusEventDescription, 
                      sonusEventClass, sonusEventLevel, sonusSequenceId, 
                      sonusEventTime }
    STATUS          current
    DESCRIPTION     
            "This trap indicates that ISUP TCVT timer expiry event data has been consolidated"
    ::= { sonusIsupServiceGroupMIBNotificationsPrefix 33 }

sonusIsupSgTCQMExpiryNotification NOTIFICATION-TYPE
    OBJECTS         { sonusShelfIndex, sonusSlotIndex, 
                      sonusIsupSvcGrpName, sonusIsupTrunkGrpName, 
                      sonusIsupTCQMExpiryEvents, sonusEventDescription, 
                      sonusEventClass, sonusEventLevel, sonusSequenceId, 
                      sonusEventTime }
    STATUS          current
    DESCRIPTION     
            "This trap indicates that ISUP TCQM timer expiry event data has been consolidated"
    ::= { sonusIsupServiceGroupMIBNotificationsPrefix 34 }

END -- end of module SONUS-ISUP-SERVICE-GROUP-MIB.
