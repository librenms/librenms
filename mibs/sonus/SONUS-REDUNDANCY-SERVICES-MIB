--
-- This SMIv2 module has been generated by smidump 0.2-cvs. Do not edit.
--

SONUS-REDUNDANCY-SERVICES-MIB DEFINITIONS ::= BEGIN

IMPORTS
    Integer32, MODULE-IDENTITY, NOTIFICATION-TYPE, OBJECT-TYPE
        FROM SNMPv2-SMI
    DateAndTime, RowStatus
        FROM SNMPv2-TC
    sonusEventClass, sonusEventDescription, sonusEventLevel, 
    sonusEventTime, sonusSequenceId, sonusShelfIndex, sonusSlotIndex
        FROM SONUS-COMMON-MIB
    sonusServicesMIBs
        FROM SONUS-SMI
    ServerFunctionType, ServerTypeID, SonusName, SonusShelfIndex, 
    SonusSlotIndex
        FROM SONUS-TC;

sonusRedundancyServicesMIB MODULE-IDENTITY
    LAST-UPDATED    "200802230000Z"
    ORGANIZATION    
            "Sonus Networks, Inc."
    CONTACT-INFO    
            "   Customer Support    
             Sonus Networks, Inc.
             7 Technology Park Drive
             Westford, MA 01886
             USA
             
             Tel: 978-614-8100
             Fax: 978-614-8609"
    DESCRIPTION     
            "The MIB Module for Redundancy Group and Clients Configuration."
    ::= { sonusServicesMIBs 8 }


sonusRedundancyServicesMIBObjects OBJECT IDENTIFIER
    ::= { sonusRedundancyServicesMIB 1 }

sonusRedundGroup OBJECT IDENTIFIER
    ::= { sonusRedundancyServicesMIBObjects 1 }

sonusRedundGroupNextIndex OBJECT-TYPE
    SYNTAX          Integer32
    MAX-ACCESS      read-only
    STATUS          current
    DESCRIPTION     
            "The next valid index to use when creating an entry in
             the sonusRedundGroupTable."
    ::= { sonusRedundGroup 1 }

sonusRedundGroupTable OBJECT-TYPE
    SYNTAX          SEQUENCE OF SonusRedundGroupEntry
    MAX-ACCESS      not-accessible
    STATUS          current
    DESCRIPTION     
            "This table specifies the redundancy group list."
    ::= { sonusRedundGroup 2 }

sonusRedundGroupEntry OBJECT-TYPE
    SYNTAX          SonusRedundGroupEntry
    MAX-ACCESS      not-accessible
    STATUS          current
    DESCRIPTION     
            ""
    INDEX           { sonusRedundGroupAdmnIndex }
    ::= { sonusRedundGroupTable 1 }

SonusRedundGroupEntry ::=
    SEQUENCE {
        sonusRedundGroupAdmnIndex       Integer32,
        sonusRedundGroupAdmnState       INTEGER,
        sonusRedundGroupName            SonusName,
        sonusRedundGroupShelfIndex      SonusShelfIndex,
        sonusRedundGroupRedundSlotIndex SonusSlotIndex,
        sonusRedundGroupSwitchoverCntrl INTEGER,
        sonusRedundGroupSwitchoverClientSlotIndex         SonusSlotIndex,
        sonusRedundGroupFallbackCntrl   INTEGER,
        sonusRedundGroupWaitToRevertTime Integer32,
        sonusRedundGroupAutoDetectCntrl INTEGER,
        sonusRedundGroupHwType          ServerTypeID,
        sonusRedundGroupHealthcheckCntrl INTEGER,
        sonusRedundGroupAdmnRowStatus   RowStatus,
        sonusRedundGroupSrvrFunction    ServerFunctionType,
        sonusRedundGroupTestCntrl       INTEGER,
        sonusRedundGroupTestAction      INTEGER
    }

sonusRedundGroupAdmnIndex OBJECT-TYPE
    SYNTAX          Integer32
    MAX-ACCESS      read-only
    STATUS          current
    DESCRIPTION     
            "Identifies the target redundancy group entry."
    ::= { sonusRedundGroupEntry 1 }

sonusRedundGroupAdmnState OBJECT-TYPE
    SYNTAX          INTEGER { disabled(1), enabled(2) }
    MAX-ACCESS      read-write
    STATUS          current
    DESCRIPTION     
            "The administrative state of this redundancy group entry."
    DEFVAL          { disabled }
    ::= { sonusRedundGroupEntry 2 }

sonusRedundGroupName OBJECT-TYPE
    SYNTAX          SonusName
    MAX-ACCESS      read-write
    STATUS          current
    DESCRIPTION     
            "The name of this redundancy group instance."
    ::= { sonusRedundGroupEntry 3 }

sonusRedundGroupShelfIndex OBJECT-TYPE
    SYNTAX          SonusShelfIndex
    MAX-ACCESS      read-write
    STATUS          current
    DESCRIPTION     
            "The shelf index of this redundancy group entry."
    ::= { sonusRedundGroupEntry 4 }

sonusRedundGroupRedundSlotIndex OBJECT-TYPE
    SYNTAX          SonusSlotIndex
    MAX-ACCESS      read-write
    STATUS          current
    DESCRIPTION     
            "The redundant slot index of this redundancy group entry."
    ::= { sonusRedundGroupEntry 5 }

sonusRedundGroupSwitchoverCntrl OBJECT-TYPE
    SYNTAX          INTEGER { none(1), normal(2), forced(3), revert(4), 
                        revertForced(5) }
    MAX-ACCESS      read-write
    STATUS          current
    DESCRIPTION     
            "The client switching control of this redundancy group entry.  The revert
             options are used when the redundant server module is currently active.  The
             forced options do not require synchronization and may result in a loss of
             service."
    DEFVAL          { none }
    ::= { sonusRedundGroupEntry 6 }

sonusRedundGroupSwitchoverClientSlotIndex OBJECT-TYPE
    SYNTAX          SonusSlotIndex
    MAX-ACCESS      read-write
    STATUS          current
    DESCRIPTION     
            "The switchover client slot index of this redundancy group."
    ::= { sonusRedundGroupEntry 7 }

sonusRedundGroupFallbackCntrl OBJECT-TYPE
    SYNTAX          INTEGER { revertive(1), nonrevertive(2) }
    MAX-ACCESS      read-write
    STATUS          current
    DESCRIPTION     
            "The fallback control of this redundancy group entry."
    DEFVAL          { nonrevertive }
    ::= { sonusRedundGroupEntry 8 }

sonusRedundGroupWaitToRevertTime OBJECT-TYPE
    SYNTAX          Integer32 (5..12)
    MAX-ACCESS      read-write
    STATUS          current
    DESCRIPTION     
            "The Wait to Revert Time (in minutes) of this redundancy group entry."
    DEFVAL          { 5 }
    ::= { sonusRedundGroupEntry 9 }

sonusRedundGroupAutoDetectCntrl OBJECT-TYPE
    SYNTAX          INTEGER { disabled(1), enabled(2) }
    MAX-ACCESS      read-write
    STATUS          current
    DESCRIPTION     
            "The auto detected control of this redundancy group entry."
    DEFVAL          { disabled }
    ::= { sonusRedundGroupEntry 10 }

sonusRedundGroupHwType OBJECT-TYPE
    SYNTAX          ServerTypeID
    MAX-ACCESS      read-write
    STATUS          current
    DESCRIPTION     
            "The hardware type of this redundancy group entry."
    ::= { sonusRedundGroupEntry 11 }

sonusRedundGroupHealthcheckCntrl OBJECT-TYPE
    SYNTAX          INTEGER { disabled(1), enabled(2) }
    MAX-ACCESS      read-write
    STATUS          current
    DESCRIPTION     
            "The health check control of this redundancy group entry.
             
             For the MNS redundancy group only, this also controls health checking of
             unprotected and standby server modules."
    DEFVAL          { enabled }
    ::= { sonusRedundGroupEntry 12 }

sonusRedundGroupAdmnRowStatus OBJECT-TYPE
    SYNTAX          RowStatus
    MAX-ACCESS      read-write
    STATUS          current
    DESCRIPTION     
            ""
    ::= { sonusRedundGroupEntry 13 }

sonusRedundGroupSrvrFunction OBJECT-TYPE
    SYNTAX          ServerFunctionType
    MAX-ACCESS      read-write
    STATUS          current
    DESCRIPTION     
            "The function of the server modules contained within this redundancy group."
    ::= { sonusRedundGroupEntry 14 }

sonusRedundGroupTestCntrl OBJECT-TYPE
    SYNTAX          INTEGER { disabled(1), enabled(2) }
    MAX-ACCESS      read-write
    STATUS          current
    DESCRIPTION     
            "The CNA test control."
    DEFVAL          { disabled }
    ::= { sonusRedundGroupEntry 15 }

sonusRedundGroupTestAction OBJECT-TYPE
    SYNTAX          INTEGER { none(1), runCnaRedundancyPlaneTest(2) }
    MAX-ACCESS      read-write
    STATUS          current
    DESCRIPTION     
            "Run a runtime diagnostics test sequence."
    DEFVAL          { none }
    ::= { sonusRedundGroupEntry 16 }

sonusRedundClient OBJECT IDENTIFIER
    ::= { sonusRedundancyServicesMIBObjects 2 }

sonusRedundClientNextIndex OBJECT-TYPE
    SYNTAX          Integer32
    MAX-ACCESS      read-only
    STATUS          current
    DESCRIPTION     
            "The next valid index to use when creating an entry in
             the sonusRedundClientTable."
    ::= { sonusRedundClient 1 }

sonusRedundClientTable OBJECT-TYPE
    SYNTAX          SEQUENCE OF SonusRedundClientEntry
    MAX-ACCESS      not-accessible
    STATUS          current
    DESCRIPTION     
            "This table specifies the redundancy group client list."
    ::= { sonusRedundClient 2 }

sonusRedundClientEntry OBJECT-TYPE
    SYNTAX          SonusRedundClientEntry
    MAX-ACCESS      not-accessible
    STATUS          current
    DESCRIPTION     
            ""
    INDEX           { sonusRedundClientAdmnGroupIndex, 
                      sonusRedundClientAdmnSlotIndex }
    ::= { sonusRedundClientTable 1 }

SonusRedundClientEntry ::=
    SEQUENCE {
        sonusRedundClientAdmnGroupIndex Integer32,
        sonusRedundClientAdmnSlotIndex  SonusSlotIndex,
        sonusRedundClientAdmnState      INTEGER,
        sonusRedundClientAdmnRowStatus  RowStatus
    }

sonusRedundClientAdmnGroupIndex OBJECT-TYPE
    SYNTAX          Integer32
    MAX-ACCESS      read-only
    STATUS          current
    DESCRIPTION     
            "The index of the redundancy group to which this client belongs to."
    ::= { sonusRedundClientEntry 1 }

sonusRedundClientAdmnSlotIndex OBJECT-TYPE
    SYNTAX          SonusSlotIndex
    MAX-ACCESS      read-only
    STATUS          current
    DESCRIPTION     
            "The slot index of this client entry."
    ::= { sonusRedundClientEntry 2 }

sonusRedundClientAdmnState OBJECT-TYPE
    SYNTAX          INTEGER { disabled(1), enabled(2) }
    MAX-ACCESS      read-write
    STATUS          current
    DESCRIPTION     
            "The state of this client entry."
    DEFVAL          { disabled }
    ::= { sonusRedundClientEntry 3 }

sonusRedundClientAdmnRowStatus OBJECT-TYPE
    SYNTAX          RowStatus
    MAX-ACCESS      read-write
    STATUS          current
    DESCRIPTION     
            ""
    ::= { sonusRedundClientEntry 4 }

sonusRedundGroupStatTable OBJECT-TYPE
    SYNTAX          SEQUENCE OF SonusRedundGroupStatEntry
    MAX-ACCESS      not-accessible
    STATUS          current
    DESCRIPTION     
            "This table presents status for the redundancy group."
    ::= { sonusRedundancyServicesMIBObjects 3 }

sonusRedundGroupStatEntry OBJECT-TYPE
    SYNTAX          SonusRedundGroupStatEntry
    MAX-ACCESS      not-accessible
    STATUS          current
    DESCRIPTION     
            ""
    INDEX           { sonusRedundGroupStatIndex }
    ::= { sonusRedundGroupStatTable 1 }

SonusRedundGroupStatEntry ::=
    SEQUENCE {
        sonusRedundGroupStatIndex       Integer32,
        sonusRedundGroupRedundOpState   INTEGER,
        sonusRedundGroupStandbySlotIndex SonusSlotIndex,
        sonusRedundGroupRedundSonicId   Integer32,
        sonusRedundGroupProtectedSlotIndex  SonusSlotIndex,
        sonusRedundGroupNumClients      Integer32,
        sonusRedundGroupNumSwitchovers  Integer32,
        sonusRedundGroupLastSwitchoverReason    INTEGER
    }

sonusRedundGroupStatIndex OBJECT-TYPE
    SYNTAX          Integer32
    MAX-ACCESS      read-only
    STATUS          current
    DESCRIPTION     
            "Identifies the index of this redundancy group index."
    ::= { sonusRedundGroupStatEntry 1 }

sonusRedundGroupRedundOpState OBJECT-TYPE
    SYNTAX          INTEGER { standby(1), activeSynced(2), 
                        activeSyncing(3), activeNotSynced(4), absent(5), 
                        reset(6), failed(7), unknown(8), outOfService(9), 
                        activeSyncedHoldOff(10), standbyHoldOff(11) }
    MAX-ACCESS      read-only
    STATUS          current
    DESCRIPTION     
            "Identifies the redundant slot operation state of this redundancy group."
    ::= { sonusRedundGroupStatEntry 2 }

sonusRedundGroupStandbySlotIndex OBJECT-TYPE
    SYNTAX          SonusSlotIndex
    MAX-ACCESS      read-only
    STATUS          current
    DESCRIPTION     
            "Identifies the standby slot index for this redundancy group.(Internal use only)"
    ::= { sonusRedundGroupStatEntry 3 }

sonusRedundGroupRedundSonicId OBJECT-TYPE
    SYNTAX          Integer32
    MAX-ACCESS      read-only
    STATUS          current
    DESCRIPTION     
            "Identifies the redundant slot's sonic Id of this redundancy group.(Internal use only)"
    ::= { sonusRedundGroupStatEntry 4 }

sonusRedundGroupProtectedSlotIndex OBJECT-TYPE
    SYNTAX          SonusSlotIndex
    MAX-ACCESS      read-only
    STATUS          current
    DESCRIPTION     
            "Identifies the protected slot of this redundancy group."
    ::= { sonusRedundGroupStatEntry 5 }

sonusRedundGroupNumClients OBJECT-TYPE
    SYNTAX          Integer32
    MAX-ACCESS      read-only
    STATUS          current
    DESCRIPTION     
            "Indicates the number of clients of this redundancy group."
    ::= { sonusRedundGroupStatEntry 6 }

sonusRedundGroupNumSwitchovers OBJECT-TYPE
    SYNTAX          Integer32
    MAX-ACCESS      read-only
    STATUS          current
    DESCRIPTION     
            "Indicates the total number of switchovers on this redundancy group."
    ::= { sonusRedundGroupStatEntry 7 }

sonusRedundGroupLastSwitchoverReason OBJECT-TYPE
    SYNTAX          INTEGER { none(1), adminSwitchover(2), 
                        autoReversion(3), reset(4), removal(5), 
                        softwareFailure(6), hardwareFailure(7), 
                        healthCheckTimeout(8), other(9), 
                        softwareUpgrade(10), excessiveLinkFailure(11), 
                        reserved2(12), unknown(13) }
    MAX-ACCESS      read-only
    STATUS          current
    DESCRIPTION     
            "Reason for the last switchover in this redundancy group."
    ::= { sonusRedundGroupStatEntry 8 }

sonusRedundClientStatTable OBJECT-TYPE
    SYNTAX          SEQUENCE OF SonusRedundClientStatEntry
    MAX-ACCESS      not-accessible
    STATUS          current
    DESCRIPTION     
            "This table presents clients status for the redundancy group."
    ::= { sonusRedundancyServicesMIBObjects 4 }

sonusRedundClientStatEntry OBJECT-TYPE
    SYNTAX          SonusRedundClientStatEntry
    MAX-ACCESS      not-accessible
    STATUS          current
    DESCRIPTION     
            ""
    INDEX           { sonusRedundClientStatGroupIndex, 
                      sonusRedundClientStatSlotIndex }
    ::= { sonusRedundClientStatTable 1 }

SonusRedundClientStatEntry ::=
    SEQUENCE {
        sonusRedundClientStatGroupIndex Integer32,
        sonusRedundClientStatSlotIndex  SonusSlotIndex,
        sonusRedundClientSonicId        Integer32,
        sonusRedundClientState          INTEGER,
        sonusRedundClientTestResult     INTEGER,
        sonusRedundClientTestTime       DateAndTime
    }

sonusRedundClientStatGroupIndex OBJECT-TYPE
    SYNTAX          Integer32
    MAX-ACCESS      read-only
    STATUS          current
    DESCRIPTION     
            "Identifies the redundancy group index of this client."
    ::= { sonusRedundClientStatEntry 1 }

sonusRedundClientStatSlotIndex OBJECT-TYPE
    SYNTAX          SonusSlotIndex
    MAX-ACCESS      read-only
    STATUS          current
    DESCRIPTION     
            "Identifies the slot of this client."
    ::= { sonusRedundClientStatEntry 2 }

sonusRedundClientSonicId OBJECT-TYPE
    SYNTAX          Integer32
    MAX-ACCESS      read-only
    STATUS          current
    DESCRIPTION     
            "Identifies the sonic id of this client. (Internal use only)"
    ::= { sonusRedundClientStatEntry 3 }

sonusRedundClientState OBJECT-TYPE
    SYNTAX          INTEGER { standby(1), activeSynced(2), 
                        activeSyncing(3), activeNotSynced(4), absent(5), 
                        reset(6), failed(7), unknown(8), outOfService(9), 
                        activeSyncedHoldOff(10), standbyHoldOff(11) }
    MAX-ACCESS      read-only
    STATUS          current
    DESCRIPTION     
            "Indicates the state of this client."
    ::= { sonusRedundClientStatEntry 4 }

sonusRedundClientTestResult OBJECT-TYPE
    SYNTAX          INTEGER { passed(1), failed(2), indeterminate(3), 
                        notRun(4), aborted(5), notSupported(6), 
                        underTest(7), cna0XPwrFail(8), syncFail(9), 
                        prbsEnbFail(10) }
    MAX-ACCESS      read-only
    STATUS          current
    DESCRIPTION     
            "The result of the diagnostic test.
             Passed	       - The test completed successfully.
             Failed        - The test failed.
             Indeterminate - Additional manual testing required.
             Aborted       - The test was not completed.
             UnderTest     - The client is currently being tested.
             NotRun        - The test could not be run on the client.
             NotSupported  - The card type does not support the test.
             CNA03PwrFail  - CNA03 detected power failure."
    ::= { sonusRedundClientStatEntry 5 }

sonusRedundClientTestTime OBJECT-TYPE
    SYNTAX          DateAndTime
    MAX-ACCESS      read-only
    STATUS          current
    DESCRIPTION     
            "Octet string that identifies the GMT timestamp 
             of the last time the test was run."
    ::= { sonusRedundClientStatEntry 6 }

sonusRedundancyServicesMIBNotifications OBJECT IDENTIFIER
    ::= { sonusRedundancyServicesMIB 2 }

sonusRedundancyServicesMIBNotificationsPrefix OBJECT IDENTIFIER
    ::= { sonusRedundancyServicesMIBNotifications 0 }

sonusRedundancyServicesMIBNotificationsObjects OBJECT IDENTIFIER
    ::= { sonusRedundancyServicesMIBNotifications 1 }

sonusRedundPrevActiveSlotIndex OBJECT-TYPE
    SYNTAX          SonusSlotIndex
    MAX-ACCESS      read-only
    STATUS          current
    DESCRIPTION     
            "The slot index of the failed server module whose switchover generated
             this trap."
    ::= { sonusRedundancyServicesMIBNotificationsObjects 1 }

sonusRedundGroupSwitchOverNotification NOTIFICATION-TYPE
    OBJECTS         { sonusShelfIndex, sonusSlotIndex, 
                      sonusRedundPrevActiveSlotIndex, 
                      sonusRedundGroupLastSwitchoverReason, 
                      sonusRedundGroupName, sonusRedundGroupAdmnIndex, 
                      sonusEventDescription, sonusEventClass, 
                      sonusEventLevel, sonusSequenceId, sonusEventTime }
    STATUS          current
    DESCRIPTION     
            "This trap indicates a server module redundancy switchover has occurred.
             The standby server module in the specified shelf and slot has become
             active.  The previous active slot, switchover reason, and group
             information are included."
    ::= { sonusRedundancyServicesMIBNotificationsPrefix 1 }

sonusRedundGroupNoRedundancyNotification NOTIFICATION-TYPE
    OBJECTS         { sonusRedundGroupName, sonusRedundGroupAdmnIndex, 
                      sonusEventDescription, sonusEventClass, 
                      sonusEventLevel, sonusSequenceId, sonusEventTime }
    STATUS          current
    DESCRIPTION     
            "This trap indicates that the specified redundancy group has
             no redundancy protection."
    ::= { sonusRedundancyServicesMIBNotificationsPrefix 2 }

sonusRedundGroupFullRedundancyNotification NOTIFICATION-TYPE
    OBJECTS         { sonusRedundGroupName, sonusRedundGroupAdmnIndex, 
                      sonusEventDescription, sonusEventClass, 
                      sonusEventLevel, sonusSequenceId, sonusEventTime }
    STATUS          current
    DESCRIPTION     
            "This trap indicates that the specified redundancy group has
             full redundancy protection."
    ::= { sonusRedundancyServicesMIBNotificationsPrefix 3 }

sonusRedundGroupProtectedClientRestored NOTIFICATION-TYPE
    OBJECTS         { sonusShelfIndex, sonusSlotIndex, 
                      sonusRedundGroupName, sonusRedundGroupAdmnIndex, 
                      sonusEventDescription, sonusEventClass, 
                      sonusEventLevel, sonusSequenceId, sonusEventTime }
    STATUS          current
    DESCRIPTION     
            "This trap indicates that the specified redundancy group's protected
             client slot has been restored and is synchronized to the currently
             active redundant module.  For Nx1 redundancy groups, a revertive
             switchover is recommended to restore full redundancy protection to
             the group."
    ::= { sonusRedundancyServicesMIBNotificationsPrefix 4 }

sonusRedundGroupMnsActiveNotification NOTIFICATION-TYPE
    OBJECTS         { sonusShelfIndex, sonusSlotIndex, 
                      sonusEventDescription, sonusEventClass, 
                      sonusEventLevel, sonusSequenceId, sonusEventTime }
    STATUS          current
    DESCRIPTION     
            "The Management Node Server in the specified shelf and
             slot has become active following a MNS Switchover."
    ::= { sonusRedundancyServicesMIBNotificationsPrefix 5 }

sonusRedundNoRedundancySlotNotification NOTIFICATION-TYPE
    OBJECTS         { sonusShelfIndex, sonusSlotIndex, 
                      sonusEventDescription, sonusEventClass, 
                      sonusEventLevel, sonusSequenceId, sonusEventTime }
    STATUS          current
    DESCRIPTION     
            "This trap indicates that the redundant xNS has been active for a significant period
             of time.  There is no redundancy for the redundant group, except for the xNS it is
             active for."
    ::= { sonusRedundancyServicesMIBNotificationsPrefix 6 }

END -- end of module SONUS-REDUNDANCY-SERVICES-MIB.
