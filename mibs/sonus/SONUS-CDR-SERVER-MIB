--
-- This SMIv2 module has been generated by smidump 0.2-cvs. Do not edit.
--

SONUS-CDR-SERVER-MIB DEFINITIONS ::= BEGIN

IMPORTS
    Counter32, Counter64, Gauge32, Integer32, IpAddress, MODULE-IDENTITY, 
    OBJECT-TYPE, Unsigned32
        FROM SNMPv2-SMI
    DateAndTime, RowStatus, TEXTUAL-CONVENTION, TruthValue
        FROM SNMPv2-TC
    sonusCommonSoftwarePlatformServicesMIBs
        FROM SONUS-SMI;

sonusCdrServerMIB MODULE-IDENTITY
    LAST-UPDATED    "201212310000Z"
    ORGANIZATION    
            "Sonus Networks, Inc."
    CONTACT-INFO    
            "Customer Support        
             Sonus Networks, Inc.    
             4 Technology Park Drive 
             Westford, MA 01886      
             USA                     
                                     
             Tel: 978-614-8100       
             Fax: 978-614-8609"
    DESCRIPTION     
            "Configuration for external CDR servers."
    REVISION        "201212310000Z"
    DESCRIPTION     
            "Auto generated MIB."
    ::= { sonusCommonSoftwarePlatformServicesMIBs 17 }


ConfdString ::= TEXTUAL-CONVENTION
    DISPLAY-HINT    "1t"
    STATUS          current
    DESCRIPTION     
            "xs: and confd: types mapped to strings"
    SYNTAX          OCTET STRING

InetAddressIP ::= TEXTUAL-CONVENTION
    STATUS          current
    DESCRIPTION     
            "confd:inetAddressIP"
    SYNTAX          OCTET STRING (SIZE(4 | 16))

String ::= TEXTUAL-CONVENTION
    DISPLAY-HINT    "1t"
    STATUS          current
    DESCRIPTION     
            "xs:string"
    SYNTAX          OCTET STRING

SonusCdrServerTypeXferState ::= TEXTUAL-CONVENTION
    STATUS          current
    DESCRIPTION     
            "
             Server state
             "
    SYNTAX          INTEGER { idle(0), started(1), connecting(2), 
                        transferring(3), failed(4), done(5) }

SonusAccountingOutOfServiceReason ::= TEXTUAL-CONVENTION
    STATUS          current
    DESCRIPTION     
            "
             The reason why Sonus Acccounting is out of Service
             "
    SYNTAX          INTEGER { configchange(1), eventloggingerror(2) }

SonusCdrServerTypePasswdStr ::= TEXTUAL-CONVENTION
    DISPLAY-HINT    "1t"
    STATUS          current
    DESCRIPTION     
            "
             Enter encrypted string password data
             "
    SYNTAX          OCTET STRING

SonusCdrServerTypeState ::= TEXTUAL-CONVENTION
    STATUS          current
    DESCRIPTION     
            "
             Server state
             "
    SYNTAX          INTEGER { active(1), standby(2) }

SonusCdrServerTypeName ::= TEXTUAL-CONVENTION
    DISPLAY-HINT    "1t"
    STATUS          current
    DESCRIPTION     
            "
             Enter string character data
             "
    SYNTAX          OCTET STRING (SIZE(0..255))

SonusCdrServerBufferSizeType ::= TEXTUAL-CONVENTION
    STATUS          current
    DESCRIPTION     
            "
             Enter a value between in the range (4..1024)    
             "
    SYNTAX          Integer32 (4..1024)

SonusCdrServerTimeoutType ::= TEXTUAL-CONVENTION
    STATUS          current
    DESCRIPTION     
            "
             Enter a value between in the range (15..600)    
             "
    SYNTAX          Integer32 (15..600)

SonusCdrServerTypeType ::= TEXTUAL-CONVENTION
    STATUS          current
    DESCRIPTION     
            "
             One of primary or secondary
             "
    SYNTAX          INTEGER { primary(1), secondary(2) }

sonusCdrServer OBJECT IDENTIFIER
    ::= { sonusCdrServerMIB 1 }

sonusCdrServerAdminTable OBJECT-TYPE
    SYNTAX          SEQUENCE OF SonusCdrServerAdminEntry
    MAX-ACCESS      not-accessible
    STATUS          current
    DESCRIPTION     
            "
             CDR server admin
             "
    ::= { sonusCdrServer 1 }

sonusCdrServerAdminEntry OBJECT-TYPE
    SYNTAX          SonusCdrServerAdminEntry
    MAX-ACCESS      not-accessible
    STATUS          current
    DESCRIPTION     
            ""
    INDEX           { sonusCdrServerAdminType }
    ::= { sonusCdrServerAdminTable 1 }

SonusCdrServerAdminEntry ::=
    SEQUENCE {
        sonusCdrServerAdminType         SonusCdrServerTypeType,
        sonusCdrServerAdminIpAddress    InetAddressIP,
        sonusCdrServerAdminUsername     SonusCdrServerTypeName,
        sonusCdrServerAdminPassword     SonusCdrServerTypePasswdStr,
        sonusCdrServerAdminPath         SonusCdrServerTypeName,
        sonusCdrServerAdminFilePrefix   SonusCdrServerTypeName,
        sonusCdrServerAdminConnectionTimeout    SonusCdrServerTimeoutType,
        sonusCdrServerAdminTransferTimeout  SonusCdrServerTimeoutType,
        sonusCdrServerAdminRowstatus    RowStatus,
        sonusCdrServerAdminBufferSize   SonusCdrServerBufferSizeType
    }

sonusCdrServerAdminType OBJECT-TYPE
    SYNTAX          SonusCdrServerTypeType
    MAX-ACCESS      not-accessible
    STATUS          current
    DESCRIPTION     
            "
             Server type - either primary of secondary.
             "
    ::= { sonusCdrServerAdminEntry 1 }

sonusCdrServerAdminIpAddress OBJECT-TYPE
    SYNTAX          InetAddressIP
    MAX-ACCESS      read-create
    STATUS          current
    DESCRIPTION     
            "
             The IP address of the server
             "
    ::= { sonusCdrServerAdminEntry 2 }

sonusCdrServerAdminUsername OBJECT-TYPE
    SYNTAX          SonusCdrServerTypeName
    MAX-ACCESS      read-create
    STATUS          current
    DESCRIPTION     
            "
             The username on the remote server
             "
    ::= { sonusCdrServerAdminEntry 3 }

sonusCdrServerAdminPassword OBJECT-TYPE
    SYNTAX          SonusCdrServerTypePasswdStr
    MAX-ACCESS      read-create
    STATUS          current
    DESCRIPTION     
            "
             The password on the remote server
             "
    ::= { sonusCdrServerAdminEntry 4 }

sonusCdrServerAdminPath OBJECT-TYPE
    SYNTAX          SonusCdrServerTypeName
    MAX-ACCESS      read-create
    STATUS          current
    DESCRIPTION     
            "
             The path on the remote server
             "
    ::= { sonusCdrServerAdminEntry 5 }

sonusCdrServerAdminFilePrefix OBJECT-TYPE
    SYNTAX          SonusCdrServerTypeName
    MAX-ACCESS      read-create
    STATUS          current
    DESCRIPTION     
            "
             The remote file prefix that will be appended with a datestamp
             "
    ::= { sonusCdrServerAdminEntry 6 }

sonusCdrServerAdminConnectionTimeout OBJECT-TYPE
    SYNTAX          SonusCdrServerTimeoutType
    MAX-ACCESS      read-create
    STATUS          current
    DESCRIPTION     
            "
             The time to wait before timing out the connect operation
             "
    DEFVAL          { 30 }
    ::= { sonusCdrServerAdminEntry 7 }

sonusCdrServerAdminTransferTimeout OBJECT-TYPE
    SYNTAX          SonusCdrServerTimeoutType
    MAX-ACCESS      read-create
    STATUS          current
    DESCRIPTION     
            "
             The time to wait before timing out the file transfer
             "
    DEFVAL          { 120 }
    ::= { sonusCdrServerAdminEntry 8 }

sonusCdrServerAdminRowstatus OBJECT-TYPE
    SYNTAX          RowStatus
    MAX-ACCESS      read-create
    STATUS          current
    DESCRIPTION     
            ""
    ::= { sonusCdrServerAdminEntry 9 }

sonusCdrServerAdminBufferSize OBJECT-TYPE
    SYNTAX          SonusCdrServerBufferSizeType
    MAX-ACCESS      read-create
    STATUS          current
    DESCRIPTION     
            "
             The size of data to send to sftp server. Some servers may not handle large sizes.
             "
    DEFVAL          { 1024 }
    ::= { sonusCdrServerAdminEntry 10 }

sonusCdrServerStatusTable OBJECT-TYPE
    SYNTAX          SEQUENCE OF SonusCdrServerStatusEntry
    MAX-ACCESS      not-accessible
    STATUS          current
    DESCRIPTION     
            "
             CDR server status
             "
    ::= { sonusCdrServer 2 }

sonusCdrServerStatusEntry OBJECT-TYPE
    SYNTAX          SonusCdrServerStatusEntry
    MAX-ACCESS      not-accessible
    STATUS          current
    DESCRIPTION     
            ""
    INDEX           { sonusCdrServerStatusType }
    ::= { sonusCdrServerStatusTable 1 }

SonusCdrServerStatusEntry ::=
    SEQUENCE {
        sonusCdrServerStatusType        SonusCdrServerTypeType,
        sonusCdrServerStatusState       SonusCdrServerTypeState,
        sonusCdrServerStatusProgress    SonusCdrServerTypeXferState,
        sonusCdrServerStatusSuccessfulTransfers       Counter32,
        sonusCdrServerStatusFailedTransfers   Counter32,
        sonusCdrServerStatusPendingTransfers    Counter32
    }

sonusCdrServerStatusType OBJECT-TYPE
    SYNTAX          SonusCdrServerTypeType
    MAX-ACCESS      not-accessible
    STATUS          current
    DESCRIPTION     
            "
             Server type - either primary of secondary.
             "
    ::= { sonusCdrServerStatusEntry 1 }

sonusCdrServerStatusState OBJECT-TYPE
    SYNTAX          SonusCdrServerTypeState
    MAX-ACCESS      read-only
    STATUS          current
    DESCRIPTION     
            "
             The type of the event log.  Each type has separate
             configuration parameters and logs to a separate file.
             "
    ::= { sonusCdrServerStatusEntry 2 }

sonusCdrServerStatusProgress OBJECT-TYPE
    SYNTAX          SonusCdrServerTypeXferState
    MAX-ACCESS      read-only
    STATUS          current
    DESCRIPTION     
            "
             Indicator that a transfer is in progress.
             "
    ::= { sonusCdrServerStatusEntry 3 }

sonusCdrServerStatusSuccessfulTransfers OBJECT-TYPE
    SYNTAX          Counter32
    MAX-ACCESS      read-only
    STATUS          current
    DESCRIPTION     
            "
             Count of the number of files successfully transferred.
             "
    ::= { sonusCdrServerStatusEntry 4 }

sonusCdrServerStatusFailedTransfers OBJECT-TYPE
    SYNTAX          Counter32
    MAX-ACCESS      read-only
    STATUS          current
    DESCRIPTION     
            "
             Count of the number of failed transfers.
             "
    ::= { sonusCdrServerStatusEntry 5 }

sonusCdrServerStatusPendingTransfers OBJECT-TYPE
    SYNTAX          Counter32
    MAX-ACCESS      read-only
    STATUS          current
    DESCRIPTION     
            "
             Count the nmber of pending transfers.
             "
    ::= { sonusCdrServerStatusEntry 6 }

END -- end of module SONUS-CDR-SERVER-MIB.
