--
-- This SMIv2 module has been generated by smidump 0.2-cvs. Do not edit.
--

SONUS-IP-FILTER-MIB DEFINITIONS ::= BEGIN

IMPORTS
    Ipv6Address
        FROM IPV6-TC
    Integer32, IpAddress, MODULE-IDENTITY, NOTIFICATION-TYPE, 
    OBJECT-TYPE, Unsigned32
        FROM SNMPv2-SMI
    RowStatus
        FROM SNMPv2-TC
    sonusEventClass, sonusEventDescription, sonusEventLevel, 
    sonusEventTime, sonusSequenceId
        FROM SONUS-COMMON-MIB
    sonusPacketMIBs
        FROM SONUS-SMI
    SonusAdminState, SonusName, SonusShelfIndex, SonusSlotIndex
        FROM SONUS-TC;

sonusIpFilterMIB MODULE-IDENTITY
    LAST-UPDATED    "201010030000Z"
    ORGANIZATION    
            "Sonus Networks, Inc."
    CONTACT-INFO    
            "   Customer Support    
             Sonus Networks, Inc.
             7 Technology Park Drive
             Westford, MA 01886
             USA
             
             Tel: 978-614-8100
             Fax: 978-614-8609"
    DESCRIPTION     
            "The MIB Module for IP Filter management."
    ::= { sonusPacketMIBs 8 }


sonusIpFilterMIBObjects OBJECT IDENTIFIER
    ::= { sonusIpFilterMIB 1 }

sonusIpFilter OBJECT IDENTIFIER
    ::= { sonusIpFilterMIBObjects 1 }

sonusIpFilterNextIndex OBJECT-TYPE
    SYNTAX          Integer32
    MAX-ACCESS      read-only
    STATUS          current
    DESCRIPTION     
            "The next valid index to use when creating a new sonusIpFilterEntry"
    ::= { sonusIpFilter 1 }

sonusIpFilterTable OBJECT-TYPE
    SYNTAX          SEQUENCE OF SonusIpFilterEntry
    MAX-ACCESS      not-accessible
    STATUS          current
    DESCRIPTION     
            "The table of filters."
    ::= { sonusIpFilter 2 }

sonusIpFilterEntry OBJECT-TYPE
    SYNTAX          SonusIpFilterEntry
    MAX-ACCESS      not-accessible
    STATUS          current
    DESCRIPTION     
            "The specification, filter fields, for a filter."
    INDEX           { sonusIpFilterIndex }
    ::= { sonusIpFilterTable 1 }

SonusIpFilterEntry ::=
    SEQUENCE {
        sonusIpFilterIndex              Integer32,
        sonusIpFilterName               SonusName,
        sonusIpFilterDgram              INTEGER,
        sonusIpFilterDestAddrStart      IpAddress,
        sonusIpFilterDestAddrEnd        IpAddress,
        sonusIpFilterSrcAddrStart       IpAddress,
        sonusIpFilterSrcAddrEnd         IpAddress,
        sonusIpFilterProt               INTEGER,
        sonusIpFilterDestPortStart      Integer32,
        sonusIpFilterDestPortEnd        Integer32,
        sonusIpFilterSrcPortStart       Integer32,
        sonusIpFilterSrcPortEnd         Integer32,
        sonusIpFilterApp                INTEGER,
        sonusIpFilterNif                SonusName,
        sonusIpFilterState              INTEGER,
        sonusIpFilterRowStatus          RowStatus,
        sonusIpFilterDestAddrv6Start    Ipv6Address,
        sonusIpFilterDestAddrv6End      Ipv6Address,
        sonusIpFilterSrcAddrv6Start     Ipv6Address,
        sonusIpFilterSrcAddrv6End       Ipv6Address,
        sonusIpFilterIpVersion          INTEGER
    }

sonusIpFilterIndex OBJECT-TYPE
    SYNTAX          Integer32
    MAX-ACCESS      read-only
    STATUS          current
    DESCRIPTION     
            "Integer index for entry; one for one with sonusIpFilterName."
    ::= { sonusIpFilterEntry 1 }

sonusIpFilterName OBJECT-TYPE
    SYNTAX          SonusName
    MAX-ACCESS      read-write
    STATUS          current
    DESCRIPTION     
            "Name used by CLI to reference filter."
    ::= { sonusIpFilterEntry 2 }

sonusIpFilterDgram OBJECT-TYPE
    SYNTAX          INTEGER { any(1), ip(2), arp(3) }
    MAX-ACCESS      read-write
    STATUS          current
    DESCRIPTION     
            "Match specified datagram packet type, or any. If ARP, then
             all other fields are not applicaple."
    DEFVAL          { any }
    ::= { sonusIpFilterEntry 3 }

sonusIpFilterDestAddrStart OBJECT-TYPE
    SYNTAX          IpAddress
    MAX-ACCESS      read-write
    STATUS          current
    DESCRIPTION     
            "Match destination addresses inclusive of 
             sonusIpFilterDestAddrStart and sonusIpFilterDestAddrEnd.
             If sonusIpFilterDestAddrStart and FilterIpDestAddrEnd
             are zero, they are ignored (all values match)."
    DEFVAL          { 0 }
    ::= { sonusIpFilterEntry 4 }

sonusIpFilterDestAddrEnd OBJECT-TYPE
    SYNTAX          IpAddress
    MAX-ACCESS      read-write
    STATUS          current
    DESCRIPTION     
            "Match destination addresses inclusive of 
             sonusIpFilterDestAddrStart and sonusIpFilterDestAddrEnd.
             If sonusIpFilterDestAddrStart and FilterIpDestAddrEnd
             are zero, they are ignored (all values match)."
    DEFVAL          { 0 }
    ::= { sonusIpFilterEntry 5 }

sonusIpFilterSrcAddrStart OBJECT-TYPE
    SYNTAX          IpAddress
    MAX-ACCESS      read-write
    STATUS          current
    DESCRIPTION     
            "Match source addresses inclusive of 
             sonusIpFilterSrcAddrStart and sonusIpFilterSrcAddrEnd.
             If sonusIpFilterSrcAddrStart and FilterIpSrctAddrEnd
             are zero, they are ignored (all values match)."
    DEFVAL          { 0 }
    ::= { sonusIpFilterEntry 6 }

sonusIpFilterSrcAddrEnd OBJECT-TYPE
    SYNTAX          IpAddress
    MAX-ACCESS      read-write
    STATUS          current
    DESCRIPTION     
            "Match source addresses inclusive of 
             sonusIpFilterSrcAddrStart and sonusIpFilterSrcAddrEnd.
             If sonusIpFilterSrcAddrStart and FilterIpSrctAddrEnd
             are zero, they are ignored (all values match)."
    DEFVAL          { 0 }
    ::= { sonusIpFilterEntry 7 }

sonusIpFilterProt OBJECT-TYPE
    SYNTAX          INTEGER { any(1), icmp(2), udp(3), tcp(4), ospf(5), 
                        sctp(6) }
    MAX-ACCESS      read-write
    STATUS          current
    DESCRIPTION     
            "Match IP protocol type. Following port parameters meanings
             are a function of the IP protocol type."
    DEFVAL          { any }
    ::= { sonusIpFilterEntry 8 }

sonusIpFilterDestPortStart OBJECT-TYPE
    SYNTAX          Integer32 (0..65535)
    MAX-ACCESS      read-write
    STATUS          current
    DESCRIPTION     
            "Match source IP port inclusive of 
             sonusIpFilterDestPortStart and sonusIpFilterDestPortEnd.
             If sonusIpFilterDestPortStart and FilterIpDestPortEnd
             are zero, they are ignored (all values match)."
    DEFVAL          { 0 }
    ::= { sonusIpFilterEntry 9 }

sonusIpFilterDestPortEnd OBJECT-TYPE
    SYNTAX          Integer32 (0..65535)
    MAX-ACCESS      read-write
    STATUS          current
    DESCRIPTION     
            "Match source IP port inclusive of 
             sonusIpFilterDestPortStart and sonusIpFilterDestPortEnd.
             If sonusIpFilterDestPortStart and FilterIpDestPortEnd
             are zero, they are ignored (all values match)."
    DEFVAL          { 0 }
    ::= { sonusIpFilterEntry 10 }

sonusIpFilterSrcPortStart OBJECT-TYPE
    SYNTAX          Integer32 (0..65535)
    MAX-ACCESS      read-write
    STATUS          current
    DESCRIPTION     
            "Match source IP port inclusive of 
             sonusIpFilterSrcPortStart and sonusIpFilterSrcPortEnd.
             If sonusIpFilterSrcPortStart and FilterIpSrcPortEnd
             are zero, they are ignored (all values match)."
    DEFVAL          { 0 }
    ::= { sonusIpFilterEntry 11 }

sonusIpFilterSrcPortEnd OBJECT-TYPE
    SYNTAX          Integer32 (0..65535)
    MAX-ACCESS      read-write
    STATUS          current
    DESCRIPTION     
            "Match source IP port inclusive of 
             sonusIpFilterSrcPortStart and sonusIpFilterSrcPortEnd.
             If sonusIpFilterSrcPortStart and FilterIpSrcPortEnd
             are zero, they are ignored (all values match)."
    DEFVAL          { 0 }
    ::= { sonusIpFilterEntry 12 }

sonusIpFilterApp OBJECT-TYPE
    SYNTAX          INTEGER { any(1), other(2), snmp(3), nfs(4), 
                        telnet(5), sip(6), h323(7), ping(8), ospf(9), 
                        ss7(10), gwgw(11) }
    MAX-ACCESS      read-write
    STATUS          current
    DESCRIPTION     
            "Match application by using well known UDP or TCP ports, or
             through the use of a port-mapper."
    DEFVAL          { any }
    ::= { sonusIpFilterEntry 13 }

sonusIpFilterNif OBJECT-TYPE
    SYNTAX          SonusName
    MAX-ACCESS      read-write
    STATUS          current
    DESCRIPTION     
            "Match the outgoing NIF. If a null string, or
             the strings 'ALL'  or 'all', then all NIFs are matched."
    DEFVAL          { "" }
    ::= { sonusIpFilterEntry 14 }

sonusIpFilterState OBJECT-TYPE
    SYNTAX          INTEGER { disabled(1), enabled(2) }
    MAX-ACCESS      read-write
    STATUS          current
    DESCRIPTION     
            "Controls the desired state of the filter. A filter
             can only be enabled if it is unique among existing
             enabled filters"
    DEFVAL          { disabled }
    ::= { sonusIpFilterEntry 15 }

sonusIpFilterRowStatus OBJECT-TYPE
    SYNTAX          RowStatus
    MAX-ACCESS      read-write
    STATUS          current
    DESCRIPTION     
            ""
    ::= { sonusIpFilterEntry 16 }

sonusIpFilterDestAddrv6Start OBJECT-TYPE
    SYNTAX          Ipv6Address
    MAX-ACCESS      read-write
    STATUS          current
    DESCRIPTION     
            "Match destination addresses inclusive of 
             sonusIpFilterDestAddrStart and sonusIpFilterDestAddrv6End.
             If sonusIpFilterDestAddrv6Start and FilterIpDestAddrv6End
             are zero, they are ignored (all values match)."
    ::= { sonusIpFilterEntry 17 }

sonusIpFilterDestAddrv6End OBJECT-TYPE
    SYNTAX          Ipv6Address
    MAX-ACCESS      read-write
    STATUS          current
    DESCRIPTION     
            "Match destination addresses inclusive of 
             sonusIpFilterDestAddrv6Start and sonusIpFilterDestAddrv6End.
             If sonusIpFilterDestAddrv6Start and FilterIpDestAddrv6End
             are zero, they are ignored (all values match)."
    ::= { sonusIpFilterEntry 18 }

sonusIpFilterSrcAddrv6Start OBJECT-TYPE
    SYNTAX          Ipv6Address
    MAX-ACCESS      read-write
    STATUS          current
    DESCRIPTION     
            "Match source addresses inclusive of 
             sonusIpFilterSrcAddrv6Start and sonusIpFilterSrcAddrv6End.
             If sonusIpFilterSrcAddrv6Start and FilterIpSrctAddrv6End
             are zero, they are ignored (all values match)."
    ::= { sonusIpFilterEntry 19 }

sonusIpFilterSrcAddrv6End OBJECT-TYPE
    SYNTAX          Ipv6Address
    MAX-ACCESS      read-write
    STATUS          current
    DESCRIPTION     
            "Match source addresses inclusive of 
             sonusIpFilterSrcAddrv6Start and sonusIpFilterSrcAddrv6End.
             If sonusIpFilterSrcAddrv6Start and FilterIpSrctAddrv6End
             are zero, they are ignored (all values match)."
    ::= { sonusIpFilterEntry 20 }

sonusIpFilterIpVersion OBJECT-TYPE
    SYNTAX          INTEGER { afInet(2), afInet6(24) }
    MAX-ACCESS      read-only
    STATUS          current
    DESCRIPTION     
            " Ip address type for IP Output Filter."
    ::= { sonusIpFilterEntry 21 }

sonusIpFilterMIBNotifications OBJECT IDENTIFIER
    ::= { sonusIpFilter 10 }

sonusIpFilterMIBNotificationsPrefix OBJECT IDENTIFIER
    ::= { sonusIpFilterMIBNotifications 0 }

sonusIpFilterMIBNotificationsObjects OBJECT IDENTIFIER
    ::= { sonusIpFilterMIBNotifications 1 }

sonusIpInputFilter OBJECT IDENTIFIER
    ::= { sonusIpFilterMIBObjects 2 }

sonusIpInputFilterNextIndex OBJECT-TYPE
    SYNTAX          Integer32
    MAX-ACCESS      read-only
    STATUS          current
    DESCRIPTION     
            " The next valid index to use when creating a new
             sonusIpInputFilterEntry "
    ::= { sonusIpInputFilter 1 }

sonusIpInputFilterTable OBJECT-TYPE
    SYNTAX          SEQUENCE OF SonusIpInputFilterEntry
    MAX-ACCESS      not-accessible
    STATUS          current
    DESCRIPTION     
            "The table of input filters."
    ::= { sonusIpInputFilter 2 }

sonusIpInputFilterEntry OBJECT-TYPE
    SYNTAX          SonusIpInputFilterEntry
    MAX-ACCESS      not-accessible
    STATUS          current
    DESCRIPTION     
            "The specification, filter fields, for an ip input filter."
    INDEX           { sonusIpInputFilterIndex }
    ::= { sonusIpInputFilterTable 1 }

SonusIpInputFilterEntry ::=
    SEQUENCE {
        sonusIpInputFilterIndex         Integer32,
        sonusIpInputFilterName          SonusName,
        sonusIpInputFilterProt          INTEGER,
        sonusIpInputFilterNifIndexStart Integer32,
        sonusIpInputFilterNifIndexEnd   Integer32,
        sonusIpInputFilterSrcAddrStart  IpAddress,
        sonusIpInputFilterSrcAddrEnd    IpAddress,
        sonusIpInputFilterSrcPortStart  Integer32,
        sonusIpInputFilterSrcPortEnd    Integer32,
        sonusIpInputFilterDestPortStart Integer32,
        sonusIpInputFilterDestPortEnd   Integer32,
        sonusIpInputFilterState         SonusAdminState,
        sonusIpInputFilterRowStatus     RowStatus,
        sonusIpInputFilterShelf         SonusShelfIndex,
        sonusIpInputFilterSlot          SonusSlotIndex,
        sonusIpv6InputFilterSrcAddrStart Ipv6Address,
        sonusIpv6InputFilterSrcAddrEnd  Ipv6Address,
        sonusIpInputFilterVersion       INTEGER
    }

sonusIpInputFilterIndex OBJECT-TYPE
    SYNTAX          Integer32
    MAX-ACCESS      read-only
    STATUS          current
    DESCRIPTION     
            "Integer index for entry; one for one with sonusIpInputFilterName."
    ::= { sonusIpInputFilterEntry 1 }

sonusIpInputFilterName OBJECT-TYPE
    SYNTAX          SonusName
    MAX-ACCESS      read-write
    STATUS          current
    DESCRIPTION     
            "Name used by CLI to reference filter."
    ::= { sonusIpInputFilterEntry 2 }

sonusIpInputFilterProt OBJECT-TYPE
    SYNTAX          INTEGER { any(1), icmp(2), udp(3), tcp(4), sctp(5), 
                        ospf(6) }
    MAX-ACCESS      read-write
    STATUS          current
    DESCRIPTION     
            "Match IP protocol type. Following port parameters meanings
             are a function of the IP protocol type."
    DEFVAL          { any }
    ::= { sonusIpInputFilterEntry 3 }

sonusIpInputFilterNifIndexStart OBJECT-TYPE
    SYNTAX          Integer32 (1..65535)
    MAX-ACCESS      read-write
    STATUS          current
    DESCRIPTION     
            "Match the interface index inclusive of start and end
             values of interface index. This variable specifies the
             start value."
    DEFVAL          { 1 }
    ::= { sonusIpInputFilterEntry 4 }

sonusIpInputFilterNifIndexEnd OBJECT-TYPE
    SYNTAX          Integer32 (1..65535)
    MAX-ACCESS      read-write
    STATUS          current
    DESCRIPTION     
            "Match the interface index inclusive of start and end
             values of interface index. This variable specifies the
             end value. If End value is unspecified an exact match
             on the start value is performed."
    DEFVAL          { 65535 }
    ::= { sonusIpInputFilterEntry 5 }

sonusIpInputFilterSrcAddrStart OBJECT-TYPE
    SYNTAX          IpAddress
    MAX-ACCESS      read-write
    STATUS          current
    DESCRIPTION     
            "Match source addresses inclusive of 
             sonusIpInputFilterSrcAddrStart and sonusIpInputFilterSrcAddrEnd.
             If sonusIpInputFilterSrcAddrStart and FilterIpSrctAddrEnd
             are zero, they are ignored (all values match)."
    DEFVAL          { 0 }
    ::= { sonusIpInputFilterEntry 6 }

sonusIpInputFilterSrcAddrEnd OBJECT-TYPE
    SYNTAX          IpAddress
    MAX-ACCESS      read-write
    STATUS          current
    DESCRIPTION     
            "Match source addresses inclusive of 
             sonusIpInputFilterSrcAddrStart and sonusIpInputFilterSrcAddrEnd.
             If sonusIpInputFilterSrcAddrStart and FilterIpSrctAddrEnd
             are zero, they are ignored (all values match)."
    DEFVAL          { 0 }
    ::= { sonusIpInputFilterEntry 7 }

sonusIpInputFilterSrcPortStart OBJECT-TYPE
    SYNTAX          Integer32 (1..65535)
    MAX-ACCESS      read-write
    STATUS          current
    DESCRIPTION     
            "Match source IP port inclusive of 
             sonusIpInputFilterDestPortStart and sonusIpInputFilterDestPortEnd.
             If sonusIpInputFilterDestPortStart and FilterIpDestPortEnd
             are zero, they are ignored (all values match)."
    DEFVAL          { 1 }
    ::= { sonusIpInputFilterEntry 8 }

sonusIpInputFilterSrcPortEnd OBJECT-TYPE
    SYNTAX          Integer32 (1..65535)
    MAX-ACCESS      read-write
    STATUS          current
    DESCRIPTION     
            "Match source IP port inclusive of 
             sonusIpInputFilterDestPortStart and sonusIpInputFilterDestPortEnd.
             If sonusIpInputFilterDestPortStart and FilterIpDestPortEnd
             are zero, they are ignored (all values match)."
    DEFVAL          { 65535 }
    ::= { sonusIpInputFilterEntry 9 }

sonusIpInputFilterDestPortStart OBJECT-TYPE
    SYNTAX          Integer32 (1..65535)
    MAX-ACCESS      read-write
    STATUS          current
    DESCRIPTION     
            "Match source IP port inclusive of 
             sonusIpInputFilterDestPortStart and sonusIpInputFilterDestPortEnd.
             If sonusIpInputFilterDestPortStart and FilterIpDestPortEnd
             are zero, they are ignored (all values match)."
    DEFVAL          { 1 }
    ::= { sonusIpInputFilterEntry 10 }

sonusIpInputFilterDestPortEnd OBJECT-TYPE
    SYNTAX          Integer32 (1..65535)
    MAX-ACCESS      read-write
    STATUS          current
    DESCRIPTION     
            "Match source IP port inclusive of 
             sonusIpInputFilterDestPortStart and sonusIpInputFilterDestPortEnd.
             If sonusIpInputFilterDestPortStart and FilterIpDestPortEnd
             are zero, they are ignored (all values match)."
    DEFVAL          { 65535 }
    ::= { sonusIpInputFilterEntry 11 }

sonusIpInputFilterState OBJECT-TYPE
    SYNTAX          SonusAdminState
    MAX-ACCESS      read-write
    STATUS          current
    DESCRIPTION     
            "Controls the desired state of the filter. A filter
             can only be enabled if it is unique among existing
             enabled filters"
    DEFVAL          { disabled }
    ::= { sonusIpInputFilterEntry 12 }

sonusIpInputFilterRowStatus OBJECT-TYPE
    SYNTAX          RowStatus
    MAX-ACCESS      read-write
    STATUS          current
    DESCRIPTION     
            ""
    ::= { sonusIpInputFilterEntry 13 }

sonusIpInputFilterShelf OBJECT-TYPE
    SYNTAX          SonusShelfIndex
    MAX-ACCESS      read-write
    STATUS          current
    DESCRIPTION     
            "A 32-bit integer identifying the shelf of the IP input Filter"
    ::= { sonusIpInputFilterEntry 14 }

sonusIpInputFilterSlot OBJECT-TYPE
    SYNTAX          SonusSlotIndex
    MAX-ACCESS      read-write
    STATUS          current
    DESCRIPTION     
            "A 32-bit integer identifying the slot of the IP input Filter"
    ::= { sonusIpInputFilterEntry 15 }

sonusIpv6InputFilterSrcAddrStart OBJECT-TYPE
    SYNTAX          Ipv6Address
    MAX-ACCESS      read-write
    STATUS          current
    DESCRIPTION     
            "The IPv6 Address of this entry"
    ::= { sonusIpInputFilterEntry 16 }

sonusIpv6InputFilterSrcAddrEnd OBJECT-TYPE
    SYNTAX          Ipv6Address
    MAX-ACCESS      read-write
    STATUS          current
    DESCRIPTION     
            "The next hop IPv6 Address of this entry"
    ::= { sonusIpInputFilterEntry 17 }

sonusIpInputFilterVersion OBJECT-TYPE
    SYNTAX          INTEGER { afInet(2), afInet6(24) }
    MAX-ACCESS      read-only
    STATUS          current
    DESCRIPTION     
            " Ip address type for IP InPut Filter."
    ::= { sonusIpInputFilterEntry 18 }

sonusIpInputFilterActionTable OBJECT-TYPE
    SYNTAX          SEQUENCE OF SonusIpInputFilterActionEntry
    MAX-ACCESS      not-accessible
    STATUS          current
    DESCRIPTION     
            "The table of filters."
    ::= { sonusIpInputFilter 3 }

sonusIpInputFilterActionEntry OBJECT-TYPE
    SYNTAX          SonusIpInputFilterActionEntry
    MAX-ACCESS      not-accessible
    STATUS          current
    DESCRIPTION     
            "Action that can be taken on an IP input filter"
    INDEX           { sonusIpInputFilterActionIndex }
    ::= { sonusIpInputFilterActionTable 1 }

SonusIpInputFilterActionEntry ::=
    SEQUENCE {
        sonusIpInputFilterActionIndex   Integer32,
        sonusIpInputFilterAction        INTEGER,
        sonusIpInputFilterActionRowStatus RowStatus
    }

sonusIpInputFilterActionIndex OBJECT-TYPE
    SYNTAX          Integer32
    MAX-ACCESS      read-only
    STATUS          current
    DESCRIPTION     
            "Integer index for entry corresponding to an input ip
             filter entry.  This value must correspond to an
             existing sonusIpInputFilterIndex."
    ::= { sonusIpInputFilterActionEntry 1 }

sonusIpInputFilterAction OBJECT-TYPE
    SYNTAX          INTEGER { deny(1), permit(2) }
    MAX-ACCESS      read-write
    STATUS          current
    DESCRIPTION     
            "action to be taken "
    ::= { sonusIpInputFilterActionEntry 2 }

sonusIpInputFilterActionRowStatus OBJECT-TYPE
    SYNTAX          RowStatus
    MAX-ACCESS      read-write
    STATUS          current
    DESCRIPTION     
            "status of input filter action"
    ::= { sonusIpInputFilterActionEntry 3 }

sonusIpInputFilterStatusTable OBJECT-TYPE
    SYNTAX          SEQUENCE OF SonusIpInputFilterStatusEntry
    MAX-ACCESS      not-accessible
    STATUS          current
    DESCRIPTION     
            "The table of input filters."
    ::= { sonusIpInputFilter 4 }

sonusIpInputFilterStatusEntry OBJECT-TYPE
    SYNTAX          SonusIpInputFilterStatusEntry
    MAX-ACCESS      not-accessible
    STATUS          current
    DESCRIPTION     
            "fields of an Ip input filters' status table"
    INDEX           { sonusIpInputFilterStatusIndex }
    ::= { sonusIpInputFilterStatusTable 1 }

SonusIpInputFilterStatusEntry ::=
    SEQUENCE {
        sonusIpInputFilterStatusIndex   Integer32,
        sonusIpInputFilterStatusHitCount Unsigned32
    }

sonusIpInputFilterStatusIndex OBJECT-TYPE
    SYNTAX          Integer32
    MAX-ACCESS      read-only
    STATUS          current
    DESCRIPTION     
            "Integer index for entry corresponding to an input ip
             filter entry.  This value must correspond to an
             existing sonusIpInputFilterIndex."
    ::= { sonusIpInputFilterStatusEntry 1 }

sonusIpInputFilterStatusHitCount OBJECT-TYPE
    SYNTAX          Unsigned32
    MAX-ACCESS      read-only
    STATUS          current
    DESCRIPTION     
            "Number of incoming IP packets matched this filter"
    ::= { sonusIpInputFilterStatusEntry 2 }

sonusIpInputFilterDefaultWhiteListNotification NOTIFICATION-TYPE
    OBJECTS         { sonusIpInputFilterName, sonusEventDescription, 
                      sonusEventClass, sonusEventLevel, sonusSequenceId, 
                      sonusEventTime }
    STATUS          current
    DESCRIPTION     
            "This trap indicates a default white list is added to
             accept all the incoming IP packets since no other IP
             input filter is configured on this box"
    ::= { sonusIpFilterMIBNotificationsPrefix 1 }

END -- end of module SONUS-IP-FILTER-MIB.
