--
-- This SMIv2 module has been generated by smidump 0.2-cvs. Do not edit.
--

SONUS-SS7-MTP3-MIB DEFINITIONS ::= BEGIN

IMPORTS
    Integer32, MODULE-IDENTITY, NOTIFICATION-TYPE, OBJECT-TYPE, 
    Unsigned32
        FROM SNMPv2-SMI
    DisplayString, RowStatus
        FROM SNMPv2-TC
    sonusEventClass, sonusEventDescription, sonusEventLevel, 
    sonusEventTime, sonusSequenceId
        FROM SONUS-COMMON-MIB
    sonusSs7NodeName, sonusSs7ServicesMIB
        FROM SONUS-SS7-SERVICES-MIB
    SonusName, SonusNameReference, SonusPointCode
        FROM SONUS-TC;

sonusSs7Mtp3MIB MODULE-IDENTITY
    LAST-UPDATED    "200708150000Z"
    ORGANIZATION    
            "Sonus Networks, Inc."
    CONTACT-INFO    
            "   Customer Support    
             Sonus Networks, Inc.
             7 Technology Park Drive
             Westford, MA 01886
             USA
             
             Tel: 978-614-8100
             Fax: 978-614-8609"
    DESCRIPTION     
            "The MIB Module for SS7 MTP3 Configuration."
    ::= { sonusSs7ServicesMIB 3 }


sonusSs7Mtp3MIBObjects OBJECT IDENTIFIER
    ::= { sonusSs7Mtp3MIB 1 }

sonusSs7Mtp3ItuProfile OBJECT IDENTIFIER
    ::= { sonusSs7Mtp3MIBObjects 1 }

sonusSs7Mtp3ItuProfileNextIndex OBJECT-TYPE
    SYNTAX          Integer32
    MAX-ACCESS      read-only
    STATUS          current
    DESCRIPTION     
            "The next valid index to use when creating an entry in
             the sonusSs7Mtp3ItuProfileTable."
    ::= { sonusSs7Mtp3ItuProfile 1 }

sonusSs7Mtp3ItuProfileTable OBJECT-TYPE
    SYNTAX          SEQUENCE OF SonusSs7Mtp3ItuProfileEntry
    MAX-ACCESS      not-accessible
    STATUS          current
    DESCRIPTION     
            "This table specifies MTP3 timers. "
    ::= { sonusSs7Mtp3ItuProfile 2 }

sonusSs7Mtp3ItuProfileEntry OBJECT-TYPE
    SYNTAX          SonusSs7Mtp3ItuProfileEntry
    MAX-ACCESS      not-accessible
    STATUS          current
    DESCRIPTION     
            ""
    INDEX           { sonusSs7Mtp3ItuProfileIndex }
    ::= { sonusSs7Mtp3ItuProfileTable 1 }

SonusSs7Mtp3ItuProfileEntry ::=
    SEQUENCE {
        sonusSs7Mtp3ItuProfileIndex     Integer32,
        sonusSs7Mtp3ItuProfileName      SonusName,
        sonusSs7Mtp3ItuProfileRowStatus RowStatus,
        sonusSs7Mtp3ItuProfileT1        Integer32,
        sonusSs7Mtp3ItuProfileT2        Integer32,
        sonusSs7Mtp3ItuProfileT3        Integer32,
        sonusSs7Mtp3ItuProfileT4        Integer32,
        sonusSs7Mtp3ItuProfileT5        Integer32,
        sonusSs7Mtp3ItuProfileT6        Integer32,
        sonusSs7Mtp3ItuProfileT7        Integer32,
        sonusSs7Mtp3ItuProfileT8        Integer32,
        sonusSs7Mtp3ItuProfileT10       Integer32,
        sonusSs7Mtp3ItuProfileT11       Integer32,
        sonusSs7Mtp3ItuProfileT12       Integer32,
        sonusSs7Mtp3ItuProfileT13       Integer32,
        sonusSs7Mtp3ItuProfileT14       Integer32,
        sonusSs7Mtp3ItuProfileT15       Integer32,
        sonusSs7Mtp3ItuProfileT16       Integer32,
        sonusSs7Mtp3ItuProfileT17       Integer32,
        sonusSs7Mtp3ItuProfileT18       Integer32,
        sonusSs7Mtp3ItuProfileT19       Integer32,
        sonusSs7Mtp3ItuProfileT20       Integer32,
        sonusSs7Mtp3ItuProfileT21       Integer32,
        sonusSs7Mtp3ItuProfileT22       Integer32,
        sonusSs7Mtp3ItuProfileT23       Integer32,
        sonusSs7Mtp3ItuProfileT24       Integer32,
        sonusSs7Mtp3ItuProfileSltT1     Integer32,
        sonusSs7Mtp3ItuProfileSltT2     Integer32,
        sonusSs7Mtp3ItuProfileL2RespTimer Integer32
    }

sonusSs7Mtp3ItuProfileIndex OBJECT-TYPE
    SYNTAX          Integer32
    MAX-ACCESS      read-only
    STATUS          current
    DESCRIPTION     
            "Identifies the target SS7 Mtp3ItuProfile entry."
    ::= { sonusSs7Mtp3ItuProfileEntry 1 }

sonusSs7Mtp3ItuProfileName OBJECT-TYPE
    SYNTAX          SonusName
    MAX-ACCESS      read-write
    STATUS          current
    DESCRIPTION     
            "The name of this SS7 Mtp3ItuProfile instance."
    ::= { sonusSs7Mtp3ItuProfileEntry 2 }

sonusSs7Mtp3ItuProfileRowStatus OBJECT-TYPE
    SYNTAX          RowStatus
    MAX-ACCESS      read-write
    STATUS          current
    DESCRIPTION     
            ""
    ::= { sonusSs7Mtp3ItuProfileEntry 3 }

sonusSs7Mtp3ItuProfileT1 OBJECT-TYPE
    SYNTAX          Integer32 (500..1200)
    MAX-ACCESS      read-write
    STATUS          current
    DESCRIPTION     
            "MTP3 ITU T1 in millisecond -- delay to avoid message 
             mis-sequencing on changeover."
    DEFVAL          { 800 }
    ::= { sonusSs7Mtp3ItuProfileEntry 4 }

sonusSs7Mtp3ItuProfileT2 OBJECT-TYPE
    SYNTAX          Integer32 (700..2000)
    MAX-ACCESS      read-write
    STATUS          current
    DESCRIPTION     
            "MTP3 ITU T2 in millisecond -- waiting for changeover ack."
    DEFVAL          { 800 }
    ::= { sonusSs7Mtp3ItuProfileEntry 5 }

sonusSs7Mtp3ItuProfileT3 OBJECT-TYPE
    SYNTAX          Integer32 (500..1200)
    MAX-ACCESS      read-write
    STATUS          current
    DESCRIPTION     
            "MTP3 ITU T3 in millisecond -- time controlled diversion-delay
             to avoid mis-sequencing on changeback."
    DEFVAL          { 800 }
    ::= { sonusSs7Mtp3ItuProfileEntry 6 }

sonusSs7Mtp3ItuProfileT4 OBJECT-TYPE
    SYNTAX          Integer32 (500..1200)
    MAX-ACCESS      read-write
    STATUS          current
    DESCRIPTION     
            "MTP3 ITU T4 in millisecond -- waiting for changeback ack
             first attempt."
    DEFVAL          { 800 }
    ::= { sonusSs7Mtp3ItuProfileEntry 7 }

sonusSs7Mtp3ItuProfileT5 OBJECT-TYPE
    SYNTAX          Integer32 (500..1200)
    MAX-ACCESS      read-write
    STATUS          current
    DESCRIPTION     
            "MTP3 ITU T5 in millisecond -- waiting for changeback ack
             second attempt."
    DEFVAL          { 800 }
    ::= { sonusSs7Mtp3ItuProfileEntry 8 }

sonusSs7Mtp3ItuProfileT6 OBJECT-TYPE
    SYNTAX          Integer32 (500..1200)
    MAX-ACCESS      read-write
    STATUS          current
    DESCRIPTION     
            "MTP3 ITU T6 in millisecond -- delay to avoid message 
             mis-sequencing on controlled rerouting."
    DEFVAL          { 800 }
    ::= { sonusSs7Mtp3ItuProfileEntry 9 }

sonusSs7Mtp3ItuProfileT7 OBJECT-TYPE
    SYNTAX          Integer32 (1000..2000)
    MAX-ACCESS      read-write
    STATUS          current
    DESCRIPTION     
            "MTP3 ITU T7 in millisecond -- waiting for signaling data
             link connection ack."
    DEFVAL          { 1500 }
    ::= { sonusSs7Mtp3ItuProfileEntry 10 }

sonusSs7Mtp3ItuProfileT8 OBJECT-TYPE
    SYNTAX          Integer32 (800..1200)
    MAX-ACCESS      read-write
    STATUS          current
    DESCRIPTION     
            "MTP3 ITU T8 in millisecond -- transfer prohibited inhibition
             timer."
    DEFVAL          { 1000 }
    ::= { sonusSs7Mtp3ItuProfileEntry 11 }

sonusSs7Mtp3ItuProfileT10 OBJECT-TYPE
    SYNTAX          Integer32 (30000..60000)
    MAX-ACCESS      read-write
    STATUS          current
    DESCRIPTION     
            "MTP3 ITU T10 in millisecond -- waiting to repeat signaling
             route set test message."
    DEFVAL          { 40000 }
    ::= { sonusSs7Mtp3ItuProfileEntry 12 }

sonusSs7Mtp3ItuProfileT11 OBJECT-TYPE
    SYNTAX          Integer32 (30000..90000)
    MAX-ACCESS      read-write
    STATUS          current
    DESCRIPTION     
            "MTP3 ITU T11 in millisecond -- transfer restricted timer."
    DEFVAL          { 40000 }
    ::= { sonusSs7Mtp3ItuProfileEntry 13 }

sonusSs7Mtp3ItuProfileT12 OBJECT-TYPE
    SYNTAX          Integer32 (800..1500)
    MAX-ACCESS      read-write
    STATUS          current
    DESCRIPTION     
            "MTP3 ITU T12 in millisecond -- waiting for uninhibit ack."
    DEFVAL          { 1000 }
    ::= { sonusSs7Mtp3ItuProfileEntry 14 }

sonusSs7Mtp3ItuProfileT13 OBJECT-TYPE
    SYNTAX          Integer32 (800..1500)
    MAX-ACCESS      read-write
    STATUS          current
    DESCRIPTION     
            "MTP3 ITU T13 in millisecond -- waiting for force uninhibit."
    DEFVAL          { 1000 }
    ::= { sonusSs7Mtp3ItuProfileEntry 15 }

sonusSs7Mtp3ItuProfileT14 OBJECT-TYPE
    SYNTAX          Integer32 (2000..3000)
    MAX-ACCESS      read-write
    STATUS          current
    DESCRIPTION     
            "MTP3 ITU T14 in millisecond -- waiting for inhibition ack."
    DEFVAL          { 2500 }
    ::= { sonusSs7Mtp3ItuProfileEntry 16 }

sonusSs7Mtp3ItuProfileT15 OBJECT-TYPE
    SYNTAX          Integer32 (2000..3000)
    MAX-ACCESS      read-write
    STATUS          current
    DESCRIPTION     
            "MTP3 ITU T15 in millisecond -- waiting to start signaling 
             route set congestion test."
    DEFVAL          { 2500 }
    ::= { sonusSs7Mtp3ItuProfileEntry 17 }

sonusSs7Mtp3ItuProfileT16 OBJECT-TYPE
    SYNTAX          Integer32 (1400..2000)
    MAX-ACCESS      read-write
    STATUS          current
    DESCRIPTION     
            "MTP3 ITU T16 in millisecond -- waiting for route set 
             congestion status update."
    DEFVAL          { 1500 }
    ::= { sonusSs7Mtp3ItuProfileEntry 18 }

sonusSs7Mtp3ItuProfileT17 OBJECT-TYPE
    SYNTAX          Integer32 (800..1500)
    MAX-ACCESS      read-write
    STATUS          current
    DESCRIPTION     
            "MTP3 ITU T17 in millisecond -- delay to avoid oscillation of
             initial alignment failure and link restart."
    DEFVAL          { 1000 }
    ::= { sonusSs7Mtp3ItuProfileEntry 19 }

sonusSs7Mtp3ItuProfileT18 OBJECT-TYPE
    SYNTAX          Integer32 (15000..25000)
    MAX-ACCESS      read-write
    STATUS          current
    DESCRIPTION     
            "MTP3 ITU T18 in millisecond -- timer within within a 
             signalling point whose MTP restarts for supervising link and 
             link set activation as well as the receipt of routing 
             information."
    DEFVAL          { 20000 }
    ::= { sonusSs7Mtp3ItuProfileEntry 20 }

sonusSs7Mtp3ItuProfileT19 OBJECT-TYPE
    SYNTAX          Integer32 (67000..69000)
    MAX-ACCESS      read-write
    STATUS          current
    DESCRIPTION     
            "MTP3 ITU T19 in millisecond -- Supervision timer during 
             MTP restart to avoid possible ping-pong of TFP, TFR1 and TRA 
             messages."
    DEFVAL          { 68000 }
    ::= { sonusSs7Mtp3ItuProfileEntry 21 }

sonusSs7Mtp3ItuProfileT20 OBJECT-TYPE
    SYNTAX          Integer32 (59000..61000)
    MAX-ACCESS      read-write
    STATUS          current
    DESCRIPTION     
            "MTP3 ITU T20 in millisecond -- Overall MTP restart timer at 
             the signalling point whose MTP restarts."
    DEFVAL          { 60000 }
    ::= { sonusSs7Mtp3ItuProfileEntry 22 }

sonusSs7Mtp3ItuProfileT21 OBJECT-TYPE
    SYNTAX          Integer32 (63000..65000)
    MAX-ACCESS      read-write
    STATUS          current
    DESCRIPTION     
            "MTP3 ITU T21 in millisecond -- Overall MTP restart timer at 
             a signalling point adjacent to one whose MTP restarts."
    DEFVAL          { 64000 }
    ::= { sonusSs7Mtp3ItuProfileEntry 23 }

sonusSs7Mtp3ItuProfileT22 OBJECT-TYPE
    SYNTAX          Integer32 (180000..360000)
    MAX-ACCESS      read-write
    STATUS          current
    DESCRIPTION     
            "MTP3 ITU T22 in millisecond -- local inhibit test timer."
    DEFVAL          { 240000 }
    ::= { sonusSs7Mtp3ItuProfileEntry 24 }

sonusSs7Mtp3ItuProfileT23 OBJECT-TYPE
    SYNTAX          Integer32 (180000..360000)
    MAX-ACCESS      read-write
    STATUS          current
    DESCRIPTION     
            "MTP3 ITU T23 in millisecond -- remote inhibit test timer."
    DEFVAL          { 240000 }
    ::= { sonusSs7Mtp3ItuProfileEntry 25 }

sonusSs7Mtp3ItuProfileT24 OBJECT-TYPE
    SYNTAX          Integer32 (400..600)
    MAX-ACCESS      read-write
    STATUS          current
    DESCRIPTION     
            "MTP3 ITU T24 in millisecond -- stabilizing timer after 
             removal of local processor outage, used in LPO latching to 
             RPO."
    DEFVAL          { 500 }
    ::= { sonusSs7Mtp3ItuProfileEntry 26 }

sonusSs7Mtp3ItuProfileSltT1 OBJECT-TYPE
    SYNTAX          Integer32 (4000..12000)
    MAX-ACCESS      read-write
    STATUS          current
    DESCRIPTION     
            "ITU SLT T1 in millisecond -- supervision timer for signaling
             link test ack message."
    DEFVAL          { 5000 }
    ::= { sonusSs7Mtp3ItuProfileEntry 27 }

sonusSs7Mtp3ItuProfileSltT2 OBJECT-TYPE
    SYNTAX          Integer32 (30000..90000)
    MAX-ACCESS      read-write
    STATUS          current
    DESCRIPTION     
            "ITU SLT T2 in millisecond -- interval timer for sending
             signaling link test messages."
    DEFVAL          { 60000 }
    ::= { sonusSs7Mtp3ItuProfileEntry 28 }

sonusSs7Mtp3ItuProfileL2RespTimer OBJECT-TYPE
    SYNTAX          Integer32 (1000..1500)
    MAX-ACCESS      read-write
    STATUS          current
    DESCRIPTION     
            "ITU Layer 2 response in millisecond -- waiting for layer 2 
             response."
    DEFVAL          { 1000 }
    ::= { sonusSs7Mtp3ItuProfileEntry 29 }

sonusSs7Mtp3AnsiProfile OBJECT IDENTIFIER
    ::= { sonusSs7Mtp3MIBObjects 2 }

sonusSs7Mtp3AnsiProfileNextIndex OBJECT-TYPE
    SYNTAX          Integer32
    MAX-ACCESS      read-only
    STATUS          current
    DESCRIPTION     
            "The next valid index to use when creating an entry in
             the sonusSs7Mtp3AnsiProfileTable."
    ::= { sonusSs7Mtp3AnsiProfile 1 }

sonusSs7Mtp3AnsiProfileTable OBJECT-TYPE
    SYNTAX          SEQUENCE OF SonusSs7Mtp3AnsiProfileEntry
    MAX-ACCESS      not-accessible
    STATUS          current
    DESCRIPTION     
            "This table specifies MTP3 timers. "
    ::= { sonusSs7Mtp3AnsiProfile 2 }

sonusSs7Mtp3AnsiProfileEntry OBJECT-TYPE
    SYNTAX          SonusSs7Mtp3AnsiProfileEntry
    MAX-ACCESS      not-accessible
    STATUS          current
    DESCRIPTION     
            ""
    INDEX           { sonusSs7Mtp3AnsiProfileIndex }
    ::= { sonusSs7Mtp3AnsiProfileTable 1 }

SonusSs7Mtp3AnsiProfileEntry ::=
    SEQUENCE {
        sonusSs7Mtp3AnsiProfileIndex    Integer32,
        sonusSs7Mtp3AnsiProfileName     SonusName,
        sonusSs7Mtp3AnsiProfileRowStatus RowStatus,
        sonusSs7Mtp3AnsiProfileT1       Integer32,
        sonusSs7Mtp3AnsiProfileT2       Integer32,
        sonusSs7Mtp3AnsiProfileT3       Integer32,
        sonusSs7Mtp3AnsiProfileT4       Integer32,
        sonusSs7Mtp3AnsiProfileT5       Integer32,
        sonusSs7Mtp3AnsiProfileT6       Integer32,
        sonusSs7Mtp3AnsiProfileT7       Integer32,
        sonusSs7Mtp3AnsiProfileT8       Integer32,
        sonusSs7Mtp3AnsiProfileT10      Integer32,
        sonusSs7Mtp3AnsiProfileT11      Integer32,
        sonusSs7Mtp3AnsiProfileT12      Integer32,
        sonusSs7Mtp3AnsiProfileT13      Integer32,
        sonusSs7Mtp3AnsiProfileT14      Integer32,
        sonusSs7Mtp3AnsiProfileT15      Integer32,
        sonusSs7Mtp3AnsiProfileT16      Integer32,
        sonusSs7Mtp3AnsiProfileT17      Integer32,
        sonusSs7Mtp3AnsiProfileT18      Integer32,
        sonusSs7Mtp3AnsiProfileT19      Integer32,
        sonusSs7Mtp3AnsiProfileT20      Integer32,
        sonusSs7Mtp3AnsiProfileT21      Integer32,
        sonusSs7Mtp3AnsiProfileT22      Integer32,
        sonusSs7Mtp3AnsiProfileT23      Integer32,
        sonusSs7Mtp3AnsiProfileT24      Integer32,
        sonusSs7Mtp3AnsiProfileT25      Integer32,
        sonusSs7Mtp3AnsiProfileT26      Integer32,
        sonusSs7Mtp3AnsiProfileT27      Integer32,
        sonusSs7Mtp3AnsiProfileT28      Integer32,
        sonusSs7Mtp3AnsiProfileT29      Integer32,
        sonusSs7Mtp3AnsiProfileT30      Integer32,
        sonusSs7Mtp3AnsiProfileT31      Integer32,
        sonusSs7Mtp3AnsiProfileT32      Integer32,
        sonusSs7Mtp3AnsiProfileT33      Integer32,
        sonusSs7Mtp3AnsiProfileT34      Integer32,
        sonusSs7Mtp3AnsiProfileSltT1    Integer32,
        sonusSs7Mtp3AnsiProfileSltT2    Integer32,
        sonusSs7Mtp3AnsiProfileL2RespTimer  Integer32
    }

sonusSs7Mtp3AnsiProfileIndex OBJECT-TYPE
    SYNTAX          Integer32
    MAX-ACCESS      read-only
    STATUS          current
    DESCRIPTION     
            "Identifies the target SS7 Mtp3AnsiProfile entry."
    ::= { sonusSs7Mtp3AnsiProfileEntry 1 }

sonusSs7Mtp3AnsiProfileName OBJECT-TYPE
    SYNTAX          SonusName
    MAX-ACCESS      read-write
    STATUS          current
    DESCRIPTION     
            "The name of this SS7 Mtp3AnsiProfile instance."
    ::= { sonusSs7Mtp3AnsiProfileEntry 2 }

sonusSs7Mtp3AnsiProfileRowStatus OBJECT-TYPE
    SYNTAX          RowStatus
    MAX-ACCESS      read-write
    STATUS          current
    DESCRIPTION     
            ""
    ::= { sonusSs7Mtp3AnsiProfileEntry 3 }

sonusSs7Mtp3AnsiProfileT1 OBJECT-TYPE
    SYNTAX          Integer32 (500..1200)
    MAX-ACCESS      read-write
    STATUS          current
    DESCRIPTION     
            "MTP3 ANSI T1 in millisecond -- delay to avoid message 
             mis-sequencing on changeover."
    DEFVAL          { 800 }
    ::= { sonusSs7Mtp3AnsiProfileEntry 4 }

sonusSs7Mtp3AnsiProfileT2 OBJECT-TYPE
    SYNTAX          Integer32 (700..2000)
    MAX-ACCESS      read-write
    STATUS          current
    DESCRIPTION     
            "MTP3 ANSI T2 in millisecond -- waiting for changeover ack."
    DEFVAL          { 800 }
    ::= { sonusSs7Mtp3AnsiProfileEntry 5 }

sonusSs7Mtp3AnsiProfileT3 OBJECT-TYPE
    SYNTAX          Integer32 (500..1200)
    MAX-ACCESS      read-write
    STATUS          current
    DESCRIPTION     
            "MTP3 ANSI T3 in millisecond -- time controlled diversion-delay
             to avoid mis-sequencing on changeback."
    DEFVAL          { 800 }
    ::= { sonusSs7Mtp3AnsiProfileEntry 6 }

sonusSs7Mtp3AnsiProfileT4 OBJECT-TYPE
    SYNTAX          Integer32 (500..1200)
    MAX-ACCESS      read-write
    STATUS          current
    DESCRIPTION     
            "MTP3 ANSI T4 in millisecond -- waiting for changeback ack
             first attempt."
    DEFVAL          { 800 }
    ::= { sonusSs7Mtp3AnsiProfileEntry 7 }

sonusSs7Mtp3AnsiProfileT5 OBJECT-TYPE
    SYNTAX          Integer32 (500..1200)
    MAX-ACCESS      read-write
    STATUS          current
    DESCRIPTION     
            "MTP3 ANSI T5 in millisecond -- waiting for changeback ack
             second attempt."
    DEFVAL          { 800 }
    ::= { sonusSs7Mtp3AnsiProfileEntry 8 }

sonusSs7Mtp3AnsiProfileT6 OBJECT-TYPE
    SYNTAX          Integer32 (500..1200)
    MAX-ACCESS      read-write
    STATUS          current
    DESCRIPTION     
            "MTP3 ANSI T6 in millisecond -- delay to avoid message 
             mis-sequencing on controlled rerouting."
    DEFVAL          { 800 }
    ::= { sonusSs7Mtp3AnsiProfileEntry 9 }

sonusSs7Mtp3AnsiProfileT7 OBJECT-TYPE
    SYNTAX          Integer32 (1000..2000)
    MAX-ACCESS      read-write
    STATUS          current
    DESCRIPTION     
            "MTP3 ANSI T7 in millisecond -- waiting for signaling data
             link connection ack."
    DEFVAL          { 1500 }
    ::= { sonusSs7Mtp3AnsiProfileEntry 10 }

sonusSs7Mtp3AnsiProfileT8 OBJECT-TYPE
    SYNTAX          Integer32 (800..1200)
    MAX-ACCESS      read-write
    STATUS          current
    DESCRIPTION     
            "MTP3 ANSI T8 in millisecond -- transfer prohibited inhibition
             timer."
    DEFVAL          { 1000 }
    ::= { sonusSs7Mtp3AnsiProfileEntry 11 }

sonusSs7Mtp3AnsiProfileT10 OBJECT-TYPE
    SYNTAX          Integer32 (30000..60000)
    MAX-ACCESS      read-write
    STATUS          current
    DESCRIPTION     
            "MTP3 ANSI T10 in millisecond -- waiting to repeat signaling
             route set test message."
    DEFVAL          { 40000 }
    ::= { sonusSs7Mtp3AnsiProfileEntry 12 }

sonusSs7Mtp3AnsiProfileT11 OBJECT-TYPE
    SYNTAX          Integer32 (30000..90000)
    MAX-ACCESS      read-write
    STATUS          current
    DESCRIPTION     
            "MTP3 ANSI T11 in millisecond -- transfer restricted timer."
    DEFVAL          { 40000 }
    ::= { sonusSs7Mtp3AnsiProfileEntry 13 }

sonusSs7Mtp3AnsiProfileT12 OBJECT-TYPE
    SYNTAX          Integer32 (800..1500)
    MAX-ACCESS      read-write
    STATUS          current
    DESCRIPTION     
            "MTP3 ANSI T12 in millisecond -- waiting for uninhibit ack."
    DEFVAL          { 1000 }
    ::= { sonusSs7Mtp3AnsiProfileEntry 14 }

sonusSs7Mtp3AnsiProfileT13 OBJECT-TYPE
    SYNTAX          Integer32 (800..1500)
    MAX-ACCESS      read-write
    STATUS          current
    DESCRIPTION     
            "MTP3 ANSI T13 in millisecond -- waiting for force uninhibit."
    DEFVAL          { 1000 }
    ::= { sonusSs7Mtp3AnsiProfileEntry 15 }

sonusSs7Mtp3AnsiProfileT14 OBJECT-TYPE
    SYNTAX          Integer32 (2000..3000)
    MAX-ACCESS      read-write
    STATUS          current
    DESCRIPTION     
            "MTP3 ANSI T14 in millisecond -- waiting for inhibition ack."
    DEFVAL          { 2500 }
    ::= { sonusSs7Mtp3AnsiProfileEntry 16 }

sonusSs7Mtp3AnsiProfileT15 OBJECT-TYPE
    SYNTAX          Integer32 (2000..3000)
    MAX-ACCESS      read-write
    STATUS          current
    DESCRIPTION     
            "MTP3 ANSI T15 in millisecond -- waiting to start signaling 
             route set congestion test."
    DEFVAL          { 2500 }
    ::= { sonusSs7Mtp3AnsiProfileEntry 17 }

sonusSs7Mtp3AnsiProfileT16 OBJECT-TYPE
    SYNTAX          Integer32 (1400..2000)
    MAX-ACCESS      read-write
    STATUS          current
    DESCRIPTION     
            "MTP3 ANSI T16 in millisecond -- waiting for route set 
             congestion status update."
    DEFVAL          { 1500 }
    ::= { sonusSs7Mtp3AnsiProfileEntry 18 }

sonusSs7Mtp3AnsiProfileT17 OBJECT-TYPE
    SYNTAX          Integer32 (800..1500)
    MAX-ACCESS      read-write
    STATUS          current
    DESCRIPTION     
            "MTP3 ANSI T17 in millisecond -- delay to avoid oscillation of
             initial alignment failure and link restart."
    DEFVAL          { 1000 }
    ::= { sonusSs7Mtp3AnsiProfileEntry 19 }

sonusSs7Mtp3AnsiProfileT18 OBJECT-TYPE
    SYNTAX          Integer32 (2000..20000)
    MAX-ACCESS      read-write
    STATUS          current
    DESCRIPTION     
            "MTP3 ANSI T18 in millisecond -- repeat TFR once by response
             mode."
    DEFVAL          { 5000 }
    ::= { sonusSs7Mtp3AnsiProfileEntry 20 }

sonusSs7Mtp3AnsiProfileT19 OBJECT-TYPE
    SYNTAX          Integer32 (480000..600000)
    MAX-ACCESS      read-write
    STATUS          current
    DESCRIPTION     
            "MTP3 ANSI T19 in millisecond -- failed link craft referral 
             timer."
    DEFVAL          { 480000 }
    ::= { sonusSs7Mtp3AnsiProfileEntry 21 }

sonusSs7Mtp3AnsiProfileT20 OBJECT-TYPE
    SYNTAX          Integer32 (90000..120000)
    MAX-ACCESS      read-write
    STATUS          current
    DESCRIPTION     
            "MTP3 ANSI T20 in millisecond -- waiting to repeat local
             inhibit test."
    DEFVAL          { 90000 }
    ::= { sonusSs7Mtp3AnsiProfileEntry 22 }

sonusSs7Mtp3AnsiProfileT21 OBJECT-TYPE
    SYNTAX          Integer32 (90000..120000)
    MAX-ACCESS      read-write
    STATUS          current
    DESCRIPTION     
            "MTP3 ANSI T21 in millisecond -- waiting to repeat remote
             inhibit test."
    DEFVAL          { 90000 }
    ::= { sonusSs7Mtp3AnsiProfileEntry 23 }

sonusSs7Mtp3AnsiProfileT22 OBJECT-TYPE
    SYNTAX          Integer32 (15000..25000)
    MAX-ACCESS      read-write
    STATUS          current
    DESCRIPTION     
            "MTP3 ANSI T22 in millisecond -- timer at restarting SP
             waiting for signaling links to become available."
    DEFVAL          { 20000 }
    ::= { sonusSs7Mtp3AnsiProfileEntry 24 }

sonusSs7Mtp3AnsiProfileT23 OBJECT-TYPE
    SYNTAX          Integer32 (3000..5000)
    MAX-ACCESS      read-write
    STATUS          current
    DESCRIPTION     
            "MTP3 ANSI T23 in millisecond -- timer at restarting SP, started
             after T22, waiting to receive all traffic restart allowed
             messages."
    DEFVAL          { 4000 }
    ::= { sonusSs7Mtp3AnsiProfileEntry 25 }

sonusSs7Mtp3AnsiProfileT24 OBJECT-TYPE
    SYNTAX          Integer32 (3000..5000)
    MAX-ACCESS      read-write
    STATUS          current
    DESCRIPTION     
            "MTP3 ANSI T24 in millisecond -- timer at restarting SP with
             transfer function, started after T23, waiting to broadcast
             all traffic restart allowed messages."
    DEFVAL          { 4000 }
    ::= { sonusSs7Mtp3AnsiProfileEntry 26 }

sonusSs7Mtp3AnsiProfileT25 OBJECT-TYPE
    SYNTAX          Integer32 (30000..35000)
    MAX-ACCESS      read-write
    STATUS          current
    DESCRIPTION     
            "MTP3 ANSI T25 in millisecond -- timer at SP adjacent to 
             restarting SP waiting for traffic allowed message."
    DEFVAL          { 30000 }
    ::= { sonusSs7Mtp3AnsiProfileEntry 27 }

sonusSs7Mtp3AnsiProfileT26 OBJECT-TYPE
    SYNTAX          Integer32 (12000..15000)
    MAX-ACCESS      read-write
    STATUS          current
    DESCRIPTION     
            "MTP3 ANSI T26 in millisecond -- timer at restarting SP 
             waiting to repeat traffic restart waiting message."
    DEFVAL          { 12000 }
    ::= { sonusSs7Mtp3AnsiProfileEntry 28 }

sonusSs7Mtp3AnsiProfileT27 OBJECT-TYPE
    SYNTAX          Integer32 (2000..5000)
    MAX-ACCESS      read-write
    STATUS          current
    DESCRIPTION     
            "MTP3 ANSI T27 in millisecond -- minimum duration of 
             unavailability for full restart."
    DEFVAL          { 3000 }
    ::= { sonusSs7Mtp3AnsiProfileEntry 29 }

sonusSs7Mtp3AnsiProfileT28 OBJECT-TYPE
    SYNTAX          Integer32 (3000..35000)
    MAX-ACCESS      read-write
    STATUS          current
    DESCRIPTION     
            "MTP3 ANSI T28 in millisecond -- timer at SP adjacent to 
             restarting SP waiting for traffic restart waiting message."
    DEFVAL          { 5000 }
    ::= { sonusSs7Mtp3AnsiProfileEntry 30 }

sonusSs7Mtp3AnsiProfileT29 OBJECT-TYPE
    SYNTAX          Integer32 (60000..65000)
    MAX-ACCESS      read-write
    STATUS          current
    DESCRIPTION     
            "MTP3 ANSI T29 in millisecond -- timer started when TRA sent
             in response to unexpected TRA or TRW."
    DEFVAL          { 60000 }
    ::= { sonusSs7Mtp3AnsiProfileEntry 31 }

sonusSs7Mtp3AnsiProfileT30 OBJECT-TYPE
    SYNTAX          Integer32 (30000..35000)
    MAX-ACCESS      read-write
    STATUS          current
    DESCRIPTION     
            "MTP3 ANSI T30 in millisecond -- timer to limit sending of 
             TFPs and TFRs in response to unexpected TRA or TRW."
    DEFVAL          { 30000 }
    ::= { sonusSs7Mtp3AnsiProfileEntry 32 }

sonusSs7Mtp3AnsiProfileT31 OBJECT-TYPE
    SYNTAX          Integer32 (10000..120000)
    MAX-ACCESS      read-write
    STATUS          current
    DESCRIPTION     
            "MTP3 ANSI T31 in millisecond -- false link congestion detection
             timer."
    DEFVAL          { 30000 }
    ::= { sonusSs7Mtp3AnsiProfileEntry 33 }

sonusSs7Mtp3AnsiProfileT32 OBJECT-TYPE
    SYNTAX          Integer32 (5000..120000)
    MAX-ACCESS      read-write
    STATUS          current
    DESCRIPTION     
            "MTP3 ANSI T32 in millisecond -- link oscillation timer, 
             procedure A."
    DEFVAL          { 10000 }
    ::= { sonusSs7Mtp3AnsiProfileEntry 34 }

sonusSs7Mtp3AnsiProfileT33 OBJECT-TYPE
    SYNTAX          Integer32 (60000..600000)
    MAX-ACCESS      read-write
    STATUS          current
    DESCRIPTION     
            "MTP3 ANSI T33 in millisecond -- probation timer for link
             oscillation, procedure B."
    DEFVAL          { 60000 }
    ::= { sonusSs7Mtp3AnsiProfileEntry 35 }

sonusSs7Mtp3AnsiProfileT34 OBJECT-TYPE
    SYNTAX          Integer32 (5000..120000)
    MAX-ACCESS      read-write
    STATUS          current
    DESCRIPTION     
            "MTP3 ANSI T34 in millisecond -- suspension timer for
             link oscillation, procedure C."
    DEFVAL          { 30000 }
    ::= { sonusSs7Mtp3AnsiProfileEntry 36 }

sonusSs7Mtp3AnsiProfileSltT1 OBJECT-TYPE
    SYNTAX          Integer32 (4000..12000)
    MAX-ACCESS      read-write
    STATUS          current
    DESCRIPTION     
            "ANSI SLT T1 in millisecond -- supervision timer for signaling
             link test ack message."
    DEFVAL          { 5000 }
    ::= { sonusSs7Mtp3AnsiProfileEntry 37 }

sonusSs7Mtp3AnsiProfileSltT2 OBJECT-TYPE
    SYNTAX          Integer32 (30000..90000)
    MAX-ACCESS      read-write
    STATUS          current
    DESCRIPTION     
            "ANSI SLT T2 in millisecond -- interval timer for sending
             signaling link test messages."
    DEFVAL          { 60000 }
    ::= { sonusSs7Mtp3AnsiProfileEntry 38 }

sonusSs7Mtp3AnsiProfileL2RespTimer OBJECT-TYPE
    SYNTAX          Integer32 (1000..1500)
    MAX-ACCESS      read-write
    STATUS          current
    DESCRIPTION     
            "ANSI Layer 2 response in millisecond -- waiting for layer 2 
             response."
    DEFVAL          { 1000 }
    ::= { sonusSs7Mtp3AnsiProfileEntry 39 }

sonusSs7Destination OBJECT IDENTIFIER
    ::= { sonusSs7Mtp3MIBObjects 3 }

sonusSs7DestinationNextIndex OBJECT-TYPE
    SYNTAX          Integer32
    MAX-ACCESS      read-only
    STATUS          current
    DESCRIPTION     
            "The next valid index to use when creating an entry in
             the sonusSs7DestinationTable."
    ::= { sonusSs7Destination 1 }

sonusSs7DestinationTable OBJECT-TYPE
    SYNTAX          SEQUENCE OF SonusSs7DestinationEntry
    MAX-ACCESS      not-accessible
    STATUS          current
    DESCRIPTION     
            "This table specifies an MTP3 destination."
    ::= { sonusSs7Destination 2 }

sonusSs7DestinationEntry OBJECT-TYPE
    SYNTAX          SonusSs7DestinationEntry
    MAX-ACCESS      not-accessible
    STATUS          current
    DESCRIPTION     
            ""
    INDEX           { sonusSs7DestinationIndex }
    ::= { sonusSs7DestinationTable 1 }

SonusSs7DestinationEntry ::=
    SEQUENCE {
        sonusSs7DestinationIndex        Integer32,
        sonusSs7DestinationName         SonusName,
        sonusSs7DestinationRowStatus    RowStatus,
        sonusSs7DestinationType         INTEGER,
        sonusSs7DestinationPcInFormat   SonusPointCode,
        sonusSs7DestinationPcInBinary   Integer32,
        sonusSs7DestinationNodeIndex    Integer32,
        sonusSs7DestinationMgmtIndex    Integer32
    }

sonusSs7DestinationIndex OBJECT-TYPE
    SYNTAX          Integer32
    MAX-ACCESS      read-only
    STATUS          current
    DESCRIPTION     
            "Identifies the target SS7 Destination entry."
    ::= { sonusSs7DestinationEntry 1 }

sonusSs7DestinationName OBJECT-TYPE
    SYNTAX          SonusName
    MAX-ACCESS      read-write
    STATUS          current
    DESCRIPTION     
            "The name of this SS7 Destination instance."
    ::= { sonusSs7DestinationEntry 2 }

sonusSs7DestinationRowStatus OBJECT-TYPE
    SYNTAX          RowStatus
    MAX-ACCESS      read-write
    STATUS          current
    DESCRIPTION     
            ""
    ::= { sonusSs7DestinationEntry 3 }

sonusSs7DestinationType OBJECT-TYPE
    SYNTAX          INTEGER { adjacent(0), remote(1), cluster(2) }
    MAX-ACCESS      read-write
    STATUS          current
    DESCRIPTION     
            "To designate the destination as an adjacent node, a 
             remote node, or a (remote) cluster. Note that a cluster is
             valid for ANSI only."
    ::= { sonusSs7DestinationEntry 4 }

sonusSs7DestinationPcInFormat OBJECT-TYPE
    SYNTAX          SonusPointCode
    MAX-ACCESS      read-write
    STATUS          current
    DESCRIPTION     
            "The point code value in the format as specifed."
    ::= { sonusSs7DestinationEntry 5 }

sonusSs7DestinationPcInBinary OBJECT-TYPE
    SYNTAX          Integer32
    MAX-ACCESS      read-only
    STATUS          current
    DESCRIPTION     
            "The point code in binary."
    ::= { sonusSs7DestinationEntry 6 }

sonusSs7DestinationNodeIndex OBJECT-TYPE
    SYNTAX          Integer32
    MAX-ACCESS      read-write
    STATUS          current
    DESCRIPTION     
            "The index of the SS7 node with which this SS7 destination
             has signaling relationship."
    ::= { sonusSs7DestinationEntry 7 }

sonusSs7DestinationMgmtIndex OBJECT-TYPE
    SYNTAX          Integer32
    MAX-ACCESS      read-write
    STATUS          current
    DESCRIPTION     
            "The index of the SS7 MTP3 MGMT with which this SS7 destination
             is associated."
    ::= { sonusSs7DestinationEntry 8 }

sonusSs7DestinationStatusTable OBJECT-TYPE
    SYNTAX          SEQUENCE OF SonusSs7DestinationStatusEntry
    MAX-ACCESS      not-accessible
    STATUS          current
    DESCRIPTION     
            "Status Table of the SS7 destination for the GSX9000 node."
    ::= { sonusSs7Destination 3 }

sonusSs7DestinationStatusEntry OBJECT-TYPE
    SYNTAX          SonusSs7DestinationStatusEntry
    MAX-ACCESS      not-accessible
    STATUS          current
    DESCRIPTION     
            "List of SS7 destination status elements."
    INDEX           { sonusSs7DestinationStatusIndex }
    ::= { sonusSs7DestinationStatusTable 1 }

SonusSs7DestinationStatusEntry ::=
    SEQUENCE {
        sonusSs7DestinationStatusIndex  Integer32,
        sonusSs7DestinationState        INTEGER,
        sonusSs7DestinationCongLevel    Integer32,
        sonusSs7DestinationDiscardLevel Integer32,
        sonusSs7DestinationMsuDiscRouting Unsigned32,
        sonusSs7DestinationMsuDiscCongested   Unsigned32,
        sonusSs7DestinationInaccTimes   Integer32,
        sonusSs7DestinationInaccStartTime Unsigned32,
        sonusSs7DestinationInaccStopTime Unsigned32,
        sonusSs7DestinationInaccDuration Unsigned32
    }

sonusSs7DestinationStatusIndex OBJECT-TYPE
    SYNTAX          Integer32
    MAX-ACCESS      read-only
    STATUS          current
    DESCRIPTION     
            "Identifies the SS7 destination status entry."
    ::= { sonusSs7DestinationStatusEntry 1 }

sonusSs7DestinationState OBJECT-TYPE
    SYNTAX          INTEGER { accessible(0), restart(1), congested(2), 
                        inaccessible(3), restricted(4), unconfigured(5), 
                        init(6) }
    MAX-ACCESS      read-only
    STATUS          current
    DESCRIPTION     
            "The current state of the specified SS7 destination."
    DEFVAL          { inaccessible }
    ::= { sonusSs7DestinationStatusEntry 2 }

sonusSs7DestinationCongLevel OBJECT-TYPE
    SYNTAX          Integer32 (0..3)
    MAX-ACCESS      read-only
    STATUS          current
    DESCRIPTION     
            "The congestion level of the SS7 destination."
    DEFVAL          { 0 }
    ::= { sonusSs7DestinationStatusEntry 3 }

sonusSs7DestinationDiscardLevel OBJECT-TYPE
    SYNTAX          Integer32 (0..3)
    MAX-ACCESS      read-only
    STATUS          current
    DESCRIPTION     
            "The discard level of the SS7 destination."
    DEFVAL          { 0 }
    ::= { sonusSs7DestinationStatusEntry 4 }

sonusSs7DestinationMsuDiscRouting OBJECT-TYPE
    SYNTAX          Unsigned32 (0..4294967295)
    MAX-ACCESS      read-only
    STATUS          current
    DESCRIPTION     
            "The number of MSUs that have been discarded over the
             measured interval as a result of routing error -- a 
             Q.752 statistics item."
    DEFVAL          { 0 }
    ::= { sonusSs7DestinationStatusEntry 5 }

sonusSs7DestinationMsuDiscCongested OBJECT-TYPE
    SYNTAX          Unsigned32 (0..4294967295)
    MAX-ACCESS      read-only
    STATUS          current
    DESCRIPTION     
            "The number of MSUs that have been discarded over the
             measured interval as a result of destinatioin congestion 
             -- a Q.752 statistics item."
    DEFVAL          { 0 }
    ::= { sonusSs7DestinationStatusEntry 6 }

sonusSs7DestinationInaccTimes OBJECT-TYPE
    SYNTAX          Integer32 (0..65535)
    MAX-ACCESS      read-only
    STATUS          current
    DESCRIPTION     
            "The number of times that the destination has become 
             inaccessible over the measured interval -- a Q.752 
             statistics item."
    DEFVAL          { 0 }
    ::= { sonusSs7DestinationStatusEntry 7 }

sonusSs7DestinationInaccStartTime OBJECT-TYPE
    SYNTAX          Unsigned32 (0..4294967295)
    MAX-ACCESS      read-only
    STATUS          current
    DESCRIPTION     
            "The start time at which the destination became 
             inaccessible -- a Q.752 statistics item."
    DEFVAL          { 0 }
    ::= { sonusSs7DestinationStatusEntry 8 }

sonusSs7DestinationInaccStopTime OBJECT-TYPE
    SYNTAX          Unsigned32 (0..4294967295)
    MAX-ACCESS      read-only
    STATUS          current
    DESCRIPTION     
            "The stop time at which the destination became 
             inaccessible -- a Q.752 statistics item."
    DEFVAL          { 0 }
    ::= { sonusSs7DestinationStatusEntry 9 }

sonusSs7DestinationInaccDuration OBJECT-TYPE
    SYNTAX          Unsigned32 (0..4294967295)
    MAX-ACCESS      read-only
    STATUS          current
    DESCRIPTION     
            "The duration during which the destination remained 
             inaccessible -- a Q.752 statistics item."
    DEFVAL          { 0 }
    ::= { sonusSs7DestinationStatusEntry 10 }

sonusSs7Link OBJECT IDENTIFIER
    ::= { sonusSs7Mtp3MIBObjects 4 }

sonusSs7LinkNextIndex OBJECT-TYPE
    SYNTAX          Integer32
    MAX-ACCESS      read-only
    STATUS          current
    DESCRIPTION     
            "The next valid index to use when creating an entry in
             the sonusSs7LinkTable."
    ::= { sonusSs7Link 1 }

sonusSs7LinkTable OBJECT-TYPE
    SYNTAX          SEQUENCE OF SonusSs7LinkEntry
    MAX-ACCESS      not-accessible
    STATUS          current
    DESCRIPTION     
            "This table specifies an SS7 link."
    ::= { sonusSs7Link 2 }

sonusSs7LinkEntry OBJECT-TYPE
    SYNTAX          SonusSs7LinkEntry
    MAX-ACCESS      not-accessible
    STATUS          current
    DESCRIPTION     
            ""
    INDEX           { sonusSs7LinkIndex }
    ::= { sonusSs7LinkTable 1 }

SonusSs7LinkEntry ::=
    SEQUENCE {
        sonusSs7LinkIndex               Integer32,
        sonusSs7LinkName                SonusName,
        sonusSs7LinkRowStatus           RowStatus,
        sonusSs7LinkActivationMode      INTEGER,
        sonusSs7LinkType                INTEGER,
        sonusSs7LinkSlc                 Integer32,
        sonusSs7LinkSltMode             INTEGER,
        sonusSs7LinkBlockMode           INTEGER,
        sonusSs7LinkInhibitMode         INTEGER,
        sonusSs7LinkNodeIndex           Integer32,
        sonusSs7LinkDestinationIndex    Integer32,
        sonusSs7LinkLayer2Name          SonusNameReference,
        sonusSs7LinkLayer2Id            Integer32,
        sonusSs7LinkLayer2LinkId        Integer32
    }

sonusSs7LinkIndex OBJECT-TYPE
    SYNTAX          Integer32
    MAX-ACCESS      read-only
    STATUS          current
    DESCRIPTION     
            "The index of the SS7 link entry."
    ::= { sonusSs7LinkEntry 1 }

sonusSs7LinkName OBJECT-TYPE
    SYNTAX          SonusName
    MAX-ACCESS      read-write
    STATUS          current
    DESCRIPTION     
            "The name of the SS7 link."
    ::= { sonusSs7LinkEntry 2 }

sonusSs7LinkRowStatus OBJECT-TYPE
    SYNTAX          RowStatus
    MAX-ACCESS      read-write
    STATUS          current
    DESCRIPTION     
            ""
    ::= { sonusSs7LinkEntry 3 }

sonusSs7LinkActivationMode OBJECT-TYPE
    SYNTAX          INTEGER { deactivate(0), normal(1), emergency(2) }
    MAX-ACCESS      read-write
    STATUS          current
    DESCRIPTION     
            "The activation mode of the SS7 link.  The link can 
             be deactivated, activated in normal or emergency mode."
    DEFVAL          { normal }
    ::= { sonusSs7LinkEntry 4 }

sonusSs7LinkType OBJECT-TYPE
    SYNTAX          INTEGER { f(0), a(1), e(2) }
    MAX-ACCESS      read-write
    STATUS          current
    DESCRIPTION     
            "The type of the SS7 link."
    ::= { sonusSs7LinkEntry 5 }

sonusSs7LinkSlc OBJECT-TYPE
    SYNTAX          Integer32 (0..15)
    MAX-ACCESS      read-write
    STATUS          current
    DESCRIPTION     
            "The SLC assignment of the SS7 link."
    ::= { sonusSs7LinkEntry 6 }

sonusSs7LinkSltMode OBJECT-TYPE
    SYNTAX          INTEGER { single(0), periodic(1), off(2) }
    MAX-ACCESS      read-write
    STATUS          current
    DESCRIPTION     
            "The SLT test mode of the SS7 link:
             When set to single, a single SLTM message will be sent.
             When sest to periodic, SLTM messages will be sent periodically.
             Off is used to stop on going periodic SLT."
    ::= { sonusSs7LinkEntry 7 }

sonusSs7LinkBlockMode OBJECT-TYPE
    SYNTAX          INTEGER { off(0), on(1) }
    MAX-ACCESS      read-write
    STATUS          current
    DESCRIPTION     
            "The block mode of the SS7 link."
    ::= { sonusSs7LinkEntry 8 }

sonusSs7LinkInhibitMode OBJECT-TYPE
    SYNTAX          INTEGER { off(0), on(1) }
    MAX-ACCESS      read-write
    STATUS          current
    DESCRIPTION     
            "The inhibit mode of the SS7 link."
    ::= { sonusSs7LinkEntry 9 }

sonusSs7LinkNodeIndex OBJECT-TYPE
    SYNTAX          Integer32
    MAX-ACCESS      read-write
    STATUS          current
    DESCRIPTION     
            "The index of the SS7 node on which this SS7 link terminates."
    ::= { sonusSs7LinkEntry 10 }

sonusSs7LinkDestinationIndex OBJECT-TYPE
    SYNTAX          Integer32
    MAX-ACCESS      read-write
    STATUS          current
    DESCRIPTION     
            "The index of the far end SS7 node on which this SS7 link 
             terminates."
    ::= { sonusSs7LinkEntry 11 }

sonusSs7LinkLayer2Name OBJECT-TYPE
    SYNTAX          SonusNameReference
    MAX-ACCESS      read-write
    STATUS          current
    DESCRIPTION     
            "The Layer2 name of this SS7 link."
    ::= { sonusSs7LinkEntry 12 }

sonusSs7LinkLayer2Id OBJECT-TYPE
    SYNTAX          Integer32
    MAX-ACCESS      read-only
    STATUS          current
    DESCRIPTION     
            "The layer2 id."
    ::= { sonusSs7LinkEntry 13 }

sonusSs7LinkLayer2LinkId OBJECT-TYPE
    SYNTAX          Integer32
    MAX-ACCESS      read-only
    STATUS          current
    DESCRIPTION     
            "The layer2 logical link id."
    ::= { sonusSs7LinkEntry 14 }

sonusSs7LinkStatusTable OBJECT-TYPE
    SYNTAX          SEQUENCE OF SonusSs7LinkStatusEntry
    MAX-ACCESS      not-accessible
    STATUS          current
    DESCRIPTION     
            "Status Table of the SS7 link for the GSX9000 node."
    ::= { sonusSs7Link 3 }

sonusSs7LinkStatusEntry OBJECT-TYPE
    SYNTAX          SonusSs7LinkStatusEntry
    MAX-ACCESS      not-accessible
    STATUS          current
    DESCRIPTION     
            "SS7 link entry."
    INDEX           { sonusSs7LinkStatusIndex }
    ::= { sonusSs7LinkStatusTable 1 }

SonusSs7LinkStatusEntry ::=
    SEQUENCE {
        sonusSs7LinkStatusIndex         Integer32,
        sonusSs7LinkState               BITS,
        sonusSs7LinkReceivedSio         Unsigned32,
        sonusSs7LinkReceivedSif         Unsigned32,
        sonusSs7LinkTransmittedSio      Unsigned32,
        sonusSs7LinkTransmittedSif      Unsigned32,
        sonusSs7LinkUnavlStartTime      Unsigned32,
        sonusSs7LinkUnavlStopTime       Unsigned32,
        sonusSs7LinkUnavlDuration       Unsigned32,
        sonusSs7LinkActivationStatus    INTEGER,
        sonusSs7LinkPeriodicSltStatus   INTEGER,
        sonusSs7LinkCongestionLevel     Integer32,
        sonusSs7LinkDiscardLevel        Integer32,
        sonusSs7LinkSuccessiveRestorationAttempts         Integer32,
        sonusSs7LinkSuccessiveSltTests  Integer32
    }

sonusSs7LinkStatusIndex OBJECT-TYPE
    SYNTAX          Integer32
    MAX-ACCESS      read-only
    STATUS          current
    DESCRIPTION     
            "The index of the SS7 link."
    ::= { sonusSs7LinkStatusEntry 1 }

sonusSs7LinkState OBJECT-TYPE
    SYNTAX          BITS { unavl(0), reserved1(1), reserved2(2), 
                        reserved3(3), reserved4(4), reserved5(5), 
                        reserved6(6), reserved7(7), reserved8(8), 
                        reserved9(9), forceUninhInProg(10), 
                        coTimeCtrlPending(11), coEmrgPending(12), 
                        coNormPending(13), coPending(14), 
                        coTimeCtrlInProg(15), coEmrgInProg(16), 
                        coNormInProg(17), coInProg(18), 
                        cbTimeCtrlPending(19), cbSeqCtrlPending(20), 
                        cbPending(21), cbTimeCtrlInProg(22), 
                        cbSeqCtrlInProg(23), cbInProg(24), 
                        localUninhInProg(25), localInhInProg(26), 
                        linh(27), rinh(28), lblk(29), rblk(30), 
                        l2oos(31) }
    MAX-ACCESS      read-only
    STATUS          current
    DESCRIPTION     
            "The current state of the SS7 link:
             unavl(0),				Link unavailable
             forceUninhInProg(10),	Forced uninhibit in progress,
             coTimeCtrlPending(11),	Changeover in time control mode pending,
             coEmrgPending(12),		Changeover in emergency mode pending,
             coNormPending(13),		Changeover in normal mode pending,
             coPending(14),			Changeover pending,
             coTimeCtrlInProg(15),	Changeover in time control mode in progress,
             coEmgyInProg(16),		Changeover in emergency mode in progress,
             coNormInProg(17),		Changeover in normal mode in progress, 
             coInProg(18),			Changeover in progress,
             cbTimeCtrlPending(19),	Changeback in time control mode pending,
             cbSeqCtrlPending(20),	Changeback in sequence control mode pending,
             cbPending(21),			Changeback pending,
             cbTimeCtrlInProg(22),	Changeback in time control mode in progress,
             cbSeqCtrlInProg(23),	Changeback in sequence control mode in progress,
             cbInProg(24),			Changeback in progress,
             localUninhInProg(25),	Local un-inhibit in progress,
             localInhInProg(26),		Local inhibit in progress,
             linh(27),				Local inhibited,
             rinh(28),				Remote inhibited,
             lblk(29),				Local blocked,
             rblk(30),				Remote blocked,
             l2oos(31),				Layer 2 out of service"
    ::= { sonusSs7LinkStatusEntry 2 }

sonusSs7LinkReceivedSio OBJECT-TYPE
    SYNTAX          Unsigned32 (0..4294967295)
    MAX-ACCESS      read-only
    STATUS          current
    DESCRIPTION     
            "The number of SIOs received on this link over the 
             measured interval -- a Q.752 statistics item."
    DEFVAL          { 0 }
    ::= { sonusSs7LinkStatusEntry 3 }

sonusSs7LinkReceivedSif OBJECT-TYPE
    SYNTAX          Unsigned32 (0..4294967295)
    MAX-ACCESS      read-only
    STATUS          current
    DESCRIPTION     
            "The number of SIF bytes received on this link over the 
             measured interval -- a Q.752 statistics item."
    DEFVAL          { 0 }
    ::= { sonusSs7LinkStatusEntry 4 }

sonusSs7LinkTransmittedSio OBJECT-TYPE
    SYNTAX          Unsigned32 (0..4294967295)
    MAX-ACCESS      read-only
    STATUS          current
    DESCRIPTION     
            "The number of SIOs transmitted on this link over the 
             measured interval -- a Q.752 statistics item."
    DEFVAL          { 0 }
    ::= { sonusSs7LinkStatusEntry 5 }

sonusSs7LinkTransmittedSif OBJECT-TYPE
    SYNTAX          Unsigned32 (0..4294967295)
    MAX-ACCESS      read-only
    STATUS          current
    DESCRIPTION     
            "The number of SIF bytes transmitted on this link over the 
             measured interval -- a Q.752 statistics item."
    DEFVAL          { 0 }
    ::= { sonusSs7LinkStatusEntry 6 }

sonusSs7LinkUnavlStartTime OBJECT-TYPE
    SYNTAX          Unsigned32 (0..4294967295)
    MAX-ACCESS      read-only
    STATUS          current
    DESCRIPTION     
            "The start time at which the link became unavailable
             -- a Q.752 statistics item."
    DEFVAL          { 0 }
    ::= { sonusSs7LinkStatusEntry 7 }

sonusSs7LinkUnavlStopTime OBJECT-TYPE
    SYNTAX          Unsigned32 (0..4294967295)
    MAX-ACCESS      read-only
    STATUS          current
    DESCRIPTION     
            "The stop time at which the link became unavailable
             -- a Q.752 statistics item."
    DEFVAL          { 0 }
    ::= { sonusSs7LinkStatusEntry 8 }

sonusSs7LinkUnavlDuration OBJECT-TYPE
    SYNTAX          Unsigned32 (0..4294967295)
    MAX-ACCESS      read-only
    STATUS          current
    DESCRIPTION     
            "The duration during which the link remained unavailable
             -- a Q.752 statistics item."
    DEFVAL          { 0 }
    ::= { sonusSs7LinkStatusEntry 9 }

sonusSs7LinkActivationStatus OBJECT-TYPE
    SYNTAX          INTEGER { activated(0), deactivated(1) }
    MAX-ACCESS      read-only
    STATUS          current
    DESCRIPTION     
            "The current activation/deactivation status of the link.
             Note that a link can be activated/deactivated by the link
             or its belongling linkset."
    ::= { sonusSs7LinkStatusEntry 10 }

sonusSs7LinkPeriodicSltStatus OBJECT-TYPE
    SYNTAX          INTEGER { on(0), off(1) }
    MAX-ACCESS      read-only
    STATUS          current
    DESCRIPTION     
            "The current periodic SLT status of the link."
    ::= { sonusSs7LinkStatusEntry 11 }

sonusSs7LinkCongestionLevel OBJECT-TYPE
    SYNTAX          Integer32 (0..3)
    MAX-ACCESS      read-only
    STATUS          current
    DESCRIPTION     
            "The current congestion level of the link."
    DEFVAL          { 0 }
    ::= { sonusSs7LinkStatusEntry 12 }

sonusSs7LinkDiscardLevel OBJECT-TYPE
    SYNTAX          Integer32 (0..3)
    MAX-ACCESS      read-only
    STATUS          current
    DESCRIPTION     
            "The current discard level of the link."
    DEFVAL          { 0 }
    ::= { sonusSs7LinkStatusEntry 13 }

sonusSs7LinkSuccessiveRestorationAttempts OBJECT-TYPE
    SYNTAX          Integer32 (0..255)
    MAX-ACCESS      read-only
    STATUS          current
    DESCRIPTION     
            "The successive restoration attempts the link has performed
             since the link became unavailble."
    DEFVAL          { 0 }
    ::= { sonusSs7LinkStatusEntry 14 }

sonusSs7LinkSuccessiveSltTests OBJECT-TYPE
    SYNTAX          Integer32 (0..255)
    MAX-ACCESS      read-only
    STATUS          current
    DESCRIPTION     
            "The successive SLTM/SLTA tests the link has performed in
             either bringing the link to the available state, or 
             executing the periodic SLTs."
    DEFVAL          { 0 }
    ::= { sonusSs7LinkStatusEntry 15 }

sonusSs7Linkset OBJECT IDENTIFIER
    ::= { sonusSs7Mtp3MIBObjects 5 }

sonusSs7LinksetNextIndex OBJECT-TYPE
    SYNTAX          Integer32
    MAX-ACCESS      read-only
    STATUS          current
    DESCRIPTION     
            "The next valid index to use when creating an entry in
             the sonusSs7LinksetTable."
    ::= { sonusSs7Linkset 1 }

sonusSs7LinksetTable OBJECT-TYPE
    SYNTAX          SEQUENCE OF SonusSs7LinksetEntry
    MAX-ACCESS      not-accessible
    STATUS          current
    DESCRIPTION     
            "This table specifies an SS7 linkset."
    ::= { sonusSs7Linkset 2 }

sonusSs7LinksetEntry OBJECT-TYPE
    SYNTAX          SonusSs7LinksetEntry
    MAX-ACCESS      not-accessible
    STATUS          current
    DESCRIPTION     
            ""
    INDEX           { sonusSs7LinksetIndex }
    ::= { sonusSs7LinksetTable 1 }

SonusSs7LinksetEntry ::=
    SEQUENCE {
        sonusSs7LinksetIndex            Integer32,
        sonusSs7LinksetName             SonusName,
        sonusSs7LinksetRowStatus        RowStatus,
        sonusSs7LinksetActivationMode   INTEGER,
        sonusSs7LinksetNodeIndex        Integer32,
        sonusSs7LinksetDestinationIndex Integer32
    }

sonusSs7LinksetIndex OBJECT-TYPE
    SYNTAX          Integer32
    MAX-ACCESS      read-only
    STATUS          current
    DESCRIPTION     
            "The index of the SS7 linkset entry."
    ::= { sonusSs7LinksetEntry 1 }

sonusSs7LinksetName OBJECT-TYPE
    SYNTAX          SonusName
    MAX-ACCESS      read-write
    STATUS          current
    DESCRIPTION     
            "The name of the SS7 linkset."
    ::= { sonusSs7LinksetEntry 2 }

sonusSs7LinksetRowStatus OBJECT-TYPE
    SYNTAX          RowStatus
    MAX-ACCESS      read-write
    STATUS          current
    DESCRIPTION     
            ""
    ::= { sonusSs7LinksetEntry 3 }

sonusSs7LinksetActivationMode OBJECT-TYPE
    SYNTAX          INTEGER { deactivate(0), normal(1), emergency(2) }
    MAX-ACCESS      read-write
    STATUS          current
    DESCRIPTION     
            "The activation mode of the SS7 linkset.  The linkset 
             can be deactivated, activated in normal or emergency mode."
    DEFVAL          { normal }
    ::= { sonusSs7LinksetEntry 4 }

sonusSs7LinksetNodeIndex OBJECT-TYPE
    SYNTAX          Integer32
    MAX-ACCESS      read-write
    STATUS          current
    DESCRIPTION     
            "The index of the SS7 node on which this SS7 linkset 
             terminates."
    ::= { sonusSs7LinksetEntry 5 }

sonusSs7LinksetDestinationIndex OBJECT-TYPE
    SYNTAX          Integer32
    MAX-ACCESS      read-write
    STATUS          current
    DESCRIPTION     
            "The index of the far end SS7 node on which this SS7 
             linkset terminates."
    ::= { sonusSs7LinksetEntry 6 }

sonusSs7Route OBJECT IDENTIFIER
    ::= { sonusSs7Mtp3MIBObjects 6 }

sonusSs7RouteNextIndex OBJECT-TYPE
    SYNTAX          Integer32
    MAX-ACCESS      read-only
    STATUS          current
    DESCRIPTION     
            "The next valid index to use when creating an entry in
             the sonusSs7RouteTable."
    ::= { sonusSs7Route 1 }

sonusSs7RouteTable OBJECT-TYPE
    SYNTAX          SEQUENCE OF SonusSs7RouteEntry
    MAX-ACCESS      not-accessible
    STATUS          current
    DESCRIPTION     
            "This table specifies an SS7 route."
    ::= { sonusSs7Route 2 }

sonusSs7RouteEntry OBJECT-TYPE
    SYNTAX          SonusSs7RouteEntry
    MAX-ACCESS      not-accessible
    STATUS          current
    DESCRIPTION     
            ""
    INDEX           { sonusSs7RouteIndex }
    ::= { sonusSs7RouteTable 1 }

SonusSs7RouteEntry ::=
    SEQUENCE {
        sonusSs7RouteIndex              Integer32,
        sonusSs7RouteName               SonusName,
        sonusSs7RouteRowStatus          RowStatus,
        sonusSs7RouteType               INTEGER,
        sonusSs7RoutePriority           Integer32,
        sonusSs7RouteNodeIndex          Integer32,
        sonusSs7RouteDestinationIndex   Integer32,
        sonusSs7RouteLinksetIndex       Integer32
    }

sonusSs7RouteIndex OBJECT-TYPE
    SYNTAX          Integer32
    MAX-ACCESS      read-only
    STATUS          current
    DESCRIPTION     
            "The index of the SS7 route entry."
    ::= { sonusSs7RouteEntry 1 }

sonusSs7RouteName OBJECT-TYPE
    SYNTAX          SonusName
    MAX-ACCESS      read-write
    STATUS          current
    DESCRIPTION     
            "The name of the SS7 route."
    ::= { sonusSs7RouteEntry 2 }

sonusSs7RouteRowStatus OBJECT-TYPE
    SYNTAX          RowStatus
    MAX-ACCESS      read-write
    STATUS          current
    DESCRIPTION     
            ""
    ::= { sonusSs7RouteEntry 3 }

sonusSs7RouteType OBJECT-TYPE
    SYNTAX          INTEGER { direct(0), indirect(1), cluster(2) }
    MAX-ACCESS      read-write
    STATUS          current
    DESCRIPTION     
            "To designate the route as a direct route to an adjacent
             node, an indirect route to a remote node, or a cluster
             route to a (remote) cluster. Note that a cluster is
             valid for ANSI only."
    ::= { sonusSs7RouteEntry 4 }

sonusSs7RoutePriority OBJECT-TYPE
    SYNTAX          Integer32 (0..3)
    MAX-ACCESS      read-write
    STATUS          current
    DESCRIPTION     
            "The priority of the SS7 route."
    ::= { sonusSs7RouteEntry 5 }

sonusSs7RouteNodeIndex OBJECT-TYPE
    SYNTAX          Integer32
    MAX-ACCESS      read-write
    STATUS          current
    DESCRIPTION     
            "The index of the SS7 node on which this SS7 route terminates."
    ::= { sonusSs7RouteEntry 6 }

sonusSs7RouteDestinationIndex OBJECT-TYPE
    SYNTAX          Integer32
    MAX-ACCESS      read-write
    STATUS          current
    DESCRIPTION     
            "The index of the far end SS7 node to which this SS7 route 
             leads."
    ::= { sonusSs7RouteEntry 7 }

sonusSs7RouteLinksetIndex OBJECT-TYPE
    SYNTAX          Integer32
    MAX-ACCESS      read-write
    STATUS          current
    DESCRIPTION     
            "The index of the linkset with which this SS7 route 
             associates."
    ::= { sonusSs7RouteEntry 8 }

sonusSs7RouteStatusTable OBJECT-TYPE
    SYNTAX          SEQUENCE OF SonusSs7RouteStatusEntry
    MAX-ACCESS      not-accessible
    STATUS          current
    DESCRIPTION     
            "Status Table of the SS7 route for the GSX9000 node."
    ::= { sonusSs7Route 3 }

sonusSs7RouteStatusEntry OBJECT-TYPE
    SYNTAX          SonusSs7RouteStatusEntry
    MAX-ACCESS      not-accessible
    STATUS          current
    DESCRIPTION     
            "SS7 route entry."
    INDEX           { sonusSs7RouteStatusIndex }
    ::= { sonusSs7RouteStatusTable 1 }

SonusSs7RouteStatusEntry ::=
    SEQUENCE {
        sonusSs7RouteStatusIndex        Integer32,
        sonusSs7RouteState              BITS,
        sonusSs7RouteCongestionLevel    Integer32
    }

sonusSs7RouteStatusIndex OBJECT-TYPE
    SYNTAX          Integer32
    MAX-ACCESS      read-only
    STATUS          current
    DESCRIPTION     
            "The index of the SS7 route status."
    ::= { sonusSs7RouteStatusEntry 1 }

sonusSs7RouteState OBJECT-TYPE
    SYNTAX          BITS { reserved0(0), unavl(1), cong(2), lsAvl(3), 
                        tfa(4), tfp(5), tfr(6), avl(7) }
    MAX-ACCESS      read-only
    STATUS          current
    DESCRIPTION     
            "The current state of the SS7 route:
             unavl(1),				Route unavailable,
             cong(2),				Route congested,
             lsAvl(3),				Associated linkset available,
             tfa(4),					Route allowed,
             tfp(5),					Route prohibited,
             tfr(6),					Route restricted,
             avl(7),					Route available"
    ::= { sonusSs7RouteStatusEntry 2 }

sonusSs7RouteCongestionLevel OBJECT-TYPE
    SYNTAX          Integer32 (0..3)
    MAX-ACCESS      read-only
    STATUS          current
    DESCRIPTION     
            "The current congestion level of the route."
    DEFVAL          { 0 }
    ::= { sonusSs7RouteStatusEntry 3 }

sonusSs7Mtp3Mgmt OBJECT IDENTIFIER
    ::= { sonusSs7Mtp3MIBObjects 7 }

sonusSs7Mtp3MgmtNextIndex OBJECT-TYPE
    SYNTAX          Integer32
    MAX-ACCESS      read-only
    STATUS          current
    DESCRIPTION     
            "The next valid index to use when creating an entry in
             the sonusMtp3MgmtTable."
    ::= { sonusSs7Mtp3Mgmt 1 }

sonusSs7Mtp3MgmtTable OBJECT-TYPE
    SYNTAX          SEQUENCE OF SonusSs7Mtp3MgmtEntry
    MAX-ACCESS      not-accessible
    STATUS          current
    DESCRIPTION     
            "This table specifies an MTP3 management."
    ::= { sonusSs7Mtp3Mgmt 2 }

sonusSs7Mtp3MgmtEntry OBJECT-TYPE
    SYNTAX          SonusSs7Mtp3MgmtEntry
    MAX-ACCESS      not-accessible
    STATUS          current
    DESCRIPTION     
            ""
    INDEX           { sonusSs7Mtp3MgmtIndex }
    ::= { sonusSs7Mtp3MgmtTable 1 }

SonusSs7Mtp3MgmtEntry ::=
    SEQUENCE {
        sonusSs7Mtp3MgmtIndex           Integer32,
        sonusSs7Mtp3MgmtName            SonusName,
        sonusSs7Mtp3MgmtRowStatus       RowStatus,
        sonusSs7Mtp3MgmtStackType       INTEGER,
        sonusSs7Mtp3MgmtNetworkIndicator INTEGER,
        sonusSs7Mtp3MgmtMaxLocalPcs     Integer32,
        sonusSs7Mtp3MgmtMaxDestinations Integer32,
        sonusSs7Mtp3MgmtMaxLinks        Integer32,
        sonusSs7Mtp3MgmtMaxLinksets     Integer32,
        sonusSs7Mtp3MgmtMaxRoutes       Integer32,
        sonusSs7Mtp3MgmtProfileName     DisplayString,
        sonusSs7Mtp3MgmtStatisticsMode  INTEGER,
        sonusSs7Mtp3MgmtStatisticsInterval  Integer32,
        sonusSs7Mtp3MgmtTraceLevel      INTEGER,
        sonusSs7Mtp3MgmtActivationMode  INTEGER,
        sonusSs7Mtp3MgmtRestartMode     INTEGER,
        sonusSs7Mtp3MgmtCongestionPriority  INTEGER
    }

sonusSs7Mtp3MgmtIndex OBJECT-TYPE
    SYNTAX          Integer32
    MAX-ACCESS      read-only
    STATUS          current
    DESCRIPTION     
            "The index of the MTP3 management entry."
    ::= { sonusSs7Mtp3MgmtEntry 1 }

sonusSs7Mtp3MgmtName OBJECT-TYPE
    SYNTAX          SonusName
    MAX-ACCESS      read-write
    STATUS          current
    DESCRIPTION     
            "The name of the MTP3 management."
    ::= { sonusSs7Mtp3MgmtEntry 2 }

sonusSs7Mtp3MgmtRowStatus OBJECT-TYPE
    SYNTAX          RowStatus
    MAX-ACCESS      read-write
    STATUS          current
    DESCRIPTION     
            ""
    ::= { sonusSs7Mtp3MgmtEntry 3 }

sonusSs7Mtp3MgmtStackType OBJECT-TYPE
    SYNTAX          INTEGER { itu(0), ansi(1) }
    MAX-ACCESS      read-write
    STATUS          current
    DESCRIPTION     
            "The stack type of the MTP3 stack."
    DEFVAL          { itu }
    ::= { sonusSs7Mtp3MgmtEntry 4 }

sonusSs7Mtp3MgmtNetworkIndicator OBJECT-TYPE
    SYNTAX          INTEGER { intl0(0), intl1(1), natl0(2), natl1(3) }
    MAX-ACCESS      read-write
    STATUS          obsolete
    DESCRIPTION     
            "The network indicator of the MTP3 stack. This object is no
             longer needed, as the Hughes stack uses the corresponding
             object associated with each node to overwrite it."
    DEFVAL          { natl0 }
    ::= { sonusSs7Mtp3MgmtEntry 5 }

sonusSs7Mtp3MgmtMaxLocalPcs OBJECT-TYPE
    SYNTAX          Integer32 (1..8)
    MAX-ACCESS      read-write
    STATUS          current
    DESCRIPTION     
            "The max. number of local point codes of the MTP3 stack."
    ::= { sonusSs7Mtp3MgmtEntry 6 }

sonusSs7Mtp3MgmtMaxDestinations OBJECT-TYPE
    SYNTAX          Integer32 (1..256)
    MAX-ACCESS      read-write
    STATUS          current
    DESCRIPTION     
            "The max. number of remote point codes of the MTP3 stack."
    ::= { sonusSs7Mtp3MgmtEntry 7 }

sonusSs7Mtp3MgmtMaxLinks OBJECT-TYPE
    SYNTAX          Integer32 (1..256)
    MAX-ACCESS      read-write
    STATUS          current
    DESCRIPTION     
            "The max. number of SS7 links of the MTP3 stack."
    ::= { sonusSs7Mtp3MgmtEntry 8 }

sonusSs7Mtp3MgmtMaxLinksets OBJECT-TYPE
    SYNTAX          Integer32 (1..256)
    MAX-ACCESS      read-write
    STATUS          current
    DESCRIPTION     
            "The max. number of SS7 linksets of the MTP3 stack."
    ::= { sonusSs7Mtp3MgmtEntry 9 }

sonusSs7Mtp3MgmtMaxRoutes OBJECT-TYPE
    SYNTAX          Integer32 (1..512)
    MAX-ACCESS      read-write
    STATUS          current
    DESCRIPTION     
            "The max. number of SS7 routes of the MTP3 stack."
    ::= { sonusSs7Mtp3MgmtEntry 10 }

sonusSs7Mtp3MgmtProfileName OBJECT-TYPE
    SYNTAX          DisplayString (SIZE(1..23))
    MAX-ACCESS      read-write
    STATUS          current
    DESCRIPTION     
            "The name of the MTP3 profile this MGMT uses."
    ::= { sonusSs7Mtp3MgmtEntry 11 }

sonusSs7Mtp3MgmtStatisticsMode OBJECT-TYPE
    SYNTAX          INTEGER { enabled(0), reset(1), disabled(2) }
    MAX-ACCESS      read-write
    STATUS          current
    DESCRIPTION     
            "The statistics collection mode of the MTP3 stack.
             The enabled mode enables the MTP3 stack statistics collection
             at the rate that is specified by 
             sonusSs7Mtp3MgmtStatisticsInterval.  The disabled mode 
             disables the collection, and the reset mode zeros all the 
             statistics counters when the collection is enabled."
    DEFVAL          { enabled }
    ::= { sonusSs7Mtp3MgmtEntry 12 }

sonusSs7Mtp3MgmtStatisticsInterval OBJECT-TYPE
    SYNTAX          Integer32 (3..30)
    MAX-ACCESS      read-write
    STATUS          current
    DESCRIPTION     
            "The interval in minutes at which the MTP3 statistics 
             are collected."
    DEFVAL          { 5 }
    ::= { sonusSs7Mtp3MgmtEntry 13 }

sonusSs7Mtp3MgmtTraceLevel OBJECT-TYPE
    SYNTAX          INTEGER { off(0), brief(1), detailed(2), override(3) }
    MAX-ACCESS      read-write
    STATUS          current
    DESCRIPTION     
            "The trace level of the MTP3 stack.
             off -- to turn the trace off.
             brief -- to log the major events,
             detailed -- to log the maximum information at numerous points
             in the flow of execution.
             override -- logs at maximum trace level, bypassing the sonus 
             event level logging"
    DEFVAL          { off }
    ::= { sonusSs7Mtp3MgmtEntry 14 }

sonusSs7Mtp3MgmtActivationMode OBJECT-TYPE
    SYNTAX          INTEGER { default(0), allEmergency(1), 
                        firstLinkEmergency(2) }
    MAX-ACCESS      read-write
    STATUS          current
    DESCRIPTION     
            "The activation mode of the MTP3 stack.
             
             ITU, ETSI:
             default -- all active links in each link set are activated
             	using the normal alignment.
             allEmergency -- all active links in each link set are
             	activated using the emergency alignment,
             firstLinkEmergency -- the first active link that was 
             	configured in each linkset is activated using the
             	emergency alignment.  The remaining are activated using
             	the normal alignment.
             
             ANSI:
             default -- same as firstLinkEmergency
             allEmergency -- all active links in each link set are
             	activated using the emergency alignment,
             firstLinkEmergency -- the first active link that was 
             	configured in each linkset is activated using the
             	emergency alignment.  The remaining are activated using
             	the normal alignment."
    DEFVAL          { default }
    ::= { sonusSs7Mtp3MgmtEntry 15 }

sonusSs7Mtp3MgmtRestartMode OBJECT-TYPE
    SYNTAX          INTEGER { full(0), partial(1) }
    MAX-ACCESS      read-write
    STATUS          current
    DESCRIPTION     
            "The MTP restart mode.  Note that this applies to ANSI only."
    DEFVAL          { partial }
    ::= { sonusSs7Mtp3MgmtEntry 16 }

sonusSs7Mtp3MgmtCongestionPriority OBJECT-TYPE
    SYNTAX          INTEGER { on(0), off(1) }
    MAX-ACCESS      read-write
    STATUS          current
    DESCRIPTION     
            "This applies to the national network, indicating whether
             the congestion priority should be on or off."
    DEFVAL          { on }
    ::= { sonusSs7Mtp3MgmtEntry 17 }

sonusSs7Mtp3MgmtStatusTable OBJECT-TYPE
    SYNTAX          SEQUENCE OF SonusSs7Mtp3MgmtStatusEntry
    MAX-ACCESS      not-accessible
    STATUS          current
    DESCRIPTION     
            "Status Table of the SS7 MTP3 MGMT for the GSX9000 node."
    ::= { sonusSs7Mtp3Mgmt 3 }

sonusSs7Mtp3MgmtStatusEntry OBJECT-TYPE
    SYNTAX          SonusSs7Mtp3MgmtStatusEntry
    MAX-ACCESS      not-accessible
    STATUS          current
    DESCRIPTION     
            "SS7 link entry."
    INDEX           { sonusSs7Mtp3MgmtStatusIndex }
    ::= { sonusSs7Mtp3MgmtStatusTable 1 }

SonusSs7Mtp3MgmtStatusEntry ::=
    SEQUENCE {
        sonusSs7Mtp3MgmtStatusIndex     Integer32,
        sonusSs7Mtp3MgmtState           BITS
    }

sonusSs7Mtp3MgmtStatusIndex OBJECT-TYPE
    SYNTAX          Integer32
    MAX-ACCESS      read-only
    STATUS          current
    DESCRIPTION     
            "The index of the SS7 Mtp3 Mgmt."
    ::= { sonusSs7Mtp3MgmtStatusEntry 1 }

sonusSs7Mtp3MgmtState OBJECT-TYPE
    SYNTAX          BITS { deactivated(0), reserved1(1), reserved2(2), 
                        reserved3(3), reserved4(4), reserved5(5), 
                        reserved6(6), reserved7(7), reserved8(8), 
                        reserved9(9), reserved10(10), reserved11(11), 
                        reserved12(12), reserved13(13), reserved14(14), 
                        reserved15(15), reserved16(16), reserved17(17), 
                        reserved18(18), reserved19(19), reserved20(20), 
                        reserved21(21), reserved22(22), reserved23(23), 
                        reserved24(24), reserved25(25), reserved26(26), 
                        reserved27(27), reserved28(28), 
                        serverInactive(29), noRoute(30), noIsup(31) }
    MAX-ACCESS      read-only
    STATUS          current
    DESCRIPTION     
            "The current state of the SS7 link:
             deactivated(0),			Mtp3 Mgmt deactivated
             serverInactive(29),		Server (MNS, or GNS) inactive,
             noRoute(30),			No routes configured,
             noIsup(31),				No ISUP CIC configured"
    ::= { sonusSs7Mtp3MgmtStatusEntry 2 }

sonusSs7Mtp3MIBNotifications OBJECT IDENTIFIER
    ::= { sonusSs7Mtp3MIB 2 }

sonusSs7Mtp3MIBNotificationsPrefix OBJECT IDENTIFIER
    ::= { sonusSs7Mtp3MIBNotifications 0 }

sonusSs7Mtp3MIBNotificationsObjects OBJECT IDENTIFIER
    ::= { sonusSs7Mtp3MIBNotifications 1 }

sonusSs7DestinationStateChangeNotification NOTIFICATION-TYPE
    OBJECTS         { sonusSs7NodeName, sonusSs7DestinationName, 
                      sonusSs7DestinationCongLevel, 
                      sonusSs7DestinationDiscardLevel, 
                      sonusEventDescription, sonusEventClass, 
                      sonusEventLevel, sonusSequenceId, sonusEventTime }
    STATUS          current
    DESCRIPTION     
            "This trap indicates that the state of the speicified SS7 
             destionation has chagned as described in the event description."
    ::= { sonusSs7Mtp3MIBNotificationsPrefix 1 }

sonusSs7LinkStateChangeNotification NOTIFICATION-TYPE
    OBJECTS         { sonusSs7LinkName, sonusSs7NodeName, 
                      sonusSs7DestinationName, sonusSs7LinkSlc, 
                      sonusSs7LinkState, sonusEventDescription, 
                      sonusEventClass, sonusEventLevel, sonusSequenceId, 
                      sonusEventTime }
    STATUS          current
    DESCRIPTION     
            "This trap indicates that the state of the speicified SS7 
             link has chagned as described in the event description."
    ::= { sonusSs7Mtp3MIBNotificationsPrefix 2 }

sonusSs7RouteStateChangeNotification NOTIFICATION-TYPE
    OBJECTS         { sonusSs7RouteName, sonusSs7NodeName, 
                      sonusSs7DestinationName, sonusSs7LinksetName, 
                      sonusEventDescription, sonusEventClass, 
                      sonusEventLevel, sonusSequenceId, sonusEventTime }
    STATUS          current
    DESCRIPTION     
            "This trap indicates that the state of the speicified SS7 
             route has chagned as described in the event description."
    ::= { sonusSs7Mtp3MIBNotificationsPrefix 3 }

END -- end of module SONUS-SS7-MTP3-MIB.
