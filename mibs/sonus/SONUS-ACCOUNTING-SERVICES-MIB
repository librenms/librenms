--
-- This SMIv2 module has been generated by smidump 0.2-cvs. Do not edit.
--

SONUS-ACCOUNTING-SERVICES-MIB DEFINITIONS ::= BEGIN

IMPORTS
    Counter32, Counter64, Integer32, MODULE-IDENTITY, NOTIFICATION-TYPE, 
    OBJECT-TYPE, Unsigned32
        FROM SNMPv2-SMI
    DisplayString
        FROM SNMPv2-TC
    sonusEventClass, sonusEventDescription, sonusEventLevel, 
    sonusEventTime, sonusSequenceId
        FROM SONUS-COMMON-MIB
    sonusServicesMIBs
        FROM SONUS-SMI
    SonusAcctRecordType, SonusAdminState, SonusBoolean, SonusGMTTime
        FROM SONUS-TC;

sonusAccountingServicesMIB MODULE-IDENTITY
    LAST-UPDATED    "201207240000Z"
    ORGANIZATION    
            "Sonus Networks, Inc."
    CONTACT-INFO    
            "   Customer Support    
             Sonus Networks, Inc.
             7 Technology Park Drive
             Westford, MA 01886
             USA
             
             Tel: 978-614-8100
             Fax: 978-614-8609"
    DESCRIPTION     
            "The MIB Module for Accounting Services Management."
    ::= { sonusServicesMIBs 5 }


sonusAccountingServicesMIBObjects OBJECT IDENTIFIER
    ::= { sonusAccountingServicesMIB 1 }

sonusCallAccountingObjects OBJECT IDENTIFIER
    ::= { sonusAccountingServicesMIBObjects 1 }

sonusCallAccountingConfigObjects OBJECT IDENTIFIER
    ::= { sonusCallAccountingObjects 1 }

sonusAcctGenerationMode OBJECT-TYPE
    SYNTAX          INTEGER { origination(1), destination(2), 
                        allcalls(3), none(4) }
    MAX-ACCESS      read-write
    STATUS          current
    DESCRIPTION     
            "This configures the accounting generation mode for the node"
    DEFVAL          { origination }
    ::= { sonusCallAccountingConfigObjects 1 }

sonusAcctLogDestination OBJECT-TYPE
    SYNTAX          INTEGER { nfs(1), streaming(2) }
    MAX-ACCESS      read-only
    STATUS          current
    DESCRIPTION     
            "The accounting log destination is no longer configurable 
             through this MIB object. This field is replaced by 
             sonusLogInterfaceAdmnLogDestination in V6.2"
    ::= { sonusCallAccountingConfigObjects 2 }

sonusAcctIntAcctState OBJECT-TYPE
    SYNTAX          SonusAdminState
    MAX-ACCESS      read-write
    STATUS          current
    DESCRIPTION     
            "This configures whether Intermediate Accounting is Enabled or 
             Disabled for the Node"
    DEFVAL          { disabled }
    ::= { sonusCallAccountingConfigObjects 3 }

sonusAcctIntAcctInterval OBJECT-TYPE
    SYNTAX          Integer32 (5..86400)
    MAX-ACCESS      read-write
    STATUS          current
    DESCRIPTION     
            "This configures the Intermediate Accounting Interval in seconds
             
             Note: this object is only applicable when sonusAcctIntAcctMode
                   is set to interval(1)."
    DEFVAL          { 60 }
    ::= { sonusCallAccountingConfigObjects 4 }

sonusAcctSecondStageInheritFirstStage OBJECT-TYPE
    SYNTAX          SonusBoolean
    MAX-ACCESS      read-write
    STATUS          current
    DESCRIPTION     
            "This indicates whether or not second stage accounting records for two
             stage calls inherit fields from the first stage call or not. "
    DEFVAL          { false }
    ::= { sonusCallAccountingConfigObjects 5 }

sonusAcctPopulateNonPortedLnpNumbers OBJECT-TYPE
    SYNTAX          SonusBoolean
    MAX-ACCESS      read-write
    STATUS          current
    DESCRIPTION     
            "This indicates whether or not to populate the Called
             Number Before Translation field in the accounting
             record for a number for which an LNP lookup was
             performed and the lookup indicated that the number 
             		has not been ported."
    DEFVAL          { true }
    ::= { sonusCallAccountingConfigObjects 6 }

sonusAcctStatsReset OBJECT-TYPE
    SYNTAX          INTEGER { unknown(1), reset(2) }
    MAX-ACCESS      read-write
    STATUS          current
    DESCRIPTION     
            "Provides a means to reset the sonusCallAccountingStatusObjects
             counters.  Any set operation on this object will result in all
             accounting counters being cleared.  Object always reads as
             value unknown(1)."
    DEFVAL          { unknown }
    ::= { sonusCallAccountingConfigObjects 7 }

sonusAcctIntAcctMode OBJECT-TYPE
    SYNTAX          INTEGER { interval(1), telcordia(2) }
    MAX-ACCESS      read-write
    STATUS          current
    DESCRIPTION     
            "This configures the intermediate record generation mode for
             the node.
             
             In INTERVAL(1) mode, intermediate records are generated
             a periodic intervals following call establishment.  This
             interval is defined by sonusAcctIntAcctInterval.
             
             In TELCORDIA(2) mode, intermediate records are geneated once
             per day for calls whose duration exceeds 24 hours.  The 
             scheduled generated time is defined by
             sonusAcctTelcoridaGenTime."
    DEFVAL          { interval }
    ::= { sonusCallAccountingConfigObjects 8 }

sonusAcctIntLongDurGenTime OBJECT-TYPE
    SYNTAX          SonusGMTTime
    MAX-ACCESS      read-write
    STATUS          current
    DESCRIPTION     
            "Octet string that identifies the GMT time to generate Telcordia
             Long Duration accounting records.  At the scheduled time an
             intermediate accounting record will be generated for all calls
             whose duration exceeds 24 hours.  Duration is measured from
             Service Established time to the current time.
             
                octet  contents      range
                -----  --------      -----
                  1    hour          0..23
                  2    minute        0..59
                  3    seconds       0..60
                  4    deci-seconds  0..9
             
             For example, 23:59:59.9 GMT is represented as 0x173B3B09.
             
             Note: this object is only applicable when sonusAcctIntAcctMode
                   is set to telcordia(2)."
    DEFVAL          { '00000000'H }
    ::= { sonusCallAccountingConfigObjects 9 }

sonusAcctLogFileFormat OBJECT-TYPE
    SYNTAX          INTEGER { default(1), patchrelease(2) }
    MAX-ACCESS      read-write
    STATUS          deprecated
    DESCRIPTION     
            "This configures the accounting file format.
             
             Under normal circumstances DEFAULT(1) mode should be selected.
             In this mode the GSX will generate accounting files with a
             format identical to the release's original format.
             
             When PATCHRELEASE(2) is selected, the GSX will generate 
             accounting files with the most recent format available for the
             release branch.  This format will contain all fields contained
             in the original release (i.e., Rel x.y.0) plus any new fields
             which have been added in patch releases (i.e., Rel x.y.1 to
             x.y.15).
             
             Modifying this object will result in the closure of the current
             accounting file and the opening of a new file of a different
             version.
             
             This object had been replaced by two objects 
             sonusAcctCurrentPatchVersion and sonusAcctUpgradePatchVersion 
             in V06.04.09R000 for supporting CDR Multi-Patch."
    DEFVAL          { 1 }
    ::= { sonusCallAccountingConfigObjects 10 }

sonusAcctStartAcctState OBJECT-TYPE
    SYNTAX          SonusAdminState
    MAX-ACCESS      read-write
    STATUS          current
    DESCRIPTION     
            "This configures whether Start Accounting is Enabled or 
             Disabled for the Node. If START records are disabled, then
             INTERMEDIATE records will also not be generated."
    DEFVAL          { enabled }
    ::= { sonusCallAccountingConfigObjects 11 }

sonusAcctIntTrapState OBJECT-TYPE
    SYNTAX          SonusAdminState
    MAX-ACCESS      read-write
    STATUS          current
    DESCRIPTION     
            "This configures whether a trap will be generated
             whenever an INTERMEDIATE record is generated."
    DEFVAL          { disabled }
    ::= { sonusCallAccountingConfigObjects 12 }

sonusAcctPopulateRemoteGsxInfoState OBJECT-TYPE
    SYNTAX          SonusAdminState
    MAX-ACCESS      read-write
    STATUS          current
    DESCRIPTION     
            "This configures whether a destination GSX propagates
             its billing data to originating GSX for GSX-GSX calls.
             If population state is enabled, then the destination GSX
             will propagate billing information to originating GSX."
    DEFVAL          { disabled }
    ::= { sonusCallAccountingConfigObjects 13 }

sonusAcctEarlyAttemptState OBJECT-TYPE
    SYNTAX          SonusAdminState
    MAX-ACCESS      read-write
    STATUS          current
    DESCRIPTION     
            "This configures whether early ATTEMPT accounting is enabled 
             or disabled. An early ATTEMPT record is associated
             with early call disconnect before the Policy Request was sent."
    DEFVAL          { disabled }
    ::= { sonusCallAccountingConfigObjects 14 }

sonusAcctCurrentPatchVersion OBJECT-TYPE
    SYNTAX          Unsigned32 (0..255)
    MAX-ACCESS      read-write
    STATUS          current
    DESCRIPTION     
            "This configures CAM patch number of a GSX release for
             generatiing call accounting records. The operator can 
             configure this object when there are multiple CAM patches 
             available in the GSX release. Modifying this object 
             will result in the closure of the current accounting file 
             and the opening of a new file of a different CAM version. 
             Patch version 0 indicates default call accounting."
    DEFVAL          { 0 }
    ::= { sonusCallAccountingConfigObjects 15 }

sonusAcctUpgradePatchVersion OBJECT-TYPE
    SYNTAX          Unsigned32 (0..255)
    MAX-ACCESS      read-write
    STATUS          current
    DESCRIPTION     
            "This is an optional configuration, only applies to
             LSWU from one GSX release to a different GSX major release. 
             This configuration does not apply to minor LSWU
             within the same major GSX release (e.g. LSWU from 
             GSX V06.04.09R000 to V06.04.10R000).
             This object configures the CAM patch version going to be used 
             for generation all accounting records after software upgrade.
             Valid for one Live Software Upgrade only."
    DEFVAL          { 0 }
    ::= { sonusCallAccountingConfigObjects 16 }

sonusAcctCamFileVersion OBJECT-TYPE
    SYNTAX          Unsigned32
    MAX-ACCESS      read-only
    STATUS          current
    DESCRIPTION     
            "The current CAM File version logged in the CAM file header. 
             This CAM file version in hex format 0xAAAAIISS includes 
             majorVersion, minorVersion, and specialVersion below. The 
             CAM major version will stay the same across all available
             CAM patches under the same GSX release branch.
               AAAA: The Major CAM version;
                 II: The Minor CAM version;
                 SS: The Special CAM version"
    ::= { sonusCallAccountingConfigObjects 17 }

sonusAcctIntLongDurThreshold OBJECT-TYPE
    SYNTAX          Unsigned32 (1..24)
    MAX-ACCESS      read-write
    STATUS          current
    DESCRIPTION     
            "This configures the Accounting Intermediate Records Duration
             in hours.
             
             When intermediate record generation mode (sonusAcctIntAcctMode)
             is set to Telcordia,and the long duration time generation time
             (sonusAcctIntLongDurGenTime) is reached, then an INTERMEDIATE
             record will be generated for each call whose duration exceeds
             this threshold.
             
             Note: this object is only applicable when sonusAcctIntAcctMode
                    is set to telcordia(2). The units for this configuration
                    is in Hours"
    DEFVAL          { 24 }
    ::= { sonusCallAccountingConfigObjects 18 }

sonusAcctSendEgressCdrInfoOnReceipt OBJECT-TYPE
    SYNTAX          SonusBoolean
    MAX-ACCESS      read-write
    STATUS          current
    DESCRIPTION     
            "This indicates whether or not to send the egress
             CDR info immediately after receiving and processing it."
    DEFVAL          { false }
    ::= { sonusCallAccountingConfigObjects 19 }

sonusAcctPopulateIpTgFarEndSwitchType OBJECT-TYPE
    SYNTAX          SonusAdminState
    MAX-ACCESS      read-write
    STATUS          current
    DESCRIPTION     
            "This configures whether or not we use Ingress Far End
             Switch Type passed down from PSX IP TG for SIP ingress
             calls or not."
    DEFVAL          { disabled }
    ::= { sonusCallAccountingConfigObjects 20 }

sonusAcctMaxRecordSequenceNum OBJECT-TYPE
    SYNTAX          INTEGER { uint16(1), uint32(2) }
    MAX-ACCESS      read-write
    STATUS          current
    DESCRIPTION     
            "This field configures the maximum record sequence number for logging
             the CDR records. if the option uint32 is selected, the maximum 
             		 record sequence number is referred to 4294967295. Otherwise, the default 
             		 maximum sequence number 65535 is used.
             
             		 Note: The run-time record sequence number will roll-over if its value 
             		 exceeded the configurable maximum record sequence number or the 
             		 default maximum record sequence number."
    DEFVAL          { uint16 }
    ::= { sonusCallAccountingConfigObjects 21 }

sonusAcctNoCdrState OBJECT-TYPE
    SYNTAX          SonusAdminState
    MAX-ACCESS      read-write
    STATUS          current
    DESCRIPTION     
            "No Attempt cdr shoud be generated for configured 
             URI specified in Service Group"
    DEFVAL          { disabled }
    ::= { sonusCallAccountingConfigObjects 22 }

sonusAcctEgressGwBlockEarlyAttemptState OBJECT-TYPE
    SYNTAX          SonusAdminState
    MAX-ACCESS      read-write
    STATUS          current
    DESCRIPTION     
            "This indicates whether the early attempt record is to be generated by the egress gateway SG/FE.    
             ENABLE- Do not generates early attempt record. 
             DISABLE- generates early attempt record"
    DEFVAL          { disabled }
    ::= { sonusCallAccountingConfigObjects 23 }

sonusCallAccountingStatusObjects OBJECT IDENTIFIER
    ::= { sonusCallAccountingObjects 2 }

sonusAcctNumCallAttempts OBJECT-TYPE
    SYNTAX          Counter64
    MAX-ACCESS      read-only
    STATUS          current
    DESCRIPTION     
            "The total Number of Call Attempts since last reboot, or last statistic reset"
    ::= { sonusCallAccountingStatusObjects 1 }

sonusAcctNumCallCompletions OBJECT-TYPE
    SYNTAX          Counter64
    MAX-ACCESS      read-only
    STATUS          current
    DESCRIPTION     
            "The total Number of Succesful Call Completions since last reboot, or last statistic reset"
    ::= { sonusCallAccountingStatusObjects 2 }

sonusAcctNumCallAttemptFailures OBJECT-TYPE
    SYNTAX          Counter64
    MAX-ACCESS      read-only
    STATUS          current
    DESCRIPTION     
            "The total Number of Unsuccesful Call Attempts since last reboot, or last statistic reset"
    ::= { sonusCallAccountingStatusObjects 3 }

sonusAcctBusyHourAttempts OBJECT-TYPE
    SYNTAX          Integer32
    MAX-ACCESS      read-only
    STATUS          current
    DESCRIPTION     
            "The Average BHCA rate in the last one hour, or last statistic reset"
    ::= { sonusCallAccountingStatusObjects 4 }

sonusAcctCallAttemptRate OBJECT-TYPE
    SYNTAX          Integer32
    MAX-ACCESS      read-only
    STATUS          current
    DESCRIPTION     
            "The Call arrival rate in calls/sec in the last one minute, or last statistic reset"
    ::= { sonusCallAccountingStatusObjects 5 }

sonusAcctAvgCallDuration OBJECT-TYPE
    SYNTAX          Integer32
    MAX-ACCESS      read-only
    STATUS          current
    DESCRIPTION     
            "The Average Call Duration in seconds.  Duration is measured
             from service established to call disconnect.  This average
             only accounts for completed calls, not calls in progress or
             call attempts.  This average is reset when accounting stats
             are reset."
    ::= { sonusCallAccountingStatusObjects 6 }

sonusAcctNumCallAttemptBlocked OBJECT-TYPE
    SYNTAX          Counter64
    MAX-ACCESS      read-only
    STATUS          current
    DESCRIPTION     
            "The total Number of Calls which were blocked/screened since last reboot, or last statistic reset"
    ::= { sonusCallAccountingStatusObjects 7 }

sonusAcctNormalSizeRecords OBJECT-TYPE
    SYNTAX          Counter64
    MAX-ACCESS      read-only
    STATUS          current
    DESCRIPTION     
            "The total number of normal size accounting records, for ASCII records under 1750 characters."
    ::= { sonusCallAccountingStatusObjects 8 }

sonusAcctLargeSizeRecords OBJECT-TYPE
    SYNTAX          Counter64
    MAX-ACCESS      read-only
    STATUS          current
    DESCRIPTION     
            "The total number of large accounting records, for ASCII records exceeds 1750 characters."
    ::= { sonusCallAccountingStatusObjects 9 }

sonusAcctLargerSizeRecords OBJECT-TYPE
    SYNTAX          Counter64
    MAX-ACCESS      read-only
    STATUS          current
    DESCRIPTION     
            "The total number of larger accounting records, for any ASCII records exceeds 3500 characters including truncated records that exceeds maximum supported size."
    ::= { sonusCallAccountingStatusObjects 10 }

sonusAcctTruncateRecords OBJECT-TYPE
    SYNTAX          Counter64
    MAX-ACCESS      read-only
    STATUS          current
    DESCRIPTION     
            "The total number of abnormal ASCII records that exceed maximum supported size."
    ::= { sonusCallAccountingStatusObjects 11 }

sonusSelCdrPopulationTable OBJECT-TYPE
    SYNTAX          SEQUENCE OF SonusSelCdrPopulationEntry
    MAX-ACCESS      not-accessible
    STATUS          current
    DESCRIPTION     
            "This table contains GSX selectable CDR configuration
             provisioned by DSI."
    ::= { sonusAccountingServicesMIBObjects 8 }

sonusSelCdrPopulationEntry OBJECT-TYPE
    SYNTAX          SonusSelCdrPopulationEntry
    MAX-ACCESS      not-accessible
    STATUS          current
    DESCRIPTION     
            "This table describs the selected CDR fields of CDR
             START/STOP/ATTEPT/INTERMEDIATE records."
    INDEX           { sonusSelCdrTypeIndex, sonusSelCdrFieldIndex }
    ::= { sonusSelCdrPopulationTable 1 }

SonusSelCdrPopulationEntry ::=
    SEQUENCE {
        sonusSelCdrTypeIndex            SonusAcctRecordType,
        sonusSelCdrFieldIndex           Unsigned32,
        sonusSelCdrFieldPopulation      INTEGER
    }

sonusSelCdrTypeIndex OBJECT-TYPE
    SYNTAX          SonusAcctRecordType
    MAX-ACCESS      not-accessible
    STATUS          current
    DESCRIPTION     
            "Identifies the call accounting record type."
    ::= { sonusSelCdrPopulationEntry 1 }

sonusSelCdrFieldIndex OBJECT-TYPE
    SYNTAX          Unsigned32 (1..166)
    MAX-ACCESS      not-accessible
    STATUS          current
    DESCRIPTION     
            "Identifies the call accounting field. "
    ::= { sonusSelCdrPopulationEntry 2 }

sonusSelCdrFieldPopulation OBJECT-TYPE
    SYNTAX          INTEGER { deselected(0), selected(1) }
    MAX-ACCESS      read-only
    STATUS          current
    DESCRIPTION     
            "Identifies whether the record field is selected for CDR logging"
    ::= { sonusSelCdrPopulationEntry 3 }

sonusSelCdrStatObjects OBJECT IDENTIFIER
    ::= { sonusAccountingServicesMIBObjects 9 }

sonusSelCdrSequenceNumber OBJECT-TYPE
    SYNTAX          Counter32
    MAX-ACCESS      read-only
    STATUS          current
    DESCRIPTION     
            "The sequence number of the GSX selectable CDR configuration of GSX-  
             DSI CDR streaming.
             
                 This data comes from DSI->GSX message GSX_CDR_CONF_COMPLETE_REQ_MSG."
    ::= { sonusSelCdrStatObjects 1 }

sonusSelCdrUpdateStatus OBJECT-TYPE
    SYNTAX          INTEGER { success(0), subsetStart(1), subsetStop(2), 
                        subsetStartStop(3), subsetAttempt(4), 
                        subsetStartAttempt(5), subsetStopAttempt(6), 
                        subsetStartStopAttempt(7), subsetIntermediate(8), 
                        subsetStartIntermediate(9), 
                        subsetStopIntermediate(10), 
                        subsetStartStopInter(11), subsetAttemptInter(12), 
                        subsetStartAttemptInter(13), 
                        subsetStopAttemptInter(14), 
                        subsetStartStopAtmpIntr(15) }
    MAX-ACCESS      read-only
    STATUS          current
    DESCRIPTION     
            "This field contains the update status of the selectable CDR configuration.
             
             Value 0 indicates GSX accepts all selectable CDR configurations 
             provisioned by DSI.
             
             Value 1 indicates GSX partially accepted the selectable CDR configuration 
             of START record type, and fully accepted all other configuration updates 
             on STOP, ATTEMPT and INTERMEDIATE record types.
             
             Value 2 indicates GSX partially accepted the selectable CDR configuration 
             on STOP record type, and fully accepted all other configuration updates 
             on START, ATTEMPT and INTERMEDIATE record types.
             
             Value 3 indicates GSX partially accepted the selectable CDR configuration 
             on START and STOP record types, and fully accepted all other configuration
             update on ATTEMPT and INTERMEDIATE record types.
             .. etc. "
    ::= { sonusSelCdrStatObjects 2 }

sonusAccountingMIBNotifications OBJECT IDENTIFIER
    ::= { sonusAccountingServicesMIB 2 }

sonusAccountingMIBNotificationsPrefix OBJECT IDENTIFIER
    ::= { sonusAccountingMIBNotifications 0 }

sonusAccountingMIBNotificationsObjects OBJECT IDENTIFIER
    ::= { sonusAccountingMIBNotifications 1 }

sonusAcctOutOfServiceReason OBJECT-TYPE
    SYNTAX          INTEGER { configChange(1), eventLoggingError(2) }
    MAX-ACCESS      read-only
    STATUS          current
    DESCRIPTION     
            "The Reason for Call Accounting for the Node being
             Out-of-Service."
    ::= { sonusAccountingMIBNotificationsObjects 1 }

sonusAcctGcid OBJECT-TYPE
    SYNTAX          Integer32
    MAX-ACCESS      read-only
    STATUS          current
    DESCRIPTION     
            "GCID associated with the call which generated the trap.
             Corresponds to INTERMEDIATE accounting record, field 65."
    ::= { sonusAccountingMIBNotificationsObjects 2 }

sonusAcctOrigTrunkgroupType OBJECT-TYPE
    SYNTAX          Integer32
    MAX-ACCESS      read-only
    STATUS          current
    DESCRIPTION     
            "This value represents the originating trunk type as specified
             by customer. This field is associated with the corresponding
             field of trunk group screen on PSX.
             Corresponds to INTERMEDIATE accounting record, field 135."
    ::= { sonusAccountingMIBNotificationsObjects 3 }

sonusAcctIngressCep OBJECT-TYPE
    SYNTAX          DisplayString (SIZE(0..31))
    MAX-ACCESS      read-only
    STATUS          current
    DESCRIPTION     
            "Ingress Circuit End Point.
             If ingress is PSTN, then CEP string contains the following:
               <Shelf>:<Slot>:<Port>:<Ds0>:<Cic>:<LPC>:<RPC>
             If ingress is IP, then CEP string containst the following:
               <Local IP Address>:<Port>/<Remote IP Address>:<Port>
             Corresponds to INTERMEDIATE accounting record, fields 32 & 33."
    ::= { sonusAccountingMIBNotificationsObjects 4 }

sonusAcctTermTrunkgroupType OBJECT-TYPE
    SYNTAX          Integer32
    MAX-ACCESS      read-only
    STATUS          current
    DESCRIPTION     
            "This value represents the terminating trunk type as specified
             by customer. This field is associated with the corresponding
             field of trunk group screen on PSX.
             Corresponds to INTERMEDIATE accounting record, field 136."
    ::= { sonusAccountingMIBNotificationsObjects 5 }

sonusAcctEgressCep OBJECT-TYPE
    SYNTAX          DisplayString (SIZE(0..31))
    MAX-ACCESS      read-only
    STATUS          current
    DESCRIPTION     
            "Egress Circuit End Point.
             If egress is PSTN, then CEP string contains the following:
               <Shelf>:<Slot>:<Port>:<Ds0>:<Cic>:<LPC>:<RPC>
             If egress is IP, then CEP string containst the following:
               <Local IP Address>:<Port>/<Remote IP Address>:<Port>
             Corresponds to INTERMEDIATE accounting record, fields 34 & 35."
    ::= { sonusAccountingMIBNotificationsObjects 6 }

sonusAcctCallingPartyNumber OBJECT-TYPE
    SYNTAX          DisplayString (SIZE(0..31))
    MAX-ACCESS      read-only
    STATUS          current
    DESCRIPTION     
            "Calling Party Number associated with the call which generated the trap.
             Corresponds to INTERMEDIATE accounting record, field 17."
    ::= { sonusAccountingMIBNotificationsObjects 7 }

sonusAcctCalledPartyNumber OBJECT-TYPE
    SYNTAX          DisplayString (SIZE(0..31))
    MAX-ACCESS      read-only
    STATUS          current
    DESCRIPTION     
            "Called Party Number associated with the call which generated the trap.
             Corresponds to INTERMEDIATE accounting record, field 18."
    ::= { sonusAccountingMIBNotificationsObjects 8 }

sonusSelCdrReqRspTimeout OBJECT-TYPE
    SYNTAX          Unsigned32
    MAX-ACCESS      read-only
    STATUS          current
    DESCRIPTION     
            ""
    ::= { sonusAccountingMIBNotifications 2 }

sonusCallAccountingInServiceNotification NOTIFICATION-TYPE
    OBJECTS         { sonusAcctGenerationMode, sonusAcctLogDestination, 
                      sonusAcctIntAcctState, sonusAcctIntAcctInterval, 
                      sonusEventDescription, sonusEventClass, 
                      sonusEventLevel, sonusSequenceId, sonusEventTime, 
                      sonusAcctIntAcctMode, sonusAcctIntLongDurGenTime }
    STATUS          current
    DESCRIPTION     
            "This Trap is Generated when a change is made to the Accounting 
             Configuration for the Node, and the resultant configuration
             state of accounting for the node is that it is enabled/in-service"
    ::= { sonusAccountingMIBNotificationsPrefix 1 }

sonusCallAccountingOutOfServiceNotification NOTIFICATION-TYPE
    OBJECTS         { sonusAcctOutOfServiceReason, sonusEventDescription, 
                      sonusEventClass, sonusEventLevel, sonusSequenceId, 
                      sonusEventTime }
    STATUS          current
    DESCRIPTION     
            "This Trap is Generated when Accounting Records are no
             longer being generated on the Node. It could be either
             because of a change to the Accounting Configuration
             or because of errors in the logging mechanism such as file logging
             errors. When the reason specified for accounting outofservice
             is event logging error, then the SYS event logs on the Node
             should be examined to obtain further information about the
             event logging failure"
    ::= { sonusAccountingMIBNotificationsPrefix 2 }

sonusSelCdrConfUpdateNotification NOTIFICATION-TYPE
    OBJECTS         { sonusSelCdrSequenceNumber, sonusSelCdrUpdateStatus, 
                      sonusEventDescription, sonusEventClass, 
                      sonusEventLevel, sonusSequenceId, sonusEventTime }
    STATUS          current
    DESCRIPTION     
            "This Trap indicates that GSX receives
             selectable CDR configuration from DSI
             stream server. The variable sonusSelCdrConfSeqNum
             indicates the new sequence number of selectable CDR
             configuration received. The variable
             sonusSelCdrConfUpdateStatus indicates
             the accept status of the configuration updates."
    ::= { sonusAccountingMIBNotificationsPrefix 3 }

sonusSelCdrConfigReqRspTimeoutNotification NOTIFICATION-TYPE
    OBJECTS         { sonusSelCdrReqRspTimeout, 
                      sonusSelCdrSequenceNumber, sonusEventDescription, 
                      sonusEventClass, sonusEventLevel, sonusSequenceId, 
                      sonusEventTime }
    STATUS          current
    DESCRIPTION     
            "This trap indicates that GSX requests DSI for current selectable
             CDR configuration due to previous CDR streaming link outage or LSWU,
             but didn\222t receive the configuration updates from DSI after three 
             		retries.
             
             The variable sonusSelCdrConfSeqNum indicates the last selectable CDR
             Configuration received, the variable sonusSelCdrReqRspTimeout
             indicates the duration of three retries."
    ::= { sonusAccountingMIBNotificationsPrefix 4 }

sonusAccountingIntermediateRecordNotification NOTIFICATION-TYPE
    OBJECTS         { sonusAcctGcid, sonusAcctOrigTrunkgroupType, 
                      sonusAcctIngressCep, sonusAcctTermTrunkgroupType, 
                      sonusAcctEgressCep, sonusAcctCallingPartyNumber, 
                      sonusAcctCalledPartyNumber, sonusEventDescription, 
                      sonusEventClass, sonusEventLevel, sonusSequenceId, 
                      sonusEventTime }
    STATUS          current
    DESCRIPTION     
            "This Trap is Generated when an INTERMEDIATE accounting
             record is generated."
    ::= { sonusAccountingMIBNotificationsPrefix 5 }

END -- end of module SONUS-ACCOUNTING-SERVICES-MIB.
