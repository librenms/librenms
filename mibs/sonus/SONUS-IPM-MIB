--
-- This SMIv2 module has been generated by smidump 0.2-cvs. Do not edit.
--

SONUS-IPM-MIB DEFINITIONS ::= BEGIN

IMPORTS
    Ipv6Address
        FROM IPV6-TC
    Counter32, Counter64, Integer32, IpAddress, MODULE-IDENTITY, 
    NOTIFICATION-TYPE, OBJECT-TYPE, Unsigned32
        FROM SNMPv2-SMI
    DisplayString, RowStatus
        FROM SNMPv2-TC
    sonusEventClass, sonusEventDescription, sonusEventLevel, 
    sonusEventTime, sonusSequenceId, sonusShelfIndex, sonusSlotIndex
        FROM SONUS-COMMON-MIB
    sonusPacketMIBs
        FROM SONUS-SMI
    SonusAdminState, SonusName, SonusNameReference, SonusServiceState, 
    SonusShelfIndex, SonusSlotIndex
        FROM SONUS-TC;

sonusIpmMIB MODULE-IDENTITY
    LAST-UPDATED    "201008100000Z"
    ORGANIZATION    
            "Sonus Networks, Inc."
    CONTACT-INFO    
            "   Customer Support    
             Sonus Networks, Inc.
             7 Technology Park Drive
             Westford, MA 01886
             USA
             
             Tel: 978-614-8100
             Fax: 978-614-8609"
    DESCRIPTION     
            "The MIB Module for IP Monitoring."
    ::= { sonusPacketMIBs 10 }


sonusIpmMIBObjects OBJECT IDENTIFIER
    ::= { sonusIpmMIB 1 }

sonusPolicerDiscardRateProfile OBJECT IDENTIFIER
    ::= { sonusIpmMIBObjects 1 }

sonusPolicerDiscardRateProfileNextIndex OBJECT-TYPE
    SYNTAX          Unsigned32
    MAX-ACCESS      read-only
    STATUS          current
    DESCRIPTION     
            "The next valid index to use when creating an entry in
             the sonusPolicerDiscardRateProfileTable."
    ::= { sonusPolicerDiscardRateProfile 1 }

sonusPolicerDiscardRateProfileTable OBJECT-TYPE
    SYNTAX          SEQUENCE OF SonusPolicerDiscardRateProfileEntry
    MAX-ACCESS      not-accessible
    STATUS          current
    DESCRIPTION     
            "This table contains policer discard rate profiles."
    ::= { sonusPolicerDiscardRateProfile 2 }

sonusPolicerDiscardRateProfileEntry OBJECT-TYPE
    SYNTAX          SonusPolicerDiscardRateProfileEntry
    MAX-ACCESS      not-accessible
    STATUS          current
    DESCRIPTION     
            ""
    INDEX           { sonusPolicerDiscardRateProfileIndex }
    ::= { sonusPolicerDiscardRateProfileTable 1 }

SonusPolicerDiscardRateProfileEntry ::=
    SEQUENCE {
        sonusPolicerDiscardRateProfileIndex   Unsigned32,
        sonusPolicerDiscardRateProfileName  SonusName,
        sonusPolicerDiscardRateProfileRowStatus       RowStatus,
        sonusPolicerDiscardRateProfileAdminState        SonusAdminState,
        sonusPolicerDiscardRateProfileWhiteSetThreshold               Unsigned32,
        sonusPolicerDiscardRateProfileWhiteClearThreshold                 Unsigned32,
        sonusPolicerDiscardRateProfileWhiteSetDuration              Unsigned32,
        sonusPolicerDiscardRateProfileWhiteClearDuration                Unsigned32,
        sonusPolicerDiscardRateProfileBlackSetThreshold               Unsigned32,
        sonusPolicerDiscardRateProfileBlackClearThreshold                 Unsigned32,
        sonusPolicerDiscardRateProfileBlackSetDuration              Unsigned32,
        sonusPolicerDiscardRateProfileBlackClearDuration                Unsigned32,
        sonusPolicerDiscardRateProfileDarkGraySetThreshold                  Unsigned32,
        sonusPolicerDiscardRateProfileDarkGrayClearThreshold                    Unsigned32,
        sonusPolicerDiscardRateProfileDarkGraySetDuration                 Unsigned32,
        sonusPolicerDiscardRateProfileDarkGrayClearDuration                   Unsigned32,
        sonusPolicerDiscardRateProfileLightGraySetThreshold                   Unsigned32,
        sonusPolicerDiscardRateProfileLightGrayClearThreshold                     Unsigned32,
        sonusPolicerDiscardRateProfileLightGraySetDuration                  Unsigned32,
        sonusPolicerDiscardRateProfileLightGrayClearDuration                    Unsigned32,
        sonusPolicerDiscardRateProfileVLanSetThreshold              Unsigned32,
        sonusPolicerDiscardRateProfileVLanClearThreshold                Unsigned32,
        sonusPolicerDiscardRateProfileVLanSetDuration             Unsigned32,
        sonusPolicerDiscardRateProfileVLanClearDuration               Unsigned32,
        sonusPolicerDiscardRateProfileServerProtectSetThreshold                       Unsigned32,
        sonusPolicerDiscardRateProfileServerProtectClearThreshold                         Unsigned32,
        sonusPolicerDiscardRateProfileServerProtectSetDuration                      Unsigned32,
        sonusPolicerDiscardRateProfileServerProtectClearDuration                        Unsigned32,
        sonusPolicerDiscardRateProfileMediaSetThreshold               Unsigned32,
        sonusPolicerDiscardRateProfileMediaClearThreshold                 Unsigned32,
        sonusPolicerDiscardRateProfileMediaSetDuration              Unsigned32,
        sonusPolicerDiscardRateProfileMediaClearDuration                Unsigned32,
        sonusPolicerDiscardRateProfileRogueUnallocPortSetThreshold                          Unsigned32,
        sonusPolicerDiscardRateProfileRogueUnallocPortClearThreshold                            Unsigned32,
        sonusPolicerDiscardRateProfileRogueUnallocPortSetDuration                         Unsigned32,
        sonusPolicerDiscardRateProfileRogueUnallocPortClearDuration                           Unsigned32,
        sonusPolicerDiscardRateProfileRogueBadSrcSetThreshold                     Unsigned32,
        sonusPolicerDiscardRateProfileRogueBadSrcClearThreshold                       Unsigned32,
        sonusPolicerDiscardRateProfileRogueBadSrcSetDuration                    Unsigned32,
        sonusPolicerDiscardRateProfileRogueBadSrcClearDuration                      Unsigned32,
        sonusPolicerDiscardRateProfileRogueBadDestSetThreshold                      Unsigned32,
        sonusPolicerDiscardRateProfileRogueBadDestClearThreshold                        Unsigned32,
        sonusPolicerDiscardRateProfileRogueBadDestSetDuration                     Unsigned32,
        sonusPolicerDiscardRateProfileRogueBadDestClearDuration                       Unsigned32,
        sonusPolicerDiscardRateProfileRogueBadVLanSetThreshold                      Unsigned32,
        sonusPolicerDiscardRateProfileRogueBadVLanClearThreshold                        Unsigned32,
        sonusPolicerDiscardRateProfileRogueBadVLanSetDuration                     Unsigned32,
        sonusPolicerDiscardRateProfileRogueBadVLanClearDuration                       Unsigned32
    }

sonusPolicerDiscardRateProfileIndex OBJECT-TYPE
    SYNTAX          Unsigned32
    MAX-ACCESS      read-only
    STATUS          current
    DESCRIPTION     
            "Identifies the Policer Discard Rate profile."
    ::= { sonusPolicerDiscardRateProfileEntry 1 }

sonusPolicerDiscardRateProfileName OBJECT-TYPE
    SYNTAX          SonusName
    MAX-ACCESS      read-write
    STATUS          current
    DESCRIPTION     
            "The profile name."
    ::= { sonusPolicerDiscardRateProfileEntry 2 }

sonusPolicerDiscardRateProfileRowStatus OBJECT-TYPE
    SYNTAX          RowStatus
    MAX-ACCESS      read-write
    STATUS          current
    DESCRIPTION     
            ""
    ::= { sonusPolicerDiscardRateProfileEntry 3 }

sonusPolicerDiscardRateProfileAdminState OBJECT-TYPE
    SYNTAX          SonusAdminState
    MAX-ACCESS      read-write
    STATUS          current
    DESCRIPTION     
            "The administrative state of the profile."
    DEFVAL          { disabled }
    ::= { sonusPolicerDiscardRateProfileEntry 4 }

sonusPolicerDiscardRateProfileWhiteSetThreshold OBJECT-TYPE
    SYNTAX          Unsigned32 (0..2147483647)
    MAX-ACCESS      read-write
    STATUS          current
    DESCRIPTION     
            "The threshold for the aggregate white policer discard rate which
             may set an alarm. A value of 0 disables the policer from causing
             an alarm."
    DEFVAL          { 20 }
    ::= { sonusPolicerDiscardRateProfileEntry 5 }

sonusPolicerDiscardRateProfileWhiteClearThreshold OBJECT-TYPE
    SYNTAX          Unsigned32 (0..2147483647)
    MAX-ACCESS      read-write
    STATUS          current
    DESCRIPTION     
            "The threshold for the aggregate white policer discard rate which
             may clear an alarm."
    DEFVAL          { 10 }
    ::= { sonusPolicerDiscardRateProfileEntry 6 }

sonusPolicerDiscardRateProfileWhiteSetDuration OBJECT-TYPE
    SYNTAX          Unsigned32 (0..65535)
    MAX-ACCESS      read-write
    STATUS          current
    DESCRIPTION     
            "The duration (in seconds) that the aggregate white policer discard rate
             must be at or above its set threshold before an alarm is set. A value of 0
             sets the alarm immediately."
    DEFVAL          { 3 }
    ::= { sonusPolicerDiscardRateProfileEntry 7 }

sonusPolicerDiscardRateProfileWhiteClearDuration OBJECT-TYPE
    SYNTAX          Unsigned32 (0..65535)
    MAX-ACCESS      read-write
    STATUS          current
    DESCRIPTION     
            "The duration (in seconds) that the aggregate white policer discard rate
             must be at or below its clear threshold before an alarm is cleared. A value of 0
             clears the alarm immediately."
    DEFVAL          { 3 }
    ::= { sonusPolicerDiscardRateProfileEntry 8 }

sonusPolicerDiscardRateProfileBlackSetThreshold OBJECT-TYPE
    SYNTAX          Unsigned32 (0..2147483647)
    MAX-ACCESS      read-write
    STATUS          current
    DESCRIPTION     
            "The threshold for the aggregate black policer discard rate which
             may set an alarm. A value of 0 disables the policer from causing
             an alarm."
    DEFVAL          { 100 }
    ::= { sonusPolicerDiscardRateProfileEntry 9 }

sonusPolicerDiscardRateProfileBlackClearThreshold OBJECT-TYPE
    SYNTAX          Unsigned32 (0..2147483647)
    MAX-ACCESS      read-write
    STATUS          current
    DESCRIPTION     
            "The threshold for the aggregate black policer discard rate which
             may clear an alarm."
    DEFVAL          { 20 }
    ::= { sonusPolicerDiscardRateProfileEntry 10 }

sonusPolicerDiscardRateProfileBlackSetDuration OBJECT-TYPE
    SYNTAX          Unsigned32 (0..65535)
    MAX-ACCESS      read-write
    STATUS          current
    DESCRIPTION     
            "The duration (in seconds) that the aggregate black policer discard rate
             must be at or above its set threshold before an alarm is set. A value of 0
             sets the alarm immediately."
    DEFVAL          { 3 }
    ::= { sonusPolicerDiscardRateProfileEntry 11 }

sonusPolicerDiscardRateProfileBlackClearDuration OBJECT-TYPE
    SYNTAX          Unsigned32 (0..65535)
    MAX-ACCESS      read-write
    STATUS          current
    DESCRIPTION     
            "The duration (in seconds) that the aggregate black policer discard rate
             must be at or below its clear threshold before an alarm is cleared. A value of 0
             clears the alarm immediately."
    DEFVAL          { 3 }
    ::= { sonusPolicerDiscardRateProfileEntry 12 }

sonusPolicerDiscardRateProfileDarkGraySetThreshold OBJECT-TYPE
    SYNTAX          Unsigned32 (0..2147483647)
    MAX-ACCESS      read-write
    STATUS          current
    DESCRIPTION     
            "The threshold for the aggregate darkGray policer discard rate which
             may set an alarm. A value of 0 disables the policer from causing
             an alarm."
    DEFVAL          { 20 }
    ::= { sonusPolicerDiscardRateProfileEntry 13 }

sonusPolicerDiscardRateProfileDarkGrayClearThreshold OBJECT-TYPE
    SYNTAX          Unsigned32 (0..2147483647)
    MAX-ACCESS      read-write
    STATUS          current
    DESCRIPTION     
            "The threshold for the aggregate darkGray policer discard rate which
             may clear an alarm."
    DEFVAL          { 10 }
    ::= { sonusPolicerDiscardRateProfileEntry 14 }

sonusPolicerDiscardRateProfileDarkGraySetDuration OBJECT-TYPE
    SYNTAX          Unsigned32 (0..65535)
    MAX-ACCESS      read-write
    STATUS          current
    DESCRIPTION     
            "The duration (in seconds) that the aggregate darkGray policer discard rate
             must be at or above its set threshold before an alarm is set. A value of 0
             sets the alarm immediately."
    DEFVAL          { 3 }
    ::= { sonusPolicerDiscardRateProfileEntry 15 }

sonusPolicerDiscardRateProfileDarkGrayClearDuration OBJECT-TYPE
    SYNTAX          Unsigned32 (0..65535)
    MAX-ACCESS      read-write
    STATUS          current
    DESCRIPTION     
            "The duration (in seconds) that the aggregate darkGray policer discard rate
             must be at or below its clear threshold before an alarm is cleared. A value of 0
             clears the alarm immediately."
    DEFVAL          { 3 }
    ::= { sonusPolicerDiscardRateProfileEntry 16 }

sonusPolicerDiscardRateProfileLightGraySetThreshold OBJECT-TYPE
    SYNTAX          Unsigned32 (0..2147483647)
    MAX-ACCESS      read-write
    STATUS          current
    DESCRIPTION     
            "The threshold for the aggregate lightGray policer discard rate which
             may set an alarm. A value of 0 disables the policer from causing
             an alarm."
    DEFVAL          { 20 }
    ::= { sonusPolicerDiscardRateProfileEntry 17 }

sonusPolicerDiscardRateProfileLightGrayClearThreshold OBJECT-TYPE
    SYNTAX          Unsigned32 (0..2147483647)
    MAX-ACCESS      read-write
    STATUS          current
    DESCRIPTION     
            "The threshold for the aggregate lightGray policer discard rate which
             may clear an alarm."
    DEFVAL          { 10 }
    ::= { sonusPolicerDiscardRateProfileEntry 18 }

sonusPolicerDiscardRateProfileLightGraySetDuration OBJECT-TYPE
    SYNTAX          Unsigned32 (0..65535)
    MAX-ACCESS      read-write
    STATUS          current
    DESCRIPTION     
            "The duration (in seconds) that the aggregate lightGray policer discard rate
             must be at or above its set threshold before an alarm is set. A value of 0
             sets the alarm immediately."
    DEFVAL          { 3 }
    ::= { sonusPolicerDiscardRateProfileEntry 19 }

sonusPolicerDiscardRateProfileLightGrayClearDuration OBJECT-TYPE
    SYNTAX          Unsigned32 (0..65535)
    MAX-ACCESS      read-write
    STATUS          current
    DESCRIPTION     
            "The duration (in seconds) that the aggregate lightGray policer discard rate
             must be at or below its clear threshold before an alarm is cleared. A value of 0
             clears the alarm immediately."
    DEFVAL          { 3 }
    ::= { sonusPolicerDiscardRateProfileEntry 20 }

sonusPolicerDiscardRateProfileVLanSetThreshold OBJECT-TYPE
    SYNTAX          Unsigned32 (0..2147483647)
    MAX-ACCESS      read-write
    STATUS          current
    DESCRIPTION     
            "The threshold for the aggregate VLan policer discard rate which
             may set an alarm. A value of 0 disables the policer from causing
             an alarm."
    DEFVAL          { 20 }
    ::= { sonusPolicerDiscardRateProfileEntry 21 }

sonusPolicerDiscardRateProfileVLanClearThreshold OBJECT-TYPE
    SYNTAX          Unsigned32 (0..2147483647)
    MAX-ACCESS      read-write
    STATUS          current
    DESCRIPTION     
            "The threshold for the aggregate VLan policer discard rate which
             may clear an alarm."
    DEFVAL          { 10 }
    ::= { sonusPolicerDiscardRateProfileEntry 22 }

sonusPolicerDiscardRateProfileVLanSetDuration OBJECT-TYPE
    SYNTAX          Unsigned32 (0..65535)
    MAX-ACCESS      read-write
    STATUS          current
    DESCRIPTION     
            "The duration (in seconds) that the aggregate VLan policer discard rate
             must be at or above its set threshold before an alarm is set. A value of 0
             sets the alarm immediately."
    DEFVAL          { 3 }
    ::= { sonusPolicerDiscardRateProfileEntry 23 }

sonusPolicerDiscardRateProfileVLanClearDuration OBJECT-TYPE
    SYNTAX          Unsigned32 (0..65535)
    MAX-ACCESS      read-write
    STATUS          current
    DESCRIPTION     
            "The duration (in seconds) that the aggregate VLan policer discard rate
             must be at or below its clear threshold before an alarm is cleared. A value of 0
             clears the alarm immediately."
    DEFVAL          { 3 }
    ::= { sonusPolicerDiscardRateProfileEntry 24 }

sonusPolicerDiscardRateProfileServerProtectSetThreshold OBJECT-TYPE
    SYNTAX          Unsigned32 (0..2147483647)
    MAX-ACCESS      read-write
    STATUS          current
    DESCRIPTION     
            "The threshold for the aggregate ServerProtect policer discard rate which
             may set an alarm. A value of 0 disables the policer from causing
             an alarm."
    DEFVAL          { 20 }
    ::= { sonusPolicerDiscardRateProfileEntry 25 }

sonusPolicerDiscardRateProfileServerProtectClearThreshold OBJECT-TYPE
    SYNTAX          Unsigned32 (0..2147483647)
    MAX-ACCESS      read-write
    STATUS          current
    DESCRIPTION     
            "The threshold for the aggregate ServerProtect policer discard rate which
             may clear an alarm."
    DEFVAL          { 10 }
    ::= { sonusPolicerDiscardRateProfileEntry 26 }

sonusPolicerDiscardRateProfileServerProtectSetDuration OBJECT-TYPE
    SYNTAX          Unsigned32 (0..65535)
    MAX-ACCESS      read-write
    STATUS          current
    DESCRIPTION     
            "The duration (in seconds) that the aggregate ServerProtect policer discard rate
             must be at or above its set threshold before an alarm is set. A value of 0
             sets the alarm immediately."
    DEFVAL          { 3 }
    ::= { sonusPolicerDiscardRateProfileEntry 27 }

sonusPolicerDiscardRateProfileServerProtectClearDuration OBJECT-TYPE
    SYNTAX          Unsigned32 (0..65535)
    MAX-ACCESS      read-write
    STATUS          current
    DESCRIPTION     
            "The duration (in seconds) that the aggregate ServerProtect policer discard rate
             must be at or below its clear threshold before an alarm is cleared. A value of 0
             clears the alarm immediately."
    DEFVAL          { 3 }
    ::= { sonusPolicerDiscardRateProfileEntry 28 }

sonusPolicerDiscardRateProfileMediaSetThreshold OBJECT-TYPE
    SYNTAX          Unsigned32 (0..2147483647)
    MAX-ACCESS      read-write
    STATUS          current
    DESCRIPTION     
            "The threshold for the aggregate media policer discard rate which
             may set an alarm. A value of 0 disables the policer from causing
             an alarm."
    DEFVAL          { 100 }
    ::= { sonusPolicerDiscardRateProfileEntry 29 }

sonusPolicerDiscardRateProfileMediaClearThreshold OBJECT-TYPE
    SYNTAX          Unsigned32 (0..2147483647)
    MAX-ACCESS      read-write
    STATUS          current
    DESCRIPTION     
            "The threshold for the aggregate media policer discard rate which
             may clear an alarm."
    DEFVAL          { 20 }
    ::= { sonusPolicerDiscardRateProfileEntry 30 }

sonusPolicerDiscardRateProfileMediaSetDuration OBJECT-TYPE
    SYNTAX          Unsigned32 (0..65535)
    MAX-ACCESS      read-write
    STATUS          current
    DESCRIPTION     
            "The duration (in seconds) that the aggregate media policer discard rate
             must be at or above its set threshold before an alarm is set. A value of 0
             sets the alarm immediately."
    DEFVAL          { 3 }
    ::= { sonusPolicerDiscardRateProfileEntry 31 }

sonusPolicerDiscardRateProfileMediaClearDuration OBJECT-TYPE
    SYNTAX          Unsigned32 (0..65535)
    MAX-ACCESS      read-write
    STATUS          current
    DESCRIPTION     
            "The duration (in seconds) that the aggregate media policer discard rate
             must be at or below its clear threshold before an alarm is cleared. A value of 0
             clears the alarm immediately."
    DEFVAL          { 3 }
    ::= { sonusPolicerDiscardRateProfileEntry 32 }

sonusPolicerDiscardRateProfileRogueUnallocPortSetThreshold OBJECT-TYPE
    SYNTAX          Unsigned32 (0..2147483647)
    MAX-ACCESS      read-write
    STATUS          current
    DESCRIPTION     
            "The threshold for the aggregate rogue media UnallocPort policer discard rate which
             may set an alarm. A value of 0 disables the policer from causing
             an alarm."
    DEFVAL          { 20 }
    ::= { sonusPolicerDiscardRateProfileEntry 33 }

sonusPolicerDiscardRateProfileRogueUnallocPortClearThreshold OBJECT-TYPE
    SYNTAX          Unsigned32 (0..2147483647)
    MAX-ACCESS      read-write
    STATUS          current
    DESCRIPTION     
            "The threshold for the aggregate rogue media UnallocPort policer discard rate which
             may clear an alarm."
    DEFVAL          { 10 }
    ::= { sonusPolicerDiscardRateProfileEntry 34 }

sonusPolicerDiscardRateProfileRogueUnallocPortSetDuration OBJECT-TYPE
    SYNTAX          Unsigned32 (0..65535)
    MAX-ACCESS      read-write
    STATUS          current
    DESCRIPTION     
            "The duration (in seconds) that the aggregate rogue media UnallocPort policer discard rate
             must be at or above its set threshold before an alarm is set. A value of 0
             sets the alarm immediately."
    DEFVAL          { 3 }
    ::= { sonusPolicerDiscardRateProfileEntry 35 }

sonusPolicerDiscardRateProfileRogueUnallocPortClearDuration OBJECT-TYPE
    SYNTAX          Unsigned32 (0..65535)
    MAX-ACCESS      read-write
    STATUS          current
    DESCRIPTION     
            "The duration (in seconds) that the aggregate rogue media UnallocPort policer discard rate
             must be at or below its clear threshold before an alarm is cleared. A value of 0
             clears the alarm immediately."
    DEFVAL          { 3 }
    ::= { sonusPolicerDiscardRateProfileEntry 36 }

sonusPolicerDiscardRateProfileRogueBadSrcSetThreshold OBJECT-TYPE
    SYNTAX          Unsigned32 (0..2147483647)
    MAX-ACCESS      read-write
    STATUS          current
    DESCRIPTION     
            "The threshold for the aggregate rogue media BadSrc policer discard rate which
             may set an alarm. A value of 0 disables the policer from causing
             an alarm."
    DEFVAL          { 20 }
    ::= { sonusPolicerDiscardRateProfileEntry 37 }

sonusPolicerDiscardRateProfileRogueBadSrcClearThreshold OBJECT-TYPE
    SYNTAX          Unsigned32 (0..2147483647)
    MAX-ACCESS      read-write
    STATUS          current
    DESCRIPTION     
            "The threshold for the aggregate rogue media BadSrc policer discard rate which
             may clear an alarm."
    DEFVAL          { 10 }
    ::= { sonusPolicerDiscardRateProfileEntry 38 }

sonusPolicerDiscardRateProfileRogueBadSrcSetDuration OBJECT-TYPE
    SYNTAX          Unsigned32 (0..65535)
    MAX-ACCESS      read-write
    STATUS          current
    DESCRIPTION     
            "The duration (in seconds) that the aggregate rogue media BadSrc policer discard rate
             must be at or above its set threshold before an alarm is set. A value of 0
             sets the alarm immediately."
    DEFVAL          { 3 }
    ::= { sonusPolicerDiscardRateProfileEntry 39 }

sonusPolicerDiscardRateProfileRogueBadSrcClearDuration OBJECT-TYPE
    SYNTAX          Unsigned32 (0..65535)
    MAX-ACCESS      read-write
    STATUS          current
    DESCRIPTION     
            "The duration (in seconds) that the aggregate rogue media BadSrc policer discard rate
             must be at or below its clear threshold before an alarm is cleared. A value of 0
             clears the alarm immediately."
    DEFVAL          { 3 }
    ::= { sonusPolicerDiscardRateProfileEntry 40 }

sonusPolicerDiscardRateProfileRogueBadDestSetThreshold OBJECT-TYPE
    SYNTAX          Unsigned32 (0..2147483647)
    MAX-ACCESS      read-write
    STATUS          current
    DESCRIPTION     
            "The threshold for the aggregate rogue media BadDest policer discard rate which
             may set an alarm. A value of 0 disables the policer from causing
             an alarm."
    DEFVAL          { 20 }
    ::= { sonusPolicerDiscardRateProfileEntry 41 }

sonusPolicerDiscardRateProfileRogueBadDestClearThreshold OBJECT-TYPE
    SYNTAX          Unsigned32 (0..2147483647)
    MAX-ACCESS      read-write
    STATUS          current
    DESCRIPTION     
            "The threshold for the aggregate rogue media BadDest policer discard rate which
             may clear an alarm."
    DEFVAL          { 10 }
    ::= { sonusPolicerDiscardRateProfileEntry 42 }

sonusPolicerDiscardRateProfileRogueBadDestSetDuration OBJECT-TYPE
    SYNTAX          Unsigned32 (0..65535)
    MAX-ACCESS      read-write
    STATUS          current
    DESCRIPTION     
            "The duration (in seconds) that the aggregate rogue media BadDest policer discard rate
             must be at or above its set threshold before an alarm is set. A value of 0
             sets the alarm immediately."
    DEFVAL          { 3 }
    ::= { sonusPolicerDiscardRateProfileEntry 43 }

sonusPolicerDiscardRateProfileRogueBadDestClearDuration OBJECT-TYPE
    SYNTAX          Unsigned32 (0..65535)
    MAX-ACCESS      read-write
    STATUS          current
    DESCRIPTION     
            "The duration (in seconds) that the aggregate rogue media BadDest policer discard rate
             must be at or below its clear threshold before an alarm is cleared. A value of 0
             clears the alarm immediately."
    DEFVAL          { 3 }
    ::= { sonusPolicerDiscardRateProfileEntry 44 }

sonusPolicerDiscardRateProfileRogueBadVLanSetThreshold OBJECT-TYPE
    SYNTAX          Unsigned32 (0..2147483647)
    MAX-ACCESS      read-write
    STATUS          current
    DESCRIPTION     
            "The threshold for the aggregate rogue media BadVLan policer discard rate which
             may set an alarm. A value of 0 disables the policer from causing
             an alarm."
    DEFVAL          { 20 }
    ::= { sonusPolicerDiscardRateProfileEntry 45 }

sonusPolicerDiscardRateProfileRogueBadVLanClearThreshold OBJECT-TYPE
    SYNTAX          Unsigned32 (0..2147483647)
    MAX-ACCESS      read-write
    STATUS          current
    DESCRIPTION     
            "The threshold for the aggregate rogue media BadVLan policer discard rate which
             may clear an alarm."
    DEFVAL          { 10 }
    ::= { sonusPolicerDiscardRateProfileEntry 46 }

sonusPolicerDiscardRateProfileRogueBadVLanSetDuration OBJECT-TYPE
    SYNTAX          Unsigned32 (0..65535)
    MAX-ACCESS      read-write
    STATUS          current
    DESCRIPTION     
            "The duration (in seconds) that the aggregate rogue media BadVLan policer discard rate
             must be at or above its set threshold before an alarm is set. A value of 0
             sets the alarm immediately."
    DEFVAL          { 3 }
    ::= { sonusPolicerDiscardRateProfileEntry 47 }

sonusPolicerDiscardRateProfileRogueBadVLanClearDuration OBJECT-TYPE
    SYNTAX          Unsigned32 (0..65535)
    MAX-ACCESS      read-write
    STATUS          current
    DESCRIPTION     
            "The duration (in seconds) that the aggregate rogue media BadVLan policer discard rate
             must be at or below its clear threshold before an alarm is cleared. A value of 0
             clears the alarm immediately."
    DEFVAL          { 3 }
    ::= { sonusPolicerDiscardRateProfileEntry 48 }

sonusSysPolicerAlarmAdmnTable OBJECT-TYPE
    SYNTAX          SEQUENCE OF SonusSysPolicerAlarmAdmnEntry
    MAX-ACCESS      not-accessible
    STATUS          current
    DESCRIPTION     
            ""
    ::= { sonusIpmMIBObjects 2 }

sonusSysPolicerAlarmAdmnEntry OBJECT-TYPE
    SYNTAX          SonusSysPolicerAlarmAdmnEntry
    MAX-ACCESS      not-accessible
    STATUS          current
    DESCRIPTION     
            ""
    INDEX           { sonusSysPolicerAlarmShelfIndex }
    ::= { sonusSysPolicerAlarmAdmnTable 1 }

SonusSysPolicerAlarmAdmnEntry ::=
    SEQUENCE {
        sonusSysPolicerAlarmShelfIndex  SonusShelfIndex,
        sonusSysPolicerAlarmMinorMode   SonusServiceState,
        sonusSysPolicerAlarmMajorMode   SonusServiceState,
        sonusSysPolicerAlarmMinorPolicerDiscardRateProfileName                      SonusNameReference,
        sonusSysPolicerAlarmMajorPolicerDiscardRateProfileName                      SonusNameReference,
        sonusSysPolicerAlarmRowStatus   RowStatus
    }

sonusSysPolicerAlarmShelfIndex OBJECT-TYPE
    SYNTAX          SonusShelfIndex
    MAX-ACCESS      read-write
    STATUS          current
    DESCRIPTION     
            "Identifies the target shelf/system for this entry."
    ::= { sonusSysPolicerAlarmAdmnEntry 1 }

sonusSysPolicerAlarmMinorMode OBJECT-TYPE
    SYNTAX          SonusServiceState
    MAX-ACCESS      read-write
    STATUS          current
    DESCRIPTION     
            "Maintenance/service mode for minor alarm notification."
    DEFVAL          { inService }
    ::= { sonusSysPolicerAlarmAdmnEntry 2 }

sonusSysPolicerAlarmMajorMode OBJECT-TYPE
    SYNTAX          SonusServiceState
    MAX-ACCESS      read-write
    STATUS          current
    DESCRIPTION     
            "Maintenance/service mode for major alarm notification."
    DEFVAL          { inService }
    ::= { sonusSysPolicerAlarmAdmnEntry 3 }

sonusSysPolicerAlarmMinorPolicerDiscardRateProfileName OBJECT-TYPE
    SYNTAX          SonusNameReference
    MAX-ACCESS      read-write
    STATUS          current
    DESCRIPTION     
            "The name of the policer discard rate profile for minor alarm notification."
    ::= { sonusSysPolicerAlarmAdmnEntry 4 }

sonusSysPolicerAlarmMajorPolicerDiscardRateProfileName OBJECT-TYPE
    SYNTAX          SonusNameReference
    MAX-ACCESS      read-write
    STATUS          current
    DESCRIPTION     
            "The name of the policer discard rate profile for major alarm notification."
    ::= { sonusSysPolicerAlarmAdmnEntry 5 }

sonusSysPolicerAlarmRowStatus OBJECT-TYPE
    SYNTAX          RowStatus
    MAX-ACCESS      read-write
    STATUS          current
    DESCRIPTION     
            ""
    ::= { sonusSysPolicerAlarmAdmnEntry 6 }

sonusServerPolicerAlarmAdmnTable OBJECT-TYPE
    SYNTAX          SEQUENCE OF SonusServerPolicerAlarmAdmnEntry
    MAX-ACCESS      not-accessible
    STATUS          current
    DESCRIPTION     
            ""
    ::= { sonusIpmMIBObjects 3 }

sonusServerPolicerAlarmAdmnEntry OBJECT-TYPE
    SYNTAX          SonusServerPolicerAlarmAdmnEntry
    MAX-ACCESS      not-accessible
    STATUS          current
    DESCRIPTION     
            ""
    INDEX           { sonusServerPolicerAlarmShelfId, 
                      sonusServerPolicerAlarmSlotId }
    ::= { sonusServerPolicerAlarmAdmnTable 1 }

SonusServerPolicerAlarmAdmnEntry ::=
    SEQUENCE {
        sonusServerPolicerAlarmShelfId  SonusShelfIndex,
        sonusServerPolicerAlarmSlotId   SonusSlotIndex,
        sonusServerPolicerAlarmMinorMode SonusServiceState,
        sonusServerPolicerAlarmMajorMode SonusServiceState,
        sonusServerPolicerAlarmMinorPolicerDiscardRateProfileName                         SonusNameReference,
        sonusServerPolicerAlarmMajorPolicerDiscardRateProfileName                         SonusNameReference,
        sonusServerPolicerAlarmRowStatus RowStatus
    }

sonusServerPolicerAlarmShelfId OBJECT-TYPE
    SYNTAX          SonusShelfIndex
    MAX-ACCESS      read-write
    STATUS          current
    DESCRIPTION     
            "Shelf index of the server."
    ::= { sonusServerPolicerAlarmAdmnEntry 1 }

sonusServerPolicerAlarmSlotId OBJECT-TYPE
    SYNTAX          SonusSlotIndex
    MAX-ACCESS      read-write
    STATUS          current
    DESCRIPTION     
            "Logical slot ID of the server."
    ::= { sonusServerPolicerAlarmAdmnEntry 2 }

sonusServerPolicerAlarmMinorMode OBJECT-TYPE
    SYNTAX          SonusServiceState
    MAX-ACCESS      read-write
    STATUS          current
    DESCRIPTION     
            "Maintenance/service mode for minor alarm notification."
    DEFVAL          { inService }
    ::= { sonusServerPolicerAlarmAdmnEntry 3 }

sonusServerPolicerAlarmMajorMode OBJECT-TYPE
    SYNTAX          SonusServiceState
    MAX-ACCESS      read-write
    STATUS          current
    DESCRIPTION     
            "Maintenance/service mode for major alarm notification."
    DEFVAL          { inService }
    ::= { sonusServerPolicerAlarmAdmnEntry 4 }

sonusServerPolicerAlarmMinorPolicerDiscardRateProfileName OBJECT-TYPE
    SYNTAX          SonusNameReference
    MAX-ACCESS      read-write
    STATUS          current
    DESCRIPTION     
            "The name of the policer discard rate profile for minor alarm notification."
    ::= { sonusServerPolicerAlarmAdmnEntry 5 }

sonusServerPolicerAlarmMajorPolicerDiscardRateProfileName OBJECT-TYPE
    SYNTAX          SonusNameReference
    MAX-ACCESS      read-write
    STATUS          current
    DESCRIPTION     
            "The name of the policer discard rate profile for major alarm notification."
    ::= { sonusServerPolicerAlarmAdmnEntry 6 }

sonusServerPolicerAlarmRowStatus OBJECT-TYPE
    SYNTAX          RowStatus
    MAX-ACCESS      read-write
    STATUS          current
    DESCRIPTION     
            ""
    ::= { sonusServerPolicerAlarmAdmnEntry 7 }

sonusSysPolicerAlarmStatTable OBJECT-TYPE
    SYNTAX          SEQUENCE OF SonusSysPolicerAlarmStatEntry
    MAX-ACCESS      not-accessible
    STATUS          current
    DESCRIPTION     
            ""
    ::= { sonusIpmMIBObjects 4 }

sonusSysPolicerAlarmStatEntry OBJECT-TYPE
    SYNTAX          SonusSysPolicerAlarmStatEntry
    MAX-ACCESS      not-accessible
    STATUS          current
    DESCRIPTION     
            ""
    INDEX           { sonusSysPolicerAlarmStatShelfIndex }
    ::= { sonusSysPolicerAlarmStatTable 1 }

SonusSysPolicerAlarmStatEntry ::=
    SEQUENCE {
        sonusSysPolicerAlarmStatShelfIndex  SonusShelfIndex,
        sonusSysPolicerAlarmStatWhiteAlarmLevel       INTEGER,
        sonusSysPolicerAlarmStatWhiteAlarmDuration          Unsigned32,
        sonusSysPolicerAlarmStatWhiteDiscardRate        Unsigned32,
        sonusSysPolicerAlarmStatWhitePacketsDiscard           Counter64,
        sonusSysPolicerAlarmStatBlackAlarmLevel       INTEGER,
        sonusSysPolicerAlarmStatBlackAlarmDuration          Unsigned32,
        sonusSysPolicerAlarmStatBlackDiscardRate        Unsigned32,
        sonusSysPolicerAlarmStatBlackPacketsDiscard           Counter64,
        sonusSysPolicerAlarmStatDarkGrayAlarmLevel          INTEGER,
        sonusSysPolicerAlarmStatDarkGrayAlarmDuration             Unsigned32,
        sonusSysPolicerAlarmStatDarkGrayDiscardRate           Unsigned32,
        sonusSysPolicerAlarmStatDarkGrayPacketsAccept             Counter64,
        sonusSysPolicerAlarmStatDarkGrayPacketsDiscard              Counter64,
        sonusSysPolicerAlarmStatLightGrayAlarmLevel           INTEGER,
        sonusSysPolicerAlarmStatLightGrayAlarmDuration              Unsigned32,
        sonusSysPolicerAlarmStatLightGrayDiscardRate            Unsigned32,
        sonusSysPolicerAlarmStatLightGrayPacketsDiscard               Counter64,
        sonusSysPolicerAlarmStatVLanAlarmLevel      INTEGER,
        sonusSysPolicerAlarmStatVLanAlarmDuration         Unsigned32,
        sonusSysPolicerAlarmStatVLanDiscardRate       Unsigned32,
        sonusSysPolicerAlarmStatVLanPacketsDiscard          Counter64,
        sonusSysPolicerAlarmStatServerProtectAlarmLevel               INTEGER,
        sonusSysPolicerAlarmStatServerProtectAlarmDuration                  Unsigned32,
        sonusSysPolicerAlarmStatServerProtectDiscardRate                Unsigned32,
        sonusSysPolicerAlarmStatServerProtectPacketsAccept                  Counter64,
        sonusSysPolicerAlarmStatServerProtectPacketsDiscard                   Counter64,
        sonusSysPolicerAlarmStatMediaAlarmLevel       INTEGER,
        sonusSysPolicerAlarmStatMediaAlarmDuration          Unsigned32,
        sonusSysPolicerAlarmStatMediaDiscardRate        Unsigned32,
        sonusSysPolicerAlarmStatMediaPacketsDiscard           Counter64,
        sonusSysPolicerAlarmStatRogueUnallocPortAlarmLevel                  INTEGER,
        sonusSysPolicerAlarmStatRogueUnallocPortAlarmDuration                     Unsigned32,
        sonusSysPolicerAlarmStatRogueUnallocPortDiscardRate                   Unsigned32,
        sonusSysPolicerAlarmStatRogueUnallocPortPacketsDiscard                      Counter64,
        sonusSysPolicerAlarmStatRogueBadSrcAlarmLevel             INTEGER,
        sonusSysPolicerAlarmStatRogueBadSrcAlarmDuration                Unsigned32,
        sonusSysPolicerAlarmStatRogueBadSrcDiscardRate              Unsigned32,
        sonusSysPolicerAlarmStatRogueBadSrcPacketsDiscard                 Counter64,
        sonusSysPolicerAlarmStatRogueBadDestAlarmLevel              INTEGER,
        sonusSysPolicerAlarmStatRogueBadDestAlarmDuration                 Unsigned32,
        sonusSysPolicerAlarmStatRogueBadDestDiscardRate               Unsigned32,
        sonusSysPolicerAlarmStatRogueBadDestPacketsDiscard                  Counter64,
        sonusSysPolicerAlarmStatRogueBadVLanAlarmLevel              INTEGER,
        sonusSysPolicerAlarmStatRogueBadVLanAlarmDuration                 Unsigned32,
        sonusSysPolicerAlarmStatRogueBadVLanDiscardRate               Unsigned32,
        sonusSysPolicerAlarmStatRogueBadVLanPacketsDiscard                  Counter64,
        sonusSysPolicerAlarmStatRogueInGracePeriodDiscardRate                     Unsigned32,
        sonusSysPolicerAlarmStatRogueInGracePeriodPacketsDiscard                        Counter64
    }

sonusSysPolicerAlarmStatShelfIndex OBJECT-TYPE
    SYNTAX          SonusShelfIndex
    MAX-ACCESS      read-only
    STATUS          current
    DESCRIPTION     
            "Shelf Index of the system."
    ::= { sonusSysPolicerAlarmStatEntry 1 }

sonusSysPolicerAlarmStatWhiteAlarmLevel OBJECT-TYPE
    SYNTAX          INTEGER { noAlarm(1), minorAlarm(2), majorAlarm(3) }
    MAX-ACCESS      read-only
    STATUS          current
    DESCRIPTION     
            "System white policer alarm level."
    ::= { sonusSysPolicerAlarmStatEntry 2 }

sonusSysPolicerAlarmStatWhiteAlarmDuration OBJECT-TYPE
    SYNTAX          Unsigned32
    MAX-ACCESS      read-only
    STATUS          current
    DESCRIPTION     
            "Number of seconds the system white policer alarm has been at this level."
    ::= { sonusSysPolicerAlarmStatEntry 3 }

sonusSysPolicerAlarmStatWhiteDiscardRate OBJECT-TYPE
    SYNTAX          Unsigned32
    MAX-ACCESS      read-only
    STATUS          current
    DESCRIPTION     
            "Current rate of white discards for the system."
    ::= { sonusSysPolicerAlarmStatEntry 4 }

sonusSysPolicerAlarmStatWhitePacketsDiscard OBJECT-TYPE
    SYNTAX          Counter64
    MAX-ACCESS      read-only
    STATUS          current
    DESCRIPTION     
            "Total number of packets discarded by white policers in system."
    ::= { sonusSysPolicerAlarmStatEntry 5 }

sonusSysPolicerAlarmStatBlackAlarmLevel OBJECT-TYPE
    SYNTAX          INTEGER { noAlarm(1), minorAlarm(2), majorAlarm(3) }
    MAX-ACCESS      read-only
    STATUS          current
    DESCRIPTION     
            "System black policer alarm level."
    ::= { sonusSysPolicerAlarmStatEntry 6 }

sonusSysPolicerAlarmStatBlackAlarmDuration OBJECT-TYPE
    SYNTAX          Unsigned32
    MAX-ACCESS      read-only
    STATUS          current
    DESCRIPTION     
            "Number of seconds the system black policer alarm has been at this level."
    ::= { sonusSysPolicerAlarmStatEntry 7 }

sonusSysPolicerAlarmStatBlackDiscardRate OBJECT-TYPE
    SYNTAX          Unsigned32
    MAX-ACCESS      read-only
    STATUS          current
    DESCRIPTION     
            "Current rate of black discards for the system."
    ::= { sonusSysPolicerAlarmStatEntry 8 }

sonusSysPolicerAlarmStatBlackPacketsDiscard OBJECT-TYPE
    SYNTAX          Counter64
    MAX-ACCESS      read-only
    STATUS          current
    DESCRIPTION     
            "Total number of packets discarded by black policers in system."
    ::= { sonusSysPolicerAlarmStatEntry 9 }

sonusSysPolicerAlarmStatDarkGrayAlarmLevel OBJECT-TYPE
    SYNTAX          INTEGER { noAlarm(1), minorAlarm(2), majorAlarm(3) }
    MAX-ACCESS      read-only
    STATUS          current
    DESCRIPTION     
            "System DarkGray policer alarm level."
    ::= { sonusSysPolicerAlarmStatEntry 10 }

sonusSysPolicerAlarmStatDarkGrayAlarmDuration OBJECT-TYPE
    SYNTAX          Unsigned32
    MAX-ACCESS      read-only
    STATUS          current
    DESCRIPTION     
            "Number of seconds the system DarkGray policer alarm has been at this level."
    ::= { sonusSysPolicerAlarmStatEntry 11 }

sonusSysPolicerAlarmStatDarkGrayDiscardRate OBJECT-TYPE
    SYNTAX          Unsigned32
    MAX-ACCESS      read-only
    STATUS          current
    DESCRIPTION     
            "Current rate of DarkGray discards for the system."
    ::= { sonusSysPolicerAlarmStatEntry 12 }

sonusSysPolicerAlarmStatDarkGrayPacketsAccept OBJECT-TYPE
    SYNTAX          Counter64
    MAX-ACCESS      read-only
    STATUS          current
    DESCRIPTION     
            "Total number of packets accepted by DarkGray policers in system."
    ::= { sonusSysPolicerAlarmStatEntry 13 }

sonusSysPolicerAlarmStatDarkGrayPacketsDiscard OBJECT-TYPE
    SYNTAX          Counter64
    MAX-ACCESS      read-only
    STATUS          current
    DESCRIPTION     
            "Total number of packets discarded by DarkGray policers in system."
    ::= { sonusSysPolicerAlarmStatEntry 14 }

sonusSysPolicerAlarmStatLightGrayAlarmLevel OBJECT-TYPE
    SYNTAX          INTEGER { noAlarm(1), minorAlarm(2), majorAlarm(3) }
    MAX-ACCESS      read-only
    STATUS          current
    DESCRIPTION     
            "System LightGray policer alarm level."
    ::= { sonusSysPolicerAlarmStatEntry 15 }

sonusSysPolicerAlarmStatLightGrayAlarmDuration OBJECT-TYPE
    SYNTAX          Unsigned32
    MAX-ACCESS      read-only
    STATUS          current
    DESCRIPTION     
            "Number of seconds the system LightGray policer alarm has been at this level."
    ::= { sonusSysPolicerAlarmStatEntry 16 }

sonusSysPolicerAlarmStatLightGrayDiscardRate OBJECT-TYPE
    SYNTAX          Unsigned32
    MAX-ACCESS      read-only
    STATUS          current
    DESCRIPTION     
            "Current rate of LightGray discards for the system."
    ::= { sonusSysPolicerAlarmStatEntry 17 }

sonusSysPolicerAlarmStatLightGrayPacketsDiscard OBJECT-TYPE
    SYNTAX          Counter64
    MAX-ACCESS      read-only
    STATUS          current
    DESCRIPTION     
            "Total number of packets discarded by LightGray policers in system."
    ::= { sonusSysPolicerAlarmStatEntry 18 }

sonusSysPolicerAlarmStatVLanAlarmLevel OBJECT-TYPE
    SYNTAX          INTEGER { noAlarm(1), minorAlarm(2), majorAlarm(3) }
    MAX-ACCESS      read-only
    STATUS          current
    DESCRIPTION     
            "System VLan policer alarm level."
    ::= { sonusSysPolicerAlarmStatEntry 19 }

sonusSysPolicerAlarmStatVLanAlarmDuration OBJECT-TYPE
    SYNTAX          Unsigned32
    MAX-ACCESS      read-only
    STATUS          current
    DESCRIPTION     
            "Number of seconds the system VLan policer alarm has been at this level."
    ::= { sonusSysPolicerAlarmStatEntry 20 }

sonusSysPolicerAlarmStatVLanDiscardRate OBJECT-TYPE
    SYNTAX          Unsigned32
    MAX-ACCESS      read-only
    STATUS          current
    DESCRIPTION     
            "Current rate of VLan discards for the system."
    ::= { sonusSysPolicerAlarmStatEntry 21 }

sonusSysPolicerAlarmStatVLanPacketsDiscard OBJECT-TYPE
    SYNTAX          Counter64
    MAX-ACCESS      read-only
    STATUS          current
    DESCRIPTION     
            "Total number of packets discarded by VLan policers in system."
    ::= { sonusSysPolicerAlarmStatEntry 22 }

sonusSysPolicerAlarmStatServerProtectAlarmLevel OBJECT-TYPE
    SYNTAX          INTEGER { noAlarm(1), minorAlarm(2), majorAlarm(3) }
    MAX-ACCESS      read-only
    STATUS          current
    DESCRIPTION     
            "System ServerProtect policer alarm level."
    ::= { sonusSysPolicerAlarmStatEntry 23 }

sonusSysPolicerAlarmStatServerProtectAlarmDuration OBJECT-TYPE
    SYNTAX          Unsigned32
    MAX-ACCESS      read-only
    STATUS          current
    DESCRIPTION     
            "Number of seconds the system ServerProtect policer alarm has been at this level."
    ::= { sonusSysPolicerAlarmStatEntry 24 }

sonusSysPolicerAlarmStatServerProtectDiscardRate OBJECT-TYPE
    SYNTAX          Unsigned32
    MAX-ACCESS      read-only
    STATUS          current
    DESCRIPTION     
            "Current rate of ServerProtect discards for the system."
    ::= { sonusSysPolicerAlarmStatEntry 25 }

sonusSysPolicerAlarmStatServerProtectPacketsAccept OBJECT-TYPE
    SYNTAX          Counter64
    MAX-ACCESS      read-only
    STATUS          current
    DESCRIPTION     
            "Total number of packets accepted by ServerProtect policers in system."
    ::= { sonusSysPolicerAlarmStatEntry 26 }

sonusSysPolicerAlarmStatServerProtectPacketsDiscard OBJECT-TYPE
    SYNTAX          Counter64
    MAX-ACCESS      read-only
    STATUS          current
    DESCRIPTION     
            "Total number of packets discarded by ServerProtect policers in system."
    ::= { sonusSysPolicerAlarmStatEntry 27 }

sonusSysPolicerAlarmStatMediaAlarmLevel OBJECT-TYPE
    SYNTAX          INTEGER { noAlarm(1), minorAlarm(2), majorAlarm(3) }
    MAX-ACCESS      read-only
    STATUS          current
    DESCRIPTION     
            "System media policer alarm level."
    ::= { sonusSysPolicerAlarmStatEntry 28 }

sonusSysPolicerAlarmStatMediaAlarmDuration OBJECT-TYPE
    SYNTAX          Unsigned32
    MAX-ACCESS      read-only
    STATUS          current
    DESCRIPTION     
            "Number of seconds the system media policer alarm has been at this level."
    ::= { sonusSysPolicerAlarmStatEntry 29 }

sonusSysPolicerAlarmStatMediaDiscardRate OBJECT-TYPE
    SYNTAX          Unsigned32
    MAX-ACCESS      read-only
    STATUS          current
    DESCRIPTION     
            "Current rate of media discards for the system."
    ::= { sonusSysPolicerAlarmStatEntry 30 }

sonusSysPolicerAlarmStatMediaPacketsDiscard OBJECT-TYPE
    SYNTAX          Counter64
    MAX-ACCESS      read-only
    STATUS          current
    DESCRIPTION     
            "Total number of packets discarded by media policers in system."
    ::= { sonusSysPolicerAlarmStatEntry 31 }

sonusSysPolicerAlarmStatRogueUnallocPortAlarmLevel OBJECT-TYPE
    SYNTAX          INTEGER { noAlarm(1), minorAlarm(2), majorAlarm(3) }
    MAX-ACCESS      read-only
    STATUS          current
    DESCRIPTION     
            "System RogueUnallocPort policer alarm level."
    ::= { sonusSysPolicerAlarmStatEntry 32 }

sonusSysPolicerAlarmStatRogueUnallocPortAlarmDuration OBJECT-TYPE
    SYNTAX          Unsigned32
    MAX-ACCESS      read-only
    STATUS          current
    DESCRIPTION     
            "Number of seconds the system RogueUnallocPort policer alarm has been at this level."
    ::= { sonusSysPolicerAlarmStatEntry 33 }

sonusSysPolicerAlarmStatRogueUnallocPortDiscardRate OBJECT-TYPE
    SYNTAX          Unsigned32
    MAX-ACCESS      read-only
    STATUS          current
    DESCRIPTION     
            "Current rate of RogueUnallocPort discards for the system."
    ::= { sonusSysPolicerAlarmStatEntry 34 }

sonusSysPolicerAlarmStatRogueUnallocPortPacketsDiscard OBJECT-TYPE
    SYNTAX          Counter64
    MAX-ACCESS      read-only
    STATUS          current
    DESCRIPTION     
            "Total number of packets discarded by RogueUnallocPort policers in system."
    ::= { sonusSysPolicerAlarmStatEntry 35 }

sonusSysPolicerAlarmStatRogueBadSrcAlarmLevel OBJECT-TYPE
    SYNTAX          INTEGER { noAlarm(1), minorAlarm(2), majorAlarm(3) }
    MAX-ACCESS      read-only
    STATUS          current
    DESCRIPTION     
            "System RogueBadSrc policer alarm level."
    ::= { sonusSysPolicerAlarmStatEntry 36 }

sonusSysPolicerAlarmStatRogueBadSrcAlarmDuration OBJECT-TYPE
    SYNTAX          Unsigned32
    MAX-ACCESS      read-only
    STATUS          current
    DESCRIPTION     
            "Number of seconds the system RogueBadSrc policer alarm has been at this level."
    ::= { sonusSysPolicerAlarmStatEntry 37 }

sonusSysPolicerAlarmStatRogueBadSrcDiscardRate OBJECT-TYPE
    SYNTAX          Unsigned32
    MAX-ACCESS      read-only
    STATUS          current
    DESCRIPTION     
            "Current rate of RogueBadSrc discards for the system."
    ::= { sonusSysPolicerAlarmStatEntry 38 }

sonusSysPolicerAlarmStatRogueBadSrcPacketsDiscard OBJECT-TYPE
    SYNTAX          Counter64
    MAX-ACCESS      read-only
    STATUS          current
    DESCRIPTION     
            "Total number of packets discarded by RogueBadSrc policers in system."
    ::= { sonusSysPolicerAlarmStatEntry 39 }

sonusSysPolicerAlarmStatRogueBadDestAlarmLevel OBJECT-TYPE
    SYNTAX          INTEGER { noAlarm(1), minorAlarm(2), majorAlarm(3) }
    MAX-ACCESS      read-only
    STATUS          current
    DESCRIPTION     
            "System RogueBadDest policer alarm level."
    ::= { sonusSysPolicerAlarmStatEntry 40 }

sonusSysPolicerAlarmStatRogueBadDestAlarmDuration OBJECT-TYPE
    SYNTAX          Unsigned32
    MAX-ACCESS      read-only
    STATUS          current
    DESCRIPTION     
            "Number of seconds the system RogueBadDest policer alarm has been at this level."
    ::= { sonusSysPolicerAlarmStatEntry 41 }

sonusSysPolicerAlarmStatRogueBadDestDiscardRate OBJECT-TYPE
    SYNTAX          Unsigned32
    MAX-ACCESS      read-only
    STATUS          current
    DESCRIPTION     
            "Current rate of RogueBadDest discards for the system."
    ::= { sonusSysPolicerAlarmStatEntry 42 }

sonusSysPolicerAlarmStatRogueBadDestPacketsDiscard OBJECT-TYPE
    SYNTAX          Counter64
    MAX-ACCESS      read-only
    STATUS          current
    DESCRIPTION     
            "Total number of packets discarded by RogueBadDest policers in system."
    ::= { sonusSysPolicerAlarmStatEntry 43 }

sonusSysPolicerAlarmStatRogueBadVLanAlarmLevel OBJECT-TYPE
    SYNTAX          INTEGER { noAlarm(1), minorAlarm(2), majorAlarm(3) }
    MAX-ACCESS      read-only
    STATUS          current
    DESCRIPTION     
            "System RogueBadVLan policer alarm level."
    ::= { sonusSysPolicerAlarmStatEntry 44 }

sonusSysPolicerAlarmStatRogueBadVLanAlarmDuration OBJECT-TYPE
    SYNTAX          Unsigned32
    MAX-ACCESS      read-only
    STATUS          current
    DESCRIPTION     
            "Number of seconds the system RogueBadVLan policer alarm has been at this level."
    ::= { sonusSysPolicerAlarmStatEntry 45 }

sonusSysPolicerAlarmStatRogueBadVLanDiscardRate OBJECT-TYPE
    SYNTAX          Unsigned32
    MAX-ACCESS      read-only
    STATUS          current
    DESCRIPTION     
            "Current rate of RogueBadVLan discards for the system."
    ::= { sonusSysPolicerAlarmStatEntry 46 }

sonusSysPolicerAlarmStatRogueBadVLanPacketsDiscard OBJECT-TYPE
    SYNTAX          Counter64
    MAX-ACCESS      read-only
    STATUS          current
    DESCRIPTION     
            "Total number of packets discarded by RogueBadVLan policers in system."
    ::= { sonusSysPolicerAlarmStatEntry 47 }

sonusSysPolicerAlarmStatRogueInGracePeriodDiscardRate OBJECT-TYPE
    SYNTAX          Unsigned32
    MAX-ACCESS      read-only
    STATUS          current
    DESCRIPTION     
            "Current rate of RogueInGracePeriod discards for the system."
    ::= { sonusSysPolicerAlarmStatEntry 48 }

sonusSysPolicerAlarmStatRogueInGracePeriodPacketsDiscard OBJECT-TYPE
    SYNTAX          Counter64
    MAX-ACCESS      read-only
    STATUS          current
    DESCRIPTION     
            "Total number of packets discarded by RogueInGracePeriod policers in system."
    ::= { sonusSysPolicerAlarmStatEntry 49 }

sonusServerPolicerAlarmStatTable OBJECT-TYPE
    SYNTAX          SEQUENCE OF SonusServerPolicerAlarmStatEntry
    MAX-ACCESS      not-accessible
    STATUS          current
    DESCRIPTION     
            ""
    ::= { sonusIpmMIBObjects 5 }

sonusServerPolicerAlarmStatEntry OBJECT-TYPE
    SYNTAX          SonusServerPolicerAlarmStatEntry
    MAX-ACCESS      not-accessible
    STATUS          current
    DESCRIPTION     
            ""
    INDEX           { sonusServerPolicerAlarmStatShelfIndex, 
                      sonusServerPolicerAlarmStatSlotIndex }
    ::= { sonusServerPolicerAlarmStatTable 1 }

SonusServerPolicerAlarmStatEntry ::=
    SEQUENCE {
        sonusServerPolicerAlarmStatShelfIndex     SonusShelfIndex,
        sonusServerPolicerAlarmStatSlotIndex    SonusSlotIndex,
        sonusServerPolicerAlarmStatWhiteAlarmLevel          INTEGER,
        sonusServerPolicerAlarmStatWhiteAlarmDuration             Unsigned32,
        sonusServerPolicerAlarmStatWhiteDiscardRate           Unsigned32,
        sonusServerPolicerAlarmStatWhitePacketsDiscard              Counter64,
        sonusServerPolicerAlarmStatBlackAlarmLevel          INTEGER,
        sonusServerPolicerAlarmStatBlackAlarmDuration             Unsigned32,
        sonusServerPolicerAlarmStatBlackDiscardRate           Unsigned32,
        sonusServerPolicerAlarmStatBlackPacketsDiscard              Counter64,
        sonusServerPolicerAlarmStatDarkGrayAlarmLevel             INTEGER,
        sonusServerPolicerAlarmStatDarkGrayAlarmDuration                Unsigned32,
        sonusServerPolicerAlarmStatDarkGrayDiscardRate              Unsigned32,
        sonusServerPolicerAlarmStatDarkGrayPacketsAccept                Counter64,
        sonusServerPolicerAlarmStatDarkGrayPacketsDiscard                 Counter64,
        sonusServerPolicerAlarmStatLightGrayAlarmLevel              INTEGER,
        sonusServerPolicerAlarmStatLightGrayAlarmDuration                 Unsigned32,
        sonusServerPolicerAlarmStatLightGrayDiscardRate               Unsigned32,
        sonusServerPolicerAlarmStatLightGrayPacketsDiscard                  Counter64,
        sonusServerPolicerAlarmStatVLanAlarmLevel         INTEGER,
        sonusServerPolicerAlarmStatVLanAlarmDuration            Unsigned32,
        sonusServerPolicerAlarmStatVLanDiscardRate          Unsigned32,
        sonusServerPolicerAlarmStatVLanPacketsDiscard             Counter64,
        sonusServerPolicerAlarmStatServerProtectAlarmLevel                  INTEGER,
        sonusServerPolicerAlarmStatServerProtectAlarmDuration                     Unsigned32,
        sonusServerPolicerAlarmStatServerProtectDiscardRate                   Unsigned32,
        sonusServerPolicerAlarmStatServerProtectPacketsAccept                     Counter64,
        sonusServerPolicerAlarmStatServerProtectPacketsDiscard                      Counter64,
        sonusServerPolicerAlarmStatMediaAlarmLevel          INTEGER,
        sonusServerPolicerAlarmStatMediaAlarmDuration             Unsigned32,
        sonusServerPolicerAlarmStatMediaDiscardRate           Unsigned32,
        sonusServerPolicerAlarmStatMediaPacketsDiscard              Counter64,
        sonusServerPolicerAlarmStatRogueUnallocPortAlarmLevel                     INTEGER,
        sonusServerPolicerAlarmStatRogueUnallocPortAlarmDuration                        Unsigned32,
        sonusServerPolicerAlarmStatRogueUnallocPortDiscardRate                      Unsigned32,
        sonusServerPolicerAlarmStatRogueUnallocPortPacketsDiscard                         Counter64,
        sonusServerPolicerAlarmStatRogueBadSrcAlarmLevel                INTEGER,
        sonusServerPolicerAlarmStatRogueBadSrcAlarmDuration                   Unsigned32,
        sonusServerPolicerAlarmStatRogueBadSrcDiscardRate                 Unsigned32,
        sonusServerPolicerAlarmStatRogueBadSrcPacketsDiscard                    Counter64,
        sonusServerPolicerAlarmStatRogueBadDestAlarmLevel                 INTEGER,
        sonusServerPolicerAlarmStatRogueBadDestAlarmDuration                    Unsigned32,
        sonusServerPolicerAlarmStatRogueBadDestDiscardRate                  Unsigned32,
        sonusServerPolicerAlarmStatRogueBadDestPacketsDiscard                     Counter64,
        sonusServerPolicerAlarmStatRogueBadVLanAlarmLevel                 INTEGER,
        sonusServerPolicerAlarmStatRogueBadVLanAlarmDuration                    Unsigned32,
        sonusServerPolicerAlarmStatRogueBadVLanDiscardRate                  Unsigned32,
        sonusServerPolicerAlarmStatRogueBadVLanPacketsDiscard                     Counter64,
        sonusServerPolicerAlarmStatRogueInGracePeriodDiscardRate                        Unsigned32,
        sonusServerPolicerAlarmStatRogueInGracePeriodPacketsDiscard                           Counter64
    }

sonusServerPolicerAlarmStatShelfIndex OBJECT-TYPE
    SYNTAX          SonusShelfIndex
    MAX-ACCESS      read-only
    STATUS          current
    DESCRIPTION     
            "Shelf index of the server."
    ::= { sonusServerPolicerAlarmStatEntry 1 }

sonusServerPolicerAlarmStatSlotIndex OBJECT-TYPE
    SYNTAX          SonusSlotIndex
    MAX-ACCESS      read-only
    STATUS          current
    DESCRIPTION     
            "Slot index of the server."
    ::= { sonusServerPolicerAlarmStatEntry 2 }

sonusServerPolicerAlarmStatWhiteAlarmLevel OBJECT-TYPE
    SYNTAX          INTEGER { noAlarm(1), minorAlarm(2), majorAlarm(3) }
    MAX-ACCESS      read-only
    STATUS          current
    DESCRIPTION     
            "Server white policer alarm level."
    ::= { sonusServerPolicerAlarmStatEntry 3 }

sonusServerPolicerAlarmStatWhiteAlarmDuration OBJECT-TYPE
    SYNTAX          Unsigned32
    MAX-ACCESS      read-only
    STATUS          current
    DESCRIPTION     
            "Number of seconds the server white policer alarm has been at this level."
    ::= { sonusServerPolicerAlarmStatEntry 4 }

sonusServerPolicerAlarmStatWhiteDiscardRate OBJECT-TYPE
    SYNTAX          Unsigned32
    MAX-ACCESS      read-only
    STATUS          current
    DESCRIPTION     
            "Current rate of white discards for the server."
    ::= { sonusServerPolicerAlarmStatEntry 5 }

sonusServerPolicerAlarmStatWhitePacketsDiscard OBJECT-TYPE
    SYNTAX          Counter64
    MAX-ACCESS      read-only
    STATUS          current
    DESCRIPTION     
            "Total number of packets discarded by white policers on server."
    ::= { sonusServerPolicerAlarmStatEntry 6 }

sonusServerPolicerAlarmStatBlackAlarmLevel OBJECT-TYPE
    SYNTAX          INTEGER { noAlarm(1), minorAlarm(2), majorAlarm(3) }
    MAX-ACCESS      read-only
    STATUS          current
    DESCRIPTION     
            "Server black policer alarm level."
    ::= { sonusServerPolicerAlarmStatEntry 7 }

sonusServerPolicerAlarmStatBlackAlarmDuration OBJECT-TYPE
    SYNTAX          Unsigned32
    MAX-ACCESS      read-only
    STATUS          current
    DESCRIPTION     
            "Number of seconds the server black policer alarm has been at this level."
    ::= { sonusServerPolicerAlarmStatEntry 8 }

sonusServerPolicerAlarmStatBlackDiscardRate OBJECT-TYPE
    SYNTAX          Unsigned32
    MAX-ACCESS      read-only
    STATUS          current
    DESCRIPTION     
            "Current rate of black discards for the server."
    ::= { sonusServerPolicerAlarmStatEntry 9 }

sonusServerPolicerAlarmStatBlackPacketsDiscard OBJECT-TYPE
    SYNTAX          Counter64
    MAX-ACCESS      read-only
    STATUS          current
    DESCRIPTION     
            "Total number of packets discarded by black policers on server."
    ::= { sonusServerPolicerAlarmStatEntry 10 }

sonusServerPolicerAlarmStatDarkGrayAlarmLevel OBJECT-TYPE
    SYNTAX          INTEGER { noAlarm(1), minorAlarm(2), majorAlarm(3) }
    MAX-ACCESS      read-only
    STATUS          current
    DESCRIPTION     
            "Server DarkGray policer alarm level."
    ::= { sonusServerPolicerAlarmStatEntry 11 }

sonusServerPolicerAlarmStatDarkGrayAlarmDuration OBJECT-TYPE
    SYNTAX          Unsigned32
    MAX-ACCESS      read-only
    STATUS          current
    DESCRIPTION     
            "Number of seconds the server DarkGray policer alarm has been at this level."
    ::= { sonusServerPolicerAlarmStatEntry 12 }

sonusServerPolicerAlarmStatDarkGrayDiscardRate OBJECT-TYPE
    SYNTAX          Unsigned32
    MAX-ACCESS      read-only
    STATUS          current
    DESCRIPTION     
            "Current rate of DarkGray discards for the server."
    ::= { sonusServerPolicerAlarmStatEntry 13 }

sonusServerPolicerAlarmStatDarkGrayPacketsAccept OBJECT-TYPE
    SYNTAX          Counter64
    MAX-ACCESS      read-only
    STATUS          current
    DESCRIPTION     
            "Total number of packets accepted by DarkGray policers on server."
    ::= { sonusServerPolicerAlarmStatEntry 14 }

sonusServerPolicerAlarmStatDarkGrayPacketsDiscard OBJECT-TYPE
    SYNTAX          Counter64
    MAX-ACCESS      read-only
    STATUS          current
    DESCRIPTION     
            "Total number of packets discarded by DarkGray policers on server."
    ::= { sonusServerPolicerAlarmStatEntry 15 }

sonusServerPolicerAlarmStatLightGrayAlarmLevel OBJECT-TYPE
    SYNTAX          INTEGER { noAlarm(1), minorAlarm(2), majorAlarm(3) }
    MAX-ACCESS      read-only
    STATUS          current
    DESCRIPTION     
            "Server LightGray policer alarm level."
    ::= { sonusServerPolicerAlarmStatEntry 16 }

sonusServerPolicerAlarmStatLightGrayAlarmDuration OBJECT-TYPE
    SYNTAX          Unsigned32
    MAX-ACCESS      read-only
    STATUS          current
    DESCRIPTION     
            "Number of seconds the server LightGray policer alarm has been at this level."
    ::= { sonusServerPolicerAlarmStatEntry 17 }

sonusServerPolicerAlarmStatLightGrayDiscardRate OBJECT-TYPE
    SYNTAX          Unsigned32
    MAX-ACCESS      read-only
    STATUS          current
    DESCRIPTION     
            "Current rate of LightGray discards for the server."
    ::= { sonusServerPolicerAlarmStatEntry 18 }

sonusServerPolicerAlarmStatLightGrayPacketsDiscard OBJECT-TYPE
    SYNTAX          Counter64
    MAX-ACCESS      read-only
    STATUS          current
    DESCRIPTION     
            "Total number of packets discarded by LightGray policers on server."
    ::= { sonusServerPolicerAlarmStatEntry 19 }

sonusServerPolicerAlarmStatVLanAlarmLevel OBJECT-TYPE
    SYNTAX          INTEGER { noAlarm(1), minorAlarm(2), majorAlarm(3) }
    MAX-ACCESS      read-only
    STATUS          current
    DESCRIPTION     
            "Server VLan policer alarm level."
    ::= { sonusServerPolicerAlarmStatEntry 20 }

sonusServerPolicerAlarmStatVLanAlarmDuration OBJECT-TYPE
    SYNTAX          Unsigned32
    MAX-ACCESS      read-only
    STATUS          current
    DESCRIPTION     
            "Number of seconds the server VLan policer alarm has been at this level."
    ::= { sonusServerPolicerAlarmStatEntry 21 }

sonusServerPolicerAlarmStatVLanDiscardRate OBJECT-TYPE
    SYNTAX          Unsigned32
    MAX-ACCESS      read-only
    STATUS          current
    DESCRIPTION     
            "Current rate of VLan discards for the server."
    ::= { sonusServerPolicerAlarmStatEntry 22 }

sonusServerPolicerAlarmStatVLanPacketsDiscard OBJECT-TYPE
    SYNTAX          Counter64
    MAX-ACCESS      read-only
    STATUS          current
    DESCRIPTION     
            "Total number of packets discarded by VLan policers on server."
    ::= { sonusServerPolicerAlarmStatEntry 23 }

sonusServerPolicerAlarmStatServerProtectAlarmLevel OBJECT-TYPE
    SYNTAX          INTEGER { noAlarm(1), minorAlarm(2), majorAlarm(3) }
    MAX-ACCESS      read-only
    STATUS          current
    DESCRIPTION     
            "Server ServerProtect policer alarm level."
    ::= { sonusServerPolicerAlarmStatEntry 24 }

sonusServerPolicerAlarmStatServerProtectAlarmDuration OBJECT-TYPE
    SYNTAX          Unsigned32
    MAX-ACCESS      read-only
    STATUS          current
    DESCRIPTION     
            "Number of seconds the server ServerProtect policer alarm has been at this level."
    ::= { sonusServerPolicerAlarmStatEntry 25 }

sonusServerPolicerAlarmStatServerProtectDiscardRate OBJECT-TYPE
    SYNTAX          Unsigned32
    MAX-ACCESS      read-only
    STATUS          current
    DESCRIPTION     
            "Current rate of ServerProtect discards for the server."
    ::= { sonusServerPolicerAlarmStatEntry 26 }

sonusServerPolicerAlarmStatServerProtectPacketsAccept OBJECT-TYPE
    SYNTAX          Counter64
    MAX-ACCESS      read-only
    STATUS          current
    DESCRIPTION     
            "Total number of packets accepted by ServerProtect policers on server."
    ::= { sonusServerPolicerAlarmStatEntry 27 }

sonusServerPolicerAlarmStatServerProtectPacketsDiscard OBJECT-TYPE
    SYNTAX          Counter64
    MAX-ACCESS      read-only
    STATUS          current
    DESCRIPTION     
            "Total number of packets discarded by ServerProtect policers on server."
    ::= { sonusServerPolicerAlarmStatEntry 28 }

sonusServerPolicerAlarmStatMediaAlarmLevel OBJECT-TYPE
    SYNTAX          INTEGER { noAlarm(1), minorAlarm(2), majorAlarm(3) }
    MAX-ACCESS      read-only
    STATUS          current
    DESCRIPTION     
            "Server media policer alarm level."
    ::= { sonusServerPolicerAlarmStatEntry 29 }

sonusServerPolicerAlarmStatMediaAlarmDuration OBJECT-TYPE
    SYNTAX          Unsigned32
    MAX-ACCESS      read-only
    STATUS          current
    DESCRIPTION     
            "Number of seconds the server media policer alarm has been at this level."
    ::= { sonusServerPolicerAlarmStatEntry 30 }

sonusServerPolicerAlarmStatMediaDiscardRate OBJECT-TYPE
    SYNTAX          Unsigned32
    MAX-ACCESS      read-only
    STATUS          current
    DESCRIPTION     
            "Current rate of media discards for the server."
    ::= { sonusServerPolicerAlarmStatEntry 31 }

sonusServerPolicerAlarmStatMediaPacketsDiscard OBJECT-TYPE
    SYNTAX          Counter64
    MAX-ACCESS      read-only
    STATUS          current
    DESCRIPTION     
            "Total number of packets discarded by media policers on server."
    ::= { sonusServerPolicerAlarmStatEntry 32 }

sonusServerPolicerAlarmStatRogueUnallocPortAlarmLevel OBJECT-TYPE
    SYNTAX          INTEGER { noAlarm(1), minorAlarm(2), majorAlarm(3) }
    MAX-ACCESS      read-only
    STATUS          current
    DESCRIPTION     
            "Server RogueUnallocPort policer alarm level."
    ::= { sonusServerPolicerAlarmStatEntry 33 }

sonusServerPolicerAlarmStatRogueUnallocPortAlarmDuration OBJECT-TYPE
    SYNTAX          Unsigned32
    MAX-ACCESS      read-only
    STATUS          current
    DESCRIPTION     
            "Number of seconds the server RogueUnallocPort policer alarm has been at this level."
    ::= { sonusServerPolicerAlarmStatEntry 34 }

sonusServerPolicerAlarmStatRogueUnallocPortDiscardRate OBJECT-TYPE
    SYNTAX          Unsigned32
    MAX-ACCESS      read-only
    STATUS          current
    DESCRIPTION     
            "Current rate of RogueUnallocPort discards for the server."
    ::= { sonusServerPolicerAlarmStatEntry 35 }

sonusServerPolicerAlarmStatRogueUnallocPortPacketsDiscard OBJECT-TYPE
    SYNTAX          Counter64
    MAX-ACCESS      read-only
    STATUS          current
    DESCRIPTION     
            "Total number of packets discarded by RogueUnallocPort policers on server."
    ::= { sonusServerPolicerAlarmStatEntry 36 }

sonusServerPolicerAlarmStatRogueBadSrcAlarmLevel OBJECT-TYPE
    SYNTAX          INTEGER { noAlarm(1), minorAlarm(2), majorAlarm(3) }
    MAX-ACCESS      read-only
    STATUS          current
    DESCRIPTION     
            "Server RogueBadSrc policer alarm level."
    ::= { sonusServerPolicerAlarmStatEntry 37 }

sonusServerPolicerAlarmStatRogueBadSrcAlarmDuration OBJECT-TYPE
    SYNTAX          Unsigned32
    MAX-ACCESS      read-only
    STATUS          current
    DESCRIPTION     
            "Number of seconds the server RogueBadSrc policer alarm has been at this level."
    ::= { sonusServerPolicerAlarmStatEntry 38 }

sonusServerPolicerAlarmStatRogueBadSrcDiscardRate OBJECT-TYPE
    SYNTAX          Unsigned32
    MAX-ACCESS      read-only
    STATUS          current
    DESCRIPTION     
            "Current rate of RogueBadSrc discards for the server."
    ::= { sonusServerPolicerAlarmStatEntry 39 }

sonusServerPolicerAlarmStatRogueBadSrcPacketsDiscard OBJECT-TYPE
    SYNTAX          Counter64
    MAX-ACCESS      read-only
    STATUS          current
    DESCRIPTION     
            "Total number of packets discarded by RogueBadSrc policers on server."
    ::= { sonusServerPolicerAlarmStatEntry 40 }

sonusServerPolicerAlarmStatRogueBadDestAlarmLevel OBJECT-TYPE
    SYNTAX          INTEGER { noAlarm(1), minorAlarm(2), majorAlarm(3) }
    MAX-ACCESS      read-only
    STATUS          current
    DESCRIPTION     
            "Server RogueBadDest policer alarm level."
    ::= { sonusServerPolicerAlarmStatEntry 41 }

sonusServerPolicerAlarmStatRogueBadDestAlarmDuration OBJECT-TYPE
    SYNTAX          Unsigned32
    MAX-ACCESS      read-only
    STATUS          current
    DESCRIPTION     
            "Number of seconds the server RogueBadDest policer alarm has been at this level."
    ::= { sonusServerPolicerAlarmStatEntry 42 }

sonusServerPolicerAlarmStatRogueBadDestDiscardRate OBJECT-TYPE
    SYNTAX          Unsigned32
    MAX-ACCESS      read-only
    STATUS          current
    DESCRIPTION     
            "Current rate of RogueBadDest discards for the server."
    ::= { sonusServerPolicerAlarmStatEntry 43 }

sonusServerPolicerAlarmStatRogueBadDestPacketsDiscard OBJECT-TYPE
    SYNTAX          Counter64
    MAX-ACCESS      read-only
    STATUS          current
    DESCRIPTION     
            "Total number of packets discarded by RogueBadDest policers on server."
    ::= { sonusServerPolicerAlarmStatEntry 44 }

sonusServerPolicerAlarmStatRogueBadVLanAlarmLevel OBJECT-TYPE
    SYNTAX          INTEGER { noAlarm(1), minorAlarm(2), majorAlarm(3) }
    MAX-ACCESS      read-only
    STATUS          current
    DESCRIPTION     
            "Server RogueBadVLan policer alarm level."
    ::= { sonusServerPolicerAlarmStatEntry 45 }

sonusServerPolicerAlarmStatRogueBadVLanAlarmDuration OBJECT-TYPE
    SYNTAX          Unsigned32
    MAX-ACCESS      read-only
    STATUS          current
    DESCRIPTION     
            "Number of seconds the server RogueBadVLan policer alarm has been at this level."
    ::= { sonusServerPolicerAlarmStatEntry 46 }

sonusServerPolicerAlarmStatRogueBadVLanDiscardRate OBJECT-TYPE
    SYNTAX          Unsigned32
    MAX-ACCESS      read-only
    STATUS          current
    DESCRIPTION     
            "Current rate of RogueBadVLan discards for the server."
    ::= { sonusServerPolicerAlarmStatEntry 47 }

sonusServerPolicerAlarmStatRogueBadVLanPacketsDiscard OBJECT-TYPE
    SYNTAX          Counter64
    MAX-ACCESS      read-only
    STATUS          current
    DESCRIPTION     
            "Total number of packets discarded by RogueBadVLan policers on server."
    ::= { sonusServerPolicerAlarmStatEntry 48 }

sonusServerPolicerAlarmStatRogueInGracePeriodDiscardRate OBJECT-TYPE
    SYNTAX          Unsigned32
    MAX-ACCESS      read-only
    STATUS          current
    DESCRIPTION     
            "Current rate of RogueInGracePeriod discards for the server."
    ::= { sonusServerPolicerAlarmStatEntry 49 }

sonusServerPolicerAlarmStatRogueInGracePeriodPacketsDiscard OBJECT-TYPE
    SYNTAX          Counter64
    MAX-ACCESS      read-only
    STATUS          current
    DESCRIPTION     
            "Total number of packets discarded by RogueInGracePeriod policers on server."
    ::= { sonusServerPolicerAlarmStatEntry 50 }

sonusWhitePolicerDiscardRingTable OBJECT-TYPE
    SYNTAX          SEQUENCE OF SonusWhitePolicerDiscardRingEntry
    MAX-ACCESS      not-accessible
    STATUS          current
    DESCRIPTION     
            "The table of statistics for the white list
             policer discard ring."
    ::= { sonusIpmMIBObjects 6 }

sonusWhitePolicerDiscardRingEntry OBJECT-TYPE
    SYNTAX          SonusWhitePolicerDiscardRingEntry
    MAX-ACCESS      not-accessible
    STATUS          current
    DESCRIPTION     
            "The white list discard ring entries."
    INDEX           { sonusWhitePolicerDiscardRingShelfIndex, 
                      sonusWhitePolicerDiscardRingSlotIndex, 
                      sonusWhitePolicerDiscardRingPositionIndex }
    ::= { sonusWhitePolicerDiscardRingTable 1 }

SonusWhitePolicerDiscardRingEntry ::=
    SEQUENCE {
        sonusWhitePolicerDiscardRingShelfIndex      SonusShelfIndex,
        sonusWhitePolicerDiscardRingSlotIndex     SonusSlotIndex,
        sonusWhitePolicerDiscardRingPositionIndex         Unsigned32,
        sonusWhitePolicerDiscardRingNIFSIFName      SonusNameReference,
        sonusWhitePolicerDiscardRingIpAddress     IpAddress,
        sonusWhitePolicerDiscardRingIpProtocol      Unsigned32,
        sonusWhitePolicerDiscardRingDiscardCount        Counter32,
        sonusWhitePolicerDiscardRingIp6Address      Ipv6Address,
        sonusWhitePolicerDiscardRingIpVer INTEGER
    }

sonusWhitePolicerDiscardRingShelfIndex OBJECT-TYPE
    SYNTAX          SonusShelfIndex
    MAX-ACCESS      read-only
    STATUS          current
    DESCRIPTION     
            "The shelf index into this table."
    ::= { sonusWhitePolicerDiscardRingEntry 1 }

sonusWhitePolicerDiscardRingSlotIndex OBJECT-TYPE
    SYNTAX          SonusSlotIndex
    MAX-ACCESS      read-only
    STATUS          current
    DESCRIPTION     
            "The slot index into this table."
    ::= { sonusWhitePolicerDiscardRingEntry 2 }

sonusWhitePolicerDiscardRingPositionIndex OBJECT-TYPE
    SYNTAX          Unsigned32
    MAX-ACCESS      read-only
    STATUS          current
    DESCRIPTION     
            "The position index into this table ordered by
             worst offender with 1 being the worst."
    ::= { sonusWhitePolicerDiscardRingEntry 3 }

sonusWhitePolicerDiscardRingNIFSIFName OBJECT-TYPE
    SYNTAX          SonusNameReference
    MAX-ACCESS      read-only
    STATUS          current
    DESCRIPTION     
            "The name of the NIF or sub-interface of 
             table entry."
    ::= { sonusWhitePolicerDiscardRingEntry 4 }

sonusWhitePolicerDiscardRingIpAddress OBJECT-TYPE
    SYNTAX          IpAddress
    MAX-ACCESS      read-only
    STATUS          current
    DESCRIPTION     
            "The IPv4 address of the table entry."
    ::= { sonusWhitePolicerDiscardRingEntry 5 }

sonusWhitePolicerDiscardRingIpProtocol OBJECT-TYPE
    SYNTAX          Unsigned32
    MAX-ACCESS      read-only
    STATUS          current
    DESCRIPTION     
            "The IP Protocol of the table entry."
    ::= { sonusWhitePolicerDiscardRingEntry 6 }

sonusWhitePolicerDiscardRingDiscardCount OBJECT-TYPE
    SYNTAX          Counter32
    MAX-ACCESS      read-only
    STATUS          current
    DESCRIPTION     
            "The number of packets discarded by the policer."
    ::= { sonusWhitePolicerDiscardRingEntry 7 }

sonusWhitePolicerDiscardRingIp6Address OBJECT-TYPE
    SYNTAX          Ipv6Address
    MAX-ACCESS      read-write
    STATUS          current
    DESCRIPTION     
            "The Stat IPv6 address"
    ::= { sonusWhitePolicerDiscardRingEntry 8 }

sonusWhitePolicerDiscardRingIpVer OBJECT-TYPE
    SYNTAX          INTEGER { afInet(2), afInet6(24) }
    MAX-ACCESS      read-only
    STATUS          current
    DESCRIPTION     
            "IP address version of the peer of this connection"
    ::= { sonusWhitePolicerDiscardRingEntry 9 }

sonusDarkGrayPolicerDiscardRingTable OBJECT-TYPE
    SYNTAX          SEQUENCE OF SonusDarkGrayPolicerDiscardRingEntry
    MAX-ACCESS      not-accessible
    STATUS          current
    DESCRIPTION     
            "The table of statistics for the dark gray list
             policer discard ring."
    ::= { sonusIpmMIBObjects 7 }

sonusDarkGrayPolicerDiscardRingEntry OBJECT-TYPE
    SYNTAX          SonusDarkGrayPolicerDiscardRingEntry
    MAX-ACCESS      not-accessible
    STATUS          current
    DESCRIPTION     
            "The dark gray list discard ring entries."
    INDEX           { sonusDarkGrayPolicerDiscardRingShelfIndex, 
                      sonusDarkGrayPolicerDiscardRingSlotIndex, 
                      sonusDarkGrayPolicerDiscardRingPositionIndex }
    ::= { sonusDarkGrayPolicerDiscardRingTable 1 }

SonusDarkGrayPolicerDiscardRingEntry ::=
    SEQUENCE {
        sonusDarkGrayPolicerDiscardRingShelfIndex         SonusShelfIndex,
        sonusDarkGrayPolicerDiscardRingSlotIndex        SonusSlotIndex,
        sonusDarkGrayPolicerDiscardRingPositionIndex            Unsigned32,
        sonusDarkGrayPolicerDiscardRingNIFSIFName         SonusNameReference,
        sonusDarkGrayPolicerDiscardRingIpAddress        IpAddress,
        sonusDarkGrayPolicerDiscardRingIpProtocol         Unsigned32,
        sonusDarkGrayPolicerDiscardRingDiscardCount           Counter32,
        sonusDarkGrayPolicerDiscardRingIp6Address         Ipv6Address,
        sonusDarkGrayPolicerDiscardRingIpVer    INTEGER
    }

sonusDarkGrayPolicerDiscardRingShelfIndex OBJECT-TYPE
    SYNTAX          SonusShelfIndex
    MAX-ACCESS      read-only
    STATUS          current
    DESCRIPTION     
            "The shelf index into this table."
    ::= { sonusDarkGrayPolicerDiscardRingEntry 1 }

sonusDarkGrayPolicerDiscardRingSlotIndex OBJECT-TYPE
    SYNTAX          SonusSlotIndex
    MAX-ACCESS      read-only
    STATUS          current
    DESCRIPTION     
            "The slot index into this table."
    ::= { sonusDarkGrayPolicerDiscardRingEntry 2 }

sonusDarkGrayPolicerDiscardRingPositionIndex OBJECT-TYPE
    SYNTAX          Unsigned32
    MAX-ACCESS      read-only
    STATUS          current
    DESCRIPTION     
            "The position index into this table ordered by
             worst offender with 1 being the worst."
    ::= { sonusDarkGrayPolicerDiscardRingEntry 3 }

sonusDarkGrayPolicerDiscardRingNIFSIFName OBJECT-TYPE
    SYNTAX          SonusNameReference
    MAX-ACCESS      read-only
    STATUS          current
    DESCRIPTION     
            "The name of the NIF or sub-interface of 
             table entry."
    ::= { sonusDarkGrayPolicerDiscardRingEntry 4 }

sonusDarkGrayPolicerDiscardRingIpAddress OBJECT-TYPE
    SYNTAX          IpAddress
    MAX-ACCESS      read-only
    STATUS          current
    DESCRIPTION     
            "The IPv4 address of the table entry."
    ::= { sonusDarkGrayPolicerDiscardRingEntry 5 }

sonusDarkGrayPolicerDiscardRingIpProtocol OBJECT-TYPE
    SYNTAX          Unsigned32
    MAX-ACCESS      read-only
    STATUS          current
    DESCRIPTION     
            "The IP Protocol of the table entry."
    ::= { sonusDarkGrayPolicerDiscardRingEntry 6 }

sonusDarkGrayPolicerDiscardRingDiscardCount OBJECT-TYPE
    SYNTAX          Counter32
    MAX-ACCESS      read-only
    STATUS          current
    DESCRIPTION     
            "The number of packets discarded by the policer."
    ::= { sonusDarkGrayPolicerDiscardRingEntry 7 }

sonusDarkGrayPolicerDiscardRingIp6Address OBJECT-TYPE
    SYNTAX          Ipv6Address
    MAX-ACCESS      read-write
    STATUS          current
    DESCRIPTION     
            "The Stat IPv6 address"
    ::= { sonusDarkGrayPolicerDiscardRingEntry 8 }

sonusDarkGrayPolicerDiscardRingIpVer OBJECT-TYPE
    SYNTAX          INTEGER { afInet(2), afInet6(24) }
    MAX-ACCESS      read-only
    STATUS          current
    DESCRIPTION     
            "IP address version of the peer of this connection"
    ::= { sonusDarkGrayPolicerDiscardRingEntry 9 }

sonusRogueMediaBySrcPolicerDiscardRingTable OBJECT-TYPE
    SYNTAX          SEQUENCE OF SonusRogueMediaBySrcPolicerDiscardRingEntry
    MAX-ACCESS      not-accessible
    STATUS          current
    DESCRIPTION     
            "The table of statistics for the rogue media by source
             policer discard ring. The table is used to identify the
             source VLAN/IP address initiating an attack."
    ::= { sonusIpmMIBObjects 8 }

sonusRogueMediaBySrcPolicerDiscardRingEntry OBJECT-TYPE
    SYNTAX          SonusRogueMediaBySrcPolicerDiscardRingEntry
    MAX-ACCESS      not-accessible
    STATUS          current
    DESCRIPTION     
            "The rogue media discard ring entries."
    INDEX           { sonusRogueMediaBySrcPolicerDiscardRingShelfIndex, 
                      sonusRogueMediaBySrcPolicerDiscardRingSlotIndex, 
                      sonusRogueMediaBySrcPolicerDiscardRingPositionIndex }
    ::= { sonusRogueMediaBySrcPolicerDiscardRingTable 1 }

SonusRogueMediaBySrcPolicerDiscardRingEntry ::=
    SEQUENCE {
        sonusRogueMediaBySrcPolicerDiscardRingShelfIndex                SonusShelfIndex,
        sonusRogueMediaBySrcPolicerDiscardRingSlotIndex               SonusSlotIndex,
        sonusRogueMediaBySrcPolicerDiscardRingPositionIndex                   Unsigned32,
        sonusRogueMediaBySrcPolicerDiscardRingNIFSIFName                SonusNameReference,
        sonusRogueMediaBySrcPolicerDiscardRingSourceIpAddress                     IpAddress,
        sonusRogueMediaBySrcPolicerDiscardRingDestIpAddress                   IpAddress,
        sonusRogueMediaBySrcPolicerDiscardRingDiscardCount                  Counter32,
        sonusRogueMediaBySrcPolicerDiscardRingType          INTEGER,
        sonusRogueMediaBySrcPolicerDiscardRingSourceIpPort                  Unsigned32,
        sonusRogueMediaBySrcPolicerDiscardRingDestIpPort                Unsigned32,
        sonusRogueMediaBySrcPolicerDiscardRingDestUnique                INTEGER,
        sonusRogueMediaBySrcPolicerDiscardRingSourceIp6Address                      Ipv6Address,
        sonusRogueMediaBySrcPolicerDiscardRingSourceIpVer                 INTEGER,
        sonusRogueMediaBySrcPolicerDiscardRingDestIp6Address                    Ipv6Address,
        sonusRogueMediaBySrcPolicerDiscardRingDestIpVer               INTEGER
    }

sonusRogueMediaBySrcPolicerDiscardRingShelfIndex OBJECT-TYPE
    SYNTAX          SonusShelfIndex
    MAX-ACCESS      read-only
    STATUS          current
    DESCRIPTION     
            "The shelf index into this table."
    ::= { sonusRogueMediaBySrcPolicerDiscardRingEntry 1 }

sonusRogueMediaBySrcPolicerDiscardRingSlotIndex OBJECT-TYPE
    SYNTAX          SonusSlotIndex
    MAX-ACCESS      read-only
    STATUS          current
    DESCRIPTION     
            "The slot index into this table."
    ::= { sonusRogueMediaBySrcPolicerDiscardRingEntry 2 }

sonusRogueMediaBySrcPolicerDiscardRingPositionIndex OBJECT-TYPE
    SYNTAX          Unsigned32
    MAX-ACCESS      read-only
    STATUS          current
    DESCRIPTION     
            "The position index into this table ordered by
             worst offender with 1 being the worst."
    ::= { sonusRogueMediaBySrcPolicerDiscardRingEntry 3 }

sonusRogueMediaBySrcPolicerDiscardRingNIFSIFName OBJECT-TYPE
    SYNTAX          SonusNameReference
    MAX-ACCESS      read-only
    STATUS          current
    DESCRIPTION     
            "The name of the NIF or sub-interface of 
             table entry."
    ::= { sonusRogueMediaBySrcPolicerDiscardRingEntry 4 }

sonusRogueMediaBySrcPolicerDiscardRingSourceIpAddress OBJECT-TYPE
    SYNTAX          IpAddress
    MAX-ACCESS      read-only
    STATUS          current
    DESCRIPTION     
            "The source IPv4 address of the table entry."
    ::= { sonusRogueMediaBySrcPolicerDiscardRingEntry 5 }

sonusRogueMediaBySrcPolicerDiscardRingDestIpAddress OBJECT-TYPE
    SYNTAX          IpAddress
    MAX-ACCESS      read-only
    STATUS          current
    DESCRIPTION     
            "The destination IPv4 address of the table entry."
    ::= { sonusRogueMediaBySrcPolicerDiscardRingEntry 6 }

sonusRogueMediaBySrcPolicerDiscardRingDiscardCount OBJECT-TYPE
    SYNTAX          Counter32
    MAX-ACCESS      read-only
    STATUS          current
    DESCRIPTION     
            "The number of packets discarded by the policer."
    ::= { sonusRogueMediaBySrcPolicerDiscardRingEntry 7 }

sonusRogueMediaBySrcPolicerDiscardRingType OBJECT-TYPE
    SYNTAX          INTEGER { duringCallGracePeriod(1), 
                        unallocatedPort(2), badDestAddr(3), 
                        badSourceAddr(4), incorrectVLan(5), 
                        unexpectedVLan(6) }
    MAX-ACCESS      read-only
    STATUS          current
    DESCRIPTION     
            "The rogue media type."
    ::= { sonusRogueMediaBySrcPolicerDiscardRingEntry 8 }

sonusRogueMediaBySrcPolicerDiscardRingSourceIpPort OBJECT-TYPE
    SYNTAX          Unsigned32
    MAX-ACCESS      read-only
    STATUS          current
    DESCRIPTION     
            "The source IPv4 port of the table entry."
    ::= { sonusRogueMediaBySrcPolicerDiscardRingEntry 9 }

sonusRogueMediaBySrcPolicerDiscardRingDestIpPort OBJECT-TYPE
    SYNTAX          Unsigned32
    MAX-ACCESS      read-only
    STATUS          current
    DESCRIPTION     
            "The destination IPv4 port of the table entry."
    ::= { sonusRogueMediaBySrcPolicerDiscardRingEntry 10 }

sonusRogueMediaBySrcPolicerDiscardRingDestUnique OBJECT-TYPE
    SYNTAX          INTEGER { unique(1), notUnique(2) }
    MAX-ACCESS      read-only
    STATUS          current
    DESCRIPTION     
            "Determines if all discards were for a unique destination address"
    ::= { sonusRogueMediaBySrcPolicerDiscardRingEntry 11 }

sonusRogueMediaBySrcPolicerDiscardRingSourceIp6Address OBJECT-TYPE
    SYNTAX          Ipv6Address
    MAX-ACCESS      read-write
    STATUS          current
    DESCRIPTION     
            "The Stat IPv6 address"
    ::= { sonusRogueMediaBySrcPolicerDiscardRingEntry 12 }

sonusRogueMediaBySrcPolicerDiscardRingSourceIpVer OBJECT-TYPE
    SYNTAX          INTEGER { afInet(2), afInet6(24) }
    MAX-ACCESS      read-only
    STATUS          current
    DESCRIPTION     
            "IP address version of the peer of this connection"
    ::= { sonusRogueMediaBySrcPolicerDiscardRingEntry 13 }

sonusRogueMediaBySrcPolicerDiscardRingDestIp6Address OBJECT-TYPE
    SYNTAX          Ipv6Address
    MAX-ACCESS      read-write
    STATUS          current
    DESCRIPTION     
            "The Stat IPv6 address"
    ::= { sonusRogueMediaBySrcPolicerDiscardRingEntry 14 }

sonusRogueMediaBySrcPolicerDiscardRingDestIpVer OBJECT-TYPE
    SYNTAX          INTEGER { afInet(2), afInet6(24) }
    MAX-ACCESS      read-only
    STATUS          current
    DESCRIPTION     
            "IP address version of the peer of this connection"
    ::= { sonusRogueMediaBySrcPolicerDiscardRingEntry 15 }

sonusRogueMediaByDestPolicerDiscardRingTable OBJECT-TYPE
    SYNTAX          SEQUENCE OF SonusRogueMediaByDestPolicerDiscardRingEntry
    MAX-ACCESS      not-accessible
    STATUS          current
    DESCRIPTION     
            "The table of statistics for the rogue media by destination
             policer discard ring. The table is used to identify the
             NIFs/RTP ports being attacked."
    ::= { sonusIpmMIBObjects 9 }

sonusRogueMediaByDestPolicerDiscardRingEntry OBJECT-TYPE
    SYNTAX          SonusRogueMediaByDestPolicerDiscardRingEntry
    MAX-ACCESS      not-accessible
    STATUS          current
    DESCRIPTION     
            "The rogue media discard ring entries."
    INDEX           { sonusRogueMediaByDestPolicerDiscardRingShelfIndex, 
                      sonusRogueMediaByDestPolicerDiscardRingSlotIndex, 
                      sonusRogueMediaByDestPolicerDiscardRingPositionIndex }
    ::= { sonusRogueMediaByDestPolicerDiscardRingTable 1 }

SonusRogueMediaByDestPolicerDiscardRingEntry ::=
    SEQUENCE {
        sonusRogueMediaByDestPolicerDiscardRingShelfIndex                 SonusShelfIndex,
        sonusRogueMediaByDestPolicerDiscardRingSlotIndex                SonusSlotIndex,
        sonusRogueMediaByDestPolicerDiscardRingPositionIndex                    Unsigned32,
        sonusRogueMediaByDestPolicerDiscardRingNIFSIFName                 SonusNameReference,
        sonusRogueMediaByDestPolicerDiscardRingSourceIpAddress                      IpAddress,
        sonusRogueMediaByDestPolicerDiscardRingDestIpAddress                    IpAddress,
        sonusRogueMediaByDestPolicerDiscardRingDiscardCount                   Counter32,
        sonusRogueMediaByDestPolicerDiscardRingType           INTEGER,
        sonusRogueMediaByDestPolicerDiscardRingSourceIpPort                   Unsigned32,
        sonusRogueMediaByDestPolicerDiscardRingDestIpPort                 Unsigned32,
        sonusRogueMediaByDestPolicerDiscardRingSourceUnique                   INTEGER,
        sonusRogueMediaByDestPolicerDiscardRingSourceIp6Address                       Ipv6Address,
        sonusRogueMediaByDestPolicerDiscardRingDestIp6Address                     Ipv6Address,
        sonusRogueMediaByDestPolicerDiscardRingDestIpVer                INTEGER
    }

sonusRogueMediaByDestPolicerDiscardRingShelfIndex OBJECT-TYPE
    SYNTAX          SonusShelfIndex
    MAX-ACCESS      read-only
    STATUS          current
    DESCRIPTION     
            "The shelf index into this table."
    ::= { sonusRogueMediaByDestPolicerDiscardRingEntry 1 }

sonusRogueMediaByDestPolicerDiscardRingSlotIndex OBJECT-TYPE
    SYNTAX          SonusSlotIndex
    MAX-ACCESS      read-only
    STATUS          current
    DESCRIPTION     
            "The slot index into this table."
    ::= { sonusRogueMediaByDestPolicerDiscardRingEntry 2 }

sonusRogueMediaByDestPolicerDiscardRingPositionIndex OBJECT-TYPE
    SYNTAX          Unsigned32
    MAX-ACCESS      read-only
    STATUS          current
    DESCRIPTION     
            "The position index into this table ordered by
             worst offender with 1 being the worst."
    ::= { sonusRogueMediaByDestPolicerDiscardRingEntry 3 }

sonusRogueMediaByDestPolicerDiscardRingNIFSIFName OBJECT-TYPE
    SYNTAX          SonusNameReference
    MAX-ACCESS      read-only
    STATUS          current
    DESCRIPTION     
            "The name of the NIF or sub-interface of 
             table entry."
    ::= { sonusRogueMediaByDestPolicerDiscardRingEntry 4 }

sonusRogueMediaByDestPolicerDiscardRingSourceIpAddress OBJECT-TYPE
    SYNTAX          IpAddress
    MAX-ACCESS      read-only
    STATUS          current
    DESCRIPTION     
            "The source IPv4 address of the table entry."
    ::= { sonusRogueMediaByDestPolicerDiscardRingEntry 5 }

sonusRogueMediaByDestPolicerDiscardRingDestIpAddress OBJECT-TYPE
    SYNTAX          IpAddress
    MAX-ACCESS      read-only
    STATUS          current
    DESCRIPTION     
            "The destination IPv4 address of the table entry."
    ::= { sonusRogueMediaByDestPolicerDiscardRingEntry 6 }

sonusRogueMediaByDestPolicerDiscardRingDiscardCount OBJECT-TYPE
    SYNTAX          Counter32
    MAX-ACCESS      read-only
    STATUS          current
    DESCRIPTION     
            "The number of packets discarded by the policer."
    ::= { sonusRogueMediaByDestPolicerDiscardRingEntry 7 }

sonusRogueMediaByDestPolicerDiscardRingType OBJECT-TYPE
    SYNTAX          INTEGER { duringCallGracePeriod(1), 
                        unallocatedPort(2), badDestAddr(3), 
                        badSourceAddr(4), incorrectVLan(5), 
                        unexpectedVLan(6) }
    MAX-ACCESS      read-only
    STATUS          current
    DESCRIPTION     
            "The rogue media type."
    ::= { sonusRogueMediaByDestPolicerDiscardRingEntry 8 }

sonusRogueMediaByDestPolicerDiscardRingSourceIpPort OBJECT-TYPE
    SYNTAX          Unsigned32
    MAX-ACCESS      read-only
    STATUS          current
    DESCRIPTION     
            "The source IPv4 port of the table entry."
    ::= { sonusRogueMediaByDestPolicerDiscardRingEntry 9 }

sonusRogueMediaByDestPolicerDiscardRingDestIpPort OBJECT-TYPE
    SYNTAX          Unsigned32
    MAX-ACCESS      read-only
    STATUS          current
    DESCRIPTION     
            "The destination IPv4 port of the table entry."
    ::= { sonusRogueMediaByDestPolicerDiscardRingEntry 10 }

sonusRogueMediaByDestPolicerDiscardRingSourceUnique OBJECT-TYPE
    SYNTAX          INTEGER { unique(1), notUnique(2) }
    MAX-ACCESS      read-only
    STATUS          current
    DESCRIPTION     
            "Determines if all discards were from a unique source address"
    ::= { sonusRogueMediaByDestPolicerDiscardRingEntry 11 }

sonusRogueMediaByDestPolicerDiscardRingSourceIp6Address OBJECT-TYPE
    SYNTAX          Ipv6Address
    MAX-ACCESS      read-write
    STATUS          current
    DESCRIPTION     
            "The Stat IPv6 address"
    ::= { sonusRogueMediaByDestPolicerDiscardRingEntry 12 }

sonusRogueMediaByDestPolicerDiscardRingDestIp6Address OBJECT-TYPE
    SYNTAX          Ipv6Address
    MAX-ACCESS      read-write
    STATUS          current
    DESCRIPTION     
            "The Stat IPv6 address"
    ::= { sonusRogueMediaByDestPolicerDiscardRingEntry 13 }

sonusRogueMediaByDestPolicerDiscardRingDestIpVer OBJECT-TYPE
    SYNTAX          INTEGER { afInet(2), afInet6(24) }
    MAX-ACCESS      read-only
    STATUS          current
    DESCRIPTION     
            "IP address version of the peer of this connection"
    ::= { sonusRogueMediaByDestPolicerDiscardRingEntry 14 }

sonusServerProtectPolicerDiscardRingTable OBJECT-TYPE
    SYNTAX          SEQUENCE OF SonusServerProtectPolicerDiscardRingEntry
    MAX-ACCESS      not-accessible
    STATUS          current
    DESCRIPTION     
            "The table of statistics for the server protect default
             policer discard ring."
    ::= { sonusIpmMIBObjects 10 }

sonusServerProtectPolicerDiscardRingEntry OBJECT-TYPE
    SYNTAX          SonusServerProtectPolicerDiscardRingEntry
    MAX-ACCESS      not-accessible
    STATUS          current
    DESCRIPTION     
            "The server protect default discard ring entries."
    INDEX           { sonusServerProtectPolicerDiscardRingShelfIndex, 
                      sonusServerProtectPolicerDiscardRingSlotIndex, 
                      sonusServerProtectPolicerDiscardRingPositionIndex }
    ::= { sonusServerProtectPolicerDiscardRingTable 1 }

SonusServerProtectPolicerDiscardRingEntry ::=
    SEQUENCE {
        sonusServerProtectPolicerDiscardRingShelfIndex              SonusShelfIndex,
        sonusServerProtectPolicerDiscardRingSlotIndex             SonusSlotIndex,
        sonusServerProtectPolicerDiscardRingPositionIndex                 Unsigned32,
        sonusServerProtectPolicerDiscardRingNIFSIFName              SonusNameReference,
        sonusServerProtectPolicerDiscardRingIpAddress             IpAddress,
        sonusServerProtectPolicerDiscardRingIpProtocol              Unsigned32,
        sonusServerProtectPolicerDiscardRingDiscardCount                Counter32,
        sonusServerProtectPolicerDiscardRingDestIpAddress                 IpAddress,
        sonusServerProtectPolicerDiscardRingEtherType             Unsigned32,
        sonusServerProtectPolicerDiscardRingDestUnique              INTEGER
    }

sonusServerProtectPolicerDiscardRingShelfIndex OBJECT-TYPE
    SYNTAX          SonusShelfIndex
    MAX-ACCESS      read-only
    STATUS          current
    DESCRIPTION     
            "The shelf index into this table."
    ::= { sonusServerProtectPolicerDiscardRingEntry 1 }

sonusServerProtectPolicerDiscardRingSlotIndex OBJECT-TYPE
    SYNTAX          SonusSlotIndex
    MAX-ACCESS      read-only
    STATUS          current
    DESCRIPTION     
            "The slot index into this table."
    ::= { sonusServerProtectPolicerDiscardRingEntry 2 }

sonusServerProtectPolicerDiscardRingPositionIndex OBJECT-TYPE
    SYNTAX          Unsigned32
    MAX-ACCESS      read-only
    STATUS          current
    DESCRIPTION     
            "The position index into this table ordered by
             worst offender with 1 being the worst."
    ::= { sonusServerProtectPolicerDiscardRingEntry 3 }

sonusServerProtectPolicerDiscardRingNIFSIFName OBJECT-TYPE
    SYNTAX          SonusNameReference
    MAX-ACCESS      read-only
    STATUS          current
    DESCRIPTION     
            "The name of the NIF or sub-interface of 
             table entry."
    ::= { sonusServerProtectPolicerDiscardRingEntry 4 }

sonusServerProtectPolicerDiscardRingIpAddress OBJECT-TYPE
    SYNTAX          IpAddress
    MAX-ACCESS      read-only
    STATUS          current
    DESCRIPTION     
            "The IPv4 address of the table entry."
    ::= { sonusServerProtectPolicerDiscardRingEntry 5 }

sonusServerProtectPolicerDiscardRingIpProtocol OBJECT-TYPE
    SYNTAX          Unsigned32
    MAX-ACCESS      read-only
    STATUS          current
    DESCRIPTION     
            "The IP Protocol of the table entry."
    ::= { sonusServerProtectPolicerDiscardRingEntry 6 }

sonusServerProtectPolicerDiscardRingDiscardCount OBJECT-TYPE
    SYNTAX          Counter32
    MAX-ACCESS      read-only
    STATUS          current
    DESCRIPTION     
            "The number of packets discarded by the policer."
    ::= { sonusServerProtectPolicerDiscardRingEntry 7 }

sonusServerProtectPolicerDiscardRingDestIpAddress OBJECT-TYPE
    SYNTAX          IpAddress
    MAX-ACCESS      read-only
    STATUS          current
    DESCRIPTION     
            "The destination IPv4 address of the table entry."
    ::= { sonusServerProtectPolicerDiscardRingEntry 8 }

sonusServerProtectPolicerDiscardRingEtherType OBJECT-TYPE
    SYNTAX          Unsigned32
    MAX-ACCESS      read-only
    STATUS          current
    DESCRIPTION     
            "The ether type of the table entry."
    ::= { sonusServerProtectPolicerDiscardRingEntry 9 }

sonusServerProtectPolicerDiscardRingDestUnique OBJECT-TYPE
    SYNTAX          INTEGER { unique(1), notUnique(2) }
    MAX-ACCESS      read-only
    STATUS          current
    DESCRIPTION     
            "Determines if all discards were for a unique destination address"
    ::= { sonusServerProtectPolicerDiscardRingEntry 10 }

sonusRogueMediaPortQuarantineStatTable OBJECT-TYPE
    SYNTAX          SEQUENCE OF SonusRogueMediaPortQuarantineStatEntry
    MAX-ACCESS      not-accessible
    STATUS          current
    DESCRIPTION     
            ""
    ::= { sonusIpmMIBObjects 11 }

sonusRogueMediaPortQuarantineStatEntry OBJECT-TYPE
    SYNTAX          SonusRogueMediaPortQuarantineStatEntry
    MAX-ACCESS      not-accessible
    STATUS          current
    DESCRIPTION     
            ""
    INDEX           { sonusRogueMediaPortQuarantineStatShelfIndex, 
                      sonusRogueMediaPortQuarantineStatSlotIndex, 
                      sonusRogueMediaPortQuarantineStatPortIndex }
    ::= { sonusRogueMediaPortQuarantineStatTable 1 }

SonusRogueMediaPortQuarantineStatEntry ::=
    SEQUENCE {
        sonusRogueMediaPortQuarantineStatShelfIndex           SonusShelfIndex,
        sonusRogueMediaPortQuarantineStatSlotIndex          SonusSlotIndex,
        sonusRogueMediaPortQuarantineStatPortIndex          Integer32,
        sonusRogueMediaPortQuarantineStatCount      Integer32,
        sonusRogueMediaPortQuarantineStatHighCount          Integer32,
        sonusRogueMediaPortQuarantineStatTotalCount           Integer32,
        sonusRogueMediaPortQuarantineStatUsedCount          Integer32,
        sonusRogueMediaPortQuarantineStatUserAddCount             Integer32,
        sonusRogueMediaPortQuarantineStatUserRemoveCount                Integer32,
        sonusRogueMediaPortQuarantineStatUserIncrCount              Integer32,
        sonusRogueMediaPortQuarantineStatUserDecrCount              Integer32
    }

sonusRogueMediaPortQuarantineStatShelfIndex OBJECT-TYPE
    SYNTAX          SonusShelfIndex
    MAX-ACCESS      read-only
    STATUS          current
    DESCRIPTION     
            "Shelf index of the server."
    ::= { sonusRogueMediaPortQuarantineStatEntry 1 }

sonusRogueMediaPortQuarantineStatSlotIndex OBJECT-TYPE
    SYNTAX          SonusSlotIndex
    MAX-ACCESS      read-only
    STATUS          current
    DESCRIPTION     
            "Logical slot ID of the server."
    ::= { sonusRogueMediaPortQuarantineStatEntry 2 }

sonusRogueMediaPortQuarantineStatPortIndex OBJECT-TYPE
    SYNTAX          Integer32
    MAX-ACCESS      read-only
    STATUS          current
    DESCRIPTION     
            "Physical port number of the server."
    ::= { sonusRogueMediaPortQuarantineStatEntry 3 }

sonusRogueMediaPortQuarantineStatCount OBJECT-TYPE
    SYNTAX          Integer32
    MAX-ACCESS      read-only
    STATUS          current
    DESCRIPTION     
            "Current number of rogue media ports quarantined."
    ::= { sonusRogueMediaPortQuarantineStatEntry 4 }

sonusRogueMediaPortQuarantineStatHighCount OBJECT-TYPE
    SYNTAX          Integer32
    MAX-ACCESS      read-only
    STATUS          current
    DESCRIPTION     
            "Highest number of rogue media ports quarantined."
    ::= { sonusRogueMediaPortQuarantineStatEntry 5 }

sonusRogueMediaPortQuarantineStatTotalCount OBJECT-TYPE
    SYNTAX          Integer32
    MAX-ACCESS      read-only
    STATUS          current
    DESCRIPTION     
            "Total number of rogue media ports quarantined."
    ::= { sonusRogueMediaPortQuarantineStatEntry 6 }

sonusRogueMediaPortQuarantineStatUsedCount OBJECT-TYPE
    SYNTAX          Integer32
    MAX-ACCESS      read-only
    STATUS          current
    DESCRIPTION     
            "Number of rogue media ports quarantined that were used."
    ::= { sonusRogueMediaPortQuarantineStatEntry 7 }

sonusRogueMediaPortQuarantineStatUserAddCount OBJECT-TYPE
    SYNTAX          Integer32
    MAX-ACCESS      read-only
    STATUS          current
    DESCRIPTION     
            "Number of ports quarantined by user."
    ::= { sonusRogueMediaPortQuarantineStatEntry 8 }

sonusRogueMediaPortQuarantineStatUserRemoveCount OBJECT-TYPE
    SYNTAX          Integer32
    MAX-ACCESS      read-only
    STATUS          current
    DESCRIPTION     
            "Number of ports removed from quarantine list by user."
    ::= { sonusRogueMediaPortQuarantineStatEntry 9 }

sonusRogueMediaPortQuarantineStatUserIncrCount OBJECT-TYPE
    SYNTAX          Integer32
    MAX-ACCESS      read-only
    STATUS          current
    DESCRIPTION     
            "Number of ports user increased the metric count."
    ::= { sonusRogueMediaPortQuarantineStatEntry 10 }

sonusRogueMediaPortQuarantineStatUserDecrCount OBJECT-TYPE
    SYNTAX          Integer32
    MAX-ACCESS      read-only
    STATUS          current
    DESCRIPTION     
            "Number of ports user decreased the metric count."
    ::= { sonusRogueMediaPortQuarantineStatEntry 11 }

sonusRogueMediaPortQuarantineListTable OBJECT-TYPE
    SYNTAX          SEQUENCE OF SonusRogueMediaPortQuarantineListEntry
    MAX-ACCESS      not-accessible
    STATUS          current
    DESCRIPTION     
            ""
    ::= { sonusIpmMIBObjects 12 }

sonusRogueMediaPortQuarantineListEntry OBJECT-TYPE
    SYNTAX          SonusRogueMediaPortQuarantineListEntry
    MAX-ACCESS      not-accessible
    STATUS          current
    DESCRIPTION     
            ""
    INDEX           { sonusRogueMediaPortQuarantineListShelfIndex, 
                      sonusRogueMediaPortQuarantineListSlotIndex, 
                      sonusRogueMediaPortQuarantineListPortIndex, 
                      sonusRogueMediaPortQuarantineListRtpPort }
    ::= { sonusRogueMediaPortQuarantineListTable 1 }

SonusRogueMediaPortQuarantineListEntry ::=
    SEQUENCE {
        sonusRogueMediaPortQuarantineListShelfIndex           SonusShelfIndex,
        sonusRogueMediaPortQuarantineListSlotIndex          SonusSlotIndex,
        sonusRogueMediaPortQuarantineListPortIndex          Integer32,
        sonusRogueMediaPortQuarantineListRtpPort        Integer32,
        sonusRogueMediaPortQuarantineListMetric       Unsigned32
    }

sonusRogueMediaPortQuarantineListShelfIndex OBJECT-TYPE
    SYNTAX          SonusShelfIndex
    MAX-ACCESS      read-only
    STATUS          current
    DESCRIPTION     
            "Shelf index of the server."
    ::= { sonusRogueMediaPortQuarantineListEntry 1 }

sonusRogueMediaPortQuarantineListSlotIndex OBJECT-TYPE
    SYNTAX          SonusSlotIndex
    MAX-ACCESS      read-only
    STATUS          current
    DESCRIPTION     
            "Logical slot ID of the server."
    ::= { sonusRogueMediaPortQuarantineListEntry 2 }

sonusRogueMediaPortQuarantineListPortIndex OBJECT-TYPE
    SYNTAX          Integer32
    MAX-ACCESS      read-only
    STATUS          current
    DESCRIPTION     
            "Physical port number of the server."
    ::= { sonusRogueMediaPortQuarantineListEntry 3 }

sonusRogueMediaPortQuarantineListRtpPort OBJECT-TYPE
    SYNTAX          Integer32
    MAX-ACCESS      read-only
    STATUS          current
    DESCRIPTION     
            "Quarantined Rogue Media Port Number."
    ::= { sonusRogueMediaPortQuarantineListEntry 4 }

sonusRogueMediaPortQuarantineListMetric OBJECT-TYPE
    SYNTAX          Unsigned32
    MAX-ACCESS      read-only
    STATUS          current
    DESCRIPTION     
            "Metric count of the port number."
    ::= { sonusRogueMediaPortQuarantineListEntry 5 }

sonusRogueMediaPortQuarantineConfigPort OBJECT-TYPE
    SYNTAX          SEQUENCE OF SonusRogueMediaPortQuarantineConfigEntry
    MAX-ACCESS      not-accessible
    STATUS          current
    DESCRIPTION     
            ""
    ::= { sonusIpmMIBObjects 13 }

sonusRogueMediaPortQuarantineConfigEntry OBJECT-TYPE
    SYNTAX          SonusRogueMediaPortQuarantineConfigEntry
    MAX-ACCESS      not-accessible
    STATUS          current
    DESCRIPTION     
            ""
    INDEX           { sonusRogueMediaPortQuarantineConfigShelfIndex, 
                      sonusRogueMediaPortQuarantineConfigSlotIndex, 
                      sonusRogueMediaPortQuarantineConfigPortIndex }
    ::= { sonusRogueMediaPortQuarantineConfigPort 1 }

SonusRogueMediaPortQuarantineConfigEntry ::=
    SEQUENCE {
        sonusRogueMediaPortQuarantineConfigShelfIndex             SonusShelfIndex,
        sonusRogueMediaPortQuarantineConfigSlotIndex            SonusSlotIndex,
        sonusRogueMediaPortQuarantineConfigPortIndex            Integer32,
        sonusRogueMediaPortQuarantineConfigRtpPort          Integer32,
        sonusRogueMediaPortQuarantineConfigMetric         Integer32
    }

sonusRogueMediaPortQuarantineConfigShelfIndex OBJECT-TYPE
    SYNTAX          SonusShelfIndex
    MAX-ACCESS      read-only
    STATUS          current
    DESCRIPTION     
            "Shelf index of the server."
    ::= { sonusRogueMediaPortQuarantineConfigEntry 1 }

sonusRogueMediaPortQuarantineConfigSlotIndex OBJECT-TYPE
    SYNTAX          SonusSlotIndex
    MAX-ACCESS      read-only
    STATUS          current
    DESCRIPTION     
            "Logical slot ID of the server."
    ::= { sonusRogueMediaPortQuarantineConfigEntry 2 }

sonusRogueMediaPortQuarantineConfigPortIndex OBJECT-TYPE
    SYNTAX          Integer32
    MAX-ACCESS      read-only
    STATUS          current
    DESCRIPTION     
            "Physical port number of the server."
    ::= { sonusRogueMediaPortQuarantineConfigEntry 3 }

sonusRogueMediaPortQuarantineConfigRtpPort OBJECT-TYPE
    SYNTAX          Integer32
    MAX-ACCESS      read-write
    STATUS          current
    DESCRIPTION     
            "Quarantined Rogue Media RTP Port Number."
    ::= { sonusRogueMediaPortQuarantineConfigEntry 4 }

sonusRogueMediaPortQuarantineConfigMetric OBJECT-TYPE
    SYNTAX          Integer32
    MAX-ACCESS      read-write
    STATUS          current
    DESCRIPTION     
            "Metric count of the port number."
    ::= { sonusRogueMediaPortQuarantineConfigEntry 5 }

sonusLightGrayPolicerDiscardRingTable OBJECT-TYPE
    SYNTAX          SEQUENCE OF SonusLightGrayPolicerDiscardRingEntry
    MAX-ACCESS      not-accessible
    STATUS          current
    DESCRIPTION     
            "The table of statistics for the white list
             policer discard ring."
    ::= { sonusIpmMIBObjects 14 }

sonusLightGrayPolicerDiscardRingEntry OBJECT-TYPE
    SYNTAX          SonusLightGrayPolicerDiscardRingEntry
    MAX-ACCESS      not-accessible
    STATUS          current
    DESCRIPTION     
            "The white list discard ring entries."
    INDEX           { sonusLightGrayPolicerDiscardRingShelfIndex, 
                      sonusLightGrayPolicerDiscardRingSlotIndex, 
                      sonusLightGrayPolicerDiscardRingPositionIndex }
    ::= { sonusLightGrayPolicerDiscardRingTable 1 }

SonusLightGrayPolicerDiscardRingEntry ::=
    SEQUENCE {
        sonusLightGrayPolicerDiscardRingShelfIndex          SonusShelfIndex,
        sonusLightGrayPolicerDiscardRingSlotIndex         SonusSlotIndex,
        sonusLightGrayPolicerDiscardRingPositionIndex             Unsigned32,
        sonusLightGrayPolicerDiscardRingNIFSIFName          SonusNameReference,
        sonusLightGrayPolicerDiscardRingIpAddress         IpAddress,
        sonusLightGrayPolicerDiscardRingIpProtocol          Unsigned32,
        sonusLightGrayPolicerDiscardRingDiscardCount            Counter32,
        sonusLightGrayPolicerDiscardRingIp6Address          Ipv6Address,
        sonusLightGrayPolicerDiscardRingIpVer     INTEGER
    }

sonusLightGrayPolicerDiscardRingShelfIndex OBJECT-TYPE
    SYNTAX          SonusShelfIndex
    MAX-ACCESS      read-only
    STATUS          current
    DESCRIPTION     
            "The shelf index into this table."
    ::= { sonusLightGrayPolicerDiscardRingEntry 1 }

sonusLightGrayPolicerDiscardRingSlotIndex OBJECT-TYPE
    SYNTAX          SonusSlotIndex
    MAX-ACCESS      read-only
    STATUS          current
    DESCRIPTION     
            "The slot index into this table."
    ::= { sonusLightGrayPolicerDiscardRingEntry 2 }

sonusLightGrayPolicerDiscardRingPositionIndex OBJECT-TYPE
    SYNTAX          Unsigned32
    MAX-ACCESS      read-only
    STATUS          current
    DESCRIPTION     
            "The position index into this table ordered by
             worst offender with 1 being the worst."
    ::= { sonusLightGrayPolicerDiscardRingEntry 3 }

sonusLightGrayPolicerDiscardRingNIFSIFName OBJECT-TYPE
    SYNTAX          SonusNameReference
    MAX-ACCESS      read-only
    STATUS          current
    DESCRIPTION     
            "The name of the NIF or sub-interface of 
             table entry."
    ::= { sonusLightGrayPolicerDiscardRingEntry 4 }

sonusLightGrayPolicerDiscardRingIpAddress OBJECT-TYPE
    SYNTAX          IpAddress
    MAX-ACCESS      read-only
    STATUS          current
    DESCRIPTION     
            "The IPv4 address of the table entry."
    ::= { sonusLightGrayPolicerDiscardRingEntry 5 }

sonusLightGrayPolicerDiscardRingIpProtocol OBJECT-TYPE
    SYNTAX          Unsigned32
    MAX-ACCESS      read-only
    STATUS          current
    DESCRIPTION     
            "The IP Protocol of the table entry."
    ::= { sonusLightGrayPolicerDiscardRingEntry 6 }

sonusLightGrayPolicerDiscardRingDiscardCount OBJECT-TYPE
    SYNTAX          Counter32
    MAX-ACCESS      read-only
    STATUS          current
    DESCRIPTION     
            "The number of packets discarded by the policer."
    ::= { sonusLightGrayPolicerDiscardRingEntry 7 }

sonusLightGrayPolicerDiscardRingIp6Address OBJECT-TYPE
    SYNTAX          Ipv6Address
    MAX-ACCESS      read-write
    STATUS          current
    DESCRIPTION     
            "The Stat IPv6 address"
    ::= { sonusLightGrayPolicerDiscardRingEntry 8 }

sonusLightGrayPolicerDiscardRingIpVer OBJECT-TYPE
    SYNTAX          INTEGER { afInet(2), afInet6(24) }
    MAX-ACCESS      read-only
    STATUS          current
    DESCRIPTION     
            "IP address version of the peer of this connection"
    ::= { sonusLightGrayPolicerDiscardRingEntry 9 }

sonusVLanPolicerDiscardRingTable OBJECT-TYPE
    SYNTAX          SEQUENCE OF SonusVLanPolicerDiscardRingEntry
    MAX-ACCESS      not-accessible
    STATUS          current
    DESCRIPTION     
            "The table of statistics for the white list
             policer discard ring."
    ::= { sonusIpmMIBObjects 15 }

sonusVLanPolicerDiscardRingEntry OBJECT-TYPE
    SYNTAX          SonusVLanPolicerDiscardRingEntry
    MAX-ACCESS      not-accessible
    STATUS          current
    DESCRIPTION     
            "The white list discard ring entries."
    INDEX           { sonusVLanPolicerDiscardRingShelfIndex, 
                      sonusVLanPolicerDiscardRingSlotIndex, 
                      sonusVLanPolicerDiscardRingPositionIndex }
    ::= { sonusVLanPolicerDiscardRingTable 1 }

SonusVLanPolicerDiscardRingEntry ::=
    SEQUENCE {
        sonusVLanPolicerDiscardRingShelfIndex     SonusShelfIndex,
        sonusVLanPolicerDiscardRingSlotIndex    SonusSlotIndex,
        sonusVLanPolicerDiscardRingPositionIndex        Unsigned32,
        sonusVLanPolicerDiscardRingNIFSIFName     SonusNameReference,
        sonusVLanPolicerDiscardRingIpAddress    IpAddress,
        sonusVLanPolicerDiscardRingIpProtocol     Unsigned32,
        sonusVLanPolicerDiscardRingDiscardCount       Counter32,
        sonusVLanPolicerDiscardRingIp6Address     Ipv6Address,
        sonusVLanPolicerDiscardRingIpVer INTEGER
    }

sonusVLanPolicerDiscardRingShelfIndex OBJECT-TYPE
    SYNTAX          SonusShelfIndex
    MAX-ACCESS      read-only
    STATUS          current
    DESCRIPTION     
            "The shelf index into this table."
    ::= { sonusVLanPolicerDiscardRingEntry 1 }

sonusVLanPolicerDiscardRingSlotIndex OBJECT-TYPE
    SYNTAX          SonusSlotIndex
    MAX-ACCESS      read-only
    STATUS          current
    DESCRIPTION     
            "The slot index into this table."
    ::= { sonusVLanPolicerDiscardRingEntry 2 }

sonusVLanPolicerDiscardRingPositionIndex OBJECT-TYPE
    SYNTAX          Unsigned32
    MAX-ACCESS      read-only
    STATUS          current
    DESCRIPTION     
            "The position index into this table ordered by
             worst offender with 1 being the worst."
    ::= { sonusVLanPolicerDiscardRingEntry 3 }

sonusVLanPolicerDiscardRingNIFSIFName OBJECT-TYPE
    SYNTAX          SonusNameReference
    MAX-ACCESS      read-only
    STATUS          current
    DESCRIPTION     
            "The name of the NIF or sub-interface of 
             table entry."
    ::= { sonusVLanPolicerDiscardRingEntry 4 }

sonusVLanPolicerDiscardRingIpAddress OBJECT-TYPE
    SYNTAX          IpAddress
    MAX-ACCESS      read-only
    STATUS          current
    DESCRIPTION     
            "The IPv4 address of the table entry."
    ::= { sonusVLanPolicerDiscardRingEntry 5 }

sonusVLanPolicerDiscardRingIpProtocol OBJECT-TYPE
    SYNTAX          Unsigned32
    MAX-ACCESS      read-only
    STATUS          current
    DESCRIPTION     
            "The IP Protocol of the table entry."
    ::= { sonusVLanPolicerDiscardRingEntry 6 }

sonusVLanPolicerDiscardRingDiscardCount OBJECT-TYPE
    SYNTAX          Counter32
    MAX-ACCESS      read-only
    STATUS          current
    DESCRIPTION     
            "The number of packets discarded by the policer."
    ::= { sonusVLanPolicerDiscardRingEntry 7 }

sonusVLanPolicerDiscardRingIp6Address OBJECT-TYPE
    SYNTAX          Ipv6Address
    MAX-ACCESS      read-write
    STATUS          current
    DESCRIPTION     
            "The Stat IPv6 address"
    ::= { sonusVLanPolicerDiscardRingEntry 8 }

sonusVLanPolicerDiscardRingIpVer OBJECT-TYPE
    SYNTAX          INTEGER { afInet(2), afInet6(24) }
    MAX-ACCESS      read-only
    STATUS          current
    DESCRIPTION     
            "IP address version of the peer of this connection"
    ::= { sonusVLanPolicerDiscardRingEntry 9 }

sonusIpmMIBNotifications OBJECT IDENTIFIER
    ::= { sonusIpmMIB 2 }

sonusIpmMIBNotificationsPrefix OBJECT IDENTIFIER
    ::= { sonusIpmMIBNotifications 0 }

sonusIpmMIBNotificationsObjects OBJECT IDENTIFIER
    ::= { sonusIpmMIBNotifications 1 }

sonusPolicerTypeStr OBJECT-TYPE
    SYNTAX          DisplayString (SIZE(1..32))
    MAX-ACCESS      read-only
    STATUS          current
    DESCRIPTION     
            "The policer type whose alarm state has changed."
    ::= { sonusIpmMIBNotificationsObjects 1 }

sonusPolicerLevelStr OBJECT-TYPE
    SYNTAX          DisplayString (SIZE(1..8))
    MAX-ACCESS      read-only
    STATUS          current
    DESCRIPTION     
            "The previous policer alarm level reported when the alarm 
             state has changed."
    ::= { sonusIpmMIBNotificationsObjects 2 }

sonusNodePolicerMinorAlarmNotification NOTIFICATION-TYPE
    OBJECTS         { sonusShelfIndex, sonusPolicerTypeStr, 
                      sonusPolicerLevelStr, sonusEventDescription, 
                      sonusEventClass, sonusEventLevel, sonusSequenceId, 
                      sonusEventTime }
    STATUS          current
    DESCRIPTION     
            "The sonusNodePolicerMinorAlarmNotification indicates
             a system policer minor level alarm."
    ::= { sonusIpmMIBNotificationsPrefix 1 }

sonusNodePolicerMajorAlarmNotification NOTIFICATION-TYPE
    OBJECTS         { sonusShelfIndex, sonusPolicerTypeStr, 
                      sonusPolicerLevelStr, sonusEventDescription, 
                      sonusEventClass, sonusEventLevel, sonusSequenceId, 
                      sonusEventTime }
    STATUS          current
    DESCRIPTION     
            "The sonusNodePolicerMajorAlarmNotification indicates
             a system policer major level alarm."
    ::= { sonusIpmMIBNotificationsPrefix 2 }

sonusNodePolicerClearAlarmNotification NOTIFICATION-TYPE
    OBJECTS         { sonusShelfIndex, sonusPolicerTypeStr, 
                      sonusPolicerLevelStr, sonusEventDescription, 
                      sonusEventClass, sonusEventLevel, sonusSequenceId, 
                      sonusEventTime }
    STATUS          current
    DESCRIPTION     
            "The sonusNodePolicerClearAlarmNotification indicates
             a system policer alarm clear."
    ::= { sonusIpmMIBNotificationsPrefix 3 }

sonusServerPolicerMinorAlarmNotification NOTIFICATION-TYPE
    OBJECTS         { sonusShelfIndex, sonusSlotIndex, 
                      sonusPolicerTypeStr, sonusPolicerLevelStr, 
                      sonusEventDescription, sonusEventClass, 
                      sonusEventLevel, sonusSequenceId, sonusEventTime }
    STATUS          current
    DESCRIPTION     
            "The sonusServerPolicerMinorAlarmNotification indicates
             a server policer minor level alarm."
    ::= { sonusIpmMIBNotificationsPrefix 4 }

sonusServerPolicerMajorAlarmNotification NOTIFICATION-TYPE
    OBJECTS         { sonusShelfIndex, sonusSlotIndex, 
                      sonusPolicerTypeStr, sonusPolicerLevelStr, 
                      sonusEventDescription, sonusEventClass, 
                      sonusEventLevel, sonusSequenceId, sonusEventTime }
    STATUS          current
    DESCRIPTION     
            "The sonusServerPolicerMajorAlarmNotification indicates
             a server policer major level alarm."
    ::= { sonusIpmMIBNotificationsPrefix 5 }

sonusServerPolicerClearAlarmNotification NOTIFICATION-TYPE
    OBJECTS         { sonusShelfIndex, sonusSlotIndex, 
                      sonusPolicerTypeStr, sonusPolicerLevelStr, 
                      sonusEventDescription, sonusEventClass, 
                      sonusEventLevel, sonusSequenceId, sonusEventTime }
    STATUS          current
    DESCRIPTION     
            "The sonusServerPolicerClearAlarmNotification indicates
             a server policer clear level alarm."
    ::= { sonusIpmMIBNotificationsPrefix 6 }

END -- end of module SONUS-IPM-MIB.
