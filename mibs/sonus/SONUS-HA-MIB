--
-- This SMIv2 module has been generated by smidump 0.2-cvs. Do not edit.
--

SONUS-HA-MIB DEFINITIONS ::= BEGIN

IMPORTS
    Counter32, Counter64, Gauge32, Integer32, IpAddress, MODULE-IDENTITY, 
    OBJECT-TYPE, Unsigned32
        FROM SNMPv2-SMI
    DateAndTime, RowStatus, TEXTUAL-CONVENTION, TruthValue
        FROM SNMPv2-TC
    sonusCommonSoftwarePlatformServicesMIBs
        FROM SONUS-SMI;

sonusHaPortMIB MODULE-IDENTITY
    LAST-UPDATED    "201212310000Z"
    ORGANIZATION    
            "Sonus Networks, Inc."
    CONTACT-INFO    
            "Customer Support        
             Sonus Networks, Inc.    
             4 Technology Park Drive 
             Westford, MA 01886      
             USA                     
                                     
             Tel: 978-614-8100       
             Fax: 978-614-8609"
    DESCRIPTION     
            "The MIB Module for High Availability Port Management."
    REVISION        "201212310000Z"
    DESCRIPTION     
            "Auto generated MIB."
    ::= { sonusCommonSoftwarePlatformServicesMIBs 10 }


ConfdString ::= TEXTUAL-CONVENTION
    DISPLAY-HINT    "1t"
    STATUS          current
    DESCRIPTION     
            "xs: and confd: types mapped to strings"
    SYNTAX          OCTET STRING

InetAddressIP ::= TEXTUAL-CONVENTION
    STATUS          current
    DESCRIPTION     
            "confd:inetAddressIP"
    SYNTAX          OCTET STRING (SIZE(4 | 16))

String ::= TEXTUAL-CONVENTION
    DISPLAY-HINT    "1t"
    STATUS          current
    DESCRIPTION     
            "xs:string"
    SYNTAX          OCTET STRING

SonusNifOnOrOff ::= TEXTUAL-CONVENTION
    STATUS          current
    DESCRIPTION     
            ""
    SYNTAX          INTEGER { on(1), off(2) }

SonusNifNegotiatedSpeedType ::= TEXTUAL-CONVENTION
    STATUS          current
    DESCRIPTION     
            ""
    SYNTAX          INTEGER { speed10Mbps(1), speed100Mbps(2), 
                        speed1000Mbps(3), unknown(4), speed10Gbps(5) }

OosReasonType ::= TEXTUAL-CONVENTION
    STATUS          current
    DESCRIPTION     
            ""
    SYNTAX          INTEGER { na(1), noSignal(4), noRemoteResponse(5) }

SonusNifDuplexModeType ::= TEXTUAL-CONVENTION
    STATUS          current
    DESCRIPTION     
            ""
    SYNTAX          INTEGER { half(1), full(2) }

SonusNifTypeType ::= TEXTUAL-CONVENTION
    STATUS          current
    DESCRIPTION     
            ""
    SYNTAX          INTEGER { bondingDevice(1), ethernetPort(2) }

sonusHighAvailabilityPort OBJECT IDENTIFIER
    ::= { sonusHaPortMIB 1 }

sonusHighAvailabilityPortStatusTable OBJECT-TYPE
    SYNTAX          SEQUENCE OF SonusHighAvailabilityPortStatusEntry
    MAX-ACCESS      not-accessible
    STATUS          current
    DESCRIPTION     
            ""
    ::= { sonusHighAvailabilityPort 1 }

sonusHighAvailabilityPortStatusEntry OBJECT-TYPE
    SYNTAX          SonusHighAvailabilityPortStatusEntry
    MAX-ACCESS      not-accessible
    STATUS          current
    DESCRIPTION     
            ""
    INDEX           { sonusHighAvailabilityPortStatusCeName, 
                      sonusHighAvailabilityPortStatusPortName }
    ::= { sonusHighAvailabilityPortStatusTable 1 }

SonusHighAvailabilityPortStatusEntry ::=
    SEQUENCE {
        sonusHighAvailabilityPortStatusCeName     String,
        sonusHighAvailabilityPortStatusPortName       String,
        sonusHighAvailabilityPortStatusMacAddress         String,
        sonusHighAvailabilityPortStatusIpAddress        InetAddressIP,
        sonusHighAvailabilityPortStatusNegotiatedSpeed              SonusNifNegotiatedSpeedType,
        sonusHighAvailabilityPortStatusOosReason        OosReasonType
    }

sonusHighAvailabilityPortStatusCeName OBJECT-TYPE
    SYNTAX          String (SIZE(0..255))
    MAX-ACCESS      not-accessible
    STATUS          current
    DESCRIPTION     
            "
             The host name is this server.
             "
    ::= { sonusHighAvailabilityPortStatusEntry 1 }

sonusHighAvailabilityPortStatusPortName OBJECT-TYPE
    SYNTAX          String (SIZE(0..23))
    MAX-ACCESS      not-accessible
    STATUS          current
    DESCRIPTION     
            "
             The name of the port.
             "
    ::= { sonusHighAvailabilityPortStatusEntry 2 }

sonusHighAvailabilityPortStatusMacAddress OBJECT-TYPE
    SYNTAX          String (SIZE(0..255))
    MAX-ACCESS      read-only
    STATUS          current
    DESCRIPTION     
            "
             The MAC address of this port.
             "
    ::= { sonusHighAvailabilityPortStatusEntry 3 }

sonusHighAvailabilityPortStatusIpAddress OBJECT-TYPE
    SYNTAX          InetAddressIP
    MAX-ACCESS      read-only
    STATUS          current
    DESCRIPTION     
            "
             The IP address of this port.
             "
    ::= { sonusHighAvailabilityPortStatusEntry 4 }

sonusHighAvailabilityPortStatusNegotiatedSpeed OBJECT-TYPE
    SYNTAX          SonusNifNegotiatedSpeedType
    MAX-ACCESS      read-only
    STATUS          current
    DESCRIPTION     
            "
             The negotiated speed of this port.
             "
    ::= { sonusHighAvailabilityPortStatusEntry 5 }

sonusHighAvailabilityPortStatusOosReason OBJECT-TYPE
    SYNTAX          OosReasonType
    MAX-ACCESS      read-only
    STATUS          current
    DESCRIPTION     
            "
             The reason this port is out of service.
             "
    ::= { sonusHighAvailabilityPortStatusEntry 6 }

sonusHighAvailabilityPortStatisticsTable OBJECT-TYPE
    SYNTAX          SEQUENCE OF SonusHighAvailabilityPortStatisticsEntry
    MAX-ACCESS      not-accessible
    STATUS          current
    DESCRIPTION     
            ""
    ::= { sonusHighAvailabilityPort 2 }

sonusHighAvailabilityPortStatisticsEntry OBJECT-TYPE
    SYNTAX          SonusHighAvailabilityPortStatisticsEntry
    MAX-ACCESS      not-accessible
    STATUS          current
    DESCRIPTION     
            ""
    INDEX           { sonusHighAvailabilityPortStatisticsCeName, 
                      sonusHighAvailabilityPortStatisticsPortName }
    ::= { sonusHighAvailabilityPortStatisticsTable 1 }

SonusHighAvailabilityPortStatisticsEntry ::=
    SEQUENCE {
        sonusHighAvailabilityPortStatisticsCeName         String,
        sonusHighAvailabilityPortStatisticsPortName           String,
        sonusHighAvailabilityPortStatisticsPacketTx           Counter64,
        sonusHighAvailabilityPortStatisticsByteTx         Counter64,
        sonusHighAvailabilityPortStatisticsErrTx        Counter32,
        sonusHighAvailabilityPortStatisticsPacketRx           Counter64,
        sonusHighAvailabilityPortStatisticsByteRx         Counter64,
        sonusHighAvailabilityPortStatisticsCrcErrRx           Counter32,
        sonusHighAvailabilityPortStatisticsOverErrRx            Counter32,
        sonusHighAvailabilityPortStatisticsNoBufCntRx             Counter32,
        sonusHighAvailabilityPortStatisticsAllocRxBufFailRx                   Counter32
    }

sonusHighAvailabilityPortStatisticsCeName OBJECT-TYPE
    SYNTAX          String (SIZE(0..255))
    MAX-ACCESS      not-accessible
    STATUS          current
    DESCRIPTION     
            "
             The host name is this server.
             "
    ::= { sonusHighAvailabilityPortStatisticsEntry 1 }

sonusHighAvailabilityPortStatisticsPortName OBJECT-TYPE
    SYNTAX          String (SIZE(0..23))
    MAX-ACCESS      not-accessible
    STATUS          current
    DESCRIPTION     
            "
             The name of the port.
             "
    ::= { sonusHighAvailabilityPortStatisticsEntry 2 }

sonusHighAvailabilityPortStatisticsPacketTx OBJECT-TYPE
    SYNTAX          Counter64
    MAX-ACCESS      read-only
    STATUS          current
    DESCRIPTION     
            "
             The number of packets transmitted.
             "
    ::= { sonusHighAvailabilityPortStatisticsEntry 3 }

sonusHighAvailabilityPortStatisticsByteTx OBJECT-TYPE
    SYNTAX          Counter64
    MAX-ACCESS      read-only
    STATUS          current
    DESCRIPTION     
            "
             The number of bytes transmitted.
             "
    ::= { sonusHighAvailabilityPortStatisticsEntry 4 }

sonusHighAvailabilityPortStatisticsErrTx OBJECT-TYPE
    SYNTAX          Counter32
    MAX-ACCESS      read-only
    STATUS          current
    DESCRIPTION     
            "
             The number of transmit errors.
             "
    ::= { sonusHighAvailabilityPortStatisticsEntry 5 }

sonusHighAvailabilityPortStatisticsPacketRx OBJECT-TYPE
    SYNTAX          Counter64
    MAX-ACCESS      read-only
    STATUS          current
    DESCRIPTION     
            "
             The number of packets received.
             "
    ::= { sonusHighAvailabilityPortStatisticsEntry 6 }

sonusHighAvailabilityPortStatisticsByteRx OBJECT-TYPE
    SYNTAX          Counter64
    MAX-ACCESS      read-only
    STATUS          current
    DESCRIPTION     
            "
             The number of bytes received.
             "
    ::= { sonusHighAvailabilityPortStatisticsEntry 7 }

sonusHighAvailabilityPortStatisticsCrcErrRx OBJECT-TYPE
    SYNTAX          Counter32
    MAX-ACCESS      read-only
    STATUS          current
    DESCRIPTION     
            "
             The number of receive CRC errors.
             "
    ::= { sonusHighAvailabilityPortStatisticsEntry 8 }

sonusHighAvailabilityPortStatisticsOverErrRx OBJECT-TYPE
    SYNTAX          Counter32
    MAX-ACCESS      read-only
    STATUS          current
    DESCRIPTION     
            "
             The number of receive overrun errors.
             "
    ::= { sonusHighAvailabilityPortStatisticsEntry 9 }

sonusHighAvailabilityPortStatisticsNoBufCntRx OBJECT-TYPE
    SYNTAX          Counter32
    MAX-ACCESS      read-only
    STATUS          current
    DESCRIPTION     
            "
             The number of receive no buffer errors.
             "
    ::= { sonusHighAvailabilityPortStatisticsEntry 10 }

sonusHighAvailabilityPortStatisticsAllocRxBufFailRx OBJECT-TYPE
    SYNTAX          Counter32
    MAX-ACCESS      read-only
    STATUS          current
    DESCRIPTION     
            "
             The number of receive buffer allocation errors.
             "
    ::= { sonusHighAvailabilityPortStatisticsEntry 11 }

END -- end of module SONUS-HA-MIB.
