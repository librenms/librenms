--
-- This SMIv2 module has been generated by smidump 0.2-cvs. Do not edit.
--

SONUS-LOAD-TEST-MIB DEFINITIONS ::= BEGIN

IMPORTS
    Counter32, Integer32, MODULE-IDENTITY, OBJECT-TYPE, Unsigned32
        FROM SNMPv2-SMI
    RowStatus
        FROM SNMPv2-TC
    sonusToolsMIBs
        FROM SONUS-SMI
    SonusAdminState, SonusName, SonusNameReference
        FROM SONUS-TC;

sonusLoadTestMIB MODULE-IDENTITY
    LAST-UPDATED    "201105240000Z"
    ORGANIZATION    
            "Sonus Networks, Inc."
    CONTACT-INFO    
            "   Customer Support    
             Sonus Networks, Inc.
             7 Technology Park Drive
             Westford, MA 01886
             USA
             
             Tel: 978-614-8100
             Fax: 978-614-8609"
    DESCRIPTION     
            "The MIB Module for Load Test Configuration."
    ::= { sonusToolsMIBs 2 }


sonusLoadTestMIBObjects OBJECT IDENTIFIER
    ::= { sonusLoadTestMIB 1 }

sonusLoadTestTable OBJECT-TYPE
    SYNTAX          SEQUENCE OF SonusLoadTestEntry
    MAX-ACCESS      not-accessible
    STATUS          current
    DESCRIPTION     
            "This table specifies the Load Test Table."
    ::= { sonusLoadTestMIBObjects 1 }

sonusLoadTestEntry OBJECT-TYPE
    SYNTAX          SonusLoadTestEntry
    MAX-ACCESS      not-accessible
    STATUS          current
    DESCRIPTION     
            ""
    INDEX           { sonusLoadTestIndex }
    ::= { sonusLoadTestTable 1 }

SonusLoadTestEntry ::=
    SEQUENCE {
        sonusLoadTestIndex              Integer32,
        sonusLoadTestName               SonusName,
        sonusLoadTestCallAttempt        Integer32,
        sonusLoadTestCallDuration       Integer32,
        sonusLoadTestVoiceTraffic       INTEGER,
        sonusLoadTestBurstCalls         Integer32,
        sonusLoadTestBurstDuration      Integer32,
        sonusLoadTestBurstState         INTEGER,
        sonusLoadTestTrunkGroupName     SonusNameReference,
        sonusLoadTestCircuitServiceProfile  SonusNameReference,
        sonusLoadTestNodePointCode      Integer32,
        sonusLoadTestMode               INTEGER,
        sonusLoadTestState              INTEGER,
        sonusLoadTestRowStatus          RowStatus,
        sonusLoadTestNodeName           SonusName,
        sonusLoadTestNodeHandle         Integer32
    }

sonusLoadTestIndex OBJECT-TYPE
    SYNTAX          Integer32
    MAX-ACCESS      read-only
    STATUS          current
    DESCRIPTION     
            "The index of the Load Test entry."
    ::= { sonusLoadTestEntry 1 }

sonusLoadTestName OBJECT-TYPE
    SYNTAX          SonusName
    MAX-ACCESS      read-write
    STATUS          current
    DESCRIPTION     
            "The name of this Load Test entry."
    ::= { sonusLoadTestEntry 2 }

sonusLoadTestCallAttempt OBJECT-TYPE
    SYNTAX          Integer32 (1..1000)
    MAX-ACCESS      read-write
    STATUS          current
    DESCRIPTION     
            "The call attempt (calls/second) of this Load Test Entry."
    DEFVAL          { 1 }
    ::= { sonusLoadTestEntry 3 }

sonusLoadTestCallDuration OBJECT-TYPE
    SYNTAX          Integer32
    MAX-ACCESS      read-write
    STATUS          current
    DESCRIPTION     
            "The call duration (second) of this Load Test Entry."
    DEFVAL          { 15 }
    ::= { sonusLoadTestEntry 4 }

sonusLoadTestVoiceTraffic OBJECT-TYPE
    SYNTAX          INTEGER { disabled(1), enabled(2) }
    MAX-ACCESS      read-write
    STATUS          current
    DESCRIPTION     
            "The voice traffic option of this Load Test entry."
    DEFVAL          { enabled }
    ::= { sonusLoadTestEntry 5 }

sonusLoadTestBurstCalls OBJECT-TYPE
    SYNTAX          Integer32 (0..1000)
    MAX-ACCESS      read-write
    STATUS          current
    DESCRIPTION     
            "The Burst Calls of this Load Test Entry."
    DEFVAL          { 0 }
    ::= { sonusLoadTestEntry 6 }

sonusLoadTestBurstDuration OBJECT-TYPE
    SYNTAX          Integer32 (1..100)
    MAX-ACCESS      read-write
    STATUS          current
    DESCRIPTION     
            "The Burst Duration (second) of this Load Test Entry."
    DEFVAL          { 1 }
    ::= { sonusLoadTestEntry 7 }

sonusLoadTestBurstState OBJECT-TYPE
    SYNTAX          INTEGER { disabled(1), enabled(2) }
    MAX-ACCESS      read-write
    STATUS          current
    DESCRIPTION     
            "The administrative call burst state of this Load Test entry."
    DEFVAL          { disabled }
    ::= { sonusLoadTestEntry 8 }

sonusLoadTestTrunkGroupName OBJECT-TYPE
    SYNTAX          SonusNameReference
    MAX-ACCESS      read-write
    STATUS          current
    DESCRIPTION     
            "The name of the Trunk Group Name to to be used by the Load Test to hunt for available DS0."
    ::= { sonusLoadTestEntry 9 }

sonusLoadTestCircuitServiceProfile OBJECT-TYPE
    SYNTAX          SonusNameReference
    MAX-ACCESS      read-write
    STATUS          current
    DESCRIPTION     
            "The name of the Circuit Service Profile used by the Load Test."
    ::= { sonusLoadTestEntry 10 }

sonusLoadTestNodePointCode OBJECT-TYPE
    SYNTAX          Integer32
    MAX-ACCESS      read-write
    STATUS          current
    DESCRIPTION     
            "The SS7 point code assigned to this Load Test Node entry."
    ::= { sonusLoadTestEntry 11 }

sonusLoadTestMode OBJECT-TYPE
    SYNTAX          INTEGER { paced(1), burst(2) }
    MAX-ACCESS      read-write
    STATUS          current
    DESCRIPTION     
            "The administrative mode of this Load Test entry."
    DEFVAL          { paced }
    ::= { sonusLoadTestEntry 12 }

sonusLoadTestState OBJECT-TYPE
    SYNTAX          INTEGER { disabled(1), enabled(2) }
    MAX-ACCESS      read-write
    STATUS          current
    DESCRIPTION     
            "The administrative state of this Load Test entry."
    DEFVAL          { disabled }
    ::= { sonusLoadTestEntry 13 }

sonusLoadTestRowStatus OBJECT-TYPE
    SYNTAX          RowStatus
    MAX-ACCESS      read-write
    STATUS          current
    DESCRIPTION     
            ""
    ::= { sonusLoadTestEntry 14 }

sonusLoadTestNodeName OBJECT-TYPE
    SYNTAX          SonusName
    MAX-ACCESS      read-only
    STATUS          current
    DESCRIPTION     
            "SS7 Node name ."
    ::= { sonusLoadTestEntry 15 }

sonusLoadTestNodeHandle OBJECT-TYPE
    SYNTAX          Integer32
    MAX-ACCESS      read-write
    STATUS          current
    DESCRIPTION     
            "The SS7 node handle assigned to this Load Test Node entry."
    ::= { sonusLoadTestEntry 16 }

sonusLoadTestDestNumberTable OBJECT-TYPE
    SYNTAX          SEQUENCE OF SonusLoadTestDestNumberEntry
    MAX-ACCESS      not-accessible
    STATUS          current
    DESCRIPTION     
            "This table specifies the destination numbers for Load Test Table"
    ::= { sonusLoadTestMIBObjects 2 }

sonusLoadTestDestNumberEntry OBJECT-TYPE
    SYNTAX          SonusLoadTestDestNumberEntry
    MAX-ACCESS      not-accessible
    STATUS          current
    DESCRIPTION     
            ""
    INDEX           { sonusLoadTestEntryIndex, 
                      sonusLoadTestDestNumberIndex }
    ::= { sonusLoadTestDestNumberTable 1 }

SonusLoadTestDestNumberEntry ::=
    SEQUENCE {
        sonusLoadTestEntryIndex         Integer32,
        sonusLoadTestDestNumberIndex    Integer32,
        sonusLoadTestDestNumber         SonusNameReference,
        sonusLoadTestDestNumberPercentage Integer32,
        sonusLoadTestDestNumberBurstFlag INTEGER,
        sonusLoadTestDestNumberState    INTEGER,
        sonusLoadTestDestNumberRowStatus RowStatus,
        sonusLoadTestDestNumberIamRef   Integer32
    }

sonusLoadTestEntryIndex OBJECT-TYPE
    SYNTAX          Integer32
    MAX-ACCESS      read-only
    STATUS          current
    DESCRIPTION     
            "The index of Load Test entry of this destination number belongs to."
    ::= { sonusLoadTestDestNumberEntry 1 }

sonusLoadTestDestNumberIndex OBJECT-TYPE
    SYNTAX          Integer32
    MAX-ACCESS      read-only
    STATUS          current
    DESCRIPTION     
            "The index of this Load Test destination number entry."
    ::= { sonusLoadTestDestNumberEntry 2 }

sonusLoadTestDestNumber OBJECT-TYPE
    SYNTAX          SonusNameReference
    MAX-ACCESS      read-write
    STATUS          current
    DESCRIPTION     
            "The number of this Load Test destination number entry."
    ::= { sonusLoadTestDestNumberEntry 3 }

sonusLoadTestDestNumberPercentage OBJECT-TYPE
    SYNTAX          Integer32 (1..100)
    MAX-ACCESS      read-write
    STATUS          current
    DESCRIPTION     
            "The percentage (10% for each increment) of the total call attempt of this Load Test destination number Entry."
    ::= { sonusLoadTestDestNumberEntry 4 }

sonusLoadTestDestNumberBurstFlag OBJECT-TYPE
    SYNTAX          INTEGER { disabled(1), enabled(2) }
    MAX-ACCESS      read-write
    STATUS          current
    DESCRIPTION     
            "The burst flag of this Load Test destination number Entry."
    DEFVAL          { disabled }
    ::= { sonusLoadTestDestNumberEntry 5 }

sonusLoadTestDestNumberState OBJECT-TYPE
    SYNTAX          INTEGER { disabled(1), enabled(2) }
    MAX-ACCESS      read-write
    STATUS          current
    DESCRIPTION     
            "The administrative state of this Load Test destination number entry."
    DEFVAL          { disabled }
    ::= { sonusLoadTestDestNumberEntry 6 }

sonusLoadTestDestNumberRowStatus OBJECT-TYPE
    SYNTAX          RowStatus
    MAX-ACCESS      read-write
    STATUS          current
    DESCRIPTION     
            ""
    ::= { sonusLoadTestDestNumberEntry 7 }

sonusLoadTestDestNumberIamRef OBJECT-TYPE
    SYNTAX          Integer32 (0..25)
    MAX-ACCESS      read-write
    STATUS          current
    DESCRIPTION     
            "Reference to an IAM entry to associate with this Load Test destination number entry."
    ::= { sonusLoadTestDestNumberEntry 8 }

sonusLoadTestStatusTable OBJECT-TYPE
    SYNTAX          SEQUENCE OF SonusLoadTestStatusEntry
    MAX-ACCESS      not-accessible
    STATUS          current
    DESCRIPTION     
            "This table contains status of the load test."
    ::= { sonusLoadTestMIBObjects 3 }

sonusLoadTestStatusEntry OBJECT-TYPE
    SYNTAX          SonusLoadTestStatusEntry
    MAX-ACCESS      not-accessible
    STATUS          current
    DESCRIPTION     
            "Status of loadtest."
    INDEX           { sonusLoadTestStatusIndex }
    ::= { sonusLoadTestStatusTable 1 }

SonusLoadTestStatusEntry ::=
    SEQUENCE {
        sonusLoadTestStatusIndex        Integer32,
        sonusLoadTestNumCallInitiated   Integer32,
        sonusLoadTestNumCallFailed      Integer32,
        sonusLoadTestNumTrmAlloFailed   Integer32,
        sonusLoadTestNumTrmAlloTimedOut Integer32,
        sonusLoadTestNumCallEstablished Integer32,
        sonusLoadTestNumCallReleased    Integer32,
        sonusLoadTestNumUnexpected      Integer32,
        sonusLoadTestNumAcmTimeOutRcvd  Integer32,
        sonusLoadTestNumLocalAcmTimeOut Integer32,
        sonusLoadTestNumAnmTimeOutRcvd  Integer32,
        sonusLoadTestNumLocalAnmTimeOut Integer32,
        sonusLoadTestNumLocalRelTimeOut Integer32,
        sonusLoadTestNumUnexpectedRelRcvdGen    Integer32,
        sonusLoadTestNumUnexpectedRelRcvdRcvr     Integer32,
        sonusLoadTestNumIamSent         Integer32,
        sonusLoadTestNumAcmRcvd         Integer32,
        sonusLoadTestNumAnmRcvd         Integer32,
        sonusLoadTestNumRelRcvd         Integer32,
        sonusLoadTestNumUcicRcvd        Integer32,
        sonusLoadTestNumRelSent         Integer32,
        sonusLoadTestNumRlcRcvd         Integer32,
        sonusLoadTestNumTotalTestUpdate Integer32,
        sonusLoadTestNumDsTestPassed    Integer32,
        sonusLoadTestNumUsTestPassed    Integer32,
        sonusLoadTestNumCallAboveBenchMark  Integer32,
        sonusLoadTestTotalCallLatency   Integer32,
        sonusLoadTestAverageCallLatency Integer32,
        sonusLoadTestMinCallLatency     Integer32,
        sonusLoadTestMaxCallLatency     Integer32,
        sonusLoadTestLastCallLatency    Integer32,
        sonusLoadTestMaxCallLatencyAboveBenchMark         Integer32,
        sonusLoadTestCallLatencyBenchMark Integer32,
        sonusLoadTestElapsedTime        Integer32,
        sonusLoadTestBusyHourCall       Integer32,
        sonusLoadTestNumRscRcvd         Integer32,
        sonusLoadTestNumRcvrIamTimeOut  Integer32
    }

sonusLoadTestStatusIndex OBJECT-TYPE
    SYNTAX          Integer32
    MAX-ACCESS      read-only
    STATUS          current
    DESCRIPTION     
            "The index of the load test instance."
    ::= { sonusLoadTestStatusEntry 1 }

sonusLoadTestNumCallInitiated OBJECT-TYPE
    SYNTAX          Integer32
    MAX-ACCESS      read-only
    STATUS          current
    DESCRIPTION     
            "Number of calls initiated."
    ::= { sonusLoadTestStatusEntry 2 }

sonusLoadTestNumCallFailed OBJECT-TYPE
    SYNTAX          Integer32
    MAX-ACCESS      read-only
    STATUS          current
    DESCRIPTION     
            "Number of calls failed."
    ::= { sonusLoadTestStatusEntry 3 }

sonusLoadTestNumTrmAlloFailed OBJECT-TYPE
    SYNTAX          Integer32
    MAX-ACCESS      read-only
    STATUS          current
    DESCRIPTION     
            "Number of TRM allocation failed."
    ::= { sonusLoadTestStatusEntry 4 }

sonusLoadTestNumTrmAlloTimedOut OBJECT-TYPE
    SYNTAX          Integer32
    MAX-ACCESS      read-only
    STATUS          current
    DESCRIPTION     
            "Number of TRM allocation timed out."
    ::= { sonusLoadTestStatusEntry 5 }

sonusLoadTestNumCallEstablished OBJECT-TYPE
    SYNTAX          Integer32
    MAX-ACCESS      read-only
    STATUS          current
    DESCRIPTION     
            "Number of calls established."
    ::= { sonusLoadTestStatusEntry 6 }

sonusLoadTestNumCallReleased OBJECT-TYPE
    SYNTAX          Integer32
    MAX-ACCESS      read-only
    STATUS          current
    DESCRIPTION     
            "Number of calls released."
    ::= { sonusLoadTestStatusEntry 7 }

sonusLoadTestNumUnexpected OBJECT-TYPE
    SYNTAX          Integer32
    MAX-ACCESS      read-only
    STATUS          current
    DESCRIPTION     
            "Number of unexpected messages received."
    ::= { sonusLoadTestStatusEntry 8 }

sonusLoadTestNumAcmTimeOutRcvd OBJECT-TYPE
    SYNTAX          Integer32
    MAX-ACCESS      read-only
    STATUS          current
    DESCRIPTION     
            "Number of ACM timeout received."
    ::= { sonusLoadTestStatusEntry 9 }

sonusLoadTestNumLocalAcmTimeOut OBJECT-TYPE
    SYNTAX          Integer32
    MAX-ACCESS      read-only
    STATUS          current
    DESCRIPTION     
            "Number of local ACM timed out."
    ::= { sonusLoadTestStatusEntry 10 }

sonusLoadTestNumAnmTimeOutRcvd OBJECT-TYPE
    SYNTAX          Integer32
    MAX-ACCESS      read-only
    STATUS          current
    DESCRIPTION     
            "Number of ANM timeout received."
    ::= { sonusLoadTestStatusEntry 11 }

sonusLoadTestNumLocalAnmTimeOut OBJECT-TYPE
    SYNTAX          Integer32
    MAX-ACCESS      read-only
    STATUS          current
    DESCRIPTION     
            "Number of local ANM timed out."
    ::= { sonusLoadTestStatusEntry 12 }

sonusLoadTestNumLocalRelTimeOut OBJECT-TYPE
    SYNTAX          Integer32
    MAX-ACCESS      read-only
    STATUS          current
    DESCRIPTION     
            "Number of local release timed out."
    ::= { sonusLoadTestStatusEntry 13 }

sonusLoadTestNumUnexpectedRelRcvdGen OBJECT-TYPE
    SYNTAX          Integer32
    MAX-ACCESS      read-only
    STATUS          current
    DESCRIPTION     
            "Number of unexpected REL received by Call Generator."
    ::= { sonusLoadTestStatusEntry 14 }

sonusLoadTestNumUnexpectedRelRcvdRcvr OBJECT-TYPE
    SYNTAX          Integer32
    MAX-ACCESS      read-only
    STATUS          current
    DESCRIPTION     
            "Number of unexpected REL received by Call Receiver."
    ::= { sonusLoadTestStatusEntry 15 }

sonusLoadTestNumIamSent OBJECT-TYPE
    SYNTAX          Integer32
    MAX-ACCESS      read-only
    STATUS          current
    DESCRIPTION     
            "Number of IAM sent."
    ::= { sonusLoadTestStatusEntry 16 }

sonusLoadTestNumAcmRcvd OBJECT-TYPE
    SYNTAX          Integer32
    MAX-ACCESS      read-only
    STATUS          current
    DESCRIPTION     
            "Number of ACM received."
    ::= { sonusLoadTestStatusEntry 17 }

sonusLoadTestNumAnmRcvd OBJECT-TYPE
    SYNTAX          Integer32
    MAX-ACCESS      read-only
    STATUS          current
    DESCRIPTION     
            "Number of ANM received."
    ::= { sonusLoadTestStatusEntry 18 }

sonusLoadTestNumRelRcvd OBJECT-TYPE
    SYNTAX          Integer32
    MAX-ACCESS      read-only
    STATUS          current
    DESCRIPTION     
            "Number of REL received."
    ::= { sonusLoadTestStatusEntry 19 }

sonusLoadTestNumUcicRcvd OBJECT-TYPE
    SYNTAX          Integer32
    MAX-ACCESS      read-only
    STATUS          current
    DESCRIPTION     
            "Number of UCIC received."
    ::= { sonusLoadTestStatusEntry 20 }

sonusLoadTestNumRelSent OBJECT-TYPE
    SYNTAX          Integer32
    MAX-ACCESS      read-only
    STATUS          current
    DESCRIPTION     
            "Number of REL sent."
    ::= { sonusLoadTestStatusEntry 21 }

sonusLoadTestNumRlcRcvd OBJECT-TYPE
    SYNTAX          Integer32
    MAX-ACCESS      read-only
    STATUS          current
    DESCRIPTION     
            "Number of RLC received."
    ::= { sonusLoadTestStatusEntry 22 }

sonusLoadTestNumTotalTestUpdate OBJECT-TYPE
    SYNTAX          Integer32
    MAX-ACCESS      read-only
    STATUS          current
    DESCRIPTION     
            "Number of data verification updates received."
    ::= { sonusLoadTestStatusEntry 23 }

sonusLoadTestNumDsTestPassed OBJECT-TYPE
    SYNTAX          Integer32
    MAX-ACCESS      read-only
    STATUS          current
    DESCRIPTION     
            "Number of Downstream test passed."
    ::= { sonusLoadTestStatusEntry 24 }

sonusLoadTestNumUsTestPassed OBJECT-TYPE
    SYNTAX          Integer32
    MAX-ACCESS      read-only
    STATUS          current
    DESCRIPTION     
            "Number of Upstream test passed."
    ::= { sonusLoadTestStatusEntry 25 }

sonusLoadTestNumCallAboveBenchMark OBJECT-TYPE
    SYNTAX          Integer32
    MAX-ACCESS      read-only
    STATUS          current
    DESCRIPTION     
            "Number of calls above benchmark."
    ::= { sonusLoadTestStatusEntry 26 }

sonusLoadTestTotalCallLatency OBJECT-TYPE
    SYNTAX          Integer32
    MAX-ACCESS      read-only
    STATUS          current
    DESCRIPTION     
            "Total Number of call latency (in milliseconds)."
    ::= { sonusLoadTestStatusEntry 27 }

sonusLoadTestAverageCallLatency OBJECT-TYPE
    SYNTAX          Integer32
    MAX-ACCESS      read-only
    STATUS          current
    DESCRIPTION     
            "Average call latency (in milliseconds)."
    ::= { sonusLoadTestStatusEntry 28 }

sonusLoadTestMinCallLatency OBJECT-TYPE
    SYNTAX          Integer32
    MAX-ACCESS      read-only
    STATUS          current
    DESCRIPTION     
            "Minimum call latency (in milliseconds)."
    ::= { sonusLoadTestStatusEntry 29 }

sonusLoadTestMaxCallLatency OBJECT-TYPE
    SYNTAX          Integer32
    MAX-ACCESS      read-only
    STATUS          current
    DESCRIPTION     
            "Maximum call latency (in milliseconds)."
    ::= { sonusLoadTestStatusEntry 30 }

sonusLoadTestLastCallLatency OBJECT-TYPE
    SYNTAX          Integer32
    MAX-ACCESS      read-only
    STATUS          current
    DESCRIPTION     
            "Last call latency (in milliseconds)."
    ::= { sonusLoadTestStatusEntry 31 }

sonusLoadTestMaxCallLatencyAboveBenchMark OBJECT-TYPE
    SYNTAX          Integer32
    MAX-ACCESS      read-only
    STATUS          current
    DESCRIPTION     
            "Maximum call latency above benchmark (in milliseconds)."
    ::= { sonusLoadTestStatusEntry 32 }

sonusLoadTestCallLatencyBenchMark OBJECT-TYPE
    SYNTAX          Integer32
    MAX-ACCESS      read-only
    STATUS          current
    DESCRIPTION     
            "Call latency benchmark (in milliseconds)."
    ::= { sonusLoadTestStatusEntry 33 }

sonusLoadTestElapsedTime OBJECT-TYPE
    SYNTAX          Integer32
    MAX-ACCESS      read-only
    STATUS          current
    DESCRIPTION     
            "Loadtest elapsed time (in seconds)."
    ::= { sonusLoadTestStatusEntry 34 }

sonusLoadTestBusyHourCall OBJECT-TYPE
    SYNTAX          Integer32
    MAX-ACCESS      read-only
    STATUS          current
    DESCRIPTION     
            "Busy hour calls."
    ::= { sonusLoadTestStatusEntry 35 }

sonusLoadTestNumRscRcvd OBJECT-TYPE
    SYNTAX          Integer32
    MAX-ACCESS      read-only
    STATUS          current
    DESCRIPTION     
            "Number of RSC received."
    ::= { sonusLoadTestStatusEntry 36 }

sonusLoadTestNumRcvrIamTimeOut OBJECT-TYPE
    SYNTAX          Integer32
    MAX-ACCESS      read-only
    STATUS          current
    DESCRIPTION     
            "Number of IAM timeouts for 2 stage calls"
    ::= { sonusLoadTestStatusEntry 37 }

sonusLoadTestIamTable OBJECT-TYPE
    SYNTAX          SEQUENCE OF SonusLoadTestIamEntry
    MAX-ACCESS      not-accessible
    STATUS          current
    DESCRIPTION     
            "This table specifies the IAM information for Load Test Table"
    ::= { sonusLoadTestMIBObjects 4 }

sonusLoadTestIamEntry OBJECT-TYPE
    SYNTAX          SonusLoadTestIamEntry
    MAX-ACCESS      not-accessible
    STATUS          current
    DESCRIPTION     
            ""
    INDEX           { sonusLoadTestIamTestIndex, 
                      sonusLoadTestIamEntryIndex }
    ::= { sonusLoadTestIamTable 1 }

SonusLoadTestIamEntry ::=
    SEQUENCE {
        sonusLoadTestIamTestIndex       Integer32,
        sonusLoadTestIamEntryIndex      Integer32,
        sonusLoadTestIamCmdParams       OCTET STRING,
        sonusLoadTestIamCmdVerify       OCTET STRING,
        sonusLoadTestIamCmdMask         OCTET STRING,
        sonusLoadTestIamRowStatus       RowStatus
    }

sonusLoadTestIamTestIndex OBJECT-TYPE
    SYNTAX          Integer32
    MAX-ACCESS      read-only
    STATUS          current
    DESCRIPTION     
            "The index of Load Test entry of this IAM information belongs to."
    ::= { sonusLoadTestIamEntry 1 }

sonusLoadTestIamEntryIndex OBJECT-TYPE
    SYNTAX          Integer32
    MAX-ACCESS      read-only
    STATUS          current
    DESCRIPTION     
            "The index of this Load Test IAM information entry."
    ::= { sonusLoadTestIamEntry 2 }

sonusLoadTestIamCmdParams OBJECT-TYPE
    SYNTAX          OCTET STRING (SIZE(0..400))
    MAX-ACCESS      read-write
    STATUS          current
    DESCRIPTION     
            "Octet string that represents IAM command message parameters."
    ::= { sonusLoadTestIamEntry 3 }

sonusLoadTestIamCmdVerify OBJECT-TYPE
    SYNTAX          OCTET STRING (SIZE(0..400))
    MAX-ACCESS      read-write
    STATUS          current
    DESCRIPTION     
            "Octet string that represents IAM message verification parameters."
    ::= { sonusLoadTestIamEntry 4 }

sonusLoadTestIamCmdMask OBJECT-TYPE
    SYNTAX          OCTET STRING (SIZE(0..400))
    MAX-ACCESS      read-write
    STATUS          current
    DESCRIPTION     
            "Octet string that represents IAM message verification mask."
    ::= { sonusLoadTestIamEntry 5 }

sonusLoadTestIamRowStatus OBJECT-TYPE
    SYNTAX          RowStatus
    MAX-ACCESS      read-write
    STATUS          current
    DESCRIPTION     
            ""
    ::= { sonusLoadTestIamEntry 6 }

sonusLt303Objects OBJECT IDENTIFIER
    ::= { sonusLoadTestMIBObjects 5 }

sonusLt303AdmnObjects OBJECT IDENTIFIER
    ::= { sonusLt303Objects 1 }

sonusLt303GenerationRate OBJECT-TYPE
    SYNTAX          Unsigned32 (0..999)
    MAX-ACCESS      read-write
    STATUS          current
    DESCRIPTION     
            "The target number of calls generated per second."
    DEFVAL          { 0 }
    ::= { sonusLt303AdmnObjects 1 }

sonusLt303GenerationInterval OBJECT-TYPE
    SYNTAX          Unsigned32 (10..65535)
    MAX-ACCESS      read-write
    STATUS          current
    DESCRIPTION     
            "The interval (in milliseconds) between bursts of call generation."
    DEFVAL          { 100 }
    ::= { sonusLt303AdmnObjects 2 }

sonusLt303GenerationLimit OBJECT-TYPE
    SYNTAX          Unsigned32 (0..20000)
    MAX-ACCESS      read-write
    STATUS          current
    DESCRIPTION     
            "The maximum number of simultaneous calls generated."
    DEFVAL          { 20000 }
    ::= { sonusLt303AdmnObjects 3 }

sonusLt303GenerateIfChannelsExist OBJECT-TYPE
    SYNTAX          SonusAdminState
    MAX-ACCESS      read-write
    STATUS          current
    DESCRIPTION     
            "If enabled, a call is generated only if free channels exist
             at the originating and terminating Interface Groups."
    DEFVAL          { enabled }
    ::= { sonusLt303AdmnObjects 4 }

sonusLt303ConnectedDurationMin OBJECT-TYPE
    SYNTAX          Unsigned32 (1..3600)
    MAX-ACCESS      read-write
    STATUS          current
    DESCRIPTION     
            "The minimum time (in seconds) a generated call stays connected.
             For each call, a random value is chosen between Min and Max."
    DEFVAL          { 30 }
    ::= { sonusLt303AdmnObjects 5 }

sonusLt303ConnectedDurationMax OBJECT-TYPE
    SYNTAX          Unsigned32 (1..3600)
    MAX-ACCESS      read-write
    STATUS          current
    DESCRIPTION     
            "The maximum time (in seconds) a generated call stays connected.
             For each call, a random value is chosen between Min and Max."
    DEFVAL          { 30 }
    ::= { sonusLt303AdmnObjects 6 }

sonusLt303CircuitServiceProfile OBJECT-TYPE
    SYNTAX          SonusNameReference
    MAX-ACCESS      read-write
    STATUS          current
    DESCRIPTION     
            "CAS and other channels with this profile name will receive media path testing."
    ::= { sonusLt303AdmnObjects 7 }

sonusLt303MediaPathTest OBJECT-TYPE
    SYNTAX          INTEGER { none(0), downThenUp(1), upThenDown(2), 
                        downOnly(3), upOnly(4) }
    MAX-ACCESS      read-write
    STATUS          current
    DESCRIPTION     
            "The kind of media path testing applied to load test calls,
             a choice of upstream and/or downstream tones."
    DEFVAL          { none }
    ::= { sonusLt303AdmnObjects 8 }

sonusLt303DisconnectSequence OBJECT-TYPE
    SYNTAX          INTEGER { random(0), originator(1), terminator(2), 
                        together(3) }
    MAX-ACCESS      read-write
    STATUS          current
    DESCRIPTION     
            "Which party goes on hook to end a call normally."
    DEFVAL          { random }
    ::= { sonusLt303AdmnObjects 9 }

sonusLt303SetupTimer OBJECT-TYPE
    SYNTAX          Unsigned32 (0..300)
    MAX-ACCESS      read-write
    STATUS          current
    DESCRIPTION     
            "The time allowed (in seconds) to connect a load test call.
             If this timer expires, the call will be aborted."
    DEFVAL          { 120 }
    ::= { sonusLt303AdmnObjects 10 }

sonusLt303ReleaseTimer OBJECT-TYPE
    SYNTAX          Unsigned32 (0..300)
    MAX-ACCESS      read-write
    STATUS          current
    DESCRIPTION     
            "The time allowed (in seconds) to release a load test call.
             If this timer expires, the call will be aborted."
    DEFVAL          { 120 }
    ::= { sonusLt303AdmnObjects 11 }

sonusLt303StopOnFailureSequence OBJECT-TYPE
    SYNTAX          INTEGER { nothing(0), rateZero(1), stopCalls(2) }
    MAX-ACCESS      read-write
    STATUS          current
    DESCRIPTION     
            "What to do when call failure detected."
    DEFVAL          { nothing }
    ::= { sonusLt303AdmnObjects 12 }

END -- end of module SONUS-LOAD-TEST-MIB.
