--
-- This SMIv2 module has been generated by smidump 0.2-cvs. Do not edit.
--

SONUS-GEN2-REDUNDANCY-SERVICES-MIB DEFINITIONS ::= BEGIN

IMPORTS
    Counter32, Counter64, Gauge32, Integer32, IpAddress, MODULE-IDENTITY, 
    OBJECT-TYPE, Unsigned32
        FROM SNMPv2-SMI
    DateAndTime, RowStatus, TEXTUAL-CONVENTION, TruthValue
        FROM SNMPv2-TC
    sonusCommonSoftwarePlatformServicesMIBs
        FROM SONUS-SMI;

sonusGen2RedundancyMIB MODULE-IDENTITY
    LAST-UPDATED    "201002030000Z"
    ORGANIZATION    
            "Sonus Networks, Inc."
    CONTACT-INFO    
            "Customer Support        
             Sonus Networks, Inc.    
             7 Technology Park Drive 
             Westford, MA 01886      
             USA                     
                                     
             Tel: 978-614-8100       
             Fax: 978-614-8609"
    DESCRIPTION     
            "
             The MIB Module for Redundancy Group and Clients Configuration.
             "
    REVISION        "201002030000Z"
    DESCRIPTION     
            "Auto generated MIB."
    ::= { sonusCommonSoftwarePlatformServicesMIBs 8 }


Token ::= TEXTUAL-CONVENTION
    DISPLAY-HINT    "1t"
    STATUS          current
    DESCRIPTION     
            "xs:token"
    SYNTAX          OCTET STRING

String ::= TEXTUAL-CONVENTION
    DISPLAY-HINT    "1t"
    STATUS          current
    DESCRIPTION     
            "xs:string"
    SYNTAX          OCTET STRING

SonusRedundGroupAdmnStateType ::= TEXTUAL-CONVENTION
    STATUS          current
    DESCRIPTION     
            "
             "
    SYNTAX          INTEGER { disabled(1), enabled(2) }

SonusRedundGroupLastSwitchoverReasonType ::= TEXTUAL-CONVENTION
    STATUS          current
    DESCRIPTION     
            "
             "
    SYNTAX          INTEGER { none(1), adminSwitchover(2), 
                        autoReversion(3), reset(4), removal(5), 
                        softwareFailure(6), hardwareFailure(7), 
                        healthCheckTimeout(8), other(9), 
                        softwareUpgrade(10), excessiveLinkFailure(11), 
                        reserved2(12), unknown(13) }

SonusRedundClientTestResultType ::= TEXTUAL-CONVENTION
    STATUS          current
    DESCRIPTION     
            "
             "
    SYNTAX          INTEGER { passed(1), failed(2), indeterminate(3), 
                        notRun(4), aborted(5), notSupported(6), 
                        underTest(7), cna0XPwrFail(8), syncFail(9), 
                        prbsEnbFail(10) }

IndexType ::= TEXTUAL-CONVENTION
    STATUS          current
    DESCRIPTION     
            "
             The index for a Sonus event log.
             "
    SYNTAX          Unsigned32

SonusRedundGroupAutoDetectCntrlType ::= TEXTUAL-CONVENTION
    STATUS          current
    DESCRIPTION     
            "
             "
    SYNTAX          INTEGER { disabled(1), enabled(2) }

SonusRedundGroupHealthcheckCntrlType ::= TEXTUAL-CONVENTION
    STATUS          current
    DESCRIPTION     
            "
             "
    SYNTAX          INTEGER { disabled(1), enabled(2) }

SonusRedundClientAdmnStateType ::= TEXTUAL-CONVENTION
    STATUS          current
    DESCRIPTION     
            "
             "
    SYNTAX          INTEGER { disabled(1), enabled(2) }

SonusRedundGroupTestActionType ::= TEXTUAL-CONVENTION
    STATUS          current
    DESCRIPTION     
            "
             "
    SYNTAX          INTEGER { none(1), runCnaRedundancyPlaneTest(2) }

SonusRedundGroupSwitchoverCntrlType ::= TEXTUAL-CONVENTION
    STATUS          current
    DESCRIPTION     
            "
             "
    SYNTAX          INTEGER { none(1), normal(2), forced(3), revert(4), 
                        revertForced(5) }

SonusRedundGroupWaitToRevertTimeType ::= TEXTUAL-CONVENTION
    STATUS          current
    DESCRIPTION     
            "
             "
    SYNTAX          Integer32 (5..12)

SonusRedundGroupFallbackCntrlType ::= TEXTUAL-CONVENTION
    STATUS          current
    DESCRIPTION     
            "
             "
    SYNTAX          INTEGER { revertive(1), nonrevertive(2) }

SonusRedundGroupRedundOpStateType ::= TEXTUAL-CONVENTION
    STATUS          current
    DESCRIPTION     
            "
             "
    SYNTAX          INTEGER { standby(1), activeSynced(2), 
                        activeSyncing(3), activeNotSynced(4), absent(5), 
                        reset(6), failed(7), unknown(8), outOfService(9), 
                        activeSyncedHoldOff(10), standbyHoldOff(11) }

SonusRedundGroupTestCntrlType ::= TEXTUAL-CONVENTION
    STATUS          current
    DESCRIPTION     
            "
             "
    SYNTAX          INTEGER { disabled(1), enabled(2) }

SonusRedundClientStateType ::= TEXTUAL-CONVENTION
    STATUS          current
    DESCRIPTION     
            "
             "
    SYNTAX          INTEGER { standby(1), activeSynced(2), 
                        activeSyncing(3), activeNotSynced(4), absent(5), 
                        reset(6), failed(7), unknown(8), outOfService(9), 
                        activeSyncedHoldOff(10), standbyHoldOff(11) }

sonusRedundancyServices OBJECT IDENTIFIER
    ::= { sonusGen2RedundancyMIB 1 }

sonusRedundancyServicesGroupAdminTable OBJECT-TYPE
    SYNTAX          SEQUENCE OF SonusRedundancyServicesGroupAdminEntry
    MAX-ACCESS      not-accessible
    STATUS          current
    DESCRIPTION     
            "
             This table specifies the redundancy group list.
             "
    ::= { sonusRedundancyServices 1 }

sonusRedundancyServicesGroupAdminEntry OBJECT-TYPE
    SYNTAX          SonusRedundancyServicesGroupAdminEntry
    MAX-ACCESS      not-accessible
    STATUS          current
    DESCRIPTION     
            ""
    INDEX           { sonusRedundancyServicesGroupAdminName }
    ::= { sonusRedundancyServicesGroupAdminTable 1 }

SonusRedundancyServicesGroupAdminEntry ::=
    SEQUENCE {
        sonusRedundancyServicesGroupAdminName     String,
        sonusRedundancyServicesGroupAdminIndex      IndexType,
        sonusRedundancyServicesGroupAdminState      SonusRedundGroupAdmnStateType,
        sonusRedundancyServicesGroupAdminShelf      Unsigned32,
        sonusRedundancyServicesGroupAdminSlot     Unsigned32,
        sonusRedundancyServicesGroupAdminSwitchoverControl                  SonusRedundGroupSwitchoverCntrlType,
        sonusRedundancyServicesGroupAdminSwitchoverClientSlot                     Unsigned32,
        sonusRedundancyServicesGroupAdminFallbackControl                SonusRedundGroupFallbackCntrlType,
        sonusRedundancyServicesGroupAdminWaitToRevertTime                 SonusRedundGroupWaitToRevertTimeType,
        sonusRedundancyServicesGroupAdminAutoDetectControl                  SonusRedundGroupAutoDetectCntrlType,
        sonusRedundancyServicesGroupAdminHardwareType             INTEGER,
        sonusRedundancyServicesGroupAdminHealthcheckControl                   SonusRedundGroupHealthcheckCntrlType,
        sonusRedundancyServicesGroupAdminServerFunction               INTEGER,
        sonusRedundancyServicesGroupAdminCnaTestControl               SonusRedundGroupTestCntrlType,
        sonusRedundancyServicesGroupAdminTestAction           SonusRedundGroupTestActionType,
        sonusRedundancyServicesGroupAdminRowstatus          RowStatus
    }

sonusRedundancyServicesGroupAdminName OBJECT-TYPE
    SYNTAX          String (SIZE(0..23))
    MAX-ACCESS      not-accessible
    STATUS          current
    DESCRIPTION     
            "
             The name of this redundancy group instance.
             "
    ::= { sonusRedundancyServicesGroupAdminEntry 1 }

sonusRedundancyServicesGroupAdminIndex OBJECT-TYPE
    SYNTAX          IndexType
    MAX-ACCESS      read-only
    STATUS          current
    DESCRIPTION     
            "
             Identifies the target redundancy group entry.
             "
    ::= { sonusRedundancyServicesGroupAdminEntry 2 }

sonusRedundancyServicesGroupAdminState OBJECT-TYPE
    SYNTAX          SonusRedundGroupAdmnStateType
    MAX-ACCESS      read-create
    STATUS          current
    DESCRIPTION     
            "
             The administrative state of this redundancy group entry.
             "
    DEFVAL          { disabled }
    ::= { sonusRedundancyServicesGroupAdminEntry 3 }

sonusRedundancyServicesGroupAdminShelf OBJECT-TYPE
    SYNTAX          Unsigned32 (1..6)
    MAX-ACCESS      read-create
    STATUS          current
    DESCRIPTION     
            "
             The shelf index of this redundancy group entry.
             "
    ::= { sonusRedundancyServicesGroupAdminEntry 4 }

sonusRedundancyServicesGroupAdminSlot OBJECT-TYPE
    SYNTAX          Unsigned32 (1..18)
    MAX-ACCESS      read-create
    STATUS          current
    DESCRIPTION     
            "
             The redundant slot index of this redundancy group entry.
             "
    ::= { sonusRedundancyServicesGroupAdminEntry 5 }

sonusRedundancyServicesGroupAdminSwitchoverControl OBJECT-TYPE
    SYNTAX          SonusRedundGroupSwitchoverCntrlType
    MAX-ACCESS      read-create
    STATUS          current
    DESCRIPTION     
            "
             The client switching control of this redundancy group entry.  The revert
             options are used when the redundant server module is currently active.  The
             forced options do not require synchronization and may result in a loss of
             service.
             "
    DEFVAL          { none }
    ::= { sonusRedundancyServicesGroupAdminEntry 6 }

sonusRedundancyServicesGroupAdminSwitchoverClientSlot OBJECT-TYPE
    SYNTAX          Unsigned32 (1..18)
    MAX-ACCESS      read-create
    STATUS          current
    DESCRIPTION     
            "
             The switchover client slot index of this redundancy group.
             "
    ::= { sonusRedundancyServicesGroupAdminEntry 7 }

sonusRedundancyServicesGroupAdminFallbackControl OBJECT-TYPE
    SYNTAX          SonusRedundGroupFallbackCntrlType
    MAX-ACCESS      read-create
    STATUS          current
    DESCRIPTION     
            "
             The fallback control of this redundancy group entry.
             "
    DEFVAL          { nonrevertive }
    ::= { sonusRedundancyServicesGroupAdminEntry 8 }

sonusRedundancyServicesGroupAdminWaitToRevertTime OBJECT-TYPE
    SYNTAX          SonusRedundGroupWaitToRevertTimeType
    MAX-ACCESS      read-create
    STATUS          current
    DESCRIPTION     
            "
             The Wait to Revert Time (in minutes) of this redundancy group entry.
             "
    DEFVAL          { 5 }
    ::= { sonusRedundancyServicesGroupAdminEntry 9 }

sonusRedundancyServicesGroupAdminAutoDetectControl OBJECT-TYPE
    SYNTAX          SonusRedundGroupAutoDetectCntrlType
    MAX-ACCESS      read-create
    STATUS          current
    DESCRIPTION     
            "
             The auto detected control of this redundancy group entry.
             "
    DEFVAL          { disabled }
    ::= { sonusRedundancyServicesGroupAdminEntry 10 }

sonusRedundancyServicesGroupAdminHardwareType OBJECT-TYPE
    SYNTAX          INTEGER { mns20(64), pns40(69), gns15(74), 
                        mns1000(256), pns1600(257), sps1000(258) }
    MAX-ACCESS      read-create
    STATUS          current
    DESCRIPTION     
            "
             The hardware type of this redundancy group entry.
             "
    ::= { sonusRedundancyServicesGroupAdminEntry 11 }

sonusRedundancyServicesGroupAdminHealthcheckControl OBJECT-TYPE
    SYNTAX          SonusRedundGroupHealthcheckCntrlType
    MAX-ACCESS      read-create
    STATUS          current
    DESCRIPTION     
            "
             The health check control of this redundancy group entry.
               
             For the MNS redundancy group only, this also controls health checking of
             unprotected and standby server modules.
             "
    DEFVAL          { enabled }
    ::= { sonusRedundancyServicesGroupAdminEntry 12 }

sonusRedundancyServicesGroupAdminServerFunction OBJECT-TYPE
    SYNTAX          INTEGER { default(1), mgmt(3), sps(7), pos(9), 
                        hiCapacityEnet(17), hiCapacityEnetLayer3(18) }
    MAX-ACCESS      read-create
    STATUS          current
    DESCRIPTION     
            "
             The function of the server modules contained within this redundancy group.
             "
    ::= { sonusRedundancyServicesGroupAdminEntry 13 }

sonusRedundancyServicesGroupAdminCnaTestControl OBJECT-TYPE
    SYNTAX          SonusRedundGroupTestCntrlType
    MAX-ACCESS      read-create
    STATUS          current
    DESCRIPTION     
            "
             The CNA test control.
             "
    DEFVAL          { disabled }
    ::= { sonusRedundancyServicesGroupAdminEntry 14 }

sonusRedundancyServicesGroupAdminTestAction OBJECT-TYPE
    SYNTAX          SonusRedundGroupTestActionType
    MAX-ACCESS      read-create
    STATUS          current
    DESCRIPTION     
            "
             Run a runtime diagnostics test sequence.
             "
    DEFVAL          { none }
    ::= { sonusRedundancyServicesGroupAdminEntry 15 }

sonusRedundancyServicesGroupAdminRowstatus OBJECT-TYPE
    SYNTAX          RowStatus
    MAX-ACCESS      read-create
    STATUS          current
    DESCRIPTION     
            ""
    ::= { sonusRedundancyServicesGroupAdminEntry 16 }

sonusRedundancyServicesClientAdminTable OBJECT-TYPE
    SYNTAX          SEQUENCE OF SonusRedundancyServicesClientAdminEntry
    MAX-ACCESS      not-accessible
    STATUS          current
    DESCRIPTION     
            "
             This table specifies the redundancy group client list.
             "
    ::= { sonusRedundancyServices 2 }

sonusRedundancyServicesClientAdminEntry OBJECT-TYPE
    SYNTAX          SonusRedundancyServicesClientAdminEntry
    MAX-ACCESS      not-accessible
    STATUS          current
    DESCRIPTION     
            ""
    INDEX           { sonusRedundancyServicesClientAdminGroupIndex, 
                      sonusRedundancyServicesClientAdminSlot }
    ::= { sonusRedundancyServicesClientAdminTable 1 }

SonusRedundancyServicesClientAdminEntry ::=
    SEQUENCE {
        sonusRedundancyServicesClientAdminGroupIndex            IndexType,
        sonusRedundancyServicesClientAdminSlot      Unsigned32,
        sonusRedundancyServicesClientAdminState       SonusRedundClientAdmnStateType,
        sonusRedundancyServicesClientAdminRowstatus           RowStatus
    }

sonusRedundancyServicesClientAdminGroupIndex OBJECT-TYPE
    SYNTAX          IndexType
    MAX-ACCESS      not-accessible
    STATUS          current
    DESCRIPTION     
            "
             The index of the redundancy group to which this client belongs to.
             "
    ::= { sonusRedundancyServicesClientAdminEntry 1 }

sonusRedundancyServicesClientAdminSlot OBJECT-TYPE
    SYNTAX          Unsigned32 (1..18)
    MAX-ACCESS      not-accessible
    STATUS          current
    DESCRIPTION     
            "
             The slot index of this client entry.
             "
    ::= { sonusRedundancyServicesClientAdminEntry 2 }

sonusRedundancyServicesClientAdminState OBJECT-TYPE
    SYNTAX          SonusRedundClientAdmnStateType
    MAX-ACCESS      read-create
    STATUS          current
    DESCRIPTION     
            "
             The state of this client entry.
             "
    DEFVAL          { disabled }
    ::= { sonusRedundancyServicesClientAdminEntry 3 }

sonusRedundancyServicesClientAdminRowstatus OBJECT-TYPE
    SYNTAX          RowStatus
    MAX-ACCESS      read-create
    STATUS          current
    DESCRIPTION     
            ""
    ::= { sonusRedundancyServicesClientAdminEntry 4 }

sonusRedundancyServicesGroupStatusTable OBJECT-TYPE
    SYNTAX          SEQUENCE OF SonusRedundancyServicesGroupStatusEntry
    MAX-ACCESS      not-accessible
    STATUS          current
    DESCRIPTION     
            "
             This table presents status for the redundancy group.
             "
    ::= { sonusRedundancyServices 3 }

sonusRedundancyServicesGroupStatusEntry OBJECT-TYPE
    SYNTAX          SonusRedundancyServicesGroupStatusEntry
    MAX-ACCESS      not-accessible
    STATUS          current
    DESCRIPTION     
            ""
    INDEX           { sonusRedundancyServicesGroupStatusIndex }
    ::= { sonusRedundancyServicesGroupStatusTable 1 }

SonusRedundancyServicesGroupStatusEntry ::=
    SEQUENCE {
        sonusRedundancyServicesGroupStatusIndex       IndexType,
        sonusRedundancyServicesGroupStatusOperationalState                  SonusRedundGroupRedundOpStateType,
        sonusRedundancyServicesGroupStatusStandbySlot             Unsigned32,
        sonusRedundancyServicesGroupStatusRedundantSonicId                  Integer32,
        sonusRedundancyServicesGroupStatusProtectedSlot               Unsigned32,
        sonusRedundancyServicesGroupStatusNumberOfClients                 Integer32,
        sonusRedundancyServicesGroupStatusNumberOfSwitchovers                     Integer32,
        sonusRedundancyServicesGroupStatusLastSwitchoverReason                      SonusRedundGroupLastSwitchoverReasonType
    }

sonusRedundancyServicesGroupStatusIndex OBJECT-TYPE
    SYNTAX          IndexType
    MAX-ACCESS      not-accessible
    STATUS          current
    DESCRIPTION     
            "
             Identifies the index of this redundancy group index.
             "
    ::= { sonusRedundancyServicesGroupStatusEntry 1 }

sonusRedundancyServicesGroupStatusOperationalState OBJECT-TYPE
    SYNTAX          SonusRedundGroupRedundOpStateType
    MAX-ACCESS      read-only
    STATUS          current
    DESCRIPTION     
            "
             Identifies the redundant slot operation state of this redundancy group.
             "
    ::= { sonusRedundancyServicesGroupStatusEntry 2 }

sonusRedundancyServicesGroupStatusStandbySlot OBJECT-TYPE
    SYNTAX          Unsigned32 (1..18)
    MAX-ACCESS      read-only
    STATUS          current
    DESCRIPTION     
            "
             Identifies the standby slot index for this redundancy group.(Internal use only)
             "
    ::= { sonusRedundancyServicesGroupStatusEntry 3 }

sonusRedundancyServicesGroupStatusRedundantSonicId OBJECT-TYPE
    SYNTAX          Integer32
    MAX-ACCESS      read-only
    STATUS          current
    DESCRIPTION     
            "
             Identifies the redundant slot's sonic Id of this redundancy group.(Internal use only)
             "
    ::= { sonusRedundancyServicesGroupStatusEntry 4 }

sonusRedundancyServicesGroupStatusProtectedSlot OBJECT-TYPE
    SYNTAX          Unsigned32 (1..18)
    MAX-ACCESS      read-only
    STATUS          current
    DESCRIPTION     
            "
             Identifies the protected slot of this redundancy group.
             "
    ::= { sonusRedundancyServicesGroupStatusEntry 5 }

sonusRedundancyServicesGroupStatusNumberOfClients OBJECT-TYPE
    SYNTAX          Integer32
    MAX-ACCESS      read-only
    STATUS          current
    DESCRIPTION     
            "
             Indicates the number of clients of this redundancy group.
             "
    ::= { sonusRedundancyServicesGroupStatusEntry 6 }

sonusRedundancyServicesGroupStatusNumberOfSwitchovers OBJECT-TYPE
    SYNTAX          Integer32
    MAX-ACCESS      read-only
    STATUS          current
    DESCRIPTION     
            "
             Indicates the total number of switchovers on this redundancy group.
             "
    ::= { sonusRedundancyServicesGroupStatusEntry 7 }

sonusRedundancyServicesGroupStatusLastSwitchoverReason OBJECT-TYPE
    SYNTAX          SonusRedundGroupLastSwitchoverReasonType
    MAX-ACCESS      read-only
    STATUS          current
    DESCRIPTION     
            "
             Reason for the last switchover in this redundancy group.
             "
    ::= { sonusRedundancyServicesGroupStatusEntry 8 }

sonusRedundancyServicesClientStatusTable OBJECT-TYPE
    SYNTAX          SEQUENCE OF SonusRedundancyServicesClientStatusEntry
    MAX-ACCESS      not-accessible
    STATUS          current
    DESCRIPTION     
            "
             This table presents clients status for the redundancy group.
             "
    ::= { sonusRedundancyServices 4 }

sonusRedundancyServicesClientStatusEntry OBJECT-TYPE
    SYNTAX          SonusRedundancyServicesClientStatusEntry
    MAX-ACCESS      not-accessible
    STATUS          current
    DESCRIPTION     
            ""
    INDEX           { sonusRedundancyServicesClientStatusGroupIndex, 
                      sonusRedundancyServicesClientStatusSlot }
    ::= { sonusRedundancyServicesClientStatusTable 1 }

SonusRedundancyServicesClientStatusEntry ::=
    SEQUENCE {
        sonusRedundancyServicesClientStatusGroupIndex             IndexType,
        sonusRedundancyServicesClientStatusSlot       Unsigned32,
        sonusRedundancyServicesClientStatusSonicId          Integer32,
        sonusRedundancyServicesClientStatusState        SonusRedundClientStateType,
        sonusRedundancyServicesClientStatusTestResult             SonusRedundClientTestResultType,
        sonusRedundancyServicesClientStatusTestTime           DateAndTime
    }

sonusRedundancyServicesClientStatusGroupIndex OBJECT-TYPE
    SYNTAX          IndexType
    MAX-ACCESS      not-accessible
    STATUS          current
    DESCRIPTION     
            "
             Identifies the redundancy group index of this client.
             "
    ::= { sonusRedundancyServicesClientStatusEntry 1 }

sonusRedundancyServicesClientStatusSlot OBJECT-TYPE
    SYNTAX          Unsigned32 (1..18)
    MAX-ACCESS      not-accessible
    STATUS          current
    DESCRIPTION     
            "
             Identifies the slot of this client.
             "
    ::= { sonusRedundancyServicesClientStatusEntry 2 }

sonusRedundancyServicesClientStatusSonicId OBJECT-TYPE
    SYNTAX          Integer32
    MAX-ACCESS      read-only
    STATUS          current
    DESCRIPTION     
            "
             Identifies the sonic id of this client. (Internal use only)
             "
    ::= { sonusRedundancyServicesClientStatusEntry 3 }

sonusRedundancyServicesClientStatusState OBJECT-TYPE
    SYNTAX          SonusRedundClientStateType
    MAX-ACCESS      read-only
    STATUS          current
    DESCRIPTION     
            "
             Indicates the state of this client.
             "
    ::= { sonusRedundancyServicesClientStatusEntry 4 }

sonusRedundancyServicesClientStatusTestResult OBJECT-TYPE
    SYNTAX          SonusRedundClientTestResultType
    MAX-ACCESS      read-only
    STATUS          current
    DESCRIPTION     
            "
             The result of the diagnostic test.
             Passed	       - The test completed successfully.
             Failed        - The test failed.
             Indeterminate - Additional manual testing required.
             Aborted       - The test was not completed.
             UnderTest     - The client is currently being tested.
             NotRun        - The test could not be run on the client.
             NotSupported  - The card type does not support the test.
             CNA03PwrFail  - CNA03 detected power failure.
             "
    ::= { sonusRedundancyServicesClientStatusEntry 5 }

sonusRedundancyServicesClientStatusTestTime OBJECT-TYPE
    SYNTAX          DateAndTime
    MAX-ACCESS      read-only
    STATUS          current
    DESCRIPTION     
            "
             Octet string that identifies the GMT timestamp 
             of the last time the test was run.
             "
    ::= { sonusRedundancyServicesClientStatusEntry 6 }

END -- end of module SONUS-GEN2-REDUNDANCY-SERVICES-MIB.
