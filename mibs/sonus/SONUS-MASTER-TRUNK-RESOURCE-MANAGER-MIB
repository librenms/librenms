--
-- This SMIv2 module has been generated by smidump 0.2-cvs. Do not edit.
--

SONUS-MASTER-TRUNK-RESOURCE-MANAGER-MIB DEFINITIONS ::= BEGIN

IMPORTS
    Ipv6Address
        FROM IPV6-TC
    Integer32, IpAddress, MODULE-IDENTITY, NOTIFICATION-TYPE, 
    OBJECT-TYPE, Unsigned32
        FROM SNMPv2-SMI
    DisplayString, RowStatus
        FROM SNMPv2-TC
    sonusEventClass, sonusEventDescription, sonusEventLevel, 
    sonusEventTime, sonusSequenceId
        FROM SONUS-COMMON-MIB
    sonusResourcesMIBs
        FROM SONUS-SMI
    SonusAdminState, SonusName, SonusNameReference, SonusServiceState
        FROM SONUS-TC;

sonusMasterTrunkResourcesManagerMIB MODULE-IDENTITY
    LAST-UPDATED    "201108190000Z"
    ORGANIZATION    
            "Sonus Networks, Inc."
    CONTACT-INFO    
            "   Customer Support    
             Sonus Networks, Inc,
             7 Technology Park Drive
             Westford, MA 01886
             USA
             
             Tel: 978-614-8100
             Fax: 978-614-8609
             E-mail: cs.snmp@sonusnet.com"
    DESCRIPTION     
            "The MIB Module for MTRM Communication Administration."
    ::= { sonusResourcesMIBs 8 }


sonusMasterTrunkResourceManagerMIBObjects OBJECT IDENTIFIER
    ::= { sonusMasterTrunkResourcesManagerMIB 1 }

sonusMtrmConnObjects OBJECT IDENTIFIER
    ::= { sonusMasterTrunkResourceManagerMIBObjects 1 }

sonusMtrmPortTable OBJECT-TYPE
    SYNTAX          SEQUENCE OF SonusMtrmPortEntry
    MAX-ACCESS      not-accessible
    STATUS          current
    DESCRIPTION     
            "Table of MTRM communication port configurations.
             Only one server port is permitted. Can have multiple
             client ports."
    ::= { sonusMtrmConnObjects 1 }

sonusMtrmPortEntry OBJECT-TYPE
    SYNTAX          SonusMtrmPortEntry
    MAX-ACCESS      not-accessible
    STATUS          current
    DESCRIPTION     
            "MTRM client/server communication configuration."
    INDEX           { sonusMtrmPortIndex }
    ::= { sonusMtrmPortTable 1 }

SonusMtrmPortEntry ::=
    SEQUENCE {
        sonusMtrmPortIndex              Integer32,
        sonusMtrmPortIpAddress          IpAddress,
        sonusMtrmPortNum                Integer32,
        sonusMtrmPortInterface          INTEGER,
        sonusMtrmPortRole               INTEGER,
        sonusMtrmPortKeepalive          Integer32,
        sonusMtrmPortTimeout            Integer32,
        sonusMtrmPortIgnoreTimeout      INTEGER,
        sonusMtrmPortMode               SonusServiceState,
        sonusMtrmPortState              SonusAdminState,
        sonusMtrmPortRowStatus          RowStatus,
        sonusMtrmPortIp6Address         Ipv6Address,
        sonusMtrmPortIpVersion          INTEGER,
        sonusMtrmPortSecondaryIpAddress IpAddress,
        sonusMtrmSecondaryPortNum       Integer32,
        sonusMtrmPortReset              INTEGER,
        sonusMtrmPortStatReset          INTEGER,
        sonusMtrmPortForceSecondary     SonusAdminState,
        sonusMtrmPortNifGroup           SonusNameReference,
        sonusMtrmPortRetryCount         Integer32
    }

sonusMtrmPortIndex OBJECT-TYPE
    SYNTAX          Integer32
    MAX-ACCESS      read-only
    STATUS          current
    DESCRIPTION     
            "Identifies the Signal Listen Port entry."
    ::= { sonusMtrmPortEntry 1 }

sonusMtrmPortIpAddress OBJECT-TYPE
    SYNTAX          IpAddress
    MAX-ACCESS      read-write
    STATUS          current
    DESCRIPTION     
            "IP Address of the Gateway Signal Listen Port - this is a required parameter."
    DEFVAL          { '00000000'H }
    ::= { sonusMtrmPortEntry 2 }

sonusMtrmPortNum OBJECT-TYPE
    SYNTAX          Integer32 (1..65535)
    MAX-ACCESS      read-write
    STATUS          current
    DESCRIPTION     
            "Port number of the MTRM communication Port 
             (default is 4360)."
    DEFVAL          { 4360 }
    ::= { sonusMtrmPortEntry 3 }

sonusMtrmPortInterface OBJECT-TYPE
    SYNTAX          INTEGER { mgtNif(1), nif(2) }
    MAX-ACCESS      read-write
    STATUS          current
    DESCRIPTION     
            "The interface type of MTRM Communication Port.  This element select 
             which network interfaces to use for MTRM Communication. 'mgtnif' routes 
             traffic over the NIFS found on the Managment card.  'nif' routes traffic 
             over one of the NIFS on the PNS cards."
    DEFVAL          { mgtNif }
    ::= { sonusMtrmPortEntry 4 }

sonusMtrmPortRole OBJECT-TYPE
    SYNTAX          INTEGER { client(1), server(2) }
    MAX-ACCESS      read-write
    STATUS          current
    DESCRIPTION     
            "Role of the MTRM Communication Port. There can only
             be one server port per GSX."
    DEFVAL          { client }
    ::= { sonusMtrmPortEntry 5 }

sonusMtrmPortKeepalive OBJECT-TYPE
    SYNTAX          Integer32 (1..20)
    MAX-ACCESS      read-write
    STATUS          current
    DESCRIPTION     
            "This is the MTRM  HealthCheck Timer (in seconds.) A
             health check message will be sent to the peer at this
             interval."
    DEFVAL          { 2 }
    ::= { sonusMtrmPortEntry 6 }

sonusMtrmPortTimeout OBJECT-TYPE
    SYNTAX          Integer32 (1..120)
    MAX-ACCESS      read-write
    STATUS          current
    DESCRIPTION     
            "This is the MTRM timeout value(in seconds). If no
             message was received from the peer for this duration
             the peer will be marked inaccessible."
    DEFVAL          { 40 }
    ::= { sonusMtrmPortEntry 7 }

sonusMtrmPortIgnoreTimeout OBJECT-TYPE
    SYNTAX          INTEGER { disabled(1), enabled(2) }
    MAX-ACCESS      read-write
    STATUS          current
    DESCRIPTION     
            "This value when is enabled will ignore health
             timeout. "
    DEFVAL          { disabled }
    ::= { sonusMtrmPortEntry 8 }

sonusMtrmPortMode OBJECT-TYPE
    SYNTAX          SonusServiceState
    MAX-ACCESS      read-write
    STATUS          current
    DESCRIPTION     
            "Mode of the MTRM Communication Port."
    DEFVAL          { inService }
    ::= { sonusMtrmPortEntry 9 }

sonusMtrmPortState OBJECT-TYPE
    SYNTAX          SonusAdminState
    MAX-ACCESS      read-write
    STATUS          current
    DESCRIPTION     
            "State of the MTRM Communication Port."
    DEFVAL          { disabled }
    ::= { sonusMtrmPortEntry 10 }

sonusMtrmPortRowStatus OBJECT-TYPE
    SYNTAX          RowStatus
    MAX-ACCESS      read-write
    STATUS          current
    DESCRIPTION     
            "This is for SNMP use."
    ::= { sonusMtrmPortEntry 11 }

sonusMtrmPortIp6Address OBJECT-TYPE
    SYNTAX          Ipv6Address
    MAX-ACCESS      read-write
    STATUS          current
    DESCRIPTION     
            "IPv6 Address of the Gateway Signal Listen Port - this is a required parameter."
    ::= { sonusMtrmPortEntry 12 }

sonusMtrmPortIpVersion OBJECT-TYPE
    SYNTAX          INTEGER { afInet(2), afInet6(24) }
    MAX-ACCESS      read-only
    STATUS          current
    DESCRIPTION     
            " IP Address type  of the MTRM communication Port ."
    ::= { sonusMtrmPortEntry 13 }

sonusMtrmPortSecondaryIpAddress OBJECT-TYPE
    SYNTAX          IpAddress
    MAX-ACCESS      read-write
    STATUS          current
    DESCRIPTION     
            "Secondary IP Address of the MTRM Listen Port "
    DEFVAL          { '00000000'H }
    ::= { sonusMtrmPortEntry 14 }

sonusMtrmSecondaryPortNum OBJECT-TYPE
    SYNTAX          Integer32 (1..65535)
    MAX-ACCESS      read-write
    STATUS          current
    DESCRIPTION     
            "Secondary Port number of the MTRM communication Port 
             (default is 4360)."
    DEFVAL          { 4360 }
    ::= { sonusMtrmPortEntry 15 }

sonusMtrmPortReset OBJECT-TYPE
    SYNTAX          INTEGER { unknown(1), reset(2) }
    MAX-ACCESS      read-write
    STATUS          current
    DESCRIPTION     
            "Reset the connection"
    ::= { sonusMtrmPortEntry 16 }

sonusMtrmPortStatReset OBJECT-TYPE
    SYNTAX          INTEGER { unknown(1), reset(2) }
    MAX-ACCESS      read-write
    STATUS          current
    DESCRIPTION     
            "Reset the statistics of the connection"
    ::= { sonusMtrmPortEntry 17 }

sonusMtrmPortForceSecondary OBJECT-TYPE
    SYNTAX          SonusAdminState
    MAX-ACCESS      read-write
    STATUS          current
    DESCRIPTION     
            "This value when is enabled will force to use 
             secondary connection. "
    DEFVAL          { disabled }
    ::= { sonusMtrmPortEntry 18 }

sonusMtrmPortNifGroup OBJECT-TYPE
    SYNTAX          SonusNameReference
    MAX-ACCESS      read-write
    STATUS          current
    DESCRIPTION     
            "The NIF Group which this SIP MTRM port belongs to."
    ::= { sonusMtrmPortEntry 20 }

sonusMtrmPortRetryCount OBJECT-TYPE
    SYNTAX          Integer32 (3..100)
    MAX-ACCESS      read-write
    STATUS          current
    DESCRIPTION     
            "Number of MTRM message retries before link reset  
             (default is 10)."
    DEFVAL          { 10 }
    ::= { sonusMtrmPortEntry 21 }

sonusMtrmMtrgObjects OBJECT IDENTIFIER
    ::= { sonusMasterTrunkResourceManagerMIBObjects 2 }

sonusMtrmMtrgTable OBJECT-TYPE
    SYNTAX          SEQUENCE OF SonusMtrmMtrgEntry
    MAX-ACCESS      not-accessible
    STATUS          current
    DESCRIPTION     
            "Table of MTRM communication MTRG Server configurations.
             Only one server port is permitted. Can have multiple
             client ports."
    ::= { sonusMtrmMtrgObjects 1 }

sonusMtrmMtrgEntry OBJECT-TYPE
    SYNTAX          SonusMtrmMtrgEntry
    MAX-ACCESS      not-accessible
    STATUS          current
    DESCRIPTION     
            "MTRM server communication configuration."
    INDEX           { sonusMtrmMtrgIndex }
    ::= { sonusMtrmMtrgTable 1 }

SonusMtrmMtrgEntry ::=
    SEQUENCE {
        sonusMtrmMtrgIndex              Integer32,
        sonusMtrmMtrgName               SonusName,
        sonusMtrmMtrgType               INTEGER,
        sonusMtrmMtrgGlobalMaxCalls     Integer32,
        sonusMtrmMtrgGlobalMaxBW        Integer32,
        sonusMtrmMtrgHuntAlgorithm      INTEGER,
        sonusMtrmMtrgMtrmIndex          Integer32,
        sonusMtrmMtrgMode               SonusServiceState,
        sonusMtrmMtrgState              SonusAdminState,
        sonusMtrmMtrgRowStatus          RowStatus,
        sonusMtrmMtrgParentMtrgName     SonusNameReference,
        sonusMtrmMtrgCallsPerReq        Integer32,
        sonusMtrmMtrgBwPerReq           Integer32,
        sonusMtrmMtrgRequestMaxCalls    Integer32,
        sonusMtrmMtrgRequestMaxBW       Integer32
    }

sonusMtrmMtrgIndex OBJECT-TYPE
    SYNTAX          Integer32
    MAX-ACCESS      read-only
    STATUS          current
    DESCRIPTION     
            "Identifies the MTRG entry."
    ::= { sonusMtrmMtrgEntry 1 }

sonusMtrmMtrgName OBJECT-TYPE
    SYNTAX          SonusName
    MAX-ACCESS      read-write
    STATUS          current
    DESCRIPTION     
            "Name of the MTRG object that is to be associated with
             the trunk groups. This name will be used as the key to
             collect the trunk groups together."
    ::= { sonusMtrmMtrgEntry 2 }

sonusMtrmMtrgType OBJECT-TYPE
    SYNTAX          INTEGER { ip(1), pstn(2) }
    MAX-ACCESS      read-write
    STATUS          current
    DESCRIPTION     
            "The rest of the configuration parameters depend on
             this. Some parameters are not applicable to IP and
             others may not be applicable to PSTN."
    DEFVAL          { ip }
    ::= { sonusMtrmMtrgEntry 3 }

sonusMtrmMtrgGlobalMaxCalls OBJECT-TYPE
    SYNTAX          Integer32 (-1..2147483647)
    MAX-ACCESS      read-write
    STATUS          current
    DESCRIPTION     
            "The number of calls that can be made on this Master
             Trunk Group. This value is only of concern if this
             object refers to an MTRM server. In the client
             incarnamtion the local maximas prevail. This value is
             currently only used when the MTRG is of type IP.
             A negative value is unlimited."
    DEFVAL          { 1000 }
    ::= { sonusMtrmMtrgEntry 4 }

sonusMtrmMtrgGlobalMaxBW OBJECT-TYPE
    SYNTAX          Integer32 (-1..2147483647)
    MAX-ACCESS      read-write
    STATUS          current
    DESCRIPTION     
            "The amount of bandwidth that can be allocated in
             total. This value is only of concern to an MTRM
             Server. This value is currently only used when the
             MTRG is of type IP."
    DEFVAL          { 64000 }
    ::= { sonusMtrmMtrgEntry 5 }

sonusMtrmMtrgHuntAlgorithm OBJECT-TYPE
    SYNTAX          INTEGER { circuithi2lo(1), circuitlo2hi(2), 
                        mostnleastidle(3), circularbottom2top(4), 
                        circulartop2bottom(5) }
    MAX-ACCESS      read-write
    STATUS          current
    DESCRIPTION     
            "This value determines the hunt algorithm used for
             this MTRG. This value is only of significance when set
             against trunk groups populated on the MTRM server."
    DEFVAL          { mostnleastidle }
    ::= { sonusMtrmMtrgEntry 10 }

sonusMtrmMtrgMtrmIndex OBJECT-TYPE
    SYNTAX          Integer32 (0..128)
    MAX-ACCESS      read-write
    STATUS          current
    DESCRIPTION     
            "This index refers to the MTRM object this MTRG
             belongs to. The MTRM should be configured and enabled
             for this object to be set. A value of 0 means no index."
    ::= { sonusMtrmMtrgEntry 11 }

sonusMtrmMtrgMode OBJECT-TYPE
    SYNTAX          SonusServiceState
    MAX-ACCESS      read-write
    STATUS          current
    DESCRIPTION     
            "Mode of the MTRM Communication Port."
    DEFVAL          { inService }
    ::= { sonusMtrmMtrgEntry 12 }

sonusMtrmMtrgState OBJECT-TYPE
    SYNTAX          SonusAdminState
    MAX-ACCESS      read-write
    STATUS          current
    DESCRIPTION     
            "State of the MTRM Communication Port."
    DEFVAL          { disabled }
    ::= { sonusMtrmMtrgEntry 13 }

sonusMtrmMtrgRowStatus OBJECT-TYPE
    SYNTAX          RowStatus
    MAX-ACCESS      read-write
    STATUS          current
    DESCRIPTION     
            "This is for SNMP use."
    ::= { sonusMtrmMtrgEntry 14 }

sonusMtrmMtrgParentMtrgName OBJECT-TYPE
    SYNTAX          SonusNameReference
    MAX-ACCESS      read-write
    STATUS          current
    DESCRIPTION     
            "Name of the parent master trunk group up the hiearchy.
             This name is used as the key to reference the next master
             trunk group up the chain."
    ::= { sonusMtrmMtrgEntry 15 }

sonusMtrmMtrgCallsPerReq OBJECT-TYPE
    SYNTAX          Integer32 (1..16777214)
    MAX-ACCESS      read-write
    STATUS          current
    DESCRIPTION     
            " The number of calls that are requested each time 
             from the parent master trunk group. "
    DEFVAL          { 10000 }
    ::= { sonusMtrmMtrgEntry 16 }

sonusMtrmMtrgBwPerReq OBJECT-TYPE
    SYNTAX          Integer32 (2480..248000000)
    MAX-ACCESS      read-write
    STATUS          current
    DESCRIPTION     
            " The bandwidth (kbit/s) that are requested each time 
             from the parent master trunk group. "
    DEFVAL          { 1240000 }
    ::= { sonusMtrmMtrgEntry 17 }

sonusMtrmMtrgRequestMaxCalls OBJECT-TYPE
    SYNTAX          Integer32 (-1..2147483647)
    MAX-ACCESS      read-write
    STATUS          current
    DESCRIPTION     
            "The maximum number of calls that can be requested from
             the parent MTRG. This is meaningful only in the
             intermediate level. "
    DEFVAL          { -1 }
    ::= { sonusMtrmMtrgEntry 18 }

sonusMtrmMtrgRequestMaxBW OBJECT-TYPE
    SYNTAX          Integer32 (-1..2147483647)
    MAX-ACCESS      read-write
    STATUS          current
    DESCRIPTION     
            "The maximum bandwidth that can be requested from
             the parent MTRG. This is meaningful only in the
             intermediate level. "
    DEFVAL          { -1 }
    ::= { sonusMtrmMtrgEntry 19 }

sonusMtrmMtrgNextIndex OBJECT-TYPE
    SYNTAX          Integer32
    MAX-ACCESS      read-only
    STATUS          current
    DESCRIPTION     
            "Retrieves the next valid index to use for the MTRG
             entry."
    ::= { sonusMtrmMtrgObjects 2 }

sonusMtrmMtrgStatTable OBJECT-TYPE
    SYNTAX          SEQUENCE OF SonusMtrmMtrgStatEntry
    MAX-ACCESS      not-accessible
    STATUS          current
    DESCRIPTION     
            "Table of the status of MTRM Connection Ports."
    ::= { sonusMtrmMtrgObjects 3 }

sonusMtrmMtrgStatEntry OBJECT-TYPE
    SYNTAX          SonusMtrmMtrgStatEntry
    MAX-ACCESS      not-accessible
    STATUS          current
    DESCRIPTION     
            "Status of Master Trunk Group."
    INDEX           { sonusMtrmMtrgStatIndex }
    ::= { sonusMtrmMtrgStatTable 1 }

SonusMtrmMtrgStatEntry ::=
    SEQUENCE {
        sonusMtrmMtrgStatIndex          Integer32,
        sonusMtrmMtrgStatGlobMaxCallAvail Integer32,
        sonusMtrmMtrgStatGlobMaxBWAvail Integer32,
        sonusMtrmMtrgStatCircConf       Integer32,
        sonusMtrmMtrgStatCircAvail      Integer32,
        sonusMtrmMtrgStatCallsAllocated Integer32,
        sonusMtrmMtrgStatBwAllocated    Integer32,
        sonusMtrmMtrgStatParentMtrgState INTEGER,
        sonusMtrmMtrgStatParentMtrgIndex Integer32,
        sonusMtrmMtrgStatRole           INTEGER,
        sonusMtrmMtrgStatMtrgName       DisplayString,
        sonusMtrmMtrgStatCallsUsage     Integer32,
        sonusMtrmMtrgStatBwUsage        Integer32
    }

sonusMtrmMtrgStatIndex OBJECT-TYPE
    SYNTAX          Integer32
    MAX-ACCESS      read-only
    STATUS          current
    DESCRIPTION     
            "Index of the MTRG entry."
    ::= { sonusMtrmMtrgStatEntry 1 }

sonusMtrmMtrgStatGlobMaxCallAvail OBJECT-TYPE
    SYNTAX          Integer32
    MAX-ACCESS      read-only
    STATUS          current
    DESCRIPTION     
            "The maximum number of calls that can still be used by
             the client MTRMs. This value is only of use if
             displayed against the server MTRM."
    ::= { sonusMtrmMtrgStatEntry 2 }

sonusMtrmMtrgStatGlobMaxBWAvail OBJECT-TYPE
    SYNTAX          Integer32
    MAX-ACCESS      read-only
    STATUS          current
    DESCRIPTION     
            "The maximum amount of B/W that can still be used by
             the client MTRMs. This value is only of use if
             displayed against the server MTRM."
    ::= { sonusMtrmMtrgStatEntry 3 }

sonusMtrmMtrgStatCircConf OBJECT-TYPE
    SYNTAX          Integer32 (0..32767)
    MAX-ACCESS      read-only
    STATUS          current
    DESCRIPTION     
            "The Circuits that have been registered against the
             MTRG on this MTRM server. This value is only useful
             when displayed on the MTRM server."
    ::= { sonusMtrmMtrgStatEntry 4 }

sonusMtrmMtrgStatCircAvail OBJECT-TYPE
    SYNTAX          Integer32 (0..32767)
    MAX-ACCESS      read-only
    STATUS          current
    DESCRIPTION     
            "The Circuits that is currently available from the
             pool of circuits that were configured against the
             MTRG on this MTRM server. This value is only useful
             when displayed on the MTRM server."
    ::= { sonusMtrmMtrgStatEntry 5 }

sonusMtrmMtrgStatCallsAllocated OBJECT-TYPE
    SYNTAX          Integer32
    MAX-ACCESS      read-only
    STATUS          current
    DESCRIPTION     
            "The number of calls allocated to all clients "
    ::= { sonusMtrmMtrgStatEntry 6 }

sonusMtrmMtrgStatBwAllocated OBJECT-TYPE
    SYNTAX          Integer32
    MAX-ACCESS      read-only
    STATUS          current
    DESCRIPTION     
            "The amount of bandwidth allocated to all clients."
    ::= { sonusMtrmMtrgStatEntry 7 }

sonusMtrmMtrgStatParentMtrgState OBJECT-TYPE
    SYNTAX          INTEGER { null(1), registration(2), awaitAudit(3), 
                        notMtrmReady(4), mtrmReady(5), trmReady(6) }
    MAX-ACCESS      read-only
    STATUS          current
    DESCRIPTION     
            " This is the state of this master runk group relative to the parent master
             trunk group.  It is only valid if sonusMtrmMtrgParentMtrgName is 
             configured. "
    ::= { sonusMtrmMtrgStatEntry 8 }

sonusMtrmMtrgStatParentMtrgIndex OBJECT-TYPE
    SYNTAX          Integer32
    MAX-ACCESS      read-only
    STATUS          current
    DESCRIPTION     
            "Index of the Parent MTRG entry."
    ::= { sonusMtrmMtrgStatEntry 9 }

sonusMtrmMtrgStatRole OBJECT-TYPE
    SYNTAX          INTEGER { client(1), server(2) }
    MAX-ACCESS      read-only
    STATUS          current
    DESCRIPTION     
            "Role of the MTRG"
    ::= { sonusMtrmMtrgStatEntry 10 }

sonusMtrmMtrgStatMtrgName OBJECT-TYPE
    SYNTAX          DisplayString (SIZE(0..23))
    MAX-ACCESS      read-only
    STATUS          current
    DESCRIPTION     
            "The name of MTRG."
    ::= { sonusMtrmMtrgStatEntry 11 }

sonusMtrmMtrgStatCallsUsage OBJECT-TYPE
    SYNTAX          Integer32
    MAX-ACCESS      read-only
    STATUS          current
    DESCRIPTION     
            "The calls usage by the MTRG."
    ::= { sonusMtrmMtrgStatEntry 12 }

sonusMtrmMtrgStatBwUsage OBJECT-TYPE
    SYNTAX          Integer32
    MAX-ACCESS      read-only
    STATUS          current
    DESCRIPTION     
            "The bandwidth usage by the MTRG. "
    ::= { sonusMtrmMtrgStatEntry 13 }

sonusMtrmTgStatTable OBJECT-TYPE
    SYNTAX          SEQUENCE OF SonusMtrmTgStatEntry
    MAX-ACCESS      not-accessible
    STATUS          current
    DESCRIPTION     
            "Table of the status of the locally registered trunk groups."
    ::= { sonusMtrmMtrgObjects 4 }

sonusMtrmTgStatEntry OBJECT-TYPE
    SYNTAX          SonusMtrmTgStatEntry
    MAX-ACCESS      not-accessible
    STATUS          current
    DESCRIPTION     
            "Status of the locally registered trunk groups."
    INDEX           { sonusMtrmTgStatMtrgIndex, sonusMtrmTgStatTgIndex }
    ::= { sonusMtrmTgStatTable 1 }

SonusMtrmTgStatEntry ::=
    SEQUENCE {
        sonusMtrmTgStatMtrgIndex        Integer32,
        sonusMtrmTgStatTgIndex          Integer32,
        sonusMtrmTgStatMtrgServerIndex  Integer32,
        sonusMtrmTgStatName             DisplayString,
        sonusMtrmTgStatState            INTEGER,
        sonusMtrmTgStatBwAllocated      Integer32,
        sonusMtrmTgStatCallsAllocated   Integer32,
        sonusMtrmTgStatRole             INTEGER,
        sonusMtrmTgStatNodeName         DisplayString
    }

sonusMtrmTgStatMtrgIndex OBJECT-TYPE
    SYNTAX          Integer32
    MAX-ACCESS      read-only
    STATUS          current
    DESCRIPTION     
            "Identifies the Master trunk group entry."
    ::= { sonusMtrmTgStatEntry 1 }

sonusMtrmTgStatTgIndex OBJECT-TYPE
    SYNTAX          Integer32
    MAX-ACCESS      read-only
    STATUS          current
    DESCRIPTION     
            "Identifies the trunk group entry."
    ::= { sonusMtrmTgStatEntry 2 }

sonusMtrmTgStatMtrgServerIndex OBJECT-TYPE
    SYNTAX          Integer32
    MAX-ACCESS      read-only
    STATUS          current
    DESCRIPTION     
            "The MTRG index assigned by the server."
    ::= { sonusMtrmTgStatEntry 3 }

sonusMtrmTgStatName OBJECT-TYPE
    SYNTAX          DisplayString (SIZE(0..23))
    MAX-ACCESS      read-only
    STATUS          current
    DESCRIPTION     
            "The registered trunk group's name."
    ::= { sonusMtrmTgStatEntry 4 }

sonusMtrmTgStatState OBJECT-TYPE
    SYNTAX          INTEGER { null(1), unregistered(2), registered(3), 
                        audit(4), active(5) }
    MAX-ACCESS      read-only
    STATUS          current
    DESCRIPTION     
            "The state of the trunk group."
    ::= { sonusMtrmTgStatEntry 5 }

sonusMtrmTgStatBwAllocated OBJECT-TYPE
    SYNTAX          Integer32
    MAX-ACCESS      read-only
    STATUS          current
    DESCRIPTION     
            "The amount of bandwidth allocated to this trunk group in 1K bits/sec."
    ::= { sonusMtrmTgStatEntry 6 }

sonusMtrmTgStatCallsAllocated OBJECT-TYPE
    SYNTAX          Integer32
    MAX-ACCESS      read-only
    STATUS          current
    DESCRIPTION     
            "The number of calls allocated to this trunk group."
    ::= { sonusMtrmTgStatEntry 7 }

sonusMtrmTgStatRole OBJECT-TYPE
    SYNTAX          INTEGER { client(1), server(2) }
    MAX-ACCESS      read-only
    STATUS          current
    DESCRIPTION     
            "The role of this entry.  There will be a client
             entry for each trunk group on the local GSX that 
             registers with a master trunk group.  There will 
             be a server entry for each trunk group on the local 
             or remote GSX that registers with a master trunk 
             group."
    ::= { sonusMtrmTgStatEntry 8 }

sonusMtrmTgStatNodeName OBJECT-TYPE
    SYNTAX          DisplayString (SIZE(0..23))
    MAX-ACCESS      read-only
    STATUS          current
    DESCRIPTION     
            "The name of the GSX where the registered trunk group resides."
    ::= { sonusMtrmTgStatEntry 9 }

sonusMtrmPeerObjects OBJECT IDENTIFIER
    ::= { sonusMasterTrunkResourceManagerMIBObjects 3 }

sonusMtrmPeerStatTable OBJECT-TYPE
    SYNTAX          SEQUENCE OF SonusMtrmPeerStatEntry
    MAX-ACCESS      not-accessible
    STATUS          current
    DESCRIPTION     
            "Table of all the MTRM Peers based on the connection"
    ::= { sonusMtrmPeerObjects 1 }

sonusMtrmPeerStatEntry OBJECT-TYPE
    SYNTAX          SonusMtrmPeerStatEntry
    MAX-ACCESS      not-accessible
    STATUS          current
    DESCRIPTION     
            "Table of Peer status entries. This table will hold
             all the client connections on the MTRM server and the
             server connection for the MTRM client"
    INDEX           { sonusMtrmPeerStatMtrmIndex, sonusMtrmPeerStatIndex }
    ::= { sonusMtrmPeerStatTable 1 }

SonusMtrmPeerStatEntry ::=
    SEQUENCE {
        sonusMtrmPeerStatMtrmIndex      Integer32,
        sonusMtrmPeerStatIndex          Integer32,
        sonusMtrmPeerStatPeerName       DisplayString,
        sonusMtrmPeerStatConnStatus     INTEGER,
        sonusMtrmPeerStatShelfId        Integer32,
        sonusMtrmPeerStatPeerRole       INTEGER,
        sonusMtrmPeerStatRTO            Integer32,
        sonusMtrmPeerStatIRRTBDepth     Integer32,
        sonusMtrmPeerStatFRRTBDepth     Integer32,
        sonusMtrmPeerStatIpAddress      IpAddress,
        sonusMtrmPeerStatMsgsSent       Integer32,
        sonusMtrmPeerStatMsgsRcvd       Integer32,
        sonusMtrmPeerStatShelfRegReqMsgsSent    Integer32,
        sonusMtrmPeerStatShelfRegReqMsgsRcvd    Integer32,
        sonusMtrmPeerStatShelfRegRespMsgsSent     Integer32,
        sonusMtrmPeerStatShelfRegRespMsgsRcvd     Integer32,
        sonusMtrmPeerStatHealthCheckReqMsgsSent       Integer32,
        sonusMtrmPeerStatHealthCheckReqMsgsRcvd       Integer32,
        sonusMtrmPeerStatHealthCheckRespMsgsSent        Integer32,
        sonusMtrmPeerStatHealthCheckRespMsgsRcvd        Integer32,
        sonusMtrmPeerStatMtrgRegReqMsgsSent   Integer32,
        sonusMtrmPeerStatMtrgRegReqMsgsRcvd   Integer32,
        sonusMtrmPeerStatMtrgRegRespMsgsSent    Integer32,
        sonusMtrmPeerStatMtrgRegRespMsgsRcvd    Integer32,
        sonusMtrmPeerStatIpAuditReqMsgsSent   Integer32,
        sonusMtrmPeerStatIpAuditReqMsgsRcvd   Integer32,
        sonusMtrmPeerStatIpAuditRespMsgsSent    Integer32,
        sonusMtrmPeerStatIpAuditRespMsgsRcvd    Integer32,
        sonusMtrmPeerStatBwAllocReqMsgsSent   Integer32,
        sonusMtrmPeerStatBwAllocReqMsgsRcvd   Integer32,
        sonusMtrmPeerStatBwAllocRespMsgsSent    Integer32,
        sonusMtrmPeerStatBwAllocRespMsgsRcvd    Integer32,
        sonusMtrmPeerStatCallAllocReqMsgsSent     Integer32,
        sonusMtrmPeerStatCallAllocReqMsgsRcvd     Integer32,
        sonusMtrmPeerStatCallAllocRespMsgsSent      Integer32,
        sonusMtrmPeerStatCallAllocRespMsgsRcvd      Integer32,
        sonusMtrmPeerStatBwFreeReqMsgsSent  Integer32,
        sonusMtrmPeerStatBwFreeReqMsgsRcvd  Integer32,
        sonusMtrmPeerStatCallFreeReqMsgsSent    Integer32,
        sonusMtrmPeerStatCallFreeReqMsgsRcvd    Integer32,
        sonusMtrmPeerStatTakeBackBwIndMsgsSent      Integer32,
        sonusMtrmPeerStatTakeBackBwIndMsgsRcvd      Integer32,
        sonusMtrmPeerStatTakeBackCallsIndMsgsSent         Integer32,
        sonusMtrmPeerStatTakeBackCallsIndMsgsRcvd         Integer32,
        sonusMtrmPeerStatMtrgDeregReqMsgsSent     Integer32,
        sonusMtrmPeerStatMtrgDeregReqMsgsRcvd     Integer32,
        sonusMtrmPeerStatMtrgUnavailableMsgsSent        Integer32,
        sonusMtrmPeerStatMtrgUnavailableMsgsRcvd        Integer32,
        sonusMtrmPeerStatIp6Address     Ipv6Address,
        sonusMtrmPeerStatIpVersion      INTEGER,
        sonusMtrmPeerStatConnType       INTEGER
    }

sonusMtrmPeerStatMtrmIndex OBJECT-TYPE
    SYNTAX          Integer32
    MAX-ACCESS      read-only
    STATUS          current
    DESCRIPTION     
            "Index of the local MTRM object to which this
             connection is being used for communication."
    ::= { sonusMtrmPeerStatEntry 1 }

sonusMtrmPeerStatIndex OBJECT-TYPE
    SYNTAX          Integer32
    MAX-ACCESS      read-only
    STATUS          current
    DESCRIPTION     
            "Index of this MTRM peer connection."
    ::= { sonusMtrmPeerStatEntry 2 }

sonusMtrmPeerStatPeerName OBJECT-TYPE
    SYNTAX          DisplayString (SIZE(0..23))
    MAX-ACCESS      read-only
    STATUS          current
    DESCRIPTION     
            "The name of the peer MTRM. If during registration a
             name is not present then the IP address of the intial
             connection will be presnted here in string form."
    ::= { sonusMtrmPeerStatEntry 3 }

sonusMtrmPeerStatConnStatus OBJECT-TYPE
    SYNTAX          INTEGER { available(1), unavailable(2), pending(3) }
    MAX-ACCESS      read-only
    STATUS          current
    DESCRIPTION     
            "The Status of the peer connection. If the connection
             is up and active this will be set to available. If the
             connection is down then it will be set to
             unavailable."
    ::= { sonusMtrmPeerStatEntry 4 }

sonusMtrmPeerStatShelfId OBJECT-TYPE
    SYNTAX          Integer32
    MAX-ACCESS      read-only
    STATUS          current
    DESCRIPTION     
            "This is the shelf ID that was assiged to this
             connection by the server."
    ::= { sonusMtrmPeerStatEntry 5 }

sonusMtrmPeerStatPeerRole OBJECT-TYPE
    SYNTAX          INTEGER { client(1), server(2) }
    MAX-ACCESS      read-only
    STATUS          current
    DESCRIPTION     
            "This is the shelf ID that was assiged to this
             connection by the server."
    ::= { sonusMtrmPeerStatEntry 6 }

sonusMtrmPeerStatRTO OBJECT-TYPE
    SYNTAX          Integer32
    MAX-ACCESS      read-only
    STATUS          current
    DESCRIPTION     
            "The current Retransmission Time Out in seconds. The
             messages that are in the retransmission buffer will be
             sent at this interval."
    ::= { sonusMtrmPeerStatEntry 7 }

sonusMtrmPeerStatIRRTBDepth OBJECT-TYPE
    SYNTAX          Integer32
    MAX-ACCESS      read-only
    STATUS          current
    DESCRIPTION     
            "This the infinite retry retransmission buffer. The
             messages in this buffer will be attempted to be sent
             to the peer as long as the connection is alive. If
             the connection to the peer is lost this buffer will be 
             flushed."
    ::= { sonusMtrmPeerStatEntry 8 }

sonusMtrmPeerStatFRRTBDepth OBJECT-TYPE
    SYNTAX          Integer32
    MAX-ACCESS      read-only
    STATUS          current
    DESCRIPTION     
            "This the finite retry retransmission buffer. The
             messages in this buffer will be attempted to be sent
             to the server at most twice. Failure to send this
             message to the server will result in the message being
             discarded. If the connection to the peer is lost this 
             buffer will be flushed."
    ::= { sonusMtrmPeerStatEntry 9 }

sonusMtrmPeerStatIpAddress OBJECT-TYPE
    SYNTAX          IpAddress
    MAX-ACCESS      read-only
    STATUS          current
    DESCRIPTION     
            "IP Address of the MTRM Peer."
    ::= { sonusMtrmPeerStatEntry 10 }

sonusMtrmPeerStatMsgsSent OBJECT-TYPE
    SYNTAX          Integer32
    MAX-ACCESS      read-only
    STATUS          current
    DESCRIPTION     
            "The total number of messages sent"
    ::= { sonusMtrmPeerStatEntry 11 }

sonusMtrmPeerStatMsgsRcvd OBJECT-TYPE
    SYNTAX          Integer32
    MAX-ACCESS      read-only
    STATUS          current
    DESCRIPTION     
            "The total number of messages received."
    ::= { sonusMtrmPeerStatEntry 12 }

sonusMtrmPeerStatShelfRegReqMsgsSent OBJECT-TYPE
    SYNTAX          Integer32
    MAX-ACCESS      read-only
    STATUS          current
    DESCRIPTION     
            "The number of Shelf Registration Request messages sent"
    ::= { sonusMtrmPeerStatEntry 13 }

sonusMtrmPeerStatShelfRegReqMsgsRcvd OBJECT-TYPE
    SYNTAX          Integer32
    MAX-ACCESS      read-only
    STATUS          current
    DESCRIPTION     
            "The number of Shelf Registration Request messages received."
    ::= { sonusMtrmPeerStatEntry 14 }

sonusMtrmPeerStatShelfRegRespMsgsSent OBJECT-TYPE
    SYNTAX          Integer32
    MAX-ACCESS      read-only
    STATUS          current
    DESCRIPTION     
            "The number of Shelf Registration Response messages sent"
    ::= { sonusMtrmPeerStatEntry 15 }

sonusMtrmPeerStatShelfRegRespMsgsRcvd OBJECT-TYPE
    SYNTAX          Integer32
    MAX-ACCESS      read-only
    STATUS          current
    DESCRIPTION     
            "The number of Shelf Registration Response messages received."
    ::= { sonusMtrmPeerStatEntry 16 }

sonusMtrmPeerStatHealthCheckReqMsgsSent OBJECT-TYPE
    SYNTAX          Integer32
    MAX-ACCESS      read-only
    STATUS          current
    DESCRIPTION     
            "The number of Health Check Request messages sent"
    ::= { sonusMtrmPeerStatEntry 17 }

sonusMtrmPeerStatHealthCheckReqMsgsRcvd OBJECT-TYPE
    SYNTAX          Integer32
    MAX-ACCESS      read-only
    STATUS          current
    DESCRIPTION     
            "The number of Health Check Request messages received."
    ::= { sonusMtrmPeerStatEntry 18 }

sonusMtrmPeerStatHealthCheckRespMsgsSent OBJECT-TYPE
    SYNTAX          Integer32
    MAX-ACCESS      read-only
    STATUS          current
    DESCRIPTION     
            "The number of Health Check Response messages sent"
    ::= { sonusMtrmPeerStatEntry 19 }

sonusMtrmPeerStatHealthCheckRespMsgsRcvd OBJECT-TYPE
    SYNTAX          Integer32
    MAX-ACCESS      read-only
    STATUS          current
    DESCRIPTION     
            "The number of Health Check Response messages received."
    ::= { sonusMtrmPeerStatEntry 20 }

sonusMtrmPeerStatMtrgRegReqMsgsSent OBJECT-TYPE
    SYNTAX          Integer32
    MAX-ACCESS      read-only
    STATUS          current
    DESCRIPTION     
            "The number of MTRG Registration Request messages sent"
    ::= { sonusMtrmPeerStatEntry 21 }

sonusMtrmPeerStatMtrgRegReqMsgsRcvd OBJECT-TYPE
    SYNTAX          Integer32
    MAX-ACCESS      read-only
    STATUS          current
    DESCRIPTION     
            "The number of MTRG Registration Request messages received."
    ::= { sonusMtrmPeerStatEntry 22 }

sonusMtrmPeerStatMtrgRegRespMsgsSent OBJECT-TYPE
    SYNTAX          Integer32
    MAX-ACCESS      read-only
    STATUS          current
    DESCRIPTION     
            "The number of MTRG Registration Response messages sent"
    ::= { sonusMtrmPeerStatEntry 23 }

sonusMtrmPeerStatMtrgRegRespMsgsRcvd OBJECT-TYPE
    SYNTAX          Integer32
    MAX-ACCESS      read-only
    STATUS          current
    DESCRIPTION     
            "The number of MTRG Registration Response messages received."
    ::= { sonusMtrmPeerStatEntry 24 }

sonusMtrmPeerStatIpAuditReqMsgsSent OBJECT-TYPE
    SYNTAX          Integer32
    MAX-ACCESS      read-only
    STATUS          current
    DESCRIPTION     
            "The number of IP Audit Request messages sent"
    ::= { sonusMtrmPeerStatEntry 25 }

sonusMtrmPeerStatIpAuditReqMsgsRcvd OBJECT-TYPE
    SYNTAX          Integer32
    MAX-ACCESS      read-only
    STATUS          current
    DESCRIPTION     
            "The number of IP Audit Request messages received."
    ::= { sonusMtrmPeerStatEntry 26 }

sonusMtrmPeerStatIpAuditRespMsgsSent OBJECT-TYPE
    SYNTAX          Integer32
    MAX-ACCESS      read-only
    STATUS          current
    DESCRIPTION     
            "The number of IP Audit Response messages sent"
    ::= { sonusMtrmPeerStatEntry 27 }

sonusMtrmPeerStatIpAuditRespMsgsRcvd OBJECT-TYPE
    SYNTAX          Integer32
    MAX-ACCESS      read-only
    STATUS          current
    DESCRIPTION     
            "The number of IP Audit Response messages received."
    ::= { sonusMtrmPeerStatEntry 28 }

sonusMtrmPeerStatBwAllocReqMsgsSent OBJECT-TYPE
    SYNTAX          Integer32
    MAX-ACCESS      read-only
    STATUS          current
    DESCRIPTION     
            "The number of Bandwidth Allocation Request messages sent"
    ::= { sonusMtrmPeerStatEntry 29 }

sonusMtrmPeerStatBwAllocReqMsgsRcvd OBJECT-TYPE
    SYNTAX          Integer32
    MAX-ACCESS      read-only
    STATUS          current
    DESCRIPTION     
            "The number of Bandwidth Allocation Request messages received."
    ::= { sonusMtrmPeerStatEntry 30 }

sonusMtrmPeerStatBwAllocRespMsgsSent OBJECT-TYPE
    SYNTAX          Integer32
    MAX-ACCESS      read-only
    STATUS          current
    DESCRIPTION     
            "The number of Bandwidth Allocation Response messages sent"
    ::= { sonusMtrmPeerStatEntry 31 }

sonusMtrmPeerStatBwAllocRespMsgsRcvd OBJECT-TYPE
    SYNTAX          Integer32
    MAX-ACCESS      read-only
    STATUS          current
    DESCRIPTION     
            "The number of Bandwidth Allocation Response messages received."
    ::= { sonusMtrmPeerStatEntry 32 }

sonusMtrmPeerStatCallAllocReqMsgsSent OBJECT-TYPE
    SYNTAX          Integer32
    MAX-ACCESS      read-only
    STATUS          current
    DESCRIPTION     
            "The number of Call Allocation Request messages sent"
    ::= { sonusMtrmPeerStatEntry 33 }

sonusMtrmPeerStatCallAllocReqMsgsRcvd OBJECT-TYPE
    SYNTAX          Integer32
    MAX-ACCESS      read-only
    STATUS          current
    DESCRIPTION     
            "The number of Call Allocation Request messages received."
    ::= { sonusMtrmPeerStatEntry 34 }

sonusMtrmPeerStatCallAllocRespMsgsSent OBJECT-TYPE
    SYNTAX          Integer32
    MAX-ACCESS      read-only
    STATUS          current
    DESCRIPTION     
            "The number of Call Allocation Response messages sent"
    ::= { sonusMtrmPeerStatEntry 35 }

sonusMtrmPeerStatCallAllocRespMsgsRcvd OBJECT-TYPE
    SYNTAX          Integer32
    MAX-ACCESS      read-only
    STATUS          current
    DESCRIPTION     
            "The number of Call Allocation Response messages received."
    ::= { sonusMtrmPeerStatEntry 36 }

sonusMtrmPeerStatBwFreeReqMsgsSent OBJECT-TYPE
    SYNTAX          Integer32
    MAX-ACCESS      read-only
    STATUS          current
    DESCRIPTION     
            "The number of  Bandwidth Free Request messages sent"
    ::= { sonusMtrmPeerStatEntry 37 }

sonusMtrmPeerStatBwFreeReqMsgsRcvd OBJECT-TYPE
    SYNTAX          Integer32
    MAX-ACCESS      read-only
    STATUS          current
    DESCRIPTION     
            "The number of Bandwidth Free Request messages received."
    ::= { sonusMtrmPeerStatEntry 38 }

sonusMtrmPeerStatCallFreeReqMsgsSent OBJECT-TYPE
    SYNTAX          Integer32
    MAX-ACCESS      read-only
    STATUS          current
    DESCRIPTION     
            "The number of Call Free Request messages sent"
    ::= { sonusMtrmPeerStatEntry 39 }

sonusMtrmPeerStatCallFreeReqMsgsRcvd OBJECT-TYPE
    SYNTAX          Integer32
    MAX-ACCESS      read-only
    STATUS          current
    DESCRIPTION     
            "The number of Call Free Request messages received."
    ::= { sonusMtrmPeerStatEntry 40 }

sonusMtrmPeerStatTakeBackBwIndMsgsSent OBJECT-TYPE
    SYNTAX          Integer32
    MAX-ACCESS      read-only
    STATUS          current
    DESCRIPTION     
            "The number of Take Back Bandwidth Indication messages sent"
    ::= { sonusMtrmPeerStatEntry 41 }

sonusMtrmPeerStatTakeBackBwIndMsgsRcvd OBJECT-TYPE
    SYNTAX          Integer32
    MAX-ACCESS      read-only
    STATUS          current
    DESCRIPTION     
            "The number of Take Back Bandwidth Indication messages received."
    ::= { sonusMtrmPeerStatEntry 42 }

sonusMtrmPeerStatTakeBackCallsIndMsgsSent OBJECT-TYPE
    SYNTAX          Integer32
    MAX-ACCESS      read-only
    STATUS          current
    DESCRIPTION     
            "The number of Take Back Call Indication messages sent"
    ::= { sonusMtrmPeerStatEntry 43 }

sonusMtrmPeerStatTakeBackCallsIndMsgsRcvd OBJECT-TYPE
    SYNTAX          Integer32
    MAX-ACCESS      read-only
    STATUS          current
    DESCRIPTION     
            "The number of Take Back Call Indication messages received."
    ::= { sonusMtrmPeerStatEntry 44 }

sonusMtrmPeerStatMtrgDeregReqMsgsSent OBJECT-TYPE
    SYNTAX          Integer32
    MAX-ACCESS      read-only
    STATUS          current
    DESCRIPTION     
            "The number of Master Trunk Group Deregistration Request messages sent"
    ::= { sonusMtrmPeerStatEntry 45 }

sonusMtrmPeerStatMtrgDeregReqMsgsRcvd OBJECT-TYPE
    SYNTAX          Integer32
    MAX-ACCESS      read-only
    STATUS          current
    DESCRIPTION     
            "The number of Master Trunk Group Deregistration Request  messages received."
    ::= { sonusMtrmPeerStatEntry 46 }

sonusMtrmPeerStatMtrgUnavailableMsgsSent OBJECT-TYPE
    SYNTAX          Integer32
    MAX-ACCESS      read-only
    STATUS          current
    DESCRIPTION     
            "The number of Master Trunk Group Unavailable messages sent"
    ::= { sonusMtrmPeerStatEntry 47 }

sonusMtrmPeerStatMtrgUnavailableMsgsRcvd OBJECT-TYPE
    SYNTAX          Integer32
    MAX-ACCESS      read-only
    STATUS          current
    DESCRIPTION     
            "The number of Master Trunk Group Unavailable messages received."
    ::= { sonusMtrmPeerStatEntry 48 }

sonusMtrmPeerStatIp6Address OBJECT-TYPE
    SYNTAX          Ipv6Address
    MAX-ACCESS      read-write
    STATUS          current
    DESCRIPTION     
            "IPV6 Address of the MTRM Peer."
    ::= { sonusMtrmPeerStatEntry 49 }

sonusMtrmPeerStatIpVersion OBJECT-TYPE
    SYNTAX          INTEGER { afInet(2), afInet6(24) }
    MAX-ACCESS      read-only
    STATUS          current
    DESCRIPTION     
            "IP Address type of the MTRM Peer."
    ::= { sonusMtrmPeerStatEntry 50 }

sonusMtrmPeerStatConnType OBJECT-TYPE
    SYNTAX          INTEGER { none(0), primary(1), secondary(2) }
    MAX-ACCESS      read-only
    STATUS          current
    DESCRIPTION     
            "This indicates the connection type is none, primary or secondary.
             In the server perspective, the connType is set to none"
    ::= { sonusMtrmPeerStatEntry 51 }

sonusMtrmMtrgClientObjects OBJECT IDENTIFIER
    ::= { sonusMasterTrunkResourceManagerMIBObjects 4 }

sonusMtrmMtrgClientTable OBJECT-TYPE
    SYNTAX          SEQUENCE OF SonusMtrmMtrgClientEntry
    MAX-ACCESS      not-accessible
    STATUS          current
    DESCRIPTION     
            "Table of MTRM communication MTRG client configurations."
    ::= { sonusMtrmMtrgClientObjects 1 }

sonusMtrmMtrgClientEntry OBJECT-TYPE
    SYNTAX          SonusMtrmMtrgClientEntry
    MAX-ACCESS      not-accessible
    STATUS          current
    DESCRIPTION     
            "MTRM client  communication configuration."
    INDEX           { sonusMtrmMtrgClientIndex }
    ::= { sonusMtrmMtrgClientTable 1 }

SonusMtrmMtrgClientEntry ::=
    SEQUENCE {
        sonusMtrmMtrgClientIndex        Integer32,
        sonusMtrmMtrgClientName         SonusName,
        sonusMtrmMtrgClientType         INTEGER,
        sonusMtrmMtrgClientMaxCalls     Integer32,
        sonusMtrmMtrgClientMaxBW        Integer32,
        sonusMtrmMtrgClientHuntAlgorithm INTEGER,
        sonusMtrmMtrgClientMtrmIndex    Integer32,
        sonusMtrmMtrgClientMode         SonusServiceState,
        sonusMtrmMtrgClientState        SonusAdminState,
        sonusMtrmMtrgClientRowStatus    RowStatus
    }

sonusMtrmMtrgClientIndex OBJECT-TYPE
    SYNTAX          Integer32
    MAX-ACCESS      read-only
    STATUS          current
    DESCRIPTION     
            "Identifies the Client MTRG entry."
    ::= { sonusMtrmMtrgClientEntry 1 }

sonusMtrmMtrgClientName OBJECT-TYPE
    SYNTAX          SonusName
    MAX-ACCESS      read-write
    STATUS          current
    DESCRIPTION     
            "Name of the Client MTRG object that is to be associated with
             the trunk groups. This name will be used as the key to
             collect the trunk groups together."
    ::= { sonusMtrmMtrgClientEntry 2 }

sonusMtrmMtrgClientType OBJECT-TYPE
    SYNTAX          INTEGER { ip(1), pstn(2) }
    MAX-ACCESS      read-write
    STATUS          current
    DESCRIPTION     
            "The rest of the configuration parameters depend on
             this. Some parameters are not applicable to IP and
             others may not be applicable to PSTN."
    DEFVAL          { ip }
    ::= { sonusMtrmMtrgClientEntry 3 }

sonusMtrmMtrgClientMaxCalls OBJECT-TYPE
    SYNTAX          Integer32 (-1..2147483647)
    MAX-ACCESS      read-write
    STATUS          current
    DESCRIPTION     
            "The number of calls that can be made on this Master
             Trunk Group. This value is only of concern if this
             object refers to an MTRM server. In the client
             incarnamtion the local maximas prevail. This value is
             currently only used when the MTRG is of type IP.
             A negative value is unlimited."
    DEFVAL          { -1 }
    ::= { sonusMtrmMtrgClientEntry 4 }

sonusMtrmMtrgClientMaxBW OBJECT-TYPE
    SYNTAX          Integer32 (-1..2147483647)
    MAX-ACCESS      read-write
    STATUS          current
    DESCRIPTION     
            "The amount of bandwidth that can be allocated in
             total. This value is only of concern to an MTRM
             Server. This value is currently only used when the
             MTRG is of type IP."
    DEFVAL          { -1 }
    ::= { sonusMtrmMtrgClientEntry 5 }

sonusMtrmMtrgClientHuntAlgorithm OBJECT-TYPE
    SYNTAX          INTEGER { circuithi2lo(1), circuitlo2hi(2), 
                        mostnleastidle(3), circularbottom2top(4), 
                        circulartop2bottom(5) }
    MAX-ACCESS      read-write
    STATUS          current
    DESCRIPTION     
            "This value determines the hunt algorithm used for
             this MTRG. This value is only of significance when set
             against trunk groups populated on the MTRM server."
    DEFVAL          { mostnleastidle }
    ::= { sonusMtrmMtrgClientEntry 6 }

sonusMtrmMtrgClientMtrmIndex OBJECT-TYPE
    SYNTAX          Integer32 (0..128)
    MAX-ACCESS      read-write
    STATUS          current
    DESCRIPTION     
            "This index refers to the MTRM object this MTRG
             belongs to. The MTRM should be configured and enabled
             for this object to be set. A value of 0 means no index."
    ::= { sonusMtrmMtrgClientEntry 7 }

sonusMtrmMtrgClientMode OBJECT-TYPE
    SYNTAX          SonusServiceState
    MAX-ACCESS      read-write
    STATUS          current
    DESCRIPTION     
            "Mode of the MTRM Communication Port."
    DEFVAL          { inService }
    ::= { sonusMtrmMtrgClientEntry 8 }

sonusMtrmMtrgClientState OBJECT-TYPE
    SYNTAX          SonusAdminState
    MAX-ACCESS      read-write
    STATUS          current
    DESCRIPTION     
            "State of the MTRM Communication Port."
    DEFVAL          { disabled }
    ::= { sonusMtrmMtrgClientEntry 9 }

sonusMtrmMtrgClientRowStatus OBJECT-TYPE
    SYNTAX          RowStatus
    MAX-ACCESS      read-write
    STATUS          current
    DESCRIPTION     
            "This is for SNMP use."
    ::= { sonusMtrmMtrgClientEntry 10 }

sonusMtrmMtrgClientNextIndex OBJECT-TYPE
    SYNTAX          Integer32
    MAX-ACCESS      read-only
    STATUS          current
    DESCRIPTION     
            "Retrieves the next valid index to use for the CLient MTRG
             entry."
    ::= { sonusMtrmMtrgClientObjects 2 }

sonusMtrmMIBNotifications OBJECT IDENTIFIER
    ::= { sonusMasterTrunkResourcesManagerMIB 2 }

sonusMtrmMIBNotificationsPrefix OBJECT IDENTIFIER
    ::= { sonusMtrmMIBNotifications 0 }

sonusMtrmMIBNotificationsObjects OBJECT IDENTIFIER
    ::= { sonusMtrmMIBNotifications 1 }

sonusMtrmConnCloseReasonCode OBJECT-TYPE
    SYNTAX          INTEGER { administratorInitiatedClose(1), 
                        closeRequestReceivedFromRemote(2), 
                        remoteNotResponding(3), internalError(4), 
                        configError(5), socketErrNetworkDown(7), 
                        socketErrNetworkUnreachable(8), 
                        socketErrNetworkReset(9), 
                        socketErrSoftwareConnectionAbort(10), 
                        socketErrConnectionResetByPeer(11), 
                        socketErrNoBufferSpaceAvail(12), 
                        socketErrAlreadyConnected(13), 
                        socketErrNotConnected(14), 
                        socketErrCantSendAfterShutdown(15), 
                        socketErrTooManyReferences(16), 
                        socketErrConnectionTimedOut(17), 
                        socketErrUnknown(18), 
                        socketErrExceptionEvent(20), 
                        primaryServerConnectionUp(21) }
    MAX-ACCESS      read-only
    STATUS          current
    DESCRIPTION     
            "Reason for MTRM unavailability."
    ::= { sonusMtrmMIBNotificationsObjects 1 }

sonusMtrmServerAddr OBJECT-TYPE
    SYNTAX          IpAddress
    MAX-ACCESS      read-only
    STATUS          current
    DESCRIPTION     
            "The IP address of the server that this port
             is communicating to."
    ::= { sonusMtrmMIBNotificationsObjects 3 }

sonusMtrmServerAddrV6 OBJECT-TYPE
    SYNTAX          Ipv6Address
    MAX-ACCESS      read-only
    STATUS          current
    DESCRIPTION     
            "The IP address of the server that this port
             is communicating to."
    ::= { sonusMtrmMIBNotificationsObjects 4 }

sonusMtrmConnType OBJECT-TYPE
    SYNTAX          DisplayString (SIZE(0..10))
    MAX-ACCESS      read-only
    STATUS          current
    DESCRIPTION     
            "The connection type:  Primary, Secondary or a blank string"
    ::= { sonusMtrmMIBNotificationsObjects 5 }

sonusMtrmPortAvailNotification NOTIFICATION-TYPE
    OBJECTS         { sonusMtrmPortIndex, sonusMtrmServerAddr, 
                      sonusEventDescription, sonusEventClass, 
                      sonusEventLevel, sonusSequenceId, sonusEventTime }
    STATUS          obsolete
    DESCRIPTION     
            "This trap is generated from the client and indicates that a MTRM server Port has become available.
             This trap is replaced by trap sonusMtrmPortConnAvailNotification. "
    ::= { sonusMtrmMIBNotificationsPrefix 1 }

sonusMtrmPortUnAvailNotification NOTIFICATION-TYPE
    OBJECTS         { sonusMtrmPortIndex, sonusMtrmServerAddr, 
                      sonusMtrmConnCloseReasonCode, 
                      sonusEventDescription, sonusEventClass, 
                      sonusEventLevel, sonusSequenceId, sonusEventTime }
    STATUS          obsolete
    DESCRIPTION     
            "This trap indicates that a MTRM connection to the peer has become unavailable.
             This trap is replaced by trap sonusMtrmPortConnUnAvailNotification. "
    ::= { sonusMtrmMIBNotificationsPrefix 2 }

sonusMtrmPortRegisterAttemptNotification NOTIFICATION-TYPE
    OBJECTS         { sonusMtrmPortIndex, sonusMtrmServerAddr, 
                      sonusEventDescription, sonusEventClass, 
                      sonusEventLevel, sonusSequenceId, sonusEventTime }
    STATUS          obsolete
    DESCRIPTION     
            "This trap is being removed.
             This trap indicates that a MTRM client has attempted to contact the MTRM server."
    ::= { sonusMtrmMIBNotificationsPrefix 3 }

sonusMtrmPortRetryTimerExpiryNotification NOTIFICATION-TYPE
    OBJECTS         { sonusMtrmPortIndex, sonusMtrmServerAddr, 
                      sonusEventDescription, sonusEventClass, 
                      sonusEventLevel, sonusSequenceId, sonusEventTime }
    STATUS          obsolete
    DESCRIPTION     
            "This trap indicates that this port has failed
             communication retries to the peer.
             This trap is replaced by trap sonusMtrmPortConnRetryTimerExpiryNotification. "
    ::= { sonusMtrmMIBNotificationsPrefix 4 }

sonusMtrmPortAvailNotificationV6 NOTIFICATION-TYPE
    OBJECTS         { sonusMtrmPortIndex, sonusMtrmServerAddrV6, 
                      sonusEventDescription, sonusEventClass, 
                      sonusEventLevel, sonusSequenceId, sonusEventTime }
    STATUS          current
    DESCRIPTION     
            "This trap is generated from the client and indicates that a MTRM server Port has become available ."
    ::= { sonusMtrmMIBNotificationsPrefix 5 }

sonusMtrmPortUnAvailNotificationV6 NOTIFICATION-TYPE
    OBJECTS         { sonusMtrmPortIndex, sonusMtrmServerAddrV6, 
                      sonusMtrmConnCloseReasonCode, 
                      sonusEventDescription, sonusEventClass, 
                      sonusEventLevel, sonusSequenceId, sonusEventTime }
    STATUS          current
    DESCRIPTION     
            "This trap indicates that a MTRM connection to the peer has become unavailable."
    ::= { sonusMtrmMIBNotificationsPrefix 6 }

sonusMtrmPortRegisterAttemptNotificationV6 NOTIFICATION-TYPE
    OBJECTS         { sonusMtrmPortIndex, sonusMtrmServerAddrV6, 
                      sonusEventDescription, sonusEventClass, 
                      sonusEventLevel, sonusSequenceId, sonusEventTime }
    STATUS          current
    DESCRIPTION     
            "This trap indicates that a MTRM client has attempted to contact the MTRM server."
    ::= { sonusMtrmMIBNotificationsPrefix 7 }

sonusMtrmPortRetryTimerExpiryNotificationV6 NOTIFICATION-TYPE
    OBJECTS         { sonusMtrmPortIndex, sonusMtrmServerAddrV6, 
                      sonusEventDescription, sonusEventClass, 
                      sonusEventLevel, sonusSequenceId, sonusEventTime }
    STATUS          current
    DESCRIPTION     
            "This trap indicates that this port has failed
             communication retries to the peer."
    ::= { sonusMtrmMIBNotificationsPrefix 8 }

sonusMtrmPortConnAvailNotification NOTIFICATION-TYPE
    OBJECTS         { sonusMtrmPortIndex, sonusMtrmServerAddr, 
                      sonusMtrmConnType, sonusEventDescription, 
                      sonusEventClass, sonusEventLevel, sonusSequenceId, 
                      sonusEventTime }
    STATUS          current
    DESCRIPTION     
            "This trap replaces sonusMtrmPortAvailNotification. It adds the sonusMtrmConnType. 
             This trap is generated from the client and indicates that a MTRM server Port has become available."
    ::= { sonusMtrmMIBNotificationsPrefix 9 }

sonusMtrmPortConnUnAvailNotification NOTIFICATION-TYPE
    OBJECTS         { sonusMtrmPortIndex, sonusMtrmServerAddr, 
                      sonusMtrmConnType, sonusMtrmConnCloseReasonCode, 
                      sonusEventDescription, sonusEventClass, 
                      sonusEventLevel, sonusSequenceId, sonusEventTime }
    STATUS          current
    DESCRIPTION     
            "This trap replaces sonusMtrmPortUnAvailNotification. It adds the sonusMtrmConnType. 
             This trap indicates that a MTRM connection to the peer has become unavailable."
    ::= { sonusMtrmMIBNotificationsPrefix 10 }

sonusMtrmPortConnRetryTimerExpiryNotification NOTIFICATION-TYPE
    OBJECTS         { sonusMtrmPortIndex, sonusMtrmServerAddr, 
                      sonusMtrmConnType, sonusEventDescription, 
                      sonusEventClass, sonusEventLevel, sonusSequenceId, 
                      sonusEventTime }
    STATUS          current
    DESCRIPTION     
            "This trap replaces sonusMtrmPortRetryTimerExpiryNotification. It adds the sonusMtrmConnType. 
             This trap indicates that this port has failed
             		communication retries to the peer."
    ::= { sonusMtrmMIBNotificationsPrefix 11 }

END -- end of module SONUS-MASTER-TRUNK-RESOURCE-MANAGER-MIB.
