--
-- This SMIv2 module has been generated by smidump 0.2-cvs. Do not edit.
--

SONUS-LICENSE-MIB DEFINITIONS ::= BEGIN

IMPORTS
    Counter32, Counter64, Gauge32, Integer32, IpAddress, MODULE-IDENTITY, 
    OBJECT-TYPE, Unsigned32
        FROM SNMPv2-SMI
    DateAndTime, RowStatus, TEXTUAL-CONVENTION, TruthValue
        FROM SNMPv2-TC
    sonusCommonSoftwarePlatformServicesMIBs
        FROM SONUS-SMI;

sonusLicenseMIB MODULE-IDENTITY
    LAST-UPDATED    "201212310000Z"
    ORGANIZATION    
            "Sonus Networks, Inc."
    CONTACT-INFO    
            "Customer Support        
             Sonus Networks, Inc.    
             4 Technology Park Drive 
             Westford, MA 01886      
             USA                     
                                     
             Tel: 978-614-8100       
             Fax: 978-614-8609"
    DESCRIPTION     
            "The MIB module for Sonus License."
    REVISION        "201212310000Z"
    DESCRIPTION     
            "Auto generated MIB."
    ::= { sonusCommonSoftwarePlatformServicesMIBs 16 }


ConfdString ::= TEXTUAL-CONVENTION
    DISPLAY-HINT    "1t"
    STATUS          current
    DESCRIPTION     
            "xs: and confd: types mapped to strings"
    SYNTAX          OCTET STRING

String ::= TEXTUAL-CONVENTION
    DISPLAY-HINT    "1t"
    STATUS          current
    DESCRIPTION     
            "xs:string"
    SYNTAX          OCTET STRING

LicenseBundleString ::= TEXTUAL-CONVENTION
    DISPLAY-HINT    "1t"
    STATUS          current
    DESCRIPTION     
            ""
    SYNTAX          OCTET STRING (SIZE(0..12288))

sonusLicense OBJECT IDENTIFIER
    ::= { sonusLicenseMIB 1 }

sonusLicenseBundleTable OBJECT-TYPE
    SYNTAX          SEQUENCE OF SonusLicenseBundleEntry
    MAX-ACCESS      not-accessible
    STATUS          current
    DESCRIPTION     
            " 
             The license bundle.
             "
    ::= { sonusLicense 1 }

sonusLicenseBundleEntry OBJECT-TYPE
    SYNTAX          SonusLicenseBundleEntry
    MAX-ACCESS      not-accessible
    STATUS          current
    DESCRIPTION     
            ""
    INDEX           { IMPLIED sonusLicenseBundleBundleName }
    ::= { sonusLicenseBundleTable 1 }

SonusLicenseBundleEntry ::=
    SEQUENCE {
        sonusLicenseBundleBundleName    String,
        sonusLicenseBundleBundleString  LicenseBundleString,
        sonusLicenseBundleRowstatus     RowStatus
    }

sonusLicenseBundleBundleName OBJECT-TYPE
    SYNTAX          String (SIZE(0..23))
    MAX-ACCESS      not-accessible
    STATUS          current
    DESCRIPTION     
            " 
             This indicates the license identifier for license bundle.
             "
    ::= { sonusLicenseBundleEntry 1 }

sonusLicenseBundleBundleString OBJECT-TYPE
    SYNTAX          LicenseBundleString
    MAX-ACCESS      read-create
    STATUS          current
    DESCRIPTION     
            "
             This object indicates the license bundle XML string.
             "
    ::= { sonusLicenseBundleEntry 2 }

sonusLicenseBundleRowstatus OBJECT-TYPE
    SYNTAX          RowStatus
    MAX-ACCESS      read-create
    STATUS          current
    DESCRIPTION     
            ""
    ::= { sonusLicenseBundleEntry 3 }

END -- end of module SONUS-LICENSE-MIB.
