--
-- This SMIv2 module has been generated by smidump 0.2-cvs. Do not edit.
--

SONUS-GEN2-SOFTWARE-UPGRADE-SERVICES-MIB DEFINITIONS ::= BEGIN

IMPORTS
    Counter32, Counter64, Gauge32, Integer32, IpAddress, MODULE-IDENTITY, 
    OBJECT-TYPE, Unsigned32
        FROM SNMPv2-SMI
    DateAndTime, RowStatus, TEXTUAL-CONVENTION, TruthValue
        FROM SNMPv2-TC
    sonusCommonSoftwarePlatformServicesMIBs
        FROM SONUS-SMI;

sonusGen2SoftwareUpgradeMIB MODULE-IDENTITY
    LAST-UPDATED    "200906010000Z"
    ORGANIZATION    
            "Sonus Networks, Inc."
    CONTACT-INFO    
            "Customer Support        
             Sonus Networks, Inc.    
             7 Technology Park Drive 
             Westford, MA 01886      
             USA                     
                                     
             Tel: 978-614-8100       
             Fax: 978-614-8609"
    DESCRIPTION     
            "
             The MIB Module for Software Upgrade Configuration.
             "
    REVISION        "200906010000Z"
    DESCRIPTION     
            "Auto generated MIB."
    ::= { sonusCommonSoftwarePlatformServicesMIBs 9 }


Token ::= TEXTUAL-CONVENTION
    DISPLAY-HINT    "1t"
    STATUS          current
    DESCRIPTION     
            "xs:token"
    SYNTAX          OCTET STRING

String ::= TEXTUAL-CONVENTION
    DISPLAY-HINT    "1t"
    STATUS          current
    DESCRIPTION     
            "xs:string"
    SYNTAX          OCTET STRING

SonusSwUpgradeShelfAdmnDirectoryType ::= TEXTUAL-CONVENTION
    DISPLAY-HINT    "1t"
    STATUS          current
    DESCRIPTION     
            ""
    SYNTAX          OCTET STRING (SIZE(0..255))

SonusSwUpgradeShelfStatStatusType ::= TEXTUAL-CONVENTION
    STATUS          current
    DESCRIPTION     
            "
             "
    SYNTAX          INTEGER { idle(1), busy(2), complete(3), 
                        incomplete(4), commitRequired(5) }

SonusSwUpgradeShelfStatLastReasonType ::= TEXTUAL-CONVENTION
    STATUS          current
    DESCRIPTION     
            "
             "
    SYNTAX          INTEGER { none(0), successfulCompletion(1), 
                        initTimeout(2), manualHalt(3), 
                        upgradeNotRequired(4), fileUnavailable(5), 
                        parametersNotSaved(6), flashUpdateInProgress(7), 
                        redundSlotActive(8), switchover1Timeout(9), 
                        sync1Timeout(10), switchover2Timeout(11), 
                        sync2Timeout(12), rebootTimeout(13), 
                        mnsNotSynced(14), notActive(15), 
                        internalTimerUnavailable(16), 
                        internalQueryTimeout(17), 
                        internalResourceUnavailable(18), 
                        internalRtmError(19), mnsSwitchover(20), 
                        overallSyncTimeout(21), unexpectedSwitchover(22), 
                        syncFailure(23), skipUnprotectedModules(24), 
                        invalidVersion(25), matrixFileUnavailable(26), 
                        unsupportedUpgradePath(27), 
                        mnsLocalDisksNotSynced(28), nvsReadError(29), 
                        nvsNotValid(30), 
                        unsupportedAcctUpgradePatchVer(31) }

SonusSwUpgradeSlotStatUpgradeType ::= TEXTUAL-CONVENTION
    STATUS          current
    DESCRIPTION     
            "
             "
    SYNTAX          INTEGER { none(1), smooth(2), disrupt(3), 
                        unavailable(4), unknown(5) }

SonusSwUpgradeSlotStatVersionType ::= TEXTUAL-CONVENTION
    DISPLAY-HINT    "1t"
    STATUS          current
    DESCRIPTION     
            ""
    SYNTAX          OCTET STRING (SIZE(0..255))

SonusSwUpgradeShelfAdmnUnprotectedControlType ::= TEXTUAL-CONVENTION
    STATUS          current
    DESCRIPTION     
            "
             "
    SYNTAX          INTEGER { upgrade(1), skip(2) }

SonusSoftwareUpgradeState ::= TEXTUAL-CONVENTION
    STATUS          current
    DESCRIPTION     
            "
             Represents the different states in LSWU FSM. (Internal use only)
             "
    SYNTAX          INTEGER { idle(0), query(1), init(2), delay1(3), 
                        start(4), sxOne(5), waitSync(6), sxTwoTx(7), 
                        sxTwoRx(8), sxTwoWait(9), variant(10), 
                        prepare(11), stopCalls(12), firstPns(13), 
                        cnsReset(14), spsReset(15), pnsReset(16), 
                        sxDelay(17), done(18), redundOosReset(19), 
                        redundOosWait(20), groupSetup(21), clientSx(22), 
                        clientRevert(23), groupRestore(24), 
                        firstUnprotectedReset(25), 
                        secondUnprotectedReset(26), parameterSave(27) }

SonusSwUpgradeShelfAdmnOverrideFeatureCheckType ::= TEXTUAL-CONVENTION
    STATUS          current
    DESCRIPTION     
            "
             "
    SYNTAX          INTEGER { ready(1), override(2) }

SonusSwUpgradeSlotStatStatusType ::= TEXTUAL-CONVENTION
    STATUS          current
    DESCRIPTION     
            "
             "
    SYNTAX          INTEGER { idle(1), busy(2), complete(3), unknown(4), 
                        noImageFile(5), invalidVersion(6) }

SonusSwUpgradeShelfAdmnCommitDirectoryType ::= TEXTUAL-CONVENTION
    STATUS          current
    DESCRIPTION     
            "
             "
    SYNTAX          INTEGER { ready(1), commit(2) }

sonusSwUpgradeServices OBJECT IDENTIFIER
    ::= { sonusGen2SoftwareUpgradeMIB 1 }

sonusSwUpgradeServicesShelfAdmnTable OBJECT-TYPE
    SYNTAX          SEQUENCE OF SonusSwUpgradeServicesShelfAdmnEntry
    MAX-ACCESS      not-accessible
    STATUS          current
    DESCRIPTION     
            "
             This table specifies the software upgrade configuration.
             "
    ::= { sonusSwUpgradeServices 1 }

sonusSwUpgradeServicesShelfAdmnEntry OBJECT-TYPE
    SYNTAX          SonusSwUpgradeServicesShelfAdmnEntry
    MAX-ACCESS      not-accessible
    STATUS          current
    DESCRIPTION     
            ""
    INDEX           { sonusSwUpgradeServicesShelfAdmnShelf }
    ::= { sonusSwUpgradeServicesShelfAdmnTable 1 }

SonusSwUpgradeServicesShelfAdmnEntry ::=
    SEQUENCE {
        sonusSwUpgradeServicesShelfAdmnShelf    Unsigned32,
        sonusSwUpgradeServicesShelfAdmnCommitDirectory              SonusSwUpgradeShelfAdmnCommitDirectoryType,
        sonusSwUpgradeServicesShelfAdmnDirectory        SonusSwUpgradeShelfAdmnDirectoryType,
        sonusSwUpgradeServicesShelfAdmnOverrideFeatureCheck                   SonusSwUpgradeShelfAdmnOverrideFeatureCheckType,
        sonusSwUpgradeServicesShelfAdmnUnprotectedControl                 SonusSwUpgradeShelfAdmnUnprotectedControlType,
        sonusSwUpgradeServicesShelfAdmnRowstatus        RowStatus
    }

sonusSwUpgradeServicesShelfAdmnShelf OBJECT-TYPE
    SYNTAX          Unsigned32 (1..6)
    MAX-ACCESS      not-accessible
    STATUS          current
    DESCRIPTION     
            "
             The shelf index of this software upgrade entry.
             "
    ::= { sonusSwUpgradeServicesShelfAdmnEntry 1 }

sonusSwUpgradeServicesShelfAdmnCommitDirectory OBJECT-TYPE
    SYNTAX          SonusSwUpgradeShelfAdmnCommitDirectoryType
    MAX-ACCESS      read-create
    STATUS          current
    DESCRIPTION     
            "
             Commit the new software distribution directory name into NVS.
               
             This MIB object can only be set by a user with admin
             privileges; it always reads as ready(1).
             "
    DEFVAL          { ready }
    ::= { sonusSwUpgradeServicesShelfAdmnEntry 2 }

sonusSwUpgradeServicesShelfAdmnDirectory OBJECT-TYPE
    SYNTAX          SonusSwUpgradeShelfAdmnDirectoryType
    MAX-ACCESS      read-create
    STATUS          current
    DESCRIPTION     
            "
             The new software distribution directory name.
               
             This MIB object can only be set by a user with admin
             privileges.
             "
    ::= { sonusSwUpgradeServicesShelfAdmnEntry 3 }

sonusSwUpgradeServicesShelfAdmnOverrideFeatureCheck OBJECT-TYPE
    SYNTAX          SonusSwUpgradeShelfAdmnOverrideFeatureCheckType
    MAX-ACCESS      read-create
    STATUS          current
    DESCRIPTION     
            "
             Ignore the check for unsupported features (i.e. features
             that would prevent a software upgrade from occurring) during
             initialization.  This MIB object must be set with
             sonusSwUpgradeShelfAdmnInit in the same request.
               
             This MIB object can only be set through the CLI, and only
             by a user with admin privileges; it always reads as ready(1).
             "
    DEFVAL          { ready }
    ::= { sonusSwUpgradeServicesShelfAdmnEntry 4 }

sonusSwUpgradeServicesShelfAdmnUnprotectedControl OBJECT-TYPE
    SYNTAX          SonusSwUpgradeShelfAdmnUnprotectedControlType
    MAX-ACCESS      read-create
    STATUS          current
    DESCRIPTION     
            "
             Controls the handling of server modules that are In Service, but
             not protected by redundancy during a Live Software Upgrade.  This
             MIB object must be set before an upgrade is initialized.
               
             If set to upgrade(1), these server modules will be individually
             reset during the upgrade, thereby dropping any calls they are
             carrying at the time.  This is the default behavior.
               
             If set to skip(2), the upgrade process will exit early, leaving
             these server modules running the old version of software in an
             Out of Service/dryup state.  When calls on these server modules
             are sufficiently dried up, a second upgrade must be initiated by
             the user to complete the shelf upgrade.  It is important not to
             make any configuration changes until the upgrade is completed.
               
             This MIB object can only be set through the CLI, and only by a
             user with admin privileges; the default value is upgrade(1).
             "
    DEFVAL          { upgrade }
    ::= { sonusSwUpgradeServicesShelfAdmnEntry 5 }

sonusSwUpgradeServicesShelfAdmnRowstatus OBJECT-TYPE
    SYNTAX          RowStatus
    MAX-ACCESS      read-create
    STATUS          current
    DESCRIPTION     
            ""
    ::= { sonusSwUpgradeServicesShelfAdmnEntry 6 }

sonusSwUpgradeServicesShelfStatusTable OBJECT-TYPE
    SYNTAX          SEQUENCE OF SonusSwUpgradeServicesShelfStatusEntry
    MAX-ACCESS      not-accessible
    STATUS          current
    DESCRIPTION     
            "
             This table contains status information about the software upgrade 
             on a shelf.
             "
    ::= { sonusSwUpgradeServices 2 }

sonusSwUpgradeServicesShelfStatusEntry OBJECT-TYPE
    SYNTAX          SonusSwUpgradeServicesShelfStatusEntry
    MAX-ACCESS      not-accessible
    STATUS          current
    DESCRIPTION     
            ""
    INDEX           { sonusSwUpgradeServicesShelfStatusShelf }
    ::= { sonusSwUpgradeServicesShelfStatusTable 1 }

SonusSwUpgradeServicesShelfStatusEntry ::=
    SEQUENCE {
        sonusSwUpgradeServicesShelfStatusShelf      Unsigned32,
        sonusSwUpgradeServicesShelfStatusStatus       SonusSwUpgradeShelfStatStatusType,
        sonusSwUpgradeServicesShelfStatusCurrrentSlot             Unsigned32,
        sonusSwUpgradeServicesShelfStatusSlotsRemaining               Unsigned32,
        sonusSwUpgradeServicesShelfStatusGroupsRemaining                Integer32,
        sonusSwUpgradeServicesShelfStatusDuration         Counter32,
        sonusSwUpgradeServicesShelfStatusStartTime          DateAndTime,
        sonusSwUpgradeServicesShelfStatusLastExitReason               SonusSwUpgradeShelfStatLastReasonType,
        sonusSwUpgradeServicesShelfStatusLastState          SonusSoftwareUpgradeState,
        sonusSwUpgradeServicesShelfStatusCurrentState             SonusSoftwareUpgradeState,
        sonusSwUpgradeServicesShelfStatusCurrentRedundancyGroup                       Integer32
    }

sonusSwUpgradeServicesShelfStatusShelf OBJECT-TYPE
    SYNTAX          Unsigned32 (1..6)
    MAX-ACCESS      not-accessible
    STATUS          current
    DESCRIPTION     
            "
             Identifies the target shelf within the node.
             "
    ::= { sonusSwUpgradeServicesShelfStatusEntry 1 }

sonusSwUpgradeServicesShelfStatusStatus OBJECT-TYPE
    SYNTAX          SonusSwUpgradeShelfStatStatusType
    MAX-ACCESS      read-only
    STATUS          current
    DESCRIPTION     
            "
             Indicates the software upgrade status of the shelf.
             "
    ::= { sonusSwUpgradeServicesShelfStatusEntry 2 }

sonusSwUpgradeServicesShelfStatusCurrrentSlot OBJECT-TYPE
    SYNTAX          Unsigned32 (1..18)
    MAX-ACCESS      read-only
    STATUS          current
    DESCRIPTION     
            "
             Identifies the slot currently being upgraded with new software.
             "
    ::= { sonusSwUpgradeServicesShelfStatusEntry 3 }

sonusSwUpgradeServicesShelfStatusSlotsRemaining OBJECT-TYPE
    SYNTAX          Unsigned32 (1..18)
    MAX-ACCESS      read-only
    STATUS          current
    DESCRIPTION     
            "
             Identifies number of slots within the shelf remained to be upgraded.
             "
    ::= { sonusSwUpgradeServicesShelfStatusEntry 4 }

sonusSwUpgradeServicesShelfStatusGroupsRemaining OBJECT-TYPE
    SYNTAX          Integer32
    MAX-ACCESS      read-only
    STATUS          current
    DESCRIPTION     
            "
             
             "
    ::= { sonusSwUpgradeServicesShelfStatusEntry 5 }

sonusSwUpgradeServicesShelfStatusDuration OBJECT-TYPE
    SYNTAX          Counter32
    MAX-ACCESS      read-only
    STATUS          current
    DESCRIPTION     
            "
             Indicates the duration of the software upgrade in seconds.
             "
    ::= { sonusSwUpgradeServicesShelfStatusEntry 6 }

sonusSwUpgradeServicesShelfStatusStartTime OBJECT-TYPE
    SYNTAX          DateAndTime
    MAX-ACCESS      read-only
    STATUS          current
    DESCRIPTION     
            "
             Indicates the start time of the software upgrade
             "
    ::= { sonusSwUpgradeServicesShelfStatusEntry 7 }

sonusSwUpgradeServicesShelfStatusLastExitReason OBJECT-TYPE
    SYNTAX          SonusSwUpgradeShelfStatLastReasonType
    MAX-ACCESS      read-only
    STATUS          current
    DESCRIPTION     
            "
             Indicates the exit reason of the last live software upgrade.
             "
    ::= { sonusSwUpgradeServicesShelfStatusEntry 8 }

sonusSwUpgradeServicesShelfStatusLastState OBJECT-TYPE
    SYNTAX          SonusSoftwareUpgradeState
    MAX-ACCESS      read-only
    STATUS          current
    DESCRIPTION     
            "
             Indicates the last state of the LSWU FSM. (Internal use only)
             "
    ::= { sonusSwUpgradeServicesShelfStatusEntry 9 }

sonusSwUpgradeServicesShelfStatusCurrentState OBJECT-TYPE
    SYNTAX          SonusSoftwareUpgradeState
    MAX-ACCESS      read-only
    STATUS          current
    DESCRIPTION     
            "
             Indicates the current state of the LSWU FSM. (Internal use only)
             "
    ::= { sonusSwUpgradeServicesShelfStatusEntry 10 }

sonusSwUpgradeServicesShelfStatusCurrentRedundancyGroup OBJECT-TYPE
    SYNTAX          Integer32
    MAX-ACCESS      read-only
    STATUS          current
    DESCRIPTION     
            "
             Identifies the Redundancy Group Index currently being upgraded with new software.
             This is the index into the sonusRedundGroupTable MIB table.
             "
    ::= { sonusSwUpgradeServicesShelfStatusEntry 11 }

sonusSwUpgradeServicesSlotStatusTable OBJECT-TYPE
    SYNTAX          SEQUENCE OF SonusSwUpgradeServicesSlotStatusEntry
    MAX-ACCESS      not-accessible
    STATUS          current
    DESCRIPTION     
            "
             This table contains status information about the software upgrade 
             on a shelf.
             "
    ::= { sonusSwUpgradeServices 3 }

sonusSwUpgradeServicesSlotStatusEntry OBJECT-TYPE
    SYNTAX          SonusSwUpgradeServicesSlotStatusEntry
    MAX-ACCESS      not-accessible
    STATUS          current
    DESCRIPTION     
            ""
    INDEX           { sonusSwUpgradeServicesSlotStatusShelf, 
                      sonusSwUpgradeServicesSlotStatusSlot }
    ::= { sonusSwUpgradeServicesSlotStatusTable 1 }

SonusSwUpgradeServicesSlotStatusEntry ::=
    SEQUENCE {
        sonusSwUpgradeServicesSlotStatusShelf     Unsigned32,
        sonusSwUpgradeServicesSlotStatusSlot    Unsigned32,
        sonusSwUpgradeServicesSlotStatusStatus      SonusSwUpgradeSlotStatStatusType,
        sonusSwUpgradeServicesSlotStatusUpgrade       SonusSwUpgradeSlotStatUpgradeType,
        sonusSwUpgradeServicesSlotStatusVersion       SonusSwUpgradeSlotStatVersionType
    }

sonusSwUpgradeServicesSlotStatusShelf OBJECT-TYPE
    SYNTAX          Unsigned32 (1..6)
    MAX-ACCESS      not-accessible
    STATUS          current
    DESCRIPTION     
            "
             Identifies the target shelf within the node.
             "
    ::= { sonusSwUpgradeServicesSlotStatusEntry 1 }

sonusSwUpgradeServicesSlotStatusSlot OBJECT-TYPE
    SYNTAX          Unsigned32 (1..18)
    MAX-ACCESS      not-accessible
    STATUS          current
    DESCRIPTION     
            "
             Identifies the target slot within the shelf.
             "
    ::= { sonusSwUpgradeServicesSlotStatusEntry 2 }

sonusSwUpgradeServicesSlotStatusStatus OBJECT-TYPE
    SYNTAX          SonusSwUpgradeSlotStatStatusType
    MAX-ACCESS      read-only
    STATUS          current
    DESCRIPTION     
            "
             Identifies the software upgrade status of a slot.
             "
    ::= { sonusSwUpgradeServicesSlotStatusEntry 3 }

sonusSwUpgradeServicesSlotStatusUpgrade OBJECT-TYPE
    SYNTAX          SonusSwUpgradeSlotStatUpgradeType
    MAX-ACCESS      read-only
    STATUS          current
    DESCRIPTION     
            "
             
             "
    ::= { sonusSwUpgradeServicesSlotStatusEntry 4 }

sonusSwUpgradeServicesSlotStatusVersion OBJECT-TYPE
    SYNTAX          SonusSwUpgradeSlotStatVersionType
    MAX-ACCESS      read-only
    STATUS          current
    DESCRIPTION     
            "
             The software version available for upgrade on the slot.
             "
    ::= { sonusSwUpgradeServicesSlotStatusEntry 5 }

END -- end of module SONUS-GEN2-SOFTWARE-UPGRADE-SERVICES-MIB.
