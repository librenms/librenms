--
-- This SMIv2 module has been generated by smidump 0.2-cvs. Do not edit.
--

SONUS-ISDN-SERVICE-GROUP-MIB DEFINITIONS ::= BEGIN

IMPORTS
    Counter32, Integer32, MODULE-IDENTITY, NOTIFICATION-TYPE, 
    OBJECT-TYPE, Unsigned32
        FROM SNMPv2-SMI
    DisplayString, RowStatus
        FROM SNMPv2-TC
    sonusEventClass, sonusEventDescription, sonusEventLevel, 
    sonusEventTime, sonusSequenceId
        FROM SONUS-COMMON-MIB
    sonusSignallingMIBs
        FROM SONUS-SMI
    SonusAdminState, SonusName, SonusNameReference, SonusServiceState
        FROM SONUS-TC;

sonusIsdnServiceGroupMIB MODULE-IDENTITY
    LAST-UPDATED    "201208240000Z"
    ORGANIZATION    
            "Sonus Networks, Inc."
    CONTACT-INFO    
            "   Customer Support    
             Sonus Networks, Inc.
             7 Technology Park Drive
             Westford, MA 01886
             USA
             
             Tel: 978-614-8100
             Fax: 978-614-8609"
    DESCRIPTION     
            "The MIB Module for ISDN Service Group Management."
    ::= { sonusSignallingMIBs 4 }


sonusIsdnServiceGroupMIBObjects OBJECT IDENTIFIER
    ::= { sonusIsdnServiceGroupMIB 1 }

sonusIsdnsgServiceGroup OBJECT IDENTIFIER
    ::= { sonusIsdnServiceGroupMIBObjects 1 }

sonusIsdnsgServiceGroupNextIndex OBJECT-TYPE
    SYNTAX          Integer32
    MAX-ACCESS      read-only
    STATUS          current
    DESCRIPTION     
            "The next valid index to use when creating a new sonusIsdnsgServiceGroupEntry"
    ::= { sonusIsdnsgServiceGroup 1 }

sonusIsdnsgServiceGroupTable OBJECT-TYPE
    SYNTAX          SEQUENCE OF SonusIsdnsgServiceGroupEntry
    MAX-ACCESS      not-accessible
    STATUS          current
    DESCRIPTION     
            "This table contains information about each ISDN Service Group.
             
             A management entity may create rows for Service Group that are
             anticipated to be supported in the future."
    ::= { sonusIsdnsgServiceGroup 2 }

sonusIsdnsgServiceGroupEntry OBJECT-TYPE
    SYNTAX          SonusIsdnsgServiceGroupEntry
    MAX-ACCESS      not-accessible
    STATUS          current
    DESCRIPTION     
            "This table describes the ISDN Service Groups that are configured
             on the GSX9000."
    INDEX           { sonusIsdnsgServiceGroupListIndex }
    ::= { sonusIsdnsgServiceGroupTable 1 }

SonusIsdnsgServiceGroupEntry ::=
    SEQUENCE {
        sonusIsdnsgServiceGroupListIndex Integer32,
        sonusIsdnsgServiceGroupName     SonusName,
        sonusIsdnsgServiceGroupTrunkGroup SonusNameReference,
        sonusIsdnsgServiceGroupHuntAlgorithm    INTEGER,
        sonusIsdnsgServiceGroupCost     Integer32,
        sonusIsdnsgServiceGroupSwitchSide INTEGER,
        sonusIsdnsgServiceGroupSwitchType INTEGER,
        sonusIsdnsgServiceGroupSwitchProfileName        DisplayString,
        sonusIsdnsgServiceGroupOperation INTEGER,
        sonusIsdnsgServiceGroupPrimaryDchannelInterface               Integer32,
        sonusIsdnsgServiceGroupPrimaryDchannelTimeSlot              Integer32,
        sonusIsdnsgServiceGroupPrimaryDchannelMode          INTEGER,
        sonusIsdnsgServiceGroupBackupDchannelInterface              Integer32,
        sonusIsdnsgServiceGroupBackupDchannelTimeSlot             Integer32,
        sonusIsdnsgServiceGroupBackupDchannelMode         INTEGER,
        sonusIsdnsgServiceGroupLayerTrace INTEGER,
        sonusIsdnsgServiceGroupMode     SonusServiceState,
        sonusIsdnsgServiceGroupAction   INTEGER,
        sonusIsdnsgServiceGroupTimeout  Integer32,
        sonusIsdnsgServiceGroupAdminState SonusAdminState,
        sonusIsdnsgServiceGroupProfileName  DisplayString,
        sonusIsdnsgServiceGroupRowStatus RowStatus,
        sonusIsdnsgServiceGroupDefaultDirectoryNumber             DisplayString,
        sonusIsdnsgServiceGroupCallingPartyNumberProvision                  INTEGER,
        sonusIsdnsgServiceGroupCallingPartyNumberDiscard                INTEGER,
        sonusIsdnsgServiceGroupCallingPartyNumberDelivery                 INTEGER,
        sonusIsdnsgServiceGroupCallingPartySubAddressTransfer                     INTEGER,
        sonusIsdnsgServiceGroupCallingPartySubAddressDelivery                     INTEGER,
        sonusIsdnsgServiceGroupBchannelAvailabilitySignaling                    INTEGER,
        sonusIsdnsgServiceGroupVerboseTrace   INTEGER,
        sonusIsdnsgServiceGroupCallingPartyNumberPresentation                     INTEGER,
        sonusIsdnsgServiceGroupDiscTreatmentProfileName               SonusNameReference,
        sonusIsdnsgServiceGroupTonePackageName      SonusNameReference,
        sonusIsdnsgServiceGroupT302     Integer32,
        sonusIsdnsgServiceGroupT303     Integer32,
        sonusIsdnsgServiceGroupT304     Integer32,
        sonusIsdnsgServiceGroupT305     Integer32,
        sonusIsdnsgServiceGroupT306     Integer32,
        sonusIsdnsgServiceGroupT308     Integer32,
        sonusIsdnsgServiceGroupT309     Integer32,
        sonusIsdnsgServiceGroupT310     Integer32,
        sonusIsdnsgServiceGroupT312     Integer32,
        sonusIsdnsgServiceGroupT313     Integer32,
        sonusIsdnsgServiceGroupT314     Integer32,
        sonusIsdnsgServiceGroupT318     Integer32,
        sonusIsdnsgServiceGroupT319     Integer32,
        sonusIsdnsgServiceGroupT322     Integer32,
        sonusIsdnsgServiceGroupK        Integer32,
        sonusIsdnsgServiceGroupT200     Integer32,
        sonusIsdnsgServiceGroupT203     Integer32,
        sonusIsdnsgServiceGroupN200     Integer32,
        sonusIsdnsgServiceGroupN201     Integer32,
        sonusIsdnsgServiceGroupBchannelInitialRestart             INTEGER,
        sonusIsdnsgServiceGroupIuaApplicationServer           SonusNameReference,
        sonusIsdnsgServiceGroupIuaAutoDatalinkEstablish               INTEGER,
        sonusIsdnsgServiceGroupCallingPartyNameDelivery               INTEGER,
        sonusIsdnsgServiceGroupCalledPartySubAddressTransfer                    INTEGER,
        sonusIsdnsgServiceGroupCalledPartySubAddressDelivery                    INTEGER,
        sonusIsdnsgServiceGroupAlertToneName    SonusNameReference,
        sonusIsdnsgServiceGroupIsupIwfEarlyACM      INTEGER,
        sonusIsdnsgServiceGroupDiscSspProfileName         SonusNameReference,
        sonusIsdnsgServiceGroupEarlyCutThruAudibleRing              INTEGER,
        sonusIsdnsgServiceGroupEarlyCutThruNetworkInterworking                      INTEGER,
        sonusIsdnsgServiceGroupRemoteSwitchType       INTEGER,
        sonusIsdnsgServiceGroupBearerCapabilityFallback               INTEGER,
        sonusIsdnsgServiceGroupDialToneName   SonusNameReference,
        sonusIsdnsgServiceGroupTbctEnabled  INTEGER,
        sonusIsdnsgServiceGroupTbctAcknowledge      INTEGER,
        sonusIsdnsgServiceGroupTbctNotificationToTransferredUsers                         INTEGER,
        sonusIsdnsgServiceGroupTbctNotificationToController                   INTEGER,
        sonusIsdnsgServiceGroupTbctActiveLimit      Integer32,
        sonusIsdnsgServiceGroupTbctIntervalLimit        Integer32,
        sonusIsdnsgServiceGroupConfirmationToneName           SonusNameReference,
        sonusIsdnsgServiceGroupMinDigitsForQuery        Integer32,
        sonusIsdnsgServiceGroupImmediateDiscWithInbandTones                   INTEGER,
        sonusIsdnsgServiceGroupConfirmationToneOverride               INTEGER,
        sonusIsdnsgServiceGroupAnsSupervisionTimeout            Integer32,
        sonusIsdnsgServiceGroupAnsSupervisionTimeoutAction                  INTEGER,
        sonusIsdnsgServiceGroupServiceType  INTEGER,
        sonusIsdnsgServiceGroupCrankBackProfile       Integer32,
        sonusIsdnsgServiceGroupCongRelTimeout     Integer32,
        sonusIsdnsgServiceGroupGuardTimer Integer32,
        sonusIsdnsgServiceGroupCallingPartyNameReceiveTimer                   Integer32,
        sonusIsdnsgServiceGroupLdcTimeout Integer32,
        sonusIsdnsgServiceGroupLdcAction INTEGER,
        sonusIsdnsgServiceGroupLdcRelCause  Integer32,
        sonusIsdnsgServiceGroupLdcEmergencyCalls        INTEGER,
        sonusIsdnsgServiceGroupBchannelNegotiation          INTEGER,
        sonusIsdnsgServiceGroupOliDelivery  INTEGER,
        sonusIsdnsgServiceGroupSendProgressOnAcmWithCause                 INTEGER,
        sonusIsdnsgServiceGroupSkipCrankBackProfile           Unsigned32,
        sonusIsdnsgServiceGroupPrecedenceParamForwarding                INTEGER,
        sonusIsdnsgServiceGroupBillableCallForConwithNonCharge                      INTEGER,
        sonusIsdnsgServiceGroupChannelIdentification            INTEGER,
        sonusIsdnsgServiceGroupUSIUpdate INTEGER,
        sonusIsdnsgServiceGroupCauseOfNoId  INTEGER,
        sonusIsdnsgServiceGroupCRLRelCause  Integer32,
        sonusIsdnsgServiceGroupColpColrIGW  INTEGER,
        sonusIsdnsgServiceGroupTransferConnectConferenceUri                   SonusNameReference,
        sonusIsdnsgServiceGroupChanIDinAlertAndConnect              INTEGER,
        sonusIsdnsgServiceGroupT307     Integer32,
        sonusIsdnsgServiceGroupSuspendResume    INTEGER,
        sonusIsdnsgServiceGroupDisplayInRestart       DisplayString,
        sonusIsdnsgServiceGroupForwardNotify    INTEGER
    }

sonusIsdnsgServiceGroupListIndex OBJECT-TYPE
    SYNTAX          Integer32
    MAX-ACCESS      read-only
    STATUS          current
    DESCRIPTION     
            "The index of the ISDN Service Group entry."
    ::= { sonusIsdnsgServiceGroupEntry 1 }

sonusIsdnsgServiceGroupName OBJECT-TYPE
    SYNTAX          SonusName
    MAX-ACCESS      read-write
    STATUS          current
    DESCRIPTION     
            "The name of the ISDN Service Group."
    ::= { sonusIsdnsgServiceGroupEntry 2 }

sonusIsdnsgServiceGroupTrunkGroup OBJECT-TYPE
    SYNTAX          SonusNameReference
    MAX-ACCESS      read-write
    STATUS          current
    DESCRIPTION     
            "The Trunk Group, which the ISDN Service Group belongs to."
    ::= { sonusIsdnsgServiceGroupEntry 3 }

sonusIsdnsgServiceGroupHuntAlgorithm OBJECT-TYPE
    SYNTAX          INTEGER { lowlow(1), highhigh(2), circularforward(3), 
                        circularbackward(4), mostIdle(5), leastIdle(6) }
    MAX-ACCESS      read-write
    STATUS          current
    DESCRIPTION     
            "The hunting method used to select channels for calls destined
             to the Service Group destination."
    DEFVAL          { lowlow }
    ::= { sonusIsdnsgServiceGroupEntry 4 }

sonusIsdnsgServiceGroupCost OBJECT-TYPE
    SYNTAX          Integer32 (0..100)
    MAX-ACCESS      read-write
    STATUS          current
    DESCRIPTION     
            "The routing cost to the ISDN Service Group."
    DEFVAL          { 50 }
    ::= { sonusIsdnsgServiceGroupEntry 5 }

sonusIsdnsgServiceGroupSwitchSide OBJECT-TYPE
    SYNTAX          INTEGER { network(1), user(2) }
    MAX-ACCESS      read-write
    STATUS          current
    DESCRIPTION     
            "The switch side the ISDN Service Group should act as."
    DEFVAL          { network }
    ::= { sonusIsdnsgServiceGroupEntry 6 }

sonusIsdnsgServiceGroupSwitchType OBJECT-TYPE
    SYNTAX          INTEGER { ni2(1), dms250(2), dms100(3), 
                        lucent5ESS(4), lucent4ESS(5), euroIsdn(6), 
                        ins1500(7), tr41459(8) }
    MAX-ACCESS      read-write
    STATUS          current
    DESCRIPTION     
            "The network switch type where the ISDN Service Group resides."
    DEFVAL          { ni2 }
    ::= { sonusIsdnsgServiceGroupEntry 7 }

sonusIsdnsgServiceGroupSwitchProfileName OBJECT-TYPE
    SYNTAX          DisplayString (SIZE(0..23))
    MAX-ACCESS      read-write
    STATUS          current
    DESCRIPTION     
            "The ISDN Service Group switch profile name."
    ::= { sonusIsdnsgServiceGroupEntry 8 }

sonusIsdnsgServiceGroupOperation OBJECT-TYPE
    SYNTAX          INTEGER { outOfService(1), maintenance(2), 
                        inService(3), restart(4), clearStats(5), 
                        dchannelSwitchover(6), restartAllInterfaces(7) }
    MAX-ACCESS      read-write
    STATUS          current
    DESCRIPTION     
            "The operation to be applied to the the ISDN Service Group."
    ::= { sonusIsdnsgServiceGroupEntry 9 }

sonusIsdnsgServiceGroupPrimaryDchannelInterface OBJECT-TYPE
    SYNTAX          Integer32 (0..127)
    MAX-ACCESS      read-write
    STATUS          current
    DESCRIPTION     
            "The ISDN Service Group primary D-channel interface."
    DEFVAL          { 0 }
    ::= { sonusIsdnsgServiceGroupEntry 10 }

sonusIsdnsgServiceGroupPrimaryDchannelTimeSlot OBJECT-TYPE
    SYNTAX          Integer32 (1..31)
    MAX-ACCESS      read-write
    STATUS          current
    DESCRIPTION     
            "The ISDN Service Group primary D-channel time slot."
    DEFVAL          { 24 }
    ::= { sonusIsdnsgServiceGroupEntry 11 }

sonusIsdnsgServiceGroupPrimaryDchannelMode OBJECT-TYPE
    SYNTAX          INTEGER { outOfService(1), inService(2) }
    MAX-ACCESS      read-write
    STATUS          current
    DESCRIPTION     
            "The mode of operation of the primary D-channel in the ISDN Service Group."
    DEFVAL          { inService }
    ::= { sonusIsdnsgServiceGroupEntry 12 }

sonusIsdnsgServiceGroupBackupDchannelInterface OBJECT-TYPE
    SYNTAX          Integer32 (0..127)
    MAX-ACCESS      read-write
    STATUS          current
    DESCRIPTION     
            "The ISDN Service Group backup D-channel interface."
    DEFVAL          { 1 }
    ::= { sonusIsdnsgServiceGroupEntry 13 }

sonusIsdnsgServiceGroupBackupDchannelTimeSlot OBJECT-TYPE
    SYNTAX          Integer32 (1..31)
    MAX-ACCESS      read-write
    STATUS          current
    DESCRIPTION     
            "The ISDN Service Group backup D-channel time slot."
    DEFVAL          { 24 }
    ::= { sonusIsdnsgServiceGroupEntry 14 }

sonusIsdnsgServiceGroupBackupDchannelMode OBJECT-TYPE
    SYNTAX          INTEGER { outOfService(1), inService(2), 
                        unEquipped(3) }
    MAX-ACCESS      read-write
    STATUS          current
    DESCRIPTION     
            "The mode of operation of the backup D-channel in the ISDN Service Group."
    DEFVAL          { unEquipped }
    ::= { sonusIsdnsgServiceGroupEntry 15 }

sonusIsdnsgServiceGroupLayerTrace OBJECT-TYPE
    SYNTAX          INTEGER { none(1), layer2(2), layer3(3), both(4) }
    MAX-ACCESS      read-write
    STATUS          current
    DESCRIPTION     
            "Controls logging of layer events to the trace event log file."
    DEFVAL          { none }
    ::= { sonusIsdnsgServiceGroupEntry 16 }

sonusIsdnsgServiceGroupMode OBJECT-TYPE
    SYNTAX          SonusServiceState
    MAX-ACCESS      read-write
    STATUS          current
    DESCRIPTION     
            "The mode of operation of channels in the ISDN Service Group."
    DEFVAL          { inService }
    ::= { sonusIsdnsgServiceGroupEntry 17 }

sonusIsdnsgServiceGroupAction OBJECT-TYPE
    SYNTAX          INTEGER { dryUp(1), force(2) }
    MAX-ACCESS      read-write
    STATUS          current
    DESCRIPTION     
            "The action taken on the channels in the ISDN Service Group when sonusIsdnsgServiceGroupMode
             is set to out of service. This object should only be set in conjunction with sonusIsdnsgServiceGroupMode."
    ::= { sonusIsdnsgServiceGroupEntry 18 }

sonusIsdnsgServiceGroupTimeout OBJECT-TYPE
    SYNTAX          Integer32 (1..1440)
    MAX-ACCESS      read-write
    STATUS          current
    DESCRIPTION     
            "The timeout value in minutes for dryup action on the ISDN Service Group.
             This object should only be set in conjunction with sonusIsdnsgServiceGroupAction, 
             when sonusIsdnsgServiceGroupAction is set to dryUp."
    ::= { sonusIsdnsgServiceGroupEntry 19 }

sonusIsdnsgServiceGroupAdminState OBJECT-TYPE
    SYNTAX          SonusAdminState
    MAX-ACCESS      read-write
    STATUS          current
    DESCRIPTION     
            "The admin state of the ISDN Service Group."
    DEFVAL          { disabled }
    ::= { sonusIsdnsgServiceGroupEntry 20 }

sonusIsdnsgServiceGroupProfileName OBJECT-TYPE
    SYNTAX          DisplayString (SIZE(0..23))
    MAX-ACCESS      read-write
    STATUS          current
    DESCRIPTION     
            "The ISDN Service Group profile name."
    ::= { sonusIsdnsgServiceGroupEntry 21 }

sonusIsdnsgServiceGroupRowStatus OBJECT-TYPE
    SYNTAX          RowStatus
    MAX-ACCESS      read-write
    STATUS          current
    DESCRIPTION     
            ""
    ::= { sonusIsdnsgServiceGroupEntry 22 }

sonusIsdnsgServiceGroupDefaultDirectoryNumber OBJECT-TYPE
    SYNTAX          DisplayString (SIZE(0..30))
    MAX-ACCESS      read-write
    STATUS          current
    DESCRIPTION     
            "Default Directory number for the ISDN Service Group."
    ::= { sonusIsdnsgServiceGroupEntry 23 }

sonusIsdnsgServiceGroupCallingPartyNumberProvision OBJECT-TYPE
    SYNTAX          INTEGER { necessary(1), notNecessary(2) }
    MAX-ACCESS      read-write
    STATUS          current
    DESCRIPTION     
            "Specifies wether the Calling Party Number is required in the incoming SETUP."
    DEFVAL          { notNecessary }
    ::= { sonusIsdnsgServiceGroupEntry 24 }

sonusIsdnsgServiceGroupCallingPartyNumberDiscard OBJECT-TYPE
    SYNTAX          INTEGER { yes(1), no(2), rdns(3), rdn2(4) }
    MAX-ACCESS      read-write
    STATUS          current
    DESCRIPTION     
            "Controls discard of Calling Party Number and Redirecting Numbers.
             yes:		discard all
             no:			discard none
             rdns:		discard redirecting numbers
             rdn2:		discard second redirecting number"
    DEFVAL          { no }
    ::= { sonusIsdnsgServiceGroupEntry 25 }

sonusIsdnsgServiceGroupCallingPartyNumberDelivery OBJECT-TYPE
    SYNTAX          INTEGER { yes(1), no(2), cpnonly(3), cpn1rdn(4), 
                        conditional(5) }
    MAX-ACCESS      read-write
    STATUS          current
    DESCRIPTION     
            "Controls the delivery of the Calling Party Number and Redirecting Numbers.
             yes:		deliver all
             no:			deliver none
             cpnonly:	deliver CPN and no RDNs
             cpn1rdn:	deliver CPN and one RDN. Please be aware the routing attribute to exclude delivery
             of the redirecting number could override this parameter. 
             conditional:deliver CPN and RDNs based on routing attributes. NOTE: 
             When sonusIsdnsgServiceGroupCallingPartyNumberDelivery is set to conditional, this value
             overrides the sonusIsdnsgServiceGroupCallingPartyNumberDiscard setting. "
    DEFVAL          { yes }
    ::= { sonusIsdnsgServiceGroupEntry 26 }

sonusIsdnsgServiceGroupCallingPartySubAddressTransfer OBJECT-TYPE
    SYNTAX          INTEGER { yes(1), no(2), conditional(3) }
    MAX-ACCESS      read-write
    STATUS          current
    DESCRIPTION     
            "Controls the transfer of the Calling Party Subaddress Information Element"
    DEFVAL          { yes }
    ::= { sonusIsdnsgServiceGroupEntry 27 }

sonusIsdnsgServiceGroupCallingPartySubAddressDelivery OBJECT-TYPE
    SYNTAX          INTEGER { yes(1), no(2), conditional(3) }
    MAX-ACCESS      read-write
    STATUS          current
    DESCRIPTION     
            "Controls the delivery of the Calling Party Subaddress Information Element to the CPE"
    DEFVAL          { yes }
    ::= { sonusIsdnsgServiceGroupEntry 28 }

sonusIsdnsgServiceGroupBchannelAvailabilitySignaling OBJECT-TYPE
    SYNTAX          INTEGER { yes(1), no(2) }
    MAX-ACCESS      read-write
    STATUS          current
    DESCRIPTION     
            "Used to enable or disable the B-channel availability signaling procedures"
    DEFVAL          { yes }
    ::= { sonusIsdnsgServiceGroupEntry 29 }

sonusIsdnsgServiceGroupVerboseTrace OBJECT-TYPE
    SYNTAX          INTEGER { off(1), on(2) }
    MAX-ACCESS      read-write
    STATUS          current
    DESCRIPTION     
            "Controls verbose mode in the logging of layer events to the trace event log file."
    DEFVAL          { on }
    ::= { sonusIsdnsgServiceGroupEntry 30 }

sonusIsdnsgServiceGroupCallingPartyNumberPresentation OBJECT-TYPE
    SYNTAX          INTEGER { yes(1), no(2) }
    MAX-ACCESS      read-write
    STATUS          current
    DESCRIPTION     
            "Used as Calling Party Number presentation indicator when none available in incoming SETUP."
    DEFVAL          { yes }
    ::= { sonusIsdnsgServiceGroupEntry 31 }

sonusIsdnsgServiceGroupDiscTreatmentProfileName OBJECT-TYPE
    SYNTAX          SonusNameReference
    MAX-ACCESS      read-write
    STATUS          current
    DESCRIPTION     
            "The disconnect treatment profile to be used for this service."
    ::= { sonusIsdnsgServiceGroupEntry 32 }

sonusIsdnsgServiceGroupTonePackageName OBJECT-TYPE
    SYNTAX          SonusNameReference
    MAX-ACCESS      read-write
    STATUS          current
    DESCRIPTION     
            "The tone package to be used for this service."
    ::= { sonusIsdnsgServiceGroupEntry 33 }

sonusIsdnsgServiceGroupT302 OBJECT-TYPE
    SYNTAX          Integer32 (0..127)
    MAX-ACCESS      read-only
    STATUS          current
    DESCRIPTION     
            "This T302 of Q.931 timer is used for both user and network sides."
    DEFVAL          { 15 }
    ::= { sonusIsdnsgServiceGroupEntry 34 }

sonusIsdnsgServiceGroupT303 OBJECT-TYPE
    SYNTAX          Integer32 (0..127)
    MAX-ACCESS      read-only
    STATUS          current
    DESCRIPTION     
            "This T303 of Q.931 timer is used for both user and network sides."
    DEFVAL          { 4 }
    ::= { sonusIsdnsgServiceGroupEntry 35 }

sonusIsdnsgServiceGroupT304 OBJECT-TYPE
    SYNTAX          Integer32 (0..127)
    MAX-ACCESS      read-only
    STATUS          current
    DESCRIPTION     
            "This T304 of Q.931 timer is used for both user and network sides."
    DEFVAL          { 30 }
    ::= { sonusIsdnsgServiceGroupEntry 36 }

sonusIsdnsgServiceGroupT305 OBJECT-TYPE
    SYNTAX          Integer32 (0..127)
    MAX-ACCESS      read-only
    STATUS          current
    DESCRIPTION     
            "This T305 of Q.931 timer is used for both user and network sides."
    DEFVAL          { 30 }
    ::= { sonusIsdnsgServiceGroupEntry 37 }

sonusIsdnsgServiceGroupT306 OBJECT-TYPE
    SYNTAX          Integer32 (0..127)
    MAX-ACCESS      read-only
    STATUS          current
    DESCRIPTION     
            "This T306 of Q.931 timer is used for network side only."
    DEFVAL          { 30 }
    ::= { sonusIsdnsgServiceGroupEntry 38 }

sonusIsdnsgServiceGroupT308 OBJECT-TYPE
    SYNTAX          Integer32 (0..127)
    MAX-ACCESS      read-only
    STATUS          current
    DESCRIPTION     
            "This T308 of Q.931 timer is used for both user and network sides."
    DEFVAL          { 4 }
    ::= { sonusIsdnsgServiceGroupEntry 39 }

sonusIsdnsgServiceGroupT309 OBJECT-TYPE
    SYNTAX          Integer32 (0..127)
    MAX-ACCESS      read-only
    STATUS          current
    DESCRIPTION     
            "This T309 of Q.931 timer is used for both user and network sides."
    DEFVAL          { 90 }
    ::= { sonusIsdnsgServiceGroupEntry 40 }

sonusIsdnsgServiceGroupT310 OBJECT-TYPE
    SYNTAX          Integer32 (0..127)
    MAX-ACCESS      read-only
    STATUS          current
    DESCRIPTION     
            "This T310 of Q.931 timer is used for both user and network sides."
    DEFVAL          { 15 }
    ::= { sonusIsdnsgServiceGroupEntry 41 }

sonusIsdnsgServiceGroupT312 OBJECT-TYPE
    SYNTAX          Integer32 (0..127)
    MAX-ACCESS      read-only
    STATUS          current
    DESCRIPTION     
            "This T312 of Q.931 timer is used for network side only."
    DEFVAL          { 6 }
    ::= { sonusIsdnsgServiceGroupEntry 42 }

sonusIsdnsgServiceGroupT313 OBJECT-TYPE
    SYNTAX          Integer32 (0..127)
    MAX-ACCESS      read-only
    STATUS          current
    DESCRIPTION     
            "This T313 of Q.931 timer is used for user side only."
    DEFVAL          { 4 }
    ::= { sonusIsdnsgServiceGroupEntry 43 }

sonusIsdnsgServiceGroupT314 OBJECT-TYPE
    SYNTAX          Integer32 (0..127)
    MAX-ACCESS      read-only
    STATUS          current
    DESCRIPTION     
            "This T314 of Q.931 timer is used for both user and network sides"
    DEFVAL          { 4 }
    ::= { sonusIsdnsgServiceGroupEntry 44 }

sonusIsdnsgServiceGroupT318 OBJECT-TYPE
    SYNTAX          Integer32 (0..127)
    MAX-ACCESS      read-only
    STATUS          current
    DESCRIPTION     
            "This T318 of Q.931 timer is used for user side only."
    DEFVAL          { 4 }
    ::= { sonusIsdnsgServiceGroupEntry 45 }

sonusIsdnsgServiceGroupT319 OBJECT-TYPE
    SYNTAX          Integer32 (0..127)
    MAX-ACCESS      read-only
    STATUS          current
    DESCRIPTION     
            "This T319 of Q.931 timer is used for user side only."
    DEFVAL          { 4 }
    ::= { sonusIsdnsgServiceGroupEntry 46 }

sonusIsdnsgServiceGroupT322 OBJECT-TYPE
    SYNTAX          Integer32 (0..127)
    MAX-ACCESS      read-only
    STATUS          current
    DESCRIPTION     
            "This T322 of Q.931 timer is used for network side only."
    DEFVAL          { 4 }
    ::= { sonusIsdnsgServiceGroupEntry 47 }

sonusIsdnsgServiceGroupK OBJECT-TYPE
    SYNTAX          Integer32 (1..127)
    MAX-ACCESS      read-only
    STATUS          current
    DESCRIPTION     
            "The maximum number of outstanding I frames. This K of Q.921 parameter is used for both user and network sides."
    DEFVAL          { 7 }
    ::= { sonusIsdnsgServiceGroupEntry 48 }

sonusIsdnsgServiceGroupT200 OBJECT-TYPE
    SYNTAX          Integer32 (1..255)
    MAX-ACCESS      read-only
    STATUS          current
    DESCRIPTION     
            "This T200 of Q.921 timer is used for both user and network sides."
    DEFVAL          { 1 }
    ::= { sonusIsdnsgServiceGroupEntry 49 }

sonusIsdnsgServiceGroupT203 OBJECT-TYPE
    SYNTAX          Integer32 (0..255)
    MAX-ACCESS      read-only
    STATUS          current
    DESCRIPTION     
            "This T203 of Q.921 timer is used for both user and network sides."
    DEFVAL          { 0 }
    ::= { sonusIsdnsgServiceGroupEntry 50 }

sonusIsdnsgServiceGroupN200 OBJECT-TYPE
    SYNTAX          Integer32 (1..100)
    MAX-ACCESS      read-only
    STATUS          current
    DESCRIPTION     
            "The maximum number of retransmissions of a frame. This N200 of Q.921 parameter is used for both user and network sides."
    DEFVAL          { 3 }
    ::= { sonusIsdnsgServiceGroupEntry 51 }

sonusIsdnsgServiceGroupN201 OBJECT-TYPE
    SYNTAX          Integer32 (1..260)
    MAX-ACCESS      read-only
    STATUS          current
    DESCRIPTION     
            "The maximum number of octets in an information field. This N201 of Q.921 parameter is used for both user and network sides."
    DEFVAL          { 260 }
    ::= { sonusIsdnsgServiceGroupEntry 52 }

sonusIsdnsgServiceGroupBchannelInitialRestart OBJECT-TYPE
    SYNTAX          INTEGER { yes(1), no(2), allInterfaces(3) }
    MAX-ACCESS      read-write
    STATUS          current
    DESCRIPTION     
            "Controls wether RESTARTs are used to initially bring channels into service"
    DEFVAL          { yes }
    ::= { sonusIsdnsgServiceGroupEntry 53 }

sonusIsdnsgServiceGroupIuaApplicationServer OBJECT-TYPE
    SYNTAX          SonusNameReference
    MAX-ACCESS      read-write
    STATUS          current
    DESCRIPTION     
            "IUA Application server to which this D-channel belongs to"
    ::= { sonusIsdnsgServiceGroupEntry 54 }

sonusIsdnsgServiceGroupIuaAutoDatalinkEstablish OBJECT-TYPE
    SYNTAX          INTEGER { yes(1), no(2) }
    MAX-ACCESS      read-write
    STATUS          current
    DESCRIPTION     
            "Controls automatic datalink establishment upon IUA application server activation"
    DEFVAL          { no }
    ::= { sonusIsdnsgServiceGroupEntry 55 }

sonusIsdnsgServiceGroupCallingPartyNameDelivery OBJECT-TYPE
    SYNTAX          INTEGER { yes(1), no(2), alerting(3), answered(4), 
                        callproc(5), displayIeOfSetup(6) }
    MAX-ACCESS      read-write
    STATUS          current
    DESCRIPTION     
            "Controls the delivery of the Calling Party Name.
             yes:		in FACILITY IE of SETUP message
             no:			not delivered
             callproc:	after the CALLPROC message
             alerting:	after the ALERTING message
             answered:	after the CONNECT
             displayIeOfSetup    in DISPLAY IE of SETUP message"
    DEFVAL          { no }
    ::= { sonusIsdnsgServiceGroupEntry 56 }

sonusIsdnsgServiceGroupCalledPartySubAddressTransfer OBJECT-TYPE
    SYNTAX          INTEGER { yes(1), no(2), conditional(3) }
    MAX-ACCESS      read-write
    STATUS          current
    DESCRIPTION     
            "Controls the transfer of the Called Party Subaddress Information Element"
    DEFVAL          { yes }
    ::= { sonusIsdnsgServiceGroupEntry 57 }

sonusIsdnsgServiceGroupCalledPartySubAddressDelivery OBJECT-TYPE
    SYNTAX          INTEGER { yes(1), no(2), conditional(3) }
    MAX-ACCESS      read-write
    STATUS          current
    DESCRIPTION     
            "Controls the delivery of the Called Party Subaddress Information Element to the CPE"
    DEFVAL          { yes }
    ::= { sonusIsdnsgServiceGroupEntry 58 }

sonusIsdnsgServiceGroupAlertToneName OBJECT-TYPE
    SYNTAX          SonusNameReference
    MAX-ACCESS      read-write
    STATUS          obsolete
    DESCRIPTION     
            "Specifies a named reference to a tone to play for ring back.
             This object is not used and was made obsolete in GSX
             release 6.0. Local Ring Back Tone Configuration has
             now moved to PSX."
    ::= { sonusIsdnsgServiceGroupEntry 59 }

sonusIsdnsgServiceGroupIsupIwfEarlyACM OBJECT-TYPE
    SYNTAX          INTEGER { yes(1), no(2) }
    MAX-ACCESS      read-write
    STATUS          current
    DESCRIPTION     
            "It is used to trigger ealy ACM or not when ISDNSG received
             a establish request from CC with edage SG is ISUP."
    DEFVAL          { no }
    ::= { sonusIsdnsgServiceGroupEntry 60 }

sonusIsdnsgServiceGroupDiscSspProfileName OBJECT-TYPE
    SYNTAX          SonusNameReference
    MAX-ACCESS      read-write
    STATUS          current
    DESCRIPTION     
            "The disconnect SSP profile to be used for this service."
    ::= { sonusIsdnsgServiceGroupEntry 61 }

sonusIsdnsgServiceGroupEarlyCutThruAudibleRing OBJECT-TYPE
    SYNTAX          INTEGER { yes(1), no(2), twoway(3) }
    MAX-ACCESS      read-write
    STATUS          current
    DESCRIPTION     
            "When enabled, early cut thru occurs on the reception of an ALERT message
             or a progress indicator #8 (inband information or appropriate pattern now available)."
    DEFVAL          { yes }
    ::= { sonusIsdnsgServiceGroupEntry 62 }

sonusIsdnsgServiceGroupEarlyCutThruNetworkInterworking OBJECT-TYPE
    SYNTAX          INTEGER { yes(1), no(2), twoway(3) }
    MAX-ACCESS      read-write
    STATUS          current
    DESCRIPTION     
            "When enabled, early cut thru occurs on the reception of a progress indicator #1
             (call is not end-to-end ISDN; further call progress information may be available inband)."
    DEFVAL          { yes }
    ::= { sonusIsdnsgServiceGroupEntry 63 }

sonusIsdnsgServiceGroupRemoteSwitchType OBJECT-TYPE
    SYNTAX          INTEGER { default(1), meridian(2), ocnrn(3), 
                        ocnrnpresentation(4), custommap(5), 
                        cpnrestrictedoverride(6), pi8inalert(7), 
                        noinbandinfo(8), atttcs(9), noprogafteralert(10) }
    MAX-ACCESS      read-write
    STATUS          current
    DESCRIPTION     
            "The remote switch type.  This should only be set to something other 
             than default if the remote switch type has unique behavior.  Currently, 
             the unique behaviors are:
                meridian: 
                    The Meridian PBX incorrectly rejects the Channel ID information
                    element when the extension bit is set correctly.  When this
                    object is set to meridian, the extension bit will not be 
                    set in the Channel ID information element.
             			ocnrn:
             				For 4ess and 5ess switch types, support both the Original
             				Called Number IE and the Redirecting Number IE.
             			ocnrnpresentation
             				Forces number presentation for the Original Called Number
             				IE and the Redirecting Number IE.  
             			custommap
             				Forces number presentation for the Original Called Number
             				IE and the Redirecting Number IE.  Also sends a DISCONNECT
             				instead of a PROGRESS with a cause IE.
                     cpn_restricted_override:
             				For INS1500 switch type. Present the calling number when
             				presentation is restricted. This option leaves the presentation
             				indication as restricted. This option cannot be used if 
             				the PSX option FORCED CLIP is enabled.
             			pi8inalert:
             				Allow progress indicator #8 in ALERT message.
             				This affects all switch types.
             			noinbandinfo:
             				Prohibit progress indicator #8 in ALERT message.
             				Prohibit progress indicator #1 and #8 in PROGRESS message.
             				This affects all switch types.
             			atttcs
             				Support AT&T Transfer Connect Service.  Enables interworking
             				of the FACILITY message, Network Specific Facility IE and
             				MAUUI.
             			noprogafteralert
             				For user side, avoid sending PROGRESS message after an ALERT."
    DEFVAL          { default }
    ::= { sonusIsdnsgServiceGroupEntry 64 }

sonusIsdnsgServiceGroupBearerCapabilityFallback OBJECT-TYPE
    SYNTAX          INTEGER { yes(1), no(2) }
    MAX-ACCESS      read-write
    STATUS          current
    DESCRIPTION     
            "Enables bearer capability fall back."
    DEFVAL          { no }
    ::= { sonusIsdnsgServiceGroupEntry 65 }

sonusIsdnsgServiceGroupDialToneName OBJECT-TYPE
    SYNTAX          SonusNameReference
    MAX-ACCESS      read-write
    STATUS          current
    DESCRIPTION     
            "Specifies a named reference to a tone to play for dial tone."
    ::= { sonusIsdnsgServiceGroupEntry 66 }

sonusIsdnsgServiceGroupTbctEnabled OBJECT-TYPE
    SYNTAX          INTEGER { yes(1), no(2) }
    MAX-ACCESS      read-write
    STATUS          current
    DESCRIPTION     
            "Enables Two B-channel Transfer."
    DEFVAL          { no }
    ::= { sonusIsdnsgServiceGroupEntry 67 }

sonusIsdnsgServiceGroupTbctAcknowledge OBJECT-TYPE
    SYNTAX          INTEGER { facility(1), disconnect(2) }
    MAX-ACCESS      read-write
    STATUS          current
    DESCRIPTION     
            "Controls whether a succesfull transfer request should be acknowledged 
             as a part of the DISCONNECT message or with its own FACILITY message."
    DEFVAL          { facility }
    ::= { sonusIsdnsgServiceGroupEntry 68 }

sonusIsdnsgServiceGroupTbctNotificationToTransferredUsers OBJECT-TYPE
    SYNTAX          INTEGER { yes(1), no(2) }
    MAX-ACCESS      read-write
    STATUS          current
    DESCRIPTION     
            "Enables Notifications to the transferred users."
    DEFVAL          { no }
    ::= { sonusIsdnsgServiceGroupEntry 69 }

sonusIsdnsgServiceGroupTbctNotificationToController OBJECT-TYPE
    SYNTAX          INTEGER { yes(1), no(2) }
    MAX-ACCESS      read-write
    STATUS          current
    DESCRIPTION     
            "Enables notification to the controller.  This includes notification of
             the number of active (and available, if applicable) transfers, and
             notification of clearing of a transferred call."
    DEFVAL          { yes }
    ::= { sonusIsdnsgServiceGroupEntry 70 }

sonusIsdnsgServiceGroupTbctActiveLimit OBJECT-TYPE
    SYNTAX          Integer32 (0..60000)
    MAX-ACCESS      read-write
    STATUS          current
    DESCRIPTION     
            "Allows limiting the number of active transfers associated with this ISDN
             service.  The value 0 disables the limiting mechanism."
    DEFVAL          { 100 }
    ::= { sonusIsdnsgServiceGroupEntry 71 }

sonusIsdnsgServiceGroupTbctIntervalLimit OBJECT-TYPE
    SYNTAX          Integer32 (0..500)
    MAX-ACCESS      read-write
    STATUS          current
    DESCRIPTION     
            "Allows limiting the number of transfer requests per 10 second interval
             The value 0 disables the limiting mechanism."
    DEFVAL          { 10 }
    ::= { sonusIsdnsgServiceGroupEntry 72 }

sonusIsdnsgServiceGroupConfirmationToneName OBJECT-TYPE
    SYNTAX          SonusNameReference
    MAX-ACCESS      read-write
    STATUS          current
    DESCRIPTION     
            "Specifies a named reference to a tone to play for confirmation tone."
    ::= { sonusIsdnsgServiceGroupEntry 73 }

sonusIsdnsgServiceGroupMinDigitsForQuery OBJECT-TYPE
    SYNTAX          Integer32 (0..30)
    MAX-ACCESS      read-write
    STATUS          current
    DESCRIPTION     
            "If Overlap Receiving is supported and CalledAddress
             received is not complete, then minimum number of
             CalledAddress Digits to receive before we go for Route
             Query."
    DEFVAL          { 0 }
    ::= { sonusIsdnsgServiceGroupEntry 74 }

sonusIsdnsgServiceGroupImmediateDiscWithInbandTones OBJECT-TYPE
    SYNTAX          INTEGER { disabled(1), enabled(2), establishing(3), 
                        allstates(4) }
    MAX-ACCESS      read-write
    STATUS          current
    DESCRIPTION     
            "When a DISCONNECT with inband tones is recieved, to maintain
             the voicepath a PROGRESS is propagated.  This parameter causes
             an immediate disconnect instead.  The options are explaned below.
             	disabled:		maintain voice path
             	enabled:		immediate disconnect in stable states
             	establishing	immediate disconnect in establishing states
             	allstates		immediate disconnect in all states"
    DEFVAL          { disabled }
    ::= { sonusIsdnsgServiceGroupEntry 75 }

sonusIsdnsgServiceGroupConfirmationToneOverride OBJECT-TYPE
    SYNTAX          INTEGER { disabled(1), enabled(2) }
    MAX-ACCESS      read-write
    STATUS          current
    DESCRIPTION     
            "If supported, informs CC to play a C-Tone for all
             calls using this service group.  If unsupported, 
             informs CC to use the enable flag from the PSX to
             decide whether or not to play a C-Tone."
    DEFVAL          { disabled }
    ::= { sonusIsdnsgServiceGroupEntry 76 }

sonusIsdnsgServiceGroupAnsSupervisionTimeout OBJECT-TYPE
    SYNTAX          Integer32 (0..1000)
    MAX-ACCESS      read-write
    STATUS          current
    DESCRIPTION     
            "This is the time from egress call setup to egress receiving an answer,
             used for both user and network sides."
    DEFVAL          { 300 }
    ::= { sonusIsdnsgServiceGroupEntry 77 }

sonusIsdnsgServiceGroupAnsSupervisionTimeoutAction OBJECT-TYPE
    SYNTAX          INTEGER { release(1), softanswer(2), 
                        trapAndRestart(3) }
    MAX-ACCESS      read-write
    STATUS          current
    DESCRIPTION     
            "This is the action to take if the answer supervision timer
             expires.  The call may be released, assumed to be answered or
             a trap can be fired and the timer restarted."
    DEFVAL          { release }
    ::= { sonusIsdnsgServiceGroupEntry 78 }

sonusIsdnsgServiceGroupServiceType OBJECT-TYPE
    SYNTAX          INTEGER { default(1), dchannel(2), bchannel(3) }
    MAX-ACCESS      read-write
    STATUS          current
    DESCRIPTION     
            "The default service is used for the classic PRI or NFAS group.  
             A dchannel service controls a D-channel.  A bchannel service manages
             a subset of B-channels."
    DEFVAL          { default }
    ::= { sonusIsdnsgServiceGroupEntry 80 }

sonusIsdnsgServiceGroupCrankBackProfile OBJECT-TYPE
    SYNTAX          Integer32 (1..20)
    MAX-ACCESS      read-write
    STATUS          current
    DESCRIPTION     
            "The Crankback Profile to be used for this service."
    DEFVAL          { 1 }
    ::= { sonusIsdnsgServiceGroupEntry 81 }

sonusIsdnsgServiceGroupCongRelTimeout OBJECT-TYPE
    SYNTAX          Integer32 (0..5)
    MAX-ACCESS      read-write
    STATUS          current
    DESCRIPTION     
            "Time to delay sending of release during congestion."
    DEFVAL          { 0 }
    ::= { sonusIsdnsgServiceGroupEntry 82 }

sonusIsdnsgServiceGroupGuardTimer OBJECT-TYPE
    SYNTAX          Integer32 (0..9999)
    MAX-ACCESS      read-write
    STATUS          current
    DESCRIPTION     
            "Time out in milliseconds before a channel can be re-hunted."
    DEFVAL          { 0 }
    ::= { sonusIsdnsgServiceGroupEntry 83 }

sonusIsdnsgServiceGroupCallingPartyNameReceiveTimer OBJECT-TYPE
    SYNTAX          Integer32 (0..3600)
    MAX-ACCESS      read-write
    STATUS          current
    DESCRIPTION     
            "Time out in milliseconds to wait to receive the Calling Party Name."
    DEFVAL          { 0 }
    ::= { sonusIsdnsgServiceGroupEntry 84 }

sonusIsdnsgServiceGroupLdcTimeout OBJECT-TYPE
    SYNTAX          Integer32 (0..2880)
    MAX-ACCESS      read-write
    STATUS          current
    DESCRIPTION     
            "The timeout value of the long duration call timer in minutes.
             Allowed values are 0 to disable the timer, 60-2880 minutes to set the timer."
    DEFVAL          { 0 }
    ::= { sonusIsdnsgServiceGroupEntry 85 }

sonusIsdnsgServiceGroupLdcAction OBJECT-TYPE
    SYNTAX          INTEGER { noAction(0), trap(1), release(2), 
                        trapAndRelease(3) }
    MAX-ACCESS      read-write
    STATUS          current
    DESCRIPTION     
            "This is the action to take if the long duration call timer
             expires.  The call may be released or a trap fired, or both."
    DEFVAL          { noAction }
    ::= { sonusIsdnsgServiceGroupEntry 86 }

sonusIsdnsgServiceGroupLdcRelCause OBJECT-TYPE
    SYNTAX          Integer32 (1..127)
    MAX-ACCESS      read-write
    STATUS          current
    DESCRIPTION     
            "The Q.850 release value to use should the call be released 
             due to long duration call timer expiry"
    DEFVAL          { 41 }
    ::= { sonusIsdnsgServiceGroupEntry 87 }

sonusIsdnsgServiceGroupLdcEmergencyCalls OBJECT-TYPE
    SYNTAX          INTEGER { include(0), exclude(1) }
    MAX-ACCESS      read-write
    STATUS          current
    DESCRIPTION     
            "Whether Emergency Calls should be exluded from 
             or included in Long Duration Call disconnect procedures"
    DEFVAL          { exclude }
    ::= { sonusIsdnsgServiceGroupEntry 88 }

sonusIsdnsgServiceGroupBchannelNegotiation OBJECT-TYPE
    SYNTAX          INTEGER { yes(1), no(2) }
    MAX-ACCESS      read-write
    STATUS          current
    DESCRIPTION     
            "Used to enable or disable the B-channel negotiation signaling procedures"
    DEFVAL          { yes }
    ::= { sonusIsdnsgServiceGroupEntry 89 }

sonusIsdnsgServiceGroupOliDelivery OBJECT-TYPE
    SYNTAX          INTEGER { yes(1), no(2) }
    MAX-ACCESS      read-write
    STATUS          current
    DESCRIPTION     
            "The configures whether the ISDN switch type delivers (or transfers on user side) the originating line information."
    DEFVAL          { yes }
    ::= { sonusIsdnsgServiceGroupEntry 90 }

sonusIsdnsgServiceGroupSendProgressOnAcmWithCause OBJECT-TYPE
    SYNTAX          INTEGER { yes(1), no(2) }
    MAX-ACCESS      read-write
    STATUS          current
    DESCRIPTION     
            "Whether Progress or Disconnect should be sent on 
             receiving an ACM/Alerting with Cause indicators"
    DEFVAL          { no }
    ::= { sonusIsdnsgServiceGroupEntry 91 }

sonusIsdnsgServiceGroupSkipCrankBackProfile OBJECT-TYPE
    SYNTAX          Unsigned32 (0..20)
    MAX-ACCESS      read-write
    STATUS          current
    DESCRIPTION     
            "The Skip Crankback Profile to be used for this service."
    DEFVAL          { 0 }
    ::= { sonusIsdnsgServiceGroupEntry 92 }

sonusIsdnsgServiceGroupPrecedenceParamForwarding OBJECT-TYPE
    SYNTAX          INTEGER { disabled(1), enabled(2) }
    MAX-ACCESS      read-write
    STATUS          current
    DESCRIPTION     
            "This enables and disables precedence parameter forwarding
             on this service group."
    DEFVAL          { disabled }
    ::= { sonusIsdnsgServiceGroupEntry 93 }

sonusIsdnsgServiceGroupBillableCallForConwithNonCharge OBJECT-TYPE
    SYNTAX          INTEGER { supported(0), unsupported(1) }
    MAX-ACCESS      read-write
    STATUS          current
    DESCRIPTION     
            "This parameter is used to send CONNECT message when a CON message with 
             Charge Indicator set to Non-Charge (i.e. other than Charge) is received.
             			If this parameter is set to UNSUPPORTED, then PROGRESS message will be sent."
    DEFVAL          { supported }
    ::= { sonusIsdnsgServiceGroupEntry 94 }

sonusIsdnsgServiceGroupChannelIdentification OBJECT-TYPE
    SYNTAX          INTEGER { channelNumber(0), slotMap(1) }
    MAX-ACCESS      read-write
    STATUS          current
    DESCRIPTION     
            "Identifies the type of channel present in the Channel Identification 
             Information Element.  It can be either Channel Number or Slot Map"
    DEFVAL          { channelNumber }
    ::= { sonusIsdnsgServiceGroupEntry 95 }

sonusIsdnsgServiceGroupUSIUpdate OBJECT-TYPE
    SYNTAX          INTEGER { supported(0), unsupported(1) }
    MAX-ACCESS      read-write
    STATUS          current
    DESCRIPTION     
            "Is the modification of Information Transfer Capability and User Information Layer1
             present in USI IE supported for the ISUP Signaling Profile.  Map 1001 value in ITC 
             to 01000 in ISDN SETUP.  Map A-Law in User Information Layer1 to M-Law in Bearer 
             Capability Parameter of ISDN SETUP. "
    DEFVAL          { unsupported }
    ::= { sonusIsdnsgServiceGroupEntry 96 }

sonusIsdnsgServiceGroupCauseOfNoId OBJECT-TYPE
    SYNTAX          INTEGER { supported(0), unsupported(1) }
    MAX-ACCESS      read-write
    STATUS          current
    DESCRIPTION     
            "This parameter is used to send Cause of No Id parameter in facility IE of SETUP
             message on egress ISDN side "
    DEFVAL          { unsupported }
    ::= { sonusIsdnsgServiceGroupEntry 97 }

sonusIsdnsgServiceGroupCRLRelCause OBJECT-TYPE
    SYNTAX          Integer32 (1..127)
    MAX-ACCESS      read-write
    STATUS          current
    DESCRIPTION     
            "The Q.850 release value to use should the call be released 
             due to call rate limiting"
    DEFVAL          { 42 }
    ::= { sonusIsdnsgServiceGroupEntry 98 }

sonusIsdnsgServiceGroupColpColrIGW OBJECT-TYPE
    SYNTAX          INTEGER { yes(1), no(2) }
    MAX-ACCESS      read-write
    STATUS          current
    DESCRIPTION     
            "It is used to trigger colp colr IGW functionality or not when ISDNSG received
             a CONNECTED Number."
    DEFVAL          { no }
    ::= { sonusIsdnsgServiceGroupEntry 99 }

sonusIsdnsgServiceGroupTransferConnectConferenceUri OBJECT-TYPE
    SYNTAX          SonusNameReference
    MAX-ACCESS      read-write
    STATUS          current
    DESCRIPTION     
            "Specifies a named reference to Conference URI for Transfer Connect feature."
    ::= { sonusIsdnsgServiceGroupEntry 100 }

sonusIsdnsgServiceGroupChanIDinAlertAndConnect OBJECT-TYPE
    SYNTAX          INTEGER { supported(0), unsupported(1) }
    MAX-ACCESS      read-write
    STATUS          current
    DESCRIPTION     
            "This is used to determine if Channel ID will be sent in ALERT and CONNECT messages "
    DEFVAL          { unsupported }
    ::= { sonusIsdnsgServiceGroupEntry 101 }

sonusIsdnsgServiceGroupT307 OBJECT-TYPE
    SYNTAX          Integer32 (60..360)
    MAX-ACCESS      read-only
    STATUS          current
    DESCRIPTION     
            "This T307 of Q.931 timer is used for  network sides."
    DEFVAL          { 180 }
    ::= { sonusIsdnsgServiceGroupEntry 102 }

sonusIsdnsgServiceGroupSuspendResume OBJECT-TYPE
    SYNTAX          INTEGER { supported(0), unsupported(1) }
    MAX-ACCESS      read-write
    STATUS          current
    DESCRIPTION     
            "This is used to determine if Suspend Resume is supported"
    DEFVAL          { unsupported }
    ::= { sonusIsdnsgServiceGroupEntry 103 }

sonusIsdnsgServiceGroupDisplayInRestart OBJECT-TYPE
    SYNTAX          DisplayString (SIZE(0..82))
    MAX-ACCESS      read-write
    STATUS          current
    DESCRIPTION     
            "Display IE content to be sent in RESTART message"
    ::= { sonusIsdnsgServiceGroupEntry 104 }

sonusIsdnsgServiceGroupForwardNotify OBJECT-TYPE
    SYNTAX          INTEGER { supported(0), unsupported(1) }
    MAX-ACCESS      read-write
    STATUS          current
    DESCRIPTION     
            "This is used to determine if forwarding of Notify message with Notification
             indicator containing User Suspended or User Resumed"
    DEFVAL          { unsupported }
    ::= { sonusIsdnsgServiceGroupEntry 105 }

sonusIsdnsgServiceGroupStatTable OBJECT-TYPE
    SYNTAX          SEQUENCE OF SonusIsdnsgServiceGroupStatEntry
    MAX-ACCESS      not-accessible
    STATUS          current
    DESCRIPTION     
            "This table contains status information about each ISDN service group
             in the GSX9000 Switch node."
    ::= { sonusIsdnServiceGroupMIBObjects 2 }

sonusIsdnsgServiceGroupStatEntry OBJECT-TYPE
    SYNTAX          SonusIsdnsgServiceGroupStatEntry
    MAX-ACCESS      not-accessible
    STATUS          current
    DESCRIPTION     
            "This table describes the status of the Service Groups that are configured
             as destinations ISDN nodes for the GSX9000 Switch node."
    INDEX           { sonusIsdnsgServiceGroupStatListIndex }
    ::= { sonusIsdnsgServiceGroupStatTable 1 }

SonusIsdnsgServiceGroupStatEntry ::=
    SEQUENCE {
        sonusIsdnsgServiceGroupStatListIndex    Integer32,
        sonusIsdnsgServiceGroupStatStatus INTEGER,
        sonusIsdnsgServiceGroupStatTgMode INTEGER,
        sonusIsdnsgServiceGroupStatNumBchConfigured           Integer32,
        sonusIsdnsgServiceGroupStatNumBchAvailable          Integer32,
        sonusIsdnsgServiceGroupStatInCallsActive        Counter32,
        sonusIsdnsgServiceGroupStatInCalls  Counter32,
        sonusIsdnsgServiceGroupStatInConnected      Counter32,
        sonusIsdnsgServiceGroupStatOutCallsActive         Counter32,
        sonusIsdnsgServiceGroupStatOutCalls   Counter32,
        sonusIsdnsgServiceGroupStatOutConnected       Counter32,
        sonusIsdnsgServiceGroupStatPrimaryDchannel          INTEGER,
        sonusIsdnsgServiceGroupStatPrimaryDchInPkts           Counter32,
        sonusIsdnsgServiceGroupStatPrimaryDchOutPkts            Counter32,
        sonusIsdnsgServiceGroupStatPrimaryDchInBytes            Counter32,
        sonusIsdnsgServiceGroupStatPrimaryDchOutBytes             Counter32,
        sonusIsdnsgServiceGroupStatBackupDchannel         INTEGER,
        sonusIsdnsgServiceGroupStatBackupDchInPkts          Counter32,
        sonusIsdnsgServiceGroupStatBackupDchOutPkts           Counter32,
        sonusIsdnsgServiceGroupStatBackupDchInBytes           Counter32,
        sonusIsdnsgServiceGroupStatBackupDchOutBytes            Counter32,
        sonusIsdnsgServiceGroupStatTbctAttempts       Counter32,
        sonusIsdnsgServiceGroupStatTbctActiveCount          Counter32,
        sonusIsdnsgServiceGroupStatTbctActiveLimitRejects                 Counter32,
        sonusIsdnsgServiceGroupStatTbctIntervalCount            Counter32,
        sonusIsdnsgServiceGroupStatTbctIntervalLimitRejects                   Counter32,
        sonusIsdnsgServiceGroupStatTbctTotalRejects           Counter32,
        sonusIsdnsgServiceGroupStatDchannelService          DisplayString,
        sonusIsdnsgServiceGroupStatDchannelPrimMonitorTest                  DisplayString,
        sonusIsdnsgServiceGroupStatDchannelBckMonitorTest                 DisplayString
    }

sonusIsdnsgServiceGroupStatListIndex OBJECT-TYPE
    SYNTAX          Integer32
    MAX-ACCESS      read-only
    STATUS          current
    DESCRIPTION     
            "The index of the ISDN Service Group."
    ::= { sonusIsdnsgServiceGroupStatEntry 1 }

sonusIsdnsgServiceGroupStatStatus OBJECT-TYPE
    SYNTAX          INTEGER { available(1), unavailable(2), dryup(3) }
    MAX-ACCESS      read-only
    STATUS          current
    DESCRIPTION     
            "The state of the ISDN Service Group."
    ::= { sonusIsdnsgServiceGroupStatEntry 2 }

sonusIsdnsgServiceGroupStatTgMode OBJECT-TYPE
    SYNTAX          INTEGER { inService(1), outOfService(2) }
    MAX-ACCESS      read-only
    STATUS          current
    DESCRIPTION     
            "The state of the Trunk Group that this ISDN Service Group belongs to."
    ::= { sonusIsdnsgServiceGroupStatEntry 3 }

sonusIsdnsgServiceGroupStatNumBchConfigured OBJECT-TYPE
    SYNTAX          Integer32
    MAX-ACCESS      read-only
    STATUS          current
    DESCRIPTION     
            "Number of Bchannels configured for this ISDN service group."
    ::= { sonusIsdnsgServiceGroupStatEntry 4 }

sonusIsdnsgServiceGroupStatNumBchAvailable OBJECT-TYPE
    SYNTAX          Integer32
    MAX-ACCESS      read-only
    STATUS          current
    DESCRIPTION     
            "Number of Bchannels available in this ISDN service group."
    ::= { sonusIsdnsgServiceGroupStatEntry 5 }

sonusIsdnsgServiceGroupStatInCallsActive OBJECT-TYPE
    SYNTAX          Counter32
    MAX-ACCESS      read-only
    STATUS          current
    DESCRIPTION     
            "Number of incoming active calls."
    ::= { sonusIsdnsgServiceGroupStatEntry 6 }

sonusIsdnsgServiceGroupStatInCalls OBJECT-TYPE
    SYNTAX          Counter32
    MAX-ACCESS      read-only
    STATUS          current
    DESCRIPTION     
            "Number of incoming call attemps."
    ::= { sonusIsdnsgServiceGroupStatEntry 7 }

sonusIsdnsgServiceGroupStatInConnected OBJECT-TYPE
    SYNTAX          Counter32
    MAX-ACCESS      read-only
    STATUS          current
    DESCRIPTION     
            "Number of incoming calls connected."
    ::= { sonusIsdnsgServiceGroupStatEntry 8 }

sonusIsdnsgServiceGroupStatOutCallsActive OBJECT-TYPE
    SYNTAX          Counter32
    MAX-ACCESS      read-only
    STATUS          current
    DESCRIPTION     
            "Number of outgoing active calls."
    ::= { sonusIsdnsgServiceGroupStatEntry 9 }

sonusIsdnsgServiceGroupStatOutCalls OBJECT-TYPE
    SYNTAX          Counter32
    MAX-ACCESS      read-only
    STATUS          current
    DESCRIPTION     
            "Number of outgoing call attemps."
    ::= { sonusIsdnsgServiceGroupStatEntry 10 }

sonusIsdnsgServiceGroupStatOutConnected OBJECT-TYPE
    SYNTAX          Counter32
    MAX-ACCESS      read-only
    STATUS          current
    DESCRIPTION     
            "Number of outgoing calls connected."
    ::= { sonusIsdnsgServiceGroupStatEntry 11 }

sonusIsdnsgServiceGroupStatPrimaryDchannel OBJECT-TYPE
    SYNTAX          INTEGER { inService(1), outOfService(2), 
                        manualOos(3), standby(4), maintenanceBusy(5), 
                        unEquipped(6), wait(7) }
    MAX-ACCESS      read-only
    STATUS          current
    DESCRIPTION     
            "The state of the Primary Dchannel of the ISDN Service Group."
    ::= { sonusIsdnsgServiceGroupStatEntry 12 }

sonusIsdnsgServiceGroupStatPrimaryDchInPkts OBJECT-TYPE
    SYNTAX          Counter32
    MAX-ACCESS      read-only
    STATUS          current
    DESCRIPTION     
            "Number of packets received on the primary D-channel."
    ::= { sonusIsdnsgServiceGroupStatEntry 13 }

sonusIsdnsgServiceGroupStatPrimaryDchOutPkts OBJECT-TYPE
    SYNTAX          Counter32
    MAX-ACCESS      read-only
    STATUS          current
    DESCRIPTION     
            "Number of packets sent on the primary D-channel."
    ::= { sonusIsdnsgServiceGroupStatEntry 14 }

sonusIsdnsgServiceGroupStatPrimaryDchInBytes OBJECT-TYPE
    SYNTAX          Counter32
    MAX-ACCESS      read-only
    STATUS          current
    DESCRIPTION     
            "Number of bytes received on the primary D-channel."
    ::= { sonusIsdnsgServiceGroupStatEntry 15 }

sonusIsdnsgServiceGroupStatPrimaryDchOutBytes OBJECT-TYPE
    SYNTAX          Counter32
    MAX-ACCESS      read-only
    STATUS          current
    DESCRIPTION     
            "Number of bytes sent on the primary D-channel."
    ::= { sonusIsdnsgServiceGroupStatEntry 16 }

sonusIsdnsgServiceGroupStatBackupDchannel OBJECT-TYPE
    SYNTAX          INTEGER { inService(1), outOfService(2), 
                        manualOos(3), standby(4), maintenanceBusy(5), 
                        unEquipped(6), wait(7) }
    MAX-ACCESS      read-only
    STATUS          current
    DESCRIPTION     
            "The state of the Backup Dchannel of the ISDN Service Group."
    ::= { sonusIsdnsgServiceGroupStatEntry 17 }

sonusIsdnsgServiceGroupStatBackupDchInPkts OBJECT-TYPE
    SYNTAX          Counter32
    MAX-ACCESS      read-only
    STATUS          current
    DESCRIPTION     
            "Number of packets received on the backup D-channel."
    ::= { sonusIsdnsgServiceGroupStatEntry 18 }

sonusIsdnsgServiceGroupStatBackupDchOutPkts OBJECT-TYPE
    SYNTAX          Counter32
    MAX-ACCESS      read-only
    STATUS          current
    DESCRIPTION     
            "Number of packets sent on the backup D-channel."
    ::= { sonusIsdnsgServiceGroupStatEntry 19 }

sonusIsdnsgServiceGroupStatBackupDchInBytes OBJECT-TYPE
    SYNTAX          Counter32
    MAX-ACCESS      read-only
    STATUS          current
    DESCRIPTION     
            "Number of bytes received on the backup D-channel."
    ::= { sonusIsdnsgServiceGroupStatEntry 20 }

sonusIsdnsgServiceGroupStatBackupDchOutBytes OBJECT-TYPE
    SYNTAX          Counter32
    MAX-ACCESS      read-only
    STATUS          current
    DESCRIPTION     
            "Number of bytes sent on the backup D-channel."
    ::= { sonusIsdnsgServiceGroupStatEntry 21 }

sonusIsdnsgServiceGroupStatTbctAttempts OBJECT-TYPE
    SYNTAX          Counter32
    MAX-ACCESS      read-only
    STATUS          current
    DESCRIPTION     
            "Number of Two Bchannel Transfer attempts."
    ::= { sonusIsdnsgServiceGroupStatEntry 22 }

sonusIsdnsgServiceGroupStatTbctActiveCount OBJECT-TYPE
    SYNTAX          Counter32
    MAX-ACCESS      read-only
    STATUS          current
    DESCRIPTION     
            "Number of Two Bchannel Transfers currently active."
    ::= { sonusIsdnsgServiceGroupStatEntry 23 }

sonusIsdnsgServiceGroupStatTbctActiveLimitRejects OBJECT-TYPE
    SYNTAX          Counter32
    MAX-ACCESS      read-only
    STATUS          current
    DESCRIPTION     
            "Number of Two Bchannel Transfer requests rejected due to active transfer limit."
    ::= { sonusIsdnsgServiceGroupStatEntry 24 }

sonusIsdnsgServiceGroupStatTbctIntervalCount OBJECT-TYPE
    SYNTAX          Counter32
    MAX-ACCESS      read-only
    STATUS          current
    DESCRIPTION     
            "Number of Two Bchannel Transfer requests received within latest 10 second interval."
    ::= { sonusIsdnsgServiceGroupStatEntry 25 }

sonusIsdnsgServiceGroupStatTbctIntervalLimitRejects OBJECT-TYPE
    SYNTAX          Counter32
    MAX-ACCESS      read-only
    STATUS          current
    DESCRIPTION     
            "Number of Two Bchannel Transfer requests rejected due interval limit."
    ::= { sonusIsdnsgServiceGroupStatEntry 26 }

sonusIsdnsgServiceGroupStatTbctTotalRejects OBJECT-TYPE
    SYNTAX          Counter32
    MAX-ACCESS      read-only
    STATUS          current
    DESCRIPTION     
            "Total number of Two Bchannel Transfer requests rejected."
    ::= { sonusIsdnsgServiceGroupStatEntry 27 }

sonusIsdnsgServiceGroupStatDchannelService OBJECT-TYPE
    SYNTAX          DisplayString (SIZE(0..23))
    MAX-ACCESS      read-only
    STATUS          current
    DESCRIPTION     
            "Dchannel service to which this Bchannel service is associated."
    ::= { sonusIsdnsgServiceGroupStatEntry 28 }

sonusIsdnsgServiceGroupStatDchannelPrimMonitorTest OBJECT-TYPE
    SYNTAX          DisplayString (SIZE(0..23))
    MAX-ACCESS      read-only
    STATUS          current
    DESCRIPTION     
            "Monitor object that is conducting a test on the primary D channel."
    ::= { sonusIsdnsgServiceGroupStatEntry 29 }

sonusIsdnsgServiceGroupStatDchannelBckMonitorTest OBJECT-TYPE
    SYNTAX          DisplayString (SIZE(0..23))
    MAX-ACCESS      read-only
    STATUS          current
    DESCRIPTION     
            "Monitor object that is conducting a test on the backup D channel."
    ::= { sonusIsdnsgServiceGroupStatEntry 30 }

sonusIsdnsgProfile OBJECT IDENTIFIER
    ::= { sonusIsdnServiceGroupMIBObjects 3 }

sonusIsdnsgProfileNextIndex OBJECT-TYPE
    SYNTAX          Integer32
    MAX-ACCESS      read-only
    STATUS          current
    DESCRIPTION     
            "The next valid index to use when creating a new sonusIsdnsgProfileEntry"
    ::= { sonusIsdnsgProfile 1 }

sonusIsdnsgProfileTable OBJECT-TYPE
    SYNTAX          SEQUENCE OF SonusIsdnsgProfileEntry
    MAX-ACCESS      not-accessible
    STATUS          current
    DESCRIPTION     
            "This table contains ISDN Service Group Profiles."
    ::= { sonusIsdnsgProfile 2 }

sonusIsdnsgProfileEntry OBJECT-TYPE
    SYNTAX          SonusIsdnsgProfileEntry
    MAX-ACCESS      not-accessible
    STATUS          current
    DESCRIPTION     
            "This table describes the ISDN Service Groups profile."
    INDEX           { sonusIsdnsgProfileListIndex }
    ::= { sonusIsdnsgProfileTable 1 }

SonusIsdnsgProfileEntry ::=
    SEQUENCE {
        sonusIsdnsgProfileListIndex     Integer32,
        sonusIsdnsgProfileName          SonusName,
        sonusIsdnsgProfileTrunkGroup    SonusNameReference,
        sonusIsdnsgProfileHuntAlgorithm INTEGER,
        sonusIsdnsgProfileCost          Integer32,
        sonusIsdnsgProfileSwitchSide    INTEGER,
        sonusIsdnsgProfileSwitchType    INTEGER,
        sonusIsdnsgProfileSwitchProfile DisplayString,
        sonusIsdnsgProfileMode          SonusServiceState,
        sonusIsdnsgProfileAdminState    SonusAdminState,
        sonusIsdnsgProfileRowStatus     RowStatus,
        sonusIsdnsgProfileDefaultDirectoryNumber        DisplayString,
        sonusIsdnsgProfileCallingPartyNumberProvision             INTEGER,
        sonusIsdnsgProfileCallingPartyNumberDiscard           INTEGER,
        sonusIsdnsgProfileCallingPartyNumberDelivery            INTEGER,
        sonusIsdnsgProfileCallingPartySubAddressTransfer                INTEGER,
        sonusIsdnsgProfileCallingPartySubAddressDelivery                INTEGER,
        sonusIsdnsgProfileCallingPartyNumberPresentation                INTEGER,
        sonusIsdnsgProfileCallingPartyNameDelivery          INTEGER,
        sonusIsdnsgProfileCalledPartySubAddressTransfer               INTEGER,
        sonusIsdnsgProfileCalledPartySubAddressDelivery               INTEGER,
        sonusIsdnsgProfileTonePackageName SonusNameReference,
        sonusIsdnsgProfileAlertToneName SonusNameReference,
        sonusIsdnsgProfileIsupIwfEarlyACM INTEGER,
        sonusIsdnsgProfileIsupEarlyCutThruAudibleRing             INTEGER,
        sonusIsdnsgProfileIsupEarlyCutThruNetworkInterworking                     INTEGER,
        sonusIsdnsgProfileDiscTreatmentProfileName          SonusNameReference,
        sonusIsdnsgProfileDiscSspProfileName    SonusNameReference,
        sonusIsdnsgProfileBearerCapabilityFallback          INTEGER,
        sonusIsdnsgProfileDialToneName  SonusNameReference,
        sonusIsdnsgProfileTbctEnabled   INTEGER,
        sonusIsdnsgProfileTbctAcknowledge INTEGER,
        sonusIsdnsgProfileTbctNotificationToTransferredUsers                    INTEGER,
        sonusIsdnsgProfileTbctNotificationToController              INTEGER,
        sonusIsdnsgProfileTbctActiveLimit Integer32,
        sonusIsdnsgProfileTbctIntervalLimit   Integer32,
        sonusIsdnsgProfileConfirmationToneName      SonusNameReference,
        sonusIsdnsgProfileMinDigitsForQuery   Integer32,
        sonusIsdnsgProfileImmediateDiscWithInbandTones              INTEGER,
        sonusIsdnsgProfileConfirmationToneOverride          INTEGER,
        sonusIsdnsgProfileAnsSupervisionTimeout       Integer32,
        sonusIsdnsgProfileAnsSupervisionTimeoutAction             INTEGER,
        sonusIsdnsgProfileCrankBackProfile  Integer32,
        sonusIsdnsgProfileCongRelTimeout Integer32,
        sonusIsdnsgProfileGuardTimer    Integer32,
        sonusIsdnsgProfileCallingPartyNameReceiveTimer              Integer32,
        sonusIsdnsgProfileLdcTimeout    Integer32,
        sonusIsdnsgProfileLdcAction     INTEGER,
        sonusIsdnsgProfileLdcRelCause   Integer32,
        sonusIsdnsgProfileLdcEmergencyCalls   INTEGER,
        sonusIsdnsgProfileOliDelivery   INTEGER,
        sonusIsdnsgProfileBchannelNegotiation     INTEGER,
        sonusIsdnsgProfileSendProgressOnAcmWithCause            INTEGER,
        sonusIsdnsgProfileSkipCrankBackProfile      Unsigned32,
        sonusIsdnsgProfilePrecedenceParamForwarding           INTEGER,
        sonusIsdnsgProfileBillableCallForConwithNonCharge                 INTEGER,
        sonusIsdnsgProfileChannelIdentification       INTEGER,
        sonusIsdnsgProfileUSIUpdate     INTEGER,
        sonusIsdnsgProfileCauseOfNoId   INTEGER,
        sonusIsdnsgProfileCRLRelCause   Integer32,
        sonusIsdnsgProfileColpColrIGW   INTEGER,
        sonusIsdnsgProfileTransferConnectConferenceUri              SonusNameReference,
        sonusIsdnsgProfileChanIDinAlertAndConnect         INTEGER,
        sonusIsdnsgProfileSuspendResume INTEGER,
        sonusIsdnsgProfileDisplayInRestart  DisplayString,
        sonusIsdnsgProfileForwardNotify INTEGER
    }

sonusIsdnsgProfileListIndex OBJECT-TYPE
    SYNTAX          Integer32 (1..128)
    MAX-ACCESS      read-only
    STATUS          current
    DESCRIPTION     
            "The index of the ISDN Service Group entry."
    ::= { sonusIsdnsgProfileEntry 1 }

sonusIsdnsgProfileName OBJECT-TYPE
    SYNTAX          SonusName
    MAX-ACCESS      read-write
    STATUS          current
    DESCRIPTION     
            "The name of the ISDN Service Group."
    ::= { sonusIsdnsgProfileEntry 2 }

sonusIsdnsgProfileTrunkGroup OBJECT-TYPE
    SYNTAX          SonusNameReference
    MAX-ACCESS      read-write
    STATUS          current
    DESCRIPTION     
            "The Trunk Group, which the ISDN Service Group belongs to."
    ::= { sonusIsdnsgProfileEntry 3 }

sonusIsdnsgProfileHuntAlgorithm OBJECT-TYPE
    SYNTAX          INTEGER { lowlow(1), highhigh(2), circularforward(3), 
                        circularbackward(4) }
    MAX-ACCESS      read-write
    STATUS          current
    DESCRIPTION     
            "The hunting method used to select channels for calls destined
             to the Service Group destination."
    DEFVAL          { lowlow }
    ::= { sonusIsdnsgProfileEntry 4 }

sonusIsdnsgProfileCost OBJECT-TYPE
    SYNTAX          Integer32 (0..100)
    MAX-ACCESS      read-write
    STATUS          current
    DESCRIPTION     
            "The routing cost to the ISDN Service Group."
    DEFVAL          { 50 }
    ::= { sonusIsdnsgProfileEntry 5 }

sonusIsdnsgProfileSwitchSide OBJECT-TYPE
    SYNTAX          INTEGER { network(1), user(2), usersym(3) }
    MAX-ACCESS      read-write
    STATUS          deprecated
    DESCRIPTION     
            "The switch side the ISDN Service Group should act as.
             This MIB object has been replaced by the
             sonusIsdnsgSwitchProfileSwitchSide MIB object."
    DEFVAL          { network }
    ::= { sonusIsdnsgProfileEntry 6 }

sonusIsdnsgProfileSwitchType OBJECT-TYPE
    SYNTAX          INTEGER { ni2(1), dms250(2), dms100(3), 
                        lucent5ESS(4), lucent4ESS(5), euroIsdn(6), 
                        ins1500(7) }
    MAX-ACCESS      read-write
    STATUS          deprecated
    DESCRIPTION     
            "The network switch type where the ISDN Service Group resides.
             This MIB object has been replaced by the
             sonusIsdnsgSwitchProfileSwitchType MIB object."
    DEFVAL          { ni2 }
    ::= { sonusIsdnsgProfileEntry 7 }

sonusIsdnsgProfileSwitchProfile OBJECT-TYPE
    SYNTAX          DisplayString (SIZE(0..23))
    MAX-ACCESS      read-write
    STATUS          obsolete
    DESCRIPTION     
            "The ISDN Service Group switch profile name.
             This MIB object is a duplicate of the
             sonusIsdnsgServiceGroupSwitchProfileName."
    ::= { sonusIsdnsgProfileEntry 8 }

sonusIsdnsgProfileMode OBJECT-TYPE
    SYNTAX          SonusServiceState
    MAX-ACCESS      read-write
    STATUS          obsolete
    DESCRIPTION     
            "The mode of operation of channels in the ISDN Service Group.
             This MIB object is no longer applicable."
    DEFVAL          { inService }
    ::= { sonusIsdnsgProfileEntry 9 }

sonusIsdnsgProfileAdminState OBJECT-TYPE
    SYNTAX          SonusAdminState
    MAX-ACCESS      read-write
    STATUS          current
    DESCRIPTION     
            "The admin state of the ISDN Service Group."
    DEFVAL          { disabled }
    ::= { sonusIsdnsgProfileEntry 10 }

sonusIsdnsgProfileRowStatus OBJECT-TYPE
    SYNTAX          RowStatus
    MAX-ACCESS      read-write
    STATUS          current
    DESCRIPTION     
            ""
    ::= { sonusIsdnsgProfileEntry 11 }

sonusIsdnsgProfileDefaultDirectoryNumber OBJECT-TYPE
    SYNTAX          DisplayString (SIZE(0..30))
    MAX-ACCESS      read-write
    STATUS          current
    DESCRIPTION     
            "Default Directory number for the ISDN Service Profile."
    ::= { sonusIsdnsgProfileEntry 12 }

sonusIsdnsgProfileCallingPartyNumberProvision OBJECT-TYPE
    SYNTAX          INTEGER { necessary(1), notNecessary(2) }
    MAX-ACCESS      read-write
    STATUS          current
    DESCRIPTION     
            "Specifies wether the Calling Party Number is required in the incoming SETUP."
    DEFVAL          { necessary }
    ::= { sonusIsdnsgProfileEntry 13 }

sonusIsdnsgProfileCallingPartyNumberDiscard OBJECT-TYPE
    SYNTAX          INTEGER { yes(1), no(2), rdns(3), rdn2(4) }
    MAX-ACCESS      read-write
    STATUS          current
    DESCRIPTION     
            "Controls discard of Calling Party Number and Redirecting Numbers.
             yes:		discard all
             no:			discard none
             rdns:		discard redirecting numbers
             rdn2:		discard second redirecting number"
    DEFVAL          { no }
    ::= { sonusIsdnsgProfileEntry 14 }

sonusIsdnsgProfileCallingPartyNumberDelivery OBJECT-TYPE
    SYNTAX          INTEGER { yes(1), no(2), cpnonly(3), cpn1rdn(4) }
    MAX-ACCESS      read-write
    STATUS          current
    DESCRIPTION     
            "Controls the delivery of the Calling Party Number and Redirecting Numbers.
             yes:		deliver all
             no:			deliver none
             cpnonly:	deliver CPN and no RDNs
             cpn1rdn:	deliver CPN and one RDN"
    DEFVAL          { yes }
    ::= { sonusIsdnsgProfileEntry 15 }

sonusIsdnsgProfileCallingPartySubAddressTransfer OBJECT-TYPE
    SYNTAX          INTEGER { yes(1), no(2), conditional(3) }
    MAX-ACCESS      read-write
    STATUS          current
    DESCRIPTION     
            "Controls the transfer of the Calling Party Subaddress Information Element"
    DEFVAL          { yes }
    ::= { sonusIsdnsgProfileEntry 16 }

sonusIsdnsgProfileCallingPartySubAddressDelivery OBJECT-TYPE
    SYNTAX          INTEGER { yes(1), no(2), conditional(3) }
    MAX-ACCESS      read-write
    STATUS          current
    DESCRIPTION     
            "Controls the delivery of the Calling Party Subaddress Information Element to the CPE"
    DEFVAL          { yes }
    ::= { sonusIsdnsgProfileEntry 17 }

sonusIsdnsgProfileCallingPartyNumberPresentation OBJECT-TYPE
    SYNTAX          INTEGER { yes(1), no(2) }
    MAX-ACCESS      read-write
    STATUS          current
    DESCRIPTION     
            "Used as Calling Party Number presentation indicator when none available in incoming SETUP."
    DEFVAL          { yes }
    ::= { sonusIsdnsgProfileEntry 18 }

sonusIsdnsgProfileCallingPartyNameDelivery OBJECT-TYPE
    SYNTAX          INTEGER { yes(1), no(2), alerting(3), answered(4), 
                        callproc(5), displayIeOfSetup(6) }
    MAX-ACCESS      read-write
    STATUS          current
    DESCRIPTION     
            "Controls the delivery of the Calling Party Name.
             yes:		in FACILITY IE of SETUP message
             no:			not delivered
             callproc:	after the CALLPROC message
             alerting:	after the ALERTING message
             answered:	after the CONNECT
             displayIeOfSetup    in DISPLAY IE of SETUP message"
    DEFVAL          { no }
    ::= { sonusIsdnsgProfileEntry 19 }

sonusIsdnsgProfileCalledPartySubAddressTransfer OBJECT-TYPE
    SYNTAX          INTEGER { yes(1), no(2), conditional(3) }
    MAX-ACCESS      read-write
    STATUS          current
    DESCRIPTION     
            "Controls the transfer of the Called Party Subaddress Information Element"
    DEFVAL          { yes }
    ::= { sonusIsdnsgProfileEntry 20 }

sonusIsdnsgProfileCalledPartySubAddressDelivery OBJECT-TYPE
    SYNTAX          INTEGER { yes(1), no(2), conditional(3) }
    MAX-ACCESS      read-write
    STATUS          current
    DESCRIPTION     
            "Controls the delivery of the Called Party Subaddress Information Element to the CPE"
    DEFVAL          { yes }
    ::= { sonusIsdnsgProfileEntry 21 }

sonusIsdnsgProfileTonePackageName OBJECT-TYPE
    SYNTAX          SonusNameReference
    MAX-ACCESS      read-write
    STATUS          current
    DESCRIPTION     
            "The tone package to be used for this service."
    ::= { sonusIsdnsgProfileEntry 22 }

sonusIsdnsgProfileAlertToneName OBJECT-TYPE
    SYNTAX          SonusNameReference
    MAX-ACCESS      read-write
    STATUS          obsolete
    DESCRIPTION     
            "Specifies a named reference to a tone to play for ring back.
             This object is not used and was made obsolete in GSX
             release 6.0. Local Ring Back Tone Configuration has
             now moved to PSX."
    ::= { sonusIsdnsgProfileEntry 23 }

sonusIsdnsgProfileIsupIwfEarlyACM OBJECT-TYPE
    SYNTAX          INTEGER { yes(1), no(2) }
    MAX-ACCESS      read-write
    STATUS          current
    DESCRIPTION     
            "It is used to trigger ealy ACM or not when ISDNSG received
             a establish request from CC with edage SG is ISUP."
    DEFVAL          { no }
    ::= { sonusIsdnsgProfileEntry 24 }

sonusIsdnsgProfileIsupEarlyCutThruAudibleRing OBJECT-TYPE
    SYNTAX          INTEGER { yes(1), no(2), twoway(3) }
    MAX-ACCESS      read-write
    STATUS          current
    DESCRIPTION     
            "When enabled, early cut thru occurs on the reception of an ALERT message
             or a progress indicator #8 (inband information or appropriate pattern now available)."
    DEFVAL          { yes }
    ::= { sonusIsdnsgProfileEntry 25 }

sonusIsdnsgProfileIsupEarlyCutThruNetworkInterworking OBJECT-TYPE
    SYNTAX          INTEGER { yes(1), no(2), twoway(3) }
    MAX-ACCESS      read-write
    STATUS          current
    DESCRIPTION     
            "When enabled, early cut thru occurs on the reception of a progress indicator #1
             (call is not end-to-end ISDN; further call progress information may be available inband)."
    DEFVAL          { yes }
    ::= { sonusIsdnsgProfileEntry 26 }

sonusIsdnsgProfileDiscTreatmentProfileName OBJECT-TYPE
    SYNTAX          SonusNameReference
    MAX-ACCESS      read-write
    STATUS          current
    DESCRIPTION     
            "The disconnect treatment profile to be used for this service."
    ::= { sonusIsdnsgProfileEntry 27 }

sonusIsdnsgProfileDiscSspProfileName OBJECT-TYPE
    SYNTAX          SonusNameReference
    MAX-ACCESS      read-write
    STATUS          current
    DESCRIPTION     
            "The disconnect SSP profile to be used for this service."
    ::= { sonusIsdnsgProfileEntry 28 }

sonusIsdnsgProfileBearerCapabilityFallback OBJECT-TYPE
    SYNTAX          INTEGER { yes(1), no(2) }
    MAX-ACCESS      read-write
    STATUS          current
    DESCRIPTION     
            "Enables bearer capability fall back."
    DEFVAL          { no }
    ::= { sonusIsdnsgProfileEntry 29 }

sonusIsdnsgProfileDialToneName OBJECT-TYPE
    SYNTAX          SonusNameReference
    MAX-ACCESS      read-write
    STATUS          current
    DESCRIPTION     
            "Specifies a named reference to a tone to play for dial tone."
    ::= { sonusIsdnsgProfileEntry 30 }

sonusIsdnsgProfileTbctEnabled OBJECT-TYPE
    SYNTAX          INTEGER { yes(1), no(2) }
    MAX-ACCESS      read-write
    STATUS          current
    DESCRIPTION     
            "Enables Two B-channel Transfer."
    DEFVAL          { no }
    ::= { sonusIsdnsgProfileEntry 31 }

sonusIsdnsgProfileTbctAcknowledge OBJECT-TYPE
    SYNTAX          INTEGER { facility(1), disconnect(2) }
    MAX-ACCESS      read-write
    STATUS          current
    DESCRIPTION     
            "Controls whether a succesfull transfer request should be acknowledged 
             as a part of the DISCONNECT message or with its own FACILITY message."
    DEFVAL          { facility }
    ::= { sonusIsdnsgProfileEntry 32 }

sonusIsdnsgProfileTbctNotificationToTransferredUsers OBJECT-TYPE
    SYNTAX          INTEGER { yes(1), no(2) }
    MAX-ACCESS      read-write
    STATUS          current
    DESCRIPTION     
            "Enables Notifications to the transferred users."
    DEFVAL          { no }
    ::= { sonusIsdnsgProfileEntry 33 }

sonusIsdnsgProfileTbctNotificationToController OBJECT-TYPE
    SYNTAX          INTEGER { yes(1), no(2) }
    MAX-ACCESS      read-write
    STATUS          current
    DESCRIPTION     
            "Enables notification to the controller.  This includes notification of
             the number of active (and available, if applicable) transfers, and
             notification of clearing of a transferred call."
    DEFVAL          { yes }
    ::= { sonusIsdnsgProfileEntry 34 }

sonusIsdnsgProfileTbctActiveLimit OBJECT-TYPE
    SYNTAX          Integer32 (0..60000)
    MAX-ACCESS      read-write
    STATUS          current
    DESCRIPTION     
            "Allows limiting the number of active transfers associated with this ISDN
             service.  The value 0 disables the limiting mechanism."
    DEFVAL          { 100 }
    ::= { sonusIsdnsgProfileEntry 35 }

sonusIsdnsgProfileTbctIntervalLimit OBJECT-TYPE
    SYNTAX          Integer32 (0..500)
    MAX-ACCESS      read-write
    STATUS          current
    DESCRIPTION     
            "Allows limiting the number of transfer requests per 10 second interval
             The value 0 disables the limiting mechanism."
    DEFVAL          { 10 }
    ::= { sonusIsdnsgProfileEntry 36 }

sonusIsdnsgProfileConfirmationToneName OBJECT-TYPE
    SYNTAX          SonusNameReference
    MAX-ACCESS      read-write
    STATUS          current
    DESCRIPTION     
            "Specifies a named reference to a tone to play for dial tone."
    ::= { sonusIsdnsgProfileEntry 37 }

sonusIsdnsgProfileMinDigitsForQuery OBJECT-TYPE
    SYNTAX          Integer32 (0..30)
    MAX-ACCESS      read-write
    STATUS          current
    DESCRIPTION     
            "If Overlap Receiving is supported and CalledAddress
             received is not complete, then minimum number of
             CalledAddress Digits to receive before we go for Route
             Query."
    DEFVAL          { 0 }
    ::= { sonusIsdnsgProfileEntry 38 }

sonusIsdnsgProfileImmediateDiscWithInbandTones OBJECT-TYPE
    SYNTAX          INTEGER { disabled(1), enabled(2), establishing(3), 
                        allstates(4) }
    MAX-ACCESS      read-write
    STATUS          current
    DESCRIPTION     
            "When a DISCONNECT with inband tones is recieved, to maintain
             the voicepath a PROGRESS is propagated.  This parameter causes
             an immediate disconnect instead.  The options are explaned below.
             	disabled:		maintain voice path
             	enabled:		immediate disconnect in stable states
             	establishing	immediate disconnect in establishing states
             	allstates		immediate disconnect in all states"
    DEFVAL          { disabled }
    ::= { sonusIsdnsgProfileEntry 39 }

sonusIsdnsgProfileConfirmationToneOverride OBJECT-TYPE
    SYNTAX          INTEGER { disabled(1), enabled(2) }
    MAX-ACCESS      read-write
    STATUS          current
    DESCRIPTION     
            "If supported, informs CC to play a C-Tone for all
             calls using this service group.  If unsupported, 
             informs CC to use the enable flag from the PSX to
             decide whether or not to play a C-Tone."
    DEFVAL          { disabled }
    ::= { sonusIsdnsgProfileEntry 40 }

sonusIsdnsgProfileAnsSupervisionTimeout OBJECT-TYPE
    SYNTAX          Integer32 (0..1000)
    MAX-ACCESS      read-write
    STATUS          current
    DESCRIPTION     
            "This is the time from egress call setup to egress receiving an answer,
             used for both user and network sides."
    DEFVAL          { 300 }
    ::= { sonusIsdnsgProfileEntry 41 }

sonusIsdnsgProfileAnsSupervisionTimeoutAction OBJECT-TYPE
    SYNTAX          INTEGER { release(1), softanswer(2), 
                        trapAndRestart(3) }
    MAX-ACCESS      read-write
    STATUS          current
    DESCRIPTION     
            "This is the action to take if the answer supervision timer
             expires.  The call may be released, assumed to be answered or
                  a trap can be fired and the timer restarted."
    DEFVAL          { release }
    ::= { sonusIsdnsgProfileEntry 42 }

sonusIsdnsgProfileCrankBackProfile OBJECT-TYPE
    SYNTAX          Integer32 (1..20)
    MAX-ACCESS      read-write
    STATUS          current
    DESCRIPTION     
            "The Crank Back Profile to be used for this service."
    DEFVAL          { 1 }
    ::= { sonusIsdnsgProfileEntry 44 }

sonusIsdnsgProfileCongRelTimeout OBJECT-TYPE
    SYNTAX          Integer32 (0..5)
    MAX-ACCESS      read-write
    STATUS          current
    DESCRIPTION     
            "Time to delay sending of release during congestion."
    DEFVAL          { 0 }
    ::= { sonusIsdnsgProfileEntry 45 }

sonusIsdnsgProfileGuardTimer OBJECT-TYPE
    SYNTAX          Integer32 (0..9999)
    MAX-ACCESS      read-write
    STATUS          current
    DESCRIPTION     
            "Time out in milliseconds before a channel can be re-hunted."
    DEFVAL          { 0 }
    ::= { sonusIsdnsgProfileEntry 46 }

sonusIsdnsgProfileCallingPartyNameReceiveTimer OBJECT-TYPE
    SYNTAX          Integer32 (0..3600)
    MAX-ACCESS      read-write
    STATUS          current
    DESCRIPTION     
            "Time out in milliseconds to wait to receive the Calling Party Name."
    DEFVAL          { 0 }
    ::= { sonusIsdnsgProfileEntry 47 }

sonusIsdnsgProfileLdcTimeout OBJECT-TYPE
    SYNTAX          Integer32 (0..2880)
    MAX-ACCESS      read-write
    STATUS          current
    DESCRIPTION     
            "The timeout value of the long duration call timer in minutes.
             Allowed values are 0 to disable the timer, 60-2880 minutes to set the timer."
    DEFVAL          { 0 }
    ::= { sonusIsdnsgProfileEntry 48 }

sonusIsdnsgProfileLdcAction OBJECT-TYPE
    SYNTAX          INTEGER { noAction(0), trap(1), release(2), 
                        trapAndRelease(3) }
    MAX-ACCESS      read-write
    STATUS          current
    DESCRIPTION     
            "This is the action to take if the long duration call timer
             expires.  The call may be released or a trap fired, or both."
    DEFVAL          { noAction }
    ::= { sonusIsdnsgProfileEntry 49 }

sonusIsdnsgProfileLdcRelCause OBJECT-TYPE
    SYNTAX          Integer32 (1..127)
    MAX-ACCESS      read-write
    STATUS          current
    DESCRIPTION     
            "The Q.850 release value to use should the call be released 
             due to long duration call timer expiry"
    DEFVAL          { 41 }
    ::= { sonusIsdnsgProfileEntry 50 }

sonusIsdnsgProfileLdcEmergencyCalls OBJECT-TYPE
    SYNTAX          INTEGER { include(0), exclude(1) }
    MAX-ACCESS      read-write
    STATUS          current
    DESCRIPTION     
            "Whether Emergency Calls should be excluded from 
             or included in Long Duration Call procedures"
    DEFVAL          { exclude }
    ::= { sonusIsdnsgProfileEntry 51 }

sonusIsdnsgProfileOliDelivery OBJECT-TYPE
    SYNTAX          INTEGER { yes(1), no(2) }
    MAX-ACCESS      read-write
    STATUS          current
    DESCRIPTION     
            "This configures whether the ISDN Service delivers (or transfers on user side) the originating line information."
    DEFVAL          { yes }
    ::= { sonusIsdnsgProfileEntry 52 }

sonusIsdnsgProfileBchannelNegotiation OBJECT-TYPE
    SYNTAX          INTEGER { yes(1), no(2) }
    MAX-ACCESS      read-write
    STATUS          current
    DESCRIPTION     
            "This configures whether the ISDN Service supports the B-channel negotiation signaling procedures."
    DEFVAL          { yes }
    ::= { sonusIsdnsgProfileEntry 53 }

sonusIsdnsgProfileSendProgressOnAcmWithCause OBJECT-TYPE
    SYNTAX          INTEGER { yes(1), no(2) }
    MAX-ACCESS      read-write
    STATUS          current
    DESCRIPTION     
            "Whether Progress or Disconnect should be sent on 
             receiving an ISUP ACM with Cause Indicators"
    DEFVAL          { no }
    ::= { sonusIsdnsgProfileEntry 54 }

sonusIsdnsgProfileSkipCrankBackProfile OBJECT-TYPE
    SYNTAX          Unsigned32 (0..20)
    MAX-ACCESS      read-write
    STATUS          current
    DESCRIPTION     
            "The Skip Crankback Profile to be used for this service."
    DEFVAL          { 0 }
    ::= { sonusIsdnsgProfileEntry 55 }

sonusIsdnsgProfilePrecedenceParamForwarding OBJECT-TYPE
    SYNTAX          INTEGER { disabled(1), enabled(2) }
    MAX-ACCESS      read-write
    STATUS          current
    DESCRIPTION     
            "This enables and disables precedence parameter forwarding
             on this service."
    DEFVAL          { disabled }
    ::= { sonusIsdnsgProfileEntry 56 }

sonusIsdnsgProfileBillableCallForConwithNonCharge OBJECT-TYPE
    SYNTAX          INTEGER { supported(0), unsupported(1) }
    MAX-ACCESS      read-write
    STATUS          current
    DESCRIPTION     
            "This parameter is used to send CONNECT message when a CON message with 
             Charge Indicator set to Non-Charge (i.e. other than Charge) is received. If this parameter is 
             set to UNSUPPORTED, then PROGRESS message will be sent. "
    DEFVAL          { supported }
    ::= { sonusIsdnsgProfileEntry 57 }

sonusIsdnsgProfileChannelIdentification OBJECT-TYPE
    SYNTAX          INTEGER { channelNumber(0), slotMap(1) }
    MAX-ACCESS      read-write
    STATUS          current
    DESCRIPTION     
            "Identifies the type of channel present in the Channel Identification 
             Information Element.  It can be either Channel Number of Slot Map"
    DEFVAL          { channelNumber }
    ::= { sonusIsdnsgProfileEntry 58 }

sonusIsdnsgProfileUSIUpdate OBJECT-TYPE
    SYNTAX          INTEGER { supported(0), unsupported(1) }
    MAX-ACCESS      read-write
    STATUS          current
    DESCRIPTION     
            "Is the modification of Information Transfer Capability and User Information Layer1
             present in USI IE supported for the ISUP Signaling Profile.  Map 1001 value in ITC 
             to 01000 in ISDN SETUP.  Map A-Law in User Information Layer1 to M-Law in Bearer 
             Capability Parameter of ISDN SETUP. "
    DEFVAL          { unsupported }
    ::= { sonusIsdnsgProfileEntry 59 }

sonusIsdnsgProfileCauseOfNoId OBJECT-TYPE
    SYNTAX          INTEGER { supported(0), unsupported(1) }
    MAX-ACCESS      read-write
    STATUS          current
    DESCRIPTION     
            "This parameter is used to send Cause of No Id parameter in facility IE of SETUP
             message on egress ISDN side "
    DEFVAL          { unsupported }
    ::= { sonusIsdnsgProfileEntry 60 }

sonusIsdnsgProfileCRLRelCause OBJECT-TYPE
    SYNTAX          Integer32 (1..127)
    MAX-ACCESS      read-write
    STATUS          current
    DESCRIPTION     
            "The Q.850 release value to use should the call be released 
             due to call rate limiting"
    DEFVAL          { 42 }
    ::= { sonusIsdnsgProfileEntry 61 }

sonusIsdnsgProfileColpColrIGW OBJECT-TYPE
    SYNTAX          INTEGER { yes(1), no(2) }
    MAX-ACCESS      read-write
    STATUS          current
    DESCRIPTION     
            "It is used to trigger colp colr IGW functionality or not when ISDNSG received
             a CONNECTED Number."
    DEFVAL          { no }
    ::= { sonusIsdnsgProfileEntry 62 }

sonusIsdnsgProfileTransferConnectConferenceUri OBJECT-TYPE
    SYNTAX          SonusNameReference
    MAX-ACCESS      read-write
    STATUS          current
    DESCRIPTION     
            "Specifies a named reference to conference URI for transfer connect feature."
    ::= { sonusIsdnsgProfileEntry 63 }

sonusIsdnsgProfileChanIDinAlertAndConnect OBJECT-TYPE
    SYNTAX          INTEGER { supported(0), unsupported(1) }
    MAX-ACCESS      read-write
    STATUS          current
    DESCRIPTION     
            "This is used to determine if Channel ID will be sent in ALERT and CONNECT messages "
    DEFVAL          { unsupported }
    ::= { sonusIsdnsgProfileEntry 64 }

sonusIsdnsgProfileSuspendResume OBJECT-TYPE
    SYNTAX          INTEGER { supported(0), unsupported(1) }
    MAX-ACCESS      read-write
    STATUS          current
    DESCRIPTION     
            "This is used to determine if Suspend Resume is supported"
    DEFVAL          { unsupported }
    ::= { sonusIsdnsgProfileEntry 65 }

sonusIsdnsgProfileDisplayInRestart OBJECT-TYPE
    SYNTAX          DisplayString (SIZE(0..82))
    MAX-ACCESS      read-write
    STATUS          current
    DESCRIPTION     
            "Display IE content to be sent in RESTART message"
    ::= { sonusIsdnsgProfileEntry 66 }

sonusIsdnsgProfileForwardNotify OBJECT-TYPE
    SYNTAX          INTEGER { supported(0), unsupported(1) }
    MAX-ACCESS      read-write
    STATUS          current
    DESCRIPTION     
            "This is used to determine if Notify with User Suspend or User Resume is to be forwarded"
    DEFVAL          { unsupported }
    ::= { sonusIsdnsgProfileEntry 67 }

sonusIsdnsgInterfaceTable OBJECT-TYPE
    SYNTAX          SEQUENCE OF SonusIsdnsgInterfaceEntry
    MAX-ACCESS      not-accessible
    STATUS          current
    DESCRIPTION     
            "The Isdnsg Interface table describes the interfaces in the indexed service
             group. This table is unavailable if the sonusIsdnsgServiceGroupStatStatus
             object indicates that this service group is unavailable."
    ::= { sonusIsdnServiceGroupMIBObjects 4 }

sonusIsdnsgInterfaceEntry OBJECT-TYPE
    SYNTAX          SonusIsdnsgInterfaceEntry
    MAX-ACCESS      not-accessible
    STATUS          current
    DESCRIPTION     
            ""
    INDEX           { sonusIsdnsgInterfaceServiceListIndex, 
                      sonusIsdnsgInterfaceIdentifier }
    ::= { sonusIsdnsgInterfaceTable 1 }

SonusIsdnsgInterfaceEntry ::=
    SEQUENCE {
        sonusIsdnsgInterfaceServiceListIndex    Integer32,
        sonusIsdnsgInterfaceIdentifier  Integer32,
        sonusIsdnsgInterfacePortName    SonusNameReference,
        sonusIsdnsgInterfaceOperation   INTEGER,
        sonusIsdnsgInterfaceAdminState  SonusAdminState,
        sonusIsdnsgInterfaceRowStatus   RowStatus
    }

sonusIsdnsgInterfaceServiceListIndex OBJECT-TYPE
    SYNTAX          Integer32
    MAX-ACCESS      read-only
    STATUS          current
    DESCRIPTION     
            "The index of the ISDN Service Group interface is defined for."
    ::= { sonusIsdnsgInterfaceEntry 1 }

sonusIsdnsgInterfaceIdentifier OBJECT-TYPE
    SYNTAX          Integer32 (0..127)
    MAX-ACCESS      read-only
    STATUS          current
    DESCRIPTION     
            "The Q931 interface identifier of the interface."
    ::= { sonusIsdnsgInterfaceEntry 2 }

sonusIsdnsgInterfacePortName OBJECT-TYPE
    SYNTAX          SonusNameReference
    MAX-ACCESS      read-write
    STATUS          current
    DESCRIPTION     
            "The name of the port interface is on."
    ::= { sonusIsdnsgInterfaceEntry 3 }

sonusIsdnsgInterfaceOperation OBJECT-TYPE
    SYNTAX          INTEGER { restart(1) }
    MAX-ACCESS      read-write
    STATUS          current
    DESCRIPTION     
            "Apply operation to the ISDN Interface."
    ::= { sonusIsdnsgInterfaceEntry 4 }

sonusIsdnsgInterfaceAdminState OBJECT-TYPE
    SYNTAX          SonusAdminState
    MAX-ACCESS      read-write
    STATUS          current
    DESCRIPTION     
            "The admin state of the ISDN Interface."
    DEFVAL          { disabled }
    ::= { sonusIsdnsgInterfaceEntry 5 }

sonusIsdnsgInterfaceRowStatus OBJECT-TYPE
    SYNTAX          RowStatus
    MAX-ACCESS      read-write
    STATUS          current
    DESCRIPTION     
            ""
    ::= { sonusIsdnsgInterfaceEntry 6 }

sonusIsdnsgBchannelTable OBJECT-TYPE
    SYNTAX          SEQUENCE OF SonusIsdnsgBchannelEntry
    MAX-ACCESS      not-accessible
    STATUS          current
    DESCRIPTION     
            "The Isdnsg B-channel table describes the B-channels in the indexed ISDN
             interface. This table is unavailable if the sonusisdnsgServiceGroupStatStatus
             object indicates that this service group is unavailable."
    ::= { sonusIsdnServiceGroupMIBObjects 5 }

sonusIsdnsgBchannelEntry OBJECT-TYPE
    SYNTAX          SonusIsdnsgBchannelEntry
    MAX-ACCESS      not-accessible
    STATUS          current
    DESCRIPTION     
            ""
    INDEX           { sonusIsdnsgBchannelServiceListIndex, 
                      sonusIsdnsgBchannelInterfaceIdentifier, 
                      sonusIsdnsgBchannelNumber }
    ::= { sonusIsdnsgBchannelTable 1 }

SonusIsdnsgBchannelEntry ::=
    SEQUENCE {
        sonusIsdnsgBchannelServiceListIndex   Integer32,
        sonusIsdnsgBchannelInterfaceIdentifier      Integer32,
        sonusIsdnsgBchannelNumber       Integer32,
        sonusIsdnsgBchannelCircuitProfileName     SonusNameReference,
        sonusIsdnsgBchannelDirection    INTEGER,
        sonusIsdnsgBchannelOperation    INTEGER,
        sonusIsdnsgBchannelMode         INTEGER,
        sonusIsdnsgBchannelAction       INTEGER,
        sonusIsdnsgBchannelTimeout      Integer32,
        sonusIsdnsgBchannelAdminState   SonusAdminState,
        sonusIsdnsgBchannelTrunkMember  Integer32,
        sonusIsdnsgBchannelRowStatus    RowStatus,
        sonusIsdnsgBchannelServiceName  SonusNameReference
    }

sonusIsdnsgBchannelServiceListIndex OBJECT-TYPE
    SYNTAX          Integer32
    MAX-ACCESS      read-only
    STATUS          current
    DESCRIPTION     
            "The index of the ISDN Service Group of the ISDN B-channel."
    ::= { sonusIsdnsgBchannelEntry 1 }

sonusIsdnsgBchannelInterfaceIdentifier OBJECT-TYPE
    SYNTAX          Integer32 (0..127)
    MAX-ACCESS      read-only
    STATUS          current
    DESCRIPTION     
            "The Q931 interface identifier of the ISDN B-channel."
    ::= { sonusIsdnsgBchannelEntry 2 }

sonusIsdnsgBchannelNumber OBJECT-TYPE
    SYNTAX          Integer32 (1..32)
    MAX-ACCESS      read-only
    STATUS          current
    DESCRIPTION     
            "The channel number of the ISDN B-channel."
    ::= { sonusIsdnsgBchannelEntry 3 }

sonusIsdnsgBchannelCircuitProfileName OBJECT-TYPE
    SYNTAX          SonusNameReference
    MAX-ACCESS      read-write
    STATUS          current
    DESCRIPTION     
            "The circuit profile name assigned to the ISDN B-channel."
    ::= { sonusIsdnsgBchannelEntry 4 }

sonusIsdnsgBchannelDirection OBJECT-TYPE
    SYNTAX          INTEGER { twoWay(1), oneWayIn(2), oneWayOut(3) }
    MAX-ACCESS      read-write
    STATUS          current
    DESCRIPTION     
            "Identifies the direction of traffic to be allowed on the ISDN B-channel."
    ::= { sonusIsdnsgBchannelEntry 5 }

sonusIsdnsgBchannelOperation OBJECT-TYPE
    SYNTAX          INTEGER { restart(1) }
    MAX-ACCESS      read-write
    STATUS          current
    DESCRIPTION     
            "Apply an operation to the ISDN B-channel."
    ::= { sonusIsdnsgBchannelEntry 6 }

sonusIsdnsgBchannelMode OBJECT-TYPE
    SYNTAX          INTEGER { outOfService(1), maintenance(2), 
                        inService(3) }
    MAX-ACCESS      read-write
    STATUS          current
    DESCRIPTION     
            "The mode of operation of the ISDN B-channel."
    ::= { sonusIsdnsgBchannelEntry 7 }

sonusIsdnsgBchannelAction OBJECT-TYPE
    SYNTAX          INTEGER { dryUp(1), force(2) }
    MAX-ACCESS      read-write
    STATUS          current
    DESCRIPTION     
            "The action taken on the ISDN B-channel when sonusIsdnsgBchannelMode is set to 
             out of service. This object should only be set in conjunction with sonusIsdnsgBchannelMode."
    ::= { sonusIsdnsgBchannelEntry 8 }

sonusIsdnsgBchannelTimeout OBJECT-TYPE
    SYNTAX          Integer32 (1..1440)
    MAX-ACCESS      read-write
    STATUS          current
    DESCRIPTION     
            "The timeout value in minutes for dryup action on the ISDN B-channel.
             This object should only be set in conjunction with sonusIsdnsgBchannelAction."
    ::= { sonusIsdnsgBchannelEntry 9 }

sonusIsdnsgBchannelAdminState OBJECT-TYPE
    SYNTAX          SonusAdminState
    MAX-ACCESS      read-write
    STATUS          current
    DESCRIPTION     
            "The admin state of the ISDN B-channel."
    ::= { sonusIsdnsgBchannelEntry 10 }

sonusIsdnsgBchannelTrunkMember OBJECT-TYPE
    SYNTAX          Integer32 (0..65536)
    MAX-ACCESS      read-write
    STATUS          current
    DESCRIPTION     
            "Identifies the Trunk Member number assigned to the B-channel.
             The value 65536 indicates no trunk member number is assigned. "
    DEFVAL          { 65536 }
    ::= { sonusIsdnsgBchannelEntry 11 }

sonusIsdnsgBchannelRowStatus OBJECT-TYPE
    SYNTAX          RowStatus
    MAX-ACCESS      read-write
    STATUS          current
    DESCRIPTION     
            "ISDN interface creation or deletion auto creates or deletes
             B channels. User can't create or delete a B channel. This object
             is added for supporting incremental PIF"
    ::= { sonusIsdnsgBchannelEntry 12 }

sonusIsdnsgBchannelServiceName OBJECT-TYPE
    SYNTAX          SonusNameReference
    MAX-ACCESS      read-write
    STATUS          current
    DESCRIPTION     
            "The ISDN service to which this B-channel belongs to."
    ::= { sonusIsdnsgBchannelEntry 13 }

sonusIsdnsgBchannelStatTable OBJECT-TYPE
    SYNTAX          SEQUENCE OF SonusIsdnsgBchannelStatEntry
    MAX-ACCESS      not-accessible
    STATUS          current
    DESCRIPTION     
            "The Isdnsg B-channel status table describes the status of the B-channels 
             in the indexed ISDN interface. This table is unavailable if the 
             sonusisdnsgServiceGroupStatStatus object indicates that this service group 
             is unavailable."
    ::= { sonusIsdnServiceGroupMIBObjects 6 }

sonusIsdnsgBchannelStatEntry OBJECT-TYPE
    SYNTAX          SonusIsdnsgBchannelStatEntry
    MAX-ACCESS      not-accessible
    STATUS          current
    DESCRIPTION     
            ""
    INDEX           { sonusIsdnsgBchannelStatServiceListIndex, 
                      sonusIsdnsgBchannelStatInterfaceIdentifier, 
                      sonusIsdnsgBchannelStatNumber }
    ::= { sonusIsdnsgBchannelStatTable 1 }

SonusIsdnsgBchannelStatEntry ::=
    SEQUENCE {
        sonusIsdnsgBchannelStatServiceListIndex       Integer32,
        sonusIsdnsgBchannelStatInterfaceIdentifier          Integer32,
        sonusIsdnsgBchannelStatNumber   Integer32,
        sonusIsdnsgBchannelStatUsage    INTEGER,
        sonusIsdnsgBchannelStatLocalMaint INTEGER,
        sonusIsdnsgBchannelStatLocalHw  INTEGER,
        sonusIsdnsgBchannelStatRemoteMaint  INTEGER
    }

sonusIsdnsgBchannelStatServiceListIndex OBJECT-TYPE
    SYNTAX          Integer32
    MAX-ACCESS      read-only
    STATUS          current
    DESCRIPTION     
            "The index of the ISDN Service Group of the ISDN B-channel."
    ::= { sonusIsdnsgBchannelStatEntry 1 }

sonusIsdnsgBchannelStatInterfaceIdentifier OBJECT-TYPE
    SYNTAX          Integer32 (0..127)
    MAX-ACCESS      read-only
    STATUS          current
    DESCRIPTION     
            "The Q931 interface identifier of the ISDN B-channel."
    ::= { sonusIsdnsgBchannelStatEntry 2 }

sonusIsdnsgBchannelStatNumber OBJECT-TYPE
    SYNTAX          Integer32 (1..32)
    MAX-ACCESS      read-only
    STATUS          current
    DESCRIPTION     
            "The channel number of the ISDN B-channel."
    ::= { sonusIsdnsgBchannelStatEntry 3 }

sonusIsdnsgBchannelStatUsage OBJECT-TYPE
    SYNTAX          INTEGER { unequipped(1), idle(2), inBusy(3), 
                        outBusy(4), transientSetup(5), 
                        transientRelease(6) }
    MAX-ACCESS      read-only
    STATUS          current
    DESCRIPTION     
            "The usage state of the ISDN B-channel."
    ::= { sonusIsdnsgBchannelStatEntry 4 }

sonusIsdnsgBchannelStatLocalMaint OBJECT-TYPE
    SYNTAX          INTEGER { inService(1), maintenance(2), 
                        outOfService(3), transientInService(4), 
                        transientMaintenance(5), 
                        transientOutOfService(6), dryup(7), 
                        notAvailable(8) }
    MAX-ACCESS      read-only
    STATUS          current
    DESCRIPTION     
            "The local maintenance state of the ISDN B-channel."
    ::= { sonusIsdnsgBchannelStatEntry 5 }

sonusIsdnsgBchannelStatLocalHw OBJECT-TYPE
    SYNTAX          INTEGER { inService(1), outOfService(2), 
                        transientInService(3), transientOutOfService(4), 
                        notAvailable(5) }
    MAX-ACCESS      read-only
    STATUS          current
    DESCRIPTION     
            "The local hardware state of the ISDN B-channel."
    ::= { sonusIsdnsgBchannelStatEntry 6 }

sonusIsdnsgBchannelStatRemoteMaint OBJECT-TYPE
    SYNTAX          INTEGER { inService(1), maintenance(2), 
                        outOfService(3), transientInService(4), 
                        transientMaintenance(5), 
                        transientOutOfService(6), notAvailable(7), 
                        restarting(8), restartError(9), 
                        autoOutOfService(10) }
    MAX-ACCESS      read-only
    STATUS          current
    DESCRIPTION     
            "The remote maintenance state of the ISDN B-channel."
    ::= { sonusIsdnsgBchannelStatEntry 7 }

sonusIsdnsgSwitchProfile OBJECT IDENTIFIER
    ::= { sonusIsdnServiceGroupMIBObjects 7 }

sonusIsdnsgSwitchProfileNextIndex OBJECT-TYPE
    SYNTAX          Integer32
    MAX-ACCESS      read-only
    STATUS          current
    DESCRIPTION     
            "The next valid index to use when creating a new sonusIsdnsgSwitchProfileEntry"
    ::= { sonusIsdnsgSwitchProfile 1 }

sonusIsdnsgSwitchProfileTable OBJECT-TYPE
    SYNTAX          SEQUENCE OF SonusIsdnsgSwitchProfileEntry
    MAX-ACCESS      not-accessible
    STATUS          current
    DESCRIPTION     
            "This table contains ISDN switch profile information."
    ::= { sonusIsdnsgSwitchProfile 2 }

sonusIsdnsgSwitchProfileEntry OBJECT-TYPE
    SYNTAX          SonusIsdnsgSwitchProfileEntry
    MAX-ACCESS      not-accessible
    STATUS          current
    DESCRIPTION     
            "This table describes the ISDN Switch Profile that are configured
             on the GSX9000."
    INDEX           { sonusIsdnsgSwitchProfileListIndex }
    ::= { sonusIsdnsgSwitchProfileTable 1 }

SonusIsdnsgSwitchProfileEntry ::=
    SEQUENCE {
        sonusIsdnsgSwitchProfileListIndex Integer32,
        sonusIsdnsgSwitchProfileName    SonusName,
        sonusIsdnsgSwitchProfileSwitchSide  INTEGER,
        sonusIsdnsgSwitchProfileSwitchType  INTEGER,
        sonusIsdnsgSwitchProfileBchannelAvailabilitySignaling                     INTEGER,
        sonusIsdnsgSwitchProfileT302    Integer32,
        sonusIsdnsgSwitchProfileT303    Integer32,
        sonusIsdnsgSwitchProfileT304    Integer32,
        sonusIsdnsgSwitchProfileT305    Integer32,
        sonusIsdnsgSwitchProfileT306    Integer32,
        sonusIsdnsgSwitchProfileT308    Integer32,
        sonusIsdnsgSwitchProfileT309    Integer32,
        sonusIsdnsgSwitchProfileT310    Integer32,
        sonusIsdnsgSwitchProfileT312    Integer32,
        sonusIsdnsgSwitchProfileT313    Integer32,
        sonusIsdnsgSwitchProfileT314    Integer32,
        sonusIsdnsgSwitchProfileT318    Integer32,
        sonusIsdnsgSwitchProfileT319    Integer32,
        sonusIsdnsgSwitchProfileT322    Integer32,
        sonusIsdnsgSwitchProfileK       Integer32,
        sonusIsdnsgSwitchProfileT200    Integer32,
        sonusIsdnsgSwitchProfileT203    Integer32,
        sonusIsdnsgSwitchProfileN200    Integer32,
        sonusIsdnsgSwitchProfileN201    Integer32,
        sonusIsdnsgSwitchProfileAdminState  SonusAdminState,
        sonusIsdnsgSwitchProfileRowStatus RowStatus,
        sonusIsdnsgSwitchProfileBchannelInitialRestart              INTEGER,
        sonusIsdnsgSwitchProfileRemoteSwitchType        INTEGER,
        sonusIsdnsgSwitchProfileBchannelNegotiation           INTEGER,
        sonusIsdnsgSwitchProfileT307    Integer32
    }

sonusIsdnsgSwitchProfileListIndex OBJECT-TYPE
    SYNTAX          Integer32 (1..128)
    MAX-ACCESS      read-only
    STATUS          current
    DESCRIPTION     
            "The index of the ISDN Switch Profile entry."
    ::= { sonusIsdnsgSwitchProfileEntry 1 }

sonusIsdnsgSwitchProfileName OBJECT-TYPE
    SYNTAX          SonusName
    MAX-ACCESS      read-write
    STATUS          current
    DESCRIPTION     
            "The name of the ISDN Switch Profile."
    ::= { sonusIsdnsgSwitchProfileEntry 2 }

sonusIsdnsgSwitchProfileSwitchSide OBJECT-TYPE
    SYNTAX          INTEGER { network(1), user(2) }
    MAX-ACCESS      read-write
    STATUS          current
    DESCRIPTION     
            "The switch side the ISDN Switch Profile should act as."
    DEFVAL          { network }
    ::= { sonusIsdnsgSwitchProfileEntry 3 }

sonusIsdnsgSwitchProfileSwitchType OBJECT-TYPE
    SYNTAX          INTEGER { ni2(1), dms250(2), dms100(3), 
                        lucent5ESS(4), lucent4ESS(5), euroIsdn(6), 
                        ins1500(7), tr41459(8) }
    MAX-ACCESS      read-write
    STATUS          current
    DESCRIPTION     
            "The network switch type where the ISDN Switch Profile resides."
    DEFVAL          { ni2 }
    ::= { sonusIsdnsgSwitchProfileEntry 4 }

sonusIsdnsgSwitchProfileBchannelAvailabilitySignaling OBJECT-TYPE
    SYNTAX          INTEGER { yes(1), no(2) }
    MAX-ACCESS      read-write
    STATUS          current
    DESCRIPTION     
            "Used to enable or disable the B-channel availability signaling procedures."
    DEFVAL          { yes }
    ::= { sonusIsdnsgSwitchProfileEntry 5 }

sonusIsdnsgSwitchProfileT302 OBJECT-TYPE
    SYNTAX          Integer32 (0..127)
    MAX-ACCESS      read-write
    STATUS          current
    DESCRIPTION     
            "This T302 of Q.931 timer is used for both user and network sides."
    DEFVAL          { 10 }
    ::= { sonusIsdnsgSwitchProfileEntry 6 }

sonusIsdnsgSwitchProfileT303 OBJECT-TYPE
    SYNTAX          Integer32 (0..127)
    MAX-ACCESS      read-write
    STATUS          current
    DESCRIPTION     
            "This T303 of Q.931 timer is used for both user and network sides."
    DEFVAL          { 4 }
    ::= { sonusIsdnsgSwitchProfileEntry 7 }

sonusIsdnsgSwitchProfileT304 OBJECT-TYPE
    SYNTAX          Integer32 (0..127)
    MAX-ACCESS      read-write
    STATUS          current
    DESCRIPTION     
            "This T304 of Q.931 timer is used for both user and network sides."
    DEFVAL          { 15 }
    ::= { sonusIsdnsgSwitchProfileEntry 8 }

sonusIsdnsgSwitchProfileT305 OBJECT-TYPE
    SYNTAX          Integer32 (0..127)
    MAX-ACCESS      read-write
    STATUS          current
    DESCRIPTION     
            "This T305 of Q.931 timer is used for both user and network sides."
    DEFVAL          { 30 }
    ::= { sonusIsdnsgSwitchProfileEntry 9 }

sonusIsdnsgSwitchProfileT306 OBJECT-TYPE
    SYNTAX          Integer32 (0..127)
    MAX-ACCESS      read-write
    STATUS          current
    DESCRIPTION     
            "This T306 of Q.931 timer is used for network side only."
    DEFVAL          { 60 }
    ::= { sonusIsdnsgSwitchProfileEntry 10 }

sonusIsdnsgSwitchProfileT308 OBJECT-TYPE
    SYNTAX          Integer32 (0..127)
    MAX-ACCESS      read-write
    STATUS          current
    DESCRIPTION     
            "This T308 of Q.931 timer is used for both user and network sides."
    DEFVAL          { 4 }
    ::= { sonusIsdnsgSwitchProfileEntry 11 }

sonusIsdnsgSwitchProfileT309 OBJECT-TYPE
    SYNTAX          Integer32 (0..127)
    MAX-ACCESS      read-write
    STATUS          current
    DESCRIPTION     
            "This T309 of Q.931 timer is used for both user and network sides."
    DEFVAL          { 90 }
    ::= { sonusIsdnsgSwitchProfileEntry 12 }

sonusIsdnsgSwitchProfileT310 OBJECT-TYPE
    SYNTAX          Integer32 (0..127)
    MAX-ACCESS      read-write
    STATUS          current
    DESCRIPTION     
            "This T310 of Q.931 timer is used for both user and network sides."
    DEFVAL          { 10 }
    ::= { sonusIsdnsgSwitchProfileEntry 13 }

sonusIsdnsgSwitchProfileT312 OBJECT-TYPE
    SYNTAX          Integer32 (0..127)
    MAX-ACCESS      read-write
    STATUS          current
    DESCRIPTION     
            "This T312 of Q.931 timer is used for network side only."
    DEFVAL          { 5 }
    ::= { sonusIsdnsgSwitchProfileEntry 14 }

sonusIsdnsgSwitchProfileT313 OBJECT-TYPE
    SYNTAX          Integer32 (0..127)
    MAX-ACCESS      read-write
    STATUS          current
    DESCRIPTION     
            "This T313 of Q.931 timer is used for user side only."
    DEFVAL          { 0 }
    ::= { sonusIsdnsgSwitchProfileEntry 15 }

sonusIsdnsgSwitchProfileT314 OBJECT-TYPE
    SYNTAX          Integer32 (0..127)
    MAX-ACCESS      read-write
    STATUS          current
    DESCRIPTION     
            "This T314 of Q.931 timer is used for both user and network sides"
    DEFVAL          { 0 }
    ::= { sonusIsdnsgSwitchProfileEntry 16 }

sonusIsdnsgSwitchProfileT318 OBJECT-TYPE
    SYNTAX          Integer32 (0..127)
    MAX-ACCESS      read-write
    STATUS          current
    DESCRIPTION     
            "This T318 of Q.931 timer is used for user side only."
    DEFVAL          { 0 }
    ::= { sonusIsdnsgSwitchProfileEntry 17 }

sonusIsdnsgSwitchProfileT319 OBJECT-TYPE
    SYNTAX          Integer32 (0..127)
    MAX-ACCESS      read-write
    STATUS          current
    DESCRIPTION     
            "This T319 of Q.931 timer is used for user side only."
    DEFVAL          { 0 }
    ::= { sonusIsdnsgSwitchProfileEntry 18 }

sonusIsdnsgSwitchProfileT322 OBJECT-TYPE
    SYNTAX          Integer32 (0..127)
    MAX-ACCESS      read-write
    STATUS          current
    DESCRIPTION     
            "This T322 of Q.931 timer is used for network side only."
    DEFVAL          { 4 }
    ::= { sonusIsdnsgSwitchProfileEntry 19 }

sonusIsdnsgSwitchProfileK OBJECT-TYPE
    SYNTAX          Integer32 (1..127)
    MAX-ACCESS      read-write
    STATUS          current
    DESCRIPTION     
            "The maximum number of outstanding I frames. This K of Q.921 parameter is used for both user and network sides."
    DEFVAL          { 7 }
    ::= { sonusIsdnsgSwitchProfileEntry 20 }

sonusIsdnsgSwitchProfileT200 OBJECT-TYPE
    SYNTAX          Integer32 (1..255)
    MAX-ACCESS      read-write
    STATUS          current
    DESCRIPTION     
            "This T200 of Q.921 timer is used for both user and network sides."
    DEFVAL          { 1 }
    ::= { sonusIsdnsgSwitchProfileEntry 21 }

sonusIsdnsgSwitchProfileT203 OBJECT-TYPE
    SYNTAX          Integer32 (0..255)
    MAX-ACCESS      read-write
    STATUS          current
    DESCRIPTION     
            "This T203 of Q.921 timer is used for both user and network sides."
    DEFVAL          { 10 }
    ::= { sonusIsdnsgSwitchProfileEntry 22 }

sonusIsdnsgSwitchProfileN200 OBJECT-TYPE
    SYNTAX          Integer32 (1..100)
    MAX-ACCESS      read-write
    STATUS          current
    DESCRIPTION     
            "The maximum number of retransmissions of a frame. This N200 of Q.921 parameter is used for both user and network sides."
    DEFVAL          { 3 }
    ::= { sonusIsdnsgSwitchProfileEntry 23 }

sonusIsdnsgSwitchProfileN201 OBJECT-TYPE
    SYNTAX          Integer32 (1..260)
    MAX-ACCESS      read-write
    STATUS          current
    DESCRIPTION     
            "The maximum number of octets in an information field. This N201 of Q.921 parameter is used for both user and network sides."
    DEFVAL          { 260 }
    ::= { sonusIsdnsgSwitchProfileEntry 24 }

sonusIsdnsgSwitchProfileAdminState OBJECT-TYPE
    SYNTAX          SonusAdminState
    MAX-ACCESS      read-write
    STATUS          current
    DESCRIPTION     
            "The admin state of the ISDN Switch Profile."
    DEFVAL          { disabled }
    ::= { sonusIsdnsgSwitchProfileEntry 25 }

sonusIsdnsgSwitchProfileRowStatus OBJECT-TYPE
    SYNTAX          RowStatus
    MAX-ACCESS      read-write
    STATUS          current
    DESCRIPTION     
            "The row status of the ISDN Switch Profile."
    ::= { sonusIsdnsgSwitchProfileEntry 26 }

sonusIsdnsgSwitchProfileBchannelInitialRestart OBJECT-TYPE
    SYNTAX          INTEGER { yes(1), no(2), allInterfaces(3) }
    MAX-ACCESS      read-write
    STATUS          current
    DESCRIPTION     
            "Controls wether RESTARTs are used to initially bring channels into service"
    DEFVAL          { yes }
    ::= { sonusIsdnsgSwitchProfileEntry 27 }

sonusIsdnsgSwitchProfileRemoteSwitchType OBJECT-TYPE
    SYNTAX          INTEGER { default(1), meridian(2), ocnrn(3), 
                        ocnrnpresentation(4), custommap(5), 
                        cpnrestrictedoverride(6), pi8inalert(7), 
                        noinbandinfo(8), atttcs(9), noprogafteralert(10) }
    MAX-ACCESS      read-write
    STATUS          current
    DESCRIPTION     
            "The remote switch type.  This should only be set to something other 
             than default if the remote switch type has unique behavior.  Currently, 
             the unique behaviors are:
                meridian: 
                    The Meridian PBX incorrectly rejects the Channel ID information
                    element when the extension bit is set correctly.  When this
                    object is set to meridian, the extension bit will not be 
                    set in the Channel ID information element.
             			ocnrn:
             				For 4ess and 5ess switch types, support both the Original
             				Called Number IE and the Redirecting Number IE.
             			ocnrnpresentation
             				Forces number presentation for the Original Called Number
             				IE and the Redirecting Number IE.  
             			custommap
             				Forces number presentation for the Original Called Number
             				IE and the Redirecting Number IE.  Also sends a DISCONNECT
             				instead of a PROGRESS with a cause IE.
                     cpn_restricted_override:
             				For INS1500 switch type. Present the calling number when
             				presentation is restricted. This option leaves the presentation
             				indication as restricted. This option cannot be used if 
             				the PSX option FORCED CLIP is enabled.
             			pi8inalert:
             				Allow progress indicator #8 in ALERT message.
             				This affects all switch types.
             			noinbandinfo:
             				Prohibit progress indicator #8 in ALERT message.
             				This affects all switch types.
             			atttcs
             				Support AT&T Transfer Connect Service.  Enables interworking
             				of the FACILITY message, Network Specific Facility IE and
             				MAUUI.
             			noprogafteralert
             				For user side, avoid sending PROGRESS message after an ALERT."
    DEFVAL          { default }
    ::= { sonusIsdnsgSwitchProfileEntry 28 }

sonusIsdnsgSwitchProfileBchannelNegotiation OBJECT-TYPE
    SYNTAX          INTEGER { yes(1), no(2) }
    MAX-ACCESS      read-write
    STATUS          obsolete
    DESCRIPTION     
            "Used to enable or disable the B-channel negotiation signaling procedures.
             This object is not used and was made obsolete in GSX release 6.4.
             BChannel Negotiation Configuration has now moved to ISDN Service Profile."
    ::= { sonusIsdnsgSwitchProfileEntry 29 }

sonusIsdnsgSwitchProfileT307 OBJECT-TYPE
    SYNTAX          Integer32 (60..360)
    MAX-ACCESS      read-write
    STATUS          current
    DESCRIPTION     
            "This T307 of Q.931 timer is used for network side"
    DEFVAL          { 180 }
    ::= { sonusIsdnsgSwitchProfileEntry 30 }

sonusIsdnsgDChannelTest OBJECT IDENTIFIER
    ::= { sonusIsdnServiceGroupMIBObjects 8 }

sonusIsdnsgDChannelTestNextIndex OBJECT-TYPE
    SYNTAX          Integer32
    MAX-ACCESS      read-only
    STATUS          current
    DESCRIPTION     
            "The next valid index to use when creating a new sonusIsdnsgDChannelTestEntry"
    ::= { sonusIsdnsgDChannelTest 1 }

sonusIsdnsgDChannelTestTable OBJECT-TYPE
    SYNTAX          SEQUENCE OF SonusIsdnsgDChannelTestEntry
    MAX-ACCESS      not-accessible
    STATUS          current
    DESCRIPTION     
            "This table contains ISDN switch profile information."
    ::= { sonusIsdnsgDChannelTest 2 }

sonusIsdnsgDChannelTestEntry OBJECT-TYPE
    SYNTAX          SonusIsdnsgDChannelTestEntry
    MAX-ACCESS      not-accessible
    STATUS          current
    DESCRIPTION     
            "This table describes the ISDN Switch Profile that are configured
             on the GSX9000."
    INDEX           { sonusIsdnsgDChannelTestListAdmnIndex }
    ::= { sonusIsdnsgDChannelTestTable 1 }

SonusIsdnsgDChannelTestEntry ::=
    SEQUENCE {
        sonusIsdnsgDChannelTestListAdmnIndex    Integer32,
        sonusIsdnsgDChannelTestAdmnName SonusName,
        sonusIsdnsgDChannelTestAdmnState SonusAdminState,
        sonusIsdnsgDChannelTestEndpointAdmnInDialNumber               DisplayString,
        sonusIsdnsgDChannelTestEndpointAdmnOutDialNumber                DisplayString,
        sonusIsdnsgDChannelTestAdmnRouteNumType       INTEGER,
        sonusIsdnsgDChannelTestAdmnRouteNumPlan       INTEGER,
        sonusIsdnsgDChannelTestAdmnMode INTEGER,
        sonusIsdnsgDChannelTestAdmnDChannelService          SonusNameReference,
        sonusIsdnsgDChannelTestAdmnDChannel   INTEGER,
        sonusIsdnsgDChannelTestAdmnBillingNumber        DisplayString,
        sonusIsdnsgDChannelTestAdmnBillingNumType         INTEGER,
        sonusIsdnsgDChannelTestAdmnBillingNumPlan         INTEGER,
        sonusIsdnsgDChannelTestAdmnOli  Integer32,
        sonusIsdnsgDChannelTestAdmnTrunkGroup     SonusNameReference,
        sonusIsdnsgDChannelTestAdmnRowStatus    RowStatus
    }

sonusIsdnsgDChannelTestListAdmnIndex OBJECT-TYPE
    SYNTAX          Integer32 (1..128)
    MAX-ACCESS      read-only
    STATUS          current
    DESCRIPTION     
            "The index of the D Channel Test Session"
    ::= { sonusIsdnsgDChannelTestEntry 1 }

sonusIsdnsgDChannelTestAdmnName OBJECT-TYPE
    SYNTAX          SonusName
    MAX-ACCESS      read-write
    STATUS          current
    DESCRIPTION     
            "The name of the D Channel Test Session"
    ::= { sonusIsdnsgDChannelTestEntry 2 }

sonusIsdnsgDChannelTestAdmnState OBJECT-TYPE
    SYNTAX          SonusAdminState
    MAX-ACCESS      read-write
    STATUS          current
    DESCRIPTION     
            "The administrative state of the D Channel Test Session"
    DEFVAL          { disabled }
    ::= { sonusIsdnsgDChannelTestEntry 3 }

sonusIsdnsgDChannelTestEndpointAdmnInDialNumber OBJECT-TYPE
    SYNTAX          DisplayString (SIZE(0..30))
    MAX-ACCESS      read-write
    STATUS          current
    DESCRIPTION     
            "The dial in number for the D Channel Test Session"
    ::= { sonusIsdnsgDChannelTestEntry 4 }

sonusIsdnsgDChannelTestEndpointAdmnOutDialNumber OBJECT-TYPE
    SYNTAX          DisplayString (SIZE(0..30))
    MAX-ACCESS      read-write
    STATUS          current
    DESCRIPTION     
            "The dial out number for the D Channel Test Session"
    ::= { sonusIsdnsgDChannelTestEntry 5 }

sonusIsdnsgDChannelTestAdmnRouteNumType OBJECT-TYPE
    SYNTAX          INTEGER { unknown(1), national(2), international(3), 
                        subs(4) }
    MAX-ACCESS      read-write
    STATUS          current
    DESCRIPTION     
            "The number type"
    DEFVAL          { national }
    ::= { sonusIsdnsgDChannelTestEntry 6 }

sonusIsdnsgDChannelTestAdmnRouteNumPlan OBJECT-TYPE
    SYNTAX          INTEGER { unknown(1), isdn(2), private(3) }
    MAX-ACCESS      read-write
    STATUS          current
    DESCRIPTION     
            "The numbering plan"
    DEFVAL          { isdn }
    ::= { sonusIsdnsgDChannelTestEntry 7 }

sonusIsdnsgDChannelTestAdmnMode OBJECT-TYPE
    SYNTAX          INTEGER { split(1), monitor(2) }
    MAX-ACCESS      read-write
    STATUS          current
    DESCRIPTION     
            "The D channel Test Session mode"
    DEFVAL          { monitor }
    ::= { sonusIsdnsgDChannelTestEntry 8 }

sonusIsdnsgDChannelTestAdmnDChannelService OBJECT-TYPE
    SYNTAX          SonusNameReference
    MAX-ACCESS      read-write
    STATUS          current
    DESCRIPTION     
            "The name of the service D channel is on."
    ::= { sonusIsdnsgDChannelTestEntry 9 }

sonusIsdnsgDChannelTestAdmnDChannel OBJECT-TYPE
    SYNTAX          INTEGER { primary(1), backup(2) }
    MAX-ACCESS      read-write
    STATUS          current
    DESCRIPTION     
            "The D channel to test"
    DEFVAL          { primary }
    ::= { sonusIsdnsgDChannelTestEntry 10 }

sonusIsdnsgDChannelTestAdmnBillingNumber OBJECT-TYPE
    SYNTAX          DisplayString (SIZE(0..30))
    MAX-ACCESS      read-write
    STATUS          current
    DESCRIPTION     
            "The billing number"
    DEFVAL          { "3693280000" }
    ::= { sonusIsdnsgDChannelTestEntry 11 }

sonusIsdnsgDChannelTestAdmnBillingNumType OBJECT-TYPE
    SYNTAX          INTEGER { unknown(1), national(2), international(3), 
                        subs(4) }
    MAX-ACCESS      read-write
    STATUS          current
    DESCRIPTION     
            "The billing number type"
    DEFVAL          { national }
    ::= { sonusIsdnsgDChannelTestEntry 12 }

sonusIsdnsgDChannelTestAdmnBillingNumPlan OBJECT-TYPE
    SYNTAX          INTEGER { unknown(1), isdn(2), private(3) }
    MAX-ACCESS      read-write
    STATUS          current
    DESCRIPTION     
            "The billing number type"
    DEFVAL          { isdn }
    ::= { sonusIsdnsgDChannelTestEntry 13 }

sonusIsdnsgDChannelTestAdmnOli OBJECT-TYPE
    SYNTAX          Integer32 (0..255)
    MAX-ACCESS      read-write
    STATUS          current
    DESCRIPTION     
            "OLI delivery value"
    DEFVAL          { 41 }
    ::= { sonusIsdnsgDChannelTestEntry 14 }

sonusIsdnsgDChannelTestAdmnTrunkGroup OBJECT-TYPE
    SYNTAX          SonusNameReference
    MAX-ACCESS      read-write
    STATUS          current
    DESCRIPTION     
            "The Trunk Group used by the PSX to lookup the route.  It should have the name of a test trunk group"
    ::= { sonusIsdnsgDChannelTestEntry 15 }

sonusIsdnsgDChannelTestAdmnRowStatus OBJECT-TYPE
    SYNTAX          RowStatus
    MAX-ACCESS      read-write
    STATUS          current
    DESCRIPTION     
            ""
    ::= { sonusIsdnsgDChannelTestEntry 16 }

sonusIsdnsgDChannelTestStatTable OBJECT-TYPE
    SYNTAX          SEQUENCE OF SonusIsdnsgDChannelTestStatEntry
    MAX-ACCESS      not-accessible
    STATUS          current
    DESCRIPTION     
            "This table contains status information about each ISDN service group
             D channel test session."
    ::= { sonusIsdnServiceGroupMIBObjects 9 }

sonusIsdnsgDChannelTestStatEntry OBJECT-TYPE
    SYNTAX          SonusIsdnsgDChannelTestStatEntry
    MAX-ACCESS      not-accessible
    STATUS          current
    DESCRIPTION     
            "This table contains status information about each ISDN service group
             D channel test session."
    INDEX           { sonusIsdnsgDChannelTestStatListIndex }
    ::= { sonusIsdnsgDChannelTestStatTable 1 }

SonusIsdnsgDChannelTestStatEntry ::=
    SEQUENCE {
        sonusIsdnsgDChannelTestStatListIndex    Integer32,
        sonusIsdnsgDChannelTestStatState DisplayString,
        sonusIsdnsgDChannelTestStatError DisplayString,
        sonusIsdnsgOutCallDChannelTestState   DisplayString,
        sonusIsdnsgOutCallDChannelTestStatError       DisplayString,
        sonusIsdnsgOutCallDisconnectReason  Integer32,
        sonusIsdnsgOutCallDisconnectLocation    Integer32,
        sonusIsdnsgOutCallDChannelTestStatAccRecord           DisplayString,
        sonusIsdnsgOutCallRouteLabel    DisplayString,
        sonusIsdnsgOutCallEgressPSTNCircuit   DisplayString,
        sonusIsdnsgOutCallEgressTrunkGroupName      DisplayString,
        sonusIsdnsgOutCallGCID          Integer32,
        sonusIsdnsgInCallDChannelTestState  DisplayString,
        sonusIsdnsgInCallDChannelTestStatError      DisplayString,
        sonusIsdnsgInCallDisconnectReason Integer32,
        sonusIsdnsgInCallDisconnectLocation   Integer32,
        sonusIsdnsgInCallDChannelTestStatAccRecord          DisplayString,
        sonusIsdnsgInCallRouteLabel     DisplayString,
        sonusIsdnsgInCallEgressPSTNCircuit  DisplayString,
        sonusIsdnsgInCallEgressTrunkGroupName     DisplayString,
        sonusIsdnsgInCallGCID           Integer32
    }

sonusIsdnsgDChannelTestStatListIndex OBJECT-TYPE
    SYNTAX          Integer32
    MAX-ACCESS      read-only
    STATUS          current
    DESCRIPTION     
            ""
    ::= { sonusIsdnsgDChannelTestStatEntry 1 }

sonusIsdnsgDChannelTestStatState OBJECT-TYPE
    SYNTAX          DisplayString (SIZE(0..23))
    MAX-ACCESS      read-only
    STATUS          current
    DESCRIPTION     
            "The state of the test session"
    ::= { sonusIsdnsgDChannelTestStatEntry 2 }

sonusIsdnsgDChannelTestStatError OBJECT-TYPE
    SYNTAX          DisplayString (SIZE(0..23))
    MAX-ACCESS      read-only
    STATUS          current
    DESCRIPTION     
            "The error (if any) encountered in the test session"
    ::= { sonusIsdnsgDChannelTestStatEntry 3 }

sonusIsdnsgOutCallDChannelTestState OBJECT-TYPE
    SYNTAX          DisplayString (SIZE(0..23))
    MAX-ACCESS      read-only
    STATUS          current
    DESCRIPTION     
            "The state of the outgoing call"
    ::= { sonusIsdnsgDChannelTestStatEntry 4 }

sonusIsdnsgOutCallDChannelTestStatError OBJECT-TYPE
    SYNTAX          DisplayString (SIZE(0..23))
    MAX-ACCESS      read-only
    STATUS          current
    DESCRIPTION     
            "The error ( if any) encountered during outgoing call setup"
    ::= { sonusIsdnsgDChannelTestStatEntry 5 }

sonusIsdnsgOutCallDisconnectReason OBJECT-TYPE
    SYNTAX          Integer32
    MAX-ACCESS      read-only
    STATUS          current
    DESCRIPTION     
            "The reason for the outgoing call disconnect"
    ::= { sonusIsdnsgDChannelTestStatEntry 6 }

sonusIsdnsgOutCallDisconnectLocation OBJECT-TYPE
    SYNTAX          Integer32
    MAX-ACCESS      read-only
    STATUS          current
    DESCRIPTION     
            "The disconnect location of the outgoing call"
    ::= { sonusIsdnsgDChannelTestStatEntry 7 }

sonusIsdnsgOutCallDChannelTestStatAccRecord OBJECT-TYPE
    SYNTAX          DisplayString (SIZE(0..23))
    MAX-ACCESS      read-only
    STATUS          current
    DESCRIPTION     
            "The accounting record of the outgoing call"
    ::= { sonusIsdnsgDChannelTestStatEntry 8 }

sonusIsdnsgOutCallRouteLabel OBJECT-TYPE
    SYNTAX          DisplayString (SIZE(0..23))
    MAX-ACCESS      read-only
    STATUS          current
    DESCRIPTION     
            "The routing label of the outgoing call"
    ::= { sonusIsdnsgDChannelTestStatEntry 9 }

sonusIsdnsgOutCallEgressPSTNCircuit OBJECT-TYPE
    SYNTAX          DisplayString (SIZE(0..47))
    MAX-ACCESS      read-only
    STATUS          current
    DESCRIPTION     
            "The egress PSTN circuit of the outgoing call"
    ::= { sonusIsdnsgDChannelTestStatEntry 10 }

sonusIsdnsgOutCallEgressTrunkGroupName OBJECT-TYPE
    SYNTAX          DisplayString (SIZE(0..23))
    MAX-ACCESS      read-only
    STATUS          current
    DESCRIPTION     
            "The egress trunk name of the outgoing call"
    ::= { sonusIsdnsgDChannelTestStatEntry 11 }

sonusIsdnsgOutCallGCID OBJECT-TYPE
    SYNTAX          Integer32
    MAX-ACCESS      read-only
    STATUS          current
    DESCRIPTION     
            "The GCID associated with the outgoing call"
    ::= { sonusIsdnsgDChannelTestStatEntry 12 }

sonusIsdnsgInCallDChannelTestState OBJECT-TYPE
    SYNTAX          DisplayString (SIZE(0..23))
    MAX-ACCESS      read-only
    STATUS          current
    DESCRIPTION     
            "The state of the incoming call"
    ::= { sonusIsdnsgDChannelTestStatEntry 13 }

sonusIsdnsgInCallDChannelTestStatError OBJECT-TYPE
    SYNTAX          DisplayString (SIZE(0..23))
    MAX-ACCESS      read-only
    STATUS          current
    DESCRIPTION     
            "The error (if any) encountered in the incoming call"
    ::= { sonusIsdnsgDChannelTestStatEntry 14 }

sonusIsdnsgInCallDisconnectReason OBJECT-TYPE
    SYNTAX          Integer32
    MAX-ACCESS      read-only
    STATUS          current
    DESCRIPTION     
            "The reason for the incoming call disconnect"
    ::= { sonusIsdnsgDChannelTestStatEntry 15 }

sonusIsdnsgInCallDisconnectLocation OBJECT-TYPE
    SYNTAX          Integer32
    MAX-ACCESS      read-only
    STATUS          current
    DESCRIPTION     
            "The disconnect location of the incoming call"
    ::= { sonusIsdnsgDChannelTestStatEntry 16 }

sonusIsdnsgInCallDChannelTestStatAccRecord OBJECT-TYPE
    SYNTAX          DisplayString (SIZE(0..23))
    MAX-ACCESS      read-only
    STATUS          current
    DESCRIPTION     
            "The accounting record of the incoming call"
    ::= { sonusIsdnsgDChannelTestStatEntry 17 }

sonusIsdnsgInCallRouteLabel OBJECT-TYPE
    SYNTAX          DisplayString (SIZE(0..23))
    MAX-ACCESS      read-only
    STATUS          current
    DESCRIPTION     
            "The routing label of the incoming call"
    ::= { sonusIsdnsgDChannelTestStatEntry 18 }

sonusIsdnsgInCallEgressPSTNCircuit OBJECT-TYPE
    SYNTAX          DisplayString (SIZE(0..47))
    MAX-ACCESS      read-only
    STATUS          current
    DESCRIPTION     
            "The egress PSTN circuit of the incoming call"
    ::= { sonusIsdnsgDChannelTestStatEntry 19 }

sonusIsdnsgInCallEgressTrunkGroupName OBJECT-TYPE
    SYNTAX          DisplayString (SIZE(0..23))
    MAX-ACCESS      read-only
    STATUS          current
    DESCRIPTION     
            "The egress trunk name of the incoming call"
    ::= { sonusIsdnsgDChannelTestStatEntry 20 }

sonusIsdnsgInCallGCID OBJECT-TYPE
    SYNTAX          Integer32
    MAX-ACCESS      read-only
    STATUS          current
    DESCRIPTION     
            "The GCID associated with the incoming call"
    ::= { sonusIsdnsgDChannelTestStatEntry 21 }

sonusIsdnServiceGroupMIBNotifications OBJECT IDENTIFIER
    ::= { sonusIsdnServiceGroupMIB 2 }

sonusIsdnServiceGroupMIBNotificationsPrefix OBJECT IDENTIFIER
    ::= { sonusIsdnServiceGroupMIBNotifications 0 }

sonusIsdnServiceGroupMIBNotificationsObjects OBJECT IDENTIFIER
    ::= { sonusIsdnServiceGroupMIBNotifications 1 }

sonusIsdnSvcGrpName OBJECT-TYPE
    SYNTAX          DisplayString (SIZE(0..23))
    MAX-ACCESS      read-only
    STATUS          current
    DESCRIPTION     
            "Name of the ISDN service group."
    ::= { sonusIsdnServiceGroupMIBNotificationsObjects 1 }

sonusIsdnInterfaceId OBJECT-TYPE
    SYNTAX          Integer32 (0..127)
    MAX-ACCESS      read-only
    STATUS          current
    DESCRIPTION     
            "The Q931 interface identifier of the ISDN interface."
    ::= { sonusIsdnServiceGroupMIBNotificationsObjects 2 }

sonusIsdnBchannelOffsets OBJECT-TYPE
    SYNTAX          BITS { bchOffset0(0), bchOffset1(1), bchOffset2(2), 
                        bchOffset3(3), bchOffset4(4), bchOffset5(5), 
                        bchOffset6(6), bchOffset7(7), bchOffset8(8), 
                        bchOffset9(9), bchOffset10(10), bchOffset11(11), 
                        bchOffset12(12), bchOffset13(13), 
                        bchOffset14(14), bchOffset15(15), 
                        bchOffset16(16), bchOffset17(17), 
                        bchOffset18(18), bchOffset19(19), 
                        bchOffset20(20), bchOffset21(21), 
                        bchOffset22(22), bchOffset23(23), 
                        bchOffset24(24), bchOffset25(25), 
                        bchOffset26(26), bchOffset27(27), 
                        bchOffset28(28), bchOffset29(29), 
                        bchOffset30(30), bchOffset31(31) }
    MAX-ACCESS      read-only
    STATUS          current
    DESCRIPTION     
            "B-channel maintenance status bitmap."
    ::= { sonusIsdnServiceGroupMIBNotificationsObjects 3 }

sonusIsdnSvcGrpInServiceNotification NOTIFICATION-TYPE
    OBJECTS         { sonusIsdnSvcGrpName, sonusEventDescription, 
                      sonusEventClass, sonusEventLevel, sonusSequenceId, 
                      sonusEventTime }
    STATUS          current
    DESCRIPTION     
            "This trap indicates that the specified ISDN Service Group
             was placed in service."
    ::= { sonusIsdnServiceGroupMIBNotificationsPrefix 1 }

sonusIsdnSvcGrpOutOfServiceNotification NOTIFICATION-TYPE
    OBJECTS         { sonusIsdnSvcGrpName, sonusEventDescription, 
                      sonusEventClass, sonusEventLevel, sonusSequenceId, 
                      sonusEventTime }
    STATUS          current
    DESCRIPTION     
            "This trap indicates that the specified ISDN Service Group
             was taken out of service."
    ::= { sonusIsdnServiceGroupMIBNotificationsPrefix 2 }

sonusIsdnBChannelInServiceNotification NOTIFICATION-TYPE
    OBJECTS         { sonusIsdnSvcGrpName, sonusIsdnInterfaceId, 
                      sonusIsdnBchannelOffsets, sonusEventDescription, 
                      sonusEventClass, sonusEventLevel, sonusSequenceId, 
                      sonusEventTime }
    STATUS          current
    DESCRIPTION     
            "This trap indicates that the specified ISDN B Channels
             are placed in service."
    ::= { sonusIsdnServiceGroupMIBNotificationsPrefix 3 }

sonusIsdnBChannelOutOfServiceNotification NOTIFICATION-TYPE
    OBJECTS         { sonusIsdnSvcGrpName, sonusIsdnInterfaceId, 
                      sonusIsdnBchannelOffsets, sonusEventDescription, 
                      sonusEventClass, sonusEventLevel, sonusSequenceId, 
                      sonusEventTime }
    STATUS          current
    DESCRIPTION     
            "This trap indicates that the specified ISDN B Channels
             are taken out of service."
    ::= { sonusIsdnServiceGroupMIBNotificationsPrefix 4 }

sonusIsdnPrimaryDChannelInServiceNotification NOTIFICATION-TYPE
    OBJECTS         { sonusIsdnSvcGrpName, sonusEventDescription, 
                      sonusEventClass, sonusEventLevel, sonusSequenceId, 
                      sonusEventTime }
    STATUS          current
    DESCRIPTION     
            "This trap indicates that the Primary D Channel for the
             specified ISDN Service Group was placed in service."
    ::= { sonusIsdnServiceGroupMIBNotificationsPrefix 5 }

sonusIsdnPrimaryDChannelOutOfServiceNotification NOTIFICATION-TYPE
    OBJECTS         { sonusIsdnSvcGrpName, sonusEventDescription, 
                      sonusEventClass, sonusEventLevel, sonusSequenceId, 
                      sonusEventTime }
    STATUS          current
    DESCRIPTION     
            "This trap indicates that the Primary D Channel for the
             specified ISDN Service Group was taken out of service."
    ::= { sonusIsdnServiceGroupMIBNotificationsPrefix 6 }

sonusIsdnBackupDChannelInServiceNotification NOTIFICATION-TYPE
    OBJECTS         { sonusIsdnSvcGrpName, sonusEventDescription, 
                      sonusEventClass, sonusEventLevel, sonusSequenceId, 
                      sonusEventTime }
    STATUS          current
    DESCRIPTION     
            "This trap indicates that the Backup D Channel for the
             specified ISDN Service Group was placed in service."
    ::= { sonusIsdnServiceGroupMIBNotificationsPrefix 7 }

sonusIsdnBackupDChannelOutOfServiceNotification NOTIFICATION-TYPE
    OBJECTS         { sonusIsdnSvcGrpName, sonusEventDescription, 
                      sonusEventClass, sonusEventLevel, sonusSequenceId, 
                      sonusEventTime }
    STATUS          current
    DESCRIPTION     
            "This trap indicates that the Backup D Channel for the
             specified ISDN Service Group was taken out of service."
    ::= { sonusIsdnServiceGroupMIBNotificationsPrefix 8 }

END -- end of module SONUS-ISDN-SERVICE-GROUP-MIB.
