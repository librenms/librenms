--
-- This SMIv2 module has been generated by smidump 0.2-cvs. Do not edit.
--

SONUS-SECURITY-MIB DEFINITIONS ::= BEGIN

IMPORTS
    Ipv6Address
        FROM IPV6-TC
    Counter32, Integer32, IpAddress, MODULE-IDENTITY, OBJECT-TYPE, 
    Unsigned32
        FROM SNMPv2-SMI
    DisplayString, RowStatus
        FROM SNMPv2-TC
    sonusServicesMIBs
        FROM SONUS-SMI
    SonusAdminState, SonusBoolean, SonusName, SonusNameReference, 
    SonusShelfIndex, SonusSlotIndex, SonusTlsCipherSuite
        FROM SONUS-TC;

sonusSecurityMIB MODULE-IDENTITY
    LAST-UPDATED    "201010030000Z"
    ORGANIZATION    
            "Sonus Networks, Inc."
    CONTACT-INFO    
            "   Customer Support    
             Sonus Networks, Inc.
             7 Technology Park Drive
             Westford, MA 01886
             USA
             
             Tel: 978-614-8100
             Fax: 978-614-8609"
    DESCRIPTION     
            "The MIB Module for Security Management."
    ::= { sonusServicesMIBs 26 }


sonusSecurityMIBObjects OBJECT IDENTIFIER
    ::= { sonusSecurityMIB 1 }

sonusSecuritySSH OBJECT IDENTIFIER
    ::= { sonusSecurityMIBObjects 1 }

sonusSecuritySSHKeysHostAction OBJECT-TYPE
    SYNTAX          INTEGER { delete(1), generate(2) }
    MAX-ACCESS      read-write
    STATUS          current
    DESCRIPTION     
            "Force generation or deletion of host public and private
             SSH keys"
    ::= { sonusSecuritySSH 1 }

sonusSecuritySSHKeysHostStatus OBJECT-TYPE
    SYNTAX          INTEGER { notConfigured(1), generated(2), 
                        generating(3) }
    MAX-ACCESS      read-only
    STATUS          current
    DESCRIPTION     
            "Current status of SSH Host Keys"
    ::= { sonusSecuritySSH 2 }

sonusSecuritySSHSessionTable OBJECT-TYPE
    SYNTAX          SEQUENCE OF SonusSecuritySSHSessionEntry
    MAX-ACCESS      not-accessible
    STATUS          current
    DESCRIPTION     
            "The collection of current SSH sessions."
    ::= { sonusSecuritySSH 3 }

sonusSecuritySSHSessionEntry OBJECT-TYPE
    SYNTAX          SonusSecuritySSHSessionEntry
    MAX-ACCESS      not-accessible
    STATUS          current
    DESCRIPTION     
            "The collection of current SSH sessions."
    INDEX           { sonusSecuritySSHSessionLocalAddress, 
                      sonusSecuritySSHSessionLocalPort, 
                      sonusSecuritySSHSessionRemoteAddress, 
                      sonusSecuritySSHSessionRemotePort, 
                      sonusSecuritySSHSessionLocal6Address, 
                      sonusSecuritySSHSessionRemote6Address, 
                      sonusSecuritySSHSessionIpVersion }
    ::= { sonusSecuritySSHSessionTable 1 }

SonusSecuritySSHSessionEntry ::=
    SEQUENCE {
        sonusSecuritySSHSessionLocalAddress   IpAddress,
        sonusSecuritySSHSessionLocalPort Unsigned32,
        sonusSecuritySSHSessionRemoteAddress    IpAddress,
        sonusSecuritySSHSessionRemotePort Unsigned32,
        sonusSecuritySSHSessionTimeConnected    Unsigned32,
        sonusSecuritySSHSessionUser     SonusName,
        sonusSecuritySSHSessionRowStatus RowStatus,
        sonusSecuritySSHSessionInCipherName   SonusName,
        sonusSecuritySSHSessionOutCipherName    SonusName,
        sonusSecuritySSHSessionInMACName SonusName,
        sonusSecuritySSHSessionOutMACName SonusName,
        sonusSecuritySSHSessionLocal6Address    Ipv6Address,
        sonusSecuritySSHSessionRemote6Address     Ipv6Address,
        sonusSecuritySSHSessionIpVersion INTEGER
    }

sonusSecuritySSHSessionLocalAddress OBJECT-TYPE
    SYNTAX          IpAddress
    MAX-ACCESS      read-only
    STATUS          current
    DESCRIPTION     
            "The local address of this SSH Session."
    ::= { sonusSecuritySSHSessionEntry 1 }

sonusSecuritySSHSessionLocalPort OBJECT-TYPE
    SYNTAX          Unsigned32
    MAX-ACCESS      read-only
    STATUS          current
    DESCRIPTION     
            "The local port of this SSH Session."
    ::= { sonusSecuritySSHSessionEntry 2 }

sonusSecuritySSHSessionRemoteAddress OBJECT-TYPE
    SYNTAX          IpAddress
    MAX-ACCESS      read-only
    STATUS          current
    DESCRIPTION     
            "The remote address of this SSH Session."
    ::= { sonusSecuritySSHSessionEntry 3 }

sonusSecuritySSHSessionRemotePort OBJECT-TYPE
    SYNTAX          Unsigned32
    MAX-ACCESS      read-only
    STATUS          current
    DESCRIPTION     
            "The remote port of this SSH Session."
    ::= { sonusSecuritySSHSessionEntry 4 }

sonusSecuritySSHSessionTimeConnected OBJECT-TYPE
    SYNTAX          Unsigned32
    MAX-ACCESS      read-only
    STATUS          current
    DESCRIPTION     
            "The time in seconds that this session has been connected."
    ::= { sonusSecuritySSHSessionEntry 5 }

sonusSecuritySSHSessionUser OBJECT-TYPE
    SYNTAX          SonusName
    MAX-ACCESS      read-only
    STATUS          current
    DESCRIPTION     
            "The user name this session was logged in under."
    ::= { sonusSecuritySSHSessionEntry 6 }

sonusSecuritySSHSessionRowStatus OBJECT-TYPE
    SYNTAX          RowStatus
    MAX-ACCESS      read-write
    STATUS          current
    DESCRIPTION     
            ""
    ::= { sonusSecuritySSHSessionEntry 7 }

sonusSecuritySSHSessionInCipherName OBJECT-TYPE
    SYNTAX          SonusName
    MAX-ACCESS      read-only
    STATUS          current
    DESCRIPTION     
            "The name of the cipher used for inbound traffic on this
             session."
    ::= { sonusSecuritySSHSessionEntry 8 }

sonusSecuritySSHSessionOutCipherName OBJECT-TYPE
    SYNTAX          SonusName
    MAX-ACCESS      read-only
    STATUS          current
    DESCRIPTION     
            "The name of the cipher used for outbound traffic on this
             session."
    ::= { sonusSecuritySSHSessionEntry 9 }

sonusSecuritySSHSessionInMACName OBJECT-TYPE
    SYNTAX          SonusName
    MAX-ACCESS      read-only
    STATUS          current
    DESCRIPTION     
            "The name of the MAC used for inbound traffic on this
             session."
    ::= { sonusSecuritySSHSessionEntry 10 }

sonusSecuritySSHSessionOutMACName OBJECT-TYPE
    SYNTAX          SonusName
    MAX-ACCESS      read-only
    STATUS          current
    DESCRIPTION     
            "The name of the MAC used for outbound traffic on this
             session."
    ::= { sonusSecuritySSHSessionEntry 11 }

sonusSecuritySSHSessionLocal6Address OBJECT-TYPE
    SYNTAX          Ipv6Address
    MAX-ACCESS      read-write
    STATUS          current
    DESCRIPTION     
            "The local ipv6 address of this SSH Session."
    ::= { sonusSecuritySSHSessionEntry 12 }

sonusSecuritySSHSessionRemote6Address OBJECT-TYPE
    SYNTAX          Ipv6Address
    MAX-ACCESS      read-write
    STATUS          current
    DESCRIPTION     
            "The remote ipv6 address of this SSH Session."
    ::= { sonusSecuritySSHSessionEntry 13 }

sonusSecuritySSHSessionIpVersion OBJECT-TYPE
    SYNTAX          INTEGER { afInet(2), afInet6(24) }
    MAX-ACCESS      read-only
    STATUS          current
    DESCRIPTION     
            "The ip address type for  SSH."
    ::= { sonusSecuritySSHSessionEntry 14 }

sonusSecuritySSHKeysHostPublic OBJECT-TYPE
    SYNTAX          OCTET STRING (SIZE(1..1024))
    MAX-ACCESS      read-only
    STATUS          current
    DESCRIPTION     
            "Current public host key"
    ::= { sonusSecuritySSH 4 }

sonusSecuritySSHKeysHostPublicLen OBJECT-TYPE
    SYNTAX          Integer32
    MAX-ACCESS      read-only
    STATUS          current
    DESCRIPTION     
            "Length of current public host key"
    ::= { sonusSecuritySSH 5 }

sonusTlsProfile OBJECT IDENTIFIER
    ::= { sonusSecurityMIBObjects 2 }

sonusTlsProfileNextIndex OBJECT-TYPE
    SYNTAX          Integer32
    MAX-ACCESS      read-only
    STATUS          current
    DESCRIPTION     
            "The next valid index to use when creating an entry in
             the sonusTlsProfileTable."
    ::= { sonusTlsProfile 1 }

sonusTlsProfileTable OBJECT-TYPE
    SYNTAX          SEQUENCE OF SonusTlsProfileEntry
    MAX-ACCESS      not-accessible
    STATUS          current
    DESCRIPTION     
            "This table contains TLS profiles for the GSX."
    ::= { sonusTlsProfile 2 }

sonusTlsProfileEntry OBJECT-TYPE
    SYNTAX          SonusTlsProfileEntry
    MAX-ACCESS      not-accessible
    STATUS          current
    DESCRIPTION     
            ""
    INDEX           { sonusTlsProfileIndex }
    ::= { sonusTlsProfileTable 1 }

SonusTlsProfileEntry ::=
    SEQUENCE {
        sonusTlsProfileIndex            Unsigned32,
        sonusTlsProfileName             SonusName,
        sonusTlsProfileAppAuthenticationTimer     Unsigned32,
        sonusTlsProfileHandshakeTimer   Unsigned32,
        sonusTlsProfileSessionResumptionTimer     Unsigned32,
        sonusTlsProfileCipherSuite1     SonusTlsCipherSuite,
        sonusTlsProfileCipherSuite2     SonusTlsCipherSuite,
        sonusTlsProfileCipherSuite3     SonusTlsCipherSuite,
        sonusTlsProfileAllowedRoles     INTEGER,
        sonusTlsProfileAuthenticateClient SonusBoolean,
        sonusTlsProfileRowStatus        RowStatus,
        sonusTlsProfileClientCertificateName    SonusNameReference,
        sonusTlsProfileServerCertificateName    SonusNameReference,
        sonusTlsProfileReferenceCount   Unsigned32,
        sonusTlsProfileVerifyServerIdentityState        SonusAdminState
    }

sonusTlsProfileIndex OBJECT-TYPE
    SYNTAX          Unsigned32
    MAX-ACCESS      read-only
    STATUS          current
    DESCRIPTION     
            "Identifies the TLS profile entry."
    ::= { sonusTlsProfileEntry 1 }

sonusTlsProfileName OBJECT-TYPE
    SYNTAX          SonusName
    MAX-ACCESS      read-write
    STATUS          current
    DESCRIPTION     
            "The user name of this TLS profile."
    ::= { sonusTlsProfileEntry 2 }

sonusTlsProfileAppAuthenticationTimer OBJECT-TYPE
    SYNTAX          Unsigned32 (1..60)
    MAX-ACCESS      read-write
    STATUS          current
    DESCRIPTION     
            "The higher layer authentication timer in seconds.
             In the case in which a client does not authenticate
             itself within TLS, this is the time in which it must
             complete authentication in a higher-level protocol 
             after the TLS connection comes up."
    DEFVAL          { 5 }
    ::= { sonusTlsProfileEntry 3 }

sonusTlsProfileHandshakeTimer OBJECT-TYPE
    SYNTAX          Unsigned32 (1..60)
    MAX-ACCESS      read-write
    STATUS          current
    DESCRIPTION     
            "The TLS handshake timer in seconds."
    DEFVAL          { 5 }
    ::= { sonusTlsProfileEntry 4 }

sonusTlsProfileSessionResumptionTimer OBJECT-TYPE
    SYNTAX          Unsigned32 (0..86400)
    MAX-ACCESS      read-write
    STATUS          current
    DESCRIPTION     
            "The TLS session resumption timer in seconds.
             The TLS protocol allows multiple connections 
             to be created within one TLS session. The TLS
             allows resuming a session without repeating 
             the entire expense of the authentication and
             other setup costs for each connection."
    DEFVAL          { 3600 }
    ::= { sonusTlsProfileEntry 5 }

sonusTlsProfileCipherSuite1 OBJECT-TYPE
    SYNTAX          SonusTlsCipherSuite
    MAX-ACCESS      read-write
    STATUS          current
    DESCRIPTION     
            "The first TLS cipher suite choice of this TLS profile."
    DEFVAL          { rsa-with-aes-128-cbc-sha }
    ::= { sonusTlsProfileEntry 6 }

sonusTlsProfileCipherSuite2 OBJECT-TYPE
    SYNTAX          SonusTlsCipherSuite
    MAX-ACCESS      read-write
    STATUS          current
    DESCRIPTION     
            "The second TLS cipher suite choice of this TLS profile."
    DEFVAL          { nosuite }
    ::= { sonusTlsProfileEntry 7 }

sonusTlsProfileCipherSuite3 OBJECT-TYPE
    SYNTAX          SonusTlsCipherSuite
    MAX-ACCESS      read-write
    STATUS          current
    DESCRIPTION     
            "The third TLS cipher suite choice of this TLS profile."
    DEFVAL          { nosuite }
    ::= { sonusTlsProfileEntry 8 }

sonusTlsProfileAllowedRoles OBJECT-TYPE
    SYNTAX          INTEGER { server(1), clientandserver(2) }
    MAX-ACCESS      read-write
    STATUS          current
    DESCRIPTION     
            "The allowed TLS roles of this TLS profile."
    DEFVAL          { clientandserver }
    ::= { sonusTlsProfileEntry 9 }

sonusTlsProfileAuthenticateClient OBJECT-TYPE
    SYNTAX          SonusBoolean
    MAX-ACCESS      read-write
    STATUS          current
    DESCRIPTION     
            "This indicates whether or not a TLS client is forced
             to authenticate itself within TLS. If it's set to false,
             the client must complete authentication within a 
             higher-lever protocol after the TLS connection comes up."
    DEFVAL          { true }
    ::= { sonusTlsProfileEntry 10 }

sonusTlsProfileRowStatus OBJECT-TYPE
    SYNTAX          RowStatus
    MAX-ACCESS      read-write
    STATUS          current
    DESCRIPTION     
            "The row status of this TLS profile."
    ::= { sonusTlsProfileEntry 11 }

sonusTlsProfileClientCertificateName OBJECT-TYPE
    SYNTAX          SonusNameReference
    MAX-ACCESS      read-write
    STATUS          current
    DESCRIPTION     
            "The name of Client Certificate refered by this TLS profile."
    ::= { sonusTlsProfileEntry 12 }

sonusTlsProfileServerCertificateName OBJECT-TYPE
    SYNTAX          SonusNameReference
    MAX-ACCESS      read-write
    STATUS          current
    DESCRIPTION     
            "The name of Server Certificate refered by this TLS profile."
    ::= { sonusTlsProfileEntry 13 }

sonusTlsProfileReferenceCount OBJECT-TYPE
    SYNTAX          Unsigned32
    MAX-ACCESS      read-only
    STATUS          current
    DESCRIPTION     
            "The number of zone objects that refering to this TLS profile ."
    DEFVAL          { 0 }
    ::= { sonusTlsProfileEntry 14 }

sonusTlsProfileVerifyServerIdentityState OBJECT-TYPE
    SYNTAX          SonusAdminState
    MAX-ACCESS      read-write
    STATUS          current
    DESCRIPTION     
            "The state of the flag to verify certificate server identity with host portion of the SIP URI ."
    DEFVAL          { disabled }
    ::= { sonusTlsProfileEntry 15 }

sonusSecurityPKI OBJECT IDENTIFIER
    ::= { sonusSecurityMIBObjects 3 }

sonusSecurityPkiMasterKeyAction OBJECT-TYPE
    SYNTAX          INTEGER { rekey(1), delete(2) }
    MAX-ACCESS      read-write
    STATUS          current
    DESCRIPTION     
            "Force rekey or deletion of PKI master key used for 
             protecting RSA private keys"
    ::= { sonusSecurityPKI 1 }

sonusSecurityCertificateNextIndex OBJECT-TYPE
    SYNTAX          Integer32
    MAX-ACCESS      read-only
    STATUS          current
    DESCRIPTION     
            "The next valid index to use when creating an entry in
             the sonusSecurityCertificateTable."
    ::= { sonusSecurityPKI 2 }

sonusSecurityCertificateTable OBJECT-TYPE
    SYNTAX          SEQUENCE OF SonusSecurityCertificateEntry
    MAX-ACCESS      not-accessible
    STATUS          current
    DESCRIPTION     
            "The collection of certificates configured on GSX."
    ::= { sonusSecurityPKI 3 }

sonusSecurityCertificateEntry OBJECT-TYPE
    SYNTAX          SonusSecurityCertificateEntry
    MAX-ACCESS      not-accessible
    STATUS          current
    DESCRIPTION     
            "The table entry for the collection of certificates configured on GSX."
    INDEX           { sonusSecurityCertificateIndex }
    ::= { sonusSecurityCertificateTable 1 }

SonusSecurityCertificateEntry ::=
    SEQUENCE {
        sonusSecurityCertificateIndex   Unsigned32,
        sonusSecurityCertificateName    SonusName,
        sonusSecurityCertificateState   SonusAdminState,
        sonusSecurityCertificateType    INTEGER,
        sonusSecurityCertificateEncoding INTEGER,
        sonusSecurityCertificateFileName DisplayString,
        sonusSecurityCertificatePassPhrase  OCTET STRING,
        sonusSecurityCertificateRowStatus RowStatus
    }

sonusSecurityCertificateIndex OBJECT-TYPE
    SYNTAX          Unsigned32
    MAX-ACCESS      read-only
    STATUS          current
    DESCRIPTION     
            "The index of the certificate entry."
    ::= { sonusSecurityCertificateEntry 1 }

sonusSecurityCertificateName OBJECT-TYPE
    SYNTAX          SonusName
    MAX-ACCESS      read-write
    STATUS          current
    DESCRIPTION     
            "The name of the certificate entry."
    ::= { sonusSecurityCertificateEntry 2 }

sonusSecurityCertificateState OBJECT-TYPE
    SYNTAX          SonusAdminState
    MAX-ACCESS      read-write
    STATUS          current
    DESCRIPTION     
            "The administration state of this certificate."
    ::= { sonusSecurityCertificateEntry 3 }

sonusSecurityCertificateType OBJECT-TYPE
    SYNTAX          INTEGER { remote(1), local(2) }
    MAX-ACCESS      read-write
    STATUS          current
    DESCRIPTION     
            "The type of the certificate - CA (remote) certificate or local certificate"
    ::= { sonusSecurityCertificateEntry 4 }

sonusSecurityCertificateEncoding OBJECT-TYPE
    SYNTAX          INTEGER { der(1), pkcs12(2) }
    MAX-ACCESS      read-only
    STATUS          current
    DESCRIPTION     
            "The encoding type of the certificate."
    ::= { sonusSecurityCertificateEntry 5 }

sonusSecurityCertificateFileName OBJECT-TYPE
    SYNTAX          DisplayString (SIZE(1..23))
    MAX-ACCESS      read-write
    STATUS          current
    DESCRIPTION     
            "The certificate content file name"
    ::= { sonusSecurityCertificateEntry 6 }

sonusSecurityCertificatePassPhrase OBJECT-TYPE
    SYNTAX          OCTET STRING (SIZE(1..23))
    MAX-ACCESS      read-write
    STATUS          current
    DESCRIPTION     
            "Pass-phrase to decrypt RSA private key in PKCS12 file.
             This value is ****** when read."
    ::= { sonusSecurityCertificateEntry 7 }

sonusSecurityCertificateRowStatus OBJECT-TYPE
    SYNTAX          RowStatus
    MAX-ACCESS      read-write
    STATUS          current
    DESCRIPTION     
            "RowStatus for the certificate Entry"
    ::= { sonusSecurityCertificateEntry 8 }

sonusSecurityCertStatTable OBJECT-TYPE
    SYNTAX          SEQUENCE OF SonusSecurityCertStatEntry
    MAX-ACCESS      not-accessible
    STATUS          current
    DESCRIPTION     
            "The collection of certificate status on GSX."
    ::= { sonusSecurityPKI 4 }

sonusSecurityCertStatEntry OBJECT-TYPE
    SYNTAX          SonusSecurityCertStatEntry
    MAX-ACCESS      not-accessible
    STATUS          current
    DESCRIPTION     
            "The table entry for the collection of certificate status on GSX."
    INDEX           { sonusSecurityCertStatShelfIndex, 
                      sonusSecurityCertStatSlotIndex, 
                      sonusSecurityCertStatIndex }
    ::= { sonusSecurityCertStatTable 1 }

SonusSecurityCertStatEntry ::=
    SEQUENCE {
        sonusSecurityCertStatShelfIndex SonusShelfIndex,
        sonusSecurityCertStatSlotIndex  SonusSlotIndex,
        sonusSecurityCertStatIndex      Unsigned32,
        sonusSecurityCertStatName       DisplayString,
        sonusSecurityCertStatCertType   INTEGER,
        sonusSecurityCertStatComps      Counter32,
        sonusSecurityCertStatMatches    Counter32,
        sonusSecurityCertStatGets       Counter32,
        sonusSecurityCertStatValids     Counter32,
        sonusSecurityCertStatStatus     INTEGER,
        sonusSecurityCertStatDisplay1   OCTET STRING,
        sonusSecurityCertStatDisplay2   OCTET STRING,
        sonusSecurityCertStatDisplay3   OCTET STRING,
        sonusSecurityCertStatDisplay4   OCTET STRING
    }

sonusSecurityCertStatShelfIndex OBJECT-TYPE
    SYNTAX          SonusShelfIndex
    MAX-ACCESS      read-only
    STATUS          current
    DESCRIPTION     
            "The shelf of the card where certificate status is being shown."
    ::= { sonusSecurityCertStatEntry 1 }

sonusSecurityCertStatSlotIndex OBJECT-TYPE
    SYNTAX          SonusSlotIndex
    MAX-ACCESS      read-only
    STATUS          current
    DESCRIPTION     
            "The card slot where certificate status is being shown."
    ::= { sonusSecurityCertStatEntry 2 }

sonusSecurityCertStatIndex OBJECT-TYPE
    SYNTAX          Unsigned32
    MAX-ACCESS      read-only
    STATUS          current
    DESCRIPTION     
            "The index of the certificate status entry."
    ::= { sonusSecurityCertStatEntry 3 }

sonusSecurityCertStatName OBJECT-TYPE
    SYNTAX          DisplayString (SIZE(0..23))
    MAX-ACCESS      read-only
    STATUS          current
    DESCRIPTION     
            "The name of the certificate in certificate status entry."
    ::= { sonusSecurityCertStatEntry 4 }

sonusSecurityCertStatCertType OBJECT-TYPE
    SYNTAX          INTEGER { remote(1), local(2) }
    MAX-ACCESS      read-only
    STATUS          current
    DESCRIPTION     
            "The type of the certificate - CA (remote) certificate or local certificate"
    ::= { sonusSecurityCertStatEntry 5 }

sonusSecurityCertStatComps OBJECT-TYPE
    SYNTAX          Counter32
    MAX-ACCESS      read-only
    STATUS          current
    DESCRIPTION     
            "Number of comparisons the certificate is used for"
    ::= { sonusSecurityCertStatEntry 6 }

sonusSecurityCertStatMatches OBJECT-TYPE
    SYNTAX          Counter32
    MAX-ACCESS      read-only
    STATUS          current
    DESCRIPTION     
            "Number of matched comparisons the certificate is used for"
    ::= { sonusSecurityCertStatEntry 7 }

sonusSecurityCertStatGets OBJECT-TYPE
    SYNTAX          Counter32
    MAX-ACCESS      read-only
    STATUS          current
    DESCRIPTION     
            "Number of local certificate retrievals (gets)"
    ::= { sonusSecurityCertStatEntry 8 }

sonusSecurityCertStatValids OBJECT-TYPE
    SYNTAX          Counter32
    MAX-ACCESS      read-only
    STATUS          current
    DESCRIPTION     
            "Number of times the certificate is used for validating peers."
    ::= { sonusSecurityCertStatEntry 9 }

sonusSecurityCertStatStatus OBJECT-TYPE
    SYNTAX          INTEGER { disabled(1), enabled(2), noCertFile(3) }
    MAX-ACCESS      read-only
    STATUS          current
    DESCRIPTION     
            "The state of the certificate. 
             Disabled means the certificate is in certificate database, but disabled.
             Enabled means the certificate is in certificate database and enabled. 
             NoCertFile means the certificate is configured but not in certificate 
             database since it has no certificate file associated with."
    ::= { sonusSecurityCertStatEntry 10 }

sonusSecurityCertStatDisplay1 OBJECT-TYPE
    SYNTAX          OCTET STRING (SIZE(0..1200))
    MAX-ACCESS      read-only
    STATUS          current
    DESCRIPTION     
            "Used to display the content of certificate - part 1"
    ::= { sonusSecurityCertStatEntry 11 }

sonusSecurityCertStatDisplay2 OBJECT-TYPE
    SYNTAX          OCTET STRING (SIZE(0..1200))
    MAX-ACCESS      read-only
    STATUS          current
    DESCRIPTION     
            "Used to display the content of certificate - part 2"
    ::= { sonusSecurityCertStatEntry 12 }

sonusSecurityCertStatDisplay3 OBJECT-TYPE
    SYNTAX          OCTET STRING (SIZE(0..1200))
    MAX-ACCESS      read-only
    STATUS          current
    DESCRIPTION     
            "Used to display the content of certificate - part 3"
    ::= { sonusSecurityCertStatEntry 13 }

sonusSecurityCertStatDisplay4 OBJECT-TYPE
    SYNTAX          OCTET STRING (SIZE(0..1200))
    MAX-ACCESS      read-only
    STATUS          current
    DESCRIPTION     
            "Used to display the content of certificate - part 4"
    ::= { sonusSecurityCertStatEntry 14 }

sonusSecurityCertGlobalStatsTable OBJECT-TYPE
    SYNTAX          SEQUENCE OF SonusSecurityCertGlobalStatsEntry
    MAX-ACCESS      not-accessible
    STATUS          current
    DESCRIPTION     
            "The collection of certificate's global statistics per card on GSX."
    ::= { sonusSecurityPKI 5 }

sonusSecurityCertGlobalStatsEntry OBJECT-TYPE
    SYNTAX          SonusSecurityCertGlobalStatsEntry
    MAX-ACCESS      not-accessible
    STATUS          current
    DESCRIPTION     
            "The table entry for the collection of certificate's global statistics per card on GSX."
    INDEX           { sonusSecurityCertGlobalStatsShelfIndex, 
                      sonusSecurityCertGlobalStatsSlotIndex }
    ::= { sonusSecurityCertGlobalStatsTable 1 }

SonusSecurityCertGlobalStatsEntry ::=
    SEQUENCE {
        sonusSecurityCertGlobalStatsShelfIndex      SonusShelfIndex,
        sonusSecurityCertGlobalStatsSlotIndex     SonusSlotIndex,
        sonusSecurityCertGlobalStatsLocalInstalled          Counter32,
        sonusSecurityCertGlobalStatsCaInstalled       Counter32,
        sonusSecurityCertGlobalStatsSuccValid     Counter32,
        sonusSecurityCertGlobalStatsFailedValid       Counter32,
        sonusSecurityCertGlobalStatsLocalLongChains           Counter32,
        sonusSecurityCertGlobalStatsCaLongChains        Counter32,
        sonusSecurityCertGlobalStatsNoMasterKey       Counter32,
        sonusSecurityCertGlobalStatsWrongMasterKey          Counter32,
        sonusSecurityCertGlobalStatsBadPeerCerts        Counter32,
        sonusSecurityCertGlobalStatsBadLocalCerts         Counter32,
        sonusSecurityCertGlobalStatsBadCaCerts      Counter32,
        sonusSecurityCertGlobalStatsFailedServerIdentity                Counter32
    }

sonusSecurityCertGlobalStatsShelfIndex OBJECT-TYPE
    SYNTAX          SonusShelfIndex
    MAX-ACCESS      read-only
    STATUS          current
    DESCRIPTION     
            "The GSX shelf index where global certificate statistics is being shown."
    ::= { sonusSecurityCertGlobalStatsEntry 1 }

sonusSecurityCertGlobalStatsSlotIndex OBJECT-TYPE
    SYNTAX          SonusSlotIndex
    MAX-ACCESS      read-only
    STATUS          current
    DESCRIPTION     
            "The GSX slot index where global certificate statistics is being shown."
    ::= { sonusSecurityCertGlobalStatsEntry 2 }

sonusSecurityCertGlobalStatsLocalInstalled OBJECT-TYPE
    SYNTAX          Counter32
    MAX-ACCESS      read-only
    STATUS          current
    DESCRIPTION     
            "Number of installed local certificates"
    ::= { sonusSecurityCertGlobalStatsEntry 3 }

sonusSecurityCertGlobalStatsCaInstalled OBJECT-TYPE
    SYNTAX          Counter32
    MAX-ACCESS      read-only
    STATUS          current
    DESCRIPTION     
            "Number of installed CA/remote certificates"
    ::= { sonusSecurityCertGlobalStatsEntry 4 }

sonusSecurityCertGlobalStatsSuccValid OBJECT-TYPE
    SYNTAX          Counter32
    MAX-ACCESS      read-only
    STATUS          current
    DESCRIPTION     
            "Number of successful certificate validations"
    ::= { sonusSecurityCertGlobalStatsEntry 5 }

sonusSecurityCertGlobalStatsFailedValid OBJECT-TYPE
    SYNTAX          Counter32
    MAX-ACCESS      read-only
    STATUS          current
    DESCRIPTION     
            "Number of failed certificate validations"
    ::= { sonusSecurityCertGlobalStatsEntry 6 }

sonusSecurityCertGlobalStatsLocalLongChains OBJECT-TYPE
    SYNTAX          Counter32
    MAX-ACCESS      read-only
    STATUS          current
    DESCRIPTION     
            "Number of failed local certificate chain validations due to 
             the chain length exceeding the limit"
    ::= { sonusSecurityCertGlobalStatsEntry 7 }

sonusSecurityCertGlobalStatsCaLongChains OBJECT-TYPE
    SYNTAX          Counter32
    MAX-ACCESS      read-only
    STATUS          current
    DESCRIPTION     
            "Number of failed CA/remote certificate chain validations due to 
             the chain length exceeding the limit"
    ::= { sonusSecurityCertGlobalStatsEntry 8 }

sonusSecurityCertGlobalStatsNoMasterKey OBJECT-TYPE
    SYNTAX          Counter32
    MAX-ACCESS      read-only
    STATUS          current
    DESCRIPTION     
            "Number of RSA private key blob decrytion/encryption failures due to missing master key"
    ::= { sonusSecurityCertGlobalStatsEntry 9 }

sonusSecurityCertGlobalStatsWrongMasterKey OBJECT-TYPE
    SYNTAX          Counter32
    MAX-ACCESS      read-only
    STATUS          current
    DESCRIPTION     
            "Number of RSA private key blob decrytion failures due to wrong master key"
    ::= { sonusSecurityCertGlobalStatsEntry 10 }

sonusSecurityCertGlobalStatsBadPeerCerts OBJECT-TYPE
    SYNTAX          Counter32
    MAX-ACCESS      read-only
    STATUS          current
    DESCRIPTION     
            "Number of bad/malformed peer certificates presented for validation"
    ::= { sonusSecurityCertGlobalStatsEntry 11 }

sonusSecurityCertGlobalStatsBadLocalCerts OBJECT-TYPE
    SYNTAX          Counter32
    MAX-ACCESS      read-only
    STATUS          current
    DESCRIPTION     
            "Number of bad/malformed local certificates presented for installation"
    ::= { sonusSecurityCertGlobalStatsEntry 12 }

sonusSecurityCertGlobalStatsBadCaCerts OBJECT-TYPE
    SYNTAX          Counter32
    MAX-ACCESS      read-only
    STATUS          current
    DESCRIPTION     
            "Number of bad/malformed CA/remote certificates presented for installation"
    ::= { sonusSecurityCertGlobalStatsEntry 13 }

sonusSecurityCertGlobalStatsFailedServerIdentity OBJECT-TYPE
    SYNTAX          Counter32
    MAX-ACCESS      read-only
    STATUS          current
    DESCRIPTION     
            "Number of failed certificate validations due to server Identity mismatch
             with host portion of the SIP URI"
    ::= { sonusSecurityCertGlobalStatsEntry 14 }

sonusSecurityCertChainStatTable OBJECT-TYPE
    SYNTAX          SEQUENCE OF SonusSecurityCertChainStatEntry
    MAX-ACCESS      not-accessible
    STATUS          current
    DESCRIPTION     
            "The collection of certificate chain status on GSX."
    ::= { sonusSecurityPKI 6 }

sonusSecurityCertChainStatEntry OBJECT-TYPE
    SYNTAX          SonusSecurityCertChainStatEntry
    MAX-ACCESS      not-accessible
    STATUS          current
    DESCRIPTION     
            "The table entry for the collection of certificate chains of local certificates on GSX."
    INDEX           { sonusSecurityCertChainStatIndex }
    ::= { sonusSecurityCertChainStatTable 1 }

SonusSecurityCertChainStatEntry ::=
    SEQUENCE {
        sonusSecurityCertChainStatIndex Unsigned32,
        sonusSecurityCertChainStatLocCertName     DisplayString,
        sonusSecurityCertChainStatIssuer1Name     DisplayString,
        sonusSecurityCertChainStatIssuer2Name     DisplayString,
        sonusSecurityCertChainStatIssuer3Name     DisplayString,
        sonusSecurityCertChainStatLocCertSubj     DisplayString,
        sonusSecurityCertChainStatIssuer1Subj     DisplayString,
        sonusSecurityCertChainStatIssuer2Subj     DisplayString,
        sonusSecurityCertChainStatIssuer3Subj     DisplayString
    }

sonusSecurityCertChainStatIndex OBJECT-TYPE
    SYNTAX          Unsigned32
    MAX-ACCESS      read-only
    STATUS          current
    DESCRIPTION     
            "The sonusSecurityCertificateIndex value of the local certificate 
             for the certificate chain status entry."
    ::= { sonusSecurityCertChainStatEntry 1 }

sonusSecurityCertChainStatLocCertName OBJECT-TYPE
    SYNTAX          DisplayString (SIZE(0..23))
    MAX-ACCESS      read-only
    STATUS          current
    DESCRIPTION     
            "The configuration name of the local certificate for the certificate chain status entry."
    ::= { sonusSecurityCertChainStatEntry 2 }

sonusSecurityCertChainStatIssuer1Name OBJECT-TYPE
    SYNTAX          DisplayString (SIZE(0..23))
    MAX-ACCESS      read-only
    STATUS          current
    DESCRIPTION     
            "The configuration name of the Level 1 Issuer certificate, 
             which signed the local certificate."
    ::= { sonusSecurityCertChainStatEntry 3 }

sonusSecurityCertChainStatIssuer2Name OBJECT-TYPE
    SYNTAX          DisplayString (SIZE(0..23))
    MAX-ACCESS      read-only
    STATUS          current
    DESCRIPTION     
            "The configuration name of the Level 2 Issuer certificate, 
             which signed the Level 1 Issuer certificate."
    ::= { sonusSecurityCertChainStatEntry 4 }

sonusSecurityCertChainStatIssuer3Name OBJECT-TYPE
    SYNTAX          DisplayString (SIZE(0..23))
    MAX-ACCESS      read-only
    STATUS          current
    DESCRIPTION     
            "The configuration name of the Level 3 Issuer certificate, 
             which signed the Level 2 Issuer certificate."
    ::= { sonusSecurityCertChainStatEntry 5 }

sonusSecurityCertChainStatLocCertSubj OBJECT-TYPE
    SYNTAX          DisplayString (SIZE(0..63))
    MAX-ACCESS      read-only
    STATUS          current
    DESCRIPTION     
            "The subject name of the local certificate in certificate chain status entry."
    ::= { sonusSecurityCertChainStatEntry 6 }

sonusSecurityCertChainStatIssuer1Subj OBJECT-TYPE
    SYNTAX          DisplayString (SIZE(0..63))
    MAX-ACCESS      read-only
    STATUS          current
    DESCRIPTION     
            "The subject name of the Level 1 Issuer certificate, 
             which signed the local certificate."
    ::= { sonusSecurityCertChainStatEntry 7 }

sonusSecurityCertChainStatIssuer2Subj OBJECT-TYPE
    SYNTAX          DisplayString (SIZE(0..63))
    MAX-ACCESS      read-only
    STATUS          current
    DESCRIPTION     
            "The subject name of the Level 2 Issuer certificate, 
             which signed the Level 1 Issuer certificate."
    ::= { sonusSecurityCertChainStatEntry 8 }

sonusSecurityCertChainStatIssuer3Subj OBJECT-TYPE
    SYNTAX          DisplayString (SIZE(0..63))
    MAX-ACCESS      read-only
    STATUS          current
    DESCRIPTION     
            "The subject name of the Level 3 Issuer certificate, 
             which signed the Level 2 Issuer certificate."
    ::= { sonusSecurityCertChainStatEntry 9 }

END -- end of module SONUS-SECURITY-MIB.
