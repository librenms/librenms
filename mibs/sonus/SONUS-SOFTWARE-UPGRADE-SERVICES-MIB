--
-- This SMIv2 module has been generated by smidump 0.2-cvs. Do not edit.
--

SONUS-SOFTWARE-UPGRADE-SERVICES-MIB DEFINITIONS ::= BEGIN

IMPORTS
    Counter32, Integer32, MODULE-IDENTITY, NOTIFICATION-TYPE, 
    OBJECT-TYPE
        FROM SNMPv2-SMI
    DateAndTime, DisplayString, TEXTUAL-CONVENTION
        FROM SNMPv2-TC
    sonusEventClass, sonusEventDescription, sonusEventLevel, 
    sonusEventTime, sonusSequenceId, sonusShelfIndex
        FROM SONUS-COMMON-MIB
    sonusServicesMIBs
        FROM SONUS-SMI
    SonusShelfIndex, SonusSlotIndex
        FROM SONUS-TC;

sonusSoftwareUpgradeServicesMIB MODULE-IDENTITY
    LAST-UPDATED    "200802120000Z"
    ORGANIZATION    
            "Sonus Networks, Inc."
    CONTACT-INFO    
            "   Customer Support    
             Sonus Networks, Inc.
             7 Technology Park Drive
             Westford, MA 01886
             USA
             
             Tel: 978-614-8100
             Fax: 978-614-8609"
    DESCRIPTION     
            "The MIB Module for Software Upgrade Configuration."
    ::= { sonusServicesMIBs 11 }


SonusSoftwareUpgradeState ::= TEXTUAL-CONVENTION
    STATUS          current
    DESCRIPTION     
            "Represents the different states in LSWU FSM. (Internal use only)"
    SYNTAX          INTEGER { idle(0), query(1), init(2), delay1(3), 
                        start(4), sxOne(5), waitSync(6), sxTwoTx(7), 
                        sxTwoRx(8), sxTwoWait(9), variant(10), 
                        prepare(11), stopCalls(12), firstPns(13), 
                        cnsReset(14), spsReset(15), pnsReset(16), 
                        sxDelay(17), done(18), redundOosReset(19), 
                        redundOosWait(20), groupSetup(21), clientSx(22), 
                        clientRevert(23), groupRestore(24), 
                        firstUnprotectedReset(25), 
                        secondUnprotectedReset(26), parameterSave(27) }

sonusSoftwareUpgradeServicesMIBObjects OBJECT IDENTIFIER
    ::= { sonusSoftwareUpgradeServicesMIB 1 }

sonusSwUpgradeShelfAdmnTable OBJECT-TYPE
    SYNTAX          SEQUENCE OF SonusSwUpgradeShelfAdmnEntry
    MAX-ACCESS      not-accessible
    STATUS          current
    DESCRIPTION     
            "This table specifies the software upgrade configuration."
    ::= { sonusSoftwareUpgradeServicesMIBObjects 1 }

sonusSwUpgradeShelfAdmnEntry OBJECT-TYPE
    SYNTAX          SonusSwUpgradeShelfAdmnEntry
    MAX-ACCESS      not-accessible
    STATUS          current
    DESCRIPTION     
            ""
    INDEX           { sonusSwUpgradeShelfAdmnShelfIndex }
    ::= { sonusSwUpgradeShelfAdmnTable 1 }

SonusSwUpgradeShelfAdmnEntry ::=
    SEQUENCE {
        sonusSwUpgradeShelfAdmnShelfIndex SonusShelfIndex,
        sonusSwUpgradeShelfAdmnInit     INTEGER,
        sonusSwUpgradeShelfAdmnUpgradeNow INTEGER,
        sonusSwUpgradeShelfAdmnHalt     INTEGER,
        sonusSwUpgradeShelfAdmnCommitDirectory      INTEGER,
        sonusSwUpgradeShelfAdmnDirectory DisplayString,
        sonusSwUpgradeShelfAdmnOverrideFeatureCheck           INTEGER,
        sonusSwUpgradeShelfAdmnUnprotectedControl         INTEGER
    }

sonusSwUpgradeShelfAdmnShelfIndex OBJECT-TYPE
    SYNTAX          SonusShelfIndex
    MAX-ACCESS      read-only
    STATUS          current
    DESCRIPTION     
            "The shelf index of this software upgrade entry."
    ::= { sonusSwUpgradeShelfAdmnEntry 1 }

sonusSwUpgradeShelfAdmnInit OBJECT-TYPE
    SYNTAX          INTEGER { ready(1), initialize(2) }
    MAX-ACCESS      read-write
    STATUS          current
    DESCRIPTION     
            "Initialize the software upgrade, verify software image
             availability, check for unsupported features.  The feature
             check can be disabled by setting
             sonusSwUpgradeShelfAdmnOverrideFeatureCheck in the same
             request.
             
             This MIB object can only be set through the CLI, and only
             by a user with admin privileges; it always reads as ready(1)."
    DEFVAL          { ready }
    ::= { sonusSwUpgradeShelfAdmnEntry 2 }

sonusSwUpgradeShelfAdmnUpgradeNow OBJECT-TYPE
    SYNTAX          INTEGER { ready(1), upgrade(2) }
    MAX-ACCESS      read-write
    STATUS          current
    DESCRIPTION     
            "Initiate the software upgrade of the specified shelf now.
             
             This MIB object can only be set through the CLI, and only
             by a user with admin privileges; it always reads as ready(1)."
    DEFVAL          { ready }
    ::= { sonusSwUpgradeShelfAdmnEntry 3 }

sonusSwUpgradeShelfAdmnHalt OBJECT-TYPE
    SYNTAX          INTEGER { ready(1), halt(2) }
    MAX-ACCESS      read-write
    STATUS          current
    DESCRIPTION     
            "Halt the software upgrade in progress.
             
             This MIB object can only be set through the CLI, and only
             by a user with admin privileges; it always reads as ready(1)."
    DEFVAL          { ready }
    ::= { sonusSwUpgradeShelfAdmnEntry 4 }

sonusSwUpgradeShelfAdmnCommitDirectory OBJECT-TYPE
    SYNTAX          INTEGER { ready(1), commit(2) }
    MAX-ACCESS      read-write
    STATUS          current
    DESCRIPTION     
            "Commit the new software distribution directory name into NVS.
             
             This MIB object can only be set by a user with admin
             privileges; it always reads as ready(1)."
    DEFVAL          { ready }
    ::= { sonusSwUpgradeShelfAdmnEntry 5 }

sonusSwUpgradeShelfAdmnDirectory OBJECT-TYPE
    SYNTAX          DisplayString (SIZE(0..15))
    MAX-ACCESS      read-write
    STATUS          current
    DESCRIPTION     
            "The new software distribution directory name.
             
             This MIB object can only be set by a user with admin
             privileges."
    ::= { sonusSwUpgradeShelfAdmnEntry 6 }

sonusSwUpgradeShelfAdmnOverrideFeatureCheck OBJECT-TYPE
    SYNTAX          INTEGER { ready(1), override(2) }
    MAX-ACCESS      read-write
    STATUS          current
    DESCRIPTION     
            "Ignore the check for unsupported features (i.e. features
             that would prevent a software upgrade from occurring) during
             initialization.  This MIB object must be set with
             sonusSwUpgradeShelfAdmnInit in the same request.
             
             This MIB object can only be set through the CLI, and only
             by a user with admin privileges; it always reads as ready(1)."
    DEFVAL          { ready }
    ::= { sonusSwUpgradeShelfAdmnEntry 7 }

sonusSwUpgradeShelfAdmnUnprotectedControl OBJECT-TYPE
    SYNTAX          INTEGER { upgrade(1), skip(2) }
    MAX-ACCESS      read-write
    STATUS          current
    DESCRIPTION     
            "Controls the handling of server modules that are In Service, but
             not protected by redundancy during a Live Software Upgrade.  This
             MIB object must be set before an upgrade is initialized.
             
             If set to upgrade(1), these server modules will be individually
             reset during the upgrade, thereby dropping any calls they are
             carrying at the time.  This is the default behavior.
             
             If set to skip(2), the upgrade process will exit early, leaving
             these server modules running the old version of software in an
             Out of Service/dryup state.  When calls on these server modules
             are sufficiently dried up, a second upgrade must be initiated by
             the user to complete the shelf upgrade.  It is important not to
             make any configuration changes until the upgrade is completed.
             
             This MIB object can only be set through the CLI, and only by a
             user with admin privileges; the default value is upgrade(1)."
    DEFVAL          { upgrade }
    ::= { sonusSwUpgradeShelfAdmnEntry 8 }

sonusSwUpgradeShelfStatTable OBJECT-TYPE
    SYNTAX          SEQUENCE OF SonusSwUpgradeShelfStatEntry
    MAX-ACCESS      not-accessible
    STATUS          current
    DESCRIPTION     
            "This table contains status information about the software upgrade 
             on a shelf."
    ::= { sonusSoftwareUpgradeServicesMIBObjects 2 }

sonusSwUpgradeShelfStatEntry OBJECT-TYPE
    SYNTAX          SonusSwUpgradeShelfStatEntry
    MAX-ACCESS      not-accessible
    STATUS          current
    DESCRIPTION     
            ""
    INDEX           { sonusSwUpgradeShelfStatShelfIndex }
    ::= { sonusSwUpgradeShelfStatTable 1 }

SonusSwUpgradeShelfStatEntry ::=
    SEQUENCE {
        sonusSwUpgradeShelfStatShelfIndex SonusShelfIndex,
        sonusSwUpgradeShelfStatStatus   INTEGER,
        sonusSwUpgradeShelfStatCurSlot  SonusSlotIndex,
        sonusSwUpgradeShelfStatSlotRemain SonusSlotIndex,
        sonusSwUpgradeShelfStatGroupRemain  Integer32,
        sonusSwUpgradeShelfStatDuration Counter32,
        sonusSwUpgradeShelfStatStartTime DateAndTime,
        sonusSwUpgradeShelfStatLastReason INTEGER,
        sonusSwUpgradeShelfStatLastState SonusSoftwareUpgradeState,
        sonusSwUpgradeShelfStatState    SonusSoftwareUpgradeState,
        sonusSwUpgradeShelfStatCurGroup Integer32
    }

sonusSwUpgradeShelfStatShelfIndex OBJECT-TYPE
    SYNTAX          SonusShelfIndex
    MAX-ACCESS      read-only
    STATUS          current
    DESCRIPTION     
            "Identifies the target shelf within the node."
    ::= { sonusSwUpgradeShelfStatEntry 1 }

sonusSwUpgradeShelfStatStatus OBJECT-TYPE
    SYNTAX          INTEGER { idle(1), busy(2), complete(3), 
                        incomplete(4), commitRequired(5) }
    MAX-ACCESS      read-only
    STATUS          current
    DESCRIPTION     
            "Indicates the software upgrade status of the shelf."
    ::= { sonusSwUpgradeShelfStatEntry 2 }

sonusSwUpgradeShelfStatCurSlot OBJECT-TYPE
    SYNTAX          SonusSlotIndex
    MAX-ACCESS      read-only
    STATUS          current
    DESCRIPTION     
            "Identifies the slot currently being upgraded with new software."
    ::= { sonusSwUpgradeShelfStatEntry 3 }

sonusSwUpgradeShelfStatSlotRemain OBJECT-TYPE
    SYNTAX          SonusSlotIndex
    MAX-ACCESS      read-only
    STATUS          current
    DESCRIPTION     
            "Identifies number of slots within the shelf remained to be upgraded."
    ::= { sonusSwUpgradeShelfStatEntry 4 }

sonusSwUpgradeShelfStatGroupRemain OBJECT-TYPE
    SYNTAX          Integer32
    MAX-ACCESS      read-only
    STATUS          current
    DESCRIPTION     
            ""
    ::= { sonusSwUpgradeShelfStatEntry 5 }

sonusSwUpgradeShelfStatDuration OBJECT-TYPE
    SYNTAX          Counter32
    MAX-ACCESS      read-only
    STATUS          current
    DESCRIPTION     
            "Indicates the duration of the software upgrade in seconds."
    ::= { sonusSwUpgradeShelfStatEntry 6 }

sonusSwUpgradeShelfStatStartTime OBJECT-TYPE
    SYNTAX          DateAndTime
    MAX-ACCESS      read-only
    STATUS          current
    DESCRIPTION     
            "Indicates the start time of the software upgrade"
    ::= { sonusSwUpgradeShelfStatEntry 7 }

sonusSwUpgradeShelfStatLastReason OBJECT-TYPE
    SYNTAX          INTEGER { none(0), successfulCompletion(1), 
                        initTimeout(2), manualHalt(3), 
                        upgradeNotRequired(4), fileUnavailable(5), 
                        parametersNotSaved(6), flashUpdateInProgress(7), 
                        redundSlotActive(8), switchover1Timeout(9), 
                        sync1Timeout(10), switchover2Timeout(11), 
                        sync2Timeout(12), rebootTimeout(13), 
                        mnsNotSynced(14), notActive(15), 
                        internalTimerUnavailable(16), 
                        internalQueryTimeout(17), 
                        internalResourceUnavailable(18), 
                        internalRtmError(19), mnsSwitchover(20), 
                        overallSyncTimeout(21), unexpectedSwitchover(22), 
                        syncFailure(23), skipUnprotectedModules(24), 
                        invalidVersion(25), matrixFileUnavailable(26), 
                        unsupportedUpgradePath(27), 
                        mnsLocalDisksNotSynced(28), nvsReadError(29), 
                        nvsNotValid(30), 
                        unsupportedAcctUpgradePatchVer(31) }
    MAX-ACCESS      read-only
    STATUS          current
    DESCRIPTION     
            "Indicates the exit reason of the last live software upgrade."
    ::= { sonusSwUpgradeShelfStatEntry 8 }

sonusSwUpgradeShelfStatLastState OBJECT-TYPE
    SYNTAX          SonusSoftwareUpgradeState
    MAX-ACCESS      read-only
    STATUS          current
    DESCRIPTION     
            "Indicates the last state of the LSWU FSM. (Internal use only)"
    ::= { sonusSwUpgradeShelfStatEntry 9 }

sonusSwUpgradeShelfStatState OBJECT-TYPE
    SYNTAX          SonusSoftwareUpgradeState
    MAX-ACCESS      read-only
    STATUS          current
    DESCRIPTION     
            "Indicates the current state of the LSWU FSM. (Internal use only)"
    ::= { sonusSwUpgradeShelfStatEntry 10 }

sonusSwUpgradeShelfStatCurGroup OBJECT-TYPE
    SYNTAX          Integer32
    MAX-ACCESS      read-only
    STATUS          current
    DESCRIPTION     
            "Identifies the Redundancy Group Index currently being upgraded with new software.
             This is the index into the sonusRedundGroupTable MIB table."
    ::= { sonusSwUpgradeShelfStatEntry 11 }

sonusSwUpgradeSlotStatTable OBJECT-TYPE
    SYNTAX          SEQUENCE OF SonusSwUpgradeSlotStatEntry
    MAX-ACCESS      not-accessible
    STATUS          current
    DESCRIPTION     
            "This table contains status information about the software upgrade 
             on a shelf."
    ::= { sonusSoftwareUpgradeServicesMIBObjects 3 }

sonusSwUpgradeSlotStatEntry OBJECT-TYPE
    SYNTAX          SonusSwUpgradeSlotStatEntry
    MAX-ACCESS      not-accessible
    STATUS          current
    DESCRIPTION     
            ""
    INDEX           { sonusSwUpgradeSlotStatShelfIndex, 
                      sonusSwUpgradeSlotStatSlotIndex }
    ::= { sonusSwUpgradeSlotStatTable 1 }

SonusSwUpgradeSlotStatEntry ::=
    SEQUENCE {
        sonusSwUpgradeSlotStatShelfIndex SonusShelfIndex,
        sonusSwUpgradeSlotStatSlotIndex SonusSlotIndex,
        sonusSwUpgradeSlotStatStatus    INTEGER,
        sonusSwUpgradeSlotStatUpgrade   INTEGER,
        sonusSwUpgradeSlotStatVersion   DisplayString
    }

sonusSwUpgradeSlotStatShelfIndex OBJECT-TYPE
    SYNTAX          SonusShelfIndex
    MAX-ACCESS      read-only
    STATUS          current
    DESCRIPTION     
            "Identifies the target shelf within the node."
    ::= { sonusSwUpgradeSlotStatEntry 1 }

sonusSwUpgradeSlotStatSlotIndex OBJECT-TYPE
    SYNTAX          SonusSlotIndex
    MAX-ACCESS      read-only
    STATUS          current
    DESCRIPTION     
            "Identifies the target slot within the shelf."
    ::= { sonusSwUpgradeSlotStatEntry 2 }

sonusSwUpgradeSlotStatStatus OBJECT-TYPE
    SYNTAX          INTEGER { idle(1), busy(2), complete(3), unknown(4), 
                        noImageFile(5), invalidVersion(6) }
    MAX-ACCESS      read-only
    STATUS          current
    DESCRIPTION     
            "Identifies the software upgrade status of a slot."
    ::= { sonusSwUpgradeSlotStatEntry 3 }

sonusSwUpgradeSlotStatUpgrade OBJECT-TYPE
    SYNTAX          INTEGER { none(1), smooth(2), disrupt(3), 
                        unavailable(4), unknown(5) }
    MAX-ACCESS      read-only
    STATUS          current
    DESCRIPTION     
            ""
    ::= { sonusSwUpgradeSlotStatEntry 4 }

sonusSwUpgradeSlotStatVersion OBJECT-TYPE
    SYNTAX          DisplayString (SIZE(0..15))
    MAX-ACCESS      read-only
    STATUS          current
    DESCRIPTION     
            "The software version available for upgrade on the slot."
    ::= { sonusSwUpgradeSlotStatEntry 5 }

sonusSoftwareUpgradeServicesMIBNotifications OBJECT IDENTIFIER
    ::= { sonusSoftwareUpgradeServicesMIB 2 }

sonusSoftwareUpgradeServicesMIBNotificationsPrefix OBJECT IDENTIFIER
    ::= { sonusSoftwareUpgradeServicesMIBNotifications 0 }

sonusSoftwareUpgradeServicesMIBNotificationsObjects OBJECT IDENTIFIER
    ::= { sonusSoftwareUpgradeServicesMIBNotifications 1 }

sonusSoftwareUpgradeInitiatedNotification NOTIFICATION-TYPE
    OBJECTS         { sonusShelfIndex, sonusSwUpgradeShelfAdmnDirectory, 
                      sonusEventDescription, sonusEventClass, 
                      sonusEventLevel, sonusSequenceId, sonusEventTime }
    STATUS          current
    DESCRIPTION     
            "This trap indicates that a software upgrade to the
             specified Software Path directory has been initiated
             by the user for this shelf."
    ::= { sonusSoftwareUpgradeServicesMIBNotificationsPrefix 1 }

sonusSoftwareUpgradeTerminatedNotification NOTIFICATION-TYPE
    OBJECTS         { sonusShelfIndex, sonusSwUpgradeShelfAdmnDirectory, 
                      sonusSwUpgradeShelfStatLastReason, 
                      sonusEventDescription, sonusEventClass, 
                      sonusEventLevel, sonusSequenceId, sonusEventTime }
    STATUS          current
    DESCRIPTION     
            "This trap indicates that a software upgrade to the
             specified Software Path directory has terminated in
             this shelf for the specified reason."
    ::= { sonusSoftwareUpgradeServicesMIBNotificationsPrefix 2 }

sonusSoftwareUpgradeSucceededNotification NOTIFICATION-TYPE
    OBJECTS         { sonusShelfIndex, sonusSwUpgradeShelfAdmnDirectory, 
                      sonusSwUpgradeShelfStatLastReason, 
                      sonusEventDescription, sonusEventClass, 
                      sonusEventLevel, sonusSequenceId, sonusEventTime }
    STATUS          current
    DESCRIPTION     
            "This trap indicates that a software upgrade to the
             specified Software Path directory has succeeded in
             this shelf for the specified reason."
    ::= { sonusSoftwareUpgradeServicesMIBNotificationsPrefix 3 }

sonusSoftwareUpgradeCommitRequiredNotification NOTIFICATION-TYPE
    OBJECTS         { sonusShelfIndex, sonusSwUpgradeShelfAdmnDirectory, 
                      sonusEventDescription, sonusEventClass, 
                      sonusEventLevel, sonusSequenceId, sonusEventTime }
    STATUS          current
    DESCRIPTION     
            "This trap indicates that the Live Software Upgrade
             directory specified must be committed to NVS."
    ::= { sonusSoftwareUpgradeServicesMIBNotificationsPrefix 4 }

END -- end of module SONUS-SOFTWARE-UPGRADE-SERVICES-MIB.
