--
-- This SMIv2 module has been generated by smidump 0.2-cvs. Do not edit.
--

SONUS-IP-ACL-MIB DEFINITIONS ::= BEGIN

IMPORTS
    Ipv6Address
        FROM IPV6-TC
    Integer32, IpAddress, MODULE-IDENTITY, NOTIFICATION-TYPE, 
    OBJECT-TYPE, Unsigned32
        FROM SNMPv2-SMI
    DisplayString, RowStatus
        FROM SNMPv2-TC
    sonusEventClass, sonusEventDescription, sonusEventLevel, 
    sonusEventTime, sonusSequenceId
        FROM SONUS-COMMON-MIB
    sonusPacketMIBs
        FROM SONUS-SMI
    SonusAdminState, SonusName, SonusNameReference, SonusShelfIndex, 
    SonusSlotIndex
        FROM SONUS-TC;

sonusIpAclMIB MODULE-IDENTITY
    LAST-UPDATED    "201008100000Z"
    ORGANIZATION    
            "Sonus Networks, Inc."
    CONTACT-INFO    
            "   Customer Support    
             Sonus Networks, Inc.
             7 Technology Park Drive
             Westford, MA 01886
             USA
             
             Tel: 978-614-8100
             Fax: 978-614-8609"
    DESCRIPTION     
            "The MIB Module for IP Access Lists management."
    ::= { sonusPacketMIBs 12 }


sonusIpAcl OBJECT IDENTIFIER
    ::= { sonusIpAclMIB 1 }

sonusIpAclNextIndex OBJECT-TYPE
    SYNTAX          Integer32
    MAX-ACCESS      read-only
    STATUS          current
    DESCRIPTION     
            " The next valid index to use when creating a new
             sonusIpAclEntry "
    ::= { sonusIpAcl 1 }

sonusIpAclTable OBJECT-TYPE
    SYNTAX          SEQUENCE OF SonusIpAclEntry
    MAX-ACCESS      not-accessible
    STATUS          current
    DESCRIPTION     
            "The table of input filters."
    ::= { sonusIpAcl 2 }

sonusIpAclEntry OBJECT-TYPE
    SYNTAX          SonusIpAclEntry
    MAX-ACCESS      not-accessible
    STATUS          current
    DESCRIPTION     
            "The specification, filter fields, for an ip input filter."
    INDEX           { sonusIpAclIndex }
    ::= { sonusIpAclTable 1 }

SonusIpAclEntry ::=
    SEQUENCE {
        sonusIpAclShelf                 SonusShelfIndex,
        sonusIpAclSlot                  SonusSlotIndex,
        sonusIpAclIndex                 Integer32,
        sonusIpAclName                  SonusName,
        sonusIpAclProtocol              INTEGER,
        sonusIpAclPrecedence            Integer32,
        sonusIpAclNifGroupIndex         Integer32,
        sonusIpAclIfIndex               Integer32,
        sonusIpAclSrcPrefix             IpAddress,
        sonusIpAclSrcPrefixLen          Integer32,
        sonusIpAclDestPrefix            IpAddress,
        sonusIpAclDestPrefixLen         Integer32,
        sonusIpAclSrcPort               Integer32,
        sonusIpAclDestPort              Integer32,
        sonusIpAclAction                INTEGER,
        sonusIpAclState                 SonusAdminState,
        sonusIpAclRowStatus             RowStatus,
        sonusIpAclNifGroupName          SonusNameReference,
        sonusIpAclIfName                SonusNameReference,
        sonusIpAclSrc6Prefix            Ipv6Address,
        sonusIpAclDest6Prefix           Ipv6Address,
        sonusIpAclSrcIpVersion          INTEGER,
        sonusIpAclDestIpVersion         INTEGER
    }

sonusIpAclShelf OBJECT-TYPE
    SYNTAX          SonusShelfIndex
    MAX-ACCESS      read-write
    STATUS          current
    DESCRIPTION     
            "A 32-bit integer identifying the shelf of the IP input ACL"
    ::= { sonusIpAclEntry 1 }

sonusIpAclSlot OBJECT-TYPE
    SYNTAX          SonusSlotIndex
    MAX-ACCESS      read-write
    STATUS          current
    DESCRIPTION     
            "A 32-bit integer identifying the slot of the IP input ACL"
    ::= { sonusIpAclEntry 2 }

sonusIpAclIndex OBJECT-TYPE
    SYNTAX          Integer32
    MAX-ACCESS      read-only
    STATUS          current
    DESCRIPTION     
            "Integer index for entry; one for one with sonusIpAclName."
    ::= { sonusIpAclEntry 3 }

sonusIpAclName OBJECT-TYPE
    SYNTAX          SonusName
    MAX-ACCESS      read-write
    STATUS          current
    DESCRIPTION     
            "Name used by CLI to reference filter."
    ::= { sonusIpAclEntry 4 }

sonusIpAclProtocol OBJECT-TYPE
    SYNTAX          INTEGER { any(0), icmp(1), tcp(6), udp(17), ospf(89), 
                        sctp(132) }
    MAX-ACCESS      read-write
    STATUS          current
    DESCRIPTION     
            "Match IP protocol type. Following port parameters meanings
             are a function of the IP protocol type."
    DEFVAL          { any }
    ::= { sonusIpAclEntry 5 }

sonusIpAclPrecedence OBJECT-TYPE
    SYNTAX          Integer32
    MAX-ACCESS      read-write
    STATUS          current
    DESCRIPTION     
            "Precedence of the IP ACL rule"
    ::= { sonusIpAclEntry 6 }

sonusIpAclNifGroupIndex OBJECT-TYPE
    SYNTAX          Integer32
    MAX-ACCESS      read-write
    STATUS          current
    DESCRIPTION     
            "NIFgroup index "
    DEFVAL          { 0 }
    ::= { sonusIpAclEntry 7 }

sonusIpAclIfIndex OBJECT-TYPE
    SYNTAX          Integer32 (0..65535)
    MAX-ACCESS      read-write
    STATUS          current
    DESCRIPTION     
            "Match the interface index inclusive of start and end
             values of interface index. This variable specifies the
             start value."
    DEFVAL          { 0 }
    ::= { sonusIpAclEntry 8 }

sonusIpAclSrcPrefix OBJECT-TYPE
    SYNTAX          IpAddress
    MAX-ACCESS      read-write
    STATUS          current
    DESCRIPTION     
            "Match source address by validating against
             sourcePrefix and Source Mask/prefixlen. A value
             of 0 will match all sources"
    DEFVAL          { 0 }
    ::= { sonusIpAclEntry 9 }

sonusIpAclSrcPrefixLen OBJECT-TYPE
    SYNTAX          Integer32 (0..128)
    MAX-ACCESS      read-write
    STATUS          current
    DESCRIPTION     
            "Mask of the source address. When applied to source prefix it
             determines the range of addresses that match ACL"
    DEFVAL          { 0 }
    ::= { sonusIpAclEntry 10 }

sonusIpAclDestPrefix OBJECT-TYPE
    SYNTAX          IpAddress
    MAX-ACCESS      read-write
    STATUS          current
    DESCRIPTION     
            "Match destination address by validating against
             DestPrefix and Destination Mask/prefixlen. A value of
             0 matches all destinations"
    DEFVAL          { 0 }
    ::= { sonusIpAclEntry 11 }

sonusIpAclDestPrefixLen OBJECT-TYPE
    SYNTAX          Integer32 (0..128)
    MAX-ACCESS      read-write
    STATUS          current
    DESCRIPTION     
            "Mask of the destinationaddress. When applied to destination
             prefix it determines the range of addresses that match ACL"
    DEFVAL          { 0 }
    ::= { sonusIpAclEntry 12 }

sonusIpAclSrcPort OBJECT-TYPE
    SYNTAX          Integer32 (0..65535)
    MAX-ACCESS      read-write
    STATUS          current
    DESCRIPTION     
            "Match source IP port inclusive of 
             sonusIpAclSrcPortStart and sonusIpAclSrcPortEnd.
             If sonusIpAclSrcPort is set to ZERO, all values will match"
    DEFVAL          { 0 }
    ::= { sonusIpAclEntry 13 }

sonusIpAclDestPort OBJECT-TYPE
    SYNTAX          Integer32 (0..65535)
    MAX-ACCESS      read-write
    STATUS          current
    DESCRIPTION     
            "Match destination IP port inclusive of 
             sonusIpAclDestPortStart and sonusIpAclDestPortEnd.
             If sonusIpAclDesPort is set to ZERO, all values will match"
    DEFVAL          { 0 }
    ::= { sonusIpAclEntry 14 }

sonusIpAclAction OBJECT-TYPE
    SYNTAX          INTEGER { permit(1), deny(2) }
    MAX-ACCESS      read-write
    STATUS          current
    DESCRIPTION     
            "Action to be taken if the ACL matches the received packet. 
             Only enabled, disabled are supported and rate-limiting is left 
             for future"
    DEFVAL          { 1 }
    ::= { sonusIpAclEntry 15 }

sonusIpAclState OBJECT-TYPE
    SYNTAX          SonusAdminState
    MAX-ACCESS      read-write
    STATUS          current
    DESCRIPTION     
            "Controls the desired state of the filter. A filter
             can only be enabled if it is unique among existing
             enabled filters"
    DEFVAL          { disabled }
    ::= { sonusIpAclEntry 16 }

sonusIpAclRowStatus OBJECT-TYPE
    SYNTAX          RowStatus
    MAX-ACCESS      read-write
    STATUS          current
    DESCRIPTION     
            ""
    ::= { sonusIpAclEntry 17 }

sonusIpAclNifGroupName OBJECT-TYPE
    SYNTAX          SonusNameReference
    MAX-ACCESS      read-write
    STATUS          current
    DESCRIPTION     
            "NIF Group name associated with the ACL"
    ::= { sonusIpAclEntry 18 }

sonusIpAclIfName OBJECT-TYPE
    SYNTAX          SonusNameReference
    MAX-ACCESS      read-write
    STATUS          current
    DESCRIPTION     
            "Interface name associated with the ACL"
    ::= { sonusIpAclEntry 19 }

sonusIpAclSrc6Prefix OBJECT-TYPE
    SYNTAX          Ipv6Address
    MAX-ACCESS      read-write
    STATUS          current
    DESCRIPTION     
            "Match source IPv6 address by validating against
             sourcePrefix and Source Mask/prefixlen. A value
             of 0 will match all sources"
    ::= { sonusIpAclEntry 20 }

sonusIpAclDest6Prefix OBJECT-TYPE
    SYNTAX          Ipv6Address
    MAX-ACCESS      read-write
    STATUS          current
    DESCRIPTION     
            "Match destination IPv6 address by validating against
             DestPrefix and Destination Mask/prefixlen. A value of
             0 matches all destinations"
    ::= { sonusIpAclEntry 21 }

sonusIpAclSrcIpVersion OBJECT-TYPE
    SYNTAX          INTEGER { afInet(2), afInet6(24) }
    MAX-ACCESS      read-only
    STATUS          current
    DESCRIPTION     
            "Source IP Version"
    ::= { sonusIpAclEntry 22 }

sonusIpAclDestIpVersion OBJECT-TYPE
    SYNTAX          INTEGER { afInet(2), afInet6(24) }
    MAX-ACCESS      read-only
    STATUS          current
    DESCRIPTION     
            "Destination IP Version"
    ::= { sonusIpAclEntry 23 }

sonusIpAclStatusTable OBJECT-TYPE
    SYNTAX          SEQUENCE OF SonusIpAclStatusEntry
    MAX-ACCESS      not-accessible
    STATUS          current
    DESCRIPTION     
            "IP input ACLs status table"
    ::= { sonusIpAcl 3 }

sonusIpAclStatusEntry OBJECT-TYPE
    SYNTAX          SonusIpAclStatusEntry
    MAX-ACCESS      not-accessible
    STATUS          current
    DESCRIPTION     
            "fields of an Input IP ACL status table"
    INDEX           { sonusIpAclStatSlot, sonusIpAclStatIndex }
    ::= { sonusIpAclStatusTable 1 }

SonusIpAclStatusEntry ::=
    SEQUENCE {
        sonusIpAclStatShelf             SonusShelfIndex,
        sonusIpAclStatSlot              SonusSlotIndex,
        sonusIpAclStatIndex             Integer32,
        sonusIpAclStatHitCount          Unsigned32,
        sonusIpAclStatName              DisplayString,
        sonusIpAclStatState             SonusAdminState,
        sonusIpAclStatConfigured        Unsigned32,
        sonusIpAclStatAvailable         Unsigned32
    }

sonusIpAclStatShelf OBJECT-TYPE
    SYNTAX          SonusShelfIndex
    MAX-ACCESS      read-only
    STATUS          current
    DESCRIPTION     
            "A 32-bit integer identifying the shelf of the IP input ACL"
    ::= { sonusIpAclStatusEntry 1 }

sonusIpAclStatSlot OBJECT-TYPE
    SYNTAX          SonusSlotIndex
    MAX-ACCESS      read-only
    STATUS          current
    DESCRIPTION     
            "A 32-bit integer identifying the slot of the IP input ACL"
    ::= { sonusIpAclStatusEntry 2 }

sonusIpAclStatIndex OBJECT-TYPE
    SYNTAX          Integer32
    MAX-ACCESS      read-only
    STATUS          current
    DESCRIPTION     
            "Integer index for entry corresponding to an input ip
             acl entry.  This value must correspond to an
             existing sonusIpAclIndex."
    ::= { sonusIpAclStatusEntry 3 }

sonusIpAclStatHitCount OBJECT-TYPE
    SYNTAX          Unsigned32
    MAX-ACCESS      read-only
    STATUS          current
    DESCRIPTION     
            "Number of incoming IP packets matched this ACL"
    ::= { sonusIpAclStatusEntry 4 }

sonusIpAclStatName OBJECT-TYPE
    SYNTAX          DisplayString (SIZE(0..23))
    MAX-ACCESS      read-only
    STATUS          current
    DESCRIPTION     
            "Name used by CLI to reference filter."
    ::= { sonusIpAclStatusEntry 5 }

sonusIpAclStatState OBJECT-TYPE
    SYNTAX          SonusAdminState
    MAX-ACCESS      read-only
    STATUS          current
    DESCRIPTION     
            "Controls the desired state of the filter. A filter
             can only be enabled if it is unique among existing
             enabled filters"
    ::= { sonusIpAclStatusEntry 6 }

sonusIpAclStatConfigured OBJECT-TYPE
    SYNTAX          Unsigned32
    MAX-ACCESS      read-only
    STATUS          current
    DESCRIPTION     
            "Number of IP ACLs configured"
    ::= { sonusIpAclStatusEntry 7 }

sonusIpAclStatAvailable OBJECT-TYPE
    SYNTAX          Unsigned32
    MAX-ACCESS      read-only
    STATUS          current
    DESCRIPTION     
            "Number of IP ACLs available"
    ::= { sonusIpAclStatusEntry 8 }

END -- end of module SONUS-IP-ACL-MIB.
