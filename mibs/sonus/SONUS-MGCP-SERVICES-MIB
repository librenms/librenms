--
-- This SMIv2 module has been generated by smidump 0.2-cvs. Do not edit.
--

SONUS-MGCP-SERVICES-MIB DEFINITIONS ::= BEGIN

IMPORTS
    Integer32, IpAddress, MODULE-IDENTITY, NOTIFICATION-TYPE, 
    OBJECT-TYPE
        FROM SNMPv2-SMI
    DisplayString, RowStatus
        FROM SNMPv2-TC
    sonusEventClass, sonusEventDescription, sonusEventLevel, 
    sonusEventTime, sonusSequenceId
        FROM SONUS-COMMON-MIB
    sonusServicesMIBs
        FROM SONUS-SMI
    SonusAdminState, SonusBoolean, SonusName, SonusNameReference, 
    SonusServiceState, SonusShelfIndex, SonusSlotIndex, SonusSupportFlag
        FROM SONUS-TC;

sonusMgcpServicesMIB MODULE-IDENTITY
    LAST-UPDATED    "201105240000Z"
    ORGANIZATION    
            "Sonus Networks, Inc."
    CONTACT-INFO    
            "   Customer Support    
             Sonus Networks, Inc.
             7 Technology Park Drive
             Westford, MA 01886
             USA
             
             Tel: 978-614-8100
             Fax: 978-614-8609"
    DESCRIPTION     
            "The MIB Module for MGCP Services Management."
    ::= { sonusServicesMIBs 12 }


sonusMgcpServicesMIBObjects OBJECT IDENTIFIER
    ::= { sonusMgcpServicesMIB 1 }

sonusMgcpGateway OBJECT IDENTIFIER
    ::= { sonusMgcpServicesMIBObjects 1 }

sonusMgcpGatewayPort OBJECT-TYPE
    SYNTAX          Integer32 (0..65535)
    MAX-ACCESS      read-write
    STATUS          current
    DESCRIPTION     
            "Specifies local listen port.  A value of 0 indicates
             the local listen port is unspecified and the protocol
             specific default port should be used:
                 MGCP default listen port: 2427
                 H248 default listen port: 2944"
    DEFVAL          { 0 }
    ::= { sonusMgcpGateway 1 }

sonusMgcpGatewayRxThrottle OBJECT-TYPE
    SYNTAX          Integer32 (0..65535)
    MAX-ACCESS      read-write
    STATUS          current
    DESCRIPTION     
            "Receive flow control threshold. 
             Sets maximum limit on number of concurrent outstanding 
             MGCP/H248 commands which have not been responded to.
             The value 0 disables flow control."
    DEFVAL          { 0 }
    ::= { sonusMgcpGateway 2 }

sonusMgcpGatewayMaxReXmit OBJECT-TYPE
    SYNTAX          Integer32 (1..5000)
    MAX-ACCESS      read-write
    STATUS          current
    DESCRIPTION     
            "Maximum consecutive re-transmissions of one MGCP command."
    DEFVAL          { 5 }
    ::= { sonusMgcpGateway 3 }

sonusMgcpGatewayCmdTimeout OBJECT-TYPE
    SYNTAX          Integer32 (1..10000)
    MAX-ACCESS      read-write
    STATUS          current
    DESCRIPTION     
            "MGCP command re-transmission timeout in Msec"
    DEFVAL          { 250 }
    ::= { sonusMgcpGateway 4 }

sonusMgcpGatewayRspTimeout OBJECT-TYPE
    SYNTAX          Integer32 (1..65535)
    MAX-ACCESS      read-write
    STATUS          current
    DESCRIPTION     
            "Response cache purge timeout interval in Msec"
    DEFVAL          { 1000 }
    ::= { sonusMgcpGateway 5 }

sonusMgcpGatewayCriticalTimeout OBJECT-TYPE
    SYNTAX          Integer32 (50..60000)
    MAX-ACCESS      read-write
    STATUS          current
    DESCRIPTION     
            "DTMF Interdigit timer-Critical in Msec"
    DEFVAL          { 4000 }
    ::= { sonusMgcpGateway 6 }

sonusMgcpGatewayPartialTimeout OBJECT-TYPE
    SYNTAX          Integer32 (50..60000)
    MAX-ACCESS      read-write
    STATUS          current
    DESCRIPTION     
            "DTMF Interdigit timer-Partial in Msec"
    DEFVAL          { 16000 }
    ::= { sonusMgcpGateway 7 }

sonusMgcpGatewayMsgPiggyBacking OBJECT-TYPE
    SYNTAX          SonusBoolean
    MAX-ACCESS      read-write
    STATUS          current
    DESCRIPTION     
            "Enable-disable piggy backing of messages sent to Call Agents"
    DEFVAL          { true }
    ::= { sonusMgcpGateway 8 }

sonusMgcpGatewayMaxIPReXmit OBJECT-TYPE
    SYNTAX          Integer32 (1..5000)
    MAX-ACCESS      read-write
    STATUS          current
    DESCRIPTION     
            "Maximum consecutive re-transmissions to one Call Agent IP address."
    DEFVAL          { 5 }
    ::= { sonusMgcpGateway 9 }

sonusMgcpGatewayMaxPwrOnWaitDelay OBJECT-TYPE
    SYNTAX          Integer32 (50..60000)
    MAX-ACCESS      read-write
    STATUS          current
    DESCRIPTION     
            "Maximum Power-On RSIP transmit delay (MS)"
    DEFVAL          { 5000 }
    ::= { sonusMgcpGateway 10 }

sonusMgcpGatewayMaxDiscWaitDelay OBJECT-TYPE
    SYNTAX          Integer32 (50..60000)
    MAX-ACCESS      read-write
    STATUS          current
    DESCRIPTION     
            "Maximum Disc RSIP transmit delay (MS)"
    DEFVAL          { 5000 }
    ::= { sonusMgcpGateway 11 }

sonusMgcpGatewayDiscWaitDelayBound OBJECT-TYPE
    SYNTAX          Integer32 (50..300000)
    MAX-ACCESS      read-write
    STATUS          current
    DESCRIPTION     
            "Upper Bound on Power-On RSIP transmit delay (MS)"
    DEFVAL          { 5000 }
    ::= { sonusMgcpGateway 12 }

sonusMgcpGatewayLocalIpAddr OBJECT-TYPE
    SYNTAX          IpAddress
    MAX-ACCESS      read-write
    STATUS          current
    DESCRIPTION     
            "Specifies the (optional) logical IP Address local to this Gateway."
    DEFVAL          { '00000000'H }
    ::= { sonusMgcpGateway 13 }

sonusMgcpGatewayH248Encoding OBJECT-TYPE
    SYNTAX          INTEGER { binary(1), text(2), shortText(3) }
    MAX-ACCESS      read-write
    STATUS          current
    DESCRIPTION     
            "Selects the encoding of H.248 messages.  Encoding examples
             for the Service Change token are listed below:
             binary(1):     7  (00000111)
             text(2):      'SERVICECHANGE'
             shortText(3): 'SC'
             Note1: currently the GSX does not support binary encoding.
             Note2: this field is only applicable to H248 messages."
    DEFVAL          { text }
    ::= { sonusMgcpGateway 14 }

sonusMgcpGatewaySlotCrcxRxThrottle OBJECT-TYPE
    SYNTAX          Integer32 (0..65535)
    MAX-ACCESS      read-write
    STATUS          current
    DESCRIPTION     
            "Receive flow control threshold for ADD/CRCX commands per slot.
             Sets maximum limit on number of concurrent outstanding 
             H248/MGCP commands which have not been responded to.
             The value 0 disables flow control."
    DEFVAL          { 40 }
    ::= { sonusMgcpGateway 15 }

sonusMgcpGatewaySlotRxThrottle OBJECT-TYPE
    SYNTAX          Integer32 (0..65535)
    MAX-ACCESS      read-write
    STATUS          current
    DESCRIPTION     
            "Receive flow control threshold for all commands per slot. 
             Sets maximum limit on number of concurrent outstanding 
             H248/MGCP commands which have not been responded to.
             The value 0 disables flow control."
    DEFVAL          { 80 }
    ::= { sonusMgcpGateway 16 }

sonusMgcpGatewayProvRspTimer OBJECT-TYPE
    SYNTAX          Integer32 (0..9999)
    MAX-ACCESS      read-write
    STATUS          current
    DESCRIPTION     
            "Indicates the time within which the MGC should expect a
             Pending Response from the MG requires additional time to
             process a Transaction."
    DEFVAL          { 1000 }
    ::= { sonusMgcpGateway 17 }

sonusMgcpGatewayStartInputTimeout OBJECT-TYPE
    SYNTAX          Integer32 (0..60000)
    MAX-ACCESS      read-write
    STATUS          current
    DESCRIPTION     
            "DTMF Predigit timer in Msec"
    DEFVAL          { 15000 }
    ::= { sonusMgcpGateway 18 }

sonusMgcpGatewayNifGroupName OBJECT-TYPE
    SYNTAX          SonusNameReference
    MAX-ACCESS      read-write
    STATUS          current
    DESCRIPTION     
            "The NIF Group which this MGCP/H248 application port belongs to."
    ::= { sonusMgcpGateway 19 }

sonusMgcpGatewayNetworkAccess OBJECT-TYPE
    SYNTAX          INTEGER { none(1), nifgroup(2), anynif(3) }
    MAX-ACCESS      read-write
    STATUS          current
    DESCRIPTION     
            "The Network access type of MGCP/H248 application. Option NONE is basically as good as disabled; NIFGROUP uses only the interfaces in the NIF group; ANYNIF would use any of the interfaces"
    DEFVAL          { nifgroup }
    ::= { sonusMgcpGateway 20 }

sonusMgcpGatewaySlotAuditRxThrottle OBJECT-TYPE
    SYNTAX          Integer32 (0..65535)
    MAX-ACCESS      read-write
    STATUS          current
    DESCRIPTION     
            "Receive flow control threshold for AUDIT commands per slot.
             Sets maximum limit on number of concurrent outstanding 
             H248/MGCP commands which have not been responded to.
             The value 0 disables flow control."
    DEFVAL          { 40 }
    ::= { sonusMgcpGateway 21 }

sonusMgcpGatewayRateIncrementTimer OBJECT-TYPE
    SYNTAX          Integer32 (0..100)
    MAX-ACCESS      read-write
    STATUS          current
    DESCRIPTION     
            "Rate increment timer to be used while increasing the leak rate"
    DEFVAL          { 1 }
    ::= { sonusMgcpGateway 22 }

sonusMgcpGatewayLeakRateGrowthFactor OBJECT-TYPE
    SYNTAX          Integer32 (1..200)
    MAX-ACCESS      read-write
    STATUS          current
    DESCRIPTION     
            "Leak rate growth factor to be used while increasing the leak rate"
    DEFVAL          { 1 }
    ::= { sonusMgcpGateway 23 }

sonusMgcpGatewayAutonomousSupport OBJECT-TYPE
    SYNTAX          SonusSupportFlag
    MAX-ACCESS      read-write
    STATUS          current
    DESCRIPTION     
            "Used to enable/disable the autonomous mode on system"
    DEFVAL          { unsupported }
    ::= { sonusMgcpGateway 24 }

sonusMgcpGatewayBurstSize OBJECT-TYPE
    SYNTAX          Integer32 (1..5)
    MAX-ACCESS      read-write
    STATUS          current
    DESCRIPTION     
            "The factor to calculate the burst size for the policer during ASX overload"
    DEFVAL          { 1 }
    ::= { sonusMgcpGateway 26 }

sonusMgcpGatewayMaxLeakRate OBJECT-TYPE
    SYNTAX          Integer32 (0..65535)
    MAX-ACCESS      read-write
    STATUS          current
    DESCRIPTION     
            "The max leak rate of the MGW"
    DEFVAL          { 4000 }
    ::= { sonusMgcpGateway 27 }

sonusMgcpGatewayDmapValue OBJECT-TYPE
    SYNTAX          OCTET STRING (SIZE(1..1024))
    MAX-ACCESS      read-write
    STATUS          current
    DESCRIPTION     
            "This field indicates the digitmap value armed by the GSX when ASX sends the MODIFY digitmap"
    ::= { sonusMgcpGateway 31 }

sonusMgcpSession OBJECT IDENTIFIER
    ::= { sonusMgcpServicesMIBObjects 2 }

sonusMgcpSessionNextIndex OBJECT-TYPE
    SYNTAX          Integer32
    MAX-ACCESS      read-only
    STATUS          current
    DESCRIPTION     
            "The next valid index to use when creating a new sonusMgcpSessionEntry"
    ::= { sonusMgcpSession 1 }

sonusMgcpSessionTable OBJECT-TYPE
    SYNTAX          SEQUENCE OF SonusMgcpSessionEntry
    MAX-ACCESS      not-accessible
    STATUS          current
    DESCRIPTION     
            "This table specifies the MGCP Session list for the GSX node."
    ::= { sonusMgcpSession 2 }

sonusMgcpSessionEntry OBJECT-TYPE
    SYNTAX          SonusMgcpSessionEntry
    MAX-ACCESS      not-accessible
    STATUS          current
    DESCRIPTION     
            ""
    INDEX           { sonusMgcpSessionIndex }
    ::= { sonusMgcpSessionTable 1 }

SonusMgcpSessionEntry ::=
    SEQUENCE {
        sonusMgcpSessionIndex           Integer32,
        sonusMgcpSessionName            SonusName,
        sonusMgcpSessionMode            SonusServiceState,
        sonusMgcpSessionState           SonusAdminState,
        sonusMgcpSessionRowStatus       RowStatus,
        sonusMgcpSessionServProfileName SonusNameReference,
        sonusMgcpSessionProtID          INTEGER
    }

sonusMgcpSessionIndex OBJECT-TYPE
    SYNTAX          Integer32
    MAX-ACCESS      read-only
    STATUS          current
    DESCRIPTION     
            "Identifies the target MGCP Session entry."
    ::= { sonusMgcpSessionEntry 1 }

sonusMgcpSessionName OBJECT-TYPE
    SYNTAX          SonusName
    MAX-ACCESS      read-write
    STATUS          current
    DESCRIPTION     
            "The name of this MGCP Session instance."
    ::= { sonusMgcpSessionEntry 2 }

sonusMgcpSessionMode OBJECT-TYPE
    SYNTAX          SonusServiceState
    MAX-ACCESS      read-write
    STATUS          current
    DESCRIPTION     
            "Specifies the operating mode of this MGCP Session."
    DEFVAL          { inService }
    ::= { sonusMgcpSessionEntry 3 }

sonusMgcpSessionState OBJECT-TYPE
    SYNTAX          SonusAdminState
    MAX-ACCESS      read-write
    STATUS          current
    DESCRIPTION     
            "The administrative state of this MGCP Session entry."
    DEFVAL          { disabled }
    ::= { sonusMgcpSessionEntry 4 }

sonusMgcpSessionRowStatus OBJECT-TYPE
    SYNTAX          RowStatus
    MAX-ACCESS      read-write
    STATUS          current
    DESCRIPTION     
            ""
    ::= { sonusMgcpSessionEntry 5 }

sonusMgcpSessionServProfileName OBJECT-TYPE
    SYNTAX          SonusNameReference
    MAX-ACCESS      read-write
    STATUS          current
    DESCRIPTION     
            "The name of the service profile this MGCP Session is bound to."
    DEFVAL          { "default" }
    ::= { sonusMgcpSessionEntry 6 }

sonusMgcpSessionProtID OBJECT-TYPE
    SYNTAX          INTEGER { mgcpstd(1), mgcpcmnctl(2), tgcp(3), 
                        h248v1vmg(4), h248v2vmg(5), h248v1std(6), 
                        h248v2std(7), h248v3bgf(8) }
    MAX-ACCESS      read-write
    STATUS          current
    DESCRIPTION     
            "The protocol type ID for this session.
             mgcpstd    - Media Gateway Control Protocol (standard)
             mgcpcmnctl - Media Gateway Control Protocol (common control)
             tgcp       - Trunking Gateway Control Protocol (packet cable)
             h248v1vmg  - H248/MEGACO V1 (virtual media gateways)
             h248v2vmg  - H248/MEGACO V2 (virtual media gateways)
             h248v1std  - H248/MEGACO V1 (standard)
             h248v2std  - H248/MEGACO V2 (standard)
             h248v3bgf  - H248/MEGACO V3 (BGF)"
    DEFVAL          { mgcpcmnctl }
    ::= { sonusMgcpSessionEntry 7 }

sonusMgcpCallAgnt OBJECT IDENTIFIER
    ::= { sonusMgcpServicesMIBObjects 3 }

sonusMgcpCallAgntNextIndex OBJECT-TYPE
    SYNTAX          Integer32
    MAX-ACCESS      read-only
    STATUS          current
    DESCRIPTION     
            "The next valid index to use when creating a new sonusMgcpCallAgntEntry"
    ::= { sonusMgcpCallAgnt 1 }

sonusMgcpCallAgntTable OBJECT-TYPE
    SYNTAX          SEQUENCE OF SonusMgcpCallAgntEntry
    MAX-ACCESS      not-accessible
    STATUS          current
    DESCRIPTION     
            "This table specifies the MGCP Call Agent list for the GSX node."
    ::= { sonusMgcpCallAgnt 2 }

sonusMgcpCallAgntEntry OBJECT-TYPE
    SYNTAX          SonusMgcpCallAgntEntry
    MAX-ACCESS      not-accessible
    STATUS          current
    DESCRIPTION     
            ""
    INDEX           { sonusMgcpCallAgntIndex }
    ::= { sonusMgcpCallAgntTable 1 }

SonusMgcpCallAgntEntry ::=
    SEQUENCE {
        sonusMgcpCallAgntIndex          Integer32,
        sonusMgcpCallAgntName           SonusName,
        sonusMgcpCallAgntState          SonusAdminState,
        sonusMgcpCallAgntRowStatus      RowStatus,
        sonusMgcpCallAgntSessionName    SonusNameReference,
        sonusMgcpCallAgntDefNotEnt      SonusBoolean
    }

sonusMgcpCallAgntIndex OBJECT-TYPE
    SYNTAX          Integer32
    MAX-ACCESS      read-only
    STATUS          current
    DESCRIPTION     
            "Identifies the target MGCP Call Agent entry."
    ::= { sonusMgcpCallAgntEntry 1 }

sonusMgcpCallAgntName OBJECT-TYPE
    SYNTAX          SonusName
    MAX-ACCESS      read-write
    STATUS          current
    DESCRIPTION     
            "The name of this MGCP Call Agent instance."
    ::= { sonusMgcpCallAgntEntry 2 }

sonusMgcpCallAgntState OBJECT-TYPE
    SYNTAX          SonusAdminState
    MAX-ACCESS      read-write
    STATUS          current
    DESCRIPTION     
            "The administrative state of this MGCP Call Agent entry."
    DEFVAL          { disabled }
    ::= { sonusMgcpCallAgntEntry 4 }

sonusMgcpCallAgntRowStatus OBJECT-TYPE
    SYNTAX          RowStatus
    MAX-ACCESS      read-write
    STATUS          current
    DESCRIPTION     
            ""
    ::= { sonusMgcpCallAgntEntry 5 }

sonusMgcpCallAgntSessionName OBJECT-TYPE
    SYNTAX          SonusNameReference
    MAX-ACCESS      read-write
    STATUS          current
    DESCRIPTION     
            "The name of the MGCP Session this Call Agent is bound to."
    ::= { sonusMgcpCallAgntEntry 6 }

sonusMgcpCallAgntDefNotEnt OBJECT-TYPE
    SYNTAX          SonusBoolean
    MAX-ACCESS      read-write
    STATUS          current
    DESCRIPTION     
            "Designates this Call Agent as the default notified entity."
    DEFVAL          { false }
    ::= { sonusMgcpCallAgntEntry 7 }

sonusMgcpConnectionTable OBJECT-TYPE
    SYNTAX          SEQUENCE OF SonusMgcpConnectionEntry
    MAX-ACCESS      not-accessible
    STATUS          current
    DESCRIPTION     
            "This table specifies the MGCP Connection list for the GSX node."
    ::= { sonusMgcpServicesMIBObjects 4 }

sonusMgcpConnectionEntry OBJECT-TYPE
    SYNTAX          SonusMgcpConnectionEntry
    MAX-ACCESS      not-accessible
    STATUS          current
    DESCRIPTION     
            ""
    INDEX           { sonusMgcpConnectionIpaddr, sonusMgcpConnectionPort }
    ::= { sonusMgcpConnectionTable 1 }

SonusMgcpConnectionEntry ::=
    SEQUENCE {
        sonusMgcpConnectionIpaddr       IpAddress,
        sonusMgcpConnectionPort         Integer32,
        sonusMgcpConnectionState        SonusAdminState,
        sonusMgcpConnectionRowStatus    RowStatus,
        sonusMgcpConnectionCallAgntName SonusNameReference,
        sonusMgcpConnectionIpPriority   INTEGER
    }

sonusMgcpConnectionIpaddr OBJECT-TYPE
    SYNTAX          IpAddress
    MAX-ACCESS      read-only
    STATUS          current
    DESCRIPTION     
            "Specifies the IP Address of the Call Agent connection.
             This is an allowed address for the named Call Agent."
    ::= { sonusMgcpConnectionEntry 1 }

sonusMgcpConnectionPort OBJECT-TYPE
    SYNTAX          Integer32 (1..65535)
    MAX-ACCESS      read-only
    STATUS          current
    DESCRIPTION     
            "Specifies the port nummber of the Call Agent connection."
    DEFVAL          { 2427 }
    ::= { sonusMgcpConnectionEntry 2 }

sonusMgcpConnectionState OBJECT-TYPE
    SYNTAX          SonusAdminState
    MAX-ACCESS      read-write
    STATUS          current
    DESCRIPTION     
            "The administrative state of this MGCP Connection entry."
    DEFVAL          { disabled }
    ::= { sonusMgcpConnectionEntry 3 }

sonusMgcpConnectionRowStatus OBJECT-TYPE
    SYNTAX          RowStatus
    MAX-ACCESS      read-write
    STATUS          current
    DESCRIPTION     
            ""
    ::= { sonusMgcpConnectionEntry 4 }

sonusMgcpConnectionCallAgntName OBJECT-TYPE
    SYNTAX          SonusNameReference
    MAX-ACCESS      read-write
    STATUS          current
    DESCRIPTION     
            "The name of the MGCP Call Agent this Connection is bound to."
    ::= { sonusMgcpConnectionEntry 5 }

sonusMgcpConnectionIpPriority OBJECT-TYPE
    SYNTAX          INTEGER { primary(1), secondary(2) }
    MAX-ACCESS      read-write
    STATUS          current
    DESCRIPTION     
            "The priority of the call agent IP."
    DEFVAL          { secondary }
    ::= { sonusMgcpConnectionEntry 8 }

sonusMgcpSessionStatusTable OBJECT-TYPE
    SYNTAX          SEQUENCE OF SonusMgcpSessionStatusEntry
    MAX-ACCESS      not-accessible
    STATUS          current
    DESCRIPTION     
            "This table specifies the status MGCP Sessions for the GSX node."
    ::= { sonusMgcpServicesMIBObjects 5 }

sonusMgcpSessionStatusEntry OBJECT-TYPE
    SYNTAX          SonusMgcpSessionStatusEntry
    MAX-ACCESS      not-accessible
    STATUS          current
    DESCRIPTION     
            ""
    INDEX           { sonusMgcpSessionStatusIndex }
    ::= { sonusMgcpSessionStatusTable 1 }

SonusMgcpSessionStatusEntry ::=
    SEQUENCE {
        sonusMgcpSessionStatusIndex     Integer32,
        sonusMgcpSessionStatusMajorVersion  Integer32,
        sonusMgcpSessionStatusMinorVersion  Integer32,
        sonusMgcpSessionStatusNumCallAgnts  Integer32,
        sonusMgcpSessionStatusStatus    INTEGER,
        sonusMgcpSessionStatusRxMsgTotal Integer32,
        sonusMgcpSessionStatusTxMsgTotal Integer32,
        sonusMgcpSessionStatusRxCmdTotal Integer32,
        sonusMgcpSessionStatusRxRspTotal Integer32,
        sonusMgcpSessionStatusTxCmdTotal Integer32,
        sonusMgcpSessionStatusTxRspTotal Integer32,
        sonusMgcpSessionStatusTxTOTotal Integer32,
        sonusMgcpSessionStatusTxAbortTotal  Integer32,
        sonusMgcpSessionStatusTxErrTotal Integer32,
        sonusMgcpSessionStatusRxTOTotal Integer32,
        sonusMgcpSessionStatusRxDupCmdTotal   Integer32,
        sonusMgcpSessionStatusRxDupRspTotal   Integer32,
        sonusMgcpSessionStatusRxRspErrTotal   Integer32,
        sonusMgcpSessionStatusRxRspInPTotal   Integer32,
        sonusMgcpSessionStatusRxUnknownTotal    Integer32,
        sonusMgcpSessionStatusRxOverLenTotal    Integer32,
        sonusMgcpSessionStatusRxMaxByteCnt  Integer32,
        sonusMgcpSessionStatusRxMaxPigBCnt  Integer32,
        sonusMgcpSessionStatusTxMaxByteCnt  Integer32,
        sonusMgcpSessionStatusTxMaxPigBCnt  Integer32,
        sonusMgcpSessionStatusTxMaxCmdPnd Integer32,
        sonusMgcpSessionStatusTxMaxRspPnd Integer32,
        sonusMgcpSessionStatusRxCmdThrotCnt   Integer32,
        sonusMgcpSessionStatusRxErrorTotal  Integer32,
        sonusMgcpSessionStatusTxErrorTotal  Integer32,
        sonusMgcpSessionStatusRxCRCX    Integer32,
        sonusMgcpSessionStatusRxCRCXL   Integer32,
        sonusMgcpSessionStatusRxMDCX    Integer32,
        sonusMgcpSessionStatusRxDLCX    Integer32,
        sonusMgcpSessionStatusRxRQNT    Integer32,
        sonusMgcpSessionStatusRxEPCF    Integer32,
        sonusMgcpSessionStatusRxAUDT    Integer32,
        sonusMgcpSessionStatusTxCRCXRsp Integer32,
        sonusMgcpSessionStatusTxCRCXRspL Integer32,
        sonusMgcpSessionStatusTxCRCXRspErr  Integer32,
        sonusMgcpSessionStatusTxMDCXRsp Integer32,
        sonusMgcpSessionStatusTxMDCXRspErr  Integer32,
        sonusMgcpSessionStatusTxDLCXRsp Integer32,
        sonusMgcpSessionStatusTxDLCXRspErr  Integer32,
        sonusMgcpSessionStatusTxAUDTRsp Integer32,
        sonusMgcpSessionStatusTxAUDTRspErr  Integer32,
        sonusMgcpSessionStatusTxRQNTRsp Integer32,
        sonusMgcpSessionStatusTxRQNTRspErr  Integer32,
        sonusMgcpSessionStatusTxRSIPCmd Integer32,
        sonusMgcpSessionStatusTxNTFYCmd Integer32,
        sonusMgcpSessionStatusTxDLCXCmd Integer32,
        sonusMgcpSessionStatusRxDC900   Integer32,
        sonusMgcpSessionStatusRxFL909   Integer32,
        sonusMgcpSessionStatusRxFO904   Integer32,
        sonusMgcpSessionStatusRxFO905   Integer32,
        sonusMgcpSessionStatusRxGR905   Integer32,
        sonusMgcpSessionStatusRxHO903   Integer32,
        sonusMgcpSessionStatusRxRS900   Integer32,
        sonusMgcpSessionStatusRxRS901   Integer32,
        sonusMgcpSessionStatusRxRS902   Integer32,
        sonusMgcpSessionStatusRxDC909   Integer32,
        sonusMgcpSessionStatusRxFO908   Integer32,
        sonusMgcpSessionStatusTxDC900   Integer32,
        sonusMgcpSessionStatusTxFL909   Integer32,
        sonusMgcpSessionStatusTxFO904   Integer32,
        sonusMgcpSessionStatusTxFO905   Integer32,
        sonusMgcpSessionStatusTxGR905   Integer32,
        sonusMgcpSessionStatusTxHO903   Integer32,
        sonusMgcpSessionStatusTxRS900   Integer32,
        sonusMgcpSessionStatusTxRS901   Integer32,
        sonusMgcpSessionStatusTxRS902   Integer32,
        sonusMgcpSessionStatusTxDC909   Integer32,
        sonusMgcpSessionStatusTxFO908   Integer32
    }

sonusMgcpSessionStatusIndex OBJECT-TYPE
    SYNTAX          Integer32
    MAX-ACCESS      read-only
    STATUS          current
    DESCRIPTION     
            "Identifies the target MGCP Session entry.  
             The index used should match the index of the MGCP Session."
    ::= { sonusMgcpSessionStatusEntry 1 }

sonusMgcpSessionStatusMajorVersion OBJECT-TYPE
    SYNTAX          Integer32 (1..255)
    MAX-ACCESS      read-only
    STATUS          current
    DESCRIPTION     
            "The major version of the MGCP protocol supported by this MGCP Media Gateway."
    ::= { sonusMgcpSessionStatusEntry 3 }

sonusMgcpSessionStatusMinorVersion OBJECT-TYPE
    SYNTAX          Integer32 (0..255)
    MAX-ACCESS      read-only
    STATUS          current
    DESCRIPTION     
            "The minor version of the MGCP protocol supported by this MGCP Media Gateway."
    ::= { sonusMgcpSessionStatusEntry 4 }

sonusMgcpSessionStatusNumCallAgnts OBJECT-TYPE
    SYNTAX          Integer32
    MAX-ACCESS      read-only
    STATUS          current
    DESCRIPTION     
            "The number of Call Agents bound to this session."
    ::= { sonusMgcpSessionStatusEntry 5 }

sonusMgcpSessionStatusStatus OBJECT-TYPE
    SYNTAX          INTEGER { inactive(1), active(2), faulted(3) }
    MAX-ACCESS      read-only
    STATUS          current
    DESCRIPTION     
            "The status of this session.  If active this session has a valid MGCP 
             session with an MGCP Mgc.  If the DCL/H248 Stack fails to initialize
             or encounters a system error, then the session status will be set to
             'faulted'.  The fault will be cleared when the session is taken
             OutOfService."
    ::= { sonusMgcpSessionStatusEntry 6 }

sonusMgcpSessionStatusRxMsgTotal OBJECT-TYPE
    SYNTAX          Integer32
    MAX-ACCESS      read-only
    STATUS          current
    DESCRIPTION     
            "Total messages received."
    ::= { sonusMgcpSessionStatusEntry 7 }

sonusMgcpSessionStatusTxMsgTotal OBJECT-TYPE
    SYNTAX          Integer32
    MAX-ACCESS      read-only
    STATUS          current
    DESCRIPTION     
            "Total messages transmitted."
    ::= { sonusMgcpSessionStatusEntry 8 }

sonusMgcpSessionStatusRxCmdTotal OBJECT-TYPE
    SYNTAX          Integer32
    MAX-ACCESS      read-only
    STATUS          current
    DESCRIPTION     
            "Total command messages received."
    ::= { sonusMgcpSessionStatusEntry 9 }

sonusMgcpSessionStatusRxRspTotal OBJECT-TYPE
    SYNTAX          Integer32
    MAX-ACCESS      read-only
    STATUS          current
    DESCRIPTION     
            "Total response messages received."
    ::= { sonusMgcpSessionStatusEntry 10 }

sonusMgcpSessionStatusTxCmdTotal OBJECT-TYPE
    SYNTAX          Integer32
    MAX-ACCESS      read-only
    STATUS          current
    DESCRIPTION     
            "Total command messages transmitted."
    ::= { sonusMgcpSessionStatusEntry 11 }

sonusMgcpSessionStatusTxRspTotal OBJECT-TYPE
    SYNTAX          Integer32
    MAX-ACCESS      read-only
    STATUS          current
    DESCRIPTION     
            "Total response messages transmitted."
    ::= { sonusMgcpSessionStatusEntry 12 }

sonusMgcpSessionStatusTxTOTotal OBJECT-TYPE
    SYNTAX          Integer32
    MAX-ACCESS      read-only
    STATUS          current
    DESCRIPTION     
            "Number of message transmit timeouts."
    ::= { sonusMgcpSessionStatusEntry 13 }

sonusMgcpSessionStatusTxAbortTotal OBJECT-TYPE
    SYNTAX          Integer32
    MAX-ACCESS      read-only
    STATUS          current
    DESCRIPTION     
            "Number of message aborts due to transmit timeouts."
    ::= { sonusMgcpSessionStatusEntry 14 }

sonusMgcpSessionStatusTxErrTotal OBJECT-TYPE
    SYNTAX          Integer32
    MAX-ACCESS      read-only
    STATUS          current
    DESCRIPTION     
            "Number of message transmission errors."
    ::= { sonusMgcpSessionStatusEntry 15 }

sonusMgcpSessionStatusRxTOTotal OBJECT-TYPE
    SYNTAX          Integer32
    MAX-ACCESS      read-only
    STATUS          current
    DESCRIPTION     
            "Number of ACK ACK timeouts.
             Occurs when call agent fails to acknowledge a GW response."
    ::= { sonusMgcpSessionStatusEntry 16 }

sonusMgcpSessionStatusRxDupCmdTotal OBJECT-TYPE
    SYNTAX          Integer32
    MAX-ACCESS      read-only
    STATUS          current
    DESCRIPTION     
            "Number of duplicate commands received."
    ::= { sonusMgcpSessionStatusEntry 17 }

sonusMgcpSessionStatusRxDupRspTotal OBJECT-TYPE
    SYNTAX          Integer32
    MAX-ACCESS      read-only
    STATUS          current
    DESCRIPTION     
            "Number of duplicate reponses received."
    ::= { sonusMgcpSessionStatusEntry 18 }

sonusMgcpSessionStatusRxRspErrTotal OBJECT-TYPE
    SYNTAX          Integer32
    MAX-ACCESS      read-only
    STATUS          current
    DESCRIPTION     
            "Number of responses received that did not 
             match an outstanding command."
    ::= { sonusMgcpSessionStatusEntry 19 }

sonusMgcpSessionStatusRxRspInPTotal OBJECT-TYPE
    SYNTAX          Integer32
    MAX-ACCESS      read-only
    STATUS          current
    DESCRIPTION     
            "Number of provisional responses received."
    ::= { sonusMgcpSessionStatusEntry 20 }

sonusMgcpSessionStatusRxUnknownTotal OBJECT-TYPE
    SYNTAX          Integer32
    MAX-ACCESS      read-only
    STATUS          current
    DESCRIPTION     
            "Number of messages received which were 
             not understood by the GW."
    ::= { sonusMgcpSessionStatusEntry 21 }

sonusMgcpSessionStatusRxOverLenTotal OBJECT-TYPE
    SYNTAX          Integer32
    MAX-ACCESS      read-only
    STATUS          current
    DESCRIPTION     
            "Number of messages received that were 
             longer than the GW supports."
    ::= { sonusMgcpSessionStatusEntry 22 }

sonusMgcpSessionStatusRxMaxByteCnt OBJECT-TYPE
    SYNTAX          Integer32
    MAX-ACCESS      read-only
    STATUS          current
    DESCRIPTION     
            "Largest UDP packet received in bytes."
    ::= { sonusMgcpSessionStatusEntry 23 }

sonusMgcpSessionStatusRxMaxPigBCnt OBJECT-TYPE
    SYNTAX          Integer32
    MAX-ACCESS      read-only
    STATUS          current
    DESCRIPTION     
            "Largest number of messages received in a single UDP packet."
    ::= { sonusMgcpSessionStatusEntry 24 }

sonusMgcpSessionStatusTxMaxByteCnt OBJECT-TYPE
    SYNTAX          Integer32
    MAX-ACCESS      read-only
    STATUS          current
    DESCRIPTION     
            "Largest UDP packet transmitted in bytes."
    ::= { sonusMgcpSessionStatusEntry 25 }

sonusMgcpSessionStatusTxMaxPigBCnt OBJECT-TYPE
    SYNTAX          Integer32
    MAX-ACCESS      read-only
    STATUS          current
    DESCRIPTION     
            "Largest number of messages transmitted in a single UDP packet."
    ::= { sonusMgcpSessionStatusEntry 26 }

sonusMgcpSessionStatusTxMaxCmdPnd OBJECT-TYPE
    SYNTAX          Integer32
    MAX-ACCESS      read-only
    STATUS          current
    DESCRIPTION     
            "Largest number of command messages waiting for call agent response."
    ::= { sonusMgcpSessionStatusEntry 27 }

sonusMgcpSessionStatusTxMaxRspPnd OBJECT-TYPE
    SYNTAX          Integer32
    MAX-ACCESS      read-only
    STATUS          current
    DESCRIPTION     
            "Largest number of response messages waiting for call agent acknowledgement."
    ::= { sonusMgcpSessionStatusEntry 28 }

sonusMgcpSessionStatusRxCmdThrotCnt OBJECT-TYPE
    SYNTAX          Integer32
    MAX-ACCESS      read-only
    STATUS          current
    DESCRIPTION     
            "Number of times GW ignored received messages due to receive throttling."
    ::= { sonusMgcpSessionStatusEntry 29 }

sonusMgcpSessionStatusRxErrorTotal OBJECT-TYPE
    SYNTAX          Integer32
    MAX-ACCESS      read-only
    STATUS          current
    DESCRIPTION     
            "Number of received messages with parse errors."
    ::= { sonusMgcpSessionStatusEntry 30 }

sonusMgcpSessionStatusTxErrorTotal OBJECT-TYPE
    SYNTAX          Integer32
    MAX-ACCESS      read-only
    STATUS          current
    DESCRIPTION     
            "Number of error indications received by the GW from call agents."
    ::= { sonusMgcpSessionStatusEntry 31 }

sonusMgcpSessionStatusRxCRCX OBJECT-TYPE
    SYNTAX          Integer32
    MAX-ACCESS      read-only
    STATUS          current
    DESCRIPTION     
            "Number of MGCP Create (CRCX) commands received."
    ::= { sonusMgcpSessionStatusEntry 32 }

sonusMgcpSessionStatusRxCRCXL OBJECT-TYPE
    SYNTAX          Integer32
    MAX-ACCESS      read-only
    STATUS          current
    DESCRIPTION     
            "Number of MGCP Create (CRCX) local connection commands received."
    ::= { sonusMgcpSessionStatusEntry 33 }

sonusMgcpSessionStatusRxMDCX OBJECT-TYPE
    SYNTAX          Integer32
    MAX-ACCESS      read-only
    STATUS          current
    DESCRIPTION     
            "Number of MGCP Modify (MDCX) commands received."
    ::= { sonusMgcpSessionStatusEntry 34 }

sonusMgcpSessionStatusRxDLCX OBJECT-TYPE
    SYNTAX          Integer32
    MAX-ACCESS      read-only
    STATUS          current
    DESCRIPTION     
            "Number of MGCP Delete (DLCX) commands received."
    ::= { sonusMgcpSessionStatusEntry 35 }

sonusMgcpSessionStatusRxRQNT OBJECT-TYPE
    SYNTAX          Integer32
    MAX-ACCESS      read-only
    STATUS          current
    DESCRIPTION     
            "Number of MGCP Request Notify (RQNT) commands received."
    ::= { sonusMgcpSessionStatusEntry 36 }

sonusMgcpSessionStatusRxEPCF OBJECT-TYPE
    SYNTAX          Integer32
    MAX-ACCESS      read-only
    STATUS          current
    DESCRIPTION     
            "Number of MGCP Endpoint Configuration (EPCF) commands received."
    ::= { sonusMgcpSessionStatusEntry 37 }

sonusMgcpSessionStatusRxAUDT OBJECT-TYPE
    SYNTAX          Integer32
    MAX-ACCESS      read-only
    STATUS          current
    DESCRIPTION     
            "Number of MGCP Audit (AUEP, AUCX) commands received."
    ::= { sonusMgcpSessionStatusEntry 38 }

sonusMgcpSessionStatusTxCRCXRsp OBJECT-TYPE
    SYNTAX          Integer32
    MAX-ACCESS      read-only
    STATUS          current
    DESCRIPTION     
            "Number of successful creates (CRCX)."
    ::= { sonusMgcpSessionStatusEntry 39 }

sonusMgcpSessionStatusTxCRCXRspL OBJECT-TYPE
    SYNTAX          Integer32
    MAX-ACCESS      read-only
    STATUS          current
    DESCRIPTION     
            "Number of successful local connection creates (CRCX)."
    ::= { sonusMgcpSessionStatusEntry 40 }

sonusMgcpSessionStatusTxCRCXRspErr OBJECT-TYPE
    SYNTAX          Integer32
    MAX-ACCESS      read-only
    STATUS          current
    DESCRIPTION     
            "Number of failed creates (CRCX)."
    ::= { sonusMgcpSessionStatusEntry 41 }

sonusMgcpSessionStatusTxMDCXRsp OBJECT-TYPE
    SYNTAX          Integer32
    MAX-ACCESS      read-only
    STATUS          current
    DESCRIPTION     
            "Number of successful modifes (MDCX)."
    ::= { sonusMgcpSessionStatusEntry 42 }

sonusMgcpSessionStatusTxMDCXRspErr OBJECT-TYPE
    SYNTAX          Integer32
    MAX-ACCESS      read-only
    STATUS          current
    DESCRIPTION     
            "Number of failed modifes (MDCX)."
    ::= { sonusMgcpSessionStatusEntry 43 }

sonusMgcpSessionStatusTxDLCXRsp OBJECT-TYPE
    SYNTAX          Integer32
    MAX-ACCESS      read-only
    STATUS          current
    DESCRIPTION     
            "Number of successful deletes (DLCX)."
    ::= { sonusMgcpSessionStatusEntry 44 }

sonusMgcpSessionStatusTxDLCXRspErr OBJECT-TYPE
    SYNTAX          Integer32
    MAX-ACCESS      read-only
    STATUS          current
    DESCRIPTION     
            "Number of failed deletes (DLCX)."
    ::= { sonusMgcpSessionStatusEntry 45 }

sonusMgcpSessionStatusTxAUDTRsp OBJECT-TYPE
    SYNTAX          Integer32
    MAX-ACCESS      read-only
    STATUS          current
    DESCRIPTION     
            "Number of successful audits (AUEP, AUCX)."
    ::= { sonusMgcpSessionStatusEntry 46 }

sonusMgcpSessionStatusTxAUDTRspErr OBJECT-TYPE
    SYNTAX          Integer32
    MAX-ACCESS      read-only
    STATUS          current
    DESCRIPTION     
            "Number of failed audits (AUEP, AUCX)."
    ::= { sonusMgcpSessionStatusEntry 47 }

sonusMgcpSessionStatusTxRQNTRsp OBJECT-TYPE
    SYNTAX          Integer32
    MAX-ACCESS      read-only
    STATUS          current
    DESCRIPTION     
            "Number of successful request notifies (RQNT)."
    ::= { sonusMgcpSessionStatusEntry 48 }

sonusMgcpSessionStatusTxRQNTRspErr OBJECT-TYPE
    SYNTAX          Integer32
    MAX-ACCESS      read-only
    STATUS          current
    DESCRIPTION     
            "Number of failed request notifies (RQNT)."
    ::= { sonusMgcpSessionStatusEntry 49 }

sonusMgcpSessionStatusTxRSIPCmd OBJECT-TYPE
    SYNTAX          Integer32
    MAX-ACCESS      read-only
    STATUS          current
    DESCRIPTION     
            "Number of Restart In Progress (RSIP) messages transmitted."
    ::= { sonusMgcpSessionStatusEntry 50 }

sonusMgcpSessionStatusTxNTFYCmd OBJECT-TYPE
    SYNTAX          Integer32
    MAX-ACCESS      read-only
    STATUS          current
    DESCRIPTION     
            "Number of Notify (NTFY) messages transmitted."
    ::= { sonusMgcpSessionStatusEntry 51 }

sonusMgcpSessionStatusTxDLCXCmd OBJECT-TYPE
    SYNTAX          Integer32
    MAX-ACCESS      read-only
    STATUS          current
    DESCRIPTION     
            "Number of Delete (DLCX) messages transmitted."
    ::= { sonusMgcpSessionStatusEntry 52 }

sonusMgcpSessionStatusRxDC900 OBJECT-TYPE
    SYNTAX          Integer32
    MAX-ACCESS      read-only
    STATUS          current
    DESCRIPTION     
            "Number of Service change recieve with Disconnected method and reason as Service Restored."
    ::= { sonusMgcpSessionStatusEntry 53 }

sonusMgcpSessionStatusRxFL909 OBJECT-TYPE
    SYNTAX          Integer32
    MAX-ACCESS      read-only
    STATUS          current
    DESCRIPTION     
            "Number of Service change recieve with Failover method and reason as MGC Impending Failure."
    ::= { sonusMgcpSessionStatusEntry 54 }

sonusMgcpSessionStatusRxFO904 OBJECT-TYPE
    SYNTAX          Integer32
    MAX-ACCESS      read-only
    STATUS          current
    DESCRIPTION     
            "Number of Service change recieve with Forced method and reason as Termination Malfunctioning."
    ::= { sonusMgcpSessionStatusEntry 55 }

sonusMgcpSessionStatusRxFO905 OBJECT-TYPE
    SYNTAX          Integer32
    MAX-ACCESS      read-only
    STATUS          current
    DESCRIPTION     
            "Number of Service change recieve with forced method and reason as Termination taken ouf of service."
    ::= { sonusMgcpSessionStatusEntry 56 }

sonusMgcpSessionStatusRxGR905 OBJECT-TYPE
    SYNTAX          Integer32
    MAX-ACCESS      read-only
    STATUS          current
    DESCRIPTION     
            "Number of Service change recieve with Graceful method and reason as Termination taken ouf of service."
    ::= { sonusMgcpSessionStatusEntry 57 }

sonusMgcpSessionStatusRxHO903 OBJECT-TYPE
    SYNTAX          Integer32
    MAX-ACCESS      read-only
    STATUS          current
    DESCRIPTION     
            "Number of Service change recieve with handoff method and reason as MGC directed change."
    ::= { sonusMgcpSessionStatusEntry 58 }

sonusMgcpSessionStatusRxRS900 OBJECT-TYPE
    SYNTAX          Integer32
    MAX-ACCESS      read-only
    STATUS          current
    DESCRIPTION     
            "Number of Service change recieve with restart method and reason as Service Restored."
    ::= { sonusMgcpSessionStatusEntry 59 }

sonusMgcpSessionStatusRxRS901 OBJECT-TYPE
    SYNTAX          Integer32
    MAX-ACCESS      read-only
    STATUS          current
    DESCRIPTION     
            "Number of Service change recieve with restart method and reason as Cold Boot."
    ::= { sonusMgcpSessionStatusEntry 60 }

sonusMgcpSessionStatusRxRS902 OBJECT-TYPE
    SYNTAX          Integer32
    MAX-ACCESS      read-only
    STATUS          current
    DESCRIPTION     
            "Number of Service change recieve with restart method and reason as Warm Boot."
    ::= { sonusMgcpSessionStatusEntry 61 }

sonusMgcpSessionStatusRxDC909 OBJECT-TYPE
    SYNTAX          Integer32
    MAX-ACCESS      read-only
    STATUS          current
    DESCRIPTION     
            "Number of Service change recieve with disconnect method and reason as MGC Impending Failure."
    ::= { sonusMgcpSessionStatusEntry 62 }

sonusMgcpSessionStatusRxFO908 OBJECT-TYPE
    SYNTAX          Integer32
    MAX-ACCESS      read-only
    STATUS          current
    DESCRIPTION     
            "Number of Service change recieve with forced method and reason as MG Impneding failure."
    ::= { sonusMgcpSessionStatusEntry 63 }

sonusMgcpSessionStatusTxDC900 OBJECT-TYPE
    SYNTAX          Integer32
    MAX-ACCESS      read-only
    STATUS          current
    DESCRIPTION     
            "Number of Service change transmit with Disconnected method and reason as Service Restored."
    ::= { sonusMgcpSessionStatusEntry 64 }

sonusMgcpSessionStatusTxFL909 OBJECT-TYPE
    SYNTAX          Integer32
    MAX-ACCESS      read-only
    STATUS          current
    DESCRIPTION     
            "Number of Service change transmit with Failover method and reason as MGC Impending Failure."
    ::= { sonusMgcpSessionStatusEntry 65 }

sonusMgcpSessionStatusTxFO904 OBJECT-TYPE
    SYNTAX          Integer32
    MAX-ACCESS      read-only
    STATUS          current
    DESCRIPTION     
            "Number of Service change transmit with Forced method and reason as Termination Malfunctioning."
    ::= { sonusMgcpSessionStatusEntry 66 }

sonusMgcpSessionStatusTxFO905 OBJECT-TYPE
    SYNTAX          Integer32
    MAX-ACCESS      read-only
    STATUS          current
    DESCRIPTION     
            "Number of Service change transmit with forced method and reason as Termination taken ouf of service."
    ::= { sonusMgcpSessionStatusEntry 67 }

sonusMgcpSessionStatusTxGR905 OBJECT-TYPE
    SYNTAX          Integer32
    MAX-ACCESS      read-only
    STATUS          current
    DESCRIPTION     
            "Number of Service change transmit with Graceful method and reason as Termination taken ouf of service."
    ::= { sonusMgcpSessionStatusEntry 68 }

sonusMgcpSessionStatusTxHO903 OBJECT-TYPE
    SYNTAX          Integer32
    MAX-ACCESS      read-only
    STATUS          current
    DESCRIPTION     
            "Number of Service change transmit with handoff method and reason as MGC directed change."
    ::= { sonusMgcpSessionStatusEntry 69 }

sonusMgcpSessionStatusTxRS900 OBJECT-TYPE
    SYNTAX          Integer32
    MAX-ACCESS      read-only
    STATUS          current
    DESCRIPTION     
            "Number of Service change transmit with restart method and reason as Service Restored."
    ::= { sonusMgcpSessionStatusEntry 70 }

sonusMgcpSessionStatusTxRS901 OBJECT-TYPE
    SYNTAX          Integer32
    MAX-ACCESS      read-only
    STATUS          current
    DESCRIPTION     
            "Number of Service change transmit with restart method and reason as Cold Boot."
    ::= { sonusMgcpSessionStatusEntry 71 }

sonusMgcpSessionStatusTxRS902 OBJECT-TYPE
    SYNTAX          Integer32
    MAX-ACCESS      read-only
    STATUS          current
    DESCRIPTION     
            "Number of Service change transmit with restart method and reason as Warm Boot."
    ::= { sonusMgcpSessionStatusEntry 72 }

sonusMgcpSessionStatusTxDC909 OBJECT-TYPE
    SYNTAX          Integer32
    MAX-ACCESS      read-only
    STATUS          current
    DESCRIPTION     
            "Number of Service change transmit with diconnect method and reason as MGC Impending failure."
    ::= { sonusMgcpSessionStatusEntry 73 }

sonusMgcpSessionStatusTxFO908 OBJECT-TYPE
    SYNTAX          Integer32
    MAX-ACCESS      read-only
    STATUS          current
    DESCRIPTION     
            "Number of Service change transmit with forced method and reason as MG Impneding failure."
    ::= { sonusMgcpSessionStatusEntry 74 }

sonusMgcpCallAgntStatusTable OBJECT-TYPE
    SYNTAX          SEQUENCE OF SonusMgcpCallAgntStatusEntry
    MAX-ACCESS      not-accessible
    STATUS          current
    DESCRIPTION     
            "This table specifies the status of MGCP Mgces for the GSX node."
    ::= { sonusMgcpServicesMIBObjects 6 }

sonusMgcpCallAgntStatusEntry OBJECT-TYPE
    SYNTAX          SonusMgcpCallAgntStatusEntry
    MAX-ACCESS      not-accessible
    STATUS          current
    DESCRIPTION     
            ""
    INDEX           { sonusMgcpCallAgntStatusIndex }
    ::= { sonusMgcpCallAgntStatusTable 1 }

SonusMgcpCallAgntStatusEntry ::=
    SEQUENCE {
        sonusMgcpCallAgntStatusIndex    Integer32,
        sonusMgcpCallAgntStatusNumConnections     Integer32,
        sonusMgcpCallAgntStatusStatus   INTEGER
    }

sonusMgcpCallAgntStatusIndex OBJECT-TYPE
    SYNTAX          Integer32
    MAX-ACCESS      read-only
    STATUS          current
    DESCRIPTION     
            "Identifies the target MGCP Mgc entry."
    ::= { sonusMgcpCallAgntStatusEntry 1 }

sonusMgcpCallAgntStatusNumConnections OBJECT-TYPE
    SYNTAX          Integer32
    MAX-ACCESS      read-only
    STATUS          current
    DESCRIPTION     
            "The number of IP addresses bound to this MGC"
    ::= { sonusMgcpCallAgntStatusEntry 2 }

sonusMgcpCallAgntStatusStatus OBJECT-TYPE
    SYNTAX          INTEGER { inactive(1), active(2) }
    MAX-ACCESS      read-only
    STATUS          current
    DESCRIPTION     
            "The status of this MGC.  Active indicates this MGC is actively acting active."
    ::= { sonusMgcpCallAgntStatusEntry 3 }

sonusMgcpServProfile OBJECT IDENTIFIER
    ::= { sonusMgcpServicesMIBObjects 8 }

sonusMgcpServProfileNextIndex OBJECT-TYPE
    SYNTAX          Integer32
    MAX-ACCESS      read-only
    STATUS          current
    DESCRIPTION     
            "The next valid index to use when creating a new sonusMgcpServProfileEntry"
    ::= { sonusMgcpServProfile 1 }

sonusMgcpServProfileTable OBJECT-TYPE
    SYNTAX          SEQUENCE OF SonusMgcpServProfileEntry
    MAX-ACCESS      not-accessible
    STATUS          current
    DESCRIPTION     
            "This table specifies the MGCP Call Service Profile for the GSX node.
             The service profile provides default values for local connection options 
             not provided by the Call Agent."
    ::= { sonusMgcpServProfile 2 }

sonusMgcpServProfileEntry OBJECT-TYPE
    SYNTAX          SonusMgcpServProfileEntry
    MAX-ACCESS      not-accessible
    STATUS          current
    DESCRIPTION     
            ""
    INDEX           { sonusMgcpServProfileIndex }
    ::= { sonusMgcpServProfileTable 1 }

SonusMgcpServProfileEntry ::=
    SEQUENCE {
        sonusMgcpServProfileIndex       Integer32,
        sonusMgcpServProfileName        SonusName,
        sonusMgcpServProfileState       SonusAdminState,
        sonusMgcpServProfileRowStatus   RowStatus,
        sonusMgcpServProfileEncodeType  INTEGER,
        sonusMgcpServProfilePacketPeriod Integer32,
        sonusMgcpServProfileTypeOfService Integer32,
        sonusMgcpServProfileEchoCancellation    INTEGER,
        sonusMgcpServProfileSilenceSuppression      INTEGER,
        sonusMgcpServProfileCotControlMode  INTEGER
    }

sonusMgcpServProfileIndex OBJECT-TYPE
    SYNTAX          Integer32
    MAX-ACCESS      read-only
    STATUS          current
    DESCRIPTION     
            "Identifies the target MGCP Call Service Profile entry."
    ::= { sonusMgcpServProfileEntry 1 }

sonusMgcpServProfileName OBJECT-TYPE
    SYNTAX          SonusName
    MAX-ACCESS      read-write
    STATUS          current
    DESCRIPTION     
            "The name of this MGCP ServProfile instance."
    ::= { sonusMgcpServProfileEntry 2 }

sonusMgcpServProfileState OBJECT-TYPE
    SYNTAX          SonusAdminState
    MAX-ACCESS      read-write
    STATUS          current
    DESCRIPTION     
            "The administrative state of this MGCP ServProfile entry."
    DEFVAL          { disabled }
    ::= { sonusMgcpServProfileEntry 3 }

sonusMgcpServProfileRowStatus OBJECT-TYPE
    SYNTAX          RowStatus
    MAX-ACCESS      read-write
    STATUS          current
    DESCRIPTION     
            ""
    ::= { sonusMgcpServProfileEntry 4 }

sonusMgcpServProfileEncodeType OBJECT-TYPE
    SYNTAX          INTEGER { g711ulaw(1), g711alaw(2), g723(3), g729(4) }
    MAX-ACCESS      read-write
    STATUS          current
    DESCRIPTION     
            "The default encoding type."
    DEFVAL          { g711ulaw }
    ::= { sonusMgcpServProfileEntry 5 }

sonusMgcpServProfilePacketPeriod OBJECT-TYPE
    SYNTAX          Integer32 (10..40)
    MAX-ACCESS      read-write
    STATUS          current
    DESCRIPTION     
            "The default size of packets, in milliseconds in 5 millisecond increments."
    DEFVAL          { 10 }
    ::= { sonusMgcpServProfileEntry 6 }

sonusMgcpServProfileTypeOfService OBJECT-TYPE
    SYNTAX          Integer32 (0..255)
    MAX-ACCESS      read-write
    STATUS          current
    DESCRIPTION     
            "The default Type Of Service setting, an arbitrary one byte value used by network applications."
    DEFVAL          { 0 }
    ::= { sonusMgcpServProfileEntry 7 }

sonusMgcpServProfileEchoCancellation OBJECT-TYPE
    SYNTAX          INTEGER { off(1), on(2), useCktProfile(3) }
    MAX-ACCESS      read-write
    STATUS          current
    DESCRIPTION     
            "The default control of echo cancellation on the PSTN endpoint."
    DEFVAL          { useCktProfile }
    ::= { sonusMgcpServProfileEntry 8 }

sonusMgcpServProfileSilenceSuppression OBJECT-TYPE
    SYNTAX          INTEGER { off(1), on(2) }
    MAX-ACCESS      read-write
    STATUS          current
    DESCRIPTION     
            "The default control of silence suppression for the RTP audio stream."
    DEFVAL          { off }
    ::= { sonusMgcpServProfileEntry 9 }

sonusMgcpServProfileCotControlMode OBJECT-TYPE
    SYNTAX          INTEGER { mg(1), ca(2) }
    MAX-ACCESS      read-write
    STATUS          current
    DESCRIPTION     
            "Specifies whether Call Agent (CA) or Media Gateway (MG) controls type of COT."
    DEFVAL          { mg }
    ::= { sonusMgcpServProfileEntry 10 }

sonusIuaGateway OBJECT IDENTIFIER
    ::= { sonusMgcpServicesMIBObjects 9 }

sonusIuaGatewayPort OBJECT-TYPE
    SYNTAX          Integer32 (0..65535)
    MAX-ACCESS      read-write
    STATUS          current
    DESCRIPTION     
            "Specifies local IUA listen port."
    DEFVAL          { 9900 }
    ::= { sonusIuaGateway 1 }

sonusIuaGatewayHbTimeout OBJECT-TYPE
    SYNTAX          Integer32 (0..20000)
    MAX-ACCESS      read-write
    STATUS          current
    DESCRIPTION     
            "ASP heart beat timer in Msec."
    DEFVAL          { 3000 }
    ::= { sonusIuaGateway 2 }

sonusIuaGatewayASPendingTimeout OBJECT-TYPE
    SYNTAX          Integer32 (0..20000)
    MAX-ACCESS      read-write
    STATUS          current
    DESCRIPTION     
            "Application Server pending timer in Msec."
    DEFVAL          { 250 }
    ::= { sonusIuaGateway 3 }

sonusIuaGatewayEstRelIndRetry OBJECT-TYPE
    SYNTAX          Integer32 (1..5)
    MAX-ACCESS      read-write
    STATUS          current
    DESCRIPTION     
            "Number of Establish/Release Indication retries."
    DEFVAL          { 2 }
    ::= { sonusIuaGateway 4 }

sonusIuaGatewayEstRelIndTimeout OBJECT-TYPE
    SYNTAX          Integer32 (1..5000)
    MAX-ACCESS      read-write
    STATUS          current
    DESCRIPTION     
            "Establish/Release Indication timeout interval in Msec."
    DEFVAL          { 250 }
    ::= { sonusIuaGateway 5 }

sonusIuaGatewayDataIndTimeout OBJECT-TYPE
    SYNTAX          Integer32 (1..5000)
    MAX-ACCESS      read-write
    STATUS          current
    DESCRIPTION     
            "Data Indication timeout interval in Msec."
    DEFVAL          { 250 }
    ::= { sonusIuaGateway 6 }

sonusIuaGatewayDataIndRetryExp OBJECT-TYPE
    SYNTAX          Integer32 (1..5)
    MAX-ACCESS      read-write
    STATUS          current
    DESCRIPTION     
            "Data Indication retry exponent"
    DEFVAL          { 2 }
    ::= { sonusIuaGateway 7 }

sonusIuaGatewayDataIndWindowSize OBJECT-TYPE
    SYNTAX          Integer32 (1..32)
    MAX-ACCESS      read-write
    STATUS          current
    DESCRIPTION     
            "Data Indication message window size"
    DEFVAL          { 16 }
    ::= { sonusIuaGateway 8 }

sonusIuaGatewayDataIndMaxTimeout OBJECT-TYPE
    SYNTAX          Integer32 (1..20)
    MAX-ACCESS      read-write
    STATUS          current
    DESCRIPTION     
            "Data Indication maximum number of timeout"
    DEFVAL          { 5 }
    ::= { sonusIuaGateway 9 }

sonusIuaAs OBJECT IDENTIFIER
    ::= { sonusMgcpServicesMIBObjects 10 }

sonusIuaAsNextIndex OBJECT-TYPE
    SYNTAX          Integer32
    MAX-ACCESS      read-only
    STATUS          current
    DESCRIPTION     
            "The next valid index to use when creating a new sonusIuaAsEntry"
    ::= { sonusIuaAs 1 }

sonusIuaAsTable OBJECT-TYPE
    SYNTAX          SEQUENCE OF SonusIuaAsEntry
    MAX-ACCESS      not-accessible
    STATUS          current
    DESCRIPTION     
            "This table specifies the IUA Application Server list for the GSX node."
    ::= { sonusIuaAs 2 }

sonusIuaAsEntry OBJECT-TYPE
    SYNTAX          SonusIuaAsEntry
    MAX-ACCESS      not-accessible
    STATUS          current
    DESCRIPTION     
            ""
    INDEX           { sonusIuaAsIndex }
    ::= { sonusIuaAsTable 1 }

SonusIuaAsEntry ::=
    SEQUENCE {
        sonusIuaAsIndex                 Integer32,
        sonusIuaAsName                  SonusName,
        sonusIuaAsMode                  SonusServiceState,
        sonusIuaAsState                 SonusAdminState,
        sonusIuaAsRowStatus             RowStatus
    }

sonusIuaAsIndex OBJECT-TYPE
    SYNTAX          Integer32
    MAX-ACCESS      read-only
    STATUS          current
    DESCRIPTION     
            "Identifies the target IUA Application Server entry."
    ::= { sonusIuaAsEntry 1 }

sonusIuaAsName OBJECT-TYPE
    SYNTAX          SonusName
    MAX-ACCESS      read-write
    STATUS          current
    DESCRIPTION     
            "The name of this IUA Application Server instance."
    ::= { sonusIuaAsEntry 2 }

sonusIuaAsMode OBJECT-TYPE
    SYNTAX          SonusServiceState
    MAX-ACCESS      read-write
    STATUS          current
    DESCRIPTION     
            "Specifies the operating mode of this IUA Application Server."
    DEFVAL          { inService }
    ::= { sonusIuaAsEntry 3 }

sonusIuaAsState OBJECT-TYPE
    SYNTAX          SonusAdminState
    MAX-ACCESS      read-write
    STATUS          current
    DESCRIPTION     
            "The administrative state of this IUA Application Server entry."
    DEFVAL          { disabled }
    ::= { sonusIuaAsEntry 4 }

sonusIuaAsRowStatus OBJECT-TYPE
    SYNTAX          RowStatus
    MAX-ACCESS      read-write
    STATUS          current
    DESCRIPTION     
            ""
    ::= { sonusIuaAsEntry 5 }

sonusIuaAsp OBJECT IDENTIFIER
    ::= { sonusMgcpServicesMIBObjects 11 }

sonusIuaAspNextIndex OBJECT-TYPE
    SYNTAX          Integer32
    MAX-ACCESS      read-only
    STATUS          current
    DESCRIPTION     
            "The next valid index to use when creating a new sonusIuaAspEntry"
    ::= { sonusIuaAsp 1 }

sonusIuaAspTable OBJECT-TYPE
    SYNTAX          SEQUENCE OF SonusIuaAspEntry
    MAX-ACCESS      not-accessible
    STATUS          current
    DESCRIPTION     
            "This table specifies the IUA ASP list for the GSX node."
    ::= { sonusIuaAsp 2 }

sonusIuaAspEntry OBJECT-TYPE
    SYNTAX          SonusIuaAspEntry
    MAX-ACCESS      not-accessible
    STATUS          current
    DESCRIPTION     
            ""
    INDEX           { sonusIuaAspIndex }
    ::= { sonusIuaAspTable 1 }

SonusIuaAspEntry ::=
    SEQUENCE {
        sonusIuaAspIndex                Integer32,
        sonusIuaAspName                 SonusName,
        sonusIuaAspState                SonusAdminState,
        sonusIuaAspRowStatus            RowStatus
    }

sonusIuaAspIndex OBJECT-TYPE
    SYNTAX          Integer32
    MAX-ACCESS      read-only
    STATUS          current
    DESCRIPTION     
            "Identifies the target IUA ASP entry."
    ::= { sonusIuaAspEntry 1 }

sonusIuaAspName OBJECT-TYPE
    SYNTAX          SonusName
    MAX-ACCESS      read-write
    STATUS          current
    DESCRIPTION     
            "The name of this IUA ASP instance."
    ::= { sonusIuaAspEntry 2 }

sonusIuaAspState OBJECT-TYPE
    SYNTAX          SonusAdminState
    MAX-ACCESS      read-write
    STATUS          current
    DESCRIPTION     
            "The administrative state of this IUA ASP entry."
    DEFVAL          { disabled }
    ::= { sonusIuaAspEntry 3 }

sonusIuaAspRowStatus OBJECT-TYPE
    SYNTAX          RowStatus
    MAX-ACCESS      read-write
    STATUS          current
    DESCRIPTION     
            ""
    ::= { sonusIuaAspEntry 4 }

sonusIuaConnectionTable OBJECT-TYPE
    SYNTAX          SEQUENCE OF SonusIuaConnectionEntry
    MAX-ACCESS      not-accessible
    STATUS          current
    DESCRIPTION     
            "This table specifies the IUA Connection list for the GSX node."
    ::= { sonusMgcpServicesMIBObjects 12 }

sonusIuaConnectionEntry OBJECT-TYPE
    SYNTAX          SonusIuaConnectionEntry
    MAX-ACCESS      not-accessible
    STATUS          current
    DESCRIPTION     
            ""
    INDEX           { sonusIuaConnectionIpaddr, sonusIuaConnectionPort }
    ::= { sonusIuaConnectionTable 1 }

SonusIuaConnectionEntry ::=
    SEQUENCE {
        sonusIuaConnectionIpaddr        IpAddress,
        sonusIuaConnectionPort          Integer32,
        sonusIuaConnectionState         SonusAdminState,
        sonusIuaConnectionRowStatus     RowStatus,
        sonusIuaConnectionAspName       SonusNameReference
    }

sonusIuaConnectionIpaddr OBJECT-TYPE
    SYNTAX          IpAddress
    MAX-ACCESS      read-only
    STATUS          current
    DESCRIPTION     
            "Specifies the IP Address of the ASP connection.
             This is an allowed address for the named ASP."
    ::= { sonusIuaConnectionEntry 1 }

sonusIuaConnectionPort OBJECT-TYPE
    SYNTAX          Integer32 (1..65535)
    MAX-ACCESS      read-only
    STATUS          current
    DESCRIPTION     
            "Specifies the port nummber of the ASP connection."
    DEFVAL          { 9900 }
    ::= { sonusIuaConnectionEntry 2 }

sonusIuaConnectionState OBJECT-TYPE
    SYNTAX          SonusAdminState
    MAX-ACCESS      read-write
    STATUS          current
    DESCRIPTION     
            "The administrative state of this IUA Connection entry."
    DEFVAL          { disabled }
    ::= { sonusIuaConnectionEntry 3 }

sonusIuaConnectionRowStatus OBJECT-TYPE
    SYNTAX          RowStatus
    MAX-ACCESS      read-write
    STATUS          current
    DESCRIPTION     
            ""
    ::= { sonusIuaConnectionEntry 4 }

sonusIuaConnectionAspName OBJECT-TYPE
    SYNTAX          SonusNameReference
    MAX-ACCESS      read-write
    STATUS          current
    DESCRIPTION     
            "The name of the IUA ASP this Connection is bound to."
    ::= { sonusIuaConnectionEntry 5 }

sonusIuaInterfaceTable OBJECT-TYPE
    SYNTAX          SEQUENCE OF SonusIuaInterfaceEntry
    MAX-ACCESS      not-accessible
    STATUS          current
    DESCRIPTION     
            "This table specifies the IUA Interface list for the GSX node."
    ::= { sonusMgcpServicesMIBObjects 13 }

sonusIuaInterfaceEntry OBJECT-TYPE
    SYNTAX          SonusIuaInterfaceEntry
    MAX-ACCESS      not-accessible
    STATUS          current
    DESCRIPTION     
            ""
    INDEX           { sonusIuaInterfaceShelf, sonusIuaInterfaceSlot, 
                      sonusIuaInterfacePort, sonusIuaInterfaceTimeslot }
    ::= { sonusIuaInterfaceTable 1 }

SonusIuaInterfaceEntry ::=
    SEQUENCE {
        sonusIuaInterfaceShelf          SonusShelfIndex,
        sonusIuaInterfaceSlot           SonusSlotIndex,
        sonusIuaInterfacePort           Integer32,
        sonusIuaInterfaceTimeslot       Integer32,
        sonusIuaInterfaceRowStatus      RowStatus,
        sonusIuaInterfaceAsName         SonusNameReference
    }

sonusIuaInterfaceShelf OBJECT-TYPE
    SYNTAX          SonusShelfIndex
    MAX-ACCESS      read-only
    STATUS          current
    DESCRIPTION     
            "Identifies the target IUA Interface Shelf associated to the Application Server."
    ::= { sonusIuaInterfaceEntry 1 }

sonusIuaInterfaceSlot OBJECT-TYPE
    SYNTAX          SonusSlotIndex
    MAX-ACCESS      read-only
    STATUS          current
    DESCRIPTION     
            "Identifies the target IUA Interface Slot associated to the Application Server."
    ::= { sonusIuaInterfaceEntry 2 }

sonusIuaInterfacePort OBJECT-TYPE
    SYNTAX          Integer32 (1..28)
    MAX-ACCESS      read-only
    STATUS          current
    DESCRIPTION     
            "Identifies the target IUA Interface Port associated to the Application Server."
    ::= { sonusIuaInterfaceEntry 3 }

sonusIuaInterfaceTimeslot OBJECT-TYPE
    SYNTAX          Integer32 (1..32)
    MAX-ACCESS      read-only
    STATUS          current
    DESCRIPTION     
            "Identifies the target IUA Interface Timeslot associated to the Application Server."
    ::= { sonusIuaInterfaceEntry 4 }

sonusIuaInterfaceRowStatus OBJECT-TYPE
    SYNTAX          RowStatus
    MAX-ACCESS      read-write
    STATUS          current
    DESCRIPTION     
            ""
    ::= { sonusIuaInterfaceEntry 5 }

sonusIuaInterfaceAsName OBJECT-TYPE
    SYNTAX          SonusNameReference
    MAX-ACCESS      read-write
    STATUS          current
    DESCRIPTION     
            "The name of the IUA Application Server this Interface is bound to."
    ::= { sonusIuaInterfaceEntry 6 }

sonusIuaAsaTable OBJECT-TYPE
    SYNTAX          SEQUENCE OF SonusIuaAsaEntry
    MAX-ACCESS      not-accessible
    STATUS          current
    DESCRIPTION     
            "This table specifies the IUA Application Server Association list for the GSX node."
    ::= { sonusMgcpServicesMIBObjects 14 }

sonusIuaAsaEntry OBJECT-TYPE
    SYNTAX          SonusIuaAsaEntry
    MAX-ACCESS      not-accessible
    STATUS          current
    DESCRIPTION     
            ""
    INDEX           { sonusIuaAsaAsIndex, sonusIuaAsaAspIndex }
    ::= { sonusIuaAsaTable 1 }

SonusIuaAsaEntry ::=
    SEQUENCE {
        sonusIuaAsaAsIndex              Integer32,
        sonusIuaAsaAspIndex             Integer32,
        sonusIuaAsaRowStatus            RowStatus
    }

sonusIuaAsaAsIndex OBJECT-TYPE
    SYNTAX          Integer32
    MAX-ACCESS      read-only
    STATUS          current
    DESCRIPTION     
            "Specifies the Index of Application Server associated to the Application Server Process."
    ::= { sonusIuaAsaEntry 1 }

sonusIuaAsaAspIndex OBJECT-TYPE
    SYNTAX          Integer32
    MAX-ACCESS      read-only
    STATUS          current
    DESCRIPTION     
            "Specifies the Index of Application Server Process associated to the Application Server."
    ::= { sonusIuaAsaEntry 2 }

sonusIuaAsaRowStatus OBJECT-TYPE
    SYNTAX          RowStatus
    MAX-ACCESS      read-write
    STATUS          current
    DESCRIPTION     
            ""
    ::= { sonusIuaAsaEntry 3 }

sonusIuaAsStatusTable OBJECT-TYPE
    SYNTAX          SEQUENCE OF SonusIuaAsStatusEntry
    MAX-ACCESS      not-accessible
    STATUS          current
    DESCRIPTION     
            "This table specifies the status of IUA Application Servers for the GSX node."
    ::= { sonusMgcpServicesMIBObjects 15 }

sonusIuaAsStatusEntry OBJECT-TYPE
    SYNTAX          SonusIuaAsStatusEntry
    MAX-ACCESS      not-accessible
    STATUS          current
    DESCRIPTION     
            ""
    INDEX           { sonusIuaAsStatusIndex }
    ::= { sonusIuaAsStatusTable 1 }

SonusIuaAsStatusEntry ::=
    SEQUENCE {
        sonusIuaAsStatusIndex           Integer32,
        sonusIuaAsStatusMessageVersion  Integer32,
        sonusIuaAsStatusNumAsps         Integer32,
        sonusIuaAsStatusNumInterfaces   Integer32,
        sonusIuaAsStatusStatus          INTEGER,
        sonusIuaAsStatusRxMsgTotal      Integer32,
        sonusIuaAsStatusTxMsgTotal      Integer32,
        sonusIuaAsStatusRxQptmTotal     Integer32,
        sonusIuaAsStatusTxQptmTotal     Integer32,
        sonusIuaAsStatusRxAspSmTotal    Integer32,
        sonusIuaAsStatusTxAspSmTotal    Integer32,
        sonusIuaAsStatusRxAspTmTotal    Integer32,
        sonusIuaAsStatusTxAspTmTotal    Integer32,
        sonusIuaAsStatusTxTOTotal       Integer32,
        sonusIuaAsStatusTxAbortTotal    Integer32,
        sonusIuaAsStatusTxErrTotal      Integer32,
        sonusIuaAsStatusRxUnknownTotal  Integer32,
        sonusIuaAsStatusRxOverLenTotal  Integer32,
        sonusIuaAsStatusRxAspUp         Integer32,
        sonusIuaAsStatusRxAspDown       Integer32,
        sonusIuaAsStatusRxAspActive     Integer32,
        sonusIuaAsStatusRxAspInactive   Integer32,
        sonusIuaAsStatusRxEstReq        Integer32,
        sonusIuaAsStatusRxRelReq        Integer32,
        sonusIuaAsStatusRxEstRsp        Integer32,
        sonusIuaAsStatusRxRelRsp        Integer32,
        sonusIuaAsStatusRxDataReq       Integer32,
        sonusIuaAsStatusRxDataIndAck    Integer32,
        sonusIuaAsStatusTxAspUpAck      Integer32,
        sonusIuaAsStatusTxAspDownAck    Integer32,
        sonusIuaAsStatusTxAspActiveAck  Integer32,
        sonusIuaAsStatusTxAspInactiveAck Integer32,
        sonusIuaAsStatusTxEstConfirm    Integer32,
        sonusIuaAsStatusTxRelConfirm    Integer32,
        sonusIuaAsStatusTxEstInd        Integer32,
        sonusIuaAsStatusTxRelInd        Integer32,
        sonusIuaAsStatusTxDataReqAck    Integer32,
        sonusIuaAsStatusTxDataInd       Integer32,
        sonusIuaAsStatusRxMaxByteCnt    Integer32,
        sonusIuaAsStatusTxMaxByteCnt    Integer32,
        sonusIuaAsStatusRxError         Integer32,
        sonusIuaAsStatusTxError         Integer32,
        sonusIuaAsStatusRxNotify        Integer32,
        sonusIuaAsStatusTxNotify        Integer32,
        sonusIuaAsStatusActiveAsp       DisplayString,
        sonusIuaAsStatusSoftwareVersion DisplayString,
        sonusIuaAsStatusRxMgmtTotal     Integer32,
        sonusIuaAsStatusTxMgmtTotal     Integer32,
        sonusIuaAsStatusAspDownByGw     Integer32
    }

sonusIuaAsStatusIndex OBJECT-TYPE
    SYNTAX          Integer32
    MAX-ACCESS      read-only
    STATUS          current
    DESCRIPTION     
            "Identifies the target IUA Application Server entry.  
             The index used should match the index of the IUA Appication Server."
    ::= { sonusIuaAsStatusEntry 1 }

sonusIuaAsStatusMessageVersion OBJECT-TYPE
    SYNTAX          Integer32 (1..255)
    MAX-ACCESS      read-only
    STATUS          current
    DESCRIPTION     
            "The version of the IUA protocol supported by this IUA Gateway."
    ::= { sonusIuaAsStatusEntry 2 }

sonusIuaAsStatusNumAsps OBJECT-TYPE
    SYNTAX          Integer32
    MAX-ACCESS      read-only
    STATUS          current
    DESCRIPTION     
            "The number of ASPs bound to this Application Server."
    ::= { sonusIuaAsStatusEntry 4 }

sonusIuaAsStatusNumInterfaces OBJECT-TYPE
    SYNTAX          Integer32
    MAX-ACCESS      read-only
    STATUS          current
    DESCRIPTION     
            "The number of Interfaces bound to the AS by the ASPs bound to the AS."
    ::= { sonusIuaAsStatusEntry 5 }

sonusIuaAsStatusStatus OBJECT-TYPE
    SYNTAX          INTEGER { down(1), inactive(2), pending(3), 
                        active(4) }
    MAX-ACCESS      read-only
    STATUS          current
    DESCRIPTION     
            "The status of this AS.  If active this AS has an active ASP."
    ::= { sonusIuaAsStatusEntry 6 }

sonusIuaAsStatusRxMsgTotal OBJECT-TYPE
    SYNTAX          Integer32
    MAX-ACCESS      read-only
    STATUS          current
    DESCRIPTION     
            "Total messages received."
    ::= { sonusIuaAsStatusEntry 7 }

sonusIuaAsStatusTxMsgTotal OBJECT-TYPE
    SYNTAX          Integer32
    MAX-ACCESS      read-only
    STATUS          current
    DESCRIPTION     
            "Total messages transmitted."
    ::= { sonusIuaAsStatusEntry 8 }

sonusIuaAsStatusRxQptmTotal OBJECT-TYPE
    SYNTAX          Integer32
    MAX-ACCESS      read-only
    STATUS          current
    DESCRIPTION     
            "Total QPTM messages received."
    ::= { sonusIuaAsStatusEntry 9 }

sonusIuaAsStatusTxQptmTotal OBJECT-TYPE
    SYNTAX          Integer32
    MAX-ACCESS      read-only
    STATUS          current
    DESCRIPTION     
            "Total QPTM messages transmitted."
    ::= { sonusIuaAsStatusEntry 10 }

sonusIuaAsStatusRxAspSmTotal OBJECT-TYPE
    SYNTAX          Integer32
    MAX-ACCESS      read-only
    STATUS          current
    DESCRIPTION     
            "Total ASP State Maintenance messages received."
    ::= { sonusIuaAsStatusEntry 11 }

sonusIuaAsStatusTxAspSmTotal OBJECT-TYPE
    SYNTAX          Integer32
    MAX-ACCESS      read-only
    STATUS          current
    DESCRIPTION     
            "Total ASP State Maintenance messages transmitted."
    ::= { sonusIuaAsStatusEntry 12 }

sonusIuaAsStatusRxAspTmTotal OBJECT-TYPE
    SYNTAX          Integer32
    MAX-ACCESS      read-only
    STATUS          current
    DESCRIPTION     
            "Total ASP Traffic Maintenance messages received."
    ::= { sonusIuaAsStatusEntry 13 }

sonusIuaAsStatusTxAspTmTotal OBJECT-TYPE
    SYNTAX          Integer32
    MAX-ACCESS      read-only
    STATUS          current
    DESCRIPTION     
            "Total ASP Traffic Maintenance messages transmitted."
    ::= { sonusIuaAsStatusEntry 14 }

sonusIuaAsStatusTxTOTotal OBJECT-TYPE
    SYNTAX          Integer32
    MAX-ACCESS      read-only
    STATUS          current
    DESCRIPTION     
            "Number of message transmit timeouts."
    ::= { sonusIuaAsStatusEntry 15 }

sonusIuaAsStatusTxAbortTotal OBJECT-TYPE
    SYNTAX          Integer32
    MAX-ACCESS      read-only
    STATUS          current
    DESCRIPTION     
            "Number of message aborts due to transmit timeouts."
    ::= { sonusIuaAsStatusEntry 16 }

sonusIuaAsStatusTxErrTotal OBJECT-TYPE
    SYNTAX          Integer32
    MAX-ACCESS      read-only
    STATUS          current
    DESCRIPTION     
            "Number of message transmission errors."
    ::= { sonusIuaAsStatusEntry 17 }

sonusIuaAsStatusRxUnknownTotal OBJECT-TYPE
    SYNTAX          Integer32
    MAX-ACCESS      read-only
    STATUS          current
    DESCRIPTION     
            "Number of messages received which were 
             not understood by the GW."
    ::= { sonusIuaAsStatusEntry 20 }

sonusIuaAsStatusRxOverLenTotal OBJECT-TYPE
    SYNTAX          Integer32
    MAX-ACCESS      read-only
    STATUS          current
    DESCRIPTION     
            "Number of messages received that were 
             longer than the GW supports."
    ::= { sonusIuaAsStatusEntry 21 }

sonusIuaAsStatusRxAspUp OBJECT-TYPE
    SYNTAX          Integer32
    MAX-ACCESS      read-only
    STATUS          current
    DESCRIPTION     
            "Number of ASP Up messages received."
    ::= { sonusIuaAsStatusEntry 24 }

sonusIuaAsStatusRxAspDown OBJECT-TYPE
    SYNTAX          Integer32
    MAX-ACCESS      read-only
    STATUS          current
    DESCRIPTION     
            "Number of ASP Down messages received."
    ::= { sonusIuaAsStatusEntry 25 }

sonusIuaAsStatusRxAspActive OBJECT-TYPE
    SYNTAX          Integer32
    MAX-ACCESS      read-only
    STATUS          current
    DESCRIPTION     
            "Number of ASP Active messages received."
    ::= { sonusIuaAsStatusEntry 26 }

sonusIuaAsStatusRxAspInactive OBJECT-TYPE
    SYNTAX          Integer32
    MAX-ACCESS      read-only
    STATUS          current
    DESCRIPTION     
            "Number of ASP Inactive messages received."
    ::= { sonusIuaAsStatusEntry 28 }

sonusIuaAsStatusRxEstReq OBJECT-TYPE
    SYNTAX          Integer32
    MAX-ACCESS      read-only
    STATUS          current
    DESCRIPTION     
            "Number of Establish Request messages received."
    ::= { sonusIuaAsStatusEntry 29 }

sonusIuaAsStatusRxRelReq OBJECT-TYPE
    SYNTAX          Integer32
    MAX-ACCESS      read-only
    STATUS          current
    DESCRIPTION     
            "Number of Release Request messages received."
    ::= { sonusIuaAsStatusEntry 30 }

sonusIuaAsStatusRxEstRsp OBJECT-TYPE
    SYNTAX          Integer32
    MAX-ACCESS      read-only
    STATUS          current
    DESCRIPTION     
            "Number of Establish Response messages received."
    ::= { sonusIuaAsStatusEntry 31 }

sonusIuaAsStatusRxRelRsp OBJECT-TYPE
    SYNTAX          Integer32
    MAX-ACCESS      read-only
    STATUS          current
    DESCRIPTION     
            "Number of Release Response messages received."
    ::= { sonusIuaAsStatusEntry 32 }

sonusIuaAsStatusRxDataReq OBJECT-TYPE
    SYNTAX          Integer32
    MAX-ACCESS      read-only
    STATUS          current
    DESCRIPTION     
            "Number of Data Request messages received."
    ::= { sonusIuaAsStatusEntry 33 }

sonusIuaAsStatusRxDataIndAck OBJECT-TYPE
    SYNTAX          Integer32
    MAX-ACCESS      read-only
    STATUS          current
    DESCRIPTION     
            "Number of Data Indication Ack messages received."
    ::= { sonusIuaAsStatusEntry 34 }

sonusIuaAsStatusTxAspUpAck OBJECT-TYPE
    SYNTAX          Integer32
    MAX-ACCESS      read-only
    STATUS          current
    DESCRIPTION     
            "Number of ASP Up Ack messages transmitted."
    ::= { sonusIuaAsStatusEntry 35 }

sonusIuaAsStatusTxAspDownAck OBJECT-TYPE
    SYNTAX          Integer32
    MAX-ACCESS      read-only
    STATUS          current
    DESCRIPTION     
            "Number of ASP Down Ack messages transmitted."
    ::= { sonusIuaAsStatusEntry 36 }

sonusIuaAsStatusTxAspActiveAck OBJECT-TYPE
    SYNTAX          Integer32
    MAX-ACCESS      read-only
    STATUS          current
    DESCRIPTION     
            "Number of ASP Active Ack messages transmitted."
    ::= { sonusIuaAsStatusEntry 37 }

sonusIuaAsStatusTxAspInactiveAck OBJECT-TYPE
    SYNTAX          Integer32
    MAX-ACCESS      read-only
    STATUS          current
    DESCRIPTION     
            "Number of ASP Inactive Ack messages transmitted."
    ::= { sonusIuaAsStatusEntry 38 }

sonusIuaAsStatusTxEstConfirm OBJECT-TYPE
    SYNTAX          Integer32
    MAX-ACCESS      read-only
    STATUS          current
    DESCRIPTION     
            "Number of ASP Establish Confirm messages transmitted."
    ::= { sonusIuaAsStatusEntry 39 }

sonusIuaAsStatusTxRelConfirm OBJECT-TYPE
    SYNTAX          Integer32
    MAX-ACCESS      read-only
    STATUS          current
    DESCRIPTION     
            "Number of ASP Release Confirm messages transmitted."
    ::= { sonusIuaAsStatusEntry 40 }

sonusIuaAsStatusTxEstInd OBJECT-TYPE
    SYNTAX          Integer32
    MAX-ACCESS      read-only
    STATUS          current
    DESCRIPTION     
            "Number of ASP Establish Indication messages transmitted."
    ::= { sonusIuaAsStatusEntry 41 }

sonusIuaAsStatusTxRelInd OBJECT-TYPE
    SYNTAX          Integer32
    MAX-ACCESS      read-only
    STATUS          current
    DESCRIPTION     
            "Number of ASP Release Indication messages transmitted."
    ::= { sonusIuaAsStatusEntry 42 }

sonusIuaAsStatusTxDataReqAck OBJECT-TYPE
    SYNTAX          Integer32
    MAX-ACCESS      read-only
    STATUS          current
    DESCRIPTION     
            "Number of ASP Data Request Ack messages transmitted."
    ::= { sonusIuaAsStatusEntry 43 }

sonusIuaAsStatusTxDataInd OBJECT-TYPE
    SYNTAX          Integer32
    MAX-ACCESS      read-only
    STATUS          current
    DESCRIPTION     
            "Number of ASP Data Indication messages transmitted."
    ::= { sonusIuaAsStatusEntry 44 }

sonusIuaAsStatusRxMaxByteCnt OBJECT-TYPE
    SYNTAX          Integer32
    MAX-ACCESS      read-only
    STATUS          current
    DESCRIPTION     
            "Largest UDP packet received in bytes."
    ::= { sonusIuaAsStatusEntry 45 }

sonusIuaAsStatusTxMaxByteCnt OBJECT-TYPE
    SYNTAX          Integer32
    MAX-ACCESS      read-only
    STATUS          current
    DESCRIPTION     
            "Largest UDP packet transmitted in bytes."
    ::= { sonusIuaAsStatusEntry 46 }

sonusIuaAsStatusRxError OBJECT-TYPE
    SYNTAX          Integer32
    MAX-ACCESS      read-only
    STATUS          current
    DESCRIPTION     
            "Number of Error messages received."
    ::= { sonusIuaAsStatusEntry 47 }

sonusIuaAsStatusTxError OBJECT-TYPE
    SYNTAX          Integer32
    MAX-ACCESS      read-only
    STATUS          current
    DESCRIPTION     
            "Number of Error messages transmitted."
    ::= { sonusIuaAsStatusEntry 48 }

sonusIuaAsStatusRxNotify OBJECT-TYPE
    SYNTAX          Integer32
    MAX-ACCESS      read-only
    STATUS          current
    DESCRIPTION     
            "Number of Error messages received."
    ::= { sonusIuaAsStatusEntry 49 }

sonusIuaAsStatusTxNotify OBJECT-TYPE
    SYNTAX          Integer32
    MAX-ACCESS      read-only
    STATUS          current
    DESCRIPTION     
            "Number of Error messages transmitted."
    ::= { sonusIuaAsStatusEntry 50 }

sonusIuaAsStatusActiveAsp OBJECT-TYPE
    SYNTAX          DisplayString (SIZE(0..23))
    MAX-ACCESS      read-only
    STATUS          current
    DESCRIPTION     
            "The active Application Server Process of this Application Server."
    ::= { sonusIuaAsStatusEntry 51 }

sonusIuaAsStatusSoftwareVersion OBJECT-TYPE
    SYNTAX          DisplayString (SIZE(0..63))
    MAX-ACCESS      read-only
    STATUS          current
    DESCRIPTION     
            "The software version of the IUA protocol supported by this IUA Gateway."
    ::= { sonusIuaAsStatusEntry 52 }

sonusIuaAsStatusRxMgmtTotal OBJECT-TYPE
    SYNTAX          Integer32
    MAX-ACCESS      read-only
    STATUS          current
    DESCRIPTION     
            "Total MGMT messages received."
    ::= { sonusIuaAsStatusEntry 53 }

sonusIuaAsStatusTxMgmtTotal OBJECT-TYPE
    SYNTAX          Integer32
    MAX-ACCESS      read-only
    STATUS          current
    DESCRIPTION     
            "Total MGMT messages transmitted."
    ::= { sonusIuaAsStatusEntry 54 }

sonusIuaAsStatusAspDownByGw OBJECT-TYPE
    SYNTAX          Integer32
    MAX-ACCESS      read-only
    STATUS          current
    DESCRIPTION     
            "Number of ASP Down initiated by the IUA Gateway."
    ::= { sonusIuaAsStatusEntry 55 }

sonusIuaAspStatusTable OBJECT-TYPE
    SYNTAX          SEQUENCE OF SonusIuaAspStatusEntry
    MAX-ACCESS      not-accessible
    STATUS          current
    DESCRIPTION     
            "This table specifies the status of IUA ASPs for the GSX node."
    ::= { sonusMgcpServicesMIBObjects 16 }

sonusIuaAspStatusEntry OBJECT-TYPE
    SYNTAX          SonusIuaAspStatusEntry
    MAX-ACCESS      not-accessible
    STATUS          current
    DESCRIPTION     
            ""
    INDEX           { sonusIuaAspStatusIndex }
    ::= { sonusIuaAspStatusTable 1 }

SonusIuaAspStatusEntry ::=
    SEQUENCE {
        sonusIuaAspStatusIndex          Integer32,
        sonusIuaAspStatusNumConnections Integer32,
        sonusIuaAspStatusNumAppServers  Integer32,
        sonusIuaAspStatusStatus         INTEGER,
        sonusIuaAspStatusMessageVersion Integer32,
        sonusIuaAspStatusRxMsgTotal     Integer32,
        sonusIuaAspStatusTxMsgTotal     Integer32,
        sonusIuaAspStatusRxQptmTotal    Integer32,
        sonusIuaAspStatusTxQptmTotal    Integer32,
        sonusIuaAspStatusRxAspSmTotal   Integer32,
        sonusIuaAspStatusTxAspSmTotal   Integer32,
        sonusIuaAspStatusRxAspTmTotal   Integer32,
        sonusIuaAspStatusTxAspTmTotal   Integer32,
        sonusIuaAspStatusTxTOTotal      Integer32,
        sonusIuaAspStatusTxAbortTotal   Integer32,
        sonusIuaAspStatusTxErrTotal     Integer32,
        sonusIuaAspStatusRxUnknownTotal Integer32,
        sonusIuaAspStatusRxOverLenTotal Integer32,
        sonusIuaAspStatusRxAspUp        Integer32,
        sonusIuaAspStatusRxAspDown      Integer32,
        sonusIuaAspStatusRxAspActive    Integer32,
        sonusIuaAspStatusRxAspInactive  Integer32,
        sonusIuaAspStatusRxEstReq       Integer32,
        sonusIuaAspStatusRxRelReq       Integer32,
        sonusIuaAspStatusRxEstRsp       Integer32,
        sonusIuaAspStatusRxRelRsp       Integer32,
        sonusIuaAspStatusRxDataReq      Integer32,
        sonusIuaAspStatusRxDataIndAck   Integer32,
        sonusIuaAspStatusTxAspUpAck     Integer32,
        sonusIuaAspStatusTxAspDownAck   Integer32,
        sonusIuaAspStatusTxAspActiveAck Integer32,
        sonusIuaAspStatusTxAspInactiveAck Integer32,
        sonusIuaAspStatusTxEstConfirm   Integer32,
        sonusIuaAspStatusTxRelConfirm   Integer32,
        sonusIuaAspStatusTxEstInd       Integer32,
        sonusIuaAspStatusTxRelInd       Integer32,
        sonusIuaAspStatusTxDataReqAck   Integer32,
        sonusIuaAspStatusTxDataInd      Integer32,
        sonusIuaAspStatusRxMaxByteCnt   Integer32,
        sonusIuaAspStatusTxMaxByteCnt   Integer32,
        sonusIuaAspStatusRxError        Integer32,
        sonusIuaAspStatusTxError        Integer32,
        sonusIuaAspStatusRxNotify       Integer32,
        sonusIuaAspStatusTxNotify       Integer32,
        sonusIuaAspStatusSoftwareVersion DisplayString,
        sonusIuaAspStatusRxMgmtTotal    Integer32,
        sonusIuaAspStatusTxMgmtTotal    Integer32,
        sonusIuaAspStatusAspDownByGw    Integer32
    }

sonusIuaAspStatusIndex OBJECT-TYPE
    SYNTAX          Integer32
    MAX-ACCESS      read-only
    STATUS          current
    DESCRIPTION     
            "Identifies the target IUA Application Server Process entry."
    ::= { sonusIuaAspStatusEntry 1 }

sonusIuaAspStatusNumConnections OBJECT-TYPE
    SYNTAX          Integer32
    MAX-ACCESS      read-only
    STATUS          current
    DESCRIPTION     
            "The number of IP addresses bound to this Application Server Process"
    ::= { sonusIuaAspStatusEntry 2 }

sonusIuaAspStatusNumAppServers OBJECT-TYPE
    SYNTAX          Integer32
    MAX-ACCESS      read-only
    STATUS          current
    DESCRIPTION     
            "The number of Application Servers bound to this Application Server Process"
    ::= { sonusIuaAspStatusEntry 3 }

sonusIuaAspStatusStatus OBJECT-TYPE
    SYNTAX          INTEGER { down(1), up(2) }
    MAX-ACCESS      read-only
    STATUS          current
    DESCRIPTION     
            "The status of this Application Server Process.  Active indicates this Application Server Process is actively acting active."
    ::= { sonusIuaAspStatusEntry 4 }

sonusIuaAspStatusMessageVersion OBJECT-TYPE
    SYNTAX          Integer32 (1..255)
    MAX-ACCESS      read-only
    STATUS          current
    DESCRIPTION     
            "The version of the IUA protocol supported by this IUA Gateway."
    ::= { sonusIuaAspStatusEntry 5 }

sonusIuaAspStatusRxMsgTotal OBJECT-TYPE
    SYNTAX          Integer32
    MAX-ACCESS      read-only
    STATUS          current
    DESCRIPTION     
            "Total messages received."
    ::= { sonusIuaAspStatusEntry 7 }

sonusIuaAspStatusTxMsgTotal OBJECT-TYPE
    SYNTAX          Integer32
    MAX-ACCESS      read-only
    STATUS          current
    DESCRIPTION     
            "Total messages transmitted."
    ::= { sonusIuaAspStatusEntry 8 }

sonusIuaAspStatusRxQptmTotal OBJECT-TYPE
    SYNTAX          Integer32
    MAX-ACCESS      read-only
    STATUS          current
    DESCRIPTION     
            "Total QPTM messages received."
    ::= { sonusIuaAspStatusEntry 9 }

sonusIuaAspStatusTxQptmTotal OBJECT-TYPE
    SYNTAX          Integer32
    MAX-ACCESS      read-only
    STATUS          current
    DESCRIPTION     
            "Total QPTM messages transmitted."
    ::= { sonusIuaAspStatusEntry 10 }

sonusIuaAspStatusRxAspSmTotal OBJECT-TYPE
    SYNTAX          Integer32
    MAX-ACCESS      read-only
    STATUS          current
    DESCRIPTION     
            "Total ASP State Maintenance messages received."
    ::= { sonusIuaAspStatusEntry 11 }

sonusIuaAspStatusTxAspSmTotal OBJECT-TYPE
    SYNTAX          Integer32
    MAX-ACCESS      read-only
    STATUS          current
    DESCRIPTION     
            "Total ASP State Maintenance messages transmitted."
    ::= { sonusIuaAspStatusEntry 12 }

sonusIuaAspStatusRxAspTmTotal OBJECT-TYPE
    SYNTAX          Integer32
    MAX-ACCESS      read-only
    STATUS          current
    DESCRIPTION     
            "Total ASP Traffic Maintenance messages received."
    ::= { sonusIuaAspStatusEntry 13 }

sonusIuaAspStatusTxAspTmTotal OBJECT-TYPE
    SYNTAX          Integer32
    MAX-ACCESS      read-only
    STATUS          current
    DESCRIPTION     
            "Total ASP Traffic Maintenance messages transmitted."
    ::= { sonusIuaAspStatusEntry 14 }

sonusIuaAspStatusTxTOTotal OBJECT-TYPE
    SYNTAX          Integer32
    MAX-ACCESS      read-only
    STATUS          current
    DESCRIPTION     
            "Number of message transmit timeouts."
    ::= { sonusIuaAspStatusEntry 15 }

sonusIuaAspStatusTxAbortTotal OBJECT-TYPE
    SYNTAX          Integer32
    MAX-ACCESS      read-only
    STATUS          current
    DESCRIPTION     
            "Number of message aborts due to transmit timeouts."
    ::= { sonusIuaAspStatusEntry 16 }

sonusIuaAspStatusTxErrTotal OBJECT-TYPE
    SYNTAX          Integer32
    MAX-ACCESS      read-only
    STATUS          current
    DESCRIPTION     
            "Number of message transmission errors."
    ::= { sonusIuaAspStatusEntry 17 }

sonusIuaAspStatusRxUnknownTotal OBJECT-TYPE
    SYNTAX          Integer32
    MAX-ACCESS      read-only
    STATUS          current
    DESCRIPTION     
            "Number of messages received which were 
             not understood by the GW."
    ::= { sonusIuaAspStatusEntry 20 }

sonusIuaAspStatusRxOverLenTotal OBJECT-TYPE
    SYNTAX          Integer32
    MAX-ACCESS      read-only
    STATUS          current
    DESCRIPTION     
            "Number of messages received that were 
             longer than the GW supports."
    ::= { sonusIuaAspStatusEntry 21 }

sonusIuaAspStatusRxAspUp OBJECT-TYPE
    SYNTAX          Integer32
    MAX-ACCESS      read-only
    STATUS          current
    DESCRIPTION     
            "Number of ASP Up messages received."
    ::= { sonusIuaAspStatusEntry 24 }

sonusIuaAspStatusRxAspDown OBJECT-TYPE
    SYNTAX          Integer32
    MAX-ACCESS      read-only
    STATUS          current
    DESCRIPTION     
            "Number of ASP Down messages received."
    ::= { sonusIuaAspStatusEntry 25 }

sonusIuaAspStatusRxAspActive OBJECT-TYPE
    SYNTAX          Integer32
    MAX-ACCESS      read-only
    STATUS          current
    DESCRIPTION     
            "Number of ASP Active messages received."
    ::= { sonusIuaAspStatusEntry 26 }

sonusIuaAspStatusRxAspInactive OBJECT-TYPE
    SYNTAX          Integer32
    MAX-ACCESS      read-only
    STATUS          current
    DESCRIPTION     
            "Number of ASP Inactive messages received."
    ::= { sonusIuaAspStatusEntry 28 }

sonusIuaAspStatusRxEstReq OBJECT-TYPE
    SYNTAX          Integer32
    MAX-ACCESS      read-only
    STATUS          current
    DESCRIPTION     
            "Number of Establish Request messages received."
    ::= { sonusIuaAspStatusEntry 29 }

sonusIuaAspStatusRxRelReq OBJECT-TYPE
    SYNTAX          Integer32
    MAX-ACCESS      read-only
    STATUS          current
    DESCRIPTION     
            "Number of Release Request messages received."
    ::= { sonusIuaAspStatusEntry 30 }

sonusIuaAspStatusRxEstRsp OBJECT-TYPE
    SYNTAX          Integer32
    MAX-ACCESS      read-only
    STATUS          current
    DESCRIPTION     
            "Number of Establish Response messages received."
    ::= { sonusIuaAspStatusEntry 31 }

sonusIuaAspStatusRxRelRsp OBJECT-TYPE
    SYNTAX          Integer32
    MAX-ACCESS      read-only
    STATUS          current
    DESCRIPTION     
            "Number of Release Response messages received."
    ::= { sonusIuaAspStatusEntry 32 }

sonusIuaAspStatusRxDataReq OBJECT-TYPE
    SYNTAX          Integer32
    MAX-ACCESS      read-only
    STATUS          current
    DESCRIPTION     
            "Number of Data Request messages received."
    ::= { sonusIuaAspStatusEntry 33 }

sonusIuaAspStatusRxDataIndAck OBJECT-TYPE
    SYNTAX          Integer32
    MAX-ACCESS      read-only
    STATUS          current
    DESCRIPTION     
            "Number of Data Indication Ack messages received."
    ::= { sonusIuaAspStatusEntry 34 }

sonusIuaAspStatusTxAspUpAck OBJECT-TYPE
    SYNTAX          Integer32
    MAX-ACCESS      read-only
    STATUS          current
    DESCRIPTION     
            "Number of ASP Up Ack messages transmitted."
    ::= { sonusIuaAspStatusEntry 35 }

sonusIuaAspStatusTxAspDownAck OBJECT-TYPE
    SYNTAX          Integer32
    MAX-ACCESS      read-only
    STATUS          current
    DESCRIPTION     
            "Number of ASP Down Ack messages transmitted."
    ::= { sonusIuaAspStatusEntry 36 }

sonusIuaAspStatusTxAspActiveAck OBJECT-TYPE
    SYNTAX          Integer32
    MAX-ACCESS      read-only
    STATUS          current
    DESCRIPTION     
            "Number of ASP Active Ack messages transmitted."
    ::= { sonusIuaAspStatusEntry 37 }

sonusIuaAspStatusTxAspInactiveAck OBJECT-TYPE
    SYNTAX          Integer32
    MAX-ACCESS      read-only
    STATUS          current
    DESCRIPTION     
            "Number of ASP Inactive Ack messages transmitted."
    ::= { sonusIuaAspStatusEntry 38 }

sonusIuaAspStatusTxEstConfirm OBJECT-TYPE
    SYNTAX          Integer32
    MAX-ACCESS      read-only
    STATUS          current
    DESCRIPTION     
            "Number of ASP Establish Confirm messages transmitted."
    ::= { sonusIuaAspStatusEntry 39 }

sonusIuaAspStatusTxRelConfirm OBJECT-TYPE
    SYNTAX          Integer32
    MAX-ACCESS      read-only
    STATUS          current
    DESCRIPTION     
            "Number of ASP Release Confirm messages transmitted."
    ::= { sonusIuaAspStatusEntry 40 }

sonusIuaAspStatusTxEstInd OBJECT-TYPE
    SYNTAX          Integer32
    MAX-ACCESS      read-only
    STATUS          current
    DESCRIPTION     
            "Number of ASP Establish Indication messages transmitted."
    ::= { sonusIuaAspStatusEntry 41 }

sonusIuaAspStatusTxRelInd OBJECT-TYPE
    SYNTAX          Integer32
    MAX-ACCESS      read-only
    STATUS          current
    DESCRIPTION     
            "Number of ASP Release Indication messages transmitted."
    ::= { sonusIuaAspStatusEntry 42 }

sonusIuaAspStatusTxDataReqAck OBJECT-TYPE
    SYNTAX          Integer32
    MAX-ACCESS      read-only
    STATUS          current
    DESCRIPTION     
            "Number of ASP Data Request Ack messages transmitted."
    ::= { sonusIuaAspStatusEntry 43 }

sonusIuaAspStatusTxDataInd OBJECT-TYPE
    SYNTAX          Integer32
    MAX-ACCESS      read-only
    STATUS          current
    DESCRIPTION     
            "Number of ASP Data Indication messages transmitted."
    ::= { sonusIuaAspStatusEntry 44 }

sonusIuaAspStatusRxMaxByteCnt OBJECT-TYPE
    SYNTAX          Integer32
    MAX-ACCESS      read-only
    STATUS          current
    DESCRIPTION     
            "Largest UDP packet received in bytes."
    ::= { sonusIuaAspStatusEntry 45 }

sonusIuaAspStatusTxMaxByteCnt OBJECT-TYPE
    SYNTAX          Integer32
    MAX-ACCESS      read-only
    STATUS          current
    DESCRIPTION     
            "Largest UDP packet transmitted in bytes."
    ::= { sonusIuaAspStatusEntry 46 }

sonusIuaAspStatusRxError OBJECT-TYPE
    SYNTAX          Integer32
    MAX-ACCESS      read-only
    STATUS          current
    DESCRIPTION     
            "Number of Error messages received."
    ::= { sonusIuaAspStatusEntry 47 }

sonusIuaAspStatusTxError OBJECT-TYPE
    SYNTAX          Integer32
    MAX-ACCESS      read-only
    STATUS          current
    DESCRIPTION     
            "Number of Error messages transmitted."
    ::= { sonusIuaAspStatusEntry 48 }

sonusIuaAspStatusRxNotify OBJECT-TYPE
    SYNTAX          Integer32
    MAX-ACCESS      read-only
    STATUS          current
    DESCRIPTION     
            "Number of Error messages received."
    ::= { sonusIuaAspStatusEntry 49 }

sonusIuaAspStatusTxNotify OBJECT-TYPE
    SYNTAX          Integer32
    MAX-ACCESS      read-only
    STATUS          current
    DESCRIPTION     
            "Number of Error messages transmitted."
    ::= { sonusIuaAspStatusEntry 50 }

sonusIuaAspStatusSoftwareVersion OBJECT-TYPE
    SYNTAX          DisplayString (SIZE(0..63))
    MAX-ACCESS      read-only
    STATUS          current
    DESCRIPTION     
            "The software version of the IUA protocol supported by this IUA Gateway."
    ::= { sonusIuaAspStatusEntry 52 }

sonusIuaAspStatusRxMgmtTotal OBJECT-TYPE
    SYNTAX          Integer32
    MAX-ACCESS      read-only
    STATUS          current
    DESCRIPTION     
            "Total MGMT messages received."
    ::= { sonusIuaAspStatusEntry 53 }

sonusIuaAspStatusTxMgmtTotal OBJECT-TYPE
    SYNTAX          Integer32
    MAX-ACCESS      read-only
    STATUS          current
    DESCRIPTION     
            "Total MGMT messages transmitted."
    ::= { sonusIuaAspStatusEntry 54 }

sonusIuaAspStatusAspDownByGw OBJECT-TYPE
    SYNTAX          Integer32
    MAX-ACCESS      read-only
    STATUS          current
    DESCRIPTION     
            "Number of ASP Down initiated by the IUA Gateway."
    ::= { sonusIuaAspStatusEntry 55 }

sonusMgcpServicesMIBNotifications OBJECT IDENTIFIER
    ::= { sonusMgcpServicesMIB 2 }

sonusMgcpServicesMIBNotificationsPrefix OBJECT IDENTIFIER
    ::= { sonusMgcpServicesMIBNotifications 0 }

sonusMgcpServicesMIBNotificationsObjects OBJECT IDENTIFIER
    ::= { sonusMgcpServicesMIBNotifications 1 }

sonusMgcpSCMethod OBJECT-TYPE
    SYNTAX          INTEGER { failover(0), graceful(1), forced(2), 
                        restart(3), disconnected(4), handoff(5) }
    MAX-ACCESS      read-only
    STATUS          current
    DESCRIPTION     
            "The SC Method."
    ::= { sonusMgcpServicesMIBNotificationsObjects 1 }

sonusMgcpCallAgntIpaddr OBJECT-TYPE
    SYNTAX          DisplayString (SIZE(0..20))
    MAX-ACCESS      read-only
    STATUS          current
    DESCRIPTION     
            "The Call Agent IP."
    ::= { sonusMgcpServicesMIBNotificationsObjects 2 }

sonusMgcpSessionConnectNotification NOTIFICATION-TYPE
    OBJECTS         { sonusMgcpSessionName, sonusEventDescription, 
                      sonusEventClass, sonusEventLevel, sonusSequenceId, 
                      sonusEventTime }
    STATUS          current
    DESCRIPTION     
            "This trap indicates the MGCP Session has succesfully 
             contacted a Call Agent to establish the session."
    ::= { sonusMgcpServicesMIBNotificationsPrefix 1 }

sonusMgcpSessionDisconnectNotification NOTIFICATION-TYPE
    OBJECTS         { sonusMgcpSessionName, sonusEventDescription, 
                      sonusEventClass, sonusEventLevel, sonusSequenceId, 
                      sonusEventTime }
    STATUS          current
    DESCRIPTION     
            "This trap indicates the MGCP Session has lost contact 
             with all call agents in the session."
    ::= { sonusMgcpServicesMIBNotificationsPrefix 2 }

sonusMgcpCallAgntConnectNotification NOTIFICATION-TYPE
    OBJECTS         { sonusMgcpSessionName, sonusMgcpCallAgntName, 
                      sonusEventDescription, sonusEventClass, 
                      sonusEventLevel, sonusSequenceId, sonusEventTime }
    STATUS          current
    DESCRIPTION     
            "This trap indicates the MGCP Session has 
             succesfully contacted this Call Agent."
    ::= { sonusMgcpServicesMIBNotificationsPrefix 3 }

sonusMgcpCallAgntDisconnectNotification NOTIFICATION-TYPE
    OBJECTS         { sonusMgcpSessionName, sonusMgcpCallAgntName, 
                      sonusEventDescription, sonusEventClass, 
                      sonusEventLevel, sonusSequenceId, sonusEventTime }
    STATUS          current
    DESCRIPTION     
            "This trap indicates the MGCP Session has lost contact 
             with this Call Agent."
    ::= { sonusMgcpServicesMIBNotificationsPrefix 4 }

sonusIuaAsDownNotification NOTIFICATION-TYPE
    OBJECTS         { sonusIuaAsName, sonusEventDescription, 
                      sonusEventClass, sonusEventLevel, sonusSequenceId, 
                      sonusEventTime }
    STATUS          current
    DESCRIPTION     
            "This trap indicates the IUA AS is down."
    ::= { sonusMgcpServicesMIBNotificationsPrefix 5 }

sonusIuaAsInactiveNotification NOTIFICATION-TYPE
    OBJECTS         { sonusIuaAsName, sonusEventDescription, 
                      sonusEventClass, sonusEventLevel, sonusSequenceId, 
                      sonusEventTime }
    STATUS          current
    DESCRIPTION     
            "This trap indicates the IUA AS is inactive."
    ::= { sonusMgcpServicesMIBNotificationsPrefix 6 }

sonusIuaAsActiveNotification NOTIFICATION-TYPE
    OBJECTS         { sonusIuaAsName, sonusEventDescription, 
                      sonusEventClass, sonusEventLevel, sonusSequenceId, 
                      sonusEventTime }
    STATUS          current
    DESCRIPTION     
            "This trap indicates the IUA AS is active."
    ::= { sonusMgcpServicesMIBNotificationsPrefix 7 }

sonusIuaAsPendingNotification NOTIFICATION-TYPE
    OBJECTS         { sonusIuaAsName, sonusEventDescription, 
                      sonusEventClass, sonusEventLevel, sonusSequenceId, 
                      sonusEventTime }
    STATUS          current
    DESCRIPTION     
            "This trap indicates the IUA AS is in pending state."
    ::= { sonusMgcpServicesMIBNotificationsPrefix 8 }

sonusIuaAspDownNotification NOTIFICATION-TYPE
    OBJECTS         { sonusIuaAspName, sonusEventDescription, 
                      sonusEventClass, sonusEventLevel, sonusSequenceId, 
                      sonusEventTime }
    STATUS          current
    DESCRIPTION     
            "This trap indicates the IUA ASP is down."
    ::= { sonusMgcpServicesMIBNotificationsPrefix 9 }

sonusIuaAspUpNotification NOTIFICATION-TYPE
    OBJECTS         { sonusIuaAspName, sonusEventDescription, 
                      sonusEventClass, sonusEventLevel, sonusSequenceId, 
                      sonusEventTime }
    STATUS          current
    DESCRIPTION     
            "This trap indicates the IUA ASP is up."
    ::= { sonusMgcpServicesMIBNotificationsPrefix 10 }

sonusMgcpMGCAckSCConnectNotification NOTIFICATION-TYPE
    OBJECTS         { sonusMgcpSessionName, sonusMgcpCallAgntName, 
                      sonusMgcpSCMethod, sonusMgcpCallAgntIpaddr, 
                      sonusEventDescription, sonusEventClass, 
                      sonusEventLevel, sonusSequenceId, sonusEventTime }
    STATUS          current
    DESCRIPTION     
            "This trap indicates the MG SC  has
             succesfully acknowledge by Call Agent."
    ::= { sonusMgcpServicesMIBNotificationsPrefix 15 }

sonusMgcpMGCSendSCConnectNotification NOTIFICATION-TYPE
    OBJECTS         { sonusMgcpSessionName, sonusMgcpCallAgntName, 
                      sonusMgcpSCMethod, sonusMgcpCallAgntIpaddr, 
                      sonusEventDescription, sonusEventClass, 
                      sonusEventLevel, sonusSequenceId, sonusEventTime }
    STATUS          current
    DESCRIPTION     
            "This trap indicates the MGC  has
             send the SC to MG."
    ::= { sonusMgcpServicesMIBNotificationsPrefix 16 }

sonusMgcpMGCNackSCConnectNotification NOTIFICATION-TYPE
    OBJECTS         { sonusMgcpSessionName, sonusMgcpCallAgntName, 
                      sonusMgcpSCMethod, sonusMgcpCallAgntIpaddr, 
                      sonusEventDescription, sonusEventClass, 
                      sonusEventLevel, sonusSequenceId, sonusEventTime }
    STATUS          current
    DESCRIPTION     
            "This trap indicates the SC has
             nacked or timeout."
    ::= { sonusMgcpServicesMIBNotificationsPrefix 17 }

END -- end of module SONUS-MGCP-SERVICES-MIB.
