--
-- This SMIv2 module has been generated by smidump 0.2-cvs. Do not edit.
--

SONUS-SONET-APS-MIB DEFINITIONS ::= BEGIN

IMPORTS
    InterfaceIndex, ifIndex
        FROM IF-MIB
    MODULE-COMPLIANCE, NOTIFICATION-GROUP, OBJECT-GROUP
        FROM SNMPv2-CONF
    Counter32, Gauge32, Integer32, MODULE-IDENTITY, NOTIFICATION-TYPE, 
    OBJECT-TYPE, TimeTicks
        FROM SNMPv2-SMI
    DisplayString, RowStatus, TEXTUAL-CONVENTION
        FROM SNMPv2-TC
    sonusServicesMIBs
        FROM SONUS-SMI;

sonusSonetApsMIB MODULE-IDENTITY
    LAST-UPDATED    "200703280000Z"
    ORGANIZATION    
            "Sonus Networks, Inc."
    CONTACT-INFO    
            "   Customer Support    
             Sonus Networks, Inc.
             7 Technology Park Drive
             Westford, MA 01886
             USA
             
             Tel: 978-614-8100
             Fax: 978-614-8609"
    DESCRIPTION     
            "The MIB module for managing SONET linear Automatic Protection
             Switching (APS) architectures.  The objects defined in this MIB
             are based on the following industry references:
             
             1. ANSI T1.105.01-1995, 'Synchronous Optical Network (SONET) -
                Automatic Protection Switching'.
             
             2. Telcordia Technologies (Bellcore) GR-253-CORE, Issue 2,
                Revision 2 (January 1999), 'SONET Transport Systems: Common
                Criteria References' sections 5.3 and 6.2.1.1.6."
    ::= { sonusServicesMIBs 9 }


SonusSonetApsK1K2 ::= TEXTUAL-CONVENTION
    STATUS          current
    DESCRIPTION     
            "This Textual Convention describes an object that contains the
             K1 and K2 bytes in the SONET APS channel protocol message field.
             
             K1 is located in the first octet.
             
             Bits 1-4 of the K1 byte indicate a request.
             
             1111  Lockout of Protection
             1110  Forced Switch
             1101  SF - High Priority
             1100  SF - Low Priority
             1011  SD - High Priority
             1010  SD - Low Priority
             1001  not used
             1000  Manual Switch
             0111  not used
             0110  Wait-to-Restore
             0101  not used
             0100  Exercise
             0011  not used
             0010  Reverse Request
             0001  Do Not Revert
             0000  No Request
             
             Bits 5-8 of the K1 byte indicate the channel associated with the
             request defined in bits 1-4.
             
             0     is the Null channel
             1-14  are working channels.
             15    is the extra traffic channel
             
             K2 is located in the second octet.
             
             Bits 1-4 of the K2 byte indicate a channel.  The channel is
             defined with the same syntax as K1 Bits 5-8.
             
             Bits 5 of the K2 byte indicates the architecture.
             
             0 if the architecture is 1+1
             1 if the architecture is 1:n
             
             Bits 6-8 of the K2 byte indicates the mode.
             
             000 - 011 are reserved for future use
             100  indicates the mode is unidirectional
             101  indicates the mode is bidirectional
             110  RDI-L
             111  AIS-L
             "
    REFERENCE       
            "This Textual Convention describes an object that contains the
             K1 and K2 bytes in the SONET APS channel protocol message field.
             
             K1 is located in the first octet.
             
             Bits 1-4 of the K1 byte indicate a request.
             
             1111  Lockout of Protection
             1110  Forced Switch
             1101  SF - High Priority
             1100  SF - Low Priority
             1011  SD - High Priority
             1010  SD - Low Priority
             1001  not used
             1000  Manual Switch
             0111  not used
             0110  Wait-to-Restore
             0101  not used
             0100  Exercise
             0011  not used
             0010  Reverse Request
             0001  Do Not Revert
             0000  No Request
             
             Bits 5-8 of the K1 byte indicate the channel associated with the
             request defined in bits 1-4.
             
             0     is the Null channel
             1-14  are working channels.
             15    is the extra traffic channel
             
             K2 is located in the second octet.
             
             Bits 1-4 of the K2 byte indicate a channel.  The channel is
             defined with the same syntax as K1 Bits 5-8.
             
             Bits 5 of the K2 byte indicates the architecture.
             
             0 if the architecture is 1+1
             1 if the architecture is 1:n
             
             Bits 6-8 of the K2 byte indicates the mode.
             
             000 - 011 are reserved for future use
             100  indicates the mode is unidirectional
             101  indicates the mode is bidirectional
             110  RDI-L
             111  AIS-L
             "
    SYNTAX          Integer32

sonusSonetApsMIBObjects OBJECT IDENTIFIER
    ::= { sonusSonetApsMIB 1 }

sonusApsGroupCount OBJECT-TYPE
    SYNTAX          Gauge32
    MAX-ACCESS      read-only
    STATUS          current
    DESCRIPTION     
            "The number of APS groups currently active."
    ::= { sonusSonetApsMIBObjects 1 }

sonusApsGroupTable OBJECT-TYPE
    SYNTAX          SEQUENCE OF SonusApsGroupEntry
    MAX-ACCESS      not-accessible
    STATUS          current
    DESCRIPTION     
            "This table provides the configuration and status information
             for SONET APS groups."
    ::= { sonusSonetApsMIBObjects 2 }

sonusApsGroupEntry OBJECT-TYPE
    SYNTAX          SonusApsGroupEntry
    MAX-ACCESS      not-accessible
    STATUS          current
    DESCRIPTION     
            "An entry in the SONET APS group table."
    INDEX           { sonusApsGroupId }
    ::= { sonusApsGroupTable 1 }

SonusApsGroupEntry ::=
    SEQUENCE {
        sonusApsGroupId                 InterfaceIndex,
        sonusApsGroupStatus             RowStatus,
        sonusApsGroupArchitecture       INTEGER,
        sonusApsGroupAdminDirection     INTEGER,
        sonusApsGroupAdminSwitching     INTEGER,
        sonusApsGroupExtraTraffic       INTEGER,
        sonusApsGroupSignalFailBerThreshold   Integer32,
        sonusApsGroupSignalDegradeBerThreshold      Integer32,
        sonusApsGroupWaitToRestoreTime  Integer32,
        sonusApsGroupName               DisplayString,
        sonusApsGroupSwitchedChannel    Integer32,
        sonusApsGroupOperStatus         BITS,
        sonusApsGroupK1K2Received       SonusSonetApsK1K2,
        sonusApsGroupK1K2Transmitted    SonusSonetApsK1K2,
        sonusApsGroupProtectionSwitchingByteFailures            Counter32,
        sonusApsGroupChannelMismatches  Counter32,
        sonusApsGroupModeMismatches     Counter32,
        sonusApsGroupFarEndProtectionLineFailures         Counter32,
        sonusApsGroupCreationTime       TimeTicks
    }

sonusApsGroupId OBJECT-TYPE
    SYNTAX          InterfaceIndex
    MAX-ACCESS      not-accessible
    STATUS          current
    DESCRIPTION     
            "The ifIndex for the SONET line that is the designated
             Protection line.  The protection line's ifIndex provides a
             unique id for the group which it protects."
    ::= { sonusApsGroupEntry 1 }

sonusApsGroupStatus OBJECT-TYPE
    SYNTAX          RowStatus
    MAX-ACCESS      read-create
    STATUS          current
    DESCRIPTION     
            "The status of the MIB table entry (row).  See SNMPv2-TC for the
             definition and use of RowStatus."
    ::= { sonusApsGroupEntry 2 }

sonusApsGroupArchitecture OBJECT-TYPE
    SYNTAX          INTEGER { onePlusOne(1), oneToN(2), resilientUNI(3) }
    MAX-ACCESS      read-create
    STATUS          current
    DESCRIPTION     
            "The linear APS architecure for this group of lines.  An attempt
             to create a row in this table indicating the 1:n architecture on
             an LTE that only supports the 1+1 architecture shall result in
             an inconstentValue error."
    DEFVAL          { onePlusOne }
    ::= { sonusApsGroupEntry 3 }

sonusApsGroupAdminDirection OBJECT-TYPE
    SYNTAX          INTEGER { unidirectional(1), bidirectional(2) }
    MAX-ACCESS      read-create
    STATUS          current
    DESCRIPTION     
            "The desired APS directional mode that the APS group is to
             operate in.  The default for the 1+1 architecture is
             unidirectional.  The default for the 1:n architecture is
             bidirectional."
    ::= { sonusApsGroupEntry 4 }

sonusApsGroupAdminSwitching OBJECT-TYPE
    SYNTAX          INTEGER { nonrevertive(1), revertive(2) }
    MAX-ACCESS      read-create
    STATUS          current
    DESCRIPTION     
            "The desired APS switching mode that the APS channel is to
             operate in.  This variable is only provided if the
             sonusApsGroupArchitecture is onePlusOne(1)."
    DEFVAL          { nonrevertive }
    ::= { sonusApsGroupEntry 5 }

sonusApsGroupExtraTraffic OBJECT-TYPE
    SYNTAX          INTEGER { enabled(1), disabled(2) }
    MAX-ACCESS      read-create
    STATUS          current
    DESCRIPTION     
            "Extra traffic may be carried on the protection channel in a 1:n
             architecture if this variable is enabled.  It may be necessary
             to disable this in order to interwork with other SONET network
             elements that don't support extra traffic.  This variable is not
             provided if the sonusApsGroupArchitecture is onePlusOne(1)."
    DEFVAL          { enabled }
    ::= { sonusApsGroupEntry 6 }

sonusApsGroupSignalFailBerThreshold OBJECT-TYPE
    SYNTAX          Integer32 (3..5)
    MAX-ACCESS      read-create
    STATUS          current
    DESCRIPTION     
            "The BER threshold at which a Signal Fail is declared.  The
             value is the negative power of 10 (n - where threshold is
             1x10**-n)."
    DEFVAL          { 5 }
    ::= { sonusApsGroupEntry 7 }

sonusApsGroupSignalDegradeBerThreshold OBJECT-TYPE
    SYNTAX          Integer32 (5..9)
    MAX-ACCESS      read-create
    STATUS          current
    DESCRIPTION     
            "The BER threshold at which a Signal Degrade is declared.  The
             value is the negative power of 10 (n - where threshold is
             1x10**-n)."
    DEFVAL          { 9 }
    ::= { sonusApsGroupEntry 8 }

sonusApsGroupWaitToRestoreTime OBJECT-TYPE
    SYNTAX          Integer32 (5..12)
    MAX-ACCESS      read-create
    STATUS          current
    DESCRIPTION     
            "The Wait to Restore (WTR) Time in minutes."
    DEFVAL          { 5 }
    ::= { sonusApsGroupEntry 9 }

sonusApsGroupName OBJECT-TYPE
    SYNTAX          DisplayString (SIZE(0..32))
    MAX-ACCESS      read-create
    STATUS          current
    DESCRIPTION     
            "A textual name for the APS group."
    DEFVAL          { "" }
    ::= { sonusApsGroupEntry 10 }

sonusApsGroupSwitchedChannel OBJECT-TYPE
    SYNTAX          Integer32 (0..15)
    MAX-ACCESS      read-only
    STATUS          current
    DESCRIPTION     
            "The number of the working channel that is currently being
             switched to the protection line.  If no working channel is being
             switched, this value is zero (0).  If the protection line is
             being used for extra traffic, this value is 15."
    ::= { sonusApsGroupEntry 11 }

sonusApsGroupOperStatus OBJECT-TYPE
    SYNTAX          BITS { extraTraffic(0), 
                        protectionSwitchingByteDefect(1), 
                        channelMismatch(2), apsModeMismatch(3), 
                        farEndProtectionLineDefect(4) }
    MAX-ACCESS      read-only
    STATUS          current
    DESCRIPTION     
            "The current status of the APS group.
             
             Bit 0 - Extra Traffic.  Indicates that extra traffic is
             currently being accepted on the protection line.
             
             Bit 1 - Protection Switching Byte Defect.  Indicates that either
             an inconsistent APS byte or an invalid code has been detected.
             
             Bit 2 - Channel Mismatch.  Indicates that a mismatch between the
             transmitted K1 channel and the received K2 channel has been
             detected.
             
             Bit 3 - APS Mode Mismatch.  Indicates a conflict between the
             current local mode and the received K2 mode information.  Modes
             other than 1+1 unidirectional monitor protection line: K2 bit 5
             indicates the architecture; K2 bits 6-8 indicate if the mode is
             unidirectional or bidirectional.
             
             Bit 4 - Far-End Protection-Line Defect.  Indicates the LTE
             received an SF code for the protection line, which means that
             the far-end LTE is no longer receiving its request, or (in
             bidirectional operation) the far-end LTE considers the near-end
             LTE's request to be invalid."
    ::= { sonusApsGroupEntry 12 }

sonusApsGroupK1K2Received OBJECT-TYPE
    SYNTAX          SonusSonetApsK1K2
    MAX-ACCESS      read-only
    STATUS          current
    DESCRIPTION     
            "The current value of the K1 and K2 bytes received on the
             protection line."
    ::= { sonusApsGroupEntry 13 }

sonusApsGroupK1K2Transmitted OBJECT-TYPE
    SYNTAX          SonusSonetApsK1K2
    MAX-ACCESS      read-only
    STATUS          current
    DESCRIPTION     
            "The current value of the K1 and K2 bytes transmitted on the
             protection line."
    ::= { sonusApsGroupEntry 14 }

sonusApsGroupProtectionSwitchingByteFailures OBJECT-TYPE
    SYNTAX          Counter32
    MAX-ACCESS      read-only
    STATUS          current
    DESCRIPTION     
            "A count of APS Protection Switching Byte failures.  A
             Protection Switching Byte defect occurs when either an
             inconsistent APS byte or an invalid code is detected.  An
             inconsistent APS byte occurs when no three consecutive K1 bytes
             of the last 12 successive frames are identical, starting with
             the last frame containing a previously consistent byte.  An
             invalid code occurs when the incoming K1 byte contains an unused
             code, or a code irrelevant for the specific switching operation
             (e.g., Reverse Request while no switching request is
             outstanding) in three consecutive frames.  An invalid code also
             occurs when the incoming K1 byte contains an invalid channel
             number in three consecutive frames."
    ::= { sonusApsGroupEntry 15 }

sonusApsGroupChannelMismatches OBJECT-TYPE
    SYNTAX          Counter32
    MAX-ACCESS      read-only
    STATUS          current
    DESCRIPTION     
            "A count of Channel Mismatch failures.  A Channel Mismatch
             indicates that a mismatch between the transmitted K1 channel and
             the received K2 channel has been detected.  Under normal
             conditions, a mismatch will occure each time the LTE changes the
             channel number on its transmitted K1 byte (i.e., when the
             channel with the highest priority switch request changes).  A
             mismatch could also occur if the channel number on the incoming
             K2 byte changes (e.g., due to a failure at the far-end LTE)."
    ::= { sonusApsGroupEntry 16 }

sonusApsGroupModeMismatches OBJECT-TYPE
    SYNTAX          Counter32
    MAX-ACCESS      read-only
    STATUS          current
    DESCRIPTION     
            "A count of APS Mode Mismatch failures.  An APS Mode Mismatch is
             a conflict between the current local mode and the received K2
             mode information.  An LTE in a mode other than 1+1
             unidirectional must monitor the mode of operation indicators in
             the incoming K2 byte of the protection line for APS Mode
             Mismatch failures.  K2 bit 5 indicates the architecture; K2 bits
             6-8 indicate if the mode is unidirectional or bidirectional."
    ::= { sonusApsGroupEntry 17 }

sonusApsGroupFarEndProtectionLineFailures OBJECT-TYPE
    SYNTAX          Counter32
    MAX-ACCESS      read-only
    STATUS          current
    DESCRIPTION     
            "A count of APS Far-End Protection-Line failures.  Unless it is
             operating in the 1+1 unidirectional mode, the LTE must monitor
             the K1 byte for Far-End Protection-Line failures."
    ::= { sonusApsGroupEntry 18 }

sonusApsGroupCreationTime OBJECT-TYPE
    SYNTAX          TimeTicks
    MAX-ACCESS      read-only
    STATUS          current
    DESCRIPTION     
            "The value of SNMPv2-MIB:sysUpTime at the time the associated
             sonusApsGroupStatus variable was set to active(1)."
    ::= { sonusApsGroupEntry 19 }

sonusApsChannelTable OBJECT-TYPE
    SYNTAX          SEQUENCE OF SonusApsChannelEntry
    MAX-ACCESS      not-accessible
    STATUS          current
    DESCRIPTION     
            "This table provides the control and status information for
             individual SONET APS channels."
    ::= { sonusSonetApsMIBObjects 3 }

sonusApsChannelEntry OBJECT-TYPE
    SYNTAX          SonusApsChannelEntry
    MAX-ACCESS      not-accessible
    STATUS          current
    DESCRIPTION     
            "An entry in the SONET APS channel table."
    INDEX           { sonusApsGroupId, sonusApsChannelNumber }
    ::= { sonusApsChannelTable 1 }

SonusApsChannelEntry ::=
    SEQUENCE {
        sonusApsChannelNumber           Integer32,
        sonusApsChannelLineId           InterfaceIndex,
        sonusApsChannelPriority         INTEGER,
        sonusApsChannelSwitchCommand    INTEGER,
        sonusApsChannelControlCommand   INTEGER,
        sonusApsChannelStatus           BITS,
        sonusApsChannelOperDirectionMode INTEGER,
        sonusApsChannelSignalDegrades   Counter32,
        sonusApsChannelSignalFails      Counter32,
        sonusApsChannelSwitchovers      Counter32,
        sonusApsChannelLastSwitchover   TimeTicks,
        sonusApsChannelRowStatus        RowStatus
    }

sonusApsChannelNumber OBJECT-TYPE
    SYNTAX          Integer32 (0..15)
    MAX-ACCESS      not-accessible
    STATUS          current
    DESCRIPTION     
            "The number for the APS channel within the APS group.  Number 0
             is for the null channel (associated with the protection line).
             Number 15 designates the extra traffic channel.  Numbers 1 thru
             14 are for working channels.  For an APS group in the 1+1
             architecture, there are only two channels: the null channel (0)
             and the first working channel (1)."
    ::= { sonusApsChannelEntry 1 }

sonusApsChannelLineId OBJECT-TYPE
    SYNTAX          InterfaceIndex
    MAX-ACCESS      read-create
    STATUS          current
    DESCRIPTION     
            "The ifIndex for the SONET line that is associated with this APS
             channel.  This variable is used to add working channels to an
             APS group; a channel is not configured without a valid SONET
             line interface to use as a working line."
    ::= { sonusApsChannelEntry 2 }

sonusApsChannelPriority OBJECT-TYPE
    SYNTAX          INTEGER { low(1), high(2) }
    MAX-ACCESS      read-create
    STATUS          current
    DESCRIPTION     
            "The priority of the channel.  This variable deterimines whether
             high or low priority SD and SF codes are used in K1 requests.
             This variable is not present if the channel belongs to an APS
             group using the 1+1 architecture."
    ::= { sonusApsChannelEntry 3 }

sonusApsChannelSwitchCommand OBJECT-TYPE
    SYNTAX          INTEGER { clear(1), lockoutOfProtection(2), 
                        forcedSwitchOfWorking(3), 
                        forcedSwitchOfProtection(4), 
                        manualSwitchOfWorking(5), 
                        manualSwitchOfProtection(6), exercise(7) }
    MAX-ACCESS      read-create
    STATUS          current
    DESCRIPTION     
            "A switch command initiates one external request for evaluation.
             
             (1) Clear - Clears all switch commands on the channel.
             
             (2) Lockout Of Protection - Prevents any of the working channels
             from switching to the protection line by issuing a Lockout of
             Protection request [unless a request of equal priority (i.e., a
             Lockout of Protection) is already in effect].
             
             (3) Forced Switch of Working (to Protection) - Switches the
             working channel to the protection line unless a request of equal
             or higher priority is in effect, by issuing a Forced Switch
             request.
             
             (4) Forced Switch of Protection (to Working) - Switches the
             working channel back from the protection line to the working
             line unless a request of equal or higher priority is in effect,
             by issuing a Forced Switch request.  This command applies only
             in the 1+1 architecture.
             
             (5) Manual Switch of Working (to Protection) - Switches the
             working channel to the protection line unless a request of equal
             or higher priority is in effect, by issuing a Manual Switch
             request.
             
             (6) Manual Switch of Protection (to Working) - Switches the
             working channel back from the protection line to the working
             line unless a request of equal or higher priority is in effect,
             by issuing a Manual Switch request.  This command applies only
             in the 1+1 architecture for the null.
             
             (7) Exercise - Exercises the protocol for a protection switch
             unless a request of equal or higher priority is in effect, by
             issuing an Exercise request and checking the response on the APS
             channel.
             
             Reading this variable always returns zero (0)."
    DEFVAL          { clear }
    ::= { sonusApsChannelEntry 4 }

sonusApsChannelControlCommand OBJECT-TYPE
    SYNTAX          INTEGER { lockoutWorkingChannel(1), clearLockout(2) }
    MAX-ACCESS      read-create
    STATUS          current
    DESCRIPTION     
            "A control command controls the APS operation.
             
             (1) Lockout a Working Channel - Prevents the specified working channel
             from switching to the protection line.
             (2) Clear Lockout-a-Working-Channel - Clears the Lockout a
             Working Channel command for the specified channel.
             
             Reading this variable always returns zero (0).
             
             This variable is not provided if the channels's
             GroupArchitecture is onePlusOne(1)."
    DEFVAL          { clearLockout }
    ::= { sonusApsChannelEntry 5 }

sonusApsChannelStatus OBJECT-TYPE
    SYNTAX          BITS { sdCondition(0), sfCondition(1), lockedOut(2), 
                        switched(3), bothLinesFailed(4), 
                        protectionLineBusy(5) }
    MAX-ACCESS      read-only
    STATUS          current
    DESCRIPTION     
            "Indicates the current state of the channel.
             
             Bit 0 - Signal Degrade (SD) Condition.  Indicates a 'soft
             failure' condition resulting from the Line BER exceeding a
             pre-selected threshold.
             
             Bit 1 - Signal Fail (SF) Condition.  Indicates a 'hard failure'
             condition detected on the incoming OC-N signal.
             
             Bit 2 - Locked Out.  This bit, when applied to a working
             channel, indicates that the channel is prevented from switching
             to the protection line.  When applied to the null channel, this
             bit indicates that no working channel may switch to the
             protection line.
             
             The remaining states only apply to working channels which have
             attempted to initiate an automatic protection switch.
             
             Bit 3 - Switched.  Indictes that the working channel is
             currently switched to the protection line.
             
             Bit 4 - Both Lines Failed.  Indictes that both the working line
             and the protection line are currently in a failure state.
             
             Bit 5 - Protection Line Busy.  Indictes that the protection line
             is busy servicing a different working channel.  (This condition
             can only occur in the 1:n architecture.)"
    ::= { sonusApsChannelEntry 6 }

sonusApsChannelOperDirectionMode OBJECT-TYPE
    SYNTAX          INTEGER { unidirectional(1), bidirectional(2) }
    MAX-ACCESS      read-only
    STATUS          current
    DESCRIPTION     
            "The current APS directional mode that the APS channel is
             operating in."
    ::= { sonusApsChannelEntry 7 }

sonusApsChannelSignalDegrades OBJECT-TYPE
    SYNTAX          Counter32
    MAX-ACCESS      read-only
    STATUS          current
    DESCRIPTION     
            "A count of Signal Degrade conditions.  This condition occurs
             when the line Bit Error Rate exceeds the currently configured
             threshold."
    ::= { sonusApsChannelEntry 8 }

sonusApsChannelSignalFails OBJECT-TYPE
    SYNTAX          Counter32
    MAX-ACCESS      read-only
    STATUS          current
    DESCRIPTION     
            "A count of Signal Fail conditions that have been detected on
             the incoming signal.  This condition occurs when a loss of
             signal, loss of frame, AIS-L or a Line bit error rate exceeding
             10^-3 is detected on an incoming line."
    ::= { sonusApsChannelEntry 9 }

sonusApsChannelSwitchovers OBJECT-TYPE
    SYNTAX          Counter32
    MAX-ACCESS      read-only
    STATUS          current
    DESCRIPTION     
            "The number of switchovers that have occurred on this channel."
    ::= { sonusApsChannelEntry 10 }

sonusApsChannelLastSwitchover OBJECT-TYPE
    SYNTAX          TimeTicks
    MAX-ACCESS      read-only
    STATUS          current
    DESCRIPTION     
            "The value of sysUpTime when this channel last switched over."
    ::= { sonusApsChannelEntry 11 }

sonusApsChannelRowStatus OBJECT-TYPE
    SYNTAX          RowStatus
    MAX-ACCESS      read-create
    STATUS          current
    DESCRIPTION     
            "The status of the MIB table entry (row).  See SNMPv2-TC for the
             definition and use of RowStatus."
    ::= { sonusApsChannelEntry 12 }

sonusApsLineTable OBJECT-TYPE
    SYNTAX          SEQUENCE OF SonusApsLineEntry
    MAX-ACCESS      not-accessible
    STATUS          current
    DESCRIPTION     
            "This table provides a mapping of ifIndex values for SONET lines
             to their corresponding APS channels.  Only interfaces whose
             ifType value is sonet(39) will have entries in this table."
    ::= { sonusSonetApsMIBObjects 4 }

sonusApsLineEntry OBJECT-TYPE
    SYNTAX          SonusApsLineEntry
    MAX-ACCESS      not-accessible
    STATUS          current
    DESCRIPTION     
            "An entry in the APS line table."
    INDEX           { ifIndex }
    ::= { sonusApsLineTable 1 }

SonusApsLineEntry ::=
    SEQUENCE {
        sonusApsLineGroupId             InterfaceIndex,
        sonusApsLineChannelNumber       Integer32
    }

sonusApsLineGroupId OBJECT-TYPE
    SYNTAX          InterfaceIndex
    MAX-ACCESS      read-only
    STATUS          current
    DESCRIPTION     
            "The ifIndex that provides a unique id for the APS group."
    ::= { sonusApsLineEntry 1 }

sonusApsLineChannelNumber OBJECT-TYPE
    SYNTAX          Integer32 (0..15)
    MAX-ACCESS      read-only
    STATUS          current
    DESCRIPTION     
            "The identifying number of the APS channel within the APS
             group."
    ::= { sonusApsLineEntry 2 }

sonusSonetApsMIBNotifications OBJECT IDENTIFIER
    ::= { sonusSonetApsMIB 2 }

sonusSonetApsMIBNotificationsPrefix OBJECT IDENTIFIER
    ::= { sonusSonetApsMIBNotifications 0 }

sonusSonetApsConformance OBJECT IDENTIFIER
    ::= { sonusSonetApsMIB 3 }

sonusSonetApsGroups OBJECT IDENTIFIER
    ::= { sonusSonetApsConformance 1 }

sonusSonetApsCompliances OBJECT IDENTIFIER
    ::= { sonusSonetApsConformance 2 }

sonusApsTrapProtectionSwitchingByteFailure NOTIFICATION-TYPE
    OBJECTS         { sonusApsGroupProtectionSwitchingByteFailures, 
                      sonusApsGroupOperStatus }
    STATUS          current
    DESCRIPTION     
            "A sonusApsTrapProtectionSwitchingByteFailure notification is sent
             when the value of an instance of
             sonusApsGroupProtectionSwitchingByteFailures increments."
    ::= { sonusSonetApsMIBNotificationsPrefix 1 }

sonusApsTrapChannelMismatch NOTIFICATION-TYPE
    OBJECTS         { sonusApsGroupChannelMismatches, 
                      sonusApsGroupOperStatus }
    STATUS          current
    DESCRIPTION     
            "A sonusApsTrapChannelMismatch notification is sent when the value
             of an instance of sonusApsStatusChannelMismatches increments."
    ::= { sonusSonetApsMIBNotificationsPrefix 2 }

sonusApsTrapModeMismatch NOTIFICATION-TYPE
    OBJECTS         { sonusApsGroupModeMismatches, 
                      sonusApsGroupOperStatus }
    STATUS          current
    DESCRIPTION     
            "A sonusApsTrapModeMismatch notification is sent when the value of
             an instance of sonusApsStatusModeMismatches increments."
    ::= { sonusSonetApsMIBNotificationsPrefix 3 }

sonusApsTrapFarEndProtectionLineFailure NOTIFICATION-TYPE
    OBJECTS         { sonusApsGroupFarEndProtectionLineFailures, 
                      sonusApsGroupOperStatus }
    STATUS          current
    DESCRIPTION     
            "A sonusApsTrapFarEndProtectionLineFailure notification is sent when
             the value of an instance of sonusApsGroupFarEndProtectionLineFailures
             increments."
    ::= { sonusSonetApsMIBNotificationsPrefix 4 }

sonusApsTrapSwitchover NOTIFICATION-TYPE
    OBJECTS         { sonusApsChannelSwitchovers, sonusApsChannelStatus }
    STATUS          current
    DESCRIPTION     
            "A sonusApsTrapSwitchover notification is sent when the value of an
             instance of sonusApsChanSwitchovers for a working channel
             increments."
    ::= { sonusSonetApsMIBNotificationsPrefix 5 }

sonusApsGroupGroup OBJECT-GROUP
    OBJECTS         { sonusApsGroupCount, sonusApsGroupStatus, 
                      sonusApsGroupArchitecture, 
                      sonusApsGroupAdminDirection, 
                      sonusApsGroupAdminSwitching, 
                      sonusApsGroupExtraTraffic, 
                      sonusApsGroupSignalFailBerThreshold, 
                      sonusApsGroupSignalDegradeBerThreshold, 
                      sonusApsGroupWaitToRestoreTime, sonusApsGroupName, 
                      sonusApsGroupSwitchedChannel, 
                      sonusApsGroupOperStatus, sonusApsGroupK1K2Received, 
                      sonusApsGroupK1K2Transmitted, 
                      sonusApsGroupProtectionSwitchingByteFailures, 
                      sonusApsGroupChannelMismatches, 
                      sonusApsGroupModeMismatches, 
                      sonusApsGroupFarEndProtectionLineFailures, 
                      sonusApsGroupCreationTime }
    STATUS          current
    DESCRIPTION     
            "The objects which are used to provide SONET APS group
             configuration and status."
    ::= { sonusSonetApsGroups 1 }

sonusApsChannelGroup OBJECT-GROUP
    OBJECTS         { sonusApsChannelLineId, sonusApsChannelPriority, 
                      sonusApsChannelSwitchCommand, 
                      sonusApsChannelControlCommand, 
                      sonusApsChannelStatus, 
                      sonusApsChannelOperDirectionMode, 
                      sonusApsChannelSignalDegrades, 
                      sonusApsChannelSignalFails, 
                      sonusApsChannelSwitchovers, 
                      sonusApsChannelLastSwitchover }
    STATUS          current
    DESCRIPTION     
            "The objects which are used to provide SONET APS channel
             configuration and status."
    ::= { sonusSonetApsGroups 2 }

sonusApsLineGroup OBJECT-GROUP
    OBJECTS         { sonusApsLineGroupId, sonusApsLineChannelNumber }
    STATUS          current
    DESCRIPTION     
            "The objects which are used to provide the mapping of SONET
             lines to APS channels."
    ::= { sonusSonetApsGroups 3 }

sonusApsNotificationGroup NOTIFICATION-GROUP
    NOTIFICATIONS   { sonusApsTrapProtectionSwitchingByteFailure, 
                      sonusApsTrapChannelMismatch, 
                      sonusApsTrapModeMismatch, 
                      sonusApsTrapFarEndProtectionLineFailure, 
                      sonusApsTrapSwitchover }
    STATUS          current
    DESCRIPTION     
            "The notifications (traps) that may be supported for the LTE."
    ::= { sonusSonetApsGroups 4 }

sonusSonetApsCompliance MODULE-COMPLIANCE
    STATUS          current
    DESCRIPTION     
            "The compliance statement for this MIB."

    MODULE          -- this module

        MANDATORY-GROUPS    { sonusApsGroupGroup, sonusApsChannelGroup, 
                      sonusApsLineGroup, sonusApsNotificationGroup }

    ::= { sonusSonetApsCompliances 1 }

END -- end of module SONUS-SONET-APS-MIB.
