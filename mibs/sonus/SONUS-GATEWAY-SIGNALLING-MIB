--
-- This SMIv2 module has been generated by smidump 0.2-cvs. Do not edit.
--

SONUS-GATEWAY-SIGNALLING-MIB DEFINITIONS ::= BEGIN

IMPORTS
    Ipv6Address
        FROM IPV6-TC
    Counter64, Integer32, IpAddress, MODULE-IDENTITY, NOTIFICATION-TYPE, 
    OBJECT-TYPE
        FROM SNMPv2-SMI
    DisplayString, RowStatus
        FROM SNMPv2-TC
    sonusEventClass, sonusEventDescription, sonusEventLevel, 
    sonusEventTime, sonusSequenceId
        FROM SONUS-COMMON-MIB
    sonusSignallingMIBs
        FROM SONUS-SMI
    SonusAdminState, SonusName, SonusNameReference, SonusServiceState
        FROM SONUS-TC;

sonusGatewaySignallingMIB MODULE-IDENTITY
    LAST-UPDATED    "201205110000Z"
    ORGANIZATION    
            "Sonus Networks, Inc."
    CONTACT-INFO    
            "   Customer Support    
             Sonus Networks, Inc.
             7 Technology Park Drive
             Westford, MA 01886
             USA
             
             Tel: 978-614-8100
             Fax: 978-614-8609"
    DESCRIPTION     
            "The MIB Module for IP Call Signal Channel Management."
    ::= { sonusSignallingMIBs 2 }


sonusGatewaySignallingMIBObjects OBJECT IDENTIFIER
    ::= { sonusGatewaySignallingMIB 1 }

sonusGwSigTimerObjects OBJECT IDENTIFIER
    ::= { sonusGatewaySignallingMIBObjects 1 }

sonusGwSigSrvTimerT301 OBJECT-TYPE
    SYNTAX          Integer32 (1..65535)
    MAX-ACCESS      read-write
    STATUS          obsolete
    DESCRIPTION     
            "This is the gateway to gateway call establishment timer T301 (in seconds). This value applies to all future GW-GW calls."
    DEFVAL          { 30 }
    ::= { sonusGwSigTimerObjects 1 }

sonusGwSigSrvTimerT303 OBJECT-TYPE
    SYNTAX          Integer32 (1..65535)
    MAX-ACCESS      read-write
    STATUS          obsolete
    DESCRIPTION     
            "This is the gateway to gateway call setup timer T303 (in seconds). This value applies to all future GW-GW calls."
    DEFVAL          { 180 }
    ::= { sonusGwSigTimerObjects 2 }

sonusGwSigTimerEstabish OBJECT-TYPE
    SYNTAX          Integer32 (1..65535)
    MAX-ACCESS      read-write
    STATUS          current
    DESCRIPTION     
            "This is the Gateway Signal Channel Establishment Timer (in seconds.)  This value applies to all signal channels."
    DEFVAL          { 10 }
    ::= { sonusGwSigTimerObjects 3 }

sonusGwSigTimerKeepalive OBJECT-TYPE
    SYNTAX          Integer32 (1..65535)
    MAX-ACCESS      read-write
    STATUS          current
    DESCRIPTION     
            "This is the Gateway Signal Channel Keepalive Timer (in seconds.)  This value applies to all signal channels."
    DEFVAL          { 3 }
    ::= { sonusGwSigTimerObjects 4 }

sonusGwSigTimerRetry OBJECT-TYPE
    SYNTAX          Integer32 (1..65535)
    MAX-ACCESS      read-write
    STATUS          current
    DESCRIPTION     
            "The amount of time (in minutes) the GSX will continue to attempt to recover a GW Signaling Link as long as there are stable calls up."
    DEFVAL          { 60 }
    ::= { sonusGwSigTimerObjects 5 }

sonusGwSigTimerIdle OBJECT-TYPE
    SYNTAX          Integer32 (0..65535)
    MAX-ACCESS      read-write
    STATUS          current
    DESCRIPTION     
            "The amount of time (in hours) a GW Signaling Link May be idle before it is taken down.  If set to 0, the link will not be taken down."
    DEFVAL          { 0 }
    ::= { sonusGwSigTimerObjects 6 }

sonusGwSigTimerCongRelDelay OBJECT-TYPE
    SYNTAX          Integer32 (0..5)
    MAX-ACCESS      read-write
    STATUS          current
    DESCRIPTION     
            "The amount of time (in seconds) that a call which is rejected due to congestion will be delayed before the release is issued. Prevents re-attempts from causing overload conditions."
    DEFVAL          { 0 }
    ::= { sonusGwSigTimerObjects 7 }

sonusGwSigActionObjects OBJECT IDENTIFIER
    ::= { sonusGatewaySignallingMIBObjects 2 }

sonusGwSigAction OBJECT-TYPE
    SYNTAX          INTEGER { open(1), close(2), none(3) }
    MAX-ACCESS      read-write
    STATUS          current
    DESCRIPTION     
            "The action to be taken on the specified link."
    DEFVAL          { none }
    ::= { sonusGwSigActionObjects 1 }

sonusGwSigActionDestIpAddr OBJECT-TYPE
    SYNTAX          IpAddress
    MAX-ACCESS      read-write
    STATUS          current
    DESCRIPTION     
            "The IP Address of the Destination Gateway to which the signaling link will be opened or closed."
    DEFVAL          { '00000000'H }
    ::= { sonusGwSigActionObjects 2 }

sonusGwSigActionDestPort OBJECT-TYPE
    SYNTAX          Integer32 (1..65535)
    MAX-ACCESS      read-write
    STATUS          current
    DESCRIPTION     
            "The Port Number to which a call sig link will be opened."
    DEFVAL          { 2569 }
    ::= { sonusGwSigActionObjects 3 }

sonusGwSigActionDir OBJECT-TYPE
    SYNTAX          INTEGER { to(1), from(2), both(3) }
    MAX-ACCESS      read-write
    STATUS          current
    DESCRIPTION     
            "The direction of the link which we will be opening or closing."
    DEFVAL          { to }
    ::= { sonusGwSigActionObjects 4 }

sonusGwSigActionDestIp6Addr OBJECT-TYPE
    SYNTAX          Ipv6Address
    MAX-ACCESS      read-write
    STATUS          current
    DESCRIPTION     
            "The IPv6 Address of the Destination Gateway to which the signaling link will be opened or closed."
    ::= { sonusGwSigActionObjects 5 }

sonusGwSigActionDestIpVersion OBJECT-TYPE
    SYNTAX          INTEGER { afInet(2), afInet6(24) }
    MAX-ACCESS      read-only
    STATUS          current
    DESCRIPTION     
            "The IP Address type  of the Destination Gateway ."
    ::= { sonusGwSigActionObjects 6 }

sonusGwSigPortTable OBJECT-TYPE
    SYNTAX          SEQUENCE OF SonusGwSigPortEntry
    MAX-ACCESS      not-accessible
    STATUS          current
    DESCRIPTION     
            "Table of Gateway Signal Listen Port configurations.  Limit of two ports."
    ::= { sonusGatewaySignallingMIBObjects 3 }

sonusGwSigPortEntry OBJECT-TYPE
    SYNTAX          SonusGwSigPortEntry
    MAX-ACCESS      not-accessible
    STATUS          current
    DESCRIPTION     
            "Gateway Signal Listen Port configuration."
    INDEX           { sonusGwSigPortIndex }
    ::= { sonusGwSigPortTable 1 }

SonusGwSigPortEntry ::=
    SEQUENCE {
        sonusGwSigPortIndex             Integer32,
        sonusGwSigPortIpAddress         IpAddress,
        sonusGwSigPortNum               Integer32,
        sonusGwSigPortInterface         INTEGER,
        sonusGwSigPortRole              INTEGER,
        sonusGwSigPortMode              SonusServiceState,
        sonusGwSigPortState             SonusAdminState,
        sonusGwSigPortRowStatus         RowStatus,
        sonusGwSigPortNifGroupName      SonusNameReference,
        sonusGwSigPortIp6Address        Ipv6Address,
        sonusGwSigPortIpVersion         INTEGER
    }

sonusGwSigPortIndex OBJECT-TYPE
    SYNTAX          Integer32
    MAX-ACCESS      read-only
    STATUS          current
    DESCRIPTION     
            "Identifies the Signal Listen Port entry."
    ::= { sonusGwSigPortEntry 1 }

sonusGwSigPortIpAddress OBJECT-TYPE
    SYNTAX          IpAddress
    MAX-ACCESS      read-write
    STATUS          current
    DESCRIPTION     
            "IP Address of the Gateway Signal Listen Port - this is a required parameter."
    DEFVAL          { '00000000'H }
    ::= { sonusGwSigPortEntry 2 }

sonusGwSigPortNum OBJECT-TYPE
    SYNTAX          Integer32 (1..65535)
    MAX-ACCESS      read-write
    STATUS          current
    DESCRIPTION     
            "TCP port number of Gateway Signal Listen Port (default is Sonus registered port 2569)."
    ::= { sonusGwSigPortEntry 3 }

sonusGwSigPortInterface OBJECT-TYPE
    SYNTAX          INTEGER { mgtNif(1), nif(2) }
    MAX-ACCESS      read-write
    STATUS          current
    DESCRIPTION     
            "The interface type of Gateway Signal Listen Port.  This element select which gateway network interfaces to use for GW-GW signaling traffic. 'mgtnif' routes traffic over the gateway Managment ports.  'nif' routes traffic over one of the gateway PNS ports."
    DEFVAL          { mgtNif }
    ::= { sonusGwSigPortEntry 4 }

sonusGwSigPortRole OBJECT-TYPE
    SYNTAX          INTEGER { primary(1), secondary(2) }
    MAX-ACCESS      read-write
    STATUS          current
    DESCRIPTION     
            "Role of the Gateway Signal Listen Port."
    DEFVAL          { primary }
    ::= { sonusGwSigPortEntry 5 }

sonusGwSigPortMode OBJECT-TYPE
    SYNTAX          SonusServiceState
    MAX-ACCESS      read-write
    STATUS          current
    DESCRIPTION     
            "Mode of the Gateway Signal Listen Port."
    DEFVAL          { inService }
    ::= { sonusGwSigPortEntry 6 }

sonusGwSigPortState OBJECT-TYPE
    SYNTAX          SonusAdminState
    MAX-ACCESS      read-write
    STATUS          current
    DESCRIPTION     
            "State of the Gateway Signal Listen Port."
    DEFVAL          { disabled }
    ::= { sonusGwSigPortEntry 7 }

sonusGwSigPortRowStatus OBJECT-TYPE
    SYNTAX          RowStatus
    MAX-ACCESS      read-write
    STATUS          current
    DESCRIPTION     
            "This is for SNMP use."
    ::= { sonusGwSigPortEntry 8 }

sonusGwSigPortNifGroupName OBJECT-TYPE
    SYNTAX          SonusNameReference
    MAX-ACCESS      read-write
    STATUS          current
    DESCRIPTION     
            "The NIF group associated with this signaling port."
    ::= { sonusGwSigPortEntry 9 }

sonusGwSigPortIp6Address OBJECT-TYPE
    SYNTAX          Ipv6Address
    MAX-ACCESS      read-write
    STATUS          current
    DESCRIPTION     
            "IPV6 Address of the Gateway Signal Listen Port - this is a required parameter."
    ::= { sonusGwSigPortEntry 11 }

sonusGwSigPortIpVersion OBJECT-TYPE
    SYNTAX          INTEGER { afInet(2), afInet6(24) }
    MAX-ACCESS      read-only
    STATUS          current
    DESCRIPTION     
            "IP Address type of the Gateway Signal Listen Port."
    ::= { sonusGwSigPortEntry 12 }

sonusGwSigPortStatTable OBJECT-TYPE
    SYNTAX          SEQUENCE OF SonusGwSigPortStatEntry
    MAX-ACCESS      not-accessible
    STATUS          current
    DESCRIPTION     
            "Table of the status of Gateway Signal Listen Ports."
    ::= { sonusGatewaySignallingMIBObjects 4 }

sonusGwSigPortStatEntry OBJECT-TYPE
    SYNTAX          SonusGwSigPortStatEntry
    MAX-ACCESS      not-accessible
    STATUS          current
    DESCRIPTION     
            "Status of Gateway Signal Listen Port."
    INDEX           { sonusGwSigPortStatIndex }
    ::= { sonusGwSigPortStatTable 1 }

SonusGwSigPortStatEntry ::=
    SEQUENCE {
        sonusGwSigPortStatIndex         Integer32,
        sonusGwSigPortStatIpAddress     IpAddress,
        sonusGwSigPortStatNum           Integer32,
        sonusGwSigPortStatInterface     INTEGER,
        sonusGwSigPortStatRole          INTEGER,
        sonusGwSigPortStatNif           Integer32,
        sonusGwSigPortStatState         SonusServiceState,
        sonusGwSigPortStatNifGroupName  SonusNameReference
    }

sonusGwSigPortStatIndex OBJECT-TYPE
    SYNTAX          Integer32
    MAX-ACCESS      read-only
    STATUS          current
    DESCRIPTION     
            "Identifies the Signal Listen Port entry."
    ::= { sonusGwSigPortStatEntry 1 }

sonusGwSigPortStatIpAddress OBJECT-TYPE
    SYNTAX          IpAddress
    MAX-ACCESS      read-only
    STATUS          current
    DESCRIPTION     
            "IP Address of the Gateway Signal Listen Port."
    ::= { sonusGwSigPortStatEntry 2 }

sonusGwSigPortStatNum OBJECT-TYPE
    SYNTAX          Integer32
    MAX-ACCESS      read-only
    STATUS          current
    DESCRIPTION     
            "TCP port number of Gateway Signal Listen Port."
    ::= { sonusGwSigPortStatEntry 3 }

sonusGwSigPortStatInterface OBJECT-TYPE
    SYNTAX          INTEGER { mgtNif(1), nif(2) }
    MAX-ACCESS      read-only
    STATUS          current
    DESCRIPTION     
            "The interface type of Gateway Signal Listen Port."
    ::= { sonusGwSigPortStatEntry 4 }

sonusGwSigPortStatRole OBJECT-TYPE
    SYNTAX          INTEGER { primary(1), secondary(2) }
    MAX-ACCESS      read-only
    STATUS          current
    DESCRIPTION     
            "Role of the Gateway Signal Listen Port."
    ::= { sonusGwSigPortStatEntry 5 }

sonusGwSigPortStatNif OBJECT-TYPE
    SYNTAX          Integer32
    MAX-ACCESS      read-only
    STATUS          current
    DESCRIPTION     
            "The network interface (NIF) ifIndex for this Gateway Signal Listen Port."
    ::= { sonusGwSigPortStatEntry 6 }

sonusGwSigPortStatState OBJECT-TYPE
    SYNTAX          SonusServiceState
    MAX-ACCESS      read-only
    STATUS          current
    DESCRIPTION     
            "State of the Gateway Signal Listen Port."
    ::= { sonusGwSigPortStatEntry 7 }

sonusGwSigPortStatNifGroupName OBJECT-TYPE
    SYNTAX          SonusNameReference
    MAX-ACCESS      read-only
    STATUS          current
    DESCRIPTION     
            "The NIF group associated with this signaling port."
    ::= { sonusGwSigPortStatEntry 8 }

sonusGwSigActGwStatusTable OBJECT-TYPE
    SYNTAX          SEQUENCE OF SonusGwSigActGwStatusEntry
    MAX-ACCESS      not-accessible
    STATUS          current
    DESCRIPTION     
            "This table contains status of the active signaling channels with other gateways."
    ::= { sonusGatewaySignallingMIBObjects 5 }

sonusGwSigActGwStatusEntry OBJECT-TYPE
    SYNTAX          SonusGwSigActGwStatusEntry
    MAX-ACCESS      not-accessible
    STATUS          current
    DESCRIPTION     
            "Status of signaling channel another gateway."
    INDEX           { sonusGwSigActGwIpAddress, 
                      sonusGwSigActGwIp6Address, 
                      sonusGwSigActGwIpVersion }
    ::= { sonusGwSigActGwStatusTable 1 }

SonusGwSigActGwStatusEntry ::=
    SEQUENCE {
        sonusGwSigActGwName             DisplayString,
        sonusGwSigActGwIpAddress        IpAddress,
        sonusGwSigActGwLnkProto         INTEGER,
        sonusGwSigActGwNumActiveCalls   Integer32,
        sonusGwSigActGwNumActiveCallsTo Integer32,
        sonusGwSigActGwNumActiveCallsFrom Integer32,
        sonusGwSigActGwToState          SonusServiceState,
        sonusGwSigActGwFromState        SonusServiceState,
        sonusGwSigActGwInterface        INTEGER,
        sonusGwSigActGwFromBytesSent    Counter64,
        sonusGwSigActGwFromPdusSent     Counter64,
        sonusGwSigActGwFromBytesReceived Counter64,
        sonusGwSigActGwFromPdusReceived Counter64,
        sonusGwSigActGwFromTotalCalls   Counter64,
        sonusGwSigActGwFromCallRate     Integer32,
        sonusGwSigActGwToBytesSent      Counter64,
        sonusGwSigActGwToPdusSent       Counter64,
        sonusGwSigActGwToBytesReceived  Counter64,
        sonusGwSigActGwToPdusReceived   Counter64,
        sonusGwSigActGwToTotalCalls     Counter64,
        sonusGwSigActGwToCallRate       Integer32,
        sonusGwSigActGwFromLnkMajorVer  Integer32,
        sonusGwSigActGwFromLnkMinorVer  Integer32,
        sonusGwSigActGwToLnkMajorVer    Integer32,
        sonusGwSigActGwToLnkMinorVer    Integer32,
        sonusGwSigActGwRemoteMcLevel    Integer32,
        sonusGwSigActGwIp6Address       Ipv6Address,
        sonusGwSigActGwIpVersion        INTEGER
    }

sonusGwSigActGwName OBJECT-TYPE
    SYNTAX          DisplayString (SIZE(0..23))
    MAX-ACCESS      read-only
    STATUS          deprecated
    DESCRIPTION     
            "Name of the remote Gateway."
    ::= { sonusGwSigActGwStatusEntry 1 }

sonusGwSigActGwIpAddress OBJECT-TYPE
    SYNTAX          IpAddress
    MAX-ACCESS      read-only
    STATUS          current
    DESCRIPTION     
            "IP Address of the remote Gateway."
    ::= { sonusGwSigActGwStatusEntry 2 }

sonusGwSigActGwLnkProto OBJECT-TYPE
    SYNTAX          INTEGER { ioi(1), h323(2) }
    MAX-ACCESS      read-only
    STATUS          current
    DESCRIPTION     
            "The protocol being used between gateways."
    ::= { sonusGwSigActGwStatusEntry 3 }

sonusGwSigActGwNumActiveCalls OBJECT-TYPE
    SYNTAX          Integer32
    MAX-ACCESS      read-only
    STATUS          current
    DESCRIPTION     
            "Number of active calls between local and remote Gateway."
    ::= { sonusGwSigActGwStatusEntry 4 }

sonusGwSigActGwNumActiveCallsTo OBJECT-TYPE
    SYNTAX          Integer32
    MAX-ACCESS      read-only
    STATUS          current
    DESCRIPTION     
            "Number of active calls to this remote Gateway."
    ::= { sonusGwSigActGwStatusEntry 5 }

sonusGwSigActGwNumActiveCallsFrom OBJECT-TYPE
    SYNTAX          Integer32
    MAX-ACCESS      read-only
    STATUS          current
    DESCRIPTION     
            "Number of active calls from this remote Gateway."
    ::= { sonusGwSigActGwStatusEntry 6 }

sonusGwSigActGwToState OBJECT-TYPE
    SYNTAX          SonusServiceState
    MAX-ACCESS      read-only
    STATUS          current
    DESCRIPTION     
            "Current state of the signaling link to this remote Gateway"
    ::= { sonusGwSigActGwStatusEntry 7 }

sonusGwSigActGwFromState OBJECT-TYPE
    SYNTAX          SonusServiceState
    MAX-ACCESS      read-only
    STATUS          current
    DESCRIPTION     
            "Current state of the signaling link from this remote Gateway"
    ::= { sonusGwSigActGwStatusEntry 8 }

sonusGwSigActGwInterface OBJECT-TYPE
    SYNTAX          INTEGER { mgtNif(1), nif(2) }
    MAX-ACCESS      read-only
    STATUS          current
    DESCRIPTION     
            "The interface used for this link."
    ::= { sonusGwSigActGwStatusEntry 9 }

sonusGwSigActGwFromBytesSent OBJECT-TYPE
    SYNTAX          Counter64
    MAX-ACCESS      read-only
    STATUS          current
    DESCRIPTION     
            "The total number of signaling bytes sent to this remote Gateway for incoming calls"
    ::= { sonusGwSigActGwStatusEntry 10 }

sonusGwSigActGwFromPdusSent OBJECT-TYPE
    SYNTAX          Counter64
    MAX-ACCESS      read-only
    STATUS          current
    DESCRIPTION     
            "The total number of signaling PDUS sent to this remote Gateway for incoming calls"
    ::= { sonusGwSigActGwStatusEntry 11 }

sonusGwSigActGwFromBytesReceived OBJECT-TYPE
    SYNTAX          Counter64
    MAX-ACCESS      read-only
    STATUS          current
    DESCRIPTION     
            "The total number of signaling bytes received from this remote Gateway for incoming calls"
    ::= { sonusGwSigActGwStatusEntry 12 }

sonusGwSigActGwFromPdusReceived OBJECT-TYPE
    SYNTAX          Counter64
    MAX-ACCESS      read-only
    STATUS          current
    DESCRIPTION     
            "The total number of signaling PDUS received from this remote Gateway for incoming calls"
    ::= { sonusGwSigActGwStatusEntry 13 }

sonusGwSigActGwFromTotalCalls OBJECT-TYPE
    SYNTAX          Counter64
    MAX-ACCESS      read-only
    STATUS          current
    DESCRIPTION     
            "The total number of calls originated by the remote on this link "
    ::= { sonusGwSigActGwStatusEntry 14 }

sonusGwSigActGwFromCallRate OBJECT-TYPE
    SYNTAX          Integer32
    MAX-ACCESS      read-only
    STATUS          current
    DESCRIPTION     
            "The number of calls/sec processed by the GWFE in the last minute on the link which was originated by the remote"
    ::= { sonusGwSigActGwStatusEntry 15 }

sonusGwSigActGwToBytesSent OBJECT-TYPE
    SYNTAX          Counter64
    MAX-ACCESS      read-only
    STATUS          current
    DESCRIPTION     
            "The total number of signaling bytes sent to this remote Gateway for outgoing calls"
    ::= { sonusGwSigActGwStatusEntry 16 }

sonusGwSigActGwToPdusSent OBJECT-TYPE
    SYNTAX          Counter64
    MAX-ACCESS      read-only
    STATUS          current
    DESCRIPTION     
            "The total number of signaling PDUS sent to this remote Gateway for outgoing calls"
    ::= { sonusGwSigActGwStatusEntry 17 }

sonusGwSigActGwToBytesReceived OBJECT-TYPE
    SYNTAX          Counter64
    MAX-ACCESS      read-only
    STATUS          current
    DESCRIPTION     
            "The total number of signaling bytes received from this remote Gateway for outgoing calls"
    ::= { sonusGwSigActGwStatusEntry 18 }

sonusGwSigActGwToPdusReceived OBJECT-TYPE
    SYNTAX          Counter64
    MAX-ACCESS      read-only
    STATUS          current
    DESCRIPTION     
            "The total number of signaling PDUS received from this remote Gateway for outgoing calls"
    ::= { sonusGwSigActGwStatusEntry 19 }

sonusGwSigActGwToTotalCalls OBJECT-TYPE
    SYNTAX          Counter64
    MAX-ACCESS      read-only
    STATUS          current
    DESCRIPTION     
            "The total number of calls originated locally on this link "
    ::= { sonusGwSigActGwStatusEntry 20 }

sonusGwSigActGwToCallRate OBJECT-TYPE
    SYNTAX          Integer32
    MAX-ACCESS      read-only
    STATUS          current
    DESCRIPTION     
            "The number of calls/sec processed by the GWFE in the last minute on the link which was originated locally"
    ::= { sonusGwSigActGwStatusEntry 21 }

sonusGwSigActGwFromLnkMajorVer OBJECT-TYPE
    SYNTAX          Integer32
    MAX-ACCESS      read-only
    STATUS          current
    DESCRIPTION     
            "The major version of link protocol being used between gateways."
    ::= { sonusGwSigActGwStatusEntry 22 }

sonusGwSigActGwFromLnkMinorVer OBJECT-TYPE
    SYNTAX          Integer32
    MAX-ACCESS      read-only
    STATUS          current
    DESCRIPTION     
            "The minor version of link protocol being used between gateways."
    ::= { sonusGwSigActGwStatusEntry 23 }

sonusGwSigActGwToLnkMajorVer OBJECT-TYPE
    SYNTAX          Integer32
    MAX-ACCESS      read-only
    STATUS          current
    DESCRIPTION     
            "The major version of link protocol being used between gateways."
    ::= { sonusGwSigActGwStatusEntry 24 }

sonusGwSigActGwToLnkMinorVer OBJECT-TYPE
    SYNTAX          Integer32
    MAX-ACCESS      read-only
    STATUS          current
    DESCRIPTION     
            "The minor version of link protocol being used between gateways."
    ::= { sonusGwSigActGwStatusEntry 25 }

sonusGwSigActGwRemoteMcLevel OBJECT-TYPE
    SYNTAX          Integer32
    MAX-ACCESS      read-only
    STATUS          current
    DESCRIPTION     
            "The remote gateways machine congestion level."
    ::= { sonusGwSigActGwStatusEntry 26 }

sonusGwSigActGwIp6Address OBJECT-TYPE
    SYNTAX          Ipv6Address
    MAX-ACCESS      read-only
    STATUS          current
    DESCRIPTION     
            "IPV6 Address of the remote Gateway."
    ::= { sonusGwSigActGwStatusEntry 27 }

sonusGwSigActGwIpVersion OBJECT-TYPE
    SYNTAX          INTEGER { afInet(2), afInet6(24) }
    MAX-ACCESS      read-only
    STATUS          current
    DESCRIPTION     
            "IP Address Type of the Gateway signaling link"
    ::= { sonusGwSigActGwStatusEntry 28 }

sonusGwSigLinkObjects OBJECT IDENTIFIER
    ::= { sonusGatewaySignallingMIBObjects 6 }

sonusGwSigPendQMax OBJECT-TYPE
    SYNTAX          Integer32 (1..20)
    MAX-ACCESS      read-write
    STATUS          current
    DESCRIPTION     
            "The maximum number of calls to be queued waiting for Signaling Link to be established."
    DEFVAL          { 20 }
    ::= { sonusGwSigLinkObjects 1 }

sonusGwSigServiceGroup OBJECT IDENTIFIER
    ::= { sonusGatewaySignallingMIBObjects 7 }

sonusGwSigServiceGroupNextIndex OBJECT-TYPE
    SYNTAX          Integer32
    MAX-ACCESS      read-only
    STATUS          current
    DESCRIPTION     
            "The next valid index to use when creating a new sonusGwSigServiceGroupEntry"
    ::= { sonusGwSigServiceGroup 1 }

sonusGwSigServiceGroupTable OBJECT-TYPE
    SYNTAX          SEQUENCE OF SonusGwSigServiceGroupEntry
    MAX-ACCESS      not-accessible
    STATUS          current
    DESCRIPTION     
            "This table contains information about each Gateway Service Group
             configured to be a member of the node. 
             A management entity may create rows for Service Group that are
             anticipated to be supported in the future."
    ::= { sonusGwSigServiceGroup 2 }

sonusGwSigServiceGroupEntry OBJECT-TYPE
    SYNTAX          SonusGwSigServiceGroupEntry
    MAX-ACCESS      not-accessible
    STATUS          current
    DESCRIPTION     
            "This table describes the Gateway Service Groups that interconnect
             GSX9000s"
    INDEX           { sonusGwSigServiceGroupListIndex }
    ::= { sonusGwSigServiceGroupTable 1 }

SonusGwSigServiceGroupEntry ::=
    SEQUENCE {
        sonusGwSigServiceGroupListIndex Integer32,
        sonusGwSigServiceGroupName      SonusName,
        sonusGwSigServiceGroupRowStatus RowStatus,
        sonusGwSigServiceGroupAdminState SonusAdminState,
        sonusGwSigServiceGroupMode      SonusServiceState,
        sonusGwSigServiceGroupAction    INTEGER,
        sonusGwSigServiceGroupDryupTimeout  Integer32,
        sonusGwSigServiceGroupTG        SonusNameReference,
        sonusGwSigServiceGroupSourceAddressFiltering            SonusAdminState,
        sonusGwSigServiceGroupMediaNifGroupName       SonusNameReference,
        sonusGwSigServiceGroupAccMc1Percent   Integer32,
        sonusGwSigServiceGroupAccMc2Percent   Integer32,
        sonusGwSigServiceGroupAccTimer  Integer32,
        sonusGwSigServiceGroupDirectMediaAllowed        SonusAdminState,
        sonusGwSigServiceGroupMediaZoneName   SonusNameReference,
        sonusGwSigServiceGroupMediaZoneId Integer32
    }

sonusGwSigServiceGroupListIndex OBJECT-TYPE
    SYNTAX          Integer32 (1..256)
    MAX-ACCESS      read-only
    STATUS          current
    DESCRIPTION     
            "The index of the Gateway Service Group entry."
    ::= { sonusGwSigServiceGroupEntry 1 }

sonusGwSigServiceGroupName OBJECT-TYPE
    SYNTAX          SonusName
    MAX-ACCESS      read-write
    STATUS          current
    DESCRIPTION     
            "The name of this Gateway Service Group."
    ::= { sonusGwSigServiceGroupEntry 2 }

sonusGwSigServiceGroupRowStatus OBJECT-TYPE
    SYNTAX          RowStatus
    MAX-ACCESS      read-write
    STATUS          current
    DESCRIPTION     
            ""
    ::= { sonusGwSigServiceGroupEntry 3 }

sonusGwSigServiceGroupAdminState OBJECT-TYPE
    SYNTAX          SonusAdminState
    MAX-ACCESS      read-write
    STATUS          current
    DESCRIPTION     
            "The admin state of the this Gateway Service Group."
    ::= { sonusGwSigServiceGroupEntry 4 }

sonusGwSigServiceGroupMode OBJECT-TYPE
    SYNTAX          SonusServiceState
    MAX-ACCESS      read-write
    STATUS          current
    DESCRIPTION     
            "The mode of operation of this Gateway Service Group."
    ::= { sonusGwSigServiceGroupEntry 5 }

sonusGwSigServiceGroupAction OBJECT-TYPE
    SYNTAX          INTEGER { dryup(1), force(2), undefined(3) }
    MAX-ACCESS      read-write
    STATUS          current
    DESCRIPTION     
            "The action taken on calls for this Gateway Service Group."
    DEFVAL          { dryup }
    ::= { sonusGwSigServiceGroupEntry 6 }

sonusGwSigServiceGroupDryupTimeout OBJECT-TYPE
    SYNTAX          Integer32 (0..1440)
    MAX-ACCESS      read-write
    STATUS          current
    DESCRIPTION     
            "The timeout value in minutes for dryup action for this
             Gateway Service Group."
    DEFVAL          { 5 }
    ::= { sonusGwSigServiceGroupEntry 7 }

sonusGwSigServiceGroupTG OBJECT-TYPE
    SYNTAX          SonusNameReference
    MAX-ACCESS      read-write
    STATUS          current
    DESCRIPTION     
            "The Trunk Group which this Gateway Service Group belongs to."
    ::= { sonusGwSigServiceGroupEntry 8 }

sonusGwSigServiceGroupSourceAddressFiltering OBJECT-TYPE
    SYNTAX          SonusAdminState
    MAX-ACCESS      read-write
    STATUS          current
    DESCRIPTION     
            "This object indicates whether or not the GSX will perform IP source
             address filtering on incoming media packets for this trunk group.
             When ENABLED, the SG will only accept incoming media packets whose
             source address matches the destination address of outbound packets.
             When DISABLED, the GSX does not filter the incoming media stream.
             The source address to filter on is supplied during call signaling."
    DEFVAL          { enabled }
    ::= { sonusGwSigServiceGroupEntry 9 }

sonusGwSigServiceGroupMediaNifGroupName OBJECT-TYPE
    SYNTAX          SonusNameReference
    MAX-ACCESS      read-write
    STATUS          current
    DESCRIPTION     
            "The Media NIF Group associated with this Gateway Service Group."
    ::= { sonusGwSigServiceGroupEntry 10 }

sonusGwSigServiceGroupAccMc1Percent OBJECT-TYPE
    SYNTAX          Integer32 (0..100)
    MAX-ACCESS      read-write
    STATUS          current
    DESCRIPTION     
            "The percentage of calls to continue to send to a remote congested gateway (in MC1)."
    DEFVAL          { 90 }
    ::= { sonusGwSigServiceGroupEntry 11 }

sonusGwSigServiceGroupAccMc2Percent OBJECT-TYPE
    SYNTAX          Integer32 (0..100)
    MAX-ACCESS      read-write
    STATUS          current
    DESCRIPTION     
            "The percentage of calls to continue to send to a remote congested gateway (in MC2)."
    DEFVAL          { 70 }
    ::= { sonusGwSigServiceGroupEntry 12 }

sonusGwSigServiceGroupAccTimer OBJECT-TYPE
    SYNTAX          Integer32 (0..10)
    MAX-ACCESS      read-write
    STATUS          current
    DESCRIPTION     
            "Automatic congestion control timer."
    DEFVAL          { 0 }
    ::= { sonusGwSigServiceGroupEntry 13 }

sonusGwSigServiceGroupDirectMediaAllowed OBJECT-TYPE
    SYNTAX          SonusAdminState
    MAX-ACCESS      read-write
    STATUS          current
    DESCRIPTION     
            "This indicates whether or not Direct Media should be attempted
             for calls to or from endpoints in this service group. If
             enabled, the GSX will attempt to set up the media path such
             that media flows directly between two Direct-Media-enabled 
             endpoints in the same media zone."
    DEFVAL          { disabled }
    ::= { sonusGwSigServiceGroupEntry 14 }

sonusGwSigServiceGroupMediaZoneName OBJECT-TYPE
    SYNTAX          SonusNameReference
    MAX-ACCESS      read-write
    STATUS          current
    DESCRIPTION     
            "The Media Zone to which this SIP service group is bound."
    ::= { sonusGwSigServiceGroupEntry 15 }

sonusGwSigServiceGroupMediaZoneId OBJECT-TYPE
    SYNTAX          Integer32 (0..32)
    MAX-ACCESS      read-only
    STATUS          current
    DESCRIPTION     
            "Identifies the Media Zone this SIP service group is bound to."
    ::= { sonusGwSigServiceGroupEntry 16 }

sonusGwSigServiceGroupStatTable OBJECT-TYPE
    SYNTAX          SEQUENCE OF SonusGwSigServiceGroupStatEntry
    MAX-ACCESS      not-accessible
    STATUS          current
    DESCRIPTION     
            "This table contains status information about each Gateway Service
             Group in the GSX9000 Switch node."
    ::= { sonusGwSigServiceGroup 3 }

sonusGwSigServiceGroupStatEntry OBJECT-TYPE
    SYNTAX          SonusGwSigServiceGroupStatEntry
    MAX-ACCESS      not-accessible
    STATUS          current
    DESCRIPTION     
            "This table describes the status of the Gateway Service Groups."
    INDEX           { sonusGwSigServiceGroupStatListIndex }
    ::= { sonusGwSigServiceGroupStatTable 1 }

SonusGwSigServiceGroupStatEntry ::=
    SEQUENCE {
        sonusGwSigServiceGroupStatListIndex   Integer32,
        sonusGwSigServiceGroupStatStatus INTEGER
    }

sonusGwSigServiceGroupStatListIndex OBJECT-TYPE
    SYNTAX          Integer32 (1..256)
    MAX-ACCESS      read-only
    STATUS          current
    DESCRIPTION     
            "The index of the Gateway Service Group."
    ::= { sonusGwSigServiceGroupStatEntry 1 }

sonusGwSigServiceGroupStatStatus OBJECT-TYPE
    SYNTAX          INTEGER { available(1), unavailable(2), dryup(3) }
    MAX-ACCESS      read-only
    STATUS          current
    DESCRIPTION     
            "The state of the Gateway Service Group."
    ::= { sonusGwSigServiceGroupStatEntry 2 }

sonusGwSigPortPerNifStatusTable OBJECT-TYPE
    SYNTAX          SEQUENCE OF SonusGwSigPortPerNifStatusEntry
    MAX-ACCESS      not-accessible
    STATUS          current
    DESCRIPTION     
            "Table of Gateway Signalling Port Per-NIF status."
    ::= { sonusGatewaySignallingMIBObjects 8 }

sonusGwSigPortPerNifStatusEntry OBJECT-TYPE
    SYNTAX          SonusGwSigPortPerNifStatusEntry
    MAX-ACCESS      not-accessible
    STATUS          current
    DESCRIPTION     
            "Gateway Signalling Port Per-NIF Status."
    INDEX           { sonusGwSigPortPerNifStatusIndex, 
                      sonusGwSigPortPerNifStatusIfNum }
    ::= { sonusGwSigPortPerNifStatusTable 1 }

SonusGwSigPortPerNifStatusEntry ::=
    SEQUENCE {
        sonusGwSigPortPerNifStatusIndex Integer32,
        sonusGwSigPortPerNifStatusIfNum Integer32,
        sonusGwSigPortPerNifStatusNifName SonusNameReference,
        sonusGwSigPortPerNifStatusStatus INTEGER
    }

sonusGwSigPortPerNifStatusIndex OBJECT-TYPE
    SYNTAX          Integer32
    MAX-ACCESS      read-only
    STATUS          current
    DESCRIPTION     
            "Gateway signaling port index number."
    ::= { sonusGwSigPortPerNifStatusEntry 1 }

sonusGwSigPortPerNifStatusIfNum OBJECT-TYPE
    SYNTAX          Integer32
    MAX-ACCESS      read-only
    STATUS          current
    DESCRIPTION     
            "The NIF's Interface number."
    ::= { sonusGwSigPortPerNifStatusEntry 2 }

sonusGwSigPortPerNifStatusNifName OBJECT-TYPE
    SYNTAX          SonusNameReference
    MAX-ACCESS      read-only
    STATUS          current
    DESCRIPTION     
            "The NIF's name."
    ::= { sonusGwSigPortPerNifStatusEntry 3 }

sonusGwSigPortPerNifStatusStatus OBJECT-TYPE
    SYNTAX          INTEGER { unavailable(0), available(1), 
                        notApplicable(2) }
    MAX-ACCESS      read-only
    STATUS          current
    DESCRIPTION     
            "The availability status of the local address allocated
             to the NIF of the NIF group bound to this signaling port."
    ::= { sonusGwSigPortPerNifStatusEntry 4 }

sonusGatewaySignallingMIBNotifications OBJECT IDENTIFIER
    ::= { sonusGatewaySignallingMIB 2 }

sonusGatewaySignallingMIBNotificationsPrefix OBJECT IDENTIFIER
    ::= { sonusGatewaySignallingMIBNotifications 0 }

sonusGatewaySignallingMIBNotificationsObjects OBJECT IDENTIFIER
    ::= { sonusGatewaySignallingMIBNotifications 1 }

sonusGwRemoteGwName OBJECT-TYPE
    SYNTAX          DisplayString (SIZE(0..23))
    MAX-ACCESS      read-only
    STATUS          deprecated
    DESCRIPTION     
            "Name of the remote Gateway."
    ::= { sonusGatewaySignallingMIBNotificationsObjects 1 }

sonusGwCloseReasonCode OBJECT-TYPE
    SYNTAX          INTEGER { administratorInitiatedClose(1), 
                        closeRequestReceivedFromRemote(2), 
                        remoteNotResponding(3), internalError(4), 
                        configError(5), recvCallSigReqFromUnknownGw(6), 
                        socketErrNetworkDown(7), 
                        socketErrNetworkUnreachable(8), 
                        socketErrNetworkReset(9), 
                        socketErrSoftwareConnectionAbort(10), 
                        socketErrConnectionResetByPeer(11), 
                        socketErrNoBufferSpaceAvail(12), 
                        socketErrAlreadyConnected(13), 
                        socketErrNotConnected(14), 
                        socketErrCantSendAfterShutdown(15), 
                        socketErrTooManyReferences(16), 
                        socketErrConnectionTimedOut(17), 
                        socketErrUnknown(18), 
                        recvDuplicateLinkOpenReq(19), 
                        socketErrExceptionEvent(20), 
                        linkXmtCongestion(21), 
                        openNackReceivedFromRemote(22), idleTimeout(23) }
    MAX-ACCESS      read-only
    STATUS          current
    DESCRIPTION     
            "Reason for close of Call Signaling Link."
    ::= { sonusGatewaySignallingMIBNotificationsObjects 2 }

sonusGwRemoteGwAddr OBJECT-TYPE
    SYNTAX          IpAddress
    MAX-ACCESS      read-only
    STATUS          current
    DESCRIPTION     
            "Ip Address of the remote Gateway."
    ::= { sonusGatewaySignallingMIBNotificationsObjects 3 }

sonusGwSigSvcGrpName OBJECT-TYPE
    SYNTAX          SonusNameReference
    MAX-ACCESS      read-only
    STATUS          current
    DESCRIPTION     
            "Name of the Gateway service group."
    ::= { sonusGatewaySignallingMIBNotificationsObjects 4 }

sonusGwRemoteGw6Addr OBJECT-TYPE
    SYNTAX          Ipv6Address
    MAX-ACCESS      read-only
    STATUS          current
    DESCRIPTION     
            "Ipv6 Address of the remote Gateway."
    ::= { sonusGatewaySignallingMIBNotificationsObjects 12 }

sonusGwCallSigChanOpenNotification NOTIFICATION-TYPE
    OBJECTS         { sonusGwRemoteGwName, sonusEventDescription, 
                      sonusEventClass, sonusEventLevel }
    STATUS          deprecated
    DESCRIPTION     
            "This trap indicates that a Call Signalling channel to a Remote Gateway has been opened.
             This trap has been replaced with sonusGwSigChanOpenNotification."
    ::= { sonusGatewaySignallingMIBNotificationsPrefix 1 }

sonusGwCallSigChanCloseNotification NOTIFICATION-TYPE
    OBJECTS         { sonusGwRemoteGwName, sonusGwCloseReasonCode, 
                      sonusEventDescription, sonusEventClass, 
                      sonusEventLevel }
    STATUS          deprecated
    DESCRIPTION     
            "This trap indicates that a Call Signaling channel to a Remote Gateway has been closed.
             This trap has been replaced with sonusGwSigChanCloseNotification."
    ::= { sonusGatewaySignallingMIBNotificationsPrefix 2 }

sonusGwSigChanOpenNotification NOTIFICATION-TYPE
    OBJECTS         { sonusGwRemoteGwAddr, sonusEventDescription, 
                      sonusEventClass, sonusEventLevel, sonusSequenceId, 
                      sonusEventTime }
    STATUS          current
    DESCRIPTION     
            "This trap indicates that a Call Signaling Link to a Remote Gateway has been sucessfully opened."
    ::= { sonusGatewaySignallingMIBNotificationsPrefix 3 }

sonusGwSigChanCloseNotification NOTIFICATION-TYPE
    OBJECTS         { sonusGwRemoteGwAddr, sonusGwCloseReasonCode, 
                      sonusEventDescription, sonusEventClass, 
                      sonusEventLevel, sonusSequenceId, sonusEventTime }
    STATUS          current
    DESCRIPTION     
            "This trap indicates that a Call Signaling Link to a Remote Gateway has been closed."
    ::= { sonusGatewaySignallingMIBNotificationsPrefix 4 }

sonusGwSigChanOpenAttemptNotification NOTIFICATION-TYPE
    OBJECTS         { sonusGwRemoteGwAddr, sonusEventDescription, 
                      sonusEventClass, sonusEventLevel, sonusSequenceId, 
                      sonusEventTime }
    STATUS          current
    DESCRIPTION     
            "This trap indicates that a request to Open a Call Signaling Link has been sent to a Remote Gateway."
    ::= { sonusGatewaySignallingMIBNotificationsPrefix 5 }

sonusGwSigChanRetryTimerExpiredNotification NOTIFICATION-TYPE
    OBJECTS         { sonusGwRemoteGwAddr, sonusEventDescription, 
                      sonusEventClass, sonusEventLevel, sonusSequenceId, 
                      sonusEventTime }
    STATUS          current
    DESCRIPTION     
            "This trap indicates that attempts to recover a Call Signaling Link to a Remote GW have failed."
    ::= { sonusGatewaySignallingMIBNotificationsPrefix 6 }

sonusGwSigSvcGrpInServiceNotification NOTIFICATION-TYPE
    OBJECTS         { sonusGwSigSvcGrpName, sonusEventDescription, 
                      sonusEventClass, sonusEventLevel, sonusSequenceId, 
                      sonusEventTime }
    STATUS          current
    DESCRIPTION     
            "This trap indicates that the Gateway Service Group was put
             into service by maintenance staff."
    ::= { sonusGatewaySignallingMIBNotificationsPrefix 7 }

sonusGwSigSvcGrpOutOfServiceNotification NOTIFICATION-TYPE
    OBJECTS         { sonusGwSigSvcGrpName, sonusEventDescription, 
                      sonusEventClass, sonusEventLevel, sonusSequenceId, 
                      sonusEventTime }
    STATUS          current
    DESCRIPTION     
            "This trap indicates that the Gateway Service Group was taken
             out of service by maintenance staff."
    ::= { sonusGatewaySignallingMIBNotificationsPrefix 8 }

sonusGwSigChanOpenNotificationV6 NOTIFICATION-TYPE
    OBJECTS         { sonusGwRemoteGw6Addr, sonusEventDescription, 
                      sonusEventClass, sonusEventLevel, sonusSequenceId, 
                      sonusEventTime }
    STATUS          current
    DESCRIPTION     
            "This trap indicates that a Call Signaling Link to a Remote Gateway has been sucessfully opened."
    ::= { sonusGatewaySignallingMIBNotificationsPrefix 9 }

sonusGwSigChanCloseNotificationV6 NOTIFICATION-TYPE
    OBJECTS         { sonusGwRemoteGw6Addr, sonusGwCloseReasonCode, 
                      sonusEventDescription, sonusEventClass, 
                      sonusEventLevel, sonusSequenceId, sonusEventTime }
    STATUS          current
    DESCRIPTION     
            "This trap indicates that a Call Signaling Link to a Remote Gateway has been closed."
    ::= { sonusGatewaySignallingMIBNotificationsPrefix 10 }

sonusGwSigChanOpenAttemptNotificationV6 NOTIFICATION-TYPE
    OBJECTS         { sonusGwRemoteGw6Addr, sonusEventDescription, 
                      sonusEventClass, sonusEventLevel, sonusSequenceId, 
                      sonusEventTime }
    STATUS          current
    DESCRIPTION     
            "This trap indicates that a request to Open a Call Signaling Link has been sent to a Remote Gateway."
    ::= { sonusGatewaySignallingMIBNotificationsPrefix 11 }

sonusGwSigChanRetryTimerExpiredNotificationV6 NOTIFICATION-TYPE
    OBJECTS         { sonusGwRemoteGw6Addr, sonusEventDescription, 
                      sonusEventClass, sonusEventLevel, sonusSequenceId, 
                      sonusEventTime }
    STATUS          current
    DESCRIPTION     
            "This trap indicates that attempts to recover a Call Signaling Link to a Remote GW have failed."
    ::= { sonusGatewaySignallingMIBNotificationsPrefix 12 }

END -- end of module SONUS-GATEWAY-SIGNALLING-MIB.
