--
-- This SMIv2 module has been generated by smidump 0.2-cvs. Do not edit.
--

SONUS-DIFFSERV-MIB DEFINITIONS ::= BEGIN

IMPORTS
    Integer32, MODULE-IDENTITY, OBJECT-TYPE
        FROM SNMPv2-SMI
    RowStatus
        FROM SNMPv2-TC
    sonusPacketMIBs
        FROM SONUS-SMI;

sonusDiffServMIB MODULE-IDENTITY
    LAST-UPDATED    "200703280000Z"
    ORGANIZATION    
            "Sonus Networks, Inc."
    CONTACT-INFO    
            "   Customer Support    
             Sonus Networks, Inc.
             7 Technology Park Drive
             Westford, MA 01886
             USA
             
             Tel: 978-614-8100
             Fax: 978-614-8609"
    DESCRIPTION     
            "The MIB Module for DiffServ management."
    ::= { sonusPacketMIBs 7 }


sonusDiffServMIBObjects OBJECT IDENTIFIER
    ::= { sonusDiffServMIB 1 }

sonusDiffServTable OBJECT-TYPE
    SYNTAX          SEQUENCE OF SonusDiffServEntry
    MAX-ACCESS      not-accessible
    STATUS          current
    DESCRIPTION     
            "The table of diff-serv dscp marks to apply based on
             a give filter table match."
    ::= { sonusDiffServMIBObjects 1 }

sonusDiffServEntry OBJECT-TYPE
    SYNTAX          SonusDiffServEntry
    MAX-ACCESS      not-accessible
    STATUS          current
    DESCRIPTION     
            "A mapping for a given filter, when matched, to dscp value."
    INDEX           { sonusDiffServIndex }
    ::= { sonusDiffServTable 1 }

SonusDiffServEntry ::=
    SEQUENCE {
        sonusDiffServIndex              Integer32,
        sonusDiffServDscp               Integer32,
        sonusDiffServRowStatus          RowStatus
    }

sonusDiffServIndex OBJECT-TYPE
    SYNTAX          Integer32
    MAX-ACCESS      read-only
    STATUS          current
    DESCRIPTION     
            "Integer index for entry corresponding to a filter entry.
             The value must correspond to an existing sonusFilterIndex."
    ::= { sonusDiffServEntry 1 }

sonusDiffServDscp OBJECT-TYPE
    SYNTAX          Integer32 (0..63)
    MAX-ACCESS      read-write
    STATUS          current
    DESCRIPTION     
            "Integer index for entry; one for one with sonusFilterName."
    DEFVAL          { 0 }
    ::= { sonusDiffServEntry 2 }

sonusDiffServRowStatus OBJECT-TYPE
    SYNTAX          RowStatus
    MAX-ACCESS      read-write
    STATUS          current
    DESCRIPTION     
            ""
    ::= { sonusDiffServEntry 3 }

END -- end of module SONUS-DIFFSERV-MIB.
