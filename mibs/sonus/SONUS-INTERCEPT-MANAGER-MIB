--
-- This SMIv2 module has been generated by smidump 0.2-cvs. Do not edit.
--

SONUS-INTERCEPT-MANAGER-MIB DEFINITIONS ::= BEGIN

IMPORTS
    Ipv6Address
        FROM IPV6-TC
    Counter32, Integer32, IpAddress, MODULE-IDENTITY, NOTIFICATION-TYPE, 
    OBJECT-TYPE, Unsigned32
        FROM SNMPv2-SMI
    DisplayString, RowStatus
        FROM SNMPv2-TC
    sonusEventClass, sonusEventDescription, sonusEventLevel, 
    sonusEventTime, sonusSequenceId
        FROM SONUS-COMMON-MIB
    sonusServicesMIBs
        FROM SONUS-SMI
    SonusName, SonusNameReference
        FROM SONUS-TC;

sonusInterceptManagerMIB MODULE-IDENTITY
    LAST-UPDATED    "201209130000Z"
    ORGANIZATION    
            "Sonus Networks, Inc."
    CONTACT-INFO    
            "   Customer Support    
             Sonus Networks, Inc,
             5 carlisle Road
             Westford, MA 01886
             USA
             
             Tel: 978-692-8999
             Fax: 978-392-9118
             E-mail: cs.snmp@sonusnet.com"
    DESCRIPTION     
            "The MIB Module for the Intercept Manager."
    ::= { sonusServicesMIBs 28 }


sonusInterceptManagerMIBObjects OBJECT IDENTIFIER
    ::= { sonusInterceptManagerMIB 1 }

sonusImAdmnNodeNumber OBJECT-TYPE
    SYNTAX          DisplayString (SIZE(1..5))
    MAX-ACCESS      read-write
    STATUS          current
    DESCRIPTION     
            "The node number that will be used to identify this GSX in all call data
             messages sent to the Intercept Server.  It must be unique within a 
             carrier's network."
    ::= { sonusInterceptManagerMIBObjects 1 }

sonusImAdmnTableNextIndex OBJECT-TYPE
    SYNTAX          Integer32
    MAX-ACCESS      read-only
    STATUS          current
    DESCRIPTION     
            "The next valid index to use when creating a new sonusImAdmnEntry"
    ::= { sonusInterceptManagerMIBObjects 2 }

sonusImAdmnTable OBJECT-TYPE
    SYNTAX          SEQUENCE OF SonusImAdmnEntry
    MAX-ACCESS      not-accessible
    STATUS          current
    DESCRIPTION     
            "A list of Intercept Manager entries."
    ::= { sonusInterceptManagerMIBObjects 3 }

sonusImAdmnEntry OBJECT-TYPE
    SYNTAX          SonusImAdmnEntry
    MAX-ACCESS      not-accessible
    STATUS          current
    DESCRIPTION     
            "Each sonusImAdmnEntry containing configuration objects.
             Rules & Behaviors:
                  A sonusImAdmnEntry cannot be modified when it is  enabled."
    INDEX           { sonusImAdmnIndex }
    ::= { sonusImAdmnTable 1 }

SonusImAdmnEntry ::=
    SEQUENCE {
        sonusImAdmnIndex                Unsigned32,
        sonusImAdmnName                 SonusName,
        sonusImAdmnPriState             INTEGER,
        sonusImAdmnPriIpaddr            IpAddress,
        sonusImAdmnUdpPort              Unsigned32,
        sonusImAdmnPriMode              INTEGER,
        sonusImAdmnSecState             INTEGER,
        sonusImAdmnSecIpaddr            IpAddress,
        sonusImAdmnSecMode              INTEGER,
        sonusImAdmnKeepAliveTimer       Unsigned32,
        sonusImAdmnRetries              Unsigned32,
        sonusImAdmnRowStatus            RowStatus,
        sonusImAdmnNifGroupName         SonusNameReference,
        sonusImAdmnPriIp6addr           Ipv6Address,
        sonusImAdmnSecIp6addr           Ipv6Address,
        sonusImAdmnPriIpVersion         INTEGER,
        sonusImAdmnSecIpVersion         INTEGER,
        sonusImAdmnNoaParamSupport      INTEGER,
        sonusImAdmnServerType           INTEGER
    }

sonusImAdmnIndex OBJECT-TYPE
    SYNTAX          Unsigned32
    MAX-ACCESS      read-only
    STATUS          current
    DESCRIPTION     
            "A unique value for each Intercept Manager that is between 1
             and maximum allowed"
    ::= { sonusImAdmnEntry 1 }

sonusImAdmnName OBJECT-TYPE
    SYNTAX          SonusName
    MAX-ACCESS      read-write
    STATUS          current
    DESCRIPTION     
            "The name of this Intercept Manager instance."
    ::= { sonusImAdmnEntry 2 }

sonusImAdmnPriState OBJECT-TYPE
    SYNTAX          INTEGER { disabled(1), enabled(2) }
    MAX-ACCESS      read-write
    STATUS          current
    DESCRIPTION     
            "The administrative state of the call data channel to the primary Intercept Server."
    DEFVAL          { disabled }
    ::= { sonusImAdmnEntry 3 }

sonusImAdmnPriIpaddr OBJECT-TYPE
    SYNTAX          IpAddress
    MAX-ACCESS      read-write
    STATUS          current
    DESCRIPTION     
            "Specifies the IP Address of the primary call data channel to the Intercept Server platform."
    ::= { sonusImAdmnEntry 4 }

sonusImAdmnUdpPort OBJECT-TYPE
    SYNTAX          Unsigned32 (1..65535)
    MAX-ACCESS      read-write
    STATUS          current
    DESCRIPTION     
            "UDP port for the primary and secondary call data channel to the Intercept Server platform."
    ::= { sonusImAdmnEntry 5 }

sonusImAdmnPriMode OBJECT-TYPE
    SYNTAX          INTEGER { active(1), standby(2), outOfService(3) }
    MAX-ACCESS      read-write
    STATUS          current
    DESCRIPTION     
            "Specifies the service mode of the primary call data channel to the Intercept Server platform."
    DEFVAL          { outOfService }
    ::= { sonusImAdmnEntry 6 }

sonusImAdmnSecState OBJECT-TYPE
    SYNTAX          INTEGER { disabled(1), enabled(2) }
    MAX-ACCESS      read-write
    STATUS          current
    DESCRIPTION     
            "The administrative state of the call data channel to the secondary Intercept Server."
    DEFVAL          { disabled }
    ::= { sonusImAdmnEntry 7 }

sonusImAdmnSecIpaddr OBJECT-TYPE
    SYNTAX          IpAddress
    MAX-ACCESS      read-write
    STATUS          current
    DESCRIPTION     
            "Specifies the IP Address of the primary call data channel to the Intercept Server platform."
    ::= { sonusImAdmnEntry 8 }

sonusImAdmnSecMode OBJECT-TYPE
    SYNTAX          INTEGER { active(1), standby(2), outOfService(3) }
    MAX-ACCESS      read-write
    STATUS          current
    DESCRIPTION     
            "Specifies the service mode of the secondary call data channel to the Intercept Server platform."
    DEFVAL          { outOfService }
    ::= { sonusImAdmnEntry 9 }

sonusImAdmnKeepAliveTimer OBJECT-TYPE
    SYNTAX          Unsigned32 (0..60)
    MAX-ACCESS      read-write
    STATUS          current
    DESCRIPTION     
            "The value in seconds of the keep alive timer for the active call data channel."
    DEFVAL          { 5 }
    ::= { sonusImAdmnEntry 10 }

sonusImAdmnRetries OBJECT-TYPE
    SYNTAX          Unsigned32 (1..10)
    MAX-ACCESS      read-write
    STATUS          current
    DESCRIPTION     
            "The number of retries that will be attempted when a call data channel message is lost."
    DEFVAL          { 3 }
    ::= { sonusImAdmnEntry 11 }

sonusImAdmnRowStatus OBJECT-TYPE
    SYNTAX          RowStatus
    MAX-ACCESS      read-write
    STATUS          current
    DESCRIPTION     
            "This object is used to create a new row or modify or delete an  existing row in this table."
    ::= { sonusImAdmnEntry 12 }

sonusImAdmnNifGroupName OBJECT-TYPE
    SYNTAX          SonusNameReference
    MAX-ACCESS      read-write
    STATUS          current
    DESCRIPTION     
            "The NIF group which this call data channel belongs to."
    ::= { sonusImAdmnEntry 13 }

sonusImAdmnPriIp6addr OBJECT-TYPE
    SYNTAX          Ipv6Address
    MAX-ACCESS      read-write
    STATUS          current
    DESCRIPTION     
            "Specifies the IPV6 Address of the primary call data channel to the Intercept Server platform."
    ::= { sonusImAdmnEntry 14 }

sonusImAdmnSecIp6addr OBJECT-TYPE
    SYNTAX          Ipv6Address
    MAX-ACCESS      read-write
    STATUS          current
    DESCRIPTION     
            "Specifies the IPV6 Address of the primary call data channel to the Intercept Server platform."
    ::= { sonusImAdmnEntry 15 }

sonusImAdmnPriIpVersion OBJECT-TYPE
    SYNTAX          INTEGER { afInet(2), afInet6(24) }
    MAX-ACCESS      read-only
    STATUS          current
    DESCRIPTION     
            "The Im Admn Pri IP version."
    ::= { sonusImAdmnEntry 16 }

sonusImAdmnSecIpVersion OBJECT-TYPE
    SYNTAX          INTEGER { afInet(2), afInet6(24) }
    MAX-ACCESS      read-only
    STATUS          current
    DESCRIPTION     
            "The Im Admn Sec IP version."
    ::= { sonusImAdmnEntry 17 }

sonusImAdmnNoaParamSupport OBJECT-TYPE
    SYNTAX          INTEGER { disabled(1), enabled(2) }
    MAX-ACCESS      read-write
    STATUS          current
    DESCRIPTION     
            "This flag will determine if the NOA parameter will be sent in LI messages or not. "
    DEFVAL          { disabled }
    ::= { sonusImAdmnEntry 18 }

sonusImAdmnServerType OBJECT-TYPE
    SYNTAX          INTEGER { default(0), zeel(1) }
    MAX-ACCESS      read-write
    STATUS          current
    DESCRIPTION     
            "The server type being used for this Intercept Server, currently support for DEFAULT or ZEEL."
    DEFVAL          { default }
    ::= { sonusImAdmnEntry 19 }

sonusImStatusTable OBJECT-TYPE
    SYNTAX          SEQUENCE OF SonusImStatusEntry
    MAX-ACCESS      not-accessible
    STATUS          current
    DESCRIPTION     
            "Status Table of the intercept server"
    ::= { sonusInterceptManagerMIBObjects 4 }

sonusImStatusEntry OBJECT-TYPE
    SYNTAX          SonusImStatusEntry
    MAX-ACCESS      not-accessible
    STATUS          current
    DESCRIPTION     
            "Each entry describes the current status of a intercept manager entry."
    INDEX           { sonusImStatusIndex }
    ::= { sonusImStatusTable 1 }

SonusImStatusEntry ::=
    SEQUENCE {
        sonusImStatusIndex              Unsigned32,
        sonusImStatusPriOperState       INTEGER,
        sonusImStatusSecOperState       INTEGER,
        sonusImStatusSignalStartSuccess Counter32,
        sonusImStatusSignalStartUnsuccess Counter32,
        sonusImStatusCallAnswerSuccess  Counter32,
        sonusImStatusCallAnswerUnsuccess Counter32,
        sonusImStatusCallDisconnectSuccess  Counter32,
        sonusImStatusCallDisconnectUnsuccess    Counter32,
        sonusImStatusMediaReportSuccess Counter32,
        sonusImStatusMediaReportUnsuccess Counter32,
        sonusImStatusServiceInstanceSuccess   Counter32,
        sonusImStatusServiceInstanceUnsuccess     Counter32,
        sonusImStatusSignalInstanceSuccess  Counter32,
        sonusImStatusSignalInstanceUnsuccess    Counter32,
        sonusImStatusIndicationSuccess  Counter32,
        sonusImStatusIndicationUnsuccess Counter32,
        sonusImStatusKeepAliveSuccess   Counter32,
        sonusImStatusKeepAliveUnsuccess Counter32,
        sonusImStatusRestartSuccess     Counter32,
        sonusImStatusRestartUnsuccess   Counter32,
        sonusImStatusRadiusAckReceived  Counter32,
        sonusImStatusRadiusUnknownMsgReceived     Counter32,
        sonusImStatusSignalStartResponseReceived        Counter32,
        sonusImStatusSignalStopSuccess  Counter32,
        sonusImStatusSignalStopUnsuccess Counter32
    }

sonusImStatusIndex OBJECT-TYPE
    SYNTAX          Unsigned32
    MAX-ACCESS      read-only
    STATUS          current
    DESCRIPTION     
            "A unique value for each intercept manager entry between 1 and maximum 
             allowed."
    ::= { sonusImStatusEntry 1 }

sonusImStatusPriOperState OBJECT-TYPE
    SYNTAX          INTEGER { inService(1), outOfService(2), standBy(3) }
    MAX-ACCESS      read-only
    STATUS          current
    DESCRIPTION     
            " Current operational state of the primary call data channel."
    ::= { sonusImStatusEntry 2 }

sonusImStatusSecOperState OBJECT-TYPE
    SYNTAX          INTEGER { inService(1), outOfService(2), standBy(3) }
    MAX-ACCESS      read-only
    STATUS          current
    DESCRIPTION     
            " Current operational state of the Secondary call data channel."
    ::= { sonusImStatusEntry 3 }

sonusImStatusSignalStartSuccess OBJECT-TYPE
    SYNTAX          Counter32
    MAX-ACCESS      read-only
    STATUS          current
    DESCRIPTION     
            " The number of successful Signal Start messages sent on the active call data channel."
    ::= { sonusImStatusEntry 4 }

sonusImStatusSignalStartUnsuccess OBJECT-TYPE
    SYNTAX          Counter32
    MAX-ACCESS      read-only
    STATUS          current
    DESCRIPTION     
            " The number of unsuccessful Signal Start messages sent on the active call data channel."
    ::= { sonusImStatusEntry 5 }

sonusImStatusCallAnswerSuccess OBJECT-TYPE
    SYNTAX          Counter32
    MAX-ACCESS      read-only
    STATUS          current
    DESCRIPTION     
            " The number of successful Call Answer messages sent on the active call data channel."
    ::= { sonusImStatusEntry 6 }

sonusImStatusCallAnswerUnsuccess OBJECT-TYPE
    SYNTAX          Counter32
    MAX-ACCESS      read-only
    STATUS          current
    DESCRIPTION     
            " The number of unsuccessful Call Answer messages sent on the active call data channel."
    ::= { sonusImStatusEntry 7 }

sonusImStatusCallDisconnectSuccess OBJECT-TYPE
    SYNTAX          Counter32
    MAX-ACCESS      read-only
    STATUS          current
    DESCRIPTION     
            " The number of successful Call Disconnect messages sent on the active call data channel."
    ::= { sonusImStatusEntry 8 }

sonusImStatusCallDisconnectUnsuccess OBJECT-TYPE
    SYNTAX          Counter32
    MAX-ACCESS      read-only
    STATUS          current
    DESCRIPTION     
            " The number of unsuccessful Call Disconnect messages sent on the active call data channel."
    ::= { sonusImStatusEntry 9 }

sonusImStatusMediaReportSuccess OBJECT-TYPE
    SYNTAX          Counter32
    MAX-ACCESS      read-only
    STATUS          current
    DESCRIPTION     
            " The number of successful Media Report messages sent on the active call data channel."
    ::= { sonusImStatusEntry 10 }

sonusImStatusMediaReportUnsuccess OBJECT-TYPE
    SYNTAX          Counter32
    MAX-ACCESS      read-only
    STATUS          current
    DESCRIPTION     
            " The number of unsuccessful Media Report messages sent on the active call data channel."
    ::= { sonusImStatusEntry 11 }

sonusImStatusServiceInstanceSuccess OBJECT-TYPE
    SYNTAX          Counter32
    MAX-ACCESS      read-only
    STATUS          current
    DESCRIPTION     
            " The number of successful Service Instance messages sent on the active call data channel."
    ::= { sonusImStatusEntry 12 }

sonusImStatusServiceInstanceUnsuccess OBJECT-TYPE
    SYNTAX          Counter32
    MAX-ACCESS      read-only
    STATUS          current
    DESCRIPTION     
            " The number of unsuccessful Service Instance messages sent on the active call data channel."
    ::= { sonusImStatusEntry 13 }

sonusImStatusSignalInstanceSuccess OBJECT-TYPE
    SYNTAX          Counter32
    MAX-ACCESS      read-only
    STATUS          current
    DESCRIPTION     
            " The number of successful Signal Instance messages sent on the active call data channel."
    ::= { sonusImStatusEntry 14 }

sonusImStatusSignalInstanceUnsuccess OBJECT-TYPE
    SYNTAX          Counter32
    MAX-ACCESS      read-only
    STATUS          current
    DESCRIPTION     
            " The number of unsuccessful Signal Instance messages sent on the active call data channel."
    ::= { sonusImStatusEntry 15 }

sonusImStatusIndicationSuccess OBJECT-TYPE
    SYNTAX          Counter32
    MAX-ACCESS      read-only
    STATUS          current
    DESCRIPTION     
            " The number of successful Indication messages sent on the active call data channel."
    ::= { sonusImStatusEntry 16 }

sonusImStatusIndicationUnsuccess OBJECT-TYPE
    SYNTAX          Counter32
    MAX-ACCESS      read-only
    STATUS          current
    DESCRIPTION     
            " The number of unsuccessful Indication messages sent on the active call data channel."
    ::= { sonusImStatusEntry 17 }

sonusImStatusKeepAliveSuccess OBJECT-TYPE
    SYNTAX          Counter32
    MAX-ACCESS      read-only
    STATUS          current
    DESCRIPTION     
            " The number of successful Keep Alive messages sent on the active call data channel."
    ::= { sonusImStatusEntry 18 }

sonusImStatusKeepAliveUnsuccess OBJECT-TYPE
    SYNTAX          Counter32
    MAX-ACCESS      read-only
    STATUS          current
    DESCRIPTION     
            " The number of unsuccessful Keep Alive messages sent on the active call data channel."
    ::= { sonusImStatusEntry 19 }

sonusImStatusRestartSuccess OBJECT-TYPE
    SYNTAX          Counter32
    MAX-ACCESS      read-only
    STATUS          current
    DESCRIPTION     
            " The number of successful Restart messages sent on the active call data channel."
    ::= { sonusImStatusEntry 20 }

sonusImStatusRestartUnsuccess OBJECT-TYPE
    SYNTAX          Counter32
    MAX-ACCESS      read-only
    STATUS          current
    DESCRIPTION     
            " The number of unsuccessful Restart messages sent on the active call data channel."
    ::= { sonusImStatusEntry 21 }

sonusImStatusRadiusAckReceived OBJECT-TYPE
    SYNTAX          Counter32
    MAX-ACCESS      read-only
    STATUS          current
    DESCRIPTION     
            " The number of Radius Acknowledgement messages received on the active call data channel."
    ::= { sonusImStatusEntry 22 }

sonusImStatusRadiusUnknownMsgReceived OBJECT-TYPE
    SYNTAX          Counter32
    MAX-ACCESS      read-only
    STATUS          current
    DESCRIPTION     
            " The number of messages received with an unknown Radius message code on the active call data channel."
    ::= { sonusImStatusEntry 23 }

sonusImStatusSignalStartResponseReceived OBJECT-TYPE
    SYNTAX          Counter32
    MAX-ACCESS      read-only
    STATUS          current
    DESCRIPTION     
            " The number of Signaling Start Response messages received on the active call data channel."
    ::= { sonusImStatusEntry 24 }

sonusImStatusSignalStopSuccess OBJECT-TYPE
    SYNTAX          Counter32
    MAX-ACCESS      read-only
    STATUS          current
    DESCRIPTION     
            " The number of successful Signal Stop messages sent on the active call data channel."
    ::= { sonusImStatusEntry 25 }

sonusImStatusSignalStopUnsuccess OBJECT-TYPE
    SYNTAX          Counter32
    MAX-ACCESS      read-only
    STATUS          current
    DESCRIPTION     
            " The number of unsuccessful Signal Stop messages sent on the active call data channel."
    ::= { sonusImStatusEntry 26 }

sonusInterceptManagerMIBNotifications OBJECT IDENTIFIER
    ::= { sonusInterceptManagerMIB 2 }

sonusInterceptManagerMIBNotificationsPrefix OBJECT IDENTIFIER
    ::= { sonusInterceptManagerMIBNotifications 0 }

sonusInterceptManagerMIBNotificationsObjects OBJECT IDENTIFIER
    ::= { sonusInterceptManagerMIBNotifications 1 }

sonusImPriOperStateChange NOTIFICATION-TYPE
    OBJECTS         { sonusImAdmnName, sonusImStatusPriOperState, 
                      sonusEventDescription, sonusEventClass, 
                      sonusEventLevel, sonusSequenceId, sonusEventTime }
    STATUS          current
    DESCRIPTION     
            "This trap indicates the intercept manager primary operational state has changed."
    ::= { sonusInterceptManagerMIBNotificationsPrefix 1 }

sonusImSecOperStateChange NOTIFICATION-TYPE
    OBJECTS         { sonusImAdmnName, sonusImStatusSecOperState, 
                      sonusEventDescription, sonusEventClass, 
                      sonusEventLevel, sonusSequenceId, sonusEventTime }
    STATUS          current
    DESCRIPTION     
            "This trap indicates the intercept manager secondary operational state has changed."
    ::= { sonusInterceptManagerMIBNotificationsPrefix 2 }

END -- end of module SONUS-INTERCEPT-MANAGER-MIB.
