--
-- This SMIv2 module has been generated by smidump 0.2-cvs. Do not edit.
--

SONUS-EVENT-LOG-MIB DEFINITIONS ::= BEGIN

IMPORTS
    Integer32, MODULE-IDENTITY, NOTIFICATION-TYPE, OBJECT-TYPE, 
    Unsigned32
        FROM SNMPv2-SMI
    DateAndTime, DisplayString
        FROM SNMPv2-TC
    sonusEventClass, sonusEventDescription, sonusEventLevel, 
    sonusEventTime, sonusSequenceId, sonusShelfIndex
        FROM SONUS-COMMON-MIB
    sonusNfsServerIp, sonusNfsServerIpAddrV6, sonusNfsServerMount
        FROM SONUS-NODE-MIB
    sonusSystemMIBs
        FROM SONUS-SMI
    SonusAdminState, SonusEventClass, SonusEventFilterLevel, 
    SonusEventString, SonusShelfIndex, SonusSlotIndex, SonusSysId
        FROM SONUS-TC;

sonusEventLogMIB MODULE-IDENTITY
    LAST-UPDATED    "201108190000Z"
    ORGANIZATION    
            "Sonus Networks, Inc."
    CONTACT-INFO    
            "   Customer Support    
             Sonus Networks, Inc.
             7 Technology Park Drive
             Westford, MA 01886
             USA
             
             Tel: 978-614-8100
             Fax: 978-614-8609"
    DESCRIPTION     
            "The MIB Module for Event Log Management."
    ::= { sonusSystemMIBs 2 }


sonusEventLogMIBObjects OBJECT IDENTIFIER
    ::= { sonusEventLogMIB 1 }

sonusEvLogTypeTable OBJECT-TYPE
    SYNTAX          SEQUENCE OF SonusEvLogTypeEntry
    MAX-ACCESS      not-accessible
    STATUS          current
    DESCRIPTION     
            "Event Log configuration table for configuration items
             related to each Event Log type."
    ::= { sonusEventLogMIBObjects 1 }

sonusEvLogTypeEntry OBJECT-TYPE
    SYNTAX          SonusEvLogTypeEntry
    MAX-ACCESS      not-accessible
    STATUS          current
    DESCRIPTION     
            "An entry of Event Log configuration related to each
             event log type."
    INDEX           { sonusEvLogType }
    ::= { sonusEvLogTypeTable 1 }

SonusEvLogTypeEntry ::=
    SEQUENCE {
        sonusEvLogType                  INTEGER,
        sonusEvLogTypeAdminState        INTEGER,
        sonusEvLogTypeFileCount         Integer32,
        sonusEvLogTypeFileSize          Integer32,
        sonusEvLogTypeFileMsgQueue      Integer32,
        sonusEvLogTypeBaseDirectory     DisplayString,
        sonusEvLogTypeSaveTo            INTEGER,
        sonusEvLogTypeMaxEventMemSize   Integer32,
        sonusEvLogTypeFilterLevel       SonusEventFilterLevel,
        sonusEvLogTypeRolloverStartTime Integer32,
        sonusEvLogTypeRolloverInterval  Integer32,
        sonusEvLogTypeRolloverType      INTEGER,
        sonusEvLogTypeRolloverAction    INTEGER,
        sonusEvLogTypeDisk              INTEGER,
        sonusEvLogTypeFileWriteMode     INTEGER
    }

sonusEvLogType OBJECT-TYPE
    SYNTAX          INTEGER { system(1), debug(2), trace(3), acct(4), 
                        cli(6) }
    MAX-ACCESS      read-only
    STATUS          current
    DESCRIPTION     
            "The type of the event log.  Each type has separate
             configuration parameters and logs to a separate file."
    ::= { sonusEvLogTypeEntry 1 }

sonusEvLogTypeAdminState OBJECT-TYPE
    SYNTAX          INTEGER { disabled(1), enabled(2), rollfile(3) }
    MAX-ACCESS      read-write
    STATUS          current
    DESCRIPTION     
            "The requested state of the given Event Log type."
    DEFVAL          { enabled }
    ::= { sonusEvLogTypeEntry 2 }

sonusEvLogTypeFileCount OBJECT-TYPE
    SYNTAX          Integer32 (1..1000)
    MAX-ACCESS      read-write
    STATUS          current
    DESCRIPTION     
            "The number of event log files that will be maintained
             for this event type.  All event types except accounting
             will overwrite the oldest file when the file count is
             exceeded.  Accounting will issue warnings as the file
             count approaches the maximum and shutdown if it is exceeded."
    DEFVAL          { 32 }
    ::= { sonusEvLogTypeEntry 3 }

sonusEvLogTypeFileSize OBJECT-TYPE
    SYNTAX          Integer32 (256..65535)
    MAX-ACCESS      read-write
    STATUS          current
    DESCRIPTION     
            "The maximum size (in KB) that a single event log
             file will ever grow to."
    DEFVAL          { 2048 }
    ::= { sonusEvLogTypeEntry 4 }

sonusEvLogTypeFileMsgQueue OBJECT-TYPE
    SYNTAX          Integer32 (2..32)
    MAX-ACCESS      read-write
    STATUS          current
    DESCRIPTION     
            "The number of event log message entries to buffer
             before writing them to disk.
             
             The size may be a value between 2 and 32 (inclusive)."
    DEFVAL          { 10 }
    ::= { sonusEvLogTypeEntry 5 }

sonusEvLogTypeBaseDirectory OBJECT-TYPE
    SYNTAX          DisplayString
    MAX-ACCESS      read-only
    STATUS          current
    DESCRIPTION     
            "The directory in which to place the event log files.
             Each event log type has its own base directory"
    ::= { sonusEvLogTypeEntry 6 }

sonusEvLogTypeSaveTo OBJECT-TYPE
    SYNTAX          INTEGER { none(0), disk(1), memory(2), both(3) }
    MAX-ACCESS      read-write
    STATUS          current
    DESCRIPTION     
            "Save events to memory, disk, both, or neither."
    DEFVAL          { both }
    ::= { sonusEvLogTypeEntry 7 }

sonusEvLogTypeMaxEventMemSize OBJECT-TYPE
    SYNTAX          Integer32 (1..64)
    MAX-ACCESS      read-write
    STATUS          current
    DESCRIPTION     
            "The maximum size of the memory event log buffer
             (in KB)."
    DEFVAL          { 16 }
    ::= { sonusEvLogTypeEntry 8 }

sonusEvLogTypeFilterLevel OBJECT-TYPE
    SYNTAX          SonusEventFilterLevel
    MAX-ACCESS      read-write
    STATUS          current
    DESCRIPTION     
            "Events that are at least as severe as the designated
             level will be logged. noevents suppresses all events
             of this type from being logged."
    DEFVAL          { major }
    ::= { sonusEvLogTypeEntry 9 }

sonusEvLogTypeRolloverStartTime OBJECT-TYPE
    SYNTAX          Integer32
    MAX-ACCESS      read-write
    STATUS          current
    DESCRIPTION     
            "The start time for event log rollover."
    DEFVAL          { 0 }
    ::= { sonusEvLogTypeEntry 10 }

sonusEvLogTypeRolloverInterval OBJECT-TYPE
    SYNTAX          Integer32
    MAX-ACCESS      read-write
    STATUS          current
    DESCRIPTION     
            "The event log rollover interval."
    DEFVAL          { 0 }
    ::= { sonusEvLogTypeEntry 11 }

sonusEvLogTypeRolloverType OBJECT-TYPE
    SYNTAX          INTEGER { repetitive(1), nonrepetitive(2) }
    MAX-ACCESS      read-write
    STATUS          current
    DESCRIPTION     
            "The even log reollover type. Repetative type wiill
             rollover logs continuosly after rollover Interval."
    DEFVAL          { nonrepetitive }
    ::= { sonusEvLogTypeEntry 12 }

sonusEvLogTypeRolloverAction OBJECT-TYPE
    SYNTAX          INTEGER { now(1), start(2), stop(3) }
    MAX-ACCESS      read-write
    STATUS          current
    DESCRIPTION     
            "Event log roallover actions.
             1. NOW   - Roll event log immediately.
             2. START - Start event log rolling at specified starting time.
             3. STOP  - Stop event log rolling."
    DEFVAL          { stop }
    ::= { sonusEvLogTypeEntry 13 }

sonusEvLogTypeDisk OBJECT-TYPE
    SYNTAX          INTEGER { nfsServer(1), localDisk(2) }
    MAX-ACCESS      read-only
    STATUS          current
    DESCRIPTION     
            "This MIB object is not used."
    DEFVAL          { nfsServer }
    ::= { sonusEvLogTypeEntry 14 }

sonusEvLogTypeFileWriteMode OBJECT-TYPE
    SYNTAX          INTEGER { default(1), optimize(2) }
    MAX-ACCESS      read-write
    STATUS          current
    DESCRIPTION     
            "Identifies event log NFS write mode.
             1. DEFAULT  - Log data is written to NFS as 1344 byte packet.
             2. OPTIMIZE - Log data is written to NFS as 8000 byte packet.
             Optimize write mode results in IP fragmentation but yields better throughput."
    DEFVAL          { default }
    ::= { sonusEvLogTypeEntry 15 }

sonusEvLogTypeStatusTable OBJECT-TYPE
    SYNTAX          SEQUENCE OF SonusEvLogTypeStatusEntry
    MAX-ACCESS      not-accessible
    STATUS          current
    DESCRIPTION     
            "Event Log status table for status items
             related to each Event Log type."
    ::= { sonusEventLogMIBObjects 2 }

sonusEvLogTypeStatusEntry OBJECT-TYPE
    SYNTAX          SonusEvLogTypeStatusEntry
    MAX-ACCESS      not-accessible
    STATUS          current
    DESCRIPTION     
            "An entry of Event Log status related to each
             event log type."
    INDEX           { sonusEvLogTypeStatusShelf, 
                      sonusEvLogTypeStatusType }
    ::= { sonusEvLogTypeStatusTable 1 }

SonusEvLogTypeStatusEntry ::=
    SEQUENCE {
        sonusEvLogTypeStatusShelf       SonusShelfIndex,
        sonusEvLogTypeStatusType        INTEGER,
        sonusEvLogTypeStatusCurrentFile DisplayString,
        sonusEvLogTypeStatusFileRecs    Unsigned32,
        sonusEvLogTypeStatusFileBytes   Unsigned32,
        sonusEvLogTypeStatusMemRecs     Unsigned32,
        sonusEvLogTypeStatusMemBytes    Unsigned32,
        sonusEvLogTypeStatusFileDropped Unsigned32,
        sonusEvLogTypeStatusMemDropped  Unsigned32,
        sonusEvLogTypeStatusNextRollover Unsigned32,
        sonusEvLogTypeStatusLogDestination  INTEGER,
        sonusEvLogTypeStatusLastFileDrop DateAndTime,
        sonusEvLogTypeStatusLastMemDrop DateAndTime,
        sonusEvLogTypeStatusResetAction INTEGER,
        sonusEvLogTypeStatusExtMemRecs  Unsigned32
    }

sonusEvLogTypeStatusShelf OBJECT-TYPE
    SYNTAX          SonusShelfIndex
    MAX-ACCESS      read-only
    STATUS          current
    DESCRIPTION     
            "The shelf number for which these table entries
             apply."
    ::= { sonusEvLogTypeStatusEntry 1 }

sonusEvLogTypeStatusType OBJECT-TYPE
    SYNTAX          INTEGER { system(1), debug(2), trace(3), acct(4), 
                        pfm(5), cli(6) }
    MAX-ACCESS      read-only
    STATUS          current
    DESCRIPTION     
            "The type of the event log.  Each type has separate
             configuration parameters and logs to a separate file."
    ::= { sonusEvLogTypeStatusEntry 2 }

sonusEvLogTypeStatusCurrentFile OBJECT-TYPE
    SYNTAX          DisplayString
    MAX-ACCESS      read-only
    STATUS          current
    DESCRIPTION     
            "The filename that is currently being used for logging.
             No name is displayed when disk logging is disabled. The
             name RECOVERING is displayed when an attempt to automatically
             restart disk logging is in progress."
    ::= { sonusEvLogTypeStatusEntry 3 }

sonusEvLogTypeStatusFileRecs OBJECT-TYPE
    SYNTAX          Unsigned32
    MAX-ACCESS      read-only
    STATUS          current
    DESCRIPTION     
            "Count of the number of event records written to
             the current event log file."
    ::= { sonusEvLogTypeStatusEntry 4 }

sonusEvLogTypeStatusFileBytes OBJECT-TYPE
    SYNTAX          Unsigned32
    MAX-ACCESS      read-only
    STATUS          current
    DESCRIPTION     
            "Count of the number of bytes written to
             the current event log file."
    ::= { sonusEvLogTypeStatusEntry 5 }

sonusEvLogTypeStatusMemRecs OBJECT-TYPE
    SYNTAX          Unsigned32
    MAX-ACCESS      read-only
    STATUS          current
    DESCRIPTION     
            "Count of the number of event records written to
             the event log memory buffer."
    ::= { sonusEvLogTypeStatusEntry 6 }

sonusEvLogTypeStatusMemBytes OBJECT-TYPE
    SYNTAX          Unsigned32
    MAX-ACCESS      read-only
    STATUS          current
    DESCRIPTION     
            "Count of the number of bytes written to
             the event log memory buffer."
    ::= { sonusEvLogTypeStatusEntry 7 }

sonusEvLogTypeStatusFileDropped OBJECT-TYPE
    SYNTAX          Unsigned32
    MAX-ACCESS      read-only
    STATUS          current
    DESCRIPTION     
            "Count of the number of event records dropped when writing
             to an Event Log file."
    ::= { sonusEvLogTypeStatusEntry 8 }

sonusEvLogTypeStatusMemDropped OBJECT-TYPE
    SYNTAX          Unsigned32
    MAX-ACCESS      read-only
    STATUS          current
    DESCRIPTION     
            "Count of the number of event records dropped when writing
             to an Event Log memory buffer."
    ::= { sonusEvLogTypeStatusEntry 9 }

sonusEvLogTypeStatusNextRollover OBJECT-TYPE
    SYNTAX          Unsigned32
    MAX-ACCESS      read-only
    STATUS          current
    DESCRIPTION     
            "Time in minutes left before next rollover."
    ::= { sonusEvLogTypeStatusEntry 10 }

sonusEvLogTypeStatusLogDestination OBJECT-TYPE
    SYNTAX          INTEGER { nfsServer(1), localDisk(2), 
                        streamServer(3) }
    MAX-ACCESS      read-only
    STATUS          current
    DESCRIPTION     
            "Identifies the location where this Event Log type writes to."
    ::= { sonusEvLogTypeStatusEntry 11 }

sonusEvLogTypeStatusLastFileDrop OBJECT-TYPE
    SYNTAX          DateAndTime
    MAX-ACCESS      read-only
    STATUS          current
    DESCRIPTION     
            "Time of the last event record dropped when writing
             to an Event Log file. The value will be zero length if
             no records have been dropped since last reboot."
    ::= { sonusEvLogTypeStatusEntry 12 }

sonusEvLogTypeStatusLastMemDrop OBJECT-TYPE
    SYNTAX          DateAndTime
    MAX-ACCESS      read-only
    STATUS          current
    DESCRIPTION     
            "Time of the last event record dropped when writing
             to an Event Log memory buffer. The value will be zero length if
             no records have been dropped since last reboot."
    ::= { sonusEvLogTypeStatusEntry 13 }

sonusEvLogTypeStatusResetAction OBJECT-TYPE
    SYNTAX          INTEGER { dropCount(1) }
    MAX-ACCESS      read-write
    STATUS          current
    DESCRIPTION     
            "Take action to reset a statistic counter.
             1. dropCount  - reset record drop counts."
    ::= { sonusEvLogTypeStatusEntry 14 }

sonusEvLogTypeStatusExtMemRecs OBJECT-TYPE
    SYNTAX          Unsigned32
    MAX-ACCESS      read-only
    STATUS          current
    DESCRIPTION     
            "Count of the number of event records written to
             the event log extended memory buffer."
    ::= { sonusEvLogTypeStatusEntry 15 }

sonusEvLogMemTable OBJECT-TYPE
    SYNTAX          SEQUENCE OF SonusEvLogMemEntry
    MAX-ACCESS      not-accessible
    STATUS          current
    DESCRIPTION     
            "Events logged to memory."
    ::= { sonusEventLogMIBObjects 3 }

sonusEvLogMemEntry OBJECT-TYPE
    SYNTAX          SonusEvLogMemEntry
    MAX-ACCESS      not-accessible
    STATUS          current
    DESCRIPTION     
            "An entry of the Event Log memory table."
    INDEX           { sonusEvLogMemShelf, sonusEvLogMemType, 
                      sonusEvLogMemIndex }
    ::= { sonusEvLogMemTable 1 }

SonusEvLogMemEntry ::=
    SEQUENCE {
        sonusEvLogMemShelf              SonusShelfIndex,
        sonusEvLogMemType               INTEGER,
        sonusEvLogMemIndex              Integer32,
        sonusEvLogMemText               SonusEventString
    }

sonusEvLogMemShelf OBJECT-TYPE
    SYNTAX          SonusShelfIndex
    MAX-ACCESS      read-only
    STATUS          current
    DESCRIPTION     
            "The shelf number for which these table entries
             apply."
    ::= { sonusEvLogMemEntry 1 }

sonusEvLogMemType OBJECT-TYPE
    SYNTAX          INTEGER { system(1), debug(2), trace(3), acct(4), 
                        cli(6) }
    MAX-ACCESS      read-only
    STATUS          current
    DESCRIPTION     
            "The Event Log Type to which these table entries
             apply."
    ::= { sonusEvLogMemEntry 2 }

sonusEvLogMemIndex OBJECT-TYPE
    SYNTAX          Integer32
    MAX-ACCESS      read-only
    STATUS          current
    DESCRIPTION     
            "The index for the entry."
    ::= { sonusEvLogMemEntry 3 }

sonusEvLogMemText OBJECT-TYPE
    SYNTAX          SonusEventString
    MAX-ACCESS      read-only
    STATUS          current
    DESCRIPTION     
            "The event log text.  This object only contains the first 1023
             characters of the event.  The event log file will contain the
             entire event."
    ::= { sonusEvLogMemEntry 4 }

sonusEvLogSubsystemTable OBJECT-TYPE
    SYNTAX          SEQUENCE OF SonusEvLogSubsystemEntry
    MAX-ACCESS      not-accessible
    STATUS          current
    DESCRIPTION     
            "Subsystem Event Logging configuration table.
             This table configures subsystems DO NOT filter events."
    ::= { sonusEventLogMIBObjects 5 }

sonusEvLogSubsystemEntry OBJECT-TYPE
    SYNTAX          SonusEvLogSubsystemEntry
    MAX-ACCESS      not-accessible
    STATUS          current
    DESCRIPTION     
            "An entry of Subsystem Event Logging configuration."
    INDEX           { sonusEvLogSubsysShelf, sonusEvLogSubsysSlot, 
                      sonusEvLogSubsysSysid }
    ::= { sonusEvLogSubsystemTable 1 }

SonusEvLogSubsystemEntry ::=
    SEQUENCE {
        sonusEvLogSubsysShelf           SonusShelfIndex,
        sonusEvLogSubsysSlot            SonusSlotIndex,
        sonusEvLogSubsysSysid           SonusSysId,
        sonusEvLogSubsysInfoLogState    SonusAdminState,
        sonusEvLogSubsysMinEventId      Unsigned32,
        sonusEvLogSubsysMaxEventId      Unsigned32,
        sonusEvLogSubsysEventCategory   BITS
    }

sonusEvLogSubsysShelf OBJECT-TYPE
    SYNTAX          SonusShelfIndex
    MAX-ACCESS      read-only
    STATUS          current
    DESCRIPTION     
            "The GSX shelf index for which subsystem event entries apply."
    ::= { sonusEvLogSubsystemEntry 1 }

sonusEvLogSubsysSlot OBJECT-TYPE
    SYNTAX          SonusSlotIndex
    MAX-ACCESS      read-only
    STATUS          current
    DESCRIPTION     
            "The GSX slot index for which the subsystem event entries apply."
    ::= { sonusEvLogSubsystemEntry 2 }

sonusEvLogSubsysSysid OBJECT-TYPE
    SYNTAX          SonusSysId
    MAX-ACCESS      read-only
    STATUS          current
    DESCRIPTION     
            "The GSX subsystem ID for which the subsystem event entries apply."
    ::= { sonusEvLogSubsystemEntry 3 }

sonusEvLogSubsysInfoLogState OBJECT-TYPE
    SYNTAX          SonusAdminState
    MAX-ACCESS      read-write
    STATUS          current
    DESCRIPTION     
            "The subsystem's INFO level event logging state. If this state is
             enabled, then subsystem INFO/MINOR events fall into specified 
             range, sonusEvLogSubsystemMinEventId to sonusEvLogSubsystemMinEventId,
             will not be filtered."
    DEFVAL          { disabled }
    ::= { sonusEvLogSubsystemEntry 4 }

sonusEvLogSubsysMinEventId OBJECT-TYPE
    SYNTAX          Unsigned32 (0..2048)
    MAX-ACCESS      read-write
    STATUS          current
    DESCRIPTION     
            "The subsystem's minimun event ID that do not get filtered."
    DEFVAL          { 0 }
    ::= { sonusEvLogSubsystemEntry 5 }

sonusEvLogSubsysMaxEventId OBJECT-TYPE
    SYNTAX          Unsigned32 (0..2048)
    MAX-ACCESS      read-write
    STATUS          current
    DESCRIPTION     
            "The subsystem's maxmum event ID that do not get filtered."
    DEFVAL          { 2048 }
    ::= { sonusEvLogSubsystemEntry 6 }

sonusEvLogSubsysEventCategory OBJECT-TYPE
    SYNTAX          BITS { c0(0), c1(1), c2(2), c3(3), c4(4), c5(5), 
                        c6(6), c7(7) }
    MAX-ACCESS      read-write
    STATUS          current
    DESCRIPTION     
            "The subsystem's event categories that do not get filtered."
    DEFVAL          { {c0, c1, c2, c3, c4, c5, c6, c7} }
    ::= { sonusEvLogSubsystemEntry 7 }

sonusEvLogFilterTable OBJECT-TYPE
    SYNTAX          SEQUENCE OF SonusEvLogFilterEntry
    MAX-ACCESS      not-accessible
    STATUS          current
    DESCRIPTION     
            "Event Log Class Filter configuration table per card."
    ::= { sonusEventLogMIBObjects 6 }

sonusEvLogFilterEntry OBJECT-TYPE
    SYNTAX          SonusEvLogFilterEntry
    MAX-ACCESS      not-accessible
    STATUS          current
    DESCRIPTION     
            "An entry of Event Log Class Filter configuration per card."
    INDEX           { sonusEvLogFilterShelf, sonusEvLogFilterSlot, 
                      sonusEvLogFilterType, sonusEvLogFilterEventClass }
    ::= { sonusEvLogFilterTable 1 }

SonusEvLogFilterEntry ::=
    SEQUENCE {
        sonusEvLogFilterShelf           SonusShelfIndex,
        sonusEvLogFilterSlot            SonusSlotIndex,
        sonusEvLogFilterType            INTEGER,
        sonusEvLogFilterEventClass      SonusEventClass,
        sonusEvLogFilterLevel           SonusEventFilterLevel,
        sonusEvLogFilterState           INTEGER
    }

sonusEvLogFilterShelf OBJECT-TYPE
    SYNTAX          SonusShelfIndex
    MAX-ACCESS      read-only
    STATUS          current
    DESCRIPTION     
            "The shelf number for which these table entries
             apply."
    ::= { sonusEvLogFilterEntry 1 }

sonusEvLogFilterSlot OBJECT-TYPE
    SYNTAX          SonusSlotIndex
    MAX-ACCESS      read-only
    STATUS          current
    DESCRIPTION     
            "The slot number for which these table entries
             apply."
    ::= { sonusEvLogFilterEntry 2 }

sonusEvLogFilterType OBJECT-TYPE
    SYNTAX          INTEGER { system(1), debug(2), trace(3), cli(6) }
    MAX-ACCESS      read-only
    STATUS          current
    DESCRIPTION     
            "The event log type for which these filter table entries
             apply."
    ::= { sonusEvLogFilterEntry 3 }

sonusEvLogFilterEventClass OBJECT-TYPE
    SYNTAX          SonusEventClass
    MAX-ACCESS      read-only
    STATUS          current
    DESCRIPTION     
            "The class of events to which the filter entry applies."
    ::= { sonusEvLogFilterEntry 4 }

sonusEvLogFilterLevel OBJECT-TYPE
    SYNTAX          SonusEventFilterLevel
    MAX-ACCESS      read-write
    STATUS          current
    DESCRIPTION     
            "Events that are at least as severe as the designated
             level will be logged. noevents suppresses all events
             of this type from being logged."
    DEFVAL          { major }
    ::= { sonusEvLogFilterEntry 5 }

sonusEvLogFilterState OBJECT-TYPE
    SYNTAX          INTEGER { off(1), on(2) }
    MAX-ACCESS      read-write
    STATUS          current
    DESCRIPTION     
            "On if this filter entry should take precedence over the
             per-node settings."
    DEFVAL          { off }
    ::= { sonusEvLogFilterEntry 6 }

sonusEvLogFilterStatusTable OBJECT-TYPE
    SYNTAX          SEQUENCE OF SonusEvLogFilterStatusEntry
    MAX-ACCESS      not-accessible
    STATUS          current
    DESCRIPTION     
            "Event Log Class Filter status table per card."
    ::= { sonusEventLogMIBObjects 7 }

sonusEvLogFilterStatusEntry OBJECT-TYPE
    SYNTAX          SonusEvLogFilterStatusEntry
    MAX-ACCESS      not-accessible
    STATUS          current
    DESCRIPTION     
            "An entry of Event Log Class Filter status per card."
    INDEX           { sonusEvLogFilterStatusShelf, 
                      sonusEvLogFilterStatusSlot, 
                      sonusEvLogFilterStatusType, 
                      sonusEvLogFilterStatusEventClass }
    ::= { sonusEvLogFilterStatusTable 1 }

SonusEvLogFilterStatusEntry ::=
    SEQUENCE {
        sonusEvLogFilterStatusShelf     SonusShelfIndex,
        sonusEvLogFilterStatusSlot      SonusSlotIndex,
        sonusEvLogFilterStatusType      INTEGER,
        sonusEvLogFilterStatusEventClass SonusEventClass,
        sonusEvLogFilterStatusFiltered  Integer32
    }

sonusEvLogFilterStatusShelf OBJECT-TYPE
    SYNTAX          SonusShelfIndex
    MAX-ACCESS      read-only
    STATUS          current
    DESCRIPTION     
            "The shelf number for which these table entries
             apply."
    ::= { sonusEvLogFilterStatusEntry 1 }

sonusEvLogFilterStatusSlot OBJECT-TYPE
    SYNTAX          SonusSlotIndex
    MAX-ACCESS      read-only
    STATUS          current
    DESCRIPTION     
            "The slot number for which these table entries
             apply."
    ::= { sonusEvLogFilterStatusEntry 2 }

sonusEvLogFilterStatusType OBJECT-TYPE
    SYNTAX          INTEGER { system(1), debug(2), trace(3), cli(6) }
    MAX-ACCESS      read-only
    STATUS          current
    DESCRIPTION     
            "The event log type for which these table entries
             apply."
    ::= { sonusEvLogFilterStatusEntry 3 }

sonusEvLogFilterStatusEventClass OBJECT-TYPE
    SYNTAX          SonusEventClass
    MAX-ACCESS      read-only
    STATUS          current
    DESCRIPTION     
            "The event class to which the filter entry applies."
    ::= { sonusEvLogFilterStatusEntry 4 }

sonusEvLogFilterStatusFiltered OBJECT-TYPE
    SYNTAX          Integer32
    MAX-ACCESS      read-only
    STATUS          current
    DESCRIPTION     
            "The number of events that were filtered."
    ::= { sonusEvLogFilterStatusEntry 5 }

sonusDflushNetworkFailureEventStatTable OBJECT-TYPE
    SYNTAX          SEQUENCE OF SonusDflushNetworkFailureEventStatEntry
    MAX-ACCESS      not-accessible
    STATUS          current
    DESCRIPTION     
            "This table specifies Dflush Network Failover status objects"
    ::= { sonusEventLogMIBObjects 8 }

sonusDflushNetworkFailureEventStatEntry OBJECT-TYPE
    SYNTAX          SonusDflushNetworkFailureEventStatEntry
    MAX-ACCESS      not-accessible
    STATUS          current
    DESCRIPTION     
            ""
    INDEX           { sonusNfoInterfaceStatType }
    ::= { sonusDflushNetworkFailureEventStatTable 1 }

SonusDflushNetworkFailureEventStatEntry ::=
    SEQUENCE {
        sonusNfoInterfaceStatType       INTEGER,
        sonusNfoInterfaceStatState      SonusAdminState,
        sonusNfoInterfaceStatEventsLogged Integer32,
        sonusNfoInterfaceStatEventsTotalMemBytes        Integer32,
        sonusNfoInterfaceStatReason     INTEGER,
        sonusNfoInterfaceStatStartTime  DateAndTime,
        sonusNfoInterfaceStatStopTime   DateAndTime,
        sonusNfoBeginFileName           DisplayString,
        sonusNfoEndFileName             DisplayString
    }

sonusNfoInterfaceStatType OBJECT-TYPE
    SYNTAX          INTEGER { sys(0), dbg(1), trc(2), act(3), pfm(4) }
    MAX-ACCESS      read-only
    STATUS          current
    DESCRIPTION     
            "This object defines the type of the statistics
             being currently displayed"
    ::= { sonusDflushNetworkFailureEventStatEntry 1 }

sonusNfoInterfaceStatState OBJECT-TYPE
    SYNTAX          SonusAdminState
    MAX-ACCESS      read-only
    STATUS          current
    DESCRIPTION     
            "This object defines the admin state 
             of the Network Failover feature."
    DEFVAL          { disabled }
    ::= { sonusDflushNetworkFailureEventStatEntry 2 }

sonusNfoInterfaceStatEventsLogged OBJECT-TYPE
    SYNTAX          Integer32
    MAX-ACCESS      read-only
    STATUS          current
    DESCRIPTION     
            "This object defines the number of events 
             logged by the Network Failover Feature since
             the admin state was set to ENABLED"
    DEFVAL          { 0 }
    ::= { sonusDflushNetworkFailureEventStatEntry 3 }

sonusNfoInterfaceStatEventsTotalMemBytes OBJECT-TYPE
    SYNTAX          Integer32
    MAX-ACCESS      read-only
    STATUS          current
    DESCRIPTION     
            "This object defines the number of bytes 
             logged by the Network Failover Feature since
             the admin state was set to ENABLED"
    DEFVAL          { 0 }
    ::= { sonusDflushNetworkFailureEventStatEntry 4 }

sonusNfoInterfaceStatReason OBJECT-TYPE
    SYNTAX          INTEGER { nfsOOS(0), lnkFail(1), lnkCong(2) }
    MAX-ACCESS      read-only
    STATUS          current
    DESCRIPTION     
            "This object defines the stat reason"
    DEFVAL          { 1 }
    ::= { sonusDflushNetworkFailureEventStatEntry 5 }

sonusNfoInterfaceStatStartTime OBJECT-TYPE
    SYNTAX          DateAndTime
    MAX-ACCESS      read-only
    STATUS          current
    DESCRIPTION     
            "Time when the NFO started for this type of event
             log"
    ::= { sonusDflushNetworkFailureEventStatEntry 6 }

sonusNfoInterfaceStatStopTime OBJECT-TYPE
    SYNTAX          DateAndTime
    MAX-ACCESS      read-only
    STATUS          current
    DESCRIPTION     
            "Time when the NFO stopped for this type of event
             log"
    ::= { sonusDflushNetworkFailureEventStatEntry 7 }

sonusNfoBeginFileName OBJECT-TYPE
    SYNTAX          DisplayString (SIZE(1..16))
    MAX-ACCESS      read-only
    STATUS          current
    DESCRIPTION     
            "The event file log directory name."
    ::= { sonusDflushNetworkFailureEventStatEntry 8 }

sonusNfoEndFileName OBJECT-TYPE
    SYNTAX          DisplayString (SIZE(1..16))
    MAX-ACCESS      read-only
    STATUS          current
    DESCRIPTION     
            "The event file log directory name."
    ::= { sonusDflushNetworkFailureEventStatEntry 9 }

sonusEventLogMIBNotifications OBJECT IDENTIFIER
    ::= { sonusEventLogMIB 2 }

sonusEventLogMIBNotificationsPrefix OBJECT IDENTIFIER
    ::= { sonusEventLogMIBNotifications 0 }

sonusEventLogMIBNotificationsObjects OBJECT IDENTIFIER
    ::= { sonusEventLogMIBNotifications 1 }

sonusEvLogAdminState OBJECT-TYPE
    SYNTAX          INTEGER { disabled(1), enabled(2), rollfile(3) }
    MAX-ACCESS      read-only
    STATUS          current
    DESCRIPTION     
            "The requested state of the given Event Log type.  Rollfile
             will close an enabled log file and reopen, incrementing the
             suffix.  If a file is disabled and rolled, the command is
             ignored."
    ::= { sonusEventLogMIBNotificationsObjects 1 }

sonusEvLogShutdownReason OBJECT-TYPE
    SYNTAX          INTEGER { fileWriteFailed(1), nfsError(2), 
                        createDirectoryFailed(3), 
                        maximumFileCountReached(4), fileRemoveFailed(5), 
                        fileOpenFailed(6), fileHeaderWriteFailed(7), 
                        memoryAllocationFailed(8), 
                        administrativeShutdown(9), 
                        localDiskUnavailable(10) }
    MAX-ACCESS      read-only
    STATUS          current
    DESCRIPTION     
            "The reason that event file logging has been shutdown."
    ::= { sonusEventLogMIBNotificationsObjects 2 }

sonusEvLogDirName OBJECT-TYPE
    SYNTAX          DisplayString
    MAX-ACCESS      read-only
    STATUS          current
    DESCRIPTION     
            "The event file log directory name."
    ::= { sonusEventLogMIBNotificationsObjects 3 }

sonusEvLogFilePercentage OBJECT-TYPE
    SYNTAX          Integer32
    MAX-ACCESS      read-only
    STATUS          current
    DESCRIPTION     
            "The percentage the event log directory is full based on file count."
    ::= { sonusEventLogMIBNotificationsObjects 4 }

sonusEvLogCurFileCount OBJECT-TYPE
    SYNTAX          Integer32
    MAX-ACCESS      read-only
    STATUS          current
    DESCRIPTION     
            "The current count of event files."
    ::= { sonusEventLogMIBNotificationsObjects 5 }

sonusEvLogErrorCode OBJECT-TYPE
    SYNTAX          Integer32
    MAX-ACCESS      read-only
    STATUS          current
    DESCRIPTION     
            "The evlog error code."
    ::= { sonusEventLogMIBNotificationsObjects 6 }

sonusEvLogTypeName OBJECT-TYPE
    SYNTAX          DisplayString
    MAX-ACCESS      read-only
    STATUS          current
    DESCRIPTION     
            "The event file log type."
    ::= { sonusEventLogMIBNotificationsObjects 7 }

sonusEventLogFileStateNotification NOTIFICATION-TYPE
    OBJECTS         { sonusShelfIndex, sonusEvLogType, 
                      sonusEvLogAdminState, sonusEventDescription, 
                      sonusEventClass, sonusEventLevel, sonusSequenceId, 
                      sonusEventTime }
    STATUS          current
    DESCRIPTION     
            "This trap indicates the current state of event file logging."
    ::= { sonusEventLogMIBNotificationsPrefix 1 }

sonusEventLogFileCreatedNotification NOTIFICATION-TYPE
    OBJECTS         { sonusShelfIndex, sonusEvLogType, 
                      sonusEvLogTypeStatusCurrentFile, 
                      sonusEventDescription, sonusEventClass, 
                      sonusEventLevel, sonusSequenceId, sonusEventTime, 
                      sonusEvLogTypeDisk }
    STATUS          current
    DESCRIPTION     
            "This trap indicates the name of the event file which has been created for logging."
    ::= { sonusEventLogMIBNotificationsPrefix 2 }

sonusEventLogAcctFileCreatedNotification NOTIFICATION-TYPE
    OBJECTS         { sonusShelfIndex, sonusEvLogTypeStatusCurrentFile, 
                      sonusEventDescription, sonusEventClass, 
                      sonusEventLevel, sonusSequenceId, sonusEventTime, 
                      sonusEvLogTypeDisk }
    STATUS          current
    DESCRIPTION     
            "This trap indicates the name of the accounting event file which has been created for logging."
    ::= { sonusEventLogMIBNotificationsPrefix 3 }

sonusEventLogFileRestartNotification NOTIFICATION-TYPE
    OBJECTS         { sonusShelfIndex, sonusEvLogType, 
                      sonusEventDescription, sonusEventClass, 
                      sonusEventLevel, sonusSequenceId, sonusEventTime }
    STATUS          current
    DESCRIPTION     
            "This trap indicates that file event logging has been automatically restarted."
    ::= { sonusEventLogMIBNotificationsPrefix 4 }

sonusEventLogAcctFileRestartNotification NOTIFICATION-TYPE
    OBJECTS         { sonusShelfIndex, sonusEventDescription, 
                      sonusEventClass, sonusEventLevel, sonusSequenceId, 
                      sonusEventTime }
    STATUS          current
    DESCRIPTION     
            "This trap indicates that accounting file event logging has been automatically restarted."
    ::= { sonusEventLogMIBNotificationsPrefix 5 }

sonusEventLogFileClosedNotification NOTIFICATION-TYPE
    OBJECTS         { sonusShelfIndex, sonusEvLogType, 
                      sonusEvLogTypeStatusCurrentFile, 
                      sonusEventDescription, sonusEventClass, 
                      sonusEventLevel, sonusNfsServerIp, 
                      sonusNfsServerMount, sonusEvLogTypeBaseDirectory, 
                      sonusSequenceId, sonusEventTime, 
                      sonusEvLogTypeDisk }
    STATUS          current
    DESCRIPTION     
            "This trap indicates the name of the event file which has been closed."
    ::= { sonusEventLogMIBNotificationsPrefix 6 }

sonusEventLogAcctFileClosedNotification NOTIFICATION-TYPE
    OBJECTS         { sonusShelfIndex, sonusEvLogTypeStatusCurrentFile, 
                      sonusEventDescription, sonusEventClass, 
                      sonusEventLevel, sonusNfsServerIp, 
                      sonusNfsServerMount, sonusEvLogTypeBaseDirectory, 
                      sonusSequenceId, sonusEventTime, 
                      sonusEvLogTypeDisk }
    STATUS          current
    DESCRIPTION     
            "This trap indicates the name of the accounting event file which has been closed."
    ::= { sonusEventLogMIBNotificationsPrefix 7 }

sonusEventLogFileShutdownNotification NOTIFICATION-TYPE
    OBJECTS         { sonusShelfIndex, sonusEvLogType, 
                      sonusEvLogShutdownReason, sonusEvLogAdminState, 
                      sonusEventDescription, sonusEventClass, 
                      sonusEventLevel, sonusSequenceId, sonusEventTime }
    STATUS          current
    DESCRIPTION     
            "This trap indicates that a shutdown of file event logging has occurred."
    ::= { sonusEventLogMIBNotificationsPrefix 8 }

sonusEventLogFileCountNotification NOTIFICATION-TYPE
    OBJECTS         { sonusEvLogDirName, sonusEvLogFilePercentage, 
                      sonusEvLogCurFileCount, sonusEvLogTypeFileCount, 
                      sonusEventDescription, sonusEventClass, 
                      sonusEventLevel, sonusSequenceId, sonusEventTime }
    STATUS          current
    DESCRIPTION     
            "This trap indicates that the number of event log files is approaching or has reached the configured maximum."
    ::= { sonusEventLogMIBNotificationsPrefix 9 }

sonusEventLogFileCountChngNotification NOTIFICATION-TYPE
    OBJECTS         { sonusShelfIndex, sonusEvLogType, 
                      sonusEvLogTypeFileCount, sonusEventDescription, 
                      sonusEventClass, sonusEventLevel, sonusSequenceId, 
                      sonusEventTime }
    STATUS          current
    DESCRIPTION     
            "This trap indicates the number of Event Log files that will be maintained for this event type is changed"
    ::= { sonusEventLogMIBNotificationsPrefix 10 }

sonusEventLogFileSizeChngNotification NOTIFICATION-TYPE
    OBJECTS         { sonusShelfIndex, sonusEvLogType, 
                      sonusEvLogTypeFileSize, sonusEventDescription, 
                      sonusEventClass, sonusEventLevel, sonusSequenceId, 
                      sonusEventTime }
    STATUS          current
    DESCRIPTION     
            "This trap indicates that the maximum size of a single event log file has changed."
    ::= { sonusEventLogMIBNotificationsPrefix 11 }

sonusEventLogFileMsgQueueChngNotification NOTIFICATION-TYPE
    OBJECTS         { sonusShelfIndex, sonusEvLogType, 
                      sonusEvLogTypeFileMsgQueue, sonusEventDescription, 
                      sonusEventClass, sonusEventLevel, sonusSequenceId, 
                      sonusEventTime }
    STATUS          current
    DESCRIPTION     
            "This trap indicates that the number event log message entries to the buffer changed"
    ::= { sonusEventLogMIBNotificationsPrefix 12 }

sonusEventLogSaveToChngNotification NOTIFICATION-TYPE
    OBJECTS         { sonusShelfIndex, sonusEvLogType, 
                      sonusEvLogTypeSaveTo, sonusEventDescription, 
                      sonusEventClass, sonusEventLevel, sonusSequenceId, 
                      sonusEventTime }
    STATUS          current
    DESCRIPTION     
            "This Trap indicates that the location where events are saved is being changed "
    ::= { sonusEventLogMIBNotificationsPrefix 13 }

sonusEventLogFileMaxEventMemSizeChngNotification NOTIFICATION-TYPE
    OBJECTS         { sonusShelfIndex, sonusEvLogType, 
                      sonusEvLogTypeMaxEventMemSize, 
                      sonusEventDescription, sonusEventClass, 
                      sonusEventLevel, sonusSequenceId, sonusEventTime }
    STATUS          current
    DESCRIPTION     
            "This trap indicates that the maximum size of the memory event log buffer is changed"
    ::= { sonusEventLogMIBNotificationsPrefix 14 }

sonusEventLogFileFilterLevelChngNotification NOTIFICATION-TYPE
    OBJECTS         { sonusShelfIndex, sonusEvLogType, 
                      sonusEvLogTypeFilterLevel, sonusEventDescription, 
                      sonusEventClass, sonusEventLevel, sonusSequenceId, 
                      sonusEventTime }
    STATUS          current
    DESCRIPTION     
            "This trap indicates that the level of event logging for this event type is changed"
    ::= { sonusEventLogMIBNotificationsPrefix 15 }

sonusEventLogDirectoryCreateErrorNotification NOTIFICATION-TYPE
    OBJECTS         { sonusEvLogType, sonusEvLogDirName, 
                      sonusEvLogErrorCode, sonusEventDescription, 
                      sonusEventClass, sonusEventLevel, sonusSequenceId, 
                      sonusEventTime }
    STATUS          current
    DESCRIPTION     
            "This trap indicates that the inability of the GSX to create a directory for event logging.
             This could also indicate an generic error with the NFS server."
    ::= { sonusEventLogMIBNotificationsPrefix 16 }

sonusEventLogRolloverScheduledNotification NOTIFICATION-TYPE
    OBJECTS         { sonusShelfIndex, sonusEvLogType, 
                      sonusEventDescription, sonusEventClass, 
                      sonusEventLevel, sonusSequenceId, sonusEventTime }
    STATUS          current
    DESCRIPTION     
            "This trap indicates that event log for this log type is scheduled to rollover."
    ::= { sonusEventLogMIBNotificationsPrefix 17 }

sonusEventLogRolloverStoppedNotification NOTIFICATION-TYPE
    OBJECTS         { sonusShelfIndex, sonusEvLogType, 
                      sonusEventDescription, sonusEventClass, 
                      sonusEventLevel, sonusSequenceId, sonusEventTime }
    STATUS          current
    DESCRIPTION     
            "This trap indicates that event log rollover for this log type is stopped."
    ::= { sonusEventLogMIBNotificationsPrefix 18 }

sonusEventLogDiskLocationChngNotification NOTIFICATION-TYPE
    OBJECTS         { sonusShelfIndex, sonusEvLogType, 
                      sonusEvLogTypeDisk, sonusEventDescription, 
                      sonusEventClass, sonusEventLevel, sonusSequenceId, 
                      sonusEventTime }
    STATUS          obsolete
    DESCRIPTION     
            "This MIB notification object is not used."
    ::= { sonusEventLogMIBNotificationsPrefix 19 }

sonusEventLogRolloverFastNotification NOTIFICATION-TYPE
    OBJECTS         { sonusShelfIndex, sonusEvLogTypeName, 
                      sonusEventDescription, sonusEventClass, 
                      sonusEventLevel, sonusSequenceId, sonusEventTime }
    STATUS          current
    DESCRIPTION     
            "This trap indicates that event log rollover is occuring frequently."
    ::= { sonusEventLogMIBNotificationsPrefix 20 }

sonusEventLogDestinationChangeNotification NOTIFICATION-TYPE
    OBJECTS         { sonusShelfIndex, sonusEvLogType, 
                      sonusEvLogTypeStatusLogDestination, 
                      sonusEventDescription, sonusEventClass, 
                      sonusEventLevel, sonusSequenceId, sonusEventTime }
    STATUS          current
    DESCRIPTION     
            "This trap indicates that the log destination for this log type has changed."
    ::= { sonusEventLogMIBNotificationsPrefix 21 }

sonusEventLogAcctRecDropWarnNotification NOTIFICATION-TYPE
    OBJECTS         { sonusShelfIndex, sonusEventDescription, 
                      sonusEventClass, sonusEventLevel, sonusSequenceId, 
                      sonusEventTime, sonusEvLogTypeStatusFileDropped, 
                      sonusEvLogTypeStatusLastFileDrop }
    STATUS          current
    DESCRIPTION     
            "This trap indicates that accounting records are being dropped."
    ::= { sonusEventLogMIBNotificationsPrefix 22 }

sonusEventLogFileClosedNotificationV6 NOTIFICATION-TYPE
    OBJECTS         { sonusShelfIndex, sonusEvLogType, 
                      sonusEvLogTypeStatusCurrentFile, 
                      sonusEventDescription, sonusEventClass, 
                      sonusEventLevel, sonusNfsServerIpAddrV6, 
                      sonusNfsServerMount, sonusEvLogTypeBaseDirectory, 
                      sonusSequenceId, sonusEventTime, 
                      sonusEvLogTypeDisk }
    STATUS          current
    DESCRIPTION     
            "This trap indicates the name of the event file which has been closed."
    ::= { sonusEventLogMIBNotificationsPrefix 25 }

sonusEventLogAcctFileClosedNotificationV6 NOTIFICATION-TYPE
    OBJECTS         { sonusShelfIndex, sonusEvLogTypeStatusCurrentFile, 
                      sonusEventDescription, sonusEventClass, 
                      sonusEventLevel, sonusNfsServerIpAddrV6, 
                      sonusNfsServerMount, sonusEvLogTypeBaseDirectory, 
                      sonusSequenceId, sonusEventTime, 
                      sonusEvLogTypeDisk }
    STATUS          current
    DESCRIPTION     
            "This trap indicates the name of the accounting event file which has been closed."
    ::= { sonusEventLogMIBNotificationsPrefix 26 }

END -- end of module SONUS-EVENT-LOG-MIB.
