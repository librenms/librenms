--
-- This SMIv2 module has been generated by smidump 0.2-cvs. Do not edit.
--

SONUS-SIP-SMM-MIB DEFINITIONS ::= BEGIN

IMPORTS
    MODULE-IDENTITY, OBJECT-TYPE, Unsigned32
        FROM SNMPv2-SMI
    DisplayString, RowStatus
        FROM SNMPv2-TC
    sonusSipSignallingMIB
        FROM SONUS-SIP-SIGNALLING-MIB
    SonusAdminState, SonusName, SonusSipSmmActionType, 
    SonusSipSmmCriterionType, SonusSipSmmGlobalVariableType, 
    SonusSipSmmHdrInstance, SonusSipSmmHdrRange, 
    SonusSipSmmOperationType, SonusSipSmmParamType, SonusSipSmmTokenType, 
    SonusSipSmmVariableType
        FROM SONUS-TC;

sonusSipPduManipulationMIB MODULE-IDENTITY
    LAST-UPDATED    "200909110000Z"
    ORGANIZATION    
            "Sonus Networks, Inc."
    CONTACT-INFO    
            "   Customer Support    
             Sonus Networks, Inc.
             7 Technology Park Drive
             Westford, MA 01886
             USA
             
             Tel: 978-614-8100
             Fax: 978-614-8609"
    DESCRIPTION     
            "The MIB Module for SIP Message Manipulation Management."
    ::= { sonusSipSignallingMIB 3 }


sonusSipPduManipulationMIBObjects OBJECT IDENTIFIER
    ::= { sonusSipPduManipulationMIB 1 }

sonusSipPduManipulationProfileTable OBJECT-TYPE
    SYNTAX          SEQUENCE OF SonusSipPduManipulationProfileEntry
    MAX-ACCESS      not-accessible
    STATUS          current
    DESCRIPTION     
            "A list of SIP Message Manipulation Profile entries."
    ::= { sonusSipPduManipulationMIBObjects 1 }

sonusSipPduManipulationProfileEntry OBJECT-TYPE
    SYNTAX          SonusSipPduManipulationProfileEntry
    MAX-ACCESS      not-accessible
    STATUS          current
    DESCRIPTION     
            "sonusSipPduManipulationProfileEntry contianing SIP message manipulation
             rules, criterions, and actions"
    INDEX           { sonusSipPduManipulationProfileIndex }
    ::= { sonusSipPduManipulationProfileTable 1 }

SonusSipPduManipulationProfileEntry ::=
    SEQUENCE {
        sonusSipPduManipulationProfileIndex   Unsigned32,
        sonusSipPduManipulationProfileName  SonusName,
        sonusSipPduManipulationProfileState   SonusAdminState,
        sonusSipPduManipulationProfileRowStatus       RowStatus
    }

sonusSipPduManipulationProfileIndex OBJECT-TYPE
    SYNTAX          Unsigned32 (1..32)
    MAX-ACCESS      read-only
    STATUS          current
    DESCRIPTION     
            "Identifies the SIP Pdu Manipulation profile."
    ::= { sonusSipPduManipulationProfileEntry 1 }

sonusSipPduManipulationProfileName OBJECT-TYPE
    SYNTAX          SonusName
    MAX-ACCESS      read-write
    STATUS          current
    DESCRIPTION     
            "The name of SIP Pdu Manipulation profile."
    ::= { sonusSipPduManipulationProfileEntry 2 }

sonusSipPduManipulationProfileState OBJECT-TYPE
    SYNTAX          SonusAdminState
    MAX-ACCESS      read-write
    STATUS          current
    DESCRIPTION     
            "The administrative state of this SIP Pdu Manipulation entry."
    ::= { sonusSipPduManipulationProfileEntry 3 }

sonusSipPduManipulationProfileRowStatus OBJECT-TYPE
    SYNTAX          RowStatus
    MAX-ACCESS      read-write
    STATUS          current
    DESCRIPTION     
            "row status object"
    ::= { sonusSipPduManipulationProfileEntry 4 }

sonusSipPduManipulationRuleTable OBJECT-TYPE
    SYNTAX          SEQUENCE OF SonusSipPduManipulationRuleEntry
    MAX-ACCESS      not-accessible
    STATUS          current
    DESCRIPTION     
            "A list of SIP Message Manipulation Profile entries."
    ::= { sonusSipPduManipulationMIBObjects 2 }

sonusSipPduManipulationRuleEntry OBJECT-TYPE
    SYNTAX          SonusSipPduManipulationRuleEntry
    MAX-ACCESS      not-accessible
    STATUS          current
    DESCRIPTION     
            "sonusSipiPduManipulationEntry contianing SIP message manipulation
             criterias, and actions"
    INDEX           { sonusSipPduManipulationRuleProfileIndex, 
                      sonusSipPduManipulationRuleIndex }
    ::= { sonusSipPduManipulationRuleTable 1 }

SonusSipPduManipulationRuleEntry ::=
    SEQUENCE {
        sonusSipPduManipulationRuleProfileIndex       Unsigned32,
        sonusSipPduManipulationRuleIndex Unsigned32,
        sonusSipPduManipulationRuleRowStatus    RowStatus,
        sonusSipPduManipulationRuleMatchHdrInstance           SonusSipSmmHdrInstance,
        sonusSipPduManipulationRuleMatchHdrRange        SonusSipSmmHdrRange
    }

sonusSipPduManipulationRuleProfileIndex OBJECT-TYPE
    SYNTAX          Unsigned32 (1..32)
    MAX-ACCESS      read-only
    STATUS          current
    DESCRIPTION     
            "Identifies the PDU Manipulation profile for this rule entry."
    ::= { sonusSipPduManipulationRuleEntry 1 }

sonusSipPduManipulationRuleIndex OBJECT-TYPE
    SYNTAX          Unsigned32 (1..32)
    MAX-ACCESS      read-only
    STATUS          current
    DESCRIPTION     
            "Identifies the PDU Manipulation rule within a PDU Manipulation profile."
    ::= { sonusSipPduManipulationRuleEntry 2 }

sonusSipPduManipulationRuleRowStatus OBJECT-TYPE
    SYNTAX          RowStatus
    MAX-ACCESS      read-write
    STATUS          current
    DESCRIPTION     
            "row status object"
    ::= { sonusSipPduManipulationRuleEntry 3 }

sonusSipPduManipulationRuleMatchHdrInstance OBJECT-TYPE
    SYNTAX          SonusSipSmmHdrInstance
    MAX-ACCESS      read-write
    STATUS          current
    DESCRIPTION     
            "Apply actions on matched header instance number. This header instance number will be applied 
             for all actions within a rule. It is a mandatory field and the default is the first 
             matched instance number (one)."
    DEFVAL          { one }
    ::= { sonusSipPduManipulationRuleEntry 4 }

sonusSipPduManipulationRuleMatchHdrRange OBJECT-TYPE
    SYNTAX          SonusSipSmmHdrRange
    MAX-ACCESS      read-write
    STATUS          current
    DESCRIPTION     
            "This is an optional upper range of the matching header instances. If this field is configured, 
             then each header instance from sonusSipPduManipulationRuleMatchHdrInstance to 
             sonusSipPduManipulationRuleMatchHdrRange will be applied for all actions within a rule."
    ::= { sonusSipPduManipulationRuleEntry 5 }

sonusSipPduManipulationCriterionTable OBJECT-TYPE
    SYNTAX          SEQUENCE OF SonusSipPduManipulationCriterionEntry
    MAX-ACCESS      not-accessible
    STATUS          current
    DESCRIPTION     
            "A list of SIP Message Manipulation criterion entries."
    ::= { sonusSipPduManipulationMIBObjects 3 }

sonusSipPduManipulationCriterionEntry OBJECT-TYPE
    SYNTAX          SonusSipPduManipulationCriterionEntry
    MAX-ACCESS      not-accessible
    STATUS          current
    DESCRIPTION     
            "This table describes the SIP PDU Manipalation Criterion."
    INDEX           { sonusSipPduManipulationCriterionProfileIndex, 
                      sonusSipPduManipulationCriterionRuleIndex, 
                      sonusSipPduManipulationCriterionTypeIndex, 
                      sonusSipPduManipulationCriterionIndex }
    ::= { sonusSipPduManipulationCriterionTable 1 }

SonusSipPduManipulationCriterionEntry ::=
    SEQUENCE {
        sonusSipPduManipulationCriterionProfileIndex            Unsigned32,
        sonusSipPduManipulationCriterionRuleIndex         Unsigned32,
        sonusSipPduManipulationCriterionTypeIndex         SonusSipSmmCriterionType,
        sonusSipPduManipulationCriterionIndex     Unsigned32,
        sonusSipPduManipulationMessageTypes   INTEGER,
        sonusSipPduManipulationMethodTypes  BITS,
        sonusSipPduManipulationStatusCode Unsigned32,
        sonusSipPduManipulationCriterionName    DisplayString,
        sonusSipPduManipulationCriterionValue     DisplayString,
        sonusSipPduManipulationCriterionCondition         INTEGER,
        sonusSipPduManipulationCriterionParamType         SonusSipSmmParamType,
        sonusSipPduManipulationCriterionToken     SonusSipSmmTokenType,
        sonusSipPduManipulationCriterionVariable        SonusSipSmmVariableType,
        sonusSipPduManipulationCriterionRowStatus         RowStatus,
        sonusSipPduManipulationCriterionHdrInstance           SonusSipSmmHdrInstance,
        sonusSipPduManipulationCriterionHdrRange        SonusSipSmmHdrRange,
        sonusSipPduManipulationStatusRange  Unsigned32,
        sonusSipPduManipulationCriterionTotalHdrInstances                 Unsigned32,
        sonusSipPduManipulationCriterionTotalHdrCondition                 INTEGER,
        sonusSipPduManipulationCriterionGlobalVariable              SonusSipSmmGlobalVariableType,
        sonusSipPduManipulationCriterionRegexString           DisplayString,
        sonusSipPduManipulationCriterionRegexNumMatch             INTEGER,
        sonusSipPduManipulationCriterionMsgBodyType           INTEGER
    }

sonusSipPduManipulationCriterionProfileIndex OBJECT-TYPE
    SYNTAX          Unsigned32 (1..32)
    MAX-ACCESS      read-only
    STATUS          current
    DESCRIPTION     
            "Identifies the SIP Pdu Manipulation criterion."
    ::= { sonusSipPduManipulationCriterionEntry 1 }

sonusSipPduManipulationCriterionRuleIndex OBJECT-TYPE
    SYNTAX          Unsigned32 (1..32)
    MAX-ACCESS      read-only
    STATUS          current
    DESCRIPTION     
            "Identifies the SIP Pdu Manipulation criterion."
    ::= { sonusSipPduManipulationCriterionEntry 2 }

sonusSipPduManipulationCriterionTypeIndex OBJECT-TYPE
    SYNTAX          SonusSipSmmCriterionType
    MAX-ACCESS      read-only
    STATUS          current
    DESCRIPTION     
            "Identifies the SIP PDU Manipulation criterion."
    ::= { sonusSipPduManipulationCriterionEntry 3 }

sonusSipPduManipulationCriterionIndex OBJECT-TYPE
    SYNTAX          Unsigned32 (1..10)
    MAX-ACCESS      read-only
    STATUS          current
    DESCRIPTION     
            "Identifies the SIP Pdu Manipulation criterion."
    ::= { sonusSipPduManipulationCriterionEntry 4 }

sonusSipPduManipulationMessageTypes OBJECT-TYPE
    SYNTAX          INTEGER { request(1), requestAll(2), response(3), 
                        responseAll(4), all(5) }
    MAX-ACCESS      read-write
    STATUS          current
    DESCRIPTION     
            "The SIP PDU manipulation message types of this rule entry."
    ::= { sonusSipPduManipulationCriterionEntry 5 }

sonusSipPduManipulationMethodTypes OBJECT-TYPE
    SYNTAX          BITS { options(0), cancel(1), invite(2), ack(3), 
                        prack(4), info(5), refer(6), bye(7), register(8), 
                        notify(9), subscribe(10), update(11), 
                        publish(12), message(13) }
    MAX-ACCESS      read-write
    STATUS          current
    DESCRIPTION     
            "The SIP PDU manipulation method types of this rule entry."
    DEFVAL          { {} }
    ::= { sonusSipPduManipulationCriterionEntry 6 }

sonusSipPduManipulationStatusCode OBJECT-TYPE
    SYNTAX          Unsigned32 (100..700)
    MAX-ACCESS      read-write
    STATUS          current
    DESCRIPTION     
            "The status code of SIP PDU manipulation rule"
    ::= { sonusSipPduManipulationCriterionEntry 7 }

sonusSipPduManipulationCriterionName OBJECT-TYPE
    SYNTAX          DisplayString (SIZE(1..128))
    MAX-ACCESS      read-write
    STATUS          current
    DESCRIPTION     
            "The header name or parameter name of this SIP PDU Manipulation criterion entry."
    ::= { sonusSipPduManipulationCriterionEntry 8 }

sonusSipPduManipulationCriterionValue OBJECT-TYPE
    SYNTAX          DisplayString (SIZE(1..128))
    MAX-ACCESS      read-write
    STATUS          current
    DESCRIPTION     
            "The criterion's value of this SIP PDU Manipulation criterion entry."
    ::= { sonusSipPduManipulationCriterionEntry 9 }

sonusSipPduManipulationCriterionCondition OBJECT-TYPE
    SYNTAX          INTEGER { exist(1), absent(2), has-value(3), 
                        not-equal-to(4), regex-match(5) }
    MAX-ACCESS      read-write
    STATUS          current
    DESCRIPTION     
            "The patten matching condition of this SIP PDU Manipulation criterion entry."
    ::= { sonusSipPduManipulationCriterionEntry 10 }

sonusSipPduManipulationCriterionParamType OBJECT-TYPE
    SYNTAX          SonusSipSmmParamType
    MAX-ACCESS      read-write
    STATUS          current
    DESCRIPTION     
            "Details the Parameter type of this SIP PDU Manipulation criterion entry."
    ::= { sonusSipPduManipulationCriterionEntry 11 }

sonusSipPduManipulationCriterionToken OBJECT-TYPE
    SYNTAX          SonusSipSmmTokenType
    MAX-ACCESS      read-write
    STATUS          current
    DESCRIPTION     
            "Details the token type of this SIP PDU Manipulation criterion entry."
    ::= { sonusSipPduManipulationCriterionEntry 12 }

sonusSipPduManipulationCriterionVariable OBJECT-TYPE
    SYNTAX          SonusSipSmmVariableType
    MAX-ACCESS      read-write
    STATUS          current
    DESCRIPTION     
            "Details the variable type of this SIP PDU Manipulation criterion entry."
    ::= { sonusSipPduManipulationCriterionEntry 13 }

sonusSipPduManipulationCriterionRowStatus OBJECT-TYPE
    SYNTAX          RowStatus
    MAX-ACCESS      read-write
    STATUS          current
    DESCRIPTION     
            "Row status object"
    ::= { sonusSipPduManipulationCriterionEntry 14 }

sonusSipPduManipulationCriterionHdrInstance OBJECT-TYPE
    SYNTAX          SonusSipSmmHdrInstance
    MAX-ACCESS      read-write
    STATUS          current
    DESCRIPTION     
            "Apply criteria on header instance number. This header instance number will be applied for
             to all the criteria within a rule. The default is all header instances."
    DEFVAL          { all }
    ::= { sonusSipPduManipulationCriterionEntry 15 }

sonusSipPduManipulationCriterionHdrRange OBJECT-TYPE
    SYNTAX          SonusSipSmmHdrRange
    MAX-ACCESS      read-write
    STATUS          current
    DESCRIPTION     
            "This is an optional upper range of header instances. If this field is configured,
             then each each header instance from sonusSipPduManipulationCriterionHdrInstance to
             sonusSipPduManipulationCriterionHdrRange will be applied to all the criteria within a rule"
    ::= { sonusSipPduManipulationCriterionEntry 16 }

sonusSipPduManipulationStatusRange OBJECT-TYPE
    SYNTAX          Unsigned32 (100..700)
    MAX-ACCESS      read-write
    STATUS          current
    DESCRIPTION     
            "The status code range of SIP PDU manipulation rule"
    ::= { sonusSipPduManipulationCriterionEntry 17 }

sonusSipPduManipulationCriterionTotalHdrInstances OBJECT-TYPE
    SYNTAX          Unsigned32 (1..32)
    MAX-ACCESS      read-write
    STATUS          current
    DESCRIPTION     
            "Criterion required to have total number of header instances"
    ::= { sonusSipPduManipulationCriterionEntry 18 }

sonusSipPduManipulationCriterionTotalHdrCondition OBJECT-TYPE
    SYNTAX          INTEGER { lessthan(1), greater(2), equal(3) }
    MAX-ACCESS      read-write
    STATUS          current
    DESCRIPTION     
            "The total number of headers matching condition"
    ::= { sonusSipPduManipulationCriterionEntry 19 }

sonusSipPduManipulationCriterionGlobalVariable OBJECT-TYPE
    SYNTAX          SonusSipSmmGlobalVariableType
    MAX-ACCESS      read-write
    STATUS          current
    DESCRIPTION     
            "Details the global variable type of this SIP PDU Manipulation criterion entry."
    ::= { sonusSipPduManipulationCriterionEntry 20 }

sonusSipPduManipulationCriterionRegexString OBJECT-TYPE
    SYNTAX          DisplayString (SIZE(0..128))
    MAX-ACCESS      read-write
    STATUS          current
    DESCRIPTION     
            "The regular expression text in criterion"
    ::= { sonusSipPduManipulationCriterionEntry 21 }

sonusSipPduManipulationCriterionRegexNumMatch OBJECT-TYPE
    SYNTAX          INTEGER { match(0), notmatch(16) }
    MAX-ACCESS      read-write
    STATUS          current
    DESCRIPTION     
            "number of match for regular expression"
    DEFVAL          { match }
    ::= { sonusSipPduManipulationCriterionEntry 22 }

sonusSipPduManipulationCriterionMsgBodyType OBJECT-TYPE
    SYNTAX          INTEGER { all(1) }
    MAX-ACCESS      read-write
    STATUS          current
    DESCRIPTION     
            "specifies message body type in the criterion"
    DEFVAL          { all }
    ::= { sonusSipPduManipulationCriterionEntry 23 }

sonusSipPduManipulationActionTable OBJECT-TYPE
    SYNTAX          SEQUENCE OF SonusSipPduManipulationActionEntry
    MAX-ACCESS      not-accessible
    STATUS          current
    DESCRIPTION     
            "A list of SIP Message Manipulation Action entries."
    ::= { sonusSipPduManipulationMIBObjects 4 }

sonusSipPduManipulationActionEntry OBJECT-TYPE
    SYNTAX          SonusSipPduManipulationActionEntry
    MAX-ACCESS      not-accessible
    STATUS          current
    DESCRIPTION     
            "This  "
    INDEX           { sonusSipPduManipulationActionProfileIndex, 
                      sonusSipPduManipulationActionRuleIndex, 
                      sonusSipPduManipulationActionIndex }
    ::= { sonusSipPduManipulationActionTable 1 }

SonusSipPduManipulationActionEntry ::=
    SEQUENCE {
        sonusSipPduManipulationActionProfileIndex         Unsigned32,
        sonusSipPduManipulationActionRuleIndex      Unsigned32,
        sonusSipPduManipulationActionIndex  Unsigned32,
        sonusSipPduManipulationActionType SonusSipSmmActionType,
        sonusSipPduManipulationActionOperationType          SonusSipSmmOperationType,
        sonusSipPduManipulationOpValueOrLine    INTEGER,
        sonusSipPduManipulationHeaderPosition     INTEGER,
        sonusSipPduManipulationParamType SonusSipSmmParamType,
        sonusSipPduManipulationFromType INTEGER,
        sonusSipPduManipulationToType   INTEGER,
        sonusSipPduManipulationFromString DisplayString,
        sonusSipPduManipulationToString DisplayString,
        sonusSipPduManipulationFromToken SonusSipSmmTokenType,
        sonusSipPduManipulationToToken  SonusSipSmmTokenType,
        sonusSipPduManipulationFromVariable   SonusSipSmmVariableType,
        sonusSipPduManipulationToVariable SonusSipSmmVariableType,
        sonusSipPduManipulationActionRowStatus      RowStatus,
        sonusSipPduManipulationRegexString  DisplayString,
        sonusSipPduManipulationRegexMatchInstance         INTEGER,
        sonusSipPduManipulationFromGlobalVariable         SonusSipSmmGlobalVariableType,
        sonusSipPduManipulationFromMsgBodyType      INTEGER,
        sonusSipPduManipulationToMsgBodyType    INTEGER,
        sonusSipPduManipulationToVariableRange      SonusSipSmmVariableType
    }

sonusSipPduManipulationActionProfileIndex OBJECT-TYPE
    SYNTAX          Unsigned32 (1..32)
    MAX-ACCESS      read-only
    STATUS          current
    DESCRIPTION     
            "Profile Identifier of this SIP PDU Manipulation action entry."
    ::= { sonusSipPduManipulationActionEntry 1 }

sonusSipPduManipulationActionRuleIndex OBJECT-TYPE
    SYNTAX          Unsigned32 (1..32)
    MAX-ACCESS      read-only
    STATUS          current
    DESCRIPTION     
            "Rule Identifier of this SIP PDU Manipulation action entry."
    ::= { sonusSipPduManipulationActionEntry 2 }

sonusSipPduManipulationActionIndex OBJECT-TYPE
    SYNTAX          Unsigned32 (1..10)
    MAX-ACCESS      read-only
    STATUS          current
    DESCRIPTION     
            "Action Identifier of this SIP PDU Manipulation action entry."
    ::= { sonusSipPduManipulationActionEntry 3 }

sonusSipPduManipulationActionType OBJECT-TYPE
    SYNTAX          SonusSipSmmActionType
    MAX-ACCESS      read-write
    STATUS          current
    DESCRIPTION     
            "The action type of this SIP PDU manipulation action entry."
    ::= { sonusSipPduManipulationActionEntry 4 }

sonusSipPduManipulationActionOperationType OBJECT-TYPE
    SYNTAX          SonusSipSmmOperationType
    MAX-ACCESS      read-write
    STATUS          current
    DESCRIPTION     
            "The action type of this SIP PDU manipulation action entry."
    ::= { sonusSipPduManipulationActionEntry 5 }

sonusSipPduManipulationOpValueOrLine OBJECT-TYPE
    SYNTAX          INTEGER { fieldValue(1), headerValue(2) }
    MAX-ACCESS      read-write
    STATUS          current
    DESCRIPTION     
            "The field details the header information of SIP header manipulation. It indicates whether the action apply to header value or field value."
    ::= { sonusSipPduManipulationActionEntry 6 }

sonusSipPduManipulationHeaderPosition OBJECT-TYPE
    SYNTAX          INTEGER { last(1), first(2) }
    MAX-ACCESS      read-write
    STATUS          current
    DESCRIPTION     
            "The header postion of add header action."
    ::= { sonusSipPduManipulationActionEntry 7 }

sonusSipPduManipulationParamType OBJECT-TYPE
    SYNTAX          SonusSipSmmParamType
    MAX-ACCESS      read-write
    STATUS          current
    DESCRIPTION     
            "Deatails the parameter type when this action entry applies to an parameter."
    ::= { sonusSipPduManipulationActionEntry 8 }

sonusSipPduManipulationFromType OBJECT-TYPE
    SYNTAX          INTEGER { token(1), string(2), variable(3), 
                        globalvar(4), msgbody(5) }
    MAX-ACCESS      read-write
    STATUS          current
    DESCRIPTION     
            "The from operand type of this action entry."
    ::= { sonusSipPduManipulationActionEntry 9 }

sonusSipPduManipulationToType OBJECT-TYPE
    SYNTAX          INTEGER { token(1), string(2), variable(3), 
                        msgbody(4) }
    MAX-ACCESS      read-write
    STATUS          current
    DESCRIPTION     
            "The to operand type of this action entry."
    ::= { sonusSipPduManipulationActionEntry 10 }

sonusSipPduManipulationFromString OBJECT-TYPE
    SYNTAX          DisplayString (SIZE(1..128))
    MAX-ACCESS      read-write
    STATUS          current
    DESCRIPTION     
            "The from string of this action entry."
    ::= { sonusSipPduManipulationActionEntry 11 }

sonusSipPduManipulationToString OBJECT-TYPE
    SYNTAX          DisplayString (SIZE(1..128))
    MAX-ACCESS      read-write
    STATUS          current
    DESCRIPTION     
            "The to string of this action entry."
    ::= { sonusSipPduManipulationActionEntry 12 }

sonusSipPduManipulationFromToken OBJECT-TYPE
    SYNTAX          SonusSipSmmTokenType
    MAX-ACCESS      read-write
    STATUS          current
    DESCRIPTION     
            "The from token of this action entry."
    ::= { sonusSipPduManipulationActionEntry 13 }

sonusSipPduManipulationToToken OBJECT-TYPE
    SYNTAX          SonusSipSmmTokenType
    MAX-ACCESS      read-write
    STATUS          current
    DESCRIPTION     
            "The to token of this action entry."
    ::= { sonusSipPduManipulationActionEntry 14 }

sonusSipPduManipulationFromVariable OBJECT-TYPE
    SYNTAX          SonusSipSmmVariableType
    MAX-ACCESS      read-write
    STATUS          current
    DESCRIPTION     
            "The from variable of this action entry."
    ::= { sonusSipPduManipulationActionEntry 15 }

sonusSipPduManipulationToVariable OBJECT-TYPE
    SYNTAX          SonusSipSmmVariableType
    MAX-ACCESS      read-write
    STATUS          current
    DESCRIPTION     
            "The to variable of this action entry."
    ::= { sonusSipPduManipulationActionEntry 16 }

sonusSipPduManipulationActionRowStatus OBJECT-TYPE
    SYNTAX          RowStatus
    MAX-ACCESS      read-write
    STATUS          current
    DESCRIPTION     
            "Row status object"
    ::= { sonusSipPduManipulationActionEntry 17 }

sonusSipPduManipulationRegexString OBJECT-TYPE
    SYNTAX          DisplayString (SIZE(0..128))
    MAX-ACCESS      read-write
    STATUS          current
    DESCRIPTION     
            "The regular expression text of this action entry."
    ::= { sonusSipPduManipulationActionEntry 18 }

sonusSipPduManipulationRegexMatchInstance OBJECT-TYPE
    SYNTAX          INTEGER { one(1), two(2), three(3), four(4), five(5), 
                        last(63), all(64) }
    MAX-ACCESS      read-write
    STATUS          current
    DESCRIPTION     
            "apply the action associated with a regualr expression to a particular match instance "
    DEFVAL          { one }
    ::= { sonusSipPduManipulationActionEntry 19 }

sonusSipPduManipulationFromGlobalVariable OBJECT-TYPE
    SYNTAX          SonusSipSmmGlobalVariableType
    MAX-ACCESS      read-write
    STATUS          current
    DESCRIPTION     
            "The from environment variable of this action entry."
    ::= { sonusSipPduManipulationActionEntry 20 }

sonusSipPduManipulationFromMsgBodyType OBJECT-TYPE
    SYNTAX          INTEGER { all(1) }
    MAX-ACCESS      read-write
    STATUS          current
    DESCRIPTION     
            "from msgbody content"
    DEFVAL          { all }
    ::= { sonusSipPduManipulationActionEntry 21 }

sonusSipPduManipulationToMsgBodyType OBJECT-TYPE
    SYNTAX          INTEGER { all(1) }
    MAX-ACCESS      read-write
    STATUS          current
    DESCRIPTION     
            "to msgbody content"
    DEFVAL          { all }
    ::= { sonusSipPduManipulationActionEntry 22 }

sonusSipPduManipulationToVariableRange OBJECT-TYPE
    SYNTAX          SonusSipSmmVariableType
    MAX-ACCESS      read-write
    STATUS          current
    DESCRIPTION     
            "The last of the variable use for store regex match."
    ::= { sonusSipPduManipulationActionEntry 23 }

END -- end of module SONUS-SIP-SMM-MIB.
