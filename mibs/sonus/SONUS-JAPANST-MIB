--
-- This SMIv2 module has been generated by smidump 0.2-cvs. Do not edit.
--

SONUS-JAPANST-MIB DEFINITIONS ::= BEGIN

IMPORTS
    Integer32, MODULE-IDENTITY, NOTIFICATION-TYPE, OBJECT-TYPE
        FROM SNMPv2-SMI
    RowStatus
        FROM SNMPv2-TC
    sonusDs1Index, sonusEventClass, sonusEventDescription, 
    sonusEventLevel, sonusEventTime, sonusPortIndex, sonusSequenceId, 
    sonusShelfIndex, sonusSlotIndex
        FROM SONUS-COMMON-MIB
    sonusCircuitMIBs
        FROM SONUS-SMI
    SonusAdminState, SonusShelfIndex, SonusSlotIndex
        FROM SONUS-TC;

sonusJapanSTFrameMIB MODULE-IDENTITY
    LAST-UPDATED    "200703280000Z"
    ORGANIZATION    
            "Sonus Networks, Inc."
    CONTACT-INFO    
            "   Customer Support    
             Sonus Networks, Inc.
             7 Technology Park Drive
             Westford, MA 01886
             USA
             
             Tel: 978-614-8100
             Fax: 978-614-8609"
    DESCRIPTION     
            "The MIB Module for Sonus Japan ST Framing extensions."
    ::= { sonusCircuitMIBs 4 }


sonusJapanSTFrameObjects OBJECT IDENTIFIER
    ::= { sonusJapanSTFrameMIB 1 }

sonusJapanSTFrameAdmn OBJECT IDENTIFIER
    ::= { sonusJapanSTFrameObjects 1 }

sonusJapanSTFrameAdmnTable OBJECT-TYPE
    SYNTAX          SEQUENCE OF SonusJapanSTFrameAdmnEntry
    MAX-ACCESS      not-accessible
    STATUS          current
    DESCRIPTION     
            "Sonus Japan ST Frame Admn Table"
    ::= { sonusJapanSTFrameAdmn 1 }

sonusJapanSTFrameAdmnEntry OBJECT-TYPE
    SYNTAX          SonusJapanSTFrameAdmnEntry
    MAX-ACCESS      not-accessible
    STATUS          current
    DESCRIPTION     
            "An entry in the Sonus Japan ST Frame Admn table."
    INDEX           { sonusJapanSTFrameAdmnShelfIndex, 
                      sonusJapanSTFrameAdmnSlotIndex, 
                      sonusJapanSTFrameAdmnPortIndex, 
                      sonusJapanSTFrameAdmnDs1Index }
    ::= { sonusJapanSTFrameAdmnTable 1 }

SonusJapanSTFrameAdmnEntry ::=
    SEQUENCE {
        sonusJapanSTFrameAdmnShelfIndex SonusShelfIndex,
        sonusJapanSTFrameAdmnSlotIndex  SonusSlotIndex,
        sonusJapanSTFrameAdmnPortIndex  Integer32,
        sonusJapanSTFrameAdmnDs1Index   Integer32,
        sonusJapanSTFrameAdmnRowStatus  RowStatus,
        sonusJapanSTFrameAdmnFrameFormat INTEGER,
        sonusJapanSTFrameAdmnDBitValue  INTEGER,
        sonusJapanSTFrameAdmnInitStatistics   SonusAdminState
    }

sonusJapanSTFrameAdmnShelfIndex OBJECT-TYPE
    SYNTAX          SonusShelfIndex
    MAX-ACCESS      read-only
    STATUS          current
    DESCRIPTION     
            "Shelf index for this table."
    ::= { sonusJapanSTFrameAdmnEntry 1 }

sonusJapanSTFrameAdmnSlotIndex OBJECT-TYPE
    SYNTAX          SonusSlotIndex
    MAX-ACCESS      read-only
    STATUS          current
    DESCRIPTION     
            "Slot index for this table."
    ::= { sonusJapanSTFrameAdmnEntry 2 }

sonusJapanSTFrameAdmnPortIndex OBJECT-TYPE
    SYNTAX          Integer32
    MAX-ACCESS      read-only
    STATUS          current
    DESCRIPTION     
            "Optical Port index for this table."
    ::= { sonusJapanSTFrameAdmnEntry 3 }

sonusJapanSTFrameAdmnDs1Index OBJECT-TYPE
    SYNTAX          Integer32
    MAX-ACCESS      read-only
    STATUS          current
    DESCRIPTION     
            "DS1 index for this table."
    ::= { sonusJapanSTFrameAdmnEntry 4 }

sonusJapanSTFrameAdmnRowStatus OBJECT-TYPE
    SYNTAX          RowStatus
    MAX-ACCESS      read-write
    STATUS          current
    DESCRIPTION     
            "This object is used to create, delete, or modify a row in this table."
    ::= { sonusJapanSTFrameAdmnEntry 5 }

sonusJapanSTFrameAdmnFrameFormat OBJECT-TYPE
    SYNTAX          INTEGER { xc(1), trunk(2) }
    MAX-ACCESS      read-write
    STATUS          current
    DESCRIPTION     
            "ST Frame format. Valid format types are XC and Trunk."
    DEFVAL          { trunk }
    ::= { sonusJapanSTFrameAdmnEntry 6 }

sonusJapanSTFrameAdmnDBitValue OBJECT-TYPE
    SYNTAX          INTEGER { allZero(1), allOne(2) }
    MAX-ACCESS      read-write
    STATUS          current
    DESCRIPTION     
            " Value sent in the D2-D4 bits."
    DEFVAL          { allOne }
    ::= { sonusJapanSTFrameAdmnEntry 7 }

sonusJapanSTFrameAdmnInitStatistics OBJECT-TYPE
    SYNTAX          SonusAdminState
    MAX-ACCESS      read-write
    STATUS          current
    DESCRIPTION     
            "Initializes error statistics counts to zero."
    DEFVAL          { disabled }
    ::= { sonusJapanSTFrameAdmnEntry 8 }

sonusJapanSTFrame OBJECT IDENTIFIER
    ::= { sonusJapanSTFrameObjects 2 }

sonusJapanSTFrameStatTable OBJECT-TYPE
    SYNTAX          SEQUENCE OF SonusJapanSTFrameStatEntry
    MAX-ACCESS      not-accessible
    STATUS          current
    DESCRIPTION     
            "Sonus Japan ST Framing Stat Table"
    ::= { sonusJapanSTFrame 1 }

sonusJapanSTFrameStatEntry OBJECT-TYPE
    SYNTAX          SonusJapanSTFrameStatEntry
    MAX-ACCESS      not-accessible
    STATUS          current
    DESCRIPTION     
            "An entry in the Sonus Japan ST Framing Stat table."
    INDEX           { sonusJapanSTFrameStatShelfIndex, 
                      sonusJapanSTFrameStatSlotIndex, 
                      sonusJapanSTFrameStatPortIndex, 
                      sonusJapanSTFrameStatDs1Index }
    ::= { sonusJapanSTFrameStatTable 1 }

SonusJapanSTFrameStatEntry ::=
    SEQUENCE {
        sonusJapanSTFrameStatShelfIndex SonusShelfIndex,
        sonusJapanSTFrameStatSlotIndex  SonusSlotIndex,
        sonusJapanSTFrameStatPortIndex  Integer32,
        sonusJapanSTFrameStatDs1Index   Integer32,
        sonusJapanSTFrameStatAlarmStatus Integer32,
        sonusJapanSTFrameStatBAISAlarmCount   Integer32
    }

sonusJapanSTFrameStatShelfIndex OBJECT-TYPE
    SYNTAX          SonusShelfIndex
    MAX-ACCESS      read-only
    STATUS          current
    DESCRIPTION     
            "Shelf index for this table."
    ::= { sonusJapanSTFrameStatEntry 1 }

sonusJapanSTFrameStatSlotIndex OBJECT-TYPE
    SYNTAX          SonusSlotIndex
    MAX-ACCESS      read-only
    STATUS          current
    DESCRIPTION     
            "Slot index for this table."
    ::= { sonusJapanSTFrameStatEntry 2 }

sonusJapanSTFrameStatPortIndex OBJECT-TYPE
    SYNTAX          Integer32
    MAX-ACCESS      read-only
    STATUS          current
    DESCRIPTION     
            "Optical Port index for this table."
    ::= { sonusJapanSTFrameStatEntry 3 }

sonusJapanSTFrameStatDs1Index OBJECT-TYPE
    SYNTAX          Integer32
    MAX-ACCESS      read-only
    STATUS          current
    DESCRIPTION     
            "DS1 index for this table."
    ::= { sonusJapanSTFrameStatEntry 4 }

sonusJapanSTFrameStatAlarmStatus OBJECT-TYPE
    SYNTAX          Integer32 (1..4)
    MAX-ACCESS      read-only
    STATUS          current
    DESCRIPTION     
            "Bitmap indicating the alarm status of the BAIS alarm (BA bit).
             1	noAlarm
             2	baisAlarm
             4	notMonitored"
    ::= { sonusJapanSTFrameStatEntry 5 }

sonusJapanSTFrameStatBAISAlarmCount OBJECT-TYPE
    SYNTAX          Integer32
    MAX-ACCESS      read-only
    STATUS          current
    DESCRIPTION     
            "Count of the number of BAIS alarms that have occured."
    ::= { sonusJapanSTFrameStatEntry 6 }

sonusJapanSTHdlGrpObjects OBJECT IDENTIFIER
    ::= { sonusJapanSTFrameMIB 2 }

sonusJapanSTHdlGrpAdmn OBJECT IDENTIFIER
    ::= { sonusJapanSTHdlGrpObjects 1 }

sonusJapanSTHdlGrpAdmnTable OBJECT-TYPE
    SYNTAX          SEQUENCE OF SonusJapanSTHdlGrpAdmnEntry
    MAX-ACCESS      not-accessible
    STATUS          current
    DESCRIPTION     
            "Sonus Japan ST Handling Group Admn Table"
    ::= { sonusJapanSTHdlGrpAdmn 1 }

sonusJapanSTHdlGrpAdmnEntry OBJECT-TYPE
    SYNTAX          SonusJapanSTHdlGrpAdmnEntry
    MAX-ACCESS      not-accessible
    STATUS          current
    DESCRIPTION     
            "An entry in the Sonus Japan ST Handling Group Admn table."
    INDEX           { sonusJapanSTHdlGrpAdmnShelfIndex, 
                      sonusJapanSTHdlGrpAdmnSlotIndex, 
                      sonusJapanSTHdlGrpAdmnPortIndex, 
                      sonusJapanSTHdlGrpAdmnDs1Index, 
                      sonusJapanSTHdlGrpAdmnHGIndex }
    ::= { sonusJapanSTHdlGrpAdmnTable 1 }

SonusJapanSTHdlGrpAdmnEntry ::=
    SEQUENCE {
        sonusJapanSTHdlGrpAdmnShelfIndex SonusShelfIndex,
        sonusJapanSTHdlGrpAdmnSlotIndex SonusSlotIndex,
        sonusJapanSTHdlGrpAdmnPortIndex Integer32,
        sonusJapanSTHdlGrpAdmnDs1Index  Integer32,
        sonusJapanSTHdlGrpAdmnHGIndex   Integer32,
        sonusJapanSTHdlGrpAdmnRowStatus RowStatus,
        sonusJapanSTHdlGrpAdmnSBitValue INTEGER,
        sonusJapanSTHdlGrpAdmnInitStatistics    SonusAdminState
    }

sonusJapanSTHdlGrpAdmnShelfIndex OBJECT-TYPE
    SYNTAX          SonusShelfIndex
    MAX-ACCESS      read-only
    STATUS          current
    DESCRIPTION     
            "Shelf index for this table."
    ::= { sonusJapanSTHdlGrpAdmnEntry 1 }

sonusJapanSTHdlGrpAdmnSlotIndex OBJECT-TYPE
    SYNTAX          SonusSlotIndex
    MAX-ACCESS      read-only
    STATUS          current
    DESCRIPTION     
            "Slot index for this table."
    ::= { sonusJapanSTHdlGrpAdmnEntry 2 }

sonusJapanSTHdlGrpAdmnPortIndex OBJECT-TYPE
    SYNTAX          Integer32
    MAX-ACCESS      read-only
    STATUS          current
    DESCRIPTION     
            "Optical Port index for this table."
    ::= { sonusJapanSTHdlGrpAdmnEntry 3 }

sonusJapanSTHdlGrpAdmnDs1Index OBJECT-TYPE
    SYNTAX          Integer32
    MAX-ACCESS      read-only
    STATUS          current
    DESCRIPTION     
            "DS1 index for this table."
    ::= { sonusJapanSTHdlGrpAdmnEntry 4 }

sonusJapanSTHdlGrpAdmnHGIndex OBJECT-TYPE
    SYNTAX          Integer32
    MAX-ACCESS      read-only
    STATUS          current
    DESCRIPTION     
            "Handling Group index for this table."
    ::= { sonusJapanSTHdlGrpAdmnEntry 5 }

sonusJapanSTHdlGrpAdmnRowStatus OBJECT-TYPE
    SYNTAX          RowStatus
    MAX-ACCESS      read-write
    STATUS          current
    DESCRIPTION     
            "This object is used to create, delete, or modify a row in this table."
    ::= { sonusJapanSTHdlGrpAdmnEntry 6 }

sonusJapanSTHdlGrpAdmnSBitValue OBJECT-TYPE
    SYNTAX          INTEGER { allZero(1), allOne(2) }
    MAX-ACCESS      read-write
    STATUS          current
    DESCRIPTION     
            " Value sent in the S1-S3 bits."
    DEFVAL          { allZero }
    ::= { sonusJapanSTHdlGrpAdmnEntry 7 }

sonusJapanSTHdlGrpAdmnInitStatistics OBJECT-TYPE
    SYNTAX          SonusAdminState
    MAX-ACCESS      read-write
    STATUS          current
    DESCRIPTION     
            "Initializes error statistics counts to zero."
    DEFVAL          { disabled }
    ::= { sonusJapanSTHdlGrpAdmnEntry 8 }

sonusJapanSTHdlGrp OBJECT IDENTIFIER
    ::= { sonusJapanSTHdlGrpObjects 2 }

sonusJapanSTHdlGrpStatTable OBJECT-TYPE
    SYNTAX          SEQUENCE OF SonusJapanSTHdlGrpStatEntry
    MAX-ACCESS      not-accessible
    STATUS          current
    DESCRIPTION     
            "Sonus Japan ST Handling Group Stat Table"
    ::= { sonusJapanSTHdlGrp 1 }

sonusJapanSTHdlGrpStatEntry OBJECT-TYPE
    SYNTAX          SonusJapanSTHdlGrpStatEntry
    MAX-ACCESS      not-accessible
    STATUS          current
    DESCRIPTION     
            "An entry in the Sonus Japan ST Handling Group Stat table."
    INDEX           { sonusJapanSTHdlGrpStatShelfIndex, 
                      sonusJapanSTHdlGrpStatSlotIndex, 
                      sonusJapanSTHdlGrpStatPortIndex, 
                      sonusJapanSTHdlGrpStatDs1Index, 
                      sonusJapanSTHdlGrpStatHGIndex }
    ::= { sonusJapanSTHdlGrpStatTable 1 }

SonusJapanSTHdlGrpStatEntry ::=
    SEQUENCE {
        sonusJapanSTHdlGrpStatShelfIndex SonusShelfIndex,
        sonusJapanSTHdlGrpStatSlotIndex SonusSlotIndex,
        sonusJapanSTHdlGrpStatPortIndex Integer32,
        sonusJapanSTHdlGrpStatDs1Index  Integer32,
        sonusJapanSTHdlGrpStatHGIndex   Integer32,
        sonusJapanSTHdlGrpStatAlarmStatus Integer32,
        sonusJapanSTHdlGrpStatRECAlarmCount   Integer32,
        sonusJapanSTHdlGrpStatAISAlarmCount   Integer32
    }

sonusJapanSTHdlGrpStatShelfIndex OBJECT-TYPE
    SYNTAX          SonusShelfIndex
    MAX-ACCESS      read-only
    STATUS          current
    DESCRIPTION     
            "Shelf index for this table."
    ::= { sonusJapanSTHdlGrpStatEntry 1 }

sonusJapanSTHdlGrpStatSlotIndex OBJECT-TYPE
    SYNTAX          SonusSlotIndex
    MAX-ACCESS      read-only
    STATUS          current
    DESCRIPTION     
            "Slot index for this table."
    ::= { sonusJapanSTHdlGrpStatEntry 2 }

sonusJapanSTHdlGrpStatPortIndex OBJECT-TYPE
    SYNTAX          Integer32
    MAX-ACCESS      read-only
    STATUS          current
    DESCRIPTION     
            "Optical Port index for this table."
    ::= { sonusJapanSTHdlGrpStatEntry 3 }

sonusJapanSTHdlGrpStatDs1Index OBJECT-TYPE
    SYNTAX          Integer32
    MAX-ACCESS      read-only
    STATUS          current
    DESCRIPTION     
            "DS1 index for this table."
    ::= { sonusJapanSTHdlGrpStatEntry 4 }

sonusJapanSTHdlGrpStatHGIndex OBJECT-TYPE
    SYNTAX          Integer32
    MAX-ACCESS      read-only
    STATUS          current
    DESCRIPTION     
            "Handling Group index for this table."
    ::= { sonusJapanSTHdlGrpStatEntry 5 }

sonusJapanSTHdlGrpStatAlarmStatus OBJECT-TYPE
    SYNTAX          Integer32 (1..512)
    MAX-ACCESS      read-only
    STATUS          current
    DESCRIPTION     
            "Bitmap indicating the alarm status of the HG AIS alarm (S0 bit),
             HG REC alarm (S0 bit), CH AIS alarm (S1-S3 bits), and CH BAIS
             alarm (S4-S6 bits).
             1	noAlarm
             2	hg15mAisAlarm
             3	hg15mRecAlarm
             4	chS1AisAlarm,
             5	chS2AisAlarm
             6	chS3AisAlarm
             7	chS4BAisAlarm
             8	chS5BAisAlarm
             9	chS6BAisAlarm
             10	notMonitored"
    ::= { sonusJapanSTHdlGrpStatEntry 6 }

sonusJapanSTHdlGrpStatRECAlarmCount OBJECT-TYPE
    SYNTAX          Integer32
    MAX-ACCESS      read-only
    STATUS          current
    DESCRIPTION     
            "Count of the number of HGREC alarms that have occured."
    ::= { sonusJapanSTHdlGrpStatEntry 7 }

sonusJapanSTHdlGrpStatAISAlarmCount OBJECT-TYPE
    SYNTAX          Integer32
    MAX-ACCESS      read-only
    STATUS          current
    DESCRIPTION     
            "Count of the number of HGAIS alarms that have occured."
    ::= { sonusJapanSTHdlGrpStatEntry 8 }

sonusJapanSTFrameNotifications OBJECT IDENTIFIER
    ::= { sonusJapanSTFrameMIB 3 }

sonusJapanSTFrameNotificationsPrefix OBJECT IDENTIFIER
    ::= { sonusJapanSTFrameNotifications 0 }

sonusJapanSTFrameNotificationsObjects OBJECT IDENTIFIER
    ::= { sonusJapanSTFrameNotifications 1 }

sonusHGIndex OBJECT-TYPE
    SYNTAX          Integer32 (1..4)
    MAX-ACCESS      read-only
    STATUS          current
    DESCRIPTION     
            "ST Frame Handling Group index."
    ::= { sonusJapanSTFrameNotificationsObjects 1 }

sonusSTFrameAlarmStatus OBJECT-TYPE
    SYNTAX          INTEGER { bAis(1), bAisClear(2), hgRec(3), 
                        hgRecClear(4), hgAis(5), hgAisClear(6) }
    MAX-ACCESS      read-only
    STATUS          current
    DESCRIPTION     
            "ST Frame alarm conditions."
    ::= { sonusJapanSTFrameNotificationsObjects 2 }

sonusJapanSTFrameAlarmNotification NOTIFICATION-TYPE
    OBJECTS         { sonusShelfIndex, sonusSlotIndex, sonusPortIndex, 
                      sonusDs1Index, sonusSTFrameAlarmStatus, 
                      sonusEventDescription, sonusEventClass, 
                      sonusEventLevel, sonusSequenceId, sonusEventTime }
    STATUS          current
    DESCRIPTION     
            "This trap indicates the ST Frame alarm state has changed."
    ::= { sonusJapanSTFrameNotificationsPrefix 1 }

sonusJapanSTHdlGrpAlarmNotification NOTIFICATION-TYPE
    OBJECTS         { sonusShelfIndex, sonusSlotIndex, sonusPortIndex, 
                      sonusDs1Index, sonusHGIndex, 
                      sonusSTFrameAlarmStatus, sonusEventDescription, 
                      sonusEventClass, sonusEventLevel, sonusSequenceId, 
                      sonusEventTime }
    STATUS          current
    DESCRIPTION     
            "This trap indicates the ST Frame Handling Group alarm state has changed."
    ::= { sonusJapanSTFrameNotificationsPrefix 2 }

END -- end of module SONUS-JAPANST-MIB.
