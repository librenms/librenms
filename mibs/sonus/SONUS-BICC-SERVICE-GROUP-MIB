--
-- This SMIv2 module has been generated by smidump 0.2-cvs. Do not edit.
--

SONUS-BICC-SERVICE-GROUP-MIB DEFINITIONS ::= BEGIN

IMPORTS
    Integer32, MODULE-IDENTITY, NOTIFICATION-TYPE, OBJECT-TYPE, 
    Unsigned32
        FROM SNMPv2-SMI
    DateAndTime, DisplayString, RowStatus
        FROM SNMPv2-TC
    sonusEventClass, sonusEventDescription, sonusEventLevel, 
    sonusEventTime, sonusSequenceId, sonusShelfIndex, sonusSlotIndex
        FROM SONUS-COMMON-MIB
    sonusSignallingMIBs
        FROM SONUS-SMI
    PointCode, SonusAdminState, SonusName, SonusNameReference, 
    SonusPointCode, SonusSupportFlag
        FROM SONUS-TC;

sonusBiccServiceGroupMIB MODULE-IDENTITY
    LAST-UPDATED    "201105110000Z"
    ORGANIZATION    
            "Sonus Networks, Inc."
    CONTACT-INFO    
            "   Customer Support    
             Sonus Networks, Inc.
             7 Technology Park Drive
             Westford, MA 01886
             USA
             
             Tel: 978-614-8100
             Fax: 978-614-8609"
    DESCRIPTION     
            "The MIB Module for BICC Service Group Management."
    ::= { sonusSignallingMIBs 13 }


sonusBiccServiceGroupMIBObjects OBJECT IDENTIFIER
    ::= { sonusBiccServiceGroupMIB 1 }

sonusBiccsgServiceGroup OBJECT IDENTIFIER
    ::= { sonusBiccServiceGroupMIBObjects 1 }

sonusBiccsgServiceGroupNextIndex OBJECT-TYPE
    SYNTAX          Integer32
    MAX-ACCESS      read-only
    STATUS          current
    DESCRIPTION     
            "The next valid index to use when creating a new sonusBiccsgServiceGroupEntry"
    ::= { sonusBiccsgServiceGroup 1 }

sonusBiccsgServiceGroupTable OBJECT-TYPE
    SYNTAX          SEQUENCE OF SonusBiccsgServiceGroupEntry
    MAX-ACCESS      not-accessible
    STATUS          current
    DESCRIPTION     
            "This table contains information about each BICC Service Group
             configured to be a member of the node. 
             
             A management entity may create rows for Service Group that are
             anticipated to be supported in the future."
    ::= { sonusBiccsgServiceGroup 2 }

sonusBiccsgServiceGroupEntry OBJECT-TYPE
    SYNTAX          SonusBiccsgServiceGroupEntry
    MAX-ACCESS      not-accessible
    STATUS          current
    DESCRIPTION     
            "This table describes the BICC Service Groups that are configured as
             members of the GSX9000 BICC Service Group."
    INDEX           { sonusBiccsgServiceGroupListIndex }
    ::= { sonusBiccsgServiceGroupTable 1 }

SonusBiccsgServiceGroupEntry ::=
    SEQUENCE {
        sonusBiccsgServiceGroupListIndex Integer32,
        sonusBiccsgServiceGroupName     SonusName,
        sonusBiccsgServiceGroupRemotePointCode      PointCode,
        sonusBiccsgServiceGroupTG       SonusNameReference,
        sonusBiccsgServiceGroupRevision INTEGER,
        sonusBiccsgServiceGroupHuntAlgorithm    INTEGER,
        sonusBiccsgServiceGroupCost     Integer32,
        sonusBiccsgServiceGroupCicControl INTEGER,
        sonusBiccsgServiceGroupOperation INTEGER,
        sonusBiccsgServiceGroupMode     INTEGER,
        sonusBiccsgServiceGroupAction   INTEGER,
        sonusBiccsgServiceGroupTimeout  Integer32,
        sonusBiccsgServiceGroupAdminState SonusAdminState,
        sonusBiccsgServiceGroupProfileName  DisplayString,
        sonusBiccsgServiceGroupRowStatus RowStatus,
        sonusBiccsgServiceGroupDiscTreatmentProfileName               SonusNameReference,
        sonusBiccsgServiceGroupGrsStartup INTEGER,
        sonusBiccsgServiceGroupRemPc    SonusPointCode,
        sonusBiccsgServiceGroupInspectionTime     DateAndTime,
        sonusBiccsgServiceGroupInspectionFreq     INTEGER,
        sonusBiccsgServiceGroupInspectionState      SonusAdminState,
        sonusBiccsgServiceGroupSignalingProfileName           SonusNameReference,
        sonusBiccsgServiceGroupInrInfProfileName        SonusNameReference,
        sonusBiccsgServiceGroupFarEndTestType     INTEGER,
        sonusBiccsgServiceGroupClusterRouting     INTEGER,
        sonusBiccsgServiceGroupAnsSupervisionTimeout            Integer32,
        sonusBiccsgServiceGroupAnsSupervisionTimeoutAction                  INTEGER,
        sonusBiccsgServiceGroupOverrideCutThruOnRcvAcmWithBciIw                       INTEGER,
        sonusBiccsgServiceGroupCrankBackProfile       Integer32,
        sonusBiccsgServiceGroupSequentialGRS    SonusSupportFlag,
        sonusBiccsgServiceGroupCongRelTimeout     Integer32,
        sonusBiccsgServiceGroupMessageThrottling        SonusSupportFlag,
        sonusBiccsgServiceGroupMessageThrottlingTimer             Integer32,
        sonusBiccsgServiceGroupCallCleanupCallsPerSegment                 Integer32,
        sonusBiccsgServiceGroupCallCleanupInterSegmentTimer                   Integer32,
        sonusBiccsgServiceGroupLdcTimeout Integer32,
        sonusBiccsgServiceGroupLdcAction INTEGER,
        sonusBiccsgServiceGroupLdcRelCause  Integer32,
        sonusBiccsgServiceGroupLdcEmergencyCalls        INTEGER,
        sonusBiccsgServiceGroupLocationOfREL34      INTEGER,
        sonusBiccsgServiceGroupLocationOfREL42      INTEGER,
        sonusBiccsgServiceGroupTandemLimitCounter         Integer32,
        sonusBiccsgServiceGroupIPBCPVersion   Integer32,
        sonusBiccsgServiceGroupLocationOfREL    INTEGER,
        sonusBiccsgServiceGroupDeleteIxcTcCode      DisplayString,
        sonusBiccsgServiceGroupSkipCrankBackProfile           Unsigned32,
        sonusBiccsgServiceGroupIpbcpT1  Integer32,
        sonusBiccsgServiceGroupIpbcpT2  Integer32,
        sonusBiccsgServiceGroupNIFGroupName   SonusNameReference,
        sonusBiccsgServiceGroupSourceAddressFiltering             SonusAdminState,
        sonusBiccsgServiceGroupHopCounterState      SonusAdminState,
        sonusBiccsgServiceGroupHopCounterValue      Integer32,
        sonusBiccsgServiceGroupDirectMediaAllowed         SonusAdminState,
        sonusBiccsgServiceGroupMediaZoneId  Integer32,
        sonusBiccsgServiceGroupMediaZoneName    SonusNameReference,
        sonusBiccsgServiceGroupSendXdmi SonusAdminState
    }

sonusBiccsgServiceGroupListIndex OBJECT-TYPE
    SYNTAX          Integer32 (1..3500)
    MAX-ACCESS      read-only
    STATUS          current
    DESCRIPTION     
            "The index of the BICC Service Group entry."
    ::= { sonusBiccsgServiceGroupEntry 1 }

sonusBiccsgServiceGroupName OBJECT-TYPE
    SYNTAX          SonusName
    MAX-ACCESS      read-write
    STATUS          current
    DESCRIPTION     
            "The name of the BICC Service Group."
    ::= { sonusBiccsgServiceGroupEntry 2 }

sonusBiccsgServiceGroupRemotePointCode OBJECT-TYPE
    SYNTAX          PointCode
    MAX-ACCESS      read-write
    STATUS          current
    DESCRIPTION     
            "Identifies the SS7 Point Code of the BICC Service Group in decimal format,
             the least significant three bytes representing Network-Cluster-Member values."
    ::= { sonusBiccsgServiceGroupEntry 3 }

sonusBiccsgServiceGroupTG OBJECT-TYPE
    SYNTAX          SonusNameReference
    MAX-ACCESS      read-write
    STATUS          current
    DESCRIPTION     
            "The Trunk Group, which the BICC Service Group belongs to."
    ::= { sonusBiccsgServiceGroupEntry 4 }

sonusBiccsgServiceGroupRevision OBJECT-TYPE
    SYNTAX          INTEGER { itu1997(6), chinacnc(27) }
    MAX-ACCESS      read-write
    STATUS          current
    DESCRIPTION     
            "The revision of the BICC protocol supported on this Service Group.
             Please Note:
             Values are assigned here for itu1997(6) and chinacnc(27), to maintain
             the consistency  for the rest of the values defined for Revision (as a part of ISUP).
             Please refer to /software/src/marlin/MIB/sonusIsupsg.smib"
    ::= { sonusBiccsgServiceGroupEntry 5 }

sonusBiccsgServiceGroupHuntAlgorithm OBJECT-TYPE
    SYNTAX          INTEGER { mostnleastidle(5) }
    MAX-ACCESS      read-write
    STATUS          current
    DESCRIPTION     
            "The hunting method used to select circuits for calls destined
             to the Service Group destination.
             Please Note:
             Values are assigned here for mostnleastidle(5), to maintain
             the consistency  for the rest of the values defined for Hunt Algorithm (as a part of ISUP).
             Please refer to /software/src/marlin/MIB/sonusIsupsg.smib"
    ::= { sonusBiccsgServiceGroupEntry 6 }

sonusBiccsgServiceGroupCost OBJECT-TYPE
    SYNTAX          Integer32 (0..100)
    MAX-ACCESS      read-write
    STATUS          current
    DESCRIPTION     
            "The routing cost to the BICC Service Group."
    ::= { sonusBiccsgServiceGroupEntry 7 }

sonusBiccsgServiceGroupCicControl OBJECT-TYPE
    SYNTAX          INTEGER { noCics(1), oddCics(2), evenCics(3), 
                        allCics(4) }
    MAX-ACCESS      read-write
    STATUS          current
    DESCRIPTION     
            "The CICs being controlled to resolve dual seizure."
    ::= { sonusBiccsgServiceGroupEntry 8 }

sonusBiccsgServiceGroupOperation OBJECT-TYPE
    SYNTAX          INTEGER { block(1), unblock(2), reset(3), 
                        undefined(4) }
    MAX-ACCESS      read-write
    STATUS          current
    DESCRIPTION     
            "The operation to be applied to the circuits in the BICC Service Group."
    ::= { sonusBiccsgServiceGroupEntry 9 }

sonusBiccsgServiceGroupMode OBJECT-TYPE
    SYNTAX          INTEGER { outOfService(1), inService(2) }
    MAX-ACCESS      read-write
    STATUS          current
    DESCRIPTION     
            "The mode of operation of circuits in the BICC Service Group."
    ::= { sonusBiccsgServiceGroupEntry 10 }

sonusBiccsgServiceGroupAction OBJECT-TYPE
    SYNTAX          INTEGER { dryUp(1), force(2), undefined(3) }
    MAX-ACCESS      read-write
    STATUS          current
    DESCRIPTION     
            "The action taken on the circuits in the BICC Service Group."
    ::= { sonusBiccsgServiceGroupEntry 11 }

sonusBiccsgServiceGroupTimeout OBJECT-TYPE
    SYNTAX          Integer32 (0..1440)
    MAX-ACCESS      read-write
    STATUS          current
    DESCRIPTION     
            "The timeout value in minutes for dryup action on the BICC Service Group."
    ::= { sonusBiccsgServiceGroupEntry 12 }

sonusBiccsgServiceGroupAdminState OBJECT-TYPE
    SYNTAX          SonusAdminState
    MAX-ACCESS      read-write
    STATUS          current
    DESCRIPTION     
            "The admin state of the BICC Service Group."
    ::= { sonusBiccsgServiceGroupEntry 13 }

sonusBiccsgServiceGroupProfileName OBJECT-TYPE
    SYNTAX          DisplayString (SIZE(0..23))
    MAX-ACCESS      read-write
    STATUS          current
    DESCRIPTION     
            "The BICC Service Group profile name."
    ::= { sonusBiccsgServiceGroupEntry 14 }

sonusBiccsgServiceGroupRowStatus OBJECT-TYPE
    SYNTAX          RowStatus
    MAX-ACCESS      read-write
    STATUS          current
    DESCRIPTION     
            ""
    ::= { sonusBiccsgServiceGroupEntry 15 }

sonusBiccsgServiceGroupDiscTreatmentProfileName OBJECT-TYPE
    SYNTAX          SonusNameReference
    MAX-ACCESS      read-write
    STATUS          current
    DESCRIPTION     
            "The disconnect treatment profile to be used for this service."
    ::= { sonusBiccsgServiceGroupEntry 16 }

sonusBiccsgServiceGroupGrsStartup OBJECT-TYPE
    SYNTAX          INTEGER { disabled(1), enabled(2) }
    MAX-ACCESS      read-write
    STATUS          current
    DESCRIPTION     
            "Specifies whether support is enabled or disabled for
             GRS/GRA at Startup for the BICC Service Group."
    ::= { sonusBiccsgServiceGroupEntry 17 }

sonusBiccsgServiceGroupRemPc OBJECT-TYPE
    SYNTAX          SonusPointCode
    MAX-ACCESS      read-write
    STATUS          current
    DESCRIPTION     
            "The Remote point code is not maintained as an OCTET STRING"
    ::= { sonusBiccsgServiceGroupEntry 18 }

sonusBiccsgServiceGroupInspectionTime OBJECT-TYPE
    SYNTAX          DateAndTime
    MAX-ACCESS      read-write
    STATUS          current
    DESCRIPTION     
            "Octet string that identifies the GMT time and date
             to start Periodic Circuit Inspection.
             
             	field  octects  contents    			  range
             	-----  -------  --------      			  -----
             1      1-2    year                      0..65536
             2       3     month                     1..12
             3       4     day                       1..31
             4       5     hour                      0..23
              5       6     minutes                   0..59
             6       7     seconds                   0..60
                        (use 60 for leap-second)
             7       8     deci-seconds              0..9
             8       9     direction from UTC        '+' / '-'
             9      10     hours from UTC            0..11
             10      11     minutes from UTC          0..59
             
             For example, Tuesday May 26, 1992 at 1:30:15 PM EDT would be
             displayed as:
             
             1992-5-26,13:30:15.0,-4:0
             
             * Notes:
             - the value of year is in network-byte order"
    ::= { sonusBiccsgServiceGroupEntry 19 }

sonusBiccsgServiceGroupInspectionFreq OBJECT-TYPE
    SYNTAX          INTEGER { onehour(1), threehours(2), sixhours(3), 
                        twelvehours(4), oneday(5), twodays(6) }
    MAX-ACCESS      read-write
    STATUS          current
    DESCRIPTION     
            ""
    DEFVAL          { oneday }
    ::= { sonusBiccsgServiceGroupEntry 20 }

sonusBiccsgServiceGroupInspectionState OBJECT-TYPE
    SYNTAX          SonusAdminState
    MAX-ACCESS      read-write
    STATUS          current
    DESCRIPTION     
            ""
    DEFVAL          { disabled }
    ::= { sonusBiccsgServiceGroupEntry 21 }

sonusBiccsgServiceGroupSignalingProfileName OBJECT-TYPE
    SYNTAX          SonusNameReference
    MAX-ACCESS      read-write
    STATUS          current
    DESCRIPTION     
            "The BICC Signaling Profile to be used for this service."
    ::= { sonusBiccsgServiceGroupEntry 22 }

sonusBiccsgServiceGroupInrInfProfileName OBJECT-TYPE
    SYNTAX          SonusNameReference
    MAX-ACCESS      read-write
    STATUS          current
    DESCRIPTION     
            "The BICC INR INF Profile to be used for this service."
    ::= { sonusBiccsgServiceGroupEntry 23 }

sonusBiccsgServiceGroupFarEndTestType OBJECT-TYPE
    SYNTAX          INTEGER { cqm(1), reset(3), undefined(4) }
    MAX-ACCESS      read-write
    STATUS          current
    DESCRIPTION     
            "The far end action taken on all BICC Circuit.
             Please Note:
             Values are assigned here for cqm(1), reset(3), undefined(4), to maintain
             the consistency  for the rest of the values defined for FarEnd Test Type (as a part of ISUP).
             Please refer to /software/src/marlin/MIB/sonusIsupsg.smib"
    ::= { sonusBiccsgServiceGroupEntry 24 }

sonusBiccsgServiceGroupClusterRouting OBJECT-TYPE
    SYNTAX          INTEGER { disabled(1), enabled(2) }
    MAX-ACCESS      read-write
    STATUS          current
    DESCRIPTION     
            "Specifies whether this DPC supports cluster routing or member routing."
    DEFVAL          { disabled }
    ::= { sonusBiccsgServiceGroupEntry 25 }

sonusBiccsgServiceGroupAnsSupervisionTimeout OBJECT-TYPE
    SYNTAX          Integer32 (0..1000)
    MAX-ACCESS      read-write
    STATUS          current
    DESCRIPTION     
            "This is the time from egress call setup to egress receiving an answer."
    DEFVAL          { 300 }
    ::= { sonusBiccsgServiceGroupEntry 26 }

sonusBiccsgServiceGroupAnsSupervisionTimeoutAction OBJECT-TYPE
    SYNTAX          INTEGER { release(1), trapAndRestart(3) }
    MAX-ACCESS      read-write
    STATUS          current
    DESCRIPTION     
            "This is the action to take if the answer supervision timer
             expires.  The call may be released, assumed to be answered or
             a trap can be fired and the timer restarted."
    DEFVAL          { release }
    ::= { sonusBiccsgServiceGroupEntry 27 }

sonusBiccsgServiceGroupOverrideCutThruOnRcvAcmWithBciIw OBJECT-TYPE
    SYNTAX          INTEGER { unsupported(1), backwardscutthru(2), 
                        fullduplexcutthru(3), nocutthru(4) }
    MAX-ACCESS      read-write
    STATUS          current
    DESCRIPTION     
            "Specifies whether to override protocol specific cut thru direction
             when ACM is received with BCI of Interworking Encountered.  If the
             override is set to unsupported, no override will occur.  If the 
             the override is set to fullduplexcutthru, full duplex cut through will
             occur.  If the override is set to nocutthru, no cut through change will
             be made."
    DEFVAL          { unsupported }
    ::= { sonusBiccsgServiceGroupEntry 28 }

sonusBiccsgServiceGroupCrankBackProfile OBJECT-TYPE
    SYNTAX          Integer32 (1..10)
    MAX-ACCESS      read-write
    STATUS          current
    DESCRIPTION     
            "The Crank Back Profile to be used for this Service."
    DEFVAL          { 1 }
    ::= { sonusBiccsgServiceGroupEntry 29 }

sonusBiccsgServiceGroupSequentialGRS OBJECT-TYPE
    SYNTAX          SonusSupportFlag
    MAX-ACCESS      read-write
    STATUS          current
    DESCRIPTION     
            "Is Sequential GRS Procedures Supported by this Service."
    DEFVAL          { unsupported }
    ::= { sonusBiccsgServiceGroupEntry 30 }

sonusBiccsgServiceGroupCongRelTimeout OBJECT-TYPE
    SYNTAX          Integer32 (0..5)
    MAX-ACCESS      read-write
    STATUS          current
    DESCRIPTION     
            "Time to delay sending of release during congestion."
    DEFVAL          { 0 }
    ::= { sonusBiccsgServiceGroupEntry 31 }

sonusBiccsgServiceGroupMessageThrottling OBJECT-TYPE
    SYNTAX          SonusSupportFlag
    MAX-ACCESS      read-write
    STATUS          current
    DESCRIPTION     
            "Is the procedure to throttle automatic message generation active for
             this service."
    DEFVAL          { unsupported }
    ::= { sonusBiccsgServiceGroupEntry 32 }

sonusBiccsgServiceGroupMessageThrottlingTimer OBJECT-TYPE
    SYNTAX          Integer32 (0..1000)
    MAX-ACCESS      read-write
    STATUS          current
    DESCRIPTION     
            "Time in miliseconds used by the message throttling inserted between messages
             which would otherwise be simultaneous."
    DEFVAL          { 0 }
    ::= { sonusBiccsgServiceGroupEntry 33 }

sonusBiccsgServiceGroupCallCleanupCallsPerSegment OBJECT-TYPE
    SYNTAX          Integer32 (1..25)
    MAX-ACCESS      read-write
    STATUS          current
    DESCRIPTION     
            "The number of calls to be cleaned up in before suspending."
    DEFVAL          { 25 }
    ::= { sonusBiccsgServiceGroupEntry 34 }

sonusBiccsgServiceGroupCallCleanupInterSegmentTimer OBJECT-TYPE
    SYNTAX          Integer32 (10..1000)
    MAX-ACCESS      read-write
    STATUS          current
    DESCRIPTION     
            "Time in miliseconds between cleaning up each consecutive group of calls."
    DEFVAL          { 100 }
    ::= { sonusBiccsgServiceGroupEntry 35 }

sonusBiccsgServiceGroupLdcTimeout OBJECT-TYPE
    SYNTAX          Integer32 (0..2880)
    MAX-ACCESS      read-write
    STATUS          current
    DESCRIPTION     
            "The timeout value of the long duration call timer in minutes.
             Allowed values are 0 to disable the timer, 60-2880 minutes to set the timer."
    DEFVAL          { 0 }
    ::= { sonusBiccsgServiceGroupEntry 36 }

sonusBiccsgServiceGroupLdcAction OBJECT-TYPE
    SYNTAX          INTEGER { noAction(0), trap(1), release(2), 
                        trapAndRelease(3) }
    MAX-ACCESS      read-write
    STATUS          current
    DESCRIPTION     
            "This is the action to take if the long duration call timer
             expires.  The call may be released or a trap fired, or both."
    DEFVAL          { noAction }
    ::= { sonusBiccsgServiceGroupEntry 37 }

sonusBiccsgServiceGroupLdcRelCause OBJECT-TYPE
    SYNTAX          Integer32 (1..127)
    MAX-ACCESS      read-write
    STATUS          current
    DESCRIPTION     
            "The Q.850 release value to use should the call be released 
             due to long duration call timer expiry"
    DEFVAL          { 41 }
    ::= { sonusBiccsgServiceGroupEntry 38 }

sonusBiccsgServiceGroupLdcEmergencyCalls OBJECT-TYPE
    SYNTAX          INTEGER { include(0), exclude(1) }
    MAX-ACCESS      read-write
    STATUS          current
    DESCRIPTION     
            "Whether Emergency Calls should be excluded from or included 
             in Long Duration Call Disconnect procedures"
    DEFVAL          { exclude }
    ::= { sonusBiccsgServiceGroupEntry 39 }

sonusBiccsgServiceGroupLocationOfREL34 OBJECT-TYPE
    SYNTAX          INTEGER { notUsed(0), user(1), privateLocal(2), 
                        publicLocal(3), transitNet(4), publicRemote(5), 
                        privateRemote(6), natReserved6(7), 
                        internationalNet(8), natReserved8(9), 
                        natReserved9(10), netBeyondInterPoint(11), 
                        natReserved11(12), natReserved12(13), 
                        natReserved13(14), natReserved14(15), 
                        natReserved15(16) }
    MAX-ACCESS      read-write
    STATUS          current
    DESCRIPTION     
            "Update the Location in the REL if Cause Value is 34"
    DEFVAL          { notUsed }
    ::= { sonusBiccsgServiceGroupEntry 40 }

sonusBiccsgServiceGroupLocationOfREL42 OBJECT-TYPE
    SYNTAX          INTEGER { notUsed(0), user(1), privateLocal(2), 
                        publicLocal(3), transitNet(4), publicRemote(5), 
                        privateRemote(6), natReserved6(7), 
                        internationalNet(8), natReserved8(9), 
                        natReserved9(10), netBeyondInterPoint(11), 
                        natReserved11(12), natReserved12(13), 
                        natReserved13(14), natReserved14(15), 
                        natReserved15(16) }
    MAX-ACCESS      read-write
    STATUS          current
    DESCRIPTION     
            "Update the Location in the REL if Cause Value is 42"
    DEFVAL          { notUsed }
    ::= { sonusBiccsgServiceGroupEntry 41 }

sonusBiccsgServiceGroupTandemLimitCounter OBJECT-TYPE
    SYNTAX          Integer32 (0..15)
    MAX-ACCESS      read-write
    STATUS          current
    DESCRIPTION     
            "Limit Counter to be set in outgoing IAM in Tandem Call Counter parameter in SBTM Network"
    DEFVAL          { 0 }
    ::= { sonusBiccsgServiceGroupEntry 42 }

sonusBiccsgServiceGroupIPBCPVersion OBJECT-TYPE
    SYNTAX          Integer32 (1..2)
    MAX-ACCESS      read-write
    STATUS          current
    DESCRIPTION     
            "Specifies the IPBCP Version supported"
    DEFVAL          { 2 }
    ::= { sonusBiccsgServiceGroupEntry 43 }

sonusBiccsgServiceGroupLocationOfREL OBJECT-TYPE
    SYNTAX          INTEGER { notUsed(0), user(1), privateLocal(2), 
                        publicLocal(3), transitNet(4), publicRemote(5), 
                        privateRemote(6), natReserved6(7), 
                        internationalNet(8), natReserved8(9), 
                        natReserved9(10), netBeyondInterPoint(11), 
                        natReserved11(12), natReserved12(13), 
                        natReserved13(14), natReserved14(15), 
                        natReserved15(16) }
    MAX-ACCESS      read-write
    STATUS          current
    DESCRIPTION     
            "Update the Location in the REL"
    DEFVAL          { notUsed }
    ::= { sonusBiccsgServiceGroupEntry 44 }

sonusBiccsgServiceGroupDeleteIxcTcCode OBJECT-TYPE
    SYNTAX          DisplayString (SIZE(0..4))
    MAX-ACCESS      read-write
    STATUS          current
    DESCRIPTION     
            "Delete the IXC/TC code in the CIT"
    ::= { sonusBiccsgServiceGroupEntry 45 }

sonusBiccsgServiceGroupSkipCrankBackProfile OBJECT-TYPE
    SYNTAX          Unsigned32 (0..10)
    MAX-ACCESS      read-write
    STATUS          current
    DESCRIPTION     
            "The Skip Crankback Profile to be used for this Service."
    DEFVAL          { 0 }
    ::= { sonusBiccsgServiceGroupEntry 46 }

sonusBiccsgServiceGroupIpbcpT1 OBJECT-TYPE
    SYNTAX          Integer32 (1..30)
    MAX-ACCESS      read-write
    STATUS          current
    DESCRIPTION     
            "Timer to guard IP bearer establishment"
    DEFVAL          { 15 }
    ::= { sonusBiccsgServiceGroupEntry 47 }

sonusBiccsgServiceGroupIpbcpT2 OBJECT-TYPE
    SYNTAX          Integer32 (1..30)
    MAX-ACCESS      read-write
    STATUS          current
    DESCRIPTION     
            "Timer to guard IP bearer establishment"
    DEFVAL          { 5 }
    ::= { sonusBiccsgServiceGroupEntry 48 }

sonusBiccsgServiceGroupNIFGroupName OBJECT-TYPE
    SYNTAX          SonusNameReference
    MAX-ACCESS      read-write
    STATUS          current
    DESCRIPTION     
            "Specifies the Media NIF Group Associated with BICC Service Group"
    ::= { sonusBiccsgServiceGroupEntry 49 }

sonusBiccsgServiceGroupSourceAddressFiltering OBJECT-TYPE
    SYNTAX          SonusAdminState
    MAX-ACCESS      read-write
    STATUS          current
    DESCRIPTION     
            "This object indicates whether or not the MSE will perform IP source
             address filtering on incoming media packets for this trunk group.
             When ENABLED, the SG will only accept incoming media packets whose
             source address matches the destination address of outbound packets.
             When DISABLED, the MSE does not filter the incoming media stream.
             The source address to filter on is supplied during call signaling."
    DEFVAL          { enabled }
    ::= { sonusBiccsgServiceGroupEntry 50 }

sonusBiccsgServiceGroupHopCounterState OBJECT-TYPE
    SYNTAX          SonusAdminState
    MAX-ACCESS      read-write
    STATUS          current
    DESCRIPTION     
            "The Hop Counter state for the BICC Service Group."
    ::= { sonusBiccsgServiceGroupEntry 51 }

sonusBiccsgServiceGroupHopCounterValue OBJECT-TYPE
    SYNTAX          Integer32 (0..31)
    MAX-ACCESS      read-write
    STATUS          current
    DESCRIPTION     
            "Specifies the value of the Hop Counter if initiated by the switch."
    ::= { sonusBiccsgServiceGroupEntry 52 }

sonusBiccsgServiceGroupDirectMediaAllowed OBJECT-TYPE
    SYNTAX          SonusAdminState
    MAX-ACCESS      read-write
    STATUS          current
    DESCRIPTION     
            "This indicates whether or not Direct Media should be attempted
             for calls to or from endpoints in this service group. If
             enabled, the GSX will attempt to set up the media path such
             that media flows directly between two Direct-Media-enabled 
             endpoints in the same media zone."
    DEFVAL          { disabled }
    ::= { sonusBiccsgServiceGroupEntry 53 }

sonusBiccsgServiceGroupMediaZoneId OBJECT-TYPE
    SYNTAX          Integer32 (0..32)
    MAX-ACCESS      read-write
    STATUS          current
    DESCRIPTION     
            "Identifies the Media Zone this BICC service group is bound to."
    DEFVAL          { 0 }
    ::= { sonusBiccsgServiceGroupEntry 54 }

sonusBiccsgServiceGroupMediaZoneName OBJECT-TYPE
    SYNTAX          SonusNameReference
    MAX-ACCESS      read-write
    STATUS          current
    DESCRIPTION     
            "The Media Zone to which this Bicc service group is bound."
    ::= { sonusBiccsgServiceGroupEntry 55 }

sonusBiccsgServiceGroupSendXdmi OBJECT-TYPE
    SYNTAX          SonusAdminState
    MAX-ACCESS      read-write
    STATUS          current
    DESCRIPTION     
            "This indicates whether or not to send the X-Dmi attribute in the IpBCP.
             If not allowed, it essentially says that This is the last leg in the Direct Media call. "
    DEFVAL          { disabled }
    ::= { sonusBiccsgServiceGroupEntry 56 }

sonusBiccsgServiceGroupStatTable OBJECT-TYPE
    SYNTAX          SEQUENCE OF SonusBiccsgServiceGroupStatEntry
    MAX-ACCESS      not-accessible
    STATUS          current
    DESCRIPTION     
            "This table contains status information about each BICC access point
             in the GSX9000 Switch node.  BICC Service Groups within the node can
             can be configured before SS7 connections is physically attached to
             the node.  The remote BICC user part may be unavailable or the SS7
             links to the destination may not be connected or correctly configured.
             Therefore, it is possible that an access point can be unavailable,
             and is absent."
    ::= { sonusBiccServiceGroupMIBObjects 2 }

sonusBiccsgServiceGroupStatEntry OBJECT-TYPE
    SYNTAX          SonusBiccsgServiceGroupStatEntry
    MAX-ACCESS      not-accessible
    STATUS          current
    DESCRIPTION     
            "This table describes the status of the Service Groups that are configured
             as destinations BICC nodes for the GSX9000 Switch node."
    INDEX           { sonusBiccsgServiceGroupStatListIndex }
    ::= { sonusBiccsgServiceGroupStatTable 1 }

SonusBiccsgServiceGroupStatEntry ::=
    SEQUENCE {
        sonusBiccsgServiceGroupStatListIndex    Integer32,
        sonusBiccsgServiceGroupStatName SonusNameReference,
        sonusBiccsgServiceGroupStatStatus INTEGER,
        sonusBiccsgServiceGroupStatLastInspectionTime             DateAndTime,
        sonusBiccsgServiceGroupStatNextInspectionTime             DateAndTime
    }

sonusBiccsgServiceGroupStatListIndex OBJECT-TYPE
    SYNTAX          Integer32 (0..3500)
    MAX-ACCESS      read-only
    STATUS          current
    DESCRIPTION     
            "The index of the BICC Service Group."
    ::= { sonusBiccsgServiceGroupStatEntry 1 }

sonusBiccsgServiceGroupStatName OBJECT-TYPE
    SYNTAX          SonusNameReference
    MAX-ACCESS      read-only
    STATUS          current
    DESCRIPTION     
            "The name of the BICC Service Group."
    ::= { sonusBiccsgServiceGroupStatEntry 2 }

sonusBiccsgServiceGroupStatStatus OBJECT-TYPE
    SYNTAX          INTEGER { available(1), unavailable(2), congested(3), 
                        congested2(4), congested3(5) }
    MAX-ACCESS      read-only
    STATUS          current
    DESCRIPTION     
            "The state of the BICC Service Group."
    ::= { sonusBiccsgServiceGroupStatEntry 3 }

sonusBiccsgServiceGroupStatLastInspectionTime OBJECT-TYPE
    SYNTAX          DateAndTime
    MAX-ACCESS      read-write
    STATUS          current
    DESCRIPTION     
            "Octet string that identifies the GMT time and date
             of the last Periodic Circuit Inspection.
             
             	field  octects  contents    			  range
             	-----  -------  --------      			  -----
             1      1-2    year                      0..65536
             2       3     month                     1..12
             3       4     day                       1..31
             4       5     hour                      0..23
              5       6     minutes                   0..59
             6       7     seconds                   0..60
                        (use 60 for leap-second)
             7       8     deci-seconds              0..9
             8       9     direction from UTC        '+' / '-'
             9      10     hours from UTC            0..11
             10      11     minutes from UTC          0..59
             
             For example, Tuesday May 26, 1992 at 1:30:15 PM EDT would be
             displayed as:
             
             1992-5-26,13:30:15.0,-4:0
             
             * Notes:
             - the value of year is in network-byte order"
    ::= { sonusBiccsgServiceGroupStatEntry 4 }

sonusBiccsgServiceGroupStatNextInspectionTime OBJECT-TYPE
    SYNTAX          DateAndTime
    MAX-ACCESS      read-write
    STATUS          current
    DESCRIPTION     
            "Octet string that identifies the GMT time and date
             of the next Periodic Circuit Inspection.
             
             	field  octects  contents    			  range
             	-----  -------  --------      			  -----
             1      1-2    year                      0..65536
             2       3     month                     1..12
             3       4     day                       1..31
             4       5     hour                      0..23
              5       6     minutes                   0..59
             6       7     seconds                   0..60
                        (use 60 for leap-second)
             7       8     deci-seconds              0..9
             8       9     direction from UTC        '+' / '-'
             9      10     hours from UTC            0..11
             10      11     minutes from UTC          0..59
             
             For example, Tuesday May 26, 1992 at 1:30:15 PM EDT would be
             displayed as:
             
             1992-5-26,13:30:15.0,-4:0
             
             * Notes:
             - the value of year is in network-byte order"
    ::= { sonusBiccsgServiceGroupStatEntry 5 }

sonusBiccsgSvcGrpProfile OBJECT IDENTIFIER
    ::= { sonusBiccServiceGroupMIBObjects 3 }

sonusBiccsgSvcGrpProfileNextIndex OBJECT-TYPE
    SYNTAX          Integer32
    MAX-ACCESS      read-only
    STATUS          current
    DESCRIPTION     
            "The next valid index to use when creating a new sonusBiccsgSvcGrpProfileEntry"
    ::= { sonusBiccsgSvcGrpProfile 1 }

sonusBiccsgSvcGrpProfileTable OBJECT-TYPE
    SYNTAX          SEQUENCE OF SonusBiccsgSvcGrpProfileEntry
    MAX-ACCESS      not-accessible
    STATUS          current
    DESCRIPTION     
            "This table contains BICC Service Group profiles."
    ::= { sonusBiccsgSvcGrpProfile 2 }

sonusBiccsgSvcGrpProfileEntry OBJECT-TYPE
    SYNTAX          SonusBiccsgSvcGrpProfileEntry
    MAX-ACCESS      not-accessible
    STATUS          current
    DESCRIPTION     
            "This table describes the Service Group profile."
    INDEX           { sonusBiccsgSvcGrpProfileListIndex }
    ::= { sonusBiccsgSvcGrpProfileTable 1 }

SonusBiccsgSvcGrpProfileEntry ::=
    SEQUENCE {
        sonusBiccsgSvcGrpProfileListIndex Integer32,
        sonusBiccsgSvcGrpProfileName    SonusName,
        sonusBiccsgSvcGrpProfileTG      SonusNameReference,
        sonusBiccsgSvcGrpProfileRevision INTEGER,
        sonusBiccsgSvcGrpProfileHuntAlgorithm     INTEGER,
        sonusBiccsgSvcGrpProfileCost    Integer32,
        sonusBiccsgSvcGrpProfileCicControl  INTEGER,
        sonusBiccsgSvcGrpProfileAdminState  SonusAdminState,
        sonusBiccsgSvcGrpProfileRowStatus RowStatus,
        sonusBiccsgSvcGrpProfileDiscTreatmentProfileName                SonusNameReference,
        sonusBiccsgSvcGrpProfileGrsStartup  INTEGER,
        sonusBiccsgSvcGrpProfileInspectionTime      DateAndTime,
        sonusBiccsgSvcGrpProfileInspectionFreq      INTEGER,
        sonusBiccsgSvcGrpProfileInspectionState       SonusAdminState,
        sonusBiccsgSvcGrpProfileSignalingProfileName            SonusNameReference,
        sonusBiccsgSvcGrpProfileInrInfProfileName         SonusNameReference,
        sonusBiccsgSvcGrpProfileClusterRouting      INTEGER,
        sonusBiccsgSvcGrpProfileAnsSupervisionTimeout             Integer32,
        sonusBiccsgSvcGrpProfileAnsSupervisionTimeoutAction                   INTEGER,
        sonusBiccsgSvcGrpProfileOverrideCutThruOnRcvAcmWithBciIw                        INTEGER,
        sonusBiccsgSvcGrpProfileCrankBackProfile        Integer32,
        sonusBiccsgSvcGrpProfileSequentialGRS     SonusSupportFlag,
        sonusBiccsgSvcGrpProfileCongRelTimeout      Integer32,
        sonusBiccsgSvcGrpProfileMessageThrottling         SonusSupportFlag,
        sonusBiccsgSvcGrpProfileMessageThrottlingTimer              Integer32,
        sonusBiccsgSvcGrpProfileCallCleanupCallsPerSegment                  Integer32,
        sonusBiccsgSvcGrpProfileCallCleanupInterSegmentTimer                    Integer32,
        sonusBiccsgSvcGrpProfileLdcTimeout  Integer32,
        sonusBiccsgSvcGrpProfileLdcAction INTEGER,
        sonusBiccsgSvcGrpProfileLdcRelCause   Integer32,
        sonusBiccsgSvcGrpProfileLdcEmergencyCalls         INTEGER,
        sonusBiccsgSvcGrpProfileLocationOfREL34       INTEGER,
        sonusBiccsgSvcGrpProfileLocationOfREL42       INTEGER,
        sonusBiccsgSvcGrpProfileTandemLimitCounter          Integer32,
        sonusBiccsgSvcGrpProfileIPBCPVersion    Integer32,
        sonusBiccsgSvcGrpProfileLocationOfREL     INTEGER,
        sonusBiccsgSvcGrpProfileDeleteIxcTcCode       DisplayString,
        sonusBiccsgSvcGrpProfileSkipCrankBackProfile            Unsigned32,
        sonusBiccsgSvcGrpProfileIpbcpT1 Integer32,
        sonusBiccsgSvcGrpProfileIpbcpT2 Integer32,
        sonusBiccsgSvcGrpProfileNIFGroupName    SonusNameReference,
        sonusBiccsgSvcGrpProfileSourceAddressFiltering              SonusAdminState,
        sonusBiccsgSvcGrpProfileHopCounterState       SonusAdminState,
        sonusBiccsgSvcGrpProfileHopCounterValue       Integer32
    }

sonusBiccsgSvcGrpProfileListIndex OBJECT-TYPE
    SYNTAX          Integer32 (0..127)
    MAX-ACCESS      read-only
    STATUS          current
    DESCRIPTION     
            "The index of the BICC Service Group Profile."
    ::= { sonusBiccsgSvcGrpProfileEntry 1 }

sonusBiccsgSvcGrpProfileName OBJECT-TYPE
    SYNTAX          SonusName
    MAX-ACCESS      read-write
    STATUS          current
    DESCRIPTION     
            "The name of the BICC Service Group Profile."
    ::= { sonusBiccsgSvcGrpProfileEntry 2 }

sonusBiccsgSvcGrpProfileTG OBJECT-TYPE
    SYNTAX          SonusNameReference
    MAX-ACCESS      read-write
    STATUS          current
    DESCRIPTION     
            "The Trunk Group, which the BICC Service Group belongs to."
    ::= { sonusBiccsgSvcGrpProfileEntry 3 }

sonusBiccsgSvcGrpProfileRevision OBJECT-TYPE
    SYNTAX          INTEGER { itu1997(6), chinacnc(27) }
    MAX-ACCESS      read-write
    STATUS          current
    DESCRIPTION     
            "The revision of the BICC protocol supported on this Service Group.
             Please Note:
             Values are assigned here for itu1997(6) and chinacnc(27), to maintain
             the consistency  for the rest of the values defined for Revision (as a part of ISUP).
             Please refer to /software/src/marlin/MIB/sonusIsupsg.smib"
    ::= { sonusBiccsgSvcGrpProfileEntry 4 }

sonusBiccsgSvcGrpProfileHuntAlgorithm OBJECT-TYPE
    SYNTAX          INTEGER { mostnleastidle(5) }
    MAX-ACCESS      read-write
    STATUS          current
    DESCRIPTION     
            "The hunting method used to select circuits for calls destined
             to the Service Group destination.
             Please Note:
             Values are assigned here for mostnleastidle(5), to maintain
             the consistency  for the rest of the values defined for Hunt Algorithm (as a part of ISUP).
             Please refer to /software/src/marlin/MIB/sonusIsupsg.smib"
    ::= { sonusBiccsgSvcGrpProfileEntry 5 }

sonusBiccsgSvcGrpProfileCost OBJECT-TYPE
    SYNTAX          Integer32 (0..100)
    MAX-ACCESS      read-write
    STATUS          current
    DESCRIPTION     
            "The routing cost to the BICC Service Group."
    ::= { sonusBiccsgSvcGrpProfileEntry 6 }

sonusBiccsgSvcGrpProfileCicControl OBJECT-TYPE
    SYNTAX          INTEGER { noCics(1), oddCics(2), evenCics(3), 
                        allCics(4) }
    MAX-ACCESS      read-write
    STATUS          current
    DESCRIPTION     
            "The CICs being controlled to resolve dual seizure."
    ::= { sonusBiccsgSvcGrpProfileEntry 7 }

sonusBiccsgSvcGrpProfileAdminState OBJECT-TYPE
    SYNTAX          SonusAdminState
    MAX-ACCESS      read-write
    STATUS          current
    DESCRIPTION     
            "The admin state of the BICC Service Group Profile."
    ::= { sonusBiccsgSvcGrpProfileEntry 8 }

sonusBiccsgSvcGrpProfileRowStatus OBJECT-TYPE
    SYNTAX          RowStatus
    MAX-ACCESS      read-write
    STATUS          current
    DESCRIPTION     
            ""
    ::= { sonusBiccsgSvcGrpProfileEntry 9 }

sonusBiccsgSvcGrpProfileDiscTreatmentProfileName OBJECT-TYPE
    SYNTAX          SonusNameReference
    MAX-ACCESS      read-write
    STATUS          current
    DESCRIPTION     
            "The disconnect treatment profile to be used for this service."
    ::= { sonusBiccsgSvcGrpProfileEntry 10 }

sonusBiccsgSvcGrpProfileGrsStartup OBJECT-TYPE
    SYNTAX          INTEGER { disabled(1), enabled(2) }
    MAX-ACCESS      read-write
    STATUS          current
    DESCRIPTION     
            "Specifies whether support is enabled or disabled for
             GRS/GRA at Startup for the BICC Service Group."
    ::= { sonusBiccsgSvcGrpProfileEntry 11 }

sonusBiccsgSvcGrpProfileInspectionTime OBJECT-TYPE
    SYNTAX          DateAndTime
    MAX-ACCESS      read-write
    STATUS          current
    DESCRIPTION     
            "Octet string that identifies the GMT time and date
             to start Periodic Circuit Inspection.
             
             	field  octects  contents    			  range
             	-----  -------  --------      			  -----
             1      1-2    year                      0..65536
             2       3     month                     1..12
             3       4     day                       1..31
             4       5     hour                      0..23
              5       6     minutes                   0..59
             6       7     seconds                   0..60
                        (use 60 for leap-second)
             7       8     deci-seconds              0..9
             8       9     direction from UTC        '+' / '-'
             9      10     hours from UTC            0..11
             10      11     minutes from UTC          0..59
             
             For example, Tuesday May 26, 1992 at 1:30:15 PM EDT would be
             displayed as:
             
             1992-5-26,13:30:15.0,-4:0
             
             * Notes:
             - the value of year is in network-byte order"
    ::= { sonusBiccsgSvcGrpProfileEntry 12 }

sonusBiccsgSvcGrpProfileInspectionFreq OBJECT-TYPE
    SYNTAX          INTEGER { onehour(1), threehours(2), sixhours(3), 
                        twelvehours(4), oneday(5), twodays(6) }
    MAX-ACCESS      read-write
    STATUS          current
    DESCRIPTION     
            ""
    DEFVAL          { oneday }
    ::= { sonusBiccsgSvcGrpProfileEntry 13 }

sonusBiccsgSvcGrpProfileInspectionState OBJECT-TYPE
    SYNTAX          SonusAdminState
    MAX-ACCESS      read-write
    STATUS          current
    DESCRIPTION     
            ""
    DEFVAL          { disabled }
    ::= { sonusBiccsgSvcGrpProfileEntry 14 }

sonusBiccsgSvcGrpProfileSignalingProfileName OBJECT-TYPE
    SYNTAX          SonusNameReference
    MAX-ACCESS      read-write
    STATUS          current
    DESCRIPTION     
            "The BICC Signaling Profile to be used for this service."
    ::= { sonusBiccsgSvcGrpProfileEntry 15 }

sonusBiccsgSvcGrpProfileInrInfProfileName OBJECT-TYPE
    SYNTAX          SonusNameReference
    MAX-ACCESS      read-write
    STATUS          current
    DESCRIPTION     
            "The BICC INR INF Profile to be used for this service."
    ::= { sonusBiccsgSvcGrpProfileEntry 16 }

sonusBiccsgSvcGrpProfileClusterRouting OBJECT-TYPE
    SYNTAX          INTEGER { disabled(1), enabled(2) }
    MAX-ACCESS      read-write
    STATUS          current
    DESCRIPTION     
            "Specifies whether this DPC supports cluster routing or member routing"
    DEFVAL          { disabled }
    ::= { sonusBiccsgSvcGrpProfileEntry 17 }

sonusBiccsgSvcGrpProfileAnsSupervisionTimeout OBJECT-TYPE
    SYNTAX          Integer32 (0..1000)
    MAX-ACCESS      read-write
    STATUS          current
    DESCRIPTION     
            "This is the time from egress call setup to egress receiving an answer,
             used for both user and network sides."
    DEFVAL          { 300 }
    ::= { sonusBiccsgSvcGrpProfileEntry 18 }

sonusBiccsgSvcGrpProfileAnsSupervisionTimeoutAction OBJECT-TYPE
    SYNTAX          INTEGER { release(1), trapAndRestart(2) }
    MAX-ACCESS      read-write
    STATUS          current
    DESCRIPTION     
            "This is the action to take if the answer supervision timer
             expires.  The call may be released, assumed to be answered or
             a trap can be fired and the timer restarted."
    DEFVAL          { release }
    ::= { sonusBiccsgSvcGrpProfileEntry 19 }

sonusBiccsgSvcGrpProfileOverrideCutThruOnRcvAcmWithBciIw OBJECT-TYPE
    SYNTAX          INTEGER { unsupported(1), backwardscutthru(2), 
                        fullduplexcutthru(3), nocutthru(4) }
    MAX-ACCESS      read-write
    STATUS          current
    DESCRIPTION     
            "Specifies whether to override protocol specific cut thru direction
             when ACM is received with BCI of Interworking Encountered.  If the
             override is set to unsupported, no override will occur.  If the 
             the override is set to fullduplexcutthru, full duplex cut through will
             occur.  If the override is set to nocutthru, no cut through change will
             be made."
    DEFVAL          { unsupported }
    ::= { sonusBiccsgSvcGrpProfileEntry 20 }

sonusBiccsgSvcGrpProfileCrankBackProfile OBJECT-TYPE
    SYNTAX          Integer32 (1..10)
    MAX-ACCESS      read-write
    STATUS          current
    DESCRIPTION     
            "The Crank Back Profile to be used for this Service."
    DEFVAL          { 1 }
    ::= { sonusBiccsgSvcGrpProfileEntry 21 }

sonusBiccsgSvcGrpProfileSequentialGRS OBJECT-TYPE
    SYNTAX          SonusSupportFlag
    MAX-ACCESS      read-write
    STATUS          current
    DESCRIPTION     
            "Is Sequential GRS Procedures Supported by this Service."
    DEFVAL          { unsupported }
    ::= { sonusBiccsgSvcGrpProfileEntry 22 }

sonusBiccsgSvcGrpProfileCongRelTimeout OBJECT-TYPE
    SYNTAX          Integer32 (0..5)
    MAX-ACCESS      read-write
    STATUS          current
    DESCRIPTION     
            "Time to delay sending of release during congestion."
    DEFVAL          { 0 }
    ::= { sonusBiccsgSvcGrpProfileEntry 23 }

sonusBiccsgSvcGrpProfileMessageThrottling OBJECT-TYPE
    SYNTAX          SonusSupportFlag
    MAX-ACCESS      read-write
    STATUS          current
    DESCRIPTION     
            "Is the procedure to throttle automatic message generation active for
             this service."
    DEFVAL          { unsupported }
    ::= { sonusBiccsgSvcGrpProfileEntry 24 }

sonusBiccsgSvcGrpProfileMessageThrottlingTimer OBJECT-TYPE
    SYNTAX          Integer32 (0..1000)
    MAX-ACCESS      read-write
    STATUS          current
    DESCRIPTION     
            "Time in miliseconds used by the message throttling - inserted between messages
             which would otherwise be simultaneous."
    DEFVAL          { 0 }
    ::= { sonusBiccsgSvcGrpProfileEntry 25 }

sonusBiccsgSvcGrpProfileCallCleanupCallsPerSegment OBJECT-TYPE
    SYNTAX          Integer32 (1..25)
    MAX-ACCESS      read-write
    STATUS          current
    DESCRIPTION     
            "The number of calls to be cleaned up before suspending."
    DEFVAL          { 25 }
    ::= { sonusBiccsgSvcGrpProfileEntry 26 }

sonusBiccsgSvcGrpProfileCallCleanupInterSegmentTimer OBJECT-TYPE
    SYNTAX          Integer32 (10..1000)
    MAX-ACCESS      read-write
    STATUS          current
    DESCRIPTION     
            "Time in miliseconds between cleaning up each consecutive group of calls."
    DEFVAL          { 100 }
    ::= { sonusBiccsgSvcGrpProfileEntry 27 }

sonusBiccsgSvcGrpProfileLdcTimeout OBJECT-TYPE
    SYNTAX          Integer32 (0..2880)
    MAX-ACCESS      read-write
    STATUS          current
    DESCRIPTION     
            "The timeout value of the long duration call timer in minutes. 
             Allowed values are 0 to disable the timer, 60-2880 minutes to set the timer."
    DEFVAL          { 0 }
    ::= { sonusBiccsgSvcGrpProfileEntry 28 }

sonusBiccsgSvcGrpProfileLdcAction OBJECT-TYPE
    SYNTAX          INTEGER { noAction(0), trap(1), release(2), 
                        trapAndRelease(3) }
    MAX-ACCESS      read-write
    STATUS          current
    DESCRIPTION     
            "This is the action to take if the long duration call timer
             expires.  The call may be released or a trap fired, or both."
    DEFVAL          { noAction }
    ::= { sonusBiccsgSvcGrpProfileEntry 29 }

sonusBiccsgSvcGrpProfileLdcRelCause OBJECT-TYPE
    SYNTAX          Integer32 (1..127)
    MAX-ACCESS      read-write
    STATUS          current
    DESCRIPTION     
            "The Q.850 release value to use should the call be released 
             due to long duration call timer expiry"
    DEFVAL          { 41 }
    ::= { sonusBiccsgSvcGrpProfileEntry 30 }

sonusBiccsgSvcGrpProfileLdcEmergencyCalls OBJECT-TYPE
    SYNTAX          INTEGER { include(0), exclude(1) }
    MAX-ACCESS      read-write
    STATUS          current
    DESCRIPTION     
            "Whether Emergency Calls should be excluded from or included 
             in Long Duration Call Disconnect procedures"
    DEFVAL          { exclude }
    ::= { sonusBiccsgSvcGrpProfileEntry 31 }

sonusBiccsgSvcGrpProfileLocationOfREL34 OBJECT-TYPE
    SYNTAX          INTEGER { notUsed(0), user(1), privateLocal(2), 
                        publicLocal(3), transitNet(4), publicRemote(5), 
                        privateRemote(6), natReserved6(7), 
                        internationalNet(8), natReserved8(9), 
                        natReserved9(10), netBeyondInterPoint(11), 
                        natReserved11(12), natReserved12(13), 
                        natReserved13(14), natReserved14(15), 
                        natReserved15(16) }
    MAX-ACCESS      read-write
    STATUS          current
    DESCRIPTION     
            "Update the Location in the REL if Cause Value is 34"
    DEFVAL          { notUsed }
    ::= { sonusBiccsgSvcGrpProfileEntry 32 }

sonusBiccsgSvcGrpProfileLocationOfREL42 OBJECT-TYPE
    SYNTAX          INTEGER { notUsed(0), user(1), privateLocal(2), 
                        publicLocal(3), transitNet(4), publicRemote(5), 
                        privateRemote(6), natReserved6(7), 
                        internationalNet(8), natReserved8(9), 
                        natReserved9(10), netBeyondInterPoint(11), 
                        natReserved11(12), natReserved12(13), 
                        natReserved13(14), natReserved14(15), 
                        natReserved15(16) }
    MAX-ACCESS      read-write
    STATUS          current
    DESCRIPTION     
            "Update the Location in the REL if Cause Value is 42"
    DEFVAL          { notUsed }
    ::= { sonusBiccsgSvcGrpProfileEntry 33 }

sonusBiccsgSvcGrpProfileTandemLimitCounter OBJECT-TYPE
    SYNTAX          Integer32 (0..15)
    MAX-ACCESS      read-write
    STATUS          current
    DESCRIPTION     
            "Limit Counter to be set in outgoing IAM in Tandem Call Counter parameter in SBTM Network"
    DEFVAL          { 0 }
    ::= { sonusBiccsgSvcGrpProfileEntry 34 }

sonusBiccsgSvcGrpProfileIPBCPVersion OBJECT-TYPE
    SYNTAX          Integer32 (1..2)
    MAX-ACCESS      read-write
    STATUS          current
    DESCRIPTION     
            "Specifies the IBPCP Version supported"
    DEFVAL          { 2 }
    ::= { sonusBiccsgSvcGrpProfileEntry 35 }

sonusBiccsgSvcGrpProfileLocationOfREL OBJECT-TYPE
    SYNTAX          INTEGER { notUsed(0), user(1), privateLocal(2), 
                        publicLocal(3), transitNet(4), publicRemote(5), 
                        privateRemote(6), natReserved6(7), 
                        internationalNet(8), natReserved8(9), 
                        natReserved9(10), netBeyondInterPoint(11), 
                        natReserved11(12), natReserved12(13), 
                        natReserved13(14), natReserved14(15), 
                        natReserved15(16) }
    MAX-ACCESS      read-write
    STATUS          current
    DESCRIPTION     
            "Update the Location in the REL"
    DEFVAL          { notUsed }
    ::= { sonusBiccsgSvcGrpProfileEntry 36 }

sonusBiccsgSvcGrpProfileDeleteIxcTcCode OBJECT-TYPE
    SYNTAX          DisplayString (SIZE(0..4))
    MAX-ACCESS      read-write
    STATUS          current
    DESCRIPTION     
            "Delete the IXC/TC code in the CIT"
    ::= { sonusBiccsgSvcGrpProfileEntry 37 }

sonusBiccsgSvcGrpProfileSkipCrankBackProfile OBJECT-TYPE
    SYNTAX          Unsigned32 (0..10)
    MAX-ACCESS      read-write
    STATUS          current
    DESCRIPTION     
            "The Skip Crankback Profile to be used for this Service."
    DEFVAL          { 0 }
    ::= { sonusBiccsgSvcGrpProfileEntry 38 }

sonusBiccsgSvcGrpProfileIpbcpT1 OBJECT-TYPE
    SYNTAX          Integer32 (1..30)
    MAX-ACCESS      read-write
    STATUS          current
    DESCRIPTION     
            "Timer to guard IP bearer establishment"
    DEFVAL          { 5 }
    ::= { sonusBiccsgSvcGrpProfileEntry 39 }

sonusBiccsgSvcGrpProfileIpbcpT2 OBJECT-TYPE
    SYNTAX          Integer32 (1..30)
    MAX-ACCESS      read-write
    STATUS          current
    DESCRIPTION     
            "Timer to guard IP bearer establishment"
    DEFVAL          { 5 }
    ::= { sonusBiccsgSvcGrpProfileEntry 40 }

sonusBiccsgSvcGrpProfileNIFGroupName OBJECT-TYPE
    SYNTAX          SonusNameReference
    MAX-ACCESS      read-write
    STATUS          current
    DESCRIPTION     
            "Specifies the Media NIF Group Associated with BICC Service Group"
    ::= { sonusBiccsgSvcGrpProfileEntry 41 }

sonusBiccsgSvcGrpProfileSourceAddressFiltering OBJECT-TYPE
    SYNTAX          SonusAdminState
    MAX-ACCESS      read-write
    STATUS          current
    DESCRIPTION     
            "This object indicates whether or not the MSE will perform IP source
             address filtering on incoming media packets for this trunk group.
             When ENABLED, the SG will only accept incoming media packets whose
             source address matches the destination address of outbound packets.
             When DISABLED, the MSE does not filter the incoming media stream.
             The source address to filter on is supplied during call signaling."
    DEFVAL          { enabled }
    ::= { sonusBiccsgSvcGrpProfileEntry 42 }

sonusBiccsgSvcGrpProfileHopCounterState OBJECT-TYPE
    SYNTAX          SonusAdminState
    MAX-ACCESS      read-write
    STATUS          current
    DESCRIPTION     
            "The Hop Counter state of the BICC Service Group Profile."
    ::= { sonusBiccsgSvcGrpProfileEntry 43 }

sonusBiccsgSvcGrpProfileHopCounterValue OBJECT-TYPE
    SYNTAX          Integer32 (0..31)
    MAX-ACCESS      read-write
    STATUS          current
    DESCRIPTION     
            "Specifies the value of the Hop Counter if initiated by the switch."
    ::= { sonusBiccsgSvcGrpProfileEntry 44 }

sonusBiccServiceGroupMIBNotifications OBJECT IDENTIFIER
    ::= { sonusBiccServiceGroupMIB 2 }

sonusBiccServiceGroupMIBNotificationsPrefix OBJECT IDENTIFIER
    ::= { sonusBiccServiceGroupMIBNotifications 0 }

sonusBiccServiceGroupMIBNotificationsObjects OBJECT IDENTIFIER
    ::= { sonusBiccServiceGroupMIBNotifications 1 }

sonusBiccSvcGrpName OBJECT-TYPE
    SYNTAX          DisplayString (SIZE(0..23))
    MAX-ACCESS      read-only
    STATUS          current
    DESCRIPTION     
            "Name of the BICC service group."
    ::= { sonusBiccServiceGroupMIBNotificationsObjects 1 }

sonusBiccMaintReason OBJECT-TYPE
    SYNTAX          INTEGER { ss7GwRegistration(1), 
                        remoteSs7PointCodeAccess(2), trunkGroupMode(3), 
                        serviceGroupMode(4), circuitMode(5), ds1Mode(6), 
                        serverMode(7), localHardware(8), 
                        remoteMaintenance(9), remoteHardware(10), 
                        remoteUnequipped(11), ss7GwResynchronization(12), 
                        localMaintenance(13) }
    MAX-ACCESS      read-only
    STATUS          current
    DESCRIPTION     
            "Maintenance reason for blocking/unblocking of the circuit."
    ::= { sonusBiccServiceGroupMIBNotificationsObjects 2 }

sonusBiccTrunkGrpName OBJECT-TYPE
    SYNTAX          DisplayString (SIZE(0..23))
    MAX-ACCESS      read-only
    STATUS          current
    DESCRIPTION     
            "Name of the trunk group."
    ::= { sonusBiccServiceGroupMIBNotificationsObjects 3 }

sonusBiccCircuit OBJECT-TYPE
    SYNTAX          Integer32 (0..16383)
    MAX-ACCESS      read-only
    STATUS          current
    DESCRIPTION     
            "Base circuit identity code (CIC) for the circuit."
    ::= { sonusBiccServiceGroupMIBNotificationsObjects 4 }

sonusBiccCircuitOffsets OBJECT-TYPE
    SYNTAX          BITS { cicOffset0(0), cicOffset1(1), cicOffset2(2), 
                        cicOffset3(3), cicOffset4(4), cicOffset5(5), 
                        cicOffset6(6), cicOffset7(7), cicOffset8(8), 
                        cicOffset9(9), cicOffset10(10), cicOffset11(11), 
                        cicOffset12(12), cicOffset13(13), 
                        cicOffset14(14), cicOffset15(15), 
                        cicOffset16(16), cicOffset17(17), 
                        cicOffset18(18), cicOffset19(19), 
                        cicOffset20(20), cicOffset21(21), 
                        cicOffset22(22), cicOffset23(23) }
    MAX-ACCESS      read-only
    STATUS          current
    DESCRIPTION     
            "Circuit maintenance status bitmap for CIC range. A 32 bit field is used in which the MSB is offset 0 from base"
    ::= { sonusBiccServiceGroupMIBNotificationsObjects 5 }

sonusBiccCalledPartyNumber OBJECT-TYPE
    SYNTAX          DisplayString (SIZE(0..31))
    MAX-ACCESS      read-only
    STATUS          current
    DESCRIPTION     
            "Called Party Number."
    ::= { sonusBiccServiceGroupMIBNotificationsObjects 6 }

sonusBiccCallingPartyNumber OBJECT-TYPE
    SYNTAX          DisplayString (SIZE(0..31))
    MAX-ACCESS      read-only
    STATUS          current
    DESCRIPTION     
            "Calling Party Number."
    ::= { sonusBiccServiceGroupMIBNotificationsObjects 7 }

sonusBiccMaintCode OBJECT-TYPE
    SYNTAX          DisplayString (SIZE(0..31))
    MAX-ACCESS      read-only
    STATUS          current
    DESCRIPTION     
            "Maintainence code."
    ::= { sonusBiccServiceGroupMIBNotificationsObjects 8 }

sonusBiccLocalPointCode OBJECT-TYPE
    SYNTAX          Integer32 (0..16777215)
    MAX-ACCESS      read-only
    STATUS          current
    DESCRIPTION     
            "Local Point Code."
    ::= { sonusBiccServiceGroupMIBNotificationsObjects 9 }

sonusBiccRemotePointCode OBJECT-TYPE
    SYNTAX          Integer32 (0..16777215)
    MAX-ACCESS      read-only
    STATUS          current
    DESCRIPTION     
            "Remote Point Code."
    ::= { sonusBiccServiceGroupMIBNotificationsObjects 10 }

sonusBiccNodeIndex OBJECT-TYPE
    SYNTAX          Integer32 (0..16777215)
    MAX-ACCESS      read-only
    STATUS          current
    DESCRIPTION     
            "The index value of the node."
    ::= { sonusBiccServiceGroupMIBNotificationsObjects 13 }

sonusBiccCircuitBlockedTrapsSuppressed OBJECT-TYPE
    SYNTAX          Unsigned32 (0..4294967295)
    MAX-ACCESS      read-only
    STATUS          current
    DESCRIPTION     
            "The number of BICC circuit Blocked traps Suppressed"
    ::= { sonusBiccServiceGroupMIBNotificationsObjects 15 }

sonusBiccCircuitBlockedCount OBJECT-TYPE
    SYNTAX          Unsigned32 (0..4294967295)
    MAX-ACCESS      read-only
    STATUS          current
    DESCRIPTION     
            "The number of BICC circuits Blocked relating to the traps Suppressed"
    ::= { sonusBiccServiceGroupMIBNotificationsObjects 16 }

sonusBiccCircuitUnblockedTrapsSuppressed OBJECT-TYPE
    SYNTAX          Unsigned32 (0..4294967295)
    MAX-ACCESS      read-only
    STATUS          current
    DESCRIPTION     
            "The number of BICC circuit Unblocked traps Suppressed"
    ::= { sonusBiccServiceGroupMIBNotificationsObjects 17 }

sonusBiccCircuitUnblockedCount OBJECT-TYPE
    SYNTAX          Unsigned32 (0..4294967295)
    MAX-ACCESS      read-only
    STATUS          current
    DESCRIPTION     
            "The number of BICC circuits Unblocked relating to the traps Suppressed"
    ::= { sonusBiccServiceGroupMIBNotificationsObjects 18 }

sonusBiccCircuitResetTrapsSuppressed OBJECT-TYPE
    SYNTAX          Unsigned32 (0..4294967295)
    MAX-ACCESS      read-only
    STATUS          current
    DESCRIPTION     
            "The number of BICC circuit reset traps Suppressed"
    ::= { sonusBiccServiceGroupMIBNotificationsObjects 19 }

sonusBiccCircuitResetCount OBJECT-TYPE
    SYNTAX          Unsigned32 (0..4294967295)
    MAX-ACCESS      read-only
    STATUS          current
    DESCRIPTION     
            "The number of BICC circuits reset relating to the traps Suppressed"
    ::= { sonusBiccServiceGroupMIBNotificationsObjects 20 }

sonusBiccT17ExpiryEvents OBJECT-TYPE
    SYNTAX          Unsigned32 (0..4294967295)
    MAX-ACCESS      read-only
    STATUS          current
    DESCRIPTION     
            "The number of BICC T17 expiry events during consolidation period"
    ::= { sonusBiccServiceGroupMIBNotificationsObjects 23 }

sonusBiccT19ExpiryEvents OBJECT-TYPE
    SYNTAX          Unsigned32 (0..4294967295)
    MAX-ACCESS      read-only
    STATUS          current
    DESCRIPTION     
            "The number of BICC T19 expiry events during consolidation period"
    ::= { sonusBiccServiceGroupMIBNotificationsObjects 24 }

sonusBiccT21ExpiryEvents OBJECT-TYPE
    SYNTAX          Unsigned32 (0..4294967295)
    MAX-ACCESS      read-only
    STATUS          current
    DESCRIPTION     
            "The number of BICC T21 expiry events during consolidation period"
    ::= { sonusBiccServiceGroupMIBNotificationsObjects 25 }

sonusBiccT23ExpiryEvents OBJECT-TYPE
    SYNTAX          Unsigned32 (0..4294967295)
    MAX-ACCESS      read-only
    STATUS          current
    DESCRIPTION     
            "The number of BICC T23 expiry events during consolidation period"
    ::= { sonusBiccServiceGroupMIBNotificationsObjects 26 }

sonusBiccT33ExpiryEvents OBJECT-TYPE
    SYNTAX          Unsigned32 (0..4294967295)
    MAX-ACCESS      read-only
    STATUS          current
    DESCRIPTION     
            "The number of BICC T33 expiry events during consolidation period"
    ::= { sonusBiccServiceGroupMIBNotificationsObjects 27 }

sonusBiccT5ExpiryEvents OBJECT-TYPE
    SYNTAX          Unsigned32 (0..4294967295)
    MAX-ACCESS      read-only
    STATUS          current
    DESCRIPTION     
            "The number of BICC T5 expiry events during consolidation period"
    ::= { sonusBiccServiceGroupMIBNotificationsObjects 28 }

sonusBiccTCQMExpiryEvents OBJECT-TYPE
    SYNTAX          Unsigned32 (0..4294967295)
    MAX-ACCESS      read-only
    STATUS          current
    DESCRIPTION     
            "The number of BICC TCQM expiry events during consolidation period"
    ::= { sonusBiccServiceGroupMIBNotificationsObjects 30 }

sonusBiccSvcGrpInServiceNotification NOTIFICATION-TYPE
    OBJECTS         { sonusBiccSvcGrpName, sonusEventDescription, 
                      sonusEventClass, sonusEventLevel, sonusSequenceId, 
                      sonusEventTime }
    STATUS          current
    DESCRIPTION     
            "This trap indicates that the BICC Service Group was put in service by maintenance staff."
    ::= { sonusBiccServiceGroupMIBNotificationsPrefix 1 }

sonusBiccSvcGrpOutOfServiceNotification NOTIFICATION-TYPE
    OBJECTS         { sonusBiccSvcGrpName, sonusEventDescription, 
                      sonusEventClass, sonusEventLevel, sonusSequenceId, 
                      sonusEventTime }
    STATUS          current
    DESCRIPTION     
            "This trap indicates that the BICC Service Group was taken out of service by maintenance staff."
    ::= { sonusBiccServiceGroupMIBNotificationsPrefix 2 }

sonusBiccCircuitBlockedNotification NOTIFICATION-TYPE
    OBJECTS         { sonusBiccSvcGrpName, sonusBiccMaintReason, 
                      sonusBiccTrunkGrpName, sonusBiccCircuit, 
                      sonusBiccCircuitOffsets, sonusEventDescription, 
                      sonusEventClass, sonusEventLevel, sonusSequenceId, 
                      sonusEventTime }
    STATUS          current
    DESCRIPTION     
            "This trap indicates that the BICC Circuit(s) were blocked."
    ::= { sonusBiccServiceGroupMIBNotificationsPrefix 3 }

sonusBiccCircuitUnblockedNotification NOTIFICATION-TYPE
    OBJECTS         { sonusBiccSvcGrpName, sonusBiccMaintReason, 
                      sonusBiccTrunkGrpName, sonusBiccCircuit, 
                      sonusBiccCircuitOffsets, sonusEventDescription, 
                      sonusEventClass, sonusEventLevel, sonusSequenceId, 
                      sonusEventTime }
    STATUS          current
    DESCRIPTION     
            "This trap indicates that the BICC Circuit(s) were unblocked."
    ::= { sonusBiccServiceGroupMIBNotificationsPrefix 4 }

sonusBiccCircuitResetNotification NOTIFICATION-TYPE
    OBJECTS         { sonusBiccSvcGrpName, sonusBiccTrunkGrpName, 
                      sonusBiccCircuit, sonusBiccCircuitOffsets, 
                      sonusEventDescription, sonusEventClass, 
                      sonusEventLevel, sonusSequenceId, sonusEventTime }
    STATUS          current
    DESCRIPTION     
            "This trap indicates that the BICC Circuit(s) were reset."
    ::= { sonusBiccServiceGroupMIBNotificationsPrefix 5 }

sonusBiccCicRegistrationFailedNotification NOTIFICATION-TYPE
    OBJECTS         { sonusBiccCircuit, sonusEventDescription, 
                      sonusEventClass, sonusEventLevel, sonusSequenceId, 
                      sonusEventTime }
    STATUS          current
    DESCRIPTION     
            "This trap indicates that the CIC Registration failed after multiple retries."
    ::= { sonusBiccServiceGroupMIBNotificationsPrefix 6 }

sonusBiccHopCounterExhaustedNotification NOTIFICATION-TYPE
    OBJECTS         { sonusBiccSvcGrpName, sonusBiccCircuit, 
                      sonusBiccCalledPartyNumber, 
                      sonusBiccCallingPartyNumber, sonusEventDescription, 
                      sonusEventClass, sonusEventLevel, sonusSequenceId, 
                      sonusEventTime }
    STATUS          current
    DESCRIPTION     
            "This trap indicates that the Hop Counter value received in IAM is zero."
    ::= { sonusBiccServiceGroupMIBNotificationsPrefix 7 }

sonusBiccRelWithExchangeRoutingErrorNotification NOTIFICATION-TYPE
    OBJECTS         { sonusBiccSvcGrpName, sonusBiccCircuit, 
                      sonusBiccCalledPartyNumber, 
                      sonusBiccCallingPartyNumber, sonusEventDescription, 
                      sonusEventClass, sonusEventLevel, sonusSequenceId, 
                      sonusEventTime }
    STATUS          current
    DESCRIPTION     
            "This trap indicates that a REL message is received with Exchange Routing Error cause value."
    ::= { sonusBiccServiceGroupMIBNotificationsPrefix 8 }

sonusBiccCqmTimeoutNotification NOTIFICATION-TYPE
    OBJECTS         { sonusBiccCircuit, sonusEventDescription, 
                      sonusEventClass, sonusEventLevel, sonusSequenceId, 
                      sonusEventTime }
    STATUS          current
    DESCRIPTION     
            "This trap indicates that the timed out has occured waiting for CQM response"
    ::= { sonusBiccServiceGroupMIBNotificationsPrefix 9 }

sonusBiccFarendCircuitStateMismatchedNotification NOTIFICATION-TYPE
    OBJECTS         { sonusBiccCircuit, sonusEventDescription, 
                      sonusEventClass, sonusEventLevel, sonusSequenceId, 
                      sonusEventTime }
    STATUS          current
    DESCRIPTION     
            "This trap indicates that the circuit/block state is mismatched as report by CQR"
    ::= { sonusBiccServiceGroupMIBNotificationsPrefix 10 }

sonusBiccCircuitTimerExpired NOTIFICATION-TYPE
    OBJECTS         { sonusBiccTrunkGrpName, sonusBiccSvcGrpName, 
                      sonusBiccCircuit, sonusBiccMaintCode, 
                      sonusEventDescription, sonusEventClass, 
                      sonusEventLevel, sonusSequenceId, sonusEventTime }
    STATUS          current
    DESCRIPTION     
            "This trap indicates that the BICC Circuit had a timer expire."
    ::= { sonusBiccServiceGroupMIBNotificationsPrefix 11 }

sonusBiccCircuitCgbaStatusMismatchNotification NOTIFICATION-TYPE
    OBJECTS         { sonusBiccSvcGrpName, sonusBiccMaintReason, 
                      sonusBiccTrunkGrpName, sonusBiccCircuit, 
                      sonusBiccCircuitOffsets, sonusEventDescription, 
                      sonusEventClass, sonusEventLevel, sonusSequenceId, 
                      sonusEventTime }
    STATUS          current
    DESCRIPTION     
            "This trap indicates that expected status bits for some BICC Circuit(s)
             in a CGBA were not set."
    ::= { sonusBiccServiceGroupMIBNotificationsPrefix 12 }

sonusBiccCircuitCguaStatusMismatchNotification NOTIFICATION-TYPE
    OBJECTS         { sonusBiccSvcGrpName, sonusBiccMaintReason, 
                      sonusBiccTrunkGrpName, sonusBiccCircuit, 
                      sonusBiccCircuitOffsets, sonusEventDescription, 
                      sonusEventClass, sonusEventLevel, sonusSequenceId, 
                      sonusEventTime }
    STATUS          current
    DESCRIPTION     
            "This trap indicates that expected status bits for some BICC Circuit(s)
             in a CGUA were not set."
    ::= { sonusBiccServiceGroupMIBNotificationsPrefix 13 }

sonusBiccSvcGrpCircuitsUnblockedNotification NOTIFICATION-TYPE
    OBJECTS         { sonusBiccSvcGrpName, sonusBiccMaintReason, 
                      sonusBiccTrunkGrpName, sonusEventDescription, 
                      sonusEventClass, sonusEventLevel, sonusSequenceId, 
                      sonusEventTime }
    STATUS          current
    DESCRIPTION     
            "This trap indicates that the all BICC Circuits in the
             Service Group were unblocked."
    ::= { sonusBiccServiceGroupMIBNotificationsPrefix 14 }

sonusBiccUCICNotification NOTIFICATION-TYPE
    OBJECTS         { sonusBiccLocalPointCode, sonusBiccRemotePointCode, 
                      sonusBiccCircuit, sonusEventDescription, 
                      sonusEventClass, sonusEventLevel, sonusSequenceId, 
                      sonusEventTime, sonusBiccNodeIndex }
    STATUS          current
    DESCRIPTION     
            "This trap indicates that a UCIC message has been received."
    ::= { sonusBiccServiceGroupMIBNotificationsPrefix 15 }

sonusBiccSgConsolidatedCctBlockedNotification NOTIFICATION-TYPE
    OBJECTS         { sonusShelfIndex, sonusSlotIndex, 
                      sonusBiccSvcGrpName, sonusBiccTrunkGrpName, 
                      sonusBiccCircuitBlockedTrapsSuppressed, 
                      sonusBiccCircuitBlockedCount, 
                      sonusEventDescription, sonusEventClass, 
                      sonusEventLevel, sonusSequenceId, sonusEventTime }
    STATUS          current
    DESCRIPTION     
            "This trap indicates that BICC circuit blocked event data has been consolidated"
    ::= { sonusBiccServiceGroupMIBNotificationsPrefix 16 }

sonusBiccSgConsolidatedCctUnblockedNotification NOTIFICATION-TYPE
    OBJECTS         { sonusShelfIndex, sonusSlotIndex, 
                      sonusBiccSvcGrpName, sonusBiccTrunkGrpName, 
                      sonusBiccCircuitUnblockedTrapsSuppressed, 
                      sonusBiccCircuitUnblockedCount, 
                      sonusEventDescription, sonusEventClass, 
                      sonusEventLevel, sonusSequenceId, sonusEventTime }
    STATUS          current
    DESCRIPTION     
            "This trap indicates that BICC circuit unblocked event data has been consolidated"
    ::= { sonusBiccServiceGroupMIBNotificationsPrefix 17 }

sonusBiccSgConsolidatedCctResetNotification NOTIFICATION-TYPE
    OBJECTS         { sonusShelfIndex, sonusSlotIndex, 
                      sonusBiccSvcGrpName, sonusBiccTrunkGrpName, 
                      sonusBiccCircuitResetTrapsSuppressed, 
                      sonusBiccCircuitResetCount, sonusEventDescription, 
                      sonusEventClass, sonusEventLevel, sonusSequenceId, 
                      sonusEventTime }
    STATUS          current
    DESCRIPTION     
            "This trap indicates that BICC circuit reset event data has been consolidated"
    ::= { sonusBiccServiceGroupMIBNotificationsPrefix 18 }

sonusBiccSgT17ExpiryNotification NOTIFICATION-TYPE
    OBJECTS         { sonusShelfIndex, sonusSlotIndex, 
                      sonusBiccSvcGrpName, sonusBiccTrunkGrpName, 
                      sonusBiccT17ExpiryEvents, sonusEventDescription, 
                      sonusEventClass, sonusEventLevel, sonusSequenceId, 
                      sonusEventTime }
    STATUS          current
    DESCRIPTION     
            "This trap indicates that BICC T17 timer expiry event data has been consolidated"
    ::= { sonusBiccServiceGroupMIBNotificationsPrefix 19 }

sonusBiccSgT19ExpiryNotification NOTIFICATION-TYPE
    OBJECTS         { sonusShelfIndex, sonusSlotIndex, 
                      sonusBiccSvcGrpName, sonusBiccTrunkGrpName, 
                      sonusBiccT19ExpiryEvents, sonusEventDescription, 
                      sonusEventClass, sonusEventLevel, sonusSequenceId, 
                      sonusEventTime }
    STATUS          current
    DESCRIPTION     
            "This trap indicates that BICC T19 timer expiry event data has been consolidated"
    ::= { sonusBiccServiceGroupMIBNotificationsPrefix 20 }

sonusBiccSgT21ExpiryNotification NOTIFICATION-TYPE
    OBJECTS         { sonusShelfIndex, sonusSlotIndex, 
                      sonusBiccSvcGrpName, sonusBiccTrunkGrpName, 
                      sonusBiccT21ExpiryEvents, sonusEventDescription, 
                      sonusEventClass, sonusEventLevel, sonusSequenceId, 
                      sonusEventTime }
    STATUS          current
    DESCRIPTION     
            "This trap indicates that BICC T21 timer expiry event data has been consolidated"
    ::= { sonusBiccServiceGroupMIBNotificationsPrefix 21 }

sonusBiccSgT23ExpiryNotification NOTIFICATION-TYPE
    OBJECTS         { sonusShelfIndex, sonusSlotIndex, 
                      sonusBiccSvcGrpName, sonusBiccTrunkGrpName, 
                      sonusBiccT23ExpiryEvents, sonusEventDescription, 
                      sonusEventClass, sonusEventLevel, sonusSequenceId, 
                      sonusEventTime }
    STATUS          current
    DESCRIPTION     
            "This trap indicates that BICC T23 timer expiry event data has been consolidated"
    ::= { sonusBiccServiceGroupMIBNotificationsPrefix 22 }

sonusBiccSgT33ExpiryNotification NOTIFICATION-TYPE
    OBJECTS         { sonusShelfIndex, sonusSlotIndex, 
                      sonusBiccSvcGrpName, sonusBiccTrunkGrpName, 
                      sonusBiccT33ExpiryEvents, sonusEventDescription, 
                      sonusEventClass, sonusEventLevel, sonusSequenceId, 
                      sonusEventTime }
    STATUS          current
    DESCRIPTION     
            "This trap indicates that BICC T33 timer expiry event data has been consolidated"
    ::= { sonusBiccServiceGroupMIBNotificationsPrefix 23 }

sonusBiccSgT5ExpiryNotification NOTIFICATION-TYPE
    OBJECTS         { sonusShelfIndex, sonusSlotIndex, 
                      sonusBiccSvcGrpName, sonusBiccTrunkGrpName, 
                      sonusBiccT5ExpiryEvents, sonusEventDescription, 
                      sonusEventClass, sonusEventLevel, sonusSequenceId, 
                      sonusEventTime }
    STATUS          current
    DESCRIPTION     
            "This trap indicates that BICC T5 timer expiry event data has been consolidated"
    ::= { sonusBiccServiceGroupMIBNotificationsPrefix 24 }

sonusBiccSgTCQMExpiryNotification NOTIFICATION-TYPE
    OBJECTS         { sonusShelfIndex, sonusSlotIndex, 
                      sonusBiccSvcGrpName, sonusBiccTrunkGrpName, 
                      sonusBiccTCQMExpiryEvents, sonusEventDescription, 
                      sonusEventClass, sonusEventLevel, sonusSequenceId, 
                      sonusEventTime }
    STATUS          current
    DESCRIPTION     
            "This trap indicates that BICC TCQM timer expiry event data has been consolidated"
    ::= { sonusBiccServiceGroupMIBNotificationsPrefix 25 }

END -- end of module SONUS-BICC-SERVICE-GROUP-MIB.
