--
-- This SMIv2 module has been generated by smidump 0.2-cvs. Do not edit.
--

SONUS-DS3THRESHOLD-MIB DEFINITIONS ::= BEGIN

IMPORTS
    Integer32, MODULE-IDENTITY, NOTIFICATION-TYPE, OBJECT-TYPE
        FROM SNMPv2-SMI
    sonusDs3Index, sonusEventClass, sonusEventDescription, 
    sonusEventLevel, sonusEventTime, sonusPortIndex, sonusSequenceId, 
    sonusShelfIndex, sonusSlotIndex
        FROM SONUS-COMMON-MIB
    sonusDs3ThresholdType, sonusDsx3MIBNotificationsObjects, 
    sonusDsx3MIBNotificationsPrefix, sonusDsx3MIBObjects
        FROM SONUS-DS3-MIB
    sonusCircuitMIBs
        FROM SONUS-SMI
    SonusAdminState, SonusShelfIndex, SonusSlotIndex
        FROM SONUS-TC;

sonusDsx3ThresholdMIB MODULE-IDENTITY
    LAST-UPDATED    "200703280000Z"
    ORGANIZATION    
            "Sonus Networks, Inc."
    CONTACT-INFO    
            "   Customer Support    
             Sonus Networks, Inc.
             7 Technology Park Drive
             Westford, MA 01886
             USA
             
             Tel: 978-614-8100
             Fax: 978-614-8609"
    DESCRIPTION     
            "The MIB Module DS3 management."
    ::= { sonusCircuitMIBs 6 }


sonusDsx3Threshold OBJECT IDENTIFIER
    ::= { sonusDsx3MIBObjects 11 }

sonusDsx3ThresholdTable OBJECT-TYPE
    SYNTAX          SEQUENCE OF SonusDsx3ThresholdEntry
    MAX-ACCESS      not-accessible
    STATUS          current
    DESCRIPTION     
            " "
    ::= { sonusDsx3Threshold 1 }

sonusDsx3ThresholdEntry OBJECT-TYPE
    SYNTAX          SonusDsx3ThresholdEntry
    MAX-ACCESS      not-accessible
    STATUS          current
    DESCRIPTION     
            "Entry in Sonus Dsx3 Threshold Table"
    INDEX           { sonusDsx3ThresholdShelfIndex, 
                      sonusDsx3ThresholdSlotIndex, 
                      sonusDsx3ThresholdPortIndex, 
                      sonusDsx3ThresholdDs3Index }
    ::= { sonusDsx3ThresholdTable 1 }

SonusDsx3ThresholdEntry ::=
    SEQUENCE {
        sonusDsx3ThresholdShelfIndex    SonusShelfIndex,
        sonusDsx3ThresholdSlotIndex     SonusSlotIndex,
        sonusDsx3ThresholdPortIndex     Integer32,
        sonusDsx3ThresholdDs3Index      Integer32,
        sonusDsx3ThresholdMinorLCVThreshold   Integer32,
        sonusDsx3ThresholdMinorLESThreshold   Integer32,
        sonusDsx3ThresholdMinorLSESThreshold    Integer32,
        sonusDsx3ThresholdMinorPCVThreshold   Integer32,
        sonusDsx3ThresholdMinorPESThreshold   Integer32,
        sonusDsx3ThresholdMinorPSESThreshold    Integer32,
        sonusDsx3ThresholdMinorUASThreshold   Integer32,
        sonusDsx3ThresholdDayMinorLCVThreshold      Integer32,
        sonusDsx3ThresholdDayMinorLESThreshold      Integer32,
        sonusDsx3ThresholdDayMinorLSESThreshold       Integer32,
        sonusDsx3ThresholdDayMinorPCVThreshold      Integer32,
        sonusDsx3ThresholdDayMinorPESThreshold      Integer32,
        sonusDsx3ThresholdDayMinorPSESThreshold       Integer32,
        sonusDsx3ThresholdDayMinorUASThreshold      Integer32,
        sonusDsx3ThresholdMajorLCVThreshold   Integer32,
        sonusDsx3ThresholdMajorLESThreshold   Integer32,
        sonusDsx3ThresholdMajorLSESThreshold    Integer32,
        sonusDsx3ThresholdMajorPCVThreshold   Integer32,
        sonusDsx3ThresholdMajorPESThreshold   Integer32,
        sonusDsx3ThresholdMajorPSESThreshold    Integer32,
        sonusDsx3ThresholdMajorUASThreshold   Integer32,
        sonusDsx3ThresholdDayMajorLCVThreshold      Integer32,
        sonusDsx3ThresholdDayMajorLESThreshold      Integer32,
        sonusDsx3ThresholdDayMajorLSESThreshold       Integer32,
        sonusDsx3ThresholdDayMajorPCVThreshold      Integer32,
        sonusDsx3ThresholdDayMajorPESThreshold      Integer32,
        sonusDsx3ThresholdDayMajorPSESThreshold       Integer32,
        sonusDsx3ThresholdDayMajorUASThreshold      Integer32,
        sonusDsx3ThresholdCriticalLCVThreshold      Integer32,
        sonusDsx3ThresholdCriticalLESThreshold      Integer32,
        sonusDsx3ThresholdCriticalLSESThreshold       Integer32,
        sonusDsx3ThresholdCriticalPCVThreshold      Integer32,
        sonusDsx3ThresholdCriticalPESThreshold      Integer32,
        sonusDsx3ThresholdCriticalPSESThreshold       Integer32,
        sonusDsx3ThresholdCriticalUASThreshold      Integer32,
        sonusDsx3ThresholdDayCriticalLCVThreshold         Integer32,
        sonusDsx3ThresholdDayCriticalLESThreshold         Integer32,
        sonusDsx3ThresholdDayCriticalLSESThreshold          Integer32,
        sonusDsx3ThresholdDayCriticalPCVThreshold         Integer32,
        sonusDsx3ThresholdDayCriticalPESThreshold         Integer32,
        sonusDsx3ThresholdDayCriticalPSESThreshold          Integer32,
        sonusDsx3ThresholdDayCriticalUASThreshold         Integer32,
        sonusDsx3ThresholdLCVTcaFilter  SonusAdminState,
        sonusDsx3ThresholdLESTcaFilter  SonusAdminState,
        sonusDsx3ThresholdLSESTcaFilter SonusAdminState,
        sonusDsx3ThresholdPCVTcaFilter  SonusAdminState,
        sonusDsx3ThresholdPESTcaFilter  SonusAdminState,
        sonusDsx3ThresholdPSESTcaFilter SonusAdminState,
        sonusDsx3ThresholdUASTcaFilter  SonusAdminState,
        sonusDsx3ThresholdReportMinorCriticalTca        SonusAdminState,
        sonusDsx3ThresholdReportDs3OosTca SonusAdminState
    }

sonusDsx3ThresholdShelfIndex OBJECT-TYPE
    SYNTAX          SonusShelfIndex
    MAX-ACCESS      read-only
    STATUS          current
    DESCRIPTION     
            "Shelf index for this table"
    ::= { sonusDsx3ThresholdEntry 1 }

sonusDsx3ThresholdSlotIndex OBJECT-TYPE
    SYNTAX          SonusSlotIndex
    MAX-ACCESS      read-only
    STATUS          current
    DESCRIPTION     
            "Slot index for this table"
    ::= { sonusDsx3ThresholdEntry 2 }

sonusDsx3ThresholdPortIndex OBJECT-TYPE
    SYNTAX          Integer32
    MAX-ACCESS      read-only
    STATUS          current
    DESCRIPTION     
            "Port index for this table"
    ::= { sonusDsx3ThresholdEntry 3 }

sonusDsx3ThresholdDs3Index OBJECT-TYPE
    SYNTAX          Integer32
    MAX-ACCESS      read-only
    STATUS          current
    DESCRIPTION     
            "Ds3 Index into this table"
    ::= { sonusDsx3ThresholdEntry 4 }

sonusDsx3ThresholdMinorLCVThreshold OBJECT-TYPE
    SYNTAX          Integer32 (1..16383)
    MAX-ACCESS      read-write
    STATUS          current
    DESCRIPTION     
            "Line Code Violations Minor threshold value for 15 minute interval."
    DEFVAL          { 310 }
    ::= { sonusDsx3ThresholdEntry 5 }

sonusDsx3ThresholdMinorLESThreshold OBJECT-TYPE
    SYNTAX          Integer32 (1..900)
    MAX-ACCESS      read-write
    STATUS          current
    DESCRIPTION     
            "Line Errored Seconds Minor threshold value for 15 minute interval."
    DEFVAL          { 20 }
    ::= { sonusDsx3ThresholdEntry 6 }

sonusDsx3ThresholdMinorLSESThreshold OBJECT-TYPE
    SYNTAX          Integer32 (1..900)
    MAX-ACCESS      read-write
    STATUS          current
    DESCRIPTION     
            "Line Severely Errored Seconds Minor threshold value for 15 minute interval."
    DEFVAL          { 3 }
    ::= { sonusDsx3ThresholdEntry 7 }

sonusDsx3ThresholdMinorPCVThreshold OBJECT-TYPE
    SYNTAX          Integer32 (1..16383)
    MAX-ACCESS      read-write
    STATUS          current
    DESCRIPTION     
            "Path Code Violations Minor threshold value for 15 minute interval, for both
             P-bit and CP-bit."
    DEFVAL          { 306 }
    ::= { sonusDsx3ThresholdEntry 8 }

sonusDsx3ThresholdMinorPESThreshold OBJECT-TYPE
    SYNTAX          Integer32 (1..900)
    MAX-ACCESS      read-write
    STATUS          current
    DESCRIPTION     
            "Path Errored Seconds Minor threshold value for 15 minute interval, for both
             P-bit and CP-bit."
    DEFVAL          { 20 }
    ::= { sonusDsx3ThresholdEntry 9 }

sonusDsx3ThresholdMinorPSESThreshold OBJECT-TYPE
    SYNTAX          Integer32 (1..900)
    MAX-ACCESS      read-write
    STATUS          current
    DESCRIPTION     
            "Path Severely Errored Seconds Minor threshold value for 15 minute interval, for both
             P-bit and CP-bit."
    DEFVAL          { 3 }
    ::= { sonusDsx3ThresholdEntry 10 }

sonusDsx3ThresholdMinorUASThreshold OBJECT-TYPE
    SYNTAX          Integer32 (1..900)
    MAX-ACCESS      read-write
    STATUS          current
    DESCRIPTION     
            "Path Unavailable Seconds Minor threshold value for 15 minute interval, for both
             P-bit and CP-bit."
    DEFVAL          { 8 }
    ::= { sonusDsx3ThresholdEntry 11 }

sonusDsx3ThresholdDayMinorLCVThreshold OBJECT-TYPE
    SYNTAX          Integer32 (1..1048575)
    MAX-ACCESS      read-write
    STATUS          current
    DESCRIPTION     
            "Line Code Violations Minor threshold value for 24 hour interval."
    DEFVAL          { 3092 }
    ::= { sonusDsx3ThresholdEntry 12 }

sonusDsx3ThresholdDayMinorLESThreshold OBJECT-TYPE
    SYNTAX          Integer32 (1..65535)
    MAX-ACCESS      read-write
    STATUS          current
    DESCRIPTION     
            "Line Errored Seconds Minor threshold value for 24 hour interval."
    DEFVAL          { 200 }
    ::= { sonusDsx3ThresholdEntry 13 }

sonusDsx3ThresholdDayMinorLSESThreshold OBJECT-TYPE
    SYNTAX          Integer32 (1..65535)
    MAX-ACCESS      read-write
    STATUS          current
    DESCRIPTION     
            "Line Severely Errored Seconds Minor threshold value for 24 hour interval."
    DEFVAL          { 32 }
    ::= { sonusDsx3ThresholdEntry 14 }

sonusDsx3ThresholdDayMinorPCVThreshold OBJECT-TYPE
    SYNTAX          Integer32 (1..65535)
    MAX-ACCESS      read-write
    STATUS          current
    DESCRIPTION     
            "Path Code Violations Minor threshold value for 24 hour interval, for both
             P-bit and CP-bit."
    DEFVAL          { 3056 }
    ::= { sonusDsx3ThresholdEntry 15 }

sonusDsx3ThresholdDayMinorPESThreshold OBJECT-TYPE
    SYNTAX          Integer32 (1..65535)
    MAX-ACCESS      read-write
    STATUS          current
    DESCRIPTION     
            "Path Errored Seconds Minor threshold value for 24 hour interval, for both
             P-bit and CP-bit."
    DEFVAL          { 200 }
    ::= { sonusDsx3ThresholdEntry 16 }

sonusDsx3ThresholdDayMinorPSESThreshold OBJECT-TYPE
    SYNTAX          Integer32 (1..65535)
    MAX-ACCESS      read-write
    STATUS          current
    DESCRIPTION     
            "Path Severely Errored Seconds Minor threshold value for 24 hour interval, for both
             P-bit and CP-bit."
    DEFVAL          { 32 }
    ::= { sonusDsx3ThresholdEntry 17 }

sonusDsx3ThresholdDayMinorUASThreshold OBJECT-TYPE
    SYNTAX          Integer32 (1..65535)
    MAX-ACCESS      read-write
    STATUS          current
    DESCRIPTION     
            "Path Unavailable Seconds Minor threshold value for 24 hour interval, for both
             P-bit and CP-bit."
    DEFVAL          { 8 }
    ::= { sonusDsx3ThresholdEntry 18 }

sonusDsx3ThresholdMajorLCVThreshold OBJECT-TYPE
    SYNTAX          Integer32 (1..16383)
    MAX-ACCESS      read-write
    STATUS          current
    DESCRIPTION     
            "Line Code Violations Major threshold value for 15 minute interval."
    DEFVAL          { 387 }
    ::= { sonusDsx3ThresholdEntry 19 }

sonusDsx3ThresholdMajorLESThreshold OBJECT-TYPE
    SYNTAX          Integer32 (1..900)
    MAX-ACCESS      read-write
    STATUS          current
    DESCRIPTION     
            "Line Errored Seconds Major threshold value for 15 minute interval."
    DEFVAL          { 25 }
    ::= { sonusDsx3ThresholdEntry 20 }

sonusDsx3ThresholdMajorLSESThreshold OBJECT-TYPE
    SYNTAX          Integer32 (1..900)
    MAX-ACCESS      read-write
    STATUS          current
    DESCRIPTION     
            "Line Severely Errored Seconds Major threshold value for 15 minute interval."
    DEFVAL          { 4 }
    ::= { sonusDsx3ThresholdEntry 21 }

sonusDsx3ThresholdMajorPCVThreshold OBJECT-TYPE
    SYNTAX          Integer32 (1..16383)
    MAX-ACCESS      read-write
    STATUS          current
    DESCRIPTION     
            "Path Code Violations Major threshold value for 15 minute interval, for both
             P-bit and CP-bit."
    DEFVAL          { 382 }
    ::= { sonusDsx3ThresholdEntry 22 }

sonusDsx3ThresholdMajorPESThreshold OBJECT-TYPE
    SYNTAX          Integer32 (1..900)
    MAX-ACCESS      read-write
    STATUS          current
    DESCRIPTION     
            "Path Errored Seconds Major threshold value for 15 minute interval, for both
             P-bit and CP-bit."
    DEFVAL          { 25 }
    ::= { sonusDsx3ThresholdEntry 23 }

sonusDsx3ThresholdMajorPSESThreshold OBJECT-TYPE
    SYNTAX          Integer32 (1..900)
    MAX-ACCESS      read-write
    STATUS          current
    DESCRIPTION     
            "Path Severely Errored Seconds Major threshold value for 15 minute interval, for both
             P-bit and CP-bit."
    DEFVAL          { 4 }
    ::= { sonusDsx3ThresholdEntry 24 }

sonusDsx3ThresholdMajorUASThreshold OBJECT-TYPE
    SYNTAX          Integer32 (1..900)
    MAX-ACCESS      read-write
    STATUS          current
    DESCRIPTION     
            "Path Unavailable Seconds Major threshold value for 15 minute interval, for both
             P-bit and CP-bit."
    DEFVAL          { 10 }
    ::= { sonusDsx3ThresholdEntry 25 }

sonusDsx3ThresholdDayMajorLCVThreshold OBJECT-TYPE
    SYNTAX          Integer32 (1..1048575)
    MAX-ACCESS      read-write
    STATUS          current
    DESCRIPTION     
            "Line Code Violations Major threshold value for 24 hour interval."
    DEFVAL          { 3865 }
    ::= { sonusDsx3ThresholdEntry 26 }

sonusDsx3ThresholdDayMajorLESThreshold OBJECT-TYPE
    SYNTAX          Integer32 (1..65535)
    MAX-ACCESS      read-write
    STATUS          current
    DESCRIPTION     
            "Line Errored Seconds Major threshold value for 24 hour interval."
    DEFVAL          { 250 }
    ::= { sonusDsx3ThresholdEntry 27 }

sonusDsx3ThresholdDayMajorLSESThreshold OBJECT-TYPE
    SYNTAX          Integer32 (1..65535)
    MAX-ACCESS      read-write
    STATUS          current
    DESCRIPTION     
            "Line Severely Errored Seconds Major threshold value for 24 hour interval."
    DEFVAL          { 40 }
    ::= { sonusDsx3ThresholdEntry 28 }

sonusDsx3ThresholdDayMajorPCVThreshold OBJECT-TYPE
    SYNTAX          Integer32 (1..65535)
    MAX-ACCESS      read-write
    STATUS          current
    DESCRIPTION     
            "Path Code Violations Major threshold value for 24 hour interval, for both
             P-bit and CP-bit."
    DEFVAL          { 3820 }
    ::= { sonusDsx3ThresholdEntry 29 }

sonusDsx3ThresholdDayMajorPESThreshold OBJECT-TYPE
    SYNTAX          Integer32 (1..65535)
    MAX-ACCESS      read-write
    STATUS          current
    DESCRIPTION     
            "Path Errored Seconds Major threshold value for 24 hour interval, for both
             P-bit and CP-bit."
    DEFVAL          { 250 }
    ::= { sonusDsx3ThresholdEntry 30 }

sonusDsx3ThresholdDayMajorPSESThreshold OBJECT-TYPE
    SYNTAX          Integer32 (1..65535)
    MAX-ACCESS      read-write
    STATUS          current
    DESCRIPTION     
            "Path Severely Errored Seconds Major threshold value for 24 hour interval, for both
             P-bit and CP-bit."
    DEFVAL          { 40 }
    ::= { sonusDsx3ThresholdEntry 31 }

sonusDsx3ThresholdDayMajorUASThreshold OBJECT-TYPE
    SYNTAX          Integer32 (1..65535)
    MAX-ACCESS      read-write
    STATUS          current
    DESCRIPTION     
            "Path Unavailable Seconds Major threshold value for 24 hour interval, for both
             P-bit and CP-bit."
    DEFVAL          { 10 }
    ::= { sonusDsx3ThresholdEntry 32 }

sonusDsx3ThresholdCriticalLCVThreshold OBJECT-TYPE
    SYNTAX          Integer32 (1..16383)
    MAX-ACCESS      read-write
    STATUS          current
    DESCRIPTION     
            "Line Code Violations Critical threshold value for 15 minute interval."
    DEFVAL          { 464 }
    ::= { sonusDsx3ThresholdEntry 33 }

sonusDsx3ThresholdCriticalLESThreshold OBJECT-TYPE
    SYNTAX          Integer32 (1..900)
    MAX-ACCESS      read-write
    STATUS          current
    DESCRIPTION     
            "Line Errored Seconds Critical threshold value for 15 minute interval."
    DEFVAL          { 30 }
    ::= { sonusDsx3ThresholdEntry 34 }

sonusDsx3ThresholdCriticalLSESThreshold OBJECT-TYPE
    SYNTAX          Integer32 (1..900)
    MAX-ACCESS      read-write
    STATUS          current
    DESCRIPTION     
            "Line Severely Errored Seconds Critical threshold value for 15 minute interval."
    DEFVAL          { 5 }
    ::= { sonusDsx3ThresholdEntry 35 }

sonusDsx3ThresholdCriticalPCVThreshold OBJECT-TYPE
    SYNTAX          Integer32 (1..16383)
    MAX-ACCESS      read-write
    STATUS          current
    DESCRIPTION     
            "Path Code Violations Critical threshold value for 15 minute interval, for both
             P-bit and CP-bit."
    DEFVAL          { 458 }
    ::= { sonusDsx3ThresholdEntry 36 }

sonusDsx3ThresholdCriticalPESThreshold OBJECT-TYPE
    SYNTAX          Integer32 (1..900)
    MAX-ACCESS      read-write
    STATUS          current
    DESCRIPTION     
            "Path Errored Seconds Critical threshold value for 15 minute interval, for both
             P-bit and CP-bit."
    DEFVAL          { 30 }
    ::= { sonusDsx3ThresholdEntry 37 }

sonusDsx3ThresholdCriticalPSESThreshold OBJECT-TYPE
    SYNTAX          Integer32 (1..900)
    MAX-ACCESS      read-write
    STATUS          current
    DESCRIPTION     
            "Path Severely Errored Seconds Critical threshold value for 15 minute interval, for both
             P-bit and CP-bit."
    DEFVAL          { 5 }
    ::= { sonusDsx3ThresholdEntry 38 }

sonusDsx3ThresholdCriticalUASThreshold OBJECT-TYPE
    SYNTAX          Integer32 (1..900)
    MAX-ACCESS      read-write
    STATUS          current
    DESCRIPTION     
            "Path Unavailable Seconds Critical threshold value for 15 minute interval, for both
             P-bit and CP-bit."
    DEFVAL          { 12 }
    ::= { sonusDsx3ThresholdEntry 39 }

sonusDsx3ThresholdDayCriticalLCVThreshold OBJECT-TYPE
    SYNTAX          Integer32 (1..1048575)
    MAX-ACCESS      read-write
    STATUS          current
    DESCRIPTION     
            "Line Code Violations Critical threshold value for 24 hour interval."
    DEFVAL          { 4638 }
    ::= { sonusDsx3ThresholdEntry 40 }

sonusDsx3ThresholdDayCriticalLESThreshold OBJECT-TYPE
    SYNTAX          Integer32 (1..65535)
    MAX-ACCESS      read-write
    STATUS          current
    DESCRIPTION     
            "Line Errored Seconds Critical threshold value for 24 hour interval."
    DEFVAL          { 300 }
    ::= { sonusDsx3ThresholdEntry 41 }

sonusDsx3ThresholdDayCriticalLSESThreshold OBJECT-TYPE
    SYNTAX          Integer32 (1..65535)
    MAX-ACCESS      read-write
    STATUS          current
    DESCRIPTION     
            "Line Severely Errored Seconds Critical threshold value for 24 hour interval."
    DEFVAL          { 48 }
    ::= { sonusDsx3ThresholdEntry 42 }

sonusDsx3ThresholdDayCriticalPCVThreshold OBJECT-TYPE
    SYNTAX          Integer32 (1..65535)
    MAX-ACCESS      read-write
    STATUS          current
    DESCRIPTION     
            "Path Code Violations Critical threshold value for 24 hour interval, for both
             P-bit and CP-bit."
    DEFVAL          { 4584 }
    ::= { sonusDsx3ThresholdEntry 43 }

sonusDsx3ThresholdDayCriticalPESThreshold OBJECT-TYPE
    SYNTAX          Integer32 (1..65535)
    MAX-ACCESS      read-write
    STATUS          current
    DESCRIPTION     
            "Path Errored Seconds Critical threshold value for 24 hour interval, for both
             P-bit and CP-bit."
    DEFVAL          { 300 }
    ::= { sonusDsx3ThresholdEntry 44 }

sonusDsx3ThresholdDayCriticalPSESThreshold OBJECT-TYPE
    SYNTAX          Integer32 (1..65535)
    MAX-ACCESS      read-write
    STATUS          current
    DESCRIPTION     
            "Path Severely Errored Seconds Critical threshold value for 24 hour interval, for both
             P-bit and CP-bit."
    DEFVAL          { 48 }
    ::= { sonusDsx3ThresholdEntry 45 }

sonusDsx3ThresholdDayCriticalUASThreshold OBJECT-TYPE
    SYNTAX          Integer32 (1..65535)
    MAX-ACCESS      read-write
    STATUS          current
    DESCRIPTION     
            "Path Unavailable Seconds Critical threshold value for 24 hour interval, for both
             P-bit and CP-bit."
    DEFVAL          { 12 }
    ::= { sonusDsx3ThresholdEntry 46 }

sonusDsx3ThresholdLCVTcaFilter OBJECT-TYPE
    SYNTAX          SonusAdminState
    MAX-ACCESS      read-write
    STATUS          current
    DESCRIPTION     
            "Controls whether a threshold Crossing Alert (TCA) is reported (via
             an event log and trap). Setting this object to Enabled will prevent
             the TCA from being reported (i.e will Filter the TCA report)."
    DEFVAL          { disabled }
    ::= { sonusDsx3ThresholdEntry 47 }

sonusDsx3ThresholdLESTcaFilter OBJECT-TYPE
    SYNTAX          SonusAdminState
    MAX-ACCESS      read-write
    STATUS          current
    DESCRIPTION     
            "Controls whether a threshold Crossing Alert (TCA) is reported (via
             an event log and trap). Setting this object to Enabled will prevent
             the TCA from being reported (i.e will Filter the TCA report)."
    DEFVAL          { disabled }
    ::= { sonusDsx3ThresholdEntry 48 }

sonusDsx3ThresholdLSESTcaFilter OBJECT-TYPE
    SYNTAX          SonusAdminState
    MAX-ACCESS      read-write
    STATUS          current
    DESCRIPTION     
            "Controls whether a threshold Crossing Alert (TCA) is reported (via
             an event log and trap). Setting this object to Enabled will prevent
             the TCA from being reported (i.e will Filter the TCA report)."
    DEFVAL          { disabled }
    ::= { sonusDsx3ThresholdEntry 49 }

sonusDsx3ThresholdPCVTcaFilter OBJECT-TYPE
    SYNTAX          SonusAdminState
    MAX-ACCESS      read-write
    STATUS          current
    DESCRIPTION     
            "Controls whether a threshold Crossing Alert (TCA) is reported (via
             an event log and trap). Setting this object to Enabled will prevent
             the TCA from being reported (i.e will Filter the TCA report)."
    DEFVAL          { disabled }
    ::= { sonusDsx3ThresholdEntry 50 }

sonusDsx3ThresholdPESTcaFilter OBJECT-TYPE
    SYNTAX          SonusAdminState
    MAX-ACCESS      read-write
    STATUS          current
    DESCRIPTION     
            "Controls whether a threshold Crossing Alert (TCA) is reported (via
             an event log and trap). Setting this object to Enabled will prevent
             the TCA from being reported (i.e will Filter the TCA report)."
    DEFVAL          { disabled }
    ::= { sonusDsx3ThresholdEntry 51 }

sonusDsx3ThresholdPSESTcaFilter OBJECT-TYPE
    SYNTAX          SonusAdminState
    MAX-ACCESS      read-write
    STATUS          current
    DESCRIPTION     
            "Controls whether a threshold Crossing Alert (TCA) is reported (via
             an event log and trap). Setting this object to Enabled will prevent
             the TCA from being reported (i.e will Filter the TCA report)."
    DEFVAL          { disabled }
    ::= { sonusDsx3ThresholdEntry 52 }

sonusDsx3ThresholdUASTcaFilter OBJECT-TYPE
    SYNTAX          SonusAdminState
    MAX-ACCESS      read-write
    STATUS          current
    DESCRIPTION     
            "Controls whether a threshold Crossing Alert (TCA) is reported (via
             an event log and trap). Setting this object to Enabled will prevent
             the TCA from being reported (i.e will Filter the TCA report)."
    DEFVAL          { disabled }
    ::= { sonusDsx3ThresholdEntry 53 }

sonusDsx3ThresholdReportMinorCriticalTca OBJECT-TYPE
    SYNTAX          SonusAdminState
    MAX-ACCESS      read-write
    STATUS          current
    DESCRIPTION     
            "Controls whether Minor-level and Critical-level threshold Crossing
             Alerts (TCA) are reported (via an event log and trap). Setting this
             object to Disabled will prevent all Minor and Critical TCAs from being
             reported."
    DEFVAL          { disabled }
    ::= { sonusDsx3ThresholdEntry 54 }

sonusDsx3ThresholdReportDs3OosTca OBJECT-TYPE
    SYNTAX          SonusAdminState
    MAX-ACCESS      read-write
    STATUS          current
    DESCRIPTION     
            "Controls whether threshold Crossing Alerts (TCA) are reported
             (via an event log and trap) while the DS3 is Out of Service. Setting
             this object to Enabled allows TCAs to be reported while the DS3 is
             Out of Service."
    DEFVAL          { disabled }
    ::= { sonusDsx3ThresholdEntry 55 }

sonusDs3PmonIntervalType OBJECT-TYPE
    SYNTAX          INTEGER { fifteenMin(1), day(2) }
    MAX-ACCESS      read-only
    STATUS          current
    DESCRIPTION     
            "Pmon interval type."
    ::= { sonusDsx3MIBNotificationsObjects 6 }

sonusDsx3ThresholdCrossingNotification NOTIFICATION-TYPE
    OBJECTS         { sonusShelfIndex, sonusSlotIndex, sonusPortIndex, 
                      sonusDs3Index, sonusDs3ThresholdType, 
                      sonusEventDescription, sonusEventClass, 
                      sonusEventLevel, sonusSequenceId, sonusEventTime }
    STATUS          current
    DESCRIPTION     
            "A sonusDsx3ThresholdCrossingNotification trap indicates that a DS3
             threshold has been crossed. The type indicates the type of threshold."
    ::= { sonusDsx3MIBNotificationsPrefix 3 }

sonusDsx3PerfmonIntervalStartedNotification NOTIFICATION-TYPE
    OBJECTS         { sonusShelfIndex, sonusSlotIndex, sonusPortIndex, 
                      sonusDs3Index, sonusDs3PmonIntervalType, 
                      sonusEventDescription, sonusEventClass, 
                      sonusEventLevel, sonusSequenceId, sonusEventTime }
    STATUS          current
    DESCRIPTION     
            "A  sonusDsx3PerfmonIntervalStartedNotification trap indicates that a new
             15 minute or 24 hour performance monitoring interval has started."
    ::= { sonusDsx3MIBNotificationsPrefix 5 }

END -- end of module SONUS-DS3THRESHOLD-MIB.
