--
-- This SMIv2 module has been generated by smidump 0.2-cvs. Do not edit.
--

SONUS-APSOPTIMIZED-MIB DEFINITIONS ::= BEGIN

IMPORTS
    Integer32, MODULE-IDENTITY, OBJECT-TYPE
        FROM SNMPv2-SMI
    sonusApsChanConfigGroupName
        FROM SONUS-APS-MIB
    sonusServicesMIBs
        FROM SONUS-SMI;

sonusApsOptimizedMIB MODULE-IDENTITY
    LAST-UPDATED    "200703280000Z"
    ORGANIZATION    
            "Sonus Networks, Inc."
    CONTACT-INFO    
            "   Customer Support    
             Sonus Networks, Inc.
             7 Technology Park Drive
             Westford, MA 01886
             USA
             
             Tel: 978-614-8100
             Fax: 978-614-8609"
    DESCRIPTION     
            "The MIB Module for configuration and status information unique
             to APS Optimized Bidirectional mode."
    ::= { sonusServicesMIBs 24 }


sonusApsOptimizedMIBObjects OBJECT IDENTIFIER
    ::= { sonusApsOptimizedMIB 1 }

sonusApsOptimizedCommandTable OBJECT-TYPE
    SYNTAX          SEQUENCE OF SonusApsOptimizedCommandEntry
    MAX-ACCESS      not-accessible
    STATUS          current
    DESCRIPTION     
            "This table allows commands to be sent to configured APS groups."
    ::= { sonusApsOptimizedMIBObjects 1 }

sonusApsOptimizedCommandEntry OBJECT-TYPE
    SYNTAX          SonusApsOptimizedCommandEntry
    MAX-ACCESS      not-accessible
    STATUS          current
    DESCRIPTION     
            "An entry in the Sonus APS Optimized Command table."
    INDEX           { sonusApsChanConfigGroupName }
    ::= { sonusApsOptimizedCommandTable 1 }

SonusApsOptimizedCommandEntry ::=
    SEQUENCE {
        sonusApsOptimizedCommandSwitch  INTEGER,
        sonusApsOptimizedCommandTimeout Integer32
    }

sonusApsOptimizedCommandSwitch OBJECT-TYPE
    SYNTAX          INTEGER { noCmd(1), clear(2), lockout(3), 
                        forcedSwitch(4) }
    MAX-ACCESS      read-write
    STATUS          current
    DESCRIPTION     
            "This table provides the ability to initiate APS commands."
    ::= { sonusApsOptimizedCommandEntry 1 }

sonusApsOptimizedCommandTimeout OBJECT-TYPE
    SYNTAX          Integer32 (0..10)
    MAX-ACCESS      read-write
    STATUS          current
    DESCRIPTION     
            "If non-zero, a local request for a Forced Switch command will
             be automatically cleared if far-end does not respond within
             the timeout period. This would typically happen if far-end was
             in a local Lockout state. If zero, the Forced Switch command
             will not automatically be cleared."
    DEFVAL          { 0 }
    ::= { sonusApsOptimizedCommandEntry 2 }

END -- end of module SONUS-APSOPTIMIZED-MIB.
