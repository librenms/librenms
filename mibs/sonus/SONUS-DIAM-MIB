--
-- This SMIv2 module has been generated by smidump 0.2-cvs. Do not edit.
--

SONUS-DIAM-MIB DEFINITIONS ::= BEGIN

IMPORTS
    Ipv6Address
        FROM IPV6-TC
    Counter32, Integer32, IpAddress, MODULE-IDENTITY, OBJECT-TYPE, 
    Unsigned32
        FROM SNMPv2-SMI
    DisplayString, RowStatus
        FROM SNMPv2-TC
    sonusServicesMIBs
        FROM SONUS-SMI
    SonusAdminState, SonusName, SonusNameReference, SonusServiceState
        FROM SONUS-TC;

sonusDiamMIB MODULE-IDENTITY
    LAST-UPDATED    "201010030000Z"
    ORGANIZATION    
            "Sonus Networks, Inc."
    CONTACT-INFO    
            "   Customer Support    
             Sonus Networks, Inc.
             7 Technology Park Drive
             Westford, MA 01886
             USA
             
             Tel: 978-614-8100
             Fax: 978-614-8609
             E-mail: cs.snmp@sonusnet.com"
    DESCRIPTION     
            "The MIB Module for Diameter Client."
    ::= { sonusServicesMIBs 33 }


sonusDiamMIBObjects OBJECT IDENTIFIER
    ::= { sonusDiamMIB 1 }

sonusDiamNode OBJECT IDENTIFIER
    ::= { sonusDiamMIBObjects 1 }

sonusDiamNodeNextIndex OBJECT-TYPE
    SYNTAX          Integer32
    MAX-ACCESS      read-only
    STATUS          current
    DESCRIPTION     
            "The next valid index to use when creating a new sonusDiamNodeEntry"
    ::= { sonusDiamNode 1 }

sonusDiamNodeTable OBJECT-TYPE
    SYNTAX          SEQUENCE OF SonusDiamNodeEntry
    MAX-ACCESS      not-accessible
    STATUS          current
    DESCRIPTION     
            "This table contains information about each Diameter node."
    ::= { sonusDiamNode 2 }

sonusDiamNodeEntry OBJECT-TYPE
    SYNTAX          SonusDiamNodeEntry
    MAX-ACCESS      not-accessible
    STATUS          current
    DESCRIPTION     
            "This table describes the Diameter node."
    INDEX           { sonusDiamNodeIndex }
    ::= { sonusDiamNodeTable 1 }

SonusDiamNodeEntry ::=
    SEQUENCE {
        sonusDiamNodeIndex              Unsigned32,
        sonusDiamNodeName               SonusName,
        sonusDiamNodeRowStatus          RowStatus,
        sonusDiamNodeAdminState         SonusAdminState,
        sonusDiamNodeOriginPrimaryHost  DisplayString,
        sonusDiamNodeOriginSecondaryHost DisplayString,
        sonusDiamNodeOriginRealm        DisplayString,
        sonusDiamNodeTransactionTimeout Unsigned32
    }

sonusDiamNodeIndex OBJECT-TYPE
    SYNTAX          Unsigned32
    MAX-ACCESS      read-only
    STATUS          current
    DESCRIPTION     
            "The index of the diameter node entry."
    ::= { sonusDiamNodeEntry 1 }

sonusDiamNodeName OBJECT-TYPE
    SYNTAX          SonusName
    MAX-ACCESS      read-write
    STATUS          current
    DESCRIPTION     
            "The name of this diameter node entry."
    ::= { sonusDiamNodeEntry 2 }

sonusDiamNodeRowStatus OBJECT-TYPE
    SYNTAX          RowStatus
    MAX-ACCESS      read-write
    STATUS          current
    DESCRIPTION     
            ""
    ::= { sonusDiamNodeEntry 3 }

sonusDiamNodeAdminState OBJECT-TYPE
    SYNTAX          SonusAdminState
    MAX-ACCESS      read-write
    STATUS          current
    DESCRIPTION     
            "The admin state of the diameter node entry."
    DEFVAL          { disabled }
    ::= { sonusDiamNodeEntry 4 }

sonusDiamNodeOriginPrimaryHost OBJECT-TYPE
    SYNTAX          DisplayString (SIZE(0..127))
    MAX-ACCESS      read-write
    STATUS          current
    DESCRIPTION     
            "The origin name for the primary host."
    ::= { sonusDiamNodeEntry 5 }

sonusDiamNodeOriginSecondaryHost OBJECT-TYPE
    SYNTAX          DisplayString (SIZE(0..127))
    MAX-ACCESS      read-write
    STATUS          current
    DESCRIPTION     
            "The origin name for the secondary host."
    ::= { sonusDiamNodeEntry 6 }

sonusDiamNodeOriginRealm OBJECT-TYPE
    SYNTAX          DisplayString (SIZE(0..127))
    MAX-ACCESS      read-write
    STATUS          current
    DESCRIPTION     
            "The origin realm name for this diameter node."
    ::= { sonusDiamNodeEntry 7 }

sonusDiamNodeTransactionTimeout OBJECT-TYPE
    SYNTAX          Unsigned32 (500..32000)
    MAX-ACCESS      read-write
    STATUS          current
    DESCRIPTION     
            "Transaction timeout."
    DEFVAL          { 1000 }
    ::= { sonusDiamNodeEntry 8 }

sonusDiamPeer OBJECT IDENTIFIER
    ::= { sonusDiamMIBObjects 2 }

sonusDiamPeerNextIndex OBJECT-TYPE
    SYNTAX          Integer32
    MAX-ACCESS      read-only
    STATUS          current
    DESCRIPTION     
            "The next valid index to use when creating a new sonusDiamPeerEntry"
    ::= { sonusDiamPeer 1 }

sonusDiamPeerTable OBJECT-TYPE
    SYNTAX          SEQUENCE OF SonusDiamPeerEntry
    MAX-ACCESS      not-accessible
    STATUS          current
    DESCRIPTION     
            "This table contains information about each Diameter peer."
    ::= { sonusDiamPeer 2 }

sonusDiamPeerEntry OBJECT-TYPE
    SYNTAX          SonusDiamPeerEntry
    MAX-ACCESS      not-accessible
    STATUS          current
    DESCRIPTION     
            "This table describes the Diameter peer."
    INDEX           { sonusDiamPeerIndex }
    ::= { sonusDiamPeerTable 1 }

SonusDiamPeerEntry ::=
    SEQUENCE {
        sonusDiamPeerIndex              Unsigned32,
        sonusDiamPeerName               SonusName,
        sonusDiamPeerRowStatus          RowStatus,
        sonusDiamPeerAdminState         SonusAdminState,
        sonusDiamPeerIpAddress          IpAddress,
        sonusDiamPeerFqdn               DisplayString,
        sonusDiamPeerTcpPort            Unsigned32,
        sonusDiamPeerConnStatus         SonusServiceState,
        sonusDiamPeerIp6Address         Ipv6Address,
        sonusDiamPeerIpVersion          INTEGER
    }

sonusDiamPeerIndex OBJECT-TYPE
    SYNTAX          Unsigned32
    MAX-ACCESS      read-only
    STATUS          current
    DESCRIPTION     
            "The index of the diameter peer entry."
    ::= { sonusDiamPeerEntry 1 }

sonusDiamPeerName OBJECT-TYPE
    SYNTAX          SonusName
    MAX-ACCESS      read-write
    STATUS          current
    DESCRIPTION     
            "The name of this diameter peer entry."
    ::= { sonusDiamPeerEntry 2 }

sonusDiamPeerRowStatus OBJECT-TYPE
    SYNTAX          RowStatus
    MAX-ACCESS      read-write
    STATUS          current
    DESCRIPTION     
            ""
    ::= { sonusDiamPeerEntry 3 }

sonusDiamPeerAdminState OBJECT-TYPE
    SYNTAX          SonusAdminState
    MAX-ACCESS      read-write
    STATUS          current
    DESCRIPTION     
            "The admin state of the diameter peer entry."
    DEFVAL          { disabled }
    ::= { sonusDiamPeerEntry 4 }

sonusDiamPeerIpAddress OBJECT-TYPE
    SYNTAX          IpAddress
    MAX-ACCESS      read-write
    STATUS          current
    DESCRIPTION     
            "The IP address for the peer."
    ::= { sonusDiamPeerEntry 5 }

sonusDiamPeerFqdn OBJECT-TYPE
    SYNTAX          DisplayString (SIZE(0..127))
    MAX-ACCESS      read-write
    STATUS          current
    DESCRIPTION     
            "The FQDN for the peer."
    ::= { sonusDiamPeerEntry 6 }

sonusDiamPeerTcpPort OBJECT-TYPE
    SYNTAX          Unsigned32 (1..65535)
    MAX-ACCESS      read-write
    STATUS          current
    DESCRIPTION     
            "TCP port number for the peer."
    DEFVAL          { 3868 }
    ::= { sonusDiamPeerEntry 7 }

sonusDiamPeerConnStatus OBJECT-TYPE
    SYNTAX          SonusServiceState
    MAX-ACCESS      read-only
    STATUS          current
    DESCRIPTION     
            "TCP Connection status to the peer."
    DEFVAL          { outOfService }
    ::= { sonusDiamPeerEntry 8 }

sonusDiamPeerIp6Address OBJECT-TYPE
    SYNTAX          Ipv6Address
    MAX-ACCESS      read-write
    STATUS          current
    DESCRIPTION     
            "The IPV6 address for the peer."
    ::= { sonusDiamPeerEntry 9 }

sonusDiamPeerIpVersion OBJECT-TYPE
    SYNTAX          INTEGER { afInet(2), afInet6(24) }
    MAX-ACCESS      read-only
    STATUS          current
    DESCRIPTION     
            "The IP-Address type for the diameter peer."
    ::= { sonusDiamPeerEntry 10 }

sonusDiamRoute OBJECT IDENTIFIER
    ::= { sonusDiamMIBObjects 3 }

sonusDiamRouteNextIndex OBJECT-TYPE
    SYNTAX          Integer32
    MAX-ACCESS      read-only
    STATUS          current
    DESCRIPTION     
            "The next valid index to use when creating a new sonusDiamRouteEntry"
    ::= { sonusDiamRoute 1 }

sonusDiamRouteTable OBJECT-TYPE
    SYNTAX          SEQUENCE OF SonusDiamRouteEntry
    MAX-ACCESS      not-accessible
    STATUS          current
    DESCRIPTION     
            "This table contains information about each Diameter route."
    ::= { sonusDiamRoute 2 }

sonusDiamRouteEntry OBJECT-TYPE
    SYNTAX          SonusDiamRouteEntry
    MAX-ACCESS      not-accessible
    STATUS          current
    DESCRIPTION     
            "This table describes the Diameter route."
    INDEX           { sonusDiamRouteIndex }
    ::= { sonusDiamRouteTable 1 }

SonusDiamRouteEntry ::=
    SEQUENCE {
        sonusDiamRouteIndex             Unsigned32,
        sonusDiamRouteName              SonusName,
        sonusDiamRouteRowStatus         RowStatus,
        sonusDiamRouteAdminState        SonusAdminState,
        sonusDiamRouteRealm             DisplayString,
        sonusDiamRouteApplicationId     INTEGER,
        sonusDiamRoutePeerName          SonusNameReference,
        sonusDiamRoutePriority          Unsigned32
    }

sonusDiamRouteIndex OBJECT-TYPE
    SYNTAX          Unsigned32
    MAX-ACCESS      read-only
    STATUS          current
    DESCRIPTION     
            "The index of the diameter route entry."
    ::= { sonusDiamRouteEntry 1 }

sonusDiamRouteName OBJECT-TYPE
    SYNTAX          SonusName
    MAX-ACCESS      read-write
    STATUS          current
    DESCRIPTION     
            "The name of this diameter route entry."
    ::= { sonusDiamRouteEntry 2 }

sonusDiamRouteRowStatus OBJECT-TYPE
    SYNTAX          RowStatus
    MAX-ACCESS      read-write
    STATUS          current
    DESCRIPTION     
            ""
    ::= { sonusDiamRouteEntry 3 }

sonusDiamRouteAdminState OBJECT-TYPE
    SYNTAX          SonusAdminState
    MAX-ACCESS      read-write
    STATUS          current
    DESCRIPTION     
            "The admin state of the diameter route entry."
    DEFVAL          { disabled }
    ::= { sonusDiamRouteEntry 4 }

sonusDiamRouteRealm OBJECT-TYPE
    SYNTAX          DisplayString (SIZE(0..127))
    MAX-ACCESS      read-write
    STATUS          current
    DESCRIPTION     
            "The realm (FQDN) associated with this route."
    ::= { sonusDiamRouteEntry 5 }

sonusDiamRouteApplicationId OBJECT-TYPE
    SYNTAX          INTEGER { rx(0) }
    MAX-ACCESS      read-write
    STATUS          current
    DESCRIPTION     
            "The application ID associated with this route. (Only Rx current supported)."
    DEFVAL          { 0 }
    ::= { sonusDiamRouteEntry 6 }

sonusDiamRoutePeerName OBJECT-TYPE
    SYNTAX          SonusNameReference
    MAX-ACCESS      read-write
    STATUS          current
    DESCRIPTION     
            "The peer name to use for this route."
    ::= { sonusDiamRouteEntry 7 }

sonusDiamRoutePriority OBJECT-TYPE
    SYNTAX          Unsigned32 (0..31)
    MAX-ACCESS      read-write
    STATUS          current
    DESCRIPTION     
            "The priority for this route (lower number means higher priority.)"
    DEFVAL          { 0 }
    ::= { sonusDiamRouteEntry 8 }

END -- end of module SONUS-DIAM-MIB.
