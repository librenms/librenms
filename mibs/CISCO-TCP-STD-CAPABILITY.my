-- *****************************************************************
-- CISCO-TCP-STD-CAPABILITY.my: TCP-MIB AGENT-CAPABILITIES
--   
-- February 2006, Sreenivasulu Chalamcharla
--   
-- Copyright (c) 2006, 2008 by cisco Systems, Inc.
-- All rights reserved.
--   
-- *****************************************************************

CISCO-TCP-STD-CAPABILITY DEFINITIONS ::= BEGIN

IMPORTS
    MODULE-IDENTITY
        FROM SNMPv2-SMI
    AGENT-CAPABILITIES
        FROM SNMPv2-CONF
    ciscoAgentCapability
        FROM CISCO-SMI;


ciscoTcpStdCapability MODULE-IDENTITY
    LAST-UPDATED    "200808110000Z"
    ORGANIZATION    "Cisco Systems, Inc."
    CONTACT-INFO
            "Cisco Systems
            Customer Service
            Postal: 170 West Tasman Drive
            San Jose, CA  95134
            USA

            Tel: +1 800 553-NETS

            E-mail: cs-snmp@cisco.com"
    DESCRIPTION
        "Agent capabilities for TCP-MIB"
    REVISION        "200808110000Z"
    DESCRIPTION
        "Added newlines at the end of the MIB file."
    REVISION        "200802080000Z"
    DESCRIPTION
        "Added ciscoTcpStdCapc4710aceVA1R700 agent
        capability for ACE 4710 Application Control Engine
        Appliance."
    REVISION        "200611080000Z"
    DESCRIPTION
        "Added ciscoTcpStdCapIOSXRV3R4CRS1 agent
        capability for IOS XR 3.4"
    REVISION        "200610250000Z"
    DESCRIPTION
        "Added capability for Cisco TelePresence System (CTS) and
        Cisco TelePresence Manager (CTM) platforms."
    REVISION        "200605260000Z"
    DESCRIPTION
        "Added capability statement
        ciscoTcpStdCapACSWV03R000"
    REVISION        "200602060000Z"
    DESCRIPTION
        "Initial version of this MIB module."
    ::= { ciscoAgentCapability 481 }



ciscoTcpStdCapIOSXRV3R2CRS1 AGENT-CAPABILITIES
    PRODUCT-RELEASE "Cisco IOS XR 3.2.0 for CRS-1"
    STATUS          current
    DESCRIPTION
        "TCP-MIB capabilities
        for IOS XR release 3.2.0"

    SUPPORTS        TCP-MIB
    INCLUDES        {
                        tcpGroup,
                        tcpBaseGroup,
                        tcpConnectionGroup,
                        tcpHCGroup
                    }
    VARIATION       tcpConnectionProcess
    ACCESS          not-implemented
    DESCRIPTION
        "No backend supported is provided to
        get the process ID."

    ::= { ciscoTcpStdCapability 1 }

ciscoTcpStdCapACSWV03R000 AGENT-CAPABILITIES
    PRODUCT-RELEASE "ACSW (Application Control Software) 3.0

                    for Application Control Engine(ACE)

                    Service Module."
    STATUS          current
    DESCRIPTION
        "TCP-MIB capabilities for ACSW 3.0"

    SUPPORTS        TCP-MIB
    INCLUDES        { tcpBaseGroup }
    ::= { ciscoTcpStdCapability 2 }

ciscoTcpStdCapCTSV100 AGENT-CAPABILITIES
    PRODUCT-RELEASE "Cisco TelePresence System (CTS) 1.0.0."
    STATUS          current
    DESCRIPTION
        "TCP-MIB capabilities for CTS 1.0.0"

    SUPPORTS        TCP-MIB
    INCLUDES        { tcpGroup }
    VARIATION       tcpConnState
    ACCESS          read-only
    DESCRIPTION
        "Write operation not allowed via SNMP."

    ::= { ciscoTcpStdCapability 3 }

ciscoTcpStdCapCTMV1000 AGENT-CAPABILITIES
    PRODUCT-RELEASE "Cisco TelePresence Manager (CTM) 1.0.0.0."
    STATUS          current
    DESCRIPTION
        "TCP-MIB capabilities for CTM 1.0.0.0"

    SUPPORTS        TCP-MIB
    INCLUDES        { tcpGroup }
    VARIATION       tcpConnState
    ACCESS          read-only
    DESCRIPTION
        "Write operation not allowed via SNMP."

    ::= { ciscoTcpStdCapability 4 }

ciscoTcpStdCapIOSXRV3R4CRS1 AGENT-CAPABILITIES
    PRODUCT-RELEASE "Cisco IOS XR 3.4 for CRS-1"
    STATUS          current
    DESCRIPTION
        "TCP-MIB capabilities
        for IOS XR release 3.4"

    SUPPORTS        TCP-MIB
    INCLUDES        {
                        tcpGroup,
                        tcpBaseGroup,
                        tcpConnectionGroup,
                        tcpHCGroup
                    }
    ::= { ciscoTcpStdCapability 5 }

ciscoTcpStdCapc4710aceVA1R700 AGENT-CAPABILITIES
    PRODUCT-RELEASE "ACSW (Application Control Software) A1(7)
                    for ACE 4710 Application Control Engine 
                    Appliance."
    STATUS          current
    DESCRIPTION
        "TCP-MIB capabilities for ACSW A1(7)"

    SUPPORTS        TCP-MIB
    INCLUDES        { tcpBaseGroup }
    ::= { ciscoTcpStdCapability 6 }

END
