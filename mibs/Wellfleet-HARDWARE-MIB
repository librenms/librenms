Wellfleet-HARDWARE-MIB DEFINITIONS ::= BEGIN

-- Created by mdl2asn version 3.1
-- Creation date: Wed Aug 30 16:42:01 EDT 1995


    IMPORTS

      OBJECT-TYPE
        FROM RFC-1212
      DisplayString
        FROM RFC1213-MIB
      wfHardwareConfig
        FROM Wellfleet-COMMON-MIB;


    wfHwBase	OBJECT IDENTIFIER ::= { wfHardwareConfig 1 }

    wfHwBpIdOpt OBJECT-TYPE
        SYNTAX	INTEGER {
    		    acefn(1),
    		    aceln(2),
    		    acecn(3),
    		    afn(4),
    		    in(5),
    		    an(16),
		    arn(32),
                    fbr4slot(34),
		    lite(36),
    		    sys5000(5000),
    		    freln(16640),
    		    frecn(16896),
    		    frerbln(17152),
    		    asn(20480),
    		    asnzcable(20736),
    		    asnbcable(20992),
                    sn(24576),
    		    v15k(26368)
    		}
        ACCESS	read-only
        STATUS	mandatory
        DESCRIPTION
                "The BackPlane identification number."
        ::= { wfHwBase 1 }

    wfHwBpRev OBJECT-TYPE
        SYNTAX	OCTET STRING
        ACCESS	read-only
        STATUS	mandatory
        DESCRIPTION
                "The revision level of the BackPlane. High byte is in upper 2 bytes."
        ::= { wfHwBase 2 }

    wfHwBpSerialNumber OBJECT-TYPE
        SYNTAX	OCTET STRING
        ACCESS	read-only
        STATUS	mandatory
        DESCRIPTION
                "The serial number of the BackPlane."
        ::= { wfHwBase 3 }

    wfBCNPwrSupply1 OBJECT-TYPE
        SYNTAX	INTEGER {
    		    ok(1),
    		    fail(2),
    		    notpresent(3)
    		}
        ACCESS	read-only
        STATUS	mandatory
        DESCRIPTION
                "Status of BCN Hot-Swappable Power Supply 1"
        DEFVAL	{ notpresent }
        ::= { wfHwBase 4 }

    wfBCNPwrSupply2 OBJECT-TYPE
        SYNTAX	INTEGER {
    		    ok(1),
    		    fail(2),
    		    notpresent(3)
    		}
        ACCESS	read-only
        STATUS	mandatory
        DESCRIPTION
                "Status of BCN Hot-Swappable Power Supply 2"
        DEFVAL	{ notpresent }
        ::= { wfHwBase 5 }

    wfBCNPwrSupply3 OBJECT-TYPE
        SYNTAX	INTEGER {
    		    ok(1),
    		    fail(2),
    		    notpresent(3)
    		}
        ACCESS	read-only
        STATUS	mandatory
        DESCRIPTION
                "Status of BCN Hot-Swappable Power Supply 3"
        DEFVAL	{ notpresent }
        ::= { wfHwBase 6 }

    wfBCNPwrSupply4 OBJECT-TYPE
        SYNTAX	INTEGER {
    		    ok(1),
    		    fail(2),
    		    notpresent(3)
    		}
        ACCESS	read-only
        STATUS	mandatory
        DESCRIPTION
                "Status of BCN Hot-Swappable Power Supply 4"
        DEFVAL	{ notpresent }
        ::= { wfHwBase 7 }

    wfBCNFanStatus OBJECT-TYPE
        SYNTAX	INTEGER {
    		    ok(1),
    		    fail(2),
    		    notpresent(3)
    		}
        ACCESS	read-only
        STATUS	mandatory
        DESCRIPTION
                "Status of BCN Fan Tray"
        DEFVAL	{ notpresent }
        ::= { wfHwBase 8 }

    wfBCNTemperature OBJECT-TYPE
        SYNTAX	INTEGER {
    		    ok(1),
    		    caution(2),
    		    notpresent(3),
    		    fail(4)
    		}
        ACCESS	read-only
        STATUS	mandatory
        DESCRIPTION
                "Status of BCN Temperature sensor"
        DEFVAL	{ notpresent }
        ::= { wfHwBase 9 }

    wfBCNTemperature2 OBJECT-TYPE
        SYNTAX	INTEGER {
    		    ok(1),
    		    caution(2),
    		    notpresent(3),
    		    fail(4)
    		}
        ACCESS	read-only
        STATUS	mandatory
        DESCRIPTION
                "Status of second BCN Temperature sensor"
        DEFVAL	{ notpresent }
        ::= { wfHwBase 10 }

    wfFanSpeed OBJECT-TYPE
        SYNTAX	INTEGER {
    		    low(1),
    		    high(2),
    		    notpresent(3)
    		}
        ACCESS	read-only
        STATUS	mandatory
        DESCRIPTION
                "This object indicates the current speed of the fan module"
        DEFVAL	{ notpresent }
        ::= { wfHwBase 11 }

    wfHwTable OBJECT-TYPE
        SYNTAX	SEQUENCE OF WfHwEntry
        ACCESS	not-accessible
        STATUS	mandatory
        DESCRIPTION
                "Hardware Table  - indexed by slot number"
        ::= { wfHardwareConfig 2 }

    wfHwEntry OBJECT-TYPE
        SYNTAX	WfHwEntry
        ACCESS not-accessible
        STATUS	mandatory
        DESCRIPTION
                "Hardware specific information about a slot."
        INDEX	{ wfHwSlot }
        ::= { wfHwTable 1 }

    WfHwEntry ::= SEQUENCE {
    	    wfHwSlot
    		INTEGER,
    	    wfHwModIdOpt
    		INTEGER,
    	    wfHwModRev
    		OCTET STRING,
    	    wfHwModSerialNumber
    		OCTET STRING,
    	    wfHwMotherBdIdOpt
    		INTEGER,
    	    wfHwMotherBdRev
    		OCTET STRING,
    	    wfHwMotherBdSerialNumber
    		OCTET STRING,
    	    wfHwDaughterBdIdOpt
    		INTEGER,
    	    wfHwDaughterBdRev
    		OCTET STRING,
    	    wfHwDaughterBdSerialNumber
    		OCTET STRING,
    	    wfHwBabyBdIdOpt
    		INTEGER,
    	    wfHwBabyBdRev
    		OCTET STRING,
    	    wfHwBabyBdSerialNumber
    		OCTET STRING,
    	    wfHwDiagPromRev
    		OCTET STRING,
    	    wfHwDiagPromDate
    		DisplayString,
    	    wfHwDiagPromSource
    		DisplayString,
    	    wfHwBootPromRev
    		OCTET STRING,
    	    wfHwBootPromDate
    		DisplayString,
    	    wfHwBootPromSource
    		DisplayString,
    	    wfHwSparePromRev
    		OCTET STRING,
    	    wfHwSparePromDate
    		DisplayString,
    	    wfHwSparePromSource
    		DisplayString,
    	    wfHwFileSysPresent
    		INTEGER,
    	    wfHwFileSysPresent2
    		INTEGER,
    	    wfHwConfigServer
    		INTEGER,
    	    wfHwConfigFile
    		DisplayString,
    	    wfHwConfigDateAndTime
    		OCTET STRING,
    	    wfHwActiveImageName
    		DisplayString,
    	    wfHwActiveImageSource
    		DisplayString,
    	    wfHwActiveImageDate
    		DisplayString,
    	    wfHwMotherBdMemorySize
    		INTEGER,
    	    wfHwFastPacketCacheSize
    		INTEGER,
    	    wfHwModDaughterBd1IdOpt
    		INTEGER,
    	    wfHwModDaughterBd1AwRev
    		OCTET STRING,
    	    wfHwModDaughterBd1Rev
    		OCTET STRING,
    	    wfHwModDaughterBd1SerialNumber
    		OCTET STRING,
    	    wfHwModDaughterBd2IdOpt
    		INTEGER,
    	    wfHwModDaughterBd2AwRev
    		OCTET STRING,
    	    wfHwModDaughterBd2Rev
    		OCTET STRING,
    	    wfHwModDaughterBd2SerialNumber
    		OCTET STRING,
            wfRASNPwrSupply1
                INTEGER,
            wfRASNPwrSupply2
                INTEGER,
            wfPowerSupply1
                INTEGER,
            wfPowerSupply2
                INTEGER,
            wfFanStatus1
                INTEGER,
            wfFanStatus2
                INTEGER,
            wfRASNRPSUPresent
                INTEGER,
	    wfModDiagStatus
		INTEGER
        }

    wfHwSlot OBJECT-TYPE
        SYNTAX	INTEGER
        ACCESS	read-only
        STATUS	mandatory
        DESCRIPTION
                "A unique value for each slot.
                Its value ranges between 1 and 14.
                There are products in this family that contain 1, 5, and 14 slots."
        ::= { wfHwEntry 1 }

    wfHwModIdOpt OBJECT-TYPE
        SYNTAX	INTEGER {
    		    enet1(1),
    		    enet2(8),
    		    sync1(16),
    		    sync1a(17),
    		    t11(24),
    		    dse1(32),
    		    dse1a(33),
    		    dst416(40),
    		    sst416a(41),
    		    dst4(42),
    		    sst4a(43),
    		    sst416(44),
    		    stok416(45),
    		    sst4(46),
    		    stok4(47),
    		    floppy(48),
    		    necfloppy(49),
    		    t12(56),
    		    t12a(57),
    		    st1(58),
    		    t156k(60),
    		    e1(61),
    		    st156k(62),
    		    se1(63),
    		    t12n(64),
    		    st1n(65),
    		    t156kn(66),
    		    st156kn(67),
    		    e1n(68),
    		    se1n(69),
    		    sync(80),
    		    sync2a(81),
    		    cmcfddi(88),
    		    iphfddi(89),
    		    dt(104),
    		    dsde1(112),
    		    dsde1a(113),
    		    enet(114),
    		    dse2(116),
    		    dse2a(117),
    		    sse(118),
    		    ssea(119),
    		    dsde10bt(120),
    		    enet3(132),
    		    dsde2(156),
    		    oldqenf(160),
    		    denf(161),
    		    qenf(162),
    		    qef(164),
    		    def(165),
    		    mct1(168),
    		    smct1(169),
    		    dtok(176),
    		    mce1(184),
    		    smce1(185),
    		    mce1ii75(188),
    		    smce1ii75(189),
    		    mce1ii120(190),
    		    smce1ii120(191),
    		    wffddi2m(192),
    		    wffddi1m(193),
    		    wffddi2s(194),
    		    wffddi1s(195),
    		    wffddi2mf(196),
    		    wffddi1mf(197),
    		    wffddi2sf(198),
    		    wffddi1sf(199),
    		    fmdset(200),
    		    fmdst(201),
    		    fmdse(202),
    		    fmsst(203),
    		    fmsse(204),
    		    fnsdse(208),
    		    fnsdsdt(216),
    		    fnsdst(217),
    		    dhssi(224),
    		    shssi(225),
    		    esafnf(232),
    		    esafdsenf(233),
    		    esafssenf(234),
    		    esafdenf(235),
    		    esaf(236),
    		    esafdse(237),
    		    esafsse(238),
    		    esafde(239),
    		    qtok(256),
                    m5380(508),
		    m5580(509),
		    m5780(510),
    		    asn(511),
                    sn(513),
		    m5782(512),
		    arn(767),
                    fbrcpu(777),
		    lite(787),
                    fbr2pmccarrier(778),
    		    anseds(1024),
    		    ansedst(1025),
    		    ansedsh(1026),
    		    ansedsi(1027),
    		    ansedsti(1028),
    		    ansedshi(1029),
    		    ansets(1030),
    		    ansetst(1031),
    		    ansetsh(1032),
    		    andeds(1033),
    		    andedst(1034),
    		    andedsh(1035),
    		    andstx(1036),
    		    andst(1037),
    		    andsti(1038),
    		    antst(1039),
    		    antstx(1040),
    		    ansdsedst(1041),
    		    ansdsedstx(1042),
    		    ansedsi2(1043),
    		    ansedsti2(1044),
    		    ansedshi2(1045),
    		    andsti2(1046),
    		    ansedsg(1047),
    		    ansedsgx(1048),
    		    ansetsg(1049),
    		    andedsg(1050),
    		    ansedsgi(1051),
    		    ansetsgx(1052),
    		    andedsgx(1053),
    		    ansedsgix(1054),
    		    ansedsx(1055),
    		    ansetsx(1056),
    		    andedsx(1057),
    		    ansedstx(1058),
    		    ansetstx(1059),
    		    andedstx(1060),
    		    andsti2x(1061),
    		    ansedsi2x(1062),
    		    ansedsti2x(1063),
                    ansedi(1064),
                    ansedsu(1066),
                    ansedsu2(1067),
                    andstu(1068),
                    andstu2(1069),
                    ansedstu(1070),
                    ansedstu2(1071),
                    ansedshu(1072),
                    ansedshu2(1073),
                    ansedsgu(1074),
                    ansedsu2x(1075),
                    andstu2x(1076),
                    ansedstu2x(1077),
                    ansedshu2x(1078),
                    ansedsgu2x(1079),
                    ansedsv(1080),
                    andstv(1081),
                    ansedstv(1082),
                    ansedshv(1083),
                    ansedsgv(1084),
                    ansedsvx(1085),
                    andstvx(1086),
                    ansedstvx(1087),
                    ansedshvx(1088),
                    ansedsgvx(1089),
                    ansedsc(1090),
                    andstc(1091),
                    ansedstc(1092),
                    ansedshc(1093),
                    ansedsgc(1094),
                    ansedscx(1095),
                    andstcx(1096),
                    ansedstcx(1097),
                    ansedshcx(1098),
                    ansedsgcx(1099),
                    ansedsf(1100),
                    ansedsf2(1101),
                    andstf(1102),
                    andstf2(1103),
                    ansedstf(1104),
                    ansedstf2(1105),
                    ansedshf(1106),
                    ansedshf2(1107),
                    ansedsgf(1108),
                    ansedsf2x(1109),
                    andstf2x(1110),
                    ansedstf2x(1111),
                    ansedshf2x(1112),
                    ansedsgf2x(1113),
                    ansedsfx(1114),
                    andstfx(1115),
                    ansedstfx(1116),
                    ansedshfx(1117),
                    ansedsgfx(1118),
                    ansedsj(1119),
                    ansedsj2(1120),
                    andstj(1121),
                    andstj2(1122),
                    ansedstj(1123),
                    ansedstj2(1124),
                    ansedshj(1125),
                    ansedshj2(1126),
                    ansedsgj(1127),
                    ansedsj2x(1128),
                    andstj2x(1129),
                    ansedstj2x(1130),
                    ansedshj2x(1131),
                    ansedsgj2x(1132),
                    ansedsjx(1133),
                    andstjx(1134),
                    ansedstjx(1135),
                    ansedshjx(1136),
                    ansedsgjx(1137),
    		    atmalc(4096),
    		    atmalctaxi100(4097),
    		    atmalcsonetmm(4098),
    		    atmalcsonetsm(4099),
    		    osync(4352),
    		    comp(4353),
    		    comp128(4354),
    		    atmcoc3mm(4608),
    		    atmcoc3sm(4609),
    		    atmcoc3utp5(4610),
    		    de100(4864),
    		    atmcds3(5120),
    		    atmce3(5121),
		    qmct1rj48(5376),
		    qmct1db15(5377),
		    qmct1ds0a(5378),
                    sqe100(6144),
		    sqe100fx(6145),
                    gigenet(6400),
		    gigenetlx(6401),
    		    srml(8448),
   		    fvoip(8500),
    		    hds3(24848),
                    arm(24849),
    		    dmcoc3(24864),
    		    atmoc12(24880),
    		    sspcons(24896),
    		    sspenet(24912),
		    atm5000ah(524288),
		    atm5000bh(524544),
    		    qe(1048799),
    		    qehwf(1048798),
    		    qefddi2m(1048831),
    		    qefddi2mhwf(1048830),
    		    qefddi2s(1048823),
    		    qefddi2shwf(1048822),
    		    qefddi1m(1048815),
    		    qefddi1mhwf(1048814),
    		    qefddi1s(1048807),
    		    qefddi1shwf(1048806),
    		    qecddi2stp(1048827),
    		    qecddi2stphwf(1048826),
    		    qecddi1stp(1048811),
    		    qecddi1stphwf(1048810),
    		    qecddi2utp(1048763),
    		    qecddi2utphwf(1048762),
    		    qecddi1utp(1048747),
    		    qecddi1utphwf(1048746),
    		    enet3atm(1048832),
    		    enet3enet(1048833),
    		    enet3fddi(1048834),
    		    enet3tok(1048835),
    		    enet3tokf(1048836),
    		    enet3sync(1048837),
    		    enet3only(1048863),
    		    fddiatm(1048864),
    		    fddienet(1048865),
    		    fddifddi(1048866),
    		    fdditok(1048867),
    		    fdditokf(1048868),
    		    fddisync(1048869),
    		    fddionly(1048895),
    		    tok3atm(1048896),
    		    tok3enet(1048897),
    		    tok3fddi(1048898),
    		    tok3tok(1048899),
    		    tok3tokf(1048900),
    		    tok3sync(1048901),
    		    tok3only(1048927),
    		    tokf3atm(1048928),
    		    tokf3enet(1048929),
    		    tokf3fddi(1048930),
    		    tokf3tok(1048931),
    		    tokf3tokf(1048932),
    		    tokf3sync(1048933),
    		    tokf3only(1048959),
    		    enet3datm(1048960),
    		    enet3denet(1048961),
    		    enet3dfddi(1048962),
    		    enet3dtok(1048963),
    		    enet3dtokf(1048964),
    		    enet3dsync(1048965),
    		    enet3donly(1048991),
    		    chipcomfenet(1049089),
    		    chipcomffddi(1049090),
    		    chipcomftok(1049091),
    		    chipcomftokf(1049092),
    		    chipcomfdsync(1049093),
    		    chipcomfisdn(1049094),
    		    chipcomffddis(1049095),
    		    chipcomfonly(1049119),
    		    chipcomenet(1049217),
    		    chipcomfddi(1049218),
    		    chipcomtok(1049219),
    		    chipcomtokf(1049220),
    		    chipcomdsync(1049221),
    		    chipcomisdn(1049222),
    		    chipcomfddis(1049223),
    		    chipcomonly(1049247),
                    fntsenet(1049344),
                    fntstok(1049376)

    		}
        ACCESS	read-only
        STATUS	mandatory
        DESCRIPTION
                "The module identification number.

                                          Port Configurations
              HWStat Name                 Enet   Sync     Async Token Framer Fiber
              ------ ------------         ------ -------- ----- ----- ------ -----
                   1 ENET-1               2      0        0     0     0      0
                   8 ENET-2               2      0        0     0     0      0

                  16 SYNC-1               0      4        1     0     0      0
                  17 SYNC-1[1]            0      4        1     0     0      0

                  24 T1-1                 0      2        1     0     2      0

                  32 DSE-1                1      2        1     0     0      0
                  33 DSE-1[1]             1      2        1     0     0      0

                  40 DST-4/16             0      2        1     1     0      0
                  41 SST-4/16[1]          0      1        1     1     0      0
                  42 DST-4                0      2        1     1     0      0
                  43 SST-4[1]             0      1        1     1     0      0
                  44 SST-4/16             0      1        1     1     0      0
                  45 STOK-4/16[3]         0      0        0     1     0      0
                  46 SST-4                0      1        1     1     0      0
                  47 STOK-4[3]            0      0        0     1     0      0

                  48 FLOPPY               0      0        0     0     0      0

                  56 T1-2                 0      2        1     0     2      0
                  57 T1-2                 0      2        1     0     2      0
                  58 ST1                  0      1        1     0     1      0
                  60 T1-56K               0      1        1     0     1      0
                  61 E1[3]                0      2        0     0     2      0
                  62 ST1-56K              0      1        1     0     1      0
                  63 SE1[3]               0      1        0     0     1      0

                  64 T1-2n                0      2        1     0     2      0
                  65 ST1n                 0      1        1     0     1      0
                  66 T1-56Kn              0      1        1     0     1      0
                  67 ST1-56Kn             0      1        1     0     1      0
                  68 E1n[3]               0      2        0     0     2      0
                  69 SE1n[3]              0      1        0     0     1      0

                  80 SYNC-2               0      4        1     0     0      0
                  81 SYNC-2[1]            0      4        1     0     0      0

                  88 CMC-FDDI[6]          0      0        0     0     0      1
                  89 IPHASE-FDDI[6]       0      0        0     0     0      1

                 112 DSDE-1               2      2        1     0     0      0
                 113 DSDE-1[1]            2      2        1     0     0      0
                 114 ENET                 2      0        0     0     0      0
                 116 DSE-2                1      2        1     0     0      0
                 117 DSE-2[1]             1      2        1     0     0      0
                 118 SSE                  1      1        1     0     0      0
                 119 SSE[1]               1      1        1     0     0      0

                 132 ENET-3[2]            2      0        0     0     0      0

                 156 DSDE-2[2]            2      2        1     0     0      0

                 160 QE/NF                4      0        0     0     0      0
                 161 DE/NF[5]             2      0        0     0     0      0
                 162 QE/NF                4      0        0     0     0      0
                 164 QE/F[4]              4      0        0     0     0      0
                 165 DE/F[4,5]            2      0        0     0     0      0

                 168 MCT1                 0      2 Munich 0     0     2      0
                 169 SMCT1                0      1 Munich 0     0     1      0

                 176 DTOK                 0      0        0     2     0      0

                 184 MCE1                 0      2 Munich 0     0     2      0
                 185 SMCE1                0      1 Munich 0     0     1      0
                 188 MCE1II75             0      2 Munich 0     0     2      0
                 189 SMCE1II75            0      1 Munich 0     0     1      0
                 190 MCE1II120            0      2 Munich 0     0     2      0
                 191 SMCE1II120           0      1 Munich 0     0     1      0

                 192 WF_FDDI_2M           0      0        0     0     0      1
                 193 WF_FDDI_1M           0      0        0     0     0      1
                 194 WF_FDDI_2S           0      0        0     0     0      1
                 195 WF_FDDI_1S           0      0        0     0     0      1
                 196 WF_FDDI_2MF          0      0        0     0     0      1
                 197 WF_FDDI_1MF          0      0        0     0     0      1
                 198 WF_FDDI_2SF          0      0        0     0     0      1
                 199 WF_FDDI_1SF          0      0        0     0     0      1

                 200 HW_MODULE_FMDSET[7]  1      2        0     1     0      0
                 201 HW_MODULE_FMDST[7]   0      2        0     1     0      0
                 202 HW_MODULE_FMDSE[7]   1      2        0     0     0      0
                 203 HW_MODULE_FMSST[7]   0      1        0     1     0      0
                 204 HW_MODULE_FMSSE[7]   1      1        0     0     0      0

                 208 FNSDSE[7]            1      2        0     0     0      0
                 216 FNSDSDT[7]           0      2        0     2     0      0
                 217 FNSDST[7]            0      2        0     1     0      0

                 224 DHSSI                0      2 hssi   0     0     0      0
                 225 SHSSI                0      1 hssi   0     0     0      0

                 232 ESAF_NF              2      2        0     0     0      0
                 233 ESAF_DSE_NF          1      2        0     0     0      0
                 234 ESAF_SSE_NF          1      1        0     0     0      0
                 235 ESAF_DE_NF           2      0        0     0     0      0
                 236 ESAF[2]              2      2        0     0     0      0
                 237 ESAF_DSE[2]          1      2        0     0     0      0
                 238 ESAF_SSE[2]          1      1        0     0     0      0
                 239 ESAF_DE[2]           2      0        0     0     0      0

                 256 QTOK                 0      0        0     4     0      0

                 511 ASN[8]               ASN (Barracuda)

                 513 SN[12]               SN  (Fiddlestix)

                 767 ARN[11]              ARN (Neptune)

                 777 FBR[13]              FBR (Orion)

                 778 FBRCARRIER[14]       FBR Carrier Card (Orion)

                 787 LITE                 LITE (Valkyrie)

                 AN Module IDs (Piranha, Guppy...)

                 ID      Mnemonic        ENET    SYNC    ISDN    TR      HUB     DCM
                 --      --------        ----    ----    ----    --      ---     ---
                 1024    ANSEDS          1       2       0       0       0       N

                 1025    ANSEDST         1       2       0       1       0       N

                 1026    ANSEDSH         1       2       0       0       12      N

                 1027    ANSEDSI         1       2       1       0       0       N

                 1028    ANSEDSTI        1       2       1       1       0       N

                 1029    ANSEDSHI        1       2       1       0       12      N

                 1030    ANSETS          1       3       0       0       0       N

                 1031    ANSETST         1       3       0       1       0       N

                 1032    ANSETSH         1       3       0       0       12      N

                 1033    ANDEDS          2       2       0       0       0       N

                 1034    ANDEDST         2       2       0       1       0       N

                 1035    ANDEDSH         2       2       0       0       12      N

                 1036    ANDSTX          0       2       0       1       0       Y
                 (formerly ANDS)

                 1037    ANDST           0       2       0       1       0       N

                 1038    ANDSTI          0       2       1       1       0       N

                 1039    ANTST           0       3       0       1       0       N

                 1040    ANTSTX          0       3       0       1       0       Y
                 (formerly ANSDSEDS)

                 1041    ANSDSEDST       1       2       0       1       0       N

                 1042    ANSDSEDSTX      1       2       0       1       0       Y
                 (formerly ANSDSEDSH)

                 1043    ANSEDSI2        1       2       1       0       0       N

                 1044    ANSEDSTI2       1       2       1       1       0       N

                 1045    ANSEDSHI2       1       2       1       0       12      N

                 1046    ANDSTI2         0       2       1       1       0       N

                 1047    ANSEDSG         1       2       0       0       8       N

                 1048    ANSEDSGX        1       2       0       0       8       Y

                 1049    ANSETSG         1       3       0       0       8       N

                 1050    ANDEDSG         2       2       0       0       8       N

                 1051    ANSEDSGI        1       2       1       0       8       N

                 1052    ANSETSGX        1       3       0       0       8       Y

                 1053    ANDEDSGX        2       2       0       0       8       Y

                 1054    ANSEDSGIX       1       2       1       0       8       Y

                 1055    ANSEDSX         1       2       0       0       0       Y

                 1056    ANSETSX         1       3       0       0       0       Y

                 1057    ANDEDSX         2       2       0       0       0       Y

                 1058    ANSEDSTX        1       2       0       1       0       Y

                 1059    ANSETSTX        1       3       0       1       0       Y

                 1060    ANDEDSTX        2       2       0       1       0       Y

                 1061    ANDSTI2X        0       2       1       0       0       Y

                 1062    ANSEDSI2X       1       2       1       0       0       Y

                 1063    ANSEDSTI2X      1       2       1       1       0       Y


                 4096    ATMALC          0       0       0       0       0       0
                 4097    ATMALCTAXI100   0       0       0       0       0       1
                 4098    ATMALCSONETMM   0       0       0       0       1       1 [9]
                 4099    ATMALCSONETSM   0       0       0       0       1       1 [9]
                 4352    OSYNC           0       8       0       0       0       0
                 4353    OSYNC_COMP (32) 0       8       0       0       0       0
                 4354    OSYNC_COMP128   0       8       0       0       0       0

                 4608    ATMCOC3MM       0       0       0       0       1       1 [10]
                 4609    ATMCOC3SM       0       0       0       0       1       1 [10]
                 4610    ATMCOC3UTP5     0       0       0       0       1       0 [10]

                 4864    DE100           2       0       0       0       0       0

                 5120    ATMCDS3         0       0       0       0       1       0 [10]
                 5121    ATMCE3          0       0       0       0       1       0 [10]

                 8448    SRML            0       0       0       0       0       0


                 NOTES:
                   [1] Indicates Module has COM Port 1 configured for ASYNC.
                       The AM8530's port B is configured for COM1.

                   [2] This Module contains the DEFA - Hardware Filtering.  CAMS
                       must be programmed (can contain 2 - 6 CAMS onboard).

                   [3] The AM8530 has been removed (depopulated) from this module.
                       Programming this device should not be performed.

                   [4] Contains Dual Defa hardware. (Can be depopulated)

                   [5] Depop'd two ports of hardware to make Dual Ethernet module.

                   [6] These are FDDI modules.  The ID cannot be read from the Link
                       module I/O space.

                   [7] These are AFN Platform Integrated 'Modules' - Cannot be detached
                       or be used by any other platform.

                   [8] Module IDs from 1280(0x500) to 2559(0x9ff) are used
                       for the ASN Net Modules. Module ID 512(0x200) is
                       used for the ASN SPEX. These IDs are documented in
                       module.mib. A module ID of 511(0x1ff) in
                       'wfHwEntry.wfHwModIdOpt' indicates that it is an
                       ASN platform and the user should refer to
                       'wfHwModuleEntry.wfHwModuleModIdOpt' for Module ID details.

                   [9] ATMALC link modules. The physical option for SONET includes a
                       framer and the medium is fiber optics. Only one port per physical
                       daughtercard per link module.

                  [10] ARE UTOPIA link modules. 
    
                  [11] Module IDs from 8704(0x2200) to 16383(0x3FFF) are used
                       for the ARN Net Modules. These IDs are documented in
                       module.mib. A module ID of 767(0x2ff) in
                       'wfHwEntry.wfHwModIdOpt' indicates that it is a
                       Neptune platform and the user should refer to
                       'wfHwModuleEntry.wfHwModuleModIdOpt' for Module ID details.

                  [12] Module IDs from 16384(0x4000) to 18944(0x4A00) are used
                       for the SN Switched Net Modules (SNM). These IDs are documented
                       in module.mib. A module ID of 513(0x201) in
                       'wfHwEntry.wfHwModIdOpt' indicates that it is an
                       SN (Fiddlestix) platform and the user should refer to
                       'wfHwModuleEntry.wfHwModuleModIdOpt' for Module ID details.

                  [13] A module ID of 777(0x309) in 'wfHwEntry.wfHwModIdOpt' indicates 
                       that it is a FBR (Fast Branch Router) platform and the user should 
                       refer to 'wfHwModuleEntry.wfHwModuleModIdOpt' for Module ID details.

                  [14] A module ID of 778(0x30A) in 'wfHwEntry.wfHwModIdOpt' indicates
                       the presence of a PCI PMC carrier card.  The carrier card can have
                       2 PMC cards attached to it.  For PMC card module IDs, refer to
                       'wfHwModuleEntry.wfHwModuleModIdOpt' for details."
    
   	 ::= { wfHwEntry 2 }

    wfHwModRev OBJECT-TYPE
        SYNTAX	OCTET STRING
        ACCESS	read-only
        STATUS	mandatory
        DESCRIPTION
                "The revision level of the module. High byte is in upper 2 bytes."
        ::= { wfHwEntry 3 }

    wfHwModSerialNumber OBJECT-TYPE
        SYNTAX	OCTET STRING
        ACCESS	read-only
        STATUS	mandatory
        DESCRIPTION
                "The serial number of the module."
        ::= { wfHwEntry 4 }

    wfHwMotherBdIdOpt OBJECT-TYPE
        SYNTAX	INTEGER {
    		    sysctrl(1),
    		    ace12(2),
    		    ace25(3),
    		    ace32(4),
    		    afn(5),
    		    in(6),
    		    sysctrl2(7),
    		    an(16),
		    arn(32),
                    lite(36),
                    fbr(64),
    		    fre(256),
    		    fre2(768),
    		    o60(769),
    		    asn(1024),
    		    asn2(1025),
    		    are(1280),
    		    srmf(8704),
                    are5000(1536),
                    asn5000(1792),
                    sn060(2561),
		    fre2060epci(5632),
		    fre2060e(5633),
                    ssp(25088),
                    ifp(25344),
                    atp(25600),
                    cap(25856),
                    fre4(6656)
    		}
        ACCESS	read-only
        STATUS	mandatory
        DESCRIPTION
                "The mother board identification number."
        ::= { wfHwEntry 5 }

    wfHwMotherBdRev OBJECT-TYPE
        SYNTAX	OCTET STRING
        ACCESS	read-only
        STATUS	mandatory
        DESCRIPTION
                "The revision level of the mother board. High byte is in upper 2 bytes."
        ::= { wfHwEntry 6 }

    wfHwMotherBdSerialNumber OBJECT-TYPE
        SYNTAX	OCTET STRING
        ACCESS	read-only
        STATUS	mandatory
        DESCRIPTION
                "The serial number of the mother board."
        ::= { wfHwEntry 7 }

    wfHwDaughterBdIdOpt OBJECT-TYPE
        SYNTAX	INTEGER {
    		    sysctrl(1),
    		    ace68020mhz12(2),
    		    ace68020mhz25(3),
    		    ace68030mhz32(4),
    		    fre68040mhz25(4352),
    		    fre68040mhz33(4608),
                    arnv34(8752),
		    hwcomp128pci(5888),
		    hwcomp128(5889),
		    hwcomp256pci(5890),
		    hwcomp256(5891),
                    ifprspdtr(25345),
                    cap3m13dtr(25857)
    		}
        ACCESS	read-only
        STATUS	mandatory
        DESCRIPTION
                "The daughter board identification number."
        ::= { wfHwEntry 8 }

    wfHwDaughterBdRev OBJECT-TYPE
        SYNTAX	OCTET STRING
        ACCESS	read-only
        STATUS	mandatory
        DESCRIPTION
                "The revision level of the daughter board. High byte is in upper 2 bytes."
        ::= { wfHwEntry 9 }

    wfHwDaughterBdSerialNumber OBJECT-TYPE
        SYNTAX	OCTET STRING
        ACCESS	read-only
        STATUS	mandatory
        DESCRIPTION
                "The serial number of the daughter board."
        ::= { wfHwEntry 10 }

    wfHwBabyBdIdOpt OBJECT-TYPE
        SYNTAX	INTEGER
        ACCESS	read-only
        STATUS	mandatory
        DESCRIPTION
                "The baby board identification number."
        ::= { wfHwEntry 11 }

    wfHwBabyBdRev OBJECT-TYPE
        SYNTAX	OCTET STRING
        ACCESS	read-only
        STATUS	mandatory
        DESCRIPTION
                "The revision level of the baby board. High byte is in upper 2 bytes."
        ::= { wfHwEntry 12 }

    wfHwBabyBdSerialNumber OBJECT-TYPE
        SYNTAX	OCTET STRING
        ACCESS	read-only
        STATUS	mandatory
        DESCRIPTION
                "The serial number of the baby board."
        ::= { wfHwEntry 13 }

    wfHwDiagPromRev OBJECT-TYPE
        SYNTAX	OCTET STRING
        ACCESS	read-only
        STATUS	mandatory
        DESCRIPTION
                "The revision level of the Diagnostic PROM. Major revision level
                is in the upper 2 bytes, minor revision level in the lower 2 bytes."
        ::= { wfHwEntry 14 }

    wfHwDiagPromDate OBJECT-TYPE
        SYNTAX	DisplayString
        ACCESS	read-only
        STATUS	mandatory
        DESCRIPTION
                "The creation date of the Diagnostic PROM"
        ::= { wfHwEntry 15 }

    wfHwDiagPromSource OBJECT-TYPE
        SYNTAX	DisplayString
        ACCESS	read-only
        STATUS	mandatory
        DESCRIPTION
                "The origin of the Diagnostic PROM contents"
        ::= { wfHwEntry 16 }

    wfHwBootPromRev OBJECT-TYPE
        SYNTAX	OCTET STRING
        ACCESS	read-only
        STATUS	mandatory
        DESCRIPTION
                "The revision level of the BOOT PROM. Major revision level
                is in the upper 2 bytes, minor revision level in the lower 2 bytes."
        ::= { wfHwEntry 17 }

    wfHwBootPromDate OBJECT-TYPE
        SYNTAX	DisplayString
        ACCESS	read-only
        STATUS	mandatory
        DESCRIPTION
                "The creation date of the Boot PROM"
        ::= { wfHwEntry 18 }

    wfHwBootPromSource OBJECT-TYPE
        SYNTAX	DisplayString
        ACCESS	read-only
        STATUS	mandatory
        DESCRIPTION
                "The origin of the Boot PROM contents"
        ::= { wfHwEntry 19 }

    wfHwSparePromRev OBJECT-TYPE
        SYNTAX	OCTET STRING
        ACCESS	read-only
        STATUS	mandatory
        DESCRIPTION
                "The revision level of the BOOT PROM. Major revision level
                is in the upper 2 bytes, minor revision level in the lower 2 bytes."
        ::= { wfHwEntry 20 }

    wfHwSparePromDate OBJECT-TYPE
        SYNTAX	DisplayString
        ACCESS	read-only
        STATUS	mandatory
        DESCRIPTION
                "The creation date of the Spare PROM"
        ::= { wfHwEntry 21 }

    wfHwSparePromSource OBJECT-TYPE
        SYNTAX	DisplayString
        ACCESS	read-only
        STATUS	mandatory
        DESCRIPTION
                "The origin of the Spare PROM contents"
        ::= { wfHwEntry 22 }

    wfHwFileSysPresent OBJECT-TYPE
        SYNTAX	INTEGER {
    		    filesys(1),
    		    nofilesys(2)
    		}
        ACCESS	read-only
        STATUS	mandatory
        DESCRIPTION
                "Flag indicating presence of File System on this slot."
        DEFVAL	{ nofilesys }
        ::= { wfHwEntry 23 }

    wfHwFileSysPresent2 OBJECT-TYPE
        SYNTAX	INTEGER {
    		    filesys(1),
    		    nofilesys(2)
    		}
        ACCESS	read-only
        STATUS	mandatory
        DESCRIPTION
                "Flag indicating presence of File System (Syscon2 volume#2) on this slot."
        DEFVAL	{ nofilesys }
        ::= { wfHwEntry 24 }

    wfHwConfigServer OBJECT-TYPE
        SYNTAX	INTEGER
        ACCESS	read-only
        STATUS	mandatory
        DESCRIPTION
                "The slot number from which this slot was served its
                configuration.  If the value for this attribute is 0, this
                slot obtained its configuration from a file system resource
                (not necessarily local); If the value for this attribute is
                -1, this slot does not participate in the boot process (e.g.
                SRM). A positive value indicates that the configuration was
                obtained from memory from the slot indicated by the value of
                this attribute."
        ::= { wfHwEntry 25 }

    wfHwConfigFile OBJECT-TYPE
        SYNTAX	DisplayString
        ACCESS	read-only
        STATUS	mandatory
        DESCRIPTION
                "The name of the config file the active configuration was
                derived from.  This does NOT necessarily reflect the
                current configuration!"
        ::= { wfHwEntry 26 }

    wfHwConfigDateAndTime OBJECT-TYPE
        SYNTAX	OCTET STRING
        ACCESS	read-only
        STATUS	mandatory
        DESCRIPTION
                "The 11 octet date and time that a configuration was
                loaded on/served to this slot. Octet map: 1-2 Year,
                3 Month, 4 Day, 5 Hour, 6 Minutes, 7 Seconds,
                8 Deci-seconds, 9 Direction from GMT ('+'|`-'), 10 GMT Hour
                Offset, 11 GMT Minute Offset."
        ::= { wfHwEntry 27 }

    wfHwActiveImageName OBJECT-TYPE
        SYNTAX	DisplayString
        ACCESS	read-only
        STATUS	mandatory
        DESCRIPTION
                "If slot was booted from a local source: this is the name of the active
                image, which is in the form of <volume>:<image name>.
                If slot was booted from a network source: this is the full pathname
                where the active image was found on the remote server."
        ::= { wfHwEntry 28 }

    wfHwActiveImageSource OBJECT-TYPE
        SYNTAX	DisplayString
        ACCESS	read-only
        STATUS	mandatory
        DESCRIPTION
                "The origin of the active image"
        ::= { wfHwEntry 29 }

    wfHwActiveImageDate OBJECT-TYPE
        SYNTAX	DisplayString
        ACCESS	read-only
        STATUS	mandatory
        DESCRIPTION
                "The date which the active image was created"
        ::= { wfHwEntry 30 }

    wfHwMotherBdMemorySize OBJECT-TYPE
        SYNTAX	INTEGER
        ACCESS	read-only
        STATUS	mandatory
        DESCRIPTION
                "The total installed dram size in kilobytes."
        ::= { wfHwEntry 31 }

    wfHwFastPacketCacheSize OBJECT-TYPE
        SYNTAX	INTEGER
        ACCESS	read-only
        STATUS	mandatory
        DESCRIPTION
                "The size of the installed fast packet cache in kilobytes."
        ::= { wfHwEntry 32 }

    wfHwModDaughterBd1IdOpt OBJECT-TYPE
        SYNTAX	INTEGER
        ACCESS	read-only
        STATUS	mandatory
        DESCRIPTION
                "Link module daughter board #1 identification number"
        ::= { wfHwEntry 33 }

    wfHwModDaughterBd1AwRev OBJECT-TYPE
        SYNTAX	OCTET STRING
        ACCESS	read-only
        STATUS	mandatory
        DESCRIPTION
                "Link module daughter board #1 artwork revision level"
        ::= { wfHwEntry 34 }

    wfHwModDaughterBd1Rev OBJECT-TYPE
        SYNTAX	OCTET STRING
        ACCESS	read-only
        STATUS	mandatory
        DESCRIPTION
                "Link module daughter board #1 board revision level"
        ::= { wfHwEntry 35 }

    wfHwModDaughterBd1SerialNumber OBJECT-TYPE
        SYNTAX	OCTET STRING
        ACCESS	read-only
        STATUS	mandatory
        DESCRIPTION
                "Link module daughter board #1 serial number"
        ::= { wfHwEntry 36 }

    wfHwModDaughterBd2IdOpt OBJECT-TYPE
        SYNTAX	INTEGER
        ACCESS	read-only
        STATUS	mandatory
        DESCRIPTION
                "Link module daughter board #2 identification number"
        ::= { wfHwEntry 37 }

    wfHwModDaughterBd2AwRev OBJECT-TYPE
        SYNTAX	OCTET STRING
        ACCESS	read-only
        STATUS	mandatory
        DESCRIPTION
                "Link module daughter board #2 artwork revision level"
        ::= { wfHwEntry 38 }

    wfHwModDaughterBd2Rev OBJECT-TYPE
        SYNTAX	OCTET STRING
        ACCESS	read-only
        STATUS	mandatory
        DESCRIPTION
                "Link module daughter board #2 board revision level"
        ::= { wfHwEntry 39 }

    wfHwModDaughterBd2SerialNumber OBJECT-TYPE
        SYNTAX	OCTET STRING
        ACCESS	read-only
        STATUS	mandatory
        DESCRIPTION
                "Link module daughter board #2 serial number"
        ::= { wfHwEntry 40 }

    wfRASNPwrSupply1 OBJECT-TYPE
        SYNTAX  INTEGER {
                    ok(1),
                    fail(2),
                    notpresent(3),
                    notapplicable(4)
                }
        ACCESS  read-only
        STATUS  mandatory
        DESCRIPTION
                "Status of RASN Internal Power Supply PS1"
        DEFVAL  { notapplicable }
        ::= { wfHwEntry 41 }

    wfRASNPwrSupply2 OBJECT-TYPE
        SYNTAX  INTEGER {
                    ok(1),
                    fail(2),
                    notpresent(3),
                    notapplicable(4)
                }
        ACCESS  read-only
        STATUS  mandatory
        DESCRIPTION
                "Status of RASN External Power Supply PS2"
        DEFVAL  { notapplicable }
        ::= { wfHwEntry 42 }

    wfPowerSupply1 OBJECT-TYPE
        SYNTAX  INTEGER {
                    ok(1),
                    fail(2),
                    notpresent(3),
                    notapplicable(4)
                }
        ACCESS  read-only
        STATUS  mandatory
        DESCRIPTION
                "Status of Power Supply 1.  The meaning of this object
                 is platform dependent.  It is normally used to report
                 the status of the internal power supply.  Not all
                 platforms support this object."
        DEFVAL  { notapplicable }
        ::= { wfHwEntry 43 }

    wfPowerSupply2 OBJECT-TYPE
        SYNTAX  INTEGER {
                    ok(1),
                    fail(2),
                    notpresent(3),
                    notapplicable(4)
                }
        ACCESS  read-only
        STATUS  mandatory
        DESCRIPTION
                "Status of Power Supply 1.  The meaning of this object
                 is platform dependent.  It is normally used to report
                 the status of the external power supply.  Not all
                 platforms support this object."
        DEFVAL  { notapplicable }
        ::= { wfHwEntry 44 }

    wfFanStatus1 OBJECT-TYPE
        SYNTAX  INTEGER {
                    ok(1),
                    fail(2),
                    notpresent(3),
                    notapplicable(4)
                }
        ACCESS  read-only
        STATUS  mandatory
        DESCRIPTION
                "Status of Fan 1.  The meaning of this object is platform
                 dependent.  Not all platforms support this object."
        DEFVAL  { notapplicable }
        ::= { wfHwEntry 45 }

    wfFanStatus2 OBJECT-TYPE
        SYNTAX  INTEGER {
                    ok(1),
                    fail(2),
                    notpresent(3),
                    notapplicable(4)
                }
        ACCESS  read-only
        STATUS  mandatory
        DESCRIPTION
                "Status of Fan 2.  The meaning of this object is platform
                 dependent.  Not all platforms support this object."
        DEFVAL  { notapplicable }
        ::= { wfHwEntry 46 }

    wfRASNRPSUPresent OBJECT-TYPE
        SYNTAX  INTEGER {
                    present(1),
                    notpresent(2),
		    notapplicable(3)
                }
        ACCESS  read-write
        STATUS  obsolete 
        DESCRIPTION
                "Status of RASN External Power Supply PS2 Presence"
        DEFVAL  { notapplicable }
        ::= { wfHwEntry 47 }

    wfModDiagStatus OBJECT-TYPE
        SYNTAX  INTEGER {
                    passed(1),
                    failed(2),
                    notrun(3),
                    notpresent(4),
                    notapplicable(20)
                }
        ACCESS  read-only
        STATUS  mandatory
        DESCRIPTION
                 "For TIB, BF and BAR builds only.  Module Diag. status 
                determines if diags have been run on a netmodule, and 
                if they passed or failed."
        DEFVAL  { notapplicable }
        ::= { wfHwEntry 48 }

    wfHwCfgTable OBJECT-TYPE
        SYNTAX  SEQUENCE OF WfHwCfgEntry
        ACCESS  not-accessible
        STATUS  mandatory
        DESCRIPTION
                "Hardware Config Table  - indexed by slot number"
        ::= { wfHardwareConfig 7 }

    wfHwCfgEntry OBJECT-TYPE
        SYNTAX  WfHwCfgEntry
        ACCESS not-accessible
        STATUS  mandatory
        DESCRIPTION
                "Hardware specific information about a slot."
        INDEX   { wfHwCfgSlot }
        ::= { wfHwCfgTable 1 }

    WfHwCfgEntry ::= SEQUENCE {
            wfHwCfgSlot
                INTEGER,
            wfRPSUPresent
                INTEGER
    }

    wfHwCfgSlot OBJECT-TYPE
        SYNTAX  INTEGER
        ACCESS  read-only
        STATUS  mandatory
        DESCRIPTION
                "A unique value for each slot."
        ::= { wfHwCfgEntry 1 }

    wfRPSUPresent OBJECT-TYPE
        SYNTAX  INTEGER {
                    present(1),
                    notpresent(2),
                    notapplicable(3)
                }
        ACCESS  read-write
        STATUS  mandatory
        DESCRIPTION
                "Status of External Power Supply PS2 Presence"
        DEFVAL  { notapplicable }
        ::= { wfHwCfgEntry 2 }

    END  -- Wellfleet-HARDWARE-MIB
