PACKETLOGIC-MIB DEFINITIONS ::= BEGIN

IMPORTS
	NOTIFICATION-TYPE,
	MODULE-IDENTITY, OBJECT-TYPE, Integer32, Counter64,
	Unsigned32, TimeTicks, enterprises FROM SNMPv2-SMI
	DisplayString FROM SNMPv2-TC;

procera MODULE-IDENTITY
	LAST-UPDATED "201110211250Z"
	ORGANIZATION "Procera Networks, Inc."
	CONTACT-INFO "support@proceranetworks.com"
	DESCRIPTION "MIB for PacketLogic2"
	REVISION "201110211250Z"
	DESCRIPTION " Latest version at the revision date for version GET VERSION HERE"

	::={enterprises 15397}
packetlogic2	OBJECT IDENTIFIER ::={procera 2}

psm	OBJECT IDENTIFIER ::={procera 3}

sysdiag	OBJECT IDENTIFIER ::={packetlogic2 1}

channelstats	OBJECT IDENTIFIER ::={packetlogic2 2}

pl2Trap	OBJECT IDENTIFIER ::={packetlogic2 8}

snoopers	OBJECT IDENTIFIER ::={packetlogic2 10}

dynamiczones	OBJECT IDENTIFIER ::={packetlogic2 20}

packetprocessing	OBJECT IDENTIFIER ::={sysdiag 8}

packetprocessingRx	OBJECT IDENTIFIER ::={packetprocessing 1}

packetprocessingRxVal	OBJECT-TYPE
	SYNTAX	 Counter64
	MAX-ACCESS read-only
	STATUS current
	DESCRIPTION "RX packets"

	::={packetprocessingRx 1}

packetprocessingRxMom	OBJECT-TYPE
	SYNTAX	 Unsigned32
	MAX-ACCESS read-only
	STATUS current
	DESCRIPTION "RX packets"

	::={packetprocessingRx 2}

packetprocessingRxMax	OBJECT-TYPE
	SYNTAX	 Counter64
	MAX-ACCESS read-only
	STATUS current
	DESCRIPTION "RX packets"

	::={packetprocessingRx 3}

packetprocessingRxDrops	OBJECT IDENTIFIER ::={packetprocessing 2}

packetprocessingRxDropsVal	OBJECT-TYPE
	SYNTAX	 Counter64
	MAX-ACCESS read-only
	STATUS current
	DESCRIPTION "RX drops"

	::={packetprocessingRxDrops 1}

packetprocessingRxDropsMom	OBJECT-TYPE
	SYNTAX	 Unsigned32
	MAX-ACCESS read-only
	STATUS current
	DESCRIPTION "RX drops"

	::={packetprocessingRxDrops 2}

packetprocessingRxDropsMax	OBJECT-TYPE
	SYNTAX	 Counter64
	MAX-ACCESS read-only
	STATUS current
	DESCRIPTION "RX drops"

	::={packetprocessingRxDrops 3}

packetprocessingTx	OBJECT IDENTIFIER ::={packetprocessing 6}

packetprocessingTxVal	OBJECT-TYPE
	SYNTAX	 Counter64
	MAX-ACCESS read-only
	STATUS current
	DESCRIPTION "TX packets"

	::={packetprocessingTx 1}

packetprocessingTxMom	OBJECT-TYPE
	SYNTAX	 Unsigned32
	MAX-ACCESS read-only
	STATUS current
	DESCRIPTION "TX packets"

	::={packetprocessingTx 2}

packetprocessingTxMax	OBJECT-TYPE
	SYNTAX	 Counter64
	MAX-ACCESS read-only
	STATUS current
	DESCRIPTION "TX packets"

	::={packetprocessingTx 3}

packetprocessingTxDrops	OBJECT IDENTIFIER ::={packetprocessing 7}

packetprocessingTxDropsVal	OBJECT-TYPE
	SYNTAX	 Counter64
	MAX-ACCESS read-only
	STATUS current
	DESCRIPTION "TX drops"

	::={packetprocessingTxDrops 1}

packetprocessingTxDropsMom	OBJECT-TYPE
	SYNTAX	 Unsigned32
	MAX-ACCESS read-only
	STATUS current
	DESCRIPTION "TX drops"

	::={packetprocessingTxDrops 2}

packetprocessingTxDropsMax	OBJECT-TYPE
	SYNTAX	 Counter64
	MAX-ACCESS read-only
	STATUS current
	DESCRIPTION "TX drops"

	::={packetprocessingTxDrops 3}

packetprocessingRuntime	OBJECT IDENTIFIER ::={packetprocessing 8}

packetprocessingRuntimeVal	OBJECT-TYPE
	SYNTAX	 Unsigned32
	MAX-ACCESS read-only
	STATUS current
	DESCRIPTION "Average cycles per packet"

	::={packetprocessingRuntime 1}

packetprocessingRuntimeMax	OBJECT-TYPE
	SYNTAX	 Unsigned32
	MAX-ACCESS read-only
	STATUS current
	DESCRIPTION "Average cycles per packet"

	::={packetprocessingRuntime 3}

packetprocessingRecvtime	OBJECT IDENTIFIER ::={packetprocessing 9}

packetprocessingRecvtimeVal	OBJECT-TYPE
	SYNTAX	 Unsigned32
	MAX-ACCESS read-only
	STATUS current
	DESCRIPTION "Average cycles since rx-irq"

	::={packetprocessingRecvtime 1}

packetprocessingRecvtimeMax	OBJECT-TYPE
	SYNTAX	 Unsigned32
	MAX-ACCESS read-only
	STATUS current
	DESCRIPTION "Average cycles since rx-irq"

	::={packetprocessingRecvtime 3}

packetprocessingPacketPoolSize	OBJECT IDENTIFIER ::={packetprocessing 10}

packetprocessingPacketPoolSizeVal	OBJECT-TYPE
	SYNTAX	 Unsigned32
	MAX-ACCESS read-only
	STATUS current
	DESCRIPTION "Packets left in pool"

	::={packetprocessingPacketPoolSize 1}

packetprocessingPacketPoolSizeMax	OBJECT-TYPE
	SYNTAX	 Unsigned32
	MAX-ACCESS read-only
	STATUS current
	DESCRIPTION "Packets left in pool"

	::={packetprocessingPacketPoolSize 3}

packetprocessingRxQueueUsed	OBJECT IDENTIFIER ::={packetprocessing 11}

packetprocessingRxQueueUsedVal	OBJECT-TYPE
	SYNTAX	 Unsigned32
	MAX-ACCESS read-only
	STATUS current
	DESCRIPTION "Packets in RX queue"

	::={packetprocessingRxQueueUsed 1}

packetprocessingRxQueueUsedMax	OBJECT-TYPE
	SYNTAX	 Unsigned32
	MAX-ACCESS read-only
	STATUS current
	DESCRIPTION "Packets in RX queue"

	::={packetprocessingRxQueueUsed 3}

packetprocessingTxQueueUsed	OBJECT IDENTIFIER ::={packetprocessing 12}

packetprocessingTxQueueUsedVal	OBJECT-TYPE
	SYNTAX	 Unsigned32
	MAX-ACCESS read-only
	STATUS current
	DESCRIPTION "Packets in TX queue"

	::={packetprocessingTxQueueUsed 1}

packetprocessingTxQueueUsedMax	OBJECT-TYPE
	SYNTAX	 Unsigned32
	MAX-ACCESS read-only
	STATUS current
	DESCRIPTION "Packets in TX queue"

	::={packetprocessingTxQueueUsed 3}

packetprocessingDmaAllocs	OBJECT IDENTIFIER ::={packetprocessing 13}

packetprocessingDmaAllocsVal	OBJECT-TYPE
	SYNTAX	 Unsigned32
	MAX-ACCESS read-only
	STATUS current
	DESCRIPTION "DMA-allocated packets"

	::={packetprocessingDmaAllocs 1}

packetprocessingDmaAllocsMax	OBJECT-TYPE
	SYNTAX	 Unsigned32
	MAX-ACCESS read-only
	STATUS current
	DESCRIPTION "DMA-allocated packets"

	::={packetprocessingDmaAllocs 3}

packetprocessingHeavy	OBJECT IDENTIFIER ::={packetprocessing 14}

packetprocessingHeavyVal	OBJECT-TYPE
	SYNTAX	 Counter64
	MAX-ACCESS read-only
	STATUS current
	DESCRIPTION "Heavy cycle packets"

	::={packetprocessingHeavy 1}

packetprocessingHeavyMom	OBJECT-TYPE
	SYNTAX	 Unsigned32
	MAX-ACCESS read-only
	STATUS current
	DESCRIPTION "Heavy cycle packets"

	::={packetprocessingHeavy 2}

packetprocessingHeavyMax	OBJECT-TYPE
	SYNTAX	 Counter64
	MAX-ACCESS read-only
	STATUS current
	DESCRIPTION "Heavy cycle packets"

	::={packetprocessingHeavy 3}

packetprocessingLoad	OBJECT IDENTIFIER ::={packetprocessing 15}

packetprocessingLoadVal	OBJECT-TYPE
	SYNTAX	 Unsigned32
	MAX-ACCESS read-only
	STATUS current
	DESCRIPTION "CPU Load"

	::={packetprocessingLoad 1}

packetprocessingLoadMax	OBJECT-TYPE
	SYNTAX	 Unsigned32
	MAX-ACCESS read-only
	STATUS current
	DESCRIPTION "CPU Load"

	::={packetprocessingLoad 3}

packetprocessingUptime	OBJECT IDENTIFIER ::={packetprocessing 17}

packetprocessingUptimeVal	OBJECT-TYPE
	SYNTAX	 TimeTicks
	MAX-ACCESS read-only
	STATUS current
	DESCRIPTION "CPU uptime"

	::={packetprocessingUptime 1}

packetprocessingHeapfree	OBJECT IDENTIFIER ::={packetprocessing 16}

packetprocessingHeapfreeVal	OBJECT-TYPE
	SYNTAX	 Unsigned32
	MAX-ACCESS read-only
	STATUS current
	DESCRIPTION "Free memory (Kbytes)"

	::={packetprocessingHeapfree 1}

packetprocessingHeapfreeMax	OBJECT-TYPE
	SYNTAX	 Unsigned32
	MAX-ACCESS read-only
	STATUS current
	DESCRIPTION "Free memory (Kbytes)"

	::={packetprocessingHeapfree 3}

packetprocessingPushbackQueueFull	OBJECT IDENTIFIER ::={packetprocessing 18}

packetprocessingPushbackQueueFullVal	OBJECT-TYPE
	SYNTAX	 Counter64
	MAX-ACCESS read-only
	STATUS current
	DESCRIPTION "Push back queue full"

	::={packetprocessingPushbackQueueFull 1}

packetprocessingPushbackQueueFullMom	OBJECT-TYPE
	SYNTAX	 Unsigned32
	MAX-ACCESS read-only
	STATUS current
	DESCRIPTION "Push back queue full"

	::={packetprocessingPushbackQueueFull 2}

packetprocessingPushbackQueueFullMax	OBJECT-TYPE
	SYNTAX	 Counter64
	MAX-ACCESS read-only
	STATUS current
	DESCRIPTION "Push back queue full"

	::={packetprocessingPushbackQueueFull 3}

packetprocessingPushbackPackets	OBJECT IDENTIFIER ::={packetprocessing 19}

packetprocessingPushbackPacketsVal	OBJECT-TYPE
	SYNTAX	 Counter64
	MAX-ACCESS read-only
	STATUS current
	DESCRIPTION "Push back packets"

	::={packetprocessingPushbackPackets 1}

packetprocessingPushbackPacketsMom	OBJECT-TYPE
	SYNTAX	 Unsigned32
	MAX-ACCESS read-only
	STATUS current
	DESCRIPTION "Push back packets"

	::={packetprocessingPushbackPackets 2}

packetprocessingPushbackPacketsMax	OBJECT-TYPE
	SYNTAX	 Counter64
	MAX-ACCESS read-only
	STATUS current
	DESCRIPTION "Push back packets"

	::={packetprocessingPushbackPackets 3}

packetprocessingPushbackQueueSize	OBJECT IDENTIFIER ::={packetprocessing 20}

packetprocessingPushbackQueueSizeVal	OBJECT-TYPE
	SYNTAX	 Unsigned32
	MAX-ACCESS read-only
	STATUS current
	DESCRIPTION "Push back queue size"

	::={packetprocessingPushbackQueueSize 1}

packetprocessingPushbackQueueSizeMax	OBJECT-TYPE
	SYNTAX	 Unsigned32
	MAX-ACCESS read-only
	STATUS current
	DESCRIPTION "Push back queue size"

	::={packetprocessingPushbackQueueSize 3}

packetprocessingPushbackRequeues	OBJECT IDENTIFIER ::={packetprocessing 21}

packetprocessingPushbackRequeuesVal	OBJECT-TYPE
	SYNTAX	 Unsigned32
	MAX-ACCESS read-only
	STATUS current
	DESCRIPTION "Push back requeues"

	::={packetprocessingPushbackRequeues 1}

packetprocessingPushbackRequeuesMax	OBJECT-TYPE
	SYNTAX	 Unsigned32
	MAX-ACCESS read-only
	STATUS current
	DESCRIPTION "Push back requeues"

	::={packetprocessingPushbackRequeues 3}

drdl	OBJECT IDENTIFIER ::={sysdiag 24}

drdlWaitingChildren	OBJECT IDENTIFIER ::={drdl 1}

drdlWaitingChildrenVal	OBJECT-TYPE
	SYNTAX	 Unsigned32
	MAX-ACCESS read-only
	STATUS current
	DESCRIPTION "Waiting childconnections"

	::={drdlWaitingChildren 1}

drdlWaitingChildrenMax	OBJECT-TYPE
	SYNTAX	 Unsigned32
	MAX-ACCESS read-only
	STATUS current
	DESCRIPTION "Waiting childconnections"

	::={drdlWaitingChildren 3}

drdlAddedChildren	OBJECT IDENTIFIER ::={drdl 2}

drdlAddedChildrenVal	OBJECT-TYPE
	SYNTAX	 Counter64
	MAX-ACCESS read-only
	STATUS current
	DESCRIPTION "New childconnections"

	::={drdlAddedChildren 1}

drdlAddedChildrenMom	OBJECT-TYPE
	SYNTAX	 Unsigned32
	MAX-ACCESS read-only
	STATUS current
	DESCRIPTION "New childconnections"

	::={drdlAddedChildren 2}

drdlAddedChildrenMax	OBJECT-TYPE
	SYNTAX	 Counter64
	MAX-ACCESS read-only
	STATUS current
	DESCRIPTION "New childconnections"

	::={drdlAddedChildren 3}

drdlChildAbuses	OBJECT IDENTIFIER ::={drdl 3}

drdlChildAbusesVal	OBJECT-TYPE
	SYNTAX	 Counter64
	MAX-ACCESS read-only
	STATUS current
	DESCRIPTION "LRU child allocations"

	::={drdlChildAbuses 1}

drdlChildAbusesMom	OBJECT-TYPE
	SYNTAX	 Unsigned32
	MAX-ACCESS read-only
	STATUS current
	DESCRIPTION "LRU child allocations"

	::={drdlChildAbuses 2}

drdlChildAbusesMax	OBJECT-TYPE
	SYNTAX	 Counter64
	MAX-ACCESS read-only
	STATUS current
	DESCRIPTION "LRU child allocations"

	::={drdlChildAbuses 3}

drdlChildEmpty	OBJECT IDENTIFIER ::={drdl 4}

drdlChildEmptyVal	OBJECT-TYPE
	SYNTAX	 Counter64
	MAX-ACCESS read-only
	STATUS current
	DESCRIPTION "Child allocation failures"

	::={drdlChildEmpty 1}

drdlChildEmptyMom	OBJECT-TYPE
	SYNTAX	 Unsigned32
	MAX-ACCESS read-only
	STATUS current
	DESCRIPTION "Child allocation failures"

	::={drdlChildEmpty 2}

drdlChildEmptyMax	OBJECT-TYPE
	SYNTAX	 Counter64
	MAX-ACCESS read-only
	STATUS current
	DESCRIPTION "Child allocation failures"

	::={drdlChildEmpty 3}

drdlProp32Fail	OBJECT IDENTIFIER ::={drdl 5}

drdlProp32FailVal	OBJECT-TYPE
	SYNTAX	 Counter64
	MAX-ACCESS read-only
	STATUS current
	DESCRIPTION "Property allocation failures (32)"

	::={drdlProp32Fail 1}

drdlProp32FailMom	OBJECT-TYPE
	SYNTAX	 Unsigned32
	MAX-ACCESS read-only
	STATUS current
	DESCRIPTION "Property allocation failures (32)"

	::={drdlProp32Fail 2}

drdlProp32FailMax	OBJECT-TYPE
	SYNTAX	 Counter64
	MAX-ACCESS read-only
	STATUS current
	DESCRIPTION "Property allocation failures (32)"

	::={drdlProp32Fail 3}

drdlProp64Fail	OBJECT IDENTIFIER ::={drdl 6}

drdlProp64FailVal	OBJECT-TYPE
	SYNTAX	 Counter64
	MAX-ACCESS read-only
	STATUS obsolete
	DESCRIPTION "Unused"

	::={drdlProp64Fail 1}

drdlProp64FailMom	OBJECT-TYPE
	SYNTAX	 Unsigned32
	MAX-ACCESS read-only
	STATUS obsolete
	DESCRIPTION "Unused"

	::={drdlProp64Fail 2}

drdlProp64FailMax	OBJECT-TYPE
	SYNTAX	 Counter64
	MAX-ACCESS read-only
	STATUS obsolete
	DESCRIPTION "Unused"

	::={drdlProp64Fail 3}

drdlProp256Fail	OBJECT IDENTIFIER ::={drdl 7}

drdlProp256FailVal	OBJECT-TYPE
	SYNTAX	 Counter64
	MAX-ACCESS read-only
	STATUS current
	DESCRIPTION "Property allocation failures (256)"

	::={drdlProp256Fail 1}

drdlProp256FailMom	OBJECT-TYPE
	SYNTAX	 Unsigned32
	MAX-ACCESS read-only
	STATUS current
	DESCRIPTION "Property allocation failures (256)"

	::={drdlProp256Fail 2}

drdlProp256FailMax	OBJECT-TYPE
	SYNTAX	 Counter64
	MAX-ACCESS read-only
	STATUS current
	DESCRIPTION "Property allocation failures (256)"

	::={drdlProp256Fail 3}

drdlProp32Used	OBJECT IDENTIFIER ::={drdl 8}

drdlProp32UsedVal	OBJECT-TYPE
	SYNTAX	 Unsigned32
	MAX-ACCESS read-only
	STATUS current
	DESCRIPTION "Properties used (32)"

	::={drdlProp32Used 1}

drdlProp32UsedMax	OBJECT-TYPE
	SYNTAX	 Unsigned32
	MAX-ACCESS read-only
	STATUS current
	DESCRIPTION "Properties used (32)"

	::={drdlProp32Used 3}

drdlProp64Used	OBJECT IDENTIFIER ::={drdl 9}

drdlProp64UsedVal	OBJECT-TYPE
	SYNTAX	 Counter64
	MAX-ACCESS read-only
	STATUS obsolete
	DESCRIPTION "Unused"

	::={drdlProp64Used 1}

drdlProp64UsedMom	OBJECT-TYPE
	SYNTAX	 Unsigned32
	MAX-ACCESS read-only
	STATUS obsolete
	DESCRIPTION "Unused"

	::={drdlProp64Used 2}

drdlProp64UsedMax	OBJECT-TYPE
	SYNTAX	 Counter64
	MAX-ACCESS read-only
	STATUS obsolete
	DESCRIPTION "Unused"

	::={drdlProp64Used 3}

drdlProp256Used	OBJECT IDENTIFIER ::={drdl 10}

drdlProp256UsedVal	OBJECT-TYPE
	SYNTAX	 Unsigned32
	MAX-ACCESS read-only
	STATUS current
	DESCRIPTION "Properties used (256)"

	::={drdlProp256Used 1}

drdlProp256UsedMax	OBJECT-TYPE
	SYNTAX	 Unsigned32
	MAX-ACCESS read-only
	STATUS current
	DESCRIPTION "Properties used (256)"

	::={drdlProp256Used 3}

drdlAnalyzerChecks	OBJECT IDENTIFIER ::={drdl 11}

drdlAnalyzerChecksVal	OBJECT-TYPE
	SYNTAX	 Counter64
	MAX-ACCESS read-only
	STATUS current
	DESCRIPTION "Analyzer packet checks"

	::={drdlAnalyzerChecks 1}

drdlAnalyzerChecksMom	OBJECT-TYPE
	SYNTAX	 Unsigned32
	MAX-ACCESS read-only
	STATUS current
	DESCRIPTION "Analyzer packet checks"

	::={drdlAnalyzerChecks 2}

drdlAnalyzerChecksMax	OBJECT-TYPE
	SYNTAX	 Counter64
	MAX-ACCESS read-only
	STATUS current
	DESCRIPTION "Analyzer packet checks"

	::={drdlAnalyzerChecks 3}

drdlAnalyzerCheckedBytes	OBJECT IDENTIFIER ::={drdl 12}

drdlAnalyzerCheckedBytesVal	OBJECT-TYPE
	SYNTAX	 Counter64
	MAX-ACCESS read-only
	STATUS current
	DESCRIPTION "Analyzed bytes"

	::={drdlAnalyzerCheckedBytes 1}

drdlAnalyzerCheckedBytesMom	OBJECT-TYPE
	SYNTAX	 Unsigned32
	MAX-ACCESS read-only
	STATUS current
	DESCRIPTION "Analyzed bytes"

	::={drdlAnalyzerCheckedBytes 2}

drdlAnalyzerCheckedBytesMax	OBJECT-TYPE
	SYNTAX	 Counter64
	MAX-ACCESS read-only
	STATUS current
	DESCRIPTION "Analyzed bytes"

	::={drdlAnalyzerCheckedBytes 3}

drdlAnalyzerSkippedBytes	OBJECT IDENTIFIER ::={drdl 13}

drdlAnalyzerSkippedBytesVal	OBJECT-TYPE
	SYNTAX	 Counter64
	MAX-ACCESS read-only
	STATUS current
	DESCRIPTION "Skipped bytes"

	::={drdlAnalyzerSkippedBytes 1}

drdlAnalyzerSkippedBytesMom	OBJECT-TYPE
	SYNTAX	 Unsigned32
	MAX-ACCESS read-only
	STATUS current
	DESCRIPTION "Skipped bytes"

	::={drdlAnalyzerSkippedBytes 2}

drdlAnalyzerSkippedBytesMax	OBJECT-TYPE
	SYNTAX	 Counter64
	MAX-ACCESS read-only
	STATUS current
	DESCRIPTION "Skipped bytes"

	::={drdlAnalyzerSkippedBytes 3}

drdlAnalyzerActions	OBJECT IDENTIFIER ::={drdl 14}

drdlAnalyzerActionsVal	OBJECT-TYPE
	SYNTAX	 Counter64
	MAX-ACCESS read-only
	STATUS current
	DESCRIPTION "Analyzer actions called"

	::={drdlAnalyzerActions 1}

drdlAnalyzerActionsMom	OBJECT-TYPE
	SYNTAX	 Unsigned32
	MAX-ACCESS read-only
	STATUS current
	DESCRIPTION "Analyzer actions called"

	::={drdlAnalyzerActions 2}

drdlAnalyzerActionsMax	OBJECT-TYPE
	SYNTAX	 Counter64
	MAX-ACCESS read-only
	STATUS current
	DESCRIPTION "Analyzer actions called"

	::={drdlAnalyzerActions 3}

drdlPropertySet	OBJECT IDENTIFIER ::={drdl 15}

drdlPropertySetVal	OBJECT-TYPE
	SYNTAX	 Counter64
	MAX-ACCESS read-only
	STATUS current
	DESCRIPTION "Analyzer properties set"

	::={drdlPropertySet 1}

drdlPropertySetMom	OBJECT-TYPE
	SYNTAX	 Unsigned32
	MAX-ACCESS read-only
	STATUS current
	DESCRIPTION "Analyzer properties set"

	::={drdlPropertySet 2}

drdlPropertySetMax	OBJECT-TYPE
	SYNTAX	 Counter64
	MAX-ACCESS read-only
	STATUS current
	DESCRIPTION "Analyzer properties set"

	::={drdlPropertySet 3}

drdlRuntime	OBJECT IDENTIFIER ::={drdl 16}

drdlRuntimeVal	OBJECT-TYPE
	SYNTAX	 Unsigned32
	MAX-ACCESS read-only
	STATUS current
	DESCRIPTION "Average cycles per packet"

	::={drdlRuntime 1}

drdlRuntimeMax	OBJECT-TYPE
	SYNTAX	 Unsigned32
	MAX-ACCESS read-only
	STATUS current
	DESCRIPTION "Average cycles per packet"

	::={drdlRuntime 3}

drdlOrphans	OBJECT IDENTIFIER ::={drdl 18}

drdlOrphansVal	OBJECT-TYPE
	SYNTAX	 Counter64
	MAX-ACCESS read-only
	STATUS current
	DESCRIPTION "Orphaned childconnections"

	::={drdlOrphans 1}

drdlOrphansMom	OBJECT-TYPE
	SYNTAX	 Unsigned32
	MAX-ACCESS read-only
	STATUS current
	DESCRIPTION "Orphaned childconnections"

	::={drdlOrphans 2}

drdlOrphansMax	OBJECT-TYPE
	SYNTAX	 Counter64
	MAX-ACCESS read-only
	STATUS current
	DESCRIPTION "Orphaned childconnections"

	::={drdlOrphans 3}

drdlTooManyChildren	OBJECT IDENTIFIER ::={drdl 17}

drdlTooManyChildrenVal	OBJECT-TYPE
	SYNTAX	 Counter64
	MAX-ACCESS read-only
	STATUS current
	DESCRIPTION "Refused childconnection"

	::={drdlTooManyChildren 1}

drdlTooManyChildrenMom	OBJECT-TYPE
	SYNTAX	 Unsigned32
	MAX-ACCESS read-only
	STATUS current
	DESCRIPTION "Refused childconnection"

	::={drdlTooManyChildren 2}

drdlTooManyChildrenMax	OBJECT-TYPE
	SYNTAX	 Counter64
	MAX-ACCESS read-only
	STATUS current
	DESCRIPTION "Refused childconnection"

	::={drdlTooManyChildren 3}

drdlRuntimeFinished	OBJECT IDENTIFIER ::={drdl 19}

drdlRuntimeFinishedVal	OBJECT-TYPE
	SYNTAX	 Unsigned32
	MAX-ACCESS read-only
	STATUS current
	DESCRIPTION "Average cycles per finished packet"

	::={drdlRuntimeFinished 1}

drdlRuntimeFinishedMax	OBJECT-TYPE
	SYNTAX	 Unsigned32
	MAX-ACCESS read-only
	STATUS current
	DESCRIPTION "Average cycles per finished packet"

	::={drdlRuntimeFinished 3}

drdlFindHeavy	OBJECT IDENTIFIER ::={drdl 20}

drdlFindHeavyVal	OBJECT-TYPE
	SYNTAX	 Counter64
	MAX-ACCESS read-only
	STATUS current
	DESCRIPTION "Heavy cycle packets"

	::={drdlFindHeavy 1}

drdlFindHeavyMom	OBJECT-TYPE
	SYNTAX	 Unsigned32
	MAX-ACCESS read-only
	STATUS current
	DESCRIPTION "Heavy cycle packets"

	::={drdlFindHeavy 2}

drdlFindHeavyMax	OBJECT-TYPE
	SYNTAX	 Counter64
	MAX-ACCESS read-only
	STATUS current
	DESCRIPTION "Heavy cycle packets"

	::={drdlFindHeavy 3}

drdlAutoAccepts	OBJECT IDENTIFIER ::={drdl 21}

drdlAutoAcceptsVal	OBJECT-TYPE
	SYNTAX	 Counter64
	MAX-ACCESS read-only
	STATUS current
	DESCRIPTION "Number of automatic accepts"

	::={drdlAutoAccepts 1}

drdlAutoAcceptsMom	OBJECT-TYPE
	SYNTAX	 Unsigned32
	MAX-ACCESS read-only
	STATUS current
	DESCRIPTION "Number of automatic accepts"

	::={drdlAutoAccepts 2}

drdlAutoAcceptsMax	OBJECT-TYPE
	SYNTAX	 Counter64
	MAX-ACCESS read-only
	STATUS current
	DESCRIPTION "Number of automatic accepts"

	::={drdlAutoAccepts 3}

drdlBuffersUsed	OBJECT IDENTIFIER ::={drdl 22}

drdlBuffersUsedVal	OBJECT-TYPE
	SYNTAX	 Unsigned32
	MAX-ACCESS read-only
	STATUS current
	DESCRIPTION "Number of buffers used"

	::={drdlBuffersUsed 1}

drdlBuffersUsedMax	OBJECT-TYPE
	SYNTAX	 Unsigned32
	MAX-ACCESS read-only
	STATUS current
	DESCRIPTION "Number of buffers used"

	::={drdlBuffersUsed 3}

drdlBufferAllocationFailures	OBJECT IDENTIFIER ::={drdl 23}

drdlBufferAllocationFailuresVal	OBJECT-TYPE
	SYNTAX	 Counter64
	MAX-ACCESS read-only
	STATUS current
	DESCRIPTION "Number of buffer allocation failures"

	::={drdlBufferAllocationFailures 1}

drdlBufferAllocationFailuresMom	OBJECT-TYPE
	SYNTAX	 Unsigned32
	MAX-ACCESS read-only
	STATUS current
	DESCRIPTION "Number of buffer allocation failures"

	::={drdlBufferAllocationFailures 2}

drdlBufferAllocationFailuresMax	OBJECT-TYPE
	SYNTAX	 Counter64
	MAX-ACCESS read-only
	STATUS current
	DESCRIPTION "Number of buffer allocation failures"

	::={drdlBufferAllocationFailures 3}

drdlFullPackets	OBJECT IDENTIFIER ::={drdl 24}

drdlFullPacketsVal	OBJECT-TYPE
	SYNTAX	 Counter64
	MAX-ACCESS read-only
	STATUS current
	DESCRIPTION "Number of full run packets"

	::={drdlFullPackets 1}

drdlFullPacketsMom	OBJECT-TYPE
	SYNTAX	 Unsigned32
	MAX-ACCESS read-only
	STATUS current
	DESCRIPTION "Number of full run packets"

	::={drdlFullPackets 2}

drdlFullPacketsMax	OBJECT-TYPE
	SYNTAX	 Counter64
	MAX-ACCESS read-only
	STATUS current
	DESCRIPTION "Number of full run packets"

	::={drdlFullPackets 3}

drdlProp0Fail	OBJECT IDENTIFIER ::={drdl 25}

drdlProp0FailVal	OBJECT-TYPE
	SYNTAX	 Unsigned32
	MAX-ACCESS read-only
	STATUS obsolete
	DESCRIPTION "Unused"

	::={drdlProp0Fail 1}

drdlProp0FailMax	OBJECT-TYPE
	SYNTAX	 Unsigned32
	MAX-ACCESS read-only
	STATUS obsolete
	DESCRIPTION "Unused"

	::={drdlProp0Fail 3}

drdlProp0Used	OBJECT IDENTIFIER ::={drdl 26}

drdlProp0UsedVal	OBJECT-TYPE
	SYNTAX	 Unsigned32
	MAX-ACCESS read-only
	STATUS obsolete
	DESCRIPTION "Unused"

	::={drdlProp0Used 1}

drdlProp0UsedMax	OBJECT-TYPE
	SYNTAX	 Unsigned32
	MAX-ACCESS read-only
	STATUS obsolete
	DESCRIPTION "Unused"

	::={drdlProp0Used 3}

drdlSliceStateUsed	OBJECT IDENTIFIER ::={drdl 27}

drdlSliceStateUsedVal	OBJECT-TYPE
	SYNTAX	 Unsigned32
	MAX-ACCESS read-only
	STATUS current
	DESCRIPTION "Number of slice state structures used"

	::={drdlSliceStateUsed 1}

drdlSliceStateUsedMax	OBJECT-TYPE
	SYNTAX	 Unsigned32
	MAX-ACCESS read-only
	STATUS current
	DESCRIPTION "Number of slice state structures used"

	::={drdlSliceStateUsed 3}

drdlSliceStateFail	OBJECT IDENTIFIER ::={drdl 28}

drdlSliceStateFailVal	OBJECT-TYPE
	SYNTAX	 Counter64
	MAX-ACCESS read-only
	STATUS current
	DESCRIPTION "Number of slice state structure allocation failures"

	::={drdlSliceStateFail 1}

drdlSliceStateFailMom	OBJECT-TYPE
	SYNTAX	 Unsigned32
	MAX-ACCESS read-only
	STATUS current
	DESCRIPTION "Number of slice state structure allocation failures"

	::={drdlSliceStateFail 2}

drdlSliceStateFailMax	OBJECT-TYPE
	SYNTAX	 Counter64
	MAX-ACCESS read-only
	STATUS current
	DESCRIPTION "Number of slice state structure allocation failures"

	::={drdlSliceStateFail 3}

drdlLiteralSet	OBJECT IDENTIFIER ::={drdl 29}

drdlLiteralSetVal	OBJECT-TYPE
	SYNTAX	 Counter64
	MAX-ACCESS read-only
	STATUS current
	DESCRIPTION "Analyzer literals set"

	::={drdlLiteralSet 1}

drdlLiteralSetMom	OBJECT-TYPE
	SYNTAX	 Unsigned32
	MAX-ACCESS read-only
	STATUS current
	DESCRIPTION "Analyzer literals set"

	::={drdlLiteralSet 2}

drdlLiteralSetMax	OBJECT-TYPE
	SYNTAX	 Counter64
	MAX-ACCESS read-only
	STATUS current
	DESCRIPTION "Analyzer literals set"

	::={drdlLiteralSet 3}

drdlPropertyFail	OBJECT IDENTIFIER ::={drdl 30}

drdlPropertyFailVal	OBJECT-TYPE
	SYNTAX	 Counter64
	MAX-ACCESS read-only
	STATUS current
	DESCRIPTION "Analyzer properties that could not be set"

	::={drdlPropertyFail 1}

drdlPropertyFailMom	OBJECT-TYPE
	SYNTAX	 Unsigned32
	MAX-ACCESS read-only
	STATUS current
	DESCRIPTION "Analyzer properties that could not be set"

	::={drdlPropertyFail 2}

drdlPropertyFailMax	OBJECT-TYPE
	SYNTAX	 Counter64
	MAX-ACCESS read-only
	STATUS current
	DESCRIPTION "Analyzer properties that could not be set"

	::={drdlPropertyFail 3}

drdlVsRangeTests	OBJECT IDENTIFIER ::={drdl 45}

drdlVsRangeTestsVal	OBJECT-TYPE
	SYNTAX	 Counter64
	MAX-ACCESS read-only
	STATUS current
	DESCRIPTION "Virtual services range tests"

	::={drdlVsRangeTests 1}

drdlVsRangeTestsMom	OBJECT-TYPE
	SYNTAX	 Unsigned32
	MAX-ACCESS read-only
	STATUS current
	DESCRIPTION "Virtual services range tests"

	::={drdlVsRangeTests 2}

drdlVsRangeTestsMax	OBJECT-TYPE
	SYNTAX	 Counter64
	MAX-ACCESS read-only
	STATUS current
	DESCRIPTION "Virtual services range tests"

	::={drdlVsRangeTests 3}

drdlVsRangeSteps	OBJECT IDENTIFIER ::={drdl 46}

drdlVsRangeStepsVal	OBJECT-TYPE
	SYNTAX	 Counter64
	MAX-ACCESS read-only
	STATUS current
	DESCRIPTION "Virtual services range steps"

	::={drdlVsRangeSteps 1}

drdlVsRangeStepsMom	OBJECT-TYPE
	SYNTAX	 Unsigned32
	MAX-ACCESS read-only
	STATUS current
	DESCRIPTION "Virtual services range steps"

	::={drdlVsRangeSteps 2}

drdlVsRangeStepsMax	OBJECT-TYPE
	SYNTAX	 Counter64
	MAX-ACCESS read-only
	STATUS current
	DESCRIPTION "Virtual services range steps"

	::={drdlVsRangeSteps 3}

drdlVsRegexTests	OBJECT IDENTIFIER ::={drdl 47}

drdlVsRegexTestsVal	OBJECT-TYPE
	SYNTAX	 Counter64
	MAX-ACCESS read-only
	STATUS current
	DESCRIPTION "Virtual services regex tests"

	::={drdlVsRegexTests 1}

drdlVsRegexTestsMom	OBJECT-TYPE
	SYNTAX	 Unsigned32
	MAX-ACCESS read-only
	STATUS current
	DESCRIPTION "Virtual services regex tests"

	::={drdlVsRegexTests 2}

drdlVsRegexTestsMax	OBJECT-TYPE
	SYNTAX	 Counter64
	MAX-ACCESS read-only
	STATUS current
	DESCRIPTION "Virtual services regex tests"

	::={drdlVsRegexTests 3}

drdlVsRegexSteps	OBJECT IDENTIFIER ::={drdl 48}

drdlVsRegexStepsVal	OBJECT-TYPE
	SYNTAX	 Counter64
	MAX-ACCESS read-only
	STATUS current
	DESCRIPTION "Virtual services regex steps"

	::={drdlVsRegexSteps 1}

drdlVsRegexStepsMom	OBJECT-TYPE
	SYNTAX	 Unsigned32
	MAX-ACCESS read-only
	STATUS current
	DESCRIPTION "Virtual services regex steps"

	::={drdlVsRegexSteps 2}

drdlVsRegexStepsMax	OBJECT-TYPE
	SYNTAX	 Counter64
	MAX-ACCESS read-only
	STATUS current
	DESCRIPTION "Virtual services regex steps"

	::={drdlVsRegexSteps 3}

drdlTaintFill	OBJECT IDENTIFIER ::={drdl 49}

drdlTaintFillVal	OBJECT-TYPE
	SYNTAX	 Unsigned32
	MAX-ACCESS read-only
	STATUS current
	DESCRIPTION "Buckets used in taint store"

	::={drdlTaintFill 1}

drdlTaintFillMax	OBJECT-TYPE
	SYNTAX	 Unsigned32
	MAX-ACCESS read-only
	STATUS current
	DESCRIPTION "Buckets used in taint store"

	::={drdlTaintFill 3}

drdlChildIterateMax	OBJECT IDENTIFIER ::={drdl 33}

drdlChildIterateMaxVal	OBJECT-TYPE
	SYNTAX	 Unsigned32
	MAX-ACCESS read-only
	STATUS current
	DESCRIPTION "Childconnection iterations during search (max)"

	::={drdlChildIterateMax 1}

drdlChildIterateMaxMax	OBJECT-TYPE
	SYNTAX	 Unsigned32
	MAX-ACCESS read-only
	STATUS current
	DESCRIPTION "Childconnection iterations during search (max)"

	::={drdlChildIterateMax 3}

ethernet	OBJECT IDENTIFIER ::={sysdiag 28}

ethernetUnicast	OBJECT IDENTIFIER ::={ethernet 1}

ethernetUnicastVal	OBJECT-TYPE
	SYNTAX	 Counter64
	MAX-ACCESS read-only
	STATUS current
	DESCRIPTION "Unicast packets"

	::={ethernetUnicast 1}

ethernetUnicastMom	OBJECT-TYPE
	SYNTAX	 Unsigned32
	MAX-ACCESS read-only
	STATUS current
	DESCRIPTION "Unicast packets"

	::={ethernetUnicast 2}

ethernetUnicastMax	OBJECT-TYPE
	SYNTAX	 Counter64
	MAX-ACCESS read-only
	STATUS current
	DESCRIPTION "Unicast packets"

	::={ethernetUnicast 3}

ethernetBroadcast	OBJECT IDENTIFIER ::={ethernet 2}

ethernetBroadcastVal	OBJECT-TYPE
	SYNTAX	 Counter64
	MAX-ACCESS read-only
	STATUS current
	DESCRIPTION "Broadcast packets"

	::={ethernetBroadcast 1}

ethernetBroadcastMom	OBJECT-TYPE
	SYNTAX	 Unsigned32
	MAX-ACCESS read-only
	STATUS current
	DESCRIPTION "Broadcast packets"

	::={ethernetBroadcast 2}

ethernetBroadcastMax	OBJECT-TYPE
	SYNTAX	 Counter64
	MAX-ACCESS read-only
	STATUS current
	DESCRIPTION "Broadcast packets"

	::={ethernetBroadcast 3}

ethernetMulticast	OBJECT IDENTIFIER ::={ethernet 3}

ethernetMulticastVal	OBJECT-TYPE
	SYNTAX	 Counter64
	MAX-ACCESS read-only
	STATUS current
	DESCRIPTION "Multicast packets"

	::={ethernetMulticast 1}

ethernetMulticastMom	OBJECT-TYPE
	SYNTAX	 Unsigned32
	MAX-ACCESS read-only
	STATUS current
	DESCRIPTION "Multicast packets"

	::={ethernetMulticast 2}

ethernetMulticastMax	OBJECT-TYPE
	SYNTAX	 Counter64
	MAX-ACCESS read-only
	STATUS current
	DESCRIPTION "Multicast packets"

	::={ethernetMulticast 3}

ethernet8021q	OBJECT IDENTIFIER ::={ethernet 4}

ethernet8021qVal	OBJECT-TYPE
	SYNTAX	 Counter64
	MAX-ACCESS read-only
	STATUS current
	DESCRIPTION "802.1q encapsulated packets"

	::={ethernet8021q 1}

ethernet8021qMom	OBJECT-TYPE
	SYNTAX	 Unsigned32
	MAX-ACCESS read-only
	STATUS current
	DESCRIPTION "802.1q encapsulated packets"

	::={ethernet8021q 2}

ethernet8021qMax	OBJECT-TYPE
	SYNTAX	 Counter64
	MAX-ACCESS read-only
	STATUS current
	DESCRIPTION "802.1q encapsulated packets"

	::={ethernet8021q 3}

ethernetMpls	OBJECT IDENTIFIER ::={ethernet 5}

ethernetMplsVal	OBJECT-TYPE
	SYNTAX	 Counter64
	MAX-ACCESS read-only
	STATUS current
	DESCRIPTION "MPLS over Ethernet frames"

	::={ethernetMpls 1}

ethernetMplsMom	OBJECT-TYPE
	SYNTAX	 Unsigned32
	MAX-ACCESS read-only
	STATUS current
	DESCRIPTION "MPLS over Ethernet frames"

	::={ethernetMpls 2}

ethernetMplsMax	OBJECT-TYPE
	SYNTAX	 Counter64
	MAX-ACCESS read-only
	STATUS current
	DESCRIPTION "MPLS over Ethernet frames"

	::={ethernetMpls 3}

ethernetMplsOoh	OBJECT IDENTIFIER ::={ethernet 6}

ethernetMplsOohVal	OBJECT-TYPE
	SYNTAX	 Counter64
	MAX-ACCESS read-only
	STATUS current
	DESCRIPTION "Invalid MPLS frames"

	::={ethernetMplsOoh 1}

ethernetMplsOohMom	OBJECT-TYPE
	SYNTAX	 Unsigned32
	MAX-ACCESS read-only
	STATUS current
	DESCRIPTION "Invalid MPLS frames"

	::={ethernetMplsOoh 2}

ethernetMplsOohMax	OBJECT-TYPE
	SYNTAX	 Counter64
	MAX-ACCESS read-only
	STATUS current
	DESCRIPTION "Invalid MPLS frames"

	::={ethernetMplsOoh 3}

ethernetNonIp	OBJECT IDENTIFIER ::={ethernet 7}

ethernetNonIpVal	OBJECT-TYPE
	SYNTAX	 Counter64
	MAX-ACCESS read-only
	STATUS current
	DESCRIPTION "Non IP packets"

	::={ethernetNonIp 1}

ethernetNonIpMom	OBJECT-TYPE
	SYNTAX	 Unsigned32
	MAX-ACCESS read-only
	STATUS current
	DESCRIPTION "Non IP packets"

	::={ethernetNonIp 2}

ethernetNonIpMax	OBJECT-TYPE
	SYNTAX	 Counter64
	MAX-ACCESS read-only
	STATUS current
	DESCRIPTION "Non IP packets"

	::={ethernetNonIp 3}

ethernetDivert	OBJECT IDENTIFIER ::={ethernet 8}

ethernetDivertVal	OBJECT-TYPE
	SYNTAX	 Counter64
	MAX-ACCESS read-only
	STATUS current
	DESCRIPTION "Divert packets"

	::={ethernetDivert 1}

ethernetDivertMom	OBJECT-TYPE
	SYNTAX	 Unsigned32
	MAX-ACCESS read-only
	STATUS current
	DESCRIPTION "Divert packets"

	::={ethernetDivert 2}

ethernetDivertMax	OBJECT-TYPE
	SYNTAX	 Counter64
	MAX-ACCESS read-only
	STATUS current
	DESCRIPTION "Divert packets"

	::={ethernetDivert 3}

ethernetHBResetDrops	OBJECT IDENTIFIER ::={ethernet 21}

ethernetHBResetDropsVal	OBJECT-TYPE
	SYNTAX	 Counter64
	MAX-ACCESS read-only
	STATUS current
	DESCRIPTION "Dropped packets because of HB Reset"

	::={ethernetHBResetDrops 1}

ethernetHBResetDropsMom	OBJECT-TYPE
	SYNTAX	 Unsigned32
	MAX-ACCESS read-only
	STATUS current
	DESCRIPTION "Dropped packets because of HB Reset"

	::={ethernetHBResetDrops 2}

ethernetHBResetDropsMax	OBJECT-TYPE
	SYNTAX	 Counter64
	MAX-ACCESS read-only
	STATUS current
	DESCRIPTION "Dropped packets because of HB Reset"

	::={ethernetHBResetDrops 3}

ethernetShuntEthertypePackets	OBJECT IDENTIFIER ::={ethernet 22}

ethernetShuntEthertypePacketsVal	OBJECT-TYPE
	SYNTAX	 Counter64
	MAX-ACCESS read-only
	STATUS current
	DESCRIPTION "Shunted packets (ethertype)"

	::={ethernetShuntEthertypePackets 1}

ethernetShuntEthertypePacketsMom	OBJECT-TYPE
	SYNTAX	 Unsigned32
	MAX-ACCESS read-only
	STATUS current
	DESCRIPTION "Shunted packets (ethertype)"

	::={ethernetShuntEthertypePackets 2}

ethernetShuntEthertypePacketsMax	OBJECT-TYPE
	SYNTAX	 Counter64
	MAX-ACCESS read-only
	STATUS current
	DESCRIPTION "Shunted packets (ethertype)"

	::={ethernetShuntEthertypePackets 3}

ethernetShuntEthertypeBytes	OBJECT IDENTIFIER ::={ethernet 23}

ethernetShuntEthertypeBytesVal	OBJECT-TYPE
	SYNTAX	 Counter64
	MAX-ACCESS read-only
	STATUS current
	DESCRIPTION "Shunted bytes (ethertype)"

	::={ethernetShuntEthertypeBytes 1}

ethernetShuntEthertypeBytesMom	OBJECT-TYPE
	SYNTAX	 Unsigned32
	MAX-ACCESS read-only
	STATUS current
	DESCRIPTION "Shunted bytes (ethertype)"

	::={ethernetShuntEthertypeBytes 2}

ethernetShuntEthertypeBytesMax	OBJECT-TYPE
	SYNTAX	 Counter64
	MAX-ACCESS read-only
	STATUS current
	DESCRIPTION "Shunted bytes (ethertype)"

	::={ethernetShuntEthertypeBytes 3}

ethernetShuntMplsPackets	OBJECT IDENTIFIER ::={ethernet 24}

ethernetShuntMplsPacketsVal	OBJECT-TYPE
	SYNTAX	 Counter64
	MAX-ACCESS read-only
	STATUS current
	DESCRIPTION "Shunted packets (MPLS)"

	::={ethernetShuntMplsPackets 1}

ethernetShuntMplsPacketsMom	OBJECT-TYPE
	SYNTAX	 Unsigned32
	MAX-ACCESS read-only
	STATUS current
	DESCRIPTION "Shunted packets (MPLS)"

	::={ethernetShuntMplsPackets 2}

ethernetShuntMplsPacketsMax	OBJECT-TYPE
	SYNTAX	 Counter64
	MAX-ACCESS read-only
	STATUS current
	DESCRIPTION "Shunted packets (MPLS)"

	::={ethernetShuntMplsPackets 3}

ethernetShuntMplsBytes	OBJECT IDENTIFIER ::={ethernet 25}

ethernetShuntMplsBytesVal	OBJECT-TYPE
	SYNTAX	 Counter64
	MAX-ACCESS read-only
	STATUS current
	DESCRIPTION "Shunted bytes (MPLS)"

	::={ethernetShuntMplsBytes 1}

ethernetShuntMplsBytesMom	OBJECT-TYPE
	SYNTAX	 Unsigned32
	MAX-ACCESS read-only
	STATUS current
	DESCRIPTION "Shunted bytes (MPLS)"

	::={ethernetShuntMplsBytes 2}

ethernetShuntMplsBytesMax	OBJECT-TYPE
	SYNTAX	 Counter64
	MAX-ACCESS read-only
	STATUS current
	DESCRIPTION "Shunted bytes (MPLS)"

	::={ethernetShuntMplsBytes 3}

ethernetShuntEoMplsPackets	OBJECT IDENTIFIER ::={ethernet 26}

ethernetShuntEoMplsPacketsVal	OBJECT-TYPE
	SYNTAX	 Counter64
	MAX-ACCESS read-only
	STATUS current
	DESCRIPTION "Shunted packets (EoMPLS)"

	::={ethernetShuntEoMplsPackets 1}

ethernetShuntEoMplsPacketsMom	OBJECT-TYPE
	SYNTAX	 Unsigned32
	MAX-ACCESS read-only
	STATUS current
	DESCRIPTION "Shunted packets (EoMPLS)"

	::={ethernetShuntEoMplsPackets 2}

ethernetShuntEoMplsPacketsMax	OBJECT-TYPE
	SYNTAX	 Counter64
	MAX-ACCESS read-only
	STATUS current
	DESCRIPTION "Shunted packets (EoMPLS)"

	::={ethernetShuntEoMplsPackets 3}

ethernetShuntEoMplsBytes	OBJECT IDENTIFIER ::={ethernet 27}

ethernetShuntEoMplsBytesVal	OBJECT-TYPE
	SYNTAX	 Counter64
	MAX-ACCESS read-only
	STATUS current
	DESCRIPTION "Shunted bytes (EoMPLS)"

	::={ethernetShuntEoMplsBytes 1}

ethernetShuntEoMplsBytesMom	OBJECT-TYPE
	SYNTAX	 Unsigned32
	MAX-ACCESS read-only
	STATUS current
	DESCRIPTION "Shunted bytes (EoMPLS)"

	::={ethernetShuntEoMplsBytes 2}

ethernetShuntEoMplsBytesMax	OBJECT-TYPE
	SYNTAX	 Counter64
	MAX-ACCESS read-only
	STATUS current
	DESCRIPTION "Shunted bytes (EoMPLS)"

	::={ethernetShuntEoMplsBytes 3}

ethernetShuntDot1qPackets	OBJECT IDENTIFIER ::={ethernet 28}

ethernetShuntDot1qPacketsVal	OBJECT-TYPE
	SYNTAX	 Counter64
	MAX-ACCESS read-only
	STATUS current
	DESCRIPTION "Shunted packets (Dot1q)"

	::={ethernetShuntDot1qPackets 1}

ethernetShuntDot1qPacketsMom	OBJECT-TYPE
	SYNTAX	 Unsigned32
	MAX-ACCESS read-only
	STATUS current
	DESCRIPTION "Shunted packets (Dot1q)"

	::={ethernetShuntDot1qPackets 2}

ethernetShuntDot1qPacketsMax	OBJECT-TYPE
	SYNTAX	 Counter64
	MAX-ACCESS read-only
	STATUS current
	DESCRIPTION "Shunted packets (Dot1q)"

	::={ethernetShuntDot1qPackets 3}

ethernetShuntDot1qBytes	OBJECT IDENTIFIER ::={ethernet 29}

ethernetShuntDot1qBytesVal	OBJECT-TYPE
	SYNTAX	 Counter64
	MAX-ACCESS read-only
	STATUS current
	DESCRIPTION "Shunted bytes (Dot1q)"

	::={ethernetShuntDot1qBytes 1}

ethernetShuntDot1qBytesMom	OBJECT-TYPE
	SYNTAX	 Unsigned32
	MAX-ACCESS read-only
	STATUS current
	DESCRIPTION "Shunted bytes (Dot1q)"

	::={ethernetShuntDot1qBytes 2}

ethernetShuntDot1qBytesMax	OBJECT-TYPE
	SYNTAX	 Counter64
	MAX-ACCESS read-only
	STATUS current
	DESCRIPTION "Shunted bytes (Dot1q)"

	::={ethernetShuntDot1qBytes 3}

ipv4	OBJECT IDENTIFIER ::={sysdiag 32}

ipv4Packets	OBJECT IDENTIFIER ::={ipv4 1}

ipv4PacketsVal	OBJECT-TYPE
	SYNTAX	 Counter64
	MAX-ACCESS read-only
	STATUS current
	DESCRIPTION "RX packets"

	::={ipv4Packets 1}

ipv4PacketsMom	OBJECT-TYPE
	SYNTAX	 Unsigned32
	MAX-ACCESS read-only
	STATUS current
	DESCRIPTION "RX packets"

	::={ipv4Packets 2}

ipv4PacketsMax	OBJECT-TYPE
	SYNTAX	 Counter64
	MAX-ACCESS read-only
	STATUS current
	DESCRIPTION "RX packets"

	::={ipv4Packets 3}

ipv4Bytes	OBJECT IDENTIFIER ::={ipv4 2}

ipv4BytesVal	OBJECT-TYPE
	SYNTAX	 Counter64
	MAX-ACCESS read-only
	STATUS current
	DESCRIPTION "RX data"

	::={ipv4Bytes 1}

ipv4BytesMom	OBJECT-TYPE
	SYNTAX	 Unsigned32
	MAX-ACCESS read-only
	STATUS current
	DESCRIPTION "RX data"

	::={ipv4Bytes 2}

ipv4BytesMax	OBJECT-TYPE
	SYNTAX	 Counter64
	MAX-ACCESS read-only
	STATUS current
	DESCRIPTION "RX data"

	::={ipv4Bytes 3}

ipv4RefusedShort	OBJECT IDENTIFIER ::={ipv4 3}

ipv4RefusedShortVal	OBJECT-TYPE
	SYNTAX	 Counter64
	MAX-ACCESS read-only
	STATUS current
	DESCRIPTION "Refused (packet is too short)"

	::={ipv4RefusedShort 1}

ipv4RefusedShortMom	OBJECT-TYPE
	SYNTAX	 Unsigned32
	MAX-ACCESS read-only
	STATUS current
	DESCRIPTION "Refused (packet is too short)"

	::={ipv4RefusedShort 2}

ipv4RefusedShortMax	OBJECT-TYPE
	SYNTAX	 Counter64
	MAX-ACCESS read-only
	STATUS current
	DESCRIPTION "Refused (packet is too short)"

	::={ipv4RefusedShort 3}

ipv4RefusedVersion	OBJECT IDENTIFIER ::={ipv4 4}

ipv4RefusedVersionVal	OBJECT-TYPE
	SYNTAX	 Counter64
	MAX-ACCESS read-only
	STATUS current
	DESCRIPTION "Refused (invalid version)"

	::={ipv4RefusedVersion 1}

ipv4RefusedVersionMom	OBJECT-TYPE
	SYNTAX	 Unsigned32
	MAX-ACCESS read-only
	STATUS current
	DESCRIPTION "Refused (invalid version)"

	::={ipv4RefusedVersion 2}

ipv4RefusedVersionMax	OBJECT-TYPE
	SYNTAX	 Counter64
	MAX-ACCESS read-only
	STATUS current
	DESCRIPTION "Refused (invalid version)"

	::={ipv4RefusedVersion 3}

ipv4RefusedSelf	OBJECT IDENTIFIER ::={ipv4 5}

ipv4RefusedSelfVal	OBJECT-TYPE
	SYNTAX	 Counter64
	MAX-ACCESS read-only
	STATUS current
	DESCRIPTION "Refused (src == dest)"

	::={ipv4RefusedSelf 1}

ipv4RefusedSelfMom	OBJECT-TYPE
	SYNTAX	 Unsigned32
	MAX-ACCESS read-only
	STATUS current
	DESCRIPTION "Refused (src == dest)"

	::={ipv4RefusedSelf 2}

ipv4RefusedSelfMax	OBJECT-TYPE
	SYNTAX	 Counter64
	MAX-ACCESS read-only
	STATUS current
	DESCRIPTION "Refused (src == dest)"

	::={ipv4RefusedSelf 3}

ipv4Unfragmented	OBJECT IDENTIFIER ::={ipv4 6}

ipv4UnfragmentedVal	OBJECT-TYPE
	SYNTAX	 Counter64
	MAX-ACCESS read-only
	STATUS current
	DESCRIPTION "Unfragmented packets"

	::={ipv4Unfragmented 1}

ipv4UnfragmentedMom	OBJECT-TYPE
	SYNTAX	 Unsigned32
	MAX-ACCESS read-only
	STATUS current
	DESCRIPTION "Unfragmented packets"

	::={ipv4Unfragmented 2}

ipv4UnfragmentedMax	OBJECT-TYPE
	SYNTAX	 Counter64
	MAX-ACCESS read-only
	STATUS current
	DESCRIPTION "Unfragmented packets"

	::={ipv4Unfragmented 3}

ipv4Fragmented	OBJECT IDENTIFIER ::={ipv4 7}

ipv4FragmentedVal	OBJECT-TYPE
	SYNTAX	 Counter64
	MAX-ACCESS read-only
	STATUS current
	DESCRIPTION "Packet fragments"

	::={ipv4Fragmented 1}

ipv4FragmentedMom	OBJECT-TYPE
	SYNTAX	 Unsigned32
	MAX-ACCESS read-only
	STATUS current
	DESCRIPTION "Packet fragments"

	::={ipv4Fragmented 2}

ipv4FragmentedMax	OBJECT-TYPE
	SYNTAX	 Counter64
	MAX-ACCESS read-only
	STATUS current
	DESCRIPTION "Packet fragments"

	::={ipv4Fragmented 3}

ipv4Forwarded	OBJECT IDENTIFIER ::={ipv4 8}

ipv4ForwardedVal	OBJECT-TYPE
	SYNTAX	 Counter64
	MAX-ACCESS read-only
	STATUS current
	DESCRIPTION "TX packets"

	::={ipv4Forwarded 1}

ipv4ForwardedMom	OBJECT-TYPE
	SYNTAX	 Unsigned32
	MAX-ACCESS read-only
	STATUS current
	DESCRIPTION "TX packets"

	::={ipv4Forwarded 2}

ipv4ForwardedMax	OBJECT-TYPE
	SYNTAX	 Counter64
	MAX-ACCESS read-only
	STATUS current
	DESCRIPTION "TX packets"

	::={ipv4Forwarded 3}

ipv4RefusedFwd	OBJECT IDENTIFIER ::={ipv4 9}

ipv4RefusedFwdVal	OBJECT-TYPE
	SYNTAX	 Counter64
	MAX-ACCESS read-only
	STATUS current
	DESCRIPTION "Enqueued or dropped packets"

	::={ipv4RefusedFwd 1}

ipv4RefusedFwdMom	OBJECT-TYPE
	SYNTAX	 Unsigned32
	MAX-ACCESS read-only
	STATUS current
	DESCRIPTION "Enqueued or dropped packets"

	::={ipv4RefusedFwd 2}

ipv4RefusedFwdMax	OBJECT-TYPE
	SYNTAX	 Counter64
	MAX-ACCESS read-only
	STATUS current
	DESCRIPTION "Enqueued or dropped packets"

	::={ipv4RefusedFwd 3}

ipv4FragmentedIds	OBJECT IDENTIFIER ::={ipv4 10}

ipv4FragmentedIdsVal	OBJECT-TYPE
	SYNTAX	 Unsigned32
	MAX-ACCESS read-only
	STATUS current
	DESCRIPTION "Fragment ids"

	::={ipv4FragmentedIds 1}

ipv4FragmentedIdsMax	OBJECT-TYPE
	SYNTAX	 Unsigned32
	MAX-ACCESS read-only
	STATUS current
	DESCRIPTION "Fragment ids"

	::={ipv4FragmentedIds 3}

ipv4Fragments	OBJECT IDENTIFIER ::={ipv4 11}

ipv4FragmentsVal	OBJECT-TYPE
	SYNTAX	 Unsigned32
	MAX-ACCESS read-only
	STATUS current
	DESCRIPTION "Fragments in queue"

	::={ipv4Fragments 1}

ipv4FragmentsMax	OBJECT-TYPE
	SYNTAX	 Unsigned32
	MAX-ACCESS read-only
	STATUS current
	DESCRIPTION "Fragments in queue"

	::={ipv4Fragments 3}

ipv4FragmentHeadersUsed	OBJECT IDENTIFIER ::={ipv4 12}

ipv4FragmentHeadersUsedVal	OBJECT-TYPE
	SYNTAX	 Unsigned32
	MAX-ACCESS read-only
	STATUS current
	DESCRIPTION "Fragment headers"

	::={ipv4FragmentHeadersUsed 1}

ipv4FragmentHeadersUsedMax	OBJECT-TYPE
	SYNTAX	 Unsigned32
	MAX-ACCESS read-only
	STATUS current
	DESCRIPTION "Fragment headers"

	::={ipv4FragmentHeadersUsed 3}

ipv4Runtime	OBJECT IDENTIFIER ::={ipv4 13}

ipv4RuntimeVal	OBJECT-TYPE
	SYNTAX	 Unsigned32
	MAX-ACCESS read-only
	STATUS current
	DESCRIPTION "Average cycles per packet"

	::={ipv4Runtime 1}

ipv4RuntimeMax	OBJECT-TYPE
	SYNTAX	 Unsigned32
	MAX-ACCESS read-only
	STATUS current
	DESCRIPTION "Average cycles per packet"

	::={ipv4Runtime 3}

ipv4RefusedOof	OBJECT IDENTIFIER ::={ipv4 14}

ipv4RefusedOofVal	OBJECT-TYPE
	SYNTAX	 Counter64
	MAX-ACCESS read-only
	STATUS current
	DESCRIPTION "Refused (out of fragments)"

	::={ipv4RefusedOof 1}

ipv4RefusedOofMom	OBJECT-TYPE
	SYNTAX	 Unsigned32
	MAX-ACCESS read-only
	STATUS current
	DESCRIPTION "Refused (out of fragments)"

	::={ipv4RefusedOof 2}

ipv4RefusedOofMax	OBJECT-TYPE
	SYNTAX	 Counter64
	MAX-ACCESS read-only
	STATUS current
	DESCRIPTION "Refused (out of fragments)"

	::={ipv4RefusedOof 3}

ipv4FragmentAllocationFailures	OBJECT IDENTIFIER ::={ipv4 15}

ipv4FragmentAllocationFailuresVal	OBJECT-TYPE
	SYNTAX	 Counter64
	MAX-ACCESS read-only
	STATUS current
	DESCRIPTION "Fragment allocation failures"

	::={ipv4FragmentAllocationFailures 1}

ipv4FragmentAllocationFailuresMom	OBJECT-TYPE
	SYNTAX	 Unsigned32
	MAX-ACCESS read-only
	STATUS current
	DESCRIPTION "Fragment allocation failures"

	::={ipv4FragmentAllocationFailures 2}

ipv4FragmentAllocationFailuresMax	OBJECT-TYPE
	SYNTAX	 Counter64
	MAX-ACCESS read-only
	STATUS current
	DESCRIPTION "Fragment allocation failures"

	::={ipv4FragmentAllocationFailures 3}

ipv4FragmentReassFail	OBJECT IDENTIFIER ::={ipv4 16}

ipv4FragmentReassFailVal	OBJECT-TYPE
	SYNTAX	 Counter64
	MAX-ACCESS read-only
	STATUS current
	DESCRIPTION "Fragment reassembly failures"

	::={ipv4FragmentReassFail 1}

ipv4FragmentReassFailMom	OBJECT-TYPE
	SYNTAX	 Unsigned32
	MAX-ACCESS read-only
	STATUS current
	DESCRIPTION "Fragment reassembly failures"

	::={ipv4FragmentReassFail 2}

ipv4FragmentReassFailMax	OBJECT-TYPE
	SYNTAX	 Counter64
	MAX-ACCESS read-only
	STATUS current
	DESCRIPTION "Fragment reassembly failures"

	::={ipv4FragmentReassFail 3}

ipv4RefusedFilter	OBJECT IDENTIFIER ::={ipv4 17}

ipv4RefusedFilterVal	OBJECT-TYPE
	SYNTAX	 Counter64
	MAX-ACCESS read-only
	STATUS current
	DESCRIPTION "Packets refused by lowlevel filter"

	::={ipv4RefusedFilter 1}

ipv4RefusedFilterMom	OBJECT-TYPE
	SYNTAX	 Unsigned32
	MAX-ACCESS read-only
	STATUS current
	DESCRIPTION "Packets refused by lowlevel filter"

	::={ipv4RefusedFilter 2}

ipv4RefusedFilterMax	OBJECT-TYPE
	SYNTAX	 Counter64
	MAX-ACCESS read-only
	STATUS current
	DESCRIPTION "Packets refused by lowlevel filter"

	::={ipv4RefusedFilter 3}

ipv4Heavy	OBJECT IDENTIFIER ::={ipv4 18}

ipv4HeavyVal	OBJECT-TYPE
	SYNTAX	 Counter64
	MAX-ACCESS read-only
	STATUS current
	DESCRIPTION "Heavy cycle packets"

	::={ipv4Heavy 1}

ipv4HeavyMom	OBJECT-TYPE
	SYNTAX	 Unsigned32
	MAX-ACCESS read-only
	STATUS current
	DESCRIPTION "Heavy cycle packets"

	::={ipv4Heavy 2}

ipv4HeavyMax	OBJECT-TYPE
	SYNTAX	 Counter64
	MAX-ACCESS read-only
	STATUS current
	DESCRIPTION "Heavy cycle packets"

	::={ipv4Heavy 3}

ipv4FragmentTooNoisy	OBJECT IDENTIFIER ::={ipv4 19}

ipv4FragmentTooNoisyVal	OBJECT-TYPE
	SYNTAX	 Counter64
	MAX-ACCESS read-only
	STATUS current
	DESCRIPTION "Packets refused (too many fragments)"

	::={ipv4FragmentTooNoisy 1}

ipv4FragmentTooNoisyMom	OBJECT-TYPE
	SYNTAX	 Unsigned32
	MAX-ACCESS read-only
	STATUS current
	DESCRIPTION "Packets refused (too many fragments)"

	::={ipv4FragmentTooNoisy 2}

ipv4FragmentTooNoisyMax	OBJECT-TYPE
	SYNTAX	 Counter64
	MAX-ACCESS read-only
	STATUS current
	DESCRIPTION "Packets refused (too many fragments)"

	::={ipv4FragmentTooNoisy 3}

ipv4Reassembled	OBJECT IDENTIFIER ::={ipv4 20}

ipv4ReassembledVal	OBJECT-TYPE
	SYNTAX	 Counter64
	MAX-ACCESS read-only
	STATUS current
	DESCRIPTION "Reassembled packets"

	::={ipv4Reassembled 1}

ipv4ReassembledMom	OBJECT-TYPE
	SYNTAX	 Unsigned32
	MAX-ACCESS read-only
	STATUS current
	DESCRIPTION "Reassembled packets"

	::={ipv4Reassembled 2}

ipv4ReassembledMax	OBJECT-TYPE
	SYNTAX	 Counter64
	MAX-ACCESS read-only
	STATUS current
	DESCRIPTION "Reassembled packets"

	::={ipv4Reassembled 3}

ipv4FragmentDrops	OBJECT IDENTIFIER ::={ipv4 21}

ipv4FragmentDropsVal	OBJECT-TYPE
	SYNTAX	 Counter64
	MAX-ACCESS read-only
	STATUS current
	DESCRIPTION "Dropped fragments (timeout/LRU)"

	::={ipv4FragmentDrops 1}

ipv4FragmentDropsMom	OBJECT-TYPE
	SYNTAX	 Unsigned32
	MAX-ACCESS read-only
	STATUS current
	DESCRIPTION "Dropped fragments (timeout/LRU)"

	::={ipv4FragmentDrops 2}

ipv4FragmentDropsMax	OBJECT-TYPE
	SYNTAX	 Counter64
	MAX-ACCESS read-only
	STATUS current
	DESCRIPTION "Dropped fragments (timeout/LRU)"

	::={ipv4FragmentDrops 3}

ipv4ShuntAddressPackets	OBJECT IDENTIFIER ::={ipv4 35}

ipv4ShuntAddressPacketsVal	OBJECT-TYPE
	SYNTAX	 Counter64
	MAX-ACCESS read-only
	STATUS current
	DESCRIPTION "Shunted packets (address)"

	::={ipv4ShuntAddressPackets 1}

ipv4ShuntAddressPacketsMom	OBJECT-TYPE
	SYNTAX	 Unsigned32
	MAX-ACCESS read-only
	STATUS current
	DESCRIPTION "Shunted packets (address)"

	::={ipv4ShuntAddressPackets 2}

ipv4ShuntAddressPacketsMax	OBJECT-TYPE
	SYNTAX	 Counter64
	MAX-ACCESS read-only
	STATUS current
	DESCRIPTION "Shunted packets (address)"

	::={ipv4ShuntAddressPackets 3}

ipv4ShuntAddressBytes	OBJECT IDENTIFIER ::={ipv4 36}

ipv4ShuntAddressBytesVal	OBJECT-TYPE
	SYNTAX	 Counter64
	MAX-ACCESS read-only
	STATUS current
	DESCRIPTION "Shunted bytes (address)"

	::={ipv4ShuntAddressBytes 1}

ipv4ShuntAddressBytesMom	OBJECT-TYPE
	SYNTAX	 Unsigned32
	MAX-ACCESS read-only
	STATUS current
	DESCRIPTION "Shunted bytes (address)"

	::={ipv4ShuntAddressBytes 2}

ipv4ShuntAddressBytesMax	OBJECT-TYPE
	SYNTAX	 Counter64
	MAX-ACCESS read-only
	STATUS current
	DESCRIPTION "Shunted bytes (address)"

	::={ipv4ShuntAddressBytes 3}

ipv4ShuntProtoPackets	OBJECT IDENTIFIER ::={ipv4 37}

ipv4ShuntProtoPacketsVal	OBJECT-TYPE
	SYNTAX	 Counter64
	MAX-ACCESS read-only
	STATUS current
	DESCRIPTION "Shunted packets (protocol)"

	::={ipv4ShuntProtoPackets 1}

ipv4ShuntProtoPacketsMom	OBJECT-TYPE
	SYNTAX	 Unsigned32
	MAX-ACCESS read-only
	STATUS current
	DESCRIPTION "Shunted packets (protocol)"

	::={ipv4ShuntProtoPackets 2}

ipv4ShuntProtoPacketsMax	OBJECT-TYPE
	SYNTAX	 Counter64
	MAX-ACCESS read-only
	STATUS current
	DESCRIPTION "Shunted packets (protocol)"

	::={ipv4ShuntProtoPackets 3}

ipv4ShuntProtoBytes	OBJECT IDENTIFIER ::={ipv4 38}

ipv4ShuntProtoBytesVal	OBJECT-TYPE
	SYNTAX	 Counter64
	MAX-ACCESS read-only
	STATUS current
	DESCRIPTION "Shunted bytes (protocol)"

	::={ipv4ShuntProtoBytes 1}

ipv4ShuntProtoBytesMom	OBJECT-TYPE
	SYNTAX	 Unsigned32
	MAX-ACCESS read-only
	STATUS current
	DESCRIPTION "Shunted bytes (protocol)"

	::={ipv4ShuntProtoBytes 2}

ipv4ShuntProtoBytesMax	OBJECT-TYPE
	SYNTAX	 Counter64
	MAX-ACCESS read-only
	STATUS current
	DESCRIPTION "Shunted bytes (protocol)"

	::={ipv4ShuntProtoBytes 3}

ipv6	OBJECT IDENTIFIER ::={sysdiag 126}

ipv6Packets	OBJECT IDENTIFIER ::={ipv6 1}

ipv6PacketsVal	OBJECT-TYPE
	SYNTAX	 Counter64
	MAX-ACCESS read-only
	STATUS current
	DESCRIPTION "RX packets"

	::={ipv6Packets 1}

ipv6PacketsMom	OBJECT-TYPE
	SYNTAX	 Unsigned32
	MAX-ACCESS read-only
	STATUS current
	DESCRIPTION "RX packets"

	::={ipv6Packets 2}

ipv6PacketsMax	OBJECT-TYPE
	SYNTAX	 Counter64
	MAX-ACCESS read-only
	STATUS current
	DESCRIPTION "RX packets"

	::={ipv6Packets 3}

ipv6Bytes	OBJECT IDENTIFIER ::={ipv6 2}

ipv6BytesVal	OBJECT-TYPE
	SYNTAX	 Counter64
	MAX-ACCESS read-only
	STATUS current
	DESCRIPTION "RX data"

	::={ipv6Bytes 1}

ipv6BytesMom	OBJECT-TYPE
	SYNTAX	 Unsigned32
	MAX-ACCESS read-only
	STATUS current
	DESCRIPTION "RX data"

	::={ipv6Bytes 2}

ipv6BytesMax	OBJECT-TYPE
	SYNTAX	 Counter64
	MAX-ACCESS read-only
	STATUS current
	DESCRIPTION "RX data"

	::={ipv6Bytes 3}

ipv6RefusedShort	OBJECT IDENTIFIER ::={ipv6 3}

ipv6RefusedShortVal	OBJECT-TYPE
	SYNTAX	 Counter64
	MAX-ACCESS read-only
	STATUS current
	DESCRIPTION "Refused (packet is too short)"

	::={ipv6RefusedShort 1}

ipv6RefusedShortMom	OBJECT-TYPE
	SYNTAX	 Unsigned32
	MAX-ACCESS read-only
	STATUS current
	DESCRIPTION "Refused (packet is too short)"

	::={ipv6RefusedShort 2}

ipv6RefusedShortMax	OBJECT-TYPE
	SYNTAX	 Counter64
	MAX-ACCESS read-only
	STATUS current
	DESCRIPTION "Refused (packet is too short)"

	::={ipv6RefusedShort 3}

ipv6RefusedVersion	OBJECT IDENTIFIER ::={ipv6 4}

ipv6RefusedVersionVal	OBJECT-TYPE
	SYNTAX	 Counter64
	MAX-ACCESS read-only
	STATUS current
	DESCRIPTION "Refused (invalid version)"

	::={ipv6RefusedVersion 1}

ipv6RefusedVersionMom	OBJECT-TYPE
	SYNTAX	 Unsigned32
	MAX-ACCESS read-only
	STATUS current
	DESCRIPTION "Refused (invalid version)"

	::={ipv6RefusedVersion 2}

ipv6RefusedVersionMax	OBJECT-TYPE
	SYNTAX	 Counter64
	MAX-ACCESS read-only
	STATUS current
	DESCRIPTION "Refused (invalid version)"

	::={ipv6RefusedVersion 3}

ipv6RefusedSelf	OBJECT IDENTIFIER ::={ipv6 5}

ipv6RefusedSelfVal	OBJECT-TYPE
	SYNTAX	 Counter64
	MAX-ACCESS read-only
	STATUS current
	DESCRIPTION "Refused (src == dest)"

	::={ipv6RefusedSelf 1}

ipv6RefusedSelfMom	OBJECT-TYPE
	SYNTAX	 Unsigned32
	MAX-ACCESS read-only
	STATUS current
	DESCRIPTION "Refused (src == dest)"

	::={ipv6RefusedSelf 2}

ipv6RefusedSelfMax	OBJECT-TYPE
	SYNTAX	 Counter64
	MAX-ACCESS read-only
	STATUS current
	DESCRIPTION "Refused (src == dest)"

	::={ipv6RefusedSelf 3}

ipv6Unfragmented	OBJECT IDENTIFIER ::={ipv6 6}

ipv6UnfragmentedVal	OBJECT-TYPE
	SYNTAX	 Counter64
	MAX-ACCESS read-only
	STATUS current
	DESCRIPTION "Unfragmented packets"

	::={ipv6Unfragmented 1}

ipv6UnfragmentedMom	OBJECT-TYPE
	SYNTAX	 Unsigned32
	MAX-ACCESS read-only
	STATUS current
	DESCRIPTION "Unfragmented packets"

	::={ipv6Unfragmented 2}

ipv6UnfragmentedMax	OBJECT-TYPE
	SYNTAX	 Counter64
	MAX-ACCESS read-only
	STATUS current
	DESCRIPTION "Unfragmented packets"

	::={ipv6Unfragmented 3}

ipv6Fragmented	OBJECT IDENTIFIER ::={ipv6 7}

ipv6FragmentedVal	OBJECT-TYPE
	SYNTAX	 Counter64
	MAX-ACCESS read-only
	STATUS current
	DESCRIPTION "Packet fragments"

	::={ipv6Fragmented 1}

ipv6FragmentedMom	OBJECT-TYPE
	SYNTAX	 Unsigned32
	MAX-ACCESS read-only
	STATUS current
	DESCRIPTION "Packet fragments"

	::={ipv6Fragmented 2}

ipv6FragmentedMax	OBJECT-TYPE
	SYNTAX	 Counter64
	MAX-ACCESS read-only
	STATUS current
	DESCRIPTION "Packet fragments"

	::={ipv6Fragmented 3}

ipv6Forwarded	OBJECT IDENTIFIER ::={ipv6 8}

ipv6ForwardedVal	OBJECT-TYPE
	SYNTAX	 Counter64
	MAX-ACCESS read-only
	STATUS current
	DESCRIPTION "TX packets"

	::={ipv6Forwarded 1}

ipv6ForwardedMom	OBJECT-TYPE
	SYNTAX	 Unsigned32
	MAX-ACCESS read-only
	STATUS current
	DESCRIPTION "TX packets"

	::={ipv6Forwarded 2}

ipv6ForwardedMax	OBJECT-TYPE
	SYNTAX	 Counter64
	MAX-ACCESS read-only
	STATUS current
	DESCRIPTION "TX packets"

	::={ipv6Forwarded 3}

ipv6RefusedFwd	OBJECT IDENTIFIER ::={ipv6 9}

ipv6RefusedFwdVal	OBJECT-TYPE
	SYNTAX	 Counter64
	MAX-ACCESS read-only
	STATUS current
	DESCRIPTION "Enqueued or dropped packets"

	::={ipv6RefusedFwd 1}

ipv6RefusedFwdMom	OBJECT-TYPE
	SYNTAX	 Unsigned32
	MAX-ACCESS read-only
	STATUS current
	DESCRIPTION "Enqueued or dropped packets"

	::={ipv6RefusedFwd 2}

ipv6RefusedFwdMax	OBJECT-TYPE
	SYNTAX	 Counter64
	MAX-ACCESS read-only
	STATUS current
	DESCRIPTION "Enqueued or dropped packets"

	::={ipv6RefusedFwd 3}

ipv6FragmentedIds	OBJECT IDENTIFIER ::={ipv6 10}

ipv6FragmentedIdsVal	OBJECT-TYPE
	SYNTAX	 Unsigned32
	MAX-ACCESS read-only
	STATUS current
	DESCRIPTION "Fragment ids"

	::={ipv6FragmentedIds 1}

ipv6FragmentedIdsMax	OBJECT-TYPE
	SYNTAX	 Unsigned32
	MAX-ACCESS read-only
	STATUS current
	DESCRIPTION "Fragment ids"

	::={ipv6FragmentedIds 3}

ipv6Fragments	OBJECT IDENTIFIER ::={ipv6 11}

ipv6FragmentsVal	OBJECT-TYPE
	SYNTAX	 Unsigned32
	MAX-ACCESS read-only
	STATUS current
	DESCRIPTION "Fragments in queue"

	::={ipv6Fragments 1}

ipv6FragmentsMax	OBJECT-TYPE
	SYNTAX	 Unsigned32
	MAX-ACCESS read-only
	STATUS current
	DESCRIPTION "Fragments in queue"

	::={ipv6Fragments 3}

ipv6FragmentHeadersUsed	OBJECT IDENTIFIER ::={ipv6 12}

ipv6FragmentHeadersUsedVal	OBJECT-TYPE
	SYNTAX	 Unsigned32
	MAX-ACCESS read-only
	STATUS current
	DESCRIPTION "Fragment headers"

	::={ipv6FragmentHeadersUsed 1}

ipv6FragmentHeadersUsedMax	OBJECT-TYPE
	SYNTAX	 Unsigned32
	MAX-ACCESS read-only
	STATUS current
	DESCRIPTION "Fragment headers"

	::={ipv6FragmentHeadersUsed 3}

ipv6Runtime	OBJECT IDENTIFIER ::={ipv6 13}

ipv6RuntimeVal	OBJECT-TYPE
	SYNTAX	 Unsigned32
	MAX-ACCESS read-only
	STATUS current
	DESCRIPTION "Average cycles per packet"

	::={ipv6Runtime 1}

ipv6RuntimeMax	OBJECT-TYPE
	SYNTAX	 Unsigned32
	MAX-ACCESS read-only
	STATUS current
	DESCRIPTION "Average cycles per packet"

	::={ipv6Runtime 3}

ipv6RefusedOof	OBJECT IDENTIFIER ::={ipv6 14}

ipv6RefusedOofVal	OBJECT-TYPE
	SYNTAX	 Counter64
	MAX-ACCESS read-only
	STATUS current
	DESCRIPTION "Refused (out of fragments)"

	::={ipv6RefusedOof 1}

ipv6RefusedOofMom	OBJECT-TYPE
	SYNTAX	 Unsigned32
	MAX-ACCESS read-only
	STATUS current
	DESCRIPTION "Refused (out of fragments)"

	::={ipv6RefusedOof 2}

ipv6RefusedOofMax	OBJECT-TYPE
	SYNTAX	 Counter64
	MAX-ACCESS read-only
	STATUS current
	DESCRIPTION "Refused (out of fragments)"

	::={ipv6RefusedOof 3}

ipv6FragmentAllocationFailures	OBJECT IDENTIFIER ::={ipv6 15}

ipv6FragmentAllocationFailuresVal	OBJECT-TYPE
	SYNTAX	 Counter64
	MAX-ACCESS read-only
	STATUS current
	DESCRIPTION "Fragment allocation failures"

	::={ipv6FragmentAllocationFailures 1}

ipv6FragmentAllocationFailuresMom	OBJECT-TYPE
	SYNTAX	 Unsigned32
	MAX-ACCESS read-only
	STATUS current
	DESCRIPTION "Fragment allocation failures"

	::={ipv6FragmentAllocationFailures 2}

ipv6FragmentAllocationFailuresMax	OBJECT-TYPE
	SYNTAX	 Counter64
	MAX-ACCESS read-only
	STATUS current
	DESCRIPTION "Fragment allocation failures"

	::={ipv6FragmentAllocationFailures 3}

ipv6FragmentReassFail	OBJECT IDENTIFIER ::={ipv6 16}

ipv6FragmentReassFailVal	OBJECT-TYPE
	SYNTAX	 Counter64
	MAX-ACCESS read-only
	STATUS current
	DESCRIPTION "Fragment reassembly failures"

	::={ipv6FragmentReassFail 1}

ipv6FragmentReassFailMom	OBJECT-TYPE
	SYNTAX	 Unsigned32
	MAX-ACCESS read-only
	STATUS current
	DESCRIPTION "Fragment reassembly failures"

	::={ipv6FragmentReassFail 2}

ipv6FragmentReassFailMax	OBJECT-TYPE
	SYNTAX	 Counter64
	MAX-ACCESS read-only
	STATUS current
	DESCRIPTION "Fragment reassembly failures"

	::={ipv6FragmentReassFail 3}

ipv6RefusedFilter	OBJECT IDENTIFIER ::={ipv6 17}

ipv6RefusedFilterVal	OBJECT-TYPE
	SYNTAX	 Counter64
	MAX-ACCESS read-only
	STATUS current
	DESCRIPTION "Packets refused by lowlevel filter"

	::={ipv6RefusedFilter 1}

ipv6RefusedFilterMom	OBJECT-TYPE
	SYNTAX	 Unsigned32
	MAX-ACCESS read-only
	STATUS current
	DESCRIPTION "Packets refused by lowlevel filter"

	::={ipv6RefusedFilter 2}

ipv6RefusedFilterMax	OBJECT-TYPE
	SYNTAX	 Counter64
	MAX-ACCESS read-only
	STATUS current
	DESCRIPTION "Packets refused by lowlevel filter"

	::={ipv6RefusedFilter 3}

ipv6Heavy	OBJECT IDENTIFIER ::={ipv6 18}

ipv6HeavyVal	OBJECT-TYPE
	SYNTAX	 Counter64
	MAX-ACCESS read-only
	STATUS current
	DESCRIPTION "Heavy cycle packets"

	::={ipv6Heavy 1}

ipv6HeavyMom	OBJECT-TYPE
	SYNTAX	 Unsigned32
	MAX-ACCESS read-only
	STATUS current
	DESCRIPTION "Heavy cycle packets"

	::={ipv6Heavy 2}

ipv6HeavyMax	OBJECT-TYPE
	SYNTAX	 Counter64
	MAX-ACCESS read-only
	STATUS current
	DESCRIPTION "Heavy cycle packets"

	::={ipv6Heavy 3}

ipv6FragmentTooNoisy	OBJECT IDENTIFIER ::={ipv6 19}

ipv6FragmentTooNoisyVal	OBJECT-TYPE
	SYNTAX	 Counter64
	MAX-ACCESS read-only
	STATUS current
	DESCRIPTION "Packets refused (too many fragments)"

	::={ipv6FragmentTooNoisy 1}

ipv6FragmentTooNoisyMom	OBJECT-TYPE
	SYNTAX	 Unsigned32
	MAX-ACCESS read-only
	STATUS current
	DESCRIPTION "Packets refused (too many fragments)"

	::={ipv6FragmentTooNoisy 2}

ipv6FragmentTooNoisyMax	OBJECT-TYPE
	SYNTAX	 Counter64
	MAX-ACCESS read-only
	STATUS current
	DESCRIPTION "Packets refused (too many fragments)"

	::={ipv6FragmentTooNoisy 3}

ipv6Reassembled	OBJECT IDENTIFIER ::={ipv6 20}

ipv6ReassembledVal	OBJECT-TYPE
	SYNTAX	 Counter64
	MAX-ACCESS read-only
	STATUS current
	DESCRIPTION "Reassembled packets"

	::={ipv6Reassembled 1}

ipv6ReassembledMom	OBJECT-TYPE
	SYNTAX	 Unsigned32
	MAX-ACCESS read-only
	STATUS current
	DESCRIPTION "Reassembled packets"

	::={ipv6Reassembled 2}

ipv6ReassembledMax	OBJECT-TYPE
	SYNTAX	 Counter64
	MAX-ACCESS read-only
	STATUS current
	DESCRIPTION "Reassembled packets"

	::={ipv6Reassembled 3}

ipv6FragmentOverlap	OBJECT IDENTIFIER ::={ipv6 21}

ipv6FragmentOverlapVal	OBJECT-TYPE
	SYNTAX	 Counter64
	MAX-ACCESS read-only
	STATUS current
	DESCRIPTION "Overlapping Fragments"

	::={ipv6FragmentOverlap 1}

ipv6FragmentOverlapMom	OBJECT-TYPE
	SYNTAX	 Unsigned32
	MAX-ACCESS read-only
	STATUS current
	DESCRIPTION "Overlapping Fragments"

	::={ipv6FragmentOverlap 2}

ipv6FragmentOverlapMax	OBJECT-TYPE
	SYNTAX	 Counter64
	MAX-ACCESS read-only
	STATUS current
	DESCRIPTION "Overlapping Fragments"

	::={ipv6FragmentOverlap 3}

ipv6ExtDest	OBJECT IDENTIFIER ::={ipv6 22}

ipv6ExtDestVal	OBJECT-TYPE
	SYNTAX	 Counter64
	MAX-ACCESS read-only
	STATUS current
	DESCRIPTION "Destination Ext. Headers"

	::={ipv6ExtDest 1}

ipv6ExtDestMom	OBJECT-TYPE
	SYNTAX	 Unsigned32
	MAX-ACCESS read-only
	STATUS current
	DESCRIPTION "Destination Ext. Headers"

	::={ipv6ExtDest 2}

ipv6ExtDestMax	OBJECT-TYPE
	SYNTAX	 Counter64
	MAX-ACCESS read-only
	STATUS current
	DESCRIPTION "Destination Ext. Headers"

	::={ipv6ExtDest 3}

ipv6ExtHbh	OBJECT IDENTIFIER ::={ipv6 23}

ipv6ExtHbhVal	OBJECT-TYPE
	SYNTAX	 Counter64
	MAX-ACCESS read-only
	STATUS current
	DESCRIPTION "Hob-by-hop Ext. Headers"

	::={ipv6ExtHbh 1}

ipv6ExtHbhMom	OBJECT-TYPE
	SYNTAX	 Unsigned32
	MAX-ACCESS read-only
	STATUS current
	DESCRIPTION "Hob-by-hop Ext. Headers"

	::={ipv6ExtHbh 2}

ipv6ExtHbhMax	OBJECT-TYPE
	SYNTAX	 Counter64
	MAX-ACCESS read-only
	STATUS current
	DESCRIPTION "Hob-by-hop Ext. Headers"

	::={ipv6ExtHbh 3}

ipv6ExtRoute	OBJECT IDENTIFIER ::={ipv6 24}

ipv6ExtRouteVal	OBJECT-TYPE
	SYNTAX	 Counter64
	MAX-ACCESS read-only
	STATUS current
	DESCRIPTION "Route Ext, Headers"

	::={ipv6ExtRoute 1}

ipv6ExtRouteMom	OBJECT-TYPE
	SYNTAX	 Unsigned32
	MAX-ACCESS read-only
	STATUS current
	DESCRIPTION "Route Ext, Headers"

	::={ipv6ExtRoute 2}

ipv6ExtRouteMax	OBJECT-TYPE
	SYNTAX	 Counter64
	MAX-ACCESS read-only
	STATUS current
	DESCRIPTION "Route Ext, Headers"

	::={ipv6ExtRoute 3}

ipv6ExtInvl	OBJECT IDENTIFIER ::={ipv6 25}

ipv6ExtInvlVal	OBJECT-TYPE
	SYNTAX	 Counter64
	MAX-ACCESS read-only
	STATUS current
	DESCRIPTION "Invalid Ext. Headers"

	::={ipv6ExtInvl 1}

ipv6ExtInvlMom	OBJECT-TYPE
	SYNTAX	 Unsigned32
	MAX-ACCESS read-only
	STATUS current
	DESCRIPTION "Invalid Ext. Headers"

	::={ipv6ExtInvl 2}

ipv6ExtInvlMax	OBJECT-TYPE
	SYNTAX	 Counter64
	MAX-ACCESS read-only
	STATUS current
	DESCRIPTION "Invalid Ext. Headers"

	::={ipv6ExtInvl 3}

ipv6FragnentTimeout	OBJECT IDENTIFIER ::={ipv6 26}

ipv6FragnentTimeoutVal	OBJECT-TYPE
	SYNTAX	 Counter64
	MAX-ACCESS read-only
	STATUS current
	DESCRIPTION "Reassembly Timeout"

	::={ipv6FragnentTimeout 1}

ipv6FragnentTimeoutMom	OBJECT-TYPE
	SYNTAX	 Unsigned32
	MAX-ACCESS read-only
	STATUS current
	DESCRIPTION "Reassembly Timeout"

	::={ipv6FragnentTimeout 2}

ipv6FragnentTimeoutMax	OBJECT-TYPE
	SYNTAX	 Counter64
	MAX-ACCESS read-only
	STATUS current
	DESCRIPTION "Reassembly Timeout"

	::={ipv6FragnentTimeout 3}

ipv6FragmentDrops	OBJECT IDENTIFIER ::={ipv6 27}

ipv6FragmentDropsVal	OBJECT-TYPE
	SYNTAX	 Counter64
	MAX-ACCESS read-only
	STATUS current
	DESCRIPTION "Dropped fragments (timeout/LRU)"

	::={ipv6FragmentDrops 1}

ipv6FragmentDropsMom	OBJECT-TYPE
	SYNTAX	 Unsigned32
	MAX-ACCESS read-only
	STATUS current
	DESCRIPTION "Dropped fragments (timeout/LRU)"

	::={ipv6FragmentDrops 2}

ipv6FragmentDropsMax	OBJECT-TYPE
	SYNTAX	 Counter64
	MAX-ACCESS read-only
	STATUS current
	DESCRIPTION "Dropped fragments (timeout/LRU)"

	::={ipv6FragmentDrops 3}

ipv6ShuntAddressPackets	OBJECT IDENTIFIER ::={ipv6 28}

ipv6ShuntAddressPacketsVal	OBJECT-TYPE
	SYNTAX	 Counter64
	MAX-ACCESS read-only
	STATUS current
	DESCRIPTION "Shunted packets (address)"

	::={ipv6ShuntAddressPackets 1}

ipv6ShuntAddressPacketsMom	OBJECT-TYPE
	SYNTAX	 Unsigned32
	MAX-ACCESS read-only
	STATUS current
	DESCRIPTION "Shunted packets (address)"

	::={ipv6ShuntAddressPackets 2}

ipv6ShuntAddressPacketsMax	OBJECT-TYPE
	SYNTAX	 Counter64
	MAX-ACCESS read-only
	STATUS current
	DESCRIPTION "Shunted packets (address)"

	::={ipv6ShuntAddressPackets 3}

ipv6ShuntAddressBytes	OBJECT IDENTIFIER ::={ipv6 29}

ipv6ShuntAddressBytesVal	OBJECT-TYPE
	SYNTAX	 Counter64
	MAX-ACCESS read-only
	STATUS current
	DESCRIPTION "Shunted bytes (address)"

	::={ipv6ShuntAddressBytes 1}

ipv6ShuntAddressBytesMom	OBJECT-TYPE
	SYNTAX	 Unsigned32
	MAX-ACCESS read-only
	STATUS current
	DESCRIPTION "Shunted bytes (address)"

	::={ipv6ShuntAddressBytes 2}

ipv6ShuntAddressBytesMax	OBJECT-TYPE
	SYNTAX	 Counter64
	MAX-ACCESS read-only
	STATUS current
	DESCRIPTION "Shunted bytes (address)"

	::={ipv6ShuntAddressBytes 3}

ipv6ShuntProtoPackets	OBJECT IDENTIFIER ::={ipv6 30}

ipv6ShuntProtoPacketsVal	OBJECT-TYPE
	SYNTAX	 Counter64
	MAX-ACCESS read-only
	STATUS current
	DESCRIPTION "Shunted packets (protocol)"

	::={ipv6ShuntProtoPackets 1}

ipv6ShuntProtoPacketsMom	OBJECT-TYPE
	SYNTAX	 Unsigned32
	MAX-ACCESS read-only
	STATUS current
	DESCRIPTION "Shunted packets (protocol)"

	::={ipv6ShuntProtoPackets 2}

ipv6ShuntProtoPacketsMax	OBJECT-TYPE
	SYNTAX	 Counter64
	MAX-ACCESS read-only
	STATUS current
	DESCRIPTION "Shunted packets (protocol)"

	::={ipv6ShuntProtoPackets 3}

ipv6ShuntProtoBytes	OBJECT IDENTIFIER ::={ipv6 31}

ipv6ShuntProtoBytesVal	OBJECT-TYPE
	SYNTAX	 Counter64
	MAX-ACCESS read-only
	STATUS current
	DESCRIPTION "Shunted bytes (protocol)"

	::={ipv6ShuntProtoBytes 1}

ipv6ShuntProtoBytesMom	OBJECT-TYPE
	SYNTAX	 Unsigned32
	MAX-ACCESS read-only
	STATUS current
	DESCRIPTION "Shunted bytes (protocol)"

	::={ipv6ShuntProtoBytes 2}

ipv6ShuntProtoBytesMax	OBJECT-TYPE
	SYNTAX	 Counter64
	MAX-ACCESS read-only
	STATUS current
	DESCRIPTION "Shunted bytes (protocol)"

	::={ipv6ShuntProtoBytes 3}

ipv6FragInFrag	OBJECT IDENTIFIER ::={ipv6 32}

ipv6FragInFragVal	OBJECT-TYPE
	SYNTAX	 Counter64
	MAX-ACCESS read-only
	STATUS current
	DESCRIPTION "Fragments in Fragments"

	::={ipv6FragInFrag 1}

ipv6FragInFragMom	OBJECT-TYPE
	SYNTAX	 Unsigned32
	MAX-ACCESS read-only
	STATUS current
	DESCRIPTION "Fragments in Fragments"

	::={ipv6FragInFrag 2}

ipv6FragInFragMax	OBJECT-TYPE
	SYNTAX	 Counter64
	MAX-ACCESS read-only
	STATUS current
	DESCRIPTION "Fragments in Fragments"

	::={ipv6FragInFrag 3}

tcpv4	OBJECT IDENTIFIER ::={sysdiag 48}

tcpv4Packets	OBJECT IDENTIFIER ::={tcpv4 1}

tcpv4PacketsVal	OBJECT-TYPE
	SYNTAX	 Counter64
	MAX-ACCESS read-only
	STATUS current
	DESCRIPTION "RX packets"

	::={tcpv4Packets 1}

tcpv4PacketsMom	OBJECT-TYPE
	SYNTAX	 Unsigned32
	MAX-ACCESS read-only
	STATUS current
	DESCRIPTION "RX packets"

	::={tcpv4Packets 2}

tcpv4PacketsMax	OBJECT-TYPE
	SYNTAX	 Counter64
	MAX-ACCESS read-only
	STATUS current
	DESCRIPTION "RX packets"

	::={tcpv4Packets 3}

tcpv4Bytes	OBJECT IDENTIFIER ::={tcpv4 2}

tcpv4BytesVal	OBJECT-TYPE
	SYNTAX	 Counter64
	MAX-ACCESS read-only
	STATUS current
	DESCRIPTION "RX bytes"

	::={tcpv4Bytes 1}

tcpv4BytesMom	OBJECT-TYPE
	SYNTAX	 Unsigned32
	MAX-ACCESS read-only
	STATUS current
	DESCRIPTION "RX bytes"

	::={tcpv4Bytes 2}

tcpv4BytesMax	OBJECT-TYPE
	SYNTAX	 Counter64
	MAX-ACCESS read-only
	STATUS current
	DESCRIPTION "RX bytes"

	::={tcpv4Bytes 3}

tcpv4Forwarded	OBJECT IDENTIFIER ::={tcpv4 3}

tcpv4ForwardedVal	OBJECT-TYPE
	SYNTAX	 Counter64
	MAX-ACCESS read-only
	STATUS current
	DESCRIPTION "TX packets"

	::={tcpv4Forwarded 1}

tcpv4ForwardedMom	OBJECT-TYPE
	SYNTAX	 Unsigned32
	MAX-ACCESS read-only
	STATUS current
	DESCRIPTION "TX packets"

	::={tcpv4Forwarded 2}

tcpv4ForwardedMax	OBJECT-TYPE
	SYNTAX	 Counter64
	MAX-ACCESS read-only
	STATUS current
	DESCRIPTION "TX packets"

	::={tcpv4Forwarded 3}

tcpv4CreateAttempts	OBJECT IDENTIFIER ::={tcpv4 4}

tcpv4CreateAttemptsVal	OBJECT-TYPE
	SYNTAX	 Counter64
	MAX-ACCESS read-only
	STATUS current
	DESCRIPTION "Connection create attempts"

	::={tcpv4CreateAttempts 1}

tcpv4CreateAttemptsMom	OBJECT-TYPE
	SYNTAX	 Unsigned32
	MAX-ACCESS read-only
	STATUS current
	DESCRIPTION "Connection create attempts"

	::={tcpv4CreateAttempts 2}

tcpv4CreateAttemptsMax	OBJECT-TYPE
	SYNTAX	 Counter64
	MAX-ACCESS read-only
	STATUS current
	DESCRIPTION "Connection create attempts"

	::={tcpv4CreateAttempts 3}

tcpv4Created	OBJECT IDENTIFIER ::={tcpv4 5}

tcpv4CreatedVal	OBJECT-TYPE
	SYNTAX	 Counter64
	MAX-ACCESS read-only
	STATUS current
	DESCRIPTION "Connections created"

	::={tcpv4Created 1}

tcpv4CreatedMom	OBJECT-TYPE
	SYNTAX	 Unsigned32
	MAX-ACCESS read-only
	STATUS current
	DESCRIPTION "Connections created"

	::={tcpv4Created 2}

tcpv4CreatedMax	OBJECT-TYPE
	SYNTAX	 Counter64
	MAX-ACCESS read-only
	STATUS current
	DESCRIPTION "Connections created"

	::={tcpv4Created 3}

tcpv4RefusedRuleset	OBJECT IDENTIFIER ::={tcpv4 6}

tcpv4RefusedRulesetVal	OBJECT-TYPE
	SYNTAX	 Counter64
	MAX-ACCESS read-only
	STATUS current
	DESCRIPTION "Refused (ruleset)"

	::={tcpv4RefusedRuleset 1}

tcpv4RefusedRulesetMom	OBJECT-TYPE
	SYNTAX	 Unsigned32
	MAX-ACCESS read-only
	STATUS current
	DESCRIPTION "Refused (ruleset)"

	::={tcpv4RefusedRuleset 2}

tcpv4RefusedRulesetMax	OBJECT-TYPE
	SYNTAX	 Counter64
	MAX-ACCESS read-only
	STATUS current
	DESCRIPTION "Refused (ruleset)"

	::={tcpv4RefusedRuleset 3}

tcpv4RefusedShort	OBJECT IDENTIFIER ::={tcpv4 7}

tcpv4RefusedShortVal	OBJECT-TYPE
	SYNTAX	 Counter64
	MAX-ACCESS read-only
	STATUS current
	DESCRIPTION "Refused (short)"

	::={tcpv4RefusedShort 1}

tcpv4RefusedShortMom	OBJECT-TYPE
	SYNTAX	 Unsigned32
	MAX-ACCESS read-only
	STATUS current
	DESCRIPTION "Refused (short)"

	::={tcpv4RefusedShort 2}

tcpv4RefusedShortMax	OBJECT-TYPE
	SYNTAX	 Counter64
	MAX-ACCESS read-only
	STATUS current
	DESCRIPTION "Refused (short)"

	::={tcpv4RefusedShort 3}

tcpv4RefusedBroadcast	OBJECT IDENTIFIER ::={tcpv4 8}

tcpv4RefusedBroadcastVal	OBJECT-TYPE
	SYNTAX	 Counter64
	MAX-ACCESS read-only
	STATUS current
	DESCRIPTION "Refused (broadcast)"

	::={tcpv4RefusedBroadcast 1}

tcpv4RefusedBroadcastMom	OBJECT-TYPE
	SYNTAX	 Unsigned32
	MAX-ACCESS read-only
	STATUS current
	DESCRIPTION "Refused (broadcast)"

	::={tcpv4RefusedBroadcast 2}

tcpv4RefusedBroadcastMax	OBJECT-TYPE
	SYNTAX	 Counter64
	MAX-ACCESS read-only
	STATUS current
	DESCRIPTION "Refused (broadcast)"

	::={tcpv4RefusedBroadcast 3}

tcpv4RefusedOffset	OBJECT IDENTIFIER ::={tcpv4 9}

tcpv4RefusedOffsetVal	OBJECT-TYPE
	SYNTAX	 Counter64
	MAX-ACCESS read-only
	STATUS current
	DESCRIPTION "Refused (offset)"

	::={tcpv4RefusedOffset 1}

tcpv4RefusedOffsetMom	OBJECT-TYPE
	SYNTAX	 Unsigned32
	MAX-ACCESS read-only
	STATUS current
	DESCRIPTION "Refused (offset)"

	::={tcpv4RefusedOffset 2}

tcpv4RefusedOffsetMax	OBJECT-TYPE
	SYNTAX	 Counter64
	MAX-ACCESS read-only
	STATUS current
	DESCRIPTION "Refused (offset)"

	::={tcpv4RefusedOffset 3}

tcpv4Rejected	OBJECT IDENTIFIER ::={tcpv4 10}

tcpv4RejectedVal	OBJECT-TYPE
	SYNTAX	 Counter64
	MAX-ACCESS read-only
	STATUS current
	DESCRIPTION "Rejected packets"

	::={tcpv4Rejected 1}

tcpv4RejectedMom	OBJECT-TYPE
	SYNTAX	 Unsigned32
	MAX-ACCESS read-only
	STATUS current
	DESCRIPTION "Rejected packets"

	::={tcpv4Rejected 2}

tcpv4RejectedMax	OBJECT-TYPE
	SYNTAX	 Counter64
	MAX-ACCESS read-only
	STATUS current
	DESCRIPTION "Rejected packets"

	::={tcpv4Rejected 3}

tcpv4RejectedOld	OBJECT IDENTIFIER ::={tcpv4 11}

tcpv4RejectedOldVal	OBJECT-TYPE
	SYNTAX	 Counter64
	MAX-ACCESS read-only
	STATUS current
	DESCRIPTION "Rejected packets (old)"

	::={tcpv4RejectedOld 1}

tcpv4RejectedOldMom	OBJECT-TYPE
	SYNTAX	 Unsigned32
	MAX-ACCESS read-only
	STATUS current
	DESCRIPTION "Rejected packets (old)"

	::={tcpv4RejectedOld 2}

tcpv4RejectedOldMax	OBJECT-TYPE
	SYNTAX	 Counter64
	MAX-ACCESS read-only
	STATUS current
	DESCRIPTION "Rejected packets (old)"

	::={tcpv4RejectedOld 3}

tcpv4Lostsync	OBJECT IDENTIFIER ::={tcpv4 12}

tcpv4LostsyncVal	OBJECT-TYPE
	SYNTAX	 Unsigned32
	MAX-ACCESS read-only
	STATUS current
	DESCRIPTION "Out-of-sync connections"

	::={tcpv4Lostsync 1}

tcpv4LostsyncMax	OBJECT-TYPE
	SYNTAX	 Unsigned32
	MAX-ACCESS read-only
	STATUS current
	DESCRIPTION "Out-of-sync connections"

	::={tcpv4Lostsync 3}

tcpv4OldPackets	OBJECT IDENTIFIER ::={tcpv4 13}

tcpv4OldPacketsVal	OBJECT-TYPE
	SYNTAX	 Counter64
	MAX-ACCESS read-only
	STATUS current
	DESCRIPTION "Old packets"

	::={tcpv4OldPackets 1}

tcpv4OldPacketsMom	OBJECT-TYPE
	SYNTAX	 Unsigned32
	MAX-ACCESS read-only
	STATUS current
	DESCRIPTION "Old packets"

	::={tcpv4OldPackets 2}

tcpv4OldPacketsMax	OBJECT-TYPE
	SYNTAX	 Counter64
	MAX-ACCESS read-only
	STATUS current
	DESCRIPTION "Old packets"

	::={tcpv4OldPackets 3}

tcpv4GoodputPackets	OBJECT IDENTIFIER ::={tcpv4 14}

tcpv4GoodputPacketsVal	OBJECT-TYPE
	SYNTAX	 Counter64
	MAX-ACCESS read-only
	STATUS current
	DESCRIPTION "Goodput packets"

	::={tcpv4GoodputPackets 1}

tcpv4GoodputPacketsMom	OBJECT-TYPE
	SYNTAX	 Unsigned32
	MAX-ACCESS read-only
	STATUS current
	DESCRIPTION "Goodput packets"

	::={tcpv4GoodputPackets 2}

tcpv4GoodputPacketsMax	OBJECT-TYPE
	SYNTAX	 Counter64
	MAX-ACCESS read-only
	STATUS current
	DESCRIPTION "Goodput packets"

	::={tcpv4GoodputPackets 3}

tcpv4GoodputBytes	OBJECT IDENTIFIER ::={tcpv4 15}

tcpv4GoodputBytesVal	OBJECT-TYPE
	SYNTAX	 Counter64
	MAX-ACCESS read-only
	STATUS current
	DESCRIPTION "Goodput bytes"

	::={tcpv4GoodputBytes 1}

tcpv4GoodputBytesMom	OBJECT-TYPE
	SYNTAX	 Unsigned32
	MAX-ACCESS read-only
	STATUS current
	DESCRIPTION "Goodput bytes"

	::={tcpv4GoodputBytes 2}

tcpv4GoodputBytesMax	OBJECT-TYPE
	SYNTAX	 Counter64
	MAX-ACCESS read-only
	STATUS current
	DESCRIPTION "Goodput bytes"

	::={tcpv4GoodputBytes 3}

tcpv4Fragments	OBJECT IDENTIFIER ::={tcpv4 16}

tcpv4FragmentsVal	OBJECT-TYPE
	SYNTAX	 Unsigned32
	MAX-ACCESS read-only
	STATUS current
	DESCRIPTION "Saved fragments"

	::={tcpv4Fragments 1}

tcpv4FragmentsMax	OBJECT-TYPE
	SYNTAX	 Unsigned32
	MAX-ACCESS read-only
	STATUS current
	DESCRIPTION "Saved fragments"

	::={tcpv4Fragments 3}

tcpv4FragmentsPayload	OBJECT IDENTIFIER ::={tcpv4 17}

tcpv4FragmentsPayloadVal	OBJECT-TYPE
	SYNTAX	 Unsigned32
	MAX-ACCESS read-only
	STATUS current
	DESCRIPTION "Saved fragments with payload"

	::={tcpv4FragmentsPayload 1}

tcpv4FragmentsPayloadMax	OBJECT-TYPE
	SYNTAX	 Unsigned32
	MAX-ACCESS read-only
	STATUS current
	DESCRIPTION "Saved fragments with payload"

	::={tcpv4FragmentsPayload 3}

tcpv4FragmentsDropped	OBJECT IDENTIFIER ::={tcpv4 18}

tcpv4FragmentsDroppedVal	OBJECT-TYPE
	SYNTAX	 Counter64
	MAX-ACCESS read-only
	STATUS current
	DESCRIPTION "Ignored fragments"

	::={tcpv4FragmentsDropped 1}

tcpv4FragmentsDroppedMom	OBJECT-TYPE
	SYNTAX	 Unsigned32
	MAX-ACCESS read-only
	STATUS current
	DESCRIPTION "Ignored fragments"

	::={tcpv4FragmentsDropped 2}

tcpv4FragmentsDroppedMax	OBJECT-TYPE
	SYNTAX	 Counter64
	MAX-ACCESS read-only
	STATUS current
	DESCRIPTION "Ignored fragments"

	::={tcpv4FragmentsDropped 3}

tcpv4PacketAllocFail	OBJECT IDENTIFIER ::={tcpv4 19}

tcpv4PacketAllocFailVal	OBJECT-TYPE
	SYNTAX	 Counter64
	MAX-ACCESS read-only
	STATUS current
	DESCRIPTION "Packet allocation failures"

	::={tcpv4PacketAllocFail 1}

tcpv4PacketAllocFailMom	OBJECT-TYPE
	SYNTAX	 Unsigned32
	MAX-ACCESS read-only
	STATUS current
	DESCRIPTION "Packet allocation failures"

	::={tcpv4PacketAllocFail 2}

tcpv4PacketAllocFailMax	OBJECT-TYPE
	SYNTAX	 Counter64
	MAX-ACCESS read-only
	STATUS current
	DESCRIPTION "Packet allocation failures"

	::={tcpv4PacketAllocFail 3}

tcpv4Runtime	OBJECT IDENTIFIER ::={tcpv4 20}

tcpv4RuntimeVal	OBJECT-TYPE
	SYNTAX	 Unsigned32
	MAX-ACCESS read-only
	STATUS current
	DESCRIPTION "Average cycles per packet (normal)"

	::={tcpv4Runtime 1}

tcpv4RuntimeMax	OBJECT-TYPE
	SYNTAX	 Unsigned32
	MAX-ACCESS read-only
	STATUS current
	DESCRIPTION "Average cycles per packet (normal)"

	::={tcpv4Runtime 3}

tcpv4RuntimeNew	OBJECT IDENTIFIER ::={tcpv4 21}

tcpv4RuntimeNewVal	OBJECT-TYPE
	SYNTAX	 Unsigned32
	MAX-ACCESS read-only
	STATUS current
	DESCRIPTION "Average cycles per packet (SYN)"

	::={tcpv4RuntimeNew 1}

tcpv4RuntimeNewMax	OBJECT-TYPE
	SYNTAX	 Unsigned32
	MAX-ACCESS read-only
	STATUS current
	DESCRIPTION "Average cycles per packet (SYN)"

	::={tcpv4RuntimeNew 3}

tcpv4RuntimeOld	OBJECT IDENTIFIER ::={tcpv4 22}

tcpv4RuntimeOldVal	OBJECT-TYPE
	SYNTAX	 Unsigned32
	MAX-ACCESS read-only
	STATUS current
	DESCRIPTION "Average cycles per packet (old connections)"

	::={tcpv4RuntimeOld 1}

tcpv4RuntimeOldMax	OBJECT-TYPE
	SYNTAX	 Unsigned32
	MAX-ACCESS read-only
	STATUS current
	DESCRIPTION "Average cycles per packet (old connections)"

	::={tcpv4RuntimeOld 3}

tcpv4OldGoodput	OBJECT IDENTIFIER ::={tcpv4 23}

tcpv4OldGoodputVal	OBJECT-TYPE
	SYNTAX	 Counter64
	MAX-ACCESS read-only
	STATUS current
	DESCRIPTION "Old bytes (goodput)"

	::={tcpv4OldGoodput 1}

tcpv4OldGoodputMom	OBJECT-TYPE
	SYNTAX	 Unsigned32
	MAX-ACCESS read-only
	STATUS current
	DESCRIPTION "Old bytes (goodput)"

	::={tcpv4OldGoodput 2}

tcpv4OldGoodputMax	OBJECT-TYPE
	SYNTAX	 Counter64
	MAX-ACCESS read-only
	STATUS current
	DESCRIPTION "Old bytes (goodput)"

	::={tcpv4OldGoodput 3}

tcpv4OldBytes	OBJECT IDENTIFIER ::={tcpv4 24}

tcpv4OldBytesVal	OBJECT-TYPE
	SYNTAX	 Counter64
	MAX-ACCESS read-only
	STATUS current
	DESCRIPTION "Old bytes"

	::={tcpv4OldBytes 1}

tcpv4OldBytesMom	OBJECT-TYPE
	SYNTAX	 Unsigned32
	MAX-ACCESS read-only
	STATUS current
	DESCRIPTION "Old bytes"

	::={tcpv4OldBytes 2}

tcpv4OldBytesMax	OBJECT-TYPE
	SYNTAX	 Counter64
	MAX-ACCESS read-only
	STATUS current
	DESCRIPTION "Old bytes"

	::={tcpv4OldBytes 3}

tcpv4CorruptOptions	OBJECT IDENTIFIER ::={tcpv4 25}

tcpv4CorruptOptionsVal	OBJECT-TYPE
	SYNTAX	 Counter64
	MAX-ACCESS read-only
	STATUS current
	DESCRIPTION "Packets with corrupt options"

	::={tcpv4CorruptOptions 1}

tcpv4CorruptOptionsMom	OBJECT-TYPE
	SYNTAX	 Unsigned32
	MAX-ACCESS read-only
	STATUS current
	DESCRIPTION "Packets with corrupt options"

	::={tcpv4CorruptOptions 2}

tcpv4CorruptOptionsMax	OBJECT-TYPE
	SYNTAX	 Counter64
	MAX-ACCESS read-only
	STATUS current
	DESCRIPTION "Packets with corrupt options"

	::={tcpv4CorruptOptions 3}

tcpv4CorruptConn	OBJECT IDENTIFIER ::={tcpv4 26}

tcpv4CorruptConnVal	OBJECT-TYPE
	SYNTAX	 Counter64
	MAX-ACCESS read-only
	STATUS current
	DESCRIPTION "Packets with corrupt conn"

	::={tcpv4CorruptConn 1}

tcpv4CorruptConnMom	OBJECT-TYPE
	SYNTAX	 Unsigned32
	MAX-ACCESS read-only
	STATUS current
	DESCRIPTION "Packets with corrupt conn"

	::={tcpv4CorruptConn 2}

tcpv4CorruptConnMax	OBJECT-TYPE
	SYNTAX	 Counter64
	MAX-ACCESS read-only
	STATUS current
	DESCRIPTION "Packets with corrupt conn"

	::={tcpv4CorruptConn 3}

tcpv4FragmentedConnections	OBJECT IDENTIFIER ::={tcpv4 27}

tcpv4FragmentedConnectionsVal	OBJECT-TYPE
	SYNTAX	 Unsigned32
	MAX-ACCESS read-only
	STATUS current
	DESCRIPTION "Connections with fragments"

	::={tcpv4FragmentedConnections 1}

tcpv4FragmentedConnectionsMax	OBJECT-TYPE
	SYNTAX	 Unsigned32
	MAX-ACCESS read-only
	STATUS current
	DESCRIPTION "Connections with fragments"

	::={tcpv4FragmentedConnections 3}

tcpv4OutOfWindowPackets	OBJECT IDENTIFIER ::={tcpv4 28}

tcpv4OutOfWindowPacketsVal	OBJECT-TYPE
	SYNTAX	 Counter64
	MAX-ACCESS read-only
	STATUS current
	DESCRIPTION "Out of window packets (ignored)"

	::={tcpv4OutOfWindowPackets 1}

tcpv4OutOfWindowPacketsMom	OBJECT-TYPE
	SYNTAX	 Unsigned32
	MAX-ACCESS read-only
	STATUS current
	DESCRIPTION "Out of window packets (ignored)"

	::={tcpv4OutOfWindowPackets 2}

tcpv4OutOfWindowPacketsMax	OBJECT-TYPE
	SYNTAX	 Counter64
	MAX-ACCESS read-only
	STATUS current
	DESCRIPTION "Out of window packets (ignored)"

	::={tcpv4OutOfWindowPackets 3}

tcpv4RefusedFilter	OBJECT IDENTIFIER ::={tcpv4 29}

tcpv4RefusedFilterVal	OBJECT-TYPE
	SYNTAX	 Counter64
	MAX-ACCESS read-only
	STATUS current
	DESCRIPTION "Packets refused by lowlevel filter"

	::={tcpv4RefusedFilter 1}

tcpv4RefusedFilterMom	OBJECT-TYPE
	SYNTAX	 Unsigned32
	MAX-ACCESS read-only
	STATUS current
	DESCRIPTION "Packets refused by lowlevel filter"

	::={tcpv4RefusedFilter 2}

tcpv4RefusedFilterMax	OBJECT-TYPE
	SYNTAX	 Counter64
	MAX-ACCESS read-only
	STATUS current
	DESCRIPTION "Packets refused by lowlevel filter"

	::={tcpv4RefusedFilter 3}

tcpv4NewHeavy	OBJECT IDENTIFIER ::={tcpv4 30}

tcpv4NewHeavyVal	OBJECT-TYPE
	SYNTAX	 Counter64
	MAX-ACCESS read-only
	STATUS current
	DESCRIPTION "Heavy new packets"

	::={tcpv4NewHeavy 1}

tcpv4NewHeavyMom	OBJECT-TYPE
	SYNTAX	 Unsigned32
	MAX-ACCESS read-only
	STATUS current
	DESCRIPTION "Heavy new packets"

	::={tcpv4NewHeavy 2}

tcpv4NewHeavyMax	OBJECT-TYPE
	SYNTAX	 Counter64
	MAX-ACCESS read-only
	STATUS current
	DESCRIPTION "Heavy new packets"

	::={tcpv4NewHeavy 3}

tcpv4Heavy	OBJECT IDENTIFIER ::={tcpv4 31}

tcpv4HeavyVal	OBJECT-TYPE
	SYNTAX	 Counter64
	MAX-ACCESS read-only
	STATUS current
	DESCRIPTION "Heavy packets"

	::={tcpv4Heavy 1}

tcpv4HeavyMom	OBJECT-TYPE
	SYNTAX	 Unsigned32
	MAX-ACCESS read-only
	STATUS current
	DESCRIPTION "Heavy packets"

	::={tcpv4Heavy 2}

tcpv4HeavyMax	OBJECT-TYPE
	SYNTAX	 Counter64
	MAX-ACCESS read-only
	STATUS current
	DESCRIPTION "Heavy packets"

	::={tcpv4Heavy 3}

tcpv4SynExisting	OBJECT IDENTIFIER ::={tcpv4 32}

tcpv4SynExistingVal	OBJECT-TYPE
	SYNTAX	 Counter64
	MAX-ACCESS read-only
	STATUS current
	DESCRIPTION "SYN packets for existing connections"

	::={tcpv4SynExisting 1}

tcpv4SynExistingMom	OBJECT-TYPE
	SYNTAX	 Unsigned32
	MAX-ACCESS read-only
	STATUS current
	DESCRIPTION "SYN packets for existing connections"

	::={tcpv4SynExisting 2}

tcpv4SynExistingMax	OBJECT-TYPE
	SYNTAX	 Counter64
	MAX-ACCESS read-only
	STATUS current
	DESCRIPTION "SYN packets for existing connections"

	::={tcpv4SynExisting 3}

tcpv4FragmentAllocFail	OBJECT IDENTIFIER ::={tcpv4 33}

tcpv4FragmentAllocFailVal	OBJECT-TYPE
	SYNTAX	 Counter64
	MAX-ACCESS read-only
	STATUS current
	DESCRIPTION "Fragment allocation failures"

	::={tcpv4FragmentAllocFail 1}

tcpv4FragmentAllocFailMom	OBJECT-TYPE
	SYNTAX	 Unsigned32
	MAX-ACCESS read-only
	STATUS current
	DESCRIPTION "Fragment allocation failures"

	::={tcpv4FragmentAllocFail 2}

tcpv4FragmentAllocFailMax	OBJECT-TYPE
	SYNTAX	 Counter64
	MAX-ACCESS read-only
	STATUS current
	DESCRIPTION "Fragment allocation failures"

	::={tcpv4FragmentAllocFail 3}

tcpv4EnqueuedFragments	OBJECT IDENTIFIER ::={tcpv4 34}

tcpv4EnqueuedFragmentsVal	OBJECT-TYPE
	SYNTAX	 Counter64
	MAX-ACCESS read-only
	STATUS current
	DESCRIPTION "Enqueued fragments"

	::={tcpv4EnqueuedFragments 1}

tcpv4EnqueuedFragmentsMom	OBJECT-TYPE
	SYNTAX	 Unsigned32
	MAX-ACCESS read-only
	STATUS current
	DESCRIPTION "Enqueued fragments"

	::={tcpv4EnqueuedFragments 2}

tcpv4EnqueuedFragmentsMax	OBJECT-TYPE
	SYNTAX	 Counter64
	MAX-ACCESS read-only
	STATUS current
	DESCRIPTION "Enqueued fragments"

	::={tcpv4EnqueuedFragments 3}

tcpv4DequeuedFragments	OBJECT IDENTIFIER ::={tcpv4 35}

tcpv4DequeuedFragmentsVal	OBJECT-TYPE
	SYNTAX	 Counter64
	MAX-ACCESS read-only
	STATUS current
	DESCRIPTION "Dequeued fragments"

	::={tcpv4DequeuedFragments 1}

tcpv4DequeuedFragmentsMom	OBJECT-TYPE
	SYNTAX	 Unsigned32
	MAX-ACCESS read-only
	STATUS current
	DESCRIPTION "Dequeued fragments"

	::={tcpv4DequeuedFragments 2}

tcpv4DequeuedFragmentsMax	OBJECT-TYPE
	SYNTAX	 Counter64
	MAX-ACCESS read-only
	STATUS current
	DESCRIPTION "Dequeued fragments"

	::={tcpv4DequeuedFragments 3}

tcpv4DiscardedFragments	OBJECT IDENTIFIER ::={tcpv4 36}

tcpv4DiscardedFragmentsVal	OBJECT-TYPE
	SYNTAX	 Counter64
	MAX-ACCESS read-only
	STATUS current
	DESCRIPTION "Discarded fragments"

	::={tcpv4DiscardedFragments 1}

tcpv4DiscardedFragmentsMom	OBJECT-TYPE
	SYNTAX	 Unsigned32
	MAX-ACCESS read-only
	STATUS current
	DESCRIPTION "Discarded fragments"

	::={tcpv4DiscardedFragments 2}

tcpv4DiscardedFragmentsMax	OBJECT-TYPE
	SYNTAX	 Counter64
	MAX-ACCESS read-only
	STATUS current
	DESCRIPTION "Discarded fragments"

	::={tcpv4DiscardedFragments 3}

tcpv4EmptyPackets	OBJECT IDENTIFIER ::={tcpv4 37}

tcpv4EmptyPacketsVal	OBJECT-TYPE
	SYNTAX	 Counter64
	MAX-ACCESS read-only
	STATUS current
	DESCRIPTION "Packets without payload"

	::={tcpv4EmptyPackets 1}

tcpv4EmptyPacketsMom	OBJECT-TYPE
	SYNTAX	 Unsigned32
	MAX-ACCESS read-only
	STATUS current
	DESCRIPTION "Packets without payload"

	::={tcpv4EmptyPackets 2}

tcpv4EmptyPacketsMax	OBJECT-TYPE
	SYNTAX	 Counter64
	MAX-ACCESS read-only
	STATUS current
	DESCRIPTION "Packets without payload"

	::={tcpv4EmptyPackets 3}

tcpv4OosPackets	OBJECT IDENTIFIER ::={tcpv4 38}

tcpv4OosPacketsVal	OBJECT-TYPE
	SYNTAX	 Counter64
	MAX-ACCESS read-only
	STATUS current
	DESCRIPTION "Out-of-sync packets"

	::={tcpv4OosPackets 1}

tcpv4OosPacketsMom	OBJECT-TYPE
	SYNTAX	 Unsigned32
	MAX-ACCESS read-only
	STATUS current
	DESCRIPTION "Out-of-sync packets"

	::={tcpv4OosPackets 2}

tcpv4OosPacketsMax	OBJECT-TYPE
	SYNTAX	 Counter64
	MAX-ACCESS read-only
	STATUS current
	DESCRIPTION "Out-of-sync packets"

	::={tcpv4OosPackets 3}

tcpv4OosBytes	OBJECT IDENTIFIER ::={tcpv4 39}

tcpv4OosBytesVal	OBJECT-TYPE
	SYNTAX	 Counter64
	MAX-ACCESS read-only
	STATUS current
	DESCRIPTION "Out-of-sync bytes"

	::={tcpv4OosBytes 1}

tcpv4OosBytesMom	OBJECT-TYPE
	SYNTAX	 Unsigned32
	MAX-ACCESS read-only
	STATUS current
	DESCRIPTION "Out-of-sync bytes"

	::={tcpv4OosBytes 2}

tcpv4OosBytesMax	OBJECT-TYPE
	SYNTAX	 Counter64
	MAX-ACCESS read-only
	STATUS current
	DESCRIPTION "Out-of-sync bytes"

	::={tcpv4OosBytes 3}

tcpv4Retransmits	OBJECT IDENTIFIER ::={tcpv4 40}

tcpv4RetransmitsVal	OBJECT-TYPE
	SYNTAX	 Counter64
	MAX-ACCESS read-only
	STATUS current
	DESCRIPTION "Retransmitted packets"

	::={tcpv4Retransmits 1}

tcpv4RetransmitsMom	OBJECT-TYPE
	SYNTAX	 Unsigned32
	MAX-ACCESS read-only
	STATUS current
	DESCRIPTION "Retransmitted packets"

	::={tcpv4Retransmits 2}

tcpv4RetransmitsMax	OBJECT-TYPE
	SYNTAX	 Counter64
	MAX-ACCESS read-only
	STATUS current
	DESCRIPTION "Retransmitted packets"

	::={tcpv4Retransmits 3}

tcpv6	OBJECT IDENTIFIER ::={sysdiag 127}

tcpv6Packets	OBJECT IDENTIFIER ::={tcpv6 1}

tcpv6PacketsVal	OBJECT-TYPE
	SYNTAX	 Counter64
	MAX-ACCESS read-only
	STATUS current
	DESCRIPTION "RX packets"

	::={tcpv6Packets 1}

tcpv6PacketsMom	OBJECT-TYPE
	SYNTAX	 Unsigned32
	MAX-ACCESS read-only
	STATUS current
	DESCRIPTION "RX packets"

	::={tcpv6Packets 2}

tcpv6PacketsMax	OBJECT-TYPE
	SYNTAX	 Counter64
	MAX-ACCESS read-only
	STATUS current
	DESCRIPTION "RX packets"

	::={tcpv6Packets 3}

tcpv6Bytes	OBJECT IDENTIFIER ::={tcpv6 2}

tcpv6BytesVal	OBJECT-TYPE
	SYNTAX	 Counter64
	MAX-ACCESS read-only
	STATUS current
	DESCRIPTION "RX bytes"

	::={tcpv6Bytes 1}

tcpv6BytesMom	OBJECT-TYPE
	SYNTAX	 Unsigned32
	MAX-ACCESS read-only
	STATUS current
	DESCRIPTION "RX bytes"

	::={tcpv6Bytes 2}

tcpv6BytesMax	OBJECT-TYPE
	SYNTAX	 Counter64
	MAX-ACCESS read-only
	STATUS current
	DESCRIPTION "RX bytes"

	::={tcpv6Bytes 3}

tcpv6Forwarded	OBJECT IDENTIFIER ::={tcpv6 3}

tcpv6ForwardedVal	OBJECT-TYPE
	SYNTAX	 Counter64
	MAX-ACCESS read-only
	STATUS current
	DESCRIPTION "TX packets"

	::={tcpv6Forwarded 1}

tcpv6ForwardedMom	OBJECT-TYPE
	SYNTAX	 Unsigned32
	MAX-ACCESS read-only
	STATUS current
	DESCRIPTION "TX packets"

	::={tcpv6Forwarded 2}

tcpv6ForwardedMax	OBJECT-TYPE
	SYNTAX	 Counter64
	MAX-ACCESS read-only
	STATUS current
	DESCRIPTION "TX packets"

	::={tcpv6Forwarded 3}

tcpv6CreateAttempts	OBJECT IDENTIFIER ::={tcpv6 4}

tcpv6CreateAttemptsVal	OBJECT-TYPE
	SYNTAX	 Counter64
	MAX-ACCESS read-only
	STATUS current
	DESCRIPTION "Connection create attempts"

	::={tcpv6CreateAttempts 1}

tcpv6CreateAttemptsMom	OBJECT-TYPE
	SYNTAX	 Unsigned32
	MAX-ACCESS read-only
	STATUS current
	DESCRIPTION "Connection create attempts"

	::={tcpv6CreateAttempts 2}

tcpv6CreateAttemptsMax	OBJECT-TYPE
	SYNTAX	 Counter64
	MAX-ACCESS read-only
	STATUS current
	DESCRIPTION "Connection create attempts"

	::={tcpv6CreateAttempts 3}

tcpv6Created	OBJECT IDENTIFIER ::={tcpv6 5}

tcpv6CreatedVal	OBJECT-TYPE
	SYNTAX	 Counter64
	MAX-ACCESS read-only
	STATUS current
	DESCRIPTION "Connections created"

	::={tcpv6Created 1}

tcpv6CreatedMom	OBJECT-TYPE
	SYNTAX	 Unsigned32
	MAX-ACCESS read-only
	STATUS current
	DESCRIPTION "Connections created"

	::={tcpv6Created 2}

tcpv6CreatedMax	OBJECT-TYPE
	SYNTAX	 Counter64
	MAX-ACCESS read-only
	STATUS current
	DESCRIPTION "Connections created"

	::={tcpv6Created 3}

tcpv6RefusedRuleset	OBJECT IDENTIFIER ::={tcpv6 6}

tcpv6RefusedRulesetVal	OBJECT-TYPE
	SYNTAX	 Counter64
	MAX-ACCESS read-only
	STATUS current
	DESCRIPTION "Refused (ruleset)"

	::={tcpv6RefusedRuleset 1}

tcpv6RefusedRulesetMom	OBJECT-TYPE
	SYNTAX	 Unsigned32
	MAX-ACCESS read-only
	STATUS current
	DESCRIPTION "Refused (ruleset)"

	::={tcpv6RefusedRuleset 2}

tcpv6RefusedRulesetMax	OBJECT-TYPE
	SYNTAX	 Counter64
	MAX-ACCESS read-only
	STATUS current
	DESCRIPTION "Refused (ruleset)"

	::={tcpv6RefusedRuleset 3}

tcpv6RefusedShort	OBJECT IDENTIFIER ::={tcpv6 7}

tcpv6RefusedShortVal	OBJECT-TYPE
	SYNTAX	 Counter64
	MAX-ACCESS read-only
	STATUS current
	DESCRIPTION "Refused (short)"

	::={tcpv6RefusedShort 1}

tcpv6RefusedShortMom	OBJECT-TYPE
	SYNTAX	 Unsigned32
	MAX-ACCESS read-only
	STATUS current
	DESCRIPTION "Refused (short)"

	::={tcpv6RefusedShort 2}

tcpv6RefusedShortMax	OBJECT-TYPE
	SYNTAX	 Counter64
	MAX-ACCESS read-only
	STATUS current
	DESCRIPTION "Refused (short)"

	::={tcpv6RefusedShort 3}

tcpv6RefusedBroadcast	OBJECT IDENTIFIER ::={tcpv6 8}

tcpv6RefusedBroadcastVal	OBJECT-TYPE
	SYNTAX	 Counter64
	MAX-ACCESS read-only
	STATUS current
	DESCRIPTION "Refused (broadcast)"

	::={tcpv6RefusedBroadcast 1}

tcpv6RefusedBroadcastMom	OBJECT-TYPE
	SYNTAX	 Unsigned32
	MAX-ACCESS read-only
	STATUS current
	DESCRIPTION "Refused (broadcast)"

	::={tcpv6RefusedBroadcast 2}

tcpv6RefusedBroadcastMax	OBJECT-TYPE
	SYNTAX	 Counter64
	MAX-ACCESS read-only
	STATUS current
	DESCRIPTION "Refused (broadcast)"

	::={tcpv6RefusedBroadcast 3}

tcpv6RefusedOffset	OBJECT IDENTIFIER ::={tcpv6 9}

tcpv6RefusedOffsetVal	OBJECT-TYPE
	SYNTAX	 Counter64
	MAX-ACCESS read-only
	STATUS current
	DESCRIPTION "Refused (offset)"

	::={tcpv6RefusedOffset 1}

tcpv6RefusedOffsetMom	OBJECT-TYPE
	SYNTAX	 Unsigned32
	MAX-ACCESS read-only
	STATUS current
	DESCRIPTION "Refused (offset)"

	::={tcpv6RefusedOffset 2}

tcpv6RefusedOffsetMax	OBJECT-TYPE
	SYNTAX	 Counter64
	MAX-ACCESS read-only
	STATUS current
	DESCRIPTION "Refused (offset)"

	::={tcpv6RefusedOffset 3}

tcpv6Rejected	OBJECT IDENTIFIER ::={tcpv6 10}

tcpv6RejectedVal	OBJECT-TYPE
	SYNTAX	 Counter64
	MAX-ACCESS read-only
	STATUS current
	DESCRIPTION "Rejected packets"

	::={tcpv6Rejected 1}

tcpv6RejectedMom	OBJECT-TYPE
	SYNTAX	 Unsigned32
	MAX-ACCESS read-only
	STATUS current
	DESCRIPTION "Rejected packets"

	::={tcpv6Rejected 2}

tcpv6RejectedMax	OBJECT-TYPE
	SYNTAX	 Counter64
	MAX-ACCESS read-only
	STATUS current
	DESCRIPTION "Rejected packets"

	::={tcpv6Rejected 3}

tcpv6RejectedOld	OBJECT IDENTIFIER ::={tcpv6 11}

tcpv6RejectedOldVal	OBJECT-TYPE
	SYNTAX	 Counter64
	MAX-ACCESS read-only
	STATUS current
	DESCRIPTION "Rejected packets (old)"

	::={tcpv6RejectedOld 1}

tcpv6RejectedOldMom	OBJECT-TYPE
	SYNTAX	 Unsigned32
	MAX-ACCESS read-only
	STATUS current
	DESCRIPTION "Rejected packets (old)"

	::={tcpv6RejectedOld 2}

tcpv6RejectedOldMax	OBJECT-TYPE
	SYNTAX	 Counter64
	MAX-ACCESS read-only
	STATUS current
	DESCRIPTION "Rejected packets (old)"

	::={tcpv6RejectedOld 3}

tcpv6Lostsync	OBJECT IDENTIFIER ::={tcpv6 12}

tcpv6LostsyncVal	OBJECT-TYPE
	SYNTAX	 Unsigned32
	MAX-ACCESS read-only
	STATUS current
	DESCRIPTION "Out-of-sync connections"

	::={tcpv6Lostsync 1}

tcpv6LostsyncMax	OBJECT-TYPE
	SYNTAX	 Unsigned32
	MAX-ACCESS read-only
	STATUS current
	DESCRIPTION "Out-of-sync connections"

	::={tcpv6Lostsync 3}

tcpv6OldPackets	OBJECT IDENTIFIER ::={tcpv6 13}

tcpv6OldPacketsVal	OBJECT-TYPE
	SYNTAX	 Counter64
	MAX-ACCESS read-only
	STATUS current
	DESCRIPTION "Old packets"

	::={tcpv6OldPackets 1}

tcpv6OldPacketsMom	OBJECT-TYPE
	SYNTAX	 Unsigned32
	MAX-ACCESS read-only
	STATUS current
	DESCRIPTION "Old packets"

	::={tcpv6OldPackets 2}

tcpv6OldPacketsMax	OBJECT-TYPE
	SYNTAX	 Counter64
	MAX-ACCESS read-only
	STATUS current
	DESCRIPTION "Old packets"

	::={tcpv6OldPackets 3}

tcpv6GoodputPackets	OBJECT IDENTIFIER ::={tcpv6 14}

tcpv6GoodputPacketsVal	OBJECT-TYPE
	SYNTAX	 Counter64
	MAX-ACCESS read-only
	STATUS current
	DESCRIPTION "Goodput packets"

	::={tcpv6GoodputPackets 1}

tcpv6GoodputPacketsMom	OBJECT-TYPE
	SYNTAX	 Unsigned32
	MAX-ACCESS read-only
	STATUS current
	DESCRIPTION "Goodput packets"

	::={tcpv6GoodputPackets 2}

tcpv6GoodputPacketsMax	OBJECT-TYPE
	SYNTAX	 Counter64
	MAX-ACCESS read-only
	STATUS current
	DESCRIPTION "Goodput packets"

	::={tcpv6GoodputPackets 3}

tcpv6GoodputBytes	OBJECT IDENTIFIER ::={tcpv6 15}

tcpv6GoodputBytesVal	OBJECT-TYPE
	SYNTAX	 Counter64
	MAX-ACCESS read-only
	STATUS current
	DESCRIPTION "Goodput bytes"

	::={tcpv6GoodputBytes 1}

tcpv6GoodputBytesMom	OBJECT-TYPE
	SYNTAX	 Unsigned32
	MAX-ACCESS read-only
	STATUS current
	DESCRIPTION "Goodput bytes"

	::={tcpv6GoodputBytes 2}

tcpv6GoodputBytesMax	OBJECT-TYPE
	SYNTAX	 Counter64
	MAX-ACCESS read-only
	STATUS current
	DESCRIPTION "Goodput bytes"

	::={tcpv6GoodputBytes 3}

tcpv6Fragments	OBJECT IDENTIFIER ::={tcpv6 16}

tcpv6FragmentsVal	OBJECT-TYPE
	SYNTAX	 Unsigned32
	MAX-ACCESS read-only
	STATUS current
	DESCRIPTION "Saved fragments"

	::={tcpv6Fragments 1}

tcpv6FragmentsMax	OBJECT-TYPE
	SYNTAX	 Unsigned32
	MAX-ACCESS read-only
	STATUS current
	DESCRIPTION "Saved fragments"

	::={tcpv6Fragments 3}

tcpv6FragmentsPayload	OBJECT IDENTIFIER ::={tcpv6 17}

tcpv6FragmentsPayloadVal	OBJECT-TYPE
	SYNTAX	 Unsigned32
	MAX-ACCESS read-only
	STATUS current
	DESCRIPTION "Saved fragments with payload"

	::={tcpv6FragmentsPayload 1}

tcpv6FragmentsPayloadMax	OBJECT-TYPE
	SYNTAX	 Unsigned32
	MAX-ACCESS read-only
	STATUS current
	DESCRIPTION "Saved fragments with payload"

	::={tcpv6FragmentsPayload 3}

tcpv6FragmentsDropped	OBJECT IDENTIFIER ::={tcpv6 18}

tcpv6FragmentsDroppedVal	OBJECT-TYPE
	SYNTAX	 Counter64
	MAX-ACCESS read-only
	STATUS current
	DESCRIPTION "Ignored fragments"

	::={tcpv6FragmentsDropped 1}

tcpv6FragmentsDroppedMom	OBJECT-TYPE
	SYNTAX	 Unsigned32
	MAX-ACCESS read-only
	STATUS current
	DESCRIPTION "Ignored fragments"

	::={tcpv6FragmentsDropped 2}

tcpv6FragmentsDroppedMax	OBJECT-TYPE
	SYNTAX	 Counter64
	MAX-ACCESS read-only
	STATUS current
	DESCRIPTION "Ignored fragments"

	::={tcpv6FragmentsDropped 3}

tcpv6PacketAllocFail	OBJECT IDENTIFIER ::={tcpv6 19}

tcpv6PacketAllocFailVal	OBJECT-TYPE
	SYNTAX	 Unsigned32
	MAX-ACCESS read-only
	STATUS current
	DESCRIPTION "Packet allocation failures"

	::={tcpv6PacketAllocFail 1}

tcpv6PacketAllocFailMax	OBJECT-TYPE
	SYNTAX	 Unsigned32
	MAX-ACCESS read-only
	STATUS current
	DESCRIPTION "Packet allocation failures"

	::={tcpv6PacketAllocFail 3}

tcpv6Runtime	OBJECT IDENTIFIER ::={tcpv6 20}

tcpv6RuntimeVal	OBJECT-TYPE
	SYNTAX	 Unsigned32
	MAX-ACCESS read-only
	STATUS current
	DESCRIPTION "Average cycles per packet (normal)"

	::={tcpv6Runtime 1}

tcpv6RuntimeMax	OBJECT-TYPE
	SYNTAX	 Unsigned32
	MAX-ACCESS read-only
	STATUS current
	DESCRIPTION "Average cycles per packet (normal)"

	::={tcpv6Runtime 3}

tcpv6RuntimeNew	OBJECT IDENTIFIER ::={tcpv6 21}

tcpv6RuntimeNewVal	OBJECT-TYPE
	SYNTAX	 Unsigned32
	MAX-ACCESS read-only
	STATUS current
	DESCRIPTION "Average cycles per packet (SYN)"

	::={tcpv6RuntimeNew 1}

tcpv6RuntimeNewMax	OBJECT-TYPE
	SYNTAX	 Unsigned32
	MAX-ACCESS read-only
	STATUS current
	DESCRIPTION "Average cycles per packet (SYN)"

	::={tcpv6RuntimeNew 3}

tcpv6RuntimeOld	OBJECT IDENTIFIER ::={tcpv6 22}

tcpv6RuntimeOldVal	OBJECT-TYPE
	SYNTAX	 Unsigned32
	MAX-ACCESS read-only
	STATUS current
	DESCRIPTION "Average cycles per packet (old connections)"

	::={tcpv6RuntimeOld 1}

tcpv6RuntimeOldMax	OBJECT-TYPE
	SYNTAX	 Unsigned32
	MAX-ACCESS read-only
	STATUS current
	DESCRIPTION "Average cycles per packet (old connections)"

	::={tcpv6RuntimeOld 3}

tcpv6OldGoodput	OBJECT IDENTIFIER ::={tcpv6 23}

tcpv6OldGoodputVal	OBJECT-TYPE
	SYNTAX	 Counter64
	MAX-ACCESS read-only
	STATUS current
	DESCRIPTION "Old bytes (goodput)"

	::={tcpv6OldGoodput 1}

tcpv6OldGoodputMom	OBJECT-TYPE
	SYNTAX	 Unsigned32
	MAX-ACCESS read-only
	STATUS current
	DESCRIPTION "Old bytes (goodput)"

	::={tcpv6OldGoodput 2}

tcpv6OldGoodputMax	OBJECT-TYPE
	SYNTAX	 Counter64
	MAX-ACCESS read-only
	STATUS current
	DESCRIPTION "Old bytes (goodput)"

	::={tcpv6OldGoodput 3}

tcpv6OldBytes	OBJECT IDENTIFIER ::={tcpv6 24}

tcpv6OldBytesVal	OBJECT-TYPE
	SYNTAX	 Counter64
	MAX-ACCESS read-only
	STATUS current
	DESCRIPTION "Old bytes"

	::={tcpv6OldBytes 1}

tcpv6OldBytesMom	OBJECT-TYPE
	SYNTAX	 Unsigned32
	MAX-ACCESS read-only
	STATUS current
	DESCRIPTION "Old bytes"

	::={tcpv6OldBytes 2}

tcpv6OldBytesMax	OBJECT-TYPE
	SYNTAX	 Counter64
	MAX-ACCESS read-only
	STATUS current
	DESCRIPTION "Old bytes"

	::={tcpv6OldBytes 3}

tcpv6CorruptOptions	OBJECT IDENTIFIER ::={tcpv6 25}

tcpv6CorruptOptionsVal	OBJECT-TYPE
	SYNTAX	 Counter64
	MAX-ACCESS read-only
	STATUS current
	DESCRIPTION "Packets with corrupt options"

	::={tcpv6CorruptOptions 1}

tcpv6CorruptOptionsMom	OBJECT-TYPE
	SYNTAX	 Unsigned32
	MAX-ACCESS read-only
	STATUS current
	DESCRIPTION "Packets with corrupt options"

	::={tcpv6CorruptOptions 2}

tcpv6CorruptOptionsMax	OBJECT-TYPE
	SYNTAX	 Counter64
	MAX-ACCESS read-only
	STATUS current
	DESCRIPTION "Packets with corrupt options"

	::={tcpv6CorruptOptions 3}

tcpv6CorruptConn	OBJECT IDENTIFIER ::={tcpv6 26}

tcpv6CorruptConnVal	OBJECT-TYPE
	SYNTAX	 Counter64
	MAX-ACCESS read-only
	STATUS current
	DESCRIPTION "Packets with corrupt conn"

	::={tcpv6CorruptConn 1}

tcpv6CorruptConnMom	OBJECT-TYPE
	SYNTAX	 Unsigned32
	MAX-ACCESS read-only
	STATUS current
	DESCRIPTION "Packets with corrupt conn"

	::={tcpv6CorruptConn 2}

tcpv6CorruptConnMax	OBJECT-TYPE
	SYNTAX	 Counter64
	MAX-ACCESS read-only
	STATUS current
	DESCRIPTION "Packets with corrupt conn"

	::={tcpv6CorruptConn 3}

tcpv6FragmentedConnections	OBJECT IDENTIFIER ::={tcpv6 27}

tcpv6FragmentedConnectionsVal	OBJECT-TYPE
	SYNTAX	 Unsigned32
	MAX-ACCESS read-only
	STATUS current
	DESCRIPTION "Connections with fragments"

	::={tcpv6FragmentedConnections 1}

tcpv6FragmentedConnectionsMax	OBJECT-TYPE
	SYNTAX	 Unsigned32
	MAX-ACCESS read-only
	STATUS current
	DESCRIPTION "Connections with fragments"

	::={tcpv6FragmentedConnections 3}

tcpv6OutOfWindowPackets	OBJECT IDENTIFIER ::={tcpv6 28}

tcpv6OutOfWindowPacketsVal	OBJECT-TYPE
	SYNTAX	 Counter64
	MAX-ACCESS read-only
	STATUS current
	DESCRIPTION "Out of window packets (ignored)"

	::={tcpv6OutOfWindowPackets 1}

tcpv6OutOfWindowPacketsMom	OBJECT-TYPE
	SYNTAX	 Unsigned32
	MAX-ACCESS read-only
	STATUS current
	DESCRIPTION "Out of window packets (ignored)"

	::={tcpv6OutOfWindowPackets 2}

tcpv6OutOfWindowPacketsMax	OBJECT-TYPE
	SYNTAX	 Counter64
	MAX-ACCESS read-only
	STATUS current
	DESCRIPTION "Out of window packets (ignored)"

	::={tcpv6OutOfWindowPackets 3}

tcpv6RefusedFilter	OBJECT IDENTIFIER ::={tcpv6 29}

tcpv6RefusedFilterVal	OBJECT-TYPE
	SYNTAX	 Counter64
	MAX-ACCESS read-only
	STATUS current
	DESCRIPTION "Packets refused by lowlevel filter"

	::={tcpv6RefusedFilter 1}

tcpv6RefusedFilterMom	OBJECT-TYPE
	SYNTAX	 Unsigned32
	MAX-ACCESS read-only
	STATUS current
	DESCRIPTION "Packets refused by lowlevel filter"

	::={tcpv6RefusedFilter 2}

tcpv6RefusedFilterMax	OBJECT-TYPE
	SYNTAX	 Counter64
	MAX-ACCESS read-only
	STATUS current
	DESCRIPTION "Packets refused by lowlevel filter"

	::={tcpv6RefusedFilter 3}

tcpv6NewHeavy	OBJECT IDENTIFIER ::={tcpv6 30}

tcpv6NewHeavyVal	OBJECT-TYPE
	SYNTAX	 Counter64
	MAX-ACCESS read-only
	STATUS current
	DESCRIPTION "Heavy new packets"

	::={tcpv6NewHeavy 1}

tcpv6NewHeavyMom	OBJECT-TYPE
	SYNTAX	 Unsigned32
	MAX-ACCESS read-only
	STATUS current
	DESCRIPTION "Heavy new packets"

	::={tcpv6NewHeavy 2}

tcpv6NewHeavyMax	OBJECT-TYPE
	SYNTAX	 Counter64
	MAX-ACCESS read-only
	STATUS current
	DESCRIPTION "Heavy new packets"

	::={tcpv6NewHeavy 3}

tcpv6Heavy	OBJECT IDENTIFIER ::={tcpv6 31}

tcpv6HeavyVal	OBJECT-TYPE
	SYNTAX	 Counter64
	MAX-ACCESS read-only
	STATUS current
	DESCRIPTION "Heavy packets"

	::={tcpv6Heavy 1}

tcpv6HeavyMom	OBJECT-TYPE
	SYNTAX	 Unsigned32
	MAX-ACCESS read-only
	STATUS current
	DESCRIPTION "Heavy packets"

	::={tcpv6Heavy 2}

tcpv6HeavyMax	OBJECT-TYPE
	SYNTAX	 Counter64
	MAX-ACCESS read-only
	STATUS current
	DESCRIPTION "Heavy packets"

	::={tcpv6Heavy 3}

tcpv6SynExisting	OBJECT IDENTIFIER ::={tcpv6 32}

tcpv6SynExistingVal	OBJECT-TYPE
	SYNTAX	 Counter64
	MAX-ACCESS read-only
	STATUS current
	DESCRIPTION "SYN packets for existing connections"

	::={tcpv6SynExisting 1}

tcpv6SynExistingMom	OBJECT-TYPE
	SYNTAX	 Unsigned32
	MAX-ACCESS read-only
	STATUS current
	DESCRIPTION "SYN packets for existing connections"

	::={tcpv6SynExisting 2}

tcpv6SynExistingMax	OBJECT-TYPE
	SYNTAX	 Counter64
	MAX-ACCESS read-only
	STATUS current
	DESCRIPTION "SYN packets for existing connections"

	::={tcpv6SynExisting 3}

tcpv6FragmentAllocFail	OBJECT IDENTIFIER ::={tcpv6 33}

tcpv6FragmentAllocFailVal	OBJECT-TYPE
	SYNTAX	 Unsigned32
	MAX-ACCESS read-only
	STATUS current
	DESCRIPTION "Fragment allocation failures"

	::={tcpv6FragmentAllocFail 1}

tcpv6FragmentAllocFailMax	OBJECT-TYPE
	SYNTAX	 Unsigned32
	MAX-ACCESS read-only
	STATUS current
	DESCRIPTION "Fragment allocation failures"

	::={tcpv6FragmentAllocFail 3}

tcpv6EnqueuedFragments	OBJECT IDENTIFIER ::={tcpv6 34}

tcpv6EnqueuedFragmentsVal	OBJECT-TYPE
	SYNTAX	 Counter64
	MAX-ACCESS read-only
	STATUS current
	DESCRIPTION "Enqueued fragments"

	::={tcpv6EnqueuedFragments 1}

tcpv6EnqueuedFragmentsMom	OBJECT-TYPE
	SYNTAX	 Unsigned32
	MAX-ACCESS read-only
	STATUS current
	DESCRIPTION "Enqueued fragments"

	::={tcpv6EnqueuedFragments 2}

tcpv6EnqueuedFragmentsMax	OBJECT-TYPE
	SYNTAX	 Counter64
	MAX-ACCESS read-only
	STATUS current
	DESCRIPTION "Enqueued fragments"

	::={tcpv6EnqueuedFragments 3}

tcpv6DequeuedFragments	OBJECT IDENTIFIER ::={tcpv6 35}

tcpv6DequeuedFragmentsVal	OBJECT-TYPE
	SYNTAX	 Counter64
	MAX-ACCESS read-only
	STATUS current
	DESCRIPTION "Dequeued fragments"

	::={tcpv6DequeuedFragments 1}

tcpv6DequeuedFragmentsMom	OBJECT-TYPE
	SYNTAX	 Unsigned32
	MAX-ACCESS read-only
	STATUS current
	DESCRIPTION "Dequeued fragments"

	::={tcpv6DequeuedFragments 2}

tcpv6DequeuedFragmentsMax	OBJECT-TYPE
	SYNTAX	 Counter64
	MAX-ACCESS read-only
	STATUS current
	DESCRIPTION "Dequeued fragments"

	::={tcpv6DequeuedFragments 3}

tcpv6DiscardedFragments	OBJECT IDENTIFIER ::={tcpv6 36}

tcpv6DiscardedFragmentsVal	OBJECT-TYPE
	SYNTAX	 Counter64
	MAX-ACCESS read-only
	STATUS current
	DESCRIPTION "Discarded fragments"

	::={tcpv6DiscardedFragments 1}

tcpv6DiscardedFragmentsMom	OBJECT-TYPE
	SYNTAX	 Unsigned32
	MAX-ACCESS read-only
	STATUS current
	DESCRIPTION "Discarded fragments"

	::={tcpv6DiscardedFragments 2}

tcpv6DiscardedFragmentsMax	OBJECT-TYPE
	SYNTAX	 Counter64
	MAX-ACCESS read-only
	STATUS current
	DESCRIPTION "Discarded fragments"

	::={tcpv6DiscardedFragments 3}

tcpv6EmptyPackets	OBJECT IDENTIFIER ::={tcpv6 37}

tcpv6EmptyPacketsVal	OBJECT-TYPE
	SYNTAX	 Counter64
	MAX-ACCESS read-only
	STATUS current
	DESCRIPTION "Packets without payload"

	::={tcpv6EmptyPackets 1}

tcpv6EmptyPacketsMom	OBJECT-TYPE
	SYNTAX	 Unsigned32
	MAX-ACCESS read-only
	STATUS current
	DESCRIPTION "Packets without payload"

	::={tcpv6EmptyPackets 2}

tcpv6EmptyPacketsMax	OBJECT-TYPE
	SYNTAX	 Counter64
	MAX-ACCESS read-only
	STATUS current
	DESCRIPTION "Packets without payload"

	::={tcpv6EmptyPackets 3}

tcpv6OosPackets	OBJECT IDENTIFIER ::={tcpv6 38}

tcpv6OosPacketsVal	OBJECT-TYPE
	SYNTAX	 Counter64
	MAX-ACCESS read-only
	STATUS current
	DESCRIPTION "Out-of-sync packets"

	::={tcpv6OosPackets 1}

tcpv6OosPacketsMom	OBJECT-TYPE
	SYNTAX	 Unsigned32
	MAX-ACCESS read-only
	STATUS current
	DESCRIPTION "Out-of-sync packets"

	::={tcpv6OosPackets 2}

tcpv6OosPacketsMax	OBJECT-TYPE
	SYNTAX	 Counter64
	MAX-ACCESS read-only
	STATUS current
	DESCRIPTION "Out-of-sync packets"

	::={tcpv6OosPackets 3}

tcpv6OosBytes	OBJECT IDENTIFIER ::={tcpv6 39}

tcpv6OosBytesVal	OBJECT-TYPE
	SYNTAX	 Counter64
	MAX-ACCESS read-only
	STATUS current
	DESCRIPTION "Out-of-sync bytes"

	::={tcpv6OosBytes 1}

tcpv6OosBytesMom	OBJECT-TYPE
	SYNTAX	 Unsigned32
	MAX-ACCESS read-only
	STATUS current
	DESCRIPTION "Out-of-sync bytes"

	::={tcpv6OosBytes 2}

tcpv6OosBytesMax	OBJECT-TYPE
	SYNTAX	 Counter64
	MAX-ACCESS read-only
	STATUS current
	DESCRIPTION "Out-of-sync bytes"

	::={tcpv6OosBytes 3}

tcpv6Retransmits	OBJECT IDENTIFIER ::={tcpv6 40}

tcpv6RetransmitsVal	OBJECT-TYPE
	SYNTAX	 Counter64
	MAX-ACCESS read-only
	STATUS current
	DESCRIPTION "Retransmitted packets"

	::={tcpv6Retransmits 1}

tcpv6RetransmitsMom	OBJECT-TYPE
	SYNTAX	 Unsigned32
	MAX-ACCESS read-only
	STATUS current
	DESCRIPTION "Retransmitted packets"

	::={tcpv6Retransmits 2}

tcpv6RetransmitsMax	OBJECT-TYPE
	SYNTAX	 Counter64
	MAX-ACCESS read-only
	STATUS current
	DESCRIPTION "Retransmitted packets"

	::={tcpv6Retransmits 3}

connection	OBJECT IDENTIFIER ::={sysdiag 56}

connectionCount	OBJECT IDENTIFIER ::={connection 1}

connectionCountVal	OBJECT-TYPE
	SYNTAX	 Unsigned32
	MAX-ACCESS read-only
	STATUS current
	DESCRIPTION "Current count"

	::={connectionCount 1}

connectionCountMax	OBJECT-TYPE
	SYNTAX	 Unsigned32
	MAX-ACCESS read-only
	STATUS current
	DESCRIPTION "Current count"

	::={connectionCount 3}

connectionEstCount	OBJECT IDENTIFIER ::={connection 2}

connectionEstCountVal	OBJECT-TYPE
	SYNTAX	 Unsigned32
	MAX-ACCESS read-only
	STATUS current
	DESCRIPTION "Current established count"

	::={connectionEstCount 1}

connectionEstCountMax	OBJECT-TYPE
	SYNTAX	 Unsigned32
	MAX-ACCESS read-only
	STATUS current
	DESCRIPTION "Current established count"

	::={connectionEstCount 3}

connectionCreateAttemptsInbound	OBJECT IDENTIFIER ::={connection 3}

connectionCreateAttemptsInboundVal	OBJECT-TYPE
	SYNTAX	 Counter64
	MAX-ACCESS read-only
	STATUS current
	DESCRIPTION "Create attempts inbound"

	::={connectionCreateAttemptsInbound 1}

connectionCreateAttemptsInboundMom	OBJECT-TYPE
	SYNTAX	 Unsigned32
	MAX-ACCESS read-only
	STATUS current
	DESCRIPTION "Create attempts inbound"

	::={connectionCreateAttemptsInbound 2}

connectionCreateAttemptsInboundMax	OBJECT-TYPE
	SYNTAX	 Counter64
	MAX-ACCESS read-only
	STATUS current
	DESCRIPTION "Create attempts inbound"

	::={connectionCreateAttemptsInbound 3}

connectionCreateAttemptsOutbound	OBJECT IDENTIFIER ::={connection 4}

connectionCreateAttemptsOutboundVal	OBJECT-TYPE
	SYNTAX	 Counter64
	MAX-ACCESS read-only
	STATUS current
	DESCRIPTION "Create attempts outbound"

	::={connectionCreateAttemptsOutbound 1}

connectionCreateAttemptsOutboundMom	OBJECT-TYPE
	SYNTAX	 Unsigned32
	MAX-ACCESS read-only
	STATUS current
	DESCRIPTION "Create attempts outbound"

	::={connectionCreateAttemptsOutbound 2}

connectionCreateAttemptsOutboundMax	OBJECT-TYPE
	SYNTAX	 Counter64
	MAX-ACCESS read-only
	STATUS current
	DESCRIPTION "Create attempts outbound"

	::={connectionCreateAttemptsOutbound 3}

connectionRefusedProt	OBJECT IDENTIFIER ::={connection 5}

connectionRefusedProtVal	OBJECT-TYPE
	SYNTAX	 Counter64
	MAX-ACCESS read-only
	STATUS current
	DESCRIPTION "Attempts refused (connprot)"

	::={connectionRefusedProt 1}

connectionRefusedProtMom	OBJECT-TYPE
	SYNTAX	 Unsigned32
	MAX-ACCESS read-only
	STATUS current
	DESCRIPTION "Attempts refused (connprot)"

	::={connectionRefusedProt 2}

connectionRefusedProtMax	OBJECT-TYPE
	SYNTAX	 Counter64
	MAX-ACCESS read-only
	STATUS current
	DESCRIPTION "Attempts refused (connprot)"

	::={connectionRefusedProt 3}

connectionRefusedFull	OBJECT IDENTIFIER ::={connection 6}

connectionRefusedFullVal	OBJECT-TYPE
	SYNTAX	 Counter64
	MAX-ACCESS read-only
	STATUS current
	DESCRIPTION "Attempts refused (resources)"

	::={connectionRefusedFull 1}

connectionRefusedFullMom	OBJECT-TYPE
	SYNTAX	 Unsigned32
	MAX-ACCESS read-only
	STATUS current
	DESCRIPTION "Attempts refused (resources)"

	::={connectionRefusedFull 2}

connectionRefusedFullMax	OBJECT-TYPE
	SYNTAX	 Counter64
	MAX-ACCESS read-only
	STATUS current
	DESCRIPTION "Attempts refused (resources)"

	::={connectionRefusedFull 3}

connectionCreatedInbound	OBJECT IDENTIFIER ::={connection 7}

connectionCreatedInboundVal	OBJECT-TYPE
	SYNTAX	 Counter64
	MAX-ACCESS read-only
	STATUS current
	DESCRIPTION "Created inbound"

	::={connectionCreatedInbound 1}

connectionCreatedInboundMom	OBJECT-TYPE
	SYNTAX	 Unsigned32
	MAX-ACCESS read-only
	STATUS current
	DESCRIPTION "Created inbound"

	::={connectionCreatedInbound 2}

connectionCreatedInboundMax	OBJECT-TYPE
	SYNTAX	 Counter64
	MAX-ACCESS read-only
	STATUS current
	DESCRIPTION "Created inbound"

	::={connectionCreatedInbound 3}

connectionCreatedOutbound	OBJECT IDENTIFIER ::={connection 8}

connectionCreatedOutboundVal	OBJECT-TYPE
	SYNTAX	 Counter64
	MAX-ACCESS read-only
	STATUS current
	DESCRIPTION "Created outbound"

	::={connectionCreatedOutbound 1}

connectionCreatedOutboundMom	OBJECT-TYPE
	SYNTAX	 Unsigned32
	MAX-ACCESS read-only
	STATUS current
	DESCRIPTION "Created outbound"

	::={connectionCreatedOutbound 2}

connectionCreatedOutboundMax	OBJECT-TYPE
	SYNTAX	 Counter64
	MAX-ACCESS read-only
	STATUS current
	DESCRIPTION "Created outbound"

	::={connectionCreatedOutbound 3}

connectionLruAllocs	OBJECT IDENTIFIER ::={connection 9}

connectionLruAllocsVal	OBJECT-TYPE
	SYNTAX	 Counter64
	MAX-ACCESS read-only
	STATUS current
	DESCRIPTION "Connections allocated from LRU"

	::={connectionLruAllocs 1}

connectionLruAllocsMom	OBJECT-TYPE
	SYNTAX	 Unsigned32
	MAX-ACCESS read-only
	STATUS current
	DESCRIPTION "Connections allocated from LRU"

	::={connectionLruAllocs 2}

connectionLruAllocsMax	OBJECT-TYPE
	SYNTAX	 Counter64
	MAX-ACCESS read-only
	STATUS current
	DESCRIPTION "Connections allocated from LRU"

	::={connectionLruAllocs 3}

connectionLookups	OBJECT IDENTIFIER ::={connection 10}

connectionLookupsVal	OBJECT-TYPE
	SYNTAX	 Counter64
	MAX-ACCESS read-only
	STATUS current
	DESCRIPTION "Lookups"

	::={connectionLookups 1}

connectionLookupsMom	OBJECT-TYPE
	SYNTAX	 Unsigned32
	MAX-ACCESS read-only
	STATUS current
	DESCRIPTION "Lookups"

	::={connectionLookups 2}

connectionLookupsMax	OBJECT-TYPE
	SYNTAX	 Counter64
	MAX-ACCESS read-only
	STATUS current
	DESCRIPTION "Lookups"

	::={connectionLookups 3}

connectionEstablished	OBJECT IDENTIFIER ::={connection 11}

connectionEstablishedVal	OBJECT-TYPE
	SYNTAX	 Counter64
	MAX-ACCESS read-only
	STATUS current
	DESCRIPTION "Made established"

	::={connectionEstablished 1}

connectionEstablishedMom	OBJECT-TYPE
	SYNTAX	 Unsigned32
	MAX-ACCESS read-only
	STATUS current
	DESCRIPTION "Made established"

	::={connectionEstablished 2}

connectionEstablishedMax	OBJECT-TYPE
	SYNTAX	 Counter64
	MAX-ACCESS read-only
	STATUS current
	DESCRIPTION "Made established"

	::={connectionEstablished 3}

connectionUpdates	OBJECT IDENTIFIER ::={connection 12}

connectionUpdatesVal	OBJECT-TYPE
	SYNTAX	 Counter64
	MAX-ACCESS read-only
	STATUS current
	DESCRIPTION "Updates sent"

	::={connectionUpdates 1}

connectionUpdatesMom	OBJECT-TYPE
	SYNTAX	 Unsigned32
	MAX-ACCESS read-only
	STATUS current
	DESCRIPTION "Updates sent"

	::={connectionUpdates 2}

connectionUpdatesMax	OBJECT-TYPE
	SYNTAX	 Counter64
	MAX-ACCESS read-only
	STATUS current
	DESCRIPTION "Updates sent"

	::={connectionUpdates 3}

connectionTtlTimeouts	OBJECT IDENTIFIER ::={connection 13}

connectionTtlTimeoutsVal	OBJECT-TYPE
	SYNTAX	 Counter64
	MAX-ACCESS read-only
	STATUS current
	DESCRIPTION "TTL timeouts"

	::={connectionTtlTimeouts 1}

connectionTtlTimeoutsMom	OBJECT-TYPE
	SYNTAX	 Unsigned32
	MAX-ACCESS read-only
	STATUS current
	DESCRIPTION "TTL timeouts"

	::={connectionTtlTimeouts 2}

connectionTtlTimeoutsMax	OBJECT-TYPE
	SYNTAX	 Counter64
	MAX-ACCESS read-only
	STATUS current
	DESCRIPTION "TTL timeouts"

	::={connectionTtlTimeouts 3}

connectionProtEnables	OBJECT IDENTIFIER ::={connection 14}

connectionProtEnablesVal	OBJECT-TYPE
	SYNTAX	 Counter64
	MAX-ACCESS read-only
	STATUS current
	DESCRIPTION "Protection enabled"

	::={connectionProtEnables 1}

connectionProtEnablesMom	OBJECT-TYPE
	SYNTAX	 Unsigned32
	MAX-ACCESS read-only
	STATUS current
	DESCRIPTION "Protection enabled"

	::={connectionProtEnables 2}

connectionProtEnablesMax	OBJECT-TYPE
	SYNTAX	 Counter64
	MAX-ACCESS read-only
	STATUS current
	DESCRIPTION "Protection enabled"

	::={connectionProtEnables 3}

connectionNotFound	OBJECT IDENTIFIER ::={connection 15}

connectionNotFoundVal	OBJECT-TYPE
	SYNTAX	 Counter64
	MAX-ACCESS read-only
	STATUS current
	DESCRIPTION "Failed lookups"

	::={connectionNotFound 1}

connectionNotFoundMom	OBJECT-TYPE
	SYNTAX	 Unsigned32
	MAX-ACCESS read-only
	STATUS current
	DESCRIPTION "Failed lookups"

	::={connectionNotFound 2}

connectionNotFoundMax	OBJECT-TYPE
	SYNTAX	 Counter64
	MAX-ACCESS read-only
	STATUS current
	DESCRIPTION "Failed lookups"

	::={connectionNotFound 3}

connectionRuntimeFind	OBJECT IDENTIFIER ::={connection 16}

connectionRuntimeFindVal	OBJECT-TYPE
	SYNTAX	 Unsigned32
	MAX-ACCESS read-only
	STATUS current
	DESCRIPTION "Average cycles per packet (find)"

	::={connectionRuntimeFind 1}

connectionRuntimeFindMax	OBJECT-TYPE
	SYNTAX	 Unsigned32
	MAX-ACCESS read-only
	STATUS current
	DESCRIPTION "Average cycles per packet (find)"

	::={connectionRuntimeFind 3}

connectionRuntimeNew	OBJECT IDENTIFIER ::={connection 17}

connectionRuntimeNewVal	OBJECT-TYPE
	SYNTAX	 Unsigned32
	MAX-ACCESS read-only
	STATUS current
	DESCRIPTION "Average cycles per packet (new)"

	::={connectionRuntimeNew 1}

connectionRuntimeNewMax	OBJECT-TYPE
	SYNTAX	 Unsigned32
	MAX-ACCESS read-only
	STATUS current
	DESCRIPTION "Average cycles per packet (new)"

	::={connectionRuntimeNew 3}

connectionRefusedExisting	OBJECT IDENTIFIER ::={connection 18}

connectionRefusedExistingVal	OBJECT-TYPE
	SYNTAX	 Counter64
	MAX-ACCESS read-only
	STATUS current
	DESCRIPTION "Attempts refused (already existed)"

	::={connectionRefusedExisting 1}

connectionRefusedExistingMom	OBJECT-TYPE
	SYNTAX	 Unsigned32
	MAX-ACCESS read-only
	STATUS current
	DESCRIPTION "Attempts refused (already existed)"

	::={connectionRefusedExisting 2}

connectionRefusedExistingMax	OBJECT-TYPE
	SYNTAX	 Counter64
	MAX-ACCESS read-only
	STATUS current
	DESCRIPTION "Attempts refused (already existed)"

	::={connectionRefusedExisting 3}

connectionRefusedRuleset	OBJECT IDENTIFIER ::={connection 19}

connectionRefusedRulesetVal	OBJECT-TYPE
	SYNTAX	 Counter64
	MAX-ACCESS read-only
	STATUS current
	DESCRIPTION "Attempts refused (ruleset)"

	::={connectionRefusedRuleset 1}

connectionRefusedRulesetMom	OBJECT-TYPE
	SYNTAX	 Unsigned32
	MAX-ACCESS read-only
	STATUS current
	DESCRIPTION "Attempts refused (ruleset)"

	::={connectionRefusedRuleset 2}

connectionRefusedRulesetMax	OBJECT-TYPE
	SYNTAX	 Counter64
	MAX-ACCESS read-only
	STATUS current
	DESCRIPTION "Attempts refused (ruleset)"

	::={connectionRefusedRuleset 3}

connectionRedirected	OBJECT IDENTIFIER ::={connection 20}

connectionRedirectedVal	OBJECT-TYPE
	SYNTAX	 Unsigned32
	MAX-ACCESS read-only
	STATUS current
	DESCRIPTION "Redirected"

	::={connectionRedirected 1}

connectionRedirectedMax	OBJECT-TYPE
	SYNTAX	 Unsigned32
	MAX-ACCESS read-only
	STATUS current
	DESCRIPTION "Redirected"

	::={connectionRedirected 3}

connectionRedirectCollisions	OBJECT IDENTIFIER ::={connection 21}

connectionRedirectCollisionsVal	OBJECT-TYPE
	SYNTAX	 Unsigned32
	MAX-ACCESS read-only
	STATUS current
	DESCRIPTION "Refused redirects (collision)"

	::={connectionRedirectCollisions 1}

connectionRedirectCollisionsMax	OBJECT-TYPE
	SYNTAX	 Unsigned32
	MAX-ACCESS read-only
	STATUS current
	DESCRIPTION "Refused redirects (collision)"

	::={connectionRedirectCollisions 3}

connectionFindHeavy	OBJECT IDENTIFIER ::={connection 22}

connectionFindHeavyVal	OBJECT-TYPE
	SYNTAX	 Counter64
	MAX-ACCESS read-only
	STATUS current
	DESCRIPTION "Heavy find packets"

	::={connectionFindHeavy 1}

connectionFindHeavyMom	OBJECT-TYPE
	SYNTAX	 Unsigned32
	MAX-ACCESS read-only
	STATUS current
	DESCRIPTION "Heavy find packets"

	::={connectionFindHeavy 2}

connectionFindHeavyMax	OBJECT-TYPE
	SYNTAX	 Counter64
	MAX-ACCESS read-only
	STATUS current
	DESCRIPTION "Heavy find packets"

	::={connectionFindHeavy 3}

connectionNewHeavy	OBJECT IDENTIFIER ::={connection 23}

connectionNewHeavyVal	OBJECT-TYPE
	SYNTAX	 Counter64
	MAX-ACCESS read-only
	STATUS current
	DESCRIPTION "Heavy new packets"

	::={connectionNewHeavy 1}

connectionNewHeavyMom	OBJECT-TYPE
	SYNTAX	 Unsigned32
	MAX-ACCESS read-only
	STATUS current
	DESCRIPTION "Heavy new packets"

	::={connectionNewHeavy 2}

connectionNewHeavyMax	OBJECT-TYPE
	SYNTAX	 Counter64
	MAX-ACCESS read-only
	STATUS current
	DESCRIPTION "Heavy new packets"

	::={connectionNewHeavy 3}

connectionUnestablished	OBJECT IDENTIFIER ::={connection 24}

connectionUnestablishedVal	OBJECT-TYPE
	SYNTAX	 Counter64
	MAX-ACCESS read-only
	STATUS current
	DESCRIPTION "Made unestablished"

	::={connectionUnestablished 1}

connectionUnestablishedMom	OBJECT-TYPE
	SYNTAX	 Unsigned32
	MAX-ACCESS read-only
	STATUS current
	DESCRIPTION "Made unestablished"

	::={connectionUnestablished 2}

connectionUnestablishedMax	OBJECT-TYPE
	SYNTAX	 Counter64
	MAX-ACCESS read-only
	STATUS current
	DESCRIPTION "Made unestablished"

	::={connectionUnestablished 3}

connectionDestroyedEst	OBJECT IDENTIFIER ::={connection 25}

connectionDestroyedEstVal	OBJECT-TYPE
	SYNTAX	 Unsigned32
	MAX-ACCESS read-only
	STATUS current
	DESCRIPTION "Destroyed established"

	::={connectionDestroyedEst 1}

connectionDestroyedEstMax	OBJECT-TYPE
	SYNTAX	 Unsigned32
	MAX-ACCESS read-only
	STATUS current
	DESCRIPTION "Destroyed established"

	::={connectionDestroyedEst 3}

connectionInvalidRulesetUpdate	OBJECT IDENTIFIER ::={connection 26}

connectionInvalidRulesetUpdateVal	OBJECT-TYPE
	SYNTAX	 Counter64
	MAX-ACCESS read-only
	STATUS current
	DESCRIPTION "Updates with invalid ruleset"

	::={connectionInvalidRulesetUpdate 1}

connectionInvalidRulesetUpdateMom	OBJECT-TYPE
	SYNTAX	 Unsigned32
	MAX-ACCESS read-only
	STATUS current
	DESCRIPTION "Updates with invalid ruleset"

	::={connectionInvalidRulesetUpdate 2}

connectionInvalidRulesetUpdateMax	OBJECT-TYPE
	SYNTAX	 Counter64
	MAX-ACCESS read-only
	STATUS current
	DESCRIPTION "Updates with invalid ruleset"

	::={connectionInvalidRulesetUpdate 3}

connectionOrphaned	OBJECT IDENTIFIER ::={connection 27}

connectionOrphanedVal	OBJECT-TYPE
	SYNTAX	 Unsigned32
	MAX-ACCESS read-only
	STATUS current
	DESCRIPTION "Connections without timer"

	::={connectionOrphaned 1}

connectionOrphanedMax	OBJECT-TYPE
	SYNTAX	 Unsigned32
	MAX-ACCESS read-only
	STATUS current
	DESCRIPTION "Connections without timer"

	::={connectionOrphaned 3}

connectionFailureShuntPackets	OBJECT IDENTIFIER ::={connection 40}

connectionFailureShuntPacketsVal	OBJECT-TYPE
	SYNTAX	 Counter64
	MAX-ACCESS read-only
	STATUS current
	DESCRIPTION "Shunted packets (connection create failure)"

	::={connectionFailureShuntPackets 1}

connectionFailureShuntPacketsMom	OBJECT-TYPE
	SYNTAX	 Unsigned32
	MAX-ACCESS read-only
	STATUS current
	DESCRIPTION "Shunted packets (connection create failure)"

	::={connectionFailureShuntPackets 2}

connectionFailureShuntPacketsMax	OBJECT-TYPE
	SYNTAX	 Counter64
	MAX-ACCESS read-only
	STATUS current
	DESCRIPTION "Shunted packets (connection create failure)"

	::={connectionFailureShuntPackets 3}

connectionFailureShuntBytes	OBJECT IDENTIFIER ::={connection 41}

connectionFailureShuntBytesVal	OBJECT-TYPE
	SYNTAX	 Counter64
	MAX-ACCESS read-only
	STATUS current
	DESCRIPTION "Shunted bytes (connection create failure)"

	::={connectionFailureShuntBytes 1}

connectionFailureShuntBytesMom	OBJECT-TYPE
	SYNTAX	 Unsigned32
	MAX-ACCESS read-only
	STATUS current
	DESCRIPTION "Shunted bytes (connection create failure)"

	::={connectionFailureShuntBytes 2}

connectionFailureShuntBytesMax	OBJECT-TYPE
	SYNTAX	 Counter64
	MAX-ACCESS read-only
	STATUS current
	DESCRIPTION "Shunted bytes (connection create failure)"

	::={connectionFailureShuntBytes 3}

connsync	OBJECT IDENTIFIER ::={sysdiag 60}

connsyncSeenSnt	OBJECT IDENTIFIER ::={connsync 1}

connsyncSeenSntVal	OBJECT-TYPE
	SYNTAX	 Counter64
	MAX-ACCESS read-only
	STATUS current
	DESCRIPTION "Seen sent"

	::={connsyncSeenSnt 1}

connsyncSeenSntMom	OBJECT-TYPE
	SYNTAX	 Unsigned32
	MAX-ACCESS read-only
	STATUS current
	DESCRIPTION "Seen sent"

	::={connsyncSeenSnt 2}

connsyncSeenSntMax	OBJECT-TYPE
	SYNTAX	 Counter64
	MAX-ACCESS read-only
	STATUS current
	DESCRIPTION "Seen sent"

	::={connsyncSeenSnt 3}

connsyncSeenRcv	OBJECT IDENTIFIER ::={connsync 2}

connsyncSeenRcvVal	OBJECT-TYPE
	SYNTAX	 Counter64
	MAX-ACCESS read-only
	STATUS current
	DESCRIPTION "Seen received"

	::={connsyncSeenRcv 1}

connsyncSeenRcvMom	OBJECT-TYPE
	SYNTAX	 Unsigned32
	MAX-ACCESS read-only
	STATUS current
	DESCRIPTION "Seen received"

	::={connsyncSeenRcv 2}

connsyncSeenRcvMax	OBJECT-TYPE
	SYNTAX	 Counter64
	MAX-ACCESS read-only
	STATUS current
	DESCRIPTION "Seen received"

	::={connsyncSeenRcv 3}

connsyncUpdateSnt	OBJECT IDENTIFIER ::={connsync 3}

connsyncUpdateSntVal	OBJECT-TYPE
	SYNTAX	 Counter64
	MAX-ACCESS read-only
	STATUS current
	DESCRIPTION "Updates Sent"

	::={connsyncUpdateSnt 1}

connsyncUpdateSntMom	OBJECT-TYPE
	SYNTAX	 Unsigned32
	MAX-ACCESS read-only
	STATUS current
	DESCRIPTION "Updates Sent"

	::={connsyncUpdateSnt 2}

connsyncUpdateSntMax	OBJECT-TYPE
	SYNTAX	 Counter64
	MAX-ACCESS read-only
	STATUS current
	DESCRIPTION "Updates Sent"

	::={connsyncUpdateSnt 3}

connsyncSeenackRcv	OBJECT IDENTIFIER ::={connsync 4}

connsyncSeenackRcvVal	OBJECT-TYPE
	SYNTAX	 Counter64
	MAX-ACCESS read-only
	STATUS current
	DESCRIPTION "First updates received"

	::={connsyncSeenackRcv 1}

connsyncSeenackRcvMom	OBJECT-TYPE
	SYNTAX	 Unsigned32
	MAX-ACCESS read-only
	STATUS current
	DESCRIPTION "First updates received"

	::={connsyncSeenackRcv 2}

connsyncSeenackRcvMax	OBJECT-TYPE
	SYNTAX	 Counter64
	MAX-ACCESS read-only
	STATUS current
	DESCRIPTION "First updates received"

	::={connsyncSeenackRcv 3}

connsyncUpdateRcv	OBJECT IDENTIFIER ::={connsync 5}

connsyncUpdateRcvVal	OBJECT-TYPE
	SYNTAX	 Counter64
	MAX-ACCESS read-only
	STATUS current
	DESCRIPTION "Updates received"

	::={connsyncUpdateRcv 1}

connsyncUpdateRcvMom	OBJECT-TYPE
	SYNTAX	 Unsigned32
	MAX-ACCESS read-only
	STATUS current
	DESCRIPTION "Updates received"

	::={connsyncUpdateRcv 2}

connsyncUpdateRcvMax	OBJECT-TYPE
	SYNTAX	 Counter64
	MAX-ACCESS read-only
	STATUS current
	DESCRIPTION "Updates received"

	::={connsyncUpdateRcv 3}

connsyncUnknownUpdateRcv	OBJECT IDENTIFIER ::={connsync 6}

connsyncUnknownUpdateRcvVal	OBJECT-TYPE
	SYNTAX	 Counter64
	MAX-ACCESS read-only
	STATUS current
	DESCRIPTION "Updates for unknown connections received"

	::={connsyncUnknownUpdateRcv 1}

connsyncUnknownUpdateRcvMom	OBJECT-TYPE
	SYNTAX	 Unsigned32
	MAX-ACCESS read-only
	STATUS current
	DESCRIPTION "Updates for unknown connections received"

	::={connsyncUnknownUpdateRcv 2}

connsyncUnknownUpdateRcvMax	OBJECT-TYPE
	SYNTAX	 Counter64
	MAX-ACCESS read-only
	STATUS current
	DESCRIPTION "Updates for unknown connections received"

	::={connsyncUnknownUpdateRcv 3}

connsyncOutofsync	OBJECT IDENTIFIER ::={connsync 7}

connsyncOutofsyncVal	OBJECT-TYPE
	SYNTAX	 Counter64
	MAX-ACCESS read-only
	STATUS current
	DESCRIPTION "Out of syncs"

	::={connsyncOutofsync 1}

connsyncOutofsyncMom	OBJECT-TYPE
	SYNTAX	 Unsigned32
	MAX-ACCESS read-only
	STATUS current
	DESCRIPTION "Out of syncs"

	::={connsyncOutofsync 2}

connsyncOutofsyncMax	OBJECT-TYPE
	SYNTAX	 Counter64
	MAX-ACCESS read-only
	STATUS current
	DESCRIPTION "Out of syncs"

	::={connsyncOutofsync 3}

connsyncSynced	OBJECT IDENTIFIER ::={connsync 8}

connsyncSyncedVal	OBJECT-TYPE
	SYNTAX	 Unsigned32
	MAX-ACCESS read-only
	STATUS current
	DESCRIPTION "Connections actively syncing"

	::={connsyncSynced 1}

connsyncSyncedMax	OBJECT-TYPE
	SYNTAX	 Unsigned32
	MAX-ACCESS read-only
	STATUS current
	DESCRIPTION "Connections actively syncing"

	::={connsyncSynced 3}

connsyncDoubleSeen	OBJECT IDENTIFIER ::={connsync 9}

connsyncDoubleSeenVal	OBJECT-TYPE
	SYNTAX	 Counter64
	MAX-ACCESS read-only
	STATUS current
	DESCRIPTION "Double seen"

	::={connsyncDoubleSeen 1}

connsyncDoubleSeenMom	OBJECT-TYPE
	SYNTAX	 Unsigned32
	MAX-ACCESS read-only
	STATUS current
	DESCRIPTION "Double seen"

	::={connsyncDoubleSeen 2}

connsyncDoubleSeenMax	OBJECT-TYPE
	SYNTAX	 Counter64
	MAX-ACCESS read-only
	STATUS current
	DESCRIPTION "Double seen"

	::={connsyncDoubleSeen 3}

connsyncHelloRcv	OBJECT IDENTIFIER ::={connsync 10}

connsyncHelloRcvVal	OBJECT-TYPE
	SYNTAX	 Counter64
	MAX-ACCESS read-only
	STATUS current
	DESCRIPTION "Hello received"

	::={connsyncHelloRcv 1}

connsyncHelloRcvMom	OBJECT-TYPE
	SYNTAX	 Unsigned32
	MAX-ACCESS read-only
	STATUS current
	DESCRIPTION "Hello received"

	::={connsyncHelloRcv 2}

connsyncHelloRcvMax	OBJECT-TYPE
	SYNTAX	 Counter64
	MAX-ACCESS read-only
	STATUS current
	DESCRIPTION "Hello received"

	::={connsyncHelloRcv 3}

connsyncOutofsyncMissedRcv	OBJECT IDENTIFIER ::={connsync 11}

connsyncOutofsyncMissedRcvVal	OBJECT-TYPE
	SYNTAX	 Counter64
	MAX-ACCESS read-only
	STATUS current
	DESCRIPTION "Out of sync - missed rcv/late collision"

	::={connsyncOutofsyncMissedRcv 1}

connsyncOutofsyncMissedRcvMom	OBJECT-TYPE
	SYNTAX	 Unsigned32
	MAX-ACCESS read-only
	STATUS current
	DESCRIPTION "Out of sync - missed rcv/late collision"

	::={connsyncOutofsyncMissedRcv 2}

connsyncOutofsyncMissedRcvMax	OBJECT-TYPE
	SYNTAX	 Counter64
	MAX-ACCESS read-only
	STATUS current
	DESCRIPTION "Out of sync - missed rcv/late collision"

	::={connsyncOutofsyncMissedRcv 3}

connsyncOutofsyncCollision	OBJECT IDENTIFIER ::={connsync 12}

connsyncOutofsyncCollisionVal	OBJECT-TYPE
	SYNTAX	 Counter64
	MAX-ACCESS read-only
	STATUS current
	DESCRIPTION "Out of sync - collision"

	::={connsyncOutofsyncCollision 1}

connsyncOutofsyncCollisionMom	OBJECT-TYPE
	SYNTAX	 Unsigned32
	MAX-ACCESS read-only
	STATUS current
	DESCRIPTION "Out of sync - collision"

	::={connsyncOutofsyncCollision 2}

connsyncOutofsyncCollisionMax	OBJECT-TYPE
	SYNTAX	 Counter64
	MAX-ACCESS read-only
	STATUS current
	DESCRIPTION "Out of sync - collision"

	::={connsyncOutofsyncCollision 3}

connsyncBadAdler	OBJECT IDENTIFIER ::={connsync 13}

connsyncBadAdlerVal	OBJECT-TYPE
	SYNTAX	 Counter64
	MAX-ACCESS read-only
	STATUS current
	DESCRIPTION "Updates for mismatching ARM"

	::={connsyncBadAdler 1}

connsyncBadAdlerMom	OBJECT-TYPE
	SYNTAX	 Unsigned32
	MAX-ACCESS read-only
	STATUS current
	DESCRIPTION "Updates for mismatching ARM"

	::={connsyncBadAdler 2}

connsyncBadAdlerMax	OBJECT-TYPE
	SYNTAX	 Counter64
	MAX-ACCESS read-only
	STATUS current
	DESCRIPTION "Updates for mismatching ARM"

	::={connsyncBadAdler 3}

connsyncPktOverflow	OBJECT IDENTIFIER ::={connsync 14}

connsyncPktOverflowVal	OBJECT-TYPE
	SYNTAX	 Counter64
	MAX-ACCESS read-only
	STATUS current
	DESCRIPTION "Update packet overflow"

	::={connsyncPktOverflow 1}

connsyncPktOverflowMom	OBJECT-TYPE
	SYNTAX	 Unsigned32
	MAX-ACCESS read-only
	STATUS current
	DESCRIPTION "Update packet overflow"

	::={connsyncPktOverflow 2}

connsyncPktOverflowMax	OBJECT-TYPE
	SYNTAX	 Counter64
	MAX-ACCESS read-only
	STATUS current
	DESCRIPTION "Update packet overflow"

	::={connsyncPktOverflow 3}

connsyncCorruptPkt	OBJECT IDENTIFIER ::={connsync 15}

connsyncCorruptPktVal	OBJECT-TYPE
	SYNTAX	 Counter64
	MAX-ACCESS read-only
	STATUS current
	DESCRIPTION "Corrupt packet received"

	::={connsyncCorruptPkt 1}

connsyncCorruptPktMom	OBJECT-TYPE
	SYNTAX	 Unsigned32
	MAX-ACCESS read-only
	STATUS current
	DESCRIPTION "Corrupt packet received"

	::={connsyncCorruptPkt 2}

connsyncCorruptPktMax	OBJECT-TYPE
	SYNTAX	 Counter64
	MAX-ACCESS read-only
	STATUS current
	DESCRIPTION "Corrupt packet received"

	::={connsyncCorruptPkt 3}

connsyncConnNotfound	OBJECT IDENTIFIER ::={connsync 16}

connsyncConnNotfoundVal	OBJECT-TYPE
	SYNTAX	 Counter64
	MAX-ACCESS read-only
	STATUS current
	DESCRIPTION "Connection not found"

	::={connsyncConnNotfound 1}

connsyncConnNotfoundMom	OBJECT-TYPE
	SYNTAX	 Unsigned32
	MAX-ACCESS read-only
	STATUS current
	DESCRIPTION "Connection not found"

	::={connsyncConnNotfound 2}

connsyncConnNotfoundMax	OBJECT-TYPE
	SYNTAX	 Counter64
	MAX-ACCESS read-only
	STATUS current
	DESCRIPTION "Connection not found"

	::={connsyncConnNotfound 3}

connsyncBadVer	OBJECT IDENTIFIER ::={connsync 17}

connsyncBadVerVal	OBJECT-TYPE
	SYNTAX	 Counter64
	MAX-ACCESS read-only
	STATUS current
	DESCRIPTION "Received packets with incompatible version"

	::={connsyncBadVer 1}

connsyncBadVerMom	OBJECT-TYPE
	SYNTAX	 Unsigned32
	MAX-ACCESS read-only
	STATUS current
	DESCRIPTION "Received packets with incompatible version"

	::={connsyncBadVer 2}

connsyncBadVerMax	OBJECT-TYPE
	SYNTAX	 Counter64
	MAX-ACCESS read-only
	STATUS current
	DESCRIPTION "Received packets with incompatible version"

	::={connsyncBadVer 3}

connsyncBadType	OBJECT IDENTIFIER ::={connsync 18}

connsyncBadTypeVal	OBJECT-TYPE
	SYNTAX	 Counter64
	MAX-ACCESS read-only
	STATUS current
	DESCRIPTION "Received packets with incorrect ethernet type"

	::={connsyncBadType 1}

connsyncBadTypeMom	OBJECT-TYPE
	SYNTAX	 Unsigned32
	MAX-ACCESS read-only
	STATUS current
	DESCRIPTION "Received packets with incorrect ethernet type"

	::={connsyncBadType 2}

connsyncBadTypeMax	OBJECT-TYPE
	SYNTAX	 Counter64
	MAX-ACCESS read-only
	STATUS current
	DESCRIPTION "Received packets with incorrect ethernet type"

	::={connsyncBadType 3}

connsyncBadEngineid	OBJECT IDENTIFIER ::={connsync 19}

connsyncBadEngineidVal	OBJECT-TYPE
	SYNTAX	 Counter64
	MAX-ACCESS read-only
	STATUS current
	DESCRIPTION "Received packets with own engine-id"

	::={connsyncBadEngineid 1}

connsyncBadEngineidMom	OBJECT-TYPE
	SYNTAX	 Unsigned32
	MAX-ACCESS read-only
	STATUS current
	DESCRIPTION "Received packets with own engine-id"

	::={connsyncBadEngineid 2}

connsyncBadEngineidMax	OBJECT-TYPE
	SYNTAX	 Counter64
	MAX-ACCESS read-only
	STATUS current
	DESCRIPTION "Received packets with own engine-id"

	::={connsyncBadEngineid 3}

ruleset	OBJECT IDENTIFIER ::={sysdiag 64}

rulesetReceived	OBJECT IDENTIFIER ::={ruleset 1}

rulesetReceivedVal	OBJECT-TYPE
	SYNTAX	 Counter64
	MAX-ACCESS read-only
	STATUS current
	DESCRIPTION "RX packets"

	::={rulesetReceived 1}

rulesetReceivedMom	OBJECT-TYPE
	SYNTAX	 Unsigned32
	MAX-ACCESS read-only
	STATUS current
	DESCRIPTION "RX packets"

	::={rulesetReceived 2}

rulesetReceivedMax	OBJECT-TYPE
	SYNTAX	 Counter64
	MAX-ACCESS read-only
	STATUS current
	DESCRIPTION "RX packets"

	::={rulesetReceived 3}

rulesetForwarded	OBJECT IDENTIFIER ::={ruleset 2}

rulesetForwardedVal	OBJECT-TYPE
	SYNTAX	 Counter64
	MAX-ACCESS read-only
	STATUS current
	DESCRIPTION "TX packets"

	::={rulesetForwarded 1}

rulesetForwardedMom	OBJECT-TYPE
	SYNTAX	 Unsigned32
	MAX-ACCESS read-only
	STATUS current
	DESCRIPTION "TX packets"

	::={rulesetForwarded 2}

rulesetForwardedMax	OBJECT-TYPE
	SYNTAX	 Counter64
	MAX-ACCESS read-only
	STATUS current
	DESCRIPTION "TX packets"

	::={rulesetForwarded 3}

rulesetRuntime	OBJECT IDENTIFIER ::={ruleset 3}

rulesetRuntimeVal	OBJECT-TYPE
	SYNTAX	 Unsigned32
	MAX-ACCESS read-only
	STATUS current
	DESCRIPTION "Average cycles per packet"

	::={rulesetRuntime 1}

rulesetRuntimeMax	OBJECT-TYPE
	SYNTAX	 Unsigned32
	MAX-ACCESS read-only
	STATUS current
	DESCRIPTION "Average cycles per packet"

	::={rulesetRuntime 3}

rulesetRuntimeRecalc	OBJECT IDENTIFIER ::={ruleset 4}

rulesetRuntimeRecalcVal	OBJECT-TYPE
	SYNTAX	 Unsigned32
	MAX-ACCESS read-only
	STATUS current
	DESCRIPTION "Average cycles per packet (recalc)"

	::={rulesetRuntimeRecalc 1}

rulesetRuntimeRecalcMax	OBJECT-TYPE
	SYNTAX	 Unsigned32
	MAX-ACCESS read-only
	STATUS current
	DESCRIPTION "Average cycles per packet (recalc)"

	::={rulesetRuntimeRecalc 3}

rulesetFwrules	OBJECT IDENTIFIER ::={ruleset 5}

rulesetFwrulesVal	OBJECT-TYPE
	SYNTAX	 Unsigned32
	MAX-ACCESS read-only
	STATUS current
	DESCRIPTION "FW rules loaded"

	::={rulesetFwrules 1}

rulesetFwrulesMax	OBJECT-TYPE
	SYNTAX	 Unsigned32
	MAX-ACCESS read-only
	STATUS current
	DESCRIPTION "FW rules loaded"

	::={rulesetFwrules 3}

rulesetShapingrules	OBJECT IDENTIFIER ::={ruleset 6}

rulesetShapingrulesVal	OBJECT-TYPE
	SYNTAX	 Unsigned32
	MAX-ACCESS read-only
	STATUS current
	DESCRIPTION "Shaping rules loaded"

	::={rulesetShapingrules 1}

rulesetShapingrulesMax	OBJECT-TYPE
	SYNTAX	 Unsigned32
	MAX-ACCESS read-only
	STATUS current
	DESCRIPTION "Shaping rules loaded"

	::={rulesetShapingrules 3}

rulesetClienttreeSize	OBJECT IDENTIFIER ::={ruleset 7}

rulesetClienttreeSizeVal	OBJECT-TYPE
	SYNTAX	 Unsigned32
	MAX-ACCESS read-only
	STATUS current
	DESCRIPTION "Nodes in Client IP-tree"

	::={rulesetClienttreeSize 1}

rulesetClienttreeSizeMax	OBJECT-TYPE
	SYNTAX	 Unsigned32
	MAX-ACCESS read-only
	STATUS current
	DESCRIPTION "Nodes in Client IP-tree"

	::={rulesetClienttreeSize 3}

rulesetServertreeSize	OBJECT IDENTIFIER ::={ruleset 8}

rulesetServertreeSizeVal	OBJECT-TYPE
	SYNTAX	 Unsigned32
	MAX-ACCESS read-only
	STATUS current
	DESCRIPTION "Nodes in Server IP-tree"

	::={rulesetServertreeSize 1}

rulesetServertreeSizeMax	OBJECT-TYPE
	SYNTAX	 Unsigned32
	MAX-ACCESS read-only
	STATUS current
	DESCRIPTION "Nodes in Server IP-tree"

	::={rulesetServertreeSize 3}

rulesetBgpNumpaths	OBJECT IDENTIFIER ::={ruleset 9}

rulesetBgpNumpathsVal	OBJECT-TYPE
	SYNTAX	 Unsigned32
	MAX-ACCESS read-only
	STATUS current
	DESCRIPTION "Number of ASPaths"

	::={rulesetBgpNumpaths 1}

rulesetBgpNumpathsMax	OBJECT-TYPE
	SYNTAX	 Unsigned32
	MAX-ACCESS read-only
	STATUS current
	DESCRIPTION "Number of ASPaths"

	::={rulesetBgpNumpaths 3}

rulesetBgpTreesize	OBJECT IDENTIFIER ::={ruleset 10}

rulesetBgpTreesizeVal	OBJECT-TYPE
	SYNTAX	 Unsigned32
	MAX-ACCESS read-only
	STATUS current
	DESCRIPTION "Nodes in BGP-tree"

	::={rulesetBgpTreesize 1}

rulesetBgpTreesizeMax	OBJECT-TYPE
	SYNTAX	 Unsigned32
	MAX-ACCESS read-only
	STATUS current
	DESCRIPTION "Nodes in BGP-tree"

	::={rulesetBgpTreesize 3}

rulesetBgpRuntimeLookup	OBJECT IDENTIFIER ::={ruleset 11}

rulesetBgpRuntimeLookupVal	OBJECT-TYPE
	SYNTAX	 Unsigned32
	MAX-ACCESS read-only
	STATUS current
	DESCRIPTION "Average cycles per ASPath lookup"

	::={rulesetBgpRuntimeLookup 1}

rulesetBgpRuntimeLookupMax	OBJECT-TYPE
	SYNTAX	 Unsigned32
	MAX-ACCESS read-only
	STATUS current
	DESCRIPTION "Average cycles per ASPath lookup"

	::={rulesetBgpRuntimeLookup 3}

rulesetBgpNumLookup	OBJECT IDENTIFIER ::={ruleset 12}

rulesetBgpNumLookupVal	OBJECT-TYPE
	SYNTAX	 Counter64
	MAX-ACCESS read-only
	STATUS current
	DESCRIPTION "BGP path lookups"

	::={rulesetBgpNumLookup 1}

rulesetBgpNumLookupMom	OBJECT-TYPE
	SYNTAX	 Unsigned32
	MAX-ACCESS read-only
	STATUS current
	DESCRIPTION "BGP path lookups"

	::={rulesetBgpNumLookup 2}

rulesetBgpNumLookupMax	OBJECT-TYPE
	SYNTAX	 Counter64
	MAX-ACCESS read-only
	STATUS current
	DESCRIPTION "BGP path lookups"

	::={rulesetBgpNumLookup 3}

rulesetPropChecks	OBJECT IDENTIFIER ::={ruleset 13}

rulesetPropChecksVal	OBJECT-TYPE
	SYNTAX	 Counter64
	MAX-ACCESS read-only
	STATUS current
	DESCRIPTION "Property checks"

	::={rulesetPropChecks 1}

rulesetPropChecksMom	OBJECT-TYPE
	SYNTAX	 Unsigned32
	MAX-ACCESS read-only
	STATUS current
	DESCRIPTION "Property checks"

	::={rulesetPropChecks 2}

rulesetPropChecksMax	OBJECT-TYPE
	SYNTAX	 Counter64
	MAX-ACCESS read-only
	STATUS current
	DESCRIPTION "Property checks"

	::={rulesetPropChecks 3}

rulesetRuntimeProp	OBJECT IDENTIFIER ::={ruleset 14}

rulesetRuntimePropVal	OBJECT-TYPE
	SYNTAX	 Unsigned32
	MAX-ACCESS read-only
	STATUS current
	DESCRIPTION "Average cycles per property check"

	::={rulesetRuntimeProp 1}

rulesetRuntimePropMax	OBJECT-TYPE
	SYNTAX	 Unsigned32
	MAX-ACCESS read-only
	STATUS current
	DESCRIPTION "Average cycles per property check"

	::={rulesetRuntimeProp 3}

rulesetBitmasksAvg	OBJECT IDENTIFIER ::={ruleset 15}

rulesetBitmasksAvgVal	OBJECT-TYPE
	SYNTAX	 Unsigned32
	MAX-ACCESS read-only
	STATUS current
	DESCRIPTION "Bitmask average number of words"

	::={rulesetBitmasksAvg 1}

rulesetBitmasksAvgMax	OBJECT-TYPE
	SYNTAX	 Unsigned32
	MAX-ACCESS read-only
	STATUS current
	DESCRIPTION "Bitmask average number of words"

	::={rulesetBitmasksAvg 3}

rulesetBitmasksMax	OBJECT IDENTIFIER ::={ruleset 16}

rulesetBitmasksMaxVal	OBJECT-TYPE
	SYNTAX	 Unsigned32
	MAX-ACCESS read-only
	STATUS current
	DESCRIPTION "Bitmask max number of words"

	::={rulesetBitmasksMax 1}

rulesetBitmasksMaxMax	OBJECT-TYPE
	SYNTAX	 Unsigned32
	MAX-ACCESS read-only
	STATUS current
	DESCRIPTION "Bitmask max number of words"

	::={rulesetBitmasksMax 3}

rulesetDynipAdd	OBJECT IDENTIFIER ::={ruleset 17}

rulesetDynipAddVal	OBJECT-TYPE
	SYNTAX	 Counter64
	MAX-ACCESS read-only
	STATUS current
	DESCRIPTION "Dynamic ips added"

	::={rulesetDynipAdd 1}

rulesetDynipAddMom	OBJECT-TYPE
	SYNTAX	 Unsigned32
	MAX-ACCESS read-only
	STATUS current
	DESCRIPTION "Dynamic ips added"

	::={rulesetDynipAdd 2}

rulesetDynipAddMax	OBJECT-TYPE
	SYNTAX	 Counter64
	MAX-ACCESS read-only
	STATUS current
	DESCRIPTION "Dynamic ips added"

	::={rulesetDynipAdd 3}

rulesetDynipRemove	OBJECT IDENTIFIER ::={ruleset 18}

rulesetDynipRemoveVal	OBJECT-TYPE
	SYNTAX	 Counter64
	MAX-ACCESS read-only
	STATUS current
	DESCRIPTION "Dynamic ips removed"

	::={rulesetDynipRemove 1}

rulesetDynipRemoveMom	OBJECT-TYPE
	SYNTAX	 Unsigned32
	MAX-ACCESS read-only
	STATUS current
	DESCRIPTION "Dynamic ips removed"

	::={rulesetDynipRemove 2}

rulesetDynipRemoveMax	OBJECT-TYPE
	SYNTAX	 Counter64
	MAX-ACCESS read-only
	STATUS current
	DESCRIPTION "Dynamic ips removed"

	::={rulesetDynipRemove 3}

rulesetRecalcHeavy	OBJECT IDENTIFIER ::={ruleset 19}

rulesetRecalcHeavyVal	OBJECT-TYPE
	SYNTAX	 Counter64
	MAX-ACCESS read-only
	STATUS current
	DESCRIPTION "Heavy recalc packets"

	::={rulesetRecalcHeavy 1}

rulesetRecalcHeavyMom	OBJECT-TYPE
	SYNTAX	 Unsigned32
	MAX-ACCESS read-only
	STATUS current
	DESCRIPTION "Heavy recalc packets"

	::={rulesetRecalcHeavy 2}

rulesetRecalcHeavyMax	OBJECT-TYPE
	SYNTAX	 Counter64
	MAX-ACCESS read-only
	STATUS current
	DESCRIPTION "Heavy recalc packets"

	::={rulesetRecalcHeavy 3}

rulesetHeavy	OBJECT IDENTIFIER ::={ruleset 20}

rulesetHeavyVal	OBJECT-TYPE
	SYNTAX	 Counter64
	MAX-ACCESS read-only
	STATUS current
	DESCRIPTION "Heavy check packets"

	::={rulesetHeavy 1}

rulesetHeavyMom	OBJECT-TYPE
	SYNTAX	 Unsigned32
	MAX-ACCESS read-only
	STATUS current
	DESCRIPTION "Heavy check packets"

	::={rulesetHeavy 2}

rulesetHeavyMax	OBJECT-TYPE
	SYNTAX	 Counter64
	MAX-ACCESS read-only
	STATUS current
	DESCRIPTION "Heavy check packets"

	::={rulesetHeavy 3}

rulesetPropHeavy	OBJECT IDENTIFIER ::={ruleset 21}

rulesetPropHeavyVal	OBJECT-TYPE
	SYNTAX	 Counter64
	MAX-ACCESS read-only
	STATUS current
	DESCRIPTION "Heavy property checks"

	::={rulesetPropHeavy 1}

rulesetPropHeavyMom	OBJECT-TYPE
	SYNTAX	 Unsigned32
	MAX-ACCESS read-only
	STATUS current
	DESCRIPTION "Heavy property checks"

	::={rulesetPropHeavy 2}

rulesetPropHeavyMax	OBJECT-TYPE
	SYNTAX	 Counter64
	MAX-ACCESS read-only
	STATUS current
	DESCRIPTION "Heavy property checks"

	::={rulesetPropHeavy 3}

rulesetLastUpdate	OBJECT IDENTIFIER ::={ruleset 22}

rulesetLastUpdateVal	OBJECT-TYPE
	SYNTAX	 TimeTicks
	MAX-ACCESS read-only
	STATUS current
	DESCRIPTION "Last ruleset reload"

	::={rulesetLastUpdate 1}

rulesetDynipNum	OBJECT IDENTIFIER ::={ruleset 23}

rulesetDynipNumVal	OBJECT-TYPE
	SYNTAX	 Unsigned32
	MAX-ACCESS read-only
	STATUS current
	DESCRIPTION "Dynamic ips current"

	::={rulesetDynipNum 1}

rulesetDynipNumMax	OBJECT-TYPE
	SYNTAX	 Unsigned32
	MAX-ACCESS read-only
	STATUS current
	DESCRIPTION "Dynamic ips current"

	::={rulesetDynipNum 3}

rulesetStatisticsrules	OBJECT IDENTIFIER ::={ruleset 24}

rulesetStatisticsrulesVal	OBJECT-TYPE
	SYNTAX	 Unsigned32
	MAX-ACCESS read-only
	STATUS current
	DESCRIPTION "Statistics rules loaded"

	::={rulesetStatisticsrules 1}

rulesetStatisticsrulesMax	OBJECT-TYPE
	SYNTAX	 Unsigned32
	MAX-ACCESS read-only
	STATUS current
	DESCRIPTION "Statistics rules loaded"

	::={rulesetStatisticsrules 3}

rulesetLocaltreeSize	OBJECT IDENTIFIER ::={ruleset 25}

rulesetLocaltreeSizeVal	OBJECT-TYPE
	SYNTAX	 Unsigned32
	MAX-ACCESS read-only
	STATUS current
	DESCRIPTION "Nodes in Local IP-tree"

	::={rulesetLocaltreeSize 1}

rulesetLocaltreeSizeMax	OBJECT-TYPE
	SYNTAX	 Unsigned32
	MAX-ACCESS read-only
	STATUS current
	DESCRIPTION "Nodes in Local IP-tree"

	::={rulesetLocaltreeSize 3}

rulesetStatisticsRuleOverflow	OBJECT IDENTIFIER ::={ruleset 26}

rulesetStatisticsRuleOverflowVal	OBJECT-TYPE
	SYNTAX	 Counter64
	MAX-ACCESS read-only
	STATUS current
	DESCRIPTION "Too many matching statistics rules"

	::={rulesetStatisticsRuleOverflow 1}

rulesetStatisticsRuleOverflowMom	OBJECT-TYPE
	SYNTAX	 Unsigned32
	MAX-ACCESS read-only
	STATUS current
	DESCRIPTION "Too many matching statistics rules"

	::={rulesetStatisticsRuleOverflow 2}

rulesetStatisticsRuleOverflowMax	OBJECT-TYPE
	SYNTAX	 Counter64
	MAX-ACCESS read-only
	STATUS current
	DESCRIPTION "Too many matching statistics rules"

	::={rulesetStatisticsRuleOverflow 3}

rulesetConnStatechange	OBJECT IDENTIFIER ::={ruleset 27}

rulesetConnStatechangeVal	OBJECT-TYPE
	SYNTAX	 Counter64
	MAX-ACCESS read-only
	STATUS current
	DESCRIPTION "Flow ruleset statechanges"

	::={rulesetConnStatechange 1}

rulesetConnStatechangeMom	OBJECT-TYPE
	SYNTAX	 Unsigned32
	MAX-ACCESS read-only
	STATUS current
	DESCRIPTION "Flow ruleset statechanges"

	::={rulesetConnStatechange 2}

rulesetConnStatechangeMax	OBJECT-TYPE
	SYNTAX	 Counter64
	MAX-ACCESS read-only
	STATUS current
	DESCRIPTION "Flow ruleset statechanges"

	::={rulesetConnStatechange 3}

rulesetConnStatechangeProp	OBJECT IDENTIFIER ::={ruleset 28}

rulesetConnStatechangePropVal	OBJECT-TYPE
	SYNTAX	 Counter64
	MAX-ACCESS read-only
	STATUS current
	DESCRIPTION "Flow ruleset statechanges (prop)"

	::={rulesetConnStatechangeProp 1}

rulesetConnStatechangePropMom	OBJECT-TYPE
	SYNTAX	 Unsigned32
	MAX-ACCESS read-only
	STATUS current
	DESCRIPTION "Flow ruleset statechanges (prop)"

	::={rulesetConnStatechangeProp 2}

rulesetConnStatechangePropMax	OBJECT-TYPE
	SYNTAX	 Counter64
	MAX-ACCESS read-only
	STATUS current
	DESCRIPTION "Flow ruleset statechanges (prop)"

	::={rulesetConnStatechangeProp 3}

rulesetConnStatechangeService	OBJECT IDENTIFIER ::={ruleset 29}

rulesetConnStatechangeServiceVal	OBJECT-TYPE
	SYNTAX	 Counter64
	MAX-ACCESS read-only
	STATUS current
	DESCRIPTION "Flow ruleset statechanges (service)"

	::={rulesetConnStatechangeService 1}

rulesetConnStatechangeServiceMom	OBJECT-TYPE
	SYNTAX	 Unsigned32
	MAX-ACCESS read-only
	STATUS current
	DESCRIPTION "Flow ruleset statechanges (service)"

	::={rulesetConnStatechangeService 2}

rulesetConnStatechangeServiceMax	OBJECT-TYPE
	SYNTAX	 Counter64
	MAX-ACCESS read-only
	STATUS current
	DESCRIPTION "Flow ruleset statechanges (service)"

	::={rulesetConnStatechangeService 3}

rulesetConnStatechangeFlags	OBJECT IDENTIFIER ::={ruleset 30}

rulesetConnStatechangeFlagsVal	OBJECT-TYPE
	SYNTAX	 Counter64
	MAX-ACCESS read-only
	STATUS current
	DESCRIPTION "Flow ruleset statechanges (flags)"

	::={rulesetConnStatechangeFlags 1}

rulesetConnStatechangeFlagsMom	OBJECT-TYPE
	SYNTAX	 Unsigned32
	MAX-ACCESS read-only
	STATUS current
	DESCRIPTION "Flow ruleset statechanges (flags)"

	::={rulesetConnStatechangeFlags 2}

rulesetConnStatechangeFlagsMax	OBJECT-TYPE
	SYNTAX	 Counter64
	MAX-ACCESS read-only
	STATUS current
	DESCRIPTION "Flow ruleset statechanges (flags)"

	::={rulesetConnStatechangeFlags 3}

rulesetConnStatechangeAspath	OBJECT IDENTIFIER ::={ruleset 31}

rulesetConnStatechangeAspathVal	OBJECT-TYPE
	SYNTAX	 Counter64
	MAX-ACCESS read-only
	STATUS current
	DESCRIPTION "Flow ruleset statechanges (aspath)"

	::={rulesetConnStatechangeAspath 1}

rulesetConnStatechangeAspathMom	OBJECT-TYPE
	SYNTAX	 Unsigned32
	MAX-ACCESS read-only
	STATUS current
	DESCRIPTION "Flow ruleset statechanges (aspath)"

	::={rulesetConnStatechangeAspath 2}

rulesetConnStatechangeAspathMax	OBJECT-TYPE
	SYNTAX	 Counter64
	MAX-ACCESS read-only
	STATUS current
	DESCRIPTION "Flow ruleset statechanges (aspath)"

	::={rulesetConnStatechangeAspath 3}

rulesetRecalcVersion	OBJECT IDENTIFIER ::={ruleset 32}

rulesetRecalcVersionVal	OBJECT-TYPE
	SYNTAX	 Counter64
	MAX-ACCESS read-only
	STATUS current
	DESCRIPTION "Flow ruleset recalcs from version"

	::={rulesetRecalcVersion 1}

rulesetRecalcVersionMom	OBJECT-TYPE
	SYNTAX	 Unsigned32
	MAX-ACCESS read-only
	STATUS current
	DESCRIPTION "Flow ruleset recalcs from version"

	::={rulesetRecalcVersion 2}

rulesetRecalcVersionMax	OBJECT-TYPE
	SYNTAX	 Counter64
	MAX-ACCESS read-only
	STATUS current
	DESCRIPTION "Flow ruleset recalcs from version"

	::={rulesetRecalcVersion 3}

rulesetRecalcTime	OBJECT IDENTIFIER ::={ruleset 33}

rulesetRecalcTimeVal	OBJECT-TYPE
	SYNTAX	 Counter64
	MAX-ACCESS read-only
	STATUS current
	DESCRIPTION "Flow ruleset recalcs from time"

	::={rulesetRecalcTime 1}

rulesetRecalcTimeMom	OBJECT-TYPE
	SYNTAX	 Unsigned32
	MAX-ACCESS read-only
	STATUS current
	DESCRIPTION "Flow ruleset recalcs from time"

	::={rulesetRecalcTime 2}

rulesetRecalcTimeMax	OBJECT-TYPE
	SYNTAX	 Counter64
	MAX-ACCESS read-only
	STATUS current
	DESCRIPTION "Flow ruleset recalcs from time"

	::={rulesetRecalcTime 3}

rulesetRecalcBgp	OBJECT IDENTIFIER ::={ruleset 34}

rulesetRecalcBgpVal	OBJECT-TYPE
	SYNTAX	 Counter64
	MAX-ACCESS read-only
	STATUS current
	DESCRIPTION "Flow ruleset recalcs from bgp"

	::={rulesetRecalcBgp 1}

rulesetRecalcBgpMom	OBJECT-TYPE
	SYNTAX	 Unsigned32
	MAX-ACCESS read-only
	STATUS current
	DESCRIPTION "Flow ruleset recalcs from bgp"

	::={rulesetRecalcBgp 2}

rulesetRecalcBgpMax	OBJECT-TYPE
	SYNTAX	 Counter64
	MAX-ACCESS read-only
	STATUS current
	DESCRIPTION "Flow ruleset recalcs from bgp"

	::={rulesetRecalcBgp 3}

rulesetRecalcUnknown	OBJECT IDENTIFIER ::={ruleset 35}

rulesetRecalcUnknownVal	OBJECT-TYPE
	SYNTAX	 Counter64
	MAX-ACCESS read-only
	STATUS current
	DESCRIPTION "Flow ruleset recalcs from state"

	::={rulesetRecalcUnknown 1}

rulesetRecalcUnknownMom	OBJECT-TYPE
	SYNTAX	 Unsigned32
	MAX-ACCESS read-only
	STATUS current
	DESCRIPTION "Flow ruleset recalcs from state"

	::={rulesetRecalcUnknown 2}

rulesetRecalcUnknownMax	OBJECT-TYPE
	SYNTAX	 Counter64
	MAX-ACCESS read-only
	STATUS current
	DESCRIPTION "Flow ruleset recalcs from state"

	::={rulesetRecalcUnknown 3}

rulesetOutdatedService	OBJECT IDENTIFIER ::={ruleset 36}

rulesetOutdatedServiceVal	OBJECT-TYPE
	SYNTAX	 Counter64
	MAX-ACCESS read-only
	STATUS current
	DESCRIPTION "Ruleset recalcs with outdated service ruleset"

	::={rulesetOutdatedService 1}

rulesetOutdatedServiceMom	OBJECT-TYPE
	SYNTAX	 Unsigned32
	MAX-ACCESS read-only
	STATUS current
	DESCRIPTION "Ruleset recalcs with outdated service ruleset"

	::={rulesetOutdatedService 2}

rulesetOutdatedServiceMax	OBJECT-TYPE
	SYNTAX	 Counter64
	MAX-ACCESS read-only
	STATUS current
	DESCRIPTION "Ruleset recalcs with outdated service ruleset"

	::={rulesetOutdatedService 3}

rulesetSubscribers	OBJECT IDENTIFIER ::={ruleset 37}

rulesetSubscribersVal	OBJECT-TYPE
	SYNTAX	 Unsigned32
	MAX-ACCESS read-only
	STATUS current
	DESCRIPTION "Number of added subscribers"

	::={rulesetSubscribers 1}

rulesetSubscribersMax	OBJECT-TYPE
	SYNTAX	 Unsigned32
	MAX-ACCESS read-only
	STATUS current
	DESCRIPTION "Number of added subscribers"

	::={rulesetSubscribers 3}

rulesetBadAspath	OBJECT IDENTIFIER ::={ruleset 38}

rulesetBadAspathVal	OBJECT-TYPE
	SYNTAX	 Counter64
	MAX-ACCESS read-only
	STATUS current
	DESCRIPTION "Old or corrupted AS-path entry"

	::={rulesetBadAspath 1}

rulesetBadAspathMom	OBJECT-TYPE
	SYNTAX	 Unsigned32
	MAX-ACCESS read-only
	STATUS current
	DESCRIPTION "Old or corrupted AS-path entry"

	::={rulesetBadAspath 2}

rulesetBadAspathMax	OBJECT-TYPE
	SYNTAX	 Counter64
	MAX-ACCESS read-only
	STATUS current
	DESCRIPTION "Old or corrupted AS-path entry"

	::={rulesetBadAspath 3}

rulesetConnStatechangeLinklevel	OBJECT IDENTIFIER ::={ruleset 39}

rulesetConnStatechangeLinklevelVal	OBJECT-TYPE
	SYNTAX	 Counter64
	MAX-ACCESS read-only
	STATUS current
	DESCRIPTION "Flow ruleset statechanges (linklevel)"

	::={rulesetConnStatechangeLinklevel 1}

rulesetConnStatechangeLinklevelMom	OBJECT-TYPE
	SYNTAX	 Unsigned32
	MAX-ACCESS read-only
	STATUS current
	DESCRIPTION "Flow ruleset statechanges (linklevel)"

	::={rulesetConnStatechangeLinklevel 2}

rulesetConnStatechangeLinklevelMax	OBJECT-TYPE
	SYNTAX	 Counter64
	MAX-ACCESS read-only
	STATUS current
	DESCRIPTION "Flow ruleset statechanges (linklevel)"

	::={rulesetConnStatechangeLinklevel 3}

rulesetSubscriberAllocFail	OBJECT IDENTIFIER ::={ruleset 40}

rulesetSubscriberAllocFailVal	OBJECT-TYPE
	SYNTAX	 Counter64
	MAX-ACCESS read-only
	STATUS current
	DESCRIPTION "Subscriber allocation failures"

	::={rulesetSubscriberAllocFail 1}

rulesetSubscriberAllocFailMom	OBJECT-TYPE
	SYNTAX	 Unsigned32
	MAX-ACCESS read-only
	STATUS current
	DESCRIPTION "Subscriber allocation failures"

	::={rulesetSubscriberAllocFail 2}

rulesetSubscriberAllocFailMax	OBJECT-TYPE
	SYNTAX	 Counter64
	MAX-ACCESS read-only
	STATUS current
	DESCRIPTION "Subscriber allocation failures"

	::={rulesetSubscriberAllocFail 3}

rulesetDynipAllocFail	OBJECT IDENTIFIER ::={ruleset 41}

rulesetDynipAllocFailVal	OBJECT-TYPE
	SYNTAX	 Counter64
	MAX-ACCESS read-only
	STATUS current
	DESCRIPTION "Dynamic ip loading failures (allocation failure)"

	::={rulesetDynipAllocFail 1}

rulesetDynipAllocFailMom	OBJECT-TYPE
	SYNTAX	 Unsigned32
	MAX-ACCESS read-only
	STATUS current
	DESCRIPTION "Dynamic ip loading failures (allocation failure)"

	::={rulesetDynipAllocFail 2}

rulesetDynipAllocFailMax	OBJECT-TYPE
	SYNTAX	 Counter64
	MAX-ACCESS read-only
	STATUS current
	DESCRIPTION "Dynamic ip loading failures (allocation failure)"

	::={rulesetDynipAllocFail 3}

rulesetDynipOversized	OBJECT IDENTIFIER ::={ruleset 42}

rulesetDynipOversizedVal	OBJECT-TYPE
	SYNTAX	 Counter64
	MAX-ACCESS read-only
	STATUS current
	DESCRIPTION "Dynamic ip loading failures (oversized)"

	::={rulesetDynipOversized 1}

rulesetDynipOversizedMom	OBJECT-TYPE
	SYNTAX	 Unsigned32
	MAX-ACCESS read-only
	STATUS current
	DESCRIPTION "Dynamic ip loading failures (oversized)"

	::={rulesetDynipOversized 2}

rulesetDynipOversizedMax	OBJECT-TYPE
	SYNTAX	 Counter64
	MAX-ACCESS read-only
	STATUS current
	DESCRIPTION "Dynamic ip loading failures (oversized)"

	::={rulesetDynipOversized 3}

firewall	OBJECT IDENTIFIER ::={sysdiag 80}

fwAccepts	OBJECT IDENTIFIER ::={firewall 1}

fwAcceptsVal	OBJECT-TYPE
	SYNTAX	 Counter64
	MAX-ACCESS read-only
	STATUS current
	DESCRIPTION "Ruleset evaluations giving ACCEPT"

	::={fwAccepts 1}

fwAcceptsMom	OBJECT-TYPE
	SYNTAX	 Unsigned32
	MAX-ACCESS read-only
	STATUS current
	DESCRIPTION "Ruleset evaluations giving ACCEPT"

	::={fwAccepts 2}

fwAcceptsMax	OBJECT-TYPE
	SYNTAX	 Counter64
	MAX-ACCESS read-only
	STATUS current
	DESCRIPTION "Ruleset evaluations giving ACCEPT"

	::={fwAccepts 3}

fwRejects	OBJECT IDENTIFIER ::={firewall 2}

fwRejectsVal	OBJECT-TYPE
	SYNTAX	 Counter64
	MAX-ACCESS read-only
	STATUS current
	DESCRIPTION "Ruleset evaluations giving REJECT"

	::={fwRejects 1}

fwRejectsMom	OBJECT-TYPE
	SYNTAX	 Unsigned32
	MAX-ACCESS read-only
	STATUS current
	DESCRIPTION "Ruleset evaluations giving REJECT"

	::={fwRejects 2}

fwRejectsMax	OBJECT-TYPE
	SYNTAX	 Counter64
	MAX-ACCESS read-only
	STATUS current
	DESCRIPTION "Ruleset evaluations giving REJECT"

	::={fwRejects 3}

fwDrops	OBJECT IDENTIFIER ::={firewall 3}

fwDropsVal	OBJECT-TYPE
	SYNTAX	 Counter64
	MAX-ACCESS read-only
	STATUS current
	DESCRIPTION "Ruleset evaluations giving DROP"

	::={fwDrops 1}

fwDropsMom	OBJECT-TYPE
	SYNTAX	 Unsigned32
	MAX-ACCESS read-only
	STATUS current
	DESCRIPTION "Ruleset evaluations giving DROP"

	::={fwDrops 2}

fwDropsMax	OBJECT-TYPE
	SYNTAX	 Counter64
	MAX-ACCESS read-only
	STATUS current
	DESCRIPTION "Ruleset evaluations giving DROP"

	::={fwDrops 3}

fwRewites	OBJECT IDENTIFIER ::={firewall 4}

fwRewitesVal	OBJECT-TYPE
	SYNTAX	 Counter64
	MAX-ACCESS read-only
	STATUS current
	DESCRIPTION "Ruleset evaluations giving REWRITE"

	::={fwRewites 1}

fwRewitesMom	OBJECT-TYPE
	SYNTAX	 Unsigned32
	MAX-ACCESS read-only
	STATUS current
	DESCRIPTION "Ruleset evaluations giving REWRITE"

	::={fwRewites 2}

fwRewitesMax	OBJECT-TYPE
	SYNTAX	 Counter64
	MAX-ACCESS read-only
	STATUS current
	DESCRIPTION "Ruleset evaluations giving REWRITE"

	::={fwRewites 3}

fwDiverts	OBJECT IDENTIFIER ::={firewall 5}

fwDivertsVal	OBJECT-TYPE
	SYNTAX	 Counter64
	MAX-ACCESS read-only
	STATUS current
	DESCRIPTION "Ruleset evaluations giving DIVERT"

	::={fwDiverts 1}

fwDivertsMom	OBJECT-TYPE
	SYNTAX	 Unsigned32
	MAX-ACCESS read-only
	STATUS current
	DESCRIPTION "Ruleset evaluations giving DIVERT"

	::={fwDiverts 2}

fwDivertsMax	OBJECT-TYPE
	SYNTAX	 Counter64
	MAX-ACCESS read-only
	STATUS current
	DESCRIPTION "Ruleset evaluations giving DIVERT"

	::={fwDiverts 3}

fwRuleSets	OBJECT IDENTIFIER ::={firewall 6}

fwRuleSetsVal	OBJECT-TYPE
	SYNTAX	 Counter64
	MAX-ACCESS read-only
	STATUS current
	DESCRIPTION "Ruleset evaluations"

	::={fwRuleSets 1}

fwRuleSetsMom	OBJECT-TYPE
	SYNTAX	 Unsigned32
	MAX-ACCESS read-only
	STATUS current
	DESCRIPTION "Ruleset evaluations"

	::={fwRuleSets 2}

fwRuleSetsMax	OBJECT-TYPE
	SYNTAX	 Counter64
	MAX-ACCESS read-only
	STATUS current
	DESCRIPTION "Ruleset evaluations"

	::={fwRuleSets 3}

fwLogs	OBJECT IDENTIFIER ::={firewall 7}

fwLogsVal	OBJECT-TYPE
	SYNTAX	 Counter64
	MAX-ACCESS read-only
	STATUS current
	DESCRIPTION "Log entries"

	::={fwLogs 1}

fwLogsMom	OBJECT-TYPE
	SYNTAX	 Unsigned32
	MAX-ACCESS read-only
	STATUS current
	DESCRIPTION "Log entries"

	::={fwLogs 2}

fwLogsMax	OBJECT-TYPE
	SYNTAX	 Counter64
	MAX-ACCESS read-only
	STATUS current
	DESCRIPTION "Log entries"

	::={fwLogs 3}

fwMonitor	OBJECT IDENTIFIER ::={firewall 8}

fwMonitorVal	OBJECT-TYPE
	SYNTAX	 Counter64
	MAX-ACCESS read-only
	STATUS current
	DESCRIPTION "Monitored packets"

	::={fwMonitor 1}

fwMonitorMom	OBJECT-TYPE
	SYNTAX	 Unsigned32
	MAX-ACCESS read-only
	STATUS current
	DESCRIPTION "Monitored packets"

	::={fwMonitor 2}

fwMonitorMax	OBJECT-TYPE
	SYNTAX	 Counter64
	MAX-ACCESS read-only
	STATUS current
	DESCRIPTION "Monitored packets"

	::={fwMonitor 3}

fwMonitorFailures	OBJECT IDENTIFIER ::={firewall 9}

fwMonitorFailuresVal	OBJECT-TYPE
	SYNTAX	 Counter64
	MAX-ACCESS read-only
	STATUS current
	DESCRIPTION "Failed monitored packets"

	::={fwMonitorFailures 1}

fwMonitorFailuresMom	OBJECT-TYPE
	SYNTAX	 Unsigned32
	MAX-ACCESS read-only
	STATUS current
	DESCRIPTION "Failed monitored packets"

	::={fwMonitorFailures 2}

fwMonitorFailuresMax	OBJECT-TYPE
	SYNTAX	 Counter64
	MAX-ACCESS read-only
	STATUS current
	DESCRIPTION "Failed monitored packets"

	::={fwMonitorFailures 3}

fwInjects	OBJECT IDENTIFIER ::={firewall 10}

fwInjectsVal	OBJECT-TYPE
	SYNTAX	 Counter64
	MAX-ACCESS read-only
	STATUS current
	DESCRIPTION "Ruleset evaluations giving INJECT"

	::={fwInjects 1}

fwInjectsMom	OBJECT-TYPE
	SYNTAX	 Unsigned32
	MAX-ACCESS read-only
	STATUS current
	DESCRIPTION "Ruleset evaluations giving INJECT"

	::={fwInjects 2}

fwInjectsMax	OBJECT-TYPE
	SYNTAX	 Counter64
	MAX-ACCESS read-only
	STATUS current
	DESCRIPTION "Ruleset evaluations giving INJECT"

	::={fwInjects 3}

fwInjectsFailures	OBJECT IDENTIFIER ::={firewall 11}

fwInjectsFailuresVal	OBJECT-TYPE
	SYNTAX	 Counter64
	MAX-ACCESS read-only
	STATUS current
	DESCRIPTION "Inject data preparation failures"

	::={fwInjectsFailures 1}

fwInjectsFailuresMom	OBJECT-TYPE
	SYNTAX	 Unsigned32
	MAX-ACCESS read-only
	STATUS current
	DESCRIPTION "Inject data preparation failures"

	::={fwInjectsFailures 2}

fwInjectsFailuresMax	OBJECT-TYPE
	SYNTAX	 Counter64
	MAX-ACCESS read-only
	STATUS current
	DESCRIPTION "Inject data preparation failures"

	::={fwInjectsFailures 3}

fwInjectsFailuresProp	OBJECT IDENTIFIER ::={firewall 12}

fwInjectsFailuresPropVal	OBJECT-TYPE
	SYNTAX	 Counter64
	MAX-ACCESS read-only
	STATUS current
	DESCRIPTION "Inject properties exceeding	max length (255)"

	::={fwInjectsFailuresProp 1}

fwInjectsFailuresPropMom	OBJECT-TYPE
	SYNTAX	 Unsigned32
	MAX-ACCESS read-only
	STATUS current
	DESCRIPTION "Inject properties exceeding	max length (255)"

	::={fwInjectsFailuresProp 2}

fwInjectsFailuresPropMax	OBJECT-TYPE
	SYNTAX	 Counter64
	MAX-ACCESS read-only
	STATUS current
	DESCRIPTION "Inject properties exceeding	max length (255)"

	::={fwInjectsFailuresProp 3}

fwMidconnRewrite	OBJECT IDENTIFIER ::={firewall 13}

fwMidconnRewriteVal	OBJECT-TYPE
	SYNTAX	 Counter64
	MAX-ACCESS read-only
	STATUS current
	DESCRIPTION "Rewrites changed in active connection"

	::={fwMidconnRewrite 1}

fwMidconnRewriteMom	OBJECT-TYPE
	SYNTAX	 Unsigned32
	MAX-ACCESS read-only
	STATUS current
	DESCRIPTION "Rewrites changed in active connection"

	::={fwMidconnRewrite 2}

fwMidconnRewriteMax	OBJECT-TYPE
	SYNTAX	 Counter64
	MAX-ACCESS read-only
	STATUS current
	DESCRIPTION "Rewrites changed in active connection"

	::={fwMidconnRewrite 3}

shaping	OBJECT IDENTIFIER ::={sysdiag 88}

shapingEnqueued	OBJECT IDENTIFIER ::={shaping 1}

shapingEnqueuedVal	OBJECT-TYPE
	SYNTAX	 Counter64
	MAX-ACCESS read-only
	STATUS current
	DESCRIPTION "Enqueued packets"

	::={shapingEnqueued 1}

shapingEnqueuedMom	OBJECT-TYPE
	SYNTAX	 Unsigned32
	MAX-ACCESS read-only
	STATUS current
	DESCRIPTION "Enqueued packets"

	::={shapingEnqueued 2}

shapingEnqueuedMax	OBJECT-TYPE
	SYNTAX	 Counter64
	MAX-ACCESS read-only
	STATUS current
	DESCRIPTION "Enqueued packets"

	::={shapingEnqueued 3}

shapingDequeued	OBJECT IDENTIFIER ::={shaping 2}

shapingDequeuedVal	OBJECT-TYPE
	SYNTAX	 Counter64
	MAX-ACCESS read-only
	STATUS current
	DESCRIPTION "Dequeued packets"

	::={shapingDequeued 1}

shapingDequeuedMom	OBJECT-TYPE
	SYNTAX	 Unsigned32
	MAX-ACCESS read-only
	STATUS current
	DESCRIPTION "Dequeued packets"

	::={shapingDequeued 2}

shapingDequeuedMax	OBJECT-TYPE
	SYNTAX	 Counter64
	MAX-ACCESS read-only
	STATUS current
	DESCRIPTION "Dequeued packets"

	::={shapingDequeued 3}

shapingBrownConnDrops	OBJECT IDENTIFIER ::={shaping 8}

shapingBrownConnDropsVal	OBJECT-TYPE
	SYNTAX	 Counter64
	MAX-ACCESS read-only
	STATUS current
	DESCRIPTION "BROWN per connection drops"

	::={shapingBrownConnDrops 1}

shapingBrownConnDropsMom	OBJECT-TYPE
	SYNTAX	 Unsigned32
	MAX-ACCESS read-only
	STATUS current
	DESCRIPTION "BROWN per connection drops"

	::={shapingBrownConnDrops 2}

shapingBrownConnDropsMax	OBJECT-TYPE
	SYNTAX	 Counter64
	MAX-ACCESS read-only
	STATUS current
	DESCRIPTION "BROWN per connection drops"

	::={shapingBrownConnDrops 3}

shapingQueueSize	OBJECT IDENTIFIER ::={shaping 9}

shapingQueueSizeVal	OBJECT-TYPE
	SYNTAX	 Unsigned32
	MAX-ACCESS read-only
	STATUS current
	DESCRIPTION "Queue size"

	::={shapingQueueSize 1}

shapingQueueSizeMax	OBJECT-TYPE
	SYNTAX	 Unsigned32
	MAX-ACCESS read-only
	STATUS current
	DESCRIPTION "Queue size"

	::={shapingQueueSize 3}

shapingRulesSetCount	OBJECT IDENTIFIER ::={shaping 10}

shapingRulesSetCountVal	OBJECT-TYPE
	SYNTAX	 Counter64
	MAX-ACCESS read-only
	STATUS current
	DESCRIPTION "Rule sets"

	::={shapingRulesSetCount 1}

shapingRulesSetCountMom	OBJECT-TYPE
	SYNTAX	 Unsigned32
	MAX-ACCESS read-only
	STATUS current
	DESCRIPTION "Rule sets"

	::={shapingRulesSetCount 2}

shapingRulesSetCountMax	OBJECT-TYPE
	SYNTAX	 Counter64
	MAX-ACCESS read-only
	STATUS current
	DESCRIPTION "Rule sets"

	::={shapingRulesSetCount 3}

shapingEnqueuedBytes	OBJECT IDENTIFIER ::={shaping 11}

shapingEnqueuedBytesVal	OBJECT-TYPE
	SYNTAX	 Counter64
	MAX-ACCESS read-only
	STATUS current
	DESCRIPTION "Enqueued bytes"

	::={shapingEnqueuedBytes 1}

shapingEnqueuedBytesMom	OBJECT-TYPE
	SYNTAX	 Unsigned32
	MAX-ACCESS read-only
	STATUS current
	DESCRIPTION "Enqueued bytes"

	::={shapingEnqueuedBytes 2}

shapingEnqueuedBytesMax	OBJECT-TYPE
	SYNTAX	 Counter64
	MAX-ACCESS read-only
	STATUS current
	DESCRIPTION "Enqueued bytes"

	::={shapingEnqueuedBytes 3}

shapingDequeuedBytes	OBJECT IDENTIFIER ::={shaping 12}

shapingDequeuedBytesVal	OBJECT-TYPE
	SYNTAX	 Counter64
	MAX-ACCESS read-only
	STATUS current
	DESCRIPTION "Dequeued bytes"

	::={shapingDequeuedBytes 1}

shapingDequeuedBytesMom	OBJECT-TYPE
	SYNTAX	 Unsigned32
	MAX-ACCESS read-only
	STATUS current
	DESCRIPTION "Dequeued bytes"

	::={shapingDequeuedBytes 2}

shapingDequeuedBytesMax	OBJECT-TYPE
	SYNTAX	 Counter64
	MAX-ACCESS read-only
	STATUS current
	DESCRIPTION "Dequeued bytes"

	::={shapingDequeuedBytes 3}

shapingObjectCopies	OBJECT IDENTIFIER ::={shaping 13}

shapingObjectCopiesVal	OBJECT-TYPE
	SYNTAX	 Unsigned32
	MAX-ACCESS read-only
	STATUS current
	DESCRIPTION "Object copies"

	::={shapingObjectCopies 1}

shapingObjectCopiesMax	OBJECT-TYPE
	SYNTAX	 Unsigned32
	MAX-ACCESS read-only
	STATUS current
	DESCRIPTION "Object copies"

	::={shapingObjectCopies 3}

shapingOutofpacketsDrops	OBJECT IDENTIFIER ::={shaping 15}

shapingOutofpacketsDropsVal	OBJECT-TYPE
	SYNTAX	 Counter64
	MAX-ACCESS read-only
	STATUS current
	DESCRIPTION "Out of packets drops"

	::={shapingOutofpacketsDrops 1}

shapingOutofpacketsDropsMom	OBJECT-TYPE
	SYNTAX	 Unsigned32
	MAX-ACCESS read-only
	STATUS current
	DESCRIPTION "Out of packets drops"

	::={shapingOutofpacketsDrops 2}

shapingOutofpacketsDropsMax	OBJECT-TYPE
	SYNTAX	 Counter64
	MAX-ACCESS read-only
	STATUS current
	DESCRIPTION "Out of packets drops"

	::={shapingOutofpacketsDrops 3}

shapingReceived	OBJECT IDENTIFIER ::={shaping 16}

shapingReceivedVal	OBJECT-TYPE
	SYNTAX	 Counter64
	MAX-ACCESS read-only
	STATUS current
	DESCRIPTION "Packets received"

	::={shapingReceived 1}

shapingReceivedMom	OBJECT-TYPE
	SYNTAX	 Unsigned32
	MAX-ACCESS read-only
	STATUS current
	DESCRIPTION "Packets received"

	::={shapingReceived 2}

shapingReceivedMax	OBJECT-TYPE
	SYNTAX	 Counter64
	MAX-ACCESS read-only
	STATUS current
	DESCRIPTION "Packets received"

	::={shapingReceived 3}

shapingObjectChecks	OBJECT IDENTIFIER ::={shaping 17}

shapingObjectChecksVal	OBJECT-TYPE
	SYNTAX	 Counter64
	MAX-ACCESS read-only
	STATUS current
	DESCRIPTION "Object checks"

	::={shapingObjectChecks 1}

shapingObjectChecksMom	OBJECT-TYPE
	SYNTAX	 Unsigned32
	MAX-ACCESS read-only
	STATUS current
	DESCRIPTION "Object checks"

	::={shapingObjectChecks 2}

shapingObjectChecksMax	OBJECT-TYPE
	SYNTAX	 Counter64
	MAX-ACCESS read-only
	STATUS current
	DESCRIPTION "Object checks"

	::={shapingObjectChecks 3}

shapingRuntimeCheck	OBJECT IDENTIFIER ::={shaping 18}

shapingRuntimeCheckVal	OBJECT-TYPE
	SYNTAX	 Unsigned32
	MAX-ACCESS read-only
	STATUS current
	DESCRIPTION "Average cycles per packet (check)"

	::={shapingRuntimeCheck 1}

shapingRuntimeCheckMax	OBJECT-TYPE
	SYNTAX	 Unsigned32
	MAX-ACCESS read-only
	STATUS current
	DESCRIPTION "Average cycles per packet (check)"

	::={shapingRuntimeCheck 3}

shapingRuntimeEnqueue	OBJECT IDENTIFIER ::={shaping 19}

shapingRuntimeEnqueueVal	OBJECT-TYPE
	SYNTAX	 Unsigned32
	MAX-ACCESS read-only
	STATUS current
	DESCRIPTION "Average cycles per packet (enqueue)"

	::={shapingRuntimeEnqueue 1}

shapingRuntimeEnqueueMax	OBJECT-TYPE
	SYNTAX	 Unsigned32
	MAX-ACCESS read-only
	STATUS current
	DESCRIPTION "Average cycles per packet (enqueue)"

	::={shapingRuntimeEnqueue 3}

shapingObjectPoolExhausted	OBJECT IDENTIFIER ::={shaping 25}

shapingObjectPoolExhaustedVal	OBJECT-TYPE
	SYNTAX	 Counter64
	MAX-ACCESS read-only
	STATUS current
	DESCRIPTION "Too many dynamic objects"

	::={shapingObjectPoolExhausted 1}

shapingObjectPoolExhaustedMom	OBJECT-TYPE
	SYNTAX	 Unsigned32
	MAX-ACCESS read-only
	STATUS current
	DESCRIPTION "Too many dynamic objects"

	::={shapingObjectPoolExhausted 2}

shapingObjectPoolExhaustedMax	OBJECT-TYPE
	SYNTAX	 Counter64
	MAX-ACCESS read-only
	STATUS current
	DESCRIPTION "Too many dynamic objects"

	::={shapingObjectPoolExhausted 3}

shapingOutOfCreditsDrops	OBJECT IDENTIFIER ::={shaping 26}

shapingOutOfCreditsDropsVal	OBJECT-TYPE
	SYNTAX	 Counter64
	MAX-ACCESS read-only
	STATUS current
	DESCRIPTION "Out of credits (vbs) drops"

	::={shapingOutOfCreditsDrops 1}

shapingOutOfCreditsDropsMom	OBJECT-TYPE
	SYNTAX	 Unsigned32
	MAX-ACCESS read-only
	STATUS current
	DESCRIPTION "Out of credits (vbs) drops"

	::={shapingOutOfCreditsDrops 2}

shapingOutOfCreditsDropsMax	OBJECT-TYPE
	SYNTAX	 Counter64
	MAX-ACCESS read-only
	STATUS current
	DESCRIPTION "Out of credits (vbs) drops"

	::={shapingOutOfCreditsDrops 3}

shapingRuntimeDequeue	OBJECT IDENTIFIER ::={shaping 30}

shapingRuntimeDequeueVal	OBJECT-TYPE
	SYNTAX	 Counter64
	MAX-ACCESS read-only
	STATUS current
	DESCRIPTION "Average cycles per packet (dequeue)"

	::={shapingRuntimeDequeue 1}

shapingRuntimeDequeueMom	OBJECT-TYPE
	SYNTAX	 Unsigned32
	MAX-ACCESS read-only
	STATUS current
	DESCRIPTION "Average cycles per packet (dequeue)"

	::={shapingRuntimeDequeue 2}

shapingRuntimeDequeueMax	OBJECT-TYPE
	SYNTAX	 Counter64
	MAX-ACCESS read-only
	STATUS current
	DESCRIPTION "Average cycles per packet (dequeue)"

	::={shapingRuntimeDequeue 3}

shapingObjectOverflow	OBJECT IDENTIFIER ::={shaping 31}

shapingObjectOverflowVal	OBJECT-TYPE
	SYNTAX	 Counter64
	MAX-ACCESS read-only
	STATUS current
	DESCRIPTION "Too many shaping objects matching a connection"

	::={shapingObjectOverflow 1}

shapingObjectOverflowMom	OBJECT-TYPE
	SYNTAX	 Unsigned32
	MAX-ACCESS read-only
	STATUS current
	DESCRIPTION "Too many shaping objects matching a connection"

	::={shapingObjectOverflow 2}

shapingObjectOverflowMax	OBJECT-TYPE
	SYNTAX	 Counter64
	MAX-ACCESS read-only
	STATUS current
	DESCRIPTION "Too many shaping objects matching a connection"

	::={shapingObjectOverflow 3}

shapingRuleOverflow	OBJECT IDENTIFIER ::={shaping 32}

shapingRuleOverflowVal	OBJECT-TYPE
	SYNTAX	 Counter64
	MAX-ACCESS read-only
	STATUS current
	DESCRIPTION "Too many matching rules"

	::={shapingRuleOverflow 1}

shapingRuleOverflowMom	OBJECT-TYPE
	SYNTAX	 Unsigned32
	MAX-ACCESS read-only
	STATUS current
	DESCRIPTION "Too many matching rules"

	::={shapingRuleOverflow 2}

shapingRuleOverflowMax	OBJECT-TYPE
	SYNTAX	 Counter64
	MAX-ACCESS read-only
	STATUS current
	DESCRIPTION "Too many matching rules"

	::={shapingRuleOverflow 3}

shapingOutOfArrays	OBJECT IDENTIFIER ::={shaping 33}

shapingOutOfArraysVal	OBJECT-TYPE
	SYNTAX	 Counter64
	MAX-ACCESS read-only
	STATUS current
	DESCRIPTION "Out of shaping rule arrays"

	::={shapingOutOfArrays 1}

shapingOutOfArraysMom	OBJECT-TYPE
	SYNTAX	 Unsigned32
	MAX-ACCESS read-only
	STATUS current
	DESCRIPTION "Out of shaping rule arrays"

	::={shapingOutOfArrays 2}

shapingOutOfArraysMax	OBJECT-TYPE
	SYNTAX	 Counter64
	MAX-ACCESS read-only
	STATUS current
	DESCRIPTION "Out of shaping rule arrays"

	::={shapingOutOfArrays 3}

shapingDrops	OBJECT IDENTIFIER ::={shaping 37}

shapingDropsVal	OBJECT-TYPE
	SYNTAX	 Counter64
	MAX-ACCESS read-only
	STATUS current
	DESCRIPTION "Queuing drops (all types)"

	::={shapingDrops 1}

shapingDropsMom	OBJECT-TYPE
	SYNTAX	 Unsigned32
	MAX-ACCESS read-only
	STATUS current
	DESCRIPTION "Queuing drops (all types)"

	::={shapingDrops 2}

shapingDropsMax	OBJECT-TYPE
	SYNTAX	 Counter64
	MAX-ACCESS read-only
	STATUS current
	DESCRIPTION "Queuing drops (all types)"

	::={shapingDrops 3}

shapingObjectFull	OBJECT IDENTIFIER ::={shaping 38}

shapingObjectFullVal	OBJECT-TYPE
	SYNTAX	 Counter64
	MAX-ACCESS read-only
	STATUS current
	DESCRIPTION "Shaping object queue full"

	::={shapingObjectFull 1}

shapingObjectFullMom	OBJECT-TYPE
	SYNTAX	 Unsigned32
	MAX-ACCESS read-only
	STATUS current
	DESCRIPTION "Shaping object queue full"

	::={shapingObjectFull 2}

shapingObjectFullMax	OBJECT-TYPE
	SYNTAX	 Counter64
	MAX-ACCESS read-only
	STATUS current
	DESCRIPTION "Shaping object queue full"

	::={shapingObjectFull 3}

shapingUnshaped	OBJECT IDENTIFIER ::={shaping 39}

shapingUnshapedVal	OBJECT-TYPE
	SYNTAX	 Counter64
	MAX-ACCESS read-only
	STATUS current
	DESCRIPTION "Unshaped packets"

	::={shapingUnshaped 1}

shapingUnshapedMom	OBJECT-TYPE
	SYNTAX	 Unsigned32
	MAX-ACCESS read-only
	STATUS current
	DESCRIPTION "Unshaped packets"

	::={shapingUnshaped 2}

shapingUnshapedMax	OBJECT-TYPE
	SYNTAX	 Counter64
	MAX-ACCESS read-only
	STATUS current
	DESCRIPTION "Unshaped packets"

	::={shapingUnshaped 3}

shapingUnshapedBytes	OBJECT IDENTIFIER ::={shaping 40}

shapingUnshapedBytesVal	OBJECT-TYPE
	SYNTAX	 Counter64
	MAX-ACCESS read-only
	STATUS current
	DESCRIPTION "Unshaped bytes"

	::={shapingUnshapedBytes 1}

shapingUnshapedBytesMom	OBJECT-TYPE
	SYNTAX	 Unsigned32
	MAX-ACCESS read-only
	STATUS current
	DESCRIPTION "Unshaped bytes"

	::={shapingUnshapedBytes 2}

shapingUnshapedBytesMax	OBJECT-TYPE
	SYNTAX	 Counter64
	MAX-ACCESS read-only
	STATUS current
	DESCRIPTION "Unshaped bytes"

	::={shapingUnshapedBytes 3}

shapingDequeueCalls	OBJECT IDENTIFIER ::={shaping 41}

shapingDequeueCallsVal	OBJECT-TYPE
	SYNTAX	 Counter64
	MAX-ACCESS read-only
	STATUS current
	DESCRIPTION "Dequeue calls"

	::={shapingDequeueCalls 1}

shapingDequeueCallsMom	OBJECT-TYPE
	SYNTAX	 Unsigned32
	MAX-ACCESS read-only
	STATUS current
	DESCRIPTION "Dequeue calls"

	::={shapingDequeueCalls 2}

shapingDequeueCallsMax	OBJECT-TYPE
	SYNTAX	 Counter64
	MAX-ACCESS read-only
	STATUS current
	DESCRIPTION "Dequeue calls"

	::={shapingDequeueCalls 3}

shapingRecycleObjects	OBJECT IDENTIFIER ::={shaping 42}

shapingRecycleObjectsVal	OBJECT-TYPE
	SYNTAX	 Unsigned32
	MAX-ACCESS read-only
	STATUS current
	DESCRIPTION "Objects in recycle queue"

	::={shapingRecycleObjects 1}

shapingRecycleObjectsMax	OBJECT-TYPE
	SYNTAX	 Unsigned32
	MAX-ACCESS read-only
	STATUS current
	DESCRIPTION "Objects in recycle queue"

	::={shapingRecycleObjects 3}

shapingLocalhostOverflow	OBJECT IDENTIFIER ::={shaping 43}

shapingLocalhostOverflowVal	OBJECT-TYPE
	SYNTAX	 Counter64
	MAX-ACCESS read-only
	STATUS current
	DESCRIPTION "Too many dynamic objects in rule"

	::={shapingLocalhostOverflow 1}

shapingLocalhostOverflowMom	OBJECT-TYPE
	SYNTAX	 Unsigned32
	MAX-ACCESS read-only
	STATUS current
	DESCRIPTION "Too many dynamic objects in rule"

	::={shapingLocalhostOverflow 2}

shapingLocalhostOverflowMax	OBJECT-TYPE
	SYNTAX	 Counter64
	MAX-ACCESS read-only
	STATUS current
	DESCRIPTION "Too many dynamic objects in rule"

	::={shapingLocalhostOverflow 3}

shapingDirect	OBJECT IDENTIFIER ::={shaping 44}

shapingDirectVal	OBJECT-TYPE
	SYNTAX	 Counter64
	MAX-ACCESS read-only
	STATUS current
	DESCRIPTION "Directly sent packets"

	::={shapingDirect 1}

shapingDirectMom	OBJECT-TYPE
	SYNTAX	 Unsigned32
	MAX-ACCESS read-only
	STATUS current
	DESCRIPTION "Directly sent packets"

	::={shapingDirect 2}

shapingDirectMax	OBJECT-TYPE
	SYNTAX	 Counter64
	MAX-ACCESS read-only
	STATUS current
	DESCRIPTION "Directly sent packets"

	::={shapingDirect 3}

shapingDirectBytes	OBJECT IDENTIFIER ::={shaping 45}

shapingDirectBytesVal	OBJECT-TYPE
	SYNTAX	 Counter64
	MAX-ACCESS read-only
	STATUS current
	DESCRIPTION "Directly sent bytes"

	::={shapingDirectBytes 1}

shapingDirectBytesMom	OBJECT-TYPE
	SYNTAX	 Unsigned32
	MAX-ACCESS read-only
	STATUS current
	DESCRIPTION "Directly sent bytes"

	::={shapingDirectBytes 2}

shapingDirectBytesMax	OBJECT-TYPE
	SYNTAX	 Counter64
	MAX-ACCESS read-only
	STATUS current
	DESCRIPTION "Directly sent bytes"

	::={shapingDirectBytes 3}

shapingBorrowDequeues	OBJECT IDENTIFIER ::={shaping 46}

shapingBorrowDequeuesVal	OBJECT-TYPE
	SYNTAX	 Counter64
	MAX-ACCESS read-only
	STATUS current
	DESCRIPTION "Borrowing dequeues"

	::={shapingBorrowDequeues 1}

shapingBorrowDequeuesMom	OBJECT-TYPE
	SYNTAX	 Unsigned32
	MAX-ACCESS read-only
	STATUS current
	DESCRIPTION "Borrowing dequeues"

	::={shapingBorrowDequeues 2}

shapingBorrowDequeuesMax	OBJECT-TYPE
	SYNTAX	 Counter64
	MAX-ACCESS read-only
	STATUS current
	DESCRIPTION "Borrowing dequeues"

	::={shapingBorrowDequeues 3}

shapingVbsSplitError	OBJECT IDENTIFIER ::={shaping 47}

shapingVbsSplitErrorVal	OBJECT-TYPE
	SYNTAX	 Counter64
	MAX-ACCESS read-only
	STATUS obsolete
	DESCRIPTION "VBS split allocation failures"

	::={shapingVbsSplitError 1}

shapingVbsSplitErrorMom	OBJECT-TYPE
	SYNTAX	 Unsigned32
	MAX-ACCESS read-only
	STATUS obsolete
	DESCRIPTION "VBS split allocation failures"

	::={shapingVbsSplitError 2}

shapingVbsSplitErrorMax	OBJECT-TYPE
	SYNTAX	 Counter64
	MAX-ACCESS read-only
	STATUS obsolete
	DESCRIPTION "VBS split allocation failures"

	::={shapingVbsSplitError 3}

shapingBrownHostDrops	OBJECT IDENTIFIER ::={shaping 48}

shapingBrownHostDropsVal	OBJECT-TYPE
	SYNTAX	 Counter64
	MAX-ACCESS read-only
	STATUS current
	DESCRIPTION "BROWN per host drops"

	::={shapingBrownHostDrops 1}

shapingBrownHostDropsMom	OBJECT-TYPE
	SYNTAX	 Unsigned32
	MAX-ACCESS read-only
	STATUS current
	DESCRIPTION "BROWN per host drops"

	::={shapingBrownHostDrops 2}

shapingBrownHostDropsMax	OBJECT-TYPE
	SYNTAX	 Counter64
	MAX-ACCESS read-only
	STATUS current
	DESCRIPTION "BROWN per host drops"

	::={shapingBrownHostDrops 3}

shapingMaxConnDrops	OBJECT IDENTIFIER ::={shaping 49}

shapingMaxConnDropsVal	OBJECT-TYPE
	SYNTAX	 Counter64
	MAX-ACCESS read-only
	STATUS current
	DESCRIPTION "Object max connections reached"

	::={shapingMaxConnDrops 1}

shapingMaxConnDropsMom	OBJECT-TYPE
	SYNTAX	 Unsigned32
	MAX-ACCESS read-only
	STATUS current
	DESCRIPTION "Object max connections reached"

	::={shapingMaxConnDrops 2}

shapingMaxConnDropsMax	OBJECT-TYPE
	SYNTAX	 Counter64
	MAX-ACCESS read-only
	STATUS current
	DESCRIPTION "Object max connections reached"

	::={shapingMaxConnDrops 3}

shapingScheduledOdirs	OBJECT IDENTIFIER ::={shaping 50}

shapingScheduledOdirsVal	OBJECT-TYPE
	SYNTAX	 Unsigned32
	MAX-ACCESS read-only
	STATUS current
	DESCRIPTION "Scheduled odirs"

	::={shapingScheduledOdirs 1}

shapingScheduledOdirsMax	OBJECT-TYPE
	SYNTAX	 Unsigned32
	MAX-ACCESS read-only
	STATUS current
	DESCRIPTION "Scheduled odirs"

	::={shapingScheduledOdirs 3}

shapingQueuePoolExhausted	OBJECT IDENTIFIER ::={shaping 51}

shapingQueuePoolExhaustedVal	OBJECT-TYPE
	SYNTAX	 Counter64
	MAX-ACCESS read-only
	STATUS current
	DESCRIPTION "Queue pool exhausted"

	::={shapingQueuePoolExhausted 1}

shapingQueuePoolExhaustedMom	OBJECT-TYPE
	SYNTAX	 Unsigned32
	MAX-ACCESS read-only
	STATUS current
	DESCRIPTION "Queue pool exhausted"

	::={shapingQueuePoolExhausted 2}

shapingQueuePoolExhaustedMax	OBJECT-TYPE
	SYNTAX	 Counter64
	MAX-ACCESS read-only
	STATUS current
	DESCRIPTION "Queue pool exhausted"

	::={shapingQueuePoolExhausted 3}

shapingActiveQueues	OBJECT IDENTIFIER ::={shaping 52}

shapingActiveQueuesVal	OBJECT-TYPE
	SYNTAX	 Unsigned32
	MAX-ACCESS read-only
	STATUS current
	DESCRIPTION "Active queues"

	::={shapingActiveQueues 1}

shapingActiveQueuesMax	OBJECT-TYPE
	SYNTAX	 Unsigned32
	MAX-ACCESS read-only
	STATUS current
	DESCRIPTION "Active queues"

	::={shapingActiveQueues 3}

shapingQueueAllocations	OBJECT IDENTIFIER ::={shaping 53}

shapingQueueAllocationsVal	OBJECT-TYPE
	SYNTAX	 Counter64
	MAX-ACCESS read-only
	STATUS current
	DESCRIPTION "Queue allocations"

	::={shapingQueueAllocations 1}

shapingQueueAllocationsMom	OBJECT-TYPE
	SYNTAX	 Unsigned32
	MAX-ACCESS read-only
	STATUS current
	DESCRIPTION "Queue allocations"

	::={shapingQueueAllocations 2}

shapingQueueAllocationsMax	OBJECT-TYPE
	SYNTAX	 Counter64
	MAX-ACCESS read-only
	STATUS current
	DESCRIPTION "Queue allocations"

	::={shapingQueueAllocations 3}

shapingDropsPrio1	OBJECT IDENTIFIER ::={shaping 54}

shapingDropsPrio1Val	OBJECT-TYPE
	SYNTAX	 Counter64
	MAX-ACCESS read-only
	STATUS current
	DESCRIPTION "Queuing drops (prio 1)"

	::={shapingDropsPrio1 1}

shapingDropsPrio1Mom	OBJECT-TYPE
	SYNTAX	 Unsigned32
	MAX-ACCESS read-only
	STATUS current
	DESCRIPTION "Queuing drops (prio 1)"

	::={shapingDropsPrio1 2}

shapingDropsPrio1Max	OBJECT-TYPE
	SYNTAX	 Counter64
	MAX-ACCESS read-only
	STATUS current
	DESCRIPTION "Queuing drops (prio 1)"

	::={shapingDropsPrio1 3}

shapingDropsPrio2	OBJECT IDENTIFIER ::={shaping 55}

shapingDropsPrio2Val	OBJECT-TYPE
	SYNTAX	 Counter64
	MAX-ACCESS read-only
	STATUS current
	DESCRIPTION "Queuing drops (prio 2)"

	::={shapingDropsPrio2 1}

shapingDropsPrio2Mom	OBJECT-TYPE
	SYNTAX	 Unsigned32
	MAX-ACCESS read-only
	STATUS current
	DESCRIPTION "Queuing drops (prio 2)"

	::={shapingDropsPrio2 2}

shapingDropsPrio2Max	OBJECT-TYPE
	SYNTAX	 Counter64
	MAX-ACCESS read-only
	STATUS current
	DESCRIPTION "Queuing drops (prio 2)"

	::={shapingDropsPrio2 3}

shapingDropsPrio3	OBJECT IDENTIFIER ::={shaping 56}

shapingDropsPrio3Val	OBJECT-TYPE
	SYNTAX	 Counter64
	MAX-ACCESS read-only
	STATUS current
	DESCRIPTION "Queuing drops (prio 3)"

	::={shapingDropsPrio3 1}

shapingDropsPrio3Mom	OBJECT-TYPE
	SYNTAX	 Unsigned32
	MAX-ACCESS read-only
	STATUS current
	DESCRIPTION "Queuing drops (prio 3)"

	::={shapingDropsPrio3 2}

shapingDropsPrio3Max	OBJECT-TYPE
	SYNTAX	 Counter64
	MAX-ACCESS read-only
	STATUS current
	DESCRIPTION "Queuing drops (prio 3)"

	::={shapingDropsPrio3 3}

shapingDropsPrio4	OBJECT IDENTIFIER ::={shaping 57}

shapingDropsPrio4Val	OBJECT-TYPE
	SYNTAX	 Counter64
	MAX-ACCESS read-only
	STATUS current
	DESCRIPTION "Queuing drops (prio 4)"

	::={shapingDropsPrio4 1}

shapingDropsPrio4Mom	OBJECT-TYPE
	SYNTAX	 Unsigned32
	MAX-ACCESS read-only
	STATUS current
	DESCRIPTION "Queuing drops (prio 4)"

	::={shapingDropsPrio4 2}

shapingDropsPrio4Max	OBJECT-TYPE
	SYNTAX	 Counter64
	MAX-ACCESS read-only
	STATUS current
	DESCRIPTION "Queuing drops (prio 4)"

	::={shapingDropsPrio4 3}

shapingDropsPrio5	OBJECT IDENTIFIER ::={shaping 58}

shapingDropsPrio5Val	OBJECT-TYPE
	SYNTAX	 Counter64
	MAX-ACCESS read-only
	STATUS current
	DESCRIPTION "Queuing drops (prio 5)"

	::={shapingDropsPrio5 1}

shapingDropsPrio5Mom	OBJECT-TYPE
	SYNTAX	 Unsigned32
	MAX-ACCESS read-only
	STATUS current
	DESCRIPTION "Queuing drops (prio 5)"

	::={shapingDropsPrio5 2}

shapingDropsPrio5Max	OBJECT-TYPE
	SYNTAX	 Counter64
	MAX-ACCESS read-only
	STATUS current
	DESCRIPTION "Queuing drops (prio 5)"

	::={shapingDropsPrio5 3}

shapingDropsPrio6	OBJECT IDENTIFIER ::={shaping 59}

shapingDropsPrio6Val	OBJECT-TYPE
	SYNTAX	 Counter64
	MAX-ACCESS read-only
	STATUS current
	DESCRIPTION "Queuing drops (prio 6)"

	::={shapingDropsPrio6 1}

shapingDropsPrio6Mom	OBJECT-TYPE
	SYNTAX	 Unsigned32
	MAX-ACCESS read-only
	STATUS current
	DESCRIPTION "Queuing drops (prio 6)"

	::={shapingDropsPrio6 2}

shapingDropsPrio6Max	OBJECT-TYPE
	SYNTAX	 Counter64
	MAX-ACCESS read-only
	STATUS current
	DESCRIPTION "Queuing drops (prio 6)"

	::={shapingDropsPrio6 3}

shapingDropsPrio7	OBJECT IDENTIFIER ::={shaping 60}

shapingDropsPrio7Val	OBJECT-TYPE
	SYNTAX	 Counter64
	MAX-ACCESS read-only
	STATUS current
	DESCRIPTION "Queuing drops (prio 7)"

	::={shapingDropsPrio7 1}

shapingDropsPrio7Mom	OBJECT-TYPE
	SYNTAX	 Unsigned32
	MAX-ACCESS read-only
	STATUS current
	DESCRIPTION "Queuing drops (prio 7)"

	::={shapingDropsPrio7 2}

shapingDropsPrio7Max	OBJECT-TYPE
	SYNTAX	 Counter64
	MAX-ACCESS read-only
	STATUS current
	DESCRIPTION "Queuing drops (prio 7)"

	::={shapingDropsPrio7 3}

shapingDropsPrio8	OBJECT IDENTIFIER ::={shaping 61}

shapingDropsPrio8Val	OBJECT-TYPE
	SYNTAX	 Counter64
	MAX-ACCESS read-only
	STATUS current
	DESCRIPTION "Queuing drops (prio 8)"

	::={shapingDropsPrio8 1}

shapingDropsPrio8Mom	OBJECT-TYPE
	SYNTAX	 Unsigned32
	MAX-ACCESS read-only
	STATUS current
	DESCRIPTION "Queuing drops (prio 8)"

	::={shapingDropsPrio8 2}

shapingDropsPrio8Max	OBJECT-TYPE
	SYNTAX	 Counter64
	MAX-ACCESS read-only
	STATUS current
	DESCRIPTION "Queuing drops (prio 8)"

	::={shapingDropsPrio8 3}

shapingDropsPrio9	OBJECT IDENTIFIER ::={shaping 62}

shapingDropsPrio9Val	OBJECT-TYPE
	SYNTAX	 Counter64
	MAX-ACCESS read-only
	STATUS current
	DESCRIPTION "Queuing drops (prio 9)"

	::={shapingDropsPrio9 1}

shapingDropsPrio9Mom	OBJECT-TYPE
	SYNTAX	 Unsigned32
	MAX-ACCESS read-only
	STATUS current
	DESCRIPTION "Queuing drops (prio 9)"

	::={shapingDropsPrio9 2}

shapingDropsPrio9Max	OBJECT-TYPE
	SYNTAX	 Counter64
	MAX-ACCESS read-only
	STATUS current
	DESCRIPTION "Queuing drops (prio 9)"

	::={shapingDropsPrio9 3}

shapingDropsPrioOther	OBJECT IDENTIFIER ::={shaping 63}

shapingDropsPrioOtherVal	OBJECT-TYPE
	SYNTAX	 Counter64
	MAX-ACCESS read-only
	STATUS current
	DESCRIPTION "Queuing drops (other prio)"

	::={shapingDropsPrioOther 1}

shapingDropsPrioOtherMom	OBJECT-TYPE
	SYNTAX	 Unsigned32
	MAX-ACCESS read-only
	STATUS current
	DESCRIPTION "Queuing drops (other prio)"

	::={shapingDropsPrioOther 2}

shapingDropsPrioOtherMax	OBJECT-TYPE
	SYNTAX	 Counter64
	MAX-ACCESS read-only
	STATUS current
	DESCRIPTION "Queuing drops (other prio)"

	::={shapingDropsPrioOther 3}

shapingDropsCps	OBJECT IDENTIFIER ::={shaping 64}

shapingDropsCpsVal	OBJECT-TYPE
	SYNTAX	 Counter64
	MAX-ACCESS read-only
	STATUS current
	DESCRIPTION "CPS limit drops"

	::={shapingDropsCps 1}

shapingDropsCpsMom	OBJECT-TYPE
	SYNTAX	 Unsigned32
	MAX-ACCESS read-only
	STATUS current
	DESCRIPTION "CPS limit drops"

	::={shapingDropsCps 2}

shapingDropsCpsMax	OBJECT-TYPE
	SYNTAX	 Counter64
	MAX-ACCESS read-only
	STATUS current
	DESCRIPTION "CPS limit drops"

	::={shapingDropsCps 3}

shapingFailedFairnessObjects	OBJECT IDENTIFIER ::={shaping 65}

shapingFailedFairnessObjectsVal	OBJECT-TYPE
	SYNTAX	 Counter64
	MAX-ACCESS read-only
	STATUS current
	DESCRIPTION "Host fairness data allocation failures"

	::={shapingFailedFairnessObjects 1}

shapingFailedFairnessObjectsMom	OBJECT-TYPE
	SYNTAX	 Unsigned32
	MAX-ACCESS read-only
	STATUS current
	DESCRIPTION "Host fairness data allocation failures"

	::={shapingFailedFairnessObjects 2}

shapingFailedFairnessObjectsMax	OBJECT-TYPE
	SYNTAX	 Counter64
	MAX-ACCESS read-only
	STATUS current
	DESCRIPTION "Host fairness data allocation failures"

	::={shapingFailedFairnessObjects 3}

shapingUsedFairnessObjects	OBJECT IDENTIFIER ::={shaping 66}

shapingUsedFairnessObjectsVal	OBJECT-TYPE
	SYNTAX	 Unsigned32
	MAX-ACCESS read-only
	STATUS current
	DESCRIPTION "Host fairness data used"

	::={shapingUsedFairnessObjects 1}

shapingUsedFairnessObjectsMax	OBJECT-TYPE
	SYNTAX	 Unsigned32
	MAX-ACCESS read-only
	STATUS current
	DESCRIPTION "Host fairness data used"

	::={shapingUsedFairnessObjects 3}

shapingReloadDrops	OBJECT IDENTIFIER ::={shaping 67}

shapingReloadDropsVal	OBJECT-TYPE
	SYNTAX	 Counter64
	MAX-ACCESS read-only
	STATUS current
	DESCRIPTION "Drops caused by ruleset reload"

	::={shapingReloadDrops 1}

shapingReloadDropsMom	OBJECT-TYPE
	SYNTAX	 Unsigned32
	MAX-ACCESS read-only
	STATUS current
	DESCRIPTION "Drops caused by ruleset reload"

	::={shapingReloadDrops 2}

shapingReloadDropsMax	OBJECT-TYPE
	SYNTAX	 Counter64
	MAX-ACCESS read-only
	STATUS current
	DESCRIPTION "Drops caused by ruleset reload"

	::={shapingReloadDrops 3}

shapingRequeueQueueUsed	OBJECT IDENTIFIER ::={shaping 68}

shapingRequeueQueueUsedVal	OBJECT-TYPE
	SYNTAX	 Unsigned32
	MAX-ACCESS read-only
	STATUS current
	DESCRIPTION "Packets in requeue queue"

	::={shapingRequeueQueueUsed 1}

shapingRequeueQueueUsedMax	OBJECT-TYPE
	SYNTAX	 Unsigned32
	MAX-ACCESS read-only
	STATUS current
	DESCRIPTION "Packets in requeue queue"

	::={shapingRequeueQueueUsed 3}

shapingDirectBytesPrio0	OBJECT IDENTIFIER ::={shaping 69}

shapingDirectBytesPrio0Val	OBJECT-TYPE
	SYNTAX	 Counter64
	MAX-ACCESS read-only
	STATUS current
	DESCRIPTION "Directly sent bytes (prio 0)"

	::={shapingDirectBytesPrio0 1}

shapingDirectBytesPrio0Mom	OBJECT-TYPE
	SYNTAX	 Unsigned32
	MAX-ACCESS read-only
	STATUS current
	DESCRIPTION "Directly sent bytes (prio 0)"

	::={shapingDirectBytesPrio0 2}

shapingDirectBytesPrio0Max	OBJECT-TYPE
	SYNTAX	 Counter64
	MAX-ACCESS read-only
	STATUS current
	DESCRIPTION "Directly sent bytes (prio 0)"

	::={shapingDirectBytesPrio0 3}

shapingDequeuedOdirs	OBJECT IDENTIFIER ::={shaping 70}

shapingDequeuedOdirsVal	OBJECT-TYPE
	SYNTAX	 Counter64
	MAX-ACCESS read-only
	STATUS current
	DESCRIPTION "Dequeued Odirs"

	::={shapingDequeuedOdirs 1}

shapingDequeuedOdirsMom	OBJECT-TYPE
	SYNTAX	 Unsigned32
	MAX-ACCESS read-only
	STATUS current
	DESCRIPTION "Dequeued Odirs"

	::={shapingDequeuedOdirs 2}

shapingDequeuedOdirsMax	OBJECT-TYPE
	SYNTAX	 Counter64
	MAX-ACCESS read-only
	STATUS current
	DESCRIPTION "Dequeued Odirs"

	::={shapingDequeuedOdirs 3}

shapingSkippedQsyncUpdates	OBJECT IDENTIFIER ::={shaping 71}

shapingSkippedQsyncUpdatesVal	OBJECT-TYPE
	SYNTAX	 Counter64
	MAX-ACCESS read-only
	STATUS current
	DESCRIPTION "Skipped qsync updates (no xfer)"

	::={shapingSkippedQsyncUpdates 1}

shapingSkippedQsyncUpdatesMom	OBJECT-TYPE
	SYNTAX	 Unsigned32
	MAX-ACCESS read-only
	STATUS current
	DESCRIPTION "Skipped qsync updates (no xfer)"

	::={shapingSkippedQsyncUpdates 2}

shapingSkippedQsyncUpdatesMax	OBJECT-TYPE
	SYNTAX	 Counter64
	MAX-ACCESS read-only
	STATUS current
	DESCRIPTION "Skipped qsync updates (no xfer)"

	::={shapingSkippedQsyncUpdates 3}

shapingObjectCopiesCreated	OBJECT IDENTIFIER ::={shaping 72}

shapingObjectCopiesCreatedVal	OBJECT-TYPE
	SYNTAX	 Counter64
	MAX-ACCESS read-only
	STATUS current
	DESCRIPTION "Object copies created"

	::={shapingObjectCopiesCreated 1}

shapingObjectCopiesCreatedMom	OBJECT-TYPE
	SYNTAX	 Unsigned32
	MAX-ACCESS read-only
	STATUS current
	DESCRIPTION "Object copies created"

	::={shapingObjectCopiesCreated 2}

shapingObjectCopiesCreatedMax	OBJECT-TYPE
	SYNTAX	 Counter64
	MAX-ACCESS read-only
	STATUS current
	DESCRIPTION "Object copies created"

	::={shapingObjectCopiesCreated 3}

pppoe	OBJECT IDENTIFIER ::={sysdiag 96}

pppoeShortPackets	OBJECT IDENTIFIER ::={pppoe 1}

pppoeShortPacketsVal	OBJECT-TYPE
	SYNTAX	 Counter64
	MAX-ACCESS read-only
	STATUS current
	DESCRIPTION "Short Packets dropped"

	::={pppoeShortPackets 1}

pppoeShortPacketsMom	OBJECT-TYPE
	SYNTAX	 Unsigned32
	MAX-ACCESS read-only
	STATUS current
	DESCRIPTION "Short Packets dropped"

	::={pppoeShortPackets 2}

pppoeShortPacketsMax	OBJECT-TYPE
	SYNTAX	 Counter64
	MAX-ACCESS read-only
	STATUS current
	DESCRIPTION "Short Packets dropped"

	::={pppoeShortPackets 3}

pppoeBadversionPackets	OBJECT IDENTIFIER ::={pppoe 2}

pppoeBadversionPacketsVal	OBJECT-TYPE
	SYNTAX	 Counter64
	MAX-ACCESS read-only
	STATUS current
	DESCRIPTION "Packets with unknown version"

	::={pppoeBadversionPackets 1}

pppoeBadversionPacketsMom	OBJECT-TYPE
	SYNTAX	 Unsigned32
	MAX-ACCESS read-only
	STATUS current
	DESCRIPTION "Packets with unknown version"

	::={pppoeBadversionPackets 2}

pppoeBadversionPacketsMax	OBJECT-TYPE
	SYNTAX	 Counter64
	MAX-ACCESS read-only
	STATUS current
	DESCRIPTION "Packets with unknown version"

	::={pppoeBadversionPackets 3}

pppoeControlPackets	OBJECT IDENTIFIER ::={pppoe 3}

pppoeControlPacketsVal	OBJECT-TYPE
	SYNTAX	 Counter64
	MAX-ACCESS read-only
	STATUS current
	DESCRIPTION "Control packets"

	::={pppoeControlPackets 1}

pppoeControlPacketsMom	OBJECT-TYPE
	SYNTAX	 Unsigned32
	MAX-ACCESS read-only
	STATUS current
	DESCRIPTION "Control packets"

	::={pppoeControlPackets 2}

pppoeControlPacketsMax	OBJECT-TYPE
	SYNTAX	 Counter64
	MAX-ACCESS read-only
	STATUS current
	DESCRIPTION "Control packets"

	::={pppoeControlPackets 3}

pppoeTruncatedPackets	OBJECT IDENTIFIER ::={pppoe 4}

pppoeTruncatedPacketsVal	OBJECT-TYPE
	SYNTAX	 Counter64
	MAX-ACCESS read-only
	STATUS current
	DESCRIPTION "Truncated packets dropped"

	::={pppoeTruncatedPackets 1}

pppoeTruncatedPacketsMom	OBJECT-TYPE
	SYNTAX	 Unsigned32
	MAX-ACCESS read-only
	STATUS current
	DESCRIPTION "Truncated packets dropped"

	::={pppoeTruncatedPackets 2}

pppoeTruncatedPacketsMax	OBJECT-TYPE
	SYNTAX	 Counter64
	MAX-ACCESS read-only
	STATUS current
	DESCRIPTION "Truncated packets dropped"

	::={pppoeTruncatedPackets 3}

pppoePaddedPackets	OBJECT IDENTIFIER ::={pppoe 5}

pppoePaddedPacketsVal	OBJECT-TYPE
	SYNTAX	 Counter64
	MAX-ACCESS read-only
	STATUS current
	DESCRIPTION "Padded packets"

	::={pppoePaddedPackets 1}

pppoePaddedPacketsMom	OBJECT-TYPE
	SYNTAX	 Unsigned32
	MAX-ACCESS read-only
	STATUS current
	DESCRIPTION "Padded packets"

	::={pppoePaddedPackets 2}

pppoePaddedPacketsMax	OBJECT-TYPE
	SYNTAX	 Counter64
	MAX-ACCESS read-only
	STATUS current
	DESCRIPTION "Padded packets"

	::={pppoePaddedPackets 3}

pppoeIpv4Packets	OBJECT IDENTIFIER ::={pppoe 6}

pppoeIpv4PacketsVal	OBJECT-TYPE
	SYNTAX	 Counter64
	MAX-ACCESS read-only
	STATUS current
	DESCRIPTION "IPv4 packets"

	::={pppoeIpv4Packets 1}

pppoeIpv4PacketsMom	OBJECT-TYPE
	SYNTAX	 Unsigned32
	MAX-ACCESS read-only
	STATUS current
	DESCRIPTION "IPv4 packets"

	::={pppoeIpv4Packets 2}

pppoeIpv4PacketsMax	OBJECT-TYPE
	SYNTAX	 Counter64
	MAX-ACCESS read-only
	STATUS current
	DESCRIPTION "IPv4 packets"

	::={pppoeIpv4Packets 3}

pppoeNonIpPackets	OBJECT IDENTIFIER ::={pppoe 7}

pppoeNonIpPacketsVal	OBJECT-TYPE
	SYNTAX	 Counter64
	MAX-ACCESS read-only
	STATUS current
	DESCRIPTION "Non IP packets"

	::={pppoeNonIpPackets 1}

pppoeNonIpPacketsMom	OBJECT-TYPE
	SYNTAX	 Unsigned32
	MAX-ACCESS read-only
	STATUS current
	DESCRIPTION "Non IP packets"

	::={pppoeNonIpPackets 2}

pppoeNonIpPacketsMax	OBJECT-TYPE
	SYNTAX	 Counter64
	MAX-ACCESS read-only
	STATUS current
	DESCRIPTION "Non IP packets"

	::={pppoeNonIpPackets 3}

pppoeIpv6Packets	OBJECT IDENTIFIER ::={pppoe 8}

pppoeIpv6PacketsVal	OBJECT-TYPE
	SYNTAX	 Counter64
	MAX-ACCESS read-only
	STATUS current
	DESCRIPTION "IPv6 packets"

	::={pppoeIpv6Packets 1}

pppoeIpv6PacketsMom	OBJECT-TYPE
	SYNTAX	 Unsigned32
	MAX-ACCESS read-only
	STATUS current
	DESCRIPTION "IPv6 packets"

	::={pppoeIpv6Packets 2}

pppoeIpv6PacketsMax	OBJECT-TYPE
	SYNTAX	 Counter64
	MAX-ACCESS read-only
	STATUS current
	DESCRIPTION "IPv6 packets"

	::={pppoeIpv6Packets 3}

general	OBJECT IDENTIFIER ::={sysdiag 104}

generalUptime	OBJECT IDENTIFIER ::={general 1}

generalUptimeVal	OBJECT-TYPE
	SYNTAX	 TimeTicks
	MAX-ACCESS read-only
	STATUS current
	DESCRIPTION "System uptime"

	::={generalUptime 1}

generalPldUptime	OBJECT IDENTIFIER ::={general 2}

generalPldUptimeVal	OBJECT-TYPE
	SYNTAX	 TimeTicks
	MAX-ACCESS read-only
	STATUS current
	DESCRIPTION "PLD uptime"

	::={generalPldUptime 1}

generalUser	OBJECT IDENTIFIER ::={general 3}

generalUserVal	OBJECT-TYPE
	SYNTAX	 Unsigned32
	MAX-ACCESS read-only
	STATUS current
	DESCRIPTION "CPU User (0)"

	::={generalUser 1}

generalUserMax	OBJECT-TYPE
	SYNTAX	 Unsigned32
	MAX-ACCESS read-only
	STATUS current
	DESCRIPTION "CPU User (0)"

	::={generalUser 3}

generalNice	OBJECT IDENTIFIER ::={general 4}

generalNiceVal	OBJECT-TYPE
	SYNTAX	 Unsigned32
	MAX-ACCESS read-only
	STATUS current
	DESCRIPTION "CPU Nice (0)"

	::={generalNice 1}

generalNiceMax	OBJECT-TYPE
	SYNTAX	 Unsigned32
	MAX-ACCESS read-only
	STATUS current
	DESCRIPTION "CPU Nice (0)"

	::={generalNice 3}

generalSystem	OBJECT IDENTIFIER ::={general 5}

generalSystemVal	OBJECT-TYPE
	SYNTAX	 Unsigned32
	MAX-ACCESS read-only
	STATUS current
	DESCRIPTION "CPU System (0)"

	::={generalSystem 1}

generalSystemMax	OBJECT-TYPE
	SYNTAX	 Unsigned32
	MAX-ACCESS read-only
	STATUS current
	DESCRIPTION "CPU System (0)"

	::={generalSystem 3}

generalUsage	OBJECT IDENTIFIER ::={general 6}

generalUsageVal	OBJECT-TYPE
	SYNTAX	 Unsigned32
	MAX-ACCESS read-only
	STATUS current
	DESCRIPTION "CPU Usage (0)"

	::={generalUsage 1}

generalUsageMax	OBJECT-TYPE
	SYNTAX	 Unsigned32
	MAX-ACCESS read-only
	STATUS current
	DESCRIPTION "CPU Usage (0)"

	::={generalUsage 3}

generalIowait	OBJECT IDENTIFIER ::={general 7}

generalIowaitVal	OBJECT-TYPE
	SYNTAX	 Unsigned32
	MAX-ACCESS read-only
	STATUS current
	DESCRIPTION "CPU IO Wait (0)"

	::={generalIowait 1}

generalIowaitMax	OBJECT-TYPE
	SYNTAX	 Unsigned32
	MAX-ACCESS read-only
	STATUS current
	DESCRIPTION "CPU IO Wait (0)"

	::={generalIowait 3}

generalIrq	OBJECT IDENTIFIER ::={general 8}

generalIrqVal	OBJECT-TYPE
	SYNTAX	 Unsigned32
	MAX-ACCESS read-only
	STATUS current
	DESCRIPTION "CPU IRQ (0)"

	::={generalIrq 1}

generalIrqMax	OBJECT-TYPE
	SYNTAX	 Unsigned32
	MAX-ACCESS read-only
	STATUS current
	DESCRIPTION "CPU IRQ (0)"

	::={generalIrq 3}

generalSoftirq	OBJECT IDENTIFIER ::={general 9}

generalSoftirqVal	OBJECT-TYPE
	SYNTAX	 Unsigned32
	MAX-ACCESS read-only
	STATUS current
	DESCRIPTION "CPU SoftIRQ (0)"

	::={generalSoftirq 1}

generalSoftirqMax	OBJECT-TYPE
	SYNTAX	 Unsigned32
	MAX-ACCESS read-only
	STATUS current
	DESCRIPTION "CPU SoftIRQ (0)"

	::={generalSoftirq 3}

generalUser1	OBJECT IDENTIFIER ::={general 10}

generalUser1Val	OBJECT-TYPE
	SYNTAX	 Unsigned32
	MAX-ACCESS read-only
	STATUS current
	DESCRIPTION "CPU User (1)"

	::={generalUser1 1}

generalUser1Max	OBJECT-TYPE
	SYNTAX	 Unsigned32
	MAX-ACCESS read-only
	STATUS current
	DESCRIPTION "CPU User (1)"

	::={generalUser1 3}

generalNice1	OBJECT IDENTIFIER ::={general 11}

generalNice1Val	OBJECT-TYPE
	SYNTAX	 Unsigned32
	MAX-ACCESS read-only
	STATUS current
	DESCRIPTION "CPU Nice (1)"

	::={generalNice1 1}

generalNice1Max	OBJECT-TYPE
	SYNTAX	 Unsigned32
	MAX-ACCESS read-only
	STATUS current
	DESCRIPTION "CPU Nice (1)"

	::={generalNice1 3}

generalSystem1	OBJECT IDENTIFIER ::={general 12}

generalSystem1Val	OBJECT-TYPE
	SYNTAX	 Unsigned32
	MAX-ACCESS read-only
	STATUS current
	DESCRIPTION "CPU System (1)"

	::={generalSystem1 1}

generalSystem1Max	OBJECT-TYPE
	SYNTAX	 Unsigned32
	MAX-ACCESS read-only
	STATUS current
	DESCRIPTION "CPU System (1)"

	::={generalSystem1 3}

generalUsage1	OBJECT IDENTIFIER ::={general 13}

generalUsage1Val	OBJECT-TYPE
	SYNTAX	 Unsigned32
	MAX-ACCESS read-only
	STATUS current
	DESCRIPTION "CPU Usage (1)"

	::={generalUsage1 1}

generalUsage1Max	OBJECT-TYPE
	SYNTAX	 Unsigned32
	MAX-ACCESS read-only
	STATUS current
	DESCRIPTION "CPU Usage (1)"

	::={generalUsage1 3}

generalIowait1	OBJECT IDENTIFIER ::={general 14}

generalIowait1Val	OBJECT-TYPE
	SYNTAX	 Unsigned32
	MAX-ACCESS read-only
	STATUS current
	DESCRIPTION "CPU IO Wait (1)"

	::={generalIowait1 1}

generalIowait1Max	OBJECT-TYPE
	SYNTAX	 Unsigned32
	MAX-ACCESS read-only
	STATUS current
	DESCRIPTION "CPU IO Wait (1)"

	::={generalIowait1 3}

generalIrq1	OBJECT IDENTIFIER ::={general 15}

generalIrq1Val	OBJECT-TYPE
	SYNTAX	 Unsigned32
	MAX-ACCESS read-only
	STATUS current
	DESCRIPTION "CPU IRQ (1)"

	::={generalIrq1 1}

generalIrq1Max	OBJECT-TYPE
	SYNTAX	 Unsigned32
	MAX-ACCESS read-only
	STATUS current
	DESCRIPTION "CPU IRQ (1)"

	::={generalIrq1 3}

generalSoftirq1	OBJECT IDENTIFIER ::={general 16}

generalSoftirq1Val	OBJECT-TYPE
	SYNTAX	 Unsigned32
	MAX-ACCESS read-only
	STATUS current
	DESCRIPTION "CPU SoftIRQ (1)"

	::={generalSoftirq1 1}

generalSoftirq1Max	OBJECT-TYPE
	SYNTAX	 Unsigned32
	MAX-ACCESS read-only
	STATUS current
	DESCRIPTION "CPU SoftIRQ (1)"

	::={generalSoftirq1 3}

generalSwapIn	OBJECT IDENTIFIER ::={general 17}

generalSwapInVal	OBJECT-TYPE
	SYNTAX	 Unsigned32
	MAX-ACCESS read-only
	STATUS current
	DESCRIPTION "Pages swapped in"

	::={generalSwapIn 1}

generalSwapInMax	OBJECT-TYPE
	SYNTAX	 Unsigned32
	MAX-ACCESS read-only
	STATUS current
	DESCRIPTION "Pages swapped in"

	::={generalSwapIn 3}

generalSwapOut	OBJECT IDENTIFIER ::={general 18}

generalSwapOutVal	OBJECT-TYPE
	SYNTAX	 Unsigned32
	MAX-ACCESS read-only
	STATUS current
	DESCRIPTION "Pages swapped out"

	::={generalSwapOut 1}

generalSwapOutMax	OBJECT-TYPE
	SYNTAX	 Unsigned32
	MAX-ACCESS read-only
	STATUS current
	DESCRIPTION "Pages swapped out"

	::={generalSwapOut 3}

generalClients	OBJECT IDENTIFIER ::={general 19}

generalClientsVal	OBJECT-TYPE
	SYNTAX	 Unsigned32
	MAX-ACCESS read-only
	STATUS current
	DESCRIPTION "Connected clients"

	::={generalClients 1}

generalClientsMax	OBJECT-TYPE
	SYNTAX	 Unsigned32
	MAX-ACCESS read-only
	STATUS current
	DESCRIPTION "Connected clients"

	::={generalClients 3}

generalClientsAll	OBJECT IDENTIFIER ::={general 20}

generalClientsAllVal	OBJECT-TYPE
	SYNTAX	 Unsigned32
	MAX-ACCESS read-only
	STATUS current
	DESCRIPTION "Connected full clients"

	::={generalClientsAll 1}

generalClientsAllMax	OBJECT-TYPE
	SYNTAX	 Unsigned32
	MAX-ACCESS read-only
	STATUS current
	DESCRIPTION "Connected full clients"

	::={generalClientsAll 3}

generalMemFree	OBJECT IDENTIFIER ::={general 21}

generalMemFreeVal	OBJECT-TYPE
	SYNTAX	 Unsigned32
	MAX-ACCESS read-only
	STATUS current
	DESCRIPTION "Memory free"

	::={generalMemFree 1}

generalMemFreeMax	OBJECT-TYPE
	SYNTAX	 Unsigned32
	MAX-ACCESS read-only
	STATUS current
	DESCRIPTION "Memory free"

	::={generalMemFree 3}

generalMemUsed	OBJECT IDENTIFIER ::={general 22}

generalMemUsedVal	OBJECT-TYPE
	SYNTAX	 Unsigned32
	MAX-ACCESS read-only
	STATUS current
	DESCRIPTION "Memory used"

	::={generalMemUsed 1}

generalMemUsedMax	OBJECT-TYPE
	SYNTAX	 Unsigned32
	MAX-ACCESS read-only
	STATUS current
	DESCRIPTION "Memory used"

	::={generalMemUsed 3}

generalVmallocFree	OBJECT IDENTIFIER ::={general 23}

generalVmallocFreeVal	OBJECT-TYPE
	SYNTAX	 Unsigned32
	MAX-ACCESS read-only
	STATUS current
	DESCRIPTION "VMalloc Memory free"

	::={generalVmallocFree 1}

generalVmallocFreeMax	OBJECT-TYPE
	SYNTAX	 Unsigned32
	MAX-ACCESS read-only
	STATUS current
	DESCRIPTION "VMalloc Memory free"

	::={generalVmallocFree 3}

generalVmallocUsed	OBJECT IDENTIFIER ::={general 24}

generalVmallocUsedVal	OBJECT-TYPE
	SYNTAX	 Unsigned32
	MAX-ACCESS read-only
	STATUS current
	DESCRIPTION "VMalloc memory used"

	::={generalVmallocUsed 1}

generalVmallocUsedMax	OBJECT-TYPE
	SYNTAX	 Unsigned32
	MAX-ACCESS read-only
	STATUS current
	DESCRIPTION "VMalloc memory used"

	::={generalVmallocUsed 3}

generalVmallocChunk	OBJECT IDENTIFIER ::={general 25}

generalVmallocChunkVal	OBJECT-TYPE
	SYNTAX	 Unsigned32
	MAX-ACCESS read-only
	STATUS current
	DESCRIPTION "VMalloc memory chunk"

	::={generalVmallocChunk 1}

generalVmallocChunkMax	OBJECT-TYPE
	SYNTAX	 Unsigned32
	MAX-ACCESS read-only
	STATUS current
	DESCRIPTION "VMalloc memory chunk"

	::={generalVmallocChunk 3}

generalHosts	OBJECT IDENTIFIER ::={general 29}

generalHostsVal	OBJECT-TYPE
	SYNTAX	 Unsigned32
	MAX-ACCESS read-only
	STATUS current
	DESCRIPTION "Hosts"

	::={generalHosts 1}

generalHostsMax	OBJECT-TYPE
	SYNTAX	 Unsigned32
	MAX-ACCESS read-only
	STATUS current
	DESCRIPTION "Hosts"

	::={generalHosts 3}

generalConnections	OBJECT IDENTIFIER ::={general 30}

generalConnectionsVal	OBJECT-TYPE
	SYNTAX	 Unsigned32
	MAX-ACCESS read-only
	STATUS current
	DESCRIPTION "Connections"

	::={generalConnections 1}

generalConnectionsMax	OBJECT-TYPE
	SYNTAX	 Unsigned32
	MAX-ACCESS read-only
	STATUS current
	DESCRIPTION "Connections"

	::={generalConnections 3}

generalVnos	OBJECT IDENTIFIER ::={general 31}

generalVnosVal	OBJECT-TYPE
	SYNTAX	 Unsigned32
	MAX-ACCESS read-only
	STATUS current
	DESCRIPTION "Visible NetObjects"

	::={generalVnos 1}

generalVnosMax	OBJECT-TYPE
	SYNTAX	 Unsigned32
	MAX-ACCESS read-only
	STATUS current
	DESCRIPTION "Visible NetObjects"

	::={generalVnos 3}

generalSystemHdUsage	OBJECT IDENTIFIER ::={general 32}

generalSystemHdUsageVal	OBJECT-TYPE
	SYNTAX	 Unsigned32
	MAX-ACCESS read-only
	STATUS current
	DESCRIPTION "System disk usage"

	::={generalSystemHdUsage 1}

generalSystemHdUsageMax	OBJECT-TYPE
	SYNTAX	 Unsigned32
	MAX-ACCESS read-only
	STATUS current
	DESCRIPTION "System disk usage"

	::={generalSystemHdUsage 3}

generalStatsHdUsage	OBJECT IDENTIFIER ::={general 33}

generalStatsHdUsageVal	OBJECT-TYPE
	SYNTAX	 Unsigned32
	MAX-ACCESS read-only
	STATUS current
	DESCRIPTION "Stats disk usage"

	::={generalStatsHdUsage 1}

generalStatsHdUsageMax	OBJECT-TYPE
	SYNTAX	 Unsigned32
	MAX-ACCESS read-only
	STATUS current
	DESCRIPTION "Stats disk usage"

	::={generalStatsHdUsage 3}

generalStatsHdSize	OBJECT IDENTIFIER ::={general 34}

generalStatsHdSizeVal	OBJECT-TYPE
	SYNTAX	 Unsigned32
	MAX-ACCESS read-only
	STATUS current
	DESCRIPTION "Stats disk size"

	::={generalStatsHdSize 1}

generalStatsHdSizeMax	OBJECT-TYPE
	SYNTAX	 Unsigned32
	MAX-ACCESS read-only
	STATUS current
	DESCRIPTION "Stats disk size"

	::={generalStatsHdSize 3}

generalSystemHdSize	OBJECT IDENTIFIER ::={general 35}

generalSystemHdSizeVal	OBJECT-TYPE
	SYNTAX	 Unsigned32
	MAX-ACCESS read-only
	STATUS current
	DESCRIPTION "System disk size"

	::={generalSystemHdSize 1}

generalSystemHdSizeMax	OBJECT-TYPE
	SYNTAX	 Unsigned32
	MAX-ACCESS read-only
	STATUS current
	DESCRIPTION "System disk size"

	::={generalSystemHdSize 3}

generalPlsdRingbufUsage	OBJECT IDENTIFIER ::={general 37}

generalPlsdRingbufUsageVal	OBJECT-TYPE
	SYNTAX	 Unsigned32
	MAX-ACCESS read-only
	STATUS current
	DESCRIPTION "PLSD buffer usage"

	::={generalPlsdRingbufUsage 1}

generalPlsdRingbufUsageMax	OBJECT-TYPE
	SYNTAX	 Unsigned32
	MAX-ACCESS read-only
	STATUS current
	DESCRIPTION "PLSD buffer usage"

	::={generalPlsdRingbufUsage 3}

generalActiveVnos	OBJECT IDENTIFIER ::={general 40}

generalActiveVnosVal	OBJECT-TYPE
	SYNTAX	 Unsigned32
	MAX-ACCESS read-only
	STATUS current
	DESCRIPTION "Active visible NetObjects"

	::={generalActiveVnos 1}

generalActiveVnosMax	OBJECT-TYPE
	SYNTAX	 Unsigned32
	MAX-ACCESS read-only
	STATUS current
	DESCRIPTION "Active visible NetObjects"

	::={generalActiveVnos 3}

generalDrdlRevision	OBJECT IDENTIFIER ::={general 42}

generalDrdlRevisionVal	OBJECT-TYPE
	SYNTAX	 Unsigned32
	MAX-ACCESS read-only
	STATUS current
	DESCRIPTION "DRDL revision"

	::={generalDrdlRevision 1}

generalDrdlRevisionMax	OBJECT-TYPE
	SYNTAX	 Unsigned32
	MAX-ACCESS read-only
	STATUS current
	DESCRIPTION "DRDL revision"

	::={generalDrdlRevision 3}

generalFailedNetobjects	OBJECT IDENTIFIER ::={general 43}

generalFailedNetobjectsVal	OBJECT-TYPE
	SYNTAX	 Counter64
	MAX-ACCESS read-only
	STATUS current
	DESCRIPTION "Visible netobject pool exhausted"

	::={generalFailedNetobjects 1}

generalFailedNetobjectsMom	OBJECT-TYPE
	SYNTAX	 Unsigned32
	MAX-ACCESS read-only
	STATUS current
	DESCRIPTION "Visible netobject pool exhausted"

	::={generalFailedNetobjects 2}

generalFailedNetobjectsMax	OBJECT-TYPE
	SYNTAX	 Counter64
	MAX-ACCESS read-only
	STATUS current
	DESCRIPTION "Visible netobject pool exhausted"

	::={generalFailedNetobjects 3}

generalFailedFullNetobjects	OBJECT IDENTIFIER ::={general 44}

generalFailedFullNetobjectsVal	OBJECT-TYPE
	SYNTAX	 Counter64
	MAX-ACCESS read-only
	STATUS current
	DESCRIPTION "Active visible netobject pool exhausted"

	::={generalFailedFullNetobjects 1}

generalFailedFullNetobjectsMom	OBJECT-TYPE
	SYNTAX	 Unsigned32
	MAX-ACCESS read-only
	STATUS current
	DESCRIPTION "Active visible netobject pool exhausted"

	::={generalFailedFullNetobjects 2}

generalFailedFullNetobjectsMax	OBJECT-TYPE
	SYNTAX	 Counter64
	MAX-ACCESS read-only
	STATUS current
	DESCRIPTION "Active visible netobject pool exhausted"

	::={generalFailedFullNetobjects 3}

generalStringCacheUsage	OBJECT IDENTIFIER ::={general 45}

generalStringCacheUsageVal	OBJECT-TYPE
	SYNTAX	 Unsigned32
	MAX-ACCESS read-only
	STATUS current
	DESCRIPTION "String cache usage"

	::={generalStringCacheUsage 1}

generalStringCacheUsageMax	OBJECT-TYPE
	SYNTAX	 Unsigned32
	MAX-ACCESS read-only
	STATUS current
	DESCRIPTION "String cache usage"

	::={generalStringCacheUsage 3}

generalUnaccountedPlsdIn	OBJECT IDENTIFIER ::={general 46}

generalUnaccountedPlsdInVal	OBJECT-TYPE
	SYNTAX	 Counter64
	MAX-ACCESS read-only
	STATUS current
	DESCRIPTION "Bytes in not accounted in plsd"

	::={generalUnaccountedPlsdIn 1}

generalUnaccountedPlsdInMom	OBJECT-TYPE
	SYNTAX	 Unsigned32
	MAX-ACCESS read-only
	STATUS current
	DESCRIPTION "Bytes in not accounted in plsd"

	::={generalUnaccountedPlsdIn 2}

generalUnaccountedPlsdInMax	OBJECT-TYPE
	SYNTAX	 Counter64
	MAX-ACCESS read-only
	STATUS current
	DESCRIPTION "Bytes in not accounted in plsd"

	::={generalUnaccountedPlsdIn 3}

generalUnaccountedPlsdOut	OBJECT IDENTIFIER ::={general 47}

generalUnaccountedPlsdOutVal	OBJECT-TYPE
	SYNTAX	 Counter64
	MAX-ACCESS read-only
	STATUS current
	DESCRIPTION "Bytes out not accounted in plsd"

	::={generalUnaccountedPlsdOut 1}

generalUnaccountedPlsdOutMom	OBJECT-TYPE
	SYNTAX	 Unsigned32
	MAX-ACCESS read-only
	STATUS current
	DESCRIPTION "Bytes out not accounted in plsd"

	::={generalUnaccountedPlsdOut 2}

generalUnaccountedPlsdOutMax	OBJECT-TYPE
	SYNTAX	 Counter64
	MAX-ACCESS read-only
	STATUS current
	DESCRIPTION "Bytes out not accounted in plsd"

	::={generalUnaccountedPlsdOut 3}

generalUnaccountedPlsdFlows	OBJECT IDENTIFIER ::={general 48}

generalUnaccountedPlsdFlowsVal	OBJECT-TYPE
	SYNTAX	 Counter64
	MAX-ACCESS read-only
	STATUS current
	DESCRIPTION "Flow updates not sent to plsd"

	::={generalUnaccountedPlsdFlows 1}

generalUnaccountedPlsdFlowsMom	OBJECT-TYPE
	SYNTAX	 Unsigned32
	MAX-ACCESS read-only
	STATUS current
	DESCRIPTION "Flow updates not sent to plsd"

	::={generalUnaccountedPlsdFlows 2}

generalUnaccountedPlsdFlowsMax	OBJECT-TYPE
	SYNTAX	 Counter64
	MAX-ACCESS read-only
	STATUS current
	DESCRIPTION "Flow updates not sent to plsd"

	::={generalUnaccountedPlsdFlows 3}

generalHostCacheExhausted	OBJECT IDENTIFIER ::={general 59}

generalHostCacheExhaustedVal	OBJECT-TYPE
	SYNTAX	 Counter64
	MAX-ACCESS read-only
	STATUS current
	DESCRIPTION "Hosts not created due to exhausted cache"

	::={generalHostCacheExhausted 1}

generalHostCacheExhaustedMom	OBJECT-TYPE
	SYNTAX	 Unsigned32
	MAX-ACCESS read-only
	STATUS current
	DESCRIPTION "Hosts not created due to exhausted cache"

	::={generalHostCacheExhausted 2}

generalHostCacheExhaustedMax	OBJECT-TYPE
	SYNTAX	 Counter64
	MAX-ACCESS read-only
	STATUS current
	DESCRIPTION "Hosts not created due to exhausted cache"

	::={generalHostCacheExhausted 3}

interface	OBJECT IDENTIFIER ::={sysdiag 120}

interfaceBytesToEngine	OBJECT IDENTIFIER ::={interface 8}

interfaceBytesToEngineVal	OBJECT-TYPE
	SYNTAX	 Counter64
	MAX-ACCESS read-only
	STATUS current
	DESCRIPTION "Sent to engine"

	::={interfaceBytesToEngine 1}

interfaceBytesToEngineMom	OBJECT-TYPE
	SYNTAX	 Unsigned32
	MAX-ACCESS read-only
	STATUS current
	DESCRIPTION "Sent to engine"

	::={interfaceBytesToEngine 2}

interfaceBytesToEngineMax	OBJECT-TYPE
	SYNTAX	 Counter64
	MAX-ACCESS read-only
	STATUS current
	DESCRIPTION "Sent to engine"

	::={interfaceBytesToEngine 3}

interfaceBytesFromEngine	OBJECT IDENTIFIER ::={interface 9}

interfaceBytesFromEngineVal	OBJECT-TYPE
	SYNTAX	 Counter64
	MAX-ACCESS read-only
	STATUS current
	DESCRIPTION "Received from engine"

	::={interfaceBytesFromEngine 1}

interfaceBytesFromEngineMom	OBJECT-TYPE
	SYNTAX	 Unsigned32
	MAX-ACCESS read-only
	STATUS current
	DESCRIPTION "Received from engine"

	::={interfaceBytesFromEngine 2}

interfaceBytesFromEngineMax	OBJECT-TYPE
	SYNTAX	 Counter64
	MAX-ACCESS read-only
	STATUS current
	DESCRIPTION "Received from engine"

	::={interfaceBytesFromEngine 3}

interfaceFlowNewMissed	OBJECT IDENTIFIER ::={interface 10}

interfaceFlowNewMissedVal	OBJECT-TYPE
	SYNTAX	 Counter64
	MAX-ACCESS read-only
	STATUS current
	DESCRIPTION "New flows missed"

	::={interfaceFlowNewMissed 1}

interfaceFlowNewMissedMom	OBJECT-TYPE
	SYNTAX	 Unsigned32
	MAX-ACCESS read-only
	STATUS current
	DESCRIPTION "New flows missed"

	::={interfaceFlowNewMissed 2}

interfaceFlowNewMissedMax	OBJECT-TYPE
	SYNTAX	 Counter64
	MAX-ACCESS read-only
	STATUS current
	DESCRIPTION "New flows missed"

	::={interfaceFlowNewMissed 3}

interfaceFlowUpdMissed	OBJECT IDENTIFIER ::={interface 11}

interfaceFlowUpdMissedVal	OBJECT-TYPE
	SYNTAX	 Counter64
	MAX-ACCESS read-only
	STATUS current
	DESCRIPTION "Flow updates missed"

	::={interfaceFlowUpdMissed 1}

interfaceFlowUpdMissedMom	OBJECT-TYPE
	SYNTAX	 Unsigned32
	MAX-ACCESS read-only
	STATUS current
	DESCRIPTION "Flow updates missed"

	::={interfaceFlowUpdMissed 2}

interfaceFlowUpdMissedMax	OBJECT-TYPE
	SYNTAX	 Counter64
	MAX-ACCESS read-only
	STATUS current
	DESCRIPTION "Flow updates missed"

	::={interfaceFlowUpdMissed 3}

interfaceFlowNew	OBJECT IDENTIFIER ::={interface 12}

interfaceFlowNewVal	OBJECT-TYPE
	SYNTAX	 Counter64
	MAX-ACCESS read-only
	STATUS current
	DESCRIPTION "New flows"

	::={interfaceFlowNew 1}

interfaceFlowNewMom	OBJECT-TYPE
	SYNTAX	 Unsigned32
	MAX-ACCESS read-only
	STATUS current
	DESCRIPTION "New flows"

	::={interfaceFlowNew 2}

interfaceFlowNewMax	OBJECT-TYPE
	SYNTAX	 Counter64
	MAX-ACCESS read-only
	STATUS current
	DESCRIPTION "New flows"

	::={interfaceFlowNew 3}

interfaceFlowHostnameAllocFail	OBJECT IDENTIFIER ::={interface 13}

interfaceFlowHostnameAllocFailVal	OBJECT-TYPE
	SYNTAX	 Counter64
	MAX-ACCESS read-only
	STATUS current
	DESCRIPTION "Hostname allocation failures"

	::={interfaceFlowHostnameAllocFail 1}

interfaceFlowHostnameAllocFailMom	OBJECT-TYPE
	SYNTAX	 Unsigned32
	MAX-ACCESS read-only
	STATUS current
	DESCRIPTION "Hostname allocation failures"

	::={interfaceFlowHostnameAllocFail 2}

interfaceFlowHostnameAllocFailMax	OBJECT-TYPE
	SYNTAX	 Counter64
	MAX-ACCESS read-only
	STATUS current
	DESCRIPTION "Hostname allocation failures"

	::={interfaceFlowHostnameAllocFail 3}

interfaceFlowUpdReordered	OBJECT IDENTIFIER ::={interface 14}

interfaceFlowUpdReorderedVal	OBJECT-TYPE
	SYNTAX	 Counter64
	MAX-ACCESS read-only
	STATUS current
	DESCRIPTION "Reordered flow updates"

	::={interfaceFlowUpdReordered 1}

interfaceFlowUpdReorderedMom	OBJECT-TYPE
	SYNTAX	 Unsigned32
	MAX-ACCESS read-only
	STATUS current
	DESCRIPTION "Reordered flow updates"

	::={interfaceFlowUpdReordered 2}

interfaceFlowUpdReorderedMax	OBJECT-TYPE
	SYNTAX	 Counter64
	MAX-ACCESS read-only
	STATUS current
	DESCRIPTION "Reordered flow updates"

	::={interfaceFlowUpdReordered 3}

dynnetobjs	OBJECT IDENTIFIER ::={sysdiag 121}

dynamicnetobjectFailedInserts	OBJECT IDENTIFIER ::={dynnetobjs 1}

dynamicnetobjectFailedInsertsVal	OBJECT-TYPE
	SYNTAX	 Counter64
	MAX-ACCESS read-only
	STATUS current
	DESCRIPTION "Failed inserts (too many dynamic items)"

	::={dynamicnetobjectFailedInserts 1}

dynamicnetobjectFailedInsertsMom	OBJECT-TYPE
	SYNTAX	 Unsigned32
	MAX-ACCESS read-only
	STATUS current
	DESCRIPTION "Failed inserts (too many dynamic items)"

	::={dynamicnetobjectFailedInserts 2}

dynamicnetobjectFailedInsertsMax	OBJECT-TYPE
	SYNTAX	 Counter64
	MAX-ACCESS read-only
	STATUS current
	DESCRIPTION "Failed inserts (too many dynamic items)"

	::={dynamicnetobjectFailedInserts 3}

dynamicnetobjectListItems	OBJECT IDENTIFIER ::={dynnetobjs 2}

dynamicnetobjectListItemsVal	OBJECT-TYPE
	SYNTAX	 Unsigned32
	MAX-ACCESS read-only
	STATUS current
	DESCRIPTION "Items returned from last PLDB query"

	::={dynamicnetobjectListItems 1}

dynamicnetobjectListItemsMax	OBJECT-TYPE
	SYNTAX	 Unsigned32
	MAX-ACCESS read-only
	STATUS current
	DESCRIPTION "Items returned from last PLDB query"

	::={dynamicnetobjectListItems 3}

dynamicnetobjectRemoveSucceeded	OBJECT IDENTIFIER ::={dynnetobjs 3}

dynamicnetobjectRemoveSucceededVal	OBJECT-TYPE
	SYNTAX	 Counter64
	MAX-ACCESS read-only
	STATUS current
	DESCRIPTION "Remove calls succeeded"

	::={dynamicnetobjectRemoveSucceeded 1}

dynamicnetobjectRemoveSucceededMom	OBJECT-TYPE
	SYNTAX	 Unsigned32
	MAX-ACCESS read-only
	STATUS current
	DESCRIPTION "Remove calls succeeded"

	::={dynamicnetobjectRemoveSucceeded 2}

dynamicnetobjectRemoveSucceededMax	OBJECT-TYPE
	SYNTAX	 Counter64
	MAX-ACCESS read-only
	STATUS current
	DESCRIPTION "Remove calls succeeded"

	::={dynamicnetobjectRemoveSucceeded 3}

dynamicnetobjectRemoveFailed	OBJECT IDENTIFIER ::={dynnetobjs 4}

dynamicnetobjectRemoveFailedVal	OBJECT-TYPE
	SYNTAX	 Counter64
	MAX-ACCESS read-only
	STATUS current
	DESCRIPTION "Remove calls failed"

	::={dynamicnetobjectRemoveFailed 1}

dynamicnetobjectRemoveFailedMom	OBJECT-TYPE
	SYNTAX	 Unsigned32
	MAX-ACCESS read-only
	STATUS current
	DESCRIPTION "Remove calls failed"

	::={dynamicnetobjectRemoveFailed 2}

dynamicnetobjectRemoveFailedMax	OBJECT-TYPE
	SYNTAX	 Counter64
	MAX-ACCESS read-only
	STATUS current
	DESCRIPTION "Remove calls failed"

	::={dynamicnetobjectRemoveFailed 3}

dynamicnetobjectCurrentIpCount	OBJECT IDENTIFIER ::={dynnetobjs 5}

dynamicnetobjectCurrentIpCountVal	OBJECT-TYPE
	SYNTAX	 Unsigned32
	MAX-ACCESS read-only
	STATUS current
	DESCRIPTION "IPs in table"

	::={dynamicnetobjectCurrentIpCount 1}

dynamicnetobjectCurrentIpCountMax	OBJECT-TYPE
	SYNTAX	 Unsigned32
	MAX-ACCESS read-only
	STATUS current
	DESCRIPTION "IPs in table"

	::={dynamicnetobjectCurrentIpCount 3}

dynamicnetobjectCurrentCount	OBJECT IDENTIFIER ::={dynnetobjs 6}

dynamicnetobjectCurrentCountVal	OBJECT-TYPE
	SYNTAX	 Unsigned32
	MAX-ACCESS read-only
	STATUS current
	DESCRIPTION "Items in table"

	::={dynamicnetobjectCurrentCount 1}

dynamicnetobjectCurrentCountMax	OBJECT-TYPE
	SYNTAX	 Unsigned32
	MAX-ACCESS read-only
	STATUS current
	DESCRIPTION "Items in table"

	::={dynamicnetobjectCurrentCount 3}

dynamicnetobjectRemovePldbFailed	OBJECT IDENTIFIER ::={dynnetobjs 7}

dynamicnetobjectRemovePldbFailedVal	OBJECT-TYPE
	SYNTAX	 Counter64
	MAX-ACCESS read-only
	STATUS current
	DESCRIPTION "Remove calls failed in PLDB"

	::={dynamicnetobjectRemovePldbFailed 1}

dynamicnetobjectRemovePldbFailedMom	OBJECT-TYPE
	SYNTAX	 Unsigned32
	MAX-ACCESS read-only
	STATUS current
	DESCRIPTION "Remove calls failed in PLDB"

	::={dynamicnetobjectRemovePldbFailed 2}

dynamicnetobjectRemovePldbFailedMax	OBJECT-TYPE
	SYNTAX	 Counter64
	MAX-ACCESS read-only
	STATUS current
	DESCRIPTION "Remove calls failed in PLDB"

	::={dynamicnetobjectRemovePldbFailed 3}

dynamicnetobjectAddSucceeded	OBJECT IDENTIFIER ::={dynnetobjs 8}

dynamicnetobjectAddSucceededVal	OBJECT-TYPE
	SYNTAX	 Counter64
	MAX-ACCESS read-only
	STATUS current
	DESCRIPTION "Add calls succeeded"

	::={dynamicnetobjectAddSucceeded 1}

dynamicnetobjectAddSucceededMom	OBJECT-TYPE
	SYNTAX	 Unsigned32
	MAX-ACCESS read-only
	STATUS current
	DESCRIPTION "Add calls succeeded"

	::={dynamicnetobjectAddSucceeded 2}

dynamicnetobjectAddSucceededMax	OBJECT-TYPE
	SYNTAX	 Counter64
	MAX-ACCESS read-only
	STATUS current
	DESCRIPTION "Add calls succeeded"

	::={dynamicnetobjectAddSucceeded 3}

dynamicnetobjectAddFailed	OBJECT IDENTIFIER ::={dynnetobjs 9}

dynamicnetobjectAddFailedVal	OBJECT-TYPE
	SYNTAX	 Counter64
	MAX-ACCESS read-only
	STATUS current
	DESCRIPTION "Add calls failed"

	::={dynamicnetobjectAddFailed 1}

dynamicnetobjectAddFailedMom	OBJECT-TYPE
	SYNTAX	 Unsigned32
	MAX-ACCESS read-only
	STATUS current
	DESCRIPTION "Add calls failed"

	::={dynamicnetobjectAddFailed 2}

dynamicnetobjectAddFailedMax	OBJECT-TYPE
	SYNTAX	 Counter64
	MAX-ACCESS read-only
	STATUS current
	DESCRIPTION "Add calls failed"

	::={dynamicnetobjectAddFailed 3}

dynamicnetobjectInsertPldbFailed	OBJECT IDENTIFIER ::={dynnetobjs 10}

dynamicnetobjectInsertPldbFailedVal	OBJECT-TYPE
	SYNTAX	 Counter64
	MAX-ACCESS read-only
	STATUS current
	DESCRIPTION "Add calls failed in PLDB"

	::={dynamicnetobjectInsertPldbFailed 1}

dynamicnetobjectInsertPldbFailedMom	OBJECT-TYPE
	SYNTAX	 Unsigned32
	MAX-ACCESS read-only
	STATUS current
	DESCRIPTION "Add calls failed in PLDB"

	::={dynamicnetobjectInsertPldbFailed 2}

dynamicnetobjectInsertPldbFailedMax	OBJECT-TYPE
	SYNTAX	 Counter64
	MAX-ACCESS read-only
	STATUS current
	DESCRIPTION "Add calls failed in PLDB"

	::={dynamicnetobjectInsertPldbFailed 3}

dynamicnetobjectAddCalls	OBJECT IDENTIFIER ::={dynnetobjs 11}

dynamicnetobjectAddCallsVal	OBJECT-TYPE
	SYNTAX	 Counter64
	MAX-ACCESS read-only
	STATUS current
	DESCRIPTION "Add calls attempted"

	::={dynamicnetobjectAddCalls 1}

dynamicnetobjectAddCallsMom	OBJECT-TYPE
	SYNTAX	 Unsigned32
	MAX-ACCESS read-only
	STATUS current
	DESCRIPTION "Add calls attempted"

	::={dynamicnetobjectAddCalls 2}

dynamicnetobjectAddCallsMax	OBJECT-TYPE
	SYNTAX	 Counter64
	MAX-ACCESS read-only
	STATUS current
	DESCRIPTION "Add calls attempted"

	::={dynamicnetobjectAddCalls 3}

dynamicnetobjectRemoveCalls	OBJECT IDENTIFIER ::={dynnetobjs 12}

dynamicnetobjectRemoveCallsVal	OBJECT-TYPE
	SYNTAX	 Counter64
	MAX-ACCESS read-only
	STATUS current
	DESCRIPTION "Remove calls attempted"

	::={dynamicnetobjectRemoveCalls 1}

dynamicnetobjectRemoveCallsMom	OBJECT-TYPE
	SYNTAX	 Unsigned32
	MAX-ACCESS read-only
	STATUS current
	DESCRIPTION "Remove calls attempted"

	::={dynamicnetobjectRemoveCalls 2}

dynamicnetobjectRemoveCallsMax	OBJECT-TYPE
	SYNTAX	 Counter64
	MAX-ACCESS read-only
	STATUS current
	DESCRIPTION "Remove calls attempted"

	::={dynamicnetobjectRemoveCalls 3}

dynamicnetobjectUnqualifiedNoRemoveCalls	OBJECT IDENTIFIER ::={dynnetobjs 13}

dynamicnetobjectUnqualifiedNoRemoveCallsVal	OBJECT-TYPE
	SYNTAX	 Counter64
	MAX-ACCESS read-only
	STATUS current
	DESCRIPTION "Remove calls for unknown netobject"

	::={dynamicnetobjectUnqualifiedNoRemoveCalls 1}

dynamicnetobjectUnqualifiedNoRemoveCallsMom	OBJECT-TYPE
	SYNTAX	 Unsigned32
	MAX-ACCESS read-only
	STATUS current
	DESCRIPTION "Remove calls for unknown netobject"

	::={dynamicnetobjectUnqualifiedNoRemoveCalls 2}

dynamicnetobjectUnqualifiedNoRemoveCallsMax	OBJECT-TYPE
	SYNTAX	 Counter64
	MAX-ACCESS read-only
	STATUS current
	DESCRIPTION "Remove calls for unknown netobject"

	::={dynamicnetobjectUnqualifiedNoRemoveCalls 3}

dynamicnetobjectUnqualifiedIpRemoveCalls	OBJECT IDENTIFIER ::={dynnetobjs 14}

dynamicnetobjectUnqualifiedIpRemoveCallsVal	OBJECT-TYPE
	SYNTAX	 Counter64
	MAX-ACCESS read-only
	STATUS current
	DESCRIPTION "Remove calls for unknown IP"

	::={dynamicnetobjectUnqualifiedIpRemoveCalls 1}

dynamicnetobjectUnqualifiedIpRemoveCallsMom	OBJECT-TYPE
	SYNTAX	 Unsigned32
	MAX-ACCESS read-only
	STATUS current
	DESCRIPTION "Remove calls for unknown IP"

	::={dynamicnetobjectUnqualifiedIpRemoveCalls 2}

dynamicnetobjectUnqualifiedIpRemoveCallsMax	OBJECT-TYPE
	SYNTAX	 Counter64
	MAX-ACCESS read-only
	STATUS current
	DESCRIPTION "Remove calls for unknown IP"

	::={dynamicnetobjectUnqualifiedIpRemoveCalls 3}

dynamicnetobjectListCalls	OBJECT IDENTIFIER ::={dynnetobjs 15}

dynamicnetobjectListCallsVal	OBJECT-TYPE
	SYNTAX	 Counter64
	MAX-ACCESS read-only
	STATUS current
	DESCRIPTION "List calls attempted"

	::={dynamicnetobjectListCalls 1}

dynamicnetobjectListCallsMom	OBJECT-TYPE
	SYNTAX	 Unsigned32
	MAX-ACCESS read-only
	STATUS current
	DESCRIPTION "List calls attempted"

	::={dynamicnetobjectListCalls 2}

dynamicnetobjectListCallsMax	OBJECT-TYPE
	SYNTAX	 Counter64
	MAX-ACCESS read-only
	STATUS current
	DESCRIPTION "List calls attempted"

	::={dynamicnetobjectListCalls 3}

dynamicnetobjectListItemsReturned	OBJECT IDENTIFIER ::={dynnetobjs 16}

dynamicnetobjectListItemsReturnedVal	OBJECT-TYPE
	SYNTAX	 Counter64
	MAX-ACCESS read-only
	STATUS current
	DESCRIPTION "Items returned from list calls"

	::={dynamicnetobjectListItemsReturned 1}

dynamicnetobjectListItemsReturnedMom	OBJECT-TYPE
	SYNTAX	 Unsigned32
	MAX-ACCESS read-only
	STATUS current
	DESCRIPTION "Items returned from list calls"

	::={dynamicnetobjectListItemsReturned 2}

dynamicnetobjectListItemsReturnedMax	OBJECT-TYPE
	SYNTAX	 Counter64
	MAX-ACCESS read-only
	STATUS current
	DESCRIPTION "Items returned from list calls"

	::={dynamicnetobjectListItemsReturned 3}

dynamicnetobjectSubscriberConflicts	OBJECT IDENTIFIER ::={dynnetobjs 17}

dynamicnetobjectSubscriberConflictsVal	OBJECT-TYPE
	SYNTAX	 Counter64
	MAX-ACCESS read-only
	STATUS current
	DESCRIPTION "Conflicting subscriber names"

	::={dynamicnetobjectSubscriberConflicts 1}

dynamicnetobjectSubscriberConflictsMom	OBJECT-TYPE
	SYNTAX	 Unsigned32
	MAX-ACCESS read-only
	STATUS current
	DESCRIPTION "Conflicting subscriber names"

	::={dynamicnetobjectSubscriberConflicts 2}

dynamicnetobjectSubscriberConflictsMax	OBJECT-TYPE
	SYNTAX	 Counter64
	MAX-ACCESS read-only
	STATUS current
	DESCRIPTION "Conflicting subscriber names"

	::={dynamicnetobjectSubscriberConflicts 3}

dynamicnetobjectSubscriberCount	OBJECT IDENTIFIER ::={dynnetobjs 18}

dynamicnetobjectSubscriberCountVal	OBJECT-TYPE
	SYNTAX	 Unsigned32
	MAX-ACCESS read-only
	STATUS current
	DESCRIPTION "Number of unique subscriber names"

	::={dynamicnetobjectSubscriberCount 1}

dynamicnetobjectSubscriberCountMax	OBJECT-TYPE
	SYNTAX	 Unsigned32
	MAX-ACCESS read-only
	STATUS current
	DESCRIPTION "Number of unique subscriber names"

	::={dynamicnetobjectSubscriberCount 3}

dynamicnetobjectSubscriberTooMany	OBJECT IDENTIFIER ::={dynnetobjs 19}

dynamicnetobjectSubscriberTooManyVal	OBJECT-TYPE
	SYNTAX	 Counter64
	MAX-ACCESS read-only
	STATUS current
	DESCRIPTION "Too many unique subscriber names failures"

	::={dynamicnetobjectSubscriberTooMany 1}

dynamicnetobjectSubscriberTooManyMom	OBJECT-TYPE
	SYNTAX	 Unsigned32
	MAX-ACCESS read-only
	STATUS current
	DESCRIPTION "Too many unique subscriber names failures"

	::={dynamicnetobjectSubscriberTooMany 2}

dynamicnetobjectSubscriberTooManyMax	OBJECT-TYPE
	SYNTAX	 Counter64
	MAX-ACCESS read-only
	STATUS current
	DESCRIPTION "Too many unique subscriber names failures"

	::={dynamicnetobjectSubscriberTooMany 3}

dynamicnetobjectSqliteMemoryUsed	OBJECT IDENTIFIER ::={dynnetobjs 20}

dynamicnetobjectSqliteMemoryUsedVal	OBJECT-TYPE
	SYNTAX	 Unsigned32
	MAX-ACCESS read-only
	STATUS obsolete
	DESCRIPTION "Add requests in queue"

	::={dynamicnetobjectSqliteMemoryUsed 1}

dynamicnetobjectSqliteMemoryUsedMax	OBJECT-TYPE
	SYNTAX	 Unsigned32
	MAX-ACCESS read-only
	STATUS obsolete
	DESCRIPTION "Add requests in queue"

	::={dynamicnetobjectSqliteMemoryUsed 3}

dynamicnetobjectPendingAdds	OBJECT IDENTIFIER ::={dynnetobjs 21}

dynamicnetobjectPendingAddsVal	OBJECT-TYPE
	SYNTAX	 Unsigned32
	MAX-ACCESS read-only
	STATUS obsolete
	DESCRIPTION "Memory used by the dynitems sqlite thread"

	::={dynamicnetobjectPendingAdds 1}

dynamicnetobjectPendingAddsMax	OBJECT-TYPE
	SYNTAX	 Unsigned32
	MAX-ACCESS read-only
	STATUS obsolete
	DESCRIPTION "Memory used by the dynitems sqlite thread"

	::={dynamicnetobjectPendingAdds 3}

bgp	OBJECT IDENTIFIER ::={sysdiag 122}

bgpUpdates	OBJECT IDENTIFIER ::={bgp 1}

bgpUpdatesVal	OBJECT-TYPE
	SYNTAX	 Unsigned32
	MAX-ACCESS read-only
	STATUS current
	DESCRIPTION "Updates received"

	::={bgpUpdates 1}

bgpUpdatesMax	OBJECT-TYPE
	SYNTAX	 Unsigned32
	MAX-ACCESS read-only
	STATUS current
	DESCRIPTION "Updates received"

	::={bgpUpdates 3}

bgpPrefixes	OBJECT IDENTIFIER ::={bgp 2}

bgpPrefixesVal	OBJECT-TYPE
	SYNTAX	 Unsigned32
	MAX-ACCESS read-only
	STATUS current
	DESCRIPTION "Number of prefixes"

	::={bgpPrefixes 1}

bgpPrefixesMax	OBJECT-TYPE
	SYNTAX	 Unsigned32
	MAX-ACCESS read-only
	STATUS current
	DESCRIPTION "Number of prefixes"

	::={bgpPrefixes 3}

bgpPaths	OBJECT IDENTIFIER ::={bgp 3}

bgpPathsVal	OBJECT-TYPE
	SYNTAX	 Unsigned32
	MAX-ACCESS read-only
	STATUS current
	DESCRIPTION "Number of unique paths"

	::={bgpPaths 1}

bgpPathsMax	OBJECT-TYPE
	SYNTAX	 Unsigned32
	MAX-ACCESS read-only
	STATUS current
	DESCRIPTION "Number of unique paths"

	::={bgpPaths 3}

bgpUptime	OBJECT IDENTIFIER ::={bgp 4}

bgpUptimeVal	OBJECT-TYPE
	SYNTAX	 TimeTicks
	MAX-ACCESS read-only
	STATUS current
	DESCRIPTION "Connection uptime"

	::={bgpUptime 1}

bgpConvresionTime	OBJECT IDENTIFIER ::={bgp 5}

bgpConvresionTimeVal	OBJECT-TYPE
	SYNTAX	 Unsigned32
	MAX-ACCESS read-only
	STATUS current
	DESCRIPTION "Time to convert lookup tree"

	::={bgpConvresionTime 1}

bgpConvresionTimeMax	OBJECT-TYPE
	SYNTAX	 Unsigned32
	MAX-ACCESS read-only
	STATUS current
	DESCRIPTION "Time to convert lookup tree"

	::={bgpConvresionTime 3}

bgpSendTime	OBJECT IDENTIFIER ::={bgp 6}

bgpSendTimeVal	OBJECT-TYPE
	SYNTAX	 Unsigned32
	MAX-ACCESS read-only
	STATUS current
	DESCRIPTION "Time to update lookup tree"

	::={bgpSendTime 1}

bgpSendTimeMax	OBJECT-TYPE
	SYNTAX	 Unsigned32
	MAX-ACCESS read-only
	STATUS current
	DESCRIPTION "Time to update lookup tree"

	::={bgpSendTime 3}

bgpReplaces	OBJECT IDENTIFIER ::={bgp 7}

bgpReplacesVal	OBJECT-TYPE
	SYNTAX	 Unsigned32
	MAX-ACCESS read-only
	STATUS current
	DESCRIPTION "Total count of announces without withdraw"

	::={bgpReplaces 1}

bgpReplacesMax	OBJECT-TYPE
	SYNTAX	 Unsigned32
	MAX-ACCESS read-only
	STATUS current
	DESCRIPTION "Total count of announces without withdraw"

	::={bgpReplaces 3}

bgpWithdraws	OBJECT IDENTIFIER ::={bgp 8}

bgpWithdrawsVal	OBJECT-TYPE
	SYNTAX	 Unsigned32
	MAX-ACCESS read-only
	STATUS current
	DESCRIPTION "Total count of withdrawn routes"

	::={bgpWithdraws 1}

bgpWithdrawsMax	OBJECT-TYPE
	SYNTAX	 Unsigned32
	MAX-ACCESS read-only
	STATUS current
	DESCRIPTION "Total count of withdrawn routes"

	::={bgpWithdraws 3}

bgpAnnounces	OBJECT IDENTIFIER ::={bgp 9}

bgpAnnouncesVal	OBJECT-TYPE
	SYNTAX	 Unsigned32
	MAX-ACCESS read-only
	STATUS current
	DESCRIPTION "Total count of announced routes"

	::={bgpAnnounces 1}

bgpAnnouncesMax	OBJECT-TYPE
	SYNTAX	 Unsigned32
	MAX-ACCESS read-only
	STATUS current
	DESCRIPTION "Total count of announced routes"

	::={bgpAnnounces 3}

bgpReconnects	OBJECT IDENTIFIER ::={bgp 10}

bgpReconnectsVal	OBJECT-TYPE
	SYNTAX	 Unsigned32
	MAX-ACCESS read-only
	STATUS current
	DESCRIPTION "Total number of reconnects"

	::={bgpReconnects 1}

bgpReconnectsMax	OBJECT-TYPE
	SYNTAX	 Unsigned32
	MAX-ACCESS read-only
	STATUS current
	DESCRIPTION "Total number of reconnects"

	::={bgpReconnects 3}

bgpPathConvTime	OBJECT IDENTIFIER ::={bgp 11}

bgpPathConvTimeVal	OBJECT-TYPE
	SYNTAX	 Unsigned32
	MAX-ACCESS read-only
	STATUS current
	DESCRIPTION "Time to convert/send paths"

	::={bgpPathConvTime 1}

bgpPathConvTimeMax	OBJECT-TYPE
	SYNTAX	 Unsigned32
	MAX-ACCESS read-only
	STATUS current
	DESCRIPTION "Time to convert/send paths"

	::={bgpPathConvTime 3}

bgpRecyclePaths	OBJECT IDENTIFIER ::={bgp 12}

bgpRecyclePathsVal	OBJECT-TYPE
	SYNTAX	 Unsigned32
	MAX-ACCESS read-only
	STATUS current
	DESCRIPTION "Number of paths waiting for garbage collection"

	::={bgpRecyclePaths 1}

bgpRecyclePathsMax	OBJECT-TYPE
	SYNTAX	 Unsigned32
	MAX-ACCESS read-only
	STATUS current
	DESCRIPTION "Number of paths waiting for garbage collection"

	::={bgpRecyclePaths 3}

bgpFreelistPaths	OBJECT IDENTIFIER ::={bgp 13}

bgpFreelistPathsVal	OBJECT-TYPE
	SYNTAX	 Unsigned32
	MAX-ACCESS read-only
	STATUS current
	DESCRIPTION "Number of paths in freelist"

	::={bgpFreelistPaths 1}

bgpFreelistPathsMax	OBJECT-TYPE
	SYNTAX	 Unsigned32
	MAX-ACCESS read-only
	STATUS current
	DESCRIPTION "Number of paths in freelist"

	::={bgpFreelistPaths 3}

bgpBalanceTime	OBJECT IDENTIFIER ::={bgp 14}

bgpBalanceTimeVal	OBJECT-TYPE
	SYNTAX	 Unsigned32
	MAX-ACCESS read-only
	STATUS current
	DESCRIPTION "Time to rebalance tree"

	::={bgpBalanceTime 1}

bgpBalanceTimeMax	OBJECT-TYPE
	SYNTAX	 Unsigned32
	MAX-ACCESS read-only
	STATUS current
	DESCRIPTION "Time to rebalance tree"

	::={bgpBalanceTime 3}

bgpCommunityTooSmall	OBJECT IDENTIFIER ::={bgp 24}

bgpCommunityTooSmallVal	OBJECT-TYPE
	SYNTAX	 Unsigned32
	MAX-ACCESS read-only
	STATUS current
	DESCRIPTION "Number of community updates received that exceed PL_CONFIG_BGP_MAX_COMMUNITIES"

	::={bgpCommunityTooSmall 1}

bgpCommunityTooSmallMax	OBJECT-TYPE
	SYNTAX	 Unsigned32
	MAX-ACCESS read-only
	STATUS current
	DESCRIPTION "Number of community updates received that exceed PL_CONFIG_BGP_MAX_COMMUNITIES"

	::={bgpCommunityTooSmall 3}

bgpCommunityMaxSeen	OBJECT IDENTIFIER ::={bgp 25}

bgpCommunityMaxSeenVal	OBJECT-TYPE
	SYNTAX	 Unsigned32
	MAX-ACCESS read-only
	STATUS current
	DESCRIPTION "Maximum number of communities we have seen in a BGP update"

	::={bgpCommunityMaxSeen 1}

bgpCommunityMaxSeenMax	OBJECT-TYPE
	SYNTAX	 Unsigned32
	MAX-ACCESS read-only
	STATUS current
	DESCRIPTION "Maximum number of communities we have seen in a BGP update"

	::={bgpCommunityMaxSeen 3}

qsync	OBJECT IDENTIFIER ::={sysdiag 123}

qsyncIUpdates	OBJECT IDENTIFIER ::={qsync 1}

qsyncIUpdatesVal	OBJECT-TYPE
	SYNTAX	 Counter64
	MAX-ACCESS read-only
	STATUS current
	DESCRIPTION "Updates received from reapers"

	::={qsyncIUpdates 1}

qsyncIUpdatesMom	OBJECT-TYPE
	SYNTAX	 Unsigned32
	MAX-ACCESS read-only
	STATUS current
	DESCRIPTION "Updates received from reapers"

	::={qsyncIUpdates 2}

qsyncIUpdatesMax	OBJECT-TYPE
	SYNTAX	 Counter64
	MAX-ACCESS read-only
	STATUS current
	DESCRIPTION "Updates received from reapers"

	::={qsyncIUpdates 3}

qsyncIUpdatesOldRuleset	OBJECT IDENTIFIER ::={qsync 2}

qsyncIUpdatesOldRulesetVal	OBJECT-TYPE
	SYNTAX	 Counter64
	MAX-ACCESS read-only
	STATUS current
	DESCRIPTION "Updates received from reapers with old ruleset"

	::={qsyncIUpdatesOldRuleset 1}

qsyncIUpdatesOldRulesetMom	OBJECT-TYPE
	SYNTAX	 Unsigned32
	MAX-ACCESS read-only
	STATUS current
	DESCRIPTION "Updates received from reapers with old ruleset"

	::={qsyncIUpdatesOldRuleset 2}

qsyncIUpdatesOldRulesetMax	OBJECT-TYPE
	SYNTAX	 Counter64
	MAX-ACCESS read-only
	STATUS current
	DESCRIPTION "Updates received from reapers with old ruleset"

	::={qsyncIUpdatesOldRuleset 3}

qsyncIUpdatesUnknownObject	OBJECT IDENTIFIER ::={qsync 3}

qsyncIUpdatesUnknownObjectVal	OBJECT-TYPE
	SYNTAX	 Counter64
	MAX-ACCESS read-only
	STATUS current
	DESCRIPTION "Updates received for unknown object"

	::={qsyncIUpdatesUnknownObject 1}

qsyncIUpdatesUnknownObjectMom	OBJECT-TYPE
	SYNTAX	 Unsigned32
	MAX-ACCESS read-only
	STATUS current
	DESCRIPTION "Updates received for unknown object"

	::={qsyncIUpdatesUnknownObject 2}

qsyncIUpdatesUnknownObjectMax	OBJECT-TYPE
	SYNTAX	 Counter64
	MAX-ACCESS read-only
	STATUS current
	DESCRIPTION "Updates received for unknown object"

	::={qsyncIUpdatesUnknownObject 3}

qsyncIReaperSplitsCreated	OBJECT IDENTIFIER ::={qsync 4}

qsyncIReaperSplitsCreatedVal	OBJECT-TYPE
	SYNTAX	 Counter64
	MAX-ACCESS read-only
	STATUS current
	DESCRIPTION "Split entries created (reaper)"

	::={qsyncIReaperSplitsCreated 1}

qsyncIReaperSplitsCreatedMom	OBJECT-TYPE
	SYNTAX	 Unsigned32
	MAX-ACCESS read-only
	STATUS current
	DESCRIPTION "Split entries created (reaper)"

	::={qsyncIReaperSplitsCreated 2}

qsyncIReaperSplitsCreatedMax	OBJECT-TYPE
	SYNTAX	 Counter64
	MAX-ACCESS read-only
	STATUS current
	DESCRIPTION "Split entries created (reaper)"

	::={qsyncIReaperSplitsCreated 3}

qsyncIReaperSplitsActive	OBJECT IDENTIFIER ::={qsync 5}

qsyncIReaperSplitsActiveVal	OBJECT-TYPE
	SYNTAX	 Unsigned32
	MAX-ACCESS read-only
	STATUS current
	DESCRIPTION "Split entries active (reaper)"

	::={qsyncIReaperSplitsActive 1}

qsyncIReaperSplitsActiveMax	OBJECT-TYPE
	SYNTAX	 Unsigned32
	MAX-ACCESS read-only
	STATUS current
	DESCRIPTION "Split entries active (reaper)"

	::={qsyncIReaperSplitsActive 3}

qsyncISumFreelistSize	OBJECT IDENTIFIER ::={qsync 6}

qsyncISumFreelistSizeVal	OBJECT-TYPE
	SYNTAX	 Unsigned32
	MAX-ACCESS read-only
	STATUS current
	DESCRIPTION "Split entries on free list (sum)"

	::={qsyncISumFreelistSize 1}

qsyncISumFreelistSizeMax	OBJECT-TYPE
	SYNTAX	 Unsigned32
	MAX-ACCESS read-only
	STATUS current
	DESCRIPTION "Split entries on free list (sum)"

	::={qsyncISumFreelistSize 3}

qsyncISumSplitsActive	OBJECT IDENTIFIER ::={qsync 7}

qsyncISumSplitsActiveVal	OBJECT-TYPE
	SYNTAX	 Unsigned32
	MAX-ACCESS read-only
	STATUS current
	DESCRIPTION "Split entries active (sum)"

	::={qsyncISumSplitsActive 1}

qsyncISumSplitsActiveMax	OBJECT-TYPE
	SYNTAX	 Unsigned32
	MAX-ACCESS read-only
	STATUS current
	DESCRIPTION "Split entries active (sum)"

	::={qsyncISumSplitsActive 3}

qsyncIAdjustmentsSent	OBJECT IDENTIFIER ::={qsync 8}

qsyncIAdjustmentsSentVal	OBJECT-TYPE
	SYNTAX	 Counter64
	MAX-ACCESS read-only
	STATUS current
	DESCRIPTION "Object adjustments sent"

	::={qsyncIAdjustmentsSent 1}

qsyncIAdjustmentsSentMom	OBJECT-TYPE
	SYNTAX	 Unsigned32
	MAX-ACCESS read-only
	STATUS current
	DESCRIPTION "Object adjustments sent"

	::={qsyncIAdjustmentsSent 2}

qsyncIAdjustmentsSentMax	OBJECT-TYPE
	SYNTAX	 Counter64
	MAX-ACCESS read-only
	STATUS current
	DESCRIPTION "Object adjustments sent"

	::={qsyncIAdjustmentsSent 3}

qsyncENumPeers	OBJECT IDENTIFIER ::={qsync 9}

qsyncENumPeersVal	OBJECT-TYPE
	SYNTAX	 Unsigned32
	MAX-ACCESS read-only
	STATUS current
	DESCRIPTION "(ext) Number of peers"

	::={qsyncENumPeers 1}

qsyncENumPeersMax	OBJECT-TYPE
	SYNTAX	 Unsigned32
	MAX-ACCESS read-only
	STATUS current
	DESCRIPTION "(ext) Number of peers"

	::={qsyncENumPeers 3}

qsyncEUpdatesMismatch	OBJECT IDENTIFIER ::={qsync 10}

qsyncEUpdatesMismatchVal	OBJECT-TYPE
	SYNTAX	 Counter64
	MAX-ACCESS read-only
	STATUS current
	DESCRIPTION "(ext) Updates with mismatching ruleset"

	::={qsyncEUpdatesMismatch 1}

qsyncEUpdatesMismatchMom	OBJECT-TYPE
	SYNTAX	 Unsigned32
	MAX-ACCESS read-only
	STATUS current
	DESCRIPTION "(ext) Updates with mismatching ruleset"

	::={qsyncEUpdatesMismatch 2}

qsyncEUpdatesMismatchMax	OBJECT-TYPE
	SYNTAX	 Counter64
	MAX-ACCESS read-only
	STATUS current
	DESCRIPTION "(ext) Updates with mismatching ruleset"

	::={qsyncEUpdatesMismatch 3}

qsyncEUpdatePackets	OBJECT IDENTIFIER ::={qsync 11}

qsyncEUpdatePacketsVal	OBJECT-TYPE
	SYNTAX	 Counter64
	MAX-ACCESS read-only
	STATUS current
	DESCRIPTION "(ext) Update packets"

	::={qsyncEUpdatePackets 1}

qsyncEUpdatePacketsMom	OBJECT-TYPE
	SYNTAX	 Unsigned32
	MAX-ACCESS read-only
	STATUS current
	DESCRIPTION "(ext) Update packets"

	::={qsyncEUpdatePackets 2}

qsyncEUpdatePacketsMax	OBJECT-TYPE
	SYNTAX	 Counter64
	MAX-ACCESS read-only
	STATUS current
	DESCRIPTION "(ext) Update packets"

	::={qsyncEUpdatePackets 3}

qsyncESplitTimeout	OBJECT IDENTIFIER ::={qsync 12}

qsyncESplitTimeoutVal	OBJECT-TYPE
	SYNTAX	 Counter64
	MAX-ACCESS read-only
	STATUS current
	DESCRIPTION "(ext) Split object age timeout"

	::={qsyncESplitTimeout 1}

qsyncESplitTimeoutMom	OBJECT-TYPE
	SYNTAX	 Unsigned32
	MAX-ACCESS read-only
	STATUS current
	DESCRIPTION "(ext) Split object age timeout"

	::={qsyncESplitTimeout 2}

qsyncESplitTimeoutMax	OBJECT-TYPE
	SYNTAX	 Counter64
	MAX-ACCESS read-only
	STATUS current
	DESCRIPTION "(ext) Split object age timeout"

	::={qsyncESplitTimeout 3}

qsyncERecvUpdateEntries	OBJECT IDENTIFIER ::={qsync 13}

qsyncERecvUpdateEntriesVal	OBJECT-TYPE
	SYNTAX	 Counter64
	MAX-ACCESS read-only
	STATUS current
	DESCRIPTION "(ext) Received update entries"

	::={qsyncERecvUpdateEntries 1}

qsyncERecvUpdateEntriesMom	OBJECT-TYPE
	SYNTAX	 Unsigned32
	MAX-ACCESS read-only
	STATUS current
	DESCRIPTION "(ext) Received update entries"

	::={qsyncERecvUpdateEntries 2}

qsyncERecvUpdateEntriesMax	OBJECT-TYPE
	SYNTAX	 Counter64
	MAX-ACCESS read-only
	STATUS current
	DESCRIPTION "(ext) Received update entries"

	::={qsyncERecvUpdateEntries 3}

qsyncESendUpdateEntries	OBJECT IDENTIFIER ::={qsync 14}

qsyncESendUpdateEntriesVal	OBJECT-TYPE
	SYNTAX	 Counter64
	MAX-ACCESS read-only
	STATUS current
	DESCRIPTION "(ext) Sent update entries"

	::={qsyncESendUpdateEntries 1}

qsyncESendUpdateEntriesMom	OBJECT-TYPE
	SYNTAX	 Unsigned32
	MAX-ACCESS read-only
	STATUS current
	DESCRIPTION "(ext) Sent update entries"

	::={qsyncESendUpdateEntries 2}

qsyncESendUpdateEntriesMax	OBJECT-TYPE
	SYNTAX	 Counter64
	MAX-ACCESS read-only
	STATUS current
	DESCRIPTION "(ext) Sent update entries"

	::={qsyncESendUpdateEntries 3}

qsyncESendUpdatePackets	OBJECT IDENTIFIER ::={qsync 15}

qsyncESendUpdatePacketsVal	OBJECT-TYPE
	SYNTAX	 Counter64
	MAX-ACCESS read-only
	STATUS current
	DESCRIPTION "(ext) Sent update packets"

	::={qsyncESendUpdatePackets 1}

qsyncESendUpdatePacketsMom	OBJECT-TYPE
	SYNTAX	 Unsigned32
	MAX-ACCESS read-only
	STATUS current
	DESCRIPTION "(ext) Sent update packets"

	::={qsyncESendUpdatePackets 2}

qsyncESendUpdatePacketsMax	OBJECT-TYPE
	SYNTAX	 Counter64
	MAX-ACCESS read-only
	STATUS current
	DESCRIPTION "(ext) Sent update packets"

	::={qsyncESendUpdatePackets 3}

qsyncIUnsync	OBJECT IDENTIFIER ::={qsync 16}

qsyncIUnsyncVal	OBJECT-TYPE
	SYNTAX	 Counter64
	MAX-ACCESS read-only
	STATUS current
	DESCRIPTION "Qsync not run because unsynced objects"

	::={qsyncIUnsync 1}

qsyncIUnsyncMom	OBJECT-TYPE
	SYNTAX	 Unsigned32
	MAX-ACCESS read-only
	STATUS current
	DESCRIPTION "Qsync not run because unsynced objects"

	::={qsyncIUnsync 2}

qsyncIUnsyncMax	OBJECT-TYPE
	SYNTAX	 Counter64
	MAX-ACCESS read-only
	STATUS current
	DESCRIPTION "Qsync not run because unsynced objects"

	::={qsyncIUnsync 3}

qsyncESendbufFull	OBJECT IDENTIFIER ::={qsync 17}

qsyncESendbufFullVal	OBJECT-TYPE
	SYNTAX	 Counter64
	MAX-ACCESS read-only
	STATUS current
	DESCRIPTION "(ext) Entries dropped due to full sendbuffer"

	::={qsyncESendbufFull 1}

qsyncESendbufFullMom	OBJECT-TYPE
	SYNTAX	 Unsigned32
	MAX-ACCESS read-only
	STATUS current
	DESCRIPTION "(ext) Entries dropped due to full sendbuffer"

	::={qsyncESendbufFull 2}

qsyncESendbufFullMax	OBJECT-TYPE
	SYNTAX	 Counter64
	MAX-ACCESS read-only
	STATUS current
	DESCRIPTION "(ext) Entries dropped due to full sendbuffer"

	::={qsyncESendbufFull 3}

qsyncESendbufUsage	OBJECT IDENTIFIER ::={qsync 18}

qsyncESendbufUsageVal	OBJECT-TYPE
	SYNTAX	 Unsigned32
	MAX-ACCESS read-only
	STATUS current
	DESCRIPTION "(ext) Sendbuffer usage"

	::={qsyncESendbufUsage 1}

qsyncESendbufUsageMax	OBJECT-TYPE
	SYNTAX	 Unsigned32
	MAX-ACCESS read-only
	STATUS current
	DESCRIPTION "(ext) Sendbuffer usage"

	::={qsyncESendbufUsage 3}

qsyncIIgnoredOOO	OBJECT IDENTIFIER ::={qsync 19}

qsyncIIgnoredOOOVal	OBJECT-TYPE
	SYNTAX	 Counter64
	MAX-ACCESS read-only
	STATUS current
	DESCRIPTION "Ignored out of order updates"

	::={qsyncIIgnoredOOO 1}

qsyncIIgnoredOOOMom	OBJECT-TYPE
	SYNTAX	 Unsigned32
	MAX-ACCESS read-only
	STATUS current
	DESCRIPTION "Ignored out of order updates"

	::={qsyncIIgnoredOOO 2}

qsyncIIgnoredOOOMax	OBJECT-TYPE
	SYNTAX	 Counter64
	MAX-ACCESS read-only
	STATUS current
	DESCRIPTION "Ignored out of order updates"

	::={qsyncIIgnoredOOO 3}

qsyncIIgnoredGenWrap	OBJECT IDENTIFIER ::={qsync 20}

qsyncIIgnoredGenWrapVal	OBJECT-TYPE
	SYNTAX	 Counter64
	MAX-ACCESS read-only
	STATUS current
	DESCRIPTION "Ignored updates (generation wrap)"

	::={qsyncIIgnoredGenWrap 1}

qsyncIIgnoredGenWrapMom	OBJECT-TYPE
	SYNTAX	 Unsigned32
	MAX-ACCESS read-only
	STATUS current
	DESCRIPTION "Ignored updates (generation wrap)"

	::={qsyncIIgnoredGenWrap 2}

qsyncIIgnoredGenWrapMax	OBJECT-TYPE
	SYNTAX	 Counter64
	MAX-ACCESS read-only
	STATUS current
	DESCRIPTION "Ignored updates (generation wrap)"

	::={qsyncIIgnoredGenWrap 3}

shapingcounter	OBJECT IDENTIFIER ::={sysdiag 124}

shapingcounterUpdates	OBJECT IDENTIFIER ::={shapingcounter 1}

shapingcounterUpdatesVal	OBJECT-TYPE
	SYNTAX	 Counter64
	MAX-ACCESS read-only
	STATUS current
	DESCRIPTION "Updates received"

	::={shapingcounterUpdates 1}

shapingcounterUpdatesMom	OBJECT-TYPE
	SYNTAX	 Unsigned32
	MAX-ACCESS read-only
	STATUS current
	DESCRIPTION "Updates received"

	::={shapingcounterUpdates 2}

shapingcounterUpdatesMax	OBJECT-TYPE
	SYNTAX	 Counter64
	MAX-ACCESS read-only
	STATUS current
	DESCRIPTION "Updates received"

	::={shapingcounterUpdates 3}

shapingcounterActive	OBJECT IDENTIFIER ::={shapingcounter 2}

shapingcounterActiveVal	OBJECT-TYPE
	SYNTAX	 Unsigned32
	MAX-ACCESS read-only
	STATUS current
	DESCRIPTION "Active counters"

	::={shapingcounterActive 1}

shapingcounterActiveMax	OBJECT-TYPE
	SYNTAX	 Unsigned32
	MAX-ACCESS read-only
	STATUS current
	DESCRIPTION "Active counters"

	::={shapingcounterActive 3}

shapingcounterClients	OBJECT IDENTIFIER ::={shapingcounter 3}

shapingcounterClientsVal	OBJECT-TYPE
	SYNTAX	 Unsigned32
	MAX-ACCESS read-only
	STATUS current
	DESCRIPTION "Active clients"

	::={shapingcounterClients 1}

shapingcounterClientsMax	OBJECT-TYPE
	SYNTAX	 Unsigned32
	MAX-ACCESS read-only
	STATUS current
	DESCRIPTION "Active clients"

	::={shapingcounterClients 3}

shapingcounterRecycle	OBJECT IDENTIFIER ::={shapingcounter 4}

shapingcounterRecycleVal	OBJECT-TYPE
	SYNTAX	 Counter64
	MAX-ACCESS read-only
	STATUS current
	DESCRIPTION "Recycles"

	::={shapingcounterRecycle 1}

shapingcounterRecycleMom	OBJECT-TYPE
	SYNTAX	 Unsigned32
	MAX-ACCESS read-only
	STATUS current
	DESCRIPTION "Recycles"

	::={shapingcounterRecycle 2}

shapingcounterRecycleMax	OBJECT-TYPE
	SYNTAX	 Counter64
	MAX-ACCESS read-only
	STATUS current
	DESCRIPTION "Recycles"

	::={shapingcounterRecycle 3}

shapingcounterUpdatesInteresting	OBJECT IDENTIFIER ::={shapingcounter 5}

shapingcounterUpdatesInterestingVal	OBJECT-TYPE
	SYNTAX	 Counter64
	MAX-ACCESS read-only
	STATUS current
	DESCRIPTION "Updates crossing granularity boundary received"

	::={shapingcounterUpdatesInteresting 1}

shapingcounterUpdatesInterestingMom	OBJECT-TYPE
	SYNTAX	 Unsigned32
	MAX-ACCESS read-only
	STATUS current
	DESCRIPTION "Updates crossing granularity boundary received"

	::={shapingcounterUpdatesInteresting 2}

shapingcounterUpdatesInterestingMax	OBJECT-TYPE
	SYNTAX	 Counter64
	MAX-ACCESS read-only
	STATUS current
	DESCRIPTION "Updates crossing granularity boundary received"

	::={shapingcounterUpdatesInteresting 3}

divert	OBJECT IDENTIFIER ::={sysdiag 125}

divertOutOfHosts	OBJECT IDENTIFIER ::={divert 2}

divertOutOfHostsVal	OBJECT-TYPE
	SYNTAX	 Counter64
	MAX-ACCESS read-only
	STATUS current
	DESCRIPTION "Out of hosts"

	::={divertOutOfHosts 1}

divertOutOfHostsMom	OBJECT-TYPE
	SYNTAX	 Unsigned32
	MAX-ACCESS read-only
	STATUS current
	DESCRIPTION "Out of hosts"

	::={divertOutOfHosts 2}

divertOutOfHostsMax	OBJECT-TYPE
	SYNTAX	 Counter64
	MAX-ACCESS read-only
	STATUS current
	DESCRIPTION "Out of hosts"

	::={divertOutOfHosts 3}

divertOversizeL2	OBJECT IDENTIFIER ::={divert 3}

divertOversizeL2Val	OBJECT-TYPE
	SYNTAX	 Counter64
	MAX-ACCESS read-only
	STATUS current
	DESCRIPTION "Too large L2-headers"

	::={divertOversizeL2 1}

divertOversizeL2Mom	OBJECT-TYPE
	SYNTAX	 Unsigned32
	MAX-ACCESS read-only
	STATUS current
	DESCRIPTION "Too large L2-headers"

	::={divertOversizeL2 2}

divertOversizeL2Max	OBJECT-TYPE
	SYNTAX	 Counter64
	MAX-ACCESS read-only
	STATUS current
	DESCRIPTION "Too large L2-headers"

	::={divertOversizeL2 3}

divertEgressPackets	OBJECT IDENTIFIER ::={divert 4}

divertEgressPacketsVal	OBJECT-TYPE
	SYNTAX	 Counter64
	MAX-ACCESS read-only
	STATUS current
	DESCRIPTION "Egress packets"

	::={divertEgressPackets 1}

divertEgressPacketsMom	OBJECT-TYPE
	SYNTAX	 Unsigned32
	MAX-ACCESS read-only
	STATUS current
	DESCRIPTION "Egress packets"

	::={divertEgressPackets 2}

divertEgressPacketsMax	OBJECT-TYPE
	SYNTAX	 Counter64
	MAX-ACCESS read-only
	STATUS current
	DESCRIPTION "Egress packets"

	::={divertEgressPackets 3}

divertEgressBytes	OBJECT IDENTIFIER ::={divert 5}

divertEgressBytesVal	OBJECT-TYPE
	SYNTAX	 Counter64
	MAX-ACCESS read-only
	STATUS current
	DESCRIPTION "Egress bytes"

	::={divertEgressBytes 1}

divertEgressBytesMom	OBJECT-TYPE
	SYNTAX	 Unsigned32
	MAX-ACCESS read-only
	STATUS current
	DESCRIPTION "Egress bytes"

	::={divertEgressBytes 2}

divertEgressBytesMax	OBJECT-TYPE
	SYNTAX	 Counter64
	MAX-ACCESS read-only
	STATUS current
	DESCRIPTION "Egress bytes"

	::={divertEgressBytes 3}

divertIngressPackets	OBJECT IDENTIFIER ::={divert 6}

divertIngressPacketsVal	OBJECT-TYPE
	SYNTAX	 Counter64
	MAX-ACCESS read-only
	STATUS current
	DESCRIPTION "Ingress packets"

	::={divertIngressPackets 1}

divertIngressPacketsMom	OBJECT-TYPE
	SYNTAX	 Unsigned32
	MAX-ACCESS read-only
	STATUS current
	DESCRIPTION "Ingress packets"

	::={divertIngressPackets 2}

divertIngressPacketsMax	OBJECT-TYPE
	SYNTAX	 Counter64
	MAX-ACCESS read-only
	STATUS current
	DESCRIPTION "Ingress packets"

	::={divertIngressPackets 3}

divertIngressBytes	OBJECT IDENTIFIER ::={divert 7}

divertIngressBytesVal	OBJECT-TYPE
	SYNTAX	 Counter64
	MAX-ACCESS read-only
	STATUS current
	DESCRIPTION "Ingress bytes"

	::={divertIngressBytes 1}

divertIngressBytesMom	OBJECT-TYPE
	SYNTAX	 Unsigned32
	MAX-ACCESS read-only
	STATUS current
	DESCRIPTION "Ingress bytes"

	::={divertIngressBytes 2}

divertIngressBytesMax	OBJECT-TYPE
	SYNTAX	 Counter64
	MAX-ACCESS read-only
	STATUS current
	DESCRIPTION "Ingress bytes"

	::={divertIngressBytes 3}

divertIngressPacketsNohost	OBJECT IDENTIFIER ::={divert 8}

divertIngressPacketsNohostVal	OBJECT-TYPE
	SYNTAX	 Counter64
	MAX-ACCESS read-only
	STATUS current
	DESCRIPTION "Ingress packets with missing host"

	::={divertIngressPacketsNohost 1}

divertIngressPacketsNohostMom	OBJECT-TYPE
	SYNTAX	 Unsigned32
	MAX-ACCESS read-only
	STATUS current
	DESCRIPTION "Ingress packets with missing host"

	::={divertIngressPacketsNohost 2}

divertIngressPacketsNohostMax	OBJECT-TYPE
	SYNTAX	 Counter64
	MAX-ACCESS read-only
	STATUS current
	DESCRIPTION "Ingress packets with missing host"

	::={divertIngressPacketsNohost 3}

divertIngressPacketsNol2	OBJECT IDENTIFIER ::={divert 9}

divertIngressPacketsNol2Val	OBJECT-TYPE
	SYNTAX	 Counter64
	MAX-ACCESS read-only
	STATUS current
	DESCRIPTION "Ingress packets with host missing L2-header"

	::={divertIngressPacketsNol2 1}

divertIngressPacketsNol2Mom	OBJECT-TYPE
	SYNTAX	 Unsigned32
	MAX-ACCESS read-only
	STATUS current
	DESCRIPTION "Ingress packets with host missing L2-header"

	::={divertIngressPacketsNol2 2}

divertIngressPacketsNol2Max	OBJECT-TYPE
	SYNTAX	 Counter64
	MAX-ACCESS read-only
	STATUS current
	DESCRIPTION "Ingress packets with host missing L2-header"

	::={divertIngressPacketsNol2 3}

divertHostsUse	OBJECT IDENTIFIER ::={divert 10}

divertHostsUseVal	OBJECT-TYPE
	SYNTAX	 Unsigned32
	MAX-ACCESS read-only
	STATUS current
	DESCRIPTION "Hosts"

	::={divertHostsUse 1}

divertHostsUseMax	OBJECT-TYPE
	SYNTAX	 Unsigned32
	MAX-ACCESS read-only
	STATUS current
	DESCRIPTION "Hosts"

	::={divertHostsUse 3}

divertConnections	OBJECT IDENTIFIER ::={divert 11}

divertConnectionsVal	OBJECT-TYPE
	SYNTAX	 Unsigned32
	MAX-ACCESS read-only
	STATUS current
	DESCRIPTION "Connections"

	::={divertConnections 1}

divertConnectionsMax	OBJECT-TYPE
	SYNTAX	 Unsigned32
	MAX-ACCESS read-only
	STATUS current
	DESCRIPTION "Connections"

	::={divertConnections 3}

divertHbReqSent	OBJECT IDENTIFIER ::={divert 12}

divertHbReqSentVal	OBJECT-TYPE
	SYNTAX	 Counter64
	MAX-ACCESS read-only
	STATUS current
	DESCRIPTION "Heartbeat requests sent"

	::={divertHbReqSent 1}

divertHbReqSentMom	OBJECT-TYPE
	SYNTAX	 Unsigned32
	MAX-ACCESS read-only
	STATUS current
	DESCRIPTION "Heartbeat requests sent"

	::={divertHbReqSent 2}

divertHbReqSentMax	OBJECT-TYPE
	SYNTAX	 Counter64
	MAX-ACCESS read-only
	STATUS current
	DESCRIPTION "Heartbeat requests sent"

	::={divertHbReqSent 3}

divertHbReqRecv	OBJECT IDENTIFIER ::={divert 13}

divertHbReqRecvVal	OBJECT-TYPE
	SYNTAX	 Counter64
	MAX-ACCESS read-only
	STATUS current
	DESCRIPTION "Heartbeat requests received"

	::={divertHbReqRecv 1}

divertHbReqRecvMom	OBJECT-TYPE
	SYNTAX	 Unsigned32
	MAX-ACCESS read-only
	STATUS current
	DESCRIPTION "Heartbeat requests received"

	::={divertHbReqRecv 2}

divertHbReqRecvMax	OBJECT-TYPE
	SYNTAX	 Counter64
	MAX-ACCESS read-only
	STATUS current
	DESCRIPTION "Heartbeat requests received"

	::={divertHbReqRecv 3}

divertHbRepSent	OBJECT IDENTIFIER ::={divert 14}

divertHbRepSentVal	OBJECT-TYPE
	SYNTAX	 Counter64
	MAX-ACCESS read-only
	STATUS current
	DESCRIPTION "Heartbeat replies sent"

	::={divertHbRepSent 1}

divertHbRepSentMom	OBJECT-TYPE
	SYNTAX	 Unsigned32
	MAX-ACCESS read-only
	STATUS current
	DESCRIPTION "Heartbeat replies sent"

	::={divertHbRepSent 2}

divertHbRepSentMax	OBJECT-TYPE
	SYNTAX	 Counter64
	MAX-ACCESS read-only
	STATUS current
	DESCRIPTION "Heartbeat replies sent"

	::={divertHbRepSent 3}

divertHbRepRecv	OBJECT IDENTIFIER ::={divert 15}

divertHbRepRecvVal	OBJECT-TYPE
	SYNTAX	 Counter64
	MAX-ACCESS read-only
	STATUS current
	DESCRIPTION "Heartbeat replies received"

	::={divertHbRepRecv 1}

divertHbRepRecvMom	OBJECT-TYPE
	SYNTAX	 Unsigned32
	MAX-ACCESS read-only
	STATUS current
	DESCRIPTION "Heartbeat replies received"

	::={divertHbRepRecv 2}

divertHbRepRecvMax	OBJECT-TYPE
	SYNTAX	 Counter64
	MAX-ACCESS read-only
	STATUS current
	DESCRIPTION "Heartbeat replies received"

	::={divertHbRepRecv 3}

divertHbLost	OBJECT IDENTIFIER ::={divert 16}

divertHbLostVal	OBJECT-TYPE
	SYNTAX	 Counter64
	MAX-ACCESS read-only
	STATUS current
	DESCRIPTION "Heartbeats lost"

	::={divertHbLost 1}

divertHbLostMom	OBJECT-TYPE
	SYNTAX	 Unsigned32
	MAX-ACCESS read-only
	STATUS current
	DESCRIPTION "Heartbeats lost"

	::={divertHbLost 2}

divertHbLostMax	OBJECT-TYPE
	SYNTAX	 Counter64
	MAX-ACCESS read-only
	STATUS current
	DESCRIPTION "Heartbeats lost"

	::={divertHbLost 3}

divertBypassPackets	OBJECT IDENTIFIER ::={divert 17}

divertBypassPacketsVal	OBJECT-TYPE
	SYNTAX	 Counter64
	MAX-ACCESS read-only
	STATUS current
	DESCRIPTION "Bypassed packets"

	::={divertBypassPackets 1}

divertBypassPacketsMom	OBJECT-TYPE
	SYNTAX	 Unsigned32
	MAX-ACCESS read-only
	STATUS current
	DESCRIPTION "Bypassed packets"

	::={divertBypassPackets 2}

divertBypassPacketsMax	OBJECT-TYPE
	SYNTAX	 Counter64
	MAX-ACCESS read-only
	STATUS current
	DESCRIPTION "Bypassed packets"

	::={divertBypassPackets 3}

divertDroppedPackets	OBJECT IDENTIFIER ::={divert 18}

divertDroppedPacketsVal	OBJECT-TYPE
	SYNTAX	 Counter64
	MAX-ACCESS read-only
	STATUS current
	DESCRIPTION "Dropped packets"

	::={divertDroppedPackets 1}

divertDroppedPacketsMom	OBJECT-TYPE
	SYNTAX	 Unsigned32
	MAX-ACCESS read-only
	STATUS current
	DESCRIPTION "Dropped packets"

	::={divertDroppedPackets 2}

divertDroppedPacketsMax	OBJECT-TYPE
	SYNTAX	 Counter64
	MAX-ACCESS read-only
	STATUS current
	DESCRIPTION "Dropped packets"

	::={divertDroppedPackets 3}




END
