-- =====================================================================
-- == OG-PATTERN-MIB:                                          ==
-- == Opengear pattern match notification Management Information Base ==
-- ==                                                                 ==
-- == (c) Copyright 2005-2014 Opengear Inc.                           ==
-- =====================================================================

OG-PATTERN-MIB DEFINITIONS ::= BEGIN

IMPORTS
	ogMgmt 
		FROM OG-SMI-MIB
	MODULE-IDENTITY, NOTIFICATION-TYPE, OBJECT-TYPE, Integer32
		FROM SNMPv2-SMI
	MODULE-COMPLIANCE, NOTIFICATION-GROUP, OBJECT-GROUP
		FROM SNMPv2-CONF
	DisplayString
		FROM SNMPv2-TC;


ogPatternMib MODULE-IDENTITY
	LAST-UPDATED "201308110000Z"
	ORGANIZATION "Opengear Inc."
	CONTACT-INFO
		"Opengear Inc.
		 9270 South 500 West, Suite J,
		 Sandy, UT 84070
		 support@opengear.com"
	DESCRIPTION
		"Opengear console pattern matching MIB"
	REVISION "201308110000Z"
	DESCRIPTION
		"Renamed from OPENGEAR-PATTERN-MIB to OG-PATTERN-MIB to
		fix naming discrepancy."
	REVISION "201003221127Z"
	DESCRIPTION
		"Syntax corrections by Opengear Inc."
	REVISION "200811271140Z"
	DESCRIPTION
		"Initial version."
        ::= { ogMgmt 12 }

ogPatternMibObjects OBJECT IDENTIFIER ::= { ogPatternMib 10 }

-- Subgroups

ogpatnEvent OBJECT IDENTIFIER ::= { ogPatternMibObjects 1 }

ogpatnEventTable OBJECT-TYPE
        SYNTAX     SEQUENCE OF OgPatnEventEntry
        MAX-ACCESS not-accessible
        STATUS     current
        DESCRIPTION
                "A table of sensor status events generated by this device."
        ::= { ogpatnEvent 1 }

ogpatnEventEntry OBJECT-TYPE
        SYNTAX     OgPatnEventEntry
        MAX-ACCESS not-accessible
        STATUS     current
        DESCRIPTION
                "A console connection event occuring at this
                 device. Each entry is indexed by a message index."
        INDEX   { ogpatnEventIndex }
        ::= { ogpatnEventTable 1 }

OgPatnEventEntry ::=
    SEQUENCE {
        ogpatnEventIndex        Integer32,
        ogpatnEventDescription 	DisplayString,
        ogpatnEventText 	DisplayString,
	ogpatnEventPortNumber   Integer32,
	ogpatnEventPortLabel    DisplayString
    }

ogpatnEventIndex OBJECT-TYPE
        SYNTAX     Integer32 (1..2147483647)
        MAX-ACCESS not-accessible
        STATUS     current
        DESCRIPTION
                "A monotonically increasing integer for the sole
                 purpose of indexing messages.  When it reaches the
                 maximum value the agent flushes the table and wraps
                 the value back to 1."
        ::= { ogpatnEventEntry 1 }

ogpatnEventDescription OBJECT-TYPE
	SYNTAX DisplayString
	MAX-ACCESS read-only
	STATUS current
	DESCRIPTION
	        "A description of the matches purpose"
	::= { ogpatnEventEntry 10 }

ogpatnEventText OBJECT-TYPE
	SYNTAX DisplayString
	MAX-ACCESS read-only
	STATUS current
	DESCRIPTION
		"The full text which matched the pattern"
	::= { ogpatnEventEntry 11 }

ogpatnEventPortNumber OBJECT-TYPE
	SYNTAX Integer32
	MAX-ACCESS read-only
	STATUS current
	DESCRIPTION
		"Serial port number on which the pattern matched"
	::= { ogpatnEventEntry 12 }

ogpatnEventPortLabel OBJECT-TYPE
	SYNTAX DisplayString
	MAX-ACCESS read-only
	STATUS current
	DESCRIPTION
		"The label for the serial port where pattern matched occurred"
	::= { ogpatnEventEntry 13 }

-- notifications

ogPatternMibNotificationPrefix    OBJECT IDENTIFIER ::= {
	ogPatternMib 2
}

ogpatnMibNotifications         OBJECT IDENTIFIER ::= {
	ogPatternMibNotificationPrefix 0
}

ogpatnEventOccurred NOTIFICATION-TYPE
        OBJECTS {
        	ogpatnEventDescription,
        	ogpatnEventText,
		ogpatnEventPortNumber,
		ogpatnEventPortLabel }
	STATUS current
	DESCRIPTION
		"An alert sent when a pre-defined pattern was
		matched text in a consoles serial character stream"
        ::= { ogpatnMibNotifications 200 }

-- conformance information

ogPatternMibConformance OBJECT IDENTIFIER ::= { ogPatternMib 3 }
ogPatternMibCompliances OBJECT IDENTIFIER ::= { ogPatternMibConformance 1 }
ogPatternMibGroups      OBJECT IDENTIFIER ::= { ogPatternMibConformance 2 }

-- compliance statements

ogPatternMibCompliance MODULE-COMPLIANCE
       STATUS  current
       DESCRIPTION
               "The compliance statement for entities which implement
                the Opengear Pattern MIB."
       MODULE  -- this module
               MANDATORY-GROUPS { ogPatternMibGroup }

       GROUP ogpatnNotificationsGroup
       DESCRIPTION
           "The implementation of this group is
           mandatory for those systems where
           sensor notification is supported."

       ::= { ogPatternMibCompliances 1 }

-- Units of conformance

ogPatternMibGroup OBJECT-GROUP
       OBJECTS {
        	ogpatnEventDescription,
        	ogpatnEventText,
		ogpatnEventPortNumber,
		ogpatnEventPortLabel
       }
       STATUS  current
       DESCRIPTION
               "A collection of objects providing the sensor MIB capability."
      ::= { ogPatternMibGroups 1 }

ogpatnNotificationsGroup NOTIFICATION-GROUP
       NOTIFICATIONS {
               ogpatnEventOccurred
       }
       STATUS  current
       DESCRIPTION
               "A collection of notification(s) for sensor system."
       ::= { ogPatternMibGroups 2 }

END
