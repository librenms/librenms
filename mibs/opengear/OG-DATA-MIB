-- =====================================================================
-- == OG-DATA-MIB:                                              ==
-- == Opengear Data Usage status notification Management Information Base    ==
-- ==                                                                 ==
-- == (c) Copyright 2005-2014 Opengear Inc.                           ==
-- =====================================================================

OG-DATA-MIB DEFINITIONS ::= BEGIN

IMPORTS
	ogMgmt
		FROM OG-SMI-MIB
	MODULE-IDENTITY, NOTIFICATION-TYPE, OBJECT-TYPE, Integer32
		FROM SNMPv2-SMI
	MODULE-COMPLIANCE, NOTIFICATION-GROUP, OBJECT-GROUP
		FROM SNMPv2-CONF
	DisplayString
		FROM SNMPv2-TC;

ogDataMib MODULE-IDENTITY
	LAST-UPDATED "201308110000Z"
ORGANIZATION "Opengear Inc."
CONTACT-INFO
"Opengear Inc.
9270 South 500 West, Suite J,
Sandy, UT 84070
support@opengear.com"
DESCRIPTION
"Opengear data logging status MIB"
REVISION "201308110000Z"
DESCRIPTION
"Renamed from OPENGEAR-DATA-MIB to OG-DATA-MIB to
fix naming discrepancy."
REVISION "201101302110Z"
DESCRIPTION
"Initial version."
      ::= { ogMgmt 17 }

ogDataMibObjects OBJECT IDENTIFIER ::= { ogDataMib 10 }

-- Subgroups

ogdataEvent OBJECT IDENTIFIER ::= { ogDataMibObjects 1 }

ogdataEventTable OBJECT-TYPE
        SYNTAX     SEQUENCE OF OgDataEventEntry
        MAX-ACCESS not-accessible
        STATUS     current
        DESCRIPTION
                "A table of data logging events generated by this device."
        ::= { ogdataEvent 1 }

ogdataEventEntry OBJECT-TYPE
        SYNTAX     OgDataEventEntry
        MAX-ACCESS not-accessible
        STATUS     current
        DESCRIPTION
                "A console connection event occuring at this
                 device. Each entry is indexed by a message index."
        INDEX   { ogdataEventIndex }
        ::= { ogdataEventTable 1 }

OgDataEventEntry ::=
    SEQUENCE {
        ogdataEventIndex        Integer32,
        ogdataEventBytes        Integer32,
        ogdataEventSeconds      Integer32,
 	ogdataEventDevice       DisplayString,
 	ogdataEventState        INTEGER
    }

ogdataEventIndex OBJECT-TYPE
        SYNTAX     Integer32 (1..2147483647)
        MAX-ACCESS not-accessible
        STATUS     current
        DESCRIPTION
                "A monotonically increasing integer for the sole
                 purpose of indexing messages.  When it reaches the
                 maximum value the agent flushes the table and wraps
                 the value back to 1."
        ::= { ogdataEventEntry 1 }

ogdataEventBytes OBJECT-TYPE
	SYNTAX Integer32
	MAX-ACCESS read-only
	STATUS current
	DESCRIPTION
		"The number of bytes exceeded during the time period"
	::= { ogdataEventEntry 10 }

ogdataEventSeconds OBJECT-TYPE
	SYNTAX Integer32
	MAX-ACCESS read-only
	STATUS current
	DESCRIPTION
		"The time in seconds over which the number of bytes was exceeded"
	::= { ogdataEventEntry 11 }

ogdataEventDevice OBJECT-TYPE
	SYNTAX DisplayString
	MAX-ACCESS read-only
	STATUS current
	DESCRIPTION
		"The unique name for the interface the alert occurred on."
	::= { ogdataEventEntry 12 }

ogdataEventState OBJECT-TYPE
        SYNTAX INTEGER {
            off(0),
            on(1)
        }
	MAX-ACCESS read-only
	STATUS current
	DESCRIPTION
		"The status of the data alert."
	::= { ogdataEventEntry 13 }

-- notifications

ogDataMibNotificationPrefix    OBJECT IDENTIFIER ::= {
	ogDataMib 2
}

ogdataMibNotifications         OBJECT IDENTIFIER ::= {
	ogDataMibNotificationPrefix 0
}

ogdataEventOccurred NOTIFICATION-TYPE
	OBJECTS { ogdataEventBytes, ogdataEventSeconds, ogdataEventDevice, ogdataEventState  }
	STATUS current
	DESCRIPTION
		"The notification sent when a status event occurs"
	::= { ogdataMibNotifications 200 }
-- conformance information

ogDataMibConformance OBJECT IDENTIFIER ::= { ogDataMib 3 }
ogDataMibCompliances OBJECT IDENTIFIER ::= {
	ogDataMibConformance 1 }
ogDataMibGroups      OBJECT IDENTIFIER ::= {
	ogDataMibConformance 2 }

-- compliance statements

ogDataMibCompliance MODULE-COMPLIANCE
       STATUS  current
       DESCRIPTION
               "The compliance statement for entities which implement
                the Opengear Data Logging MIB."
       MODULE  -- this module
               MANDATORY-GROUPS { ogDataMibGroup }

       GROUP ogdataNotificationsGroup
       DESCRIPTION
           "The implementation of this group is
           mandatory for those systems where
           sensor notification is supported."

       ::= { ogDataMibCompliances 1 }

-- Units of conformance

ogDataMibGroup OBJECT-GROUP
       OBJECTS {
		ogdataEventBytes,
		ogdataEventSeconds,
		ogdataEventDevice,
		ogdataEventState
       }
       STATUS  current
       DESCRIPTION
               "A collection of objects providing the sensor MIB capability."
      ::= { ogDataMibGroups 1 }

ogdataNotificationsGroup NOTIFICATION-GROUP
       NOTIFICATIONS {
               ogdataEventOccurred
       }
       STATUS  current
       DESCRIPTION
               "A collection of notification(s) for the data logging system."
       ::= { ogDataMibGroups 2 }

END
