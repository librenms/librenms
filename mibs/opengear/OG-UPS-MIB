-- =====================================================================
-- == OG-UPS-MIB:                                              ==
-- == Opengear UPS status notification Management Information Base    ==
-- ==                                                                 ==
-- == (c) Copyright 2005-2014 Opengear Inc.                           ==
-- =====================================================================

OG-UPS-MIB DEFINITIONS ::= BEGIN

IMPORTS
	ogMgmt
		FROM OG-SMI-MIB
	MODULE-IDENTITY, NOTIFICATION-TYPE, OBJECT-TYPE, Integer32
		FROM SNMPv2-SMI
	MODULE-COMPLIANCE, NOTIFICATION-GROUP, OBJECT-GROUP
		FROM SNMPv2-CONF
	DisplayString
		FROM SNMPv2-TC;

ogNetUpsMib MODULE-IDENTITY
	LAST-UPDATED "201308110000Z"
ORGANIZATION "Opengear Inc."
CONTACT-INFO
"Opengear Inc.
9270 South 500 West, Suite J,
Sandy, UT 84070
support@opengear.com"
DESCRIPTION
"Opengear UPS status MIB"
REVISION "201308110000Z"
DESCRIPTION
"Renamed from OPENGEAR-UPS-MIB to OG-UPS-MIB to
fix naming discrepancy."
REVISION "201003221127Z"
DESCRIPTION
"Syntax corrections by Opengear Inc."
REVISION "200806131100Z"
DESCRIPTION
"Initial version."
      ::= { ogMgmt 16 }

ogNetUpsMibObjects OBJECT IDENTIFIER ::= { ogNetUpsMib 10 }

-- Subgroups

ognupsEvent OBJECT IDENTIFIER ::= { ogNetUpsMibObjects 1 }

ognupsEventTable OBJECT-TYPE
        SYNTAX     SEQUENCE OF OgNUpsEventEntry
        MAX-ACCESS not-accessible
        STATUS     current
        DESCRIPTION
                "A table of serial signal events generated by this device."
        ::= { ognupsEvent 1 }

ognupsEventEntry OBJECT-TYPE
        SYNTAX     OgNUpsEventEntry
        MAX-ACCESS not-accessible
        STATUS     current
        DESCRIPTION
                "A console connection event occuring at this
                 device. Each entry is indexed by a message index."
        INDEX   { ognupsEventIndex }
        ::= { ognupsEventTable 1 }

OgNUpsEventEntry ::=
    SEQUENCE {
        ognupsEventIndex        Integer32,
 	ognupsEventName		DisplayString,
 	ognupsEventType		DisplayString
    }

ognupsEventIndex OBJECT-TYPE
        SYNTAX     Integer32 (1..2147483647)
        MAX-ACCESS not-accessible
        STATUS     current
        DESCRIPTION
                "A monotonically increasing integer for the sole
                 purpose of indexing messages.  When it reaches the
                 maximum value the agent flushes the table and wraps
                 the value back to 1."
        ::= { ognupsEventEntry 1 }

ognupsEventName OBJECT-TYPE
	SYNTAX DisplayString
	MAX-ACCESS read-only
	STATUS current
	DESCRIPTION
	        "The name of the UPS pertaining to the status event"
	::= { ognupsEventEntry 10 }

ognupsEventType OBJECT-TYPE
	SYNTAX DisplayString
	MAX-ACCESS read-only
	STATUS current
	DESCRIPTION
	        "The type of status event"
	::= { ognupsEventEntry 11 }

-- notifications

ogNetUpsMibNotificationPrefix    OBJECT IDENTIFIER ::= {
	ogNetUpsMib 2
}

ognupsMibNotifications         OBJECT IDENTIFIER ::= {
	ogNetUpsMibNotificationPrefix 0
}

ognupsEventOccurred NOTIFICATION-TYPE
	OBJECTS { ognupsEventName, ognupsEventType }
	STATUS current
	DESCRIPTION
		"The notification sent when a UPS status event occurs"
	::= { ognupsMibNotifications 200 }
-- conformance information

ogNetUpsMibConformance OBJECT IDENTIFIER ::= { ogNetUpsMib 3 }
ogNetUpsMibCompliances OBJECT IDENTIFIER ::= { ogNetUpsMibConformance 1 }
ogNetUpsMibGroups      OBJECT IDENTIFIER ::= { ogNetUpsMibConformance 2 }

-- compliance statements

ogNetUpsMibCompliance MODULE-COMPLIANCE
       STATUS  current
       DESCRIPTION
               "The compliance statement for entities which implement
                the Opengear UPS MIB."
       MODULE  -- this module
               MANDATORY-GROUPS { ogNetUpsMibGroup }

       GROUP ognupsNotificationsGroup
       DESCRIPTION
           "The implementation of this group is
           mandatory for those systems where
           sensor notification is supported."

       ::= { ogNetUpsMibCompliances 1 }

-- Units of conformance

ogNetUpsMibGroup OBJECT-GROUP
       OBJECTS {
		ognupsEventName,
		ognupsEventType
       }
       STATUS  current
       DESCRIPTION
               "A collection of objects providing the sensor MIB capability."
      ::= { ogNetUpsMibGroups 1 }

ognupsNotificationsGroup NOTIFICATION-GROUP
       NOTIFICATIONS {
               ognupsEventOccurred
       }
       STATUS  current
       DESCRIPTION
               "A collection of notification(s) for sensor system."
       ::= { ogNetUpsMibGroups 2 }

END
