-- =========================================================================
-- == OG-FAILOVER-MIB:                                             ==
-- == Opengear network failover notification Management Information Base  ==
-- ==                                                                     ==
-- == (c) Copyright 2005-2014 Opengear Inc.                               ==
-- =========================================================================

OG-FAILOVER-MIB DEFINITIONS ::= BEGIN

IMPORTS
	ogMgmt
		FROM OG-SMI-MIB
	OBJECT-TYPE
		FROM RFC-1212
	MODULE-IDENTITY, NOTIFICATION-TYPE, Integer32
		FROM SNMPv2-SMI
	MODULE-COMPLIANCE, NOTIFICATION-GROUP, OBJECT-GROUP
		FROM SNMPv2-CONF
	DisplayString
		FROM SNMPv2-TC;

ogFailoverMib MODULE-IDENTITY
        LAST-UPDATED "201308110000Z"
	ORGANIZATION "Opengear Inc."
	CONTACT-INFO
		"Opengear Inc.
		 9270 South 500 West, Suite J,
		 Sandy, UT 84070
		 support@opengear.com"
	DESCRIPTION
		"Opengear network failover MIB"
	REVISION "201308110000Z"
	DESCRIPTION
		"Renamed from OPENGEAR-FAILOVER-MIB to OG-FAILOVER-MIB to
		fix naming discrepancy."
	REVISION "201003221127Z"
	DESCRIPTION
		"Syntax corrections by Opengear Inc."
	REVISION "200811271140Z"
	DESCRIPTION
		"Initial version."
        ::= { ogMgmt 15 }

ogFailoverMibObjects OBJECT IDENTIFIER ::= { ogFailoverMib 10 }

-- Subgroups

ogfovrEvent OBJECT IDENTIFIER ::= { ogFailoverMibObjects 1 }

ogfovrEventTable OBJECT-TYPE
        SYNTAX     SEQUENCE OF OgFovrEventEntry
        MAX-ACCESS not-accessible
        STATUS     current
        DESCRIPTION
                "A table of sensor status events generated by this device."
        ::= { ogfovrEvent 1 }

ogfovrEventEntry OBJECT-TYPE
        SYNTAX     OgFovrEventEntry
        MAX-ACCESS not-accessible
        STATUS     current
        DESCRIPTION
                "A console connection event occuring at this
                 device. Each entry is indexed by a message index."
        INDEX   { ogfovrEventIndex }
        ::= { ogfovrEventTable 1 }

OgFovrEventEntry ::=
    SEQUENCE {
        ogfovrEventIndex      Integer32,
        ogfovrEventPrimary    DisplayString,
	ogfovrEventSecondary  DisplayString
    }

ogfovrEventIndex OBJECT-TYPE
        SYNTAX     Integer32 (1..2147483647)
        MAX-ACCESS not-accessible
        STATUS     current
        DESCRIPTION
                "A monotonically increasing integer for the sole
                 purpose of indexing messages.  When it reaches the
                 maximum value the agent flushes the table and wraps
                 the value back to 1."
        ::= { ogfovrEventEntry 1 }

ogfovrEventPrimary OBJECT-TYPE
	SYNTAX DisplayString
	MAX-ACCESS read-only
	STATUS current
	DESCRIPTION
	        "The name of the network interface which failed"
	::= { ogfovrEventEntry 10 }

ogfovrEventSecondary OBJECT-TYPE
	SYNTAX DisplayString
	MAX-ACCESS read-only
	STATUS current
	DESCRIPTION
	        "The name of the network interface which was connected instead"
	::= { ogfovrEventEntry 11 }

-- notifications

ogFailoverMibNotificationPrefix    OBJECT IDENTIFIER ::= {
	ogFailoverMib 2
}

ogfovrMibNotifications         OBJECT IDENTIFIER ::= {
	ogFailoverMibNotificationPrefix 0
}

ogfovrEventOccurred NOTIFICATION-TYPE
	OBJECTS { ogfovrEventPrimary, ogfovrEventSecondary }
	STATUS current
	DESCRIPTION
		"The notification sent when a network failover event occurs"
	::= { ogfovrMibNotifications 200 }
-- conformance information

ogFailoverMibConformance OBJECT IDENTIFIER ::= { ogFailoverMib 3 }
ogFailoverMibCompliances OBJECT IDENTIFIER ::= { ogFailoverMibConformance 1 }
ogFailoverMibGroups      OBJECT IDENTIFIER ::= { ogFailoverMibConformance 2 }

-- compliance statements

ogFailoverMibCompliance MODULE-COMPLIANCE
       STATUS  current
       DESCRIPTION
               "The compliance statement for entities which implement
                the Opengear sensor MIB."
       MODULE  -- this module
               MANDATORY-GROUPS { ogFailoverMibGroup }

       GROUP ogfovrNotificationsGroup
       DESCRIPTION
           "The implementation of this group is
           mandatory for those systems where
           sensor notification is supported."

       ::= { ogFailoverMibCompliances 1 }

-- Units of conformance

ogFailoverMibGroup OBJECT-GROUP
       OBJECTS { ogfovrEventPrimary,
                 ogfovrEventSecondary
       }
       STATUS  current
       DESCRIPTION
               "A collection of objects providing the sensor MIB capability."
      ::= { ogFailoverMibGroups 1 }

ogfovrNotificationsGroup NOTIFICATION-GROUP
       NOTIFICATIONS {
               ogfovrEventOccurred
       }
       STATUS  current
       DESCRIPTION
               "A collection of notification(s) for sensor system."
       ::= { ogFailoverMibGroups 2 }

END
