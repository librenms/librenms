------------------------------------------------------------------------
------------------------------------------------------------------------
--
-- Copyright (C) BTI Systems Inc. 2003-2011. All Rights Reserved.
--
-- The information contained herein is the property of BTI Systems Inc.
-- and is strictly confidential. Except as expressly authorized in
-- writing by BTI Systems Inc., the holder shall keep all information
-- contained herein confidential, shall disclose the information only
-- to its employees with a need to know, and shall protect the
-- information, in whole or in part, from disclosure and dissemination
-- to third parties with the same degree of care it uses to protect
-- its own confidential information, but with no less than reasonable
-- care. Except as expressly authorized in writing by BTI Systems Inc.,
-- the holder is granted no rights to use the information contained
-- herein.
--
-- Unpublished. All rights reserved under the copyright laws of
-- Canada.
-- 
-- OSS Integration 
-- BTI Systems Inc. can provide customers with direct access to 
-- network element SNMP MIBs for use for integration to OSS systems. 
-- Customers must note the following caveats:
--
-- 1) Performance: The BTI Systems Inc. MIBS are performance tested for
-- use with the BTI Systems proNX 900 Node Controller and proNX 9000 
-- Network Manager. Customers are responsible for conducting their 
-- own testing to ensure that the BTI Systems Inc. NE interfaces meet 
-- the needs of their proposed usage. BTI Systems Inc. makes no
-- guarantees that any proposed usage will meet customer requirements.
--
-- 2) Changes between releases: BTI Systems Inc. SNMP MIBs are subject 
-- to change as support for new functionality is introduced. BTI  
-- Systems Inc. strives to maintain backward compatibility of MIBs 
-- across releases but this is not guaranteed and BTI Systems Inc. 
-- reserves the right to deprecate or remove support for obsolete 
-- MIB elements. OSS integrators must be careful not to rely on 
-- functionality that is marked as deprecated as it may be unsupported 
-- in a subsequent release. Customers that integrate directly to BTI 
-- Systems Inc. MIBs are responsible for all OSS development and 
-- integration testing that may arise from MIB changes between releases 
-- of BTI Systems Inc. software.
--
------------------------------------------------------------------------
------------------------------------------------------------------------

PACKET-VX-BRIDGE-MIB DEFINITIONS ::= BEGIN

IMPORTS
    MODULE-IDENTITY, OBJECT-TYPE, NOTIFICATION-TYPE, Integer32, Unsigned32,
    IpAddress
        FROM SNMPv2-SMI
        
    TEXTUAL-CONVENTION,  DisplayString, MacAddress, TruthValue, RowStatus,
    DateAndTime, TimeInterval
        FROM SNMPv2-TC
        
    btiModules
        FROM BTI-MIB
        
    pvxObjects, pvxBridge, mstpCondNotifications, mstpNotificationObjects, 
    pvxL2IntfSwitchIdx, pvxL2IntfShelfIdx, pvxL2IntfSlotIdx,
    pvxL2IntfPortTypeIdx, pvxL2IntfPortIdx, lagCondNotifications,
    swMemberCondNotifications,
    pvxL2IntfSubPortNumber,
    mstpEvtNotifications, evtDateAndTime,
    condReportType, condServiceAffecting, condObjectType, condCodeType,
    condDateAndTime, condSeverity, condDescription, 
    trapSeqNum, performance, evtDescription, evtObjectType, evtCodeType,
    pvxESrvcBWPrflEvtNotifications, pvxESrvcEvtNotifications,
    pvxERPSSrvcNNIEvtNotifications, pvxERPSSrvcEvtNotifications,
    tcaDateAndTime, tcaThreshold, pvxSlaMsmtEvtNotifications,
    pvxSUniEvtNotifications,   erpsCondNotifications,        
    tcaMontype, tcaValue, eventNotifications
        FROM BTI-7000-MIB
                    
    CondReportType, CondSeverity, CondServiceAffecting, AdminStatus, OperStatus,     
    SwitchIdxType, ProtocolActionType, PvxPortType, PMIntervalType, Unsigned64,
    PMValidity, InitializeCmd, ProfileNameType, FixedX100, InetAddressType, InetAddress,
    MonitorPeriodType, CommandStateType, CirTestResult, FixedX1000, SlaTestRole, 
    PmTestCmdState, MirrorConfigType 
        FROM BTI-TC-MIB;
        
          
    
packetVxBridgeMib MODULE-IDENTITY
    LAST-UPDATED "201304031200Z"  -- Wednesday, April 03, 12:00:00 EST 2013
    ORGANIZATION "BTI Systems Inc."
    CONTACT-INFO "Technical Support
                  BTI Systems Inc.
                  200-1000 Innovation Drive
                  Ottawa, Ontario, Canada  K2K 3E7
                  (613) 287-1700
                  support@btisystems.com"
    DESCRIPTION  "The external MIB definitions for the PacketVX Module on
		  the BTI 7000 series products."

    REVISION     "201304031200Z"  -- Wednesday, April 03, 12:00:00 EST 2013
    DESCRIPTION  "MIB Updates for BTI 7000 Rel 11.1.0:
                 - added CcmLinkDetection attribute to the PvxERPSServiceNNIEntry 
                   entry to allow CCM messages to be disabled or enabled as the 
                   link status detection method"
    REVISION     "201212201200Z"  -- Thursday, December 20, 12:00:00 EST 2012
    DESCRIPTION  "MIB Updates for BTI 7000 Rel 10.2.3:
                 - added cfmDestinationAddress attribute to the pvxSwitchTable entry
                   to allow CCM messages to have a unicast/multicast addressing"
    REVISION     "201212061200Z"  -- Thursday, December 06, 12:00:00 EST 2012
    DESCRIPTION  "MIB Updates for BTI 7000 Rel 10.2.3:
                 - added trap cfmRMepStateChangeEvt to provide a remote MEP state 
                   change alert."
    REVISION     "201206201200Z"  -- Wednesday, June 20, 12:00:00 EST 2012
    DESCRIPTION  "MIB Updates for BTI 7000 Rel 10.2.0:
                 - added pvxSwitchErpsVlanPropagate to provide an option to
                   user on how the user traffic is converged during ERPS ring
                   failures.
                 - added pvxLGMinLinks to support minimum number of links to
                   be active in a link aggregation group for it to be active.
                 - added pvxClassMapCVlanEndFilter to support C-VLAN range in a class
                   of service."
    REVISION     "201202101200Z"  -- Friday, February 10, 12:00:00 EST 2012
    DESCRIPTION  "MIB Updates for BTI 7000 Rel 9.2.0:
                 - Deprecated pvxVlanPortIngressFiltering in pvxVlanPortTable
                 - removed pvxSwitchMemberAdminState object from the SwitchMemberTable
                 - added new object pvxMSTPPortLoopGuardState
                 - expanded range of pvxUNICPVid value to 0..4094 and set the
                   default value to 0
                 - changed the status of pvxL2IntfIngressFiltering object to deprecated
                 - expanded size range of pvxERPSSrvcNNIMEName object to 1..6"              
    REVISION     "201106231200Z"  -- Thursday, June 23, 12:00:00 EST 2011
    DESCRIPTION  "MIB Updates for BTI 7000 Rel 8.2.1:
                 - Added eptree and evptree to pvxEthSrvcType to 
                   support ETREE services
                 - Added pvxSrvsUNIForwarding to PvxServiceUNIEntry to 
                   support ETREE services
                 - Added attributes to the PVXSwitchModule and 
                   PVXSwitchMember tables to support stacking
                 - Port numbering changes on multiple tables: Static Multicast,
                   Static Unicast, Multicast Group, MSTPXstTable
                 - Added pvxLGMaxLinks to support Active/Standby LAG
                 - Added service-Map to pvxClassMapType to support 
                   per-flow services
                 - Added pvxSrvcUNIServiceMap and pvxSrvcUNIFilterSequence 
                   to support per-flow services
                 - Added pvxSrvcUNIEFPSDEnabled to support EFPSD
                 - Added new tables pvSLAMeasurementProfileTable, 
                   pvxEServiceSlaCrntPMTable, pvxEServiceSlaHistPMTable, 
                   pvxEServieSlaPMThresholdTable, pvxSLAThroughputTestTable, 
                   pvxSLAMsmtInitiatorDBTable, and pvxSLAMsmtResponderDBTable 
                   to support the Y.1731 SLA Measurement feature
                 - Added trap pvxSrvcUNIEFPSDLocalEFPSDStateChangeEvent"
    REVISION     "201008061200Z"  -- Friday, August 6, 12:00:00 EST 2010
    DESCRIPTION  "MIB Updates for BTI 7000 Rel 8.1.0:
                 - changed range of objects representing a slot number
                   to support new 7200 shelf which has 20 slots"                   
    REVISION     "201006181200Z"  -- Friday, June 18, 12:00:00 EST 2010
    DESCRIPTION  "MIB Updates for BTI 7000 Rel 7.3.2.
                 - changed the following tables to use ESrvcVlanId rather than
                   ESrvcName as index value:
                       - pvxMepListTable
                       - pvxEcfmMepDbTable
                       - pvxEcfmLtrTable
                 - removed unused pvxEcfmConfigErrorListTable"
    REVISION     "201002121200Z"  -- Friday, February 12, 12:00:00 EST 2010
    DESCRIPTION  "MIB Updates for BTI 7000 Rel 7.3.0.
                    
                  Existing tables modified to support PVX ECFM, management VLAN and 
                  GVRP functions:
                    - pvxSwitchTable
                    - pvxEthServiceTable
                    - pvxServiceUNITable
                    - Deprecated pvxVlanEgressPortTable and pvxVlanDeleteCounterTable
                     
                  New tables added to support PVX ECFM, management VLAN, ERPS and GVRP services:
                    - pvxMepListTable
                    - pvxEcfmMepTable
                    - pvxEcfmMepDbTable
                    - pvxEcfmMipTable
                    - pvxEcfmConfigErrorListTable
                    - pvxY1731LbStatsTable
                    - pvxEcfmLtrTable
                    - pvxMgmtVLANTable
                    - pvxServiceNNITable
                    - pvxERPSServiceNNITable
                    - pvxERPSServiceTable
                    - pvxDynamicVlanPortTable
                    
                  New tables to support the statistic monitoring of the Ethernet servcies:
                    - pvxESrvcCrntPMTable
                    - pvxESrvcHistPMTable
                    - pvxESrvcBWPrflCrntPMTable
                    - pvxESrvcBWPrflHistPMTable
                    - pvxESrvcBWPrflPMThresholdTable
                    - pvxERPSPortCrntPMTable
                    - pvxERPSPortHistPMTable
                   
                 New events defined:
                    - pvxESrvcBWPrflBDWUtlzTcaEvt
                    - pvxESrvcOperStateChangeEvt
                    - pvxERPSSrvcNNIProtectionSwitchChangeEvent"                

    REVISION     "200812191200Z"  -- Thursday, December 19, 12:00:00 EST 2008
    DESCRIPTION  "MIB Updates for BTI 7000 Rel 7.1.2: Completion of SNMP
                  coverage for Packet VX.
                  - Remove pvxServiceMapTable
                  - Add pvxPbCVidRegistrationTable
                  - Modify pvxCtrlFrmProfileTable
                  - Add pvxTunnmacAddrProfileTable
                  - Add AdminStatus, operStatus, and MTU attributes to pvxLagGroupTable
                  - Add MSTP notification objects.                
                  - Add condition notifications and event notifications for ethernet interface,
                    L2 interface, MSTP and LAG.
                  - Add PM tables for ethernet interface, L2 interface, MSTP protocol and LAG.
                  - Other modified tables include: pvxSwitchTable, pvxL2IntfTable, pvxLagTable,
                    pvxVlanTable, pvxMSTPGenTable, and pvxMSTPMapTable."
  
    REVISION     "200803101200Z"  -- Monday, March 10, 12:00:00 EST 2008
    DESCRIPTION  "MIB Updates for BTI 7000 Rel 7.1.2: Completion of SNMP
                  coverage for Packet VX.
                  New and expanded tables and other objects include:
                  - pvxSwitchTable
                  - pvxSwitchMemberTable"
                   
    ::= { btiModules 5 }




-- -------------------------------------------------------------
-- Textual Conventions
-- -------------------------------------------------------------
PvxPhyPort ::= TEXTUAL-CONVENTION
    STATUS      current
    DESCRIPTION "Port list in the format of shelf/slot/porttype/portNum. 
		 shelf: 1, 11, 21, or 31 
		 shot:  1 - 20 
		 porttype: 1 - GE, 2 - 10GE
		 portnum: 1-24 "
    SYNTAX      DisplayString 


PvxPhyPortList ::= TEXTUAL-CONVENTION
    STATUS      current
    DESCRIPTION "Port list in the format of shelf/slot/porttype/portNum. 
		 shelf: 1, 11, 21, or 31 
		 shot:  1 - 20 
		 porttype: 1 - GE, 2 - 10GE
		 portnum: 1-24 "
    SYNTAX      DisplayString 

PvxL2PortList ::= TEXTUAL-CONVENTION
    STATUS      current
    DESCRIPTION "Port list in the format of switch/shelf/slot/porttype/portNum. 
		 switch: 1 - 11
		 shelf: 1, 11, 21, or 31 
		 shot:  1 - 20 
		 porttype: 1 - GE, 2 - 10GE
		 portnum: 1-24 "
    SYNTAX      DisplayString 

PvxVLANPortList ::= TEXTUAL-CONVENTION
    STATUS      current
    DESCRIPTION "Port list in the format of shelf/slot{ports}. 
                 for example: L{1,4};1/1{g2,g6,x1}
                          or: 11/3{g1,g2,g3,x2}
                 The sub-list indicated by L indicates the LAG ports.
                 The sub-list indicated by the shelf/slot pair contains
                     entries for the non-lag ports. They are qualified
                     by g for gigabit ports and x for ten-gigabit ports."
    SYNTAX      DisplayString 

PvxL2Port ::= TEXTUAL-CONVENTION
    STATUS      current
    DESCRIPTION "Port list in the format of switch/shelf/slot/porttype/portNum. 
		 switch: 1 - 11
		 shelf: 1, 11, 21, or 31 
		 shot:  1 - 20 
		 porttype: 1 - GE, 2 - 10GE
		 portnum: 1-24 "
    SYNTAX      DisplayString 


PvxVlanId ::= TEXTUAL-CONVENTION
    STATUS      current
    DESCRIPTION "A 12-bit VLAN ID used in the VLAN Tag header."
    SYNTAX      INTEGER (1..4094)

PvxMSTPVlanList ::= TEXTUAL-CONVENTION
    DISPLAY-HINT "x"
    STATUS       current
    DESCRIPTION  "a binary string representation"
    SYNTAX       OCTET STRING (SIZE (0..128))

PvxPCPDecodingList ::= TEXTUAL-CONVENTION
    STATUS      current
    DESCRIPTION "A 12-bit VLAN ID used in the VLAN Tag header."
    SYNTAX      INTEGER { priority7    (1),
                          prioirty7-DE (2),
                          priority6    (3),
                          priority6-DE (4),
                          priority5    (5),
                          priority5-DE (6),
                          priority4    (7),
                          priority4-DE (8),
                          priority3    (9),
                          priority3-DE (10),
                          priority2    (11),
                          priority2-DE (12),
                          priority1    (13),
                          priority1-DE (14),
                          priority0    (15),
                          priority0-DE (16)}
                          
PvxPolicyDropAction ::= TEXTUAL-CONVENTION
    STATUS      current
    DESCRIPTION "Policy drop action definiiton."
    SYNTAX      INTEGER { drop        (1),
                          doNotDrop   (2),
                          notDefined  (3)} 
                          
PvxQoSColorMode ::= TEXTUAL-CONVENTION
    STATUS      current
    DESCRIPTION "Color aware action definiiton."
    SYNTAX      INTEGER { color-aware   (1),
                          color-blind   (2)} 
                          
PvxQoSPmCounterMode ::= TEXTUAL-CONVENTION
    STATUS      current
    DESCRIPTION "Counter mode for policy action definiiton."
    SYNTAX      INTEGER { count-violate           (1),
                          count-cnfrm             (2),
                          count-cnfrmAndExceed    (3),
                          count-violateAndExceec  (4),
                          notUsed                 (5)}

PvxCVidMapOperStatus ::= TEXTUAL-CONVENTION
    STATUS       current
    DESCRIPTION  ""
    SYNTAX       INTEGER { programmed    (1),
                           notProgrammed (2) }
                           
PvxEcfmTransmitStatus ::= TEXTUAL-CONVENTION
    STATUS      current
    DESCRIPTION
       "An enumerated value indicates whether LBM or LTM trasmission 
        can be initiated.
        ready(1)              Indicates LTM or LBM transmission 
                              can be initiated.
        notReady(2)           Indicates LTM or LBM transmission
                              can not be initiated.
        transmit(3)           To initiate the transmission of LBM or LTM.
        NOTE: A 2 value is used to initiate LBM or LTM transmission."
        
    SYNTAX      INTEGER {
                  ready                   (1),
                  notReady                (2),
                  transmit                (3)
                }

PvxEcfmMepDefects ::= TEXTUAL-CONVENTION
    STATUS      current
    DESCRIPTION
       "A MEP can detect and report a number of defects, and multiple
        defects can be present at the same time. These defects are:
        remoteMepDefect(1) A remote MEP is reported the RDI bit in its
                     last CCM.
        macStatusDefect(2) Either some remote MEP is reporting its
                     Interface Status TLV as not isUp, or all remote
                     MEPs are reporting a Port Status TLV that
                     contains some value other than psUp.
        remoteCCMDefect(3) The MEP is not receiving valid CCMs from at
                     least one of the remote MEPs.
        errorCCMDefect(4) The MEP has received at least one invalid CCM
                     whose CCM Interval has not yet timed out.
        xConnCCMDefect(5) The MEP has received at least one CCM from
                     either another MAID or a lower MD Level whose
                     CCM Interval has not yet timed out."
    
    SYNTAX BITS {
                remoteMepDefect(0),
                macStatusDefect(1),
                remoteCCMDefect(2),
                errorCCMDefect(3),
                xConnCCMDefect(4)
                }

PvxY1731MepDefects ::= TEXTUAL-CONVENTION
    STATUS      current
    DESCRIPTION
       "A MEP can detect and report a number of defects, 
        and multiple defects can be present at the same time.
        These defects conditions are:
        remoteMepDefectCondition (1)     The MEP has encountered remote MEP defect
                                         condition.
        lossOfContinuity (2)             The MEP has encountered loss of continuity
                                         defect condition.
        bDefUnexpectedPeriod (3)         The MEP has encountered unexpected period
                                         defect condition.
        unexpectedPeriod (4)             The MEP has encountered unexpected MEP defect
                                         condition.
        misMerge (5)                     The MEP has encountered mismerge defect
                                         condition.
        unexpectedMegLevel (6)           The MEP has encountered unexpected MEG level
                                         defect condition.
        localLinkFailure (7)             The MEP has encountered local link failure
                                         defect condition.
        internalHWFailure (8)            The MEP has encountered internal hardware
                                         failure defect condition.
        internalSWFailure (9)            The MEP has encountered internal software
                                         failure defect condition.
        aisCondition(10)                 The MEP has encountered alarm indication defect
                                         condition.
        lckCondition(11)                 The MEP has encountered locked defect
                                         condition. "
    SYNTAX      BITS{
                        remoteMepDefectCondition (0),
                        lossOfContinuity (1),
                        unexpectedPeriod (2),
                        unexpectedMep (3),
                        misMerge (4),
                        unexpectedMegLevel (5),
                        localLinkFailure (6),
                        internalHWFailure (7),
                        internalSWFailure (8),
                        aisCondition (9),
                        lckCondition (10)
                    }

PvxEcfmRemoteMepState ::= TEXTUAL-CONVENTION
    STATUS      current
    DESCRIPTION
       "Operational state of the remote MEP state machine.  This
        state machine monitors the reception of valid CCMs from a
        remote MEP with a specific MEPID.  It uses a timer that
        expires in 3.5 times the length of time indicated by the
        dot1agCfmMaCcmInterval object.
        rMepIdle(1)            Momentary state during reset.
        rMepStart(2)           The timer has not expired since the
                               state machine was reset, and no valid
                               CCM has yet been received.
        rMepFailed(3)          The timer has expired, both since the
                               state machine was reset, and since a
                               valid CCM was received.
        rMepOk(4)              The timer has not expired since a
                               valid CCM was received."
    SYNTAX      INTEGER {
                  rMepIdle    (1),
                  rMepStart   (2),
                  rMepFailed  (3),
                  rMepOk      (4)
                }

PvxEcfmConfigErrors ::= TEXTUAL-CONVENTION
    STATUS      current
    DESCRIPTION
       "While making the MIP creation evaluation described in 802.1ag
        clause 22.2.3, the management entity can encounter errors in
        the configuration. These are possible errors that can be
        encountered:
        CFMleak(0)   MA x is associated with a specific VID list,
                     one or more of the VIDs in MA x can pass through
                     the Bridge Port, no Down MEP is configured on
                     any Bridge Port for MA x, and some other MA y,
                     at a higher MD Level than MA x, and associated
                     with at least one of the VID(s) also in MA x,
                     does have a MEP configured on the Bridge Port.
        conflictingVids(1)  MA x is associated with a specific VID
                     list, an Up MEP is configured on MA x on the
                     Bridge Port, and some other MA y, associated
                     with at least one of the VID(s) also in MA x,
                     also has an Up MEP configured on some Bridge
                     Port.
        ExcessiveLevels(2)  The number of different MD Levels at
                     which MIPs are to be created on this port
                     exceeds the Bridge's capabilities (see
                     subclause 22.3).
        OverlappedLevels(3) A MEP is created for one VID at one MD
                     Level, but a MEP is configured on another
                     VID at that MD Level or higher, exceeding
                     the Bridge's capabilities."
    SYNTAX BITS {
                cfmLeak(0),
                conflictingVids(1),
                excessiveLevels(2),
                overlappedLevels(3)
               }
                           
PvxEcfmRelayActionFieldValue ::= TEXTUAL-CONVENTION
    STATUS      current
    DESCRIPTION
       "Possible values the Relay action field can take."
    SYNTAX      INTEGER {
                  rlyHit     (1),
                  rlyFdb     (2),
                  rlyMpdb    (3)
                }
               
PvxEcfmIngressActionFieldValue ::= TEXTUAL-CONVENTION
    STATUS      current
    DESCRIPTION
       "Possible values returned in the ingress action field."
    SYNTAX      INTEGER {
                  ingOk       (1),
                  ingDown     (2),
                  ingBlocked  (3),
                  ingVid      (4)
                }

PvxEcfmEgressActionFieldValue ::= TEXTUAL-CONVENTION
    STATUS      current
    DESCRIPTION
       "Possible values returned in the egress action field."
    SYNTAX      INTEGER {
                  egrOK       (1),
                  egrDown     (2),
                  egrBlocked  (3),
                  egrVid      (4)
                }

PvxErpsVirtualLinkList ::= TEXTUAL-CONVENTION
    STATUS      current
    DESCRIPTION "VIRTUAL-LINK list in the format of vlan-ids delimited by comas. 
                 for example: 100,200,300"
    SYNTAX      DisplayString (SIZE(0..64)) 

PvxESrvcBWPrflPMThresholdLevelType ::= TEXTUAL-CONVENTION
    STATUS       current
    DESCRIPTION  "The type of threshold level used to generate threshold crossing
                  alerts against perEVC and perCoS instances."
    SYNTAX       INTEGER { min15CIR   (1),  -- 15-minute Committed Information Rate
    					   min15EIR   (2),  -- 15-minute Exceed Information Rate
                           day1CIR    (3),  -- 1-day Committed Information Rate
                           day1EIR    (4) } -- 1-day Exceed Information Rate

PvxStackingPortCommState ::= TEXTUAL-CONVENTION
    STATUS      current
    DESCRIPTION
       "Virtual switch stacking port communication state values."
    SYNTAX      INTEGER {
                  noConnection     (1),
                  connectionOk     (2)
                }

PvxVlanIdOrZero ::= TEXTUAL-CONVENTION
    STATUS      current
    DESCRIPTION "A 12-bit VLAN ID used in the VLAN Tag header.
                 Allow a value of zero for MIB objects that need
                 to show the value is not used."
    SYNTAX      INTEGER (0..4094)

-----------------------------------------------------------------------
-----------------------------------------------------------------------
-- Managed object definitions.
-----------------------------------------------------------------------
-----------------------------------------------------------------------
-- pvxBridge	 			OBJECT IDENTIFIER ::= { pvxObjects 1 }
pvxBridgeServices 			OBJECT IDENTIFIER ::= { pvxObjects 2 }
pvxBridgeProfiles 			OBJECT IDENTIFIER ::= { pvxObjects 3 }
pvxBridgeGVRP               OBJECT IDENTIFIER ::= { pvxObjects 5 }

pvxEcfmService              OBJECT IDENTIFIER ::= { pvxBridgeServices  21  }

cfmRMepStateChangeEvtNotifications  OBJECT IDENTIFIER ::= { eventNotifications  36 }
pvxVlanPortLastBpduOriginChangeEvtNotifications OBJECT IDENTIFIER ::= { eventNotifications  37 }
pvxVlanPortAddDynamicVlanEvtNotifications OBJECT IDENTIFIER ::= { eventNotifications  38 }
pvxVlanPortRemoveDynamicVlanEvtNotifications OBJECT IDENTIFIER ::= { eventNotifications  39 }

-----------------------------------------------------------------------
-- Objects related to the Netstender NE as a whole
-----------------------------------------------------------------------

pvxSwitchTable  OBJECT-TYPE
    SYNTAX       SEQUENCE OF PVXSwitchEntry 
    MAX-ACCESS   not-accessible
    STATUS       current
    DESCRIPTION  "This table is used to  configure the switching related 
                  properties of a virtual switch."
    ::= { pvxBridge 1 }

pvxSwitchEntry OBJECT-TYPE
    SYNTAX      PVXSwitchEntry 
    MAX-ACCESS   not-accessible
    STATUS       current
    DESCRIPTION  ""
    INDEX        { pvxSwitchIdx }
    ::= { pvxSwitchTable 1 }


PVXSwitchEntry ::= SEQUENCE { pvxSwitchIdx                            INTEGER,
                              pvxSwitchMode                           INTEGER,
                       	      pvxSwitchInnerEthType                   Integer32,
                       	      pvxSwitchLearning                       INTEGER,
                       	      pvxSwitchAgingTimer                     INTEGER,
                       	      pvxSwitchTimeToAge    	              INTEGER,
                              pvxSwitchMasterNode                     DisplayString,
                              pvxSwitchForceSwitch                    TruthValue,
                              pvxSwitchClearDynamicFDBEntries         TruthValue,
                              pvxSwitchProtocolAdminState             INTEGER,
                              pvxSwitchTunnMacAddrProfile             ProfileNameType,
                              pvxSwitchEvcMEGName                     DisplayString,
                              pvxSwitchEvcMEGLevel                    INTEGER,
                              pvxSwitchName                           DisplayString,
                              pvxSwitchMIPAutoCreate                  TruthValue,
                              pvxSwitchMIPAutoCreateMEL               INTEGER,
                              pvxSwitchStackingPrimary                Integer32,
                              pvxSwitchStackingTimeAsPrimary          Integer32,
                              pvxSwitchErpsVlanPropagate              INTEGER,
                              pvxSwitchCfmDestinationAddress          INTEGER,
                              pvxSwitchIntfBouncingTimerPeriod        INTEGER,
                              pvxSwitchCpuRLCos0PPS                   INTEGER,
                       	      pvxSwitchCpuRLCos1PPS                   INTEGER,
                       	      pvxSwitchCpuRLCos2PPS                   INTEGER,
                       	      pvxSwitchCpuRLCos3PPS                   INTEGER,
                       	      pvxSwitchCpuRLCos4PPS                   INTEGER,
                       	      pvxSwitchCpuRLCos5PPS                   INTEGER,
                       	      pvxSwitchCpuRLCos6PPS                   INTEGER,
                       	      pvxSwitchCpuRLCos7PPS                   INTEGER,
                       	      pvxSwitchCpuRLCos0DEPTH                 INTEGER,
                       	      pvxSwitchCpuRLCos1DEPTH                 INTEGER,
                       	      pvxSwitchCpuRLCos2DEPTH                 INTEGER,
                       	      pvxSwitchCpuRLCos3DEPTH                 INTEGER,
                       	      pvxSwitchCpuRLCos4DEPTH                 INTEGER,
                       	      pvxSwitchCpuRLCos5DEPTH                 INTEGER,
                       	      pvxSwitchCpuRLCos6DEPTH                 INTEGER,
                       	      pvxSwitchCpuRLCos7DEPTH                 INTEGER,
                       	      pvxSwitchCpuRLCos0BURST                 INTEGER,
                       	      pvxSwitchCpuRLCos1BURST                 INTEGER,
                       	      pvxSwitchCpuRLCos2BURST                 INTEGER,
                       	      pvxSwitchCpuRLCos3BURST                 INTEGER,
                       	      pvxSwitchCpuRLCos4BURST                 INTEGER,
                       	      pvxSwitchCpuRLCos5BURST                 INTEGER,
                       	      pvxSwitchCpuRLCos6BURST                 INTEGER,
                       	      pvxSwitchCpuRLCos7BURST                 INTEGER,
                       	      pvxSwitchMirrorFromCpu                  INTEGER,
                              pvxSwitchLldpTrapInterval               INTEGER,
                              pvxSwitchMEGIDPad                       TruthValue,
                              pvxSwitchTPIDAwareOrBlind               INTEGER,
                       	      pvxSwitchRowStatus    	              RowStatus
                             }


pvxSwitchIdx 	OBJECT-TYPE
    SYNTAX       INTEGER(1..11)
    MAX-ACCESS   accessible-for-notify
    STATUS       current
    DESCRIPTION  "An index represents the switch ID. It can be from 1 to 11."
    ::= { pvxSwitchEntry 1 }


pvxSwitchMode         OBJECT-TYPE
    SYNTAX       INTEGER { q-bridge(1),
                           provider-bridge(2) }
    MAX-ACCESS   read-create
    STATUS       current
    DESCRIPTION  "Sets the top-level operational mode for the packetVX Switch, 
                  which is based on the VLAN tagging scheme (802.1Q or 802.1ad) 
                  employed by the customer. "
    DEFVAL       { provider-bridge }
    ::= { pvxSwitchEntry 2 }


pvxSwitchInnerEthType OBJECT-TYPE
    SYNTAX       Integer32
    MAX-ACCESS   read-only
    STATUS       current
    DESCRIPTION  "The inner ethertype (802.1Q) is configurable (switch-level only); 
                  enhancement for customers who want/need to support a C-Tag ethertype 
                  other than the standard 0x8100 value.  Note: this should not be 
                  confused with the OuterEtherTypeDot1ad port attribute, which is 
                  used to define the ethertype for the S-Tag. This object only applies 
                  when the switch is operating in 802.1q mode."
    ::= { pvxSwitchEntry 3 }


pvxSwitchLearning OBJECT-TYPE
    SYNTAX       INTEGER { enabled  (1),
                           disabled (2) }
    MAX-ACCESS   read-create
    STATUS       current
    DESCRIPTION  "This attribute used to enable/disable the MAC learning of the bridge. 
                  MAC Learning can be enabled to populate the Forwarding Database (FDB) 
                  and achieve unicast behavior based on a MAC lookup operation."
    DEFVAL       { enabled }
    ::= { pvxSwitchEntry 4 }


pvxSwitchAgingTimer OBJECT-TYPE
    SYNTAX       INTEGER (0..604800)
    MAX-ACCESS   read-create
    STATUS       current
    DESCRIPTION  "When learning and aging are enabled, FDB entries will age out according 
                 to the timer value.  The aging timer for a particular FDB entry (source 
                 MAC address) is reset when it is learned or re-learned."
    DEFVAL       { 300 }
    ::= { pvxSwitchEntry 5 }


pvxSwitchTimeToAge OBJECT-TYPE
    SYNTAX       INTEGER (0..604800)
    MAX-ACCESS   read-create
    STATUS       current
    DESCRIPTION  ""
    ::= { pvxSwitchEntry 6 }

pvxSwitchMasterNode	OBJECT-TYPE
    SYNTAX       DisplayString
    MAX-ACCESS   read-only
    STATUS       deprecated
    DESCRIPTION  "This is a read-only attribute used to inform the user as to the amount of 
                  time remaining before the next aging cycle - the time at which FDB entries 
                  may be deleted as a result of aging."
    ::= { pvxSwitchEntry 7 }

pvxSwitchForceSwitch	 OBJECT-TYPE
    SYNTAX       TruthValue 
    MAX-ACCESS   read-create
    STATUS       deprecated
    DESCRIPTION  ""
    ::= { pvxSwitchEntry 8 }
    
-- { pvxSwitchEntry 9 } obsolete, removed

pvxSwitchClearDynamicFDBEntries	 OBJECT-TYPE
    SYNTAX       TruthValue 
    MAX-ACCESS   read-create
    STATUS       current
    DESCRIPTION  "An action trigger object.  Setting the value of this object to 'true' will
                  cause the switch to clear out all of the dynamic MAC address table
                  entries in its forwarding databse table, forcing the switch to relearn
                  all its dynamic entries.  When reading this object, the value 'false' will
                  always be returned."
    ::= { pvxSwitchEntry 10 }


pvxSwitchProtocolAdminState OBJECT-TYPE 
	 SYNTAX INTEGER (0..1023)
	 MAX-ACCESS read-create
	 STATUS current
	 DESCRIPTION "Bit map indicating protocols enabled on the switch.  A 
                  value of one in the bit map means the corresponding  
                  protocol is enabled.  Zero means the protocol is  
                  disabled. The bit definition is as follow:                  
                    mstp(0) 
                    lacp(1) 
                    ieee802dot1x(2) 
                    gvrp(3) 
                    igmp(4)
                    802.1ag(5)
                    Y.1731(6)
                    ccmOffload(7)
                    erps(8)
                    slaMeasurement(9)"
 	::= { pvxSwitchEntry 11  }

pvxSwitchTunnMacAddrProfile OBJECT-TYPE
    SYNTAX       ProfileNameType
    MAX-ACCESS   read-create
    STATUS       current
    DESCRIPTION  " The name of the Tunnel MAC Address profile used by the switch. "
    ::= { pvxSwitchEntry 12 }

pvxSwitchEvcMEGName  OBJECT-TYPE
    SYNTAX       DisplayString (SIZE(1..6))
    MAX-ACCESS   read-create
    STATUS       current
    DESCRIPTION  "Name of the EVC Maintanence Entity Group. Maximum length is 6 characters. Default value is set to BTI by the system."
    ::= { pvxSwitchEntry 13 }

pvxSwitchEvcMEGLevel  OBJECT-TYPE
    SYNTAX       INTEGER (1..7)
    MAX-ACCESS   read-create
    STATUS       current
    DESCRIPTION  "The EVC Maintanence Entity Group Level."
    ::= { pvxSwitchEntry 14 }

pvxSwitchName  OBJECT-TYPE
    SYNTAX       DisplayString (SIZE(1..32))
    MAX-ACCESS   read-create
    STATUS       current
    DESCRIPTION  "The switch name string."
    ::= { pvxSwitchEntry 15 }

pvxSwitchMIPAutoCreate  OBJECT-TYPE
    SYNTAX       TruthValue
    MAX-ACCESS   read-create
    STATUS       current
    DESCRIPTION  "This field controls MIP auto-creation funcion. When set true, 
                  MIPs are created automatically."
    ::= { pvxSwitchEntry 16 }

pvxSwitchMIPAutoCreateMEL  OBJECT-TYPE
    SYNTAX       INTEGER (1..7)
    MAX-ACCESS   read-create
    STATUS       current
    DESCRIPTION  "The maintanence entity Level at which MIPs are auto created."
    ::= { pvxSwitchEntry 17 }

pvxSwitchStackingPrimary OBJECT-TYPE
    SYNTAX       Integer32
    MAX-ACCESS   read-only
    STATUS       current
    DESCRIPTION  "The instance number of the primary PacketVX."
    ::= { pvxSwitchEntry 18 }

pvxSwitchStackingTimeAsPrimary OBJECT-TYPE
    SYNTAX       Integer32
    MAX-ACCESS   read-only
    STATUS       current
    DESCRIPTION  "The number of seconds that the stacking primary has remained as 
                  primary."
    ::= { pvxSwitchEntry 19 }

pvxSwitchErpsVlanPropagate OBJECT-TYPE
    SYNTAX       INTEGER { fast  (1),
                           slow (2) }
    MAX-ACCESS   read-create
    STATUS       current
    DESCRIPTION  "This provides option the user to control how the user traffic
                  needs to be converged in case of ERPS ring failures. With
                  fast option, user traffic converges in the order of ERPS
                  times. The side effect is there is redundant traffic all over
                  rings. With slow option, user traffic flows on the shortest
                  possible path. There is no extra traffic all over the ring.
                  But, when ERPS ring failures occur, the convergence times will
                  not be in the order of ERPS convergence times."
    DEFVAL       { fast }
    ::= { pvxSwitchEntry 20 }

pvxSwitchCfmDestinationAddress OBJECT-TYPE
    SYNTAX       INTEGER { unicast   (1),
                           multicast (2) }
    MAX-ACCESS   read-create
    STATUS       current
    DESCRIPTION  "This provides an option to the user to control CCM message
                  destination address which will scale down time necessary to 
                  process CCM messages."
    ::= { pvxSwitchEntry 21  }

pvxSwitchIntfBouncingTimerPeriod OBJECT-TYPE
    SYNTAX       INTEGER (1..15)
    MAX-ACCESS   read-create
    STATUS       current
    DESCRIPTION  "A timer interval in seconds used to detect port bouncing state."
    ::= { pvxSwitchEntry 22 }

pvxSwitchCpuRLCos0PPS OBJECT-TYPE
    SYNTAX       INTEGER (1..10000)
    MAX-ACCESS   read-only
    STATUS       current
    DESCRIPTION  "packets per sec for queue 0 used to set pps for cpu-rate-limit."
    ::= { pvxSwitchEntry 23 }

pvxSwitchCpuRLCos1PPS OBJECT-TYPE
    SYNTAX       INTEGER (1..10000)
    MAX-ACCESS   read-only
    STATUS       current
    DESCRIPTION  "packets per sec for queue 1 used to set pps for cpu-rate-limit."
    ::= { pvxSwitchEntry 24 }

pvxSwitchCpuRLCos2PPS OBJECT-TYPE
    SYNTAX       INTEGER (1..10000)
    MAX-ACCESS   read-only
    STATUS       current
    DESCRIPTION  "packets per sec for queue 2 used to set pps for cpu-rate-limit."
    ::= { pvxSwitchEntry 25 }

pvxSwitchCpuRLCos3PPS OBJECT-TYPE
    SYNTAX       INTEGER (1..10000)
    MAX-ACCESS   read-only
    STATUS       current
    DESCRIPTION  "packets per sec for queue 3 used to set pps for cpu-rate-limit."
    ::= { pvxSwitchEntry 26 }

pvxSwitchCpuRLCos4PPS OBJECT-TYPE
    SYNTAX       INTEGER (1..10000)
    MAX-ACCESS   read-only
    STATUS       current
    DESCRIPTION  "packets per sec for queue 4 used to set pps for cpu-rate-limit."
    ::= { pvxSwitchEntry 27 }

pvxSwitchCpuRLCos5PPS OBJECT-TYPE
    SYNTAX       INTEGER (1..10000)
    MAX-ACCESS   read-only
    STATUS       current
    DESCRIPTION  "packets per sec for queue 5 used to set pps for cpu-rate-limit."
    ::= { pvxSwitchEntry 28 }

pvxSwitchCpuRLCos6PPS OBJECT-TYPE
    SYNTAX       INTEGER (1..10000)
    MAX-ACCESS   read-only
    STATUS       current
    DESCRIPTION  "packets per sec for queue 6 used to set pps for cpu-rate-limit."
    ::= { pvxSwitchEntry 29 }

pvxSwitchCpuRLCos7PPS OBJECT-TYPE
    SYNTAX       INTEGER (1..10000)
    MAX-ACCESS   read-only
    STATUS       current
    DESCRIPTION  "packets per sec for queue 7 used to set pps for cpu-rate-limit."
    ::= { pvxSwitchEntry 30 }

pvxSwitchCpuRLCos0DEPTH OBJECT-TYPE
    SYNTAX       INTEGER (1..10000)
    MAX-ACCESS   read-only
    STATUS       current
    DESCRIPTION  "number of packets for queue 0 used to set DEPTH for cpu-rate-limit."
    ::= { pvxSwitchEntry 31 }

pvxSwitchCpuRLCos1DEPTH OBJECT-TYPE
    SYNTAX       INTEGER (1..10000)
    MAX-ACCESS   read-only
    STATUS       current
    DESCRIPTION  "number of packets for queue 1 used to set DEPTH for cpu-rate-limit."
    ::= { pvxSwitchEntry 32 }

pvxSwitchCpuRLCos2DEPTH OBJECT-TYPE
    SYNTAX       INTEGER (1..10000)
    MAX-ACCESS   read-only
    STATUS       current
    DESCRIPTION  "number of packets for queue 2 used to set DEPTH for cpu-rate-limit."
    ::= { pvxSwitchEntry 33 }

pvxSwitchCpuRLCos3DEPTH OBJECT-TYPE
    SYNTAX       INTEGER (1..10000)
    MAX-ACCESS   read-only
    STATUS       current
    DESCRIPTION  "number of packets for queue 3 used to set DEPTH for cpu-rate-limit."
    ::= { pvxSwitchEntry 34 }

pvxSwitchCpuRLCos4DEPTH OBJECT-TYPE
    SYNTAX       INTEGER (1..10000)
    MAX-ACCESS   read-only
    STATUS       current
    DESCRIPTION  "number of packets for queue 4 used to set DEPTH for cpu-rate-limit."
    ::= { pvxSwitchEntry 35 }

pvxSwitchCpuRLCos5DEPTH OBJECT-TYPE
    SYNTAX       INTEGER (1..10000)
    MAX-ACCESS   read-only
    STATUS       current
    DESCRIPTION  "number of packets for queue 5 used to set DEPTH for cpu-rate-limit."
    ::= { pvxSwitchEntry 36 }

pvxSwitchCpuRLCos6DEPTH OBJECT-TYPE
    SYNTAX       INTEGER (1..10000)
    MAX-ACCESS   read-only
    STATUS       current
    DESCRIPTION  "number of packets for queue 6 used to set DEPTH for cpu-rate-limit."
    ::= { pvxSwitchEntry 37 }

pvxSwitchCpuRLCos7DEPTH OBJECT-TYPE
    SYNTAX       INTEGER (1..10000)
    MAX-ACCESS   read-only
    STATUS       current
    DESCRIPTION  "number of packets for queue 7 used to set DEPTH for cpu-rate-limit."
    ::= { pvxSwitchEntry 38 }

pvxSwitchCpuRLCos0BURST OBJECT-TYPE
    SYNTAX       INTEGER (1..10000)
    MAX-ACCESS   read-only
    STATUS       current
    DESCRIPTION  "burst size for queue 0 used to set BURST for cpu-rate-limit."
    ::= { pvxSwitchEntry 39 }

pvxSwitchCpuRLCos1BURST OBJECT-TYPE
    SYNTAX       INTEGER (1..10000)
    MAX-ACCESS   read-only
    STATUS       current
    DESCRIPTION  "burst size for queue 1 used to set BURST for cpu-rate-limit."
    ::= { pvxSwitchEntry 40 }

pvxSwitchCpuRLCos2BURST OBJECT-TYPE
    SYNTAX       INTEGER (1..10000)
    MAX-ACCESS   read-only
    STATUS       current
    DESCRIPTION  "burst size for queue 2 used to set BURST for cpu-rate-limit."
    ::= { pvxSwitchEntry 41 }

pvxSwitchCpuRLCos3BURST OBJECT-TYPE
    SYNTAX       INTEGER (1..10000)
    MAX-ACCESS   read-only
    STATUS       current
    DESCRIPTION  "burst size for queue 3 used to set BURST for cpu-rate-limit."
    ::= { pvxSwitchEntry 42 }

pvxSwitchCpuRLCos4BURST OBJECT-TYPE
    SYNTAX       INTEGER (1..10000)
    MAX-ACCESS   read-only
    STATUS       current
    DESCRIPTION  "burst size for queue 4 used to set BURST for cpu-rate-limit."
    ::= { pvxSwitchEntry 43 }

pvxSwitchCpuRLCos5BURST OBJECT-TYPE
    SYNTAX       INTEGER (1..10000)
    MAX-ACCESS   read-only
    STATUS       current
    DESCRIPTION  "burst size for queue 5 used to set BURST for cpu-rate-limit."
    ::= { pvxSwitchEntry 44 }

pvxSwitchCpuRLCos6BURST OBJECT-TYPE
    SYNTAX       INTEGER (1..10000)
    MAX-ACCESS   read-only
    STATUS       current
    DESCRIPTION  "burst size for queue 6 used to set BURST for cpu-rate-limit."
    ::= { pvxSwitchEntry 45 }

pvxSwitchCpuRLCos7BURST OBJECT-TYPE
    SYNTAX       INTEGER (1..10000)
    MAX-ACCESS   read-only
    STATUS       current
    DESCRIPTION  "burst size for queue 7 used to set BURST for cpu-rate-limit."
    ::= { pvxSwitchEntry 46 }

pvxSwitchMirrorFromCpu OBJECT-TYPE
    SYNTAX       MirrorConfigType
    MAX-ACCESS   read-create
    STATUS       current
    DESCRIPTION  "Mirror from CPU. CPU can not be configured as a MTP port."
    ::= { pvxSwitchEntry 47 }

pvxSwitchLldpTrapInterval OBJECT-TYPE
    SYNTAX       INTEGER (5..3600)
    MAX-ACCESS   read-create
    STATUS       current
    DESCRIPTION  "LLDP time intervalbetween RemoteChange traps."
    ::= { pvxSwitchEntry 48 }

pvxSwitchMEGIDPad  OBJECT-TYPE
    SYNTAX       TruthValue
    MAX-ACCESS   read-create
    STATUS       current
    DESCRIPTION  "This configuration determines how the ICC and UMC of CCM packet will be 
                  concatenated together to make the MEG-ID.   If padding is true then the 
                  ICC will be padded to 6 characters.   If padding is false then the UMC 
                  will follow the ICC immediately with no padding bytes between."
    DEFVAL { true }
    ::= { pvxSwitchEntry 49 }

pvxSwitchTPIDAwareOrBlind  OBJECT-TYPE
    SYNTAX       INTEGER { aware      (1),
	                       blind      (2)
			     }
    MAX-ACCESS   read-create
    STATUS       current
    DESCRIPTION  "It is an indication of whether EPLINE/EPLAN EServices are transparent for all 
 	              the custome pacekts on a virtual switch. The default value is TPID aware."
    DEFVAL { 1 }
    ::= { pvxSwitchEntry 50 }

pvxSwitchRowStatus OBJECT-TYPE
    SYNTAX       RowStatus
    MAX-ACCESS   read-create
    STATUS       current
    DESCRIPTION  "Used to control the addition and deletion of entries in the
                  switch table, which in turn controls provisioning
                  and deprovisioning of the switches."
    ::= { pvxSwitchEntry 100 }
 

-----------------------------------------------------------------------
-- Switch Member Table
-----------------------------------------------------------------------

pvxSwitchMemberTable     OBJECT-TYPE
    SYNTAX       SEQUENCE OF PVXSwitchMemberEntry
    MAX-ACCESS   not-accessible
    STATUS       current
    DESCRIPTION  "This table is used to configure the members of a virtual switch. Each 
				   member corresponds to the physical pack in the system."
                  
    ::= { pvxBridge 2 }


pvxSwitchMemberEntry  OBJECT-TYPE
    SYNTAX       PVXSwitchMemberEntry
    MAX-ACCESS   not-accessible
    STATUS       current
    DESCRIPTION  ""
    INDEX        { pvxSwitchMemberIdx,
                   pvxSwitchMemberInstIdx }
    ::= { pvxSwitchMemberTable  1 }

PVXSwitchMemberEntry ::= SEQUENCE { pvxSwitchMemberIdx     		  INTEGER,
                                    pvxSwitchMemberInstIdx  		  INTEGER,
                       		    pvxSwitchMemberShelfId 	   	  INTEGER,
                       		    pvxSwitchMemberSlotId 	    	  INTEGER,
                       		    pvxSwitchMemberStackingState          INTEGER,
                       		    pvxSwitchMemberStackingPortCommState  PvxStackingPortCommState,
                       		    pvxSwitchMemberBackplaneCommState     PvxStackingPortCommState,
                       		    pvxSwitchMemberRowStatus    	      RowStatus }

pvxSwitchMemberIdx OBJECT-TYPE
    SYNTAX       INTEGER(1..11)
    MAX-ACCESS   accessible-for-notify
    STATUS       current
    DESCRIPTION  "An index represents the switch ID. It can be from 1 to 11."
    ::= { pvxSwitchMemberEntry 1 }

pvxSwitchMemberInstIdx     OBJECT-TYPE
    SYNTAX       INTEGER (1..2)
    MAX-ACCESS   accessible-for-notify
    STATUS       current
    DESCRIPTION  "An index represents the member ID. It can be from 1 to 2."
    ::= { pvxSwitchMemberEntry  2 }


pvxSwitchMemberShelfId OBJECT-TYPE
    SYNTAX       INTEGER (1|11|21|31) 
    MAX-ACCESS   read-create
    STATUS       current
    DESCRIPTION  "The number of the shelf on which the member is
                  provisioned."
    ::= { pvxSwitchMemberEntry 3 }


pvxSwitchMemberSlotId OBJECT-TYPE
    SYNTAX       INTEGER (1|3|5|7|9|11|13|15|17|19)
    MAX-ACCESS   read-create
    STATUS       current
    DESCRIPTION  "The number of the slot on which the member is
                  provisioned."
    ::= { pvxSwitchMemberEntry 4 }

-- { pvxSwitchMemberEntry 5 } obsolete, removed

-- { pvxSwitchMemberEntry 6 } obsolete, removed

-- { pvxSwitchMemberEntry 7 } obsolete, removed
    
pvxSwitchMemberStackingState  OBJECT-TYPE
    SYNTAX       INTEGER { disabled   (1),
	                   unstacked  (2),
	                   primary    (3),
	                   secondary  (4),
                           notPresent (5) }
    MAX-ACCESS   read-only
    STATUS       current
    DESCRIPTION  "If the AdminState is disabled, the stacking state will be disabled. If there is
	          only one PacketVX enabled in the switch, the value of this variable will be unstacked.
	          If there is more than one PacketVX, then the card running the control plane will be
	          primary, any other cards will be secondary. If there is no PacketVX in the slot,
		  the StackingState is notPresent"
    ::= { pvxSwitchMemberEntry 8 }
    
pvxSwitchMemberStackingPortCommState  OBJECT-TYPE
    SYNTAX       PvxStackingPortCommState
    MAX-ACCESS   read-only
    STATUS       current
    DESCRIPTION  "If the redundancy manager believes it can communicate with its peer across the stacking
	          port, the value of this variable will be connectionOk. Otherwise, it will be noConnection."
    ::= { pvxSwitchMemberEntry 9 }
    
pvxSwitchMemberBackplaneCommState  OBJECT-TYPE
    SYNTAX       PvxStackingPortCommState
    MAX-ACCESS   read-only
    STATUS       current
    DESCRIPTION  "If the redundancy manager believes it can communicate with its peer across the backplane,
	          the value of this variable will be connectionOk. Otherwise, it will be noConnection."
    ::= { pvxSwitchMemberEntry 10 }

pvxSwitchMemberRowStatus  OBJECT-TYPE
    SYNTAX       RowStatus
    MAX-ACCESS   read-create
    STATUS       current
    DESCRIPTION  ""
    ::= { pvxSwitchMemberEntry 100 }


-----------------------------------------------------------------------
-- Objects related to provisioned Ethernet facilities 
------------------------------------------------------------------------


-----------------------------------------------------------------------
-- Vlan Table
-----------------------------------------------------------------------
pvxVLANTable OBJECT-TYPE
    SYNTAX       SEQUENCE OF PVXVLANEntry
    MAX-ACCESS   not-accessible
    STATUS       current
    DESCRIPTION  "This table is used to configure the Vlan related entries 
                  on a particular port of a virtual switch member."
    ::= { pvxBridge 4 }

pvxVLANEntry OBJECT-TYPE
    SYNTAX       PVXVLANEntry
    MAX-ACCESS   not-accessible
    STATUS       current
    DESCRIPTION  "The conceptual row object of the Vlan Config table."
    INDEX        { pvxVLANSwitchIdx,
                   pvxVLANIdx }
    ::= { pvxVLANTable 1 }

PVXVLANEntry ::= SEQUENCE { pvxVLANSwitchIdx            INTEGER,
                            pvxVLANIdx                  INTEGER,
                            pvxVLANMemberPortList       PvxVLANPortList,
                            pvxVLANUnTaggedPortList     PvxVLANPortList,
                            pvxVLANMacLearning          INTEGER, 
                            pvxVLANAdminState           INTEGER,
                            pvxVLANMSTPId               Integer32,
                            pvxVLANService              DisplayString,
                            pvxVLANForbiddenPortList    PvxVLANPortList,
                            pvxVLANOperStatus           INTEGER,
                            pvxVLANRowStatus            RowStatus }

pvxVLANSwitchIdx OBJECT-TYPE
    SYNTAX       INTEGER(1..11)
    MAX-ACCESS   not-accessible
    STATUS       current
    DESCRIPTION  "This object represents the particular switch id on which 
                  Vlan is configured."
    ::= { pvxVLANEntry 1 }

pvxVLANIdx OBJECT-TYPE
    SYNTAX       INTEGER(1..4094) 
    MAX-ACCESS   not-accessible
    STATUS       current
    DESCRIPTION  "This object is the index of the Vlan id of the CP."
    ::= { pvxVLANEntry 2 }

-- { pvxVLANEntry 3 } obsolete, removed

pvxVLANMemberPortList OBJECT-TYPE
    SYNTAX   PvxL2PortList
    MAX-ACCESS   read-create
    STATUS       current
    DESCRIPTION  "This object represents a single ingress port or set of ports 
                  which can be configured for a particular vlan. The format 
                  of the set request for this object will depend on the 
                  value of the vlanPortListOpType object being sent in the 
                  set request.
                  Note: The set request will fail if the syntax of the value
                  is not exactly the same as defined by vlanPortListOpType 
                  description."
    ::= { pvxVLANEntry 4 }

pvxVLANUnTaggedPortList OBJECT-TYPE
    SYNTAX PvxL2PortList 
    MAX-ACCESS   read-create
    STATUS       current
	DESCRIPTION 	"The set of ports which are transmitting traffic for
        			 this VLAN as untagged frames.
                  	 Note: The set request will fail if the syntax of the value 
                     is not exactly the same as defined by vlanPortListOpType 
                     description."
    ::= { pvxVLANEntry 5 }
    
pvxVLANMacLearning OBJECT-TYPE
    SYNTAX       INTEGER { enable  (1),
                           disable (2) }
    MAX-ACCESS   read-create
    STATUS       current
    DESCRIPTION  "This object is used to configure the Vlan Mac learnining"
    DEFVAL       { enable }
    ::= { pvxVLANEntry 6 }

pvxVLANAdminState OBJECT-TYPE
    SYNTAX       INTEGER { enable (1),
                           disable (2) }
    MAX-ACCESS   read-create
    STATUS       current
    DESCRIPTION  "The administrative status of the Vlan."
    DEFVAL       { enable }
    ::= { pvxVLANEntry 7 }

pvxVLANMSTPId OBJECT-TYPE
    SYNTAX       Integer32
    MAX-ACCESS   read-create
    STATUS       current
    DESCRIPTION  "An alpha-numeric book keeping attribute for the VLAN."
    ::= { pvxVLANEntry 8 }

pvxVLANService OBJECT-TYPE
    SYNTAX       DisplayString (SIZE(0..32))
    MAX-ACCESS   read-only
    STATUS       current
    DESCRIPTION  "Name of the service associated with this VLAN. If no
                  service is associated with the value is a zero length 
                  string."
    ::= { pvxVLANEntry 9 }
    
pvxVLANForbiddenPortList OBJECT-TYPE
    SYNTAX PvxL2PortList 
    MAX-ACCESS   read-create
    STATUS       current
    DESCRIPTION  "The set of ports which GVRP is forbidden to learn."
    ::= { pvxVLANEntry 10 }
        
pvxVLANOperStatus OBJECT-TYPE
   	SYNTAX       INTEGER { up       (1),
                               down     (2),
			       reserved (3) }
   	MAX-ACCESS   read-only 
   	STATUS       current
   	DESCRIPTION  "The current operational state of the VLAN."
    ::= {pvxVLANEntry 11 }

pvxVLANRowStatus OBJECT-TYPE
    SYNTAX       RowStatus
    MAX-ACCESS   read-create
    STATUS       current
    DESCRIPTION  "This object is used to create a new row in the vlan
                  table."
    ::= { pvxVLANEntry 100 }

-----------------------------------------------------------------------
-- fdbTable Table
-----------------------------------------------------------------------
pvxFDBTable OBJECT-TYPE
    SYNTAX       SEQUENCE OF PVXFDBEntry
    MAX-ACCESS   not-accessible
    STATUS       current
    DESCRIPTION  "This table is used to configure the MAC (FDB) related 
                  entries."
    ::= {pvxBridge 5 }

pvxFDBEntry OBJECT-TYPE
    SYNTAX       PVXFDBEntry
    MAX-ACCESS   not-accessible
    STATUS       current
    DESCRIPTION  "The conceptual row object of the forwardinngDB table."
    INDEX        { pvxFDBSwitchIdx,
                   pvxFDBVlanIdx,
                   pvxFDBMACAddrIdx }
    ::= { pvxFDBTable 1 }

PVXFDBEntry ::= SEQUENCE { 	pvxFDBSwitchIdx       INTEGER,
                        	pvxFDBVlanIdx         Integer32,
                        	pvxFDBMACAddrIdx      MacAddress,       
                        	pvxFDBPort            PvxL2Port, 
                        	pvxFDBAddressType     INTEGER,
                         	pvxFDBRowStatus       RowStatus}

pvxFDBSwitchIdx OBJECT-TYPE
    SYNTAX       INTEGER(1..11)
    MAX-ACCESS   not-accessible
    STATUS       current
    DESCRIPTION  "This object represents the particular switch ID."
    ::= { pvxFDBEntry 1 }

pvxFDBVlanIdx OBJECT-TYPE
    SYNTAX       Integer32
    MAX-ACCESS   not-accessible
    STATUS       current
    DESCRIPTION  "This object is the fdb vlan id."
    ::= { pvxFDBEntry 2 }

pvxFDBMACAddrIdx OBJECT-TYPE
    SYNTAX       MacAddress
    MAX-ACCESS   not-accessible
    STATUS       current
    DESCRIPTION  "This object represents the particular MAC address."
    ::= { pvxFDBEntry 3 }

pvxFDBPort OBJECT-TYPE
    SYNTAX       PvxL2Port 
    MAX-ACCESS   read-only
    STATUS       current
    DESCRIPTION  "This object represents the port of the forwarding Database."
    ::= { pvxFDBEntry 4 }

pvxFDBAddressType OBJECT-TYPE
    SYNTAX       INTEGER { other(1),
                           invalid(2),
                           learned(3),
                           self(4),
                           mgmt(5) } 
    MAX-ACCESS   read-only
    STATUS       current
    DESCRIPTION  "The status of this entry.  The meanings of the values
        are:
            other(1) - none of the following.  This may include
                the case where some other MIB object (not the
                corresponding instance of pvxFDBIntfId, nor an
                entry in the dot1qStaticUnicastTable) is being
                used to determine if and how frames addressed to
                the value of the corresponding instance of
                dot1qTpFdbAddress are being forwarded.
            invalid(2) - this entry is no longer valid (e.g., it
                was learned but has since aged out), but has not
                yet been flushed from the table.
            learned(3) - the value of the corresponding instance
                of dot1qTpFdbPort was learned and is being used.
            self(4) - the value of the corresponding instance of
                dot1qTpFdbAddress represents one of the device's
                addresses.  The corresponding instance of
                dot1qTpFdbPort indicates which of the device's
                ports has this address.
            mgmt(5) - the value of the corresponding instance of
                dot1qTpFdbAddress is also the value of an
                existing instance of dot1qStaticAddress."

    ::= { pvxFDBEntry 5 }

pvxFDBRowStatus OBJECT-TYPE
    SYNTAX       RowStatus
    MAX-ACCESS   read-create
    STATUS       current
    DESCRIPTION  "This object is used to create a new row in the FDB
                  table."
    ::= { pvxFDBEntry 6 }
    
-----------------------------------------------------------------------
-- Static Unicast (FDB) Table
-----------------------------------------------------------------------

pvxStaticUnicastTable OBJECT-TYPE
    SYNTAX       SEQUENCE OF PVXStaticUnicastEntry
    MAX-ACCESS   not-accessible
    STATUS       current
    DESCRIPTION  "A table containing filtering information for Unicast
        MAC addresses for each Filtering Database, configured
        into the device by (local or network) management
        specifying the set of ports to which frames received
        from specific ports and containing specific unicast
        destination addresses are allowed to be forwarded."
    ::= { pvxBridge 6 }

pvxStaticUnicastEntry OBJECT-TYPE
    SYNTAX      PVXStaticUnicastEntry
    MAX-ACCESS  not-accessible
    STATUS      current
    DESCRIPTION "Filtering information configured into the device by 
        (local or network) management specifying the set of 
        ports to which frames received from a specific port and 
        containing a specific unicast destination address are 
        allowed to be forwarded." 
    INDEX        { pvxStaticUnicastSwitchIdx,
                   pvxStaticUnicastVlanIdx,
                   pvxStaticUnicastMACAddrIdx,
                   pvxStaticUnicastReceivePort }
    ::= { pvxStaticUnicastTable 1 }

PVXStaticUnicastEntry ::= SEQUENCE { 	pvxStaticUnicastSwitchIdx       INTEGER,
                pvxStaticUnicastVlanIdx         INTEGER,
                pvxStaticUnicastMACAddrIdx      MacAddress,       
                pvxStaticUnicastReceivePort     PvxL2Port,
                pvxStaticUnicastIntfIdList      PvxVLANPortList,  
                pvxStaticUnicastAddressType     INTEGER,
                pvxStaticUnicastRowStatus       RowStatus }
    
pvxStaticUnicastSwitchIdx OBJECT-TYPE
    SYNTAX       INTEGER(1..11)
    MAX-ACCESS   not-accessible
    STATUS       current
    DESCRIPTION  "This object represents the particular switch ID."
    ::= { pvxStaticUnicastEntry 1 }

pvxStaticUnicastVlanIdx OBJECT-TYPE
    SYNTAX       INTEGER (1..4095) 
    MAX-ACCESS   not-accessible
    STATUS       current
    DESCRIPTION  "This object is the fdb vlan id."
    ::= { pvxStaticUnicastEntry 2 }

pvxStaticUnicastMACAddrIdx OBJECT-TYPE
    SYNTAX       MacAddress
    MAX-ACCESS   not-accessible
    STATUS       current
    DESCRIPTION  "This object represents the particular MAC address."
    ::= { pvxStaticUnicastEntry 3 }

pvxStaticUnicastReceivePort OBJECT-TYPE
    SYNTAX      PvxL2Port 
    MAX-ACCESS  not-accessible
    STATUS      current
    DESCRIPTION "Either the value '0', or the port number of the port
        from which a frame must be received in order for this
        entry's filtering information to apply.  A value of zero
        indicates that this entry applies on all ports of the
        device for which there is no other applicable entry."
    ::= { pvxStaticUnicastEntry 4 }

pvxStaticUnicastIntfIdList OBJECT-TYPE
    SYNTAX      PvxVLANPortList
    MAX-ACCESS  read-create
    STATUS      current
    DESCRIPTION "The set of ports for which a frame with a specific
        unicast address will be flooded in the event that it
        has not been learned."
    ::= { pvxStaticUnicastEntry 5 }

pvxStaticUnicastAddressType OBJECT-TYPE
    SYNTAX      INTEGER {
                    other(1),
                    invalid(2),
                    permanent(3),
                    deleteOnReset(4),
                    deleteOnTimeout(5)
                }
    MAX-ACCESS  read-create
    STATUS      current
    DESCRIPTION "This object indicates the status of this entry.
            other(1) - this entry is currently in use but
                the conditions under which it will remain
                so differ from the following values.
            invalid(2) - writing this value to the object
                removes the corresponding entry.
            permanent(3) - this entry is currently in use
                and will remain so after the next reset of
                the bridge.
            deleteOnReset(4) - this entry is currently in
                use and will remain so until the next
                reset of the bridge.
            deleteOnTimeout(5) - this entry is currently in
                use and will remain so until it is aged out."
    DEFVAL      { permanent }
	::= { pvxStaticUnicastEntry 6 }
    
pvxStaticUnicastRowStatus OBJECT-TYPE
    SYNTAX       RowStatus
    MAX-ACCESS   read-create
    STATUS       current
    DESCRIPTION  "This object is used to create a new row in the 
                  static unicast table."
    ::= { pvxStaticUnicastEntry 100 }

-----------------------------------------------------------------------
-- multicastGroup Table
-----------------------------------------------------------------------
pvxMultiCastGroupTable OBJECT-TYPE
    SYNTAX       SEQUENCE OF PVXMultiCastEntry
    MAX-ACCESS   not-accessible
    STATUS       current
    DESCRIPTION  "This table is used to configure the multicast table related 
                  entries."
    ::= { pvxBridge 7 } 

pvxMultiCastEntry OBJECT-TYPE
    SYNTAX       PVXMultiCastEntry
    MAX-ACCESS   not-accessible
    STATUS       current
    DESCRIPTION  "The conceptual row object of the forwardinngDB table."
    INDEX        { pvxMCSwitchIdx,
                   pvxMCVlanIdx,
                   pvxMCMACAddrIdx }
    ::= { pvxMultiCastGroupTable 1 }

PVXMultiCastEntry ::= SEQUENCE { pvxMCSwitchIdx       INTEGER,
                                 pvxMCVlanIdx         Integer32,
                                 pvxMCMACAddrIdx      MacAddress,       
                                 pvxMCIntfIdList      PvxVLANPortList,
                         	 pvxMCRowStatus       RowStatus }

pvxMCSwitchIdx OBJECT-TYPE
    SYNTAX       INTEGER(1..11)
    MAX-ACCESS   not-accessible
    STATUS       current
    DESCRIPTION  "This object represents the particular switch ID."
    ::= { pvxMultiCastEntry 1 }

pvxMCVlanIdx OBJECT-TYPE
    SYNTAX       Integer32
    MAX-ACCESS   not-accessible
    STATUS       current
    DESCRIPTION  "This object is the fdb vlan id."
    ::= { pvxMultiCastEntry 2 }

pvxMCMACAddrIdx OBJECT-TYPE
    SYNTAX       MacAddress
    MAX-ACCESS   not-accessible
    STATUS       current
    DESCRIPTION  "This object represents the particular MAC address."
    ::= { pvxMultiCastEntry 3 }

pvxMCIntfIdList OBJECT-TYPE
    SYNTAX       PvxVLANPortList 
    MAX-ACCESS   read-only
    STATUS       current
    DESCRIPTION  "The set of ports to which frames received from a
        specific port and destined for a specific Multicast or
        Broadcast MAC address must be forwarded, regardless of
        any dynamic information" 
    ::= { pvxMultiCastEntry 4 }

pvxMCRowStatus OBJECT-TYPE
    SYNTAX       RowStatus
    MAX-ACCESS   read-create
    STATUS       current
    DESCRIPTION  "This object is used to create a new row in the MCG
                  table."
    ::= { pvxMultiCastEntry 6 }

-----------------------------------------------------------------------
-- Static Multicast Table
-----------------------------------------------------------------------

pvxStaticMulticastTable OBJECT-TYPE
    SYNTAX       SEQUENCE OF PVXStaticMulticastEntry
    MAX-ACCESS   not-accessible
    STATUS       current
    DESCRIPTION  "A table containing filtering information for Unicast
        MAC addresses for each Filtering Database, configured
        into the device by (local or network) management
        specifying the set of ports to which frames received
        from specific ports and containing specific unicast
        destination addresses are allowed to be forwarded."
    ::= { pvxBridge 8 }

pvxStaticMulticastEntry OBJECT-TYPE
    SYNTAX      PVXStaticMulticastEntry
    MAX-ACCESS  not-accessible
    STATUS      current
    DESCRIPTION "Filtering information configured into the device by
        (local or network) management specifying the set of
        ports to which frames received from a specific port and
        containing a specific unicast destination address are
        allowed to be forwarded."
    INDEX        { pvxStaticMCSwitchIdx,
                   pvxStaticMCVlanIdx,
                   pvxStaticMCMACAddrIdx,
                   pvxStaticMCReceivePort }
    ::= { pvxStaticMulticastTable 1 }

PVXStaticMulticastEntry ::= SEQUENCE { 	pvxStaticMCSwitchIdx            INTEGER,
                pvxStaticMCVlanIdx              INTEGER,
                pvxStaticMCMACAddrIdx           MacAddress,
                pvxStaticMCReceivePort          PvxL2Port,
                pvxStaticMCStaticIntfIdList     PvxVLANPortList,  
                pvxStaticMCForbiddenIntfIdList  PvxVLANPortList,  
                pvxStaticMCAddressType          INTEGER,
                pvxStaticMCRowStatus            RowStatus }
    
pvxStaticMCSwitchIdx OBJECT-TYPE
    SYNTAX       INTEGER(1..11)
    MAX-ACCESS   not-accessible
    STATUS       current
    DESCRIPTION  "This object represents the particular switch ID."
    ::= { pvxStaticMulticastEntry 1 }

pvxStaticMCVlanIdx OBJECT-TYPE
    SYNTAX       INTEGER (1..4095) 
    MAX-ACCESS   not-accessible
    STATUS       current
    DESCRIPTION  "This object is the fdb vlan id."
    ::= { pvxStaticMulticastEntry 2 }

pvxStaticMCMACAddrIdx OBJECT-TYPE
    SYNTAX       MacAddress
    MAX-ACCESS   not-accessible
    STATUS       current
    DESCRIPTION  "This object represents the particular MAC address."
    ::= { pvxStaticMulticastEntry 3 }

pvxStaticMCReceivePort OBJECT-TYPE
    SYNTAX      PvxL2Port 
    MAX-ACCESS  not-accessible
    STATUS      current
    DESCRIPTION "Either the value '0', or the port number of the port
        from which a frame must be received in order for this
        entry's filtering information to apply.  A value of zero
        indicates that this entry applies on all ports of the
        device for which there is no other applicable entry."
    ::= { pvxStaticMulticastEntry 4 }
    
pvxStaticMCStaticIntfIdList OBJECT-TYPE
    SYNTAX      PvxVLANPortList
    MAX-ACCESS  read-create
    STATUS      current
    DESCRIPTION "The set of ports to which frames received from a
        specific port and destined for a specific Multicast or
        Broadcast MAC address must be forwarded."
    ::= { pvxStaticMulticastEntry 5 }

pvxStaticMCForbiddenIntfIdList OBJECT-TYPE
    SYNTAX      PvxVLANPortList
    MAX-ACCESS  read-create
    STATUS      current
    DESCRIPTION "The set of ports to which frames received from a
        specific port and destined for a specific Multicast or
        Broadcast MAC address must not be forwarded." 
    ::= { pvxStaticMulticastEntry 6 }

pvxStaticMCAddressType OBJECT-TYPE
    SYNTAX      INTEGER {
                    other(1),
                    invalid(2),
                    permanent(3),
                    deleteOnReset(4),
                    deleteOnTimeout(5)
                }
    MAX-ACCESS  read-create
    STATUS      current
    DESCRIPTION "This object indicates the status of this entry.
            other(1) - this entry is currently in use but
                the conditions under which it will remain
                so differ from the following values.
            invalid(2) - writing this value to the object
                removes the corresponding entry.
            permanent(3) - this entry is currently in use
                and will remain so after the next reset of
                the bridge.
            deleteOnReset(4) - this entry is currently in
                use and will remain so until the next
                reset of the bridge.
            deleteOnTimeout(5) - this entry is currently in
                use and will remain so until it is aged out."
    DEFVAL      { permanent }
    ::= { pvxStaticMulticastEntry 7 }
    
pvxStaticMCRowStatus OBJECT-TYPE
    SYNTAX       RowStatus
    MAX-ACCESS   read-create
    STATUS       current
    DESCRIPTION  "This object is used to create a new row in the 
                  static multicast table."
    ::= { pvxStaticMulticastEntry 100 }

-----------------------------------------------------------------------
-- Lag  Table
-----------------------------------------------------------------------
pvxLagTable OBJECT-TYPE
    SYNTAX       SEQUENCE OF PVXLagEntry
    MAX-ACCESS   not-accessible
    STATUS       current
    DESCRIPTION  "This table is used to configure the link aggregation at 
                  system level."
    ::= { pvxBridge 9 }

pvxLagEntry OBJECT-TYPE
    SYNTAX       PVXLagEntry
    MAX-ACCESS   not-accessible
    STATUS       current
    DESCRIPTION  "The conceptual row object of the lag Config table."
    INDEX        { pvxLagSwitchIdx }
    ::= { pvxLagTable 1 }

PVXLagEntry ::= SEQUENCE { 	pvxLagSwitchIdx    	INTEGER,
                        	pvxLagState            INTEGER,
                        	pvxLagSystemPriority   Integer32,
                        	pvxLagSystemIdentifier DisplayString,
                        	pvxLagRowStatus        RowStatus }

pvxLagSwitchIdx OBJECT-TYPE
   	SYNTAX       INTEGER(1..11)
   	MAX-ACCESS   not-accessible
   	STATUS       current
   	DESCRIPTION  "This object represents the particular switch id ."
   	::= { pvxLagEntry 1 }

pvxLagState OBJECT-TYPE
    SYNTAX INTEGER { enable  (1),
                     disable (2) } 
    MAX-ACCESS   read-create
    STATUS       current
    DESCRIPTION  "The administrative status."
    DEFVAL       { enable }
    ::= { pvxLagEntry 2 }

pvxLagSystemPriority OBJECT-TYPE
   SYNTAX  Integer32
    MAX-ACCESS   read-create
    STATUS       current
    DESCRIPTION  "This object represents the lag  system priority." 
    ::= { pvxLagEntry 3 }

pvxLagSystemIdentifier OBJECT-TYPE
    SYNTAX       DisplayString
    MAX-ACCESS   read-only
    STATUS       current
    DESCRIPTION  "This object is used to identify the particular lag ID."
    ::= { pvxLagEntry 4 }

pvxLagRowStatus OBJECT-TYPE
    SYNTAX       RowStatus
    MAX-ACCESS   read-create
    STATUS       current
    DESCRIPTION  "This object is used to create a new row in the 
                  lag table."
    ::= { pvxLagEntry 100 }


-----------------------------------------------------------------------
-- Lag Group Table
-----------------------------------------------------------------------
pvxLagGroupTable OBJECT-TYPE
    SYNTAX       SEQUENCE OF PVXLagGroupEntry
    MAX-ACCESS   not-accessible
    STATUS       current
    DESCRIPTION  "This table is used to configure the link aggregation 
                  protocol related entries."
    ::= { pvxBridge 10 }

pvxLagGroupEntry OBJECT-TYPE
    SYNTAX       PVXLagGroupEntry
    MAX-ACCESS   not-accessible
    STATUS       current
    DESCRIPTION  "The conceptual row object of the lag Config table."
    INDEX        { pvxLGSwitchIdx,
                   pvxLGIdx }
    ::= { pvxLagGroupTable 1 }

PVXLagGroupEntry ::= SEQUENCE {	pvxLGSwitchIdx   		INTEGER,
                        		pvxLGIdx              	Integer32,
                     			pvxLGPortList         	PvxPhyPortList,
                        		pvxLGDistribution     	INTEGER,
                     			pvxLGMacAddress       	MacAddress,
                     			pvxLGPortCount        	Integer32,
                      			pvxLGActivePortCount  	Integer32,
                      			pvxLGMtuSize     	    Integer32,
                                pvxLGAdminStatus        AdminStatus,
                                pvxLGOperStatus		    OperStatus,
                                pvxLGDataRate		    INTEGER,
                                pvxLGMaxLinks           INTEGER,
                                pvxLGMinLinks           INTEGER,
                    			pvxLGRowStatus        	RowStatus }

pvxLGSwitchIdx OBJECT-TYPE
   	SYNTAX       INTEGER(1..11)
   	MAX-ACCESS   not-accessible
   	STATUS       current
   	DESCRIPTION  "This object represents the particular switch id of lag group."
   	::= { pvxLagGroupEntry 1 }

pvxLGIdx OBJECT-TYPE
    SYNTAX       Integer32
    MAX-ACCESS   not-accessible
    STATUS       current
    DESCRIPTION  "This is the id index of the lagGroup."
    ::= { pvxLagGroupEntry 2 }

pvxLGPortList OBJECT-TYPE
    SYNTAX  PvxPhyPortList 
    MAX-ACCESS   read-only
    STATUS       current
    DESCRIPTION  "Each entry in this list is for each physical port that participates 
                  in Link Aggregation which can be either aggregatable or individual."
    ::= {pvxLagGroupEntry 3 }

pvxLGDistribution OBJECT-TYPE
    SYNTAX  INTEGER { srcmac        (1),
                      dstmac        (2),
                      srcdstmac     (3), 
                      srcip         (4), 
                      dstip         (5), 
                      srcdstip      (6) }
    MAX-ACCESS   read-create
    STATUS       current
    DESCRIPTION  "This object represents the distribution method for LAG traffic."
    ::= {pvxLagGroupEntry 4 }

-- { pvxLagGroupEntry 5 } obsolete, removed

pvxLGMacAddress OBJECT-TYPE
    SYNTAX       MacAddress
    MAX-ACCESS   read-only
    STATUS       current
    DESCRIPTION  "This object represents the MAC address of the LAG group"
    ::= {pvxLagGroupEntry 6 }

pvxLGPortCount OBJECT-TYPE
    SYNTAX       Integer32
    MAX-ACCESS   read-only
    STATUS       current
    DESCRIPTION  "The number of ports actually configured to the LAG group"
    ::= {pvxLagGroupEntry 7 }

pvxLGActivePortCount OBJECT-TYPE
    SYNTAX       Integer32 
    MAX-ACCESS   read-only
    STATUS       current
    DESCRIPTION   "This object will give the number of ports that are attached to the 
                   LAG group and actively carrying data traffic on the link."
    ::= {pvxLagGroupEntry 8 }

pvxLGMtuSize OBJECT-TYPE
    SYNTAX       Integer32 
    MAX-ACCESS   read-create
    STATUS       current
    DESCRIPTION  "This object will give the MTU size of the LAG group"
    ::= {pvxLagGroupEntry 9 }

pvxLGAdminStatus OBJECT-TYPE
    SYNTAX       INTEGER { enabled  (1),
                           disabled (2) }
    MAX-ACCESS   read-create
    STATUS       current
    DESCRIPTION  "Sets the Link Aggregation Module administrative status as 
                  enabled or disabled."
    ::= {pvxLagGroupEntry 10 }

pvxLGOperStatus OBJECT-TYPE
    SYNTAX       OperStatus 
    MAX-ACCESS   read-only
    STATUS       current
    DESCRIPTION  "This read only objects gives actual status of the Link 
                  Aggregation Module (Operational status of module). When
                  Module is enabled Link Aggregation protocol starts 
                  functioning. When the module is disabled all the dynamically
                  allocated memory will be freed and Link Aggregation protocol
                  stops functioning."
    ::= {pvxLagGroupEntry 11 }

pvxLGDataRate OBJECT-TYPE
    SYNTAX	INTEGER(1..1000000)
    MAX-ACCESS	read-only
    STATUS	current
    DESCRIPTION	"The current data rate, in megabits per second, of the aggregate 
	link.  The value is calculated as N times the data rate of a single link 
	in the aggregation, where N is the number of active links."
    ::= {pvxLagGroupEntry 12}

pvxLGMaxLinks OBJECT-TYPE
    SYNTAX	INTEGER(1..8)
    MAX-ACCESS   read-create
    STATUS       current
    DESCRIPTION   "Sets the number of maximum links in the Link Aggregation Group. 
                   If the number of links in an aggregation exceeds the maximum value
                   set, then the links with the lower lacp priority will become active
                   links. Note: the switch with the lowest lacp priority value decides
                   the standby and active links in the aggregation."
    DEFVAL       { 8 }                   
    ::= {pvxLagGroupEntry 13 }

pvxLGMinLinks OBJECT-TYPE 
    SYNTAX  INTEGER(1..8) 
    MAX-ACCESS   read-create
    STATUS       current
    DESCRIPTION   "Sets the minimum number of links in the Link Aggregation Group to be
                   active to advertise upper layers that  the aggregate link operationally
                   up."
    DEFVAL       { 1 }
    ::= {pvxLagGroupEntry 14 }

pvxLGRowStatus OBJECT-TYPE
    SYNTAX       RowStatus
    MAX-ACCESS   read-create
    STATUS       current
    DESCRIPTION  "This object is used to create a new row in the 
                  lagConfig table."
    ::= {pvxLagGroupEntry 100 }


-----------------------------------------------------------------------
-- Lag Port Table
-----------------------------------------------------------------------
pvxLagPortTable OBJECT-TYPE
    SYNTAX       SEQUENCE OF PVXLagPortEntry
    MAX-ACCESS   not-accessible
    STATUS       current
    DESCRIPTION  "This table is used to configure the link aggregation 
                  protocol related entries.
				  TODO: Need to re-check the index here, and what is pvxLagPortId"
    ::= { pvxBridge 11 }

pvxLagPortEntry OBJECT-TYPE
    SYNTAX       PVXLagPortEntry
    MAX-ACCESS   not-accessible
    STATUS       current
    DESCRIPTION  "The conceptual row object of the lag Config table."
    INDEX        { 	pvxLagPortSwitchIdx,
			pvxLagPortShelfIdx,
			pvxLagPortSlotIdx,
			pvxLagPortTypeIdx,	
                   	pvxLagPortIdx }
    ::= { pvxLagPortTable 1 }

PVXLagPortEntry ::= SEQUENCE { 	pvxLagPortSwitchIdx   		INTEGER,
				pvxLagPortShelfIdx		INTEGER,
				pvxLagPortSlotIdx		INTEGER,
				pvxLagPortTypeIdx		PvxPortType,
                        	pvxLagPortIdx          		Integer32,
                        	pvxLagPortPriority      	Integer32,      
                        	pvxLagPortMode          	INTEGER,
                        	pvxLagPortAggState      	INTEGER,
                        	pvxLagPortLcapId        	Integer32,
                        	pvxLagPortTimeout       	INTEGER,
         			pvxLagPortWaitTime		 Integer32,
         			pvxLagPortActAdminState  	Integer32,
         			pvxLagPortPrtnrAdminState 	Integer32,
                        	pvxLagPortGroupId              	Integer32,
                        	pvxLagPortRowStatus   		RowStatus }

pvxLagPortSwitchIdx OBJECT-TYPE
   	SYNTAX       INTEGER(1..11)
   	MAX-ACCESS   not-accessible
   	STATUS       current
   	DESCRIPTION  "This object represents the particular switch id of lag group."
   	::= { pvxLagPortEntry 1 }

pvxLagPortShelfIdx OBJECT-TYPE
    SYNTAX       INTEGER (1|11|21|31)
    MAX-ACCESS   not-accessible
    STATUS       current
    DESCRIPTION  "This is the id index of the lagGroup."
    ::= {pvxLagPortEntry 2 }

pvxLagPortSlotIdx OBJECT-TYPE
    SYNTAX       INTEGER (1|3|5|7|9|11|13|15|17|19)
    MAX-ACCESS   not-accessible
    STATUS       current
    DESCRIPTION  "The is the slot number for the lag port."
    ::= {pvxLagPortEntry 3 }

pvxLagPortTypeIdx OBJECT-TYPE
    SYNTAX  PvxPortType 
    MAX-ACCESS   not-accessible
    STATUS       current
    DESCRIPTION  "This object is port type of the lag port."
    ::= {pvxLagPortEntry 4 }

pvxLagPortIdx OBJECT-TYPE
    SYNTAX  Integer32
    MAX-ACCESS   not-accessible
    STATUS       current
    DESCRIPTION  "This object is the port number of the lag port."
    ::= {pvxLagPortEntry 5 }

pvxLagPortPriority OBJECT-TYPE
    SYNTAX  Integer32 
    MAX-ACCESS   read-create
    STATUS       current
    DESCRIPTION  "This object represents the lag port priority"
    ::= {pvxLagPortEntry 6 }

pvxLagPortMode OBJECT-TYPE
    SYNTAX       INTEGER { active (1),
                           passive(2),
                           on     (3) }
    MAX-ACCESS   read-create
    STATUS       current
    DESCRIPTION   "This object is used to enable LACP , disable LACP or manually
                   aggregate a port"
    ::= {pvxLagPortEntry 7 }

pvxLagPortAggState OBJECT-TYPE
    SYNTAX       INTEGER  { inbndl (1),
                            stdby  (2),
                            down   (3),
                            alone  (4) }
    MAX-ACCESS   read-only
    STATUS       current
    DESCRIPTION        "This read-only object is used to display the port state in aggregation
                        inBndl(1)      - The port is operationally up and actively 
                                         takes part in aggregation.
                        standby(2)     - The port is capable of joining in
                                         aggregation group, when any of the ports in  
                                         aggregation group goes down.
                        down(3)        - The port is operationally down in lower layers.
                                         or the port is operational in lower layers
                                         but temporarily not able to participate
                                         in aggregation because of different partner
                                         information in the same group.
                        alone(4)       - The port is operating individually and
                                         is not taking part in aggregation."
    ::= {pvxLagPortEntry 8 }

pvxLagPortLcapId OBJECT-TYPE
    SYNTAX       Integer32 
    MAX-ACCESS   read-create
    STATUS       current
    DESCRIPTION  "This object sets the global LCAP System ID."
    ::= {pvxLagPortEntry 9 }

pvxLagPortTimeout OBJECT-TYPE
    SYNTAX       INTEGER { long  (1),
                           short (2) } 
    MAX-ACCESS   read-create
    STATUS       current
    DESCRIPTION  "This object sets the LACP timeout period.
                  long(1)  - LACP PDU will be sent every 30 seconds and
                             LACP timeout value (no packet is received from peer)
                             is 90 seconds
                  short(2) - LACP PDU will be sent every 1 second and timeout value
                             is 3 seconds."
    ::= {pvxLagPortEntry 10 }

pvxLagPortWaitTime OBJECT-TYPE
    SYNTAX       Integer32 
    MAX-ACCESS   read-create
    STATUS       current
    DESCRIPTION  "Duration of time for the port to attach to the LAG group."
    ::= {pvxLagPortEntry 11 }


pvxLagPortActAdminState OBJECT-TYPE
    SYNTAX       Integer32 
    MAX-ACCESS   read-only
    STATUS       current
    DESCRIPTION  "This object is the actors administrative state."
    ::= {pvxLagPortEntry 12 }

pvxLagPortPrtnrAdminState OBJECT-TYPE
    SYNTAX       Integer32 
    MAX-ACCESS   read-only
    STATUS       current
    DESCRIPTION  "This object is the partners administrative state."
    ::= {pvxLagPortEntry 13 }
    
pvxLagPortGroupId OBJECT-TYPE
    SYNTAX       Integer32 
    MAX-ACCESS   read-create
    STATUS       current
    DESCRIPTION  "This object is the LAG group id associated with the lag port."
    ::= {pvxLagPortEntry 14 }    
    
pvxLagPortRowStatus OBJECT-TYPE
    SYNTAX       RowStatus
    MAX-ACCESS   read-create
    STATUS       current
    DESCRIPTION  "This object is used to create a new row in the 
                  lagConfig table."
    ::= {pvxLagPortEntry 100 }
         


-----------------------------------------------------------------------
-- Spanning Tree Protocol  Table
-----------------------------------------------------------------------
pvxMSTPGenTable OBJECT-TYPE
    SYNTAX       SEQUENCE OF PVXMSTPGenEntry
    MAX-ACCESS   not-accessible
    STATUS       current
    DESCRIPTION  "This table is used to configure the Spanning Tree 
                  protocol on a virtual switch."
    ::= { pvxBridge 12 }

pvxMSTPGenEntry OBJECT-TYPE
    SYNTAX       PVXMSTPGenEntry
    MAX-ACCESS   not-accessible
    STATUS       current
    DESCRIPTION  "The conceptual row object of the packet Spanning Tree 
                  protocol config table."
    INDEX        { pvxMSTPGenSwitchIdx }
    ::= { pvxMSTPGenTable 1 }

PVXMSTPGenEntry ::= SEQUENCE { 	pvxMSTPGenSwitchIdx          INTEGER, 
                          		pvxMSTPGenMaxHops    		 INTEGER,      
                         		pvxMSTPGenVersionSupported   INTEGER, 
                         		pvxMSTPGenIdFmtSel           Integer32,
                         		pvxMSTPGenIdName             DisplayString,
                         		pvxMSTPGenIdRevisionLevel    Integer32,
                         		pvxMSTPGenIdDigest           DisplayString, 
                         		pvxMSTPGenRegionalRoot       DisplayString,
                         		pvxMSTPGenExternalRootCost   Integer32,
                         		pvxMSTPGenCistPriority       INTEGER,
                                pvxMSTPGenBrdgId             DisplayString,
                         		pvxMSTPGenCistRoot           DisplayString,
                         		pvxMSTPGenCistRootPriority   INTEGER,
                         		pvxMSTPGenCistRootCost       Integer32 }

pvxMSTPGenSwitchIdx OBJECT-TYPE
    SYNTAX       INTEGER(1..11)
    MAX-ACCESS   not-accessible
    STATUS       current
    DESCRIPTION  "This object represents the switch id of the MSTP Gen."
    ::= { pvxMSTPGenEntry 1 }

pvxMSTPGenMaxHops OBJECT-TYPE
    SYNTAX       INTEGER (1..40)
    MAX-ACCESS   read-create
    STATUS       current
    DESCRIPTION  "This object represents the maximum hops that can be configured." 
    ::= { pvxMSTPGenEntry 2 }

pvxMSTPGenVersionSupported OBJECT-TYPE
    SYNTAX       INTEGER { unknown (1),
                           nonStp(2),  
                           dot1d (3),
                           dot1w (4),  
                           dot1s (5),   
                           dot1q (6) } 
 
    MAX-ACCESS   read-only
    STATUS       current
    DESCRIPTION  "This object is used to read the supported version  "
    ::= {pvxMSTPGenEntry 3 }

pvxMSTPGenIdFmtSel  OBJECT-TYPE
    SYNTAX       Integer32
    MAX-ACCESS   read-only
    STATUS       current
    DESCRIPTION  "This object is used to configure the Frame Selection on 
                  particular virtual switch."
    ::= {pvxMSTPGenEntry 4 }

pvxMSTPGenIdName  OBJECT-TYPE
    SYNTAX       DisplayString
    MAX-ACCESS   read-create
    STATUS       current
    DESCRIPTION  "This object is used to configure MSTP ID name on a 
                  particular virtual switch."
    ::= {pvxMSTPGenEntry 5 }   

pvxMSTPGenIdRevisionLevel  OBJECT-TYPE
    SYNTAX       Integer32
    MAX-ACCESS   read-create
    STATUS       current
    DESCRIPTION  "This object represents MSTP Revision Level in seconds."
    ::= {pvxMSTPGenEntry 6 }   
                          
pvxMSTPGenIdDigest   OBJECT-TYPE
    SYNTAX       DisplayString
    MAX-ACCESS   read-only
    STATUS       current
    DESCRIPTION  "This object represents MSTP ID digest value."
    ::= {pvxMSTPGenEntry 7 }   
                          
pvxMSTPGenRegionalRoot    OBJECT-TYPE
    SYNTAX       DisplayString
    MAX-ACCESS   read-only
    STATUS       current
    DESCRIPTION  "This object represents the mstp Regional Root ."
    ::= {pvxMSTPGenEntry 8 }   

pvxMSTPGenExternalRootCost     OBJECT-TYPE
    SYNTAX       Integer32
    MAX-ACCESS   read-only
    STATUS       current
    DESCRIPTION  "This represents the mstp External Root Cost ."
    ::= {pvxMSTPGenEntry 9 }   

pvxMSTPGenCistPriority 		   OBJECT-TYPE
    SYNTAX       INTEGER (0..61440)
    MAX-ACCESS   read-create
    STATUS       current
    DESCRIPTION  "This CIST priority of this bridge."
    ::= {pvxMSTPGenEntry 10 }

pvxMSTPGenBrdgId  OBJECT-TYPE
    SYNTAX       DisplayString
    MAX-ACCESS   read-only
    STATUS       current
    DESCRIPTION  "The bridge ID."
    ::= {pvxMSTPGenEntry 11 }

pvxMSTPGenCistRoot  OBJECT-TYPE
    SYNTAX       DisplayString
    MAX-ACCESS   read-only
    STATUS       current
    DESCRIPTION  "The root of the CIST."
    ::= {pvxMSTPGenEntry 12 }

pvxMSTPGenCistRootPriority  OBJECT-TYPE
    SYNTAX       INTEGER(0..61440)
    MAX-ACCESS   read-only
    STATUS       current
    DESCRIPTION  "The priority of the CIST root."
    ::= {pvxMSTPGenEntry 13 }

pvxMSTPGenCistRootCost  OBJECT-TYPE
    SYNTAX       Integer32
    MAX-ACCESS   read-only
    STATUS       current
    DESCRIPTION  "The cost of the CIST root bridge."
    ::= {pvxMSTPGenEntry 14 }


-----------------------------------------------------------------------
-- MSTP MAP 
-----------------------------------------------------------------------
pvxMSTPMapTable OBJECT-TYPE
    SYNTAX       SEQUENCE OF PVXMSTPMapEntry
    MAX-ACCESS   not-accessible
    STATUS       current
    DESCRIPTION  "This table is used to configure the Spanning Tree 
                  Map on a virtual switch."
    ::= { pvxBridge 13 }

pvxMSTPMapEntry OBJECT-TYPE
    SYNTAX       PVXMSTPMapEntry
    MAX-ACCESS   not-accessible
    STATUS       current
    DESCRIPTION  "The conceptual row object of the MSTP Map table."
    INDEX        { pvxMSTPMapSwitchIdx,
                   pvxMSTPMapIdx }
    ::= { pvxMSTPMapTable 1 }

PVXMSTPMapEntry ::= SEQUENCE { 	pvxMSTPMapSwitchIdx    INTEGER, 
                           		pvxMSTPMapIdx    		Integer32,      
                         		pvxMSTPMapVlanS1k   	PvxMSTPVlanList,
                        		pvxMSTPMapVlanS2k      PvxMSTPVlanList,
                        		pvxMSTPMapVlanS3k      PvxMSTPVlanList,
                        		pvxMSTPMapVlanS4k    	PvxMSTPVlanList,
                        		pvxMSTPMapRowStatus    RowStatus }

pvxMSTPMapSwitchIdx OBJECT-TYPE
    SYNTAX       INTEGER(1..11)
    MAX-ACCESS   not-accessible
    STATUS       current
    DESCRIPTION  "This object represents the switch id of the mstp map."
    ::= {pvxMSTPMapEntry 1 }

pvxMSTPMapIdx OBJECT-TYPE
    SYNTAX       Integer32
    MAX-ACCESS   not-accessible
    STATUS       current
    DESCRIPTION  "This object represents the mstp map index." 
    ::= {pvxMSTPMapEntry 2 }

pvxMSTPMapVlanS1k OBJECT-TYPE
    SYNTAX       PvxMSTPVlanList
    MAX-ACCESS   read-create
    STATUS       current
    DESCRIPTION  "This object is used to configure 1k Vlans"
    ::= {pvxMSTPMapEntry 3 }

pvxMSTPMapVlanS2k  OBJECT-TYPE
    SYNTAX       PvxMSTPVlanList
    MAX-ACCESS   read-create
    STATUS       current
    DESCRIPTION  "This object is used to configure 2k Vlans."
    ::= {pvxMSTPMapEntry 4 }

pvxMSTPMapVlanS3k  OBJECT-TYPE
    SYNTAX       PvxMSTPVlanList
    MAX-ACCESS   read-create
    STATUS       current
    DESCRIPTION  "This object is used to configure configure 3k Vlans."
    ::= {pvxMSTPMapEntry 5 }   

pvxMSTPMapVlanS4k  OBJECT-TYPE
    SYNTAX       PvxMSTPVlanList
    MAX-ACCESS   read-create
    STATUS       current
    DESCRIPTION  "This object is used to configure configure 4k Vlans."
    ::= {pvxMSTPMapEntry 6 }   
                          
pvxMSTPMapRowStatus  OBJECT-TYPE
    SYNTAX       RowStatus
    MAX-ACCESS   read-create
    STATUS       current
    DESCRIPTION  "Used to control the addition and deletion of entries in the
                  mstp table."
    ::= {pvxMSTPMapEntry 100 }   

-----------------------------------------------------------------------
--	mstPortTable  Table
-----------------------------------------------------------------------
pvxMSTPPortTable OBJECT-TYPE
    SYNTAX       SEQUENCE OF PVXMSTPPortEntry
    MAX-ACCESS   not-accessible
    STATUS       current
    DESCRIPTION  "This table is used to configure the Spanning tree port 
                  related entries.
				  TODO: This table needs to change to be able to deal with indexing based on shelf and slot.
				  If the index has switch associated with it , that will mean that we are dealing with layer 2 ports."
    ::= { pvxBridge 14 }

pvxMSTPPortEntry OBJECT-TYPE
    SYNTAX       PVXMSTPPortEntry
    MAX-ACCESS   not-accessible
    STATUS       current
    DESCRIPTION  "The conceptual row object of the mstp port."
    INDEX        { pvxMSTPPortSwitchIdx,
                   pvxMSTPPortShelfIdx,
                   pvxMSTPPortSlotIdx,
                   pvxMSTPPortTypeIdx,
                   pvxMSTPPortIdx }
    ::= { pvxMSTPPortTable 1 }

PVXMSTPPortEntry ::= SEQUENCE { pvxMSTPPortSwitchIdx            INTEGER,
                                pvxMSTPPortShelfIdx             INTEGER,
                                pvxMSTPPortSlotIdx              INTEGER,
                                pvxMSTPPortTypeIdx              PvxPortType,
                                pvxMSTPPortIdx                  Integer32,
                                pvxMSTPPortDesignatedRoot       DisplayString,
                                pvxMSTPPortDesignatedBridge     DisplayString,
                                pvxMSTPPortDesignatedPort       Integer32,
                                pvxMSTPPortPathCost             Integer32,
                                pvxMSTPPortPriority             Integer32,
                                pvxMSTPPortState                INTEGER,
                                pvxMSTPPortRole                 INTEGER,
                                pvxMSTPPortRegRoot              DisplayString,
                                pvxMSTPPortRegRootCost          Integer32,
                                pvxMSTPPortRestrictedRole       TruthValue,
                                pvxMSTPPortRestrictedTCN        TruthValue,
                                pvxMSTPPortForcedPortState      INTEGER,
								pvxMSTPPortLoopGuardState       INTEGER,
								pvxMSTPPortLinkType             INTEGER }
							    
pvxMSTPPortSwitchIdx OBJECT-TYPE
   	SYNTAX       INTEGER(1..11)
   	MAX-ACCESS   not-accessible
   	STATUS       current
   	DESCRIPTION  "This object represents the particular switch id ."
    ::= {pvxMSTPPortEntry 1 }

pvxMSTPPortShelfIdx OBJECT-TYPE
    SYNTAX       INTEGER (0|1|11|21|31)
    MAX-ACCESS   not-accessible
    STATUS       current
    DESCRIPTION  "The instace Id of the mstp port."
    ::= {pvxMSTPPortEntry 2 }

pvxMSTPPortSlotIdx OBJECT-TYPE
    SYNTAX       INTEGER (0|1|3|5|7|9|11|13|15|17|19)
    MAX-ACCESS   not-accessible
    STATUS       current
    DESCRIPTION  "This is the port index of the mstp port."
    ::= {pvxMSTPPortEntry 3 }

pvxMSTPPortTypeIdx OBJECT-TYPE
    SYNTAX       PvxPortType
    MAX-ACCESS   not-accessible
    STATUS       current
    DESCRIPTION  "This is the port index of the mstp port."
    ::= {pvxMSTPPortEntry 4 }

pvxMSTPPortIdx OBJECT-TYPE
    SYNTAX       Integer32 
    MAX-ACCESS   not-accessible
    STATUS       current
    DESCRIPTION  "This is the port index of the mstp port."
    ::= {pvxMSTPPortEntry 5 }

pvxMSTPPortDesignatedRoot OBJECT-TYPE
    SYNTAX       DisplayString
    MAX-ACCESS   read-only
    STATUS       current
    DESCRIPTION  "This is the designated root."
    ::= {pvxMSTPPortEntry 6 }

pvxMSTPPortDesignatedBridge OBJECT-TYPE
    SYNTAX       DisplayString
    MAX-ACCESS   read-only
    STATUS       current
    DESCRIPTION  "This is the designated bridge ID."
    ::= {pvxMSTPPortEntry 7 }


pvxMSTPPortDesignatedPort OBJECT-TYPE
    SYNTAX       Integer32
    MAX-ACCESS   read-only
    STATUS       current
    DESCRIPTION  "This is the designated port."
    ::= {pvxMSTPPortEntry 8 }


pvxMSTPPortPathCost OBJECT-TYPE
    SYNTAX       Integer32
    MAX-ACCESS   read-create
    STATUS       current
    DESCRIPTION  "This is the path cost."
    ::= {pvxMSTPPortEntry 9 }

pvxMSTPPortPriority OBJECT-TYPE
    SYNTAX       Integer32
    MAX-ACCESS   read-create
    STATUS       current
    DESCRIPTION  "This is the port priority."
    ::= {pvxMSTPPortEntry 10 }

pvxMSTPPortState OBJECT-TYPE
    SYNTAX       INTEGER {
                 unknown (1),
                 disabled (2),
                 discarding (3),
                 learning (4),
                 forwarding (5) }
    MAX-ACCESS   read-only
    STATUS       current
    DESCRIPTION  "This is the port state."
    ::= {pvxMSTPPortEntry 11 }

pvxMSTPPortRole  OBJECT-TYPE
    SYNTAX       INTEGER {
                 disabled (1),
                 alternate (2),
                 backup (3),
                 root (4),
                 designated (5),
                 nonSTP (6) }
    MAX-ACCESS   read-only
    STATUS       current
    DESCRIPTION  "This is the port role."
    ::= {pvxMSTPPortEntry 12 }

pvxMSTPPortRegRoot OBJECT-TYPE
    SYNTAX       DisplayString
    MAX-ACCESS   read-only
    STATUS       current
    DESCRIPTION  "This is the port's reg root."
    ::= {pvxMSTPPortEntry 13 }


pvxMSTPPortRegRootCost OBJECT-TYPE
    SYNTAX       Integer32
    MAX-ACCESS   read-only
    STATUS       current
    DESCRIPTION  "This is the port's reg root cost."
    ::= {pvxMSTPPortEntry 14 }


pvxMSTPPortRestrictedRole OBJECT-TYPE
    SYNTAX       TruthValue
    MAX-ACCESS   read-create
    STATUS       current
    DESCRIPTION  "This is the port's restricted role."
    ::= {pvxMSTPPortEntry 15 }


pvxMSTPPortRestrictedTCN OBJECT-TYPE
    SYNTAX       TruthValue
    MAX-ACCESS   read-create
    STATUS       current
    DESCRIPTION  "This is the port's restricted TCN."
    ::= {pvxMSTPPortEntry 16 }


pvxMSTPPortForcedPortState OBJECT-TYPE
    SYNTAX       INTEGER { enable  (1),
                           disable (2) }
    MAX-ACCESS   read-create
    STATUS       current
    DESCRIPTION  "This is the port's forced port state."
    ::= {pvxMSTPPortEntry 17 }

pvxMSTPPortLoopGuardState OBJECT-TYPE
    SYNTAX       INTEGER { enable  (1),
                           disable (2) }
    MAX-ACCESS   read-create
    STATUS       current
    DESCRIPTION  "This is the port's Loop Guard state."
    DEFVAL       { disable } 	     
    ::= {pvxMSTPPortEntry 18 }

pvxMSTPPortLinkType  OBJECT-TYPE
    SYNTAX       INTEGER { shared (1),
                           point-to-point(2) } 
    MAX-ACCESS   read-create
    STATUS       current
    DESCRIPTION  "The link type of this port."
    DEFVAL       { point-to-point }
    ::= {pvxMSTPPortEntry 19 }

-----------------------------------------------------------------------
--	mstXst  Table
-----------------------------------------------------------------------
pvxMSTPXstTable OBJECT-TYPE
    SYNTAX       SEQUENCE OF PVXMSTPXstEntry
    MAX-ACCESS   not-accessible
    STATUS       current
    DESCRIPTION  "This table is used to configure the Mstp Xst  
                  related entries."
    ::= { pvxBridge 15 }

pvxMSTPXstEntry OBJECT-TYPE
    SYNTAX       PVXMSTPXstEntry
    MAX-ACCESS   not-accessible
    STATUS       current
    DESCRIPTION  "The conceptual row object of the mstpXst table."
    INDEX        { 	pvxMSTPXstSwitchIdx,
               		pvxMSTPXstIdx }
    ::= { pvxMSTPXstTable 1 }

PVXMSTPXstEntry ::= SEQUENCE { 	pvxMSTPXstSwitchIdx         INTEGER,
                                pvxMSTPXstIdx               INTEGER,
                                pvxMSTPXstBrdgPriority      INTEGER,
                                pvxMSTPXstBrdgId            DisplayString,
                                pvxMSTPXstBrdgRegRoot       DisplayString,
                                pvxMSTPXstBrdgRegRootCost   INTEGER,
                                pvxMSTPXstRootPort          PvxL2Port,
                                pvxMSTPXstRootPortSwitch    INTEGER,
                                pvxMSTPXstRootPortShelf     INTEGER,
                                pvxMSTPXstRootPortSlot      INTEGER,
                                pvxMSTPXstRootPortType      PvxPortType,
                                pvxMSTPXstRootPortNum       INTEGER }

pvxMSTPXstSwitchIdx OBJECT-TYPE
   	SYNTAX       INTEGER(1..11)
   	MAX-ACCESS   not-accessible
   	STATUS       current
   	DESCRIPTION  "This object represents the particular switch id."
    ::= {pvxMSTPXstEntry 1 }

pvxMSTPXstIdx OBJECT-TYPE
    SYNTAX       INTEGER (1..16)
    MAX-ACCESS   not-accessible
    STATUS       current
    DESCRIPTION  "The instance of the mstpXst Id."
    ::= {pvxMSTPXstEntry 2 }

pvxMSTPXstBrdgPriority OBJECT-TYPE
    SYNTAX       INTEGER (0..61440)
    MAX-ACCESS   read-create
    STATUS       current
    DESCRIPTION  "This Bridge priority."
    ::= {pvxMSTPXstEntry 3 }

pvxMSTPXstBrdgId  OBJECT-TYPE
    SYNTAX       DisplayString
    MAX-ACCESS   read-only
    STATUS       current
    DESCRIPTION  "The bridge ID."
    ::= {pvxMSTPXstEntry 4 }

pvxMSTPXstBrdgRegRoot OBJECT-TYPE
    SYNTAX       DisplayString
    MAX-ACCESS   read-only
    STATUS       current
    DESCRIPTION  "The bridge Reg Root."
    ::= {pvxMSTPXstEntry 5 }

pvxMSTPXstBrdgRegRootCost   OBJECT-TYPE
    SYNTAX       INTEGER (1..65535)
    MAX-ACCESS   read-only
    STATUS       current
    DESCRIPTION  "The root cost of destination bridge."
    ::= {pvxMSTPXstEntry 6 }

pvxMSTPXstRootPort OBJECT-TYPE
    SYNTAX       PvxL2Port
    MAX-ACCESS   read-only
    STATUS       deprecated
    DESCRIPTION  "The root port number."
    ::= {pvxMSTPXstEntry 7 }

pvxMSTPXstRootPortSwitch OBJECT-TYPE
    SYNTAX       INTEGER(1..11)
    MAX-ACCESS   read-only
    STATUS       current
    DESCRIPTION  "The Switch ID of the port on this bridge through which the spanning tree root node is reached."
    ::= {pvxMSTPXstEntry 8 }

pvxMSTPXstRootPortShelf OBJECT-TYPE
    SYNTAX       INTEGER (0|1|11|21|31)
    MAX-ACCESS   read-only
    STATUS       current
    DESCRIPTION  "The shelf ID of the port on this bridge through which the spanning tree root node is reached."
    ::= {pvxMSTPXstEntry 9 }

pvxMSTPXstRootPortSlot OBJECT-TYPE
    SYNTAX       INTEGER (0|1|3|5|7|9|11|13|15|17|19)
    MAX-ACCESS   read-only
    STATUS       current
    DESCRIPTION  "The slot ID of the port on this bridge through which the spanning tree root node is reached."
    ::= {pvxMSTPXstEntry 10 }

pvxMSTPXstRootPortType OBJECT-TYPE
    SYNTAX       PvxPortType 
    MAX-ACCESS   read-only
    STATUS       current
    DESCRIPTION  "The port type of the port on this bridge through which the spanning tree root node is reached."
    ::= {pvxMSTPXstEntry 11 }

pvxMSTPXstRootPortNum OBJECT-TYPE
    SYNTAX       INTEGER (1..28)
    MAX-ACCESS   read-only
    STATUS       current
    DESCRIPTION  "The port ID of the port on this bridge through which the spanning tree root node is reached."
    ::= {pvxMSTPXstEntry 12 }

-----------------------------------------------------------------------
-- mstpXstPortTable  Table
-----------------------------------------------------------------------
pvxMSTPXstPortTable OBJECT-TYPE
    SYNTAX       SEQUENCE OF PVXMSTPXstPortEntry
    MAX-ACCESS   not-accessible
    STATUS       current
    DESCRIPTION  "This table is used to configure the mstp Xst Port 
                  related entries."
    ::= { pvxBridge 16 }

pvxMSTPXstPortEntry OBJECT-TYPE
    SYNTAX       PVXMSTPXstPortEntry
    MAX-ACCESS   not-accessible
    STATUS       current
    DESCRIPTION  "The conceptual row object of the mstp Xst Port."
    INDEX        { 	pvxMSTPXstPortSwitchIdx,
			pvxMSTPXstPortShelfIdx,
			pvxMSTPXstPortSlotIdx,
			pvxMSTPXstPortTypeIdx,
			pvxMSTPXstPortInstIdx,
               		pvxMSTPXstPortIdx }
    ::= { pvxMSTPXstPortTable 1 }

PVXMSTPXstPortEntry ::= SEQUENCE { pvxMSTPXstPortSwitchIdx        INTEGER,
                                   pvxMSTPXstPortShelfIdx         INTEGER,
                                   pvxMSTPXstPortSlotIdx          INTEGER,
                                   pvxMSTPXstPortTypeIdx          PvxPortType,
                                   pvxMSTPXstPortInstIdx          INTEGER,
                                   pvxMSTPXstPortIdx              INTEGER,
                                   pvxMSTPXstPortState            INTEGER,
                                   pvxMSTPXstPortRole             INTEGER,
                                   pvxMSTPXstPortDesigRoot        DisplayString,
                                   pvxMSTPXstPortDesigCost        Integer32,
                                   pvxMSTPXstPortDesigBridge      DisplayString,
                                   pvxMSTPXstPortDesigPortId      Integer32,
                                   pvxMSTPXstPortPriority         Integer32,
                                   pvxMSTPXstPortPathCost         Integer32,
                                   pvxMSTPXstPortForcedPortState  INTEGER }

pvxMSTPXstPortSwitchIdx OBJECT-TYPE
   	SYNTAX       INTEGER(1..11)
   	MAX-ACCESS   not-accessible
   	STATUS       current
   	DESCRIPTION  "This object represents the particular switch id of mstpXstPort."
    ::= {pvxMSTPXstPortEntry 1 }

pvxMSTPXstPortShelfIdx OBJECT-TYPE
    SYNTAX       INTEGER (0|1|11|21|31)
    MAX-ACCESS   not-accessible
    STATUS       current
    DESCRIPTION  "The instace index of the mstp Xst Port table ."
    ::= {pvxMSTPXstPortEntry 2 }

pvxMSTPXstPortSlotIdx OBJECT-TYPE
    SYNTAX       INTEGER (0|1|3|5|7|9|11|13|15|17|19)
    MAX-ACCESS   not-accessible
    STATUS       current
    DESCRIPTION  "The instace index of the mstp Xst Port table ."
    ::= {pvxMSTPXstPortEntry 3 }

pvxMSTPXstPortTypeIdx OBJECT-TYPE
    SYNTAX       PvxPortType 
    MAX-ACCESS   not-accessible
    STATUS       current
    DESCRIPTION  "The instace index of the mstp Xst Port table ."
    ::= {pvxMSTPXstPortEntry 4 }

pvxMSTPXstPortInstIdx OBJECT-TYPE
    SYNTAX       INTEGER (1..16)
    MAX-ACCESS   not-accessible
    STATUS       current
    DESCRIPTION  "This Xst instance index of the mstpXstPort table."
    ::= {pvxMSTPXstPortEntry 5 }

pvxMSTPXstPortIdx OBJECT-TYPE
    SYNTAX       INTEGER (1..28)
    MAX-ACCESS   not-accessible
    STATUS       current
    DESCRIPTION  "This port instance of the mstpXstPort table."
    ::= {pvxMSTPXstPortEntry 6 }

pvxMSTPXstPortState OBJECT-TYPE
    SYNTAX       INTEGER {unknown (1), disabled (2), 
                          discarding (3), learning (4),
                          forwarding (5) }
    MAX-ACCESS   read-only
    STATUS       current
    DESCRIPTION  "The port state of the mstp Xst."
    ::= {pvxMSTPXstPortEntry 7 }

pvxMSTPXstPortRole OBJECT-TYPE
	SYNTAX       INTEGER { disabled (1), 
	                       alternate (2), 
	                       backup (3),
	                       root (4), 
	                       designated (5),
	                       master (6),
	                       nonSTP (7)}
     MAX-ACCESS   read-only
     STATUS       current
     DESCRIPTION  "The role of the participating port."
    ::= {pvxMSTPXstPortEntry 8 }

pvxMSTPXstPortDesigRoot   OBJECT-TYPE
    SYNTAX       DisplayString
    MAX-ACCESS   read-only
    STATUS       current
    DESCRIPTION  "The designated root attribute of the mstp Xst Port."
    ::= {pvxMSTPXstPortEntry 9 }

pvxMSTPXstPortDesigCost  OBJECT-TYPE
    SYNTAX       Integer32  
    MAX-ACCESS   read-only
    STATUS       current
    DESCRIPTION  "The root cost of the mstpXstPort."
    ::= {pvxMSTPXstPortEntry 10 }

pvxMSTPXstPortDesigBridge  OBJECT-TYPE 
    SYNTAX       DisplayString
    MAX-ACCESS   read-only
    STATUS       current
    DESCRIPTION  "The designated bridge ID of the mstpXstPort."
    ::= {pvxMSTPXstPortEntry 11 }

pvxMSTPXstPortDesigPortId       OBJECT-TYPE 
    SYNTAX       Integer32
    MAX-ACCESS   read-only
    STATUS       current
    DESCRIPTION  "The designated port id of the mstpXstPort."
    ::= {pvxMSTPXstPortEntry 12 }
    
pvxMSTPXstPortPriority       OBJECT-TYPE 
    SYNTAX       Integer32
    MAX-ACCESS   read-create
    STATUS       current
    DESCRIPTION  "The port priority of the mstp Xst Port"
    ::= {pvxMSTPXstPortEntry 13 }
    
pvxMSTPXstPortPathCost      OBJECT-TYPE 
    SYNTAX       Integer32
    MAX-ACCESS   read-create
    STATUS       current
    DESCRIPTION  "This path cost of the mstpXst port."
    ::= {pvxMSTPXstPortEntry 14 }        

pvxMSTPXstPortForcedPortState OBJECT-TYPE
    SYNTAX       INTEGER { enable  (1),
                           disable (2) }
    MAX-ACCESS   read-create
    STATUS       current
    DESCRIPTION  "This is the port's forced port state."
    ::= {pvxMSTPXstPortEntry 15 }

-----------------------------------------------------------------------
-- pvxNextFreeIndex  Table
-----------------------------------------------------------------------
pvxNextFreeIndexTable OBJECT-TYPE
    SYNTAX       SEQUENCE OF PVXNextFreeIndexEntry
    MAX-ACCESS   not-accessible
    STATUS       current
    DESCRIPTION  "This table is used to find the next free index in
                  some tables that use integer indices."
    ::= { pvxBridge 17 }

pvxNextFreeIndexEntry OBJECT-TYPE
    SYNTAX       PVXNextFreeIndexEntry
    MAX-ACCESS   not-accessible
    STATUS       current
    DESCRIPTION  "The conceptual row object of the Next Free Index Table."
    INDEX        {
                 pvxNextFreeIndexTableIndex,
                 pvxNextFreeIndexSwitchIdx
                 }
    ::= { pvxNextFreeIndexTable 1 }

PVXNextFreeIndexEntry ::= SEQUENCE {
                              pvxNextFreeIndexTableIndex       INTEGER,
                              pvxNextFreeIndexSwitchIdx	       INTEGER,
                              pvxNextFreeIndexValue            Integer32
                              }

pvxNextFreeIndexTableIndex OBJECT-TYPE
   	SYNTAX       INTEGER { none(1), lagGroup(70), switches(84), flowclass(87), vlan(93) }
   	MAX-ACCESS   not-accessible
   	STATUS       current
   	DESCRIPTION  "This object indicates from which table to fetch the next free index."
    ::= {pvxNextFreeIndexEntry 1 }

pvxNextFreeIndexSwitchIdx OBJECT-TYPE
    SYNTAX       INTEGER (1..11)
    MAX-ACCESS   not-accessible
    STATUS       current
   	DESCRIPTION  "This object represents the particular switch id to fetch."
    ::= {pvxNextFreeIndexEntry 2 }

pvxNextFreeIndexValue OBJECT-TYPE
    SYNTAX       Integer32
    MAX-ACCESS   read-only
    STATUS       current
    DESCRIPTION  "The value of the next free index in the specified table on
                  the specified switch."
    ::= {pvxNextFreeIndexEntry 3 }

-----------------------------------------------------------------------
-- pvxUNITable
-----------------------------------------------------------------------
pvxUNITable OBJECT-TYPE
    SYNTAX       SEQUENCE OF PvxUNIEntry
    MAX-ACCESS   not-accessible
    STATUS       current
    DESCRIPTION  "This table defines all User Network Interfaces on all swotches."
    ::= { pvxBridge 18 }

pvxUNIEntry OBJECT-TYPE
    SYNTAX       PvxUNIEntry
    MAX-ACCESS   not-accessible
    STATUS       current
    DESCRIPTION  "The conceptual row object of the UNI Table"
    INDEX        { pvxUNISwitchId,
                   pvxUNIShelfId,
                   pvxUNISlotId,
                   pvxUNIPortTypeId,
                   pvxUNIPortId }
    ::= { pvxUNITable 1 }

PvxUNIEntry ::= SEQUENCE { pvxUNISwitchId         INTEGER,
                           pvxUNIShelfId          INTEGER,
                           pvxUNISlotId           INTEGER,
                           pvxUNIPortTypeId       PvxPortType,
                           pvxUNIPortId           Integer32,
                           pvxUNISpeed            Integer32,
                           pvxUNIMode             INTEGER,
                           pvxUNIMaxFrameSize     INTEGER,
                           pvxUNICurrentFrameSize INTEGER,
                           pvxUNIServiceType      INTEGER,
                           pvxUNINumServices      Integer32,
                           pvxUNICPVid            INTEGER,
                           pvxUNIRowStatus        RowStatus }

 
pvxUNISwitchId   OBJECT-TYPE
   	    SYNTAX       INTEGER(1..11)
       	MAX-ACCESS   not-accessible
       	STATUS       current
   	    DESCRIPTION  "This object represents the particular switch id."
        ::= { pvxUNIEntry 1 }

pvxUNIShelfId OBJECT-TYPE
        SYNTAX       INTEGER (0|1|11|21|31)
        MAX-ACCESS   not-accessible
        STATUS       current
        DESCRIPTION  ""
        ::= { pvxUNIEntry 2 }

pvxUNISlotId OBJECT-TYPE
        SYNTAX       INTEGER (0|1|3|5|7|9|11|13|15|17|19)
        MAX-ACCESS   not-accessible
        STATUS       current
        DESCRIPTION  ""
        ::= { pvxUNIEntry 3 }

pvxUNIPortTypeId OBJECT-TYPE
        SYNTAX       PvxPortType 
        MAX-ACCESS   not-accessible
        STATUS       current
        DESCRIPTION  ""
        ::= { pvxUNIEntry 4 }

pvxUNIPortId OBJECT-TYPE
        SYNTAX       Integer32
        MAX-ACCESS   not-accessible
        STATUS       current
        DESCRIPTION  ""
        ::= { pvxUNIEntry 5 }

pvxUNISpeed OBJECT-TYPE
        SYNTAX       Integer32
        MAX-ACCESS   read-only
        STATUS       current
        DESCRIPTION  "Speed of the UNI in mb/sec"
        ::= { pvxUNIEntry 6 }

pvxUNIMode OBJECT-TYPE
        SYNTAX       INTEGER { fullDuplex (1),
                               halfDuplex (2) }
        MAX-ACCESS   read-only
        STATUS       current
        DESCRIPTION  "Full/half duplex mode of the UNI"
        ::= { pvxUNIEntry 7 }

pvxUNIMaxFrameSize OBJECT-TYPE
        SYNTAX       INTEGER (1522..9600)
        MAX-ACCESS   read-create
        STATUS       current
        DESCRIPTION  "Maximum Frame size for the UNI"
        DEFVAL       { 1522 }
        ::= { pvxUNIEntry 8 }

pvxUNICurrentFrameSize OBJECT-TYPE
        SYNTAX       INTEGER (1522..9600)
        MAX-ACCESS   read-only
        STATUS       current
        DESCRIPTION  "The maximum of the Max Frame Size of all the 
                      services associated with the UNI."
        ::= { pvxUNIEntry 9 }

pvxUNIServiceType OBJECT-TYPE
        SYNTAX       INTEGER { unspecified     (1),
                               private         (2),
                               virtualSingle   (3),
                               virtualMultiple (4),
                               virtualUntagged (5) }
        MAX-ACCESS   read-create
        STATUS       current
        DESCRIPTION  "A combination of the MEF variables for multiplexing, bundling
                      and all-in-bundling."
        DEFVAL       { unspecified }
        ::= { pvxUNIEntry 10 }

pvxUNINumServices OBJECT-TYPE
        SYNTAX       Integer32
        MAX-ACCESS   read-only
        STATUS       current
        DESCRIPTION  "The number of services that attach to this UNI."
        ::= { pvxUNIEntry 11 }

pvxUNICPVid OBJECT-TYPE
        SYNTAX       INTEGER (0..4094)
        MAX-ACCESS   read-create
        STATUS       current
        DESCRIPTION  "The Port VLAN Id at the customer level for this 
                      UNI. This field is valid only if UNIServiceType 
                      is virtualSingle, virtualMultiple, or virtualUntagged."
        DEFVAL       { 0 }
    ::= { pvxUNIEntry 12 }

pvxUNIRowStatus OBJECT-TYPE
        SYNTAX       RowStatus
        MAX-ACCESS   read-create
        STATUS       current
        DESCRIPTION  ""
    ::= { pvxUNIEntry 100 }   


-----------------------------------------------------------------------
-- pvxNNITable
-----------------------------------------------------------------------
pvxNNITable OBJECT-TYPE
    SYNTAX       SEQUENCE OF PvxNNIEntry
    MAX-ACCESS   not-accessible
    STATUS       current
    DESCRIPTION  "This table defines all User Network Interfaces on all swotches."
    ::= { pvxBridge 19 }

pvxNNIEntry OBJECT-TYPE
    SYNTAX       PvxNNIEntry
    MAX-ACCESS   not-accessible
    STATUS       current
    DESCRIPTION  "The conceptual row object of the NNI Table"
    INDEX        { pvxNNISwitchId,
                   pvxNNIShelfId,
                   pvxNNISlotId,
                   pvxNNIPortTypeId,
                   pvxNNIPortId }
    ::= { pvxNNITable 1 }

PvxNNIEntry ::= SEQUENCE { pvxNNISwitchId      INTEGER,
                           pvxNNIShelfId       INTEGER,
                           pvxNNISlotId        INTEGER,
                           pvxNNIPortTypeId    PvxPortType,
                           pvxNNIPortId        Integer32,
                           pvxNNISpeed         Integer32,
                           pvxNNIMode          INTEGER,
                           pvxNNIMaxFrameSize  INTEGER,
                           pvxNNIExternal      TruthValue,
                           pvxNNIRowStatus     RowStatus }
 
pvxNNISwitchId   OBJECT-TYPE
       	SYNTAX       INTEGER(1..11)
       	MAX-ACCESS   not-accessible
       	STATUS       current
       	DESCRIPTION  "This object represents the particular switch id."
        ::= { pvxNNIEntry 1 }

pvxNNIShelfId OBJECT-TYPE
        SYNTAX       INTEGER (0|1|11|21|31)
        MAX-ACCESS   not-accessible
        STATUS       current
        DESCRIPTION  ""
        ::= { pvxNNIEntry 2 }

pvxNNISlotId OBJECT-TYPE
        SYNTAX       INTEGER (0|1|3|5|7|9|11|13|15|17|19)
        MAX-ACCESS   not-accessible
        STATUS       current
        DESCRIPTION  ""
        ::= { pvxNNIEntry 3 }

pvxNNIPortTypeId OBJECT-TYPE
        SYNTAX       PvxPortType 
        MAX-ACCESS   not-accessible
        STATUS       current
        DESCRIPTION  ""
        ::= { pvxNNIEntry 4 }

pvxNNIPortId OBJECT-TYPE
        SYNTAX       Integer32
        MAX-ACCESS   not-accessible
        STATUS       current
        DESCRIPTION  ""
        ::= { pvxNNIEntry 5 }

pvxNNISpeed OBJECT-TYPE
        SYNTAX       Integer32
        MAX-ACCESS   read-only
        STATUS       current
        DESCRIPTION  "Speed of the NNI in mb/sec"
    ::= { pvxNNIEntry 6 }

pvxNNIMode OBJECT-TYPE
        SYNTAX       INTEGER { fullDuplex (1),
                               halfDuplex (2) }
        MAX-ACCESS   read-only
        STATUS       current
        DESCRIPTION  "Full/half duplex mode of the NNI"
        ::= { pvxNNIEntry 7 }

pvxNNIMaxFrameSize OBJECT-TYPE
        SYNTAX       INTEGER (1526..9600)
        MAX-ACCESS   read-create
        STATUS       current
        DESCRIPTION  "Maximum Frame size for the NNI"
        DEFVAL       { 9600 }
        ::= { pvxNNIEntry 8 }

pvxNNIExternal OBJECT-TYPE
        SYNTAX       TruthValue
        MAX-ACCESS   read-create
        STATUS       current
        DESCRIPTION  "Boolean value to indicate if a NNI port is an External NNI(ENNI).
                      A value of true means the prot is an ENNI."
        DEFVAL       { false }
        ::= { pvxNNIEntry 9 }

pvxNNIRowStatus OBJECT-TYPE
        SYNTAX       RowStatus
        MAX-ACCESS   read-create
        STATUS       current
        DESCRIPTION  ""
    ::= { pvxNNIEntry 100 }

-----------------------------------------------------------------------
--	pvxVlanPortTable  Table
-----------------------------------------------------------------------
pvxVlanPortTable OBJECT-TYPE
    SYNTAX       SEQUENCE OF PVXVLANPortEntry
    MAX-ACCESS   not-accessible
    STATUS       current
    DESCRIPTION  "This table is used to configure Vlan port related entries."
    ::= { pvxBridge 20 }

pvxVlanPortEntry OBJECT-TYPE
    SYNTAX       PVXVLANPortEntry
    MAX-ACCESS   not-accessible
    STATUS       current
    DESCRIPTION  "The conceptual row object of the vlan port."
    INDEX        { pvxVlanPortSwitchIdx,
                   pvxVlanPortShelfIdx,
                   pvxVlanPortSlotIdx,
                   pvxVlanPortTypeIdx,
                   pvxVlanPortIdx }
    ::= { pvxVlanPortTable 1 }

PVXVLANPortEntry ::= SEQUENCE { pvxVlanPortSwitchIdx		        INTEGER,
               				    pvxVlanPortShelfIdx       	        INTEGER,
				                pvxVlanPortSlotIdx        	        INTEGER,
				                pvxVlanPortTypeIdx		            PvxPortType,
                        	    pvxVlanPortIdx         		        INTEGER,
                                pvxVlanPortGvrpAdminState           INTEGER,
                                pvxVlanPortRestrictedVlanState      INTEGER,
                                pvxVlanPortEthPortAllowedFrametType INTEGER,
                                pvxVlanPortIngressFiltering         INTEGER,
                                pvxVlanPortGvrpFailedRegistrations  Integer32,
                                pvxVlanPortLastBpduOrigin           MacAddress }

                                
pvxVlanPortSwitchIdx OBJECT-TYPE
   	SYNTAX       INTEGER(1..11)
   	MAX-ACCESS   not-accessible
   	STATUS       current
   	DESCRIPTION  "This object represents the particular switch id ."
    ::= {pvxVlanPortEntry 1 }

pvxVlanPortShelfIdx OBJECT-TYPE
    SYNTAX       INTEGER (0|1|11|21|31)
    MAX-ACCESS   not-accessible
    STATUS       current
    DESCRIPTION  "This represents the shelf this port belongs to."
    ::= {pvxVlanPortEntry 2 }

pvxVlanPortSlotIdx OBJECT-TYPE
    SYNTAX       INTEGER (0|1|3|5|7|9|11|13|15|17|19)
    MAX-ACCESS   not-accessible
    STATUS       current
    DESCRIPTION  "This represents the slot this port belogs to."
    ::= {pvxVlanPortEntry 3 }

pvxVlanPortTypeIdx OBJECT-TYPE
    SYNTAX       PvxPortType
    MAX-ACCESS   not-accessible
    STATUS       current
    DESCRIPTION  "This represents the port type."
    ::= {pvxVlanPortEntry 4 }

pvxVlanPortIdx OBJECT-TYPE
    SYNTAX       INTEGER (1..24) 
    MAX-ACCESS   not-accessible
    STATUS       current
    DESCRIPTION  "This is the port index of the vlan port."
    ::= {pvxVlanPortEntry 5 }

pvxVlanPortGvrpAdminState OBJECT-TYPE
    SYNTAX       INTEGER { enable  (1),
                           disable (2) }
    MAX-ACCESS   read-create
    STATUS       current
    DESCRIPTION  "The state of GVRP operation on this port.  The value 
        enabled(1) indicates that GVRP is enabled on this port, 
        as long as the global GVRP status is enabled on the switch.
        When disabled(2) but global GVRP is still enabled for the device,
        GVRP is disabled on this port: any GVRP packets received will be 
        silently discarded and no GVRP registrations will be propagated from
        other ports."
    DEFVAL       { enable }
    ::= {pvxVlanPortEntry 6 }

pvxVlanPortRestrictedVlanState OBJECT-TYPE
    SYNTAX       INTEGER { enable  (1),
                           disable (2) }
    MAX-ACCESS   read-create
    STATUS       current
    DESCRIPTION  "The state of Restricted VLAN Registration on this port. 
         If the value of this control is enabled(1), then creation 
         of a new dynamic VLAN entry is permitted only if there 
         is a Static VLAN Registration Entry for the VLAN concerned.  If the
         value is set to disabled(2), dynamic vlan participation is allowed."
    DEFVAL       { disable }
    ::= {pvxVlanPortEntry 7 }

pvxVlanPortEthPortAllowedFrametType OBJECT-TYPE
    SYNTAX       INTEGER {
		            admitAll(1), 
		            admitOnlyVlanTagged(2), 
		            admitOnlyUntaggedAndPriorityTagged(3),
                    admitDefault(4)
		         }
    MAX-ACCESS   read-only
    STATUS       current
    DESCRIPTION  "When the value is admitOnlyVlanTagged(2) port will
        discard untagged frames or Priority-Tagged frames.  When admitAll(1),
        untagged frames or Priority-Tagged frames received on this port 
        will be accepted and assigned to the PVID for this port.
        When this is admitOnlyUntaggedAndPriorityTagged the device  
        will recieve only untagged and priority tagged frames on  
        this port."
    ::= {pvxVlanPortEntry 8 }


pvxVlanPortIngressFiltering OBJECT-TYPE
    SYNTAX       INTEGER {
                    true (1),
                    false (2)
                 }
    MAX-ACCESS   read-only
    STATUS       deprecated
    DESCRIPTION  "When this is true(1) the device will discard incoming 
        frames for VLANs which do not include this Port in its 
        Member set.  When false(2), the port will accept all 
        incoming frames"
    ::= {pvxVlanPortEntry 9 }

pvxVlanPortGvrpFailedRegistrations OBJECT-TYPE
    SYNTAX       Integer32
    MAX-ACCESS   read-only
    STATUS       current
    DESCRIPTION  "The total number of failed GVRP registrations, for any 
        reason, on this port."
    ::= {pvxVlanPortEntry 10 }

pvxVlanPortLastBpduOrigin OBJECT-TYPE
    SYNTAX       MacAddress
    MAX-ACCESS   read-only
    STATUS       current
    DESCRIPTION  "The Source MAC Address of the last GVRP message 
        received on this port."
    ::= {pvxVlanPortEntry 11 }



-----------------------------------------------------------------------
-- Last BPDU MAC Address changes event
-----------------------------------------------------------------------


pvxVlanPortLastBpduOriginChangeEvt NOTIFICATION-TYPE
    OBJECTS      { pvxVlanPortSwitchIdx,
                   pvxVlanPortShelfIdx,
                   pvxVlanPortSlotIdx,
                   pvxVlanPortTypeIdx,
                   pvxVlanPortIdx }
    STATUS        current
    DESCRIPTION "A pvxVlanPortLastBpduOriginChangeEvt notification is sent when 
                 the Source MAC Address of the last GVRP message received on this 
                 port changes."
   ::= { pvxVlanPortLastBpduOriginChangeEvtNotifications 0 1 }


-----------------------------------------------------------------------
-- Add or Remove port to a VLAN in a dynamic VLAN table events
-----------------------------------------------------------------------

pvxVlanPortAddDynamicVlanEvt NOTIFICATION-TYPE
    OBJECTS      {  pvxVlanPortSwitchIdx,
                    pvxVlanPortShelfIdx,
                    pvxVlanPortSlotIdx,
                    pvxVlanPortTypeIdx,
                    pvxVlanPortIdx,
                    pvxVLANIdx }
    STATUS        current
    DESCRIPTION "A pvxVlanPortAddDynamicVlanEvt notification is sent when 
                 a port is added to a VLAN in a dynamic VLAN table."
   ::= { pvxVlanPortAddDynamicVlanEvtNotifications 0 1 }

pvxVlanPortRemoveDynamicVlanEvt NOTIFICATION-TYPE
    OBJECTS      {  pvxVlanPortSwitchIdx,
                    pvxVlanPortShelfIdx,
                    pvxVlanPortSlotIdx,
                    pvxVlanPortTypeIdx,
                    pvxVlanPortIdx,
                    pvxVLANIdx }
    STATUS        current
    DESCRIPTION "A pvxVlanPortRemoveDynamicVlanEvt notification is sent when 
                 a port is removed from a VLAN in a dynamic VLAN table."
   ::= { pvxVlanPortRemoveDynamicVlanEvtNotifications 0 1 }



-----------------------------------------------------------------------
--	pvxVlanCurrentTable  Table
-----------------------------------------------------------------------
pvxVlanCurrentTable OBJECT-TYPE
    SYNTAX       SEQUENCE OF PVXVLANCurrentEntry
    MAX-ACCESS   not-accessible
    STATUS       current
    DESCRIPTION  "This table is used to retrieve Vlan related entries."
    ::= { pvxBridge 21 }

pvxVlanCurrentEntry OBJECT-TYPE
    SYNTAX       PVXVLANCurrentEntry
    MAX-ACCESS   not-accessible
    STATUS       current
    DESCRIPTION  "The conceptual row object of the vlan entity."
    INDEX        { 	pvxVlanCurrentSwitchIdx,
					pvxVlanCurrentTimeMark,
					pvxVlanCurrentVlanIdx }
    ::= { pvxVlanCurrentTable 1 }

PVXVLANCurrentEntry ::= SEQUENCE { pvxVlanCurrentSwitchIdx		        INTEGER,
				                   pvxVlanCurrentTimeMark       	    Unsigned32,
				                   pvxVlanCurrentVlanIdx        	    INTEGER,
				                   pvxVlanCurrentStatus		            INTEGER,
                        	       pvxVlanCurrentCreationTime	        Integer32
                                 }
                                
pvxVlanCurrentSwitchIdx OBJECT-TYPE
   	SYNTAX       INTEGER(1..11)
   	MAX-ACCESS   not-accessible
   	STATUS       current
   	DESCRIPTION  "This object represents the particular switch id."
    ::= {pvxVlanCurrentEntry 1 }

pvxVlanCurrentTimeMark OBJECT-TYPE
    SYNTAX       Unsigned32
    MAX-ACCESS   not-accessible
    STATUS       current
    DESCRIPTION  "A TimeFilter for this entry."
    ::= {pvxVlanCurrentEntry 2 }

pvxVlanCurrentVlanIdx OBJECT-TYPE
    SYNTAX       INTEGER (1..4094)
    MAX-ACCESS   not-accessible
    STATUS       current
    DESCRIPTION  "Represents the VLAN IDs in the system"
    ::= {pvxVlanCurrentEntry 3 }

pvxVlanCurrentStatus OBJECT-TYPE
    SYNTAX       INTEGER {
  		            other(1), 
		            permanent(2), 
		            dynamicGVRP(3)
		         }
    MAX-ACCESS   read-only
    STATUS       current
    DESCRIPTION  "This object indicates the status of this entry. 
            other(1) - this entry is currently in use but the 
                conditions under which it will remain so differ 
                from the following values. 
            permanent(2) - this entry, corresponding to an entry 
                in the static vlan table that is currently in use and 
                will remain so after the next reset of the 
                device.  The port lists for this entry include 
                ports from static entry and ports learnt dynamically. 
            dynamicGVRP(3) - this entry is currently in use 
                and will remain so until removed by GVRP.  There 
                is no static entry for this VLAN and it will be 
                removed when the last port leaves the VLAN."
    ::= {pvxVlanCurrentEntry 4 }

pvxVlanCurrentCreationTime OBJECT-TYPE
    SYNTAX       Integer32 
    MAX-ACCESS   read-only
    STATUS       current
    DESCRIPTION  "The value of sysUpTime when this VLAN was created."
    ::= {pvxVlanCurrentEntry 5 }


-- { pvxBridge 22 } table obsolete, removed

-- { pvxBridge 23 } table obsolete, removed
  
-----------------------------------------------------------------------
--	pvxDynamicVlanPortTable  Table
-----------------------------------------------------------------------
pvxDynamicVlanPortTable OBJECT-TYPE
    SYNTAX       SEQUENCE OF PVXDynamicVLANPortEntry
    MAX-ACCESS   not-accessible
    STATUS       current
    DESCRIPTION  "This table is used to configure Vlan Egress port related entries."
    ::= { pvxBridge 24 }

pvxDynamicVlanPortEntry OBJECT-TYPE
    SYNTAX       PVXDynamicVLANPortEntry
    MAX-ACCESS   not-accessible
    STATUS       current
    DESCRIPTION  "The conceptual row object of the vlan egress port."
    INDEX        {
                    pvxL2IntfSwitchIdx,
                    pvxDynamicVlanPortTimeMark,
                    pvxDynamicVlanPortVlanIdx,
                    pvxL2IntfShelfIdx,
                    pvxL2IntfSlotIdx,
                    pvxL2IntfPortTypeIdx,
                    pvxL2IntfPortIdx,
               	    pvxL2IntfSubPortNumber
                 }
    ::= { pvxDynamicVlanPortTable 1 }

PVXDynamicVLANPortEntry ::= SEQUENCE {
                                      pvxDynamicVlanPortTimeMark        Unsigned32,
                                      pvxDynamicVlanPortVlanIdx         INTEGER,
                                      pvxDynamicVlanPortTagged          INTEGER
                                    }
                                
pvxDynamicVlanPortTimeMark OBJECT-TYPE
    SYNTAX       Unsigned32
    MAX-ACCESS   not-accessible
    STATUS       current
    DESCRIPTION  "A TimeFilter for this entry."
    ::= {pvxDynamicVlanPortEntry 1 }

pvxDynamicVlanPortVlanIdx OBJECT-TYPE
    SYNTAX       INTEGER (1..4094)
    MAX-ACCESS   not-accessible
    STATUS       current
    DESCRIPTION  "Represents the VLAN IDs in the system"
    ::= {pvxDynamicVlanPortEntry 2 }

pvxDynamicVlanPortTagged OBJECT-TYPE
    SYNTAX       INTEGER {
                           tagged(1), 
                           untagged(2)
		         }
    MAX-ACCESS   read-only
    STATUS       current
    DESCRIPTION  "Indicates whether the port is a tagged or a untagged 
                  member in the VLAN. 

                  tagged   - to add the port in the tagged portlist. 
                  untagged - to add the port in the untagged portlist."
    ::= {pvxDynamicVlanPortEntry 3 }



-----------------------------------------------------------------------
-- StackingPort Table
-----------------------------------------------------------------------
pvxStackingPortTable OBJECT-TYPE
    SYNTAX       SEQUENCE OF PVXStackingPortEntry
    MAX-ACCESS   not-accessible
    STATUS       current
    DESCRIPTION  "This table allows the administrator to configure which port
                 or ports will be used as teh stacking port or ports between the
                 PacketVXes in the switch."
    ::= { pvxBridge 25 }

pvxStackingPortEntry OBJECT-TYPE
    SYNTAX       PVXStackingPortEntry
    MAX-ACCESS   not-accessible
    STATUS       current
    DESCRIPTION  "The conceptual row object of the stacking port."
    INDEX        {
                    pvxL2IntfSwitchIdx,                    
                    pvxL2IntfShelfIdx,
                    pvxL2IntfSlotIdx,
                    pvxL2IntfPortTypeIdx,
                    pvxL2IntfPortIdx
                 }
    ::= { pvxStackingPortTable 1 }

PVXStackingPortEntry ::= SEQUENCE {
                                  pvxStackingPortOperStatus          INTEGER,
                                  pvxStackingPortRowStatus           RowStatus
                                  }

pvxStackingPortOperStatus OBJECT-TYPE
    SYNTAX       INTEGER {
                           up(1), 
                           down(2),
                           notPresent(3)
		         }
    MAX-ACCESS   read-only
    STATUS       current
    DESCRIPTION  "Indicates the current operational state of te stacking port."
    ::= {pvxStackingPortEntry 1 }
    
pvxStackingPortRowStatus OBJECT-TYPE
        SYNTAX       RowStatus
        MAX-ACCESS   read-create
        STATUS       current
        DESCRIPTION  ""
    ::= { pvxStackingPortEntry 100 }

-----------------------------------------------------------------------
-- Flow  Table
-----------------------------------------------------------------------
pvxFlowTable OBJECT-TYPE
    SYNTAX       SEQUENCE OF PVXFlowEntry
    MAX-ACCESS   not-accessible
    STATUS       current
    DESCRIPTION  ""
    ::= { pvxBridgeServices 12 }

pvxFlowEntry OBJECT-TYPE
    SYNTAX       PVXFlowEntry
    MAX-ACCESS   not-accessible
    STATUS       current
    DESCRIPTION  "The conceptual row object of the Flow Class Config table."
    INDEX        { pvxFSwitchIdx,
                   pvxFIdx }
    ::= { pvxFlowTable 1 }

PVXFlowEntry ::= SEQUENCE 		{ 	pvxFSwitchIdx    			INTEGER,  
                              		pvxFIdx     	 			Integer32,
                              		pvxFClassificationIdList 	DisplayString,  
							  		pvxFMeterId					Integer32,
							  		pvxFCoSName					DisplayString,
                              		pvxFRowStatus   			RowStatus }

pvxFSwitchIdx OBJECT-TYPE
   	SYNTAX       INTEGER(1..11)
   	MAX-ACCESS   not-accessible
   	STATUS       current
   	DESCRIPTION  "This object represents the particular switch Id."
   	    ::= { pvxFlowEntry 1 }

pvxFIdx OBJECT-TYPE
    SYNTAX       Integer32
    MAX-ACCESS   not-accessible
    STATUS       current
    DESCRIPTION  ""
    ::= { pvxFlowEntry 2 }

pvxFClassificationIdList OBJECT-TYPE
    SYNTAX       DisplayString 
    MAX-ACCESS   read-create
    STATUS       current
    DESCRIPTION  ""
    ::= { pvxFlowEntry 3 }

pvxFMeterId OBJECT-TYPE
    SYNTAX       Integer32 
    MAX-ACCESS   read-create
    STATUS       current
    DESCRIPTION  ""
    ::= { pvxFlowEntry 4 }

pvxFCoSName OBJECT-TYPE
    SYNTAX       DisplayString
    MAX-ACCESS   read-create
    STATUS       current
    DESCRIPTION  ""
    ::= { pvxFlowEntry 5 }

pvxFRowStatus OBJECT-TYPE
    SYNTAX       RowStatus
    MAX-ACCESS   read-create
    STATUS       current
    DESCRIPTION  "This object is used to create a new row in the 
                  flowClassTable."
    ::= { pvxFlowEntry 100 }



pvxFlowClassificationTable OBJECT-TYPE
    SYNTAX       SEQUENCE OF PVXFlowClassificationEntry
    MAX-ACCESS   not-accessible
    STATUS       current
    DESCRIPTION  "This table is used to configure the Flow classification 
                  on virtual switch. A single value or a range of values can be 
                  specified in the set request for the filter objects as following 
                  # for single or #to# for range of values."
    ::= { pvxBridgeServices 13 }

pvxFlowClassificationEntry OBJECT-TYPE
    SYNTAX       PVXFlowClassificationEntry
    MAX-ACCESS   not-accessible
    STATUS       current
    DESCRIPTION  "The conceptual row object of the Flow Class Config table."
    INDEX        { pvxFloClSwitchIdx,
                   pvxFloClIdx }
    ::= { pvxFlowClassificationTable 1 }

PVXFlowClassificationEntry ::= SEQUENCE {   pvxFloClSwitchIdx             INTEGER,  
                                            pvxFloClIdx                   INTEGER,
                                            pvxFloClActionId              INTEGER,
                                            pvxFloClMeterId               INTEGER,
                                            pvxFloClStatus                INTEGER,
                                            pvxFloClEntryType             INTEGER,
                                            pvxFloClL2InterfaceRange      PvxL2PortList,
                                            pvxFloClCVlanFilter           DisplayString,
                                            pvxFloClSVlanFilter           DisplayString,
                                            pvxFloClSourceIPFilter        DisplayString,
                                            pvxFloClDestIPFilter          DisplayString,
                                            pvxFloClIPProtocolFilter      DisplayString,
                                            pvxFloClEtherTypeFilter       DisplayString,
                                            pvxFloClSourceMacFilter       DisplayString,
                                            pvxFloClDestMacFilter         DisplayString,
                                            pvxFloClSourceUDPorTCPFilter  DisplayString,
                                            pvxFloClDestUDPorTCPFilter    DisplayString,
                                            pvxFloClRowStatus             RowStatus }

pvxFloClSwitchIdx OBJECT-TYPE
   	SYNTAX       INTEGER(1..11)
   	MAX-ACCESS   not-accessible
   	STATUS       current
   	DESCRIPTION  "This object represents the particular switch Id."
   	    ::= { pvxFlowClassificationEntry 1 }

pvxFloClIdx OBJECT-TYPE
    SYNTAX       INTEGER (1..4096)
    MAX-ACCESS   not-accessible
    STATUS       current
    DESCRIPTION  "Index of this flow classification on this switch"
    ::= { pvxFlowClassificationEntry 2 }

pvxFloClActionId OBJECT-TYPE
    SYNTAX       INTEGER (0..4096)
    MAX-ACCESS   read-create
    STATUS       current
    DESCRIPTION  "The action taken by the switch when this classification is matched;
                  0 = no action."
    ::= { pvxFlowClassificationEntry 3 }

pvxFloClMeterId OBJECT-TYPE
    SYNTAX       INTEGER (0..4096)
    MAX-ACCESS   read-create
    STATUS       current
    DESCRIPTION  "Meter associated with this flow classification, 0 = no meter"
    ::= { pvxFlowClassificationEntry 4 }

pvxFloClStatus OBJECT-TYPE
    SYNTAX       INTEGER { enable  (1),
                           disable (2) }
    MAX-ACCESS   read-create
    STATUS       current
    DESCRIPTION  "The administrative status of this entry"
    ::= { pvxFlowClassificationEntry 5 }

pvxFloClEntryType OBJECT-TYPE
    SYNTAX       INTEGER { untyped  (1),
                           ipAcl (2),
                           macAcl (3) }
    MAX-ACCESS   read-create
    STATUS       current
    DESCRIPTION  "The administrative status of this entry"
    ::= { pvxFlowClassificationEntry 6 }


pvxFloClL2InterfaceRange OBJECT-TYPE
    SYNTAX       DisplayString 
    MAX-ACCESS   read-create
    STATUS       current
    DESCRIPTION  "Range of interfaces on which this flow classification applies,
                  blank=all interfaces
				  of the form: L2Interface#[-L2Interface#]"
    ::= { pvxFlowClassificationEntry 7 }

pvxFloClCVlanFilter OBJECT-TYPE
    SYNTAX       DisplayString
    MAX-ACCESS   read-create
    STATUS       current
    DESCRIPTION  "C-VLAN to match, blank=don't care"
    ::= { pvxFlowClassificationEntry 8 }

pvxFloClSVlanFilter OBJECT-TYPE
    SYNTAX       DisplayString
    MAX-ACCESS   read-create
    STATUS       current
    DESCRIPTION  "S-VLAN to match, blank=don't care"
    ::= { pvxFlowClassificationEntry 9 }

pvxFloClSourceIPFilter OBJECT-TYPE
    SYNTAX       DisplayString
    MAX-ACCESS   read-create
    STATUS       current
    DESCRIPTION  "Source IP Address (range or subnet) to match,
                  blank=don't care
	              Of the form: a.b.c.d[-e.f.g.h|/n]"
    ::= { pvxFlowClassificationEntry 10 }

pvxFloClDestIPFilter OBJECT-TYPE
    SYNTAX       DisplayString
    MAX-ACCESS   read-create
    STATUS       current
    DESCRIPTION  "Destination IP Address (range or subnet) to match,
                  blank=don't care
	              Of the form: a.b.c.d[-e.f.g.h|/n]"
    ::= { pvxFlowClassificationEntry 11 }

pvxFloClIPProtocolFilter OBJECT-TYPE
    SYNTAX       DisplayString
    MAX-ACCESS   read-create
    STATUS       current
    DESCRIPTION  "IP protocol range to match, blank=don't care
			      of the form: #[-#]"
    ::= { pvxFlowClassificationEntry 12 }

pvxFloClEtherTypeFilter OBJECT-TYPE
    SYNTAX       DisplayString
    MAX-ACCESS   read-create
    STATUS       current
    DESCRIPTION  "Ethernet Protoocl Type range to match, blank=don't care
			      of the form: #[-#]"
    ::= { pvxFlowClassificationEntry 13 }

pvxFloClSourceMacFilter OBJECT-TYPE
    SYNTAX       DisplayString
    MAX-ACCESS   read-create
    STATUS       current
    DESCRIPTION  "Source MAC Address (range) to match, blank=don't care
	              Of the form: a.b.c.d.e.f[-g.h.i.j.k.l]"
    ::= { pvxFlowClassificationEntry 14 }

pvxFloClDestMacFilter OBJECT-TYPE
    SYNTAX       DisplayString
    MAX-ACCESS   read-create
    STATUS       current
    DESCRIPTION  "Destination MAC Address (range) to match, blank=don't care
	              Of the form: a.b.c.d.e.f[-g.h.i.j.k.l]"
    ::= { pvxFlowClassificationEntry 15 }

pvxFloClSourceUDPorTCPFilter OBJECT-TYPE
    SYNTAX       DisplayString
    MAX-ACCESS   read-create
    STATUS       current
    DESCRIPTION  "Source TCP or UDP port to match, blank=don't care
	              Of the form: #[-#]"
    ::= { pvxFlowClassificationEntry 16 }

pvxFloClDestUDPorTCPFilter OBJECT-TYPE
    SYNTAX       DisplayString
    MAX-ACCESS   read-create
    STATUS       current
    DESCRIPTION  "Destination TCP or UDP port to match, blank=don't care
	              Of the form: #[-#]"
    ::= { pvxFlowClassificationEntry 17 }
 
pvxFloClRowStatus OBJECT-TYPE
    SYNTAX       RowStatus
    MAX-ACCESS   read-create
    STATUS       current
    DESCRIPTION  "This object is used to create a new row in the 
                  flowClassTable."
    ::= { pvxFlowClassificationEntry 100 }





pvxFlowActionsTable OBJECT-TYPE
    SYNTAX       SEQUENCE OF PVXFlowActionsEntry
    MAX-ACCESS   not-accessible
    STATUS       current
    DESCRIPTION  ""
    ::= { pvxBridgeServices 14 }

pvxFlowActionsEntry OBJECT-TYPE
    SYNTAX       PVXFlowActionsEntry
    MAX-ACCESS   not-accessible
    STATUS       current
    DESCRIPTION  "The conceptual row object of the Flow Class Config table."
    INDEX        { pvxFloActSwitchIdx,
                   pvxFloActIdx }
    ::= { pvxFlowActionsTable 1 }

PVXFlowActionsEntry ::= SEQUENCE { pvxFloActSwitchIdx                INTEGER,  
                              	   pvxFloActIdx                      INTEGER,
                                   pvxFloActChangePriority           TruthValue,
                                   pvxFloActNewPriority              INTEGER,
                                   pvxFloActPacketAction             INTEGER,
                              	   pvxFloActRedirectToInterfaceIndex DisplayString,
                              	   pvxFloActMirrorType               INTEGER,
                              	   pvxFloActMirrorToInterfaceIndex   DisplayString,
                              	   pvxFloActSVlanValue               INTEGER,
                                   pvxFloActCVlanValue               INTEGER,
                                   pvxFloActSVlanAction              INTEGER,
                                   pvxFloActCVlanAction              INTEGER,
                                   pvxFloActGreenAction              INTEGER,
                                   pvxFloActGreenCNGAction           INTEGER,
                                   pvxFloActRedAction                INTEGER,
                              	   pvxFloActRedCNGAction             INTEGER,
                              	   pvxFloActYellowAction             INTEGER,
                              	   pvxFloActYellowCNGAction          INTEGER,
                                   pvxFloActRowStatus                RowStatus }

pvxFloActSwitchIdx OBJECT-TYPE
   	SYNTAX       INTEGER(1..11)
   	MAX-ACCESS   not-accessible
   	STATUS       current
   	DESCRIPTION  "This object represents the particular switch Id."
   	    ::= { pvxFlowActionsEntry 1 }

pvxFloActIdx OBJECT-TYPE
    SYNTAX          INTEGER ( 1..4096 )
    MAX-ACCESS   	not-accessible
    STATUS       	current
    DESCRIPTION  	"Index of this flow action on this switch"
    ::= { pvxFlowActionsEntry 2 }

pvxFloActChangePriority OBJECT-TYPE
    SYNTAX       TruthValue
    MAX-ACCESS   read-create
    STATUS       current
    DESCRIPTION  "Should the priority of this flow be re-assigned? If true,
                  the value of the pvxFloActNewPriority will be applied as the
                  new priority for the packets in the stream. If false,
                  the priority is left unchanged."
    ::= { pvxFlowActionsEntry 3 }

pvxFloActNewPriority OBJECT-TYPE
    SYNTAX       INTEGER ( 0..7 )
    MAX-ACCESS   read-create
    STATUS       current
    DESCRIPTION  "If the pvxFloActChangePriority field is true, the value of
                  this field will be used as the priority of packets
                  in the flow."
    ::= { pvxFlowActionsEntry 4 }


pvxFloActPacketAction OBJECT-TYPE
    SYNTAX       INTEGER { default (1),
                           drop (2),
                           redirect (3) }
    MAX-ACCESS   read-create
    STATUS       current
    DESCRIPTION  "Should we drop, redirect the packets or let them on their way?"
    ::= { pvxFlowActionsEntry 5 }

pvxFloActRedirectToInterfaceIndex OBJECT-TYPE
    SYNTAX       DisplayString 
    MAX-ACCESS   read-create
    STATUS       current
    DESCRIPTION  "When redirecting, Index of L2 Port to which the system
                  should redirect the flow"
    ::= { pvxFlowActionsEntry 6 }

pvxFloActMirrorType OBJECT-TYPE
    SYNTAX       INTEGER { none (1),
                           ingress (2),
                           egress (3),
                           both (4) }
    MAX-ACCESS   read-create
    STATUS       current
    DESCRIPTION  "What Mirroring action to perform on the flow?"
    ::= { pvxFlowActionsEntry 7 }

pvxFloActMirrorToInterfaceIndex OBJECT-TYPE
    SYNTAX       DisplayString
    MAX-ACCESS   read-create
    STATUS       current
    DESCRIPTION  "Index of L2 interface to which the switch will mirror the flow."
    ::= { pvxFlowActionsEntry 8 }

pvxFloActSVlanValue OBJECT-TYPE
    SYNTAX       INTEGER ( 0..4094 )
    MAX-ACCESS   read-create
    STATUS       current
    DESCRIPTION  "S-VLAN to assign. 0=none"
    ::= { pvxFlowActionsEntry 9 }

pvxFloActCVlanValue OBJECT-TYPE
    SYNTAX       INTEGER ( 0..4095 )
    MAX-ACCESS   read-create
    STATUS       current
    DESCRIPTION  "C-VLAN to assign. 0=none"
    ::= { pvxFlowActionsEntry 10 }

pvxFloActSVlanAction OBJECT-TYPE
    SYNTAX       INTEGER { none (1),
                           add (2),
                           replace (3) }
    MAX-ACCESS   read-create
    STATUS       current
    DESCRIPTION  "What action should be performed on the S-VLAN?"
    ::= { pvxFlowActionsEntry 11 }

pvxFloActCVlanAction OBJECT-TYPE
    SYNTAX       INTEGER { none (1),
                           add (2),
                           replace (3) }
    MAX-ACCESS   read-create
    STATUS       current
    DESCRIPTION  "What action should be performed on the C-VLAN"
    ::= { pvxFlowActionsEntry 12 }

pvxFloActGreenAction OBJECT-TYPE
    SYNTAX       INTEGER { doNotDrop (1),
                           drop (2) }
    MAX-ACCESS   read-create
    STATUS       current
    DESCRIPTION  "What action should the switch take on Green Packets?"
    ::= { pvxFlowActionsEntry 13 }

pvxFloActGreenCNGAction OBJECT-TYPE
    SYNTAX       INTEGER { doNotChange (1),
                           green (2),
                           yellow (3),
                           red (4) }
    MAX-ACCESS   read-create
    STATUS       current
    DESCRIPTION  "If a green packet of this flow is found, what color
                  should it be changed to?"
    ::= { pvxFlowActionsEntry 14 }

pvxFloActRedAction OBJECT-TYPE
    SYNTAX       INTEGER { doNotDrop (1),
                           drop (2) }
    MAX-ACCESS   read-create
    STATUS       current
    DESCRIPTION  "What action should the switch take on Red Packets?"
    ::= { pvxFlowActionsEntry 15 }


pvxFloActRedCNGAction OBJECT-TYPE
    SYNTAX       INTEGER { doNotChange (1),
                           green (2),
                           yellow (3),
                           red (4) }
    MAX-ACCESS   read-create
    STATUS       current
    DESCRIPTION  "If a red packet of this flow is found, what color
                  should it be changed to?"
    ::= { pvxFlowActionsEntry 16 }

pvxFloActYellowAction OBJECT-TYPE
    SYNTAX       INTEGER { doNotDrop (1),
                           drop (2) }
    MAX-ACCESS   read-create
    STATUS       current
    DESCRIPTION  "What action should the switch take on Yellow Packets?"
    ::= { pvxFlowActionsEntry 17 }

pvxFloActYellowCNGAction OBJECT-TYPE
    SYNTAX       INTEGER { doNotChange (1),
                           green (2),
                           yellow (3),
                           red (4) }
    MAX-ACCESS   read-create
    STATUS       current
    DESCRIPTION  "If a yellow packet of this flow is found, what color
                  should it be changed to?"
    ::= { pvxFlowActionsEntry 18 }
 
pvxFloActRowStatus OBJECT-TYPE
    SYNTAX       RowStatus
    MAX-ACCESS   read-create
    STATUS       current
    DESCRIPTION  ""
    ::= { pvxFlowActionsEntry 100 }



pvxFlowMeterTable OBJECT-TYPE
    SYNTAX       SEQUENCE OF PVXFlowMeterEntry
    MAX-ACCESS   not-accessible
    STATUS       current
    DESCRIPTION  ""
    ::= { pvxBridgeServices 15 }


pvxFlowMeterEntry OBJECT-TYPE
    SYNTAX       PVXFlowMeterEntry
    MAX-ACCESS   not-accessible
    STATUS       current
    DESCRIPTION  "The conceptual row object of the Flow Class Config table."
    INDEX        { pvxFMSwitchIdx,
                   pvxFMMeterIdx}
    ::= { pvxFlowMeterTable 1 }

PVXFlowMeterEntry ::= SEQUENCE {	pvxFMSwitchIdx   	INTEGER,  
                               		pvxFMMeterIdx    	Integer32,
                               		pvxFMBWProfileId 	Integer32,  
                               		pvxFMMeterProfileId Integer32,
                               		pvxFMRowStatus 		RowStatus }
pvxFMSwitchIdx OBJECT-TYPE
   	SYNTAX       INTEGER(1..11)
   	MAX-ACCESS   not-accessible
   	STATUS       current
   	DESCRIPTION  "This object represents the particular switch Id."
   	    ::= { pvxFlowMeterEntry 1 }

pvxFMMeterIdx OBJECT-TYPE
    SYNTAX       Integer32 
    MAX-ACCESS   not-accessible
    STATUS       current
    DESCRIPTION  ""
    ::= { pvxFlowMeterEntry 2 }

pvxFMBWProfileId OBJECT-TYPE
    SYNTAX       Integer32 
    MAX-ACCESS   read-create
    STATUS       current
    DESCRIPTION  ""
    ::= { pvxFlowMeterEntry 3 }

pvxFMMeterProfileId OBJECT-TYPE
    SYNTAX       Integer32 
    MAX-ACCESS   read-create
    STATUS       current
    DESCRIPTION  ""
    ::= { pvxFlowMeterEntry 4 }

pvxFMRowStatus 	OBJECT-TYPE
    SYNTAX       RowStatus
    MAX-ACCESS   read-create
    STATUS       current
    DESCRIPTION  "This object is used to create a new row in the 
                  serviceMapTable."
    ::= { pvxFlowMeterEntry 100 }




pvxFlowStatsTable OBJECT-TYPE
    SYNTAX       SEQUENCE OF PVXFlowStatsEntry
    MAX-ACCESS   not-accessible
    STATUS       current
    DESCRIPTION  ""
    ::= { pvxBridgeServices 16 }


pvxFlowStatsEntry OBJECT-TYPE
    SYNTAX       PVXFlowStatsEntry
    MAX-ACCESS   not-accessible
    STATUS       current
    DESCRIPTION  ""
    INDEX        { pvxFSSwitchIdx,
                   pvxFSStatsIdx}
    ::= { pvxFlowStatsTable 1 }

PVXFlowStatsEntry ::= SEQUENCE {	pvxFSSwitchIdx    				INTEGER,  
                               		pvxFSStatsIdx     	 			Integer32,
                               		pvxFSFlowId 					Integer32,  
                               		pvxFSInProfilePackets 			Integer32,
					pvxFSOutOfProfilePackets 		Integer32,
					pvxFSCountOfClassifiedPackets 	Integer32,
                               		pvxFSRowStatus 					RowStatus }

pvxFSSwitchIdx OBJECT-TYPE
   	SYNTAX       INTEGER(1..11)
   	MAX-ACCESS   not-accessible
   	STATUS       current
   	DESCRIPTION  "This object represents the particular switch Id."
   	    ::= { pvxFlowStatsEntry 1 }

pvxFSStatsIdx OBJECT-TYPE
    SYNTAX       Integer32 
    MAX-ACCESS   not-accessible
    STATUS       current
    DESCRIPTION  ""
    ::= { pvxFlowStatsEntry 2 }

pvxFSFlowId OBJECT-TYPE
    SYNTAX       Integer32
    MAX-ACCESS   read-create
    STATUS       current
    DESCRIPTION  ""
    ::= { pvxFlowStatsEntry 3 }

pvxFSInProfilePackets OBJECT-TYPE
    SYNTAX       Integer32 
    MAX-ACCESS   read-create
    STATUS       current
    DESCRIPTION  ""
    ::= { pvxFlowStatsEntry 4 }

pvxFSOutOfProfilePackets OBJECT-TYPE
    SYNTAX      Integer32 
    MAX-ACCESS   read-create
    STATUS       current
    DESCRIPTION  ""
    ::= { pvxFlowStatsEntry 5 }

pvxFSCountOfClassifiedPackets OBJECT-TYPE
    SYNTAX       Integer32 
    MAX-ACCESS   read-create
    STATUS       current
    DESCRIPTION  ""
    ::= { pvxFlowStatsEntry 6 }


pvxFSRowStatus 	OBJECT-TYPE
    SYNTAX       RowStatus
    MAX-ACCESS   read-create
    STATUS       current
    DESCRIPTION  ""
    ::= { pvxFlowStatsEntry 100 }



-----------------------------------------------------------------------
-- pvxPbCVidRegistrationTable
-----------------------------------------------------------------------

pvxPbCVidRegistrationTable OBJECT-TYPE
    SYNTAX       SEQUENCE OF PVXPbCVidRegistrationTableEntry
    MAX-ACCESS   not-accessible
    STATUS       current
    DESCRIPTION  ""
    ::= { pvxBridgeServices 17 }


pvxPbCVidRegistrationTableEntry OBJECT-TYPE
    SYNTAX       PVXPbCVidRegistrationTableEntry
    MAX-ACCESS   not-accessible
    STATUS       current
    DESCRIPTION  ""
	INDEX 		 { 
                 pvxL2IntfSwitchIdx,
                 pvxL2IntfShelfIdx,
                 pvxL2IntfSlotIdx,
                 pvxL2IntfPortTypeIdx,
                 pvxL2IntfPortIdx,
                 pvxPCVRTCVlanIdFrom
                 }
    ::= { pvxPbCVidRegistrationTable 1 }

           
PVXPbCVidRegistrationTableEntry ::= SEQUENCE {
                 pvxPCVRTCVlanIdFrom     INTEGER,
                 pvxPCVRTCVlanIdTo       INTEGER,
                 pvxPCVRTSVlanId         INTEGER,
                 pvxPCVRTUntaggedPEP     TruthValue,
                 pvxPCVRTUntaggedCEP     TruthValue,
                 pvxPCVRTSource          INTEGER,
                 pvxPCVRTMapOperStatus   INTEGER,
                 pvxPCVRTXlateOperStatus INTEGER,
                 pvxPCVRTRowStatus       RowStatus
                 }

pvxPCVRTCVlanIdFrom OBJECT-TYPE
    SYNTAX       INTEGER(1..4094)
    MAX-ACCESS   not-accessible
    STATUS       current
    DESCRIPTION  "The beginning of the range of customer VLAN IDs that the system
                  will map to the service VLAN specified in pvxPCVRTSVlanId."
    ::= { pvxPbCVidRegistrationTableEntry 1 }

pvxPCVRTCVlanIdTo OBJECT-TYPE
    SYNTAX       INTEGER(1..4094)
    MAX-ACCESS   read-create
    STATUS       current
    DESCRIPTION  "The end of the range of customer VLAN IDs. To specify a single
                  C-VLAN ID, this value should be equal to pvxPCVRTCVlanFrom. This
                  value may never be smaller than pvxPCVRTCVlanFrom."
    ::= { pvxPbCVidRegistrationTableEntry 2 }


pvxPCVRTSVlanId OBJECT-TYPE
    SYNTAX       INTEGER(1..4094)
    MAX-ACCESS   read-create
    STATUS       current
    DESCRIPTION  "The S-VLAN that the system will assign to any packets that it
                  forwards from this port that had any of the C-VLAN ids in the
                  range pvxPCVRTCVlanIdFrom..pvxPCVRTCVlanIdTo"
    ::= { pvxPbCVidRegistrationTableEntry 3 }

pvxPCVRTUntaggedPEP OBJECT-TYPE
    SYNTAX       TruthValue
    MAX-ACCESS   read-create
    STATUS       current
    DESCRIPTION  "A boolean indicating frames for this specified Customer VLAN 
                  identifier ingress at this specified Customer Edge Port (CEP)
                  should be forwarded untagged through the Provider Edge Port
                  (PEP). 
                  When it is set to 'True' the C-VLAN tag will be stripped. Otherwise
                  the packet will be sent out with a C-tag and with valid C-VID."
    ::= { pvxPbCVidRegistrationTableEntry 4 }

pvxPCVRTUntaggedCEP OBJECT-TYPE
    SYNTAX       TruthValue
    MAX-ACCESS   read-create
    STATUS       current
    DESCRIPTION  "A boolean indicating frames for this specified Customer VLAN 
                  identifier should be forwarded untagged through this specified
                  Customer Edge Port (CEP).
                  When it is set to 'True' the C-VLAN tag will be stripped. Otherwise 
                  the tag will be added if the packet is C-VLAN untagged."
    ::= { pvxPbCVidRegistrationTableEntry 5 }

pvxPCVRTSource OBJECT-TYPE
    SYNTAX       INTEGER { manualCreate (1),
                           autoCreate (2) }
    MAX-ACCESS   read-only
    STATUS       current
    DESCRIPTION  ""
    ::= { pvxPbCVidRegistrationTableEntry 6 }

pvxPCVRTMapOperStatus   OBJECT-TYPE
    SYNTAX       PvxCVidMapOperStatus
    MAX-ACCESS   read-only
    STATUS       current
    DESCRIPTION  ""
    ::= { pvxPbCVidRegistrationTableEntry 7 }

pvxPCVRTXlateOperStatus   OBJECT-TYPE
    SYNTAX       PvxCVidMapOperStatus
    MAX-ACCESS   read-only
    STATUS       current
    DESCRIPTION  ""
    ::= { pvxPbCVidRegistrationTableEntry 8 } 

pvxPCVRTRowStatus OBJECT-TYPE
    SYNTAX       RowStatus
    MAX-ACCESS   read-create
    STATUS       current
    DESCRIPTION  "This object is used to create or delete a new row in the 
                  pvxPbCVidRegistrationTable."
    ::= { pvxPbCVidRegistrationTableEntry 100 }

-----------------------------------------------------------------------
-- pvxEthServiceTable
-----------------------------------------------------------------------
pvxEthServiceTable OBJECT-TYPE
    SYNTAX       SEQUENCE OF PvxEthServiceEntry
    MAX-ACCESS   not-accessible
    STATUS       current
    DESCRIPTION  "This table is used to configure services on all the switches in
                  the chassis."
    ::= { pvxBridgeServices 18 }

pvxEthServiceEntry OBJECT-TYPE
    SYNTAX       PvxEthServiceEntry
    MAX-ACCESS   not-accessible
    STATUS       current
    DESCRIPTION  "The conceptual row object of the Ethernet Service table.
                  
                 Note the pvxEthSrvcName index is a variable length OCTET STRING
                 object. When encoded as part of the index, it 
                 includes the string length as part of the instance.

                 For example, a service named 'aaa' is encoded as '3.61.61.61'.

                 For more info on encoding OCTET STRING instances in OID's, 
                 see RFC-2578, section 7.7.
                 "
    INDEX        { pvxEthSrvcSwitchIdx,
                   pvxEthSrvcName }
    ::= { pvxEthServiceTable 1 }

PvxEthServiceEntry ::= SEQUENCE { pvxEthSrvcSwitchIdx        INTEGER,
                                  pvxEthSrvcName             DisplayString,
                                  pvxEthSrvcType             INTEGER,
                                  pvxEthSrvcState            INTEGER,
                                  pvxEthSrvcOperState        OperStatus,
                                  pvxEthSrvcTransportType    INTEGER,
                                  pvxEthSrvcSVLAN            PvxVlanId,
                                  pvxEthSrvcSpanTreeInstance INTEGER,
                                  pvxEthSrvcMaxUNIs          Integer32,
                                  pvxEthSrvcNumUNIs          Integer32,
                                  pvxEthSrvcPointedness      INTEGER,
                                  pvxEthSrvcFrameSize        INTEGER,
                                  pvxEthSrvcCVidXlate        TruthValue,
                                  pvxEthSrvcMECciInterval    INTEGER,
                                  pvxEthSrvcMECciEnable      TruthValue,
                                  pvxEthSrvcMEName           DisplayString,
                                  pvxEthSrvcMaxNNIs          Integer32,
                                  pvxEthSrvcNumNNIs          Integer32,
                                  pvxEthSrvcLockNNIs         TruthValue,
                                  pvxEthSrvcExceedMaxUNI     TruthValue,
                                  pvxEthSrvcAccess           TruthValue,
                                  pvxEthSrvcRowStatus        RowStatus }

pvxEthSrvcSwitchIdx OBJECT-TYPE
   	SYNTAX       INTEGER(1..11)
   	MAX-ACCESS   not-accessible
   	STATUS       current
   	DESCRIPTION  "This object represents the particular switch id."
    ::= {pvxEthServiceEntry 1 }

pvxEthSrvcName OBJECT-TYPE
   	SYNTAX       DisplayString (SIZE(1..32))
   	MAX-ACCESS   not-accessible
   	STATUS       current
   	DESCRIPTION  "The name of the service."
    ::= {pvxEthServiceEntry 2 }

pvxEthSrvcType OBJECT-TYPE
   	SYNTAX       INTEGER { epline         (1),
                           evpline        (2),
                           eplan          (3),
                           evplan         (4),
                           erps           (5),
                           igmp           (6),
                           managementVLAN (7),
			   eptree         (8),
			   evptree        (9)
                         }
   	MAX-ACCESS   read-create
   	STATUS       current
   	DESCRIPTION  "This object represents the particular service type. This object
                      must be specifyed during row creation and cannot be changed."
    ::= {pvxEthServiceEntry 3 }

pvxEthSrvcState OBJECT-TYPE
   	SYNTAX       INTEGER { enable  (1),
                           disable (2),
						   testing (3)
						 }
   	MAX-ACCESS   read-create
   	STATUS       current
   	DESCRIPTION  "Is this service administratively enabled or disabled?"
    DEFVAL       { enable }
    ::= {pvxEthServiceEntry 4 }

pvxEthSrvcOperState OBJECT-TYPE
   	SYNTAX       OperStatus
   	MAX-ACCESS   read-only 
   	STATUS       current
   	DESCRIPTION  "The current operational state of the service."
    ::= {pvxEthServiceEntry 5 }

pvxEthSrvcTransportType OBJECT-TYPE
   	SYNTAX       INTEGER { providerBridge (1),
                               none           (2) }
   	MAX-ACCESS   read-only
   	STATUS       current
   	DESCRIPTION  "For future compatibily; describes the transport mechanism
                  for this service. For the current release we only support
                  providerBridge IEEE802.1ad transport."
    ::= {pvxEthServiceEntry 6 }

pvxEthSrvcSVLAN OBJECT-TYPE
   	SYNTAX       PvxVlanId
   	MAX-ACCESS   read-create
   	STATUS       current
   	DESCRIPTION  "If no value is specified in the row create request, the value 
                  defaults to the current reserved SVLAN value."
    ::= {pvxEthServiceEntry 7 }

pvxEthSrvcSpanTreeInstance OBJECT-TYPE
   	SYNTAX       INTEGER(0..16) 
   	MAX-ACCESS   read-create
   	STATUS       current
   	DESCRIPTION  "The spanning tree instance for this service. Default is 0"
        DEFVAL       { 0 }
    ::= {pvxEthServiceEntry 8 }

pvxEthSrvcMaxUNIs OBJECT-TYPE
   	SYNTAX       Integer32
   	MAX-ACCESS   read-only
   	STATUS       current
   	DESCRIPTION  "The maximum number of UNIs that can be associated with
                  this Service. This value is derived from the ServiceType"
    ::= {pvxEthServiceEntry 9 }

pvxEthSrvcNumUNIs OBJECT-TYPE
   	SYNTAX       Integer32
   	MAX-ACCESS   read-only
   	STATUS       current
   	DESCRIPTION  "The number of UNIs currently associated with the Service."
    ::= {pvxEthServiceEntry 10 }

pvxEthSrvcPointedness OBJECT-TYPE
   	SYNTAX       INTEGER { pointToPoint (1),
                           multiPoint   (2),
                           internal     (3),
                           ring         (4)
                         }
   	MAX-ACCESS   read-only
   	STATUS       current
   	DESCRIPTION  "Is this a point-to-point or multipoint service"
    ::= {pvxEthServiceEntry 11 }

pvxEthSrvcFrameSize OBJECT-TYPE
   	SYNTAX       INTEGER (1518..9600)
   	MAX-ACCESS   read-create
   	STATUS       current
   	DESCRIPTION  "The maximum size of a frame transported on this service."
        DEFVAL       { 1522 }
    ::= {pvxEthServiceEntry 12 }

pvxEthSrvcCVidXlate OBJECT-TYPE
   	SYNTAX       TruthValue 
   	MAX-ACCESS   read-create
   	STATUS       current
   	DESCRIPTION  "Do we translate the C-VID on this service? Can
                  only be true if all UNIs have a single C-VID 
                  mapped to this service."
    ::= {pvxEthServiceEntry 13 }

pvxEthSrvcMECciInterval OBJECT-TYPE 
	 SYNTAX INTEGER {
                  intervalInvalid   (1),
                  interval300Hz     (2),
                  interval10ms      (3),
                  interval100ms     (4),
                  interval1s        (5),
                  interval10s       (6),
                  interval1min      (7),
                  interval10min     (8)
                }
                    
	 MAX-ACCESS read-create
	 STATUS current
	 DESCRIPTION "Indicates the interval at which CCMs are sent by a MEP.
        The possible values are:
        intervalInvalid(0) No CCMs are sent (disabled).
        interval300Hz(1)   CCMs are sent every 3 1/3 milliseconds
                           (300Hz).
        interval10ms(2)    CCMs are sent every 10 milliseconds.
        interval100ms(3)   CCMs are sent every 100 milliseconds.
        interval1s(4)      CCMs are sent every 1 second.
        interval10s(5)     CCMs are sent every 10 seconds.
        interval1min(6)    CCMs are sent every minute.
        interval10min(7)   CCMs are sent every 10 minutes.
	 Default value is set to interval1s by the system. "
 	::= { pvxEthServiceEntry 14  }

pvxEthSrvcMECciEnable OBJECT-TYPE
    SYNTAX      TruthValue
    MAX-ACCESS  read-create
    STATUS      current
    DESCRIPTION  "If set to true, the MEP will generate CCM messages. 
                  Default is set to false by the system."
::= { pvxEthServiceEntry 15  }

pvxEthSrvcMEName OBJECT-TYPE
    SYNTAX       DisplayString (SIZE(1..6))
    MAX-ACCESS   read-create
    STATUS       current
    DESCRIPTION  "Name of the EVC Maintanence Entity. Maximum length is 6 characters."
    ::= { pvxEthServiceEntry 16 }

pvxEthSrvcMaxNNIs OBJECT-TYPE
   	SYNTAX       Integer32
   	MAX-ACCESS   read-only
   	STATUS       current
   	DESCRIPTION  "The maximum number of NNIs that can be associated with
                  this Service. This value is derived from the ServiceType"
    ::= {pvxEthServiceEntry 17 }

pvxEthSrvcNumNNIs OBJECT-TYPE
   	SYNTAX       Integer32
   	MAX-ACCESS   read-only
   	STATUS       current
   	DESCRIPTION  "The number of NNIs currently associated with the Service."
    ::= {pvxEthServiceEntry 18 }
    
pvxEthSrvcLockNNIs OBJECT-TYPE
    SYNTAX      TruthValue
    MAX-ACCESS  read-create
    STATUS      current
    DESCRIPTION  "If true, the switch will not let any dynamic VLAN protocols, 
                  such as GVRP, add NNIs to the Service."
::= { pvxEthServiceEntry 19  }

pvxEthSrvcExceedMaxUNI OBJECT-TYPE
    SYNTAX      TruthValue
    MAX-ACCESS  read-only
    STATUS      current
    DESCRIPTION  "This attribute is used to indicate the error condition that the 
                  maximum number of NUIs has exceeded for EPLINE or EVPLINE."
::= { pvxEthServiceEntry 20  }

pvxEthSrvcAccess OBJECT-TYPE
    SYNTAX      TruthValue
    MAX-ACCESS  read-create
    STATUS      current
    DESCRIPTION  "A boolean vlaue to indicate the ethernet service is an Access services 
                  carring Operator Virtual Connections(OVC). A value of true is set for
                  ACCESS services."
    DEFVAL      { false }
::= { pvxEthServiceEntry 21  }

pvxEthSrvcRowStatus OBJECT-TYPE
   	SYNTAX       RowStatus
   	MAX-ACCESS   read-create
   	STATUS       current
   	DESCRIPTION  ""
    ::= { pvxEthServiceEntry 100 }


-----------------------------------------------------------------------
-- pvxServiceUNITable
-----------------------------------------------------------------------
pvxServiceUNITable OBJECT-TYPE
    SYNTAX       SEQUENCE OF PvxServiceUNIEntry
    MAX-ACCESS   not-accessible
    STATUS       current
    DESCRIPTION  "This table binds a UNI to a service and describes the configuration
                  of the UNI-service combination."
    ::= { pvxBridgeServices 19 }

pvxServiceUNIEntry OBJECT-TYPE
    SYNTAX       PvxServiceUNIEntry
    MAX-ACCESS   not-accessible
    STATUS       current
    DESCRIPTION  "The conceptual row object of the Service UNI table.
                  
                 Note the pvxSrvcUNISrvcName index is a variable length OCTET STRING
                 object. When encoded as part of the Service UNI index, it 
                 includes the string length as part of the instance.

                 For example, a service named 'aaa' is encoded as '3.61.61.61'.

                 For more info on encoding OCTET STRING instances in OID's, 
                 see RFC-2578, section 7.7.
                 "
    INDEX        { pvxSrvcUNISwitchId,
                   pvxSrvcUNIShelfId,
                   pvxSrvcUNISlotId,
                   pvxSrvcUNIPortTypeId,
                   pvxSrvcUNIPortId,
                   pvxSrvcUNISrvcName
                 }
    ::= { pvxServiceUNITable 1 }

PvxServiceUNIEntry ::= SEQUENCE { pvxSrvcUNISwitchId         INTEGER,
                                  pvxSrvcUNIShelfId          INTEGER,
                                  pvxSrvcUNISlotId           INTEGER,
                                  pvxSrvcUNIPortTypeId       PvxPortType,
                                  pvxSrvcUNIPortId           Integer32,
                                  pvxSrvcUNISrvcName         DisplayString,
                                  pvxSrvcUNINumCVids         Integer32,
                                  pvxSrvcUNIIngressBW        DisplayString,
                                  pvxSrvcUNIIngressBWperCos  DisplayString,
                                  pvxSrvcUNIEgressBW         DisplayString,
                                  pvxSrvcUNIEgressBWperCos   DisplayString,
                                  pvxSrvcUNIUserDefinedMepId INTEGER,
				                  pvxSrvcUNIForwarding       INTEGER,
                                  pvxSrvcUNIServiceMap       DisplayString,
				                  pvxSrvcUNIFilterSequence   INTEGER,
				                  pvxSrvcUNIEFPSDEnabled     TruthValue,
				                  pvxSrvcUNIEFPSDLocalEFPSDState     TruthValue,
				                  pvxSrvcUNISlaMeasurementProfile    DisplayString,
                                  pvxSrvcUNITpidAwareOrBlind INTEGER,
                                  pvxSrvcUNIRowStatus        RowStatus }
 
pvxSrvcUNISwitchId   OBJECT-TYPE
   	SYNTAX       INTEGER(1..11)
   	MAX-ACCESS   not-accessible
   	STATUS       current
   	DESCRIPTION  "This object represents the particular switch id."
    ::= { pvxServiceUNIEntry 1 }

pvxSrvcUNIShelfId OBJECT-TYPE
        SYNTAX       INTEGER (0|1|11|21|31)
        MAX-ACCESS   not-accessible
        STATUS       current
        DESCRIPTION  ""
        ::= { pvxServiceUNIEntry 2 }

pvxSrvcUNISlotId OBJECT-TYPE
        SYNTAX       INTEGER (0|1|3|5|7|9|11|13|15|17|19)
        MAX-ACCESS   not-accessible
        STATUS       current
        DESCRIPTION  ""
        ::= { pvxServiceUNIEntry 3 }

pvxSrvcUNIPortTypeId OBJECT-TYPE
        SYNTAX       PvxPortType 
        MAX-ACCESS   not-accessible
        STATUS       current
        DESCRIPTION  ""
        ::= { pvxServiceUNIEntry 4 }

pvxSrvcUNIPortId OBJECT-TYPE
        SYNTAX  Integer32
        MAX-ACCESS   not-accessible
        STATUS       current
        DESCRIPTION  ""
        ::= { pvxServiceUNIEntry 5 }

pvxSrvcUNISrvcName OBJECT-TYPE
        SYNTAX       DisplayString (SIZE(1..32))
        MAX-ACCESS   not-accessible
        STATUS       current
        DESCRIPTION  "The name of the service."
        ::= { pvxServiceUNIEntry 6 }

pvxSrvcUNINumCVids OBJECT-TYPE
        SYNTAX       Integer32
        MAX-ACCESS   read-only
        STATUS       current
        DESCRIPTION  "The number of C-VIDs associated with this service on this
                      UNI."
        ::= { pvxServiceUNIEntry 7 }

pvxSrvcUNIIngressBW OBJECT-TYPE
        SYNTAX       DisplayString (SIZE(0..32))
        MAX-ACCESS   read-create
        STATUS       current
        DESCRIPTION  "The name of the profile thay specifies the ingress bandwidth 
                      for this service in this UNI."
        DEFVAL       {""}
        ::= { pvxServiceUNIEntry 8 }

pvxSrvcUNIIngressBWperCos OBJECT-TYPE
   	    SYNTAX       DisplayString (SIZE(0..32))
        MAX-ACCESS   read-create
        STATUS       current
        DESCRIPTION  "The name of the profile thay specifies the ingress bandwidth
                      per COS Id for this service in this UNI."
        DEFVAL       {""}
        ::= { pvxServiceUNIEntry 9 }

pvxSrvcUNIEgressBW OBJECT-TYPE
       	SYNTAX       DisplayString (SIZE(0..32))
       	MAX-ACCESS   read-create
       	STATUS       current
       	DESCRIPTION  "The name of the profile thay specifies the egress bandwidth 
                      for this service in this UNI."
        DEFVAL       {""}
        ::= { pvxServiceUNIEntry 10 }

pvxSrvcUNIEgressBWperCos OBJECT-TYPE
       	SYNTAX       DisplayString (SIZE(0..32))
        MAX-ACCESS   read-create
       	STATUS       current
   	DESCRIPTION  "The name of the profile thay specifies the egress bandwidth 
                      per COS Id for this service in this UNI."
        DEFVAL       {""}
        ::= { pvxServiceUNIEntry 11 }

pvxSrvcUNIUserDefinedMepId  OBJECT-TYPE
       	SYNTAX       INTEGER(0..8191)
        MAX-ACCESS   read-create
       	STATUS       current
   	DESCRIPTION  "If the value is zero, then the user has not set a MEP ID
                      for the Service UNI and one will be autogenerated by
                      the system. If the user wishes to manually configure a
                      MEP ID it must be in the range of 1 - 8191, inclusive."
        DEFVAL       {0}
        ::= { pvxServiceUNIEntry 12 }

pvxSrvcUNIForwarding OBJECT-TYPE
        SYNTAX       INTEGER { normal      (1),
	                       etree-leaf  (2)
			     }
	MAX-ACCESS   read-create
       	STATUS       current
	DESCRIPTION  "Forwarding specification applies only to E-Tree services.
                      It is an indication of whether a UNI is a Leaf port(etree-leaf) 
                      or a Root port(normal). The default value for all UNIs is etree-leaf.
                      For other eservices except E-tree, it's only shown as
                      normal and not configurable."
	DEFVAL       {2}
	::= { pvxServiceUNIEntry 13 }

pvxSrvcUNIServiceMap OBJECT-TYPE
       	SYNTAX       DisplayString (SIZE(0..32))
        MAX-ACCESS   read-create
       	STATUS       current
   	DESCRIPTION  "The name of the profile that specifies the service map 
                      filters for this service in this UNI."
        DEFVAL       {""}
        ::= { pvxServiceUNIEntry 14 }

pvxSrvcUNIFilterSequence  OBJECT-TYPE
       	SYNTAX       INTEGER(1..100)
        MAX-ACCESS   read-create
       	STATUS       current
   	DESCRIPTION  "A numerical value used to order service map filter evaluation
                      on a UNI. Lower values are evaluated before higher values"
        DEFVAL       {50}
        ::= { pvxServiceUNIEntry 15 }

pvxSrvcUNIEFPSDEnabled  OBJECT-TYPE
       	SYNTAX       TruthValue
        MAX-ACCESS   read-create
       	STATUS       current
   	DESCRIPTION  "Indicates if Ethernet Fault Propagation Shut Down (EFPSD) feature
		      is enabled on this service UNI."
        DEFVAL       {false}
        ::= { pvxServiceUNIEntry 16 }

pvxSrvcUNIEFPSDLocalEFPSDState  OBJECT-TYPE
       	SYNTAX       TruthValue
        MAX-ACCESS   read-only
       	STATUS       current
   	DESCRIPTION  "For service UNIs with EFPSD enabled, indicates if EFPSD is currently
		      engaged on the local UNI. If EFPSD is engaged, the transmitter on the UNI
		      is off."
        ::= { pvxServiceUNIEntry 17 }

pvxSrvcUNISlaMeasurementProfile OBJECT-TYPE
       	SYNTAX       DisplayString (SIZE(0..32))
        MAX-ACCESS   read-create
       	STATUS       current
   	DESCRIPTION  "The name of the profile that specifies the SLA mesaurement thresholds
   	             for this service in this UNI."
        DEFVAL       {""}
        ::= { pvxServiceUNIEntry 18 }

pvxSrvcUNITpidAwareOrBlind OBJECT-TYPE
        SYNTAX       INTEGER { aware      (1),
	                           blind      (2),
	                           none       (3)}
        MAX-ACCESS   read-create
       	STATUS       current
        DESCRIPTION  "TPID blind specification applies only to EPLINE or EPLAN services.
                      It is an indication of whether a EPLINE/EPLAN is transparent for all 
                      the custome pacekts. The default value is TPID none."
        DEFVAL       {3}
        ::= { pvxServiceUNIEntry 19 }
       
pvxSrvcUNIRowStatus OBJECT-TYPE
        SYNTAX       RowStatus
       	MAX-ACCESS   read-create
       	STATUS       current
       	DESCRIPTION  ""
        ::= { pvxServiceUNIEntry 100 }  


-----------------------------------------------------------------------
-- pvxSvidXlateTable
-----------------------------------------------------------------------
pvxSvidXlateTable OBJECT-TYPE
        SYNTAX       SEQUENCE OF PvxSvidXlateEntry
        MAX-ACCESS   not-accessible
        STATUS       current
        DESCRIPTION  "This table defines all User Network Interfaces on all switches."
        ::= { pvxBridgeServices 20 }

pvxSvidXlateEntry OBJECT-TYPE
        SYNTAX       PvxSvidXlateEntry
        MAX-ACCESS   not-accessible
        STATUS       current
        DESCRIPTION  "The conceptual row object of the SvidXlate Table"
        INDEX        { pvxSvidXlateSwitchId,
                       pvxSvidXlateShelfId,
                       pvxSvidXlateSlotId,
                       pvxSvidXlatePortTypeId,
                       pvxSvidXlatePortId,
                       pvxSvidXlateInternalSVid }
        ::= { pvxSvidXlateTable 1 }

PvxSvidXlateEntry ::= SEQUENCE { pvxSvidXlateSwitchId       INTEGER,
                                 pvxSvidXlateShelfId        INTEGER,
                                 pvxSvidXlateSlotId         INTEGER,
                                 pvxSvidXlatePortTypeId     PvxPortType,
                                 pvxSvidXlatePortId         Integer32,
                                 pvxSvidXlateInternalSVid   PvxVlanId,
                                 pvxSvidXlateExternalSVid   PvxVlanId,
                                 pvxSvidXlateRowStatus      RowStatus }

 pvxSvidXlateSwitchId   OBJECT-TYPE
        SYNTAX       INTEGER(1..11)
      	MAX-ACCESS   not-accessible
   	    STATUS       current
       	DESCRIPTION  "This object represents the particular switch id."
        ::= { pvxSvidXlateEntry 1 }

pvxSvidXlateShelfId OBJECT-TYPE
        SYNTAX       INTEGER (0|1|11|21|31)
        MAX-ACCESS   not-accessible
        STATUS       current
        DESCRIPTION  ""
        ::= { pvxSvidXlateEntry 2 }

pvxSvidXlateSlotId OBJECT-TYPE
        SYNTAX       INTEGER (0|1|3|5|7|9|11|13|15|17|19)
        MAX-ACCESS   not-accessible
        STATUS       current
        DESCRIPTION  ""
        ::= { pvxSvidXlateEntry 3 }

pvxSvidXlatePortTypeId OBJECT-TYPE
        SYNTAX       PvxPortType 
        MAX-ACCESS   not-accessible
        STATUS       current
        DESCRIPTION  ""
        ::= { pvxSvidXlateEntry 4 }

pvxSvidXlatePortId OBJECT-TYPE
        SYNTAX  Integer32
        MAX-ACCESS   not-accessible
        STATUS       current
        DESCRIPTION  ""
        ::= { pvxSvidXlateEntry 5 }

pvxSvidXlateInternalSVid OBJECT-TYPE
        SYNTAX       PvxVlanId
        MAX-ACCESS   not-accessible
        STATUS       current
        DESCRIPTION  ""
        ::= { pvxSvidXlateEntry 6 }

pvxSvidXlateExternalSVid OBJECT-TYPE
        SYNTAX       PvxVlanId
        MAX-ACCESS   read-write
        STATUS       current
        DESCRIPTION  ""
        ::= { pvxSvidXlateEntry 7 }

pvxSvidXlateRowStatus OBJECT-TYPE
        SYNTAX       RowStatus
       	MAX-ACCESS   read-create
       	STATUS       current
       	DESCRIPTION  ""
        ::= { pvxSvidXlateEntry 100 }  

-----------------------------------------------------------------------
-- pvxMgmtVLANTable
-----------------------------------------------------------------------

pvxMgmtVLANTable OBJECT-TYPE
    SYNTAX       SEQUENCE OF PvxMgmtVLANEntry
    MAX-ACCESS   not-accessible
    STATUS       current
    DESCRIPTION  "This table describes the Management VLAN service for the switch." 
    ::= { pvxBridgeServices 22 }


pvxMgmtVLANEntry OBJECT-TYPE
    SYNTAX       PvxMgmtVLANEntry
    MAX-ACCESS   not-accessible
    STATUS       current
    DESCRIPTION  "A row in the Management VLAN Table. Note that in Provider Bridge
                  mode, a row in this table is auto-created by adding an entry in
                  the pvxEthServiceTable. You cannot create the row directly. "
    INDEX    { 
              pvxMgmtVLANSwitchIdx,
              pvxMgmtVLANSrvcName
             }
    ::= { pvxMgmtVLANTable 1 }

PvxMgmtVLANEntry ::= SEQUENCE { pvxMgmtVLANSwitchIdx      INTEGER,
                                pvxMgmtVLANSrvcName       DisplayString,
                                pvxMgmtVLANBWProfileName  DisplayString,
                                pvxMgmtVLANCVLANId        INTEGER,
                                pvxMgmtVLANAddressType    InetAddressType,
                                pvxMgmtVLANIpAddress      InetAddress,
                                pvxMgmtVLANNetMask        InetAddress,
                                pvxMgmtVLANDebugMode      TruthValue,
                                pvxMgmtVLANRowStatus      RowStatus }


pvxMgmtVLANSwitchIdx  OBJECT-TYPE
     SYNTAX       INTEGER(1..11)
     MAX-ACCESS   not-accessible
     STATUS       current
     DESCRIPTION  "This object represents the switch on which this Mgmt VLAN runs."
     ::= { pvxMgmtVLANEntry 1 }


pvxMgmtVLANSrvcName    OBJECT-TYPE
     SYNTAX       DisplayString
     MAX-ACCESS   not-accessible
     STATUS       current
     DESCRIPTION  "This is the name of the Mgmt VLAN service. A corresponding
                   entry with this name is in the pvxEthServicesTable"
     ::= { pvxMgmtVLANEntry 2 }


pvxMgmtVLANBWProfileName  OBJECT-TYPE
     SYNTAX        DisplayString
     MAX-ACCESS    read-create
     STATUS        current
     DESCRIPTION  "The name of the bandwidth profile that applies to the management VLAN.
                   Does not apply in provider bridge mode."
     ::= { pvxMgmtVLANEntry 3 }


pvxMgmtVLANCVLANId  OBJECT-TYPE
     SYNTAX        INTEGER(0..4095)
     MAX-ACCESS    read-create
     STATUS        current
     DESCRIPTION  "The Customer VLAN ID with which packets will be tagged when
                   sent on the Mgmt VLAN. If 0, no CVLAN tagging will occur."
     ::= { pvxMgmtVLANEntry 4 }


pvxMgmtVLANAddressType  OBJECT-TYPE
     SYNTAX        InetAddressType
     MAX-ACCESS    read-create
     STATUS        current
     DESCRIPTION  "The type of addresses (v4/v6) used in this row of
                   this MIB. Currently only ipv4 is allowed in this table."
     ::= { pvxMgmtVLANEntry 5 }

pvxMgmtVLANIpAddress  OBJECT-TYPE
     SYNTAX        InetAddress
     MAX-ACCESS    read-create
     STATUS        current
     DESCRIPTION  "The IP Address associated with this interface."
     ::= { pvxMgmtVLANEntry 6 }

pvxMgmtVLANNetMask  OBJECT-TYPE
     SYNTAX        InetAddress
     MAX-ACCESS    read-create
     STATUS        current
     DESCRIPTION  "The sub-net mask associated with this interface."
     ::= { pvxMgmtVLANEntry 7 }

pvxMgmtVLANDebugMode  OBJECT-TYPE
     SYNTAX        TruthValue
     MAX-ACCESS    read-create
     STATUS        current
     DESCRIPTION  "Debug Mode for Management VLAN, defaulted to off"
     ::= { pvxMgmtVLANEntry 8 }


pvxMgmtVLANRowStatus OBJECT-TYPE
    SYNTAX       RowStatus
    MAX-ACCESS   read-create
    STATUS       current
    DESCRIPTION  "This object is used to create a new row in the MgmtVLAN table."
    ::= { pvxMgmtVLANEntry 100 }

-----------------------------------------------------------------------
-- pvxServiceNNITable
-----------------------------------------------------------------------
pvxServiceNNITable OBJECT-TYPE
    SYNTAX       SEQUENCE OF PvxServiceNNIEntry
    MAX-ACCESS   not-accessible
    STATUS       current
    DESCRIPTION  "This table binds a NNI to a service and describes the configuration
                  of the NNI-service combination."
    ::= { pvxBridgeServices 23 }

pvxServiceNNIEntry OBJECT-TYPE
    SYNTAX       PvxServiceNNIEntry
    MAX-ACCESS   not-accessible
    STATUS       current
    DESCRIPTION  "The conceptual row object of the Service NNI table.
                  
                 Note the pvxSrvcNNISrvcName index is a variable length OCTET STRING
                 object. When encoded as part of the Service NNI index, it 
                 includes the string length as part of the instance.

                 For example, a service named 'aaa' is encoded as '3.61.61.61'.

                 For more info on encoding OCTET STRING instances in OID's, 
                 see RFC-2578, section 7.7.
                 "
    INDEX        { pvxSrvcNNISwitchId,
                   pvxSrvcNNIShelfId,
                   pvxSrvcNNISlotId,
                   pvxSrvcNNIPortTypeId,
                   pvxSrvcNNIPortId,
                   pvxSrvcNNISrvcName
                 }
    ::= { pvxServiceNNITable 1 }

PvxServiceNNIEntry ::= SEQUENCE { pvxSrvcNNISwitchId         INTEGER,
                                  pvxSrvcNNIShelfId          INTEGER,
                                  pvxSrvcNNISlotId           INTEGER,
                                  pvxSrvcNNIPortTypeId       PvxPortType,
                                  pvxSrvcNNIPortId           Integer32,
                                  pvxSrvcNNISrvcName         DisplayString,
                                  pvxSrvcNNIIngressBW        DisplayString,
                                  pvxSrvcNNIIngressBWperCos  DisplayString,
                                  pvxSrvcNNIEgressBW         DisplayString,
                                  pvxSrvcNNIEgressBWperCos   DisplayString,
                                  pvxSrvcNNIXlateSVLAN       PvxVlanIdOrZero,
                                  pvxSrvcNNIRowStatus        RowStatus }
 
pvxSrvcNNISwitchId   OBJECT-TYPE
   	SYNTAX       INTEGER(1..11)
   	MAX-ACCESS   not-accessible
   	STATUS       current
   	DESCRIPTION  "This object represents the particular switch id."
    ::= { pvxServiceNNIEntry 1 }

pvxSrvcNNIShelfId OBJECT-TYPE
        SYNTAX       INTEGER (0|1|11|21|31)
        MAX-ACCESS   not-accessible
        STATUS       current
        DESCRIPTION  ""
        ::= { pvxServiceNNIEntry 2 }

pvxSrvcNNISlotId OBJECT-TYPE
        SYNTAX       INTEGER (0|1|3|5|7|9|11|13|15|17|19)
        MAX-ACCESS   not-accessible
        STATUS       current
        DESCRIPTION  ""
        ::= { pvxServiceNNIEntry 3 }

pvxSrvcNNIPortTypeId OBJECT-TYPE
        SYNTAX       PvxPortType 
        MAX-ACCESS   not-accessible
        STATUS       current
        DESCRIPTION  ""
        ::= { pvxServiceNNIEntry 4 }

pvxSrvcNNIPortId OBJECT-TYPE
        SYNTAX  Integer32
        MAX-ACCESS   not-accessible
        STATUS       current
        DESCRIPTION  ""
        ::= { pvxServiceNNIEntry 5 }

pvxSrvcNNISrvcName OBJECT-TYPE
        SYNTAX       DisplayString (SIZE(1..32))
        MAX-ACCESS   not-accessible
        STATUS       current
        DESCRIPTION  "The name of the service."
        ::= { pvxServiceNNIEntry 6 }

pvxSrvcNNIIngressBW OBJECT-TYPE
        SYNTAX       DisplayString (SIZE(0..32))
        MAX-ACCESS   read-create
        STATUS       current
        DESCRIPTION  "The name of the profile thay specifies the ingress bandwidth 
                      for this service in this NNI."
        DEFVAL       {""}
        ::= { pvxServiceNNIEntry 8 }

pvxSrvcNNIIngressBWperCos OBJECT-TYPE
   	    SYNTAX       DisplayString (SIZE(0..32))
        MAX-ACCESS   read-create
        STATUS       current
        DESCRIPTION  "The name of the profile thay specifies the ingress bandwidth
                      per COS Id for this service in this NNI."
        DEFVAL       {""}
        ::= { pvxServiceNNIEntry 9 }

pvxSrvcNNIEgressBW OBJECT-TYPE
       	SYNTAX       DisplayString (SIZE(0..32))
       	MAX-ACCESS   read-create
       	STATUS       current
       	DESCRIPTION  "The name of the profile thay specifies the egress bandwidth 
                      for this service in this NNI."
        DEFVAL       {""}
        ::= { pvxServiceNNIEntry 10 }

pvxSrvcNNIEgressBWperCos OBJECT-TYPE
       	SYNTAX       DisplayString (SIZE(0..32))
   	    MAX-ACCESS   read-create
       	STATUS       current
   	    DESCRIPTION  "The name of the profile thay specifies the egress bandwidth 
                      per COS Id for this service in this NNI."
        DEFVAL       {""}
        ::= { pvxServiceNNIEntry 11 }

pvxSrvcNNIXlateSVLAN OBJECT-TYPE
       	SYNTAX       PvxVlanIdOrZero
   	    MAX-ACCESS   read-create
       	STATUS       current
   	    DESCRIPTION  "For ENNI ports on Access services, the VLAN ID that is translated
   	                  to/from for all frames on the ENNI wire. For NNI ports, this value
   	                  MUST be zero. For ENNI ports, the value defaults to zero and must be
   	                  set to a valid VLAN ID before the eservice can transmit or receive 
   	                  frames over the ENNI port. "
        DEFVAL       {0}
        ::= { pvxServiceNNIEntry 12 }

pvxSrvcNNIRowStatus OBJECT-TYPE
   	    SYNTAX       RowStatus
       	MAX-ACCESS   read-create
       	STATUS       current
       	DESCRIPTION  ""
        ::= { pvxServiceNNIEntry 100 }  


-----------------------------------------------------------------------
-- pvxERPSServiceNNITable
-----------------------------------------------------------------------
pvxERPSServiceNNITable OBJECT-TYPE
    SYNTAX       SEQUENCE OF PvxERPSServiceNNIEntry
    MAX-ACCESS   not-accessible
    STATUS       current
    DESCRIPTION  "This table provides configuration for an ERPS NNI."
    ::= { pvxBridgeServices 24 }

pvxERPSServiceNNIEntry OBJECT-TYPE
    SYNTAX       PvxERPSServiceNNIEntry
    MAX-ACCESS   not-accessible
    STATUS       current
    DESCRIPTION  "The conceptual row object of the ERPS Service NNI table."
    INDEX        { pvxERPSSrvcNNISwitchId,
                   pvxERPSSrvcNNIShelfId,
                   pvxERPSSrvcNNISlotId,
                   pvxERPSSrvcNNIPortTypeId,
                   pvxERPSSrvcNNIPortId
                 }
    ::= { pvxERPSServiceNNITable 1 }

PvxERPSServiceNNIEntry ::= SEQUENCE {
                 pvxERPSSrvcNNISwitchId         INTEGER,
                 pvxERPSSrvcNNIShelfId          INTEGER,
                 pvxERPSSrvcNNISlotId           INTEGER,
                 pvxERPSSrvcNNIPortTypeId       PvxPortType,
                 pvxERPSSrvcNNIPortId           Integer32,
                 pvxERPSSrvcNNIRingProtectLink  INTEGER,
                 pvxERPSSrvcNNIProtectionSwitch INTEGER,
                 pvxERPSSrvcNNIRingPortStatus   INTEGER,
                 pvxERPSSrvcNNISrvcName         DisplayString,
                 pvxERPSSrvcNNIRingPortId       INTEGER,
                 pvxERPSSrvcNNIMEName           DisplayString,
                 pvxERPSSrvcNNIRemoteMepId      INTEGER,
                 pvxERPSSrvcNNIECFMInfo         DisplayString,
                 pvxERPSSrvcNNILocalMepId       INTEGER,
                 pvxERPSSrvcNNINeighborPort     INTEGER,
		 pvxERPSSrvcNNINextNeighborPort INTEGER,
                 pvxERPSSrvcNNIFlushRemoteMEP   TruthValue,
                 pvxERPSSrvcNNICcmLinkDetection INTEGER
                 }
 
pvxERPSSrvcNNISwitchId   OBJECT-TYPE
   	SYNTAX       INTEGER(1..11)
   	MAX-ACCESS   not-accessible
   	STATUS       current
   	DESCRIPTION  "This object represents the particular switch id."
    ::= { pvxERPSServiceNNIEntry 1 }

pvxERPSSrvcNNIShelfId OBJECT-TYPE
        SYNTAX       INTEGER (0|1|11|21|31)
        MAX-ACCESS   not-accessible
        STATUS       current
        DESCRIPTION  "This object represents the particular shelf id."
        ::= { pvxERPSServiceNNIEntry 2 }

pvxERPSSrvcNNISlotId OBJECT-TYPE
        SYNTAX       INTEGER (0|1|3|5|7|9|11|13|15|17|19)
        MAX-ACCESS   not-accessible
        STATUS       current
        DESCRIPTION  "This object represents the particular slot id."
        ::= { pvxERPSServiceNNIEntry 3 }

pvxERPSSrvcNNIPortTypeId OBJECT-TYPE
        SYNTAX       PvxPortType 
        MAX-ACCESS   not-accessible
        STATUS       current
        DESCRIPTION  "This object represents the particular port type."
        ::= { pvxERPSServiceNNIEntry 4 }

pvxERPSSrvcNNIPortId OBJECT-TYPE
        SYNTAX  Integer32
        MAX-ACCESS   not-accessible
        STATUS       current
        DESCRIPTION  "This object represents the particular port id."
        ::= { pvxERPSServiceNNIEntry 5 }

pvxERPSSrvcNNIRingProtectLink OBJECT-TYPE
        SYNTAX       INTEGER { enable(1),
                               disable(2) }
        MAX-ACCESS   read-write
        STATUS       current
        DESCRIPTION  "This variable indicates whether this NNI is the protection link
                      for the ring.
                      When a port is configured as a RPL port, this node becomes
                      RPL Owner for the ring. The administrator has to ensure that
                      only one node in a ring is configured as RPL Owner."
        DEFVAL       { enable }
        ::= { pvxERPSServiceNNIEntry 6 }

pvxERPSSrvcNNIProtectionSwitch OBJECT-TYPE
        SYNTAX       INTEGER { enable(1),
                               disable(2) }
        MAX-ACCESS   read-write
        STATUS       current
        DESCRIPTION  "This object identifies the port that will be blocked by
                      enforcing forced or manual switching. Enabling this port
                      configures pvxERSPSrvcProtectionSwitchMode to operate
                      on this port. The pvxERPSSrvcProtectionSwitchMode must be
                      set to 'normal' in order to enable or disable
                      pvxERPSSrvcNNIProtectionSwitch on this port."
        DEFVAL       { enable }
        ::= { pvxERPSServiceNNIEntry 7 }

pvxERPSSrvcNNIRingPortStatus OBJECT-TYPE
   	    SYNTAX       INTEGER { blocked(1),
                               unblocked(2) }
        MAX-ACCESS   read-only
        STATUS       current
        DESCRIPTION  "This object indicates the port's current status updated by
                      the ERPS control process of this ring."
        ::= { pvxERPSServiceNNIEntry 8 }

pvxERPSSrvcNNISrvcName OBJECT-TYPE
       	SYNTAX       DisplayString (SIZE(1..32))
       	MAX-ACCESS   read-only
       	STATUS       current
       	DESCRIPTION  "The name of the ERPS service this port is part of."
        ::= { pvxERPSServiceNNIEntry 9 }

pvxERPSSrvcNNIRingPortId OBJECT-TYPE
       	SYNTAX       INTEGER { ringPort1 (1),
                               ringPort2 (2) }
   	    MAX-ACCESS   read-only
       	STATUS       current
   	    DESCRIPTION  "The designation of this port w.r.t. the ERPS ring."
        ::= { pvxERPSServiceNNIEntry 10 }

pvxERPSSrvcNNIMEName OBJECT-TYPE
       	SYNTAX       DisplayString (SIZE(1..6))
   	    MAX-ACCESS   read-write
       	STATUS       current
   	    DESCRIPTION  "The Maintanence Entity Name for the CCMs for this ERPS NNI.
	                  Maximum length is 6 characters."
        ::= { pvxERPSServiceNNIEntry 11 }

pvxERPSSrvcNNIRemoteMepId OBJECT-TYPE
       	SYNTAX       INTEGER (0..8191)
   	    MAX-ACCESS   read-write
       	STATUS       current
   	    DESCRIPTION  "The MEP Id of the remote end-point of the NNI. 0 indicates
                      that the value should be auto-discovered."
		DEFVAL       { 0 }
        ::= { pvxERPSServiceNNIEntry 12 }

pvxERPSSrvcNNIECFMInfo OBJECT-TYPE
       	SYNTAX       DisplayString (SIZE(1..127))
       	MAX-ACCESS   read-only
       	STATUS       current
       	DESCRIPTION  "The provisioned information about the ECMF entities in the ring."
        ::= { pvxERPSServiceNNIEntry 13 }

pvxERPSSrvcNNILocalMepId OBJECT-TYPE
       	SYNTAX       INTEGER (0..8191)
   	    MAX-ACCESS   read-write
       	STATUS       current
   	    DESCRIPTION  "The MEP Id of the local end-point of the NNI. 0 indicates
                      that the value should be auto-discovered."
		DEFVAL       { 0 }
        ::= { pvxERPSServiceNNIEntry 14 }

pvxERPSSrvcNNINeighborPort OBJECT-TYPE
    SYNTAX      INTEGER { enable(1), disable(2)}
    MAX-ACCESS  read-write
    STATUS      current
    DESCRIPTION "This object identifies the RPL Neighbor port of the ring.  When a\
                 port is configured as a RPL Neighbor port, that node becomes RPL Neighbor 
                 for that ring. [Reference : Section 10.1 of ITU-T G.8032 Y.1344 (03/2010)] 
                 Value '2' indicates that this ring port is not a RPL Neighbor port.  Both 
                 the RPL owner and RPL Neighbor node cannot be enabled at the same Ethernet 
                 Ring Node. Administrator has to ensure that, only one node in a ring is
                 configured as RPL Neighbor, and the node is adjacent to the RPL ."
    DEFVAL { 2}
    ::= { pvxERPSServiceNNIEntry 15 }

pvxERPSSrvcNNINextNeighborPort OBJECT-TYPE
    SYNTAX      INTEGER { enable(1), disable(2)}
    MAX-ACCESS  read-write
    STATUS      current
    DESCRIPTION "This object identifies the RPL Next Neighbor port of the ring.  When a port 
                 is configured as a RPL Next Neighbor port, that node becomes RPL Next Neighbor 
                 for that ring. [Reference : Section VIII.4 of ITU-T G.8032 Y.1344 (03/2010)] 
                 Value '2' indicates that this ring port is not a RPL Next Neighbor port.  
                 Both the RPL owner and RPL Next Neighbor node cannot be enabled at the same 
                 Ethernet Ring Node. Administrator has to ensure that, only nodes in a ring
                 which are adjacent to the RPL owner or RPL Neighbor node are configured as RPL
                 Next Neighbor Nodess."
    DEFVAL { 2}
    ::= { pvxERPSServiceNNIEntry 16 }

pvxERPSSrvcNNIFlushRemoteMEP   OBJECT-TYPE
    SYNTAX      TruthValue
    MAX-ACCESS  read-write
    STATUS      current
    DESCRIPTION  "A Boolean indicating whether the remote MEP needs to flush its MEP list or not
        True indicates that the remote MEP needs to flush and rebuild its MEP lists."
    DEFVAL       { false }
    ::= { pvxERPSServiceNNIEntry 17 }

pvxERPSSrvcNNICcmLinkDetection OBJECT-TYPE
    SYNTAX      INTEGER { enable(1), disable(2)}
    MAX-ACCESS  read-write
    STATUS      current
    DESCRIPTION "This object identifies the Link-state detection method for ERPS NNIs. If this
                 is set to 'Enable', CCMs are transmitted to the peer NNI, and the peer is 
                 expected to send back CCMs if it is enabled. Upon receipt of a CCM from the
                 peer, the ERPS link will go 'up'. If there is a physical link failure or CCMs
                 stop being received, the link will go 'down'. If this is set to 'Disable', 
                 link status will be based on physical link up or down."
    DEFVAL { 2}
    ::= { pvxERPSServiceNNIEntry 18 }



-----------------------------------------------------------------------
-- pvxERPSServiceTable
-----------------------------------------------------------------------

pvxERPSServiceTable OBJECT-TYPE
    SYNTAX       SEQUENCE OF PvxERPSServiceEntry
    MAX-ACCESS   not-accessible
    STATUS       current
    DESCRIPTION "This table is used to configure ERPS service on a particular
                 switch in the chassis."
    ::= { pvxBridgeServices 25 }

pvxERPSServiceEntry OBJECT-TYPE
    SYNTAX       PvxERPSServiceEntry
    MAX-ACCESS   not-accessible
    STATUS       current
    DESCRIPTION "The conceptual row object of the ERPS Service."
    INDEX        { pvxERPSSrvcSwitchIdx,
                   pvxERPSSrvcName
                 }
    ::= { pvxERPSServiceTable 1 }

PvxERPSServiceEntry ::= SEQUENCE {
                           pvxERPSSrvcSwitchIdx                    INTEGER,
                           pvxERPSSrvcName                         DisplayString,
                           pvxERPSSrvcRevertMode                   INTEGER,
                           pvxERPSSrvcProtectionSwitchMode         INTEGER,
                           pvxERPSSrvcHoldTimer                    Unsigned32,
                           pvxERPSSrvcWaitToRestoreTimer           Unsigned32,
                           pvxERPSSrvcGuardTimer                   Unsigned32,
                           pvxERPSSrvcPeriodicTimer                Unsigned32,
                           pvxERPSSrvcPropagateTC                  INTEGER,
                           pvxERPSSrvcNodeType                    INTEGER,
                           pvxERPSSrvcRingMonitoring              INTEGER,
                           pvxERPSSrvcRingProperty                INTEGER,
                           pvxERPSSrvcRingSemState                INTEGER,
                           pvxERPSSrvcRingNodeStatus              Integer32,
                           pvxERPSSrvcNumRingPorts                INTEGER,
                           pvxERPSSrvcSVLAN                       PvxVlanId,
                           pvxERPSSrvcVirtualLink                 PvxErpsVirtualLinkList,
                           pvxERPSSrvcWaitToBlockTimer            Unsigned32,
                           pvxERPSSrvcCompatibleVersion           INTEGER,
                           pvxERPSSrvcMultipleFailure             INTEGER,
                           pvxERPSSrvcSubRingWithoutVC            TruthValue,
                           pvxERPSSrvcDownMegLevel                INTEGER,
                           pvxERPSSrvcUpMegLevel                  INTEGER,
                           pvxERPSSrvcWTRRemaining                Unsigned32
                         }

pvxERPSSrvcSwitchIdx OBJECT-TYPE
       SYNTAX       INTEGER(1..11)
       MAX-ACCESS   not-accessible
       STATUS       current
       DESCRIPTION "This object represents the particular switch id."
       ::= { pvxERPSServiceEntry 1 }

pvxERPSSrvcName OBJECT-TYPE
       SYNTAX       DisplayString (SIZE(1..32))
       MAX-ACCESS   not-accessible
       STATUS       current
       DESCRIPTION "The name of the ERPS service."
       ::= { pvxERPSServiceEntry 2 }

pvxERPSSrvcRevertMode OBJECT-TYPE
       SYNTAX       INTEGER { revertive (1),
                              non-revertive (2) }
       MAX-ACCESS   read-write
       STATUS       current
       DESCRIPTION "This object identifies whether the ring is operating in
                     revertive or nonRevertive manner. In revertive mode of
                     operation, once the failed link recovers, the data path
                     will be switched back from protection path to working
                     path. In nonRevertive mode of operation, once the failed
                     link recovers, the recovered link port will remain blocked
                     state and the data still remains with the protection path."
       DEFVAL       { revertive }
       ::= { pvxERPSServiceEntry 3 }

pvxERPSSrvcProtectionSwitchMode OBJECT-TYPE
       SYNTAX       INTEGER { normalSwitch (1),
                              forceSwitch (2),
                              manualSwitch (3),
                              clear (4)}
       MAX-ACCESS   read-write
       STATUS       current
       DESCRIPTION "Before configuring this object with 'forceSwitch' or
                     'manualSwitch', pvxERPSSrvcNNIProtectionSwitch MUST be
                     enabled on one of the NNI ports.
                     When forcedSwitch is enabled on a ring, irrespective of
                     the status (Failed or not failed) of the NNI port, the
                     port will be blocked. If a link failure is present in the
                     ring, then setting the value as 'manualSwitch' will not be
                     allowed. Failure of the link in the ring will clear the
                     manual switch condition.
                     Force Switch is higher priority than the manual switch, as
                     such forceSwitch will overwrite the manual switch
                     configuration. Similarly manualSwitch will not be allowed,
                     when forceSwitch is enabled. 'normalSwitch' command will
                     clear the Manual/Force switch"
       DEFVAL       { normalSwitch }
     ::= { pvxERPSServiceEntry 4 }

pvxERPSSrvcHoldTimer OBJECT-TYPE
       SYNTAX       Unsigned32 (0..100)
       UNITS        "deciseconds"
       MAX-ACCESS   read-write
       STATUS       current
       DESCRIPTION "This object is used to configure the period for the hold
                     timer of this ring. Hold-Off timer will be started when a
                     new defect (SF) is received on this ring. This defect will
                     not be give as local SF to ERP control process until hold
                     timer expires. When the hold-off timer expires, and if a
                     local defect still exists it will be given as local SF to
                     the ERP control process of this ring."
       DEFVAL       { 0 }
       ::= { pvxERPSServiceEntry 5 }

pvxERPSSrvcWaitToRestoreTimer OBJECT-TYPE
       SYNTAX       Unsigned32 (20|300|360|420|480|540|600|660|720|780|840|900)
       UNITS        "seconds"
       MAX-ACCESS   read-write
       STATUS       current
       DESCRIPTION "This object is used to configure the period for the Wait to
                    restore timer. This object is applicable only if this ring
                    is operating in the revertive mode of operation. In the
                    revertive mode of operation, if this object is configured
                    with a value of '0', then the traffic is switched back to
                    the working entity from the protection entity immediately
                    upon recovery from failure of the working entity.
                    Value can be set to 20 seconds or any value between 
                    5 minutes (300) and 15 minutes (900) that is an even one minute
                    interval."
       DEFVAL       { 300 }
       ::= { pvxERPSServiceEntry 6 }

pvxERPSSrvcGuardTimer OBJECT-TYPE
       SYNTAX       Unsigned32 (0..200)
       UNITS        "centiseconds"
       MAX-ACCESS   read-write
       STATUS       current
       DESCRIPTION "This object is used to configure the period for the guard
                     timer of this ring. This timer is required to prevent
                     reception of outdated R-APS messages. Guard timer will be
                     started on reception of local clear SF event. R-APS messages
                     (except R-APS event messages) received on a ring when guard
                     timer is running, will be discarded."
       DEFVAL       { 50 }
       ::= { pvxERPSServiceEntry 7 }

pvxERPSSrvcPeriodicTimer OBJECT-TYPE
       SYNTAX       Unsigned32 (5..10)
       UNITS        "seconds"
       MAX-ACCESS   read-write
       STATUS       current
       DESCRIPTION "This object is used to configure the periodic timer. Periodic
                     timer is used to configure the transmission interval of R-APS
                     PDUs. Periodic timer is not valid for the first 3 R-APS PDU
                     transmission, that will be send on any change of R-APS
                     information."
       DEFVAL       { 5 }
       ::= { pvxERPSServiceEntry 8 }

pvxERPSSrvcPropagateTC OBJECT-TYPE
       SYNTAX       INTEGER { enable (1),
                              disable (2) }
       MAX-ACCESS   read-only
       STATUS       current
       DESCRIPTION "This object is used to Enable/Disable the Propagation of TC
                     in the associated rings, whenever the flush FDB is triggered
                     for this sub-ring. This configuration is applicable only
                     in the interconnecting nodes of the sub-ring"
       DEFVAL       { disable }
       ::= { pvxERPSServiceEntry 9 }

pvxERPSSrvcNodeType OBJECT-TYPE
       SYNTAX       INTEGER { rplOwner (1),
                              nonRplOwner (2) }
       MAX-ACCESS   read-only
       STATUS       current
       DESCRIPTION "This object identifies the node state of this ring node.
                     If one of the NNI is configured as the RPL, then this ring
                     node becomes 'rplOwner', otherwise the node remains as
                     'nonRplOwner'."
       ::= { pvxERPSServiceEntry 10 }

pvxERPSSrvcRingMonitoring OBJECT-TYPE
       SYNTAX       INTEGER { cfm (1),
                              local (2) }
       MAX-ACCESS   read-only
       STATUS       current
       DESCRIPTION "This attribute is the configurations related to the link
                     monitoring entities. The fault monitoring could be using
                     the Y.1731 mechanism or local detection mechanisms."
       ::= { pvxERPSServiceEntry 11 }

pvxERPSSrvcRingProperty OBJECT-TYPE
       SYNTAX       INTEGER { normal (1),
                              inter-connect (2) }
       MAX-ACCESS   read-write
       STATUS       current
       DESCRIPTION "This attributes indicates the ring property of the service.
                     The 'normal' ring propery indicates that this node supports
                     the regular ring properties for the service. The 'inter-connect'
                     ring property indicates that this nodes supports the 'sub-ring'
                     connectivity for this service"
       ::= { pvxERPSServiceEntry 12 }

pvxERPSSrvcRingSemState OBJECT-TYPE
       SYNTAX       INTEGER { disable (1),
                              idle (2),
                              protection (3),
                              manualswitch(4),
                              forcedswitch(5),
                              pending(6) }
       MAX-ACCESS   read-only
       STATUS       current
       DESCRIPTION "This object gives the node state as per the G.8032 state
                     event machine. During fault-free operation the state would
                     be in 'idle' state. Any fault condition on the ring network
                     would move this attribute into the protection state. If a manual 
                     switch is issued on any node in the ring the operation state of 
                     the ring would be manualswitch state.  If a force switch is issued
                     on any node in the ring the operation state of the ring would be
                     forcedswitch. Pending state occurs when a ring transition has 
                     occurred and the node is waiting for a timer to expire. "
       ::= {pvxERPSServiceEntry 13 }

pvxERPSSrvcRingNodeStatus OBJECT-TYPE
       SYNTAX       Integer32
       MAX-ACCESS   read-only
       STATUS       current
       DESCRIPTION  "A 32 bit mask giving the current status of the ring by
                     specifying the events/status currently present:
                            Bit 1  - Signal-failure on Ring Port 1
                            Bit 2  - Signal-failure on Ring Port 2
                            Bit 3  - Remote-signal-failure received on Ring Port 1
                            Bit 4  - Remote-signal-failure received on Ring Port 2
                            Bit 5  - Rpl-Blocked
                            Bit 6  - Wait-to-restore-timer-running
                            Bit 7  - Hold-timer-running
                            Bit 8  - Guard-timer-running
                    Value 1 of the bit signifies the presence of the event
                    associated with that bit and values zero signifies absence of
                    that event"
       ::= {pvxERPSServiceEntry 14 }

pvxERPSSrvcNumRingPorts OBJECT-TYPE
       SYNTAX       INTEGER (0..2)
       MAX-ACCESS   read-only
       STATUS       current
       DESCRIPTION "This attribute indicates the number of ring ports attached
                     to this ERPS service"
       ::= {pvxERPSServiceEntry 15 }

pvxERPSSrvcSVLAN OBJECT-TYPE
       SYNTAX       PvxVlanId
       MAX-ACCESS   read-only
       STATUS       current
       DESCRIPTION "VlanID associated with the Eservice"
       ::= {pvxERPSServiceEntry 16 }

pvxERPSSrvcVirtualLink  OBJECT-TYPE
    SYNTAX PvxErpsVirtualLinkList  
    MAX-ACCESS   read-write
    STATUS       current
	DESCRIPTION  "The set of VIRTUAL-LINKs (vlan-ids) associated with the ERPS Service"
    ::= { pvxERPSServiceEntry 17 }

pvxERPSSrvcWaitToBlockTimer OBJECT-TYPE
       SYNTAX       Unsigned32 (5500..7000)
       UNITS        "miliseconds"
       MAX-ACCESS   read-write
       STATUS       current
       DESCRIPTION " This object is used to configure the period for  Wait to Block
                     timer.  This object is effective, only when force switch or manual 
                     switch is configured in the ring and when clear command is issued
                     to recover the ring from force switch or manual switch.

                     The WTB timer is defined to be 5 seconds longer than the guard timer.
       	             The WTB timer has a period from 0 to 24 hour, configurable in units
                     of 1 millisecond. For example, to configure WTB timer  as 1 second
                     configure the value as 1000. "
       DEFVAL       { 5500 }
       ::= { pvxERPSServiceEntry 18}

pvxERPSSrvcCompatibleVersion OBJECT-TYPE
   SYNTAX      INTEGER { v1(1), v2(2)}
   MAX-ACCESS  read-write
   STATUS      current
   DESCRIPTION  "This is used to configure the compatible version number of the node in the ring.   
                 The ITU-T G.8032/Y.1344 (03//2010) standard states that the default compatible
                 version is version2. The default value is version2 (2). The version number can 
                 be modified only when the row status of the ring entry is in not in service."
   DEFVAL { v2}
   ::= { pvxERPSServiceEntry 19 }

pvxERPSSrvcMultipleFailure OBJECT-TYPE
   SYNTAX      INTEGER { disabled(1), primary(2)}
   MAX-ACCESS  read-write
   STATUS      current
   DESCRIPTION  "This object is configured in interconnection node of the sub-ring to
                support the feature 'Minimizing segmentation in interconnected rings'
                as per Appendix X of ITU-T G.8032/Y.1344 (03/2010) standard.

                Configured value of vxERPSSrvcMultipleFailure is used in Block Indication Logic Procedure
                as per Section X.3.2 in Appendix X of ITU-T G.8032/Y.1344 (03/2010) standard.
                Interconnected rings as described below :
                 a) If Loss of connectivity between the interconnection nodes is detected
                    and if the object pvxERPSSrvcMultipleFailure is configured as primary
                    then Local MS command is applied on the subring port else loss of connectivity
                    between the interconnection nodes is ignored.
                 b) Similarly when loss of connectivity between the interconnection nodes
                    is recovered and if the object pvxERPSSrvcInterconnectedNode is primary
                    then Local MS command on the subring port is cleared else recovery of 
                    connectivity between the interconnection nodes is ignored.

               This object is effective only when ring node is interconnection node.  The default
               value is disabled (1).  This object is applicable only when the compatible version is 2."
   DEFVAL { disabled }
   ::= { pvxERPSServiceEntry 20 }


pvxERPSSrvcSubRingWithoutVC OBJECT-TYPE
   SYNTAX      TruthValue
   MAX-ACCESS  read-write
   STATUS      current
   DESCRIPTION "This configuration helps to configure the sub-ring to run with or without an RAPS 
                Virtual Channel.
	
                When this object is set to 'false', the sub-ring is configured to run with a R-APS 
                Virtual Channel and both the traffic channel and the R-APS channel are blocked, when 
                the ring port is set to blocked state. When this object is set to 'true',the sub-ring 
                is configured to run without a R-APS Virtual Channel and the traffic channel is blocked
                but the R-APS channel is not blocked, when the ring port is set to blocked state
                [Reference : Section 10.1.14 of ITU-T G.8032 Y.1344 (03/2010)].

                Administrator has to ensure that, this object is configured to true only in the 
                nodes of a sub-ring.

               This object should be set to the same value (true/false) on all the nodes of the sub-ring. 
               This object is applicable only when the compatible version is 2. This object can be changed, 
               only when the rowstatus for this ring is not active."
    DEFVAL { false }
   ::= { pvxERPSServiceEntry 21}

pvxERPSSrvcDownMegLevel OBJECT-TYPE
    SYNTAX      INTEGER (0..6)
    MAX-ACCESS  read-write
    STATUS      current
    DESCRIPTION  "This object identifies the MEG level that will be used on CCM messages sent for 
                  DOWN MEPs for this ERPS eservice.   This object can only be modified if ERPS 
                  service is disabled "
    DEFVAL { 0}
    ::= { pvxERPSServiceEntry 22}

pvxERPSSrvcUpMegLevel OBJECT-TYPE
    SYNTAX      INTEGER (0..6)
    MAX-ACCESS  read-write
    STATUS      current
    DESCRIPTION  "This object identifies the MEG level that will be used on CCM messages sent 
                 for UP MEPs for this ERPS eservice.   This object can only be modified if ERPS 
                 service is disabled "
    DEFVAL { 1}
    ::= { pvxERPSServiceEntry 23}
 
 
pvxERPSSrvcWTRRemaining OBJECT-TYPE 
    SYNTAX       Unsigned32 
    MAX-ACCESS   read-only 
    STATUS       current 
    DESCRIPTION "The value of remain time of WTR timer if it's fired." 
    ::= { pvxERPSServiceEntry 24 } 


-----------------------------------------------------------------------
-- Bandwidth profile  Table
-----------------------------------------------------------------------
pvxBWProfileTable OBJECT-TYPE
    SYNTAX       SEQUENCE OF PVXBWProfileEntry
    MAX-ACCESS   not-accessible
    STATUS       current
    DESCRIPTION  ""
    ::= { pvxBridgeProfiles 1 }

pvxBWProfileEntry OBJECT-TYPE
    SYNTAX       PVXBWProfileEntry
    MAX-ACCESS   not-accessible
    STATUS       current
    DESCRIPTION  ""
    INDEX        { pvxBWPIdx }
    ::= { pvxBWProfileTable 1 }

PVXBWProfileEntry ::= SEQUENCE {	pvxBWPIdx	Integer32,
                              		pvxBWPCir       Integer32,  
                              		pvxBWPCbs       Integer32,
                              		pvxBWPEir       Integer32,
                              		pvxBWPEbs       Integer32,
                              		pvxBWPCoSQueue  Integer32,
                              		pvxBWPRowStatus RowStatus }

pvxBWPIdx OBJECT-TYPE
   	SYNTAX       Integer32 
   	MAX-ACCESS   not-accessible
   	STATUS       current
   	DESCRIPTION  ""
    ::= { pvxBWProfileEntry 1 }

pvxBWPCir OBJECT-TYPE
    SYNTAX       Integer32
    MAX-ACCESS   read-create
    STATUS       current
    DESCRIPTION  ""
    ::= { pvxBWProfileEntry 2 }

pvxBWPCbs OBJECT-TYPE
    SYNTAX       Integer32
    MAX-ACCESS   read-create
    STATUS       current
    DESCRIPTION  ""
    ::= { pvxBWProfileEntry 3 }

pvxBWPEir OBJECT-TYPE
    SYNTAX       Integer32
    MAX-ACCESS   read-create
    STATUS       current
    DESCRIPTION  ""
    ::= { pvxBWProfileEntry 4 }

pvxBWPEbs OBJECT-TYPE
    SYNTAX       Integer32
    MAX-ACCESS   read-create
    STATUS       current
    DESCRIPTION  ""
    ::= { pvxBWProfileEntry 5 }

pvxBWPCoSQueue OBJECT-TYPE
    SYNTAX       Integer32
    MAX-ACCESS   read-create
    STATUS       current
    DESCRIPTION  ""
    ::= { pvxBWProfileEntry 6 }
 
pvxBWPRowStatus OBJECT-TYPE
    SYNTAX       RowStatus
    MAX-ACCESS   read-create
    STATUS       current
    DESCRIPTION  ""
    ::= { pvxBWProfileEntry 100 }

-----------------------------------------------------------------------
-- Cos Table
-----------------------------------------------------------------------
pvxCoSProfileTable OBJECT-TYPE
    SYNTAX       SEQUENCE OF PVXCoSProfileEntry
    MAX-ACCESS   not-accessible
    STATUS       current
    DESCRIPTION  "This table is used to configure the Class of service on a 
                  port of a particular member of a virtual switch."
    ::= { pvxBridgeProfiles 2 }

pvxCoSProfileEntry OBJECT-TYPE
    SYNTAX       PVXCoSProfileEntry
    MAX-ACCESS   not-accessible
    STATUS       current
    DESCRIPTION  "The conceptual row object of the Cos table."
    INDEX        { pvxCPIdx }
    ::= {pvxCoSProfileTable  1 }

PVXCoSProfileEntry ::= SEQUENCE { 	pvxCPIdx 			Integer32,
                        			pvxCPMaxBandwidth  	Integer32, 
                        			pvxCPMinBandwidth  	Integer32,
                        			pvxCPWeight        	Integer32,
                        			pvxCPQueueAlgo     	INTEGER,
                        			pvxCPRowStatus     	RowStatus }

pvxCPIdx OBJECT-TYPE
   	SYNTAX          Integer32	
   	MAX-ACCESS   	not-accessible
   	STATUS       	current
   	DESCRIPTION  	""
    ::= { pvxCoSProfileEntry 1 }
    
pvxCPMaxBandwidth  OBJECT-TYPE 
    SYNTAX       Integer32 
    MAX-ACCESS   read-create
    STATUS       current
    DESCRIPTION  ""
    ::= { pvxCoSProfileEntry 2 }

pvxCPMinBandwidth OBJECT-TYPE  
    SYNTAX       Integer32 
    MAX-ACCESS   read-create
    STATUS       current
    DESCRIPTION  ""
    ::= { pvxCoSProfileEntry 3 }
                      
pvxCPWeight OBJECT-TYPE  
    SYNTAX       Integer32 
    MAX-ACCESS   read-create
    STATUS       current
    DESCRIPTION  "The weight of the queue associated with a CoS 
                   for WRR(+SP) and DRR(+SP) queuing algorithms"
    ::= { pvxCoSProfileEntry 4 }

pvxCPQueueAlgo OBJECT-TYPE  
    SYNTAX       INTEGER { sp    (1), 
                           rr    (2),
                           wrr   (3),
                           drr   (4),
                           wrrsp (5),
                           drrsp (6) }
    MAX-ACCESS   read-create
    STATUS       current
    DESCRIPTION  "This object represents the queuing algorithm configured for a 
                  particular cos on a virtual switch."
    ::= { pvxCoSProfileEntry 5 }
 
pvxCPRowStatus OBJECT-TYPE  
    SYNTAX       RowStatus 
    MAX-ACCESS   read-create
    STATUS       current
    DESCRIPTION  ""
    ::= { pvxCoSProfileEntry 100 }


-----------------------------------------------------------------------
-- Control frame profile Table
-----------------------------------------------------------------------

pvxCtrlFrmProfileTable OBJECT IDENTIFIER ::= { pvxBridgeProfiles 3 }

--
-- Table obsolete, removed.
--

-----------------------------------------------------------------------
-- Flow Meter Profile 
-----------------------------------------------------------------------
pvxFlowMeterProfileTable OBJECT-TYPE
    SYNTAX       SEQUENCE OF PVXFlowMeterProfileEntry
    MAX-ACCESS   not-accessible
    STATUS       current
    DESCRIPTION  ""
    ::= { pvxBridgeProfiles 4 }

pvxFlowMeterProfileEntry OBJECT-TYPE
    SYNTAX       PVXFlowMeterProfileEntry
    MAX-ACCESS   not-accessible
    STATUS       current
    DESCRIPTION  ""
    INDEX        { pvxFMPIdx }
    ::= { pvxFlowMeterProfileTable 1 }

PVXFlowMeterProfileEntry ::= SEQUENCE { pvxFMPIdx	 		Integer32,
								     	pvxFMPBWProfileId 	Integer32,  
                                     	pvxFMPColorAware  	TruthValue,
                                     	pvxFMPMeterType 	INTEGER,
                                     	pvxFMPStatsEnabled 	TruthValue,
                                     	pvxFMPRowStatus		RowStatus }

pvxFMPIdx OBJECT-TYPE
    SYNTAX       Integer32 
    MAX-ACCESS   not-accessible
    STATUS       current
    DESCRIPTION  ""
    ::= { pvxFlowMeterProfileEntry 1 }

pvxFMPBWProfileId OBJECT-TYPE
    SYNTAX       Integer32 
    MAX-ACCESS   read-create
    STATUS       current
    DESCRIPTION  ""
    ::= { pvxFlowMeterProfileEntry 2 }

pvxFMPColorAware OBJECT-TYPE
    SYNTAX       TruthValue 
    MAX-ACCESS   read-create
    STATUS       current
    DESCRIPTION  ""
    ::= { pvxFlowMeterProfileEntry 3 }

pvxFMPMeterType OBJECT-TYPE
    SYNTAX       INTEGER  { flow   (1),
							srTCM  (2),
							drTCM  (3) }
    MAX-ACCESS   read-create
    STATUS       current
    DESCRIPTION  ""
    ::= { pvxFlowMeterProfileEntry 4 }

pvxFMPStatsEnabled OBJECT-TYPE
    SYNTAX       ProtocolActionType
    MAX-ACCESS   read-create
    STATUS       current
    DESCRIPTION  ""
    ::= { pvxFlowMeterProfileEntry 5 }

pvxFMPRowStatus OBJECT-TYPE
    SYNTAX       RowStatus 
    MAX-ACCESS   read-create
    STATUS       current
    DESCRIPTION  ""
    ::= { pvxFlowMeterProfileEntry 100 }

-----------------------------------------------------------------------
-- Tunnel Mac address Profile Table
-----------------------------------------------------------------------
pvxTunnMacAddrProfileTable OBJECT IDENTIFIER ::= { pvxBridgeProfiles 5 }

--
-- Table obsolete, removed.
--

-----------------------------------------------------------------------
-- pvx Scheduler Profile Table
-----------------------------------------------------------------------
pvxSchedulerProfileTable OBJECT-TYPE
    SYNTAX       SEQUENCE OF PVXSchedulerProfileEntry
    MAX-ACCESS   not-accessible
    STATUS       current
    DESCRIPTION  "This is the scheduler profile table."
    ::= { pvxBridgeProfiles 6 }

pvxSchedulerProfileEntry OBJECT-TYPE
    SYNTAX       PVXSchedulerProfileEntry
    MAX-ACCESS   not-accessible
    STATUS       current
    DESCRIPTION  "The conceptual row object of the Scheduler Profile Table

                 Note the pvxSchedProfName index is a variable length OCTET STRING
                 object. When encoded as part of the index, it 
                 includes the string length as part of the instance.

                 For example, a profile named 'aaa' is encoded as '3.61.61.61'.

                 For more info on encoding OCTET STRING instances in OID's, 
                 see RFC-2578, section 7.7.
                 "
    INDEX        { pvxSchedProfName }
    ::= { pvxSchedulerProfileTable 1 }

PVXSchedulerProfileEntry ::= SEQUENCE { pvxSchedProfName             DisplayString,
                                        pvxSchedProfAlgorithm   	 INTEGER,  
                                     	pvxSchedProfWeightQ0       	 Integer32,
                                     	pvxSchedProfWeightQ1       	 Integer32,
                                     	pvxSchedProfWeightQ2       	 Integer32,
                                     	pvxSchedProfWeightQ3       	 Integer32,
                                     	pvxSchedProfWeightQ4       	 Integer32,
                                     	pvxSchedProfWeightQ5       	 Integer32,
                                     	pvxSchedProfWeightQ6       	 Integer32,
                                     	pvxSchedProfWeightQ7       	 Integer32,                                    	
                                     	pvxSchedProfMinBwQ0       	 Integer32,                                    	
                                     	pvxSchedProfMaxBwQ0       	 Integer32,                                    	
                                     	pvxSchedProfMinBwQ1       	 Integer32,                                    	
                                     	pvxSchedProfMaxBwQ1       	 Integer32,                                    	
                                     	pvxSchedProfMinBwQ2       	 Integer32,                                    	
                                     	pvxSchedProfMaxBwQ2       	 Integer32,                                    	
                                     	pvxSchedProfMinBwQ3       	 Integer32,                                    	
                                     	pvxSchedProfMaxBwQ3       	 Integer32,                                    	
                                     	pvxSchedProfMinBwQ4       	 Integer32,                                    	
                                     	pvxSchedProfMaxBwQ4       	 Integer32,                                    	
                                     	pvxSchedProfMinBwQ5       	 Integer32,                                    	
                                     	pvxSchedProfMaxBwQ5       	 Integer32,                                    	
                                     	pvxSchedProfMinBwQ6       	 Integer32,                                    	
                                     	pvxSchedProfMaxBwQ6       	 Integer32,                                    	
                                     	pvxSchedProfMinBwQ7       	 Integer32,                                    	
                                     	pvxSchedProfMaxBwQ7       	 Integer32,
                                     	pvxSchedProfMTUQuanta        INTEGER,                                    	
                                     	pvxSchedProfRowStatus		 RowStatus }

    
pvxSchedProfName OBJECT-TYPE
    SYNTAX       DisplayString (SIZE(1..32))
    MAX-ACCESS   not-accessible
    STATUS       current
    DESCRIPTION  "The scheduler profile name string."
    ::= { pvxSchedulerProfileEntry 1 }

pvxSchedProfAlgorithm OBJECT-TYPE
    SYNTAX       INTEGER  { sp     (1),
							rr     (2),
							wrr    (3),
							drr    (4),
							sp-wrr (5),
							sp-drr (6)} 
    MAX-ACCESS   read-create
    STATUS       current
    DESCRIPTION  "The scheduler algorithm. The default value is sp. Once the algorithm is set, changes
                  to this value is not allowed. "
    ::= { pvxSchedulerProfileEntry 2 }

pvxSchedProfWeightQ0 OBJECT-TYPE
    SYNTAX       Integer32(0..255) 
    MAX-ACCESS   read-create
    STATUS       current
    DESCRIPTION  "The weight value for queue 0. The default value is 1. However, in wrr and drr mode,
                 the lowerest value can only be 1."
    DEFVAL       { 1 }
    ::= { pvxSchedulerProfileEntry 3 }

pvxSchedProfWeightQ1 OBJECT-TYPE
    SYNTAX       Integer32(0..255) 
    MAX-ACCESS   read-create
    STATUS       current
    DESCRIPTION  "The weight value for queue 1. The default value is 1.However, in wrr and drr mode,
                 the lowerest value can only be 1."
    DEFVAL       { 1 }
    ::= { pvxSchedulerProfileEntry 4 }

pvxSchedProfWeightQ2 OBJECT-TYPE
    SYNTAX       Integer32(0..255) 
    MAX-ACCESS   read-create
    STATUS       current
    DESCRIPTION  "The weight value for queue 2. The default value is 1.However, in wrr and drr mode,
                 the lowerest value can only be 1."
    DEFVAL       { 1 }
    ::= { pvxSchedulerProfileEntry 5 }

pvxSchedProfWeightQ3 OBJECT-TYPE
    SYNTAX       Integer32(0..255) 
    MAX-ACCESS   read-create
    STATUS       current
    DESCRIPTION  "The weight value for queue 3. The default value is 1.However, in wrr and drr mode,
                 the lowerest value can only be 1."
    DEFVAL       { 1 }
    ::= { pvxSchedulerProfileEntry 6 }

pvxSchedProfWeightQ4 OBJECT-TYPE
    SYNTAX       Integer32(0..255) 
    MAX-ACCESS   read-create
    STATUS       current
    DESCRIPTION  "The weight value for queue 4. The default value is 1.However, in wrr and drr mode,
                 the lowerest value can only be 1."
    DEFVAL       { 1 }
    ::= { pvxSchedulerProfileEntry 7 }

pvxSchedProfWeightQ5 OBJECT-TYPE
    SYNTAX       Integer32(0..255) 
    MAX-ACCESS   read-create
    STATUS       current
    DESCRIPTION  "The weight value for queue 5. The default value is 1.However, in wrr and drr mode,
                 the lowerest value can only be 1."
    DEFVAL       { 1 }
    ::= { pvxSchedulerProfileEntry 8 }

pvxSchedProfWeightQ6 OBJECT-TYPE
    SYNTAX       Integer32(0..255) 
    MAX-ACCESS   read-create
    STATUS       current
    DESCRIPTION  "The weight value for queue 6. The default value is 1.However, in wrr and drr mode,
                 the lowerest value can only be 1."
    DEFVAL       { 1 }
    ::= { pvxSchedulerProfileEntry 9 }

pvxSchedProfWeightQ7 OBJECT-TYPE
    SYNTAX       Integer32(0..255) 
    MAX-ACCESS   read-create
    STATUS       current
    DESCRIPTION  "The weight value for queue 7. The default value is 1.However, in wrr and drr mode,
                 the lowerest value can only be 1."
    DEFVAL       { 1 }
    ::= { pvxSchedulerProfileEntry 10}

pvxSchedProfMinBwQ0 OBJECT-TYPE
    SYNTAX       Integer32 
    MAX-ACCESS   read-create
    STATUS       current
    DESCRIPTION  "The minmum bandwidth for Queue 0. The default value is 0."
    DEFVAL       { 0 }
    ::= { pvxSchedulerProfileEntry 11}

pvxSchedProfMaxBwQ0 OBJECT-TYPE
    SYNTAX       Integer32 
    MAX-ACCESS   read-create
    STATUS       current
    DESCRIPTION  "The maximum bandwidth for Queue 0. The default value is 0."
    DEFVAL       { 0 }
    ::= { pvxSchedulerProfileEntry 12}

pvxSchedProfMinBwQ1 OBJECT-TYPE
    SYNTAX       Integer32 
    MAX-ACCESS   read-create
    STATUS       current
    DESCRIPTION  "The minmum bandwidth for Queue 1. The default value is 0."
    DEFVAL       { 0 }
    ::= { pvxSchedulerProfileEntry 13}

pvxSchedProfMaxBwQ1 OBJECT-TYPE
    SYNTAX       Integer32 
    MAX-ACCESS   read-create
    STATUS       current
    DESCRIPTION  "The maximum bandwidth for Queue 1. The default value is 0."
    DEFVAL       { 0 }
    ::= { pvxSchedulerProfileEntry 14}

pvxSchedProfMinBwQ2 OBJECT-TYPE
    SYNTAX       Integer32 
    MAX-ACCESS   read-create
    STATUS       current
    DESCRIPTION  "The minmum bandwidth for Queue 2. The default value is 0."
    DEFVAL       { 0 }
    ::= { pvxSchedulerProfileEntry 15}

pvxSchedProfMaxBwQ2 OBJECT-TYPE
    SYNTAX       Integer32 
    MAX-ACCESS   read-create
    STATUS       current
    DESCRIPTION  "The maximum bandwidth for Queue 2. The default value is 0."
    DEFVAL       { 0 }
    ::= { pvxSchedulerProfileEntry 16}

pvxSchedProfMinBwQ3 OBJECT-TYPE
    SYNTAX       Integer32 
    MAX-ACCESS   read-create
    STATUS       current
    DESCRIPTION  "The minmum bandwidth for Queue 3. The default value is 0."
    DEFVAL       { 0 }
    ::= { pvxSchedulerProfileEntry 17}

pvxSchedProfMaxBwQ3 OBJECT-TYPE
    SYNTAX       Integer32 
    MAX-ACCESS   read-create
    STATUS       current
    DESCRIPTION  "The maximum bandwidth for Queue 3. The default value is 0."
    DEFVAL       { 0 }
    ::= { pvxSchedulerProfileEntry 18}

pvxSchedProfMinBwQ4 OBJECT-TYPE
    SYNTAX       Integer32 
    MAX-ACCESS   read-create
    STATUS       current
    DESCRIPTION  "The minmum bandwidth for Queue 4. The default value is 0."
    DEFVAL       { 0 }
    ::= { pvxSchedulerProfileEntry 19 }

pvxSchedProfMaxBwQ4 OBJECT-TYPE
    SYNTAX       Integer32 
    MAX-ACCESS   read-create
    STATUS       current
    DESCRIPTION  "The maximum bandwidth for Queue 4. The default value is 0."
    DEFVAL       { 0 }
    ::= { pvxSchedulerProfileEntry 20}

pvxSchedProfMinBwQ5 OBJECT-TYPE
    SYNTAX       Integer32 
    MAX-ACCESS   read-create
    STATUS       current
    DESCRIPTION  "The minmum bandwidth for Queue 5. The default value is 0."
    DEFVAL       { 0 }
    ::= { pvxSchedulerProfileEntry 21}

pvxSchedProfMaxBwQ5 OBJECT-TYPE
    SYNTAX       Integer32 
    MAX-ACCESS   read-create
    STATUS       current
    DESCRIPTION  "The maximum bandwidth for Queue 5. The default value is 0."
    DEFVAL       { 0 }
    ::= { pvxSchedulerProfileEntry 22 }

pvxSchedProfMinBwQ6 OBJECT-TYPE
    SYNTAX       Integer32 
    MAX-ACCESS   read-create
    STATUS       current
    DESCRIPTION  "The minmum bandwidth for Queue 6. The default value is 0."
    DEFVAL       { 0 }
    ::= { pvxSchedulerProfileEntry 23}

pvxSchedProfMaxBwQ6 OBJECT-TYPE
    SYNTAX       Integer32 
    MAX-ACCESS   read-create
    STATUS       current
    DESCRIPTION  "The maximum bandwidth for Queue 6. The default value is 0."
    DEFVAL       { 0 }
    ::= { pvxSchedulerProfileEntry 24}

pvxSchedProfMinBwQ7 OBJECT-TYPE
    SYNTAX       Integer32 
    MAX-ACCESS   read-create
    STATUS       current
    DESCRIPTION  "The minmum bandwidth for Queue 7. The default value is 0."
    DEFVAL       { 0 }
    ::= { pvxSchedulerProfileEntry 25}

pvxSchedProfMaxBwQ7 OBJECT-TYPE
    SYNTAX       Integer32 
    MAX-ACCESS   read-create
    STATUS       current
    DESCRIPTION  "The maximum bandwidth for Queue 7. The default value is 0."
    DEFVAL       { 0 }
    ::= { pvxSchedulerProfileEntry 26}

pvxSchedProfMTUQuanta OBJECT-TYPE
    SYNTAX       INTEGER { byte2k (1),
                           byte16k (2) } 
    MAX-ACCESS   read-create
    STATUS       current
    DESCRIPTION  "The attribute is only used by drr, or sp_drr scheduler mode.
                  Default is 2Kbyte."
    ::= { pvxSchedulerProfileEntry 27}
    
pvxSchedProfRowStatus OBJECT-TYPE
    SYNTAX       RowStatus 
    MAX-ACCESS   read-create
    STATUS       current
    DESCRIPTION  ""
    ::= { pvxSchedulerProfileEntry 100 }
 
-----------------------------------------------------------------------
-- pvx Priority Traffic Class Map Profile Table
-----------------------------------------------------------------------
pvxPriorityTCMapTable OBJECT-TYPE
    SYNTAX       SEQUENCE OF PVXPriorityTCMapEntry
    MAX-ACCESS   not-accessible
    STATUS       current
    DESCRIPTION  "A table mapping evaluated User Priority to Traffic
                  Class, for forwarding by the bridge."
    ::= { pvxBridgeProfiles 7 }

pvxPriorityTCMapEntry OBJECT-TYPE
    SYNTAX       PVXPriorityTCMapEntry
    MAX-ACCESS   not-accessible
    STATUS       current
    DESCRIPTION  "The conceptual row object of the Priority Traffic 
                 Class Map Profile Table.

                 Note the pvxPriorityTCMapName index is a variable length OCTET STRING
                 object. When encoded as part of the index, it 
                 includes the string length as part of the instance.

                 For example, a profile named 'aaa' is encoded as '3.61.61.61'.

                 For more info on encoding OCTET STRING instances in OID's, 
                 see RFC-2578, section 7.7."
    INDEX        { pvxPriorityTCMapName }
    ::= { pvxPriorityTCMapTable 1 }

PVXPriorityTCMapEntry ::= SEQUENCE { pvxPriorityTCMapName            DisplayString,
                                     pvxPriority7TrafficClass   	 Integer32,  
                                     pvxPriority6TrafficClass   	 Integer32,
                                     pvxPriority5TrafficClass   	 Integer32,
                                     pvxPriority4TrafficClass   	 Integer32,
                                     pvxPriority3TrafficClass   	 Integer32,
                                     pvxPriority2TrafficClass   	 Integer32,
                                     pvxPriority1TrafficClass   	 Integer32,
                                     pvxPriority0TrafficClass   	 Integer32,
                                     pvxPriorityTCMapRowStatus		 RowStatus }
    
pvxPriorityTCMapName OBJECT-TYPE
    SYNTAX       DisplayString (SIZE(1..32))
    MAX-ACCESS   not-accessible
    STATUS       current
    DESCRIPTION  "The scheduler profile name string."
    ::= { pvxPriorityTCMapEntry 1 }

pvxPriority7TrafficClass OBJECT-TYPE
    SYNTAX    Integer32(0..7)
    MAX-ACCESS   read-create
    STATUS       current
    DESCRIPTION  "The traffic class for priority 7. Default is 7."
    ::= { pvxPriorityTCMapEntry 2 }

pvxPriority6TrafficClass OBJECT-TYPE
    SYNTAX    Integer32(0..7)
    MAX-ACCESS   read-create
    STATUS       current
    DESCRIPTION  "The traffic class for priority 6. Default is 6."
    ::= { pvxPriorityTCMapEntry 3 }
    
pvxPriority5TrafficClass OBJECT-TYPE
    SYNTAX    Integer32(0..7)
    MAX-ACCESS   read-create
    STATUS       current
    DESCRIPTION  "The traffic class for priority 5. Default is 5."
    ::= { pvxPriorityTCMapEntry 4 }

pvxPriority4TrafficClass OBJECT-TYPE
    SYNTAX    Integer32(0..7)
    MAX-ACCESS   read-create
    STATUS       current
    DESCRIPTION  "The traffic class for priority 4. Default is 4."
    ::= { pvxPriorityTCMapEntry 5 }

pvxPriority3TrafficClass OBJECT-TYPE
    SYNTAX    Integer32(0..7)
    MAX-ACCESS   read-create
    STATUS       current
    DESCRIPTION  "The traffic class for priority 3. Default is 3."
    ::= { pvxPriorityTCMapEntry 6 }
    
pvxPriority2TrafficClass OBJECT-TYPE
    SYNTAX    Integer32(0..7)
    MAX-ACCESS   read-create
    STATUS       current
    DESCRIPTION  "The traffic class for priority 2. Default is 2."
    ::= { pvxPriorityTCMapEntry 7 }
    
pvxPriority1TrafficClass OBJECT-TYPE
    SYNTAX    Integer32(0..7)
    MAX-ACCESS   read-create
    STATUS       current
    DESCRIPTION  "The traffic class for priority 1. Default is 0."
    ::= { pvxPriorityTCMapEntry 8 }
    
pvxPriority0TrafficClass OBJECT-TYPE
    SYNTAX    Integer32(0..7)
    MAX-ACCESS   read-create
    STATUS       current
    DESCRIPTION  "The traffic class for priority 0. Default is 1."
    ::= { pvxPriorityTCMapEntry 9 }

pvxPriorityTCMapRowStatus OBJECT-TYPE
    SYNTAX       RowStatus 
    MAX-ACCESS   read-create
    STATUS       current
    DESCRIPTION  ""
    ::= { pvxPriorityTCMapEntry 100 }

-----------------------------------------------------------------------
-- pvx PCP Encoding Decoding Profile Table
-----------------------------------------------------------------------
pvxPCPEncDecProfileTable OBJECT-TYPE
    SYNTAX       SEQUENCE OF PVXPCPEncDecProfEntry
    MAX-ACCESS   not-accessible
    STATUS       current
    DESCRIPTION  "This table contains information about Priority Code
                  Point Enable and Decoding for a Port of a provider bridge."
    ::= { pvxBridgeProfiles 8 }

pvxPCPEncDecProfEntry OBJECT-TYPE
    SYNTAX       PVXPCPEncDecProfEntry
    MAX-ACCESS   not-accessible
    STATUS       current
    DESCRIPTION  "The conceptual row object of the PCP Encoding Decoding Profile Table

                 Note the pvxPCPEncDecProfileName index is a variable length OCTET STRING
                 object. When encoded as part of the index, it 
                 includes the string length as part of the instance.

                 For example, a profile named 'aaa' is encoded as '3.61.61.61'.

                 For more info on encoding OCTET STRING instances in OID's, 
                 see RFC-2578, section 7.7."
    INDEX        { pvxPCPEncDecProfileName }
    ::= { pvxPCPEncDecProfileTable 1 }

PVXPCPEncDecProfEntry ::= SEQUENCE {       pvxPCPEncDecProfileName  DisplayString,
                                           pvxPCPEncDecSelectRow    INTEGER,
                                           pvxPCPEncPriority7       Integer32,  
                                           pvxPCPEncPriority7DE     Integer32,
                                           pvxPCPEncPriority6       Integer32,  
                                           pvxPCPEncPriority6DE     Integer32,
                                           pvxPCPEncPriority5       Integer32,  
                                           pvxPCPEncPriority5DE     Integer32,
                                           pvxPCPEncPriority4       Integer32,  
                                           pvxPCPEncPriority4DE     Integer32,
                                           pvxPCPEncPriority3       Integer32,  
                                           pvxPCPEncPriority3DE     Integer32,
                                           pvxPCPEncPriority2       Integer32,  
                                           pvxPCPEncPriority2DE     Integer32,
                                           pvxPCPEncPriority1       Integer32,  
                                           pvxPCPEncPriority1DE     Integer32,
                                           pvxPCPEncPriority0       Integer32,  
                                           pvxPCPEncPriority0DE     Integer32,
                                           pvxPCPDecPriority7       PvxPCPDecodingList,  
                                           pvxPCPDecPriority6       PvxPCPDecodingList,
                                           pvxPCPDecPriority5       PvxPCPDecodingList,
                                           pvxPCPDecPriority4       PvxPCPDecodingList,
                                           pvxPCPDecPriority3       PvxPCPDecodingList,
                                           pvxPCPDecPriority2       PvxPCPDecodingList,
                                           pvxPCPDecPriority1       PvxPCPDecodingList,
                                           pvxPCPDecPriority0       PvxPCPDecodingList,
                                           pvxPCPEncDecRowStatus    RowStatus }
    
pvxPCPEncDecProfileName OBJECT-TYPE
    SYNTAX       DisplayString (SIZE(1..32))
    MAX-ACCESS   not-accessible
    STATUS       current
    DESCRIPTION  "The scheduler profile name string."
    ::= { pvxPCPEncDecProfEntry 1 }
    
pvxPCPEncDecSelectRow OBJECT-TYPE
    SYNTAX       INTEGER { row-8P0D (1),
                           row-7P1D (2),
                           row-6P2D (3),
                           row-5P3D (4) }
    MAX-ACCESS   read-create
    STATUS       current
    DESCRIPTION  "The attribute is used to select one of the four default profiles: 8P0D, 7P1D, 6P2D,
                  or 5P3D. Default value is 8P0D. "
    ::= { pvxPCPEncDecProfEntry 2 }

pvxPCPEncPriority7 OBJECT-TYPE
    SYNTAX       Integer32(0..7)
    MAX-ACCESS   read-create
    STATUS       current
    DESCRIPTION  "The encoding value for this priority. Default is 7."
    ::= { pvxPCPEncDecProfEntry 3 }

pvxPCPEncPriority7DE OBJECT-TYPE
    SYNTAX       Integer32(0..7) 
    MAX-ACCESS   read-create
    STATUS       current
    DESCRIPTION  "The encoding value for this priority. Default is 7."
    ::= { pvxPCPEncDecProfEntry 4 }

pvxPCPEncPriority6 OBJECT-TYPE
    SYNTAX       Integer32(0..7)
    MAX-ACCESS   read-create
    STATUS       current
    DESCRIPTION  "The encoding value for this priority. Default is 6."
    ::= { pvxPCPEncDecProfEntry 5 }

pvxPCPEncPriority6DE OBJECT-TYPE
    SYNTAX       Integer32(0..7) 
    MAX-ACCESS   read-create
    STATUS       current
    DESCRIPTION  "The encoding value for this priority. Default is 6."
    ::= { pvxPCPEncDecProfEntry 6 }

pvxPCPEncPriority5 OBJECT-TYPE
    SYNTAX       Integer32(0..7)
    MAX-ACCESS   read-create
    STATUS       current
    DESCRIPTION  "The encoding value for this priority. Default is 5."
    ::= { pvxPCPEncDecProfEntry 7 }

pvxPCPEncPriority5DE OBJECT-TYPE
    SYNTAX       Integer32(0..7) 
    MAX-ACCESS   read-create
    STATUS       current
    DESCRIPTION  "The encoding value for this priority. Default is 5."
    ::= { pvxPCPEncDecProfEntry 8 }

pvxPCPEncPriority4 OBJECT-TYPE
    SYNTAX       Integer32(0..7)
    MAX-ACCESS   read-create
    STATUS       current
    DESCRIPTION  "The encoding value for this priority. Default is 4."
    ::= { pvxPCPEncDecProfEntry 9 }

pvxPCPEncPriority4DE OBJECT-TYPE
    SYNTAX       Integer32(0..7) 
    MAX-ACCESS   read-create
    STATUS       current
    DESCRIPTION  "The encoding value for this priority. Default is 4."
    ::= { pvxPCPEncDecProfEntry 10 }

pvxPCPEncPriority3 OBJECT-TYPE
    SYNTAX       Integer32(0..7)
    MAX-ACCESS   read-create
    STATUS       current
    DESCRIPTION  "The encoding value for this priority. Default is 3."
    ::= { pvxPCPEncDecProfEntry 11 }

pvxPCPEncPriority3DE OBJECT-TYPE
    SYNTAX       Integer32(0..7) 
    MAX-ACCESS   read-create
    STATUS       current
    DESCRIPTION  "The encoding value for this priority. Default is 3."
    ::= { pvxPCPEncDecProfEntry 12 }
    
pvxPCPEncPriority2 OBJECT-TYPE
    SYNTAX       Integer32(0..7)
    MAX-ACCESS   read-create
    STATUS       current
    DESCRIPTION  "The encoding value for this priority. Default is 2."
    ::= { pvxPCPEncDecProfEntry 13 }

pvxPCPEncPriority2DE OBJECT-TYPE
    SYNTAX       Integer32(0..7) 
    MAX-ACCESS   read-create
    STATUS       current
    DESCRIPTION  "The encoding value for this priority. Default is 2."
    ::= { pvxPCPEncDecProfEntry 14 }

pvxPCPEncPriority1 OBJECT-TYPE
    SYNTAX       Integer32(0..7)
    MAX-ACCESS   read-create
    STATUS       current
    DESCRIPTION  "The encoding value for this priority. Default is 1."
    ::= { pvxPCPEncDecProfEntry 15 }

pvxPCPEncPriority1DE OBJECT-TYPE
    SYNTAX       Integer32(0..7) 
    MAX-ACCESS   read-create
    STATUS       current
    DESCRIPTION  "The encoding value for this priority. Default is 1."
    ::= { pvxPCPEncDecProfEntry 16 }

pvxPCPEncPriority0 OBJECT-TYPE
    SYNTAX       Integer32(0..7)
    MAX-ACCESS   read-create
    STATUS       current
    DESCRIPTION  "The encoding value for this priority. Default is prioirty 0."
    ::= { pvxPCPEncDecProfEntry 17 }

pvxPCPEncPriority0DE OBJECT-TYPE
    SYNTAX       Integer32(0..7) 
    MAX-ACCESS   read-create
    STATUS       current
    DESCRIPTION  "The encoding value for this priority. Default is prioirty 0."
    ::= { pvxPCPEncDecProfEntry 18 }
        
pvxPCPDecPriority7 OBJECT-TYPE
    SYNTAX       PvxPCPDecodingList
    MAX-ACCESS   read-create
    STATUS       current
    DESCRIPTION  "The decoding value for this priority. Default is prioirty7."
    ::= { pvxPCPEncDecProfEntry 19 }

pvxPCPDecPriority6 OBJECT-TYPE
    SYNTAX       PvxPCPDecodingList
    MAX-ACCESS   read-create
    STATUS       current
    DESCRIPTION  "The decoding value for this priority. Default is prioirty6."
    ::= { pvxPCPEncDecProfEntry 20 }

pvxPCPDecPriority5 OBJECT-TYPE
    SYNTAX       PvxPCPDecodingList
    MAX-ACCESS   read-create
    STATUS       current
    DESCRIPTION  "The decoding value for this priority. Default is prioirty5."
    ::= { pvxPCPEncDecProfEntry 21 }

pvxPCPDecPriority4 OBJECT-TYPE
    SYNTAX       PvxPCPDecodingList
    MAX-ACCESS   read-create
    STATUS       current
    DESCRIPTION  "The decoding value for this priority. Default is prioirty4."
    ::= { pvxPCPEncDecProfEntry 22 }

pvxPCPDecPriority3 OBJECT-TYPE
    SYNTAX       PvxPCPDecodingList
    MAX-ACCESS   read-create
    STATUS       current
    DESCRIPTION  "The decoding value for this priority. Default is prioirty3."
    ::= { pvxPCPEncDecProfEntry 23 }

pvxPCPDecPriority2 OBJECT-TYPE
    SYNTAX       PvxPCPDecodingList
    MAX-ACCESS   read-create
    STATUS       current
    DESCRIPTION  "The decoding value for this priority. Default is prioirty2."
    ::= { pvxPCPEncDecProfEntry 24 }

pvxPCPDecPriority1 OBJECT-TYPE
    SYNTAX       PvxPCPDecodingList
    MAX-ACCESS   read-create
    STATUS       current
    DESCRIPTION  "The decoding value for this priority. Default is prioirty1."
    ::= { pvxPCPEncDecProfEntry 25 }    

pvxPCPDecPriority0 OBJECT-TYPE
    SYNTAX       PvxPCPDecodingList
    MAX-ACCESS   read-create
    STATUS       current
    DESCRIPTION  "The decoding value for this priority. Default is prioirty0."
    ::= { pvxPCPEncDecProfEntry 26 }

pvxPCPEncDecRowStatus OBJECT-TYPE
    SYNTAX       RowStatus 
    MAX-ACCESS   read-create
    STATUS       current
    DESCRIPTION  ""
    ::= { pvxPCPEncDecProfEntry 100 }

-----------------------------------------------------------------------
-- pvx DSCP PHB Profile Table
-----------------------------------------------------------------------
pvxDscpPHBProfileTable OBJECT-TYPE
    SYNTAX       SEQUENCE OF PVXDscpPHBProfileEntry
    MAX-ACCESS   not-accessible
    STATUS       current
    DESCRIPTION  "This table defines internal priority settings for
                  the DSCP definitions in the TOS byte in IPV4 header."
    ::= { pvxBridgeProfiles 9 }

pvxDscpPHBProfileEntry OBJECT-TYPE
    SYNTAX       PVXDscpPHBProfileEntry
    MAX-ACCESS   not-accessible
    STATUS       current
    DESCRIPTION  "The conceptual row object of the DSCP PHB Profile Table

                 Note the pvxDscpPHBProfileName index is a variable length OCTET STRING
                 object. When encoded as part of the index, it 
                 includes the string length as part of the instance.

                 For example, a profile named 'aaa' is encoded as '3.61.61.61'.

                 For more info on encoding OCTET STRING instances in OID's, 
                 see RFC-2578, section 7.7."
    INDEX        { pvxDscpPHBProfileName }
    ::= { pvxDscpPHBProfileTable 1 }

PVXDscpPHBProfileEntry ::= SEQUENCE { pvxDscpPHBProfileName          DisplayString,
								      pvxDscpClassSelector7  	     Integer32,  
                                      pvxDscpClassSelector6   	     Integer32,
                                      pvxDscpClassSelector5   	     Integer32,
                                      pvxDscpClassSelector4   	     Integer32,
                                      pvxDscpClassSelector3   	     Integer32,
                                      pvxDscpClassSelector2   	     Integer32,
                                      pvxDscpClassSelector1   	     Integer32,
                                      pvxDscpClassBestEffort   	     Integer32,                                     
                                      pvxDscpAssuredFwd1y            Integer32,                                     
                                      pvxDscpAssuredFwd2y            Integer32, 
                                      pvxDscpAssuredFwd3y            Integer32,
                                      pvxDscpAssuredFwd4y            Integer32,
                                      pvxDscpExpeditedFwd            Integer32,                                                                  	
                                      pvxDscpPHBProfileRowStatus     RowStatus }
    
pvxDscpPHBProfileName OBJECT-TYPE
    SYNTAX       DisplayString (SIZE(1..32))
    MAX-ACCESS   not-accessible
    STATUS       current
    DESCRIPTION  "A string for profile name."
    ::= { pvxDscpPHBProfileEntry 1 }

pvxDscpClassSelector7 OBJECT-TYPE
    SYNTAX    Integer32(0..7)
    MAX-ACCESS   read-create
    STATUS       current
    DESCRIPTION  "This attribute assigns the internal priority value for DSCP class selector 7. 
                  Default priority is set to 7."
    ::= { pvxDscpPHBProfileEntry 2 }

pvxDscpClassSelector6 OBJECT-TYPE
    SYNTAX    Integer32(0..7)
    MAX-ACCESS   read-create
    STATUS       current
    DESCRIPTION  "This attribute assigns the internal priority value for DSCP class selector 6. 
                  Default priority is set to 6."
    ::= { pvxDscpPHBProfileEntry 3 }
    
pvxDscpClassSelector5 OBJECT-TYPE
    SYNTAX    Integer32(0..7)
    MAX-ACCESS   read-create
    STATUS       current
    DESCRIPTION  "This attribute assigns the internal priority value for DSCP class selector 5. 
                  Default priority is set to 5."
    ::= { pvxDscpPHBProfileEntry 4 }

pvxDscpClassSelector4 OBJECT-TYPE
    SYNTAX    Integer32(0..7)
    MAX-ACCESS   read-create
    STATUS       current
    DESCRIPTION  "This attribute assigns the internal priority value for DSCP class selector 4. 
                  Default priority is set to 4."
    ::= { pvxDscpPHBProfileEntry 5 }

pvxDscpClassSelector3 OBJECT-TYPE
    SYNTAX    Integer32(0..7)
    MAX-ACCESS   read-create
    STATUS       current
    DESCRIPTION  "This attribute assigns the internal priority value for DSCP class selector 3. 
                  Default priority is set to 3."
    ::= { pvxDscpPHBProfileEntry 6 }

pvxDscpClassSelector2 OBJECT-TYPE
    SYNTAX    Integer32(0..7)
    MAX-ACCESS   read-create
    STATUS       current
    DESCRIPTION  "This attribute assigns the internal priority value for DSCP class selector 2. 
                  Default priority is set to 2."
    ::= { pvxDscpPHBProfileEntry 7 }

pvxDscpClassSelector1 OBJECT-TYPE
    SYNTAX    Integer32(0..7)
    MAX-ACCESS   read-create
    STATUS       current
    DESCRIPTION  "This attribute assigns the internal priority value for DSCP class selector 1. 
                  Default priority is set to 0."
    ::= { pvxDscpPHBProfileEntry 8 }

pvxDscpClassBestEffort OBJECT-TYPE
    SYNTAX    Integer32(0..7)
    MAX-ACCESS   read-create
    STATUS       current
    DESCRIPTION  "This attribute assigns the internal priority value for DSCP best effort. 
                  Default priority is set to 1."
    ::= { pvxDscpPHBProfileEntry 9 }
    
pvxDscpAssuredFwd1y OBJECT-TYPE
    SYNTAX    Integer32(0..7)
    MAX-ACCESS   read-create
    STATUS       current
    DESCRIPTION  "This attribute assigns the internal priority value for DSCP assured forwarding
                  with IP precedence value of 1, drop preference value of 1,2, or 3. 
                  Default priority is set to 2."
    ::= { pvxDscpPHBProfileEntry 10 }
    
pvxDscpAssuredFwd2y OBJECT-TYPE
    SYNTAX    Integer32(0..7)
    MAX-ACCESS   read-create
    STATUS       current
    DESCRIPTION  "This attribute assigns the internal priority value for DSCP assured forwarding
                  with IP precedence value of 2, drop preference value of 1,2, or 3.
                  Default priority is set to 3."
    ::= { pvxDscpPHBProfileEntry 11 }
    
pvxDscpAssuredFwd3y OBJECT-TYPE
    SYNTAX    Integer32(0..7)
    MAX-ACCESS   read-create
    STATUS       current
    DESCRIPTION  "This attribute assigns the internal priority value for DSCP assured forwarding
                  with IP precedence value of 3, drop preference value of 1,2, or 3.
                  Default priority is set to 4."
    ::= { pvxDscpPHBProfileEntry 12 }
 
pvxDscpAssuredFwd4y OBJECT-TYPE
    SYNTAX    Integer32(0..7)
    MAX-ACCESS   read-create
    STATUS       current
    DESCRIPTION  "This attribute assigns the internal priority value for DSCP assured forwarding
                  with IP precedence value of 4, drop preference value of 1,2, or 3.
                  Default priority is set to 5."
    ::= { pvxDscpPHBProfileEntry 13 }
       
pvxDscpExpeditedFwd OBJECT-TYPE
    SYNTAX    Integer32(0..7)
    MAX-ACCESS   read-create
    STATUS       current
    DESCRIPTION  "This attribute assigns the internal priority value for DSCP expedited forwarding. 
                  Default priority is set to 7."
    ::= { pvxDscpPHBProfileEntry 14 }

pvxDscpPHBProfileRowStatus OBJECT-TYPE
    SYNTAX       RowStatus 
    MAX-ACCESS   read-create
    STATUS       current
    DESCRIPTION  ""
    ::= { pvxDscpPHBProfileEntry 100 }
    
-----------------------------------------------------------------------
-- pvx bandwidth Profile Table
-----------------------------------------------------------------------
pvxBandwidthProfileTable OBJECT-TYPE
    SYNTAX       SEQUENCE OF PVXBandwidthProfileEntry
    MAX-ACCESS   not-accessible
    STATUS       current
    DESCRIPTION  "This table is used to configure the Class of service bandwidth
                  paramaters." 
    ::= { pvxBridgeProfiles 10 }

pvxBandwidthProfileEntry OBJECT-TYPE
    SYNTAX       PVXBandwidthProfileEntry
    MAX-ACCESS   not-accessible
    STATUS       current
    DESCRIPTION  "The conceptual row object of the Bandwidth Profile Table

                 Note the pvxBandwidthProfileName index is a variable length OCTET STRING
                 object. When encoded as part of the index, it 
                 includes the string length as part of the instance.

                 For example, a profile named 'aaa' is encoded as '3.61.61.61'.

                 For more info on encoding OCTET STRING instances in OID's, 
                 see RFC-2578, section 7.7."
    INDEX        { pvxBandwidthProfileName }
    ::= { pvxBandwidthProfileTable 1 }

PVXBandwidthProfileEntry ::= SEQUENCE { pvxBandwidthProfileName             DisplayString,
                                        pvxBWCnfrmActionChangeDscp  	    Integer32,  
                                        pvxBWCnfrmActionChangeTOSFrmPri     INTEGER,
                                        pvxBWExceedActionChangeDscp   	    Integer32,
                                        pvxBWMeterColorAware  	            PvxQoSColorMode,  
                                        pvxBWMeterMode                      INTEGER,
                                        pvxBWMeterCir                       Integer32,
                                        pvxBWMeterCbs                       Integer32,
                                        pvxBWMeterEir                       Integer32,
                                        pvxBWMeterEbs                       Integer32,
                                        pvxBWSetInternalPriority            Integer32,
                                        pvxBWExceedActionSetDEI             INTEGER,
                                        pvxBandwidthProfileRowStatus        RowStatus }
    
pvxBandwidthProfileName OBJECT-TYPE
    SYNTAX       DisplayString (SIZE(1..32))
    MAX-ACCESS   not-accessible
    STATUS       current
    DESCRIPTION  "A string for profile name."
    ::= { pvxBandwidthProfileEntry 1 }

pvxBWCnfrmActionChangeDscp OBJECT-TYPE
    SYNTAX    Integer32(-1..63)
    MAX-ACCESS   read-create
    STATUS       current
    DESCRIPTION  "This field configures the DSCP value for profile conformance action.
                  Default is -1, means do not use this field."
    ::= { pvxBandwidthProfileEntry 2 }

pvxBWCnfrmActionChangeTOSFrmPri OBJECT-TYPE
    SYNTAX       INTEGER { change        (1),
                           doNotChange   (2),
                           notUsed       (3)}
    MAX-ACCESS   read-create
    STATUS       current
    DESCRIPTION  "This field configures the TOS frame priority for profile conformance action.
                  1: change, 2: do not change, 3: not defined.
                  Default is 3, means do not use this field."
    ::= { pvxBandwidthProfileEntry 3 }

-- { pvxBandwidthProfileEntry 4 } obsolete, removed

-- { pvxBandwidthProfileEntry 5 } obsolete, removed

-- { pvxBandwidthProfileEntry 6 } obsolete, removed

-- { pvxBandwidthProfileEntry 7 } obsolete, removed

pvxBWExceedActionChangeDscp OBJECT-TYPE
    SYNTAX    Integer32(-1..63)
    MAX-ACCESS   read-create
    STATUS       current
    DESCRIPTION  "This field configures the DSCP value for profile exceed action.
                  Default is -1, means ignore this action."
    ::= { pvxBandwidthProfileEntry 8 }

-- { pvxBandwidthProfileEntry 9 } obsolete, removed

-- { pvxBandwidthProfileEntry 10 } obsolete, removed

-- { pvxBandwidthProfileEntry 11 } obsolete, removed

-- { pvxBandwidthProfileEntry 12 } obsolete, removed

pvxBWMeterColorAware OBJECT-TYPE
    SYNTAX       PvxQoSColorMode
    MAX-ACCESS   read-create
    STATUS       current
    DESCRIPTION  "This field indicates whether color-aware or color-blind proprety is employed.
                 Default is color-blind."
    ::= { pvxBandwidthProfileEntry 13 }

pvxBWMeterMode OBJECT-TYPE
    SYNTAX       INTEGER { srTCM     (1),
                           trTCM     (2),
                           notUsed   (3)}
    MAX-ACCESS   read-create
    STATUS       current
    DESCRIPTION  "This field configures meter enging schemes. The value can be single-rate Three-Color
                  Marker, or two-rate Three-Color Marker, or not used. Default is not used."
    ::= { pvxBandwidthProfileEntry 14 }

pvxBWMeterCir OBJECT-TYPE
    SYNTAX       Integer32(0..10000000)
    MAX-ACCESS   read-create
    STATUS       current
    DESCRIPTION  "This field defines Committed Information Rate, in kbps."
    DEFVAL       { 1000 }
    ::= { pvxBandwidthProfileEntry 15 }

pvxBWMeterCbs OBJECT-TYPE
    SYNTAX       Integer32(4..256)
    MAX-ACCESS   read-create
    STATUS       current
    DESCRIPTION  "This field defines Committed Burst Size, in kilobytes."
    DEFVAL       { 12 }
    ::= { pvxBandwidthProfileEntry 16 }

pvxBWMeterEir OBJECT-TYPE
    SYNTAX       Integer32(0..32000000)
    MAX-ACCESS   read-create
    STATUS       current
    DESCRIPTION  "This field defines Excess Information Rate, in kbps."
    DEFVAL       { 10000 }
    ::= { pvxBandwidthProfileEntry 17 }

pvxBWMeterEbs OBJECT-TYPE
    SYNTAX       Integer32(0..256)
    MAX-ACCESS   read-create
    STATUS       current
    DESCRIPTION  "This field defines Excess Burst Size, in kilobytes."
    DEFVAL       { 12 }
    ::= { pvxBandwidthProfileEntry 18 }
    
pvxBWSetInternalPriority OBJECT-TYPE
    SYNTAX       Integer32(-1..7)
    MAX-ACCESS   read-create
    STATUS       current
    DESCRIPTION  "This field defines internal priority for policy actions. Default is set to -1 by
                 the switch, which indicates that this fields is ignored."
    ::= { pvxBandwidthProfileEntry 19 }

pvxBWExceedActionSetDEI OBJECT-TYPE
    SYNTAX       INTEGER { set        (1),
                           doNotSet   (2),
                           notUsed    (3)}
    MAX-ACCESS   read-create
    STATUS       current
    DESCRIPTION  "This field configures frame's DEI bit for profile exceed action.
                  1: set, 2: do not set, 3: not defined.
                  Default is 1, means set DEI bit for frames exceed rate."
    ::= { pvxBandwidthProfileEntry 20}

pvxBandwidthProfileRowStatus OBJECT-TYPE
    SYNTAX       RowStatus
    MAX-ACCESS   read-create
    STATUS       current
    DESCRIPTION  ""
    ::= { pvxBandwidthProfileEntry 100 }
    
-----------------------------------------------------------------------
-- pvx Class MAP Profile Table
-----------------------------------------------------------------------
pvxClassMapProfileTable OBJECT-TYPE
    SYNTAX       SEQUENCE OF PVXClassMapProfileEntry
    MAX-ACCESS   not-accessible
    STATUS       current
    DESCRIPTION  "The table configures filter actions for each Class of Service."
    ::= { pvxBridgeProfiles 11 }

pvxClassMapProfileEntry OBJECT-TYPE
    SYNTAX       PVXClassMapProfileEntry
    MAX-ACCESS   not-accessible
    STATUS       current
    DESCRIPTION  "The conceptual row object of the Class MAP Profile Table.

                 Note the pvxClassMapProfileName index is a variable length OCTET STRING
                 object. When encoded as part of the index, it 
                 includes the string length as part of the instance.

                 For example, a profile named 'aaa' is encoded as '3.61.61.61'.

                 For more info on encoding OCTET STRING instances in OID's, 
                 see RFC-2578, section 7.7."
    INDEX        { pvxClassMapProfileName }
    ::= { pvxClassMapProfileTable 1 }

PVXClassMapProfileEntry ::= SEQUENCE { pvxClassMapProfileName           DisplayString,
                                       pvxClassMapType                  INTEGER,
                                       pvxClassMapMatchType             INTEGER,
                                       pvxClassMapCVlanFilter           Integer32,
                                       pvxClassMapSVlanFilter           Integer32,
                                       pvxClassMapCVlanPriFilter        Integer32,
                                       pvxClassMapSVlanPriFilter        Integer32,
                                       pvxClassMapSrcIpFilter           IpAddress,
                                       pvxClassMapSrcIpNetMaskFilter    IpAddress,
                                       pvxClassMapDstIpFilter           IpAddress,
                                       pvxClassMapDstIpNetMaskFilter    IpAddress,
                                       pvxClassMapIpProtocolFilter   	Integer32,
                                       pvxClassMapDscpFilter   	        Integer32,
                                       pvxClassMapL4SrcPortFilter   	Integer32, 
                                       pvxClassMapL4DstPortFilter   	Integer32,
                                       pvxClassMapTcpControlFilter   	Integer32,
                                       pvxClassMapSrcMACAddrFilter      MacAddress,
                                       pvxClassMapDstMACAddrFilter      MacAddress,  
                                       pvxClassMapEtherTypeFilter       Integer32,
                                       pvxClassMapSrcMACMaskFilter      Integer32,
                                       pvxClassMapDstMACMaskFilter      Integer32,
                                       pvxClassMapL4SrcPortEndFilter    Integer32,
                                       pvxClassMapL4DstPortEndFilter    Integer32,
                                       pvxClassMapCVlanEndFilter        Integer32,
                                       pvxClassMapProfileRowStatus      RowStatus }
    
pvxClassMapProfileName OBJECT-TYPE
    SYNTAX       DisplayString (SIZE(1..32))
    MAX-ACCESS   not-accessible
    STATUS       current
    DESCRIPTION  "A string for profile name."
    ::= { pvxClassMapProfileEntry 1 }

pvxClassMapType OBJECT-TYPE
    SYNTAX       INTEGER { ingress-Per-Cos     (1),
                           egress-Per-Cos      (2),
                           service-Map         (3) }
    MAX-ACCESS   read-create
    STATUS       current
    DESCRIPTION  "This field indicates whether this profile is for ingress Class of Service or 
                  egress Class of Service."
    ::= { pvxClassMapProfileEntry 2 }

pvxClassMapMatchType OBJECT-TYPE
    SYNTAX       INTEGER { match-all     (1),
                           match-any     (2)}
    MAX-ACCESS   read-create
    STATUS       current
    DESCRIPTION  "This field defines filter action. It can be match-all, or match any. Default is matchAll. "
    ::= { pvxClassMapProfileEntry 3 }

pvxClassMapCVlanFilter OBJECT-TYPE
    SYNTAX       Integer32(-1..4095)
    MAX-ACCESS   read-create
    STATUS       current
    DESCRIPTION  "This field defines the Customer vlan filter for this class of servcie. 
                  Default is -1, means ignore this field.
                  If pvxClassMapCVlanEndFilter is unused, this value represents a
                  single vlan to match. If pvxClassMapCVlanEndFilter contains a filter
                  value, then this value is the beginning of a range of vlans to match.
                  When a range of vlans is specified, the beginning vlan value MUST 
                  be greater than end value."
    DEFVAL { -1 }
    ::= { pvxClassMapProfileEntry 4 }
    
pvxClassMapSVlanFilter OBJECT-TYPE
    SYNTAX       Integer32(-1..4095)
    MAX-ACCESS   read-only
    STATUS       deprecated
    DESCRIPTION  "This field defines the Service VLAN filter for this class of servcie. 
                  Default is -1, means ignore this field."
    DEFVAL { -1 }
    ::= { pvxClassMapProfileEntry 5 }

pvxClassMapCVlanPriFilter OBJECT-TYPE
    SYNTAX       Integer32(-1..7)
    MAX-ACCESS   read-create
    STATUS       current
    DESCRIPTION  "This field defines the Customer vlan priority filter for this class of servcie.
                  Default is -1, means ignore this field."
    DEFVAL { -1 }
    ::= { pvxClassMapProfileEntry 6 }
    
pvxClassMapSVlanPriFilter OBJECT-TYPE
    SYNTAX       Integer32(-1..7)
    MAX-ACCESS   read-create
    STATUS       current
    DESCRIPTION  "This field defines the Servicre vlan priority filter for this class of servcie. 
                 Default is -1, means ignore this field."
    DEFVAL { -1 }
    ::= { pvxClassMapProfileEntry 7 }

pvxClassMapSrcIpFilter OBJECT-TYPE
    SYNTAX       IpAddress
    MAX-ACCESS   read-create
    STATUS       current
    DESCRIPTION  "This field defines the Source IP filter for this class of servcie. Defult is an empty string."
    ::= { pvxClassMapProfileEntry 8 }
    
pvxClassMapSrcIpNetMaskFilter OBJECT-TYPE
    SYNTAX       IpAddress
    MAX-ACCESS   read-create
    STATUS       current
    DESCRIPTION  "This field defines the Network Mask filter of source IP for this class of servcie. Defult is an empty string."
    ::= { pvxClassMapProfileEntry 9 }
    
pvxClassMapDstIpFilter OBJECT-TYPE
    SYNTAX       IpAddress
    MAX-ACCESS   read-create
    STATUS       current
    DESCRIPTION  "This field defines the Destination IP filter for this class of servcie. Defult is an empty string."
    ::= { pvxClassMapProfileEntry 10 }
    
pvxClassMapDstIpNetMaskFilter OBJECT-TYPE
    SYNTAX       IpAddress
    MAX-ACCESS   read-create
    STATUS       current
    DESCRIPTION  "This field defines the Network Mask filter of destination IP for this class of servcie. Defult is an empty string."
    ::= { pvxClassMapProfileEntry 11 } 

pvxClassMapIpProtocolFilter OBJECT-TYPE
    SYNTAX       Integer32(-1..255)
    MAX-ACCESS   read-create
    STATUS       current
    DESCRIPTION  "This field defines the IP protocol filter for this class of servcie. Default is -1, means ignore this field."
    DEFVAL { -1 }
    ::= { pvxClassMapProfileEntry 12 }

pvxClassMapDscpFilter OBJECT-TYPE
    SYNTAX       Integer32(-1..63)
    MAX-ACCESS   read-create
    STATUS       current
    DESCRIPTION  "This field defines the DSCP filter for this class of servcie. Default is -1, means the field is not used."
    DEFVAL { -1 }
    ::= { pvxClassMapProfileEntry 13 }

pvxClassMapL4SrcPortFilter OBJECT-TYPE
    SYNTAX       Integer32(-1..65535)
    MAX-ACCESS   read-create
    STATUS       current
    DESCRIPTION  "This field defines the Layer 4 source port filter for this class of servcie. 
                  Default is -1, means the field is not used.

                  If pvxClassMapL4SrcPortEndFilter is unused, this value represents a
                  single port to match. If pvxClassMapL4SrcPortEndFilter contains a filter
                  value, then this value is the beginning of a range of ports to match.

                  When a range of ports is specified, the beginning port value MUST be a
                  power of 2."
    DEFVAL { -1 }
    ::= { pvxClassMapProfileEntry 14 }

pvxClassMapL4DstPortFilter OBJECT-TYPE
    SYNTAX       Integer32(-1..65535)
    MAX-ACCESS   read-create
    STATUS       current
    DESCRIPTION  "This field defines the Layer 4 destinatin port filter for this class of servcie.
                  Default is -1, means the field is not used.

                  If pvxClassMapL4DstPortEndFilter is unused, this value represents a
                  single port to match. If pvxClassMapL4SrcPortEndFilter contains a filter
                  value, then this value is the beginning of a range of ports to match.

                  When a range of ports is specified, the beginning port value MUST be a
                  power of 2."
    DEFVAL { -1 }
    ::= { pvxClassMapProfileEntry 15 }

pvxClassMapTcpControlFilter OBJECT-TYPE
    SYNTAX       Integer32(-1..63)
    MAX-ACCESS   read-create
    STATUS       current
    DESCRIPTION  "This field defines the Tcp control filter for this class of servcie.
                 Default is -1, means the field is not used."
    DEFVAL { -1 }
    ::= { pvxClassMapProfileEntry 16 }
    
pvxClassMapSrcMACAddrFilter OBJECT-TYPE
    SYNTAX       MacAddress
    MAX-ACCESS   read-create
    STATUS       current
    DESCRIPTION  "This field defines the Source MAC address filter for this class of servcie. 
                  Default is an empty string."
    ::= { pvxClassMapProfileEntry 17 }

pvxClassMapDstMACAddrFilter OBJECT-TYPE
    SYNTAX       MacAddress
    MAX-ACCESS   read-create
    STATUS       current
    DESCRIPTION  "This field defines the Destination MAC address filter for this class of servcie. 
                 Default is an empty string."
    ::= { pvxClassMapProfileEntry 18 }

pvxClassMapEtherTypeFilter OBJECT-TYPE
    SYNTAX       Integer32(-1..65535)
    MAX-ACCESS   read-create
    STATUS       current
    DESCRIPTION  "This field defines the ethernet address type filter for this class of servcie. 
                 Default is -1, means the filter is not used."
    DEFVAL { -1 }
    ::= { pvxClassMapProfileEntry 19 }
    
pvxClassMapSrcMACMaskFilter OBJECT-TYPE
    SYNTAX       Integer32(0..48)
    MAX-ACCESS   read-create
    STATUS       current
    DESCRIPTION  "This field defines the source MAC address mask. Default is set to 0, which indicates
                  the source MAC address filter is not used."
    ::= { pvxClassMapProfileEntry 20 }
    
pvxClassMapDstMACMaskFilter OBJECT-TYPE
    SYNTAX       Integer32(0..48)
    MAX-ACCESS   read-create
    STATUS       current
    DESCRIPTION  "This field defines the destination MAC address mask. Default is set to 0, which indicates
                  the destination MAC address filter is not used."
    ::= { pvxClassMapProfileEntry 21 }

pvxClassMapL4SrcPortEndFilter OBJECT-TYPE
    SYNTAX       Integer32(-1 | 3 | 7 | 15 | 31 | 63 | 127 | 255 | 511 | 1023 | 2047 | 4095 | 8191 | 16383 | 32767 | 65535 )
    MAX-ACCESS   read-create
    STATUS       current
    DESCRIPTION  "This field defines the Layer 4 source port filter for this class of service. 
                  Default is -1, means the field is not used.

                  When specified this value MUST be greater than the value of
                  pvxClassMapL4SrcPortFilter"
    DEFVAL  { -1 }
    ::= { pvxClassMapProfileEntry 22 }

pvxClassMapL4DstPortEndFilter OBJECT-TYPE
    SYNTAX       Integer32(-1 | 3 | 7 | 15 | 31 | 63 | 127 | 255 | 511 | 1023 | 2047 | 4095 | 8191 | 16383 | 32767 | 65535 )
    MAX-ACCESS   read-create
    STATUS       current
    DESCRIPTION  "This field defines the Layer 4 destination port filter for this class of service.
                  Default is -1, means the field is not used.

                  When specified this value MUST be greater than the value of
                  pvxClassMapL4DstPortFilter"
    DEFVAL  { -1 }
    ::= { pvxClassMapProfileEntry 23 }
           
pvxClassMapCVlanEndFilter OBJECT-TYPE
    SYNTAX       Integer32(-1..4095)
    MAX-ACCESS   read-create
    STATUS       current
    DESCRIPTION  "This field s used to define end point of range of C-VLANs which will
                  be part of this class of service.
                  Default is -1, means ignore this field."
    DEFVAL  { -1 }
    ::= { pvxClassMapProfileEntry 24 }
    
pvxClassMapProfileRowStatus OBJECT-TYPE
    SYNTAX       RowStatus
    MAX-ACCESS   read-create
    STATUS       current
    DESCRIPTION  ""
    ::= { pvxClassMapProfileEntry 100 }  

-----------------------------------------------------------------------
-- pvx Policy Map Profile Table
-----------------------------------------------------------------------
pvxPolicyMapProfileTable OBJECT-TYPE
    SYNTAX       SEQUENCE OF PVXPolicyMapProfileEntry
    MAX-ACCESS   not-accessible
    STATUS       current
    DESCRIPTION  "Policy Map Profile Table."
    ::= { pvxBridgeProfiles 12 }

pvxPolicyMapProfileEntry OBJECT-TYPE
    SYNTAX       PVXPolicyMapProfileEntry
    MAX-ACCESS   not-accessible
    STATUS       current
    DESCRIPTION  "This table contains Class profile identifier to policy identifier mapping.
                  One policy identifier can be associated with multiple Class profiles.

                  Note that both pvxPolicyMapPolicyName and pvxPolicyMapClassMapName 
                  indices are variable length OCTET STRING
                  objects. When encoded as part of the index, it 
                  includes the string length as part of the instance.

                  For example, a policy named 'aaa' is encoded as '3.97.97.97' (decimal).

                  For more info on encoding OCTET STRING instances in OID's, 
                  see RFC-2578, section 7.7.
                  "
    INDEX        { pvxPolicyMapPolicyName,
                   pvxPolicyMapClassMapName }
    ::= { pvxPolicyMapProfileTable 1 }

PVXPolicyMapProfileEntry ::= SEQUENCE {  pvxPolicyMapPolicyName       DisplayString,
                                         pvxPolicyMapClassMapName     DisplayString,
                                         pvxPolicyMapBWProfileName    DisplayString,
                                         pvxPolicyMapProfileRowStatus RowStatus }
    
pvxPolicyMapPolicyName OBJECT-TYPE
    SYNTAX       DisplayString (SIZE(1..32))
    MAX-ACCESS   not-accessible
    STATUS       current
    DESCRIPTION  "The policy map profile name string."
    ::= { pvxPolicyMapProfileEntry 1 }

pvxPolicyMapClassMapName OBJECT-TYPE
    SYNTAX       DisplayString (SIZE(1..32))
    MAX-ACCESS   not-accessible
    STATUS       current
    DESCRIPTION  "The class map profile applied to this policy."
    ::= { pvxPolicyMapProfileEntry 2 }
    
pvxPolicyMapBWProfileName OBJECT-TYPE
    SYNTAX       DisplayString (SIZE(0..32))
    MAX-ACCESS   read-create
    STATUS       current
    DESCRIPTION  "The bandwidth profile used for this policy. For ClassMap profiles of
                  type service-Map, this parameter MUST be an empty string. For
                  all other ClassMap profile types, the object MUST contain the 
                  name of a valid Bandwidth Profile name."
    DEFVAL {""}
    ::= { pvxPolicyMapProfileEntry 3 }
    
pvxPolicyMapProfileRowStatus OBJECT-TYPE
    SYNTAX       RowStatus
    MAX-ACCESS   read-create
    STATUS       current
    DESCRIPTION  ""
    ::= { pvxPolicyMapProfileEntry 100 } 



-----------------------------------------------------------------------
-- Control Frame Profile Table  (string index version)
-----------------------------------------------------------------------
pvxControlFrameProfileTable OBJECT-TYPE
    SYNTAX       SEQUENCE OF PVXControlFrameProfileEntry
    MAX-ACCESS   not-accessible
    STATUS       current
    DESCRIPTION  "This table is used to configure the Layer 2 control profile on a 
                  particular virtual switch."
    ::= { pvxBridgeProfiles 13 }

pvxControlFrameProfileEntry OBJECT-TYPE
    SYNTAX       PVXControlFrameProfileEntry
    MAX-ACCESS   not-accessible
    STATUS       current
    DESCRIPTION  "The conceptual row object of the Control Frame profile Table.

                 Note the pvxControlFrameProfileTable index is a variable length OCTET STRING
                 object. When encoded as part of the index, it 
                 includes the string length as part of the instance.

                 For example, a profile named 'aaa' is encoded as '3.61.61.61'.

                 For more info on encoding OCTET STRING instances in OID's, 
                 see RFC-2578, section 7.7."
    INDEX        { pvxControlFrameProfileName }
    ::= { pvxControlFrameProfileTable 1 }

PVXControlFrameProfileEntry ::= SEQUENCE { pvxControlFrameProfileName      ProfileNameType,
                                           pvxControlFrameProfileLacp      ProtocolActionType,
                                     	   pvxControlFrameProfileStp   	   ProtocolActionType,
                                     	   pvxControlFrameProfileDot1x 	   ProtocolActionType,
                                     	   pvxControlFrameProfileGvrp      ProtocolActionType,
                                     	   pvxControlFrameProfileGmrp      ProtocolActionType,
                                     	   pvxControlFrameProfileLldp      ProtocolActionType,
                                     	   pvxControlFrameProfileRowStatus RowStatus }


pvxControlFrameProfileName OBJECT-TYPE
    SYNTAX       ProfileNameType
    MAX-ACCESS   read-create
    STATUS       current
    DESCRIPTION  "Control frame profile name string."
    ::= { pvxControlFrameProfileEntry 1 }
    
pvxControlFrameProfileLacp OBJECT-TYPE
    SYNTAX       ProtocolActionType
    MAX-ACCESS   read-create
    STATUS       current
    DESCRIPTION  "This attributes defined the control action to LACP protocol."
    ::= { pvxControlFrameProfileEntry 2 }

pvxControlFrameProfileStp OBJECT-TYPE
    SYNTAX       ProtocolActionType
    MAX-ACCESS   read-create
    STATUS       current
    DESCRIPTION  "This attributes defined the control action to STP protocol."
    ::= { pvxControlFrameProfileEntry 3 }

pvxControlFrameProfileDot1x OBJECT-TYPE
    SYNTAX       ProtocolActionType
    MAX-ACCESS   read-create
    STATUS       current
    DESCRIPTION  "This attributes defined the control action to Dot1x protocol."
    ::= { pvxControlFrameProfileEntry 4 }

pvxControlFrameProfileGvrp OBJECT-TYPE
    SYNTAX       ProtocolActionType
    MAX-ACCESS   read-create
    STATUS       current
    DESCRIPTION  "This attributes defined the control action to GVRP protocol."
    ::= { pvxControlFrameProfileEntry 5 }

pvxControlFrameProfileGmrp OBJECT-TYPE
    SYNTAX       ProtocolActionType
    MAX-ACCESS   read-create
    STATUS       current
    DESCRIPTION  "This attributes defined the control action to GMRP protocol."
    ::= { pvxControlFrameProfileEntry 6 }

pvxControlFrameProfileLldp OBJECT-TYPE
    SYNTAX       ProtocolActionType
    MAX-ACCESS   read-create
    STATUS       current
    DESCRIPTION  "This attributes defined the control action to LLDP protocol."
    ::= { pvxControlFrameProfileEntry 7 }

pvxControlFrameProfileRowStatus OBJECT-TYPE
    SYNTAX       RowStatus 
    MAX-ACCESS   read-create
    STATUS       current
    DESCRIPTION  ""
    ::= { pvxControlFrameProfileEntry 100 }


-----------------------------------------------------------------------
-- Tunnel MAC Address Profile Table  (string index version)
-----------------------------------------------------------------------

pvxTunnelMacAddrProfileTable OBJECT-TYPE
    SYNTAX       SEQUENCE OF PVXTunnelMacAddrProfileEntry
    MAX-ACCESS   not-accessible
    STATUS       current
    DESCRIPTION  "This table is used to control L2 tunneling Mac addresses."
    ::= { pvxBridgeProfiles 14 }


pvxTunnelMacAddrProfileEntry OBJECT-TYPE
    SYNTAX       PVXTunnelMacAddrProfileEntry
    MAX-ACCESS   not-accessible
    STATUS       current
    DESCRIPTION  "The conceptual row object of the Tunnel MAC Address Profile Table

                 Note the pvxTMAPName index is a variable length OCTET STRING
                 object. When encoded as part of the index, it 
                 includes the string length as part of the instance.

                 For example, a profile named 'aaa' is encoded as '3.61.61.61'.

                 For more info on encoding OCTET STRING instances in OID's, 
                 see RFC-2578, section 7.7."
    INDEX        { pvxTMAPName }
    ::= { pvxTunnelMacAddrProfileTable 1 }

PVXTunnelMacAddrProfileEntry ::= SEQUENCE {pvxTMAPName              ProfileNameType,
                                           pvxTMAPDot1xTunnMacAddr  MacAddress,  
                                           pvxTMAPLacpTunnMacAddr   MacAddress,
                                           pvxTMAPStpTunnMacAddr    MacAddress,
                                           pvxTMAPGvrpTunnMacAddr   MacAddress,
                                           pvxTMAPGmrpTunnMacAddr   MacAddress,
                                           pvxTMAPLldpTunnMacAddr   MacAddress,
                                           pvxTMAPRowStatus         RowStatus }

pvxTMAPName OBJECT-TYPE
    SYNTAX       ProfileNameType
    MAX-ACCESS   read-create
    STATUS       current
    DESCRIPTION  "Tunnel MAC address profile name string."
    ::= { pvxTunnelMacAddrProfileEntry 1 }
    
pvxTMAPDot1xTunnMacAddr OBJECT-TYPE
    SYNTAX       MacAddress 
    MAX-ACCESS   read-create
    STATUS       current
    DESCRIPTION  ""
    ::= { pvxTunnelMacAddrProfileEntry 2 }

pvxTMAPLacpTunnMacAddr OBJECT-TYPE
    SYNTAX       MacAddress 
    MAX-ACCESS   read-create
    STATUS       current
    DESCRIPTION  ""
    ::= { pvxTunnelMacAddrProfileEntry 3 }

pvxTMAPStpTunnMacAddr OBJECT-TYPE
    SYNTAX       MacAddress
    MAX-ACCESS   read-create
    STATUS       current
    DESCRIPTION  ""
    ::= { pvxTunnelMacAddrProfileEntry 4 }

pvxTMAPGvrpTunnMacAddr OBJECT-TYPE
    SYNTAX       MacAddress
    MAX-ACCESS   read-create
    STATUS       current
    DESCRIPTION  ""
    ::= { pvxTunnelMacAddrProfileEntry 5 }
    
pvxTMAPGmrpTunnMacAddr OBJECT-TYPE
    SYNTAX       MacAddress
    MAX-ACCESS   read-create
    STATUS       current
    DESCRIPTION  ""
    ::= { pvxTunnelMacAddrProfileEntry 6 }

pvxTMAPLldpTunnMacAddr OBJECT-TYPE
    SYNTAX       MacAddress
    MAX-ACCESS   read-create
    STATUS       current
    DESCRIPTION  ""
    ::= { pvxTunnelMacAddrProfileEntry 7 }

pvxTMAPRowStatus OBJECT-TYPE
    SYNTAX       RowStatus 
    MAX-ACCESS   read-create
    STATUS       current
    DESCRIPTION  ""
    ::= { pvxTunnelMacAddrProfileEntry 100 }

-----------------------------------------------------------------------
-- SLA measurement Profile Table  
-----------------------------------------------------------------------

pvxSLAMeasurementProfileTable OBJECT-TYPE
    SYNTAX       SEQUENCE OF PVXSLAMeasurementProfileEntry
    MAX-ACCESS   not-accessible
    STATUS       current
    DESCRIPTION  "This table is used to control Ethernet service SLA measurement."
    ::= { pvxBridgeProfiles 15 }


pvxSLAMeasurementProfileEntry OBJECT-TYPE
    SYNTAX       PVXSLAMeasurementProfileEntry
    MAX-ACCESS   not-accessible
    STATUS       current
    DESCRIPTION  "The conceptual row object for the SLA measurement profile."
    INDEX        { pvxSLAMsmtProfileName }
    ::= { pvxSLAMeasurementProfileTable 1 }

PVXSLAMeasurementProfileEntry ::= SEQUENCE {pvxSLAMsmtProfileName                ProfileNameType,
                                           pvxSLAMsmtThresholdFarEndLossRatio    FixedX1000,  
                                           pvxSLAMsmtThresholdNearEndLossRatio   FixedX1000,
                                           pvxSLAMsmtThresholdDelayMaximum       Unsigned32,
                                           pvxSLAMsmtThresholdDelayAverage       Unsigned32,
                                           pvxSLAMsmtThresholdDelayVarMaximum    Unsigned32,
                                           pvxSLAMsmtThresholdDelayVarAverage    Unsigned32,
                                           pvxSLAMsmtMonitorPeriod               MonitorPeriodType,
                                           pvxSLAMsmtRowStatus                   RowStatus }

pvxSLAMsmtProfileName OBJECT-TYPE
    SYNTAX       ProfileNameType
    MAX-ACCESS   not-accessible
    STATUS       current
    DESCRIPTION  "SLA measurement profile name string."
    ::= { pvxSLAMeasurementProfileEntry 1 }
    
pvxSLAMsmtThresholdFarEndLossRatio OBJECT-TYPE
    SYNTAX       FixedX1000
    MAX-ACCESS   read-create
    STATUS       current
    DESCRIPTION  "Threshold for the far end farme loss ratio.
                  It is a percentage value multiply with one thousand."
    ::= { pvxSLAMeasurementProfileEntry 2 }
    
pvxSLAMsmtThresholdNearEndLossRatio OBJECT-TYPE
    SYNTAX       FixedX1000
    MAX-ACCESS   read-create
    STATUS       current
    DESCRIPTION  "Threshold for the near end farme loss ratio.
                  It is a percentage value multiply with one thousand."
    ::= { pvxSLAMeasurementProfileEntry 3 }
    
pvxSLAMsmtThresholdDelayMaximum OBJECT-TYPE
    SYNTAX       Unsigned32
    MAX-ACCESS   read-create
    STATUS       current
    DESCRIPTION  "Two-way delay maximum in microseconds."
    ::= { pvxSLAMeasurementProfileEntry 4 }
    
pvxSLAMsmtThresholdDelayAverage OBJECT-TYPE
    SYNTAX       Unsigned32
    MAX-ACCESS   read-create
    STATUS       current
    DESCRIPTION  "Two-way delay average in microseconds."
    ::= { pvxSLAMeasurementProfileEntry 5 }
    
pvxSLAMsmtThresholdDelayVarMaximum OBJECT-TYPE
    SYNTAX       Unsigned32
    MAX-ACCESS   read-create
    STATUS       current
    DESCRIPTION  "Two-way delay variation maximum in microseconds."
    ::= { pvxSLAMeasurementProfileEntry 6 }
    
pvxSLAMsmtThresholdDelayVarAverage OBJECT-TYPE
    SYNTAX       Unsigned32
    MAX-ACCESS   read-create
    STATUS       current
    DESCRIPTION  "Two-way delay variation average in microseconds."
    ::= { pvxSLAMeasurementProfileEntry 7 }
    
pvxSLAMsmtMonitorPeriod OBJECT-TYPE
    SYNTAX       MonitorPeriodType
    MAX-ACCESS   read-create
    STATUS       current
    DESCRIPTION  "Monitor period, 15-min or 24-hour."
    ::= { pvxSLAMeasurementProfileEntry 8 }
    
pvxSLAMsmtRowStatus OBJECT-TYPE
    SYNTAX       RowStatus 
    MAX-ACCESS   read-create
    STATUS       current
    DESCRIPTION  ""
    ::= { pvxSLAMeasurementProfileEntry 100 }
    
-----------------------------------------------------------------------
-- Objects used to retrieve current Performance Monitoring
-- statistics for PacketVX Switch-level MSTP and MSTP Instance Objects
-----------------------------------------------------------------------

pvxMSTPCrntPMTable OBJECT-TYPE
    SYNTAX       SEQUENCE OF PvxMSTPCrntPMEntry
    MAX-ACCESS   not-accessible
    STATUS       current
    DESCRIPTION  "A table of current performance monitoring statistics collected
                  for the PacketVX switch-level MSTP and MSTP instance objects."
    ::= { performance 32 }


pvxMSTPCrntPMEntry OBJECT-TYPE
    SYNTAX       PvxMSTPCrntPMEntry
    MAX-ACCESS   not-accessible
    STATUS       current
    DESCRIPTION  "The row entry object of the PacketVX MSTP current
                  performance monitoring table. Each row of this table contains
                  a full set of MSTP PM statistics and related data for a current
                  measurement interval for a given PVX switch or MSTP instance."
    INDEX        { pvxMSTPCrntPMSwitchIdx,
    			   pvxMSTPCrntPMXstIdx,
    			   pvxMSTPCrntPMIntervalTypeIdx }
    ::= { pvxMSTPCrntPMTable 1 }


PvxMSTPCrntPMEntry ::= SEQUENCE { pvxMSTPCrntPMSwitchIdx        INTEGER,
                                  pvxMSTPCrntPMXstIdx           INTEGER,
                                  pvxMSTPCrntPMIntervalTypeIdx  PMIntervalType,
                                  pvxMSTPCrntPMRCCCValue        Unsigned64,
                                  pvxMSTPCrntPMRCCCTimeStamp    DateAndTime,
                                  pvxMSTPCrntPMRCCCValidity     PMValidity,
                                  pvxMSTPCrntPMRCCCInitialize   InitializeCmd,
                                  pvxMSTPCrntPMTCCValue         Unsigned64,
                                  pvxMSTPCrntPMTCCTimeStamp     DateAndTime,
                                  pvxMSTPCrntPMTCCValidity      PMValidity,
                                  pvxMSTPCrntPMTCCInitialize    InitializeCmd,
                                  pvxMSTPCrntPMNRBCValue        Unsigned64,
                                  pvxMSTPCrntPMNRBCTimeStamp    DateAndTime,
                                  pvxMSTPCrntPMNRBCValidity     PMValidity,
                                  pvxMSTPCrntPMNRBCInitialize   InitializeCmd }
                                  
                                  
pvxMSTPCrntPMSwitchIdx OBJECT-TYPE
   	SYNTAX       INTEGER(1..11)
   	MAX-ACCESS   not-accessible
   	STATUS       current
   	DESCRIPTION  "This object represents the particular switch id."
    ::= {pvxMSTPCrntPMEntry 1 }


pvxMSTPCrntPMXstIdx OBJECT-TYPE
    SYNTAX       INTEGER (0..64)
    MAX-ACCESS   not-accessible
    STATUS       current
    DESCRIPTION  "The instance number of the MSTP instance. For the
    			  global MSTP object on the switch, this index object
    			  is set to 0."
    ::= {pvxMSTPCrntPMEntry 2 }


pvxMSTPCrntPMIntervalTypeIdx OBJECT-TYPE
    SYNTAX       PMIntervalType
    MAX-ACCESS   not-accessible
    STATUS       current
    DESCRIPTION  "The type of PM bin according to interval length."
    ::= { pvxMSTPCrntPMEntry 3 }


pvxMSTPCrntPMRCCCValue OBJECT-TYPE
    SYNTAX       Unsigned64
    MAX-ACCESS   read-only
    STATUS       current
    DESCRIPTION  "The CIST region configuration change count. This
    			  object applies only to the global MSTP object on
    			  the switch."
    ::= { pvxMSTPCrntPMEntry 4 }


pvxMSTPCrntPMRCCCTimeStamp OBJECT-TYPE
    SYNTAX       DateAndTime
    MAX-ACCESS   read-only
    STATUS       current
    DESCRIPTION  "The date and time stamp of the CIST region configuration
    			  change count value."
    ::= { pvxMSTPCrntPMEntry 5 }


pvxMSTPCrntPMRCCCValidity OBJECT-TYPE
    SYNTAX       PMValidity
    MAX-ACCESS   read-only
    STATUS       current
    DESCRIPTION  "Indicates the validity of the provided CIST region configuration
    			  change count value."
    ::= { pvxMSTPCrntPMEntry 6 }


pvxMSTPCrntPMRCCCInitialize OBJECT-TYPE
    SYNTAX       InitializeCmd
    MAX-ACCESS   read-write
    STATUS       current
    DESCRIPTION  "Used to initialize the value of the pvxMSTPCrntPMRCCCValue object
                  to 0."
    ::= { pvxMSTPCrntPMEntry 7 }


pvxMSTPCrntPMTCCValue OBJECT-TYPE
    SYNTAX       Unsigned64
    MAX-ACCESS   read-only
    STATUS       current
    DESCRIPTION  "The CIST/MSTI region configuration change count."
    ::= { pvxMSTPCrntPMEntry 8 }


pvxMSTPCrntPMTCCTimeStamp OBJECT-TYPE
    SYNTAX       DateAndTime
    MAX-ACCESS   read-only
    STATUS       current
    DESCRIPTION  "The date and time stamp of the CIST/MSTI region
    			  configuration change count value."
    ::= { pvxMSTPCrntPMEntry 9 }


pvxMSTPCrntPMTCCValidity OBJECT-TYPE
    SYNTAX       PMValidity
    MAX-ACCESS   read-only
    STATUS       current
    DESCRIPTION  "Indicates the validity of the provided CIST/MSTI
    			  region configuration change count value."
    ::= { pvxMSTPCrntPMEntry 10 }


pvxMSTPCrntPMTCCInitialize OBJECT-TYPE
    SYNTAX       InitializeCmd
    MAX-ACCESS   read-write
    STATUS       current
    DESCRIPTION  "Used to initialize the value of the pvxMSTPCrntPMTCCValue object
                  to 0."
    ::= { pvxMSTPCrntPMEntry 11 }


pvxMSTPCrntPMNRBCValue OBJECT-TYPE
    SYNTAX       Unsigned64
    MAX-ACCESS   read-only
    STATUS       current
    DESCRIPTION  "The CIST/MSTI new root bridge count."
    ::= { pvxMSTPCrntPMEntry 12 }


pvxMSTPCrntPMNRBCTimeStamp OBJECT-TYPE
    SYNTAX       DateAndTime
    MAX-ACCESS   read-only
    STATUS       current
    DESCRIPTION  "The date and time stamp of the CIST/MSTI new
    			  root bridge count value."
    ::= { pvxMSTPCrntPMEntry 13 }


pvxMSTPCrntPMNRBCValidity OBJECT-TYPE
    SYNTAX       PMValidity
    MAX-ACCESS   read-only
    STATUS       current
    DESCRIPTION  "Indicates the validity of the provided CIST/MSTI
    			  new root bridge count value."
    ::= { pvxMSTPCrntPMEntry 14 }


pvxMSTPCrntPMNRBCInitialize OBJECT-TYPE
    SYNTAX       InitializeCmd
    MAX-ACCESS   read-write
    STATUS       current
    DESCRIPTION  "Used to initialize the value of the pvxMSTPCrntPMNRBCValue object
                  to 0."
    ::= { pvxMSTPCrntPMEntry 15 }



-----------------------------------------------------------------------
-- Objects used to retrieve historical Performance Monitoring
-- statistics for PacketVX Switch-level MSTP and MSTP Instance Objects
-----------------------------------------------------------------------

pvxMSTPHistPMTable OBJECT-TYPE
    SYNTAX       SEQUENCE OF PvxMSTPHistPMEntry
    MAX-ACCESS   not-accessible
    STATUS       current
    DESCRIPTION  "A table of historical performance monitoring statistics collected
                  for the PacketVX switch-level MSTP and MSTP instance objects."
    ::= { performance 33 }


pvxMSTPHistPMEntry OBJECT-TYPE
    SYNTAX       PvxMSTPHistPMEntry
    MAX-ACCESS   not-accessible
    STATUS       current
    DESCRIPTION  "The row entry object of the PacketVX MSTP current
                  performance monitoring table. Each row of this table contains
                  a full set of MSTP PM statistics and related data for a historical
                  measurement interval for a given PVX switch or MSTP instance."
    INDEX        { pvxMSTPHistPMSwitchIdx,
    			   pvxMSTPHistPMXstIdx,
    			   pvxMSTPHistPMIntervalTypeIdx,
    			   pvxMSTPHistPMIntervalIdx }
    ::= { pvxMSTPHistPMTable 1 }


PvxMSTPHistPMEntry ::= SEQUENCE { pvxMSTPHistPMSwitchIdx        INTEGER,
                                  pvxMSTPHistPMXstIdx           INTEGER,
                                  pvxMSTPHistPMIntervalTypeIdx  PMIntervalType,
                                  pvxMSTPHistPMIntervalIdx      INTEGER,
                                  pvxMSTPHistPMRCCCValue        Unsigned64,
                                  pvxMSTPHistPMRCCCTimeStamp    DateAndTime,
                                  pvxMSTPHistPMRCCCValidity     PMValidity,
                                  pvxMSTPHistPMRCCCInitialize   InitializeCmd,
                                  pvxMSTPHistPMTCCValue         Unsigned64,
                                  pvxMSTPHistPMTCCTimeStamp     DateAndTime,
                                  pvxMSTPHistPMTCCValidity      PMValidity,
                                  pvxMSTPHistPMTCCInitialize    InitializeCmd,
                                  pvxMSTPHistPMNRBCValue        Unsigned64,
                                  pvxMSTPHistPMNRBCTimeStamp    DateAndTime,
                                  pvxMSTPHistPMNRBCValidity     PMValidity,
                                  pvxMSTPHistPMNRBCInitialize   InitializeCmd }
                                  
                                  
pvxMSTPHistPMSwitchIdx OBJECT-TYPE
   	SYNTAX       INTEGER(1..11)
   	MAX-ACCESS   not-accessible
   	STATUS       current
   	DESCRIPTION  "This object represents the particular switch id."
    ::= {pvxMSTPHistPMEntry 1 }


pvxMSTPHistPMXstIdx OBJECT-TYPE
    SYNTAX       INTEGER (0..64)
    MAX-ACCESS   not-accessible
    STATUS       current
    DESCRIPTION  "The instance number of the MSTP instance. For the
    			  global MSTP object on the switch, this index object
    			  is set to 0."
    ::= {pvxMSTPHistPMEntry 2 }


pvxMSTPHistPMIntervalTypeIdx OBJECT-TYPE
    SYNTAX       PMIntervalType
    MAX-ACCESS   not-accessible
    STATUS       current
    DESCRIPTION  "The type of PM bin according to interval length."
    ::= { pvxMSTPHistPMEntry 3 }


pvxMSTPHistPMIntervalIdx OBJECT-TYPE
    SYNTAX       INTEGER (1..96)
    MAX-ACCESS   not-accessible
    STATUS       current
    DESCRIPTION  "The specific PM bin number. The range is 1 to 96 for the
                  15-minute historical bins. For the 1-day historical bin, the
                  value is 1."
    ::= { pvxMSTPHistPMEntry 4 }


pvxMSTPHistPMRCCCValue OBJECT-TYPE
    SYNTAX       Unsigned64
    MAX-ACCESS   read-only
    STATUS       current
    DESCRIPTION  "The CIST region configuration change count. This
    			  object applies only to the global MSTP object on
    			  the switch."
    ::= { pvxMSTPHistPMEntry 5 }


pvxMSTPHistPMRCCCTimeStamp OBJECT-TYPE
    SYNTAX       DateAndTime
    MAX-ACCESS   read-only
    STATUS       current
    DESCRIPTION  "The date and time stamp of the CIST region configuration
    			  change count value."
    ::= { pvxMSTPHistPMEntry 6 }


pvxMSTPHistPMRCCCValidity OBJECT-TYPE
    SYNTAX       PMValidity
    MAX-ACCESS   read-only
    STATUS       current
    DESCRIPTION  "Indicates the validity of the provided CIST region configuration
    			  change count value."
    ::= { pvxMSTPHistPMEntry 7 }


pvxMSTPHistPMRCCCInitialize OBJECT-TYPE
    SYNTAX       InitializeCmd
    MAX-ACCESS   read-write
    STATUS       current
    DESCRIPTION  "Used to initialize the value of the pvxMSTPHistPMRCCCValue object
                  to 0."
    ::= { pvxMSTPHistPMEntry 8 }


pvxMSTPHistPMTCCValue OBJECT-TYPE
    SYNTAX       Unsigned64
    MAX-ACCESS   read-only
    STATUS       current
    DESCRIPTION  "The CIST/MSTI region configuration change count."
    ::= { pvxMSTPHistPMEntry 9 }


pvxMSTPHistPMTCCTimeStamp OBJECT-TYPE
    SYNTAX       DateAndTime
    MAX-ACCESS   read-only
    STATUS       current
    DESCRIPTION  "The date and time stamp of the CIST/MSTI region
    			  configuration change count value."
    ::= { pvxMSTPHistPMEntry 10 }


pvxMSTPHistPMTCCValidity OBJECT-TYPE
    SYNTAX       PMValidity
    MAX-ACCESS   read-only
    STATUS       current
    DESCRIPTION  "Indicates the validity of the provided CIST/MSTI
    			  region configuration change count value."
    ::= { pvxMSTPHistPMEntry 11 }


pvxMSTPHistPMTCCInitialize OBJECT-TYPE
    SYNTAX       InitializeCmd
    MAX-ACCESS   read-write
    STATUS       current
    DESCRIPTION  "Used to initialize the value of the pvxMSTPHistPMTCCValue object
                  to 0."
    ::= { pvxMSTPHistPMEntry 12 }


pvxMSTPHistPMNRBCValue OBJECT-TYPE
    SYNTAX       Unsigned64
    MAX-ACCESS   read-only
    STATUS       current
    DESCRIPTION  "The CIST/MSTI new root bridge count."
    ::= { pvxMSTPHistPMEntry 13 }


pvxMSTPHistPMNRBCTimeStamp OBJECT-TYPE
    SYNTAX       DateAndTime
    MAX-ACCESS   read-only
    STATUS       current
    DESCRIPTION  "The date and time stamp of the CIST/MSTI new
    			  root bridge count value."
    ::= { pvxMSTPHistPMEntry 14 }


pvxMSTPHistPMNRBCValidity OBJECT-TYPE
    SYNTAX       PMValidity
    MAX-ACCESS   read-only
    STATUS       current
    DESCRIPTION  "Indicates the validity of the provided CIST/MSTI
    			  new root bridge count value."
    ::= { pvxMSTPHistPMEntry 15 }


pvxMSTPHistPMNRBCInitialize OBJECT-TYPE
    SYNTAX       InitializeCmd
    MAX-ACCESS   read-write
    STATUS       current
    DESCRIPTION  "Used to initialize the value of the pvxMSTPHistPMNRBCValue object
                  to 0."
    ::= { pvxMSTPHistPMEntry 16 }


-----------------------------------------------------------------------
-- Objects used to retrieve current Performance Monitoring
-- statistics for PacketVX MSTP Port and MSTP Instance Port Objects
-----------------------------------------------------------------------

pvxMSTPPortCrntPMTable OBJECT-TYPE
    SYNTAX       SEQUENCE OF PvxMSTPPortCrntPMEntry
    MAX-ACCESS   not-accessible
    STATUS       current
    DESCRIPTION  "A table of current performance monitoring statistics collected
                  for PacketVX MSTP Port and MSTP Instance Port objects."
    ::= { performance 34 }


pvxMSTPPortCrntPMEntry OBJECT-TYPE
    SYNTAX       PvxMSTPPortCrntPMEntry
    MAX-ACCESS   not-accessible
    STATUS       current
    DESCRIPTION  "The row entry object of the PacketVX MSTP Port current
                  performance monitoring table. Each row of this table contains
                  a full set of PM statistics and related data for a current
                  measurement interval for a given PVX MSTP Port or MSTP Instance Port."
    INDEX        { pvxMSTPPortCrntPMSwitchIdx,
				   pvxMSTPPortCrntPMShelfIdx,
				   pvxMSTPPortCrntPMSlotIdx,
               	   pvxMSTPPortCrntPMTypeIdx,
    			   pvxMSTPPortCrntPMXstIdx,
               	   pvxMSTPPortCrntPMIdx,
    			   pvxMSTPPortCrntPMIntervalTypeIdx }
    ::= { pvxMSTPPortCrntPMTable 1 }


PvxMSTPPortCrntPMEntry ::= SEQUENCE { pvxMSTPPortCrntPMSwitchIdx              INTEGER,
				                      pvxMSTPPortCrntPMShelfIdx       	      INTEGER,
				                      pvxMSTPPortCrntPMSlotIdx        	      INTEGER,
				                      pvxMSTPPortCrntPMTypeIdx		          PvxPortType,
                                      pvxMSTPPortCrntPMXstIdx                 INTEGER,
                        	          pvxMSTPPortCrntPMIdx         		      INTEGER,
                                      pvxMSTPPortCrntPMIntervalTypeIdx        PMIntervalType,
                                      pvxMSTPPortCrntPMFWDTRValue             Unsigned64,
                                      pvxMSTPPortCrntPMFWDTRTimeStamp         DateAndTime,
                                      pvxMSTPPortCrntPMFWDTRValidity          PMValidity,
                                      pvxMSTPPortCrntPMFWDTRInitialize        InitializeCmd,
                                      pvxMSTPPortCrntPMPMCValue               Unsigned64,
                                      pvxMSTPPortCrntPMPMCTimeStamp           DateAndTime,
                                      pvxMSTPPortCrntPMPMCValidity            PMValidity,
                                      pvxMSTPPortCrntPMPMCInitialize          InitializeCmd,
                                      pvxMSTPPortCrntPMBPDURXValue            Unsigned64,
                                      pvxMSTPPortCrntPMBPDURXTimeStamp        DateAndTime,
                                      pvxMSTPPortCrntPMBPDURXValidity         PMValidity,
                                      pvxMSTPPortCrntPMBPDURXInitialize       InitializeCmd,
                                      pvxMSTPPortCrntPMBPDUTXValue            Unsigned64,
                                      pvxMSTPPortCrntPMBPDUTXTimeStamp        DateAndTime,
                                      pvxMSTPPortCrntPMBPDUTXValidity         PMValidity,
                                      pvxMSTPPortCrntPMBPDUTXInitialize       InitializeCmd,
                                      pvxMSTPPortCrntPMBPDUCFGRXValue         Unsigned64,
                                      pvxMSTPPortCrntPMBPDUCFGRXTimeStamp     DateAndTime,
                                      pvxMSTPPortCrntPMBPDUCFGRXValidity      PMValidity,
                                      pvxMSTPPortCrntPMBPDUCFGRXInitialize    InitializeCmd,
                                      pvxMSTPPortCrntPMBPDUCFGTXValue         Unsigned64,
                                      pvxMSTPPortCrntPMBPDUCFGTXTimeStamp     DateAndTime,
                                      pvxMSTPPortCrntPMBPDUCFGTXValidity      PMValidity,
                                      pvxMSTPPortCrntPMBPDUCFGTXInitialize    InitializeCmd,
                                      pvxMSTPPortCrntPMBPDUTCNRXValue         Unsigned64,
                                      pvxMSTPPortCrntPMBPDUTCNRXTimeStamp     DateAndTime,
                                      pvxMSTPPortCrntPMBPDUTCNRXValidity      PMValidity,
                                      pvxMSTPPortCrntPMBPDUTCNRXInitialize    InitializeCmd,
                                      pvxMSTPPortCrntPMBPDUTCNTXValue         Unsigned64,
                                      pvxMSTPPortCrntPMBPDUTCNTXTimeStamp     DateAndTime,
                                      pvxMSTPPortCrntPMBPDUTCNTXValidity      PMValidity,
                                      pvxMSTPPortCrntPMBPDUTCNTXInitialize    InitializeCmd,
                                      pvxMSTPPortCrntPMINVBPDURXValue         Unsigned64,
                                      pvxMSTPPortCrntPMINVBPDURXTimeStamp     DateAndTime,
                                      pvxMSTPPortCrntPMINVBPDURXValidity      PMValidity,
                                      pvxMSTPPortCrntPMINVBPDURXInitialize    InitializeCmd,
                                      pvxMSTPPortCrntPMINVBPDUCFGRXValue      Unsigned64,
                                      pvxMSTPPortCrntPMINVBPDUCFGRXTimeStamp  DateAndTime,
                                      pvxMSTPPortCrntPMINVBPDUCFGRXValidity   PMValidity,
                                      pvxMSTPPortCrntPMINVBPDUCFGRXInitialize InitializeCmd,
                                      pvxMSTPPortCrntPMINVBPDUTCNRXValue      Unsigned64,
                                      pvxMSTPPortCrntPMINVBPDUTCNRXTimeStamp  DateAndTime,
                                      pvxMSTPPortCrntPMINVBPDUTCNRXValidity   PMValidity,
                                      pvxMSTPPortCrntPMINVBPDUTCNRXInitialize InitializeCmd }
                                  
                                  
pvxMSTPPortCrntPMSwitchIdx OBJECT-TYPE
   	SYNTAX       INTEGER(1..11)
   	MAX-ACCESS   not-accessible
   	STATUS       current
    DESCRIPTION  "The identifier of the ethernet switch instance on which the
                  MSTP Port is provisioned."
    ::= {pvxMSTPPortCrntPMEntry 1 }


pvxMSTPPortCrntPMShelfIdx OBJECT-TYPE
    SYNTAX       INTEGER (0|1|11|21|31)
    MAX-ACCESS   not-accessible
    STATUS       current
    DESCRIPTION  "The number of the shelf on which the MSTP Port targeted
                  for PMs is provisioned. For LAG entities, the shelf number is 0."
    ::= {pvxMSTPPortCrntPMEntry 2 }


pvxMSTPPortCrntPMSlotIdx OBJECT-TYPE
    SYNTAX       INTEGER (0|1|3|5|7|9|11|13|15|17|19)
    MAX-ACCESS   not-accessible
    STATUS       current
    DESCRIPTION  "The number of the slot within which the MSTP Port targeted
                  for PMs is provisioned. For LAG entities, the slot number is 0."
    ::= {pvxMSTPPortCrntPMEntry 3 }


pvxMSTPPortCrntPMTypeIdx OBJECT-TYPE
    SYNTAX       PvxPortType
    MAX-ACCESS   not-accessible
    STATUS       current
    DESCRIPTION  "The type of PacketVX port on which the MSTP Port
                  facility is provisioned."
    ::= {pvxMSTPPortCrntPMEntry 4 }


pvxMSTPPortCrntPMXstIdx OBJECT-TYPE
    SYNTAX       INTEGER (0..64)
    MAX-ACCESS   not-accessible
    STATUS       current
    DESCRIPTION  "The instance number of the MSTP instance. For the
    			  global MSTP object on the switch, this index object
    			  is set to 0."
    ::= {pvxMSTPPortCrntPMEntry 5 }


pvxMSTPPortCrntPMIdx OBJECT-TYPE
    SYNTAX       INTEGER (1..24) 
    MAX-ACCESS   not-accessible
    STATUS       current
    DESCRIPTION  "The number of the port of the identified type on which the PVX
                  MSTP Port facility targeted for PMs is provisioned."
    ::= {pvxMSTPPortCrntPMEntry 6 }


pvxMSTPPortCrntPMIntervalTypeIdx OBJECT-TYPE
    SYNTAX       PMIntervalType
    MAX-ACCESS   not-accessible
    STATUS       current
    DESCRIPTION  "The type of PM bin according to interval length."
    ::= { pvxMSTPPortCrntPMEntry 7 }


pvxMSTPPortCrntPMFWDTRValue OBJECT-TYPE
    SYNTAX       Unsigned64
    MAX-ACCESS   read-only
    STATUS       current
    DESCRIPTION  "The CIST/MSTI number of forward transitions."
    ::= { pvxMSTPPortCrntPMEntry 8 }


pvxMSTPPortCrntPMFWDTRTimeStamp OBJECT-TYPE
    SYNTAX       DateAndTime
    MAX-ACCESS   read-only
    STATUS       current
    DESCRIPTION  "The date and time stamp of the CIST/MSTI number
    			  of forward transitions value."
    ::= { pvxMSTPPortCrntPMEntry 9 }


pvxMSTPPortCrntPMFWDTRValidity OBJECT-TYPE
    SYNTAX       PMValidity
    MAX-ACCESS   read-only
    STATUS       current
    DESCRIPTION  "Indicates the validity of the provided CIST/MSTI
    			  number of forward transitions value."
    ::= { pvxMSTPPortCrntPMEntry 10 }


pvxMSTPPortCrntPMFWDTRInitialize OBJECT-TYPE
    SYNTAX       InitializeCmd
    MAX-ACCESS   read-write
    STATUS       current
    DESCRIPTION  "Used to initialize the value of the pvxMSTPPortCrntPMFWDTRValue object
                  to 0."
    ::= { pvxMSTPPortCrntPMEntry 11 }


pvxMSTPPortCrntPMPMCValue OBJECT-TYPE
    SYNTAX       Unsigned64
    MAX-ACCESS   read-only
    STATUS       current
    DESCRIPTION  "The CIST protocol migration count. This
    			  object applies only to the global MSTP Port objects on
    			  the switch."
    ::= { pvxMSTPPortCrntPMEntry 12 }


pvxMSTPPortCrntPMPMCTimeStamp OBJECT-TYPE
    SYNTAX       DateAndTime
    MAX-ACCESS   read-only
    STATUS       current
    DESCRIPTION  "The date and time stamp of the CIST protocol
    			  migration count value."
    ::= { pvxMSTPPortCrntPMEntry 13 }


pvxMSTPPortCrntPMPMCValidity OBJECT-TYPE
    SYNTAX       PMValidity
    MAX-ACCESS   read-only
    STATUS       current
    DESCRIPTION  "Indicates the validity of the provided CIST
    			  protocol migration count value."
    ::= { pvxMSTPPortCrntPMEntry 14 }


pvxMSTPPortCrntPMPMCInitialize OBJECT-TYPE
    SYNTAX       InitializeCmd
    MAX-ACCESS   read-write
    STATUS       current
    DESCRIPTION  "Used to initialize the value of the pvxMSTPPortCrntPMPMCValue object
                  to 0."
    ::= { pvxMSTPPortCrntPMEntry 15 }


pvxMSTPPortCrntPMBPDURXValue OBJECT-TYPE
    SYNTAX       Unsigned64
    MAX-ACCESS   read-only
    STATUS       current
    DESCRIPTION  "The number of bridging protocol data units received."
    ::= { pvxMSTPPortCrntPMEntry 16 }


pvxMSTPPortCrntPMBPDURXTimeStamp OBJECT-TYPE
    SYNTAX       DateAndTime
    MAX-ACCESS   read-only
    STATUS       current
    DESCRIPTION  "The date and time stamp of the number of bridging
    			  protocol data units received value."
    ::= { pvxMSTPPortCrntPMEntry 17 }


pvxMSTPPortCrntPMBPDURXValidity OBJECT-TYPE
    SYNTAX       PMValidity
    MAX-ACCESS   read-only
    STATUS       current
    DESCRIPTION  "Indicates the validity of the provided number of
    			  bridging protocol data units received value."
    ::= { pvxMSTPPortCrntPMEntry 18 }


pvxMSTPPortCrntPMBPDURXInitialize OBJECT-TYPE
    SYNTAX       InitializeCmd
    MAX-ACCESS   read-write
    STATUS       current
    DESCRIPTION  "Used to initialize the value of the pvxMSTPPortCrntPMBPDURXValue object
                  to 0."
    ::= { pvxMSTPPortCrntPMEntry 19 }


pvxMSTPPortCrntPMBPDUTXValue OBJECT-TYPE
    SYNTAX       Unsigned64
    MAX-ACCESS   read-only
    STATUS       current
    DESCRIPTION  "The number of bridging protocol data units transmitted."
    ::= { pvxMSTPPortCrntPMEntry 20 }


pvxMSTPPortCrntPMBPDUTXTimeStamp OBJECT-TYPE
    SYNTAX       DateAndTime
    MAX-ACCESS   read-only
    STATUS       current
    DESCRIPTION  "The date and time stamp of the number of bridging
    			  protocol data units transmitted value."
    ::= { pvxMSTPPortCrntPMEntry 21 }


pvxMSTPPortCrntPMBPDUTXValidity OBJECT-TYPE
    SYNTAX       PMValidity
    MAX-ACCESS   read-only
    STATUS       current
    DESCRIPTION  "Indicates the validity of the provided number of
    			  bridging protocol data units transmitted value."
    ::= { pvxMSTPPortCrntPMEntry 22 }


pvxMSTPPortCrntPMBPDUTXInitialize OBJECT-TYPE
    SYNTAX       InitializeCmd
    MAX-ACCESS   read-write
    STATUS       current
    DESCRIPTION  "Used to initialize the value of the pvxMSTPPortCrntPMBPDUTXValue object
                  to 0."
    ::= { pvxMSTPPortCrntPMEntry 23 }


pvxMSTPPortCrntPMBPDUCFGRXValue OBJECT-TYPE
    SYNTAX       Unsigned64
    MAX-ACCESS   read-only
    STATUS       current
    DESCRIPTION  "The number of configuration bridging protocol data units received.
    			  This object applies only to the global MSTP Port objects."
    ::= { pvxMSTPPortCrntPMEntry 24 }


pvxMSTPPortCrntPMBPDUCFGRXTimeStamp OBJECT-TYPE
    SYNTAX       DateAndTime
    MAX-ACCESS   read-only
    STATUS       current
    DESCRIPTION  "The date and time stamp of the number of configuration bridging
    			  protocol data units received value."
    ::= { pvxMSTPPortCrntPMEntry 25 }


pvxMSTPPortCrntPMBPDUCFGRXValidity OBJECT-TYPE
    SYNTAX       PMValidity
    MAX-ACCESS   read-only
    STATUS       current
    DESCRIPTION  "Indicates the validity of the provided number of
    			  configuration bridging protocol data units received value."
    ::= { pvxMSTPPortCrntPMEntry 26 }


pvxMSTPPortCrntPMBPDUCFGRXInitialize OBJECT-TYPE
    SYNTAX       InitializeCmd
    MAX-ACCESS   read-write
    STATUS       current
    DESCRIPTION  "Used to initialize the value of the pvxMSTPPortCrntPMBPDUCFGRXValue object
                  to 0."
    ::= { pvxMSTPPortCrntPMEntry 27 }


pvxMSTPPortCrntPMBPDUCFGTXValue OBJECT-TYPE
    SYNTAX       Unsigned64
    MAX-ACCESS   read-only
    STATUS       current
    DESCRIPTION  "The number of configuration bridging protocol data units transmitted.
    			  This object applies only to the global MSTP Port objects."
    ::= { pvxMSTPPortCrntPMEntry 28 }


pvxMSTPPortCrntPMBPDUCFGTXTimeStamp OBJECT-TYPE
    SYNTAX       DateAndTime
    MAX-ACCESS   read-only
    STATUS       current
    DESCRIPTION  "The date and time stamp of the number of configuration bridging
    			  protocol data units transmitted value."
    ::= { pvxMSTPPortCrntPMEntry 29 }


pvxMSTPPortCrntPMBPDUCFGTXValidity OBJECT-TYPE
    SYNTAX       PMValidity
    MAX-ACCESS   read-only
    STATUS       current
    DESCRIPTION  "Indicates the validity of the provided number of
    			  configuration bridging protocol data units transmitted value."
    ::= { pvxMSTPPortCrntPMEntry 30 }


pvxMSTPPortCrntPMBPDUCFGTXInitialize OBJECT-TYPE
    SYNTAX       InitializeCmd
    MAX-ACCESS   read-write
    STATUS       current
    DESCRIPTION  "Used to initialize the value of the pvxMSTPPortCrntPMBPDUCFGTXValue object
                  to 0."
    ::= { pvxMSTPPortCrntPMEntry 31 }


pvxMSTPPortCrntPMBPDUTCNRXValue OBJECT-TYPE
    SYNTAX       Unsigned64
    MAX-ACCESS   read-only
    STATUS       current
    DESCRIPTION  "The number of topology change notifications bridging
    			  protocol data units received. This object applies
    			  only to the global MSTP Port objects."
    ::= { pvxMSTPPortCrntPMEntry 32 }


pvxMSTPPortCrntPMBPDUTCNRXTimeStamp OBJECT-TYPE
    SYNTAX       DateAndTime
    MAX-ACCESS   read-only
    STATUS       current
    DESCRIPTION  "The date and time stamp of the number of topology
    			  change notifications bridging protocol data units
    			  received value."
    ::= { pvxMSTPPortCrntPMEntry 33 }


pvxMSTPPortCrntPMBPDUTCNRXValidity OBJECT-TYPE
    SYNTAX       PMValidity
    MAX-ACCESS   read-only
    STATUS       current
    DESCRIPTION  "Indicates the validity of the provided number of
    			  topology change notifications bridging protocol
    			  data units received value."
    ::= { pvxMSTPPortCrntPMEntry 34 }


pvxMSTPPortCrntPMBPDUTCNRXInitialize OBJECT-TYPE
    SYNTAX       InitializeCmd
    MAX-ACCESS   read-write
    STATUS       current
    DESCRIPTION  "Used to initialize the value of the pvxMSTPPortCrntPMBPDUTCNRXValue object
                  to 0."
    ::= { pvxMSTPPortCrntPMEntry 35 }


pvxMSTPPortCrntPMBPDUTCNTXValue OBJECT-TYPE
    SYNTAX       Unsigned64
    MAX-ACCESS   read-only
    STATUS       current
    DESCRIPTION  "The number of topology change notifications bridging
    			  protocol data units transmitted. This object applies
    			  only to the global MSTP Port objects."
    ::= { pvxMSTPPortCrntPMEntry 36 }


pvxMSTPPortCrntPMBPDUTCNTXTimeStamp OBJECT-TYPE
    SYNTAX       DateAndTime
    MAX-ACCESS   read-only
    STATUS       current
    DESCRIPTION  "The date and time stamp of the number of topology
    			  change notifications bridging protocol data units
    			  transmitted value."
    ::= { pvxMSTPPortCrntPMEntry 37 }


pvxMSTPPortCrntPMBPDUTCNTXValidity OBJECT-TYPE
    SYNTAX       PMValidity
    MAX-ACCESS   read-only
    STATUS       current
    DESCRIPTION  "Indicates the validity of the provided number of
    			  topology change notifications bridging protocol
    			  data units transmitted value."
    ::= { pvxMSTPPortCrntPMEntry 38 }


pvxMSTPPortCrntPMBPDUTCNTXInitialize OBJECT-TYPE
    SYNTAX       InitializeCmd
    MAX-ACCESS   read-write
    STATUS       current
    DESCRIPTION  "Used to initialize the value of the pvxMSTPPortCrntPMBPDUTCNTXValue object
                  to 0."
    ::= { pvxMSTPPortCrntPMEntry 39 }


pvxMSTPPortCrntPMINVBPDURXValue OBJECT-TYPE
    SYNTAX       Unsigned64
    MAX-ACCESS   read-only
    STATUS       current
    DESCRIPTION  "The number of invalid bridging protocol data units received."
    ::= { pvxMSTPPortCrntPMEntry 40 }


pvxMSTPPortCrntPMINVBPDURXTimeStamp OBJECT-TYPE
    SYNTAX       DateAndTime
    MAX-ACCESS   read-only
    STATUS       current
    DESCRIPTION  "The date and time stamp of the number of invalid bridging
    			  protocol data units received value."
    ::= { pvxMSTPPortCrntPMEntry 41 }


pvxMSTPPortCrntPMINVBPDURXValidity OBJECT-TYPE
    SYNTAX       PMValidity
    MAX-ACCESS   read-only
    STATUS       current
    DESCRIPTION  "Indicates the validity of the provided number of
    			  invalid bridging protocol data units received value."
    ::= { pvxMSTPPortCrntPMEntry 42 }


pvxMSTPPortCrntPMINVBPDURXInitialize OBJECT-TYPE
    SYNTAX       InitializeCmd
    MAX-ACCESS   read-write
    STATUS       current
    DESCRIPTION  "Used to initialize the value of the pvxMSTPPortCrntPMBPDURXValue object
                  to 0."
    ::= { pvxMSTPPortCrntPMEntry 43 }


pvxMSTPPortCrntPMINVBPDUCFGRXValue OBJECT-TYPE
    SYNTAX       Unsigned64
    MAX-ACCESS   read-only
    STATUS       current
    DESCRIPTION  "The number of invalid configuration bridging protocol
    			  data units received. This object applies only to the
    			  global MSTP Port objects."
    ::= { pvxMSTPPortCrntPMEntry 44 }


pvxMSTPPortCrntPMINVBPDUCFGRXTimeStamp OBJECT-TYPE
    SYNTAX       DateAndTime
    MAX-ACCESS   read-only
    STATUS       current
    DESCRIPTION  "The date and time stamp of the number of invalid configuration
    			  bridging protocol data units received value."
    ::= { pvxMSTPPortCrntPMEntry 45 }


pvxMSTPPortCrntPMINVBPDUCFGRXValidity OBJECT-TYPE
    SYNTAX       PMValidity
    MAX-ACCESS   read-only
    STATUS       current
    DESCRIPTION  "Indicates the validity of the provided number of
    			  invalid configuration bridging protocol data units
    			  received value."
    ::= { pvxMSTPPortCrntPMEntry 46 }


pvxMSTPPortCrntPMINVBPDUCFGRXInitialize OBJECT-TYPE
    SYNTAX       InitializeCmd
    MAX-ACCESS   read-write
    STATUS       current
    DESCRIPTION  "Used to initialize the value of the pvxMSTPPortCrntPMINVBPDUCFGRXValue object
                  to 0."
    ::= { pvxMSTPPortCrntPMEntry 47 }


pvxMSTPPortCrntPMINVBPDUTCNRXValue OBJECT-TYPE
    SYNTAX       Unsigned64
    MAX-ACCESS   read-only
    STATUS       current
    DESCRIPTION  "The number of invalid topology change notifications bridging
    			  protocol data units received. This object applies
    			  only to the global MSTP Port objects."
    ::= { pvxMSTPPortCrntPMEntry 48 }


pvxMSTPPortCrntPMINVBPDUTCNRXTimeStamp OBJECT-TYPE
    SYNTAX       DateAndTime
    MAX-ACCESS   read-only
    STATUS       current
    DESCRIPTION  "The date and time stamp of the number of invalid topology
    			  change notifications bridging protocol data units
    			  received value."
    ::= { pvxMSTPPortCrntPMEntry 49 }


pvxMSTPPortCrntPMINVBPDUTCNRXValidity OBJECT-TYPE
    SYNTAX       PMValidity
    MAX-ACCESS   read-only
    STATUS       current
    DESCRIPTION  "Indicates the validity of the provided number of
    			  invalid topology change notifications bridging protocol
    			  data units received value."
    ::= { pvxMSTPPortCrntPMEntry 50 }


pvxMSTPPortCrntPMINVBPDUTCNRXInitialize OBJECT-TYPE
    SYNTAX       InitializeCmd
    MAX-ACCESS   read-write
    STATUS       current
    DESCRIPTION  "Used to initialize the value of the pvxMSTPPortCrntPMINVBPDUTCNRXValue object
                  to 0."
    ::= { pvxMSTPPortCrntPMEntry 51 }



-----------------------------------------------------------------------
-- Objects used to retrieve historical Performance Monitoring
-- statistics for PacketVX MSTP Port and MSTP Instance Port Objects
-----------------------------------------------------------------------

pvxMSTPPortHistPMTable OBJECT-TYPE
    SYNTAX       SEQUENCE OF PvxMSTPPortHistPMEntry
    MAX-ACCESS   not-accessible
    STATUS       current
    DESCRIPTION  "A table of historical performance monitoring statistics collected
                  for PacketVX MSTP Port and MSTP Instance Port objects."
    ::= { performance 35 }


pvxMSTPPortHistPMEntry OBJECT-TYPE
    SYNTAX       PvxMSTPPortHistPMEntry
    MAX-ACCESS   not-accessible
    STATUS       current
    DESCRIPTION  "The row entry object of the PacketVX MSTP Port historical
                  performance monitoring table. Each row of this table contains
                  a full set of PM statistics and related data for an historical
                  measurement interval for a given PVX MSTP Port or MSTP Instance Port."
    INDEX        { pvxMSTPPortHistPMSwitchIdx,
				   pvxMSTPPortHistPMShelfIdx,
				   pvxMSTPPortHistPMSlotIdx,
               	   pvxMSTPPortHistPMTypeIdx,
    			   pvxMSTPPortHistPMXstIdx,
               	   pvxMSTPPortHistPMIdx,
    			   pvxMSTPPortHistPMIntervalTypeIdx,
    			   pvxMSTPPortHistPMIntervalIdx }
    ::= { pvxMSTPPortHistPMTable 1 }


PvxMSTPPortHistPMEntry ::= SEQUENCE { pvxMSTPPortHistPMSwitchIdx              INTEGER,
				                      pvxMSTPPortHistPMShelfIdx       	      INTEGER,
				                      pvxMSTPPortHistPMSlotIdx        	      INTEGER,
				                      pvxMSTPPortHistPMTypeIdx		          PvxPortType,
                                      pvxMSTPPortHistPMXstIdx                 INTEGER,
                        	          pvxMSTPPortHistPMIdx         		      INTEGER,
                                      pvxMSTPPortHistPMIntervalTypeIdx        PMIntervalType,
                                      pvxMSTPPortHistPMIntervalIdx            INTEGER,
                                      pvxMSTPPortHistPMFWDTRValue             Unsigned64,
                                      pvxMSTPPortHistPMFWDTRTimeStamp         DateAndTime,
                                      pvxMSTPPortHistPMFWDTRValidity          PMValidity,
                                      pvxMSTPPortHistPMFWDTRInitialize        InitializeCmd,
                                      pvxMSTPPortHistPMPMCValue               Unsigned64,
                                      pvxMSTPPortHistPMPMCTimeStamp           DateAndTime,
                                      pvxMSTPPortHistPMPMCValidity            PMValidity,
                                      pvxMSTPPortHistPMPMCInitialize          InitializeCmd,
                                      pvxMSTPPortHistPMBPDURXValue            Unsigned64,
                                      pvxMSTPPortHistPMBPDURXTimeStamp        DateAndTime,
                                      pvxMSTPPortHistPMBPDURXValidity         PMValidity,
                                      pvxMSTPPortHistPMBPDURXInitialize       InitializeCmd,
                                      pvxMSTPPortHistPMBPDUTXValue            Unsigned64,
                                      pvxMSTPPortHistPMBPDUTXTimeStamp        DateAndTime,
                                      pvxMSTPPortHistPMBPDUTXValidity         PMValidity,
                                      pvxMSTPPortHistPMBPDUTXInitialize       InitializeCmd,
                                      pvxMSTPPortHistPMBPDUCFGRXValue         Unsigned64,
                                      pvxMSTPPortHistPMBPDUCFGRXTimeStamp     DateAndTime,
                                      pvxMSTPPortHistPMBPDUCFGRXValidity      PMValidity,
                                      pvxMSTPPortHistPMBPDUCFGRXInitialize    InitializeCmd,
                                      pvxMSTPPortHistPMBPDUCFGTXValue         Unsigned64,
                                      pvxMSTPPortHistPMBPDUCFGTXTimeStamp     DateAndTime,
                                      pvxMSTPPortHistPMBPDUCFGTXValidity      PMValidity,
                                      pvxMSTPPortHistPMBPDUCFGTXInitialize    InitializeCmd,
                                      pvxMSTPPortHistPMBPDUTCNRXValue         Unsigned64,
                                      pvxMSTPPortHistPMBPDUTCNRXTimeStamp     DateAndTime,
                                      pvxMSTPPortHistPMBPDUTCNRXValidity      PMValidity,
                                      pvxMSTPPortHistPMBPDUTCNRXInitialize    InitializeCmd,
                                      pvxMSTPPortHistPMBPDUTCNTXValue         Unsigned64,
                                      pvxMSTPPortHistPMBPDUTCNTXTimeStamp     DateAndTime,
                                      pvxMSTPPortHistPMBPDUTCNTXValidity      PMValidity,
                                      pvxMSTPPortHistPMBPDUTCNTXInitialize    InitializeCmd,
                                      pvxMSTPPortHistPMINVBPDURXValue         Unsigned64,
                                      pvxMSTPPortHistPMINVBPDURXTimeStamp     DateAndTime,
                                      pvxMSTPPortHistPMINVBPDURXValidity      PMValidity,
                                      pvxMSTPPortHistPMINVBPDURXInitialize    InitializeCmd,
                                      pvxMSTPPortHistPMINVBPDUCFGRXValue      Unsigned64,
                                      pvxMSTPPortHistPMINVBPDUCFGRXTimeStamp  DateAndTime,
                                      pvxMSTPPortHistPMINVBPDUCFGRXValidity   PMValidity,
                                      pvxMSTPPortHistPMINVBPDUCFGRXInitialize InitializeCmd,
                                      pvxMSTPPortHistPMINVBPDUTCNRXValue      Unsigned64,
                                      pvxMSTPPortHistPMINVBPDUTCNRXTimeStamp  DateAndTime,
                                      pvxMSTPPortHistPMINVBPDUTCNRXValidity   PMValidity,
                                      pvxMSTPPortHistPMINVBPDUTCNRXInitialize InitializeCmd }
                                  
                                  
pvxMSTPPortHistPMSwitchIdx OBJECT-TYPE
   	SYNTAX       INTEGER(1..11)
   	MAX-ACCESS   not-accessible
   	STATUS       current
    DESCRIPTION  "The identifier of the ethernet switch instance on which the
                  MSTP Port is provisioned."
    ::= {pvxMSTPPortHistPMEntry 1 }


pvxMSTPPortHistPMShelfIdx OBJECT-TYPE
    SYNTAX       INTEGER (0|1|11|21|31)
    MAX-ACCESS   not-accessible
    STATUS       current
    DESCRIPTION  "The number of the shelf on which the MSTP Port targeted
                  for PMs is provisioned. For LAG entities, the shelf number is 0."
    ::= {pvxMSTPPortHistPMEntry 2 }


pvxMSTPPortHistPMSlotIdx OBJECT-TYPE
    SYNTAX       INTEGER (0|1|3|5|7|9|11|13|15|17|19)
    MAX-ACCESS   not-accessible
    STATUS       current
    DESCRIPTION  "The number of the slot within which the MSTP Port targeted
                  for PMs is provisioned. For LAG entities, the slot number is 0."
    ::= {pvxMSTPPortHistPMEntry 3 }


pvxMSTPPortHistPMTypeIdx OBJECT-TYPE
    SYNTAX       PvxPortType
    MAX-ACCESS   not-accessible
    STATUS       current
    DESCRIPTION  "The type of PacketVX port on which the MSTP Port
                  facility is provisioned."
    ::= {pvxMSTPPortHistPMEntry 4 }


pvxMSTPPortHistPMXstIdx OBJECT-TYPE
    SYNTAX       INTEGER (0..64)
    MAX-ACCESS   not-accessible
    STATUS       current
    DESCRIPTION  "The instance number of the MSTP instance. For the
    			  global MSTP object on the switch, this index object
    			  is set to 0."
    ::= {pvxMSTPPortHistPMEntry 5 }


pvxMSTPPortHistPMIdx OBJECT-TYPE
    SYNTAX       INTEGER (1..24) 
    MAX-ACCESS   not-accessible
    STATUS       current
    DESCRIPTION  "The number of the port of the identified type on which the PVX
                  MSTP Port facility targeted for PMs is provisioned."
    ::= {pvxMSTPPortHistPMEntry 6 }


pvxMSTPPortHistPMIntervalTypeIdx OBJECT-TYPE
    SYNTAX       PMIntervalType
    MAX-ACCESS   not-accessible
    STATUS       current
    DESCRIPTION  "The type of PM bin according to interval length."
    ::= { pvxMSTPPortHistPMEntry 7 }


pvxMSTPPortHistPMIntervalIdx OBJECT-TYPE
    SYNTAX       INTEGER (1..96)
    MAX-ACCESS   not-accessible
    STATUS       current
    DESCRIPTION  "The specific PM bin number. The range is 1 to 96 for the
                  15-minute historical bins. For the 1-day historical bin, the
                  value is 1."
    ::= { pvxMSTPPortHistPMEntry 8 }


pvxMSTPPortHistPMFWDTRValue OBJECT-TYPE
    SYNTAX       Unsigned64
    MAX-ACCESS   read-only
    STATUS       current
    DESCRIPTION  "The CIST/MSTI number of forward transitions."
    ::= { pvxMSTPPortHistPMEntry 9 }


pvxMSTPPortHistPMFWDTRTimeStamp OBJECT-TYPE
    SYNTAX       DateAndTime
    MAX-ACCESS   read-only
    STATUS       current
    DESCRIPTION  "The date and time stamp of the CIST/MSTI number
    			  of forward transitions value."
    ::= { pvxMSTPPortHistPMEntry 10 }


pvxMSTPPortHistPMFWDTRValidity OBJECT-TYPE
    SYNTAX       PMValidity
    MAX-ACCESS   read-only
    STATUS       current
    DESCRIPTION  "Indicates the validity of the provided CIST/MSTI
    			  number of forward transitions value."
    ::= { pvxMSTPPortHistPMEntry 11 }


pvxMSTPPortHistPMFWDTRInitialize OBJECT-TYPE
    SYNTAX       InitializeCmd
    MAX-ACCESS   read-write
    STATUS       current
    DESCRIPTION  "Used to initialize the value of the pvxMSTPPortHistPMFWDTRValue object
                  to 0."
    ::= { pvxMSTPPortHistPMEntry 12 }


pvxMSTPPortHistPMPMCValue OBJECT-TYPE
    SYNTAX       Unsigned64
    MAX-ACCESS   read-only
    STATUS       current
    DESCRIPTION  "The CIST protocol migration count. This
    			  object applies only to the global MSTP Port objects on
    			  the switch."
    ::= { pvxMSTPPortHistPMEntry 13 }


pvxMSTPPortHistPMPMCTimeStamp OBJECT-TYPE
    SYNTAX       DateAndTime
    MAX-ACCESS   read-only
    STATUS       current
    DESCRIPTION  "The date and time stamp of the CIST protocol
    			  migration count value."
    ::= { pvxMSTPPortHistPMEntry 14 }


pvxMSTPPortHistPMPMCValidity OBJECT-TYPE
    SYNTAX       PMValidity
    MAX-ACCESS   read-only
    STATUS       current
    DESCRIPTION  "Indicates the validity of the provided CIST
    			  protocol migration count value."
    ::= { pvxMSTPPortHistPMEntry 15 }


pvxMSTPPortHistPMPMCInitialize OBJECT-TYPE
    SYNTAX       InitializeCmd
    MAX-ACCESS   read-write
    STATUS       current
    DESCRIPTION  "Used to initialize the value of the pvxMSTPPortHistPMPMCValue object
                  to 0."
    ::= { pvxMSTPPortHistPMEntry 16 }


pvxMSTPPortHistPMBPDURXValue OBJECT-TYPE
    SYNTAX       Unsigned64
    MAX-ACCESS   read-only
    STATUS       current
    DESCRIPTION  "The number of bridging protocol data units received."
    ::= { pvxMSTPPortHistPMEntry 17 }


pvxMSTPPortHistPMBPDURXTimeStamp OBJECT-TYPE
    SYNTAX       DateAndTime
    MAX-ACCESS   read-only
    STATUS       current
    DESCRIPTION  "The date and time stamp of the number of bridging
    			  protocol data units received value."
    ::= { pvxMSTPPortHistPMEntry 18 }


pvxMSTPPortHistPMBPDURXValidity OBJECT-TYPE
    SYNTAX       PMValidity
    MAX-ACCESS   read-only
    STATUS       current
    DESCRIPTION  "Indicates the validity of the provided number of
    			  bridging protocol data units received value."
    ::= { pvxMSTPPortHistPMEntry 19 }


pvxMSTPPortHistPMBPDURXInitialize OBJECT-TYPE
    SYNTAX       InitializeCmd
    MAX-ACCESS   read-write
    STATUS       current
    DESCRIPTION  "Used to initialize the value of the pvxMSTPPortHistPMBPDURXValue object
                  to 0."
    ::= { pvxMSTPPortHistPMEntry 20 }


pvxMSTPPortHistPMBPDUTXValue OBJECT-TYPE
    SYNTAX       Unsigned64
    MAX-ACCESS   read-only
    STATUS       current
    DESCRIPTION  "The number of bridging protocol data units transmitted."
    ::= { pvxMSTPPortHistPMEntry 21 }


pvxMSTPPortHistPMBPDUTXTimeStamp OBJECT-TYPE
    SYNTAX       DateAndTime
    MAX-ACCESS   read-only
    STATUS       current
    DESCRIPTION  "The date and time stamp of the number of bridging
    			  protocol data units transmitted value."
    ::= { pvxMSTPPortHistPMEntry 22 }


pvxMSTPPortHistPMBPDUTXValidity OBJECT-TYPE
    SYNTAX       PMValidity
    MAX-ACCESS   read-only
    STATUS       current
    DESCRIPTION  "Indicates the validity of the provided number of
    			  bridging protocol data units transmitted value."
    ::= { pvxMSTPPortHistPMEntry 23 }


pvxMSTPPortHistPMBPDUTXInitialize OBJECT-TYPE
    SYNTAX       InitializeCmd
    MAX-ACCESS   read-write
    STATUS       current
    DESCRIPTION  "Used to initialize the value of the pvxMSTPPortHistPMBPDUTXValue object
                  to 0."
    ::= { pvxMSTPPortHistPMEntry 24 }


pvxMSTPPortHistPMBPDUCFGRXValue OBJECT-TYPE
    SYNTAX       Unsigned64
    MAX-ACCESS   read-only
    STATUS       current
    DESCRIPTION  "The number of configuration bridging protocol data units received.
    			  This object applies only to the global MSTP Port objects."
    ::= { pvxMSTPPortHistPMEntry 25 }


pvxMSTPPortHistPMBPDUCFGRXTimeStamp OBJECT-TYPE
    SYNTAX       DateAndTime
    MAX-ACCESS   read-only
    STATUS       current
    DESCRIPTION  "The date and time stamp of the number of configuration bridging
    			  protocol data units received value."
    ::= { pvxMSTPPortHistPMEntry 26 }


pvxMSTPPortHistPMBPDUCFGRXValidity OBJECT-TYPE
    SYNTAX       PMValidity
    MAX-ACCESS   read-only
    STATUS       current
    DESCRIPTION  "Indicates the validity of the provided number of
    			  configuration bridging protocol data units received value."
    ::= { pvxMSTPPortHistPMEntry 27 }


pvxMSTPPortHistPMBPDUCFGRXInitialize OBJECT-TYPE
    SYNTAX       InitializeCmd
    MAX-ACCESS   read-write
    STATUS       current
    DESCRIPTION  "Used to initialize the value of the pvxMSTPPortHistPMBPDUCFGRXValue object
                  to 0."
    ::= { pvxMSTPPortHistPMEntry 28 }


pvxMSTPPortHistPMBPDUCFGTXValue OBJECT-TYPE
    SYNTAX       Unsigned64
    MAX-ACCESS   read-only
    STATUS       current
    DESCRIPTION  "The number of configuration bridging protocol data units transmitted.
    			  This object applies only to the global MSTP Port objects."
    ::= { pvxMSTPPortHistPMEntry 29 }


pvxMSTPPortHistPMBPDUCFGTXTimeStamp OBJECT-TYPE
    SYNTAX       DateAndTime
    MAX-ACCESS   read-only
    STATUS       current
    DESCRIPTION  "The date and time stamp of the number of configuration bridging
    			  protocol data units transmitted value."
    ::= { pvxMSTPPortHistPMEntry 30 }


pvxMSTPPortHistPMBPDUCFGTXValidity OBJECT-TYPE
    SYNTAX       PMValidity
    MAX-ACCESS   read-only
    STATUS       current
    DESCRIPTION  "Indicates the validity of the provided number of
    			  configuration bridging protocol data units transmitted value."
    ::= { pvxMSTPPortHistPMEntry 31 }


pvxMSTPPortHistPMBPDUCFGTXInitialize OBJECT-TYPE
    SYNTAX       InitializeCmd
    MAX-ACCESS   read-write
    STATUS       current
    DESCRIPTION  "Used to initialize the value of the pvxMSTPPortHistPMBPDUCFGTXValue object
                  to 0."
    ::= { pvxMSTPPortHistPMEntry 32 }


pvxMSTPPortHistPMBPDUTCNRXValue OBJECT-TYPE
    SYNTAX       Unsigned64
    MAX-ACCESS   read-only
    STATUS       current
    DESCRIPTION  "The number of topology change notifications bridging
    			  protocol data units received. This object applies
    			  only to the global MSTP Port objects."
    ::= { pvxMSTPPortHistPMEntry 33 }


pvxMSTPPortHistPMBPDUTCNRXTimeStamp OBJECT-TYPE
    SYNTAX       DateAndTime
    MAX-ACCESS   read-only
    STATUS       current
    DESCRIPTION  "The date and time stamp of the number of topology
    			  change notifications bridging protocol data units
    			  received value."
    ::= { pvxMSTPPortHistPMEntry 34 }


pvxMSTPPortHistPMBPDUTCNRXValidity OBJECT-TYPE
    SYNTAX       PMValidity
    MAX-ACCESS   read-only
    STATUS       current
    DESCRIPTION  "Indicates the validity of the provided number of
    			  topology change notifications bridging protocol
    			  data units received value."
    ::= { pvxMSTPPortHistPMEntry 35 }


pvxMSTPPortHistPMBPDUTCNRXInitialize OBJECT-TYPE
    SYNTAX       InitializeCmd
    MAX-ACCESS   read-write
    STATUS       current
    DESCRIPTION  "Used to initialize the value of the pvxMSTPPortHistPMBPDUTCNRXValue object
                  to 0."
    ::= { pvxMSTPPortHistPMEntry 36 }


pvxMSTPPortHistPMBPDUTCNTXValue OBJECT-TYPE
    SYNTAX       Unsigned64
    MAX-ACCESS   read-only
    STATUS       current
    DESCRIPTION  "The number of topology change notifications bridging
    			  protocol data units transmitted. This object applies
    			  only to the global MSTP Port objects."
    ::= { pvxMSTPPortHistPMEntry 37 }


pvxMSTPPortHistPMBPDUTCNTXTimeStamp OBJECT-TYPE
    SYNTAX       DateAndTime
    MAX-ACCESS   read-only
    STATUS       current
    DESCRIPTION  "The date and time stamp of the number of topology
    			  change notifications bridging protocol data units
    			  transmitted value."
    ::= { pvxMSTPPortHistPMEntry 38 }


pvxMSTPPortHistPMBPDUTCNTXValidity OBJECT-TYPE
    SYNTAX       PMValidity
    MAX-ACCESS   read-only
    STATUS       current
    DESCRIPTION  "Indicates the validity of the provided number of
    			  topology change notifications bridging protocol
    			  data units transmitted value."
    ::= { pvxMSTPPortHistPMEntry 39 }


pvxMSTPPortHistPMBPDUTCNTXInitialize OBJECT-TYPE
    SYNTAX       InitializeCmd
    MAX-ACCESS   read-write
    STATUS       current
    DESCRIPTION  "Used to initialize the value of the pvxMSTPPortHistPMBPDUTCNTXValue object
                  to 0."
    ::= { pvxMSTPPortHistPMEntry 40 }


pvxMSTPPortHistPMINVBPDURXValue OBJECT-TYPE
    SYNTAX       Unsigned64
    MAX-ACCESS   read-only
    STATUS       current
    DESCRIPTION  "The number of invalid bridging protocol data units received."
    ::= { pvxMSTPPortHistPMEntry 41 }


pvxMSTPPortHistPMINVBPDURXTimeStamp OBJECT-TYPE
    SYNTAX       DateAndTime
    MAX-ACCESS   read-only
    STATUS       current
    DESCRIPTION  "The date and time stamp of the number of invalid bridging
    			  protocol data units received value."
    ::= { pvxMSTPPortHistPMEntry 42 }


pvxMSTPPortHistPMINVBPDURXValidity OBJECT-TYPE
    SYNTAX       PMValidity
    MAX-ACCESS   read-only
    STATUS       current
    DESCRIPTION  "Indicates the validity of the provided number of
    			  invalid bridging protocol data units received value."
    ::= { pvxMSTPPortHistPMEntry 43 }


pvxMSTPPortHistPMINVBPDURXInitialize OBJECT-TYPE
    SYNTAX       InitializeCmd
    MAX-ACCESS   read-write
    STATUS       current
    DESCRIPTION  "Used to initialize the value of the pvxMSTPPortHistPMBPDURXValue object
                  to 0."
    ::= { pvxMSTPPortHistPMEntry 44 }


pvxMSTPPortHistPMINVBPDUCFGRXValue OBJECT-TYPE
    SYNTAX       Unsigned64
    MAX-ACCESS   read-only
    STATUS       current
    DESCRIPTION  "The number of invalid configuration bridging protocol
    			  data units received. This object applies only to the
    			  global MSTP Port objects."
    ::= { pvxMSTPPortHistPMEntry 45 }


pvxMSTPPortHistPMINVBPDUCFGRXTimeStamp OBJECT-TYPE
    SYNTAX       DateAndTime
    MAX-ACCESS   read-only
    STATUS       current
    DESCRIPTION  "The date and time stamp of the number of invalid configuration
    			  bridging protocol data units received value."
    ::= { pvxMSTPPortHistPMEntry 46 }


pvxMSTPPortHistPMINVBPDUCFGRXValidity OBJECT-TYPE
    SYNTAX       PMValidity
    MAX-ACCESS   read-only
    STATUS       current
    DESCRIPTION  "Indicates the validity of the provided number of
    			  invalid configuration bridging protocol data units
    			  received value."
    ::= { pvxMSTPPortHistPMEntry 47 }


pvxMSTPPortHistPMINVBPDUCFGRXInitialize OBJECT-TYPE
    SYNTAX       InitializeCmd
    MAX-ACCESS   read-write
    STATUS       current
    DESCRIPTION  "Used to initialize the value of the pvxMSTPPortHistPMINVBPDUCFGRXValue object
                  to 0."
    ::= { pvxMSTPPortHistPMEntry 48 }


pvxMSTPPortHistPMINVBPDUTCNRXValue OBJECT-TYPE
    SYNTAX       Unsigned64
    MAX-ACCESS   read-only
    STATUS       current
    DESCRIPTION  "The number of invalid topology change notifications bridging
    			  protocol data units received. This object applies
    			  only to the global MSTP Port objects."
    ::= { pvxMSTPPortHistPMEntry 49 }


pvxMSTPPortHistPMINVBPDUTCNRXTimeStamp OBJECT-TYPE
    SYNTAX       DateAndTime
    MAX-ACCESS   read-only
    STATUS       current
    DESCRIPTION  "The date and time stamp of the number of invalid topology
    			  change notifications bridging protocol data units
    			  received value."
    ::= { pvxMSTPPortHistPMEntry 50 }


pvxMSTPPortHistPMINVBPDUTCNRXValidity OBJECT-TYPE
    SYNTAX       PMValidity
    MAX-ACCESS   read-only
    STATUS       current
    DESCRIPTION  "Indicates the validity of the provided number of
    			  invalid topology change notifications bridging protocol
    			  data units received value."
    ::= { pvxMSTPPortHistPMEntry 51 }


pvxMSTPPortHistPMINVBPDUTCNRXInitialize OBJECT-TYPE
    SYNTAX       InitializeCmd
    MAX-ACCESS   read-write
    STATUS       current
    DESCRIPTION  "Used to initialize the value of the pvxMSTPPortHistPMINVBPDUTCNRXValue object
                  to 0."
    ::= { pvxMSTPPortHistPMEntry 52 }


-----------------------------------------------------------------------
-- Objects used to retrieve current LAG Port
-- Performance Monitoring statistics for PacketVX Interfaces
-----------------------------------------------------------------------


pvxLAGPortCrntPMTable OBJECT-TYPE
    SYNTAX       SEQUENCE OF PvxLAGPortCrntPMEntry
    MAX-ACCESS   not-accessible
    STATUS       current
    DESCRIPTION  "A table of current performance monitoring statistics collected
                  for the PacketVX LAG port interfaces on the NE."
    ::= { performance 36 }


pvxLAGPortCrntPMEntry OBJECT-TYPE
    SYNTAX       PvxLAGPortCrntPMEntry
    MAX-ACCESS   not-accessible
    STATUS       current
    DESCRIPTION  "The row entry object of the PacketVX LAG port current
                  performance monitoring table. Each row of this table contains
                  a full set of PM statistics and related data for a current
                  measurement interval for a given PVX LAG Port."
    INDEX        { pvxLAGPortCrntPMSwitchIdx,
			       pvxLAGPortCrntPMShelfIdx,
                   pvxLAGPortCrntPMSlotIdx,
                   pvxLAGPortCrntPMTypeIdx,
                   pvxLAGPortCrntPMIdx,
                   pvxLAGPortCrntPMIntervalTypeIdx }
    ::= { pvxLAGPortCrntPMTable 1 }


PvxLAGPortCrntPMEntry ::= SEQUENCE { pvxLAGPortCrntPMSwitchIdx                 INTEGER,
					     		     pvxLAGPortCrntPMShelfIdx                  INTEGER,
                                     pvxLAGPortCrntPMSlotIdx                   INTEGER,
                                     pvxLAGPortCrntPMTypeIdx                   PvxPortType,
                                     pvxLAGPortCrntPMIdx                       INTEGER,
                                     pvxLAGPortCrntPMIntervalTypeIdx           PMIntervalType,
                                     pvxLAGPortCrntPMLACPDURXValue             Unsigned64,
                                     pvxLAGPortCrntPMLACPDURXTimeStamp         DateAndTime,
                                     pvxLAGPortCrntPMLACPDURXValidity          PMValidity,
                                     pvxLAGPortCrntPMLACPDURXInitialize        InitializeCmd,
                                     pvxLAGPortCrntPMMRKPDURXValue             Unsigned64,
                                     pvxLAGPortCrntPMMRKPDURXTimeStamp         DateAndTime,
                                     pvxLAGPortCrntPMMRKPDURXValidity          PMValidity,
                                     pvxLAGPortCrntPMMRKPDURXInitialize        InitializeCmd,
                                     pvxLAGPortCrntPMMRKRSPPDURXValue          Unsigned64,
                                     pvxLAGPortCrntPMMRKRSPPDURXTimeStamp      DateAndTime,
                                     pvxLAGPortCrntPMMRKRSPPDURXValidity       PMValidity,
                                     pvxLAGPortCrntPMMRKRSPPDURXInitialize     InitializeCmd,
                                     pvxLAGPortCrntPMINVLACFRRXValue           Unsigned64,
                                     pvxLAGPortCrntPMINVLACFRRXTimeStamp       DateAndTime,
                                     pvxLAGPortCrntPMINVLACFRRXValidity        PMValidity,
                                     pvxLAGPortCrntPMINVLACFRRXInitialize      InitializeCmd,
                                     pvxLAGPortCrntPMLACPDUTXValue             Unsigned64,
                                     pvxLAGPortCrntPMLACPDUTXTimeStamp         DateAndTime,
                                     pvxLAGPortCrntPMLACPDUTXValidity          PMValidity,
                                     pvxLAGPortCrntPMLACPDUTXInitialize        InitializeCmd,
                                     pvxLAGPortCrntPMMRKPDUTXValue             Unsigned64,
                                     pvxLAGPortCrntPMMRKPDUTXTimeStamp         DateAndTime,
                                     pvxLAGPortCrntPMMRKPDUTXValidity          PMValidity,
                                     pvxLAGPortCrntPMMRKPDUTXInitialize        InitializeCmd,
                                     pvxLAGPortCrntPMMRKRSPPDUTXValue          Unsigned64,
                                     pvxLAGPortCrntPMMRKRSPPDUTXTimeStamp      DateAndTime,
                                     pvxLAGPortCrntPMMRKRSPPDUTXValidity       PMValidity,
                                     pvxLAGPortCrntPMMRKRSPPDUTXInitialize     InitializeCmd }


pvxLAGPortCrntPMSwitchIdx OBJECT-TYPE
    SYNTAX       INTEGER(1..11) 
    MAX-ACCESS   not-accessible
    STATUS       current
    DESCRIPTION  "The identifier of the ethernet switch instance on which
			      the PVX LAG port is provisioned."
    ::= {pvxLAGPortCrntPMEntry 1 }


pvxLAGPortCrntPMShelfIdx OBJECT-TYPE
    SYNTAX       INTEGER (0|1|11|21|31)
    MAX-ACCESS   not-accessible
    STATUS       current
    DESCRIPTION  "The number of the shelf on which the PVX LAG port targeted for
                  PMs is provisioned. For LAG entities, the shelf number is 0."
    ::= { pvxLAGPortCrntPMEntry 2 }


pvxLAGPortCrntPMSlotIdx OBJECT-TYPE
    SYNTAX       INTEGER (0|1|3|5|7|9|11|13|15|17|19)
    MAX-ACCESS   not-accessible
    STATUS       current
    DESCRIPTION  "The number of the slot within which the PVX LAG port targeted
                  for PMs is provisioned. For LAG entities, the slot number is 0."
    ::= { pvxLAGPortCrntPMEntry 3 }


pvxLAGPortCrntPMTypeIdx OBJECT-TYPE
    SYNTAX       PvxPortType 
    MAX-ACCESS   not-accessible
    STATUS       current
    DESCRIPTION  "The type of PacketVX port on which the LAG port
			      is provisioned."
    ::= { pvxLAGPortCrntPMEntry 4 }


pvxLAGPortCrntPMIdx OBJECT-TYPE
    SYNTAX       INTEGER (1..24)
    MAX-ACCESS   not-accessible
    STATUS       current
    DESCRIPTION  "The number of the port of the identified type on which the 
                  PVX LAG port targeted for PMs is provisioned."
    ::= { pvxLAGPortCrntPMEntry 5 }


pvxLAGPortCrntPMIntervalTypeIdx OBJECT-TYPE
    SYNTAX       PMIntervalType
    MAX-ACCESS   not-accessible
    STATUS       current
    DESCRIPTION  "The type of PM bin according to interval length."
    ::= { pvxLAGPortCrntPMEntry 6 }


pvxLAGPortCrntPMLACPDURXValue OBJECT-TYPE
    SYNTAX       Unsigned64
    MAX-ACCESS   read-only
    STATUS       current
    DESCRIPTION  "The total Link Access Control PDUs received on the
    			  LAG port."
    ::= { pvxLAGPortCrntPMEntry 7 }


pvxLAGPortCrntPMLACPDURXTimeStamp OBJECT-TYPE
    SYNTAX       DateAndTime
    MAX-ACCESS   read-only
    STATUS       current
    DESCRIPTION  "The date and time stamp of the total
                  Link Access Control PDUs received value."
    ::= { pvxLAGPortCrntPMEntry 8 }


pvxLAGPortCrntPMLACPDURXValidity OBJECT-TYPE
    SYNTAX       PMValidity
    MAX-ACCESS   read-only
    STATUS       current
    DESCRIPTION  "Indicates the validity of the provided total 
                  Link Access Control PDUs received value."
    ::= { pvxLAGPortCrntPMEntry 9 }


pvxLAGPortCrntPMLACPDURXInitialize OBJECT-TYPE
    SYNTAX       InitializeCmd
    MAX-ACCESS   read-write
    STATUS       current
    DESCRIPTION  "Used to initialize the value of the pvxLAGPortCrntPMLACPDURXValue
                  object to 0."
    ::= { pvxLAGPortCrntPMEntry 10 }


pvxLAGPortCrntPMMRKPDURXValue OBJECT-TYPE
    SYNTAX       Unsigned64
    MAX-ACCESS   read-only
    STATUS       current
    DESCRIPTION  "The count of Marker PDUs received on the
    			  LAG port."
    ::= { pvxLAGPortCrntPMEntry 11 }


pvxLAGPortCrntPMMRKPDURXTimeStamp OBJECT-TYPE
    SYNTAX       DateAndTime
    MAX-ACCESS   read-only
    STATUS       current
    DESCRIPTION  "The date and time stamp of the Marker
    			  PDUs received value."
    ::= { pvxLAGPortCrntPMEntry 12 }


pvxLAGPortCrntPMMRKPDURXValidity OBJECT-TYPE
    SYNTAX       PMValidity
    MAX-ACCESS   read-only
    STATUS       current
    DESCRIPTION  "Indicates the validity of the provided Marker
                  PDUs received value."
    ::= { pvxLAGPortCrntPMEntry 13 }


pvxLAGPortCrntPMMRKPDURXInitialize OBJECT-TYPE
    SYNTAX       InitializeCmd
    MAX-ACCESS   read-write
    STATUS       current
    DESCRIPTION  "Used to initialize the value of the pvxLAGPortCrntPMMRKPDURXValue
                  object to 0."
    ::= { pvxLAGPortCrntPMEntry 14 }


pvxLAGPortCrntPMMRKRSPPDURXValue OBJECT-TYPE
    SYNTAX       Unsigned64
    MAX-ACCESS   read-only
    STATUS       current
    DESCRIPTION  "The count of Marker Response PDUs received on the
    			  LAG port."
    ::= { pvxLAGPortCrntPMEntry 15 }


pvxLAGPortCrntPMMRKRSPPDURXTimeStamp OBJECT-TYPE
    SYNTAX       DateAndTime
    MAX-ACCESS   read-only
    STATUS       current
    DESCRIPTION  "The date and time stamp of the Marker Response
    			  PDUs received value."
    ::= { pvxLAGPortCrntPMEntry 16 }


pvxLAGPortCrntPMMRKRSPPDURXValidity OBJECT-TYPE
    SYNTAX       PMValidity
    MAX-ACCESS   read-only
    STATUS       current
    DESCRIPTION  "Indicates the validity of the provided Marker Response
                  PDUs received value."
    ::= { pvxLAGPortCrntPMEntry 17 }


pvxLAGPortCrntPMMRKRSPPDURXInitialize OBJECT-TYPE
    SYNTAX       InitializeCmd
    MAX-ACCESS   read-write
    STATUS       current
    DESCRIPTION  "Used to initialize the value of the pvxLAGPortCrntPMMRKPDURSPRXValue
                  object to 0."
    ::= { pvxLAGPortCrntPMEntry 18 }


pvxLAGPortCrntPMINVLACFRRXValue OBJECT-TYPE
    SYNTAX       Unsigned64
    MAX-ACCESS   read-only
    STATUS       current
    DESCRIPTION  "The count of invalid Link Access Control frames
                  received on the LAG port."
    ::= { pvxLAGPortCrntPMEntry 19 }


pvxLAGPortCrntPMINVLACFRRXTimeStamp OBJECT-TYPE
    SYNTAX       DateAndTime
    MAX-ACCESS   read-only
    STATUS       current
    DESCRIPTION  "The date and time stamp of the count of
                  invalid Link Access Control frames value."
    ::= { pvxLAGPortCrntPMEntry 20 }


pvxLAGPortCrntPMINVLACFRRXValidity OBJECT-TYPE
    SYNTAX       PMValidity
    MAX-ACCESS   read-only
    STATUS       current
    DESCRIPTION  "Indicates the validity of the provided count of
                  invalid Link Access Control frames value."
    ::= { pvxLAGPortCrntPMEntry 21 }


pvxLAGPortCrntPMINVLACFRRXInitialize OBJECT-TYPE
    SYNTAX       InitializeCmd
    MAX-ACCESS   read-write
    STATUS       current
    DESCRIPTION  "Used to initialize the value of the pvxLAGPortCrntPMINVLACFRRXValue
                  object to 0."
    ::= { pvxLAGPortCrntPMEntry 22 }


pvxLAGPortCrntPMLACPDUTXValue OBJECT-TYPE
    SYNTAX       Unsigned64
    MAX-ACCESS   read-only
    STATUS       current
    DESCRIPTION  "The total Link Access Control PDUs transmitted on the
    			  LAG port."
    ::= { pvxLAGPortCrntPMEntry 23 }


pvxLAGPortCrntPMLACPDUTXTimeStamp OBJECT-TYPE
    SYNTAX       DateAndTime
    MAX-ACCESS   read-only
    STATUS       current
    DESCRIPTION  "The date and time stamp of the total
                  Link Access Control PDUs transmitted value."
    ::= { pvxLAGPortCrntPMEntry 24 }


pvxLAGPortCrntPMLACPDUTXValidity OBJECT-TYPE
    SYNTAX       PMValidity
    MAX-ACCESS   read-only
    STATUS       current
    DESCRIPTION  "Indicates the validity of the provided total 
                  Link Access Control PDUs transmitted value."
    ::= { pvxLAGPortCrntPMEntry 25 }


pvxLAGPortCrntPMLACPDUTXInitialize OBJECT-TYPE
    SYNTAX       InitializeCmd
    MAX-ACCESS   read-write
    STATUS       current
    DESCRIPTION  "Used to initialize the value of the pvxLAGPortCrntPMLACPDUTXValue
                  object to 0."
    ::= { pvxLAGPortCrntPMEntry 26 }


pvxLAGPortCrntPMMRKPDUTXValue OBJECT-TYPE
    SYNTAX       Unsigned64
    MAX-ACCESS   read-only
    STATUS       current
    DESCRIPTION  "The count of Marker PDUs transmitted on the
    			  LAG port."
    ::= { pvxLAGPortCrntPMEntry 27 }


pvxLAGPortCrntPMMRKPDUTXTimeStamp OBJECT-TYPE
    SYNTAX       DateAndTime
    MAX-ACCESS   read-only
    STATUS       current
    DESCRIPTION  "The date and time stamp of the Marker
    			  PDUs transmitted value."
    ::= { pvxLAGPortCrntPMEntry 28 }


pvxLAGPortCrntPMMRKPDUTXValidity OBJECT-TYPE
    SYNTAX       PMValidity
    MAX-ACCESS   read-only
    STATUS       current
    DESCRIPTION  "Indicates the validity of the provided Marker
                  PDUs transmitted value."
    ::= { pvxLAGPortCrntPMEntry 29 }


pvxLAGPortCrntPMMRKPDUTXInitialize OBJECT-TYPE
    SYNTAX       InitializeCmd
    MAX-ACCESS   read-write
    STATUS       current
    DESCRIPTION  "Used to initialize the value of the pvxLAGPortCrntPMMRKPDUTXValue
                  object to 0."
    ::= { pvxLAGPortCrntPMEntry 30 }


pvxLAGPortCrntPMMRKRSPPDUTXValue OBJECT-TYPE
    SYNTAX       Unsigned64
    MAX-ACCESS   read-only
    STATUS       current
    DESCRIPTION  "The count of Marker Response PDUs transmitted on the
    			  LAG port."
    ::= { pvxLAGPortCrntPMEntry 31 }


pvxLAGPortCrntPMMRKRSPPDUTXTimeStamp OBJECT-TYPE
    SYNTAX       DateAndTime
    MAX-ACCESS   read-only
    STATUS       current
    DESCRIPTION  "The date and time stamp of the Marker Response
    			  PDUs transmitted value."
    ::= { pvxLAGPortCrntPMEntry 32 }


pvxLAGPortCrntPMMRKRSPPDUTXValidity OBJECT-TYPE
    SYNTAX       PMValidity
    MAX-ACCESS   read-only
    STATUS       current
    DESCRIPTION  "Indicates the validity of the provided Marker Response
                  PDUs transmitted value."
    ::= { pvxLAGPortCrntPMEntry 33 }


pvxLAGPortCrntPMMRKRSPPDUTXInitialize OBJECT-TYPE
    SYNTAX       InitializeCmd
    MAX-ACCESS   read-write
    STATUS       current
    DESCRIPTION  "Used to initialize the value of the pvxLAGPortCrntPMMRKPDURSPTXValue
                  object to 0."
    ::= { pvxLAGPortCrntPMEntry 34 }



-----------------------------------------------------------------------
-- Objects used to retrieve historical LAG Port
-- Performance Monitoring statistics for PacketVX Interfaces
-----------------------------------------------------------------------


pvxLAGPortHistPMTable OBJECT-TYPE
    SYNTAX       SEQUENCE OF PvxLAGPortHistPMEntry
    MAX-ACCESS   not-accessible
    STATUS       current
    DESCRIPTION  "A table of historical performance monitoring statistics
                  collected for the PacketVX LAG port interfaces on the NE."
    ::= { performance 37 }


pvxLAGPortHistPMEntry OBJECT-TYPE
    SYNTAX       PvxLAGPortHistPMEntry
    MAX-ACCESS   not-accessible
    STATUS       current
    DESCRIPTION  "The row entry object of the PacketVX LAG port historical
                  performance monitoring table. Each row of this table contains
                  a full set of PM statistics and related data for a historical
                  measurement interval for a given PVX LAG Port."
    INDEX        { pvxLAGPortHistPMSwitchIdx,
			       pvxLAGPortHistPMShelfIdx,
                   pvxLAGPortHistPMSlotIdx,
                   pvxLAGPortHistPMTypeIdx,
                   pvxLAGPortHistPMIdx,
                   pvxLAGPortHistPMIntervalTypeIdx,
                   pvxLAGPortHistPMIntervalIdx }
    ::= { pvxLAGPortHistPMTable 1 }


PvxLAGPortHistPMEntry ::= SEQUENCE { pvxLAGPortHistPMSwitchIdx                 INTEGER,
					     		     pvxLAGPortHistPMShelfIdx                  INTEGER,
                                     pvxLAGPortHistPMSlotIdx                   INTEGER,
                                     pvxLAGPortHistPMTypeIdx                   PvxPortType,
                                     pvxLAGPortHistPMIdx                       INTEGER,
                                     pvxLAGPortHistPMIntervalTypeIdx           PMIntervalType,
                                     pvxLAGPortHistPMIntervalIdx               INTEGER,
                                     pvxLAGPortHistPMLACPDURXValue             Unsigned64,
                                     pvxLAGPortHistPMLACPDURXTimeStamp         DateAndTime,
                                     pvxLAGPortHistPMLACPDURXValidity          PMValidity,
                                     pvxLAGPortHistPMLACPDURXInitialize        InitializeCmd,
                                     pvxLAGPortHistPMMRKPDURXValue             Unsigned64,
                                     pvxLAGPortHistPMMRKPDURXTimeStamp         DateAndTime,
                                     pvxLAGPortHistPMMRKPDURXValidity          PMValidity,
                                     pvxLAGPortHistPMMRKPDURXInitialize        InitializeCmd,
                                     pvxLAGPortHistPMMRKRSPPDURXValue          Unsigned64,
                                     pvxLAGPortHistPMMRKRSPPDURXTimeStamp      DateAndTime,
                                     pvxLAGPortHistPMMRKRSPPDURXValidity       PMValidity,
                                     pvxLAGPortHistPMMRKRSPPDURXInitialize     InitializeCmd,
                                     pvxLAGPortHistPMINVLACFRRXValue           Unsigned64,
                                     pvxLAGPortHistPMINVLACFRRXTimeStamp       DateAndTime,
                                     pvxLAGPortHistPMINVLACFRRXValidity        PMValidity,
                                     pvxLAGPortHistPMINVLACFRRXInitialize      InitializeCmd,
                                     pvxLAGPortHistPMLACPDUTXValue             Unsigned64,
                                     pvxLAGPortHistPMLACPDUTXTimeStamp         DateAndTime,
                                     pvxLAGPortHistPMLACPDUTXValidity          PMValidity,
                                     pvxLAGPortHistPMLACPDUTXInitialize        InitializeCmd,
                                     pvxLAGPortHistPMMRKPDUTXValue             Unsigned64,
                                     pvxLAGPortHistPMMRKPDUTXTimeStamp         DateAndTime,
                                     pvxLAGPortHistPMMRKPDUTXValidity          PMValidity,
                                     pvxLAGPortHistPMMRKPDUTXInitialize        InitializeCmd,
                                     pvxLAGPortHistPMMRKRSPPDUTXValue          Unsigned64,
                                     pvxLAGPortHistPMMRKRSPPDUTXTimeStamp      DateAndTime,
                                     pvxLAGPortHistPMMRKRSPPDUTXValidity       PMValidity,
                                     pvxLAGPortHistPMMRKRSPPDUTXInitialize     InitializeCmd }


pvxLAGPortHistPMSwitchIdx OBJECT-TYPE
    SYNTAX       INTEGER(1..11) 
    MAX-ACCESS   not-accessible
    STATUS       current
    DESCRIPTION  "The identifier of the ethernet switch instance on which
			      the PVX LAG port is provisioned."
    ::= {pvxLAGPortHistPMEntry 1 }


pvxLAGPortHistPMShelfIdx OBJECT-TYPE
    SYNTAX       INTEGER (0|1|11|21|31)
    MAX-ACCESS   not-accessible
    STATUS       current
    DESCRIPTION  "The number of the shelf on which the PVX LAG port targeted for
                  PMs is provisioned. For LAG entities, the shelf number is 0."
    ::= { pvxLAGPortHistPMEntry 2 }


pvxLAGPortHistPMSlotIdx OBJECT-TYPE
    SYNTAX       INTEGER (0|1|3|5|7|9|11|13|15|17|19)
    MAX-ACCESS   not-accessible
    STATUS       current
    DESCRIPTION  "The number of the slot within which the PVX LAG port targeted
                  for PMs is provisioned. For LAG entities, the slot number is 0."
    ::= { pvxLAGPortHistPMEntry 3 }


pvxLAGPortHistPMTypeIdx OBJECT-TYPE
    SYNTAX       PvxPortType 
    MAX-ACCESS   not-accessible
    STATUS       current
    DESCRIPTION  "The type of PacketVX port on which the LAG port
			      is provisioned."
    ::= { pvxLAGPortHistPMEntry 4 }


pvxLAGPortHistPMIdx OBJECT-TYPE
    SYNTAX       INTEGER (1..24)
    MAX-ACCESS   not-accessible
    STATUS       current
    DESCRIPTION  "The number of the port of the identified type on which the 
                  PVX LAG port targeted for PMs is provisioned."
    ::= { pvxLAGPortHistPMEntry 5 }


pvxLAGPortHistPMIntervalTypeIdx OBJECT-TYPE
    SYNTAX       PMIntervalType
    MAX-ACCESS   not-accessible
    STATUS       current
    DESCRIPTION  "The type of PM bin according to interval length."
    ::= { pvxLAGPortHistPMEntry 6 }


pvxLAGPortHistPMIntervalIdx OBJECT-TYPE
    SYNTAX       INTEGER (1..96)
    MAX-ACCESS   not-accessible
    STATUS       current
    DESCRIPTION  "The specific PM bin number. The range is 1 to 96 for the
                  15-minute historical bins. For the 1-day historical bin, the
                  value is 1."
    ::= { pvxLAGPortHistPMEntry 7 }


pvxLAGPortHistPMLACPDURXValue OBJECT-TYPE
    SYNTAX       Unsigned64
    MAX-ACCESS   read-only
    STATUS       current
    DESCRIPTION  "The total Link Access Control PDUs received on the
    			  LAG port."
    ::= { pvxLAGPortHistPMEntry 8 }


pvxLAGPortHistPMLACPDURXTimeStamp OBJECT-TYPE
    SYNTAX       DateAndTime
    MAX-ACCESS   read-only
    STATUS       current
    DESCRIPTION  "The date and time stamp of the total
                  Link Access Control PDUs received value."
    ::= { pvxLAGPortHistPMEntry 9 }


pvxLAGPortHistPMLACPDURXValidity OBJECT-TYPE
    SYNTAX       PMValidity
    MAX-ACCESS   read-only
    STATUS       current
    DESCRIPTION  "Indicates the validity of the provided total 
                  Link Access Control PDUs received value."
    ::= { pvxLAGPortHistPMEntry 10 }


pvxLAGPortHistPMLACPDURXInitialize OBJECT-TYPE
    SYNTAX       InitializeCmd
    MAX-ACCESS   read-write
    STATUS       current
    DESCRIPTION  "Used to initialize the value of the pvxLAGPortHistPMLACPDURXValue
                  object to 0."
    ::= { pvxLAGPortHistPMEntry 11 }


pvxLAGPortHistPMMRKPDURXValue OBJECT-TYPE
    SYNTAX       Unsigned64
    MAX-ACCESS   read-only
    STATUS       current
    DESCRIPTION  "The count of Marker PDUs received on the
    			  LAG port."
    ::= { pvxLAGPortHistPMEntry 12 }


pvxLAGPortHistPMMRKPDURXTimeStamp OBJECT-TYPE
    SYNTAX       DateAndTime
    MAX-ACCESS   read-only
    STATUS       current
    DESCRIPTION  "The date and time stamp of the Marker
    			  PDUs received value."
    ::= { pvxLAGPortHistPMEntry 13 }


pvxLAGPortHistPMMRKPDURXValidity OBJECT-TYPE
    SYNTAX       PMValidity
    MAX-ACCESS   read-only
    STATUS       current
    DESCRIPTION  "Indicates the validity of the provided Marker
                  PDUs received value."
    ::= { pvxLAGPortHistPMEntry 14 }


pvxLAGPortHistPMMRKPDURXInitialize OBJECT-TYPE
    SYNTAX       InitializeCmd
    MAX-ACCESS   read-write
    STATUS       current
    DESCRIPTION  "Used to initialize the value of the pvxLAGPortHistPMMRKPDURXValue
                  object to 0."
    ::= { pvxLAGPortHistPMEntry 15 }


pvxLAGPortHistPMMRKRSPPDURXValue OBJECT-TYPE
    SYNTAX       Unsigned64
    MAX-ACCESS   read-only
    STATUS       current
    DESCRIPTION  "The count of Marker Response PDUs received on the
    			  LAG port."
    ::= { pvxLAGPortHistPMEntry 16 }


pvxLAGPortHistPMMRKRSPPDURXTimeStamp OBJECT-TYPE
    SYNTAX       DateAndTime
    MAX-ACCESS   read-only
    STATUS       current
    DESCRIPTION  "The date and time stamp of the Marker Response
    			  PDUs received value."
    ::= { pvxLAGPortHistPMEntry 17 }


pvxLAGPortHistPMMRKRSPPDURXValidity OBJECT-TYPE
    SYNTAX       PMValidity
    MAX-ACCESS   read-only
    STATUS       current
    DESCRIPTION  "Indicates the validity of the provided Marker Response
                  PDUs received value."
    ::= { pvxLAGPortHistPMEntry 18 }


pvxLAGPortHistPMMRKRSPPDURXInitialize OBJECT-TYPE
    SYNTAX       InitializeCmd
    MAX-ACCESS   read-write
    STATUS       current
    DESCRIPTION  "Used to initialize the value of the pvxLAGPortHistPMMRKPDURSPRXValue
                  object to 0."
    ::= { pvxLAGPortHistPMEntry 19 }


pvxLAGPortHistPMINVLACFRRXValue OBJECT-TYPE
    SYNTAX       Unsigned64
    MAX-ACCESS   read-only
    STATUS       current
    DESCRIPTION  "The count of invalid Link Access Control frames
                  received on the LAG port."
    ::= { pvxLAGPortHistPMEntry 20 }


pvxLAGPortHistPMINVLACFRRXTimeStamp OBJECT-TYPE
    SYNTAX       DateAndTime
    MAX-ACCESS   read-only
    STATUS       current
    DESCRIPTION  "The date and time stamp of the count of
                  invalid Link Access Control frames value."
    ::= { pvxLAGPortHistPMEntry 21 }


pvxLAGPortHistPMINVLACFRRXValidity OBJECT-TYPE
    SYNTAX       PMValidity
    MAX-ACCESS   read-only
    STATUS       current
    DESCRIPTION  "Indicates the validity of the provided count of
                  invalid Link Access Control frames value."
    ::= { pvxLAGPortHistPMEntry 22 }


pvxLAGPortHistPMINVLACFRRXInitialize OBJECT-TYPE
    SYNTAX       InitializeCmd
    MAX-ACCESS   read-write
    STATUS       current
    DESCRIPTION  "Used to initialize the value of the pvxLAGPortHistPMINVLACFRRXValue
                  object to 0."
    ::= { pvxLAGPortHistPMEntry 23 }


pvxLAGPortHistPMLACPDUTXValue OBJECT-TYPE
    SYNTAX       Unsigned64
    MAX-ACCESS   read-only
    STATUS       current
    DESCRIPTION  "The total Link Access Control PDUs transmitted on the
    			  LAG port."
    ::= { pvxLAGPortHistPMEntry 24 }


pvxLAGPortHistPMLACPDUTXTimeStamp OBJECT-TYPE
    SYNTAX       DateAndTime
    MAX-ACCESS   read-only
    STATUS       current
    DESCRIPTION  "The date and time stamp of the total
                  Link Access Control PDUs transmitted value."
    ::= { pvxLAGPortHistPMEntry 25 }


pvxLAGPortHistPMLACPDUTXValidity OBJECT-TYPE
    SYNTAX       PMValidity
    MAX-ACCESS   read-only
    STATUS       current
    DESCRIPTION  "Indicates the validity of the provided total 
                  Link Access Control PDUs transmitted value."
    ::= { pvxLAGPortHistPMEntry 26 }


pvxLAGPortHistPMLACPDUTXInitialize OBJECT-TYPE
    SYNTAX       InitializeCmd
    MAX-ACCESS   read-write
    STATUS       current
    DESCRIPTION  "Used to initialize the value of the pvxLAGPortHistPMLACPDUTXValue
                  object to 0."
    ::= { pvxLAGPortHistPMEntry 27 }


pvxLAGPortHistPMMRKPDUTXValue OBJECT-TYPE
    SYNTAX       Unsigned64
    MAX-ACCESS   read-only
    STATUS       current
    DESCRIPTION  "The count of Marker PDUs transmitted on the
    			  LAG port."
    ::= { pvxLAGPortHistPMEntry 28 }


pvxLAGPortHistPMMRKPDUTXTimeStamp OBJECT-TYPE
    SYNTAX       DateAndTime
    MAX-ACCESS   read-only
    STATUS       current
    DESCRIPTION  "The date and time stamp of the Marker
    			  PDUs transmitted value."
    ::= { pvxLAGPortHistPMEntry 29 }


pvxLAGPortHistPMMRKPDUTXValidity OBJECT-TYPE
    SYNTAX       PMValidity
    MAX-ACCESS   read-only
    STATUS       current
    DESCRIPTION  "Indicates the validity of the provided Marker
                  PDUs transmitted value."
    ::= { pvxLAGPortHistPMEntry 30 }


pvxLAGPortHistPMMRKPDUTXInitialize OBJECT-TYPE
    SYNTAX       InitializeCmd
    MAX-ACCESS   read-write
    STATUS       current
    DESCRIPTION  "Used to initialize the value of the pvxLAGPortHistPMMRKPDUTXValue
                  object to 0."
    ::= { pvxLAGPortHistPMEntry 31 }


pvxLAGPortHistPMMRKRSPPDUTXValue OBJECT-TYPE
    SYNTAX       Unsigned64
    MAX-ACCESS   read-only
    STATUS       current
    DESCRIPTION  "The count of Marker Response PDUs transmitted on the
    			  LAG port."
    ::= { pvxLAGPortHistPMEntry 32 }


pvxLAGPortHistPMMRKRSPPDUTXTimeStamp OBJECT-TYPE
    SYNTAX       DateAndTime
    MAX-ACCESS   read-only
    STATUS       current
    DESCRIPTION  "The date and time stamp of the Marker Response
    			  PDUs transmitted value."
    ::= { pvxLAGPortHistPMEntry 33 }


pvxLAGPortHistPMMRKRSPPDUTXValidity OBJECT-TYPE
    SYNTAX       PMValidity
    MAX-ACCESS   read-only
    STATUS       current
    DESCRIPTION  "Indicates the validity of the provided Marker Response
                  PDUs transmitted value."
    ::= { pvxLAGPortHistPMEntry 34 }


pvxLAGPortHistPMMRKRSPPDUTXInitialize OBJECT-TYPE
    SYNTAX       InitializeCmd
    MAX-ACCESS   read-write
    STATUS       current
    DESCRIPTION  "Used to initialize the value of the pvxLAGPortHistPMMRKPDURSPTXValue
                  object to 0."
    ::= { pvxLAGPortHistPMEntry 35 }



-----------------------------------------------------------------------
-- Objects used to retrieve current Performance Monitoring
-- statistics for Ethernet Services Objects
-----------------------------------------------------------------------

pvxESrvcCrntPMTable OBJECT-TYPE
    SYNTAX       SEQUENCE OF PvxESrvcCrntPMEntry
    MAX-ACCESS   not-accessible
    STATUS       current
    DESCRIPTION  "A table of current performance monitoring statistics collected
                  for the PacketVX ethernet services objects."
    ::= { performance 40 }


pvxESrvcCrntPMEntry OBJECT-TYPE
    SYNTAX       PvxESrvcCrntPMEntry
    MAX-ACCESS   not-accessible
    STATUS       current
    DESCRIPTION  "The row entry object of the PacketVX ethernet services current
                  performance monitoring table. Each row of this table contains
                  a full set of PM statistics and related data for a current
                  measurement interval for a given ethernet service instance."
    INDEX        { pvxESrvcCrntPMSwitchIdx,
    			   pvxESrvcCrntPMESrvcNameIdx,
    			   pvxESrvcCrntPMIntervalTypeIdx }
    ::= { pvxESrvcCrntPMTable 1 }


PvxESrvcCrntPMEntry ::= SEQUENCE { pvxESrvcCrntPMSwitchIdx        INTEGER,
                                   pvxESrvcCrntPMESrvcNameIdx     DisplayString,
                                   pvxESrvcCrntPMIntervalTypeIdx  PMIntervalType,
                                   pvxESrvcCrntPMUASValue         Unsigned32,
                                   pvxESrvcCrntPMUASTimeStamp     DateAndTime,
                                   pvxESrvcCrntPMUASValidity      PMValidity,
                                   pvxESrvcCrntPMUASInitialize    InitializeCmd }
                                  
                                  
pvxESrvcCrntPMSwitchIdx OBJECT-TYPE
   	SYNTAX       INTEGER(1..11)
   	MAX-ACCESS   not-accessible
   	STATUS       current
   	DESCRIPTION  "The identifier of the ethernet switch instance on which the
                  ethernet service is provisioned."
    ::= { pvxESrvcCrntPMEntry 1 }


pvxESrvcCrntPMESrvcNameIdx OBJECT-TYPE
   	SYNTAX       DisplayString (SIZE(1..32))
   	MAX-ACCESS   not-accessible
   	STATUS       current
   	DESCRIPTION  "The name of the ethernet service."
    ::= { pvxESrvcCrntPMEntry 2 }


pvxESrvcCrntPMIntervalTypeIdx OBJECT-TYPE
    SYNTAX       PMIntervalType
    MAX-ACCESS   not-accessible
    STATUS       current
    DESCRIPTION  "The type of PM bin according to interval length."
    ::= { pvxESrvcCrntPMEntry 3 }


pvxESrvcCrntPMUASValue OBJECT-TYPE
    SYNTAX       Unsigned32
    MAX-ACCESS   read-write
    STATUS       current
    DESCRIPTION  "The count of unavailable seconds for the ethernet service."
    ::= { pvxESrvcCrntPMEntry 4 }


pvxESrvcCrntPMUASTimeStamp OBJECT-TYPE
    SYNTAX       DateAndTime
    MAX-ACCESS   read-only
    STATUS       current
    DESCRIPTION  "The date and time stamp of the ethernet service unavailable
    		      seconds count value."
    ::= { pvxESrvcCrntPMEntry 5 }


pvxESrvcCrntPMUASValidity OBJECT-TYPE
    SYNTAX       PMValidity
    MAX-ACCESS   read-only
    STATUS       current
    DESCRIPTION  "Indicates the validity of the provided ethernet service unavailable
    		      seconds count value."
    ::= { pvxESrvcCrntPMEntry 6 }


pvxESrvcCrntPMUASInitialize OBJECT-TYPE
    SYNTAX       InitializeCmd
    MAX-ACCESS   read-write
    STATUS       current
    DESCRIPTION  "Used to initialize the value of the pvxESrvcCrntPMUASValue object
                  to 0."
    ::= { pvxESrvcCrntPMEntry 7 }



-----------------------------------------------------------------------
-- Objects used to retrieve historical Performance Monitoring
-- statistics for Ethernet Services Objects
-----------------------------------------------------------------------

pvxESrvcHistPMTable OBJECT-TYPE
    SYNTAX       SEQUENCE OF PvxESrvcHistPMEntry
    MAX-ACCESS   not-accessible
    STATUS       current
    DESCRIPTION  "A table of historical performance monitoring statistics collected
                  for the PacketVX ethernet services objects."
    ::= { performance 41 }


pvxESrvcHistPMEntry OBJECT-TYPE
    SYNTAX       PvxESrvcHistPMEntry
    MAX-ACCESS   not-accessible
    STATUS       current
    DESCRIPTION  "The row entry object of the PacketVX ethernet services historical
                  performance monitoring table. Each row of this table contains
                  a full set of PM statistics and related data for a historical
                  measurement interval for a given ethernet service instance."
    INDEX        { pvxESrvcHistPMSwitchIdx,
    			   pvxESrvcHistPMESrvcNameIdx,
    			   pvxESrvcHistPMIntervalTypeIdx,
    			   pvxESrvcHistPMIntervalIdx }
    ::= { pvxESrvcHistPMTable 1 }


PvxESrvcHistPMEntry ::= SEQUENCE { pvxESrvcHistPMSwitchIdx        INTEGER,
                                   pvxESrvcHistPMESrvcNameIdx     DisplayString,
                                   pvxESrvcHistPMIntervalTypeIdx  PMIntervalType,
                                   pvxESrvcHistPMIntervalIdx      INTEGER,
                                   pvxESrvcHistPMUASValue         Unsigned32,
                                   pvxESrvcHistPMUASTimeStamp     DateAndTime,
                                   pvxESrvcHistPMUASValidity      PMValidity,
                                   pvxESrvcHistPMUASInitialize    InitializeCmd }
                                  
                                  
pvxESrvcHistPMSwitchIdx OBJECT-TYPE
   	SYNTAX       INTEGER(1..11)
   	MAX-ACCESS   not-accessible
   	STATUS       current
   	DESCRIPTION  "The identifier of the ethernet switch instance on which the
                  ethernet service is provisioned."
    ::= { pvxESrvcHistPMEntry 1 }


pvxESrvcHistPMESrvcNameIdx OBJECT-TYPE
   	SYNTAX       DisplayString (SIZE(1..32))
   	MAX-ACCESS   not-accessible
   	STATUS       current
   	DESCRIPTION  "The name of the ethernet service."
    ::= { pvxESrvcHistPMEntry 2 }


pvxESrvcHistPMIntervalTypeIdx OBJECT-TYPE
    SYNTAX       PMIntervalType
    MAX-ACCESS   not-accessible
    STATUS       current
    DESCRIPTION  "The type of PM bin according to interval length."
    ::= { pvxESrvcHistPMEntry 3 }


pvxESrvcHistPMIntervalIdx OBJECT-TYPE
    SYNTAX       INTEGER (1..96)
    MAX-ACCESS   not-accessible
    STATUS       current
    DESCRIPTION  "The specific PM bin number. The range is 1 to 96 for the
                  15-minute historical bins. For the 1-day historical bin, the
                  value is 1."
    ::= { pvxESrvcHistPMEntry 4 }


pvxESrvcHistPMUASValue OBJECT-TYPE
    SYNTAX       Unsigned32
    MAX-ACCESS   read-write
    STATUS       current
    DESCRIPTION  "The count of unavailable seconds for the ethernet service."
    ::= { pvxESrvcHistPMEntry 5 }


pvxESrvcHistPMUASTimeStamp OBJECT-TYPE
    SYNTAX       DateAndTime
    MAX-ACCESS   read-only
    STATUS       current
    DESCRIPTION  "The date and time stamp of the ethernet service unavailable
    		      seconds count value."
    ::= { pvxESrvcHistPMEntry 6 }


pvxESrvcHistPMUASValidity OBJECT-TYPE
    SYNTAX       PMValidity
    MAX-ACCESS   read-only
    STATUS       current
    DESCRIPTION  "Indicates the validity of the provided ethernet service unavailable
    		      seconds count value."
    ::= { pvxESrvcHistPMEntry 7 }


pvxESrvcHistPMUASInitialize OBJECT-TYPE
    SYNTAX       InitializeCmd
    MAX-ACCESS   read-write
    STATUS       current
    DESCRIPTION  "Used to initialize the value of the pvxESrvcHistPMUASValue object
                  to 0."
    ::= { pvxESrvcHistPMEntry 8 }



-----------------------------------------------------------------------
-- Objects used to retrieve current Performance Monitoring
-- statistics for perEVC and perCoS Objects
-----------------------------------------------------------------------

pvxESrvcBWPrflCrntPMTable OBJECT-TYPE
    SYNTAX       SEQUENCE OF PvxESrvcBWPrflCrntPMEntry
    MAX-ACCESS   not-accessible
    STATUS       current
    DESCRIPTION  "A table of current performance monitoring statistics collected
                  for the PacketVX perEVC and perCoS objects."
    ::= { performance 42 }


pvxESrvcBWPrflCrntPMEntry OBJECT-TYPE
    SYNTAX       PvxESrvcBWPrflCrntPMEntry
    MAX-ACCESS   not-accessible
    STATUS       current
    DESCRIPTION  "The row entry object of the PacketVX ethernet services
    			  bandwidth profile current performance monitoring table.
    			  Each row of this table contains a full set of PM statistics
    			  and related data for a current measurement interval for a
    			  given perEVC or perCoS instance."
    INDEX        { pvxESrvcBWPrflCrntPMSwitchIdx,
                   pvxESrvcBWPrflCrntPMShelfIdx,
                   pvxESrvcBWPrflCrntPMSlotIdx,
                   pvxESrvcBWPrflCrntPMPortTypeIdx,
                   pvxESrvcBWPrflCrntPMPortIdx,
    			   pvxESrvcBWPrflCrntPMESrvcNameIdx,
    			   pvxESrvcBWPrflCrntPMPlcyNameIdx,
    			   pvxESrvcBWPrflCrntPMClsMapNameIdx,
    			   pvxESrvcBWPrflCrntPMDirectionIdx,
    			   pvxESrvcBWPrflCrntPMIntervalTypeIdx }
    ::= { pvxESrvcBWPrflCrntPMTable 1 }


PvxESrvcBWPrflCrntPMEntry ::= SEQUENCE { pvxESrvcBWPrflCrntPMSwitchIdx               INTEGER,
					     		         pvxESrvcBWPrflCrntPMShelfIdx                INTEGER,
                                         pvxESrvcBWPrflCrntPMSlotIdx                 INTEGER,
                                         pvxESrvcBWPrflCrntPMPortTypeIdx             PvxPortType,
                                         pvxESrvcBWPrflCrntPMPortIdx                 INTEGER,
                                         pvxESrvcBWPrflCrntPMESrvcNameIdx            DisplayString,
                                         pvxESrvcBWPrflCrntPMPlcyNameIdx             DisplayString,
                                         pvxESrvcBWPrflCrntPMClsMapNameIdx           DisplayString,
                                         pvxESrvcBWPrflCrntPMDirectionIdx            INTEGER,
                                         pvxESrvcBWPrflCrntPMIntervalTypeIdx         PMIntervalType,
                                         pvxESrvcBWPrflCrntPMOctetsTotalValue        Unsigned64,
                                         pvxESrvcBWPrflCrntPMOctetsTotalTimeStamp    DateAndTime,
                                         pvxESrvcBWPrflCrntPMOctetsTotalValidity     PMValidity,
                                         pvxESrvcBWPrflCrntPMOctetsTotalInitialize   InitializeCmd,
                                         pvxESrvcBWPrflCrntPMOctetsVltValue          Unsigned64,
                                         pvxESrvcBWPrflCrntPMOctetsVltTimeStamp      DateAndTime,
                                         pvxESrvcBWPrflCrntPMOctetsVltValidity       PMValidity,
                                         pvxESrvcBWPrflCrntPMOctetsVltInitialize     InitializeCmd,
                                         pvxESrvcBWPrflCrntPMOctetsCnfExcValue       Unsigned64,
                                         pvxESrvcBWPrflCrntPMOctetsCnfExcTimeStamp   DateAndTime,
                                         pvxESrvcBWPrflCrntPMOctetsCnfExcValidity    PMValidity,
                                         pvxESrvcBWPrflCrntPMOctetsCnfExcInitialize  InitializeCmd,
                                         pvxESrvcBWPrflCrntPMBDWUtlzValue            FixedX100,
                                         pvxESrvcBWPrflCrntPMBDWUtlzTimeStamp        DateAndTime,
                                         pvxESrvcBWPrflCrntPMBDWUtlzValidity         PMValidity,
                                         pvxESrvcBWPrflCrntPMBDWUtlzInitialize       InitializeCmd }
                                  
                                  
pvxESrvcBWPrflCrntPMSwitchIdx OBJECT-TYPE
   	SYNTAX       INTEGER(1..11)
   	MAX-ACCESS   not-accessible
   	STATUS       current
   	DESCRIPTION  "The identifier of the ethernet switch instance on which the
                  monitored object is provisioned."
    ::= { pvxESrvcBWPrflCrntPMEntry 1 }


pvxESrvcBWPrflCrntPMShelfIdx OBJECT-TYPE
    SYNTAX       INTEGER (0|1|11|21|31)
    MAX-ACCESS   not-accessible
    STATUS       current
    DESCRIPTION  "The number of the shelf on which the monitored object is
                  provisioned."
    ::= { pvxESrvcBWPrflCrntPMEntry 2 }


pvxESrvcBWPrflCrntPMSlotIdx OBJECT-TYPE
    SYNTAX       INTEGER (0|1|3|5|7|9|11|13|15|17|19)
    MAX-ACCESS   not-accessible
    STATUS       current
    DESCRIPTION  "The number of the slot on which the monitored object is
                  provisioned."
    ::= { pvxESrvcBWPrflCrntPMEntry 3 }


pvxESrvcBWPrflCrntPMPortTypeIdx OBJECT-TYPE
    SYNTAX       PvxPortType 
    MAX-ACCESS   not-accessible
    STATUS       current
    DESCRIPTION  "The type of PacketVX port on which the monitored object
			      is provisioned."
    ::= { pvxESrvcBWPrflCrntPMEntry 4 }


pvxESrvcBWPrflCrntPMPortIdx OBJECT-TYPE
    SYNTAX       INTEGER (1..24)
    MAX-ACCESS   not-accessible
    STATUS       current
    DESCRIPTION  "The number of the port of the identified type on which the 
                  monitored object is provisioned."
    ::= { pvxESrvcBWPrflCrntPMEntry 5 }


pvxESrvcBWPrflCrntPMESrvcNameIdx OBJECT-TYPE
   	SYNTAX       DisplayString (SIZE(1..32))
   	MAX-ACCESS   not-accessible
   	STATUS       current
   	DESCRIPTION  "The name of the ethernet service."
    ::= { pvxESrvcBWPrflCrntPMEntry 6 }


pvxESrvcBWPrflCrntPMPlcyNameIdx OBJECT-TYPE
   	SYNTAX       DisplayString (SIZE(1..32))
   	MAX-ACCESS   not-accessible
   	STATUS       current
   	DESCRIPTION  "The name of the policy."
    ::= { pvxESrvcBWPrflCrntPMEntry 7 }


pvxESrvcBWPrflCrntPMClsMapNameIdx OBJECT-TYPE
   	SYNTAX       DisplayString (SIZE(1..32))
   	MAX-ACCESS   not-accessible
   	STATUS       current
   	DESCRIPTION  "The name of the class map."
    ::= { pvxESrvcBWPrflCrntPMEntry 8 }


pvxESrvcBWPrflCrntPMDirectionIdx OBJECT-TYPE
    SYNTAX       INTEGER { ingress (1),
                           egress  (2) }
    MAX-ACCESS   not-accessible
    STATUS       current
    DESCRIPTION  "The direction of traffic of the monitored object."
    ::= { pvxESrvcBWPrflCrntPMEntry 9 }


pvxESrvcBWPrflCrntPMIntervalTypeIdx OBJECT-TYPE
    SYNTAX       PMIntervalType
    MAX-ACCESS   not-accessible
    STATUS       current
    DESCRIPTION  "The type of PM bin according to interval length."
    ::= { pvxESrvcBWPrflCrntPMEntry 10 }


pvxESrvcBWPrflCrntPMOctetsTotalValue OBJECT-TYPE
    SYNTAX       Unsigned64
    MAX-ACCESS   read-only
    STATUS       current
    DESCRIPTION  "The total count of octets received or transmitted for the
                  monitored service."
    ::= { pvxESrvcBWPrflCrntPMEntry 11 }


pvxESrvcBWPrflCrntPMOctetsTotalTimeStamp OBJECT-TYPE
    SYNTAX       DateAndTime
    MAX-ACCESS   read-only
    STATUS       current
    DESCRIPTION  "The date and time stamp of the total octets count value."
    ::= { pvxESrvcBWPrflCrntPMEntry 12 }


pvxESrvcBWPrflCrntPMOctetsTotalValidity OBJECT-TYPE
    SYNTAX       PMValidity
    MAX-ACCESS   read-only
    STATUS       current
    DESCRIPTION  "Indicates the validity of the provided total octets count value."
    ::= { pvxESrvcBWPrflCrntPMEntry 13 }


pvxESrvcBWPrflCrntPMOctetsTotalInitialize OBJECT-TYPE
    SYNTAX       InitializeCmd
    MAX-ACCESS   read-write
    STATUS       current
    DESCRIPTION  "Used to initialize the value of the
                  pvxESrvcBWPrflCrntPMOctetsTotalValue object to 0."
    ::= { pvxESrvcBWPrflCrntPMEntry 14 }


pvxESrvcBWPrflCrntPMOctetsVltValue OBJECT-TYPE
    SYNTAX       Unsigned64
    MAX-ACCESS   read-only
    STATUS       current
    DESCRIPTION  "The count of octets violate for the monitored service."
    ::= { pvxESrvcBWPrflCrntPMEntry 15 }


pvxESrvcBWPrflCrntPMOctetsVltTimeStamp OBJECT-TYPE
    SYNTAX       DateAndTime
    MAX-ACCESS   read-only
    STATUS       current
    DESCRIPTION  "The date and time stamp of the octets violate count value."
    ::= { pvxESrvcBWPrflCrntPMEntry 16 }


pvxESrvcBWPrflCrntPMOctetsVltValidity OBJECT-TYPE
    SYNTAX       PMValidity
    MAX-ACCESS   read-only
    STATUS       current
    DESCRIPTION  "Indicates the validity of the provided octets violate count value."
    ::= { pvxESrvcBWPrflCrntPMEntry 17 }


pvxESrvcBWPrflCrntPMOctetsVltInitialize OBJECT-TYPE
    SYNTAX       InitializeCmd
    MAX-ACCESS   read-write
    STATUS       current
    DESCRIPTION  "Used to initialize the value of the
                  pvxESrvcBWPrflCrntPMOctetsVltValue object to 0."
    ::= { pvxESrvcBWPrflCrntPMEntry 18 }


pvxESrvcBWPrflCrntPMOctetsCnfExcValue OBJECT-TYPE
    SYNTAX       Unsigned64
    MAX-ACCESS   read-only
    STATUS       current
    DESCRIPTION  "The count of octets conform and exceeded for the
                  monitored service."
    ::= { pvxESrvcBWPrflCrntPMEntry 19 }


pvxESrvcBWPrflCrntPMOctetsCnfExcTimeStamp OBJECT-TYPE
    SYNTAX       DateAndTime
    MAX-ACCESS   read-only
    STATUS       current
    DESCRIPTION  "The date and time stamp of the octets conform and
                  exceeded count value."
    ::= { pvxESrvcBWPrflCrntPMEntry 20 }


pvxESrvcBWPrflCrntPMOctetsCnfExcValidity OBJECT-TYPE
    SYNTAX       PMValidity
    MAX-ACCESS   read-only
    STATUS       current
    DESCRIPTION  "Indicates the validity of the provided octets conform
                  and exceeded count value."
    ::= { pvxESrvcBWPrflCrntPMEntry 21 }


pvxESrvcBWPrflCrntPMOctetsCnfExcInitialize OBJECT-TYPE
    SYNTAX       InitializeCmd
    MAX-ACCESS   read-write
    STATUS       current
    DESCRIPTION  "Used to initialize the value of the
                  pvxESrvcBWPrflCrntPMOctetsCnfExcValue object to 0."
    ::= { pvxESrvcBWPrflCrntPMEntry 22 }


pvxESrvcBWPrflCrntPMBDWUtlzValue OBJECT-TYPE
    SYNTAX       FixedX100
    MAX-ACCESS   read-write
    STATUS       current
    DESCRIPTION  "The bandwidth utilization of the monitored service."
    ::= { pvxESrvcBWPrflCrntPMEntry 23 }


pvxESrvcBWPrflCrntPMBDWUtlzTimeStamp OBJECT-TYPE
    SYNTAX       DateAndTime
    MAX-ACCESS   read-only
    STATUS       current
    DESCRIPTION  "The date and time stamp of the bandwidth utilization value."
    ::= { pvxESrvcBWPrflCrntPMEntry 24 }


pvxESrvcBWPrflCrntPMBDWUtlzValidity OBJECT-TYPE
    SYNTAX       PMValidity
    MAX-ACCESS   read-only
    STATUS       current
    DESCRIPTION  "Indicates the validity of the provided bandwidth utilization value."
    ::= { pvxESrvcBWPrflCrntPMEntry 25 }


pvxESrvcBWPrflCrntPMBDWUtlzInitialize OBJECT-TYPE
    SYNTAX       InitializeCmd
    MAX-ACCESS   read-write
    STATUS       current
    DESCRIPTION  "Used to initialize the value of the
                  pvxESrvcBWPrflCrntPMBDWUtlzValue object to 0."
    ::= { pvxESrvcBWPrflCrntPMEntry 26 }


-----------------------------------------------------------------------
-- Objects used to retrieve historical Performance Monitoring
-- statistics for perEVC and perCoS Objects
-----------------------------------------------------------------------

pvxESrvcBWPrflHistPMTable OBJECT-TYPE
    SYNTAX       SEQUENCE OF PvxESrvcBWPrflHistPMEntry
    MAX-ACCESS   not-accessible
    STATUS       current
    DESCRIPTION  "A table of historical performance monitoring statistics collected
                  for the PacketVX perEVC and perCoS objects."
    ::= { performance 43 }


pvxESrvcBWPrflHistPMEntry OBJECT-TYPE
    SYNTAX       PvxESrvcBWPrflHistPMEntry
    MAX-ACCESS   not-accessible
    STATUS       current
    DESCRIPTION  "The row entry object of the PacketVX ethernet services
    			  bandwidth profile historical performance monitoring table.
    			  Each row of this table contains a full set of PM statistics
    			  and related data for an historical measurement interval for a
    			  given perEVC or perCoS instance."
    INDEX        { pvxESrvcBWPrflHistPMSwitchIdx,
                   pvxESrvcBWPrflHistPMShelfIdx,
                   pvxESrvcBWPrflHistPMSlotIdx,
                   pvxESrvcBWPrflHistPMPortTypeIdx,
                   pvxESrvcBWPrflHistPMPortIdx,
    			   pvxESrvcBWPrflHistPMESrvcNameIdx,
    			   pvxESrvcBWPrflHistPMPlcyNameIdx,
    			   pvxESrvcBWPrflHistPMClsMapNameIdx,
    			   pvxESrvcBWPrflHistPMDirectionIdx,
    			   pvxESrvcBWPrflHistPMIntervalTypeIdx,
    			   pvxESrvcBWPrflHistPMIntervalIdx }
    ::= { pvxESrvcBWPrflHistPMTable 1 }


PvxESrvcBWPrflHistPMEntry ::= SEQUENCE { pvxESrvcBWPrflHistPMSwitchIdx               INTEGER,
					     		         pvxESrvcBWPrflHistPMShelfIdx                INTEGER,
                                         pvxESrvcBWPrflHistPMSlotIdx                 INTEGER,
                                         pvxESrvcBWPrflHistPMPortTypeIdx             PvxPortType,
                                         pvxESrvcBWPrflHistPMPortIdx                 INTEGER,
                                         pvxESrvcBWPrflHistPMESrvcNameIdx            DisplayString,
                                         pvxESrvcBWPrflHistPMPlcyNameIdx             DisplayString,
                                         pvxESrvcBWPrflHistPMClsMapNameIdx           DisplayString,
                                         pvxESrvcBWPrflHistPMDirectionIdx            INTEGER,
                                         pvxESrvcBWPrflHistPMIntervalTypeIdx         PMIntervalType,
                                         pvxESrvcBWPrflHistPMIntervalIdx             INTEGER,
                                         pvxESrvcBWPrflHistPMOctetsTotalValue        Unsigned64,
                                         pvxESrvcBWPrflHistPMOctetsTotalTimeStamp    DateAndTime,
                                         pvxESrvcBWPrflHistPMOctetsTotalValidity     PMValidity,
                                         pvxESrvcBWPrflHistPMOctetsTotalInitialize   InitializeCmd,
                                         pvxESrvcBWPrflHistPMOctetsVltValue          Unsigned64,
                                         pvxESrvcBWPrflHistPMOctetsVltTimeStamp      DateAndTime,
                                         pvxESrvcBWPrflHistPMOctetsVltValidity       PMValidity,
                                         pvxESrvcBWPrflHistPMOctetsVltInitialize     InitializeCmd,
                                         pvxESrvcBWPrflHistPMOctetsCnfExcValue       Unsigned64,
                                         pvxESrvcBWPrflHistPMOctetsCnfExcTimeStamp   DateAndTime,
                                         pvxESrvcBWPrflHistPMOctetsCnfExcValidity    PMValidity,
                                         pvxESrvcBWPrflHistPMOctetsCnfExcInitialize  InitializeCmd,
                                         pvxESrvcBWPrflHistPMBDWUtlzValue            FixedX100,
                                         pvxESrvcBWPrflHistPMBDWUtlzTimeStamp        DateAndTime,
                                         pvxESrvcBWPrflHistPMBDWUtlzValidity         PMValidity,
                                         pvxESrvcBWPrflHistPMBDWUtlzInitialize       InitializeCmd }
                                  
                                  
pvxESrvcBWPrflHistPMSwitchIdx OBJECT-TYPE
   	SYNTAX       INTEGER(1..11)
   	MAX-ACCESS   not-accessible
   	STATUS       current
   	DESCRIPTION  "The identifier of the ethernet switch instance on which the
                  monitored object is provisioned."
    ::= { pvxESrvcBWPrflHistPMEntry 1 }


pvxESrvcBWPrflHistPMShelfIdx OBJECT-TYPE
    SYNTAX       INTEGER (0|1|11|21|31)
    MAX-ACCESS   not-accessible
    STATUS       current
    DESCRIPTION  "The number of the shelf on which the monitored object is
                  provisioned."
    ::= { pvxESrvcBWPrflHistPMEntry 2 }


pvxESrvcBWPrflHistPMSlotIdx OBJECT-TYPE
    SYNTAX       INTEGER (0|1|3|5|7|9|11|13|15|17|19)
    MAX-ACCESS   not-accessible
    STATUS       current
    DESCRIPTION  "The number of the slot on which the monitored object is
                  provisioned."
    ::= { pvxESrvcBWPrflHistPMEntry 3 }


pvxESrvcBWPrflHistPMPortTypeIdx OBJECT-TYPE
    SYNTAX       PvxPortType 
    MAX-ACCESS   not-accessible
    STATUS       current
    DESCRIPTION  "The type of PacketVX port on which the monitored object
			      is provisioned."
    ::= { pvxESrvcBWPrflHistPMEntry 4 }


pvxESrvcBWPrflHistPMPortIdx OBJECT-TYPE
    SYNTAX       INTEGER (1..24)
    MAX-ACCESS   not-accessible
    STATUS       current
    DESCRIPTION  "The number of the port of the identified type on which the 
                  monitored object is provisioned."
    ::= { pvxESrvcBWPrflHistPMEntry 5 }


pvxESrvcBWPrflHistPMESrvcNameIdx OBJECT-TYPE
   	SYNTAX       DisplayString (SIZE(1..32))
   	MAX-ACCESS   not-accessible
   	STATUS       current
   	DESCRIPTION  "The name of the ethernet service."
    ::= { pvxESrvcBWPrflHistPMEntry 6 }


pvxESrvcBWPrflHistPMPlcyNameIdx OBJECT-TYPE
   	SYNTAX       DisplayString (SIZE(1..32))
   	MAX-ACCESS   not-accessible
   	STATUS       current
   	DESCRIPTION  "The name of the policy."
    ::= { pvxESrvcBWPrflHistPMEntry 7 }


pvxESrvcBWPrflHistPMClsMapNameIdx OBJECT-TYPE
   	SYNTAX       DisplayString (SIZE(1..32))
   	MAX-ACCESS   not-accessible
   	STATUS       current
   	DESCRIPTION  "The name of the class map."
    ::= { pvxESrvcBWPrflHistPMEntry 8 }


pvxESrvcBWPrflHistPMDirectionIdx OBJECT-TYPE
    SYNTAX       INTEGER { ingress (1),
                           egress  (2) }
    MAX-ACCESS   not-accessible
    STATUS       current
    DESCRIPTION  "The direction of traffic of the monitored object."
    ::= { pvxESrvcBWPrflHistPMEntry 9 }


pvxESrvcBWPrflHistPMIntervalTypeIdx OBJECT-TYPE
    SYNTAX       PMIntervalType
    MAX-ACCESS   not-accessible
    STATUS       current
    DESCRIPTION  "The type of PM bin according to interval length."
    ::= { pvxESrvcBWPrflHistPMEntry 10 }


pvxESrvcBWPrflHistPMIntervalIdx OBJECT-TYPE
    SYNTAX       INTEGER (1..96)
    MAX-ACCESS   not-accessible
    STATUS       current
    DESCRIPTION  "The specific PM bin number. The range is 1 to 96 for the
                  15-minute historical bins. For the 1-day historical bin, the
                  value is 1."
    ::= { pvxESrvcBWPrflHistPMEntry 11 }


pvxESrvcBWPrflHistPMOctetsTotalValue OBJECT-TYPE
    SYNTAX       Unsigned64
    MAX-ACCESS   read-only
    STATUS       current
    DESCRIPTION  "The total count of octets received or transmitted for the
                  monitored service."
    ::= { pvxESrvcBWPrflHistPMEntry 12 }


pvxESrvcBWPrflHistPMOctetsTotalTimeStamp OBJECT-TYPE
    SYNTAX       DateAndTime
    MAX-ACCESS   read-only
    STATUS       current
    DESCRIPTION  "The date and time stamp of the total octets count value."
    ::= { pvxESrvcBWPrflHistPMEntry 13 }


pvxESrvcBWPrflHistPMOctetsTotalValidity OBJECT-TYPE
    SYNTAX       PMValidity
    MAX-ACCESS   read-only
    STATUS       current
    DESCRIPTION  "Indicates the validity of the provided total octets count value."
    ::= { pvxESrvcBWPrflHistPMEntry 14 }


pvxESrvcBWPrflHistPMOctetsTotalInitialize OBJECT-TYPE
    SYNTAX       InitializeCmd
    MAX-ACCESS   read-write
    STATUS       current
    DESCRIPTION  "Used to initialize the value of the
                  pvxESrvcBWPrflHistPMOctetsTotalValue object to 0."
    ::= { pvxESrvcBWPrflHistPMEntry 15 }


pvxESrvcBWPrflHistPMOctetsVltValue OBJECT-TYPE
    SYNTAX       Unsigned64
    MAX-ACCESS   read-only
    STATUS       current
    DESCRIPTION  "The count of octets violate for the monitored service."
    ::= { pvxESrvcBWPrflHistPMEntry 16 }


pvxESrvcBWPrflHistPMOctetsVltTimeStamp OBJECT-TYPE
    SYNTAX       DateAndTime
    MAX-ACCESS   read-only
    STATUS       current
    DESCRIPTION  "The date and time stamp of the octets violate count value."
    ::= { pvxESrvcBWPrflHistPMEntry 17 }


pvxESrvcBWPrflHistPMOctetsVltValidity OBJECT-TYPE
    SYNTAX       PMValidity
    MAX-ACCESS   read-only
    STATUS       current
    DESCRIPTION  "Indicates the validity of the provided octets violate count value."
    ::= { pvxESrvcBWPrflHistPMEntry 18 }


pvxESrvcBWPrflHistPMOctetsVltInitialize OBJECT-TYPE
    SYNTAX       InitializeCmd
    MAX-ACCESS   read-write
    STATUS       current
    DESCRIPTION  "Used to initialize the value of the
                  pvxESrvcBWPrflHistPMOctetsVltValue object to 0."
    ::= { pvxESrvcBWPrflHistPMEntry 19 }


pvxESrvcBWPrflHistPMOctetsCnfExcValue OBJECT-TYPE
    SYNTAX       Unsigned64
    MAX-ACCESS   read-only
    STATUS       current
    DESCRIPTION  "The count of octets conform and exceeded for the
                  monitored service."
    ::= { pvxESrvcBWPrflHistPMEntry 20 }


pvxESrvcBWPrflHistPMOctetsCnfExcTimeStamp OBJECT-TYPE
    SYNTAX       DateAndTime
    MAX-ACCESS   read-only
    STATUS       current
    DESCRIPTION  "The date and time stamp of the octets conform and
                  exceeded count value."
    ::= { pvxESrvcBWPrflHistPMEntry 21 }


pvxESrvcBWPrflHistPMOctetsCnfExcValidity OBJECT-TYPE
    SYNTAX       PMValidity
    MAX-ACCESS   read-only
    STATUS       current
    DESCRIPTION  "Indicates the validity of the provided octets conform
                  and exceeded count value."
    ::= { pvxESrvcBWPrflHistPMEntry 22 }


pvxESrvcBWPrflHistPMOctetsCnfExcInitialize OBJECT-TYPE
    SYNTAX       InitializeCmd
    MAX-ACCESS   read-write
    STATUS       current
    DESCRIPTION  "Used to initialize the value of the
                  pvxESrvcBWPrflHistPMOctetsCnfExcValue object to 0."
    ::= { pvxESrvcBWPrflHistPMEntry 23 }


pvxESrvcBWPrflHistPMBDWUtlzValue OBJECT-TYPE
    SYNTAX       FixedX100
    MAX-ACCESS   read-write
    STATUS       current
    DESCRIPTION  "The bandwidth utilization of the monitored service."
    ::= { pvxESrvcBWPrflHistPMEntry 24 }


pvxESrvcBWPrflHistPMBDWUtlzTimeStamp OBJECT-TYPE
    SYNTAX       DateAndTime
    MAX-ACCESS   read-only
    STATUS       current
    DESCRIPTION  "The date and time stamp of the bandwidth utilization value."
    ::= { pvxESrvcBWPrflHistPMEntry 25 }


pvxESrvcBWPrflHistPMBDWUtlzValidity OBJECT-TYPE
    SYNTAX       PMValidity
    MAX-ACCESS   read-only
    STATUS       current
    DESCRIPTION  "Indicates the validity of the provided bandwidth utilization value."
    ::= { pvxESrvcBWPrflHistPMEntry 26 }


pvxESrvcBWPrflHistPMBDWUtlzInitialize OBJECT-TYPE
    SYNTAX       InitializeCmd
    MAX-ACCESS   read-write
    STATUS       current
    DESCRIPTION  "Used to initialize the value of the
                  pvxESrvcBWPrflHistPMBDWUtlzValue object to 0."
    ::= { pvxESrvcBWPrflHistPMEntry 27 }

-----------------------------------------------------------------------
-- Objects used to manage Performance Monitoring Threshold Levels
-- for perEVC and perCoS Objects
-----------------------------------------------------------------------

pvxESrvcBWPrflPMThresholdTable OBJECT-TYPE
    SYNTAX       SEQUENCE OF PvxESrvcBWPrflPMThresholdEntry
    MAX-ACCESS   not-accessible
    STATUS       current
    DESCRIPTION  "A table of threshold levels for monitored parameters which
                  support threshold crossing alerts on PacketVX perEVC and
                  perCoS objects."
    ::= { performance 44 }


pvxESrvcBWPrflPMThresholdEntry OBJECT-TYPE
    SYNTAX       PvxESrvcBWPrflPMThresholdEntry
    MAX-ACCESS   not-accessible
    STATUS       current
    DESCRIPTION  "The row entry object of the PVX Ethernet Service Bandwidth
                  Profile performance monitoring threshold table. Each row
                  of this table contains a set of PM thresholds for a given
                  interval level that applies to an individual perEVC or perCoS
                  instance."
    INDEX        { pvxESrvcBWPrflPMThresholdSwitchIdx,
                   pvxESrvcBWPrflPMThresholdShelfIdx,
                   pvxESrvcBWPrflPMThresholdSlotIdx,
                   pvxESrvcBWPrflPMThresholdPortTypeIdx,
                   pvxESrvcBWPrflPMThresholdPortIdx,
    			   pvxESrvcBWPrflPMThresholdESrvcNameIdx,
    			   pvxESrvcBWPrflPMThresholdPlcyNameIdx,
    			   pvxESrvcBWPrflPMThresholdClsMapNameIdx,
    			   pvxESrvcBWPrflPMThresholdDirectionIdx,
    			   pvxESrvcBWPrflPMThresholdLevelTypeIdx }
    ::= { pvxESrvcBWPrflPMThresholdTable 1 }


PvxESrvcBWPrflPMThresholdEntry ::= SEQUENCE { pvxESrvcBWPrflPMThresholdSwitchIdx               INTEGER,
					     		              pvxESrvcBWPrflPMThresholdShelfIdx                INTEGER,
                                              pvxESrvcBWPrflPMThresholdSlotIdx                 INTEGER,
                                              pvxESrvcBWPrflPMThresholdPortTypeIdx             PvxPortType,
                                              pvxESrvcBWPrflPMThresholdPortIdx                 INTEGER,
                                              pvxESrvcBWPrflPMThresholdESrvcNameIdx            DisplayString,
                                              pvxESrvcBWPrflPMThresholdPlcyNameIdx             DisplayString,
                                              pvxESrvcBWPrflPMThresholdClsMapNameIdx           DisplayString,
                                              pvxESrvcBWPrflPMThresholdDirectionIdx            INTEGER,
                                              pvxESrvcBWPrflPMThresholdLevelTypeIdx            PvxESrvcBWPrflPMThresholdLevelType,
                                              pvxESrvcBWPrflPMThresholdBDWUtlzValue            FixedX100 }
                                  
                                  
pvxESrvcBWPrflPMThresholdSwitchIdx OBJECT-TYPE
   	SYNTAX       INTEGER(1..11)
   	MAX-ACCESS   not-accessible
   	STATUS       current
   	DESCRIPTION  "The identifier of the ethernet switch instance on which the
                  monitored object is provisioned."
    ::= { pvxESrvcBWPrflPMThresholdEntry 1 }


pvxESrvcBWPrflPMThresholdShelfIdx OBJECT-TYPE
    SYNTAX       INTEGER (0|1|11|21|31)
    MAX-ACCESS   not-accessible
    STATUS       current
    DESCRIPTION  "The number of the shelf on which the monitored object is
                  provisioned."
    ::= { pvxESrvcBWPrflPMThresholdEntry 2 }


pvxESrvcBWPrflPMThresholdSlotIdx OBJECT-TYPE
    SYNTAX       INTEGER (0|1|3|5|7|9|11|13|15|17|19)
    MAX-ACCESS   not-accessible
    STATUS       current
    DESCRIPTION  "The number of the slot on which the monitored object is
                  provisioned."
    ::= { pvxESrvcBWPrflPMThresholdEntry 3 }


pvxESrvcBWPrflPMThresholdPortTypeIdx OBJECT-TYPE
    SYNTAX       PvxPortType 
    MAX-ACCESS   not-accessible
    STATUS       current
    DESCRIPTION  "The type of PacketVX port on which the monitored object
			      is provisioned."
    ::= { pvxESrvcBWPrflPMThresholdEntry 4 }


pvxESrvcBWPrflPMThresholdPortIdx OBJECT-TYPE
    SYNTAX       INTEGER (1..24)
    MAX-ACCESS   not-accessible
    STATUS       current
    DESCRIPTION  "The number of the port of the identified type on which the 
                  monitored object is provisioned."
    ::= { pvxESrvcBWPrflPMThresholdEntry 5 }


pvxESrvcBWPrflPMThresholdESrvcNameIdx OBJECT-TYPE
   	SYNTAX       DisplayString (SIZE(1..32))
   	MAX-ACCESS   not-accessible
   	STATUS       current
   	DESCRIPTION  "The name of the ethernet service."
    ::= { pvxESrvcBWPrflPMThresholdEntry 6 }


pvxESrvcBWPrflPMThresholdPlcyNameIdx OBJECT-TYPE
   	SYNTAX       DisplayString (SIZE(1..32))
   	MAX-ACCESS   not-accessible
   	STATUS       current
   	DESCRIPTION  "The name of the policy."
    ::= { pvxESrvcBWPrflPMThresholdEntry 7 }


pvxESrvcBWPrflPMThresholdClsMapNameIdx OBJECT-TYPE
   	SYNTAX       DisplayString (SIZE(1..32))
   	MAX-ACCESS   not-accessible
   	STATUS       current
   	DESCRIPTION  "The name of the class map."
    ::= { pvxESrvcBWPrflPMThresholdEntry 8 }


pvxESrvcBWPrflPMThresholdDirectionIdx OBJECT-TYPE
    SYNTAX       INTEGER { ingress (1),
                           egress  (2) }
    MAX-ACCESS   not-accessible
    STATUS       current
    DESCRIPTION  "The direction of traffic of the monitored object."
    ::= { pvxESrvcBWPrflPMThresholdEntry 9 }


pvxESrvcBWPrflPMThresholdLevelTypeIdx OBJECT-TYPE
    SYNTAX       PvxESrvcBWPrflPMThresholdLevelType
    MAX-ACCESS   not-accessible
    STATUS       current
    DESCRIPTION  "Identifies the specific PM threshold according to
                  interval length and level criticality."
    ::= { pvxESrvcBWPrflPMThresholdEntry 10 }


pvxESrvcBWPrflPMThresholdBDWUtlzValue OBJECT-TYPE
    SYNTAX       FixedX100
    MAX-ACCESS   read-write
    STATUS       current
    DESCRIPTION  "The threshold for the bandwidth utilization."
    ::= { pvxESrvcBWPrflPMThresholdEntry 11 }



-----------------------------------------------------------------------
-- Objects used to retrieve current Performance Monitoring
-- statistics for PacketVX ERPS Port
-----------------------------------------------------------------------


pvxERPSPortCrntPMTable OBJECT-TYPE
    SYNTAX       SEQUENCE OF PvxERPSPortCrntPMEntry
    MAX-ACCESS   not-accessible
    STATUS       current
    DESCRIPTION  "A table of current performance monitoring statistics collected
                  for PacketVX ERPS Port"
    ::= { performance 45 }


pvxERPSPortCrntPMEntry OBJECT-TYPE
    SYNTAX       PvxERPSPortCrntPMEntry
    MAX-ACCESS   not-accessible
    STATUS       current
    DESCRIPTION  "The row entry object of the PacketVX ERPS Port current
                  performance monitoring table. Each row of this table contains
                  a full set of PM statistics and related data for a current
                  measurement interval for a given PVX ERPS Port."
    INDEX        { pvxERPSPortCrntPMSwitchIdx,
				   pvxERPSPortCrntPMShelfIdx,
				   pvxERPSPortCrntPMSlotIdx,
               	   pvxERPSPortCrntPMTypeIdx,
    			   pvxERPSPortCrntPMPortIdx,
    			   pvxERPSPortCrntPMIntervalTypeIdx }
    ::= { pvxERPSPortCrntPMTable 1 }


PvxERPSPortCrntPMEntry ::= SEQUENCE { pvxERPSPortCrntPMSwitchIdx              INTEGER,
				                      pvxERPSPortCrntPMShelfIdx       	      INTEGER,
				                      pvxERPSPortCrntPMSlotIdx        	      INTEGER,
				                      pvxERPSPortCrntPMTypeIdx		          PvxPortType,
                                      pvxERPSPortCrntPMPortIdx                INTEGER,
                                      pvxERPSPortCrntPMIntervalTypeIdx        PMIntervalType,
                                      pvxERPSPortCrntPMPduTxValue             Unsigned64,
                                      pvxERPSPortCrntPMPduTxTimeStamp         DateAndTime,
                                      pvxERPSPortCrntPMPduTxValidity          PMValidity,
                                      pvxERPSPortCrntPMPduTxInitialize        InitializeCmd,
                                      pvxERPSPortCrntPMPduRxValue             Unsigned64,
                                      pvxERPSPortCrntPMPduRxTimeStamp         DateAndTime,
                                      pvxERPSPortCrntPMPduRxValidity          PMValidity,
                                      pvxERPSPortCrntPMPduRxInitialize        InitializeCmd,
                                      pvxERPSPortCrntPMPduDiscardValue        Unsigned64,
                                      pvxERPSPortCrntPMPduDiscardTimeStamp    DateAndTime,
                                      pvxERPSPortCrntPMPduDiscardValidity     PMValidity,
                                      pvxERPSPortCrntPMPduDiscardInitialize   InitializeCmd,
                                      pvxERPSPortCrntPMBlockedValue           Unsigned64,
                                      pvxERPSPortCrntPMBlockedTimeStamp       DateAndTime,
                                      pvxERPSPortCrntPMBlockedValidity        PMValidity,
                                      pvxERPSPortCrntPMBlockedInitialize      InitializeCmd,
                                      pvxERPSPortCrntPMUnblockedValue         Unsigned64,
                                      pvxERPSPortCrntPMUnblockedTimeStamp     DateAndTime,
                                      pvxERPSPortCrntPMUnblockedValidity      PMValidity,
                                      pvxERPSPortCrntPMUnblockedInitialize    InitializeCmd,
                                      pvxERPSPortCrntPMFailuresValue          Unsigned64,
                                      pvxERPSPortCrntPMFailuresTimeStamp      DateAndTime,
                                      pvxERPSPortCrntPMFailuresValidity       PMValidity,
                                      pvxERPSPortCrntPMFailuresInitialize     InitializeCmd,
                                      pvxERPSPortCrntPMRecoveriesValue        Unsigned64,
                                      pvxERPSPortCrntPMRecoveriesTimeStamp    DateAndTime,
                                      pvxERPSPortCrntPMRecoveriesValidity     PMValidity,
                                      pvxERPSPortCrntPMRecoveriesInitialize   InitializeCmd,
                                      pvxERPSPortCrntPMNrPduTxValue           Unsigned64,
                                      pvxERPSPortCrntPMNrPduTxTimeStamp       DateAndTime,
                                      pvxERPSPortCrntPMNrPduTxValidity        PMValidity,
                                      pvxERPSPortCrntPMNrPduTxInitialize      InitializeCmd,
                                      pvxERPSPortCrntPMNrPduRxValue           Unsigned64,
                                      pvxERPSPortCrntPMNrPduRxTimeStamp       DateAndTime,
                                      pvxERPSPortCrntPMNrPduRxValidity        PMValidity,
                                      pvxERPSPortCrntPMNrPduRxInitialize      InitializeCmd,
                                      pvxERPSPortCrntPMNrrbPduTxValue         Unsigned64,
                                      pvxERPSPortCrntPMNrrbPduTxTimeStamp     DateAndTime,
                                      pvxERPSPortCrntPMNrrbPduTxValidity      PMValidity,
                                      pvxERPSPortCrntPMNrrbPduTxInitialize    InitializeCmd,
                                      pvxERPSPortCrntPMNrrbPduRxValue         Unsigned64,
                                      pvxERPSPortCrntPMNrrbPduRxTimeStamp     DateAndTime,
                                      pvxERPSPortCrntPMNrrbPduRxValidity      PMValidity,
                                      pvxERPSPortCrntPMNrrbPduRxInitialize    InitializeCmd,
                                      pvxERPSPortCrntPMSfPduTxValue           Unsigned64,
                                      pvxERPSPortCrntPMSfPduTxTimeStamp       DateAndTime,
                                      pvxERPSPortCrntPMSfPduTxValidity        PMValidity,
                                      pvxERPSPortCrntPMSfPduTxInitialize      InitializeCmd,
                                      pvxERPSPortCrntPMSfPduRxValue           Unsigned64,
                                      pvxERPSPortCrntPMSfPduRxTimeStamp       DateAndTime,
                                      pvxERPSPortCrntPMSfPduRxValidity        PMValidity,
                                      pvxERPSPortCrntPMSfPduRxInitialize      InitializeCmd,
                                      pvxERPSPortCrntPMFsPduTxValue           Unsigned64,
                                      pvxERPSPortCrntPMFsPduTxTimeStamp       DateAndTime,
                                      pvxERPSPortCrntPMFsPduTxValidity        PMValidity,
                                      pvxERPSPortCrntPMFsPduTxInitialize      InitializeCmd,
                                      pvxERPSPortCrntPMFsPduRxValue           Unsigned64,
                                      pvxERPSPortCrntPMFsPduRxTimeStamp       DateAndTime,
                                      pvxERPSPortCrntPMFsPduRxValidity        PMValidity,
                                      pvxERPSPortCrntPMFsPduRxInitialize      InitializeCmd,
                                      pvxERPSPortCrntPMMsPduTxValue           Unsigned64,
                                      pvxERPSPortCrntPMMsPduTxTimeStamp       DateAndTime,
                                      pvxERPSPortCrntPMMsPduTxValidity        PMValidity,
                                      pvxERPSPortCrntPMMsPduTxInitialize      InitializeCmd,
                                      pvxERPSPortCrntPMMsPduRxValue           Unsigned64,
                                      pvxERPSPortCrntPMMsPduRxTimeStamp       DateAndTime,
                                      pvxERPSPortCrntPMMsPduRxValidity        PMValidity,
                                      pvxERPSPortCrntPMMsPduRxInitialize      InitializeCmd,
                                      pvxERPSPortCrntPMEventPduTxValue        Unsigned64,
                                      pvxERPSPortCrntPMEventPduTxTimeStamp    DateAndTime,
                                      pvxERPSPortCrntPMEventPduTxValidity     PMValidity,
                                      pvxERPSPortCrntPMEventPduTxInitialize   InitializeCmd,
                                      pvxERPSPortCrntPMEventPduRxValue        Unsigned64,
                                      pvxERPSPortCrntPMEventPduRxTimeStamp    DateAndTime,
                                      pvxERPSPortCrntPMEventPduRxValidity     PMValidity,
                                      pvxERPSPortCrntPMEventPduRxInitialize   InitializeCmd,
                                      pvxERPSPortCrntPMVersionDiscardValue        Unsigned64,
                                      pvxERPSPortCrntPMVersionDiscardTimeStamp    DateAndTime,
                                      pvxERPSPortCrntPMVersionDiscardValidity     PMValidity,
                                      pvxERPSPortCrntPMVersionDiscardInitialize   InitializeCmd }
                                  
                                  
pvxERPSPortCrntPMSwitchIdx OBJECT-TYPE
   	SYNTAX       INTEGER(1..11)
   	MAX-ACCESS   not-accessible
   	STATUS       current
    DESCRIPTION  "The identifier of the ethernet switch instance on which the
                  ERPS Port is provisioned."
    ::= {pvxERPSPortCrntPMEntry 1 }


pvxERPSPortCrntPMShelfIdx OBJECT-TYPE
    SYNTAX       INTEGER (0|1|11|21|31)
    MAX-ACCESS   not-accessible
    STATUS       current
    DESCRIPTION  "The number of the shelf on which the ERPS Port targeted
                  for PMs is provisioned. For LAG entities, the shelf number is 0."
    ::= {pvxERPSPortCrntPMEntry 2 }


pvxERPSPortCrntPMSlotIdx OBJECT-TYPE
    SYNTAX       INTEGER (0|1|3|5|7|9|11|13|15|17|19)
    MAX-ACCESS   not-accessible
    STATUS       current
    DESCRIPTION  "The number of the slot within which the ERPS Port targeted
                  for PMs is provisioned. For LAG entities, the slot number is 0."
    ::= {pvxERPSPortCrntPMEntry 3 }


pvxERPSPortCrntPMTypeIdx OBJECT-TYPE
    SYNTAX       PvxPortType
    MAX-ACCESS   not-accessible
    STATUS       current
    DESCRIPTION  "The type of PacketVX port on which the ERPS Port
                  facility is provisioned."
    ::= {pvxERPSPortCrntPMEntry 4 }


pvxERPSPortCrntPMPortIdx OBJECT-TYPE
    SYNTAX       INTEGER (0..64)
    MAX-ACCESS   not-accessible
    STATUS       current
    DESCRIPTION  "The port number for the ERPS Port"
    ::= {pvxERPSPortCrntPMEntry 5 }


pvxERPSPortCrntPMIntervalTypeIdx OBJECT-TYPE
    SYNTAX       PMIntervalType
    MAX-ACCESS   not-accessible
    STATUS       current
    DESCRIPTION  "The type of PM bin according to interval length."
    ::= { pvxERPSPortCrntPMEntry 6 }


pvxERPSPortCrntPMPduTxValue OBJECT-TYPE
    SYNTAX       Unsigned64
    MAX-ACCESS   read-only
    STATUS       current
    DESCRIPTION  "The Number of PDUs transmitted on this port"
    ::= { pvxERPSPortCrntPMEntry 7 }


pvxERPSPortCrntPMPduTxTimeStamp OBJECT-TYPE
    SYNTAX       DateAndTime
    MAX-ACCESS   read-only
    STATUS       current
    DESCRIPTION  "The date and time stamp of the value."
    ::= { pvxERPSPortCrntPMEntry 8 }


pvxERPSPortCrntPMPduTxValidity OBJECT-TYPE
    SYNTAX       PMValidity
    MAX-ACCESS   read-only
    STATUS       current
    DESCRIPTION  "Indicates the validity of the value."
    ::= { pvxERPSPortCrntPMEntry 9 }


pvxERPSPortCrntPMPduTxInitialize OBJECT-TYPE
    SYNTAX       InitializeCmd
    MAX-ACCESS   read-write
    STATUS       current
    DESCRIPTION  "Used to initialize the value to 0."
    ::= { pvxERPSPortCrntPMEntry 10 }
    
pvxERPSPortCrntPMPduRxValue OBJECT-TYPE
    SYNTAX       Unsigned64
    MAX-ACCESS   read-only
    STATUS       current
    DESCRIPTION  "The number of PDUs received on this port"
    ::= { pvxERPSPortCrntPMEntry 11 }


pvxERPSPortCrntPMPduRxTimeStamp OBJECT-TYPE
    SYNTAX       DateAndTime
    MAX-ACCESS   read-only
    STATUS       current
    DESCRIPTION  "The date and time stamp of the value."
    ::= { pvxERPSPortCrntPMEntry 12 }


pvxERPSPortCrntPMPduRxValidity OBJECT-TYPE
    SYNTAX       PMValidity
    MAX-ACCESS   read-only
    STATUS       current
    DESCRIPTION  "Indicates the validity of the value."
    ::= { pvxERPSPortCrntPMEntry 13 }


pvxERPSPortCrntPMPduRxInitialize OBJECT-TYPE
    SYNTAX       InitializeCmd
    MAX-ACCESS   read-write
    STATUS       current
    DESCRIPTION  "Used to initialize the value to 0."
    ::= { pvxERPSPortCrntPMEntry 14 }
    

pvxERPSPortCrntPMPduDiscardValue OBJECT-TYPE
    SYNTAX       Unsigned64
    MAX-ACCESS   read-only
    STATUS       current
    DESCRIPTION  "The number of PDUs discarded on this port"
    ::= { pvxERPSPortCrntPMEntry 15 }


pvxERPSPortCrntPMPduDiscardTimeStamp OBJECT-TYPE
    SYNTAX       DateAndTime
    MAX-ACCESS   read-only
    STATUS       current
    DESCRIPTION  "The date and time stamp of the value."
    ::= { pvxERPSPortCrntPMEntry 16 }


pvxERPSPortCrntPMPduDiscardValidity OBJECT-TYPE
    SYNTAX       PMValidity
    MAX-ACCESS   read-only
    STATUS       current
    DESCRIPTION  "Indicates the validity of the value."
    ::= { pvxERPSPortCrntPMEntry 17 }


pvxERPSPortCrntPMPduDiscardInitialize OBJECT-TYPE
    SYNTAX       InitializeCmd
    MAX-ACCESS   read-write
    STATUS       current
    DESCRIPTION  "Used to initialize the value to 0."
    ::= { pvxERPSPortCrntPMEntry 18 }
    
pvxERPSPortCrntPMBlockedValue OBJECT-TYPE
    SYNTAX       Unsigned64
    MAX-ACCESS   read-only
    STATUS       current
    DESCRIPTION  "The number of times this port has transitioned to blocked state"
    ::= { pvxERPSPortCrntPMEntry 19 }


pvxERPSPortCrntPMBlockedTimeStamp OBJECT-TYPE
    SYNTAX       DateAndTime
    MAX-ACCESS   read-only
    STATUS       current
    DESCRIPTION  "The date and time stamp of the value."
    ::= { pvxERPSPortCrntPMEntry 20 }


pvxERPSPortCrntPMBlockedValidity OBJECT-TYPE
    SYNTAX       PMValidity
    MAX-ACCESS   read-only
    STATUS       current
    DESCRIPTION  "Indicates the validity of the value."
    ::= { pvxERPSPortCrntPMEntry 21 }


pvxERPSPortCrntPMBlockedInitialize OBJECT-TYPE
    SYNTAX       InitializeCmd
    MAX-ACCESS   read-write
    STATUS       current
    DESCRIPTION  "Used to initialize the value to 0."
    ::= { pvxERPSPortCrntPMEntry 22 }
    
pvxERPSPortCrntPMUnblockedValue OBJECT-TYPE
    SYNTAX       Unsigned64
    MAX-ACCESS   read-only
    STATUS       current
    DESCRIPTION  "The number of times this port has transitioned to unblocked state"
    ::= { pvxERPSPortCrntPMEntry 23 }


pvxERPSPortCrntPMUnblockedTimeStamp OBJECT-TYPE
    SYNTAX       DateAndTime
    MAX-ACCESS   read-only
    STATUS       current
    DESCRIPTION  "The date and time stamp of the value."
    ::= { pvxERPSPortCrntPMEntry 24 }


pvxERPSPortCrntPMUnblockedValidity OBJECT-TYPE
    SYNTAX       PMValidity
    MAX-ACCESS   read-only
    STATUS       current
    DESCRIPTION  "Indicates the validity of the value."
    ::= { pvxERPSPortCrntPMEntry 25 }


pvxERPSPortCrntPMUnblockedInitialize OBJECT-TYPE
    SYNTAX       InitializeCmd
    MAX-ACCESS   read-write
    STATUS       current
    DESCRIPTION  "Used to initialize the value to 0."
    ::= { pvxERPSPortCrntPMEntry 26 }
    
pvxERPSPortCrntPMFailuresValue OBJECT-TYPE
    SYNTAX       Unsigned64
    MAX-ACCESS   read-only
    STATUS       current
    DESCRIPTION  "The number of times this port has transitioned to failed state"
    ::= { pvxERPSPortCrntPMEntry 27 }


pvxERPSPortCrntPMFailuresTimeStamp OBJECT-TYPE
    SYNTAX       DateAndTime
    MAX-ACCESS   read-only
    STATUS       current
    DESCRIPTION  "The date and time stamp of the value."
    ::= { pvxERPSPortCrntPMEntry 28 }


pvxERPSPortCrntPMFailuresValidity OBJECT-TYPE
    SYNTAX       PMValidity
    MAX-ACCESS   read-only
    STATUS       current
    DESCRIPTION  "Indicates the validity of the value."
    ::= { pvxERPSPortCrntPMEntry 29 }


pvxERPSPortCrntPMFailuresInitialize OBJECT-TYPE
    SYNTAX       InitializeCmd
    MAX-ACCESS   read-write
    STATUS       current
    DESCRIPTION  "Used to initialize the value to 0."
    ::= { pvxERPSPortCrntPMEntry 30 }
    
pvxERPSPortCrntPMRecoveriesValue OBJECT-TYPE
    SYNTAX       Unsigned64
    MAX-ACCESS   read-only
    STATUS       current
    DESCRIPTION  "The number of times this port has recovered from failed state"
    ::= { pvxERPSPortCrntPMEntry 31 }


pvxERPSPortCrntPMRecoveriesTimeStamp OBJECT-TYPE
    SYNTAX       DateAndTime
    MAX-ACCESS   read-only
    STATUS       current
    DESCRIPTION  "The date and time stamp of the value."
    ::= { pvxERPSPortCrntPMEntry 32 }


pvxERPSPortCrntPMRecoveriesValidity OBJECT-TYPE
    SYNTAX       PMValidity
    MAX-ACCESS   read-only
    STATUS       current
    DESCRIPTION  "Indicates the validity of the value."
    ::= { pvxERPSPortCrntPMEntry 33 }


pvxERPSPortCrntPMRecoveriesInitialize OBJECT-TYPE
    SYNTAX       InitializeCmd
    MAX-ACCESS   read-write
    STATUS       current
    DESCRIPTION  "Used to initialize the value to 0."
    ::= { pvxERPSPortCrntPMEntry 34 }

pvxERPSPortCrntPMNrPduTxValue OBJECT-TYPE
    SYNTAX       Unsigned64
    MAX-ACCESS   read-only
    STATUS       current
    DESCRIPTION  "The Number of NR PDUs transmitted on this port"
    ::= { pvxERPSPortCrntPMEntry 35 }


pvxERPSPortCrntPMNrPduTxTimeStamp OBJECT-TYPE
    SYNTAX       DateAndTime
    MAX-ACCESS   read-only
    STATUS       current
    DESCRIPTION  "The date and time stamp of the value."
    ::= { pvxERPSPortCrntPMEntry 36 }


pvxERPSPortCrntPMNrPduTxValidity OBJECT-TYPE
    SYNTAX       PMValidity
    MAX-ACCESS   read-only
    STATUS       current
    DESCRIPTION  "Indicates the validity of the value."
    ::= { pvxERPSPortCrntPMEntry 37 }


pvxERPSPortCrntPMNrPduTxInitialize OBJECT-TYPE
    SYNTAX       InitializeCmd
    MAX-ACCESS   read-write
    STATUS       current
    DESCRIPTION  "Used to initialize the value to 0."
    ::= { pvxERPSPortCrntPMEntry 38 }
    
pvxERPSPortCrntPMNrPduRxValue OBJECT-TYPE
    SYNTAX       Unsigned64
    MAX-ACCESS   read-only
    STATUS       current
    DESCRIPTION  "The number of NR PDUs received on this port"
    ::= { pvxERPSPortCrntPMEntry 39 }


pvxERPSPortCrntPMNrPduRxTimeStamp OBJECT-TYPE
    SYNTAX       DateAndTime
    MAX-ACCESS   read-only
    STATUS       current
    DESCRIPTION  "The date and time stamp of the value."
    ::= { pvxERPSPortCrntPMEntry 40 }


pvxERPSPortCrntPMNrPduRxValidity OBJECT-TYPE
    SYNTAX       PMValidity
    MAX-ACCESS   read-only
    STATUS       current
    DESCRIPTION  "Indicates the validity of the value."
    ::= { pvxERPSPortCrntPMEntry 41 }


pvxERPSPortCrntPMNrPduRxInitialize OBJECT-TYPE
    SYNTAX       InitializeCmd
    MAX-ACCESS   read-write
    STATUS       current
    DESCRIPTION  "Used to initialize the value to 0."
    ::= { pvxERPSPortCrntPMEntry 42 }
    

pvxERPSPortCrntPMNrrbPduTxValue OBJECT-TYPE
    SYNTAX       Unsigned64
    MAX-ACCESS   read-only
    STATUS       current
    DESCRIPTION  "The Number of NRRB PDUs transmitted on this port"
    ::= { pvxERPSPortCrntPMEntry 43 }


pvxERPSPortCrntPMNrrbPduTxTimeStamp OBJECT-TYPE
    SYNTAX       DateAndTime
    MAX-ACCESS   read-only
    STATUS       current
    DESCRIPTION  "The date and time stamp of the value."
    ::= { pvxERPSPortCrntPMEntry 44 }


pvxERPSPortCrntPMNrrbPduTxValidity OBJECT-TYPE
    SYNTAX       PMValidity
    MAX-ACCESS   read-only
    STATUS       current
    DESCRIPTION  "Indicates the validity of the value."
    ::= { pvxERPSPortCrntPMEntry 45 }


pvxERPSPortCrntPMNrrbPduTxInitialize OBJECT-TYPE
    SYNTAX       InitializeCmd
    MAX-ACCESS   read-write
    STATUS       current
    DESCRIPTION  "Used to initialize the value to 0."
    ::= { pvxERPSPortCrntPMEntry 46 }
    
pvxERPSPortCrntPMNrrbPduRxValue OBJECT-TYPE
    SYNTAX       Unsigned64
    MAX-ACCESS   read-only
    STATUS       current
    DESCRIPTION  "The number of NRRB PDUs received on this port"
    ::= { pvxERPSPortCrntPMEntry 47 }


pvxERPSPortCrntPMNrrbPduRxTimeStamp OBJECT-TYPE
    SYNTAX       DateAndTime
    MAX-ACCESS   read-only
    STATUS       current
    DESCRIPTION  "The date and time stamp of the value."
    ::= { pvxERPSPortCrntPMEntry 48 }


pvxERPSPortCrntPMNrrbPduRxValidity OBJECT-TYPE
    SYNTAX       PMValidity
    MAX-ACCESS   read-only
    STATUS       current
    DESCRIPTION  "Indicates the validity of the value."
    ::= { pvxERPSPortCrntPMEntry 49 }


pvxERPSPortCrntPMNrrbPduRxInitialize OBJECT-TYPE
    SYNTAX       InitializeCmd
    MAX-ACCESS   read-write
    STATUS       current
    DESCRIPTION  "Used to initialize the value to 0."
    ::= { pvxERPSPortCrntPMEntry 50 }
    

pvxERPSPortCrntPMSfPduTxValue OBJECT-TYPE
    SYNTAX       Unsigned64
    MAX-ACCESS   read-only
    STATUS       current
    DESCRIPTION  "The Number of SF PDUs transmitted on this port"
    ::= { pvxERPSPortCrntPMEntry 51 }


pvxERPSPortCrntPMSfPduTxTimeStamp OBJECT-TYPE
    SYNTAX       DateAndTime
    MAX-ACCESS   read-only
    STATUS       current
    DESCRIPTION  "The date and time stamp of the value."
    ::= { pvxERPSPortCrntPMEntry 52 }


pvxERPSPortCrntPMSfPduTxValidity OBJECT-TYPE
    SYNTAX       PMValidity
    MAX-ACCESS   read-only
    STATUS       current
    DESCRIPTION  "Indicates the validity of the value."
    ::= { pvxERPSPortCrntPMEntry 53 }


pvxERPSPortCrntPMSfPduTxInitialize OBJECT-TYPE
    SYNTAX       InitializeCmd
    MAX-ACCESS   read-write
    STATUS       current
    DESCRIPTION  "Used to initialize the value to 0."
    ::= { pvxERPSPortCrntPMEntry 54 }
    
pvxERPSPortCrntPMSfPduRxValue OBJECT-TYPE
    SYNTAX       Unsigned64
    MAX-ACCESS   read-only
    STATUS       current
    DESCRIPTION  "The number of SF PDUs received on this port"
    ::= { pvxERPSPortCrntPMEntry 55 }


pvxERPSPortCrntPMSfPduRxTimeStamp OBJECT-TYPE
    SYNTAX       DateAndTime
    MAX-ACCESS   read-only
    STATUS       current
    DESCRIPTION  "The date and time stamp of the value."
    ::= { pvxERPSPortCrntPMEntry 56 }


pvxERPSPortCrntPMSfPduRxValidity OBJECT-TYPE
    SYNTAX       PMValidity
    MAX-ACCESS   read-only
    STATUS       current
    DESCRIPTION  "Indicates the validity of the value."
    ::= { pvxERPSPortCrntPMEntry 57 }


pvxERPSPortCrntPMSfPduRxInitialize OBJECT-TYPE
    SYNTAX       InitializeCmd
    MAX-ACCESS   read-write
    STATUS       current
    DESCRIPTION  "Used to initialize the value to 0."
    ::= { pvxERPSPortCrntPMEntry 58 }
    
pvxERPSPortCrntPMFsPduTxValue OBJECT-TYPE
    SYNTAX       Unsigned64
    MAX-ACCESS   read-only
    STATUS       current
    DESCRIPTION  "The Number of FS PDUs transmitted on this port"
    ::= { pvxERPSPortCrntPMEntry 59 }


pvxERPSPortCrntPMFsPduTxTimeStamp OBJECT-TYPE
    SYNTAX       DateAndTime
    MAX-ACCESS   read-only
    STATUS       current
    DESCRIPTION  "The date and time stamp of the value."
    ::= { pvxERPSPortCrntPMEntry 60 }


pvxERPSPortCrntPMFsPduTxValidity OBJECT-TYPE
    SYNTAX       PMValidity
    MAX-ACCESS   read-only
    STATUS       current
    DESCRIPTION  "Indicates the validity of the value."
    ::= { pvxERPSPortCrntPMEntry 61 }


pvxERPSPortCrntPMFsPduTxInitialize OBJECT-TYPE
    SYNTAX       InitializeCmd
    MAX-ACCESS   read-write
    STATUS       current
    DESCRIPTION  "Used to initialize the value to 0."
    ::= { pvxERPSPortCrntPMEntry 62 }
    
pvxERPSPortCrntPMFsPduRxValue OBJECT-TYPE
    SYNTAX       Unsigned64
    MAX-ACCESS   read-only
    STATUS       current
    DESCRIPTION  "The number of FS PDUs received on this port"
    ::= { pvxERPSPortCrntPMEntry 63 }


pvxERPSPortCrntPMFsPduRxTimeStamp OBJECT-TYPE
    SYNTAX       DateAndTime
    MAX-ACCESS   read-only
    STATUS       current
    DESCRIPTION  "The date and time stamp of the value."
    ::= { pvxERPSPortCrntPMEntry 64 }


pvxERPSPortCrntPMFsPduRxValidity OBJECT-TYPE
    SYNTAX       PMValidity
    MAX-ACCESS   read-only
    STATUS       current
    DESCRIPTION  "Indicates the validity of the value."
    ::= { pvxERPSPortCrntPMEntry 65 }


pvxERPSPortCrntPMFsPduRxInitialize OBJECT-TYPE
    SYNTAX       InitializeCmd
    MAX-ACCESS   read-write
    STATUS       current
    DESCRIPTION  "Used to initialize the value to 0."
    ::= { pvxERPSPortCrntPMEntry 66 }
    
pvxERPSPortCrntPMMsPduTxValue OBJECT-TYPE
    SYNTAX       Unsigned64
    MAX-ACCESS   read-only
    STATUS       current
    DESCRIPTION  "The Number of MS PDUs transmitted on this port"
    ::= { pvxERPSPortCrntPMEntry 67 }


pvxERPSPortCrntPMMsPduTxTimeStamp OBJECT-TYPE
    SYNTAX       DateAndTime
    MAX-ACCESS   read-only
    STATUS       current
    DESCRIPTION  "The date and time stamp of the value."
    ::= { pvxERPSPortCrntPMEntry 68 }


pvxERPSPortCrntPMMsPduTxValidity OBJECT-TYPE
    SYNTAX       PMValidity
    MAX-ACCESS   read-only
    STATUS       current
    DESCRIPTION  "Indicates the validity of the value."
    ::= { pvxERPSPortCrntPMEntry 69 }


pvxERPSPortCrntPMMsPduTxInitialize OBJECT-TYPE
    SYNTAX       InitializeCmd
    MAX-ACCESS   read-write
    STATUS       current
    DESCRIPTION  "Used to initialize the value to 0."
    ::= { pvxERPSPortCrntPMEntry 70 }
    
pvxERPSPortCrntPMMsPduRxValue OBJECT-TYPE
    SYNTAX       Unsigned64
    MAX-ACCESS   read-only
    STATUS       current
    DESCRIPTION  "The number of MS PDUs received on this port"
    ::= { pvxERPSPortCrntPMEntry 71 }


pvxERPSPortCrntPMMsPduRxTimeStamp OBJECT-TYPE
    SYNTAX       DateAndTime
    MAX-ACCESS   read-only
    STATUS       current
    DESCRIPTION  "The date and time stamp of the value."
    ::= { pvxERPSPortCrntPMEntry 72 }


pvxERPSPortCrntPMMsPduRxValidity OBJECT-TYPE
    SYNTAX       PMValidity
    MAX-ACCESS   read-only
    STATUS       current
    DESCRIPTION  "Indicates the validity of the value."
    ::= { pvxERPSPortCrntPMEntry 73 }


pvxERPSPortCrntPMMsPduRxInitialize OBJECT-TYPE
    SYNTAX       InitializeCmd
    MAX-ACCESS   read-write
    STATUS       current
    DESCRIPTION  "Used to initialize the value to 0."
    ::= { pvxERPSPortCrntPMEntry 74 }
    
pvxERPSPortCrntPMEventPduTxValue OBJECT-TYPE
    SYNTAX       Unsigned64
    MAX-ACCESS   read-only
    STATUS       current
    DESCRIPTION  "The Number of Event PDUs transmitted on this port"
    ::= { pvxERPSPortCrntPMEntry 75 }


pvxERPSPortCrntPMEventPduTxTimeStamp OBJECT-TYPE
    SYNTAX       DateAndTime
    MAX-ACCESS   read-only
    STATUS       current
    DESCRIPTION  "The date and time stamp of the value."
    ::= { pvxERPSPortCrntPMEntry 76 }


pvxERPSPortCrntPMEventPduTxValidity OBJECT-TYPE
    SYNTAX       PMValidity
    MAX-ACCESS   read-only
    STATUS       current
    DESCRIPTION  "Indicates the validity of the value."
    ::= { pvxERPSPortCrntPMEntry 77 }


pvxERPSPortCrntPMEventPduTxInitialize OBJECT-TYPE
    SYNTAX       InitializeCmd
    MAX-ACCESS   read-write
    STATUS       current
    DESCRIPTION  "Used to initialize the value to 0."
    ::= { pvxERPSPortCrntPMEntry 78 }
    
pvxERPSPortCrntPMEventPduRxValue OBJECT-TYPE
    SYNTAX       Unsigned64
    MAX-ACCESS   read-only
    STATUS       current
    DESCRIPTION  "The number of Event PDUs received on this port"
    ::= { pvxERPSPortCrntPMEntry 79 }


pvxERPSPortCrntPMEventPduRxTimeStamp OBJECT-TYPE
    SYNTAX       DateAndTime
    MAX-ACCESS   read-only
    STATUS       current
    DESCRIPTION  "The date and time stamp of the value."
    ::= { pvxERPSPortCrntPMEntry 80 }


pvxERPSPortCrntPMEventPduRxValidity OBJECT-TYPE
    SYNTAX       PMValidity
    MAX-ACCESS   read-only
    STATUS       current
    DESCRIPTION  "Indicates the validity of the value."
    ::= { pvxERPSPortCrntPMEntry 81 }


pvxERPSPortCrntPMEventPduRxInitialize OBJECT-TYPE
    SYNTAX       InitializeCmd
    MAX-ACCESS   read-write
    STATUS       current
    DESCRIPTION  "Used to initialize the value to 0."
    ::= { pvxERPSPortCrntPMEntry 82 }


pvxERPSPortCrntPMVersionDiscardValue OBJECT-TYPE
    SYNTAX       Unsigned64
    MAX-ACCESS   read-only
    STATUS       current
    DESCRIPTION  "The number of PDUs version discards on this port"
    ::= { pvxERPSPortCrntPMEntry 83 }


pvxERPSPortCrntPMVersionDiscardTimeStamp OBJECT-TYPE
    SYNTAX       DateAndTime
    MAX-ACCESS   read-only
    STATUS       current
    DESCRIPTION  "The date and time stamp of the value."
    ::= { pvxERPSPortCrntPMEntry 84 }


pvxERPSPortCrntPMVersionDiscardValidity OBJECT-TYPE
    SYNTAX       PMValidity
    MAX-ACCESS   read-only
    STATUS       current
    DESCRIPTION  "Indicates the validity of the value."
    ::= { pvxERPSPortCrntPMEntry 85 }


pvxERPSPortCrntPMVersionDiscardInitialize OBJECT-TYPE
    SYNTAX       InitializeCmd
    MAX-ACCESS   read-write
    STATUS       current
    DESCRIPTION  "Used to initialize the value to 0."
    ::= { pvxERPSPortCrntPMEntry 86 }



-----------------------------------------------------------------------
-- Objects used to retrieve historical Performance Monitoring
-- statistics for PacketVX ERPS Port and ERPS Instance Port Objects
-----------------------------------------------------------------------

pvxERPSPortHistPMTable OBJECT-TYPE
    SYNTAX       SEQUENCE OF PvxERPSPortHistPMEntry
    MAX-ACCESS   not-accessible
    STATUS       current
    DESCRIPTION  "A table of historical performance monitoring statistics collected
                  for PacketVX ERPS Port and ERPS Instance Port objects."
    ::= { performance 46 }


pvxERPSPortHistPMEntry OBJECT-TYPE
    SYNTAX       PvxERPSPortHistPMEntry
    MAX-ACCESS   not-accessible
    STATUS       current
    DESCRIPTION  "The row entry object of the PacketVX ERPS Port historical
                  performance monitoring table. Each row of this table contains
                  a full set of PM statistics and related data for an historical
                  measurement interval for a given PVX ERPS Port or ERPS Instance Port."
    INDEX        { pvxERPSPortHistPMSwitchIdx,
				   pvxERPSPortHistPMShelfIdx,
				   pvxERPSPortHistPMSlotIdx,
               	   pvxERPSPortHistPMTypeIdx,
    			   pvxERPSPortHistPMPortIdx,
    			   pvxERPSPortHistPMIntervalTypeIdx,
    			   pvxERPSPortHistPMIntervalIdx }
    ::= { pvxERPSPortHistPMTable 1 }


PvxERPSPortHistPMEntry ::= SEQUENCE { pvxERPSPortHistPMSwitchIdx              INTEGER,
				                      pvxERPSPortHistPMShelfIdx       	      INTEGER,
				                      pvxERPSPortHistPMSlotIdx        	      INTEGER,
				                      pvxERPSPortHistPMTypeIdx		          PvxPortType,
                                      pvxERPSPortHistPMPortIdx                INTEGER,
                                      pvxERPSPortHistPMIntervalTypeIdx        PMIntervalType,
                                      pvxERPSPortHistPMIntervalIdx            INTEGER,
                                      pvxERPSPortHistPMPduTxValue             Unsigned64,
                                      pvxERPSPortHistPMPduTxTimeStamp         DateAndTime,
                                      pvxERPSPortHistPMPduTxValidity          PMValidity,
                                      pvxERPSPortHistPMPduTxInitialize        InitializeCmd,
                                      pvxERPSPortHistPMPduRxValue             Unsigned64,
                                      pvxERPSPortHistPMPduRxTimeStamp         DateAndTime,
                                      pvxERPSPortHistPMPduRxValidity          PMValidity,
                                      pvxERPSPortHistPMPduRxInitialize        InitializeCmd,
                                      pvxERPSPortHistPMPduDiscardValue        Unsigned64,
                                      pvxERPSPortHistPMPduDiscardTimeStamp    DateAndTime,
                                      pvxERPSPortHistPMPduDiscardValidity     PMValidity,
                                      pvxERPSPortHistPMPduDiscardInitialize   InitializeCmd,
                                      pvxERPSPortHistPMBlockedValue           Unsigned64,
                                      pvxERPSPortHistPMBlockedTimeStamp       DateAndTime,
                                      pvxERPSPortHistPMBlockedValidity        PMValidity,
                                      pvxERPSPortHistPMBlockedInitialize      InitializeCmd,
                                      pvxERPSPortHistPMUnblockedValue         Unsigned64,
                                      pvxERPSPortHistPMUnblockedTimeStamp     DateAndTime,
                                      pvxERPSPortHistPMUnblockedValidity      PMValidity,
                                      pvxERPSPortHistPMUnblockedInitialize    InitializeCmd,
                                      pvxERPSPortHistPMFailuresValue          Unsigned64,
                                      pvxERPSPortHistPMFailuresTimeStamp      DateAndTime,
                                      pvxERPSPortHistPMFailuresValidity       PMValidity,
                                      pvxERPSPortHistPMFailuresInitialize     InitializeCmd,
                                      pvxERPSPortHistPMRecoveriesValue        Unsigned64,
                                      pvxERPSPortHistPMRecoveriesTimeStamp    DateAndTime,
                                      pvxERPSPortHistPMRecoveriesValidity     PMValidity,
                                      pvxERPSPortHistPMRecoveriesInitialize   InitializeCmd,
                                      pvxERPSPortHistPMNrPduTxValue           Unsigned64,
                                      pvxERPSPortHistPMNrPduTxTimeStamp       DateAndTime,
                                      pvxERPSPortHistPMNrPduTxValidity        PMValidity,
                                      pvxERPSPortHistPMNrPduTxInitialize      InitializeCmd,
                                      pvxERPSPortHistPMNrPduRxValue           Unsigned64,
                                      pvxERPSPortHistPMNrPduRxTimeStamp       DateAndTime,
                                      pvxERPSPortHistPMNrPduRxValidity        PMValidity,
                                      pvxERPSPortHistPMNrPduRxInitialize      InitializeCmd,
                                      pvxERPSPortHistPMNrrbPduTxValue         Unsigned64,
                                      pvxERPSPortHistPMNrrbPduTxTimeStamp     DateAndTime,
                                      pvxERPSPortHistPMNrrbPduTxValidity      PMValidity,
                                      pvxERPSPortHistPMNrrbPduTxInitialize    InitializeCmd,
                                      pvxERPSPortHistPMNrrbPduRxValue         Unsigned64,
                                      pvxERPSPortHistPMNrrbPduRxTimeStamp     DateAndTime,
                                      pvxERPSPortHistPMNrrbPduRxValidity      PMValidity,
                                      pvxERPSPortHistPMNrrbPduRxInitialize    InitializeCmd,
                                      pvxERPSPortHistPMSfPduTxValue           Unsigned64,
                                      pvxERPSPortHistPMSfPduTxTimeStamp       DateAndTime,
                                      pvxERPSPortHistPMSfPduTxValidity        PMValidity,
                                      pvxERPSPortHistPMSfPduTxInitialize      InitializeCmd,
                                      pvxERPSPortHistPMSfPduRxValue           Unsigned64,
                                      pvxERPSPortHistPMSfPduRxTimeStamp       DateAndTime,
                                      pvxERPSPortHistPMSfPduRxValidity        PMValidity,
                                      pvxERPSPortHistPMSfPduRxInitialize      InitializeCmd,
                                      pvxERPSPortHistPMFsPduTxValue           Unsigned64,
                                      pvxERPSPortHistPMFsPduTxTimeStamp       DateAndTime,
                                      pvxERPSPortHistPMFsPduTxValidity        PMValidity,
                                      pvxERPSPortHistPMFsPduTxInitialize      InitializeCmd,
                                      pvxERPSPortHistPMFsPduRxValue           Unsigned64,
                                      pvxERPSPortHistPMFsPduRxTimeStamp       DateAndTime,
                                      pvxERPSPortHistPMFsPduRxValidity        PMValidity,
                                      pvxERPSPortHistPMFsPduRxInitialize      InitializeCmd,
                                      pvxERPSPortHistPMMsPduTxValue           Unsigned64,
                                      pvxERPSPortHistPMMsPduTxTimeStamp       DateAndTime,
                                      pvxERPSPortHistPMMsPduTxValidity        PMValidity,
                                      pvxERPSPortHistPMMsPduTxInitialize      InitializeCmd,
                                      pvxERPSPortHistPMMsPduRxValue           Unsigned64,
                                      pvxERPSPortHistPMMsPduRxTimeStamp       DateAndTime,
                                      pvxERPSPortHistPMMsPduRxValidity        PMValidity,
                                      pvxERPSPortHistPMMsPduRxInitialize      InitializeCmd,
                                      pvxERPSPortHistPMEventPduTxValue        Unsigned64,
                                      pvxERPSPortHistPMEventPduTxTimeStamp    DateAndTime,
                                      pvxERPSPortHistPMEventPduTxValidity     PMValidity,
                                      pvxERPSPortHistPMEventPduTxInitialize   InitializeCmd,
                                      pvxERPSPortHistPMEventPduRxValue        Unsigned64,
                                      pvxERPSPortHistPMEventPduRxTimeStamp    DateAndTime,
                                      pvxERPSPortHistPMEventPduRxValidity     PMValidity,
                                      pvxERPSPortHistPMEventPduRxInitialize   InitializeCmd,
                                      pvxERPSPortHistPMVersionDiscardValue        Unsigned64,
                                      pvxERPSPortHistPMVersionDiscardTimeStamp    DateAndTime,
                                      pvxERPSPortHistPMVersionDiscardValidity     PMValidity,
                                      pvxERPSPortHistPMVersionDiscardInitialize   InitializeCmd }
                                  
                                  
pvxERPSPortHistPMSwitchIdx OBJECT-TYPE
   	SYNTAX       INTEGER(1..11)
   	MAX-ACCESS   not-accessible
   	STATUS       current
    DESCRIPTION  "The identifier of the ethernet switch instance on which the
                  ERPS Port is provisioned."
    ::= {pvxERPSPortHistPMEntry 1 }


pvxERPSPortHistPMShelfIdx OBJECT-TYPE
    SYNTAX       INTEGER (0|1|11|21|31)
    MAX-ACCESS   not-accessible
    STATUS       current
    DESCRIPTION  "The number of the shelf on which the ERPS Port targeted
                  for PMs is provisioned. For LAG entities, the shelf number is 0."
    ::= {pvxERPSPortHistPMEntry 2 }


pvxERPSPortHistPMSlotIdx OBJECT-TYPE
    SYNTAX       INTEGER (0|1|3|5|7|9|11|13|15|17|19)
    MAX-ACCESS   not-accessible
    STATUS       current
    DESCRIPTION  "The number of the slot within which the ERPS Port targeted
                  for PMs is provisioned. For LAG entities, the slot number is 0."
    ::= {pvxERPSPortHistPMEntry 3 }


pvxERPSPortHistPMTypeIdx OBJECT-TYPE
    SYNTAX       PvxPortType
    MAX-ACCESS   not-accessible
    STATUS       current
    DESCRIPTION  "The type of PacketVX port on which the ERPS Port
                  facility is provisioned."
    ::= {pvxERPSPortHistPMEntry 4 }


pvxERPSPortHistPMPortIdx OBJECT-TYPE
    SYNTAX       INTEGER (0..64)
    MAX-ACCESS   not-accessible
    STATUS       current
    DESCRIPTION  "The port number of the ERPS Port."
    ::= {pvxERPSPortHistPMEntry 5 }


pvxERPSPortHistPMIntervalTypeIdx OBJECT-TYPE
    SYNTAX       PMIntervalType
    MAX-ACCESS   not-accessible
    STATUS       current
    DESCRIPTION  "The type of PM bin according to interval length."
    ::= { pvxERPSPortHistPMEntry 6 }


pvxERPSPortHistPMIntervalIdx OBJECT-TYPE
    SYNTAX       INTEGER (1..96)
    MAX-ACCESS   not-accessible
    STATUS       current
    DESCRIPTION  "The specific PM bin number. The range is 1 to 96 for the
                  15-minute historical bins. For the 1-day historical bin, the
                  value is 1."
    ::= { pvxERPSPortHistPMEntry 7 }

pvxERPSPortHistPMPduTxValue OBJECT-TYPE
    SYNTAX       Unsigned64
    MAX-ACCESS   read-only
    STATUS       current
    DESCRIPTION  "The Number of PDUs transmitted on this port"
    ::= { pvxERPSPortHistPMEntry 8 }


pvxERPSPortHistPMPduTxTimeStamp OBJECT-TYPE
    SYNTAX       DateAndTime
    MAX-ACCESS   read-only
    STATUS       current
    DESCRIPTION  "The date and time stamp of the value."
    ::= { pvxERPSPortHistPMEntry 9 }


pvxERPSPortHistPMPduTxValidity OBJECT-TYPE
    SYNTAX       PMValidity
    MAX-ACCESS   read-only
    STATUS       current
    DESCRIPTION  "Indicates the validity of the value."
    ::= { pvxERPSPortHistPMEntry 10 }


pvxERPSPortHistPMPduTxInitialize OBJECT-TYPE
    SYNTAX       InitializeCmd
    MAX-ACCESS   read-write
    STATUS       current
    DESCRIPTION  "Used to initialize the value to 0."
    ::= { pvxERPSPortHistPMEntry 11 }

pvxERPSPortHistPMPduRxValue OBJECT-TYPE
    SYNTAX       Unsigned64
    MAX-ACCESS   read-only
    STATUS       current
    DESCRIPTION  "The number of PDUs received on this port"
    ::= { pvxERPSPortHistPMEntry 12 }


pvxERPSPortHistPMPduRxTimeStamp OBJECT-TYPE
    SYNTAX       DateAndTime
    MAX-ACCESS   read-only
    STATUS       current
    DESCRIPTION  "The date and time stamp of the value."
    ::= { pvxERPSPortHistPMEntry 13 }


pvxERPSPortHistPMPduRxValidity OBJECT-TYPE
    SYNTAX       PMValidity
    MAX-ACCESS   read-only
    STATUS       current
    DESCRIPTION  "Indicates the validity of the value."
    ::= { pvxERPSPortHistPMEntry 14 }


pvxERPSPortHistPMPduRxInitialize OBJECT-TYPE
    SYNTAX       InitializeCmd
    MAX-ACCESS   read-write
    STATUS       current
    DESCRIPTION  "Used to initialize the value to 0."
    ::= { pvxERPSPortHistPMEntry 15 }

pvxERPSPortHistPMPduDiscardValue OBJECT-TYPE
    SYNTAX       Unsigned64
    MAX-ACCESS   read-only
    STATUS       current
    DESCRIPTION  "The number of PDUs discarded on this port"
    ::= { pvxERPSPortHistPMEntry 16 }


pvxERPSPortHistPMPduDiscardTimeStamp OBJECT-TYPE
    SYNTAX       DateAndTime
    MAX-ACCESS   read-only
    STATUS       current
    DESCRIPTION  "The date and time stamp of the value."
    ::= { pvxERPSPortHistPMEntry 17 }


pvxERPSPortHistPMPduDiscardValidity OBJECT-TYPE
    SYNTAX       PMValidity
    MAX-ACCESS   read-only
    STATUS       current
    DESCRIPTION  "Indicates the validity of the value."
    ::= { pvxERPSPortHistPMEntry 18 }


pvxERPSPortHistPMPduDiscardInitialize OBJECT-TYPE
    SYNTAX       InitializeCmd
    MAX-ACCESS   read-write
    STATUS       current
    DESCRIPTION  "Used to initialize the value to 0."
    ::= { pvxERPSPortHistPMEntry 19 }

pvxERPSPortHistPMBlockedValue OBJECT-TYPE
    SYNTAX       Unsigned64
    MAX-ACCESS   read-only
    STATUS       current
    DESCRIPTION  "The number of times this port has transitioned to blocked state"
    ::= { pvxERPSPortHistPMEntry 20 }


pvxERPSPortHistPMBlockedTimeStamp OBJECT-TYPE
    SYNTAX       DateAndTime
    MAX-ACCESS   read-only
    STATUS       current
    DESCRIPTION  "The date and time stamp of the value."
    ::= { pvxERPSPortHistPMEntry 21 }


pvxERPSPortHistPMBlockedValidity OBJECT-TYPE
    SYNTAX       PMValidity
    MAX-ACCESS   read-only
    STATUS       current
    DESCRIPTION  "Indicates the validity of the value."
    ::= { pvxERPSPortHistPMEntry 22 }


pvxERPSPortHistPMBlockedInitialize OBJECT-TYPE
    SYNTAX       InitializeCmd
    MAX-ACCESS   read-write
    STATUS       current
    DESCRIPTION  "Used to initialize the value to 0."
    ::= { pvxERPSPortHistPMEntry 23 }

pvxERPSPortHistPMUnblockedValue OBJECT-TYPE
    SYNTAX       Unsigned64
    MAX-ACCESS   read-only
    STATUS       current
    DESCRIPTION  "The number of times this port has transitioned to unblocked state"
    ::= { pvxERPSPortHistPMEntry 24 }


pvxERPSPortHistPMUnblockedTimeStamp OBJECT-TYPE
    SYNTAX       DateAndTime
    MAX-ACCESS   read-only
    STATUS       current
    DESCRIPTION  "The date and time stamp of the value."
    ::= { pvxERPSPortHistPMEntry 25 }


pvxERPSPortHistPMUnblockedValidity OBJECT-TYPE
    SYNTAX       PMValidity
    MAX-ACCESS   read-only
    STATUS       current
    DESCRIPTION  "Indicates the validity of the value."
    ::= { pvxERPSPortHistPMEntry 26 }


pvxERPSPortHistPMUnblockedInitialize OBJECT-TYPE
    SYNTAX       InitializeCmd
    MAX-ACCESS   read-write
    STATUS       current
    DESCRIPTION  "Used to initialize the value to 0."
    ::= { pvxERPSPortHistPMEntry 27 }

pvxERPSPortHistPMFailuresValue OBJECT-TYPE
    SYNTAX       Unsigned64
    MAX-ACCESS   read-only
    STATUS       current
    DESCRIPTION  "The number of times this port has transitioned to failed state"
    ::= { pvxERPSPortHistPMEntry 28 }


pvxERPSPortHistPMFailuresTimeStamp OBJECT-TYPE
    SYNTAX       DateAndTime
    MAX-ACCESS   read-only
    STATUS       current
    DESCRIPTION  "The date and time stamp of the value."
    ::= { pvxERPSPortHistPMEntry 29 }


pvxERPSPortHistPMFailuresValidity OBJECT-TYPE
    SYNTAX       PMValidity
    MAX-ACCESS   read-only
    STATUS       current
    DESCRIPTION  "Indicates the validity of the value."
    ::= { pvxERPSPortHistPMEntry 30 }


pvxERPSPortHistPMFailuresInitialize OBJECT-TYPE
    SYNTAX       InitializeCmd
    MAX-ACCESS   read-write
    STATUS       current
    DESCRIPTION  "Used to initialize the value to 0."
    ::= { pvxERPSPortHistPMEntry 31 }

pvxERPSPortHistPMRecoveriesValue OBJECT-TYPE
    SYNTAX       Unsigned64
    MAX-ACCESS   read-only
    STATUS       current
    DESCRIPTION  "The number of times this port has recovered from failed state"
    ::= { pvxERPSPortHistPMEntry 32 }


pvxERPSPortHistPMRecoveriesTimeStamp OBJECT-TYPE
    SYNTAX       DateAndTime
    MAX-ACCESS   read-only
    STATUS       current
    DESCRIPTION  "The date and time stamp of the value."
    ::= { pvxERPSPortHistPMEntry 33 }


pvxERPSPortHistPMRecoveriesValidity OBJECT-TYPE
    SYNTAX       PMValidity
    MAX-ACCESS   read-only
    STATUS       current
    DESCRIPTION  "Indicates the validity of the value."
    ::= { pvxERPSPortHistPMEntry 34 }


pvxERPSPortHistPMRecoveriesInitialize OBJECT-TYPE
    SYNTAX       InitializeCmd
    MAX-ACCESS   read-write
    STATUS       current
    DESCRIPTION  "Used to initialize the value to 0."
    ::= { pvxERPSPortHistPMEntry 35 }

pvxERPSPortHistPMNrPduTxValue OBJECT-TYPE
    SYNTAX       Unsigned64
    MAX-ACCESS   read-only
    STATUS       current
    DESCRIPTION  "The Number of NR PDUs transmitted on this port"
    ::= { pvxERPSPortHistPMEntry 36 }


pvxERPSPortHistPMNrPduTxTimeStamp OBJECT-TYPE
    SYNTAX       DateAndTime
    MAX-ACCESS   read-only
    STATUS       current
    DESCRIPTION  "The date and time stamp of the value."
    ::= { pvxERPSPortHistPMEntry 37 }


pvxERPSPortHistPMNrPduTxValidity OBJECT-TYPE
    SYNTAX       PMValidity
    MAX-ACCESS   read-only
    STATUS       current
    DESCRIPTION  "Indicates the validity of the value."
    ::= { pvxERPSPortHistPMEntry 38 }


pvxERPSPortHistPMNrPduTxInitialize OBJECT-TYPE
    SYNTAX       InitializeCmd
    MAX-ACCESS   read-write
    STATUS       current
    DESCRIPTION  "Used to initialize the value to 0."
    ::= { pvxERPSPortHistPMEntry 39 }
    
pvxERPSPortHistPMNrPduRxValue OBJECT-TYPE
    SYNTAX       Unsigned64
    MAX-ACCESS   read-only
    STATUS       current
    DESCRIPTION  "The number of NR PDUs received on this port"
    ::= { pvxERPSPortHistPMEntry 40 }


pvxERPSPortHistPMNrPduRxTimeStamp OBJECT-TYPE
    SYNTAX       DateAndTime
    MAX-ACCESS   read-only
    STATUS       current
    DESCRIPTION  "The date and time stamp of the value."
    ::= { pvxERPSPortHistPMEntry 41 }


pvxERPSPortHistPMNrPduRxValidity OBJECT-TYPE
    SYNTAX       PMValidity
    MAX-ACCESS   read-only
    STATUS       current
    DESCRIPTION  "Indicates the validity of the value."
    ::= { pvxERPSPortHistPMEntry 42 }


pvxERPSPortHistPMNrPduRxInitialize OBJECT-TYPE
    SYNTAX       InitializeCmd
    MAX-ACCESS   read-write
    STATUS       current
    DESCRIPTION  "Used to initialize the value to 0."
    ::= { pvxERPSPortHistPMEntry 43 }
    

pvxERPSPortHistPMNrrbPduTxValue OBJECT-TYPE
    SYNTAX       Unsigned64
    MAX-ACCESS   read-only
    STATUS       current
    DESCRIPTION  "The Number of NRRB PDUs transmitted on this port"
    ::= { pvxERPSPortHistPMEntry 44 }


pvxERPSPortHistPMNrrbPduTxTimeStamp OBJECT-TYPE
    SYNTAX       DateAndTime
    MAX-ACCESS   read-only
    STATUS       current
    DESCRIPTION  "The date and time stamp of the value."
    ::= { pvxERPSPortHistPMEntry 45 }


pvxERPSPortHistPMNrrbPduTxValidity OBJECT-TYPE
    SYNTAX       PMValidity
    MAX-ACCESS   read-only
    STATUS       current
    DESCRIPTION  "Indicates the validity of the value."
    ::= { pvxERPSPortHistPMEntry 46 }


pvxERPSPortHistPMNrrbPduTxInitialize OBJECT-TYPE
    SYNTAX       InitializeCmd
    MAX-ACCESS   read-write
    STATUS       current
    DESCRIPTION  "Used to initialize the value to 0."
    ::= { pvxERPSPortHistPMEntry 47 }
    
pvxERPSPortHistPMNrrbPduRxValue OBJECT-TYPE
    SYNTAX       Unsigned64
    MAX-ACCESS   read-only
    STATUS       current
    DESCRIPTION  "The number of NRRB PDUs received on this port"
    ::= { pvxERPSPortHistPMEntry 48 }


pvxERPSPortHistPMNrrbPduRxTimeStamp OBJECT-TYPE
    SYNTAX       DateAndTime
    MAX-ACCESS   read-only
    STATUS       current
    DESCRIPTION  "The date and time stamp of the value."
    ::= { pvxERPSPortHistPMEntry 49 }


pvxERPSPortHistPMNrrbPduRxValidity OBJECT-TYPE
    SYNTAX       PMValidity
    MAX-ACCESS   read-only
    STATUS       current
    DESCRIPTION  "Indicates the validity of the value."
    ::= { pvxERPSPortHistPMEntry 50 }


pvxERPSPortHistPMNrrbPduRxInitialize OBJECT-TYPE
    SYNTAX       InitializeCmd
    MAX-ACCESS   read-write
    STATUS       current
    DESCRIPTION  "Used to initialize the value to 0."
    ::= { pvxERPSPortHistPMEntry 51 }
    

pvxERPSPortHistPMSfPduTxValue OBJECT-TYPE
    SYNTAX       Unsigned64
    MAX-ACCESS   read-only
    STATUS       current
    DESCRIPTION  "The Number of SF PDUs transmitted on this port"
    ::= { pvxERPSPortHistPMEntry 52 }


pvxERPSPortHistPMSfPduTxTimeStamp OBJECT-TYPE
    SYNTAX       DateAndTime
    MAX-ACCESS   read-only
    STATUS       current
    DESCRIPTION  "The date and time stamp of the value."
    ::= { pvxERPSPortHistPMEntry 53 }


pvxERPSPortHistPMSfPduTxValidity OBJECT-TYPE
    SYNTAX       PMValidity
    MAX-ACCESS   read-only
    STATUS       current
    DESCRIPTION  "Indicates the validity of the value."
    ::= { pvxERPSPortHistPMEntry 54 }


pvxERPSPortHistPMSfPduTxInitialize OBJECT-TYPE
    SYNTAX       InitializeCmd
    MAX-ACCESS   read-write
    STATUS       current
    DESCRIPTION  "Used to initialize the value to 0."
    ::= { pvxERPSPortHistPMEntry 55 }
    
pvxERPSPortHistPMSfPduRxValue OBJECT-TYPE
    SYNTAX       Unsigned64
    MAX-ACCESS   read-only
    STATUS       current
    DESCRIPTION  "The number of SF PDUs received on this port"
    ::= { pvxERPSPortHistPMEntry 56 }


pvxERPSPortHistPMSfPduRxTimeStamp OBJECT-TYPE
    SYNTAX       DateAndTime
    MAX-ACCESS   read-only
    STATUS       current
    DESCRIPTION  "The date and time stamp of the value."
    ::= { pvxERPSPortHistPMEntry 57 }


pvxERPSPortHistPMSfPduRxValidity OBJECT-TYPE
    SYNTAX       PMValidity
    MAX-ACCESS   read-only
    STATUS       current
    DESCRIPTION  "Indicates the validity of the value."
    ::= { pvxERPSPortHistPMEntry 58 }


pvxERPSPortHistPMSfPduRxInitialize OBJECT-TYPE
    SYNTAX       InitializeCmd
    MAX-ACCESS   read-write
    STATUS       current
    DESCRIPTION  "Used to initialize the value to 0."
    ::= { pvxERPSPortHistPMEntry 59 }
    
pvxERPSPortHistPMFsPduTxValue OBJECT-TYPE
    SYNTAX       Unsigned64
    MAX-ACCESS   read-only
    STATUS       current
    DESCRIPTION  "The Number of FS PDUs transmitted on this port"
    ::= { pvxERPSPortHistPMEntry 60 }


pvxERPSPortHistPMFsPduTxTimeStamp OBJECT-TYPE
    SYNTAX       DateAndTime
    MAX-ACCESS   read-only
    STATUS       current
    DESCRIPTION  "The date and time stamp of the value."
    ::= { pvxERPSPortHistPMEntry 61 }


pvxERPSPortHistPMFsPduTxValidity OBJECT-TYPE
    SYNTAX       PMValidity
    MAX-ACCESS   read-only
    STATUS       current
    DESCRIPTION  "Indicates the validity of the value."
    ::= { pvxERPSPortHistPMEntry 62 }


pvxERPSPortHistPMFsPduTxInitialize OBJECT-TYPE
    SYNTAX       InitializeCmd
    MAX-ACCESS   read-write
    STATUS       current
    DESCRIPTION  "Used to initialize the value to 0."
    ::= { pvxERPSPortHistPMEntry 63 }
    
pvxERPSPortHistPMFsPduRxValue OBJECT-TYPE
    SYNTAX       Unsigned64
    MAX-ACCESS   read-only
    STATUS       current
    DESCRIPTION  "The number of FS PDUs received on this port"
    ::= { pvxERPSPortHistPMEntry 64 }


pvxERPSPortHistPMFsPduRxTimeStamp OBJECT-TYPE
    SYNTAX       DateAndTime
    MAX-ACCESS   read-only
    STATUS       current
    DESCRIPTION  "The date and time stamp of the value."
    ::= { pvxERPSPortHistPMEntry 65 }


pvxERPSPortHistPMFsPduRxValidity OBJECT-TYPE
    SYNTAX       PMValidity
    MAX-ACCESS   read-only
    STATUS       current
    DESCRIPTION  "Indicates the validity of the value."
    ::= { pvxERPSPortHistPMEntry 66 }


pvxERPSPortHistPMFsPduRxInitialize OBJECT-TYPE
    SYNTAX       InitializeCmd
    MAX-ACCESS   read-write
    STATUS       current
    DESCRIPTION  "Used to initialize the value to 0."
    ::= { pvxERPSPortHistPMEntry 67 }
    
pvxERPSPortHistPMMsPduTxValue OBJECT-TYPE
    SYNTAX       Unsigned64
    MAX-ACCESS   read-only
    STATUS       current
    DESCRIPTION  "The Number of MS PDUs transmitted on this port"
    ::= { pvxERPSPortHistPMEntry 68 }


pvxERPSPortHistPMMsPduTxTimeStamp OBJECT-TYPE
    SYNTAX       DateAndTime
    MAX-ACCESS   read-only
    STATUS       current
    DESCRIPTION  "The date and time stamp of the value."
    ::= { pvxERPSPortHistPMEntry 69 }


pvxERPSPortHistPMMsPduTxValidity OBJECT-TYPE
    SYNTAX       PMValidity
    MAX-ACCESS   read-only
    STATUS       current
    DESCRIPTION  "Indicates the validity of the value."
    ::= { pvxERPSPortHistPMEntry 70 }


pvxERPSPortHistPMMsPduTxInitialize OBJECT-TYPE
    SYNTAX       InitializeCmd
    MAX-ACCESS   read-write
    STATUS       current
    DESCRIPTION  "Used to initialize the value to 0."
    ::= { pvxERPSPortHistPMEntry 71 }
    
pvxERPSPortHistPMMsPduRxValue OBJECT-TYPE
    SYNTAX       Unsigned64
    MAX-ACCESS   read-only
    STATUS       current
    DESCRIPTION  "The number of MS PDUs received on this port"
    ::= { pvxERPSPortHistPMEntry 72 }


pvxERPSPortHistPMMsPduRxTimeStamp OBJECT-TYPE
    SYNTAX       DateAndTime
    MAX-ACCESS   read-only
    STATUS       current
    DESCRIPTION  "The date and time stamp of the value."
    ::= { pvxERPSPortHistPMEntry 73 }


pvxERPSPortHistPMMsPduRxValidity OBJECT-TYPE
    SYNTAX       PMValidity
    MAX-ACCESS   read-only
    STATUS       current
    DESCRIPTION  "Indicates the validity of the value."
    ::= { pvxERPSPortHistPMEntry 74 }


pvxERPSPortHistPMMsPduRxInitialize OBJECT-TYPE
    SYNTAX       InitializeCmd
    MAX-ACCESS   read-write
    STATUS       current
    DESCRIPTION  "Used to initialize the value to 0."
    ::= { pvxERPSPortHistPMEntry 75 }
    
pvxERPSPortHistPMEventPduTxValue OBJECT-TYPE
    SYNTAX       Unsigned64
    MAX-ACCESS   read-only
    STATUS       current
    DESCRIPTION  "The Number of Event PDUs transmitted on this port"
    ::= { pvxERPSPortHistPMEntry 76 }


pvxERPSPortHistPMEventPduTxTimeStamp OBJECT-TYPE
    SYNTAX       DateAndTime
    MAX-ACCESS   read-only
    STATUS       current
    DESCRIPTION  "The date and time stamp of the value."
    ::= { pvxERPSPortHistPMEntry 77 }


pvxERPSPortHistPMEventPduTxValidity OBJECT-TYPE
    SYNTAX       PMValidity
    MAX-ACCESS   read-only
    STATUS       current
    DESCRIPTION  "Indicates the validity of the value."
    ::= { pvxERPSPortHistPMEntry 78 }


pvxERPSPortHistPMEventPduTxInitialize OBJECT-TYPE
    SYNTAX       InitializeCmd
    MAX-ACCESS   read-write
    STATUS       current
    DESCRIPTION  "Used to initialize the value to 0."
    ::= { pvxERPSPortHistPMEntry 79 }
   
pvxERPSPortHistPMEventPduRxValue OBJECT-TYPE
    SYNTAX       Unsigned64
    MAX-ACCESS   read-only
    STATUS       current
    DESCRIPTION  "The number of Event PDUs received on this port"
    ::= { pvxERPSPortHistPMEntry 80 }


pvxERPSPortHistPMEventPduRxTimeStamp OBJECT-TYPE
    SYNTAX       DateAndTime
    MAX-ACCESS   read-only
    STATUS       current
    DESCRIPTION  "The date and time stamp of the value."
    ::= { pvxERPSPortHistPMEntry 81 }


pvxERPSPortHistPMEventPduRxValidity OBJECT-TYPE
    SYNTAX       PMValidity
    MAX-ACCESS   read-only
    STATUS       current
    DESCRIPTION  "Indicates the validity of the value."
    ::= { pvxERPSPortHistPMEntry 82 }


pvxERPSPortHistPMEventPduRxInitialize OBJECT-TYPE
    SYNTAX       InitializeCmd
    MAX-ACCESS   read-write
    STATUS       current
    DESCRIPTION  "Used to initialize the value to 0."
    ::= { pvxERPSPortHistPMEntry 83 }


pvxERPSPortHistPMVersionDiscardValue OBJECT-TYPE
    SYNTAX       Unsigned64
    MAX-ACCESS   read-only
    STATUS       current
    DESCRIPTION  "The number of PDUs version discards on this port"
    ::= { pvxERPSPortHistPMEntry 84 }


pvxERPSPortHistPMVersionDiscardTimeStamp OBJECT-TYPE
    SYNTAX       DateAndTime
    MAX-ACCESS   read-only
    STATUS       current
    DESCRIPTION  "The date and time stamp of the value."
    ::= { pvxERPSPortHistPMEntry 85 }


pvxERPSPortHistPMVersionDiscardValidity OBJECT-TYPE
    SYNTAX       PMValidity
    MAX-ACCESS   read-only
    STATUS       current
    DESCRIPTION  "Indicates the validity of the value."
    ::= { pvxERPSPortHistPMEntry 86 }


pvxERPSPortHistPMVersionDiscardInitialize OBJECT-TYPE
    SYNTAX       InitializeCmd
    MAX-ACCESS   read-write
    STATUS       current
    DESCRIPTION  "Used to initialize the value to 0."
    ::= { pvxERPSPortHistPMEntry 87 }


-----------------------------------------------------------------------
-- Objects used to retrieve historical Performance Monitoring
-- statistics for PacketVX Ethernet Service SLA PM Objects
-----------------------------------------------------------------------

pvxEServiceSlaCrntPMTable OBJECT-TYPE
    SYNTAX       SEQUENCE OF PvxEServiceSlaCrntPMEntry
    MAX-ACCESS   not-accessible
    STATUS       current
    DESCRIPTION  "A table of performance monitoring statistics collected
                  for PacketVX Ethernet Service SLA objects."
    ::= { performance 47 }

pvxEServiceSlaCrntPMEntry OBJECT-TYPE
    SYNTAX       PvxEServiceSlaCrntPMEntry
    MAX-ACCESS   not-accessible
    STATUS       current
    DESCRIPTION  "The row entry object of the PacketVX Ethernet Service SLA historical
                  performance monitoring table. Each row of this table contains
                  a full set of PM statistics and related data for an historical
                  measurement interval for a given PVX Ethernet Service's SLA."
    INDEX        { pvxEServiceSlaCrntPMSwitchIdx,
				   pvxEServiceSlaCrntPMShelfIdx,
				   pvxEServiceSlaCrntPMSlotIdx,
               	   pvxEServiceSlaCrntPMPortTypeIdx,
    			   pvxEServiceSlaCrntPMPortIdx,
    			   pvxEServiceSlaCrntPMESName,
                   pvxEServiceSlaCrntPMRMepId,
                   pvxEServiceSlaCrntPMIntervalTypeIdx }
                   
    ::= { pvxEServiceSlaCrntPMTable 1 }


PvxEServiceSlaCrntPMEntry ::= SEQUENCE { pvxEServiceSlaCrntPMSwitchIdx                      INTEGER,
                                         pvxEServiceSlaCrntPMShelfIdx                       INTEGER,
                                         pvxEServiceSlaCrntPMSlotIdx                        INTEGER,
                                         pvxEServiceSlaCrntPMPortTypeIdx                    PvxPortType,
                                         pvxEServiceSlaCrntPMPortIdx                        INTEGER,
                                         pvxEServiceSlaCrntPMESName                         DisplayString,
                                         pvxEServiceSlaCrntPMRMepId                         INTEGER,
                                         pvxEServiceSlaCrntPMIntervalTypeIdx                PMIntervalType,
                                         pvxEServiceSlaCrntPMNearEndFrameLoss               FixedX1000,
                                         pvxEServiceSlaCrntPMNearEndFrameLossTimeStamp      DateAndTime,
                                         pvxEServiceSlaCrntPMNearEndFrameLossValidity       PMValidity,
                                         pvxEServiceSlaCrntPMNearEndFrameLossInitialize     InitializeCmd,
                                         pvxEServiceSlaCrntPMFarEndFrameLoss                FixedX1000,
                                         pvxEServiceSlaCrntPMFarEndFrameLossTimeStamp       DateAndTime,
                                         pvxEServiceSlaCrntPMFarEndFrameLossValidity        PMValidity,
                                         pvxEServiceSlaCrntPMFarEndFrameLossInitialize      InitializeCmd,
                                         pvxEServiceSlaCrntPM2WayDelayMinimum               Unsigned32,
                                         pvxEServiceSlaCrntPM2WayDelayMinimumTimeStamp      DateAndTime,
                                         pvxEServiceSlaCrntPM2WayDelayMinimumValidity       PMValidity,
                                         pvxEServiceSlaCrntPM2WayDelayMinimumInitialize     InitializeCmd,
                                         pvxEServiceSlaCrntPM2WayDelayMaximum               Unsigned32,
                                         pvxEServiceSlaCrntPM2WayDelayMaximumTimeStamp      DateAndTime,
                                         pvxEServiceSlaCrntPM2WayDelayMaximumValidity       PMValidity,
                                         pvxEServiceSlaCrntPM2WayDelayMaximumInitialize     InitializeCmd,
                                         pvxEServiceSlaCrntPM2WayDelayAverage               Unsigned32,
                                         pvxEServiceSlaCrntPM2WayDelayAverageTimeStamp      DateAndTime,
                                         pvxEServiceSlaCrntPM2WayDelayAverageValidity       PMValidity,
                                         pvxEServiceSlaCrntPM2WayDelayAverageInitialize     InitializeCmd,
                                         pvxEServiceSlaCrntPM2WayDelayVariationMinimum      Unsigned32,
                                         pvxEServiceSlaCrntPM2WayDelayVariationMinimumTimeStamp         DateAndTime,
                                         pvxEServiceSlaCrntPM2WayDelayVariationMinimumValidity          PMValidity,
                                         pvxEServiceSlaCrntPM2WayDelayVariationMinimumInitialize        InitializeCmd,
                                         pvxEServiceSlaCrntPM2WayDelayVariationMaximum                  Unsigned32,
                                         pvxEServiceSlaCrntPM2WayDelayVariationMaximumTimeStamp         DateAndTime,
                                         pvxEServiceSlaCrntPM2WayDelayVariationMaximumValidity          PMValidity,
                                         pvxEServiceSlaCrntPM2WayDelayVariationMaximumInitialize        InitializeCmd,
                                         pvxEServiceSlaCrntPM2WayDelayVariationAverage                  Unsigned32,
                                         pvxEServiceSlaCrntPM2WayDelayVariationAverageTimeStamp         DateAndTime,
                                         pvxEServiceSlaCrntPM2WayDelayVariationAverageValidity          PMValidity,
                                         pvxEServiceSlaCrntPM2WayDelayVariationAverageInitialize        InitializeCmd }

                                  
pvxEServiceSlaCrntPMSwitchIdx OBJECT-TYPE
   	SYNTAX       INTEGER(1..11)
   	MAX-ACCESS   not-accessible
   	STATUS       current
    DESCRIPTION  "The identifier of the ethernet switch instance on which the
                  Ethernet Service SLA is provisioned."
    ::= {pvxEServiceSlaCrntPMEntry 1 }


pvxEServiceSlaCrntPMShelfIdx OBJECT-TYPE
    SYNTAX       INTEGER (0|1|11|21|31)
    MAX-ACCESS   not-accessible
    STATUS       current
    DESCRIPTION  "The number of the shelf on which the Ethernet Service SLA targeted
                  for PMs is provisioned. For LAG entities, the shelf number is 0."
    ::= {pvxEServiceSlaCrntPMEntry 2 }


pvxEServiceSlaCrntPMSlotIdx OBJECT-TYPE
    SYNTAX       INTEGER (0|1|3|5|7|9|11|13|15|17|19)
    MAX-ACCESS   not-accessible
    STATUS       current
    DESCRIPTION  "The number of the slot within which the Ethernet Service SLA targeted
                  for PMs is provisioned. For LAG entities, the slot number is 0."
    ::= {pvxEServiceSlaCrntPMEntry 3 }


pvxEServiceSlaCrntPMPortTypeIdx OBJECT-TYPE
    SYNTAX       PvxPortType
    MAX-ACCESS   not-accessible
    STATUS       current
    DESCRIPTION  "The type of PacketVX port on which the Ethernet Service SLA
                  facility is provisioned."
    ::= {pvxEServiceSlaCrntPMEntry 4 }


pvxEServiceSlaCrntPMPortIdx OBJECT-TYPE
    SYNTAX       INTEGER (0..64)
    MAX-ACCESS   not-accessible
    STATUS       current
    DESCRIPTION  "The port number of the Ethernet Service SLA."
    ::= {pvxEServiceSlaCrntPMEntry 5 }


pvxEServiceSlaCrntPMESName OBJECT-TYPE
    SYNTAX       DisplayString
    MAX-ACCESS   not-accessible
    STATUS       current
    DESCRIPTION  "The Ethernet service name."
    ::= { pvxEServiceSlaCrntPMEntry 6 }


pvxEServiceSlaCrntPMRMepId OBJECT-TYPE
    SYNTAX       INTEGER (1..8191)
    MAX-ACCESS   not-accessible
    STATUS       current
    DESCRIPTION  "Remote MEP ID."
    ::= { pvxEServiceSlaCrntPMEntry 7 }
    
pvxEServiceSlaCrntPMIntervalTypeIdx OBJECT-TYPE
    SYNTAX       PMIntervalType
    MAX-ACCESS   not-accessible
    STATUS       current
    DESCRIPTION  "The type of PM bin according to interval length."
    ::= { pvxEServiceSlaCrntPMEntry 8 }

pvxEServiceSlaCrntPMNearEndFrameLoss OBJECT-TYPE
    SYNTAX       FixedX1000
    MAX-ACCESS   read-only
    STATUS       current
    DESCRIPTION  "Indicates near end frame loss ratio value."
    ::= { pvxEServiceSlaCrntPMEntry 9 }

pvxEServiceSlaCrntPMNearEndFrameLossTimeStamp OBJECT-TYPE
    SYNTAX       DateAndTime
    MAX-ACCESS   read-only
    STATUS       current
    DESCRIPTION  "The date and time stamp of the value."
    ::= { pvxEServiceSlaCrntPMEntry 10 }

pvxEServiceSlaCrntPMNearEndFrameLossValidity OBJECT-TYPE
    SYNTAX       PMValidity
    MAX-ACCESS   read-only
    STATUS       current
    DESCRIPTION  "Indicates the validity of the value."
    ::= { pvxEServiceSlaCrntPMEntry 11 }
    
pvxEServiceSlaCrntPMNearEndFrameLossInitialize OBJECT-TYPE
    SYNTAX       InitializeCmd
    MAX-ACCESS   read-write
    STATUS       current
    DESCRIPTION  "Used to initialize the value to 0."
    ::= { pvxEServiceSlaCrntPMEntry 12 }

pvxEServiceSlaCrntPMFarEndFrameLoss OBJECT-TYPE
    SYNTAX       FixedX1000
    MAX-ACCESS   read-only
    STATUS       current
    DESCRIPTION  "Indicates far end frame loss ratio value."
    ::= { pvxEServiceSlaCrntPMEntry 13 }

pvxEServiceSlaCrntPMFarEndFrameLossTimeStamp OBJECT-TYPE
    SYNTAX       DateAndTime
    MAX-ACCESS   read-only
    STATUS       current
    DESCRIPTION  "The date and time stamp of the value."
    ::= { pvxEServiceSlaCrntPMEntry 14 }

pvxEServiceSlaCrntPMFarEndFrameLossValidity OBJECT-TYPE
    SYNTAX       PMValidity
    MAX-ACCESS   read-only
    STATUS       current
    DESCRIPTION  "Indicates the validity of the value."
    ::= { pvxEServiceSlaCrntPMEntry 15 }
    
pvxEServiceSlaCrntPMFarEndFrameLossInitialize OBJECT-TYPE
    SYNTAX       InitializeCmd
    MAX-ACCESS   read-write
    STATUS       current
    DESCRIPTION  "Used to initialize the value to 0."
    ::= { pvxEServiceSlaCrntPMEntry 16 }

pvxEServiceSlaCrntPM2WayDelayMinimum OBJECT-TYPE
    SYNTAX       Unsigned32
    MAX-ACCESS   read-only
    STATUS       current
    DESCRIPTION  "Indicates two way delay minimum value."
    ::= { pvxEServiceSlaCrntPMEntry 17 }

pvxEServiceSlaCrntPM2WayDelayMinimumTimeStamp OBJECT-TYPE
    SYNTAX       DateAndTime
    MAX-ACCESS   read-only
    STATUS       current
    DESCRIPTION  "The date and time stamp of the value."
    ::= { pvxEServiceSlaCrntPMEntry 18 }

pvxEServiceSlaCrntPM2WayDelayMinimumValidity OBJECT-TYPE
    SYNTAX       PMValidity
    MAX-ACCESS   read-only
    STATUS       current
    DESCRIPTION  "Indicates the validity of the value."
    ::= { pvxEServiceSlaCrntPMEntry 19 }
    
pvxEServiceSlaCrntPM2WayDelayMinimumInitialize OBJECT-TYPE
    SYNTAX       InitializeCmd
    MAX-ACCESS   read-write
    STATUS       current
    DESCRIPTION  "Used to initialize the value to 0."
    ::= { pvxEServiceSlaCrntPMEntry 21 } 
    
pvxEServiceSlaCrntPM2WayDelayMaximum OBJECT-TYPE
    SYNTAX       Unsigned32
    MAX-ACCESS   read-only
    STATUS       current
    DESCRIPTION  "Indicates two way delay maximum value."
    ::= { pvxEServiceSlaCrntPMEntry 22 }

pvxEServiceSlaCrntPM2WayDelayMaximumTimeStamp OBJECT-TYPE
    SYNTAX       DateAndTime
    MAX-ACCESS   read-only
    STATUS       current
    DESCRIPTION  "The date and time stamp of the value."
    ::= { pvxEServiceSlaCrntPMEntry 23 }

pvxEServiceSlaCrntPM2WayDelayMaximumValidity OBJECT-TYPE
    SYNTAX       PMValidity
    MAX-ACCESS   read-only
    STATUS       current
    DESCRIPTION  "Indicates the validity of the value."
    ::= { pvxEServiceSlaCrntPMEntry 24 }
    
pvxEServiceSlaCrntPM2WayDelayMaximumInitialize OBJECT-TYPE
    SYNTAX       InitializeCmd
    MAX-ACCESS   read-write
    STATUS       current
    DESCRIPTION  "Used to initialize the value to 0."
    ::= { pvxEServiceSlaCrntPMEntry 25 }
    
pvxEServiceSlaCrntPM2WayDelayAverage OBJECT-TYPE
    SYNTAX       Unsigned32
    MAX-ACCESS   read-only
    STATUS       current
    DESCRIPTION  "Indicates two way delay average value."
    ::= { pvxEServiceSlaCrntPMEntry 26 }

pvxEServiceSlaCrntPM2WayDelayAverageTimeStamp OBJECT-TYPE
    SYNTAX       DateAndTime
    MAX-ACCESS   read-only
    STATUS       current
    DESCRIPTION  "The date and time stamp of the value."
    ::= { pvxEServiceSlaCrntPMEntry 27 }

pvxEServiceSlaCrntPM2WayDelayAverageValidity OBJECT-TYPE
    SYNTAX       PMValidity
    MAX-ACCESS   read-only
    STATUS       current
    DESCRIPTION  "Indicates the validity of the value."
    ::= { pvxEServiceSlaCrntPMEntry 28 }
    
pvxEServiceSlaCrntPM2WayDelayAverageInitialize OBJECT-TYPE
    SYNTAX       InitializeCmd
    MAX-ACCESS   read-write
    STATUS       current
    DESCRIPTION  "Used to initialize the value to 0."
    ::= { pvxEServiceSlaCrntPMEntry 29 }
    
pvxEServiceSlaCrntPM2WayDelayVariationMinimum OBJECT-TYPE
    SYNTAX       Unsigned32
    MAX-ACCESS   read-only
    STATUS       current
    DESCRIPTION  "Indicates two way delay Variation Minimum value."
    ::= { pvxEServiceSlaCrntPMEntry 30 }

pvxEServiceSlaCrntPM2WayDelayVariationMinimumTimeStamp OBJECT-TYPE
    SYNTAX       DateAndTime
    MAX-ACCESS   read-only
    STATUS       current
    DESCRIPTION  "The date and time stamp of the value."
    ::= { pvxEServiceSlaCrntPMEntry 31 }

pvxEServiceSlaCrntPM2WayDelayVariationMinimumValidity OBJECT-TYPE
    SYNTAX       PMValidity
    MAX-ACCESS   read-only
    STATUS       current
    DESCRIPTION  "Indicates the validity of the value."
    ::= { pvxEServiceSlaCrntPMEntry 32 }
    
pvxEServiceSlaCrntPM2WayDelayVariationMinimumInitialize OBJECT-TYPE
    SYNTAX       InitializeCmd
    MAX-ACCESS   read-write
    STATUS       current
    DESCRIPTION  "Used to initialize the value to 0."
    ::= { pvxEServiceSlaCrntPMEntry 33 }
 
pvxEServiceSlaCrntPM2WayDelayVariationMaximum OBJECT-TYPE
    SYNTAX       Unsigned32
    MAX-ACCESS   read-only
    STATUS       current
    DESCRIPTION  "Indicates two way delay Variation Maximum value."
    ::= { pvxEServiceSlaCrntPMEntry 34 }

pvxEServiceSlaCrntPM2WayDelayVariationMaximumTimeStamp OBJECT-TYPE
    SYNTAX       DateAndTime
    MAX-ACCESS   read-only
    STATUS       current
    DESCRIPTION  "The date and time stamp of the value."
    ::= { pvxEServiceSlaCrntPMEntry 35 }

pvxEServiceSlaCrntPM2WayDelayVariationMaximumValidity OBJECT-TYPE
    SYNTAX       PMValidity
    MAX-ACCESS   read-only
    STATUS       current
    DESCRIPTION  "Indicates the validity of the value."
    ::= { pvxEServiceSlaCrntPMEntry 36 }
    
pvxEServiceSlaCrntPM2WayDelayVariationMaximumInitialize OBJECT-TYPE
    SYNTAX       InitializeCmd
    MAX-ACCESS   read-write
    STATUS       current
    DESCRIPTION  "Used to initialize the value to 0."
    ::= { pvxEServiceSlaCrntPMEntry 37 } 
    
pvxEServiceSlaCrntPM2WayDelayVariationAverage OBJECT-TYPE
    SYNTAX       Unsigned32
    MAX-ACCESS   read-only
    STATUS       current
    DESCRIPTION  "Indicates two way delay Variation Minimum value."
    ::= { pvxEServiceSlaCrntPMEntry 38 }

pvxEServiceSlaCrntPM2WayDelayVariationAverageTimeStamp OBJECT-TYPE
    SYNTAX       DateAndTime
    MAX-ACCESS   read-only
    STATUS       current
    DESCRIPTION  "The date and time stamp of the value."
    ::= { pvxEServiceSlaCrntPMEntry 39 }

pvxEServiceSlaCrntPM2WayDelayVariationAverageValidity OBJECT-TYPE
    SYNTAX       PMValidity
    MAX-ACCESS   read-only
    STATUS       current
    DESCRIPTION  "Indicates the validity of the value."
    ::= { pvxEServiceSlaCrntPMEntry 40 }
    
pvxEServiceSlaCrntPM2WayDelayVariationAverageInitialize OBJECT-TYPE
    SYNTAX       InitializeCmd
    MAX-ACCESS   read-write
    STATUS       current
    DESCRIPTION  "Used to initialize the value to 0."
    ::= { pvxEServiceSlaCrntPMEntry 41 }  
    

-----------------------------------------------------------------------
-- Objects used to retrieve historical Performance Monitoring
-- statistics for PacketVX Ethernet Service SLA PM History Objects
-----------------------------------------------------------------------

pvxEServiceSlaHistPMTable OBJECT-TYPE
    SYNTAX       SEQUENCE OF PvxEServiceSlaHistPMEntry
    MAX-ACCESS   not-accessible
    STATUS       current
    DESCRIPTION  "A table of historical performance monitoring statistics collected
                  for PacketVX ERPS Port and ERPS Instance Port objects."
    ::= { performance 48 }


pvxEServiceSlaHistPMEntry OBJECT-TYPE
    SYNTAX       PvxEServiceSlaHistPMEntry
    MAX-ACCESS   not-accessible
    STATUS       current
    DESCRIPTION  "The row entry object of the PacketVX Ethernet Service SLA historical
                  performance monitoring table. Each row of this table contains
                  a full set of PM statistics and related data for an historical
                  measurement interval for a given PVX Ethernet Service's SLA."
    INDEX        { pvxEServiceSlaHistPMSwitchIdx,
				   pvxEServiceSlaHistPMShelfIdx,
				   pvxEServiceSlaHistPMSlotIdx,
               	   pvxEServiceSlaHistPMPortTypeIdx,
    			   pvxEServiceSlaHistPMPortIdx,
    			   pvxEServiceSlaHistPMESName,
                   pvxEServiceSlaHistPMRMepId,
                   pvxEServiceSlaHistPMIntervalTypeIdx,
                   pvxEServiceSlaHistPMIntervalIdx }
    ::= { pvxEServiceSlaHistPMTable 1 }


PvxEServiceSlaHistPMEntry ::= SEQUENCE { pvxEServiceSlaHistPMSwitchIdx                      INTEGER,
                                         pvxEServiceSlaHistPMShelfIdx                       INTEGER,
                                         pvxEServiceSlaHistPMSlotIdx                        INTEGER,
                                         pvxEServiceSlaHistPMPortTypeIdx                    PvxPortType,
                                         pvxEServiceSlaHistPMPortIdx                        INTEGER,
                                         pvxEServiceSlaHistPMESName                         DisplayString,
                                         pvxEServiceSlaHistPMRMepId                         INTEGER,
                                         pvxEServiceSlaHistPMIntervalTypeIdx                PMIntervalType,
                                         pvxEServiceSlaHistPMIntervalIdx                    INTEGER,
                                         pvxEServiceSlaHistPMNearEndFrameLoss               FixedX1000,
                                         pvxEServiceSlaHistPMNearEndFrameLossTimeStamp      DateAndTime,
                                         pvxEServiceSlaHistPMNearEndFrameLossValidity       PMValidity,
                                         pvxEServiceSlaHistPMNearEndFrameLossInitialize     InitializeCmd,
                                         pvxEServiceSlaHistPMFarEndFrameLoss                FixedX1000,
                                         pvxEServiceSlaHistPMFarEndFrameLossTimeStamp       DateAndTime,
                                         pvxEServiceSlaHistPMFarEndFrameLossValidity        PMValidity,
                                         pvxEServiceSlaHistPMFarEndFrameLossInitialize      InitializeCmd,
                                         pvxEServiceSlaHistPM2WayDelayMinimum               Unsigned32,
                                         pvxEServiceSlaHistPM2WayDelayMinimumTimeStamp      DateAndTime,
                                         pvxEServiceSlaHistPM2WayDelayMinimumValidity       PMValidity,
                                         pvxEServiceSlaHistPM2WayDelayMinimumInitialize     InitializeCmd,
                                         pvxEServiceSlaHistPM2WayDelayMaximum               Unsigned32,
                                         pvxEServiceSlaHistPM2WayDelayMaximumTimeStamp      DateAndTime,
                                         pvxEServiceSlaHistPM2WayDelayMaximumValidity       PMValidity,
                                         pvxEServiceSlaHistPM2WayDelayMaximumInitialize     InitializeCmd,
                                         pvxEServiceSlaHistPM2WayDelayAverage               Unsigned32,
                                         pvxEServiceSlaHistPM2WayDelayAverageTimeStamp      DateAndTime,
                                         pvxEServiceSlaHistPM2WayDelayAverageValidity       PMValidity,
                                         pvxEServiceSlaHistPM2WayDelayAverageInitialize     InitializeCmd,
                                         pvxEServiceSlaHistPM2WayDelayVariationMinimum      Unsigned32,
                                         pvxEServiceSlaHistPM2WayDelayVariationMinimumTimeStamp         DateAndTime,
                                         pvxEServiceSlaHistPM2WayDelayVariationMinimumValidity          PMValidity,
                                         pvxEServiceSlaHistPM2WayDelayVariationMinimumInitialize        InitializeCmd,
                                         pvxEServiceSlaHistPM2WayDelayVariationMaximum                  Unsigned32,
                                         pvxEServiceSlaHistPM2WayDelayVariationMaximumTimeStamp         DateAndTime,
                                         pvxEServiceSlaHistPM2WayDelayVariationMaximumValidity          PMValidity,
                                         pvxEServiceSlaHistPM2WayDelayVariationMaximumInitialize        InitializeCmd,
                                         pvxEServiceSlaHistPM2WayDelayVariationAverage                  Unsigned32,
                                         pvxEServiceSlaHistPM2WayDelayVariationAverageTimeStamp         DateAndTime,
                                         pvxEServiceSlaHistPM2WayDelayVariationAverageValidity          PMValidity,
                                         pvxEServiceSlaHistPM2WayDelayVariationAverageInitialize        InitializeCmd }

                                  
pvxEServiceSlaHistPMSwitchIdx OBJECT-TYPE
   	SYNTAX       INTEGER(1..11)
   	MAX-ACCESS   not-accessible
   	STATUS       current
    DESCRIPTION  "The identifier of the ethernet switch instance on which the
                  Ethernet Service SLA is provisioned."
    ::= {pvxEServiceSlaHistPMEntry 1 }


pvxEServiceSlaHistPMShelfIdx OBJECT-TYPE
    SYNTAX       INTEGER (0|1|11|21|31)
    MAX-ACCESS   not-accessible
    STATUS       current
    DESCRIPTION  "The number of the shelf on which the Ethernet Service SLA targeted
                  for PMs is provisioned. For LAG entities, the shelf number is 0."
    ::= {pvxEServiceSlaHistPMEntry 2 }


pvxEServiceSlaHistPMSlotIdx OBJECT-TYPE
    SYNTAX       INTEGER (0|1|3|5|7|9|11|13|15|17|19)
    MAX-ACCESS   not-accessible
    STATUS       current
    DESCRIPTION  "The number of the slot within which the Ethernet Service SLA targeted
                  for PMs is provisioned. For LAG entities, the slot number is 0."
    ::= {pvxEServiceSlaHistPMEntry 3 }


pvxEServiceSlaHistPMPortTypeIdx OBJECT-TYPE
    SYNTAX       PvxPortType
    MAX-ACCESS   not-accessible
    STATUS       current
    DESCRIPTION  "The type of PacketVX port on which the Ethernet Service SLA
                  facility is provisioned."
    ::= {pvxEServiceSlaHistPMEntry 4 }


pvxEServiceSlaHistPMPortIdx OBJECT-TYPE
    SYNTAX       INTEGER (0..64)
    MAX-ACCESS   not-accessible
    STATUS       current
    DESCRIPTION  "The port number of the Ethernet Service SLA."
    ::= {pvxEServiceSlaHistPMEntry 5 }


pvxEServiceSlaHistPMESName OBJECT-TYPE
    SYNTAX       DisplayString
    MAX-ACCESS   not-accessible
    STATUS       current
    DESCRIPTION  "The Ethernet service name."
    ::= { pvxEServiceSlaHistPMEntry 6 }


pvxEServiceSlaHistPMRMepId OBJECT-TYPE
    SYNTAX       INTEGER (1..8191)
    MAX-ACCESS   not-accessible
    STATUS       current
    DESCRIPTION  "Remote MEP ID."
    ::= { pvxEServiceSlaHistPMEntry 7 }
    
pvxEServiceSlaHistPMIntervalTypeIdx OBJECT-TYPE
    SYNTAX       PMIntervalType
    MAX-ACCESS   not-accessible
    STATUS       current
    DESCRIPTION  "The type of PM bin according to interval length."
    ::= { pvxEServiceSlaHistPMEntry 8 }

pvxEServiceSlaHistPMIntervalIdx OBJECT-TYPE
    SYNTAX       INTEGER (1..96)
    MAX-ACCESS   not-accessible
    STATUS       current
    DESCRIPTION  "The specific PM bin number. The range is 1 to 96 for the
                  15-minute historical bins. For the 1-day historical bin, the
                  value is 1."
    ::= { pvxEServiceSlaHistPMEntry 9 }

pvxEServiceSlaHistPMNearEndFrameLoss OBJECT-TYPE
    SYNTAX       FixedX1000
    MAX-ACCESS   read-only
    STATUS       current
    DESCRIPTION  "Indicates near end frame loss ratio value."
    ::= { pvxEServiceSlaHistPMEntry 10 }

pvxEServiceSlaHistPMNearEndFrameLossTimeStamp OBJECT-TYPE
    SYNTAX       DateAndTime
    MAX-ACCESS   read-only
    STATUS       current
    DESCRIPTION  "The date and time stamp of the value."
    ::= { pvxEServiceSlaHistPMEntry 11 }

pvxEServiceSlaHistPMNearEndFrameLossValidity OBJECT-TYPE
    SYNTAX       PMValidity
    MAX-ACCESS   read-only
    STATUS       current
    DESCRIPTION  "Indicates the validity of the value."
    ::= { pvxEServiceSlaHistPMEntry 12 }
    
pvxEServiceSlaHistPMNearEndFrameLossInitialize OBJECT-TYPE
    SYNTAX       InitializeCmd
    MAX-ACCESS   read-write
    STATUS       current
    DESCRIPTION  "Used to initialize the value to 0."
    ::= { pvxEServiceSlaHistPMEntry 13 }

pvxEServiceSlaHistPMFarEndFrameLoss OBJECT-TYPE
    SYNTAX       FixedX1000
    MAX-ACCESS   read-only
    STATUS       current
    DESCRIPTION  "Indicates far end frame loss ratio value."
    ::= { pvxEServiceSlaHistPMEntry 14 }

pvxEServiceSlaHistPMFarEndFrameLossTimeStamp OBJECT-TYPE
    SYNTAX       DateAndTime
    MAX-ACCESS   read-only
    STATUS       current
    DESCRIPTION  "The date and time stamp of the value."
    ::= { pvxEServiceSlaHistPMEntry 15 }

pvxEServiceSlaHistPMFarEndFrameLossValidity OBJECT-TYPE
    SYNTAX       PMValidity
    MAX-ACCESS   read-only
    STATUS       current
    DESCRIPTION  "Indicates the validity of the value."
    ::= { pvxEServiceSlaHistPMEntry 16 }
    
pvxEServiceSlaHistPMFarEndFrameLossInitialize OBJECT-TYPE
    SYNTAX       InitializeCmd
    MAX-ACCESS   read-write
    STATUS       current
    DESCRIPTION  "Used to initialize the value to 0."
    ::= { pvxEServiceSlaHistPMEntry 17 }

pvxEServiceSlaHistPM2WayDelayMinimum OBJECT-TYPE
    SYNTAX       Unsigned32
    MAX-ACCESS   read-only
    STATUS       current
    DESCRIPTION  "Indicates two way delay minimum value."
    ::= { pvxEServiceSlaHistPMEntry 18 }

pvxEServiceSlaHistPM2WayDelayMinimumTimeStamp OBJECT-TYPE
    SYNTAX       DateAndTime
    MAX-ACCESS   read-only
    STATUS       current
    DESCRIPTION  "The date and time stamp of the value."
    ::= { pvxEServiceSlaHistPMEntry 19 }

pvxEServiceSlaHistPM2WayDelayMinimumValidity OBJECT-TYPE
    SYNTAX       PMValidity
    MAX-ACCESS   read-only
    STATUS       current
    DESCRIPTION  "Indicates the validity of the value."
    ::= { pvxEServiceSlaHistPMEntry 20 }
    
pvxEServiceSlaHistPM2WayDelayMinimumInitialize OBJECT-TYPE
    SYNTAX       InitializeCmd
    MAX-ACCESS   read-write
    STATUS       current
    DESCRIPTION  "Used to initialize the value to 0."
    ::= { pvxEServiceSlaHistPMEntry 21 } 
    
pvxEServiceSlaHistPM2WayDelayMaximum OBJECT-TYPE
    SYNTAX       Unsigned32
    MAX-ACCESS   read-only
    STATUS       current
    DESCRIPTION  "Indicates two way delay maximum value."
    ::= { pvxEServiceSlaHistPMEntry 22 }

pvxEServiceSlaHistPM2WayDelayMaximumTimeStamp OBJECT-TYPE
    SYNTAX       DateAndTime
    MAX-ACCESS   read-only
    STATUS       current
    DESCRIPTION  "The date and time stamp of the value."
    ::= { pvxEServiceSlaHistPMEntry 23 }

pvxEServiceSlaHistPM2WayDelayMaximumValidity OBJECT-TYPE
    SYNTAX       PMValidity
    MAX-ACCESS   read-only
    STATUS       current
    DESCRIPTION  "Indicates the validity of the value."
    ::= { pvxEServiceSlaHistPMEntry 24 }
    
pvxEServiceSlaHistPM2WayDelayMaximumInitialize OBJECT-TYPE
    SYNTAX       InitializeCmd
    MAX-ACCESS   read-write
    STATUS       current
    DESCRIPTION  "Used to initialize the value to 0."
    ::= { pvxEServiceSlaHistPMEntry 25 }
    
pvxEServiceSlaHistPM2WayDelayAverage OBJECT-TYPE
    SYNTAX       Unsigned32
    MAX-ACCESS   read-only
    STATUS       current
    DESCRIPTION  "Indicates two way delay average value."
    ::= { pvxEServiceSlaHistPMEntry 26 }

pvxEServiceSlaHistPM2WayDelayAverageTimeStamp OBJECT-TYPE
    SYNTAX       DateAndTime
    MAX-ACCESS   read-only
    STATUS       current
    DESCRIPTION  "The date and time stamp of the value."
    ::= { pvxEServiceSlaHistPMEntry 27 }

pvxEServiceSlaHistPM2WayDelayAverageValidity OBJECT-TYPE
    SYNTAX       PMValidity
    MAX-ACCESS   read-only
    STATUS       current
    DESCRIPTION  "Indicates the validity of the value."
    ::= { pvxEServiceSlaHistPMEntry 28 }
    
pvxEServiceSlaHistPM2WayDelayAverageInitialize OBJECT-TYPE
    SYNTAX       InitializeCmd
    MAX-ACCESS   read-write
    STATUS       current
    DESCRIPTION  "Used to initialize the value to 0."
    ::= { pvxEServiceSlaHistPMEntry 29 }
    
pvxEServiceSlaHistPM2WayDelayVariationMinimum OBJECT-TYPE
    SYNTAX       Unsigned32
    MAX-ACCESS   read-only
    STATUS       current
    DESCRIPTION  "Indicates two way delay Variation Minimum value."
    ::= { pvxEServiceSlaHistPMEntry 30 }

pvxEServiceSlaHistPM2WayDelayVariationMinimumTimeStamp OBJECT-TYPE
    SYNTAX       DateAndTime
    MAX-ACCESS   read-only
    STATUS       current
    DESCRIPTION  "The date and time stamp of the value."
    ::= { pvxEServiceSlaHistPMEntry 31 }

pvxEServiceSlaHistPM2WayDelayVariationMinimumValidity OBJECT-TYPE
    SYNTAX       PMValidity
    MAX-ACCESS   read-only
    STATUS       current
    DESCRIPTION  "Indicates the validity of the value."
    ::= { pvxEServiceSlaHistPMEntry 32 }
    
pvxEServiceSlaHistPM2WayDelayVariationMinimumInitialize OBJECT-TYPE
    SYNTAX       InitializeCmd
    MAX-ACCESS   read-write
    STATUS       current
    DESCRIPTION  "Used to initialize the value to 0."
    ::= { pvxEServiceSlaHistPMEntry 33 }
 
pvxEServiceSlaHistPM2WayDelayVariationMaximum OBJECT-TYPE
    SYNTAX       Unsigned32
    MAX-ACCESS   read-only
    STATUS       current
    DESCRIPTION  "Indicates two way delay Variation Maximum value."
    ::= { pvxEServiceSlaHistPMEntry 34 }

pvxEServiceSlaHistPM2WayDelayVariationMaximumTimeStamp OBJECT-TYPE
    SYNTAX       DateAndTime
    MAX-ACCESS   read-only
    STATUS       current
    DESCRIPTION  "The date and time stamp of the value."
    ::= { pvxEServiceSlaHistPMEntry 35 }

pvxEServiceSlaHistPM2WayDelayVariationMaximumValidity OBJECT-TYPE
    SYNTAX       PMValidity
    MAX-ACCESS   read-only
    STATUS       current
    DESCRIPTION  "Indicates the validity of the value."
    ::= { pvxEServiceSlaHistPMEntry 36 }
    
pvxEServiceSlaHistPM2WayDelayVariationMaximumInitialize OBJECT-TYPE
    SYNTAX       InitializeCmd
    MAX-ACCESS   read-write
    STATUS       current
    DESCRIPTION  "Used to initialize the value to 0."
    ::= { pvxEServiceSlaHistPMEntry 37 } 
    
pvxEServiceSlaHistPM2WayDelayVariationAverage OBJECT-TYPE
    SYNTAX       Unsigned32
    MAX-ACCESS   read-only
    STATUS       current
    DESCRIPTION  "Indicates two way delay Variation Minimum value."
    ::= { pvxEServiceSlaHistPMEntry 38 }

pvxEServiceSlaHistPM2WayDelayVariationAverageTimeStamp OBJECT-TYPE
    SYNTAX       DateAndTime
    MAX-ACCESS   read-only
    STATUS       current
    DESCRIPTION  "The date and time stamp of the value."
    ::= { pvxEServiceSlaHistPMEntry 39 }

pvxEServiceSlaHistPM2WayDelayVariationAverageValidity OBJECT-TYPE
    SYNTAX       PMValidity
    MAX-ACCESS   read-only
    STATUS       current
    DESCRIPTION  "Indicates the validity of the value."
    ::= { pvxEServiceSlaHistPMEntry 40 }
    
pvxEServiceSlaHistPM2WayDelayVariationAverageInitialize OBJECT-TYPE
    SYNTAX       InitializeCmd
    MAX-ACCESS   read-write
    STATUS       current
    DESCRIPTION  "Used to initialize the value to 0."
    ::= { pvxEServiceSlaHistPMEntry 41 }  

                                  
--------------------------------------
-- MSTP Notification Objects 
--------------------------------------
mstpGlobalErrType OBJECT-TYPE
       SYNTAX   INTEGER   {
                    memfail (1),
                    bufffail (2)
                    }
       MAX-ACCESS  accessible-for-notify
       STATUS  current
       DESCRIPTION  "Used within the Trap Notification PDU. 
	                 It returns the following values
                         memfail - memory allocation failure
                         bufffail - buffer allocation failure"
   ::= { mstpNotificationObjects 1 }

mstpGeneralEvtType OBJECT-TYPE
       SYNTAX   INTEGER   {
                    up (1),
                    down (2)
                    }
       MAX-ACCESS  accessible-for-notify
       STATUS  current
       DESCRIPTION "Used within the Trap Notification PDU. 
	                It returns the following values
                    up - protocol up
                    down - protocol down"
   ::= { mstpNotificationObjects 2 } 
   
mstpProtocolMigrationType  OBJECT-TYPE
       SYNTAX   INTEGER   {
                    sendstp(1),
                    sendrstp(2)
                    }
       MAX-ACCESS  accessible-for-notify
       STATUS  current
       DESCRIPTION "Used within the Trap Notification PDU. 
	                Port protocol migration type occured in the port."
   ::= { mstpNotificationObjects 3 } 
   
mstpPacketErrType OBJECT-TYPE
       SYNTAX   INTEGER   {
                protocolIdErr(1), 
		        invalidBpdu(2), 
		        configLengthErr(3), 
		        tcnLengthErr(4), 
		        rstpLengthErr(5), 
		        maxAgeErr(6), 
		        fwdDelayErr(7), 
		        helloTimeErr(8), 
		        mstpLengthErr(9)
                    }
       MAX-ACCESS  accessible-for-notify
       STATUS  current
       DESCRIPTION  "Used within the Trap Notification PDU. 
	               Type of invalid packet received in each of the port"
   ::= { mstpNotificationObjects 4 }
   
mstpPacketErrValue OBJECT-TYPE
       SYNTAX   Integer32
       MAX-ACCESS  accessible-for-notify
       STATUS  current
       DESCRIPTION "Used within the Trap Notification PDU. 
	           Packet error value corresponding to the above type."
   ::= { mstpNotificationObjects 5 }
                 
-----------------------------------------------------------------------
-- MSTP Alarm 
-----------------------------------------------------------------------
resourceUnavailableCond NOTIFICATION-TYPE
    OBJECTS      { pvxMSTPGenSwitchIdx,
                   pvxMSTPXstBrdgId,
                   mstpGlobalErrType,
                   condReportType,
                   condDateAndTime,
                   condSeverity,
                   condServiceAffecting,
                   trapSeqNum,
                   condObjectType,
                   condCodeType }
    STATUS       current
    DESCRIPTION  "Generated when any of the error events like memory failure or buffer failure occurs."
    ::= {mstpCondNotifications 0 1 }

resourceUnavailableClear NOTIFICATION-TYPE
    OBJECTS      { pvxMSTPGenSwitchIdx,
                   pvxMSTPXstBrdgId,
                   mstpGlobalErrType,
                   condReportType,
                   condDateAndTime,
                   condSeverity,
                   condServiceAffecting,
                   trapSeqNum,
                   condObjectType,
                   condCodeType }
    STATUS       current
    DESCRIPTION  "Generated when any of the error events like memory failure or buffer failure clears."
    ::= {mstpCondNotifications 0 2 }


-----------------------------------------------------------------------
-- SwitchMember stacking port down Alarm ----  
-----------------------------------------------------------------------
switchMemberStkPortDownCond NOTIFICATION-TYPE
    OBJECTS      { pvxSwitchIdx,
                   pvxSwitchMemberIdx,
                   condReportType,
                   condDateAndTime,
                   condSeverity,
                   condServiceAffecting,
                   trapSeqNum,
                   condObjectType,
                   condCodeType }
    STATUS       current
    DESCRIPTION  "Generated when a switch member stacking port is down."
    ::= {swMemberCondNotifications 0 1 }

switchMemberStkPortDownClear NOTIFICATION-TYPE
    OBJECTS      { pvxSwitchIdx,
                   pvxSwitchMemberIdx,
                   condReportType,
                   condDateAndTime,
                   condSeverity,
                   condServiceAffecting,
                   trapSeqNum,
                   condObjectType,
                   condCodeType }
    STATUS       current
    DESCRIPTION  "Generated when a switch member stacking port comes in service."
    ::= {swMemberCondNotifications 0 2 }


    
-----------------------------------------------------------------------
-- MSTP Events
-----------------------------------------------------------------------
mstpProtocolGeneralEvt NOTIFICATION-TYPE
    OBJECTS      { pvxMSTPGenSwitchIdx,
                   pvxMSTPXstBrdgId,
                   mstpGeneralEvtType,
                   evtDateAndTime,                 
                   trapSeqNum,
                   evtDescription,
                   evtObjectType,
                   evtCodeType }
    STATUS       current
    DESCRIPTION  "Generated when any of the general events like protocol up or protocol down occurs."
    ::= {mstpEvtNotifications 0 1 }

mstpNewRootEvt NOTIFICATION-TYPE
    OBJECTS      { pvxMSTPGenSwitchIdx,
                   pvxMSTPXstBrdgId,
                   pvxMSTPXstBrdgRegRoot,
                   evtDateAndTime,                 
                   trapSeqNum,
                   evtDescription,
                   evtObjectType,
                   evtCodeType }
    STATUS       current
    DESCRIPTION  "Generated whenever a new root bridge is selected in the topology."
    ::= {mstpEvtNotifications 0 2 }
    
mstpTopologyChangeEvt NOTIFICATION-TYPE
    OBJECTS      { pvxMSTPGenSwitchIdx,
                   pvxMSTPXstBrdgId,                  
                   evtDateAndTime,                 
                   trapSeqNum,
                   evtDescription,
                   evtObjectType,
                   evtCodeType }
    STATUS       current
    DESCRIPTION  "Generated when topology change is detected"
    ::= {mstpEvtNotifications 0 3 }
    
mstpProtocolMigrationEvt NOTIFICATION-TYPE
    OBJECTS      { pvxMSTPGenSwitchIdx,
                   pvxMSTPXstBrdgId,
                   pvxMSTPGenVersionSupported,
                   mstpProtocolMigrationType,
                   evtDateAndTime,                 
                   trapSeqNum,
                   evtDescription,
                   evtObjectType,
                   evtCodeType }
    STATUS       current
    DESCRIPTION  "Generated when port protocol migration happens in the port."
    ::= {mstpEvtNotifications 0 4}

mstpInvalidPacketRcvdEvt NOTIFICATION-TYPE
    OBJECTS      { pvxMSTPGenSwitchIdx,
                   pvxMSTPXstBrdgId,
                   mstpPacketErrType,
                   mstpPacketErrValue,
                   evtDateAndTime,                 
                   trapSeqNum,
                   evtDescription,
                   evtObjectType,
                   evtCodeType }
    STATUS       current
    DESCRIPTION  "Generated when port protocol migration happens in the port."
    ::= {mstpEvtNotifications 0 5}
    
mstpRegionConfigChangeEvt NOTIFICATION-TYPE
    OBJECTS      { pvxMSTPGenSwitchIdx,
                   pvxMSTPXstBrdgId,
                   pvxMSTPGenIdFmtSel,
                   pvxMSTPGenIdName,
                   pvxMSTPGenIdRevisionLevel,
                   pvxMSTPGenIdDigest,
                   evtDateAndTime,                 
                   trapSeqNum,
                   evtDescription,
                   evtObjectType,
                   evtCodeType }
    STATUS       current
    DESCRIPTION  " Generated when the MST region�s configuration identifier changes."
    ::= {mstpEvtNotifications 0 6}

mstpRoleChangeEvt NOTIFICATION-TYPE
    OBJECTS      { pvxMSTPGenSwitchIdx,
                   pvxMSTPXstBrdgId,
                   pvxMSTPPortRole,                   
                   evtDateAndTime,                 
                   trapSeqNum,
                   evtDescription,
                   evtObjectType,
                   evtCodeType }
    STATUS       current
    DESCRIPTION  " Generated whenever a new role is selected for the port."
    ::= {mstpEvtNotifications 0 7}

--------------------------------------
-- LAG alarms 
--------------------------------------
lagLinkDownCond NOTIFICATION-TYPE
    OBJECTS      { pvxLGSwitchIdx,
                   pvxLGIdx,
                   condReportType,
                   condDateAndTime,
                   condSeverity,
                   condServiceAffecting,
                   trapSeqNum,
                   condDescription,
                   condObjectType,
                   condCodeType }
    STATUS       current
    DESCRIPTION  "PVX LAG link down."
    ::= { lagCondNotifications 0 1 }
    
lagLinkDownClear NOTIFICATION-TYPE
    OBJECTS      { pvxLGSwitchIdx,
                   pvxLGIdx,
                   condReportType,
                   condDateAndTime,
                   condSeverity,
                   condServiceAffecting,
                   trapSeqNum,
                   condDescription,
                   condObjectType,
                   condCodeType }
    STATUS       current
    DESCRIPTION  "PVX LAG link down has cleared."
    ::= { lagCondNotifications 0 2 }
    
-----------------------------------------------------------------------
-- PVX Ethernet Service Bandwidth Profile Events
-----------------------------------------------------------------------


pvxESrvcBWPrflBDWUtlzTcaEvt NOTIFICATION-TYPE
    OBJECTS      { pvxESrvcBWPrflCrntPMSwitchIdx,
                   pvxESrvcBWPrflCrntPMShelfIdx,
                   pvxESrvcBWPrflCrntPMSlotIdx,
                   pvxESrvcBWPrflCrntPMPortTypeIdx,
                   pvxESrvcBWPrflCrntPMPortIdx,
    			   pvxESrvcBWPrflCrntPMESrvcNameIdx,
    			   pvxESrvcBWPrflCrntPMPlcyNameIdx,
    			   pvxESrvcBWPrflCrntPMClsMapNameIdx,
    			   pvxESrvcBWPrflCrntPMDirectionIdx,
    			   pvxESrvcBWPrflCrntPMIntervalTypeIdx,
    			   pvxESrvcBWPrflCrntPMBDWUtlzValue,
    			   pvxESrvcBWPrflPMThresholdLevelTypeIdx,
    			   pvxESrvcBWPrflPMThresholdBDWUtlzValue,
                   tcaDateAndTime,
                   evtDateAndTime,
                   trapSeqNum,
                   evtDescription,
                   evtObjectType,
                   evtCodeType }
    STATUS       current
    DESCRIPTION  "This trap provides a threshold crossing alert when the
    			  bandwidth utilization rate of a perEVC or perCoS
                  instance exceeds a configured threshold."
    ::= { pvxESrvcBWPrflEvtNotifications 0 1 }


pvxSlaMeasurementTcaEvt NOTIFICATION-TYPE
    OBJECTS      { pvxEServiceSlaCrntPMSwitchIdx,
                   pvxEServiceSlaCrntPMShelfIdx,
                   pvxEServiceSlaCrntPMSlotIdx,
                   pvxEServiceSlaCrntPMPortTypeIdx,
                   pvxEServiceSlaCrntPMPortIdx,
    			   pvxEServiceSlaCrntPMESName,
    			   pvxEServiceSlaCrntPMRMepId,   			   
    			   pvxEServiceSlaCrntPMIntervalTypeIdx,
                   tcaDateAndTime,
                   tcaMontype,
                   tcaValue,
                   tcaThreshold,
                   evtDateAndTime,
                   trapSeqNum,
                   evtDescription,
                   evtObjectType,
                   evtCodeType }
    STATUS       current
    DESCRIPTION  "This trap provides a threshold crossing alert for a
                  performance monitoring statistic for the PVX SLA measurement."
    ::= { pvxSlaMsmtEvtNotifications 0 1 }

-----------------------------------------------------------------------
-- PVX Ethernet Service Events
-----------------------------------------------------------------------

pvxESrvcOperStateChangeEvt NOTIFICATION-TYPE
    OBJECTS      { pvxEthSrvcSwitchIdx,
                   pvxEthSrvcName,
                   pvxEthSrvcOperState, 
                   pvxEcfmMepDefects,
                   pvxEcfmMepY1731DefectConditions,     
                   pvxEthSrvcExceedMaxUNI,                 
                   evtDateAndTime,
                   trapSeqNum,
                   evtDescription,
                   evtObjectType,
                   evtCodeType }
    STATUS       current
    DESCRIPTION  "This trap provides an ethernet service operational state change
                  alert."
    ::= { pvxESrvcEvtNotifications 0 1 }


-----------------------------------------------------------------------
-- PVX ERPS Service Events
-----------------------------------------------------------------------

pvxERPSSrvcNNIProtectionSwitchChangeEvent NOTIFICATION-TYPE
    OBJECTS      { pvxERPSSrvcNNISwitchId,
                   pvxERPSSrvcNNIShelfId,
                   pvxERPSSrvcNNISlotId,
                   pvxERPSSrvcNNIPortTypeId,
                   pvxERPSSrvcNNIPortId,
                   pvxERPSSrvcNNISrvcName,
                   pvxERPSSrvcProtectionSwitchMode,
                   pvxERPSSrvcNNIProtectionSwitch,
                   pvxERPSSrvcNNIRingPortStatus,
                   evtDateAndTime,
                   trapSeqNum,
                   evtDescription,
                   evtObjectType,
                   evtCodeType }
    STATUS       current
    DESCRIPTION  "This trap provides an ERPS service ring port state change
                  alert."
    ::= { pvxERPSSrvcNNIEvtNotifications 0 1 }



pvxERPSSrvcRingSemStateChangeEvent NOTIFICATION-TYPE
    OBJECTS      { pvxERPSSrvcSwitchIdx,
                   pvxERPSSrvcName,
                   pvxERPSSrvcRingSemState,
                   evtDateAndTime,
                   trapSeqNum,
                   evtDescription,
                   evtObjectType,
                   evtCodeType }
    STATUS       current
    DESCRIPTION  "This trap provides an ERPS service sem state change
                  alert."
    ::= { pvxERPSSrvcEvtNotifications 0 1 }

pvxERPSSrvcConfigFailEvent NOTIFICATION-TYPE
    OBJECTS      { pvxERPSSrvcSwitchIdx,
                   pvxERPSSrvcName,
                   pvxERPSSrvcRingSemState,
                   evtDateAndTime,
                   trapSeqNum,
                   evtDescription,
                   evtObjectType,
                   evtCodeType }
    STATUS       current
DESCRIPTION  "This trap indicates a failure occurred while programming the hardware 
              to capture R-APS messages.  The ERPS ring will not function if
              this trap occurs."
    ::= { pvxERPSSrvcEvtNotifications 0 2 }

pvxERPSSrvcTimerStartEvent NOTIFICATION-TYPE
    OBJECTS      { pvxERPSSrvcSwitchIdx,
                   pvxERPSSrvcName,
                   pvxERPSSrvcRingSemState,
                   evtDateAndTime,
                   trapSeqNum,
                   evtDescription,
                   evtObjectType,
                   evtCodeType }
    STATUS       current
DESCRIPTION  "This trap indicates a failure starting one of the ERPS timers.   
             The ERPS ring will not function correctly after this trap occurs."
    ::= { pvxERPSSrvcEvtNotifications 0 3 }
    

--------------------------------------
-- ERPS alarms 
--------------------------------------
pvxERPSSrvcVersionMismatchCond NOTIFICATION-TYPE
    OBJECTS      { pvxERPSSrvcSwitchIdx,
                   pvxERPSSrvcName,
                   pvxERPSSrvcRingSemState,
	           pvxERPSSrvcCompatibleVersion,
                   condReportType,
                   condDateAndTime,
                   condSeverity,
                   condServiceAffecting,
                   trapSeqNum,
                   condDescription,
                   condObjectType,
                   condCodeType }
    STATUS       current
DESCRIPTION  "This trap indicates a misconfiguration in the ERPS ring. 
              This node is configured for one version of ERPS and is receiving 
              packets from a node configured to run at a different version"
    ::= { erpsCondNotifications 0 1 }
    
pvxERPSSrvcVersionMismatchClear NOTIFICATION-TYPE
    OBJECTS      { pvxERPSSrvcSwitchIdx,
                   pvxERPSSrvcName,
                   pvxERPSSrvcRingSemState,
	               pvxERPSSrvcCompatibleVersion,
                   condReportType,
                   condDateAndTime,
                   condSeverity,
                   condServiceAffecting,
                   trapSeqNum,
                   condDescription,
                   condObjectType,
                   condCodeType }
    STATUS       current
DESCRIPTION  "This trap indicates a misconfiguration in the ERPS ring is cleared"
    ::= { erpsCondNotifications 0 2 }
    
pvxERPSSrvcFOPProvisionMismatchCond NOTIFICATION-TYPE
    OBJECTS      { pvxERPSSrvcSwitchIdx,
                   pvxERPSSrvcName,
                   pvxERPSSrvcRingSemState,
                   condReportType,
                   condDateAndTime,
                   condSeverity,
                   condServiceAffecting,
                   trapSeqNum,
                   condDescription,
                   condObjectType,
                   condCodeType }
    STATUS       current
DESCRIPTION  "This trap indicates a misconfiguration in the ERPS ring.  The RPL 
              Owner has received a R-APS (NR,RB) packet from another node that 
              believes it is the RPL Owner."
    ::= { erpsCondNotifications 0 3 }
    
pvxERPSSrvcFOPProvisionMismatchClear NOTIFICATION-TYPE
    OBJECTS      { pvxERPSSrvcSwitchIdx,
                   pvxERPSSrvcName,
                   pvxERPSSrvcRingSemState,
                   condReportType,
                   condDateAndTime,
                   condSeverity,
                   condServiceAffecting,
                   trapSeqNum,
                   condDescription,
                   condObjectType,
                   condCodeType }
    STATUS       current
DESCRIPTION  "This trap indicates a misconfiguration in the ERPS ring is cleared."
    ::= { erpsCondNotifications 0 4 }

-----------------------------------------------------------------------
-- PVX Service UNI Events
-----------------------------------------------------------------------

pvxSrvcUNIEFPSDLocalEFPSDStateChangeEvent NOTIFICATION-TYPE
    OBJECTS      { pvxSrvcUNISwitchId,
                   pvxSrvcUNIShelfId,
                   pvxSrvcUNISlotId,
                   pvxSrvcUNIPortTypeId,
                   pvxSrvcUNIPortId,
                   pvxSrvcUNISrvcName,
                   pvxSrvcUNIEFPSDLocalEFPSDState,
                   evtDateAndTime,
                   trapSeqNum,
                   evtDescription,
                   evtObjectType,
                   evtCodeType }
    STATUS       current
    DESCRIPTION  "This trap provides an Local EFPSD state change alert."
    ::= { pvxSUniEvtNotifications 0 1 }


    
--------------------------------------
-- ECFM Tables 
--------------------------------------    
-- ----------------------------------------------------------------
-- ----------------------------------------------------------------
-- The MEP List Table
-- ----------------------------------------------------------------
-- ----------------------------------------------------------------

pvxMepListTable OBJECT-TYPE
    SYNTAX      SEQUENCE OF PvxMepListEntry
    MAX-ACCESS  not-accessible
    STATUS      current
    DESCRIPTION  "List of MEPIDs (in any bridge) that belong to the same ME."
    ::= { pvxEcfmService  1 }

pvxMepListEntry OBJECT-TYPE
    SYNTAX      PvxMepListEntry
    MAX-ACCESS  not-accessible
    STATUS      current
    DESCRIPTION "The known MEPs table entry."
    INDEX { pvxMepListSwitchIdx,
            pvxMepListESrvcVlanId,
            pvxMepListIdentifier }
    ::= { pvxMepListTable 1 }

PvxMepListEntry ::= SEQUENCE { pvxMepListSwitchIdx      INTEGER,
                               pvxMepListESrvcVlanId    INTEGER,
                               pvxMepListIdentifier    	INTEGER,
                               pvxMepLocalRemoteFlag    INTEGER,
                               pvxMepSequenceId         INTEGER,
                               pvxMepListRowStatus     	RowStatus }

pvxMepListSwitchIdx  OBJECT-TYPE
   	SYNTAX       INTEGER(1..11)
   	MAX-ACCESS   not-accessible
   	STATUS       current
   	DESCRIPTION  "This object represents the particular switch id."
    ::= {pvxMepListEntry 1 }

pvxMepListESrvcVlanId   OBJECT-TYPE
   	SYNTAX       INTEGER (1..4094)
   	MAX-ACCESS   not-accessible
   	STATUS       current
   	DESCRIPTION  "The name of the service."
    ::= {pvxMepListEntry 2 }

pvxMepListIdentifier    OBJECT-TYPE
    SYNTAX      INTEGER(1..8191)
    MAX-ACCESS  not-accessible
    STATUS      current
    DESCRIPTION  "A 13 bits value of MEP id."
    ::= { pvxMepListEntry 3 }

pvxMepLocalRemoteFlag       OBJECT-TYPE
    SYNTAX      INTEGER{localMEP(1),
                        remoteMEP(2)}
    MAX-ACCESS  read-only
    STATUS      current
    DESCRIPTION "A flag indicating whether the MEP is local or remote. Default is set to remoteMEP by the system."
    ::= { pvxMepListEntry 4 }

pvxMepSequenceId            OBJECT-TYPE
    SYNTAX      INTEGER(1..8191)
    MAX-ACCESS  read-only
    STATUS      current
    DESCRIPTION ""
    ::= { pvxMepListEntry 5 }

pvxMepListRowStatus    OBJECT-TYPE
    SYNTAX      RowStatus
    MAX-ACCESS  read-create
    STATUS      current
    DESCRIPTION "The status of the row."
    ::= { pvxMepListEntry 100 }

-- ----------------------------------------------------------------
-- ----------------------------------------------------------------
-- The MEP Table
-- ----------------------------------------------------------------
-- ----------------------------------------------------------------
pvxEcfmMepTable OBJECT-TYPE
    SYNTAX      SEQUENCE OF PvxEcfmMepEntry
    MAX-ACCESS  not-accessible
    STATUS      current
    DESCRIPTION  "The Maintenance Association End Point (MEP) table.
        Each row in the table represents a different MEP.  A MEP is
        an actively managed CFM entity, associated with a specific
        DSAP of a Service Instance, which can generate and receive
        CFM PDUs and track any responses. "
   ::= { pvxEcfmService  2 }

pvxEcfmMepEntry OBJECT-TYPE
    SYNTAX      PvxEcfmMepEntry
    MAX-ACCESS  not-accessible
    STATUS      current
    DESCRIPTION "The MEP table entry"
    INDEX { pvxEcfmMepSwitchIdx,
            pvxEcfmMepShelfId,
            pvxEcfmMepSlotId,
            pvxEcfmMepPortTypeId,
            pvxEcfmMepPortId,
            pvxEcfmMepESrvcName
          }
    ::= { pvxEcfmMepTable 1 }

PvxEcfmMepEntry ::= SEQUENCE {
            pvxEcfmMepSwitchIdx                    INTEGER,
            pvxEcfmMepShelfId                      INTEGER,
            pvxEcfmMepSlotId                       INTEGER,
            pvxEcfmMepPortTypeId                   PvxPortType,
            pvxEcfmMepPortId                       Integer32,
            pvxEcfmMepESrvcName                    DisplayString,
            pvxEcfmMepIdentifier                   INTEGER,
            pvxEcfmMepDirection                    INTEGER,           
            pvxEcfmMepActive                       TruthValue,      
            pvxEcfmMepAutoGenerateFlag             TruthValue,
            pvxEcfmMepMacAddress                   MacAddress,
            pvxEcfmMepFlushRMepDb                  TruthValue,
            pvxEcfmMepOutOfService                 TruthValue,
            pvxEcfmMepY1731DefectConditions        PvxY1731MepDefects,
            pvxEcfmMepDefects                      PvxEcfmMepDefects,
            pvxEcfmMepCcmSequenceErr               Unsigned32,
            pvxEcfmMepSentCcms                     Unsigned32,
            pvxEcfmMepTransmitLtmStatus            PvxEcfmTransmitStatus,
            pvxEcfmMepTransmitLtmTargetMepId       INTEGER,
            pvxEcfmMepTransmitLtmTtl               Unsigned32,
            pvxEcfmMepTransmitLtmResultOK          TruthValue,
            pvxEcfmMepTransmitLtmSeqNumber         Unsigned32,
            pvxEcfmMepTransmitLbmStatus            PvxEcfmTransmitStatus ,
            pvxEcfmMepTransmitLbmDestMepId         INTEGER,
            pvxEcfmMepTransmitLbmCount             Unsigned32,
            pvxEcfmMepTransmitLbmResultOK          TruthValue,
            pvxEcfmMepY1731LbmCurrentTransId       Unsigned32,
            pvxEcfmMepLbrIn                        Unsigned32,
            pvxEcfmMepLbrInOutOfOrder              Unsigned32,
            pvxEcfmMepLbrBadMsdu                   Unsigned32,
            pvxEcfmMepLbrOut                       Unsigned32,
            pvxEcfmMepUnexpLtrIn                   Unsigned32, 
            pvxEcfmMepErrCcmRMepId                 Unsigned32,
            pvxEcfmMepXconnRMepId                  Unsigned32 }

pvxEcfmMepSwitchIdx     OBJECT-TYPE
   	SYNTAX       INTEGER(1..11)
   	MAX-ACCESS   not-accessible
   	STATUS       current
   	DESCRIPTION  "This object represents the particular switch id."
    ::= {pvxEcfmMepEntry 1 }

pvxEcfmMepShelfId     OBJECT-TYPE
        SYNTAX       INTEGER (0|1|11|21|31)
        MAX-ACCESS   not-accessible
        STATUS       current
        DESCRIPTION  ""
   ::= { pvxEcfmMepEntry 2 }

pvxEcfmMepSlotId OBJECT-TYPE
        SYNTAX       INTEGER (0|1|3|5|7|9|11|13|15|17|19)
        MAX-ACCESS   not-accessible
        STATUS       current
        DESCRIPTION  ""
   ::= { pvxEcfmMepEntry 3 }

pvxEcfmMepPortTypeId OBJECT-TYPE
        SYNTAX       PvxPortType 
        MAX-ACCESS   not-accessible
        STATUS       current
        DESCRIPTION  ""
   ::= { pvxEcfmMepEntry 4 }

pvxEcfmMepPortId OBJECT-TYPE
        SYNTAX  Integer32
        MAX-ACCESS   not-accessible
        STATUS       current
        DESCRIPTION  ""
   ::= { pvxEcfmMepEntry 5 }

pvxEcfmMepESrvcName     OBJECT-TYPE
   	SYNTAX       DisplayString (SIZE(1..32))
   	MAX-ACCESS   not-accessible
   	STATUS       current
   	DESCRIPTION  "The name of the service."
    ::= {pvxEcfmMepEntry 6 }

pvxEcfmMepIdentifier     OBJECT-TYPE
    SYNTAX      INTEGER(1..8191)
    MAX-ACCESS  read-write
    STATUS      current
    DESCRIPTION "A 13 bits value of MEP id."
    ::= { pvxEcfmMepEntry 7 }

pvxEcfmMepDirection  OBJECT-TYPE
        SYNTAX  INTEGER { up(1), 
                          down(2)}
        MAX-ACCESS   read-write
        STATUS       current
        DESCRIPTION  "MEP direction. Default is set to up by the system."
        DEFVAL       { up }
   ::= { pvxEcfmMepEntry 8 }

pvxEcfmMepActive      OBJECT-TYPE
        SYNTAX      TruthValue
        MAX-ACCESS  read-write
        STATUS      current
        DESCRIPTION  "A Boolean indicating the administrative state of the MEP.
             True indicates that the MEP is to function normally, and
             false that it is to cease functioning."
        DEFVAL       { true }
    ::= { pvxEcfmMepEntry 9 }

pvxEcfmMepAutoGenerateFlag   OBJECT-TYPE
    SYNTAX      TruthValue
    MAX-ACCESS  read-write
    STATUS      current
    DESCRIPTION  "A Boolean indicating whether the MEP ID is auto-generated by the system. FALSE indicates the user configured the MEP ID."
    DEFVAL       { true }
    ::= { pvxEcfmMepEntry 10 }

pvxEcfmMepMacAddress OBJECT-TYPE
    SYNTAX      MacAddress
    MAX-ACCESS  read-only
    STATUS      current
    DESCRIPTION  "MAC address of the MEP."
    ::= { pvxEcfmMepEntry 11 }

pvxEcfmMepFlushRMepDb   OBJECT-TYPE
    SYNTAX      TruthValue
    MAX-ACCESS  read-write
    STATUS      current
    DESCRIPTION  "A Boolean indicating whether the remote MEP needs to flush its MEP list or not
        True indicates that the remote MEP needs to flush and rebuild its MEP lists."
    DEFVAL       { false }
    ::= { pvxEcfmMepEntry 12 }

pvxEcfmMepOutOfService  OBJECT-TYPE
    SYNTAX      TruthValue
    MAX-ACCESS  read-write
    STATUS      current
    DESCRIPTION  "Adminstrative service that is being or to be performed. True indicates that the operation needs to be
                  performed out-of-service. Otherwise, the operation needs to be performed in-service.."
    DEFVAL       { true }
    ::= { pvxEcfmMepEntry 13 }

pvxEcfmMepY1731DefectConditions    OBJECT-TYPE
    SYNTAX      PvxY1731MepDefects 
    MAX-ACCESS  read-only
    STATUS      current
    DESCRIPTION "A vector of Boolean indicates the defect conditions."
    ::= { pvxEcfmMepEntry 14 }  

  pvxEcfmMepDefects  OBJECT-TYPE
    SYNTAX      PvxEcfmMepDefects  
    MAX-ACCESS  read-only
    STATUS      current
    DESCRIPTION "A vector of Boolean indicates the defect conditions."
    ::= { pvxEcfmMepEntry 15 } 

pvxEcfmMepCcmSequenceErr OBJECT-TYPE
    SYNTAX      Unsigned32
    MAX-ACCESS  read-only
    STATUS      current
    DESCRIPTION "The total number of out-of-sequence CCMs received from all
        remote MEPs. "
    ::= { pvxEcfmMepEntry 16 } 
            
pvxEcfmMepSentCcms OBJECT-TYPE
    SYNTAX      Unsigned32
    MAX-ACCESS  read-only
    STATUS      current
    DESCRIPTION  "Total number of Continuity Check messages transmitted."   
    ::= { pvxEcfmMepEntry 17 }

pvxEcfmMepTransmitLtmStatus OBJECT-TYPE
   SYNTAX      PvxEcfmTransmitStatus
   MAX-ACCESS  read-write
   STATUS      current
   DESCRIPTION  "A Enumerated value set to 'transmit' to initiate LTM transmission. 
       Set to 'ready' or 'notReady' by the MEP Linktrace Initiator State Machine."
   DEFVAL { transmit }
   ::= { pvxEcfmMepEntry 18 }

pvxEcfmMepTransmitLtmTargetMepId OBJECT-TYPE
    SYNTAX      INTEGER(1..8191)
    MAX-ACCESS  read-write
    STATUS      current
    DESCRIPTION "Target MEP ID."
    DEFVAL       { 1 }
    ::= { pvxEcfmMepEntry 19 }

pvxEcfmMepTransmitLtmTtl OBJECT-TYPE
    SYNTAX      Unsigned32 (0..255)
    MAX-ACCESS  read-write
    STATUS      current
    DESCRIPTION  "The LTM TTL field. Default value, if not specified, is 64.
        The TTL field indicates the number of hops remaining to the
        LTM.  Decremented by 1 by each Linktrace Responder that
        handles the LTM.  The value received in the LTM is returned
        in the LTR.  If 0 on input, the LTM is not transmitted to the
        next hop."
    DEFVAL {64}
    ::= { pvxEcfmMepEntry 20 }

pvxEcfmMepTransmitLtmResultOK OBJECT-TYPE
    SYNTAX      TruthValue
    MAX-ACCESS  read-only
    STATUS      current
    DESCRIPTION "Indicates the result of the operation:

        - true    The Linktrace Message will be (or has been) sent.
        - false   The Linktrace Message will not be sent"
   ::= { pvxEcfmMepEntry 21 }

pvxEcfmMepTransmitLtmSeqNumber OBJECT-TYPE
    SYNTAX      Unsigned32
    MAX-ACCESS  read-only
    STATUS      current
    DESCRIPTION "The LTM Transaction Identifier of the LTM sent.
        The value returned is undefined if
        pvxEcfmMepTransmitLtmResultOK is false."
    ::= { pvxEcfmMepEntry 22 }

pvxEcfmMepTransmitLbmStatus OBJECT-TYPE
   SYNTAX      PvxEcfmTransmitStatus
   MAX-ACCESS  read-write
   STATUS      current
   DESCRIPTION "A Enumerated value set to 'transmit'to initiate LBM transmission.
       Set to 'ready' or 'notReady' by the MEP Loopback Initiator State Machine."
   DEFVAL       { ready }
   ::= { pvxEcfmMepEntry 23 }

pvxEcfmMepTransmitLbmDestMepId  OBJECT-TYPE
    SYNTAX      INTEGER(1..8191)
    MAX-ACCESS  read-write
    STATUS      current
    DESCRIPTION  "Target MEP ID."
    DEFVAL       { 1 }
    ::= { pvxEcfmMepEntry 24 }

pvxEcfmMepTransmitLbmCount    OBJECT-TYPE
         SYNTAX        Unsigned32
         MAX-ACCESS    read-write
         STATUS        current
         DESCRIPTION "Identifies the number of LBMs transmitted"
         DEFVAL       { 0 }
        ::= { pvxEcfmMepEntry 25 }

pvxEcfmMepTransmitLbmResultOK OBJECT-TYPE
    SYNTAX      TruthValue
    MAX-ACCESS  read-only
    STATUS      current
    DESCRIPTION "Indicates the result of the operation:

        - true       The Loopback Message(s) will be
                     (or has been) sent.
        - false      The Loopback Message(s) will not
                     be sent."
    ::= { pvxEcfmMepEntry 26 }

pvxEcfmMepY1731LbmCurrentTransId   OBJECT-TYPE
    SYNTAX      Unsigned32(1..4294967295)
    MAX-ACCESS  read-only
    STATUS      current
    DESCRIPTION "Identifies the current LBM Transaction."
    ::= { pvxEcfmMepEntry 27 } 

pvxEcfmMepLbrIn OBJECT-TYPE
    SYNTAX      Unsigned32
    MAX-ACCESS  read-only
    STATUS      current
    DESCRIPTION "Total number of valid, in-order Loopback Replies received."
    ::= { pvxEcfmMepEntry 28 }

pvxEcfmMepLbrInOutOfOrder OBJECT-TYPE
    SYNTAX      Unsigned32
    MAX-ACCESS  read-only
    STATUS      current
    DESCRIPTION  "The total number of valid, out-of-order Loopback Replies
        received."
    ::= { pvxEcfmMepEntry 29 }   

pvxEcfmMepLbrBadMsdu OBJECT-TYPE
    SYNTAX      Unsigned32
    MAX-ACCESS  read-only
    STATUS      current
    DESCRIPTION  "The total number of LBRs received whose
        mac_service_data_unit did not match (except for the OpCode)
        that of the corresponding LBM."
    ::= { pvxEcfmMepEntry 30 }  

pvxEcfmMepLbrOut OBJECT-TYPE
    SYNTAX      Unsigned32
    MAX-ACCESS  read-only
    STATUS      current
    DESCRIPTION "Total number of Loopback Replies transmitted."
    ::= { pvxEcfmMepEntry 31 } 

pvxEcfmMepUnexpLtrIn OBJECT-TYPE
    SYNTAX      Unsigned32
    MAX-ACCESS  read-only
    STATUS      current
    DESCRIPTION "The total number of unexpected LTRs received."
    ::= { pvxEcfmMepEntry 32 }
    
pvxEcfmMepErrCcmRMepId OBJECT-TYPE
    SYNTAX      Unsigned32
    MAX-ACCESS  read-only
    STATUS      current
    DESCRIPTION "Mep Id of the CCM which caused the Error CCM Defect."
    ::= { pvxEcfmMepEntry 33 }
    
pvxEcfmMepXconnRMepId OBJECT-TYPE
    SYNTAX      Unsigned32
    MAX-ACCESS  read-only
    STATUS      current
    DESCRIPTION "Mep Id of the CCM which caused the Xconn CCM Defect"
    ::= { pvxEcfmMepEntry 34 }


-----------------------------------------------------------------------
-- Remote MEP Events
-----------------------------------------------------------------------

cfmRMepStateChangeV2Evt NOTIFICATION-TYPE
    OBJECTS      {
                   pvxEcfmMepDbRMepState,
                   pvxEcfmMepDefects }
    STATUS        current
    DESCRIPTION "A cfmRMepStateChangeEvt notification is sent when 
            a remote MEP changes its state."

   ::= { cfmRMepStateChangeEvtNotifications 0 2 }

-- ----------------------------------------------------------------
-- ----------------------------------------------------------------
-- The MEP DB Table
-- ----------------------------------------------------------------
-- ----------------------------------------------------------------
pvxEcfmMepDbTable OBJECT-TYPE
    SYNTAX      SEQUENCE OF PvxEcfmMepDbEntry
    MAX-ACCESS  not-accessible
    STATUS      current
    DESCRIPTION "The MEP Database. A database, maintained by every MEP, that
        maintains received information about other MEPs in the
        Maintenance Domain."
    ::= { pvxEcfmService  3 }

pvxEcfmMepDbEntry OBJECT-TYPE
    SYNTAX      PvxEcfmMepDbEntry
    MAX-ACCESS  not-accessible
    STATUS      current
    DESCRIPTION  "The MEP Database table entry."
    INDEX { pvxEcfmMepDbSwitchIdx,
            pvxEcfmMepDbVlanId,
            pvxEcfmMepDbLocalMepId,
            pvxEcfmMepDbRemoteMepId
          }
    ::= { pvxEcfmMepDbTable 1 }

PvxEcfmMepDbEntry ::= SEQUENCE { pvxEcfmMepDbSwitchIdx            INTEGER,
            pvxEcfmMepDbVlanId               INTEGER,
            pvxEcfmMepDbLocalMepId           INTEGER,
            pvxEcfmMepDbRemoteMepId          INTEGER,            
            pvxEcfmMepDbRMepState            PvxEcfmRemoteMepState,
            pvxEcfmMepDbMacAddress           MacAddress,
            pvxEcfmMepDbRMepSwitchName       DisplayString,
            pvxEcfmMepDbRMepPortInfo         DisplayString,            
            pvxEcfmMepDbRMepRDI              TruthValue,
            pvxEcfmMepDbRMepCcmDefect        TruthValue,
            pvxEcfmMepDbRMepPortStatusDefect TruthValue,
            pvxEcfmMepDbRMepIntfStatusDefect TruthValue}

pvxEcfmMepDbSwitchIdx    OBJECT-TYPE
   	SYNTAX       INTEGER(1..11)
   	MAX-ACCESS   not-accessible
   	STATUS       current
   	DESCRIPTION  "This object represents the particular switch id."
    ::= {pvxEcfmMepDbEntry 1 }

pvxEcfmMepDbVlanId    OBJECT-TYPE
   	SYNTAX       INTEGER (1..4094)
   	MAX-ACCESS   not-accessible
   	STATUS       current
   	DESCRIPTION  "The vlan ID of the ethernet service."
    ::= {pvxEcfmMepDbEntry 2 }

pvxEcfmMepDbLocalMepId   OBJECT-TYPE
    SYNTAX      INTEGER(1..8191)
    MAX-ACCESS  not-accessible
    STATUS      current
    DESCRIPTION "A 13 bits value of MEP id."
    ::= { pvxEcfmMepDbEntry 3 }

pvxEcfmMepDbRemoteMepId   OBJECT-TYPE
    SYNTAX      INTEGER(1..8191)
    MAX-ACCESS  not-accessible
    STATUS      current
    DESCRIPTION "A 13 bits value of remote MEP id."
    ::= { pvxEcfmMepDbEntry 4 }

pvxEcfmMepDbRMepState OBJECT-TYPE
    SYNTAX      PvxEcfmRemoteMepState
    MAX-ACCESS  read-only
    STATUS      current
    DESCRIPTION "The operational state of the remote MEP IFF State machines."
    ::= { pvxEcfmMepDbEntry 5}

pvxEcfmMepDbMacAddress OBJECT-TYPE
    SYNTAX      MacAddress
    MAX-ACCESS  read-only
    STATUS      current
    DESCRIPTION "The MAC address of the remote MEP."
    ::= { pvxEcfmMepDbEntry 6 }
      
pvxEcfmMepDbRMepSwitchName  OBJECT-TYPE
   	SYNTAX       DisplayString (SIZE(1..32))
   	MAX-ACCESS   read-only
   	STATUS       current
   	DESCRIPTION  "The name of the remote switch. It is set by the system as PVX-x
                    where 'x' is the switch nubmer."
    ::= {pvxEcfmMepDbEntry 7 }

 pvxEcfmMepDbRMepPortInfo   OBJECT-TYPE
   	SYNTAX       DisplayString (SIZE(1..32))
   	MAX-ACCESS   read-only
   	STATUS       current
   	DESCRIPTION  "The port information of the remote port. It is set by the system as 
                    a string of shelfNumber/slotNumber/portType/portNumber."
    ::= {pvxEcfmMepDbEntry 8 }
    
pvxEcfmMepDbRMepRDI   OBJECT-TYPE
   	SYNTAX       TruthValue
   	MAX-ACCESS   read-only
   	STATUS       current
   	DESCRIPTION  "State of the RDI bit in the last received CCM (true for RDI=1),
   	              or false if none has been received."
    ::= {pvxEcfmMepDbEntry 9 }

pvxEcfmMepDbRMepCcmDefect   OBJECT-TYPE
   	SYNTAX       TruthValue
   	MAX-ACCESS   read-only
   	STATUS       current
   	DESCRIPTION  "A Boolean indicating that no CCM has been received from the 
   	             remote MEP for at least (3.25*CCM time (CCMInterval)) seconds"
    ::= {pvxEcfmMepDbEntry 10 }
    
pvxEcfmMepDbRMepPortStatusDefect   OBJECT-TYPE
   	SYNTAX       TruthValue
   	MAX-ACCESS   read-only
   	STATUS       current
   	DESCRIPTION  "True if a Port Status Defect is reported by a remote MEP"
    ::= {pvxEcfmMepDbEntry 11 }

pvxEcfmMepDbRMepIntfStatusDefect   OBJECT-TYPE
   	SYNTAX       TruthValue
   	MAX-ACCESS   read-only
   	STATUS       current
   	DESCRIPTION  "True if an Interface Status Defect is reported by a remote MEP"
    ::= {pvxEcfmMepDbEntry 12 }


-- ----------------------------------------------------------------
-- ----------------------------------------------------------------
-- The MIP Table
-- ----------------------------------------------------------------
-- ----------------------------------------------------------------
 pvxEcfmMipTable OBJECT-TYPE
     SYNTAX SEQUENCE OF PvxEcfmMipEntry
     MAX-ACCESS    not-accessible
     STATUS        current
     DESCRIPTION  "The Maintenance Intermediate Point (MIP) table.
                  Each row in the table represents a different MIP. 
                  A MIP consists two MIP Half Functions (MHFs) on a 
                  single Bridge Port, an Up MHF and a Down MHF."
     ::= { pvxEcfmService  4 }

 pvxEcfmMipEntry OBJECT-TYPE
     SYNTAX       PvxEcfmMipEntry
     MAX-ACCESS   not-accessible
     STATUS       current
     DESCRIPTION "The MIP table entry."
     INDEX {  pvxEcfmMipSwitchIdx,
              pvxEcfmMipShelfId,
              pvxEcfmMipSlotId,
              pvxEcfmMipPortTypeId,
              pvxEcfmMipPortId,
              pvxEcfmMipMegLevel,
              pvxEcfmMipESrvcVlanId
               }
     ::= { pvxEcfmMipTable 1 }

 PvxEcfmMipEntry ::= SEQUENCE {
             pvxEcfmMipSwitchIdx                    INTEGER,
             pvxEcfmMipShelfId                      INTEGER,
             pvxEcfmMipSlotId                       INTEGER,
             pvxEcfmMipPortTypeId                   PvxPortType,
             pvxEcfmMipPortId                       INTEGER,
             pvxEcfmMipMegLevel                     INTEGER,
             pvxEcfmMipESrvcVlanId                  INTEGER,
             pvxEcfmMipESrvcName                    DisplayString,
             pvxEcfmMipActiveState                  TruthValue,                
             pvxEcfmMipRowStatus                    RowStatus     
             }

 pvxEcfmMipSwitchIdx     OBJECT-TYPE
   	SYNTAX       INTEGER(1..11)
   	MAX-ACCESS   not-accessible
   	STATUS       current
   	DESCRIPTION  "This object represents the particular switch id."
    ::= {pvxEcfmMipEntry 1 }

pvxEcfmMipShelfId     OBJECT-TYPE
        SYNTAX       INTEGER (0|1|11|21|31)
        MAX-ACCESS   not-accessible
        STATUS       current
        DESCRIPTION  "The shelf number."
   ::= { pvxEcfmMipEntry 2 }

pvxEcfmMipSlotId OBJECT-TYPE
        SYNTAX       INTEGER (0|1|3|5|7|9|11|13|15|17|19)
        MAX-ACCESS   not-accessible
        STATUS       current
        DESCRIPTION  "The slot number."
   ::= { pvxEcfmMipEntry 3 }

pvxEcfmMipPortTypeId OBJECT-TYPE
        SYNTAX       PvxPortType 
        MAX-ACCESS   not-accessible
        STATUS       current
        DESCRIPTION  "The port type."
   ::= { pvxEcfmMipEntry 4 }

pvxEcfmMipPortId OBJECT-TYPE
        SYNTAX  INTEGER(1..24)
        MAX-ACCESS   not-accessible
        STATUS       current
        DESCRIPTION  "The port number"
   ::= { pvxEcfmMipEntry 5 }
 
pvxEcfmMipMegLevel OBJECT-TYPE
        SYNTAX  INTEGER(1..7)
        MAX-ACCESS   not-accessible
        STATUS       current
        DESCRIPTION  "The MEG level."
   ::= { pvxEcfmMipEntry 6 }
   
pvxEcfmMipESrvcVlanId     OBJECT-TYPE
   	SYNTAX       INTEGER (1..4094)
   	MAX-ACCESS   not-accessible
   	STATUS       current
   	DESCRIPTION  "The vlan ID of the service."
    ::= {pvxEcfmMipEntry 7 }
          
pvxEcfmMipESrvcName     OBJECT-TYPE
   	SYNTAX       DisplayString (SIZE(1..32))
   	MAX-ACCESS   read-only
   	STATUS       current
   	DESCRIPTION  "The name of the service."
    ::= {pvxEcfmMipEntry 8 }

pvxEcfmMipActiveState  OBJECT-TYPE
     SYNTAX        TruthValue
     MAX-ACCESS    read-create
     STATUS        current
     DESCRIPTION "A Boolean indicating the administrative state of the MIP.
         True indicates that the MIP is to function normally, and
         false that it is to cease functioning."
    ::= { pvxEcfmMipEntry 9 }  

pvxEcfmMipRowStatus    OBJECT-TYPE
    SYNTAX      RowStatus
    MAX-ACCESS  read-create
    STATUS      current
    DESCRIPTION "The status of the row."
    ::= { pvxEcfmMipEntry 100 }


-- ----------------------------------------------------------------
-- ----------------------------------------------------------------
-- The Y.1731 loopback stats Table
-- ----------------------------------------------------------------
-- ----------------------------------------------------------------
pvxY1731LbStatsTable OBJECT-TYPE
    SYNTAX      SEQUENCE OF PvxY1731LbStatsEntry
    MAX-ACCESS  not-accessible
    STATUS      current
    DESCRIPTION "This table extends the MEP table and contains output of loopback 
       or ping transaction. 
       Output includes number of replies recieved, time taken for a reply to
       come."
    ::= {pvxEcfmService  6}

pvxY1731LbStatsEntry OBJECT-TYPE
    SYNTAX      PvxY1731LbStatsEntry
    MAX-ACCESS  not-accessible
    STATUS      current
    DESCRIPTION "The Loopback Statistics table entry."
    INDEX { pvxY1731LbStatsSwitchIdx,
            pvxY1731LbStatsESrvcName,
            pvxY1731LbStatsIdentifier,
            pvxY1731LbmTransId
          }
    ::= { pvxY1731LbStatsTable 1 }

PvxY1731LbStatsEntry ::= SEQUENCE {
         pvxY1731LbStatsSwitchIdx             INTEGER,
         pvxY1731LbStatsESrvcName             DisplayString,
         pvxY1731LbStatsIdentifier            INTEGER,
         pvxY1731LbmTransId                   Unsigned32,
         pvxY1731LbStatsLbmOut                Unsigned32,
         pvxY1731LbStatsLbrIn                 Unsigned32,
         pvxY1731LbStatsLbrTimeAverage        TimeInterval,
         pvxY1731LbStatsLbrTimeMin            TimeInterval,
         pvxY1731LbStatsLbrTimeMax            TimeInterval,
         pvxY1731LbStatsTotalResponders       Unsigned32,
         pvxY1731LbStatsAvgLbrsPerResponder   Unsigned32            
    }

pvxY1731LbStatsSwitchIdx    OBJECT-TYPE
   	SYNTAX       INTEGER(1..11)
   	MAX-ACCESS   not-accessible
   	STATUS       current
   	DESCRIPTION  "This object represents the particular switch id."
    ::= {pvxY1731LbStatsEntry 1 }

pvxY1731LbStatsESrvcName     OBJECT-TYPE
   	SYNTAX       DisplayString (SIZE(1..32))
   	MAX-ACCESS   not-accessible
   	STATUS       current
   	DESCRIPTION  "The name of the service."
    ::= {pvxY1731LbStatsEntry 2 }

pvxY1731LbStatsIdentifier    OBJECT-TYPE
    SYNTAX      INTEGER(1..8191)
    MAX-ACCESS  not-accessible
    STATUS      current
    DESCRIPTION "A 13 bits value of MEP id."
    ::= { pvxY1731LbStatsEntry 3 }

pvxY1731LbmTransId    OBJECT-TYPE
    SYNTAX      Unsigned32 (1..4294967295)
    MAX-ACCESS  not-accessible
    STATUS      current
    DESCRIPTION  "Transaction Identifier identifies a loopback or ping (LBM)transaction."
    ::= { pvxY1731LbStatsEntry 4}

pvxY1731LbStatsLbmOut OBJECT-TYPE
    SYNTAX      Unsigned32
    MAX-ACCESS  read-only
    STATUS      current
    DESCRIPTION "Number of LBMs sent in a loopback or ping transaction."
    ::= { pvxY1731LbStatsEntry 5}

pvxY1731LbStatsLbrIn OBJECT-TYPE
    SYNTAX      Unsigned32
    MAX-ACCESS  read-only
    STATUS      current
    DESCRIPTION "Number of replies (LBR) received in a loopback or ping transaction."
    ::= { pvxY1731LbStatsEntry 6 }

pvxY1731LbStatsLbrTimeAverage OBJECT-TYPE
    SYNTAX      TimeInterval
    MAX-ACCESS  read-only
    STATUS      current
    DESCRIPTION  "Average time taken to receive the replies (LBR) for the current 
        loopback or ping transaction."
    ::= { pvxY1731LbStatsEntry 7 }

pvxY1731LbStatsLbrTimeMin OBJECT-TYPE
    SYNTAX      TimeInterval
    MAX-ACCESS  read-only
    STATUS      current
    DESCRIPTION "Minimum time taken to receive the replies (LBR) for the
       current loopback or ping transaction."
    ::= { pvxY1731LbStatsEntry 8 }

pvxY1731LbStatsLbrTimeMax OBJECT-TYPE
    SYNTAX      TimeInterval
    MAX-ACCESS  read-only
    STATUS      current
    DESCRIPTION "Maximum time taken to receive the replies (LBR) for the current 
        loopback or ping transaction."
    ::= { pvxY1731LbStatsEntry 9 }

pvxY1731LbStatsTotalResponders OBJECT-TYPE
    SYNTAX      Unsigned32
    MAX-ACCESS  read-only
    STATUS      current
    DESCRIPTION "Total Number of Responders which have sent the reply
        (LBR) for the initiated LBM."
    ::= { pvxY1731LbStatsEntry 10 }

pvxY1731LbStatsAvgLbrsPerResponder OBJECT-TYPE
    SYNTAX      Unsigned32
    MAX-ACCESS  read-only
    STATUS      current
    DESCRIPTION "Average Number of LBR(s) received per Responder."
    ::= { pvxY1731LbStatsEntry 11 }

-- ----------------------------------------------------------------
-- ----------------------------------------------------------------
-- The Linktrace Reply Table 
-- ----------------------------------------------------------------
-- ----------------------------------------------------------------
pvxEcfmLtrTable OBJECT-TYPE
    SYNTAX      SEQUENCE OF PvxEcfmLtrEntry
    MAX-ACCESS  not-accessible
    STATUS      current
    DESCRIPTION "This table extends the MEP table and contains a list of
        Linktrace replies received by a specific MEP in response to
        a linktrace message."
    ::= { pvxEcfmService  7 }

pvxEcfmLtrEntry OBJECT-TYPE
    SYNTAX      PvxEcfmLtrEntry
    MAX-ACCESS  not-accessible
    STATUS      current
    DESCRIPTION "The Linktrace Reply table entry."
    INDEX { pvxEcfmLtrSwitchIdx,
            pvxEcfmLtrVlanId,
            pvxEcfmLtrMepIdentifier,
            pvxEcfmLtrSeqNumber,
            pvxEcfmLtrReceiveOrder
          }
    ::= { pvxEcfmLtrTable 1 }

PvxEcfmLtrEntry ::= SEQUENCE {
      pvxEcfmLtrSwitchIdx            INTEGER,
      pvxEcfmLtrVlanId               INTEGER,
      pvxEcfmLtrMepIdentifier        INTEGER,      
      pvxEcfmLtrSeqNumber            Unsigned32,
      pvxEcfmLtrReceiveOrder         Unsigned32,
      pvxEcfmLtrTtl                  Unsigned32,
      pvxEcfmLtrForwarded            TruthValue,
      pvxEcfmLtrTerminalMep          TruthValue,
      pvxEcfmLtrRelayAction          PvxEcfmRelayActionFieldValue,
      pvxEcfmLtrSwitchName           DisplayString,
      pvxEcfmLtrIngressAction        PvxEcfmIngressActionFieldValue,
      pvxEcfmLtrIngressMac           MacAddress,
      pvxEcfmLtrIngressPortInfo      DisplayString,
      pvxEcfmLtrEgressAction         PvxEcfmEgressActionFieldValue,
      pvxEcfmLtrEgressMac            MacAddress,
      pvxEcfmLtrEgressPortInfo       DisplayString
    } 

pvxEcfmLtrSwitchIdx     OBJECT-TYPE
   	SYNTAX       INTEGER(1..11)
   	MAX-ACCESS   not-accessible
   	STATUS       current
   	DESCRIPTION  "This object represents the particular switch id."
    ::= {pvxEcfmLtrEntry 1 }

pvxEcfmLtrVlanId     OBJECT-TYPE
   	SYNTAX       INTEGER (1..4094)
   	MAX-ACCESS   not-accessible
   	STATUS       current
   	DESCRIPTION  "The s-vlan of the service."
    ::= {pvxEcfmLtrEntry 2 }

pvxEcfmLtrMepIdentifier    OBJECT-TYPE
    SYNTAX      INTEGER(1..8191)
    MAX-ACCESS  not-accessible
    STATUS      current
    DESCRIPTION "A 13 bits value of MEP id."
    ::= { pvxEcfmLtrEntry 3 }

pvxEcfmLtrSeqNumber OBJECT-TYPE
    SYNTAX      Unsigned32 (0..4294967295)
    MAX-ACCESS  not-accessible
    STATUS      current
    DESCRIPTION "Transaction identifier/Sequence number returned by a previous
        transmit linktrace message command, indicating which LTM's
        response is going to be returned."
    ::= { pvxEcfmLtrEntry 4}

pvxEcfmLtrReceiveOrder OBJECT-TYPE
    SYNTAX      Unsigned32(1..4294967295)
    MAX-ACCESS  not-accessible
    STATUS      current
    DESCRIPTION "An index to distinguish among multiple LTRs with the same LTR
        Transaction Identifier field value.  pvxEcfmLtrReceiveOrder 
        are assigned sequentially from 1, in the order that the
        Linktrace Initiator received the LTRs."
    ::= { pvxEcfmLtrEntry 5 }

pvxEcfmLtrTtl OBJECT-TYPE
    SYNTAX      Unsigned32 (0..255)
    MAX-ACCESS  read-only
    STATUS      current
    DESCRIPTION "TTL field value for a returned LTR."
    ::= { pvxEcfmLtrEntry 6 }

pvxEcfmLtrForwarded OBJECT-TYPE
    SYNTAX      TruthValue
    MAX-ACCESS  read-only
    STATUS      current
    DESCRIPTION  "Indicates if a LTM was forwarded by the responding MP."
    ::= { pvxEcfmLtrEntry 7 }

pvxEcfmLtrTerminalMep OBJECT-TYPE
    SYNTAX      TruthValue
    MAX-ACCESS  read-only
    STATUS      current
    DESCRIPTION "A boolean value stating whether the forwarded LTM reached a
        MEP enclosing its ME. "
    ::= { pvxEcfmLtrEntry 8 }

pvxEcfmLtrRelayAction OBJECT-TYPE
    SYNTAX      PvxEcfmRelayActionFieldValue
    MAX-ACCESS  read-only
    STATUS      current
    DESCRIPTION "Value returned in the Relay Action field."
    ::= { pvxEcfmLtrEntry 9 }

pvxEcfmLtrSwitchName   OBJECT-TYPE
   	SYNTAX       DisplayString (SIZE(1..32))
   	MAX-ACCESS   read-only
   	STATUS       current
   	DESCRIPTION  "The switch name of the MEP. It is set by the system as PVX-x
                    where 'x' is the switch nubmer."
    ::= {pvxEcfmLtrEntry 10 }

pvxEcfmLtrIngressAction OBJECT-TYPE
    SYNTAX      PvxEcfmIngressActionFieldValue
    MAX-ACCESS  read-only
    STATUS      current
    DESCRIPTION "The value returned in the Ingress Action Field of the LTM."
    ::= { pvxEcfmLtrEntry 11 }

pvxEcfmLtrIngressMac OBJECT-TYPE
    SYNTAX      MacAddress
    MAX-ACCESS  read-only
    STATUS      current
    DESCRIPTION "MAC address returned in the ingress MAC address field."
    ::= { pvxEcfmLtrEntry 12 }

 pvxEcfmLtrIngressPortInfo    OBJECT-TYPE
   	SYNTAX       DisplayString (SIZE(1..32))
   	MAX-ACCESS   read-only
   	STATUS       current
   	DESCRIPTION  "The port information of the ingress port. It is set by the system as 
                    a string of shelfNumber/slotNumber/portType/portNumber."
    ::= {pvxEcfmLtrEntry 13 }

pvxEcfmLtrEgressAction OBJECT-TYPE
    SYNTAX      PvxEcfmEgressActionFieldValue
    MAX-ACCESS  read-only
    STATUS      current
    DESCRIPTION "The value returned in the Egress Action Field of the LTM."
    ::= { pvxEcfmLtrEntry 14 }

pvxEcfmLtrEgressMac OBJECT-TYPE
    SYNTAX      MacAddress
    MAX-ACCESS  read-only
    STATUS      current
    DESCRIPTION  "MAC address returned in the egress MAC address field."
    ::= { pvxEcfmLtrEntry 15 }

 pvxEcfmLtrEgressPortInfo    OBJECT-TYPE
   	SYNTAX       DisplayString (SIZE(1..32))
   	MAX-ACCESS   read-only
   	STATUS       current
   	DESCRIPTION  "The port information of the egress port. It is set by the system as 
                    a string of shelfNumber/slotNumber/portType/portNumber."
    ::= {pvxEcfmLtrEntry 16 }

-- ----------------------------------------------------------------
-- ----------------------------------------------------------------
-- The Throughput test Table 
-- ----------------------------------------------------------------
-- ----------------------------------------------------------------
pvxSLAThroughputTestTable OBJECT-TYPE
    SYNTAX      SEQUENCE OF PvxSLAThroughputTestEntry
    MAX-ACCESS  not-accessible
    STATUS      current
    DESCRIPTION "This table sets the parameters to setup SLA throughput test
                 and captures the results."
    ::= { pvxEcfmService  8 }

pvxSLAThroughputTestEntry OBJECT-TYPE
    SYNTAX      PvxSLAThroughputTestEntry
    MAX-ACCESS  not-accessible
    STATUS      current
    DESCRIPTION "The throughput test table entry."
    INDEX { pvxSLAThroughputTestSwitchIdx,
		    pvxSLAThroughputTestShelfIdx,
			pvxSLAThroughputTestSlotIdx,
            pvxSLAThroughputTestPortTypeIdx,
    	    pvxSLAThroughputTestPortIdx,
            pvxSLAThroughputTestESName,
            pvxSLAThroughputTestRMepId
          }
    ::= { pvxSLAThroughputTestTable 1 }

PvxSLAThroughputTestEntry ::= SEQUENCE { pvxSLAThroughputTestSwitchIdx                      INTEGER,
                                         pvxSLAThroughputTestShelfIdx                       INTEGER,
                                         pvxSLAThroughputTestSlotIdx                        INTEGER,
                                         pvxSLAThroughputTestPortTypeIdx                    PvxPortType,
                                         pvxSLAThroughputTestPortIdx                        INTEGER,
                                         pvxSLAThroughputTestESName                         DisplayString,
                                         pvxSLAThroughputTestRMepId                         INTEGER,
                                         pvxSLAThroughputTestRole                           SlaTestRole,
                                         pvxSLAThroughputTestInitiatorCmdState              CommandStateType,
                                         pvxSLAThroughputTestResponderOpState               INTEGER,
                                         pvxSLAThroughputTestFrameSize1                     INTEGER,
                                         pvxSLAThroughputTestFrameSize2                     INTEGER,
                                         pvxSLAThroughputTestFrameSize3                     INTEGER,
                                         pvxSLAThroughputTestFrameSize4                     INTEGER,
                                         pvxSLAThroughputTestFrameSize5                     INTEGER,
                                         pvxSLAThroughputTestFrameSize6                     INTEGER,
                                         pvxSLAThroughputTestSrvcPolicyName                 DisplayString,
                                         pvxSLAThroughputTestClassMapName                   DisplayString,
                                         pvxSLAThroughputTestBwProfileName                  DisplayString,
                                         pvxSLAThroughputTestSVlanPriority                  INTEGER,
                                         pvxSLAThroughputTestCirRateTestResult              CirTestResult,
                                         pvxSLAThroughputTestFrameSize1FarEndThroughput     Unsigned32,
                                         pvxSLAThroughputTestFrameSize1NearEndThroughput    Unsigned32,
                                         pvxSLAThroughputTestFrameSize2FarEndThroughput     Unsigned32,
                                         pvxSLAThroughputTestFrameSize2NearEndThroughput    Unsigned32,
                                         pvxSLAThroughputTestFrameSize3FarEndThroughput     Unsigned32,
                                         pvxSLAThroughputTestFrameSize3NearEndThroughput    Unsigned32,
                                         pvxSLAThroughputTestFrameSize4FarEndThroughput     Unsigned32,
                                         pvxSLAThroughputTestFrameSize4NearEndThroughput    Unsigned32,
                                         pvxSLAThroughputTestFrameSize5FarEndThroughput     Unsigned32,
                                         pvxSLAThroughputTestFrameSize5NearEndThroughput    Unsigned32,
                                         pvxSLAThroughputTestFrameSize6FarEndThroughput     Unsigned32,
                                         pvxSLAThroughputTestFrameSize6NearEndThroughput    Unsigned32,
                                         pvxSLAThroughputTestRowStatus                      RowStatus }

                                  
pvxSLAThroughputTestSwitchIdx OBJECT-TYPE
   	SYNTAX       INTEGER(1..11)
   	MAX-ACCESS   not-accessible
   	STATUS       current
    DESCRIPTION  "The identifier of the ethernet switch instance on which the
                  Ethernet Service SLA is provisioned."
    ::= {pvxSLAThroughputTestEntry 1 }


pvxSLAThroughputTestShelfIdx OBJECT-TYPE
    SYNTAX       INTEGER (0|1|11|21|31)
    MAX-ACCESS   not-accessible
    STATUS       current
    DESCRIPTION  "The number of the shelf on which the Ethernet Service SLA targeted
                  for PMs is provisioned. For LAG entities, the shelf number is 0."
    ::= {pvxSLAThroughputTestEntry 2 }


pvxSLAThroughputTestSlotIdx OBJECT-TYPE
    SYNTAX       INTEGER (0|1|3|5|7|9|11|13|15|17|19)
    MAX-ACCESS   not-accessible
    STATUS       current
    DESCRIPTION  "The number of the slot within which the Ethernet Service SLA targeted
                  for PMs is provisioned. For LAG entities, the slot number is 0."
    ::= {pvxSLAThroughputTestEntry 3 }


pvxSLAThroughputTestPortTypeIdx OBJECT-TYPE
    SYNTAX       PvxPortType
    MAX-ACCESS   not-accessible
    STATUS       current
    DESCRIPTION  "The type of PacketVX port on which the Ethernet Service SLA
                  facility is provisioned."
    ::= {pvxSLAThroughputTestEntry 4 }


pvxSLAThroughputTestPortIdx OBJECT-TYPE
    SYNTAX       INTEGER (0..64)
    MAX-ACCESS   not-accessible
    STATUS       current
    DESCRIPTION  "The port number of the Ethernet Service SLA."
    ::= {pvxSLAThroughputTestEntry 5 }


pvxSLAThroughputTestESName OBJECT-TYPE
    SYNTAX       DisplayString
    MAX-ACCESS   not-accessible
    STATUS       current
    DESCRIPTION  "The Ethernet service name."
    ::= { pvxSLAThroughputTestEntry 6 }


pvxSLAThroughputTestRMepId OBJECT-TYPE
    SYNTAX       INTEGER (1..8191)
    MAX-ACCESS   not-accessible
    STATUS       current
    DESCRIPTION  "Remote MEP ID."
    ::= { pvxSLAThroughputTestEntry 7 }
    
pvxSLAThroughputTestRole OBJECT-TYPE
    SYNTAX       SlaTestRole
    MAX-ACCESS   read-create
    STATUS       current
    DESCRIPTION  "Set the test role, initiator or responder."
    ::= { pvxSLAThroughputTestEntry 8 }
    
pvxSLAThroughputTestInitiatorCmdState OBJECT-TYPE
    SYNTAX       CommandStateType
    MAX-ACCESS   read-create
    STATUS       current
    DESCRIPTION  "Set the initiator command state."
    ::= { pvxSLAThroughputTestEntry 9 }
    
pvxSLAThroughputTestResponderOpState OBJECT-TYPE
    SYNTAX       INTEGER { idle(1),
                           testInProgress(2),
                           rmepNotReady(3)
                          }
    MAX-ACCESS   read-only
    STATUS       current
    DESCRIPTION  "Test responder operational state."
    ::= { pvxSLAThroughputTestEntry 10 }
    
pvxSLAThroughputTestFrameSize1 OBJECT-TYPE
    SYNTAX       INTEGER (0..9600)
    MAX-ACCESS   read-create
    STATUS       current
    DESCRIPTION  "Frame size number 1."
    ::= { pvxSLAThroughputTestEntry 11 }

pvxSLAThroughputTestFrameSize2 OBJECT-TYPE
    SYNTAX       INTEGER (0..9600)
    MAX-ACCESS   read-create
    STATUS       current
    DESCRIPTION  "Frame size number 2."
    ::= { pvxSLAThroughputTestEntry 12 }

pvxSLAThroughputTestFrameSize3 OBJECT-TYPE
    SYNTAX       INTEGER (0..9600)
    MAX-ACCESS   read-create
    STATUS       current
    DESCRIPTION  "Frame size number 3."
    ::= { pvxSLAThroughputTestEntry 13 }

pvxSLAThroughputTestFrameSize4 OBJECT-TYPE
    SYNTAX       INTEGER (0..9600)
    MAX-ACCESS   read-create
    STATUS       current
    DESCRIPTION  "Frame size number 4."
    ::= { pvxSLAThroughputTestEntry 14 }

pvxSLAThroughputTestFrameSize5 OBJECT-TYPE
    SYNTAX       INTEGER (0..9600)
    MAX-ACCESS   read-create
    STATUS       current
    DESCRIPTION  "Frame size number 5."
    ::= { pvxSLAThroughputTestEntry 15 }

pvxSLAThroughputTestFrameSize6 OBJECT-TYPE
    SYNTAX       INTEGER (0..9600)
    MAX-ACCESS   read-create
    STATUS       current
    DESCRIPTION  "Frame size number 6."
    ::= { pvxSLAThroughputTestEntry 16 }
    
pvxSLAThroughputTestSrvcPolicyName OBJECT-TYPE
    SYNTAX       DisplayString
    MAX-ACCESS   read-create
    STATUS       current
    DESCRIPTION  "Service policy profile name."
    ::= { pvxSLAThroughputTestEntry 17 }

pvxSLAThroughputTestClassMapName OBJECT-TYPE
    SYNTAX       DisplayString
    MAX-ACCESS   read-create
    STATUS       current
    DESCRIPTION  "Class map profile name."
    ::= { pvxSLAThroughputTestEntry 18 }
 
pvxSLAThroughputTestBwProfileName OBJECT-TYPE
    SYNTAX       DisplayString
    MAX-ACCESS   read-create
    STATUS       current
    DESCRIPTION  "Bandwidth profile name."
    ::= { pvxSLAThroughputTestEntry 19 }

pvxSLAThroughputTestSVlanPriority OBJECT-TYPE
    SYNTAX       INTEGER (0..7)
    MAX-ACCESS   read-create
    STATUS       current
    DESCRIPTION  "SLA Throughput test S-Vlan priority."
    ::= { pvxSLAThroughputTestEntry 20 }    

pvxSLAThroughputTestCirRateTestResult OBJECT-TYPE
    SYNTAX       CirTestResult
    MAX-ACCESS   read-only
    STATUS       current
    DESCRIPTION  "Test result, pass or fail. Pass means 100% CIR has been met."
    ::= { pvxSLAThroughputTestEntry 21 }
       
pvxSLAThroughputTestFrameSize1FarEndThroughput OBJECT-TYPE
    SYNTAX       Unsigned32
    MAX-ACCESS   read-only
    STATUS       current
    DESCRIPTION  "Frame Size 1 far end throughput result in Mbps."
    ::= { pvxSLAThroughputTestEntry 22 }

pvxSLAThroughputTestFrameSize1NearEndThroughput OBJECT-TYPE
    SYNTAX       Unsigned32
    MAX-ACCESS   read-only
    STATUS       current
    DESCRIPTION  "Frame Size 1 near end throughput result in Mbps."
    ::= { pvxSLAThroughputTestEntry 23 }

pvxSLAThroughputTestFrameSize2FarEndThroughput OBJECT-TYPE
    SYNTAX       Unsigned32
    MAX-ACCESS   read-only
    STATUS       current
    DESCRIPTION  "Frame Size 2 far end throughput result in Mbps."
    ::= { pvxSLAThroughputTestEntry 24 }

pvxSLAThroughputTestFrameSize2NearEndThroughput OBJECT-TYPE
    SYNTAX       Unsigned32
    MAX-ACCESS   read-only
    STATUS       current
    DESCRIPTION  "Frame Size 2 near end throughput result in Mbps."
    ::= { pvxSLAThroughputTestEntry 25 }

pvxSLAThroughputTestFrameSize3FarEndThroughput OBJECT-TYPE
    SYNTAX       Unsigned32
    MAX-ACCESS   read-only
    STATUS       current
    DESCRIPTION  "Frame Size 3 far end throughput result in Mbps."
    ::= { pvxSLAThroughputTestEntry 26 }

pvxSLAThroughputTestFrameSize3NearEndThroughput OBJECT-TYPE
    SYNTAX       Unsigned32
    MAX-ACCESS   read-only
    STATUS       current
    DESCRIPTION  "Frame Size 3 near end throughput result in Mbps."
    ::= { pvxSLAThroughputTestEntry 27 }

pvxSLAThroughputTestFrameSize4FarEndThroughput OBJECT-TYPE
    SYNTAX       Unsigned32
    MAX-ACCESS   read-only
    STATUS       current
    DESCRIPTION  "Frame Size 4 far end throughput result in Mbps."
    ::= { pvxSLAThroughputTestEntry 28 }

pvxSLAThroughputTestFrameSize4NearEndThroughput OBJECT-TYPE
    SYNTAX       Unsigned32
    MAX-ACCESS   read-only
    STATUS       current
    DESCRIPTION  "Frame Size 4 near end throughput result in Mbps."
    ::= { pvxSLAThroughputTestEntry 29 }

pvxSLAThroughputTestFrameSize5FarEndThroughput OBJECT-TYPE
    SYNTAX       Unsigned32
    MAX-ACCESS   read-only
    STATUS       current
    DESCRIPTION  "Frame Size 5 far end throughput result in Mbps."
    ::= { pvxSLAThroughputTestEntry 30 }

pvxSLAThroughputTestFrameSize5NearEndThroughput OBJECT-TYPE
    SYNTAX       Unsigned32
    MAX-ACCESS   read-only
    STATUS       current
    DESCRIPTION  "Frame Size 5 near end throughput result in Mbps."
    ::= { pvxSLAThroughputTestEntry 31 }

pvxSLAThroughputTestFrameSize6FarEndThroughput OBJECT-TYPE
    SYNTAX       Unsigned32
    MAX-ACCESS   read-only
    STATUS       current
    DESCRIPTION  "Frame Size 6 far end throughput result in Mbps."
    ::= { pvxSLAThroughputTestEntry 32 }

pvxSLAThroughputTestFrameSize6NearEndThroughput OBJECT-TYPE
    SYNTAX       Unsigned32
    MAX-ACCESS   read-only
    STATUS       current
    DESCRIPTION  "Frame Size 6 near end throughput result in Mbps."
    ::= { pvxSLAThroughputTestEntry 33 }

pvxSLAThroughputTestRowStatus    OBJECT-TYPE
    SYNTAX      RowStatus
    MAX-ACCESS  read-create
    STATUS      current
    DESCRIPTION "The status of the row."
    ::= { pvxSLAThroughputTestEntry 100 }

-- ----------------------------------------------------------------
-- ----------------------------------------------------------------
-- The SLA Measurement Initiator DB Table 
-- ----------------------------------------------------------------
-- ----------------------------------------------------------------
pvxSLAMsmtInitiatorDBTable OBJECT-TYPE
    SYNTAX      SEQUENCE OF PvxSLAMsmtInitiatorDBEntry
    MAX-ACCESS  not-accessible
    STATUS      current
    DESCRIPTION "This table sets the SLA measurement Initiator
                 test command state."
    ::= { pvxEcfmService  9 }

pvxSLAMsmtInitiatorDBEntry OBJECT-TYPE
    SYNTAX      PvxSLAMsmtInitiatorDBEntry
    MAX-ACCESS  not-accessible
    STATUS      current
    DESCRIPTION "The SLA measurement initiator table entry."
    INDEX { pvxSLAMsmtInitiatorDBSwitchIdx,
		    pvxSLAMsmtInitiatorDBShelfIdx,
			pvxSLAMsmtInitiatorDBSlotIdx,
            pvxSLAMsmtInitiatorDBPortTypeIdx,
    	    pvxSLAMsmtInitiatorDBPortIdx,
            pvxSLAMsmtInitiatorDBESName,
            pvxSLAMsmtInitiatorDBRMepId
          }
    ::= { pvxSLAMsmtInitiatorDBTable 1 }

PvxSLAMsmtInitiatorDBEntry ::= SEQUENCE { pvxSLAMsmtInitiatorDBSwitchIdx                     INTEGER,
                                         pvxSLAMsmtInitiatorDBShelfIdx                       INTEGER,
                                         pvxSLAMsmtInitiatorDBSlotIdx                        INTEGER,
                                         pvxSLAMsmtInitiatorDBPortTypeIdx                    PvxPortType,
                                         pvxSLAMsmtInitiatorDBPortIdx                        INTEGER,
                                         pvxSLAMsmtInitiatorDBESName                         DisplayString,
                                         pvxSLAMsmtInitiatorDBRMepId                         INTEGER,
                                         pvxSLAMsmtInitiatorDBCmdState                       PmTestCmdState,                                                   
                                         pvxSLAMsmtInitiatorDBDelayMsmtSVlanPriority         INTEGER,                         
                                         pvxSLAMsmtInitiatorDBRowStatus                      RowStatus }

                                  
pvxSLAMsmtInitiatorDBSwitchIdx OBJECT-TYPE
   	SYNTAX       INTEGER(1..11)
   	MAX-ACCESS   not-accessible
   	STATUS       current
    DESCRIPTION  "The identifier of the ethernet switch instance on which the
                  Ethernet Service SLA is provisioned."
    ::= {pvxSLAMsmtInitiatorDBEntry 1 }


pvxSLAMsmtInitiatorDBShelfIdx OBJECT-TYPE
    SYNTAX       INTEGER (0|1|11|21|31)
    MAX-ACCESS   not-accessible
    STATUS       current
    DESCRIPTION  "The number of the shelf on which the Ethernet Service SLA targeted
                  for PMs is provisioned. For LAG entities, the shelf number is 0."
    ::= {pvxSLAMsmtInitiatorDBEntry 2 }


pvxSLAMsmtInitiatorDBSlotIdx OBJECT-TYPE
    SYNTAX       INTEGER (0|1|3|5|7|9|11|13|15|17|19)
    MAX-ACCESS   not-accessible
    STATUS       current
    DESCRIPTION  "The number of the slot within which the Ethernet Service SLA targeted
                  for PMs is provisioned. For LAG entities, the slot number is 0."
    ::= {pvxSLAMsmtInitiatorDBEntry 3 }


pvxSLAMsmtInitiatorDBPortTypeIdx OBJECT-TYPE
    SYNTAX       PvxPortType
    MAX-ACCESS   not-accessible
    STATUS       current
    DESCRIPTION  "The type of PacketVX port on which the Ethernet Service SLA
                  facility is provisioned."
    ::= {pvxSLAMsmtInitiatorDBEntry 4 }


pvxSLAMsmtInitiatorDBPortIdx OBJECT-TYPE
    SYNTAX       INTEGER (0..64)
    MAX-ACCESS   not-accessible
    STATUS       current
    DESCRIPTION  "The port number of the Ethernet Service SLA."
    ::= {pvxSLAMsmtInitiatorDBEntry 5 }


pvxSLAMsmtInitiatorDBESName OBJECT-TYPE
    SYNTAX       DisplayString
    MAX-ACCESS   not-accessible
    STATUS       current
    DESCRIPTION  "The Ethernet service name."
    ::= { pvxSLAMsmtInitiatorDBEntry 6 }


pvxSLAMsmtInitiatorDBRMepId OBJECT-TYPE
    SYNTAX       INTEGER (1..8191)
    MAX-ACCESS   not-accessible
    STATUS       current
    DESCRIPTION  "Remote MEP ID."
    ::= { pvxSLAMsmtInitiatorDBEntry 7 }
    
pvxSLAMsmtInitiatorDBCmdState OBJECT-TYPE
    SYNTAX       PmTestCmdState
    MAX-ACCESS   read-create
    STATUS       current
    DESCRIPTION  "Set the PM frame loss test command state."
    ::= { pvxSLAMsmtInitiatorDBEntry 8 }
    
pvxSLAMsmtInitiatorDBDelayMsmtSVlanPriority OBJECT-TYPE
    SYNTAX       INTEGER (0..7)
    MAX-ACCESS   read-create
    STATUS       current
    DESCRIPTION  "Set the PM frame delay test s-vlan priority."
    ::= { pvxSLAMsmtInitiatorDBEntry 9 }
    
pvxSLAMsmtInitiatorDBRowStatus    OBJECT-TYPE
    SYNTAX      RowStatus
    MAX-ACCESS  read-create
    STATUS      current
    DESCRIPTION "The status of the row."
    ::= { pvxSLAMsmtInitiatorDBEntry 100 }
    
-- ----------------------------------------------------------------
-- ----------------------------------------------------------------
-- The SLA Measurement Responder DB Table 
-- ----------------------------------------------------------------
-- ----------------------------------------------------------------
pvxSLAMsmtResponderDBTable OBJECT-TYPE
    SYNTAX      SEQUENCE OF PvxSLAMsmtResponderDBEntry
    MAX-ACCESS  not-accessible
    STATUS      current
    DESCRIPTION "This table keeps a record of responder MEP IDs."
    ::= { pvxEcfmService  10 }

pvxSLAMsmtResponderDBEntry OBJECT-TYPE
    SYNTAX      PvxSLAMsmtResponderDBEntry
    MAX-ACCESS  not-accessible
    STATUS      current
    DESCRIPTION "The SLA measurement responder table entry."
    INDEX { pvxSLAMsmtResponderDBSwitchIdx,
            pvxSLAMsmtResponderDBShelfIdx,
            pvxSLAMsmtResponderDBSlotIdx,
            pvxSLAMsmtResponderDBPortTypeIdx,
    	    pvxSLAMsmtResponderDBPortIdx,
            pvxSLAMsmtResponderDBESName,
            pvxSLAMsmtResponderDBRMepId
          }
    ::= { pvxSLAMsmtResponderDBTable 1 }

PvxSLAMsmtResponderDBEntry ::= SEQUENCE { pvxSLAMsmtResponderDBSwitchIdx                     INTEGER,
                                         pvxSLAMsmtResponderDBShelfIdx                       INTEGER,
                                         pvxSLAMsmtResponderDBSlotIdx                        INTEGER,
                                         pvxSLAMsmtResponderDBPortTypeIdx                    PvxPortType,
                                         pvxSLAMsmtResponderDBPortIdx                        INTEGER,
                                         pvxSLAMsmtResponderDBESName                         DisplayString,
                                         pvxSLAMsmtResponderDBRMepId                         INTEGER,                          
                                         pvxSLAMsmtResponderDBRowStatus                      RowStatus }

                                  
pvxSLAMsmtResponderDBSwitchIdx OBJECT-TYPE
   	SYNTAX       INTEGER(1..11)
   	MAX-ACCESS   not-accessible
   	STATUS       current
    DESCRIPTION  "The identifier of the ethernet switch instance on which the
                  Ethernet Service SLA is provisioned."
    ::= {pvxSLAMsmtResponderDBEntry 1 }


pvxSLAMsmtResponderDBShelfIdx OBJECT-TYPE
    SYNTAX       INTEGER (0|1|11|21|31)
    MAX-ACCESS   not-accessible
    STATUS       current
    DESCRIPTION  "The number of the shelf on which the Ethernet Service SLA targeted
                  for PMs is provisioned. For LAG entities, the shelf number is 0."
    ::= {pvxSLAMsmtResponderDBEntry 2 }


pvxSLAMsmtResponderDBSlotIdx OBJECT-TYPE
    SYNTAX       INTEGER (0|1|3|5|7|9|11|13|15|17|19)
    MAX-ACCESS   not-accessible
    STATUS       current
    DESCRIPTION  "The number of the slot within which the Ethernet Service SLA targeted
                  for PMs is provisioned. For LAG entities, the slot number is 0."
    ::= {pvxSLAMsmtResponderDBEntry 3 }


pvxSLAMsmtResponderDBPortTypeIdx OBJECT-TYPE
    SYNTAX       PvxPortType
    MAX-ACCESS   not-accessible
    STATUS       current
    DESCRIPTION  "The type of PacketVX port on which the Ethernet Service SLA
                  facility is provisioned."
    ::= {pvxSLAMsmtResponderDBEntry 4 }


pvxSLAMsmtResponderDBPortIdx OBJECT-TYPE
    SYNTAX       INTEGER (0..64)
    MAX-ACCESS   not-accessible
    STATUS       current
    DESCRIPTION  "The port number of the Ethernet Service SLA."
    ::= {pvxSLAMsmtResponderDBEntry 5 }


pvxSLAMsmtResponderDBESName OBJECT-TYPE
    SYNTAX       DisplayString
    MAX-ACCESS   not-accessible
    STATUS       current
    DESCRIPTION  "The Ethernet service name."
    ::= { pvxSLAMsmtResponderDBEntry 6 }


pvxSLAMsmtResponderDBRMepId OBJECT-TYPE
    SYNTAX       INTEGER (1..8191)
    MAX-ACCESS   not-accessible
    STATUS       current
    DESCRIPTION  "Remote MEP ID."
    ::= { pvxSLAMsmtResponderDBEntry 7 }

pvxSLAMsmtResponderDBRowStatus    OBJECT-TYPE
    SYNTAX      RowStatus
    MAX-ACCESS  read-create
    STATUS      current
    DESCRIPTION "The status of the row."
    ::= { pvxSLAMsmtResponderDBEntry 100 }
    
-----------------------------------------------------------------------
--  pvxSwitchCpuRLMonTable  Table
-----------------------------------------------------------------------
pvxSwitchCpuRLMonTable OBJECT-TYPE
    SYNTAX       SEQUENCE OF PVXSwitchCpuRLMonEntry
    MAX-ACCESS   not-accessible
    STATUS       current
    DESCRIPTION  "This table is used to get cpu-rate-limit statistic of virtual-switch."
    ::= { pvxBridge 26 }

pvxSwitchCpuRLMonEntry OBJECT-TYPE
    SYNTAX       PVXSwitchCpuRLMonEntry
    MAX-ACCESS   not-accessible
    STATUS       current
    DESCRIPTION  "The cpu-rate-limit statistic entry."
    INDEX        {
                    pvxSwitchCpuRLMonSwitchIdx,
                    pvxSwitchCpuRLMonShelfIdx,
                    pvxSwitchCpuRLMonSlotIdx,
                    pvxSwitchCpuRLMonCosIdx
                 }
    ::= { pvxSwitchCpuRLMonTable 1 }

PVXSwitchCpuRLMonEntry ::= SEQUENCE { pvxSwitchCpuRLMonSwitchIdx                       INTEGER,
                                      pvxSwitchCpuRLMonShelfIdx                        INTEGER,
                                      pvxSwitchCpuRLMonSlotIdx                         INTEGER,
                                      pvxSwitchCpuRLMonCosIdx                          INTEGER,
                                      pvxSwitchCpuRLMonCosCurrDepth                    Integer32,
                                      pvxSwitchCpuRLMonCosReceived                     Integer32,
                                      pvxSwitchCpuRLMonCosDiscards                     Integer32,
                                      pvxSwitchCpuRLMonCosMinDepth60Sec                Integer32,
                                      pvxSwitchCpuRLMonCosMaxDepth60Sec                Integer32,
                                      pvxSwitchCpuRLMonCosReceived60Sec                Integer32,
                                      pvxSwitchCpuRLMonCosDiscards60Sec                Integer32,
                                      pvxSwitchCpuRLMonCosDiscardsTotal                Integer32,
                                      pvxSwitchCpuRLMonCosReceivedRateLimit            Integer32,
                                      pvxSwitchCpuRLMonCosMaxAllowedDepth              Integer32,
                                      pvxSwitchCpuRLMonCosHighWatermark                Integer32,
                                      pvxSwitchCpuRLMonCosHighWatermark60Sec           Integer32,
                                      pvxSwitchCpuRLMonCosHighestWatermark             Integer32}
                                
pvxSwitchCpuRLMonSwitchIdx OBJECT-TYPE
    SYNTAX       INTEGER (1..11)
    MAX-ACCESS   not-accessible
    STATUS       current
    DESCRIPTION  "This object represents the particular switch id."
    ::= {pvxSwitchCpuRLMonEntry 1 }

pvxSwitchCpuRLMonShelfIdx OBJECT-TYPE
    SYNTAX       INTEGER (0|1|11|21|31)
    MAX-ACCESS   not-accessible
    STATUS       current
    DESCRIPTION  "The shelf number."
    ::= {pvxSwitchCpuRLMonEntry 2 }

pvxSwitchCpuRLMonSlotIdx OBJECT-TYPE
    SYNTAX       INTEGER (0|1|3|5|7|9|11|13|15|17|19)
    MAX-ACCESS   not-accessible
    STATUS       current
    DESCRIPTION  "The slot number."
    ::= {pvxSwitchCpuRLMonEntry 3 }

pvxSwitchCpuRLMonCosIdx OBJECT-TYPE
    SYNTAX       INTEGER (0..8)
    MAX-ACCESS   not-accessible
    STATUS       current
    DESCRIPTION  "The cos-queue number. Cos 8 represents CFA queue"
    ::= {pvxSwitchCpuRLMonEntry 4 }

pvxSwitchCpuRLMonCosCurrDepth OBJECT-TYPE
    SYNTAX       Integer32
    MAX-ACCESS   read-only
    STATUS       current
    DESCRIPTION  "Cos current depth."
    ::= {pvxSwitchCpuRLMonEntry 5 }

pvxSwitchCpuRLMonCosReceived OBJECT-TYPE
    SYNTAX       Integer32
    MAX-ACCESS   read-only
    STATUS       current
    DESCRIPTION  "Cos current received."
    ::= {pvxSwitchCpuRLMonEntry 6 }

pvxSwitchCpuRLMonCosDiscards OBJECT-TYPE
    SYNTAX       Integer32
    MAX-ACCESS   read-only
    STATUS       current
    DESCRIPTION  "Cos current discards."
    ::= {pvxSwitchCpuRLMonEntry 7 }

pvxSwitchCpuRLMonCosMinDepth60Sec OBJECT-TYPE
    SYNTAX       Integer32
    MAX-ACCESS   read-only
    STATUS       current
    DESCRIPTION  "Cos minimum depth in the past 60 seconds."
    ::= {pvxSwitchCpuRLMonEntry 8 }

pvxSwitchCpuRLMonCosMaxDepth60Sec OBJECT-TYPE
    SYNTAX       Integer32
    MAX-ACCESS   read-only
    STATUS       current
    DESCRIPTION  "Cos maximum depth in the past 60 seconds."
    ::= {pvxSwitchCpuRLMonEntry 9 }

pvxSwitchCpuRLMonCosReceived60Sec OBJECT-TYPE
    SYNTAX       Integer32
    MAX-ACCESS   read-only
    STATUS       current
    DESCRIPTION  "Cos received in the past 60 seconds."
    ::= {pvxSwitchCpuRLMonEntry 10 }

pvxSwitchCpuRLMonCosDiscards60Sec OBJECT-TYPE
    SYNTAX       Integer32
    MAX-ACCESS   read-only
    STATUS       current
    DESCRIPTION  "Cos discards in the past 60 seconds."
    ::= {pvxSwitchCpuRLMonEntry 11 }

pvxSwitchCpuRLMonCosDiscardsTotal OBJECT-TYPE
    SYNTAX       Integer32
    MAX-ACCESS   read-only
    STATUS       current
    DESCRIPTION  "Cos total number of discards since last reboot."
    ::= {pvxSwitchCpuRLMonEntry 12 }

pvxSwitchCpuRLMonCosReceivedRateLimit OBJECT-TYPE
    SYNTAX       Integer32
    MAX-ACCESS   read-only
    STATUS       current
    DESCRIPTION  "Cos rate limit."
    ::= {pvxSwitchCpuRLMonEntry 13 }

pvxSwitchCpuRLMonCosMaxAllowedDepth OBJECT-TYPE
    SYNTAX       Integer32
    MAX-ACCESS   read-only
    STATUS       current
    DESCRIPTION  "Cos max allowed depth."
    ::= {pvxSwitchCpuRLMonEntry 14 }

pvxSwitchCpuRLMonCosHighWatermark OBJECT-TYPE
    SYNTAX       Integer32
    MAX-ACCESS   read-only
    STATUS       current
    DESCRIPTION  "Cos highwater mark."
    ::= {pvxSwitchCpuRLMonEntry 15 }

pvxSwitchCpuRLMonCosHighWatermark60Sec OBJECT-TYPE
    SYNTAX       Integer32
    MAX-ACCESS   read-only
    STATUS       current
    DESCRIPTION  "Cos highwater mark in the past 60 seconds."
    ::= {pvxSwitchCpuRLMonEntry 16 }

pvxSwitchCpuRLMonCosHighestWatermark OBJECT-TYPE
    SYNTAX       Integer32
    MAX-ACCESS   read-only
    STATUS       current
    DESCRIPTION  "Cos highest water mark."
    ::= {pvxSwitchCpuRLMonEntry 17 }
    
-------------------------------------------------------------------
-- Station loopback
-------------------------------------------------------------------
pvxStationLoopback OBJECT IDENTIFIER ::= { pvxEcfmService  11  }
-- ----------------------------------------------------------------
-- Station loopback Table
-- ----------------------------------------------------------------
pvxSLBTable OBJECT-TYPE
    SYNTAX      SEQUENCE OF PVXSLBEntry
    MAX-ACCESS  not-accessible
    STATUS      current
    DESCRIPTION "This table is used to configur station loopback and display statistic on the switch."
    ::= { pvxStationLoopback  1 }

pvxSLBEntry OBJECT-TYPE
    SYNTAX      PVXSLBEntry
    MAX-ACCESS  not-accessible
    STATUS      current
    DESCRIPTION "The station loopback global table entry."
    INDEX { pvxSLBSwitchIdx }
    ::= { pvxSLBTable 1 }

PVXSLBEntry ::= SEQUENCE { pvxSLBSwitchIdx                      INTEGER,
                           pvxSLBEnable                         INTEGER,
                           pvxSLBMacRecordEnable                INTEGER,
                           pvxSLBLast10SwapMac                  DisplayString,
                           pvxSLB10UniqueSwapMac                DisplayString,
                           pvxSLBMacSwapCounterRX               Unsigned32,
                           pvxSLBMacSwapCounterTX               Unsigned32,
                           pvxSLBStatisticsClear                INTEGER}


pvxSLBSwitchIdx OBJECT-TYPE
   	SYNTAX       INTEGER(1..11)
   	MAX-ACCESS   not-accessible
   	STATUS       current
    DESCRIPTION  "The identifier of the ethernet switch instance on which the station loopback is provisioned."
    ::= {pvxSLBEntry 1 }


pvxSLBEnable OBJECT-TYPE
    SYNTAX       INTEGER { enabled  (1),
                           disabled (2) }
    MAX-ACCESS   read-create
    STATUS       current
    DESCRIPTION  "This attribute is used to enable/disable the station loopback on the switch."
    DEFVAL       { disabled }
    ::= { pvxSLBEntry 2 }

pvxSLBMacRecordEnable OBJECT-TYPE
    SYNTAX       INTEGER { enabled  (1),
                           disabled (2) }
    MAX-ACCESS   read-create
    STATUS       current
    DESCRIPTION  "This attribute is used to enable/disable the MAC record for station loopback on the switch."
    DEFVAL       { disabled }
    ::= { pvxSLBEntry 3 }

pvxSLBLast10SwapMac OBJECT-TYPE
    SYNTAX       DisplayString (SIZE(120))
    MAX-ACCESS   read-only
    STATUS       current
    DESCRIPTION  "The source and destination MAC address of the last 10 frames swapped.
                  Fixed 120 bytes. It can save ten couples of source and destination MAC at most. 
                  MAC is saved by Hexadecimal Values. For example, if one frame with source 
                  MAC <00:E0:FC:00:00:01> and destination MAC <00:E0:FC:00:00:02> is recorded, 
                  then the first 12 bytes is <00E0FC00000200E0FC000001>,the other 108 bytes are zeros"
    ::= {pvxSLBEntry 4 }

pvxSLB10UniqueSwapMac OBJECT-TYPE
    SYNTAX       DisplayString (SIZE(120))
    MAX-ACCESS   read-only
    STATUS       current
    DESCRIPTION  "The source and destination MAC address of the last 10 frames swapped with different 
                  source and destination MAC. 
                  Fixed 120 bytes. It can save ten couples of source and destination MAC at most. 
                  MAC is saved by Hexadecimal Values. For example, if one frame with source 
                  MAC <00:E0:FC:00:00:01> and destination MAC <00:E0:FC:00:00:02> is recorded, 
                  then the first 12 bytes is <00E0FC00000200E0FC000001>,the other 108 bytes are zeros"
    ::= {pvxSLBEntry 5 }

pvxSLBMacSwapCounterRX OBJECT-TYPE
    SYNTAX       Unsigned32
    MAX-ACCESS   read-only
    STATUS       current
    DESCRIPTION  "This attribute is used to display the receive packet counter for station loopback on the switch."
    ::= { pvxSLBEntry 6 }

pvxSLBMacSwapCounterTX OBJECT-TYPE
    SYNTAX       Unsigned32
    MAX-ACCESS   read-create
    STATUS       current
    DESCRIPTION  "This attribute is used to display the transmit packet counter for station loopback on the switch."
    ::= { pvxSLBEntry 7 }

pvxSLBStatisticsClear OBJECT-TYPE
    SYNTAX       TruthValue
    MAX-ACCESS   read-create
    STATUS       current
    DESCRIPTION  "An action trigger object. Setting the value of this object to 'true' will cause the switch 
                  to clear out all of the statistics information. When reading this object, 
                  the value 'false' always will be returned."
    ::= { pvxSLBEntry 8 }

-- ----------------------------------------------------------------
-- Station loopback global instance Table
-- ----------------------------------------------------------------
pvxSLBInstTable OBJECT-TYPE
    SYNTAX      SEQUENCE OF PVXSLBInstEntry
    MAX-ACCESS  not-accessible
    STATUS      current
    DESCRIPTION "This table is used to configur station loopback and class-map on the switch."
    ::= { pvxStationLoopback 2 }

pvxSLBInstEntry OBJECT-TYPE
    SYNTAX      PVXSLBInstEntry
    MAX-ACCESS  not-accessible
    STATUS      current
    DESCRIPTION "The station loopback global instance table entry."
    INDEX { pvxSLBInstSwitchIdx,
            pvxSLBInstName}
    ::= { pvxSLBInstTable 1 }

PVXSLBInstEntry ::= SEQUENCE { pvxSLBInstSwitchIdx          INTEGER,
                               pvxSLBInstName               DisplayString,
                               pvxSLBInstSVlanId            INTEGER,
                               pvxSLBInstClassmap           DisplayString,
                               pvxSLBInstCmdState           CommandStateType,
                               pvxSLBInstRowStatus          RowStatus}

pvxSLBInstSwitchIdx OBJECT-TYPE
   	SYNTAX       INTEGER(1..11)
   	MAX-ACCESS   not-accessible
   	STATUS       current
    DESCRIPTION  "The identifier of the ethernet switch instance on which the station loopback is provisioned."
    ::= {pvxSLBInstEntry 1 }

pvxSLBInstName OBJECT-TYPE
    SYNTAX       DisplayString (SIZE(1..32))
    MAX-ACCESS   not-accessible
    STATUS       current
    DESCRIPTION  "The name of the station loopback instance is provisioned."
    ::= {pvxSLBInstEntry 2 }

pvxSLBInstSVlanId OBJECT-TYPE
    SYNTAX       INTEGER (1..4094)
    MAX-ACCESS   read-create
    STATUS       current
    DESCRIPTION  "The s-vlan ID of the station loopback is provisioned."
    ::= {pvxSLBInstEntry 3 }

pvxSLBInstClassmap OBJECT-TYPE
    SYNTAX       DisplayString
    MAX-ACCESS   read-create
    STATUS       current
    DESCRIPTION  "The class-map of the station loopback is provisioned."
    ::= {pvxSLBInstEntry 4 }

pvxSLBInstCmdState OBJECT-TYPE
    SYNTAX       CommandStateType
    MAX-ACCESS   read-create
    STATUS       current
    DESCRIPTION  "Set the instance command state, only suppport start(2) and step(5)."
    ::= { pvxSLBInstEntry 5 }

pvxSLBInstRowStatus OBJECT-TYPE
    SYNTAX      RowStatus
    MAX-ACCESS  read-create
    STATUS      current
    DESCRIPTION "The status of the row."
    ::= { pvxSLBInstEntry 100 }
    
END
