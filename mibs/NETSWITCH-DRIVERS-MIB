-- HP Enterprise NETSWITCH DRIVERS MIB 


          NETSWITCH-DRIVERS-MIB DEFINITIONS ::= BEGIN

          IMPORTS
                       enterprises
                           FROM RFC1155-SMI
                       OBJECT-TYPE
			   FROM RFC-1212;

          hp		OBJECT IDENTIFIER ::= { enterprises 11 }
          nm		OBJECT IDENTIFIER ::= { hp 2 }
	  icf		OBJECT IDENTIFIER ::= { nm 14 }


          -- Icf Devices 

          hpicfObjects  OBJECT IDENTIFIER ::= { icf 11 }
          hpicfSwitch   OBJECT IDENTIFIER ::= { hpicfObjects 5 }
          hpSwitch      OBJECT IDENTIFIER ::= { hpicfSwitch  1 }

          -- Icf Switch Specific 
          hpOpSystem    OBJECT IDENTIFIER ::= { hpSwitch 1 }
          hpHwSystem    OBJECT IDENTIFIER ::= { hpSwitch 2 }

          -- ###########################################################
          -- the hpDriverStats Group
          -- Provide statistics of low-level drivers in a switch
          -- such as FDDI, ATM, etc.

          -- ###########################################################

          hpDriverStats    OBJECT IDENTIFIER ::= { hpHwSystem 3 }

          -- the Driver Statistic Table
          -- This table contains the common statistic for all HP Switch Port
          -- drivers

          hpDriverStatsTable OBJECT-TYPE
                SYNTAX  SEQUENCE OF HpDriverStatsEntry 
                ACCESS  not-accessible 
                STATUS  mandatory 
                DESCRIPTION 
                      "A list of driver entries. "  
              ::= { hpDriverStats 1 }         

          hpDriverStatsEntry OBJECT-TYPE 
              SYNTAX  HpDriverStatsEntry 
              ACCESS  not-accessible 
              STATUS  mandatory 
              DESCRIPTION 
                      "A driver entry containing information common to  
                      all drivers." 
              INDEX   { hpDriverStatsIndex } 
              ::= { hpDriverStatsTable 1 } 
 
          HpDriverStatsEntry ::=
              SEQUENCE {
                hpDriverStatsIndex
                        INTEGER,
                hpDriverStatsType
                        OCTET STRING,
                hpDriverStatsOctetsRxOk
                        INTEGER,
                hpDriverStatsFrameRxOk
                        INTEGER,
                hpDriverStatsTotalRxError
                        INTEGER,
                hpDriverStatsOctetTxOk
                        INTEGER,
                hpDriverStatsFrameTxOk
                        INTEGER,
                hpDriverStatsTotalTxError
                        INTEGER,
                hpDriverStatsOctetsRxPerSec
                        INTEGER,
                hpDriverStatsPeakOctetsRx
                        INTEGER,
                hpDriverStatsFramesRxPerSec
                        INTEGER,
                hpDriverStatsPeakFramesRx
                        INTEGER,
                hpDriverStatsOctetsTxPerSec
                        INTEGER,
                hpDriverStatsPeakOctetsTx
                        INTEGER,
                hpDriverStatsFramesTxPerSec
                        INTEGER,
                hpDriverStatsPeakFramesTx
                        INTEGER
                }

          hpDriverStatsIndex OBJECT-TYPE 
              SYNTAX  INTEGER (1..65535) 
              ACCESS  read-only 
              STATUS  mandatory 
              DESCRIPTION 
                      "A unique value for each driver.  The value for each 
                      driver must remain constant at least from one re- 
                      initialization of the entity's network management 
                      system to the next re-initialization." 
              ::= { hpDriverStatsEntry 1 } 

          hpDriverStatsType OBJECT-TYPE 
              SYNTAX  OCTET STRING (SIZE (10))
              ACCESS  read-only 
              STATUS  mandatory 
              DESCRIPTION 
                      "Type of driver, FDDI, ATM, SPITFIRE, etc. "
              ::= { hpDriverStatsEntry 2 } 

          hpDriverStatsOctetsRxOk OBJECT-TYPE 
              SYNTAX  INTEGER 
              ACCESS  read-only 
              STATUS  mandatory 
              DESCRIPTION 
                      "The number of octets received by the driver
                       including the FCS but not including framing
                       bits."
              ::= { hpDriverStatsEntry 3 } 

          hpDriverStatsFrameRxOk OBJECT-TYPE 
              SYNTAX  INTEGER 
              ACCESS  read-only 
              STATUS  mandatory 
              DESCRIPTION 
                      "The number of frames received by the driver."
              ::= { hpDriverStatsEntry 4 } 

          hpDriverStatsTotalRxError OBJECT-TYPE 
              SYNTAX  INTEGER 
              ACCESS  read-only 
              STATUS  mandatory 
              DESCRIPTION 
                      "The total number of receive errors."
              ::= { hpDriverStatsEntry 5 } 

          hpDriverStatsOctetTxOk OBJECT-TYPE 
              SYNTAX  INTEGER 
              ACCESS  read-only 
              STATUS  mandatory 
              DESCRIPTION 
                      "The number of octets transmitted by the driver
                       including the FCS but not including framing
                       bits."
              ::= { hpDriverStatsEntry 6 } 

          hpDriverStatsFrameTxOk OBJECT-TYPE 
              SYNTAX  INTEGER 
              ACCESS  read-only 
              STATUS  mandatory 
              DESCRIPTION 
                      "The number of frames transmitted by the driver."
              ::= { hpDriverStatsEntry 7 } 

          hpDriverStatsTotalTxError OBJECT-TYPE 
              SYNTAX  INTEGER 
              ACCESS  read-only 
              STATUS  mandatory 
              DESCRIPTION 
                      "The total number of transmit errors."
              ::= { hpDriverStatsEntry 8 } 

          hpDriverStatsOctetsRxPerSec OBJECT-TYPE 
              SYNTAX  INTEGER 
              ACCESS  read-only 
              STATUS  mandatory 
              DESCRIPTION 
                      "The number of octets received by the driver during
                       the previous one second sample period."
              ::= { hpDriverStatsEntry 9 } 

          hpDriverStatsPeakOctetsRx OBJECT-TYPE 
              SYNTAX  INTEGER 
              ACCESS  read-only 
              STATUS  mandatory 
              DESCRIPTION 
                      "The highest number of octets received by the driver
                       during one second sample periods."
              ::= { hpDriverStatsEntry 10 } 

          hpDriverStatsFramesRxPerSec OBJECT-TYPE 
              SYNTAX  INTEGER 
              ACCESS  read-only 
              STATUS  mandatory 
              DESCRIPTION 
                      "The number of frames received by the driver during
                       the previous one second sample period."
              ::= { hpDriverStatsEntry 11 } 

          hpDriverStatsPeakFramesRx OBJECT-TYPE 
              SYNTAX  INTEGER 
              ACCESS  read-only 
              STATUS  mandatory 
              DESCRIPTION 
                      "The highest number of frames received by the driver
                       during one second sample periods."
              ::= { hpDriverStatsEntry 12 } 

          hpDriverStatsOctetsTxPerSec OBJECT-TYPE 
              SYNTAX  INTEGER 
              ACCESS  read-only 
              STATUS  mandatory 
              DESCRIPTION 
                      "The number of octets transmitted by the driver during
                       the previous one second sample period."
              ::= { hpDriverStatsEntry 13 } 

          hpDriverStatsPeakOctetsTx OBJECT-TYPE 
              SYNTAX  INTEGER 
              ACCESS  read-only 
              STATUS  mandatory 
              DESCRIPTION 
                      "The highest number of octets transmitted by the driver
                       during one second sample periods. "
              ::= { hpDriverStatsEntry 14 } 

          hpDriverStatsFramesTxPerSec OBJECT-TYPE 
              SYNTAX  INTEGER 
              ACCESS  read-only 
              STATUS  mandatory 
              DESCRIPTION 
                      "The number of frames transmitted by the driver during
                       the previous one second sample period "
              ::= { hpDriverStatsEntry 15 } 

          hpDriverStatsPeakFramesTx OBJECT-TYPE 
              SYNTAX  INTEGER 
              ACCESS  read-only 
              STATUS  mandatory 
              DESCRIPTION 
                      "The highest number of frames transmitted by the driver
                       during one second sample periods. "
              ::= { hpDriverStatsEntry 16 } 

          -- the FDDI Driver Statistic Table

          hpFddiDriverStatsTable OBJECT-TYPE
                SYNTAX  SEQUENCE OF HpFddiDriverStatsEntry 
                ACCESS  not-accessible 
                STATUS  mandatory 
                DESCRIPTION 
                      "A list of FDDI driver entries. "  
              ::= { hpDriverStats 2 }         

          hpFddiDriverStatsEntry OBJECT-TYPE 
              SYNTAX  HpFddiDriverStatsEntry 
              ACCESS  not-accessible 
              STATUS  mandatory 
              DESCRIPTION 
                      "A FDDI driver entry containing information common to a 
                      given driver." 
              INDEX   { hpFddiDriverStatsIndex } 
              ::= { hpFddiDriverStatsTable 1 } 
 
          HpFddiDriverStatsEntry ::=
              SEQUENCE {
                hpFddiDriverStatsIndex
                        INTEGER,
                hpFddiDriverStatsSMTOctetsRxOk
                        INTEGER,
                hpFddiDriverStatsSMTFrameRxOk
                        INTEGER,
                hpFddiDriverStatsSMTOctetsTxOk
                        INTEGER,
                hpFddiDriverStatsSMTFrameTxOk
                        INTEGER,
                hpFddiDriverStatsErrRxCRC
                        INTEGER,
                hpFddiDriverStatsErrRxOverrun
                        INTEGER,
                hpFddiDriverStatsErrRxParity
                        INTEGER,
                hpFddiDriverStatsErrRxMACStatus
                        INTEGER,
                hpFddiDriverStatsErrTxAbort
                        INTEGER,
                hpFddiDriverStatsErrTxUnderrun
                        INTEGER,
                hpFddiDriverStatsErrTxParity
                        INTEGER,
                hpFddiDriverStatsErrGsrLlcTxRer
                        INTEGER,
                hpFddiDriverStatsErrGsrLlcRxRer
                        INTEGER,
                hpFddiDriverStatsErrGsrSMTTxRer
                        INTEGER,
                hpFddiDriverStatsErrGsrSMTRxRer
                        INTEGER,
                hpFddiDriverStatsErrGsrPortOp
                        INTEGER,
                hpFddiDriverStatsErrGsrLlcRxRov
                        INTEGER,
                hpFddiDriverStatsErrGsrSMTRxRov
                        INTEGER,
                hpFddiDriverStatsErrGsrInternalOp
                        INTEGER,
                hpFddiDriverStatsIoeMov
                        INTEGER,
                hpFddiDriverStatsErrGsrHost
                        INTEGER,
                hpFddiDriverStatsTxCongestion
                        INTEGER,
                hpFddiDriverStatsMissedCmd
                        INTEGER,
                hpFddiDriverStatsMissedCRF
                        INTEGER
          }                                  

          hpFddiDriverStatsIndex OBJECT-TYPE 
              SYNTAX  INTEGER (1..65535) 
              ACCESS  read-only 
              STATUS  mandatory 
              DESCRIPTION 
                      "A unique value for each driver.  The value for each 
                      driver must remain constant at least from one re- 
                      initialization of the entity's network management 
                      system to the next re-initialization." 
              ::= { hpFddiDriverStatsEntry 1 } 


          hpFddiDriverStatsSMTOctetsRxOk OBJECT-TYPE 
              SYNTAX  INTEGER 
              ACCESS  read-only 
              STATUS  mandatory 
              DESCRIPTION 
                      "The number of SMT octets received by the driver
                       including the FCS but not including framing
                       bits."
              ::= { hpFddiDriverStatsEntry 2 } 

          hpFddiDriverStatsSMTFrameRxOk OBJECT-TYPE 
              SYNTAX  INTEGER 
              ACCESS  read-only 
              STATUS  mandatory 
              DESCRIPTION 
                      "The number of SMT frames received by the driver."
              ::= { hpFddiDriverStatsEntry 3 } 

          hpFddiDriverStatsSMTOctetsTxOk OBJECT-TYPE 
              SYNTAX  INTEGER 
              ACCESS  read-only 
              STATUS  mandatory 
              DESCRIPTION 
                      "The number of SMT octets transmitted by the driver
                       including the FCS but not including framing bits."
              ::= { hpFddiDriverStatsEntry 4 } 

          hpFddiDriverStatsSMTFrameTxOk OBJECT-TYPE 
              SYNTAX  INTEGER 
              ACCESS  read-only 
              STATUS  mandatory 
              DESCRIPTION 
                      "The number of SMT frames transmitted by the driver."
              ::= { hpFddiDriverStatsEntry 5 } 

          hpFddiDriverStatsErrRxCRC OBJECT-TYPE 
              SYNTAX  INTEGER 
              ACCESS  read-only 
              STATUS  mandatory 
              DESCRIPTION 
                      "The number of received frames containing a CRC
                       error detected by the FDDI network interface chip."
              ::= { hpFddiDriverStatsEntry 6 } 

          hpFddiDriverStatsErrRxOverrun OBJECT-TYPE 
              SYNTAX  INTEGER 
              ACCESS  read-only 
              STATUS  mandatory 
              DESCRIPTION 
                      "The number of received frames that are invalid
                       due to overrun conditions in the FSI of the
                       MC68840 FDDI network interface chip."
              ::= { hpFddiDriverStatsEntry 7 } 

          hpFddiDriverStatsErrRxParity OBJECT-TYPE 
              SYNTAX  INTEGER 
              ACCESS  read-only 
              STATUS  mandatory 
              DESCRIPTION 
                      "The number of received frames containing a parity
                       error detected by the FDDI network interface chip."
              ::= { hpFddiDriverStatsEntry 8 } 

          hpFddiDriverStatsErrRxMACStatus OBJECT-TYPE 
              SYNTAX  INTEGER 
              ACCESS  read-only 
              STATUS  mandatory 
              DESCRIPTION 
                      "The number of received frames generating MAC
                       status errors in the MC68840 FDDI network interface
                       chip."
              ::= { hpFddiDriverStatsEntry 9 } 

          hpFddiDriverStatsErrTxAbort OBJECT-TYPE 
              SYNTAX  INTEGER 
              ACCESS  read-only 
              STATUS  mandatory 
              DESCRIPTION 
                      "The number of transmit frames that were aborted
                       by the MC68840 FDDI network interface chip."
              ::= { hpFddiDriverStatsEntry 10 } 

          hpFddiDriverStatsErrTxUnderrun OBJECT-TYPE 
              SYNTAX  INTEGER 
              ACCESS  read-only 
              STATUS  mandatory 
              DESCRIPTION 
                      "The number of transmit frames that were aborted
                       due to underrun errors in the MC68840 FDDI network
                       interface chip."
              ::= { hpFddiDriverStatsEntry 11 } 

          hpFddiDriverStatsErrTxParity OBJECT-TYPE 
              SYNTAX  INTEGER 
              ACCESS  read-only 
              STATUS  mandatory 
              DESCRIPTION 
                      "The number of transmit frames that were aborted
                       due to parity errors in the MC68840 FDDI network
                       interface chip."
              ::= { hpFddiDriverStatsEntry 12 } 

          hpFddiDriverStatsErrGsrLlcTxRer OBJECT-TYPE 
              SYNTAX  INTEGER 
              ACCESS  read-only 
              STATUS  mandatory 
              DESCRIPTION 
                      "The number of LLC transmit ring errors detected
                       by the MC68840 FDDI network interface chip."
              ::= { hpFddiDriverStatsEntry 13 } 

          hpFddiDriverStatsErrGsrLlcRxRer OBJECT-TYPE 
              SYNTAX  INTEGER 
              ACCESS  read-only 
              STATUS  mandatory 
              DESCRIPTION 
                      "The number of LLC receive ring errors detected
                       by the MC68840 FDDI network interface chip."
              ::= { hpFddiDriverStatsEntry 14 } 

          hpFddiDriverStatsErrGsrSMTTxRer OBJECT-TYPE 
              SYNTAX  INTEGER 
              ACCESS  read-only 
              STATUS  mandatory 
              DESCRIPTION 
                      "The number of SMT transmit ring errors detected
                       by the MC68840 FDDI network interface chip."
              ::= { hpFddiDriverStatsEntry 15 } 

          hpFddiDriverStatsErrGsrSMTRxRer OBJECT-TYPE 
              SYNTAX  INTEGER 
              ACCESS  read-only 
              STATUS  mandatory 
              DESCRIPTION 
                      "The number of SMT receive ring errors detected
                       by the MC68840 FDDI network interface chip."
              ::= { hpFddiDriverStatsEntry 16 } 

          hpFddiDriverStatsErrGsrPortOp OBJECT-TYPE 
              SYNTAX  INTEGER 
              ACCESS  read-only 
              STATUS  mandatory 
              DESCRIPTION 
                      "The number of port operation errors detected by
                       the FSI of the MC68840 FDDI network interface chip."
              ::= { hpFddiDriverStatsEntry 17 } 

          hpFddiDriverStatsErrGsrLlcRxRov OBJECT-TYPE 
              SYNTAX  INTEGER 
              ACCESS  read-only 
              STATUS  mandatory 
              DESCRIPTION 
                      "The number of LLC receive overrun condition detected
                       by the FSI of the MC68840 FDDI network interface chip."
              ::= { hpFddiDriverStatsEntry 18 } 

          hpFddiDriverStatsErrGsrSMTRxRov OBJECT-TYPE 
              SYNTAX  INTEGER 
              ACCESS  read-only 
              STATUS  mandatory 
              DESCRIPTION 
                      "The number of SMT receive overrun condition detected
                       by the FSI of the MC68840 FDDI network interface chip."
              ::= { hpFddiDriverStatsEntry 19 } 

          hpFddiDriverStatsErrGsrInternalOp OBJECT-TYPE 
              SYNTAX  INTEGER 
              ACCESS  read-only 
              STATUS  mandatory 
              DESCRIPTION 
                      "The number of interal operation errors detected by
                       the FSI of the MC68840 FDDI network interface chip."
              ::= { hpFddiDriverStatsEntry 20 } 

          hpFddiDriverStatsIoeMov OBJECT-TYPE 
              SYNTAX  INTEGER 
              ACCESS  read-only 
              STATUS  mandatory 
              DESCRIPTION 
                      "The number of memory overrun conditions that
                       the FSI has detected in MC68840 FDDI network
                       interface chip.  The internal operation error
                       count will also be incremented under this
                       condition."
              ::= { hpFddiDriverStatsEntry 21 } 

          hpFddiDriverStatsErrGsrHost OBJECT-TYPE 
              SYNTAX  INTEGER 
              ACCESS  read-only 
              STATUS  mandatory 
              DESCRIPTION 
                      "The number of host errros detected by the FSI of
                       the MC68840 FDDI network interface chip."
              ::= { hpFddiDriverStatsEntry 22 } 

          hpFddiDriverStatsTxCongestion OBJECT-TYPE 
              SYNTAX  INTEGER 
              ACCESS  read-only 
              STATUS  mandatory 
              DESCRIPTION 
                      "The number of transmit packets dropped due to
                       insufficient space on the FDDI driver transmit
                       ring."
              ::= { hpFddiDriverStatsEntry 23 } 

          hpFddiDriverStatsMissedCmd OBJECT-TYPE 
              SYNTAX  INTEGER 
              ACCESS  read-only 
              STATUS  mandatory 
              DESCRIPTION 
                      "The number of FSI commands that did not execute
                       properly in the MC68840 FDDI network interface
                       chip."
              ::= { hpFddiDriverStatsEntry 24 } 

          hpFddiDriverStatsMissedCRF OBJECT-TYPE 
              SYNTAX  INTEGER 
              ACCESS  read-only 
              STATUS  mandatory 
              DESCRIPTION 
                      "The number of FSI commands that could not be
                       issued because of an unavailable command register
                       in the MC68840 FDDI network interface chip."
              ::= { hpFddiDriverStatsEntry 25 } 


          END
