--
--
--  BlueArc Server Enterprise MIB Module
--
--

BLUEARC-SERVER-MIB DEFINITIONS ::= BEGIN

IMPORTS
    MODULE-IDENTITY, OBJECT-TYPE, Integer32,
    Unsigned32, Counter32, Counter64,
    IpAddress, mib-2, enterprises             FROM SNMPv2-SMI
    DisplayString                             FROM SNMPv2-TC
    MODULE-COMPLIANCE, OBJECT-GROUP           FROM SNMPv2-CONF
    ifIndex                                   FROM RFC1213-MIB;

blueArcServer MODULE-IDENTITY
    LAST-UPDATED "200711051200Z"
    ORGANIZATION "BlueArc UK Ltd."
    CONTACT-INFO
                 "Contact:  Support Team

                   Postal:  BlueArc Corporation
                            50 Rio Robles Dr.
                            San Jose, CA 95134
                            USA

                      Tel:  408 576 6600
                      Fax:  408 576 6601

                      WEB:  http://www.bluearc.com
                    email:  support@bluearc.com"
    DESCRIPTION
                 "The MIB module for monitoring a BlueArc Server."
    REVISION
                 "200711051200Z"
    DESCRIPTION
                "Obsolete: NFS user and group tables; HTTP 
                 and web server objects (HTTP server is no 
                 longer present); winAlert objects (Winpopup 
                 feature has been removed); racks and raid 
                 branches; event log reporting; NFS statistics
                 (replaced with tables indexed by cluster node; 
                 licenseKeyTable (replaced with licenseTable).
                 Implement serialNumberTable.
                 Add value to clusterQuorumDeviceStatus."
    REVISION
                 "200605121200Z"
    DESCRIPTION
                "Obsolete all previously deprecated objects."
    REVISION
                 "200604241200Z"
    DESCRIPTION
                "Add tables of NVRAM statistics, for the whole pool,
                 and per file system."
    REVISION
                 "200512131200Z"
    DESCRIPTION
                "Add a table of ops/sec statistics for File Systems.
                 Re-implement the fcStats table, to index by Cluster Node
                 as well as the index of the fibre channel interface. Add
                 columns to this table to indicate the enabled state, the status,
                 the link speed and the link type."
    REVISION
                 "200512091200Z"
    DESCRIPTION
                 "Provide clusterPNodeStatus with a 'dormant' value."
    REVISION
                 "200508291200Z"
    DESCRIPTION
                "Obsolete any SiCtrl-related objects, as SiCtrl is not now
                 available as a Management Service."
    REVISION
                 "200403231200Z"
    DESCRIPTION
                 "Provide field in volumeTable (volumeEnterpriseVirtualServer),
                 in autoChangerTable (autoChangerEVS), and in tapeDriveTable
                 (tapeDriveEVS).
                 Obsolete all ftp objects, to re-implement indexed by Cluster Node.
                 Obsolete share objects, and re-implement in this mib as a 
                 table indexed by EVS and share name.
                 Obsolete NFS export objects, and re-implement in this mib as a
                 table indexed by EVS and export name.
                 Obsolete snapshot rule and schedule objects, and re-implement 
                 in this mib as a table indexed by EVS and snapshot rule name.
                 Add iSCSI objects.
                 Obsolete sensor and psu tables, re-implementing as
                 temperatureSensor, fan and psu tables.
                 Provide 'unknown' INTEGER values in tables where the value
                 may not be obtainable."
    REVISION
                 "200310141200Z"
    DESCRIPTION
                 "Provide clustering objects with 'unknown' values."
    REVISION
                 "200309011200Z"
    DESCRIPTION
                 "Obsolete existing statistics lists (ethernet, tcp, udp...)
                 and place them in tables indexed by ifIndex.
                 Add ifIndex to list of IMPORTS."
    REVISION
                 "200307241200Z"
    DESCRIPTION
                 "Add Volume Label as column in snapshotRuleTable."
    REVISION
                 "200307111200Z"
    DESCRIPTION
                 "Deprecate objects which are not valid for current servers."
    REVISION
                 "200306101200Z"
    DESCRIPTION
                 "Add status codes for sysDriveStatus."
    REVISION
                 "200303311200Z"
    DESCRIPTION
                 "Rev 1.13 31 March 2003 12.00 GMT
                 Create objects describing clustering
                 configuration and status."
    REVISION
                 "200303271200Z"
    DESCRIPTION
                 "Rev 1.12 27 March 2003 12.00 GMT
                 Include File System Load objects under
                 System/Server/Environment."
    REVISION
                 "200301161400Z"
    DESCRIPTION
                 "Rev 1.11 16 January 2003 14.00 GMT
                 Make obsolete all Hardware Flow Control objects."
    REVISION
                 "200301161200Z"
    DESCRIPTION
                 "Rev 1.10 16 January 2003 12.00 GMT
                 Make obsolete all Power Unit tables, in order to index them with
                 their IP addresses.
                 Re-define all power unit tables accordingly"
    REVISION
                 "200301151016Z"
    DESCRIPTION
                 "Rev 1.9 15 January 2003 10.16 GMT
                 Make obsolete all objects describing failover, as failover has
                 been replaced by clustering."
    REVISION
                 "200301071621Z"
    DESCRIPTION
                 "Rev 1.8 07 January 2003 16:21 GMT
                 Make obsolete all objects describing automount characteristics, as
                 volumes are not now automounted."
    REVISION
                 "200211281620Z"
    DESCRIPTION
                 "Rev 1.7 28 November 2002 16:20 GMT
                 Reorder ethernet stats, to include transmitted, received and total bytes,
                 and total packets. Required making re-ordered values obsolete, and
                 re-defining them."
    REVISION
                 "200210251452Z"
    DESCRIPTION
                 "Rev 1.6 25 October 2002 14:52 GMT
                  Include new object: opsPerSecond."
    REVISION
                 "200210241407Z"
    DESCRIPTION
                 "Rev 1.5 24 October 2002 14:07 GMT
                  All Undisclosed SMTP recipient objects have been made
                  obsolete, along with the objects to generate the SMTP
                  recipient table.  As these are now combined into one
                  new table."
    REVISION
                 "200205311200Z"
    DESCRIPTION
                 "Rev 1.4  31 May 2002 12:00 GMT
                  If the snapshot facility is disabled on this system,
                  the variables:

                  a) ndmpAutoSnapCreateEnabled and ndmpAutoSnapDeleteMode
                     are returned as unknown(3) 
                  b) ndmpAutoSnapMaxRetention is returned as 0

                  by the agent.

                  The objects snmpRecipNumber and snmpRecipTable
                  have been made obsolete as they are available through
                  the objects snmpTrapHostNumber and snmpTrapHostTable
                  respectively."
    REVISION
                 "200205271200Z"
    DESCRIPTION
                 "Rev 1.3  27 May 2002 12:00 GMT
                  nfsMounts, nfsClients and nfsExportNumberMounts
                  have been made obsolete as they cannot be measured."
    REVISION
                 "200204041200Z"
    DESCRIPTION
                 "Rev 1.2  04 Apr 2002 12:00 GMT
                  Additional objects:

                  cron - a branch containing cron and at job
                         configuration.

                  secureWeb - a branch containing secure web 
                              access configuration.

                  lcd - a branch containing front panel
                        configuration.

                  New object indicating whether diagnostics email
                  is uuencoded or not.

                  New table containing SMTP recipients which
                  are to receive undisclosed alert information.

                  mgmntStats - a branch containing management
                               statistics.

                  hwFlowControl - a branch containing hardware
                                  flow control settings.

                  ftpSecurity - a branch containing FTP security
                                configuration.

                  ndmpSnapshotOptions - a branch containing snapshot
                                        options.

                  virtualVolumes - a branch containing virtual volumes
                                   and associated configuration.

                  snapshot - a branch containing snapshot configuration.

                  nis - a branch containing NIS configuration.

                  Enhancements:

                  web, sictrl, telnet (and secureWeb) indicate
                  port number and maximum number of connections
                  permitted."

    REVISION
                 "200203191200Z"
    DESCRIPTION
                 "Rev 1.1  19 Mar 2002 12:00 GMT
                  Additional objects:

                  HTTP
                  Changes made to RAID management."
    REVISION
                 "200112211200Z"
    DESCRIPTION
                 "Initial Revision 21 Dec 2001 12:00 GMT."

::= { blueArcPrivate 1 }

blueArc                 OBJECT IDENTIFIER ::= { enterprises 11096 }
blueArcPrivate          OBJECT IDENTIFIER ::= { blueArc 6 }

--------------------------------------------------------------------------------
--
-- MIB Tree Structure
--
--------------------------------------------------------------------------------

    blueArcServerObjs                OBJECT IDENTIFIER ::= { blueArcServer 1 }
        sys                          OBJECT IDENTIFIER ::= { blueArcServerObjs 1 }
            powerUnits               OBJECT IDENTIFIER ::= { sys 1 }
            server                   OBJECT IDENTIFIER ::= { sys 2 }
                environment          OBJECT IDENTIFIER ::= { server 1 }
                locale               OBJECT IDENTIFIER ::= { server 2 }
                failover             OBJECT IDENTIFIER ::= { server 3 }
                cache                OBJECT IDENTIFIER ::= { server 4 }
                    sectorCache      OBJECT IDENTIFIER ::= { cache 1 }
                    fileSysCache     OBJECT IDENTIFIER ::= { cache 2 }
                clustering           OBJECT IDENTIFIER ::= { server 5 }
                serialNumbers        OBJECT IDENTIFIER ::= { server 6 }
            storage                  OBJECT IDENTIFIER ::= { sys 3 }
                racks                OBJECT IDENTIFIER ::= { storage 1 }
                raid                 OBJECT IDENTIFIER ::= { storage 2 }
                    controllers      OBJECT IDENTIFIER ::= { raid 1 }
                    physicalDrives   OBJECT IDENTIFIER ::= { raid 2 }
                    enclosures       OBJECT IDENTIFIER ::= { raid 3 }
                automount            OBJECT IDENTIFIER ::= { storage 3 }
                systemDrives         OBJECT IDENTIFIER ::= { storage 4 }
                volumes              OBJECT IDENTIFIER ::= { storage 5 }
                fcStats              OBJECT IDENTIFIER ::= { storage 6 }
                virtualVolumes       OBJECT IDENTIFIER ::= { storage 7 }
                snapshot             OBJECT IDENTIFIER ::= { storage 8 }
                nvramStats           OBJECT IDENTIFIER ::= { storage 9 }
        network                      OBJECT IDENTIFIER ::= { blueArcServerObjs 2 }
            etherStats               OBJECT IDENTIFIER ::= { network 1 }
            tcpipStats               OBJECT IDENTIFIER ::= { network 2 }
            udpStats                 OBJECT IDENTIFIER ::= { network 3 }
            advipConfig              OBJECT IDENTIFIER ::= { network 4 }
            engipConfig              OBJECT IDENTIFIER ::= { network 5 }
            nameService              OBJECT IDENTIFIER ::= { network 6 }
                wins                 OBJECT IDENTIFIER ::= { nameService 1 }
                dns                  OBJECT IDENTIFIER ::= { nameService 2 }
                nsOrder              OBJECT IDENTIFIER ::= { nameService 3 }
            nis                      OBJECT IDENTIFIER ::= { network 7 }
        fileProtocol                 OBJECT IDENTIFIER ::= { blueArcServerObjs 3 }
            security                 OBJECT IDENTIFIER ::= { fileProtocol 1 }
            cifs                     OBJECT IDENTIFIER ::= { fileProtocol 2 }
                shares               OBJECT IDENTIFIER ::= { cifs 1 }
                shareAccess          OBJECT IDENTIFIER ::= { cifs 2 }
                cifsStats            OBJECT IDENTIFIER ::= { cifs 3 }
                cifsService          OBJECT IDENTIFIER ::= { cifs 4 }
            nfs                      OBJECT IDENTIFIER ::= { fileProtocol 3 }
                nfsExports           OBJECT IDENTIFIER ::= { nfs 1 }
                nfsUsers             OBJECT IDENTIFIER ::= { nfs 2 }
                nfsUserMapping       OBJECT IDENTIFIER ::= { nfs 3 }
                nfsGroups            OBJECT IDENTIFIER ::= { nfs 4 }
                nfsGroupMapping      OBJECT IDENTIFIER ::= { nfs 5 }
                nfsStats             OBJECT IDENTIFIER ::= { nfs 6 }
                    nfsVersion2      OBJECT IDENTIFIER ::= { nfsStats 1 }
                    nfsVersion3      OBJECT IDENTIFIER ::= { nfsStats 2 }
                nfsService           OBJECT IDENTIFIER ::= { nfs 7 }
            ftp                      OBJECT IDENTIFIER ::= { fileProtocol 4 }
                ftpMountPoints       OBJECT IDENTIFIER ::= { ftp 2 }
                ftpUsers             OBJECT IDENTIFIER ::= { ftp 3 }
                ftpLogging           OBJECT IDENTIFIER ::= { ftp 4 }
                ftpStats             OBJECT IDENTIFIER ::= { ftp 5 }
                ftpService           OBJECT IDENTIFIER ::= { ftp 6 }
                ftpSecurity          OBJECT IDENTIFIER ::= { ftp 7 }
            http                     OBJECT IDENTIFIER ::= { fileProtocol 5 }
                httpConfig           OBJECT IDENTIFIER ::= { http 1 }
                httpStats            OBJECT IDENTIFIER ::= { http 2 }
                httpService          OBJECT IDENTIFIER ::= { http 3 }
            iScsi                    OBJECT IDENTIFIER ::= { fileProtocol 6 }
                iScsiConfiguration   OBJECT IDENTIFIER ::= { iScsi 1 }
                iScsiStatistics      OBJECT IDENTIFIER ::= { iScsi 2 }
        backup                       OBJECT IDENTIFIER ::= { blueArcServerObjs 4 }
            ndmpStatus               OBJECT IDENTIFIER ::= { backup 1 }
            ndmpDevices              OBJECT IDENTIFIER ::= { backup 2 }
            ndmpSnapshotOptions      OBJECT IDENTIFIER ::= { backup 3 }
        mgmnt                        OBJECT IDENTIFIER ::= { blueArcServerObjs 5 }
            systemUsers              OBJECT IDENTIFIER ::= { mgmnt 1 }
            license                  OBJECT IDENTIFIER ::= { mgmnt 2 }
            access                   OBJECT IDENTIFIER ::= { mgmnt 3 }
                web                  OBJECT IDENTIFIER ::= { access 1 }
                sictrl               OBJECT IDENTIFIER ::= { access 2 }
                telnet               OBJECT IDENTIFIER ::= { access 3 }
                secureWeb            OBJECT IDENTIFIER ::= { access 4 }
                lcd                  OBJECT IDENTIFIER ::= { access 5 }
            eventlog                 OBJECT IDENTIFIER ::= { mgmnt 4 }
            alerts                   OBJECT IDENTIFIER ::= { mgmnt 5 }
                mailAlertConfig      OBJECT IDENTIFIER ::= { alerts 1 }
                winAlertConfig       OBJECT IDENTIFIER ::= { alerts 2 }
                snmpAlertConfig      OBJECT IDENTIFIER ::= { alerts 3 }
            snmpAgent                OBJECT IDENTIFIER ::= { mgmnt 6 }
            versions                 OBJECT IDENTIFIER ::= { mgmnt 7 }
            cron                     OBJECT IDENTIFIER ::= { mgmnt 8 }
            mgmntStats               OBJECT IDENTIFIER ::= { mgmnt 9 }
                webMgmntStats        OBJECT IDENTIFIER ::= { mgmntStats 1 }
                sictrlMgmntStats     OBJECT IDENTIFIER ::= { mgmntStats 2 }
                telnetMgmntStats     OBJECT IDENTIFIER ::= { mgmntStats 3 }
                secureWebMgmntStats  OBJECT IDENTIFIER ::= { mgmntStats 4 }
            hwFlowControl            OBJECT IDENTIFIER ::= { mgmnt 10 }

--------------------------------------------------------------------------------
--
-- System / Power Unit Configuration
--
--------------------------------------------------------------------------------

    puConfigNumber OBJECT-TYPE
        SYNTAX Integer32
        MAX-ACCESS read-only
        STATUS obsolete
        DESCRIPTION
            "The number of power units (regardless of their current state)
             which may be present on this system.

             This object is obsolete. Power units must be indexed by
             IP address."
        ::= { powerUnits 1 }

    puConfigTable OBJECT-TYPE
        SYNTAX SEQUENCE OF PuConfigEntry
        MAX-ACCESS not-accessible
        STATUS obsolete
        DESCRIPTION
            "A table of configuration information relevant to each power
             unit which may be present on this system.

             The number of entries in this table is given by the value of
             puConfigNumber.

             This object is obsolete. Power units must be indexed by
             IP address."
        ::= { powerUnits 2 }

    puConfigEntry OBJECT-TYPE
        SYNTAX PuConfigEntry
        MAX-ACCESS not-accessible
        STATUS obsolete
        DESCRIPTION
            "Configuration information for a power unit which may be
             present on this system.

             This object is obsolete. Power units must be indexed by
             IP address."
        INDEX { puConfigIndex }
        ::= { puConfigTable 1 }

    PuConfigEntry ::=
        SEQUENCE {
            puConfigIndex
                Integer32,
            puConfigShutdownEnabled
                INTEGER,
            puConfigShutdownInterval
                INTEGER,
            puConfigShutdownRemainingLife
                INTEGER,
            puConfigCommsOK
                INTEGER,
            puConfigCommsEverOK
                INTEGER
        }

    puConfigIndex OBJECT-TYPE
        SYNTAX Integer32 (1..2)
        MAX-ACCESS read-only
        STATUS obsolete
        DESCRIPTION
            "A unique value for each power unit which may be present on
             this system.

             Its value ranges between 1 and the value of puConfigNumber.

             This object is obsolete. Power units must be indexed by
             IP address."
        ::= { puConfigEntry 1 }

    puConfigShutdownEnabled OBJECT-TYPE
        SYNTAX INTEGER {
            enabled(1),
            disabled(2)
        }
        MAX-ACCESS read-only
        STATUS obsolete
        DESCRIPTION
            "Indicates whether the power unit is to control the shutdown
             of the system when a power outage is detected.

             enabled(1)  - the power unit will control the shutdown.
             disabled(2) - the power unit will NOT control the shutdown.

             This object is obsolete. Power units must be indexed by
             IP address."
        ::= { puConfigEntry 2 }

    puConfigShutdownInterval OBJECT-TYPE
        SYNTAX INTEGER {
            remainingLife(1),
            immediately(2),
            oneMinute(3),
            twoMinutes(4),
            threeMinutes(5),
            fiveMinutes(6),
            tenMinutes(7)
        }
        MAX-ACCESS read-only
        STATUS obsolete
        DESCRIPTION
            "This variable is used in conjunction with
             puConfigShutdownRemainingLife such that when either
             condition is met a controlled shutdown will take place.

             puConfigShutdownInterval specifies the interval after
             which a controlled shutdown should take place in the event
             of a power outage.

             remainingLife(1) - indicates that the shutdown is based
                                on the remaining battery life only and NOT
                                the duration of the power outage.
                                The variable puConfigShutdownRemainingLife
                                determines how the shutdown is controlled.
             immediately(2)   - the shutdown should take place as soon as
                                the power outage is detected.  The variable
                                puConfigRemainingLife is irrelevant in this
                                case.
             oneMinute(3),
             twoMinutes(4),
             threeMinutes(5), - the interval after which a controlled
             fiveMinutes(6),    shutdown should take place in the event of
             tenMinutes(7)      a power outage.

             NOTE: the variable puConfigShutdownEnabled must be enabled(1),
                   for this variable to have any effect in determining
                   when the controlled shutdown is performed.

             This object is obsolete. Power units must be indexed by
             IP address."
        ::= { puConfigEntry 3 }

    puConfigShutdownRemainingLife OBJECT-TYPE
        SYNTAX INTEGER {
            fiveMinutes(5),
            tenMinutes(10)
        }
        MAX-ACCESS read-only
        STATUS obsolete
        DESCRIPTION
            "Specifies the number of minutes of battery life which when
             depleted will cause a controlled shutdown of the system.

             NOTE: the variable puConfigShutdownEnabled must be enabled(1),
                   for this variable to have any effect in determining
                   when the controlled shutdown is performed.

             This object is obsolete. Power units must be indexed by
             IP address."
        ::= { puConfigEntry 4 }

    puConfigCommsOK OBJECT-TYPE
        SYNTAX INTEGER {
            communicating(1),
            notCommunicating(2)
        }
        MAX-ACCESS read-only
        STATUS obsolete
        DESCRIPTION
            "Indicates whether the system is currently communicating with
             the power unit.

             This object is obsolete. Power units must be indexed by
             IP address."
        ::= { puConfigEntry 5 }

    puConfigCommsEverOK OBJECT-TYPE
        SYNTAX INTEGER {
            communicated(1),
            neverCommunicated(2)
        }
        MAX-ACCESS read-only
        STATUS obsolete
        DESCRIPTION
            "Indicates whether the system has ever communicated
             with the power unit.

             This object is obsolete. Power units must be indexed by
             IP address."
        ::= { puConfigEntry 6 }

    puConfigurationCount OBJECT-TYPE
        SYNTAX Integer32
        MAX-ACCESS read-only
        STATUS current
        DESCRIPTION
            "The number of power units (regardless of their current state)
             which may be present on this system."
        ::= { powerUnits 7 }

    puConfigurationTable OBJECT-TYPE
        SYNTAX SEQUENCE OF PuConfigurationEntry
        MAX-ACCESS not-accessible
        STATUS current
        DESCRIPTION
            "A table of configuration information relevant to each power
             unit which may be present on this system.

             The number of entries in this table is given by the value of
             puConfigurationCount."
        ::= { powerUnits 8 }

    puConfigurationEntry OBJECT-TYPE
        SYNTAX PuConfigurationEntry
        MAX-ACCESS not-accessible
        STATUS current
        DESCRIPTION
            "Configuration information for a power unit which may be
             present on this system."
        INDEX { puConfigurationIndex }
        ::= { puConfigurationTable 1 }

    PuConfigurationEntry ::=
        SEQUENCE {
            puConfigurationIndex
                IpAddress,
            puConfigurationUserName
                DisplayString,
            puConfigurationMonitoringEnabled
                INTEGER,
            puConfigurationShutdownOnBattery
                Integer32,
            puConfigurationShutdownOnRuntime
                Integer32,
            puConfigurationShutdownOnLowBattery
                Integer32,
            puConfigurationOnBatteryTolerance
                Integer32,
            puConfigurationCommsOK
                INTEGER,
            puConfigurationCommsEverOK
                INTEGER
        }

    puConfigurationIndex OBJECT-TYPE
        SYNTAX IpAddress
        MAX-ACCESS read-only
        STATUS current
        DESCRIPTION
            "An IP address for each power unit which may be present on
             this system.

             0.0.0.0 is given for a serial-attached UPS."
        ::= { puConfigurationEntry 1 }

    puConfigurationUserName OBJECT-TYPE
        SYNTAX DisplayString
        MAX-ACCESS read-only
        STATUS current
        DESCRIPTION
            "The UPS management card's admin user name, used with the
            authentication phrase for authenticating status updates
            from the UPS. Empty if authentication is disabled."
        ::= { puConfigurationEntry 2 }

    puConfigurationMonitoringEnabled OBJECT-TYPE
        SYNTAX INTEGER {
            enabled(1),
            disabled(2),
            unknown(3)
        }
        MAX-ACCESS read-only
        STATUS current
        DESCRIPTION
            "Indicates whether monitoring is enabled on the UPS.

            If monitoring is enabled, then the power unit is to
            control the shutdown of the system when a power outage is
            detected."
        ::= { puConfigurationEntry 3 }

    puConfigurationShutdownOnBattery OBJECT-TYPE
        SYNTAX Integer32
        MAX-ACCESS read-only
        STATUS current
        DESCRIPTION
            "If the value is not -1, then the system will be shut down
            after running on battery for the specified time in minutes."
        ::= { puConfigurationEntry 4 }

    puConfigurationShutdownOnRuntime OBJECT-TYPE
        SYNTAX Integer32
        MAX-ACCESS read-only
        STATUS current
        DESCRIPTION
            "If the value is not -1, then shutdown will occur when the
            estimated remaining runtime falls below the specified value
            in minutes."
        ::= { puConfigurationEntry 5 }

    puConfigurationShutdownOnLowBattery OBJECT-TYPE
        SYNTAX Integer32
        MAX-ACCESS read-only
        STATUS current
        DESCRIPTION
            "If the value is not -1, then the system will shut down
            when UPS reports a low battery, with a delay of the
            specified number of minutes."
        ::= { puConfigurationEntry 6 }

    puConfigurationOnBatteryTolerance OBJECT-TYPE
        SYNTAX Integer32
        MAX-ACCESS read-only
        STATUS current
        DESCRIPTION
            "The length of time, in seconds, for which the UPS must be
            on battery before the system will act on it, no matter what
            the shutdown settings are."
        ::= { puConfigurationEntry 7 }

    puConfigurationCommsOK OBJECT-TYPE
        SYNTAX INTEGER {
            communicating(1),
            notCommunicating(2),
            unknown(3)
        }
        MAX-ACCESS read-only
        STATUS current
        DESCRIPTION
            "Indicates whether the system is currently communicating with
             the power unit."
        ::= { puConfigurationEntry 8 }

    puConfigurationCommsEverOK OBJECT-TYPE
        SYNTAX INTEGER {
            communicated(1),
            neverCommunicated(2),
            unknown(3)
        }
        MAX-ACCESS read-only
        STATUS current
        DESCRIPTION
            "Indicates whether the system has ever communicated
             with the power unit."
        ::= { puConfigurationEntry 9 }

--------------------------------------------------------------------------------
--
-- System / Power Unit Status
--
--------------------------------------------------------------------------------

    puStatusNumber OBJECT-TYPE
        SYNTAX Integer32
        MAX-ACCESS read-only
        STATUS obsolete
        DESCRIPTION
            "The number of power units from which status information
             can be gathered.  Status information is only available for
             power units that the system is able to communicate with.

             This object is obsolete. Power units must be indexed by
             IP address."
        ::= { powerUnits 3 }

    puStatusTable OBJECT-TYPE
        SYNTAX SEQUENCE OF PuStatusEntry
        MAX-ACCESS not-accessible
        STATUS obsolete
        DESCRIPTION
            "A table containing the status of each power unit the system
             is communicating with.

             The number of entries in this table is given by the value of
             puStatusNumber.

             This object is obsolete. Power units must be indexed by
             IP address."
        ::= { powerUnits 4 }

    puStatusEntry OBJECT-TYPE
        SYNTAX PuStatusEntry
        MAX-ACCESS not-accessible
        STATUS obsolete
        DESCRIPTION
            "Status information for each power unit the system is
             communicating with.

             This object is obsolete. Power units must be indexed by
             IP address."
        INDEX { puStatusIndex }
        ::= { puStatusTable 1 }

    PuStatusEntry ::=
        SEQUENCE {
            puStatusIndex
                Integer32,
            puStatusModel
                DisplayString,
            puStatusSerialNumber
                DisplayString,
            puStatusManufactureDate
                DisplayString,
            puStatusBatteryReplaceDate
                DisplayString,
            puStatusUpperTransferVoltage
                Integer32,
            puStatusLowerTransferVoltage
                Integer32,
            puStatusSensitivity
                INTEGER,
            puStatusLowBatteryInterval
                Integer32,
            puStatusAlarmSetting
                INTEGER,
            puStatusCalibrating
                INTEGER,
            puStatusSleeping
                INTEGER,
            puStatusOnline
                INTEGER,
            puStatusOnBattery
                INTEGER,
            puStatusBatteryAlmostUsedUp
                INTEGER,
            puStatusChangeBattery
                INTEGER
        }

    puStatusIndex OBJECT-TYPE
        SYNTAX Integer32 (1..2)
        MAX-ACCESS read-only
        STATUS obsolete
        DESCRIPTION
            "The power unit from which the status information has been
             gathered. The power unit identified by a particular value
             of this index is the same power unit as identified by the
             same value of puConfigIndex.

             This object is obsolete. Power units must be indexed by
             IP address."
        ::= { puStatusEntry 1 }

    puStatusModel OBJECT-TYPE
        SYNTAX DisplayString
        MAX-ACCESS read-only
        STATUS obsolete
        DESCRIPTION
            "The model of the power unit as declared by the
             manufacturer.

             This object is obsolete. Power units must be indexed by
             IP address."
        ::= { puStatusEntry 2 }

    puStatusSerialNumber OBJECT-TYPE
        SYNTAX DisplayString
        MAX-ACCESS read-only
        STATUS obsolete
        DESCRIPTION
            "The serial number of the power unit as declared by the
             manufacturer.

             This object is obsolete. Power units must be indexed by
             IP address."
        ::= { puStatusEntry 3 }

    puStatusManufactureDate OBJECT-TYPE
        SYNTAX DisplayString
        MAX-ACCESS read-only
        STATUS obsolete
        DESCRIPTION
            "The date of manufacture of the power unit as declared by the
             manufacturer in their chosen format.

             This object is obsolete. Power units must be indexed by
             IP address."
        ::= { puStatusEntry 4 }

    puStatusBatteryReplaceDate OBJECT-TYPE
        SYNTAX DisplayString
        MAX-ACCESS read-only
        STATUS obsolete
        DESCRIPTION
            "The last date a battery was replaced within this the power unit
             in manufacturers format.

             This object is obsolete. Power units must be indexed by
             IP address."
        ::= { puStatusEntry 5 }

    puStatusUpperTransferVoltage OBJECT-TYPE
        SYNTAX Integer32
        MAX-ACCESS read-only
        STATUS obsolete
        DESCRIPTION
            "The upper battery transfer voltage in Volts.

             This object is obsolete. Power units must be indexed by
             IP address."
        ::= { puStatusEntry 6 }

    puStatusLowerTransferVoltage OBJECT-TYPE
        SYNTAX Integer32
        MAX-ACCESS read-only
        STATUS obsolete
        DESCRIPTION
            "The lower battery transfer voltage in Volts.

             This object is obsolete. Power units must be indexed by
             IP address."
        ::= { puStatusEntry 7 }

    puStatusSensitivity OBJECT-TYPE
        SYNTAX INTEGER {
            high(1),
            medium(2),
            low(3),
            automatic(4),
            unknown(5)
        }
        MAX-ACCESS read-only
        STATUS obsolete
        DESCRIPTION
            "The sensitivity of the power unit.

             This object is obsolete. Power units must be indexed by
             IP address."
        ::= { puStatusEntry 8 }

    puStatusLowBatteryInterval OBJECT-TYPE
        SYNTAX Integer32
        MAX-ACCESS read-only
        STATUS obsolete
        DESCRIPTION
            "The length of time between the power unit warning of a low
             battery and turning off in minutes.

             This object is obsolete. Power units must be indexed by
             IP address."
        ::= { puStatusEntry 9 }

    puStatusAlarmSetting OBJECT-TYPE
        SYNTAX INTEGER {
            immediately(1),
            delayedUtilityFailure(2),
            lowBatteryOnly(3),
            never(4),
            unknown(5)
        }
        MAX-ACCESS read-only
        STATUS obsolete
        DESCRIPTION
            "The audible alarm setting for the power unit.

             This object is obsolete. Power units must be indexed by
             IP address."
        ::= { puStatusEntry 10 }

    puStatusCalibrating OBJECT-TYPE
        SYNTAX INTEGER {
            calibrating(1),
            notCalibrating(2)
        }
        MAX-ACCESS read-only
        STATUS obsolete
        DESCRIPTION
            "Indicates whether the power unit is calibrating or not.

             This object is obsolete. Power units must be indexed by
             IP address."
        ::= { puStatusEntry 11 }

    puStatusSleeping OBJECT-TYPE
        SYNTAX INTEGER {
            sleeping(1),
            notSleeping(2)
        }
        MAX-ACCESS read-only
        STATUS obsolete
        DESCRIPTION
            "Indicates whether the power unit is sleeping or not.

             This object is obsolete. Power units must be indexed by
             IP address."
        ::= { puStatusEntry 12 }

    puStatusOnline OBJECT-TYPE
        SYNTAX INTEGER {
            online(1),
            offline(2)
        }
        MAX-ACCESS read-only
        STATUS obsolete
        DESCRIPTION
            "Indicates whether the power unit is on or off line.

             This object is obsolete. Power units must be indexed by
             IP address."
        ::= { puStatusEntry 13 }

    puStatusOnBattery OBJECT-TYPE
        SYNTAX INTEGER {
            onBattery(1),
            onMains(2)
        }
        MAX-ACCESS read-only
        STATUS obsolete
        DESCRIPTION
            "Indicates whether the power unit is operating on
             the battery or mains.

             This object is obsolete. Power units must be indexed by
             IP address."
        ::= { puStatusEntry 14 }

    puStatusBatteryAlmostUsedUp OBJECT-TYPE
        SYNTAX INTEGER {
            batteryAlmostUsedUp(1),
            batteryOK(2)
        }
        MAX-ACCESS read-only
        STATUS obsolete
        DESCRIPTION
            "Indicates whether the power units battery is almost
             used up.

             This object is obsolete. Power units must be indexed by
             IP address."
        ::= { puStatusEntry 15 }

    puStatusChangeBattery OBJECT-TYPE
        SYNTAX INTEGER {
            changeBattery(1),
            batteryOK(2)
        }
        MAX-ACCESS read-only
        STATUS obsolete
        DESCRIPTION
            "Indicates whether the power units battery should be
             changed.

             This object is obsolete. Power units must be indexed by
             IP address."
        ::= { puStatusEntry 16 }

    puCurrentStatusCount OBJECT-TYPE
        SYNTAX Integer32
        MAX-ACCESS read-only
        STATUS current
        DESCRIPTION
            "The number of power units from which status information
             can be gathered.  Status information is only available for
             power units that the system is able to communicate with."
        ::= { powerUnits 9 }

    puCurrentStatusTable OBJECT-TYPE
        SYNTAX SEQUENCE OF PuCurrentStatusEntry
        MAX-ACCESS not-accessible
        STATUS current
        DESCRIPTION
            "A table containing the status of each power unit the system
             is communicating with.

             The number of entries in this table is given by the value of
             puCurrentStatusCount."
        ::= { powerUnits 10 }

    puCurrentStatusEntry OBJECT-TYPE
        SYNTAX PuCurrentStatusEntry
        MAX-ACCESS not-accessible
        STATUS current
        DESCRIPTION
            "Status information for each power unit the system is
             communicating with."
        INDEX { puCurrentStatusIndex }
        ::= { puCurrentStatusTable 1 }

    PuCurrentStatusEntry ::=
        SEQUENCE {
            puCurrentStatusIndex
                IpAddress,
            puCurrentStatusModel
                DisplayString,
            puCurrentStatusSerialNumber
                DisplayString,
            puCurrentStatusManufactureDate
                DisplayString,
            puCurrentStatusBatteryReplacedDate
                DisplayString,
            puCurrentStatusUpperTransferVoltage
                Integer32,
            puCurrentStatusLowerTransferVoltage
                Integer32,
            puCurrentStatusSensitivity
                INTEGER,
            puCurrentStatusLowBatteryInterval
                Integer32,
            puCurrentStatusAlarmSetting
                INTEGER,
            puCurrentStatusCalibrating
                INTEGER,
            puCurrentStatusSleeping
                INTEGER,
            puCurrentStatusSmartTrim
                INTEGER,
            puCurrentStatusSmartBoost
                INTEGER,
            puCurrentStatusOnline
                INTEGER,
            puCurrentStatusOnBattery
                INTEGER,
            puCurrentStatusOverload
                INTEGER,
            puCurrentStatusBatteryAlmostUsedUp
                INTEGER,
            puCurrentStatusChangeBattery
                INTEGER
        }

    puCurrentStatusIndex OBJECT-TYPE
        SYNTAX IpAddress
        MAX-ACCESS read-only
        STATUS current
        DESCRIPTION
            "The power unit from which the status information has been
             gathered. The power unit identified by a particular IP
             address is the same power unit as identified by the
             same value of puConfigurationIndex."
        ::= { puCurrentStatusEntry 1 }

    puCurrentStatusModel OBJECT-TYPE
        SYNTAX DisplayString
        MAX-ACCESS read-only
        STATUS current
        DESCRIPTION
            "The model of the power unit as declared by the
             manufacturer."
        ::= { puCurrentStatusEntry 2 }

    puCurrentStatusSerialNumber OBJECT-TYPE
        SYNTAX DisplayString
        MAX-ACCESS read-only
        STATUS current
        DESCRIPTION
            "The serial number of the power unit as declared by the
             manufacturer."
        ::= { puCurrentStatusEntry 3 }

    puCurrentStatusManufactureDate OBJECT-TYPE
        SYNTAX DisplayString
        MAX-ACCESS read-only
        STATUS current
        DESCRIPTION
            "The date of manufacture of the power unit as declared by the
             manufacturer in their chosen format."
        ::= { puCurrentStatusEntry 4 }

    puCurrentStatusBatteryReplacedDate OBJECT-TYPE
        SYNTAX DisplayString
        MAX-ACCESS read-only
        STATUS current
        DESCRIPTION
            "The last date a battery was replaced within this the power unit
             in manufacturers format."
        ::= { puCurrentStatusEntry 5 }

    puCurrentStatusUpperTransferVoltage OBJECT-TYPE
        SYNTAX Integer32
        MAX-ACCESS read-only
        STATUS current
        DESCRIPTION
            "The upper battery transfer voltage in Volts."
        ::= { puCurrentStatusEntry 6 }

    puCurrentStatusLowerTransferVoltage OBJECT-TYPE
        SYNTAX Integer32
        MAX-ACCESS read-only
        STATUS current
        DESCRIPTION
            "The lower battery transfer voltage in Volts."
        ::= { puCurrentStatusEntry 7 }

    puCurrentStatusSensitivity OBJECT-TYPE
        SYNTAX INTEGER {
            high(1),
            medium(2),
            low(3),
            automatic(4),
            unknown(5)
        }
        MAX-ACCESS read-only
        STATUS current
        DESCRIPTION
            "The sensitivity of the power unit."
        ::= { puCurrentStatusEntry 8 }

    puCurrentStatusLowBatteryInterval OBJECT-TYPE
        SYNTAX Integer32
        MAX-ACCESS read-only
        STATUS current
        DESCRIPTION
            "The length of time between the power unit warning of a low
             battery and turning off in minutes."
        ::= { puCurrentStatusEntry 9 }

    puCurrentStatusAlarmSetting OBJECT-TYPE
        SYNTAX INTEGER {
            immediately(1),
            delayedUtilityFailure(2),
            lowBatteryOnly(3),
            never(4),
            unknown(5)
        }
        MAX-ACCESS read-only
        STATUS current
        DESCRIPTION
            "The audible alarm setting for the power unit."
        ::= { puCurrentStatusEntry 10 }

    puCurrentStatusCalibrating OBJECT-TYPE
        SYNTAX INTEGER {
            notDefined(0),
            calibrating(1),
            notCalibrating(2)
        }
        MAX-ACCESS read-only
        STATUS current
        DESCRIPTION
            "Indicates whether the power unit is calibrating or not."
        ::= { puCurrentStatusEntry 11 }

    puCurrentStatusSleeping OBJECT-TYPE
        SYNTAX INTEGER {
            notDefined(0),
            sleeping(1),
            notSleeping(2)
        }
        MAX-ACCESS read-only
        STATUS current
        DESCRIPTION
            "Indicates whether the power unit is sleeping or not.

            This object is only applicable to a Symmetra UPS;
            in all other cases, it will be notDefined(1)."
        ::= { puCurrentStatusEntry 12 }

    puCurrentStatusSmartTrim OBJECT-TYPE
        SYNTAX INTEGER {
            notDefined(0),
            notEnabled(1),
            enabled(2)
        }
        MAX-ACCESS read-only
        STATUS current
        DESCRIPTION
            "Indicates whether SmartTrim is enabled or not.

            This object is not applicable to a Symmetra UPS;
            in this case, it will be notDefined(1)."
        ::= { puCurrentStatusEntry 13 }

    puCurrentStatusSmartBoost OBJECT-TYPE
        SYNTAX INTEGER {
            notDefined(0),
            notEnabled(1),
            enabled(2)
        }
        MAX-ACCESS read-only
        STATUS current
        DESCRIPTION
            "Indicates whether SmartBoost is enabled or not."
        ::= { puCurrentStatusEntry 14 }

    puCurrentStatusOnline OBJECT-TYPE
        SYNTAX INTEGER {
            notDefined(0),
            online(1),
            offline(2)
        }
        MAX-ACCESS read-only
        STATUS current
        DESCRIPTION
            "Indicates whether the power unit is on or off line."
        ::= { puCurrentStatusEntry 15 }

    puCurrentStatusOnBattery OBJECT-TYPE
        SYNTAX INTEGER {
            notDefined(0),
            onBattery(1),
            onMains(2)
        }
        MAX-ACCESS read-only
        STATUS current
        DESCRIPTION
            "Indicates whether the power unit is operating on
             the battery or mains."
        ::= { puCurrentStatusEntry 16 }

    puCurrentStatusOverload OBJECT-TYPE
        SYNTAX INTEGER {
            notDefined(0),
            notEnabled(1),
            enabled(2)
        }
        MAX-ACCESS read-only
        STATUS current
        DESCRIPTION
            "Indicates whether the UPS is overloaded."
        ::= { puCurrentStatusEntry 17 }

    puCurrentStatusBatteryAlmostUsedUp OBJECT-TYPE
        SYNTAX INTEGER {
            notDefined(0),
            batteryAlmostUsedUp(1),
            batteryOK(2)
        }
        MAX-ACCESS read-only
        STATUS current
        DESCRIPTION
            "Indicates whether the power units battery is almost
             used up."
        ::= { puCurrentStatusEntry 18 }

    puCurrentStatusChangeBattery OBJECT-TYPE
        SYNTAX INTEGER {
            notDefined(0),
            changeBattery(1),
            batteryOK(2)
        }
        MAX-ACCESS read-only
        STATUS current
        DESCRIPTION
            "Indicates whether the power units battery should be
             changed."
        ::= { puCurrentStatusEntry 19 }


--------------------------------------------------------------------------------
--
-- System / Power Unit Statistics
--
--------------------------------------------------------------------------------

    puStatsNumber OBJECT-TYPE
        SYNTAX Integer32
        MAX-ACCESS read-only
        STATUS obsolete
        DESCRIPTION
            "The number of power units from which statistics
             can be gathered.  Statistics are only available for
             power units that the system is able to communicate with.

             This object is obsolete. Power units must be indexed by
             IP address."
        ::= { powerUnits 5 }

    puStatsTable OBJECT-TYPE
        SYNTAX SEQUENCE OF PuStatsEntry
        MAX-ACCESS not-accessible
        STATUS obsolete
        DESCRIPTION
            "A table containing statistics for each power unit the system
             is communicating with.

             The number of entries in this table is given by the value of
             puStatsNumber.

             This object is obsolete. Power units must be indexed by
             IP address."
        ::= { powerUnits 6 }

    puStatsEntry OBJECT-TYPE
        SYNTAX PuStatsEntry
        MAX-ACCESS not-accessible
        STATUS obsolete
        DESCRIPTION
            "Statistics for each power unit the system is communicating
             with.

             This object is obsolete. Power units must be indexed by
             IP address."
        INDEX { puStatsIndex }
        ::= { puStatsTable 1 }

    PuStatsEntry ::=
        SEQUENCE {
            puStatsIndex
                Integer32,
            puStatsBatteryCharge
                INTEGER,
            puStatsLoad
                INTEGER,
            puStatsFrequency
                Integer32,
            puStatsLineVoltage
                Integer32,
            puStatsOutputVoltage
                Integer32,
            puStatsBatteryVoltage
                Integer32,
            puStatsTemperatureC
                Integer32,
            puStatsTemperatureF
                Integer32,
            puStatsLineMininumVoltage
                Integer32,
            puStatsLineMaximumVoltage
                Integer32,
            puStatsRemainingRunTime
                Integer32
        }

    puStatsIndex OBJECT-TYPE
        SYNTAX Integer32 (1..2)
        MAX-ACCESS read-only
        STATUS obsolete
        DESCRIPTION
            "The power unit from which the statistics have been gathered.
             The power unit identified by a particular value of this
             index is the same power unit as identified by the same value
             of puConfigurationIndex.

             This object is obsolete. Power units must be indexed by
             IP address."
        ::= { puStatsEntry 1 }

    puStatsBatteryCharge OBJECT-TYPE
        SYNTAX INTEGER (0..100)
        MAX-ACCESS read-only
        STATUS obsolete
        DESCRIPTION
            "The percentage by which the battery is charged.

             This object is obsolete. Power units must be indexed by
             IP address."
        ::= { puStatsEntry 2 }

    puStatsLoad OBJECT-TYPE
        SYNTAX INTEGER (0..100)
        MAX-ACCESS read-only
        STATUS obsolete
        DESCRIPTION
            "The percentage of the rated load in Watts.

             This object is obsolete. Power units must be indexed by
             IP address."
        ::= { puStatsEntry 3 }

    puStatsFrequency OBJECT-TYPE
        SYNTAX Integer32
        MAX-ACCESS read-only
        STATUS obsolete
        DESCRIPTION
            "The frequency of the AC mains in Hertz.

             This object is obsolete. Power units must be indexed by
             IP address."
        ::= { puStatsEntry 4 }

    puStatsLineVoltage OBJECT-TYPE
        SYNTAX Integer32
        MAX-ACCESS read-only
        STATUS obsolete
        DESCRIPTION
            "The AC mains voltage entering the power unit in Volts.

             This object is obsolete. Power units must be indexed by
             IP address."
        ::= { puStatsEntry 5 }

    puStatsOutputVoltage OBJECT-TYPE
        SYNTAX Integer32
        MAX-ACCESS read-only
        STATUS obsolete
        DESCRIPTION
            "The output voltage of the power unit in Volts.

             This object is obsolete. Power units must be indexed by
             IP address."
        ::= { puStatsEntry 6 }

    puStatsBatteryVoltage OBJECT-TYPE
        SYNTAX Integer32
        MAX-ACCESS read-only
        STATUS obsolete
        DESCRIPTION
            "The battery voltage in Volts.

             This object is obsolete. Power units must be indexed by
             IP address."
        ::= { puStatsEntry 7 }

    puStatsTemperatureC OBJECT-TYPE
        SYNTAX Integer32
        MAX-ACCESS read-only
        STATUS obsolete
        DESCRIPTION
            "The temperature inside the power unit in degrees Celsius.

             This object is obsolete. Power units must be indexed by
             IP address."
        ::= { puStatsEntry 8 }

    puStatsTemperatureF OBJECT-TYPE
        SYNTAX Integer32
        MAX-ACCESS read-only
        STATUS obsolete
        DESCRIPTION
            "The temperature inside the power unit in degrees Fahrenheit.

             This object is obsolete. Power units must be indexed by
             IP address."
        ::= { puStatsEntry 9 }

    puStatsLineMininumVoltage OBJECT-TYPE
        SYNTAX Integer32
        MAX-ACCESS read-only
        STATUS obsolete
        DESCRIPTION
            "The minimum line voltage in Volts.

             This object is obsolete. Power units must be indexed by
             IP address."
        ::= { puStatsEntry 10 }

    puStatsLineMaximumVoltage OBJECT-TYPE
        SYNTAX Integer32
        MAX-ACCESS read-only
        STATUS obsolete
        DESCRIPTION
            "The maximum line voltage in Volts.

             This object is obsolete. Power units must be indexed by
             IP address."
        ::= { puStatsEntry 11 }

    puStatsRemainingRunTime OBJECT-TYPE
        SYNTAX Integer32
        MAX-ACCESS read-only
        STATUS obsolete
        DESCRIPTION
            "The remaining runtime of the battery based on the
             obsolete load in minutes.

             This object is obsolete. Power units must be indexed by
             IP address."
        ::= { puStatsEntry 12 }

    puStatisticsCount OBJECT-TYPE
        SYNTAX Integer32
        MAX-ACCESS read-only
        STATUS current
        DESCRIPTION
            "The number of power units from which statistics
             can be gathered.  Statistics are only available for
             power units that the system is able to communicate with."
        ::= { powerUnits 11 }

    puStatisticsTable OBJECT-TYPE
        SYNTAX SEQUENCE OF PuStatisticsEntry
        MAX-ACCESS not-accessible
        STATUS current
        DESCRIPTION
            "A table containing statistics for each power unit the system
             is communicating with.

             The number of entries in this table is given by the value of
             puStatisticsCount."
        ::= { powerUnits 12 }

    puStatisticsEntry OBJECT-TYPE
        SYNTAX PuStatisticsEntry
        MAX-ACCESS not-accessible
        STATUS current
        DESCRIPTION
            "Statistics for each power unit the system is communicating
             with."
        INDEX { puStatisticsIndex }
        ::= { puStatisticsTable 1 }

    PuStatisticsEntry ::=
        SEQUENCE {
            puStatisticsIndex
                Integer32,
            puStatisticsBatteryCharge
                INTEGER,
            puStatisticsLoad
                INTEGER,
            puStatisticsFrequency
                Integer32,
            puStatisticsLineVoltage
                Integer32,
            puStatisticsOutputVoltage
                Integer32,
            puStatisticsBatteryVoltage
                Integer32,
            puStatisticsTemperatureC
                Integer32,
            puStatisticsTemperatureF
                Integer32,
            puStatisticsLineMininumVoltage
                Integer32,
            puStatisticsLineMaximumVoltage
                Integer32,
            puStatisticsRemainingRunTime
                Integer32
        }

    puStatisticsIndex OBJECT-TYPE
        SYNTAX Integer32 (1..2)
        MAX-ACCESS read-only
        STATUS current
        DESCRIPTION
            "The power unit from which the statistics have been gathered.
             The power unit identified by a particular value of this
             index is the same power unit as identified by the same value
             of puConfigurationIndex."
        ::= { puStatisticsEntry 1 }

    puStatisticsBatteryCharge OBJECT-TYPE
        SYNTAX INTEGER (0..100)
        MAX-ACCESS read-only
        STATUS current
        DESCRIPTION
            "The percentage by which the battery is charged."
        ::= { puStatisticsEntry 2 }

    puStatisticsLoad OBJECT-TYPE
        SYNTAX INTEGER (0..100)
        MAX-ACCESS read-only
        STATUS current
        DESCRIPTION
            "The percentage of the rated load in Watts."
        ::= { puStatisticsEntry 3 }

    puStatisticsFrequency OBJECT-TYPE
        SYNTAX Integer32
        MAX-ACCESS read-only
        STATUS current
        DESCRIPTION
            "The frequency of the AC mains in Hertz."
        ::= { puStatisticsEntry 4 }

    puStatisticsLineVoltage OBJECT-TYPE
        SYNTAX Integer32
        MAX-ACCESS read-only
        STATUS current
        DESCRIPTION
            "The AC mains voltage entering the power unit in Volts."
        ::= { puStatisticsEntry 5 }

    puStatisticsOutputVoltage OBJECT-TYPE
        SYNTAX Integer32
        MAX-ACCESS read-only
        STATUS current
        DESCRIPTION
            "The output voltage of the power unit in Volts."
        ::= { puStatisticsEntry 6 }

    puStatisticsBatteryVoltage OBJECT-TYPE
        SYNTAX Integer32
        MAX-ACCESS read-only
        STATUS current
        DESCRIPTION
            "The battery voltage in Volts."
        ::= { puStatisticsEntry 7 }

    puStatisticsTemperatureC OBJECT-TYPE
        SYNTAX Integer32
        MAX-ACCESS read-only
        STATUS current
        DESCRIPTION
            "The temperature inside the power unit in degrees Celsius."
        ::= { puStatisticsEntry 8 }

    puStatisticsTemperatureF OBJECT-TYPE
        SYNTAX Integer32
        MAX-ACCESS read-only
        STATUS current
        DESCRIPTION
            "The temperature inside the power unit in degrees Fahrenheit."
        ::= { puStatisticsEntry 9 }

    puStatisticsLineMininumVoltage OBJECT-TYPE
        SYNTAX Integer32
        MAX-ACCESS read-only
        STATUS current
        DESCRIPTION
            "The minimum line voltage in Volts."
        ::= { puStatisticsEntry 10 }

    puStatisticsLineMaximumVoltage OBJECT-TYPE
        SYNTAX Integer32
        MAX-ACCESS read-only
        STATUS current
        DESCRIPTION
            "The maximum line voltage in Volts."
        ::= { puStatisticsEntry 11 }

    puStatisticsRemainingRunTime OBJECT-TYPE
        SYNTAX Integer32
        MAX-ACCESS read-only
        STATUS current
        DESCRIPTION
            "The remaining runtime of the battery based on the
             obsolete load in minutes."
        ::= { puStatisticsEntry 12 }

--------------------------------------------------------------------------------
--
-- System / Server/ Environment
--
--------------------------------------------------------------------------------

    sensorNumber OBJECT-TYPE
        SYNTAX Integer32
        MAX-ACCESS read-only
        STATUS obsolete
        DESCRIPTION
            "The number of sensors (regardless of their current state)
             which are present within silicon server unit."
        ::= { environment 1 }

    sensorTable OBJECT-TYPE
        SYNTAX SEQUENCE OF SensorEntry
        MAX-ACCESS not-accessible
        STATUS obsolete
        DESCRIPTION
            "A table containing information gathered by sensors located
             within the silicon server unit.  Each sensor takes a 
             measurement of both fan speed and temperature.

             The number of entries in this table is given by the value of
             sensorNumber."
        ::= { environment 2 }

    sensorEntry OBJECT-TYPE
        SYNTAX SensorEntry
        MAX-ACCESS not-accessible
        STATUS obsolete
        DESCRIPTION
            "Information collected from each sensor located within
             the silicon server unit."
        INDEX { sensorIndex }
        ::= { sensorTable 1 }

    SensorEntry ::=
        SEQUENCE {
            sensorIndex
                Integer32,
            sensorSpeedStatus
                INTEGER,
            sensorSpeedReading
                Unsigned32,
            sensorTempStatus
                INTEGER,
            sensorTempCReading
                Integer32,
            sensorTempFReading
                Integer32
        }

    sensorIndex OBJECT-TYPE
        SYNTAX Integer32 (1..3)
        MAX-ACCESS read-only
        STATUS obsolete
        DESCRIPTION
            "A unique value for each sensor within the silicon server unit.

             Its value ranges between 1 and the value of sensorNumber."
        ::= { sensorEntry 1 }

    sensorSpeedStatus OBJECT-TYPE
        SYNTAX INTEGER {
            ok(1),
            warning(2),
            severe(3),
            failed(4)
        }
        MAX-ACCESS read-only
        STATUS obsolete
        DESCRIPTION
            "Indicates whether the speed measurement is within the
             expected range.

             ok(1)      - the reading is within the expected range.
             warning(2) - the reading is outside of the expected range,
                          but not severe.
             severe(3)  - the sensor unit should be replaced.
             failed(4)  - the sensor unit has failed.  The measured
                          speed is invalid.
             unknown(5) - the speed status could not be determined."
        ::= { sensorEntry 2 }

    sensorSpeedReading OBJECT-TYPE
        SYNTAX Unsigned32
        MAX-ACCESS read-only
        STATUS obsolete
        DESCRIPTION
            "A measurement of the fan speed taken by the sensor in rpm."
        ::= { sensorEntry 3 }

    sensorTempStatus OBJECT-TYPE
        SYNTAX INTEGER {
            ok(1),
            warning(2),
            severe(3),
            failed(4)
        }
        MAX-ACCESS read-only
        STATUS obsolete
        DESCRIPTION
            "Indicates whether the temperature measurement is within the
             expected range.

             ok(1)      - the reading is within the expected range.
             warning(2) - the reading is outside of the expected range,
                          but not severe.
             severe(3)  - the sensor unit should be replaced.
             failed(4)  - the sensor unit has failed.  The measured
                          temperature is invalid."
        ::= { sensorEntry 4 }

    sensorTempCReading OBJECT-TYPE
        SYNTAX Integer32
        MAX-ACCESS read-only
        STATUS obsolete
        DESCRIPTION
            "A measurement of the temperature taken by the sensor in degrees
             Celsius."
        ::= { sensorEntry 5 }

    sensorTempFReading OBJECT-TYPE
        SYNTAX Integer32
        MAX-ACCESS read-only
        STATUS obsolete
        DESCRIPTION
            "A measurement of the temperature taken by the sensor in degrees
             Fahrenheit."
        ::= { sensorEntry 6 }


    psuOneStatus OBJECT-TYPE
        SYNTAX INTEGER {
            ok(1),
            failed(2)
        }
        MAX-ACCESS read-only
        STATUS obsolete
        DESCRIPTION
            "The status of power supply unit 1 within the silicon server."
        ::= { environment 3 }

    psuTwoStatus OBJECT-TYPE
        SYNTAX INTEGER {
            ok(1),
            failed(2)
        }
        MAX-ACCESS read-only
        STATUS obsolete
        DESCRIPTION
            "The status of power supply unit 2 within the silicon server."
        ::= { environment 4 }

    opsPerSecond OBJECT-TYPE
        SYNTAX Unsigned32
        MAX-ACCESS read-only
        STATUS current
        DESCRIPTION
            "The number of operations per second."
        ::= { environment 5 }

    fileSystemLoadClient OBJECT-TYPE
        SYNTAX Integer32
        MAX-ACCESS read-only
        STATUS current
        DESCRIPTION
            "The percentage of maximum load on file system resources
            due to client usage, averaged over the last 10 seconds.
            This represents the load on FSA."
        ::= { environment 6 }

    fileSystemLoadSystem OBJECT-TYPE
        SYNTAX Integer32
        MAX-ACCESS read-only
        STATUS current
        DESCRIPTION
            "The percentage of maximum load on file system resources
            due to system usage, averaged over the last 10 seconds.
            This represents the load on FSB."
        ::= { environment 7 }

    temperatureSensorNumber OBJECT-TYPE
        SYNTAX Integer32
        MAX-ACCESS read-only
        STATUS current
        DESCRIPTION
            "The number of temperature sensors (regardless of their
            current state) present in all silicon server units
            in the cluster."
        ::= { environment 8 }

    temperatureSensorTable OBJECT-TYPE
        SYNTAX SEQUENCE OF TemperatureSensorEntry
        MAX-ACCESS not-accessible
        STATUS current
        DESCRIPTION
            "A table containing information gathered by temperature
            sensors located in all silicon server units in the 
            cluster.

            The number of entries in this table is given by the value of
            temperatureSensorNumber."
        ::= { environment 9 }

    temperatureSensorEntry OBJECT-TYPE
        SYNTAX TemperatureSensorEntry
        MAX-ACCESS not-accessible
        STATUS current
        DESCRIPTION
            "Information collected from each temperature sensor located
            in the silicon server unit."
        INDEX { temperatureSensorClusterNode, temperatureSensorIndex }
        ::= { temperatureSensorTable 1 }

    TemperatureSensorEntry ::=
        SEQUENCE {
            temperatureSensorClusterNode
                Integer32,
            temperatureSensorIndex
                Integer32,
            temperatureSensorStatus
                INTEGER,
            temperatureSensorCReading
                Integer32,
            temperatureSensorFReading
                Integer32
        }

    temperatureSensorClusterNode OBJECT-TYPE
        SYNTAX Integer32 (1..255)
        MAX-ACCESS read-only
        STATUS current
        DESCRIPTION
            "The ID of the Cluster Node in which the fan
            is located."
        ::= { temperatureSensorEntry 1 }

    temperatureSensorIndex OBJECT-TYPE
        SYNTAX Integer32 (1..255)
        MAX-ACCESS read-only
        STATUS current
        DESCRIPTION
            "A unique value for each temperature sensor on a
            cluster node."
        ::= { temperatureSensorEntry 2 }

    temperatureSensorStatus OBJECT-TYPE
        SYNTAX INTEGER {
            ok(1),
            tempWarning(2),
            tempSevere(3),
            tempSensorFailed(4),
            tempSensorWarning(5),
            unknown(6)
        }
        MAX-ACCESS read-only
        STATUS current
        DESCRIPTION
            "Indicates whether the temperature measurement is within the
             expected range.

             ok(1)                  - the reading is within the expected range.
             tempWarning(2)         - the reading is outside of the expected
                                      range, but not severe.
             tempSevere(3)          - The reading is severely outside the
                                      expected range.
             tempSensoreFailed(4)   - the sensor unit has failed. The measured
                                      temperature is invalid
             tempSensorWarning(5)   - the sensor unit is in a warning condition.
             unknown(6)             - the status of the sensor could not be
                                      determined."
        ::= { temperatureSensorEntry 3 }

    temperatureSensorCReading OBJECT-TYPE
        SYNTAX Integer32
        MAX-ACCESS read-only
        STATUS current
        DESCRIPTION
            "A measurement of the temperature taken by the sensor in degrees
             Celsius."
        ::= { temperatureSensorEntry 4 }

    temperatureSensorFReading OBJECT-TYPE
        SYNTAX Integer32
        MAX-ACCESS read-only
        STATUS current
        DESCRIPTION
            "A measurement of the temperature taken by the sensor in degrees
             Fahrenheit."
        ::= { temperatureSensorEntry 5 }

    fanNumber OBJECT-TYPE
        SYNTAX Integer32
        MAX-ACCESS read-only
        STATUS current
        DESCRIPTION
            "The number of fans (regardless of their current state) present
            in all silicon server units in the cluster."
        ::= { environment 10 }

    fanTable OBJECT-TYPE
        SYNTAX SEQUENCE OF FanEntry
        MAX-ACCESS not-accessible
        STATUS current
        DESCRIPTION
            "A table containing information about the fans located in all 
            silicon server units in the cluster."
        ::= { environment 11 }

    fanEntry OBJECT-TYPE
        SYNTAX FanEntry
        MAX-ACCESS not-accessible
        STATUS current
        DESCRIPTION
            "Information about each fan located in all silicon server 
            units in the cluster."
        INDEX { fanClusterNode, fanIndex }
        ::= { fanTable 1 }

    FanEntry ::=
        SEQUENCE {
            fanClusterNode
                Integer32,
            fanIndex
                Integer32,
            fanFittedStatus
                INTEGER,
            fanSpeedStatus
                INTEGER,
            fanSpeed
                Integer32
        }

    fanClusterNode OBJECT-TYPE
        SYNTAX Integer32 (1..255)
        MAX-ACCESS read-only
        STATUS current
        DESCRIPTION
            "The ID of the Cluster Node in which the fan
            is located."
        ::= { fanEntry 1 }

    fanIndex OBJECT-TYPE
        SYNTAX Integer32 (1..255)
        MAX-ACCESS read-only
        STATUS current
        DESCRIPTION
            "A unique value for each fan on a
            cluster node."
        ::= { fanEntry 2 }

    fanFittedStatus OBJECT-TYPE
        SYNTAX INTEGER {
            ok(1),
            okIdWrong(2),
            notFitted(3),
            unknown(4)
        }
        MAX-ACCESS read-only
        STATUS current
        DESCRIPTION
            "Indicates the 'fitted' status of the fan.

             ok(1)                  - the fan is fitted correctly.
             okIdWrong(2)           - the fan is fitted correctly, but the
                                      ID is wrong.
             notFitted(3)           - the fan is not fitted.
             unknown(4)             - the status could not be determined."
        ::= { fanEntry 3 }

    fanSpeedStatus OBJECT-TYPE
        SYNTAX INTEGER {
            ok(1),
            warning(2),
            severe(3),
            unknown(4)
        }
        MAX-ACCESS read-only
        STATUS current
        DESCRIPTION
            "Indicates the 'speed' status of the fan.

             ok(1)                  - the fan speed is ok.
             warning(2)             - the fan speed is at a warning level.
             severe(3)              - the fan speed is at a severe level.
             unknown(4)             - the fan speed status could not be
                                      determined."
        ::= { fanEntry 4 }

    fanSpeed OBJECT-TYPE
        SYNTAX Integer32
        MAX-ACCESS read-only
        STATUS current
        DESCRIPTION
            "The speed of the fan."
        ::= { fanEntry 5 }

    psuNumber OBJECT-TYPE
        SYNTAX Integer32
        MAX-ACCESS read-only
        STATUS current
        DESCRIPTION
            "The number of psus (regardless of their current state) present
            in all silicon server units in the cluster."
        ::= { environment 12 }

    psuTable OBJECT-TYPE
        SYNTAX SEQUENCE OF PsuEntry
        MAX-ACCESS not-accessible
        STATUS current
        DESCRIPTION
            "A table containing information about the psus located in the
            silicon server unit."
        ::= { environment 13 }

    psuEntry OBJECT-TYPE
        SYNTAX PsuEntry
        MAX-ACCESS not-accessible
        STATUS current
        DESCRIPTION
            "Information about each psu."
        INDEX { psuClusterNode, psuIndex }
        ::= { psuTable 1 }

    PsuEntry ::=
        SEQUENCE {
            psuClusterNode
                Integer32,
            psuIndex
                Integer32,
            psuStatus
                INTEGER
        }

    psuClusterNode OBJECT-TYPE
        SYNTAX Integer32 (1..255)
        MAX-ACCESS read-only
        STATUS current
        DESCRIPTION
            "The ID of the Cluster Node in which the psu
            is located."
        ::= { psuEntry 1 }

    psuIndex OBJECT-TYPE
        SYNTAX Integer32 (1..255)
        MAX-ACCESS read-only
        STATUS current
        DESCRIPTION
            "A unique value for each psu on a
            cluster node."
        ::= { psuEntry 2 }

    psuStatus OBJECT-TYPE
        SYNTAX INTEGER {
            ok(1),
            failed(2),
            notFitted(3),
            unknown(4)
        }
        MAX-ACCESS read-only
        STATUS current
        DESCRIPTION
            "Indicates the status of the psu.

             ok(1)                  - the psu is ok.
             failed(2)              - the psu has failed.
             notFitted(3)           - the psu is not fitted.
             unknown(4)             - the status could not be determined."
        ::= { psuEntry 3 }



--------------------------------------------------------------------------------
--
-- System / Server/ Locale
--
--------------------------------------------------------------------------------

    serverDate OBJECT-TYPE
        SYNTAX DisplayString
        MAX-ACCESS read-only
        STATUS current
        DESCRIPTION
            "The local date reported by the server in the form
             YYYY-MM-DD

             Where YYYY is the year.
                   MM   is the number of the month (01-12).
                   DD   is the day of the month."
        ::= { locale 1 }

    serverTime OBJECT-TYPE
        SYNTAX DisplayString
        MAX-ACCESS read-only
        STATUS current
        DESCRIPTION
            "The local time reported by the server in the form
             HH:MM:SS (UTC+/-hh:mm)

             Where HH is the hour (using 24 hour clock).
                   MM is the minute.
                   SS is the second.
                   
                   The remainder of the date indicates the number
                   of hours (hh) and minutes (mm) east of UTC
                   the local time has been adjusted by.

             NOTE: a negative value for the UTC offset indicates
                   a time zone which is west of UTC."
        ::= { locale 2 }

    utcOffset OBJECT-TYPE
        SYNTAX Integer32
        MAX-ACCESS read-only
        STATUS current
        DESCRIPTION
            "The local time zone offset setting for the server 
             expressed as a number of minutes.
             NOTE: a negative value indicates a time zone west 
                   of UTC."
        ::= { locale 3 }

    daylightSavings OBJECT-TYPE
        SYNTAX INTEGER {
            daylightSavings(1),
            noDaylightSavings(2),
            unknown(3)
        }
        MAX-ACCESS read-only
        STATUS current
        DESCRIPTION
            "Indicates whether daylight savings are in effect."
        ::= { locale 4 }

    ntpServerNumber OBJECT-TYPE
        SYNTAX Integer32
        MAX-ACCESS read-only
        STATUS current
        DESCRIPTION
            "The number of NTP servers which have been configured
             to assist in synchronization of this silicon servers
             time."
        ::= { locale 5 }

    ntpServerTable OBJECT-TYPE
        SYNTAX SEQUENCE OF NtpServerEntry
        MAX-ACCESS not-accessible
        STATUS current
        DESCRIPTION
            "A table containing information about each NTP server.

             The number of entries in this table is given by the value of
             ntpServerNumber."
        ::= { locale 6 }

    ntpServerEntry OBJECT-TYPE
        SYNTAX NtpServerEntry
        MAX-ACCESS not-accessible
        STATUS current
        DESCRIPTION
            "Information about each configured NTP server."
        INDEX { ntpServerHost }
        ::= { ntpServerTable 1 }

    NtpServerEntry ::=
        SEQUENCE {
            ntpServerHost
                DisplayString
        }

    ntpServerHost OBJECT-TYPE
        SYNTAX DisplayString
        MAX-ACCESS read-only
        STATUS current
        DESCRIPTION
            "The hostname or IP address of the NTP server."
        ::= { ntpServerEntry 1 }

--------------------------------------------------------------------------------
--
-- System / Server / Failover
--
--------------------------------------------------------------------------------

    failoverConfigStatus OBJECT-TYPE
        SYNTAX INTEGER {
            configured(1),
            notConfigured(2)
        }
        MAX-ACCESS read-only
        STATUS obsolete
        DESCRIPTION
            "Indicates whether failover is configured for the silicon server.

            This object is obsolete.
            Failover has been replaced by clustering."
        ::= { failover 1 }

    failoverPrimaryName OBJECT-TYPE
        SYNTAX DisplayString
        MAX-ACCESS read-only
        STATUS obsolete
        DESCRIPTION
            "The primary management name or a zero length string if
             failover is not configured for this system.

            This object is obsolete.
            Failover has been replaced by clustering."
        ::= { failover 2 }

    failoverSystemName OBJECT-TYPE
        SYNTAX DisplayString
        MAX-ACCESS read-only
        STATUS obsolete
        DESCRIPTION
            "The system management name or a zero length string if
             failover is not configured for this system.

            This object is obsolete.
            Failover has been replaced by clustering."
        ::= { failover 3 }

    failoverSecondaryName OBJECT-TYPE
        SYNTAX DisplayString
        MAX-ACCESS read-only
        STATUS obsolete
        DESCRIPTION
            "The secondary management name or a zero length string if
             failover is not configured for this system.

            This object is obsolete.
            Failover has been replaced by clustering."
        ::= { failover 4 }

    failoverPrimaryIpAddr OBJECT-TYPE
        SYNTAX IpAddress
        MAX-ACCESS read-only
        STATUS obsolete
        DESCRIPTION
            "The primary IP address or 0.0.0.0 if
             failover is not configured for this system.

            This object is obsolete.
            Failover has been replaced by clustering."
        ::= { failover 5 }

    failoverSystemIpAddr OBJECT-TYPE
        SYNTAX IpAddress
        MAX-ACCESS read-only
        STATUS obsolete
        DESCRIPTION
            "The system IP address or 0.0.0.0 if
             failover is not configured for this system.

            This object is obsolete.
            Failover has been replaced by clustering."
        ::= { failover 6 }

    failoverSecondaryIpAddr OBJECT-TYPE
        SYNTAX IpAddress
        MAX-ACCESS read-only
        STATUS obsolete
        DESCRIPTION
            "The secondary IP address or 0.0.0.0 if
             failover is not configured for this system.

            This object is obsolete.
            Failover has been replaced by clustering."
        ::= { failover 7 }

    failoverPrimaryStatus OBJECT-TYPE
        SYNTAX INTEGER {
            notConfigured(1),
            master(2),
            standby(3),
            notDetected(4),
            unknown(5)
        }
        MAX-ACCESS read-only
        STATUS obsolete
        DESCRIPTION
            "The status of the primary.

            This object is obsolete.
            Failover has been replaced by clustering."
        ::= { failover 8 }

    failoverSecondaryStatus OBJECT-TYPE
        SYNTAX INTEGER {
            notConfigured(1),
            master(2),
            standby(3),
            notDetected(4),
            unknown(5)
        }
        MAX-ACCESS read-only
        STATUS obsolete
        DESCRIPTION
            "The status of the secondary.

            This object is obsolete.
            Failover has been replaced by clustering."
        ::= { failover 9 }

--------------------------------------------------------------------------------
--
-- System / Server / Cache / Sector Cache
--
--------------------------------------------------------------------------------

    sectorCacheMode OBJECT-TYPE
        SYNTAX INTEGER {
            ramdisk(1),
            writeThrough(2),
            writeBack(3),
            disabled(4),
            unknown(5)
        }
        MAX-ACCESS read-only
        STATUS current
        DESCRIPTION
            "The mode the disk sector cache is currently operating in."
        ::= { sectorCache 1 }

    sectorCacheDirtyPageWtmk OBJECT-TYPE
        SYNTAX INTEGER (0..99)
        MAX-ACCESS read-only
        STATUS obsolete
        DESCRIPTION
            "The current setting of the percentage dirty page watermark
             which is used in determining when to flush the disk sector
             cache.
             This object is now obsolete."
        ::= { sectorCache 2 }

    sectorCacheDirtyPageTimeout OBJECT-TYPE
        SYNTAX INTEGER (0..655)
        MAX-ACCESS read-only
        STATUS current
        DESCRIPTION
            "The current setting of the percentage dirty page timeout
             (specified in seconds) which is used in determining when
             to flush the disk sector cache."
        ::= { sectorCache 3 }

--------------------------------------------------------------------------------
--
-- System / Server / Cache / File System Cache
--
--------------------------------------------------------------------------------

    fileSysCacheMode OBJECT-TYPE
        SYNTAX INTEGER {
            writeThrough(1),
            writeBack(2)
        }
        MAX-ACCESS read-only
        STATUS obsolete
        DESCRIPTION
            "The mode the file system cache is currently operating in.

            This object is obsolete."
        ::= { fileSysCache 1 }

    fileSysTransactionLogging OBJECT-TYPE
        SYNTAX INTEGER {
            enabled(1),
            disabled(2)
        }
        MAX-ACCESS read-only
        STATUS obsolete
        DESCRIPTION
            "Indicates whether file system transaction logging is enabled
             or not.

            This object is obsolete."
        ::= { fileSysCache 2 }

    fileSysCacheTimeout OBJECT-TYPE
        SYNTAX INTEGER (1..655)
        MAX-ACCESS read-only
        STATUS obsolete
        DESCRIPTION
            "The file system cache timeout in seconds.

            This object is obsolete."
        ::= { fileSysCache 3 }

    fileSysUpdateLastAccess OBJECT-TYPE
        SYNTAX INTEGER {
            enabled(1),
            disabled(2)
        }
        MAX-ACCESS read-only
        STATUS current
        DESCRIPTION
            "Indicates whether the file system should update the last
             access time(s) on files or not."
        ::= { fileSysCache 4 }

--------------------------------------------------------------------------------
--
-- System / Server / Clustering
--
--------------------------------------------------------------------------------

    clusterName OBJECT-TYPE
        SYNTAX DisplayString
        MAX-ACCESS read-only
        STATUS current
        DESCRIPTION
            "The cluster management name."
        ::= { clustering 1 }

    clusterUuid OBJECT-TYPE
        SYNTAX DisplayString
        MAX-ACCESS read-only
        STATUS current
        DESCRIPTION
            "A unique identification number for the cluster."
        ::= { clustering 2 }

    clusterConfig OBJECT-TYPE
        SYNTAX INTEGER {
            singleNode(1),
            activeStandby(2),
            activeActive(3),
            unknown(4)
        }
        MAX-ACCESS read-only
        STATUS current
        DESCRIPTION
            "The configuration of the cluster:
             1 - single standalone node
             2 - active / standby pair
             3 - active / active cluster
             4 - the configuration could not be determined."
        ::= { clustering 3 }

    clusterQuorumDeviceName OBJECT-TYPE
        SYNTAX DisplayString
        MAX-ACCESS read-only
        STATUS current
        DESCRIPTION
            "The quorum device management name."
        ::= { clustering 4 }

    clusterQuorumDeviceIpAddr OBJECT-TYPE
        SYNTAX IpAddress
        MAX-ACCESS read-only
        STATUS current
        DESCRIPTION
            "The quorum device IP address, or 0.0.0.0 if no quorum device
             is present."
        ::= { clustering 5 }

    clusterQuorumDeviceOwnedByPNode OBJECT-TYPE
        SYNTAX Integer32
        MAX-ACCESS read-only
        STATUS current
        DESCRIPTION
            "The identification number of the physical node which
             owns this quorum device. A value of -1 indicates that
             this cannot be determined."
        ::= { clustering 6 }

    clusterQuorumDeviceStatus OBJECT-TYPE
        SYNTAX INTEGER {
            unknown(0),
            unconfigured(1),
            offLine(2),
            owned(3),
            configured(4),
            granted(5),
            clusterNodeNotUp(6),
            misconfigured(7)
        }
        MAX-ACCESS read-only
        STATUS current
        DESCRIPTION
            "The status of the quorum device:
             0 - unknown
             1 - unconfigured
             2 - off line
             3 - owned
             4 - configured
             5 - granted
             6 - cluster node being queried is not up
             7 - quorum device does not have the correct
                 UUID for the cluster"
        ::= { clustering 7 }

    clusterPNodeNumber OBJECT-TYPE
        SYNTAX Integer32
        MAX-ACCESS read-only
        STATUS current
        DESCRIPTION
            "The number of physical nodes in the cluster. A value of -1
            indicates that this cannot be determined.
            
            This object is now obsolete, and has been replaced with
            clusterNodeNumber."
        ::= { clustering 8 }

    clusterPNodeTable OBJECT-TYPE
        SYNTAX SEQUENCE OF ClusterPNodeEntry
        MAX-ACCESS not-accessible
        STATUS current
        DESCRIPTION
            "Information about each physical node in the cluster.

             The number of entries in this table is given by
             clusterPNodeNumber.
            
            This object is now obsolete, and has been replaced with
            clusterNodeTable."
        ::= { clustering 9 }

    clusterPNodeEntry OBJECT-TYPE
        SYNTAX ClusterPNodeEntry
        MAX-ACCESS not-accessible
        STATUS current
        DESCRIPTION
            "Information about each physical node.
            
            This object is now obsolete, and has been replaced with
            clusterNodeEntry."
        INDEX { clusterPNodeId }
        ::= { clusterPNodeTable 1 }

    ClusterPNodeEntry ::=
        SEQUENCE {
            clusterPNodeId
                Integer32,
            clusterPNodeName
                DisplayString,
            clusterPNodeIpAddr
                IpAddress,
            clusterPNodeStatus
                INTEGER
        }

    clusterPNodeId OBJECT-TYPE
        SYNTAX Integer32 (0..255)
        MAX-ACCESS read-only
        STATUS current
        DESCRIPTION
            "The identification number of the physical node. A value of -1
            indicates that this cannot be determined.
            
            This object is now obsolete, and has been replaced with
            clusterNodeId."
        ::= { clusterPNodeEntry 1 }

    clusterPNodeName OBJECT-TYPE
        SYNTAX DisplayString
        MAX-ACCESS read-only
        STATUS current
        DESCRIPTION
            "The management name of the physical node.
            
            This object is now obsolete, and has been replaced with
            clusterNodeName."
        ::= { clusterPNodeEntry 2 }

    clusterPNodeIpAddr OBJECT-TYPE
        SYNTAX IpAddress
        MAX-ACCESS read-only
        STATUS current
        DESCRIPTION
            "The IP address of the physical node. A value of 0.0.0.0 indicates
            that this cannot be determined.
            
            This object is now obsolete, and has been replaced with
            clusterNodeIpAddr."
        ::= { clusterPNodeEntry 3 }

    clusterPNodeStatus OBJECT-TYPE
        SYNTAX INTEGER {
            unknown(1),
            up(2),
            notUp(3),
            onLine(4),
            dead(5),
            dormant(6)
        }
        MAX-ACCESS read-only
        STATUS current
        DESCRIPTION
            "The status of the physical node:
             1 - unknown
             2 - up
             3 - not up
             4 - on line
             5 - dead
             6 - dormant
            
            This object is now obsolete, and has been replaced with
            clusterNodeStatus."
        ::= { clusterPNodeEntry 4 }

    clusterVNodeNumber OBJECT-TYPE
        SYNTAX Integer32
        MAX-ACCESS read-only
        STATUS current
        DESCRIPTION
            "The number of virtual nodes in the cluster. A value of -1
            indicates that this cannot be determined."
        ::= { clustering 10 }

    clusterVNodeTable OBJECT-TYPE
        SYNTAX SEQUENCE OF ClusterVNodeEntry
        MAX-ACCESS not-accessible
        STATUS current
        DESCRIPTION
            "Information about each virtual node in the cluster.

             The number of entries in this table is given by
             clusterVNodeNumber"
        ::= { clustering 11 }

    clusterVNodeEntry OBJECT-TYPE
        SYNTAX ClusterVNodeEntry
        MAX-ACCESS not-accessible
        STATUS current
        DESCRIPTION
            "Information about each virtual node in the cluster."
        INDEX { clusterVNodeId }
        ::= { clusterVNodeTable 1 }

    ClusterVNodeEntry ::=
        SEQUENCE {
            clusterVNodeId
                Integer32,
            clusterVNodeName
                DisplayString,
            clusterVNodeIpAddr
                IpAddress,
            clusterVNodeStatus
                INTEGER,
            clusterVNodeAdmin
                INTEGER,
            clusterVNodeHostedBy
                Integer32
        }

    clusterVNodeId OBJECT-TYPE
        SYNTAX Integer32 (0..255)
        MAX-ACCESS read-only
        STATUS current
        DESCRIPTION
            "The identification number of the virtual node. A value of -1
            indicates that this cannot be determined."
        ::= { clusterVNodeEntry 1 }

    clusterVNodeName OBJECT-TYPE
        SYNTAX DisplayString
        MAX-ACCESS read-only
        STATUS current
        DESCRIPTION
            "The management name of the virtual node."
        ::= { clusterVNodeEntry 2 }

    clusterVNodeIpAddr OBJECT-TYPE
        SYNTAX IpAddress
        MAX-ACCESS read-only
        STATUS current
        DESCRIPTION
            "The IP address of the virtual node. A value of 0.0.0.0 indicates
            that this cannot be determined."
        ::= { clusterVNodeEntry 3 }

    clusterVNodeStatus OBJECT-TYPE
        SYNTAX INTEGER {
            unknown(1),
            onLine(2),
            offLine(3)
        }
        MAX-ACCESS read-only
        STATUS current
        DESCRIPTION
            "The status of the virtual node:
             1 - unknown
             2 - on line
             3 - off line"
        ::= { clusterVNodeEntry 4 }

    clusterVNodeAdmin OBJECT-TYPE
        SYNTAX INTEGER {
            false(0),
            true(1),
            unknown(2)
        }
        MAX-ACCESS read-only
        STATUS current
        DESCRIPTION
            "Whether the virtual node is the administrative virtual node:
             0 - a service node (i.e. not the administrative virtual node)
             1 - the administrative virtual node
             2 - cannot be determined"
        ::= { clusterVNodeEntry 5 }

    clusterVNodeHostedBy OBJECT-TYPE
        SYNTAX Integer32
        MAX-ACCESS read-only
        STATUS current
        DESCRIPTION
            "The identification number of the physical node hosting this
            virtual node. A value of -1 indicates that this cannot be 
            determined."
        ::= { clusterVNodeEntry 6 }

--------------------------------------------------------------------------------
--
-- System / Server / Serial Numbers
--
--------------------------------------------------------------------------------


    serialNumberTable OBJECT-TYPE
        SYNTAX SEQUENCE OF SerialNumberEntry
        MAX-ACCESS not-accessible
        STATUS current
        DESCRIPTION
            "Serial numbers for server components."
        ::= { serialNumbers 1 }

    serialNumberEntry OBJECT-TYPE
        SYNTAX SerialNumberEntry
        MAX-ACCESS not-accessible
        STATUS current
        DESCRIPTION
            "Serial number for a component."
        INDEX { componentType, subComponentType, clusterNode }
        ::= { serialNumberTable 1 }

    SerialNumberEntry ::=
        SEQUENCE {
            componentType
                INTEGER,
            subComponentType
                INTEGER,
            clusterNode
                Integer32,
            serialNumber
                DisplayString
        }

    componentType OBJECT-TYPE
        SYNTAX INTEGER {
            chassis(1),
            blade(2),
            psu(3)
        }
        MAX-ACCESS read-only
        STATUS current
        DESCRIPTION
            "The type of component:
             1 - a chassis
             2 - a blade, such as NIM2
             3 - a power supply unit"
        ::= { serialNumberEntry 1 }

    subComponentType OBJECT-TYPE
        SYNTAX INTEGER {
            unknown(0),
            nim1(1),
            nim2(2),
            nim3(3),
            fsa17455(4),
            fsa1(5),
            fsa2(6),
            fsx1(7),
            fsb1(8),
            fsb2(9),
            sim1(10),
            sim2(11),
            chassis(12),
            psu1(13),
            psu2(14),
            fsb3(15),
            sim3(16),
            mcp1(17),
            mmb1(18),
            mfb1(19)
        }
        MAX-ACCESS read-only
        STATUS current
        DESCRIPTION
            "The sub-type of component."
        ::= { serialNumberEntry 2 }

    clusterNode OBJECT-TYPE
        SYNTAX Integer32 (0..255)
        MAX-ACCESS read-only
        STATUS current
        DESCRIPTION
            "The identification number of the cluster node hosting this 
             component. A value of -1 indicates that this cannot be 
             determined."
        ::= { serialNumberEntry 3 }

    serialNumber OBJECT-TYPE
        SYNTAX DisplayString
        MAX-ACCESS read-only
        STATUS current
        DESCRIPTION
            "The serial number of the component."
        ::= { serialNumberEntry 4 }



--------------------------------------------------------------------------------
--
-- System / Storage / Racks
--
--------------------------------------------------------------------------------

    rackNumber OBJECT-TYPE
        SYNTAX Integer32
        MAX-ACCESS read-only
        STATUS obsolete
        DESCRIPTION
            "The number of racks (regardless of their current state)
             which are present in this system.

            This object is now obsolete."
        ::= { racks 1 }

    rackTable OBJECT-TYPE
        SYNTAX SEQUENCE OF RackEntry
        MAX-ACCESS not-accessible
        STATUS obsolete
        DESCRIPTION
            "A table containing information about each rack in
             this system.
             
             The number of entries in this table is given by the value of 
             rackNumber.

             This table is now obsolete."
        ::= { racks 2 }

    rackEntry OBJECT-TYPE
        SYNTAX RackEntry
        MAX-ACCESS not-accessible
        STATUS obsolete
        DESCRIPTION
            "Status information about each rack in the system.

             This table is now obsolete."
        INDEX { rackIndex }
        ::= { rackTable 1 }

    RackEntry ::=
        SEQUENCE {
            rackIndex
                Integer32,
            rackStatus
                INTEGER,
            rackNumberOfEnclosures
                Unsigned32,
            rackNumberOfPhysicalDrives
                Unsigned32
        }

    rackIndex OBJECT-TYPE
        SYNTAX Integer32 (1..10)
        MAX-ACCESS read-only
        STATUS obsolete
        DESCRIPTION
            "A unique value for each rack present in this system.

             Its value ranges between 1 and the value of rackNumber.

             This object is now obsolete."
        ::= { rackEntry 1 }

    rackStatus OBJECT-TYPE
        SYNTAX INTEGER {
            ok(1),
            storageFailed(2),
            loopFailed(3),
            otherFailure(4)
        }
        MAX-ACCESS read-only
        STATUS obsolete
        DESCRIPTION
            "Indicates the status of the rack.

             ok(1)            - the RAID monitoring software is
                                communicating with the rack.
             storageFailed(2) - the RAID controller associated with
                                this rack has failed.
             loopFailed(3)    - the fibre channel loop has failed.
             otherFailure(4)  - the system is unable to communicate with the
                                rack, it may be booting.

             This object is now obsolete."
        ::= { rackEntry 2 }

    rackNumberOfEnclosures OBJECT-TYPE
        SYNTAX Unsigned32
        MAX-ACCESS read-only
        STATUS obsolete
        DESCRIPTION
            "The number of storage enclosures which are normally accessible
             by this rack.
             NOTE: If rackStatus is not ok, the value of this variable
                   will be 0.

             This object is now obsolete."
        ::= { rackEntry 3 }

    rackNumberOfPhysicalDrives OBJECT-TYPE
        SYNTAX Unsigned32
        MAX-ACCESS read-only
        STATUS obsolete
        DESCRIPTION
            "The number of physical drives which are normally accessible
             by this rack.
             NOTE: If rackStatus is not ok, the value of this variable 
                   will be 0.

             This object is now obsolete."
        ::= { rackEntry 4 }

--------------------------------------------------------------------------------
--
-- System / Storage / RAID / Controllers
--
--------------------------------------------------------------------------------

    raidControllerTable OBJECT-TYPE
        SYNTAX SEQUENCE OF RaidControllerEntry
        MAX-ACCESS not-accessible
        STATUS obsolete
        DESCRIPTION
            "A table containing general information about RAID controller(s)
             present in each rack within the system.

             A rack may contain dual controllers for redundancy purposes.
             This (if present) will be indicated by the secondaryStatus field.

             The number of entries in the table is given by the value of
             rackNumber provided that the system can communicate with the rack.

             This table is now obsolete."
        ::= { controllers 1 }

    raidControllerEntry OBJECT-TYPE
        SYNTAX RaidControllerEntry
        MAX-ACCESS not-accessible
        STATUS obsolete
        DESCRIPTION
            "General information about the RAID controller(s) in a rack.

             This table is now obsolete."
        INDEX { raidControllerRackIndex }
        ::= { raidControllerTable 1 }

    RaidControllerEntry ::=
        SEQUENCE {
            raidControllerRackIndex
                Integer32,
            raidControllerWWN
                DisplayString,
            raidControllerPrimaryStatus
                INTEGER,
            raidControllerSecondaryStatus
                INTEGER,
            raidControllerManufacturer
                DisplayString,
            raidControllerModel
                DisplayString,
            raidControllerCacheSize
                Unsigned32
        }

    raidControllerRackIndex OBJECT-TYPE
        SYNTAX Integer32 (1..10)
        MAX-ACCESS read-only
        STATUS obsolete
        DESCRIPTION
            "The rack in which the RAID controller(s) are located.
             The controller(s) identified by a particular value
             of this index is located within the rack identified by the
             same value of rackIndex.

             This object is now obsolete."
        ::= { raidControllerEntry 1 }

    raidControllerWWN OBJECT-TYPE
        SYNTAX DisplayString
        MAX-ACCESS read-only
        STATUS obsolete
        DESCRIPTION
            "The world wide name identifying the RAID controller(s).
             NOTE: If the world wide name cannot be obtained this value will
                   be a zero length string.

             This object is now obsolete."
        ::= { raidControllerEntry 2 }

    raidControllerPrimaryStatus OBJECT-TYPE
        SYNTAX INTEGER {
            online(1),
            failed(2),
            notPresent(3),
            unknown(4),
            inserted(5),
            offline(6)
        }
        MAX-ACCESS read-only
        STATUS obsolete
        DESCRIPTION
            "The status of primary RAID controller.

             This object is now obsolete."
        ::= { raidControllerEntry 3 }

    raidControllerSecondaryStatus OBJECT-TYPE
        SYNTAX INTEGER {
            online(1),
            failed(2),
            notPresent(3),
            unknown(4)
        }
        MAX-ACCESS read-only
        STATUS obsolete
        DESCRIPTION
            "The status of secondary RAID controller.

             NOTE: A status of notPresent(3) indicates that there is only
                   one RAID controller within this rack.

             This object is now obsolete."
        ::= { raidControllerEntry 4 }

    raidControllerManufacturer OBJECT-TYPE
        SYNTAX DisplayString
        MAX-ACCESS read-only
        STATUS obsolete
        DESCRIPTION
            "The manufacturer of the RAID controller(s).
             NOTE: If the manufacturer cannot be obtained this value will 
                   be a zero length string.

             This object is now obsolete."
        ::= { raidControllerEntry 5 }

    raidControllerModel OBJECT-TYPE
        SYNTAX DisplayString
        MAX-ACCESS read-only
        STATUS obsolete
        DESCRIPTION
            "The model of the RAID controller(s).
             NOTE: If the model cannot be obtained this value will 
                   be a zero length string.

             This object is now obsolete."
        ::= { raidControllerEntry 6 }

    raidControllerCacheSize OBJECT-TYPE
        SYNTAX Unsigned32
        MAX-ACCESS read-only
        STATUS obsolete
        DESCRIPTION
            "The size of the RAID controller(s) cache in bytes.
             NOTE: If the cache size cannot be obtained this value will
                   be a 0.

             This object is now obsolete."
        ::= { raidControllerEntry 7 }

    raidControllerConfigTable OBJECT-TYPE
        SYNTAX SEQUENCE OF RaidControllerConfigEntry
        MAX-ACCESS not-accessible
        STATUS obsolete
        DESCRIPTION
            "A table containing configuration information about
             the RAID controller present in each rack within 
             the system.  This information is the same for a
             RAID controller which has redundancy.

             The number of entries in the table is given by the value of
             rackNumber provided that the system can communicate with the rack.

             This object is now obsolete."
        ::= { controllers 2 }

    raidControllerConfigEntry OBJECT-TYPE
        SYNTAX RaidControllerConfigEntry
        MAX-ACCESS not-accessible
        STATUS obsolete
        DESCRIPTION
            "Configuration information about the RAID controller in a rack.

             This object is now obsolete."
        INDEX { raidControllerConfigRackIndex }
        ::= { raidControllerConfigTable 1 }

    RaidControllerConfigEntry ::=
        SEQUENCE {
            raidControllerConfigRackIndex
                Integer32,
            raidControllerConfigDRAMSize
                Unsigned32,
            raidControllerConfigFlashSize
                Unsigned32,
            raidControllerConfigNVRSize
                Unsigned32,
            raidControllerConfigClockSpeed
                Unsigned32,
            raidControllerConfigMemAccess
                Unsigned32,
            raidControllerConfigMemCycle
                Unsigned32,
            raidControllerConfigPhysicalSectorSize
                Unsigned32,
            raidControllerConfigLogicalSectorSize
                Unsigned32,
            raidControllerConfigMaxSystemDrives
                Unsigned32,
            raidControllerConfigMaxDrivesPerSystemDrive
                Unsigned32,
            raidControllerConfigMaxSpanPerVirtualDrive
                Unsigned32,
            raidControllerConfigFirmwareVersion
                DisplayString,
            raidControllerConfigFirmwareType
                Unsigned32,
            raidControllerConfigFirmwareMajor
                Unsigned32,
            raidControllerConfigFirmwareMinor
                Unsigned32,
            raidControllerConfigMaximumCommands
                Unsigned32,
            raidControllerConfigFirmwareBuild
                Unsigned32,
            raidControllerConfigRebuildRate
                Unsigned32,
            raidControllerConfigRebuildUnit
                Unsigned32,
            raidControllerConfigRebuildOn
                Unsigned32,
            raidControllerConfigRebuildOff
                Unsigned32
        }

    raidControllerConfigRackIndex OBJECT-TYPE
        SYNTAX Integer32 (1..10)
        MAX-ACCESS read-only
        STATUS obsolete
        DESCRIPTION
            "The rack in which the RAID controller is located.
             The controller identified by a particular value 
             of this index is located within the rack identified by the 
             same value of rackIndex.

             This object is now obsolete."
        ::= { raidControllerConfigEntry 1 }

    raidControllerConfigDRAMSize OBJECT-TYPE
        SYNTAX Unsigned32
        MAX-ACCESS read-only
        STATUS obsolete
        DESCRIPTION
            "The size of the DRAM present in the RAID controller 
             in bytes.

             This object is now obsolete."
        ::= { raidControllerConfigEntry 2 }

    raidControllerConfigFlashSize OBJECT-TYPE
        SYNTAX Unsigned32
        MAX-ACCESS read-only
        STATUS obsolete
        DESCRIPTION
            "The size of flash memory present in the RAID controller
             in bytes.

             This object is now obsolete."
        ::= { raidControllerConfigEntry 3 }

    raidControllerConfigNVRSize OBJECT-TYPE
        SYNTAX Unsigned32
        MAX-ACCESS read-only
        STATUS obsolete
        DESCRIPTION
            "The size of non volatile memory present in the RAID controller 
             in bytes.

             This object is now obsolete."
        ::= { raidControllerConfigEntry 4 }

    raidControllerConfigClockSpeed OBJECT-TYPE
        SYNTAX Unsigned32
        MAX-ACCESS read-only
        STATUS obsolete
        DESCRIPTION
            "The clock speed of the memory in the RAID controller
             in nanoseconds.

             This object is now obsolete."
        ::= { raidControllerConfigEntry 5 }

    raidControllerConfigMemAccess OBJECT-TYPE
        SYNTAX Unsigned32
        MAX-ACCESS read-only
        STATUS obsolete
        DESCRIPTION
            "The access time of the memory in the RAID controller
             in nanoseconds.

             This object is now obsolete."
        ::= { raidControllerConfigEntry 6 }

    raidControllerConfigMemCycle OBJECT-TYPE
        SYNTAX Unsigned32
        MAX-ACCESS read-only
        STATUS obsolete
        DESCRIPTION
            "The cycle time of the memory in the RAID controller
             in nanoseconds.

             This object is now obsolete."
        ::= { raidControllerConfigEntry 7 }

    raidControllerConfigPhysicalSectorSize OBJECT-TYPE
        SYNTAX Unsigned32
        MAX-ACCESS read-only
        STATUS obsolete
        DESCRIPTION
            "The physical sector size supported by the RAID controller
             in bytes.

             This object is now obsolete."
        ::= { raidControllerConfigEntry 8 }

    raidControllerConfigLogicalSectorSize OBJECT-TYPE
        SYNTAX Unsigned32
        MAX-ACCESS read-only
        STATUS obsolete
        DESCRIPTION
            "The logical sector size supported by the RAID controller
             in bytes.

             This object is now obsolete."
        ::= { raidControllerConfigEntry 9 }

    raidControllerConfigMaxSystemDrives OBJECT-TYPE
        SYNTAX Unsigned32
        MAX-ACCESS read-only
        STATUS obsolete
        DESCRIPTION
            "The maximum number of system drives supported by the
             RAID controller.

             This object is now obsolete."
        ::= { raidControllerConfigEntry 10 }

    raidControllerConfigMaxDrivesPerSystemDrive OBJECT-TYPE
        SYNTAX Unsigned32
        MAX-ACCESS read-only
        STATUS obsolete
        DESCRIPTION
            "The maximum number of drives which the RAID controller 
             permits to be part of a system drive.

             This object is now obsolete."
        ::= { raidControllerConfigEntry 11 }

    raidControllerConfigMaxSpanPerVirtualDrive OBJECT-TYPE
        SYNTAX Unsigned32
        MAX-ACCESS read-only
        STATUS obsolete
        DESCRIPTION
            "The maximum number of spans which the RAID controller permits
             to be part of a virtual drive.

             This object is now obsolete."
        ::= { raidControllerConfigEntry 12 }

    raidControllerConfigFirmwareVersion OBJECT-TYPE
        SYNTAX DisplayString
        MAX-ACCESS read-only
        STATUS obsolete
        DESCRIPTION
            "Firmware version installed in this RAID controller.

             This object is now obsolete."
        ::= { raidControllerConfigEntry 13 }

    raidControllerConfigFirmwareType OBJECT-TYPE
        SYNTAX Unsigned32
        MAX-ACCESS read-only
        STATUS obsolete
        DESCRIPTION
            "Firmware type installed in this RAID controller.

             This object is now obsolete."
        ::= { raidControllerConfigEntry 14 }

    raidControllerConfigFirmwareMajor OBJECT-TYPE
        SYNTAX Unsigned32
        MAX-ACCESS read-only
        STATUS obsolete
        DESCRIPTION
            "Major version of firmware installed in this RAID controller.

             This object is now obsolete."
        ::= { raidControllerConfigEntry 15 }

    raidControllerConfigFirmwareMinor OBJECT-TYPE
        SYNTAX Unsigned32
        MAX-ACCESS read-only
        STATUS obsolete
        DESCRIPTION
            "Minor version of firmware installed in the RAID controller.

             This object is now obsolete."
        ::= { raidControllerConfigEntry 16 }

    raidControllerConfigMaximumCommands OBJECT-TYPE
        SYNTAX Unsigned32
        MAX-ACCESS read-only
        STATUS obsolete
        DESCRIPTION
            "Maximum number concurrent commands that may be performed by
             the RAID controller.

             This object is now obsolete."
        ::= { raidControllerConfigEntry 17 }

    raidControllerConfigFirmwareBuild OBJECT-TYPE
        SYNTAX Unsigned32
        MAX-ACCESS read-only
        STATUS obsolete
        DESCRIPTION
            "Build version of the firmware installed in the RAID controller.

             This object is now obsolete."
        ::= { raidControllerConfigEntry 18 }

    raidControllerConfigRebuildRate OBJECT-TYPE
        SYNTAX Unsigned32
        MAX-ACCESS read-only
        STATUS obsolete
        DESCRIPTION
            "The rebuild rate of the RAID controller.

             This object is now obsolete."
        ::= { raidControllerConfigEntry 19 }

    raidControllerConfigRebuildUnit OBJECT-TYPE
        SYNTAX Unsigned32
        MAX-ACCESS read-only
        STATUS obsolete
        DESCRIPTION
            "The rebuild unit size in milliseconds used in the rate
             figure raidControllerConfigRebuildRate for the RAID controller.

             This object is now obsolete."
        ::= { raidControllerConfigEntry 20 }

    raidControllerConfigRebuildOn OBJECT-TYPE
        SYNTAX Unsigned32
        MAX-ACCESS read-only
        STATUS obsolete
        DESCRIPTION
            "The rebuild on time of the RAID controller.

             This object is now obsolete."
        ::= { raidControllerConfigEntry 21 }

    raidControllerConfigRebuildOff OBJECT-TYPE
        SYNTAX Unsigned32
        MAX-ACCESS read-only
        STATUS obsolete
        DESCRIPTION
            "The rebuild off time of the RAID controller.

             This object is now obsolete."
        ::= { raidControllerConfigEntry 22 }

    raidControllerBatteryBackupTable OBJECT-TYPE
        SYNTAX SEQUENCE OF RaidControllerBatteryBackupEntry
        MAX-ACCESS not-accessible
        STATUS obsolete
        DESCRIPTION
            "A table containing information about the battery
             backup unit within each RAID controller present in 
             each rack within the system.

             The number of entries in the table is given by the value of 
             rackNumber provided that the system can communicate with the rack.

             This object is now obsolete."
        ::= { controllers 3 }

    raidControllerBatteryBackupEntry OBJECT-TYPE
        SYNTAX RaidControllerBatteryBackupEntry
        MAX-ACCESS not-accessible
        STATUS obsolete
        DESCRIPTION
            "Information about the battery backup unit within
             a RAID controller.

             This object is now obsolete."
        INDEX { raidControllerBatteryBackupRackIndex }
        ::= { raidControllerBatteryBackupTable 1 }

    RaidControllerBatteryBackupEntry ::=
        SEQUENCE {
            raidControllerBatteryBackupRackIndex
                Integer32,
            raidControllerBatteryBackupNoSync
                INTEGER,
            raidControllerBatteryBackupOutOfSync
                INTEGER,
            raidControllerBatteryBackupFirstWarning
                INTEGER,
            raidControllerBatteryBackupSecondWarning
                INTEGER,
            raidControllerBatteryBackupReconditioning
                INTEGER,
            raidControllerBatteryBackupDischarging
                INTEGER,
            raidControllerBatteryBackupFastCharging
                INTEGER,
            raidControllerBatteryBackupLowPower
                INTEGER,
            raidControllerBatteryBackupChargePercent
                INTEGER,
            raidControllerBatteryBackupHardwareVersion
                Unsigned32,
            raidControllerBatteryBackupBatteryType
                INTEGER,
            raidControllerBatteryBackupThreshold
                Unsigned32
        }

    raidControllerBatteryBackupRackIndex OBJECT-TYPE
        SYNTAX Integer32 (1..10)
        MAX-ACCESS read-only
        STATUS obsolete
        DESCRIPTION
            "The rack in which the RAID controller containing
             the battery backup unit is located.
             The controller and battery backup unit identified 
             by a particular value of this index is located within
             the rack identified by the same value of rackIndex.

             This object is now obsolete."
        ::= { raidControllerBatteryBackupEntry 1 }

    raidControllerBatteryBackupNoSync OBJECT-TYPE
        SYNTAX INTEGER {
            noSync(1),
            sync(2),
            unknown(3)
        }
        MAX-ACCESS read-only
        STATUS obsolete
        DESCRIPTION
            "Indicates whether a reconditioning cycle has been performed
             since power up of the RAID controller.

             noSync(1) - there has NOT been a reconditioning cycle
                         since powering up the RAID controller.
             sync(2)   - there has been a reconditioning cycle
                         since powering up the RAID controller.

             This object is now obsolete."
        ::= { raidControllerBatteryBackupEntry 2 }

    raidControllerBatteryBackupOutOfSync OBJECT-TYPE
        SYNTAX INTEGER {
            outOfsync(1),
            sync(2),
            unknown(3)
        }
        MAX-ACCESS read-only
        STATUS obsolete
        DESCRIPTION
            "Indicates whether a reconditioning cycle is needed.

             outOfSync(1) - a reconditioning cycle needs to be performed.
             sync(2)      - a reconditioning cycle does NOT need to be
                            performed.

             This object is now obsolete."
        ::= { raidControllerBatteryBackupEntry 3 }

    raidControllerBatteryBackupFirstWarning OBJECT-TYPE
        SYNTAX INTEGER {
            firstWarning(1),
            noFirstWarning(2),
            unknown(3)
        }
        MAX-ACCESS read-only
        STATUS obsolete
        DESCRIPTION
            "Indicates whether a first warning for low battery power
             has been issued.

             firstWarning(1)   - a first warning has been issued.
             noFirstWarning(2) - no first warning has been issued.

             This object is now obsolete."
        ::= { raidControllerBatteryBackupEntry 4 }

    raidControllerBatteryBackupSecondWarning OBJECT-TYPE
        SYNTAX INTEGER {
            secondWarning(1),
            noSecondWarning(2),
            unknown(3)
        }
        MAX-ACCESS read-only
        STATUS obsolete
        DESCRIPTION
            "Indicates whether a second warning for low battery power
             has been issued.

             secondWarning(1)   - a second warning has been issued.
             noSecondWarning(2) - no second warning has been issued.

             This object is now obsolete."
        ::= { raidControllerBatteryBackupEntry 5 }

    raidControllerBatteryBackupReconditioning OBJECT-TYPE
        SYNTAX INTEGER {
            reconditioning(1),
            notReconditioning(2),
            unknown(3)
        }
        MAX-ACCESS read-only
        STATUS obsolete
        DESCRIPTION
            "Indicates whether the battery is currently being reconditioned.

             reconditioning(1)    - the battery is being reconditioned.
             notReconditioning(2) - the battery is NOT being reconditioned.

             This object is now obsolete."
        ::= { raidControllerBatteryBackupEntry 6 }

    raidControllerBatteryBackupDischarging OBJECT-TYPE
        SYNTAX INTEGER {
            discharging(1),
            notDischarging(2),
            unknown(3)
        }
        MAX-ACCESS read-only
        STATUS obsolete
        DESCRIPTION
            "Indicates whether the battery is currently being discharged.

             discharging(1)    - the battery is currently being discharged.
             notDischarging(2) - the battery is NOT currently being discharged.

             This object is now obsolete."
        ::= { raidControllerBatteryBackupEntry 7 }

    raidControllerBatteryBackupFastCharging OBJECT-TYPE
        SYNTAX INTEGER {
            fastCharging(1),
            notFastCharging(2),
            unknown(3)
        }
        MAX-ACCESS read-only
        STATUS obsolete
        DESCRIPTION
            "Indicates whether the battery is currently fast charging.

             fastCharging(1)    - the battery is currently being fast
                                  charged.
             notFastCharging(2) - the battery is NOT currently being fast
                                  charged.

             This object is now obsolete."
        ::= { raidControllerBatteryBackupEntry 8 }

    raidControllerBatteryBackupLowPower OBJECT-TYPE
        SYNTAX INTEGER {
            lowPowerAlarm(1),
            noLowPowerAlarm(2),
            unknown(3)
        }
        MAX-ACCESS read-only
        STATUS obsolete
        DESCRIPTION
            "Indicates whether the battery is issuing a low power alarm.

             lowPowerAlarm(1)   - the battery is issuing a low power
                                  alarm.
             noLowPowerAlarm(2) - the battery is NOT issuing a lower
                                  power alarm.

             This object is now obsolete."
        ::= { raidControllerBatteryBackupEntry 9 }

    raidControllerBatteryBackupChargePercent OBJECT-TYPE
        SYNTAX INTEGER (0..100)
        MAX-ACCESS read-only
        STATUS obsolete
        DESCRIPTION
            "The percentage charge held by the battery.

             This object is now obsolete."
        ::= { raidControllerBatteryBackupEntry 10 }

    raidControllerBatteryBackupHardwareVersion OBJECT-TYPE
        SYNTAX Unsigned32
        MAX-ACCESS read-only
        STATUS obsolete
        DESCRIPTION
            "The hardware version of the battery backup unit.

             This object is now obsolete."
        ::= { raidControllerBatteryBackupEntry 11 }

    raidControllerBatteryBackupBatteryType OBJECT-TYPE
        SYNTAX INTEGER {
            niCd(1),
            none(2),
            unknown(3),
            niMH(4),
            lion(5)
        }
        MAX-ACCESS read-only
        STATUS obsolete
        DESCRIPTION
            "The type of the battery in the battery backup unit.

             This object is now obsolete."
        ::= { raidControllerBatteryBackupEntry 12 }

    raidControllerBatteryBackupThreshold OBJECT-TYPE
        SYNTAX Unsigned32
        MAX-ACCESS read-only
        STATUS obsolete
        DESCRIPTION
            "The threshold of the battery life in minutes.

             This object is now obsolete."
        ::= { raidControllerBatteryBackupEntry 13 }

    raidControllerActiveTaskNumber OBJECT-TYPE
        SYNTAX Integer32
        MAX-ACCESS read-only
        STATUS obsolete
        DESCRIPTION
            "The number of active tasks which are currently being
             performed by the RAID controller(s) in the system.

             This object is now obsolete."
        ::= { controllers 4 }

    raidControllerActiveTaskTable OBJECT-TYPE
        SYNTAX SEQUENCE OF RaidControllerActiveTaskEntry
        MAX-ACCESS not-accessible
        STATUS obsolete
        DESCRIPTION
            "A table containing information about the tasks currently
             being performed by RAID controller(s) present in the system.

             The number of entries in this table is given by the value of
             raidControllerActiveTaskNumber.

             This object is now obsolete."
        ::= { controllers 5 }

    raidControllerActiveTaskEntry OBJECT-TYPE
        SYNTAX RaidControllerActiveTaskEntry
        MAX-ACCESS not-accessible
        STATUS obsolete
        DESCRIPTION
            "Information about the active task being performed by the 
             RAID controller.

             This object is now obsolete."
        INDEX { raidControllerActiveTaskRackIndex, raidControllerActiveTaskIndex }
        ::= { raidControllerActiveTaskTable 1 }

    RaidControllerActiveTaskEntry ::=
        SEQUENCE {
            raidControllerActiveTaskRackIndex
                Integer32,
            raidControllerActiveTaskIndex
                Unsigned32,
            raidControllerActiveTaskType
                INTEGER,
            raidControllerActiveTaskLUN
                Unsigned32,
            raidControllerActiveTaskPercentageDone
                INTEGER
        }

    raidControllerActiveTaskRackIndex OBJECT-TYPE
        SYNTAX Integer32 (1..10)
        MAX-ACCESS read-only
        STATUS obsolete
        DESCRIPTION
            "The rack in which the RAID controller is located.
             The controller identified by a particular value 
             of this index is located within the rack identified by the 
             same value of rackIndex.

             This object is now obsolete."
        ::= { raidControllerActiveTaskEntry 1 }

    raidControllerActiveTaskIndex OBJECT-TYPE
        SYNTAX Unsigned32
        MAX-ACCESS read-only
        STATUS obsolete
        DESCRIPTION
            "A unique value for each task being performed on a 
             specific RAID controller.

             This object is now obsolete."
        ::= { raidControllerActiveTaskEntry 2 }

    raidControllerActiveTaskType OBJECT-TYPE
        SYNTAX INTEGER {
            initializing(1),
            checking(2),
            checkingAndRestoring(3),
            rebuilding(4),
            reconditioningBattery(5),
            chargingBattery(6),
            unknown(7),
            backgroundInitialising(8),
            migrating(9)
        }
        MAX-ACCESS read-only
        STATUS obsolete
        DESCRIPTION
            "The type of task being performed by the RAID controller.

             This object is now obsolete."
        ::= { raidControllerActiveTaskEntry 3 }

    raidControllerActiveTaskLUN OBJECT-TYPE
        SYNTAX Unsigned32
        MAX-ACCESS read-only
        STATUS obsolete
        DESCRIPTION
            "The LUN of the system drive on which the active task is
             being performed by the RAID controller.
             NOTE: the value is 0 for tasks which are not related to
                   System Drives. These are where the variable
                   raidControllerActiveTaskType is
                   reconditioningBattery(5) or chargingBattery(6)
                   (affecting the battery backup unit), or
                   unknown(7).

             This object is now obsolete."
        ::= { raidControllerActiveTaskEntry 4 }

    raidControllerActiveTaskPercentageDone OBJECT-TYPE
        SYNTAX INTEGER (0..100)
        MAX-ACCESS read-only
        STATUS obsolete
        DESCRIPTION
            "The percentage of the task which is complete.

             This object is now obsolete."
        ::= { raidControllerActiveTaskEntry 5 }

--------------------------------------------------------------------------------
--
-- System / Storage / RAID / PhysicalDrives
--
--------------------------------------------------------------------------------

    physicalDriveNumber OBJECT-TYPE
        SYNTAX Integer32
        MAX-ACCESS read-only
        STATUS obsolete
        DESCRIPTION
            "The number of physical drive bays (regardless of whether
             they contain a drive) which are present within all racks
             and enclosures within the system.

             This object is now obsolete."
        ::= { physicalDrives 1 }

    physicalDriveTable OBJECT-TYPE
        SYNTAX SEQUENCE OF PhysicalDriveEntry
        MAX-ACCESS not-accessible
        STATUS obsolete
        DESCRIPTION
            "A table containing the status of each drive bay
             present on this system.

             The number of entries in this table is given by the value of
             physicalDriveNumber.

             This object is now obsolete."
        ::= { physicalDrives 2 }

    physicalDriveEntry OBJECT-TYPE
        SYNTAX PhysicalDriveEntry
        MAX-ACCESS not-accessible
        STATUS obsolete
        DESCRIPTION
            "Status information about the drive bay.

             This object is now obsolete."
        INDEX { physicalDriveRackIndex, physicalDriveEnclosureIndex, physicalDriveColumnIndex, physicalDriveRowIndex }
        ::= { physicalDriveTable 1 }

    PhysicalDriveEntry ::=
        SEQUENCE {
            physicalDriveRackIndex
                Integer32,
            physicalDriveEnclosureIndex
                Unsigned32,
            physicalDriveColumnIndex
                Unsigned32,
            physicalDriveRowIndex
                Unsigned32,
            physicalDriveStatus
                INTEGER,
            physicalDriveVendor
                INTEGER,
            physicalDriveVersion
                DisplayString,
            physicalDriveCapacity
                Counter64
        }

    physicalDriveRackIndex OBJECT-TYPE
        SYNTAX Integer32 (1..10)
        MAX-ACCESS read-only
        STATUS obsolete
        DESCRIPTION
            "The rack in which the drive is located.
             The drive identified by a particular value
             of this index is located within the rack identified by the
             same value of rackIndex.

             This object is now obsolete."
        ::= { physicalDriveEntry 1 }

    physicalDriveEnclosureIndex OBJECT-TYPE
        SYNTAX Unsigned32
        MAX-ACCESS read-only
        STATUS obsolete
        DESCRIPTION
            "The enclosure in which the physical drive bay is located.  
             Enclosure numbers start at 1.

             This object is now obsolete."
        ::= { physicalDriveEntry 2 }

    physicalDriveColumnIndex OBJECT-TYPE
        SYNTAX Unsigned32
        MAX-ACCESS read-only
        STATUS obsolete
        DESCRIPTION
            "The column in the enclosure in which the physical
             drive bay is located.  
             Column numbers starts at 1 (column 1 is located at the
             left hand side of the enclosure).

             This object is now obsolete."
        ::= { physicalDriveEntry 3 }

    physicalDriveRowIndex OBJECT-TYPE
        SYNTAX Unsigned32
        MAX-ACCESS read-only
        STATUS obsolete
        DESCRIPTION
            "The row in the enclosure in which the physical
             drive bay is located.  
             Row numbers starts at 1 (row 1 is located at the
             top of the enclosure).

             Example: row 1, column 1 is the top left hand bay 
                      within an enclosure.

             This object is now obsolete."
        ::= { physicalDriveEntry 4 }

    physicalDriveStatus OBJECT-TYPE
        SYNTAX INTEGER {
            notPresent(1),
            online(2),
            failed(3),
            rebuilding(6),
            hotspare(7),
            notConfigured(8),
            migrating(9),
            unknown(10)
        }
        MAX-ACCESS read-only
        STATUS obsolete
        DESCRIPTION
            "The status of the physical drive bay.

             notPresent(1) - indicates that there is no drive present
                             within the drive bay.

             This object is now obsolete."
        ::= { physicalDriveEntry 5 }

    physicalDriveVendor OBJECT-TYPE
        SYNTAX INTEGER {
            seagate(1),
            unknown(2)
        }
        MAX-ACCESS read-only
        STATUS obsolete
        DESCRIPTION
            "The vendor of the drive.
             NOTE: If the drive bay is empty this value will be set to 
                   unknown(2).

             This object is now obsolete."
        ::= { physicalDriveEntry 6 }

    physicalDriveVersion OBJECT-TYPE
        SYNTAX DisplayString
        MAX-ACCESS read-only
        STATUS obsolete
        DESCRIPTION
            "The version of the firmware installed in the drive.
             NOTE: If the drive bay is empty this value will be a zero
                   length string.

             This object is now obsolete."
        ::= { physicalDriveEntry 7 }

    physicalDriveCapacity OBJECT-TYPE
        SYNTAX Counter64
        MAX-ACCESS read-only
        STATUS obsolete
        DESCRIPTION
            "The storage capacity of the drive in bytes.
             NOTE: If the drive bay is empty this value will be 0.

             This object is now obsolete."
        ::= { physicalDriveEntry 8 }

--------------------------------------------------------------------------------
--
-- System / Storage / RAID / Enclosures
--
--------------------------------------------------------------------------------

    enclosureFanNumber OBJECT-TYPE
        SYNTAX Integer32
        MAX-ACCESS read-only
        STATUS obsolete
        DESCRIPTION
            "The total number of fans which are present in all of the 
             enclosures in all racks within the system.

             This object is now obsolete."
        ::= { enclosures 1 }

    enclosureFanTable OBJECT-TYPE
        SYNTAX SEQUENCE OF EnclosureFanEntry
        MAX-ACCESS not-accessible
        STATUS obsolete
        DESCRIPTION
            "A table containing status information for each fan located
             within each enclosure (of each rack) within this system.

             The number of entries in this table is given by the value of 
             enclosureFanNumber.

             This object is now obsolete."
        ::= { enclosures 2 }

    enclosureFanEntry OBJECT-TYPE
        SYNTAX EnclosureFanEntry
        MAX-ACCESS not-accessible
        STATUS obsolete
        DESCRIPTION
            "Fan status information.

             This object is now obsolete."
        INDEX { enclosureFanRackIndex, enclosureFanEnclosureIndex, enclosureFanFanIndex }
        ::= { enclosureFanTable 1 }

    EnclosureFanEntry ::=
        SEQUENCE {
            enclosureFanRackIndex
                Integer32,
            enclosureFanEnclosureIndex
                Unsigned32,
            enclosureFanFanIndex
                Unsigned32,
            enclosureFanStatus
                INTEGER,
            enclosureFanSpeed
                INTEGER
        }

    enclosureFanRackIndex OBJECT-TYPE
        SYNTAX Integer32 (1..10)
        MAX-ACCESS read-only
        STATUS obsolete
        DESCRIPTION
            "The rack in which the fan is located.
             The fan identified by a particular value of this index is
             located within the rack identified by the same value of 
             rackIndex.

             This object is now obsolete."
        ::= { enclosureFanEntry 1 }

    enclosureFanEnclosureIndex OBJECT-TYPE
        SYNTAX Unsigned32
        MAX-ACCESS read-only
        STATUS obsolete
        DESCRIPTION
            "The enclosure in which the fan is located.
             Enclosure numbers start at 1.

             This object is now obsolete."
        ::= { enclosureFanEntry 2 }

    enclosureFanFanIndex OBJECT-TYPE
        SYNTAX Unsigned32
        MAX-ACCESS read-only
        STATUS obsolete
        DESCRIPTION
            "An identifier for the fan within the enclosure.
             Fan numbers start at 1.

             This object is now obsolete."
        ::= { enclosureFanEntry 3 }

    enclosureFanStatus OBJECT-TYPE
        SYNTAX INTEGER {
            ok(1),
            failed(2),
            unknown(3)
        }
        MAX-ACCESS read-only
        STATUS obsolete
        DESCRIPTION
            "The status of the fan sensor.

             This object is now obsolete."
        ::= { enclosureFanEntry 4 }

    enclosureFanSpeed OBJECT-TYPE
        SYNTAX INTEGER {
            fast(1),
            slow(2),
            stoppedOrUnknown(3)
        }
        MAX-ACCESS read-only
        STATUS obsolete
        DESCRIPTION
            "An indication of the speed at which the fan is 
             running.

             This object is now obsolete."
        ::= { enclosureFanEntry 5 }

    enclosureTemperatureNumber OBJECT-TYPE
        SYNTAX Integer32
        MAX-ACCESS read-only
        STATUS obsolete
        DESCRIPTION
            "The total number of temperature sensors which are 
             present in all of the enclosures in all racks within 
             the system.

             This object is now obsolete."
        ::= { enclosures 3 }

    enclosureTemperatureTable OBJECT-TYPE
        SYNTAX SEQUENCE OF EnclosureTemperatureEntry
        MAX-ACCESS not-accessible
        STATUS obsolete
        DESCRIPTION
            "A table containing temperature readings for each 
             sensor located within each enclosure (of each rack)
             within this system.

             The number of entries in this table is given by the value of 
             enclosureTemperatureNumber.

             This object is now obsolete."
        ::= { enclosures 4 }

    enclosureTemperatureEntry OBJECT-TYPE
        SYNTAX EnclosureTemperatureEntry
        MAX-ACCESS not-accessible
        STATUS obsolete
        DESCRIPTION
            "Information obtained from a temperature sensor located
             within an enclosure.

             This object is now obsolete."
        INDEX { enclosureTemperatureRackIndex, enclosureTemperatureEnclosureIndex, enclosureTemperatureTempIndex }
        ::= { enclosureTemperatureTable 1 }

    EnclosureTemperatureEntry ::=
        SEQUENCE {
            enclosureTemperatureRackIndex
                Integer32,
            enclosureTemperatureEnclosureIndex
                Integer32,
            enclosureTemperatureTempIndex
                Integer32,
            enclosureTemperatureStatus
                INTEGER,
            enclosureTemperatureOverTemp
                INTEGER,
            enclosureTemperatureTempC
                Integer32,
            enclosureTemperatureTempF
                Integer32,
            enclosureTemperatureRange
                INTEGER
        }

    enclosureTemperatureRackIndex OBJECT-TYPE
        SYNTAX Integer32 (1..10)
        MAX-ACCESS read-only
        STATUS obsolete
        DESCRIPTION
            "The rack in which the temperature sensor is located.
             The sensor identified by a particular value of this index is
             located within the rack identified by the same value of
             rackIndex.

             This object is now obsolete."
        ::= { enclosureTemperatureEntry 1 }

    enclosureTemperatureEnclosureIndex OBJECT-TYPE
        SYNTAX Integer32 (1..8)
        MAX-ACCESS read-only
        STATUS obsolete
        DESCRIPTION
            "The enclosure in which the temperature sensor is located.
             Enclosure numbers start at 1.

             This object is now obsolete."
        ::= { enclosureTemperatureEntry 2 }

    enclosureTemperatureTempIndex OBJECT-TYPE
        SYNTAX Integer32 (1..4)
        MAX-ACCESS read-only
        STATUS obsolete
        DESCRIPTION
            "An identifier for the temperature sensor within
             the enclosure.
             Temperature sensor numbers start at 1.

             This object is now obsolete."
        ::= { enclosureTemperatureEntry 3 }

    enclosureTemperatureStatus OBJECT-TYPE
        SYNTAX INTEGER {
            ok(1),
            failed(2),
            unknown(3)
        }
        MAX-ACCESS read-only
        STATUS obsolete
        DESCRIPTION
            "The status of the temperature sensor.

             This object is now obsolete."
        ::= { enclosureTemperatureEntry 4 }

    enclosureTemperatureOverTemp OBJECT-TYPE
        SYNTAX INTEGER {
            overTemp(1),
            noOverTemp(2),
            unknown(3)
        }
        MAX-ACCESS read-only
        STATUS obsolete
        DESCRIPTION
            "A flag indicating whether an over temperature has
             been detected by the sensor.
             
             overTemp(1)   - an over temperature has been detected.
             noOverTemp(2) - an over temperature has NOT been detected.

             This object is now obsolete."
        ::= { enclosureTemperatureEntry 5 }

    enclosureTemperatureTempC OBJECT-TYPE
        SYNTAX Integer32
        MAX-ACCESS read-only
        STATUS obsolete
        DESCRIPTION
            "The temperature measured by the sensor in degrees Celsius.

            A value of -1 indicates the temperature could not be
            determined.

             This object is now obsolete."
        ::= { enclosureTemperatureEntry 6 }

    enclosureTemperatureTempF OBJECT-TYPE
        SYNTAX Integer32
        MAX-ACCESS read-only
        STATUS obsolete
        DESCRIPTION
            "The temperature measured by the sensor in degrees Fahrenheit.

            A value of -1 indicates the temperature could not be
            determined.

             This object is now obsolete."
        ::= { enclosureTemperatureEntry 7 }

    enclosureTemperatureRange OBJECT-TYPE
        SYNTAX INTEGER {
            normal(1),
            warm(2),
            hot(3),
            unknown(4)
        }
        MAX-ACCESS read-only
        STATUS obsolete
        DESCRIPTION
            "Status indicator of the temperature with regard to the
             operating temperatures expected within the enclosure.

             This object is now obsolete."
        ::= { enclosureTemperatureEntry 8 }

    enclosurePSUNumber OBJECT-TYPE
        SYNTAX Integer32
        MAX-ACCESS read-only
        STATUS obsolete
        DESCRIPTION
            "The total number of power supplies which are present in 
             all of the enclosures in all racks within the system.

             This object is now obsolete."
        ::= { enclosures 5 }

    enclosurePSUTable OBJECT-TYPE
        SYNTAX SEQUENCE OF EnclosurePSUEntry
        MAX-ACCESS not-accessible
        STATUS obsolete
        DESCRIPTION
            "A table containing status information on each 
             power supply located within each enclosure (of each rack)
             within this system.

             The number of entries in this table is given by the value of
             enclosurePSUNumber.

             This object is now obsolete."
        ::= { enclosures 6 }

    enclosurePSUEntry OBJECT-TYPE
        SYNTAX EnclosurePSUEntry
        MAX-ACCESS not-accessible
        STATUS obsolete
        DESCRIPTION
            "Information about a power supply within an enclosure.

             This object is now obsolete."
        INDEX { enclosurePSURackIndex, enclosurePSUEnclosureIndex, enclosurePSUPSUIndex }
        ::= { enclosurePSUTable 1 }

    EnclosurePSUEntry ::=
        SEQUENCE {
            enclosurePSURackIndex
                Integer32,
            enclosurePSUEnclosureIndex
                Integer32,
            enclosurePSUPSUIndex
                Integer32,
            enclosurePSUStatus
                INTEGER
        }

    enclosurePSURackIndex OBJECT-TYPE
        SYNTAX Integer32 (1..10)
        MAX-ACCESS read-only
        STATUS obsolete
        DESCRIPTION
            "The rack in which the power supply is located.
             The power supply identified by a particular value of this index is
             located within the rack identified by the same value of 
             rackIndex.

             This object is now obsolete."
        ::= { enclosurePSUEntry 1 }

    enclosurePSUEnclosureIndex OBJECT-TYPE
        SYNTAX Integer32 (1..8)
        MAX-ACCESS read-only
        STATUS obsolete
        DESCRIPTION
            "The enclosure in which the power supply is located.
             Enclosure numbers start at 1.

             This object is now obsolete."
        ::= { enclosurePSUEntry 2 }

    enclosurePSUPSUIndex OBJECT-TYPE
        SYNTAX Integer32 (1..4)
        MAX-ACCESS read-only
        STATUS obsolete
        DESCRIPTION
            "An identifier for the power supply within the
             enclosure.
             Power supply numbers start at 1.

             This object is now obsolete."
        ::= { enclosurePSUEntry 3 }

    enclosurePSUStatus OBJECT-TYPE
        SYNTAX INTEGER {
            ok(1),
            failed(2),
            unknown(3)
        }
        MAX-ACCESS read-only
        STATUS obsolete
        DESCRIPTION
            "The operational status of the power supply.

             This object is now obsolete."
        ::= { enclosurePSUEntry 4 }

    enclosureAlarmNumber OBJECT-TYPE
        SYNTAX Integer32
        MAX-ACCESS read-only
        STATUS obsolete
        DESCRIPTION
            "The total number of alarm modules which are present
             in all of the enclosures in all racks within the system.

             This object is now obsolete."
        ::= { enclosures 7 }

    enclosureAlarmTable OBJECT-TYPE
        SYNTAX SEQUENCE OF EnclosureAlarmEntry
        MAX-ACCESS not-accessible
        STATUS obsolete
        DESCRIPTION
            "A table containing status information on each 
             alarm module located within each enclosure (of each rack)
             within this system.

             The number of entries in this table is given by the value of
             enclosureAlarmNumber.

             This object is now obsolete."
        ::= { enclosures 8 }

    enclosureAlarmEntry OBJECT-TYPE
        SYNTAX EnclosureAlarmEntry
        MAX-ACCESS not-accessible
        STATUS obsolete
        DESCRIPTION
            "Information about a alarm module within an enclosure.

             This object is now obsolete."
        INDEX { enclosureAlarmRackIndex, enclosureAlarmEnclosureIndex, enclosureAlarmAlarmIndex }
        ::= { enclosureAlarmTable 1 }

    EnclosureAlarmEntry ::=
        SEQUENCE {
            enclosureAlarmRackIndex
                Integer32,
            enclosureAlarmEnclosureIndex
                Integer32,
            enclosureAlarmAlarmIndex
                Integer32,
            enclosureAlarmStatus
                INTEGER,
            enclosureAlarmBeeping
                INTEGER
        }

    enclosureAlarmRackIndex OBJECT-TYPE
        SYNTAX Integer32 (1..10)
        MAX-ACCESS read-only
        STATUS obsolete
        DESCRIPTION
            "The rack in which the alarm module is located.
             The alarm module identified by a particular value of this index is
             located within the rack identified by the same value of 
             rackIndex.

             This object is now obsolete."
        ::= { enclosureAlarmEntry 1 }

    enclosureAlarmEnclosureIndex OBJECT-TYPE
        SYNTAX Integer32 (1..4)
        MAX-ACCESS read-only
        STATUS obsolete
        DESCRIPTION
            "The enclosure in which the alarm module is located.
             Enclosure numbers start at 1.

             This object is now obsolete."
        ::= { enclosureAlarmEntry 2 }

    enclosureAlarmAlarmIndex OBJECT-TYPE
        SYNTAX Integer32 (1..4)
        MAX-ACCESS read-only
        STATUS obsolete
        DESCRIPTION
            "An identifier for the alarm module within the
             enclosure.
             Alarm module numbers start at 1.

             This object is now obsolete."
        ::= { enclosureAlarmEntry 3 }

    enclosureAlarmStatus OBJECT-TYPE
        SYNTAX INTEGER {
            ok(1),
            failed(2),
            unknown(3)
        }
        MAX-ACCESS read-only
        STATUS obsolete
        DESCRIPTION
            "The operational status of alarm module.

             This object is now obsolete."
        ::= { enclosureAlarmEntry 4 }

    enclosureAlarmBeeping OBJECT-TYPE
        SYNTAX INTEGER {
            beeping(1),
            notBeeping(2),
            unknown(3)
        }
        MAX-ACCESS read-only
        STATUS obsolete
        DESCRIPTION
            "Indicates whether the alarm module is beeping or not.

             This object is now obsolete."
        ::= { enclosureAlarmEntry 5 }

--------------------------------------------------------------------------------
--
-- System / Storage / Automount
--
--------------------------------------------------------------------------------

    automountNumber OBJECT-TYPE
        SYNTAX Integer32
        MAX-ACCESS read-only
        STATUS obsolete
        DESCRIPTION
            "The number of automounts configured.

            This object is obsolete.
            Volumes are no longer automounted."
        ::= { automount 1 }

    automountTable OBJECT-TYPE
        SYNTAX SEQUENCE OF AutomountEntry
        MAX-ACCESS not-accessible
        STATUS obsolete
        DESCRIPTION
            "A table containing the automount configuration.

             The number of entries in this table is given by the value of 
             automountNumber.

            This object is obsolete.
            Volumes are no longer automounted."
        ::= { automount 2 }

    automountEntry OBJECT-TYPE
        SYNTAX AutomountEntry
        MAX-ACCESS not-accessible
        STATUS obsolete
        DESCRIPTION
            "An automount configuration entry.

            This object is obsolete.
            Volumes are no longer automounted."
        INDEX { automountIndex, automountPartitionIndex }
        ::= { automountTable 1 }

    AutomountEntry ::=
        SEQUENCE {
            automountIndex
                Integer32,
            automountPartitionIndex
                Unsigned32,
            automountWWN
                DisplayString,
            automountLUN
                Unsigned32
        }

    automountIndex OBJECT-TYPE
        SYNTAX Integer32 (1..100)
        MAX-ACCESS read-only
        STATUS obsolete
        DESCRIPTION
            "An identifier for the automount.

             Its value ranges between 1 and the value of automountNumber.

            This object is obsolete.
            Volumes are no longer automounted."
        ::= { automountEntry 1 }

    automountPartitionIndex OBJECT-TYPE
        SYNTAX Unsigned32
        MAX-ACCESS read-only
        STATUS obsolete
        DESCRIPTION
            "The partition number of the disk to automount.

            This object is obsolete.
            Volumes are no longer automounted."
        ::= { automountEntry 2 }

    automountWWN OBJECT-TYPE
        SYNTAX DisplayString
        MAX-ACCESS read-only
        STATUS obsolete
        DESCRIPTION
            "The world wide name (WWN) of the disk to automount.

            This object is obsolete.
            Volumes are no longer automounted."
        ::= { automountEntry 3 }

    automountLUN OBJECT-TYPE
        SYNTAX Unsigned32
        MAX-ACCESS read-only
        STATUS obsolete
        DESCRIPTION
            "The logical unit number (LUN) of the disk to automount.

            This object is obsolete.
            Volumes are no longer automounted."
        ::= { automountEntry 4 }

--------------------------------------------------------------------------------
--
-- System / Storage / System Drives
--
--------------------------------------------------------------------------------

    sysDriveNumber OBJECT-TYPE
        SYNTAX Integer32
        MAX-ACCESS read-only
        STATUS current
        DESCRIPTION
            "The number of accessible system drives.
             NOTE: A system drive is a single logical drive which is
                   created and managed by a RAID controller.  It comprises of
                   a number of physical drives, each of which contribute to
                   the total storage capability of the system drive."
        ::= { systemDrives 1 }

    sysDriveTable OBJECT-TYPE
        SYNTAX SEQUENCE OF SysDriveEntry
        MAX-ACCESS not-accessible
        STATUS current
        DESCRIPTION
            "A table containing information about each accessible
             system drive.

             The number of entries in this table is given by the value of
             sysDriveNumber."
        ::= { systemDrives 2 }

    sysDriveEntry OBJECT-TYPE
        SYNTAX SysDriveEntry
        MAX-ACCESS not-accessible
        STATUS current
        DESCRIPTION
            "Information about a system drive."
        INDEX { sysDriveIndex }
        ::= { sysDriveTable 1 }

    SysDriveEntry ::=
        SEQUENCE {
            sysDriveIndex
                Integer32,
            sysDriveWWN
                DisplayString,
            sysDriveLUN
                Unsigned32,
            sysDriveStatus
                INTEGER,
            sysDriveCapacity
                Counter64,
            sysDriveRaidLevel
                INTEGER,
            sysDriveCacheMode
                INTEGER
        }

    sysDriveIndex OBJECT-TYPE
        SYNTAX Integer32 (1..25)
        MAX-ACCESS read-only
        STATUS current
        DESCRIPTION
            "An identifier for the system drive (system drive id).

             Its value ranges between 1 and the value of sysDriveNumber."
        ::= { sysDriveEntry 1 }

    sysDriveWWN OBJECT-TYPE
        SYNTAX DisplayString
        MAX-ACCESS read-only
        STATUS current
        DESCRIPTION
            "The world wide name (WWN) of the system drive."
        ::= { sysDriveEntry 2 }

    sysDriveLUN OBJECT-TYPE
        SYNTAX Unsigned32
        MAX-ACCESS read-only
        STATUS current
        DESCRIPTION
            "The logical unit number (LUN) of the system drive.
             NOTE: upto 8 system drives can exist under a single
                   RAID controller.

             LUNs range from 0 to 7."
        ::= { sysDriveEntry 3 }

    sysDriveStatus OBJECT-TYPE
        SYNTAX INTEGER {
            online(1),
            corrupt(2),
            failed(3),
            notPresent(4),
            disconnected(5),
            offline(6),
            initializing(7),
            formatting(8),
            unknown(9)
        }
        MAX-ACCESS read-only
        STATUS current
        DESCRIPTION
            "The status of the system drive.

             online(1)          - the system drive is accessible through
                                  the fibre channel interface.
             corrupt(2)         - the system drives master boot record
                                  is corrupt.
             failed(3)          - the system drive has failed and is no
                                  longer accessible through the fibre
                                  channel interface.
             notPresent(4)      - device no longer present.
             disconnected(5)    - device is present but not accessible
                                  by the controller
             offline(6)         - all ports are offline  
             initializing(7)    - not accessible until initialization phase has 
                                  completed
             formatting(8)      - device is formatting
             unknown(9)         - unknown device status

             This object will only have the value unknown(9)."

        ::= { sysDriveEntry 4 }

    sysDriveCapacity OBJECT-TYPE
        SYNTAX Counter64
        MAX-ACCESS read-only
        STATUS current
        DESCRIPTION
            "The capacity of the system drive in bytes."
        ::= { sysDriveEntry 5 }

    sysDriveRaidLevel OBJECT-TYPE
        SYNTAX INTEGER {
            raid0(1),
            raid1(2),
            raid3(3),
            raid5(4),
            raid10(5),
            jBOD(6),
            raid30(7),
            raid50(8),
            unknown(9)
        }
        MAX-ACCESS read-only
        STATUS current
        DESCRIPTION
            "The configured RAID level of the system drive.
             NOTE : jBOD(6) - means just a bunch of disks."
        ::= { sysDriveEntry 6 }

    sysDriveCacheMode OBJECT-TYPE
        SYNTAX INTEGER {
            writeThrough(1),
            writeBack(2),
            unknown(3)
        }
        MAX-ACCESS read-only
        STATUS current
        DESCRIPTION
            "The caching mode employed by the RAID controller for
             this system drive.

             This object will only have the value unknown(3)."
        ::= { sysDriveEntry 7 }

--------------------------------------------------------------------------------
--
-- System / Storage / Volumes
--
--------------------------------------------------------------------------------

    volumeNumber OBJECT-TYPE
        SYNTAX Integer32
        MAX-ACCESS read-only
        STATUS current
        DESCRIPTION
            "The number of volumes which are known to the system."
        ::= { volumes 1 }

    volumeTable OBJECT-TYPE
        SYNTAX SEQUENCE OF VolumeEntry
        MAX-ACCESS not-accessible
        STATUS current
        DESCRIPTION
            "A table containing information about each volume
             known to the system.

             The number of entries in this table is given by the value of
             volumeNumber."
        ::= { volumes 2 }

    volumeEntry OBJECT-TYPE
        SYNTAX VolumeEntry
        MAX-ACCESS not-accessible
        STATUS current
        DESCRIPTION
            "Information about a volume."
        INDEX { volumeSysDriveIndex, volumePartitionID }
        ::= { volumeTable 1 }

    VolumeEntry ::=
        SEQUENCE {
            volumeSysDriveIndex
                Integer32,
            volumePartitionID
                Unsigned32,
            volumeLabel
                DisplayString,
            volumeStatus
                INTEGER,
            volumeCapacity
                Counter64,
            volumeFreeCapacity
                Counter64,
            volumeEnterpriseVirtualServer
                DisplayString
        }

    volumeSysDriveIndex OBJECT-TYPE
        SYNTAX Integer32 (1..2147483647)
        MAX-ACCESS read-only
        STATUS current
        DESCRIPTION
            "The system drive on which the volume is stored.
             The system drive identified by a particular value of this index is
             located on the system drive identified by the same value of
             sysDriveIndex."
        ::= { volumeEntry 1 }

    volumePartitionID OBJECT-TYPE
        SYNTAX Unsigned32
        MAX-ACCESS read-only
        STATUS current
        DESCRIPTION
            "The partition ID of the volume.
             NOTE: this is the offset from the start of the system drive
                   at which the volume starts."
        ::= { volumeEntry 2 }

    volumeLabel OBJECT-TYPE
        SYNTAX DisplayString
        MAX-ACCESS read-only
        STATUS current
        DESCRIPTION
            "The label assigned to the volume by a user for
             identification purposes.
             NOTE: If a label has not been assigned to the volume, this
                   value will be a zero length string."
        ::= { volumeEntry 3 }

    volumeStatus OBJECT-TYPE
        SYNTAX INTEGER {
            unformatted(1),
            mounted(2),
            formatted(3),
            needsChecking(4)
        }
        MAX-ACCESS read-only
        STATUS current
        DESCRIPTION
            "The status of the volume.

             unformatted(1)   - the volume does NOT contain a filesystem.
             mounted(2)       - the volume contains a file system and may
                                be being accessed by users.
             formatted(3)     - the volume contains a filesystem, but is
                                not accessible by users as it is not
                                mounted.
             needsChecking(4) - the filesystem has some errors and cannot
                                be mounted.  Its must be checked and fixed
                                before it can be accessed by users."
        ::= { volumeEntry 4 }

    volumeCapacity OBJECT-TYPE
        SYNTAX Counter64
        MAX-ACCESS read-only
        STATUS current
        DESCRIPTION
            "The volumes capacity in bytes."
        ::= { volumeEntry 5 }

    volumeFreeCapacity OBJECT-TYPE
        SYNTAX Counter64
        MAX-ACCESS read-only
        STATUS current
        DESCRIPTION
            "The remaining free volume capacity in bytes.
             NOTE: This value is 0 if the volume is not mounted."
        ::= { volumeEntry 6 }

    volumeEnterpriseVirtualServer OBJECT-TYPE
        SYNTAX DisplayString
        MAX-ACCESS read-only
        STATUS current
        DESCRIPTION
            "The name of the Enterprise Virtual Server to which this
            volume is assigned."
        ::= { volumeEntry 7 }

    fsStatsTable OBJECT-TYPE
        SYNTAX SEQUENCE OF FsStatsEntry
        MAX-ACCESS not-accessible
        STATUS current
        DESCRIPTION
            "A table containing statistics about each FileSystem
             known to the system.

             The number of entries in this table is given by the value of
             volumeNumber."
        ::= { volumes 3 }

    fsStatsEntry OBJECT-TYPE
        SYNTAX FsStatsEntry
        MAX-ACCESS not-accessible
        STATUS current
        DESCRIPTION
            "Statistics on a FileSystem."
        INDEX { fsPermId }
        ::= { fsStatsTable 1 }

    FsStatsEntry ::=
        SEQUENCE {
            fsPermId
                Counter64,
            fsLabel
                DisplayString,
            opsPerSecAverage
                Unsigned32
        }

    fsPermId OBJECT-TYPE
        SYNTAX Counter64
        MAX-ACCESS read-only
        STATUS current
        DESCRIPTION
            "The permanent ID of the FileSystem for which these statistics
             are reported."
        ::= { fsStatsEntry 1 }

    fsLabel OBJECT-TYPE
        SYNTAX DisplayString
        MAX-ACCESS read-only
        STATUS current
        DESCRIPTION
            "The label of the FileSystem for which these statistics
             are reported."
        ::= { fsStatsEntry 2 }

    opsPerSecAverage OBJECT-TYPE
        SYNTAX Unsigned32
        MAX-ACCESS read-only
        STATUS current
        DESCRIPTION
            "The average ops per second for the FileSystem.

             If the FileSystem is not mounted, or is unavailable for some other
             reason, this value is zero."
        ::= { fsStatsEntry 3 }


--------------------------------------------------------------------------------
--
-- System / Storage / Fibre Channel Statistics
--
--------------------------------------------------------------------------------

    fcRequests OBJECT-TYPE
        SYNTAX Counter64
        MAX-ACCESS read-only
        STATUS current
        DESCRIPTION
            "The total number of requests issued through the fibre channel
             interface."
        ::= { fcStats 1 }

    fcResponses OBJECT-TYPE
        SYNTAX Counter64
        MAX-ACCESS read-only
        STATUS current
        DESCRIPTION
            "The total number of responses received through the fibre channel
             interface."
        ::= { fcStats 2 }

    fcReadReqs OBJECT-TYPE
        SYNTAX Counter64
        MAX-ACCESS read-only
        STATUS current
        DESCRIPTION
            "The total number of disk read requests issued through the fibre
             channel interface."
        ::= { fcStats 3 }

    fcWriteReqs OBJECT-TYPE
        SYNTAX Counter64
        MAX-ACCESS read-only
        STATUS current
        DESCRIPTION
            "The total number of disk write requests issued through the
             fibre channel interface."
        ::= { fcStats 4 }

    fcReadResps OBJECT-TYPE
        SYNTAX Counter64
        MAX-ACCESS read-only
        STATUS current
        DESCRIPTION
            "The total number of disk read responses received through the
             fibre channel interface."
        ::= { fcStats 5 }

    fcWriteResps OBJECT-TYPE
        SYNTAX Counter64
        MAX-ACCESS read-only
        STATUS current
        DESCRIPTION
            "The total number of disk write responses received through the
             fibre channel interface."
        ::= { fcStats 6 }

    fcInstInRate OBJECT-TYPE
        SYNTAX Counter32
        MAX-ACCESS read-only
        STATUS obsolete
        DESCRIPTION
            "The instantaneous receive rate in bytes per second for data
             received through the fibre channel interface.

             This object is obsolete. It forms a column in fcStatsTable."
        ::= { fcStats 7 }

    fcInstOutRate OBJECT-TYPE
        SYNTAX Counter32
        MAX-ACCESS read-only
        STATUS obsolete
        DESCRIPTION
            "The instantaneous transmission rate in bytes per second for
             data transmitted through the fibre channel interface.

             This object is obsolete. It forms a column in fcStatsTable."
        ::= { fcStats 8 }

    fcPkInRate OBJECT-TYPE
        SYNTAX Counter32
        MAX-ACCESS read-only
        STATUS obsolete
        DESCRIPTION
            "The peak receive rate in bytes per second for data received
             through the fibre channel interface.

             This object is obsolete. It forms a column in fcStatsTable."
        ::= { fcStats 9 }

    fcPkOutRate OBJECT-TYPE
        SYNTAX Counter32
        MAX-ACCESS read-only
        STATUS obsolete
        DESCRIPTION
            "The peak transmission rate in bytes per second for
             data transmitted through the fibre channel interface.

             This object is obsolete. It forms a column in fcStatsTable."
        ::= { fcStats 10 }

    fcCacheHits OBJECT-TYPE
        SYNTAX Counter64
        MAX-ACCESS read-only
        STATUS current
        DESCRIPTION
            "The total number of disk read requests which were fulfilled
             through reading the sector cache (ie the requests did NOT
             require access to the disk)."
        ::= { fcStats 11 }

    fcCacheMisses OBJECT-TYPE
        SYNTAX Counter64
        MAX-ACCESS read-only
        STATUS current
        DESCRIPTION
            "The total number disk read requests which required access
             to the disk (ie the requests could NOT be fulfilled
             through reading the sector cache)."
        ::= { fcStats 12 }

    fcLossSignalErrs OBJECT-TYPE
        SYNTAX Counter32
        MAX-ACCESS read-only
        STATUS obsolete
        DESCRIPTION
            "The total number of loss of signal errors.

             This object is obsolete. It forms a column in fcStatsTable."
        ::= { fcStats 13 }

    fcBadRXCharErrs OBJECT-TYPE
        SYNTAX Counter32
        MAX-ACCESS read-only
        STATUS obsolete
        DESCRIPTION
            "The total number of bad receive character errors.

             This object is obsolete. It forms a column in fcStatsTable."
        ::= { fcStats 14 }

    fcLossSyncErrs OBJECT-TYPE
        SYNTAX Counter32
        MAX-ACCESS read-only
        STATUS obsolete
        DESCRIPTION
            "The total number of loss of synchronisation errors.

             This object is obsolete. It forms a column in fcStatsTable."
        ::= { fcStats 15 }

    fcLinkFailErrs OBJECT-TYPE
        SYNTAX Counter32
        MAX-ACCESS read-only
        STATUS obsolete
        DESCRIPTION
            "The total number of link fail errors.

             This object is obsolete. It forms a column in fcStatsTable."
        ::= { fcStats 16 }

    fcRXEOFErrs OBJECT-TYPE
        SYNTAX Counter32
        MAX-ACCESS read-only
        STATUS obsolete
        DESCRIPTION
            "The total number of messages received from the frame sender
             indicating that the frame should be aborted because a problem
             occurred during transmission.

             This object is obsolete. It forms a column in fcStatsTable."
        ::= { fcStats 17 }

    fcDiscardedFrameErrs OBJECT-TYPE
        SYNTAX Counter32
        MAX-ACCESS read-only
        STATUS obsolete
        DESCRIPTION
            "The total number of discarded frame errors.

             This object is obsolete. It forms a column in fcStatsTable."
        ::= { fcStats 18 }

    fcBadCRCErrs OBJECT-TYPE
        SYNTAX Counter32
        MAX-ACCESS read-only
        STATUS obsolete
        DESCRIPTION
            "The total number of framing errors due to bad cyclic redundancy
             codes.

             This object is obsolete. It forms a column in fcStatsTable."
        ::= { fcStats 19 }

    fcProtErrs OBJECT-TYPE
        SYNTAX Counter32
        MAX-ACCESS read-only
        STATUS obsolete
        DESCRIPTION
            "The total number of fibre channel protocol errors.

             This object is obsolete. It forms a column in fcStatsTable."
        ::= { fcStats 20 }

    fcIOStatusResubs OBJECT-TYPE
        SYNTAX Counter64
        MAX-ACCESS read-only
        STATUS current
        DESCRIPTION
            "The number of I/O requests that were resubmitted because they
             failed the first time."
        ::= { fcStats 21 }

    fcIOStatusFails OBJECT-TYPE
        SYNTAX Counter64
        MAX-ACCESS read-only
        STATUS current
        DESCRIPTION
            "The number of I/O requests that failed after resubmission.
             NOTE: This indicates a fatal error condition with the fibre
                   channel interface hardware."
        ::= { fcStats 22 }

    fibreChannelInterfaceNumber OBJECT-TYPE
        SYNTAX Unsigned32 (1 .. 32)              --32 interfaces?
        MAX-ACCESS read-only
        STATUS current
        DESCRIPTION
            "The number of fibre channel interfaces."
        ::= { fcStats 23 }

    fcStatsTable OBJECT-TYPE
        SYNTAX SEQUENCE OF FcStatsEntry
        MAX-ACCESS not-accessible
        STATUS obsolete
        DESCRIPTION
            "A table of statistics for the fibre channel interfaces.

            This object is now obsolete."
        ::= { fcStats 24 }

    fcStatsEntry OBJECT-TYPE
        SYNTAX FcStatsEntry
        MAX-ACCESS not-accessible
        STATUS obsolete
        DESCRIPTION
            "A set of statistics for a fibre channel interface. The
            interface is indexed by fcInterfaceIndex.

            This object is now obsolete."
        INDEX { fcInterfaceIndex }
        ::= { fcStatsTable 1 }

    FcStatsEntry ::=
        SEQUENCE {
            fcInterfaceIndex
                Integer32,
            fcInstantaneousInRate
                Counter32,
            fcInstantaneousOutRate
                Counter32,
            fcPeakInRate
                Counter32,
            fcPeakOutRate
                Counter32,
            fcSignalLossErrors
                Counter32,
            fcBadRXCharErrors
                Counter32,
            fcLossSyncErrors
                Counter32,
            fcLinkFailErrors
                Counter32,
            fcRXEOFErrors
                Counter32,
            fcDiscardedFrameErrors
                Counter32,
            fcBadCRCErrors
                Counter32,
            fcProtocolErrors
                Counter32
        }

    fcInterfaceIndex OBJECT-TYPE
        SYNTAX Integer32 (0..128)
        MAX-ACCESS read-only
        STATUS obsolete
        DESCRIPTION
            "The index of the fibre channel interface to which
            the statistics in this row apply.

            This object is now obsolete."
        ::= { fcStatsEntry 1 }

    fcInstantaneousInRate OBJECT-TYPE
        SYNTAX Counter32
        MAX-ACCESS read-only
        STATUS obsolete
        DESCRIPTION
            "The number of bytes received by a fibre channel
             interface in the last second.

            This object is now obsolete."
        ::= { fcStatsEntry 2 }

    fcInstantaneousOutRate OBJECT-TYPE
        SYNTAX Counter32
        MAX-ACCESS read-only
        STATUS obsolete
        DESCRIPTION
            "The number of bytes transmitted by a fibre channel
             interface in the last second.

            This object is now obsolete."
        ::= { fcStatsEntry 3 }

    fcPeakInRate OBJECT-TYPE
        SYNTAX Counter32
        MAX-ACCESS read-only
        STATUS obsolete
        DESCRIPTION
            "The peak receive rate in bytes per second for data received
             through a fibre channel interface.

            This object is now obsolete."
        ::= { fcStatsEntry 4 }

    fcPeakOutRate OBJECT-TYPE
        SYNTAX Counter32
        MAX-ACCESS read-only
        STATUS obsolete
        DESCRIPTION
            "The peak transmission rate in bytes per second for data
            transmitted through a fibre channel interface."
        ::= { fcStatsEntry 5 }

    fcSignalLossErrors OBJECT-TYPE
        SYNTAX Counter32
        MAX-ACCESS read-only
        STATUS obsolete
        DESCRIPTION
            "The total number of loss of signal errors by a fibre channel
             interface.

            This object is now obsolete."
        ::= { fcStatsEntry 6 }

    fcBadRXCharErrors OBJECT-TYPE
        SYNTAX Counter32
        MAX-ACCESS read-only
        STATUS obsolete
        DESCRIPTION
            "The number of bad receive character errors at a fibre
            channel interface.

            This object is now obsolete."
        ::= { fcStatsEntry 7 }

    fcLossSyncErrors OBJECT-TYPE
        SYNTAX Counter32
        MAX-ACCESS read-only
        STATUS obsolete
        DESCRIPTION
            "The number of loss of synchronisation errors at a fibre
            channel interface.

            This object is now obsolete."
        ::= { fcStatsEntry 8 }

    fcLinkFailErrors OBJECT-TYPE
        SYNTAX Counter32
        MAX-ACCESS read-only
        STATUS obsolete
        DESCRIPTION
            "The number of link fail errors at a fibre channel interface.

            This object is now obsolete."
        ::= { fcStatsEntry 9 }

    fcRXEOFErrors OBJECT-TYPE
        SYNTAX Counter32
        MAX-ACCESS read-only
        STATUS obsolete
        DESCRIPTION
            "The number of messages received at a fibre channel interface
            from the frame sender indicating that the frame should be
            aborted because a problem occurred during transmission.

            This object is now obsolete."
        ::= { fcStatsEntry 10 }

     fcDiscardedFrameErrors OBJECT-TYPE
        SYNTAX Counter32
        MAX-ACCESS read-only
        STATUS obsolete
        DESCRIPTION
            "The number of discarded frame errors at a fibre channel
            interface.

            This object is now obsolete."
        ::= { fcStatsEntry 11 }

     fcBadCRCErrors OBJECT-TYPE
        SYNTAX Counter32
        MAX-ACCESS read-only
        STATUS obsolete
        DESCRIPTION
            "The number of framing errors due to bad cyclic redundancy
             codes, at a fibre channel interface.

            This object is now obsolete."
        ::= { fcStatsEntry 12 }

    fcProtocolErrors OBJECT-TYPE
        SYNTAX Counter32
        MAX-ACCESS read-only
        STATUS obsolete
        DESCRIPTION
            "The number of fibre channel protocol errors at a fibre
            channel interface.

            This object is now obsolete."
        ::= { fcStatsEntry 13 }

    fcStatisticsTable OBJECT-TYPE
        SYNTAX SEQUENCE OF FcStatisticsEntry
        MAX-ACCESS not-accessible
        STATUS current
        DESCRIPTION
            "A table of statistics for the fibre channel interfaces."
        ::= { fcStats 25 }

    fcStatisticsEntry OBJECT-TYPE
        SYNTAX FcStatisticsEntry
        MAX-ACCESS not-accessible
        STATUS current
        DESCRIPTION
            "A set of statistics for a fibre channel interface. The
            interface is indexed by fcInterfaceIndex."
        INDEX { fcInterfaceIndex }
        ::= { fcStatisticsTable 1 }



    FcStatisticsEntry ::=
        SEQUENCE {
            fcStatsClusterNode
                Integer32,
            fcStatsInterfaceIndex
                Integer32,
            fcStatsInterfaceEnabled
                INTEGER,
            fcStatsInterfaceStatus
                INTEGER,
            fcStatsInterfaceLinkSpeed
                Integer32,
            fcStatsInterfaceLinkType
                INTEGER,
            fcStatsInstantaneousInRate
                Counter32,
            fcStatsInstantaneousOutRate
                Counter32,
            fcStatsPeakInRate
                Counter32,
            fcStatsPeakOutRate
                Counter32,
            fcStatsTotalRxBytes
                Counter64,
            fcStatsTotalTxBytes
                Counter64,
            fcStatsSignalLossErrors
                Counter32,
            fcStatsBadRXCharErrors
                Counter32,
            fcStatsLossSyncErrors
                Counter32,
            fcStatsLinkFailErrors
                Counter32,
            fcStatsRXEOFErrors
                Counter32,
            fcStatsDiscardedFrameErrors
                Counter32,
            fcStatsBadCRCErrors
                Counter32,
            fcStatsProtocolErrors
                Counter32
        }

    fcStatsClusterNode OBJECT-TYPE
        SYNTAX Integer32 (0..128)
        MAX-ACCESS read-only
        STATUS current
        DESCRIPTION
            "The Cluster Node to which this row applies."
        ::= { fcStatisticsEntry 1 }

    fcStatsInterfaceIndex OBJECT-TYPE
        SYNTAX Integer32 (0..128)
        MAX-ACCESS read-only
        STATUS current
        DESCRIPTION
            "The index of the fibre channel interface to which
            the statistics in this row apply."
        ::= { fcStatisticsEntry 2 }

    fcStatsInterfaceEnabled OBJECT-TYPE
        SYNTAX INTEGER {
            unknown(0),
            enabled(1),
            disabled(2)
        }
        MAX-ACCESS read-only
        STATUS current
        DESCRIPTION
            "Whether the fibre interface is enabled or not.

             unknown(0)  - the information could not be obtained.
             enabled(1)  - the interface is enabled.
             disabled(2) - the interface is disabled."
        ::= { fcStatisticsEntry 3 }

    fcStatsInterfaceStatus OBJECT-TYPE
        SYNTAX INTEGER {
            unknown(0),
            up(1),
            isolated(2),
            down(3)
        }
        MAX-ACCESS read-only
        STATUS current
        DESCRIPTION
            "The status of the fibre interface.

             unknown(0)  - the information could not be obtained.
             up(1)  - the interface is up.
             isolated(2) - the interface is isolated.
             down(3) - the interface is down."
        ::= { fcStatisticsEntry 4 }

    fcStatsInterfaceLinkSpeed OBJECT-TYPE
        SYNTAX Integer32 (0..128)
        MAX-ACCESS read-only
        STATUS current
        DESCRIPTION
            "The speed of the fibre channel interface in Gbps."
        ::= { fcStatisticsEntry 5 }

    fcStatsInterfaceLinkType OBJECT-TYPE
        SYNTAX INTEGER {
            unknown(0),
            n(1),
            nl(2)
        }
        MAX-ACCESS read-only
        STATUS current
        DESCRIPTION
            "The link-type of the fibre interface.

             unknown(0)  - the information could not be obtained.
             n(1)        - fabric direct attach.
             nl(2)       - arbitrated loop operation."
        ::= { fcStatisticsEntry 6 }

    fcStatsInstantaneousInRate OBJECT-TYPE
        SYNTAX Counter32
        MAX-ACCESS read-only
        STATUS current
        DESCRIPTION
            "The number of bytes received by a fibre channel
             interface in the last second."
        ::= { fcStatisticsEntry 7 }

    fcStatsInstantaneousOutRate OBJECT-TYPE
        SYNTAX Counter32
        MAX-ACCESS read-only
        STATUS current
        DESCRIPTION
            "The number of bytes transmitted by a fibre channel
             interface in the last second."
        ::= { fcStatisticsEntry 8 }

    fcStatsPeakInRate OBJECT-TYPE
        SYNTAX Counter32
        MAX-ACCESS read-only
        STATUS current
        DESCRIPTION
            "The peak receive rate in bytes per second for data received
             through a fibre channel interface."
        ::= { fcStatisticsEntry 9 }

    fcStatsPeakOutRate OBJECT-TYPE
        SYNTAX Counter32
        MAX-ACCESS read-only
        STATUS current
        DESCRIPTION
            "The peak transmission rate in bytes per second for data
            transmitted through a fibre channel interface."
        ::= { fcStatisticsEntry 10 }

    fcStatsTotalRxBytes OBJECT-TYPE
        SYNTAX Counter64
        MAX-ACCESS read-only
        STATUS current
        DESCRIPTION
            "The total bytes received through a fibre channel interface."
        ::= { fcStatisticsEntry 11 }

    fcStatsTotalTxBytes OBJECT-TYPE
        SYNTAX Counter64
        MAX-ACCESS read-only
        STATUS current
        DESCRIPTION
            "The total bytes transmitted through a fibre channel interface."
        ::= { fcStatisticsEntry 12 }

    fcStatsSignalLossErrors OBJECT-TYPE
        SYNTAX Counter32
        MAX-ACCESS read-only
        STATUS current
        DESCRIPTION
            "The total number of loss of signal errors by a fibre channel
             interface."
        ::= { fcStatisticsEntry 13 }

    fcStatsBadRXCharErrors OBJECT-TYPE
        SYNTAX Counter32
        MAX-ACCESS read-only
        STATUS current
        DESCRIPTION
            "The number of bad receive character errors at a fibre
            channel interface."
        ::= { fcStatisticsEntry 14 }

    fcStatsLossSyncErrors OBJECT-TYPE
        SYNTAX Counter32
        MAX-ACCESS read-only
        STATUS current
        DESCRIPTION
            "The number of loss of synchronisation errors at a fibre
            channel interface."
        ::= { fcStatisticsEntry 15 }

    fcStatsLinkFailErrors OBJECT-TYPE
        SYNTAX Counter32
        MAX-ACCESS read-only
        STATUS current
        DESCRIPTION
            "The number of link fail errors at a fibre channel interface."
        ::= { fcStatisticsEntry 16 }

    fcStatsRXEOFErrors OBJECT-TYPE
        SYNTAX Counter32
        MAX-ACCESS read-only
        STATUS current
        DESCRIPTION
            "The number of messages received at a fibre channel interface
            from the frame sender indicating that the frame should be
            aborted because a problem occurred during transmission."
        ::= { fcStatisticsEntry 17 }

     fcStatsDiscardedFrameErrors OBJECT-TYPE
        SYNTAX Counter32
        MAX-ACCESS read-only
        STATUS current
        DESCRIPTION
            "The number of discarded frame errors at a fibre channel
            interface."
        ::= { fcStatisticsEntry 18 }

     fcStatsBadCRCErrors OBJECT-TYPE
        SYNTAX Counter32
        MAX-ACCESS read-only
        STATUS current
        DESCRIPTION
            "The number of framing errors due to bad cyclic redundancy
             codes, at a fibre channel interface."
        ::= { fcStatisticsEntry 19 }

    fcStatsProtocolErrors OBJECT-TYPE
        SYNTAX Counter32
        MAX-ACCESS read-only
        STATUS current
        DESCRIPTION
            "The number of fibre channel protocol errors at a fibre
            channel interface."
        ::= { fcStatisticsEntry 20 }

--------------------------------------------------------------------------------
--
-- System / Storage / Virtual Volumes
--
--------------------------------------------------------------------------------

    virtualVolumeNumber OBJECT-TYPE
        SYNTAX Integer32
        MAX-ACCESS read-only
        STATUS obsolete
        DESCRIPTION
            "The number of virtual volumes which are currently accessible.
             NOTE: a virtual volume is only accessible if its associated
                   parent volume is mounted.

             This object has been obsolete."
        ::= { virtualVolumes 1 }

    virtualVolumeTable OBJECT-TYPE
        SYNTAX SEQUENCE OF VirtualVolumeEntry
        MAX-ACCESS not-accessible
        STATUS obsolete
        DESCRIPTION
            "A table containing information about each virtual volume.

             The number of entries in this table is given by the value of 
             virtualVolumeNumber.

             This object has been obsolete."
        ::= { virtualVolumes 2 }

    virtualVolumeEntry OBJECT-TYPE
        SYNTAX VirtualVolumeEntry
        MAX-ACCESS not-accessible
        STATUS obsolete
        DESCRIPTION
            "Information about a virtual volume.

             This object has been obsolete."
        INDEX { virtualVolumeSysDriveIndex, virtualVolumePartitionID, virtualVolumeLabel }
        ::= { virtualVolumeTable 1 }

    VirtualVolumeEntry ::=
        SEQUENCE {
            virtualVolumeSysDriveIndex
                Integer32,
            virtualVolumePartitionID
                Unsigned32,
            virtualVolumeLabel
                DisplayString,
            virtualVolumeQuotaEnabled
                INTEGER,
            virtualVolumeLimit
                Counter64,
            virtualVolumeWarningAlert
                Integer32,
            virtualVolumeCriticalAlert
                Integer32,
            virtualVolumeHardLimitEnabled
                INTEGER,
            virtualVolumeQuotaBytesUsed
                Counter64,
            virtualVolumeQuotaPercentageUsed
                Integer32
        }

    virtualVolumeSysDriveIndex OBJECT-TYPE
        SYNTAX Integer32 (1..25)
        MAX-ACCESS read-only
        STATUS obsolete
        DESCRIPTION
            "The parent system drive of the virtual volume.
             The system drive identified by a particular value of this index is
             located on the system drive identified by the same value of 
             sysDriveIndex.

             This object has been obsolete."
        ::= { virtualVolumeEntry 1 }

    virtualVolumePartitionID OBJECT-TYPE
        SYNTAX Unsigned32
        MAX-ACCESS read-only
        STATUS obsolete
        DESCRIPTION
            "The partition ID of the parent volume of this virtual volume.
             The virtualVolumeSysDriveIndex and this value may be used to
             index the volumeTable in order to establish the parent volume.

             This object has been obsolete."
        ::= { virtualVolumeEntry 2 }

    virtualVolumeLabel OBJECT-TYPE
        SYNTAX DisplayString
        MAX-ACCESS read-only
        STATUS obsolete
        DESCRIPTION
            "The label assigned to the virtual volume by a user for 
             identification purposes.

             This object has been obsolete."
        ::= { virtualVolumeEntry 3 }

    virtualVolumeQuotaEnabled OBJECT-TYPE
        SYNTAX INTEGER {
            enabled(1),
            disabled(2)
        }
        MAX-ACCESS read-only
        STATUS obsolete
        DESCRIPTION
            "Indicates whether the virtual volume quota checking
             facility is enabled or not.

             enabled(1)  - quota checking is enabled.
             disabled(2) - quota checking is disabled.

             This object has been obsolete."
        ::= { virtualVolumeEntry 4 }

    virtualVolumeLimit OBJECT-TYPE
        SYNTAX Counter64
        MAX-ACCESS read-only
        STATUS obsolete
        DESCRIPTION
            "The maximum size this virtual volume is limited to
             in bytes for the purposes of quota checking.

             This object has been obsolete."
        ::= { virtualVolumeEntry 5 }

    virtualVolumeWarningAlert OBJECT-TYPE
        SYNTAX Integer32 (1..100)
        MAX-ACCESS read-only
        STATUS obsolete
        DESCRIPTION
            "If the quota facility is enabled and the storage
             space used exceeds this percentage of the virtual
             volumes limit (virtualVolumeLimit) a warning alert 
             will be generated.

             This object has been obsolete."
        ::= { virtualVolumeEntry 6 }

    virtualVolumeCriticalAlert OBJECT-TYPE
        SYNTAX Integer32 (1..100)
        MAX-ACCESS read-only
        STATUS obsolete
        DESCRIPTION
            "If the quota facility is enabled and the storage
             space used exceeds this percentage of the virtual
             volumes limit (virtualVolumeLimit) a critical alert 
             will be generated.

             This object has been obsolete."
        ::= { virtualVolumeEntry 7 }

    virtualVolumeHardLimitEnabled OBJECT-TYPE
        SYNTAX INTEGER {
            enabled(1),
            disabled(2)
        }
        MAX-ACCESS read-only
        STATUS obsolete
        DESCRIPTION
            "If the quota facility is enabled, this value
             indicates whether the file system should enforce
             a hard limit on the quota such that if the
             virtual volumes limit (virtualVolumeLimit) is reached,
             the user will not be able to create or modify any file 
             which would cause the quota to be exceeded.

             enabled(1)  - quota hard limit is enabled.
             disabled(2) - quota hard limit is disabled.

             This object has been obsolete."
        ::= { virtualVolumeEntry 8 }

    virtualVolumeQuotaBytesUsed OBJECT-TYPE
        SYNTAX Counter64
        MAX-ACCESS read-only
        STATUS obsolete
        DESCRIPTION
            "If the quota facility is enabled this value is 
             the number of bytes used from this quota otherwise
             it will be set 0.

             This object has been obsolete."
        ::= { virtualVolumeEntry 9 }

    virtualVolumeQuotaPercentageUsed OBJECT-TYPE
        SYNTAX Integer32 (1..100)
        MAX-ACCESS read-only
        STATUS obsolete
        DESCRIPTION
            "If the quota facility is enabled this value is 
             the percentage of the quota used otherwise it will
             set to 0.

             This object has been obsolete."
        ::= { virtualVolumeEntry 10 }

--------------------------------------------------------------------------------
--
-- System / Storage / Member Lists for Virtual Volumes
--
--------------------------------------------------------------------------------

    memberListNumber OBJECT-TYPE
        SYNTAX Integer32
        MAX-ACCESS read-only
        STATUS obsolete
        DESCRIPTION
            "The number of member list entries for all virtual volumes
             which are accessible.

             This object has been obsolete."
        ::= { virtualVolumes 3 }

    memberListTable OBJECT-TYPE
        SYNTAX SEQUENCE OF MemberListEntry
        MAX-ACCESS not-accessible
        STATUS obsolete
        DESCRIPTION
            "A table containing information about each member list
             item.

             The number of entries in this table is given by the value of
             memberListNumber..

             This object has been obsolete."
        ::= { virtualVolumes 4 }

    memberListEntry OBJECT-TYPE
        SYNTAX MemberListEntry
        MAX-ACCESS not-accessible
        STATUS obsolete
        DESCRIPTION
            "Information about a member list item.

             This object has been obsolete."
        INDEX { memberListVolumeSysDriveIndex, memberListVolumePartitionID,
                memberListVirtualVolumeLabel, memberListIndex }
        ::= { memberListTable 1 }

    MemberListEntry ::=
        SEQUENCE {
            memberListVolumeSysDriveIndex
                Integer32,
            memberListVolumePartitionID
                Unsigned32,
            memberListVirtualVolumeLabel
                DisplayString,
            memberListIndex
                Integer32,
            memberListPath
                DisplayString,
            memberListStatus
                INTEGER
        }

    memberListVolumeSysDriveIndex OBJECT-TYPE
        SYNTAX Integer32 (1..25)
        MAX-ACCESS read-only
        STATUS obsolete
        DESCRIPTION
            "The parent system drive of the virtual volume and
             member list item.
             The system drive identified by a particular value of this index is
             located on the system drive identified by the same value of 
             sysDriveIndex.

             This object has been obsolete."
        ::= { memberListEntry 1 }

    memberListVolumePartitionID OBJECT-TYPE
        SYNTAX Unsigned32
        MAX-ACCESS read-only
        STATUS obsolete
        DESCRIPTION
            "The partition ID of the parent volume of this virtual volume
             and member list item.
             The memberListVolumeSysDriveIndex and this value may be used to
             index the volumeTable in order to establish the parent volume.

             This object has been obsolete."
        ::= { memberListEntry 2 }

    memberListVirtualVolumeLabel OBJECT-TYPE
        SYNTAX DisplayString
        MAX-ACCESS read-only
        STATUS obsolete
        DESCRIPTION
            "The label of the parent virtual volume of this member list
             item.

             This object has been obsolete."
        ::= { memberListEntry 3 }

    memberListIndex OBJECT-TYPE
        SYNTAX Integer32 (1..200)
        MAX-ACCESS read-only
        STATUS obsolete
        DESCRIPTION
            "An identifier for this member list entry.
             This identifier ranges from 1 to the number of member list
             items configured for the parent virtual volume.

             This object has been obsolete."
        ::= { memberListEntry 4 }

    memberListPath OBJECT-TYPE
        SYNTAX DisplayString
        MAX-ACCESS read-only
        STATUS obsolete
        DESCRIPTION
            "The path the member list item is associated with.

             This object has been obsolete."
        ::= { memberListEntry 5 }

    memberListStatus OBJECT-TYPE
        SYNTAX INTEGER {
            done(1),
            pending(2),
            assigning(3),
            reparenting(4),
            deleting(5),
            failed(6)
        }
        MAX-ACCESS read-only
        STATUS obsolete
        DESCRIPTION
            "This status of the member list item.

             This object has been obsolete."
        ::= { memberListEntry 6 }

--------------------------------------------------------------------------------
--
-- System / Storage / Snapshot Rules
--
--------------------------------------------------------------------------------

    snapshotRuleNumber OBJECT-TYPE
        SYNTAX Integer32
        MAX-ACCESS read-only
        STATUS current
        DESCRIPTION
            "The number of snapshot rules which are configured for
             this system."
        ::= { snapshot 1 }

    snapshotRuleTable OBJECT-TYPE
        SYNTAX SEQUENCE OF SnapshotRuleEntry
        MAX-ACCESS not-accessible
        STATUS obsolete
        DESCRIPTION
            "A table containing information about each snapshot rule.

             The number of entries in this table is given by the value of
             snapshotRuleNumber.

             This object is now obsolete."
        ::= { snapshot 2 }

    snapshotRuleEntry OBJECT-TYPE
        SYNTAX SnapshotRuleEntry
        MAX-ACCESS not-accessible
        STATUS obsolete
        DESCRIPTION
            "Information about a snapshot rule.

             This object is now obsolete."
        INDEX { snapshotRuleName }
        ::= { snapshotRuleTable 1 }

    SnapshotRuleEntry ::=
        SEQUENCE {
            snapshotRuleName
                DisplayString,
            snapshotRuleWWN
                DisplayString,
            snapshotRuleLUN
                Unsigned32,
            snapshotRulePartitionID
                Unsigned32,
            snapshotRuleQueueSize
                Integer32,
            snapshotRuleVolumeLabel
                DisplayString
        }

    snapshotRuleName OBJECT-TYPE
        SYNTAX DisplayString
        MAX-ACCESS read-only
        STATUS obsolete
        DESCRIPTION
            "The name of the snapshot rule.  Each snapshot rule has a unique
             name.

             This object is now obsolete."
        ::= { snapshotRuleEntry 1 }

    snapshotRuleWWN OBJECT-TYPE
        SYNTAX DisplayString
        MAX-ACCESS read-only
        STATUS obsolete
        DESCRIPTION
            "The world wide name (WWN) of the system drive the snapshot rule
             is associated with.

             This object is now obsolete."
        ::= { snapshotRuleEntry 2 }

    snapshotRuleLUN OBJECT-TYPE
        SYNTAX Unsigned32
        MAX-ACCESS read-only
        STATUS obsolete
        DESCRIPTION
            "The logical unit number (LUN) of the system drive the
             snapshot rule is associated with.

             This object is now obsolete."
        ::= { snapshotRuleEntry 3 }

    snapshotRulePartitionID OBJECT-TYPE
        SYNTAX Unsigned32
        MAX-ACCESS read-only
        STATUS obsolete
        DESCRIPTION
            "The partition ID of the volume the snapshot rule is associated
             with.

             This object is now obsolete."
        ::= { snapshotRuleEntry 4 }

    snapshotRuleQueueSize OBJECT-TYPE
        SYNTAX Integer32
        MAX-ACCESS read-only
        STATUS obsolete
        DESCRIPTION
            "The number of snapshots to keep before the system deletes the
             oldest snapshot.

             This object is now obsolete."
        ::= { snapshotRuleEntry 5 }

    snapshotRuleVolumeLabel OBJECT-TYPE
        SYNTAX DisplayString
        MAX-ACCESS read-only
        STATUS obsolete
        DESCRIPTION
            "The label of the volume to which the snapshot rule relates.

             This object is now obsolete."
        ::= { snapshotRuleEntry 6 }

--------------------------------------------------------------------------------
--
-- System / Storage / Snapshot Schedules
--
--------------------------------------------------------------------------------

    snapshotScheduleNumber OBJECT-TYPE
        SYNTAX Integer32
        MAX-ACCESS read-only
        STATUS current
        DESCRIPTION
            "The number of snapshot schedules which are configured for
             this system."
        ::= { snapshot 3 }

    snapshotScheduleTable OBJECT-TYPE
        SYNTAX SEQUENCE OF SnapshotScheduleEntry
        MAX-ACCESS not-accessible
        STATUS obsolete
        DESCRIPTION
            "A table containing information about each snapshot schedule.

             The number of entries in this table is given by the value of
             snapshotScheduleNumber.

             This object is now obsolete."
        ::= { snapshot 4 }

    snapshotScheduleEntry OBJECT-TYPE
        SYNTAX SnapshotScheduleEntry
        MAX-ACCESS not-accessible
        STATUS obsolete
        DESCRIPTION
            "Information about a snapshot schedule.

             This object is now obsolete."
        INDEX { snapshotScheduleRuleName, snapshotScheduleIndex }
        ::= { snapshotScheduleTable 1 }

    SnapshotScheduleEntry ::=
        SEQUENCE {
            snapshotScheduleRuleName
                DisplayString,
            snapshotScheduleIndex
                Integer32,
            snapshotScheduleDateTimeSpec
                DisplayString
        }

    snapshotScheduleRuleName OBJECT-TYPE
        SYNTAX DisplayString
        MAX-ACCESS read-only
        STATUS obsolete
        DESCRIPTION
            "The name of the parent snapshot rule that this schedule
             is associated with.

             This object is now obsolete."
        ::= { snapshotScheduleEntry 1 }

    snapshotScheduleIndex OBJECT-TYPE
        SYNTAX Integer32 (1..100)
        MAX-ACCESS read-only
        STATUS obsolete
        DESCRIPTION
            "An identifier for this snapshot schedule entry.
             This identifier ranges from 1 to the number of snapshot
             schedules configured for the parent snapshot rule.

             This object is now obsolete."
        ::= { snapshotScheduleEntry 2 }

    snapshotScheduleDateTimeSpec OBJECT-TYPE
        SYNTAX DisplayString
        MAX-ACCESS read-only
        STATUS obsolete
        DESCRIPTION
            "The date and time specification for when this snapshot
             schedule will be run in cron format.

             This object is now obsolete."
        ::= { snapshotScheduleEntry 3 }

--------------------------------------------------------------------------------
--
-- System / Storage / Snapshot Rules by EVS
--
--------------------------------------------------------------------------------

    snapshotRulesTable OBJECT-TYPE
        SYNTAX SEQUENCE OF SnapshotRulesEntry
        MAX-ACCESS not-accessible
        STATUS current
        DESCRIPTION
            "A table containing information about each snapshot rule.

             The number of entries in this table is given by the value of
             snapshotRuleNumber."
        ::= { snapshot 5 }

    snapshotRulesEntry OBJECT-TYPE
        SYNTAX SnapshotRulesEntry
        MAX-ACCESS not-accessible
        STATUS current
        DESCRIPTION
            "Information about a snapshot rule."
        INDEX { snapshotRulesEVS, snapshotRulesName }
        ::= { snapshotRulesTable 1 }

    SnapshotRulesEntry ::=
        SEQUENCE {
            snapshotRulesEVS
                Unsigned32,
            snapshotRulesName
                DisplayString,
            snapshotRulesQueueSize
                Integer32,
            snapshotRulesVolumeLabel
                DisplayString
        }

    snapshotRulesEVS OBJECT-TYPE
        SYNTAX Unsigned32
        MAX-ACCESS read-only
        STATUS current
        DESCRIPTION
            "The ID of the EVS on which this rule is defined."
        ::= { snapshotRulesEntry 1 }

    snapshotRulesName OBJECT-TYPE
        SYNTAX DisplayString
        MAX-ACCESS read-only
        STATUS current
        DESCRIPTION
            "The name of the snapshot rule.  Each snapshot rule has a unique
             name."
        ::= { snapshotRulesEntry 2 }

    snapshotRulesQueueSize OBJECT-TYPE
        SYNTAX Integer32
        MAX-ACCESS read-only
        STATUS current
        DESCRIPTION
            "The number of snapshots to keep before the system deletes the
             oldest snapshot."
        ::= { snapshotRulesEntry 3 }

    snapshotRulesVolumeLabel OBJECT-TYPE
        SYNTAX DisplayString
        MAX-ACCESS read-only
        STATUS current
        DESCRIPTION
            "The label of the volume to which the snapshot rule relates."
        ::= { snapshotRulesEntry 4 }

--------------------------------------------------------------------------------
--
-- System / Storage / Snapshot Schedules by EVS
--
--------------------------------------------------------------------------------

    snapshotSchedulesTable OBJECT-TYPE
        SYNTAX SEQUENCE OF SnapshotSchedulesEntry
        MAX-ACCESS not-accessible
        STATUS current
        DESCRIPTION
            "A table containing information about each snapshot schedule.

             The number of entries in this table is given by the value of
             snapshotScheduleNumber."
        ::= { snapshot 6 }

    snapshotSchedulesEntry OBJECT-TYPE
        SYNTAX SnapshotSchedulesEntry
        MAX-ACCESS not-accessible
        STATUS current
        DESCRIPTION
            "Information about a snapshot schedule."
        INDEX { snapshotSchedulesEVS, snapshotSchedulesRuleName, snapshotSchedulesIndex }
        ::= { snapshotSchedulesTable 1 }

    SnapshotSchedulesEntry ::=
        SEQUENCE {
            snapshotSchedulesEVS
                Unsigned32,
            snapshotSchedulesRuleName
                DisplayString,
            snapshotSchedulesIndex
                Integer32,
            snapshotSchedulesDateTimeSpec
                DisplayString
        }

    snapshotSchedulesEVS OBJECT-TYPE
        SYNTAX Unsigned32
        MAX-ACCESS read-only
        STATUS current
        DESCRIPTION
            "The ID of the EVS on which this schedule is defined."
        ::= { snapshotSchedulesEntry 1 }

    snapshotSchedulesRuleName OBJECT-TYPE
        SYNTAX DisplayString
        MAX-ACCESS read-only
        STATUS current
        DESCRIPTION
            "The name of the parent snapshot rule that this schedule
             is associated with."
        ::= { snapshotSchedulesEntry 2 }

    snapshotSchedulesIndex OBJECT-TYPE
        SYNTAX Integer32 (1..100)
        MAX-ACCESS read-only
        STATUS current
        DESCRIPTION
            "An identifier for this snapshot schedule entry.
             This identifier ranges from 1 to the number of snapshot
             schedules configured for the parent snapshot rule."
        ::= { snapshotSchedulesEntry 3 }

    snapshotSchedulesDateTimeSpec OBJECT-TYPE
        SYNTAX DisplayString
        MAX-ACCESS read-only
        STATUS current
        DESCRIPTION
            "The date and time specification for when this snapshot
             schedule will be run in cron format."
        ::= { snapshotSchedulesEntry 4 }

--------------------------------------------------------------------------------
--
-- System / Storage / NVRAM volume statistics
--
--------------------------------------------------------------------------------

    nvramFsStatsNumber OBJECT-TYPE
        SYNTAX Unsigned32 (1..2147483647)
        MAX-ACCESS read-only
        STATUS current
        DESCRIPTION
            "The number of volumes with NVRAM statistics."
        ::= { nvramStats 1 }

    nvramFsStatsTable OBJECT-TYPE
        SYNTAX SEQUENCE OF NvramFsStatsEntry
        MAX-ACCESS not-accessible
        STATUS current
        DESCRIPTION
            "A table of NVRAM data for a given volume."
        ::= { nvramStats 2 }

    nvramFsStatsEntry OBJECT-TYPE
        SYNTAX NvramFsStatsEntry
        MAX-ACCESS not-accessible
        STATUS current
        DESCRIPTION
            "Information about NVRAM on a given volume. The
            volume must be formatted, mounted, and NVRAM must
            be supported."
        INDEX { fsId }
        ::= { nvramFsStatsTable 1 }

    NvramFsStatsEntry ::=
        SEQUENCE {
            fsId
                Unsigned32,
            nvramFsStatsCurrentUsage
                Unsigned32,
            nvramFsStatsCheckpoints
                Unsigned32,
            nvramFsStatsActivityCheckpoints
                Unsigned32,
            nvramFsStatsWaitedAllocs
                Unsigned32,
            nvramFsStatsWaitingAllocs
                Unsigned32
        }

    fsId OBJECT-TYPE
        SYNTAX Unsigned32
        MAX-ACCESS read-only
        STATUS current
        DESCRIPTION
            "The id of the Span hosting the volume with which the
            NVRAM is associated."
        ::= { nvramFsStatsEntry 1 }

    nvramFsStatsCurrentUsage OBJECT-TYPE
        SYNTAX Unsigned32
        MAX-ACCESS read-only
        STATUS current
        DESCRIPTION
            "The amount of NVRAM currently in use for this volume."
        ::= { nvramFsStatsEntry 2 }

   nvramFsStatsCheckpoints OBJECT-TYPE
        SYNTAX Unsigned32
        MAX-ACCESS read-only
        STATUS current
        DESCRIPTION
            "The total number of checkpoints which have occurred for the
            NVRAM assigned to this volume."
        ::= { nvramFsStatsEntry 3 }

   nvramFsStatsActivityCheckpoints OBJECT-TYPE
        SYNTAX Unsigned32
        MAX-ACCESS read-only
        STATUS current
        DESCRIPTION
            "The number of checkpoints which have occurred for the NVRAM
            assigned to this volume as a result of file system activity
            (i.e. not timed checkpoints."
        ::= { nvramFsStatsEntry 4 }

   nvramFsStatsWaitedAllocs OBJECT-TYPE
        SYNTAX Unsigned32
        MAX-ACCESS read-only
        STATUS current
        DESCRIPTION
            "The number of allocations for this file system for which
             a wait has occurred."
        ::= { nvramFsStatsEntry 5 }

   nvramFsStatsWaitingAllocs OBJECT-TYPE
        SYNTAX Unsigned32
        MAX-ACCESS read-only
        STATUS current
        DESCRIPTION
            "The number of allocations for this file system for which 
             a wait is currently occurring."
        ::= { nvramFsStatsEntry 6 } 

--------------------------------------------------------------------------------
--
-- System / Storage / NVRAM pool statistics
--
--------------------------------------------------------------------------------
        
   nvramPoolStatsTable OBJECT-TYPE
        SYNTAX SEQUENCE OF NvramPoolStatsEntry
        MAX-ACCESS not-accessible
        STATUS current
        DESCRIPTION
            "A table of NVRAM data for a given Cluster Node."
        ::= { nvramStats 6 }

    nvramPoolStatsEntry OBJECT-TYPE
        SYNTAX NvramPoolStatsEntry
        MAX-ACCESS not-accessible
        STATUS current
        DESCRIPTION
            "Information about NVRAM on a given Cluster Node."
        INDEX { clusterNodeId }
        ::= { nvramPoolStatsTable 1 }

    NvramPoolStatsEntry ::=
        SEQUENCE {
            clusterNodeId
                Unsigned32,
            nvramPoolStatsSize
                Unsigned32,
            nvramPoolStatsMaximumUsed
                Unsigned32,
            nvramPoolStatsTotalCurrentUsage
                Unsigned32,
            nvramPoolStatsWaitedAllocs
                Unsigned32,
            nvramPoolStatsWaitingAllocs
                Unsigned32
        }

    clusterNodeId OBJECT-TYPE
        SYNTAX Unsigned32 (0..255)
        MAX-ACCESS read-only
        STATUS current
        DESCRIPTION
            "The ID of the cluster node for which these pool
            statistics are reported."
        ::= { nvramPoolStatsEntry 1 }

    nvramPoolStatsSize OBJECT-TYPE
        SYNTAX Unsigned32 (1..2147483647)
        MAX-ACCESS read-only
        STATUS current
        DESCRIPTION
            "The total size of nvram. If no formatted or mounted volume
            is found, or if nvram is not supported, this value will be reported
            as zero."
        ::= { nvramPoolStatsEntry 2 }

    nvramPoolStatsMaximumUsed OBJECT-TYPE
        SYNTAX Unsigned32 (1..2147483647)
        MAX-ACCESS read-only
        STATUS current
        DESCRIPTION
            "The maximum amount of nvram used. If no formatted or mounted volume
            is found, or if nvram is not supported, this value will be reported
            as zero."
        ::= { nvramPoolStatsEntry 3 }

    nvramPoolStatsTotalCurrentUsage OBJECT-TYPE
        SYNTAX Unsigned32 (1..2147483647)
        MAX-ACCESS read-only
        STATUS current
        DESCRIPTION
            "The amount of nvram currently in use. If no formatted or mounted
            volume is found, or if nvram is not supported, this value will be
            reported as zero."
        ::= { nvramPoolStatsEntry 4 }

    nvramPoolStatsWaitedAllocs OBJECT-TYPE
        SYNTAX Unsigned32 (1..2147483647)
        MAX-ACCESS read-only
        STATUS current
        DESCRIPTION
            "The number of allocations, for the entire NVRAM pool, for which 
            a wait has occurred."
        ::= { nvramPoolStatsEntry 5 }

    nvramPoolStatsWaitingAllocs OBJECT-TYPE
        SYNTAX Unsigned32 (1..2147483647)
        MAX-ACCESS read-only
        STATUS current
        DESCRIPTION
            "The number of allocations, for the entire NVRAM pool, for which 
            a wait is occurring."
        ::= { nvramPoolStatsEntry 6 }

--------------------------------------------------------------------------------
--
-- Network / Ethernet Statistics
--
--------------------------------------------------------------------------------

    ethOutPkts OBJECT-TYPE
        SYNTAX Counter64
        MAX-ACCESS read-only
        STATUS obsolete
        DESCRIPTION
            "The number of packets successfully transmitted through the
             network interface.

             This object is obsolete.
             It has been grouped with other related statistics."

        ::= { etherStats 1 }

    ethInPkts OBJECT-TYPE
        SYNTAX Counter64
        MAX-ACCESS read-only
        STATUS obsolete
        DESCRIPTION
            "The number of packets successfully received through the
             network interface.

             This object is obsolete.
             It has been grouped with other related statistics."
        ::= { etherStats 2 }

    ethInstInOctetRate OBJECT-TYPE
        SYNTAX Counter32
        MAX-ACCESS read-only
        STATUS obsolete
        DESCRIPTION
            "The instantaneous receive rate in bytes per second for
             data received through the network interface.

             This object is obsolete. It now forms part of the table
             ethernetStatisticsTable."
        ::= { etherStats 3 }

    ethInstOutOctetRate OBJECT-TYPE
        SYNTAX Counter32
        MAX-ACCESS read-only
        STATUS obsolete
        DESCRIPTION
            "The instantaneous transmission rate in bytes per second for
             data transmitted through the network interface.

             This object is obsolete. It now forms part of the table
             ethernetStatisticsTable."
        ::= { etherStats 4 }

    ethPkInOctetRate OBJECT-TYPE
        SYNTAX Counter32
        MAX-ACCESS read-only
        STATUS obsolete
        DESCRIPTION
            "The peak receive rate in bytes per second for data received
             through the network interface.

             This object is obsolete. It now forms part of the table
             ethernetStatisticsTable."
        ::= { etherStats 5 }

    ethPkOutOctetRate OBJECT-TYPE
        SYNTAX Counter32
        MAX-ACCESS read-only
        STATUS obsolete
        DESCRIPTION
            "The peak transmission rate in bytes per second for data
             transmitted through the network interface.

             This object is obsolete. It now forms part of the table
             ethernetStatisticsTable."
        ::= { etherStats 6 }

    ethInFIFODrops OBJECT-TYPE
        SYNTAX Counter64
        MAX-ACCESS read-only
        STATUS obsolete
        DESCRIPTION
            "The number of FIFO drops which have occurred on the network
             interface.

             This object is obsolete. It now forms part of the table
             ethernetStatisticsTable."
        ::= { etherStats 7 }

    ethCRCErrs OBJECT-TYPE
        SYNTAX Counter64
        MAX-ACCESS read-only
        STATUS obsolete
        DESCRIPTION
            "The number of cyclic redundancy code errors which have
             occurred on the network interface.

             This object is obsolete. It now forms part of the table
             ethernetStatisticsTable."
        ::= { etherStats 8 }

    ethOutFIFOUflows OBJECT-TYPE
        SYNTAX Counter64
        MAX-ACCESS read-only
        STATUS obsolete
        DESCRIPTION
            "The number of transmit FIFO underflows which have occurred
             on the network interface.

             This object is obsolete. It now forms part of the table
             ethernetStatisticsTable."
        ::= { etherStats 9 }

    ethOutOneCollision OBJECT-TYPE
        SYNTAX Counter64
        MAX-ACCESS read-only
        STATUS obsolete
        DESCRIPTION
            "The number of one collisions which have occurred on the
             network interface.

             This object is obsolete. It now forms part of the table
             ethernetStatisticsTable."
        ::= { etherStats 10 }

    ethOutTwoCollision OBJECT-TYPE
        SYNTAX Counter64
        MAX-ACCESS read-only
        STATUS obsolete
        DESCRIPTION
            "The number of two to fifteen collisions which have occurred on
             the network interface.

             This object is obsolete. It now forms part of the table
             ethernetStatisticsTable."
        ::= { etherStats 11 }

    ethOutFifteenCollision OBJECT-TYPE
        SYNTAX Counter64
        MAX-ACCESS read-only
        STATUS obsolete
        DESCRIPTION
            "The number of more than fifteen collisions which have occurred on
             the network interface.

             This object is obsolete. It now forms part of the table
             ethernetStatisticsTable."
        ::= { etherStats 12 }

    ethInEvFIFOPktDrop OBJECT-TYPE
        SYNTAX Counter64
        MAX-ACCESS read-only
        STATUS obsolete
        DESCRIPTION
            "The number received packets dropped by the event FIFO.

             This object is obsolete. It now forms part of the table
             ethernetStatisticsTable."
        ::= { etherStats 13 }

    ethEvFIFOMaxEvents OBJECT-TYPE
        SYNTAX Counter64
        MAX-ACCESS read-only
        STATUS obsolete
        DESCRIPTION
            "The maximum number of events in the event FIFO.

             This object is obsolete. It now forms part of the table
             ethernetStatisticsTable."
        ::= { etherStats 14 }

    ethOutPackets OBJECT-TYPE
        SYNTAX Counter64
        MAX-ACCESS read-only
        STATUS obsolete
        DESCRIPTION
            "The number of packets successfully transmitted through the
             network interface.

             This object is obsolete. It now forms part of the table
             ethernetStatisticsTable."
        ::= { etherStats 15 }

    ethInPackets OBJECT-TYPE
        SYNTAX Counter64
        MAX-ACCESS read-only
        STATUS obsolete
        DESCRIPTION
            "The number of packets successfully received through the
             network interface.

             This object is obsolete. It now forms part of the table
             ethernetStatisticsTable."
        ::= { etherStats 16 }

    ethTotalPackets OBJECT-TYPE
        SYNTAX Counter64
        MAX-ACCESS read-only
        STATUS obsolete
        DESCRIPTION
            "The total number of packets successfully transmitted and received
            through the network interface.

             This object is obsolete. It now forms part of the table
             ethernetStatisticsTable."
        ::= { etherStats 17 }

    ethOutBytes OBJECT-TYPE
        SYNTAX Counter64
        MAX-ACCESS read-only
        STATUS obsolete
        DESCRIPTION
            "The number of bytes successfully transmitted through the
             network interface.

             This object is obsolete. It now forms part of the table
             ethernetStatisticsTable."
        ::= { etherStats 18 }

    ethInBytes OBJECT-TYPE
        SYNTAX Counter64
        MAX-ACCESS read-only
        STATUS obsolete
        DESCRIPTION
            "The number of bytes successfully received through the
             network interface.

             This object is obsolete. It now forms part of the table
             ethernetStatisticsTable."
        ::= { etherStats 19 }

    ethTotalBytes OBJECT-TYPE
        SYNTAX Counter64
        MAX-ACCESS read-only
        STATUS obsolete
        DESCRIPTION
            "The total number of bytes successfully transmitted and received
            through the network interface.

             This object is obsolete. It now forms part of the table
             ethernetStatisticsTable."
        ::= { etherStats 20 }

    ethernetStatisticsTable OBJECT-TYPE
        SYNTAX SEQUENCE OF EthernetStatisticsEntry
        MAX-ACCESS not-accessible
        STATUS current
        DESCRIPTION
            "A table of statistics for ethernet interfaces.

             The number of entries in this table is given by the value of
             ifNumber."
        ::= { etherStats 21 }

    ethernetStatisticsEntry OBJECT-TYPE
        SYNTAX EthernetStatisticsEntry
        MAX-ACCESS not-accessible
        STATUS current
        DESCRIPTION
            "Statistics for ethernet interfaces."
        INDEX { ifIndex }
        ::= { ethernetStatisticsTable 1 }

    EthernetStatisticsEntry ::=
        SEQUENCE {
            ethernetInstInOctetRate
                Counter32,
            ethernetInstOutOctetRate
                Counter32,
            ethernetPkInOctetRate
                Counter32,
            ethernetPkOutOctetRate
                Counter32,
            ethernetInFIFODrops
                Counter64,
            ethernetCRCErrs
                Counter64,
            ethernetOutFIFOUflows
                Counter64,
            ethernetOutOneCollision
                Counter64,
            ethernetOutTwoCollision
                Counter64,
            ethernetOutFifteenCollision
                Counter64,
            ethernetInEvFIFOPktDrop
                Counter64,
            ethernetEvFIFOMaxEvents
                Counter64,
            ethernetOutPackets
                Counter64,
            ethernetInPackets
                Counter64,
            ethernetTotalPackets
                Counter64,
            ethernetOutBytes
                Counter64,
            ethernetInBytes
                Counter64,
            ethernetTotalBytes
                Counter64
        }

     ethernetInstInOctetRate OBJECT-TYPE
        SYNTAX Counter32
        MAX-ACCESS read-only
        STATUS current
        DESCRIPTION
            "The instantaneous receive rate in bytes per second for
             data received through the network interface."
        ::= { ethernetStatisticsEntry 1 }

    ethernetInstOutOctetRate OBJECT-TYPE
        SYNTAX Counter32
        MAX-ACCESS read-only
        STATUS current
        DESCRIPTION
            "The instantaneous transmission rate in bytes per second for
             data transmitted through the network interface."
        ::= { ethernetStatisticsEntry 2 }

    ethernetPkInOctetRate OBJECT-TYPE
        SYNTAX Counter32
        MAX-ACCESS read-only
        STATUS current
        DESCRIPTION
            "The peak receive rate in bytes per second for data received
             through the network interface."
        ::= { ethernetStatisticsEntry 3 }

    ethernetPkOutOctetRate OBJECT-TYPE
        SYNTAX Counter32
        MAX-ACCESS read-only
        STATUS current
        DESCRIPTION
            "The peak transmission rate in bytes per second for data
             transmitted through the network interface."
        ::= { ethernetStatisticsEntry 4 }

    ethernetInFIFODrops OBJECT-TYPE
        SYNTAX Counter64
        MAX-ACCESS read-only
        STATUS current
        DESCRIPTION
            "The number of FIFO drops which have occurred on the network
             interface."
        ::= { ethernetStatisticsEntry 5 }

    ethernetCRCErrs OBJECT-TYPE
        SYNTAX Counter64
        MAX-ACCESS read-only
        STATUS current
        DESCRIPTION
            "The number of cyclic redundancy code errors which have
             occurred on the network interface."
        ::= { ethernetStatisticsEntry 6 }

    ethernetOutFIFOUflows OBJECT-TYPE
        SYNTAX Counter64
        MAX-ACCESS read-only
        STATUS current
        DESCRIPTION
            "The number of transmit FIFO underflows which have occurred
             on the network interface."
        ::= { ethernetStatisticsEntry 7 }

    ethernetOutOneCollision OBJECT-TYPE
        SYNTAX Counter64
        MAX-ACCESS read-only
        STATUS current
        DESCRIPTION
            "The number of one collisions which have occurred on the
             network interface."
        ::= { ethernetStatisticsEntry 8 }

    ethernetOutTwoCollision OBJECT-TYPE
        SYNTAX Counter64
        MAX-ACCESS read-only
        STATUS current
        DESCRIPTION
            "The number of two to fifteen collisions which have occurred on
             the network interface."
        ::= { ethernetStatisticsEntry 9 }

    ethernetOutFifteenCollision OBJECT-TYPE
        SYNTAX Counter64
        MAX-ACCESS read-only
        STATUS current
        DESCRIPTION
            "The number of more than fifteen collisions which have occurred on
             the network interface."
        ::= { ethernetStatisticsEntry 10 }

    ethernetInEvFIFOPktDrop OBJECT-TYPE
        SYNTAX Counter64
        MAX-ACCESS read-only
        STATUS current
        DESCRIPTION
            "The number received packets dropped by the event FIFO."
        ::= { ethernetStatisticsEntry 11 }

    ethernetEvFIFOMaxEvents OBJECT-TYPE
        SYNTAX Counter64
        MAX-ACCESS read-only
        STATUS current
        DESCRIPTION
            "The maximum number of events in the event FIFO."
        ::= { ethernetStatisticsEntry 12 }

    ethernetOutPackets OBJECT-TYPE
        SYNTAX Counter64
        MAX-ACCESS read-only
        STATUS current
        DESCRIPTION
            "The number of packets successfully transmitted through the
             network interface."
        ::= { ethernetStatisticsEntry 13 }

    ethernetInPackets OBJECT-TYPE
        SYNTAX Counter64
        MAX-ACCESS read-only
        STATUS current
        DESCRIPTION
            "The number of packets successfully received through the
             network interface."
        ::= { ethernetStatisticsEntry 14 }

    ethernetTotalPackets OBJECT-TYPE
        SYNTAX Counter64
        MAX-ACCESS read-only
        STATUS current
        DESCRIPTION
            "The total number of packets successfully transmitted and received
            through the network interface."
        ::= { ethernetStatisticsEntry 15 }

    ethernetOutBytes OBJECT-TYPE
        SYNTAX Counter64
        MAX-ACCESS read-only
        STATUS current
        DESCRIPTION
            "The number of bytes successfully transmitted through the
             network interface."
        ::= { ethernetStatisticsEntry 16 }

    ethernetInBytes OBJECT-TYPE
        SYNTAX Counter64
        MAX-ACCESS read-only
        STATUS current
        DESCRIPTION
            "The number of bytes successfully received through the
             network interface."
        ::= { ethernetStatisticsEntry 17 }

    ethernetTotalBytes OBJECT-TYPE
        SYNTAX Counter64
        MAX-ACCESS read-only
        STATUS current
        DESCRIPTION
            "The total number of bytes successfully transmitted and received
            through the network interface."
        ::= { ethernetStatisticsEntry 18 }

--------------------------------------------------------------------------------
--
-- Network / TCPIP Statistics
--
--------------------------------------------------------------------------------

    tcpOpenConns OBJECT-TYPE
        SYNTAX Counter32
        MAX-ACCESS read-only
        STATUS current
        DESCRIPTION
            "The number of currently open TCP/IP connections."
        ::= { tcpipStats 1 }

    tcpMaxOpenConns OBJECT-TYPE
        SYNTAX Counter32
        MAX-ACCESS read-only
        STATUS current
        DESCRIPTION
            "The maximum number of open TCP/IP connections."
        ::= { tcpipStats 2 }

    tcpTotalOpenConns OBJECT-TYPE
        SYNTAX Counter64
        MAX-ACCESS read-only
        STATUS current
        DESCRIPTION
            "The total number of TCP/IP connections ever opened (cumulative)."
        ::= { tcpipStats 3 }

    tcpFailedInConns OBJECT-TYPE
        SYNTAX Counter64
        MAX-ACCESS read-only
        STATUS current
        DESCRIPTION
            "The number of failed incoming TCP/IP connections."
        ::= { tcpipStats 4 }

    tcpFailedOutConns OBJECT-TYPE
        SYNTAX Counter64
        MAX-ACCESS read-only
        STATUS current
        DESCRIPTION
            "The number of failed outgoing TCP/IP connections."
        ::= { tcpipStats 5 }


    tcpOutSegments OBJECT-TYPE
        SYNTAX Counter64
        MAX-ACCESS read-only
        STATUS obsolete
        DESCRIPTION
            "The number of segments transmitted.

             This object is obsolete. It now forms part of the table
             tcpStatisticsTable."
        ::= { tcpipStats 6 }

    tcpInSegments OBJECT-TYPE
        SYNTAX Counter64
        MAX-ACCESS read-only
        STATUS obsolete
        DESCRIPTION
            "The number of segments received.

             This object is obsolete. It now forms part of the table
             tcpStatisticsTable."
        ::= { tcpipStats 7 }

    tcpReOutSegments OBJECT-TYPE
        SYNTAX Counter64
        MAX-ACCESS read-only
        STATUS obsolete
        DESCRIPTION
            "The number of retransmitted segments.

             This object is obsolete. It now forms part of the table
             tcpStatisticsTable."
        ::= { tcpipStats 8 }

    tcpInvSegments OBJECT-TYPE
        SYNTAX Counter64
        MAX-ACCESS read-only
        STATUS obsolete
        DESCRIPTION
            "The number of invalid segments.

             This object is obsolete. It now forms part of the table
             tcpStatisticsTable."
        ::= { tcpipStats 9 }

    tcpIPInPkts OBJECT-TYPE
        SYNTAX Counter64
        MAX-ACCESS read-only
        STATUS obsolete
        DESCRIPTION
            "The total number of IP packets received.

             This object is obsolete. It now forms part of the table
             tcpStatisticsTable."
        ::= { tcpipStats 10 }

    tcpIPOutPkts OBJECT-TYPE
        SYNTAX Counter64
        MAX-ACCESS read-only
        STATUS obsolete
        DESCRIPTION
            "The total number of IP packets transmitted.

             This object is obsolete. It now forms part of the table
             tcpStatisticsTable."
        ::= { tcpipStats 11 }

    tcpIPInInvPkts OBJECT-TYPE
        SYNTAX Counter64
        MAX-ACCESS read-only
        STATUS obsolete
        DESCRIPTION
            "The total number of invalid IP packets received.

             This object is obsolete. It now forms part of the table
             tcpStatisticsTable."
        ::= { tcpipStats 12 }

    tcpIPInInvHdrPkts OBJECT-TYPE
        SYNTAX Counter64
        MAX-ACCESS read-only
        STATUS obsolete
        DESCRIPTION
            "The total number of IP packets received with invalid
             header fields.

             This object is obsolete. It now forms part of the table
             tcpStatisticsTable."
        ::= { tcpipStats 13 }

    tcpIPInInvChksumPkts OBJECT-TYPE
        SYNTAX Counter64
        MAX-ACCESS read-only
        STATUS obsolete
        DESCRIPTION
            "The total number of IP packets received with invalid
             checksums.

             This object is obsolete. It now forms part of the table
             tcpStatisticsTable."
        ::= { tcpipStats 14 }

    tcpIPInInvNUcastAddrPkts OBJECT-TYPE
        SYNTAX Counter64
        MAX-ACCESS read-only
        STATUS obsolete
        DESCRIPTION
            "The total number of IP packets received with broadcast/multicast
             destination address errors.

             This object is obsolete. It now forms part of the table
             tcpStatisticsTable."
        ::= { tcpipStats 15 }

    tcpIPInInvUcastAddrPkts OBJECT-TYPE
        SYNTAX Counter64
        MAX-ACCESS read-only
        STATUS obsolete
        DESCRIPTION
            "The total number of IP packets received with unicast destination
             address errors.

             This object is obsolete. It now forms part of the table
             tcpStatisticsTable."
        ::= { tcpipStats 16 }

    tcpIPInInvSrcAddrPkts OBJECT-TYPE
        SYNTAX Counter64
        MAX-ACCESS read-only
        STATUS obsolete
        DESCRIPTION
            "The total number of IP packets received with source address
             errors.

             This object is obsolete. It now forms part of the table
             tcpStatisticsTable."
        ::= { tcpipStats 17 }

    tcpIPInInvOptionPkts OBJECT-TYPE
        SYNTAX Counter64
        MAX-ACCESS read-only
        STATUS obsolete
        DESCRIPTION
            "The total number of IP packets received with invalid
             options.

             This object is obsolete. It now forms part of the table
             tcpStatisticsTable."
        ::= { tcpipStats 18 }

    tcpInOversizeSegmentErrs OBJECT-TYPE
        SYNTAX Counter64
        MAX-ACCESS read-only
        STATUS obsolete
        DESCRIPTION
            "The total number of received segments which are oversized

             This object is obsolete. It now forms part of the table
             tcpStatisticsTable."
        ::= { tcpipStats 19 }

    tcpInInvChksumPkts OBJECT-TYPE
        SYNTAX Counter64
        MAX-ACCESS read-only
        STATUS obsolete
        DESCRIPTION
            "The total number of received TCP packets with invalid checksums.

             This object is obsolete. It now forms part of the table
             tcpStatisticsTable."
        ::= { tcpipStats 20 }

    tcpLinkPktDrops OBJECT-TYPE
        SYNTAX Counter64
        MAX-ACCESS read-only
        STATUS obsolete
        DESCRIPTION
            "The total number of packet dropped by the link layer.

             This object is obsolete. It now forms part of the table
             tcpStatisticsTable."
        ::= { tcpipStats 21 }

    tcpStatisticsTable OBJECT-TYPE
        SYNTAX SEQUENCE OF TcpStatisticsEntry
        MAX-ACCESS not-accessible
        STATUS current
        DESCRIPTION
            "A table of TCP statistics for ethernet interfaces.

             The number of entries in this table is given by the value of
             ifNumber."
        ::= { tcpipStats 22 }

    tcpStatisticsEntry OBJECT-TYPE
        SYNTAX TcpStatisticsEntry
        MAX-ACCESS not-accessible
        STATUS current
        DESCRIPTION
            "TCP statistics for ethernet interfaces."
        INDEX { ifIndex }
        ::= { tcpStatisticsTable 1 }

    TcpStatisticsEntry ::=
        SEQUENCE {
            tcpTxSegments
                Counter64,
            tcpRxSegments
                Counter64,
            tcpReTxSegments
                Counter64,
            tcpInvalidSegments
                Counter64,
            tcpIPTxPkts
                Counter64,
            tcpIPRxPkts
                Counter64,
            tcpIPRxInvalidPkts
                Counter64,
            tcpIPRxInvalidHdrPkts
                Counter64,
            tcpIPRxInvalidChksumPkts
                Counter64,
            tcpIPRxInvalidNUcastAddrPkts
                Counter64,
            tcpIPRxInvalidUcastAddrPkts
                Counter64,
            tcpIPRxInvalidSrcAddrPkts
                Counter64,
            tcpIPRxInvalidOptionPkts
                Counter64,
            tcpIPMiscBadSegments
                Counter64,
            tcpRxOversizeSegmentErrs
                Counter64,
            tcpRxInvalidChksumPkts
                Counter64,
            tcpLinkPacketDrops
                Counter64
        }
    
    tcpTxSegments OBJECT-TYPE
        SYNTAX Counter64
        MAX-ACCESS read-only
        STATUS current
        DESCRIPTION
            "The number of segments transmitted."
        ::= { tcpStatisticsEntry 1 }

    tcpRxSegments OBJECT-TYPE
        SYNTAX Counter64
        MAX-ACCESS read-only
        STATUS current
        DESCRIPTION
            "The number of segments received."
        ::= { tcpStatisticsEntry 2 }

    tcpReTxSegments OBJECT-TYPE
        SYNTAX Counter64
        MAX-ACCESS read-only
        STATUS current
        DESCRIPTION
            "The number of retransmitted segments."
        ::= { tcpStatisticsEntry 3 }

    tcpInvalidSegments OBJECT-TYPE
        SYNTAX Counter64
        MAX-ACCESS read-only
        STATUS current
        DESCRIPTION
            "The number of invalid segments."
        ::= { tcpStatisticsEntry 4 }

    tcpIPTxPkts OBJECT-TYPE
        SYNTAX Counter64
        MAX-ACCESS read-only
        STATUS current
        DESCRIPTION
            "The total number of IP packets transmitted."
        ::= { tcpStatisticsEntry 5 }

    tcpIPRxPkts OBJECT-TYPE
        SYNTAX Counter64
        MAX-ACCESS read-only
        STATUS current
        DESCRIPTION
            "The total number of invalid IP packets received."
        ::= { tcpStatisticsEntry 6 }

    tcpIPRxInvalidPkts OBJECT-TYPE
        SYNTAX Counter64
        MAX-ACCESS read-only
        STATUS current
        DESCRIPTION
            "The total number of invalid IP packets received."
        ::= { tcpStatisticsEntry 7 }

    tcpIPRxInvalidHdrPkts OBJECT-TYPE
        SYNTAX Counter64
        MAX-ACCESS read-only
        STATUS current
        DESCRIPTION
            "The total number of IP packets received with invalid
             header fields."
        ::= { tcpStatisticsEntry 8 }

    tcpIPRxInvalidChksumPkts OBJECT-TYPE
        SYNTAX Counter64
        MAX-ACCESS read-only
        STATUS obsolete
        DESCRIPTION
            "The total number of IP packets received with invalid
             checksums.

            This object has been obsolete. It is now
            included in the object tcpIPMiscBadSegements."
        ::= { tcpStatisticsEntry 9 }

    tcpIPRxInvalidNUcastAddrPkts OBJECT-TYPE
        SYNTAX Counter64
        MAX-ACCESS read-only
        STATUS obsolete
        DESCRIPTION
            "The total number of IP packets received with broadcast/multicast
             destination address errors.

            This object has been obsolete. It is now
            included in the object tcpIPMiscBadSegements."
        ::= { tcpStatisticsEntry 10 }

    tcpIPRxInvalidUcastAddrPkts OBJECT-TYPE
        SYNTAX Counter64
        MAX-ACCESS read-only
        STATUS obsolete
        DESCRIPTION
            "The total number of IP packets received with unicast destination
             address errors.

            This object has been obsolete. It is now
            included in the object tcpIPMiscBadSegements."
        ::= { tcpStatisticsEntry 11 }

    tcpIPRxInvalidSrcAddrPkts OBJECT-TYPE
        SYNTAX Counter64
        MAX-ACCESS read-only
        STATUS current
        DESCRIPTION
            "The total number of IP packets received with source address
             errors."
        ::= { tcpStatisticsEntry 12 }

    tcpIPRxInvalidOptionPkts OBJECT-TYPE
        SYNTAX Counter64
        MAX-ACCESS read-only
        STATUS obsolete
        DESCRIPTION
            "The total number of IP packets received with invalid
             options.

            This object has been obsolete. It is now
            included in the object tcpIPMiscBadSegements."
        ::= { tcpStatisticsEntry 13 }

    tcpIPMiscBadSegments OBJECT-TYPE
        SYNTAX Counter64
        MAX-ACCESS read-only
        STATUS current
        DESCRIPTION
            "The total number of invalid IP packets received. The
            faults include invalid checksum, unicast and non-unicast
            address, and option."
        ::= { tcpStatisticsEntry 14 }

    tcpRxOversizeSegmentErrs OBJECT-TYPE
        SYNTAX Counter64
        MAX-ACCESS read-only
        STATUS obsolete
        DESCRIPTION
            "The total number of received segments which are oversized.

            This object has been obsolete. It is now
            included in the object tcpRxInvalidSegments."
        ::= { tcpStatisticsEntry 15 }

    tcpRxInvalidChksumPkts OBJECT-TYPE
        SYNTAX Counter64
        MAX-ACCESS read-only
        STATUS current
        DESCRIPTION
            "The total number of received segments which are oversized."
        ::= { tcpStatisticsEntry 16 }

    tcpLinkPacketDrops OBJECT-TYPE
        SYNTAX Counter64
        MAX-ACCESS read-only
        STATUS obsolete
        DESCRIPTION
            "The total number of packet dropped by the link layer.

            This object has been obsolete. It is now
            included in the object tcpRxInvalidSegments."
        ::= { tcpStatisticsEntry 17 }

--------------------------------------------------------------------------------
--
-- Network / UDP Statistics
--
--------------------------------------------------------------------------------

    udpInShortPkts OBJECT-TYPE
        SYNTAX Counter64
        MAX-ACCESS read-only
        STATUS obsolete
        DESCRIPTION
            "The total number of short UDP packets received.

             This object is obsolete. It now forms part of the table
             udpStatisticsTable."
        ::= { udpStats 1 }

    udpInInvChksumPkts OBJECT-TYPE
        SYNTAX Counter64
        MAX-ACCESS read-only
        STATUS obsolete
        DESCRIPTION
            "The total number of UDP packets received with invalid
             checksums.

             This object is obsolete. It now forms part of the table
             udpStatisticsTable."
        ::= { udpStats 2 }
        
    udpStatisticsTable OBJECT-TYPE
        SYNTAX SEQUENCE OF UdpStatisticsEntry
        MAX-ACCESS not-accessible
        STATUS current
        DESCRIPTION
            "A table of UDP statistics for ethernet interfaces.

             The number of entries in this table is given by the value of
             ifNumber."
        ::= { udpStats 3 }

    udpStatisticsEntry OBJECT-TYPE
        SYNTAX UdpStatisticsEntry
        MAX-ACCESS not-accessible
        STATUS current
        DESCRIPTION
            "UDP statistics for ethernet interfaces."
        INDEX { ifIndex }
        ::= { udpStatisticsTable 1 }

    UdpStatisticsEntry ::=
        SEQUENCE {
            udpRxShortPkts
                Counter64,
            udpRxInvChksumPkts
                Counter64
        }

    udpRxShortPkts OBJECT-TYPE
        SYNTAX Counter64
        MAX-ACCESS read-only
        STATUS current
        DESCRIPTION
            "The total number of short UDP packets received."
        ::= { udpStatisticsEntry 1 }

    udpRxInvChksumPkts OBJECT-TYPE
        SYNTAX Counter64
        MAX-ACCESS read-only
        STATUS current
        DESCRIPTION
            "The total number of UDP packets received with invalid
             checksums."
        ::= { udpStatisticsEntry 2 }

--------------------------------------------------------------------------------
--
-- Network / Advanced IP Configuration
--
--------------------------------------------------------------------------------

    tcpArpCacheTimeout OBJECT-TYPE
        SYNTAX Unsigned32
        MAX-ACCESS read-only
        STATUS current
        DESCRIPTION
            "The ARP cache timeout in seconds."
        ::= { advipConfig 1 }

    tcpBroadCastUsingZero OBJECT-TYPE
        SYNTAX INTEGER {
            enabled(1),
            disabled(2),
            unknown(3)
        }
        MAX-ACCESS read-only
        STATUS current
        DESCRIPTION
            "Broadcast using IP address 0.
             
             enabled(1)  - broadcast using IP address 0.
             disabled(2) - DONT broadcast using IP address 0."
        ::= { advipConfig 2 }

    tcpIgnoreICMPEcho OBJECT-TYPE
        SYNTAX INTEGER {
            enabled(1),
            disabled(2),
            unknown(3)
        }
        MAX-ACCESS read-only
        STATUS current
        DESCRIPTION
            "Ignore ICMP echo requests.

             enabled(1)  - ignore ICMP echo requests.
             disabled(2) - DONT ignore ICMP echo requests."
        ::= { advipConfig 3 }

    tcpOffSubnetMTU OBJECT-TYPE
        SYNTAX INTEGER
        MAX-ACCESS read-only
        STATUS current
        DESCRIPTION
            "The IP MTU for off-subnet transmits in bytes."
        ::= { advipConfig 4 }

    tcpAllSubnetsMTU OBJECT-TYPE
        SYNTAX INTEGER {
            enabled(1),
            disabled(2),
            unknown(3)
        }
        MAX-ACCESS read-only
        STATUS current
        DESCRIPTION
            "Use the same IP MTU (1500 bytes) for all subnets of the
             connected network.

             enabled(1)  - use the same MTU for all subnets.
             disabled(2) - DONT use the same MTU for all subnets."
        ::= { advipConfig 5 }

    tcpKeepAlive OBJECT-TYPE
        SYNTAX INTEGER {
            enabled(1),
            disabled(2),
            unknown(3)
        }
        MAX-ACCESS read-only
        STATUS current
        DESCRIPTION
            "TCP keep alive option.

             enabled(1)  - use TCP keep alive.
             disabled(2) - DONT use TCP keep alive."
        ::= { advipConfig 6 }

    tcpKeepAliveTimeout OBJECT-TYPE
        SYNTAX Unsigned32
        MAX-ACCESS read-only
        STATUS current
        DESCRIPTION
            "The TCP keep alive timeout in seconds."
        ::= { advipConfig 7 }

--------------------------------------------------------------------------------
--
-- Network / Engineers IP Configuration
--
--------------------------------------------------------------------------------

    tcpDefWnd OBJECT-TYPE
        SYNTAX Unsigned32
        MAX-ACCESS read-only
        STATUS current
        DESCRIPTION
            "Default window size in bytes."
        ::= { engipConfig 1 }

    tcpDelayedAcks OBJECT-TYPE
        SYNTAX INTEGER {
            enabled(1),
            disabled(2),
            unknown(3)
        }
        MAX-ACCESS read-only
        STATUS current
        DESCRIPTION
            "Indicates whether the delayed ack setting is enabled or not."
        ::= { engipConfig 2 }

    tcpSlowStartCA OBJECT-TYPE
        SYNTAX INTEGER {
            enabled(1),
            disabled(2),
            unknown(3)
        }
        MAX-ACCESS read-only
        STATUS current
        DESCRIPTION
            "Indicates whether the slow start ca setting is enabled or not."
        ::= { engipConfig 3 }

    tcpSSRestartDoubleMSS OBJECT-TYPE
        SYNTAX INTEGER {
            enabled(1),
            disabled(2),
            unknown(3)
        }
        MAX-ACCESS read-only
        STATUS current
        DESCRIPTION
            "Indicates whether the SS restart double mss setting is enabled 
             or not."
        ::= { engipConfig 4 }

    tcpNagle OBJECT-TYPE
        SYNTAX INTEGER {
            enabled(1),
            disabled(2),
            unknown(3)
        }
        MAX-ACCESS read-only
        STATUS current
        DESCRIPTION
            "Indicates whether the nagle setting is enabled or not."
        ::= { engipConfig 5 }

    tcpSillyWindowAvoid OBJECT-TYPE
        SYNTAX INTEGER {
            enabled(1),
            disabled(2),
            unknown(3)
        }
        MAX-ACCESS read-only
        STATUS current
        DESCRIPTION
            "Indicates whether the silly window avoid setting is enabled 
             or not."
        ::= { engipConfig 6 }

    tcpOldAckStrategy OBJECT-TYPE
        SYNTAX INTEGER {
            enabled(1),
            disabled(2),
            unknown(3)
        }
        MAX-ACCESS read-only
        STATUS current
        DESCRIPTION
            "Indicates whether the old ack strategy setting is enabled 
             or not."
        ::= { engipConfig 7 }

    tcpSlowStartOnIdle OBJECT-TYPE
        SYNTAX INTEGER {
            enabled(1),
            disabled(2),
            unknown(3)
        }
        MAX-ACCESS read-only
        STATUS current
        DESCRIPTION
            "Indicates whether the slow start on idle setting is enabled
             or not."
        ::= { engipConfig 8 }

    tcpFastRetxFastRecovery OBJECT-TYPE
        SYNTAX INTEGER {
            enabled(1),
            disabled(2),
            unknown(3)
        }
        MAX-ACCESS read-only
        STATUS current
        DESCRIPTION
            "Indicates whether the fast retx fast recovery setting is enabled
             or not."
        ::= { engipConfig 9 }

    tcpOldPushStrategy OBJECT-TYPE
        SYNTAX INTEGER {
            enabled(1),
            disabled(2),
            unknown(3)
        }
        MAX-ACCESS read-only
        STATUS current
        DESCRIPTION
            "Indicates whether the old push strategy setting is enabled or not."
        ::= { engipConfig 10 }

    tcpOffSubnetSlowStart OBJECT-TYPE
        SYNTAX INTEGER {
            enabled(1),
            disabled(2),
            unknown(3)
        }
        MAX-ACCESS read-only
        STATUS current
        DESCRIPTION
            "Indicates whether the off subnet slow start setting is enabled 
             or not."
        ::= { engipConfig 11 }

    tcpUDPCheckSumGen OBJECT-TYPE
        SYNTAX INTEGER {
            enabled(1),
            disabled(2),
            unknown(3)
        }
        MAX-ACCESS read-only
        STATUS current
        DESCRIPTION
            "Indicates whether the UDP checksum generation setting is enabled
             or not."
        ::= { engipConfig 12 }

    tcpIntelliSeg OBJECT-TYPE
        SYNTAX INTEGER {
            enabled(1),
            disabled(2),
            unknown(3)
        }
        MAX-ACCESS read-only
        STATUS current
        DESCRIPTION
            "Indicates whether the intelliseg setting is enabled or not."
        ::= { engipConfig 13 }

--------------------------------------------------------------------------------
--
-- Network / Name Service / WINS
--
--------------------------------------------------------------------------------

    winsPrimaryIpAddr OBJECT-TYPE
        SYNTAX IpAddress
        MAX-ACCESS read-only
        STATUS current
        DESCRIPTION
            "The IP address of the primary wins server if enabled or 
             0.0.0.0 if not enabled."
        ::= { wins 1 }

    winsSecondaryIpAddr OBJECT-TYPE
        SYNTAX IpAddress
        MAX-ACCESS read-only
        STATUS current
        DESCRIPTION
            "The IP address of the secondary wins server if enabled or 
             0.0.0.0 if not enabled."
        ::= { wins 2 }

--------------------------------------------------------------------------------
--
-- Network / Name Service / DNS
--
--------------------------------------------------------------------------------

    dnsServerNumber OBJECT-TYPE
        SYNTAX Integer32
        MAX-ACCESS read-only
        STATUS current
        DESCRIPTION
            "The number of configured DNS servers."
        ::= { dns 1 }

    dnsServerTable OBJECT-TYPE
        SYNTAX SEQUENCE OF DnsServerEntry
        MAX-ACCESS not-accessible
        STATUS current
        DESCRIPTION
            "A table containing the IP addresses of each of the
             servers which have been configured as DNS servers
             for this system.

             The number of entries in this table is given by the value of 
             dnsServerNumber."
        ::= { dns 2 }

    dnsServerEntry OBJECT-TYPE
        SYNTAX DnsServerEntry
        MAX-ACCESS not-accessible
        STATUS current
        DESCRIPTION
            "Information about the configured DNS server."
        INDEX { dnsServerIndex }
        ::= { dnsServerTable 1 }

    DnsServerEntry ::=
        SEQUENCE {
            dnsServerIndex
                Integer32,
            dnsServerIpAddress
                IpAddress
        }

    dnsServerIndex OBJECT-TYPE
        SYNTAX Integer32 (1..10)
        MAX-ACCESS read-only
        STATUS current
        DESCRIPTION
            "A unique value for each configured DNS server.
             This value defines the DNS search ordering.

             Its value ranges between 1 and the value of dnsServerNumber."
        ::= { dnsServerEntry 1 }

    dnsServerIpAddress OBJECT-TYPE
        SYNTAX IpAddress
        MAX-ACCESS read-only
        STATUS current
        DESCRIPTION
            "The IP address of the DNS server."
        ::= { dnsServerEntry 2 }

    dnsSearchNumber OBJECT-TYPE
        SYNTAX Integer32
        MAX-ACCESS read-only
        STATUS current
        DESCRIPTION
            "The number of DNS search list entries which are configured 
             for the system."
        ::= { dns 3 }

    dnsSearchTable OBJECT-TYPE
        SYNTAX SEQUENCE OF DnsSearchEntry
        MAX-ACCESS not-accessible
        STATUS current
        DESCRIPTION
            "A table containing the DNS search list which is a list of
             domain suffices.

             The number of entries in this table is given by the value of 
             dnsSearchNumber."
        ::= { dns 4 }

    dnsSearchEntry OBJECT-TYPE
        SYNTAX DnsSearchEntry
        MAX-ACCESS not-accessible
        STATUS current
        DESCRIPTION
            "DNS search information."
        INDEX { dnsSearchIndex }
        ::= { dnsSearchTable 1 }

    DnsSearchEntry ::=
        SEQUENCE {
            dnsSearchIndex
                Integer32,
            dnsSearchString
                DisplayString
        }

    dnsSearchIndex OBJECT-TYPE
        SYNTAX Integer32 (1..10)
        MAX-ACCESS read-only
        STATUS current
        DESCRIPTION
            "A unique value for each configured DNS search string.
             This value defines the DNS search ordering.

             Its value ranges between 1 and the value of dnsSearchNumber."
        ::= { dnsSearchEntry 1 }

    dnsSearchString OBJECT-TYPE
        SYNTAX DisplayString
        MAX-ACCESS read-only
        STATUS current
        DESCRIPTION
            "The DNS search string."
        ::= { dnsSearchEntry 2 }

--------------------------------------------------------------------------------
--
-- Network / Name Service / Name Service Ordering
--
--------------------------------------------------------------------------------

    nameServiceNumber OBJECT-TYPE
        SYNTAX Integer32
        MAX-ACCESS read-only
        STATUS current
        DESCRIPTION
            "The number of name services configured to be used for hostname
             lookups."
        ::= { nsOrder 1 }

    nameServiceTable OBJECT-TYPE
        SYNTAX SEQUENCE OF NameServiceEntry
        MAX-ACCESS not-accessible
        STATUS current
        DESCRIPTION
            "A table containing the name services which have been
             configured for hostname lookups.

             The number of entries in this table is given by the value of 
             nameServiceNumber."
        ::= { nsOrder 2 }

    nameServiceEntry OBJECT-TYPE
        SYNTAX NameServiceEntry
        MAX-ACCESS not-accessible
        STATUS current
        DESCRIPTION
            "Information about the name service."
        INDEX { nameServiceOrder }
        ::= { nameServiceTable 1 }

    NameServiceEntry ::=
        SEQUENCE {
            nameServiceOrder
                Integer32,
            nameServiceType
                INTEGER
        }

    nameServiceOrder OBJECT-TYPE
        SYNTAX Integer32 (1..4)
        MAX-ACCESS read-only
        STATUS current
        DESCRIPTION
            "The order in which the lookup is made.

             Its value ranges between 1 and the value of nameServiceNumber."
        ::= { nameServiceEntry 1 }

    nameServiceType OBJECT-TYPE
        SYNTAX INTEGER {
            dns(1),
            wins(2),
            nis(3),
            unknown(4)
        }
        MAX-ACCESS read-only
        STATUS current
        DESCRIPTION
            "Indicates the configured service type.

             dns(1)  - domain name service.
             wins(2) - the windows service.
             nis(3)  - network information service."
        ::= { nameServiceEntry 2 }

--------------------------------------------------------------------------------
--
-- Network / NIS
--
--------------------------------------------------------------------------------

    nisEnabled OBJECT-TYPE
        SYNTAX INTEGER {
            enabled(1),
            disabled(2),
            unknown(3)
        }
        MAX-ACCESS read-only
        STATUS current
        DESCRIPTION
            "Indicates whether NIS is enabled on this system or not."
        ::= { nis 1 }

    nisDomain OBJECT-TYPE
        SYNTAX DisplayString
        MAX-ACCESS read-only
        STATUS current
        DESCRIPTION
            "The NIS domain name."
        ::= { nis 2 }

    nisCurrentMaster OBJECT-TYPE
        SYNTAX DisplayString
        MAX-ACCESS read-only
        STATUS current
        DESCRIPTION
            "The current NIS master host address."
        ::= { nis 3 }

    nisServerBroadcastEnabled OBJECT-TYPE
        SYNTAX INTEGER {
            enabled(1),
            disabled(2),
            unknown(3)
        }
        MAX-ACCESS read-only
        STATUS current
        DESCRIPTION
            "Indicates whether NIS should broadcast for NIS servers 
             on the local network instead of using the configured list
             of servers."
        ::= { nis 4 }

    nisVerificationEnabled OBJECT-TYPE
        SYNTAX INTEGER {
            enabled(1),
            disabled(2),
            unknown(3)
        }
        MAX-ACCESS read-only
        STATUS current
        DESCRIPTION
            "Indicates whether NIS verification is enabled or not."
        ::= { nis 5 }

    nisTimeout OBJECT-TYPE
        SYNTAX Unsigned32
        MAX-ACCESS read-only
        STATUS current
        DESCRIPTION
            "NIS timeout value in milliseconds."
        ::= { nis 6 }

    nisRebindInterval OBJECT-TYPE
        SYNTAX Unsigned32
        MAX-ACCESS read-only
        STATUS current
        DESCRIPTION
            "NIS rebind in minutes."
        ::= { nis 7 }

    nisUserGroupTimeout OBJECT-TYPE
        SYNTAX Unsigned32
        MAX-ACCESS read-only
        STATUS current
        DESCRIPTION
            "NIS user/group/netgroup timeout value in minutes."
        ::= { nis 8 }

    nisServerNumber OBJECT-TYPE
        SYNTAX Integer32
        MAX-ACCESS read-only
        STATUS current
        DESCRIPTION
            "The number of NIS servers which have been configured.

            A value of -1 indicates this information could not
            be determined."
        ::= { nis 9 }

    nisServerTable OBJECT-TYPE
        SYNTAX SEQUENCE OF NisServerEntry
        MAX-ACCESS not-accessible
        STATUS current
        DESCRIPTION
            "A table containing information about each NIS server.

             The number of entries in this table is given by the value of 
             nisServerNumber."
        ::= { nis 10 }

    nisServerEntry OBJECT-TYPE
        SYNTAX NisServerEntry
        MAX-ACCESS not-accessible
        STATUS current
        DESCRIPTION
            "Information about each configured NIS server."
        INDEX { nisServerIndex }
        ::= { nisServerTable 1 }

    NisServerEntry ::=
        SEQUENCE {
            nisServerIndex
                Integer32,
            nisServerIpAddress
                IpAddress,
            nisServerPriority
                Integer32
        }

    nisServerIndex OBJECT-TYPE
        SYNTAX Integer32 (1..50)
        MAX-ACCESS read-only
        STATUS current
        DESCRIPTION
            "A unique value for each configured NIS server.

             Its value ranges between 1 and the value of nisServerNumber."
        ::= { nisServerEntry 1 }

    nisServerIpAddress OBJECT-TYPE
        SYNTAX IpAddress
        MAX-ACCESS read-only
        STATUS current
        DESCRIPTION
            "The IP address of the NIS server."
        ::= { nisServerEntry 2 }

    nisServerPriority OBJECT-TYPE
        SYNTAX Integer32
        MAX-ACCESS read-only
        STATUS current
        DESCRIPTION
            "The priority assigned to the NIS server.

            A value of -1 indicates this information could not
            be determined."
        ::= { nisServerEntry 3 }
    
--------------------------------------------------------------------------------
--
-- File Protocol / Security
--
--------------------------------------------------------------------------------

    securityMode OBJECT-TYPE
        SYNTAX INTEGER {
            mixed(1),
            unix(2),
            nosecurity(3),
            unknown(4)
        }
        MAX-ACCESS read-only
        STATUS current
        DESCRIPTION
            "Indicates the configured security model.

             mixed(1)      - Windows or UNIX environments.
             unix(2)       - primarily UNIX environments.
             nosecurity(3) - all requests granted."
        ::= { security 1 }

    securityDomain OBJECT-TYPE
        SYNTAX DisplayString
        MAX-ACCESS read-only
        STATUS current
        DESCRIPTION
            "The servers configured domain name."
        ::= { security 2 }

--------------------------------------------------------------------------------
--
-- File Protocol / CIFS / Shares
--
--------------------------------------------------------------------------------

    shareNumber OBJECT-TYPE
        SYNTAX Integer32
        MAX-ACCESS read-only
        STATUS current
        DESCRIPTION
            "The number of CIFS shares which are configured for the system."
        ::= { shares 1 }

    shareTable OBJECT-TYPE
        SYNTAX SEQUENCE OF ShareEntry
        MAX-ACCESS not-accessible
        STATUS obsolete
        DESCRIPTION
            "A table containing the CIFS share configuration for the
             system.

             The number of entries in this table is given by the value of
             shareNumber."
        ::= { shares 2 }

    shareEntry OBJECT-TYPE
        SYNTAX ShareEntry
        MAX-ACCESS not-accessible
        STATUS obsolete
        DESCRIPTION
            "CIFS share information."
        INDEX { shareName }
        ::= { shareTable 1 }

    ShareEntry ::=
        SEQUENCE {
            shareName
                DisplayString,
            sharePath
                DisplayString,
            shareComment
                DisplayString,
            shareUsers
                Unsigned32,
            shareWWN
                DisplayString,
            shareLUN
                Unsigned32,
            sharePartitionID
                Unsigned32,
            shareMaxUsers
                Integer32
        }

    shareName OBJECT-TYPE
        SYNTAX DisplayString
        MAX-ACCESS read-only
        STATUS obsolete
        DESCRIPTION
            "The name of the CIFS share.  Each share has a unique name."
        ::= { shareEntry 1 }

    sharePath OBJECT-TYPE
        SYNTAX DisplayString
        MAX-ACCESS read-only
        STATUS obsolete
        DESCRIPTION
            "The path to the CIFS share."
        ::= { shareEntry 2 }

    shareComment OBJECT-TYPE
        SYNTAX DisplayString
        MAX-ACCESS read-only
        STATUS obsolete
        DESCRIPTION
            "An optional comment assigned by the creator of the 
             CIFS share to assist in identifying it.
             NOTE: This will be a zero length string if the creator has
                   not assigned a comment to it."
        ::= { shareEntry 3 }

    shareUsers OBJECT-TYPE
        SYNTAX Unsigned32
        MAX-ACCESS read-only
        STATUS obsolete
        DESCRIPTION
            "The number of users currently accessing the CIFS share."
        ::= { shareEntry 4 }

    shareWWN OBJECT-TYPE
        SYNTAX DisplayString
        MAX-ACCESS read-only
        STATUS obsolete
        DESCRIPTION
            "The world wide name (WWN) of the system drive the CIFS
             share is associated with.
             
             This will identify the File System
             on which the volume associated with the share is hosted."
        ::= { shareEntry 5 }

    shareLUN OBJECT-TYPE
        SYNTAX Unsigned32
        MAX-ACCESS read-only
        STATUS obsolete
        DESCRIPTION
            "The logical unit number (LUN) of the system drive the
             CIFS share is associated with.

             This now has no meaning and is set to zero."
        ::= { shareEntry 6 }

    sharePartitionID OBJECT-TYPE
        SYNTAX Unsigned32
        MAX-ACCESS read-only
        STATUS obsolete
        DESCRIPTION
            "The partition ID of the volume the CIFS share is associated
             with.

             This now has no meaning and is set to zero."
        ::= { shareEntry 7 }

    shareMaxUsers OBJECT-TYPE
        SYNTAX Integer32
        MAX-ACCESS read-only
        STATUS obsolete
        DESCRIPTION
            "The maximum number of users which are permitted access to 
             the CIFS share simultaneously.
             NOTE: this value is set to -1 if the number of maximum
                   number of simultaneous users is unlimited."
        ::= { shareEntry 8 }

    cifsShareTable OBJECT-TYPE
        SYNTAX SEQUENCE OF CifsShareEntry
        MAX-ACCESS not-accessible
        STATUS current
        DESCRIPTION
            "A table containing the CIFS share configuration for the
             system.

             The number of entries in this table is given by the value of
             shareNumber."
        ::= { shares 3 }

    cifsShareEntry OBJECT-TYPE
        SYNTAX CifsShareEntry
        MAX-ACCESS not-accessible
        STATUS current
        DESCRIPTION
            "CIFS share information."
        INDEX { cifsShareEvsId, cifsShareName }
        ::= { cifsShareTable 1 }

    CifsShareEntry ::=
        SEQUENCE {
            cifsShareEvsId
                Integer32,
            cifsShareName
                DisplayString,
            cifsSharePath
                DisplayString,
            cifsShareComment
                DisplayString,
            cifsShareUsers
                Unsigned32,
            cifsShareMaxUsers
                Integer32,
            cifsShareSpanId
                Integer32
        }

    cifsShareEvsId OBJECT-TYPE
        SYNTAX Integer32 (1..255)
        MAX-ACCESS read-only
        STATUS current
        DESCRIPTION
            "The ID of the Enterprise Virtual Server to which this
            share belongs."
        ::= { cifsShareEntry 1 }

    cifsShareName OBJECT-TYPE
        SYNTAX DisplayString
        MAX-ACCESS read-only
        STATUS current
        DESCRIPTION
            "The name of the CIFS share.  Each share has a name unique 
            to the EVS to which it belongs."
        ::= { cifsShareEntry 2 }

    cifsSharePath OBJECT-TYPE
        SYNTAX DisplayString
        MAX-ACCESS read-only
        STATUS current
        DESCRIPTION
            "The path to the CIFS share."
        ::= { cifsShareEntry 3 }

    cifsShareComment OBJECT-TYPE
        SYNTAX DisplayString
        MAX-ACCESS read-only
        STATUS current
        DESCRIPTION
            "An optional comment assigned by the creator of the
             CIFS share to assist in identifying it.
             NOTE: This will be a zero length string if the creator has
                   not assigned a comment to it."
        ::= { cifsShareEntry 4 }

    cifsShareUsers OBJECT-TYPE
        SYNTAX Unsigned32
        MAX-ACCESS read-only
        STATUS current
        DESCRIPTION
            "The number of users currently accessing the CIFS share."
        ::= { cifsShareEntry 5 }

    cifsShareMaxUsers OBJECT-TYPE
        SYNTAX Integer32
        MAX-ACCESS read-only
        STATUS current
        DESCRIPTION
            "The maximum number of users which are permitted access to
             the CIFS share simultaneously.
             NOTE: this value is set to -1 if the maximum
                   number of simultaneous users is unlimited."
        ::= { cifsShareEntry 6 }

    cifsShareSpanId OBJECT-TYPE
        SYNTAX Integer32
        MAX-ACCESS read-only
        STATUS current
        DESCRIPTION
            "The ID of the volume the CIFS share is associated
             with."
        ::= { cifsShareEntry 7 }

--------------------------------------------------------------------------------
--
-- File Protocol / CIFS / Share Access
--
--------------------------------------------------------------------------------

    shareAccessNumber OBJECT-TYPE
        SYNTAX Integer32
        MAX-ACCESS read-only
        STATUS current
        DESCRIPTION
            "The number of CIFS share access entries which are 
             configured for the system."
        ::= { shareAccess 1 }

    shareAccessTable OBJECT-TYPE
        SYNTAX SEQUENCE OF ShareAccessEntry
        MAX-ACCESS not-accessible
        STATUS current
        DESCRIPTION
            "A table containing the CIFS share access configuration 
             for the system.

             The number of entries in this table is given by the value of 
             shareAccessNumber."
        ::= { shareAccess 2 }

    shareAccessEntry OBJECT-TYPE
        SYNTAX ShareAccessEntry
        MAX-ACCESS not-accessible
        STATUS current
        DESCRIPTION
            "CIFS share access information."
        INDEX { shareAccessIndex, shareAccessShareName }
        ::= { shareAccessTable 1 }

    ShareAccessEntry ::=
        SEQUENCE {
            shareAccessIndex
                Integer32,
            shareAccessShareName
                DisplayString,
            shareAccessName
                DisplayString,
            shareAccessPerms
                INTEGER
        }

    shareAccessIndex OBJECT-TYPE
        SYNTAX Integer32 (1..200)
        MAX-ACCESS read-only
        STATUS current
        DESCRIPTION
            "An index for each access entry which exists for a
             CIFS share.

             For Si7000 and Si8000 families of SiServers, this 
             value ranges between 1 and the number of access
             entries which exist for the share.
             
             The value is the ID of the EVS of the CIFS share for the 
             access configuration."
        ::= { shareAccessEntry 1 }

    shareAccessShareName OBJECT-TYPE
        SYNTAX DisplayString
        MAX-ACCESS read-only
        STATUS current
        DESCRIPTION
            "The name of the CIFS share that the access configuration
             entry exists for."
        ::= { shareAccessEntry 2 }

    shareAccessName OBJECT-TYPE
        SYNTAX DisplayString
        MAX-ACCESS read-only
        STATUS current
        DESCRIPTION
            "The name of the user or group which has been granted access."
        ::= { shareAccessEntry 3 }

    shareAccessPerms OBJECT-TYPE
        SYNTAX INTEGER {
            noAccess(1),
            read(2),
            change(3),
            fullControl(4)
        }
        MAX-ACCESS read-only
        STATUS current
        DESCRIPTION
            "The access permissions the user or group has been granted to 
             the CIFS share."
        ::= { shareAccessEntry 4 }

--------------------------------------------------------------------------------
--
-- File Protocol / CIFS / Statistics
--
--------------------------------------------------------------------------------

    cifsClients OBJECT-TYPE
        SYNTAX Unsigned32
        MAX-ACCESS read-only
        STATUS obsolete
        DESCRIPTION
            "The total number of CIFS clients since power up."
        ::= { cifsStats 1 }

    cifsMkdirCalls OBJECT-TYPE
        SYNTAX Unsigned32
        MAX-ACCESS read-only
        STATUS obsolete
        DESCRIPTION
            "The total number of 'Mkdir' CIFS calls received since
             power up."
        ::= { cifsStats 2 }

    cifsRmdirCalls OBJECT-TYPE
        SYNTAX Unsigned32
        MAX-ACCESS read-only
        STATUS obsolete
        DESCRIPTION
            "The total number of 'Rmdir' CIFS calls received since 
             power up."
        ::= { cifsStats 3 }

    cifsOpenCalls OBJECT-TYPE
        SYNTAX Unsigned32
        MAX-ACCESS read-only
        STATUS obsolete
        DESCRIPTION
            "The total number of 'Open' CIFS calls received since 
             power up."
        ::= { cifsStats 4 }

    cifsCreateCalls OBJECT-TYPE
        SYNTAX Unsigned32
        MAX-ACCESS read-only
        STATUS obsolete
        DESCRIPTION
            "The total number of 'Create' CIFS calls received since 
             power up."
        ::= { cifsStats 5 }

    cifsCloseCalls OBJECT-TYPE
        SYNTAX Unsigned32
        MAX-ACCESS read-only
        STATUS obsolete
        DESCRIPTION
            "The total number of 'Close' CIFS calls received since
             power up."
        ::= { cifsStats 6 }

    cifsFlushCalls OBJECT-TYPE
        SYNTAX Unsigned32
        MAX-ACCESS read-only
        STATUS obsolete
        DESCRIPTION
            "The total number of 'Flush' CIFS calls received since 
             power up."
        ::= { cifsStats 7 }

    cifsUnlinkCalls OBJECT-TYPE
        SYNTAX Unsigned32
        MAX-ACCESS read-only
        STATUS obsolete
        DESCRIPTION
            "The total number of 'Unlink' CIFS calls received since 
             power up."
        ::= { cifsStats 8 }

    cifsRenameCalls OBJECT-TYPE
        SYNTAX Unsigned32
        MAX-ACCESS read-only
        STATUS obsolete
        DESCRIPTION
            "The total number of 'Rename' CIFS calls received since 
             power up."
        ::= { cifsStats 9 }

    cifsGetatrCalls OBJECT-TYPE
        SYNTAX Unsigned32
        MAX-ACCESS read-only
        STATUS obsolete
        DESCRIPTION
            "The total number of 'Getatr' CIFS calls received since 
             power up."
        ::= { cifsStats 10 }

    cifsSetatrCalls OBJECT-TYPE
        SYNTAX Unsigned32
        MAX-ACCESS read-only
        STATUS obsolete
        DESCRIPTION
            "The total number of 'Setatr' CIFS calls received since 
             power up."
        ::= { cifsStats 11 }

    cifsReadCalls OBJECT-TYPE
        SYNTAX Unsigned32
        MAX-ACCESS read-only
        STATUS obsolete
        DESCRIPTION
            "The total number of 'Read' CIFS calls received since 
             power up."
        ::= { cifsStats 12 }

    cifsWriteCalls OBJECT-TYPE
        SYNTAX Unsigned32
        MAX-ACCESS read-only
        STATUS obsolete
        DESCRIPTION
            "The total number of 'Write' CIFS calls received since 
             power up."
        ::= { cifsStats 13 }

    cifsMknewCalls OBJECT-TYPE
        SYNTAX Unsigned32
        MAX-ACCESS read-only
        STATUS obsolete
        DESCRIPTION
            "The total number of 'Mknew' CIFS calls received since 
             power up."
        ::= { cifsStats 14 }

    cifsChkpthCalls OBJECT-TYPE
        SYNTAX Unsigned32
        MAX-ACCESS read-only
        STATUS obsolete
        DESCRIPTION
            "The total number of 'Chkpth' CIFS calls received since 
             power up."
        ::= { cifsStats 15 }

    cifsLseekCalls OBJECT-TYPE
        SYNTAX Unsigned32
        MAX-ACCESS read-only
        STATUS obsolete
        DESCRIPTION
            "The total number of 'Lseek' CIFS calls received since 
             power up."
        ::= { cifsStats 16 }

    cifsReadBrawCalls OBJECT-TYPE
        SYNTAX Unsigned32
        MAX-ACCESS read-only
        STATUS obsolete
        DESCRIPTION
            "The total number of 'ReadBraw' CIFS calls received since 
             power up."
        ::= { cifsStats 17 }

    cifsWriteBrawCalls OBJECT-TYPE
        SYNTAX Unsigned32
        MAX-ACCESS read-only
        STATUS obsolete
        DESCRIPTION
            "The total number of 'WriteBraw' CIFS calls received since 
             power up."
        ::= { cifsStats 18 }

    cifsLockingXCalls OBJECT-TYPE
        SYNTAX Unsigned32
        MAX-ACCESS read-only
        STATUS obsolete
        DESCRIPTION
            "The total number of 'LockingX' CIFS calls received since 
             power up."
        ::= { cifsStats 19 }

    cifsTransCalls OBJECT-TYPE
        SYNTAX Unsigned32
        MAX-ACCESS read-only
        STATUS obsolete
        DESCRIPTION
            "The total number of 'Trans' CIFS calls received since 
             power up."
        ::= { cifsStats 20 }

    cifsEchoCalls OBJECT-TYPE
        SYNTAX Unsigned32
        MAX-ACCESS read-only
        STATUS obsolete
        DESCRIPTION
            "The total number of 'Echo' CIFS calls received since 
             power up."
        ::= { cifsStats 21 }

    cifsWriteCloseCalls OBJECT-TYPE
        SYNTAX Unsigned32
        MAX-ACCESS read-only
        STATUS obsolete
        DESCRIPTION
            "The total number of 'WriteClose' CIFS calls received since 
             power up."
        ::= { cifsStats 22 }

    cifsOpenXCalls OBJECT-TYPE
        SYNTAX Unsigned32
        MAX-ACCESS read-only
        STATUS obsolete
        DESCRIPTION
            "The total number of 'OpenX' CIFS calls received since 
             power up."
        ::= { cifsStats 23 }

    cifsReadXCalls OBJECT-TYPE
        SYNTAX Unsigned32
        MAX-ACCESS read-only
        STATUS obsolete
        DESCRIPTION
            "The total number of 'ReadX' CIFS calls received since 
             power up."
        ::= { cifsStats 24 }

    cifsWriteXCalls OBJECT-TYPE
        SYNTAX Unsigned32
        MAX-ACCESS read-only
        STATUS obsolete
        DESCRIPTION
            "The total number of 'WriteX' CIFS calls received since 
             power up."
        ::= { cifsStats 25 }

    cifsTrans2Calls OBJECT-TYPE
        SYNTAX Unsigned32
        MAX-ACCESS read-only
        STATUS obsolete
        DESCRIPTION
            "The total number of 'Trans2' CIFS calls received since
             power up."
        ::= { cifsStats 26 }

    cifsFindCloseCalls OBJECT-TYPE
        SYNTAX Unsigned32
        MAX-ACCESS read-only
        STATUS obsolete
        DESCRIPTION
            "The total number of 'FindClose' CIFS calls received since 
             power up."
        ::= { cifsStats 27 }

    cifsTdisCalls OBJECT-TYPE
        SYNTAX Unsigned32
        MAX-ACCESS read-only
        STATUS obsolete
        DESCRIPTION
            "The total number of 'Tdis' CIFS calls received since 
             power up."
        ::= { cifsStats 28 }

    cifsNegProtCalls OBJECT-TYPE
        SYNTAX Unsigned32
        MAX-ACCESS read-only
        STATUS obsolete
        DESCRIPTION
            "The total number of 'NegProt' CIFS calls received since 
             power up."
        ::= { cifsStats 29 }

    cifsSessSetupXCalls OBJECT-TYPE
        SYNTAX Unsigned32
        MAX-ACCESS read-only
        STATUS obsolete
        DESCRIPTION
            "The total number of 'SessSetupX' CIFS calls received since 
             power up."
        ::= { cifsStats 30 }

    cifsUlogoffXCalls OBJECT-TYPE
        SYNTAX Unsigned32
        MAX-ACCESS read-only
        STATUS obsolete
        DESCRIPTION
            "The total number of 'UlogoffX' CIFS calls received since 
             power up."
        ::= { cifsStats 31 }

    cifsTconXCalls OBJECT-TYPE
        SYNTAX Unsigned32
        MAX-ACCESS read-only
        STATUS obsolete
        DESCRIPTION
            "The total number of 'TconX' CIFS calls received since 
             power up."
        ::= { cifsStats 32 }

    cifsDskattrCalls OBJECT-TYPE
        SYNTAX Unsigned32
        MAX-ACCESS read-only
        STATUS obsolete
        DESCRIPTION
            "The total number of 'Dskattr' CIFS calls received since 
             power up."
        ::= { cifsStats 33 }

    cifsSearchCalls OBJECT-TYPE
        SYNTAX Unsigned32
        MAX-ACCESS read-only
        STATUS obsolete
        DESCRIPTION
            "The total number of 'Search' CIFS calls received since 
             power up."
        ::= { cifsStats 34 }

    cifsNTtransCalls OBJECT-TYPE
        SYNTAX Unsigned32
        MAX-ACCESS read-only
        STATUS obsolete
        DESCRIPTION
            "The total number of 'NTtrans' CIFS calls received since 
             power up."
        ::= { cifsStats 35 }

    cifsNTtranssCalls OBJECT-TYPE
        SYNTAX Unsigned32
        MAX-ACCESS read-only
        STATUS obsolete
        DESCRIPTION
            "The total number of 'NTtranss' CIFS calls received since
             power up."
        ::= { cifsStats 36 }

    cifsNTcreateXCalls OBJECT-TYPE
        SYNTAX Unsigned32
        MAX-ACCESS read-only
        STATUS obsolete
        DESCRIPTION
            "The total number of 'NTcreateX' CIFS calls received since 
             power up."
        ::= { cifsStats 37 }

    cifsNTcancelCalls OBJECT-TYPE
        SYNTAX Unsigned32
        MAX-ACCESS read-only
        STATUS obsolete
        DESCRIPTION
            "The total number of 'NTcancel' CIFS calls received since 
             power up."
        ::= { cifsStats 38 }

    cifsStatsTable OBJECT-TYPE
        SYNTAX SEQUENCE OF CifsStatsEntry
        MAX-ACCESS not-accessible
        STATUS current
        DESCRIPTION
            "The statistics for the CIFS service.

            The number of entries in this table is given by the
            value of cifsStatsClusterNode."
        ::= { cifsStats 39 }

    cifsStatsEntry OBJECT-TYPE
        SYNTAX CifsStatsEntry
        MAX-ACCESS not-accessible
        STATUS current
        DESCRIPTION
            "The statistics for the CIFS service."
        INDEX { cifsStatsClusterNode }
        ::= { cifsStatsTable 1 }

    CifsStatsEntry ::=
        SEQUENCE {
            cifsStatsClusterNode
                Unsigned32,
            clients
                Unsigned32,
            mkdirCalls
                Unsigned32,
            rmdirCalls
                Unsigned32,
            openCalls
                Unsigned32,
            createCalls
                Unsigned32,
            closeCalls
                Unsigned32,
            flushCalls
                Unsigned32,
            unlinkCalls
                Unsigned32,
            renameCalls
                Unsigned32,
            getatrCalls
                Unsigned32,
            setatrCalls
                Unsigned32,
            readCalls
                Unsigned32,
            writeCalls
                Unsigned32,
            mknewCalls
                Unsigned32,
            chkpthCalls
                Unsigned32,
            lseekCalls
                Unsigned32,
            readBrawCalls
                Unsigned32,
            writeBrawCalls
                Unsigned32,
            lockingXCalls
                Unsigned32,
            transCalls
                Unsigned32,
            echoCalls
                Unsigned32,
            writeCloseCalls
                Unsigned32,
            openXCalls
                Unsigned32,
            readXCalls
                Unsigned32,
            writeXCalls
                Unsigned32,
            trans2Calls
                Unsigned32,
            findCloseCalls
                Unsigned32,
            tdisCalls
                Unsigned32,
            negProtCalls
                Unsigned32,
            sessSetupXCalls
                Unsigned32,
            ulogoffXCalls
                Unsigned32,
            tconXCalls
                Unsigned32,
            dskattrCalls
                Unsigned32,
            searchCalls
                Unsigned32,
            ntTransCalls    
                Unsigned32,
            ntTranssCalls
                Unsigned32,
            ntCreateXCalls
                Unsigned32,
            ntCancelCalls
                Unsigned32
        }

    cifsStatsClusterNode OBJECT-TYPE
        SYNTAX Unsigned32
        MAX-ACCESS read-only
        STATUS current
        DESCRIPTION
            "The Cluster Node for this value."
        ::= { cifsStatsEntry 1 }

    clients OBJECT-TYPE
        SYNTAX Unsigned32
        MAX-ACCESS read-only
        STATUS current
        DESCRIPTION
            "The total number of CIFS clients since power up."
        ::= { cifsStatsEntry 2 }

    mkdirCalls OBJECT-TYPE
        SYNTAX Unsigned32
        MAX-ACCESS read-only
        STATUS current
        DESCRIPTION
            "The total number of 'Mkdir' CIFS calls received since
             power up."
        ::= { cifsStatsEntry 3 }

    rmdirCalls OBJECT-TYPE
        SYNTAX Unsigned32
        MAX-ACCESS read-only
        STATUS current
        DESCRIPTION
            "The total number of 'Rmdir' CIFS calls received since 
             power up."
        ::= { cifsStatsEntry 4 }

    openCalls OBJECT-TYPE
        SYNTAX Unsigned32
        MAX-ACCESS read-only
        STATUS current
        DESCRIPTION
            "The total number of 'Open' CIFS calls received since 
             power up."
        ::= { cifsStatsEntry 5 }

    createCalls OBJECT-TYPE
        SYNTAX Unsigned32
        MAX-ACCESS read-only
        STATUS current
        DESCRIPTION
            "The total number of 'Create' CIFS calls received since 
             power up."
        ::= { cifsStatsEntry 6 }

    closeCalls OBJECT-TYPE
        SYNTAX Unsigned32
        MAX-ACCESS read-only
        STATUS current
        DESCRIPTION
            "The total number of 'Close' CIFS calls received since
             power up."
        ::= { cifsStatsEntry 7 }

    flushCalls OBJECT-TYPE
        SYNTAX Unsigned32
        MAX-ACCESS read-only
        STATUS current
        DESCRIPTION
            "The total number of 'Flush' CIFS calls received since 
             power up."
        ::= { cifsStatsEntry 8 }

    unlinkCalls OBJECT-TYPE
        SYNTAX Unsigned32
        MAX-ACCESS read-only
        STATUS current
        DESCRIPTION
            "The total number of 'Unlink' CIFS calls received since 
             power up."
        ::= { cifsStatsEntry 9 }

    renameCalls OBJECT-TYPE
        SYNTAX Unsigned32
        MAX-ACCESS read-only
        STATUS current
        DESCRIPTION
            "The total number of 'Rename' CIFS calls received since 
             power up."
        ::= { cifsStatsEntry 10 }

    getatrCalls OBJECT-TYPE
        SYNTAX Unsigned32
        MAX-ACCESS read-only
        STATUS current
        DESCRIPTION
            "The total number of 'Getatr' CIFS calls received since 
             power up."
        ::= { cifsStatsEntry 11 }

    setatrCalls OBJECT-TYPE
        SYNTAX Unsigned32
        MAX-ACCESS read-only
        STATUS current
        DESCRIPTION
            "The total number of 'Setatr' CIFS calls received since 
             power up."
        ::= { cifsStatsEntry 12 }

    readCalls OBJECT-TYPE
        SYNTAX Unsigned32
        MAX-ACCESS read-only
        STATUS current
        DESCRIPTION
            "The total number of 'Read' CIFS calls received since 
             power up."
        ::= { cifsStatsEntry 13 }

    writeCalls OBJECT-TYPE
        SYNTAX Unsigned32
        MAX-ACCESS read-only
        STATUS current
        DESCRIPTION
            "The total number of 'Write' CIFS calls received since 
             power up."
        ::= { cifsStatsEntry 14 }

    mknewCalls OBJECT-TYPE
        SYNTAX Unsigned32
        MAX-ACCESS read-only
        STATUS current
        DESCRIPTION
            "The total number of 'Mknew' CIFS calls received since 
             power up."
        ::= { cifsStatsEntry 15 }

    chkpthCalls OBJECT-TYPE
        SYNTAX Unsigned32
        MAX-ACCESS read-only
        STATUS current
        DESCRIPTION
            "The total number of 'Chkpth' CIFS calls received since 
             power up."
        ::= { cifsStatsEntry 16 }

    lseekCalls OBJECT-TYPE
        SYNTAX Unsigned32
        MAX-ACCESS read-only
        STATUS current
        DESCRIPTION
            "The total number of 'Lseek' CIFS calls received since 
             power up."
        ::= { cifsStatsEntry 17 }

    readBrawCalls OBJECT-TYPE
        SYNTAX Unsigned32
        MAX-ACCESS read-only
        STATUS current
        DESCRIPTION
            "The total number of 'ReadBraw' CIFS calls received since 
             power up."
        ::= { cifsStatsEntry 18 }

    writeBrawCalls OBJECT-TYPE
        SYNTAX Unsigned32
        MAX-ACCESS read-only
        STATUS current
        DESCRIPTION
            "The total number of 'WriteBraw' CIFS calls received since 
             power up."
        ::= { cifsStatsEntry 19 }

    lockingXCalls OBJECT-TYPE
        SYNTAX Unsigned32
        MAX-ACCESS read-only
        STATUS current
        DESCRIPTION
            "The total number of 'LockingX' CIFS calls received since 
             power up."
        ::= { cifsStatsEntry 20 }

    transCalls OBJECT-TYPE
        SYNTAX Unsigned32
        MAX-ACCESS read-only
        STATUS current
        DESCRIPTION
            "The total number of 'Trans' CIFS calls received since 
             power up."
        ::= { cifsStatsEntry 21 }

    echoCalls OBJECT-TYPE
        SYNTAX Unsigned32
        MAX-ACCESS read-only
        STATUS current
        DESCRIPTION
            "The total number of 'Echo' CIFS calls received since 
             power up."
        ::= { cifsStatsEntry 22 }

    writeCloseCalls OBJECT-TYPE
        SYNTAX Unsigned32
        MAX-ACCESS read-only
        STATUS current
        DESCRIPTION
            "The total number of 'WriteClose' CIFS calls received since 
             power up."
        ::= { cifsStatsEntry 23 }

    openXCalls OBJECT-TYPE
        SYNTAX Unsigned32
        MAX-ACCESS read-only
        STATUS current
        DESCRIPTION
            "The total number of 'OpenX' CIFS calls received since 
             power up."
        ::= { cifsStatsEntry 24 }

    readXCalls OBJECT-TYPE
        SYNTAX Unsigned32
        MAX-ACCESS read-only
        STATUS current
        DESCRIPTION
            "The total number of 'ReadX' CIFS calls received since 
             power up."
        ::= { cifsStatsEntry 25 }

    writeXCalls OBJECT-TYPE
        SYNTAX Unsigned32
        MAX-ACCESS read-only
        STATUS current
        DESCRIPTION
            "The total number of 'WriteX' CIFS calls received since 
             power up."
        ::= { cifsStatsEntry 26 }

    trans2Calls OBJECT-TYPE
        SYNTAX Unsigned32
        MAX-ACCESS read-only
        STATUS current
        DESCRIPTION
            "The total number of 'Trans2' CIFS calls received since
             power up."
        ::= { cifsStatsEntry 27 }

    findCloseCalls OBJECT-TYPE
        SYNTAX Unsigned32
        MAX-ACCESS read-only
        STATUS current
        DESCRIPTION
            "The total number of 'FindClose' CIFS calls received since 
             power up."
        ::= { cifsStatsEntry 28 }

    tdisCalls OBJECT-TYPE
        SYNTAX Unsigned32
        MAX-ACCESS read-only
        STATUS current
        DESCRIPTION
            "The total number of 'Tdis' CIFS calls received since 
             power up."
        ::= { cifsStatsEntry 29 }

    negProtCalls OBJECT-TYPE
        SYNTAX Unsigned32
        MAX-ACCESS read-only
        STATUS current
        DESCRIPTION
            "The total number of 'NegProt' CIFS calls received since 
             power up."
        ::= { cifsStatsEntry 30 }

    sessSetupXCalls OBJECT-TYPE
        SYNTAX Unsigned32
        MAX-ACCESS read-only
        STATUS current
        DESCRIPTION
            "The total number of 'SessSetupX' CIFS calls received since 
             power up."
        ::= { cifsStatsEntry 31 }

    ulogoffXCalls OBJECT-TYPE
        SYNTAX Unsigned32
        MAX-ACCESS read-only
        STATUS current
        DESCRIPTION
            "The total number of 'UlogoffX' CIFS calls received since 
             power up."
        ::= { cifsStatsEntry 32 }

    tconXCalls OBJECT-TYPE
        SYNTAX Unsigned32
        MAX-ACCESS read-only
        STATUS current
        DESCRIPTION
            "The total number of 'TconX' CIFS calls received since 
             power up."
        ::= { cifsStatsEntry 33 }

    dskattrCalls OBJECT-TYPE
        SYNTAX Unsigned32
        MAX-ACCESS read-only
        STATUS current
        DESCRIPTION
            "The total number of 'Dskattr' CIFS calls received since 
             power up."
        ::= { cifsStatsEntry 34 }

    searchCalls OBJECT-TYPE
        SYNTAX Unsigned32
        MAX-ACCESS read-only
        STATUS current
        DESCRIPTION
            "The total number of 'Search' CIFS calls received since 
             power up."
        ::= { cifsStatsEntry 35 }

    ntTransCalls OBJECT-TYPE
        SYNTAX Unsigned32
        MAX-ACCESS read-only
        STATUS current
        DESCRIPTION
            "The total number of 'NTtrans' CIFS calls received since 
             power up."
        ::= { cifsStatsEntry 36 }

    ntTranssCalls OBJECT-TYPE
        SYNTAX Unsigned32
        MAX-ACCESS read-only
        STATUS current
        DESCRIPTION
            "The total number of 'NTtranss' CIFS calls received since
             power up."
        ::= { cifsStatsEntry 37 }

    ntCreateXCalls OBJECT-TYPE
        SYNTAX Unsigned32
        MAX-ACCESS read-only
        STATUS current
        DESCRIPTION
            "The total number of 'NTcreateX' CIFS calls received since 
             power up."
        ::= { cifsStatsEntry 38 }

    ntCancelCalls OBJECT-TYPE
        SYNTAX Unsigned32
        MAX-ACCESS read-only
        STATUS current
        DESCRIPTION
            "The total number of 'NTcancel' CIFS calls received since 
             power up."
        ::= { cifsStatsEntry 39 }


--------------------------------------------------------------------------------
--
-- File Protocol / CIFS / CIFS Service Configuration
--
--------------------------------------------------------------------------------

    cifsServiceEnabled OBJECT-TYPE
        SYNTAX INTEGER {
            enabled(1),
            disabled(2),
            unknown(3)
        }
        MAX-ACCESS read-only
        STATUS current
        DESCRIPTION
            "Indicates whether the CIFS service is enabled or not."
        ::= { cifsService 1 }

    cifsServiceMaxUsers OBJECT-TYPE
        SYNTAX Unsigned32
        MAX-ACCESS read-only
        STATUS current
        DESCRIPTION
            "The maximum number of CIFS users the service will allow."
        ::= { cifsService 2 }

--------------------------------------------------------------------------------
--
-- File Protocol / NFS / NFS Exports
--
--------------------------------------------------------------------------------

    nfsExportNumber OBJECT-TYPE
        SYNTAX Integer32
        MAX-ACCESS read-only
        STATUS current
        DESCRIPTION
            "The number of NFS exports which are configured for the system."
        ::= { nfsExports 1 }

    nfsExportTable OBJECT-TYPE
        SYNTAX SEQUENCE OF NfsExportEntry
        MAX-ACCESS not-accessible
        STATUS obsolete
        DESCRIPTION
            "A table containing the NFS export configuration for the
             system.

             The number of entries in this table is given by the value of
             nfsExportNumber.

             This object is now obsolete, and is re-implemented as a table
             indexed by EVS and name."
        ::= { nfsExports 2 }

    nfsExportEntry OBJECT-TYPE
        SYNTAX NfsExportEntry
        MAX-ACCESS not-accessible
        STATUS obsolete
        DESCRIPTION
            "NFS export information."
        INDEX { nfsExportIndex }
        ::= { nfsExportTable 1 }

    NfsExportEntry ::=
        SEQUENCE {
            nfsExportIndex
                Integer32,
            nfsExportName
                DisplayString,
            nfsExportPath
                DisplayString,
            nfsExportNumberMounts
                Unsigned32,
            nfsExportWWN
                DisplayString,
            nfsExportLUN
                Unsigned32,
            nfsExportPartitionID
                Unsigned32
        }

    nfsExportIndex OBJECT-TYPE
        SYNTAX Integer32 (1..2000)
        MAX-ACCESS read-only
        STATUS obsolete
        DESCRIPTION
            "A unique value for each NFS export configuration
             in this system.

             Its value ranges between 1 and the value of nfsExportNumber.

             This object is now obsolete, and is re-implemented as a table
             indexed by EVS and name."
        ::= { nfsExportEntry 1 }

    nfsExportName OBJECT-TYPE
        SYNTAX DisplayString
        MAX-ACCESS read-only
        STATUS obsolete
        DESCRIPTION
            "The name of the NFS export.  Each export has a unique name.

             This object is now obsolete, and is re-implemented as a table
             indexed by EVS and name."
        ::= { nfsExportEntry 2 }

    nfsExportPath OBJECT-TYPE
        SYNTAX DisplayString
        MAX-ACCESS read-only
        STATUS obsolete
        DESCRIPTION
            "The path to the NFS export."
        ::= { nfsExportEntry 3 }

    nfsExportNumberMounts OBJECT-TYPE
        SYNTAX Unsigned32
        MAX-ACCESS read-only
        STATUS obsolete
        DESCRIPTION
            "The number of mounts of the NFS export.

             This object is obsolete.  It could not be measured.

             This object is now obsolete, and is re-implemented as a table
             indexed by EVS and name."
        ::= { nfsExportEntry 4 }

    nfsExportWWN OBJECT-TYPE
        SYNTAX DisplayString
        MAX-ACCESS read-only
        STATUS obsolete
        DESCRIPTION
            "The world wide name (WWN) of the system drive the NFS
             export is associated with.

             This object is now obsolete, and is re-implemented as a table
             indexed by EVS and name."
        ::= { nfsExportEntry 5 }

    nfsExportLUN OBJECT-TYPE
        SYNTAX Unsigned32
        MAX-ACCESS read-only
        STATUS obsolete
        DESCRIPTION
            "The logical unit number (LUN) of the system drive the
             NFS export is associated with.

             This now has no meaning and is set to zero.

             This object is now obsolete, and is re-implemented as a table
             indexed by EVS and name."
        ::= { nfsExportEntry 6 }

    nfsExportPartitionID OBJECT-TYPE
        SYNTAX Unsigned32
        MAX-ACCESS read-only
        STATUS obsolete
        DESCRIPTION
            "The partition ID of the volume the NFS export is associated
             with.

             This now has no meaning and is set to zero.

             This object is now obsolete, and is re-implemented as a table
             indexed by EVS and name."
        ::= { nfsExportEntry 7 }



    nfsExportsTable OBJECT-TYPE
        SYNTAX SEQUENCE OF NfsExportsEntry
        MAX-ACCESS not-accessible
        STATUS current
        DESCRIPTION
            "A table containing the NFS export configuration for the
             system.

             The number of entries in this table is given by the value of
             nfsExportNumber."
        ::= { nfsExports 3 }

    nfsExportsEntry OBJECT-TYPE
        SYNTAX NfsExportsEntry
        MAX-ACCESS not-accessible
        STATUS current
        DESCRIPTION
            "NFS export information."
        INDEX { nfsExportsEvs, nfsExportsName }
        ::= { nfsExportsTable 1 }

    NfsExportsEntry ::=
        SEQUENCE {
            nfsExportsEvs
                Unsigned32,
            nfsExportsName
                DisplayString,
            nfsExportsPath
                DisplayString,
            nfsExportsDeviceId
                Unsigned32
        }

    nfsExportsEvs OBJECT-TYPE
        SYNTAX Unsigned32 (1..255)
        MAX-ACCESS read-only
        STATUS current
        DESCRIPTION
            "The ID of the EVS the NFS export is associated with."
        ::= { nfsExportsEntry 1 }

    nfsExportsName OBJECT-TYPE
        SYNTAX DisplayString
        MAX-ACCESS read-only
        STATUS current
        DESCRIPTION
            "The name of the NFS export.  Each export has a unique name."
        ::= { nfsExportsEntry 2 }

    nfsExportsPath OBJECT-TYPE
        SYNTAX DisplayString
        MAX-ACCESS read-only
        STATUS current
        DESCRIPTION
            "The path to the NFS export."
        ::= { nfsExportsEntry 3 }

    nfsExportsDeviceId OBJECT-TYPE
        SYNTAX Unsigned32 (1..4294967295)
        MAX-ACCESS read-only
        STATUS current
        DESCRIPTION
            "The device ID of the volume the NFS
             export is associated with."
        ::= { nfsExportsEntry 4 }

--------------------------------------------------------------------------------
--
-- File Protocol / NFS / NFS Users
--
--------------------------------------------------------------------------------

    nfsUserNumber OBJECT-TYPE
        SYNTAX Integer32
        MAX-ACCESS read-only
        STATUS obsolete
        DESCRIPTION
            "The number of NFS users which are configured for the system."
        ::= { nfsUsers 1 }

    nfsUserTable OBJECT-TYPE
        SYNTAX SEQUENCE OF NfsUserEntry
        MAX-ACCESS not-accessible
        STATUS obsolete
        DESCRIPTION
            "A table containing the NFS user configuration for the
             system.

             The number of entries in this table is given by the value of
             nfsUserNumber."
        ::= { nfsUsers 2 }

    nfsUserEntry OBJECT-TYPE
        SYNTAX NfsUserEntry
        MAX-ACCESS not-accessible
        STATUS obsolete
        DESCRIPTION
            "NFS user information."
        INDEX { nfsUserName }
        ::= { nfsUserTable 1 }

    NfsUserEntry ::=
        SEQUENCE {
            nfsUserName
                DisplayString,
            nfsUserID
                Unsigned32
        }

    nfsUserName OBJECT-TYPE
        SYNTAX DisplayString
        MAX-ACCESS read-only
        STATUS obsolete
        DESCRIPTION
            "The name of the UNIX user."
        ::= { nfsUserEntry 1 }

    nfsUserID OBJECT-TYPE
        SYNTAX Unsigned32
        MAX-ACCESS read-only
        STATUS obsolete
        DESCRIPTION
            "The ID of the UNIX user."
        ::= { nfsUserEntry 2 }

--------------------------------------------------------------------------------
--
-- File Protocol / NFS / NFS User Mapping
--
--------------------------------------------------------------------------------

    nfsUserMappingNumber OBJECT-TYPE
        SYNTAX Integer32
        MAX-ACCESS read-only
        STATUS obsolete
        DESCRIPTION
            "The number of NFS to NT user mappings which are configured 
             for the system."
        ::= { nfsUserMapping 1 }

    nfsUserMappingTable OBJECT-TYPE
        SYNTAX SEQUENCE OF NfsUserMappingEntry
        MAX-ACCESS not-accessible
        STATUS obsolete
        DESCRIPTION
            "A table containing the NFS to NT user mapping configuration
             for the system.

             The number of entries in this table is given by the value of 
             nfsUserMappingNumber."
        ::= { nfsUserMapping 2 }

    nfsUserMappingEntry OBJECT-TYPE
        SYNTAX NfsUserMappingEntry
        MAX-ACCESS not-accessible
        STATUS obsolete
        DESCRIPTION
            "NFS to NT user mapping information."
        INDEX { nfsUserMappingUnixUserName }
        ::= { nfsUserMappingTable 1 }

    NfsUserMappingEntry ::=
        SEQUENCE {
            nfsUserMappingUnixUserName
                DisplayString,
            nfsUserMappingUnixUserIDValid
                INTEGER,
            nfsUserMappingUnixUserID
                Unsigned32,
            nfsUserMappingNtUserName
                DisplayString,
            nfsUserMappingNtUserDomainName
                DisplayString
        }

    nfsUserMappingUnixUserName OBJECT-TYPE
        SYNTAX DisplayString
        MAX-ACCESS read-only
        STATUS obsolete
        DESCRIPTION
            "The name of the UNIX user for which the mapping exists."
        ::= { nfsUserMappingEntry 1 }

    nfsUserMappingUnixUserIDValid OBJECT-TYPE
        SYNTAX INTEGER {
            valid(1),
            invalid(2),
            unknown(3)
        }
        MAX-ACCESS read-only
        STATUS obsolete
        DESCRIPTION
            "Indicates whether the UNIX user ID is configured user in
             the nfsUserTable."
        ::= { nfsUserMappingEntry 2 }

    nfsUserMappingUnixUserID OBJECT-TYPE
        SYNTAX Unsigned32
        MAX-ACCESS read-only
        STATUS obsolete
        DESCRIPTION
            "The UNIX user ID."
        ::= { nfsUserMappingEntry 3 }

    nfsUserMappingNtUserName OBJECT-TYPE
        SYNTAX DisplayString
        MAX-ACCESS read-only
        STATUS obsolete
        DESCRIPTION
            "The name of the NT user for which the mapping exists."
        ::= { nfsUserMappingEntry 4 }

    nfsUserMappingNtUserDomainName OBJECT-TYPE
        SYNTAX DisplayString
        MAX-ACCESS read-only
        STATUS obsolete
        DESCRIPTION
            "The NT domain name for which the mapping exists."
        ::= { nfsUserMappingEntry 5 }

--------------------------------------------------------------------------------
--
-- File Protocol / NFS / NFS Groups
--
--------------------------------------------------------------------------------

    nfsGroupNumber OBJECT-TYPE
        SYNTAX Integer32
        MAX-ACCESS read-only
        STATUS obsolete
        DESCRIPTION
            "The number of NFS groups configured for the system."
        ::= { nfsGroups 1 }

    nfsGroupTable OBJECT-TYPE
        SYNTAX SEQUENCE OF NfsGroupEntry
        MAX-ACCESS not-accessible
        STATUS obsolete
        DESCRIPTION
            "A table containing the NFS group configuration for the
             system.

             The number of entries in this table is given by the value of 
             nfsGroupNumber."
        ::= { nfsGroups 2 }

    nfsGroupEntry OBJECT-TYPE
        SYNTAX NfsGroupEntry
        MAX-ACCESS not-accessible
        STATUS obsolete
        DESCRIPTION
            "NFS group information."
        INDEX { nfsGroupName }
        ::= { nfsGroupTable 1 }

    NfsGroupEntry ::=
        SEQUENCE {
            nfsGroupName
                DisplayString,
            nfsGroupID
                Unsigned32
        }

    nfsGroupName OBJECT-TYPE
        SYNTAX DisplayString
        MAX-ACCESS read-only
        STATUS obsolete
        DESCRIPTION
            "The name of the UNIX group."
        ::= { nfsGroupEntry 1 }

    nfsGroupID OBJECT-TYPE
        SYNTAX Unsigned32
        MAX-ACCESS read-only
        STATUS obsolete
        DESCRIPTION
            "The ID of the UNIX group."
        ::= { nfsGroupEntry 2 }

--------------------------------------------------------------------------------
--
-- File Protocol / NFS / NFS Group Mapping
--
--------------------------------------------------------------------------------

    nfsGroupMappingNumber OBJECT-TYPE
        SYNTAX Integer32
        MAX-ACCESS read-only
        STATUS obsolete
        DESCRIPTION
            "The number of NFS to NT group mappings which are configured 
             for the system."
        ::= { nfsGroupMapping 1 }

    nfsGroupMappingTable OBJECT-TYPE
        SYNTAX SEQUENCE OF NfsGroupMappingEntry
        MAX-ACCESS not-accessible
        STATUS obsolete
        DESCRIPTION
            "A table containing the NFS to NT group mapping configuration
             for the system.

             The number of entries in this table is given by the value of 
             nfsGroupMappingNumber."
        ::= { nfsGroupMapping 2 }

    nfsGroupMappingEntry OBJECT-TYPE
        SYNTAX NfsGroupMappingEntry
        MAX-ACCESS not-accessible
        STATUS obsolete
        DESCRIPTION
            "NFS to NT group mapping information."
        INDEX { nfsGroupMappingUnixGroupName }
        ::= { nfsGroupMappingTable 1 }

    NfsGroupMappingEntry ::=
        SEQUENCE {
            nfsGroupMappingUnixGroupName
                DisplayString,
            nfsGroupMappingUnixGroupIDValid
                INTEGER,
            nfsGroupMappingUnixGroupID
                Unsigned32,
            nfsGroupMappingNtGroupName
                DisplayString,
            nfsGroupMappingNtGroupDomainName
                DisplayString
        }

    nfsGroupMappingUnixGroupName OBJECT-TYPE
        SYNTAX DisplayString
        MAX-ACCESS read-only
        STATUS obsolete
        DESCRIPTION
            "The name of the UNIX group for which the mapping exists."
        ::= { nfsGroupMappingEntry 1 }

    nfsGroupMappingUnixGroupIDValid OBJECT-TYPE
        SYNTAX INTEGER {
            valid(1),
            invalid(2),
            unknown(3)
        }
        MAX-ACCESS read-only
        STATUS obsolete
        DESCRIPTION
            "Indicates whether the UNIX group ID is configured user in
             the nfsGroupTable."
        ::= { nfsGroupMappingEntry 2 }

    nfsGroupMappingUnixGroupID OBJECT-TYPE
        SYNTAX Unsigned32
        MAX-ACCESS read-only
        STATUS obsolete
        DESCRIPTION
            "The UNIX group ID."
        ::= { nfsGroupMappingEntry 3 }

    nfsGroupMappingNtGroupName OBJECT-TYPE
        SYNTAX DisplayString
        MAX-ACCESS read-only
        STATUS obsolete
        DESCRIPTION
            "The name of the NT group for which the mapping exists."
        ::= { nfsGroupMappingEntry 4 }

    nfsGroupMappingNtGroupDomainName OBJECT-TYPE
        SYNTAX DisplayString
        MAX-ACCESS read-only
        STATUS obsolete
        DESCRIPTION
            "The NT domain name for which the mapping exists."
        ::= { nfsGroupMappingEntry 5 }

--------------------------------------------------------------------------------
--
-- File Protocol / NFS / Statistics / NFS Version 2
--
--------------------------------------------------------------------------------

    null2Calls OBJECT-TYPE
        SYNTAX Counter32
        MAX-ACCESS read-only
        STATUS obsolete
        DESCRIPTION
            "The total number of 'Null' calls received for NFS version 2 
             since power up.

             This object is now obsolete, and is replaced with a table
             of values indexed by Cluster Node and name."
        ::= { nfsVersion2 1 }

    getAttr2Calls OBJECT-TYPE
        SYNTAX Counter32
        MAX-ACCESS read-only
        STATUS obsolete
        DESCRIPTION
            "The total number of 'GetAttr' calls received for NFS version 2 
             since power up.

             This object is now obsolete, and is replaced with a table
             of values indexed by Cluster Node and name."
        ::= { nfsVersion2 2 }

    setAttr2Calls OBJECT-TYPE
        SYNTAX Counter32
        MAX-ACCESS read-only
        STATUS obsolete
        DESCRIPTION
            "The total number of 'SetAttr' calls received for NFS version 2 
             since power up.

             This object is now obsolete, and is replaced with a table
             of values indexed by Cluster Node and name."
        ::= { nfsVersion2 3 }

    rootCalls OBJECT-TYPE
        SYNTAX Counter32
        MAX-ACCESS read-only
        STATUS obsolete
        DESCRIPTION
            "The total number of 'Root' calls received since power up
             NOTE: this variable is not used/implemented.

             This object is now obsolete, and is replaced with a table
             of values indexed by Cluster Node and name."
        ::= { nfsVersion2 4 }

    lookup2Calls OBJECT-TYPE
        SYNTAX Counter32
        MAX-ACCESS read-only
        STATUS obsolete
        DESCRIPTION
            "The total number of 'Lookup' calls received for NFS version 2 
             since power up.

             This object is now obsolete, and is replaced with a table
             of values indexed by Cluster Node and name."
        ::= { nfsVersion2 5 }

    readLink2 OBJECT-TYPE
        SYNTAX Counter32
        MAX-ACCESS read-only
        STATUS obsolete
        DESCRIPTION
            "The total number of 'ReadLink' calls received for NFS version 2 
             since power up.

             This object is now obsolete, and is replaced with a table
             of values indexed by Cluster Node and name."
        ::= { nfsVersion2 6 }

    read2 OBJECT-TYPE
        SYNTAX Counter32
        MAX-ACCESS read-only
        STATUS obsolete
        DESCRIPTION
            "The total number of 'Read' calls received for NFS version 2 
             since power up.

             This object is now obsolete, and is replaced with a table
             of values indexed by Cluster Node and name."
        ::= { nfsVersion2 7 }

    writeCache OBJECT-TYPE
        SYNTAX Counter32
        MAX-ACCESS read-only
        STATUS obsolete
        DESCRIPTION
            "The total number of 'Write Cache' calls received since power up.
             NOTE : this variable is not used/implemented.

             This object is now obsolete, and is replaced with a table
             of values indexed by Cluster Node and name."
        ::= { nfsVersion2 8 }

    write2 OBJECT-TYPE
        SYNTAX Counter32
        MAX-ACCESS read-only
        STATUS obsolete
        DESCRIPTION
            "The total number of 'Write' calls received for NFS version 2 
             since power up.

             This object is now obsolete, and is replaced with a table
             of values indexed by Cluster Node and name."
        ::= { nfsVersion2 9 }

    create2 OBJECT-TYPE
        SYNTAX Counter32
        MAX-ACCESS read-only
        STATUS obsolete
        DESCRIPTION
            "The total number of 'Create' calls received for NFS version 2 
             since power up.

             This object is now obsolete, and is replaced with a table
             of values indexed by Cluster Node and name."
        ::= { nfsVersion2 10 }

    remove2 OBJECT-TYPE
        SYNTAX Counter32
        MAX-ACCESS read-only
        STATUS obsolete
        DESCRIPTION
            "The total number of 'Remove' calls received for NFS version 2 
             since power up.

             This object is now obsolete, and is replaced with a table
             of values indexed by Cluster Node and name."
        ::= { nfsVersion2 11 }

    rename2 OBJECT-TYPE
        SYNTAX Counter32
        MAX-ACCESS read-only
        STATUS obsolete
        DESCRIPTION
            "The total number of 'Rename' calls received for NFS version 2 
             since power up.

             This object is now obsolete, and is replaced with a table
             of values indexed by Cluster Node and name."
        ::= { nfsVersion2 12 }

    link2 OBJECT-TYPE
        SYNTAX Counter32
        MAX-ACCESS read-only
        STATUS obsolete
        DESCRIPTION
            "The total number of 'Link' calls received for NFS version 2 
             since power up.

             This object is now obsolete, and is replaced with a table
             of values indexed by Cluster Node and name."
        ::= { nfsVersion2 13 }

    symLink2 OBJECT-TYPE
        SYNTAX Counter32
        MAX-ACCESS read-only
        STATUS obsolete
        DESCRIPTION
            "The total number of 'Sym Link' calls received for NFS version 2 
             since power up."
        ::= { nfsVersion2 14 }

    mkDir2 OBJECT-TYPE
        SYNTAX Counter32
        MAX-ACCESS read-only
        STATUS obsolete
        DESCRIPTION
            "The total number of 'MkDir' calls received for NFS version 2 
             since power up.

             This object is now obsolete, and is replaced with a table
             of values indexed by Cluster Node and name."
        ::= { nfsVersion2 15 }

    rmDir2 OBJECT-TYPE
        SYNTAX Counter32
        MAX-ACCESS read-only
        STATUS obsolete
        DESCRIPTION
            "The total number of 'RmDir' calls received for NFS version 2 
             since power up.

             This object is now obsolete, and is replaced with a table
             of values indexed by Cluster Node and name."
        ::= { nfsVersion2 16 }

    readDir2 OBJECT-TYPE
        SYNTAX Counter32
        MAX-ACCESS read-only
        STATUS obsolete
        DESCRIPTION
            "The total number of 'ReadDir' calls received for NFS version 2 
             since power up.

             This object is now obsolete, and is replaced with a table
             of values indexed by Cluster Node and name."
        ::= { nfsVersion2 17 }

    statFS2 OBJECT-TYPE
        SYNTAX Counter32
        MAX-ACCESS read-only
        STATUS obsolete
        DESCRIPTION
            "The total number of 'StatFS' calls received for NFS version 2 
             since power up.

             This object is now obsolete, and is replaced with a table
             of values indexed by Cluster Node and name."
        ::= { nfsVersion2 18 }

    nfsV2StatsTable OBJECT-TYPE
        SYNTAX SEQUENCE OF NfsV2StatsEntry
        MAX-ACCESS not-accessible
        STATUS current
        DESCRIPTION
            "The statistics for the NFS version 2 service.

            The number of entries in this table is given by the
            value of clusterPNodeNumber."
        ::= { nfsVersion2 19 }

    nfsV2StatsEntry OBJECT-TYPE
        SYNTAX NfsV2StatsEntry
        MAX-ACCESS not-accessible
        STATUS current
        DESCRIPTION
            "The statistics for the NFS version 2 service."
        INDEX { nfsV2StatsClusterNode }
        ::= { nfsV2StatsTable 1 }

    NfsV2StatsEntry ::=
        SEQUENCE {
            nfsV2StatsClusterNode
                Unsigned32,
            nfsV2nullCalls
                Counter32,
            nfsV2getAttrCalls
                Counter32,
            nfsV2setAttrCalls
                Counter32,
            nfsV2rootCalls
                Counter32,
            nfsV2lookupCalls
                Counter32,
            nfsV2readLink
                Counter32,
            nfsV2read
                Counter32,
            nfsV2writeCache
                Counter32,
            nfsV2write
                Counter32,
            nfsV2create
                Counter32,
            nfsV2remove
                Counter32,
            nfsV2rename
                Counter32,
            nfsV2link
                Counter32,
            nfsV2symLink
                Counter32,
            nfsV2mkDir
                Counter32,
            nfsV2rmDir
                Counter32,
            nfsV2readDir
                Counter32,
            nfsV2statFS
                Counter32
        }

    nfsV2StatsClusterNode OBJECT-TYPE
        SYNTAX Unsigned32
        MAX-ACCESS read-only
        STATUS current
        DESCRIPTION
            "The Cluster Node for this value."
        ::= { nfsV2StatsEntry 1 }

    nfsV2nullCalls OBJECT-TYPE
        SYNTAX Counter32
        MAX-ACCESS read-only
        STATUS current
        DESCRIPTION
            "The total number of 'Null' calls received for NFS version 2 
             since power up."
        ::= { nfsV2StatsEntry 2 }

    nfsV2getAttrCalls OBJECT-TYPE
        SYNTAX Counter32
        MAX-ACCESS read-only
        STATUS current
        DESCRIPTION
            "The total number of 'GetAttr' calls received for NFS version 2 
             since power up."
        ::= { nfsV2StatsEntry 3 }

    nfsV2setAttrCalls OBJECT-TYPE
        SYNTAX Counter32
        MAX-ACCESS read-only
        STATUS current
        DESCRIPTION
            "The total number of 'SetAttr' calls received for NFS version 2 
             since power up."
        ::= { nfsV2StatsEntry 4 }

    nfsV2rootCalls OBJECT-TYPE
        SYNTAX Counter32
        MAX-ACCESS read-only
        STATUS current
        DESCRIPTION
            "The total number of 'Root' calls received since power up
             NOTE: this variable is not used/implemented."
        ::= { nfsV2StatsEntry 5 }

    nfsV2lookupCalls OBJECT-TYPE
        SYNTAX Counter32
        MAX-ACCESS read-only
        STATUS current
        DESCRIPTION
            "The total number of 'Lookup' calls received for NFS version 2 
             since power up."
        ::= { nfsV2StatsEntry 6 }

    nfsV2readLink OBJECT-TYPE
        SYNTAX Counter32
        MAX-ACCESS read-only
        STATUS current
        DESCRIPTION
            "The total number of 'ReadLink' calls received for NFS version 2 
             since power up."
        ::= { nfsV2StatsEntry 7 }

    nfsV2read OBJECT-TYPE
        SYNTAX Counter32
        MAX-ACCESS read-only
        STATUS current
        DESCRIPTION
            "The total number of 'Read' calls received for NFS version 2 
             since power up."
        ::= { nfsV2StatsEntry 8 }

    nfsV2writeCache OBJECT-TYPE
        SYNTAX Counter32
        MAX-ACCESS read-only
        STATUS current
        DESCRIPTION
            "The total number of 'Write Cache' calls received since power up.
             NOTE : this variable is not used/implemented."
        ::= { nfsV2StatsEntry 9 }

    nfsV2write OBJECT-TYPE
        SYNTAX Counter32
        MAX-ACCESS read-only
        STATUS current
        DESCRIPTION
            "The total number of 'Write' calls received for NFS version 2 
             since power up."
        ::= { nfsV2StatsEntry 10 }

    nfsV2create OBJECT-TYPE
        SYNTAX Counter32
        MAX-ACCESS read-only
        STATUS current
        DESCRIPTION
            "The total number of 'Create' calls received for NFS version 2 
             since power up."
        ::= { nfsV2StatsEntry 11 }

    nfsV2remove OBJECT-TYPE
        SYNTAX Counter32
        MAX-ACCESS read-only
        STATUS current
        DESCRIPTION
            "The total number of 'Remove' calls received for NFS version 2 
             since power up."
        ::= { nfsV2StatsEntry 12 }

    nfsV2rename OBJECT-TYPE
        SYNTAX Counter32
        MAX-ACCESS read-only
        STATUS current
        DESCRIPTION
            "The total number of 'Rename' calls received for NFS version 2 
             since power up."
        ::= { nfsV2StatsEntry 13 }

    nfsV2link OBJECT-TYPE
        SYNTAX Counter32
        MAX-ACCESS read-only
        STATUS current
        DESCRIPTION
            "The total number of 'Link' calls received for NFS version 2 
             since power up."
        ::= { nfsV2StatsEntry 14 }

    nfsV2symLink OBJECT-TYPE
        SYNTAX Counter32
        MAX-ACCESS read-only
        STATUS current
        DESCRIPTION
            "The total number of 'Sym Link' calls received for NFS version 2 
             since power up."
        ::= { nfsV2StatsEntry 15 }

    nfsV2mkDir OBJECT-TYPE
        SYNTAX Counter32
        MAX-ACCESS read-only
        STATUS current
        DESCRIPTION
            "The total number of 'MkDir' calls received for NFS version 2 
             since power up."
        ::= { nfsV2StatsEntry 16 }

    nfsV2rmDir OBJECT-TYPE
        SYNTAX Counter32
        MAX-ACCESS read-only
        STATUS current
        DESCRIPTION
            "The total number of 'RmDir' calls received for NFS version 2 
             since power up."
        ::= { nfsV2StatsEntry 17 }

    nfsV2readDir OBJECT-TYPE
        SYNTAX Counter32
        MAX-ACCESS read-only
        STATUS current
        DESCRIPTION
            "The total number of 'ReadDir' calls received for NFS version 2 
             since power up."
        ::= { nfsV2StatsEntry 18 }

    nfsV2statFS OBJECT-TYPE
        SYNTAX Counter32
        MAX-ACCESS read-only
        STATUS current
        DESCRIPTION
            "The total number of 'StatFS' calls received for NFS version 2 
             since power up."
        ::= { nfsV2StatsEntry 19 }

--------------------------------------------------------------------------------
--
-- File Protocol / NFS / Statistics / NFS Version 3
--
--------------------------------------------------------------------------------

    null3Calls OBJECT-TYPE
        SYNTAX Counter32
        MAX-ACCESS read-only
        STATUS obsolete
        DESCRIPTION
            "The total number of 'Null' calls received for NFS version 3 
             since power up.

             This object is now obsolete, and is replaced with a table
             of values indexed by Cluster Node and name."
        ::= { nfsVersion3 1 }

    getAttr3Calls OBJECT-TYPE
        SYNTAX Counter32
        MAX-ACCESS read-only
        STATUS obsolete
        DESCRIPTION
            "The total number of 'GetAttr' calls received for NFS version 3 
             since power up.

             This object is now obsolete, and is replaced with a table
             of values indexed by Cluster Node and name."
        ::= { nfsVersion3 2 }

    setAttr3Calls OBJECT-TYPE
        SYNTAX Counter32
        MAX-ACCESS read-only
        STATUS obsolete
        DESCRIPTION
            "The total number of 'SetAttr' calls received for NFS version 3 
             since power up.

             This object is now obsolete, and is replaced with a table
             of values indexed by Cluster Node and name."
        ::= { nfsVersion3 3 }

    lookup3Calls OBJECT-TYPE
        SYNTAX Counter32
        MAX-ACCESS read-only
        STATUS obsolete
        DESCRIPTION
            "The total number of 'Lookup' calls received for NFS version 3 
             since power up.

             This object is now obsolete, and is replaced with a table
             of values indexed by Cluster Node and name."
        ::= { nfsVersion3 4 }

    access3Calls OBJECT-TYPE
        SYNTAX Counter32
        MAX-ACCESS read-only
        STATUS obsolete
        DESCRIPTION
            "The total number of 'Access' calls received for NFS version 3 
             since power up.

             This object is now obsolete, and is replaced with a table
             of values indexed by Cluster Node and name."
        ::= { nfsVersion3 5 }

    readLink3 OBJECT-TYPE
        SYNTAX Counter32
        MAX-ACCESS read-only
        STATUS obsolete
        DESCRIPTION
            "The total number of 'ReadLink' calls received for NFS version 3 
             since power up.

             This object is now obsolete, and is replaced with a table
             of values indexed by Cluster Node and name."
        ::= { nfsVersion3 6 }

    read3 OBJECT-TYPE
        SYNTAX Counter32
        MAX-ACCESS read-only
        STATUS obsolete
        DESCRIPTION
            "The total number of 'Read' calls received for NFS version 3 
             since power up.

             This object is now obsolete, and is replaced with a table
             of values indexed by Cluster Node and name."
        ::= { nfsVersion3 7 }

    write3 OBJECT-TYPE
        SYNTAX Counter32
        MAX-ACCESS read-only
        STATUS obsolete
        DESCRIPTION
            "The total number of 'Write' calls received for NFS version 3
             since power up.

             This object is now obsolete, and is replaced with a table
             of values indexed by Cluster Node and name."
        ::= { nfsVersion3 8 }

    create3 OBJECT-TYPE
        SYNTAX Counter32
        MAX-ACCESS read-only
        STATUS obsolete
        DESCRIPTION
            "The total number of 'Create' calls received for NFS version 3 
             since power up.

             This object is now obsolete, and is replaced with a table
             of values indexed by Cluster Node and name."
        ::= { nfsVersion3 9 }

    mkdir3 OBJECT-TYPE
        SYNTAX Counter32
        MAX-ACCESS read-only
        STATUS obsolete
        DESCRIPTION
            "The total number of 'MkDir' calls received for NFS version 3
             since power up.

             This object is now obsolete, and is replaced with a table
             of values indexed by Cluster Node and name."
        ::= { nfsVersion3 10 }

    symLink3 OBJECT-TYPE
        SYNTAX Counter32
        MAX-ACCESS read-only
        STATUS obsolete
        DESCRIPTION
            "The total number of 'SymLink' calls received for NFS version 3 
             since power up.

             This object is now obsolete, and is replaced with a table
             of values indexed by Cluster Node and name."
        ::= { nfsVersion3 11 }

    mkNod3 OBJECT-TYPE
        SYNTAX Counter32
        MAX-ACCESS read-only
        STATUS obsolete
        DESCRIPTION
            "The total number of 'MkNod' calls received for NFS version 3
             since power up.

             This object is now obsolete, and is replaced with a table
             of values indexed by Cluster Node and name."
        ::= { nfsVersion3 12 }

    remove3 OBJECT-TYPE
        SYNTAX Counter32
        MAX-ACCESS read-only
        STATUS obsolete
        DESCRIPTION
            "The total number of 'Remove' calls received for NFS version 3 
             since power up.

             This object is now obsolete, and is replaced with a table
             of values indexed by Cluster Node and name."
        ::= { nfsVersion3 13 }

    rmDir3 OBJECT-TYPE
        SYNTAX Counter32
        MAX-ACCESS read-only
        STATUS obsolete
        DESCRIPTION
            "The total number of 'RmDir' calls received for NFS version 3 
             since power up.

             This object is now obsolete, and is replaced with a table
             of values indexed by Cluster Node and name."
        ::= { nfsVersion3 14 }

    rename3 OBJECT-TYPE
        SYNTAX Counter32
        MAX-ACCESS read-only
        STATUS obsolete
        DESCRIPTION
            "The total number of 'Rename' calls received for NFS version 3
             since power up.

             This object is now obsolete, and is replaced with a table
             of values indexed by Cluster Node and name."
        ::= { nfsVersion3 15 }

    link3 OBJECT-TYPE
        SYNTAX Counter32
        MAX-ACCESS read-only
        STATUS obsolete
        DESCRIPTION
            "The total number of 'Link' calls received for NFS version 3 
             since power up.

             This object is now obsolete, and is replaced with a table
             of values indexed by Cluster Node and name."
        ::= { nfsVersion3 16 }

    readDir3 OBJECT-TYPE
        SYNTAX Counter32
        MAX-ACCESS read-only
        STATUS obsolete
        DESCRIPTION
            "The total number of 'ReadDir' calls received for NFS version 3 
             since power up.

             This object is now obsolete, and is replaced with a table
             of values indexed by Cluster Node and name."
        ::= { nfsVersion3 17 }

    readDirPlus3 OBJECT-TYPE
        SYNTAX Counter32
        MAX-ACCESS read-only
        STATUS obsolete
        DESCRIPTION
            "The total number of 'ReadDirPlus' calls received for NFS version 3 
             since power up.

             This object is now obsolete, and is replaced with a table
             of values indexed by Cluster Node and name."
        ::= { nfsVersion3 18 }

    fsStat3 OBJECT-TYPE
        SYNTAX Counter32
        MAX-ACCESS read-only
        STATUS obsolete
        DESCRIPTION
            "The total number of 'FSStat' calls received for NFS version 3
             since power up.

             This object is now obsolete, and is replaced with a table
             of values indexed by Cluster Node and name."
        ::= { nfsVersion3 19 }

    fsInfo3 OBJECT-TYPE
        SYNTAX Counter32
        MAX-ACCESS read-only
        STATUS obsolete
        DESCRIPTION
            "The total number of 'FSInfo' calls received for NFS version 3 
             since power up.

             This object is now obsolete, and is replaced with a table
             of values indexed by Cluster Node and name."
        ::= { nfsVersion3 20 }

    pathConf3 OBJECT-TYPE
        SYNTAX Counter32
        MAX-ACCESS read-only
        STATUS obsolete
        DESCRIPTION
            "The total number of 'PathConf' calls received for NFS version 3 
             since power up.

             This object is now obsolete, and is replaced with a table
             of values indexed by Cluster Node and name."
        ::= { nfsVersion3 21 }

    commit3 OBJECT-TYPE
        SYNTAX Counter32
        MAX-ACCESS read-only
        STATUS obsolete
        DESCRIPTION
            "The total number of 'Commit' calls received for NFS version 3 
             since power up.

             This object is now obsolete, and is replaced with a table
             of values indexed by Cluster Node and name."
        ::= { nfsVersion3 22 }

    nfsV3StatsTable OBJECT-TYPE
        SYNTAX SEQUENCE OF NfsV3StatsEntry
        MAX-ACCESS not-accessible
        STATUS current
        DESCRIPTION
            "The statistics for the NFS version 3 service.

            The number of entries in this table is given by the
            value of clusterPNodeNumber."
        ::= { nfsVersion3 23 }

    nfsV3StatsEntry OBJECT-TYPE
        SYNTAX NfsV3StatsEntry
        MAX-ACCESS not-accessible
        STATUS current
        DESCRIPTION
            "The statistics for the NFS version 3 service."
        INDEX { nfsV3StatsClusterNode }
        ::= { nfsV3StatsTable 1 }

    NfsV3StatsEntry ::=
        SEQUENCE {
            nfsV3StatsClusterNode
                Unsigned32,
            nfsV3nullCalls
                Counter32,
            nfsV3getAttrCalls
                Counter32,
            nfsV3setAttrCalls
                Counter32,
            nfsV3lookupCalls
                Counter32,
            nfsV3accessCalls
                Counter32,
            nfsV3readLink
                Counter32,
            nfsV3read
                Counter32,
            nfsV3write
                Counter32,
            nfsV3create
                Counter32,
            nfsV3mkdir
                Counter32,
            nfsV3symLink
                Counter32,
            nfsV3mkNod
                Counter32,
            nfsV3remove
                Counter32,
            nfsV3rmDir
                Counter32,
            nfsV3rename
                Counter32,
            nfsV3link       
                Counter32,
            nfsV3readDir
                Counter32,
            nfsV3readDirPlus
                Counter32,
            nfsV3fsStat
                Counter32,
            nfsV3fsInfo
                Counter32,
            nfsV3pathConf
                Counter32,
            nfsV3commit
                Counter32
        }

    nfsV3StatsClusterNode OBJECT-TYPE
        SYNTAX Unsigned32
        MAX-ACCESS read-only
        STATUS current
        DESCRIPTION
            "The Cluster Node for this value."
        ::= { nfsV3StatsEntry 1 }

    nfsV3nullCalls OBJECT-TYPE
        SYNTAX Counter32
        MAX-ACCESS read-only
        STATUS current
        DESCRIPTION
            "The total number of 'Null' calls received for NFS version 3 
             since power up."
        ::= { nfsV3StatsEntry 2 }

    nfsV3getAttrCalls OBJECT-TYPE
        SYNTAX Counter32
        MAX-ACCESS read-only
        STATUS current
        DESCRIPTION
            "The total number of 'GetAttr' calls received for NFS version 3 
             since power up."
        ::= { nfsV3StatsEntry 3 }

    nfsV3setAttrCalls OBJECT-TYPE
        SYNTAX Counter32
        MAX-ACCESS read-only
        STATUS current
        DESCRIPTION
            "The total number of 'SetAttr' calls received for NFS version 3 
             since power up."
        ::= { nfsV3StatsEntry 4 }

    nfsV3lookupCalls OBJECT-TYPE
        SYNTAX Counter32
        MAX-ACCESS read-only
        STATUS current
        DESCRIPTION
            "The total number of 'Lookup' calls received for NFS version 3 
             since power up."
        ::= { nfsV3StatsEntry 5 }

    nfsV3accessCalls OBJECT-TYPE
        SYNTAX Counter32
        MAX-ACCESS read-only
        STATUS current
        DESCRIPTION
            "The total number of 'Access' calls received for NFS version 3 
             since power up."
        ::= { nfsV3StatsEntry 6 }

    nfsV3readLink OBJECT-TYPE
        SYNTAX Counter32
        MAX-ACCESS read-only
        STATUS current
        DESCRIPTION
            "The total number of 'ReadLink' calls received for NFS version 3 
             since power up."
        ::= { nfsV3StatsEntry 7 }

    nfsV3read OBJECT-TYPE
        SYNTAX Counter32
        MAX-ACCESS read-only
        STATUS current
        DESCRIPTION
            "The total number of 'Read' calls received for NFS version 3 
             since power up."
        ::= { nfsV3StatsEntry 8 }

    nfsV3write OBJECT-TYPE
        SYNTAX Counter32
        MAX-ACCESS read-only
        STATUS current
        DESCRIPTION
            "The total number of 'Write' calls received for NFS version 3
             since power up."
        ::= { nfsV3StatsEntry 9 }

    nfsV3create OBJECT-TYPE
        SYNTAX Counter32
        MAX-ACCESS read-only
        STATUS current
        DESCRIPTION
            "The total number of 'Create' calls received for NFS version 3 
             since power up."
        ::= { nfsV3StatsEntry 10 }

    nfsV3mkdir OBJECT-TYPE
        SYNTAX Counter32
        MAX-ACCESS read-only
        STATUS current
        DESCRIPTION
            "The total number of 'MkDir' calls received for NFS version 3
             since power up."
        ::= { nfsV3StatsEntry 11 }

    nfsV3symLink OBJECT-TYPE
        SYNTAX Counter32
        MAX-ACCESS read-only
        STATUS current
        DESCRIPTION
            "The total number of 'SymLink' calls received for NFS version 3 
             since power up."
        ::= { nfsV3StatsEntry 12 }

    nfsV3mkNod OBJECT-TYPE
        SYNTAX Counter32
        MAX-ACCESS read-only
        STATUS current
        DESCRIPTION
            "The total number of 'MkNod' calls received for NFS version 3
             since power up."
        ::= { nfsV3StatsEntry 13 }

    nfsV3remove OBJECT-TYPE
        SYNTAX Counter32
        MAX-ACCESS read-only
        STATUS current
        DESCRIPTION
            "The total number of 'Remove' calls received for NFS version 3 
             since power up."
        ::= { nfsV3StatsEntry 14 }

    nfsV3rmDir OBJECT-TYPE
        SYNTAX Counter32
        MAX-ACCESS read-only
        STATUS current
        DESCRIPTION
            "The total number of 'RmDir' calls received for NFS version 3 
             since power up."
        ::= { nfsV3StatsEntry 15 }

    nfsV3rename OBJECT-TYPE
        SYNTAX Counter32
        MAX-ACCESS read-only
        STATUS current
        DESCRIPTION
            "The total number of 'Rename' calls received for NFS version 3
             since power up."
        ::= { nfsV3StatsEntry 16 }

    nfsV3link OBJECT-TYPE
        SYNTAX Counter32
        MAX-ACCESS read-only
        STATUS current
        DESCRIPTION
            "The total number of 'Link' calls received for NFS version 3 
             since power up."
        ::= { nfsV3StatsEntry 17 }

    nfsV3readDir OBJECT-TYPE
        SYNTAX Counter32
        MAX-ACCESS read-only
        STATUS current
        DESCRIPTION
            "The total number of 'ReadDir' calls received for NFS version 3 
             since power up."
        ::= { nfsV3StatsEntry 18 }

    nfsV3readDirPlus OBJECT-TYPE
        SYNTAX Counter32
        MAX-ACCESS read-only
        STATUS current
        DESCRIPTION
            "The total number of 'ReadDirPlus' calls received for NFS version 3 
             since power up."
        ::= { nfsV3StatsEntry 19 }

    nfsV3fsStat OBJECT-TYPE
        SYNTAX Counter32
        MAX-ACCESS read-only
        STATUS current
        DESCRIPTION
            "The total number of 'FSStat' calls received for NFS version 3
             since power up."
        ::= { nfsV3StatsEntry 20 }

    nfsV3fsInfo OBJECT-TYPE
        SYNTAX Counter32
        MAX-ACCESS read-only
        STATUS current
        DESCRIPTION
            "The total number of 'FSInfo' calls received for NFS version 3 
             since power up."
        ::= { nfsV3StatsEntry 21 }

    nfsV3pathConf OBJECT-TYPE
        SYNTAX Counter32
        MAX-ACCESS read-only
        STATUS current
        DESCRIPTION
            "The total number of 'PathConf' calls received for NFS version 3 
             since power up."
        ::= { nfsV3StatsEntry 22 }

    nfsV3commit OBJECT-TYPE
        SYNTAX Counter32
        MAX-ACCESS read-only
        STATUS current
        DESCRIPTION
            "The total number of 'Commit' calls received for NFS version 3 
             since power up."
        ::= { nfsV3StatsEntry 23 }

--------------------------------------------------------------------------------
--
-- File Protocol / NFS / Statistics
--
--------------------------------------------------------------------------------

    nfsMounts OBJECT-TYPE
        SYNTAX Counter32
        MAX-ACCESS read-only
        STATUS obsolete
        DESCRIPTION
            "The total number of NFS mounts since power up.
             
             This object is obsolete.  It could not be measured."
        ::= { nfsStats 3 }

    nfsClients OBJECT-TYPE
        SYNTAX Counter32
        MAX-ACCESS read-only
        STATUS obsolete
        DESCRIPTION
            "The total number of NFS clients since power up.

             This object is obsolete.  It could not be measured."
        ::= { nfsStats 4 }

--------------------------------------------------------------------------------
--
-- File Protocol / NFS / NFS Service Configuration
--
--------------------------------------------------------------------------------

    nfsServiceEnabled OBJECT-TYPE
        SYNTAX INTEGER {
            enabled(1),
            disabled(2),
            unknown(3)
        }
        MAX-ACCESS read-only
        STATUS current
        DESCRIPTION
            "Indicates whether the NFS service is enabled or not."
        ::= { nfsService 1 }

    nfsServiceMaxUsers OBJECT-TYPE
        SYNTAX Unsigned32
        MAX-ACCESS read-only
        STATUS current
        DESCRIPTION
            "The maximum number of NFS users the service will allow."
        ::= { nfsService 2 }

--------------------------------------------------------------------------------
--
-- File Protocol / FTP
--
--------------------------------------------------------------------------------

    ftpTimeout OBJECT-TYPE
        SYNTAX Integer32
        MAX-ACCESS read-only
        STATUS obsolete
        DESCRIPTION
            "The FTP session timeout in minutes.
             NOTE: this value applies to all FTP sessions.

            This object is obsolete."
        ::= { ftp 1 }

    ftpMountNumber OBJECT-TYPE
        SYNTAX Integer32
        MAX-ACCESS read-only
        STATUS obsolete
        DESCRIPTION
            "The number of FTP mount points which are configured
             for the system.

            This object is obsolete."
        ::= { ftpMountPoints 1 }

    ftpMountTable OBJECT-TYPE
        SYNTAX SEQUENCE OF FtpMountEntry
        MAX-ACCESS not-accessible
        STATUS obsolete
        DESCRIPTION
            "A table containing the FTP mount point configuration for the
             system.

             The number of entries in this table is given by the value of 
             ftpMountNumber.

            This object is obsolete."
        ::= { ftpMountPoints 2 }

    ftpMountEntry OBJECT-TYPE
        SYNTAX FtpMountEntry
        MAX-ACCESS not-accessible
        STATUS obsolete
        DESCRIPTION
            "FTP mount point information.

            This object is obsolete."
        INDEX { ftpMountName }
        ::= { ftpMountTable 1 }

    FtpMountEntry ::=
        SEQUENCE {
            ftpMountName
                DisplayString,
            ftpMountNumberUsers
                Unsigned32,
            ftpMountWWN
                DisplayString,
            ftpMountLUN
                Unsigned32,
            ftpMountPartitionID
                Unsigned32
        }

    ftpMountName OBJECT-TYPE
        SYNTAX DisplayString
        MAX-ACCESS read-only
        STATUS obsolete
        DESCRIPTION
            "The name of the FTP mount point.  Each FTP mount point
             has a unique name.

            This object is obsolete."
        ::= { ftpMountEntry 1 }

    ftpMountNumberUsers OBJECT-TYPE
        SYNTAX Unsigned32
        MAX-ACCESS read-only
        STATUS obsolete
        DESCRIPTION
            "The number of users of the FTP mount point.

            This object is obsolete."
        ::= { ftpMountEntry 2 }

    ftpMountWWN OBJECT-TYPE
        SYNTAX DisplayString
        MAX-ACCESS read-only
        STATUS obsolete
        DESCRIPTION
            "The world wide name (WWN) of the system drive the 
             FTP mount point is associated with.

            This object is obsolete."
        ::= { ftpMountEntry 3 }

    ftpMountLUN OBJECT-TYPE
        SYNTAX Unsigned32
        MAX-ACCESS read-only
        STATUS obsolete
        DESCRIPTION
            "The logical unit number (LUN) of the system drive
             the FTP mount point is associated with.

            This object is obsolete."
        ::= { ftpMountEntry 4 }

    ftpMountPartitionID OBJECT-TYPE
        SYNTAX Unsigned32
        MAX-ACCESS read-only
        STATUS obsolete
        DESCRIPTION
            "The partition ID of the volume the FTP mount point
             is associated with.

            This object is obsolete."
        ::= { ftpMountEntry 5 }

--------------------------------------------------------------------------------
--
-- File Protocol / FTP / FTP Users
--
--------------------------------------------------------------------------------

    ftpUserNumber OBJECT-TYPE
        SYNTAX Integer32
        MAX-ACCESS read-only
        STATUS obsolete
        DESCRIPTION
            "The number of FTP users which are configured for the system.

            This object is obsolete."
        ::= { ftpUsers 1 }

    ftpUserTable OBJECT-TYPE
        SYNTAX SEQUENCE OF FtpUserEntry
        MAX-ACCESS not-accessible
        STATUS obsolete
        DESCRIPTION
            "A table containing the FTP user configuration for the
             system.

             The number of entries in this table is given by the value of
             ftpUserNumber.

            This object is obsolete."
        ::= { ftpUsers 2 }

    ftpUserEntry OBJECT-TYPE
        SYNTAX FtpUserEntry
        MAX-ACCESS not-accessible
        STATUS obsolete
        DESCRIPTION
            "FTP user information.

            This object is obsolete."
        INDEX { ftpUserName }
        ::= { ftpUserTable 1 }

    FtpUserEntry ::=
        SEQUENCE {
            ftpUserName
                DisplayString,
            ftpUserMountPointExists
                INTEGER,
            ftpUserMountPoint
                DisplayString,
            ftpUserMountInitDirectory
                DisplayString
        }

    ftpUserName OBJECT-TYPE
        SYNTAX DisplayString
        MAX-ACCESS read-only
        STATUS obsolete
        DESCRIPTION
            "The name of the FTP user.

            This object is obsolete."
        ::= { ftpUserEntry 1 }

    ftpUserMountPointExists OBJECT-TYPE
        SYNTAX INTEGER {
            exists(1),
            doesnotExist(2)
        }
        MAX-ACCESS read-only
        STATUS obsolete
        DESCRIPTION
            "Indicates whether the FTP mount point is configured in
             the ftpMountTable.

            This object is obsolete."
        ::= { ftpUserEntry 2 }

    ftpUserMountPoint OBJECT-TYPE
        SYNTAX DisplayString
        MAX-ACCESS read-only
        STATUS obsolete
        DESCRIPTION
            "The name of the FTP users mount point.

            This object is obsolete."
        ::= { ftpUserEntry 3 }

    ftpUserMountInitDirectory OBJECT-TYPE
        SYNTAX DisplayString
        MAX-ACCESS read-only
        STATUS obsolete
        DESCRIPTION
            "The FTP users initial directory.

            This object is obsolete."
        ::= { ftpUserEntry 4 }

--------------------------------------------------------------------------------
--
-- File Protocol / FTP / FTP Audit Logging
--
--------------------------------------------------------------------------------

    ftpAuditLogging OBJECT-TYPE
        SYNTAX INTEGER {
            enabled(1),
            disabled(2)
        }
        MAX-ACCESS read-only
        STATUS obsolete
        DESCRIPTION
            "Indicates whether FTP Audit logging is enabled or not.

            This object is obsolete."
        ::= { ftpLogging 1 }

    ftpAuditLogVolumeWWN OBJECT-TYPE
        SYNTAX DisplayString
        MAX-ACCESS read-only
        STATUS obsolete
        DESCRIPTION
            "The world wide name (WWN) of the system drive the FTP 
             server is to write the audit log to.

            This object is obsolete."
        ::= { ftpLogging 2 }

    ftpAuditLogVolumeLUN OBJECT-TYPE
        SYNTAX Unsigned32
        MAX-ACCESS read-only
        STATUS obsolete
        DESCRIPTION
            "The logical unit number (LUN) of the system drive the
             FTP server is to write the audit log to.

            This object is obsolete."
        ::= { ftpLogging 3 }

    ftpAuditLogVolumePartitionID OBJECT-TYPE
        SYNTAX Unsigned32
        MAX-ACCESS read-only
        STATUS obsolete
        DESCRIPTION
            "The partition ID of the volume the FTP server is to
             write the audit log to.

            This object is obsolete."
        ::= { ftpLogging 4 }

    ftpAuditLogDirectory OBJECT-TYPE
        SYNTAX DisplayString
        MAX-ACCESS read-only
        STATUS obsolete
        DESCRIPTION
            "The directory the FTP server is to write the audit log to.

            This object is obsolete."
        ::= { ftpLogging 5 }

    ftpAuditLogRecordsPerFile OBJECT-TYPE
        SYNTAX Unsigned32
        MAX-ACCESS read-only
        STATUS obsolete
        DESCRIPTION
            "The number of records in each audit log file.

            This object is obsolete."
        ::= { ftpLogging 6 }

    ftpAuditMaximumLogFiles OBJECT-TYPE
        SYNTAX Unsigned32
        MAX-ACCESS read-only
        STATUS obsolete
        DESCRIPTION
            "The maximum number of audit log files.

            This object is obsolete."
        ::= { ftpLogging 7 }

--------------------------------------------------------------------------------
--
-- File Protocol / FTP / FTP Statistics
--
--------------------------------------------------------------------------------

    ftpTotalSess OBJECT-TYPE
        SYNTAX Counter32
        MAX-ACCESS read-only
        STATUS obsolete
        DESCRIPTION
            "The total number of FTP sessions since power up.

            This object is obsolete."
        ::= { ftpStats 1 }

    ftpTotalFtpXferIn OBJECT-TYPE
        SYNTAX Counter32
        MAX-ACCESS read-only
        STATUS obsolete
        DESCRIPTION
            "The total number of data transfers (files) in since power up.

            This object is obsolete."
        ::= { ftpStats 2 }

    ftpBytesTotalXferIn OBJECT-TYPE
        SYNTAX Counter64
        MAX-ACCESS read-only
        STATUS obsolete
        DESCRIPTION
            "The total number of data bytes transferred in since power up.

            This object is obsolete."
        ::= { ftpStats 3 }

    ftpTotalFtpXferOut OBJECT-TYPE
        SYNTAX Counter32
        MAX-ACCESS read-only
        STATUS obsolete
        DESCRIPTION
            "The total number of data transfers (files) out since power up.

            This object is obsolete."
        ::= { ftpStats 4 }

    ftpBytesTotalXferOut OBJECT-TYPE
        SYNTAX Counter64
        MAX-ACCESS read-only
        STATUS obsolete
        DESCRIPTION
            "The total number of data bytes transferred out since power up.

            This object is obsolete."
        ::= { ftpStats 5 }

    ftpTotalFtpCommands OBJECT-TYPE
        SYNTAX Counter32
        MAX-ACCESS read-only
        STATUS obsolete
        DESCRIPTION
            "The total number of commands issued from clients since power up.

            This object is obsolete."
        ::= { ftpStats 6 }

    ftpTotalFtpReplies OBJECT-TYPE
        SYNTAX Counter32
        MAX-ACCESS read-only
        STATUS obsolete
        DESCRIPTION
            "The total number of replies sent to clients since power up.

            This object is obsolete."
        ::= { ftpStats 7 }

    ftpTotalBytesCommands OBJECT-TYPE
        SYNTAX Counter64
        MAX-ACCESS read-only
        STATUS obsolete
        DESCRIPTION
            "The total number of bytes received in commands since power up.

            This object is obsolete."
        ::= { ftpStats 8 }

    ftpTotalBytesReplies OBJECT-TYPE
        SYNTAX Counter64
        MAX-ACCESS read-only
        STATUS obsolete
        DESCRIPTION
            "The total number of bytes set in replies since power up.

            This object is obsolete."
        ::= { ftpStats 9 }

--------------------------------------------------------------------------------
--
-- File Protocol / FTP / FTP Service Configuration
--
--------------------------------------------------------------------------------

    ftpServiceEnabled OBJECT-TYPE
        SYNTAX INTEGER {
            enabled(1),
            disabled(2)
        }
        MAX-ACCESS read-only
        STATUS obsolete
        DESCRIPTION
            "Indicates whether the FTP service is enabled or not.

            This object is obsolete."
        ::= { ftpService 1 }

    ftpServiceMaxUsers OBJECT-TYPE
        SYNTAX Unsigned32
        MAX-ACCESS read-only
        STATUS obsolete
        DESCRIPTION
            "The maximum number of FTP users the service will allow.

            This object is obsolete."
        ::= { ftpService 2 }

--------------------------------------------------------------------------------
--
-- File Protocol / FTP / FTP Security
--
--------------------------------------------------------------------------------

    ftpNTPasswordEnabled OBJECT-TYPE
        SYNTAX INTEGER {
            enabled(1),
            disabled(2),
            unknown(3)
        }
        MAX-ACCESS read-only
        STATUS obsolete
        DESCRIPTION
            "Indicates whether FTP uses NT password authentication
             or not.

            This object is obsolete."
        ::= { ftpSecurity 1 }

    ftpNISPasswordEnabled OBJECT-TYPE
        SYNTAX INTEGER {
            enabled(1),
            disabled(2),
            unknown(3)
        }
        MAX-ACCESS read-only
        STATUS obsolete
        DESCRIPTION
            "Indicates whether FTP uses NIS password authentication
             or not.

            This object is obsolete."
        ::= { ftpSecurity 2 }

--------------------------------------------------------------------------------
--
-- File Protocol / HTTP / HTTP Configuration
--
--------------------------------------------------------------------------------

    httpHostVolumeWWN OBJECT-TYPE
        SYNTAX DisplayString
        MAX-ACCESS read-only
        STATUS obsolete
        DESCRIPTION
            "The world wide name (WWN) of the system drive the
             HTTP server is hosting.

             This object is now obsolete as no HTTP server is
             present."
        ::= { httpConfig 1 }

    httpHostVolumeLUN OBJECT-TYPE
        SYNTAX Unsigned32
        MAX-ACCESS read-only
        STATUS obsolete
        DESCRIPTION
            "The logical unit number (LUN) of the system drive the
             HTTP server is hosting.

             This object is now obsolete as no HTTP server is
             present."
        ::= { httpConfig 2 }

    httpHostVolumePartitionID OBJECT-TYPE
        SYNTAX Unsigned32
        MAX-ACCESS read-only
        STATUS obsolete
        DESCRIPTION
            "The partition ID of the volume the HTTP server is hosting.

             This object is now obsolete as no HTTP server is
             present."
        ::= { httpConfig 3 }

    httpRoot OBJECT-TYPE
        SYNTAX DisplayString
        MAX-ACCESS read-only
        STATUS obsolete
        DESCRIPTION
            "The root directory the HTTP server is hosting.

             This object is now obsolete as no HTTP server is
             present."
        ::= { httpConfig 4 }

    httpProduct OBJECT-TYPE
        SYNTAX DisplayString
        MAX-ACCESS read-only
        STATUS obsolete
        DESCRIPTION
            "The product string used by the HTTP server.

             This object is now obsolete as no HTTP server is
             present."
        ::= { httpConfig 5 }

    httpMinTimeOut OBJECT-TYPE
        SYNTAX Unsigned32
        MAX-ACCESS read-only
        STATUS obsolete
        DESCRIPTION
            "The minimum timeout used by the HTTP server
             in milliseconds.

             This object is now obsolete as no HTTP server is
             present."
        ::= { httpConfig 6 }

    httpMaxTimeOut OBJECT-TYPE
        SYNTAX Unsigned32
        MAX-ACCESS read-only
        STATUS obsolete
        DESCRIPTION
            "The maximum timeout used by the HTTP server
             in milliseconds.

             This object is now obsolete as no HTTP server is
             present."
        ::= { httpConfig 7 }

    httpDecrTimeOut OBJECT-TYPE
        SYNTAX Unsigned32
        MAX-ACCESS read-only
        STATUS obsolete
        DESCRIPTION
            "The time the HTTP server uses to decrement the timeout on
             client connection in milliseconds.

             This object is now obsolete as no HTTP server is
             present."
        ::= { httpConfig 8 }

    httpIncrTimeOut OBJECT-TYPE
        SYNTAX Unsigned32
        MAX-ACCESS read-only
        STATUS obsolete
        DESCRIPTION
            "The time the HTTP server uses to increment the timeout on a
             valid incoming request.

             This object is now obsolete as no HTTP server is
             present."
        ::= { httpConfig 9 }

    httpMaxConnections OBJECT-TYPE
        SYNTAX Unsigned32
        MAX-ACCESS read-only
        STATUS obsolete
        DESCRIPTION
            "The maximum number of connections allowed by the HTTP
             server.

             This object is now obsolete as no HTTP server is
             present."
        ::= { httpConfig 10 }

    httpListDirectories OBJECT-TYPE
        SYNTAX INTEGER {
            enabled(1),
            disabled(2)
        }
        MAX-ACCESS read-only
        STATUS obsolete
        DESCRIPTION
            "Indicates whether the HTTP server list directories option
             is enabled or not.

             This object is now obsolete as no HTTP server is
             present."
        ::= { httpConfig 11 }

    httpLogging OBJECT-TYPE
        SYNTAX INTEGER {
            enabled(1),
            disabled(2)
        }
        MAX-ACCESS read-only
        STATUS obsolete
        DESCRIPTION
            "Indicates whether HTTP server logging is enabled or not.

             This object is now obsolete as no HTTP server is
             present."
        ::= { httpConfig 12 }

    httpMaximalLogging OBJECT-TYPE
        SYNTAX INTEGER {
            enabled(1),
            disabled(2)
        }
        MAX-ACCESS read-only
        STATUS obsolete
        DESCRIPTION
            "Indicates whether maximal logging is enabled
             or not for the HTTP server.

             This object is now obsolete as no HTTP server is
             present."
        ::= { httpConfig 13 }

    httpLogVolumeWWN OBJECT-TYPE
        SYNTAX DisplayString
        MAX-ACCESS read-only
        STATUS obsolete
        DESCRIPTION
            "The world wide name (WWN) of the system drive the 
             HTTP server is logging to.

             This object is now obsolete as no HTTP server is
             present."
        ::= { httpConfig 14 }

    httpLogVolumeLUN OBJECT-TYPE
        SYNTAX Unsigned32
        MAX-ACCESS read-only
        STATUS obsolete
        DESCRIPTION
            "The logical unit number (LUN) of the system drive
             the HTTP server is logging to.

             This object is now obsolete as no HTTP server is
             present."
        ::= { httpConfig 15 }

    httpLogVolumePartitionID OBJECT-TYPE
        SYNTAX Unsigned32
        MAX-ACCESS read-only
        STATUS obsolete
        DESCRIPTION
            "The partition ID of the volume the HTTP server is logging to.

             This object is now obsolete as no HTTP server is
             present."
        ::= { httpConfig 16 }

    httpLogDirectory OBJECT-TYPE
        SYNTAX DisplayString
        MAX-ACCESS read-only
        STATUS obsolete
        DESCRIPTION
            "The name of the directory the HTTP server is logging to.

             This object is now obsolete as no HTTP server is
             present."
        ::= { httpConfig 17 }

    httpLogRecordsPerFile OBJECT-TYPE
        SYNTAX Unsigned32
        MAX-ACCESS read-only
        STATUS obsolete
        DESCRIPTION
            "The number of records per log file the HTTP server
             will generate during logging.

             This object is now obsolete as no HTTP server is
             present."
        ::= { httpConfig 18 }

    httpMaximumLogFiles OBJECT-TYPE
        SYNTAX Unsigned32
        MAX-ACCESS read-only
        STATUS obsolete
        DESCRIPTION
            "The maximum number of log files the HTTP server will
             generate during logging.

             This object is now obsolete as no HTTP server is
             present."
        ::= { httpConfig 19 }

    httpMimeMapNumber OBJECT-TYPE
        SYNTAX Integer32
        MAX-ACCESS read-only
        STATUS obsolete
        DESCRIPTION
            "The number of mime map entries configured for the HTTP server.

             This object is now obsolete as no HTTP server is
             present."
        ::= { httpConfig 20 }

    httpMimeMapTable OBJECT-TYPE
        SYNTAX SEQUENCE OF HttpMimeMapEntry
        MAX-ACCESS not-accessible
        STATUS obsolete
        DESCRIPTION
            "A table containing the mime map configuration for the
             HTTP server in the system.

             The number of entries in this table is given by the value of 
             httpMimeMapNumber.

             This object is now obsolete as no HTTP server is
             present."
        ::= { httpConfig 21 }

    httpMimeMapEntry OBJECT-TYPE
        SYNTAX HttpMimeMapEntry
        MAX-ACCESS not-accessible
        STATUS obsolete
        DESCRIPTION
            "Mime map information.

             This object is now obsolete as no HTTP server is
             present."
        INDEX { httpMimeMapIndex }
        ::= { httpMimeMapTable 1 }

    HttpMimeMapEntry ::=
        SEQUENCE {
            httpMimeMapIndex
                Integer32,
            httpMimeMapExtension
                DisplayString,
            httpMimeMapType
                DisplayString
        }

    httpMimeMapIndex OBJECT-TYPE
        SYNTAX Integer32 (1..150)
        MAX-ACCESS read-only
        STATUS obsolete
        DESCRIPTION
            "A unique value for each mime map configured for the
             HTTP server in this system.

             Its value ranges between 1 and the value of httpMimeMapNumber.

             This object is now obsolete as no HTTP server is
             present."
        ::= { httpMimeMapEntry 1 }

    httpMimeMapExtension OBJECT-TYPE
        SYNTAX DisplayString
        MAX-ACCESS read-only
        STATUS obsolete
        DESCRIPTION
            "The extension on the file.

             This object is now obsolete as no HTTP server is
             present."
        ::= { httpMimeMapEntry 2 }

    httpMimeMapType OBJECT-TYPE
        SYNTAX DisplayString
        MAX-ACCESS read-only
        STATUS obsolete
        DESCRIPTION
            "The corresponding type the extension maps to.

             This object is now obsolete as no HTTP server is
             present."
        ::= { httpMimeMapEntry 3 }

--------------------------------------------------------------------------------
--
-- File Protocol / HTTP / HTTP Statistics
--
--------------------------------------------------------------------------------

    httpConnsAccepted OBJECT-TYPE
        SYNTAX Counter64
        MAX-ACCESS read-only
        STATUS obsolete
        DESCRIPTION
            "The number of TCP/IP connections that clients have 
             made to the server.  Clients running HTTP/1.1 can make 
             multiple requests per connection, and so this number will
             typically be lower that the total number of requests.

             This object is now obsolete as no HTTP server is
             present."
        ::= { httpStats 1 }

    httpConnsRefused OBJECT-TYPE
        SYNTAX Counter64
        MAX-ACCESS read-only
        STATUS obsolete
        DESCRIPTION
            "The total number of connections that were rejected 
             with a '503 Service Unavailable' message.

             This object is now obsolete as no HTTP server is
             present."
        ::= { httpStats 2 }

    httpBytesXferOut OBJECT-TYPE
        SYNTAX Counter64
        MAX-ACCESS read-only
        STATUS obsolete
        DESCRIPTION
            "The number of bytes sent by the server.  
             This includes output HTTP headers.

             This object is now obsolete as no HTTP server is
             present."
        ::= { httpStats 3 }

    httpBytesXferIn OBJECT-TYPE
        SYNTAX Counter64
        MAX-ACCESS read-only
        STATUS obsolete
        DESCRIPTION
            "The number of bytes received by the server.

             This object is now obsolete as no HTTP server is
             present."
        ::= { httpStats 4 }

    httpGetRequests OBJECT-TYPE
        SYNTAX Counter64
        MAX-ACCESS read-only
        STATUS obsolete
        DESCRIPTION
            "The number of GET requests received.

             This object is now obsolete as no HTTP server is
             present."
        ::= { httpStats 5 }

    httpHeadRequests OBJECT-TYPE
        SYNTAX Counter64
        MAX-ACCESS read-only
        STATUS obsolete
        DESCRIPTION
            "The number of HEAD requests received.

             This object is now obsolete as no HTTP server is
             present."
        ::= { httpStats 6 }

    httpPutRequests OBJECT-TYPE
        SYNTAX Counter64
        MAX-ACCESS read-only
        STATUS obsolete
        DESCRIPTION
            "The number of PUT requests received.

             This object is now obsolete as no HTTP server is
             present."
        ::= { httpStats 7 }

    httpPostRequests OBJECT-TYPE
        SYNTAX Counter64
        MAX-ACCESS read-only
        STATUS obsolete
        DESCRIPTION
            "The number of POST requests received.

             This object is now obsolete as no HTTP server is
             present."
        ::= { httpStats 8 }

    httpStatusOK OBJECT-TYPE
        SYNTAX Counter64
        MAX-ACCESS read-only
        STATUS obsolete
        DESCRIPTION
            "The number of 200 OK status replies.

             This object is now obsolete as no HTTP server is
             present."
        ::= { httpStats 9 }

    httpStatusNotModified OBJECT-TYPE
        SYNTAX Counter64
        MAX-ACCESS read-only
        STATUS obsolete
        DESCRIPTION
            "The number of 304 Not Modified status replies.

             This object is now obsolete as no HTTP server is
             present."
        ::= { httpStats 10 }

    httpStatusPreconFailed OBJECT-TYPE
        SYNTAX Counter64
        MAX-ACCESS read-only
        STATUS obsolete
        DESCRIPTION
            "The number of 412 Precondition Failed status replies.

             This object is now obsolete as no HTTP server is
             present."
        ::= { httpStats 11 }

    httpStatusBadRequest OBJECT-TYPE
        SYNTAX Counter64
        MAX-ACCESS read-only
        STATUS obsolete
        DESCRIPTION
            "The number of 400 Bad Request status replies.

             This object is now obsolete as no HTTP server is
             present."
        ::= { httpStats 12 }

    httpStatusForbidden OBJECT-TYPE
        SYNTAX Counter64
        MAX-ACCESS read-only
        STATUS obsolete
        DESCRIPTION
            "The number of 403 Forbidden status replies.

             This object is now obsolete as no HTTP server is
             present."
        ::= { httpStats 13 }

    httpStatusNotFound OBJECT-TYPE
        SYNTAX Counter64
        MAX-ACCESS read-only
        STATUS obsolete
        DESCRIPTION
            "The number of 404 Not Found status replies.

             This object is now obsolete as no HTTP server is
             present."
        ::= { httpStats 14 }

    httpStatusURITooLong OBJECT-TYPE
        SYNTAX Counter64
        MAX-ACCESS read-only
        STATUS obsolete
        DESCRIPTION
            "The number of 414 URI Too Long status replies.

             This object is now obsolete as no HTTP server is
             present."
        ::= { httpStats 15 }

    httpStatusServerError OBJECT-TYPE
        SYNTAX Counter64
        MAX-ACCESS read-only
        STATUS obsolete
        DESCRIPTION
            "The number of 500 Server Error status replies.

             This object is now obsolete as no HTTP server is
             present."
        ::= { httpStats 16 }

    httpStatusNotImplemented OBJECT-TYPE
        SYNTAX Counter64
        MAX-ACCESS read-only
        STATUS obsolete
        DESCRIPTION
            "The number of 501 Not Implemented status replies.

             This object is now obsolete as no HTTP server is
             present."
        ::= { httpStats 17 }

    httpStatusServiceUnavailable OBJECT-TYPE
        SYNTAX Counter64
        MAX-ACCESS read-only
        STATUS obsolete
        DESCRIPTION
            "The number of 503 Service Unavailable status replies.

             This object is now obsolete as no HTTP server is
             present."
        ::= { httpStats 18 }

    httpStatusOtherErr OBJECT-TYPE
        SYNTAX Counter64
        MAX-ACCESS read-only
        STATUS obsolete
        DESCRIPTION
            "The number of other errors occurring.

             This object is now obsolete as no HTTP server is
             present."
        ::= { httpStats 19 }

    httpTimeOut OBJECT-TYPE
        SYNTAX Unsigned32
        MAX-ACCESS read-only
        STATUS obsolete
        DESCRIPTION
            "The timeout period in milliseconds.

             This object is now obsolete as no HTTP server is
             present."
        ::= { httpStats 20 }

    httpOpenConnections OBJECT-TYPE
        SYNTAX Unsigned32
        MAX-ACCESS read-only
        STATUS obsolete
        DESCRIPTION
            "The number of open HTTP connections.

             This object is now obsolete as no HTTP server is
             present."
        ::= { httpStats 21 }

    httpActiveConnections OBJECT-TYPE
        SYNTAX Unsigned32
        MAX-ACCESS read-only
        STATUS obsolete
        DESCRIPTION
            "The number of active HTTP connections.

             This object is now obsolete as no HTTP server is
             present."
        ::= { httpStats 22 }


--------------------------------------------------------------------------------
--
-- File Protocol / HTTP / HTTP Service Configuration
--
--------------------------------------------------------------------------------

    httpServiceEnabled OBJECT-TYPE
        SYNTAX INTEGER {
            enabled(1),
            disabled(2),
            unknown(3)
        }
        MAX-ACCESS read-only
        STATUS obsolete
        DESCRIPTION
            "Indicates whether the HTTP service is enabled or not.

             This object is now obsolete as no HTTP server is
             present."
        ::= { httpService 1 }

    httpServiceMaxUsers OBJECT-TYPE
        SYNTAX Unsigned32
        MAX-ACCESS read-only
        STATUS obsolete
        DESCRIPTION
            "The maximum number of HTTP clients the service will allow.

             This object is now obsolete as no HTTP server is
             present."
        ::= { httpService 2 }


--------------------------------------------------------------------------------
--
-- File Protocol / ISCSI / ISCSI Configuration
--
--------------------------------------------------------------------------------

    iScsiServiceEnabled OBJECT-TYPE
        SYNTAX INTEGER {
            enabled(1),
            disabled(2),
            unknown(3)
        }
        MAX-ACCESS read-only
        STATUS current
        DESCRIPTION
            "Indicates whether the iSCSI service is enabled or not.
            
            enabled(1)  The service is enabled
            disabled(2) The service is not enabled
            unknown(3)  The service status cannot be determined."
        ::= { iScsiConfiguration 1 }

    iScsiParameterTable OBJECT-TYPE
        SYNTAX SEQUENCE OF IScsiParameterEntry
        MAX-ACCESS not-accessible
        STATUS current
        DESCRIPTION
            "A table containing a list of iSCSI parameters."
        ::= { iScsiConfiguration 2 }

    iScsiParameterEntry OBJECT-TYPE
        SYNTAX IScsiParameterEntry
        MAX-ACCESS not-accessible
        STATUS current
        DESCRIPTION
            "iSCSI parameter information."
        INDEX { iScsiParameterEVS, iScsiParameterName }
        ::= { iScsiParameterTable 1 }

    IScsiParameterEntry ::=
        SEQUENCE {
            iScsiParameterEVS
                Unsigned32,
            iScsiParameterName
                DisplayString,
            iScsiParameterIsBoolean
                INTEGER,
            iScsiParameterValue
                Unsigned32
        }

    iScsiParameterEVS OBJECT-TYPE
        SYNTAX Unsigned32 (1..255)
        MAX-ACCESS read-only
        STATUS current
        DESCRIPTION
            "The EVS for which the Logical Unit parameters
            are configured."
        ::= { iScsiParameterEntry 1 }

    iScsiParameterName OBJECT-TYPE
        SYNTAX DisplayString
        MAX-ACCESS read-only
        STATUS current
        DESCRIPTION
            "A unique name for the iSCSI parameter."
        ::= { iScsiParameterEntry 2 }

    iScsiParameterIsBoolean OBJECT-TYPE
        SYNTAX INTEGER {
            boolean(1),
            notBoolean(2)
        }
        MAX-ACCESS read-only
        STATUS current
        DESCRIPTION
            "Whether the parameter is a boolean value.

            If the parameter is boolean, it will have either
            the value 0 (false) or 1 (true)."
        ::= { iScsiParameterEntry 3 }

    iScsiParameterValue OBJECT-TYPE
        SYNTAX Unsigned32
        MAX-ACCESS read-only
        STATUS current
        DESCRIPTION
            "The value for the parameter.

            If the parameter is boolean, it will have either
            the value 0 (false) or 1 (true)."
        ::= { iScsiParameterEntry 4 }

    iScsiTargetNumber OBJECT-TYPE
        SYNTAX Integer32
        MAX-ACCESS read-only
        STATUS current
        DESCRIPTION
            "The number of iSCSI targets."
        ::= { iScsiConfiguration 3 }

    iScsiTargetTable OBJECT-TYPE
        SYNTAX SEQUENCE OF IScsiTargetEntry
        MAX-ACCESS not-accessible
        STATUS current
        DESCRIPTION
            "A table containing a list of iSCSI targets.

             The number of entries in this table is given by the value of
             iScsiTargetNumber."
        ::= { iScsiConfiguration 4 }

    iScsiTargetEntry OBJECT-TYPE
        SYNTAX IScsiTargetEntry
        MAX-ACCESS not-accessible
        STATUS current
        DESCRIPTION
            "iSCSI target information."
        INDEX { iScsiGloballyUniqueName }
        ::= { iScsiTargetTable 1 }

    IScsiTargetEntry ::=
        SEQUENCE {
            iScsiGloballyUniqueName
                DisplayString,
            iScsiTargetName
                DisplayString,
            iScsiTargetComment
                DisplayString,
            iScsiTargetLogicalUnitNumber
                Unsigned32,
            iScsiTargetAuthEnabled
                INTEGER
        }

    iScsiGloballyUniqueName OBJECT-TYPE
        SYNTAX DisplayString
        MAX-ACCESS read-only
        STATUS current
        DESCRIPTION
            "A unique name for the iSCSI target."
        ::= { iScsiTargetEntry 1 }

    iScsiTargetName OBJECT-TYPE
        SYNTAX DisplayString
        MAX-ACCESS read-only
        STATUS current
        DESCRIPTION
            "The name of the iSCSI target."
        ::= { iScsiTargetEntry 2 }

    iScsiTargetComment OBJECT-TYPE
        SYNTAX DisplayString
        MAX-ACCESS read-only
        STATUS current
        DESCRIPTION
            "The comment for the iSCSI target."
        ::= { iScsiTargetEntry 3 }

    iScsiTargetLogicalUnitNumber OBJECT-TYPE
        SYNTAX Unsigned32
        MAX-ACCESS read-only
        STATUS current
        DESCRIPTION
            "The number of Logical Units assigned
            to the iSCSI target."
        ::= { iScsiTargetEntry 4 }

    iScsiTargetAuthEnabled OBJECT-TYPE
        SYNTAX INTEGER {
            enabled(1),
            disabled(2)
        }
        MAX-ACCESS read-only
        STATUS current
        DESCRIPTION
            "Whether authentication is enabled for this
            target."
        ::= { iScsiTargetEntry 5 }

    iScsiLogicalUnitNumber OBJECT-TYPE
        SYNTAX Integer32
        MAX-ACCESS read-only
        STATUS current
        DESCRIPTION
            "The number of iSCSI logical units."
        ::= { iScsiConfiguration 5 }


    iScsiLogicalUnitTable OBJECT-TYPE
        SYNTAX SEQUENCE OF IScsiLogicalUnitEntry
        MAX-ACCESS not-accessible
        STATUS current
        DESCRIPTION
            "A table containing a list of iSCSI Logical Units.

             The number of entries in this table is given by the value of
             iScsiTargetLogicalUnitNumber in iScsiTargetTable."
        ::= { iScsiConfiguration 6 }

    iScsiLogicalUnitEntry OBJECT-TYPE
        SYNTAX IScsiLogicalUnitEntry
        MAX-ACCESS not-accessible
        STATUS current
        DESCRIPTION
            "iSCSI Logical Unit information.

            Indexed by EVS and Logical Unit name."
        INDEX { iScsiLUEvs, iScsiLUName }
        ::= { iScsiLogicalUnitTable 1 }

    IScsiLogicalUnitEntry ::=
        SEQUENCE {
            iScsiLUEvs
                Unsigned32,
            iScsiLUName
                DisplayString,
            iScsiLUStatus
                INTEGER,
            iScsiLUComment
                DisplayString,
            iScsiLUDeviceId
                Unsigned32,
            iScsiLUPath
                DisplayString,
            iScsiLUInitialized
                INTEGER,
            iScsiLUSize
                Counter64
        }

    iScsiLUEvs OBJECT-TYPE
        SYNTAX Unsigned32 (1..255)
        MAX-ACCESS read-only
        STATUS current
        DESCRIPTION
            "The EVS to which the Logical Unit is assigned."
        ::= { iScsiLogicalUnitEntry 1 }

    iScsiLUName OBJECT-TYPE
        SYNTAX DisplayString
        MAX-ACCESS read-only
        STATUS current
        DESCRIPTION
            "The name of the Logical Unit."
        ::= { iScsiLogicalUnitEntry 2 }

    iScsiLUStatus OBJECT-TYPE
        SYNTAX INTEGER {
            unknown(1)
        }
        MAX-ACCESS read-only
        STATUS current
        DESCRIPTION
            "The status of the Logical Unit

            unknown(1) - the status cannot be determined."
        ::= { iScsiLogicalUnitEntry 3 }

    iScsiLUComment OBJECT-TYPE
        SYNTAX DisplayString
        MAX-ACCESS read-only
        STATUS current
        DESCRIPTION
            "The comment relating to the Logical Unit."
        ::= { iScsiLogicalUnitEntry 4 }

    iScsiLUDeviceId OBJECT-TYPE
        SYNTAX Unsigned32 (1..4294967295)
        MAX-ACCESS read-only
        STATUS current
        DESCRIPTION
            "The ID of the File System to which the Logical Unit
            is assigned."
        ::= { iScsiLogicalUnitEntry 5 }

    iScsiLUPath OBJECT-TYPE
        SYNTAX DisplayString
        MAX-ACCESS read-only
        STATUS current
        DESCRIPTION
            "The path on the File System relating to the 
            Logical Unit."
        ::= { iScsiLogicalUnitEntry 6 }

    iScsiLUInitialized OBJECT-TYPE
        SYNTAX INTEGER {
            initialized(1),
            uninitialized(2),
            unknown(3)
        }
        MAX-ACCESS read-only
        STATUS current
        DESCRIPTION
            "Whether the Logical Unit is initialized.

            initialized(1) - the Logical Unit is initialized
            uninitialized(2) - the Logical unit is not initialized
            unknown(3) - the initialization status cannot be determined."
        ::= { iScsiLogicalUnitEntry 7 }

    iScsiLUSize OBJECT-TYPE
        SYNTAX Counter64
        MAX-ACCESS read-only
        STATUS current
        DESCRIPTION
            "The size, in bytes, of the Logical Unit."
        ::= { iScsiLogicalUnitEntry 8 }

    iScsiTargetLogicalUnitTable OBJECT-TYPE
        SYNTAX SEQUENCE OF IScsiTargetLogicalUnitEntry
        MAX-ACCESS not-accessible
        STATUS current
        DESCRIPTION
            "A table containing a list of iSCSI Logical Units
            assigned to iSCSI targets.

             The number of entries in this table is given by the value of
             iScsiTargetLogicalUnitNumber in iScsiTargetTable."
        ::= { iScsiConfiguration 7 }

    iScsiTargetLogicalUnitEntry OBJECT-TYPE
        SYNTAX IScsiTargetLogicalUnitEntry
        MAX-ACCESS not-accessible
        STATUS current
        DESCRIPTION
            "Information about iSCSI Logical Units
            assigned to iScsi targets.

            Indexed by target name and Logical Unit name."
        INDEX { iScsiTargetLUTargetName, iScsiTargetLULogicalUnitName }
        ::= { iScsiTargetLogicalUnitTable 1 }

    IScsiTargetLogicalUnitEntry ::=
        SEQUENCE {
            iScsiTargetLUTargetName
                DisplayString,
            iScsiTargetLULogicalUnitName
                DisplayString,
            iScsiTargetLun
                Integer32
        }

    iScsiTargetLUTargetName OBJECT-TYPE
        SYNTAX DisplayString
        MAX-ACCESS read-only
        STATUS current
        DESCRIPTION
            "The globally unique name of the target."
        ::= { iScsiTargetLogicalUnitEntry 1 }

    iScsiTargetLULogicalUnitName OBJECT-TYPE
        SYNTAX DisplayString
        MAX-ACCESS read-only
        STATUS current
        DESCRIPTION
            "The name of the Logical Unit assigned to the
            target."
        ::= { iScsiTargetLogicalUnitEntry 2 }

    iScsiTargetLun OBJECT-TYPE
        SYNTAX Integer32
        MAX-ACCESS read-only
        STATUS current
        DESCRIPTION
            "The Logical Unit Number allocated to the
            LUN when it was assigned to the target.
            This is an arbitrary number which must be unique
            on the target."
        ::= { iScsiTargetLogicalUnitEntry 3 }

    iSNSTable OBJECT-TYPE
        SYNTAX SEQUENCE OF ISNSEntry
        MAX-ACCESS not-accessible
        STATUS current
        DESCRIPTION
            "A table containing details of iSNS servers."

        ::= { iScsiConfiguration 8 }

    iSNSEntry OBJECT-TYPE
        SYNTAX ISNSEntry
        MAX-ACCESS not-accessible
        STATUS current
        DESCRIPTION
            "Information about iSNS servers."
        INDEX { iSNSIpAddress }
        ::= { iSNSTable 1 }

    ISNSEntry ::=
        SEQUENCE {
            iSNSIpAddress
                IpAddress,
            iSNSPort
                Unsigned32
        }

    iSNSIpAddress OBJECT-TYPE
        SYNTAX IpAddress
        MAX-ACCESS read-only
        STATUS current
        DESCRIPTION
            "The IP address of the iSNS server."
        ::= { iSNSEntry 1 }

    iSNSPort OBJECT-TYPE
        SYNTAX Unsigned32
        MAX-ACCESS read-only
        STATUS current
        DESCRIPTION
            "The port on which to connect to the iSNS
            server."
        ::= { iSNSEntry 2 }

    iScsiStatisticsTable OBJECT-TYPE
        SYNTAX SEQUENCE OF IScsiStatisticsEntry
        MAX-ACCESS not-accessible
        STATUS current
        DESCRIPTION
            "A table containing a list of iSCSI statistics."
        ::= { iScsiStatistics 1 }

    iScsiStatisticsEntry OBJECT-TYPE
        SYNTAX IScsiStatisticsEntry
        MAX-ACCESS not-accessible
        STATUS current
        DESCRIPTION
            "Information about iSCSI statistics.

            Indexed by Cluster Node id and metric name."
        INDEX { iScsiStatisticsNodeId, iScsiStatisticsName }
        ::= { iScsiStatisticsTable 1 }

    IScsiStatisticsEntry ::=
        SEQUENCE {
            iScsiStatisticsNodeId
                Unsigned32,
            iScsiStatisticsName
                DisplayString,
            iScsiStatisticsValue
                Counter64
        }

    iScsiStatisticsNodeId OBJECT-TYPE
        SYNTAX Unsigned32
        MAX-ACCESS read-only
        STATUS current
        DESCRIPTION
            "The Cluster Node for this value."
        ::= { iScsiStatisticsEntry 1 }

    iScsiStatisticsName OBJECT-TYPE
        SYNTAX DisplayString
        MAX-ACCESS read-only
        STATUS current
        DESCRIPTION
            "The name of the value being reported."
        ::= { iScsiStatisticsEntry 2 }

    iScsiStatisticsValue OBJECT-TYPE
        SYNTAX Counter64
        MAX-ACCESS read-only
        STATUS current
        DESCRIPTION
            "The statistics value reported."
        ::= { iScsiStatisticsEntry 3 }


--------------------------------------------------------------------------------
--
-- Backup / NDMP Status
--
--------------------------------------------------------------------------------

    ndmpCurrentStatus OBJECT-TYPE
        SYNTAX INTEGER {
            started(1),
            stopped(2),
            aborting(3),
            unknown(4)
        }
        MAX-ACCESS read-only
        STATUS current
        DESCRIPTION
            "Indicates the current status of the NDMP backup."
        ::= { ndmpStatus 1 }

    ndmpEnabledOnBoot OBJECT-TYPE
        SYNTAX INTEGER {
            enabled(1),
            disabled(2),
            unknown(3)
        }
        MAX-ACCESS read-only
        STATUS current
        DESCRIPTION
            "Indicates whether or not NDMP is enabled at boot time."
        ::= { ndmpStatus 2 }

--------------------------------------------------------------------------------
--
-- Backup / NDMP Devices
--
--------------------------------------------------------------------------------

    autoChangerNumber OBJECT-TYPE
        SYNTAX Integer32
        MAX-ACCESS read-only
        STATUS current
        DESCRIPTION
            "The number of auto changers NDMP has detected."
        ::= { ndmpDevices 1 }

    autoChangerTable OBJECT-TYPE
        SYNTAX SEQUENCE OF AutoChangerEntry
        MAX-ACCESS not-accessible
        STATUS current
        DESCRIPTION
            "A table containing a list of auto changers NDMP has
             detected.

             The number of entries in this table is given by the value of
             autoChangerNumber."
        ::= { ndmpDevices 2 }

    autoChangerEntry OBJECT-TYPE
        SYNTAX AutoChangerEntry
        MAX-ACCESS not-accessible
        STATUS current
        DESCRIPTION
            "Auto changer information."
        INDEX { autoChangerIndex }
        ::= { autoChangerTable 1 }

    AutoChangerEntry ::=
        SEQUENCE {
            autoChangerIndex
                Integer32,
            autoChangerDeviceName
                DisplayString,
            autoChangerSerialNumber
                DisplayString,
            autoChangerEVS
                DisplayString
        }

    autoChangerIndex OBJECT-TYPE
        SYNTAX Integer32 (1..10)
        MAX-ACCESS read-only
        STATUS current
        DESCRIPTION
            "A unique value for each auto changer detected.

             Its value ranges between 1 and the value of
             autoChangerNumber."
        ::= { autoChangerEntry 1 }

    autoChangerDeviceName OBJECT-TYPE
        SYNTAX DisplayString
        MAX-ACCESS read-only
        STATUS current
        DESCRIPTION
            "The device name of the auto changer."
        ::= { autoChangerEntry 2 }

    autoChangerSerialNumber OBJECT-TYPE
        SYNTAX DisplayString
        MAX-ACCESS read-only
        STATUS current
        DESCRIPTION
            "The serial number of the auto changer."
        ::= { autoChangerEntry 3 }

    autoChangerEVS OBJECT-TYPE
        SYNTAX DisplayString
        MAX-ACCESS read-only
        STATUS current
        DESCRIPTION
            "The Enterprise Virtual Server to which this
            auto changer is assigned."
        ::= { autoChangerEntry 4 }

    tapeDriveNumber OBJECT-TYPE
        SYNTAX Integer32
        MAX-ACCESS read-only
        STATUS current
        DESCRIPTION
            "The number of tape drives that NDMP has detected."
        ::= { ndmpDevices 3 }

    tapeDriveTable OBJECT-TYPE
        SYNTAX SEQUENCE OF TapeDriveEntry
        MAX-ACCESS not-accessible
        STATUS current
        DESCRIPTION
            "A table containing a list of all tape drives NDMP has detected.

             The number of entries in this table is given by the value of 
             tapeDriveNumber."
        ::= { ndmpDevices 4 }

    tapeDriveEntry OBJECT-TYPE
        SYNTAX TapeDriveEntry
        MAX-ACCESS not-accessible
        STATUS current
        DESCRIPTION
            "Tape drive information."
        INDEX { tapeDriveIndex }
        ::= { tapeDriveTable 1 }

    TapeDriveEntry ::=
        SEQUENCE {
            tapeDriveIndex
                Integer32,
            tapeDriveAutoChangerIndex
                Integer32,
            tapeDriveDeviceName
                DisplayString,
            tapeDriveSerialNumber
                DisplayString,
            tapeDriveLocation
                DisplayString,
            tapeDriveEVS
                DisplayString
        }

    tapeDriveIndex OBJECT-TYPE
        SYNTAX Integer32 (1..10)
        MAX-ACCESS read-only
        STATUS current
        DESCRIPTION
            "A unique value for each tape drive.

             Its value ranges between 1 and the value of 
             tapeDriveNumber."
        ::= { tapeDriveEntry 1 }

    tapeDriveAutoChangerIndex OBJECT-TYPE
        SYNTAX Integer32
        MAX-ACCESS read-only
        STATUS current
        DESCRIPTION
            "The index of the auto changer in the autoChangerTable
             to which this tape drive is connected or -1 if it is
             not associated with an auto changer."
        ::= { tapeDriveEntry 2 }

    tapeDriveDeviceName OBJECT-TYPE
        SYNTAX DisplayString
        MAX-ACCESS read-only
        STATUS current
        DESCRIPTION
            "The device name of the tape drive."
        ::= { tapeDriveEntry 3 }

    tapeDriveSerialNumber OBJECT-TYPE
        SYNTAX DisplayString
        MAX-ACCESS read-only
        STATUS current
        DESCRIPTION
            "The serial number of the tape drive."
        ::= { tapeDriveEntry 4 }

    tapeDriveLocation OBJECT-TYPE
        SYNTAX DisplayString
        MAX-ACCESS read-only
        STATUS current
        DESCRIPTION
            "The location of the tape drive."
        ::= { tapeDriveEntry 5 }

    tapeDriveEVS OBJECT-TYPE
        SYNTAX DisplayString
        MAX-ACCESS read-only
        STATUS current
        DESCRIPTION
            "The Enterprise Virtual Server to which this
            tape drive is assigned."
        ::= { tapeDriveEntry 6 }

--------------------------------------------------------------------------------
--
-- Backup / NDMP Snapshot Options
--
--------------------------------------------------------------------------------

    ndmpAutoSnapCreateEnabled OBJECT-TYPE
        SYNTAX INTEGER {
            enabled(1),
            disabled(2),
            unknown(3)
        }
        MAX-ACCESS read-only
        STATUS current
        DESCRIPTION
            "Determines whether snapshots are automatically created when 
             NDMP performs a backup.

             enabled(1)  - indicates that NDMP will create a snapshot (if one 
                           does not already exist) when a backup is to be
                           performed.
             disabled(2) - indicates that NDMP will not automatically
                           create a snapshot when a backup is to be performed.
                           It will take a backup of the live file system
                           if no snapshot exists.
             unknown(3)  - indicates that snapshot is disabled on this system
                           and the value is therefore unknown."
        ::= { ndmpSnapshotOptions 1 }

    ndmpAutoSnapDeleteMode OBJECT-TYPE
        SYNTAX INTEGER {
            immediately(1),
            whenObsolete(2),
            unknown(3)
        }
        MAX-ACCESS read-only
        STATUS current
        DESCRIPTION
            "Indicates whether NDMP will remove a snapshot automatically
             when the backup is complete.
             immediately(1)  - indicates that the snapshot will be deleted
                               immediately after use.
             whenObsolete(2) - indicates that the snapshot will be deleted
                               when it becomes obsolete.
             unknown(3)      - indicates that snapshot is disabled on this 
                               system and the value is therefore unknown."
        ::= { ndmpSnapshotOptions 2 }

    ndmpAutoSnapMaxRetention OBJECT-TYPE
        SYNTAX Unsigned32
        MAX-ACCESS read-only
        STATUS current
        DESCRIPTION
            "The maximum retention time of snapshot (in days) which has been
             automatically created by NDMP as a result of performing
             a backup.

             NOTE: this value is set to 0 if snapshot is disabled on this
                   system."
        ::= { ndmpSnapshotOptions 3 }


--------------------------------------------------------------------------------
--
-- Management / System Users
--
--------------------------------------------------------------------------------

    systemUserNumber OBJECT-TYPE
        SYNTAX Integer32
        MAX-ACCESS read-only
        STATUS current
        DESCRIPTION
            "The number of users which are configured to access the system
             through web and telnet via password authentication.
             NOTE: this does not include users which have higher level access
             than supervisor."
        ::= { systemUsers 1 }

    systemUserTable OBJECT-TYPE
        SYNTAX SEQUENCE OF SystemUserEntry
        MAX-ACCESS not-accessible
        STATUS current
        DESCRIPTION
            "A table containing a list of all users configured to access the
             system through web and telnet via password authentication.
             NOTE: this does not include users which have higher level access
             than supervisor.

             The number of entries in this table is given by the value of 
             systemUserNumber."
        ::= { systemUsers 2 }

    systemUserEntry OBJECT-TYPE
        SYNTAX SystemUserEntry
        MAX-ACCESS not-accessible
        STATUS current
        DESCRIPTION
            "System user information."
        INDEX { systemUserName }
        ::= { systemUserTable 1 }

    SystemUserEntry ::=
        SEQUENCE {
            systemUserName
                DisplayString,
            systemUserAccessLevel
                DisplayString
        }

    systemUserName OBJECT-TYPE
        SYNTAX DisplayString
        MAX-ACCESS read-only
        STATUS current
        DESCRIPTION
            "The login name of the system user."
        ::= { systemUserEntry 1 }

    systemUserAccessLevel OBJECT-TYPE
        SYNTAX DisplayString
        MAX-ACCESS read-only
        STATUS current
        DESCRIPTION
            "The access level granted to the system user."
        ::= { systemUserEntry 2 }

--------------------------------------------------------------------------------
--
-- Management / License Information
--
--------------------------------------------------------------------------------

    licenseKeyNumber OBJECT-TYPE
        SYNTAX Integer32
        MAX-ACCESS read-only
        STATUS current
        DESCRIPTION
            "The number of license keys for this server."
        ::= { license 1 }

    licenseKeyTable OBJECT-TYPE
        SYNTAX SEQUENCE OF LicenseKeyEntry
        MAX-ACCESS not-accessible
        STATUS obsolete
        DESCRIPTION
            "A table containing a list of license keys.

             The number of entries in this table is given by the value
             of licenseKeyNumber."
        ::= { license 2 }

    licenseKeyEntry OBJECT-TYPE
        SYNTAX LicenseKeyEntry
        MAX-ACCESS not-accessible
        STATUS obsolete
        DESCRIPTION
            "License key information."
        INDEX { licenseKeyIndex }
        ::= { licenseKeyTable 1 }

    LicenseKeyEntry ::=
        SEQUENCE {
            licenseKeyIndex
                Integer32,
            licenseKeyString
                DisplayString,
            licenseKeyValid
                INTEGER,
            licenseCIFSService
                INTEGER,
            licenseNFSService
                INTEGER,
            licenseFTPService
                INTEGER,
            licenseHTTPService
                INTEGER,
            licenseFailoverService
                INTEGER,
            licenseRAIDService
                INTEGER
        }

    licenseKeyIndex OBJECT-TYPE
        SYNTAX Integer32 (1..30)
        MAX-ACCESS read-only
        STATUS obsolete
        DESCRIPTION
            "A unique value for each license key.

             Its value ranges between 1 and the value of
             licenseKeyNumber."
        ::= { licenseKeyEntry 1 }

    licenseKeyString OBJECT-TYPE
        SYNTAX DisplayString
        MAX-ACCESS read-only
        STATUS obsolete
        DESCRIPTION
            "The license key string."
        ::= { licenseKeyEntry 2 }

    licenseKeyValid OBJECT-TYPE
        SYNTAX INTEGER {
            valid(1),
            invalid(2),
            unknown(3)
        }
        MAX-ACCESS read-only
        STATUS obsolete
        DESCRIPTION
            "Indicates whether the license key is valid on this
             server or not."
        ::= { licenseKeyEntry 3 }

    licenseCIFSService OBJECT-TYPE
        SYNTAX INTEGER {
            enabled(1),
            disabled(2),
            unknown(3)
        }
        MAX-ACCESS read-only
        STATUS obsolete
        DESCRIPTION
            "Indicates whether this license key enables the
             use of the CIFS service or not."
        ::= { licenseKeyEntry 4 }

    licenseNFSService OBJECT-TYPE
        SYNTAX INTEGER {
            enabled(1),
            disabled(2),
            unknown(3)
        }
        MAX-ACCESS read-only
        STATUS obsolete
        DESCRIPTION
            "Indicates whether this license key enables the use
             of the NFS service or not."
        ::= { licenseKeyEntry 5 }

    licenseFTPService OBJECT-TYPE
        SYNTAX INTEGER {
            enabled(1),
            disabled(2),
            unknown(3)
        }
        MAX-ACCESS read-only
        STATUS obsolete
        DESCRIPTION
            "Indicates whether this license key enables the use of 
             the FTP service or not."
        ::= { licenseKeyEntry 6 }

    licenseHTTPService OBJECT-TYPE
        SYNTAX INTEGER {
            enabled(1),
            disabled(2),
            unknown(3)
        }
        MAX-ACCESS read-only
        STATUS obsolete
        DESCRIPTION
            "Indicates whether this license key enables the use of 
             the HTTP service or not."
        ::= { licenseKeyEntry 7 }

    licenseFailoverService OBJECT-TYPE
        SYNTAX INTEGER {
            enabled(1),
            disabled(2),
            unknown(3)
        }
        MAX-ACCESS read-only
        STATUS obsolete
        DESCRIPTION
            "Indicates whether this license key enables the use
             of the Failover service or not.

             This object is obsolete: failover has been
             superceded by clustering."
        ::= { licenseKeyEntry 8 }

    licenseRAIDService OBJECT-TYPE
        SYNTAX INTEGER {
            single(1),
            multiple(2),
            unknown(3)
        }
        MAX-ACCESS read-only
        STATUS obsolete
        DESCRIPTION
            "Indicates whether this license key enables the 
             use of more than one RAID controller in the system
             or not."
        ::= { licenseKeyEntry 9 }

    licenseTable OBJECT-TYPE
        SYNTAX SEQUENCE OF LicenseEntry
        MAX-ACCESS not-accessible
        STATUS current
        DESCRIPTION
            "A table containing a list of valid license keys and the service(s)
             they license."
        ::= { license 3 }

    licenseEntry OBJECT-TYPE
        SYNTAX LicenseEntry
        MAX-ACCESS not-accessible
        STATUS current
        DESCRIPTION
            "License information."
        INDEX { licenseIndex }
        ::= { licenseTable 1 }

    LicenseEntry ::=
        SEQUENCE {
            licenseIndex
                Integer32,
            licenseKey
                DisplayString,
            licenseService
                DisplayString
        }

    licenseIndex OBJECT-TYPE
        SYNTAX Integer32 (1..1024)
        MAX-ACCESS read-only
        STATUS current
        DESCRIPTION
            "A unique value for each licensed service."
        ::= { licenseEntry 1 }

    licenseKey OBJECT-TYPE
        SYNTAX DisplayString
        MAX-ACCESS read-only
        STATUS current
        DESCRIPTION
            "The license key."
        ::= { licenseEntry 2 }

    licenseService OBJECT-TYPE
        SYNTAX DisplayString
        MAX-ACCESS read-only
        STATUS current
        DESCRIPTION
            "A service licensed by the given license."
        ::= { licenseEntry 3 }

--------------------------------------------------------------------------------
--
-- Management / Access / Web
--
--------------------------------------------------------------------------------

    webAccessEnabled OBJECT-TYPE
        SYNTAX INTEGER {
            enabled(1),
            disabled(2),
            unknown(3)
        }
        MAX-ACCESS read-only
        STATUS obsolete
        DESCRIPTION
            "Indicates whether access to the web (GUI) interface is
             permitted or not.

             The setting disabled(2) indicates access to the
             web interface will not be allowed regardless of any
             other configuration settings for this interface."
        ::= { web 1 }

    webAccessRestricted OBJECT-TYPE
        SYNTAX INTEGER {
            restricted(1),
            unrestricted(2),
            unknown(3)
        }
        MAX-ACCESS read-only
        STATUS obsolete
        DESCRIPTION
            "Indicates whether access to the web interface is
             restricted to the set of hostnames or IP addresses
             configured in webAccessRestrictedTable or
             unrestricted (such that any client may access the
             web interface).

             NOTE : this setting controls the use of the web access
                    restricted table in that there may be entries
                    in this table, but access to the interface will
                    be allowed from any host if this variable is
                    set to unrestricted(2).
                    
            This object is now obsolete."
        ::= { web 2 }

    webAccessRestrictedNumber OBJECT-TYPE
        SYNTAX Integer32
        MAX-ACCESS read-only
        STATUS obsolete
        DESCRIPTION
            "The number of restricted web access entries
             configured.
                    
            This object is now obsolete."
        ::= { web 3 }

    webAccessRestrictedTable OBJECT-TYPE
        SYNTAX SEQUENCE OF WebAccessRestrictedEntry
        MAX-ACCESS not-accessible
        STATUS obsolete
        DESCRIPTION
            "A table containing the hostnames or IP addresses of clients
             which have restricted access to the web interface.

             The number of entries in this table is given by the value of
             webAccessRestrictedNumber.
                    
            This object is now obsolete."
        ::= { web 4 }

    webAccessRestrictedEntry OBJECT-TYPE
        SYNTAX WebAccessRestrictedEntry
        MAX-ACCESS not-accessible
        STATUS obsolete
        DESCRIPTION
            "Restricted web access information.
                    
            This object is now obsolete."
        INDEX { webAccessRestrictedHost }
        ::= { webAccessRestrictedTable 1 }

    WebAccessRestrictedEntry ::=
        SEQUENCE {
            webAccessRestrictedHost
                DisplayString
        }

    webAccessRestrictedHost OBJECT-TYPE
        SYNTAX DisplayString
        MAX-ACCESS read-only
        STATUS obsolete
        DESCRIPTION
            "The hostname or IP address of a client which has
             restricted access to the web interface.
                    
            This object is now obsolete."
        ::= { webAccessRestrictedEntry 1 }

    webAccessPortNumber OBJECT-TYPE
        SYNTAX Integer32
        MAX-ACCESS read-only
        STATUS obsolete
        DESCRIPTION
            "The port number through which access to the web interface
             is available (subject to any security restrictions).
                    
            This object is now obsolete."
        ::= { web 5 }

    webAccessMaxConnections OBJECT-TYPE
        SYNTAX Integer32
        MAX-ACCESS read-only
        STATUS obsolete
        DESCRIPTION
            "The maximum number of simultaneous connections which are
             allowed access to the web interface.
                    
            This object is now obsolete."
        ::= { web 6 }

--------------------------------------------------------------------------------
--
-- Management / Access / SiCtrl
--
--------------------------------------------------------------------------------

    sictrlAccessEnabled OBJECT-TYPE
        SYNTAX INTEGER {
            enabled(1),
            disabled(2),
            unknown(3)
        }
        MAX-ACCESS read-only
        STATUS obsolete
        DESCRIPTION
            "Indicates whether access to the SiCtrl
             (command line) interface is permitted or not.

             The setting disabled(2) indicates access to the
             SiCtrl interface will not be allowed regardless of any
             other configuration settings for this interface."
        ::= { sictrl 1 }

    sictrlAccessRestricted OBJECT-TYPE
        SYNTAX INTEGER {
            restricted(1),
            unrestricted(2),
            unknown(3)
        }
        MAX-ACCESS read-only
        STATUS obsolete
        DESCRIPTION
            "Indicates whether access to the SiCtrl interface
             is restricted to the set of hostnames or IP addresses
             configured in sictrlAccessRestrictedTable or
             unrestricted (such that any client may access the
             SiCtrl interface).

             NOTE: this setting controls the use of the SiCtrl access
                   restricted table in that there may be entries
                   in this table, but access to the interface will be
                   allowed from any host if this variable is set to
                   unrestricted(2)."
        ::= { sictrl 2 }

    sictrlAccessRestrictedNumber OBJECT-TYPE
        SYNTAX Integer32
        MAX-ACCESS read-only
        STATUS obsolete
        DESCRIPTION
            "The number of restricted SiCtrl access entries
             configured."
        ::= { sictrl 3 }

    sictrlAccessRestrictedTable OBJECT-TYPE
        SYNTAX SEQUENCE OF SictrlAccessRestrictedEntry
        MAX-ACCESS not-accessible
        STATUS obsolete
        DESCRIPTION
            "A table containing the hostnames or IP addresses of
             clients which have restricted access the SiCtrl interface.

             The number of entries in this table is given by the value of
             sictrlAccessRestrictedNumber."
        ::= { sictrl 4 }

    sictrlAccessRestrictedEntry OBJECT-TYPE
        SYNTAX SictrlAccessRestrictedEntry
        MAX-ACCESS not-accessible
        STATUS obsolete
        DESCRIPTION
            "Restricted SiCtrl access information."
        INDEX { sictrlAccessRestrictedHost }
        ::= { sictrlAccessRestrictedTable 1 }

    SictrlAccessRestrictedEntry ::=
        SEQUENCE {
            sictrlAccessRestrictedHost
                DisplayString
        }

    sictrlAccessRestrictedHost OBJECT-TYPE
        SYNTAX DisplayString
        MAX-ACCESS read-only
        STATUS obsolete
        DESCRIPTION
            "The hostname or IP address of a client which has restricted
             access to the SiCtrl interface."
        ::= { sictrlAccessRestrictedEntry 1 }

    sictrlAccessPortNumber OBJECT-TYPE
        SYNTAX Integer32
        MAX-ACCESS read-only
        STATUS obsolete
        DESCRIPTION
            "The port number through which access to the SiCtrl interface
             is available (subject to any security restrictions)."
        ::= { sictrl 5 }

    sictrlAccessMaxConnections OBJECT-TYPE
        SYNTAX Integer32
        MAX-ACCESS read-only
        STATUS obsolete
        DESCRIPTION
            "The maximum number of simultaneous connections which are
             allowed access to the SiCtrl interface."
        ::= { sictrl 6 }

--------------------------------------------------------------------------------
--
-- Management / Access / Telnet
--
--------------------------------------------------------------------------------

    telnetAccessEnabled OBJECT-TYPE
        SYNTAX INTEGER {
            enabled(1),
            disabled(2),
            unknown(3)
        }
        MAX-ACCESS read-only
        STATUS current
        DESCRIPTION
            "Indicates whether access to the telnet interface is permitted
             or not.

            The setting disabled(2) indicates access to the
            telnet interface will not be allowed regardless of any other 
            configuration settings for this interface."
        ::= { telnet 1 }

    telnetAccessRestricted OBJECT-TYPE
        SYNTAX INTEGER {
            restricted(1),
            unrestricted(2),
            unknown(3)
        }
        MAX-ACCESS read-only
        STATUS current
        DESCRIPTION
            "Indicates whether access to the telnet interface is 
             restricted to the set of hostnames or IP addresses 
             configured in telnetAccessRestrictedTable or
             unrestricted (such that any client may access the 
             telnet interface).

             NOTE: this setting controls the use of the telnet access 
                   restricted table in that there may be entries in this
                   table, but access to the interface will be allowed 
                   from any host if this variable is set to
                   unrestricted(2)."
        ::= { telnet 2 }

    telnetAccessRestrictedNumber OBJECT-TYPE
        SYNTAX Integer32
        MAX-ACCESS read-only
        STATUS current
        DESCRIPTION
            "The number of restricted telnet access entries 
             configured."
        ::= { telnet 3 }

    telnetAccessRestrictedTable OBJECT-TYPE
        SYNTAX SEQUENCE OF TelnetAccessRestrictedEntry
        MAX-ACCESS not-accessible
        STATUS current
        DESCRIPTION
            "A table containing the hostnames or IP addresses of clients 
             which have restricted access the telnet interface.

             The number of entries in this table is given by the value of 
             telnetAccessRestrictedNumber."
        ::= { telnet 4 }

    telnetAccessRestrictedEntry OBJECT-TYPE
        SYNTAX TelnetAccessRestrictedEntry
        MAX-ACCESS not-accessible
        STATUS current
        DESCRIPTION
            "Restricted telnet access information."
        INDEX { telnetAccessRestrictedHost }
        ::= { telnetAccessRestrictedTable 1 }

    TelnetAccessRestrictedEntry ::=
        SEQUENCE {
            telnetAccessRestrictedHost
                DisplayString
        }

    telnetAccessRestrictedHost OBJECT-TYPE
        SYNTAX DisplayString
        MAX-ACCESS read-only
        STATUS current
        DESCRIPTION
            "The hostname or IP address of a client which has 
             restricted access to the telnet interface."
        ::= { telnetAccessRestrictedEntry 1 }

    telnetAccessPortNumber OBJECT-TYPE
        SYNTAX Integer32
        MAX-ACCESS read-only
        STATUS current
        DESCRIPTION
            "The port number through which access to the telnet interface
             is available (subject to any security restrictions)."
        ::= { telnet 5 }

    telnetAccessMaxConnections OBJECT-TYPE
        SYNTAX Integer32
        MAX-ACCESS read-only
        STATUS current
        DESCRIPTION
            "The maximum number of simultaneous connections which are
             allowed access to the telnet interface."
        ::= { telnet 6 }

--------------------------------------------------------------------------------
--
-- Management / Access / Secure Web
--
--------------------------------------------------------------------------------

    secureWebAccessEnabled OBJECT-TYPE
        SYNTAX INTEGER {
            enabled(1),
            disabled(2),
            unknown(3)
        }
        MAX-ACCESS read-only
        STATUS obsolete
        DESCRIPTION
            "Indicates whether access to the secure web interface is permitted
             or not.

            The setting disabled(2) indicates access to the
            secure web interface will not be allowed regardless of any other 
            configuration settings for this interface.
                    
            This object is now obsolete."
        ::= { secureWeb 1 }

    secureWebAccessRestricted OBJECT-TYPE
        SYNTAX INTEGER {
            restricted(1),
            unrestricted(2),
            unknown(3)
        }
        MAX-ACCESS read-only
        STATUS obsolete
        DESCRIPTION
            "Indicates whether access to the secure web interface is 
             restricted to the set of hostnames or IP addresses 
             configured in secureWebAccessRestrictedTable or
             unrestricted (such that any client may access the 
             secure web interface).

             NOTE: this setting controls the use of the secure web access 
                   restricted table in that there may be entries in this
                   table, but access to the interface will be allowed 
                   from any host if this variable is set to
                   unrestricted(2).
                    
            This object is now obsolete."
        ::= { secureWeb 2 }

    secureWebAccessRestrictedNumber OBJECT-TYPE
        SYNTAX Integer32
        MAX-ACCESS read-only
        STATUS obsolete
        DESCRIPTION
            "The number of restricted secure web access entries 
             configured.
                    
            This object is now obsolete."
        ::= { secureWeb 3 }

    secureWebAccessRestrictedTable OBJECT-TYPE
        SYNTAX SEQUENCE OF SecureWebAccessRestrictedEntry
        MAX-ACCESS not-accessible
        STATUS obsolete
        DESCRIPTION
            "A table containing the hostnames or IP addresses of clients 
             which have restricted access the secure web interface.

             The number of entries in this table is given by the value of 
             secureWebAccessRestrictedNumber.
                    
            This object is now obsolete."
        ::= { secureWeb 4 }

    secureWebAccessRestrictedEntry OBJECT-TYPE
        SYNTAX SecureWebAccessRestrictedEntry
        MAX-ACCESS not-accessible
        STATUS obsolete
        DESCRIPTION
            "Restricted secure web access information.
                    
            This object is now obsolete."
        INDEX { secureWebAccessRestrictedHost }
        ::= { secureWebAccessRestrictedTable 1 }

    SecureWebAccessRestrictedEntry ::=
        SEQUENCE {
            secureWebAccessRestrictedHost
                DisplayString
        }

    secureWebAccessRestrictedHost OBJECT-TYPE
        SYNTAX DisplayString
        MAX-ACCESS read-only
        STATUS obsolete
        DESCRIPTION
            "The hostname or IP address of a client which has 
             restricted access to the secure web interface.
                    
            This object is now obsolete."
        ::= { secureWebAccessRestrictedEntry 1 }

    secureWebAccessPortNumber OBJECT-TYPE
        SYNTAX Integer32
        MAX-ACCESS read-only
        STATUS obsolete
        DESCRIPTION
            "The port number through which access to the secure web interface
             is available (subject to any security restrictions).
                    
            This object is now obsolete."
        ::= { secureWeb 5 }

    secureWebAccessMaxConnections OBJECT-TYPE
        SYNTAX Integer32
        MAX-ACCESS read-only
        STATUS obsolete
        DESCRIPTION
            "The maximum number of simultaneous connections which are
             allowed access to the secure web interface.
                    
            This object is now obsolete."
        ::= { secureWeb 6 }

--------------------------------------------------------------------------------
--
-- Management / Access / LCD (on server front panel unit)
--
--------------------------------------------------------------------------------

    lcdFrontPanelLocked OBJECT-TYPE
        SYNTAX INTEGER {
            locked(1),
            unLocked(2)
        }
        MAX-ACCESS read-only
        STATUS obsolete
        DESCRIPTION
            "Indicates whether the front panel LCD on the server is locked 
             or not.

             
             This object is obsolete."
        ::= { lcd 1 }

--------------------------------------------------------------------------------
--
-- Management / Event Log
--
--------------------------------------------------------------------------------

    eventLogNumber OBJECT-TYPE
        SYNTAX Integer32
        MAX-ACCESS read-only
        STATUS obsolete
        DESCRIPTION
            "The total number of events currently logged.

            This object is now obsolete."
        ::= { eventlog 1 }

    eventLogTable OBJECT-TYPE
        SYNTAX SEQUENCE OF EventLogEntry
        MAX-ACCESS not-accessible
        STATUS obsolete
        DESCRIPTION
            "A table containing a list of all Events logged
             for the system.

             The number of entries in this table is given by the value of 
             eventLogNumber.

            This object is now obsolete."
        ::= { eventlog 2 }

    eventLogEntry OBJECT-TYPE
        SYNTAX EventLogEntry
        MAX-ACCESS not-accessible
        STATUS obsolete
        DESCRIPTION
            "Event log information.

            This object is now obsolete."
        INDEX { eventLogTimeStamp, eventLogHandle }
        ::= { eventLogTable 1 }

    EventLogEntry ::=
        SEQUENCE {
            eventLogTimeStamp
                DisplayString,
            eventLogHandle
                Integer32,
            eventLogText
                DisplayString
        }

    eventLogTimeStamp OBJECT-TYPE
        SYNTAX DisplayString
        MAX-ACCESS read-only
        STATUS obsolete
        DESCRIPTION
            "The timestamp of the event in UTC format.

            This object is now obsolete."
        ::= { eventLogEntry 1 }

    eventLogHandle OBJECT-TYPE
        SYNTAX Integer32 (1..65535)
        MAX-ACCESS read-only
        STATUS obsolete
        DESCRIPTION
            "A unique handle for the event.

            This object is now obsolete."
        ::= { eventLogEntry 2 }

    eventLogText OBJECT-TYPE
        SYNTAX DisplayString
        MAX-ACCESS read-only
        STATUS obsolete
        DESCRIPTION
            "The text describing the event.

            This object is now obsolete."
        ::= { eventLogEntry 3 }

--------------------------------------------------------------------------------
--
-- Management / Alert Configuration / Mail
--
--------------------------------------------------------------------------------

    smtpAddr OBJECT-TYPE
        SYNTAX DisplayString
        MAX-ACCESS read-only
        STATUS current
        DESCRIPTION
            "The IP address or hostname of the SMTP server."
        ::= { mailAlertConfig 1 }

    smtpCritFreq OBJECT-TYPE
        SYNTAX INTEGER {
            never(1),
            immediately(2),
            unknown(3)
        }
        MAX-ACCESS read-only
        STATUS current
        DESCRIPTION
            "The frequency at which alerts within the critical category
             may be sent to the mail recipient(s)."
        ::= { mailAlertConfig 2 }

    smtpSevFreq OBJECT-TYPE
        SYNTAX INTEGER {
            never(1),
            immediately(2),
            daily(3),
            unknown(4)
        }
        MAX-ACCESS read-only
        STATUS current
        DESCRIPTION
            "The frequency at which alerts within the severe category
             may be sent to the mail recipient(s)."
        ::= { mailAlertConfig 3 }

    smtpWarnFreq OBJECT-TYPE
        SYNTAX INTEGER {
            never(1),
            immediately(2),
            daily(3),
            unknown(4)
        }
        MAX-ACCESS read-only
        STATUS current
        DESCRIPTION
            "The frequency at which alerts within the warning category
             may be sent to the mail recipient(s)."
        ::= { mailAlertConfig 4 }

    smtpInfoFreq OBJECT-TYPE
        SYNTAX INTEGER {
            never(1),
            immediately(2),
            daily(3),
            unknown(4)
        }
        MAX-ACCESS read-only
        STATUS current
        DESCRIPTION
            "The frequency at which alerts within the information category
             may be sent to the mail recipient(s)."
        ::= { mailAlertConfig 5 }

    smtpRecipNumber OBJECT-TYPE
        SYNTAX Integer32
        MAX-ACCESS read-only
        STATUS current
        DESCRIPTION
            "The number of email recipients configured to receive alerts."
        ::= { mailAlertConfig 6 }

    smtpRecipTable OBJECT-TYPE
        SYNTAX SEQUENCE OF SmtpRecipEntry
        MAX-ACCESS not-accessible
        STATUS obsolete
        DESCRIPTION
            "A table containing a list of all configured mail alert
             recipients for this system.

             The number of entries in this table is given by the value of
             smtpRecipNumber.

             This object is obsolete.  Superceded by smptRecipientTable."
        ::= { mailAlertConfig 7 }

    smtpRecipEntry OBJECT-TYPE
        SYNTAX SmtpRecipEntry
        MAX-ACCESS not-accessible
        STATUS obsolete
        DESCRIPTION
            "Mail alert recipient information.

             This object is obsolete.  Superceded by smtpRecipientEntry."
        INDEX { smtpRecipIndex }
        ::= { smtpRecipTable 1 }

    SmtpRecipEntry ::=
        SEQUENCE {
            smtpRecipIndex
                Integer32,
            smtpRecipName
                DisplayString
        }

    smtpRecipIndex OBJECT-TYPE
        SYNTAX Integer32 (1..20)
        MAX-ACCESS read-only
        STATUS obsolete
        DESCRIPTION
            "A unique value for each configured mail recipient.

             Its value ranges between 1 and the value of
             smtpRecipNumber.

             This table entry is obsolete.  Superceded by smtpRecipientIndex."
        ::= { smtpRecipEntry 1 }

    smtpRecipName OBJECT-TYPE
        SYNTAX DisplayString
        MAX-ACCESS read-only
        STATUS obsolete
        DESCRIPTION
            "The email address of the recipient.

             This table entry is obsolete.  Superceded by smtpRecipientName."
        ::= { smtpRecipEntry 2 }

    smtpDiagUUencEnabled OBJECT-TYPE
        SYNTAX INTEGER {
            enabled(1),
            disabled(2),
            unknown(3)
        }
        MAX-ACCESS read-only
        STATUS current
        DESCRIPTION
            "Indicates whether diagnostic emails are UU encoded
             or not."
        ::= { mailAlertConfig 8 }

    smtpUndisclosedRecipNumber OBJECT-TYPE
        SYNTAX Integer32
        MAX-ACCESS read-only
        STATUS obsolete
        DESCRIPTION
            "The number of email recipients configured to receive
             undisclosed alerts.
             
             This object is obsolete.  Undisclosed recipients are now grouped
             with disclosed recipients."
        ::= { mailAlertConfig 9 }

    smtpUndisclosedRecipTable OBJECT-TYPE
        SYNTAX SEQUENCE OF SmtpUndisclosedRecipEntry
        MAX-ACCESS not-accessible
        STATUS obsolete
        DESCRIPTION
            "A table containing a list of all configured mail alert 
             recipients which are to receive undisclosed alerts
             for this system.

             The number of entries in this table is given by the value of 
             smtpUndisclosedRecipNumber.
             
             This object is obsolete.  Undisclosed recipients are now grouped
             with disclosed recipients."
        ::= { mailAlertConfig 10 }

    smtpUndisclosedRecipEntry OBJECT-TYPE
        SYNTAX SmtpUndisclosedRecipEntry
        MAX-ACCESS not-accessible
        STATUS obsolete
        DESCRIPTION
            "Undisclosed mail alert recipient information.
            
             This table is obsolete.  Undisclosed recipients are now
             grouped with disclosed recipients."
        INDEX { smtpUndisclosedRecipIndex }
        ::= { smtpUndisclosedRecipTable 1 }

    SmtpUndisclosedRecipEntry ::=
        SEQUENCE {
            smtpUndisclosedRecipIndex
                Integer32,
            smtpUndisclosedRecipName
                DisplayString
        }

    smtpUndisclosedRecipIndex OBJECT-TYPE
        SYNTAX Integer32 (1..20)
        MAX-ACCESS read-only
        STATUS obsolete
        DESCRIPTION
            "A unique value for each configured mail recipient
             which is to receive undisclosed alert information.

             Its value ranges between 1 and the value of 
             smtpUndisclosedRecipNumber.
             
             This table entry is obsolete.  Undisclosed recipients are now
             grouped with disclosed recipients."
        ::= { smtpUndisclosedRecipEntry 1 }

    smtpUndisclosedRecipName OBJECT-TYPE
        SYNTAX DisplayString
        MAX-ACCESS read-only
        STATUS obsolete
        DESCRIPTION
            "The email address of the recipient.
            
             This object is obsolete.  Undisclosed recipients are now
             grouped with disclosed recipients."
        ::= { smtpUndisclosedRecipEntry 2 }

    smtpRecipientTable OBJECT-TYPE
        SYNTAX SEQUENCE OF SmtpRecipientEntry
        MAX-ACCESS not-accessible
        STATUS current
        DESCRIPTION
            "A table containing a list of all configured mail alert
             recipients for this system, whether to disclose
             details in emails sent to the recipients and whether
             to send empty summary emails when due.

             The number of entries in this table is given by the value of
             smtpRecipNumber."
        ::= { mailAlertConfig 11 }

    smtpRecipientEntry OBJECT-TYPE
        SYNTAX SmtpRecipientEntry
        MAX-ACCESS not-accessible
        STATUS current
        DESCRIPTION
            "Mail alert recipient information."
        INDEX { smtpRecipientIndex }
        ::= { smtpRecipientTable 1 }

    SmtpRecipientEntry ::=
        SEQUENCE {
            smtpRecipientIndex
                Integer32,
            smtpRecipientName
                DisplayString,
            smtpRecipientDisclose
                DisplayString,
            smtpRecipientEmpty
                DisplayString
        }

    smtpRecipientIndex OBJECT-TYPE
        SYNTAX Integer32 (1..20)
        MAX-ACCESS read-only
        STATUS current
        DESCRIPTION
            "A unique value for each configured mail recipient."
        ::= { smtpRecipientEntry 1 }

    smtpRecipientName OBJECT-TYPE
        SYNTAX DisplayString
        MAX-ACCESS read-only
        STATUS current
        DESCRIPTION
            "The email address of the recipient."
        ::= { smtpRecipientEntry 2 }

    smtpRecipientDisclose OBJECT-TYPE
        SYNTAX DisplayString
        MAX-ACCESS read-only
        STATUS current
        DESCRIPTION
            "Disclose details in emails to this recipient."
        ::= { smtpRecipientEntry 3 }

    smtpRecipientEmpty OBJECT-TYPE
        SYNTAX DisplayString
        MAX-ACCESS read-only
        STATUS current
        DESCRIPTION
            "If there have been no events when summary emails are due 
            then send empty emails."
        ::= { smtpRecipientEntry 4 }


--------------------------------------------------------------------------------
--
-- Management / Alert Configuration / Windows Pop Up
--
--------------------------------------------------------------------------------

    winCritFreq OBJECT-TYPE
        SYNTAX INTEGER {
            never(1),
            immediately(2),
            unknown(3)
        }
        MAX-ACCESS read-only
        STATUS obsolete
        DESCRIPTION
            "The frequency at which alerts within the critical category
             may be sent to the windows popup recipient(s).

             This object is now obsolete."
        ::= { winAlertConfig 1 }

    winSevFreq OBJECT-TYPE
        SYNTAX INTEGER {
            never(1),
            immediately(2),
            unknown(3)
        }
        MAX-ACCESS read-only
        STATUS obsolete
        DESCRIPTION
            "The frequency at which alerts within the severe category
             may be sent to the windows popup recipient(s).

             This object is now obsolete."
        ::= { winAlertConfig 2 }

    winWarnFreq OBJECT-TYPE
        SYNTAX INTEGER {
            never(1),
            immediately(2),
            unknown(3)
        }
        MAX-ACCESS read-only
        STATUS obsolete
        DESCRIPTION
            "The frequency at which alerts within the warning category
             may be sent to the windows popup recipient(s).

             This object is now obsolete."
        ::= { winAlertConfig 3 }

    winInfoFreq OBJECT-TYPE
        SYNTAX INTEGER {
            never(1),
            immediately(2),
            unknown(3)
        }
        MAX-ACCESS read-only
        STATUS obsolete
        DESCRIPTION
            "The frequency at which alerts within the information category
             may be sent to the windows popup recipient(s).

             This object is now obsolete."
        ::= { winAlertConfig 4 }

    winRecipNumber OBJECT-TYPE
        SYNTAX Integer32
        MAX-ACCESS read-only
        STATUS obsolete
        DESCRIPTION
            "The number of windows popup recipients configured to
             receive alerts.

             This object is now obsolete."
        ::= { winAlertConfig 5 }

    winRecipTable OBJECT-TYPE
        SYNTAX SEQUENCE OF WinRecipEntry
        MAX-ACCESS not-accessible
        STATUS obsolete
        DESCRIPTION
            "A table containing a list of all configured windows
             popup alert recipients for this system.

             The number of entries in this table is given by the value of 
             winRecipNumber.

             This object is now obsolete."
        ::= { winAlertConfig 6 }

    winRecipEntry OBJECT-TYPE
        SYNTAX WinRecipEntry
        MAX-ACCESS not-accessible
        STATUS obsolete
        DESCRIPTION
            "Windows alert recipient information.

             This object is now obsolete."
        INDEX { winRecipIndex }
        ::= { winRecipTable 1 }

    WinRecipEntry ::=
        SEQUENCE {
            winRecipIndex
                Integer32,
            winRecipName
                DisplayString
        }

    winRecipIndex OBJECT-TYPE
        SYNTAX Integer32 (1..20)
        MAX-ACCESS read-only
        STATUS obsolete
        DESCRIPTION
            "A unique value for each configured windows popup recipient.

             Its value ranges between 1 and the value of 
             winRecipNumber.

             This object is now obsolete."
        ::= { winRecipEntry 1 }

    winRecipName OBJECT-TYPE
        SYNTAX DisplayString
        MAX-ACCESS read-only
        STATUS obsolete
        DESCRIPTION
            "The name of the windows popup recipient.

             This object is now obsolete."
        ::= { winRecipEntry 2 }

--------------------------------------------------------------------------------
--
-- Management / Alert Configuration / SNMP
--
--------------------------------------------------------------------------------

    snmpCritFreq OBJECT-TYPE
        SYNTAX INTEGER {
            never(1),
            immediately(2),
            unknown(3)
        }
        MAX-ACCESS read-only
        STATUS current
        DESCRIPTION
            "The frequency at which alerts within the critical category
             may be sent to the SNMP recipient(s)."
        ::= { snmpAlertConfig 1 }

    snmpSevFreq OBJECT-TYPE
        SYNTAX INTEGER {
            never(1),
            immediately(2),
            unknown(3)
        }
        MAX-ACCESS read-only
        STATUS current
        DESCRIPTION
            "The frequency at which alerts within the severe category
             may be sent to the SNMP recipient(s)."
        ::= { snmpAlertConfig 2 }

    snmpWarnFreq OBJECT-TYPE
        SYNTAX INTEGER {
            never(1),
            immediately(2),
            unknown(3)
        }
        MAX-ACCESS read-only
        STATUS current
        DESCRIPTION
            "The frequency at which alerts within the warning category
             may be sent to the SNMP recipient(s)."
        ::= { snmpAlertConfig 3 }

    snmpInfoFreq OBJECT-TYPE
        SYNTAX INTEGER {
            never(1),
            immediately(2),
            unknown(3)
        }
        MAX-ACCESS read-only
        STATUS current
        DESCRIPTION
            "The frequency at which alerts within the information category
             may be sent to the SNMP recipient(s)."
        ::= { snmpAlertConfig 4 }

    snmpRecipNumber OBJECT-TYPE
        SYNTAX Integer32
        MAX-ACCESS read-only
        STATUS obsolete
        DESCRIPTION
            "The number of SNMP recipients configured to receive alerts.

             This object is obsolete.  It has been replaced by 
             the object snmpTrapHostNumber."
        ::= { snmpAlertConfig 5 }

    snmpRecipTable OBJECT-TYPE
        SYNTAX SEQUENCE OF SnmpRecipEntry
        MAX-ACCESS not-accessible
        STATUS obsolete
        DESCRIPTION
            "A table containing a list of all SNMP alert recipients
             for this system.

             The number of entries in this table is given by the value of 
             snmpRecipNumber.

             This object is obsolete.  It has been replaced by 
             the table object snmpTrapHostTable."
        ::= { snmpAlertConfig 6 }

    snmpRecipEntry OBJECT-TYPE
        SYNTAX SnmpRecipEntry
        MAX-ACCESS not-accessible
        STATUS obsolete
        DESCRIPTION
            "SNMP alert recipient information.
             
             This object is obsolete.  It has been replaced by the
             object snmpTrapHostEntry."
        INDEX { snmpRecipIndex }
        ::= { snmpRecipTable 1 }

    SnmpRecipEntry ::=
        SEQUENCE {
            snmpRecipIndex
                Integer32,
            snmpRecipName
                DisplayString
        }

    snmpRecipIndex OBJECT-TYPE
        SYNTAX Integer32 (1..20)
        MAX-ACCESS read-only
        STATUS obsolete
        DESCRIPTION
            "A unique value for each configured SNMP alert recipient.

             Its value ranges between 1 and the value of 
             snmpRecipNumber.

             This object is obsolete.  It has been replaced by 
             the object snmpTrapHostIndex."
        ::= { snmpRecipEntry 1 }

    snmpRecipName OBJECT-TYPE
        SYNTAX DisplayString
        MAX-ACCESS read-only
        STATUS obsolete
        DESCRIPTION
            "The hostname or IP address of the SNMP 
             manager to receive the alert.

             This object is obsolete.  It has been replaced by 
             the object snmpTrapHost."
        ::= { snmpRecipEntry 2 }

--------------------------------------------------------------------------------
--
-- Management / SNMP Agent
--
--------------------------------------------------------------------------------

    snmpProtocolMode OBJECT-TYPE
        SYNTAX INTEGER {
            bilingual(1),
            version1(2),
            version2c(3),
            unknown(4)
        }
        MAX-ACCESS read-only
        STATUS current
        DESCRIPTION
            "Indicates the protocol to be used by the agent:
             
             bilingual(1) - the agent will process SNMP version 1 
                            or SNMP version 2c requests. 
                            The protocol version used in the response
                            will be that used in the request.        
             version1(2)  - the agent will only process requests made 
                            using SNMP version 1. The response will be
                            sent using SNMP version 1.
             version2c(3) - the agent will only process requests made using
                            SNMP version 2c. The response will be sent using 
                            SNMP version 2c.

             NOTE: requests made using a protocol version which does not
                   comply with the agents protocol configuration will 
                   result in the badVersions statistic being incremented and 
                   the SNMP packet being discarded."
        ::= { snmpAgent 1 }

    snmpAccessRestricted OBJECT-TYPE
        SYNTAX INTEGER {
            restricted(1),
            unrestricted(2),
            unknown(3)
        }
        MAX-ACCESS read-only
        STATUS current
        DESCRIPTION
            "Indicates whether access to the SNMP agent is restricted to
             the set of hostnames or IP addresses configured in 
             snmpAccessRestrictedTable or unrestricted (such that any manager 
             may access the SNMP agent).

             NOTE : this setting controls the use of the SNMP access 
                    restricted table in that there may be entries in this 
                    table, but access to the interface will be allowed from 
                    any host if this variable is set to unrestricted(2)."
        ::= { snmpAgent 2 }

    snmpAccessRestrictedNumber OBJECT-TYPE
        SYNTAX Integer32
        MAX-ACCESS read-only
        STATUS current
        DESCRIPTION
            "The number of configured restricted access entries."
        ::= { snmpAgent 3 }

    snmpAccessRestrictedTable OBJECT-TYPE
        SYNTAX SEQUENCE OF SnmpAccessRestrictedEntry
        MAX-ACCESS not-accessible
        STATUS current
        DESCRIPTION
            "A table containing the hostnames or IP addresses of managers 
             which have restricted access the SNMP agent.

             The number of entries in this table is given by the value of 
             snmpAccessRestrictedNumber."
        ::= { snmpAgent 4 }

    snmpAccessRestrictedEntry OBJECT-TYPE
        SYNTAX SnmpAccessRestrictedEntry
        MAX-ACCESS not-accessible
        STATUS current
        DESCRIPTION
            "Restricted SNMP access information."
        INDEX { snmpAccessRestrictedHost }
        ::= { snmpAccessRestrictedTable 1 }

    SnmpAccessRestrictedEntry ::=
        SEQUENCE {
            snmpAccessRestrictedHost
                DisplayString
        }

    snmpAccessRestrictedHost OBJECT-TYPE
        SYNTAX DisplayString
        MAX-ACCESS read-only
        STATUS current
        DESCRIPTION
            "The hostname or IP address of a manager which has restricted 
             access to the SNMP agent."
        ::= { snmpAccessRestrictedEntry 1 }

    snmpTrapHostNumber OBJECT-TYPE
        SYNTAX Integer32
        MAX-ACCESS read-only
        STATUS current
        DESCRIPTION
            "The number of configured host destinations to receive traps
             from the SNMP agent.
             NOTE: the traps generated include alert events and:

             linkUp, coldStart AND
             authenticationFailure (which is controlled by the MIBII
                                    variable snmpEnableAuthenTraps)."
        ::= { snmpAgent 5 }

    snmpTrapHostTable OBJECT-TYPE
        SYNTAX SEQUENCE OF SnmpTrapHostEntry
        MAX-ACCESS not-accessible
        STATUS current
        DESCRIPTION
            "A table containing the hostnames or IP addresses of managers 
             which are to receive traps from the SNMP agent.
           
             The number of entries in this table is given by the value of 
             snmpTrapHostNumber."
        ::= { snmpAgent 6 }

    snmpTrapHostEntry OBJECT-TYPE
        SYNTAX SnmpTrapHostEntry
        MAX-ACCESS not-accessible
        STATUS current
        DESCRIPTION
            "SNMP trap host information."
        INDEX { snmpTrapHostIndex }
        ::= { snmpTrapHostTable 1 }

    SnmpTrapHostEntry ::=
        SEQUENCE {
            snmpTrapHostIndex
                Integer32,
            snmpTrapHost
                DisplayString
        }

    snmpTrapHostIndex OBJECT-TYPE
        SYNTAX Integer32 (1..20)
        MAX-ACCESS read-only
        STATUS current
        DESCRIPTION
            "A unique value for each trap host.  
             
             Its value ranges from 1 to snmpTrapHostNumber."
        ::= { snmpTrapHostEntry 1 }

    snmpTrapHost OBJECT-TYPE
        SYNTAX DisplayString
        MAX-ACCESS read-only
        STATUS current
        DESCRIPTION
            "The hostname or IP address of a manager which is to receive
             traps from the SNMP agent."
        ::= { snmpTrapHostEntry 2 }

--------------------------------------------------------------------------------
--
-- Management / Versions
--
--------------------------------------------------------------------------------

    verinfoSw OBJECT-TYPE
        SYNTAX DisplayString
        MAX-ACCESS read-only
        STATUS current
        DESCRIPTION
            "Systems software release information."
        ::= { versions 1 }

    verinfoHw OBJECT-TYPE
        SYNTAX DisplayString
        MAX-ACCESS read-only
        STATUS current
        DESCRIPTION
            "Hardware release information."
        ::= { versions 2 }

    verModNumber OBJECT-TYPE
        SYNTAX Integer32
        MAX-ACCESS read-only
        STATUS current
        DESCRIPTION
            "The number of modules."
        ::= { versions 3 }

    verModTable OBJECT-TYPE
        SYNTAX SEQUENCE OF VerModEntry
        MAX-ACCESS not-accessible
        STATUS current
        DESCRIPTION
            "A table containing a list of version information for each module
             within the system.

             The number of entries in this table is given by the value of 
             verModNumber."
        ::= { versions 4 }

    verModEntry OBJECT-TYPE
        SYNTAX VerModEntry
        MAX-ACCESS not-accessible
        STATUS current
        DESCRIPTION
            "Module version information."
        INDEX { verModIndex }
        ::= { verModTable 1 }

    VerModEntry ::=
        SEQUENCE {
            verModIndex
                INTEGER,
            verModLoader
                DisplayString,
            verModKernel
                DisplayString,
            verModHw
                DisplayString,
            verModSerial
                Integer32,
            verModBuildState
                Integer32,
            verModUniq0
                DisplayString,
            verModUniq1
                DisplayString,
            verModFirstDate
                DisplayString,
            verModMTDSLastFailure
                DisplayString,
            verModMTDSFailures
                Integer32,
            verModMTDSLastPass
                DisplayString,
            verModMTDSPasses
                Integer32,
            verModCardID
                Integer32,
            verModCardRev
                Integer32,
            verModGlueRev
                Integer32
        }

    verModIndex OBJECT-TYPE
        SYNTAX INTEGER {
            tcp(1),
            fsb(2),
            fcp(3)
        }
        MAX-ACCESS read-only
        STATUS current
        DESCRIPTION
            "An identifier for each board.
             
             tcp(1) - the tcp board.
             fsb(2) - the filesystem board.
             fcp(3) - the fibre channel board."
        ::= { verModEntry 1 }

    verModLoader OBJECT-TYPE
        SYNTAX DisplayString
        MAX-ACCESS read-only
        STATUS current
        DESCRIPTION
            "Module loader version."
        ::= { verModEntry 2 }

    verModKernel OBJECT-TYPE
        SYNTAX DisplayString
        MAX-ACCESS read-only
        STATUS current
        DESCRIPTION
            "Module kernel version."
        ::= { verModEntry 3 }

    verModHw OBJECT-TYPE
        SYNTAX DisplayString
        MAX-ACCESS read-only
        STATUS current
        DESCRIPTION
            "Module hardware version."
        ::= { verModEntry 4 }

    verModSerial OBJECT-TYPE
        SYNTAX Integer32
        MAX-ACCESS read-only
        STATUS current
        DESCRIPTION
            "Module serial number."
        ::= { verModEntry 5 }

    verModBuildState OBJECT-TYPE
        SYNTAX Integer32
        MAX-ACCESS read-only
        STATUS current
        DESCRIPTION
            "Module build state."
        ::= { verModEntry 6 }

    verModUniq0 OBJECT-TYPE
        SYNTAX DisplayString
        MAX-ACCESS read-only
        STATUS current
        DESCRIPTION
            "EEPROM Uniq value 0."
        ::= { verModEntry 7 }

    verModUniq1 OBJECT-TYPE
        SYNTAX DisplayString
        MAX-ACCESS read-only
        STATUS current
        DESCRIPTION
            "EEPROM Uniq value 1."
        ::= { verModEntry 8 }

    verModFirstDate OBJECT-TYPE
        SYNTAX DisplayString
        MAX-ACCESS read-only
        STATUS current
        DESCRIPTION
            "First Date."
        ::= { verModEntry 9 }

    verModMTDSLastFailure OBJECT-TYPE
        SYNTAX DisplayString
        MAX-ACCESS read-only
        STATUS current
        DESCRIPTION
            "Last Failure date for MTDS."
        ::= { verModEntry 10 }

    verModMTDSFailures OBJECT-TYPE
        SYNTAX Integer32
        MAX-ACCESS read-only
        STATUS current
        DESCRIPTION
            "Manufacturing and test number of failures."
        ::= { verModEntry 11 }

    verModMTDSLastPass OBJECT-TYPE
        SYNTAX DisplayString
        MAX-ACCESS read-only
        STATUS current
        DESCRIPTION
            "Manufacturing and test last pass date."
        ::= { verModEntry 12 }

    verModMTDSPasses OBJECT-TYPE
        SYNTAX Integer32
        MAX-ACCESS read-only
        STATUS current
        DESCRIPTION
            "Manufacturing and test number of passes."
        ::= { verModEntry 13 }

    verModCardID OBJECT-TYPE
        SYNTAX Integer32
        MAX-ACCESS read-only
        STATUS current
        DESCRIPTION
            "Card identity."
        ::= { verModEntry 14 }

    verModCardRev OBJECT-TYPE
        SYNTAX Integer32
        MAX-ACCESS read-only
        STATUS current
        DESCRIPTION
            "Card revision number."
        ::= { verModEntry 15 }

    verModGlueRev OBJECT-TYPE
        SYNTAX Integer32
        MAX-ACCESS read-only
        STATUS current
        DESCRIPTION
            "Glue revision number."
        ::= { verModEntry 16 }

--------------------------------------------------------------------------------
--
-- Management / Cron
--
--------------------------------------------------------------------------------

    cronJobNumber OBJECT-TYPE
        SYNTAX Integer32
        MAX-ACCESS read-only
        STATUS current
        DESCRIPTION
            "The number of cron jobs configured to run on this system.
             NOTE: this table also includes those cron jobs which are 
                   configured to perform snapshot scheduling."
        ::= { cron 1 }

    cronJobTable OBJECT-TYPE
        SYNTAX SEQUENCE OF CronJobEntry
        MAX-ACCESS not-accessible
        STATUS current
        DESCRIPTION
            "A table containing a list of all cron jobs configured
             to run on this system.

             The number of entries in this table is given by the value of 
             cronJobNumber."
        ::= { cron 2 }

    cronJobEntry OBJECT-TYPE
        SYNTAX CronJobEntry
        MAX-ACCESS not-accessible
        STATUS current
        DESCRIPTION
            "Cron job information."
        INDEX { cronJobIndex }
        ::= { cronJobTable 1 }

    CronJobEntry ::=
        SEQUENCE {
            cronJobIndex
                Integer32,
            cronJobDateSpec
                DisplayString,
            cronJobCommandList
                DisplayString,
            cronJobMailList
                DisplayString,
            cronJobAccessLevel
                DisplayString
        }

    cronJobIndex OBJECT-TYPE
        SYNTAX Integer32 (1..16384)
        MAX-ACCESS read-only
        STATUS current
        DESCRIPTION
            "A unique value for each cron job entry."
        ::= { cronJobEntry 1 }

    cronJobDateSpec OBJECT-TYPE
        SYNTAX DisplayString
        MAX-ACCESS read-only
        STATUS current
        DESCRIPTION
            "The date specification for the cron job."
        ::= { cronJobEntry 2 }

    cronJobCommandList OBJECT-TYPE
        SYNTAX DisplayString
        MAX-ACCESS read-only
        STATUS current
        DESCRIPTION
            "A semi-colon separated list of commands to be run as 
             part of the cron job."
        ::= { cronJobEntry 3 }

    cronJobMailList OBJECT-TYPE
        SYNTAX DisplayString
        MAX-ACCESS read-only
        STATUS current
        DESCRIPTION
            "A semi-colon separated list of recipients who each are to
             receive a copy of the output generated as a result of running 
             the cron job.

             NOTE: This value will be a zero length string if the output
                   of running the job is not be emailed."
        ::= { cronJobEntry 4 }

    cronJobAccessLevel OBJECT-TYPE
        SYNTAX DisplayString
        MAX-ACCESS read-only
        STATUS current
        DESCRIPTION
            "The access level at which the cron job is run."
        ::= { cronJobEntry 5 }

    atJobNumber OBJECT-TYPE
        SYNTAX Integer32
        MAX-ACCESS read-only
        STATUS current
        DESCRIPTION
            "The number of at jobs configured to run on this system."
        ::= { cron 3 }

    atJobTable OBJECT-TYPE
        SYNTAX SEQUENCE OF AtJobEntry
        MAX-ACCESS not-accessible
        STATUS current
        DESCRIPTION
            "A table containing a list of all at jobs configured
             to run on this system.

             The number of entries in this table is given by the value of 
             atJobNumber."
        ::= { cron 4 }

    atJobEntry OBJECT-TYPE
        SYNTAX AtJobEntry
        MAX-ACCESS not-accessible
        STATUS current
        DESCRIPTION
            "At job information."
        INDEX { atJobIndex }
        ::= { atJobTable 1 }

    AtJobEntry ::=
        SEQUENCE {
            atJobIndex
                Integer32,
            atJobRunTime
                DisplayString,
            atJobCommandList
                DisplayString,
            atJobMailList
                DisplayString,
            atJobAccessLevel
                DisplayString
        }

    atJobIndex OBJECT-TYPE
        SYNTAX Integer32 (1..16384)
        MAX-ACCESS read-only
        STATUS current
        DESCRIPTION
            "A unique value for each at job entry."
        ::= { atJobEntry 1 }

    atJobRunTime OBJECT-TYPE
        SYNTAX DisplayString
        MAX-ACCESS read-only
        STATUS current
        DESCRIPTION
            "The date at which the at job is scheduled to run expressed
             as a local time in the format YYYY-MM-DD HH:MI (Local)"
        ::= { atJobEntry 2 }

    atJobCommandList OBJECT-TYPE
        SYNTAX DisplayString
        MAX-ACCESS read-only
        STATUS current
        DESCRIPTION
            "A semi-colon separated list of commands to be run as 
             part of the at job."
        ::= { atJobEntry 3 }

    atJobMailList OBJECT-TYPE
        SYNTAX DisplayString
        MAX-ACCESS read-only
        STATUS current
        DESCRIPTION
            "A semi-colon separated list of recipients who each are to
             receive a copy of the output generated as a result of running 
             the cron job.

             NOTE: This value will be a zero length string if the output
                   of running the job is not be emailed."
        ::= { atJobEntry 4 }

    atJobAccessLevel OBJECT-TYPE
        SYNTAX DisplayString
        MAX-ACCESS read-only
        STATUS current
        DESCRIPTION
            "The access level at which the at job is run."
        ::= { atJobEntry 5 }

--------------------------------------------------------------------------------
--
-- Management / Statistics
--
--------------------------------------------------------------------------------

    webCurrActiveSessions OBJECT-TYPE
        SYNTAX Counter64
        MAX-ACCESS read-only
        STATUS obsolete
        DESCRIPTION
            "The current number of active sessions made through 
             the web interface.
                    
            This object is now obsolete."
        ::= { webMgmntStats 1 }

    webMaxSessions OBJECT-TYPE
        SYNTAX Counter64
        MAX-ACCESS read-only
        STATUS obsolete
        DESCRIPTION
            "The maximum number of simultaneous sessions ever made
             through the web interface since power up.
                    
            This object is now obsolete."
        ::= { webMgmntStats 2 }

    webTotalSessions OBJECT-TYPE
        SYNTAX Counter64
        MAX-ACCESS read-only
        STATUS obsolete
        DESCRIPTION
            "The total number of sessions made through the web interface
             since power up.
                    
            This object is now obsolete."
        ::= { webMgmntStats 3 }

    webRejectedSessions OBJECT-TYPE
        SYNTAX Counter64
        MAX-ACCESS read-only
        STATUS obsolete
        DESCRIPTION
            "The number of sessions which have been rejected 
             through the web interface since power up.

             Sessions may be rejected due to either the maximum allowed 
             number of sessions being met or host access restrictions.
             
             Refer to the web access variables.
                    
            This object is now obsolete."
        ::= { webMgmntStats 4 }

    webTotalFramesTX OBJECT-TYPE
        SYNTAX Counter64
        MAX-ACCESS read-only
        STATUS obsolete
        DESCRIPTION
            "The total number of frames transmitted through the web interface
             since power up.
                    
            This object is now obsolete."
        ::= { webMgmntStats 5 }

    webTotalFramesRX OBJECT-TYPE
        SYNTAX Counter64
        MAX-ACCESS read-only
        STATUS obsolete
        DESCRIPTION
            "The total number of frames received through the web interface
             since power up.
                    
            This object is now obsolete."
        ::= { webMgmntStats 6 }

    webTotalBytesTX OBJECT-TYPE
        SYNTAX Counter64
        MAX-ACCESS read-only
        STATUS obsolete
        DESCRIPTION
            "The total number of bytes transmitted through the web interface
             since power up.
                    
            This object is now obsolete."
        ::= { webMgmntStats 7 }

    webTotalBytesRX OBJECT-TYPE
        SYNTAX Counter64
        MAX-ACCESS read-only
        STATUS obsolete
        DESCRIPTION
            "The total number of bytes received through the web interface
             since power up.
                    
            This object is now obsolete."
        ::= { webMgmntStats 8 }

    sictrlCurrActiveSessions OBJECT-TYPE
        SYNTAX Counter64
        MAX-ACCESS read-only
        STATUS obsolete
        DESCRIPTION
            "The current number of active sessions made through 
             the sictrl interface.
                    
            This object is now obsolete."
        ::= { sictrlMgmntStats 1 }

    sictrlMaxSessions OBJECT-TYPE
        SYNTAX Counter64
        MAX-ACCESS read-only
        STATUS obsolete
        DESCRIPTION
            "The maximum number of simultaneous sessions ever made
             through the sictrl interface since power up.
                    
            This object is now obsolete."
        ::= { sictrlMgmntStats 2 }

    sictrlTotalSessions OBJECT-TYPE
        SYNTAX Counter64
        MAX-ACCESS read-only
        STATUS obsolete
        DESCRIPTION
            "The total number of sessions made through the sictrl interface
             since power up.
                    
            This object is now obsolete."
        ::= { sictrlMgmntStats 3 }

    sictrlRejectedSessions OBJECT-TYPE
        SYNTAX Counter64
        MAX-ACCESS read-only
        STATUS obsolete
        DESCRIPTION
            "The number of sessions which have been rejected
             through the sictrl interface since power up.

             Sessions may be rejected due to either the maximum allowed
             number of sessions being met or host access restrictions.

             Refer to the sictrl access variables.
                    
            This object is now obsolete."
        ::= { sictrlMgmntStats 4 }

    sictrlTotalFramesTX OBJECT-TYPE
        SYNTAX Counter64
        MAX-ACCESS read-only
        STATUS obsolete
        DESCRIPTION
            "The total number of frames transmitted through the sictrl interface
             since power up."
        ::= { sictrlMgmntStats 5 }

    sictrlTotalFramesRX OBJECT-TYPE
        SYNTAX Counter64
        MAX-ACCESS read-only
        STATUS obsolete
        DESCRIPTION
            "The total number of frames received through the sictrl interface
             since power up."
        ::= { sictrlMgmntStats 6 }

    sictrlTotalBytesTX OBJECT-TYPE
        SYNTAX Counter64
        MAX-ACCESS read-only
        STATUS obsolete
        DESCRIPTION
            "The total number of bytes transmitted through the sictrl interface
             since power up."
        ::= { sictrlMgmntStats 7 }

    sictrlTotalBytesRX OBJECT-TYPE
        SYNTAX Counter64
        MAX-ACCESS read-only
        STATUS obsolete
        DESCRIPTION
            "The total number of bytes received through the sictrl interface
             since power up."
        ::= { sictrlMgmntStats 8 }

    telnetCurrActiveSessions OBJECT-TYPE
        SYNTAX Counter64
        MAX-ACCESS read-only
        STATUS current
        DESCRIPTION
            "The current number of active sessions made through
             the telnet interface."
        ::= { telnetMgmntStats 1 }

    telnetMaxSessions OBJECT-TYPE
        SYNTAX Counter64
        MAX-ACCESS read-only
        STATUS current
        DESCRIPTION
            "The maximum number of simultaneous sessions ever made
             through the telnet interface since power up."
        ::= { telnetMgmntStats 2 }

    telnetTotalSessions OBJECT-TYPE
        SYNTAX Counter64
        MAX-ACCESS read-only
        STATUS current
        DESCRIPTION
            "The total number of sessions made through the telnet interface
             since power up."
        ::= { telnetMgmntStats 3 }

    telnetRejectedSessions OBJECT-TYPE
        SYNTAX Counter64
        MAX-ACCESS read-only
        STATUS current
        DESCRIPTION
            "The number of sessions which have been rejected
             through the telnet interface since power up.

             Sessions may be rejected due to either the maximum allowed
             number of sessions being met or host access restrictions.

             Refer to the telnet access variables."
        ::= { telnetMgmntStats 4 }

    telnetTotalFramesTX OBJECT-TYPE
        SYNTAX Counter64
        MAX-ACCESS read-only
        STATUS current
        DESCRIPTION
            "The total number of frames transmitted through the telnet interface
             since power up."
        ::= { telnetMgmntStats 5 }

    telnetTotalFramesRX OBJECT-TYPE
        SYNTAX Counter64
        MAX-ACCESS read-only
        STATUS current
        DESCRIPTION
            "The total number of frames received through the telnet interface
             since power up."
        ::= { telnetMgmntStats 6 }

    telnetTotalBytesTX OBJECT-TYPE
        SYNTAX Counter64
        MAX-ACCESS read-only
        STATUS current
        DESCRIPTION
            "The total number of bytes transmitted through the telnet interface
             since power up."
        ::= { telnetMgmntStats 7 }

    telnetTotalBytesRX OBJECT-TYPE
        SYNTAX Counter64
        MAX-ACCESS read-only
        STATUS current
        DESCRIPTION
            "The total number of bytes received through the telnet interface
             since power up."
        ::= { telnetMgmntStats 8 }

    secureWebCurrActiveSessions OBJECT-TYPE
        SYNTAX Counter64
        MAX-ACCESS read-only
        STATUS obsolete
        DESCRIPTION
            "The current number of active sessions made through 
             the secure web interface.
                    
            This object is now obsolete."
        ::= { secureWebMgmntStats 1 }

    secureWebMaxSessions OBJECT-TYPE
        SYNTAX Counter64
        MAX-ACCESS read-only
        STATUS obsolete
        DESCRIPTION
            "The maximum number of simultaneous sessions ever made
             through the secure web interface since power up.
                    
            This object is now obsolete."
        ::= { secureWebMgmntStats 2 }

    secureWebTotalSessions OBJECT-TYPE
        SYNTAX Counter64
        MAX-ACCESS read-only
        STATUS obsolete
        DESCRIPTION
            "The total number of sessions made through the secure web interface
             since power up.
                    
            This object is now obsolete."
        ::= { secureWebMgmntStats 3 }

    secureWebRejectedSessions OBJECT-TYPE
        SYNTAX Counter64
        MAX-ACCESS read-only
        STATUS obsolete
        DESCRIPTION
            "The number of sessions which have been rejected 
             through the secure web interface since power up.

             Sessions may be rejected due to either the maximum allowed 
             number of sessions being met or host access restrictions.
             
             Refer to the secureWeb access variables.
                    
            This object is now obsolete."
        ::= { secureWebMgmntStats 4 }

    secureWebTotalFramesTX OBJECT-TYPE
        SYNTAX Counter64
        MAX-ACCESS read-only
        STATUS obsolete
        DESCRIPTION
            "The total number of frames transmitted through the secure web 
             interface since power up.
                    
            This object is now obsolete."
        ::= { secureWebMgmntStats 5 }

    secureWebTotalFramesRX OBJECT-TYPE
        SYNTAX Counter64
        MAX-ACCESS read-only
        STATUS obsolete
        DESCRIPTION
            "The total number of frames received through the secure web 
             interface since power up.
                    
            This object is now obsolete."
        ::= { secureWebMgmntStats 6 }

    secureWebTotalBytesTX OBJECT-TYPE
        SYNTAX Counter64
        MAX-ACCESS read-only
        STATUS obsolete
        DESCRIPTION
            "The total number of bytes transmitted through the secure web 
             interface since power up.
                    
            This object is now obsolete."
        ::= { secureWebMgmntStats 7 }

    secureWebTotalBytesRX OBJECT-TYPE
        SYNTAX Counter64
        MAX-ACCESS read-only
        STATUS obsolete
        DESCRIPTION
            "The total number of bytes received through the secure web
             interface since power up.
                    
            This object is now obsolete."
        ::= { secureWebMgmntStats 8 }

--------------------------------------------------------------------------------
--
-- Management / Hardware Flow Control
--
--------------------------------------------------------------------------------

    hwFlowNumber OBJECT-TYPE
        SYNTAX Integer32
        MAX-ACCESS read-only
        STATUS obsolete
        DESCRIPTION
            "The number of boards which permit hardware flow control.

            This object is now obsolete, as Hardware Flow is only
            for use by developers."
        ::= { hwFlowControl 1 }

    hwFlowTable OBJECT-TYPE
        SYNTAX SEQUENCE OF HwFlowEntry
        MAX-ACCESS not-accessible
        STATUS obsolete
        DESCRIPTION
            "A table containing the hardware flow control settings
             for the boards within this system.

             The number of entries in this table is given by the value of
             hwFlowNumber.

            This object is now obsolete, as Hardware Flow is only
            for use by developers."
        ::= { hwFlowControl 2 }

    hwFlowEntry OBJECT-TYPE
        SYNTAX HwFlowEntry
        MAX-ACCESS not-accessible
        STATUS obsolete
        DESCRIPTION
            "Hardware flow control setting information.

            This object is now obsolete, as Hardware Flow is only
            for use by developers."
        INDEX { hwFlowIndex }
        ::= { hwFlowTable 1 }

    HwFlowEntry ::=
        SEQUENCE {
            hwFlowIndex
                INTEGER,
            hwFlowDebug
                INTEGER,
            hwFlowConsole
                INTEGER
        }

    hwFlowIndex OBJECT-TYPE
        SYNTAX INTEGER {
            tcp(1),
            fsb(2),
            fcp(3)
        }
        MAX-ACCESS read-only
        STATUS obsolete
        DESCRIPTION
            "An identifier for each board.

             tcp(1) - the tcp board.
             fsb(2) - the filesystem board.
             fcp(3) - the fibre channel board.

            This object is now obsolete, as Hardware Flow is only
            for use by developers."
        ::= { hwFlowEntry 1 }

    hwFlowDebug OBJECT-TYPE
        SYNTAX INTEGER {
            enabled(1),
            disabled(2)
        }
        MAX-ACCESS read-only
        STATUS obsolete
        DESCRIPTION
            "Indicates whether hardware flow control is enabled on the
             debug port (port number 0) on this board.

            This object is now obsolete, as Hardware Flow is only
            for use by developers."
        ::= { hwFlowEntry 2 }

    hwFlowConsole OBJECT-TYPE
        SYNTAX INTEGER {
            enabled(1),
            disabled(2)
        }
        MAX-ACCESS read-only
        STATUS obsolete
        DESCRIPTION
            "Indicates whether hardware flow control is enabled on
             the console port (port number 1) on this board.

            This object is now obsolete, as Hardware Flow is only
            for use by developers."
        ::= { hwFlowEntry 3 }

--------------------------------------------------------------------------------
--
-- Trap Notifications
--
-- The agent may generate the following traps :
--
-- LinkUp, ColdStart
-- Authentication Failure (if configured)
--
--------------------------------------------------------------------------------

END
