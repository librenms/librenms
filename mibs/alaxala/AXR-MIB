--
-- Copyright(C) 2005-2013 ALAXALA Networks Corporation. All Rights Reserved.
--
-- AX7800R-MIB.my: Switching Router System information MIB file
--
AX7800R DEFINITIONS ::= BEGIN
IMPORTS
enterprises, OBJECT-TYPE, NetworkAddress, IpAddress,
Counter, Gauge, TimeTicks
        FROM RFC1155-SMI
RouterID, AreaID, Status, BigMetric, DesignatedRouterPriority,
HelloRange, Metric, PositiveInteger, UpToMaxAge
        FROM OSPF-MIB
OBJECT-TYPE
        FROM RFC-1212
TRAP-TYPE
        FROM RFC-1215
ifIndex, DisplayString
        FROM RFC1213-MIB
RowStatus, MacAddress, TruthValue, TimeStamp, PhysAddress, TimeInterval, StorageType
    FROM SNMPv2-TC
Ipv6IfIndex, Ipv6Address, Ipv6AddressPrefix
    FROM IPV6-TC
InterfaceIndex, InterfaceIndexOrZero
    FROM IF-MIB
InetAddressType,InetAddress,InetPortNumber
    FROM INET-ADDRESS-MIB
AddressFamilyNumbers
    FROM IANA-ADDRESS-FAMILY-NUMBERS-MIB
pimNeighborIfIndex
    FROM PIM-MIB
;

AxrMplsLdpIdentifier ::= OCTET STRING (SIZE (6))
AxrMplsLsrIdentifier ::= OCTET STRING (SIZE (4))
AxrMplsLdpGenAddr    ::= OCTET STRING (SIZE (0..60))
AxrMplsLdpLabelTypes ::= INTEGER { generic(1), atm(2), frameRelay(3) }

alaxala            OBJECT IDENTIFIER ::= { enterprises 21839 }
alaxalaProductId   OBJECT IDENTIFIER ::= { alaxala 1 }
axRouter           OBJECT IDENTIFIER ::= { alaxalaProductId 1 }
ax7800r            OBJECT IDENTIFIER ::= { axRouter 2 }
ax7700r            OBJECT IDENTIFIER ::= { axRouter 5 }

alaxalaMib         OBJECT IDENTIFIER ::= { alaxala 2 }
axrEx              OBJECT IDENTIFIER ::= { alaxalaMib 1 }

axrMib             OBJECT IDENTIFIER ::= { axrEx 1 }
ax7800rMib         OBJECT IDENTIFIER ::= { axrEx 2 }
ax7700rMib         OBJECT IDENTIFIER ::= { axrEx 5 }
--device independent
axrStats              OBJECT IDENTIFIER ::= { axrMib 1 }
axrPhysStats          OBJECT IDENTIFIER ::= { axrStats 1 }
axrSonetStats         OBJECT IDENTIFIER ::= { axrStats 3 }
axrIfStats            OBJECT IDENTIFIER ::= { axrStats 4 }
axrQoS                OBJECT IDENTIFIER ::= { axrStats 6 }
axrEtherTxQoS         OBJECT IDENTIFIER ::= { axrQoS 1 }
axrEthShaper          OBJECT IDENTIFIER ::= { axrQoS 4 }
axrEthShaperAgQue     OBJECT IDENTIFIER ::= { axrQoS 5 }

axrDHCP               OBJECT IDENTIFIER ::= { axrStats 10 }
axrIpStats            OBJECT IDENTIFIER ::= { axrStats 12 }

axrVpn                OBJECT IDENTIFIER ::= { axrMib 2 }
axrVpnIp              OBJECT IDENTIFIER ::= { axrVpn 1 }
axrVpnIpForward       OBJECT IDENTIFIER ::= { axrVpn 2 }
axrMplsLdpMIB         OBJECT IDENTIFIER ::= { axrMib 3 }
axrMplsLdpObjects       OBJECT IDENTIFIER ::= { axrMplsLdpMIB 1 }
axrMplsLdpLsrObjects    OBJECT IDENTIFIER ::= { axrMplsLdpObjects 1 }
axrMplsLdpEntityObjects OBJECT IDENTIFIER ::= { axrMplsLdpObjects 2 }
axrMplsLdpNotifications OBJECT IDENTIFIER ::= { axrMplsLdpMIB 2 }
axrMplsLdpConformance   OBJECT IDENTIFIER ::= { axrMplsLdpMIB 3 }

axrOadp                 OBJECT IDENTIFIER ::= { axrMib 7 }
axrOadpMIBObjects       OBJECT IDENTIFIER ::= { axrOadp 1 }
axrOadpGlobalInfo       OBJECT IDENTIFIER ::= { axrOadpMIBObjects 1 }
axrOadpPortInfo         OBJECT IDENTIFIER ::= { axrOadpMIBObjects 2 }
axrOadpNeighborInfo     OBJECT IDENTIFIER ::= { axrOadpMIBObjects 3 }
axrOadpMIBNotifications OBJECT IDENTIFIER ::= { axrOadp 2 }

axrFlow					OBJECT IDENTIFIER  ::= { axrMib 8 }
axrFlowResources	    	OBJECT IDENTIFIER  ::= { axrFlow 2 }
axrFlowFilter	    	OBJECT IDENTIFIER  ::= { axrFlow 3 }
axrFlowFilterStats		OBJECT IDENTIFIER  ::= { axrFlow 4 }
axrFlowQos	        	OBJECT IDENTIFIER  ::= { axrFlow 5 }
axrFlowQosStats	    	OBJECT IDENTIFIER  ::= { axrFlow 6 }

axrOspf               OBJECT IDENTIFIER ::= { axrMib 14 }
axrOspfTrap           OBJECT IDENTIFIER ::= { axrOspf 16 }
axrOspfTraps          OBJECT IDENTIFIER ::= { axrOspfTrap 2 }
axrOspfv3             OBJECT IDENTIFIER ::= { axrMib 15 }

axrPimMIB             OBJECT IDENTIFIER ::= { axrMib 24 }
axrPimMIBObjects      OBJECT IDENTIFIER ::= { axrPimMIB 1 }

axrIsisMIB             OBJECT IDENTIFIER ::= { axrMib 37 }
axrIsisObjects         OBJECT IDENTIFIER ::= { axrIsisMIB 1 }
axrIsisSystem          OBJECT IDENTIFIER ::= { axrIsisObjects 1 }
axrIsisSysLevel        OBJECT IDENTIFIER ::= { axrIsisObjects 2 }
axrIsisCirc            OBJECT IDENTIFIER ::= { axrIsisObjects 3 }
axrIsisNotification    OBJECT IDENTIFIER ::= { axrIsisObjects 10 }
axrIsisNotifications   OBJECT IDENTIFIER ::= { axrIsisMIB 2 }

axrStatic              OBJECT IDENTIFIER ::= { axrMib 38 }
axrStaticTrap          OBJECT IDENTIFIER ::= { axrStatic 2 }

axrBootManagement    OBJECT IDENTIFIER ::= { axrMib 51 }
axrLogin             OBJECT IDENTIFIER ::= { axrMib 52 }

axrlldp                      OBJECT IDENTIFIER ::= { axrMib 100 }
axrlldpConfiguration         OBJECT IDENTIFIER ::= { axrlldp 1 }
axrlldpStats                 OBJECT IDENTIFIER ::= { axrlldp 2 }
axrlldpLocalSystemData       OBJECT IDENTIFIER ::= { axrlldp 3 }
axrlldpRemoteSystemData      OBJECT IDENTIFIER ::= { axrlldp 4 }
axrlldpRemoteOriginInfoData  OBJECT IDENTIFIER ::= { axrlldp 20 }

axrBfdMIB             OBJECT IDENTIFIER ::= { axrMib 201 }
axrBfdObjects         OBJECT IDENTIFIER ::= { axrBfdMIB 1 }
axrBfdScalarObjects   OBJECT IDENTIFIER ::= { axrBfdObjects 1 }

ax7800rRouter           OBJECT IDENTIFIER ::= { ax7800rMib 1 }
ax7800rSoftware         OBJECT IDENTIFIER ::= { ax7800rRouter 2 }
ax7800rSystemMsg        OBJECT IDENTIFIER ::= { ax7800rRouter 3 }
ax7800rSnmpAgent        OBJECT IDENTIFIER ::= { ax7800rRouter 4 }
ax7800rLicense          OBJECT IDENTIFIER ::= { ax7800rRouter 6 }
ax7800rDevice           OBJECT IDENTIFIER ::= { ax7800rMib 2 }
ax7800rChassis          OBJECT IDENTIFIER ::= { ax7800rDevice 1 }
ax7800rBcuBoard          OBJECT IDENTIFIER ::= { ax7800rDevice 2 }
ax7800rPruBoard          OBJECT IDENTIFIER ::= { ax7800rDevice 3 }
ax7800rNifBoard         OBJECT IDENTIFIER ::= { ax7800rDevice 4 }
ax7800rPhysLine         OBJECT IDENTIFIER ::= { ax7800rDevice 5 }
ax7800rInterface        OBJECT IDENTIFIER ::= { ax7800rDevice 6 }

ax7700rRouter           OBJECT IDENTIFIER ::= { ax7700rMib 1 }
ax7700rSoftware         OBJECT IDENTIFIER ::= { ax7700rRouter 2 }
ax7700rSystemMsg        OBJECT IDENTIFIER ::= { ax7700rRouter 3 }
ax7700rSnmpAgent        OBJECT IDENTIFIER ::= { ax7700rRouter 4 }
ax7700rLicense          OBJECT IDENTIFIER ::= { ax7700rRouter 6 }
ax7700rDevice           OBJECT IDENTIFIER ::= { ax7700rMib 2 }
ax7700rChassis          OBJECT IDENTIFIER ::= { ax7700rDevice 1 }
ax7700rBcuBoard          OBJECT IDENTIFIER ::= { ax7700rDevice 2 }
ax7700rPruBoard          OBJECT IDENTIFIER ::= { ax7700rDevice 3 }
ax7700rNifBoard         OBJECT IDENTIFIER ::= { ax7700rDevice 4 }
ax7700rPhysLine         OBJECT IDENTIFIER ::= { ax7700rDevice 5 }
ax7700rInterface        OBJECT IDENTIFIER ::= { ax7700rDevice 6 }

axrPhysStatsTable OBJECT-TYPE
	SYNTAX  SEQUENCE OF AxrPhysStatsTableEntry
	ACCESS  not-accessible
	STATUS  mandatory
	DESCRIPTION
		"A table containing  statistics for physical and time slots layer
		interface."
	::= { axrPhysStats 1 }

axrPhysStatsEntry OBJECT-TYPE
	SYNTAX  AxrPhysStatsTableEntry
	ACCESS  not-accessible
	STATUS  mandatory
	DESCRIPTION
		"An entry containing the physical and time slots layer statistics
		for a particular interface."
	INDEX   { axrPhysStatsIfIndex }
	::= { axrPhysStatsTable 1 }

	AxrPhysStatsTableEntry ::=
		SEQUENCE {
		  axrPhysStatsIfIndex
			INTEGER,
		  axrPhysStatsIfDescr
			DisplayString,
		  axrPhysStatsIfType
			INTEGER,
		  axrPhysStatsInFCSs
			Counter,
		  axrPhysStatsInAborts
			Counter,
		  axrPhysStatsOverrun
			Counter,
		  axrPhysStatsUnderrun
			Counter,
		  axrPhysStatsInOddbits
			Counter,
		  axrPhysStatsInShortfrms
			Counter,
		  axrPhysStatsSendTimeout
			Counter,
		  axrPhysStatsOutAborts
			Counter,
		  axrPhysStatsInLongfrms
			Counter
		}

axrPhysStatsIfIndex OBJECT-TYPE
	SYNTAX  INTEGER
	ACCESS  not-accessible
	STATUS  mandatory
	DESCRIPTION
		"The value of this object identifies the physical layer interface
		or the time slot layer interface for WAN."
	::= { axrPhysStatsEntry 1 }

axrPhysStatsIfDescr OBJECT-TYPE
	SYNTAX  DisplayString
	ACCESS  read-only
	STATUS  mandatory
	DESCRIPTION
		"A textual string containing information about the interface.
		Same as ifDescr (MIB II)."
	::= { axrPhysStatsEntry 2 }


axrPhysStatsIfType OBJECT-TYPE
	SYNTAX  INTEGER {
		other(1),
		v24(2),
		v35(5),
		x21(6),
		bri(21),
		j1(31),
		j2(41),
		oc-3(101),
		oc-12(102),
		oc-48(103),
		oc-192(104),
		e1(201),
		e3(202),
		t1(203),
		t3(204)
	      }
	ACCESS  read-only
	STATUS  mandatory
	DESCRIPTION
		"The hardware type of physical interfaces."
	::= { axrPhysStatsEntry 3 }

axrPhysStatsInFCSs OBJECT-TYPE
	SYNTAX  Counter
	ACCESS  read-only
	STATUS  mandatory
	DESCRIPTION
		"Number of FCS error frames that received."
	::= { axrPhysStatsEntry 4 }

axrPhysStatsInAborts OBJECT-TYPE
	SYNTAX  Counter
	ACCESS  read-only
	STATUS  mandatory
	DESCRIPTION
		"Number of abort frames that received."
	::= { axrPhysStatsEntry 5 }

axrPhysStatsOverrun OBJECT-TYPE
	SYNTAX  Counter
	ACCESS  read-only
	STATUS  mandatory
	DESCRIPTION
		"The number of times that overrun error occurred on receiving time."
	::= { axrPhysStatsEntry 6 }

axrPhysStatsUnderrun OBJECT-TYPE
	SYNTAX  Counter
	ACCESS  read-only
	STATUS  mandatory
	DESCRIPTION
		"Number of that a transmission underrun errors occurred."
	::= { axrPhysStatsEntry 7 }

axrPhysStatsInOddbits OBJECT-TYPE
	SYNTAX  Counter
	ACCESS  read-only
	STATUS  mandatory
	DESCRIPTION
		"Number of odd bit frames that received."
	::= { axrPhysStatsEntry 8 }

axrPhysStatsInShortfrms OBJECT-TYPE
	SYNTAX  Counter
	ACCESS  read-only
	STATUS  mandatory
	DESCRIPTION
		"Number of short frames that received."
	::= { axrPhysStatsEntry 9 }

axrPhysStatsSendTimeout OBJECT-TYPE
	SYNTAX  Counter
	ACCESS  read-only
	STATUS  mandatory
	DESCRIPTION
		"Number of times that a transmission timeout ocurred."
	::= { axrPhysStatsEntry 10 }

axrPhysStatsOutAborts OBJECT-TYPE
	SYNTAX  Counter
	ACCESS  read-only
	STATUS  mandatory
	DESCRIPTION
		"The number of transmission of abort frames."
	::= { axrPhysStatsEntry 11 }

axrPhysStatsInLongfrms OBJECT-TYPE
	SYNTAX  Counter
	ACCESS  read-only
	STATUS  mandatory
	DESCRIPTION
		"Number of long frames that received."
	::= { axrPhysStatsEntry 12 }

axrSonetSectionStatsTable OBJECT-TYPE
	SYNTAX  SEQUENCE OF AxrSonetSectionStatsTableEntry
	ACCESS  not-accessible
	STATUS  mandatory
	DESCRIPTION
		"A table containing SONET section statistics for sonet interfaces."
	::= { axrSonetStats 1 }

axrSonetSectionStatsEntry OBJECT-TYPE
	SYNTAX  AxrSonetSectionStatsTableEntry
	ACCESS  not-accessible
	STATUS  mandatory
	DESCRIPTION
		"An entry containing SONET section statistics for sonet interfaces."
	INDEX   { axrSonetSectionStatsIfIndex }
	::= { axrSonetSectionStatsTable 1 }

	AxrSonetSectionStatsTableEntry ::=
		SEQUENCE {
		  axrSonetSectionStatsIfIndex
			INTEGER,
		  axrSonetSectionStatsLOS
			Counter,
		  axrSonetSectionStatsLOF
			Counter,
		  axrSonetSectionStatsOOF
			Counter,
		  axrSonetSectionStatsBIP8
			Counter,
		  axrSonetSectionStatsB2EBER
			Counter,
		  axrSonetSectionStatsB2SD
			Counter
		}

axrSonetSectionStatsIfIndex OBJECT-TYPE
	SYNTAX  INTEGER
	ACCESS  not-accessible
	STATUS  mandatory
	DESCRIPTION
		"The value of this object identifies for a SONET interface.
		This object has the same value as the ifIndex object."
	::= { axrSonetSectionStatsEntry 1 }

axrSonetSectionStatsLOS OBJECT-TYPE
	SYNTAX  Counter
	ACCESS  read-only
	STATUS  mandatory
	DESCRIPTION
		"Number of times LOS(Loss Of Signal)."
	::= { axrSonetSectionStatsEntry 2 }

axrSonetSectionStatsLOF OBJECT-TYPE
	SYNTAX  Counter
	ACCESS  read-only
	STATUS  mandatory
	DESCRIPTION
		"Number of times LOF(Loss Of Frame).An LOF defect is declared
		when OOF(Out of Frame) defect persists for a period of 3 milliseconds."
	::= { axrSonetSectionStatsEntry 3 }

axrSonetSectionStatsOOF OBJECT-TYPE
	SYNTAX  Counter
	ACCESS  read-only
	STATUS  mandatory
	DESCRIPTION
		"This object count when out of synchronous."
	::= { axrSonetSectionStatsEntry 4 }

axrSonetSectionStatsBIP8 OBJECT-TYPE
	SYNTAX  Counter
	ACCESS  read-only
	STATUS  mandatory
	DESCRIPTION
		"Number of times S-BIP8(Bit Interleaved Parity 8) Error."
	::= { axrSonetSectionStatsEntry 5 }

axrSonetSectionStatsB2EBER OBJECT-TYPE
	SYNTAX  Counter
	ACCESS  read-only
	STATUS  mandatory
	DESCRIPTION
		"Number of times B2EBER Error."
	::= { axrSonetSectionStatsEntry 6 }

axrSonetSectionStatsB2SD OBJECT-TYPE
	SYNTAX  Counter
	ACCESS  read-only
	STATUS  mandatory
	DESCRIPTION
		"Number of times B2SD Error."
	::= { axrSonetSectionStatsEntry 7 }

axrSonetLineStatsTable OBJECT-TYPE
	SYNTAX  SEQUENCE OF AxrSonetLineStatsTableEntry
	ACCESS  not-accessible
	STATUS  mandatory
	DESCRIPTION
		"A table containing line statistics for sonet interfaces."
	::= { axrSonetStats 2 }

axrSonetLineStatsEntry OBJECT-TYPE
	SYNTAX  AxrSonetLineStatsTableEntry
	ACCESS  not-accessible
	STATUS  mandatory
	DESCRIPTION
		"An entry containing line statistics for sonet interfaces."
	INDEX   { axrSonetLineStatsIfIndex }
	::= { axrSonetLineStatsTable 1 }

	AxrSonetLineStatsTableEntry ::=
		SEQUENCE {
		  axrSonetLineStatsIfIndex
			INTEGER,
		  axrSonetLineStatsAIS
			Counter,
		  axrSonetLineStatsRDI
			Counter,
		  axrSonetLineStatsBIP24
			Counter,
		  axrSonetLineStatsFEBE
			Counter,
		  axrSonetLineStatsBIP384
			Counter,
		  axrSonetLineStatsBIP1536
			Counter,
		  axrSonetLineStatsREI
			Counter
		}

axrSonetLineStatsIfIndex OBJECT-TYPE
	SYNTAX  INTEGER
	ACCESS  not-accessible
	STATUS  mandatory
	DESCRIPTION
		"The value of this object identifies for a sonet interface.
		This object has the same value as the ifIndex object."
	::= { axrSonetLineStatsEntry 1 }

axrSonetLineStatsAIS OBJECT-TYPE
	SYNTAX  Counter
	ACCESS  read-only
	STATUS  mandatory
	DESCRIPTION
		"Number of Line L-AIS(Alarm Indication Signal) that received
		at sonet interface."
	::= { axrSonetLineStatsEntry 2 }

axrSonetLineStatsRDI OBJECT-TYPE
	SYNTAX  Counter
	ACCESS  read-only
	STATUS  mandatory
	DESCRIPTION
		"Number of L-RDI(Remote Defect Indication) errors that received
		on the sonet interface."
	::= { axrSonetLineStatsEntry 3 }

axrSonetLineStatsBIP24 OBJECT-TYPE
	SYNTAX  Counter
	ACCESS  read-only
	STATUS  mandatory
	DESCRIPTION
		"Number of L-BIP24(Bit Interleaved Parity 24) errors on the sonet
		interface."
	::= { axrSonetLineStatsEntry 4 }

axrSonetLineStatsFEBE OBJECT-TYPE
	SYNTAX  Counter
	ACCESS  read-only
	STATUS  mandatory
	DESCRIPTION
		"Number of L-FEBE(Line Far End Block Error) that received on the sonet
		interface."
	::= { axrSonetLineStatsEntry 5 }

axrSonetLineStatsBIP384 OBJECT-TYPE
	SYNTAX  Counter
	ACCESS  read-only
	STATUS  mandatory
	DESCRIPTION
		"Number of L-BIP384(Bit Interleaved Parity 384) errors on the sonet
		interface."
	::= { axrSonetLineStatsEntry 6 }

axrSonetLineStatsBIP1536 OBJECT-TYPE
	SYNTAX  Counter
	ACCESS  read-only
	STATUS  mandatory
	DESCRIPTION
		"Number of L-BIP1536(Bit Interleaved Parity 1536) errors on the sonet
		interface."
	::= { axrSonetLineStatsEntry 7 }

axrSonetLineStatsREI OBJECT-TYPE
	SYNTAX  Counter
	ACCESS  read-only
	STATUS  mandatory
	DESCRIPTION
		"Number of L-REI(Line-path Remote Error Indication)that 
                 received on the sonet interface."
	::= { axrSonetLineStatsEntry 8 }

axrSonetPathStatsTable OBJECT-TYPE
	SYNTAX  SEQUENCE OF AxrSonetPathStatsTableEntry
	ACCESS  not-accessible
	STATUS  mandatory
	DESCRIPTION
		"A table containing Path statistics for SONET interface."
	::= { axrSonetStats 3 }

axrSonetPathStatsEntry OBJECT-TYPE
	SYNTAX  AxrSonetPathStatsTableEntry
	ACCESS  not-accessible
	STATUS  mandatory
	DESCRIPTION
		"An entry containing Path statistics for SONET interface."
	INDEX   { axrSonetPathStatsIfIndex }
	::= { axrSonetPathStatsTable 1 }

	AxrSonetPathStatsTableEntry ::=
		SEQUENCE {
		  axrSonetPathStatsIfIndex
			INTEGER,
		  axrSonetPathStatsLOP
			Counter,
		  axrSonetPathStatsAIS
			Counter,
		  axrSonetPathStatsRDI
			Counter,
		  axrSonetPathStatsBIP8
			Counter,
		  axrSonetPathStatsFEBE
			Counter,
		  axrSonetPathStatsREI
			Counter,
		  axrSonetRDIPathStatsAISLOP
			Counter,
		  axrSonetRDIPathStatsUNEQ
			Counter,
		  axrSonetRDIPathStatsPLM
			Counter,
		  axrSonetPathStatsUNEQ
			Counter,
		  axrSonetPathStatsPLM
			Counter
		}

axrSonetPathStatsIfIndex OBJECT-TYPE
	SYNTAX  INTEGER
	ACCESS  not-accessible
	STATUS  mandatory
	DESCRIPTION
		"The IfIndex value of interface that use SONET."
	::= { axrSonetPathStatsEntry 1 }

axrSonetPathStatsLOP OBJECT-TYPE
	SYNTAX  Counter
	ACCESS  read-only
	STATUS  mandatory
	DESCRIPTION
		"Number of LOP(Loss Of Pointer) errors that received on the sonet
		interface."
	::= { axrSonetPathStatsEntry 2 }

axrSonetPathStatsAIS OBJECT-TYPE
	SYNTAX  Counter
	ACCESS  read-only
	STATUS  mandatory
	DESCRIPTION
		"Number of P-AIS(Alarm Indication Signal) that received on the sonet
		interface."
	::= { axrSonetPathStatsEntry 3 }

axrSonetPathStatsRDI OBJECT-TYPE
	SYNTAX  Counter
	ACCESS  read-only
	STATUS  mandatory
	DESCRIPTION
		"Number of P-RDI(Path Remote Defect Indication) that received
		on the sonet interface."
	::= { axrSonetPathStatsEntry 4 }

axrSonetPathStatsBIP8 OBJECT-TYPE
	SYNTAX  Counter
	ACCESS  read-only
	STATUS  mandatory
	DESCRIPTION
		"Number of P-BIP8(Bit Interleaved Parity 8) errors that received
		on the sonet interface."
	::= { axrSonetPathStatsEntry 5 }

axrSonetPathStatsFEBE OBJECT-TYPE
	SYNTAX  Counter
	ACCESS  read-only
	STATUS  mandatory
	DESCRIPTION
		"Number of P-FEBE(Far End Block Error) errors that received
		on the sonet interface."
	::= { axrSonetPathStatsEntry 6 }

axrSonetPathStatsREI OBJECT-TYPE
	SYNTAX  Counter
	ACCESS  read-only
	STATUS  mandatory
	DESCRIPTION
		"Number of  P-REI(Path-Remote Error Indication) 
                 errors that received on the sonet interface."
	::= { axrSonetPathStatsEntry 7 }

axrSonetRDIPathStatsAISLOP OBJECT-TYPE
	SYNTAX  Counter
	ACCESS  read-only
	STATUS  mandatory
	DESCRIPTION
		"Number of P-AIS/P-LOP(Remote Defect Indication Path-Alarm 
                 Indication Signal/Path-Loss Of Pointer) that received
		 on the sonet interface."
	::= { axrSonetPathStatsEntry 8 }

axrSonetRDIPathStatsUNEQ OBJECT-TYPE
	SYNTAX  Counter
	ACCESS  read-only
	STATUS  mandatory
	DESCRIPTION
		"Number of P-UNEQ(Remote Defect Indication Path-UNEQuipment) 
                 errors that received on the sonet interface."
	::= { axrSonetPathStatsEntry 9 }

axrSonetRDIPathStatsPLM OBJECT-TYPE
	SYNTAX  Counter
	ACCESS  read-only
	STATUS  mandatory
	DESCRIPTION
		"Number of P-PLM(Remote Defect Indication
                 Path-Payload Label Mismatch) that received
		 on the sonet interface."
	::= { axrSonetPathStatsEntry 10 }

axrSonetPathStatsUNEQ OBJECT-TYPE
	SYNTAX  Counter
	ACCESS  read-only
	STATUS  mandatory
	DESCRIPTION
		"Number of P-UNEQ(Path-UNEQuipment) errors 
                 that received on the sonet interface."
	::= { axrSonetPathStatsEntry 11 }

axrSonetPathStatsPLM OBJECT-TYPE
	SYNTAX  Counter
	ACCESS  read-only
	STATUS  mandatory
	DESCRIPTION
		"Number of P-PLM(Remote Defect Indication 
                 Path-Payload Label Mismatch) errors that 
                 received on the sonet interface."
	::= { axrSonetPathStatsEntry 12 }

axrIfStatsTable OBJECT-TYPE
	SYNTAX  SEQUENCE OF AxrIfStatsTableEntry
	ACCESS  not-accessible
	STATUS  mandatory
	DESCRIPTION
		"A table containing extension statistics for more than 100,000,000
		bps interface."
	::= { axrIfStats 1 }

axrIfStatsEntry OBJECT-TYPE
	SYNTAX  AxrIfStatsTableEntry
	ACCESS  not-accessible
	STATUS  mandatory
	DESCRIPTION
		"An entry containing extension statistics for interface."
	INDEX   { axrIfStatsIndex }
	::= { axrIfStatsTable 1 }

	AxrIfStatsTableEntry ::=
		SEQUENCE {
		  axrIfStatsIndex
			INTEGER,
		  axrIfStatsName
			DisplayString,
		  axrIfStatsInMegaOctets
			Counter,
		  axrIfStatsInUcastMegaPkts
			Counter,
		  axrIfStatsInMulticastMegaPkts
			Counter,
		  axrIfStatsInBroadcastMegaPkts
			Counter,
		  axrIfStatsOutMegaOctets
			Counter,
		  axrIfStatsOutUcastMegaPkts
			Counter,
		  axrIfStatsOutMulticastMegaPkts
			Counter,
		  axrIfStatsOutBroadcastMegaPkts
			Counter,
		  axrIfStatsHighSpeed
			Counter
		}

axrIfStatsIndex OBJECT-TYPE
	SYNTAX  INTEGER
	ACCESS  not-accessible
	STATUS  mandatory
	DESCRIPTION
		"This object value is same as Ifindex which interface index
		of a system."
	::= { axrIfStatsEntry 1 }

axrIfStatsName OBJECT-TYPE
	SYNTAX  DisplayString
	ACCESS  read-only
	STATUS  mandatory
	DESCRIPTION
		"Interfaces name. Same as ifDescr."
	::= { axrIfStatsEntry 2 }

axrIfStatsInMegaOctets OBJECT-TYPE
	SYNTAX  Counter
	ACCESS  read-only
	STATUS  mandatory
	DESCRIPTION
		"Number of octets that received on the interface. This value is
		displayed in mega-octets(M). Value of 0 through 999,999 are rounded
		down."
	::= { axrIfStatsEntry 3 }

axrIfStatsInUcastMegaPkts OBJECT-TYPE
	SYNTAX  Counter
	ACCESS  read-only
	STATUS  mandatory
	DESCRIPTION
		"Number of subnetwork-unicast packets that received on the interface.
		This value is displayed in mega-packets(M).Value of 0 through 999,999
		are rounded down."
	::= { axrIfStatsEntry 4 }

axrIfStatsInMulticastMegaPkts OBJECT-TYPE
	SYNTAX  Counter
	ACCESS  read-only
	STATUS  mandatory
	DESCRIPTION
		"Number of multicast mega-packets that received on the interface.
		this value is displayed in mega-packets(M).Value of 0 through 999,999
		are rounded down."
	::= { axrIfStatsEntry 5 }


axrIfStatsInBroadcastMegaPkts OBJECT-TYPE
	SYNTAX  Counter
	ACCESS  read-only
	STATUS  mandatory
	DESCRIPTION
		"The number of non-unicast packets delivered to a higher-layer
		protocol. The value is displayed in mega-packets (M). Value of 0
		through 999,999 are rounded down. "
	::= { axrIfStatsEntry 6 }

axrIfStatsOutMegaOctets OBJECT-TYPE
	SYNTAX  Counter
	ACCESS  read-only
	STATUS  mandatory
	DESCRIPTION
		"The total number of octets transmitted out of the interface.
		The value is displayed in mega-octets(M). Value of 0 through 999,999
		are rounded down."
	::= { axrIfStatsEntry 7 }

axrIfStatsOutUcastMegaPkts OBJECT-TYPE
	SYNTAX  Counter
	ACCESS  read-only
	STATUS  mandatory
	DESCRIPTION
		"The total number of packets that higher-level protocols requested
		be transmitted to a subnetwork-unicast address.The value is displayed
		in mega packets(M). Value of 0 through 999,999 are rounded down."
	::= { axrIfStatsEntry 8 }

axrIfStatsOutMulticastMegaPkts OBJECT-TYPE
	SYNTAX  Counter
	ACCESS  read-only
	STATUS  mandatory
	DESCRIPTION
		"Number of multicast packets that transmitted on the interface.
		This value is displayed in mega-packets(M). Value of 0 through
		999,999 are rounded down."
	::= { axrIfStatsEntry 9 }

axrIfStatsOutBroadcastMegaPkts OBJECT-TYPE
	SYNTAX  Counter
	ACCESS  read-only
	STATUS  mandatory
	DESCRIPTION
		"Number of broadcast packets that transmitted on the interface.
		This value is displayed in mega-packets(M). Value of 0 through
		999,999 are rounded down. "
	::= { axrIfStatsEntry 10 }

axrIfStatsHighSpeed OBJECT-TYPE
	SYNTAX  Counter
	ACCESS  read-only
	STATUS  mandatory
	DESCRIPTION
		"A circuit speed.This value is displayed in mega-bps[Mbps].
		Round off the 1,000,000bps. "
	::= { axrIfStatsEntry 11 }

--  QoS interface statistics Variables

axrEtherTxQoSStatsTable OBJECT-TYPE
	SYNTAX  SEQUENCE OF AxrEtherTxQoSStatsEntry
	ACCESS  not-accessible
	STATUS  mandatory
	DESCRIPTION
		"A collection of QoS statistics kept for a particular
		Ethernet interface."
	::= { axrEtherTxQoS 1 }

axrEtherTxQoSStatsEntry OBJECT-TYPE
	SYNTAX  AxrEtherTxQoSStatsEntry
	ACCESS  not-accessible
	STATUS  mandatory
	DESCRIPTION
		"An entry containing QoS statistics for a particular 
		Ethernet interface."
    INDEX { axrEtherTxQoSStatsIndex }
	::= { axrEtherTxQoSStatsTable 1 }

	AxrEtherTxQoSStatsEntry ::=
		SEQUENCE {
            axrEtherTxQoSStatsIndex	INTEGER,
            axrEtherTxQoSStatsMaxQnum	INTEGER,
            axrEtherTxQoSStatsLimitQlen	INTEGER,
            axrEtherTxQoSStatsTotalOutFrames	Counter,
            axrEtherTxQoSStatsTotalOutBytesHigh	Counter,
            axrEtherTxQoSStatsTotalOutBytesLow	Counter,
            axrEtherTxQoSStatsTotalDiscardFrames	Counter
		}

axrEtherTxQoSStatsIndex OBJECT-TYPE
	SYNTAX  INTEGER
	ACCESS  not-accessible
	STATUS  mandatory
	DESCRIPTION
		"Identified by a particular value of this
		index is same value of ifIndex.Its value ranges
		between 1 and the value of ifNumber."
	::= { axrEtherTxQoSStatsEntry 1 }

axrEtherTxQoSStatsMaxQnum OBJECT-TYPE
	SYNTAX  INTEGER
	ACCESS  read-only
	STATUS  mandatory
	DESCRIPTION
		"Max length of queue for an ethernet interface."
	::= { axrEtherTxQoSStatsEntry 2 }

axrEtherTxQoSStatsLimitQlen OBJECT-TYPE
	SYNTAX  INTEGER
	ACCESS  read-only
	STATUS  mandatory
	DESCRIPTION
		"The limit length of outband queue for an ethernet interface."
	::= { axrEtherTxQoSStatsEntry 3 }

axrEtherTxQoSStatsTotalOutFrames OBJECT-TYPE
	SYNTAX  Counter
	ACCESS  read-only
	STATUS  mandatory
	DESCRIPTION
		"The total number of  packets transmitted out of the
		interface."
	::= { axrEtherTxQoSStatsEntry 4 }

axrEtherTxQoSStatsTotalOutBytesHigh OBJECT-TYPE
	SYNTAX  Counter
	ACCESS  read-only
	STATUS  mandatory
	DESCRIPTION
		"The total number of octets transmitted out of the
		interface.(Higher 4 bytes)"
	::= { axrEtherTxQoSStatsEntry 5 }

axrEtherTxQoSStatsTotalOutBytesLow OBJECT-TYPE
	SYNTAX  Counter
	ACCESS  read-only
	STATUS  mandatory
	DESCRIPTION
		"The total number of octets transmitted out of the
		interface.(Lower 4 bytes)"
	::= { axrEtherTxQoSStatsEntry 6 }

axrEtherTxQoSStatsTotalDiscardFrames OBJECT-TYPE
	SYNTAX  Counter
	ACCESS  read-only
	STATUS  mandatory
	DESCRIPTION
		"The number of outbound packets which were chosen
		to be discarded ."
	::= { axrEtherTxQoSStatsEntry 7 }

axrEtherTxQoSStatsQueueTable OBJECT-TYPE
	SYNTAX  SEQUENCE OF AxrEtherTxQoSStatsQueueEntry
	ACCESS  not-accessible
	STATUS  mandatory
	DESCRIPTION
		"A collection of priority queue statistics."
	::= { axrEtherTxQoS 2 }

axrEtherTxQoSStatsQueueEntry OBJECT-TYPE
	SYNTAX  AxrEtherTxQoSStatsQueueEntry
	ACCESS  not-accessible
	STATUS  mandatory
	DESCRIPTION
		"A entry of priority queue statistics."
    INDEX { axrEtherTxQoSStatsQueueIndex , axrEtherTxQoSStatsQueueQueIndex }
	::= { axrEtherTxQoSStatsQueueTable 1 }

	AxrEtherTxQoSStatsQueueEntry ::=
		SEQUENCE {
            axrEtherTxQoSStatsQueueIndex	        INTEGER,
            axrEtherTxQoSStatsQueueQueIndex	INTEGER,
            axrEtherTxQoSStatsQueueQlen	        INTEGER,
            axrEtherTxQoSStatsQueueMaxQlen	INTEGER,
            axrEtherTxQoSStatsQueueDiscardFramesClass1	Counter64,
            axrEtherTxQoSStatsQueueDiscardFramesClass2	Counter64,
            axrEtherTxQoSStatsQueueDiscardFramesClass3	Counter64,
            axrEtherTxQoSStatsQueueDiscardFramesClass4	Counter64
		}

axrEtherTxQoSStatsQueueIndex OBJECT-TYPE
	SYNTAX  INTEGER
	ACCESS  not-accessible
	STATUS  mandatory
	DESCRIPTION
		"Identified by a particular value of this
		index is same value of ifIndex.Its value ranges
		between 1 and the value of ifNumber."
	::= { axrEtherTxQoSStatsQueueEntry 1 }

axrEtherTxQoSStatsQueueQueIndex OBJECT-TYPE
	SYNTAX  INTEGER
	ACCESS  not-accessible
	STATUS  mandatory
	DESCRIPTION
		"An index that uniquely identifies the particular
		queue.Its value ranges between 1 and the value of
		axrEtherTxQoSStatsMaxQnum."
	::= { axrEtherTxQoSStatsQueueEntry 2 }

axrEtherTxQoSStatsQueueQlen OBJECT-TYPE
	SYNTAX  INTEGER
	ACCESS  read-only
	STATUS  mandatory
	DESCRIPTION
		"A length of outbound priority queue for a interface."
	::= { axrEtherTxQoSStatsQueueEntry 3 }

axrEtherTxQoSStatsQueueMaxQlen OBJECT-TYPE
	SYNTAX  INTEGER
	ACCESS  read-only
	STATUS  mandatory
	DESCRIPTION
		"Max length of outband priority queue for a interface since
		system was up."
	::= { axrEtherTxQoSStatsQueueEntry 4 }

axrEtherTxQoSStatsQueueDiscardFramesClass1 OBJECT-TYPE
	SYNTAX  Counter64
	ACCESS  read-only
	STATUS  mandatory
	DESCRIPTION
		"The number of discard frames in the discard class 
		 1 of output priority queue."
	::= { axrEtherTxQoSStatsQueueEntry 5 }

axrEtherTxQoSStatsQueueDiscardFramesClass2 OBJECT-TYPE
	SYNTAX  Counter64
	ACCESS  read-only
	STATUS  mandatory
	DESCRIPTION
		"The number of discard frames in the discard class 
		 2 of output priority queue."
	::= { axrEtherTxQoSStatsQueueEntry 6 }

axrEtherTxQoSStatsQueueDiscardFramesClass3 OBJECT-TYPE
	SYNTAX  Counter64
	ACCESS  read-only
	STATUS  mandatory
	DESCRIPTION
		"The number of discard frames in the discard class 
		 3 of output priority queue."
	::= { axrEtherTxQoSStatsQueueEntry 7 }

axrEtherTxQoSStatsQueueDiscardFramesClass4 OBJECT-TYPE
	SYNTAX  Counter64
	ACCESS  read-only
	STATUS  mandatory
	DESCRIPTION
		"The number of discard frames in the discard class 
		 4 of output priority queue."
	::= { axrEtherTxQoSStatsQueueEntry 8 }

axrEthShaperStatsFlowOtherFrmTable OBJECT-TYPE
	SYNTAX  SEQUENCE OF AxrEthShaperStatsFlowOtherFrmEntry
	ACCESS  not-accessible
	STATUS  mandatory
	DESCRIPTION
		"A collection of Shaper other Frame statistics kept 
		for a particular Ethernet Shaper interface."
	::= { axrEthShaper 3 }

axrEthShaperStatsFlowOtherFrmEntry OBJECT-TYPE
	SYNTAX  AxrEthShaperStatsFlowOtherFrmEntry
	ACCESS  not-accessible
	STATUS  mandatory
	DESCRIPTION
		"An entry containing Shaper other Frame statistics 
		for a particular Ethernet Shaper interface."
    INDEX { axrEthShaperStatsFlowOtherFrmNifIndex,
            axrEthShaperStatsFlowOtherFrmLineIndex }
	::= { axrEthShaperStatsFlowOtherFrmTable 1 }

	AxrEthShaperStatsFlowOtherFrmEntry ::=
		SEQUENCE {
		  axrEthShaperStatsFlowOtherFrmNifIndex		INTEGER,
		  axrEthShaperStatsFlowOtherFrmLineIndex		INTEGER,
		  axrEthShaperStatsFlowOtherFrmOutFrames		Counter64,
		  axrEthShaperStatsFlowOtherFrmOutBytes		Counter64,
		  axrEthShaperStatsFlowOtherFrmDiscardFrames	Counter64,
		  axrEthShaperStatsFlowOtherFrmDiscardBytes	Counter64
		}

axrEthShaperStatsFlowOtherFrmNifIndex OBJECT-TYPE
	SYNTAX  INTEGER
	ACCESS  not-accessible
	STATUS  mandatory
	DESCRIPTION
		"Identified by a particular value of this index 
		is same value of NIF.Its value ranges between 
		1 and the value of ax7800rNifBoardNumber."
	::= { axrEthShaperStatsFlowOtherFrmEntry 1 }

axrEthShaperStatsFlowOtherFrmLineIndex OBJECT-TYPE
	SYNTAX  INTEGER
	ACCESS  not-accessible
	STATUS  mandatory
	DESCRIPTION
		"Identified by a particular value of this index 
		is same value of Physical Line.Its value ranges 
		between 1 and the value of ax7800rNifPhysLineNumber."
	::= { axrEthShaperStatsFlowOtherFrmEntry 2 }

axrEthShaperStatsFlowOtherFrmOutFrames OBJECT-TYPE
	SYNTAX  Counter64
	ACCESS  read-only
	STATUS  mandatory
	DESCRIPTION
		"The total number of packets transmitted outside of 
		a target for control out of the NIF."
	::= { axrEthShaperStatsFlowOtherFrmEntry 3 }

axrEthShaperStatsFlowOtherFrmOutBytes OBJECT-TYPE
	SYNTAX  Counter64
	ACCESS  read-only
	STATUS  mandatory
	DESCRIPTION
		"The total number of octets transmitted outside of 
		a target for control out of the NIF."
	::= { axrEthShaperStatsFlowOtherFrmEntry 4 }

axrEthShaperStatsFlowOtherFrmDiscardFrames OBJECT-TYPE
	SYNTAX  Counter64
	ACCESS  read-only
	STATUS  mandatory
	DESCRIPTION
		"The total number of outbound packets outside of 
		a target for control which were chosen to be discarded."
	::= { axrEthShaperStatsFlowOtherFrmEntry 5 }

axrEthShaperStatsFlowOtherFrmDiscardBytes OBJECT-TYPE
	SYNTAX  Counter64
	ACCESS  read-only
	STATUS  mandatory
	DESCRIPTION
		"The total number of outbound octets outside of 
		a target for control which were chosen to be discarded."
	::= { axrEthShaperStatsFlowOtherFrmEntry 6 }


axrEthShaperAgQueStatsTable OBJECT-TYPE
	SYNTAX  SEQUENCE OF AxrEthShaperAgQueStatsEntry
	ACCESS  not-accessible
	STATUS  mandatory
	DESCRIPTION
		"A collection of Shaper statistics kept for a 
		particular Ethernet Shaper aggregated queue."
	::= { axrEthShaperAgQue 1 }

axrEthShaperAgQueStatsEntry OBJECT-TYPE
	SYNTAX  AxrEthShaperAgQueStatsEntry
	ACCESS  not-accessible
	STATUS  mandatory
	DESCRIPTION
		"An entry containing Shaper statistics for a 
		particular Ethernet Shaper aggregated queue."
    INDEX { axrEthShaperAgQueStatsNifIndex,
            axrEthShaperAgQueStatsLineIndex,
            axrEthShaperAgQueStatsAgNumber}
	::= { axrEthShaperAgQueStatsTable 1 }

	AxrEthShaperAgQueStatsEntry ::=
		SEQUENCE {
		  axrEthShaperAgQueStatsNifIndex			INTEGER,
		  axrEthShaperAgQueStatsLineIndex		INTEGER,
		  axrEthShaperAgQueStatsAgNumber  		INTEGER,
		  axrEthShaperAgQueStatsTotalOutFrames		Counter64,
		  axrEthShaperAgQueStatsTotalOutBytes		Counter64,
		  axrEthShaperAgQueStatsTotalDiscardFrames	Counter64,
		  axrEthShaperAgQueStatsTotalDiscardBytes	Counter64
		}

axrEthShaperAgQueStatsNifIndex OBJECT-TYPE
	SYNTAX  INTEGER
	ACCESS  not-accessible
	STATUS  mandatory
	DESCRIPTION
		"Identified by a particular value of this index 
		is same value of NIF.Its value ranges between 
		1 and the value of ax7800rNifBoardNumber."
	::= { axrEthShaperAgQueStatsEntry 1 }

axrEthShaperAgQueStatsLineIndex OBJECT-TYPE
	SYNTAX  INTEGER
	ACCESS  not-accessible
	STATUS  mandatory
	DESCRIPTION
		"Identified by a particular value of this index 
		is same value of Physical Line.Its value ranges 
		between 1 and the value of ax7800rNifPhysLineNumber."
	::= { axrEthShaperAgQueStatsEntry 2 }

axrEthShaperAgQueStatsAgNumber OBJECT-TYPE
	SYNTAX  INTEGER
	ACCESS  not-accessible
	STATUS  mandatory
	DESCRIPTION
		"The number of aggregated queue. Its value ranges
		 between 1 and 1023." 
	::= { axrEthShaperAgQueStatsEntry 3 }

axrEthShaperAgQueStatsTotalOutFrames OBJECT-TYPE
	SYNTAX  Counter64
	ACCESS  read-only
	STATUS  mandatory
	DESCRIPTION
		"The total number of packets transmitted out of 
		the aggregated queue."
	::= { axrEthShaperAgQueStatsEntry 4 }

axrEthShaperAgQueStatsTotalOutBytes OBJECT-TYPE
	SYNTAX  Counter64
	ACCESS  read-only
	STATUS  mandatory
	DESCRIPTION
		"The total number of octets transmitted out of 
		the aggregated queue."
	::= { axrEthShaperAgQueStatsEntry 5 }

axrEthShaperAgQueStatsTotalDiscardFrames OBJECT-TYPE
	SYNTAX  Counter64
	ACCESS  read-only
	STATUS  mandatory
	DESCRIPTION
		"The total number of outbound packets which 
		were chosen to be discarded."
	::= { axrEthShaperAgQueStatsEntry 6 }

axrEthShaperAgQueStatsTotalDiscardBytes OBJECT-TYPE
	SYNTAX  Counter64
	ACCESS  read-only
	STATUS  mandatory
	DESCRIPTION
		"The total number of outbound octets which 
		were chosen to be discarded."
	::= { axrEthShaperAgQueStatsEntry 7 }

axrEthShaperAgQueStatsQueueTable OBJECT-TYPE
	SYNTAX  SEQUENCE OF AxrEthShaperAgQueStatsQueueEntry
	ACCESS  not-accessible
	STATUS  mandatory
	DESCRIPTION
		"A collection of priority queue statistics."
	::= { axrEthShaperAgQue 2 }

axrEthShaperAgQueStatsQueueEntry OBJECT-TYPE
	SYNTAX  AxrEthShaperAgQueStatsQueueEntry
	ACCESS  not-accessible
	STATUS  mandatory
	DESCRIPTION
		"A entry of priority queue statistics."
    INDEX { axrEthShaperAgQueStatsQueueNifIndex,
	    axrEthShaperAgQueStatsQueueLineIndex,
	    axrEthShaperAgQueStatsQueueAgNumber,
	    axrEthShaperAgQueStatsQueueQueIndex}
	::= { axrEthShaperAgQueStatsQueueTable 1 }

	AxrEthShaperAgQueStatsQueueEntry ::=
		SEQUENCE {
		  axrEthShaperAgQueStatsQueueNifIndex		INTEGER,
		  axrEthShaperAgQueStatsQueueLineIndex		INTEGER,
		  axrEthShaperAgQueStatsQueueAgNumber		INTEGER,
		  axrEthShaperAgQueStatsQueueQueIndex		INTEGER,
		  axrEthShaperAgQueStatsQueueOutFrames	        Counter64,
		  axrEthShaperAgQueStatsQueueOutBytes		Counter64,
		  axrEthShaperAgQueStatsQueueDiscardFrames	Counter64,
		  axrEthShaperAgQueStatsQueueDiscardBytes	Counter64
		}

axrEthShaperAgQueStatsQueueNifIndex OBJECT-TYPE
	SYNTAX  INTEGER
	ACCESS  not-accessible
	STATUS  mandatory
	DESCRIPTION
		"Identified by a particular value of this index 
		is same value of NIF.Its value ranges between 
		1 and the value of ax7800rNifBoardNumber."
	::= { axrEthShaperAgQueStatsQueueEntry 1 }
	
axrEthShaperAgQueStatsQueueLineIndex OBJECT-TYPE
	SYNTAX  INTEGER
	ACCESS  not-accessible
	STATUS  mandatory
	DESCRIPTION
		"Identified by a particular value of this index 
		is same value of Physical Line.Its value ranges 
		between 1 and the value of ax7800rNifPhysLineNumber."
	::= { axrEthShaperAgQueStatsQueueEntry 2 }

axrEthShaperAgQueStatsQueueAgNumber OBJECT-TYPE
	SYNTAX  INTEGER
	ACCESS  not-accessible
	STATUS  mandatory
	DESCRIPTION
		"The number of aggregated queue. Its value ranges
		 between 1 and 1023." 
	::= { axrEthShaperAgQueStatsQueueEntry 3 }

axrEthShaperAgQueStatsQueueQueIndex OBJECT-TYPE
	SYNTAX  INTEGER
	ACCESS  not-accessible
	STATUS  mandatory
	DESCRIPTION
		"An index that uniquely identifies the particular queue.
		Its value ranges between 1 and 4."
	::= { axrEthShaperAgQueStatsQueueEntry 4 }

axrEthShaperAgQueStatsQueueOutFrames OBJECT-TYPE
	SYNTAX  Counter64
	ACCESS  read-only
	STATUS  mandatory
	DESCRIPTION
		"The number of packets transmitted out of the priority 
		queue interface."
	::= { axrEthShaperAgQueStatsQueueEntry 5 }

axrEthShaperAgQueStatsQueueOutBytes OBJECT-TYPE
	SYNTAX  Counter64
	ACCESS  read-only
	STATUS  mandatory
	DESCRIPTION
		"The number of octets transmitted out of the priority 
		queue interface."
	::= { axrEthShaperAgQueStatsQueueEntry 6 }

axrEthShaperAgQueStatsQueueDiscardFrames OBJECT-TYPE
	SYNTAX  Counter64
	ACCESS  read-only
	STATUS  mandatory
	DESCRIPTION
		"The number of packets which were chosen to be discarded."
	::= { axrEthShaperAgQueStatsQueueEntry 7 }

axrEthShaperAgQueStatsQueueDiscardBytes OBJECT-TYPE
	SYNTAX  Counter64
	ACCESS  read-only
	STATUS  mandatory
	DESCRIPTION
		"The number of octets which were chosen to be discarded."
	::= { axrEthShaperAgQueStatsQueueEntry 8 }

axrEthShaperDefAgQueStatsTable OBJECT-TYPE
	SYNTAX  SEQUENCE OF AxrEthShaperDefAgQueStatsEntry
	ACCESS  not-accessible
	STATUS  mandatory
	DESCRIPTION
		"Information of Shaper statistics."
	::= { axrEthShaperAgQue 3 }

axrEthShaperDefAgQueStatsEntry OBJECT-TYPE
	SYNTAX  AxrEthShaperDefAgQueStatsEntry
	ACCESS  not-accessible
	STATUS  mandatory
	DESCRIPTION
		"Entry of shaper statistics information of Ether shaper defau
		lt aggregate queue."
	INDEX {
		axrEthShaperDefAgQueStatsNifIndex,
		axrEthShaperDefAgQueStatsLineIndex
	}
	::= { axrEthShaperDefAgQueStatsTable 1 }
	AxrEthShaperDefAgQueStatsEntry ::= 
	    SEQUENCE {
		axrEthShaperDefAgQueStatsNifIndex
			INTEGER,
		axrEthShaperDefAgQueStatsLineIndex
        	INTEGER,
		axrEthShaperDefAgQueStatsTotalOutFrames
        	Counter64,
		axrEthShaperDefAgQueStatsTotalOutBytes
        	Counter64,
		axrEthShaperDefAgQueStatsTotalDiscardFrames
        	Counter64,
		axrEthShaperDefAgQueStatsTotalDiscardBytes
        	Counter64
        }

axrEthShaperDefAgQueStatsNifIndex OBJECT-TYPE
	SYNTAX  INTEGER
	ACCESS  not-accessible
	STATUS  mandatory
	DESCRIPTION
		"Indicates place information of the slot with this NIF."
	::= { axrEthShaperDefAgQueStatsEntry 1 }

axrEthShaperDefAgQueStatsLineIndex OBJECT-TYPE
	SYNTAX  INTEGER
	ACCESS  not-accessible
	STATUS  mandatory
	DESCRIPTION
		"Information of physical line number."
	::= { axrEthShaperDefAgQueStatsEntry 2 }

axrEthShaperDefAgQueStatsTotalOutFrames OBJECT-TYPE
	SYNTAX  Counter64
	ACCESS  read-only
	STATUS  mandatory
	DESCRIPTION
		"The number of sent frame of default aggregate queue."
	::= { axrEthShaperDefAgQueStatsEntry 3 }

axrEthShaperDefAgQueStatsTotalOutBytes OBJECT-TYPE
	SYNTAX  Counter64
	ACCESS  read-only
	STATUS  mandatory
	DESCRIPTION
		"The number of sent bytes of default aggregate queue."
	::= { axrEthShaperDefAgQueStatsEntry 4 }

axrEthShaperDefAgQueStatsTotalDiscardFrames OBJECT-TYPE
	SYNTAX  Counter64
	ACCESS  read-only
	STATUS  mandatory
	DESCRIPTION
		"The number of discarded frame of default aggregate queue."
	::= { axrEthShaperDefAgQueStatsEntry 5 }

axrEthShaperDefAgQueStatsTotalDiscardBytes OBJECT-TYPE
	SYNTAX  Counter64
	ACCESS  read-only
	STATUS  mandatory
	DESCRIPTION
		"The number of discarded bytes of default aggregate queue."
	::= { axrEthShaperDefAgQueStatsEntry 6 }

axrEthShaperDefAgQueStatsQueueTable OBJECT-TYPE
	SYNTAX  SEQUENCE OF AxrEthShaperDefAgQueStatsQueueEntry
	ACCESS  not-accessible
	STATUS  mandatory
	DESCRIPTION
		"Information of shaper statistics per output priority queue o
		f default aggregate queue."
	::= { axrEthShaperAgQue 4 }

axrEthShaperDefAgQueStatsQueueEntry OBJECT-TYPE
	SYNTAX  AxrEthShaperDefAgQueStatsQueueEntry
	ACCESS  not-accessible
	STATUS  mandatory
	DESCRIPTION
		"Entry of shaper statistics information per output priority q
		ueue of default aggregate queue."
	INDEX {
		axrEthShaperDefAgQueStatsQueueNifIndex,
		axrEthShaperDefAgQueStatsQueueLineIndex,
		axrEthShaperDefAgQueStatsQueueQueIndex
	}
	::= { axrEthShaperDefAgQueStatsQueueTable 1 }
	AxrEthShaperDefAgQueStatsQueueEntry ::= 
	    SEQUENCE {
		axrEthShaperDefAgQueStatsQueueNifIndex
			INTEGER,
		axrEthShaperDefAgQueStatsQueueLineIndex
        	INTEGER,
		axrEthShaperDefAgQueStatsQueueQueIndex
        	INTEGER,
		axrEthShaperDefAgQueStatsQueueOutFrames
        	Counter64,
		axrEthShaperDefAgQueStatsQueueOutBytes
        	Counter64,
		axrEthShaperDefAgQueStatsQueueDiscardFrames
        	Counter64,
		axrEthShaperDefAgQueStatsQueueDiscardBytes
        	Counter64
        }

axrEthShaperDefAgQueStatsQueueNifIndex OBJECT-TYPE
	SYNTAX  INTEGER
	ACCESS  not-accessible
	STATUS  mandatory
	DESCRIPTION
		"Indicates place information of the slot with this NIF."
	::= { axrEthShaperDefAgQueStatsQueueEntry 1 }

axrEthShaperDefAgQueStatsQueueLineIndex OBJECT-TYPE
	SYNTAX  INTEGER
	ACCESS  not-accessible
	STATUS  mandatory
	DESCRIPTION
		"Information of physical line number."
	::= { axrEthShaperDefAgQueStatsQueueEntry 2 }

axrEthShaperDefAgQueStatsQueueQueIndex OBJECT-TYPE
	SYNTAX  INTEGER
	ACCESS  not-accessible
	STATUS  mandatory
	DESCRIPTION
		"Indicates the value of index which identifies this table ent
		ry."
	::= { axrEthShaperDefAgQueStatsQueueEntry 3 }

axrEthShaperDefAgQueStatsQueueOutFrames OBJECT-TYPE
	SYNTAX  Counter64
	ACCESS  read-only
	STATUS  mandatory
	DESCRIPTION
		"The number of sent frame of output priority queue of default
		 aggregate queue."
	::= { axrEthShaperDefAgQueStatsQueueEntry 4 }

axrEthShaperDefAgQueStatsQueueOutBytes OBJECT-TYPE
	SYNTAX  Counter64
	ACCESS  read-only
	STATUS  mandatory
	DESCRIPTION
		"The number of sent bytes of output priority queue of default
		 aggregate queue."
	::= { axrEthShaperDefAgQueStatsQueueEntry 5 }

axrEthShaperDefAgQueStatsQueueDiscardFrames OBJECT-TYPE
	SYNTAX  Counter64
	ACCESS  read-only
	STATUS  mandatory
	DESCRIPTION
		"The number of discarded frame of output priority queue of de
		fault aggregate queue."
	::= { axrEthShaperDefAgQueStatsQueueEntry 6 }

axrEthShaperDefAgQueStatsQueueDiscardBytes OBJECT-TYPE
	SYNTAX  Counter64
	ACCESS  read-only
	STATUS  mandatory
	DESCRIPTION
		"The number of discarded bytes of output priority queue of de
		fault aggregate queue."
	::= { axrEthShaperDefAgQueStatsQueueEntry 7 }

--axrDHCP group Variables

axrDHCPAddrValue OBJECT-TYPE
	SYNTAX INTEGER
	ACCESS read-only
	STATUS mandatory
	DESCRIPTION
		"The number of IP addresses which are available
		within this Router."
	::= { axrDHCP 1 }

axrDHCPFreeAddrValue OBJECT-TYPE
	SYNTAX INTEGER
	ACCESS read-only
	STATUS mandatory
	DESCRIPTION
		"The number of IP addresses which are available
		within this Router. May be expressed as either
		an absolute value."
	::= { axrDHCP 2 }

--axrIpStats group Variables

axrIpNullInDiscards OBJECT-TYPE
	SYNTAX Counter64
	ACCESS read-only
	STATUS mandatory
	DESCRIPTION
		"The number of ipv4 packets discarded through null-interface."
	::= { axrIpStats 1 }

axrIpv6NullInDiscards OBJECT-TYPE
	SYNTAX Counter64
	ACCESS read-only
	STATUS mandatory
	DESCRIPTION
		"The number of ipv6 packets discarded through null-interface."
	::= { axrIpStats 2 }

axrIpPimRegisterDiscards OBJECT-TYPE
	SYNTAX Counter64
	ACCESS read-only
	STATUS mandatory
	DESCRIPTION
		"The number of ipv4 packets discarded by register checksum error of PIM."
	::= { axrIpStats 3 }

--  MPLS VPN General Variables


axrVpnIpAddrTable OBJECT-TYPE
	SYNTAX  SEQUENCE OF AxrVpnIpAddrEntry
	ACCESS  not-accessible
	STATUS  mandatory
	DESCRIPTION
		"The table of addressing information relevant to
		this entity's IP addresses."
	::= { axrVpnIp 1 }

axrVpnIpAddrEntry OBJECT-TYPE
	SYNTAX  AxrVpnIpAddrEntry
	ACCESS  not-accessible
	STATUS  mandatory
	DESCRIPTION
		"The addressing information for one of this
		entity's IP addresses."
	INDEX { axrVpnIpAddrVpnIndex, axrVpnIpAdEntAddr }
	::= { axrVpnIpAddrTable 1 }

	AxrVpnIpAddrEntry ::=
		SEQUENCE {
		  axrVpnIpAddrVpnIndex     INTEGER,
		  axrVpnIpAdEntAddr        IpAddress,
		  axrVpnIpAdEntIfIndex     INTEGER,
		  axrVpnIpAdEntNetMask     IpAddress,
		  axrVpnIpAdEntBcastAddr   INTEGER,
		  axrVpnIpAdEntReasmMaxSize INTEGER,
		  axrVpnIpAdEntDescr       DisplayString
		}

axrVpnIpAddrVpnIndex OBJECT-TYPE
	SYNTAX  INTEGER
	ACCESS  not-accessible
	STATUS  mandatory
	DESCRIPTION
		"The index value which identifies VPN number."
	::= { axrVpnIpAddrEntry 1 }

axrVpnIpAdEntAddr OBJECT-TYPE
	SYNTAX  IpAddress
	ACCESS  read-only
	STATUS  mandatory
	DESCRIPTION
		"The IP address to which this entry's addressing
		information pertains."
	::= { axrVpnIpAddrEntry 2 }

axrVpnIpAdEntIfIndex OBJECT-TYPE
	SYNTAX  INTEGER
	ACCESS  read-only
	STATUS  mandatory
	DESCRIPTION
		"The index value which uniquely identifies the
		interface to which this entry is applicable. "
	::= { axrVpnIpAddrEntry 3 }

axrVpnIpAdEntNetMask OBJECT-TYPE
	SYNTAX  IpAddress
	ACCESS  read-only
	STATUS  mandatory
	DESCRIPTION
		"The subnet mask associated with the IP address of
		this entry. "
	::= { axrVpnIpAddrEntry 4 }

axrVpnIpAdEntBcastAddr OBJECT-TYPE
	SYNTAX  INTEGER
	ACCESS  read-only
	STATUS  mandatory
	DESCRIPTION
		"The value of the least-significant bit in the IP
		broadcast address used for sending dataaxrams on
		the (logical) interface associated with the IP
		address of this entry."
	::= { axrVpnIpAddrEntry 5 }

axrVpnIpAdEntReasmMaxSize OBJECT-TYPE
	SYNTAX  INTEGER
	ACCESS  read-only
	STATUS  mandatory
	DESCRIPTION
		"The size of the largest IP dataaxram which this
		entity can re-assemble from incoming IP fragmented
		dataaxrams received on this interface."
	::= { axrVpnIpAddrEntry 6 }

axrVpnIpAdEntDescr OBJECT-TYPE
	SYNTAX  DisplayString
	ACCESS  read-only
	STATUS  mandatory
	DESCRIPTION
		"The Description of VPN. The VPN identification which user setting."
	::= { axrVpnIpAddrEntry 7 }


axrVpnIpNetToMediaTable OBJECT-TYPE
	SYNTAX  SEQUENCE OF AxrVpnIpNetToMediaEntry
	ACCESS  not-accessible
	STATUS  mandatory
	DESCRIPTION
		"The IP Address Translation table used for mapping
		from IP addresses to physical addresses."
	::= { axrVpnIp 2 }

axrVpnIpNetToMediaEntry OBJECT-TYPE
	SYNTAX  AxrVpnIpNetToMediaEntry
	ACCESS  not-accessible
	STATUS  mandatory
	DESCRIPTION
		"Each entry contains one IpAddress to physical
		address equivalence."
	INDEX { axrVpnIpNetMediaVpnIndex, axrVpnIpNetToMediaIfIndex, axrVpnIpNetToMediaNetAddress }
	::= { axrVpnIpNetToMediaTable 1 }

	AxrVpnIpNetToMediaEntry ::=
		SEQUENCE {
		  axrVpnIpNetMediaVpnIndex      INTEGER,
		  axrVpnIpNetToMediaIfIndex     INTEGER,
		  axrVpnIpNetToMediaPhysAddress PhysAddress,
		  axrVpnIpNetToMediaNetAddress  IpAddress,
		  axrVpnIpNetToMediaType        INTEGER,
		  axrVpnIpNetToMediaDescr       DisplayString
		}

axrVpnIpNetMediaVpnIndex OBJECT-TYPE
	SYNTAX  INTEGER
	ACCESS  read-only
	STATUS  mandatory
	DESCRIPTION
		"The index value which identifies VPN number."
	::= { axrVpnIpNetToMediaEntry 1 }

axrVpnIpNetToMediaIfIndex OBJECT-TYPE
	SYNTAX  INTEGER
	ACCESS  read-only
	STATUS  mandatory
	DESCRIPTION
		"The interface on which this entry's equivalence
		is effective. This index is same value of ifIndex."
	::= { axrVpnIpNetToMediaEntry 2 }

axrVpnIpNetToMediaPhysAddress OBJECT-TYPE
	SYNTAX  PhysAddress
	ACCESS  read-only
	STATUS  mandatory
	DESCRIPTION
		"The media-dependent `physical' address."
	::= { axrVpnIpNetToMediaEntry 3 }

axrVpnIpNetToMediaNetAddress OBJECT-TYPE
	SYNTAX  IpAddress
	ACCESS  read-only
	STATUS  mandatory
	DESCRIPTION
		"The IpAddress corresponding to the media-
		dependent `physical' address."
	::= { axrVpnIpNetToMediaEntry 4 }

axrVpnIpNetToMediaType OBJECT-TYPE
	SYNTAX  INTEGER {
		other(1),        -- none of the following ex. Inverse ARP
		invalid(2),      -- an invalidated mapping
		dynamic(3),
		static(4)
		}
	ACCESS  read-only
	STATUS  mandatory
	DESCRIPTION
		"The type of mapping."
	::= { axrVpnIpNetToMediaEntry 5 }

axrVpnIpNetToMediaDescr OBJECT-TYPE
	SYNTAX  DisplayString
	ACCESS  read-only
	STATUS  mandatory
	DESCRIPTION
		"The Description of VPN. The VPN identification which user setting."
	::= { axrVpnIpNetToMediaEntry 6 }

axrVpnIpFwNoTable OBJECT-TYPE
	SYNTAX  SEQUENCE OF AxrVpnIpFwNoEntry
	ACCESS  not-accessible
	STATUS  mandatory
	DESCRIPTION
		"This entity's number of IP Routing table about VPN."
	::= { axrVpnIpForward 1 }

axrVpnIpFwNoEntry OBJECT-TYPE
	SYNTAX  AxrVpnIpFwNoEntry
	ACCESS  not-accessible
	STATUS  mandatory
	DESCRIPTION
		"This entity's IP Routing table about VPN."
	INDEX { axrVpnIpFwNoVpnIndex }
	::= { axrVpnIpFwNoTable 1 }

	AxrVpnIpFwNoEntry ::=
		SEQUENCE {
		  axrVpnIpFwNoVpnIndex INTEGER,
		  axrVpnIpFwNo         INTEGER,
		  axrVpnIpFwNoDescr    DisplayString
		}

axrVpnIpFwNoVpnIndex OBJECT-TYPE
	SYNTAX  INTEGER
	ACCESS  read-only
	STATUS  mandatory
	DESCRIPTION
		"The index value which identifies VPN number."
	::= { axrVpnIpFwNoEntry 1 }

axrVpnIpFwNo OBJECT-TYPE
	SYNTAX  INTEGER
	ACCESS  read-only
	STATUS  mandatory
	DESCRIPTION
		"The number of entry that is IP Routing table ."
	::= { axrVpnIpFwNoEntry 2 }

axrVpnIpFwNoDescr OBJECT-TYPE
	SYNTAX  DisplayString
	ACCESS  read-only
	STATUS  mandatory
	DESCRIPTION
		"The Description of VPN. The VPN identification which user setting."
	::= { axrVpnIpFwNoEntry 3 }

axrVpnIpFwTable OBJECT-TYPE
	SYNTAX  SEQUENCE OF AxrVpnIpFwEntry
	ACCESS  not-accessible
	STATUS  mandatory
	DESCRIPTION
		"his entity's IP Routing table."
	::= { axrVpnIpForward 2 }

axrVpnIpFwEntry OBJECT-TYPE
	SYNTAX  AxrVpnIpFwEntry
	ACCESS  not-accessible
	STATUS  mandatory
	DESCRIPTION
		"A particular route to  a  particular  destination ,
		under a particular policy"
	INDEX { axrVpnIpFwVpnIndex,axrVpnIpFwDest, 
		axrVpnIpFwProto, axrVpnIpFwPolicy, axrVpnIpFwNextHop }
	::= { axrVpnIpFwTable 1 }

	AxrVpnIpFwEntry ::=
		SEQUENCE {
		  axrVpnIpFwVpnIndex  INTEGER,
		  axrVpnIpFwDest      IpAddress,
		  axrVpnIpFwMask      IpAddress,
		  axrVpnIpFwPolicy    INTEGER,
		  axrVpnIpFwNextHop   IpAddress,
		  axrVpnIpFwIfIndex   INTEGER,
		  axrVpnIpFwType      INTEGER,
		  axrVpnIpFwProto     INTEGER,
		  axrVpnIpFwAge       INTEGER,
		  axrVpnIpFwInfo      OBJECT IDENTIFIER,
		  axrVpnIpFwNextHopAS INTEGER,
		  axrVpnIpFwMetric1   INTEGER,
		  axrVpnIpFwMetric2   INTEGER,
		  axrVpnIpFwMetric3   INTEGER,
		  axrVpnIpFwMetric4   INTEGER,
		  axrVpnIpFwMetric5   INTEGER,
		  axrVpnIpFwDescr     DisplayString
		}

axrVpnIpFwVpnIndex OBJECT-TYPE
	SYNTAX  INTEGER
	ACCESS  read-only
	STATUS  mandatory
	DESCRIPTION
		"The index value which identifies VPN number."
	::= { axrVpnIpFwEntry 1 }

axrVpnIpFwDest OBJECT-TYPE
	SYNTAX  IpAddress
	ACCESS  read-only
	STATUS  mandatory
	DESCRIPTION
		"The destination IP address of this route."
	::= { axrVpnIpFwEntry 2 }

axrVpnIpFwMask OBJECT-TYPE
	SYNTAX  IpAddress
	ACCESS  read-only
	STATUS  mandatory
	DESCRIPTION
		"Indicate the mask to be logical-ANDed with the
		destination  address  before  being compared to
		the value  in  the  ipForwardDest  field. "
	::= { axrVpnIpFwEntry 3 }

axrVpnIpFwPolicy OBJECT-TYPE
	SYNTAX  INTEGER
	ACCESS  read-only
	STATUS  mandatory
	DESCRIPTION
		"The general set of conditions that would cause
		the  selection  of  one multipath route (set of
		next hops for a given destination) is  referred
		to as 'policy'."
	::= { axrVpnIpFwEntry 4 }

axrVpnIpFwNextHop OBJECT-TYPE
	SYNTAX  IpAddress
	ACCESS  read-only
	STATUS  mandatory
	DESCRIPTION
		"On remote routes, the address of the next system en route"
	::= { axrVpnIpFwEntry 5 }

axrVpnIpFwIfIndex OBJECT-TYPE
	SYNTAX  INTEGER
	ACCESS  read-only
	STATUS  mandatory
	DESCRIPTION
		"The ifIndex value which identifies  the  local
		interface  through  which  the next hop of this
		route should be reached."
	::= { axrVpnIpFwEntry 6 }

axrVpnIpFwType OBJECT-TYPE
	SYNTAX  INTEGER{
			other    (1), -- not specified by this MIB
			invalid  (2), -- logically deleted
			local    (3), -- local interface
			remote   (4)  -- remote destination
		}
	ACCESS  read-only
	STATUS  mandatory
	DESCRIPTION
		"The type of route."
	::= { axrVpnIpFwEntry 7 }

axrVpnIpFwProto OBJECT-TYPE
	SYNTAX  INTEGER {
			other     (1),  -- not specified
			local     (2),  -- local interface
			netmgmt   (3),  -- static route
			icmp      (4),  -- result of ICMP Redirect
					-- the following are all dynamic
					-- routing protocols
			egp       (5),  -- Exterior Gateway Protocol
			ggp       (6),  -- Gateway-Gateway Protocol
			hello     (7),  -- FuzzBall HelloSpeak
			rip       (8),  -- Berkeley RIP or RIP-II
			is-is     (9),  -- Dual IS-IS
			es-is     (10), -- ISO 9542
			ciscoIaxrp (11), -- Cisco IGRP
			bbnSpfIgp (12), -- BBN SPF IGP
			ospf      (13), -- Open Shortest Path First
			bgp       (14), -- Border Gateway Protocol
			idpr      (15)  -- InterDomain Policy Routing
		}
	ACCESS  read-only
	STATUS  mandatory
	DESCRIPTION
		"The routing mechanism via which this route was
		learned."
	::= { axrVpnIpFwEntry 8 }

axrVpnIpFwAge OBJECT-TYPE
	SYNTAX  INTEGER
	ACCESS  read-only
	STATUS  mandatory
	DESCRIPTION
		"The number of seconds  since  this  route  was
		last  updated  or  otherwise  determined  to be
		correct."
	::= { axrVpnIpFwEntry 9 }

axrVpnIpFwInfo OBJECT-TYPE
	SYNTAX  OBJECT IDENTIFIER
	ACCESS  read-only
	STATUS  mandatory
	DESCRIPTION
		"A reference to MIB definitions specific to the
		particular  routing protocol which is responsible
		for this route, as determined by the  value
		specified  in the route's ipForwardProto value.
		Its  value be set to the OBJECT IDENTIFIER { 0 0 }"
	::= { axrVpnIpFwEntry 10 }

axrVpnIpFwNextHopAS OBJECT-TYPE
	SYNTAX  INTEGER
	ACCESS  read-only
	STATUS  mandatory
	DESCRIPTION
		"The Autonomous System Number of the Next  Hop."
	::= { axrVpnIpFwEntry 11 }

axrVpnIpFwMetric1 OBJECT-TYPE
	SYNTAX  INTEGER
	ACCESS  read-only
	STATUS  mandatory
	DESCRIPTION
		"The primary routing  metric  for  this  route."
	::= { axrVpnIpFwEntry 12 }

axrVpnIpFwMetric2 OBJECT-TYPE
	SYNTAX  INTEGER
	ACCESS  read-only
	STATUS  mandatory
	DESCRIPTION
		"An alternate routing metric  for  this  route."
	::= { axrVpnIpFwEntry 13 }

axrVpnIpFwMetric3 OBJECT-TYPE
	SYNTAX  INTEGER
	ACCESS  read-only
	STATUS  mandatory
	DESCRIPTION
		"An alternate routing metric  for  this  route.
		Its value is set to -1."
	::= { axrVpnIpFwEntry 14 }

axrVpnIpFwMetric4 OBJECT-TYPE
	SYNTAX  INTEGER
	ACCESS  read-only
	STATUS  mandatory
	DESCRIPTION
		"An alternate routing metric  for  this  route.
		Its value is set to -1."
	::= { axrVpnIpFwEntry 15 }

axrVpnIpFwMetric5 OBJECT-TYPE
	SYNTAX  INTEGER
	ACCESS  read-only
	STATUS  mandatory
	DESCRIPTION
		"An alternate routing metric  for  this  route.
		Its value is set to -1."
	::= { axrVpnIpFwEntry 16 }

axrVpnIpFwDescr OBJECT-TYPE
	SYNTAX  DisplayString
	ACCESS  read-only
	STATUS  mandatory
	DESCRIPTION
		"The Description of VPN. The VPN identification which user setting."
	::= { axrVpnIpFwEntry 17 }

--  GRMPLS General Variables

axrMplsLdpLsrId OBJECT-TYPE
	SYNTAX  AxrMplsLsrIdentifier
	ACCESS  read-only
	STATUS  mandatory
	DESCRIPTION
		"The LSR's Identifier."
	::= { axrMplsLdpLsrObjects 1 }

axrMplsLdpLsrLoopDetectionCapable OBJECT-TYPE
	SYNTAX  INTEGER {
		none(1),
		other(2),
		hopCount(3),
		pathVector(4),
		hopCountAndPathVector(5)
		}
	ACCESS  read-only
	STATUS  mandatory
	DESCRIPTION
		"A indication of whether this LSR supports
		loop detection.
		none(1) -- Loop Detection is not supported
		on this LSR.
		other(2) -- Loop Detection is supported but
		by a method other than those
		listed below.
		hopCount(3) -- Loop Detection is supported by
		Hop Count only.
		pathVector(4) -- Loop Detection is supported by
		Path Vector only.
		hopCountAndPathVector(5) -- Loop Detection is
		supported by both Hop Count
		And Path Vector.
		Since Loop Detection is determined during
		Session Initialization, an individual session
		may not be running with loop detection.  This
		object simply gives an indication of whether or not the
		LSR has the ability to support Loop Detection and
		which types."
	::= { axrMplsLdpLsrObjects 2 }

--
-- The MPLS Label Distribution Protocol Entity Objects
--

axrMplsLdpEntityIndexNext  OBJECT-TYPE
	SYNTAX  Unsigned32 (0..4294967295)
	ACCESS  read-only
	STATUS  mandatory
	DESCRIPTION
		"This object contains an appropriate value to
		be used for axrMplsLdpEntityIndex when creating
		entries in the axrMplsLdpEntityTable. The value
		0 indicates that no unassigned entries are
		available. To obtain the axrMplsLdpEntityIndex
		value for a new entry, the manager issues a
		management protocol retrieval operation to obtain
		the current value of this object.  After each
		retrieval, the agent should modify the value to
		the next unassigned index."
	::= { axrMplsLdpEntityObjects 1 }

axrMplsLdpEntityTable OBJECT-TYPE
	SYNTAX  SEQUENCE OF AxrMplsLdpEntityEntry
	ACCESS  not-accessible
	STATUS  mandatory
	DESCRIPTION
		"This table contains information about the
		MPLS Label Distribution Protocol Entities which
		exist on this Label Switch Router (LSR)."
	::= { axrMplsLdpEntityObjects 2 }

axrMplsLdpEntityEntry OBJECT-TYPE
	SYNTAX  AxrMplsLdpEntityEntry
	ACCESS  not-accessible
	STATUS  mandatory
	DESCRIPTION
		"An entry in this table represents an LDP entity.
		An entry can be created by a network administrator
		or by an SNMP agent as instructed by LDP."
	INDEX  {  axrMplsLdpEntityLdpId, axrMplsLdpEntityIndex  }
	::= { axrMplsLdpEntityTable 1 }

	AxrMplsLdpEntityEntry ::= SEQUENCE {
		axrMplsLdpEntityLdpId                       AxrMplsLdpIdentifier,
		axrMplsLdpEntityIndex                       Unsigned32,
		axrMplsLdpEntityProtocolVersion             Integer32,
		axrMplsLdpEntityAdminStatus                 INTEGER,
		axrMplsLdpEntityOperStatus                  INTEGER,
		axrMplsLdpEntityWellKnownTcpDiscoveryPort   Unsigned32,
		axrMplsLdpEntityWellKnownUdpDiscoveryPort   Unsigned32,
		axrMplsLdpEntityMaxPduLength                Unsigned32,
		axrMplsLdpEntityKeepAliveHoldTimer          Integer32,
		axrMplsLdpEntityHelloHoldTimer              Integer32,
		axrMplsLdpEntityFailedInitSessionTrapEnable INTEGER,
		axrMplsLdpEntityFailedInitSessionThreshold  Integer32,
		axrMplsLdpEntityLabelDistributionMethod     INTEGER,
		axrMplsLdpEntityLabelRetentionMode          INTEGER,
		axrMplsLdpEntityPVLimitMismatchTrapEnable   INTEGER,
		axrMplsLdpEntityPathVectorLimit             Integer32,
		axrMplsLdpEntityHopCountLimit               Integer32,
		axrMplsLdpEntityTargetedPeer                TruthValue,
		axrMplsLdpEntityTargetedPeerAddrType        AddressFamilyNumbers,
		axrMplsLdpEntityTargetedPeerAddr            AxrMplsLdpGenAddr,
		axrMplsLdpEntityOptionalParameters          AxrMplsLdpLabelTypes,
		axrMplsLdpEntityDiscontinuityTime           TimeStamp,
		axrMplsLdpEntityStorageType                 StorageType,
		axrMplsLdpEntityRowStatus                   RowStatus
	}

axrMplsLdpEntityLdpId OBJECT-TYPE
	SYNTAX  AxrMplsLdpIdentifier
	ACCESS  not-accessible
	STATUS  mandatory
	DESCRIPTION
		"The LDP identifier.
		The first four octets encode an IP address
		assigned to the LSR, and the last two octets
		identify a specific label space within the
		LSR."
	REFERENCE
		"LDP Specification, Section on LDP Identifiers."
	::= { axrMplsLdpEntityEntry 1 }

axrMplsLdpEntityIndex OBJECT-TYPE
	SYNTAX  Unsigned32 (1..4294967295)
	ACCESS  not-accessible
	STATUS  mandatory
	DESCRIPTION
		"This index is used as a secondary index to uniquely
		identify this row.  Before creating a row in this table,
		the 'axrMplsLdpEntityIndexNext' object should be retrieved.
		That value should be used for the value of this index
		when creating a row in this table.  (NOTE:  if a value
		of zero (0) is retrieved, that indicates that no rows
		can be created in this table at this time.
		A secondary index (this object) is needed by some
		but not all, LDP implementations.  For example
		in an LDP implementation which uses PPP, this
		index may be needed."
	::= { axrMplsLdpEntityEntry 2 }

axrMplsLdpEntityProtocolVersion OBJECT-TYPE
	SYNTAX  Integer32
	ACCESS  read-create
	STATUS  mandatory
	DESCRIPTION
		"The version number of the protocol.  The value of 0 on a
		read indicates that the version of the protocol is unknown.
		Otherwise, the value of this object represents the version
		of the LDP protocol."
	DEFVAL { 1 }
	::= { axrMplsLdpEntityEntry 3 }

axrMplsLdpEntityAdminStatus OBJECT-TYPE
	SYNTAX  INTEGER {
		enable(1),
		disable(2)
	}
	ACCESS  read-create
	STATUS  mandatory
	DESCRIPTION
		"The administrative status of this LDP Entity.
		If this object is changed from 'enable' to 'disable'
		and this entity has already attempted to establish
		contact with a Peer (which implies that the
		'axrMplsLdpEntityRowStatus' object has been set to
		'active'), then all contact with that
		Peer is lost and all information from that Peer
		needs to be removed from the MIB.
		At this point the user is able to change values
		which are related to this entity.
		When the admin status is set back to 'up', then
		this Entity will attempt to establish new sessions
		with the Peer."
	DEFVAL  { enable }
	::= { axrMplsLdpEntityEntry 4 }

axrMplsLdpEntityOperStatus OBJECT-TYPE
	SYNTAX  INTEGER {
		unknown(0),
		enabled(1),
		disabled(2)
	}
	ACCESS  read-only
	STATUS  mandatory
	DESCRIPTION
		"The operational status of this LDP Entity."
		::= { axrMplsLdpEntityEntry 5 }

axrMplsLdpEntityWellKnownTcpDiscoveryPort OBJECT-TYPE
	SYNTAX  Unsigned32
	ACCESS  read-create
	STATUS  mandatory
	DESCRIPTION
		"The well known TCP Discovery Port for
		LDP."
	DEFVAL { 646 }
	::= { axrMplsLdpEntityEntry 6 }

axrMplsLdpEntityWellKnownUdpDiscoveryPort OBJECT-TYPE
	SYNTAX  Unsigned32
	ACCESS  read-create
	STATUS  mandatory
	DESCRIPTION
		"The well known UDP Discovery Port for
		LDP."
		DEFVAL { 646 }
		::= { axrMplsLdpEntityEntry 7 }

axrMplsLdpEntityMaxPduLength OBJECT-TYPE
	SYNTAX  Unsigned32 (0..65535)
	UNITS  "octets"
	ACCESS  read-create
	STATUS  mandatory
	DESCRIPTION
		"The maximum PDU Length that is sent in
		the Common Session Parameters of an Initialization
		Message. A value of 255 or less specifies the
		default maximum length of 4096 octets."
	REFERENCE
		"See Section on the 'Initialization Message' in the
		LDP Specification."
	DEFVAL { 4096 }
	::= { axrMplsLdpEntityEntry 8 }

axrMplsLdpEntityKeepAliveHoldTimer OBJECT-TYPE
	SYNTAX  Integer32 (1..65535)
	UNITS  "seconds"
	ACCESS  read-create
	STATUS  mandatory
	DESCRIPTION
		"The two octet value which is the proposed keep alive hold
		timer for this LDP Entity."
	DEFVAL { 40 }
	::= { axrMplsLdpEntityEntry 9 }

axrMplsLdpEntityHelloHoldTimer OBJECT-TYPE
	SYNTAX  Integer32 (0..65535)
	UNITS  "seconds"
	ACCESS  read-create
	STATUS  mandatory
	DESCRIPTION
		"The two octet value which is the proposed Hello hold
		timer for this LDP Entity. A value of 0 means use the
		default, which is 15 seconds for Link Hellos and 45
		seconds for Targeted Hellos.  A value of 65535 means
		infinite."
	DEFVAL { 0 }
	::= { axrMplsLdpEntityEntry 10 }

axrMplsLdpEntityFailedInitSessionTrapEnable OBJECT-TYPE
	SYNTAX  INTEGER {
		enabled(1),
		disabled(2)
	}
	ACCESS  read-create
	STATUS  mandatory
	DESCRIPTION
		"Indicates whether the
		'axrMplsLdpFailedInitSessionThresholdExceeded'
		trap should be generated.
		If the value of this object is 'enabled(1)'
		then the trap will generated.  If the value
		of this object is 'disabled(2)' then the
		trap will not be generated.  The DEFVAL
		is set to 'enabled(1)'."
	DEFVAL { enabled }
	::= { axrMplsLdpEntityEntry 11 }

axrMplsLdpEntityFailedInitSessionThreshold OBJECT-TYPE
	SYNTAX  Integer32
	ACCESS  read-create
	STATUS  mandatory
	DESCRIPTION
		"When attempting to establish a session with a
		given Peer, the given LDP Entity should
		send out the SNMP notification,
		'axrMplsLdpFailedInitSessionThresholdExceeded', when
		the number of Session Initialization messages sent
		exceeds this threshold.
		A value of 0 (zero) for this object
		indicates that the threshold is infinity, and
		the SNMP notification will never be sent
		when the value of this object is 0 (zero)."
	DEFVAL { 8 }
	::= { axrMplsLdpEntityEntry 12 }

axrMplsLdpEntityLabelDistributionMethod OBJECT-TYPE
	SYNTAX  INTEGER {
		downstreamOnDemand(1),
		downstreamUnsolicited(2)
	}
	ACCESS  read-create
	STATUS  mandatory
	DESCRIPTION
		"For any given LDP session, the method of
		label distribution must be specified."
	::= { axrMplsLdpEntityEntry 13 }

axrMplsLdpEntityLabelRetentionMode OBJECT-TYPE
	SYNTAX  INTEGER {
		conservative(1),
		liberal(2)
	}
	ACCESS  read-create
	STATUS  mandatory
	DESCRIPTION
		"The LDP Entity can be configured to use either
		conservative or liberal label retention mode.
		If the value of this object is conservative(1)
		then advertized label mappings are retained
		only if they will be used to forward packets,
		i.e. if label came from a valid next hop.
		If the value of this object is liberal(2)
		then all advertized label mappings are retained
		whether they are from a valid next hop or not."
	::= { axrMplsLdpEntityEntry 14 }

axrMplsLdpEntityPVLimitMismatchTrapEnable OBJECT-TYPE
	SYNTAX  INTEGER {
		enabled(1),
		disabled(2)
	}
	ACCESS  read-create
	STATUS  mandatory
	DESCRIPTION
		"Indicates whether the 'axrMplsLdpPathVectorLimitMismatch'
		trap should be generated.
		If the value of this object is 'enabled(1)'
		then the trap will generated.  If the value
		of this object is 'disabled(2)' then the
		trap will not be generated.  The DEFVAL
		is set to 'enabled(1)'."
	DEFVAL { enabled }
	::= { axrMplsLdpEntityEntry 15 }

axrMplsLdpEntityPathVectorLimit OBJECT-TYPE
	SYNTAX  Integer32 (0..255)
	ACCESS  read-create
	STATUS  mandatory
	DESCRIPTION
		"If the value of this object is 0 (zero) then
		Loop Dection for Path Vectors is disabled.
		Otherwise, if this object has a value axreater than
		zero, then Loop Dection for Path Vectors is enabled,
		and the Path Vector Limit is this value.
		Also, the value of the object,
		'axrMplsLdpLsrLoopDetectionCapable', must be set to
		either 'pathVector(4)' or 'hopCountAndPathVector(5)',
		if this object has a value axreater than 0 (zero)."
	::= { axrMplsLdpEntityEntry 16 }

axrMplsLdpEntityHopCountLimit OBJECT-TYPE
	SYNTAX  Integer32 (0..255)
	ACCESS  read-create
	STATUS  mandatory
	DESCRIPTION
		"If the value of this object is 0 (zero),
		then Loop Detection using Hop Counters is
		disabled.
		If the value of this object is axreater than
		0 (zero) then Loop Detection using Hop
		Counters is enabled, and this object
		specifies this Entity's maximum allowable
		value for the Hop Count.
		Also, the value of the object
		axrMplsLdpLsrLoopDetectionCapable must be set
		to either 'hopCount(3)' or
		'hopCountAndPathVector(5)' if this object
		has a value axreater than 0 (zero)."
	::= { axrMplsLdpEntityEntry 17 }

axrMplsLdpEntityTargetedPeer OBJECT-TYPE
	SYNTAX  TruthValue
	ACCESS  read-create
	STATUS  mandatory
	DESCRIPTION
		"If this LDP entity uses targeted peer then set
		this to true."
	DEFVAL { false }
	::= { axrMplsLdpEntityEntry 18 }

axrMplsLdpEntityTargetedPeerAddrType OBJECT-TYPE
	SYNTAX  AddressFamilyNumbers
	ACCESS  read-create
	STATUS  mandatory
	DESCRIPTION
		"The type of the internetwork layer address used for
		the Extended Discovery. This object indicates how
		the value of axrMplsLdpEntityTargetedPeerAddr is to
		be interpreted."
	::= { axrMplsLdpEntityEntry 19 }

axrMplsLdpEntityTargetedPeerAddr OBJECT-TYPE
	SYNTAX  AxrMplsLdpGenAddr
	ACCESS  read-create
	STATUS  mandatory
	DESCRIPTION
		"The value of the internetwork layer address used for
		the Extended Discovery."
	::= { axrMplsLdpEntityEntry 20 }

axrMplsLdpEntityOptionalParameters OBJECT-TYPE
	SYNTAX  AxrMplsLdpLabelTypes
	ACCESS  read-create
	STATUS  mandatory
	DESCRIPTION
		"Specifies the optional parameters for the LDP
		Initialization Message.  If the value is generic(1)
		then no optional parameters will be sent in
		the LDP Initialization message associated with
		this Entity.
		If the value is atmParameters(2) then
		a row must be created in the axrMplsLdpEntityAtmParms
		Table, which corresponds to this entry.
		If the value is frameRelayParameters(3) then
		a row must be created in the axrMplsLdpEntityFrameRelayParms
		Table, which corresponds to this entry."
	::= { axrMplsLdpEntityEntry 21 }

axrMplsLdpEntityDiscontinuityTime OBJECT-TYPE
	SYNTAX  TimeStamp
	ACCESS  read-only
	STATUS  mandatory
	DESCRIPTION
		"The value of sysUpTime on the most recent occasion
		at which any one or more of this entity's counters
		suffered a discontinuity.  The relevant counters are the
		specific instances associated with this entity of
		any Counter32, or Counter64 object contained
		in the 'axrMplsLdpEntityStatsTable'.  If no such
		discontinuities have occurred since the last
		re-initialization of the local management
		subsytem, then this object contains a zero
		value."
	::= { axrMplsLdpEntityEntry 22 }

axrMplsLdpEntityStorageType  OBJECT-TYPE
	SYNTAX  StorageType
	ACCESS  read-create
	STATUS  mandatory
	DESCRIPTION
		"The storage type for this entry."
	::= { axrMplsLdpEntityEntry 23 }

axrMplsLdpEntityRowStatus OBJECT-TYPE
	SYNTAX  RowStatus
	ACCESS  read-create
	STATUS  mandatory
	DESCRIPTION
		"An object that allows entries in this table to
		be created and deleted using the
		RowStatus convention.
		Once the 'axrMplsLdpEntityAdminStatus' object has
		the value of 'up' and this object has the value
		of 'active' then the Entity will atttempt to
		contact an LDP Peer.  If the value of this object
		is changed to 'notInService', then the Entity looses
		contact with the LDP Peer and all information related
		to that Peer must be removed from the MIB.	This has
		the same effect as changing 'axrMplsLdpEntityAdminStatus'
		from 'enable' to 'disable'.
		When this object is set to 'active' and the value of
		the 'axrMplsLdpEntityAdminStatus' is 'enable' then
		this Entity will attempt to contact the Peer and
		establish new sessions."
	::= { axrMplsLdpEntityEntry 24 }

--
-- Ldp Entity Objects for Generic Labels
--

axrMplsLdpEntityGenericObjects  OBJECT IDENTIFIER ::= {axrMplsLdpEntityObjects 3 }

--
-- The MPLS LDP Entity Configurable Generic Label Range Table
--

axrMplsLdpEntityConfGenericLabelRangeTable OBJECT-TYPE
	SYNTAX  SEQUENCE OF AxrMplsLdpEntityConfGenericLabelRangeEntry
	ACCESS  not-accessible
	STATUS  mandatory
	DESCRIPTION
		"The MPLS LDP Entity Configurable Generic Label Range Table.
		The purpose of this table is to provide a mechanism
		for specifying a contiguous range of generic labels,
		or a 'label range' for LDP Entities.
		LDP Entities which use Generic Labels must have at least one
		entry in this table."
	::= { axrMplsLdpEntityGenericObjects 1 }

axrMplsLdpEntityConfGenericLabelRangeEntry OBJECT-TYPE
	SYNTAX  AxrMplsLdpEntityConfGenericLabelRangeEntry
	ACCESS  not-accessible
	STATUS  mandatory
	DESCRIPTION
		"A row in the LDP Entity Configurable Generic Label
		Range Table.  One entry in this table contains
		information on a single range of labels
		represented by the configured Upper and Lower
		Bounds pairs.  NOTE: there is NO corresponding
		LDP message which relates to the information
		in this table, however, this table does provide
		a way for a user to 'reserve' a generic label
		range.
		NOTE:  The ranges for a specific LDP Entity
		are UNIQUE and non-overlapping.
		A row will not be created unless a unique and
		non-overlapping range is specified.  Thus, row
		creation implies a one-shot row creation of
		LDP EntityID and LowerBound and
		UpperBound."
	INDEX  {  axrMplsLdpEntityLdpId,
		axrMplsLdpEntityIndex,
		axrMplsLdpEntityConfGenericLabelRangeMinimum,
		axrMplsLdpEntityConfGenericLabelRangeMaximum
	}
	::= { axrMplsLdpEntityConfGenericLabelRangeTable 1 }

	AxrMplsLdpEntityConfGenericLabelRangeEntry ::= SEQUENCE {
		axrMplsLdpEntityConfGenericLabelRangeMinimum     Unsigned32,
		axrMplsLdpEntityConfGenericLabelRangeMaximum     Unsigned32,
		axrMplsLdpEntityConfGenericIfIndexOrZero         InterfaceIndexOrZero,
		axrMplsLdpEntityConfGenericLabelRangeStorageType StorageType,
		axrMplsLdpEntityConfGenericLabelRangeRowStatus   RowStatus
	}

axrMplsLdpEntityConfGenericLabelRangeMinimum OBJECT-TYPE
	SYNTAX  Unsigned32(0..1048575)
	ACCESS  not-accessible
	STATUS  mandatory
	DESCRIPTION
		"The minimum label configured for this range."
	::= { axrMplsLdpEntityConfGenericLabelRangeEntry 1 }

axrMplsLdpEntityConfGenericLabelRangeMaximum OBJECT-TYPE
	SYNTAX  Unsigned32(0..1048575)
	ACCESS  not-accessible
	STATUS  mandatory
	DESCRIPTION
		"The maximum label configured for this range."
	::= { axrMplsLdpEntityConfGenericLabelRangeEntry 2 }

axrMplsLdpEntityConfGenericIfIndexOrZero OBJECT-TYPE
	SYNTAX  InterfaceIndexOrZero
	ACCESS  read-create
	STATUS  mandatory
	DESCRIPTION
		"This value represents either the InterfaceIndex of
		the 'ifLayer' where these Generic Label would be created, or
		0 (zero).  The value of zero means that the InterfaceIndex
		is not known.  For example, if the InterfaceIndex is
		created subsequent to the Generic Label's creation, then
		it would not be known.  However, if the InterfaceIndex
		is known, then it must be represented by this value.
		If an InterfaceIndex becomes known, then the
		network management entity (e.g. SNMP agent) responsible
		for this object MUST change the value from 0 (zero) to the
		value of the InterfaceIndex.  If this Generic Label is
		being used in forwarding data, then the value of this
		object MUST be the InterfaceIndex."
	::= { axrMplsLdpEntityConfGenericLabelRangeEntry 3 }

axrMplsLdpEntityConfGenericLabelRangeStorageType  OBJECT-TYPE
	SYNTAX  StorageType
	ACCESS  read-create
	STATUS  mandatory
	DESCRIPTION
		"The storage type for this entry."
	::= { axrMplsLdpEntityConfGenericLabelRangeEntry 4 }

axrMplsLdpEntityConfGenericLabelRangeRowStatus OBJECT-TYPE
	SYNTAX RowStatus
	ACCESS read-create
	STATUS  mandatory
	DESCRIPTION
		"An object that allows entries in this
		table to be created and deleted using
		the RowStatus convention.
		There must exist at least one entry in this
		table for every LDP Entity that has a
		generic label configured.
		NOTE:  This RowStatus object should
		have the same value of the 'axrMplsLdpEntityRowStatus'
		related to this entry."
	::= { axrMplsLdpEntityConfGenericLabelRangeEntry 5 }

--
-- Ldp Entity Objects for ATM
--
--axrMplsLdpEntityAtmObjects  OBJECT IDENTIFIER ::=
--							{ axrMplsLdpEntityObjects 4 }
--axrMplsLdpEntityAtmParmsTable  OBJECT-TYPE
--	SYNTAX  SEQUENCE OF AxrMplsLdpEntityAtmParmsEntry
--	ACCESS  not-accessible
--	STATUS  mandatory
--	DESCRIPTION
--		"This table contains information about the
--		ATM specific information which could be used
--		in the 'Optional Parameters' and other ATM specific
--		information."
--	::= { axrMplsLdpEntityAtmObjects 1 }
--axrMplsLdpEntityAtmParmsEntry OBJECT-TYPE
--	SYNTAX  AxrMplsLdpEntityAtmParmsEntry
--	ACCESS  not-accessible
--	STATUS  mandatory
--	DESCRIPTION
--		"An entry in this table represents the ATM parameters
--		and ATM information for this LDP entity."
--	INDEX  {  axrMplsLdpEntityLdpId,
--					axrMplsLdpEntityIndex
--			}
--	::= { axrMplsLdpEntityAtmParmsTable 1 }
--	AxrMplsLdpEntityAtmParmsEntry ::= SEQUENCE {
--		axrMplsLdpEntityAtmIfIndexOrZero        InterfaceIndexOrZero,
--		axrMplsLdpEntityAtmMergeCap             INTEGER,
--		axrMplsLdpEntityAtmLabelRangeComponents Unsigned32,
--		axrMplsLdpEntityAtmVcDirectionality     INTEGER,
--		axrMplsLdpEntityAtmLsrConnectivity      INTEGER,
--		axrMplsLdpEntityDefaultControlVpi       AtmVpIdentifier,
--		axrMplsLdpEntityDefaultControlVci       MplsAtmVcIdentifier,
--		axrMplsLdpEntityUnlabTrafVpi            AtmVpIdentifier,
--		axrMplsLdpEntityUnlabTrafVci            MplsAtmVcIdentifier,
--		axrMplsLdpEntityAtmStorageType          StorageType,
--		axrMplsLdpEntityAtmRowStatus            RowStatus
--		}
--axrMplsLdpEntityAtmIfIndexOrZero  OBJECT-TYPE
--	SYNTAX  InterfaceIndexOrZero
--	ACCESS  read-create
--	STATUS  mandatory
--	DESCRIPTION
--		"This value represents either the InterfaceIndex of
--		the 'ifLayer' where the ATM Labels 'owned' by this
--		entry were created, or 0 (zero).  The value of zero
--		means that the InterfaceIndex is not known.  For example,
--		if the InterfaceIndex is created subsequent to the
--		ATM Label's creation, then it would not be known.
--		However, if the InterfaceIndex is known, then it must
--		be represented by this value.
--		If an InterfaceIndex becomes known, then the
--		network management entity (e.g. SNMP agent) responsible
--		for this object MUST change the value from 0 (zero) to the
--		value of the InterfaceIndex.  If an ATM Label is
--		being used in forwarding data, then the value of this
--		object MUST be the InterfaceIndex."
--	::= { axrMplsLdpEntityAtmParmsEntry 1 }
--axrMplsLdpEntityAtmMergeCap OBJECT-TYPE
--	SYNTAX  INTEGER {
--		notSupported(0),
--		vcMerge(2)
--	}
--	ACCESS  read-create
--	STATUS  mandatory
--	DESCRIPTION
--		"Denotes the Merge Capability of this Entity."
--	::= { axrMplsLdpEntityAtmParmsEntry 2 }
--axrMplsLdpEntityAtmLabelRangeComponents OBJECT-TYPE
--	SYNTAX  Unsigned32 (1..65535)
--	ACCESS  read-create
--	STATUS  mandatory
--	DESCRIPTION
--		"Number of LabelRange Components in the Initialization
--		message.  This also represents the number of entries
--		in the axrMplsLdpLabelRangeComponentsTable which correspond
--		to this entry."
--	::= { axrMplsLdpEntityAtmParmsEntry 3 }
--axrMplsLdpEntityAtmVcDirectionality OBJECT-TYPE
--	SYNTAX  INTEGER {
--		bidirectional(0),
--		unidirectional(1)
--	}
--	ACCESS  read-create
--	STATUS  mandatory
--	DESCRIPTION
--		"If the value of this object is 'bidirectional(0)',
--		a given VCI, within a given VPI, is used as a
--		label for both directions independently.
--		If the value of this object is 'unidirectional(1)',
--		a given VCI within a VPI designates one direction."
--	::= { axrMplsLdpEntityAtmParmsEntry 4 }
--axrMplsLdpEntityAtmLsrConnectivity OBJECT-TYPE
--	SYNTAX  INTEGER {
--		direct(1),
--		indirect(2)
--	}
--	ACCESS  read-create
--	STATUS  mandatory
--	DESCRIPTION
--		"The peer LSR may be connected indirectly by means of an
--		ATM VP so that the VPI values may be different on either
--		endpoint so the label MUST be encoded entirely within the
--		VCI field."
--		DEFVAL { direct }
--	::= { axrMplsLdpEntityAtmParmsEntry 5 }
--axrMplsLdpEntityDefaultControlVpi OBJECT-TYPE
--	SYNTAX  AtmVpIdentifier
--	ACCESS  read-create
--	STATUS  mandatory
--	DESCRIPTION
--		"The default VPI value for the non-MPLS connection.  The
--		default value of this is 0 (zero) but other values may
--		be configured.  This object allows a different value
--		to be configured."
--	DEFVAL
--		{ 0 }
--	::= { axrMplsLdpEntityAtmParmsEntry 6 }
--axrMplsLdpEntityDefaultControlVci OBJECT-TYPE
--	SYNTAX  MplsAtmVcIdentifier
--	ACCESS  read-create
--	STATUS  mandatory
--	DESCRIPTION
--		"The Default VCI value for a non-MPLS connection.  The
--		default value of this is 32 but other values may be
--		configured.  This object allows a different value to
--		be configured."
--	DEFVAL
--		{ 32 }
--	::= { axrMplsLdpEntityAtmParmsEntry 7 }
--axrMplsLdpEntityUnlabTrafVpi OBJECT-TYPE
--	SYNTAX  AtmVpIdentifier
--	ACCESS  read-create
--	STATUS  mandatory
--	DESCRIPTION
--		"VPI value of the VCC supporting unlabelled traffic.  This
--		non-MPLS connection is used to carry unlabelled (IP)
--		packets.  The default value is the same as the default
--		value of the 'axrMplsLdpEntityDefaultControlVpi', however
--		another value may be configured."
--	DEFVAL  { 0 }
--	::= { axrMplsLdpEntityAtmParmsEntry 8 }
--axrMplsLdpEntityUnlabTrafVci OBJECT-TYPE
--	SYNTAX  MplsAtmVcIdentifier
--	ACCESS  read-create
--	STATUS  mandatory
--	DESCRIPTION
--		"VCI value of the VCC supporting unlabelled traffic.
--		This non-MPLS connection is used to carry unlabelled (IP)
--		packets. The default value is the same as the default
--		value of the 'axrMplsLdpEntityDefaultControlVci', however
--		another value may be configured."
--		DEFVAL  { 32 }
--	::= { axrMplsLdpEntityAtmParmsEntry 9 }
--axrMplsLdpEntityAtmStorageType  OBJECT-TYPE
--	SYNTAX  StorageType
--	ACCESS  read-create
--	STATUS  mandatory
--	DESCRIPTION
--		"The storage type for this entry."
--	::= { axrMplsLdpEntityAtmParmsEntry 10 }
--axrMplsLdpEntityAtmRowStatus OBJECT-TYPE
--	SYNTAX  RowStatus
--	ACCESS  read-create
--	STATUS  mandatory
--	DESCRIPTION
--		"An object that allows entries in this table to
--		be created and deleted using the
--		RowStatus convention.
--		NOTE:  This RowStatus object should
--		have the same value of the 'axrMplsLdpEntityRowStatus'
--		related to this entry."
--	::= { axrMplsLdpEntityAtmParmsEntry 11 }
--
-- The MPLS LDP Entity Statistics Table
--

axrMplsLdpEntityStatsTable OBJECT-TYPE
	SYNTAX  SEQUENCE OF AxrMplsLdpEntityStatsEntry
	ACCESS  not-accessible
	STATUS  mandatory
	DESCRIPTION
		"This table is a read-only table which augments
		the axrMplsLdpEntityTable.  The purpose of this
		table is to keep statistical information about
		the LDP Entities on the LSR."
	::= { axrMplsLdpEntityObjects 6 }

axrMplsLdpEntityStatsEntry OBJECT-TYPE
	SYNTAX  AxrMplsLdpEntityStatsEntry
	ACCESS  not-accessible
	STATUS  mandatory
	DESCRIPTION
		"A row in this table contains statistical information
		about an LDP Entity.  Some counters contained in a
		row are for fatal errors received during a former
		LDP Session associated with this entry.  For example,
		an Ldp Pdu received on a TCP connection during an
		LDP Session contains a fatal error.  That
		error is counted here, because the
		session is terminated.
		If the error is NOT fatal (i.e. and the Session
		remains), then the error is counted in the
		axrMplsLdpSessionStatsEntry."
		AUGMENTS    {   axrMplsLdpEntityEntry  }
	::= { axrMplsLdpEntityStatsTable 1 }

	AxrMplsLdpEntityStatsEntry ::= SEQUENCE {
		axrMplsLdpAttemptedSessions                  Counter32,
		axrMplsLdpSessionRejectedNoHelloErrors       Counter32,
		axrMplsLdpSessionRejectedAdvertisementErrors Counter32,
		axrMplsLdpSessionRejectedMaxPduErrors        Counter32,
		axrMplsLdpSessionRejectedLabelRangeErrors    Counter32,
		axrMplsLdpBadLdpIdentifierErrors             Counter32,
		axrMplsLdpBadPduLengthErrors                 Counter32,
		axrMplsLdpBadMessageLengthErrors             Counter32,
		axrMplsLdpBadTlvLengthErrors                 Counter32,
		axrMplsLdpMalformedTlvValueErrors            Counter32,
		axrMplsLdpKeepAliveTimerExpiredErrors        Counter32,
		axrMplsLdpShutdownNotifReceived              Counter32,
		axrMplsLdpShutdownNotifSent                  Counter32
	}

axrMplsLdpAttemptedSessions OBJECT-TYPE
	SYNTAX  Counter32
	ACCESS  read-only
	STATUS  mandatory
	DESCRIPTION
		"A count of the total attempted sessions for
		this LDP Entity."
	::= { axrMplsLdpEntityStatsEntry 1 }

axrMplsLdpSessionRejectedNoHelloErrors OBJECT-TYPE
	SYNTAX  Counter32
	ACCESS  read-only
	STATUS  mandatory
	DESCRIPTION
		"A count of the Session Rejected/No Hello Error
		Notification Messages sent or received by
		this LDP Entity."
	::= { axrMplsLdpEntityStatsEntry 2 }

axrMplsLdpSessionRejectedAdvertisementErrors OBJECT-TYPE
	SYNTAX  Counter32
	ACCESS  read-only
	STATUS  mandatory
	DESCRIPTION
		"A count of the Session Rejected/Parameters
		Advertisement Mode Error Notification Messages sent
		or received by this LDP Entity."
	::= { axrMplsLdpEntityStatsEntry 3 }

axrMplsLdpSessionRejectedMaxPduErrors OBJECT-TYPE
	SYNTAX  Counter32
	ACCESS  read-only
	STATUS  mandatory
	DESCRIPTION
		"A count of the Session Rejected/Parameters
		Max Pdu Length Error Notification Messages sent
		or received by this LDP Entity."
	::= { axrMplsLdpEntityStatsEntry 4 }

axrMplsLdpSessionRejectedLabelRangeErrors OBJECT-TYPE
	SYNTAX  Counter32
	ACCESS  read-only
	STATUS  mandatory
	DESCRIPTION
		"A count of the Session Rejected/Parameters
		Label Range Notification Messages sent
		or received by this LDP Entity."
		::= { axrMplsLdpEntityStatsEntry 5 }

axrMplsLdpBadLdpIdentifierErrors OBJECT-TYPE
	SYNTAX  Counter32
	ACCESS  read-only
	STATUS  mandatory
	DESCRIPTION
		"This object counts the number of Bad LDP Identifier
		Fatal Errors detected by the session(s)
		(past and present) associated with this LDP Entity."
	REFERENCE
		"LDP Specification, Section 3.5.1.2."
	::= { axrMplsLdpEntityStatsEntry 6 }

axrMplsLdpBadPduLengthErrors OBJECT-TYPE
	SYNTAX  Counter32
	ACCESS  read-only
	STATUS  mandatory
	DESCRIPTION
		"This object counts the number of Bad Pdu Length
		Fatal Errors detected by the session(s)
		(past and present) associated with this LDP Entity."
	REFERENCE
		"LDP Specification, Section 3.5.1.2."
	::= { axrMplsLdpEntityStatsEntry 7 }

axrMplsLdpBadMessageLengthErrors OBJECT-TYPE
	SYNTAX  Counter32
	ACCESS  read-only
	STATUS  mandatory
	DESCRIPTION
		"This object counts the number of Bad Message
		Length Fatal Errors detected by the session(s)
		(past and present) associated with this LDP Entity."
	REFERENCE
		"LDP Specification, Section 3.5.1.2."
	::= { axrMplsLdpEntityStatsEntry 8 }

axrMplsLdpBadTlvLengthErrors OBJECT-TYPE
	SYNTAX  Counter32
	ACCESS  read-only
	STATUS  mandatory
	DESCRIPTION
		"This object counts the number of Bad TLV
		Length Fatal Errors detected by the session(s)
		(past and present) associated with this LDP Entity."
	REFERENCE
		"LDP Specification, Section 3.5.1.2."
	::= { axrMplsLdpEntityStatsEntry 9 }

axrMplsLdpMalformedTlvValueErrors OBJECT-TYPE
	SYNTAX  Counter32
	ACCESS  read-only
	STATUS  mandatory
	DESCRIPTION
		"This object counts the number of Malformed TLV
		Value Fatal Errors detected by the session(s)
		(past and present) associated with this
		LDP Entity."
	REFERENCE
		"LDP Specification, Section 3.5.1.2."
	::= { axrMplsLdpEntityStatsEntry 10 }

axrMplsLdpKeepAliveTimerExpiredErrors OBJECT-TYPE
	SYNTAX  Counter32
	ACCESS  read-only
	STATUS  mandatory
	DESCRIPTION
		"This object counts the number of Session Keep Alive
		Timer Expired Errors detected by the session(s)
		(past and present) associated with this LDP Entity."
	REFERENCE
		"LDP Specification, Section 3.5.1.2."
	::= { axrMplsLdpEntityStatsEntry 11 }

axrMplsLdpShutdownNotifReceived OBJECT-TYPE
	SYNTAX  Counter32
	ACCESS  read-only
	STATUS  mandatory
	DESCRIPTION
		"This object counts the number of Shutdown Notfications
		received related to session(s) (past and present)
		associated with this LDP Entity."
	::= { axrMplsLdpEntityStatsEntry 12 }

axrMplsLdpShutdownNotifSent OBJECT-TYPE
	SYNTAX  Counter32
	ACCESS  read-only
	STATUS  mandatory
	DESCRIPTION
		"This object counts the number of Shutdown Notfications
		sent related to session(s) (past and present) associated
		with this LDP Entity."
	::= { axrMplsLdpEntityStatsEntry 13 }

--
-- The MPLS LDP Peer Table
--

axrMplsLdpSessionObjects OBJECT IDENTIFIER ::= { axrMplsLdpObjects 3 }

axrMplsLdpPeerTable OBJECT-TYPE
	SYNTAX  SEQUENCE OF AxrMplsLdpPeerEntry
	ACCESS  not-accessible
	STATUS  mandatory
	DESCRIPTION
		"Information about LDP peers known by Entities in
		the axrMplsLdpEntityTable.  The information in this table
		is based on information from the Entity-Peer interaction
		during session initialization but is not appropriate
		for the axrMplsLdpSessionTable, because objects in this
		table may or may not be used in session establishment."
	::= { axrMplsLdpSessionObjects 1 }

axrMplsLdpPeerEntry OBJECT-TYPE
	SYNTAX  AxrMplsLdpPeerEntry
	ACCESS  not-accessible
	STATUS  mandatory
	DESCRIPTION
		"Information about a single Peer which is related
		to a Session.  NOTE:  this table is used to
		augment the axrMplsLdpSessionTable."
	INDEX  { axrMplsLdpEntityLdpId,
		axrMplsLdpEntityIndex,
		axrMplsLdpPeerLdpId }
	::= { axrMplsLdpPeerTable 1 }

	AxrMplsLdpPeerEntry ::= SEQUENCE {
		axrMplsLdpPeerLdpId                      AxrMplsLdpIdentifier,
		axrMplsLdpPeerLabelDistributionMethod    INTEGER,
		axrMplsLdpPeerLoopDetectionForPV         INTEGER,
		axrMplsLdpPeerPathVectorLimit            Integer32
	}

axrMplsLdpPeerLdpId OBJECT-TYPE
	SYNTAX  AxrMplsLdpIdentifier
	ACCESS  not-accessible
	STATUS  mandatory
	DESCRIPTION
		"The LDP identifier of this LDP Peer."
	::= { axrMplsLdpPeerEntry 1 }

axrMplsLdpPeerLabelDistributionMethod OBJECT-TYPE
	SYNTAX  INTEGER {
		downstreamOnDemand(1),
		downstreamUnsolicited(2)
	}
	ACCESS  read-only
	STATUS  mandatory
	DESCRIPTION
		"For any given LDP session, the method of
		label distribution must be specified."
	::= { axrMplsLdpPeerEntry 2 }

axrMplsLdpPeerLoopDetectionForPV OBJECT-TYPE
	SYNTAX  INTEGER {
		disabled(0),
		enabled(1)
	}
	ACCESS  read-only
	STATUS  mandatory
	DESCRIPTION
		"An indication of whether loop detection based
		on path vectors is disabled or enabled for this Peer.
		If this object has a value of disabled(0),
		then loop detection is disabled.  Otherwise, if this
		object has a value of enabled(1), then loop detection
		based on path vectors is enabled."
	::= { axrMplsLdpPeerEntry 3 }

axrMplsLdpPeerPathVectorLimit OBJECT-TYPE
	SYNTAX  Integer32 (0..255)
	ACCESS  read-only
	STATUS  mandatory
	DESCRIPTION
		"If the value of 'axrMplsLdpPeerLoopDetectionForPV' for
		this entry is 'enabled(1)', the this object represents
		that Path Vector Limit for this peer.
		If the value of 'axrMplsLdpPeerLoopDetectionForPV' for
		this entry is 'disabled(0)', then this value should
		be 0 (zero)."
	::= { axrMplsLdpPeerEntry 4 }

--
-- The MPLS LDP Hello Adjacency Table
--

	axrMplsLdpHelloAdjacencyObjects OBJECT IDENTIFIER ::=
								{ axrMplsLdpSessionObjects 2 }

axrMplsLdpHelloAdjacencyTable OBJECT-TYPE
	SYNTAX  SEQUENCE OF AxrMplsLdpHelloAdjacencyEntry
	ACCESS  not-accessible
	STATUS  mandatory
	DESCRIPTION
		"A table of Hello Adjacencies for Sessions."
	::= { axrMplsLdpHelloAdjacencyObjects 1 }

axrMplsLdpHelloAdjacencyEntry OBJECT-TYPE
	SYNTAX  AxrMplsLdpHelloAdjacencyEntry
	ACCESS  not-accessible
	STATUS  mandatory
	DESCRIPTION
		"Each row represents a single LDP Hello Adjacency.
		An LDP Session can have one or more Hello adjacencies."
	INDEX  { axrMplsLdpEntityLdpId,
		axrMplsLdpEntityIndex,
		axrMplsLdpPeerLdpId,
		axrMplsLdpHelloAdjacencyIndex }
	::= { axrMplsLdpHelloAdjacencyTable 1 }

	AxrMplsLdpHelloAdjacencyEntry ::= SEQUENCE {
		axrMplsLdpHelloAdjacencyIndex                  Unsigned32,
		axrMplsLdpHelloAdjacencyHoldTimeRemaining      TimeInterval,
		axrMplsLdpHelloAdjacencyType                   INTEGER
	}

axrMplsLdpHelloAdjacencyIndex OBJECT-TYPE
	SYNTAX  Unsigned32 (1..4294967295)
	ACCESS  not-accessible
	STATUS  mandatory
	DESCRIPTION
		"An identifier for this specific adjacency."
	::= { axrMplsLdpHelloAdjacencyEntry 1 }

axrMplsLdpHelloAdjacencyHoldTimeRemaining OBJECT-TYPE
	SYNTAX  TimeInterval
	ACCESS  read-only
	STATUS  mandatory
	DESCRIPTION
		"The time remaining for this Hello Adjacency.
		This interval will change when the 'next'
		Hello message which corresponds to this
		Hello Adjacency is received."
	::= { axrMplsLdpHelloAdjacencyEntry 2 }

axrMplsLdpHelloAdjacencyType OBJECT-TYPE
	SYNTAX  INTEGER {
	link(1),
	targeted(2)
	}
	ACCESS  read-only
	STATUS  mandatory
	DESCRIPTION
		"This adjacency is the result of a 'link'
		hello if the value of this object is link(1).
		Otherwise, it is a result of a 'targeted'
		hello, targeted(2)."
	::= { axrMplsLdpHelloAdjacencyEntry 3 }

--
-- The MPLS LDP Sessions Table
--

axrMplsLdpSessionUpDownTrapEnable OBJECT-TYPE
	SYNTAX  INTEGER {
		enabled(1),
		disabled(2)
	}
	ACCESS  read-write
	STATUS  mandatory
	DESCRIPTION
		"Indicates whether the traps, 'axrMplsLdpSessionUp' and
		'axrMplsLdpSessionDown' will be generated or not.
		If the value of this object is 'enabled(1)'
		then the traps will generated.  If the value
		of this object is 'disabled(2)' then the
		traps will not be generated.  The DEFVAL
		is set to 'disabled(2)'."
		DEFVAL { disabled }
	::= { axrMplsLdpSessionObjects 3 }

axrMplsLdpSessionTable OBJECT-TYPE
	SYNTAX  SEQUENCE OF AxrMplsLdpSessionEntry
	ACCESS  not-accessible
	STATUS  mandatory
	DESCRIPTION
		"A table of Sessions between the LDP Entities and
		LDP Peers.  Each row represents a single session."
	::= { axrMplsLdpSessionObjects 4 }

axrMplsLdpSessionEntry OBJECT-TYPE
	SYNTAX  AxrMplsLdpSessionEntry
	ACCESS  not-accessible
	STATUS  mandatory
	DESCRIPTION
		"An entry in this table represents information on a
		single session between an LDP Entity and LDP Peer.
		The information contained in a row is read-only.
		Please note:  the Path Vector Limit for the
		Session is the value which is configured in
		the corresponding axrMplsLdpEntityEntry. The
		Peer's Path Vector Limit is in noted in the
		axrMplsLdpPeerTable.
		Values which may differ from those configured are
		noted in the objects of this table, the
		axrMplsLdpAtmSessionTable and the
		axrMplsLdpFrameRelaySessionTable. A value will
		differ if it was negotiated between the
		Entity and the Peer. Values may or may not
		be negotiated. For example, if the values
		are the same then no negotiation takes place.
		If they are negotiated, then they may differ."
		AUGMENTS { axrMplsLdpPeerEntry }
	::= { axrMplsLdpSessionTable 1 }

	AxrMplsLdpSessionEntry ::= SEQUENCE {
		axrMplsLdpSessionState                          INTEGER,
		axrMplsLdpSessionProtocolVersion                Integer32,
		axrMplsLdpSessionKeepAliveHoldTimeRemaining     TimeInterval,
		axrMplsLdpSessionMaxPduLength                   Unsigned32,
		axrMplsLdpSessionDiscontinuityTime              TimeStamp
	}

axrMplsLdpSessionState OBJECT-TYPE
	SYNTAX  INTEGER {
		nonexistent(1),
		initialized(2),
		openrec(3),
		opensent(4),
		operational(5)
	}
	ACCESS  read-only
	STATUS  mandatory
	DESCRIPTION
		"The current state of the session, all of the
		states 1 - 5 are based on the state machine for
		session negotiation behavior."
	::= { axrMplsLdpSessionEntry 1 }

axrMplsLdpSessionProtocolVersion OBJECT-TYPE
	SYNTAX  Integer32(1..65535)
	ACCESS  read-only
	STATUS  mandatory
	DESCRIPTION
		"The version of the LDP Protocol which
		this session is using."
	::= { axrMplsLdpSessionEntry 2 }

axrMplsLdpSessionKeepAliveHoldTimeRemaining OBJECT-TYPE
	SYNTAX  TimeInterval
	ACCESS  read-only
	STATUS  mandatory
	DESCRIPTION
		"The keep alive hold time remaining for this session."
	::= { axrMplsLdpSessionEntry 3 }

axrMplsLdpSessionMaxPduLength OBJECT-TYPE
	SYNTAX  Unsigned32 (1..65535)
	ACCESS  read-only
	STATUS  mandatory
	DESCRIPTION
		"The value of maximum allowable length for LDP PDUs for
		this session.  This value may have been negotiated during
		the Session Initialization."
	::= { axrMplsLdpSessionEntry 4 }

axrMplsLdpSessionDiscontinuityTime OBJECT-TYPE
	SYNTAX  TimeStamp
	ACCESS  read-only
	STATUS  mandatory
	DESCRIPTION
		"The value of sysUpTime on the most recent occasion at
		which any one or more of this session's counters
		suffered a discontinuity.  The relevant counters are
		the specific instances associated with this session
		of any Counter32 or Counter64 object contained in the
		axrMplsLdpSessionStatsTable.  If no such discontinuities have
		occurred since the last re-initialization of the local
		management subsystem, then this object contains a zero
		value.
		Also, an NMS can distinguish when a session
		between a given Entity and Peer goes away and then is
		re-established'.  This value would change and
		thus indicate to the NMS that this is a
		different session."
	::= { axrMplsLdpSessionEntry 5 }

--
-- MPLS LDP ATM Session Information
--
--
--axrMplsLdpAtmSessionTable OBJECT-TYPE
--	SYNTAX  SEQUENCE OF AxrMplsLdpAtmSessionEntry
--	ACCESS  not-accessible
--	STATUS  mandatory
--	DESCRIPTION
--		"A table which relates Sessions in the
--		'axrMplsLdpSessionTable' and their label
--		range intersections.  There could be one
--		or more label range intersections between an
--		LDP Entity and LDP Peer using ATM as the underlying
--		media. Each row represents a single label range
--		intersection.
--		NOTE:  this table cannot use the 'AUGMENTS'
--		clause because there is not necessarily a one-to-one
--		mapping between this table and the axrMplsLdpSessionTable."
--	::= { axrMplsLdpSessionObjects 5 }
--
--axrMplsLdpAtmSessionEntry OBJECT-TYPE
--	SYNTAX  AxrMplsLdpAtmSessionEntry
--	ACCESS  not-accessible
--	STATUS  mandatory
--	DESCRIPTION
--		"An entry in this table represents information on a
--		single label range intersection between an LDP Entity
--		and LDP Peer.
--		The information contained in a row is read-only."
--	INDEX  { axrMplsLdpEntityLdpId,
--		axrMplsLdpEntityIndex,
--		axrMplsLdpPeerLdpId,
--		axrMplsLdpSessionAtmLabelRangeLowerBoundVpi,
--		axrMplsLdpSessionAtmLabelRangeLowerBoundVci
--		}
--	::= { axrMplsLdpAtmSessionTable 1 }
--
--	AxrMplsLdpAtmSessionEntry ::= SEQUENCE {
--		axrMplsLdpSessionAtmLabelRangeLowerBoundVpi     AtmVpIdentifier,
--		axrMplsLdpSessionAtmLabelRangeLowerBoundVci     MplsAtmVcIdentifier,
--		axrMplsLdpSessionAtmLabelRangeUpperBoundVpi     AtmVpIdentifier,
--		axrMplsLdpSessionAtmLabelRangeUpperBoundVci     MplsAtmVcIdentifier
--	}
--
--axrMplsLdpSessionAtmLabelRangeLowerBoundVpi OBJECT-TYPE
--	SYNTAX  AtmVpIdentifier
--	ACCESS  not-accessible
--	STATUS  mandatory
--	DESCRIPTION
--		"The minimum VPI number for this range."
--	::= { axrMplsLdpAtmSessionEntry 1 }
--
--axrMplsLdpSessionAtmLabelRangeLowerBoundVci OBJECT-TYPE
--	SYNTAX  MplsAtmVcIdentifier
--	ACCESS  not-accessible
--	STATUS  mandatory
--	DESCRIPTION
--		"The minimum VCI number for this range."
--	::= { axrMplsLdpAtmSessionEntry 2 }
--
--axrMplsLdpSessionAtmLabelRangeUpperBoundVpi OBJECT-TYPE
--	SYNTAX  AtmVpIdentifier
--	ACCESS  read-only
--	STATUS  mandatory
--	DESCRIPTION
--		"The maximum VPI number for this range."
--	::= { axrMplsLdpAtmSessionEntry 3 }
--
--axrMplsLdpSessionAtmLabelRangeUpperBoundVci OBJECT-TYPE
--	SYNTAX  MplsAtmVcIdentifier
--	ACCESS  read-only
--	STATUS  mandatory
--	DESCRIPTION
--		"The maximum VCI number for this range."
--	::= { axrMplsLdpAtmSessionEntry 4 }

--
-- The MPLS LDP Session Statistics Table
--

axrMplsLdpSessionStatsTable OBJECT-TYPE
	SYNTAX  SEQUENCE OF AxrMplsLdpSessionStatsEntry
	ACCESS  not-accessible
	STATUS  mandatory
	DESCRIPTION
		"A table of statistics for Sessions between
		LDP Entities and LDP Peers."
	::= { axrMplsLdpSessionObjects 7 }

axrMplsLdpSessionStatsEntry OBJECT-TYPE
	SYNTAX  AxrMplsLdpSessionStatsEntry
	ACCESS  not-accessible
	STATUS  mandatory
	DESCRIPTION
		"An entry in this table represents statistical
		information on a single session between an LDP
		Entity and LDP Peer."
	AUGMENTS   { axrMplsLdpPeerEntry }
	::= { axrMplsLdpSessionStatsTable 1 }

	AxrMplsLdpSessionStatsEntry ::= SEQUENCE {
		axrMplsLdpSessionStatsUnknownMessageTypeErrors Counter32,
		axrMplsLdpSessionStatsUnknownTlvErrors         Counter32
	}

axrMplsLdpSessionStatsUnknownMessageTypeErrors OBJECT-TYPE
	SYNTAX  Counter32
	ACCESS  read-only
	STATUS  mandatory
	DESCRIPTION
		"This object counts the number of Unknown Message Type
		Errors detected during this session.
		Discontinuities in the value of this counter can occur
		at re-initialization of the management system, and at
		other times as indicated by the value of
		axrMplsLdpSeeionDiscontinuityTime."
	::= { axrMplsLdpSessionStatsEntry 1 }

axrMplsLdpSessionStatsUnknownTlvErrors OBJECT-TYPE
	SYNTAX  Counter32
	ACCESS  read-only
	STATUS  mandatory
	DESCRIPTION
		"This object counts the number of Unknown TLV Errors
		detected during this session.
		Discontinuities in the value of this counter can occur
		at re-initialization of the management system, and at
		other times as indicated by the value of
		axrMplsLdpSeeionDiscontinuityTime."
	::= { axrMplsLdpSessionStatsEntry 2 }

--
-- Address Message/Address Withdraw Message Information
--
-- This information is associated with a specific Session
-- because Label Address Messages are sent after session
-- initialization has taken place.
--

axrMplsLdpSessionPeerAddressTable OBJECT-TYPE
	SYNTAX  SEQUENCE OF AxrMplsLdpSessionPeerAddressEntry
	ACCESS  not-accessible
	STATUS  mandatory
	DESCRIPTION
		"This table 'extends' the axrMplsLdpSessionTable.
		This table is used to store Label Address Information
		from Label Address Messages received by this LSR from
		Peers.	This table is read-only and should be updated
		when Label Withdraw Address Messages are received, i.e.
		Rows should be deleted as apropriate.
		NOTE:  since more than one address may be contained
		in a Label Address Message, this table 'extends',
		rather than 'AUGMENTS' the axrMplsLdpSessionTable's
		information."
	::= { axrMplsLdpSessionObjects 12 }

axrMplsLdpSessionPeerAddressEntry OBJECT-TYPE
	SYNTAX  AxrMplsLdpSessionPeerAddressEntry
	ACCESS  not-accessible
	STATUS  mandatory
	DESCRIPTION
		"An entry in this table represents information on
		session's for a single next hop address which was
		advertised in an Address Message from the LDP peer.
		The information contained in a row is read-only."
	INDEX  { axrMplsLdpEntityLdpId,
		axrMplsLdpEntityIndex,
		axrMplsLdpPeerLdpId,
		axrMplsLdpSessionPeerAddressIndex
	}
	::= { axrMplsLdpSessionPeerAddressTable 1 }

	AxrMplsLdpSessionPeerAddressEntry ::= SEQUENCE {
		axrMplsLdpSessionPeerAddressIndex           Unsigned32,
		axrMplsLdpSessionPeerNextHopAddressType     AddressFamilyNumbers,
		axrMplsLdpSessionPeerNextHopAddress         AxrMplsLdpGenAddr
	}

axrMplsLdpSessionPeerAddressIndex OBJECT-TYPE
	SYNTAX  Unsigned32 (1..4294967295)
	ACCESS  not-accessible
	STATUS  mandatory
	DESCRIPTION
		"An index which uniquely identifies this entry within
		a given session."
	::= { axrMplsLdpSessionPeerAddressEntry 1 }

axrMplsLdpSessionPeerNextHopAddressType OBJECT-TYPE
	SYNTAX  AddressFamilyNumbers
	ACCESS  read-only
	STATUS  mandatory
	DESCRIPTION
		"The internetwork layer address type of this Next Hop
		Address as specified in the Label Address Message
		associated with this Session. The value of this
		object indicates how to interpret the value of
		axrMplsLdpSessionPeerNextHopAddress."
	::= { axrMplsLdpSessionPeerAddressEntry 2 }

axrMplsLdpSessionPeerNextHopAddress OBJECT-TYPE
	SYNTAX  AxrMplsLdpGenAddr
	ACCESS  read-only
	STATUS  mandatory
	DESCRIPTION
		"The value of the next hop address."
	REFERENCE
		"LDP Specification [18] defines only IPv4 for LDP Protocol
		Version 1, see section 3.4.3."
	::= { axrMplsLdpSessionPeerAddressEntry 3 }
	

--  OADP Group

axrOadpGlobalActive  OBJECT-TYPE
	SYNTAX  TruthValue
	ACCESS  read-only
	STATUS  mandatory
	DESCRIPTION
		"Operation status of OADP function. Status set
		 by enable or disable in Oadp configuration.
		 enable : 1
		 disable: 2"
	::= { axrOadpGlobalInfo 1 }

axrOadpGlobalCdpActive  OBJECT-TYPE
	SYNTAX  TruthValue
	ACCESS  read-only
	STATUS  mandatory
	DESCRIPTION
		"Operation status of CDP reception function.
		 Status whether cdp-listener is set or not in oadp configuration.
		 cdp-listener           : 1
		 cdp-listener is not set: 2"
	::= { axrOadpGlobalInfo 2 }

axrOadpGlobalMessageInterval OBJECT-TYPE
	SYNTAX  INTEGER
	ACCESS  read-only
	STATUS  mandatory
	DESCRIPTION
		"Sending interval of OADP frame. The value of interval-time in oadp configuration."
	::= { axrOadpGlobalInfo 3 }

axrOadpGlobalHoldTime OBJECT-TYPE
	SYNTAX  INTEGER
	ACCESS  read-only
	STATUS  mandatory
	DESCRIPTION
		"Neighbor divice's holding time of OADP frame which this device send.
		 The value of hold-time in oadp configuration."
	::= { axrOadpGlobalInfo 4 }

axrOadpGlobalCacheLastChange OBJECT-TYPE
	SYNTAX  TimeTicks
	ACCESS  read-only
	STATUS  mandatory
	DESCRIPTION
		"Value of sysUpTime which is set when axrOadpNeighborTable is updated."
	::= { axrOadpGlobalInfo 5 }

axrOadpGlobalName OBJECT-TYPE
	SYNTAX  DisplayString
	ACCESS  read-only
	STATUS  mandatory
	DESCRIPTION
		"Device identifier."
	::= { axrOadpGlobalInfo 6 }

axrOadpGlobalNameType OBJECT-TYPE
	SYNTAX  INTEGER {
		other(1),
		sysName(2),
		serialNumber(3),
		macaddress(4)
    }
	ACCESS  read-only
	STATUS  mandatory
	DESCRIPTION
		"Kind of axrOadpGlobalName."
	::= { axrOadpGlobalInfo 7 }

axrOadpPortConfigTable OBJECT-TYPE
	SYNTAX  SEQUENCE OF AxrOadpPortConfigEntry
	ACCESS  not-accessible
	STATUS  mandatory
	DESCRIPTION
		"A table of OADP port information."
	::= { axrOadpPortInfo 1 }

axrOadpPortConfigEntry OBJECT-TYPE
	SYNTAX  AxrOadpPortConfigEntry
	ACCESS  not-accessible
	STATUS  mandatory
	DESCRIPTION
		"An entry of OADP port information."
    INDEX { axrOadpPortConfigIfIndex }
	::= { axrOadpPortConfigTable 1 }

	AxrOadpPortConfigEntry ::=
		SEQUENCE {
		    axrOadpPortConfigIfIndex	InterfaceIndex,
		    axrOadpPortConfigActive	TruthValue
		}

axrOadpPortConfigIfIndex OBJECT-TYPE
	SYNTAX  InterfaceIndex
	ACCESS  read-only
	STATUS  mandatory
	DESCRIPTION
		"Port identification index. The same value as ifIndex.
		 This is only for physical ports and LA ports which are given
		 ifIndex."
	::= { axrOadpPortConfigEntry 1 }

axrOadpPortConfigActive OBJECT-TYPE
	SYNTAX  TruthValue
	ACCESS  read-only
	STATUS  mandatory
	DESCRIPTION
		"Status of specified port."
	::= { axrOadpPortConfigEntry 2 }

axrOadpNeighborTable OBJECT-TYPE
	SYNTAX  SEQUENCE OF AxrOadpNeighborEntry
	ACCESS  not-accessible
	STATUS  mandatory
	DESCRIPTION
		"A table of OADP neighbor nodes."
	::= { axrOadpNeighborInfo 1 }

axrOadpNeighborEntry OBJECT-TYPE
	SYNTAX  AxrOadpNeighborEntry
	ACCESS  not-accessible
	STATUS  mandatory
	DESCRIPTION
		"An entry of OADP neighbor nodes."
    INDEX { axrOadpIfIndex, axrOadpTagID, axrOadpNeighborIndex, axrOadpNeighborTagID }
	::= { axrOadpNeighborTable 1 }

	AxrOadpNeighborEntry ::=
		SEQUENCE {
		    axrOadpIfIndex			InterfaceIndex,
		    axrOadpTagID		 		INTEGER, 
		    axrOadpNeighborIndex  		INTEGER,
		    axrOadpNeighborTagID   		INTEGER,
		    axrOadpNeighborVendorType   		INTEGER,
		    axrOadpNeighborSNMPAgentAddressType 	INTEGER,
		    axrOadpNeighborSNMPAgentAddress  	DisplayString,
		    axrOadpNeighborDescr		   	DisplayString,
		    axrOadpNeighborDeviceID	   	DisplayString,
		    axrOadpNeighborSlotPort 	   	DisplayString,
		    axrOadpNeighborIfIndex  	   	InterfaceIndex,
		    axrOadpNeighborIfSpeed   	   	Gauge,
		    axrOadpNeighborDeviceType   	   	DisplayString,
		    axrOadpNeighborService   	   	OCTET STRING,
		    axrOadpNeighborVTPMgmtDomain    	DisplayString,
		    axrOadpNeighborNativeVLAN     	INTEGER,
		    axrOadpNeighborDuplex 	     	INTEGER,
		    axrOadpNeighborApplianceID  	     	Gauge,
		    axrOadpNeighborVlanID   	     	Gauge,
		    axrOadpNeighborPowerConsumption     	Gauge,
		    axrOadpNeighborMTU           	Gauge,
		    axrOadpNeighborSysName            	DisplayString,
		    axrOadpNeighborSysObjectID          	OBJECT IDENTIFIER,
		    axrOadpNeighborSecondarySNMPAgentAddressType  INTEGER,
		    axrOadpNeighborSecondarySNMPAgentAddress      DisplayString,
		    axrOadpNeighborPhysLocation          DisplayString,
		    axrOadpNeighborCacheLastChange       TimeTicks,
		    axrOadpNeighborIfHighSpeed           Gauge
		}

axrOadpIfIndex OBJECT-TYPE
	SYNTAX  InterfaceIndex
	ACCESS  read-only
	STATUS  mandatory
	DESCRIPTION
		"ifIndex of reception interface."
	::= { axrOadpNeighborEntry 1 }

axrOadpTagID OBJECT-TYPE
	SYNTAX  INTEGER
	ACCESS  read-only
	STATUS  mandatory
	DESCRIPTION
		"Tag ID of IEEE802.1Q which is attached MAC frame."
	::= { axrOadpNeighborEntry 2 }

axrOadpNeighborIndex OBJECT-TYPE
	SYNTAX  INTEGER
	ACCESS  read-only
	STATUS  mandatory
	DESCRIPTION
		"Unique numeric which identifies neighbor nodes"
	::= { axrOadpNeighborEntry 3 }

axrOadpNeighborTagID OBJECT-TYPE
	SYNTAX  INTEGER
	ACCESS  read-only
	STATUS  mandatory
	DESCRIPTION
		"Value set at TagID TLV in OADP PDU which is sent from neighbor node."
	::= { axrOadpNeighborEntry 4 }

axrOadpNeighborVendorType OBJECT-TYPE
	SYNTAX  INTEGER {
		other(1),
		oadp(2),
		cdp(3)
    }
	ACCESS  read-only
	STATUS  mandatory
	DESCRIPTION
		"Protocol type used to find to neighbor nodes."
	::= { axrOadpNeighborEntry 5 }

axrOadpNeighborSNMPAgentAddressType OBJECT-TYPE
	SYNTAX  INTEGER {
		ipv4(1),
		ipv6(20),
		other-notSupported(65535)
    }
	ACCESS  read-only
	STATUS  mandatory
	DESCRIPTION
		"A kind of agent address to get information by SNMP."
	::= { axrOadpNeighborEntry 6 }

axrOadpNeighborSNMPAgentAddress OBJECT-TYPE
	SYNTAX  DisplayString
	ACCESS  read-only
	STATUS  mandatory
	DESCRIPTION
		"DisplayString formed information of agent address to get information by SNMP."
	::= { axrOadpNeighborEntry 7 }

axrOadpNeighborDescr OBJECT-TYPE
	SYNTAX  DisplayString
	ACCESS  read-only
	STATUS  mandatory
	DESCRIPTION
		"String of sysDescr of neighbor node."
	::= { axrOadpNeighborEntry 8 }

axrOadpNeighborDeviceID OBJECT-TYPE
	SYNTAX  DisplayString
	ACCESS  read-only
	STATUS  mandatory
	DESCRIPTION
		"Neighbor node's device identifier."
	::= { axrOadpNeighborEntry 9 }

axrOadpNeighborSlotPort OBJECT-TYPE
	SYNTAX  DisplayString
	ACCESS  read-only
	STATUS  mandatory
	DESCRIPTION
		"Unique string which identifies neighbor's sending interface."
	::= { axrOadpNeighborEntry 10 }

axrOadpNeighborIfIndex OBJECT-TYPE
	SYNTAX  InterfaceIndex
	ACCESS  read-only
	STATUS  mandatory
	DESCRIPTION
		"ifIndex of sending interface of neighbor node."
	::= { axrOadpNeighborEntry 11 }

axrOadpNeighborIfSpeed OBJECT-TYPE
	SYNTAX  Gauge
	ACCESS  read-only
	STATUS  mandatory
	DESCRIPTION
		"ifSpeed of sending interface of neighbor node."
	::= { axrOadpNeighborEntry 12 }

axrOadpNeighborDeviceType OBJECT-TYPE
	SYNTAX  DisplayString
	ACCESS  read-only
	STATUS  mandatory
	DESCRIPTION
		"Device name of neighbor node."
	::= { axrOadpNeighborEntry 13 }

axrOadpNeighborService OBJECT-TYPE
	SYNTAX  OCTET STRING
	ACCESS  read-only
	STATUS  mandatory
	DESCRIPTION
		"Functions neighbor node can offer."
	::= { axrOadpNeighborEntry 14 }

axrOadpNeighborVTPMgmtDomain OBJECT-TYPE
	SYNTAX  DisplayString
	ACCESS  read-only
	STATUS  mandatory
	DESCRIPTION
		"VTP Management Domain of sending interface of neighbor node."
	::= { axrOadpNeighborEntry 15 }

axrOadpNeighborNativeVLAN OBJECT-TYPE
	SYNTAX  INTEGER
	ACCESS  read-only
	STATUS  mandatory
	DESCRIPTION
		"Native VLAN number of sending interface of neighbor node."
	::= { axrOadpNeighborEntry 16 }

axrOadpNeighborDuplex OBJECT-TYPE
	SYNTAX  INTEGER {
		unknown(1),
		half(2),
		full(3)
    }
	ACCESS  read-only
	STATUS  mandatory
	DESCRIPTION
		"Duplex information of sending interface of neighbor node."
	::= { axrOadpNeighborEntry 17 }

axrOadpNeighborApplianceID OBJECT-TYPE
	SYNTAX  Gauge
	ACCESS  read-only
	STATUS  mandatory
	DESCRIPTION
		"Appliance ID of neighbor node."
	::= { axrOadpNeighborEntry 18 }

axrOadpNeighborVlanID OBJECT-TYPE
	SYNTAX  Gauge
	ACCESS  read-only
	STATUS  mandatory
	DESCRIPTION
		"VLAN ID for VoIP of neighbor node."
	::= { axrOadpNeighborEntry 19 }

axrOadpNeighborPowerConsumption OBJECT-TYPE
	SYNTAX  Gauge
	ACCESS  read-only
	STATUS  mandatory
	DESCRIPTION
		"Electric power comsumption of neighbor node."
	::= { axrOadpNeighborEntry 20 }

axrOadpNeighborMTU OBJECT-TYPE
	SYNTAX  Gauge
	ACCESS  read-only
	STATUS  mandatory
	DESCRIPTION
		"MTU of sending interface of neighbor node."
	::= { axrOadpNeighborEntry 21 }

axrOadpNeighborSysName OBJECT-TYPE
	SYNTAX  DisplayString
	ACCESS  read-only
	STATUS  mandatory
	DESCRIPTION
		"sysName of neighbor node."
	::= { axrOadpNeighborEntry 22 }

axrOadpNeighborSysObjectID OBJECT-TYPE
	SYNTAX  OBJECT IDENTIFIER
	ACCESS  read-only
	STATUS  mandatory
	DESCRIPTION
		"sysObjectID of neighbor node."
	::= { axrOadpNeighborEntry 23 }

axrOadpNeighborSecondarySNMPAgentAddressType OBJECT-TYPE
	SYNTAX  INTEGER {
		ipv4(1),
		ipv6(20),
		other-notSupported(65535)
    }
	ACCESS  read-only
	STATUS  mandatory
	DESCRIPTION
		"A kind of agent secondary address to get information by SNMP."
	::= { axrOadpNeighborEntry 24 }

axrOadpNeighborSecondarySNMPAgentAddress OBJECT-TYPE
	SYNTAX  DisplayString
	ACCESS  read-only
	STATUS  mandatory
	DESCRIPTION
		"DisplayString formed information of agent secondary address to get information by SNMP."
	::= { axrOadpNeighborEntry 25 }

axrOadpNeighborPhysLocation OBJECT-TYPE
	SYNTAX  DisplayString
	ACCESS  read-only
	STATUS  mandatory
	DESCRIPTION
		"sysLocation of neighbor node."
	::= { axrOadpNeighborEntry 26 }

axrOadpNeighborCacheLastChange OBJECT-TYPE
	SYNTAX  TimeTicks
	ACCESS  read-only
	STATUS  mandatory
	DESCRIPTION
		"Value of sysUpTime which is set when axrOadpNeighborEntry about neighbor node is updated."
	::= { axrOadpNeighborEntry 27 }

axrOadpNeighborIfHighSpeed OBJECT-TYPE
	SYNTAX  Gauge
	ACCESS  read-only
	STATUS  mandatory
	DESCRIPTION
		"ifHighSpeed of sending interface of neighbor node."
	::= { axrOadpNeighborEntry 28 }

-- axrFlow group
axrFlowResourcesSystemUsed OBJECT-TYPE
	SYNTAX  INTEGER
	ACCESS  read-only
	STATUS  mandatory
	DESCRIPTION
		"The number of entries used for flow filter function, flow Qo
		S function, NetFlow statistics information function per devic
		e."
	::= { axrFlowResources 1 }

axrFlowResourcesSystemFree OBJECT-TYPE
	SYNTAX  INTEGER
	ACCESS  read-only
	STATUS  mandatory
	DESCRIPTION
		"The number of empty entries usable for flow filter function,
		 flow QoS function, NetFlow statistics information function p
		er device."
	::= { axrFlowResources 2 }

axrFlowResourcesSystemMax OBJECT-TYPE
	SYNTAX  INTEGER
	ACCESS  read-only
	STATUS  mandatory
	DESCRIPTION
		"The maximum number of entries usable for flow filter functio
		n, flow Qos function, NetFlow statistics information function
		."
	::= { axrFlowResources 3 }

axrFlowResourcesSystemNetflowUsed OBJECT-TYPE
	SYNTAX  INTEGER
	ACCESS  read-only
	STATUS  mandatory
	DESCRIPTION
		"The number of entries used for NetFlow statistics informatio
		n."
	::= { axrFlowResources 4 }

axrFlowResourcesSystemPolicyUsed OBJECT-TYPE
	SYNTAX  INTEGER
	ACCESS  read-only
	STATUS  mandatory
	DESCRIPTION
		"The number of entries used for policy routing function per d
		evice."
	::= { axrFlowResources 5 }

axrFlowResourcesSystemPolicyMax OBJECT-TYPE
	SYNTAX  INTEGER
	ACCESS  read-only
	STATUS  mandatory
	DESCRIPTION
		"The maximum number of entries usable for policy routing func
		tion per device."
	::= { axrFlowResources 6 }

axrFlowResourcesTable OBJECT-TYPE
	SYNTAX  SEQUENCE OF AxrFlowResourcesEntry
	ACCESS  not-accessible
	STATUS  mandatory
	DESCRIPTION
		"Information of FlowResources table."
	::= { axrFlowResources 7 }

axrFlowResourcesEntry OBJECT-TYPE
	SYNTAX  AxrFlowResourcesEntry
	ACCESS  not-accessible
	STATUS  mandatory
	DESCRIPTION
		"Entry of FlowResources."
	INDEX {
		axrFlowResourcesIndex
	}
	::= { axrFlowResourcesTable 1 }
	AxrFlowResourcesEntry ::= 
	    SEQUENCE {
		axrFlowResourcesIndex
			INTEGER,
		axrFlowResourcesFilterUsed
        	INTEGER,
		axrFlowResourcesFilterFree
        	INTEGER,
		axrFlowResourcesQosUsed
        	INTEGER,
		axrFlowResourcesNetflowUsed
        	INTEGER,
		axrFlowResourcesQosFree
        	INTEGER,
		axrFlowResourcesUpcUsed
        	INTEGER,
		axrFlowResourcesUpcFree
        	INTEGER,
		axrFlowResourcesPolicyUsed
        	INTEGER,
        axrFlowResourcesPolicyMplsUsed
            INTEGER
        }

axrFlowResourcesIndex OBJECT-TYPE
	SYNTAX  INTEGER
	ACCESS  not-accessible
	STATUS  mandatory
	DESCRIPTION
		"Indicates place information of the slot with PRU which ident
		ifies this table entries. "
	::= { axrFlowResourcesEntry 1 }

axrFlowResourcesFilterUsed OBJECT-TYPE
	SYNTAX  INTEGER
	ACCESS  read-only
	STATUS  mandatory
	DESCRIPTION
		"The number of entries used for flow filter function per PRU.
		"
	::= { axrFlowResourcesEntry 2 }

axrFlowResourcesFilterFree OBJECT-TYPE
	SYNTAX  INTEGER
	ACCESS  read-only
	STATUS  mandatory
	DESCRIPTION
		"The number of entries usable for flow filter function per PR
		U."
	::= { axrFlowResourcesEntry 3 }

axrFlowResourcesQosUsed OBJECT-TYPE
	SYNTAX  INTEGER
	ACCESS  read-only
	STATUS  mandatory
	DESCRIPTION
		"The number of entries used for flow QoS functions per PRU."
	::= { axrFlowResourcesEntry 4 }

axrFlowResourcesNetflowUsed OBJECT-TYPE
	SYNTAX  INTEGER
	ACCESS  read-only
	STATUS  mandatory
	DESCRIPTION
		"The number of entries used for NetFlow statistics informatio
		n per PRU."
	::= { axrFlowResourcesEntry 5 }

axrFlowResourcesQosFree OBJECT-TYPE
	SYNTAX  INTEGER
	ACCESS  read-only
	STATUS  mandatory
	DESCRIPTION
		"The number of empty entries usable for flow QoS function, Ne
		tFlow statistics information function per PRU."
	::= { axrFlowResourcesEntry 6 }

axrFlowResourcesUpcUsed OBJECT-TYPE
	SYNTAX  INTEGER
	ACCESS  read-only
	STATUS  mandatory
	DESCRIPTION
		"The number of entries used for UPC per PRU."
	::= { axrFlowResourcesEntry 7 }

axrFlowResourcesUpcFree OBJECT-TYPE
	SYNTAX  INTEGER
	ACCESS  read-only
	STATUS  mandatory
	DESCRIPTION
		"The number of empty entries usable for UPC per PRU."
	::= { axrFlowResourcesEntry 8 }

axrFlowResourcesPolicyUsed OBJECT-TYPE
	SYNTAX  INTEGER
	ACCESS  read-only
	STATUS  mandatory
	DESCRIPTION
		"The number of entries used for policy routing function per P
		RU."
	::= { axrFlowResourcesEntry 9 }

axrFlowResourcesPolicyMplsUsed OBJECT-TYPE
	SYNTAX  INTEGER
	ACCESS  read-only
	STATUS  mandatory
	DESCRIPTION
		"The number of entries used for MPLS policy routing function per P
		RU."
	::= { axrFlowResourcesEntry 10 }

axrFlowResourcesFilterInterfaceInTable OBJECT-TYPE
	SYNTAX  SEQUENCE OF AxrFlowResourcesFilterInterfaceInEntry
	ACCESS  not-accessible
	STATUS  mandatory
	DESCRIPTION
		"Information of Resources table of flow filter function per i
		nterface or physical port.(Inbound)"
	::= { axrFlowResources 8 }

axrFlowResourcesFilterInterfaceInEntry OBJECT-TYPE
	SYNTAX  AxrFlowResourcesFilterInterfaceInEntry
	ACCESS  not-accessible
	STATUS  mandatory
	DESCRIPTION
		"Entry of FlowResourcesFilterInterface."
	INDEX {
		axrFlowResourcesFilterInterfaceInifIndex,
		axrFlowResourcesFilterInterfaceInifIndexType
	}
	::= { axrFlowResourcesFilterInterfaceInTable 1 }
	AxrFlowResourcesFilterInterfaceInEntry ::= 
	    SEQUENCE {
		axrFlowResourcesFilterInterfaceInifIndex
			INTEGER,
		axrFlowResourcesFilterInterfaceInifIndexType
        	INTEGER,
		axrFlowResourcesFilterInterfaceInUsed
        	INTEGER
        }

axrFlowResourcesFilterInterfaceInifIndex OBJECT-TYPE
	SYNTAX  INTEGER
	ACCESS  not-accessible
	STATUS  mandatory
	DESCRIPTION
		"Indicates the value of index(ifIndex) which identifies this 
		table entry."
	::= { axrFlowResourcesFilterInterfaceInEntry 1 }

axrFlowResourcesFilterInterfaceInifIndexType OBJECT-TYPE
	SYNTAX  INTEGER
	ACCESS  not-accessible
	STATUS  mandatory
	DESCRIPTION
		"Indicates interface type.Physical port number : 1Interface n
		ame : 2"
	::= { axrFlowResourcesFilterInterfaceInEntry 2 }

axrFlowResourcesFilterInterfaceInUsed OBJECT-TYPE
	SYNTAX  INTEGER
	ACCESS  read-only
	STATUS  mandatory
	DESCRIPTION
		"The number of entries used for flow filter function per inte
		rface or physical port."
	::= { axrFlowResourcesFilterInterfaceInEntry 3 }

axrFlowResourcesFilterInterfaceOutTable OBJECT-TYPE
	SYNTAX  SEQUENCE OF AxrFlowResourcesFilterInterfaceOutEntry
	ACCESS  not-accessible
	STATUS  mandatory
	DESCRIPTION
		"Information of Resources table of flow filter function per i
		nterface or physical port.(Outbound)"
	::= { axrFlowResources 9 }

axrFlowResourcesFilterInterfaceOutEntry OBJECT-TYPE
	SYNTAX  AxrFlowResourcesFilterInterfaceOutEntry
	ACCESS  not-accessible
	STATUS  mandatory
	DESCRIPTION
		"Entry of FlowResourcesFilterInterface."
	INDEX {
		axrFlowResourcesFilterInterfaceOutifIndex,
		axrFlowResourcesFilterInterfaceOutifIndexType
	}
	::= { axrFlowResourcesFilterInterfaceOutTable 1 }
	AxrFlowResourcesFilterInterfaceOutEntry ::= 
	    SEQUENCE {
		axrFlowResourcesFilterInterfaceOutifIndex
			INTEGER,
		axrFlowResourcesFilterInterfaceOutifIndexType
        	INTEGER,
		axrFlowResourcesFilterInterfaceOutUsed
        	INTEGER
        }

axrFlowResourcesFilterInterfaceOutifIndex OBJECT-TYPE
	SYNTAX  INTEGER
	ACCESS  not-accessible
	STATUS  mandatory
	DESCRIPTION
		"Indicates the value of index(ifIndex) which identifies this 
		table entry."
	::= { axrFlowResourcesFilterInterfaceOutEntry 1 }

axrFlowResourcesFilterInterfaceOutifIndexType OBJECT-TYPE
	SYNTAX  INTEGER
	ACCESS  not-accessible
	STATUS  mandatory
	DESCRIPTION
		"Indicates interface type.Physical port number : 1Interface n
		ame : 2"
	::= { axrFlowResourcesFilterInterfaceOutEntry 2 }

axrFlowResourcesFilterInterfaceOutUsed OBJECT-TYPE
	SYNTAX  INTEGER
	ACCESS  read-only
	STATUS  mandatory
	DESCRIPTION
		"The number of entries used for flow filter function per inte
		rface or physical port."
	::= { axrFlowResourcesFilterInterfaceOutEntry 3 }

axrFlowResourcesQosInterfaceInTable OBJECT-TYPE
	SYNTAX  SEQUENCE OF AxrFlowResourcesQosInterfaceInEntry
	ACCESS  not-accessible
	STATUS  mandatory
	DESCRIPTION
		"Information of Resources table of flow QoS function per inte
		rface or physical port.(Inbound)"
	::= { axrFlowResources 10 }

axrFlowResourcesQosInterfaceInEntry OBJECT-TYPE
	SYNTAX  AxrFlowResourcesQosInterfaceInEntry
	ACCESS  not-accessible
	STATUS  mandatory
	DESCRIPTION
		"Entry of FlowResourcesQosInterface."
	INDEX {
		axrFlowResourcesQosInterfaceInifIndex,
		axrFlowResourcesQosInterfaceInifIndexType
	}
	::= { axrFlowResourcesQosInterfaceInTable 1 }
	AxrFlowResourcesQosInterfaceInEntry ::= 
	    SEQUENCE {
		axrFlowResourcesQosInterfaceInifIndex
			INTEGER,
		axrFlowResourcesQosInterfaceInifIndexType
        	INTEGER,
		axrFlowResourcesQosInterfaceInUsed
        	INTEGER
        }

axrFlowResourcesQosInterfaceInifIndex OBJECT-TYPE
	SYNTAX  INTEGER
	ACCESS  not-accessible
	STATUS  mandatory
	DESCRIPTION
		"Indicates the value of index(ifIndex) which identifies this 
		table entry."
	::= { axrFlowResourcesQosInterfaceInEntry 1 }

axrFlowResourcesQosInterfaceInifIndexType OBJECT-TYPE
	SYNTAX  INTEGER
	ACCESS  not-accessible
	STATUS  mandatory
	DESCRIPTION
		"Indicates interface type.Physical port number : 1Interface n
		ame : 2"
	::= { axrFlowResourcesQosInterfaceInEntry 2 }

axrFlowResourcesQosInterfaceInUsed OBJECT-TYPE
	SYNTAX  INTEGER
	ACCESS  read-only
	STATUS  mandatory
	DESCRIPTION
		"The number of entries used for flow QoS function per inte
		rface or physical port."
	::= { axrFlowResourcesQosInterfaceInEntry 3 }

axrFlowResourcesQosInterfaceOutTable OBJECT-TYPE
	SYNTAX  SEQUENCE OF AxrFlowResourcesQosInterfaceOutEntry
	ACCESS  not-accessible
	STATUS  mandatory
	DESCRIPTION
		"Information of Resources table of flow QoS function per inte
		rface or physical port.(Outbound)"
	::= { axrFlowResources 11 }

axrFlowResourcesQosInterfaceOutEntry OBJECT-TYPE
	SYNTAX  AxrFlowResourcesQosInterfaceOutEntry
	ACCESS  not-accessible
	STATUS  mandatory
	DESCRIPTION
		"Entry of FlowResourcesQosInterface."
	INDEX {
		axrFlowResourcesQosInterfaceOutifIndex,
		axrFlowResourcesQosInterfaceOutifIndexType
	}
	::= { axrFlowResourcesQosInterfaceOutTable 1 }
	AxrFlowResourcesQosInterfaceOutEntry ::= 
	    SEQUENCE {
		axrFlowResourcesQosInterfaceOutifIndex
			INTEGER,
		axrFlowResourcesQosInterfaceOutifIndexType
        	INTEGER,
		axrFlowResourcesQosInterfaceOutUsed
        	INTEGER
        }

axrFlowResourcesQosInterfaceOutifIndex OBJECT-TYPE
	SYNTAX  INTEGER
	ACCESS  not-accessible
	STATUS  mandatory
	DESCRIPTION
		"Indicates the value of index(ifIndex) which identifies this 
		table entry."
	::= { axrFlowResourcesQosInterfaceOutEntry 1 }

axrFlowResourcesQosInterfaceOutifIndexType OBJECT-TYPE
	SYNTAX  INTEGER
	ACCESS  not-accessible
	STATUS  mandatory
	DESCRIPTION
		"Indicates interface type.Physical port number : 1Interface n
		ame : 2"
	::= { axrFlowResourcesQosInterfaceOutEntry 2 }

axrFlowResourcesQosInterfaceOutUsed OBJECT-TYPE
	SYNTAX  INTEGER
	ACCESS  read-only
	STATUS  mandatory
	DESCRIPTION
		"The number of entries used for flow filter function per inte
		rface or physical port."
	::= { axrFlowResourcesQosInterfaceOutEntry 3 }

axrFlowResourcesFilterListInTable OBJECT-TYPE
	SYNTAX  SEQUENCE OF AxrFlowResourcesFilterListInEntry
	ACCESS  not-accessible
	STATUS  mandatory
	DESCRIPTION
		"Information of Resources table of flow filter function per l
		ist.(Inbound)"
	::= { axrFlowResources 12 }

axrFlowResourcesFilterListInEntry OBJECT-TYPE
	SYNTAX  AxrFlowResourcesFilterListInEntry
	ACCESS  not-accessible
	STATUS  mandatory
	DESCRIPTION
		"Entry of FlowResourcesFilterList."
	INDEX {
		axrFlowResourcesFilterListInifIndex,
		axrFlowResourcesFilterListInifIndexType,
		axrFlowResourcesFilterListInNumber
	}
	::= { axrFlowResourcesFilterListInTable 1 }
	AxrFlowResourcesFilterListInEntry ::= 
	    SEQUENCE {
		axrFlowResourcesFilterListInifIndex
			INTEGER,
		axrFlowResourcesFilterListInifIndexType
        	INTEGER,
		axrFlowResourcesFilterListInNumber
        	INTEGER,
		axrFlowResourcesFilterListInUsed
        	INTEGER
        }

axrFlowResourcesFilterListInifIndex OBJECT-TYPE
	SYNTAX  INTEGER
	ACCESS  not-accessible
	STATUS  mandatory
	DESCRIPTION
		"Indicates the value of index(ifIndex) which identifies this 
		table entry."
	::= { axrFlowResourcesFilterListInEntry 1 }

axrFlowResourcesFilterListInifIndexType OBJECT-TYPE
	SYNTAX  INTEGER
	ACCESS  not-accessible
	STATUS  mandatory
	DESCRIPTION
		"Indicates interface type.Physical port number : 1Interface n
		ame : 2"
	::= { axrFlowResourcesFilterListInEntry 2 }

axrFlowResourcesFilterListInNumber OBJECT-TYPE
	SYNTAX  INTEGER
	ACCESS  not-accessible
	STATUS  mandatory
	DESCRIPTION
		"Indicates the value of index(list number) which identifies t
		his table entry."
	::= { axrFlowResourcesFilterListInEntry 3 }

axrFlowResourcesFilterListInUsed OBJECT-TYPE
	SYNTAX  INTEGER
	ACCESS  read-only
	STATUS  mandatory
	DESCRIPTION
		"The number of entries used for flow filter function per list
		."
	::= { axrFlowResourcesFilterListInEntry 4 }

axrFlowResourcesFilterListOutTable OBJECT-TYPE
	SYNTAX  SEQUENCE OF AxrFlowResourcesFilterListOutEntry
	ACCESS  not-accessible
	STATUS  mandatory
	DESCRIPTION
		"Information of Resources table of flow filter function per l
		ist.(Outbound)"
	::= { axrFlowResources 13 }

axrFlowResourcesFilterListOutEntry OBJECT-TYPE
	SYNTAX  AxrFlowResourcesFilterListOutEntry
	ACCESS  not-accessible
	STATUS  mandatory
	DESCRIPTION
		"Entry of FlowResourcesFilterList."
	INDEX {
		axrFlowResourcesFilterListOutifIndex,
		axrFlowResourcesFilterListOutifIndexType,
		axrFlowResourcesFilterListOutNumber
	}
	::= { axrFlowResourcesFilterListOutTable 1 }
	AxrFlowResourcesFilterListOutEntry ::= 
	    SEQUENCE {
		axrFlowResourcesFilterListOutifIndex
			INTEGER,
		axrFlowResourcesFilterListOutifIndexType
        	INTEGER,
		axrFlowResourcesFilterListOutNumber
        	INTEGER,
		axrFlowResourcesFilterListOutUsed
        	INTEGER
        }

axrFlowResourcesFilterListOutifIndex OBJECT-TYPE
	SYNTAX  INTEGER
	ACCESS  not-accessible
	STATUS  mandatory
	DESCRIPTION
		"Indicates the value of index(ifIndex) which identifies this 
		table entry."
	::= { axrFlowResourcesFilterListOutEntry 1 }

axrFlowResourcesFilterListOutifIndexType OBJECT-TYPE
	SYNTAX  INTEGER
	ACCESS  not-accessible
	STATUS  mandatory
	DESCRIPTION
		"Indicates interface type.Physical port number : 1Interface n
		ame : 2"
	::= { axrFlowResourcesFilterListOutEntry 2 }

axrFlowResourcesFilterListOutNumber OBJECT-TYPE
	SYNTAX  INTEGER
	ACCESS  not-accessible
	STATUS  mandatory
	DESCRIPTION
		"Indicates the value of index(list number) which identifies t
		his table entry."
	::= { axrFlowResourcesFilterListOutEntry 3 }

axrFlowResourcesFilterListOutUsed OBJECT-TYPE
	SYNTAX  INTEGER
	ACCESS  read-only
	STATUS  mandatory
	DESCRIPTION
		"The number of entries used for flow filter function per list
		."
	::= { axrFlowResourcesFilterListOutEntry 4 }

axrFlowResourcesQosListInTable OBJECT-TYPE
	SYNTAX  SEQUENCE OF AxrFlowResourcesQosListInEntry
	ACCESS  not-accessible
	STATUS  mandatory
	DESCRIPTION
		"Information of Resources table of flow QoS function per list
		.(Inbound)"
	::= { axrFlowResources 14 }

axrFlowResourcesQosListInEntry OBJECT-TYPE
	SYNTAX  AxrFlowResourcesQosListInEntry
	ACCESS  not-accessible
	STATUS  mandatory
	DESCRIPTION
		"Entry of FlowResourcesQoSList."
	INDEX {
		axrFlowResourcesQosListInifIndex,
		axrFlowResourcesQosListInifIndexType,
		axrFlowResourcesQosListInNumber
	}
	::= { axrFlowResourcesQosListInTable 1 }
	AxrFlowResourcesQosListInEntry ::= 
	    SEQUENCE {
		axrFlowResourcesQosListInifIndex
			INTEGER,
		axrFlowResourcesQosListInifIndexType
        	INTEGER,
		axrFlowResourcesQosListInNumber
        	INTEGER,
		axrFlowResourcesQosListInUsed
        	INTEGER
        }

axrFlowResourcesQosListInifIndex OBJECT-TYPE
	SYNTAX  INTEGER
	ACCESS  not-accessible
	STATUS  mandatory
	DESCRIPTION
		"Indicates the value of index(ifIndex) which identifies this 
		table entry."
	::= { axrFlowResourcesQosListInEntry 1 }

axrFlowResourcesQosListInifIndexType OBJECT-TYPE
	SYNTAX  INTEGER
	ACCESS  not-accessible
	STATUS  mandatory
	DESCRIPTION
		"Indicates interface type.Physical port number : 1Interface n
		ame : 2"
	::= { axrFlowResourcesQosListInEntry 2 }

axrFlowResourcesQosListInNumber OBJECT-TYPE
	SYNTAX  INTEGER
	ACCESS  not-accessible
	STATUS  mandatory
	DESCRIPTION
		"Indicates the value of index(list number) which identifies t
		his table entry."
	::= { axrFlowResourcesQosListInEntry 3 }

axrFlowResourcesQosListInUsed OBJECT-TYPE
	SYNTAX  INTEGER
	ACCESS  read-only
	STATUS  mandatory
	DESCRIPTION
		"The number of entries used for flow QoS function per list
		."
	::= { axrFlowResourcesQosListInEntry 4 }

axrFlowResourcesQosListOutTable OBJECT-TYPE
	SYNTAX  SEQUENCE OF AxrFlowResourcesQosListOutEntry
	ACCESS  not-accessible
	STATUS  mandatory
	DESCRIPTION
		"Information of Resources table of flow QoS function per list
		.(Outbound)"
	::= { axrFlowResources 15 }

axrFlowResourcesQosListOutEntry OBJECT-TYPE
	SYNTAX  AxrFlowResourcesQosListOutEntry
	ACCESS  not-accessible
	STATUS  mandatory
	DESCRIPTION
		"Entry of FlowResourcesQoSList."
	INDEX {
		axrFlowResourcesQosListOutifIndex,
		axrFlowResourcesQosListOutifIndexType,
		axrFlowResourcesQosListOutNumber
	}
	::= { axrFlowResourcesQosListOutTable 1 }
	AxrFlowResourcesQosListOutEntry ::= 
	    SEQUENCE {
		axrFlowResourcesQosListOutifIndex
			INTEGER,
		axrFlowResourcesQosListOutifIndexType
        	INTEGER,
		axrFlowResourcesQosListOutNumber
        	INTEGER,
		axrFlowResourcesQosListOutUsed
        	INTEGER
        }

axrFlowResourcesQosListOutifIndex OBJECT-TYPE
	SYNTAX  INTEGER
	ACCESS  not-accessible
	STATUS  mandatory
	DESCRIPTION
		"Indicates the value of index(ifIndex) which identifies this 
		table entry."
	::= { axrFlowResourcesQosListOutEntry 1 }

axrFlowResourcesQosListOutifIndexType OBJECT-TYPE
	SYNTAX  INTEGER
	ACCESS  not-accessible
	STATUS  mandatory
	DESCRIPTION
		"Indicates interface type.Physical port number : 1Interface n
		ame : 2"
	::= { axrFlowResourcesQosListOutEntry 2 }

axrFlowResourcesQosListOutNumber OBJECT-TYPE
	SYNTAX  INTEGER
	ACCESS  not-accessible
	STATUS  mandatory
	DESCRIPTION
		"Indicates the value of index(list number) which identifies t
		his table entry."
	::= { axrFlowResourcesQosListOutEntry 3 }

axrFlowResourcesQosListOutUsed OBJECT-TYPE
	SYNTAX  INTEGER
	ACCESS  read-only
	STATUS  mandatory
	DESCRIPTION
		"The number of entries used for flow QoS function per list
		."
	::= { axrFlowResourcesQosListOutEntry 4 }

axrFlowResourcesSystemPolicyMplsUsed OBJECT-TYPE
        SYNTAX  INTEGER
        ACCESS  read-only
        STATUS  mandatory
        DESCRIPTION
                "The number of entries used for MPLS policy routing function 
                per device."
        ::= { axrFlowResources 16 }
        
axrFlowResourcesSystemPolicyMplsMax OBJECT-TYPE
        SYNTAX  INTEGER
        ACCESS  read-only
        STATUS  mandatory
        DESCRIPTION
                "The maximum number of entries usable for MPLS policy routin
                g function per device."
        ::= { axrFlowResources 17 }

axrFlowFilterInTable OBJECT-TYPE
	SYNTAX  SEQUENCE OF AxrFlowFilterInEntry
	ACCESS  not-accessible
	STATUS  mandatory
	DESCRIPTION
		"Information of flow filter detection condition table.(Inboun
		d)"
	::= { axrFlowFilter 1 }

axrFlowFilterInEntry OBJECT-TYPE
	SYNTAX  AxrFlowFilterInEntry
	ACCESS  not-accessible
	STATUS  mandatory
	DESCRIPTION
		"Entry of flow filter detection condition."
	INDEX {
		axrFlowFilterInifIndex,
		axrFlowFilterInifIndexType,
		axrFlowFilterInListNumber
	}
	::= { axrFlowFilterInTable 1 }
	AxrFlowFilterInEntry ::= 
	    SEQUENCE {
		axrFlowFilterInifIndex
			INTEGER,
		axrFlowFilterInifIndexType
        	INTEGER,
		axrFlowFilterInListNumber
        	INTEGER,
		axrFlowFilterInSrcMacOp
        	INTEGER,
		axrFlowFilterInSrcMac
        	MacAddress,
		axrFlowFilterInSrcMacMask
        	MacAddress,
		axrFlowFilterInDestMacOp
        	INTEGER,
		axrFlowFilterInDestMac
        	MacAddress,
		axrFlowFilterInDestMacMask
        	MacAddress,
		axrFlowFilterInEthernetType
        	OCTET STRING,
		axrFlowFilterInUserPriority
        	INTEGER,
		axrFlowFilterInLowerVlanList
        	OCTET STRING,
		axrFlowFilterInHigherVlanList
        	OCTET STRING,
		axrFlowFilterInProtocolNumber
        	INTEGER,
		axrFlowFilterInIpAddrType
        	InetAddressType,
		axrFlowFilterInSrcIpOp
        	INTEGER,
		axrFlowFilterInSrcIp
        	InetAddress,
		axrFlowFilterInSrcIpLength
        	INTEGER,
		axrFlowFilterInSrcIpRange
        	InetAddress,
		axrFlowFilterInDestIpOp
        	INTEGER,
		axrFlowFilterInDestIp
        	InetAddress,
		axrFlowFilterInDestIpLength
        	INTEGER,
		axrFlowFilterInDestIpRange
        	InetAddress,
		axrFlowFilterInDscp
        	INTEGER,
		axrFlowFilterInPrecedence
        	INTEGER,
		axrFlowFilterInUpperLength
        	INTEGER,
		axrFlowFilterInLowerLength
        	INTEGER,
		axrFlowFilterInFragments
        	INTEGER,
		axrFlowFilterInSrcPortOp
        	INTEGER,
		axrFlowFilterInSrcPort
        	INTEGER,
		axrFlowFilterInSrcPortRange
        	INTEGER,
		axrFlowFilterInDestPortOp
        	INTEGER,
		axrFlowFilterInDestPort
        	INTEGER,
		axrFlowFilterInDestPortRange
        	INTEGER,
		axrFlowFilterInAckFlag
        	INTEGER,
		axrFlowFilterInSynFlag
        	INTEGER,
		axrFlowFilterInIcmpType
        	INTEGER,
		axrFlowFilterInIcmpCode
        	INTEGER,
		axrFlowFilterInIgmpType
        	INTEGER,
		axrFlowFilterInLabelOp
			INTEGER,
		axrFlowFilterInLabel
			INTEGER,
		axrFlowFilterInExp
			INTEGER,
		axrFlowFilterInSrcIpMask
			InetAddress,
		axrFlowFilterInDestIpMask
			InetAddress
        }

axrFlowFilterInifIndex OBJECT-TYPE
	SYNTAX  INTEGER
	ACCESS  not-accessible
	STATUS  mandatory
	DESCRIPTION
		"Indicates the value of index(ifIndex) which identifies this 
		table entry."
	::= { axrFlowFilterInEntry 1 }

axrFlowFilterInifIndexType OBJECT-TYPE
	SYNTAX  INTEGER
	ACCESS  not-accessible
	STATUS  mandatory
	DESCRIPTION
		"Indicates interface type.Physical port number : 1Interface n
		ame : 2(2)fixed."
	::= { axrFlowFilterInEntry 2 }

axrFlowFilterInListNumber OBJECT-TYPE
	SYNTAX  INTEGER
	ACCESS  not-accessible
	STATUS  mandatory
	DESCRIPTION
		"Indicates the value of index(list number) which identifies t
		his table entry."
	::= { axrFlowFilterInEntry 3 }

axrFlowFilterInSrcMacOp OBJECT-TYPE
	SYNTAX  INTEGER
	ACCESS  read-only
	STATUS  mandatory
	DESCRIPTION
		"Indicates specification method of source MAC address on dete
		ction condition."
	::= { axrFlowFilterInEntry 4 }

axrFlowFilterInSrcMac OBJECT-TYPE
	SYNTAX  MacAddress
	ACCESS  read-only
	STATUS  mandatory
	DESCRIPTION
		"Indicates source MAC address on detection condition."
	::= { axrFlowFilterInEntry 5 }

axrFlowFilterInSrcMacMask OBJECT-TYPE
	SYNTAX  MacAddress
	ACCESS  read-only
	STATUS  mandatory
	DESCRIPTION
		"Indicates mask of source MAC address on detection specificat
		ion."
	::= { axrFlowFilterInEntry 6 }

axrFlowFilterInDestMacOp OBJECT-TYPE
	SYNTAX  INTEGER
	ACCESS  read-only
	STATUS  mandatory
	DESCRIPTION
		"Indicates specification method of destination MAC address on
		 detection condition."
	::= { axrFlowFilterInEntry 7 }

axrFlowFilterInDestMac OBJECT-TYPE
	SYNTAX  MacAddress
	ACCESS  read-only
	STATUS  mandatory
	DESCRIPTION
		"Indicates destination MAC address on detection condition."
	::= { axrFlowFilterInEntry 8 }

axrFlowFilterInDestMacMask OBJECT-TYPE
	SYNTAX  MacAddress
	ACCESS  read-only
	STATUS  mandatory
	DESCRIPTION
		"Indicates mask of destination MAC address on detection speci
		fication."
	::= { axrFlowFilterInEntry 9 }

axrFlowFilterInEthernetType OBJECT-TYPE
	SYNTAX  OCTET STRING
	ACCESS  read-only
	STATUS  mandatory
	DESCRIPTION
		"Indicates type of ethernet V2 and IEEE802.3 SNAP/RFC1042 for
		m on detection condition."
	::= { axrFlowFilterInEntry 10 }

axrFlowFilterInUserPriority OBJECT-TYPE
	SYNTAX  INTEGER
	ACCESS  read-only
	STATUS  mandatory
	DESCRIPTION
		"Indicates user priority in Tag-VLAN on detection condition."
	::= { axrFlowFilterInEntry 11 }

axrFlowFilterInLowerVlanList OBJECT-TYPE
	SYNTAX  OCTET STRING
	ACCESS  read-only
	STATUS  mandatory
	DESCRIPTION
		"Bit map representation of VLAN ID on detection condition.(He
		ad 1 bit indicates existence of untagged definition, and the 
		rest effective or non-effective of VLAN 1-2047.)"
	::= { axrFlowFilterInEntry 12 }

axrFlowFilterInHigherVlanList OBJECT-TYPE
	SYNTAX  OCTET STRING
	ACCESS  read-only
	STATUS  mandatory
	DESCRIPTION
		"Bit map representation of VLAN ID on detection condition.(Ea
		ch bit indicates whether VLAN 2048-4095 is effective or non-e
		ffective in order.)"
	::= { axrFlowFilterInEntry 13 }

axrFlowFilterInProtocolNumber OBJECT-TYPE
	SYNTAX  INTEGER
	ACCESS  read-only
	STATUS  mandatory
	DESCRIPTION
		"Indicates upper protocol number on detection condition."
	::= { axrFlowFilterInEntry 14 }

axrFlowFilterInIpAddrType OBJECT-TYPE
	SYNTAX  InetAddressType
	ACCESS  read-only
	STATUS  mandatory
	DESCRIPTION
		"Indicates IP address type which is shown."
	::= { axrFlowFilterInEntry 15 }

axrFlowFilterInSrcIpOp OBJECT-TYPE
	SYNTAX  INTEGER
	ACCESS  read-only
	STATUS  mandatory
	DESCRIPTION
		"Indicates specification method of source IP address on detec
		tion condition."
	::= { axrFlowFilterInEntry 16 }

axrFlowFilterInSrcIp OBJECT-TYPE
	SYNTAX  InetAddress
	ACCESS  read-only
	STATUS  mandatory
	DESCRIPTION
		"Indicates source IP address on detection condition."
	::= { axrFlowFilterInEntry 17 }

axrFlowFilterInSrcIpLength OBJECT-TYPE
	SYNTAX  INTEGER
	ACCESS  read-only
	STATUS  mandatory
	DESCRIPTION
		"Indicates subnet mask length(ipv4) or prefix length(ipv6) of
		 source IP address on detection condition."
	::= { axrFlowFilterInEntry 18 }

axrFlowFilterInSrcIpRange OBJECT-TYPE
	SYNTAX  InetAddress
	ACCESS  read-only
	STATUS  mandatory
	DESCRIPTION
		"Source IP address in range specified by detection condition.
		(maximum IP address)"
	::= { axrFlowFilterInEntry 19 }

axrFlowFilterInDestIpOp OBJECT-TYPE
	SYNTAX  INTEGER
	ACCESS  read-only
	STATUS  mandatory
	DESCRIPTION
		"Indicates specification method of destination IP address on 
		detection condition."
	::= { axrFlowFilterInEntry 20 }

axrFlowFilterInDestIp OBJECT-TYPE
	SYNTAX  InetAddress
	ACCESS  read-only
	STATUS  mandatory
	DESCRIPTION
		"Indicates destination IP address on detection condition."
	::= { axrFlowFilterInEntry 21 }

axrFlowFilterInDestIpLength OBJECT-TYPE
	SYNTAX  INTEGER
	ACCESS  read-only
	STATUS  mandatory
	DESCRIPTION
		"Indicates subnet mask length(ipv4) or prefix length(ipv6) of
		 destination IP address on detection condition."
	::= { axrFlowFilterInEntry 22 }

axrFlowFilterInDestIpRange OBJECT-TYPE
	SYNTAX  InetAddress
	ACCESS  read-only
	STATUS  mandatory
	DESCRIPTION
		"Destination IP address in range specified by detection condi
		tion.(maximum IP address)"
	::= { axrFlowFilterInEntry 23 }

axrFlowFilterInDscp OBJECT-TYPE
	SYNTAX  INTEGER
	ACCESS  read-only
	STATUS  mandatory
	DESCRIPTION
		"The value of DSCP on detection condition."
	::= { axrFlowFilterInEntry 24 }

axrFlowFilterInPrecedence OBJECT-TYPE
	SYNTAX  INTEGER
	ACCESS  read-only
	STATUS  mandatory
	DESCRIPTION
		"The value of precedence on detection condition."
	::= { axrFlowFilterInEntry 25 }

axrFlowFilterInUpperLength OBJECT-TYPE
	SYNTAX  INTEGER
	ACCESS  read-only
	STATUS  mandatory
	DESCRIPTION
		"The upper limit of IP user data length on detection conditio
		n. "
	::= { axrFlowFilterInEntry 26 }

axrFlowFilterInLowerLength OBJECT-TYPE
	SYNTAX  INTEGER
	ACCESS  read-only
	STATUS  mandatory
	DESCRIPTION
		"The lower limit of IP user data length on detection conditio
		n."
	::= { axrFlowFilterInEntry 27 }

axrFlowFilterInFragments OBJECT-TYPE
	SYNTAX  INTEGER
	ACCESS  read-only
	STATUS  mandatory
	DESCRIPTION
		"Indicates whether 2nd fragment packet or later are included 
		in detection condition."
	::= { axrFlowFilterInEntry 28 }

axrFlowFilterInSrcPortOp OBJECT-TYPE
	SYNTAX  INTEGER
	ACCESS  read-only
	STATUS  mandatory
	DESCRIPTION
		"Indicates specification method of source port number on dete
		ction condition."
	::= { axrFlowFilterInEntry 29 }

axrFlowFilterInSrcPort OBJECT-TYPE
	SYNTAX  INTEGER
	ACCESS  read-only
	STATUS  mandatory
	DESCRIPTION
		"Indicates source port number on detection condition."
	::= { axrFlowFilterInEntry 30 }

axrFlowFilterInSrcPortRange OBJECT-TYPE
	SYNTAX  INTEGER
	ACCESS  read-only
	STATUS  mandatory
	DESCRIPTION
		"Source port number in range specified by detection condition
		.(maximum port number)"
	::= { axrFlowFilterInEntry 31 }

axrFlowFilterInDestPortOp OBJECT-TYPE
	SYNTAX  INTEGER
	ACCESS  read-only
	STATUS  mandatory
	DESCRIPTION
		"Indicates specification method of destination port number on
		 detection condition."
	::= { axrFlowFilterInEntry 32 }

axrFlowFilterInDestPort OBJECT-TYPE
	SYNTAX  INTEGER
	ACCESS  read-only
	STATUS  mandatory
	DESCRIPTION
		"Indicates destination port number on detection condition."
	::= { axrFlowFilterInEntry 33 }

axrFlowFilterInDestPortRange OBJECT-TYPE
	SYNTAX  INTEGER
	ACCESS  read-only
	STATUS  mandatory
	DESCRIPTION
		"destination port number in range specified by detection cond
		ition.(maximum port number)"
	::= { axrFlowFilterInEntry 34 }

axrFlowFilterInAckFlag OBJECT-TYPE
	SYNTAX  INTEGER
	ACCESS  read-only
	STATUS  mandatory
	DESCRIPTION
		"Indicates whether TCP one-way communication permission is in
		cluded in detection condition or not."
	::= { axrFlowFilterInEntry 35 }

axrFlowFilterInSynFlag OBJECT-TYPE
	SYNTAX  INTEGER
	ACCESS  read-only
	STATUS  mandatory
	DESCRIPTION
		"Indicates whether virtual circuit link-up permission is incl
		uded in detection condition or not."
	::= { axrFlowFilterInEntry 36 }

axrFlowFilterInIcmpType OBJECT-TYPE
	SYNTAX  INTEGER
	ACCESS  read-only
	STATUS  mandatory
	DESCRIPTION
		"Indicates ICMP or ICMPv6 type on detection condition."
	::= { axrFlowFilterInEntry 37 }

axrFlowFilterInIcmpCode OBJECT-TYPE
	SYNTAX  INTEGER
	ACCESS  read-only
	STATUS  mandatory
	DESCRIPTION
		"Indicates ICMP or ICMPv6 code on detection condition."
	::= { axrFlowFilterInEntry 38 }

axrFlowFilterInIgmpType OBJECT-TYPE
	SYNTAX  INTEGER
	ACCESS  read-only
	STATUS  mandatory
	DESCRIPTION
		"Indicates IGMP type on detection condition."
	::= { axrFlowFilterInEntry 39 }

axrFlowFilterInLabelOp OBJECT-TYPE
	SYNTAX  INTEGER
	ACCESS  read-only
	STATUS  mandatory 
	DESCRIPTION
		"Indicate the way to specify the label value on shim-header on detection condition."
	::= { axrFlowFilterInEntry 40 }

axrFlowFilterInLabel OBJECT-TYPE
	SYNTAX  INTEGER
	ACCESS  read-only
	STATUS  mandatory
	DESCRIPTION
		"The label value in shim-header on detection condition"
	::= { axrFlowFilterInEntry 41 }

axrFlowFilterInExp OBJECT-TYPE
	SYNTAX  INTEGER
	ACCESS  read-only
	STATUS  mandatory
	DESCRIPTION
		"The EXP value in shim-header on detection condition"
	::= { axrFlowFilterInEntry 42 }

axrFlowFilterInSrcIpMask OBJECT-TYPE
	SYNTAX  InetAddress
	ACCESS  read-only
	STATUS  mandatory
	DESCRIPTION
		"Indicates mask of source IP address on detection specificat
		ion."
	::= { axrFlowFilterInEntry 43}

axrFlowFilterInDestIpMask OBJECT-TYPE
	SYNTAX  InetAddress
	ACCESS  read-only
	STATUS  mandatory
	DESCRIPTION
		"Indicates mask of destination IP address on detection speci
		fication."
	::= { axrFlowFilterInEntry 44 }
	
axrFlowFilterOutTable OBJECT-TYPE
	SYNTAX  SEQUENCE OF AxrFlowFilterOutEntry
	ACCESS  not-accessible
	STATUS  mandatory
	DESCRIPTION
		"Information of flow filter detection condition table.(Outbou
		nd)"
	::= { axrFlowFilter 2 }

axrFlowFilterOutEntry OBJECT-TYPE
	SYNTAX  AxrFlowFilterOutEntry
	ACCESS  not-accessible
	STATUS  mandatory
	DESCRIPTION
		"Entry of flow filter detection condition."
	INDEX {
		axrFlowFilterOutifIndex,
		axrFlowFilterOutifIndexType,
		axrFlowFilterOutListNumber
	}
	::= { axrFlowFilterOutTable 1 }
	AxrFlowFilterOutEntry ::= 
	    SEQUENCE {
		axrFlowFilterOutifIndex
			INTEGER,
		axrFlowFilterOutifIndexType
        	INTEGER,
		axrFlowFilterOutListNumber
        	INTEGER,
		axrFlowFilterOutSrcMacOp
        	INTEGER,
		axrFlowFilterOutSrcMac
        	MacAddress,
		axrFlowFilterOutSrcMacMask
        	MacAddress,
		axrFlowFilterOutDestMacOp
        	INTEGER,
		axrFlowFilterOutDestMac
        	MacAddress,
		axrFlowFilterOutDestMacMask
        	MacAddress,
		axrFlowFilterOutEthernetType
        	OCTET STRING,
		axrFlowFilterOutUserPriority
        	INTEGER,
		axrFlowFilterOutLowerVlanList
        	OCTET STRING,
		axrFlowFilterOutHigherVlanList
        	OCTET STRING,
		axrFlowFilterOutProtocolNumber
        	INTEGER,
		axrFlowFilterOutIpAddrType
        	InetAddressType,
		axrFlowFilterOutSrcIpOp
        	INTEGER,
		axrFlowFilterOutSrcIp
        	InetAddress,
		axrFlowFilterOutSrcIpLength
        	INTEGER,
		axrFlowFilterOutSrcIpRange
        	InetAddress,
		axrFlowFilterOutDestIpOp
        	INTEGER,
		axrFlowFilterOutDestIp
        	InetAddress,
		axrFlowFilterOutDestIpLength
        	INTEGER,
		axrFlowFilterOutDestIpRange
        	InetAddress,
		axrFlowFilterOutDscp
        	INTEGER,
		axrFlowFilterOutPrecedence
        	INTEGER,
		axrFlowFilterOutUpperLength
        	INTEGER,
		axrFlowFilterOutLowerLength
        	INTEGER,
		axrFlowFilterOutFragments
        	INTEGER,
		axrFlowFilterOutSrcPortOp
        	INTEGER,
		axrFlowFilterOutSrcPort
        	INTEGER,
		axrFlowFilterOutSrcPortRange
        	INTEGER,
		axrFlowFilterOutDestPortOp
        	INTEGER,
		axrFlowFilterOutDestPort
        	INTEGER,
		axrFlowFilterOutDestPortRange
        	INTEGER,
		axrFlowFilterOutAckFlag
        	INTEGER,
		axrFlowFilterOutSynFlag
        	INTEGER,
		axrFlowFilterOutIcmpType
        	INTEGER,
		axrFlowFilterOutIcmpCode
        	INTEGER,
		axrFlowFilterOutIgmpType
        	INTEGER,
		axrFlowFilterOutLabelOp
			INTEGER,
		axrFlowFilterOutLabel
			INTEGER,
		axrFlowFilterOutExp
			INTEGER,
		axrFlowFilterOutSrcIpMask
			InetAddress,
		axrFlowFilterOutDestIpMask
			InetAddress
        }

axrFlowFilterOutifIndex OBJECT-TYPE
	SYNTAX  INTEGER
	ACCESS  not-accessible
	STATUS  mandatory
	DESCRIPTION
		"Indicates the value of index(ifIndex) which identifies this 
		table entry."
	::= { axrFlowFilterOutEntry 1 }

axrFlowFilterOutifIndexType OBJECT-TYPE
	SYNTAX  INTEGER
	ACCESS  not-accessible
	STATUS  mandatory
	DESCRIPTION
		"Indicates interface type.Physical port number : 1Interface n
		ame : 2(2)fixed."
	::= { axrFlowFilterOutEntry 2 }

axrFlowFilterOutListNumber OBJECT-TYPE
	SYNTAX  INTEGER
	ACCESS  not-accessible
	STATUS  mandatory
	DESCRIPTION
		"Indicates the value of index(list number) which identifies t
		his table entry."
	::= { axrFlowFilterOutEntry 3 }

axrFlowFilterOutSrcMacOp OBJECT-TYPE
	SYNTAX  INTEGER
	ACCESS  read-only
	STATUS  mandatory
	DESCRIPTION
		"Indicates specification method of source MAC address on dete
		ction condition."
	::= { axrFlowFilterOutEntry 4 }

axrFlowFilterOutSrcMac OBJECT-TYPE
	SYNTAX  MacAddress
	ACCESS  read-only
	STATUS  mandatory
	DESCRIPTION
		"Indicates source MAC address on detection condition."
	::= { axrFlowFilterOutEntry 5 }

axrFlowFilterOutSrcMacMask OBJECT-TYPE
	SYNTAX  MacAddress
	ACCESS  read-only
	STATUS  mandatory
	DESCRIPTION
		"Indicates mask of source MAC address on detection specificat
		ion."
	::= { axrFlowFilterOutEntry 6 }

axrFlowFilterOutDestMacOp OBJECT-TYPE
	SYNTAX  INTEGER
	ACCESS  read-only
	STATUS  mandatory
	DESCRIPTION
		"Indicates specification method of destination MAC address on
		 detection condition."
	::= { axrFlowFilterOutEntry 7 }

axrFlowFilterOutDestMac OBJECT-TYPE
	SYNTAX  MacAddress
	ACCESS  read-only
	STATUS  mandatory
	DESCRIPTION
		"Indicates destination MAC address on detection condition."
	::= { axrFlowFilterOutEntry 8 }

axrFlowFilterOutDestMacMask OBJECT-TYPE
	SYNTAX  MacAddress
	ACCESS  read-only
	STATUS  mandatory
	DESCRIPTION
		"Indicates mask of destination MAC address on detection speci
		fication."
	::= { axrFlowFilterOutEntry 9 }

axrFlowFilterOutEthernetType OBJECT-TYPE
	SYNTAX  OCTET STRING
	ACCESS  read-only
	STATUS  mandatory
	DESCRIPTION
		"Indicates type of ethernet V2 and IEEE802.3 SNAP/RFC1042 for
		m on detection condition."
	::= { axrFlowFilterOutEntry 10 }

axrFlowFilterOutUserPriority OBJECT-TYPE
	SYNTAX  INTEGER
	ACCESS  read-only
	STATUS  mandatory
	DESCRIPTION
		"Indicates user priority in Tag-VLAN on detection condition."
	::= { axrFlowFilterOutEntry 11 }

axrFlowFilterOutLowerVlanList OBJECT-TYPE
	SYNTAX  OCTET STRING
	ACCESS  read-only
	STATUS  mandatory
	DESCRIPTION
		"Bit map representation of VLAN ID on detection condition.(He
		ad 1 bit indicates existence of untagged definition, and the 
		rest effective or non-effective of VLAN 1-2047.)"
	::= { axrFlowFilterOutEntry 12 }

axrFlowFilterOutHigherVlanList OBJECT-TYPE
	SYNTAX  OCTET STRING
	ACCESS  read-only
	STATUS  mandatory
	DESCRIPTION
		"Bit map representation of VLAN ID on detection condition.(Ea
		ch bit indicates whether VLAN 2048-4095 is effective or non-e
		ffective in order.)"
	::= { axrFlowFilterOutEntry 13 }

axrFlowFilterOutProtocolNumber OBJECT-TYPE
	SYNTAX  INTEGER
	ACCESS  read-only
	STATUS  mandatory
	DESCRIPTION
		"Indicates upper protocol number on detection condition."
	::= { axrFlowFilterOutEntry 14 }

axrFlowFilterOutIpAddrType OBJECT-TYPE
	SYNTAX  InetAddressType
	ACCESS  read-only
	STATUS  mandatory
	DESCRIPTION
		"Indicates IP address type which is shown."
	::= { axrFlowFilterOutEntry 15 }

axrFlowFilterOutSrcIpOp OBJECT-TYPE
	SYNTAX  INTEGER
	ACCESS  read-only
	STATUS  mandatory
	DESCRIPTION
		"Indicates specification method of source IP address on detec
		tion condition."
	::= { axrFlowFilterOutEntry 16 }

axrFlowFilterOutSrcIp OBJECT-TYPE
	SYNTAX  InetAddress
	ACCESS  read-only
	STATUS  mandatory
	DESCRIPTION
		"Indicates source IP address on detection condition."
	::= { axrFlowFilterOutEntry 17 }

axrFlowFilterOutSrcIpLength OBJECT-TYPE
	SYNTAX  INTEGER
	ACCESS  read-only
	STATUS  mandatory
	DESCRIPTION
		"Indicates subnet mask length(ipv4) or prefix length(ipv6) of
		 source IP address on detection condition."
	::= { axrFlowFilterOutEntry 18 }

axrFlowFilterOutSrcIpRange OBJECT-TYPE
	SYNTAX  InetAddress
	ACCESS  read-only
	STATUS  mandatory
	DESCRIPTION
		"Source IP address in range specified by detection condition.
		(maximum IP address)"
	::= { axrFlowFilterOutEntry 19 }

axrFlowFilterOutDestIpOp OBJECT-TYPE
	SYNTAX  INTEGER
	ACCESS  read-only
	STATUS  mandatory
	DESCRIPTION
		"Indicates specification method of destination IP address on 
		detection condition."
	::= { axrFlowFilterOutEntry 20 }

axrFlowFilterOutDestIp OBJECT-TYPE
	SYNTAX  InetAddress
	ACCESS  read-only
	STATUS  mandatory
	DESCRIPTION
		"Indicates destination IP address on detection condition."
	::= { axrFlowFilterOutEntry 21 }

axrFlowFilterOutDestIpLength OBJECT-TYPE
	SYNTAX  INTEGER
	ACCESS  read-only
	STATUS  mandatory
	DESCRIPTION
		"Indicates subnet mask length(ipv4) or prefix length(ipv6) of
		 destination IP address on detection condition."
	::= { axrFlowFilterOutEntry 22 }

axrFlowFilterOutDestIpRange OBJECT-TYPE
	SYNTAX  InetAddress
	ACCESS  read-only
	STATUS  mandatory
	DESCRIPTION
		"Destination IP address in range specified by detection condi
		tion.(maximum IP address)"
	::= { axrFlowFilterOutEntry 23 }

axrFlowFilterOutDscp OBJECT-TYPE
	SYNTAX  INTEGER
	ACCESS  read-only
	STATUS  mandatory
	DESCRIPTION
		"The value of DSCP on detection condition."
	::= { axrFlowFilterOutEntry 24 }

axrFlowFilterOutPrecedence OBJECT-TYPE
	SYNTAX  INTEGER
	ACCESS  read-only
	STATUS  mandatory
	DESCRIPTION
		"The value of precedence on detection condition."
	::= { axrFlowFilterOutEntry 25 }

axrFlowFilterOutUpperLength OBJECT-TYPE
	SYNTAX  INTEGER
	ACCESS  read-only
	STATUS  mandatory
	DESCRIPTION
		"The upper limit of IP user data length on detection conditio
		n. "
	::= { axrFlowFilterOutEntry 26 }

axrFlowFilterOutLowerLength OBJECT-TYPE
	SYNTAX  INTEGER
	ACCESS  read-only
	STATUS  mandatory
	DESCRIPTION
		"The lower limit of IP user data length on detection conditio
		n."
	::= { axrFlowFilterOutEntry 27 }

axrFlowFilterOutFragments OBJECT-TYPE
	SYNTAX  INTEGER
	ACCESS  read-only
	STATUS  mandatory
	DESCRIPTION
		"Indicates whether 2nd fragment packet or later are included 
		in detection condition."
	::= { axrFlowFilterOutEntry 28 }

axrFlowFilterOutSrcPortOp OBJECT-TYPE
	SYNTAX  INTEGER
	ACCESS  read-only
	STATUS  mandatory
	DESCRIPTION
		"Indicates specification method of source port number on dete
		ction condition."
	::= { axrFlowFilterOutEntry 29 }

axrFlowFilterOutSrcPort OBJECT-TYPE
	SYNTAX  INTEGER
	ACCESS  read-only
	STATUS  mandatory
	DESCRIPTION
		"Indicates source port number on detection condition."
	::= { axrFlowFilterOutEntry 30 }

axrFlowFilterOutSrcPortRange OBJECT-TYPE
	SYNTAX  INTEGER
	ACCESS  read-only
	STATUS  mandatory
	DESCRIPTION
		"Source port number in range specified by detection condition
		.(maximum port number)"
	::= { axrFlowFilterOutEntry 31 }

axrFlowFilterOutDestPortOp OBJECT-TYPE
	SYNTAX  INTEGER
	ACCESS  read-only
	STATUS  mandatory
	DESCRIPTION
		"Indicates specification method of destination port number on
		 detection condition."
	::= { axrFlowFilterOutEntry 32 }

axrFlowFilterOutDestPort OBJECT-TYPE
	SYNTAX  INTEGER
	ACCESS  read-only
	STATUS  mandatory
	DESCRIPTION
		"Indicates destination port number on detection condition."
	::= { axrFlowFilterOutEntry 33 }

axrFlowFilterOutDestPortRange OBJECT-TYPE
	SYNTAX  INTEGER
	ACCESS  read-only
	STATUS  mandatory
	DESCRIPTION
		"destination port number in range specified by detection cond
		ition.(maximum port number)"
	::= { axrFlowFilterOutEntry 34 }

axrFlowFilterOutAckFlag OBJECT-TYPE
	SYNTAX  INTEGER
	ACCESS  read-only
	STATUS  mandatory
	DESCRIPTION
		"Indicates whether TCP one-way communication permission is in
		cluded in detection condition or not."
	::= { axrFlowFilterOutEntry 35 }

axrFlowFilterOutSynFlag OBJECT-TYPE
	SYNTAX  INTEGER
	ACCESS  read-only
	STATUS  mandatory
	DESCRIPTION
		"Indicates whether virtual circuit link-up permission is incl
		uded in detection condition or not."
	::= { axrFlowFilterOutEntry 36 }

axrFlowFilterOutIcmpType OBJECT-TYPE
	SYNTAX  INTEGER
	ACCESS  read-only
	STATUS  mandatory
	DESCRIPTION
		"Indicates ICMP or ICMPv6 type on detection condition."
	::= { axrFlowFilterOutEntry 37 }

axrFlowFilterOutIcmpCode OBJECT-TYPE
	SYNTAX  INTEGER
	ACCESS  read-only
	STATUS  mandatory
	DESCRIPTION
		"Indicates ICMP or ICMPv6 code on detection condition."
	::= { axrFlowFilterOutEntry 38 }

axrFlowFilterOutIgmpType OBJECT-TYPE
	SYNTAX  INTEGER
	ACCESS  read-only
	STATUS  mandatory
	DESCRIPTION
		"Indicates IGMP type on detection condition."
	::= { axrFlowFilterOutEntry 39 }

axrFlowFilterOutLabelOp OBJECT-TYPE
	SYNTAX  INTEGER
	ACCESS  read-only
	STATUS  mandatory
	DESCRIPTION
		"Indicate the way to specify the label value in shim-header on detection condition."
	::= { axrFlowFilterOutEntry 40 }

axrFlowFilterOutLabel OBJECT-TYPE
	SYNTAX  INTEGER
	ACCESS  read-only
	STATUS  mandatory
	DESCRIPTION
		"The label value in shim-header on detection condition."
	::= { axrFlowFilterOutEntry 41 }

axrFlowFilterOutExp OBJECT-TYPE
	SYNTAX  INTEGER
	ACCESS  read-only
	STATUS  mandatory
	DESCRIPTION
		"The EXP value in shim-header on detection condition."
	::= { axrFlowFilterOutEntry 42 }

axrFlowFilterOutSrcIpMask OBJECT-TYPE
	SYNTAX  InetAddress
	ACCESS  read-only
	STATUS  mandatory
	DESCRIPTION
		"Indicates mask of source IP address on detection specificat
		ion."
	::= { axrFlowFilterOutEntry 43 }

axrFlowFilterOutDestIpMask OBJECT-TYPE
	SYNTAX  InetAddress
	ACCESS  read-only
	STATUS  mandatory
	DESCRIPTION
		"Indicates mask of destination IP address on detection speci
		fication."
	::= { axrFlowFilterOutEntry 44 }

axrFlowFilterInActTable OBJECT-TYPE
	SYNTAX  SEQUENCE OF AxrFlowFilterInActEntry
	ACCESS  not-accessible
	STATUS  mandatory
	DESCRIPTION
		"Information of action parameter table on flow filter detecti
		on condition.(Inbound)"
	::= { axrFlowFilter 3 }

axrFlowFilterInActEntry OBJECT-TYPE
	SYNTAX  AxrFlowFilterInActEntry
	ACCESS  not-accessible
	STATUS  mandatory
	DESCRIPTION
		"Entry of action parameter on flow filter detection condition
		.(Inbound)"
	INDEX {
		axrFlowFilterInActifIndex,
		axrFlowFilterInActifIndexType,
		axrFlowFilterInActListNumber
	}
	::= { axrFlowFilterInActTable 1 }
	AxrFlowFilterInActEntry ::= 
	    SEQUENCE {
		axrFlowFilterInActifIndex
			INTEGER,
		axrFlowFilterInActifIndexType
        	INTEGER,
		axrFlowFilterInActListNumber
        	INTEGER,
		axrFlowFilterInActInfo
        	INTEGER
        }

axrFlowFilterInActifIndex OBJECT-TYPE
	SYNTAX  INTEGER
	ACCESS  not-accessible
	STATUS  mandatory
	DESCRIPTION
		"Indicates the value of index(ifIndex) which identifies this 
		table entry."
	::= { axrFlowFilterInActEntry 1 }

axrFlowFilterInActifIndexType OBJECT-TYPE
	SYNTAX  INTEGER
	ACCESS  not-accessible
	STATUS  mandatory
	DESCRIPTION
		"Indicates interface type.Physical port number : 1Interface n
		ame : 2"
	::= { axrFlowFilterInActEntry 2 }

axrFlowFilterInActListNumber OBJECT-TYPE
	SYNTAX  INTEGER
	ACCESS  not-accessible
	STATUS  mandatory
	DESCRIPTION
		"Indicates the value of index(list number) which identifies t
		his table entry."
	::= { axrFlowFilterInActEntry 3 }

axrFlowFilterInActInfo OBJECT-TYPE
	SYNTAX  INTEGER
	ACCESS  read-only
	STATUS  mandatory
	DESCRIPTION
		"Information of action parameter on detection condition."
	::= { axrFlowFilterInActEntry 4 }

axrFlowFilterOutActTable OBJECT-TYPE
	SYNTAX  SEQUENCE OF AxrFlowFilterOutActEntry
	ACCESS  not-accessible
	STATUS  mandatory
	DESCRIPTION
		"Information of action parameter table on flow filter detecti
		on condition.(Outbound)"
	::= { axrFlowFilter 4 }

axrFlowFilterOutActEntry OBJECT-TYPE
	SYNTAX  AxrFlowFilterOutActEntry
	ACCESS  not-accessible
	STATUS  mandatory
	DESCRIPTION
		"Entry of action parameter on flow filter detection condition
		.(Outbound)"
	INDEX {
		axrFlowFilterOutActifIndex,
		axrFlowFilterOutActifIndexType,
		axrFlowFilterOutActListNumber
	}
	::= { axrFlowFilterOutActTable 1 }
	AxrFlowFilterOutActEntry ::= 
	    SEQUENCE {
		axrFlowFilterOutActifIndex
			INTEGER,
		axrFlowFilterOutActifIndexType
        	INTEGER,
		axrFlowFilterOutActListNumber
        	INTEGER,
		axrFlowFilterOutActInfo
        	INTEGER
        }

axrFlowFilterOutActifIndex OBJECT-TYPE
	SYNTAX  INTEGER
	ACCESS  not-accessible
	STATUS  mandatory
	DESCRIPTION
		"Indicates the value of index(ifIndex) which identifies this 
		table entry."
	::= { axrFlowFilterOutActEntry 1 }

axrFlowFilterOutActifIndexType OBJECT-TYPE
	SYNTAX  INTEGER
	ACCESS  not-accessible
	STATUS  mandatory
	DESCRIPTION
		"Indicates interface type.Physical port number : 1Interface n
		ame : 2"
	::= { axrFlowFilterOutActEntry 2 }

axrFlowFilterOutActListNumber OBJECT-TYPE
	SYNTAX  INTEGER
	ACCESS  not-accessible
	STATUS  mandatory
	DESCRIPTION
		"Indicates the value of index(list number) which identifies t
		his table entry."
	::= { axrFlowFilterOutActEntry 3 }

axrFlowFilterOutActInfo OBJECT-TYPE
	SYNTAX  INTEGER
	ACCESS  read-only
	STATUS  mandatory
	DESCRIPTION
		"Information of action parameter on detection condition."
	::= { axrFlowFilterOutActEntry 4 }

axrFlowFilterStatsInTable OBJECT-TYPE
	SYNTAX  SEQUENCE OF AxrFlowFilterStatsInEntry
	ACCESS  not-accessible
	STATUS  mandatory
	DESCRIPTION
		"Information of statistics table of per action parameter on f
		low filter detection condition.(Inbound)"
	::= { axrFlowFilterStats 1 }

axrFlowFilterStatsInEntry OBJECT-TYPE
	SYNTAX  AxrFlowFilterStatsInEntry
	ACCESS  not-accessible
	STATUS  mandatory
	DESCRIPTION
		"Entry of statistics information of each action parameter on 
		flow filter detection condition.(Inbound)"
	INDEX {
		axrFlowFilterStatsInifIndex,
		axrFlowFilterStatsInifIndexType,
		axrFlowFilterStatsInListNumber
	}
	::= { axrFlowFilterStatsInTable 1 }
	AxrFlowFilterStatsInEntry ::= 
	    SEQUENCE {
		axrFlowFilterStatsInifIndex
			INTEGER,
		axrFlowFilterStatsInifIndexType
        	INTEGER,
		axrFlowFilterStatsInListNumber
        	INTEGER,
		axrFlowFilterStatsInDropPackets
        	Counter64,
		axrFlowFilterStatsInForwardPackets
        	Counter64,
		axrFlowFilterStatsInPolicyRoutedPackets
        	Counter64,
        axrFlowFilterStatsInPolicyMplsRoutedPackets
            Counter64
        }

axrFlowFilterStatsInifIndex OBJECT-TYPE
	SYNTAX  INTEGER
	ACCESS  not-accessible
	STATUS  mandatory
	DESCRIPTION
		"Indicates the value of index(ifIndex) which identifies this 
		table entry."
	::= { axrFlowFilterStatsInEntry 1 }

axrFlowFilterStatsInifIndexType OBJECT-TYPE
	SYNTAX  INTEGER
	ACCESS  not-accessible
	STATUS  mandatory
	DESCRIPTION
		"Indicates interface type.Physical port number : 1Interface n
		ame : 2"
	::= { axrFlowFilterStatsInEntry 2 }

axrFlowFilterStatsInListNumber OBJECT-TYPE
	SYNTAX  INTEGER
	ACCESS  not-accessible
	STATUS  mandatory
	DESCRIPTION
		"Indicates the value of index(list number) which identifies t
		his table entry."
	::= { axrFlowFilterStatsInEntry 3 }

axrFlowFilterStatsInDropPackets OBJECT-TYPE
	SYNTAX  Counter64
	ACCESS  read-only
	STATUS  mandatory
	DESCRIPTION
		"The number of packets which were matched with detection cond
		ition and were discarded."
	::= { axrFlowFilterStatsInEntry 4 }

axrFlowFilterStatsInForwardPackets OBJECT-TYPE
	SYNTAX  Counter64
	ACCESS  read-only
	STATUS  mandatory
	DESCRIPTION
		"The number of packets which were matched with detection cond
		ition and were forwarded."
	::= { axrFlowFilterStatsInEntry 5 }

axrFlowFilterStatsInPolicyRoutedPackets OBJECT-TYPE
	SYNTAX  Counter64
	ACCESS  read-only
	STATUS  mandatory
	DESCRIPTION
		"The number of packets which were matched with detection cond
		ition and were policy routed."
	::= { axrFlowFilterStatsInEntry 6 }

axrFlowFilterStatsInPolicyMplsRoutedPackets OBJECT-TYPE
	SYNTAX  Counter64
	ACCESS  read-only
	STATUS  mandatory
	DESCRIPTION
		"The number of packets which were matched with detection cond
		ition and were policy routed on MPLS."
	::= { axrFlowFilterStatsInEntry 10 }

axrFlowFilterStatsOutTable OBJECT-TYPE
	SYNTAX  SEQUENCE OF AxrFlowFilterStatsOutEntry
	ACCESS  not-accessible
	STATUS  mandatory
	DESCRIPTION
		"Information of statistics table of per action parameter on f
		low filter detection condition.(Outbound)"
	::= { axrFlowFilterStats 2 }

axrFlowFilterStatsOutEntry OBJECT-TYPE
	SYNTAX  AxrFlowFilterStatsOutEntry
	ACCESS  not-accessible
	STATUS  mandatory
	DESCRIPTION
		"Entry of statistics information of each action parameter on 
		flow filter detection condition.(Outbound)"
	INDEX {
		axrFlowFilterStatsOutifIndex,
		axrFlowFilterStatsOutifIndexType,
		axrFlowFilterStatsOutListNumber
	}
	::= { axrFlowFilterStatsOutTable 1 }
	AxrFlowFilterStatsOutEntry ::= 
	    SEQUENCE {
		axrFlowFilterStatsOutifIndex
			INTEGER,
		axrFlowFilterStatsOutifIndexType
        	INTEGER,
		axrFlowFilterStatsOutListNumber
        	INTEGER,
		axrFlowFilterStatsOutDropPackets
        	Counter64,
		axrFlowFilterStatsOutForwardPackets
        	Counter64
        }

axrFlowFilterStatsOutifIndex OBJECT-TYPE
	SYNTAX  INTEGER
	ACCESS  not-accessible
	STATUS  mandatory
	DESCRIPTION
		"Indicates the value of index(ifIndex) which identifies this 
		table entry."
	::= { axrFlowFilterStatsOutEntry 1 }

axrFlowFilterStatsOutifIndexType OBJECT-TYPE
	SYNTAX  INTEGER
	ACCESS  not-accessible
	STATUS  mandatory
	DESCRIPTION
		"Indicates interface type.Physical port number : 1Interface n
		ame : 2"
	::= { axrFlowFilterStatsOutEntry 2 }

axrFlowFilterStatsOutListNumber OBJECT-TYPE
	SYNTAX  INTEGER
	ACCESS  not-accessible
	STATUS  mandatory
	DESCRIPTION
		"Indicates the value of index(list number) which identifies t
		his table entry."
	::= { axrFlowFilterStatsOutEntry 3 }

axrFlowFilterStatsOutDropPackets OBJECT-TYPE
	SYNTAX  Counter64
	ACCESS  read-only
	STATUS  mandatory
	DESCRIPTION
		"The number of packets which were matched with detection cond
		ition and were discarded."
	::= { axrFlowFilterStatsOutEntry 4 }

axrFlowFilterStatsOutForwardPackets OBJECT-TYPE
	SYNTAX  Counter64
	ACCESS  read-only
	STATUS  mandatory
	DESCRIPTION
		"The number of packets which were matched with detection cond
		ition and were forwarded."
	::= { axrFlowFilterStatsOutEntry 5 }

axrFlowQosInTable OBJECT-TYPE
	SYNTAX  SEQUENCE OF AxrFlowQosInEntry
	ACCESS  not-accessible
	STATUS  mandatory
	DESCRIPTION
		"Information of normal flow QoS detection condition table.(I
		nbound)"
	::= { axrFlowQos 1 }

axrFlowQosInEntry OBJECT-TYPE
	SYNTAX  AxrFlowQosInEntry
	ACCESS  not-accessible
	STATUS  mandatory
	DESCRIPTION
		"Entry of normal flow QoS detection condition."
	INDEX {
		axrFlowQosInifIndex,
		axrFlowQosInifIndexType,
		axrFlowQosInListNumber
	}
	::= { axrFlowQosInTable 1 }
	AxrFlowQosInEntry ::= 
	    SEQUENCE {
		axrFlowQosInifIndex
			INTEGER,
		axrFlowQosInifIndexType
        	INTEGER,
		axrFlowQosInListNumber
        	INTEGER,
		axrFlowQosInSrcMacOp
        	INTEGER,
		axrFlowQosInSrcMac
        	MacAddress,
		axrFlowQosInSrcMacMask
        	MacAddress,
		axrFlowQosInDestMacOp
        	INTEGER,
		axrFlowQosInDestMac
        	MacAddress,
		axrFlowQosInDestMacMask
        	MacAddress,
		axrFlowQosInEthernetType
        	OCTET STRING,
		axrFlowQosInUserPriority
        	INTEGER,
		axrFlowQosInLowerVlanList
        	OCTET STRING,
		axrFlowQosInHigherVlanList
        	OCTET STRING,
		axrFlowQosInProtocolNumber
        	INTEGER,
		axrFlowQosInIpAddrType
        	InetAddressType,
		axrFlowQosInSrcIpOp
        	INTEGER,
		axrFlowQosInSrcIp
        	InetAddress,
		axrFlowQosInSrcIpLength
        	INTEGER,
		axrFlowQosInSrcIpRange
        	InetAddress,
		axrFlowQosInDestIpOp
        	INTEGER,
		axrFlowQosInDestIp
        	InetAddress,
		axrFlowQosInDestIpLength
        	INTEGER,
		axrFlowQosInDestIpRange
        	InetAddress,
		axrFlowQosInDscp
        	INTEGER,
		axrFlowQosInPrecedence
        	INTEGER,
		axrFlowQosInUpperLength
        	INTEGER,
		axrFlowQosInLowerLength
        	INTEGER,
		axrFlowQosInFragments
        	INTEGER,
		axrFlowQosInSrcPortOp
        	INTEGER,
		axrFlowQosInSrcPort
        	INTEGER,
		axrFlowQosInSrcPortRange
        	INTEGER,
		axrFlowQosInDestPortOp
        	INTEGER,
		axrFlowQosInDestPort
        	INTEGER,
		axrFlowQosInDestPortRange
        	INTEGER,
		axrFlowQosInAckFlag
        	INTEGER,
		axrFlowQosInSynFlag
        	INTEGER,
		axrFlowQosInIcmpType
        	INTEGER,
		axrFlowQosInIcmpCode
        	INTEGER,
		axrFlowQosInIgmpType
        	INTEGER,
		axrFlowQosInLabelOp
			INTEGER,
		axrFlowQosInLabel
			INTEGER,
		axrFlowQosInExp
			INTEGER,
		axrFlowQosInSrcIpMask
			InetAddress,
		axrFlowQosInDestIpMask
			InetAddress
        }

axrFlowQosInifIndex OBJECT-TYPE
	SYNTAX  INTEGER
	ACCESS  not-accessible
	STATUS  mandatory
	DESCRIPTION
		"Indicates the value of index(ifIndex) which identifies this 
		table entry."
	::= { axrFlowQosInEntry 1 }

axrFlowQosInifIndexType OBJECT-TYPE
	SYNTAX  INTEGER
	ACCESS  not-accessible
	STATUS  mandatory
	DESCRIPTION
		"Indicates interface type.Physical port number : 1Interface n
		ame : 2(2)fixed."
	::= { axrFlowQosInEntry 2 }

axrFlowQosInListNumber OBJECT-TYPE
	SYNTAX  INTEGER
	ACCESS  not-accessible
	STATUS  mandatory
	DESCRIPTION
		"Indicates the value of index(list number) which identifies t
		his table entry."
	::= { axrFlowQosInEntry 3 }

axrFlowQosInSrcMacOp OBJECT-TYPE
	SYNTAX  INTEGER
	ACCESS  read-only
	STATUS  mandatory
	DESCRIPTION
		"Indicates specification method of source MAC address on norm
		al flow detection condition."
	::= { axrFlowQosInEntry 4 }

axrFlowQosInSrcMac OBJECT-TYPE
	SYNTAX  MacAddress
	ACCESS  read-only
	STATUS  mandatory
	DESCRIPTION
		"Indicates source MAC address on normal flow detection condi
		tion."
	::= { axrFlowQosInEntry 5 }

axrFlowQosInSrcMacMask OBJECT-TYPE
	SYNTAX  MacAddress
	ACCESS  read-only
	STATUS  mandatory
	DESCRIPTION
		"Indicates mask of source MAC address on normal flow detecti
		on specification."
	::= { axrFlowQosInEntry 6 }

axrFlowQosInDestMacOp OBJECT-TYPE
	SYNTAX  INTEGER
	ACCESS  read-only
	STATUS  mandatory
	DESCRIPTION
		"Indicates specification method of destination MAC address on
		 normal flow detection condition."
	::= { axrFlowQosInEntry 7 }

axrFlowQosInDestMac OBJECT-TYPE
	SYNTAX  MacAddress
	ACCESS  read-only
	STATUS  mandatory
	DESCRIPTION
		"Indicates destination MAC address on normal flow detection 
		condition."
	::= { axrFlowQosInEntry 8 }

axrFlowQosInDestMacMask OBJECT-TYPE
	SYNTAX  MacAddress
	ACCESS  read-only
	STATUS  mandatory
	DESCRIPTION
		"Indicates mask of destination MAC address on normal flow de
		tection specification."
	::= { axrFlowQosInEntry 9 }

axrFlowQosInEthernetType OBJECT-TYPE
	SYNTAX  OCTET STRING
	ACCESS  read-only
	STATUS  mandatory
	DESCRIPTION
		"Indicates type of ethernet V2 and IEEE802.3 SNAP/RFC1042 for
		m on normal flow detection condition."
	::= { axrFlowQosInEntry 10 }

axrFlowQosInUserPriority OBJECT-TYPE
	SYNTAX  INTEGER
	ACCESS  read-only
	STATUS  mandatory
	DESCRIPTION
		"Indicates user priority in Tag-VLAN on normal detection con
		dition."
	::= { axrFlowQosInEntry 11 }

axrFlowQosInLowerVlanList OBJECT-TYPE
	SYNTAX  OCTET STRING
	ACCESS  read-only
	STATUS  mandatory
	DESCRIPTION
		"Bit map representation of VLAN ID on normal flow detection 
		condition.(Head 1 bit indicates existence of untagged definit
		ion, and the rest effective or non-effective of VLAN 1-2047.)
		"
	::= { axrFlowQosInEntry 12 }

axrFlowQosInHigherVlanList OBJECT-TYPE
	SYNTAX  OCTET STRING
	ACCESS  read-only
	STATUS  mandatory
	DESCRIPTION
		"Bit map representation of VLAN ID on normal flow detection 
		condition.(Each bit indicates whether VLAN 2048-4095 is effec
		tive or non-effective in order.)"
	::= { axrFlowQosInEntry 13 }

axrFlowQosInProtocolNumber OBJECT-TYPE
	SYNTAX  INTEGER
	ACCESS  read-only
	STATUS  mandatory
	DESCRIPTION
		"Indicates upper protocol number on normal flow detection co
		ndition."
	::= { axrFlowQosInEntry 14 }

axrFlowQosInIpAddrType OBJECT-TYPE
	SYNTAX  InetAddressType
	ACCESS  read-only
	STATUS  mandatory
	DESCRIPTION
		"Indicates IP address type which is shown."
	::= { axrFlowQosInEntry 15 }

axrFlowQosInSrcIpOp OBJECT-TYPE
	SYNTAX  INTEGER
	ACCESS  read-only
	STATUS  mandatory
	DESCRIPTION
		"Indicates specification method of source IP address on norma
		l flow detection condition."
	::= { axrFlowQosInEntry 16 }

axrFlowQosInSrcIp OBJECT-TYPE
	SYNTAX  InetAddress
	ACCESS  read-only
	STATUS  mandatory
	DESCRIPTION
		"Indicates source IP address on normal flow detection condit
		ion."
	::= { axrFlowQosInEntry 17 }

axrFlowQosInSrcIpLength OBJECT-TYPE
	SYNTAX  INTEGER
	ACCESS  read-only
	STATUS  mandatory
	DESCRIPTION
		"Indicates subnet mask length(ipv4) or prefix length(ipv6) of
		 source IP address on normal flow detection condition."
	::= { axrFlowQosInEntry 18 }

axrFlowQosInSrcIpRange OBJECT-TYPE
	SYNTAX  InetAddress
	ACCESS  read-only
	STATUS  mandatory
	DESCRIPTION
		"Source IP address in range specified by normal flow detecti
		on condition.(maximum IP address)"
	::= { axrFlowQosInEntry 19 }

axrFlowQosInDestIpOp OBJECT-TYPE
	SYNTAX  INTEGER
	ACCESS  read-only
	STATUS  mandatory
	DESCRIPTION
		"Indicates specification method of destination IP address on 
		normal flow detection condition."
	::= { axrFlowQosInEntry 20 }

axrFlowQosInDestIp OBJECT-TYPE
	SYNTAX  InetAddress
	ACCESS  read-only
	STATUS  mandatory
	DESCRIPTION
		"Indicates destination IP address on normal flow detection c
		ondition."
	::= { axrFlowQosInEntry 21 }

axrFlowQosInDestIpLength OBJECT-TYPE
	SYNTAX  INTEGER
	ACCESS  read-only
	STATUS  mandatory
	DESCRIPTION
		"Indicates subnet mask length(ipv4) or prefix length(ipv6) of
		 destination IP address on normal flow detection condition."
	::= { axrFlowQosInEntry 22 }

axrFlowQosInDestIpRange OBJECT-TYPE
	SYNTAX  InetAddress
	ACCESS  read-only
	STATUS  mandatory
	DESCRIPTION
		"Destination IP address in range specified by normal flow de
		tection condition.(maximum IP address)"
	::= { axrFlowQosInEntry 23 }

axrFlowQosInDscp OBJECT-TYPE
	SYNTAX  INTEGER
	ACCESS  read-only
	STATUS  mandatory
	DESCRIPTION
		"The value of DSCP on normal flow detection condition."
	::= { axrFlowQosInEntry 24 }

axrFlowQosInPrecedence OBJECT-TYPE
	SYNTAX  INTEGER
	ACCESS  read-only
	STATUS  mandatory
	DESCRIPTION
		"The value of precedence on normal flow detection condition.
		"
	::= { axrFlowQosInEntry 25 }

axrFlowQosInUpperLength OBJECT-TYPE
	SYNTAX  INTEGER
	ACCESS  read-only
	STATUS  mandatory
	DESCRIPTION
		"The upper limit of IP user data length on normal flow detec
		tion condition. "
	::= { axrFlowQosInEntry 26 }

axrFlowQosInLowerLength OBJECT-TYPE
	SYNTAX  INTEGER
	ACCESS  read-only
	STATUS  mandatory
	DESCRIPTION
		"The lower limit of IP user data length on normal flow detec
		tion condition."
	::= { axrFlowQosInEntry 27 }

axrFlowQosInFragments OBJECT-TYPE
	SYNTAX  INTEGER
	ACCESS  read-only
	STATUS  mandatory
	DESCRIPTION
		"Indicates whether 2nd fragment packet or later are included 
		in normal flow detection condition."
	::= { axrFlowQosInEntry 28 }

axrFlowQosInSrcPortOp OBJECT-TYPE
	SYNTAX  INTEGER
	ACCESS  read-only
	STATUS  mandatory
	DESCRIPTION
		"Indicates specification method of source port number on nor
		mal flow detection condition."
	::= { axrFlowQosInEntry 29 }

axrFlowQosInSrcPort OBJECT-TYPE
	SYNTAX  INTEGER
	ACCESS  read-only
	STATUS  mandatory
	DESCRIPTION
		"Indicates source port number on normal flow detection condi
		tion."
	::= { axrFlowQosInEntry 30 }

axrFlowQosInSrcPortRange OBJECT-TYPE
	SYNTAX  INTEGER
	ACCESS  read-only
	STATUS  mandatory
	DESCRIPTION
		"Source port number in range specified by normal flow detect
		ion condition.(maximum port number)"
	::= { axrFlowQosInEntry 31 }

axrFlowQosInDestPortOp OBJECT-TYPE
	SYNTAX  INTEGER
	ACCESS  read-only
	STATUS  mandatory
	DESCRIPTION
		"Indicates specification method of destination port number on
		 normal flow detection condition."
	::= { axrFlowQosInEntry 32 }

axrFlowQosInDestPort OBJECT-TYPE
	SYNTAX  INTEGER
	ACCESS  read-only
	STATUS  mandatory
	DESCRIPTION
		"Indicates destination port number on normal flow detection 
		condition."
	::= { axrFlowQosInEntry 33 }

axrFlowQosInDestPortRange OBJECT-TYPE
	SYNTAX  INTEGER
	ACCESS  read-only
	STATUS  mandatory
	DESCRIPTION
		"destination port number in range specified by normal flow d
		etection condition.(maximum port number)"
	::= { axrFlowQosInEntry 34 }

axrFlowQosInAckFlag OBJECT-TYPE
	SYNTAX  INTEGER
	ACCESS  read-only
	STATUS  mandatory
	DESCRIPTION
		"Indicates whether TCP one-way communication permission is in
		cluded in normal flow detection condition or not."
	::= { axrFlowQosInEntry 35 }

axrFlowQosInSynFlag OBJECT-TYPE
	SYNTAX  INTEGER
	ACCESS  read-only
	STATUS  mandatory
	DESCRIPTION
		"Indicates whether virtual circuit link-up permission is incl
		uded in normal flow detection condition or not."
	::= { axrFlowQosInEntry 36 }

axrFlowQosInIcmpType OBJECT-TYPE
	SYNTAX  INTEGER
	ACCESS  read-only
	STATUS  mandatory
	DESCRIPTION
		"Indicates ICMP or ICMPv6 type on normal flow detection cond
		ition."
	::= { axrFlowQosInEntry 37 }

axrFlowQosInIcmpCode OBJECT-TYPE
	SYNTAX  INTEGER
	ACCESS  read-only
	STATUS  mandatory
	DESCRIPTION
		"Indicates ICMP or ICMPv6 code on normal flow detection cond
		ition."
	::= { axrFlowQosInEntry 38 }

axrFlowQosInIgmpType OBJECT-TYPE
	SYNTAX  INTEGER
	ACCESS  read-only
	STATUS  mandatory
	DESCRIPTION
		"Indicates IGMP type on normal flow detection condition."
	::= { axrFlowQosInEntry 39 }

axrFlowQosInLabelOp OBJECT-TYPE
	SYNTAX  INTEGER
	ACCESS  read-only
	STATUS  mandatory
	DESCRIPTION
		"Indicates the way to specify the label value in shim header on normal flow detection condition."
	::= { axrFlowQosInEntry 40 }

axrFlowQosInLabel OBJECT-TYPE
	SYNTAX  INTEGER
	ACCESS  read-only
	STATUS  mandatory
	DESCRIPTION
		"The label value in shim header on normal flow detection condition."
	::= { axrFlowQosInEntry 41 }

axrFlowQosInExp OBJECT-TYPE
	SYNTAX  INTEGER
	ACCESS  read-only
	STATUS  mandatory
	DESCRIPTION
		"The EXP value in shim header on normal flow detection condition."
	::= { axrFlowQosInEntry 42 }

axrFlowQosInSrcIpMask OBJECT-TYPE
	SYNTAX  InetAddress
	ACCESS  read-only
	STATUS  mandatory
	DESCRIPTION
		"Indicates mask of source IP address on normal flow detecti
		on specification."
	::= { axrFlowQosInEntry 43 }

axrFlowQosInDestIpMask OBJECT-TYPE
	SYNTAX  InetAddress
	ACCESS  read-only
	STATUS  mandatory
	DESCRIPTION
		"Indicates mask of destination IP address on normal flow de
		tection specification."
	::= { axrFlowQosInEntry 44 }

axrFlowQosInPremTable OBJECT-TYPE
	SYNTAX  SEQUENCE OF AxrFlowQosInPremEntry
	ACCESS  not-accessible
	STATUS  mandatory
	DESCRIPTION
		"Information of premium flow QoS detection condition table.(I
		nbound)"
	::= { axrFlowQos 2 }

axrFlowQosInPremEntry OBJECT-TYPE
	SYNTAX  AxrFlowQosInPremEntry
	ACCESS  not-accessible
	STATUS  mandatory
	DESCRIPTION
		"Entry of premium flow QoS detection condition."
	INDEX {
		axrFlowQosInPremifIndex,
		axrFlowQosInPremifIndexType,
		axrFlowQosInPremListNumber
	}
	::= { axrFlowQosInPremTable 1 }
	AxrFlowQosInPremEntry ::= 
	    SEQUENCE {
		axrFlowQosInPremifIndex
			INTEGER,
		axrFlowQosInPremifIndexType
        	INTEGER,
		axrFlowQosInPremListNumber
        	INTEGER,
		axrFlowQosInPremSrcMacOp
        	INTEGER,
		axrFlowQosInPremSrcMac
        	MacAddress,
		axrFlowQosInPremSrcMacMask
        	MacAddress,
		axrFlowQosInPremDestMacOp
        	INTEGER,
		axrFlowQosInPremDestMac
        	MacAddress,
		axrFlowQosInPremDestMacMask
        	MacAddress,
		axrFlowQosInPremEthernetType
        	OCTET STRING,
		axrFlowQosInPremUserPriority
        	INTEGER,
		axrFlowQosInPremLowerVlanList
        	OCTET STRING,
		axrFlowQosInPremHigherVlanList
        	OCTET STRING,
		axrFlowQosInPremProtocolNumber
        	INTEGER,
		axrFlowQosInPremIpAddrType
        	InetAddressType,
		axrFlowQosInPremSrcIpOp
        	INTEGER,
		axrFlowQosInPremSrcIp
        	InetAddressType,
		axrFlowQosInPremSrcIpLength
        	INTEGER,
		axrFlowQosInPremSrcIpRange
        	InetAddressType,
		axrFlowQosInPremDestIpOp
        	INTEGER,
		axrFlowQosInPremDestIp
        	InetAddressType,
		axrFlowQosInPremDestIpLength
        	INTEGER,
		axrFlowQosInPremDestIpRange
        	InetAddressType,
		axrFlowQosInPremDscp
        	INTEGER,
		axrFlowQosInPremPrecedence
        	INTEGER,
		axrFlowQosInPremUpperLength
        	INTEGER,
		axrFlowQosInPremLowerLength
        	INTEGER,
		axrFlowQosInPremFragments
        	INTEGER,
		axrFlowQosInPremSrcPortOp
        	INTEGER,
		axrFlowQosInPremSrcPort
        	INTEGER,
		axrFlowQosInPremSrcPortRange
        	INTEGER,
		axrFlowQosInPremDestPortOp
        	INTEGER,
		axrFlowQosInPremDestPort
        	INTEGER,
		axrFlowQosInPremDestPortRange
        	INTEGER,
		axrFlowQosInPremAckFlag
        	INTEGER,
		axrFlowQosInPremSynFlag
        	INTEGER,
		axrFlowQosInPremIcmpType
        	INTEGER,
		axrFlowQosInPremIcmpCode
        	INTEGER,
		axrFlowQosInPremIgmpType
        	INTEGER,
		axrFlowQosInPremLabelOp
			INTEGER,
		axrFlowQosInPremLabel
			INTEGER,
		axrFlowQosInPremExp
			INTEGER,
		axrFlowQosInPremSrcIpMask
			InetAddress,
		axrFlowQosInPremDestIpMask
			InetAddress
        }

axrFlowQosInPremifIndex OBJECT-TYPE
	SYNTAX  INTEGER
	ACCESS  not-accessible
	STATUS  mandatory
	DESCRIPTION
		"Indicates the value of index(ifIndex) which identifies this 
		table entry."
	::= { axrFlowQosInPremEntry 1 }

axrFlowQosInPremifIndexType OBJECT-TYPE
	SYNTAX  INTEGER
	ACCESS  not-accessible
	STATUS  mandatory
	DESCRIPTION
		"Indicates interface type.Physical port number : 1Interface n
		ame : 2(2)fixed."
	::= { axrFlowQosInPremEntry 2 }

axrFlowQosInPremListNumber OBJECT-TYPE
	SYNTAX  INTEGER
	ACCESS  not-accessible
	STATUS  mandatory
	DESCRIPTION
		"Indicates the value of index(list number) which identifies t
		his table entry."
	::= { axrFlowQosInPremEntry 3 }

axrFlowQosInPremSrcMacOp OBJECT-TYPE
	SYNTAX  INTEGER
	ACCESS  read-only
	STATUS  mandatory
	DESCRIPTION
		"Indicates specification method of source MAC address on prem
		ium flow detection condition."
	::= { axrFlowQosInPremEntry 4 }

axrFlowQosInPremSrcMac OBJECT-TYPE
	SYNTAX  MacAddress
	ACCESS  read-only
	STATUS  mandatory
	DESCRIPTION
		"Indicates source MAC address on premium flow detection condi
		tion."
	::= { axrFlowQosInPremEntry 5 }

axrFlowQosInPremSrcMacMask OBJECT-TYPE
	SYNTAX  MacAddress
	ACCESS  read-only
	STATUS  mandatory
	DESCRIPTION
		"Indicates mask of source MAC address on premium flow detecti
		on specification."
	::= { axrFlowQosInPremEntry 6 }

axrFlowQosInPremDestMacOp OBJECT-TYPE
	SYNTAX  INTEGER
	ACCESS  read-only
	STATUS  mandatory
	DESCRIPTION
		"Indicates specification method of destination MAC address on
		 premium flow detection condition."
	::= { axrFlowQosInPremEntry 7 }

axrFlowQosInPremDestMac OBJECT-TYPE
	SYNTAX  MacAddress
	ACCESS  read-only
	STATUS  mandatory
	DESCRIPTION
		"Indicates destination MAC address on premium flow detection 
		condition."
	::= { axrFlowQosInPremEntry 8 }

axrFlowQosInPremDestMacMask OBJECT-TYPE
	SYNTAX  MacAddress
	ACCESS  read-only
	STATUS  mandatory
	DESCRIPTION
		"Indicates mask of destination MAC address on premium flow de
		tection specification."
	::= { axrFlowQosInPremEntry 9 }

axrFlowQosInPremEthernetType OBJECT-TYPE
	SYNTAX  OCTET STRING
	ACCESS  read-only
	STATUS  mandatory
	DESCRIPTION
		"Indicates type of ethernet V2 and IEEE802.3 SNAP/RFC1042 for
		m on premium flow detection condition."
	::= { axrFlowQosInPremEntry 10 }

axrFlowQosInPremUserPriority OBJECT-TYPE
	SYNTAX  INTEGER
	ACCESS  read-only
	STATUS  mandatory
	DESCRIPTION
		"Indicates user priority in Tag-VLAN on premium flow detectio
		n condition."
	::= { axrFlowQosInPremEntry 11 }

axrFlowQosInPremLowerVlanList OBJECT-TYPE
	SYNTAX  OCTET STRING
	ACCESS  read-only
	STATUS  mandatory
	DESCRIPTION
		"Bit map representation of VLAN ID on premium flow detection 
		condition.(Head 1 bit indicates existence of untagged definit
		ion, and the rest effective or non-effective of VLAN 1-2047.)
		"
	::= { axrFlowQosInPremEntry 12 }

axrFlowQosInPremHigherVlanList OBJECT-TYPE
	SYNTAX  OCTET STRING
	ACCESS  read-only
	STATUS  mandatory
	DESCRIPTION
		"Bit map representation of VLAN ID on premium flow detection 
		condition.(Each bit indicates whether VLAN 2048-4095 is effec
		tive or non-effective in order.)"
	::= { axrFlowQosInPremEntry 13 }

axrFlowQosInPremProtocolNumber OBJECT-TYPE
	SYNTAX  INTEGER
	ACCESS  read-only
	STATUS  mandatory
	DESCRIPTION
		"Indicates upper protocol number on premium flow detection co
		ndition."
	::= { axrFlowQosInPremEntry 14 }

axrFlowQosInPremIpAddrType OBJECT-TYPE
	SYNTAX  InetAddressType
	ACCESS  read-only
	STATUS  mandatory
	DESCRIPTION
		"Shown IP address type."
	::= { axrFlowQosInPremEntry 15 }

axrFlowQosInPremSrcIpOp OBJECT-TYPE
	SYNTAX  INTEGER
	ACCESS  read-only
	STATUS  mandatory
	DESCRIPTION
		"Indicates specification method of source IP address on premi
		um flow detection condition."
	::= { axrFlowQosInPremEntry 16 }

axrFlowQosInPremSrcIp OBJECT-TYPE
	SYNTAX  InetAddressType
	ACCESS  read-only
	STATUS  mandatory
	DESCRIPTION
		"Indicates source IP address on premium flow detection condit
		ion."
	::= { axrFlowQosInPremEntry 17 }

axrFlowQosInPremSrcIpLength OBJECT-TYPE
	SYNTAX  INTEGER
	ACCESS  read-only
	STATUS  mandatory
	DESCRIPTION
		"Indicates subnet mask length(ipv4) or prefix length(ipv6) of
		 source IP address on premium flow detection condition."
	::= { axrFlowQosInPremEntry 18 }

axrFlowQosInPremSrcIpRange OBJECT-TYPE
	SYNTAX  InetAddressType
	ACCESS  read-only
	STATUS  mandatory
	DESCRIPTION
		"Source IP address in range specified by premium flow detecti
		on condition.(maximum IP address)"
	::= { axrFlowQosInPremEntry 19 }

axrFlowQosInPremDestIpOp OBJECT-TYPE
	SYNTAX  INTEGER
	ACCESS  read-only
	STATUS  mandatory
	DESCRIPTION
		"Indicates specification method of destination IP address on 
		premium flow detection condition."
	::= { axrFlowQosInPremEntry 20 }

axrFlowQosInPremDestIp OBJECT-TYPE
	SYNTAX  InetAddressType
	ACCESS  read-only
	STATUS  mandatory
	DESCRIPTION
		"Indicates destination IP address on premium flow detection c
		ondition."
	::= { axrFlowQosInPremEntry 21 }

axrFlowQosInPremDestIpLength OBJECT-TYPE
	SYNTAX  INTEGER
	ACCESS  read-only
	STATUS  mandatory
	DESCRIPTION
		"Indicates subnet mask length(ipv4) or prefix length(ipv6) of
		 destination IP address on premium flow detection condition."
	::= { axrFlowQosInPremEntry 22 }

axrFlowQosInPremDestIpRange OBJECT-TYPE
	SYNTAX  InetAddressType
	ACCESS  read-only
	STATUS  mandatory
	DESCRIPTION
		"Destination IP address in range specified by premium flow de
		tection condition.(maximum IP address)"
	::= { axrFlowQosInPremEntry 23 }

axrFlowQosInPremDscp OBJECT-TYPE
	SYNTAX  INTEGER
	ACCESS  read-only
	STATUS  mandatory
	DESCRIPTION
		"The value of DSCP on premium flow detection condition."
	::= { axrFlowQosInPremEntry 24 }

axrFlowQosInPremPrecedence OBJECT-TYPE
	SYNTAX  INTEGER
	ACCESS  read-only
	STATUS  mandatory
	DESCRIPTION
		"The value of precedence on premium flow detection condition.
		"
	::= { axrFlowQosInPremEntry 25 }

axrFlowQosInPremUpperLength OBJECT-TYPE
	SYNTAX  INTEGER
	ACCESS  read-only
	STATUS  mandatory
	DESCRIPTION
		"The upper limit of IP user data length on premium flow detec
		tion condition. "
	::= { axrFlowQosInPremEntry 26 }

axrFlowQosInPremLowerLength OBJECT-TYPE
	SYNTAX  INTEGER
	ACCESS  read-only
	STATUS  mandatory
	DESCRIPTION
		"The lower limit of IP user data length on premium flow detec
		tion condition."
	::= { axrFlowQosInPremEntry 27 }

axrFlowQosInPremFragments OBJECT-TYPE
	SYNTAX  INTEGER
	ACCESS  read-only
	STATUS  mandatory
	DESCRIPTION
		"Indicates whether 2nd fragment packet or later are included 
		in premium flow detection condition."
	::= { axrFlowQosInPremEntry 28 }

axrFlowQosInPremSrcPortOp OBJECT-TYPE
	SYNTAX  INTEGER
	ACCESS  read-only
	STATUS  mandatory
	DESCRIPTION
		"Indicates specification method of source port number on prem
		ium flow detection condition."
	::= { axrFlowQosInPremEntry 29 }

axrFlowQosInPremSrcPort OBJECT-TYPE
	SYNTAX  INTEGER
	ACCESS  read-only
	STATUS  mandatory
	DESCRIPTION
		"Indicates source port number on premium flow detection condi
		tion."
	::= { axrFlowQosInPremEntry 30 }

axrFlowQosInPremSrcPortRange OBJECT-TYPE
	SYNTAX  INTEGER
	ACCESS  read-only
	STATUS  mandatory
	DESCRIPTION
		"Source port number in range specified by premium flow detect
		ion condition.(maximum port number)"
	::= { axrFlowQosInPremEntry 31 }

axrFlowQosInPremDestPortOp OBJECT-TYPE
	SYNTAX  INTEGER
	ACCESS  read-only
	STATUS  mandatory
	DESCRIPTION
		"Indicates specification method of destination port number on
		 premium flow detection condition."
	::= { axrFlowQosInPremEntry 32 }

axrFlowQosInPremDestPort OBJECT-TYPE
	SYNTAX  INTEGER
	ACCESS  read-only
	STATUS  mandatory
	DESCRIPTION
		"Indicates destination port number on premium flow detection 
		condition."
	::= { axrFlowQosInPremEntry 33 }

axrFlowQosInPremDestPortRange OBJECT-TYPE
	SYNTAX  INTEGER
	ACCESS  read-only
	STATUS  mandatory
	DESCRIPTION
		"destination port number in range specified by premium flow d
		etection condition.(maximum port number)"
	::= { axrFlowQosInPremEntry 34 }

axrFlowQosInPremAckFlag OBJECT-TYPE
	SYNTAX  INTEGER
	ACCESS  read-only
	STATUS  mandatory
	DESCRIPTION
		"Indicates whether TCP one-way communication permission is in
		cluded in premium flow detection condition or not."
	::= { axrFlowQosInPremEntry 35 }

axrFlowQosInPremSynFlag OBJECT-TYPE
	SYNTAX  INTEGER
	ACCESS  read-only
	STATUS  mandatory
	DESCRIPTION
		"Indicates whether virtual circuit link-up permission is incl
		uded in premium flow detection condition or not."
	::= { axrFlowQosInPremEntry 36 }

axrFlowQosInPremIcmpType OBJECT-TYPE
	SYNTAX  INTEGER
	ACCESS  read-only
	STATUS  mandatory
	DESCRIPTION
		"Indicates ICMP or ICMPv6 type on premium flow detection cond
		ition."
	::= { axrFlowQosInPremEntry 37 }

axrFlowQosInPremIcmpCode OBJECT-TYPE
	SYNTAX  INTEGER
	ACCESS  read-only
	STATUS  mandatory
	DESCRIPTION
		"Indicates ICMP or ICMPv6 code on premium flow detection cond
		ition."
	::= { axrFlowQosInPremEntry 38 }

axrFlowQosInPremIgmpType OBJECT-TYPE
	SYNTAX  INTEGER
	ACCESS  read-only
	STATUS  mandatory
	DESCRIPTION
		"Indicates IGMP type on premium flow detection condition."
	::= { axrFlowQosInPremEntry 39 }

axrFlowQosInPremLabelOp OBJECT-TYPE
	SYNTAX  INTEGER
	ACCESS  read-only
	STATUS  mandatory
	DESCRIPTION
		"Indicates the way to specify the label value in shim header on premium flow detection condition."
	::= { axrFlowQosInPremEntry 40 }

axrFlowQosInPremLabel OBJECT-TYPE
	SYNTAX  INTEGER
	ACCESS  read-only
	STATUS  mandatory
	DESCRIPTION
		"The label value in shim header on premium flow detection condition."
	::= { axrFlowQosInPremEntry 41 }

axrFlowQosInPremExp OBJECT-TYPE
	SYNTAX  INTEGER
	ACCESS  read-only
	STATUS  mandatory
	DESCRIPTION
		"The EXP value in shim header on premium flow detection condition."
	::= { axrFlowQosInPremEntry 42 }

axrFlowQosInPremSrcIpMask OBJECT-TYPE
	SYNTAX  InetAddress
	ACCESS  read-only
	STATUS  mandatory
	DESCRIPTION
		"Indicates mask of source IP address on premium flow detecti
		on specification."
	::= { axrFlowQosInPremEntry 43 }

axrFlowQosInPremDestIpMask OBJECT-TYPE
	SYNTAX  InetAddress
	ACCESS  read-only
	STATUS  mandatory
	DESCRIPTION
		"Indicates mask of destination IP address on premium flow de
		tection specification."
	::= { axrFlowQosInPremEntry 44 }

axrFlowQosOutTable OBJECT-TYPE
	SYNTAX  SEQUENCE OF AxrFlowQosOutEntry
	ACCESS  not-accessible
	STATUS  mandatory
	DESCRIPTION
		"Information of normal flow QoS detection condition table.(O
		utbound)"
	::= { axrFlowQos 3 }

axrFlowQosOutEntry OBJECT-TYPE
	SYNTAX  AxrFlowQosOutEntry
	ACCESS  not-accessible
	STATUS  mandatory
	DESCRIPTION
		"Entry of normal flow QoS detection condition."
	INDEX {
		axrFlowQosOutifIndex,
		axrFlowQosOutifIndexType,
		axrFlowQosOutListNumber
	}
	::= { axrFlowQosOutTable 1 }
	AxrFlowQosOutEntry ::= 
	    SEQUENCE {
		axrFlowQosOutifIndex
			INTEGER,
		axrFlowQosOutifIndexType
        	INTEGER,
		axrFlowQosOutListNumber
        	INTEGER,
		axrFlowQosOutSrcMacOp
        	INTEGER,
		axrFlowQosOutSrcMac
        	MacAddress,
		axrFlowQosOutSrcMacMask
        	MacAddress,
		axrFlowQosOutDestMacOp
        	INTEGER,
		axrFlowQosOutDestMac
        	MacAddress,
		axrFlowQosOutDestMacMask
        	MacAddress,
		axrFlowQosOutEthernetType
        	OCTET STRING,
		axrFlowQosOutUserPriority
        	INTEGER,
		axrFlowQosOutLowerVlanList
        	OCTET STRING,
		axrFlowQosOutHigherVlanList
        	OCTET STRING,
		axrFlowQosOutProtocolNumber
        	INTEGER,
		axrFlowQosOutIpAddrType
        	InetAddressType,
		axrFlowQosOutSrcIpOp
        	INTEGER,
		axrFlowQosOutSrcIp
        	InetAddress,
		axrFlowQosOutSrcIpLength
        	INTEGER,
		axrFlowQosOutSrcIpRange
        	InetAddress,
		axrFlowQosOutDestIpOp
        	INTEGER,
		axrFlowQosOutDestIp
        	InetAddress,
		axrFlowQosOutDestIpLength
        	INTEGER,
		axrFlowQosOutDestIpRange
        	InetAddress,
		axrFlowQosOutDscp
        	INTEGER,
		axrFlowQosOutPrecedence
        	INTEGER,
		axrFlowQosOutUpperLength
        	INTEGER,
		axrFlowQosOutLowerLength
        	INTEGER,
		axrFlowQosOutFragments
        	INTEGER,
		axrFlowQosOutSrcPortOp
        	INTEGER,
		axrFlowQosOutSrcPort
        	INTEGER,
		axrFlowQosOutSrcPortRange
        	INTEGER,
		axrFlowQosOutDestPortOp
        	INTEGER,
		axrFlowQosOutDestPort
        	INTEGER,
		axrFlowQosOutDestPortRange
        	INTEGER,
		axrFlowQosOutAckFlag
        	INTEGER,
		axrFlowQosOutSynFlag
        	INTEGER,
		axrFlowQosOutIcmpType
        	INTEGER,
		axrFlowQosOutIcmpCode
        	INTEGER,
		axrFlowQosOutIgmpType
        	INTEGER,
		axrFlowQosOutLabelOp
			INTEGER,
		axrFlowQosOutLabel
			INTEGER,
		axrFlowQosOutExp
			INTEGER,
		axrFlowQosOutSrcIpMask
			InetAddress,
		axrFlowQosOutDestIpMask
			InetAddress
        }

axrFlowQosOutifIndex OBJECT-TYPE
	SYNTAX  INTEGER
	ACCESS  not-accessible
	STATUS  mandatory
	DESCRIPTION
		"Indicates the value of index(ifIndex) which identifies this 
		table entry."
	::= { axrFlowQosOutEntry 1 }

axrFlowQosOutifIndexType OBJECT-TYPE
	SYNTAX  INTEGER
	ACCESS  not-accessible
	STATUS  mandatory
	DESCRIPTION
		"Indicates interface type.Physical port number : 1Interface n
		ame : 2(2)fixed."
	::= { axrFlowQosOutEntry 2 }

axrFlowQosOutListNumber OBJECT-TYPE
	SYNTAX  INTEGER
	ACCESS  not-accessible
	STATUS  mandatory
	DESCRIPTION
		"Indicates the value of index(list number) which identifies t
		his table entry."
	::= { axrFlowQosOutEntry 3 }

axrFlowQosOutSrcMacOp OBJECT-TYPE
	SYNTAX  INTEGER
	ACCESS  read-only
	STATUS  mandatory
	DESCRIPTION
		"Indicates specification method of source MAC address on norm
		al flow detection condition."
	::= { axrFlowQosOutEntry 4 }

axrFlowQosOutSrcMac OBJECT-TYPE
	SYNTAX  MacAddress
	ACCESS  read-only
	STATUS  mandatory
	DESCRIPTION
		"Indicates source MAC address on normal flow detection condi
		tion."
	::= { axrFlowQosOutEntry 5 }

axrFlowQosOutSrcMacMask OBJECT-TYPE
	SYNTAX  MacAddress
	ACCESS  read-only
	STATUS  mandatory
	DESCRIPTION
		"Indicates mask of source MAC address on normal flow detecti
		on specification."
	::= { axrFlowQosOutEntry 6 }

axrFlowQosOutDestMacOp OBJECT-TYPE
	SYNTAX  INTEGER
	ACCESS  read-only
	STATUS  mandatory
	DESCRIPTION
		"Indicates specification method of destination MAC address on
		 normal flow detection condition."
	::= { axrFlowQosOutEntry 7 }

axrFlowQosOutDestMac OBJECT-TYPE
	SYNTAX  MacAddress
	ACCESS  read-only
	STATUS  mandatory
	DESCRIPTION
		"Indicates destination MAC address on normal flow detection 
		condition."
	::= { axrFlowQosOutEntry 8 }

axrFlowQosOutDestMacMask OBJECT-TYPE
	SYNTAX  MacAddress
	ACCESS  read-only
	STATUS  mandatory
	DESCRIPTION
		"Indicates mask of destination MAC address on normal flow de
		tection specification."
	::= { axrFlowQosOutEntry 9 }

axrFlowQosOutEthernetType OBJECT-TYPE
	SYNTAX  OCTET STRING
	ACCESS  read-only
	STATUS  mandatory
	DESCRIPTION
		"Indicates type of ethernet V2 and IEEE802.3 SNAP/RFC1042 for
		m on normal flow detection condition."
	::= { axrFlowQosOutEntry 10 }

axrFlowQosOutUserPriority OBJECT-TYPE
	SYNTAX  INTEGER
	ACCESS  read-only
	STATUS  mandatory
	DESCRIPTION
		"Indicates user priority in Tag-VLAN on normal detection con
		dition."
	::= { axrFlowQosOutEntry 11 }

axrFlowQosOutLowerVlanList OBJECT-TYPE
	SYNTAX  OCTET STRING
	ACCESS  read-only
	STATUS  mandatory
	DESCRIPTION
		"Bit map representation of VLAN ID on normal flow detection 
		condition.(Head 1 bit indicates existence of untagged definit
		ion, and the rest effective or non-effective of VLAN 1-2047.)
		"
	::= { axrFlowQosOutEntry 12 }

axrFlowQosOutHigherVlanList OBJECT-TYPE
	SYNTAX  OCTET STRING
	ACCESS  read-only
	STATUS  mandatory
	DESCRIPTION
		"Bit map representation of VLAN ID on normal flow detection 
		condition.(Each bit indicates whether VLAN 2048-4095 is effec
		tive or non-effective in order.)"
	::= { axrFlowQosOutEntry 13 }

axrFlowQosOutProtocolNumber OBJECT-TYPE
	SYNTAX  INTEGER
	ACCESS  read-only
	STATUS  mandatory
	DESCRIPTION
		"Indicates upper protocol number on normal flow detection co
		ndition."
	::= { axrFlowQosOutEntry 14 }

axrFlowQosOutIpAddrType OBJECT-TYPE
	SYNTAX  InetAddressType
	ACCESS  read-only
	STATUS  mandatory
	DESCRIPTION
		"Indicates IP address type which is shown."
	::= { axrFlowQosOutEntry 15 }

axrFlowQosOutSrcIpOp OBJECT-TYPE
	SYNTAX  INTEGER
	ACCESS  read-only
	STATUS  mandatory
	DESCRIPTION
		"Indicates specification method of source IP address on norma
		l flow detection condition."
	::= { axrFlowQosOutEntry 16 }

axrFlowQosOutSrcIp OBJECT-TYPE
	SYNTAX  InetAddress
	ACCESS  read-only
	STATUS  mandatory
	DESCRIPTION
		"Indicates source IP address on normal flow detection condit
		ion."
	::= { axrFlowQosOutEntry 17 }

axrFlowQosOutSrcIpLength OBJECT-TYPE
	SYNTAX  INTEGER
	ACCESS  read-only
	STATUS  mandatory
	DESCRIPTION
		"Indicates subnet mask length(ipv4) or prefix length(ipv6) of
		 source IP address on normal flow detection condition."
	::= { axrFlowQosOutEntry 18 }

axrFlowQosOutSrcIpRange OBJECT-TYPE
	SYNTAX  InetAddress
	ACCESS  read-only
	STATUS  mandatory
	DESCRIPTION
		"Source IP address in range specified by normal flow detecti
		on condition.(maximum IP address)"
	::= { axrFlowQosOutEntry 19 }

axrFlowQosOutDestIpOp OBJECT-TYPE
	SYNTAX  INTEGER
	ACCESS  read-only
	STATUS  mandatory
	DESCRIPTION
		"Indicates specification method of destination IP address on 
		normal flow detection condition."
	::= { axrFlowQosOutEntry 20 }

axrFlowQosOutDestIp OBJECT-TYPE
	SYNTAX  InetAddress
	ACCESS  read-only
	STATUS  mandatory
	DESCRIPTION
		"Indicates destination IP address on normal flow detection c
		ondition."
	::= { axrFlowQosOutEntry 21 }

axrFlowQosOutDestIpLength OBJECT-TYPE
	SYNTAX  INTEGER
	ACCESS  read-only
	STATUS  mandatory
	DESCRIPTION
		"Indicates subnet mask length(ipv4) or prefix length(ipv6) of
		 destination IP address on normal flow detection condition."
	::= { axrFlowQosOutEntry 22 }

axrFlowQosOutDestIpRange OBJECT-TYPE
	SYNTAX  InetAddress
	ACCESS  read-only
	STATUS  mandatory
	DESCRIPTION
		"Destination IP address in range specified by normal flow de
		tection condition.(maximum IP address)"
	::= { axrFlowQosOutEntry 23 }

axrFlowQosOutDscp OBJECT-TYPE
	SYNTAX  INTEGER
	ACCESS  read-only
	STATUS  mandatory
	DESCRIPTION
		"The value of DSCP on normal flow detection condition."
	::= { axrFlowQosOutEntry 24 }

axrFlowQosOutPrecedence OBJECT-TYPE
	SYNTAX  INTEGER
	ACCESS  read-only
	STATUS  mandatory
	DESCRIPTION
		"The value of precedence on normal flow detection condition.
		"
	::= { axrFlowQosOutEntry 25 }

axrFlowQosOutUpperLength OBJECT-TYPE
	SYNTAX  INTEGER
	ACCESS  read-only
	STATUS  mandatory
	DESCRIPTION
		"The upper limit of IP user data length on normal flow detec
		tion condition. "
	::= { axrFlowQosOutEntry 26 }

axrFlowQosOutLowerLength OBJECT-TYPE
	SYNTAX  INTEGER
	ACCESS  read-only
	STATUS  mandatory
	DESCRIPTION
		"The lower limit of IP user data length on normal flow detec
		tion condition."
	::= { axrFlowQosOutEntry 27 }

axrFlowQosOutFragments OBJECT-TYPE
	SYNTAX  INTEGER
	ACCESS  read-only
	STATUS  mandatory
	DESCRIPTION
		"Indicates whether 2nd fragment packet or later are included 
		in normal flow detection condition."
	::= { axrFlowQosOutEntry 28 }

axrFlowQosOutSrcPortOp OBJECT-TYPE
	SYNTAX  INTEGER
	ACCESS  read-only
	STATUS  mandatory
	DESCRIPTION
		"Indicates specification method of source port number on norm
		al flow detection condition."
	::= { axrFlowQosOutEntry 29 }

axrFlowQosOutSrcPort OBJECT-TYPE
	SYNTAX  INTEGER
	ACCESS  read-only
	STATUS  mandatory
	DESCRIPTION
		"Indicates source port number on normal flow detection condi
		tion."
	::= { axrFlowQosOutEntry 30 }

axrFlowQosOutSrcPortRange OBJECT-TYPE
	SYNTAX  INTEGER
	ACCESS  read-only
	STATUS  mandatory
	DESCRIPTION
		"Source port number in range specified by normal flow detect
		ion condition.(maximum port number)"
	::= { axrFlowQosOutEntry 31 }

axrFlowQosOutDestPortOp OBJECT-TYPE
	SYNTAX  INTEGER
	ACCESS  read-only
	STATUS  mandatory
	DESCRIPTION
		"Indicates specification method of destination port number on
		 normal flow detection condition."
	::= { axrFlowQosOutEntry 32 }

axrFlowQosOutDestPort OBJECT-TYPE
	SYNTAX  INTEGER
	ACCESS  read-only
	STATUS  mandatory
	DESCRIPTION
		"Indicates destination port number on normal flow detection 
		condition."
	::= { axrFlowQosOutEntry 33 }

axrFlowQosOutDestPortRange OBJECT-TYPE
	SYNTAX  INTEGER
	ACCESS  read-only
	STATUS  mandatory
	DESCRIPTION
		"destination port number in range specified by normal flow d
		etection condition.(maximum port number)"
	::= { axrFlowQosOutEntry 34 }

axrFlowQosOutAckFlag OBJECT-TYPE
	SYNTAX  INTEGER
	ACCESS  read-only
	STATUS  mandatory
	DESCRIPTION
		"Indicates whether TCP one-way communication permission is in
		cluded in normal flow detection condition or not."
	::= { axrFlowQosOutEntry 35 }

axrFlowQosOutSynFlag OBJECT-TYPE
	SYNTAX  INTEGER
	ACCESS  read-only
	STATUS  mandatory
	DESCRIPTION
		"Indicates whether virtual circuit link-up permission is incl
		uded in normal flow detection condition or not."
	::= { axrFlowQosOutEntry 36 }

axrFlowQosOutIcmpType OBJECT-TYPE
	SYNTAX  INTEGER
	ACCESS  read-only
	STATUS  mandatory
	DESCRIPTION
		"Indicates ICMP or ICMPv6 type on normal flow detection cond
		ition."
	::= { axrFlowQosOutEntry 37 }

axrFlowQosOutIcmpCode OBJECT-TYPE
	SYNTAX  INTEGER
	ACCESS  read-only
	STATUS  mandatory
	DESCRIPTION
		"Indicates ICMP or ICMPv6 code on normal flow detection cond
		ition."
	::= { axrFlowQosOutEntry 38 }

axrFlowQosOutIgmpType OBJECT-TYPE
	SYNTAX  INTEGER
	ACCESS  read-only
	STATUS  mandatory
	DESCRIPTION
		"Indicates IGMP type on normal flow detection condition."
	::= { axrFlowQosOutEntry 39 }

axrFlowQosOutLabelOp OBJECT-TYPE
	SYNTAX  INTEGER
	ACCESS  read-only
	STATUS  mandatory
	DESCRIPTION
		"Indicates the way to specify the label value in shim header on normal flow detection condition."
	::= { axrFlowQosOutEntry 40 }

axrFlowQosOutLabel OBJECT-TYPE
	SYNTAX  INTEGER
	ACCESS  read-only
	STATUS  mandatory
	DESCRIPTION
		"The label value in shim header on normal flow detection condition."
	::= { axrFlowQosOutEntry 41 }

axrFlowQosOutExp OBJECT-TYPE
	SYNTAX  INTEGER
	ACCESS  read-only
	STATUS  mandatory
	DESCRIPTION
		"The EXP value in shim header on normal flow detection condition."
	::= { axrFlowQosOutEntry 42 }

axrFlowQosOutSrcIpMask OBJECT-TYPE
	SYNTAX  InetAddress
	ACCESS  read-only
	STATUS  mandatory
	DESCRIPTION
		"Indicates mask of source IP address on normal flow detecti
		on specification."
	::= { axrFlowQosOutEntry 43 }

axrFlowQosOutDestIpMask OBJECT-TYPE
	SYNTAX  InetAddress
	ACCESS  read-only
	STATUS  mandatory
	DESCRIPTION
		"Indicates mask of destination IP address on normal flow de
		tection specification."
	::= { axrFlowQosOutEntry 44 }

axrFlowQosOutPremTable OBJECT-TYPE
	SYNTAX  SEQUENCE OF AxrFlowQosOutPremEntry
	ACCESS  not-accessible
	STATUS  mandatory
	DESCRIPTION
		"Information of premium flow QoS detection condition table.(O
		utbound)"
	::= { axrFlowQos 4 }

axrFlowQosOutPremEntry OBJECT-TYPE
	SYNTAX  AxrFlowQosOutPremEntry
	ACCESS  not-accessible
	STATUS  mandatory
	DESCRIPTION
		"Entry of premium flow QoS detection condition."
	INDEX {
		axrFlowQosOutPremifIndex,
		axrFlowQosOutPremifIndexType,
		axrFlowQosOutPremListNumber
	}
	::= { axrFlowQosOutPremTable 1 }
	AxrFlowQosOutPremEntry ::= 
	    SEQUENCE {
		axrFlowQosOutPremifIndex
			INTEGER,
		axrFlowQosOutPremifIndexType
        	INTEGER,
		axrFlowQosOutPremListNumber
        	INTEGER,
		axrFlowQosOutPremSrcMacOp
        	INTEGER,
		axrFlowQosOutPremSrcMac
        	MacAddress,
		axrFlowQosOutPremSrcMacMask
        	MacAddress,
		axrFlowQosOutPremDestMacOp
        	INTEGER,
		axrFlowQosOutPremDestMac
        	MacAddress,
		axrFlowQosOutPremDestMacMask
        	MacAddress,
		axrFlowQosOutPremEthernetType
        	OCTET STRING,
		axrFlowQosOutPremUserPriority
        	INTEGER,
		axrFlowQosOutPremLowerVlanList
        	OCTET STRING,
		axrFlowQosOutPremHigherVlanList
        	OCTET STRING,
		axrFlowQosOutPremProtocolNumber
        	INTEGER,
		axrFlowQosOutPremIpAddrType
        	InetAddress,
		axrFlowQosOutPremSrcIpOp
        	INTEGER,
		axrFlowQosOutPremSrcIp
        	InetAddress,
		axrFlowQosOutPremSrcIpLength
        	INTEGER,
		axrFlowQosOutPremSrcIpRange
        	InetAddress,
		axrFlowQosOutPremDestIpOp
        	INTEGER,
		axrFlowQosOutPremDestIp
        	InetAddress,
		axrFlowQosOutPremDestIpLength
        	INTEGER,
		axrFlowQosOutPremDestIpRange
        	InetAddress,
		axrFlowQosOutPremDscp
        	INTEGER,
		axrFlowQosOutPremPrecedence
        	INTEGER,
		axrFlowQosOutPremUpperLength
        	INTEGER,
		axrFlowQosOutPremLowerLength
        	INTEGER,
		axrFlowQosOutPremFragments
        	INTEGER,
		axrFlowQosOutPremSrcPortOp
        	INTEGER,
		axrFlowQosOutPremSrcPort
        	INTEGER,
		axrFlowQosOutPremSrcPortRange
        	INTEGER,
		axrFlowQosOutPremDestPortOp
        	INTEGER,
		axrFlowQosOutPremDestPort
        	INTEGER,
		axrFlowQosOutPremDestPortRange
        	INTEGER,
		axrFlowQosOutPremAckFlag
        	INTEGER,
		axrFlowQosOutPremSynFlag
        	INTEGER,
		axrFlowQosOutPremIcmpType
        	INTEGER,
		axrFlowQosOutPremIcmpCode
        	INTEGER,
		axrFlowQosOutPremIgmpType
        	INTEGER,
		axrFlowQosOutPremLabelOp
			INTEGER,
		axrFlowQosOutPremLabel
			INTEGER,
		axrFlowQosOutPremExp
			INTEGER,
		axrFlowQosOutPremSrcIpMask
			InetAddress,
		axrFlowQosOutPremDestIpMask
			InetAddress
        }

axrFlowQosOutPremifIndex OBJECT-TYPE
	SYNTAX  INTEGER
	ACCESS  not-accessible
	STATUS  mandatory
	DESCRIPTION
		"Indicates the value of index(ifIndex) which identifies this 
		table entry."
	::= { axrFlowQosOutPremEntry 1 }

axrFlowQosOutPremifIndexType OBJECT-TYPE
	SYNTAX  INTEGER
	ACCESS  not-accessible
	STATUS  mandatory
	DESCRIPTION
		"Indicates interface type.Physical port number : 1Interface n
		ame : 2(2)fixed."
	::= { axrFlowQosOutPremEntry 2 }

axrFlowQosOutPremListNumber OBJECT-TYPE
	SYNTAX  INTEGER
	ACCESS  not-accessible
	STATUS  mandatory
	DESCRIPTION
		"Indicates the value of index(list number) which identifies t
		his table entry."
	::= { axrFlowQosOutPremEntry 3 }

axrFlowQosOutPremSrcMacOp OBJECT-TYPE
	SYNTAX  INTEGER
	ACCESS  read-only
	STATUS  mandatory
	DESCRIPTION
		"Indicates specification method of source MAC address on prem
		ium flow detection condition."
	::= { axrFlowQosOutPremEntry 4 }

axrFlowQosOutPremSrcMac OBJECT-TYPE
	SYNTAX  MacAddress
	ACCESS  read-only
	STATUS  mandatory
	DESCRIPTION
		"Indicates source MAC address on premium flow detection condi
		tion."
	::= { axrFlowQosOutPremEntry 5 }

axrFlowQosOutPremSrcMacMask OBJECT-TYPE
	SYNTAX  MacAddress
	ACCESS  read-only
	STATUS  mandatory
	DESCRIPTION
		"Indicates mask of source MAC address on premium flow detecti
		on specification."
	::= { axrFlowQosOutPremEntry 6 }

axrFlowQosOutPremDestMacOp OBJECT-TYPE
	SYNTAX  INTEGER
	ACCESS  read-only
	STATUS  mandatory
	DESCRIPTION
		"Indicates specification method of destination MAC address on
		 premium flow detection condition."
	::= { axrFlowQosOutPremEntry 7 }

axrFlowQosOutPremDestMac OBJECT-TYPE
	SYNTAX  MacAddress
	ACCESS  read-only
	STATUS  mandatory
	DESCRIPTION
		"Indicates destination MAC address on premium flow detection 
		condition."
	::= { axrFlowQosOutPremEntry 8 }

axrFlowQosOutPremDestMacMask OBJECT-TYPE
	SYNTAX  MacAddress
	ACCESS  read-only
	STATUS  mandatory
	DESCRIPTION
		"Indicates mask of destination MAC address on premium flow de
		tection specification."
	::= { axrFlowQosOutPremEntry 9 }

axrFlowQosOutPremEthernetType OBJECT-TYPE
	SYNTAX  OCTET STRING
	ACCESS  read-only
	STATUS  mandatory
	DESCRIPTION
		"Indicates type of ethernet V2 and IEEE802.3 SNAP/RFC1042 for
		m on premium flow detection condition."
	::= { axrFlowQosOutPremEntry 10 }

axrFlowQosOutPremUserPriority OBJECT-TYPE
	SYNTAX  INTEGER
	ACCESS  read-only
	STATUS  mandatory
	DESCRIPTION
		"Indicates user priority in Tag-VLAN on premium flow detectio
		n condition."
	::= { axrFlowQosOutPremEntry 11 }

axrFlowQosOutPremLowerVlanList OBJECT-TYPE
	SYNTAX  OCTET STRING
	ACCESS  read-only
	STATUS  mandatory
	DESCRIPTION
		"Bit map representation of VLAN ID on premium flow detection 
		condition.(Head 1 bit indicates existence of untagged definit
		ion, and the rest effective or non-effective of VLAN 1-2047.)
		"
	::= { axrFlowQosOutPremEntry 12 }

axrFlowQosOutPremHigherVlanList OBJECT-TYPE
	SYNTAX  OCTET STRING
	ACCESS  read-only
	STATUS  mandatory
	DESCRIPTION
		"Bit map representation of VLAN ID on premium flow detection 
		condition.(Each bit indicates whether VLAN 2048-4095 is effec
		tive or non-effective in order.)"
	::= { axrFlowQosOutPremEntry 13 }

axrFlowQosOutPremProtocolNumber OBJECT-TYPE
	SYNTAX  INTEGER
	ACCESS  read-only
	STATUS  mandatory
	DESCRIPTION
		"Indicates upper protocol number on premium flow detection co
		ndition."
	::= { axrFlowQosOutPremEntry 14 }

axrFlowQosOutPremIpAddrType OBJECT-TYPE
	SYNTAX  InetAddress
	ACCESS  read-only
	STATUS  mandatory
	DESCRIPTION
		"Shown IP address type."
	::= { axrFlowQosOutPremEntry 15 }

axrFlowQosOutPremSrcIpOp OBJECT-TYPE
	SYNTAX  INTEGER
	ACCESS  read-only
	STATUS  mandatory
	DESCRIPTION
		"Indicates specification method of source IP address on premi
		um flow detection condition."
	::= { axrFlowQosOutPremEntry 16 }

axrFlowQosOutPremSrcIp OBJECT-TYPE
	SYNTAX  InetAddress
	ACCESS  read-only
	STATUS  mandatory
	DESCRIPTION
		"Indicates source IP address on premium flow detection condit
		ion."
	::= { axrFlowQosOutPremEntry 17 }

axrFlowQosOutPremSrcIpLength OBJECT-TYPE
	SYNTAX  INTEGER
	ACCESS  read-only
	STATUS  mandatory
	DESCRIPTION
		"Indicates subnet mask length(ipv4) or prefix length(ipv6) of
		 source IP address on premium flow detection condition."
	::= { axrFlowQosOutPremEntry 18 }

axrFlowQosOutPremSrcIpRange OBJECT-TYPE
	SYNTAX  InetAddress
	ACCESS  read-only
	STATUS  mandatory
	DESCRIPTION
		"Source IP address in range specified by premium flow detecti
		on condition.(maximum IP address)"
	::= { axrFlowQosOutPremEntry 19 }

axrFlowQosOutPremDestIpOp OBJECT-TYPE
	SYNTAX  INTEGER
	ACCESS  read-only
	STATUS  mandatory
	DESCRIPTION
		"Indicates specification method of destination IP address on 
		premium flow detection condition."
	::= { axrFlowQosOutPremEntry 20 }

axrFlowQosOutPremDestIp OBJECT-TYPE
	SYNTAX  InetAddress
	ACCESS  read-only
	STATUS  mandatory
	DESCRIPTION
		"Indicates destination IP address on premium flow detection c
		ondition."
	::= { axrFlowQosOutPremEntry 21 }

axrFlowQosOutPremDestIpLength OBJECT-TYPE
	SYNTAX  INTEGER
	ACCESS  read-only
	STATUS  mandatory
	DESCRIPTION
		"Indicates subnet mask length(ipv4) or prefix length(ipv6) of
		 destination IP address on premium flow detection condition."
	::= { axrFlowQosOutPremEntry 22 }

axrFlowQosOutPremDestIpRange OBJECT-TYPE
	SYNTAX  InetAddress
	ACCESS  read-only
	STATUS  mandatory
	DESCRIPTION
		"Destination IP address in range specified by premium flow de
		tection condition.(maximum IP address)"
	::= { axrFlowQosOutPremEntry 23 }

axrFlowQosOutPremDscp OBJECT-TYPE
	SYNTAX  INTEGER
	ACCESS  read-only
	STATUS  mandatory
	DESCRIPTION
		"The value of DSCP on premium flow detection condition."
	::= { axrFlowQosOutPremEntry 24 }

axrFlowQosOutPremPrecedence OBJECT-TYPE
	SYNTAX  INTEGER
	ACCESS  read-only
	STATUS  mandatory
	DESCRIPTION
		"The value of precedence on premium flow detection condition.
		"
	::= { axrFlowQosOutPremEntry 25 }

axrFlowQosOutPremUpperLength OBJECT-TYPE
	SYNTAX  INTEGER
	ACCESS  read-only
	STATUS  mandatory
	DESCRIPTION
		"The upper limit of IP user data length on premium flow detec
		tion condition. "
	::= { axrFlowQosOutPremEntry 26 }

axrFlowQosOutPremLowerLength OBJECT-TYPE
	SYNTAX  INTEGER
	ACCESS  read-only
	STATUS  mandatory
	DESCRIPTION
		"The lower limit of IP user data length on premium flow detec
		tion condition."
	::= { axrFlowQosOutPremEntry 27 }

axrFlowQosOutPremFragments OBJECT-TYPE
	SYNTAX  INTEGER
	ACCESS  read-only
	STATUS  mandatory
	DESCRIPTION
		"Indicates whether 2nd fragment packet or later are included 
		in premium flow detection condition."
	::= { axrFlowQosOutPremEntry 28 }

axrFlowQosOutPremSrcPortOp OBJECT-TYPE
	SYNTAX  INTEGER
	ACCESS  read-only
	STATUS  mandatory
	DESCRIPTION
		"Indicates specification method of source port number on prem
		ium flow detection condition."
	::= { axrFlowQosOutPremEntry 29 }

axrFlowQosOutPremSrcPort OBJECT-TYPE
	SYNTAX  INTEGER
	ACCESS  read-only
	STATUS  mandatory
	DESCRIPTION
		"Indicates source port number on premium flow detection condi
		tion."
	::= { axrFlowQosOutPremEntry 30 }

axrFlowQosOutPremSrcPortRange OBJECT-TYPE
	SYNTAX  INTEGER
	ACCESS  read-only
	STATUS  mandatory
	DESCRIPTION
		"Source port number in range specified by premium flow detect
		ion condition.(maximum port number)"
	::= { axrFlowQosOutPremEntry 31 }

axrFlowQosOutPremDestPortOp OBJECT-TYPE
	SYNTAX  INTEGER
	ACCESS  read-only
	STATUS  mandatory
	DESCRIPTION
		"Indicates specification method of destination port number on
		 premium flow detection condition."
	::= { axrFlowQosOutPremEntry 32 }

axrFlowQosOutPremDestPort OBJECT-TYPE
	SYNTAX  INTEGER
	ACCESS  read-only
	STATUS  mandatory
	DESCRIPTION
		"Indicates destination port number on premium flow detection 
		condition."
	::= { axrFlowQosOutPremEntry 33 }

axrFlowQosOutPremDestPortRange OBJECT-TYPE
	SYNTAX  INTEGER
	ACCESS  read-only
	STATUS  mandatory
	DESCRIPTION
		"destination port number in range specified by premium flow d
		etection condition.(maximum port number)"
	::= { axrFlowQosOutPremEntry 34 }

axrFlowQosOutPremAckFlag OBJECT-TYPE
	SYNTAX  INTEGER
	ACCESS  read-only
	STATUS  mandatory
	DESCRIPTION
		"Indicates whether TCP one-way communication permission is in
		cluded in premium flow detection condition or not."
	::= { axrFlowQosOutPremEntry 35 }

axrFlowQosOutPremSynFlag OBJECT-TYPE
	SYNTAX  INTEGER
	ACCESS  read-only
	STATUS  mandatory
	DESCRIPTION
		"Indicates whether virtual circuit link-up permission is incl
		uded in premium flow detection condition or not."
	::= { axrFlowQosOutPremEntry 36 }

axrFlowQosOutPremIcmpType OBJECT-TYPE
	SYNTAX  INTEGER
	ACCESS  read-only
	STATUS  mandatory
	DESCRIPTION
		"Indicates ICMP or ICMPv6 type on premium flow detection cond
		ition."
	::= { axrFlowQosOutPremEntry 37 }

axrFlowQosOutPremIcmpCode OBJECT-TYPE
	SYNTAX  INTEGER
	ACCESS  read-only
	STATUS  mandatory
	DESCRIPTION
		"Indicates ICMP or ICMPv6 code on premium flow detection cond
		ition."
	::= { axrFlowQosOutPremEntry 38 }

axrFlowQosOutPremIgmpType OBJECT-TYPE
	SYNTAX  INTEGER
	ACCESS  read-only
	STATUS  mandatory
	DESCRIPTION
		"Indicates IGMP type on premium flow detection condition."
	::= { axrFlowQosOutPremEntry 39 }

axrFlowQosOutPremLabelOp OBJECT-TYPE
	SYNTAX  INTEGER
	ACCESS  read-only
	STATUS  mandatory
	DESCRIPTION
		"Indicates the way to specify the label value in shim header on premium flow detection condition."
	::= { axrFlowQosOutPremEntry 40 }

axrFlowQosOutPremLabel OBJECT-TYPE
	SYNTAX  INTEGER
	ACCESS  read-only
	STATUS  mandatory
	DESCRIPTION
		"The label value in shim header on premium flow detection condition."
	::= { axrFlowQosOutPremEntry 41 }

axrFlowQosOutPremExp OBJECT-TYPE
	SYNTAX  INTEGER
	ACCESS  read-only
	STATUS  mandatory
	DESCRIPTION
		"The EXP value in shim header on premium flow detection condition."
	::= { axrFlowQosOutPremEntry 42 }

axrFlowQosOutPremSrcIpMask OBJECT-TYPE
	SYNTAX  InetAddress
	ACCESS  read-only
	STATUS  mandatory
	DESCRIPTION
		"Indicates mask of source IP address on premium flow detecti
		on specification."
	::= { axrFlowQosOutPremEntry 43 }

axrFlowQosOutPremDestIpMask OBJECT-TYPE
	SYNTAX  InetAddress
	ACCESS  read-only
	STATUS  mandatory
	DESCRIPTION
		"Indicates mask of destination IP address on premium flow de
		tection specification."
	::= { axrFlowQosOutPremEntry 44 }

axrFlowQosInActTable OBJECT-TYPE
	SYNTAX  SEQUENCE OF AxrFlowQosInActEntry
	ACCESS  not-accessible
	STATUS  mandatory
	DESCRIPTION
		"Information of action parameter table on normal flow detect
		ion condition.(Inbound)"
	::= { axrFlowQos 5 }

axrFlowQosInActEntry OBJECT-TYPE
	SYNTAX  AxrFlowQosInActEntry
	ACCESS  not-accessible
	STATUS  mandatory
	DESCRIPTION
		"Entry of action parameter on normal flow detection conditio
		n.(Inbound)"
	INDEX {
		axrFlowQosInActifIndex,
		axrFlowQosInActifIndexType,
		axrFlowQosInActListNumber
	}
	::= { axrFlowQosInActTable 1 }
	AxrFlowQosInActEntry ::= 
	    SEQUENCE {
		axrFlowQosInActifIndex
			INTEGER,
		axrFlowQosInActifIndexType
        	INTEGER,
		axrFlowQosInActListNumber
        	INTEGER,
		axrFlowQosInActMaxRate
        	INTEGER,
		axrFlowQosInActMaxRateBurst
        	INTEGER,
		axrFlowQosInActMaxUpcRedMinBurst
        	INTEGER,
		axrFlowQosInActMaxUpcRedMaxBurst
        	INTEGER,
		axrFlowQosInActMaxUpcRedProbability
        	INTEGER,
		axrFlowQosInActMinRate
        	INTEGER,
		axrFlowQosInActMinRateBurst
        	INTEGER,
		axrFlowQosInActMinUpcRedMinBurst
        	INTEGER,
		axrFlowQosInActMinUpcRedMaxBurst
        	INTEGER,
		axrFlowQosInActMinUpcRedProbability
        	INTEGER,
		axrFlowQosInActAgQueueOp
        	INTEGER,
		axrFlowQosInActAgQueue
        	INTEGER,
		axrFlowQosInActPriority
        	INTEGER,
		axrFlowQosInActMaxUnderPriority
        	INTEGER,
		axrFlowQosInActMinOverPriority
        	INTEGER,
		axrFlowQosInActMinUnderPriority
        	INTEGER,
		axrFlowQosInActDiscard
        	INTEGER,
		axrFlowQosInActMaxUnderDiscard
        	INTEGER,
		axrFlowQosInActMinOverDiscard
        	INTEGER,
		axrFlowQosInActMinUnderDiscard
        	INTEGER,
		axrFlowQosInActDscpOp
        	INTEGER,
		axrFlowQosInActDscp
        	INTEGER,
		axrFlowQosInActMaxUnderDscp
        	INTEGER,
		axrFlowQosInActMinOverDscp
        	INTEGER,
		axrFlowQosInActMinUnderDscp
        	INTEGER,
		axrFlowQosInActUserPriority
        	INTEGER,
		axrFlowQosInActMaxUnderUserPriority
        	INTEGER,
		axrFlowQosInActMinOverUserPriority
        	INTEGER,
		axrFlowQosInActMinUnderUserPriority
        	INTEGER,
		axrFlowQosInActExp
			INTEGER,
		axrFlowQosInActMaxUnderExp
			INTEGER,
		axrFlowQosInActMinOverExp
			INTEGER,
		axrFlowQosInActMinUnderExp
			INTEGER
        }

axrFlowQosInActifIndex OBJECT-TYPE
	SYNTAX  INTEGER
	ACCESS  not-accessible
	STATUS  mandatory
	DESCRIPTION
		"Indicates the value of index(ifIndex) which identifies this 
		table entry."
	::= { axrFlowQosInActEntry 1 }

axrFlowQosInActifIndexType OBJECT-TYPE
	SYNTAX  INTEGER
	ACCESS  not-accessible
	STATUS  mandatory
	DESCRIPTION
		"Indicates interface type.Physical port number : 1Interface n
		ame : 2"
	::= { axrFlowQosInActEntry 2 }

axrFlowQosInActListNumber OBJECT-TYPE
	SYNTAX  INTEGER
	ACCESS  not-accessible
	STATUS  mandatory
	DESCRIPTION
		"Indicates the value of index(list number) which identifies t
		his table entry."
	::= { axrFlowQosInActEntry 3 }

axrFlowQosInActMaxRate OBJECT-TYPE
	SYNTAX  INTEGER
	ACCESS  read-only
	STATUS  mandatory
	DESCRIPTION
		"The value of monitoring bandwidth under maximum bandwidth co
		ntrol."
	::= { axrFlowQosInActEntry 4 }

axrFlowQosInActMaxRateBurst OBJECT-TYPE
	SYNTAX  INTEGER
	ACCESS  read-only
	STATUS  mandatory
	DESCRIPTION
		"Burst size under maximum bandwidth control."
	::= { axrFlowQosInActEntry 5 }

axrFlowQosInActMaxUpcRedMinBurst OBJECT-TYPE
	SYNTAX  INTEGER
	ACCESS  read-only
	STATUS  mandatory
	DESCRIPTION
		"Minimum burst size while using UPC-RED(Max) function."
	::= { axrFlowQosInActEntry 6 }

axrFlowQosInActMaxUpcRedMaxBurst OBJECT-TYPE
	SYNTAX  INTEGER
	ACCESS  read-only
	STATUS  mandatory
	DESCRIPTION
		"Maximum burst size while using UPC-RED(Max) function."
	::= { axrFlowQosInActEntry 7 }

axrFlowQosInActMaxUpcRedProbability OBJECT-TYPE
	SYNTAX  INTEGER
	ACCESS  read-only
	STATUS  mandatory
	DESCRIPTION
		"Maximum violation rate while using UPC-RED(Max) function."
	::= { axrFlowQosInActEntry 8 }

axrFlowQosInActMinRate OBJECT-TYPE
	SYNTAX  INTEGER
	ACCESS  read-only
	STATUS  mandatory
	DESCRIPTION
		"The value of monitoring bandwidth under minimum bandwidth co
		ntrol."
	::= { axrFlowQosInActEntry 9 }

axrFlowQosInActMinRateBurst OBJECT-TYPE
	SYNTAX  INTEGER
	ACCESS  read-only
	STATUS  mandatory
	DESCRIPTION
		"Burst size under minimum bandwidth control."
	::= { axrFlowQosInActEntry 10 }

axrFlowQosInActMinUpcRedMinBurst OBJECT-TYPE
	SYNTAX  INTEGER
	ACCESS  read-only
	STATUS  mandatory
	DESCRIPTION
		"Minimum burst size while using UPC-RED(Min) function."
	::= { axrFlowQosInActEntry 11 }

axrFlowQosInActMinUpcRedMaxBurst OBJECT-TYPE
	SYNTAX  INTEGER
	ACCESS  read-only
	STATUS  mandatory
	DESCRIPTION
		"Maximum burst size while using UPC-RED(Min) function."
	::= { axrFlowQosInActEntry 12 }

axrFlowQosInActMinUpcRedProbability OBJECT-TYPE
	SYNTAX  INTEGER
	ACCESS  read-only
	STATUS  mandatory
	DESCRIPTION
		"Maximum violation rate while using UPC-RED(Min) function."
	::= { axrFlowQosInActEntry 13 }

axrFlowQosInActAgQueueOp OBJECT-TYPE
	SYNTAX  INTEGER
	ACCESS  read-only
	STATUS  mandatory
	DESCRIPTION
		"Indicates specification method of aggregate queue number of 
		layered shaper."
	::= { axrFlowQosInActEntry 14 }

axrFlowQosInActAgQueue OBJECT-TYPE
	SYNTAX  INTEGER
	ACCESS  read-only
	STATUS  mandatory
	DESCRIPTION
		"Aggregate queue number of layered shaper."
	::= { axrFlowQosInActEntry 15 }

axrFlowQosInActPriority OBJECT-TYPE
	SYNTAX  INTEGER
	ACCESS  read-only
	STATUS  mandatory
	DESCRIPTION
		"Output priority when bandwidth monitoring function is not us
		ed."
	::= { axrFlowQosInActEntry 16 }

axrFlowQosInActMaxUnderPriority OBJECT-TYPE
	SYNTAX  INTEGER
	ACCESS  read-only
	STATUS  mandatory
	DESCRIPTION
		"Output priority of packets which complied with maximum contr
		act bandwidth when maximum bandwidth control is being used."
	::= { axrFlowQosInActEntry 17 }

axrFlowQosInActMinOverPriority OBJECT-TYPE
	SYNTAX  INTEGER
	ACCESS  read-only
	STATUS  mandatory
	DESCRIPTION
		"Output priority of packets which violated minimum contract b
		andwidth when minimum bandwidth control is being used."
	::= { axrFlowQosInActEntry 18 }

axrFlowQosInActMinUnderPriority OBJECT-TYPE
	SYNTAX  INTEGER
	ACCESS  read-only
	STATUS  mandatory
	DESCRIPTION
		"Output priority of packets which complied with minimum contr
		act bandwidth when minimum bandwidth control is being used."
	::= { axrFlowQosInActEntry 19 }

axrFlowQosInActDiscard OBJECT-TYPE
	SYNTAX  INTEGER
	ACCESS  read-only
	STATUS  mandatory
	DESCRIPTION
		"Queuing priority when bandwidth monitoring function is not b
		eing used."
	::= { axrFlowQosInActEntry 20 }

axrFlowQosInActMaxUnderDiscard OBJECT-TYPE
	SYNTAX  INTEGER
	ACCESS  read-only
	STATUS  mandatory
	DESCRIPTION
		"Queuing priority of packets which complied with maximum cont
		ract bandwidth when maximum bandwidth control is being used."
	::= { axrFlowQosInActEntry 21 }

axrFlowQosInActMinOverDiscard OBJECT-TYPE
	SYNTAX  INTEGER
	ACCESS  read-only
	STATUS  mandatory
	DESCRIPTION
		"Queuing priority of packets which violated minimum contract 
		bandwidth when minimum bandwidth control is being used."
	::= { axrFlowQosInActEntry 22 }

axrFlowQosInActMinUnderDiscard OBJECT-TYPE
	SYNTAX  INTEGER
	ACCESS  read-only
	STATUS  mandatory
	DESCRIPTION
		"Queuing priority of packets which complied with minimum cont
		ract bandwidth when minimum bandwidth control is being used."
	::= { axrFlowQosInActEntry 23 }

axrFlowQosInActDscpOp OBJECT-TYPE
	SYNTAX  INTEGER
	ACCESS  read-only
	STATUS  mandatory
	DESCRIPTION
		"Indicates existence of DSCP mapping specification."
	::= { axrFlowQosInActEntry 24 }

axrFlowQosInActDscp OBJECT-TYPE
	SYNTAX  INTEGER
	ACCESS  read-only
	STATUS  mandatory
	DESCRIPTION
		"The value of DSCP when bandwidth monitoring function is not 
		being used."
	::= { axrFlowQosInActEntry 25 }

axrFlowQosInActMaxUnderDscp OBJECT-TYPE
	SYNTAX  INTEGER
	ACCESS  read-only
	STATUS  mandatory
	DESCRIPTION
		"The value of DSCP of packets which complied with maximum con
		tract bandwidth when maximum bandwidth control is being used.
		"
	::= { axrFlowQosInActEntry 26 }

axrFlowQosInActMinOverDscp OBJECT-TYPE
	SYNTAX  INTEGER
	ACCESS  read-only
	STATUS  mandatory
	DESCRIPTION
		"The value of DSCP of packets which violated minimum contract
		 bandwidth when minimum bandwidth control is being used."
	::= { axrFlowQosInActEntry 27 }

axrFlowQosInActMinUnderDscp OBJECT-TYPE
	SYNTAX  INTEGER
	ACCESS  read-only
	STATUS  mandatory
	DESCRIPTION
		"The value of DSCP of packets which complied with minimum con
		tract bandwidth when minimum bandwidth control is being used.
		"
	::= { axrFlowQosInActEntry 28 }

axrFlowQosInActUserPriority OBJECT-TYPE
	SYNTAX  INTEGER
	ACCESS  read-only
	STATUS  mandatory
	DESCRIPTION
		"Indicates user priority when bandwidth monitoring function i
		s not being used."
	::= { axrFlowQosInActEntry 29 }

axrFlowQosInActMaxUnderUserPriority OBJECT-TYPE
	SYNTAX  INTEGER
	ACCESS  read-only
	STATUS  mandatory
	DESCRIPTION
		"User priority of packets which complied with maximum contrac
		t bandwidth when maximum bandwidth control is being used."
	::= { axrFlowQosInActEntry 30 }

axrFlowQosInActMinOverUserPriority OBJECT-TYPE
	SYNTAX  INTEGER
	ACCESS  read-only
	STATUS  mandatory
	DESCRIPTION
		"User priority of packets which violated minimum contract ban
		dwidth when minimum bandwidth control is being used."
	::= { axrFlowQosInActEntry 31 }

axrFlowQosInActMinUnderUserPriority OBJECT-TYPE
	SYNTAX  INTEGER
	ACCESS  read-only
	STATUS  mandatory
	DESCRIPTION
		"User priority of packets which complied with minimum contrac
		t bandwidth when minimum bandwidth control is being used."
	::= { axrFlowQosInActEntry 32 }

axrFlowQosInActExp OBJECT-TYPE
	SYNTAX  INTEGER
	ACCESS  read-only
	STATUS  mandatory
	DESCRIPTION
	        "The EXP value in shim header  when bandwidth monitoring function is not being used."
        ::= { axrFlowQosInActEntry 33 }

axrFlowQosInActMaxUnderExp OBJECT-TYPE
	SYNTAX  INTEGER
	ACCESS  read-only
	STATUS  mandatory
	DESCRIPTION
		"The EXP value of the packet which complied with maximum contract
		 bandwidth when maximum bandwidth control is being used."
        ::= { axrFlowQosInActEntry 34 }

axrFlowQosInActMinOverExp OBJECT-TYPE
	SYNTAX  INTEGER
	ACCESS  read-only
	STATUS  mandatory
	DESCRIPTION
		"The EXP value of the packet which violated minimum contract
		 bandwidth when minimum bandwidth control is being used."
        ::= { axrFlowQosInActEntry 35 }

axrFlowQosInActMinUnderExp OBJECT-TYPE
	SYNTAX  INTEGER
	ACCESS  read-only
	STATUS  mandatory
	DESCRIPTION
		"The EXP value of the packet which complied with minimum contract
		 bandwidth when minimum bandwidth control is being used."
        ::= { axrFlowQosInActEntry 36 }
        
axrFlowQosInActPremTable OBJECT-TYPE
	SYNTAX  SEQUENCE OF AxrFlowQosInActPremEntry
	ACCESS  not-accessible
	STATUS  mandatory
	DESCRIPTION
		"Information of action parameter table on premium flow detect
		ion condition.(Inbound)"
	::= { axrFlowQos 6 }

axrFlowQosInActPremEntry OBJECT-TYPE
	SYNTAX  AxrFlowQosInActPremEntry
	ACCESS  not-accessible
	STATUS  mandatory
	DESCRIPTION
		"Entry of action parameter on premium flow detection conditio
		n.(Inbound)"
	INDEX {
		axrFlowQosInActPremifIndex,
		axrFlowQosInActPremifIndexType,
		axrFlowQosInActPremListNumber
	}
	::= { axrFlowQosInActPremTable 1 }
	AxrFlowQosInActPremEntry ::= 
	    SEQUENCE {
		axrFlowQosInActPremifIndex
			INTEGER,
		axrFlowQosInActPremifIndexType
        	INTEGER,
		axrFlowQosInActPremListNumber
        	INTEGER,
		axrFlowQosInActPremMaxRateBurst
        	INTEGER,
		axrFlowQosInActPremMinRateBurst
        	INTEGER
        }

axrFlowQosInActPremifIndex OBJECT-TYPE
	SYNTAX  INTEGER
	ACCESS  not-accessible
	STATUS  mandatory
	DESCRIPTION
		"Indicates the value of index(ifIndex) which identifies this 
		table entry."
	::= { axrFlowQosInActPremEntry 1 }

axrFlowQosInActPremifIndexType OBJECT-TYPE
	SYNTAX  INTEGER
	ACCESS  not-accessible
	STATUS  mandatory
	DESCRIPTION
		"Indicates interface type.Physical port number : 1Interface n
		ame : 2"
	::= { axrFlowQosInActPremEntry 2 }

axrFlowQosInActPremListNumber OBJECT-TYPE
	SYNTAX  INTEGER
	ACCESS  not-accessible
	STATUS  mandatory
	DESCRIPTION
		"Indicates the value of index(list number) which identifies t
		his table entry."
	::= { axrFlowQosInActPremEntry 3 }

axrFlowQosInActPremMaxRateBurst OBJECT-TYPE
	SYNTAX  INTEGER
	ACCESS  read-only
	STATUS  mandatory
	DESCRIPTION
		"Burst size of premium flow under maximum bandwidth control."
	::= { axrFlowQosInActPremEntry 4 }

axrFlowQosInActPremMinRateBurst OBJECT-TYPE
	SYNTAX  INTEGER
	ACCESS  read-only
	STATUS  mandatory
	DESCRIPTION
		"Burst size of premium flow under minimum bandwidth control."
	::= { axrFlowQosInActPremEntry 5 }

axrFlowQosOutActTable OBJECT-TYPE
	SYNTAX  SEQUENCE OF AxrFlowQosOutActEntry
	ACCESS  not-accessible
	STATUS  mandatory
	DESCRIPTION
		"Information of action parameter table on normal flow detect
		ion condition.(Outbound)"
	::= { axrFlowQos 7 }

axrFlowQosOutActEntry OBJECT-TYPE
	SYNTAX  AxrFlowQosOutActEntry
	ACCESS  not-accessible
	STATUS  mandatory
	DESCRIPTION
		"Entry of action parameter on normal flow detection conditio
		n.(Outbound)"
	INDEX {
		axrFlowQosOutActifIndex,
		axrFlowQosOutActifIndexType,
		axrFlowQosOutActListNumber
	}
	::= { axrFlowQosOutActTable 1 }
	AxrFlowQosOutActEntry ::= 
	    SEQUENCE {
		axrFlowQosOutActifIndex
			INTEGER,
		axrFlowQosOutActifIndexType
        	INTEGER,
		axrFlowQosOutActListNumber
        	INTEGER,
		axrFlowQosOutActMaxRate
        	INTEGER,
		axrFlowQosOutActMaxRateBurst
        	INTEGER,
		axrFlowQosOutActMaxUpcRedMinBurst
        	INTEGER,
		axrFlowQosOutActMaxUpcRedMaxBurst
        	INTEGER,
		axrFlowQosOutActMaxUpcRedProbability
        	INTEGER,
		axrFlowQosOutActMinRate
        	INTEGER,
		axrFlowQosOutActMinRateBurst
        	INTEGER,
		axrFlowQosOutActMinUpcRedMinBurst
        	INTEGER,
		axrFlowQosOutActMinUpcRedMaxBurst
        	INTEGER,
		axrFlowQosOutActMinUpcRedProbability
        	INTEGER,
		axrFlowQosOutActAgQueueOp
        	INTEGER,
		axrFlowQosOutActAgQueue
        	INTEGER,
		axrFlowQosOutActPriority
        	INTEGER,
		axrFlowQosOutActMaxUnderPriority
        	INTEGER,
		axrFlowQosOutActMinOverPriority
        	INTEGER,
		axrFlowQosOutActMinUnderPriority
        	INTEGER,
		axrFlowQosOutActDiscard
        	INTEGER,
		axrFlowQosOutActMaxUnderDiscard
        	INTEGER,
		axrFlowQosOutActMinOverDiscard
        	INTEGER,
		axrFlowQosOutActMinUnderDiscard
        	INTEGER,
		axrFlowQosOutActDscpOp
        	INTEGER,
		axrFlowQosOutActDscp
        	INTEGER,
		axrFlowQosOutActMaxUnderDscp
        	INTEGER,
		axrFlowQosOutActMinOverDscp
        	INTEGER,
		axrFlowQosOutActMinUnderDscp
        	INTEGER,
		axrFlowQosOutActUserPriority
        	INTEGER,
		axrFlowQosOutActMaxUnderUserPriority
        	INTEGER,
		axrFlowQosOutActMinOverUserPriority
        	INTEGER,
		axrFlowQosOutActMinUnderUserPriority
        	INTEGER,
		axrFlowQosOutActExp
			INTEGER,
		axrFlowQosOutActMaxUnderExp
			INTEGER,
		axrFlowQosOutActMinOverExp
			INTEGER,
		axrFlowQosOutActMinUnderExp
			INTEGER
        }

axrFlowQosOutActifIndex OBJECT-TYPE
	SYNTAX  INTEGER
	ACCESS  not-accessible
	STATUS  mandatory
	DESCRIPTION
		"Indicates the value of index(ifIndex) which identifies this 
		table entry."
	::= { axrFlowQosOutActEntry 1 }

axrFlowQosOutActifIndexType OBJECT-TYPE
	SYNTAX  INTEGER
	ACCESS  not-accessible
	STATUS  mandatory
	DESCRIPTION
		"Indicates interface type.Physical port number : 1Interface n
		ame : 2"
	::= { axrFlowQosOutActEntry 2 }

axrFlowQosOutActListNumber OBJECT-TYPE
	SYNTAX  INTEGER
	ACCESS  not-accessible
	STATUS  mandatory
	DESCRIPTION
		"Indicates the value of index(list number) which identifies t
		his table entry."
	::= { axrFlowQosOutActEntry 3 }

axrFlowQosOutActMaxRate OBJECT-TYPE
	SYNTAX  INTEGER
	ACCESS  read-only
	STATUS  mandatory
	DESCRIPTION
		"The value of monitoring bandwidth under maximum bandwidth co
		ntrol."
	::= { axrFlowQosOutActEntry 4 }

axrFlowQosOutActMaxRateBurst OBJECT-TYPE
	SYNTAX  INTEGER
	ACCESS  read-only
	STATUS  mandatory
	DESCRIPTION
		"Burst size under maximum bandwidth control."
	::= { axrFlowQosOutActEntry 5 }

axrFlowQosOutActMaxUpcRedMinBurst OBJECT-TYPE
	SYNTAX  INTEGER
	ACCESS  read-only
	STATUS  mandatory
	DESCRIPTION
		"Minimum burst size while using UPC-RED(Max) function."
	::= { axrFlowQosOutActEntry 6 }

axrFlowQosOutActMaxUpcRedMaxBurst OBJECT-TYPE
	SYNTAX  INTEGER
	ACCESS  read-only
	STATUS  mandatory
	DESCRIPTION
		"Maximum burst size while using UPC-RED(Max) function."
	::= { axrFlowQosOutActEntry 7 }

axrFlowQosOutActMaxUpcRedProbability OBJECT-TYPE
	SYNTAX  INTEGER
	ACCESS  read-only
	STATUS  mandatory
	DESCRIPTION
		"Maximum violation rate while using UPC-RED(Max) function."
	::= { axrFlowQosOutActEntry 8 }

axrFlowQosOutActMinRate OBJECT-TYPE
	SYNTAX  INTEGER
	ACCESS  read-only
	STATUS  mandatory
	DESCRIPTION
		"The value of monitoring bandwidth under minimum bandwidth co
		ntrol."
	::= { axrFlowQosOutActEntry 9 }

axrFlowQosOutActMinRateBurst OBJECT-TYPE
	SYNTAX  INTEGER
	ACCESS  read-only
	STATUS  mandatory
	DESCRIPTION
		"Burst size under minimum bandwidth control."
	::= { axrFlowQosOutActEntry 10 }

axrFlowQosOutActMinUpcRedMinBurst OBJECT-TYPE
	SYNTAX  INTEGER
	ACCESS  read-only
	STATUS  mandatory
	DESCRIPTION
		"Minimum burst size while using UPC-RED(Min) function."
	::= { axrFlowQosOutActEntry 11 }

axrFlowQosOutActMinUpcRedMaxBurst OBJECT-TYPE
	SYNTAX  INTEGER
	ACCESS  read-only
	STATUS  mandatory
	DESCRIPTION
		"Maximum burst size while using UPC-RED(Min) function."
	::= { axrFlowQosOutActEntry 12 }

axrFlowQosOutActMinUpcRedProbability OBJECT-TYPE
	SYNTAX  INTEGER
	ACCESS  read-only
	STATUS  mandatory
	DESCRIPTION
		"Maximum violation rate while using UPC-RED(Min) function."
	::= { axrFlowQosOutActEntry 13 }

axrFlowQosOutActAgQueueOp OBJECT-TYPE
	SYNTAX  INTEGER
	ACCESS  read-only
	STATUS  mandatory
	DESCRIPTION
		"Indicates specification method of aggregate queue number of 
		layered shaper."
	::= { axrFlowQosOutActEntry 14 }

axrFlowQosOutActAgQueue OBJECT-TYPE
	SYNTAX  INTEGER
	ACCESS  read-only
	STATUS  mandatory
	DESCRIPTION
		"Aggregate queue number of layered shaper."
	::= { axrFlowQosOutActEntry 15 }

axrFlowQosOutActPriority OBJECT-TYPE
	SYNTAX  INTEGER
	ACCESS  read-only
	STATUS  mandatory
	DESCRIPTION
		"Output priority when bandwidth monitoring function is not us
		ed."
	::= { axrFlowQosOutActEntry 16 }

axrFlowQosOutActMaxUnderPriority OBJECT-TYPE
	SYNTAX  INTEGER
	ACCESS  read-only
	STATUS  mandatory
	DESCRIPTION
		"Output priority of packets which complied with maximum contr
		act bandwidth when maximum bandwidth control is being used."
	::= { axrFlowQosOutActEntry 17 }

axrFlowQosOutActMinOverPriority OBJECT-TYPE
	SYNTAX  INTEGER
	ACCESS  read-only
	STATUS  mandatory
	DESCRIPTION
		"Output priority of packets which violated minimum contract b
		andwidth when minimum bandwidth control is being used."
	::= { axrFlowQosOutActEntry 18 }

axrFlowQosOutActMinUnderPriority OBJECT-TYPE
	SYNTAX  INTEGER
	ACCESS  read-only
	STATUS  mandatory
	DESCRIPTION
		"Output priority of packets which complied with minimum contr
		act bandwidth when minimum bandwidth control is being used."
	::= { axrFlowQosOutActEntry 19 }

axrFlowQosOutActDiscard OBJECT-TYPE
	SYNTAX  INTEGER
	ACCESS  read-only
	STATUS  mandatory
	DESCRIPTION
		"Queuing priority when bandwidth monitoring function is not b
		eing used."
	::= { axrFlowQosOutActEntry 20 }

axrFlowQosOutActMaxUnderDiscard OBJECT-TYPE
	SYNTAX  INTEGER
	ACCESS  read-only
	STATUS  mandatory
	DESCRIPTION
		"Queuing priority of packets which complied with maximum cont
		ract bandwidth when maximum bandwidth control is being used."
	::= { axrFlowQosOutActEntry 21 }

axrFlowQosOutActMinOverDiscard OBJECT-TYPE
	SYNTAX  INTEGER
	ACCESS  read-only
	STATUS  mandatory
	DESCRIPTION
		"Queuing priority of packets which violated minimum contract 
		bandwidth when minimum bandwidth control is being used."
	::= { axrFlowQosOutActEntry 22 }

axrFlowQosOutActMinUnderDiscard OBJECT-TYPE
	SYNTAX  INTEGER
	ACCESS  read-only
	STATUS  mandatory
	DESCRIPTION
		"Queuing priority of packets which complied with minimum cont
		ract bandwidth when minimum bandwidth control is being used."
	::= { axrFlowQosOutActEntry 23 }

axrFlowQosOutActDscpOp OBJECT-TYPE
	SYNTAX  INTEGER
	ACCESS  read-only
	STATUS  mandatory
	DESCRIPTION
		"Indicates existence of DSCP mapping specification."
	::= { axrFlowQosOutActEntry 24 }

axrFlowQosOutActDscp OBJECT-TYPE
	SYNTAX  INTEGER
	ACCESS  read-only
	STATUS  mandatory
	DESCRIPTION
		"The value of DSCP when bandwidth monitoring function is not 
		being used."
	::= { axrFlowQosOutActEntry 25 }

axrFlowQosOutActMaxUnderDscp OBJECT-TYPE
	SYNTAX  INTEGER
	ACCESS  read-only
	STATUS  mandatory
	DESCRIPTION
		"The value of DSCP of packets which complied with maximum con
		tract bandwidth when maximum bandwidth control is being used.
		"
	::= { axrFlowQosOutActEntry 26 }

axrFlowQosOutActMinOverDscp OBJECT-TYPE
	SYNTAX  INTEGER
	ACCESS  read-only
	STATUS  mandatory
	DESCRIPTION
		"The value of DSCP of packets which violated minimum contract
		 bandwidth when minimum bandwidth control is being used."
	::= { axrFlowQosOutActEntry 27 }

axrFlowQosOutActMinUnderDscp OBJECT-TYPE
	SYNTAX  INTEGER
	ACCESS  read-only
	STATUS  mandatory
	DESCRIPTION
		"The value of DSCP of packets which complied with minimum con
		tract bandwidth when minimum bandwidth control is being used.
		"
	::= { axrFlowQosOutActEntry 28 }

axrFlowQosOutActUserPriority OBJECT-TYPE
	SYNTAX  INTEGER
	ACCESS  read-only
	STATUS  mandatory
	DESCRIPTION
		"Indicates user priority when bandwidth monitoring function i
		s not being used."
	::= { axrFlowQosOutActEntry 29 }

axrFlowQosOutActMaxUnderUserPriority OBJECT-TYPE
	SYNTAX  INTEGER
	ACCESS  read-only
	STATUS  mandatory
	DESCRIPTION
		"User priority of packets which complied with maximum contrac
		t bandwidth when maximum bandwidth control is being used."
	::= { axrFlowQosOutActEntry 30 }

axrFlowQosOutActMinOverUserPriority OBJECT-TYPE
	SYNTAX  INTEGER
	ACCESS  read-only
	STATUS  mandatory
	DESCRIPTION
		"User priority of packets which violated minimum contract ban
		dwidth when minimum bandwidth control is being used."
	::= { axrFlowQosOutActEntry 31 }

axrFlowQosOutActMinUnderUserPriority OBJECT-TYPE
	SYNTAX  INTEGER
	ACCESS  read-only
	STATUS  mandatory
	DESCRIPTION
		"User priority of packets which complied with minimum contrac
		t bandwidth when minimum bandwidth control is being used."
	::= { axrFlowQosOutActEntry 32 }

axrFlowQosOutActExp OBJECT-TYPE
	SYNTAX  INTEGER
	ACCESS  read-only
	STATUS  mandatory
	DESCRIPTION
		"The EXP value in shim header  when bandwidth monitoring function is not being used."
	::= { axrFlowQosOutActEntry 33 }

axrFlowQosOutActMaxUnderExp OBJECT-TYPE
	SYNTAX  INTEGER
	ACCESS  read-only
	STATUS  mandatory
	DESCRIPTION
		"The EXP value of the packet which complied with maximum contract
		 bandwidth when maximum bandwidth control is being used."
	::= { axrFlowQosOutActEntry 34 }

axrFlowQosOutActMinOverExp OBJECT-TYPE
	SYNTAX  INTEGER
	ACCESS  read-only
	STATUS  mandatory
	DESCRIPTION
		"The EXP value of the packet which violated minimum contract
		 bandwidth when minimum bandwidth control is being used."
	::= { axrFlowQosOutActEntry 35 }

axrFlowQosOutActMinUnderExp OBJECT-TYPE
	SYNTAX  INTEGER
	ACCESS  read-only
	STATUS  mandatory
	DESCRIPTION
		"The EXP value of the packet which complied with minimum contract
		 bandwidth when minimum bandwidth control is being used."
	::= { axrFlowQosOutActEntry 36 }
	
axrFlowQosOutActPremTable OBJECT-TYPE
	SYNTAX  SEQUENCE OF AxrFlowQosOutActPremEntry
	ACCESS  not-accessible
	STATUS  mandatory
	DESCRIPTION
		"Information of action parameter table on premium flow detect
		ion condition.(Outbound)"
	::= { axrFlowQos 8 }

axrFlowQosOutActPremEntry OBJECT-TYPE
	SYNTAX  AxrFlowQosOutActPremEntry
	ACCESS  not-accessible
	STATUS  mandatory
	DESCRIPTION
		"Entry of action parameter on premium flow detection conditio
		n.(Outbound)"
	INDEX {
		axrFlowQosOutActPremifIndex,
		axrFlowQosOutActPremifIndexType,
		axrFlowQosOutActPremListNumber
	}
	::= { axrFlowQosOutActPremTable 1 }
	AxrFlowQosOutActPremEntry ::= 
	    SEQUENCE {
		axrFlowQosOutActPremifIndex
			INTEGER,
		axrFlowQosOutActPremifIndexType
        	INTEGER,
		axrFlowQosOutActPremListNumber
        	INTEGER,
		axrFlowQosOutActPremMaxRateBurst
        	INTEGER,
		axrFlowQosOutActPremMinRateBurst
        	INTEGER
        }

axrFlowQosOutActPremifIndex OBJECT-TYPE
	SYNTAX  INTEGER
	ACCESS  not-accessible
	STATUS  mandatory
	DESCRIPTION
		"Indicates the value of index(ifIndex) which identifies this 
		table entry."
	::= { axrFlowQosOutActPremEntry 1 }

axrFlowQosOutActPremifIndexType OBJECT-TYPE
	SYNTAX  INTEGER
	ACCESS  not-accessible
	STATUS  mandatory
	DESCRIPTION
		"Indicates interface type.Physical port number : 1Interface n
		ame : 2"
	::= { axrFlowQosOutActPremEntry 2 }

axrFlowQosOutActPremListNumber OBJECT-TYPE
	SYNTAX  INTEGER
	ACCESS  not-accessible
	STATUS  mandatory
	DESCRIPTION
		"Indicates the value of index(list number) which identifies t
		his table entry."
	::= { axrFlowQosOutActPremEntry 3 }

axrFlowQosOutActPremMaxRateBurst OBJECT-TYPE
	SYNTAX  INTEGER
	ACCESS  read-only
	STATUS  mandatory
	DESCRIPTION
		"Burst size of premium flow under maximum bandwidth control."
	::= { axrFlowQosOutActPremEntry 4 }

axrFlowQosOutActPremMinRateBurst OBJECT-TYPE
	SYNTAX  INTEGER
	ACCESS  read-only
	STATUS  mandatory
	DESCRIPTION
		"Burst size of premium flow under minimum bandwidth control."
	::= { axrFlowQosOutActPremEntry 5 }

axrFlowQosStatsInTable OBJECT-TYPE
	SYNTAX  SEQUENCE OF AxrFlowQosStatsInEntry
	ACCESS  not-accessible
	STATUS  mandatory
	DESCRIPTION
		"Information of statistics table which matched normal flow de
		tection condition."
	::= { axrFlowQosStats 1 }

axrFlowQosStatsInEntry OBJECT-TYPE
	SYNTAX  AxrFlowQosStatsInEntry
	ACCESS  not-accessible
	STATUS  mandatory
	DESCRIPTION
		"Entry of statistics information which matched normal flow de
		tection condition."
	INDEX {
		axrFlowQosStatsInifIndex,
		axrFlowQosStatsInifIndexType,
		axrFlowQosStatsInListNumber
	}
	::= { axrFlowQosStatsInTable 1 }
	AxrFlowQosStatsInEntry ::= 
	    SEQUENCE {
		axrFlowQosStatsInifIndex
			INTEGER,
		axrFlowQosStatsInifIndexType
        	INTEGER,
		axrFlowQosStatsInListNumber
        	INTEGER,
		axrFlowQosStatsInHitPackets
        	Counter64,
		axrFlowQosStatsInMaxOverPackets
        	Counter64,
		axrFlowQosStatsInMaxUnderPackets
        	Counter64,
		axrFlowQosStatsInMinOverPackets
        	Counter64,
		axrFlowQosStatsInMinUnderPackets
        	Counter64
        }

axrFlowQosStatsInifIndex OBJECT-TYPE
	SYNTAX  INTEGER
	ACCESS  not-accessible
	STATUS  mandatory
	DESCRIPTION
		"Indicates the value of index(ifIndex) which identifies this 
		table entry."
	::= { axrFlowQosStatsInEntry 1 }

axrFlowQosStatsInifIndexType OBJECT-TYPE
	SYNTAX  INTEGER
	ACCESS  not-accessible
	STATUS  mandatory
	DESCRIPTION
		"Indicates interface type.Physical port number : 1Interface n
		ame : 2"
	::= { axrFlowQosStatsInEntry 2 }

axrFlowQosStatsInListNumber OBJECT-TYPE
	SYNTAX  INTEGER
	ACCESS  not-accessible
	STATUS  mandatory
	DESCRIPTION
		"Indicates the value of index(list number) which identifies t
		his table entry."
	::= { axrFlowQosStatsInEntry 3 }

axrFlowQosStatsInHitPackets OBJECT-TYPE
	SYNTAX  Counter64
	ACCESS  read-only
	STATUS  mandatory
	DESCRIPTION
		"The number of packets which matched normal flow detection co
		ndition."
	::= { axrFlowQosStatsInEntry 4 }

axrFlowQosStatsInMaxOverPackets OBJECT-TYPE
	SYNTAX  Counter64
	ACCESS  read-only
	STATUS  mandatory
	DESCRIPTION
		"The number of packets which violated maximum contract bandwi
		dth and matched normal flow detection condition."
	::= { axrFlowQosStatsInEntry 5 }

axrFlowQosStatsInMaxUnderPackets OBJECT-TYPE
	SYNTAX  Counter64
	ACCESS  read-only
	STATUS  mandatory
	DESCRIPTION
		"The number of packets which complied with maximum contract b
		andwidth and matched normal flow detection condition."
	::= { axrFlowQosStatsInEntry 6 }

axrFlowQosStatsInMinOverPackets OBJECT-TYPE
	SYNTAX  Counter64
	ACCESS  read-only
	STATUS  mandatory
	DESCRIPTION
		"The number of packets which violated minimum contract bandwi
		dth and matched normal flow detection condition."
	::= { axrFlowQosStatsInEntry 7 }

axrFlowQosStatsInMinUnderPackets OBJECT-TYPE
	SYNTAX  Counter64
	ACCESS  read-only
	STATUS  mandatory
	DESCRIPTION
		"The number of packets which complied with minimum contract b
		andwidth and matched normal flow detection condition."
	::= { axrFlowQosStatsInEntry 8 }

axrFlowQosStatsInPremTable OBJECT-TYPE
	SYNTAX  SEQUENCE OF AxrFlowQosStatsInPremEntry
	ACCESS  not-accessible
	STATUS  mandatory
	DESCRIPTION
		"Information of statistics table which matched premium flow d
		etection condition."
	::= { axrFlowQosStats 2 }

axrFlowQosStatsInPremEntry OBJECT-TYPE
	SYNTAX  AxrFlowQosStatsInPremEntry
	ACCESS  not-accessible
	STATUS  mandatory
	DESCRIPTION
		"Entry of statistics information which matched premium flow d
		etection condition."
	INDEX {
		axrFlowQosStatsInPremifIndex,
		axrFlowQosStatsInPremifIndexType,
		axrFlowQosStatsInPremListNumber
	}
	::= { axrFlowQosStatsInPremTable 1 }
	AxrFlowQosStatsInPremEntry ::= 
	    SEQUENCE {
		axrFlowQosStatsInPremifIndex
			INTEGER,
		axrFlowQosStatsInPremifIndexType
        	INTEGER,
		axrFlowQosStatsInPremListNumber
        	INTEGER,
		axrFlowQosStatsInPremMaxOverPackets
        	Counter64,
		axrFlowQosStatsInPremMaxUnderPackets
        	Counter64,
		axrFlowQosStatsInPremMinOverPackets
        	Counter64,
		axrFlowQosStatsInPremMinUnderPackets
        	Counter64
        }

axrFlowQosStatsInPremifIndex OBJECT-TYPE
	SYNTAX  INTEGER
	ACCESS  not-accessible
	STATUS  mandatory
	DESCRIPTION
		"Indicates the value of index(ifIndex) which identifies this 
		table entry."
	::= { axrFlowQosStatsInPremEntry 1 }

axrFlowQosStatsInPremifIndexType OBJECT-TYPE
	SYNTAX  INTEGER
	ACCESS  not-accessible
	STATUS  mandatory
	DESCRIPTION
		"Indicates interface type.Physical port number : 1Interface n
		ame : 2"
	::= { axrFlowQosStatsInPremEntry 2 }

axrFlowQosStatsInPremListNumber OBJECT-TYPE
	SYNTAX  INTEGER
	ACCESS  not-accessible
	STATUS  mandatory
	DESCRIPTION
		"Indicates the value of index(list number) which identifies t
		his table entry."
	::= { axrFlowQosStatsInPremEntry 3 }

axrFlowQosStatsInPremMaxOverPackets OBJECT-TYPE
	SYNTAX  Counter64
	ACCESS  read-only
	STATUS  mandatory
	DESCRIPTION
		"The number of packets which violated maximum contract bandwi
		dth and matched premium flow detection condition."
	::= { axrFlowQosStatsInPremEntry 4 }

axrFlowQosStatsInPremMaxUnderPackets OBJECT-TYPE
	SYNTAX  Counter64
	ACCESS  read-only
	STATUS  mandatory
	DESCRIPTION
		"The number of packets which complied with maximum contract b
		andwidth and matched premium flow detection condition."
	::= { axrFlowQosStatsInPremEntry 5 }

axrFlowQosStatsInPremMinOverPackets OBJECT-TYPE
	SYNTAX  Counter64
	ACCESS  read-only
	STATUS  mandatory
	DESCRIPTION
		"The number of packets which violated minimum contract bandwi
		dth and matched premium flow detection condition."
	::= { axrFlowQosStatsInPremEntry 6 }

axrFlowQosStatsInPremMinUnderPackets OBJECT-TYPE
	SYNTAX  Counter64
	ACCESS  read-only
	STATUS  mandatory
	DESCRIPTION
		"The number of packets which complied with minimum contract b
		andwidth and matched premium flow detection condition."
	::= { axrFlowQosStatsInPremEntry 7 }

axrFlowQosStatsOutTable OBJECT-TYPE
	SYNTAX  SEQUENCE OF AxrFlowQosStatsOutEntry
	ACCESS  not-accessible
	STATUS  mandatory
	DESCRIPTION
		"Information of statistics table which matched normal flow de
		tection condition."
	::= { axrFlowQosStats 3 }

axrFlowQosStatsOutEntry OBJECT-TYPE
	SYNTAX  AxrFlowQosStatsOutEntry
	ACCESS  not-accessible
	STATUS  mandatory
	DESCRIPTION
		"Entry of statistics information which matched normal flow de
		tection condition."
	INDEX {
		axrFlowQosStatsOutifIndex,
		axrFlowQosStatsOutifIndexType,
		axrFlowQosStatsOutListNumber
	}
	::= { axrFlowQosStatsOutTable 1 }
	AxrFlowQosStatsOutEntry ::= 
	    SEQUENCE {
		axrFlowQosStatsOutifIndex
			INTEGER,
		axrFlowQosStatsOutifIndexType
        	INTEGER,
		axrFlowQosStatsOutListNumber
        	INTEGER,
		axrFlowQosStatsOutHitPackets
        	Counter64,
		axrFlowQosStatsOutMaxOverPackets
        	Counter64,
		axrFlowQosStatsOutMaxUnderPackets
        	Counter64,
		axrFlowQosStatsOutMinOverPackets
        	Counter64,
		axrFlowQosStatsOutMinUnderPackets
        	Counter64
        }

axrFlowQosStatsOutifIndex OBJECT-TYPE
	SYNTAX  INTEGER
	ACCESS  not-accessible
	STATUS  mandatory
	DESCRIPTION
		"Indicates the value of index(ifIndex) which identifies this 
		table entry."
	::= { axrFlowQosStatsOutEntry 1 }

axrFlowQosStatsOutifIndexType OBJECT-TYPE
	SYNTAX  INTEGER
	ACCESS  not-accessible
	STATUS  mandatory
	DESCRIPTION
		"Indicates interface type.Physical port number : 1Interface n
		ame : 2"
	::= { axrFlowQosStatsOutEntry 2 }

axrFlowQosStatsOutListNumber OBJECT-TYPE
	SYNTAX  INTEGER
	ACCESS  not-accessible
	STATUS  mandatory
	DESCRIPTION
		"Indicates the value of index(list number) which identifies t
		his table entry."
	::= { axrFlowQosStatsOutEntry 3 }

axrFlowQosStatsOutHitPackets OBJECT-TYPE
	SYNTAX  Counter64
	ACCESS  read-only
	STATUS  mandatory
	DESCRIPTION
		"The number of packets which matched normal flow detection co
		ndition."
	::= { axrFlowQosStatsOutEntry 4 }

axrFlowQosStatsOutMaxOverPackets OBJECT-TYPE
	SYNTAX  Counter64
	ACCESS  read-only
	STATUS  mandatory
	DESCRIPTION
		"The number of packets which violated maximum contract bandwi
		dth and matched normal flow detection condition."
	::= { axrFlowQosStatsOutEntry 5 }

axrFlowQosStatsOutMaxUnderPackets OBJECT-TYPE
	SYNTAX  Counter64
	ACCESS  read-only
	STATUS  mandatory
	DESCRIPTION
		"The number of packets which complied with maximum contract b
		andwidth and matched normal flow detection condition."
	::= { axrFlowQosStatsOutEntry 6 }

axrFlowQosStatsOutMinOverPackets OBJECT-TYPE
	SYNTAX  Counter64
	ACCESS  read-only
	STATUS  mandatory
	DESCRIPTION
		"The number of packets which violated minimum contract bandwi
		dth and matched normal flow detection condition."
	::= { axrFlowQosStatsOutEntry 7 }

axrFlowQosStatsOutMinUnderPackets OBJECT-TYPE
	SYNTAX  Counter64
	ACCESS  read-only
	STATUS  mandatory
	DESCRIPTION
		"The number of packets which complied with minimum contract b
		andwidth and matched normal flow detection condition."
	::= { axrFlowQosStatsOutEntry 8 }

axrFlowQosStatsOutPremTable OBJECT-TYPE
	SYNTAX  SEQUENCE OF AxrFlowQosStatsOutPremEntry
	ACCESS  not-accessible
	STATUS  mandatory
	DESCRIPTION
		"Information of statistics table which matched premium flow d
		etection condition."
	::= { axrFlowQosStats 4 }

axrFlowQosStatsOutPremEntry OBJECT-TYPE
	SYNTAX  AxrFlowQosStatsOutPremEntry
	ACCESS  not-accessible
	STATUS  mandatory
	DESCRIPTION
		"Entry of statistics information which matched premium flow d
		etection condition."
	INDEX {
		axrFlowQosStatsOutPremifIndex,
		axrFlowQosStatsOutPremifIndexType,
		axrFlowQosStatsOutPremListNumber
	}
	::= { axrFlowQosStatsOutPremTable 1 }
	AxrFlowQosStatsOutPremEntry ::= 
	    SEQUENCE {
		axrFlowQosStatsOutPremifIndex
			INTEGER,
		axrFlowQosStatsOutPremifIndexType
        	INTEGER,
		axrFlowQosStatsOutPremListNumber
        	INTEGER,
		axrFlowQosStatsOutPremMaxOverPackets
        	Counter64,
		axrFlowQosStatsOutPremMaxUnderPackets
        	Counter64,
		axrFlowQosStatsOutPremMinOverPackets
        	Counter64,
		axrFlowQosStatsOutPremMinUnderPackets
        	Counter64
        }

axrFlowQosStatsOutPremifIndex OBJECT-TYPE
	SYNTAX  INTEGER
	ACCESS  not-accessible
	STATUS  mandatory
	DESCRIPTION
		"Indicates the value of index(ifIndex) which identifies this 
		table entry."
	::= { axrFlowQosStatsOutPremEntry 1 }

axrFlowQosStatsOutPremifIndexType OBJECT-TYPE
	SYNTAX  INTEGER
	ACCESS  not-accessible
	STATUS  mandatory
	DESCRIPTION
		"Indicates interface type.Physical port number : 1Interface n
		ame : 2"
	::= { axrFlowQosStatsOutPremEntry 2 }

axrFlowQosStatsOutPremListNumber OBJECT-TYPE
	SYNTAX  INTEGER
	ACCESS  not-accessible
	STATUS  mandatory
	DESCRIPTION
		"Indicates the value of index(list number) which identifies t
		his table entry."
	::= { axrFlowQosStatsOutPremEntry 3 }

axrFlowQosStatsOutPremMaxOverPackets OBJECT-TYPE
	SYNTAX  Counter64
	ACCESS  read-only
	STATUS  mandatory
	DESCRIPTION
		"The number of packets which violated maximum contract bandwi
		dth and matched premium flow detection condition."
	::= { axrFlowQosStatsOutPremEntry 4 }

axrFlowQosStatsOutPremMaxUnderPackets OBJECT-TYPE
	SYNTAX  Counter64
	ACCESS  read-only
	STATUS  mandatory
	DESCRIPTION
		"The number of packets which complied with maximum contract b
		andwidth and matched premium flow detection condition."
	::= { axrFlowQosStatsOutPremEntry 5 }

axrFlowQosStatsOutPremMinOverPackets OBJECT-TYPE
	SYNTAX  Counter64
	ACCESS  read-only
	STATUS  mandatory
	DESCRIPTION
		"The number of packets which violated minimum contract bandwi
		dth and matched premium flow detection condition."
	::= { axrFlowQosStatsOutPremEntry 6 }

axrFlowQosStatsOutPremMinUnderPackets OBJECT-TYPE
	SYNTAX  Counter64
	ACCESS  read-only
	STATUS  mandatory
	DESCRIPTION
		"The number of packets which complied with minimum contract b
		andwidth and matched premium flow detection condition."
	::= { axrFlowQosStatsOutPremEntry 7 }

--  OSPF General Variables

axrOspfGeneralTable OBJECT-TYPE
	SYNTAX  SEQUENCE OF AxrOspfGeneralEntry
	ACCESS  not-accessible
	STATUS  mandatory
	DESCRIPTION
		"The table of OSPF information."
	::= { axrOspf 1 }

axrOspfGeneralEntry OBJECT-TYPE
	SYNTAX  AxrOspfGeneralEntry
	ACCESS  not-accessible
	STATUS  mandatory
	DESCRIPTION
		"The entry of OSPF information."
    INDEX { axrOspfGeneralDomainNumber }
	::= { axrOspfGeneralTable 1 }

	AxrOspfGeneralEntry ::=
		SEQUENCE {
		    axrOspfGeneralDomainNumber	INTEGER,
		    axrOspfRouterId				IpAddress,
		    axrOspfAdminStat				INTEGER,
		    axrOspfVersionNumber			INTEGER,
		    axrOspfAreaBdrRtrStatus		INTEGER,
		    axrOspfASBdrRtrStatus		INTEGER,
		    axrOspfExternLsaCount		Gauge,
		    axrOspfExternLsaCksumSum		INTEGER,
		    axrOspfTOSSupport			INTEGER,
		    axrOspfOriginateNewLsas		Counter,
		    axrOspfRxNewLsas				Counter,
		    axrOspfExtLsdbLimit			INTEGER,
		    axrOspfMulticastExtensions	INTEGER
		}

axrOspfGeneralDomainNumber OBJECT-TYPE
	SYNTAX  INTEGER
	ACCESS  read-only
	STATUS  mandatory
	DESCRIPTION
		"Domain number in the Autonomous System."
	::= { axrOspfGeneralEntry 1 }

axrOspfRouterId OBJECT-TYPE
	SYNTAX  IpAddress
	ACCESS  read-only
	STATUS  mandatory
	DESCRIPTION
		"A integer uniquely identifying the router
		in the Autonomous System."
	::= { axrOspfGeneralEntry 2 }

axrOspfAdminStat OBJECT-TYPE
	SYNTAX  INTEGER   { 
				enabled(1),
				disabled(2)
		    }
	ACCESS  read-only
	STATUS  mandatory
	DESCRIPTION
		"The  administrative  status  of  OSPF  in  the
		router.  "
	::= { axrOspfGeneralEntry 3 }

axrOspfVersionNumber OBJECT-TYPE
	SYNTAX  INTEGER
	ACCESS  read-only
	STATUS  mandatory
	DESCRIPTION
		"The current version number of the OSPF  
		protocol is 2."
	::= { axrOspfGeneralEntry 4 }

axrOspfAreaBdrRtrStatus OBJECT-TYPE
	SYNTAX  INTEGER { 
				true(1),
				false(2)
			}
	ACCESS  read-only
	STATUS  mandatory
	DESCRIPTION
		"A flag to note whether this router is an  area
		 border router."
	::= { axrOspfGeneralEntry 5 }

axrOspfASBdrRtrStatus OBJECT-TYPE
	SYNTAX  INTEGER {
				true(1),
				false(2)
			}
	ACCESS  read-only
	STATUS  mandatory
	DESCRIPTION
		"A flag to note whether this router is  configured
		as an Autonomous System border router."
	::= { axrOspfGeneralEntry 6 }

axrOspfExternLsaCount OBJECT-TYPE
	SYNTAX  Gauge
	ACCESS  read-only
	STATUS  mandatory
	DESCRIPTION
		"The number of external (LS type 5)  link-state
		advertisements in the link-state database."
	::= { axrOspfGeneralEntry 7 }

axrOspfExternLsaCksumSum OBJECT-TYPE
	SYNTAX  INTEGER
	ACCESS  read-only
	STATUS  mandatory
	DESCRIPTION
		"The 32-bit unsigned sum of the LS checksums of
		the  external  link-state  advertisements  contained
		in the link-state  database."
	::= { axrOspfGeneralEntry 8 }

axrOspfTOSSupport OBJECT-TYPE
	SYNTAX  INTEGER
	ACCESS  read-only
	STATUS  mandatory
	DESCRIPTION
		"The router's support for type-of-service routing.
		 This value of false(2). "
	::= { axrOspfGeneralEntry 9 }

axrOspfOriginateNewLsas OBJECT-TYPE
	SYNTAX  Counter
	ACCESS  read-only
	STATUS  mandatory
	DESCRIPTION
		"The number of  new  link-state  advertisements
		that have been originated. "
	::= { axrOspfGeneralEntry 10 }

axrOspfRxNewLsas OBJECT-TYPE
	SYNTAX  Counter
	ACCESS  read-only
	STATUS  mandatory
	DESCRIPTION
		"The number of  link-state  advertisements  received
		determined  to  be  new instantiations."
	::= { axrOspfGeneralEntry 11 }

axrOspfExtLsdbLimit OBJECT-TYPE
	SYNTAX  INTEGER
	ACCESS  read-only
	STATUS  mandatory
	DESCRIPTION
		"The maximum number of non-default AS-external-LSAs
		entries that can be stored in the link-state database.
		If the value is -1,  then there is no limit.
		This value is -1"
	::= { axrOspfGeneralEntry 12 }

axrOspfMulticastExtensions OBJECT-TYPE
	SYNTAX  INTEGER
	ACCESS  read-only
	STATUS  mandatory
	DESCRIPTION
		"A Bit Mask indicating whether  the  router  is
		forwarding  IP  multicast  (Class  D) datagrams
		based on the algorithms defined in  the  Multicast
		Extensions to OSPF."
	::= { axrOspfGeneralEntry 13 }

axrOspfAreaTable OBJECT-TYPE
	SYNTAX  SEQUENCE OF AxrOspfAreaEntry
	ACCESS  not-accessible
	STATUS  mandatory
	DESCRIPTION
		"The router's support for demand routing."
	::= { axrOspf 2 }

axrOspfAreaEntry OBJECT-TYPE
	SYNTAX  AxrOspfAreaEntry
	ACCESS  not-accessible
	STATUS  mandatory
	DESCRIPTION
		"This entry contain ospf area information."
    INDEX { axrOspfAreaDomainNumber, axrOspfAreaId }
	::= { axrOspfAreaTable 1 }

	AxrOspfAreaEntry ::=
		SEQUENCE {
		    axrOspfAreaDomainNumber	INTEGER,
		    axrOspfAreaId			IpAddress,
		    axrOspfAuthType			INTEGER,
		    axrOspfImportAsExtern	INTEGER,
		    axrOspfSpfRuns			Counter,
		    axrOspfAreaBdrRtrCount	Gauge,
		    axrOspfAsBdrRtrCount		Gauge,
		    axrOspfAreaLsaCount		Gauge,
		    axrOspfAreaLsaCksumSum	INTEGER,
		    axrOspfAreaSummary		INTEGER,
		    axrOspfAreaStatus		INTEGER
		}

axrOspfAreaDomainNumber OBJECT-TYPE
	SYNTAX  INTEGER
	ACCESS  read-only
	STATUS  mandatory
	DESCRIPTION
		"An uniquely identifying number of domain."
	::= { axrOspfAreaEntry 1 }

axrOspfAreaId OBJECT-TYPE
	SYNTAX  IpAddress
	ACCESS  read-only
	STATUS  mandatory
	DESCRIPTION
		"A 32-bit integer uniquely identifying an area."
	::= { axrOspfAreaEntry 2 }

axrOspfAuthType OBJECT-TYPE
	SYNTAX  INTEGER
			-- none(0),
			-- simplePassword (1),
			-- md5(2)
	ACCESS  read-only
	STATUS  mandatory
	DESCRIPTION
		"The authentication type specified for an area."
	::= { axrOspfAreaEntry 3 }

axrOspfImportAsExtern OBJECT-TYPE
	SYNTAX  INTEGER { 
				importExternal (1),
				importNoExternal (2),
				importNssa (3)
			}
	ACCESS  read-only
	STATUS  mandatory
	DESCRIPTION
		"The area's support for importing  AS  external
		link- state advertisements."
	::= { axrOspfAreaEntry 4 }

axrOspfSpfRuns OBJECT-TYPE
	SYNTAX  Counter
	ACCESS  read-only
	STATUS  mandatory
	DESCRIPTION
		"The number of times that the intra-area  route
		table  has  been  calculated  using this area's
		link-state database."
	::= { axrOspfAreaEntry 5 }

axrOspfAreaBdrRtrCount OBJECT-TYPE
	SYNTAX  Gauge
	ACCESS  read-only
	STATUS  mandatory
	DESCRIPTION
		"The total number of area border routers reachable
		within this area."
	::= { axrOspfAreaEntry 6 }

axrOspfAsBdrRtrCount OBJECT-TYPE
	SYNTAX  Gauge
	ACCESS  read-only
	STATUS  mandatory
	DESCRIPTION
		"The total number of AS area border routers reachable
		within this area."
	::= { axrOspfAreaEntry 7 }

axrOspfAreaLsaCount OBJECT-TYPE
	SYNTAX  Gauge
	ACCESS  read-only
	STATUS  mandatory
	DESCRIPTION
		"The total number of LSA(link-state  advertisements) 
		in this area. Excluding AS External LSA's"
	::= { axrOspfAreaEntry 8 }

axrOspfAreaLsaCksumSum OBJECT-TYPE
	SYNTAX  INTEGER
	ACCESS  read-only
	STATUS  mandatory
	DESCRIPTION
		"The sum of LSA's  LS  checksums  contained in this
		area's link-state database."
	::= { axrOspfAreaEntry 9 }

axrOspfAreaSummary OBJECT-TYPE
	SYNTAX  INTEGER  {
				    noAreaSummary (1),
				    sendAreaSummary (2)
		    }
	ACCESS  read-only
	STATUS  mandatory
	DESCRIPTION
		"he variable axrOspfAreaSummary controls the import
		of summary LSAs into stub areas. Value is only 
		sendAreaSummary(2)."
	::= { axrOspfAreaEntry 10 }

axrOspfAreaStatus OBJECT-TYPE
	SYNTAX  INTEGER
	ACCESS  read-only
	STATUS  mandatory
	DESCRIPTION
		"This variable displays the status of  the  entry.
		Value is only valid(1)."
	::= { axrOspfAreaEntry 11 }

axrOspfStubAreaTable OBJECT-TYPE
	SYNTAX  SEQUENCE OF AxrOspfStubAreaEntry
	ACCESS  not-accessible
	STATUS  mandatory
	DESCRIPTION
		"The set of metrics that will be advertised  by
		a default Area Border Router into a stub area."
	::= { axrOspf 3 }

axrOspfStubAreaEntry OBJECT-TYPE
	SYNTAX  AxrOspfStubAreaEntry
	ACCESS  not-accessible
	STATUS  mandatory
	DESCRIPTION
		"The metric for a given Type  of  Service  that
		will be advertised by a default Area Border Router 
		into a stub area."
    INDEX { axrOspfStubDomainNumber, axrOspfStubAreaId,
		    axrOspfStubTOS }
	::= { axrOspfStubAreaTable 1 }

	AxrOspfStubAreaEntry ::=
		SEQUENCE {
		    axrOspfStubDomainNumber	INTEGER,
		    axrOspfStubAreaId		IpAddress,
		    axrOspfStubTOS			INTEGER,
		    axrOspfStubMetric		INTEGER,
		    axrOspfStubStatus		INTEGER,
		    axrOspfStubMetricType	INTEGER
		}

axrOspfStubDomainNumber OBJECT-TYPE
	SYNTAX  INTEGER
	ACCESS  read-only
	STATUS  mandatory
	DESCRIPTION
		"The domain identifier for the Stub  Area."
	::= { axrOspfStubAreaEntry 1 }

axrOspfStubAreaId OBJECT-TYPE
	SYNTAX  IpAddress
	ACCESS  read-only
	STATUS  mandatory
	DESCRIPTION
		"The identifier for the Stub  Area."
	::= { axrOspfStubAreaEntry 2 }

axrOspfStubTOS OBJECT-TYPE
	SYNTAX  INTEGER
	ACCESS  read-only
	STATUS  mandatory
	DESCRIPTION
		"The Type of Service associated with the metric.
		Value is only 0."
	::= { axrOspfStubAreaEntry 3 }

axrOspfStubMetric OBJECT-TYPE
	SYNTAX  INTEGER
	ACCESS  read-only
	STATUS  mandatory
	DESCRIPTION
		"The metric value applied at the indicated type
		of service."
	::= { axrOspfStubAreaEntry 4 }

axrOspfStubStatus OBJECT-TYPE
	SYNTAX  INTEGER
	ACCESS  read-only
	STATUS  mandatory
	DESCRIPTION
		"This variable displays the status of the entry.
		This value is only valid(1)."
	::= { axrOspfStubAreaEntry 5 }

axrOspfStubMetricType OBJECT-TYPE
	SYNTAX  INTEGER  {
				ospfMetric(1),
				comparableCost(2),
				nonComparable(3)
		    }
	ACCESS  read-only
	STATUS  mandatory
	DESCRIPTION
		"his variable displays the type of metric advertised
		as a default route."
	::= { axrOspfStubAreaEntry 6 }

axrOspfLsdbTable OBJECT-TYPE
	SYNTAX  SEQUENCE OF AxrOspfLsdbEntry
	ACCESS  not-accessible
	STATUS  mandatory
	DESCRIPTION
		"The OSPF Process's Link State Database."
	::= { axrOspf 4 }

axrOspfLsdbEntry OBJECT-TYPE
	SYNTAX  AxrOspfLsdbEntry
	ACCESS  not-accessible
	STATUS  mandatory
	DESCRIPTION
		 "A single Link State Advertisement."
    INDEX { axrOspfLsdbDomainNumber, axrOspfLsdbAreaId,
		    axrOspfLsdbType, axrOspfLsdbLsid, axrOspfLsdbRouterId }
	::= { axrOspfLsdbTable 1 }

	AxrOspfLsdbEntry ::=
		SEQUENCE {
		    axrOspfLsdbDomainNumber	INTEGER,
		    axrOspfLsdbAreaId		IpAddress,
		    axrOspfLsdbType		INTEGER,
		    axrOspfLsdbLsid		IpAddress,
		    axrOspfLsdbRouterId		IpAddress,
		    axrOspfLsdbSequence		INTEGER,
		    axrOspfLsdbAge		INTEGER,
		    axrOspfLsdbChecksum		INTEGER,
		    axrOspfLsdbAdvertisement	OCTET STRING
		}

axrOspfLsdbDomainNumber OBJECT-TYPE
	SYNTAX  INTEGER
	ACCESS  read-only
	STATUS  mandatory
	DESCRIPTION
		"The identifier of the domain from  which
		the LSA was received."
	::= { axrOspfLsdbEntry 1 }

axrOspfLsdbAreaId OBJECT-TYPE
	SYNTAX  IpAddress
	ACCESS  read-only
	STATUS  mandatory
	DESCRIPTION
		"The 32 bit identifier of the Area  from  which
		the LSA was received."
	::= { axrOspfLsdbEntry 2 }

axrOspfLsdbType OBJECT-TYPE
	SYNTAX  INTEGER    {
		       routerLink (1),
		       networkLink (2),
		       summaryLink (3),
		       asSummaryLink (4),
		       asExternalLink (5), -- but see axrOspfExtLsdbTable
		       multicastLink (6),
		       nssaExternalLink (7)
		    }
	ACCESS  read-only
	STATUS  mandatory
	DESCRIPTION
		"The type  of  the  link  state  advertisement."
	::= { axrOspfLsdbEntry 3 }

axrOspfLsdbLsid OBJECT-TYPE
	SYNTAX  IpAddress
	ACCESS  read-only
	STATUS  mandatory
	DESCRIPTION
		"The Link State ID . It identifies the piece of the routing
		domain that is being described by the advertisement."
	::= { axrOspfLsdbEntry 4 }

axrOspfLsdbRouterId OBJECT-TYPE
	SYNTAX  IpAddress
	ACCESS  read-only
	STATUS  mandatory
	DESCRIPTION
		"The number that uniquely identifies the originating 
		router in the Autonomous System."
	::= { axrOspfLsdbEntry 5 }

axrOspfLsdbSequence OBJECT-TYPE
	SYNTAX  INTEGER
	ACCESS  read-only
	STATUS  mandatory
	DESCRIPTION
		"The sequence number field is a  signed  32-bit
		integer."
	::= { axrOspfLsdbEntry 6 }

axrOspfLsdbAge OBJECT-TYPE
	SYNTAX  INTEGER
	ACCESS  read-only
	STATUS  mandatory
	DESCRIPTION
		"This the age of the link state adver-
		tisement in seconds."
	::= { axrOspfLsdbEntry 7 }

axrOspfLsdbChecksum OBJECT-TYPE
	SYNTAX  INTEGER
	ACCESS  read-only
	STATUS  mandatory
	DESCRIPTION
		"This field is the  checksum  of  the  complete
		contents  of  the  advertisement, excepting the
		age field."
	::= { axrOspfLsdbEntry 8 }

axrOspfLsdbAdvertisement OBJECT-TYPE
	SYNTAX  OCTET STRING
	ACCESS  read-only
	STATUS  mandatory
	DESCRIPTION
		"The entire Link State Advertisement, including
		its header."
	::= { axrOspfLsdbEntry 9 }

axrOspfAreaRangeTable OBJECT-TYPE
	SYNTAX  SEQUENCE OF AxrOspfAreaRangeEntry
	ACCESS  not-accessible
	STATUS  mandatory
	DESCRIPTION
		"A range if IP addresses  specified  by  an  IP
		address/IP  network  mask  pair."
	::= { axrOspf 5 }

axrOspfAreaRangeEntry OBJECT-TYPE
	SYNTAX  AxrOspfAreaRangeEntry
	ACCESS  not-accessible
	STATUS  mandatory
	DESCRIPTION
		"A range if IP addresses specified by an IP
		address/IP network mask pair."
    INDEX { axrOspfAreaRangeDomainNumber, axrOspfAreaRangeAreaId,
		    axrOspfAreaRangeNet }
	::= { axrOspfAreaRangeTable 1 }

	AxrOspfAreaRangeEntry ::=
		SEQUENCE {
		    axrOspfAreaRangeDomainNumber	INTEGER,
		    axrOspfAreaRangeAreaId	IpAddress,
		    axrOspfAreaRangeNet		IpAddress,
		    axrOspfAreaRangeMask		IpAddress,
		    axrOspfAreaRangeStatus	INTEGER,
		    axrOspfAreaRangeEffect	INTEGER
		}

axrOspfAreaRangeDomainNumber OBJECT-TYPE
	SYNTAX  INTEGER
	ACCESS  read-only
	STATUS  mandatory
	DESCRIPTION
		"Domain number of the Area."
	::= { axrOspfAreaRangeEntry 1 }

axrOspfAreaRangeAreaId OBJECT-TYPE
	SYNTAX  IpAddress
	ACCESS  read-only
	STATUS  mandatory
	DESCRIPTION
		"The Area the Address  Range  is  to  be  found
		within."
	::= { axrOspfAreaRangeEntry 2 }

axrOspfAreaRangeNet OBJECT-TYPE
	SYNTAX  IpAddress
	ACCESS  read-only
	STATUS  mandatory
	DESCRIPTION
		"The IP Address of the Net or Subnet  indicated
		by the range."
	::= { axrOspfAreaRangeEntry 3 }

axrOspfAreaRangeMask OBJECT-TYPE
	SYNTAX  IpAddress
	ACCESS  read-only
	STATUS  mandatory
	DESCRIPTION
		"The Subnet Mask that pertains to  the  Net  or
		Subnet."
	::= { axrOspfAreaRangeEntry 4 }

axrOspfAreaRangeStatus OBJECT-TYPE
	SYNTAX  INTEGER    {
		       valid(1),
		       invalid(2)
		    }
	ACCESS  read-only
	STATUS  mandatory
	DESCRIPTION
		"This variable displays the status of  the  entry.
		This value is only valid(1)."
	::= { axrOspfAreaRangeEntry 5 }

axrOspfAreaRangeEffect OBJECT-TYPE
	SYNTAX  INTEGER  {
				advertiseMatching (1),
				doNotAdvertiseMatching (2)
		    }
	ACCESS  read-only
	STATUS  mandatory
	DESCRIPTION
		"Subnets subsumed by ranges either trigger  the
		advertisement  of the indicated summary (adver-
		tiseMatching), or result in  the  subnet's  not
		being advertised at all outside the area."
	::= { axrOspfAreaRangeEntry 6 }

axrOspfHostTable OBJECT-TYPE
	SYNTAX  SEQUENCE OF AxrOspfHostEntry
	ACCESS  not-accessible
	STATUS  mandatory
	DESCRIPTION
		"The list of Hosts, and their metrics, that the
		router will advertise as host routes."
	::= { axrOspf 6 }

axrOspfHostEntry OBJECT-TYPE
	SYNTAX  AxrOspfHostEntry
	ACCESS  not-accessible
	STATUS  mandatory
	DESCRIPTION
		"A metric to be advertised, for a given type of service,
		when a given host is reachable."
    INDEX { axrOspfHostDomainNumber, axrOspfHostIpAddress,
		    axrOspfHostTOS }
	::= { axrOspfHostTable 1 }

	AxrOspfHostEntry ::=
		SEQUENCE {
		    axrOspfHostDomainNumber	INTEGER,
		    axrOspfHostIpAddress		IpAddress,
		    axrOspfHostTOS			INTEGER,
		    axrOspfHostMetric		INTEGER,
		    axrOspfHostStatus		INTEGER
		}

axrOspfHostDomainNumber OBJECT-TYPE
	SYNTAX  INTEGER
	ACCESS  read-only
	STATUS  mandatory
	DESCRIPTION
		"OSPF domain number of the Host."
	::= { axrOspfHostEntry 1 }

axrOspfHostIpAddress OBJECT-TYPE
	SYNTAX  IpAddress
	ACCESS  read-only
	STATUS  mandatory
	DESCRIPTION
		"The IP Address of the Host."
	::= { axrOspfHostEntry 2 }

axrOspfHostTOS OBJECT-TYPE
	SYNTAX  INTEGER
	ACCESS  read-only
	STATUS  mandatory
	DESCRIPTION
		"The Type of Service of the route being configured.
		This value is only 0."
	::= { axrOspfHostEntry 3 }

axrOspfHostMetric OBJECT-TYPE
	SYNTAX  INTEGER
	ACCESS  read-only
	STATUS  mandatory
	DESCRIPTION
		"The Metric to be advertised."
	::= { axrOspfHostEntry 4 }

axrOspfHostStatus OBJECT-TYPE
	SYNTAX  INTEGER   { 
				valid(1),
				invalid(2)
		    }
	ACCESS  read-only
	STATUS  mandatory
	DESCRIPTION
		"This variable displays the status of  the  entry.
		Setting it to 'invalid' has the effect of rendering
		it inoperative. The internal effect (row removal) is
		implementation dependent."
	::= { axrOspfHostEntry 5 }

axrOspfIfTable OBJECT-TYPE
	SYNTAX  SEQUENCE OF AxrOspfIfEntry
	ACCESS  not-accessible
	STATUS  mandatory
	DESCRIPTION
		"The OSPF Interface Table describes the interfaces
		from the viewpoint of OSPF."
	::= { axrOspf 7 }

axrOspfIfEntry OBJECT-TYPE
	SYNTAX  AxrOspfIfEntry
	ACCESS  not-accessible
	STATUS  mandatory
	DESCRIPTION
		"The OSPF Interface Entry describes one  interface
		from the viewpoint of OSPF."
    INDEX { axrOspfIfDomainNumber, axrOspfIfIpAddress, axrOspfAddressLessIf }
	::= { axrOspfIfTable 1 }

	AxrOspfIfEntry ::=
		SEQUENCE {
		    axrOspfIfDomainNumber			INTEGER,
		    axrOspfIfIpAddress				IpAddress,
		    axrOspfAddressLessIf				INTEGER,
		    axrOspfIfAreaId					IpAddress,
		    axrOspfIfType					INTEGER,
		    axrOspfIfAdminStat				INTEGER,
		    axrOspfIfRtrPriority				INTEGER,
		    axrOspfIfTransitDelay			INTEGER,
		    axrOspfIfRetransInterval			INTEGER,
		    axrOspfIfHelloInterval			INTEGER,
		    axrOspfIfRtrDeadInterval			INTEGER,
		    axrOspfIfPollInterval			INTEGER,
		    axrOspfIfState					INTEGER,
		    axrOspfIfDesignatedRouter		IpAddress,
		    axrOspfIfEvents					Counter,
		    axrOspfIfAuthKey					OCTET STRING,
		    axrOspfIfStatus					INTEGER,
		    axrOspfIfMulticastForwarding		INTEGER,
		    axrOspfIfBackupDesignatedRouter	IpAddress
		}

axrOspfIfDomainNumber OBJECT-TYPE
	SYNTAX  INTEGER
	ACCESS  read-only
	STATUS  mandatory
	DESCRIPTION
		"The domain number of this OSPF interface."
	::= { axrOspfIfEntry 1 }

axrOspfIfIpAddress OBJECT-TYPE
	SYNTAX  IpAddress
	ACCESS  read-only
	STATUS  mandatory
	DESCRIPTION
		"The IP address of this OSPF interface."
	::= { axrOspfIfEntry 2 }

axrOspfAddressLessIf OBJECT-TYPE
	SYNTAX  INTEGER
	ACCESS  read-only
	STATUS  mandatory
	DESCRIPTION
		"For the purpose of easing  the  instancing  of
		addressed   and  addressless  interfaces;  This
		variable takes the value 0 on  interfaces  with
		IP  Addresses,  and  the corresponding value of
		ifIndex for interfaces having no IP Address."
	::= { axrOspfIfEntry 3 }

axrOspfIfAreaId OBJECT-TYPE
	SYNTAX  IpAddress
	ACCESS  read-only
	STATUS  mandatory
	DESCRIPTION
		"A integer uniquely identifying the area to which 
		the interface connects."
	::= { axrOspfIfEntry 4 }

axrOspfIfType OBJECT-TYPE
	SYNTAX  INTEGER  {
				 broadcast (1),
				 nbma (2),
				 pointToPoint (3),
				 pointToMultipoint (5)
		    }
	ACCESS  read-only
	STATUS  mandatory
	DESCRIPTION
		"The OSPF interface type."
	::= { axrOspfIfEntry 5 }

axrOspfIfAdminStat OBJECT-TYPE
	SYNTAX  INTEGER { 
				enabled(1),
				disabled(2)
		    }
	ACCESS  read-only
	STATUS  mandatory
	DESCRIPTION
		"The OSPF  interface's  administrative  status."
	::= { axrOspfIfEntry 6 }

axrOspfIfRtrPriority OBJECT-TYPE
	SYNTAX  INTEGER
	ACCESS  read-only
	STATUS  mandatory
	DESCRIPTION
		"The priority of this interface."
	::= { axrOspfIfEntry 7 }

axrOspfIfTransitDelay OBJECT-TYPE
	SYNTAX  INTEGER
	ACCESS  read-only
	STATUS  mandatory
	DESCRIPTION
		"The estimated number of seconds  it  takes  to
		transmit  a  link state update packet over this
		interface."
	::= { axrOspfIfEntry 8 }

axrOspfIfRetransInterval OBJECT-TYPE
	SYNTAX  INTEGER
	ACCESS  read-only
	STATUS  mandatory
	DESCRIPTION
		"The number of seconds between link-state ad-
		vertisement retransmissions, for adjacencies
		belonging to this  interface."
	::= { axrOspfIfEntry 9 }

axrOspfIfHelloInterval OBJECT-TYPE
	SYNTAX  INTEGER
	ACCESS  read-only
	STATUS  mandatory
	DESCRIPTION
		"The length of time, in  seconds,  between the
		Hello  packets that the router sends on the interface."
	::= { axrOspfIfEntry 10 }

axrOspfIfRtrDeadInterval OBJECT-TYPE
	SYNTAX  INTEGER
	ACCESS  read-only
	STATUS  mandatory
	DESCRIPTION
		"The number of seconds that  a  router's  Hello
		packets  have  not been seen before it's neighbors 
		declare the router down."
	::= { axrOspfIfEntry 11 }

axrOspfIfPollInterval OBJECT-TYPE
	SYNTAX  INTEGER
	ACCESS  read-only
	STATUS  mandatory
	DESCRIPTION
		"The larger time interval, in seconds,  between
		the  Hello  packets  sent  to  an inactive non-
		broadcast multi- access neighbor."
	::= { axrOspfIfEntry 12 }

axrOspfIfState OBJECT-TYPE
	SYNTAX  INTEGER   {
				down (1),
				loopback (2),
				waiting (3),
				pointToPoint (4),
				designatedRouter (5),
				backupDesignatedRouter (6),
				otherDesignatedRouter (7)
		    }
	ACCESS  read-only
	STATUS  mandatory
	DESCRIPTION
		"The OSPF Interface State."
	::= { axrOspfIfEntry 13 }

axrOspfIfDesignatedRouter OBJECT-TYPE
	SYNTAX  IpAddress
	ACCESS  read-only
	STATUS  mandatory
	DESCRIPTION
		"The IP Address of the Designated Router."
	::= { axrOspfIfEntry 14 }

axrOspfIfEvents OBJECT-TYPE
	SYNTAX  Counter
	ACCESS  read-only
	STATUS  mandatory
	DESCRIPTION
		"The number of times this  OSPF  interface  has
		changed its state, or an error has occurred."
	::= { axrOspfIfEntry 16 }

axrOspfIfAuthKey OBJECT-TYPE
	SYNTAX  OCTET STRING
	ACCESS  read-only
	STATUS  mandatory
	DESCRIPTION
		"The Authentication Key."
	::= { axrOspfIfEntry 17 }

axrOspfIfStatus OBJECT-TYPE
	SYNTAX  INTEGER   { 
				valid(1),
				invalid(2)
		    }
	ACCESS  read-only
	STATUS  mandatory
	DESCRIPTION
		"This variable displays the status of  the  entry.
		this value is only valid(1)."
	::= { axrOspfIfEntry 18 }

axrOspfIfMulticastForwarding OBJECT-TYPE
	SYNTAX  INTEGER  {
				blocked (1),		-- no multicast forwarding
				multicast (2),     -- using multicast address
				unicast (3)		-- to each OSPF neighbor
		    }
	ACCESS  read-only
	STATUS  mandatory
	DESCRIPTION
		"The way multicasts should  forwarded  on  this
		interface;  not  forwarded,  forwarded  as data
		link multicasts, or forwarded as data link unicasts."
	::= { axrOspfIfEntry 19 }

axrOspfIfBackupDesignatedRouter OBJECT-TYPE
	SYNTAX  IpAddress
	ACCESS  read-only
	STATUS  mandatory
	DESCRIPTION
		"The IP Address of the Backup Designated Router."
	::= { axrOspfIfEntry 15 }

axrOspfIfMetricTable OBJECT-TYPE
	SYNTAX  SEQUENCE OF AxrOspfIfMetricEntry
	ACCESS  not-accessible
	STATUS  mandatory
	DESCRIPTION
		"The TOS metrics for a non-virtual interface identified
		by the interface index."
	::= { axrOspf 8 }

axrOspfIfMetricEntry OBJECT-TYPE
	SYNTAX  AxrOspfIfMetricEntry
	ACCESS  not-accessible
	STATUS  mandatory
	DESCRIPTION
		"A particular TOS metric for a non-virtual interface
		identified by the interface index."
    INDEX { axrOspfIfMetricDomainNumber, axrOspfIfMetricIpAddress,
		    axrOspfIfMetricAddressLessIf, axrOspfIfMetricTOS }
	::= { axrOspfIfMetricTable 1 }

	AxrOspfIfMetricEntry ::=
		SEQUENCE {
		    axrOspfIfMetricDomainNumber	INTEGER,
		    axrOspfIfMetricIpAddress		IpAddress,
		    axrOspfIfMetricAddressLessIf	INTEGER,
		    axrOspfIfMetricTOS			INTEGER,
		    axrOspfIfMetricValue			INTEGER,
		    axrOspfIfMetricStatus		INTEGER
		}

axrOspfIfMetricDomainNumber OBJECT-TYPE
	SYNTAX  INTEGER
	ACCESS  read-only
	STATUS  mandatory
	DESCRIPTION
		"The domain number of this OSPF interface."
	::= { axrOspfIfMetricEntry 1 }

axrOspfIfMetricIpAddress OBJECT-TYPE
	SYNTAX  IpAddress
	ACCESS  read-only
	STATUS  mandatory
	DESCRIPTION
		"The IP address of this OSPF interface."
	::= { axrOspfIfMetricEntry 2 }

axrOspfIfMetricAddressLessIf OBJECT-TYPE
	SYNTAX  INTEGER
	ACCESS  read-only
	STATUS  mandatory
	DESCRIPTION
		"For the purpose of easing  the  instancing  of
		addressed   and  addressless  interfaces;  This
		variable takes the value 0 on  interfaces  with
		IP  Addresses, and the value of ifIndex for in-
		terfaces having no IP Address."
	::= { axrOspfIfMetricEntry 3 }

axrOspfIfMetricTOS OBJECT-TYPE
	SYNTAX  INTEGER
	ACCESS  read-only
	STATUS  mandatory
	DESCRIPTION
		"The type of service metric  being  referenced.
		this value is only 0."
	::= { axrOspfIfMetricEntry 4 }

axrOspfIfMetricValue OBJECT-TYPE
	SYNTAX  INTEGER
	ACCESS  read-only
	STATUS  mandatory
	DESCRIPTION
		"The metric of using this type  of  service  on
		this interface."
	::= { axrOspfIfMetricEntry 5 }

axrOspfIfMetricStatus OBJECT-TYPE
	SYNTAX  INTEGER
	ACCESS  read-only
	STATUS  mandatory
	DESCRIPTION
		"This variable displays the status of the entry.
		This entry status is only valid(1)."
	::= { axrOspfIfMetricEntry 6 }

axrOspfVirtIfTable OBJECT-TYPE
	SYNTAX  SEQUENCE OF AxrOspfVirtIfEntry
	ACCESS  not-accessible
	STATUS  mandatory
	DESCRIPTION
		"Information about this router's virtual interfaces."
	::= { axrOspf 9 }

axrOspfVirtIfEntry OBJECT-TYPE
	SYNTAX  AxrOspfVirtIfEntry
	ACCESS  not-accessible
	STATUS  mandatory
	DESCRIPTION
		"Information about a single Virtual Interface."
    INDEX { axrOspfVirtIfDomainNumber, axrOspfVirtIfAreaId,
		    axrOspfVirtIfNeighbor }
	::= { axrOspfVirtIfTable 1 }

	AxrOspfVirtIfEntry ::=
		SEQUENCE {
		    axrOspfVirtIfDomainNumber	INTEGER,
		    axrOspfVirtIfAreaId			IpAddress,
		    axrOspfVirtIfNeighbor		IpAddress,
		    axrOspfVirtIfTransitDelay	INTEGER,
		    axrOspfVirtIfRetransInterval	INTEGER,
		    axrOspfVirtIfHelloInterval	INTEGER,
		    axrOspfVirtIfRtrDeadInterval	INTEGER,
		    axrOspfVirtIfState			INTEGER,
		    axrOspfVirtIfEvents			Counter,
		    axrOspfVirtIfAuthKey			OCTET STRING,
		    axrOspfVirtIfStatus			INTEGER
		}

axrOspfVirtIfDomainNumber OBJECT-TYPE
	SYNTAX  INTEGER
	ACCESS  read-only
	STATUS  mandatory
	DESCRIPTION
		"The domain number for this  Virtual Interface"
	::= { axrOspfVirtIfEntry 1 }

axrOspfVirtIfAreaId OBJECT-TYPE
	SYNTAX  IpAddress
	ACCESS  read-only
	STATUS  mandatory
	DESCRIPTION
		"The Transit Area that the Virtual Link traverses."
	::= { axrOspfVirtIfEntry 2 }

axrOspfVirtIfNeighbor OBJECT-TYPE
	SYNTAX  IpAddress
	ACCESS  read-only
	STATUS  mandatory
	DESCRIPTION
		"The Router ID of the Virtual Neighbor."
	::= { axrOspfVirtIfEntry 3 }

axrOspfVirtIfTransitDelay OBJECT-TYPE
	SYNTAX  INTEGER
	ACCESS  read-only
	STATUS  mandatory
	DESCRIPTION
		"The estimated number of seconds  it  takes  to
		transmit  a link- state update packet over this
		interface."
	::= { axrOspfVirtIfEntry 4 }

axrOspfVirtIfRetransInterval OBJECT-TYPE
	SYNTAX  INTEGER
	ACCESS  read-only
	STATUS  mandatory
	DESCRIPTION
		"The number of seconds between link-state advertisement
		retransmissions, for adjacencies belonging to this
		interface."
	::= { axrOspfVirtIfEntry 5 }

axrOspfVirtIfHelloInterval OBJECT-TYPE
	SYNTAX  INTEGER
	ACCESS  read-only
	STATUS  mandatory
	DESCRIPTION
		"The length of time, in  seconds, between the
		Hello  packets that the router sends on the in-
		terface. "
	::= { axrOspfVirtIfEntry 6 }

axrOspfVirtIfRtrDeadInterval OBJECT-TYPE
	SYNTAX  INTEGER
	ACCESS  read-only
	STATUS  mandatory
	DESCRIPTION
		"The number of seconds that  a  router's  Hello
		packets  have  not been seen before it's neighbors
		declare the router down."
	::= { axrOspfVirtIfEntry 7 }

axrOspfVirtIfState OBJECT-TYPE
	SYNTAX  INTEGER    {
				down (1),		    -- these use the same encoding
				pointToPoint (4)     -- as the axrOspfIfTable
		    }
	ACCESS  read-only
	STATUS  mandatory
	DESCRIPTION
		"OSPF virtual interface states."
	::= { axrOspfVirtIfEntry 8 }

axrOspfVirtIfEvents OBJECT-TYPE
	SYNTAX  Counter
	ACCESS  read-only
	STATUS  mandatory
	DESCRIPTION
		"The number of state changes or error events on
		this Virtual Link"
	::= { axrOspfVirtIfEntry 9 }

axrOspfVirtIfAuthKey OBJECT-TYPE
	SYNTAX  OCTET STRING
	ACCESS  read-only
	STATUS  mandatory
	DESCRIPTION
		"Authentication key of this interface."
	::= { axrOspfVirtIfEntry 10 }

axrOspfVirtIfStatus OBJECT-TYPE
	SYNTAX  INTEGER    { 
				valid(1),
				invalid(2)
		    }
	ACCESS  read-only
	STATUS  mandatory
	DESCRIPTION
		"This variable displays the status of  the  entry.
		This entry is only valid(1)."
	::= { axrOspfVirtIfEntry 11 }

axrOspfNbrTable OBJECT-TYPE
	SYNTAX  SEQUENCE OF AxrOspfNbrEntry
	ACCESS  not-accessible
	STATUS  mandatory
	DESCRIPTION
		"A table of non-virtual neighbor information."
	::= { axrOspf 10 }

axrOspfNbrEntry OBJECT-TYPE
	SYNTAX  AxrOspfNbrEntry
	ACCESS  not-accessible
	STATUS  mandatory
	DESCRIPTION
		"The information regarding a single neighbor."
    INDEX { axrOspfNbrDomainNumber, axrOspfNbrIpAddr, axrOspfNbrAddressLessIndex }
	::= { axrOspfNbrTable 1 }

	AxrOspfNbrEntry ::=
		SEQUENCE {
		    axrOspfNbrDomainNumber		INTEGER,
		    axrOspfNbrIpAddr				IpAddress,
		    axrOspfNbrAddressLessIndex	INTEGER,
		    axrOspfNbrRtrId				IpAddress,
		    axrOspfNbrOptions			INTEGER,
		    axrOspfNbrPriority			INTEGER,
		    axrOspfNbrState				INTEGER,
		    axrOspfNbrEvents				Counter,
		    axrOspfNbrLsRetransQLen		Gauge,
		    axrOspfNbmaNbrStatus			INTEGER,
		    axrOspfNbmaNbrPermanence		INTEGER
		}

axrOspfNbrDomainNumber OBJECT-TYPE
	SYNTAX  INTEGER
	ACCESS  read-only
	STATUS  mandatory
	DESCRIPTION
		"OSPF domain number of this neighbor."
	::= { axrOspfNbrEntry 1 }

axrOspfNbrIpAddr OBJECT-TYPE
	SYNTAX  IpAddress
	ACCESS  read-only
	STATUS  mandatory
	DESCRIPTION
		"The IP address this neighbor is using  in  its
		IP  Source  Address."
	::= { axrOspfNbrEntry 2 }

axrOspfNbrAddressLessIndex OBJECT-TYPE
	SYNTAX  INTEGER
	ACCESS  read-only
	STATUS  mandatory
	DESCRIPTION
		"On an interface having an  IP  Address,  zero.
		On  addressless  interfaces,  the corresponding
		value of ifIndex in the Internet Standard  MIB."
	::= { axrOspfNbrEntry 3 }

axrOspfNbrRtrId OBJECT-TYPE
	SYNTAX  IpAddress
	ACCESS  read-only
	STATUS  mandatory
	DESCRIPTION
		"The integer uniquely identifying the neighboring
		router in the Autonomous System."
	::= { axrOspfNbrEntry 4 }

axrOspfNbrOptions OBJECT-TYPE
	SYNTAX  INTEGER
	ACCESS  read-only
	STATUS  mandatory
	DESCRIPTION
		"A Bit Mask corresponding to the neighbor's op-
		 tions field.

		 Bit 0, if set, indicates that the  system  will
		 operate  on  Type of Service metrics other than
		 TOS 0.  If zero, the neighbor will  ignore  all
		 metrics except the TOS 0 metric.

		 Bit 1, if set, indicates  that  the  associated
		 area  accepts and operates on external informa-
		 tion; if zero, it is a stub area.

		 Bit 2, if set, indicates that the system is ca-
		 pable  of routing IP Multicast datagrams; i.e.,
		 that it implements the Multicast Extensions  to
		 OSPF.

		 Bit 3, if set, indicates  that  the  associated
		 area  is  an  NSSA.  These areas are capable of
		 carrying type 7 external advertisements,  which
		 are  translated into type 5 external advertise-
		 ments at NSSA borders."
	::= { axrOspfNbrEntry 5 }

axrOspfNbrPriority OBJECT-TYPE
	SYNTAX  INTEGER
	ACCESS  read-only
	STATUS  mandatory
	DESCRIPTION
		"The priority of this neighbor."
	::= { axrOspfNbrEntry 6 }

axrOspfNbrState OBJECT-TYPE
	SYNTAX  INTEGER   {
				down (1),
				attempt (2),
				init (3),
				twoWay (4),
				exchangeStart (5),
				exchange (6),
				loading (7),
				full (8)
		    }
	ACCESS  read-only
	STATUS  mandatory
	DESCRIPTION
		"The State of the relationship with this Neighbor."
	::= { axrOspfNbrEntry 7 }

axrOspfNbrEvents OBJECT-TYPE
	SYNTAX  Counter
	ACCESS  read-only
	STATUS  mandatory
	DESCRIPTION
		"The number of times this neighbor relationship
		has changed state, or an error has occurred."
	::= { axrOspfNbrEntry 8 }

axrOspfNbrLsRetransQLen OBJECT-TYPE
	SYNTAX  Gauge
	ACCESS  read-only
	STATUS  mandatory
	DESCRIPTION
		"The current length of the retransmission queue."
	::= { axrOspfNbrEntry 9 }

axrOspfNbmaNbrStatus OBJECT-TYPE
	SYNTAX  INTEGER
	ACCESS  read-only
	STATUS  mandatory
	DESCRIPTION
		"This variable displays the status of the entry.
		This entry value is only valid(1). And enable to response
		this entry when axrOspfIfType is nbma."
	::= { axrOspfNbrEntry 10 }

axrOspfNbmaNbrPermanence OBJECT-TYPE
	SYNTAX  INTEGER  {
				dynamic (1),		-- learned through protocol
				 permanent (2)       -- configured address
		    }
	ACCESS  read-only
	STATUS  mandatory
	DESCRIPTION
		"This variable displays the status of the entry."
	::= { axrOspfNbrEntry 11 }

axrOspfVirtNbrTable OBJECT-TYPE
	SYNTAX  SEQUENCE OF AxrOspfVirtNbrEntry
	ACCESS  not-accessible
	STATUS  mandatory
	DESCRIPTION
		"A table of virtual neighbor information."
	::= { axrOspf 11 }

axrOspfVirtNbrEntry OBJECT-TYPE
	SYNTAX  AxrOspfVirtNbrEntry
	ACCESS  not-accessible
	STATUS  mandatory
	DESCRIPTION
		"Virtual neighbor information."
    INDEX { axrOspfVirtNbrDomainNumber, axrOspfVirtNbrArea,
		    axrOspfVirtNbrRtrId }
	::= { axrOspfVirtNbrTable 1 }

	AxrOspfVirtNbrEntry ::=
		SEQUENCE {
		    axrOspfVirtNbrDomainNumber		INTEGER,
		    axrOspfVirtNbrArea				IpAddress,
		    axrOspfVirtNbrRtrId				IpAddress,
		    axrOspfVirtNbrIpAddr				IpAddress,
		    axrOspfVirtNbrOptions			INTEGER,
		    axrOspfVirtNbrState				INTEGER,
		    axrOspfVirtNbrEvents				Counter,
		    axrOspfVirtNbrLsRetransQLen		Gauge
		}

axrOspfVirtNbrDomainNumber OBJECT-TYPE
	SYNTAX  INTEGER
	ACCESS  read-only
	STATUS  mandatory
	DESCRIPTION
		"The domain number."
	::= { axrOspfVirtNbrEntry 1 }

axrOspfVirtNbrArea OBJECT-TYPE
	SYNTAX  IpAddress
	ACCESS  read-only
	STATUS  mandatory
	DESCRIPTION
		"The Transit Area Identifier."
	::= { axrOspfVirtNbrEntry 2 }

axrOspfVirtNbrRtrId OBJECT-TYPE
	SYNTAX  IpAddress
	ACCESS  read-only
	STATUS  mandatory
	DESCRIPTION
		"A integer  uniquely  identifying  the neighboring
		 router in the Autonomous System."
	::= { axrOspfVirtNbrEntry 3 }

axrOspfVirtNbrIpAddr OBJECT-TYPE
	SYNTAX  IpAddress
	ACCESS  read-only
	STATUS  mandatory
	DESCRIPTION
		"The IP address this Virtual Neighbor is using."
	::= { axrOspfVirtNbrEntry 4 }

axrOspfVirtNbrOptions OBJECT-TYPE
	SYNTAX  INTEGER
	ACCESS  read-only
	STATUS  mandatory
	DESCRIPTION
		"A Bit Mask corresponding to the neighbor's options
		 field.

		 Bit 1, if set, indicates that the  system  will operate
		 on Type of Service metrics other than TOS 0. If zero,
		 the neighbor will  ignore  all metrics except the TOS
		 0 metric.

		 Bit 2, if set, indicates  that  the  system  is Network
		 Multicast  capable; ie, that it implements OSPF Multicast
		 Routing."
	::= { axrOspfVirtNbrEntry 5 }

axrOspfVirtNbrState OBJECT-TYPE
	SYNTAX  INTEGER   {
				down (1),
				attempt (2),
				init (3),
				twoWay (4),
				exchangeStart (5),
				exchange (6),
				loading (7),
				full (8)
		    }
	ACCESS  read-only
	STATUS  mandatory
	DESCRIPTION
		"The state of the  Virtual  Neighbor  Relationship."
	::= { axrOspfVirtNbrEntry 6 }

axrOspfVirtNbrEvents OBJECT-TYPE
	SYNTAX  Counter
	ACCESS  read-only
	STATUS  mandatory
	DESCRIPTION
		"The number of times this virtual link has changed
		its state, or an error has occurred."
	::= { axrOspfVirtNbrEntry 7 }

axrOspfVirtNbrLsRetransQLen OBJECT-TYPE
	SYNTAX  Gauge
	ACCESS  read-only
	STATUS  mandatory
	DESCRIPTION
		"The current length of the retransmission queue."
	::= { axrOspfVirtNbrEntry 8 }

axrOspfExtLsdbTable OBJECT-TYPE
	SYNTAX  SEQUENCE OF AxrOspfExtLsdbEntry
	ACCESS  not-accessible
	STATUS  mandatory
	DESCRIPTION
		"The OSPF Process's Links State Database."
	::= { axrOspf 12 }

axrOspfExtLsdbEntry OBJECT-TYPE
	SYNTAX  AxrOspfExtLsdbEntry
	ACCESS  not-accessible
	STATUS  mandatory
	DESCRIPTION
		"A single Link State Advertisement."
    INDEX { axrOspfExtLsdbDomainNumber, axrOspfExtLsdbType,
		    axrOspfExtLsdbLsid, axrOspfExtLsdbRouterId }
	::= { axrOspfExtLsdbTable 1 }

	AxrOspfExtLsdbEntry ::=
		SEQUENCE {
		    axrOspfExtLsdbDomainNumber	INTEGER,
		    axrOspfExtLsdbType			INTEGER,
		    axrOspfExtLsdbLsid			IpAddress,
		    axrOspfExtLsdbRouterId		IpAddress,
		    axrOspfExtLsdbSequence		INTEGER,
		    axrOspfExtLsdbAge			INTEGER,
		    axrOspfExtLsdbChecksum		INTEGER,
		    axrOspfExtLsdbAdvertisement	OCTET STRING
		}

axrOspfExtLsdbDomainNumber OBJECT-TYPE
	SYNTAX  INTEGER
	ACCESS  read-only
	STATUS  mandatory
	DESCRIPTION
		"OSPF domain number."
	::= { axrOspfExtLsdbEntry 1 }

axrOspfExtLsdbType OBJECT-TYPE
	SYNTAX  INTEGER {
				asExternalLink (5)
		    }
	ACCESS  read-only
	STATUS  mandatory
	DESCRIPTION
		"The type  of  the  link  state  advertisement."
	::= { axrOspfExtLsdbEntry 2 }

axrOspfExtLsdbLsid OBJECT-TYPE
	SYNTAX  IpAddress
	ACCESS  read-only
	STATUS  mandatory
	DESCRIPTION
		"The Link State ID is an LS Type Specific field
		 containing either a Router ID or an IP Address;
		 it identifies the piece of the  routing  domain
		 that is being described by the advertisement."
	::= { axrOspfExtLsdbEntry 3 }

axrOspfExtLsdbRouterId OBJECT-TYPE
	SYNTAX  IpAddress
	ACCESS  read-only
	STATUS  mandatory
	DESCRIPTION
		"The 32 bit number that uniquely identifies the
		originating router in the Autonomous System."
	::= { axrOspfExtLsdbEntry 4 }

axrOspfExtLsdbSequence OBJECT-TYPE
	SYNTAX  INTEGER
	ACCESS  read-only
	STATUS  mandatory
	DESCRIPTION
		"The sequence number field is a  signed  32-bit integer."
	::= { axrOspfExtLsdbEntry 5 }

axrOspfExtLsdbAge OBJECT-TYPE
	SYNTAX  INTEGER
	ACCESS  read-only
	STATUS  mandatory
	DESCRIPTION
		"The age of the link state advertisement in seconds."
	::= { axrOspfExtLsdbEntry 6 }

axrOspfExtLsdbChecksum OBJECT-TYPE
	SYNTAX  INTEGER
	ACCESS  read-only
	STATUS  mandatory
	DESCRIPTION
		"This field is the  checksum  of  the  complete
		 contents  of  the  advertisement, excepting the
		 age field.  The age field is excepted  so  that
		 an   advertisement's  age  can  be  incremented
		 without updating the  checksum."
	::= { axrOspfExtLsdbEntry 7 }

axrOspfExtLsdbAdvertisement OBJECT-TYPE
	SYNTAX  OCTET STRING
	ACCESS  read-only
	STATUS  mandatory
	DESCRIPTION
		"The entire Link State Advertisement, including its header."
	::= { axrOspfExtLsdbEntry 8 }

axrOspfAreaAggregateTable OBJECT-TYPE
	SYNTAX  SEQUENCE OF AxrOspfAreaAggregateEntry
	ACCESS  not-accessible
	STATUS  mandatory
	DESCRIPTION
		"A range of IP addresses  specified  by  an  IP
		address/IP  network  mask  pair."
	::= { axrOspf 14 }

axrOspfAreaAggregateEntry OBJECT-TYPE
	SYNTAX  AxrOspfAreaAggregateEntry
	ACCESS  not-accessible
	STATUS  mandatory
	DESCRIPTION
		"A range of IP addresses  specified  by  an  IP
		address/IP  network  mask  pair."
    INDEX { axrOspfAreaAggregateDomainNumber, axrOspfAreaAggregateAreaID,
		    axrOspfAreaAggregateLsdbType, axrOspfAreaAggregateNet,
		    axrOspfAreaAggregateMask }
	::= { axrOspfAreaAggregateTable 1 }

	AxrOspfAreaAggregateEntry ::=
		SEQUENCE {
		    axrOspfAreaAggregateDomainNumber	INTEGER,
		    axrOspfAreaAggregateAreaID		IpAddress,
		    axrOspfAreaAggregateLsdbType		INTEGER,
		    axrOspfAreaAggregateNet			IpAddress,
		    axrOspfAreaAggregateMask			IpAddress,
		    axrOspfAreaAggregateStatus		INTEGER,
		    axrOspfAreaAggregateEffect		INTEGER
		}

axrOspfAreaAggregateDomainNumber OBJECT-TYPE
	SYNTAX  INTEGER
	ACCESS  read-only
	STATUS  mandatory
	DESCRIPTION
		"OSPF domain number."
	::= { axrOspfAreaAggregateEntry 1 }

axrOspfAreaAggregateAreaID OBJECT-TYPE
	SYNTAX  IpAddress
	ACCESS  read-only
	STATUS  mandatory
	DESCRIPTION
		"The Area the Address Aggregate is to be found within."
	::= { axrOspfAreaAggregateEntry 2 }

axrOspfAreaAggregateLsdbType OBJECT-TYPE
	SYNTAX  INTEGER  {
				summaryLink (3),
				nssaExternalLink (7)
		    }
	ACCESS  read-only
	STATUS  mandatory
	DESCRIPTION
		"The type of the Address Aggregate. This field
		 specifies  the  Lsdb type that this Address 
		 Aggregate applies to."
	::= { axrOspfAreaAggregateEntry 3 }

axrOspfAreaAggregateNet OBJECT-TYPE
	SYNTAX  IpAddress
	ACCESS  read-only
	STATUS  mandatory
	DESCRIPTION
		"The IP Address of the Net or Subnet indicated by the range."
	::= { axrOspfAreaAggregateEntry 4 }

axrOspfAreaAggregateMask OBJECT-TYPE
	SYNTAX  IpAddress
	ACCESS  read-only
	STATUS  mandatory
	DESCRIPTION
		"The Subnet Mask that pertains to the Net or Subnet."
	::= { axrOspfAreaAggregateEntry 5 }

axrOspfAreaAggregateStatus OBJECT-TYPE
	SYNTAX  INTEGER
	ACCESS  read-only
	STATUS  mandatory
	DESCRIPTION
		"This variable displays the status of  the  entry.
		This entry value is only valid(1)."
	::= { axrOspfAreaAggregateEntry 6 }

axrOspfAreaAggregateEffect OBJECT-TYPE
	SYNTAX  INTEGER   {
				advertiseMatching (1),
				doNotAdvertiseMatching (2)
		    }
	ACCESS  read-only
	STATUS  mandatory
	DESCRIPTION
		"Subnets subsumed by ranges either trigger  the
		 advertisement  of  the indicated aggregate (ad-
		 vertiseMatching), or result in the subnet's not
		 being advertised at all outside the area."
	::= { axrOspfAreaAggregateEntry 7 }

axrOspfTrapControlTable OBJECT-TYPE
	SYNTAX  SEQUENCE OF AxrOspfTrapControlEntry
	ACCESS  not-accessible
	STATUS  mandatory
	DESCRIPTION
		"The table about trap information."
	::= { axrOspfTrap 1 }

axrOspfTrapControlEntry OBJECT-TYPE
	SYNTAX  AxrOspfTrapControlEntry
	ACCESS  not-accessible
	STATUS  mandatory
	DESCRIPTION
		"The Entry about trap information."
	INDEX { axrOspfTrapDomainNumber }
	::= { axrOspfTrapControlTable 1 }

	AxrOspfTrapControlEntry ::=
	SEQUENCE {
		axrOspfTrapDomainNumber
			INTEGER,
		axrOspfSetTrap	
			OCTET STRING,
		axrOspfConfigErrorType	
			INTEGER,
		axrOspfPacketType	
			INTEGER,
		axrOspfPacketSrc	
			IpAddress
                }

axrOspfTrapDomainNumber OBJECT-TYPE
	SYNTAX  INTEGER
	ACCESS  read-only
	STATUS  mandatory
	DESCRIPTION
		"axrOspfTrap domain number."
	::= { axrOspfTrapControlEntry 1 }

axrOspfSetTrap OBJECT-TYPE
       SYNTAX   OCTET STRING
       ACCESS   read-write
       STATUS   mandatory
       DESCRIPTION
           "A four-octet string serving as a bit  map  for
           the trap events defined by the OSPF traps. This
           object is used to enable and  disable  specific
           OSPF   traps   where  a  1  in  the  bit  field
           represents enabled.  The right-most bit  (least
           significant) represents trap 0."
       ::= { axrOspfTrapControlEntry 2 }

axrOspfConfigErrorType OBJECT-TYPE
       SYNTAX   INTEGER   {
                   noError(0),
                   badVersion (1),
                   areaMismatch (2),
                   unknownNbmaNbr (3), -- Router is Dr eligible
                   unknownVirtualNbr (4),
                   authTypeMismatch(5),
                   authFailure (6),
                   netMaskMismatch (7),
                   helloIntervalMismatch (8),
                   deadIntervalMismatch (9),
                   optionMismatch (10)--,
                   --duplicateRouterId (12),
                   --noError (13)
                }
       ACCESS   read-only
       STATUS   mandatory
       DESCRIPTION
           "Potential types  of  configuration  conflicts.
           Used  by the ospfConfigError and ospfConfigVir-
           tError traps."
       ::= { axrOspfTrapControlEntry 3 }

axrOspfPacketType OBJECT-TYPE
        SYNTAX   INTEGER   {
                    noError(0),
                    hello (1),
                    dbDescript (2),
                    lsReq (3),
                    lsUpdate (4),
                    lsAck (5)--, 
                    --nullPacket (6)
                 }
        ACCESS   read-only
        STATUS   mandatory
        DESCRIPTION
           "OSPF packet types."
   ::= { axrOspfTrapControlEntry 4 }

axrOspfPacketSrc OBJECT-TYPE
        SYNTAX   IpAddress
        ACCESS   read-only
        STATUS   mandatory
        DESCRIPTION
           "The IP address of an inbound packet that  can-
           not be identified by a neighbor instance."
       ::= { axrOspfTrapControlEntry 5 }

-- axrOspfv3

axrOspfv3GeneralTable OBJECT-TYPE
	SYNTAX  SEQUENCE OF AxrOspfv3GeneralEntry
	ACCESS  not-accessible
	STATUS  mandatory
	DESCRIPTION
		"The table which ospfv3 information is stored in."
	::= { axrOspfv3 1 }

axrOspfv3GeneralEntry OBJECT-TYPE
	SYNTAX  AxrOspfv3GeneralEntry
	ACCESS  not-accessible
	STATUS  mandatory
	DESCRIPTION
		"The list of the ospfv3 information."
	INDEX { axrOspfv3GeneralDomainNumber }
	::= { axrOspfv3GeneralTable 1 }

	AxrOspfv3GeneralEntry ::=
	SEQUENCE {
		axrOspfv3GeneralDomainNumber
			INTEGER,
		axrOspfv3RouterId
			RouterID,
		axrOspfv3AdminStat
			Status,
		axrOspfv3VersionNumber
			INTEGER,
		axrOspfv3AreaBdrRtrStatus
			TruthValue,
		axrOspfv3ASBdrRtrStatus
			TruthValue,
		axrOspfv3AsScopeLsaCount
			Gauge32,
		axrOspfv3AsScopeLsaCksumSum
			Integer32,
		axrOspfv3OriginateNewLsas
			Counter32,
		axrOspfv3RxNewLsas
			Counter32,
		axrOspfv3ExtAreaLsdbLimit
			Integer32,
		axrOspfv3MulticastExtensions
			Integer32,
		axrOspfv3DemandExtensions
			TruthValue,
		axrOspfv3TrafficEngineeringSupport
			TruthValue
		}

axrOspfv3GeneralDomainNumber OBJECT-TYPE
	SYNTAX  INTEGER
	ACCESS  read-only
	STATUS  mandatory
	DESCRIPTION
		"ospfv3 domain number."
	::= { axrOspfv3GeneralEntry 1 }

axrOspfv3RouterId OBJECT-TYPE
	SYNTAX  RouterID
	ACCESS  read-only
	STATUS  mandatory
	DESCRIPTION
		"A  32-bit  integer  uniquely  identifying  the
		router in the Autonomous System.
		By convention, to  ensure  uniqueness, this
		should  default  to  the  value  of  one of the
		router's IPv4 interface addresses if IPv4 is
		configured."
	::= { axrOspfv3GeneralEntry 2 }

axrOspfv3AdminStat OBJECT-TYPE
	SYNTAX  Status
	ACCESS  read-only
	STATUS  mandatory
	DESCRIPTION
		"The  administrative  status  of  axrOspfv3  in  the
		router.  The  value 'enabled' denotes that the
		axrOspfv3 Process is active on at least  one  inter-
		face;  'disabled'  disables  it  on  all inter-
		faces."
	::= { axrOspfv3GeneralEntry 3 }

axrOspfv3VersionNumber OBJECT-TYPE
	SYNTAX  INTEGER { version3 (3) }
	ACCESS  read-only
	STATUS  mandatory
	DESCRIPTION
		"The version number of OSPF for IPv6 is 3."
	::= { axrOspfv3GeneralEntry 4 }

axrOspfv3AreaBdrRtrStatus OBJECT-TYPE
	SYNTAX  TruthValue
	ACCESS  read-only
	STATUS  mandatory
	DESCRIPTION
		"A flag to note whether this router is an  area
		border router."
	REFERENCE
		"OSPF Version 2, Section 3 Splitting the AS into
		Areas"
	::= { axrOspfv3GeneralEntry 5 }

axrOspfv3ASBdrRtrStatus OBJECT-TYPE
	SYNTAX  TruthValue
	ACCESS  read-only
	STATUS  mandatory
	DESCRIPTION
		"A flag to note whether this router is  config-
		ured as an Autonomous System border router."
	REFERENCE
		"OSPF Version 2, Section 3.3  Classification  of
		routers"
	::= { axrOspfv3GeneralEntry 6 }

axrOspfv3AsScopeLsaCount OBJECT-TYPE
	SYNTAX  Gauge32
	ACCESS  read-only
	STATUS  mandatory
	DESCRIPTION
		"The number of AS-Scope (e.g. AS-External) link-state
		advertisements in the link-state database."
	::= { axrOspfv3GeneralEntry 7 }

axrOspfv3AsScopeLsaCksumSum OBJECT-TYPE
	SYNTAX  Integer32
	ACCESS  read-only
	STATUS  mandatory
	DESCRIPTION
		"The 32-bit unsigned sum of the LS checksums of
		the  AS-scoped link-state advertisements  con-
		tained in the link-state database. This sum
		can  be  used  to determine if there has been a
		change in a router's link state  database,  and
		to  compare  the  link-state  database  of  two
		routers."
	::= { axrOspfv3GeneralEntry 8 }

axrOspfv3OriginateNewLsas OBJECT-TYPE
	SYNTAX  Counter32
	ACCESS  read-only
	STATUS  mandatory
	DESCRIPTION
		"The number of  new  link-state  advertisements
		that  have been originated.  This number is in-
		cremented each time the router originates a new
		LSA."
	::= { axrOspfv3GeneralEntry 9 }

axrOspfv3RxNewLsas OBJECT-TYPE
	SYNTAX  Counter32
	ACCESS  read-only
	STATUS  mandatory
	DESCRIPTION
		"The number of  link-state  advertisements  re-
		ceived  determined  to  be  new instantiations.
		This number does not include  newer  instantia-
		tions  of self-originated link-state advertise-
		ments."
	::= { axrOspfv3GeneralEntry 10 }

axrOspfv3ExtAreaLsdbLimit OBJECT-TYPE
	SYNTAX  Integer32 (-1..'7FFFFFFF'h)
	ACCESS  read-only
	STATUS  mandatory
	DESCRIPTION
		"The  maximum   number   of   non-default   AS-
		external-LSAs entries that can be stored in the
		link-state database.  If the value is -1,  then
		there is no limit.
		When the number of non-default AS-external-LSAs
		in  a  router's  link-state  database  reaches
		axrOspfv3ExtAreaLsdbLimit, the router  enters  Overflow-
		State.  The   router  never  holds  more  than
		axrOspfv3ExtAreaLsdbLimit  non-default  AS-external-LSAs
		in  its  database. OspfExtAreaLsdbLimit MUST be set
		identically in all routers attached to the axrOspfv3
		backbone  and/or  any regular axrOspfv3 area. (i.e.,
		axrOspfv3 stub areas and NSSAs are excluded)."
	DEFVAL { -1 }
	::= { axrOspfv3GeneralEntry 11 }

axrOspfv3MulticastExtensions OBJECT-TYPE
	SYNTAX  Integer32
	ACCESS  read-only
	STATUS  mandatory
	DESCRIPTION
		"A Bit Mask indicating whether  the  router  is
		forwarding  IPv6  multicast datagrams
		based on the algorithms defined in  the  Multi-
		cast Extensions to OSPF.
		Bit 0, if set, indicates that  the  router  can
		forward  IPv6 multicast datagrams in the router's
		directly attached areas (called intra-area mul-
		ticast routing).
		Bit 1, if set, indicates that  the  router  can
		forward  IPv6  multicast  datagrams  between axrOspfv3
		areas (called inter-area multicast routing).
		Bit 2, if set, indicates that  the  router  can
		forward  IPv6  multicast  datagrams between Auto-
		nomous Systems (called inter-AS multicast rout-
		ing).
		Only certain combinations of bit  settings are
		allowed,  namely: 0 (no multicast forwarding is
		enabled), 1 (intra-area multicasting  only),  3
		(intra-area  and  inter-area  multicasting),  5
		(intra-area and inter-AS  multicasting)  and  7
		(multicasting  everywhere). By default, no mul-
		ticast forwarding is enabled."
	DEFVAL { 0 }
	::= { axrOspfv3GeneralEntry 12 }

axrOspfv3DemandExtensions OBJECT-TYPE
	SYNTAX  TruthValue
	ACCESS  read-only
	STATUS  mandatory
	DESCRIPTION
		"The router's support for demand routing."
	REFERENCE
		"OSPF Version 2, Appendix on Demand Routing"
	::= { axrOspfv3GeneralEntry 14 }

axrOspfv3TrafficEngineeringSupport OBJECT-TYPE
	SYNTAX  TruthValue
	ACCESS  read-only
	STATUS  mandatory
	DESCRIPTION
		"The router's support for traffic engineering
		extensions."
	::= { axrOspfv3GeneralEntry 15 }

--  The axrOspfv3 Area Data Structure contains information
--  regarding the various areas. The interfaces and
--  virtual links are configured as part of these areas.
--  Area 0.0.0.0, by definition, is the Backbone Area

axrOspfv3AreaTable OBJECT-TYPE
	SYNTAX  SEQUENCE OF AxrOspfv3AreaEntry
	ACCESS  not-accessible
	STATUS  mandatory
	DESCRIPTION
		"Information describing the configured  parame-
		ters  and cumulative statistics of the router's
		attached areas."
	REFERENCE
		"OSPF Version 2, Section 6  The Area Data Struc-
		ture"
	::= { axrOspfv3 2 }

axrOspfv3AreaEntry OBJECT-TYPE
	SYNTAX  AxrOspfv3AreaEntry
	ACCESS  not-accessible
	STATUS  mandatory
	DESCRIPTION
		"Information describing the configured  parame-
		ters  and  cumulative  statistics of one of the
		router's attached areas."
		INDEX { axrOspfv3AreaId }
	::= { axrOspfv3AreaTable 1 }

	AxrOspfv3AreaEntry ::=
		SEQUENCE {
			axrOspfv3AreaDomainNumber
				INTEGER,
			axrOspfv3AreaId
				AreaID,
			axrOspfv3ImportAsExtern
				INTEGER,
			axrOspfv3SpfRuns
				Counter32,
			axrOspfv3AreaBdrRtrCount
				Gauge32,
			axrOspfv3AsBdrRtrCount
				Gauge32,
			axrOspfv3AreaScopeLsaCount
				Gauge32,
			axrOspfv3AreaScopeLsaCksumSum
				Integer32,
			axrOspfv3AreaSummary
				INTEGER,
			axrOspfv3AreaStatus
				RowStatus,
			axrOspfv3StubMetric
				BigMetric
		}

axrOspfv3AreaDomainNumber OBJECT-TYPE
	SYNTAX  INTEGER
	ACCESS  read-only
	STATUS  mandatory
	DESCRIPTION
		"ospfv3 domain number."
	::= { axrOspfv3AreaEntry 1 }

axrOspfv3AreaId OBJECT-TYPE
	SYNTAX  AreaID
	ACCESS  read-only
	STATUS  mandatory
	DESCRIPTION
		"A 32-bit integer uniquely identifying an area.
		Area ID 0.0.0.0 is used for the axrOspfv3 backbone."
	REFERENCE
		"OSPF Version 2, Appendix C.2 Area parameters"
	::= { axrOspfv3AreaEntry 2 }

axrOspfv3ImportAsExtern OBJECT-TYPE
	SYNTAX  INTEGER {
	importExternal (1),  -- normal area
	importNoExternal (2), -- stub area
	importNssa (3)        -- not-so-stubby-area
	}
	ACCESS  read-only
	STATUS  mandatory
	DESCRIPTION
		"Indicates whether an area is a Stub area, NSSA, or
		standard area. AS-scope LSAs are not imported into Stub
		Areas or NSSAs. NSSAs import AS-External data as Type-7
		LSAs which have Area-scope"
	REFERENCE
		"OSPF Version 2, Appendix C.2 Area parameters"
		DEFVAL { importExternal }
	::= { axrOspfv3AreaEntry 3 }

axrOspfv3SpfRuns OBJECT-TYPE
	SYNTAX  Counter32
	ACCESS  read-only
	STATUS  mandatory
	DESCRIPTION
		"The number of times that the intra-area  route
		table  has  been  calculated  using this area's
		link-state database.  This  is  typically  done
		using Dijkstra's algorithm."
	::= { axrOspfv3AreaEntry 4 }

axrOspfv3AreaBdrRtrCount OBJECT-TYPE
	SYNTAX  Gauge32
	ACCESS  read-only
	STATUS  mandatory
	DESCRIPTION
		"The total number of area border routers reach-
		able within this area. This is initially zero,
		and is calculated in each SPF Pass."
	::= { axrOspfv3AreaEntry 5 }

axrOspfv3AsBdrRtrCount OBJECT-TYPE
	SYNTAX  Gauge32
	ACCESS  read-only
	STATUS  mandatory
	DESCRIPTION
		"The total number of Autonomous  System  border
		routers  reachable  within  this area.  This is
		initially zero, and is calculated in  each  SPF
		Pass."
	::= { axrOspfv3AreaEntry 6 }

axrOspfv3AreaScopeLsaCount OBJECT-TYPE
	SYNTAX  Gauge32
	ACCESS  read-only
	STATUS  mandatory
	DESCRIPTION
	"The total number of Area-Scope link-state
	advertisements in  this  area's link-state
	database."
	::= { axrOspfv3AreaEntry 7 }

axrOspfv3AreaScopeLsaCksumSum OBJECT-TYPE
	SYNTAX  Integer32
	ACCESS  read-only
	STATUS  mandatory
	DESCRIPTION
		"The 32-bit unsigned sum of the Area-Scope link-state
		advertisements'  LS  checksums  contained in this
		area's link-state database.  The sum can be used
		to determine if  there  has been  a  change  in a
		router's link state database, and to compare the
		link-state database of two routers."
		DEFVAL  { 0 }
	::= { axrOspfv3AreaEntry 8 }

axrOspfv3AreaSummary OBJECT-TYPE
	SYNTAX  INTEGER {
		noAreaSummary (1),
		sendAreaSummary (2)
	}
	ACCESS  read-only
	STATUS  mandatory
	DESCRIPTION
		"The variable axrOspfv3AreaSummary controls the  im-
		port  of  summary LSAs into stub areas.  It has
		no effect on other areas.
		If it is noAreaSummary, the router will neither
		originate  nor  propagate summary LSAs into the
		stub area.  It will rely entirely  on  its  de-
		fault route.
		If it is sendAreaSummary, the router will  both
		summarize and propagate summary LSAs."
		DEFVAL  { noAreaSummary }
	::= { axrOspfv3AreaEntry 9 }

axrOspfv3AreaStatus OBJECT-TYPE
	SYNTAX  RowStatus
	ACCESS  read-only
	STATUS  mandatory
	DESCRIPTION
		"This variable displays the status of  the  en-
		try.  Setting it to 'invalid' has the effect of
		rendering it inoperative.  The internal  effect
		(row removal) is implementation dependent."
	::= { axrOspfv3AreaEntry 10 }

axrOspfv3StubMetric OBJECT-TYPE
	SYNTAX  BigMetric
--	ACCESS  read-create
	ACCESS  read-only
	STATUS  mandatory
	DESCRIPTION
		"The metric value advertised for the default route
		into Stub and NSSA areas."
	::= { axrOspfv3AreaEntry 11 }

--	axrOspfv3 AS-Scope Link State Database
--		The Link State Database contains the AS-Scope Link State
--		Advertisements from throughout the areas that the
--		device is attached to.

axrOspfv3AsLsdbTable OBJECT-TYPE
	SYNTAX  SEQUENCE OF AxrOspfv3AsLsdbEntry
	ACCESS  not-accessible
	STATUS  mandatory
	DESCRIPTION
		"The axrOspfv3 Process's AS-Scope Link State Database."
	::= { axrOspfv3 3 }

axrOspfv3AsLsdbEntry OBJECT-TYPE
	SYNTAX  AxrOspfv3AsLsdbEntry
	ACCESS  not-accessible
	STATUS  mandatory
	DESCRIPTION
	"A single AS-Scope Link State Advertisement."
	INDEX { axrOspfv3AsLsdbType,
			axrOspfv3AsLsdbRouterId,
			axrOspfv3AsLsdbLsid }
	::= { axrOspfv3AsLsdbTable 1 }

	AxrOspfv3AsLsdbEntry ::=
		SEQUENCE {
			axrOspfv3AsLsdbDomainNumber
				INTEGER,
			axrOspfv3AsLsdbType
				INTEGER,
			axrOspfv3AsLsdbRouterId
				RouterID,
			axrOspfv3AsLsdbLsid
				IpAddress,
			axrOspfv3AsLsdbSequence
				Integer32,
			axrOspfv3AsLsdbAge
				Integer32,
			axrOspfv3AsLsdbChecksum
				Integer32,
			axrOspfv3AsLsdbAdvertisement
				OCTET STRING
			}

axrOspfv3AsLsdbDomainNumber OBJECT-TYPE
	SYNTAX  INTEGER
	ACCESS  read-only
	STATUS  mandatory
	DESCRIPTION
		"ospfv3 domain number."
	::= { axrOspfv3AsLsdbEntry 1 }

axrOspfv3AsLsdbType OBJECT-TYPE
	SYNTAX  INTEGER {
		asExternalLink (16389)  -- 0x4005
	}
	ACCESS  read-only
	STATUS  mandatory
	DESCRIPTION
		"The type  of  the  link  state  advertisement.
		Each  link state type has a separate advertise-
		ment format. Unrecognized AS-Scope LSAs with the
		U-bit set are also store in this database."
	::= { axrOspfv3AsLsdbEntry 2 }

axrOspfv3AsLsdbRouterId OBJECT-TYPE
	SYNTAX  RouterID
	ACCESS  read-only
	STATUS  mandatory
	DESCRIPTION
		"The 32 bit number that uniquely identifies the
		originating router in the Autonomous System."
	REFERENCE
		"OSPF Version 2, Appendix C.1 Global parameters"
	::= { axrOspfv3AsLsdbEntry 3 }

axrOspfv3AsLsdbLsid OBJECT-TYPE
	SYNTAX  IpAddress
	ACCESS  read-only
	STATUS  mandatory
	DESCRIPTION
	"The Link State ID is an LS Type Specific field
	containing either a Router ID or a unique identifier;
	it identifies the piece of the  routing  domain
	that is being described by the advertisement.
	In contrast to OSPF for IPv4, the LSID has no
	addressing semantics."
	::= { axrOspfv3AsLsdbEntry 4 }

--  Note that the OSPF Sequence Number is a 32 bit signed
--  integer.  It starts with the value '80000001'h,
--  or -'7FFFFFFF'h, and increments until '7FFFFFFF'h
--  Thus, a typical sequence number will be very negative.

axrOspfv3AsLsdbSequence OBJECT-TYPE
	SYNTAX  Integer32
	ACCESS  read-only
	STATUS  mandatory
	DESCRIPTION
		"The sequence number field is a  signed  32-bit
		integer.   It  is used to detect old and dupli-
		cate link state advertisements.  The  space  of
		sequence  numbers  is  linearly  ordered.  The
		larger the sequence number the more recent  the
		advertisement."
	REFERENCE
		"OSPF Version  2,  Section  12.1.6  LS  sequence
		number"
	::= { axrOspfv3AsLsdbEntry 5 }

axrOspfv3AsLsdbAge OBJECT-TYPE
	SYNTAX  Integer32  -- Should be 0..MaxAge
	ACCESS  read-only
	STATUS  mandatory
	DESCRIPTION
		"This field is the age of the link state adver-
		tisement in seconds."
	REFERENCE
		"OSPF Version 2, Section 12.1.1 LS age"
	::= { axrOspfv3AsLsdbEntry 6 }

axrOspfv3AsLsdbChecksum OBJECT-TYPE
	SYNTAX  Integer32
	ACCESS  read-only
	STATUS  mandatory
	DESCRIPTION
		"This field is the  checksum  of  the  complete
		contents  of  the  advertisement, excepting the
		age field.  The age field is excepted  so  that
		an  advertisement's  age  can  be  incremented
		without updating the  checksum.  The  checksum
		used  is  the same that is used for ISO connec-
		tionless datagrams; it is commonly referred  to
		as the Fletcher checksum."
	REFERENCE
		"OSPF Version 2, Section 12.1.7 LS checksum"
	::= { axrOspfv3AsLsdbEntry 7 }

axrOspfv3AsLsdbAdvertisement OBJECT-TYPE
	SYNTAX  OCTET STRING (SIZE (1..65535))
	ACCESS  read-only
	STATUS  mandatory
	DESCRIPTION
	"The entire Link State Advertisement, including
	its header."
	::= { axrOspfv3AsLsdbEntry 8 }

--  axrOspfv3 Area-Scope Link State Database
--  The Link State Database contains the Area-Scope Link State
--  Advertisements from throughout the area that the
--  device is attached to.

axrOspfv3AreaLsdbTable OBJECT-TYPE
	SYNTAX  SEQUENCE OF AxrOspfv3AreaLsdbEntry
	ACCESS  not-accessible
	STATUS  mandatory
	DESCRIPTION
		"The axrOspfv3 Process's Area-Scope Link State Database."
	::= { axrOspfv3 4 }

axrOspfv3AreaLsdbEntry OBJECT-TYPE
	SYNTAX  AxrOspfv3AreaLsdbEntry
	ACCESS  not-accessible
	STATUS  mandatory
	DESCRIPTION
		"A single Area-Scope Link State Advertisement."
	INDEX { axrOspfv3AreaLsdbDomainNumber,
		axrOspfv3AreaLsdbAreaId,
		axrOspfv3AreaLsdbType,
		axrOspfv3AreaLsdbRouterId,
		axrOspfv3AreaLsdbLsid }
	::= { axrOspfv3AreaLsdbTable 1 }

	AxrOspfv3AreaLsdbEntry ::=
		SEQUENCE {
		axrOspfv3AreaLsdbDomainNumber
			INTEGER,
		axrOspfv3AreaLsdbAreaId
			AreaID,
		axrOspfv3AreaLsdbType
			INTEGER,
		axrOspfv3AreaLsdbRouterId
			RouterID,
		axrOspfv3AreaLsdbLsid
			IpAddress,
		axrOspfv3AreaLsdbSequence
			Integer32,
		axrOspfv3AreaLsdbAge
			Integer32,
		axrOspfv3AreaLsdbChecksum
			Integer32,
		axrOspfv3AreaLsdbAdvertisement
			OCTET STRING
	}

axrOspfv3AreaLsdbDomainNumber OBJECT-TYPE
	SYNTAX  INTEGER
	ACCESS  read-only
	STATUS  mandatory
	DESCRIPTION
		"ospfv3 domain number."
	::= { axrOspfv3AreaLsdbEntry 1 }

axrOspfv3AreaLsdbAreaId OBJECT-TYPE
	SYNTAX  AreaID
	ACCESS  read-only
	STATUS  mandatory
	DESCRIPTION
		"The 32 bit identifier of the Area from which the
		LSA was received."
	REFERENCE
		"OSPF Version 2, Appendix C.2 Area parameters."
	::= { axrOspfv3AreaLsdbEntry 2 }

axrOspfv3AreaLsdbType OBJECT-TYPE
	SYNTAX  INTEGER {
		routerLsa          (8193),  -- 0x2001
		networkLsa         (8194),  -- 0x2002
		interAreaPrefixLsa (8195),  -- 0x2003
		interAreaRouterLsa (8196),  -- 0x2004
		groupMembershipLsa (8198),  -- 0x2006
		nssaExternalLsa    (8199),  -- 0x2007
		intraAreaPrefixLsa (8201)   -- 0x2009
	}
	ACCESS  read-only
	STATUS  mandatory
	DESCRIPTION
		"The type  of  the  link  state  advertisement.
		Each  link state type has a separate advertise-
		ment format. Unrecognized Area-Scope LSAs with
		the U-bit set are also stored in this database."
	::= { axrOspfv3AreaLsdbEntry 3 }

axrOspfv3AreaLsdbRouterId OBJECT-TYPE
	SYNTAX  RouterID
	ACCESS  read-only
	STATUS  mandatory
	DESCRIPTION
		"The 32 bit number that uniquely identifies the
		originating router in the Autonomous System."
	REFERENCE
		"OSPF Version 2, Appendix C.1 Global parameters"
	::= { axrOspfv3AreaLsdbEntry 4 }

axrOspfv3AreaLsdbLsid OBJECT-TYPE
	SYNTAX  IpAddress
	ACCESS  read-only
	STATUS  mandatory
	DESCRIPTION
		"The Link State ID is an LS Type Specific field
		containing either a Router ID or a unique identifier;
		it identifies the piece of the  routing  domain
		that is being described by the advertisement.
		In contrast to OSPF for IPv4, the LSID has no
		addressing semantics."
	::= { axrOspfv3AreaLsdbEntry 5 }

--  Note that the OSPF Sequence Number is a 32 bit signed
--  integer.  It starts with the value '80000001'h,
--  or -'7FFFFFFF'h, and increments until '7FFFFFFF'h
--  Thus, a typical sequence number will be very negative.

axrOspfv3AreaLsdbSequence OBJECT-TYPE
	SYNTAX  Integer32
	ACCESS  read-only
	STATUS  mandatory
	DESCRIPTION
		"The sequence number field is a  signed  32-bit
		integer.   It  is used to detect old and dupli-
		cate link state advertisements.  The  space  of
		sequence  numbers  is  linearly  ordered.   The
		larger the sequence number the more recent  the
		advertisement."
	REFERENCE
		"OSPF Version  2,  Section  12.1.6  LS  sequence
		number"
	::= { axrOspfv3AreaLsdbEntry 6 }

axrOspfv3AreaLsdbAge OBJECT-TYPE
	SYNTAX  Integer32  -- Should be 0..MaxAge
	ACCESS  read-only
	STATUS  mandatory
	DESCRIPTION
		"This field is the age of the link state adver-
		tisement in seconds."
	REFERENCE
		"OSPF Version 2, Section 12.1.1 LS age"
	::= { axrOspfv3AreaLsdbEntry 7 }

axrOspfv3AreaLsdbChecksum OBJECT-TYPE
	SYNTAX  Integer32
	ACCESS  read-only
	STATUS  mandatory
	DESCRIPTION
		"This field is the  checksum  of  the  complete
		contents  of  the  advertisement, excepting the
		age field.  The age field is excepted  so  that
		an  advertisement's  age  can  be  incremented
		without updating the  checksum.  The  checksum
		used  is  the same that is used for ISO connec-
		tionless datagrams; it is commonly referred  to
		as the Fletcher checksum."
	REFERENCE
		"OSPF Version 2, Section 12.1.7 LS checksum"
	::= { axrOspfv3AreaLsdbEntry 8 }

axrOspfv3AreaLsdbAdvertisement OBJECT-TYPE
	SYNTAX  OCTET STRING (SIZE (1..65535))
	ACCESS  read-only
	STATUS  mandatory
	DESCRIPTION
		"The entire Link State Advertisement, including
		its header."
	::= { axrOspfv3AreaLsdbEntry 9 }

--  axrOspfv3 Link-Scope Link State Database
--    The Link State Database contains the Link-Scope Link State
--    Advertisements from the links that the
--    device is attached to.

axrOspfv3LinkLsdbTable OBJECT-TYPE
	SYNTAX  SEQUENCE OF AxrOspfv3LinkLsdbEntry
	ACCESS  not-accessible
	STATUS  mandatory
	DESCRIPTION
		"The axrOspfv3 Process's Link-Scope Link State Database."
	::= { axrOspfv3 5 }

axrOspfv3LinkLsdbEntry OBJECT-TYPE
	SYNTAX  AxrOspfv3LinkLsdbEntry
	ACCESS  not-accessible
	STATUS  mandatory
	DESCRIPTION
		"A single Link-Scope Link State Advertisement."
	INDEX { axrOspfv3LinkLsdbIfIndex,
		axrOspfv3LinkLsdbType,
		axrOspfv3LinkLsdbRouterId,
		axrOspfv3LinkLsdbLsid }
	::= { axrOspfv3LinkLsdbTable 1 }

	AxrOspfv3LinkLsdbEntry ::=
		SEQUENCE {
			axrOspfv3LinkLsdbDomainNumber
				INTEGER,
			axrOspfv3LinkLsdbIfIndex
				Ipv6IfIndex,
			axrOspfv3LinkLsdbType
				INTEGER,
			axrOspfv3LinkLsdbRouterId
				RouterID,
			axrOspfv3LinkLsdbLsid
				IpAddress,
			axrOspfv3LinkLsdbSequence
				Integer32,
			axrOspfv3LinkLsdbAge
				Integer32,
			axrOspfv3LinkLsdbChecksum
				Integer32,
			axrOspfv3LinkLsdbAdvertisement
				OCTET STRING
		}

axrOspfv3LinkLsdbDomainNumber OBJECT-TYPE
	SYNTAX  INTEGER
	ACCESS  read-only
	STATUS  mandatory
	DESCRIPTION
		"ospfv3 domain number."
	::= { axrOspfv3LinkLsdbEntry 1 }

axrOspfv3LinkLsdbIfIndex OBJECT-TYPE
	SYNTAX  Ipv6IfIndex
	ACCESS  read-only
	STATUS  mandatory
	DESCRIPTION
		"The identifier of the link from which the LSA
		was received."
	REFERENCE
		"OSPF Version 2, Appendix C.2 Area parameters"
	::= { axrOspfv3LinkLsdbEntry 2 }

axrOspfv3LinkLsdbType OBJECT-TYPE
	SYNTAX  INTEGER  {
		linkLsa (8)  -- 0x0008
	}
	ACCESS  read-only
	STATUS  mandatory
	DESCRIPTION
		"The type  of  the  link  state  advertisement.
		Each  link state type has a separate advertise-
		ment format. Unrecognized Link-Scope LSAs with
		the U-bit set are also stored in this database."
	::= { axrOspfv3LinkLsdbEntry 3 }

axrOspfv3LinkLsdbRouterId OBJECT-TYPE
	SYNTAX  RouterID
	ACCESS  read-only
	STATUS  mandatory
	DESCRIPTION
		"The 32 bit number that uniquely identifies the
		originating router in the Autonomous System."
	REFERENCE
		"OSPF Version 2, Appendix C.1 Global parameters"
	::= { axrOspfv3LinkLsdbEntry 4 }

axrOspfv3LinkLsdbLsid OBJECT-TYPE
	SYNTAX  IpAddress
	ACCESS  read-only
	STATUS  mandatory
	DESCRIPTION
		"The Link State ID is an LS Type Specific field
		containing either a Router ID or a unique identifier;
		it identifies the piece of the  routing  domain
		that is being described by the advertisement.
		In contrast to OSPF for IPv4, the LSID has no
		addressing semantics."
	::= { axrOspfv3LinkLsdbEntry 5 }

--  Note that the OSPF Sequence Number is a 32 bit signed
--  integer.  It starts with the value '80000001'h,
--  or -'7FFFFFFF'h, and increments until '7FFFFFFF'h
--  Thus, a typical sequence number will be very negative.

axrOspfv3LinkLsdbSequence OBJECT-TYPE
	SYNTAX  Integer32
	ACCESS  read-only
	STATUS  mandatory
	DESCRIPTION
		"The sequence number field is a  signed  32-bit
		integer.   It  is used to detect old and dupli-
		cate link state advertisements.  The  space  of
		sequence  numbers  is  linearly  ordered.  The
		larger the sequence number the more recent  the
		advertisement."
	REFERENCE
		"OSPF Version  2,  Section  12.1.6  LS  sequence
		number"
	::= { axrOspfv3LinkLsdbEntry 6 }

axrOspfv3LinkLsdbAge OBJECT-TYPE
	SYNTAX  Integer32  -- Should be 0..MaxAge
	ACCESS  read-only
	STATUS   mandatory
	DESCRIPTION
		"This field is the age of the link state adver-
		tisement in seconds."
	REFERENCE
		"OSPF Version 2, Section 12.1.1 LS age"
	::= { axrOspfv3LinkLsdbEntry 7 }

axrOspfv3LinkLsdbChecksum OBJECT-TYPE
	SYNTAX  Integer32
	ACCESS  read-only
	STATUS  mandatory
	DESCRIPTION
		"This field is the  checksum  of  the  complete
		contents  of  the  advertisement, excepting the
		age field.  The age field is excepted  so  that
		an  advertisement's  age  can  be  incremented
		without updating the  checksum.  The  checksum
		used  is  the same that is used for ISO connec-
		tionless datagrams; it is commonly referred  to
		as the Fletcher checksum."
	REFERENCE
		"OSPF Version 2, Section 12.1.7 LS checksum"
	::= { axrOspfv3LinkLsdbEntry 8 }

axrOspfv3LinkLsdbAdvertisement OBJECT-TYPE
	SYNTAX  OCTET STRING (SIZE (1..65535))
	ACCESS  read-only
	STATUS  mandatory
	DESCRIPTION
		"The entire Link State Advertisement, including
		its header."
	::= { axrOspfv3LinkLsdbEntry 9 }

--  OSPF Host Table
--    The Host/Metric Table indicates what hosts are directly
--    attached to the Router, and what metrics and types of
--    service should be advertised for them.
--  axrOspfv3 Interface Table

axrOspfv3IfTable OBJECT-TYPE
	SYNTAX  SEQUENCE OF AxrOspfv3IfEntry
	ACCESS  not-accessible
	STATUS  mandatory
	DESCRIPTION
		"The axrOspfv3 Interface Table describes the  inter-
		faces from the viewpoint of axrOspfv3."
	REFERENCE
		"OSPF Version 2, Appendix C.3  Router  interface
		parameters"
	::= { axrOspfv3 7 }

axrOspfv3IfEntry OBJECT-TYPE
	SYNTAX  AxrOspfv3IfEntry
	ACCESS  not-accessible
	STATUS  mandatory
	DESCRIPTION
		"The axrOspfv3 Interface Entry describes one  inter-
		face from the viewpoint of axrOspfv3."
	INDEX { axrOspfv3IfIndex }
	::= { axrOspfv3IfTable 1 }

	AxrOspfv3IfEntry ::=
		SEQUENCE {
			axrOspfv3IfDomainNumber
				INTEGER,
			axrOspfv3IfIndex
				Ipv6IfIndex,
			axrOspfv3IfAreaId
				AreaID,
			axrOspfv3IfType
				INTEGER,
			axrOspfv3IfAdminStat
				Status,
			axrOspfv3IfRtrPriority
				DesignatedRouterPriority,
			axrOspfv3IfTransitDelay
				UpToMaxAge,
			axrOspfv3IfRetransInterval
				UpToMaxAge,
			axrOspfv3IfHelloInterval
				HelloRange,
			axrOspfv3IfRtrDeadInterval
				PositiveInteger,
			axrOspfv3IfPollInterval
				PositiveInteger,
			axrOspfv3IfState
				INTEGER,
			axrOspfv3IfDesignatedRouter
				RouterID,
			axrOspfv3IfBackupDesignatedRouter
				RouterID,
			axrOspfv3IfEvents
				Counter32,
			axrOspfv3IfStatus
				RowStatus,
			axrOspfv3IfMulticastForwarding
				INTEGER,
			axrOspfv3IfDemand
				TruthValue,
			axrOspfv3IfMetricValue
				Metric,
			axrOspfv3IfLinkScopeLsaCount
				Gauge32,
			axrOspfv3IfLinkLsaCksumSum
				Integer32,
			axrOspfv3IfInstId
				Integer32
			}

axrOspfv3IfDomainNumber OBJECT-TYPE
	SYNTAX  INTEGER
	ACCESS  read-only
	STATUS  mandatory
	DESCRIPTION
		"ospfv3 domain number."
	::= { axrOspfv3IfEntry 1 }

axrOspfv3IfIndex OBJECT-TYPE
	SYNTAX  Ipv6IfIndex
	ACCESS  read-only
	STATUS  mandatory
	DESCRIPTION
		"The interface index of this axrOspfv3 interface.
		It corresponds to the interface index of the
		Ipv6 interface on which axrOspfv3 is configured."
	::= { axrOspfv3IfEntry 2 }

axrOspfv3IfAreaId OBJECT-TYPE
	SYNTAX  AreaID
	ACCESS  read-only
	STATUS  mandatory
	DESCRIPTION
		"A 32-bit integer uniquely identifying the area
		to  which  the  interface  connects.   Area  ID
		0.0.0.0 is used for the axrOspfv3 backbone."
	DEFVAL   { '00000000'H }  -- 0.0.0.0
	::= { axrOspfv3IfEntry 3 }

axrOspfv3IfType OBJECT-TYPE
	SYNTAX  INTEGER {
		broadcast (1),
		nbma (2),
		pointToPoint (3),
		pointToMultipoint (5)
	}
	ACCESS  read-only
	STATUS  mandatory
	DESCRIPTION
		"The axrOspfv3 interface type."
	::= { axrOspfv3IfEntry 4 }

axrOspfv3IfAdminStat OBJECT-TYPE
	SYNTAX  Status
	ACCESS  read-only
	STATUS  mandatory
	DESCRIPTION
		"The axrOspfv3 interface's  administrative  status.
		The  value formed on the interface, and the in-
		terface will be advertised as an internal route
		to  some  area.  The  value 'disabled' denotes
		that the interface is external to axrOspfv3."
	DEFVAL { enabled }
	::= { axrOspfv3IfEntry 5 }

axrOspfv3IfRtrPriority OBJECT-TYPE
	SYNTAX  DesignatedRouterPriority
	ACCESS  read-only
	STATUS  mandatory
	DESCRIPTION
		"The  priority  of  this  interface.   Used  in
		multi-access  networks,  this  field is used in
		the designated router election algorithm.  The
		value 0 signifies that the router is not eligi-
		ble to become the  designated  router  on  this
		particular  network.   In the event of a tie in
		this value, routers will use their Router ID as
		a tie breaker."
	DEFVAL { 1 }
	::= { axrOspfv3IfEntry 6 }

axrOspfv3IfTransitDelay OBJECT-TYPE
	SYNTAX  UpToMaxAge
	ACCESS  read-only
	STATUS  mandatory
	DESCRIPTION
		"The estimated number of seconds  it  takes  to
		transmit  a  link state update packet over this
		interface."
	DEFVAL { 1 }
	::= { axrOspfv3IfEntry 7 }

axrOspfv3IfRetransInterval OBJECT-TYPE
	SYNTAX  UpToMaxAge
	ACCESS  read-only
	STATUS  mandatory
	DESCRIPTION
		"The number of seconds between  link-state  ad-
		vertisement  retransmissions,  for  adjacencies
		belonging to this  interface.  This  value  is
		also used when retransmitting database descrip-
		tion and link-state request packets."
	DEFVAL { 5 }
	::= { axrOspfv3IfEntry 8 }

axrOspfv3IfHelloInterval OBJECT-TYPE
	SYNTAX  HelloRange
	ACCESS  read-only
	STATUS  mandatory
	DESCRIPTION
		"The length of time, in  seconds,  between  the
		Hello  packets that the router sends on the in-
		terface.  This value must be the same  for  all
		routers attached to a common network."
	DEFVAL { 10 }
	::= { axrOspfv3IfEntry 9 }

axrOspfv3IfRtrDeadInterval OBJECT-TYPE
	SYNTAX  PositiveInteger
	ACCESS  read-only
	STATUS  mandatory
	DESCRIPTION
		"The number of seconds that  a  router's  Hello
		packets  have  not been seen before it's neigh-
		bors declare the router down.  This  should  be
		some  multiple  of  the  Hello  interval.  This
		value must be the same for all routers attached
		to a common network."
	DEFVAL { 40 }
	::= { axrOspfv3IfEntry 10 }

axrOspfv3IfPollInterval OBJECT-TYPE
	SYNTAX  PositiveInteger
	ACCESS  read-only
	STATUS  mandatory
	DESCRIPTION
		"The larger time interval, in seconds,  between
		the  Hello  packets  sent  to  an inactive non-
		broadcast multi- access neighbor."
	DEFVAL { 120 }
	::= { axrOspfv3IfEntry 11 }

axrOspfv3IfState OBJECT-TYPE
	SYNTAX  INTEGER {
		down (1),
		loopback (2),
		waiting (3),
		pointToPoint (4),
		designatedRouter (5),
		backupDesignatedRouter (6),
		otherDesignatedRouter (7)
	}
	ACCESS  read-only
	STATUS  mandatory
	DESCRIPTION
		"The axrOspfv3 Interface State."
	DEFVAL { down }
	::= { axrOspfv3IfEntry 12 }

axrOspfv3IfDesignatedRouter OBJECT-TYPE
	SYNTAX  RouterID
	ACCESS  read-only
	STATUS  mandatory
	DESCRIPTION
		"The Router ID of the Designated Router."
	DEFVAL  { '00000000'H }  -- 0.0.0.0
	::= { axrOspfv3IfEntry 13 }

axrOspfv3IfBackupDesignatedRouter OBJECT-TYPE
	SYNTAX  RouterID
	ACCESS  read-only
	STATUS  mandatory
	DESCRIPTION
		"The  Router ID of  the  Backup   Designated
		Router."
	DEFVAL  { '00000000'H }  -- 0.0.0.0
	::= { axrOspfv3IfEntry 15 }

axrOspfv3IfEvents OBJECT-TYPE
	SYNTAX  Counter32
	ACCESS  read-only
	STATUS  mandatory
	DESCRIPTION
		"The number of times this  OSPF  interface  has
		changed its state, or an error has occurred."
	::= { axrOspfv3IfEntry 16 }

axrOspfv3IfStatus OBJECT-TYPE
	SYNTAX  RowStatus
	ACCESS  read-only
	STATUS  mandatory
	DESCRIPTION
		"This variable displays the status of  the  en-
		try.  Setting it to 'invalid' has the effect of
		rendering it inoperative.  The internal  effect
		(row removal) is implementation dependent."
	::= { axrOspfv3IfEntry 18 }

axrOspfv3IfMulticastForwarding OBJECT-TYPE
	SYNTAX  INTEGER {
		blocked (1),   -- no multicast forwarding
		multicast (2), -- using multicast address
		unicast (3)    -- to each axrOspfv3 neighbor
		}
	ACCESS  read-only
	STATUS  mandatory
	DESCRIPTION
		"The way multicasts should  forwarded  on  this
		interface;  not  forwarded,  forwarded  as data
		link multicasts, or forwarded as data link uni-
		casts.  Data link multicasting is not meaning-
		ful on point to point and NBMA interfaces, and
		setting axrOspfv3MulticastForwarding to 0 effective-
		ly disables all multicast forwarding."
	DEFVAL { blocked }
	::= { axrOspfv3IfEntry 19 }

axrOspfv3IfDemand OBJECT-TYPE
	SYNTAX  TruthValue
	ACCESS  read-only
	STATUS  mandatory
	DESCRIPTION
		"Indicates whether Demand axrOspfv3 procedures (hel-
		lo supression to FULL neighbors and setting the
		DoNotAge flag on proogated LSAs) should be per-
		formed on this interface."
	DEFVAL { false }
	::= { axrOspfv3IfEntry 20 }

axrOspfv3IfMetricValue OBJECT-TYPE
	SYNTAX  Metric
	ACCESS  read-only
	STATUS  mandatory
	DESCRIPTION
		"The metric assigned to this interface.
		The default value of the Metric is
		10^8 / ifSpeed."
	::= { axrOspfv3IfEntry 21 }

axrOspfv3IfLinkScopeLsaCount OBJECT-TYPE
	SYNTAX  Gauge32
	ACCESS  read-only
	STATUS  mandatory
	DESCRIPTION
		"The total number of Link-Scope link-state
		advertisements in  this  link's link-state database."
	::= { axrOspfv3IfEntry 22 }

axrOspfv3IfLinkLsaCksumSum OBJECT-TYPE
	SYNTAX  Integer32
	ACCESS  read-only
	STATUS  mandatory
	DESCRIPTION
		"The 32-bit unsigned sum of the Link-Scope link-state
		advertisements'  LS  checksums  contained in this
		link's link-state database.  The sum can be used
		to determine if  there  has been  a  change  in a
		router's link state database, and to compare the
		link-state database of two routers."
	DEFVAL  { 0 }
	::= { axrOspfv3IfEntry 23 }

axrOspfv3IfInstId OBJECT-TYPE
	SYNTAX  Integer32
	ACCESS  read-only
	STATUS  mandatory
	DESCRIPTION
		"Enables multiple instances of axrOspfv3 to be run over
		a single link. Each protocol instance would be assigned
		a separate ID. This ID has local link significance
		only."
	DEFVAL  { 0 }
	::= { axrOspfv3IfEntry 24 }

--  axrOspfv3 Virtual Interface Table
--    The Virtual Interface Table describes the virtual
--    links that the axrOspfv3 Process is configured to
--    carry on.

axrOspfv3VirtIfTable OBJECT-TYPE
	SYNTAX  SEQUENCE OF AxrOspfv3VirtIfEntry
	ACCESS  not-accessible
	STATUS  mandatory
	DESCRIPTION
		"Information about this router's virtual inter-
		faces."
	REFERENCE
		"OSPF Version  2,  Appendix  C.4   Virtual  link
		parameters"
	::= { axrOspfv3 8 }

axrOspfv3VirtIfEntry OBJECT-TYPE
	SYNTAX  AxrOspfv3VirtIfEntry
	ACCESS  not-accessible
	STATUS  mandatory
	DESCRIPTION
		"Information about a single Virtual Interface."
		INDEX { axrOspfv3VirtIfAreaId, axrOspfv3VirtIfNeighbor }
	::= { axrOspfv3VirtIfTable 1 }

	AxrOspfv3VirtIfEntry ::=
		SEQUENCE {
			axrOspfv3VirtIfDomainNumber
				INTEGER,
			axrOspfv3VirtIfAreaId
				AreaID,
			axrOspfv3VirtIfNeighbor
				RouterID,
			axrOspfv3VirtIfIndex
				Ipv6IfIndex,
			axrOspfv3VirtIfTransitDelay
				UpToMaxAge,
			axrOspfv3VirtIfRetransInterval
				UpToMaxAge,
			axrOspfv3VirtIfHelloInterval
				HelloRange,
			axrOspfv3VirtIfRtrDeadInterval
				PositiveInteger,
			axrOspfv3VirtIfState
				INTEGER,
			axrOspfv3VirtIfEvents
				Counter32,
			axrOspfv3VirtIfStatus
				RowStatus,
			axrOspfv3VirtIfLinkScopeLsaCount
				Gauge32,
			axrOspfv3VirtIfLinkLsaCksumSum
				Integer32
			}

axrOspfv3VirtIfDomainNumber OBJECT-TYPE
	SYNTAX  INTEGER
	ACCESS  read-only
	STATUS  mandatory
	DESCRIPTION
		"ospfv3 domain number."
	::= { axrOspfv3VirtIfEntry 1 }

axrOspfv3VirtIfAreaId OBJECT-TYPE
	SYNTAX  AreaID
	ACCESS  read-only
	STATUS  mandatory
	DESCRIPTION
		"The  Transit  Area  that  the   Virtual   Link
		traverses.  By definition, this is not 0.0.0.0"
	::= { axrOspfv3VirtIfEntry 2 }

axrOspfv3VirtIfNeighbor OBJECT-TYPE
	SYNTAX  RouterID
	ACCESS  read-only
	STATUS mandatory
	DESCRIPTION
		"The Router ID of the Virtual Neighbor."
	::= { axrOspfv3VirtIfEntry 3 }

axrOspfv3VirtIfIndex OBJECT-TYPE
	SYNTAX  Ipv6IfIndex
	ACCESS  read-only
	STATUS  mandatory
	DESCRIPTION
		"The interface index of this axrOspfv3 virtual interface.
		It must be unique among all the interface indices
		on the router."
		::= { axrOspfv3VirtIfEntry 4 }

axrOspfv3VirtIfTransitDelay OBJECT-TYPE
	SYNTAX  UpToMaxAge
	ACCESS  read-only
	STATUS  mandatory
	DESCRIPTION
		"The estimated number of seconds  it  takes  to
		transmit  a link- state update packet over this
		interface."
	DEFVAL { 1 }
	::= { axrOspfv3VirtIfEntry 5 }

axrOspfv3VirtIfRetransInterval OBJECT-TYPE
	SYNTAX  UpToMaxAge
	ACCESS  read-only
	STATUS  mandatory
	DESCRIPTION
		"The number of seconds between  link-state  ad-
		vertisement  retransmissions,  for  adjacencies
		belonging to this  interface.  This  value  is
		also used when retransmitting database descrip-
		tion  and  link-state  request  packets.   This
		value  should  be well over the expected round-
		trip time."
	DEFVAL { 5 }
	::= { axrOspfv3VirtIfEntry 6 }

axrOspfv3VirtIfHelloInterval OBJECT-TYPE
	SYNTAX  HelloRange
	ACCESS  read-only
	STATUS  mandatory
	DESCRIPTION
		"The length of time, in  seconds,  between  the
		Hello  packets that the router sends on the in-
		terface.  This value must be the same  for  the
		virtual neighbor."
	DEFVAL { 10 }
	::= { axrOspfv3VirtIfEntry 7 }

axrOspfv3VirtIfRtrDeadInterval OBJECT-TYPE
	SYNTAX  PositiveInteger
	ACCESS  read-only
	STATUS  mandatory
	DESCRIPTION
		"The number of seconds that  a  router's  Hello
		packets  have  not been seen before it's neigh-
		bors declare the router down.  This  should  be
		some  multiple  of  the  Hello  interval.  This
		value must be the same for the  virtual  neigh-
		bor."
	DEFVAL { 60 }
	::= { axrOspfv3VirtIfEntry 8 }

axrOspfv3VirtIfState OBJECT-TYPE
	SYNTAX  INTEGER {
		down (1),    -- these use the same encoding
		pointToPoint (4) -- as the axrOspfv3IfTable
	}
	ACCESS  read-only
	STATUS  mandatory
	DESCRIPTION
		"OSPF virtual interface states."
	DEFVAL  { down }
	::= { axrOspfv3VirtIfEntry 9 }

axrOspfv3VirtIfEvents OBJECT-TYPE
	SYNTAX  Counter32
	ACCESS  read-only
	STATUS  mandatory
	DESCRIPTION
		"The number of state changes or error events on
		this Virtual Link"
	::= { axrOspfv3VirtIfEntry 10 }

axrOspfv3VirtIfStatus OBJECT-TYPE
	SYNTAX  RowStatus
	ACCESS  read-only
	STATUS  mandatory
	DESCRIPTION
		"This variable displays the status of  the  en-
		try.  Setting it to 'invalid' has the effect of
		rendering it inoperative.  The internal  effect
		(row removal) is implementation dependent."
		::= { axrOspfv3VirtIfEntry 11 }

axrOspfv3VirtIfLinkScopeLsaCount OBJECT-TYPE
	SYNTAX  Gauge32
	ACCESS  read-only
	STATUS  mandatory
	DESCRIPTION
		"The total number of Link-Scope link-state
		advertisements in  this  virtual link's link-state
		database."
	::= { axrOspfv3VirtIfEntry 12 }

axrOspfv3VirtIfLinkLsaCksumSum OBJECT-TYPE
	SYNTAX  Integer32
	ACCESS  read-only
	STATUS  mandatory
	DESCRIPTION
		"The 32-bit unsigned sum of the Link-Scope link-state
		advertisements'  LS  checksums  contained in this
		virtual link's link-state database.  The sum can be used
		to determine if  there  has been  a  change  in a
		router's link state database, and to compare the
		link-state database of two routers."
	DEFVAL  { 0 }
	::= { axrOspfv3VirtIfEntry 13 }

--  axrOspfv3 Neighbor Table
--    The axrOspfv3 Neighbor Table describes all neighbors in
--    the locality of the subject router.

axrOspfv3NbrTable OBJECT-TYPE
	SYNTAX  SEQUENCE OF AxrOspfv3NbrEntry
	ACCESS  not-accessible
	STATUS  mandatory
	DESCRIPTION
		"A table of non-virtual neighbor information."
	REFERENCE
		"OSPF Version 2, Section 10  The  Neighbor  Data
		Structure"
	::= { axrOspfv3 9 }

axrOspfv3NbrEntry OBJECT-TYPE
	SYNTAX  AxrOspfv3NbrEntry
	ACCESS  not-accessible
	STATUS  mandatory
	DESCRIPTION
		"The information regarding a single neighbor."
	REFERENCE
		"OSPF Version 2, Section 10  The  Neighbor  Data
		Structure"
	INDEX { axrOspfv3NbrIfIndex, axrOspfv3NbrIpv6Addr }
	::= { axrOspfv3NbrTable 1 }

	AxrOspfv3NbrEntry ::=
		SEQUENCE {
			axrOspfv3NbrDomainNumber
				INTEGER,
			axrOspfv3NbrIfIndex
				Ipv6IfIndex,
			axrOspfv3NbrIpv6Addr
				Ipv6Address,
			axrOspfv3NbrRtrId
				RouterID,
			axrOspfv3NbrOptions
				Integer32,
			axrOspfv3NbrPriority
				DesignatedRouterPriority,
			axrOspfv3NbrState
				INTEGER,
			axrOspfv3NbrEvents
				Counter32,
			axrOspfv3NbrLsRetransQLen
				Gauge32,
			axrOspfv3NbrHelloSuppressed
				TruthValue,
			axrOspfv3NbrIfId
				Ipv6IfIndex
			}

axrOspfv3NbrDomainNumber OBJECT-TYPE
	SYNTAX  INTEGER
	ACCESS  read-only
	STATUS  mandatory
	DESCRIPTION
		"ospfv3 domain number."
	::= { axrOspfv3NbrEntry 1 }

axrOspfv3NbrIfIndex OBJECT-TYPE
	SYNTAX  Ipv6IfIndex
	ACCESS  read-only
	STATUS  mandatory
	DESCRIPTION
		"The local link ID of the link over which the
		neighbor can be reached."
	::= { axrOspfv3NbrEntry 2 }

axrOspfv3NbrIpv6Addr OBJECT-TYPE
	SYNTAX  Ipv6Address
	ACCESS  read-only
	STATUS  mandatory
	DESCRIPTION
		"The IPv6 address of the neighbor associated with
		the local link."
	::= { axrOspfv3NbrEntry 3 }

axrOspfv3NbrRtrId OBJECT-TYPE
	SYNTAX  RouterID
	ACCESS  read-only
	STATUS  mandatory
	DESCRIPTION
		"A 32-bit integer (represented as a type  IpAd-
		dress)  uniquely  identifying  the  neighboring
		router in the Autonomous System."
	::= { axrOspfv3NbrEntry 4 }

axrOspfv3NbrOptions OBJECT-TYPE
	SYNTAX  Integer32
	ACCESS  read-only
	STATUS  mandatory
	DESCRIPTION
		"A Bit Mask corresponding to the neighbor's op-
		tions field."
	DEFVAL { 0 }
	::= { axrOspfv3NbrEntry 5 }

axrOspfv3NbrPriority OBJECT-TYPE
	SYNTAX  DesignatedRouterPriority
	ACCESS  read-only
	STATUS  mandatory
	DESCRIPTION
		"The priority of this neighbor in the designat-
		ed router election algorithm.  The value 0 sig-
		nifies that the neighbor is not eligible to be-
		come  the  designated router on this particular
		network."
	DEFVAL { 1 }
	::= { axrOspfv3NbrEntry 6 }

axrOspfv3NbrState OBJECT-TYPE
	SYNTAX  INTEGER {
		down (1),
		attempt (2),
		init (3),
		twoWay (4),
		exchangeStart (5),
		exchange (6),
		loading (7),
		full (8)
	}
	ACCESS  read-only
	STATUS  mandatory
	DESCRIPTION
		"The State of the relationship with this Neigh-
		bor."
	REFERENCE
		"OSPF Version 2, Section 10.1 Neighbor States"
	DEFVAL  { down }
	::= { axrOspfv3NbrEntry 7 }

axrOspfv3NbrEvents OBJECT-TYPE
	SYNTAX  Counter32
	ACCESS  read-only
	STATUS  mandatory
	DESCRIPTION
		"The number of times this neighbor relationship
		has changed state, or an error has occurred."
	::= { axrOspfv3NbrEntry 8 }

axrOspfv3NbrLsRetransQLen OBJECT-TYPE
	SYNTAX  Gauge32
	ACCESS  read-only
	STATUS  mandatory
	DESCRIPTION
		"The  current  length  of  the   retransmission
		queue."
	::= { axrOspfv3NbrEntry 9 }

axrOspfv3NbrHelloSuppressed OBJECT-TYPE
	SYNTAX  TruthValue
	ACCESS  read-only
	STATUS  mandatory
	DESCRIPTION
		"Indicates whether Hellos are being  suppressed
		to the neighbor"
	::= { axrOspfv3NbrEntry 12 }

axrOspfv3NbrIfId OBJECT-TYPE
	SYNTAX  Ipv6IfIndex
	ACCESS  read-only
	STATUS  mandatory
	DESCRIPTION
		"The interface ID that the neighbor advertises
		in its Hello Packets on this link, that is, the
		neighbor's local interface index."
	::= { axrOspfv3NbrEntry 13 }

--  axrOspfv3 Virtual Neighbor Table
--    This table describes all virtual neighbors.
--    Since Virtual Links are configured in the
--    virtual interface table, this table is read-only.

axrOspfv3VirtNbrTable OBJECT-TYPE
	SYNTAX  SEQUENCE OF AxrOspfv3VirtNbrEntry
	ACCESS  not-accessible
	STATUS  mandatory
	DESCRIPTION
		"A table of virtual neighbor information."
	REFERENCE
		"OSPF Version 2, Section 15  Virtual Links"
	::= { axrOspfv3 10 }

axrOspfv3VirtNbrEntry OBJECT-TYPE
	SYNTAX  AxrOspfv3VirtNbrEntry
	ACCESS  not-accessible
	STATUS  mandatory
	DESCRIPTION
		"Virtual neighbor information."
	INDEX { axrOspfv3VirtNbrArea, axrOspfv3VirtNbrRtrId }
	::= { axrOspfv3VirtNbrTable 1 }

	AxrOspfv3VirtNbrEntry ::=
		SEQUENCE {
			axrOspfv3VirtNbrDomainNumber
				INTEGER,
			axrOspfv3VirtNbrArea
				AreaID,
			axrOspfv3VirtNbrRtrId
				RouterID,
			axrOspfv3VirtNbrIfIndex
				Ipv6IfIndex,
			axrOspfv3VirtNbrIpv6Addr
				Ipv6Address,
			axrOspfv3VirtNbrOptions
				Integer32,
			axrOspfv3VirtNbrState
				INTEGER,
			axrOspfv3VirtNbrEvents
				Counter32,
			axrOspfv3VirtNbrLsRetransQLen
				Gauge32,
			axrOspfv3VirtNbrHelloSuppressed
				TruthValue,
			axrOspfv3VirtNbrIfId
				Ipv6IfIndex
			}

axrOspfv3VirtNbrDomainNumber OBJECT-TYPE
	SYNTAX  INTEGER
	ACCESS  read-only
	STATUS  mandatory
	DESCRIPTION
		"ospfv3 domain number."
	::= { axrOspfv3VirtNbrEntry 1 }

axrOspfv3VirtNbrArea OBJECT-TYPE
	SYNTAX  AreaID
	ACCESS  read-only
	STATUS  mandatory
	DESCRIPTION
		"The Transit Area Identifier."
	::= { axrOspfv3VirtNbrEntry 2 }

axrOspfv3VirtNbrRtrId OBJECT-TYPE
	SYNTAX  RouterID
	ACCESS  read-only
	STATUS  mandatory
	DESCRIPTION
		"A  32-bit  integer  uniquely  identifying  the
		neighboring router in the Autonomous System."
	::= { axrOspfv3VirtNbrEntry 3 }

axrOspfv3VirtNbrIfIndex OBJECT-TYPE
	SYNTAX  Ipv6IfIndex
	ACCESS  read-only
	STATUS  mandatory
	DESCRIPTION
		"The local link ID for the virtual link over
		which the neighbor can be reached."
	::= { axrOspfv3VirtNbrEntry 4 }

axrOspfv3VirtNbrIpv6Addr OBJECT-TYPE
	SYNTAX  Ipv6Address
	ACCESS  read-only
	STATUS  mandatory
	DESCRIPTION
		"The IPv6 address used to reach this Virtual Neighbor.
		It must be a Site-Local or Global scope address."
	::= { axrOspfv3VirtNbrEntry 5 }

axrOspfv3VirtNbrOptions OBJECT-TYPE
	SYNTAX  Integer32
	ACCESS  read-only
	STATUS  mandatory
	DESCRIPTION
		"A Bit Mask corresponding to the neighbor's op-
		tions field."
	::= { axrOspfv3VirtNbrEntry 6 }

axrOspfv3VirtNbrState OBJECT-TYPE
	SYNTAX  INTEGER {
		down (1),
		attempt (2),
		init (3),
		twoWay (4),
		exchangeStart (5),
		exchange (6),
		loading (7),
		full (8)
	}
	ACCESS  read-only
	STATUS  mandatory
	DESCRIPTION
		"The state of the  Virtual  Neighbor  Relation-
		ship."
	::= { axrOspfv3VirtNbrEntry 7 }

axrOspfv3VirtNbrEvents OBJECT-TYPE
	SYNTAX  Counter32
	ACCESS  read-only
	STATUS  mandatory
	DESCRIPTION
		"The number of  times  this  virtual  link  has
		changed its state, or an error has occurred."
	::= { axrOspfv3VirtNbrEntry 8 }

axrOspfv3VirtNbrLsRetransQLen OBJECT-TYPE
	SYNTAX  Gauge32
	ACCESS  read-only
	STATUS  mandatory
	DESCRIPTION
		"The  current  length  of  the   retransmission
		queue."
	::= { axrOspfv3VirtNbrEntry 9 }

axrOspfv3VirtNbrHelloSuppressed OBJECT-TYPE
	SYNTAX  TruthValue
	ACCESS  read-only
	STATUS  mandatory
	DESCRIPTION
		"Indicates whether Hellos are being  suppressed
		to the neighbor"
	::= { axrOspfv3VirtNbrEntry 10 }

axrOspfv3VirtNbrIfId OBJECT-TYPE
	SYNTAX  Ipv6IfIndex
	ACCESS  read-only
	STATUS  mandatory
	DESCRIPTION
		"The interface ID that the neighbor advertises
		in its Hello Packets on this virtual link, that is,
		the neighbor's local interface index."
	::= { axrOspfv3VirtNbrEntry 11 }

 --
 --    The axrOspfv3 Area Aggregate Table
 --

axrOspfv3AreaAggregateTable OBJECT-TYPE
	SYNTAX  SEQUENCE OF AxrOspfv3AreaAggregateEntry
	ACCESS  not-accessible
	STATUS  mandatory
	DESCRIPTION
		"A range of IPv6 prefixes specified by a
		prefix/prefix length  pair. Note that if
		ranges are configured such that one range sub-
		sumes  another range the most specific match is
		the preferred one."
	::= { axrOspfv3 11 }

axrOspfv3AreaAggregateEntry OBJECT-TYPE
	SYNTAX  AxrOspfv3AreaAggregateEntry
	ACCESS  not-accessible
	STATUS  mandatory
	DESCRIPTION
		"A range of IPv6 prefixes specified by a
		prefix/prefix length  pair. Note that if
		ranges are configured such that one range sub-
		sumes  another range the most specific match is
		the preferred one."
	REFERENCE
		"OSPF Version 2, Appendix C.2  Area parameters"
	INDEX { axrOspfv3AreaAggregateAreaID,
		axrOspfv3AreaAggregateAreaLsdbType,
		axrOspfv3AreaAggregateIndex }
	::= { axrOspfv3AreaAggregateTable 1 }

	AxrOspfv3AreaAggregateEntry ::=
		SEQUENCE {
			axrOspfv3AreaAggregateDomainNumber
				INTEGER,
			axrOspfv3AreaAggregateAreaID
				AreaID,
			axrOspfv3AreaAggregateAreaLsdbType
				INTEGER,
			axrOspfv3AreaAggregateIndex
				INTEGER,
			axrOspfv3AreaAggregatePrefix
				Ipv6AddressPrefix,
			axrOspfv3AreaAggregatePrefixLen
				INTEGER,
			axrOspfv3AreaAggregateStatus
				RowStatus,
			axrOspfv3AreaAggregateEffect
				INTEGER
			}

axrOspfv3AreaAggregateDomainNumber OBJECT-TYPE
	SYNTAX  INTEGER
	ACCESS  read-only
	STATUS  mandatory
	DESCRIPTION
		"ospfv3 domain number."
	::= { axrOspfv3AreaAggregateEntry 1 }

axrOspfv3AreaAggregateAreaID OBJECT-TYPE
	SYNTAX  AreaID
	ACCESS  read-only
	STATUS  mandatory
	DESCRIPTION
		"The Area the Address Aggregate is to be  found
		within."
	REFERENCE
		"OSPF Version 2, Appendix C.2 Area parameters"
	::= { axrOspfv3AreaAggregateEntry 2 }

axrOspfv3AreaAggregateAreaLsdbType OBJECT-TYPE
	SYNTAX  INTEGER {
		interAreaPrefixLsa (8195), -- 0x2003
		nssaExternalLsa    (8199)  -- 0x2007
	}
	ACCESS  read-only
	STATUS  mandatory
	DESCRIPTION
		"The type of the Address Aggregate.  This field
		specifies  the  Area Lsdb type that this Address Ag-
		axregate applies to."
	REFERENCE
		"OSPF Version 2, Appendix A.4.1 The  Link  State
		Advertisement header"
	::= { axrOspfv3AreaAggregateEntry 3 }

axrOspfv3AreaAggregateIndex OBJECT-TYPE
	SYNTAX  INTEGER (1..2147483647)
	ACCESS  read-only
	STATUS  mandatory
	DESCRIPTION
		"A unique identifier for this aggregate table entry."
	::= { axrOspfv3AreaAggregateEntry 4 }

axrOspfv3AreaAggregatePrefix OBJECT-TYPE
	SYNTAX  Ipv6AddressPrefix
	ACCESS  read-only
	STATUS  mandatory
	DESCRIPTION
		"The IPv6 Prefix."
	REFERENCE
		"OSPF Version 2, Appendix C.2 Area parameters"
	::= { axrOspfv3AreaAggregateEntry 5 }

axrOspfv3AreaAggregatePrefixLen OBJECT-TYPE
	SYNTAX  INTEGER ( 3..128 )
--	UNITS  "bits"
	ACCESS  read-only
	STATUS  mandatory
	DESCRIPTION
		"The length of the prefix (in bits). A prefix can
		not be shorter than 3 bits."
	REFERENCE
		"OSPF Version 2, Appendix C.2 Area parameters"
	::= { axrOspfv3AreaAggregateEntry 6 }

axrOspfv3AreaAggregateStatus OBJECT-TYPE
	SYNTAX  RowStatus
	ACCESS  read-only
	STATUS  mandatory
	DESCRIPTION
		"This variable displays the status of  the  en-
		try.  Setting it to 'invalid' has the effect of
		rendering it inoperative.  The internal  effect
		(row removal) is implementation dependent."
	::= { axrOspfv3AreaAggregateEntry 7 }

axrOspfv3AreaAggregateEffect OBJECT-TYPE
	SYNTAX  INTEGER {
		advertiseMatching (1),
		doNotAdvertiseMatching (2)
	}
	ACCESS  read-only
	STATUS  mandatory
	DESCRIPTION
		"Prefixes subsumed by ranges either trigger  the
		advertisement  of  the indicated aggregate (ad-
		vertiseMatching), or result in the prefix not
		being advertised at all outside the area."
	DEFVAL  { advertiseMatching }
	::= { axrOspfv3AreaAggregateEntry 8 }

--  axrIsis group

axrIsisSysTable OBJECT-TYPE
	SYNTAX  SEQUENCE OF AxrIsisSysEntry
	ACCESS  not-accessible
	STATUS  mandatory
	DESCRIPTION
		"The set of instances of the Integrated IS-IS protocol existing on the system."
	::= { axrIsisSystem 1 }

axrIsisSysEntry OBJECT-TYPE
	SYNTAX  AxrIsisSysEntry
	ACCESS  not-accessible
	STATUS  mandatory
	DESCRIPTION
		"Each row defines information specific to a single instance of the IS-IS protocol existing on the system."
    INDEX { axrIsisSysInstance }
	::= { axrIsisSysTable 1 }

	AxrIsisSysEntry ::=
		SEQUENCE {
		    axrIsisSysInstance		INTEGER
		}

axrIsisSysInstance OBJECT-TYPE
	SYNTAX  INTEGER
--	ACCESS  accessible-for-notify
	ACCESS  not-accessible
	STATUS  mandatory
	DESCRIPTION
		"The unique identifier of the Integrated IS-IS instance to which this row corresponds."
	::= { axrIsisSysEntry 1 }

axrIsisSysLevelTable OBJECT-TYPE
	SYNTAX  SEQUENCE OF AxrIsisSysLevelEntry
	ACCESS  not-accessible
	STATUS  mandatory
	DESCRIPTION
		"Level specific information about the System."
	::= { axrIsisSysLevel 1 }

axrIsisSysLevelEntry OBJECT-TYPE
	SYNTAX  AxrIsisSysLevelEntry
	ACCESS  not-accessible
	STATUS  mandatory
	DESCRIPTION
		"Describe variables defined for Area or Domain."
    INDEX { axrIsisSysInstance,axrIsisSysLevelIndex }
	::= { axrIsisSysLevelTable 1 }

	AxrIsisSysLevelEntry ::=
		SEQUENCE {
		    axrIsisSysLevelIndex		INTEGER
		}

axrIsisSysLevelIndex OBJECT-TYPE
	SYNTAX  INTEGER
--	ACCESS  accessible-for-notify
	ACCESS  not-accessible
	STATUS  mandatory
	DESCRIPTION
		"The level that this entry describes."
	::= { axrIsisSysLevelEntry 1 }

axrIsisCircTable OBJECT-TYPE
	SYNTAX  SEQUENCE OF AxrIsisCircEntry
	ACCESS  not-accessible
	STATUS  mandatory
	DESCRIPTION
		"The table of circuits used by each instance of Integrated IS-IS on this system."
	::= { axrIsisCirc 1 }

axrIsisCircEntry OBJECT-TYPE
	SYNTAX  AxrIsisCircEntry
	ACCESS  not-accessible
	STATUS  mandatory
	DESCRIPTION
		"An isisCircEntry exists for each circuit used by Integrated IS-IS on this system."
    INDEX { axrIsisSysInstance,axrIsisCircIndex }
	::= { axrIsisCircTable 1 }

	AxrIsisCircEntry ::=
		SEQUENCE {
		    axrIsisCircIndex		INTEGER
		}

axrIsisCircIndex OBJECT-TYPE
	SYNTAX  INTEGER
--	ACCESS  accessible-for-notify
	ACCESS  not-accessible
	STATUS  mandatory
	DESCRIPTION
		"The identifier of this circuit, unique within the instance of the IS-IS protocol. This object follows the index behavior.  This is for SNMP Indexing purposes only and need not have any relation to any protocol value."
	::= { axrIsisCircEntry 1 }

axrIsisNotificationTable OBJECT-TYPE
	SYNTAX  SEQUENCE OF AxrIsisNotificationEntry
	ACCESS  not-accessible
	STATUS  mandatory
	DESCRIPTION
		"Objects seen in the most recent notification from this instance of the IS-IS protocol."
	::= { axrIsisNotification 1 }

axrIsisNotificationEntry OBJECT-TYPE
	SYNTAX  AxrIsisNotificationEntry
	ACCESS  not-accessible
	STATUS  mandatory
	DESCRIPTION
		"Each entry defines variables relevant to notifications for one instance of the IS-IS protocol."
    INDEX { axrIsisSysInstance }
	::= { axrIsisNotificationTable 1 }

	AxrIsisNotificationEntry ::=
		SEQUENCE {
		    axrIsisPduLspId		OCTET STRING,
		    axrIsisAdjState		INTEGER
		}

axrIsisPduLspId OBJECT-TYPE
	SYNTAX  OCTET STRING
--	ACCESS  accessible-for-notify
	ACCESS  not-accessible
	STATUS  mandatory
	DESCRIPTION
		"An Octet String that uniquely identifies a Link State PDU."
	::= { axrIsisNotificationEntry 1 }

axrIsisAdjState OBJECT-TYPE
	SYNTAX  INTEGER
--	ACCESS  accessible-for-notify
	ACCESS  not-accessible
	STATUS  mandatory
	DESCRIPTION
		"The state of the adjacency REFERENCE ISIS.aoi adjacencyState (78)"
	::= { axrIsisNotificationEntry 9 }

--  axrStatic
axrStaticTable OBJECT-TYPE
	SYNTAX  SEQUENCE OF AxrStaticGatewayEntry
	ACCESS  not-accessible
	STATUS  mandatory
	DESCRIPTION
		"The set of instances of the static gateway state."
	::= { axrStatic 1 }

axrStaticGatewayEntry OBJECT-TYPE
	SYNTAX  AxrStaticGatewayEntry
	ACCESS  not-accessible
	STATUS  mandatory
	DESCRIPTION
		"Each row defines information about static route gateway state."
    INDEX { axrStaticGatewayAddr }
	::= { axrStaticTable 1 }

	AxrStaticGatewayEntry ::=
		SEQUENCE {
		    axrStaticGatewayAddr		IpAddress,
		    axrStaticGatewayState		INTEGER
		}
		
axrStaticGatewayAddr OBJECT-TYPE
	SYNTAX  IpAddress
	ACCESS  not-accessible
	STATUS  mandatory
	DESCRIPTION
		"The static route gateway address."
	::= { axrStaticGatewayEntry 1 }
	
axrStaticGatewayState OBJECT-TYPE
	SYNTAX  INTEGER {
                    reachable(1),
                    unreachable(2)
                }
	ACCESS  not-accessible
	STATUS  mandatory
	DESCRIPTION
		"The state of static route gateway."
	::= { axrStaticGatewayEntry 2 }	

axrStaticIpv6Table OBJECT-TYPE
	SYNTAX  SEQUENCE OF AxrStaticIpv6GatewayEntry
	ACCESS  not-accessible
	STATUS  mandatory
	DESCRIPTION
		"The set of instances of the ipv6 static gateway state."
	::= { axrStatic 3 }

axrStaticIpv6GatewayEntry OBJECT-TYPE
	SYNTAX  AxrStaticIpv6GatewayEntry
	ACCESS  not-accessible
	STATUS  mandatory
	DESCRIPTION
		"Each row defines information about ipv6 static route gateway state."
        INDEX { axrStaticIpv6Ifindex,
                axrStaticIpv6GatewayAddr }
	::= { axrStaticIpv6Table 1 }

	AxrStaticIpv6GatewayEntry ::=
		SEQUENCE {
		    axrStaticIpv6Ifindex	INTEGER,
		    axrStaticIpv6GatewayAddr	Ipv6Address,
		    axrStaticIpv6GatewayState	INTEGER
		}
axrStaticIpv6Ifindex OBJECT-TYPE
	SYNTAX  INTEGER
	ACCESS  not-accessible
	STATUS  mandatory
	DESCRIPTION
		"The ifIndex ralated static gateway address."
	::= { axrStaticIpv6GatewayEntry 1 }
			
axrStaticIpv6GatewayAddr OBJECT-TYPE
	SYNTAX  Ipv6Address
	ACCESS  not-accessible
	STATUS  mandatory
	DESCRIPTION
		"The static route gateway address."
	::= { axrStaticIpv6GatewayEntry 2 }
	
axrStaticIpv6GatewayState OBJECT-TYPE
	SYNTAX  INTEGER {
                    reachable(1),
                    unreachable(2)
                }
	ACCESS  not-accessible
	STATUS  mandatory
	DESCRIPTION
		"The state of static route gateway."
	::= { axrStaticIpv6GatewayEntry 3 }	

--  axrLogin

axrLoginName OBJECT-TYPE
	SYNTAX  DisplayString
	ACCESS  not-accessible
	STATUS  mandatory
	DESCRIPTION
		"Log in user name."
	::= { axrLogin 1 }

axrLoginTime OBJECT-TYPE
	SYNTAX  DisplayString
	ACCESS  not-accessible
	STATUS  mandatory
	DESCRIPTION
		"Date, time and time zone of user log in.
		Format : YYYY/MM/DD hh:mm:ss XXXXXX(time zone)
		Time zone format :
		  JST    : JST
		  GMT+09 : GMT + 09 hours
		  GMT+10 : GMT + 10 hours"
	::= { axrLogin 2 }

axrLogoutTime OBJECT-TYPE
	SYNTAX  DisplayString
	ACCESS  not-accessible
	STATUS  mandatory
	DESCRIPTION
		"Date, time and time zone of user log out.
		Format : YYYY/MM/DD hh:mm:ss XXXXXX(time zone)
		Time zone format :
		  JST    : JST
		  GMT+09 : GMT + 09 hours
		  GMT+10 : GMT + 10 hours"
	::= { axrLogin 3 }

axrLoginFailureTime OBJECT-TYPE
	SYNTAX  DisplayString
	ACCESS  not-accessible
	STATUS  mandatory
	DESCRIPTION
		"Date, time and time zone of user log in failure.
		Format : YYYY/MM/DD hh:mm:ss XXXXXX(time zone)
		Time zone format :
		  JST    : JST
		  GMT+09 : GMT + 09 hours
		  GMT+10 : GMT + 10 hours"
	::= { axrLogin 4 }

axrLoginLocation OBJECT-TYPE
	SYNTAX  DisplayString
	ACCESS  not-accessible
	STATUS  mandatory
	DESCRIPTION
		"Connection information of log in user.
		The status will be 'console' or 'aux'.
		If other, displays 'IPADDRESS(APLLICATION)'.
		ex. '192.168.11.1(telnet)'"
	::= { axrLogin 5 }

axrLoginLine OBJECT-TYPE
	SYNTAX  DisplayString
	ACCESS  not-accessible
	STATUS  mandatory
	DESCRIPTION
		"Terminal information of log in user.
		The status will be 'console' or 'aux'.
		If other, displays 'TERMINAL(APLLICATION)'.
		ex. 'tty/1(telnet)'"
	::= { axrLogin 6 }

axrLogoutStatus OBJECT-TYPE
	SYNTAX  INTEGER {
		error(1),
		success(2),
		timeout(3),
		disconnect(4),
		force(5)
	      }
	ACCESS  not-accessible
	STATUS  mandatory
	DESCRIPTION
		"Log out factor.
		 error(1)      : log out due to none of bellow
		 success(2)    : log out due to command
		 timeout(3)    : log out due to 'auto-logout'
		 disconnect(4) : log out due to line disconnection
		 force(5)      : log out due to other user's command"
	::= { axrLogin 7 }

--  axrBootManagement group

axrBootReason  OBJECT-TYPE
	SYNTAX  INTEGER {
		power-on(1),
		reload(2),
		system-fault(3),
		system-stall(4),
		reset(5),
		fail-over(6),
		default-restart(7)
	      }
	ACCESS  read-only
	STATUS  mandatory
	DESCRIPTION
		"Reason of system start."
	::= { axrBootManagement 1 }

--  axrlldp group
--  axrlldpConfiguration group

axrlldpMessageTxInterval OBJECT-TYPE
	SYNTAX  INTEGER
	ACCESS  read-only
	STATUS  mandatory
	DESCRIPTION
		"LDPDU transmitting interval"
	::= { axrlldpConfiguration 1 }

axrlldpMessageTxHoldMultiplier OBJECT-TYPE
	SYNTAX  INTEGER
	ACCESS  read-only
	STATUS  mandatory
	DESCRIPTION
		"Time coefficient for contiguity equipment to hold about the LLDP frame which this equipment transmitted"
	::= { axrlldpConfiguration 2 }

axrlldpPortConfigTable OBJECT-TYPE
	SYNTAX  SEQUENCE OF AxrlldpPortConfigEntry
	ACCESS  not-accessible
	STATUS  mandatory
	DESCRIPTION
		"The table about LDPDU transmission"
	::= { axrlldpConfiguration 6 }

axrlldpPortConfigEntry OBJECT-TYPE
	SYNTAX  AxrlldpPortConfigEntry
	ACCESS  not-accessible
	STATUS  mandatory
	DESCRIPTION
		"The entry about LDPDU transmission"
    INDEX { axrlldpPortConfigPortNum }
	::= { axrlldpPortConfigTable 1 }

	AxrlldpPortConfigEntry ::=
		SEQUENCE {
		    axrlldpPortConfigPortNum		INTEGER,
		    axrlldpPortConfigAdminStatus		INTEGER,
		    axrlldpPortConfigTLVsTxEnable	BITS,
		    axrlldpPortConfigRowStatus		RowStatus
		}

axrlldpPortConfigPortNum OBJECT-TYPE
	SYNTAX  INTEGER
	ACCESS  not-accessible
	STATUS  mandatory
	DESCRIPTION
		"Port discernment index"
	::= {axrlldpPortConfigEntry 2 }

axrlldpPortConfigAdminStatus OBJECT-TYPE
	SYNTAX  INTEGER
	ACCESS  read-only
	STATUS  mandatory
	DESCRIPTION
		"The port state of this equipment about transmission and reception of LDPDU"
	::= {axrlldpPortConfigEntry 3 }

axrlldpPortConfigTLVsTxEnable OBJECT-TYPE
	SYNTAX  BITS{
                    portDesc(4),
                    sysName(5),
                    sysDesc(6),
                    sysCap(7)
                }
	ACCESS  read-only
	STATUS  mandatory
	DESCRIPTION
		"The TLV state about the port concerned which can be transmitted"
	::= {axrlldpPortConfigEntry 4 }

axrlldpPortConfigRowStatus OBJECT-TYPE
	SYNTAX  RowStatus
	ACCESS  read-only
	STATUS  mandatory
	DESCRIPTION
		"The state of this entry"
	::= {axrlldpPortConfigEntry 5 }

-- axrlldpStats group

axrlldpStatsTable OBJECT-TYPE
	SYNTAX  SEQUENCE OF AxrlldpStatsEntry
	ACCESS  not-accessible
	STATUS  mandatory
	DESCRIPTION
		"The table about LLDP statistics information"
	::= { axrlldpStats 1 }

axrlldpStatsEntry OBJECT-TYPE
	SYNTAX  AxrlldpStatsEntry
	ACCESS  not-accessible
	STATUS  mandatory
	DESCRIPTION
		"The Entry about LLDP statistics information"
    INDEX { axrlldpStatsPortNum }
	::= { axrlldpStatsTable 1 }

	AxrlldpStatsEntry ::=
		SEQUENCE {
		    axrlldpStatsPortNum			INTEGER,
		    axrlldpStatsOperStatus		INTEGER,
		    axrlldpStatsFramesInErrors		Counter,
		    axrlldpStatsFramesInTotal		Counter,
		    axrlldpStatsFramesOutTotal		Counter,
		    axrlldpStatsTLVsInErrors		Counter,
		    axrlldpStatsTLVsDiscardedTotal	Counter
		}

axrlldpStatsPortNum OBJECT-TYPE
	SYNTAX  INTEGER
	ACCESS  not-accessible
	STATUS  mandatory
	DESCRIPTION
		"Port discernment index"
	::= {axrlldpStatsEntry 2 }

axrlldpStatsOperStatus OBJECT-TYPE
	SYNTAX  INTEGER
	ACCESS  read-only
	STATUS  mandatory
	DESCRIPTION
		"The employment state about the port concerned"
	::= {axrlldpStatsEntry 3 }

axrlldpStatsFramesInErrors OBJECT-TYPE
	SYNTAX  Counter
	ACCESS  read-only
	STATUS  mandatory
	DESCRIPTION
		"The number of inaccurate LDPDU reception about the port concerned"
	::= {axrlldpStatsEntry 4 }

axrlldpStatsFramesInTotal OBJECT-TYPE
	SYNTAX  Counter
	ACCESS  read-only
	STATUS  mandatory
	DESCRIPTION
		"The total number of LDPDU reception about the port concerned"
	::= {axrlldpStatsEntry 5 }

axrlldpStatsFramesOutTotal OBJECT-TYPE
	SYNTAX  Counter
	ACCESS  read-only
	STATUS  mandatory
	DESCRIPTION
		"The total number of LDPDU transmission about the port concerned"
	::= {axrlldpStatsEntry 6 }

axrlldpStatsTLVsInErrors OBJECT-TYPE
	SYNTAX  Counter
	ACCESS  read-only
	STATUS  mandatory
	DESCRIPTION
		"The number of inaccurate TLV reception about the port concerned"
	::= {axrlldpStatsEntry 7 }

axrlldpStatsTLVsDiscardedTotal OBJECT-TYPE
	SYNTAX  Counter
	ACCESS  read-only
	STATUS  mandatory
	DESCRIPTION
		"The total abandonment TLV number about the port concerned"
	::= {axrlldpStatsEntry 8 }

-- axrlldpLocalSystemData group

axrlldpLocChassisType OBJECT-TYPE
	SYNTAX  INTEGER
	ACCESS  read-only
	STATUS  mandatory
	DESCRIPTION
		"The chassis type about this equipment"
	::= {axrlldpLocalSystemData 1 }

axrlldpLocChassisId OBJECT-TYPE
	SYNTAX  OCTET STRING 
	ACCESS  read-only
	STATUS  mandatory
	DESCRIPTION
		"The chassis ID about this equipment"
	::= {axrlldpLocalSystemData 2 }

axrlldpLocSysName OBJECT-TYPE
	SYNTAX  OCTET STRING
	ACCESS  read-only
	STATUS  mandatory
	DESCRIPTION
		"The System Name about this equipment"
	::= {axrlldpLocalSystemData 3 }

axrlldpLocSysDesc OBJECT-TYPE
	SYNTAX  DisplayString
	ACCESS  read-only
	STATUS  mandatory
	DESCRIPTION
		"System information about this equipment"
	::= {axrlldpLocalSystemData 4 }

axrlldpLocPortTable OBJECT-TYPE
	SYNTAX  SEQUENCE OF AxrlldpLocPortEntry
	ACCESS  not-accessible
	STATUS  mandatory
	DESCRIPTION
		"The table about the port of this equipment"
	::= { axrlldpLocalSystemData 7 }

axrlldpLocPortEntry OBJECT-TYPE
	SYNTAX  AxrlldpLocPortEntry
	ACCESS  not-accessible
	STATUS  mandatory
	DESCRIPTION
		"The entry about the port of this equipment"
    INDEX { axrlldpLocPortNum }
	::= { axrlldpLocPortTable 1 }

	AxrlldpLocPortEntry ::=
		SEQUENCE {
		    axrlldpLocPortNum		INTEGER,
		    axrlldpLocPortType		INTEGER,
		    axrlldpLocPortId		OCTET STRING,
		    axrlldpLocPortDesc		OCTET STRING
		}

axrlldpLocPortNum OBJECT-TYPE
	SYNTAX  INTEGER
	ACCESS  not-accessible
	STATUS  mandatory
	DESCRIPTION
		"Port discernment index"
	::= {axrlldpLocPortEntry 1 }

axrlldpLocPortType OBJECT-TYPE
	SYNTAX  INTEGER
	ACCESS  read-only
	STATUS  mandatory
	DESCRIPTION
		"The port type about the port concerned of this equipment"
	::= {axrlldpLocPortEntry 2 }

axrlldpLocPortId OBJECT-TYPE
	SYNTAX  OCTET STRING
	ACCESS  read-only
	STATUS  mandatory
	DESCRIPTION
		"The port ID about the port concerned of this equipment"
	::= {axrlldpLocPortEntry 3 }

axrlldpLocPortDesc OBJECT-TYPE
	SYNTAX  OCTET STRING
	ACCESS  read-only
	STATUS  mandatory
	DESCRIPTION
		"Port information about the port concerned of this equipment"
	::= {axrlldpLocPortEntry 4 }

-- axrlldpRemoteSystemData group

axrlldpRemTable OBJECT-TYPE
	SYNTAX  SEQUENCE OF AxrlldpRemEntry
	ACCESS  not-accessible
	STATUS  mandatory
	DESCRIPTION
		"The table about contiguity equipment"
	::= { axrlldpRemoteSystemData 1 }

axrlldpRemEntry OBJECT-TYPE
	SYNTAX  AxrlldpRemEntry
	ACCESS  not-accessible
	STATUS  mandatory
	DESCRIPTION
		"The entry about contiguity equipment"
    INDEX { axrlldpRemLocalPortNum,axrlldpRemIndex }
	::= { axrlldpRemTable 1 }

	AxrlldpRemEntry ::=
		SEQUENCE {
		    axrlldpRemLocalPortNum		INTEGER,
		    axrlldpRemIndex			INTEGER,
		    axrlldpRemRemoteChassisType		INTEGER,
		    axrlldpRemRemoteChassis		OCTET STRING,
		    axrlldpRemRemotePortType		INTEGER,
		    axrlldpRemRemotePort			OCTET STRING,
		    axrlldpRemPortDesc			OCTET STRING,
		    axrlldpRemSysName			OCTET STRING,
		    axrlldpRemSysDesc			OCTET STRING
		}

axrlldpRemLocalPortNum OBJECT-TYPE
	SYNTAX  INTEGER
	ACCESS  not-accessible
	STATUS  mandatory
	DESCRIPTION
		"The discernment index of the port of this equipment which received the information about contiguity equipment"
	::= {axrlldpRemEntry 2 }

axrlldpRemIndex OBJECT-TYPE
	SYNTAX  INTEGER
	ACCESS  not-accessible
	STATUS  mandatory
	DESCRIPTION
		"The index about contiguity equipment"
	::= {axrlldpRemEntry 3 }

axrlldpRemRemoteChassisType OBJECT-TYPE
	SYNTAX  INTEGER
	ACCESS  read-only
	STATUS  mandatory
	DESCRIPTION
		"The chassis type about contiguity equipment"
	::= {axrlldpRemEntry 4 }

axrlldpRemRemoteChassis OBJECT-TYPE
	SYNTAX  OCTET STRING
	ACCESS  read-only
	STATUS  mandatory
	DESCRIPTION
		"The chassis ID about contiguity equipment"
	::= {axrlldpRemEntry 5 }

axrlldpRemRemotePortType OBJECT-TYPE
	SYNTAX  INTEGER
	ACCESS  read-only
	STATUS  mandatory
	DESCRIPTION
		"The port type about the port concerned of contiguity equipment"
	::= {axrlldpRemEntry 6 }

axrlldpRemRemotePort OBJECT-TYPE
	SYNTAX  OCTET STRING
	ACCESS  read-only
	STATUS  mandatory
	DESCRIPTION
		"The port ID about the port concerned of contiguity equipment"
	::= {axrlldpRemEntry 7 }

axrlldpRemPortDesc OBJECT-TYPE
	SYNTAX  OCTET STRING
	ACCESS  read-only
	STATUS  mandatory
	DESCRIPTION
		"Information about the port concerned of contiguity equipment"
	::= {axrlldpRemEntry 8 }

axrlldpRemSysName OBJECT-TYPE
	SYNTAX  OCTET STRING
	ACCESS  read-only
	STATUS  mandatory
	DESCRIPTION
		"The system name about contiguity equipment"
	::= {axrlldpRemEntry 9 }

axrlldpRemSysDesc OBJECT-TYPE
	SYNTAX  OCTET STRING
	ACCESS  read-only
	STATUS  mandatory
	DESCRIPTION
		"System information about contiguity equipment"
	::= {axrlldpRemEntry 10 }

axrlldpRemOriginInfoTable OBJECT-TYPE
	SYNTAX  SEQUENCE OF AxrlldpRemOriginInfoEntry
	ACCESS  not-accessible
	STATUS  mandatory
	DESCRIPTION
		"The table about original with AlaxalA networks TLV of contiguity equipment"
	::= { axrlldpRemoteOriginInfoData 1 }

axrlldpRemOriginInfoEntry OBJECT-TYPE
	SYNTAX  AxrlldpRemOriginInfoEntry
	ACCESS  not-accessible
	STATUS  mandatory
	DESCRIPTION
		"The entry about original with AlaxalA networks TLV of contiguity equipment"
    INDEX { axrlldpRemOriginInfoPortNum,axrlldpRemOriginInfoIndex }
	::= { axrlldpRemOriginInfoTable 1 }

	AxrlldpRemOriginInfoEntry ::=
		SEQUENCE {
		    axrlldpRemOriginInfoPortNum		INTEGER,
		    axrlldpRemOriginInfoIndex		INTEGER,
		    axrlldpRemOriginInfoLowerVlanList	OCTET STRING,
		    axrlldpRemOriginInfoHigherVlanList	OCTET STRING,
		    axrlldpRemOriginInfoIPv4Address	OCTET STRING,
		    axrlldpRemOriginInfoIPv4PortType	INTEGER,
		    axrlldpRemOriginInfoIPv4VlanId	INTEGER,
		    axrlldpRemOriginInfoIPv6Address	OCTET STRING,
		    axrlldpRemOriginInfoIPv6PortType	INTEGER,
		    axrlldpRemOriginInfoIPv6VlanId	INTEGER
		}

axrlldpRemOriginInfoPortNum OBJECT-TYPE
	SYNTAX  INTEGER
	ACCESS  not-accessible
	STATUS  mandatory
	DESCRIPTION
		"The discernment index of the port of this equipment which received the information about contiguity equipment."
	::= {axrlldpRemOriginInfoEntry 1 }

axrlldpRemOriginInfoIndex OBJECT-TYPE
	SYNTAX  INTEGER
	ACCESS  not-accessible
	STATUS  mandatory
	DESCRIPTION
		"The index about contiguity equipment"
	::= {axrlldpRemOriginInfoEntry 2 }

axrlldpRemOriginInfoLowerVlanList OBJECT-TYPE
	SYNTAX  OCTET STRING
	ACCESS  read-only
	STATUS  mandatory
	DESCRIPTION
		"What expressed effective VLAN ID by the bit map by VLAN 1-2047 in the port concerned of contiguity equipment.
		 (The first bit (27 bits of the 0th byte) shows the presence of the untagged definition, and, hereafter,
		 shows effective/invalidity of VLAN 1-2047)"
	::= {axrlldpRemOriginInfoEntry 3 }

axrlldpRemOriginInfoHigherVlanList OBJECT-TYPE
	SYNTAX  OCTET STRING
	ACCESS  read-only
	STATUS  mandatory
	DESCRIPTION
		"What expressed effective VLAN ID by the bit map by VLAN 2048-4095 in the port concerned of contiguity equipment.
		(Effective/invalidity of VLAN 2048-4095 is sequentially shown from the first bit (27 bits of the 0th byte))" 
	::= {axrlldpRemOriginInfoEntry 4 }

axrlldpRemOriginInfoIPv4Address OBJECT-TYPE
	SYNTAX  OCTET STRING
	ACCESS  read-only
	STATUS  mandatory
	DESCRIPTION
		"IPv4 address given to the port concerned of contiguity equipment"
	::= {axrlldpRemOriginInfoEntry 5 }

axrlldpRemOriginInfoIPv4PortType OBJECT-TYPE
	SYNTAX  INTEGER
	ACCESS  read-only
	STATUS  mandatory
	DESCRIPTION
		"Port classification of the port of contiguity equipment concerned"
	::= {axrlldpRemOriginInfoEntry 6 }

axrlldpRemOriginInfoIPv4VlanId OBJECT-TYPE
	SYNTAX  INTEGER
	ACCESS  read-only
	STATUS  mandatory
	DESCRIPTION
		"The smallest thing among VLAN ID to which IPv4 address is given"
	::= {axrlldpRemOriginInfoEntry 7 }

axrlldpRemOriginInfoIPv6Address OBJECT-TYPE
	SYNTAX  OCTET STRING
	ACCESS  read-only
	STATUS  mandatory
	DESCRIPTION
		"The IPv6 address given to the port concerned of contiguity equipment"
	::= {axrlldpRemOriginInfoEntry 8 }

axrlldpRemOriginInfoIPv6PortType OBJECT-TYPE
	SYNTAX  INTEGER
	ACCESS  read-only
	STATUS  mandatory
	DESCRIPTION
		"Port classification of the port of contiguity equipment concerned"
	::= {axrlldpRemOriginInfoEntry 9 }

axrlldpRemOriginInfoIPv6VlanId OBJECT-TYPE
	SYNTAX  INTEGER
	ACCESS  read-only
	STATUS  mandatory
	DESCRIPTION
		"The smallest thing among VLAN ID to which the IPv6 address is given"
	::= {axrlldpRemOriginInfoEntry 10 }

--axrBfdMIB group

axrBfdAdminStatus OBJECT-TYPE
	SYNTAX  INTEGER {
		enable(1),
		disable(2)
	}
	ACCESS  read-only
	STATUS  mandatory
	DESCRIPTION
		"The status of BFD."
	::= { axrBfdScalarObjects 1 }

axrBfdVersionNumber OBJECT-TYPE
	SYNTAX  Unsigned32
	ACCESS  read-only
	STATUS  mandatory
	DESCRIPTION
		"BFD protocol version."
	::= { axrBfdScalarObjects 3 }

axrBfdSessNotificationsEnable OBJECT-TYPE
	SYNTAX  TruthValue
	ACCESS  read-only
	STATUS  mandatory
	DESCRIPTION
		"This value indicates whether trap about BFD sends or not."
	::= { axrBfdScalarObjects 4 }

axrBfdSessTable OBJECT-TYPE
	SYNTAX  SEQUENCE OF AxrBfdSessEntry
	ACCESS  not-accessible
	STATUS  mandatory
	DESCRIPTION
		"The BFD Session Table describes the BFD sessions."
	::= { axrBfdObjects 2 }

axrBfdSessEntry OBJECT-TYPE
	SYNTAX  AxrBfdSessEntry
	ACCESS  not-accessible
	STATUS  mandatory
	DESCRIPTION
		"The BFD Session Entry describes BFD session."
	INDEX  { axrBfdSessIndex }
	::= { axrBfdSessTable 1 }

	AxrBfdSessEntry ::= 
		SEQUENCE {
			axrBfdSessIndex                      Unsigned32,
			axrBfdSessApplicationId              Unsigned32,
			axrBfdSessDiscriminator              Unsigned32,
			axrBfdSessRemoteDiscr                Unsigned32,
			axrBfdSessUdpPort                    InetPortNumber,
			axrBfdSessState                      INTEGER,
			axrBfdSessRemoteHeardFlag            TruthValue,
			axrBfdSessDiag                       Unsigned32,
			axrBfdSessOperMode                   INTEGER,
			axrBfdSessDemandModeDesiredFlag      TruthValue,
			axrBfdSessEchoFuncModeDesiredFlag    TruthValue,
			axrBfdSessControlPlanIndepFlag       TruthValue,
			axrBfdSessAddrType                   InetAddressType,
			axrBfdSessAddr                       InetAddress,
			axrBfdSessDesiredMinTxInterval       Unsigned32,
			axrBfdSessDesiredMinRxInterval       Unsigned32,
			axrBfdSessDesiredMinEchoRxInterval   Unsigned32,
			axrBfdSessDetectMult                 Unsigned32,
			axrBfdSessStorType                   StorageType,
			axrBfdSessRowStatus                  RowStatus,
			axrBfdSessAuthPresFlag               TruthValue,
			axrBfdSessAuthenticationType         INTEGER
		}

axrBfdSessIndex OBJECT-TYPE
	SYNTAX  Unsigned32
	ACCESS  not-accessible
	STATUS  mandatory
	DESCRIPTION
		"This object contains an index used to represent a unique
		BFD session on this device."
	::= { axrBfdSessEntry 1 }

axrBfdSessApplicationId OBJECT-TYPE
	SYNTAX  Unsigned32
	ACCESS  read-only
	STATUS  mandatory
	DESCRIPTION
		"This object contains an index used to indicate a local
		application which owns or maintains this BFD session. For
		instance, the MPLS VPN process may maintain a subset of the
		total number of BFD sessions. This application ID provides a
		convenient way to segregate sessions by the applications
		which maintain them."
	::= { axrBfdSessEntry 2 }

axrBfdSessDiscriminator OBJECT-TYPE
	SYNTAX  Unsigned32
	ACCESS  read-only
	STATUS  mandatory
	DESCRIPTION
		"This object specifies the local discriminator for this BFD
		session, used to uniquely identify it."
	::= { axrBfdSessEntry 3 }

axrBfdSessRemoteDiscr OBJECT-TYPE
	SYNTAX  Unsigned32
	ACCESS  read-only
	STATUS  mandatory
	DESCRIPTION
		"This object specifies the session discriminator chosen by
		the remote system for this BFD session."
	::= { axrBfdSessEntry 4 }

axrBfdSessUdpPort OBJECT-TYPE
	SYNTAX  InetPortNumber
	ACCESS  read-only
	STATUS  mandatory
	DESCRIPTION
		"The UDP Port for BFD. The default value is the well-known
		value for this port."
	::= { axrBfdSessEntry 5 }

axrBfdSessState OBJECT-TYPE
	SYNTAX  INTEGER {
		adminDown(1),
		down(2),
		init(3),
		up(4)
	}
	ACCESS  read-only
	STATUS  mandatory
	DESCRIPTION
		"The perceived state of the BFD session."
	::= { axrBfdSessEntry 6 }

axrBfdSessRemoteHeardFlag OBJECT-TYPE
	SYNTAX  TruthValue
	ACCESS  read-only
	STATUS  mandatory
	DESCRIPTION
		"This object specifies status of BFD packet reception from
		the remote system. Specifically, it is set to true(1) if the
		local system is actively receiving BFD packets from the
		remote system, and is set to false(0) if the local system has
		not received BFD packets recently (within the detection time)
		or if the local system is attempting to tear down the BFD
		session."
	::= { axrBfdSessEntry 7 }

axrBfdSessDiag OBJECT-TYPE
	SYNTAX  Unsigned32
	ACCESS  not-accessible
	STATUS  mandatory
	DESCRIPTION
		"A diagnostic code specifying the local system's reason for
		the last transition of the session from up(1) to some other
		state."
	::= { axrBfdSessEntry 8 }

axrBfdSessOperMode OBJECT-TYPE
	SYNTAX  INTEGER {
		asynchModeWEchoFun(1),
		asynchModeWOEchoFun(2),
		demandModeWEchoFunction(3),
		demandModeWOEchoFunction(4)
	}
	ACCESS  read-only
	STATUS  mandatory
	DESCRIPTION
		"This object specifies current operating mode that BFD
		session is operating in."
	::= { axrBfdSessEntry 9 }

axrBfdSessDemandModeDesiredFlag OBJECT-TYPE
	SYNTAX  TruthValue
	ACCESS  read-only
	STATUS  mandatory
	DESCRIPTION
		"This object indicates that the local system's desire to use
		Demand mode. Specifically, it is set to true(1) if the local
		system wishes to use Demand mode or false(0) if not"
	::= { axrBfdSessEntry 10 }

axrBfdSessEchoFuncModeDesiredFlag OBJECT-TYPE
	SYNTAX  TruthValue
	ACCESS  read-only
	STATUS  mandatory
	DESCRIPTION
		"This object indicates that the local system's desire to use
		Echo mode. Specifically, it is set to true(1) if the local
		system wishes to use Echo mode or false(0) if not"
	::= { axrBfdSessEntry 11 }

axrBfdSessControlPlanIndepFlag OBJECT-TYPE
	SYNTAX  TruthValue
	ACCESS  read-only
	STATUS  mandatory
	DESCRIPTION
		"This object indicates that the local system's ability to
		continue to function through a disruption of the control
		plane. Specifically, it is set to true(1) if the local system
		BFD implementation is independent of the control plane.
		Otherwise, the value is set to false(0)"
	::= { axrBfdSessEntry 12 }

axrBfdSessAddrType OBJECT-TYPE
	SYNTAX  InetAddressType
	ACCESS  read-only
	STATUS  mandatory
	DESCRIPTION
		"This object specifies IP address of the interface associated
		with this BFD session.

		Only values unknown(0), ipv4(1) or ipv6(2) have to be
		supported.

		A value of unknown(0) is allowed only when the outgoing
		interface is of type point-to-point, or when the BFD session
		is not associated with a specific interface.

		If any other unsupported values are attempted in a set 
		operation, the agent MUST return an inconsistentValue error."
	::= { axrBfdSessEntry 13 }

axrBfdSessAddr OBJECT-TYPE
	SYNTAX  InetAddress
	ACCESS  read-only
	STATUS  mandatory
	DESCRIPTION
		"This object specifies IP address of the interface associated
		with this BFD session. It can also be used to enabled BFD on
		a specific interface. The value is set to zero when BFD
		session is not associated with a specific interface."
	::= { axrBfdSessEntry 14 }

axrBfdSessDesiredMinTxInterval OBJECT-TYPE
	SYNTAX  Unsigned32
	ACCESS  read-only
	STATUS  mandatory
	DESCRIPTION
		"This object specifies the minimum interval, in microseconds,
		that the local system would like to use when transmitting BFD
		Control packets."
	::= { axrBfdSessEntry 15 }

axrBfdSessDesiredMinRxInterval OBJECT-TYPE
	SYNTAX  Unsigned32
	ACCESS  read-only
	STATUS  mandatory
	DESCRIPTION
		"This object specifies the minimum interval, in microseconds,
		between received BFD Control packets the local system is
		capable of supporting."
	::= { axrBfdSessEntry 16 }

axrBfdSessDesiredMinEchoRxInterval OBJECT-TYPE
	SYNTAX  Unsigned32
	ACCESS  read-only
	STATUS  mandatory
	DESCRIPTION
		"This object specifies the minimum interval, in microseconds,
		between received BFD Echo packets that this system is capable
		of supporting."
	::= { axrBfdSessEntry 17 }

axrBfdSessDetectMult OBJECT-TYPE
	SYNTAX  Unsigned32
	ACCESS  read-only
	STATUS  mandatory
	DESCRIPTION
		"This object specifies the Detect time multiplier."
	::= { axrBfdSessEntry 18 }

axrBfdSessStorType OBJECT-TYPE
	SYNTAX  StorageType
	ACCESS  read-only
	STATUS  mandatory
	DESCRIPTION
		"This variable indicates the storage type for this object.
		Conceptual rows having the value 'permanent' need not allow
		write-access to any columnar objects in the row."
	::= { axrBfdSessEntry 19 }

axrBfdSessRowStatus OBJECT-TYPE
	SYNTAX  RowStatus
	ACCESS  read-only
	STATUS  mandatory
	DESCRIPTION
		"This variable is used to create, modify, and/or delete a row
		in this table. When a row in this table has a row in the
		active(1) state, no objects in this row can be modified
		except the bfdSessRowStatus and bfdSessStorageType."
	::= { axrBfdSessEntry 20 }

axrBfdSessAuthPresFlag OBJECT-TYPE
	SYNTAX  TruthValue
	ACCESS  read-only
	STATUS  mandatory
	DESCRIPTION
		"This object indicates that the local system's desire to use
		Authentication. Specifically, it is set to true(1) if the
		local system wishes the session to be authenticated or
		false(0) if not"
	::= { axrBfdSessEntry 21 }

axrBfdSessAuthenticationType OBJECT-TYPE
	SYNTAX  INTEGER {
		simplePassword(1),
		keyedMD5(2),
		meticulousKeyedMD5(3),
		keyedSHA1(4),
		meticulousKeyedSHA1(5)
	}
	ACCESS  read-only
	STATUS  mandatory
	DESCRIPTION
		"The Authentication Type used for this BFD session. This
		field is valid only when the Authentication Present bit is
		set"
	::= { axrBfdSessEntry 22 }

axrBfdSessPerfTable OBJECT-TYPE
	SYNTAX  SEQUENCE OF AxrBfdSessPerfEntry
	ACCESS  not-accessible
	STATUS  mandatory
	DESCRIPTION
		"This table specifies BFD Session performance counters."
	::= { axrBfdObjects 3 }

axrBfdSessPerfEntry OBJECT-TYPE
	SYNTAX  AxrBfdSessPerfEntry
	ACCESS  not-accessible
	STATUS  mandatory
	DESCRIPTION
		"An entry in this table is created by a BFD-enabled node for
		every BFD Session. bfdCounterDiscontinuityTime is used to
		indicate potential discontinuity for all counter objects in
		this table."
	INDEX  { axrBfdSessIndex }
	::= { axrBfdSessPerfTable 1 }

	AxrBfdSessPerfEntry ::= SEQUENCE {
		axrBfdSessPerfPktIn               Counter32,
		axrBfdSessPerfPktOut              Counter32,
		axrBfdSessUpTime                  TimeStamp,
		axrBfdSessPerfLastSessDownTime    TimeStamp,
		axrBfdSessPerfLastCommLostDiag    INTEGER,
		axrBfdSessPerfSessUpCount         Counter32,
		axrBfdSessPerfDiscTime            TimeStamp,
		axrBfdSessPerfPktInHC             Counter64,
		axrBfdSessPerfPktOutHC            Counter64
	}

axrBfdSessPerfPktIn OBJECT-TYPE
	SYNTAX  Counter32
	ACCESS  read-only
	STATUS  mandatory
	DESCRIPTION
		"The total number of BFD messages received for this BFD
		session."
	::= { axrBfdSessPerfEntry 1 }

axrBfdSessPerfPktOut OBJECT-TYPE
	SYNTAX  Counter32
	ACCESS  read-only
	STATUS  mandatory
	DESCRIPTION
		"The total number of BFD messages sent for this BFD
		session."
	::= { axrBfdSessPerfEntry 2 }

axrBfdSessUpTime OBJECT-TYPE
	SYNTAX  TimeStamp
	ACCESS  read-only
	STATUS  mandatory
	DESCRIPTION
		"The value of sysUpTime on the most recent occasion at which
		the session came up. If no such up event exists this object
		contains a zero value."
	::= { axrBfdSessPerfEntry 3 }

axrBfdSessPerfLastSessDownTime OBJECT-TYPE
	SYNTAX  TimeStamp
	ACCESS  read-only
	STATUS  mandatory
	DESCRIPTION
		"The value of sysUpTime on the most recent occasion at which
		the last time communication was lost with the neighbor. If
		no such down event exist this object contains a zero value."
	::= { axrBfdSessPerfEntry 4 }

axrBfdSessPerfLastCommLostDiag OBJECT-TYPE
	SYNTAX  INTEGER
	ACCESS  read-only
	STATUS  mandatory
	DESCRIPTION
		"The BFD diag code for the last time communication was lost
		with the neighbor. If no such down event exists this object
		contains a zero value."
	::= { axrBfdSessPerfEntry 5 }

axrBfdSessPerfSessUpCount OBJECT-TYPE
	SYNTAX  Counter32
	ACCESS  read-only
	STATUS  mandatory
	DESCRIPTION
		"The number of times this session has gone into the Up state
		since the router last rebooted."
	::= { axrBfdSessPerfEntry 6 }

axrBfdSessPerfDiscTime OBJECT-TYPE
	SYNTAX  TimeStamp
	ACCESS  read-only
	STATUS  mandatory
	DESCRIPTION
		"The value of sysUpTime on the most recent occasion at which
		any one or more of the session counters suffered a
		discontinuity.

		The relevant counters are the specific instances associated
		with this BFD session of any Counter32 object contained in
		the BfdSessPerfTable. If no such discontinuities have
		occurred since the last re-initialization of the local
		management subsystem, then this object contains a zero 
		value."
	::= { axrBfdSessPerfEntry 7 }

axrBfdSessPerfPktInHC OBJECT-TYPE
	SYNTAX  Counter64
	ACCESS  read-only
	STATUS  mandatory
	DESCRIPTION
		"This value represents the total number of BFD messages
		received for this BFD session. It MUST be equal to the least
		significant 32 bits of bfdSessPerfPktIn if bfdSessPerfPktInHC
		is supported according to the rules spelled out in RFC2863."
	::= { axrBfdSessPerfEntry 8 }

axrBfdSessPerfPktOutHC OBJECT-TYPE
	SYNTAX  Counter64
	ACCESS  read-only
	STATUS  mandatory
	DESCRIPTION
		"This value represents the total number of total number of
		BFD messages transmitted for this BFD session. It MUST be
		equal to the least significant 32 bits of bfdSessPerfPktIn
		if bfdSessPerfPktOutHC is supported according to the rules
		spelled out in RFC2863."
	::= { axrBfdSessPerfEntry 9 }

axrBfdSessMapTable OBJECT-TYPE
	SYNTAX  SEQUENCE OF AxrBfdSessMapEntry
	ACCESS  not-accessible
	STATUS  mandatory
	DESCRIPTION
		"The BFD Session Mapping Table maps the complex indexing of
		the BFD sessions to the flat BFDIndex used in the
		BfdSessionTable.

		Implementors need to be aware that if the value of the
		bfdSessAddr (an OID) has more  that 111 sub-identifiers,
		then OIDs of column instances in this table will have more
		than 128 sub-identifiers and cannot be accessed using SNMPv1,
		SNMPv2c, or SNMPv3."
	::= { axrBfdObjects 4 }

axrBfdSessMapEntry OBJECT-TYPE
	SYNTAX  AxrBfdSessMapEntry
	ACCESS  not-accessible
	STATUS  mandatory
	DESCRIPTION
		"The BFD Session Entry describes BFD session that is mapped
		to this index.

		Implementors need to be aware that if the value of the
		mplsInSegmentMapLabelPtrIndex (an OID) has more that 111
		sub-identifiers, then OIDs of column instances in this table
		will have more than 128 sub-identifiers and cannot be
		accessed using SNMPv1, SNMPv2c, or SNMPv3."
	INDEX  { axrBfdSessApplicationId,
			axrBfdSessDiscriminator,
			axrBfdSessAddrType,
			axrBfdSessAddr }
	::= { axrBfdSessMapTable 1 }

	AxrBfdSessMapEntry ::=
		SEQUENCE {
			axrBfdSessMapBfdIndex  Unsigned32
		}

axrBfdSessMapBfdIndex OBJECT-TYPE
	SYNTAX  Unsigned32
	ACCESS  read-only
	STATUS  mandatory
	DESCRIPTION
		"This object specifies the BfdIndex referred to by the
		indexes of this row. In essence, a mapping is provided
		between these indexes and the BfdSessTable."
	::= { axrBfdSessMapEntry 1 }

-- ax7800rRouter group

ax7800rModelType OBJECT-TYPE
	SYNTAX  INTEGER {
		other(1),
                ax7804r-ac(100),
                ax7804r-dc(101),
                ax7808r-ac(102),
                ax7808r-dc(103),
                ax7816r-dc(104),
                ax7816r-ac(105)
	      }
	ACCESS  read-only
	STATUS  mandatory
	DESCRIPTION
		"Model type of this system."
	::= { ax7800rRouter 1 }

--ax7800rSoftware OBJECT-TYPE
--	SYNTAX  INTEGER
--	ACCESS  not-accessible
--	STATUS  mandatory
--	DESCRIPTION
--		"Software information of this system."
--	::= { ax7800rRouter 2 }

ax7800rSoftwareName OBJECT-TYPE
	SYNTAX  DisplayString (SIZE (0..16))
	ACCESS  read-only
	STATUS  mandatory
	DESCRIPTION
		"Software name of this system."
	::= { ax7800rSoftware 1 }

ax7800rSoftwareAbbreviation OBJECT-TYPE
	SYNTAX  DisplayString (SIZE (0..16))
	ACCESS  read-only
	STATUS  mandatory
	DESCRIPTION
		"System software abbreviation."
	::= { ax7800rSoftware 2 }

ax7800rSoftwareVersion OBJECT-TYPE
	SYNTAX  DisplayString (SIZE (0..16))
	ACCESS  read-only
	STATUS  mandatory
	DESCRIPTION
		"System software version."
	::= { ax7800rSoftware 3 }

--ax7800rSystemMsg OBJECT-TYPE
--	SYNTAX  INTEGER
--	ACCESS  not-accessible
--	STATUS  mandatory
--	DESCRIPTION
--		"System messege group."
--	::= { ax7800rRouter 3 }

ax7800rSystemMsgText OBJECT-TYPE
	SYNTAX  DisplayString (SIZE (0..256))
	ACCESS  read-only
	STATUS  mandatory
	DESCRIPTION
		"The text of the system log message.For information about this code,
		see:  Operator's Manual. "
	::= { ax7800rSystemMsg 1 }

ax7800rSystemMsgType OBJECT-TYPE
	SYNTAX  OCTET STRING (SIZE (1))
	ACCESS  read-only
	STATUS  mandatory
	DESCRIPTION
		"The event type. For information about this code, see:  Operator's Manual."
	::= { ax7800rSystemMsg 2 }

ax7800rSystemMsgTimeStamp OBJECT-TYPE
	SYNTAX  DisplayString (SIZE (14))
	ACCESS  read-only
	STATUS  mandatory
	DESCRIPTION
		"The time that event occured. And that is expressed as type of
		MM/DD hh:mm:ss
			MM:month(01-12)
			DD:day(01-31)
			hh:hour(00-23)
			mm:minute(00-59)
			ss:second(00-59)
		Insert space between DD and hh."
	::= { ax7800rSystemMsg 3 }

ax7800rSystemMsgLevel OBJECT-TYPE
	SYNTAX  OCTET STRING (SIZE (1))
	ACCESS  read-only
	STATUS  mandatory
	DESCRIPTION
		"The newest system message log level.For information about this code,
		see:  Operator's Manual. "
	::= { ax7800rSystemMsg 4 }

ax7800rSystemMsgEventPoint OBJECT-TYPE
	SYNTAX  DisplayString (SIZE (0..8))
	ACCESS  read-only
	STATUS  mandatory
	DESCRIPTION
		"The code of part that system message error occured. For information
		about this code,see:  Operator's Manual. "
	::= { ax7800rSystemMsg 5 }

ax7800rSystemMsgEventInterfaceID OBJECT-TYPE
	SYNTAX  DisplayString (SIZE (0..40))
	ACCESS  read-only
	STATUS  mandatory
	DESCRIPTION
		"Interface identification of system messages. For information
		about this code,see:  Operator's Manual."
	::= { ax7800rSystemMsg 6 }

ax7800rSystemMsgEventCode OBJECT-TYPE
	SYNTAX  OCTET STRING (SIZE (4))
	ACCESS  read-only
	STATUS  mandatory
	DESCRIPTION
		"Event kind code of system messages. For information about this code,
		see:  Operator's Manual. "
	::= { ax7800rSystemMsg 7 }

ax7800rSystemMsgAdditionalCode OBJECT-TYPE
	SYNTAX  OCTET STRING (SIZE (6))
	ACCESS  read-only
	STATUS  mandatory
	DESCRIPTION
		"Additional code of system messages. For information about this code,
		see:  Operator's Manual. "
	::= { ax7800rSystemMsg 8 }

--ax7800rSnmpAgent OBJECT-TYPE
--	SYNTAX  INTEGER
--	ACCESS  not-accessible
--	STATUS  mandatory
--	DESCRIPTION
--		"Related information of SNMP agent."
--	::= { ax7800rRouter 4 }

ax7800rSnmpSendReceiveSize OBJECT-TYPE
	SYNTAX  INTEGER
	ACCESS  read-only
	STATUS  mandatory
	DESCRIPTION
		"SNMP packet data size in Manager-to-Agent communication. The value is
		displayed in bytes."
	::= { ax7800rSnmpAgent 1 }

ax7800rSnmpReceiveDelay OBJECT-TYPE
	SYNTAX  INTEGER
	ACCESS  read-only
	STATUS  mandatory
	DESCRIPTION
		"A recommendable interval to receive packets from Manager.The value is
		displayed in milliseconds."
	::= { ax7800rSnmpAgent 2 }

ax7800rSnmpContinuousSend OBJECT-TYPE
	SYNTAX  INTEGER
	ACCESS  read-only
	STATUS  mandatory
	DESCRIPTION
		"Number of times that is recommendable continuous transmission
		packets."
	::= { ax7800rSnmpAgent 3 }

ax7800rSnmpObjectMaxNumber OBJECT-TYPE
	SYNTAX  INTEGER
	ACCESS  read-only
	STATUS  mandatory
	DESCRIPTION
		"Max number of objects that contain SNMP packet."
	::= { ax7800rSnmpAgent 4 }

--ax7800rSerialNumber OBJECT-TYPE
--        SYNTAX  DisplayString (SIZE (0..30))
--	ACCESS  read-only
--        STATUS  mandatory
--        DESCRIPTION
--                "Management information (SerialNumber) of RMP2-CARD."
--        ::= { ax7800rRouter 5 }

ax7800rLicenseNumber OBJECT-TYPE
        SYNTAX  INTEGER
	ACCESS  read-only
        STATUS  mandatory
        DESCRIPTION
                "The number of the configured license serial numbers."
        ::= { ax7800rLicense 1 }

ax7800rLicenseTable OBJECT-TYPE
	SYNTAX  SEQUENCE OF Ax7800rLicenseTableEntry
	ACCESS  not-accessible
	STATUS  mandatory
	DESCRIPTION
		"The table containing the license information."
	::= { ax7800rLicense 2 }

ax7800rLicenseEntry OBJECT-TYPE
	SYNTAX  Ax7800rLicenseTableEntry
	ACCESS  not-accessible
	STATUS  mandatory
	DESCRIPTION
		"The entry of license information."
	INDEX   { ax7800rLicenseIndex }
	::= { ax7800rLicenseTable 1 }

	Ax7800rLicenseTableEntry ::=
		SEQUENCE {
		  ax7800rLicenseIndex
			INTEGER,
		  ax7800rLicenseSerialNumber
			DisplayString,
		  ax7800rLicenseOptionNumber
			INTEGER
                }

ax7800rLicenseIndex OBJECT-TYPE
	SYNTAX  INTEGER
	ACCESS  not-accessible
	STATUS  mandatory
	DESCRIPTION
		"The unique index number given for each serial number. The number is from 1 to ax7800rLicenseNumber."
	::= { ax7800rLicenseEntry 1 }

ax7800rLicenseSerialNumber OBJECT-TYPE
	SYNTAX  DisplayString 
	ACCESS  read-only
	STATUS  mandatory
	DESCRIPTION
		"The serial number."
	::= { ax7800rLicenseEntry 2 }

ax7800rLicenseOptionNumber OBJECT-TYPE
	SYNTAX  INTEGER 
	ACCESS  read-only
	STATUS  mandatory
	DESCRIPTION
		"The number of option licenses associated with the serial number."
	::= { ax7800rLicenseEntry 3 }

ax7800rLicenseOptionTable OBJECT-TYPE
	SYNTAX  SEQUENCE OF Ax7800rLicenseOptionTableEntry
	ACCESS  not-accessible
	STATUS  mandatory
	DESCRIPTION
		"The table containing option licenses information associated with the serial number."
	::= { ax7800rLicense 3 }

ax7800rLicenseOptionEntry OBJECT-TYPE
	SYNTAX  Ax7800rLicenseOptionTableEntry
	ACCESS  not-accessible
	STATUS  mandatory
	DESCRIPTION
		"The entry of the option license information associated with the serial number."
	INDEX   { ax7800rLicenseOptionIndex,ax7800rLicenseOptionNumberIndex }
	::= { ax7800rLicenseOptionTable 1 }

	Ax7800rLicenseOptionTableEntry ::=
		SEQUENCE {
		  ax7800rLicenseOptionIndex
			INTEGER,
		  ax7800rLicenseOptionNumberIndex
			INTEGER,
		  ax7800rLicenseOptionSoftwareName
			DisplayString,
		  ax7800rLicenseOptionSoftwareAbbreviation
			DisplayString
                }

ax7800rLicenseOptionIndex OBJECT-TYPE
	SYNTAX  INTEGER
	ACCESS  not-accessible
	STATUS  mandatory
	DESCRIPTION
		"The unique index number given for each serial number. The same number as ax7800rLicenseIndex."
	::= { ax7800rLicenseOptionEntry 1 }

ax7800rLicenseOptionNumberIndex OBJECT-TYPE
	SYNTAX  INTEGER
	ACCESS  not-accessible
	STATUS  mandatory
	DESCRIPTION
		"The unique index number of option licenses information which is given for each serial number. The number is from 1 to ax7800rLicenseNumber."
	::= { ax7800rLicenseOptionEntry 2 }

ax7800rLicenseOptionSoftwareName OBJECT-TYPE
	SYNTAX  DisplayString 
	ACCESS  read-only
	STATUS  mandatory
	DESCRIPTION
		"The software model name of the option license information associated with the serial number."
	::= { ax7800rLicenseOptionEntry 3 }

ax7800rLicenseOptionSoftwareAbbreviation OBJECT-TYPE
	SYNTAX  DisplayString 
	ACCESS  read-only
	STATUS  mandatory
	DESCRIPTION
		"The software abbreviated name of the option license information associated with the serial number. "
	::= { ax7800rLicenseOptionEntry 4 }

-- ax7800rDevice group

ax7800rChassisMaxNumber OBJECT-TYPE
	SYNTAX  INTEGER
	ACCESS  read-only
	STATUS  mandatory
	DESCRIPTION
		"Max number of cluster chassis that can connect to this router."
	::= { ax7800rChassis 1 }


ax7800rChassisTable OBJECT-TYPE
	SYNTAX  SEQUENCE OF Ax7800rChassisTableEntry
	ACCESS  not-accessible
	STATUS  mandatory
	DESCRIPTION
		"A table containing chassis information."
	::= { ax7800rChassis 2 }

ax7800rChassisEntry OBJECT-TYPE
	SYNTAX  Ax7800rChassisTableEntry
	ACCESS  not-accessible
	STATUS  mandatory
	DESCRIPTION
		"An entry containing specific chassis."
	INDEX   { ax7800rChassisIndex }
	::= { ax7800rChassisTable 1 }

	Ax7800rChassisTableEntry ::=
		SEQUENCE {
		  ax7800rChassisIndex
			INTEGER,
		  ax7800rChassisType
			INTEGER,
		  ax7800rChassisStatus
			INTEGER,
		  ax7800rBcuBoardDuplexMode
			INTEGER,
		  ax7800rPowerUnitNumber
			INTEGER,
		  ax7800rFanNumber
			INTEGER,
		  ax7800rCifNumber
			INTEGER,
		  ax7800rBcuBoardNumber
			INTEGER,
		  ax7800rPruBoardNumber
			INTEGER,
		  ax7800rNifBoardNumber
			INTEGER
		}

ax7800rChassisIndex OBJECT-TYPE
	SYNTAX  INTEGER
	ACCESS  not-accessible
	STATUS  mandatory
	DESCRIPTION
		"A number to specify ax7800rChassisEntry."
	::= { ax7800rChassisEntry 1 }

ax7800rChassisType OBJECT-TYPE
	SYNTAX  INTEGER {
		other(1),
                ax7804r-ac(100),
                ax7804r-dc(101),
                ax7808r-ac(102),
                ax7808r-dc(103),
                ax7816r-dc(104),
                ax7816r-ac(105)
	      }
	ACCESS  read-only
	STATUS  mandatory
	DESCRIPTION
		"Chassis type of this system."
	::= { ax7800rChassisEntry 2 }

ax7800rChassisStatus OBJECT-TYPE
	SYNTAX  INTEGER {
		up(2)
	      }
	ACCESS  read-only
	STATUS  mandatory
	DESCRIPTION
		"Current status of this chassis."
	::= { ax7800rChassisEntry 3 }

ax7800rBcuBoardDuplexMode OBJECT-TYPE
	SYNTAX  INTEGER {
		rm-Simplex-model(1),
		rm-Duplex-model(2)
	      }
	ACCESS  read-only
	STATUS  mandatory
	DESCRIPTION
		"Duplex mode of BCU Board."
	::= { ax7800rChassisEntry 4 }

ax7800rPowerUnitNumber OBJECT-TYPE
	SYNTAX  INTEGER
	ACCESS  read-only
	STATUS  mandatory
	DESCRIPTION
		"Number of maximum power switches that this router can connect its."
	::= { ax7800rChassisEntry 5 }

ax7800rFanNumber OBJECT-TYPE
	SYNTAX  INTEGER
	ACCESS  read-only
	STATUS  mandatory
	DESCRIPTION
		"The maximum number of fans that can connect to this chassis."
	::= { ax7800rChassisEntry 6 }

ax7800rCifNumber OBJECT-TYPE
	SYNTAX  INTEGER
	ACCESS  read-only
	STATUS  mandatory
	DESCRIPTION
		"Number of cluster interfaces that can connect to this chassis."
	::= { ax7800rChassisEntry 7 }

ax7800rBcuBoardNumber OBJECT-TYPE
	SYNTAX  INTEGER
	ACCESS  read-only
	STATUS  mandatory
	DESCRIPTION
		"Number of BCU boards that can connect to
		this chassis."
	::= { ax7800rChassisEntry 8 }

ax7800rPruBoardNumber OBJECT-TYPE
	SYNTAX  INTEGER
	ACCESS  read-only
	STATUS  mandatory
	DESCRIPTION
		"Number of PRU boards that can connect to
		this chassis."
	::= { ax7800rChassisEntry 9 }

ax7800rNifBoardNumber OBJECT-TYPE
	SYNTAX  INTEGER
	ACCESS  read-only
	STATUS  mandatory
	DESCRIPTION
		"Number of NIF(Network InterFace) boards that can connect to
		this chassis."
	::= { ax7800rChassisEntry 10 }

ax7800rPowerUnitTable OBJECT-TYPE
	SYNTAX  SEQUENCE OF Ax7800rPowerUnitTableEntry
	ACCESS  not-accessible
	STATUS  mandatory
	DESCRIPTION
		"A table containing power unit information."
	::= { ax7800rChassis 3 }

ax7800rPowerUnitEntry OBJECT-TYPE
	SYNTAX  Ax7800rPowerUnitTableEntry
	ACCESS  not-accessible
	STATUS  mandatory
	DESCRIPTION
		"An entry containing power unit information."
	INDEX   { ax7800rChassisIndex,ax7800rPowerUnitIndex }
	::= { ax7800rPowerUnitTable 1 }

	Ax7800rPowerUnitTableEntry ::=
		SEQUENCE {
		  ax7800rPowerUnitIndex
			INTEGER,
		  ax7800rPowerConnectStatus
			INTEGER,
		  ax7800rPowerSupplyStatus
			INTEGER
		}

ax7800rPowerUnitIndex OBJECT-TYPE
	SYNTAX  INTEGER
	ACCESS  not-accessible
	STATUS  mandatory
	DESCRIPTION
		"A number to position of the power units.The value from 1
		to ax7800rPowerUnitNumber."
	::= { ax7800rPowerUnitEntry 1 }
ax7800rPowerConnectStatus OBJECT-TYPE
	SYNTAX  INTEGER {
		connected(2),
		disconnected(32)
	      }
	ACCESS  read-only
	STATUS  mandatory
	DESCRIPTION
		"The current connection status of the power unit."
	::= { ax7800rPowerUnitEntry 2 }

ax7800rPowerSupplyStatus OBJECT-TYPE
	SYNTAX  INTEGER {
		ok(2),
		fault(4)
	      }
	ACCESS  read-only
	STATUS  mandatory
	DESCRIPTION
		"Status of power supply. The value is -1 when Power Supply is disconnected."
	::= { ax7800rPowerUnitEntry 3 }


ax7800rFanTable OBJECT-TYPE
	SYNTAX  SEQUENCE OF Ax7800rFanTableEntry
	ACCESS  not-accessible
	STATUS  mandatory
	DESCRIPTION
		"A table containing fan information."
	::= { ax7800rChassis 4 }

ax7800rFanEntry OBJECT-TYPE
	SYNTAX  Ax7800rFanTableEntry
	ACCESS  not-accessible
	STATUS  mandatory
	DESCRIPTION
		"This entry containing information for a fan."
	INDEX   { ax7800rChassisIndex,ax7800rFanIndex }
	::= { ax7800rFanTable 1 }

	Ax7800rFanTableEntry ::=
		SEQUENCE {
		  ax7800rFanIndex
			INTEGER,
		  ax7800rFanStatus
			INTEGER
		}

ax7800rFanIndex OBJECT-TYPE
	SYNTAX  INTEGER
	ACCESS  not-accessible
	STATUS  mandatory
	DESCRIPTION
		"Index to indicate position of fans."
	::= { ax7800rFanEntry 1 }

ax7800rFanStatus OBJECT-TYPE
	SYNTAX  INTEGER {
		ok(2),
		under-highspeed-rotation(3),
		fault(4)
	      }
	ACCESS  read-only
	STATUS  mandatory
	DESCRIPTION
		"Status of fans."
	::= { ax7800rFanEntry 2 }

ax7800rBcuBoardTable OBJECT-TYPE
	SYNTAX  SEQUENCE OF Ax7800rBcuBoardTableEntry
	ACCESS  not-accessible
	STATUS  mandatory
	DESCRIPTION
		"A table containing BCU boards information."
	::= { ax7800rBcuBoard 1 }

ax7800rBcuBoardEntry OBJECT-TYPE
	SYNTAX  Ax7800rBcuBoardTableEntry
	ACCESS  not-accessible
	STATUS  mandatory
	DESCRIPTION
		"An entry containing BCU boards about specific
		chassis."
	INDEX   { ax7800rChassisIndex,ax7800rBcuBoardIndex }
	::= { ax7800rBcuBoardTable 1 }

	Ax7800rBcuBoardTableEntry ::=
		SEQUENCE {
		  ax7800rBcuBoardIndex
			INTEGER,
		  ax7800rBcuIoBoardType
			INTEGER,
		  ax7800rBcuCpuBoardType
			INTEGER,
		  ax7800rBcuOperStatus
			INTEGER,
		  ax7800rBcuOperModeStatus
			INTEGER,
		  ax7800rBcuActiveLedStatus
			INTEGER,
		  ax7800rBcuReadyLedStatus
			INTEGER,
		  ax7800rBcuAlarmLedStatus
			INTEGER,
		  ax7800rBcuErrorLedStatus
			INTEGER,
		  ax7800rBcuEmaLedStatus
			INTEGER,
		  ax7800rBcuRmEthernetStatus
			INTEGER,
		  ax7800rBcuAtaCardNumber
			INTEGER,
		  ax7800rBcuAtaBootDev
			INTEGER,
		  ax7800rBcuBoardName
			DisplayString,
		  ax7800rBcuBoardAbbreviation
			DisplayString,
		  ax7800rBcuIoBoardProductCode
			INTEGER,
		  ax7800rBcuCpuBoardProductCode
			INTEGER,
		  ax7800rBcuRmCpuName
			DisplayString,
		  ax7800rBcuRmCpuClock
			INTEGER,
		  ax7800rBcuRmMemoryTotalSize
			INTEGER,
		  ax7800rBcuRmMemoryUsedSize
			INTEGER,
		  ax7800rBcuRmMemoryFreeSize
			INTEGER,
		  ax7800rBcuRmRomVersion
			DisplayString,
		  ax7800rBcuRmCpuLoad1m
			INTEGER,
		  ax7800rBcuTemperatureStatusNumber
			INTEGER,
		  ax7800rBcuCpOperStatus
			INTEGER,
		  ax7800rBcuCpCpuName
			DisplayString,
		  ax7800rBcuCpCpuClock
			INTEGER,
		  ax7800rBcuCpMemoryTotalSize
			INTEGER,
		  ax7800rBcuCpCpuLoad1m 
			INTEGER,
		  ax7800rBcuSerialNumber 
			DisplayString,
		  ax7800rBcuVoltage150 
			INTEGER,
		  ax7800rBcuVoltage180 
			INTEGER,
		  ax7800rBcuVoltage250 
			INTEGER,
		  ax7800rBcuVoltage330 
			INTEGER,
		  ax7800rBcuVoltage500 
			INTEGER,
		  ax7800rBcuVoltage130 
			INTEGER,
		  ax7800rBcuPbmVoltage105 
			INTEGER,
		  ax7800rBcuPbmVoltage120 
			INTEGER,
		  ax7800rBcuPbmCpuCoreVoltage 
			INTEGER,
		  ax7800rBcuPbmVoltage150 
			INTEGER,
		  ax7800rBcuPbmVoltage180 
			INTEGER
		}

ax7800rBcuBoardIndex OBJECT-TYPE
	SYNTAX  INTEGER
	ACCESS  not-accessible
	STATUS  mandatory
	DESCRIPTION
		"Position information of the BCU slot. The value is from 1 to
		ax7800rBcuBoardCardNumber."
	::= { ax7800rBcuBoardEntry  1 }

ax7800rBcuIoBoardType OBJECT-TYPE
	SYNTAX  INTEGER {
		disconnected(-1),
		ax7804r-BCU-RH8MS-IO(8),
                ax7804r-BCU-RH8MS2-IO(9),
                ax7804r-BCU-RM1GS3-IO(10),
                ax7808r-BCU-RM8MS-IO(264),
                ax7808r-BCU-RM8MS2-IO(265),
                ax7808r-BCU-RM1GS3-IO(266),
                ax7816r-BCU-RL8MS-IO(520),
                ax7816r-BCU-RL8MS2-IO(521),
                ax7816r-BCU-RL1GS3-IO(522)
                }
	ACCESS  read-only
	STATUS  mandatory
	DESCRIPTION
		"BCU IO board ID.
		The value is -1 when BCU board is disconnected."
	::= { ax7800rBcuBoardEntry  2 }

ax7800rBcuCpuBoardType OBJECT-TYPE
	SYNTAX  INTEGER {
		disconnected(-1),
		bcu-bcu2-CPU(768),
                bcu3-CPU(1280)
		}
	ACCESS  read-only
	STATUS  mandatory
	DESCRIPTION
		"The value of BCU board ID.
		The value is -1 when BCU board is disconnected."
	::= { ax7800rBcuBoardEntry 3 }

ax7800rBcuOperStatus OBJECT-TYPE
	SYNTAX  INTEGER {
		other(1),
		up(2),
		down(4),
		closed(5),
		disconnect(32)
	      }
	ACCESS  read-only
	STATUS  mandatory
	DESCRIPTION
		"Status of LED on BCU board. The value is 32 when BCU board is
		disconnected."
	::= { ax7800rBcuBoardEntry 4 }

ax7800rBcuOperModeStatus OBJECT-TYPE
	SYNTAX  INTEGER {
		disconnected(-1),
		other(1),
		active(2),
		standby(3),
		do-not-match-with-configure-mode(4),
		do-not-match-with-software-version(5),
		down(6),
		mentenance(7)
	      }
	ACCESS  read-only
	STATUS  mandatory
	DESCRIPTION
		"Operate status on BCU board. The value is -1 when BCU board is
		disconnected."
	::= { ax7800rBcuBoardEntry 5 }

ax7800rBcuActiveLedStatus OBJECT-TYPE
	SYNTAX  INTEGER {
		disconnected(-1),
		green-light-on(2),
		light-off(6)
	      }
	ACCESS  read-only
	STATUS  mandatory
	DESCRIPTION
		"Status of ACTIVE LED on BCU board. The value is -1 when BCU board is
		disconnected or LED status is unknown."
	::= { ax7800rBcuBoardEntry 6 }

ax7800rBcuReadyLedStatus OBJECT-TYPE
	SYNTAX  INTEGER {
		disconnected(-1),
		green-light-on(2),
		light-off(6)
	      }
	ACCESS  read-only
	STATUS  mandatory
	DESCRIPTION
		"Status of READY LED on BCU board. The value is -1 when BCU board is
		disconnected or LED status is unknown."
	::= { ax7800rBcuBoardEntry 7 }

ax7800rBcuAlarmLedStatus OBJECT-TYPE
	SYNTAX  INTEGER {
		disconnected(-1),
		red-light-on(4),
		light-off(6)
	      }
	ACCESS  read-only
	STATUS  mandatory
	DESCRIPTION
		"Status of ALARM LED on BCU board. The value is -1 when BCU board is
		disconnected or LED status is unknown."
	::= { ax7800rBcuBoardEntry 8 }

ax7800rBcuErrorLedStatus OBJECT-TYPE
	SYNTAX  INTEGER {
		disconnected(-1),
		yellow-light-on(5),
		light-off(6)
	      }
	ACCESS  read-only
	STATUS  mandatory
	DESCRIPTION
		"Status of LED ERROR on BCU board. The value is -1 when BCU board is
		disconnected or LED status is unknown."
	::= { ax7800rBcuBoardEntry 9 }

ax7800rBcuEmaLedStatus OBJECT-TYPE
	SYNTAX  INTEGER {
		disconnected(-1),
		yellow-light-on(5),
		light-off(6)
	      }
	ACCESS  read-only
	STATUS  mandatory
	DESCRIPTION
		"Status of LED EMA READY on BCU board. The value is -1 when BCU board is
		disconnected or LED status is unknown."
	::= { ax7800rBcuBoardEntry 10 }

ax7800rBcuRmEthernetStatus OBJECT-TYPE
	SYNTAX  INTEGER {
		disconnected(-1),
		other(1),
		active(2),
		down(4),
		nothing-configuration-or-locked(6),
		maintenance(7),
		test(9),
		unused(10),
		standby(12)
	      }
	ACCESS  read-only
	STATUS  mandatory
	DESCRIPTION
		"Operaion status on BCU ethernet. The value is -1 when BCU board is
		disconnected."
	::= { ax7800rBcuBoardEntry 12 }

ax7800rBcuAtaCardNumber OBJECT-TYPE
	SYNTAX  INTEGER
	ACCESS  read-only
	STATUS  mandatory
	DESCRIPTION
		"Number of slots in ATA card. The value is 0 when BCU board is
		disconnected."
	::= { ax7800rBcuBoardEntry 13 }

ax7800rBcuAtaBootDev OBJECT-TYPE
	SYNTAX  INTEGER {
		disconnected(-1),
		ata-slot0(1),
		ata-slot1(2)
	      }
	ACCESS  read-only
	STATUS  mandatory
	DESCRIPTION
		"The value of ATA slots number when router booted. The value is -1
		when BCU board is disconnected."
	::= { ax7800rBcuBoardEntry 14 }

ax7800rBcuBoardName OBJECT-TYPE
	SYNTAX  DisplayString (SIZE (0..16))
	ACCESS  read-only
	STATUS  mandatory
	DESCRIPTION
		"The product name of RM-IO board.When BCU board is disconnected,
		this will be an OCTET STRING of zero length."
	::= { ax7800rBcuBoardEntry 15 }

ax7800rBcuBoardAbbreviation OBJECT-TYPE
	SYNTAX  DisplayString (SIZE (0..16))
	ACCESS  read-only
	STATUS  mandatory
	DESCRIPTION
		"The abbreviation name of RM-IO board.When BCU board is disconnected,
		this will be an OCTET STRING of zero length."
	::= { ax7800rBcuBoardEntry 16 }

ax7800rBcuIoBoardProductCode OBJECT-TYPE
	SYNTAX  INTEGER
	ACCESS  read-only
	STATUS  mandatory
	DESCRIPTION
		"The manufacturing management number of BCU-IO board.The value is
		-1 when BCU board is disconnected."
	::= { ax7800rBcuBoardEntry 17 }

ax7800rBcuCpuBoardProductCode OBJECT-TYPE
	SYNTAX  INTEGER
	ACCESS  read-only
	STATUS  mandatory
	DESCRIPTION
		"The manufacturing management number of BCU-CPU board.The value is
		-1 when BCU board is disconnected."
	::= { ax7800rBcuBoardEntry 18 }

ax7800rBcuRmCpuName OBJECT-TYPE
	SYNTAX  DisplayString (SIZE (0..16))
	ACCESS  read-only
	STATUS  mandatory
	DESCRIPTION
		"The CPU name of board that load BCU.When BCU board is disconnected,
		this will be an OCTET STRING of zero length."
	::= { ax7800rBcuBoardEntry 19 }

ax7800rBcuRmCpuClock OBJECT-TYPE
	SYNTAX  INTEGER
	ACCESS  read-only
	STATUS  mandatory
	DESCRIPTION
		"The CPU clock of board that load BCU. The value is displayed in
		mega-hertz(MHz). The value is -1 when BCU board is disconnected."
	::= { ax7800rBcuBoardEntry 20 }

ax7800rBcuRmMemoryTotalSize OBJECT-TYPE
	SYNTAX  INTEGER
	ACCESS  read-only
	STATUS  mandatory
	DESCRIPTION
		"Total memory sizes of BCU. The value is displayed in kilobyte(KB).
		The value is -1 when BCU board is disconnected."
	::= { ax7800rBcuBoardEntry 21 }

ax7800rBcuRmMemoryUsedSize OBJECT-TYPE
	SYNTAX  INTEGER
	ACCESS  read-only
	STATUS  mandatory
	DESCRIPTION
		"Using memory sizes of BCU. The value is displayed in kilobyte(KB).
		The value is -1 when BCU board is disconnected."
	::= { ax7800rBcuBoardEntry 22 }

ax7800rBcuRmMemoryFreeSize OBJECT-TYPE
	SYNTAX  INTEGER
	ACCESS  read-only
	STATUS  mandatory
	DESCRIPTION
		"Free memory sizes of BCU. The value is displayed in kilobyte(KB).
		The value is -1 when BCU board is disconnected."
	::= { ax7800rBcuBoardEntry 23 }


ax7800rBcuRmRomVersion OBJECT-TYPE
	SYNTAX  DisplayString (SIZE (0..128))
	ACCESS  read-only
	STATUS  mandatory
	DESCRIPTION
		"The version of Rom on BCU board. When BCU board is disconnected,
		this will be an OCTET STRING of zero length."
	::= { ax7800rBcuBoardEntry 24 }

ax7800rBcuRmCpuLoad1m OBJECT-TYPE
	SYNTAX  INTEGER
	ACCESS  read-only
	STATUS  mandatory
	DESCRIPTION
		"The average, over the last minute, of the percentage of time that
		this processor was utilized to processing and transfer data.
		The value is 0 when BCU board is standby or disconnected."
	::= { ax7800rBcuBoardEntry 25 }

ax7800rBcuTemperatureStatusNumber OBJECT-TYPE
	SYNTAX  INTEGER
	ACCESS  read-only
	STATUS  mandatory
	DESCRIPTION
		"The maximum number of ax7800rTemperatureStatus that can be measurement at this chassis.
		The value is 0 when BCU board doesn't support the temperature measurement function or BCU board is disconnected"
	::= { ax7800rBcuBoardEntry 26 }

ax7800rBcuCpOperStatus OBJECT-TYPE
	SYNTAX  INTEGER {
		other(1),
		active(2),
		initialization(3),
		down(4),
		disconnect(32)
	      }
	ACCESS  read-only
	STATUS  mandatory
	DESCRIPTION
		"The state of CP. other(1),Under Operation(2),Initializing(3),Fault(4),Standby system BCU not implemented(32)"
	::= { ax7800rBcuBoardEntry 27 }

ax7800rBcuCpCpuName OBJECT-TYPE
	SYNTAX  DisplayString (SIZE (0..16))
	ACCESS  read-only
	STATUS  mandatory
	DESCRIPTION
		"The character sequence of the CPU name whose number is a maximum of 16.(ex :MIPS RM5261).Return length 0 if standby system BCR not implemented. "
	::= { ax7800rBcuBoardEntry 28 }

ax7800rBcuCpCpuClock OBJECT-TYPE
	SYNTAX  INTEGER
	ACCESS  read-only
	STATUS  mandatory
	DESCRIPTION
		"The numerical value of a CP CPU clock. unit of measure: MHz (ex:250), it is -1 if standby system BCU not implemented."
	::= { ax7800rBcuBoardEntry 29 }
	
ax7800rBcuCpMemoryTotalSize OBJECT-TYPE
	SYNTAX  INTEGER
	ACCESS  read-only
	STATUS  mandatory
	DESCRIPTION
		"The numerical value of the main memory size of CP. Unit of measure : KByte,(ex : 32768)"
	::= { ax7800rBcuBoardEntry 30 }
	
ax7800rBcuCpCpuLoad1m OBJECT-TYPE
	SYNTAX  INTEGER
	ACCESS  read-only
	STATUS  mandatory
	DESCRIPTION
		"The numerical value(1-100) of CP CPU activity ratio for a minute.If the state of CP is not Under Operation, return 0. If standby system BCU is not implemented return 0."
	::= { ax7800rBcuBoardEntry 33 }
	
ax7800rBcuSerialNumber OBJECT-TYPE
	SYNTAX  DisplayString (SIZE (0..30))
	ACCESS  read-only
	STATUS  mandatory
	DESCRIPTION
		"The character string of the card management information of BCU package whose number is a maximum of 30. Its length is zero if not implemented or closed."
	::= { ax7800rBcuBoardEntry 34 }
	
ax7800rBcuVoltage150 OBJECT-TYPE
	SYNTAX  INTEGER
	ACCESS  read-only
	STATUS  mandatory
	DESCRIPTION
		"The numerical value of the voltage at the observation point of 1.5V voltage. Unit of measure : 10mV (ex : 148)
		Return length 0 if standby system BCU not implemented or closed."
	::= { ax7800rBcuBoardEntry 35 }
	
ax7800rBcuVoltage180 OBJECT-TYPE
	SYNTAX  INTEGER
	ACCESS  read-only
	STATUS  mandatory
	DESCRIPTION
		"The numerical value of the voltage at the observation point of 1.8V voltage. Unit of measure : 10mV (ex : 183)
		Return length 0 if standby system BCU not implemented or closed."
	::= { ax7800rBcuBoardEntry 36 }
	
ax7800rBcuVoltage250 OBJECT-TYPE
	SYNTAX  INTEGER
	ACCESS  read-only
	STATUS  mandatory
	DESCRIPTION
		"The numerical value of the voltage at the observation point of 2.5V voltage. Unit of measure : 10mV (ex : 250)
		Return length 0 if standby system BCU not implemented or closed."
	::= { ax7800rBcuBoardEntry 37 }
	
ax7800rBcuVoltage330 OBJECT-TYPE
	SYNTAX  INTEGER
	ACCESS  read-only
	STATUS  mandatory
	DESCRIPTION
		"The numerical value of the voltage at the observation point of 3.3V voltage. Unit of measure : 10mV (ex : 328)
		Return length 0 if standby system BCU not implemented or closed."
	::= { ax7800rBcuBoardEntry 38 }
	
ax7800rBcuVoltage500 OBJECT-TYPE
	SYNTAX  INTEGER
	ACCESS  read-only
	STATUS  mandatory
	DESCRIPTION
		"The numerical value of the voltage at the observation point of 5V voltage. Unit of measure : 10mV (ex : 493)
		Return length 0 if standby system BCU not implemented or closed."
	::= { ax7800rBcuBoardEntry 39 }
	
ax7800rBcuVoltage130 OBJECT-TYPE
	SYNTAX  INTEGER
	ACCESS  read-only
	STATUS  mandatory
	DESCRIPTION
		"The numerical value of the voltage at the observation point of 1.3V voltage. Unit of measure : 10mV (ex : 133)
		Return length 0 if standby system BCU not implemented or closed."
	::= { ax7800rBcuBoardEntry 40 }

ax7800rBcuPbmVoltage105 OBJECT-TYPE
	SYNTAX  INTEGER
	ACCESS  read-only
	STATUS  mandatory
	DESCRIPTION
		"The numerical value of the voltage at the observation point of 1.05V voltage in PBM. Unit of measure : 10mV (ex : 102)
		Return length 0 if standby system BCU not implemented or closed."
	::= { ax7800rBcuBoardEntry 41 }

ax7800rBcuPbmVoltage120 OBJECT-TYPE
	SYNTAX  INTEGER
	ACCESS  read-only
	STATUS  mandatory
	DESCRIPTION
		"The numerical value of the voltage at the observation point of 1.2V voltage in PBM. Unit of measure : 10mV (ex : 121)
		Return length 0 if standby system BCU not implemented or closed."
	::= { ax7800rBcuBoardEntry 42 }

ax7800rBcuPbmCpuCoreVoltage OBJECT-TYPE
	SYNTAX  INTEGER
	ACCESS  read-only
	STATUS  mandatory
	DESCRIPTION
		"The numerical value of the voltage at the observation point of 1.2-1.3V voltage in PBM. Unit of measure : 10mV (ex : 125)
		Return length 0 if standby system BCU not implemented or closed."
	::= { ax7800rBcuBoardEntry 43 }

ax7800rBcuPbmVoltage150 OBJECT-TYPE
	SYNTAX  INTEGER
	ACCESS  read-only
	STATUS  mandatory
	DESCRIPTION
		"The numerical value of the voltage at the observation point of 1.5V voltage in PBM. Unit of measure : 10mV (ex : 148)
		Return length 0 if standby system BCU not implemented or closed."
	::= { ax7800rBcuBoardEntry 44 }

ax7800rBcuPbmVoltage180 OBJECT-TYPE
	SYNTAX  INTEGER
	ACCESS  read-only
	STATUS  mandatory
	DESCRIPTION
		"The numerical value of the voltage at the observation point of 1.8V voltage in PBM. Unit of measure : 10mV (ex : 183)
		Return length 0 if standby system BCU not implemented or closed."
	::= { ax7800rBcuBoardEntry 45 }

ax7800rAtaCardTable OBJECT-TYPE
	SYNTAX  SEQUENCE OF Ax7800rAtaCardTableEntry
	ACCESS  not-accessible
	STATUS  mandatory
	DESCRIPTION
		"A table containing ATA Card information."
	::= { ax7800rBcuBoard 2 }

ax7800rAtaCardEntry OBJECT-TYPE
	SYNTAX  Ax7800rAtaCardTableEntry
	ACCESS  not-accessible
	STATUS  mandatory
	DESCRIPTION
		"An entry containing ATA Card information."
	INDEX   { ax7800rChassisIndex, ax7800rBcuBoardIndex, ax7800rAtaCardIndex }
	::= { ax7800rAtaCardTable 1 }

	Ax7800rAtaCardTableEntry ::=
		SEQUENCE {
		  ax7800rAtaCardIndex
			INTEGER,
		  ax7800rAtaCardConnection
			INTEGER,
		  ax7800rAtaCardTotalSize
			INTEGER,
		  ax7800rAtaCardUsedSize
			INTEGER,
		  ax7800rAtaCardFreeSize
			INTEGER,
		  ax7800rAtaCardName
			DisplayString,
		  ax7800rAtaCardAbbreviation
			DisplayString,
		  ax7800rAtaCardMountStatus
			INTEGER
		}

ax7800rAtaCardIndex OBJECT-TYPE
	SYNTAX  INTEGER
	ACCESS  not-accessible
	STATUS  mandatory
	DESCRIPTION
		"Connected position of ATA cards.The value is 1 plus slot number
		that ATA card is inserted.The value is from 1 to ax7800rBcuAtaCardNumber."
	::= { ax7800rAtaCardEntry 1 }

ax7800rAtaCardConnection OBJECT-TYPE
	SYNTAX  INTEGER {
		connect(2),
		disconnect(32)
	      }
	ACCESS  read-only
	STATUS  mandatory
	DESCRIPTION
		"Connected status of ATA cards."
	::= { ax7800rAtaCardEntry 2 }

ax7800rAtaCardTotalSize OBJECT-TYPE
	SYNTAX  INTEGER
	ACCESS  read-only
	STATUS  mandatory
	DESCRIPTION
		"Total capacity of ATA cards.The value is displayed in kilobyte
		(kbyte).And the value is -1 when ATA cards is disconnected."
	::= { ax7800rAtaCardEntry 3 }

ax7800rAtaCardUsedSize OBJECT-TYPE
	SYNTAX  INTEGER
	ACCESS  read-only
	STATUS  mandatory
	DESCRIPTION
		"Using capacity of ATA cards.The value is displayed in kilobyte
		(kbyte).And the value is -1 when ATA cards is disconnected."
	::= { ax7800rAtaCardEntry 4 }

ax7800rAtaCardFreeSize OBJECT-TYPE
	SYNTAX  INTEGER
	ACCESS  read-only
	STATUS  mandatory
	DESCRIPTION
		"The rest capacity of ATA card. The value is displayed in kilobyte
		(kbyte). The value is -1 when ATA card is disconnected."
	::= { ax7800rAtaCardEntry 5 }

ax7800rAtaCardName OBJECT-TYPE
	SYNTAX  DisplayString (SIZE (0..16))
	ACCESS  read-only
	STATUS  mandatory
	DESCRIPTION
		"The product name of ATA card. When the ATA card is unknown,
		this OCTET STRING value is 'unknown'. When ATA card is disconnected,
		this will be an OCTET STRING of zero length."
	::= { ax7800rAtaCardEntry 6 }

ax7800rAtaCardAbbreviation OBJECT-TYPE
	SYNTAX  DisplayString (SIZE (0..16))
	ACCESS  read-only
	STATUS  mandatory
	DESCRIPTION
		"The kind of ATA card. When ATA card is disconnected,this will be an
		OCTET STRING of zero length."
	::= { ax7800rAtaCardEntry 7 }

ax7800rAtaCardMountStatus OBJECT-TYPE
	SYNTAX  INTEGER {
		disconnected(-1),
		unmount(1),
  		mount(2)
	      }
	ACCESS  read-only
	STATUS  mandatory
	DESCRIPTION
		"The mount state of ATA card. The value is -1 when ATA card is
		disconnected."
	::= { ax7800rAtaCardEntry 8 }

ax7800rTemperatureStatusTable OBJECT-TYPE
	SYNTAX  SEQUENCE OF Ax7800rTemperatureStatusEntry
	ACCESS  not-accessible
	STATUS  mandatory
	DESCRIPTION
		"The table of ambient temperature status maintained by the
		environmental monitor."
	::= { ax7800rBcuBoard 3 }

ax7800rTemperatureStatusEntry OBJECT-TYPE
	SYNTAX  Ax7800rTemperatureStatusEntry
	ACCESS  not-accessible
	STATUS  mandatory
	DESCRIPTION
		"An entry in the ambient temperature status table, representing
		the status of the associated testpoint maintained by the
		environmental monitor."
	INDEX  { ax7800rChassisIndex, ax7800rBcuBoardIndex, ax7800rTemperatureStatusIndex }
	::= { ax7800rTemperatureStatusTable 1 }

	Ax7800rTemperatureStatusEntry ::=
		SEQUENCE {
		  ax7800rTemperatureStatusIndex
			INTEGER(0..2147483647),
		  ax7800rTemperatureStatusDescr
			DisplayString,
		  ax7800rTemperatureStatusValue
			INTEGER,
		  ax7800rTemperatureThreshold
			INTEGER,
		  ax7800rTemperatureState
			INTEGER
		}

ax7800rTemperatureStatusIndex OBJECT-TYPE
	SYNTAX  INTEGER(0..2147483647)
	ACCESS  not-accessible
	STATUS  mandatory
	DESCRIPTION
		"Unique index for the testpoint being instrumented.
		This index is for SNMP purposes only, and has no
		intrinsic meaning."
	::= { ax7800rTemperatureStatusEntry 1 }

ax7800rTemperatureStatusDescr OBJECT-TYPE
	SYNTAX  DisplayString(SIZE(0..32))
	ACCESS  read-only
	STATUS  mandatory
	DESCRIPTION
		"Textual description of the testpoint being instrumented.
		This description is a short textual label, suitable as a
		human-sensible identification for the rest of the
		information in the entry."
	::= { ax7800rTemperatureStatusEntry 2 }

ax7800rTemperatureStatusValue OBJECT-TYPE
	SYNTAX  INTEGER
	ACCESS  read-only
	STATUS  mandatory
	DESCRIPTION
		"The current measurement of the testpoint being instrumented."
	::= { ax7800rTemperatureStatusEntry 3 }

ax7800rTemperatureThreshold OBJECT-TYPE
	SYNTAX  INTEGER
	ACCESS  read-only
	STATUS  mandatory
	DESCRIPTION
		"The highest value that the associated instance of the
		object ax7800rTemperatureStatusValue may obtain
		before an emergency shutdown of the managed device is
		initiated."
	::= { ax7800rTemperatureStatusEntry 4 }

ax7800rTemperatureState OBJECT-TYPE
	SYNTAX  INTEGER {
		normal(1),
		caution(2),
		warning(3),
		fatal(4)
		}
	ACCESS  read-only
	STATUS  mandatory
	DESCRIPTION
		"The current state of the testpoint being instrumented."
	::= { ax7800rTemperatureStatusEntry 5 }

ax7800rSopTable OBJECT-TYPE
        SYNTAX  SEQUENCE OF Ax7800rSopEntry
        ACCESS  not-accessible
        STATUS  mandatory
        DESCRIPTION
                "A table containing SOP information."
        ::= { ax7800rBcuBoard 4 }

ax7800rSopEntry OBJECT-TYPE
        SYNTAX  Ax7800rSopEntry
        ACCESS  not-accessible
        STATUS  mandatory
        DESCRIPTION
                "An entry containing SOP information."
        INDEX   { ax7800rChassisIndex, ax7800rBcuBoardIndex }
        ::= { ax7800rSopTable 1 }

        Ax7800rSopEntry ::=
                SEQUENCE {
                  ax7800rSopAlarmLevel
                        DisplayString,
                  ax7800rSopAlarmEventPoint
                        DisplayString,
                  ax7800rSopAlarmEventCode
                        DisplayString,
                  ax7800rSopAlarmEventInterfaceID
                        DisplayString,
                  ax7800rSopAlarmMsgText
                        DisplayString
                }

ax7800rSopAlarmLevel OBJECT-TYPE
        SYNTAX  DisplayString
        ACCESS  read-only
        STATUS  mandatory
        DESCRIPTION
                "Error level displayed on a SOP window. When the BCU does not
                support SOP, this will be an OCTET STRING of zero length.
                For information about this code, see:  Operator's Manual."
        ::= { ax7800rSopEntry 1 }

ax7800rSopAlarmEventPoint OBJECT-TYPE
        SYNTAX  DisplayString
        ACCESS  read-only
        STATUS  mandatory
        DESCRIPTION
                "The code displayed on a SOP window, which stands for a device
                part of the factor of the alarm message. When the BCU does not
                support SOP, this will be an OCTET STRING of zero length.
                For information about this code, see:  Operator's Manual."
        ::= { ax7800rSopEntry 2 }

ax7800rSopAlarmEventCode OBJECT-TYPE
        SYNTAX  DisplayString
        ACCESS  read-only
        STATUS  mandatory
        DESCRIPTION
                "Event kind code of alarm message displayed on a SOP window.
                When the BCU does not support SOP, this will be an OCTET STRING
                of zero length. For information about this code, see:  Operator's
                Manual."
        ::= { ax7800rSopEntry 3 }

ax7800rSopAlarmEventInterfaceID OBJECT-TYPE
        SYNTAX  DisplayString
        ACCESS  read-only
        STATUS  mandatory
        DESCRIPTION
                "Interface identification of alarm messages on a SOP window.
                When the BCU does not support SOP, this will be an OCTET STRING
                of zero length. For information about this code, see:  Operator's
                Manual."
        ::= { ax7800rSopEntry 4 }

ax7800rSopAlarmMsgText OBJECT-TYPE
        SYNTAX  DisplayString
        ACCESS  read-only
        STATUS  mandatory
        DESCRIPTION
                "The text of the alarm message on a SOP window. When the BCU does
                not support SOP, this will be an OCTET STRING of zero length.
                For more information about this code, see:  Operator's Manual."
        ::= { ax7800rSopEntry 5 }
	

ax7800rPruBoardTable OBJECT-TYPE
	SYNTAX  SEQUENCE OF Ax7800rPpuBoardTableEntry
	ACCESS  not-accessible
	STATUS  mandatory
	DESCRIPTION
		"A table containing PRU boards information about
		specific chassis."
	::= { ax7800rPruBoard 1 }

ax7800rPruBoardEntry OBJECT-TYPE
	SYNTAX  Ax7800rPpuBoardTableEntry
	ACCESS  not-accessible
	STATUS  mandatory
	DESCRIPTION
		"An entry containing PRU boards about specific
		chassis."
	INDEX   { ax7800rChassisIndex,ax7800rPruBoardIndex }
	::= { ax7800rPruBoardTable 1 }

	Ax7800rPpuBoardTableEntry ::=
		SEQUENCE {
		  ax7800rPruBoardIndex
			INTEGER,
		  ax7800rPruBoardType
			INTEGER,
		  ax7800rPruOperStatus
			INTEGER,
		  ax7800rPruBoardName
			DisplayString,
		  ax7800rPruBoardAbbreviation
			DisplayString,
		  ax7800rPruBoardProductCode
			INTEGER,
		  ax7800rPruSerialNumber
			DisplayString,
		  ax7800rPruVoltage120
			INTEGER,
		  ax7800rPruVoltage150
			INTEGER,
		  ax7800rPruVoltage180
			INTEGER,
		  ax7800rPruVoltage250
			INTEGER,
		  ax7800rPruVoltage330
			INTEGER,
		  ax7800rPruVoltage500
			INTEGER,
		  ax7800rPruVoltage120-2
			INTEGER,
		  ax7800rPruVoltage120-3
			INTEGER,
		  ax7800rPruVoltage120-4
			INTEGER,
		  ax7800rPruVoltage120-5
			INTEGER,
		  ax7800rPruVoltage120-6
			INTEGER,
		  ax7800rPruVoltage120-7
			INTEGER,
		  ax7800rPruVoltage120-8
			INTEGER
		}

ax7800rPruBoardIndex OBJECT-TYPE
	SYNTAX  INTEGER
	ACCESS  not-accessible
	STATUS  mandatory
	DESCRIPTION
		"Position information of the PRU slots. The value is from 1 to
		ax7800rPruBoardNumber."
	::= { ax7800rPruBoardEntry 1 }

ax7800rPruBoardType OBJECT-TYPE
	SYNTAX  INTEGER {
		disconnected(-1),
		pru-b2(17664),
		pru-c2(18432),
		pru-d2(19200),
		pru-d2b(19712),
		pru-b2b(19713),
		rb2-10g4rx(22272)
		}
	ACCESS  read-only
	STATUS  mandatory
	DESCRIPTION
		"PRU boards ID.
        The value is -1 when PRU board is disconnected."
	::= { ax7800rPruBoardEntry 2 }

ax7800rPruOperStatus OBJECT-TYPE
	SYNTAX  INTEGER {
		other(1),
		active(2),
		initialization(3),
		down(4),
		closed(5),
		inactive(6),
		disconnect(32)
	      }
	ACCESS  read-only
	STATUS  mandatory
	DESCRIPTION
		"Operation stasus of PRU board.(STATUS LED)"
	::= { ax7800rPruBoardEntry 3 }

ax7800rPruBoardName OBJECT-TYPE
	SYNTAX  DisplayString (SIZE (0..16))
	ACCESS  read-only
	STATUS  mandatory
	DESCRIPTION
		"PRU board name. When PRU board is disconnected, this will be an OCTET
		STRING of zero length."
	::= { ax7800rPruBoardEntry 4 }

ax7800rPruBoardAbbreviation OBJECT-TYPE
	SYNTAX  DisplayString (SIZE (0..16))
	ACCESS  read-only
	STATUS  mandatory
	DESCRIPTION
		"The abbreviation name of PRU board.
		The value is -1 when PRU board is disconnected."
	::= { ax7800rPruBoardEntry 5 }

ax7800rPruBoardProductCode OBJECT-TYPE
	SYNTAX  INTEGER
	ACCESS  read-only
	STATUS  mandatory
	DESCRIPTION
		"The revision of PRU board. When PRU board is disconnected,
		this will be -1."
	::= { ax7800rPruBoardEntry 6 }

ax7800rPruSerialNumber OBJECT-TYPE
	SYNTAX  DisplayString (SIZE (0..30))
	ACCESS  read-only
	STATUS  mandatory
	DESCRIPTION
		"The character string of the card management information of PRU package whose number is a maximum of 30. Its length is zero if not implemented or closed."
	::= { ax7800rPruBoardEntry 7 }

ax7800rPruVoltage120 OBJECT-TYPE
	SYNTAX  INTEGER
	ACCESS  read-only
	STATUS  mandatory
	DESCRIPTION
		"The numerical value of the voltage at the observation point of 1.2V voltage. Unit of measure : 10mV (ex : 148) .If PRU is closed or not implemented, return 0."
	::= { ax7800rPruBoardEntry 8 }

ax7800rPruVoltage150 OBJECT-TYPE
	SYNTAX  INTEGER
	ACCESS  read-only
	STATUS  mandatory
	DESCRIPTION
		"The numerical value of the voltage at the observation point of 1.5V voltage. Unit of measure : 10mV (ex : 148) .If PRU is closed or not implemented, return 0."
	::= { ax7800rPruBoardEntry 9 }

ax7800rPruVoltage180 OBJECT-TYPE
	SYNTAX  INTEGER
	ACCESS  read-only
	STATUS  mandatory
	DESCRIPTION
		"The numerical value of the voltage at the observation point of 1.8V voltage. Unit of measure : 10mV (ex : 183) .If PRU is closed or not implemented, return 0."
	::= { ax7800rPruBoardEntry 10 }

ax7800rPruVoltage250 OBJECT-TYPE
	SYNTAX  INTEGER
	ACCESS  read-only
	STATUS  mandatory
	DESCRIPTION
		"The numerical value of the voltage at the observation point of 2.5V voltage. Unit of measure : 10mV (ex : 250) .If PRU is closed or not implemented, return 0."
	::= { ax7800rPruBoardEntry 11 }

ax7800rPruVoltage330 OBJECT-TYPE
	SYNTAX  INTEGER
	ACCESS  read-only
	STATUS  mandatory
	DESCRIPTION
		"The numerical value of the voltage at the observation point of 3.3V voltage. Unit of measure : 10mV (ex : 328) .If PRU is closed or not implemented, return 0."
	::= { ax7800rPruBoardEntry 12 }

ax7800rPruVoltage500 OBJECT-TYPE
	SYNTAX  INTEGER
	ACCESS  read-only
	STATUS  mandatory
	DESCRIPTION
		"The numerical value of the voltage at the observation point of 5V voltage. Unit of measure : 10mV (ex : 493) .If PRU is closed or not implemented, return 0."
	::= { ax7800rPruBoardEntry 13 }

ax7800rPruVoltage120-2 OBJECT-TYPE
	SYNTAX  INTEGER
	ACCESS  read-only
	STATUS  mandatory
	DESCRIPTION
		"The numerical value of the voltage at the observation point of 1.2V voltage. Unit of measure : 10mV (ex : 123) .If PRU is closed or not implemented, return 0."
	::= { ax7800rPruBoardEntry 14 }

ax7800rPruVoltage120-3 OBJECT-TYPE
	SYNTAX  INTEGER
	ACCESS  read-only
	STATUS  mandatory
	DESCRIPTION
		"The numerical value of the voltage at the observation point of 1.2V voltage. Unit of measure : 10mV (ex : 123) .If PRU is closed or not implemented, return 0."
	::= { ax7800rPruBoardEntry 15 }

ax7800rPruVoltage120-4 OBJECT-TYPE
	SYNTAX  INTEGER
	ACCESS  read-only
	STATUS  mandatory
	DESCRIPTION
		"The numerical value of the voltage at the observation point of 1.2V voltage. Unit of measure : 10mV (ex : 123) .If PRU is closed or not implemented, return 0."
	::= { ax7800rPruBoardEntry 16 }

ax7800rPruVoltage120-5 OBJECT-TYPE
	SYNTAX  INTEGER
	ACCESS  read-only
	STATUS  mandatory
	DESCRIPTION
		"The numerical value of the voltage at the observation point of 1.2V voltage. Unit of measure : 10mV (ex : 123) .If PRU is closed or not implemented, return 0."
	::= { ax7800rPruBoardEntry 17 }

ax7800rPruVoltage120-6 OBJECT-TYPE
	SYNTAX  INTEGER
	ACCESS  read-only
	STATUS  mandatory
	DESCRIPTION
		"The numerical value of the voltage at the observation point of 1.2V voltage. Unit of measure : 10mV (ex : 123) .If PRU is closed or not implemented, return 0."
	::= { ax7800rPruBoardEntry 18 }

ax7800rPruVoltage120-7 OBJECT-TYPE
	SYNTAX  INTEGER
	ACCESS  read-only
	STATUS  mandatory
	DESCRIPTION
		"The numerical value of the voltage at the observation point of 1.2V voltage. Unit of measure : 10mV (ex : 123) .If PRU is closed or not implemented, return 0."
	::= { ax7800rPruBoardEntry 19 }

ax7800rPruVoltage120-8 OBJECT-TYPE
	SYNTAX  INTEGER
	ACCESS  read-only
	STATUS  mandatory
	DESCRIPTION
		"The numerical value of the voltage at the observation point of 1.2V voltage. Unit of measure : 10mV (ex : 123) .If PRU is closed or not implemented, return 0."
	::= { ax7800rPruBoardEntry 20 }

ax7800rNifBoardTable OBJECT-TYPE
	SYNTAX  SEQUENCE OF Ax7800rNifBoardTableEntry
	ACCESS  not-accessible
	STATUS  mandatory
	DESCRIPTION
		"A table containing Network Interface cards (NIF) information that
		slot is loaded."
	::= { ax7800rNifBoard 1 }

ax7800rNifBoardEntry OBJECT-TYPE
	SYNTAX  Ax7800rNifBoardTableEntry
	ACCESS  not-accessible
	STATUS  mandatory
	DESCRIPTION
		"An entry containing NIF information about specific chassis."
        INDEX   { ax7800rChassisIndex,ax7800rNifBoardSlotIndex }
	::= { ax7800rNifBoardTable 1 }

	Ax7800rNifBoardTableEntry ::=
		SEQUENCE {
		  ax7800rNifBoardSlotIndex
			INTEGER,
		  ax7800rNifBoardType
			INTEGER,
		  ax7800rNifBoardOperStatus
			INTEGER,
		  ax7800rNifBoardName
			DisplayString,
		  ax7800rNifBoardAbbreviation
			DisplayString,
		  ax7800rNifBoardProductCode
			INTEGER,
		  ax7800rNifPhysLineNumber
			INTEGER,
                  ax7800rNifSerialNumber
                        DisplayString,
		  ax7800rNifVoltageAM520
			INTEGER,
		  ax7800rNifVoltage150
			INTEGER,
		  ax7800rNifVoltage180
			INTEGER,
		  ax7800rNifVoltageA180
			INTEGER,
		  ax7800rNifVoltage250
			INTEGER,
		  ax7800rNifVoltage330
			INTEGER,
		  ax7800rNifVoltageA330
			INTEGER,
		  ax7800rNifVoltageA500
			INTEGER,
		  ax7800rNifVoltage330S
			INTEGER,
		  ax7800rNifVoltage500S
			INTEGER,
		  ax7800rNifVoltage120
			INTEGER,
		  ax7800rNifVoltageA500-2
			INTEGER,
		  ax7800rNifVoltage150S
			INTEGER,
		  ax7800rNifVoltage110
			INTEGER
		}

ax7800rNifBoardSlotIndex OBJECT-TYPE
	SYNTAX  INTEGER
	ACCESS  not-accessible
	STATUS  mandatory
	DESCRIPTION
		"Position information of NIF loading slot. The value is from 1
		to ax7800rNifBoardNumber."
	::= { ax7800rNifBoardEntry 1 }

ax7800rNifBoardType OBJECT-TYPE
	SYNTAX  INTEGER {
		disconnected(-1),
		other(1),
		nif-12-port-1000BASE-X-SFP-VRRP(32770),
		nif-6-port-1000BASE-X-GBIC-VRRP(32772),
		nif-12-port-10BASE-T-100BASE-TX-1000BASE-T-VRRP(32778),
		nif-8-port-1000BASE-X-SHAPER(32782),
		nif-4-port-1000BASE-X-SHAPER(32783),
		nif-1-port-10GBASE-ER(32786),
		nif-1-port-10GBASE-R-XFP(32788),
		nif-4-port-10GBASE-R-XFP-PRUB2(32790),
		nif-1-port-10GBASE-R-XFPA(32792),
		nif-1-port-10GBASE-LW(32801),
		nif-1-port-10GBASE-EW(32802),
		nif-48-port-10BASE-T-100BASE-TX-1000BASE-T(32822),
		nif-8-port-10-100-1000BASE-T-plus-4-port-1000BASE-X-SFP(32823),
		nif-1-port-OC192c-STM-64-POS-2km(40960),
		nif-1-port-OC192c-STM-64-POS-40km(40961),
		nif-4-port-OC48c-STM-16-POS(40976)
		}
	ACCESS  read-only
	STATUS  mandatory
	DESCRIPTION
		"Type of connecting package.The value is register value of NIF package.
		The value is -1 when PRU is disconnected or NIF disconnected."
	::= { ax7800rNifBoardEntry 2 }

ax7800rNifBoardOperStatus OBJECT-TYPE
	SYNTAX  INTEGER {
		other(1),
		active(2),
		initialization(3),
		down(4),
		closed(5),
		lock(6),
		disconnect(32)
	      }
	ACCESS  read-only
	STATUS  mandatory
	DESCRIPTION
		"Operation status of Network InterFace(NIF) board.(STATUS LED)"
	::= { ax7800rNifBoardEntry 3 }

ax7800rNifBoardName OBJECT-TYPE
	SYNTAX  DisplayString (SIZE (0..16))
	ACCESS  read-only
	STATUS  mandatory
	DESCRIPTION
		"Network InterFace(NIF) board name. When PRU board or NIF board is
		disconnected,this will be an OCTET STRING of zero length."
	::= { ax7800rNifBoardEntry 4 }

ax7800rNifBoardAbbreviation OBJECT-TYPE
	SYNTAX  DisplayString (SIZE (0..16))
	ACCESS  read-only
	STATUS  mandatory
	DESCRIPTION
		"The abbreviation name of Network InterFace(NIF) board. When PRU board
		or NIF board is disconnected, this will be an OCTET STRING of zero
		length."
	::= { ax7800rNifBoardEntry 5 }

ax7800rNifBoardProductCode OBJECT-TYPE
	SYNTAX  INTEGER
	ACCESS  read-only
	STATUS  mandatory
	DESCRIPTION
		"The product management code of Network InterFace(NIF) board.The value
		is -1 when PRU board or NIF board is disconncted."
	::= { ax7800rNifBoardEntry 6 }

ax7800rNifPhysLineNumber OBJECT-TYPE
	SYNTAX  INTEGER
	ACCESS  read-only
	STATUS  mandatory
	DESCRIPTION
		"Number of Network InterFace(NIF)'s physical port.The max is 8.
		The value is -1 when value of ax7800rNifCardType is -1 or other(1)."
	::= { ax7800rNifBoardEntry 7 }

ax7800rNifSerialNumber OBJECT-TYPE
        SYNTAX  DisplayString (SIZE (0..30))
        ACCESS  read-only
        STATUS  mandatory
        DESCRIPTION
                "Management information (SerialNumber) of Network InterFace(NIF) package.
                It shows by the character string of 30 characters or less.
                When PRU board or NIF board is disconnected or closed, this will be
                an OCTET STRING of zero length."
        ::= { ax7800rNifBoardEntry 8 }

ax7800rNifVoltageAM520 OBJECT-TYPE
        SYNTAX  INTEGER
        ACCESS  read-only
        STATUS  mandatory
        DESCRIPTION
                "The numerical value of the voltage at the observation point of -5.2V voltage. Unit of measure : 10mV (ex : -512) .If PRU or NIF is closed or not implemented, return 0."
        ::= { ax7800rNifBoardEntry 9 }

ax7800rNifVoltage150 OBJECT-TYPE
        SYNTAX  INTEGER
        ACCESS  read-only
        STATUS  mandatory
        DESCRIPTION
                "The numerical value of the voltage at the observation point of -1.5V voltage. Unit of measure : 10mV (ex : 148) .If PRU or NIF is closed or not implemented, return 0."
        ::= { ax7800rNifBoardEntry 10 }

ax7800rNifVoltage180 OBJECT-TYPE
        SYNTAX  INTEGER
        ACCESS  read-only
        STATUS  mandatory
        DESCRIPTION
                "The numerical value of the voltage at the observation point of 1.8V voltage. Unit of measure : 10mV (ex : 183) .If PRU or NIF is closed or not implemented, return 0."
        ::= { ax7800rNifBoardEntry 11 }

ax7800rNifVoltageA180 OBJECT-TYPE
        SYNTAX  INTEGER
        ACCESS  read-only
        STATUS  mandatory
        DESCRIPTION
                "The numerical value of the voltage at the observation point of analog 1.8V voltage. Unit of measure : 10mV (ex : 183) .If PRU or NIF is closed or not implemented, return 0."
        ::= { ax7800rNifBoardEntry 12 }

ax7800rNifVoltage250 OBJECT-TYPE
        SYNTAX  INTEGER
        ACCESS  read-only
        STATUS  mandatory
        DESCRIPTION
                "The numerical value of the voltage at the observation point of  analogu 2.5V voltage. Unit of measure : 10mV (ex : 250) .If PRU or NIF is closed or not implemented, return 0."
        ::= { ax7800rNifBoardEntry 13 }

ax7800rNifVoltage330 OBJECT-TYPE
        SYNTAX  INTEGER
        ACCESS  read-only
        STATUS  mandatory
        DESCRIPTION
                "The numerical value of the voltage at the observation point of  analogu 3.3V voltage. Unit of measure : 10mV (ex : 328) .If PRU or NIF is closed or not implemented, return 0."
        ::= { ax7800rNifBoardEntry 14 }

ax7800rNifVoltageA330 OBJECT-TYPE
        SYNTAX  INTEGER
        ACCESS  read-only
        STATUS  mandatory
        DESCRIPTION
                "The numerical value of the voltage at the observation point of analog 3.3V voltage. Unit of measure : 10mV (ex : 328) .If PRU or NIF is closed or not implemented, return 0."
        ::= { ax7800rNifBoardEntry 15 }

ax7800rNifVoltageA500 OBJECT-TYPE
        SYNTAX  INTEGER
        ACCESS  read-only
        STATUS  mandatory
        DESCRIPTION
                "The numerical value of the voltage at the observation point of analog 5V voltage. Unit of measure : 10mV (ex : 493) .If PRU or NIF is closed or not implemented, return 0."
        ::= { ax7800rNifBoardEntry 16 }

ax7800rNifVoltage330S OBJECT-TYPE
        SYNTAX  INTEGER
        ACCESS  read-only
        STATUS  mandatory
        DESCRIPTION
                "The numerical value of the voltage at the observation point of 3.3V voltage. Unit of measure : 10mV (ex : 328) .If PRU or NIF is closed or not implemented, return 0."
        ::= { ax7800rNifBoardEntry 17 }

ax7800rNifVoltage500S OBJECT-TYPE
        SYNTAX  INTEGER
        ACCESS  read-only
        STATUS  mandatory
        DESCRIPTION
                "The numerical value of the voltage at the observation point of 5V voltage. Unit of measure : 10mV (ex : 493) .If PRU or NIF is closed or not implemented, return 0."
        ::= { ax7800rNifBoardEntry 18 }

ax7800rNifVoltage120 OBJECT-TYPE
        SYNTAX  INTEGER
        ACCESS  read-only
        STATUS  mandatory
        DESCRIPTION
                "The numerical value of the voltage at the observation point of 1.2V voltage. Unit of measure : 10mV (ex : 123) .If PSU or NIF is closed or not implemented, return 0."
        ::= { ax7800rNifBoardEntry 19 }

ax7800rNifVoltageA500-2 OBJECT-TYPE
        SYNTAX  INTEGER
        ACCESS  read-only
        STATUS  mandatory
        DESCRIPTION
                "The numerical value of the voltage at the observation point of 5V voltage. Unit of measure : 10mV (ex : 493) .If PSU or NIF is closed or not implemented, return 0."
        ::= { ax7800rNifBoardEntry 20 }

ax7800rNifVoltage150S OBJECT-TYPE
        SYNTAX  INTEGER
        ACCESS  read-only
        STATUS  mandatory
        DESCRIPTION
                "The numerical value of the voltage at the observation point of 1.5V voltage. Unit of measure : 10mV (ex : 148) .If PSU or NIF is closed or not implemented, return 0."
        ::= { ax7800rNifBoardEntry 21 }

ax7800rNifVoltage110 OBJECT-TYPE
        SYNTAX  INTEGER
        ACCESS  read-only
        STATUS  mandatory
        DESCRIPTION
                "The numerical value of the voltage at the observation point of 1.15V voltage. Unit of measure : 10mV (ex : 117) .If PSU or NIF is closed or not implemented, return 0."
        ::= { ax7800rNifBoardEntry 23 }

ax7800rPhysLineTable OBJECT-TYPE
	SYNTAX  SEQUENCE OF Ax7800rPhysLineTableEntry
	ACCESS  not-accessible
	STATUS  mandatory
	DESCRIPTION
		"A table containing physical port information."
	::= { ax7800rPhysLine 1 }

ax7800rPhysLineEntry OBJECT-TYPE
	SYNTAX  Ax7800rPhysLineTableEntry
	ACCESS  not-accessible
	STATUS  mandatory
	DESCRIPTION
		"An entry containing physical port."
	INDEX   { ax7800rChassisIndex, ax7800rNifBoardSlotIndex, ax7800rPhysLineIndex }
	::= { ax7800rPhysLineTable 1 }

	Ax7800rPhysLineTableEntry ::=
		SEQUENCE {
		  ax7800rPhysLineIndex
			INTEGER,
		  ax7800rPhysLineConnectorType
			INTEGER,
		  ax7800rPhysLineOperStatus
			INTEGER,
		  ax7800rPhysLineIfIndexNumber
			INTEGER,
		  ax7800rPhysLineTransceiverStatus
		    INTEGER
		}

ax7800rPhysLineIndex OBJECT-TYPE
	SYNTAX  INTEGER
	ACCESS  not-accessible
	STATUS  mandatory
	DESCRIPTION
		"Physical port number. The value is from 1 to ax7800rNifLineNumber."
	::= { ax7800rPhysLineEntry 1 }

ax7800rPhysLineConnectorType OBJECT-TYPE
	SYNTAX  INTEGER {
		disconnected(-1),
		other(1),
		typeOC-48c-STM-16-POS-2km(103),
		typeOC-48c-STM-16-POS-40km(104),
		type1000BASE-LX(301),
		type1000BASE-SX(302),
		type1000BASE-LH(303),
		type1000BASE-LHB(310),
		type10GBASE-SR(401),
		type10GBASE-LR(402),
		type10GBASE-ER(403),
		type10GBASE-ZR(404)
		}
	ACCESS  read-only
	STATUS  mandatory
	DESCRIPTION
		"Connector type is connected physical port. The value is 1(other)
		when connector is disconnected or connector type is unknown.When
		displaying in pannel, requests board name of NIF,then will display it.
		The value is -1	when PRU or NIF board is disconnected."
	::= { ax7800rPhysLineEntry 2 }

ax7800rPhysLineOperStatus OBJECT-TYPE
	SYNTAX  INTEGER {
		disconnected(-1),
		other(1),
		active(2),
		initialization(3),
		down(4),
		lock(6),
		close(7),
		line-fault(8),
		test(9),
		nothing-configuration(10),
		missing-configuration(11),
		remote-loop-back-test-mode(12)
	      }
	ACCESS  read-only
	STATUS  mandatory
	DESCRIPTION
		"Status of physical port. The value is -1 when PRU or NIF board is
		disconnected."
	::= { ax7800rPhysLineEntry 3 }

ax7800rPhysLineIfIndexNumber OBJECT-TYPE
	SYNTAX  INTEGER
	ACCESS  read-only
	STATUS  mandatory
	DESCRIPTION
		"Number of ifIndex which is included in physical port.The value is -1
		when PRU board or NIF board is disconnected."
	::= { ax7800rPhysLineEntry 4 }

ax7800rPhysLineTransceiverStatus OBJECT-TYPE
	SYNTAX  INTEGER{
				gbic-mounted(10),
				gbic-unmounted(11),
				unsupported-gbic-mounted(12),
				gbic-status-unknown(13),
				sfp-mounted(20),
				sfp-unmounted(21),
				unsupported-sfp-mounted(22),
				sfp-status-unknown(23),
				xfp-mounted(30),
				xfp-unmounted(31),
				unsupported-xfp-mounted(32),
				xfp-status-unknown(33)
			}
	ACCESS  read-only
	STATUS  mandatory
	DESCRIPTION
		"Type and status of replaceable transceiver."
	::= { ax7800rPhysLineEntry 5 }
	
-- 

ax7800rLineIfTable OBJECT-TYPE
	SYNTAX  SEQUENCE OF Ax7800rLineIfTableEntry
	ACCESS  not-accessible
	STATUS  mandatory
	DESCRIPTION
		"A table containing physical port correspond to ifIndex."
	::= { ax7800rInterface 1 }

ax7800rLineIfEntry OBJECT-TYPE
	SYNTAX  Ax7800rLineIfTableEntry
	ACCESS  not-accessible
	STATUS  mandatory
	DESCRIPTION
		"An entry containing ifIndex is assigned to physical port."
	INDEX   { ax7800rChassisIndex, ax7800rNifBoardSlotIndex, ax7800rPhysLineIndex, ax7800rLineIfIndex }
	::= { ax7800rLineIfTable 1 }

	Ax7800rLineIfTableEntry ::=
		SEQUENCE {
		  ax7800rLineIfIndex
			INTEGER,
		  ax7800rIfIndex
			INTEGER,
		  ax7800rIfIpAddress
			IpAddress,
		  ax7800rIfIpv6Address
			OCTET STRING
		}

ax7800rLineIfIndex OBJECT-TYPE
	SYNTAX  INTEGER
	ACCESS  not-accessible
	STATUS  mandatory
	DESCRIPTION
		"The value of ifIndex to distinguish entry of this table.The value is
		from 1 to ax7800rPhysLineIfIndexNumber."
	::= { ax7800rLineIfEntry 1 }

ax7800rIfIndex OBJECT-TYPE
	SYNTAX  INTEGER
	ACCESS  read-only
	STATUS  mandatory
	DESCRIPTION
		"The value of ifIndex which is assigned to this physical port.
		The value is 0 when ifIndex is not assigned to this physical port."
	::= { ax7800rLineIfEntry 2 }

ax7800rIfIpAddress OBJECT-TYPE
	SYNTAX  IpAddress
	ACCESS  read-only
	STATUS  mandatory
	DESCRIPTION
		"The IP address correspond to ifIndex which is assigned to this
		physical port. If IP address is not assigned, it is '0.0.0.0'."
	::= { ax7800rLineIfEntry 3 }

ax7800rIfIpv6Address OBJECT-TYPE
	SYNTAX  OCTET STRING
	ACCESS  read-only
	STATUS  mandatory
	DESCRIPTION
		"The IPv6 address correspond to ifIndex which is assigned to this
		physical port. If IPv6 address is not assigned,
		it is '00 00 00 00 00 00 00 00 00 00 00 00 00 00 00 00'."
	::= { ax7800rLineIfEntry 4 }

-- ax7700rRouter group

ax7700rModelType OBJECT-TYPE
	SYNTAX  INTEGER {
		other(1),
		ax7702r(300)
      }
	ACCESS  read-only
	STATUS  mandatory
	DESCRIPTION
		"Model type of this system."
	::= { ax7700rRouter 1 }

--ax7700rSoftware OBJECT-TYPE
--	SYNTAX  INTEGER
--	ACCESS  not-accessible
--	STATUS  mandatory
--	DESCRIPTION
--		"Software information of this system."
--	::= { ax7700rRouter 2 }

ax7700rSoftwareName OBJECT-TYPE
	SYNTAX  DisplayString (SIZE (0..16))
	ACCESS  read-only
	STATUS  mandatory
	DESCRIPTION
		"Software name of this system."
	::= { ax7700rSoftware 1 }

ax7700rSoftwareAbbreviation OBJECT-TYPE
	SYNTAX  DisplayString (SIZE (0..16))
	ACCESS  read-only
	STATUS  mandatory
	DESCRIPTION
		"System software abbreviation."
	::= { ax7700rSoftware 2 }

ax7700rSoftwareVersion OBJECT-TYPE
	SYNTAX  DisplayString (SIZE (0..16))
	ACCESS  read-only
	STATUS  mandatory
	DESCRIPTION
		"System software version."
	::= { ax7700rSoftware 3 }

--ax7700rSystemMsg OBJECT-TYPE
--	SYNTAX  INTEGER
--	ACCESS  not-accessible
--	STATUS  mandatory
--	DESCRIPTION
--		"System messege group."
--	::= { ax7700rRouter 3 }

ax7700rSystemMsgText OBJECT-TYPE
	SYNTAX  DisplayString (SIZE (0..256))
	ACCESS  read-only
	STATUS  mandatory
	DESCRIPTION
		"The text of the system log message.For information about this code,
		see:  Operator's Manual. "
	::= { ax7700rSystemMsg 1 }

ax7700rSystemMsgType OBJECT-TYPE
	SYNTAX  OCTET STRING (SIZE (1))
	ACCESS  read-only
	STATUS  mandatory
	DESCRIPTION
		"The event type. For information about this code, see:  Operator's Manual."
	::= { ax7700rSystemMsg 2 }

ax7700rSystemMsgTimeStamp OBJECT-TYPE
	SYNTAX  DisplayString (SIZE (14))
	ACCESS  read-only
	STATUS  mandatory
	DESCRIPTION
		"The time that event occured. And that is expressed as type of
		MM/DD hh:mm:ss
			MM:month(01-12)
			DD:day(01-31)
			hh:hour(00-23)
			mm:minute(00-59)
			ss:second(00-59)
		Insert space between DD and hh."
	::= { ax7700rSystemMsg 3 }

ax7700rSystemMsgLevel OBJECT-TYPE
	SYNTAX  OCTET STRING (SIZE (1))
	ACCESS  read-only
	STATUS  mandatory
	DESCRIPTION
		"The newest system message log level.For information about this code,
		see:  Operator's Manual. "
	::= { ax7700rSystemMsg 4 }

ax7700rSystemMsgEventPoint OBJECT-TYPE
	SYNTAX  DisplayString (SIZE (0..8))
	ACCESS  read-only
	STATUS  mandatory
	DESCRIPTION
		"The code of part that system message error occured. For information
		about this code,see:  Operator's Manual. "
	::= { ax7700rSystemMsg 5 }

ax7700rSystemMsgEventInterfaceID OBJECT-TYPE
	SYNTAX  DisplayString (SIZE (0..40))
	ACCESS  read-only
	STATUS  mandatory
	DESCRIPTION
		"Interface identification of system messages. For information
		about this code,see:  Operator's Manual."
	::= { ax7700rSystemMsg 6 }

ax7700rSystemMsgEventCode OBJECT-TYPE
	SYNTAX  OCTET STRING (SIZE (4))
	ACCESS  read-only
	STATUS  mandatory
	DESCRIPTION
		"Event kind code of system messages. For information about this code,
		see:  Operator's Manual. "
	::= { ax7700rSystemMsg 7 }

ax7700rSystemMsgAdditionalCode OBJECT-TYPE
	SYNTAX  OCTET STRING (SIZE (6))
	ACCESS  read-only
	STATUS  mandatory
	DESCRIPTION
		"Additional code of system messages. For information about this code,
		see:  Operator's Manual. "
	::= { ax7700rSystemMsg 8 }

--ax7700rSnmpAgent OBJECT-TYPE
--	SYNTAX  INTEGER
--	ACCESS  not-accessible
--	STATUS  mandatory
--	DESCRIPTION
--		"Related information of SNMP agent."
--	::= { ax7700rRouter 4 }

ax7700rSnmpSendReceiveSize OBJECT-TYPE
	SYNTAX  INTEGER
	ACCESS  read-only
	STATUS  mandatory
	DESCRIPTION
		"SNMP packet data size in Manager-to-Agent communication. The value is
		displayed in bytes."
	::= { ax7700rSnmpAgent 1 }

ax7700rSnmpReceiveDelay OBJECT-TYPE
	SYNTAX  INTEGER
	ACCESS  read-only
	STATUS  mandatory
	DESCRIPTION
		"A recommendable interval to receive packets from Manager.The value is
		displayed in milliseconds."
	::= { ax7700rSnmpAgent 2 }

ax7700rSnmpContinuousSend OBJECT-TYPE
	SYNTAX  INTEGER
	ACCESS  read-only
	STATUS  mandatory
	DESCRIPTION
		"Number of times that is recommendable continuous transmission
		packets."
	::= { ax7700rSnmpAgent 3 }

ax7700rSnmpObjectMaxNumber OBJECT-TYPE
	SYNTAX  INTEGER
	ACCESS  read-only
	STATUS  mandatory
	DESCRIPTION
		"Max number of objects that contain SNMP packet."
	::= { ax7700rSnmpAgent 4 }

--ax7700rSerialNumber OBJECT-TYPE
--        SYNTAX  DisplayString (SIZE (0..30))
--	ACCESS  read-only
--        STATUS  mandatory
--        DESCRIPTION
--                "Management information (SerialNumber) of RMP2-CARD."
--        ::= { ax7700rRouter 5 }

ax7700rLicenseNumber OBJECT-TYPE
        SYNTAX  INTEGER
	ACCESS  read-only
        STATUS  mandatory
        DESCRIPTION
                "The number of the configured license serial numbers."
        ::= { ax7700rLicense 1 }

ax7700rLicenseTable OBJECT-TYPE
	SYNTAX  SEQUENCE OF Ax7700rLicenseTableEntry
	ACCESS  not-accessible
	STATUS  mandatory
	DESCRIPTION
		"The table containing the license information."
	::= { ax7700rLicense 2 }

ax7700rLicenseEntry OBJECT-TYPE
	SYNTAX  Ax7700rLicenseTableEntry
	ACCESS  not-accessible
	STATUS  mandatory
	DESCRIPTION
		"The entry of license information."
	INDEX   { ax7700rLicenseIndex }
	::= { ax7700rLicenseTable 1 }

	Ax7700rLicenseTableEntry ::=
		SEQUENCE {
		  ax7700rLicenseIndex
			INTEGER,
		  ax7700rLicenseSerialNumber
			DisplayString,
		  ax7700rLicenseOptionNumber
			INTEGER
                }

ax7700rLicenseIndex OBJECT-TYPE
	SYNTAX  INTEGER
	ACCESS  not-accessible
	STATUS  mandatory
	DESCRIPTION
		"The unique index number given for each serial number. The number is from 1 to ax7700rLicenseNumber."
	::= { ax7700rLicenseEntry 1 }

ax7700rLicenseSerialNumber OBJECT-TYPE
	SYNTAX  DisplayString 
	ACCESS  read-only
	STATUS  mandatory
	DESCRIPTION
		"The serial number."
	::= { ax7700rLicenseEntry 2 }

ax7700rLicenseOptionNumber OBJECT-TYPE
	SYNTAX  INTEGER 
	ACCESS  read-only
	STATUS  mandatory
	DESCRIPTION
		"The number of option licenses associated with the serial number."
	::= { ax7700rLicenseEntry 3 }

ax7700rLicenseOptionTable OBJECT-TYPE
	SYNTAX  SEQUENCE OF Ax7700rLicenseOptionTableEntry
	ACCESS  not-accessible
	STATUS  mandatory
	DESCRIPTION
		"The table containing option licenses information associated with the serial number."
	::= { ax7700rLicense 3 }

ax7700rLicenseOptionEntry OBJECT-TYPE
	SYNTAX  Ax7700rLicenseOptionTableEntry
	ACCESS  not-accessible
	STATUS  mandatory
	DESCRIPTION
		"The entry of the option license information associated with the serial number."
	INDEX   { ax7700rLicenseOptionIndex,ax7700rLicenseOptionNumberIndex }
	::= { ax7700rLicenseOptionTable 1 }

	Ax7700rLicenseOptionTableEntry ::=
		SEQUENCE {
		  ax7700rLicenseOptionIndex
			INTEGER,
		  ax7700rLicenseOptionNumberIndex
			INTEGER,
		  ax7700rLicenseOptionSoftwareName
			DisplayString,
		  ax7700rLicenseOptionSoftwareAbbreviation
			DisplayString
                }

ax7700rLicenseOptionIndex OBJECT-TYPE
	SYNTAX  INTEGER
	ACCESS  not-accessible
	STATUS  mandatory
	DESCRIPTION
		"The unique index number given for each serial number. The same number as ax7700rLicenseIndex."
	::= { ax7700rLicenseOptionEntry 1 }

ax7700rLicenseOptionNumberIndex OBJECT-TYPE
	SYNTAX  INTEGER
	ACCESS  not-accessible
	STATUS  mandatory
	DESCRIPTION
		"The unique index number of option licenses information which is given for each serial number. The number is from 1 to ax7700rLicenseNumber."
	::= { ax7700rLicenseOptionEntry 2 }

ax7700rLicenseOptionSoftwareName OBJECT-TYPE
	SYNTAX  DisplayString 
	ACCESS  read-only
	STATUS  mandatory
	DESCRIPTION
		"The software model name of the option license information associated with the serial number."
	::= { ax7700rLicenseOptionEntry 3 }

ax7700rLicenseOptionSoftwareAbbreviation OBJECT-TYPE
	SYNTAX  DisplayString 
	ACCESS  read-only
	STATUS  mandatory
	DESCRIPTION
		"The software abbreviated name of the option license information associated with the serial number. "
	::= { ax7700rLicenseOptionEntry 4 }

-- ax7700rDevice group

ax7700rChassisMaxNumber OBJECT-TYPE
	SYNTAX  INTEGER
	ACCESS  read-only
	STATUS  mandatory
	DESCRIPTION
		"Max number of cluster chassis that can connect to this router."
	::= { ax7700rChassis 1 }


ax7700rChassisTable OBJECT-TYPE
	SYNTAX  SEQUENCE OF Ax7700rChassisTableEntry
	ACCESS  not-accessible
	STATUS  mandatory
	DESCRIPTION
		"A table containing chassis information."
	::= { ax7700rChassis 2 }

ax7700rChassisEntry OBJECT-TYPE
	SYNTAX  Ax7700rChassisTableEntry
	ACCESS  not-accessible
	STATUS  mandatory
	DESCRIPTION
		"An entry containing specific chassis."
	INDEX   { ax7700rChassisIndex }
	::= { ax7700rChassisTable 1 }

	Ax7700rChassisTableEntry ::=
		SEQUENCE {
		  ax7700rChassisIndex
			INTEGER,
		  ax7700rChassisType
			INTEGER,
		  ax7700rChassisStatus
			INTEGER,
		  ax7700rBcuBoardDuplexMode
			INTEGER,
		  ax7700rPowerUnitNumber
			INTEGER,
		  ax7700rFanNumber
			INTEGER,
		  ax7700rCifNumber
			INTEGER,
		  ax7700rBcuBoardNumber
			INTEGER,
		  ax7700rPruBoardNumber
			INTEGER,
		  ax7700rNifBoardNumber
			INTEGER
		}

ax7700rChassisIndex OBJECT-TYPE
	SYNTAX  INTEGER
	ACCESS  not-accessible
	STATUS  mandatory
	DESCRIPTION
		"A number to specify ax7700rChassisEntry."
	::= { ax7700rChassisEntry 1 }

ax7700rChassisType OBJECT-TYPE
	SYNTAX  INTEGER {
		other(1),
		ax7702r(300)
      }
	ACCESS  read-only
	STATUS  mandatory
	DESCRIPTION
		"Chassis type of this system."
	::= { ax7700rChassisEntry 2 }

ax7700rChassisStatus OBJECT-TYPE
	SYNTAX  INTEGER {
		up(2)
	      }
	ACCESS  read-only
	STATUS  mandatory
	DESCRIPTION
		"Current status of this chassis."
	::= { ax7700rChassisEntry 3 }

ax7700rBcuBoardDuplexMode OBJECT-TYPE
	SYNTAX  INTEGER {
		rm-Simplex-model(1),
		rm-Duplex-model(2)
	      }
	ACCESS  read-only
	STATUS  mandatory
	DESCRIPTION
		"Duplex mode of BCU Board."
	::= { ax7700rChassisEntry 4 }

ax7700rPowerUnitNumber OBJECT-TYPE
	SYNTAX  INTEGER
	ACCESS  read-only
	STATUS  mandatory
	DESCRIPTION
		"Number of maximum power switches that this router can connect its."
	::= { ax7700rChassisEntry 5 }

ax7700rFanNumber OBJECT-TYPE
	SYNTAX  INTEGER
	ACCESS  read-only
	STATUS  mandatory
	DESCRIPTION
		"The maximum number of fans that can connect to this chassis."
	::= { ax7700rChassisEntry 6 }

ax7700rCifNumber OBJECT-TYPE
	SYNTAX  INTEGER
	ACCESS  read-only
	STATUS  mandatory
	DESCRIPTION
		"Number of cluster interfaces that can connect to this chassis."
	::= { ax7700rChassisEntry 7 }

ax7700rBcuBoardNumber OBJECT-TYPE
	SYNTAX  INTEGER
	ACCESS  read-only
	STATUS  mandatory
	DESCRIPTION
		"Number of BCU boards that can connect to
		this chassis."
	::= { ax7700rChassisEntry 8 }

ax7700rPruBoardNumber OBJECT-TYPE
	SYNTAX  INTEGER
	ACCESS  read-only
	STATUS  mandatory
	DESCRIPTION
		"Number of PRU boards that can connect to
		this chassis."
	::= { ax7700rChassisEntry 9 }

ax7700rNifBoardNumber OBJECT-TYPE
	SYNTAX  INTEGER
	ACCESS  read-only
	STATUS  mandatory
	DESCRIPTION
		"Number of NIF(Network InterFace) boards that can connect to
		this chassis."
	::= { ax7700rChassisEntry 10 }

ax7700rPowerUnitTable OBJECT-TYPE
	SYNTAX  SEQUENCE OF Ax7700rPowerUnitTableEntry
	ACCESS  not-accessible
	STATUS  mandatory
	DESCRIPTION
		"A table containing power unit information."
	::= { ax7700rChassis 3 }

ax7700rPowerUnitEntry OBJECT-TYPE
	SYNTAX  Ax7700rPowerUnitTableEntry
	ACCESS  not-accessible
	STATUS  mandatory
	DESCRIPTION
		"An entry containing power unit information."
	INDEX   { ax7700rChassisIndex,ax7700rPowerUnitIndex }
	::= { ax7700rPowerUnitTable 1 }

	Ax7700rPowerUnitTableEntry ::=
		SEQUENCE {
		  ax7700rPowerUnitIndex
			INTEGER,
		  ax7700rPowerConnectStatus
			INTEGER,
		  ax7700rPowerSupplyStatus
			INTEGER
		}

ax7700rPowerUnitIndex OBJECT-TYPE
	SYNTAX  INTEGER
	ACCESS  not-accessible
	STATUS  mandatory
	DESCRIPTION
		"A number to position of the power units.The value from 1
		to ax7700rPowerUnitNumber."
	::= { ax7700rPowerUnitEntry 1 }

ax7700rPowerConnectStatus OBJECT-TYPE
	SYNTAX  INTEGER {
		connected(2),
		disconnected(32)
	      }
	ACCESS  read-only
	STATUS  mandatory
	DESCRIPTION
		"The current connection status of the power unit."
	::= { ax7700rPowerUnitEntry 2 }

ax7700rPowerSupplyStatus OBJECT-TYPE
	SYNTAX  INTEGER {
		ok(2),
		fault(4)
	      }
	ACCESS  read-only
	STATUS  mandatory
	DESCRIPTION
		"Status of power supply. The value is -1 when Power Supply is disconnected."
	::= { ax7700rPowerUnitEntry 3 }


ax7700rFanTable OBJECT-TYPE
	SYNTAX  SEQUENCE OF Ax7700rFanTableEntry
	ACCESS  not-accessible
	STATUS  mandatory
	DESCRIPTION
		"A table containing fan information."
	::= { ax7700rChassis 4 }

ax7700rFanEntry OBJECT-TYPE
	SYNTAX  Ax7700rFanTableEntry
	ACCESS  not-accessible
	STATUS  mandatory
	DESCRIPTION
		"This entry containing information for a fan."
	INDEX   { ax7700rChassisIndex,ax7700rFanIndex }
	::= { ax7700rFanTable 1 }

	Ax7700rFanTableEntry ::=
		SEQUENCE {
		  ax7700rFanIndex
			INTEGER,
		  ax7700rFanStatus
			INTEGER
		}

ax7700rFanIndex OBJECT-TYPE
	SYNTAX  INTEGER
	ACCESS  not-accessible
	STATUS  mandatory
	DESCRIPTION
		"Index to indicate position of fans."
	::= { ax7700rFanEntry 1 }

ax7700rFanStatus OBJECT-TYPE
	SYNTAX  INTEGER {
		ok(2),
		under-highspeed-rotation(3),
		fault(4)
	      }
	ACCESS  read-only
	STATUS  mandatory
	DESCRIPTION
		"Status of fans."
	::= { ax7700rFanEntry 2 }

ax7700rBcuBoardTable OBJECT-TYPE
	SYNTAX  SEQUENCE OF Ax7700rBcuBoardTableEntry
	ACCESS  not-accessible
	STATUS  mandatory
	DESCRIPTION
		"A table containing BCU boards information."
	::= { ax7700rBcuBoard 1 }

ax7700rBcuBoardEntry OBJECT-TYPE
	SYNTAX  Ax7700rBcuBoardTableEntry
	ACCESS  not-accessible
	STATUS  mandatory
	DESCRIPTION
		"An entry containing BCU boards about specific
		chassis."
	INDEX   { ax7700rChassisIndex,ax7700rBcuBoardIndex }
	::= { ax7700rBcuBoardTable 1 }

	Ax7700rBcuBoardTableEntry ::=
		SEQUENCE {
		  ax7700rBcuBoardIndex
			INTEGER,
		  ax7700rBcuIoBoardType
			INTEGER,
		  ax7700rBcuCpuBoardType
			INTEGER,
		  ax7700rBcuOperStatus
			INTEGER,
		  ax7700rBcuOperModeStatus
			INTEGER,
		  ax7700rBcuActiveLedStatus
			INTEGER,
		  ax7700rBcuReadyLedStatus
			INTEGER,
		  ax7700rBcuAlarmLedStatus
			INTEGER,
		  ax7700rBcuErrorLedStatus
			INTEGER,
		  ax7700rBcuEmaLedStatus
			INTEGER,
		  ax7700rBcuRmEthernetStatus
			INTEGER,
		  ax7700rBcuAtaCardNumber
			INTEGER,
		  ax7700rBcuAtaBootDev
			INTEGER,
		  ax7700rBcuBoardName
			DisplayString,
		  ax7700rBcuBoardAbbreviation
			DisplayString,
		  ax7700rBcuIoBoardProductCode
			INTEGER,
		  ax7700rBcuCpuBoardProductCode
			INTEGER,
		  ax7700rBcuRmCpuName
			DisplayString,
		  ax7700rBcuRmCpuClock
			INTEGER,
		  ax7700rBcuRmMemoryTotalSize
			INTEGER,
		  ax7700rBcuRmMemoryUsedSize
			INTEGER,
		  ax7700rBcuRmMemoryFreeSize
			INTEGER,
		  ax7700rBcuRmRomVersion
			DisplayString,
		  ax7700rBcuRmCpuLoad1m
			INTEGER,
		  ax7700rBcuTemperatureStatusNumber
			INTEGER,
		  ax7700rBcuCpOperStatus
			INTEGER,
		  ax7700rBcuCpCpuName
			DisplayString,
		  ax7700rBcuCpCpuClock
			INTEGER,
		  ax7700rBcuCpMemoryTotalSize
			INTEGER,
		  ax7700rBcuCpCpuLoad1m 
			INTEGER,
		  ax7700rBcuSerialNumber 
			DisplayString,
		  ax7700rBcuVoltage150 
			INTEGER,
		  ax7700rBcuVoltage180 
			INTEGER,
		  ax7700rBcuVoltage250 
			INTEGER,
		  ax7700rBcuVoltage330 
			INTEGER,
		  ax7700rBcuVoltage500 
			INTEGER
		}

ax7700rBcuBoardIndex OBJECT-TYPE
	SYNTAX  INTEGER
	ACCESS  not-accessible
	STATUS  mandatory
	DESCRIPTION
		"Position information of the BCU slot. The value is from 1 to
		ax7700rBcuBoardCardNumber."
	::= { ax7700rBcuBoardEntry  1 }

ax7700rBcuIoBoardType OBJECT-TYPE
	SYNTAX  INTEGER {
		disconnected(-1),
		ax7702r-BCU-RS8MS-IO(776),
		ax7702r-BCU-RS8MS2-IO(777)
		}
	ACCESS  read-only
	STATUS  mandatory
	DESCRIPTION
		"BCU IO board ID.
		The value is -1 when BCU board is disconnected."
	::= { ax7700rBcuBoardEntry  2 }

ax7700rBcuCpuBoardType OBJECT-TYPE
	SYNTAX  INTEGER {
		disconnected(-1),
		bcu-bcu2-CPU(768)
		}
	ACCESS  read-only
	STATUS  mandatory
	DESCRIPTION
		"The value of BCU board ID.
		The value is -1 when BCU board is disconnected."
	::= { ax7700rBcuBoardEntry 3 }

ax7700rBcuOperStatus OBJECT-TYPE
	SYNTAX  INTEGER {
		other(1),
		up(2),
		down(4),
		closed(5),
		disconnect(32)
	      }
	ACCESS  read-only
	STATUS  mandatory
	DESCRIPTION
		"Status of LED on BCU board. The value is 32 when BCU board is
		disconnected."
	::= { ax7700rBcuBoardEntry 4 }

ax7700rBcuOperModeStatus OBJECT-TYPE
	SYNTAX  INTEGER {
		disconnected(-1),
		other(1),
		active(2),
		standby(3),
		do-not-match-with-configure-mode(4),
		do-not-match-with-software-version(5),
		down(6),
		mentenance(7)
	      }
	ACCESS  read-only
	STATUS  mandatory
	DESCRIPTION
		"Operate status on BCU board. The value is -1 when BCU board is
		disconnected."
	::= { ax7700rBcuBoardEntry 5 }

ax7700rBcuActiveLedStatus OBJECT-TYPE
	SYNTAX  INTEGER {
		disconnected(-1),
		green-light-on(2),
		light-off(6)
	      }
	ACCESS  read-only
	STATUS  mandatory
	DESCRIPTION
		"Status of ACTIVE LED on BCU board. The value is -1 when BCU board is
		disconnected or LED status is unknown."
	::= { ax7700rBcuBoardEntry 6 }

ax7700rBcuReadyLedStatus OBJECT-TYPE
	SYNTAX  INTEGER {
		disconnected(-1),
		green-light-on(2),
		light-off(6)
	      }
	ACCESS  read-only
	STATUS  mandatory
	DESCRIPTION
		"Status of READY LED on BCU board. The value is -1 when BCU board is
		disconnected or LED status is unknown."
	::= { ax7700rBcuBoardEntry 7 }

ax7700rBcuAlarmLedStatus OBJECT-TYPE
	SYNTAX  INTEGER {
		disconnected(-1),
		red-light-on(4),
		light-off(6)
	      }
	ACCESS  read-only
	STATUS  mandatory
	DESCRIPTION
		"Status of ALARM LED on BCU board. The value is -1 when BCU board is
		disconnected or LED status is unknown."
	::= { ax7700rBcuBoardEntry 8 }

ax7700rBcuErrorLedStatus OBJECT-TYPE
	SYNTAX  INTEGER {
		disconnected(-1),
		yellow-light-on(5),
		light-off(6)
	      }
	ACCESS  read-only
	STATUS  mandatory
	DESCRIPTION
		"Status of LED ERROR on BCU board. The value is -1 when BCU board is
		disconnected or LED status is unknown."
	::= { ax7700rBcuBoardEntry 9 }

ax7700rBcuEmaLedStatus OBJECT-TYPE
	SYNTAX  INTEGER {
		disconnected(-1),
		yellow-light-on(5),
		light-off(6)
	      }
	ACCESS  read-only
	STATUS  mandatory
	DESCRIPTION
		"Status of LED EMA READY on BCU board. The value is -1 when BCU board is
		disconnected or LED status is unknown."
	::= { ax7700rBcuBoardEntry 10 }

ax7700rBcuRmEthernetStatus OBJECT-TYPE
	SYNTAX  INTEGER {
		disconnected(-1),
		other(1),
		active(2),
		down(4),
		nothing-configuration-or-locked(6),
		maintenance(7),
		test(9),
		unused(10),
		standby(12)
	      }
	ACCESS  read-only
	STATUS  mandatory
	DESCRIPTION
		"Operaion status on BCU ethernet. The value is -1 when BCU board is
		disconnected."
	::= { ax7700rBcuBoardEntry 12 }

ax7700rBcuAtaCardNumber OBJECT-TYPE
	SYNTAX  INTEGER
	ACCESS  read-only
	STATUS  mandatory
	DESCRIPTION
		"Number of slots in ATA card. The value is 0 when BCU board is
		disconnected."
	::= { ax7700rBcuBoardEntry 13 }

ax7700rBcuAtaBootDev OBJECT-TYPE
	SYNTAX  INTEGER {
		disconnected(-1),
		ata-slot0(1),
		ata-slot1(2)
	      }
	ACCESS  read-only
	STATUS  mandatory
	DESCRIPTION
		"The value of ATA slots number when router booted. The value is -1
		when BCU board is disconnected."
	::= { ax7700rBcuBoardEntry 14 }

ax7700rBcuBoardName OBJECT-TYPE
	SYNTAX  DisplayString (SIZE (0..16))
	ACCESS  read-only
	STATUS  mandatory
	DESCRIPTION
		"The product name of RM-IO board.When BCU board is disconnected,
		this will be an OCTET STRING of zero length."
	::= { ax7700rBcuBoardEntry 15 }

ax7700rBcuBoardAbbreviation OBJECT-TYPE
	SYNTAX  DisplayString (SIZE (0..16))
	ACCESS  read-only
	STATUS  mandatory
	DESCRIPTION
		"The abbreviation name of RM-IO board.When BCU board is disconnected,
		this will be an OCTET STRING of zero length."
	::= { ax7700rBcuBoardEntry 16 }

ax7700rBcuIoBoardProductCode OBJECT-TYPE
	SYNTAX  INTEGER
	ACCESS  read-only
	STATUS  mandatory
	DESCRIPTION
		"The manufacturing management number of BCU-IO board.The value is
		-1 when BCU board is disconnected."
	::= { ax7700rBcuBoardEntry 17 }

ax7700rBcuCpuBoardProductCode OBJECT-TYPE
	SYNTAX  INTEGER
	ACCESS  read-only
	STATUS  mandatory
	DESCRIPTION
		"The manufacturing management number of BCU-CPU board.The value is
		-1 when BCU board is disconnected."
	::= { ax7700rBcuBoardEntry 18 }

ax7700rBcuRmCpuName OBJECT-TYPE
	SYNTAX  DisplayString (SIZE (0..16))
	ACCESS  read-only
	STATUS  mandatory
	DESCRIPTION
		"The CPU name of board that load BCU.When BCU board is disconnected,
		this will be an OCTET STRING of zero length."
	::= { ax7700rBcuBoardEntry 19 }

ax7700rBcuRmCpuClock OBJECT-TYPE
	SYNTAX  INTEGER
	ACCESS  read-only
	STATUS  mandatory
	DESCRIPTION
		"The CPU clock of board that load BCU. The value is displayed in
		mega-hertz(MHz). The value is -1 when BCU board is disconnected."
	::= { ax7700rBcuBoardEntry 20 }

ax7700rBcuRmMemoryTotalSize OBJECT-TYPE
	SYNTAX  INTEGER
	ACCESS  read-only
	STATUS  mandatory
	DESCRIPTION
		"Total memory sizes of BCU. The value is displayed in kilobyte(KB).
		The value is -1 when BCU board is disconnected."
	::= { ax7700rBcuBoardEntry 21 }

ax7700rBcuRmMemoryUsedSize OBJECT-TYPE
	SYNTAX  INTEGER
	ACCESS  read-only
	STATUS  mandatory
	DESCRIPTION
		"Using memory sizes of BCU. The value is displayed in kilobyte(KB).
		The value is -1 when BCU board is disconnected."
	::= { ax7700rBcuBoardEntry 22 }

ax7700rBcuRmMemoryFreeSize OBJECT-TYPE
	SYNTAX  INTEGER
	ACCESS  read-only
	STATUS  mandatory
	DESCRIPTION
		"Free memory sizes of BCU. The value is displayed in kilobyte(KB).
		The value is -1 when BCU board is disconnected."
	::= { ax7700rBcuBoardEntry 23 }


ax7700rBcuRmRomVersion OBJECT-TYPE
	SYNTAX  DisplayString (SIZE (0..128))
	ACCESS  read-only
	STATUS  mandatory
	DESCRIPTION
		"The version of Rom on BCU board. When BCU board is disconnected,
		this will be an OCTET STRING of zero length."
	::= { ax7700rBcuBoardEntry 24 }

ax7700rBcuRmCpuLoad1m OBJECT-TYPE
	SYNTAX  INTEGER
	ACCESS  read-only
	STATUS  mandatory
	DESCRIPTION
		"The average, over the last minute, of the percentage of time that
		this processor was utilized to processing and transfer data.
		The value is 0 when BCU board is standby or disconnected."
	::= { ax7700rBcuBoardEntry 25 }

ax7700rBcuTemperatureStatusNumber OBJECT-TYPE
	SYNTAX  INTEGER
	ACCESS  read-only
	STATUS  mandatory
	DESCRIPTION
		"The maximum number of ax7700rTemperatureStatus that can be measurement at this chassis.
		The value is 0 when BCU board doesn't support the temperature measurement function or BCU board is disconnected."
	::= { ax7700rBcuBoardEntry 26 }

ax7700rBcuCpOperStatus OBJECT-TYPE
	SYNTAX  INTEGER {
		other(1),
		active(2),
		initialization(3),
		down(4),
		disconnect(32)
	      }
	ACCESS  read-only
	STATUS  mandatory
	DESCRIPTION
		"The state of CP. other(1),Under Operation(2),Initializing(3),Fault(4),Standby system BCU not implemented(32)"
	::= { ax7700rBcuBoardEntry 27 }

ax7700rBcuCpCpuName OBJECT-TYPE
	SYNTAX  DisplayString (SIZE (0..16))
	ACCESS  read-only
	STATUS  mandatory
	DESCRIPTION
		"The character sequence of the CPU name whose number is a maximum of 16.(ex :MIPS RM5261).Return length 0 if standby system BCR not implemented. "
	::= { ax7700rBcuBoardEntry 28 }

ax7700rBcuCpCpuClock OBJECT-TYPE
	SYNTAX  INTEGER
	ACCESS  read-only
	STATUS  mandatory
	DESCRIPTION
		"The numerical value of a CP CPU clock. unit of measure: MHz (ex:250), it is -1 if standby system BCU not implemented."
	::= { ax7700rBcuBoardEntry 29 }
	
ax7700rBcuCpMemoryTotalSize OBJECT-TYPE
	SYNTAX  INTEGER
	ACCESS  read-only
	STATUS  mandatory
	DESCRIPTION
		"The numerical value of the main memory size of CP. Unit of measure : KByte,(ex : 32768)"
	::= { ax7700rBcuBoardEntry 30 }
	
ax7700rBcuCpCpuLoad1m OBJECT-TYPE
	SYNTAX  INTEGER
	ACCESS  read-only
	STATUS  mandatory
	DESCRIPTION
		"The numerical value(1-100) of CP CPU activity ratio for a minute.If the state of CP is not Under Operation, return 0. If standby system BCU is not implemented return 0."
	::= { ax7700rBcuBoardEntry 33 }
	
ax7700rBcuSerialNumber OBJECT-TYPE
	SYNTAX  DisplayString (SIZE (0..30))
	ACCESS  read-only
	STATUS  mandatory
	DESCRIPTION
		"The character string of the card management information of BCU package whose number is a maximum of 30. Its length is zero if not implemented or closed."
	::= { ax7700rBcuBoardEntry 34 }
	
ax7700rBcuVoltage150 OBJECT-TYPE
	SYNTAX  INTEGER
	ACCESS  read-only
	STATUS  mandatory
	DESCRIPTION
		"The numerical value of the voltage at the observation point of 1.5V voltage. Unit of measure : 10mV (ex : 148)"
	::= { ax7700rBcuBoardEntry 35 }
	
ax7700rBcuVoltage180 OBJECT-TYPE
	SYNTAX  INTEGER
	ACCESS  read-only
	STATUS  mandatory
	DESCRIPTION
		"The numerical value of the voltage at the observation point of 1.8V voltage. Unit of measure : 10mV (ex : 183)"
	::= { ax7700rBcuBoardEntry 36 }
	
ax7700rBcuVoltage250 OBJECT-TYPE
	SYNTAX  INTEGER
	ACCESS  read-only
	STATUS  mandatory
	DESCRIPTION
		"The numerical value of the voltage at the observation point of 2.5V voltage. Unit of measure : 10mV (ex : 250)"
	::= { ax7700rBcuBoardEntry 37 }
	
ax7700rBcuVoltage330 OBJECT-TYPE
	SYNTAX  INTEGER
	ACCESS  read-only
	STATUS  mandatory
	DESCRIPTION
		"The numerical value of the voltage at the observation point of 3.3V voltage. Unit of measure : 10mV (ex : 328)"
	::= { ax7700rBcuBoardEntry 38 }
	
ax7700rBcuVoltage500 OBJECT-TYPE
	SYNTAX  INTEGER
	ACCESS  read-only
	STATUS  mandatory
	DESCRIPTION
		"The numerical value of the voltage at the observation point of 5V voltage. Unit of measure : 10mV (ex : 493)"
	::= { ax7700rBcuBoardEntry 39 }
	
ax7700rAtaCardTable OBJECT-TYPE
	SYNTAX  SEQUENCE OF Ax7700rAtaCardTableEntry
	ACCESS  not-accessible
	STATUS  mandatory
	DESCRIPTION
		"A table containing ATA Card information."
	::= { ax7700rBcuBoard 2 }

ax7700rAtaCardEntry OBJECT-TYPE
	SYNTAX  Ax7700rAtaCardTableEntry
	ACCESS  not-accessible
	STATUS  mandatory
	DESCRIPTION
		"An entry containing ATA Card information."
	INDEX   { ax7700rChassisIndex, ax7700rBcuBoardIndex, ax7700rAtaCardIndex }
	::= { ax7700rAtaCardTable 1 }

	Ax7700rAtaCardTableEntry ::=
		SEQUENCE {
		  ax7700rAtaCardIndex
			INTEGER,
		  ax7700rAtaCardConnection
			INTEGER,
		  ax7700rAtaCardTotalSize
			INTEGER,
		  ax7700rAtaCardUsedSize
			INTEGER,
		  ax7700rAtaCardFreeSize
			INTEGER,
		  ax7700rAtaCardName
			DisplayString,
		  ax7700rAtaCardAbbreviation
			DisplayString,
		  ax7700rAtaCardMountStatus
			INTEGER
		}

ax7700rAtaCardIndex OBJECT-TYPE
	SYNTAX  INTEGER
	ACCESS  not-accessible
	STATUS  mandatory
	DESCRIPTION
		"Connected position of ATA cards.The value is 1 plus slot number
		that ATA card is inserted.The value is from 1 to ax7700rBcuAtaCardNumber."
	::= { ax7700rAtaCardEntry 1 }

ax7700rAtaCardConnection OBJECT-TYPE
	SYNTAX  INTEGER {
		connect(2),
		disconnect(32)
	      }
	ACCESS  read-only
	STATUS  mandatory
	DESCRIPTION
		"Connected status of ATA cards."
	::= { ax7700rAtaCardEntry 2 }

ax7700rAtaCardTotalSize OBJECT-TYPE
	SYNTAX  INTEGER
	ACCESS  read-only
	STATUS  mandatory
	DESCRIPTION
		"Total capacity of ATA cards.The value is displayed in kilobyte
		(kbyte).And the value is -1 when ATA cards is disconnected."
	::= { ax7700rAtaCardEntry 3 }

ax7700rAtaCardUsedSize OBJECT-TYPE
	SYNTAX  INTEGER
	ACCESS  read-only
	STATUS  mandatory
	DESCRIPTION
		"Using capacity of ATA cards.The value is displayed in kilobyte
		(kbyte).And the value is -1 when ATA cards is disconnected."
	::= { ax7700rAtaCardEntry 4 }

ax7700rAtaCardFreeSize OBJECT-TYPE
	SYNTAX  INTEGER
	ACCESS  read-only
	STATUS  mandatory
	DESCRIPTION
		"The rest capacity of ATA card. The value is displayed in kilobyte
		(kbyte). The value is -1 when ATA card is disconnected."
	::= { ax7700rAtaCardEntry 5 }

ax7700rAtaCardName OBJECT-TYPE
	SYNTAX  DisplayString (SIZE (0..16))
	ACCESS  read-only
	STATUS  mandatory
	DESCRIPTION
		"The product name of ATA card. When the ATA card is unknown,
		this OCTET STRING value is 'unknown'. When ATA card is disconnected,
		this will be an OCTET STRING of zero length."
	::= { ax7700rAtaCardEntry 6 }

ax7700rAtaCardAbbreviation OBJECT-TYPE
	SYNTAX  DisplayString (SIZE (0..16))
	ACCESS  read-only
	STATUS  mandatory
	DESCRIPTION
		"The kind of ATA card. When ATA card is disconnected,this will be an
		OCTET STRING of zero length."
	::= { ax7700rAtaCardEntry 7 }

ax7700rAtaCardMountStatus OBJECT-TYPE
	SYNTAX  INTEGER {
		disconnected(-1),
		unmount(1),
  		mount(2)
	      }
	ACCESS  read-only
	STATUS  mandatory
	DESCRIPTION
		"The mount state of ATA card. The value is -1 when ATA card is
		disconnected."
	::= { ax7700rAtaCardEntry 8 }

ax7700rTemperatureStatusTable OBJECT-TYPE
	SYNTAX  SEQUENCE OF Ax7700rTemperatureStatusEntry
	ACCESS  not-accessible
	STATUS  mandatory
	DESCRIPTION
		"The table of ambient temperature status maintained by the
		environmental monitor."
	::= { ax7700rBcuBoard 3 }

ax7700rTemperatureStatusEntry OBJECT-TYPE
	SYNTAX  Ax7700rTemperatureStatusEntry
	ACCESS  not-accessible
	STATUS  mandatory
	DESCRIPTION
		"An entry in the ambient temperature status table, representing
		the status of the associated testpoint maintained by the
		environmental monitor."
	INDEX  { ax7700rChassisIndex, ax7700rBcuBoardIndex, ax7700rTemperatureStatusIndex }
	::= { ax7700rTemperatureStatusTable 1 }

	Ax7700rTemperatureStatusEntry ::=
		SEQUENCE {
		  ax7700rTemperatureStatusIndex
			INTEGER(0..2147483647),
		  ax7700rTemperatureStatusDescr
			DisplayString,
		  ax7700rTemperatureStatusValue
			INTEGER,
		  ax7700rTemperatureThreshold
			INTEGER,
		  ax7700rTemperatureState
			INTEGER
		}

ax7700rTemperatureStatusIndex OBJECT-TYPE
	SYNTAX  INTEGER(0..2147483647)
	ACCESS  not-accessible
	STATUS  mandatory
	DESCRIPTION
		"Unique index for the testpoint being instrumented.
		This index is for SNMP purposes only, and has no
		intrinsic meaning."
	::= { ax7700rTemperatureStatusEntry 1 }

ax7700rTemperatureStatusDescr OBJECT-TYPE
	SYNTAX  DisplayString(SIZE(0..32))
	ACCESS  read-only
	STATUS  mandatory
	DESCRIPTION
		"Textual description of the testpoint being instrumented.
		This description is a short textual label, suitable as a
		human-sensible identification for the rest of the
		information in the entry."
	::= { ax7700rTemperatureStatusEntry 2 }

ax7700rTemperatureStatusValue OBJECT-TYPE
	SYNTAX  INTEGER
	ACCESS  read-only
	STATUS  mandatory
	DESCRIPTION
		"The current measurement of the testpoint being instrumented."
	::= { ax7700rTemperatureStatusEntry 3 }

ax7700rTemperatureThreshold OBJECT-TYPE
	SYNTAX  INTEGER
	ACCESS  read-only
	STATUS  mandatory
	DESCRIPTION
		"The highest value that the associated instance of the
		object ax7700rTemperatureStatusValue may obtain
		before an emergency shutdown of the managed device is
		initiated."
	::= { ax7700rTemperatureStatusEntry 4 }

ax7700rTemperatureState OBJECT-TYPE
	SYNTAX  INTEGER {
		normal(1),
		caution(2),
		warning(3),
		fatal(4)
		}
	ACCESS  read-only
	STATUS  mandatory
	DESCRIPTION
		"The current state of the testpoint being instrumented."
	::= { ax7700rTemperatureStatusEntry 5 }

ax7700rSopTable OBJECT-TYPE
        SYNTAX  SEQUENCE OF Ax7700rSopEntry
        ACCESS  not-accessible
        STATUS  mandatory
        DESCRIPTION
                "A table containing SOP information."
        ::= { ax7700rBcuBoard 4 }

ax7700rSopEntry OBJECT-TYPE
        SYNTAX  Ax7700rSopEntry
        ACCESS  not-accessible
        STATUS  mandatory
        DESCRIPTION
                "An entry containing SOP information."
        INDEX   { ax7700rChassisIndex, ax7700rBcuBoardIndex }
        ::= { ax7700rSopTable 1 }

        Ax7700rSopEntry ::=
                SEQUENCE {
                  ax7700rSopAlarmLevel
                        DisplayString,
                  ax7700rSopAlarmEventPoint
                        DisplayString,
                  ax7700rSopAlarmEventCode
                        DisplayString,
                  ax7700rSopAlarmEventInterfaceID
                        DisplayString,
                  ax7700rSopAlarmMsgText
                        DisplayString
                }

ax7700rSopAlarmLevel OBJECT-TYPE
        SYNTAX  DisplayString
        ACCESS  read-only
        STATUS  mandatory
        DESCRIPTION
                "Error level displayed on a SOP window. When the BCU does not
                support SOP, this will be an OCTET STRING of zero length.
                For information about this code, see:  Operator's Manual."
        ::= { ax7700rSopEntry 1 }

ax7700rSopAlarmEventPoint OBJECT-TYPE
        SYNTAX  DisplayString
        ACCESS  read-only
        STATUS  mandatory
        DESCRIPTION
                "The code displayed on a SOP window, which stands for a device
                part of the factor of the alarm message. When the BCU does not
                support SOP, this will be an OCTET STRING of zero length.
                For information about this code, see:  Operator's Manual."
        ::= { ax7700rSopEntry 2 }

ax7700rSopAlarmEventCode OBJECT-TYPE
        SYNTAX  DisplayString
        ACCESS  read-only
        STATUS  mandatory
        DESCRIPTION
                "Event kind code of alarm message displayed on a SOP window.
                When the BCU does not support SOP, this will be an OCTET STRING
                of zero length. For information about this code, see:  Operator's
                Manual."
        ::= { ax7700rSopEntry 3 }

ax7700rSopAlarmEventInterfaceID OBJECT-TYPE
        SYNTAX  DisplayString
        ACCESS  read-only
        STATUS  mandatory
        DESCRIPTION
                "Interface identification of alarm messages on a SOP window.
                When the BCU does not support SOP, this will be an OCTET STRING
                of zero length. For information about this code, see:  Operator's
                Manual."
        ::= { ax7700rSopEntry 4 }

ax7700rSopAlarmMsgText OBJECT-TYPE
        SYNTAX  DisplayString
        ACCESS  read-only
        STATUS  mandatory
        DESCRIPTION
                "The text of the alarm message on a SOP window. When the BCU does
                not support SOP, this will be an OCTET STRING of zero length.
                For more information about this code, see:  Operator's Manual."
        ::= { ax7700rSopEntry 5 }
	

ax7700rPruBoardTable OBJECT-TYPE
	SYNTAX  SEQUENCE OF Ax7700rPpuBoardTableEntry
	ACCESS  not-accessible
	STATUS  mandatory
	DESCRIPTION
		"A table containing PRU boards information about
		specific chassis."
	::= { ax7700rPruBoard 1 }

ax7700rPruBoardEntry OBJECT-TYPE
	SYNTAX  Ax7700rPpuBoardTableEntry
	ACCESS  not-accessible
	STATUS  mandatory
	DESCRIPTION
		"An entry containing PRU boards about specific
		chassis."
	INDEX   { ax7700rChassisIndex,ax7700rPruBoardIndex }
	::= { ax7700rPruBoardTable 1 }

	Ax7700rPpuBoardTableEntry ::=
		SEQUENCE {
		  ax7700rPruBoardIndex
			INTEGER,
		  ax7700rPruBoardType
			INTEGER,
		  ax7700rPruOperStatus
			INTEGER,
		  ax7700rPruBoardName
			DisplayString,
		  ax7700rPruBoardAbbreviation
			DisplayString,
		  ax7700rPruBoardProductCode
			INTEGER,
		  ax7700rPruSerialNumber
			DisplayString,
		  ax7700rPruVoltage120
			INTEGER,
		  ax7700rPruVoltage150
			INTEGER,
		  ax7700rPruVoltage180
			INTEGER,
		  ax7700rPruVoltage250
			INTEGER,
		  ax7700rPruVoltage330
			INTEGER,
		  ax7700rPruVoltage500
			INTEGER,
		  ax7700rPruVoltage120-2
			INTEGER,
		  ax7700rPruVoltage120-3
			INTEGER,
		  ax7700rPruVoltage120-4
			INTEGER,
		  ax7700rPruVoltage120-5
			INTEGER,
		  ax7700rPruVoltage120-6
			INTEGER,
		  ax7700rPruVoltage120-7
			INTEGER,
		  ax7700rPruVoltage120-8
			INTEGER
		}

ax7700rPruBoardIndex OBJECT-TYPE
	SYNTAX  INTEGER
	ACCESS  not-accessible
	STATUS  mandatory
	DESCRIPTION
		"Position information of the PRU slots. The value is from 1 to
		ax7700rPruBoardNumber."
	::= { ax7700rPruBoardEntry 1 }

ax7700rPruBoardType OBJECT-TYPE
	SYNTAX  INTEGER {
		disconnected(-1),
		pru-e2(18944),
		pru-d2(19200),
		re1-10g4rx(22016),
		rb2-10g4rx(22272)
		}
	ACCESS  read-only
	STATUS  mandatory
	DESCRIPTION
		"PRU boards ID.
        The value is -1 when PRU board is disconnected."
	::= { ax7700rPruBoardEntry 2 }

ax7700rPruOperStatus OBJECT-TYPE
	SYNTAX  INTEGER {
		other(1),
		active(2),
		initialization(3),
		down(4),
		closed(5),
		inactive(6),
		disconnect(32)
	      }
	ACCESS  read-only
	STATUS  mandatory
	DESCRIPTION
		"Operation stasus of PRU board.(STATUS LED)"
	::= { ax7700rPruBoardEntry 3 }

ax7700rPruBoardName OBJECT-TYPE
	SYNTAX  DisplayString (SIZE (0..16))
	ACCESS  read-only
	STATUS  mandatory
	DESCRIPTION
		"PRU board name. When PRU board is disconnected, this will be an OCTET
		STRING of zero length."
	::= { ax7700rPruBoardEntry 4 }

ax7700rPruBoardAbbreviation OBJECT-TYPE
	SYNTAX  DisplayString (SIZE (0..16))
	ACCESS  read-only
	STATUS  mandatory
	DESCRIPTION
		"The abbreviation name of PRU board. When PRU board is disconnected,
		this will be an OCTET STRING of zero length."
	::= { ax7700rPruBoardEntry 5 }

ax7700rPruBoardProductCode OBJECT-TYPE
	SYNTAX  INTEGER
	ACCESS  read-only
	STATUS  mandatory
	DESCRIPTION
		"The revision of PRU board. When PRU board is disconnected,
		this will be -1."
	::= { ax7700rPruBoardEntry 6 }

ax7700rPruSerialNumber OBJECT-TYPE
	SYNTAX  DisplayString (SIZE (0..30))
	ACCESS  read-only
	STATUS  mandatory
	DESCRIPTION
		"The character string of the card management information of PRU package whose number is a maximum of 30. Its length is zero if not implemented or closed."
	::= { ax7700rPruBoardEntry 7 }

ax7700rPruVoltage120 OBJECT-TYPE
	SYNTAX  INTEGER
	ACCESS  read-only
	STATUS  mandatory
	DESCRIPTION
		"The numerical value of the voltage at the observation point of 1.2V voltage. Unit of measure : 10mV (ex : 148) .If PRU is closed or not implemented, return length 0."
	::= { ax7700rPruBoardEntry 8 }

ax7700rPruVoltage150 OBJECT-TYPE
	SYNTAX  INTEGER
	ACCESS  read-only
	STATUS  mandatory
	DESCRIPTION
		"The numerical value of the voltage at the observation point of 1.5V voltage. Unit of measure : 10mV (ex : 148) .If PRU is closed or not implemented, return 0."
	::= { ax7700rPruBoardEntry 9 }

ax7700rPruVoltage180 OBJECT-TYPE
	SYNTAX  INTEGER
	ACCESS  read-only
	STATUS  mandatory
	DESCRIPTION
		"The numerical value of the voltage at the observation point of 1.8V voltage. Unit of measure : 10mV (ex : 183) .If PRU is closed or not implemented, return 0."
	::= { ax7700rPruBoardEntry 10 }

ax7700rPruVoltage250 OBJECT-TYPE
	SYNTAX  INTEGER
	ACCESS  read-only
	STATUS  mandatory
	DESCRIPTION
		"The numerical value of the voltage at the observation point of 2.5V voltage. Unit of measure : 10mV (ex : 250) .If PRU is closed or not implemented, return 0."
	::= { ax7700rPruBoardEntry 11 }

ax7700rPruVoltage330 OBJECT-TYPE
	SYNTAX  INTEGER
	ACCESS  read-only
	STATUS  mandatory
	DESCRIPTION
		"The numerical value of the voltage at the observation point of 3.3V voltage. Unit of measure : 10mV (ex : 328) .If PRU is closed or not implemented, return 0."
	::= { ax7700rPruBoardEntry 12 }

ax7700rPruVoltage500 OBJECT-TYPE
	SYNTAX  INTEGER
	ACCESS  read-only
	STATUS  mandatory
	DESCRIPTION
		"The numerical value of the voltage at the observation point of 5V voltage. Unit of measure : 10mV (ex : 493) .If PRU is closed or not implemented, return 0."
	::= { ax7700rPruBoardEntry 13 }

ax7700rPruVoltage120-2 OBJECT-TYPE
	SYNTAX  INTEGER
	ACCESS  read-only
	STATUS  mandatory
	DESCRIPTION
		"The numerical value of the voltage at the observation point of 1.2V voltage. Unit of measure : 10mV (ex : 123) .If PRU is closed or not implemented, return 0."
	::= { ax7700rPruBoardEntry 14 }

ax7700rPruVoltage120-3 OBJECT-TYPE
	SYNTAX  INTEGER
	ACCESS  read-only
	STATUS  mandatory
	DESCRIPTION
		"The numerical value of the voltage at the observation point of 1.2V voltage. Unit of measure : 10mV (ex : 123) .If PRU is closed or not implemented, return 0."
	::= { ax7700rPruBoardEntry 15 }

ax7700rPruVoltage120-4 OBJECT-TYPE
	SYNTAX  INTEGER
	ACCESS  read-only
	STATUS  mandatory
	DESCRIPTION
		"The numerical value of the voltage at the observation point of 1.2V voltage. Unit of measure : 10mV (ex : 123) .If PRU is closed or not implemented, return 0."
	::= { ax7700rPruBoardEntry 16 }

ax7700rPruVoltage120-5 OBJECT-TYPE
	SYNTAX  INTEGER
	ACCESS  read-only
	STATUS  mandatory
	DESCRIPTION
		"The numerical value of the voltage at the observation point of 1.2V voltage. Unit of measure : 10mV (ex : 123) .If PRU is closed or not implemented, return 0."
	::= { ax7700rPruBoardEntry 17 }

ax7700rPruVoltage120-6 OBJECT-TYPE
	SYNTAX  INTEGER
	ACCESS  read-only
	STATUS  mandatory
	DESCRIPTION
		"The numerical value of the voltage at the observation point of 1.2V voltage. Unit of measure : 10mV (ex : 123) .If PRU is closed or not implemented, return 0."
	::= { ax7700rPruBoardEntry 18 }

ax7700rPruVoltage120-7 OBJECT-TYPE
	SYNTAX  INTEGER
	ACCESS  read-only
	STATUS  mandatory
	DESCRIPTION
		"The numerical value of the voltage at the observation point of 1.2V voltage. Unit of measure : 10mV (ex : 123) .If PRU is closed or not implemented, return 0."
	::= { ax7700rPruBoardEntry 19 }

ax7700rPruVoltage120-8 OBJECT-TYPE
	SYNTAX  INTEGER
	ACCESS  read-only
	STATUS  mandatory
	DESCRIPTION
		"The numerical value of the voltage at the observation point of 1.2V voltage. Unit of measure : 10mV (ex : 123) .If PRU is closed or not implemented, return 0."
	::= { ax7700rPruBoardEntry 20 }

ax7700rNifBoardTable OBJECT-TYPE
	SYNTAX  SEQUENCE OF Ax7700rNifBoardTableEntry
	ACCESS  not-accessible
	STATUS  mandatory
	DESCRIPTION
		"A table containing Network Interface cards (NIF) information that
		slot is loaded."
	::= { ax7700rNifBoard 1 }

ax7700rNifBoardEntry OBJECT-TYPE
	SYNTAX  Ax7700rNifBoardTableEntry
	ACCESS  not-accessible
	STATUS  mandatory
	DESCRIPTION
		"An entry containing NIF information about specific chassis."
        INDEX   { ax7700rChassisIndex,ax7700rNifBoardSlotIndex }
	::= { ax7700rNifBoardTable 1 }

	Ax7700rNifBoardTableEntry ::=
		SEQUENCE {
		  ax7700rNifBoardSlotIndex
			INTEGER,
		  ax7700rNifBoardType
			INTEGER,
		  ax7700rNifBoardOperStatus
			INTEGER,
		  ax7700rNifBoardName
			DisplayString,
		  ax7700rNifBoardAbbreviation
			DisplayString,
		  ax7700rNifBoardProductCode
			INTEGER,
		  ax7700rNifPhysLineNumber
			INTEGER,
                  ax7700rNifSerialNumber
                        DisplayString,
		  ax7700rNifVoltageAM520
			INTEGER,
		  ax7700rNifVoltage150
			INTEGER,
		  ax7700rNifVoltage180
			INTEGER,
		  ax7700rNifVoltageA180
			INTEGER,
		  ax7700rNifVoltage250
			INTEGER,
		  ax7700rNifVoltage330
			INTEGER,
		  ax7700rNifVoltageA330
			INTEGER,
		  ax7700rNifVoltageA500
			INTEGER,
		  ax7700rNifVoltage330S
			INTEGER,
		  ax7700rNifVoltage500S
			INTEGER,
		  ax7700rNifVoltageA500-2
			INTEGER,
		  ax7700rNifVoltage150S
			INTEGER,
		  ax7700rNifVoltage110
			INTEGER
		}

ax7700rNifBoardSlotIndex OBJECT-TYPE
	SYNTAX  INTEGER
	ACCESS  not-accessible
	STATUS  mandatory
	DESCRIPTION
		"Position information of NIF loading slot. The value is from 1
		to ax7700rNifBoardNumber."
	::= { ax7700rNifBoardEntry 1 }

ax7700rNifBoardType OBJECT-TYPE
	SYNTAX  INTEGER {
		disconnected(-1),
		other(1),
		nif-12-port-1000BASE-X-SFP-VRRP(32770),
		nif-6-port-1000BASE-X-GBIC-VRRP(32772),
		nif-12-port-10BASE-T-100BASE-TX-1000BASE-T-VRRP(32778),
		nif-8-port-1000BASE-X-SHAPER(32782),
		nif-4-port-1000BASE-X-SHAPER(32783),
		nif-1-port-10GBASE-ER(32786),
		nif-1-port-10GBASE-R-XFP(32788),
		nif-4-port-10GBASE-R-XFP-PRUE1(32789),
		nif-1-port-10GBASE-R-XFPA(32792),
		nif-1-port-10GBASE-LW(32801),
		nif-1-port-10GBASE-EW(32802),
		nif-48-port-10BASE-T-100BASE-TX-1000BASE-T(32822),
		nif-8-port-10-100-1000BASE-T-plus-4-port-1000BASE-X-SFP(32823),
		nif-1-port-OC192c-STM-64-POS-2km(40960),
		nif-1-port-OC192c-STM-64-POS-40km(40961),
		nif-4-port-OC48c-STM-16-POS(40976)
		}
	ACCESS  read-only
	STATUS  mandatory
	DESCRIPTION
		"Type of connecting package.The value is register value of NIF package.
		The value is -1 when PRU is disconnected or NIF disconnected."
	::= { ax7700rNifBoardEntry 2 }

ax7700rNifBoardOperStatus OBJECT-TYPE
	SYNTAX  INTEGER {
		other(1),
		active(2),
		initialization(3),
		down(4),
		closed(5),
		lock(6),
		disconnect(32)
	      }
	ACCESS  read-only
	STATUS  mandatory
	DESCRIPTION
		"Operation status of Network InterFace(NIF) board.(STATUS LED)"
	::= { ax7700rNifBoardEntry 3 }

ax7700rNifBoardName OBJECT-TYPE
	SYNTAX  DisplayString (SIZE (0..16))
	ACCESS  read-only
	STATUS  mandatory
	DESCRIPTION
		"Network InterFace(NIF) board name. When PRU board or NIF board is
		disconnected,this will be an OCTET STRING of zero length."
	::= { ax7700rNifBoardEntry 4 }

ax7700rNifBoardAbbreviation OBJECT-TYPE
	SYNTAX  DisplayString (SIZE (0..16))
	ACCESS  read-only
	STATUS  mandatory
	DESCRIPTION
		"The abbreviation name of Network InterFace(NIF) board. When PRU board
		or NIF board is disconnected, this will be an OCTET STRING of zero
		length."
	::= { ax7700rNifBoardEntry 5 }

ax7700rNifBoardProductCode OBJECT-TYPE
	SYNTAX  INTEGER
	ACCESS  read-only
	STATUS  mandatory
	DESCRIPTION
		"The product management code of Network InterFace(NIF) board.The value
		is -1 when PRU board or NIF board is disconncted."
	::= { ax7700rNifBoardEntry 6 }

ax7700rNifPhysLineNumber OBJECT-TYPE
	SYNTAX  INTEGER
	ACCESS  read-only
	STATUS  mandatory
	DESCRIPTION
		"Number of Network InterFace(NIF)'s physical port.The max is 8.
		The value is -1 when value of ax7700rNifCardType is -1 or other(1)."
	::= { ax7700rNifBoardEntry 7 }

ax7700rNifSerialNumber OBJECT-TYPE
        SYNTAX  DisplayString (SIZE (0..30))
        ACCESS  read-only
        STATUS  mandatory
        DESCRIPTION
                "Management information (SerialNumber) of Network InterFace(NIF) package.
                It shows by the character string of 30 characters or less.
                When PRU board or NIF board is disconnected or closed, this will be an OCTET STRING of zero length."
        ::= { ax7700rNifBoardEntry 8 }

ax7700rNifVoltageAM520 OBJECT-TYPE
        SYNTAX  INTEGER
        ACCESS  read-only
        STATUS  mandatory
        DESCRIPTION
                "The numerical value of the voltage at the observation point of -5.2V voltage. Unit of measure : 10mV (ex : -512) .If PRU or NIF is closed or not implemented, return 0."
        ::= { ax7700rNifBoardEntry 9 }

ax7700rNifVoltage150 OBJECT-TYPE
        SYNTAX  INTEGER
        ACCESS  read-only
        STATUS  mandatory
        DESCRIPTION
                "The numerical value of the voltage at the observation point of -1.5V voltage. Unit of measure : 10mV (ex : 148) .If PRU or NIF is closed or not implemented, return 0."
        ::= { ax7700rNifBoardEntry 10 }

ax7700rNifVoltage180 OBJECT-TYPE
        SYNTAX  INTEGER
        ACCESS  read-only
        STATUS  mandatory
        DESCRIPTION
                "The numerical value of the voltage at the observation point of 1.8V voltage. Unit of measure : 10mV (ex : 183) .If PRU or NIF is closed or not implemented, return 0."
        ::= { ax7700rNifBoardEntry 11 }

ax7700rNifVoltageA180 OBJECT-TYPE
        SYNTAX  INTEGER
        ACCESS  read-only
        STATUS  mandatory
        DESCRIPTION
                "The numerical value of the voltage at the observation point of analog 1.8V voltage. Unit of measure : 10mV (ex : 183) .If PRU or NIF is closed or not implemented, return 0."
        ::= { ax7700rNifBoardEntry 12 }

ax7700rNifVoltage250 OBJECT-TYPE
        SYNTAX  INTEGER
        ACCESS  read-only
        STATUS  mandatory
        DESCRIPTION
                "The numerical value of the voltage at the observation point of  analogu 2.5V voltage. Unit of measure : 10mV (ex : 250) .If PRU or NIF is closed or not implemented, return 0."
        ::= { ax7700rNifBoardEntry 13 }

ax7700rNifVoltage330 OBJECT-TYPE
        SYNTAX  INTEGER
        ACCESS  read-only
        STATUS  mandatory
        DESCRIPTION
                "The numerical value of the voltage at the observation point of  analogu 3.3V voltage. Unit of measure : 10mV (ex : 328) .If PRU or NIF is closed or not implemented, return 0."
        ::= { ax7700rNifBoardEntry 14 }

ax7700rNifVoltageA330 OBJECT-TYPE
        SYNTAX  INTEGER
        ACCESS  read-only
        STATUS  mandatory
        DESCRIPTION
                "The numerical value of the voltage at the observation point of analog 3.3V voltage. Unit of measure : 10mV (ex : 328) .If PRU or NIF is closed or not implemented, return 0."
        ::= { ax7700rNifBoardEntry 15 }

ax7700rNifVoltageA500 OBJECT-TYPE
        SYNTAX  INTEGER
        ACCESS  read-only
        STATUS  mandatory
        DESCRIPTION
                "The numerical value of the voltage at the observation point of analog 5V voltage. Unit of measure : 10mV (ex : 493) .If PRU or NIF is closed or not implemented, return 0."
        ::= { ax7700rNifBoardEntry 16 }

ax7700rNifVoltage330S OBJECT-TYPE
        SYNTAX  INTEGER
        ACCESS  read-only
        STATUS  mandatory
        DESCRIPTION
                "The numerical value of the voltage at the observation point of 3.3V voltage. Unit of measure : 10mV (ex : 328) .If PRU or NIF is closed or not implemented, return 0."
        ::= { ax7700rNifBoardEntry 17 }

ax7700rNifVoltage500S OBJECT-TYPE
        SYNTAX  INTEGER
        ACCESS  read-only
        STATUS  mandatory
        DESCRIPTION
                "The numerical value of the voltage at the observation point of 5V voltage. Unit of measure : 10mV (ex : 493) .If PRU or NIF is closed or not implemented, return 0."
        ::= { ax7700rNifBoardEntry 18 }

ax7700rNifVoltageA500-2 OBJECT-TYPE
        SYNTAX  INTEGER
        ACCESS  read-only
        STATUS  mandatory
        DESCRIPTION
                "The numerical value of the voltage at the observation point of 5V voltage. Unit of measure : 10mV (ex : 493) .If PRU or NIF is closed or not implemented, return 0."
        ::= { ax7700rNifBoardEntry 20 }

ax7700rNifVoltage150S OBJECT-TYPE
        SYNTAX  INTEGER
        ACCESS  read-only
        STATUS  mandatory
        DESCRIPTION
                "The numerical value of the voltage at the observation point of 1.5V voltage. Unit of measure : 10mV (ex : 148) .If PRU or NIF is closed or not implemented, return 0."
        ::= { ax7700rNifBoardEntry 21 }

ax7700rNifVoltage110 OBJECT-TYPE
        SYNTAX  INTEGER
        ACCESS  read-only
        STATUS  mandatory
        DESCRIPTION
                "The numerical value of the voltage at the observation point of 1.15V voltage. Unit of measure : 10mV (ex : 117) .If PSU or NIF is closed or not implemented, return 0."
        ::= { ax7700rNifBoardEntry 23 }

ax7700rPhysLineTable OBJECT-TYPE
	SYNTAX  SEQUENCE OF Ax7700rPhysLineTableEntry
	ACCESS  not-accessible
	STATUS  mandatory
	DESCRIPTION
		"A table containing physical port information."
	::= { ax7700rPhysLine 1 }

ax7700rPhysLineEntry OBJECT-TYPE
	SYNTAX  Ax7700rPhysLineTableEntry
	ACCESS  not-accessible
	STATUS  mandatory
	DESCRIPTION
		"An entry containing physical port."
	INDEX   { ax7700rChassisIndex, ax7700rNifBoardSlotIndex, ax7700rPhysLineIndex }
	::= { ax7700rPhysLineTable 1 }

	Ax7700rPhysLineTableEntry ::=
		SEQUENCE {
		  ax7700rPhysLineIndex
			INTEGER,
		  ax7700rPhysLineConnectorType
			INTEGER,
		  ax7700rPhysLineOperStatus
			INTEGER,
		  ax7700rPhysLineIfIndexNumber
			INTEGER,
		  ax7700rPhysLineTransceiverStatus
		    INTEGER
		}

ax7700rPhysLineIndex OBJECT-TYPE
	SYNTAX  INTEGER
	ACCESS  not-accessible
	STATUS  mandatory
	DESCRIPTION
		"Physical port number. The value is from 1 to ax7700rNifLineNumber."
	::= { ax7700rPhysLineEntry 1 }

ax7700rPhysLineConnectorType OBJECT-TYPE
	SYNTAX  INTEGER {
		disconnected(-1),
		other(1),
		typeOC-48c-STM-16-POS-2km(103),
		typeOC-48c-STM-16-POS-40km(104),
		type1000BASE-LX(301),
		type1000BASE-SX(302),
		type1000BASE-LH(303),
		type1000BASE-LHB(310),
		type10GBASE-SR(401),
		type10GBASE-LR(402),
		type10GBASE-ER(403),
		type10GBASE-ZR(404)
		}
	ACCESS  read-only
	STATUS  mandatory
	DESCRIPTION
		"Connector type is connected physical port. The value is 1(other)
		when connector is disconnected or connector type is unknown.When
		displaying in pannel, requests board name of NIF,then will display it.
		The value is -1	when PRU or NIF board is disconnected."
	::= { ax7700rPhysLineEntry 2 }

ax7700rPhysLineOperStatus OBJECT-TYPE
	SYNTAX  INTEGER {
		disconnected(-1),
		other(1),
		active(2),
		initialization(3),
		down(4),
		lock(6),
		close(7),
		line-fault(8),
		test(9),
		nothing-configuration(10),
		missing-configuration(11),
		remote-loop-back-test-mode(12)
	      }
	ACCESS  read-only
	STATUS  mandatory
	DESCRIPTION
		"Status of physical port. The value is -1 when PRU or NIF board is
		disconnected."
	::= { ax7700rPhysLineEntry 3 }

ax7700rPhysLineIfIndexNumber OBJECT-TYPE
	SYNTAX  INTEGER
	ACCESS  read-only
	STATUS  mandatory
	DESCRIPTION
		"Number of ifIndex which is included in physical port.The value is -1
		when PRU board or NIF board is disconnected."
	::= { ax7700rPhysLineEntry 4 }

ax7700rPhysLineTransceiverStatus OBJECT-TYPE
	SYNTAX  INTEGER{
				gbic-mounted(10),
				gbic-unmounted(11),
				unsupported-gbic-mounted(12),
				gbic-status-unknown(13),
				sfp-mounted(20),
				sfp-unmounted(21),
				unsupported-sfp-mounted(22),
				sfp-status-unknown(23),
				xfp-mounted(30),
				xfp-unmounted(31),
				unsupported-xfp-mounted(32),
				xfp-status-unknown(33)
			}
	ACCESS  read-only
	STATUS  mandatory
	DESCRIPTION
		"Type and status of replaceable transceiver."
	::= { ax7700rPhysLineEntry 5 }
	
-- 

ax7700rLineIfTable OBJECT-TYPE
	SYNTAX  SEQUENCE OF Ax7700rLineIfTableEntry
	ACCESS  not-accessible
	STATUS  mandatory
	DESCRIPTION
		"A table containing physical port correspond to ifIndex."
	::= { ax7700rInterface 1 }

ax7700rLineIfEntry OBJECT-TYPE
	SYNTAX  Ax7700rLineIfTableEntry
	ACCESS  not-accessible
	STATUS  mandatory
	DESCRIPTION
		"An entry containing ifIndex is assigned to physical port."
	INDEX   { ax7700rChassisIndex, ax7700rNifBoardSlotIndex, ax7700rPhysLineIndex, ax7700rLineIfIndex }
	::= { ax7700rLineIfTable 1 }

	Ax7700rLineIfTableEntry ::=
		SEQUENCE {
		  ax7700rLineIfIndex
			INTEGER,
		  ax7700rIfIndex
			INTEGER,
		  ax7700rIfIpAddress
			IpAddress,
		  ax7700rIfIpv6Address
			OCTET STRING
		}

ax7700rLineIfIndex OBJECT-TYPE
	SYNTAX  INTEGER
	ACCESS  not-accessible
	STATUS  mandatory
	DESCRIPTION
		"The value of ifIndex to distinguish entry of this table.The value is
		from 1 to ax7700rPhysLineIfIndexNumber."
	::= { ax7700rLineIfEntry 1 }

ax7700rIfIndex OBJECT-TYPE
	SYNTAX  INTEGER
	ACCESS  read-only
	STATUS  mandatory
	DESCRIPTION
		"The value of ifIndex which is assigned to this physical port.
		The value is 0 when ifIndex is not assigned to this physical port."
	::= { ax7700rLineIfEntry 2 }

ax7700rIfIpAddress OBJECT-TYPE
	SYNTAX  IpAddress
	ACCESS  read-only
	STATUS  mandatory
	DESCRIPTION
		"The IP address correspond to ifIndex which is assigned to this
		physical port. If IP address is not assigned, it is '0.0.0.0'."
	::= { ax7700rLineIfEntry 3 }

ax7700rIfIpv6Address OBJECT-TYPE
	SYNTAX  OCTET STRING
	ACCESS  read-only
	STATUS  mandatory
	DESCRIPTION
		"The IPv6 address correspond to ifIndex which is assigned to this
		physical port. If IPv6 address is not assigned,
		it is '00 00 00 00 00 00 00 00 00 00 00 00 00 00 00 00'."
	::= { ax7700rLineIfEntry 4 }

-- Traps for use by AlaxalA networks AXR

-- Traps are defined using the conventions in RFC 1215.

axrIsisAdjacencyChange TRAP-TYPE
	ENTERPRISE      axrIsisNotifications
	VARIABLES       { axrIsisSysInstance, axrIsisSysLevelIndex, axrIsisCircIndex, axrIsisPduLspId, axrIsisAdjState }
	DESCRIPTION
		"IS-IS Contiguity router state change"
	::= 17

axrStaticGatewayStateChange TRAP-TYPE
	ENTERPRISE      axrStaticTrap
	VARIABLES       { axrStaticGatewayAddr, axrStaticGatewayState }
	DESCRIPTION
		"static route gateway state change."
	::= 1

axrStaticIpv6GatewayStateChange TRAP-TYPE
	ENTERPRISE      axrStaticTrap
	VARIABLES       { axrStaticIpv6Ifindex, axrStaticIpv6GatewayAddr, axrStaticIpv6GatewayState }
	DESCRIPTION
		"ipv6 static route gateway state change."
	::= 2



axrOspfVirtIfStateChange TRAP-TYPE
	ENTERPRISE      axrOspfTraps
	VARIABLES       { axrOspfVirtIfDomainNumber, axrOspfRouterId, axrOspfVirtIfAreaId, axrOspfVirtIfNeighbor, axrOspfVirtIfState }
	DESCRIPTION
		"An axrOspfIfStateChange trap signifies that there has  been a change 
		in the state of an OSPF virtual interface."
	::= 1

axrOspfNbrStateChange TRAP-TYPE
	ENTERPRISE      axrOspfTraps
	VARIABLES       { axrOspfNbrDomainNumber, axrOspfRouterId, axrOspfNbrIpAddr, axrOspfNbrAddressLessIndex, axrOspfNbrRtrId, axrOspfNbrState }
	DESCRIPTION
           "An axrOspfNbrStateChange trap signifies that
           there  has been a change in the state of a non-
           virtual OSPF neighbor.   This  trap  should  be
           generated  when  the  neighbor  state regresses
           (e.g., goes from Attempt or Full  to  1-Way  or
           Down)  or progresses to a terminal state (e.g.,
           2-Way or Full).  When an  neighbor  transitions
           from  or  to Full on non-broadcast multi-access
           and broadcast networks, the trap should be gen-
           erated  by the designated router.  A designated
           router transitioning to Down will be  noted  by
           axrOspfIfStateChange."
	::= 2

axrOspfVirtNbrStateChange TRAP-TYPE
	ENTERPRISE      axrOspfTraps
	VARIABLES       { axrOspfVirtNbrDomainNumber, axrOspfRouterId, axrOspfVirtNbrArea, axrOspfVirtNbrRtrId, axrOspfVirtNbrState }
	DESCRIPTION
           "An axrOspfIfStateChange trap signifies that there
           has  been a change in the state of an OSPF vir-
           tual neighbor.  This trap should  be  generated
           when  the  neighbor state regresses (e.g., goes
           from Attempt or  Full  to  1-Way  or  Down)  or
           progresses to a terminal state (e.g., Full)."
	::= 3

axrOspfIfConfigError TRAP-TYPE
	ENTERPRISE      axrOspfTraps
	VARIABLES       { axrOspfIfDomainNumber, axrOspfRouterId, axrOspfIfIpAddress, axrOspfAddressLessIf, axrOspfPacketSrc, axrOspfConfigErrorType, axrOspfPacketType }
	DESCRIPTION
           "An axrOspfIfConfigError  trap  signifies  that  a
           packet  has  been received on a non-virtual in-
           terface  from  a  router  whose   configuration
           parameters  conflict  with this router's confi-
           guration parameters.  Note that the  event  op-
           tionMismatch  should  cause  a  trap only if it
           prevents an adjacency from forming."
	::= 4

axrOspfVirtIfConfigError TRAP-TYPE
	ENTERPRISE      axrOspfTraps
	VARIABLES       { axrOspfVirtIfDomainNumber, axrOspfRouterId, axrOspfVirtIfAreaId, axrOspfVirtIfNeighbor, axrOspfConfigErrorType, axrOspfPacketType }
	DESCRIPTION
           "An axrOspfConfigError trap signifies that a pack-
           et  has  been  received  on a virtual interface
           from a router  whose  configuration  parameters
           conflict   with   this  router's  configuration
           parameters.  Note that the event optionMismatch
           should  cause a trap only if it prevents an ad-
           jacency from forming."
	::= 5

axrOspfIfAuthFailure TRAP-TYPE
	ENTERPRISE      axrOspfTraps
	VARIABLES       { axrOspfIfDomainNumber, axrOspfRouterId, axrOspfIfIpAddress, axrOspfAddressLessIf, axrOspfPacketSrc, axrOspfConfigErrorType, axrOspfPacketType }
	DESCRIPTION
           "An axrOspfIfAuthFailure  trap  signifies  that  a
           packet  has  been received on a non-virtual in-
           terface from a router whose authentication  key
           or  authentication  type  conflicts  with  this
           router's authentication key  or  authentication
           type."
	::= 6

axrOspfVirtIfAuthFailure TRAP-TYPE
	ENTERPRISE      axrOspfTraps
	VARIABLES       { axrOspfVirtIfDomainNumber, axrOspfRouterId, axrOspfVirtIfAreaId, axrOspfVirtIfNeighbor, axrOspfConfigErrorType, axrOspfPacketType }
	DESCRIPTION
           "An axrOspfVirtIfAuthFailure trap signifies that a
           packet has been received on a virtual interface
           from a router whose authentication key  or  au-
           thentication  type conflicts with this router's
           authentication key or authentication type."
	::= 7

axrOspfIfStateChange TRAP-TYPE
	ENTERPRISE      axrOspfTraps
	VARIABLES       { axrOspfIfDomainNumber, axrOspfRouterId, axrOspfIfIpAddress, axrOspfAddressLessIf, axrOspfIfState }
	DESCRIPTION
           "An axrOspfIfStateChange trap signifies that there
           has been a change in the state of a non-virtual
           OSPF interface. This trap should  be  generated
           when  the interface state regresses (e.g., goes
           from Dr to Down) or progresses  to  a  terminal
           state  (i.e.,  Point-to-Point, DR Other, Dr, or
           Backup)."
	::= 16 

axrOadpNeighborCachelastChangeTrap TRAP-TYPE
	ENTERPRISE      axrOadpMIBNotifications
	VARIABLES       { axrOadpNeighborCacheLastChange }
	DESCRIPTION
           "This trap indicates that information of OADP neighbor nodes is updated."
	::= 1 

axrPimNeighborFound TRAP-TYPE
	ENTERPRISE      axrPimMIBObjects
	VARIABLES       { pimNeighborIfIndex }
	DESCRIPTION
             "This trap indicates that PIM neighbor found."
	::= 1

axrPimNeighborLoss TRAP-TYPE
	ENTERPRISE      axrPimMIBObjects
	VARIABLES       { pimNeighborIfIndex }
	DESCRIPTION
             "This trap indicates that PIM neighbor lost."
	::= 2
END


-- Traps for use by AlaxalA networks AX7800R

-- Traps are defined using the conventions in RFC 1215.
AX7800R-TRAP DEFINITIONS ::= BEGIN
IMPORTS
TRAP-TYPE
    FROM RFC-1215
ifIndex
    FROM RFC1213-MIB
ax7800r, ax7800rSystemMsgType, ax7800rSystemMsgTimeStamp, ax7800rSystemMsgLevel, ax7800rSystemMsgEventPoint,
ax7800rSystemMsgEventInterfaceID, ax7800rSystemMsgEventCode, ax7800rSystemMsgAdditionalCode, ax7800rSystemMsgText,
ax7800rChassisIndex, ax7800rBcuBoardIndex, ax7800rTemperatureStatusIndex, ax7800rTemperatureStatusDescr, 
ax7800rTemperatureStatusValue, ax7800rTemperatureState,
axrLoginName, axrLoginTime, axrLoginLocation, axrLoginLine, axrLoginFailureTime, axrLogoutTime, axrLogoutStatus,ax7800rNifBoardSlotIndex
    FROM AX7800R
;

ax7800rSystemMsgTrap TRAP-TYPE
	ENTERPRISE      ax7800r
	VARIABLES       { ax7800rSystemMsgType, ax7800rSystemMsgTimeStamp,
                          ax7800rSystemMsgLevel, ax7800rSystemMsgEventPoint,
                          ax7800rSystemMsgEventInterfaceID, ax7800rSystemMsgEventCode,
                          ax7800rSystemMsgAdditionalCode, ax7800rSystemMsgText }
	DESCRIPTION
		"System message is displayed."
	::= 1

ax7800rStandbySystemUpTrap TRAP-TYPE
	ENTERPRISE      ax7800r
	VARIABLES       { ax7800rChassisIndex, ax7800rBcuBoardIndex }
	DESCRIPTION
		"Standby system is restarted."
	::= 2

ax7800rStandbySystemDownTrap TRAP-TYPE
	ENTERPRISE      ax7800r
	VARIABLES       { ax7800rChassisIndex, ax7800rBcuBoardIndex }
	DESCRIPTION
		"Standby system is failed."
	::= 3

ax7800rTemperatureTrap TRAP-TYPE
	ENTERPRISE ax7800r
	VARIABLES {
		ax7800rChassisIndex,
		ax7800rBcuBoardIndex,
		ax7800rTemperatureStatusIndex,
		ax7800rTemperatureStatusDescr, 
		ax7800rTemperatureStatusValue, 
		ax7800rTemperatureState }
	DESCRIPTION
		"A ax7800rTemperatureTrap is sent if the 
		temperature measured at a given testpoint is outside 
		the normal range for the testpoint (i.e. is at the warning, 
		critical, or shutdown stage)."
	::= 4

ax7800rAirFanStopTrap TRAP-TYPE
	ENTERPRISE      ax7800r
	DESCRIPTION
             "This trap indicates a fan failure." 
	::= 8 

ax7800rPowerSupplyFailureTrap TRAP-TYPE
	ENTERPRISE      ax7800r
	DESCRIPTION
             "This trap indicates one ( or more ) of power supplies failure." 
	::= 9 

ax7800rLoginSuccessTrap TRAP-TYPE
	ENTERPRISE      ax7800r
	VARIABLES       { axrLoginName, axrLoginTime, axrLoginLocation, axrLoginLine }
	DESCRIPTION
             "This trap indicates success of user log in." 
	::= 10 

ax7800rLoginFailureTrap TRAP-TYPE
	ENTERPRISE      ax7800r
	VARIABLES       { axrLoginName, axrLoginFailureTime, 
                          axrLoginLocation, axrLoginLine }
	DESCRIPTION
             "This trap indicates failure of user log in." 
	::= 11

ax7800rLogoutTrap TRAP-TYPE
	ENTERPRISE      ax7800r
	VARIABLES       { axrLoginName, axrLoginTime, axrLogoutTime, 
                          axrLoginLocation, axrLoginLocation, axrLoginLine, 
                          axrLogoutStatus }
	DESCRIPTION
             "This trap indicates success of following log out.
	       'logout' command, 'exit' command, 'quit' command."
	::= 12

ax7800rMemoryUsageTrap  TRAP-TYPE
	ENTERPRISE      ax7800r
	DESCRIPTION
             "This indicates available memory is fewer than lower limit." 
	::= 13

ax7800rFrameErrorReceiveTrap  TRAP-TYPE
	ENTERPRISE      ax7800r
	VARIABLES       { ifIndex }
	DESCRIPTION
             "This indicates frame receive error." 
	::= 18

ax7800rFrameErrorSendTrap  TRAP-TYPE
	ENTERPRISE      ax7800r
	VARIABLES       { ifIndex }
	DESCRIPTION
             "This indicates frame send error." 
	::= 19

-- axrEfmoamUdldPortInactivateTrap TRAP-TYPE
ax7800rEfmoamUdldPortInactivateTrap TRAP-TYPE
	ENTERPRISE      ax7800r
	VARIABLES       { ifIndex }
	DESCRIPTION
             "Efmoam udld port inactivate trap."
	::= 29

-- axrEfmoamLoopDetectPortInactivateTrap TRAP-TYPE
ax7800rEfmoamLoopDetectPortInactivateTrap TRAP-TYPE
	ENTERPRISE      ax7800r
	VARIABLES       { ifIndex }
	DESCRIPTION
             "Efmoam loop detect port inactivate trap."
	::= 30

END
-- Traps for use by AlaxalA networks AX7700R

-- Traps are defined using the conventions in RFC 1215.
AX7700R-TRAP DEFINITIONS ::= BEGIN
IMPORTS
TRAP-TYPE
    FROM RFC-1215
ifIndex
    FROM RFC1213-MIB
ax7700r, ax7700rSystemMsgType, ax7700rSystemMsgTimeStamp, ax7700rSystemMsgLevel, ax7700rSystemMsgEventPoint,
ax7700rSystemMsgEventInterfaceID, ax7700rSystemMsgEventCode, ax7700rSystemMsgAdditionalCode, ax7700rSystemMsgText,
ax7700rChassisIndex, ax7700rBcuBoardIndex, ax7700rTemperatureStatusIndex, ax7700rTemperatureStatusDescr, 
ax7700rTemperatureStatusValue, ax7700rTemperatureState,
axrLoginName, axrLoginTime, axrLoginLocation, axrLoginLine, axrLoginFailureTime, axrLogoutTime, axrLogoutStatus
    FROM AX7800R
;

ax7700rSystemMsgTrap TRAP-TYPE
	ENTERPRISE      ax7700r
	VARIABLES       { ax7700rSystemMsgType, ax7700rSystemMsgTimeStamp,
                          ax7700rSystemMsgLevel, ax7700rSystemMsgEventPoint,
                          ax7700rSystemMsgEventInterfaceID, ax7700rSystemMsgEventCode,
                          ax7700rSystemMsgAdditionalCode, ax7700rSystemMsgText }
	DESCRIPTION
		"System message is displayed."
	::= 1

ax7700rStandbySystemUpTrap TRAP-TYPE
	ENTERPRISE      ax7700r
	VARIABLES       { ax7700rChassisIndex, ax7700rBcuBoardIndex }
	DESCRIPTION
		"Standby system is restarted."
	::= 2

ax7700rStandbySystemDownTrap TRAP-TYPE
	ENTERPRISE      ax7700r
	VARIABLES       { ax7700rChassisIndex, ax7700rBcuBoardIndex }
	DESCRIPTION
		"Standby system is failed."
	::= 3

ax7700rTemperatureTrap TRAP-TYPE
	ENTERPRISE ax7700r
	VARIABLES {
		ax7700rChassisIndex,
		ax7700rBcuBoardIndex,
		ax7700rTemperatureStatusIndex,
		ax7700rTemperatureStatusDescr, 
		ax7700rTemperatureStatusValue, 
		ax7700rTemperatureState }
	DESCRIPTION
		"A ax7700rTemperatureTrap is sent if the 
		temperature measured at a given testpoint is outside 
		the normal range for the testpoint (i.e. is at the warning, 
		critical, or shutdown stage)."
	::= 4

ax7700rAirFanStopTrap TRAP-TYPE
	ENTERPRISE      ax7700r
	DESCRIPTION
             "This trap indicates a fan failure." 
	::= 8 

ax7700rPowerSupplyFailureTrap TRAP-TYPE
	ENTERPRISE      ax7700r
	DESCRIPTION
             "This trap indicates one ( or more ) of power supplies failure." 
	::= 9 

ax7700rLoginSuccessTrap TRAP-TYPE
	ENTERPRISE      ax7700r
	VARIABLES       { axrLoginName, axrLoginTime, axrLoginLocation, axrLoginLine }
	DESCRIPTION
             "This trap indicates success of user log in." 
	::= 10 

ax7700rLoginFailureTrap TRAP-TYPE
	ENTERPRISE      ax7700r
	VARIABLES       { axrLoginName, axrLoginFailureTime, 
                          axrLoginLocation, axrLoginLine }
	DESCRIPTION
             "This trap indicates failure of user log in." 
	::= 11

ax7700rLogoutTrap TRAP-TYPE
	ENTERPRISE      ax7700r
	VARIABLES       { axrLoginName, axrLoginTime, axrLogoutTime, 
                          axrLoginLocation, axrLoginLocation, axrLoginLine, 
                          axrLogoutStatus }
	DESCRIPTION
             "This trap indicates success of following log out.
	       'logout' command, 'exit' command, 'quit' command."
	::= 12

ax7700rMemoryUsageTrap  TRAP-TYPE
	ENTERPRISE      ax7700r
	DESCRIPTION
             "This indicates available memory is fewer than lower limit." 
	::= 13

ax7700rFrameErrorReceiveTrap  TRAP-TYPE
	ENTERPRISE      ax7700r
	VARIABLES       { ifIndex }
	DESCRIPTION
             "This indicates frame receive error." 
	::= 18

ax7700rFrameErrorSendTrap  TRAP-TYPE
	ENTERPRISE      ax7700r
	VARIABLES       { ifIndex }
	DESCRIPTION
             "This indicates frame send error." 
	::= 19

-- axrEfmoamUdldPortInactivateTrap TRAP-TYPE
ax7700rEfmoamUdldPortInactivateTrap TRAP-TYPE
	ENTERPRISE      ax7700r
	VARIABLES       { ifIndex }
	DESCRIPTION
             "Efmoam udld port inactivate trap."
	::= 29
-- axrEfmoamLoopDetectPortInactivateTrap TRAP-TYPE
ax7700rEfmoamLoopDetectPortInactivateTrap TRAP-TYPE
	ENTERPRISE      ax7700r
	VARIABLES       { ifIndex }
	DESCRIPTION
             "Efmoam loop detect port inactivate trap."
	::= 30
END
