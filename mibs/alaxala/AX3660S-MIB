--
-- Copyright(C) 2017 ALAXALA Networks Corporation. All Rights Reserved.
-- LAST-UPDATED "201803071200Z"
--
-- AX3660S.my: Switching Router System information MIB file
--
AX3660S DEFINITIONS ::= BEGIN
IMPORTS
enterprises, OBJECT-TYPE, NetworkAddress, IpAddress,
Counter, Gauge, TimeTicks
        FROM RFC1155-SMI
RouterID, AreaID, Status, BigMetric, DesignatedRouterPriority,
HelloRange, Metric, PositiveInteger, UpToMaxAge
        FROM OSPF-MIB
OBJECT-TYPE
        FROM RFC-1212
TRAP-TYPE
        FROM RFC-1215
ifIndex
        FROM IF-MIB
DisplayString
        FROM RFC1213-MIB
RowStatus, MacAddress, TruthValue, TimeStamp, PhysAddress
    FROM SNMPv2-TC
InterfaceIndex
    FROM IF-MIB
Ipv6IfIndex, Ipv6Address, Ipv6AddressPrefix
    FROM IPV6-TC
BridgeId, Timeout
    FROM BRIDGE-MIB
PortList
    FROM Q-BRIDGE-MIB
InterfaceIndex
    FROM IF-MIB
InetAddressType,InetAddress
    FROM INET-ADDRESS-MIB
Gauge32, Counter32, Counter64, Unsigned32, Integer32
    FROM SNMPv2-SMI
;


VlanIndex ::= INTEGER (1..2147483647)
VlanIdOrZero ::= INTEGER (0|1..4094)
VniIndex ::= INTEGER (1..2147483647)


-- object syntax difinition end

alaxala            OBJECT IDENTIFIER ::= { enterprises 21839 }
alaxalaProductId   OBJECT IDENTIFIER ::= { alaxala 1 }
axSwitch           OBJECT IDENTIFIER ::= { alaxalaProductId 2 }
ax3660s            OBJECT IDENTIFIER ::= { axSwitch 24 }

alaxalaMib         OBJECT IDENTIFIER ::= { alaxala 2 }
axsEx              OBJECT IDENTIFIER ::= { alaxalaMib 2 }

axsMib             OBJECT IDENTIFIER ::= { axsEx 1 }
ax3660sMib         OBJECT IDENTIFIER ::= { axsEx 24 }

-- device independent
axsStats              OBJECT IDENTIFIER ::= { axsMib 1 }
axsIfStats            OBJECT IDENTIFIER ::= { axsStats 4 }
axsQoS                OBJECT IDENTIFIER ::= { axsStats 6 }
axsEtherTxQoS         OBJECT IDENTIFIER ::= { axsQoS 1 }
axsEthShaper          OBJECT IDENTIFIER ::= { axsQoS 4 }
axsEthShaperAgQue     OBJECT IDENTIFIER ::= { axsQoS 5 }
axsToCpuQoS           OBJECT IDENTIFIER ::= { axsQoS 11 }
axsDHCP               OBJECT IDENTIFIER ::= { axsStats 10 }

axsGsrp               OBJECT IDENTIFIER ::= { axsMib 4 }
axsFdb                OBJECT IDENTIFIER ::= { axsMib 5 }
axsVlan               OBJECT IDENTIFIER ::= { axsMib 6 }
axsVlanBridge           OBJECT IDENTIFIER ::= { axsVlan 1 }
axsVlanBridgeBase       OBJECT IDENTIFIER ::= { axsVlanBridge 1 }
axsVlanBridgeStp        OBJECT IDENTIFIER ::= { axsVlanBridge 2 }
axsVlanBridgeTp         OBJECT IDENTIFIER ::= { axsVlanBridge 4 }
axsVlanBridgeStatic     OBJECT IDENTIFIER ::= { axsVlanBridge 5 }
axsVlanTagTranslation   OBJECT IDENTIFIER ::= { axsVlan 10 }

axsOadp                 OBJECT IDENTIFIER ::= { axsMib 7 }
axsOadpMIBObjects       OBJECT IDENTIFIER ::= { axsOadp 1 }
axsOadpGlobalInfo       OBJECT IDENTIFIER ::= { axsOadpMIBObjects 1 }
axsOadpPortInfo         OBJECT IDENTIFIER ::= { axsOadpMIBObjects 2 }
axsOadpNeighborInfo     OBJECT IDENTIFIER ::= { axsOadpMIBObjects 3 }
axsOadpMIBNotifications OBJECT IDENTIFIER ::= { axsOadp 2 }

axsFlow               OBJECT IDENTIFIER ::= { axsMib 8 }
axsAccessFilterStats  OBJECT IDENTIFIER ::= { axsFlow 9 }
axsQosFlowStats       OBJECT IDENTIFIER ::= { axsFlow 11 }

axsL2ld                OBJECT IDENTIFIER ::= { axsMib 10 }
axsL2ldGlobalInfo      OBJECT IDENTIFIER ::= { axsL2ld 1 }

axsVrf                      OBJECT IDENTIFIER ::= { axsMib 11 }
axsVrfIp                    OBJECT IDENTIFIER ::= { axsVrf 1 }
axsVrfIpForward             OBJECT IDENTIFIER ::= { axsVrf 2 }
axsVrfIpv6                  OBJECT IDENTIFIER ::= { axsVrf 3 }
axsVrfIpv6Forward           OBJECT IDENTIFIER ::= { axsVrf 4 }

axsOspf               OBJECT IDENTIFIER ::= { axsMib 14 }
axsOspfTrap           OBJECT IDENTIFIER ::= { axsOspf 16 }
axsOspfTraps          OBJECT IDENTIFIER ::= { axsOspfTrap 2 }
axsOspfv3             OBJECT IDENTIFIER ::= { axsMib 15 }

axsStatic             OBJECT IDENTIFIER ::= { axsMib 38 }
axsStaticTrap         OBJECT IDENTIFIER ::= { axsStatic 2 }

axsUlr                OBJECT IDENTIFIER ::= { axsMib 20 }
axsUlrGlobalInfo      OBJECT IDENTIFIER ::= { axsUlr 1 }

axsTrackObject             OBJECT IDENTIFIER ::= { axsMib 41 }
axsTrackObjectGeneralGroup OBJECT IDENTIFIER ::= { axsTrackObject 1 }
axsTrackObjectTraps        OBJECT IDENTIFIER ::= { axsTrackObject 2 }

axsPolicyBase           OBJECT IDENTIFIER ::= { axsMib 45 }
axsPolicyBaseRouting    OBJECT IDENTIFIER ::= { axsPolicyBase 1 }

axsBootManagement    OBJECT IDENTIFIER ::= { axsMib 51 }
axsLogin             OBJECT IDENTIFIER ::= { axsMib 52 }

axslldp                      OBJECT IDENTIFIER ::= { axsMib 100 }
axslldpConfiguration         OBJECT IDENTIFIER ::= { axslldp 1 }
axslldpStats                 OBJECT IDENTIFIER ::= { axslldp 2 }
axslldpLocalSystemData       OBJECT IDENTIFIER ::= { axslldp 3 }
axslldpRemoteSystemData      OBJECT IDENTIFIER ::= { axslldp 4 }
axslldpRemoteOriginInfoData  OBJECT IDENTIFIER ::= { axslldp 20 }

axsAxrp               OBJECT IDENTIFIER ::= { axsMib 200 }

axsPconMIB                  OBJECT IDENTIFIER ::= { axsMib 300 }
axsPconObjects              OBJECT IDENTIFIER ::= { axsPconMIB 1 }
axsPconModuleData           OBJECT IDENTIFIER ::= { axsPconObjects 1 }
axsPconPowerCon             OBJECT IDENTIFIER ::= { axsPconObjects 2 }
axsPconTraffic              OBJECT IDENTIFIER ::= { axsPconObjects 3 }

axsVxlan                 OBJECT IDENTIFIER ::= { axsMib 410 }

ax3660sSwitch           OBJECT IDENTIFIER ::= { ax3660sMib 1 }
ax3660sSoftware         OBJECT IDENTIFIER ::= { ax3660sSwitch 2 }
ax3660sSystemMsg        OBJECT IDENTIFIER ::= { ax3660sSwitch 3 }
ax3660sSnmpAgent        OBJECT IDENTIFIER ::= { ax3660sSwitch 4 }
ax3660sLicense          OBJECT IDENTIFIER ::= { ax3660sSwitch 6 }
ax3660sDevice           OBJECT IDENTIFIER ::= { ax3660sMib 2 }
ax3660sChassis          OBJECT IDENTIFIER ::= { ax3660sDevice 1 }
ax3660sPhysLine         OBJECT IDENTIFIER ::= { ax3660sDevice 5 }
ax3660sManagementMIB    OBJECT IDENTIFIER ::= { ax3660sMib 3 }
ax3660sOperationCommand OBJECT IDENTIFIER ::= { ax3660sManagementMIB 1 }
ax3660sFdbClearMIB      OBJECT IDENTIFIER ::= { ax3660sOperationCommand 1 }

axsIfStatsTable OBJECT-TYPE
	SYNTAX  SEQUENCE OF AxsIfStatsTableEntry
	ACCESS  not-accessible
	STATUS  mandatory
	DESCRIPTION
		"A table containing extension statistics for more than 100,000,000
		bps interface."
	::= { axsIfStats 1 }

axsIfStatsEntry OBJECT-TYPE
	SYNTAX  AxsIfStatsTableEntry
	ACCESS  not-accessible
	STATUS  mandatory
	DESCRIPTION
		"An entry containing extension statistics for interface."
	INDEX   { axsIfStatsIndex }
	::= { axsIfStatsTable 1 }

	AxsIfStatsTableEntry ::=
		SEQUENCE {
		  axsIfStatsIndex
			INTEGER,
		  axsIfStatsName
			DisplayString,
		  axsIfStatsInMegaOctets
			Counter,
		  axsIfStatsInUcastMegaPkts
			Counter,
		  axsIfStatsInMulticastMegaPkts
			Counter,
		  axsIfStatsInBroadcastMegaPkts
			Counter,
		  axsIfStatsOutMegaOctets
			Counter,
		  axsIfStatsOutUcastMegaPkts
			Counter,
		  axsIfStatsOutMulticastMegaPkts
			Counter,
		  axsIfStatsOutBroadcastMegaPkts
			Counter,
		  axsIfStatsHighSpeed
			Counter
		}

axsIfStatsIndex OBJECT-TYPE
	SYNTAX  INTEGER
	ACCESS  not-accessible
	STATUS  mandatory
	DESCRIPTION
		"This object value is same as Ifindex which interface index
		of a system."
	::= { axsIfStatsEntry 1 }

axsIfStatsName OBJECT-TYPE
	SYNTAX  DisplayString
	ACCESS  read-only
	STATUS  mandatory
	DESCRIPTION
		"Interfaces name. Same as ifDescr."
	::= { axsIfStatsEntry 2 }

axsIfStatsInMegaOctets OBJECT-TYPE
	SYNTAX  Counter
	ACCESS  read-only
	STATUS  mandatory
	DESCRIPTION
		"Number of octets that received on the interface. This value is
		displayed in mega-octets(M). Value of 0 through 999,999 are rounded
		down."
	::= { axsIfStatsEntry 3 }

axsIfStatsInUcastMegaPkts OBJECT-TYPE
	SYNTAX  Counter
	ACCESS  read-only
	STATUS  mandatory
	DESCRIPTION
		"Number of subnetwork-unicast packets that received on the interface.
		This value is displayed in mega-packets(M).Value of 0 through 999,999
		are rounded down."
	::= { axsIfStatsEntry 4 }

axsIfStatsInMulticastMegaPkts OBJECT-TYPE
	SYNTAX  Counter
	ACCESS  read-only
	STATUS  mandatory
	DESCRIPTION
		"Number of multicast mega-packets that received on the interface.
		this value is displayed in mega-packets(M).Value of 0 through 999,999
		are rounded down."
	::= { axsIfStatsEntry 5 }


axsIfStatsInBroadcastMegaPkts OBJECT-TYPE
	SYNTAX  Counter
	ACCESS  read-only
	STATUS  mandatory
	DESCRIPTION
		"The number of non-unicast packets delivered to a higher-layer
		protocol. The value is displayed in mega-packets (M). Value of 0
		through 999,999 are rounded down. "
	::= { axsIfStatsEntry 6 }

axsIfStatsOutMegaOctets OBJECT-TYPE
	SYNTAX  Counter
	ACCESS  read-only
	STATUS  mandatory
	DESCRIPTION
		"The total number of octets transmitted out of the interface.
		The value is displayed in mega-octets(M). Value of 0 through 999,999
		are rounded down."
	::= { axsIfStatsEntry 7 }

axsIfStatsOutUcastMegaPkts OBJECT-TYPE
	SYNTAX  Counter
	ACCESS  read-only
	STATUS  mandatory
	DESCRIPTION
		"The total number of packets that higher-level protocols requested
		be transmitted to a subnetwork-unicast address.The value is displayed
		in mega packets(M). Value of 0 through 999,999 are rounded down."
	::= { axsIfStatsEntry 8 }

axsIfStatsOutMulticastMegaPkts OBJECT-TYPE
	SYNTAX  Counter
	ACCESS  read-only
	STATUS  mandatory
	DESCRIPTION
		"Number of multicast packets that transmitted on the interface.
		This value is displayed in mega-packets(M). Value of 0 through
		999,999 are rounded down."
	::= { axsIfStatsEntry 9 }

axsIfStatsOutBroadcastMegaPkts OBJECT-TYPE
	SYNTAX  Counter
	ACCESS  read-only
	STATUS  mandatory
	DESCRIPTION
		"Number of broadcast packets that transmitted on the interface.
		This value is displayed in mega-packets(M). Value of 0 through
		999,999 are rounded down. "
	::= { axsIfStatsEntry 10 }

axsIfStatsHighSpeed OBJECT-TYPE
	SYNTAX  Counter
	ACCESS  read-only
	STATUS  mandatory
	DESCRIPTION
		"A circuit speed.This value is displayed in mega-bps[Mbps].
		Round off the 1,000,000bps. "
	::= { axsIfStatsEntry 11 }

--  QoS interface statistics Variables

axsEtherTxQoSStatsTable OBJECT-TYPE
	SYNTAX  SEQUENCE OF AxsEtherTxQoSStatsEntry
	ACCESS  not-accessible
	STATUS  mandatory
	DESCRIPTION
		"A collection of QoS statistics kept for a particular
		Ethernet interface."
	::= { axsEtherTxQoS 1 }

axsEtherTxQoSStatsEntry OBJECT-TYPE
	SYNTAX  AxsEtherTxQoSStatsEntry
	ACCESS  not-accessible
	STATUS  mandatory
	DESCRIPTION
		"An entry containing QoS statistics for a particular 
		Ethernet interface."
    INDEX { axsEtherTxQoSStatsIndex }
	::= { axsEtherTxQoSStatsTable 1 }

	AxsEtherTxQoSStatsEntry ::=
		SEQUENCE {
            axsEtherTxQoSStatsIndex	INTEGER,
            axsEtherTxQoSStatsMaxQnum	INTEGER,
            axsEtherTxQoSStatsLimitQlen	INTEGER,
            axsEtherTxQoSStatsTotalOutFrames	Counter,
            axsEtherTxQoSStatsTotalOutBytesHigh	Counter,
            axsEtherTxQoSStatsTotalOutBytesLow	Counter,
            axsEtherTxQoSStatsTotalDiscardFrames	Counter
		}

axsEtherTxQoSStatsIndex OBJECT-TYPE
	SYNTAX  INTEGER
	ACCESS  not-accessible
	STATUS  mandatory
	DESCRIPTION
		"Identified by a particular value of this
		index is same value of ifIndex.Its value ranges
		between 1 and the value of ifNumber."
	::= { axsEtherTxQoSStatsEntry 1 }

axsEtherTxQoSStatsMaxQnum OBJECT-TYPE
	SYNTAX  INTEGER
	ACCESS  read-only
	STATUS  mandatory
	DESCRIPTION
		"Max length of queue for an ethernet interface."
	::= { axsEtherTxQoSStatsEntry 2 }

axsEtherTxQoSStatsLimitQlen OBJECT-TYPE
	SYNTAX  INTEGER
	ACCESS  read-only
	STATUS  mandatory
	DESCRIPTION
		"The limit length of outbound queue for an ethernet interface."
	::= { axsEtherTxQoSStatsEntry 3 }

axsEtherTxQoSStatsTotalOutFrames OBJECT-TYPE
	SYNTAX  Counter
	ACCESS  read-only
	STATUS  mandatory
	DESCRIPTION
		"The total number of  packets transmitted out of the
		interface."
	::= { axsEtherTxQoSStatsEntry 4 }

axsEtherTxQoSStatsTotalOutBytesHigh OBJECT-TYPE
	SYNTAX  Counter
	ACCESS  read-only
	STATUS  mandatory
	DESCRIPTION
		"The total number of octets transmitted out of the
		interface."
	::= { axsEtherTxQoSStatsEntry 5 }

axsEtherTxQoSStatsTotalOutBytesLow OBJECT-TYPE
	SYNTAX  Counter
	ACCESS  read-only
	STATUS  mandatory
	DESCRIPTION
		"The total number of octets transmitted out of the
		interface."
	::= { axsEtherTxQoSStatsEntry 6 }

axsEtherTxQoSStatsTotalDiscardFrames OBJECT-TYPE
	SYNTAX  Counter
	ACCESS  read-only
	STATUS  mandatory
	DESCRIPTION
		"The number of outbound packets which were chosen
		to be discarded ."
	::= { axsEtherTxQoSStatsEntry 7 }

axsEtherTxQoSStatsQueueTable OBJECT-TYPE
	SYNTAX  SEQUENCE OF AxsEtherTxQoSStatsQueueEntry
	ACCESS  not-accessible
	STATUS  mandatory
	DESCRIPTION
		"A collection of priority queue statistics."
	::= { axsEtherTxQoS 2 }

axsEtherTxQoSStatsQueueEntry OBJECT-TYPE
	SYNTAX  AxsEtherTxQoSStatsQueueEntry
	ACCESS  not-accessible
	STATUS  mandatory
	DESCRIPTION
		"A entry of priority queue statistics."
    INDEX { axsEtherTxQoSStatsQueueIndex , axsEtherTxQoSStatsQueueQueIndex }
	::= { axsEtherTxQoSStatsQueueTable 1 }

	AxsEtherTxQoSStatsQueueEntry ::=
		SEQUENCE {
            axsEtherTxQoSStatsQueueIndex	        INTEGER,
            axsEtherTxQoSStatsQueueQueIndex	INTEGER,
            axsEtherTxQoSStatsQueueQlen	        INTEGER,
            axsEtherTxQoSStatsQueueMaxQlen	INTEGER,
            axsEtherTxQoSStatsQueueDiscardFramesClass1	Counter64,
            axsEtherTxQoSStatsQueueDiscardFramesClass2	Counter64,
            axsEtherTxQoSStatsQueueDiscardFramesClass3	Counter64,
            axsEtherTxQoSStatsQueueDiscardFramesClass4	Counter64
		}

axsEtherTxQoSStatsQueueIndex OBJECT-TYPE
	SYNTAX  INTEGER
	ACCESS  not-accessible
	STATUS  mandatory
	DESCRIPTION
		"Identified by a particular value of this
		index is same value of ifIndex.Its value ranges
		between 1 and the value of ifNumber."
	::= { axsEtherTxQoSStatsQueueEntry 1 }

axsEtherTxQoSStatsQueueQueIndex OBJECT-TYPE
	SYNTAX  INTEGER
	ACCESS  not-accessible
	STATUS  mandatory
	DESCRIPTION
		"An index that uniquely identifies the particular
		queue.Its value ranges between 1 and the value of
		axsEtherTxQoSStatsMaxQnum."
	::= { axsEtherTxQoSStatsQueueEntry 2 }

axsEtherTxQoSStatsQueueQlen OBJECT-TYPE
	SYNTAX  INTEGER
	ACCESS  read-only
	STATUS  mandatory
	DESCRIPTION
		"A length of outbound priority queue for an interface."
	::= { axsEtherTxQoSStatsQueueEntry 3 }

axsEtherTxQoSStatsQueueMaxQlen OBJECT-TYPE
	SYNTAX  INTEGER
	ACCESS  read-only
	STATUS  mandatory
	DESCRIPTION
		"Max length of outbound priority queue for an interface since
		system was up."
	::= { axsEtherTxQoSStatsQueueEntry 4 }

axsEtherTxQoSStatsQueueDiscardFramesClass1 OBJECT-TYPE
	SYNTAX  Counter64
	ACCESS  read-only
	STATUS  mandatory
	DESCRIPTION
		"The number of discard frames in the discard class 
		 1 of output priority queue."
	::= { axsEtherTxQoSStatsQueueEntry 5 }

axsEtherTxQoSStatsQueueDiscardFramesClass2 OBJECT-TYPE
	SYNTAX  Counter64
	ACCESS  read-only
	STATUS  mandatory
	DESCRIPTION
		"The number of discard frames in the discard class 
		 2 of output priority queue."
	::= { axsEtherTxQoSStatsQueueEntry 6 }

axsEtherTxQoSStatsQueueDiscardFramesClass3 OBJECT-TYPE
	SYNTAX  Counter64
	ACCESS  read-only
	STATUS  mandatory
	DESCRIPTION
		"The number of discard frames in the discard class 
		 3 of output priority queue."
	::= { axsEtherTxQoSStatsQueueEntry 7 }

axsEtherTxQoSStatsQueueDiscardFramesClass4 OBJECT-TYPE
	SYNTAX  Counter64
	ACCESS  read-only
	STATUS  mandatory
	DESCRIPTION
		"The number of discard frames in the discard class 
		 4 of output priority queue."
	::= { axsEtherTxQoSStatsQueueEntry 8 }

axsToCpuQoSStatsTable OBJECT-TYPE
	SYNTAX    SEQUENCE OF AxsToCpuQoSStatsEntry
	ACCESS    not-accessible
	STATUS    mandatory
	DESCRIPTION
		"Table information on the QoS statistics about the sending queue for cpu."
	::= { axsToCpuQoS 1 }

axsToCpuQoSStatsEntry OBJECT-TYPE
	SYNTAX    AxsToCpuQoSStatsEntry
	ACCESS    not-accessible
	STATUS    mandatory
	DESCRIPTION
		"Entry concerning corresponding QoS statistics about the sending queue for cpu."
	INDEX     { axsToCpuQoSStatsIndex }
	::= { axsToCpuQoSStatsTable 1 }

AxsToCpuQoSStatsEntry ::= SEQUENCE {
	axsToCpuQoSStatsIndex                 INTEGER,
	axsToCpuQoSStatsMaxQnum               INTEGER,
	axsToCpuQoSStatsLimitQlen             INTEGER,
	axsToCpuQoSStatsTotalOutFrames        Counter,
	axsToCpuQoSStatsTotalOutBytesHigh     Counter,
	axsToCpuQoSStatsTotalOutBytesLow      Counter,
	axsToCpuQoSStatsTotalDiscardFrames    Counter
}

axsToCpuQoSStatsIndex OBJECT-TYPE
	SYNTAX    INTEGER
	ACCESS    not-accessible
	STATUS    mandatory
	DESCRIPTION
		"The number in the part in which the sending queue for cpu exists."
	::= { axsToCpuQoSStatsEntry 1 }

axsToCpuQoSStatsMaxQnum OBJECT-TYPE
	SYNTAX    INTEGER
	ACCESS    read-only
	STATUS    mandatory
	DESCRIPTION
		"The number of queues of the sending queue for cpu."
	::= { axsToCpuQoSStatsEntry 2 }

axsToCpuQoSStatsLimitQlen OBJECT-TYPE
	SYNTAX    INTEGER
	ACCESS    read-only
	STATUS    mandatory
	DESCRIPTION
		"The limit length of the priority queue of the sending queue for cpu."
	::= { axsToCpuQoSStatsEntry 3 }

axsToCpuQoSStatsTotalOutFrames OBJECT-TYPE
	SYNTAX    Counter
	ACCESS    read-only
	STATUS    mandatory
	DESCRIPTION
		"The total number of sent frames of the sending queue for cpu."
	::= { axsToCpuQoSStatsEntry 4 }

axsToCpuQoSStatsTotalOutBytesHigh OBJECT-TYPE
	SYNTAX    Counter
	ACCESS    read-only
	STATUS    mandatory
	DESCRIPTION
		"The total number of sent bytes (the high order 4-bytes) of the sending queue for cpu."
	::= { axsToCpuQoSStatsEntry 5 }

axsToCpuQoSStatsTotalOutBytesLow OBJECT-TYPE
	SYNTAX    Counter
	ACCESS    read-only
	STATUS    mandatory
	DESCRIPTION
		"The total number of sent bytes (the low order 4-bytes) of the sending queue for cpu."
	::= { axsToCpuQoSStatsEntry 6 }

axsToCpuQoSStatsTotalDiscardFrames OBJECT-TYPE
	SYNTAX    Counter
	ACCESS    read-only
	STATUS    mandatory
	DESCRIPTION
		"The total number of discarded frames of the sending queue for cpu."
	::= { axsToCpuQoSStatsEntry 7 }

axsToCpuQoSStatsQueueTable OBJECT-TYPE
	SYNTAX    SEQUENCE OF AxsToCpuQoSStatsQueueEntry
	ACCESS    not-accessible
	STATUS    mandatory
	DESCRIPTION
		"Table information on the QoS statistics of priority queue
		 about the sending queue for cpu."
	::= { axsToCpuQoS 2 }

axsToCpuQoSStatsQueueEntry OBJECT-TYPE
	SYNTAX    AxsToCpuQoSStatsQueueEntry
	ACCESS    not-accessible
	STATUS    mandatory
	DESCRIPTION
		"Entry concerning corresponding QoS statistics of priority queue
		about the sending queue for cpu."
	INDEX     { axsToCpuQoSStatsQueueIndex,
				axsToCpuQoSStatsQueueQueIndex }
	::= { axsToCpuQoSStatsQueueTable 1 }

AxsToCpuQoSStatsQueueEntry ::= SEQUENCE {
	axsToCpuQoSStatsQueueIndex                  INTEGER,
	axsToCpuQoSStatsQueueQueIndex               INTEGER,
	axsToCpuQoSStatsQueueQlen                   INTEGER,
	axsToCpuQoSStatsQueueMaxQlen                INTEGER,
	axsToCpuQoSStatsQueueDiscardFramesClass1    Counter64,
	axsToCpuQoSStatsQueueDiscardFramesClass2    Counter64,
	axsToCpuQoSStatsQueueDiscardFramesClass3    Counter64,
	axsToCpuQoSStatsQueueDiscardFramesClass4    Counter64
}

axsToCpuQoSStatsQueueIndex OBJECT-TYPE
	SYNTAX    INTEGER
	ACCESS    not-accessible
	STATUS    mandatory
	DESCRIPTION
		"The number in the part in which the sending queue for cpu exists."
	::= { axsToCpuQoSStatsQueueEntry 1 }

axsToCpuQoSStatsQueueQueIndex OBJECT-TYPE
	SYNTAX    INTEGER
	ACCESS    not-accessible
	STATUS    mandatory
	DESCRIPTION
		"The index value which identifies the entry of this table.
		Values between 1 and axsToCpuQoSStatsMaxQnum."
    ::= { axsToCpuQoSStatsQueueEntry 2 }

axsToCpuQoSStatsQueueQlen OBJECT-TYPE
	SYNTAX    INTEGER
	ACCESS    read-only
	STATUS    mandatory
	DESCRIPTION
		"A length of priority queue about the sending queue for cpu."
	::= { axsToCpuQoSStatsQueueEntry 3 }

axsToCpuQoSStatsQueueMaxQlen OBJECT-TYPE
	SYNTAX    INTEGER
	ACCESS    read-only
	STATUS    mandatory
	DESCRIPTION
		"The highest queue length of priority queue about the sending queue for cpu
		after being cleared or initialized."
    ::= { axsToCpuQoSStatsQueueEntry 4 }

axsToCpuQoSStatsQueueDiscardFramesClass1 OBJECT-TYPE
	SYNTAX    Counter64
	ACCESS    read-only
	STATUS    mandatory
	DESCRIPTION
		"The number of discarded frames in the discard class 1 of priority queue
		about the sending queue for cpu."
	::= { axsToCpuQoSStatsQueueEntry 5 }

axsToCpuQoSStatsQueueDiscardFramesClass2 OBJECT-TYPE
	SYNTAX    Counter64
	ACCESS    read-only
	STATUS    mandatory
	DESCRIPTION
		"The number of discarded frames in the discard class 2 of priority queue
		about the sending queue for cpu."
	::= { axsToCpuQoSStatsQueueEntry 6 }

axsToCpuQoSStatsQueueDiscardFramesClass3 OBJECT-TYPE
	SYNTAX    Counter64
	ACCESS    read-only
	STATUS    mandatory
	DESCRIPTION
		"The number of discarded frames in the discard class 3 of priority queue
		about the sending queue for cpu."
	::= { axsToCpuQoSStatsQueueEntry 7 }

axsToCpuQoSStatsQueueDiscardFramesClass4 OBJECT-TYPE
	SYNTAX    Counter64
	ACCESS    read-only
	STATUS    mandatory
	DESCRIPTION
		"The number of discarded frames in the discard class 4 of priority queue
		about the sending queue for cpu."
	::= { axsToCpuQoSStatsQueueEntry 8 }


--axsDHCP group Variables

axsDHCPAddrValue OBJECT-TYPE
	SYNTAX INTEGER
	ACCESS read-only
	STATUS mandatory
	DESCRIPTION
		"The number of IP addresses which are available
		within this Router."
	::= { axsDHCP 1 }

axsDHCPFreeAddrValue OBJECT-TYPE
	SYNTAX INTEGER
	ACCESS read-only
	STATUS mandatory
	DESCRIPTION
		"The number of IP addresses which are available
		within this Router. May be expressed as either
		an absolute value."
	::= { axsDHCP 2 }

--  axsGsrp Group

axsGsrpGroupTable OBJECT-TYPE
        SYNTAX  SEQUENCE OF AxsGsrpGroupEntry
        ACCESS  not-accessible
        STATUS  mandatory
        DESCRIPTION
                "The table containing GSRP group information."
        ::= { axsGsrp 1 }

axsGsrpGroupEntry OBJECT-TYPE
        SYNTAX  AxsGsrpGroupEntry
        ACCESS  not-accessible
        STATUS  mandatory
        DESCRIPTION
                "The list of GSRP group information."
    INDEX { axsGsrpGroupId }
        ::= { axsGsrpGroupTable 1 }

        AxsGsrpGroupEntry ::=
                SEQUENCE {
                    axsGsrpGroupId             INTEGER,
                    axsGsrpGroupRowStatus      RowStatus,
                    axsGsrpMacAddress          MacAddress,
                    axsGsrpAdvertiseHoldTime    INTEGER,
                    axsGsrpAdvertiseInterval    INTEGER,
                    axsGsrpSelectionPattern    INTEGER,
                    axsGsrpLayer3Redundancy    INTEGER
		}

axsGsrpGroupId OBJECT-TYPE
	SYNTAX  INTEGER
	ACCESS  not-accessible
	STATUS  mandatory
	DESCRIPTION
		"GSRP group identifier."
	::= { axsGsrpGroupEntry 1 }

axsGsrpGroupRowStatus OBJECT-TYPE
	SYNTAX  RowStatus
	ACCESS  read-only
	STATUS  mandatory
	DESCRIPTION
		"Valid/Invalid state of this entry. Valid(1) fixed"
	::= { axsGsrpGroupEntry 2 }

axsGsrpMacAddress OBJECT-TYPE
	SYNTAX  MacAddress
	ACCESS  read-only
	STATUS  mandatory
	DESCRIPTION
		"The Media Access Control Address of this equipment."
	::= { axsGsrpGroupEntry 3 }

axsGsrpAdvertiseHoldTime OBJECT-TYPE
	SYNTAX  INTEGER
	ACCESS  read-only
	STATUS  mandatory
	DESCRIPTION
		"Holding time of the Advertise frame (milli second)."
	::= { axsGsrpGroupEntry 4 }

axsGsrpAdvertiseInterval OBJECT-TYPE
	SYNTAX  INTEGER
	ACCESS  read-only
	STATUS  mandatory
	DESCRIPTION
		"Interval between transmitting the Advertise frame (milli second)."
	::= { axsGsrpGroupEntry 5 }

axsGsrpSelectionPattern OBJECT-TYPE
	SYNTAX  INTEGER {
                ports-Priority-MAC(1),
                priority-Ports-MAC(2)
                }
	ACCESS  read-only
	STATUS  mandatory
	DESCRIPTION
		"Master/Backup selection pattern. Ports-Priority-MAC(1)  Priority-Ports-MAC(2)"
	::= { axsGsrpGroupEntry 6 }

axsGsrpLayer3Redundancy OBJECT-TYPE
	SYNTAX  INTEGER {
                off(1),
                on(2)
                }
	ACCESS  read-only
	STATUS  mandatory
	DESCRIPTION
		"The status of layer 3 redundancy-change."
	::= { axsGsrpGroupEntry 7 }

axsGsrpVlanGroupTable OBJECT-TYPE
        SYNTAX  SEQUENCE OF AxsGsrpVlanGroupEntry
        ACCESS  not-accessible
        STATUS  mandatory
        DESCRIPTION
                "The table containing GSRP VLAN group information."
        ::= { axsGsrp 2 }

axsGsrpVlanGroupEntry OBJECT-TYPE
        SYNTAX  AxsGsrpVlanGroupEntry
        ACCESS  not-accessible
        STATUS  mandatory
        DESCRIPTION
                "The list of GSRP VLAN group information."
    INDEX { axsGsrpGroupId, axsGsrpVlanGroupId }
        ::= { axsGsrpVlanGroupTable 1 }

        AxsGsrpVlanGroupEntry ::=
                SEQUENCE {
                    axsGsrpVlanGroupId                  INTEGER,
                    axsGsrpVlanGroupRowStatus           RowStatus,
                    axsGsrpState                        INTEGER,
                    axsGsrpPriority                     INTEGER,
                    axsGsrpActivePorts                  INTEGER,
                    axsGsrpTransitionToMasterCounts     INTEGER,
                    axsGsrpTransitionFromMasterCounts   INTEGER,
                    axsGsrpLastTransitionTime           TimeStamp,
		    axsGsrpVirtualMacAddress	       MacAddress
		}

axsGsrpVlanGroupId OBJECT-TYPE
	SYNTAX  INTEGER
	ACCESS  not-accessible
	STATUS  mandatory
	DESCRIPTION
		"GSRP VLAN group number(1~8)"
	::= { axsGsrpVlanGroupEntry 1 }

axsGsrpVlanGroupRowStatus OBJECT-TYPE
	SYNTAX  RowStatus
	ACCESS  read-only
	STATUS  mandatory
	DESCRIPTION
		"Valid/Invalid state of this entry. Valid(1) fixed"
	::= { axsGsrpVlanGroupEntry 2 }

axsGsrpState OBJECT-TYPE
	SYNTAX  INTEGER {
                backUp(1),
                backUp-Waiting(2),
                master(3),
                backUp-No-Neighbor(4),
		backUp-Lock(5)
                }
	ACCESS  read-only
	STATUS  mandatory
	DESCRIPTION
		"The state of GSRP group."
	::= { axsGsrpVlanGroupEntry 3 }

axsGsrpPriority OBJECT-TYPE
	SYNTAX  INTEGER
	ACCESS  read-only
	STATUS  mandatory
	DESCRIPTION
		"Configured priority."
	::= { axsGsrpVlanGroupEntry 4 }

axsGsrpActivePorts OBJECT-TYPE
	SYNTAX  INTEGER
	ACCESS  read-only
	STATUS  mandatory
	DESCRIPTION
		"The number of port which is link-up  in monitored port."
	::= { axsGsrpVlanGroupEntry 5 }

axsGsrpTransitionToMasterCounts OBJECT-TYPE
	SYNTAX  INTEGER
	ACCESS  read-only
	STATUS  mandatory
	DESCRIPTION
		"The number of times which shifted to the master state from the backup state."
	::= { axsGsrpVlanGroupEntry 6 }

axsGsrpTransitionFromMasterCounts OBJECT-TYPE
	SYNTAX  INTEGER
	ACCESS  read-only
	STATUS  mandatory
	DESCRIPTION
		"The number of times which shifted to the backup state from the master state."
	::= { axsGsrpVlanGroupEntry 7 }

axsGsrpLastTransitionTime OBJECT-TYPE
	SYNTAX  TimeStamp
	ACCESS  read-only
	STATUS  mandatory
	DESCRIPTION
		"The last time at which changed in the master state from the backup state or in the backup state from the master state."
	::= { axsGsrpVlanGroupEntry 8 }

axsGsrpVirtualMacAddress OBJECT-TYPE
	SYNTAX  MacAddress
	ACCESS  read-only
	STATUS  mandatory
	DESCRIPTION
		"The virtual Media Access Control address of the GSRP VLAN group. If the status of layer 3 redundancy-change is off, return 00 00 00 00 00 00"
	::= { axsGsrpVlanGroupEntry 9 }

axsGsrpNeighborGroupTable OBJECT-TYPE
        SYNTAX  SEQUENCE OF AxsGsrpNeighborGroupEntry
        ACCESS  not-accessible
        STATUS  mandatory
        DESCRIPTION
                "The table containing stores the GSRP group information on facing equipment."
        ::= { axsGsrp 3 }

axsGsrpNeighborGroupEntry OBJECT-TYPE
        SYNTAX  AxsGsrpNeighborGroupEntry
        ACCESS  not-accessible
        STATUS  mandatory
        DESCRIPTION
                "The table containing stores the GSRP group information on facing equipment."
    INDEX { axsGsrpNeighborGroupId, axsGsrpNeighborMacAddress }
        ::= { axsGsrpNeighborGroupTable 1 }

        AxsGsrpNeighborGroupEntry ::=
                SEQUENCE {
                    axsGsrpNeighborGroupId             INTEGER,
                    axsGsrpNeighborMacAddress          MacAddress,
                    axsGsrpNeighborAdvertiseHoldTime    INTEGER,
                    axsGsrpNeighborAdvertiseInterval    INTEGER,
                    axsGsrpNeighborSelectionPattern    INTEGER
		}

axsGsrpNeighborGroupId OBJECT-TYPE
	SYNTAX  INTEGER
	ACCESS  not-accessible
	STATUS  mandatory
	DESCRIPTION
		"The GSRP group identifier on the facing equipment."
	::= { axsGsrpNeighborGroupEntry 1 }

axsGsrpNeighborMacAddress OBJECT-TYPE
	SYNTAX  MacAddress
	ACCESS  not-accessible
	STATUS  mandatory
	DESCRIPTION
		"The Media Access Control Address of the facing equipment."
	::= { axsGsrpNeighborGroupEntry 2 }

axsGsrpNeighborAdvertiseHoldTime OBJECT-TYPE
	SYNTAX  INTEGER
	ACCESS  read-only
	STATUS  mandatory
	DESCRIPTION
		"Holding time of the Advertise frame on opposite equipment (milli second)."
	::= { axsGsrpNeighborGroupEntry 3 }

axsGsrpNeighborAdvertiseInterval OBJECT-TYPE
	SYNTAX  INTEGER
	ACCESS  read-only
	STATUS  mandatory
	DESCRIPTION
		"Interval between transmitting the Advertise frame on the facing equipment (milli second)."
	::= { axsGsrpNeighborGroupEntry 4 }

axsGsrpNeighborSelectionPattern OBJECT-TYPE
	SYNTAX  INTEGER {
                port-Priority-MAC(1),
                priority-Port-MAC(2)
                }
	ACCESS  read-only
	STATUS  mandatory
	DESCRIPTION
		"Master/Backup selection pattern on the facing equipment. Ports-Priority-MAC(1)  Priority-Ports-MAC(2)"
	::= { axsGsrpNeighborGroupEntry 5 }

axsGsrpNeighborVlanGroupTable OBJECT-TYPE
        SYNTAX  SEQUENCE OF AxsGsrpNeighborVlanGroupEntry
        ACCESS  not-accessible
        STATUS  mandatory
        DESCRIPTION
                "The table containing the GSRP VLAN group information on facing equipment."
        ::= { axsGsrp 4 }

axsGsrpNeighborVlanGroupEntry OBJECT-TYPE
        SYNTAX  AxsGsrpNeighborVlanGroupEntry
        ACCESS  not-accessible
        STATUS  mandatory
        DESCRIPTION
                "The table containing the GSRP VLAN group information on facing equipment."
    INDEX { axsGsrpNeighborGroupId, axsGsrpNeighborVlanGroupId, axsGsrpNeighborMacAddress }
        ::= { axsGsrpNeighborVlanGroupTable 1 }

        AxsGsrpNeighborVlanGroupEntry ::=
                SEQUENCE {
                    axsGsrpNeighborVlanGroupId    INTEGER,
                    axsGsrpNeighborState          INTEGER,
                    axsGsrpNeighborPriority       INTEGER,
                    axsGsrpNeighborActivePorts    INTEGER
		}

axsGsrpNeighborVlanGroupId OBJECT-TYPE
	SYNTAX  INTEGER
	ACCESS  not-accessible
	STATUS  mandatory
	DESCRIPTION
		"GSRP VLAN group number on the facing equipment (1~8)."
	::= { axsGsrpNeighborVlanGroupEntry 1 }

axsGsrpNeighborState OBJECT-TYPE
	SYNTAX  INTEGER {
                backUp(1),
                backUp-Waiting(2),
                master(3),
                backUp-No-Neighbor(4),
                backUp-Lock(5)
                }
	ACCESS  not-accessible
	STATUS  mandatory
	DESCRIPTION
		"The state of GSRP group on the facing equipment."
	::= { axsGsrpNeighborVlanGroupEntry 2 }

axsGsrpNeighborPriority OBJECT-TYPE
	SYNTAX  INTEGER
	ACCESS  read-only
	STATUS  mandatory
	DESCRIPTION
		"Configured priority on the facing equipment."
	::= { axsGsrpNeighborVlanGroupEntry 3 }

axsGsrpNeighborActivePorts OBJECT-TYPE
	SYNTAX  INTEGER
	ACCESS  read-only
	STATUS  mandatory
	DESCRIPTION
		"The number of port which is link-up  in monitored port on the facing equipment."
	::= { axsGsrpNeighborVlanGroupEntry 4 }

--  axsFdb group

axsFdbCounterTable OBJECT-TYPE
	SYNTAX  SEQUENCE OF AxsFdbCounterEntry
	ACCESS  not-accessible
	STATUS  mandatory
	DESCRIPTION
		"The table of FDB information."
	::= { axsFdb 1 }

axsFdbCounterEntry OBJECT-TYPE
	SYNTAX  AxsFdbCounterEntry
	ACCESS  not-accessible
	STATUS  mandatory
	DESCRIPTION
		"The entry of FDB information."
    INDEX { axsFdbCounterNifIndex, axsFdbCounterLineIndex }
	::= { axsFdbCounterTable 1 }

	AxsFdbCounterEntry ::=
		SEQUENCE {
			axsFdbCounterNifIndex		INTEGER,
			axsFdbCounterLineIndex		INTEGER,
			axsFdbCounterCounts		Counter32,
			axsFdbCounterType		INTEGER,
			axsFdbCounterLimits		Counter32
		}

axsFdbCounterNifIndex OBJECT-TYPE
	SYNTAX  INTEGER
	ACCESS  not-accessible
	STATUS  mandatory
	DESCRIPTION
		"Identified by a particular value of this index
		is same value of NIF.Its value ranges between 1
		and the value of ax3660sNifBoardNumber."
	::= { axsFdbCounterEntry 1 }

axsFdbCounterLineIndex OBJECT-TYPE
	SYNTAX  INTEGER
	ACCESS  not-accessible
	STATUS  mandatory
	DESCRIPTION
		"Identified by a particular value of this index
		is same value of Physical Line.Its value ranges
		between 1 and the value of ax3660sNifLineNumber."
	::= { axsFdbCounterEntry 2 }

axsFdbCounterCounts OBJECT-TYPE
	SYNTAX  Counter32
	ACCESS  read-only
	STATUS  mandatory
	DESCRIPTION
		"The number of FDB entries learned on the port."
	::= { axsFdbCounterEntry 3 }

axsFdbCounterType OBJECT-TYPE
	SYNTAX  INTEGER	{
				unlimited(0),
				limited-and-Forward(1),
				limited-and-Discard(2)
			}
	ACCESS  read-only
	STATUS  mandatory
	DESCRIPTION
		"The type of FDB entries learning."
	::= { axsFdbCounterEntry 4 }

axsFdbCounterLimits OBJECT-TYPE
	SYNTAX  Counter32
	ACCESS  read-only
	STATUS  mandatory
	DESCRIPTION
		"The maximum number of FDB entries that can be learned on the port."
	::= { axsFdbCounterEntry 5 }



--  axsVlan group

axsVBBaseTable OBJECT-TYPE
	SYNTAX  SEQUENCE OF AxsVBBaseEntry
	ACCESS  not-accessible
	STATUS  mandatory
	DESCRIPTION
		"An information table of dot1dBase by VLAN units."
	::= { axsVlanBridgeBase 1 }

axsVBBaseEntry OBJECT-TYPE
	SYNTAX  AxsVBBaseEntry
	ACCESS  not-accessible
	STATUS  mandatory
	DESCRIPTION
		"An information entry of every VLAN ID of axsVBBaseTable."
    INDEX { axsVBBaseIndex }
	::= { axsVBBaseTable 1 }

	AxsVBBaseEntry ::=
		SEQUENCE {
		    axsVBBaseIndex 			VlanIndex,
		    axsVBBaseBridgeAddress 		MacAddress,
		    axsVBBaseNumPorts 			INTEGER,
		    axsVBBaseType  			INTEGER,
		    axsVBBaseVlanIfIndex   		INTEGER,
		    axsVBBaseVlanType    		INTEGER,
		    axsVBBaseVlanID     			VlanIdOrZero,		
		    axsVBBaseAssociatedPrimaryVlan  	VlanIdOrZero,
		    axsVBBaseIfStatus      		INTEGER,
		    axsVBBaseLastChange       		TimeTicks,
		    axsVBBasePrivateVlanType       	INTEGER
                }

axsVBBaseIndex OBJECT-TYPE
	SYNTAX  VlanIndex
	ACCESS  read-only
	STATUS  mandatory
	DESCRIPTION
		"VLAN ID."
	::= { axsVBBaseEntry 1 }

axsVBBaseBridgeAddress OBJECT-TYPE
	SYNTAX  MacAddress
	ACCESS  read-only
	STATUS  mandatory
	DESCRIPTION
		"MAC address of VLAN."
	::= { axsVBBaseEntry 2 }

axsVBBaseNumPorts OBJECT-TYPE
	SYNTAX  INTEGER
	ACCESS  read-only
	STATUS  mandatory
	DESCRIPTION
		"The number of ports set at VLAN."
	::= { axsVBBaseEntry 3 }

axsVBBaseType OBJECT-TYPE
	SYNTAX  INTEGER {
		unknown(1),
		transparent-only(2),
		sourceroute-only(3),
		srt(4)
	      }
	ACCESS  read-only
	STATUS  mandatory
	DESCRIPTION
		"A bridging type VLAN may perform."
	::= { axsVBBaseEntry 4 }

axsVBBaseVlanIfIndex OBJECT-TYPE
	SYNTAX  INTEGER
	ACCESS  read-only
	STATUS  mandatory
	DESCRIPTION
		"Value of ifIndex of interface of VLAN."
	::= { axsVBBaseEntry 5 }

axsVBBaseVlanType OBJECT-TYPE
	SYNTAX  INTEGER {
		port-based(1),
		mac-based(2),
		protocol-based(3),
		ipsubnet-based(4)
	      }
	ACCESS  read-only
	STATUS  mandatory
	DESCRIPTION
		"VLAN type."
	::= { axsVBBaseEntry 6 }

axsVBBaseVlanID OBJECT-TYPE
	SYNTAX  VlanIdOrZero
	ACCESS  read-only
	STATUS  mandatory
	DESCRIPTION
		"Value of VID of VLAN-TAG corresponding VLAN."
	::= { axsVBBaseEntry 7 }

axsVBBaseAssociatedPrimaryVlan OBJECT-TYPE
	SYNTAX  VlanIdOrZero
	ACCESS  read-only
	STATUS  mandatory
	DESCRIPTION
		"Returns VLAN ID of Primary VLAN when private VLAN is used and 
		 the same VLAN is set at secondary VLAN."
	::= { axsVBBaseEntry 8 }

axsVBBaseIfStatus OBJECT-TYPE
	SYNTAX  INTEGER {
		up(1),
		down(2)
	      }
	ACCESS  read-only
	STATUS  mandatory
	DESCRIPTION
		"Status of interface against upper level protocol of VLAN."
	::= { axsVBBaseEntry 9 }

axsVBBaseLastChange OBJECT-TYPE
	SYNTAX  TimeTicks
	ACCESS  read-only
	STATUS  mandatory
	DESCRIPTION
		"Value of sysUpTime which is set when VLAN topology changes."
	::= { axsVBBaseEntry 10 }

axsVBBasePrivateVlanType OBJECT-TYPE
	SYNTAX  INTEGER {
		normal(1),
		primary(2),
		isolated(3),
		community(4)
	      }
	ACCESS  read-only
	STATUS  mandatory
	DESCRIPTION
		"A private VLAN type of VLAN."
	::= { axsVBBaseEntry 11 }

axsVBBasePortTable OBJECT-TYPE
	SYNTAX  SEQUENCE OF AxsVBBasePortEntry
	ACCESS  not-accessible
	STATUS  mandatory
	DESCRIPTION
		"An information table of dot1dBasePortTable by VLAN units."
	::= { axsVlanBridgeBase 2 }

axsVBBasePortEntry OBJECT-TYPE
	SYNTAX  AxsVBBasePortEntry
	ACCESS  not-accessible
	STATUS  mandatory
	DESCRIPTION
		"A configuration entry of axsVBBaseTable."
    INDEX { axsVBBasePortIndex, axsVBBasePort }
	::= { axsVBBasePortTable 1 }

	AxsVBBasePortEntry ::=
		SEQUENCE {
		    axsVBBasePortIndex       		VlanIndex,
		    axsVBBasePort	       		INTEGER,
		    axsVBBasePortIfIndex			INTEGER,
		    axsVBBasePortCircuit			OBJECT IDENTIFIER,
		    axsVBBasePortDelayExceededDiscards	Counter,
		    axsVBBasePortMtuExceededDiscards		Counter,
		    axsVBBasePortState			INTEGER,
		    axsVBBasePortTaggedState		INTEGER,
		    axsVBBasePortTranslatedTagID		VlanIdOrZero
                }

axsVBBasePortIndex OBJECT-TYPE
	SYNTAX  VlanIndex
	ACCESS  read-only
	STATUS  mandatory
	DESCRIPTION
		"VLAN ID."
	::= { axsVBBasePortEntry 1 }

axsVBBasePort OBJECT-TYPE
	SYNTAX  INTEGER
	ACCESS  read-only
	STATUS  mandatory
	DESCRIPTION
		"Port number of ports set at VLAN."
	::= { axsVBBasePortEntry 2 }

axsVBBasePortIfIndex OBJECT-TYPE
	SYNTAX  INTEGER
	ACCESS  read-only
	STATUS  mandatory
	DESCRIPTION
		"Value of ifIndex corresponding ports set at VLAN."
	::= { axsVBBasePortEntry 3 }

axsVBBasePortCircuit OBJECT-TYPE
	SYNTAX  OBJECT IDENTIFIER
	ACCESS  read-only
	STATUS  mandatory
	DESCRIPTION
		"Identifier which identifieds ports when VLAN ports
		 have the same value as axsVBBasePortIfIndex."
	::= { axsVBBasePortEntry 4 }

axsVBBasePortDelayExceededDiscards OBJECT-TYPE
	SYNTAX  Counter
	ACCESS  read-only
	STATUS  mandatory
	DESCRIPTION
		"Total number of discard frame caused by passing delay occured at VLAN ports."
	::= { axsVBBasePortEntry 5 }

axsVBBasePortMtuExceededDiscards OBJECT-TYPE
	SYNTAX  Counter
	ACCESS  read-only
	STATUS  mandatory
	DESCRIPTION
		"Total number of discard frame caused by data over flow occured at VLAN ports."
	::= { axsVBBasePortEntry 6 }

axsVBBasePortState OBJECT-TYPE
	SYNTAX  INTEGER {
		disabled(1),
		blocking(2),
		listening(3),
		learning(4),
		forwarding(5),
		broken(6),
		fix-forwarding(7)
	      }
	ACCESS  read-only
	STATUS  mandatory
	DESCRIPTION
		"STP port status of port set at VLAN."
	::= { axsVBBasePortEntry 7 }

axsVBBasePortTaggedState OBJECT-TYPE
	SYNTAX  INTEGER {
		untagged(1),
		tagged(2)
            }
	ACCESS  read-only
	STATUS  mandatory
	DESCRIPTION
		"Status of VLAN-TAG configuration of ports set at VLAN."
	::= { axsVBBasePortEntry 8 }

axsVBBasePortTranslatedTagID OBJECT-TYPE
	SYNTAX  VlanIdOrZero
	ACCESS  read-only
	STATUS  mandatory
	DESCRIPTION
		"Translated ID of VLAN when TAG translation is set."
	::= { axsVBBasePortEntry 9 }

axsVBStpTable OBJECT-TYPE
	SYNTAX  SEQUENCE OF AxsVBStpEntry
	ACCESS  not-accessible
	STATUS  mandatory
	DESCRIPTION
		"An information table of dot1dStpTable by VLAN units."
	::= { axsVlanBridgeStp 1 }

axsVBStpEntry OBJECT-TYPE
	SYNTAX  AxsVBStpEntry
	ACCESS  not-accessible
	STATUS  mandatory
	DESCRIPTION
		"A configuration entry of axsVBStpTable."
    INDEX { axsVBStpIndex }
	::= { axsVBStpTable 1 }

	AxsVBStpEntry ::=
		SEQUENCE {
		    axsVBStpIndex 			VlanIndex,
		    axsVBStpProtocolSpecification 	INTEGER,
		    axsVBStpPriority 			INTEGER,
		    axsVBStpTimeSinceTopologyChange	TimeTicks,
		    axsVBStpTopChanges			Counter,
		    axsVBStpDesignatedRoot		BridgeId,
		    axsVBStpRootCost			INTEGER,
		    axsVBStpRootPort			INTEGER,
		    axsVBStpMaxAge			Timeout,
		    axsVBStpHelloTime			Timeout,
		    axsVBStpHoldTime			INTEGER,
		    axsVBStpForwardDelay			Timeout,
		    axsVBStpBridgeMaxAge 		Timeout,
		    axsVBStpBridgeHelloTime 		Timeout,
		    axsVBStpBridgeForwardDelay 		Timeout
                }

axsVBStpIndex OBJECT-TYPE
	SYNTAX  VlanIndex
	ACCESS  read-only
	STATUS  mandatory
	DESCRIPTION
		"VLAN ID."
	::= { axsVBStpEntry 1 }

axsVBStpProtocolSpecification OBJECT-TYPE
	SYNTAX  INTEGER {
		unknown(1),
		decLb100(2),
		ieee8021d(3),
		ieee8021w(4)
	      }
	ACCESS  read-only
	STATUS  mandatory
	DESCRIPTION
		"A kind of spanning tree protocol by VLAN units."
	::= { axsVBStpEntry 2 }

axsVBStpPriority OBJECT-TYPE
	SYNTAX  INTEGER
	ACCESS  read-only
	STATUS  mandatory
	DESCRIPTION
		"Priority value of spanning tree by VLAN units."
	::= { axsVBStpEntry 3 }

axsVBStpTimeSinceTopologyChange OBJECT-TYPE
	SYNTAX  TimeTicks
	ACCESS  read-only
	STATUS  mandatory
	DESCRIPTION
		"Elapsed time since topology change of spanning tree by VLAN units."
	::= { axsVBStpEntry 4 }

axsVBStpTopChanges OBJECT-TYPE
	SYNTAX  Counter
	ACCESS  read-only
	STATUS  mandatory
	DESCRIPTION
		"The number of times of topology changes of spanning tree by VLAN units."
	::= { axsVBStpEntry 5 }

axsVBStpDesignatedRoot OBJECT-TYPE
	SYNTAX  BridgeId
	ACCESS  read-only
	STATUS  mandatory
	DESCRIPTION
		"Root bridge identifier of spanning tree by VLAN units."
	::= { axsVBStpEntry 6 }

axsVBStpRootCost OBJECT-TYPE
	SYNTAX  INTEGER
	ACCESS  read-only
	STATUS  mandatory
	DESCRIPTION
		"Root path cost kept by spanning tree by VLAN units."
	::= { axsVBStpEntry 7 }

axsVBStpRootPort OBJECT-TYPE
	SYNTAX  INTEGER
	ACCESS  read-only
	STATUS  mandatory
	DESCRIPTION
		"Root port value kept by spanning tree by VLAN units."
	::= { axsVBStpEntry 8 }

axsVBStpMaxAge OBJECT-TYPE
	SYNTAX  Timeout
	ACCESS  read-only
	STATUS  mandatory
	DESCRIPTION
		"Maximum aging time kept by spanning tree by VLAN units."
	::= { axsVBStpEntry 9 }

axsVBStpHelloTime OBJECT-TYPE
	SYNTAX  Timeout
	ACCESS  read-only
	STATUS  mandatory
	DESCRIPTION
		"Hello time kept by spanning tree by VLAN units."
	::= { axsVBStpEntry 10 }

axsVBStpHoldTime OBJECT-TYPE
	SYNTAX  INTEGER
	ACCESS  read-only
	STATUS  mandatory
	DESCRIPTION
		"Hold time kept by spanning tree by VLAN units."
	::= { axsVBStpEntry 11 }

axsVBStpForwardDelay OBJECT-TYPE
	SYNTAX  Timeout
	ACCESS  read-only
	STATUS  mandatory
	DESCRIPTION
		"Transfer delay time kept by spanning tree by VLAN units."
	::= { axsVBStpEntry 12 }

axsVBStpBridgeMaxAge OBJECT-TYPE
	SYNTAX  Timeout
	ACCESS  read-only
	STATUS  mandatory
	DESCRIPTION
		"Maximum aging time used when spanning tree acts as a root bridge by VLAN units."
	::= { axsVBStpEntry 13 }

axsVBStpBridgeHelloTime OBJECT-TYPE
	SYNTAX  Timeout
	ACCESS  read-only
	STATUS  mandatory
	DESCRIPTION
		"Hello time used when spanning tree act as a root bridge by VLAN units."
	::= { axsVBStpEntry 14 }

axsVBStpBridgeForwardDelay OBJECT-TYPE
	SYNTAX  Timeout
	ACCESS  read-only
	STATUS  mandatory
	DESCRIPTION
		"Transfer delay time used when spanning tree act as a root bridge by VLAN units."
	::= { axsVBStpEntry 15 }

axsVBStpPortTable OBJECT-TYPE
	SYNTAX  SEQUENCE OF AxsVBStpPortEntry
	ACCESS  not-accessible
	STATUS  mandatory
	DESCRIPTION
		"An information table of dot1dStpPortTable by VLAN units."
	::= { axsVlanBridgeStp 2 }

axsVBStpPortEntry OBJECT-TYPE
	SYNTAX  AxsVBStpPortEntry
	ACCESS  not-accessible
	STATUS  mandatory
	DESCRIPTION
		"A configuration entry of axsVBStpPortTable."
        INDEX { axsVBStpPortIndex, axsVBStpPort }
	::= { axsVBStpPortTable 1 }

	AxsVBStpPortEntry ::=
		SEQUENCE {
		    axsVBStpPortIndex			VlanIndex,
		    axsVBStpPort				INTEGER,
		    axsVBStpPortPriority			INTEGER,
		    axsVBStpPortState			INTEGER,
		    axsVBStpPortEnable			INTEGER,
		    axsVBStpPortPathCost			INTEGER,
		    axsVBStpPortDesignatedRoot		BridgeId,
		    axsVBStpPortDesignatedCost		INTEGER,
		    axsVBStpPortDesignatedBridge		BridgeId,
		    axsVBStpPortDesignatedPort		OCTET STRING,
		    axsVBStpPortForwardTransitions	Counter
                }

axsVBStpPortIndex OBJECT-TYPE
	SYNTAX  VlanIndex
	ACCESS  read-only
	STATUS  mandatory
	DESCRIPTION
		"VLAN ID."
	::= { axsVBStpPortEntry 1 }

axsVBStpPort OBJECT-TYPE
	SYNTAX  INTEGER
	ACCESS  read-only
	STATUS  mandatory
	DESCRIPTION
		"Port number corresponding configuration entry."
	::= { axsVBStpPortEntry 2 }

axsVBStpPortPriority OBJECT-TYPE
	SYNTAX  INTEGER
	ACCESS  read-only
	STATUS  mandatory
	DESCRIPTION
		"Priority of port by VLAN units."
	::= { axsVBStpPortEntry 3 }

axsVBStpPortState OBJECT-TYPE
	SYNTAX  INTEGER {
		disabled(1),
		blocking(2),
		listening(3),
		learning(4),
		forwarding(5),
		broken(6)
	      }
	ACCESS  read-only
	STATUS  mandatory
	DESCRIPTION
		"Present status of port by VLAN units."
	::= { axsVBStpPortEntry 4 }

axsVBStpPortEnable OBJECT-TYPE
	SYNTAX  INTEGER {
		enabled(1),
		disabled(2)
	      }
	ACCESS  read-only
	STATUS  mandatory
	DESCRIPTION
		"Value whether spanning tree is enabled or not at the port by VLAN units."
	::= { axsVBStpPortEntry 5 }

axsVBStpPortPathCost OBJECT-TYPE
	SYNTAX  INTEGER
	ACCESS  read-only
	STATUS  mandatory
	DESCRIPTION
		"Path cost value of the port by VLAN units."
	::= { axsVBStpPortEntry 6 }

axsVBStpPortDesignatedRoot OBJECT-TYPE
	SYNTAX  BridgeId
	ACCESS  read-only
	STATUS  mandatory
	DESCRIPTION
		"Value of root bridge identifier by VLAN units stored in BPDU from specified bridge."
	::= { axsVBStpPortEntry 7 }

axsVBStpPortDesignatedCost OBJECT-TYPE
	SYNTAX  INTEGER
	ACCESS  read-only
	STATUS  mandatory
	DESCRIPTION
		"Path cost value of specified port connected to the port by VLAN units."
	::= { axsVBStpPortEntry 8 }

axsVBStpPortDesignatedBridge OBJECT-TYPE
	SYNTAX  BridgeId
	ACCESS  read-only
	STATUS  mandatory
	DESCRIPTION
		"Bridge identifier of bridge which this port regards as specified bridge by VLAN units."
	::= { axsVBStpPortEntry 9 }

axsVBStpPortDesignatedPort OBJECT-TYPE
	SYNTAX  OCTET STRING
	ACCESS  read-only
	STATUS  mandatory
	DESCRIPTION
		"Port identifier of specified bridge connected to this port by VLAN units."
	::= { axsVBStpPortEntry 10 }

axsVBStpPortForwardTransitions OBJECT-TYPE
	SYNTAX  Counter
	ACCESS  read-only
	STATUS  mandatory
	DESCRIPTION
		"The number of times of changes from learning status into forwarding status."
	::= { axsVBStpPortEntry 11 }

axsVBTpTable OBJECT-TYPE
	SYNTAX  SEQUENCE OF AxsVBTpEntry
	ACCESS  not-accessible
	STATUS  mandatory
	DESCRIPTION
		"A dot1dTp information table by VLAN units."
	::= { axsVlanBridgeTp 1 }

axsVBTpEntry OBJECT-TYPE
	SYNTAX  AxsVBTpEntry
	ACCESS  not-accessible
	STATUS  mandatory
	DESCRIPTION
		"A configuration entry of axsVBTpTable."
    INDEX { axsVBTpIndex }
	::= { axsVBTpTable 1 }

	AxsVBTpEntry ::=
		SEQUENCE {
		    axsVBTpIndex				VlanIndex,
		    axsVBTpLearnedEntryDiscards		Counter,
		    axsVBTpAgingTime			INTEGER
                }

axsVBTpIndex OBJECT-TYPE
	SYNTAX  VlanIndex
	ACCESS  read-only
	STATUS  mandatory
	DESCRIPTION
		"VLAN ID."
	::= { axsVBTpEntry 1 }

axsVBTpLearnedEntryDiscards OBJECT-TYPE
	SYNTAX  Counter
	ACCESS  read-only
	STATUS  mandatory
	DESCRIPTION
		"The number of discarded entries because of lack of
		 not-used domain in filtering data base."
	::= { axsVBTpEntry 2 }

axsVBTpAgingTime OBJECT-TYPE
	SYNTAX  INTEGER
	ACCESS  read-only
	STATUS  mandatory
	DESCRIPTION
		"Time-out time to aging-out entry of filtering date base which is learned dynamically."
	::= { axsVBTpEntry 3 }

axsVBTpFdbTable OBJECT-TYPE
	SYNTAX  SEQUENCE OF AxsVBTpFdbEntry
	ACCESS  not-accessible
	STATUS  mandatory
	DESCRIPTION
		"An information of dot1dTpFdbTable by VLAN units."
	::= { axsVlanBridgeTp 2 }

axsVBTpFdbEntry OBJECT-TYPE
	SYNTAX  AxsVBTpFdbEntry
	ACCESS  not-accessible
	STATUS  mandatory
	DESCRIPTION
		"A configuration entry of axsVBTpFdbTable."
    INDEX { axsVBTpFdbIndex, axsVBTpFdbAddress }
	::= { axsVBTpFdbTable 1 }

	AxsVBTpFdbEntry ::=
		SEQUENCE {
		    axsVBTpFdbIndex			VlanIndex,
		    axsVBTpFdbAddress			MacAddress,
		    axsVBTpFdbPort			INTEGER,
		    axsVBTpFdbStatus			INTEGER
                }

axsVBTpFdbIndex OBJECT-TYPE
	SYNTAX  VlanIndex
	ACCESS  read-only
	STATUS  mandatory
	DESCRIPTION
		"VLAN ID."
	::= { axsVBTpFdbEntry 1 }

axsVBTpFdbAddress OBJECT-TYPE
	SYNTAX  MacAddress
	ACCESS  read-only
	STATUS  mandatory
	DESCRIPTION
		"Unicast MAC address of filtering data base entry."
	::= { axsVBTpFdbEntry 2 }

axsVBTpFdbPort OBJECT-TYPE
	SYNTAX  INTEGER
	ACCESS  read-only
	STATUS  mandatory
	DESCRIPTION
		"Indicates that it hasn't learnt port number when
		 port number 0 receives frame having MAC address
		 as source address which axsVBTpFdbAddress indicates."
	::= { axsVBTpFdbEntry 3 }

axsVBTpFdbStatus OBJECT-TYPE
	SYNTAX  INTEGER {
		other(1),
		invalid(2),
		learned(3),
		self(4),
		mgmt(5)
	      }
	ACCESS  read-only
	STATUS  mandatory
	DESCRIPTION
		"Status of filtering data base."
	::= { axsVBTpFdbEntry 4 }

axsVBTpPortTable OBJECT-TYPE
	SYNTAX  SEQUENCE OF AxsVBTpPortEntry
	ACCESS  not-accessible
	STATUS  mandatory
	DESCRIPTION
		"An information table of dot1dTpPortTable by VLAN units."
	::= { axsVlanBridgeTp 3 }

axsVBTpPortEntry OBJECT-TYPE
	SYNTAX  AxsVBTpPortEntry
	ACCESS  not-accessible
	STATUS  mandatory
	DESCRIPTION
		"An information entry of axsVBTpPortTable of ports."
    INDEX { axsVBTpPortIndex, axsVBTpPort }
	::= { axsVBTpPortTable 1 }

	AxsVBTpPortEntry ::=
		SEQUENCE {
		    axsVBTpPortIndex			VlanIndex,
		    axsVBTpPort				INTEGER,
		    axsVBTpPortMaxInfo			INTEGER,
		    axsVBTpPortInFrames 		Counter,
		    axsVBTpPortOutFrames 		Counter,
		    axsVBTpPortInDiscards  		Counter
                }

axsVBTpPortIndex OBJECT-TYPE
	SYNTAX  VlanIndex
	ACCESS  read-only
	STATUS  mandatory
	DESCRIPTION
		"VLAN ID."
	::= { axsVBTpPortEntry 1 }

axsVBTpPort OBJECT-TYPE
	SYNTAX  INTEGER
	ACCESS  read-only
	STATUS  mandatory
	DESCRIPTION
		"Port number that indicates which port management
		 information in the entry corresponds."
	::= { axsVBTpPortEntry 2 }

axsVBTpPortMaxInfo OBJECT-TYPE
	SYNTAX  INTEGER
	ACCESS  read-only
	STATUS  mandatory
	DESCRIPTION
		"Maximum INFO field size of the port by VLAN units."
	::= { axsVBTpPortEntry 3 }

axsVBTpPortInFrames OBJECT-TYPE
	SYNTAX  Counter
	ACCESS  read-only
	STATUS  mandatory
	DESCRIPTION
		"The number of reception frame of the port by VLAN units."
	::= { axsVBTpPortEntry 4 }

axsVBTpPortOutFrames OBJECT-TYPE
	SYNTAX  Counter
	ACCESS  read-only
	STATUS  mandatory
	DESCRIPTION
		"The number of sending frame of the port by VLAN units."
	::= { axsVBTpPortEntry 5 }

axsVBTpPortInDiscards OBJECT-TYPE
	SYNTAX  Counter
	ACCESS  read-only
	STATUS  mandatory
	DESCRIPTION
		"The number of reception frame of the port by VLAN units."
	::= { axsVBTpPortEntry 6 }

axsVBStaticTable OBJECT-TYPE
	SYNTAX  SEQUENCE OF AxsVBStaticEntry
	ACCESS  not-accessible
	STATUS  mandatory
	DESCRIPTION
		"An information table of dot1dStaticTable by VLAN units."
	::= { axsVlanBridgeStatic 1 }

axsVBStaticEntry OBJECT-TYPE
	SYNTAX  AxsVBStaticEntry
	ACCESS  not-accessible
	STATUS  mandatory
	DESCRIPTION
		"A configuration entry of axsVBStaticTable."
    INDEX { axsVBStaticIndex, axsVBStaticAddress }
	::= { axsVBStaticTable 1 }

	AxsVBStaticEntry ::=
		SEQUENCE {
		    axsVBStaticIndex			VlanIndex,
		    axsVBStaticAddress			MacAddress,
		    axsVBStaticReceivePort		INTEGER,
		    axsVBStaticAllowedToGoTo		OCTET STRING,		
		    axsVBStaticStatus 	 		INTEGER
		}

axsVBStaticIndex OBJECT-TYPE
	SYNTAX  VlanIndex
	ACCESS  read-only
	STATUS  mandatory
	DESCRIPTION
		"VLAN ID."
	::= { axsVBStaticEntry 1 }

axsVBStaticAddress OBJECT-TYPE
	SYNTAX  MacAddress
	ACCESS  read-only
	STATUS  mandatory
	DESCRIPTION
		"MAC address of either unicast, group or broadcast."
	::= { axsVBStaticEntry 2 }

axsVBStaticReceivePort OBJECT-TYPE
	SYNTAX  INTEGER
	ACCESS  read-only
	STATUS  mandatory
	DESCRIPTION
		"Reception port number which is applied the entry."
	::= { axsVBStaticEntry 3 }

axsVBStaticAllowedToGoTo OBJECT-TYPE
	SYNTAX  OCTET STRING
	ACCESS  read-only
	STATUS  mandatory
	DESCRIPTION
		"Bit map of port indicating destination port when transfering
		 frame whose destination is MAC address kept by this entry"
	::= { axsVBStaticEntry 4 }

axsVBStaticStatus OBJECT-TYPE
	SYNTAX  INTEGER {
		other(1),
		invalid(2),
		permanent(3),
		deleteOnReset(4),
		deleteOnTimeout(5)
	      }
	ACCESS  read-only
	STATUS  mandatory
	DESCRIPTION
		"Status of the entry."
	::= { axsVBStaticEntry 5 }

axsVlanBridgeMaxVlans OBJECT-TYPE
	SYNTAX  VlanIndex
	ACCESS  read-only
	STATUS  mandatory
	DESCRIPTION
		"Maximum value of VLAN ID of this device."
	::= { axsVlanBridge 101 }

axsVlanBridgeMaxSpans OBJECT-TYPE
	SYNTAX  VlanIndex
	ACCESS  read-only
	STATUS  mandatory
	DESCRIPTION
		"Maximum value of VLAN ID of VLAN which may operate
		 spanning tree in this device."
	::= { axsVlanBridge 102 }

axsVlanTagTranslationTable OBJECT-TYPE
	SYNTAX  SEQUENCE OF AxsVlanTagTranslationEntry
	ACCESS  not-accessible
	STATUS  mandatory
	DESCRIPTION
		"The information table about a Tag conversion function"
	::= { axsVlanTagTranslation 1 }

axsVlanTagTranslationEntry OBJECT-TYPE
	SYNTAX  AxsVlanTagTranslationEntry
	ACCESS  not-accessible
	STATUS  mandatory
	DESCRIPTION
		"The entry of the information table about a Tag conversion function"
    INDEX { axsVlanTagTranslationVlanId,axsVlanTagTranslationTranslatedId }
	::= { axsVlanTagTranslationTable 1 }

	AxsVlanTagTranslationEntry ::=
		SEQUENCE {
		    axsVlanTagTranslationVlanId		INTEGER,
		    axsVlanTagTranslationTranslatedId	INTEGER,
		    axsVlanTagTranslationPorts		PortList
                }

axsVlanTagTranslationVlanId OBJECT-TYPE
	SYNTAX  INTEGER
	ACCESS  not-accessible
	STATUS  mandatory
	DESCRIPTION
		"VLAN ID which has set up the Tag conversion function"
	::= { axsVlanTagTranslationEntry 1 }

axsVlanTagTranslationTranslatedId OBJECT-TYPE
	SYNTAX  INTEGER
	ACCESS  not-accessible
	STATUS  mandatory
	DESCRIPTION
		"Translated ID set up by the Tag conversion function"
	::= { axsVlanTagTranslationEntry 2 }

axsVlanTagTranslationPorts OBJECT-TYPE
	SYNTAX  PortList
	ACCESS  read-only
	STATUS  mandatory
	DESCRIPTION
		"The port list which has set up the same Translated ID by the same VLAN by the Tag conversion function"
	::= { axsVlanTagTranslationEntry 3 }

--  OADP Group

axsOadpGlobalActive  OBJECT-TYPE
	SYNTAX  TruthValue
	ACCESS  read-only
	STATUS  mandatory
	DESCRIPTION
		"Operation status of OADP function. Status set
		 by enable or disable in Oadp configuration.
		 enable : 1
		 disable: 2"
	::= { axsOadpGlobalInfo 1 }

axsOadpGlobalCdpActive  OBJECT-TYPE
	SYNTAX  TruthValue
	ACCESS  read-only
	STATUS  mandatory
	DESCRIPTION
		"Operation status of CDP reception function.
		 Status whether cdp-listener is set or not in oadp configuration.
		 cdp-listener           : 1
		 cdp-listener is not set: 2"
	::= { axsOadpGlobalInfo 2 }

axsOadpGlobalMessageInterval OBJECT-TYPE
	SYNTAX  INTEGER
	ACCESS  read-only
	STATUS  mandatory
	DESCRIPTION
		"Sending interval of OADP frame. The value of interval-time in oadp configuration."
	::= { axsOadpGlobalInfo 3 }

axsOadpGlobalHoldTime OBJECT-TYPE
	SYNTAX  INTEGER
	ACCESS  read-only
	STATUS  mandatory
	DESCRIPTION
		"Neighbor device's holding time of OADP frame which this device send.
		 The value of hold-time in oadp configuration."
	::= { axsOadpGlobalInfo 4 }

axsOadpGlobalCacheLastChange OBJECT-TYPE
	SYNTAX  TimeTicks
	ACCESS  read-only
	STATUS  mandatory
	DESCRIPTION
		"Value of sysUpTime which is set when axsOadpNeighborTable is updated."
	::= { axsOadpGlobalInfo 5 }

axsOadpGlobalName OBJECT-TYPE
	SYNTAX  DisplayString
	ACCESS  read-only
	STATUS  mandatory
	DESCRIPTION
		"Device identifier."
	::= { axsOadpGlobalInfo 6 }

axsOadpGlobalNameType OBJECT-TYPE
	SYNTAX  INTEGER {
		other(1),
		sysName(2),
		serialNumber(3),
		macaddress(4)
    }
	ACCESS  read-only
	STATUS  mandatory
	DESCRIPTION
		"Kind of axsOadpGlobalName."
	::= { axsOadpGlobalInfo 7 }

axsOadpPortConfigTable OBJECT-TYPE
	SYNTAX  SEQUENCE OF AxsOadpPortConfigEntry
	ACCESS  not-accessible
	STATUS  mandatory
	DESCRIPTION
		"A table of OADP port information."
	::= { axsOadpPortInfo 1 }

axsOadpPortConfigEntry OBJECT-TYPE
	SYNTAX  AxsOadpPortConfigEntry
	ACCESS  not-accessible
	STATUS  mandatory
	DESCRIPTION
		"An entry of OADP port information."
    INDEX { axsOadpPortConfigIfIndex }
	::= { axsOadpPortConfigTable 1 }

	AxsOadpPortConfigEntry ::=
		SEQUENCE {
		    axsOadpPortConfigIfIndex	InterfaceIndex,
		    axsOadpPortConfigActive	TruthValue
		}

axsOadpPortConfigIfIndex OBJECT-TYPE
	SYNTAX  InterfaceIndex
	ACCESS  read-only
	STATUS  mandatory
	DESCRIPTION
		"Port identification index. The same value as ifIndex.
		 This is only for physical ports and LA ports which are given
		 ifIndex."
	::= { axsOadpPortConfigEntry 1 }

axsOadpPortConfigActive OBJECT-TYPE
	SYNTAX  TruthValue
	ACCESS  read-only
	STATUS  mandatory
	DESCRIPTION
		"Status of specified port."
	::= { axsOadpPortConfigEntry 2 }

axsOadpNeighborTable OBJECT-TYPE
	SYNTAX  SEQUENCE OF AxsOadpNeighborEntry
	ACCESS  not-accessible
	STATUS  mandatory
	DESCRIPTION
		"A table of OADP neighbor nodes."
	::= { axsOadpNeighborInfo 1 }

axsOadpNeighborEntry OBJECT-TYPE
	SYNTAX  AxsOadpNeighborEntry
	ACCESS  not-accessible
	STATUS  mandatory
	DESCRIPTION
		"An entry of OADP neighbor nodes."
    INDEX { axsOadpIfIndex, axsOadpTagID, axsOadpNeighborIndex, axsOadpNeighborTagID }
	::= { axsOadpNeighborTable 1 }

	AxsOadpNeighborEntry ::=
		SEQUENCE {
		    axsOadpIfIndex			InterfaceIndex,
		    axsOadpTagID		 		INTEGER, 
		    axsOadpNeighborIndex  		INTEGER,
		    axsOadpNeighborTagID   		INTEGER,
		    axsOadpNeighborVendorType   		INTEGER,
		    axsOadpNeighborSNMPAgentAddressType 	INTEGER,
		    axsOadpNeighborSNMPAgentAddress  	DisplayString,
		    axsOadpNeighborDescr		   	DisplayString,
		    axsOadpNeighborDeviceID	   	DisplayString,
		    axsOadpNeighborSlotPort 	   	DisplayString,
		    axsOadpNeighborIfIndex  	   	InterfaceIndex,
		    axsOadpNeighborIfSpeed   	   	Gauge,
		    axsOadpNeighborDeviceType   	   	DisplayString,
		    axsOadpNeighborService   	   	OCTET STRING,
		    axsOadpNeighborVTPMgmtDomain    	DisplayString,
		    axsOadpNeighborNativeVLAN     	INTEGER,
		    axsOadpNeighborDuplex 	     	INTEGER,
		    axsOadpNeighborApplianceID  	     	Gauge,
		    axsOadpNeighborVlanID   	     	Gauge,
		    axsOadpNeighborPowerConsumption     	Gauge,
		    axsOadpNeighborMTU           	Gauge,
		    axsOadpNeighborSysName            	DisplayString,
		    axsOadpNeighborSysObjectID          	OBJECT IDENTIFIER,
		    axsOadpNeighborSecondarySNMPAgentAddressType  INTEGER,
		    axsOadpNeighborSecondarySNMPAgentAddress      DisplayString,
		    axsOadpNeighborPhysLocation          DisplayString,
		    axsOadpNeighborCacheLastChange       TimeTicks,
		    axsOadpNeighborIfHighSpeed           Gauge
		}

axsOadpIfIndex OBJECT-TYPE
	SYNTAX  InterfaceIndex
	ACCESS  read-only
	STATUS  mandatory
	DESCRIPTION
		"ifIndex of reception interface."
	::= { axsOadpNeighborEntry 1 }

axsOadpTagID OBJECT-TYPE
	SYNTAX  INTEGER
	ACCESS  read-only
	STATUS  mandatory
	DESCRIPTION
		"Tag ID of IEEE802.1Q which is attached MAC frame."
	::= { axsOadpNeighborEntry 2 }

axsOadpNeighborIndex OBJECT-TYPE
	SYNTAX  INTEGER
	ACCESS  read-only
	STATUS  mandatory
	DESCRIPTION
		"Unique numeric which identifies neighbor nodes"
	::= { axsOadpNeighborEntry 3 }

axsOadpNeighborTagID OBJECT-TYPE
	SYNTAX  INTEGER
	ACCESS  read-only
	STATUS  mandatory
	DESCRIPTION
		"Value set at TagID TLV in OADP PDU which is sent from neighbor node."
	::= { axsOadpNeighborEntry 4 }

axsOadpNeighborVendorType OBJECT-TYPE
	SYNTAX  INTEGER {
		other(1),
		oadp(2),
		cdp(3)
    }
	ACCESS  read-only
	STATUS  mandatory
	DESCRIPTION
		"Protocol type used to find to neighbor nodes."
	::= { axsOadpNeighborEntry 5 }

axsOadpNeighborSNMPAgentAddressType OBJECT-TYPE
	SYNTAX  INTEGER {
		ipv4(1),
		ipv6(20),
		other-notSupported(65535)
    }
	ACCESS  read-only
	STATUS  mandatory
	DESCRIPTION
		"A kind of agent address to get information by SNMP."
	::= { axsOadpNeighborEntry 6 }

axsOadpNeighborSNMPAgentAddress OBJECT-TYPE
	SYNTAX  DisplayString
	ACCESS  read-only
	STATUS  mandatory
	DESCRIPTION
		"DisplayString formed information of agent address to get information by SNMP."
	::= { axsOadpNeighborEntry 7 }

axsOadpNeighborDescr OBJECT-TYPE
	SYNTAX  DisplayString
	ACCESS  read-only
	STATUS  mandatory
	DESCRIPTION
		"String of sysDescr of neighbor node."
	::= { axsOadpNeighborEntry 8 }

axsOadpNeighborDeviceID OBJECT-TYPE
	SYNTAX  DisplayString
	ACCESS  read-only
	STATUS  mandatory
	DESCRIPTION
		"Neighbor node's device identifier."
	::= { axsOadpNeighborEntry 9 }

axsOadpNeighborSlotPort OBJECT-TYPE
	SYNTAX  DisplayString
	ACCESS  read-only
	STATUS  mandatory
	DESCRIPTION
		"Unique string which identifies neighbor's sending interface."
	::= { axsOadpNeighborEntry 10 }

axsOadpNeighborIfIndex OBJECT-TYPE
	SYNTAX  InterfaceIndex
	ACCESS  read-only
	STATUS  mandatory
	DESCRIPTION
		"ifIndex of sending interface of neighbor node."
	::= { axsOadpNeighborEntry 11 }

axsOadpNeighborIfSpeed OBJECT-TYPE
	SYNTAX  Gauge
	ACCESS  read-only
	STATUS  mandatory
	DESCRIPTION
		"ifSpeed of sending interface of neighbor node."
	::= { axsOadpNeighborEntry 12 }

axsOadpNeighborDeviceType OBJECT-TYPE
	SYNTAX  DisplayString
	ACCESS  read-only
	STATUS  mandatory
	DESCRIPTION
		"Device name of neighbor node."
	::= { axsOadpNeighborEntry 13 }

axsOadpNeighborService OBJECT-TYPE
	SYNTAX  OCTET STRING
	ACCESS  read-only
	STATUS  mandatory
	DESCRIPTION
		"Functions neighbor node can offer."
	::= { axsOadpNeighborEntry 14 }

axsOadpNeighborVTPMgmtDomain OBJECT-TYPE
	SYNTAX  DisplayString
	ACCESS  read-only
	STATUS  mandatory
	DESCRIPTION
		"VTP Management Domain of sending interface of neighbor node."
	::= { axsOadpNeighborEntry 15 }

axsOadpNeighborNativeVLAN OBJECT-TYPE
	SYNTAX  INTEGER
	ACCESS  read-only
	STATUS  mandatory
	DESCRIPTION
		"Native VLAN number of sending interface of neighbor node."
	::= { axsOadpNeighborEntry 16 }

axsOadpNeighborDuplex OBJECT-TYPE
	SYNTAX  INTEGER {
		unknown(1),
		half(2),
		full(3)
    }
	ACCESS  read-only
	STATUS  mandatory
	DESCRIPTION
		"Duplex information of sending interface of neighbor node."
	::= { axsOadpNeighborEntry 17 }

axsOadpNeighborApplianceID OBJECT-TYPE
	SYNTAX  Gauge
	ACCESS  read-only
	STATUS  mandatory
	DESCRIPTION
		"Appliance ID of neighbor node."
	::= { axsOadpNeighborEntry 18 }

axsOadpNeighborVlanID OBJECT-TYPE
	SYNTAX  Gauge
	ACCESS  read-only
	STATUS  mandatory
	DESCRIPTION
		"VLAN ID for VoIP of neighbor node."
	::= { axsOadpNeighborEntry 19 }

axsOadpNeighborPowerConsumption OBJECT-TYPE
	SYNTAX  Gauge
	ACCESS  read-only
	STATUS  mandatory
	DESCRIPTION
		"Electric power consumption of neighbor node."
	::= { axsOadpNeighborEntry 20 }

axsOadpNeighborMTU OBJECT-TYPE
	SYNTAX  Gauge
	ACCESS  read-only
	STATUS  mandatory
	DESCRIPTION
		"MTU of sending interface of neighbor node."
	::= { axsOadpNeighborEntry 21 }

axsOadpNeighborSysName OBJECT-TYPE
	SYNTAX  DisplayString
	ACCESS  read-only
	STATUS  mandatory
	DESCRIPTION
		"sysName of neighbor node."
	::= { axsOadpNeighborEntry 22 }

axsOadpNeighborSysObjectID OBJECT-TYPE
	SYNTAX  OBJECT IDENTIFIER
	ACCESS  read-only
	STATUS  mandatory
	DESCRIPTION
		"sysObjectID of neighbor node."
	::= { axsOadpNeighborEntry 23 }

axsOadpNeighborSecondarySNMPAgentAddressType OBJECT-TYPE
	SYNTAX  INTEGER {
		ipv4(1),
		ipv6(20),
		other-notSupported(65535)
    }
	ACCESS  read-only
	STATUS  mandatory
	DESCRIPTION
		"A kind of agent secondary address to get information by SNMP."
	::= { axsOadpNeighborEntry 24 }

axsOadpNeighborSecondarySNMPAgentAddress OBJECT-TYPE
	SYNTAX  DisplayString
	ACCESS  read-only
	STATUS  mandatory
	DESCRIPTION
		"DisplayString formed information of agent secondary address to get information by SNMP."
	::= { axsOadpNeighborEntry 25 }

axsOadpNeighborPhysLocation OBJECT-TYPE
	SYNTAX  DisplayString
	ACCESS  read-only
	STATUS  mandatory
	DESCRIPTION
		"sysLocation of neighbor node."
	::= { axsOadpNeighborEntry 26 }

axsOadpNeighborCacheLastChange OBJECT-TYPE
	SYNTAX  TimeTicks
	ACCESS  read-only
	STATUS  mandatory
	DESCRIPTION
		"Value of sysUpTime which is set when axsOadpNeighborEntry about neighbor node is updated."
	::= { axsOadpNeighborEntry 27 }

axsOadpNeighborIfHighSpeed OBJECT-TYPE
	SYNTAX  Gauge
	ACCESS  read-only
	STATUS  mandatory
	DESCRIPTION
		"ifHighSpeed of sending interface of neighbor node."
	::= { axsOadpNeighborEntry 28 }

--  axsFlow Group

axsAccessFilterStatsInTable OBJECT-TYPE
        SYNTAX  SEQUENCE OF AxsAccessFilterStatsInEntry
        ACCESS  not-accessible
        STATUS  mandatory
        DESCRIPTION
                "Table information on corresponding number of packets to flow detection condition 
                and operation information set by access list."
        ::= { axsAccessFilterStats 1 }

axsAccessFilterStatsInEntry OBJECT-TYPE
        SYNTAX  AxsAccessFilterStatsInEntry
        ACCESS  not-accessible
        STATUS  mandatory
        DESCRIPTION
                "Entry concerning corresponding number of packets to flow detection condition and 
                operation information set by access list."
    INDEX { axsAccessFilterStatsInifIndex, axsAccessFilterStatsInifIndexType, axsAccessFilterStatsInListIndex,axsAccessFilterStatsInSequenceNumber }
        ::= { axsAccessFilterStatsInTable 1 }

        AxsAccessFilterStatsInEntry ::=
                SEQUENCE {
                  axsAccessFilterStatsInifIndex         INTEGER,
                  axsAccessFilterStatsInifIndexType     INTEGER,
                  axsAccessFilterStatsInListIndex       Unsigned32,
                  axsAccessFilterStatsInSequenceNumber  Unsigned32,
                  axsAccessFilterStatsInListName        DisplayString,
                  axsAccessFilterStatsInMatchedPackets  Counter64
                }

axsAccessFilterStatsInifIndex OBJECT-TYPE
        SYNTAX  INTEGER
        ACCESS  not-accessible
        STATUS  mandatory
        DESCRIPTION
                "Index value in which entry of this table is identified."
        ::= { axsAccessFilterStatsInEntry 1 }

axsAccessFilterStatsInifIndexType OBJECT-TYPE
        SYNTAX  INTEGER
        ACCESS  not-accessible
        STATUS  mandatory
        DESCRIPTION
                "Indicates interface type. Physical port number : 1 Interface name : 2"
        ::= { axsAccessFilterStatsInEntry 2 }

axsAccessFilterStatsInListIndex OBJECT-TYPE
        SYNTAX  Unsigned32
        ACCESS  not-accessible
        STATUS  mandatory
        DESCRIPTION
                "Index value of access list that identifies entry of this table."
        ::= { axsAccessFilterStatsInEntry 3 }

axsAccessFilterStatsInSequenceNumber OBJECT-TYPE
        SYNTAX  Unsigned32
        ACCESS  not-accessible
        STATUS  mandatory
        DESCRIPTION
                "Sequence number of flow detection condition and operation information set to access list 
                number or access list name. 
                "
        ::= { axsAccessFilterStatsInEntry 4 }

axsAccessFilterStatsInListName OBJECT-TYPE
        SYNTAX  DisplayString
        ACCESS  read-only
        STATUS  mandatory
        DESCRIPTION
                "Access list number or access list name corresponding to index of access list."
        ::= { axsAccessFilterStatsInEntry 5 }

axsAccessFilterStatsInMatchedPackets OBJECT-TYPE
        SYNTAX  Counter64
        ACCESS  read-only
        STATUS  mandatory
        DESCRIPTION
                "Corresponding number of packets to flow detection condition of access list. "
        ::= { axsAccessFilterStatsInEntry 6 }

axsAccessFilterStatsOutTable OBJECT-TYPE
        SYNTAX  SEQUENCE OF AxsAccessFilterStatsOutEntry
        ACCESS  not-accessible
        STATUS  mandatory
        DESCRIPTION
                "Table information on corresponding number of packets to flow detection condition 
                and operation information set by access list of Outbound."
        ::= { axsAccessFilterStats 2 }

axsAccessFilterStatsOutEntry OBJECT-TYPE
        SYNTAX  AxsAccessFilterStatsOutEntry
        ACCESS  not-accessible
        STATUS  mandatory
        DESCRIPTION
                "Entry concerning corresponding number of packets to flow detection condition and 
                operation information set by access list of Outbound."
    INDEX { axsAccessFilterStatsOutifIndex, axsAccessFilterStatsOutifIndexType, axsAccessFilterStatsOutListIndex,axsAccessFilterStatsOutSequenceNumber }
        ::= { axsAccessFilterStatsOutTable 1 }

        AxsAccessFilterStatsOutEntry ::=
                SEQUENCE {
                  axsAccessFilterStatsOutifIndex         INTEGER,
                  axsAccessFilterStatsOutifIndexType     INTEGER,
                  axsAccessFilterStatsOutListIndex       Unsigned32,
                  axsAccessFilterStatsOutSequenceNumber  Unsigned32,
                  axsAccessFilterStatsOutListName        DisplayString,
                  axsAccessFilterStatsOutMatchedPackets  Counter64
                }

axsAccessFilterStatsOutifIndex OBJECT-TYPE
        SYNTAX  INTEGER
        ACCESS  not-accessible
        STATUS  mandatory
        DESCRIPTION
                "Index value in which entry of this table is identified."
        ::= { axsAccessFilterStatsOutEntry 1 }

axsAccessFilterStatsOutifIndexType OBJECT-TYPE
        SYNTAX  INTEGER
        ACCESS  not-accessible
        STATUS  mandatory
        DESCRIPTION
                "Indicates interface type. Physical port number : 1 Interface name : 2"
        ::= { axsAccessFilterStatsOutEntry 2 }

axsAccessFilterStatsOutListIndex OBJECT-TYPE
        SYNTAX  Unsigned32
        ACCESS  not-accessible
        STATUS  mandatory
        DESCRIPTION
                "Index value of access list that identifies entry of this table."
        ::= { axsAccessFilterStatsOutEntry 3 }

axsAccessFilterStatsOutSequenceNumber OBJECT-TYPE
        SYNTAX  Unsigned32
        ACCESS  not-accessible
        STATUS  mandatory
        DESCRIPTION
                "Sequence number of flow detection condition and operation information set to access list 
                number or access list name. 
                "
        ::= { axsAccessFilterStatsOutEntry 4 }

axsAccessFilterStatsOutListName OBJECT-TYPE
        SYNTAX  DisplayString
        ACCESS  read-only
        STATUS  mandatory
        DESCRIPTION
                "Access list number or access list name corresponding to index of access list."
        ::= { axsAccessFilterStatsOutEntry 5 }

axsAccessFilterStatsOutMatchedPackets OBJECT-TYPE
        SYNTAX  Counter64
        ACCESS  read-only
        STATUS  mandatory
        DESCRIPTION
                "Corresponding number of packets to flow detection condition of access list. "
        ::= { axsAccessFilterStatsOutEntry 6 }

axsAccessFilterStatsInMirrorTable OBJECT-TYPE
        SYNTAX  SEQUENCE OF AxsAccessFilterStatsInMirrorEntry
        ACCESS  not-accessible
        STATUS  mandatory
        DESCRIPTION
                "Table information on corresponding number of packets to flow detection condition 
                and operation information set by access list of In Mirror."
        ::= { axsAccessFilterStats 9 }

axsAccessFilterStatsInMirrorEntry OBJECT-TYPE
        SYNTAX  AxsAccessFilterStatsInMirrorEntry
        ACCESS  not-accessible
        STATUS  mandatory
        DESCRIPTION
                "Entry concerning corresponding number of packets to flow detection condition and 
                operation information set by access list of In Mirror."
    INDEX { axsAccessFilterStatsInMirrorifIndex, axsAccessFilterStatsInMirrorifIndexType, axsAccessFilterStatsInMirrorListIndex, axsAccessFilterStatsInMirrorSequenceNumber }
        ::= { axsAccessFilterStatsInMirrorTable 1 }

        AxsAccessFilterStatsInMirrorEntry ::=
                SEQUENCE {
                  axsAccessFilterStatsInMirrorifIndex         INTEGER,
                  axsAccessFilterStatsInMirrorifIndexType     INTEGER,
                  axsAccessFilterStatsInMirrorListIndex       Unsigned32,
                  axsAccessFilterStatsInMirrorSequenceNumber  Unsigned32,
                  axsAccessFilterStatsInMirrorListName        DisplayString,
                  axsAccessFilterStatsInMirrorMatchedPackets  Counter64
                }

axsAccessFilterStatsInMirrorifIndex OBJECT-TYPE
        SYNTAX  INTEGER
        ACCESS  not-accessible
        STATUS  mandatory
        DESCRIPTION
                "Index value in which entry of this table is identified."
        ::= { axsAccessFilterStatsInMirrorEntry 1 }

axsAccessFilterStatsInMirrorifIndexType OBJECT-TYPE
        SYNTAX  INTEGER
        ACCESS  not-accessible
        STATUS  mandatory
        DESCRIPTION
                "Indicates interface type. Physical port number : 1 Interface name : 2"
        ::= { axsAccessFilterStatsInMirrorEntry 2 }

axsAccessFilterStatsInMirrorListIndex OBJECT-TYPE
        SYNTAX  Unsigned32
        ACCESS  not-accessible
        STATUS  mandatory
        DESCRIPTION
                "Index value of access list that identifies entry of this table."
        ::= { axsAccessFilterStatsInMirrorEntry 3 }

axsAccessFilterStatsInMirrorSequenceNumber OBJECT-TYPE
        SYNTAX  Unsigned32
        ACCESS  not-accessible
        STATUS  mandatory
        DESCRIPTION
                "Sequence number of flow detection condition and operation information set to access list 
                number or access list name. 
                "
        ::= { axsAccessFilterStatsInMirrorEntry 4 }

axsAccessFilterStatsInMirrorListName OBJECT-TYPE
        SYNTAX  DisplayString
        ACCESS  read-only
        STATUS  mandatory
        DESCRIPTION
                "Access list number or access list name corresponding to index of access list."
        ::= { axsAccessFilterStatsInMirrorEntry 5 }

axsAccessFilterStatsInMirrorMatchedPackets OBJECT-TYPE
        SYNTAX  Counter64
        ACCESS  read-only
        STATUS  mandatory
        DESCRIPTION
                "Corresponding number of packets to flow detection condition of access list. "
        ::= { axsAccessFilterStatsInMirrorEntry 6 }

axsAccessFilterStatsOutMirrorTable OBJECT-TYPE
        SYNTAX  SEQUENCE OF AxsAccessFilterStatsOutMirrorEntry
        ACCESS  not-accessible
        STATUS  mandatory
        DESCRIPTION
                "Table information on corresponding number of packets to flow detection condition 
                and operation information set by access list of Out Mirror."
        ::= { axsAccessFilterStats 10 }

axsAccessFilterStatsOutMirrorEntry OBJECT-TYPE
        SYNTAX  AxsAccessFilterStatsOutMirrorEntry
        ACCESS  not-accessible
        STATUS  mandatory
        DESCRIPTION
                "Entry concerning corresponding number of packets to flow detection condition and 
                operation information set by access list of Out Mirror."
    INDEX { axsAccessFilterStatsOutMirrorifIndex, axsAccessFilterStatsOutMirrorifIndexType, axsAccessFilterStatsOutMirrorListIndex, axsAccessFilterStatsOutMirrorSequenceNumber }
        ::= { axsAccessFilterStatsOutMirrorTable 1 }

        AxsAccessFilterStatsOutMirrorEntry ::=
                SEQUENCE {
                  axsAccessFilterStatsOutMirrorifIndex         INTEGER,
                  axsAccessFilterStatsOutMirrorifIndexType     INTEGER,
                  axsAccessFilterStatsOutMirrorListIndex       Unsigned32,
                  axsAccessFilterStatsOutMirrorSequenceNumber  Unsigned32,
                  axsAccessFilterStatsOutMirrorListName        DisplayString,
                  axsAccessFilterStatsOutMirrorMatchedPackets  Counter64
                }

axsAccessFilterStatsOutMirrorifIndex OBJECT-TYPE
        SYNTAX  INTEGER
        ACCESS  not-accessible
        STATUS  mandatory
        DESCRIPTION
                "Index value in which entry of this table is identified."
        ::= { axsAccessFilterStatsOutMirrorEntry 1 }

axsAccessFilterStatsOutMirrorifIndexType OBJECT-TYPE
        SYNTAX  INTEGER
        ACCESS  not-accessible
        STATUS  mandatory
        DESCRIPTION
                "Indicates interface type. Physical port number : 1 Interface name : 2"
        ::= { axsAccessFilterStatsOutMirrorEntry 2 }

axsAccessFilterStatsOutMirrorListIndex OBJECT-TYPE
        SYNTAX  Unsigned32
        ACCESS  not-accessible
        STATUS  mandatory
        DESCRIPTION
                "Index value of access list that identifies entry of this table."
        ::= { axsAccessFilterStatsOutMirrorEntry 3 }

axsAccessFilterStatsOutMirrorSequenceNumber OBJECT-TYPE
        SYNTAX  Unsigned32
        ACCESS  not-accessible
        STATUS  mandatory
        DESCRIPTION
                "Sequence number of flow detection condition and operation information set to access list 
                number or access list name. 
                "
        ::= { axsAccessFilterStatsOutMirrorEntry 4 }

axsAccessFilterStatsOutMirrorListName OBJECT-TYPE
        SYNTAX  DisplayString
        ACCESS  read-only
        STATUS  mandatory
        DESCRIPTION
                "Access list number or access list name corresponding to index of access list."
        ::= { axsAccessFilterStatsOutMirrorEntry 5 }

axsAccessFilterStatsOutMirrorMatchedPackets OBJECT-TYPE
        SYNTAX  Counter64
        ACCESS  read-only
        STATUS  mandatory
        DESCRIPTION
                "Corresponding number of packets to flow detection condition of access list. "
        ::= { axsAccessFilterStatsOutMirrorEntry 6 }

axsQosFlowStatsInTable OBJECT-TYPE
        SYNTAX  SEQUENCE OF AxsQosFlowStatsInEntry
        ACCESS  not-accessible
        STATUS  mandatory
        DESCRIPTION
                "Table information on corresponding number of packets to QoS flow detection condition
                and operation information set in QoS flow list."
        ::= { axsQosFlowStats 1 }

axsQosFlowStatsInEntry OBJECT-TYPE
        SYNTAX  AxsQosFlowStatsInEntry
        ACCESS  not-accessible
        STATUS  mandatory
        DESCRIPTION
                "Entry concerning corresponding number of packets to QoS flow detection condition
                and operation information set in QoS Flower shop."
    INDEX { axsQosFlowStatsInifIndex, axsQosFlowStatsInifIndexType, axsQosFlowStatsInListIndex, axsQosFlowStatsInSequenceNumber }
        ::= { axsQosFlowStatsInTable 1 }

        AxsQosFlowStatsInEntry ::=
                SEQUENCE {
                  axsQosFlowStatsInifIndex                 INTEGER,
                  axsQosFlowStatsInifIndexType             INTEGER,
                  axsQosFlowStatsInListIndex               Unsigned32,
                  axsQosFlowStatsInSequenceNumber          Unsigned32,
                  axsQosFlowStatsInListName                DisplayString,
                  axsQosFlowStatsInMatchedPackets          Counter64,
                  axsQosFlowStatsInMatchedPacketsMinUnder  Counter64,
                  axsQosFlowStatsInMatchedPacketsMinOver   Counter64,
                  axsQosFlowStatsInMatchedPacketsMaxUnder  Counter64,
                  axsQosFlowStatsInMatchedPacketsMaxOver   Counter64
                }

axsQosFlowStatsInifIndex OBJECT-TYPE
        SYNTAX  INTEGER
        ACCESS  not-accessible
        STATUS  mandatory
        DESCRIPTION
                "Index value in which entry of this table is identified."
        ::= { axsQosFlowStatsInEntry 1 }

axsQosFlowStatsInifIndexType OBJECT-TYPE
        SYNTAX  INTEGER
        ACCESS  not-accessible
        STATUS  mandatory
        DESCRIPTION
                "Indicates interface type. Physical port number : 1 Interface name : 2"
        ::= { axsQosFlowStatsInEntry 2 }

axsQosFlowStatsInListIndex OBJECT-TYPE
        SYNTAX  Unsigned32
        ACCESS  not-accessible
        STATUS  mandatory
        DESCRIPTION
                "Index value of QoS Flow list where entry of this table is identified."
        ::= { axsQosFlowStatsInEntry 3 }

axsQosFlowStatsInSequenceNumber OBJECT-TYPE
        SYNTAX  Unsigned32
        ACCESS  not-accessible
        STATUS  mandatory
        DESCRIPTION
                "Sequence number of flow detection condition and operation information set to QoS 
                flow list name."
        ::= { axsQosFlowStatsInEntry 4 }

axsQosFlowStatsInListName OBJECT-TYPE
        SYNTAX  DisplayString
        ACCESS  read-only
        STATUS  mandatory
        DESCRIPTION
                "QoS flow list name corresponding to index of QoS flow list."
        ::= { axsQosFlowStatsInEntry 5 }

axsQosFlowStatsInMatchedPackets OBJECT-TYPE
        SYNTAX  Counter64
        ACCESS  read-only
        STATUS  mandatory
        DESCRIPTION
                "Corresponding number of packets to flow detection condition of QoS flow list."
        ::= { axsQosFlowStatsInEntry 6 }

axsQosFlowStatsInMatchedPacketsMinUnder OBJECT-TYPE
        SYNTAX  Counter64
        ACCESS  read-only
        STATUS  mandatory
        DESCRIPTION
                "Number of packets in which it agrees to flow detection condition of QoS flow 
                list and the lowest band watch is observed."
        ::= { axsQosFlowStatsInEntry 7 }

axsQosFlowStatsInMatchedPacketsMinOver OBJECT-TYPE
        SYNTAX  Counter64
        ACCESS  read-only
        STATUS  mandatory
        DESCRIPTION
                "Number of packets in which it agrees to flow detection condition of QoS flow 
                list and it violates the lowest band watch."
        ::= { axsQosFlowStatsInEntry 8 }

axsQosFlowStatsInMatchedPacketsMaxUnder OBJECT-TYPE
        SYNTAX  Counter64
        ACCESS  read-only
        STATUS  mandatory
        DESCRIPTION
                "Number of packets in which it agrees to flow detection condition of QoS flow 
                list and the maximum band control is observed."
        ::= { axsQosFlowStatsInEntry 9 }

axsQosFlowStatsInMatchedPacketsMaxOver OBJECT-TYPE
        SYNTAX  Counter64 
        ACCESS  read-only
        STATUS  mandatory
        DESCRIPTION
                "Number of packets in which it agrees to flow detection condition of QoS flow 
                list and it violates the maximum band control."
        ::= { axsQosFlowStatsInEntry 10 }

--  axsL2ldMIB Group

axsL2ldVersion OBJECT-TYPE
	SYNTAX  INTEGER
	ACCESS  read-only
	STATUS  mandatory
	DESCRIPTION
		"The version of L2 loop detection."
	::= { axsL2ldGlobalInfo 1 }

axsL2ldLoopDetectionId OBJECT-TYPE
	SYNTAX  INTEGER
	ACCESS  read-only
	STATUS  mandatory
	DESCRIPTION
		"L2 loop detection ID."
	::= { axsL2ldGlobalInfo 2 }

axsL2ldIntervalTime OBJECT-TYPE
	SYNTAX  INTEGER
	ACCESS  read-only
	STATUS  mandatory
	DESCRIPTION
		"Sending interval of L2 loop detection frame."
	::= { axsL2ldGlobalInfo 3 }

axsL2ldOutputRate OBJECT-TYPE
	SYNTAX  INTEGER
	ACCESS  read-only
	STATUS  mandatory
	DESCRIPTION
		"Sending rate of L2 loop detection frame."
	::= { axsL2ldGlobalInfo 4 }

axsL2ldThreshold OBJECT-TYPE
	SYNTAX  INTEGER
	ACCESS  read-only
	STATUS  mandatory
	DESCRIPTION
		"Detection counts until port is put into state of inactive."
	::= { axsL2ldGlobalInfo 5 }

axsL2ldHoldTime OBJECT-TYPE
	SYNTAX  INTEGER
	ACCESS  read-only
	STATUS  mandatory
	DESCRIPTION
		"Hold time of detection counts."
	::= { axsL2ldGlobalInfo 6 }

axsL2ldAutoRestoreTime OBJECT-TYPE
	SYNTAX  INTEGER
	ACCESS  read-only
	STATUS  mandatory
	DESCRIPTION
		"Time until port put into state of inactive is put into state of
		active by automatic operation."
	::= { axsL2ldGlobalInfo 7 }

axsL2ldConfigurationVlanPortCounts OBJECT-TYPE
	SYNTAX  INTEGER
	ACCESS  read-only
	STATUS  mandatory
	DESCRIPTION
		"The number of VLAN ports set to send L2 loop detection frame."
	::= { axsL2ldGlobalInfo 8 }

axsL2ldCapacityVlanPortCounts OBJECT-TYPE
	SYNTAX  INTEGER
	ACCESS  read-only
	STATUS  mandatory
	DESCRIPTION
		"The number of VLAN ports that can be sent by L2 loop detection
		frame sending rate."
	::= { axsL2ldGlobalInfo 9 }

axsL2ldPortTable OBJECT-TYPE
	SYNTAX  SEQUENCE OF AxsL2ldPortEntry
	ACCESS  not-accessible
	STATUS  mandatory
	DESCRIPTION
		"The table containing port information on L2 loop detection."
	::= { axsL2ld 2 }

axsL2ldPortEntry OBJECT-TYPE
	SYNTAX  AxsL2ldPortEntry
	ACCESS  not-accessible
	STATUS  mandatory
	DESCRIPTION
		"The entry of port information on L2 loop detection."
	INDEX { axsL2ldPortIndex,axsL2ldPortIfIndex }
	::= { axsL2ldPortTable 1 }

	AxsL2ldPortEntry ::=
		SEQUENCE {
			axsL2ldPortIndex					INTEGER,
			axsL2ldPortIfIndex					INTEGER,
			axsL2ldPortStatus					INTEGER,
			axsL2ldPortType						INTEGER,
			axsL2ldPortDetectCount				INTEGER,
			axsL2ldPortAutoRestoringTimer		INTEGER,
			axsL2ldPortSourcePortIfindex		INTEGER,
			axsL2ldPortDestinationPortIfindex	INTEGER,
			axsL2ldPortSourceVlan				INTEGER,
			axsL2ldPortHCInFrames				Counter64,
			axsL2ldPortHCOutFrames				Counter64,
			axsL2ldPortHCInDiscards				Counter64,
			axsL2ldPortInactiveCount			INTEGER,
			axsL2ldPortLastInactiveTime			TimeStamp,
			axsL2ldPortLastInFramesTime			TimeStamp
		}

axsL2ldPortIndex OBJECT-TYPE
	SYNTAX  INTEGER
	ACCESS  read-only
	STATUS  mandatory
	DESCRIPTION
		"Index of L2 loop detection port."
	::= { axsL2ldPortEntry 1 }

axsL2ldPortIfIndex OBJECT-TYPE
	SYNTAX  INTEGER
	ACCESS  read-only
	STATUS  mandatory
	DESCRIPTION
		"ifIndex of L2 loop detection port."
	::= { axsL2ldPortEntry 2 }

axsL2ldPortStatus OBJECT-TYPE
	SYNTAX  INTEGER {
				up (1),
				down (2),
				loopDown (3)
			}
	ACCESS  read-only
	STATUS  mandatory
	DESCRIPTION
		"State of L2 loop detection port."
	::= { axsL2ldPortEntry 3 }

axsL2ldPortType OBJECT-TYPE
	SYNTAX  INTEGER {
				trap (1),
				sendInact (2),
				send (3),
				upLink (4),
				exception (5)
			}
	ACCESS  read-only
	STATUS  mandatory
	DESCRIPTION
		"Type of L2 loop detection port."
	::= { axsL2ldPortEntry 4 }

axsL2ldPortDetectCount OBJECT-TYPE
	SYNTAX  INTEGER
	ACCESS  read-only
	STATUS  mandatory
	DESCRIPTION
		"The number of L2 loop detection. The number in which
		L2 loop detection frame is received in hold time."
	::= { axsL2ldPortEntry 5 }

axsL2ldPortAutoRestoringTimer OBJECT-TYPE
	SYNTAX  INTEGER
	ACCESS  read-only
	STATUS  mandatory
	DESCRIPTION
		"Time until restoring it automatically. The value is 0
		when port is active."
	::= { axsL2ldPortEntry 6 }

axsL2ldPortSourcePortIfindex OBJECT-TYPE
	SYNTAX  INTEGER
	ACCESS  read-only
	STATUS  mandatory
	DESCRIPTION
		"ifIndex of port transmitted when L2 loop detection frame
		was received at the end."
	::= { axsL2ldPortEntry 7 }

axsL2ldPortDestinationPortIfindex OBJECT-TYPE
	SYNTAX  INTEGER
	ACCESS  read-only
	STATUS  mandatory
	DESCRIPTION
		"ifIndex of port where L2 loop detection frame was
		received at the end."
	::= { axsL2ldPortEntry 8 }

axsL2ldPortSourceVlan OBJECT-TYPE
	SYNTAX  INTEGER
	ACCESS  read-only
	STATUS  mandatory
	DESCRIPTION
		"VLAN ID when transmitting when L2 loop detection frame
		was received at the end."
	::= { axsL2ldPortEntry 9 }

axsL2ldPortHCInFrames OBJECT-TYPE
	SYNTAX  Counter64
	ACCESS  read-only
	STATUS  mandatory
	DESCRIPTION
		"Number of receptions of L2 loop detection frames."
	::= { axsL2ldPortEntry 10 }

axsL2ldPortHCOutFrames OBJECT-TYPE
	SYNTAX  Counter64
	ACCESS  read-only
	STATUS  mandatory
	DESCRIPTION
		"Number of transmissions of L2 loop detection frames."
	::= { axsL2ldPortEntry 11 }

axsL2ldPortHCInDiscards OBJECT-TYPE
	SYNTAX  Counter64
	ACCESS  read-only
	STATUS  mandatory
	DESCRIPTION
		"Number of receptions of L2 loop detection discard frames."
	::= { axsL2ldPortEntry 12 }

axsL2ldPortInactiveCount OBJECT-TYPE
	SYNTAX  INTEGER
	ACCESS  read-only
	STATUS  mandatory
	DESCRIPTION
		"The number of put into state of inactive."
	::= { axsL2ldPortEntry 13 }

axsL2ldPortLastInactiveTime OBJECT-TYPE
	SYNTAX  TimeStamp
	ACCESS  read-only
	STATUS  mandatory
	DESCRIPTION
		"Time put into state of inactive at the end."
	::= { axsL2ldPortEntry 14 }

axsL2ldPortLastInFramesTime OBJECT-TYPE
	SYNTAX  TimeStamp
	ACCESS  read-only
	STATUS  mandatory
	DESCRIPTION
		"Time to have received L2 loop detection frame at the end."
	::= { axsL2ldPortEntry 15 }

-- AX VrfMIB Group

    axsVrfIpAddrTable OBJECT-TYPE
        SYNTAX    SEQUENCE OF AxsVrfIpAddrEntry
        ACCESS    not-accessible
        STATUS    mandatory
        DESCRIPTION
                  "The table of addressing information relevant to
                  this entity's IP addresses."
        ::= { axsVrfIp 1 }

    axsVrfIpAddrEntry OBJECT-TYPE
        SYNTAX    AxsVrfIpAddrEntry
        ACCESS    not-accessible
        STATUS    mandatory
        DESCRIPTION
                  "The addressing information for one of this
                  entity's IP addresses."
        INDEX { axsVrfIpAddrVrfIndex,
                axsVrfIpAdEntAddr }
        ::= { axsVrfIpAddrTable 1 }

    AxsVrfIpAddrEntry ::= SEQUENCE {
        axsVrfIpAddrVrfIndex         INTEGER,
        axsVrfIpAdEntAddr            IpAddress,
        axsVrfIpAdEntIfIndex         INTEGER,
        axsVrfIpAdEntNetMask         IpAddress,
        axsVrfIpAdEntBcastAddr       INTEGER,
        axsVrfIpAdEntReasmMaxSize    INTEGER,
        axsVrfIpAdEntDescr           DisplayString
    }

    axsVrfIpAddrVrfIndex OBJECT-TYPE
        SYNTAX    INTEGER
        ACCESS    read-only
        STATUS    mandatory
        DESCRIPTION
                  "The index value which identifies VRF number."
        ::= { axsVrfIpAddrEntry 1 }

    axsVrfIpAdEntAddr OBJECT-TYPE
        SYNTAX    IpAddress
        ACCESS    read-only
        STATUS    mandatory
        DESCRIPTION
                  "The IP address to which this entry's addressing
                  information pertains."
        ::= { axsVrfIpAddrEntry 2 }

    axsVrfIpAdEntIfIndex OBJECT-TYPE
        SYNTAX    INTEGER
        ACCESS    read-only
        STATUS    mandatory
        DESCRIPTION
                  "The index value which uniquely identifies the
                  interface to which this entry is applicable."
        ::= { axsVrfIpAddrEntry 3 }

    axsVrfIpAdEntNetMask OBJECT-TYPE
        SYNTAX    IpAddress
        ACCESS    read-only
        STATUS    mandatory
        DESCRIPTION
                  "The subnet mask associated with the IP address of
                  this entry."
        ::= { axsVrfIpAddrEntry 4 }

    axsVrfIpAdEntBcastAddr OBJECT-TYPE
        SYNTAX    INTEGER
        ACCESS    read-only
        STATUS    mandatory
        DESCRIPTION
                  "The value of the least-significant bit in the IP
                  broadcast address used for sending datagrams on
                  the (logical) interface associated with the IP
                  address of this entry."
        ::= { axsVrfIpAddrEntry 5 }

    axsVrfIpAdEntReasmMaxSize OBJECT-TYPE
        SYNTAX    INTEGER
        ACCESS    read-only
        STATUS    mandatory
        DESCRIPTION
                  "The size of the largest IP datagram which this
                  entity can re-assemble from incoming IP fragmented
                  datagrams received on this interface."
        ::= { axsVrfIpAddrEntry 6 }

    axsVrfIpAdEntDescr OBJECT-TYPE
        SYNTAX    DisplayString
        ACCESS    read-only
        STATUS    mandatory
        DESCRIPTION
                  "The Description of VRF. The VRF identification which user setting."
        ::= { axsVrfIpAddrEntry 7 }

    axsVrfIpNetToMediaTable OBJECT-TYPE
        SYNTAX    SEQUENCE OF AxsVrfIpNetToMediaEntry
        ACCESS    not-accessible
        STATUS    mandatory
        DESCRIPTION
                  "The IP Address Translation table used for mapping
                  from IP addresses to physical addresses."
        ::= { axsVrfIp 2 }

    axsVrfIpNetToMediaEntry OBJECT-TYPE
        SYNTAX    AxsVrfIpNetToMediaEntry
        ACCESS    not-accessible
        STATUS    mandatory
        DESCRIPTION
                  "Each entry contains one IpAddress to physical
                  address equivalence."
        INDEX { axsVrfIpNetMediaVrfIndex,
                axsVrfIpNetToMediaIfIndex,
                axsVrfIpNetToMediaNetAddress }
        ::= { axsVrfIpNetToMediaTable 1 }

    AxsVrfIpNetToMediaEntry ::= SEQUENCE {
        axsVrfIpNetMediaVrfIndex         INTEGER,
        axsVrfIpNetToMediaIfIndex        INTEGER,
        axsVrfIpNetToMediaPhysAddress    PhysAddress,
        axsVrfIpNetToMediaNetAddress     IpAddress,
        axsVrfIpNetToMediaType           INTEGER,
        axsVrfIpNetToMediaDescr          DisplayString
    }

    axsVrfIpNetMediaVrfIndex OBJECT-TYPE
        SYNTAX    INTEGER
        ACCESS    read-only
        STATUS    mandatory
        DESCRIPTION
                  "The index value which identifies VRF number."
        ::= { axsVrfIpNetToMediaEntry 1 }

    axsVrfIpNetToMediaIfIndex OBJECT-TYPE
        SYNTAX    INTEGER
        ACCESS    read-only
        STATUS    mandatory
        DESCRIPTION
                  "The interface on which this entry's equivalence
                  is effective. This index is same value of ifIndex."
        ::= { axsVrfIpNetToMediaEntry 2 }

    axsVrfIpNetToMediaPhysAddress OBJECT-TYPE
        SYNTAX    PhysAddress
        ACCESS    read-only
        STATUS    mandatory
        DESCRIPTION
                  "The media-dependent `physical' address."
        ::= { axsVrfIpNetToMediaEntry 3 }

    axsVrfIpNetToMediaNetAddress OBJECT-TYPE
        SYNTAX    IpAddress
        ACCESS    read-only
        STATUS    mandatory
        DESCRIPTION
                  "The IpAddress corresponding to the media-
                  dependent `physical' address."
        ::= { axsVrfIpNetToMediaEntry 4 }

    axsVrfIpNetToMediaType OBJECT-TYPE
        SYNTAX    INTEGER {
                      other(1),   -- none of the following ex. Inverse ARP
                      invalid(2), -- an invalidated mapping
                      dynamic(3),
                      static(4)
                  }
        ACCESS    read-only
        STATUS    mandatory
        DESCRIPTION
                  "The type of mapping."
        ::= { axsVrfIpNetToMediaEntry 5 }

    axsVrfIpNetToMediaDescr OBJECT-TYPE
        SYNTAX    DisplayString
        ACCESS    read-only
        STATUS    mandatory
        DESCRIPTION
                  "The Description of VRF. The VRF identification which user setting."
        ::= { axsVrfIpNetToMediaEntry 6 }

    axsVrfIpFwNoTable OBJECT-TYPE
        SYNTAX    SEQUENCE OF AxsVrfIpFwNoEntry
        ACCESS    not-accessible
        STATUS    mandatory
        DESCRIPTION
                  "This entity's number of IP Routing table about VRF."
        ::= { axsVrfIpForward 1 }

    axsVrfIpFwNoEntry OBJECT-TYPE
        SYNTAX    AxsVrfIpFwNoEntry
        ACCESS    not-accessible
        STATUS    mandatory
        DESCRIPTION
                  "This entity's IP Routing table about VRF."
        INDEX { axsVrfIpFwNoVRFIndex }
        ::= { axsVrfIpFwNoTable 1 }

    AxsVrfIpFwNoEntry ::= SEQUENCE {
        axsVrfIpFwNoVRFIndex    INTEGER,
        axsVrfIpFwNo            INTEGER,
        axsVrfIpFwNoDescr       DisplayString
    }

    axsVrfIpFwNoVRFIndex OBJECT-TYPE
        SYNTAX    INTEGER
        ACCESS    read-only
        STATUS    mandatory
        DESCRIPTION
                  "The index value which identifies VRF number."
        ::= { axsVrfIpFwNoEntry 1 }

    axsVrfIpFwNo OBJECT-TYPE
        SYNTAX    INTEGER
        ACCESS    read-only
        STATUS    mandatory
        DESCRIPTION
                  "The number of entry that is IP Routing table."
        ::= { axsVrfIpFwNoEntry 2 }

    axsVrfIpFwNoDescr OBJECT-TYPE
        SYNTAX    DisplayString
        ACCESS    read-only
        STATUS    mandatory
        DESCRIPTION
                  "The Description of VRF. The VRF identification which user setting."
        ::= { axsVrfIpFwNoEntry 3 }

    axsVrfIpFwTable OBJECT-TYPE
        SYNTAX    SEQUENCE OF AxsVrfIpFwEntry
        ACCESS    not-accessible
        STATUS    mandatory
        DESCRIPTION
                  "This entity's IP Routing table."
        ::= { axsVrfIpForward 2 }

    axsVrfIpFwEntry OBJECT-TYPE
        SYNTAX    AxsVrfIpFwEntry
        ACCESS    not-accessible
        STATUS    mandatory
        DESCRIPTION
                  "A particular route to a particular destination,
                  under a particular policy."
        INDEX { axsVrfIpFwVRFIndex,
                axsVrfIpFwDest,
                axsVrfIpFwProto,
                axsVrfIpFwPolicy,
                axsVrfIpFwNextHop }
        ::= { axsVrfIpFwTable 1 }

    AxsVrfIpFwEntry ::= SEQUENCE {
        axsVrfIpFwVRFIndex     INTEGER,
        axsVrfIpFwDest         IpAddress,
        axsVrfIpFwMask         IpAddress,
        axsVrfIpFwPolicy       INTEGER,
        axsVrfIpFwNextHop      IpAddress,
        axsVrfIpFwIfIndex      INTEGER,
        axsVrfIpFwType         INTEGER,
        axsVrfIpFwProto        INTEGER,
        axsVrfIpFwAge          INTEGER,
        axsVrfIpFwInfo         OBJECT IDENTIFIER,
        axsVrfIpFwNextHopAS    INTEGER,
        axsVrfIpFwMetric1      INTEGER,
        axsVrfIpFwMetric2      INTEGER,
        axsVrfIpFwMetric3      INTEGER,
        axsVrfIpFwMetric4      INTEGER,
        axsVrfIpFwMetric5      INTEGER,
        axsVrfIpFwDescr        DisplayString
    }

    axsVrfIpFwVRFIndex OBJECT-TYPE
        SYNTAX    INTEGER
        ACCESS    read-only
        STATUS    mandatory
        DESCRIPTION
                  "The index value which identifies VRF number."
        ::= { axsVrfIpFwEntry 1 }

    axsVrfIpFwDest OBJECT-TYPE
        SYNTAX    IpAddress
        ACCESS    read-only
        STATUS    mandatory
        DESCRIPTION
                  "The destination IP address of this route."
        ::= { axsVrfIpFwEntry 2 }

    axsVrfIpFwMask OBJECT-TYPE
        SYNTAX    IpAddress
        ACCESS    read-only
        STATUS    mandatory
        DESCRIPTION
                  "Indicate the mask to be logical-ANDed with the
                  destination address before being compared to
                  the value in the ipForwardDest field."
        ::= { axsVrfIpFwEntry 3 }

    axsVrfIpFwPolicy OBJECT-TYPE
        SYNTAX    INTEGER
        ACCESS    read-only
        STATUS    mandatory
        DESCRIPTION
                  "The general set of conditions that would cause
                  the selection of one multipath route (set of
                  next hops for a given destination) is referred
                  to as 'policy'."
        ::= { axsVrfIpFwEntry 4 }

    axsVrfIpFwNextHop OBJECT-TYPE
        SYNTAX    IpAddress
        ACCESS    read-only
        STATUS    mandatory
        DESCRIPTION
                  "On remote routes, the address of the next system en route."
        ::= { axsVrfIpFwEntry 5 }

    axsVrfIpFwIfIndex OBJECT-TYPE
        SYNTAX    INTEGER
        ACCESS    read-only
        STATUS    mandatory
        DESCRIPTION
                  "The ifIndex value which identifies the local
                  interface through which the next hop of this
                  route should be reached."
        ::= { axsVrfIpFwEntry 6 }

    axsVrfIpFwType OBJECT-TYPE
        SYNTAX    INTEGER{
                      other(1),   -- not specified by this MIB
                      invalid(2), -- logically deleted
                      local(3),   -- local interface
                      remote(4)   -- remote destination
                  }
        ACCESS    read-only
        STATUS    mandatory
        DESCRIPTION
                  "The type of route."
        ::= { axsVrfIpFwEntry 7 }

    axsVrfIpFwProto OBJECT-TYPE
        SYNTAX    INTEGER {
                      other(1),       -- not specified
                      local(2),       -- local interface
                      netmgmt(3),     -- static route
                      rip(8),         -- Berkeley RIP or RIP-II
                      ospf(13),       -- Open Shortest Path First
                      bgp(14)         -- Border Gateway Protocol
                  }
        ACCESS    read-only
        STATUS    mandatory
        DESCRIPTION
                  "The routing mechanism via which this route was
                  learned."
        ::= { axsVrfIpFwEntry 8 }

    axsVrfIpFwAge OBJECT-TYPE
        SYNTAX    INTEGER
        ACCESS    read-only
        STATUS    mandatory
        DESCRIPTION
                  "The number of seconds since this route was
                  last updated or otherwise determined to be
                  correct."
        ::= { axsVrfIpFwEntry 9 }

    axsVrfIpFwInfo OBJECT-TYPE
        SYNTAX    OBJECT IDENTIFIER
        ACCESS    read-only
        STATUS    mandatory
        DESCRIPTION
                  "A reference to MIB definitions specific to the
                  particular routing protocol which is responsible
                  for this route, as determined by the value
                  specified in the route's ipForwardProto value.
                  Its value be set to the OBJECT IDENTIFIER { 0 0 }."
        ::= { axsVrfIpFwEntry 10 }

    axsVrfIpFwNextHopAS OBJECT-TYPE
        SYNTAX    INTEGER
        ACCESS    read-only
        STATUS    mandatory
        DESCRIPTION
                  "The Autonomous System Number of the Next Hop."
        ::= { axsVrfIpFwEntry 11 }

    axsVrfIpFwMetric1 OBJECT-TYPE
        SYNTAX    INTEGER
        ACCESS    read-only
        STATUS    mandatory
        DESCRIPTION
                  "The primary routing metric for this route."
        ::= { axsVrfIpFwEntry 12 }

    axsVrfIpFwMetric2 OBJECT-TYPE
        SYNTAX    INTEGER
        ACCESS    read-only
        STATUS    mandatory
        DESCRIPTION
                  "An alternate routing metric for this route."
        ::= { axsVrfIpFwEntry 13 }

    axsVrfIpFwMetric3 OBJECT-TYPE
        SYNTAX    INTEGER
        ACCESS    read-only
        STATUS    mandatory
        DESCRIPTION
                  "An alternate routing metric for this route.
                  Its value is set to -1."
        ::= { axsVrfIpFwEntry 14 }

    axsVrfIpFwMetric4 OBJECT-TYPE
        SYNTAX    INTEGER
        ACCESS    read-only
        STATUS    mandatory
        DESCRIPTION
                  "An alternate routing metric for this route.
                  Its value is set to -1."
        ::= { axsVrfIpFwEntry 15 }

    axsVrfIpFwMetric5 OBJECT-TYPE
        SYNTAX    INTEGER
        ACCESS    read-only
        STATUS    mandatory
        DESCRIPTION
                  "An alternate routing metric for this route.
                  Its value is set to -1."
        ::= { axsVrfIpFwEntry 16 }

    axsVrfIpFwDescr OBJECT-TYPE
        SYNTAX    DisplayString
        ACCESS    read-only
        STATUS    mandatory
        DESCRIPTION
                  "The Description of VRF. The VRF identification which user setting."
        ::= { axsVrfIpFwEntry 17 }

    axsVrfIpv6AddrTable OBJECT-TYPE
        SYNTAX    SEQUENCE OF AxsVrfIpv6AddrEntry
        ACCESS    not-accessible
        STATUS    mandatory
        DESCRIPTION
                  "The table of addressing information relevant to
                  this node's interface IPv6 addresses per VRF."
        ::= { axsVrfIpv6 1 }

    axsVrfIpv6AddrEntry OBJECT-TYPE
        SYNTAX    AxsVrfIpv6AddrEntry
        ACCESS    not-accessible
        STATUS    mandatory
        DESCRIPTION
                  "The addressing information for one of this
                  entity's IPv6 addresses per VRF."
        INDEX { axsVrfIpv6AddrVrfIndex,
                axsVrfIpv6AddrIfIndex,
                axsVrfIpv6AddrAddress }
        ::= { axsVrfIpv6AddrTable 1 }

    AxsVrfIpv6AddrEntry ::= SEQUENCE {
        axsVrfIpv6AddrVrfIndex       INTEGER,
        axsVrfIpv6AddrIfIndex        INTEGER,
        axsVrfIpv6AddrAddress        Ipv6Address,
        axsVrfIpv6AddrPfxLength      INTEGER,
        axsVrfIpv6AddrType           INTEGER,
        axsVrfIpv6AddrAnycastFlag    TruthValue,
        axsVrfIpv6AddrStatus         INTEGER,
        axsVrfIpv6AddrDescr          DisplayString
    }

    axsVrfIpv6AddrVrfIndex OBJECT-TYPE
        SYNTAX    INTEGER
        ACCESS    read-only
        STATUS    mandatory
        DESCRIPTION
                  "The index value which identifies VRF number."
        ::= { axsVrfIpv6AddrEntry 1 }

    axsVrfIpv6AddrIfIndex OBJECT-TYPE
        SYNTAX    INTEGER
        ACCESS    read-only
        STATUS    mandatory
        DESCRIPTION
                  "The index value which uniquely identifies the
                  interface to which this entry is applicable."
        ::= { axsVrfIpv6AddrEntry 2 }

    axsVrfIpv6AddrAddress OBJECT-TYPE
        SYNTAX    Ipv6Address
        ACCESS    read-only
        STATUS    mandatory
        DESCRIPTION
                 "The IPv6 address to which this entry's addressing
                 information pertains."
        ::= { axsVrfIpv6AddrEntry 3 }

    axsVrfIpv6AddrPfxLength OBJECT-TYPE
        SYNTAX    INTEGER(0..128)
        ACCESS    read-only
        STATUS    mandatory
        DESCRIPTION
                  "The length of the prefix (in bits) associated with
                  the IPv6 address of this entry."
        ::= { axsVrfIpv6AddrEntry 4 }

    axsVrfIpv6AddrType OBJECT-TYPE
        SYNTAX    INTEGER {
                                     -- address has been formed
                                     -- using stateless
                      stateless(1),  -- autoconfiguration
                                     -- address has been acquired
                                     -- by stateful means
                                     -- (e.g. DHCPv6, manual
                      stateful(2),   -- configuration)
                                     -- type can not be determined
                      unknown(3)     -- for some reason.
                  }
        ACCESS    read-only
        STATUS    mandatory
        DESCRIPTION
                  "The type of address. Note that 'stateless(1)'
                  refers to an address that was statelessly
                  autoconfigured; 'stateful(2)' refers to a address
                  which was acquired by via a stateful protocol
                  (e.g. DHCPv6, manual configuration)."
        ::= { axsVrfIpv6AddrEntry 5 }

    axsVrfIpv6AddrAnycastFlag OBJECT-TYPE
        SYNTAX    TruthValue
        ACCESS    read-only
        STATUS    mandatory
        DESCRIPTION
                  "This object has the value 'true(1)', if this
                  address is an anycast address and the value
                  'false(2)' otherwise."
        ::= { axsVrfIpv6AddrEntry 6 }

    axsVrfIpv6AddrStatus OBJECT-TYPE
        SYNTAX    INTEGER {
                      preferred(1),
                      deprecated(2),
                      invalid(3),
                      inaccessible(4),
                      unknown(5)        -- status can not be determined
                                        -- for some reason.
                  }
        ACCESS    read-only
        STATUS    mandatory
        DESCRIPTION
                  "Address status.  The preferred(1) state indicates
                  that this is a valid address that can appear as
                  the destination or source address of a packet.
                  The deprecated(2) state indicates that this is
                  a valid but deprecated address that should no longer
                  be used as a source address in new communications,
                  but packets addressed to such an address are
                  processed as expected. The invalid(3) state indicates
                  that this is not valid address which should not
                  appear as the destination or source address of
                  a packet. The inaccessible(4) state indicates that
                  the address is not accessible because the interface
                  to which this address is assigned is not operational."
        ::= { axsVrfIpv6AddrEntry 7 }

    axsVrfIpv6AddrDescr OBJECT-TYPE
        SYNTAX    DisplayString
        ACCESS    read-only
        STATUS    mandatory
        DESCRIPTION
                  "The Description of VRF. The VRF identification which user setting."
        ::= { axsVrfIpv6AddrEntry 8 }

    axsVrfIpv6AddrPrefixTable OBJECT-TYPE
        SYNTAX    SEQUENCE OF AxsVrfIpv6AddrPrefixEntry
        ACCESS    not-accessible
        STATUS    mandatory
        DESCRIPTION
                  "The list of IPv6 address prefixes of
                  IPv6 interfaces."
        ::= { axsVrfIpv6 2 }

    axsVrfIpv6AddrPrefixEntry OBJECT-TYPE
        SYNTAX    AxsVrfIpv6AddrPrefixEntry
        ACCESS    not-accessible
        STATUS    mandatory
        DESCRIPTION
                  "An interface entry containing objects of
                  a particular IPv6 address prefix."
        INDEX { axsVrfIpv6AddrPrefixVrfIndex,
                axsVrfIpv6AddrPrefixIfIndex,
                axsVrfIpv6AddrPrefix,
                axsVrfIpv6AddrPrefixLength }
        ::= { axsVrfIpv6AddrPrefixTable 1 }

    AxsVrfIpv6AddrPrefixEntry ::= SEQUENCE {
        axsVrfIpv6AddrPrefixVrfIndex                INTEGER,
        axsVrfIpv6AddrPrefixIfIndex                 INTEGER,
        axsVrfIpv6AddrPrefix                        Ipv6AddressPrefix,
        axsVrfIpv6AddrPrefixLength                  INTEGER (0..128),
        axsVrfIpv6AddrPrefixOnLinkFlag              TruthValue,
        axsVrfIpv6AddrPrefixAutonomousFlag          TruthValue,
        axsVrfIpv6AddrPrefixAdvPreferredLifetime    Unsigned32,
        axsVrfIpv6AddrPrefixAdvValidLifetime        Unsigned32
    }

    axsVrfIpv6AddrPrefixVrfIndex OBJECT-TYPE
        SYNTAX    INTEGER
        ACCESS    not-accessible
        STATUS    mandatory
        DESCRIPTION
                  "The index value which identifies VRF number."
        ::= { axsVrfIpv6AddrPrefixEntry 1 }

    axsVrfIpv6AddrPrefixIfIndex OBJECT-TYPE
        SYNTAX    INTEGER
        ACCESS    not-accessible
        STATUS    mandatory
        DESCRIPTION
                  "The index value which uniquely identifies the
                  interface to which this entry is applicable."
        ::= { axsVrfIpv6AddrPrefixEntry 2 }

    axsVrfIpv6AddrPrefix OBJECT-TYPE
        SYNTAX    Ipv6AddressPrefix
        ACCESS    not-accessible
        STATUS    mandatory
        DESCRIPTION
                  "The prefix associated with the this interface."
        ::= { axsVrfIpv6AddrPrefixEntry 3 }

    axsVrfIpv6AddrPrefixLength OBJECT-TYPE
        SYNTAX    INTEGER (0..128)
        ACCESS    not-accessible
        STATUS    mandatory
        DESCRIPTION
                  "The length of the prefix (in bits)."
        ::= { axsVrfIpv6AddrPrefixEntry 4 }

    axsVrfIpv6AddrPrefixOnLinkFlag OBJECT-TYPE
        SYNTAX    TruthValue
        ACCESS    read-only
        STATUS    mandatory
        DESCRIPTION
                  "This object has the value 'true(1)', if this
                  prefix can be used  for on-link determination
                  and the value 'false(2)' otherwise."
        ::= { axsVrfIpv6AddrPrefixEntry 5 }

    axsVrfIpv6AddrPrefixAutonomousFlag OBJECT-TYPE
        SYNTAX    TruthValue
        ACCESS    read-only
        STATUS    mandatory
        DESCRIPTION
                  "Autonomous address configuration flag. When
                  true(1), indicates that this prefix can be used
                  for autonomous address configuration (i.e. can
                  be used to form a local interface address).
                  If false(2), it is not used to autoconfigure
                  a local interface address."
        ::= { axsVrfIpv6AddrPrefixEntry 6 }

    axsVrfIpv6AddrPrefixAdvPreferredLifetime OBJECT-TYPE
        SYNTAX    Unsigned32
        ACCESS    read-only
        STATUS    mandatory
        DESCRIPTION
                  "It is the length of time in seconds that this
                  prefix will remain preferred, i.e. time until
                  deprecation.  A value of 4,294,967,295 represents
                  infinity.

                  The address generated from a deprecated prefix
                  should no longer be used as a source address in
                  new communications, but packets received on such
                  an interface are processed as expected."
        ::= { axsVrfIpv6AddrPrefixEntry 7 }

    axsVrfIpv6AddrPrefixAdvValidLifetime OBJECT-TYPE
        SYNTAX    Unsigned32
        ACCESS    read-only
        STATUS    mandatory
        DESCRIPTION
                  "It is the length of time in seconds that this
                  prefix will remain valid, i.e. time until
                  invalidation.  A value of 4,294,967,295 represents
                  infinity.

                  The address generated from an invalidated prefix
                  should not appear as the destination or source
                  address of a packet."
        ::= { axsVrfIpv6AddrPrefixEntry 8 }

    axsVrfIpv6NetToMediaTable OBJECT-TYPE
        SYNTAX    SEQUENCE OF AxsVrfIpv6NetToMediaEntry
        ACCESS    not-accessible
        STATUS    mandatory
        DESCRIPTION
                  "The IPv6 Address Translation table used for
                  mapping from IPv6 addresses to physical addresses per VRF.

                  The IPv6 address translation table contain the
                  Ipv6Address to `physical' address equivalencies.
                  Some interfaces do not use translation tables
                  for determining address equivalencies; if all
                  interfaces are of this type, then the Address
                  Translation table is empty, i.e., has zero
                  entries."
        ::= { axsVrfIpv6 3 }

    axsVrfIpv6NetToMediaEntry OBJECT-TYPE
        SYNTAX    AxsVrfIpv6NetToMediaEntry
        ACCESS    not-accessible
        STATUS    mandatory
        DESCRIPTION
                  "Each entry contains one IPv6 address to `physical'
                  address equivalence per VRF."
        INDEX { axsVrfIpv6NetToMediaVrfIndex,
                axsVrfIpv6NetToMediaIfIndex,
                axsVrfIpv6NetToMediaNetAddress }
        ::= { axsVrfIpv6NetToMediaTable 1 }

    AxsVrfIpv6NetToMediaEntry ::= SEQUENCE {
        axsVrfIpv6NetToMediaVrfIndex         INTEGER,
        axsVrfIpv6NetToMediaIfIndex          INTEGER,
        axsVrfIpv6NetToMediaNetAddress       Ipv6Address,
        axsVrfIpv6NetToMediaPhysAddress      PhysAddress,
        axsVrfIpv6NetToMediaType             INTEGER,
        axsVrfIpv6IfNetToMediaState          INTEGER,
        axsVrfIpv6IfNetToMediaLastUpdated    TimeStamp,
        axsVrfIpv6NetToMediaValid            TruthValue,
        axsVrfIpv6NetToMediaDescr            DisplayString
    }

    axsVrfIpv6NetToMediaVrfIndex OBJECT-TYPE
        SYNTAX    INTEGER
        ACCESS    read-only
        STATUS    mandatory
        DESCRIPTION
                  "The index value which identifies VRF number."
        ::= { axsVrfIpv6NetToMediaEntry 1 }

    axsVrfIpv6NetToMediaIfIndex OBJECT-TYPE
        SYNTAX    INTEGER
        ACCESS    read-only
        STATUS    mandatory
        DESCRIPTION
                  "The index value which uniquely identifies the
                  interface to which this entry is applicable."
        ::= { axsVrfIpv6NetToMediaEntry 2 }

    axsVrfIpv6NetToMediaNetAddress OBJECT-TYPE
        SYNTAX    Ipv6Address
        ACCESS    read-only
        STATUS    mandatory
        DESCRIPTION
                  "The IPv6 Address corresponding to
                  the media-dependent `physical' address."
        ::= { axsVrfIpv6NetToMediaEntry 3 }

    axsVrfIpv6NetToMediaPhysAddress OBJECT-TYPE
        SYNTAX    PhysAddress
        ACCESS    read-only
        STATUS    mandatory
        DESCRIPTION
                  "The media-dependent `physical' address."
        ::= { axsVrfIpv6NetToMediaEntry 4 }

    axsVrfIpv6NetToMediaType OBJECT-TYPE
        SYNTAX    INTEGER {
                      other(1),    -- none of the following
                      dynamic(2),  -- dynamically resolved
                      static(3),   -- statically configured
                      local(4)     -- local interface
                  }
        ACCESS    read-only
        STATUS    mandatory
        DESCRIPTION
                  "The type of the mapping. The 'dynamic(2)' type
                  indicates that the IPv6 address to physical
                  addresses mapping has been dynamically
                  resolved using the IPv6 Neighbor Discovery
                  protocol. The static(3)' types indicates that
                  the mapping has been statically configured.
                  The local(4) indicates that the mapping is
                  provided for an entity's own interface address."
        ::= { axsVrfIpv6NetToMediaEntry 5 }

    axsVrfIpv6IfNetToMediaState OBJECT-TYPE
        SYNTAX    INTEGER {
                      reachable(1), -- confirmed reachability
                      stale(2),     -- unconfirmed reachability
                      delay(3),     -- waiting for reachability
                                    -- confirmation before entering
                                    -- the probe state
                      probe(4),     -- actively probing
                      invalid(5),   -- an invalidated mapping
                      unknown(6)    -- state can not be determined
                                    -- for some reason.
                  }
        ACCESS    read-only
        STATUS    mandatory
        DESCRIPTION
                  "The Neighbor Unreachability Detection [8] state
                  for the interface when the address mapping in
                  this entry is used."
        ::= { axsVrfIpv6NetToMediaEntry 6 }

    axsVrfIpv6IfNetToMediaLastUpdated OBJECT-TYPE
        SYNTAX    TimeStamp
        ACCESS    read-only
        STATUS    mandatory
        DESCRIPTION
                  "The value of sysUpTime at the time this entry
                  was last updated.  If this entry was updated prior
                  to the last re-initialization of the local network
                  management subsystem, then this object contains
                  a zero value."
        ::= { axsVrfIpv6NetToMediaEntry 7 }

    axsVrfIpv6NetToMediaValid OBJECT-TYPE
        SYNTAX    TruthValue
        ACCESS    read-only
        STATUS    mandatory
        DESCRIPTION
                  "Setting this object to the value 'false(2)' has
                  the effect of invalidating the corresponding entry
                  in the ipv6NetToMediaTable.  That is, it effectively
                  disassociates the interface identified with said
                  entry from the mapping identified with said entry.
                  It is an implementation-specific matter as to
                  whether the agent removes an invalidated entry
                  from the table.  Accordingly, management stations
                  must be prepared to receive tabular information
                  from agents that corresponds to entries not
                  currently in use.  Proper interpretation of such
                  entries requires examination of the relevant
                  ipv6NetToMediaValid object."
        ::= { axsVrfIpv6NetToMediaEntry 8 }

    axsVrfIpv6NetToMediaDescr OBJECT-TYPE
        SYNTAX    DisplayString
        ACCESS    read-only
        STATUS    mandatory
        DESCRIPTION
                  "The Description of VRF. The VRF identification which user setting."
        ::= { axsVrfIpv6NetToMediaEntry 9 }

    axsVrfIpv6FwNoTable OBJECT-TYPE
        SYNTAX    SEQUENCE OF AxsVrfIpv6FwNoEntry
        ACCESS    not-accessible
        STATUS    mandatory
        DESCRIPTION
                  "This entity's number of IPv6 Routing table about VRF."
        ::= { axsVrfIpv6Forward 1 }

    axsVrfIpv6FwNoEntry OBJECT-TYPE
        SYNTAX    AxsVrfIpv6FwNoEntry
        ACCESS    not-accessible
        STATUS    mandatory
        DESCRIPTION
                  "This entity's IPv6 Routing table about VRF."
        INDEX { axsVrfIpv6FwNoVRFIndex }
        ::= { axsVrfIpv6FwNoTable 1 }

    AxsVrfIpv6FwNoEntry ::= SEQUENCE {
        axsVrfIpv6FwNoVRFIndex    INTEGER,
        axsVrfIpv6FwNo            INTEGER,
        axsVrfIpv6FwNoDescr       DisplayString
    }

    axsVrfIpv6FwNoVRFIndex OBJECT-TYPE
        SYNTAX    INTEGER
        ACCESS    read-only
        STATUS    mandatory
        DESCRIPTION
                  "The index value which identifies VRF number."
        ::= { axsVrfIpv6FwNoEntry 1 }

    axsVrfIpv6FwNo OBJECT-TYPE
        SYNTAX    INTEGER
        ACCESS    read-only
        STATUS    mandatory
        DESCRIPTION
                  "The number of entry that is IPv6 Routing table."
        ::= { axsVrfIpv6FwNoEntry 2 }

    axsVrfIpv6FwNoDescr OBJECT-TYPE
        SYNTAX    DisplayString
        ACCESS    read-only
        STATUS    mandatory
        DESCRIPTION
                  "The Description of VRF. The VRF identification which user setting."
        ::= { axsVrfIpv6FwNoEntry 3 }

    axsVrfIpv6FwTable OBJECT-TYPE
        SYNTAX    SEQUENCE OF AxsVrfIpv6FwEntry
        ACCESS    not-accessible
        STATUS    mandatory
        DESCRIPTION
                  "This entity's IPv6 Routing table."
        ::= { axsVrfIpv6Forward 2 }

    axsVrfIpv6FwEntry OBJECT-TYPE
        SYNTAX    AxsVrfIpv6FwEntry
        ACCESS    not-accessible
        STATUS    mandatory
        DESCRIPTION
                  "A particular route to a particular destination,
                  under a particular policy."
        INDEX { axsVrfIpv6FwVrfIndex,
                axsVrfIpv6FwDest,
                axsVrfIpv6FwProto,
                axsVrfIpv6FwPolicy,
                axsVrfIpv6FwNextHop }
        ::= { axsVrfIpv6FwTable 1 }

    AxsVrfIpv6FwEntry ::= SEQUENCE {
        axsVrfIpv6FwVrfIndex     INTEGER,
        axsVrfIpv6FwDest         Ipv6Address,
        axsVrfIpv6FwPfxLength    INTEGER,
        axsVrfIpv6FwPolicy       INTEGER,
        axsVrfIpv6FwNextHop      Ipv6Address,
        axsVrfIpv6FwIfIndex      INTEGER,
        axsVrfIpv6FwType         INTEGER,
        axsVrfIpv6FwProto        INTEGER,
        axsVrfIpv6FwAge          INTEGER,
        axsVrfIpv6FwInfo         OBJECT IDENTIFIER,
        axsVrfIpv6FwNextHopAS    INTEGER,
        axsVrfIpv6FwMetric1      INTEGER,
        axsVrfIpv6FwMetric2      INTEGER,
        axsVrfIpv6FwMetric3      INTEGER,
        axsVrfIpv6FwMetric4      INTEGER,
        axsVrfIpv6FwMetric5      INTEGER,
        axsVrfIpv6FwDescr        DisplayString
    }

    axsVrfIpv6FwVrfIndex OBJECT-TYPE
        SYNTAX    INTEGER
        ACCESS    read-only
        STATUS    mandatory
        DESCRIPTION
                  "The index value which identifies VRF number."
        ::= { axsVrfIpv6FwEntry 1 }

    axsVrfIpv6FwDest OBJECT-TYPE
        SYNTAX    Ipv6Address
        ACCESS    read-only
        STATUS    mandatory
        DESCRIPTION
                  "The destination IPv6 address of this route."
        ::= { axsVrfIpv6FwEntry 2 }

    axsVrfIpv6FwPfxLength OBJECT-TYPE
        SYNTAX    INTEGER
        ACCESS    read-only
        STATUS    mandatory
        DESCRIPTION
                  "The length of the prefix (in bits) associated with
                  the IPv6 address of this entry."
        ::= { axsVrfIpv6FwEntry 3 }

    axsVrfIpv6FwPolicy OBJECT-TYPE
        SYNTAX    INTEGER
        ACCESS    read-only
        STATUS    mandatory
        DESCRIPTION
                  "The general set of conditions that would cause
                  the selection of one multipath route (set of
                  next hops for a given destination) is referred
                  to as 'policy'."
        ::= { axsVrfIpv6FwEntry 4 }

    axsVrfIpv6FwNextHop OBJECT-TYPE
        SYNTAX    Ipv6Address
        ACCESS    read-only
        STATUS    mandatory
        DESCRIPTION
                  "On remote routes, the address of the next system en route."
        ::= { axsVrfIpv6FwEntry 5 }

    axsVrfIpv6FwIfIndex OBJECT-TYPE
        SYNTAX    INTEGER
        ACCESS    read-only
        STATUS    mandatory
        DESCRIPTION
                  "The ifIndex value which identifies the local
                  interface through which the next hop of this
                  route should be reached."
        ::= { axsVrfIpv6FwEntry 6 }

    axsVrfIpv6FwType OBJECT-TYPE
        SYNTAX    INTEGER{
                      other(1),   -- not specified by this MIB
                      invalid(2), -- logically deleted
                      local(3),   -- local interface
                      remote(4)   -- remote destination
                  }
        ACCESS    read-only
        STATUS    mandatory
        DESCRIPTION
                  "The type of route."
        ::= { axsVrfIpv6FwEntry 7 }

    axsVrfIpv6FwProto OBJECT-TYPE
        SYNTAX    INTEGER {
                      other(1),       -- not specified
                      local(2),       -- local interface
                      netmgmt(3),     -- static route
                      rip(8),         -- Berkeley RIP or RIP-II
                      ospf(13),       -- Open Shortest Path First
                      bgp(14)         -- Border Gateway Protocol
                  }
        ACCESS    read-only
        STATUS    mandatory
        DESCRIPTION
                  "The routing mechanism via which this route was
                  learned."
        ::= { axsVrfIpv6FwEntry 8 }

    axsVrfIpv6FwAge OBJECT-TYPE
        SYNTAX    INTEGER
        ACCESS    read-only
        STATUS    mandatory
        DESCRIPTION
                  "The number of seconds since this route was
                  last updated or otherwise determined to be
                  correct."
        ::= { axsVrfIpv6FwEntry 9 }

    axsVrfIpv6FwInfo OBJECT-TYPE
        SYNTAX    OBJECT IDENTIFIER
        ACCESS    read-only
        STATUS    mandatory
        DESCRIPTION
                  "A reference to MIB definitions specific to the
                  particular routing protocol which is responsible
                  for this route, as determined by the value
                  specified in the route's axsVrfIpv6FwProto value.
                  Its value be set to the OBJECT IDENTIFIER { 0 0 }."
        ::= { axsVrfIpv6FwEntry 10 }

    axsVrfIpv6FwNextHopAS OBJECT-TYPE
        SYNTAX    INTEGER
        ACCESS    read-only
        STATUS    mandatory
        DESCRIPTION
                  "The Autonomous System Number of the Next Hop."
        ::= { axsVrfIpv6FwEntry 11 }

    axsVrfIpv6FwMetric1 OBJECT-TYPE
        SYNTAX    INTEGER
        ACCESS    read-only
        STATUS    mandatory
        DESCRIPTION
                  "The primary routing metric for this route."
        ::= { axsVrfIpv6FwEntry 12 }

    axsVrfIpv6FwMetric2 OBJECT-TYPE
        SYNTAX    INTEGER
        ACCESS    read-only
        STATUS    mandatory
        DESCRIPTION
                  "An alternate routing metric for this route."
        ::= { axsVrfIpv6FwEntry 13 }

    axsVrfIpv6FwMetric3 OBJECT-TYPE
        SYNTAX    INTEGER
        ACCESS    read-only
        STATUS    mandatory
        DESCRIPTION
                  "An alternate routing metric for this route.
                  Its value is set to -1."
        ::= { axsVrfIpv6FwEntry 14 }

    axsVrfIpv6FwMetric4 OBJECT-TYPE
        SYNTAX    INTEGER
        ACCESS    read-only
        STATUS    mandatory
        DESCRIPTION
                  "An alternate routing metric for this route.
                  Its value is set to -1."
        ::= { axsVrfIpv6FwEntry 15 }

    axsVrfIpv6FwMetric5 OBJECT-TYPE
        SYNTAX    INTEGER
        ACCESS    read-only
        STATUS    mandatory
        DESCRIPTION
                  "An alternate routing metric for this route.
                  Its value is set to -1."
        ::= { axsVrfIpv6FwEntry 16 }

    axsVrfIpv6FwDescr OBJECT-TYPE
        SYNTAX    DisplayString
        ACCESS    read-only
        STATUS    mandatory
        DESCRIPTION
                  "The Description of VRF. The VRF identification which user setting."
        ::= { axsVrfIpv6FwEntry 17 }

--  OSPF General Variables

axsOspfGeneralTable OBJECT-TYPE
	SYNTAX  SEQUENCE OF AxsOspfGeneralEntry
	ACCESS  not-accessible
	STATUS  mandatory
	DESCRIPTION
		"The table of OSPF information."
	::= { axsOspf 1 }

axsOspfGeneralEntry OBJECT-TYPE
	SYNTAX  AxsOspfGeneralEntry
	ACCESS  not-accessible
	STATUS  mandatory
	DESCRIPTION
		"The entry of OSPF information."
    INDEX { axsOspfGeneralDomainNumber }
	::= { axsOspfGeneralTable 1 }

	AxsOspfGeneralEntry ::=
		SEQUENCE {
		    axsOspfGeneralDomainNumber	INTEGER,
		    axsOspfRouterId				IpAddress,
		    axsOspfAdminStat				INTEGER,
		    axsOspfVersionNumber			INTEGER,
		    axsOspfAreaBdrRtrStatus		INTEGER,
		    axsOspfASBdrRtrStatus		INTEGER,
		    axsOspfExternLsaCount		Gauge,
		    axsOspfExternLsaCksumSum		INTEGER,
		    axsOspfTOSSupport			INTEGER,
		    axsOspfOriginateNewLsas		Counter,
		    axsOspfRxNewLsas				Counter,
		    axsOspfExtLsdbLimit			INTEGER,
		    axsOspfMulticastExtensions	INTEGER
		}

axsOspfGeneralDomainNumber OBJECT-TYPE
	SYNTAX  INTEGER
	ACCESS  read-only
	STATUS  mandatory
	DESCRIPTION
		"Domain number in the Autonomous System."
	::= { axsOspfGeneralEntry 1 }

axsOspfRouterId OBJECT-TYPE
	SYNTAX  IpAddress
	ACCESS  read-only
	STATUS  mandatory
	DESCRIPTION
		"A integer uniquely identifying the router
		in the Autonomous System."
	::= { axsOspfGeneralEntry 2 }

axsOspfAdminStat OBJECT-TYPE
	SYNTAX  INTEGER   { 
				enabled(1),
				disabled(2)
		    }
	ACCESS  read-only
	STATUS  mandatory
	DESCRIPTION
		"The  administrative  status  of  OSPF  in  the
		router.  "
	::= { axsOspfGeneralEntry 3 }

axsOspfVersionNumber OBJECT-TYPE
	SYNTAX  INTEGER
	ACCESS  read-only
	STATUS  mandatory
	DESCRIPTION
		"The current version number of the OSPF  
		protocol is 2."
	::= { axsOspfGeneralEntry 4 }

axsOspfAreaBdrRtrStatus OBJECT-TYPE
	SYNTAX  INTEGER { 
				true(1),
				false(2)
			}
	ACCESS  read-only
	STATUS  mandatory
	DESCRIPTION
		"A flag to note whether this router is an  area
		 border router."
	::= { axsOspfGeneralEntry 5 }

axsOspfASBdrRtrStatus OBJECT-TYPE
	SYNTAX  INTEGER {
				true(1),
				false(2)
			}
	ACCESS  read-only
	STATUS  mandatory
	DESCRIPTION
		"A flag to note whether this router is  configured
		as an Autonomous System border router."
	::= { axsOspfGeneralEntry 6 }

axsOspfExternLsaCount OBJECT-TYPE
	SYNTAX  Gauge
	ACCESS  read-only
	STATUS  mandatory
	DESCRIPTION
		"The number of external (LS type 5)  link-state
		advertisements in the link-state database."
	::= { axsOspfGeneralEntry 7 }

axsOspfExternLsaCksumSum OBJECT-TYPE
	SYNTAX  INTEGER
	ACCESS  read-only
	STATUS  mandatory
	DESCRIPTION
		"The 32-bit unsigned sum of the LS checksums of
		the  external  link-state  advertisements  contained
		in the link-state  database."
	::= { axsOspfGeneralEntry 8 }

axsOspfTOSSupport OBJECT-TYPE
	SYNTAX  INTEGER {
                            true(1),
                            false(2)
                        }
	ACCESS  read-only
	STATUS  mandatory
	DESCRIPTION
		"The router's support for type-of-service routing.
		 This value of false(2). "
	::= { axsOspfGeneralEntry 9 }

axsOspfOriginateNewLsas OBJECT-TYPE
	SYNTAX  Counter
	ACCESS  read-only
	STATUS  mandatory
	DESCRIPTION
		"The number of  new  link-state  advertisements
		that have been originated. "
	::= { axsOspfGeneralEntry 10 }

axsOspfRxNewLsas OBJECT-TYPE
	SYNTAX  Counter
	ACCESS  read-only
	STATUS  mandatory
	DESCRIPTION
		"The number of  link-state  advertisements  received
		determined  to  be  new instantiations."
	::= { axsOspfGeneralEntry 11 }

axsOspfExtLsdbLimit OBJECT-TYPE
	SYNTAX  INTEGER
	ACCESS  read-only
	STATUS  mandatory
	DESCRIPTION
		"The maximum number of non-default AS-external-LSAs
		entries that can be stored in the link-state database.
		If the value is -1,  then there is no limit.
		This value is -1"
	::= { axsOspfGeneralEntry 12 }

axsOspfMulticastExtensions OBJECT-TYPE
	SYNTAX  INTEGER
	ACCESS  read-only
	STATUS  mandatory
	DESCRIPTION
		"A Bit Mask indicating whether  the  router  is
		forwarding  IP  multicast  (Class  D) datagrams
		based on the algorithms defined in  the  Multicast
		Extensions to OSPF."
	::= { axsOspfGeneralEntry 13 }

axsOspfAreaTable OBJECT-TYPE
	SYNTAX  SEQUENCE OF AxsOspfAreaEntry
	ACCESS  not-accessible
	STATUS  mandatory
	DESCRIPTION
		"The router's support for demand routing."
	::= { axsOspf 2 }

axsOspfAreaEntry OBJECT-TYPE
	SYNTAX  AxsOspfAreaEntry
	ACCESS  not-accessible
	STATUS  mandatory
	DESCRIPTION
		"This entry contain ospf area information."
    INDEX { axsOspfAreaDomainNumber, axsOspfAreaId }
	::= { axsOspfAreaTable 1 }

	AxsOspfAreaEntry ::=
		SEQUENCE {
		    axsOspfAreaDomainNumber	INTEGER,
		    axsOspfAreaId			IpAddress,
		    axsOspfAuthType			INTEGER,
		    axsOspfImportAsExtern	INTEGER,
		    axsOspfSpfRuns			Counter,
		    axsOspfAreaBdrRtrCount	Gauge,
		    axsOspfAsBdrRtrCount		Gauge,
		    axsOspfAreaLsaCount		Gauge,
		    axsOspfAreaLsaCksumSum	INTEGER,
		    axsOspfAreaSummary		INTEGER,
		    axsOspfAreaStatus		INTEGER
		}

axsOspfAreaDomainNumber OBJECT-TYPE
	SYNTAX  INTEGER
	ACCESS  read-only
	STATUS  mandatory
	DESCRIPTION
		"An uniquely identifying number of domain."
	::= { axsOspfAreaEntry 1 }

axsOspfAreaId OBJECT-TYPE
	SYNTAX  IpAddress
	ACCESS  read-only
	STATUS  mandatory
	DESCRIPTION
		"A 32-bit integer uniquely identifying an area."
	::= { axsOspfAreaEntry 2 }

axsOspfAuthType OBJECT-TYPE
	SYNTAX  INTEGER
			-- none(0),
			-- simplePassword (1),
			-- md5(2)
	ACCESS  read-only
	STATUS  mandatory
	DESCRIPTION
		"The authentication type specified for an area."
	::= { axsOspfAreaEntry 3 }

axsOspfImportAsExtern OBJECT-TYPE
	SYNTAX  INTEGER { 
				importExternal (1),
				importNoExternal (2),
				importNssa (3)
			}
	ACCESS  read-only
	STATUS  mandatory
	DESCRIPTION
		"The area's support for importing  AS  external
		link- state advertisements."
	::= { axsOspfAreaEntry 4 }

axsOspfSpfRuns OBJECT-TYPE
	SYNTAX  Counter
	ACCESS  read-only
	STATUS  mandatory
	DESCRIPTION
		"The number of times that the intra-area  route
		table  has  been  calculated  using this area's
		link-state database."
	::= { axsOspfAreaEntry 5 }

axsOspfAreaBdrRtrCount OBJECT-TYPE
	SYNTAX  Gauge
	ACCESS  read-only
	STATUS  mandatory
	DESCRIPTION
		"The total number of area border routers reachable
		within this area."
	::= { axsOspfAreaEntry 6 }

axsOspfAsBdrRtrCount OBJECT-TYPE
	SYNTAX  Gauge
	ACCESS  read-only
	STATUS  mandatory
	DESCRIPTION
		"The total number of AS area border routers reachable
		within this area."
	::= { axsOspfAreaEntry 7 }

axsOspfAreaLsaCount OBJECT-TYPE
	SYNTAX  Gauge
	ACCESS  read-only
	STATUS  mandatory
	DESCRIPTION
		"The total number of LSA(link-state  advertisements) 
		in this area. Excluding AS External LSA's"
	::= { axsOspfAreaEntry 8 }

axsOspfAreaLsaCksumSum OBJECT-TYPE
	SYNTAX  INTEGER
	ACCESS  read-only
	STATUS  mandatory
	DESCRIPTION
		"The sum of LSA's  LS  checksums  contained in this
		area's link-state database."
	::= { axsOspfAreaEntry 9 }

axsOspfAreaSummary OBJECT-TYPE
	SYNTAX  INTEGER  {
				    noAreaSummary (1),
				    sendAreaSummary (2)
		    }
	ACCESS  read-only
	STATUS  mandatory
	DESCRIPTION
		"The variable axsOspfAreaSummary controls the import
		of summary LSAs into stub areas."
	::= { axsOspfAreaEntry 10 }

axsOspfAreaStatus OBJECT-TYPE
	SYNTAX  INTEGER {
                            active(1)
                        }
	ACCESS  read-only
	STATUS  mandatory
	DESCRIPTION
		"This variable displays the status of  the  entry.
		Value is only valid(1)."
	::= { axsOspfAreaEntry 11 }

axsOspfStubAreaTable OBJECT-TYPE
	SYNTAX  SEQUENCE OF AxsOspfStubAreaEntry
	ACCESS  not-accessible
	STATUS  mandatory
	DESCRIPTION
		"The set of metrics that will be advertised  by
		a default Area Border Router into a stub area."
	::= { axsOspf 3 }

axsOspfStubAreaEntry OBJECT-TYPE
	SYNTAX  AxsOspfStubAreaEntry
	ACCESS  not-accessible
	STATUS  mandatory
	DESCRIPTION
		"The metric for a given Type  of  Service  that
		will be advertised by a default Area Border Router 
		into a stub area."
    INDEX { axsOspfStubDomainNumber, axsOspfStubAreaId,
		    axsOspfStubTOS }
	::= { axsOspfStubAreaTable 1 }

	AxsOspfStubAreaEntry ::=
		SEQUENCE {
		    axsOspfStubDomainNumber	INTEGER,
		    axsOspfStubAreaId		IpAddress,
		    axsOspfStubTOS			INTEGER,
		    axsOspfStubMetric		INTEGER,
		    axsOspfStubStatus		INTEGER,
		    axsOspfStubMetricType	INTEGER
		}

axsOspfStubDomainNumber OBJECT-TYPE
	SYNTAX  INTEGER
	ACCESS  read-only
	STATUS  mandatory
	DESCRIPTION
		"The domain identifier for the Stub  Area."
	::= { axsOspfStubAreaEntry 1 }

axsOspfStubAreaId OBJECT-TYPE
	SYNTAX  IpAddress
	ACCESS  read-only
	STATUS  mandatory
	DESCRIPTION
		"The identifier for the Stub  Area."
	::= { axsOspfStubAreaEntry 2 }

axsOspfStubTOS OBJECT-TYPE
	SYNTAX  INTEGER
	ACCESS  read-only
	STATUS  mandatory
	DESCRIPTION
		"The Type of Service associated with the metric.
		Value is only 0."
	::= { axsOspfStubAreaEntry 3 }

axsOspfStubMetric OBJECT-TYPE
	SYNTAX  INTEGER
	ACCESS  read-only
	STATUS  mandatory
	DESCRIPTION
		"The metric value applied at the indicated type
		of service."
	::= { axsOspfStubAreaEntry 4 }

axsOspfStubStatus OBJECT-TYPE
	SYNTAX  INTEGER {
                            active(1)
                        }
	ACCESS  read-only
	STATUS  mandatory
	DESCRIPTION
		"This variable displays the status of the entry.
		This value is only valid(1)."
	::= { axsOspfStubAreaEntry 5 }

axsOspfStubMetricType OBJECT-TYPE
	SYNTAX  INTEGER  {
				ospfMetric(1),
				comparableCost(2),
				nonComparable(3)
		    }
	ACCESS  read-only
	STATUS  mandatory
	DESCRIPTION
		"This variable displays the type of metric advertised
		as a default route."
	::= { axsOspfStubAreaEntry 6 }

axsOspfLsdbTable OBJECT-TYPE
	SYNTAX  SEQUENCE OF AxsOspfLsdbEntry
	ACCESS  not-accessible
	STATUS  mandatory
	DESCRIPTION
		"The OSPF Process's Link State Database."
	::= { axsOspf 4 }

axsOspfLsdbEntry OBJECT-TYPE
	SYNTAX  AxsOspfLsdbEntry
	ACCESS  not-accessible
	STATUS  mandatory
	DESCRIPTION
		 "A single Link State Advertisement."
    INDEX { axsOspfLsdbDomainNumber, axsOspfLsdbAreaId,
		    axsOspfLsdbType, axsOspfLsdbLsid, axsOspfLsdbRouterId }
	::= { axsOspfLsdbTable 1 }

	AxsOspfLsdbEntry ::=
		SEQUENCE {
		    axsOspfLsdbDomainNumber	INTEGER,
		    axsOspfLsdbAreaId		IpAddress,
		    axsOspfLsdbType		INTEGER,
		    axsOspfLsdbLsid		IpAddress,
		    axsOspfLsdbRouterId		IpAddress,
		    axsOspfLsdbSequence		INTEGER,
		    axsOspfLsdbAge		INTEGER,
		    axsOspfLsdbChecksum		INTEGER,
		    axsOspfLsdbAdvertisement	OCTET STRING
		}

axsOspfLsdbDomainNumber OBJECT-TYPE
	SYNTAX  INTEGER
	ACCESS  read-only
	STATUS  mandatory
	DESCRIPTION
		"The identifier of the domain from  which
		the LSA was received."
	::= { axsOspfLsdbEntry 1 }

axsOspfLsdbAreaId OBJECT-TYPE
	SYNTAX  IpAddress
	ACCESS  read-only
	STATUS  mandatory
	DESCRIPTION
		"The 32 bit identifier of the Area  from  which
		the LSA was received."
	::= { axsOspfLsdbEntry 2 }

axsOspfLsdbType OBJECT-TYPE
	SYNTAX  INTEGER    {
		       routerLink (1),
		       networkLink (2),
		       summaryLink (3),
		       asSummaryLink (4),
		       asExternalLink (5), -- but see axsOspfExtLsdbTable
		       multicastLink (6),
		       nssaExternalLink (7)
		    }
	ACCESS  read-only
	STATUS  mandatory
	DESCRIPTION
		"The type  of  the  link  state  advertisement."
	::= { axsOspfLsdbEntry 3 }

axsOspfLsdbLsid OBJECT-TYPE
	SYNTAX  IpAddress
	ACCESS  read-only
	STATUS  mandatory
	DESCRIPTION
		"The Link State ID . It identifies the piece of the routing
		domain that is being described by the advertisement."
	::= { axsOspfLsdbEntry 4 }

axsOspfLsdbRouterId OBJECT-TYPE
	SYNTAX  IpAddress
	ACCESS  read-only
	STATUS  mandatory
	DESCRIPTION
		"The number that uniquely identifies the originating 
		router in the Autonomous System."
	::= { axsOspfLsdbEntry 5 }

axsOspfLsdbSequence OBJECT-TYPE
	SYNTAX  INTEGER
	ACCESS  read-only
	STATUS  mandatory
	DESCRIPTION
		"The sequence number field is a  signed  32-bit
		integer."
	::= { axsOspfLsdbEntry 6 }

axsOspfLsdbAge OBJECT-TYPE
	SYNTAX  INTEGER
	ACCESS  read-only
	STATUS  mandatory
	DESCRIPTION
		"This the age of the link state adver-
		tisement in seconds."
	::= { axsOspfLsdbEntry 7 }

axsOspfLsdbChecksum OBJECT-TYPE
	SYNTAX  INTEGER
	ACCESS  read-only
	STATUS  mandatory
	DESCRIPTION
		"This field is the  checksum  of  the  complete
		contents  of  the  advertisement, excepting the
		age field."
	::= { axsOspfLsdbEntry 8 }

axsOspfLsdbAdvertisement OBJECT-TYPE
	SYNTAX  OCTET STRING
	ACCESS  read-only
	STATUS  mandatory
	DESCRIPTION
		"The entire Link State Advertisement, including
		its header."
	::= { axsOspfLsdbEntry 9 }

axsOspfAreaRangeTable OBJECT-TYPE
	SYNTAX  SEQUENCE OF AxsOspfAreaRangeEntry
	ACCESS  not-accessible
	STATUS  mandatory
	DESCRIPTION
		"A range of IP addresses  specified  by  an  IP
		address/IP  network  mask  pair."
	::= { axsOspf 5 }

axsOspfAreaRangeEntry OBJECT-TYPE
	SYNTAX  AxsOspfAreaRangeEntry
	ACCESS  not-accessible
	STATUS  mandatory
	DESCRIPTION
		"A range of IP addresses specified by an IP
		address/IP network mask pair."
    INDEX { axsOspfAreaRangeDomainNumber, axsOspfAreaRangeAreaId,
		    axsOspfAreaRangeNet }
	::= { axsOspfAreaRangeTable 1 }

	AxsOspfAreaRangeEntry ::=
		SEQUENCE {
		    axsOspfAreaRangeDomainNumber	INTEGER,
		    axsOspfAreaRangeAreaId	IpAddress,
		    axsOspfAreaRangeNet		IpAddress,
		    axsOspfAreaRangeMask		IpAddress,
		    axsOspfAreaRangeStatus	INTEGER,
		    axsOspfAreaRangeEffect	INTEGER
		}

axsOspfAreaRangeDomainNumber OBJECT-TYPE
	SYNTAX  INTEGER
	ACCESS  read-only
	STATUS  mandatory
	DESCRIPTION
		"Domain number of the Area."
	::= { axsOspfAreaRangeEntry 1 }

axsOspfAreaRangeAreaId OBJECT-TYPE
	SYNTAX  IpAddress
	ACCESS  read-only
	STATUS  mandatory
	DESCRIPTION
		"The Area the Address  Range  is  to  be  found
		within."
	::= { axsOspfAreaRangeEntry 2 }

axsOspfAreaRangeNet OBJECT-TYPE
	SYNTAX  IpAddress
	ACCESS  read-only
	STATUS  mandatory
	DESCRIPTION
		"The IP Address of the Net or Subnet  indicated
		by the range."
	::= { axsOspfAreaRangeEntry 3 }

axsOspfAreaRangeMask OBJECT-TYPE
	SYNTAX  IpAddress
	ACCESS  read-only
	STATUS  mandatory
	DESCRIPTION
		"The Subnet Mask that pertains to  the  Net  or
		Subnet."
	::= { axsOspfAreaRangeEntry 4 }

axsOspfAreaRangeStatus OBJECT-TYPE
	SYNTAX  INTEGER    {
		       active(1),
		       inactive(2)
		    }
	ACCESS  read-only
	STATUS  mandatory
	DESCRIPTION
		"This variable displays the status of  the  entry.
		This value is only valid(1)."
	::= { axsOspfAreaRangeEntry 5 }

axsOspfAreaRangeEffect OBJECT-TYPE
	SYNTAX  INTEGER  {
				advertiseMatching (1),
				doNotAdvertiseMatching (2)
		    }
	ACCESS  read-only
	STATUS  mandatory
	DESCRIPTION
		"Subnets subsumed by ranges either trigger  the
		advertisement  of the indicated summary (adver-
		tiseMatching), or result in  the  subnet's  not
		being advertised at all outside the area."
	::= { axsOspfAreaRangeEntry 6 }

axsOspfIfTable OBJECT-TYPE
	SYNTAX  SEQUENCE OF AxsOspfIfEntry
	ACCESS  not-accessible
	STATUS  mandatory
	DESCRIPTION
		"The OSPF Interface Table describes the interfaces
		from the viewpoint of OSPF."
	::= { axsOspf 7 }

axsOspfIfEntry OBJECT-TYPE
	SYNTAX  AxsOspfIfEntry
	ACCESS  not-accessible
	STATUS  mandatory
	DESCRIPTION
		"The OSPF Interface Entry describes one  interface
		from the viewpoint of OSPF."
    INDEX { axsOspfIfDomainNumber, axsOspfIfIpAddress, axsOspfAddressLessIf }
	::= { axsOspfIfTable 1 }

	AxsOspfIfEntry ::=
		SEQUENCE {
		    axsOspfIfDomainNumber			INTEGER,
		    axsOspfIfIpAddress				IpAddress,
		    axsOspfAddressLessIf				INTEGER,
		    axsOspfIfAreaId					IpAddress,
		    axsOspfIfType					INTEGER,
		    axsOspfIfAdminStat				INTEGER,
		    axsOspfIfRtrPriority				INTEGER,
		    axsOspfIfTransitDelay			INTEGER,
		    axsOspfIfRetransInterval			INTEGER,
		    axsOspfIfHelloInterval			INTEGER,
		    axsOspfIfRtrDeadInterval			INTEGER,
		    axsOspfIfPollInterval			INTEGER,
		    axsOspfIfState					INTEGER,
		    axsOspfIfDesignatedRouter		IpAddress,
		    axsOspfIfEvents					Counter,
		    axsOspfIfAuthKey					OCTET STRING,
		    axsOspfIfStatus					INTEGER,
		    axsOspfIfMulticastForwarding		INTEGER,
		    axsOspfIfBackupDesignatedRouter	IpAddress
		}

axsOspfIfDomainNumber OBJECT-TYPE
	SYNTAX  INTEGER
	ACCESS  read-only
	STATUS  mandatory
	DESCRIPTION
		"The domain number of this OSPF interface."
	::= { axsOspfIfEntry 1 }

axsOspfIfIpAddress OBJECT-TYPE
	SYNTAX  IpAddress
	ACCESS  read-only
	STATUS  mandatory
	DESCRIPTION
		"The IP address of this OSPF interface."
	::= { axsOspfIfEntry 2 }

axsOspfAddressLessIf OBJECT-TYPE
	SYNTAX  INTEGER
	ACCESS  read-only
	STATUS  mandatory
	DESCRIPTION
		"For the purpose of easing  the  instancing  of
		addressed   and  addressless  interfaces;  This
		variable takes the value 0 on  interfaces  with
		IP  Addresses,  and  the corresponding value of
		ifIndex for interfaces having no IP Address."
	::= { axsOspfIfEntry 3 }

axsOspfIfAreaId OBJECT-TYPE
	SYNTAX  IpAddress
	ACCESS  read-only
	STATUS  mandatory
	DESCRIPTION
		"A integer uniquely identifying the area to which 
		the interface connects."
	::= { axsOspfIfEntry 4 }

axsOspfIfType OBJECT-TYPE
	SYNTAX  INTEGER  {
				 broadcast (1),
				 nbma (2),
				 pointToPoint (3),
				 pointToMultipoint (5)
		    }
	ACCESS  read-only
	STATUS  mandatory
	DESCRIPTION
		"The OSPF interface type."
	::= { axsOspfIfEntry 5 }

axsOspfIfAdminStat OBJECT-TYPE
	SYNTAX  INTEGER { 
				enabled(1),
				disabled(2)
		    }
	ACCESS  read-only
	STATUS  mandatory
	DESCRIPTION
		"The OSPF  interface's  administrative  status."
	::= { axsOspfIfEntry 6 }

axsOspfIfRtrPriority OBJECT-TYPE
	SYNTAX  INTEGER
	ACCESS  read-only
	STATUS  mandatory
	DESCRIPTION
		"The priority of this interface."
	::= { axsOspfIfEntry 7 }

axsOspfIfTransitDelay OBJECT-TYPE
	SYNTAX  INTEGER
	ACCESS  read-only
	STATUS  mandatory
	DESCRIPTION
		"The estimated number of seconds  it  takes  to
		transmit  a  link state update packet over this
		interface."
	::= { axsOspfIfEntry 8 }

axsOspfIfRetransInterval OBJECT-TYPE
	SYNTAX  INTEGER
	ACCESS  read-only
	STATUS  mandatory
	DESCRIPTION
		"The number of seconds between link-state ad-
		vertisement retransmissions, for adjacencies
		belonging to this  interface."
	::= { axsOspfIfEntry 9 }

axsOspfIfHelloInterval OBJECT-TYPE
	SYNTAX  INTEGER
	ACCESS  read-only
	STATUS  mandatory
	DESCRIPTION
		"The length of time, in  seconds,  between the
		Hello  packets that the router sends on the interface."
	::= { axsOspfIfEntry 10 }

axsOspfIfRtrDeadInterval OBJECT-TYPE
	SYNTAX  INTEGER
	ACCESS  read-only
	STATUS  mandatory
	DESCRIPTION
		"The number of seconds that  a  router's  Hello
		packets  have  not been seen before it's neighbors 
		declare the router down."
	::= { axsOspfIfEntry 11 }

axsOspfIfPollInterval OBJECT-TYPE
	SYNTAX  INTEGER
	ACCESS  read-only
	STATUS  mandatory
	DESCRIPTION
		"The larger time interval, in seconds,  between
		the  Hello  packets  sent  to  an inactive non-
		broadcast multi- access neighbor."
	::= { axsOspfIfEntry 12 }

axsOspfIfState OBJECT-TYPE
	SYNTAX  INTEGER   {
				down (1),
				loopback (2),
				waiting (3),
				pointToPoint (4),
				designatedRouter (5),
				backupDesignatedRouter (6),
				otherDesignatedRouter (7)
		    }
	ACCESS  read-only
	STATUS  mandatory
	DESCRIPTION
		"The OSPF Interface State."
	::= { axsOspfIfEntry 13 }

axsOspfIfDesignatedRouter OBJECT-TYPE
	SYNTAX  IpAddress
	ACCESS  read-only
	STATUS  mandatory
	DESCRIPTION
		"The IP Address of the Designated Router."
	::= { axsOspfIfEntry 14 }

axsOspfIfEvents OBJECT-TYPE
	SYNTAX  Counter
	ACCESS  read-only
	STATUS  mandatory
	DESCRIPTION
		"The number of times this  OSPF  interface  has
		changed its state, or an error has occurred."
	::= { axsOspfIfEntry 16 }

axsOspfIfAuthKey OBJECT-TYPE
	SYNTAX  OCTET STRING
	ACCESS  read-only
	STATUS  mandatory
	DESCRIPTION
		"The Authentication Key."
	::= { axsOspfIfEntry 17 }

axsOspfIfStatus OBJECT-TYPE
	SYNTAX  INTEGER   { 
				active(1),
				inactive(2)
		    }
	ACCESS  read-only
	STATUS  mandatory
	DESCRIPTION
		"This variable displays the status of  the  entry.
		this value is only valid(1)."
	::= { axsOspfIfEntry 18 }

axsOspfIfMulticastForwarding OBJECT-TYPE
	SYNTAX  INTEGER  {
				blocked (1),		-- no multicast forwarding
				multicast (2),     -- using multicast address
				unicast (3)		-- to each OSPF neighbor
		    }
	ACCESS  read-only
	STATUS  mandatory
	DESCRIPTION
		"The way multicasts should  forwarded  on  this
		interface;  not  forwarded,  forwarded  as data
		link multicasts, or forwarded as data link unicasts."
	::= { axsOspfIfEntry 19 }

axsOspfIfBackupDesignatedRouter OBJECT-TYPE
	SYNTAX  IpAddress
	ACCESS  read-only
	STATUS  mandatory
	DESCRIPTION
		"The IP Address of the Backup Designated Router."
	::= { axsOspfIfEntry 15 }

axsOspfIfMetricTable OBJECT-TYPE
	SYNTAX  SEQUENCE OF AxsOspfIfMetricEntry
	ACCESS  not-accessible
	STATUS  mandatory
	DESCRIPTION
		"The TOS metrics for a non-virtual interface identified
		by the interface index."
	::= { axsOspf 8 }

axsOspfIfMetricEntry OBJECT-TYPE
	SYNTAX  AxsOspfIfMetricEntry
	ACCESS  not-accessible
	STATUS  mandatory
	DESCRIPTION
		"A particular TOS metric for a non-virtual interface
		identified by the interface index."
    INDEX { axsOspfIfMetricDomainNumber, axsOspfIfMetricIpAddress,
		    axsOspfIfMetricAddressLessIf, axsOspfIfMetricTOS }
	::= { axsOspfIfMetricTable 1 }

	AxsOspfIfMetricEntry ::=
		SEQUENCE {
		    axsOspfIfMetricDomainNumber	INTEGER,
		    axsOspfIfMetricIpAddress		IpAddress,
		    axsOspfIfMetricAddressLessIf	INTEGER,
		    axsOspfIfMetricTOS			INTEGER,
		    axsOspfIfMetricValue			INTEGER,
		    axsOspfIfMetricStatus		INTEGER
		}

axsOspfIfMetricDomainNumber OBJECT-TYPE
	SYNTAX  INTEGER
	ACCESS  read-only
	STATUS  mandatory
	DESCRIPTION
		"The domain number of this OSPF interface."
	::= { axsOspfIfMetricEntry 1 }

axsOspfIfMetricIpAddress OBJECT-TYPE
	SYNTAX  IpAddress
	ACCESS  read-only
	STATUS  mandatory
	DESCRIPTION
		"The IP address of this OSPF interface."
	::= { axsOspfIfMetricEntry 2 }

axsOspfIfMetricAddressLessIf OBJECT-TYPE
	SYNTAX  INTEGER
	ACCESS  read-only
	STATUS  mandatory
	DESCRIPTION
		"For the purpose of easing  the  instancing  of
		addressed   and  addressless  interfaces;  This
		variable takes the value 0 on  interfaces  with
		IP  Addresses, and the value of ifIndex for in-
		terfaces having no IP Address."
	::= { axsOspfIfMetricEntry 3 }

axsOspfIfMetricTOS OBJECT-TYPE
	SYNTAX  INTEGER
	ACCESS  read-only
	STATUS  mandatory
	DESCRIPTION
		"The type of service metric  being  referenced.
		this value is only 0."
	::= { axsOspfIfMetricEntry 4 }

axsOspfIfMetricValue OBJECT-TYPE
	SYNTAX  INTEGER
	ACCESS  read-only
	STATUS  mandatory
	DESCRIPTION
		"The metric of using this type  of  service  on
		this interface."
	::= { axsOspfIfMetricEntry 5 }

axsOspfIfMetricStatus OBJECT-TYPE
	SYNTAX  INTEGER {
                                active(1)
                        }
	ACCESS  read-only
	STATUS  mandatory
	DESCRIPTION
		"This variable displays the status of the entry.
		This entry status is only valid(1)."
	::= { axsOspfIfMetricEntry 6 }

axsOspfVirtIfTable OBJECT-TYPE
	SYNTAX  SEQUENCE OF AxsOspfVirtIfEntry
	ACCESS  not-accessible
	STATUS  mandatory
	DESCRIPTION
		"Information about this router's virtual interfaces."
	::= { axsOspf 9 }

axsOspfVirtIfEntry OBJECT-TYPE
	SYNTAX  AxsOspfVirtIfEntry
	ACCESS  not-accessible
	STATUS  mandatory
	DESCRIPTION
		"Information about a single Virtual Interface."
    INDEX { axsOspfVirtIfDomainNumber, axsOspfVirtIfAreaId,
		    axsOspfVirtIfNeighbor }
	::= { axsOspfVirtIfTable 1 }

	AxsOspfVirtIfEntry ::=
		SEQUENCE {
		    axsOspfVirtIfDomainNumber	INTEGER,
		    axsOspfVirtIfAreaId			IpAddress,
		    axsOspfVirtIfNeighbor		IpAddress,
		    axsOspfVirtIfTransitDelay	INTEGER,
		    axsOspfVirtIfRetransInterval	INTEGER,
		    axsOspfVirtIfHelloInterval	INTEGER,
		    axsOspfVirtIfRtrDeadInterval	INTEGER,
		    axsOspfVirtIfState			INTEGER,
		    axsOspfVirtIfEvents			Counter,
		    axsOspfVirtIfAuthKey			OCTET STRING,
		    axsOspfVirtIfStatus			INTEGER
		}

axsOspfVirtIfDomainNumber OBJECT-TYPE
	SYNTAX  INTEGER
	ACCESS  read-only
	STATUS  mandatory
	DESCRIPTION
		"The domain number for this  Virtual Interface"
	::= { axsOspfVirtIfEntry 1 }

axsOspfVirtIfAreaId OBJECT-TYPE
	SYNTAX  IpAddress
	ACCESS  read-only
	STATUS  mandatory
	DESCRIPTION
		"The Transit Area that the Virtual Link traverses."
	::= { axsOspfVirtIfEntry 2 }

axsOspfVirtIfNeighbor OBJECT-TYPE
	SYNTAX  IpAddress
	ACCESS  read-only
	STATUS  mandatory
	DESCRIPTION
		"The Router ID of the Virtual Neighbor."
	::= { axsOspfVirtIfEntry 3 }

axsOspfVirtIfTransitDelay OBJECT-TYPE
	SYNTAX  INTEGER
	ACCESS  read-only
	STATUS  mandatory
	DESCRIPTION
		"The estimated number of seconds  it  takes  to
		transmit  a link- state update packet over this
		interface."
	::= { axsOspfVirtIfEntry 4 }

axsOspfVirtIfRetransInterval OBJECT-TYPE
	SYNTAX  INTEGER
	ACCESS  read-only
	STATUS  mandatory
	DESCRIPTION
		"The number of seconds between link-state advertisement
		retransmissions, for adjacencies belonging to this
		interface."
	::= { axsOspfVirtIfEntry 5 }

axsOspfVirtIfHelloInterval OBJECT-TYPE
	SYNTAX  INTEGER
	ACCESS  read-only
	STATUS  mandatory
	DESCRIPTION
		"The length of time, in  seconds, between the
		Hello  packets that the router sends on the in-
		terface. "
	::= { axsOspfVirtIfEntry 6 }

axsOspfVirtIfRtrDeadInterval OBJECT-TYPE
	SYNTAX  INTEGER
	ACCESS  read-only
	STATUS  mandatory
	DESCRIPTION
		"The number of seconds that  a  router's  Hello
		packets  have  not been seen before it's neighbors
		declare the router down."
	::= { axsOspfVirtIfEntry 7 }

axsOspfVirtIfState OBJECT-TYPE
	SYNTAX  INTEGER    {
				down (1),		    -- these use the same encoding
				pointToPoint (4)     -- as the axsOspfIfTable
		    }
	ACCESS  read-only
	STATUS  mandatory
	DESCRIPTION
		"OSPF virtual interface states."
	::= { axsOspfVirtIfEntry 8 }

axsOspfVirtIfEvents OBJECT-TYPE
	SYNTAX  Counter
	ACCESS  read-only
	STATUS  mandatory
	DESCRIPTION
		"The number of state changes or error events on
		this Virtual Link"
	::= { axsOspfVirtIfEntry 9 }

axsOspfVirtIfAuthKey OBJECT-TYPE
	SYNTAX  OCTET STRING
	ACCESS  read-only
	STATUS  mandatory
	DESCRIPTION
		"Authentication key of this interface."
	::= { axsOspfVirtIfEntry 10 }

axsOspfVirtIfStatus OBJECT-TYPE
	SYNTAX  INTEGER    { 
				active(1),
				inactive(2)
		    }
	ACCESS  read-only
	STATUS  mandatory
	DESCRIPTION
		"This variable displays the status of  the  entry.
		This entry is only valid(1)."
	::= { axsOspfVirtIfEntry 11 }

axsOspfNbrTable OBJECT-TYPE
	SYNTAX  SEQUENCE OF AxsOspfNbrEntry
	ACCESS  not-accessible
	STATUS  mandatory
	DESCRIPTION
		"A table of non-virtual neighbor information."
	::= { axsOspf 10 }

axsOspfNbrEntry OBJECT-TYPE
	SYNTAX  AxsOspfNbrEntry
	ACCESS  not-accessible
	STATUS  mandatory
	DESCRIPTION
		"The information regarding a single neighbor."
    INDEX { axsOspfNbrDomainNumber, axsOspfNbrIpAddr, axsOspfNbrAddressLessIndex }
	::= { axsOspfNbrTable 1 }

	AxsOspfNbrEntry ::=
		SEQUENCE {
		    axsOspfNbrDomainNumber		INTEGER,
		    axsOspfNbrIpAddr				IpAddress,
		    axsOspfNbrAddressLessIndex	INTEGER,
		    axsOspfNbrRtrId				IpAddress,
		    axsOspfNbrOptions			INTEGER,
		    axsOspfNbrPriority			INTEGER,
		    axsOspfNbrState				INTEGER,
		    axsOspfNbrEvents				Counter,
		    axsOspfNbrLsRetransQLen		Gauge,
		    axsOspfNbmaNbrStatus			INTEGER,
		    axsOspfNbmaNbrPermanence		INTEGER
		}

axsOspfNbrDomainNumber OBJECT-TYPE
	SYNTAX  INTEGER
	ACCESS  read-only
	STATUS  mandatory
	DESCRIPTION
		"OSPF domain number of this neighbor."
	::= { axsOspfNbrEntry 1 }

axsOspfNbrIpAddr OBJECT-TYPE
	SYNTAX  IpAddress
	ACCESS  read-only
	STATUS  mandatory
	DESCRIPTION
		"The IP address this neighbor is using  in  its
		IP  Source  Address."
	::= { axsOspfNbrEntry 2 }

axsOspfNbrAddressLessIndex OBJECT-TYPE
	SYNTAX  INTEGER
	ACCESS  read-only
	STATUS  mandatory
	DESCRIPTION
		"On an interface having an  IP  Address,  zero.
		On  addressless  interfaces,  the corresponding
		value of ifIndex in the Internet Standard  MIB."
	::= { axsOspfNbrEntry 3 }

axsOspfNbrRtrId OBJECT-TYPE
	SYNTAX  IpAddress
	ACCESS  read-only
	STATUS  mandatory
	DESCRIPTION
		"The integer uniquely identifying the neighboring
		router in the Autonomous System."
	::= { axsOspfNbrEntry 4 }

axsOspfNbrOptions OBJECT-TYPE
	SYNTAX  INTEGER
	ACCESS  read-only
	STATUS  mandatory
	DESCRIPTION
		"A Bit Mask corresponding to the neighbor's op-
		 tions field.

		 Bit 0, if set, indicates that the  system  will
		 operate  on  Type of Service metrics other than
		 TOS 0.  If zero, the neighbor will  ignore  all
		 metrics except the TOS 0 metric.

		 Bit 1, if set, indicates  that  the  associated
		 area  accepts and operates on external informa-
		 tion; if zero, it is a stub area.

		 Bit 2, if set, indicates that the system is ca-
		 pable  of routing IP Multicast datagrams; i.e.,
		 that it implements the Multicast Extensions  to
		 OSPF.

		 Bit 3, if set, indicates  that  the  associated
		 area  is  an  NSSA.  These areas are capable of
		 carrying type 7 external advertisements,  which
		 are  translated into type 5 external advertise-
		 ments at NSSA borders."
	::= { axsOspfNbrEntry 5 }

axsOspfNbrPriority OBJECT-TYPE
	SYNTAX  INTEGER
	ACCESS  read-only
	STATUS  mandatory
	DESCRIPTION
		"The priority of this neighbor."
	::= { axsOspfNbrEntry 6 }

axsOspfNbrState OBJECT-TYPE
	SYNTAX  INTEGER   {
				down (1),
				attempt (2),
				init (3),
				twoWay (4),
				exchangeStart (5),
				exchange (6),
				loading (7),
				full (8)
		    }
	ACCESS  read-only
	STATUS  mandatory
	DESCRIPTION
		"The State of the relationship with this Neighbor."
	::= { axsOspfNbrEntry 7 }

axsOspfNbrEvents OBJECT-TYPE
	SYNTAX  Counter
	ACCESS  read-only
	STATUS  mandatory
	DESCRIPTION
		"The number of times this neighbor relationship
		has changed state, or an error has occurred."
	::= { axsOspfNbrEntry 8 }

axsOspfNbrLsRetransQLen OBJECT-TYPE
	SYNTAX  Gauge
	ACCESS  read-only
	STATUS  mandatory
	DESCRIPTION
		"The current length of the retransmission queue."
	::= { axsOspfNbrEntry 9 }

axsOspfNbmaNbrStatus OBJECT-TYPE
	SYNTAX  INTEGER {
                               active(1)
                        }
	ACCESS  read-only
	STATUS  mandatory
	DESCRIPTION
		"This variable displays the status of the entry.
		This entry value is only valid(1). And enable to response
		this entry when axsOspfIfType is nbma."
	::= { axsOspfNbrEntry 10 }

axsOspfNbmaNbrPermanence OBJECT-TYPE
	SYNTAX  INTEGER  {
				dynamic (1),		-- learned through protocol
				 permanent (2)       -- configured address
		    }
	ACCESS  read-only
	STATUS  mandatory
	DESCRIPTION
		"This variable displays the status of the entry."
	::= { axsOspfNbrEntry 11 }

axsOspfVirtNbrTable OBJECT-TYPE
	SYNTAX  SEQUENCE OF AxsOspfVirtNbrEntry
	ACCESS  not-accessible
	STATUS  mandatory
	DESCRIPTION
		"A table of virtual neighbor information."
	::= { axsOspf 11 }

axsOspfVirtNbrEntry OBJECT-TYPE
	SYNTAX  AxsOspfVirtNbrEntry
	ACCESS  not-accessible
	STATUS  mandatory
	DESCRIPTION
		"Virtual neighbor information."
    INDEX { axsOspfVirtNbrDomainNumber, axsOspfVirtNbrArea,
		    axsOspfVirtNbrRtrId }
	::= { axsOspfVirtNbrTable 1 }

	AxsOspfVirtNbrEntry ::=
		SEQUENCE {
		    axsOspfVirtNbrDomainNumber		INTEGER,
		    axsOspfVirtNbrArea				IpAddress,
		    axsOspfVirtNbrRtrId				IpAddress,
		    axsOspfVirtNbrIpAddr				IpAddress,
		    axsOspfVirtNbrOptions			INTEGER,
		    axsOspfVirtNbrState				INTEGER,
		    axsOspfVirtNbrEvents				Counter,
		    axsOspfVirtNbrLsRetransQLen		Gauge
		}

axsOspfVirtNbrDomainNumber OBJECT-TYPE
	SYNTAX  INTEGER
	ACCESS  read-only
	STATUS  mandatory
	DESCRIPTION
		"The domain number."
	::= { axsOspfVirtNbrEntry 1 }

axsOspfVirtNbrArea OBJECT-TYPE
	SYNTAX  IpAddress
	ACCESS  read-only
	STATUS  mandatory
	DESCRIPTION
		"The Transit Area Identifier."
	::= { axsOspfVirtNbrEntry 2 }

axsOspfVirtNbrRtrId OBJECT-TYPE
	SYNTAX  IpAddress
	ACCESS  read-only
	STATUS  mandatory
	DESCRIPTION
		"A integer  uniquely  identifying  the neighboring
		 router in the Autonomous System."
	::= { axsOspfVirtNbrEntry 3 }

axsOspfVirtNbrIpAddr OBJECT-TYPE
	SYNTAX  IpAddress
	ACCESS  read-only
	STATUS  mandatory
	DESCRIPTION
		"The IP address this Virtual Neighbor is using."
	::= { axsOspfVirtNbrEntry 4 }

axsOspfVirtNbrOptions OBJECT-TYPE
	SYNTAX  INTEGER
	ACCESS  read-only
	STATUS  mandatory
	DESCRIPTION
		"A Bit Mask corresponding to the neighbor's options
		 field.

		 Bit 1, if set, indicates that the  system  will operate
		 on Type of Service metrics other than TOS 0. If zero,
		 the neighbor will  ignore  all metrics except the TOS
		 0 metric.

		 Bit 2, if set, indicates  that  the  system  is Network
		 Multicast  capable; ie, that it implements OSPF Multicast
		 Routing."
	::= { axsOspfVirtNbrEntry 5 }

axsOspfVirtNbrState OBJECT-TYPE
	SYNTAX  INTEGER   {
				down (1),
				attempt (2),
				init (3),
				twoWay (4),
				exchangeStart (5),
				exchange (6),
				loading (7),
				full (8)
		    }
	ACCESS  read-only
	STATUS  mandatory
	DESCRIPTION
		"The state of the  Virtual  Neighbor  Relationship."
	::= { axsOspfVirtNbrEntry 6 }

axsOspfVirtNbrEvents OBJECT-TYPE
	SYNTAX  Counter
	ACCESS  read-only
	STATUS  mandatory
	DESCRIPTION
		"The number of times this virtual link has changed
		its state, or an error has occurred."
	::= { axsOspfVirtNbrEntry 7 }

axsOspfVirtNbrLsRetransQLen OBJECT-TYPE
	SYNTAX  Gauge
	ACCESS  read-only
	STATUS  mandatory
	DESCRIPTION
		"The current length of the retransmission queue."
	::= { axsOspfVirtNbrEntry 8 }

axsOspfExtLsdbTable OBJECT-TYPE
	SYNTAX  SEQUENCE OF AxsOspfExtLsdbEntry
	ACCESS  not-accessible
	STATUS  mandatory
	DESCRIPTION
		"The OSPF Process's Links State Database."
	::= { axsOspf 12 }

axsOspfExtLsdbEntry OBJECT-TYPE
	SYNTAX  AxsOspfExtLsdbEntry
	ACCESS  not-accessible
	STATUS  mandatory
	DESCRIPTION
		"A single Link State Advertisement."
    INDEX { axsOspfExtLsdbDomainNumber, axsOspfExtLsdbType,
		    axsOspfExtLsdbLsid, axsOspfExtLsdbRouterId }
	::= { axsOspfExtLsdbTable 1 }

	AxsOspfExtLsdbEntry ::=
		SEQUENCE {
		    axsOspfExtLsdbDomainNumber	INTEGER,
		    axsOspfExtLsdbType			INTEGER,
		    axsOspfExtLsdbLsid			IpAddress,
		    axsOspfExtLsdbRouterId		IpAddress,
		    axsOspfExtLsdbSequence		INTEGER,
		    axsOspfExtLsdbAge			INTEGER,
		    axsOspfExtLsdbChecksum		INTEGER,
		    axsOspfExtLsdbAdvertisement	OCTET STRING
		}

axsOspfExtLsdbDomainNumber OBJECT-TYPE
	SYNTAX  INTEGER
	ACCESS  read-only
	STATUS  mandatory
	DESCRIPTION
		"OSPF domain number."
	::= { axsOspfExtLsdbEntry 1 }

axsOspfExtLsdbType OBJECT-TYPE
	SYNTAX  INTEGER {
				asExternalLink (5)
		    }
	ACCESS  read-only
	STATUS  mandatory
	DESCRIPTION
		"The type  of  the  link  state  advertisement."
	::= { axsOspfExtLsdbEntry 2 }

axsOspfExtLsdbLsid OBJECT-TYPE
	SYNTAX  IpAddress
	ACCESS  read-only
	STATUS  mandatory
	DESCRIPTION
		"The Link State ID is an LS Type Specific field
		 containing either a Router ID or an IP Address;
		 it identifies the piece of the  routing  domain
		 that is being described by the advertisement."
	::= { axsOspfExtLsdbEntry 3 }

axsOspfExtLsdbRouterId OBJECT-TYPE
	SYNTAX  IpAddress
	ACCESS  read-only
	STATUS  mandatory
	DESCRIPTION
		"The 32 bit number that uniquely identifies the
		originating router in the Autonomous System."
	::= { axsOspfExtLsdbEntry 4 }

axsOspfExtLsdbSequence OBJECT-TYPE
	SYNTAX  INTEGER
	ACCESS  read-only
	STATUS  mandatory
	DESCRIPTION
		"The sequence number field is a  signed  32-bit integer."
	::= { axsOspfExtLsdbEntry 5 }

axsOspfExtLsdbAge OBJECT-TYPE
	SYNTAX  INTEGER
	ACCESS  read-only
	STATUS  mandatory
	DESCRIPTION
		"The age of the link state advertisement in seconds."
	::= { axsOspfExtLsdbEntry 6 }

axsOspfExtLsdbChecksum OBJECT-TYPE
	SYNTAX  INTEGER
	ACCESS  read-only
	STATUS  mandatory
	DESCRIPTION
		"This field is the  checksum  of  the  complete
		 contents  of  the  advertisement, excepting the
		 age field.  The age field is excepted  so  that
		 an   advertisement's  age  can  be  incremented
		 without updating the  checksum."
	::= { axsOspfExtLsdbEntry 7 }

axsOspfExtLsdbAdvertisement OBJECT-TYPE
	SYNTAX  OCTET STRING
	ACCESS  read-only
	STATUS  mandatory
	DESCRIPTION
		"The entire Link State Advertisement, including its header."
	::= { axsOspfExtLsdbEntry 8 }

axsOspfAreaAggregateTable OBJECT-TYPE
	SYNTAX  SEQUENCE OF AxsOspfAreaAggregateEntry
	ACCESS  not-accessible
	STATUS  mandatory
	DESCRIPTION
		"A range of IP addresses  specified  by  an  IP
		address/IP  network  mask  pair."
	::= { axsOspf 14 }

axsOspfAreaAggregateEntry OBJECT-TYPE
	SYNTAX  AxsOspfAreaAggregateEntry
	ACCESS  not-accessible
	STATUS  mandatory
	DESCRIPTION
		"A range of IP addresses  specified  by  an  IP
		address/IP  network  mask  pair."
    INDEX { axsOspfAreaAggregateDomainNumber, axsOspfAreaAggregateAreaID,
		    axsOspfAreaAggregateLsdbType, axsOspfAreaAggregateNet,
		    axsOspfAreaAggregateMask }
	::= { axsOspfAreaAggregateTable 1 }

	AxsOspfAreaAggregateEntry ::=
		SEQUENCE {
		    axsOspfAreaAggregateDomainNumber	INTEGER,
		    axsOspfAreaAggregateAreaID		IpAddress,
		    axsOspfAreaAggregateLsdbType		INTEGER,
		    axsOspfAreaAggregateNet			IpAddress,
		    axsOspfAreaAggregateMask			IpAddress,
		    axsOspfAreaAggregateStatus		INTEGER,
		    axsOspfAreaAggregateEffect		INTEGER
		}

axsOspfAreaAggregateDomainNumber OBJECT-TYPE
	SYNTAX  INTEGER
	ACCESS  read-only
	STATUS  mandatory
	DESCRIPTION
		"OSPF domain number."
	::= { axsOspfAreaAggregateEntry 1 }

axsOspfAreaAggregateAreaID OBJECT-TYPE
	SYNTAX  IpAddress
	ACCESS  read-only
	STATUS  mandatory
	DESCRIPTION
		"The Area the Address Aggregate is to be found within."
	::= { axsOspfAreaAggregateEntry 2 }

axsOspfAreaAggregateLsdbType OBJECT-TYPE
	SYNTAX  INTEGER  {
				summaryLink (3),
				nssaExternalLink (7)
		    }
	ACCESS  read-only
	STATUS  mandatory
	DESCRIPTION
		"The type of the Address Aggregate. This field
		 specifies  the  Lsdb type that this Address 
		 Aggregate applies to."
	::= { axsOspfAreaAggregateEntry 3 }

axsOspfAreaAggregateNet OBJECT-TYPE
	SYNTAX  IpAddress
	ACCESS  read-only
	STATUS  mandatory
	DESCRIPTION
		"The IP Address of the Net or Subnet indicated by the range."
	::= { axsOspfAreaAggregateEntry 4 }

axsOspfAreaAggregateMask OBJECT-TYPE
	SYNTAX  IpAddress
	ACCESS  read-only
	STATUS  mandatory
	DESCRIPTION
		"The Subnet Mask that pertains to the Net or Subnet."
	::= { axsOspfAreaAggregateEntry 5 }

axsOspfAreaAggregateStatus OBJECT-TYPE
	SYNTAX  INTEGER {
                                     active(1)
                        }
	ACCESS  read-only
	STATUS  mandatory
	DESCRIPTION
		"This variable displays the status of  the  entry.
		This entry value is only valid(1)."
	::= { axsOspfAreaAggregateEntry 6 }

axsOspfAreaAggregateEffect OBJECT-TYPE
	SYNTAX  INTEGER   {
				advertiseMatching (1),
				doNotAdvertiseMatching (2)
		    }
	ACCESS  read-only
	STATUS  mandatory
	DESCRIPTION
		"Subnets subsumed by ranges either trigger  the
		 advertisement  of  the indicated aggregate (ad-
		 vertiseMatching), or result in the subnet's not
		 being advertised at all outside the area."
	::= { axsOspfAreaAggregateEntry 7 }

axsOspfTrapControlTable OBJECT-TYPE
	SYNTAX  SEQUENCE OF AxsOspfTrapControlEntry
	ACCESS  not-accessible
	STATUS  mandatory
	DESCRIPTION
		"The table about trap information."
	::= { axsOspfTrap 1 }

axsOspfTrapControlEntry OBJECT-TYPE
	SYNTAX  AxsOspfTrapControlEntry
	ACCESS  not-accessible
	STATUS  mandatory
	DESCRIPTION
		"The Entry about trap information."
	INDEX { axsOspfTrapDomainNumber }
	::= { axsOspfTrapControlTable 1 }

	AxsOspfTrapControlEntry ::=
	SEQUENCE {
		axsOspfTrapDomainNumber
			INTEGER,
		axsOspfSetTrap	
			OCTET STRING,
		axsOspfConfigErrorType	
			INTEGER,
		axsOspfPacketType	
			INTEGER,
		axsOspfPacketSrc	
			IpAddress
                }

axsOspfTrapDomainNumber OBJECT-TYPE
	SYNTAX  INTEGER
	ACCESS  read-only
	STATUS  mandatory
	DESCRIPTION
		"axsOspfTrap domain number."
	::= { axsOspfTrapControlEntry 1 }

axsOspfSetTrap OBJECT-TYPE
       SYNTAX   OCTET STRING
       ACCESS   read-only
       STATUS   mandatory
       DESCRIPTION
           "A four-octet string serving as a bit  map  for
           the trap events defined by the OSPF traps. This
           object is used to enable and  disable  specific
           OSPF   traps   where  a  1  in  the  bit  field
           represents enabled.  The right-most bit  (least
           significant) represents trap 0."
       ::= { axsOspfTrapControlEntry 2 }

axsOspfConfigErrorType OBJECT-TYPE
       SYNTAX   INTEGER   {
                   badVersion (1),
                   areaMismatch (2),
                   unknownNbmaNbr (3), -- Router is Dr eligible
                   unknownVirtualNbr (4),
                   authTypeMismatch(5),
                   authFailure (6),
                   netMaskMismatch (7),
                   helloIntervalMismatch (8),
                   deadIntervalMismatch (9),
                   optionMismatch (10),
		   duplicateRouterId (12),
		   noError (13)}
       ACCESS   read-only
       STATUS   mandatory
       DESCRIPTION
           "Potential types  of  configuration  conflicts.
           Used  by the ospfConfigError and ospfConfigVir-
           tError traps."
       ::= { axsOspfTrapControlEntry 3 }

axsOspfPacketType OBJECT-TYPE
        SYNTAX   INTEGER   {
                    hello (1),
                    dbDescript (2),
                    lsReq (3),
                    lsUpdate (4),
                    lsAck (5), 
		    nullPacket (6)}
        ACCESS   read-only
        STATUS   mandatory
        DESCRIPTION
           "OSPF packet types."
   ::= { axsOspfTrapControlEntry 4 }

axsOspfPacketSrc OBJECT-TYPE
        SYNTAX   IpAddress
        ACCESS   read-only
        STATUS   mandatory
        DESCRIPTION
           "The IP address of an inbound packet that  can-
           not be identified by a neighbor instance."
       ::= { axsOspfTrapControlEntry 5 }

-- axsOspfv3

axsOspfv3GeneralTable OBJECT-TYPE
	SYNTAX  SEQUENCE OF AxsOspfv3GeneralEntry
	ACCESS  not-accessible
	STATUS  mandatory
	DESCRIPTION
		"The table which ospfv3 information is stored in."
	::= { axsOspfv3 1 }

axsOspfv3GeneralEntry OBJECT-TYPE
	SYNTAX  AxsOspfv3GeneralEntry
	ACCESS  not-accessible
	STATUS  mandatory
	DESCRIPTION
		"The list of the ospfv3 information."
	INDEX { axsOspfv3GeneralDomainNumber }
	::= { axsOspfv3GeneralTable 1 }

	AxsOspfv3GeneralEntry ::=
	SEQUENCE {
		axsOspfv3GeneralDomainNumber
			INTEGER,
		axsOspfv3RouterId
			RouterID,
		axsOspfv3AdminStat
			Status,
		axsOspfv3VersionNumber
			INTEGER,
		axsOspfv3AreaBdrRtrStatus
			TruthValue,
		axsOspfv3ASBdrRtrStatus
			TruthValue,
		axsOspfv3AsScopeLsaCount
			Gauge32,
		axsOspfv3AsScopeLsaCksumSum
			Integer32,
		axsOspfv3OriginateNewLsas
			Counter32,
		axsOspfv3RxNewLsas
			Counter32,
		axsOspfv3ExtAreaLsdbLimit
			Integer32,
		axsOspfv3MulticastExtensions
			Integer32,
		axsOspfv3DemandExtensions
			TruthValue,
		axsOspfv3TrafficEngineeringSupport
			TruthValue
		}

axsOspfv3GeneralDomainNumber OBJECT-TYPE
	SYNTAX  INTEGER
	ACCESS  read-only
	STATUS  mandatory
	DESCRIPTION
		"ospfv3 domain number."
	::= { axsOspfv3GeneralEntry 1 }

axsOspfv3RouterId OBJECT-TYPE
	SYNTAX  RouterID
	ACCESS  read-only
	STATUS  mandatory
	DESCRIPTION
		"A  32-bit  integer  uniquely  identifying  the
		router in the Autonomous System.
		By convention, to  ensure  uniqueness, this
		should  default  to  the  value  of  one of the
		router's IPv4 interface addresses if IPv4 is
		configured."
	::= { axsOspfv3GeneralEntry 2 }

axsOspfv3AdminStat OBJECT-TYPE
	SYNTAX  Status
	ACCESS  read-only
	STATUS  mandatory
	DESCRIPTION
		"The  administrative  status  of  axsOspfv3  in  the
		router.  The  value 'enabled' denotes that the
		axsOspfv3 Process is active on at least  one  inter-
		face;  'disabled'  disables  it  on  all inter-
		faces."
	::= { axsOspfv3GeneralEntry 3 }

axsOspfv3VersionNumber OBJECT-TYPE
	SYNTAX  INTEGER { version3 (3) }
	ACCESS  read-only
	STATUS  mandatory
	DESCRIPTION
		"The version number of OSPF for IPv6 is 3."
	::= { axsOspfv3GeneralEntry 4 }

axsOspfv3AreaBdrRtrStatus OBJECT-TYPE
	SYNTAX  TruthValue
	ACCESS  read-only
	STATUS  mandatory
	DESCRIPTION
		"A flag to note whether this router is an  area
		border router."
	REFERENCE
		"OSPF Version 2, Section 3 Splitting the AS into
		Areas"
	::= { axsOspfv3GeneralEntry 5 }

axsOspfv3ASBdrRtrStatus OBJECT-TYPE
	SYNTAX  TruthValue
	ACCESS  read-only
	STATUS  mandatory
	DESCRIPTION
		"A flag to note whether this router is  config-
		ured as an Autonomous System border router."
	REFERENCE
		"OSPF Version 2, Section 3.3  Classification  of
		routers"
	::= { axsOspfv3GeneralEntry 6 }

axsOspfv3AsScopeLsaCount OBJECT-TYPE
	SYNTAX  Gauge32
	ACCESS  read-only
	STATUS  mandatory
	DESCRIPTION
		"The number of AS-Scope (e.g. AS-External) link-state
		advertisements in the link-state database."
	::= { axsOspfv3GeneralEntry 7 }

axsOspfv3AsScopeLsaCksumSum OBJECT-TYPE
	SYNTAX  Integer32
	ACCESS  read-only
	STATUS  mandatory
	DESCRIPTION
		"The 32-bit unsigned sum of the LS checksums of
		the  AS-scoped link-state advertisements  con-
		tained in the link-state database. This sum
		can  be  used  to determine if there has been a
		change in a router's link state  database,  and
		to  compare  the  link-state  database  of  two
		routers."
	::= { axsOspfv3GeneralEntry 8 }

axsOspfv3OriginateNewLsas OBJECT-TYPE
	SYNTAX  Counter32
	ACCESS  read-only
	STATUS  mandatory
	DESCRIPTION
		"The number of  new  link-state  advertisements
		that  have been originated.  This number is in-
		cremented each time the router originates a new
		LSA."
	::= { axsOspfv3GeneralEntry 9 }

axsOspfv3RxNewLsas OBJECT-TYPE
	SYNTAX  Counter32
	ACCESS  read-only
	STATUS  mandatory
	DESCRIPTION
		"The number of  link-state  advertisements  re-
		ceived  determined  to  be  new instantiations.
		This number does not include  newer  instantia-
		tions  of self-originated link-state advertise-
		ments."
	::= { axsOspfv3GeneralEntry 10 }

axsOspfv3ExtAreaLsdbLimit OBJECT-TYPE
	SYNTAX  Integer32 (-1..'7FFFFFFF'h)
	ACCESS  read-only
	STATUS  mandatory
	DESCRIPTION
		"The  maximum   number   of   non-default   AS-
		external-LSAs entries that can be stored in the
		link-state database.  If the value is -1,  then
		there is no limit.
		When the number of non-default AS-external-LSAs
		in  a  router's  link-state  database  reaches
		axsOspfv3ExtAreaLsdbLimit, the router  enters  Overflow-
		State.  The   router  never  holds  more  than
		axsOspfv3ExtAreaLsdbLimit  non-default  AS-external-LSAs
		in  its  database. OspfExtAreaLsdbLimit MUST be set
		identically in all routers attached to the axsOspfv3
		backbone  and/or  any regular axsOspfv3 area. (i.e.,
		axsOspfv3 stub areas and NSSAs are excluded)."
	DEFVAL { -1 }
	::= { axsOspfv3GeneralEntry 11 }

axsOspfv3MulticastExtensions OBJECT-TYPE
	SYNTAX  Integer32
	ACCESS  read-only
	STATUS  mandatory
	DESCRIPTION
		"A Bit Mask indicating whether  the  router  is
		forwarding  IPv6  multicast datagrams
		based on the algorithms defined in  the  Multi-
		cast Extensions to OSPF.
		Bit 0, if set, indicates that  the  router  can
		forward  IPv6 multicast datagrams in the router's
		directly attached areas (called intra-area mul-
		ticast routing).
		Bit 1, if set, indicates that  the  router  can
		forward  IPv6  multicast  datagrams  between axsOspfv3
		areas (called inter-area multicast routing).
		Bit 2, if set, indicates that  the  router  can
		forward  IPv6  multicast  datagrams between Auto-
		nomous Systems (called inter-AS multicast rout-
		ing).
		Only certain combinations of bit  settings are
		allowed,  namely: 0 (no multicast forwarding is
		enabled), 1 (intra-area multicasting  only),  3
		(intra-area  and  inter-area  multicasting),  5
		(intra-area and inter-AS  multicasting)  and  7
		(multicasting  everywhere). By default, no mul-
		ticast forwarding is enabled."
	DEFVAL { 0 }
	::= { axsOspfv3GeneralEntry 12 }

axsOspfv3DemandExtensions OBJECT-TYPE
	SYNTAX  TruthValue
	ACCESS  read-only
	STATUS  mandatory
	DESCRIPTION
		"The router's support for demand routing."
	REFERENCE
		"OSPF Version 2, Appendix on Demand Routing"
	::= { axsOspfv3GeneralEntry 14 }

axsOspfv3TrafficEngineeringSupport OBJECT-TYPE
	SYNTAX  TruthValue
	ACCESS  read-only
	STATUS  mandatory
	DESCRIPTION
		"The router's support for traffic engineering
		extensions."
	::= { axsOspfv3GeneralEntry 15 }

--  The axsOspfv3 Area Data Structure contains information
--  regarding the various areas. The interfaces and
--  virtual links are configured as part of these areas.
--  Area 0.0.0.0, by definition, is the Backbone Area

axsOspfv3AreaTable OBJECT-TYPE
	SYNTAX  SEQUENCE OF AxsOspfv3AreaEntry
	ACCESS  not-accessible
	STATUS  mandatory
	DESCRIPTION
		"Information describing the configured  parame-
		ters  and cumulative statistics of the router's
		attached areas."
	REFERENCE
		"OSPF Version 2, Section 6  The Area Data Struc-
		ture"
	::= { axsOspfv3 2 }

axsOspfv3AreaEntry OBJECT-TYPE
	SYNTAX  AxsOspfv3AreaEntry
	ACCESS  not-accessible
	STATUS  mandatory
	DESCRIPTION
		"Information describing the configured  parame-
		ters  and  cumulative  statistics of one of the
		router's attached areas."
		INDEX { axsOspfv3AreaDomainNumber,
			axsOspfv3AreaId }
	::= { axsOspfv3AreaTable 1 }

	AxsOspfv3AreaEntry ::=
		SEQUENCE {
			axsOspfv3AreaDomainNumber
				INTEGER,
			axsOspfv3AreaId
				AreaID,
			axsOspfv3ImportAsExtern
				INTEGER,
			axsOspfv3SpfRuns
				Counter32,
			axsOspfv3AreaBdrRtrCount
				Gauge32,
			axsOspfv3AsBdrRtrCount
				Gauge32,
			axsOspfv3AreaScopeLsaCount
				Gauge32,
			axsOspfv3AreaScopeLsaCksumSum
				Integer32,
			axsOspfv3AreaSummary
				INTEGER,
			axsOspfv3AreaStatus
				RowStatus,
			axsOspfv3StubMetric
				BigMetric
		}

axsOspfv3AreaDomainNumber OBJECT-TYPE
	SYNTAX  INTEGER
	ACCESS  read-only
	STATUS  mandatory
	DESCRIPTION
		"ospfv3 domain number."
	::= { axsOspfv3AreaEntry 1 }

axsOspfv3AreaId OBJECT-TYPE
	SYNTAX  AreaID
	ACCESS  read-only
	STATUS  mandatory
	DESCRIPTION
		"A 32-bit integer uniquely identifying an area.
		Area ID 0.0.0.0 is used for the axsOspfv3 backbone."
	REFERENCE
		"OSPF Version 2, Appendix C.2 Area parameters"
	::= { axsOspfv3AreaEntry 2 }

axsOspfv3ImportAsExtern OBJECT-TYPE
	SYNTAX  INTEGER {
	importExternal (1),  -- normal area
	importNoExternal (2), -- stub area
	importNssa (3)        -- not-so-stubby-area
	}
	ACCESS  read-only
	STATUS  mandatory
	DESCRIPTION
		"Indicates whether an area is a Stub area, NSSA, or
		standard area. AS-scope LSAs are not imported into Stub
		Areas or NSSAs. NSSAs import AS-External data as Type-7
		LSAs which have Area-scope"
	REFERENCE
		"OSPF Version 2, Appendix C.2 Area parameters"
		DEFVAL { importExternal }
	::= { axsOspfv3AreaEntry 3 }

axsOspfv3SpfRuns OBJECT-TYPE
	SYNTAX  Counter32
	ACCESS  read-only
	STATUS  mandatory
	DESCRIPTION
		"The number of times that the intra-area  route
		table  has  been  calculated  using this area's
		link-state database.  This  is  typically  done
		using Dijkstra's algorithm."
	::= { axsOspfv3AreaEntry 4 }

axsOspfv3AreaBdrRtrCount OBJECT-TYPE
	SYNTAX  Gauge32
	ACCESS  read-only
	STATUS  mandatory
	DESCRIPTION
		"The total number of area border routers reach-
		able within this area. This is initially zero,
		and is calculated in each SPF Pass."
	::= { axsOspfv3AreaEntry 5 }

axsOspfv3AsBdrRtrCount OBJECT-TYPE
	SYNTAX  Gauge32
	ACCESS  read-only
	STATUS  mandatory
	DESCRIPTION
		"The total number of Autonomous  System  border
		routers  reachable  within  this area.  This is
		initially zero, and is calculated in  each  SPF
		Pass."
	::= { axsOspfv3AreaEntry 6 }

axsOspfv3AreaScopeLsaCount OBJECT-TYPE
	SYNTAX  Gauge32
	ACCESS  read-only
	STATUS  mandatory
	DESCRIPTION
	"The total number of Area-Scope link-state
	advertisements in  this  area's link-state
	database."
	::= { axsOspfv3AreaEntry 7 }

axsOspfv3AreaScopeLsaCksumSum OBJECT-TYPE
	SYNTAX  Integer32
	ACCESS  read-only
	STATUS  mandatory
	DESCRIPTION
		"The 32-bit unsigned sum of the Area-Scope link-state
		advertisements'  LS  checksums  contained in this
		area's link-state database.  The sum can be used
		to determine if  there  has been  a  change  in a
		router's link state database, and to compare the
		link-state database of two routers."
		DEFVAL  { 0 }
	::= { axsOspfv3AreaEntry 8 }

axsOspfv3AreaSummary OBJECT-TYPE
	SYNTAX  INTEGER {
		noAreaSummary (1),
		sendAreaSummary (2)
	}
	ACCESS  read-only
	STATUS  mandatory
	DESCRIPTION
		"The variable axsOspfv3AreaSummary controls the  im-
		port  of  summary LSAs into stub areas.  It has
		no effect on other areas.
		If it is noAreaSummary, the router will neither
		originate  nor  propagate summary LSAs into the
		stub area.  It will rely entirely  on  its  de-
		fault route.
		If it is sendAreaSummary, the router will  both
		summarize and propagate summary LSAs."
		DEFVAL  { noAreaSummary }
	::= { axsOspfv3AreaEntry 9 }

axsOspfv3AreaStatus OBJECT-TYPE
	SYNTAX  RowStatus
	ACCESS  read-only
	STATUS  mandatory
	DESCRIPTION
		"This variable displays the status of  the  en-
		try.  Setting it to 'invalid' has the effect of
		rendering it inoperative.  The internal  effect
		(row removal) is implementation dependent."
	::= { axsOspfv3AreaEntry 10 }

axsOspfv3StubMetric OBJECT-TYPE
	SYNTAX  BigMetric
--	ACCESS  read-create
	ACCESS  read-only
	STATUS  mandatory
	DESCRIPTION
		"The metric value advertised for the default route
		into Stub and NSSA areas."
	::= { axsOspfv3AreaEntry 11 }

--	axsOspfv3 AS-Scope Link State Database
--		The Link State Database contains the AS-Scope Link State
--		Advertisements from throughout the areas that the
--		device is attached to.

axsOspfv3AsLsdbTable OBJECT-TYPE
	SYNTAX  SEQUENCE OF AxsOspfv3AsLsdbEntry
	ACCESS  not-accessible
	STATUS  mandatory
	DESCRIPTION
		"The axsOspfv3 Process's AS-Scope Link State Database."
	::= { axsOspfv3 3 }

axsOspfv3AsLsdbEntry OBJECT-TYPE
	SYNTAX  AxsOspfv3AsLsdbEntry
	ACCESS  not-accessible
	STATUS  mandatory
	DESCRIPTION
	"A single AS-Scope Link State Advertisement."
	INDEX { axsOspfv3AsLsdbDomainNumber,
			axsOspfv3AsLsdbType,
			axsOspfv3AsLsdbRouterId,
			axsOspfv3AsLsdbLsid }
	::= { axsOspfv3AsLsdbTable 1 }

	AxsOspfv3AsLsdbEntry ::=
		SEQUENCE {
			axsOspfv3AsLsdbDomainNumber
				INTEGER,
			axsOspfv3AsLsdbType
				INTEGER,
			axsOspfv3AsLsdbRouterId
				RouterID,
			axsOspfv3AsLsdbLsid
				IpAddress,
			axsOspfv3AsLsdbSequence
				Integer32,
			axsOspfv3AsLsdbAge
				Integer32,
			axsOspfv3AsLsdbChecksum
				Integer32,
			axsOspfv3AsLsdbAdvertisement
				OCTET STRING
			}

axsOspfv3AsLsdbDomainNumber OBJECT-TYPE
	SYNTAX  INTEGER
	ACCESS  read-only
	STATUS  mandatory
	DESCRIPTION
		"ospfv3 domain number."
	::= { axsOspfv3AsLsdbEntry 1 }

axsOspfv3AsLsdbType OBJECT-TYPE
	SYNTAX  INTEGER {
		asExternalLink (16389)  -- 0x4005
	}
	ACCESS  read-only
	STATUS  mandatory
	DESCRIPTION
		"The type  of  the  link  state  advertisement.
		Each  link state type has a separate advertise-
		ment format. Unrecognized AS-Scope LSAs with the
		U-bit set are also store in this database."
	::= { axsOspfv3AsLsdbEntry 2 }

axsOspfv3AsLsdbRouterId OBJECT-TYPE
	SYNTAX  RouterID
	ACCESS  read-only
	STATUS  mandatory
	DESCRIPTION
		"The 32 bit number that uniquely identifies the
		originating router in the Autonomous System."
	REFERENCE
		"OSPF Version 2, Appendix C.1 Global parameters"
	::= { axsOspfv3AsLsdbEntry 3 }

axsOspfv3AsLsdbLsid OBJECT-TYPE
	SYNTAX  IpAddress
	ACCESS  read-only
	STATUS  mandatory
	DESCRIPTION
	"The Link State ID is an LS Type Specific field
	containing either a Router ID or a unique identifier;
	it identifies the piece of the  routing  domain
	that is being described by the advertisement.
	In contrast to OSPF for IPv4, the LSID has no
	addressing semantics."
	::= { axsOspfv3AsLsdbEntry 4 }

--  Note that the OSPF Sequence Number is a 32 bit signed
--  integer.  It starts with the value '80000001'h,
--  or -'7FFFFFFF'h, and increments until '7FFFFFFF'h
--  Thus, a typical sequence number will be very negative.

axsOspfv3AsLsdbSequence OBJECT-TYPE
	SYNTAX  Integer32
	ACCESS  read-only
	STATUS  mandatory
	DESCRIPTION
		"The sequence number field is a  signed  32-bit
		integer.   It  is used to detect old and dupli-
		cate link state advertisements.  The  space  of
		sequence  numbers  is  linearly  ordered.  The
		larger the sequence number the more recent  the
		advertisement."
	REFERENCE
		"OSPF Version  2,  Section  12.1.6  LS  sequence
		number"
	::= { axsOspfv3AsLsdbEntry 5 }

axsOspfv3AsLsdbAge OBJECT-TYPE
	SYNTAX  Integer32  -- Should be 0..MaxAge
	ACCESS  read-only
	STATUS  mandatory
	DESCRIPTION
		"This field is the age of the link state adver-
		tisement in seconds."
	REFERENCE
		"OSPF Version 2, Section 12.1.1 LS age"
	::= { axsOspfv3AsLsdbEntry 6 }

axsOspfv3AsLsdbChecksum OBJECT-TYPE
	SYNTAX  Integer32
	ACCESS  read-only
	STATUS  mandatory
	DESCRIPTION
		"This field is the  checksum  of  the  complete
		contents  of  the  advertisement, excepting the
		age field.  The age field is excepted  so  that
		an  advertisement's  age  can  be  incremented
		without updating the  checksum.  The  checksum
		used  is  the same that is used for ISO connec-
		tionless datagrams; it is commonly referred  to
		as the Fletcher checksum."
	REFERENCE
		"OSPF Version 2, Section 12.1.7 LS checksum"
	::= { axsOspfv3AsLsdbEntry 7 }

axsOspfv3AsLsdbAdvertisement OBJECT-TYPE
	SYNTAX  OCTET STRING (SIZE (1..65535))
	ACCESS  read-only
	STATUS  mandatory
	DESCRIPTION
	"The entire Link State Advertisement, including
	its header."
	::= { axsOspfv3AsLsdbEntry 8 }

--  axsOspfv3 Area-Scope Link State Database
--  The Link State Database contains the Area-Scope Link State
--  Advertisements from throughout the area that the
--  device is attached to.

axsOspfv3AreaLsdbTable OBJECT-TYPE
	SYNTAX  SEQUENCE OF AxsOspfv3AreaLsdbEntry
	ACCESS  not-accessible
	STATUS  mandatory
	DESCRIPTION
		"The axsOspfv3 Process's Area-Scope Link State Database."
	::= { axsOspfv3 4 }

axsOspfv3AreaLsdbEntry OBJECT-TYPE
	SYNTAX  AxsOspfv3AreaLsdbEntry
	ACCESS  not-accessible
	STATUS  mandatory
	DESCRIPTION
		"A single Area-Scope Link State Advertisement."
	INDEX { axsOspfv3AreaLsdbDomainNumber,
		axsOspfv3AreaLsdbAreaId,
		axsOspfv3AreaLsdbType,
		axsOspfv3AreaLsdbRouterId,
		axsOspfv3AreaLsdbLsid }
	::= { axsOspfv3AreaLsdbTable 1 }

	AxsOspfv3AreaLsdbEntry ::=
		SEQUENCE {
		axsOspfv3AreaLsdbDomainNumber
			INTEGER,
		axsOspfv3AreaLsdbAreaId
			AreaID,
		axsOspfv3AreaLsdbType
			INTEGER,
		axsOspfv3AreaLsdbRouterId
			RouterID,
		axsOspfv3AreaLsdbLsid
			IpAddress,
		axsOspfv3AreaLsdbSequence
			Integer32,
		axsOspfv3AreaLsdbAge
			Integer32,
		axsOspfv3AreaLsdbChecksum
			Integer32,
		axsOspfv3AreaLsdbAdvertisement
			OCTET STRING
	}

axsOspfv3AreaLsdbDomainNumber OBJECT-TYPE
	SYNTAX  INTEGER
	ACCESS  read-only
	STATUS  mandatory
	DESCRIPTION
		"ospfv3 domain number."
	::= { axsOspfv3AreaLsdbEntry 1 }

axsOspfv3AreaLsdbAreaId OBJECT-TYPE
	SYNTAX  AreaID
	ACCESS  read-only
	STATUS  mandatory
	DESCRIPTION
		"The 32 bit identifier of the Area from which the
		LSA was received."
	REFERENCE
		"OSPF Version 2, Appendix C.2 Area parameters."
	::= { axsOspfv3AreaLsdbEntry 2 }

axsOspfv3AreaLsdbType OBJECT-TYPE
	SYNTAX  INTEGER {
		routerLsa          (8193),  -- 0x2001
		networkLsa         (8194),  -- 0x2002
		interAreaPrefixLsa (8195),  -- 0x2003
		interAreaRouterLsa (8196),  -- 0x2004
		groupMembershipLsa (8198),  -- 0x2006
		nssaExternalLsa    (8199),  -- 0x2007
		intraAreaPrefixLsa (8201)   -- 0x2009
	}
	ACCESS  read-only
	STATUS  mandatory
	DESCRIPTION
		"The type  of  the  link  state  advertisement.
		Each  link state type has a separate advertise-
		ment format. Unrecognized Area-Scope LSAs with
		the U-bit set are also stored in this database."
	::= { axsOspfv3AreaLsdbEntry 3 }

axsOspfv3AreaLsdbRouterId OBJECT-TYPE
	SYNTAX  RouterID
	ACCESS  read-only
	STATUS  mandatory
	DESCRIPTION
		"The 32 bit number that uniquely identifies the
		originating router in the Autonomous System."
	REFERENCE
		"OSPF Version 2, Appendix C.1 Global parameters"
	::= { axsOspfv3AreaLsdbEntry 4 }

axsOspfv3AreaLsdbLsid OBJECT-TYPE
	SYNTAX  IpAddress
	ACCESS  read-only
	STATUS  mandatory
	DESCRIPTION
		"The Link State ID is an LS Type Specific field
		containing either a Router ID or a unique identifier;
		it identifies the piece of the  routing  domain
		that is being described by the advertisement.
		In contrast to OSPF for IPv4, the LSID has no
		addressing semantics."
	::= { axsOspfv3AreaLsdbEntry 5 }

--  Note that the OSPF Sequence Number is a 32 bit signed
--  integer.  It starts with the value '80000001'h,
--  or -'7FFFFFFF'h, and increments until '7FFFFFFF'h
--  Thus, a typical sequence number will be very negative.

axsOspfv3AreaLsdbSequence OBJECT-TYPE
	SYNTAX  Integer32
	ACCESS  read-only
	STATUS  mandatory
	DESCRIPTION
		"The sequence number field is a  signed  32-bit
		integer.   It  is used to detect old and dupli-
		cate link state advertisements.  The  space  of
		sequence  numbers  is  linearly  ordered.   The
		larger the sequence number the more recent  the
		advertisement."
	REFERENCE
		"OSPF Version  2,  Section  12.1.6  LS  sequence
		number"
	::= { axsOspfv3AreaLsdbEntry 6 }

axsOspfv3AreaLsdbAge OBJECT-TYPE
	SYNTAX  Integer32  -- Should be 0..MaxAge
	ACCESS  read-only
	STATUS  mandatory
	DESCRIPTION
		"This field is the age of the link state adver-
		tisement in seconds."
	REFERENCE
		"OSPF Version 2, Section 12.1.1 LS age"
	::= { axsOspfv3AreaLsdbEntry 7 }

axsOspfv3AreaLsdbChecksum OBJECT-TYPE
	SYNTAX  Integer32
	ACCESS  read-only
	STATUS  mandatory
	DESCRIPTION
		"This field is the  checksum  of  the  complete
		contents  of  the  advertisement, excepting the
		age field.  The age field is excepted  so  that
		an  advertisement's  age  can  be  incremented
		without updating the  checksum.  The  checksum
		used  is  the same that is used for ISO connec-
		tionless datagrams; it is commonly referred  to
		as the Fletcher checksum."
	REFERENCE
		"OSPF Version 2, Section 12.1.7 LS checksum"
	::= { axsOspfv3AreaLsdbEntry 8 }

axsOspfv3AreaLsdbAdvertisement OBJECT-TYPE
	SYNTAX  OCTET STRING (SIZE (1..65535))
	ACCESS  read-only
	STATUS  mandatory
	DESCRIPTION
		"The entire Link State Advertisement, including
		its header."
	::= { axsOspfv3AreaLsdbEntry 9 }

--  axsOspfv3 Link-Scope Link State Database
--    The Link State Database contains the Link-Scope Link State
--    Advertisements from the links that the
--    device is attached to.

axsOspfv3LinkLsdbTable OBJECT-TYPE
	SYNTAX  SEQUENCE OF AxsOspfv3LinkLsdbEntry
	ACCESS  not-accessible
	STATUS  mandatory
	DESCRIPTION
		"The axsOspfv3 Process's Link-Scope Link State Database."
	::= { axsOspfv3 5 }

axsOspfv3LinkLsdbEntry OBJECT-TYPE
	SYNTAX  AxsOspfv3LinkLsdbEntry
	ACCESS  not-accessible
	STATUS  mandatory
	DESCRIPTION
		"A single Link-Scope Link State Advertisement."
	INDEX { axsOspfv3LinkLsdbDomainNumber,
		axsOspfv3LinkLsdbIfIndex,
		axsOspfv3LinkLsdbType,
		axsOspfv3LinkLsdbRouterId,
		axsOspfv3LinkLsdbLsid }
	::= { axsOspfv3LinkLsdbTable 1 }

	AxsOspfv3LinkLsdbEntry ::=
		SEQUENCE {
			axsOspfv3LinkLsdbDomainNumber
				INTEGER,
			axsOspfv3LinkLsdbIfIndex
				Ipv6IfIndex,
			axsOspfv3LinkLsdbType
				INTEGER,
			axsOspfv3LinkLsdbRouterId
				RouterID,
			axsOspfv3LinkLsdbLsid
				IpAddress,
			axsOspfv3LinkLsdbSequence
				Integer32,
			axsOspfv3LinkLsdbAge
				Integer32,
			axsOspfv3LinkLsdbChecksum
				Integer32,
			axsOspfv3LinkLsdbAdvertisement
				OCTET STRING
		}

axsOspfv3LinkLsdbDomainNumber OBJECT-TYPE
	SYNTAX  INTEGER
	ACCESS  read-only
	STATUS  mandatory
	DESCRIPTION
		"ospfv3 domain number."
	::= { axsOspfv3LinkLsdbEntry 1 }

axsOspfv3LinkLsdbIfIndex OBJECT-TYPE
	SYNTAX  Ipv6IfIndex
	ACCESS  read-only
	STATUS  mandatory
	DESCRIPTION
		"The identifier of the link from which the LSA
		was received."
	REFERENCE
		"OSPF Version 2, Appendix C.2 Area parameters"
	::= { axsOspfv3LinkLsdbEntry 2 }

axsOspfv3LinkLsdbType OBJECT-TYPE
	SYNTAX  INTEGER  {
		linkLsa (8)  -- 0x0008
	}
	ACCESS  read-only
	STATUS  mandatory
	DESCRIPTION
		"The type  of  the  link  state  advertisement.
		Each  link state type has a separate advertise-
		ment format. Unrecognized Link-Scope LSAs with
		the U-bit set are also stored in this database."
	::= { axsOspfv3LinkLsdbEntry 3 }

axsOspfv3LinkLsdbRouterId OBJECT-TYPE
	SYNTAX  RouterID
	ACCESS  read-only
	STATUS  mandatory
	DESCRIPTION
		"The 32 bit number that uniquely identifies the
		originating router in the Autonomous System."
	REFERENCE
		"OSPF Version 2, Appendix C.1 Global parameters"
	::= { axsOspfv3LinkLsdbEntry 4 }

axsOspfv3LinkLsdbLsid OBJECT-TYPE
	SYNTAX  IpAddress
	ACCESS  read-only
	STATUS  mandatory
	DESCRIPTION
		"The Link State ID is an LS Type Specific field
		containing either a Router ID or a unique identifier;
		it identifies the piece of the  routing  domain
		that is being described by the advertisement.
		In contrast to OSPF for IPv4, the LSID has no
		addressing semantics."
	::= { axsOspfv3LinkLsdbEntry 5 }

--  Note that the OSPF Sequence Number is a 32 bit signed
--  integer.  It starts with the value '80000001'h,
--  or -'7FFFFFFF'h, and increments until '7FFFFFFF'h
--  Thus, a typical sequence number will be very negative.

axsOspfv3LinkLsdbSequence OBJECT-TYPE
	SYNTAX  Integer32
	ACCESS  read-only
	STATUS  mandatory
	DESCRIPTION
		"The sequence number field is a  signed  32-bit
		integer.   It  is used to detect old and dupli-
		cate link state advertisements.  The  space  of
		sequence  numbers  is  linearly  ordered.  The
		larger the sequence number the more recent  the
		advertisement."
	REFERENCE
		"OSPF Version  2,  Section  12.1.6  LS  sequence
		number"
	::= { axsOspfv3LinkLsdbEntry 6 }

axsOspfv3LinkLsdbAge OBJECT-TYPE
	SYNTAX  Integer32  -- Should be 0..MaxAge
	ACCESS  read-only
	STATUS   mandatory
	DESCRIPTION
		"This field is the age of the link state adver-
		tisement in seconds."
	REFERENCE
		"OSPF Version 2, Section 12.1.1 LS age"
	::= { axsOspfv3LinkLsdbEntry 7 }

axsOspfv3LinkLsdbChecksum OBJECT-TYPE
	SYNTAX  Integer32
	ACCESS  read-only
	STATUS  mandatory
	DESCRIPTION
		"This field is the  checksum  of  the  complete
		contents  of  the  advertisement, excepting the
		age field.  The age field is excepted  so  that
		an  advertisement's  age  can  be  incremented
		without updating the  checksum.  The  checksum
		used  is  the same that is used for ISO connec-
		tionless datagrams; it is commonly referred  to
		as the Fletcher checksum."
	REFERENCE
		"OSPF Version 2, Section 12.1.7 LS checksum"
	::= { axsOspfv3LinkLsdbEntry 8 }

axsOspfv3LinkLsdbAdvertisement OBJECT-TYPE
	SYNTAX  OCTET STRING (SIZE (1..65535))
	ACCESS  read-only
	STATUS  mandatory
	DESCRIPTION
		"The entire Link State Advertisement, including
		its header."
	::= { axsOspfv3LinkLsdbEntry 9 }

--  OSPF Host Table
--    The Host/Metric Table indicates what hosts are directly
--    attached to the Router, and what metrics and types of
--    service should be advertised for them.
--  axsOspfv3 Interface Table

axsOspfv3IfTable OBJECT-TYPE
	SYNTAX  SEQUENCE OF AxsOspfv3IfEntry
	ACCESS  not-accessible
	STATUS  mandatory
	DESCRIPTION
		"The axsOspfv3 Interface Table describes the  inter-
		faces from the viewpoint of axsOspfv3."
	REFERENCE
		"OSPF Version 2, Appendix C.3  Router  interface
		parameters"
	::= { axsOspfv3 7 }

axsOspfv3IfEntry OBJECT-TYPE
	SYNTAX  AxsOspfv3IfEntry
	ACCESS  not-accessible
	STATUS  mandatory
	DESCRIPTION
		"The axsOspfv3 Interface Entry describes one  inter-
		face from the viewpoint of axsOspfv3."
	INDEX { axsOspfv3IfDomainNumber,
		axsOspfv3IfIndex }
	::= { axsOspfv3IfTable 1 }

	AxsOspfv3IfEntry ::=
		SEQUENCE {
			axsOspfv3IfDomainNumber
				INTEGER,
			axsOspfv3IfIndex
				Ipv6IfIndex,
			axsOspfv3IfAreaId
				AreaID,
			axsOspfv3IfType
				INTEGER,
			axsOspfv3IfAdminStat
				Status,
			axsOspfv3IfRtrPriority
				DesignatedRouterPriority,
			axsOspfv3IfTransitDelay
				UpToMaxAge,
			axsOspfv3IfRetransInterval
				UpToMaxAge,
			axsOspfv3IfHelloInterval
				HelloRange,
			axsOspfv3IfRtrDeadInterval
				PositiveInteger,
			axsOspfv3IfPollInterval
				PositiveInteger,
			axsOspfv3IfState
				INTEGER,
			axsOspfv3IfDesignatedRouter
				RouterID,
			axsOspfv3IfBackupDesignatedRouter
				RouterID,
			axsOspfv3IfEvents
				Counter32,
			axsOspfv3IfStatus
				RowStatus,
			axsOspfv3IfMulticastForwarding
				INTEGER,
			axsOspfv3IfDemand
				TruthValue,
			axsOspfv3IfMetricValue
				Metric,
			axsOspfv3IfLinkScopeLsaCount
				Gauge32,
			axsOspfv3IfLinkLsaCksumSum
				Integer32,
			axsOspfv3IfInstId
				Integer32
			}

axsOspfv3IfDomainNumber OBJECT-TYPE
	SYNTAX  INTEGER
	ACCESS  read-only
	STATUS  mandatory
	DESCRIPTION
		"ospfv3 domain number."
	::= { axsOspfv3IfEntry 1 }

axsOspfv3IfIndex OBJECT-TYPE
	SYNTAX  Ipv6IfIndex
	ACCESS  read-only
	STATUS  mandatory
	DESCRIPTION
		"The interface index of this axsOspfv3 interface.
		It corresponds to the interface index of the
		Ipv6 interface on which axsOspfv3 is configured."
	::= { axsOspfv3IfEntry 2 }

axsOspfv3IfAreaId OBJECT-TYPE
	SYNTAX  AreaID
	ACCESS  read-only
	STATUS  mandatory
	DESCRIPTION
		"A 32-bit integer uniquely identifying the area
		to  which  the  interface  connects.   Area  ID
		0.0.0.0 is used for the axsOspfv3 backbone."
	DEFVAL   { '00000000'H }  -- 0.0.0.0
	::= { axsOspfv3IfEntry 3 }

axsOspfv3IfType OBJECT-TYPE
	SYNTAX  INTEGER {
		broadcast (1),
		nbma (2),
		pointToPoint (3),
		pointToMultipoint (5)
	}
	ACCESS  read-only
	STATUS  mandatory
	DESCRIPTION
		"The axsOspfv3 interface type."
	::= { axsOspfv3IfEntry 4 }

axsOspfv3IfAdminStat OBJECT-TYPE
	SYNTAX  Status
	ACCESS  read-only
	STATUS  mandatory
	DESCRIPTION
		"The axsOspfv3 interface's  administrative  status.
		The  value formed on the interface, and the in-
		terface will be advertised as an internal route
		to  some  area.  The  value 'disabled' denotes
		that the interface is external to axsOspfv3."
	DEFVAL { enabled }
	::= { axsOspfv3IfEntry 5 }

axsOspfv3IfRtrPriority OBJECT-TYPE
	SYNTAX  DesignatedRouterPriority
	ACCESS  read-only
	STATUS  mandatory
	DESCRIPTION
		"The  priority  of  this  interface.   Used  in
		multi-access  networks,  this  field is used in
		the designated router election algorithm.  The
		value 0 signifies that the router is not eligi-
		ble to become the  designated  router  on  this
		particular  network.   In the event of a tie in
		this value, routers will use their Router ID as
		a tie breaker."
	DEFVAL { 1 }
	::= { axsOspfv3IfEntry 6 }

axsOspfv3IfTransitDelay OBJECT-TYPE
	SYNTAX  UpToMaxAge
	ACCESS  read-only
	STATUS  mandatory
	DESCRIPTION
		"The estimated number of seconds  it  takes  to
		transmit  a  link state update packet over this
		interface."
	DEFVAL { 1 }
	::= { axsOspfv3IfEntry 7 }

axsOspfv3IfRetransInterval OBJECT-TYPE
	SYNTAX  UpToMaxAge
	ACCESS  read-only
	STATUS  mandatory
	DESCRIPTION
		"The number of seconds between  link-state  ad-
		vertisement  retransmissions,  for  adjacencies
		belonging to this  interface.  This  value  is
		also used when retransmitting database descrip-
		tion and link-state request packets."
	DEFVAL { 5 }
	::= { axsOspfv3IfEntry 8 }

axsOspfv3IfHelloInterval OBJECT-TYPE
	SYNTAX  HelloRange
	ACCESS  read-only
	STATUS  mandatory
	DESCRIPTION
		"The length of time, in  seconds,  between  the
		Hello  packets that the router sends on the in-
		terface.  This value must be the same  for  all
		routers attached to a common network."
	DEFVAL { 10 }
	::= { axsOspfv3IfEntry 9 }

axsOspfv3IfRtrDeadInterval OBJECT-TYPE
	SYNTAX  PositiveInteger
	ACCESS  read-only
	STATUS  mandatory
	DESCRIPTION
		"The number of seconds that  a  router's  Hello
		packets  have  not been seen before it's neigh-
		bors declare the router down.  This  should  be
		some  multiple  of  the  Hello  interval.  This
		value must be the same for all routers attached
		to a common network."
	DEFVAL { 40 }
	::= { axsOspfv3IfEntry 10 }

axsOspfv3IfPollInterval OBJECT-TYPE
	SYNTAX  PositiveInteger
	ACCESS  read-only
	STATUS  mandatory
	DESCRIPTION
		"The larger time interval, in seconds,  between
		the  Hello  packets  sent  to  an inactive non-
		broadcast multi- access neighbor."
	DEFVAL { 120 }
	::= { axsOspfv3IfEntry 11 }

axsOspfv3IfState OBJECT-TYPE
	SYNTAX  INTEGER {
		down (1),
		loopback (2),
		waiting (3),
		pointToPoint (4),
		designatedRouter (5),
		backupDesignatedRouter (6),
		otherDesignatedRouter (7)
	}
	ACCESS  read-only
	STATUS  mandatory
	DESCRIPTION
		"The axsOspfv3 Interface State."
	DEFVAL { down }
	::= { axsOspfv3IfEntry 12 }

axsOspfv3IfDesignatedRouter OBJECT-TYPE
	SYNTAX  RouterID
	ACCESS  read-only
	STATUS  mandatory
	DESCRIPTION
		"The Router ID of the Designated Router."
	DEFVAL  { '00000000'H }  -- 0.0.0.0
	::= { axsOspfv3IfEntry 13 }

axsOspfv3IfBackupDesignatedRouter OBJECT-TYPE
	SYNTAX  RouterID
	ACCESS  read-only
	STATUS  mandatory
	DESCRIPTION
		"The  Router ID of  the  Backup   Designated
		Router."
	DEFVAL  { '00000000'H }  -- 0.0.0.0
	::= { axsOspfv3IfEntry 15 }

axsOspfv3IfEvents OBJECT-TYPE
	SYNTAX  Counter32
	ACCESS  read-only
	STATUS  mandatory
	DESCRIPTION
		"The number of times this  OSPF  interface  has
		changed its state, or an error has occurred."
	::= { axsOspfv3IfEntry 16 }

axsOspfv3IfStatus OBJECT-TYPE
	SYNTAX  RowStatus
	ACCESS  read-only
	STATUS  mandatory
	DESCRIPTION
		"This variable displays the status of  the  en-
		try.  Setting it to 'invalid' has the effect of
		rendering it inoperative.  The internal  effect
		(row removal) is implementation dependent."
	::= { axsOspfv3IfEntry 18 }

axsOspfv3IfMulticastForwarding OBJECT-TYPE
	SYNTAX  INTEGER {
		blocked (1),   -- no multicast forwarding
		multicast (2), -- using multicast address
		unicast (3)    -- to each axsOspfv3 neighbor
		}
	ACCESS  read-only
	STATUS  mandatory
	DESCRIPTION
		"The way multicasts should  forwarded  on  this
		interface;  not  forwarded,  forwarded  as data
		link multicasts, or forwarded as data link uni-
		casts.  Data link multicasting is not meaning-
		ful on point to point and NBMA interfaces, and
		setting axsOspfv3MulticastForwarding to 0 effective-
		ly disables all multicast forwarding."
	DEFVAL { blocked }
	::= { axsOspfv3IfEntry 19 }

axsOspfv3IfDemand OBJECT-TYPE
	SYNTAX  TruthValue
	ACCESS  read-only
	STATUS  mandatory
	DESCRIPTION
		"Indicates whether Demand axsOspfv3 procedures (hel-
		lo supression to FULL neighbors and setting the
		DoNotAge flag on proogated LSAs) should be per-
		formed on this interface."
	DEFVAL { false }
	::= { axsOspfv3IfEntry 20 }

axsOspfv3IfMetricValue OBJECT-TYPE
	SYNTAX  Metric
	ACCESS  read-only
	STATUS  mandatory
	DESCRIPTION
		"The metric assigned to this interface.
		The default value of the Metric is
		10^8 / ifSpeed."
	::= { axsOspfv3IfEntry 21 }

axsOspfv3IfLinkScopeLsaCount OBJECT-TYPE
	SYNTAX  Gauge32
	ACCESS  read-only
	STATUS  mandatory
	DESCRIPTION
		"The total number of Link-Scope link-state
		advertisements in  this  link's link-state database."
	::= { axsOspfv3IfEntry 22 }

axsOspfv3IfLinkLsaCksumSum OBJECT-TYPE
	SYNTAX  Integer32
	ACCESS  read-only
	STATUS  mandatory
	DESCRIPTION
		"The 32-bit unsigned sum of the Link-Scope link-state
		advertisements'  LS  checksums  contained in this
		link's link-state database.  The sum can be used
		to determine if  there  has been  a  change  in a
		router's link state database, and to compare the
		link-state database of two routers."
	DEFVAL  { 0 }
	::= { axsOspfv3IfEntry 23 }

axsOspfv3IfInstId OBJECT-TYPE
	SYNTAX  Integer32
	ACCESS  read-only
	STATUS  mandatory
	DESCRIPTION
		"Enables multiple instances of axsOspfv3 to be run over
		a single link. Each protocol instance would be assigned
		a separate ID. This ID has local link significance
		only."
	DEFVAL  { 0 }
	::= { axsOspfv3IfEntry 24 }

--  axsOspfv3 Virtual Interface Table
--    The Virtual Interface Table describes the virtual
--    links that the axsOspfv3 Process is configured to
--    carry on.

axsOspfv3VirtIfTable OBJECT-TYPE
	SYNTAX  SEQUENCE OF AxsOspfv3VirtIfEntry
	ACCESS  not-accessible
	STATUS  mandatory
	DESCRIPTION
		"Information about this router's virtual inter-
		faces."
	REFERENCE
		"OSPF Version  2,  Appendix  C.4   Virtual  link
		parameters"
	::= { axsOspfv3 8 }

axsOspfv3VirtIfEntry OBJECT-TYPE
	SYNTAX  AxsOspfv3VirtIfEntry
	ACCESS  not-accessible
	STATUS  mandatory
	DESCRIPTION
		"Information about a single Virtual Interface."
		INDEX { axsOspfv3VirtIfDomainNumber, axsOspfv3VirtIfAreaId, axsOspfv3VirtIfNeighbor }
	::= { axsOspfv3VirtIfTable 1 }

	AxsOspfv3VirtIfEntry ::=
		SEQUENCE {
			axsOspfv3VirtIfDomainNumber
				INTEGER,
			axsOspfv3VirtIfAreaId
				AreaID,
			axsOspfv3VirtIfNeighbor
				RouterID,
			axsOspfv3VirtIfIndex
				Ipv6IfIndex,
			axsOspfv3VirtIfTransitDelay
				UpToMaxAge,
			axsOspfv3VirtIfRetransInterval
				UpToMaxAge,
			axsOspfv3VirtIfHelloInterval
				HelloRange,
			axsOspfv3VirtIfRtrDeadInterval
				PositiveInteger,
			axsOspfv3VirtIfState
				INTEGER,
			axsOspfv3VirtIfEvents
				Counter32,
			axsOspfv3VirtIfStatus
				RowStatus,
			axsOspfv3VirtIfLinkScopeLsaCount
				Gauge32,
			axsOspfv3VirtIfLinkLsaCksumSum
				Integer32
			}

axsOspfv3VirtIfDomainNumber OBJECT-TYPE
	SYNTAX  INTEGER
	ACCESS  read-only
	STATUS  mandatory
	DESCRIPTION
		"ospfv3 domain number."
	::= { axsOspfv3VirtIfEntry 1 }

axsOspfv3VirtIfAreaId OBJECT-TYPE
	SYNTAX  AreaID
	ACCESS  read-only
	STATUS  mandatory
	DESCRIPTION
		"The  Transit  Area  that  the   Virtual   Link
		traverses.  By definition, this is not 0.0.0.0"
	::= { axsOspfv3VirtIfEntry 2 }

axsOspfv3VirtIfNeighbor OBJECT-TYPE
	SYNTAX  RouterID
	ACCESS  read-only
	STATUS mandatory
	DESCRIPTION
		"The Router ID of the Virtual Neighbor."
	::= { axsOspfv3VirtIfEntry 3 }

axsOspfv3VirtIfIndex OBJECT-TYPE
	SYNTAX  Ipv6IfIndex
	ACCESS  read-only
	STATUS  mandatory
	DESCRIPTION
		"The interface index of this axsOspfv3 virtual interface.
		It must be unique among all the interface indices
		on the router."
		::= { axsOspfv3VirtIfEntry 4 }

axsOspfv3VirtIfTransitDelay OBJECT-TYPE
	SYNTAX  UpToMaxAge
	ACCESS  read-only
	STATUS  mandatory
	DESCRIPTION
		"The estimated number of seconds  it  takes  to
		transmit  a link- state update packet over this
		interface."
	DEFVAL { 1 }
	::= { axsOspfv3VirtIfEntry 5 }

axsOspfv3VirtIfRetransInterval OBJECT-TYPE
	SYNTAX  UpToMaxAge
	ACCESS  read-only
	STATUS  mandatory
	DESCRIPTION
		"The number of seconds between  link-state  ad-
		vertisement  retransmissions,  for  adjacencies
		belonging to this  interface.  This  value  is
		also used when retransmitting database descrip-
		tion  and  link-state  request  packets.   This
		value  should  be well over the expected round-
		trip time."
	DEFVAL { 5 }
	::= { axsOspfv3VirtIfEntry 6 }

axsOspfv3VirtIfHelloInterval OBJECT-TYPE
	SYNTAX  HelloRange
	ACCESS  read-only
	STATUS  mandatory
	DESCRIPTION
		"The length of time, in  seconds,  between  the
		Hello  packets that the router sends on the in-
		terface.  This value must be the same  for  the
		virtual neighbor."
	DEFVAL { 10 }
	::= { axsOspfv3VirtIfEntry 7 }

axsOspfv3VirtIfRtrDeadInterval OBJECT-TYPE
	SYNTAX  PositiveInteger
	ACCESS  read-only
	STATUS  mandatory
	DESCRIPTION
		"The number of seconds that  a  router's  Hello
		packets  have  not been seen before it's neigh-
		bors declare the router down.  This  should  be
		some  multiple  of  the  Hello  interval.  This
		value must be the same for the  virtual  neigh-
		bor."
	DEFVAL { 60 }
	::= { axsOspfv3VirtIfEntry 8 }

axsOspfv3VirtIfState OBJECT-TYPE
	SYNTAX  INTEGER {
		down (1),    -- these use the same encoding
		pointToPoint (4) -- as the axsOspfv3IfTable
	}
	ACCESS  read-only
	STATUS  mandatory
	DESCRIPTION
		"OSPF virtual interface states."
	DEFVAL  { down }
	::= { axsOspfv3VirtIfEntry 9 }

axsOspfv3VirtIfEvents OBJECT-TYPE
	SYNTAX  Counter32
	ACCESS  read-only
	STATUS  mandatory
	DESCRIPTION
		"The number of state changes or error events on
		this Virtual Link"
	::= { axsOspfv3VirtIfEntry 10 }

axsOspfv3VirtIfStatus OBJECT-TYPE
	SYNTAX  RowStatus
	ACCESS  read-only
	STATUS  mandatory
	DESCRIPTION
		"This variable displays the status of  the  en-
		try.  Setting it to 'invalid' has the effect of
		rendering it inoperative.  The internal  effect
		(row removal) is implementation dependent."
		::= { axsOspfv3VirtIfEntry 11 }

axsOspfv3VirtIfLinkScopeLsaCount OBJECT-TYPE
	SYNTAX  Gauge32
	ACCESS  read-only
	STATUS  mandatory
	DESCRIPTION
		"The total number of Link-Scope link-state
		advertisements in  this  virtual link's link-state
		database."
	::= { axsOspfv3VirtIfEntry 12 }

axsOspfv3VirtIfLinkLsaCksumSum OBJECT-TYPE
	SYNTAX  Integer32
	ACCESS  read-only
	STATUS  mandatory
	DESCRIPTION
		"The 32-bit unsigned sum of the Link-Scope link-state
		advertisements'  LS  checksums  contained in this
		virtual link's link-state database.  The sum can be used
		to determine if  there  has been  a  change  in a
		router's link state database, and to compare the
		link-state database of two routers."
	DEFVAL  { 0 }
	::= { axsOspfv3VirtIfEntry 13 }

--  axsOspfv3 Neighbor Table
--    The axsOspfv3 Neighbor Table describes all neighbors in
--    the locality of the subject router.

axsOspfv3NbrTable OBJECT-TYPE
	SYNTAX  SEQUENCE OF AxsOspfv3NbrEntry
	ACCESS  not-accessible
	STATUS  mandatory
	DESCRIPTION
		"A table of non-virtual neighbor information."
	REFERENCE
		"OSPF Version 2, Section 10  The  Neighbor  Data
		Structure"
	::= { axsOspfv3 9 }

axsOspfv3NbrEntry OBJECT-TYPE
	SYNTAX  AxsOspfv3NbrEntry
	ACCESS  not-accessible
	STATUS  mandatory
	DESCRIPTION
		"The information regarding a single neighbor."
	REFERENCE
		"OSPF Version 2, Section 10  The  Neighbor  Data
		Structure"
	INDEX { axsOspfv3NbrDomainNumber, axsOspfv3NbrIfIndex, axsOspfv3NbrIpv6Addr }
	::= { axsOspfv3NbrTable 1 }

	AxsOspfv3NbrEntry ::=
		SEQUENCE {
			axsOspfv3NbrDomainNumber
				INTEGER,
			axsOspfv3NbrIfIndex
				Ipv6IfIndex,
			axsOspfv3NbrIpv6Addr
				Ipv6Address,
			axsOspfv3NbrRtrId
				RouterID,
			axsOspfv3NbrOptions
				Integer32,
			axsOspfv3NbrPriority
				DesignatedRouterPriority,
			axsOspfv3NbrState
				INTEGER,
			axsOspfv3NbrEvents
				Counter32,
			axsOspfv3NbrLsRetransQLen
				Gauge32,
			axsOspfv3NbrHelloSuppressed
				TruthValue,
			axsOspfv3NbrIfId
				Ipv6IfIndex
			}

axsOspfv3NbrDomainNumber OBJECT-TYPE
	SYNTAX  INTEGER
	ACCESS  read-only
	STATUS  mandatory
	DESCRIPTION
		"ospfv3 domain number."
	::= { axsOspfv3NbrEntry 1 }

axsOspfv3NbrIfIndex OBJECT-TYPE
	SYNTAX  Ipv6IfIndex
	ACCESS  read-only
	STATUS  mandatory
	DESCRIPTION
		"The local link ID of the link over which the
		neighbor can be reached."
	::= { axsOspfv3NbrEntry 2 }

axsOspfv3NbrIpv6Addr OBJECT-TYPE
	SYNTAX  Ipv6Address
	ACCESS  read-only
	STATUS  mandatory
	DESCRIPTION
		"The IPv6 address of the neighbor associated with
		the local link."
	::= { axsOspfv3NbrEntry 3 }

axsOspfv3NbrRtrId OBJECT-TYPE
	SYNTAX  RouterID
	ACCESS  read-only
	STATUS  mandatory
	DESCRIPTION
		"A 32-bit integer (represented as a type  IpAd-
		dress)  uniquely  identifying  the  neighboring
		router in the Autonomous System."
	::= { axsOspfv3NbrEntry 4 }

axsOspfv3NbrOptions OBJECT-TYPE
	SYNTAX  Integer32
	ACCESS  read-only
	STATUS  mandatory
	DESCRIPTION
		"A Bit Mask corresponding to the neighbor's op-
		tions field."
	DEFVAL { 0 }
	::= { axsOspfv3NbrEntry 5 }

axsOspfv3NbrPriority OBJECT-TYPE
	SYNTAX  DesignatedRouterPriority
	ACCESS  read-only
	STATUS  mandatory
	DESCRIPTION
		"The priority of this neighbor in the designat-
		ed router election algorithm.  The value 0 sig-
		nifies that the neighbor is not eligible to be-
		come  the  designated router on this particular
		network."
	DEFVAL { 1 }
	::= { axsOspfv3NbrEntry 6 }

axsOspfv3NbrState OBJECT-TYPE
	SYNTAX  INTEGER {
		down (1),
		attempt (2),
		init (3),
		twoWay (4),
		exchangeStart (5),
		exchange (6),
		loading (7),
		full (8)
	}
	ACCESS  read-only
	STATUS  mandatory
	DESCRIPTION
		"The State of the relationship with this Neigh-
		bor."
	REFERENCE
		"OSPF Version 2, Section 10.1 Neighbor States"
	DEFVAL  { down }
	::= { axsOspfv3NbrEntry 7 }

axsOspfv3NbrEvents OBJECT-TYPE
	SYNTAX  Counter32
	ACCESS  read-only
	STATUS  mandatory
	DESCRIPTION
		"The number of times this neighbor relationship
		has changed state, or an error has occurred."
	::= { axsOspfv3NbrEntry 8 }

axsOspfv3NbrLsRetransQLen OBJECT-TYPE
	SYNTAX  Gauge32
	ACCESS  read-only
	STATUS  mandatory
	DESCRIPTION
		"The  current  length  of  the   retransmission
		queue."
	::= { axsOspfv3NbrEntry 9 }

axsOspfv3NbrHelloSuppressed OBJECT-TYPE
	SYNTAX  TruthValue
	ACCESS  read-only
	STATUS  mandatory
	DESCRIPTION
		"Indicates whether Hellos are being  suppressed
		to the neighbor"
	::= { axsOspfv3NbrEntry 12 }

axsOspfv3NbrIfId OBJECT-TYPE
	SYNTAX  Ipv6IfIndex
	ACCESS  read-only
	STATUS  mandatory
	DESCRIPTION
		"The interface ID that the neighbor advertises
		in its Hello Packets on this link, that is, the
		neighbor's local interface index."
	::= { axsOspfv3NbrEntry 13 }

--  axsOspfv3 Virtual Neighbor Table
--    This table describes all virtual neighbors.
--    Since Virtual Links are configured in the
--    virtual interface table, this table is read-only.

axsOspfv3VirtNbrTable OBJECT-TYPE
	SYNTAX  SEQUENCE OF AxsOspfv3VirtNbrEntry
	ACCESS  not-accessible
	STATUS  mandatory
	DESCRIPTION
		"A table of virtual neighbor information."
	REFERENCE
		"OSPF Version 2, Section 15  Virtual Links"
	::= { axsOspfv3 10 }

axsOspfv3VirtNbrEntry OBJECT-TYPE
	SYNTAX  AxsOspfv3VirtNbrEntry
	ACCESS  not-accessible
	STATUS  mandatory
	DESCRIPTION
		"Virtual neighbor information."
	INDEX { axsOspfv3VirtNbrDomainNumber, axsOspfv3VirtNbrArea, axsOspfv3VirtNbrRtrId }
	::= { axsOspfv3VirtNbrTable 1 }

	AxsOspfv3VirtNbrEntry ::=
		SEQUENCE {
			axsOspfv3VirtNbrDomainNumber
				INTEGER,
			axsOspfv3VirtNbrArea
				AreaID,
			axsOspfv3VirtNbrRtrId
				RouterID,
			axsOspfv3VirtNbrIfIndex
				Ipv6IfIndex,
			axsOspfv3VirtNbrIpv6Addr
				Ipv6Address,
			axsOspfv3VirtNbrOptions
				Integer32,
			axsOspfv3VirtNbrState
				INTEGER,
			axsOspfv3VirtNbrEvents
				Counter32,
			axsOspfv3VirtNbrLsRetransQLen
				Gauge32,
			axsOspfv3VirtNbrHelloSuppressed
				TruthValue,
			axsOspfv3VirtNbrIfId
				Ipv6IfIndex
			}

axsOspfv3VirtNbrDomainNumber OBJECT-TYPE
	SYNTAX  INTEGER
	ACCESS  read-only
	STATUS  mandatory
	DESCRIPTION
		"ospfv3 domain number."
	::= { axsOspfv3VirtNbrEntry 1 }

axsOspfv3VirtNbrArea OBJECT-TYPE
	SYNTAX  AreaID
	ACCESS  read-only
	STATUS  mandatory
	DESCRIPTION
		"The Transit Area Identifier."
	::= { axsOspfv3VirtNbrEntry 2 }

axsOspfv3VirtNbrRtrId OBJECT-TYPE
	SYNTAX  RouterID
	ACCESS  read-only
	STATUS  mandatory
	DESCRIPTION
		"A  32-bit  integer  uniquely  identifying  the
		neighboring router in the Autonomous System."
	::= { axsOspfv3VirtNbrEntry 3 }

axsOspfv3VirtNbrIfIndex OBJECT-TYPE
	SYNTAX  Ipv6IfIndex
	ACCESS  read-only
	STATUS  mandatory
	DESCRIPTION
		"The local link ID for the virtual link over
		which the neighbor can be reached."
	::= { axsOspfv3VirtNbrEntry 4 }

axsOspfv3VirtNbrIpv6Addr OBJECT-TYPE
	SYNTAX  Ipv6Address
	ACCESS  read-only
	STATUS  mandatory
	DESCRIPTION
		"The IPv6 address used to reach this Virtual Neighbor.
		It must be a Site-Local or Global scope address."
	::= { axsOspfv3VirtNbrEntry 5 }

axsOspfv3VirtNbrOptions OBJECT-TYPE
	SYNTAX  Integer32
	ACCESS  read-only
	STATUS  mandatory
	DESCRIPTION
		"A Bit Mask corresponding to the neighbor's op-
		tions field."
	::= { axsOspfv3VirtNbrEntry 6 }

axsOspfv3VirtNbrState OBJECT-TYPE
	SYNTAX  INTEGER {
		down (1),
		attempt (2),
		init (3),
		twoWay (4),
		exchangeStart (5),
		exchange (6),
		loading (7),
		full (8)
	}
	ACCESS  read-only
	STATUS  mandatory
	DESCRIPTION
		"The state of the  Virtual  Neighbor  Relation-
		ship."
	::= { axsOspfv3VirtNbrEntry 7 }

axsOspfv3VirtNbrEvents OBJECT-TYPE
	SYNTAX  Counter32
	ACCESS  read-only
	STATUS  mandatory
	DESCRIPTION
		"The number of  times  this  virtual  link  has
		changed its state, or an error has occurred."
	::= { axsOspfv3VirtNbrEntry 8 }

axsOspfv3VirtNbrLsRetransQLen OBJECT-TYPE
	SYNTAX  Gauge32
	ACCESS  read-only
	STATUS  mandatory
	DESCRIPTION
		"The  current  length  of  the   retransmission
		queue."
	::= { axsOspfv3VirtNbrEntry 9 }

axsOspfv3VirtNbrHelloSuppressed OBJECT-TYPE
	SYNTAX  TruthValue
	ACCESS  read-only
	STATUS  mandatory
	DESCRIPTION
		"Indicates whether Hellos are being  suppressed
		to the neighbor"
	::= { axsOspfv3VirtNbrEntry 10 }

axsOspfv3VirtNbrIfId OBJECT-TYPE
	SYNTAX  Ipv6IfIndex
	ACCESS  read-only
	STATUS  mandatory
	DESCRIPTION
		"The interface ID that the neighbor advertises
		in its Hello Packets on this virtual link, that is,
		the neighbor's local interface index."
	::= { axsOspfv3VirtNbrEntry 11 }

 --
 --    The axsOspfv3 Area Aggregate Table
 --

axsOspfv3AreaAggregateTable OBJECT-TYPE
	SYNTAX  SEQUENCE OF AxsOspfv3AreaAggregateEntry
	ACCESS  not-accessible
	STATUS  mandatory
	DESCRIPTION
		"A range of IPv6 prefixes specified by a
		prefix/prefix length  pair. Note that if
		ranges are configured such that one range sub-
		sumes  another range the most specific match is
		the preferred one."
	::= { axsOspfv3 11 }

axsOspfv3AreaAggregateEntry OBJECT-TYPE
	SYNTAX  AxsOspfv3AreaAggregateEntry
	ACCESS  not-accessible
	STATUS  mandatory
	DESCRIPTION
		"A range of IPv6 prefixes specified by a
		prefix/prefix length  pair. Note that if
		ranges are configured such that one range sub-
		sumes  another range the most specific match is
		the preferred one."
	REFERENCE
		"OSPF Version 2, Appendix C.2  Area parameters"
	INDEX { axsOspfv3AreaAggregateDomainNumber,
		axsOspfv3AreaAggregateAreaID,
		axsOspfv3AreaAggregateAreaLsdbType,
		axsOspfv3AreaAggregateIndex }
	::= { axsOspfv3AreaAggregateTable 1 }

	AxsOspfv3AreaAggregateEntry ::=
		SEQUENCE {
			axsOspfv3AreaAggregateDomainNumber
				INTEGER,
			axsOspfv3AreaAggregateAreaID
				AreaID,
			axsOspfv3AreaAggregateAreaLsdbType
				INTEGER,
			axsOspfv3AreaAggregateIndex
				INTEGER,
			axsOspfv3AreaAggregatePrefix
				Ipv6AddressPrefix,
			axsOspfv3AreaAggregatePrefixLen
				INTEGER,
			axsOspfv3AreaAggregateStatus
				RowStatus,
			axsOspfv3AreaAggregateEffect
				INTEGER
			}

axsOspfv3AreaAggregateDomainNumber OBJECT-TYPE
	SYNTAX  INTEGER
	ACCESS  read-only
	STATUS  mandatory
	DESCRIPTION
		"ospfv3 domain number."
	::= { axsOspfv3AreaAggregateEntry 1 }

axsOspfv3AreaAggregateAreaID OBJECT-TYPE
	SYNTAX  AreaID
	ACCESS  read-only
	STATUS  mandatory
	DESCRIPTION
		"The Area the Address Aggregate is to be  found
		within."
	REFERENCE
		"OSPF Version 2, Appendix C.2 Area parameters"
	::= { axsOspfv3AreaAggregateEntry 2 }

axsOspfv3AreaAggregateAreaLsdbType OBJECT-TYPE
	SYNTAX  INTEGER {
		interAreaPrefixLsa (8195), -- 0x2003
		nssaExternalLsa    (8199)  -- 0x2007
	}
	ACCESS  read-only
	STATUS  mandatory
	DESCRIPTION
		"The type of the Address Aggregate.  This field
		specifies  the  Area Lsdb type that this Address Ag-
		gregate applies to."
	REFERENCE
		"OSPF Version 2, Appendix A.4.1 The  Link  State
		Advertisement header"
	::= { axsOspfv3AreaAggregateEntry 3 }

axsOspfv3AreaAggregateIndex OBJECT-TYPE
	SYNTAX  INTEGER (1..2147483647)
	ACCESS  read-only
	STATUS  mandatory
	DESCRIPTION
		"A unique identifier for this aggregate table entry."
	::= { axsOspfv3AreaAggregateEntry 4 }

axsOspfv3AreaAggregatePrefix OBJECT-TYPE
	SYNTAX  Ipv6AddressPrefix
	ACCESS  read-only
	STATUS  mandatory
	DESCRIPTION
		"The IPv6 Prefix."
	REFERENCE
		"OSPF Version 2, Appendix C.2 Area parameters"
	::= { axsOspfv3AreaAggregateEntry 5 }

axsOspfv3AreaAggregatePrefixLen OBJECT-TYPE
	SYNTAX  INTEGER ( 3..128 )
--	UNITS  "bits"
	ACCESS  read-only
	STATUS  mandatory
	DESCRIPTION
		"The length of the prefix (in bits). A prefix can
		not be shorter than 3 bits."
	REFERENCE
		"OSPF Version 2, Appendix C.2 Area parameters"
	::= { axsOspfv3AreaAggregateEntry 6 }

axsOspfv3AreaAggregateStatus OBJECT-TYPE
	SYNTAX  RowStatus
	ACCESS  read-only
	STATUS  mandatory
	DESCRIPTION
		"This variable displays the status of  the  en-
		try.  Setting it to 'invalid' has the effect of
		rendering it inoperative.  The internal  effect
		(row removal) is implementation dependent."
	::= { axsOspfv3AreaAggregateEntry 7 }

axsOspfv3AreaAggregateEffect OBJECT-TYPE
	SYNTAX  INTEGER {
		advertiseMatching (1),
		doNotAdvertiseMatching (2)
	}
	ACCESS  read-only
	STATUS  mandatory
	DESCRIPTION
		"Prefixes subsumed by ranges either trigger  the
		advertisement  of  the indicated aggregate (ad-
		vertiseMatching), or result in the prefix not
		being advertised at all outside the area."
	DEFVAL  { advertiseMatching }
	::= { axsOspfv3AreaAggregateEntry 8 }

-- axsStatic

axsStaticTable OBJECT-TYPE
        SYNTAX    SEQUENCE OF AxsStaticGatewayEntry
        ACCESS    not-accessible
        STATUS    mandatory
        DESCRIPTION
                  "The set of instances of the static gateway state."
        ::= { axsStatic 1 }

axsStaticGatewayEntry OBJECT-TYPE
        SYNTAX    AxsStaticGatewayEntry
        ACCESS    not-accessible
        STATUS    mandatory
        DESCRIPTION
                  "Each row defines information about static route gateway state."
        INDEX     { axsStaticGatewayAddr }
        ::= { axsStaticTable 1 }

        AxsStaticGatewayEntry ::= SEQUENCE {
            axsStaticGatewayAddr     IpAddress,
            axsStaticGatewayState    INTEGER
        }

axsStaticGatewayAddr OBJECT-TYPE
        SYNTAX    IpAddress
        ACCESS    not-accessible
        STATUS    mandatory
        DESCRIPTION
                  "The static route gateway address."
        ::= { axsStaticGatewayEntry 1 }
        
axsStaticGatewayState OBJECT-TYPE
        SYNTAX    INTEGER {
                      reachable(1),
                      unreachable(2)
                  }
        ACCESS    not-accessible
        STATUS    mandatory
        DESCRIPTION
                  "The state of static route gateway."
        ::= { axsStaticGatewayEntry 2 }

axsStaticIpv6Table OBJECT-TYPE
        SYNTAX    SEQUENCE OF AxsStaticIpv6GatewayEntry
        ACCESS    not-accessible
        STATUS    mandatory
        DESCRIPTION
                  "The set of instances of the ipv6 static gateway state."
        ::= { axsStatic 3 }

axsStaticIpv6GatewayEntry OBJECT-TYPE
        SYNTAX    AxsStaticIpv6GatewayEntry
        ACCESS    not-accessible
        STATUS    mandatory
        DESCRIPTION
                  "Each row defines information about ipv6 static route gateway state."
        INDEX { axsStaticIpv6Ifindex,
                axsStaticIpv6GatewayAddr }
        ::= { axsStaticIpv6Table 1 }

        AxsStaticIpv6GatewayEntry ::= SEQUENCE {
            axsStaticIpv6Ifindex        INTEGER,
            axsStaticIpv6GatewayAddr    Ipv6Address,
            axsStaticIpv6GatewayState   INTEGER
        }

axsStaticIpv6Ifindex OBJECT-TYPE
        SYNTAX    INTEGER
        ACCESS    not-accessible
        STATUS    mandatory
        DESCRIPTION
                  "The ifIndex related static gateway address."
        ::= { axsStaticIpv6GatewayEntry 1 }

axsStaticIpv6GatewayAddr OBJECT-TYPE
        SYNTAX    Ipv6Address
        ACCESS    not-accessible
        STATUS    mandatory
        DESCRIPTION
                  "The static route gateway address."
        ::= { axsStaticIpv6GatewayEntry 2 }

axsStaticIpv6GatewayState OBJECT-TYPE
        SYNTAX    INTEGER {
                      reachable(1),
                      unreachable(2)
                  }
        ACCESS    not-accessible
        STATUS    mandatory
        DESCRIPTION
                  "The state of static route gateway."
        ::= { axsStaticIpv6GatewayEntry 3 }

--  axsUlr
axsUlrID OBJECT-TYPE
	SYNTAX  MacAddress
	ACCESS  read-only
	STATUS  mandatory
	DESCRIPTION
		"Identifier of device."
	::= { axsUlrGlobalInfo 2 }

axsUlrConfigurationPortCounts OBJECT-TYPE
	SYNTAX  INTEGER
	ACCESS  read-only
	STATUS  mandatory
	DESCRIPTION
		"The number of primary port and secondary port in device."
	::= { axsUlrGlobalInfo 3 }

axsUlrStartupActivePortSelection OBJECT-TYPE
	SYNTAX  INTEGER
	ACCESS  read-only
	STATUS  mandatory
	DESCRIPTION
		"The configuration of startup active port selection."
	::= { axsUlrGlobalInfo 4 }

axsUlrPortTable OBJECT-TYPE
	SYNTAX  SEQUENCE OF AxsUlrPortEntry
	ACCESS  not-accessible
	STATUS  mandatory
	DESCRIPTION
		"A table containing uplink port information."
	::= { axsUlr 2 }

axsUlrPortEntry OBJECT-TYPE
	SYNTAX  AxsUlrPortEntry
	ACCESS  not-accessible
	STATUS  mandatory
	DESCRIPTION
		"An entry containing uplink port."
    INDEX { axsUlrPortIfIndex }
	::= { axsUlrPortTable 1 }

        AxsUlrPortEntry ::=
                SEQUENCE {
                    axsUlrPortIfIndex                          INTEGER,
                    axsUlrPortType                             INTEGER,
                    axsUlrPairedPortIfIndex                    INTEGER,
                    axsUlrPortStatus                           INTEGER,
                    axsUlrPairedPortStatus                     INTEGER,
                    axsUlrAutoChangeToPrimary                  INTEGER,
                    axsUlrAutoChangeToPrimaryDelay             INTEGER,
                    axsUlrAutoChangeToPrimaryRest              INTEGER,
                    axsUlrStartupActivePortSelectionStatus     INTEGER,
                    axsUlrFlushTransmit                        INTEGER,
                    axsUlrFlushVlan                            INTEGER,
                    axsUlrMacAddressUpdateTransmit             INTEGER,
                    axsUlrLastActivePortDecisionTime           TimeStamp,
                    axsUlrLastFlushTransmitTime                TimeStamp,
                    axsUlrLastMacUpdateTransmitTime            TimeStamp,
                    axsUlrLastChangeFactor                     INTEGER,
                    axsUlrFlushTransmitTotalPackets            INTEGER,
                    axsUlrMacAddressUpdateTransmitTotalPackets INTEGER,
                    axsUlrMacAddressUpdateTransmitOverFlow     INTEGER,
                    axsUlrActiveDecisionCount                  INTEGER
		}

axsUlrPortIfIndex OBJECT-TYPE
	SYNTAX  INTEGER
	ACCESS  read-only
	STATUS  mandatory
	DESCRIPTION
		"IfIndex of the port."
	::= { axsUlrPortEntry 1 }

axsUlrPortType OBJECT-TYPE
	SYNTAX  INTEGER
	ACCESS  read-only
	STATUS  mandatory
	DESCRIPTION
		"Type of port.
          1) Primary
          2) Secondary"
	::= { axsUlrPortEntry 2 }

axsUlrPairedPortIfIndex OBJECT-TYPE
	SYNTAX  INTEGER
	ACCESS  read-only
	STATUS  mandatory
	DESCRIPTION
		"IfIndex of paired port."
	::= { axsUlrPortEntry 3 }

axsUlrPortStatus OBJECT-TYPE
	SYNTAX  INTEGER {
				forwarding(1),
				down(2),
				blocking(3)
			}
	ACCESS  read-only
	STATUS  mandatory
	DESCRIPTION
		"The state of port.
          1) Forwarding
          2) Down
          3) Blocking"
	::= { axsUlrPortEntry 4 }

axsUlrPairedPortStatus OBJECT-TYPE
	SYNTAX  INTEGER {
				forwarding(1),
				down(2),
				blocking(3)
			}
	ACCESS  read-only
	STATUS  mandatory
	DESCRIPTION
		"The state of paired port.
          1) Forwarding
          2) Down
          3) Blocking"
	::= { axsUlrPortEntry 5 }

axsUlrAutoChangeToPrimary OBJECT-TYPE
	SYNTAX  INTEGER {
				off(1),
				on(2)
			}
	ACCESS  read-only
	STATUS  mandatory
	DESCRIPTION
		"The configuration of preemption.
          1) Off
          2) On"
	::= { axsUlrPortEntry 6 }

axsUlrAutoChangeToPrimaryDelay OBJECT-TYPE
	SYNTAX  INTEGER
	ACCESS  read-only
	STATUS  mandatory
	DESCRIPTION
		"The Delay time of preemption."
	::= { axsUlrPortEntry 7 }

axsUlrAutoChangeToPrimaryRest OBJECT-TYPE
	SYNTAX  INTEGER
	ACCESS  read-only
	STATUS  mandatory
	DESCRIPTION
		"The rest time of preemption."
	::= { axsUlrPortEntry 8 }

axsUlrStartupActivePortSelectionStatus OBJECT-TYPE
	SYNTAX  INTEGER {
				off(1),
				on(2)
			}
	ACCESS  read-only
	STATUS  mandatory
	DESCRIPTION
		"The state of startup active port selection.
          1) Off
          2) On"
	::= { axsUlrPortEntry 9 }

axsUlrFlushTransmit OBJECT-TYPE
	SYNTAX  INTEGER {
				off(1),
				on(2)
			}
	ACCESS  read-only
	STATUS  mandatory
	DESCRIPTION
		"The configuration of transmit flush-request frame.
          1) Off
          2) On"
	::= { axsUlrPortEntry 10 }

axsUlrFlushVlan OBJECT-TYPE
	SYNTAX  INTEGER
	ACCESS  read-only
	STATUS  mandatory
	DESCRIPTION
		"The transmit VLAN ID in flush-request frame. 0 is not configuration."
	::= { axsUlrPortEntry 11 }

axsUlrMacAddressUpdateTransmit OBJECT-TYPE
	SYNTAX  INTEGER
	ACCESS  read-only
	STATUS  mandatory
	DESCRIPTION
		"The number of transmit MAC Address update frame in one opportunity."
	::= { axsUlrPortEntry 12 }

axsUlrLastActivePortDecisionTime OBJECT-TYPE
	SYNTAX  TimeStamp
	ACCESS  read-only
	STATUS  mandatory
	DESCRIPTION
		"Last determinate time of the active port."
	::= { axsUlrPortEntry 13 }

axsUlrLastFlushTransmitTime OBJECT-TYPE
	SYNTAX  TimeStamp
	ACCESS  read-only
	STATUS  mandatory
	DESCRIPTION
		"Last transmit time of flush-request frame."
	::= { axsUlrPortEntry 14 }

axsUlrLastMacUpdateTransmitTime OBJECT-TYPE
	SYNTAX  TimeStamp
	ACCESS  read-only
	STATUS  mandatory
	DESCRIPTION
		"Last transmit time of MAC Address update frame."
	::= { axsUlrPortEntry 15 }

axsUlrLastChangeFactor OBJECT-TYPE
	SYNTAX  INTEGER {
				command(1),
				configure(2),
				primary-down(3),
				primary-up(4),
				secondary-down(5),
				secondary-up(6),
				preemption(7)
			}
	ACCESS  read-only
	STATUS  mandatory
	DESCRIPTION
		"Last determinate factor of the active port.
          1) command
          2) configure
          3) primary down
          4) primary up
          5) secondary down
          6) secondary up
          7) preemption"
	::= { axsUlrPortEntry 16 }

axsUlrFlushTransmitTotalPackets OBJECT-TYPE
	SYNTAX  INTEGER
	ACCESS  read-only
	STATUS  mandatory
	DESCRIPTION
		"The total number of transmit flush-request frame in the port."
	::= { axsUlrPortEntry 17 }

axsUlrMacAddressUpdateTransmitTotalPackets OBJECT-TYPE
	SYNTAX  INTEGER
	ACCESS  read-only
	STATUS  mandatory
	DESCRIPTION
		"The total number of transmit MAC Address update frame in the port."
	::= { axsUlrPortEntry 18 }

axsUlrMacAddressUpdateTransmitOverFlow OBJECT-TYPE
	SYNTAX  INTEGER
	ACCESS  read-only
	STATUS  mandatory
	DESCRIPTION
		"The over flow number of MAC Address update frame."
	::= { axsUlrPortEntry 19 }

axsUlrActiveDecisionCount OBJECT-TYPE
	SYNTAX  INTEGER
	ACCESS  read-only
	STATUS  mandatory
	DESCRIPTION
		"The determinate number of active port in uplink port."
	::= { axsUlrPortEntry 20 }

--  axsTrackObject

    axsTrackObjectGeneralLastChange OBJECT-TYPE
        SYNTAX    TimeTicks
        ACCESS    read-only
        STATUS    mandatory
        DESCRIPTION
                  "The last time that the tracking object state changed."
        ::= { axsTrackObjectGeneralGroup  1 }

    axsTrackObjectTable OBJECT-TYPE
        SYNTAX    SEQUENCE OF AxsTrackObjectEntry
        ACCESS    not-accessible
        STATUS    mandatory
        DESCRIPTION
                  "This table containing the tracking information."
        ::= { axsTrackObject 3 }

    axsTrackObjectEntry OBJECT-TYPE
        SYNTAX    AxsTrackObjectEntry
        ACCESS    not-accessible
        STATUS    mandatory
        DESCRIPTION
                  "The entry of track information."
        INDEX { axsTrackObjectId }
        ::= { axsTrackObjectTable 1 }
    
    AxsTrackObjectEntry ::= SEQUENCE {
        axsTrackObjectId             INTEGER,
        axsTrackObjectState          INTEGER,
        axsTrackObjectOperation      INTEGER,
        axsTrackObjectType           INTEGER,
        axsTrackObjectNetIndex       INTEGER
    }
    
    axsTrackObjectId OBJECT-TYPE
        SYNTAX    INTEGER
        ACCESS    read-only
        STATUS    mandatory
        DESCRIPTION
                  "The unique index number given for each track-object settings."
        ::= { axsTrackObjectEntry 1 }
    
    axsTrackObjectState OBJECT-TYPE
        SYNTAX    INTEGER {
                      up(1),
                      down(2)
                  }
        ACCESS    read-only
        STATUS    mandatory
        DESCRIPTION
                  "The state of the track."
        ::= { axsTrackObjectEntry 2 }
    
    axsTrackObjectOperation OBJECT-TYPE
        SYNTAX    INTEGER {
                      active(1),
                      transit(2),
                      disabled(3),
                      init(4),
                      aging(5)
                  }
        ACCESS    read-only
        STATUS    mandatory
        DESCRIPTION
                  "The operation state of the track."
        ::= { axsTrackObjectEntry 3 }
    
    axsTrackObjectType OBJECT-TYPE
        SYNTAX    INTEGER {
                      ipv4-icmp(1)
                  }
        ACCESS    read-only
        STATUS    mandatory
        DESCRIPTION
                  "The tracking type of the track."
        ::= { axsTrackObjectEntry 4 }
    
    axsTrackObjectNetIndex OBJECT-TYPE
        SYNTAX    INTEGER
        ACCESS    read-only
        STATUS    mandatory
        DESCRIPTION
                  "The network ID of the ICMP tracking object."
        ::= { axsTrackObjectEntry 5 }

-- axsPolicyBase

    axsPolicyBaseRoutingChangeListNumber OBJECT-TYPE
        SYNTAX          Unsigned32
        ACCESS          not-accessible
        STATUS          mandatory
        DESCRIPTION
                  "List number change is generated by policy base routing."
        ::= { axsPolicyBaseRouting 1 }
        
    axsPolicyBaseRoutingChangeSequenceNumber OBJECT-TYPE
        SYNTAX          Unsigned32
        ACCESS          not-accessible
        STATUS          mandatory
        DESCRIPTION
                  "Priority changed by the list number of the policy base routing."
        ::= { axsPolicyBaseRouting 2 }

--  axsLogin

axsLoginName OBJECT-TYPE
	SYNTAX  DisplayString
	ACCESS  not-accessible
	STATUS  mandatory
	DESCRIPTION
		"Log in user name."
	::= { axsLogin 1 }

axsLoginTime OBJECT-TYPE
	SYNTAX  DisplayString
	ACCESS  not-accessible
	STATUS  mandatory
	DESCRIPTION
		"Date, time and time zone of user log in.
                 Format : YYYY/MM/DD hh:mm:ss XXXXXX(time zone)
		 Time zone format :
		   JST    : JST
                   GMT+09 : GMT + 09 hours
                   GMT+10 : GMT + 10 hours"
	::= { axsLogin 2 }

axsLogoutTime OBJECT-TYPE
	SYNTAX  DisplayString
	ACCESS  not-accessible
	STATUS  mandatory
	DESCRIPTION
		"Date, time and time zone of user log out.
		Format : YYYY/MM/DD hh:mm:ss XXXXXX(time zone)
		Time zone format :
		  JST    : JST
		  GMT+09 : GMT + 09 hours
		  GMT+10 : GMT + 10 hours"
	::= { axsLogin 3 }

axsLoginFailureTime OBJECT-TYPE
	SYNTAX  DisplayString
	ACCESS  not-accessible
	STATUS  mandatory
	DESCRIPTION
		"Date, time and time zone of user log in failure.
		Format : YYYY/MM/DD hh:mm:ss XXXXXX(time zone)
		Time zone format :
		  JST    : JST
		  GMT+09 : GMT + 09 hours
		  GMT+10 : GMT + 10 hours"
	::= { axsLogin 4 }

axsLoginLocation OBJECT-TYPE
	SYNTAX  DisplayString
	ACCESS  not-accessible
	STATUS  mandatory
	DESCRIPTION
		"Terminal information of log in user.
		The status will be 'console'.
		If other, displays 'TERMINAL(APLLICATION)'.
		ex. 'tty/1(telnet)'"
	::= { axsLogin 5 }

axsLoginLine OBJECT-TYPE
	SYNTAX  DisplayString
	ACCESS  not-accessible
	STATUS  mandatory
	DESCRIPTION
		"Connection information of log in user.
		The status will be 'console'.
		If other, displays 'IPADDRESS(APLLICATION)'.
		ex. '192.168.11.1(telnet)'"
	::= { axsLogin 6 }

axsLogoutStatus OBJECT-TYPE
	SYNTAX  INTEGER {
		error(1),
		success(2),
		timeout(3),
		disconnect(4),
		force(5)
	      }
	ACCESS  not-accessible
	STATUS  mandatory
	DESCRIPTION
		"Log out factor.
		 error(1)      : log out due to none of bellow
		 success(2)    : log out due to command
		 timeout(3)    : log out due to 'auto-logout'
		 disconnect(4) : log out due to line disconnection
		 force(5)      : log out due to other user's command"
	::= { axsLogin 7 }

--  axsAxrp group 

axsAxrpGroupTable OBJECT-TYPE
        SYNTAX  SEQUENCE OF AxsAxrpGroupEntry
        ACCESS  not-accessible
        STATUS  mandatory
        DESCRIPTION
                "The table containing AXRP group information."
        ::= { axsAxrp 1 }

axsAxrpGroupEntry OBJECT-TYPE
        SYNTAX  AxsAxrpGroupEntry
        ACCESS  not-accessible
        STATUS  mandatory
        DESCRIPTION
                "The list of AXRP group information."
    INDEX { axsAxrpGroupRingId }
        ::= { axsAxrpGroupTable 1 }

        AxsAxrpGroupEntry ::=
                SEQUENCE {
                    axsAxrpGroupRingId                    INTEGER,
                    axsAxrpGroupRowStatus                 RowStatus,
                    axsAxrpGroupMode                      INTEGER,
                    axsAxrpGroupRingAttribute             INTEGER,
                    axsAxrpGroupMonitoringState           INTEGER,
                    axsAxrpGroupRingport1                 INTEGER,
                    axsAxrpGroupRingport1Shared           INTEGER,
                    axsAxrpGroupRingport2                 INTEGER,
                    axsAxrpGroupRingport2Shared           INTEGER,
                    axsAxrpGroupTransitionToFaultCounts   Counter,
                    axsAxrpGroupTransitionToNormalCounts  Counter,
                    axsAxrpGroupLastTransitionTime        TimeStamp,
                    axsAxrpGroupLinkStatusAlert           INTEGER,
                    axsAxrpGroupRingport1LinkKeepaliveSend    INTEGER,
                    axsAxrpGroupRingport1LinkKeepaliveMonitor INTEGER,
                    axsAxrpGroupRingport1LinkState        INTEGER,
                    axsAxrpGroupRingport1LinkKeepaliveReceiveCounts  Counter,
                    axsAxrpGroupRingport2LinkKeepaliveSend    INTEGER,
                    axsAxrpGroupRingport2LinkKeepaliveMonitor INTEGER,
                    axsAxrpGroupRingport2LinkState        INTEGER,
                    axsAxrpGroupRingport2LinkKeepaliveReceiveCounts  Counter,
                    axsAxrpGroupMultiFaultDetectionState  INTEGER
		}

axsAxrpGroupRingId OBJECT-TYPE
	SYNTAX  INTEGER
	ACCESS  not-accessible
	STATUS  mandatory
	DESCRIPTION
		"AXRP group ring identifier."
	::= { axsAxrpGroupEntry 1 }

axsAxrpGroupRowStatus OBJECT-TYPE
	SYNTAX  RowStatus
	ACCESS  read-only
	STATUS  mandatory
	DESCRIPTION
		"Valid/Invalid state of this entry. Valid(1) fixed"
	::= { axsAxrpGroupEntry 2 }

axsAxrpGroupMode OBJECT-TYPE
	SYNTAX  INTEGER{
	           no-config(1),
               master(2),
               transit(3)
               }
	ACCESS  read-only
	STATUS  mandatory
	DESCRIPTION
		"Operation mode of each ring ID."
	::= { axsAxrpGroupEntry 3 }

axsAxrpGroupRingAttribute OBJECT-TYPE
	SYNTAX  INTEGER{
	           no-config(1),
	           rift-ring(2),
	           rift-ring-edge1(3),
	           rift-ring-edge2(4)
	           }
	ACCESS  read-only
	STATUS  mandatory
	DESCRIPTION
		"When the multi ring is composed, it is an attribute of this device in the common link non-watch ring. "
	::= { axsAxrpGroupEntry 4 }

axsAxrpGroupMonitoringState OBJECT-TYPE
	SYNTAX  INTEGER{
	           init(1),
	           disable(2),
	           fault-monitoring(3),
	           recovery-monitoring(4),
	           flush-monitoring(5),
	           not-operating(6),
               suppress-fault-recovery(7),
               preempt-delay(8),
               recovery-re-monitoring(9)
	           }
	ACCESS  read-only
	STATUS  mandatory
	DESCRIPTION
		"Operation and state of watch of ring. "
	::= { axsAxrpGroupEntry 5 }

axsAxrpGroupRingport1 OBJECT-TYPE
	SYNTAX  INTEGER
	ACCESS  read-only
	STATUS  mandatory
	DESCRIPTION
		"IfIndex of ring port 1 (port in one where Ifindex is small)"
	::= { axsAxrpGroupEntry 6 }

axsAxrpGroupRingport1Shared OBJECT-TYPE
	SYNTAX  INTEGER {
                no-config(1),
                shared-edge(2),
                shared(3)
                }
	ACCESS  read-only
	STATUS  mandatory
	DESCRIPTION
		"Ring port 1 is common port information. "
	::= { axsAxrpGroupEntry 7 }

axsAxrpGroupRingport2 OBJECT-TYPE
	SYNTAX  INTEGER
	ACCESS  read-only
	STATUS  mandatory
	DESCRIPTION
		"IfIndex of ring port 2 (port in one where Ifindex is large)"
	::= { axsAxrpGroupEntry 8 }

axsAxrpGroupRingport2Shared OBJECT-TYPE
	SYNTAX  INTEGER {
                no-config(1),
                shared-edge(2),
                shared(3)
                }
	ACCESS  read-only
	STATUS  mandatory
	DESCRIPTION
		"Ring port 2 is common port information."
	::= { axsAxrpGroupEntry 9 }

axsAxrpGroupTransitionToFaultCounts OBJECT-TYPE
	SYNTAX  Counter
	ACCESS  read-only
	STATUS  mandatory
	DESCRIPTION
		"Frequency that shifts from state of trouble watch in state of restoration watch. "
	::= { axsAxrpGroupEntry 10 }

axsAxrpGroupTransitionToNormalCounts OBJECT-TYPE
	SYNTAX  Counter
	ACCESS  read-only
	STATUS  mandatory
	DESCRIPTION
		"Frequency that shifts from state of restoration watch in state of trouble watch. "
	::= { axsAxrpGroupEntry 11 }

axsAxrpGroupLastTransitionTime OBJECT-TYPE
	SYNTAX  TimeStamp
	ACCESS  read-only
	STATUS  mandatory
	DESCRIPTION
		"It is changing the final time to restoration from the trouble or the trouble from restoration. "
	::= { axsAxrpGroupEntry 12 }

axsAxrpGroupLinkStatusAlert OBJECT-TYPE
    SYNTAX  INTEGER {
                no-config(1),
                enable(2)
                }
    ACCESS  read-only
    STATUS  mandatory
    DESCRIPTION
        "State of each ring ID of link trouble detection."
    ::= { axsAxrpGroupEntry 13 }

axsAxrpGroupRingport1LinkKeepaliveSend OBJECT-TYPE
    SYNTAX  INTEGER {
                no-config(1),
                enable(2)
                }
    ACCESS  read-only
    STATUS  mandatory
    DESCRIPTION
        "State of transmission of link trouble watch frame of ring port 1."
    ::= { axsAxrpGroupEntry 14 }

axsAxrpGroupRingport1LinkKeepaliveMonitor OBJECT-TYPE
    SYNTAX  INTEGER {
                no-config(1),
                enable(2)
                }
    ACCESS  read-only
    STATUS  mandatory
    DESCRIPTION
        "State of link trouble watch of ring port 1. "
    ::= { axsAxrpGroupEntry 15 }

axsAxrpGroupRingport1LinkState OBJECT-TYPE
    SYNTAX  INTEGER {
                not-monitoring(1),
                normal(2),
                fault(3)
                }
    ACCESS  read-only
    STATUS  mandatory
    DESCRIPTION
        "State of link of ring port 1."
    ::= { axsAxrpGroupEntry 16 }

axsAxrpGroupRingport1LinkKeepaliveReceiveCounts OBJECT-TYPE
    SYNTAX  Counter
    ACCESS  read-only
    STATUS  mandatory
    DESCRIPTION
        "Number of reception frames of link state watch frames of ring port 1. "
    ::= { axsAxrpGroupEntry 17 }

axsAxrpGroupRingport2LinkKeepaliveSend OBJECT-TYPE
    SYNTAX  INTEGER {
                no-config(1),
                enable(2)
                }
    ACCESS  read-only
    STATUS  mandatory
    DESCRIPTION
        "State of transmission of link trouble watch frame of ring port 2."
    ::= { axsAxrpGroupEntry 18 }

axsAxrpGroupRingport2LinkKeepaliveMonitor OBJECT-TYPE
    SYNTAX  INTEGER {
                no-config(1),
                enable(2)
                }
    ACCESS  read-only
    STATUS  mandatory
    DESCRIPTION
        "State of link trouble watch of ring port 2."
    ::= { axsAxrpGroupEntry 19 }

axsAxrpGroupRingport2LinkState OBJECT-TYPE
    SYNTAX  INTEGER {
                not-monitoring(1),
                normal(2),
                fault(3)
                }
    ACCESS  read-only
    STATUS  mandatory
    DESCRIPTION
        "State of link of ring port 2."
    ::= { axsAxrpGroupEntry 20 }

axsAxrpGroupRingport2LinkKeepaliveReceiveCounts OBJECT-TYPE
    SYNTAX  Counter
    ACCESS  read-only
    STATUS  mandatory
    DESCRIPTION
        "Number of reception frames of link state watch frames of ring port 2. "
    ::= { axsAxrpGroupEntry 21 }

axsAxrpGroupMultiFaultDetectionState OBJECT-TYPE
    SYNTAX  INTEGER {
                not-monitoring(1),
                normal(2),
                fault(3)
                }
    ACCESS  read-only
    STATUS  mandatory
    DESCRIPTION
        "Operation and state of multiple fault detection of ring."
    ::= { axsAxrpGroupEntry 22 }

axsAxrpVlanGroupTable OBJECT-TYPE
        SYNTAX  SEQUENCE OF AxsAxrpVlanGroupEntry
        ACCESS  not-accessible
        STATUS  mandatory
        DESCRIPTION
                "The table containing AXRP VLAN group information."
        ::= { axsAxrp  2 }

axsAxrpVlanGroupEntry OBJECT-TYPE
        SYNTAX  AxsAxrpVlanGroupEntry
        ACCESS  not-accessible
        STATUS  mandatory
        DESCRIPTION
                "The list of AXRP VLAN group information."
    INDEX { axsAxrpVlanGroupRingId, axsAxrpVlanGroupId }
        ::= { axsAxrpVlanGroupTable 1 }

        AxsAxrpVlanGroupEntry ::=
                SEQUENCE {
                    axsAxrpVlanGroupRingId                  INTEGER,
                    axsAxrpVlanGroupId                      INTEGER,
                    axsAxrpVlanGroupRingport1               INTEGER,
                    axsAxrpVlanGroupRingport1Role           INTEGER,
                    axsAxrpVlanGroupRingport1OperState      INTEGER,
                    axsAxrpVlanGroupRingport2               INTEGER,
                    axsAxrpVlanGroupRingport2Role           INTEGER,
                    axsAxrpVlanGroupRingport2OperState      INTEGER
		}

axsAxrpVlanGroupRingId OBJECT-TYPE
	SYNTAX  INTEGER
	ACCESS  not-accessible
	STATUS  mandatory
	DESCRIPTION
		"AXRP VLAN ring group number(1~65535)"
	::= { axsAxrpVlanGroupEntry  1 }

axsAxrpVlanGroupId OBJECT-TYPE
	SYNTAX  INTEGER
	ACCESS  not-accessible
	STATUS  mandatory
	DESCRIPTION
		"AXRP VLAN group number(1~8)"
	::= { axsAxrpVlanGroupEntry  2 }

axsAxrpVlanGroupRingport1 OBJECT-TYPE
	SYNTAX  INTEGER
	ACCESS  read-only
	STATUS  mandatory
	DESCRIPTION
		"IfIndex of ring port 1 (port in one where Ifindex is small)"
	::= { axsAxrpVlanGroupEntry 3 }

axsAxrpVlanGroupRingport1Role OBJECT-TYPE
	SYNTAX  INTEGER {
                primary(1),
                secondary(2),
                other(3)
                }
	ACCESS  read-only
	STATUS  mandatory
	DESCRIPTION
		"Role of ring port 1"
	::= { axsAxrpVlanGroupEntry 4 }

axsAxrpVlanGroupRingport1OperState OBJECT-TYPE
	SYNTAX  INTEGER {
                forwarding(1),
                blocking(2),
                other(3),
                down(4)
                }
	ACCESS  read-only
	STATUS  mandatory
	DESCRIPTION
		"Present of ring port 1"
	::= { axsAxrpVlanGroupEntry 5 }

axsAxrpVlanGroupRingport2 OBJECT-TYPE
	SYNTAX  INTEGER
	ACCESS  read-only
	STATUS  mandatory
	DESCRIPTION
		"IfIndex of ring port 2 (port in one where Ifindex is small)"
	::= { axsAxrpVlanGroupEntry 6 }

axsAxrpVlanGroupRingport2Role OBJECT-TYPE
	SYNTAX  INTEGER {
                primary(1),
                secondary(2),
                other(3)
                }
	ACCESS  read-only
	STATUS  mandatory
	DESCRIPTION
		"Role of ring port 2"
	::= { axsAxrpVlanGroupEntry 7 }

axsAxrpVlanGroupRingport2OperState OBJECT-TYPE
	SYNTAX  INTEGER {
                forwarding(1),
                blocking(2),
                other(3),
                down(4)
                }
	ACCESS  read-only
	STATUS  mandatory
	DESCRIPTION
		"Present of ring port 2"
	::= { axsAxrpVlanGroupEntry 8 }

--  axsBootManagement group

axsBootReason  OBJECT-TYPE
	SYNTAX  INTEGER {
		power-on(1),
		reload(2),
		system-fault(3),
		system-stall(4),
		reset(5),
		fail-over(6),
		default-restart(7),
		wake-on-rtc(9),
		wake-on-reset(10)
	      }
	ACCESS  read-only
	STATUS  mandatory
	DESCRIPTION
		"Reason of system start."
	::= { axsBootManagement 1 }

--  axslldp group
--  axslldpConfiguration group

axslldpMessageTxInterval OBJECT-TYPE
	SYNTAX  INTEGER
	ACCESS  read-only
	STATUS  mandatory
	DESCRIPTION
		"LDPDU transmitting interval"
	::= { axslldpConfiguration 1 }

axslldpMessageTxHoldMultiplier OBJECT-TYPE
	SYNTAX  INTEGER
	ACCESS  read-only
	STATUS  mandatory
	DESCRIPTION
		"Time coefficient for contiguity equipment to hold about the LLDP frame which this equipment transmitted"
	::= { axslldpConfiguration 2 }

axslldpPortConfigTable OBJECT-TYPE
	SYNTAX  SEQUENCE OF AxslldpPortConfigEntry
	ACCESS  not-accessible
	STATUS  mandatory
	DESCRIPTION
		"The table about LDPDU transmission"
	::= { axslldpConfiguration 6 }

axslldpPortConfigEntry OBJECT-TYPE
	SYNTAX  AxslldpPortConfigEntry
	ACCESS  not-accessible
	STATUS  mandatory
	DESCRIPTION
		"The entry about LDPDU transmission"
    INDEX { axslldpPortConfigPortNum }
	::= { axslldpPortConfigTable 1 }

	AxslldpPortConfigEntry ::=
		SEQUENCE {
		    axslldpPortConfigPortNum		INTEGER,
		    axslldpPortConfigAdminStatus		INTEGER,
		    axslldpPortConfigTLVsTxEnable	BITS,
		    axslldpPortConfigRowStatus		RowStatus
		}

axslldpPortConfigPortNum OBJECT-TYPE
	SYNTAX  INTEGER
	ACCESS  not-accessible
	STATUS  mandatory
	DESCRIPTION
		"Port discernment index"
	::= {axslldpPortConfigEntry 2 }

axslldpPortConfigAdminStatus OBJECT-TYPE
	SYNTAX  INTEGER {
                                       txOnly(1),
                                       rxOnly(2),
                                       txAndRx(3),
                                       disabled(4)
                        }
	ACCESS  read-only
	STATUS  mandatory
	DESCRIPTION
		"The port state of this equipment about transmission and reception of LDPDU"
	::= {axslldpPortConfigEntry 3 }

axslldpPortConfigTLVsTxEnable OBJECT-TYPE
        SYNTAX  BITS{
                    portDesc(4),
                    sysName(5),
                    sysDesc(6),
                    sysCap(7)
                }
	ACCESS  read-only
	STATUS  mandatory
	DESCRIPTION
		"The TLV state about the port concerned which can be transmitted"
	::= {axslldpPortConfigEntry 4 }

axslldpPortConfigRowStatus OBJECT-TYPE
	SYNTAX  RowStatus
	ACCESS  read-only
	STATUS  mandatory
	DESCRIPTION
		"The state of this entry"
	::= {axslldpPortConfigEntry 5 }

-- axslldpStats group

axslldpStatsTable OBJECT-TYPE
	SYNTAX  SEQUENCE OF AxslldpStatsEntry
	ACCESS  not-accessible
	STATUS  mandatory
	DESCRIPTION
		"The table about LLDP statistics information"
	::= { axslldpStats 1 }

axslldpStatsEntry OBJECT-TYPE
	SYNTAX  AxslldpStatsEntry
	ACCESS  not-accessible
	STATUS  mandatory
	DESCRIPTION
		"The Entry about LLDP statistics information"
    INDEX { axslldpStatsPortNum }
	::= { axslldpStatsTable 1 }

	AxslldpStatsEntry ::=
		SEQUENCE {
		    axslldpStatsPortNum			INTEGER,
		    axslldpStatsOperStatus		INTEGER,
		    axslldpStatsFramesInErrors		Counter,
		    axslldpStatsFramesInTotal		Counter,
		    axslldpStatsFramesOutTotal		Counter,
		    axslldpStatsTLVsInErrors		Counter,
		    axslldpStatsTLVsDiscardedTotal	Counter
		}

axslldpStatsPortNum OBJECT-TYPE
	SYNTAX  INTEGER
	ACCESS  not-accessible
	STATUS  mandatory
	DESCRIPTION
		"Port discernment index"
	::= {axslldpStatsEntry 2 }

axslldpStatsOperStatus OBJECT-TYPE
	SYNTAX  INTEGER
	ACCESS  read-only
	STATUS  mandatory
	DESCRIPTION
		"The employment state about the port concerned"
	::= {axslldpStatsEntry 3 }

axslldpStatsFramesInErrors OBJECT-TYPE
	SYNTAX  Counter
	ACCESS  read-only
	STATUS  mandatory
	DESCRIPTION
		"The number of inaccurate LDPDU reception about the port concerned"
	::= {axslldpStatsEntry 4 }

axslldpStatsFramesInTotal OBJECT-TYPE
	SYNTAX  Counter
	ACCESS  read-only
	STATUS  mandatory
	DESCRIPTION
		"The total number of LDPDU reception about the port concerned"
	::= {axslldpStatsEntry 5 }

axslldpStatsFramesOutTotal OBJECT-TYPE
	SYNTAX  Counter
	ACCESS  read-only
	STATUS  mandatory
	DESCRIPTION
		"The total number of LDPDU transmission about the port concerned"
	::= {axslldpStatsEntry 6 }

axslldpStatsTLVsInErrors OBJECT-TYPE
	SYNTAX  Counter
	ACCESS  read-only
	STATUS  mandatory
	DESCRIPTION
		"The number of inaccurate TLV reception about the port concerned"
	::= {axslldpStatsEntry 7 }

axslldpStatsTLVsDiscardedTotal OBJECT-TYPE
	SYNTAX  Counter
	ACCESS  read-only
	STATUS  mandatory
	DESCRIPTION
		"The total abandonment TLV number about the port concerned"
	::= {axslldpStatsEntry 8 }

-- axslldpLocalSystemData group

axslldpLocChassisType OBJECT-TYPE
	SYNTAX  INTEGER {
                                entPhysicalAlias(1),
                                ifAlias(2),
                                portEntPhysicalAlias(3),
                                backplaneEntPhysicalAlias(4),
                                macAddress(5),
                                networkAddress(6)
                        }
	ACCESS  read-only
	STATUS  mandatory
	DESCRIPTION
		"The chassis type about this equipment"
	::= {axslldpLocalSystemData 1 }

axslldpLocChassisId OBJECT-TYPE
	SYNTAX  OCTET STRING 
	ACCESS  read-only
	STATUS  mandatory
	DESCRIPTION
		"The chassis ID about this equipment"
	::= {axslldpLocalSystemData 2 }

axslldpLocSysName OBJECT-TYPE
	SYNTAX  OCTET STRING
	ACCESS  read-only
	STATUS  mandatory
	DESCRIPTION
		"The system name about this equipment"
	::= {axslldpLocalSystemData 3 }

axslldpLocSysDesc OBJECT-TYPE
	SYNTAX  DisplayString
	ACCESS  read-only
	STATUS  mandatory
	DESCRIPTION
		"System information about this equipment"
	::= {axslldpLocalSystemData 4 }

axslldpLocPortTable OBJECT-TYPE
	SYNTAX  SEQUENCE OF AxslldpLocPortEntry
	ACCESS  not-accessible
	STATUS  mandatory
	DESCRIPTION
		"The table about the port of this equipment"
	::= { axslldpLocalSystemData 7 }

axslldpLocPortEntry OBJECT-TYPE
	SYNTAX  AxslldpLocPortEntry
	ACCESS  not-accessible
	STATUS  mandatory
	DESCRIPTION
		"The entry about the port of this equipment"
    INDEX { axslldpLocPortNum }
	::= { axslldpLocPortTable 1 }

	AxslldpLocPortEntry ::=
		SEQUENCE {
		    axslldpLocPortNum		INTEGER,
		    axslldpLocPortType		INTEGER,
		    axslldpLocPortId		OCTET STRING,
		    axslldpLocPortDesc		OCTET STRING
		}

axslldpLocPortNum OBJECT-TYPE
	SYNTAX  INTEGER
	ACCESS  not-accessible
	STATUS  mandatory
	DESCRIPTION
		"Port discernment index"
	::= {axslldpLocPortEntry 1 }

axslldpLocPortType OBJECT-TYPE
	SYNTAX  INTEGER {
                             ifAlias(1),
                             portEntPhysicalAlias(2),
                             backplaneEntPhysicalAlias(3),
                             macAddress(4),
                             networkAddress(5),
                             local(6)
                        }
	ACCESS  read-only
	STATUS  mandatory
	DESCRIPTION
		"The port type about the port concerned of this equipment"
	::= {axslldpLocPortEntry 2 }

axslldpLocPortId OBJECT-TYPE
	SYNTAX  OCTET STRING
	ACCESS  read-only
	STATUS  mandatory
	DESCRIPTION
		"The port ID about the port concerned of this equipment"
	::= {axslldpLocPortEntry 3 }

axslldpLocPortDesc OBJECT-TYPE
	SYNTAX  OCTET STRING
	ACCESS  read-only
	STATUS  mandatory
	DESCRIPTION
		"Port information about the port concerned of this equipment"
	::= {axslldpLocPortEntry 4 }

-- axslldpRemoteSystemData group

axslldpRemTable OBJECT-TYPE
	SYNTAX  SEQUENCE OF AxslldpRemEntry
	ACCESS  not-accessible
	STATUS  mandatory
	DESCRIPTION
		"The table about contiguity equipment"
	::= { axslldpRemoteSystemData 1 }

axslldpRemEntry OBJECT-TYPE
	SYNTAX  AxslldpRemEntry
	ACCESS  not-accessible
	STATUS  mandatory
	DESCRIPTION
		"The entry about contiguity equipment"
    INDEX { axslldpRemLocalPortNum,axslldpRemIndex }
	::= { axslldpRemTable 1 }

	AxslldpRemEntry ::=
		SEQUENCE {
		    axslldpRemLocalPortNum		INTEGER,
		    axslldpRemIndex			INTEGER,
		    axslldpRemRemoteChassisType		INTEGER,
		    axslldpRemRemoteChassis		OCTET STRING,
		    axslldpRemRemotePortType		INTEGER,
		    axslldpRemRemotePort			OCTET STRING,
		    axslldpRemPortDesc			OCTET STRING,
		    axslldpRemSysName			OCTET STRING,
		    axslldpRemSysDesc			OCTET STRING
		}

axslldpRemLocalPortNum OBJECT-TYPE
	SYNTAX  INTEGER
	ACCESS  not-accessible
	STATUS  mandatory
	DESCRIPTION
		"The discernment index of the port of this equipment which received the information about contiguity equipment"
	::= {axslldpRemEntry 2 }

axslldpRemIndex OBJECT-TYPE
	SYNTAX  INTEGER
	ACCESS  not-accessible
	STATUS  mandatory
	DESCRIPTION
		"The index about contiguity equipment"
	::= {axslldpRemEntry 3 }

axslldpRemRemoteChassisType OBJECT-TYPE
	SYNTAX  INTEGER {
                                      entPhysicalAlias(1),
                                      ifAlias(2),
                                      portEntPhysicalAlias(3),
                                      backplaneEntPhysicalAlias(4),
                                      macAddress(5),
                                      networkAddress(6)
                        }
	ACCESS  read-only
	STATUS  mandatory
	DESCRIPTION
		"The chassis type about contiguity equipment"
	::= {axslldpRemEntry 4 }

axslldpRemRemoteChassis OBJECT-TYPE
	SYNTAX  OCTET STRING
	ACCESS  read-only
	STATUS  mandatory
	DESCRIPTION
		"The chassis ID about contiguity equipment"
	::= {axslldpRemEntry 5 }

axslldpRemRemotePortType OBJECT-TYPE
	SYNTAX  INTEGER {
                                   ifAlias(1),
                                   portEntPhysicalAlias(2),
                                   backplaneEntPhysicalAlias(3),
                                   macAddress(4),
                                   networkAddress(5),
                                   local(6)
                        }
	ACCESS  read-only
	STATUS  mandatory
	DESCRIPTION
		"The port type about the port concerned of contiguity equipment"
	::= {axslldpRemEntry 6 }

axslldpRemRemotePort OBJECT-TYPE
	SYNTAX  OCTET STRING
	ACCESS  read-only
	STATUS  mandatory
	DESCRIPTION
		"The port ID about the port concerned of contiguity equipment"
	::= {axslldpRemEntry 7 }

axslldpRemPortDesc OBJECT-TYPE
	SYNTAX  OCTET STRING
	ACCESS  read-only
	STATUS  mandatory
	DESCRIPTION
		"Information about the port concerned of contiguity equipment"
	::= {axslldpRemEntry 8 }

axslldpRemSysName OBJECT-TYPE
	SYNTAX  OCTET STRING
	ACCESS  read-only
	STATUS  mandatory
	DESCRIPTION
		"The system name about contiguity equipment"
	::= {axslldpRemEntry 9 }

axslldpRemSysDesc OBJECT-TYPE
	SYNTAX  OCTET STRING
	ACCESS  read-only
	STATUS  mandatory
	DESCRIPTION
		"System information about contiguity equipment"
	::= {axslldpRemEntry 10 }

axslldpRemOriginInfoTable OBJECT-TYPE
	SYNTAX  SEQUENCE OF AxslldpRemOriginInfoEntry
	ACCESS  not-accessible
	STATUS  mandatory
	DESCRIPTION
		"The table about original with AlaxalA networks TLV of contiguity equipment"
	::= { axslldpRemoteOriginInfoData 1 }

axslldpRemOriginInfoEntry OBJECT-TYPE
	SYNTAX  AxslldpRemOriginInfoEntry
	ACCESS  not-accessible
	STATUS  mandatory
	DESCRIPTION
		"The entry about original with AlaxalA networks TLV of contiguity equipment"
    INDEX { axslldpRemOriginInfoPortNum,axslldpRemOriginInfoIndex }
	::= { axslldpRemOriginInfoTable 1 }

	AxslldpRemOriginInfoEntry ::=
		SEQUENCE {
		    axslldpRemOriginInfoPortNum		INTEGER,
		    axslldpRemOriginInfoIndex		INTEGER,
		    axslldpRemOriginInfoLowerVlanList	OCTET STRING,
		    axslldpRemOriginInfoHigherVlanList	OCTET STRING,
		    axslldpRemOriginInfoIPv4Address	OCTET STRING,
		    axslldpRemOriginInfoIPv4PortType	INTEGER,
		    axslldpRemOriginInfoIPv4VlanId	INTEGER,
		    axslldpRemOriginInfoIPv6Address	OCTET STRING,
		    axslldpRemOriginInfoIPv6PortType	INTEGER,
		    axslldpRemOriginInfoIPv6VlanId	INTEGER
		}

axslldpRemOriginInfoPortNum OBJECT-TYPE
	SYNTAX  INTEGER
	ACCESS  not-accessible
	STATUS  mandatory
	DESCRIPTION
		"The discernment index of the port of this equipment which received the information about contiguity equipment."
	::= {axslldpRemOriginInfoEntry 1 }

axslldpRemOriginInfoIndex OBJECT-TYPE
	SYNTAX  INTEGER
	ACCESS  not-accessible
	STATUS  mandatory
	DESCRIPTION
		"The index about contiguity equipment"
	::= {axslldpRemOriginInfoEntry 2 }

axslldpRemOriginInfoLowerVlanList OBJECT-TYPE
	SYNTAX  OCTET STRING
	ACCESS  read-only
	STATUS  mandatory
	DESCRIPTION
		"What expressed effective VLAN ID by the bit map by VLAN 1-2047 in the port concerned of contiguity equipment"
	::= {axslldpRemOriginInfoEntry 3 }

axslldpRemOriginInfoHigherVlanList OBJECT-TYPE
	SYNTAX  OCTET STRING
	ACCESS  read-only
	STATUS  mandatory
	DESCRIPTION
		"What expressed effective VLAN ID by the bit map by VLAN 2048-4095 in the port concerned of contiguity equipment"
	::= {axslldpRemOriginInfoEntry 4 }

axslldpRemOriginInfoIPv4Address OBJECT-TYPE
	SYNTAX  OCTET STRING
	ACCESS  read-only
	STATUS  mandatory
	DESCRIPTION
		"IPv4 address given to the port concerned of contiguity equipment"
	::= {axslldpRemOriginInfoEntry 5 }

axslldpRemOriginInfoIPv4PortType OBJECT-TYPE
	SYNTAX  INTEGER
	ACCESS  read-only
	STATUS  mandatory
	DESCRIPTION
		"Port classification of the port of contiguity equipment concerned"
	::= {axslldpRemOriginInfoEntry 6 }

axslldpRemOriginInfoIPv4VlanId OBJECT-TYPE
	SYNTAX  INTEGER
	ACCESS  read-only
	STATUS  mandatory
	DESCRIPTION
		"The smallest thing among VLAN ID to which IPv4 address is given"
	::= {axslldpRemOriginInfoEntry 7 }

axslldpRemOriginInfoIPv6Address OBJECT-TYPE
	SYNTAX  OCTET STRING
	ACCESS  read-only
	STATUS  mandatory
	DESCRIPTION
		"The IPv6 address given to the port concerned of contiguity equipment"
	::= {axslldpRemOriginInfoEntry 8 }

axslldpRemOriginInfoIPv6PortType OBJECT-TYPE
	SYNTAX  INTEGER
	ACCESS  read-only
	STATUS  mandatory
	DESCRIPTION
		"Port classification of the port of contiguity equipment concerned"
	::= {axslldpRemOriginInfoEntry 9 }

axslldpRemOriginInfoIPv6VlanId OBJECT-TYPE
	SYNTAX  INTEGER
	ACCESS  read-only
	STATUS  mandatory
	DESCRIPTION
		"The smallest thing among VLAN ID to which the IPv6 address is given"
	::= {axslldpRemOriginInfoEntry 10 }

-- axsPconMIB group
-- axsPconModuleData group
    axsPconModuleTable OBJECT-TYPE
        SYNTAX    SEQUENCE OF AxsPconModuleEntry
        ACCESS    not-accessible
        STATUS    mandatory
        DESCRIPTION
                  "A table containing electric power control information of module."
        ::= { axsPconModuleData 1 }

    axsPconModuleEntry OBJECT-TYPE
        SYNTAX    AxsPconModuleEntry
        ACCESS    not-accessible
        STATUS    mandatory
        DESCRIPTION
                  "An entry containing electric power control information of module."
        INDEX  { axsPconModuleIndex }
        ::= { axsPconModuleTable 1 }
        
    AxsPconModuleEntry ::= SEQUENCE {
        axsPconModuleIndex          Integer32,
        axsPconModuleType           INTEGER,
        axsPconModuleSlotNo         Integer32,
        axsPconModuleDescr          DisplayString,
        axsPconModuleStatus         INTEGER,
        axsPconModuleMode           INTEGER
    }

    axsPconModuleIndex OBJECT-TYPE
        SYNTAX    Integer32 (1..2147483647)
        ACCESS    not-accessible
        STATUS    mandatory
        DESCRIPTION
                  "A unique value for each module contained by the network device."
        ::= { axsPconModuleEntry 1 }

    axsPconModuleType OBJECT-TYPE
        SYNTAX    INTEGER {
                      all(1),
                      chassis(2),
                      bcu(3),
                      csu(4),
                      msu(5),
                      bsu(6),
                      nif(7)
                  }
        ACCESS    read-only
        STATUS    mandatory
        DESCRIPTION
                  "An indication of the type of module."
        ::= { axsPconModuleEntry 2 }
        
    axsPconModuleSlotNo OBJECT-TYPE
        SYNTAX    Integer32
        ACCESS    read-only
        STATUS    mandatory
        DESCRIPTION
                  "Position information of the module slots."
        ::= { axsPconModuleEntry 3 }
        
    axsPconModuleDescr OBJECT-TYPE
        SYNTAX    DisplayString
        ACCESS    read-only
        STATUS    mandatory
        DESCRIPTION
                  "The textual description of module."
        ::= { axsPconModuleEntry 4 }
        
    axsPconModuleStatus OBJECT-TYPE
        SYNTAX    INTEGER {
                      unsupported(-1),
                      disconnected(0),
                      active(1),
                      standby(2),
                      down(3)
                  }
        ACCESS    read-only
        STATUS    mandatory
        DESCRIPTION
                  "The module status of this axsPconModuleEntry."
        ::= { axsPconModuleEntry 5 }
        
    axsPconModuleMode OBJECT-TYPE
        SYNTAX    INTEGER {
                      unsupported(-1),
                      other(0),
                      normal(1),
                      saving-mode1(2),
                      saving-mode2(3),
                      saving(4),
                      changing(5)
                  }
        ACCESS    read-only
        STATUS    mandatory
        DESCRIPTION
                  "The module mode of this axsPconModuleEntry."
        ::= { axsPconModuleEntry 6 }
        
-- axsPconPowerCon group

    axsPconPowerConTable OBJECT-TYPE
        SYNTAX    SEQUENCE OF AxsPconPowerConEntry
        ACCESS    not-accessible
        STATUS    mandatory
        DESCRIPTION
                  "The power consumption information table."
        ::= { axsPconPowerCon 1 }
        
    axsPconPowerConEntry OBJECT-TYPE
        SYNTAX    AxsPconPowerConEntry
        ACCESS    not-accessible
        STATUS    mandatory
        DESCRIPTION
                  "The power consumption information entry."
        INDEX  { axsPconModuleIndex }
        ::= { axsPconPowerConTable 1 }

    AxsPconPowerConEntry ::= SEQUENCE {
        axsPconPowerConMaxPower          Gauge,
        axsPconPowerConPowerConsumption  Counter64,
        axsPconPowerConPowerMeter        Gauge
    }
        
    axsPconPowerConMaxPower OBJECT-TYPE
        SYNTAX    Gauge
        ACCESS    read-only
        STATUS    mandatory
        DESCRIPTION
                  "The maximum electric power of module."
        ::= { axsPconPowerConEntry 1 }
        
    axsPconPowerConPowerConsumption OBJECT-TYPE
        SYNTAX    Counter64
        ACCESS    read-only
        STATUS    mandatory
        DESCRIPTION
                  "The power consumption of module."
        ::= { axsPconPowerConEntry 2 }
        
    axsPconPowerConPowerMeter OBJECT-TYPE
        SYNTAX    Gauge
        ACCESS    read-only
        STATUS    mandatory
        DESCRIPTION
                  "The power meter of module."
        ::= { axsPconPowerConEntry 3 }

-- axsPconTraffic group

    axsPconTrafficTable OBJECT-TYPE
        SYNTAX    SEQUENCE OF AxsPconTrafficEntry
        ACCESS    not-accessible
        STATUS    mandatory
        DESCRIPTION
                  "The Traffic information table."
        ::= { axsPconTraffic 1 }
        
    axsPconTrafficEntry OBJECT-TYPE
        SYNTAX    AxsPconTrafficEntry
        ACCESS    not-accessible
        STATUS    mandatory
        DESCRIPTION
                  "The Traffic information entry."
        INDEX  { axsPconModuleIndex }
        ::= { axsPconTrafficTable 1 }
        
    AxsPconTrafficEntry ::= SEQUENCE {
        axsPconTrafficMaxTransferCapacity     Gauge,
        axsPconTrafficTotalTransferCapacity   Gauge,
        axsPconTrafficInOctets                Counter64,
        axsPconTrafficOutOctets               Counter64,
        axsPconTrafficInPkts                  Counter64,
        axsPconTrafficOutPkts                 Counter64,
        axsPconTrafficCapacityOctets          Counter64,
        axsPconTrafficInPeakOctetsRate        Gauge,
        axsPconTrafficPeakTransferCapacity    Gauge,
        axsPconTrafficInDiscPkts              Counter64
    }

    axsPconTrafficMaxTransferCapacity OBJECT-TYPE
        SYNTAX    Gauge
        ACCESS    read-only
        STATUS    mandatory
        DESCRIPTION
                  "The maximum transfer capacity."
        ::= { axsPconTrafficEntry 1 }
        
    axsPconTrafficTotalTransferCapacity OBJECT-TYPE
        SYNTAX    Gauge
        ACCESS    read-only
        STATUS    mandatory
        DESCRIPTION
                  "The total transfer capacity."
        ::= { axsPconTrafficEntry 2 }
        
    axsPconTrafficInOctets OBJECT-TYPE
        SYNTAX    Counter64
        ACCESS    read-only
        STATUS    mandatory
        DESCRIPTION
                  "The total number of octets that received on this module."
        ::= { axsPconTrafficEntry 3 }
        
    axsPconTrafficOutOctets OBJECT-TYPE
        SYNTAX    Counter64
        ACCESS    read-only
        STATUS    mandatory
        DESCRIPTION
                  "The total number of octets transmitted out from this module."
        ::= { axsPconTrafficEntry 4 }
        
    axsPconTrafficInPkts OBJECT-TYPE
        SYNTAX    Counter64
        ACCESS    read-only
        STATUS    mandatory
        DESCRIPTION
                  "The total number of packets that received on this module."
        ::= { axsPconTrafficEntry 5 }
        
    axsPconTrafficOutPkts OBJECT-TYPE
        SYNTAX    Counter64
        ACCESS    read-only
        STATUS    mandatory
        DESCRIPTION
                  "The total number of packets transmitted out from this module."
        ::= { axsPconTrafficEntry 6 }
        
    axsPconTrafficCapacityOctets OBJECT-TYPE
        SYNTAX    Counter64
        ACCESS    read-only
        STATUS    mandatory
        DESCRIPTION
                  "The accumulation octets capacity that can be received on this module."
        ::= { axsPconTrafficEntry 7 }
        
    axsPconTrafficInPeakOctetsRate OBJECT-TYPE
        SYNTAX    Gauge
        ACCESS    read-only
        STATUS    mandatory
        DESCRIPTION
                  "The peak rate of octets that received on this module."
        ::= { axsPconTrafficEntry 8 }
        
    axsPconTrafficPeakTransferCapacity OBJECT-TYPE
        SYNTAX    Gauge
        ACCESS    read-only
        STATUS    mandatory
        DESCRIPTION
                  "The rate of margin when incoming traffic is peak."
        ::= { axsPconTrafficEntry 9 }
        
    axsPconTrafficInDiscPkts OBJECT-TYPE
        SYNTAX    Counter64
        ACCESS    read-only
        STATUS    mandatory
        DESCRIPTION
                  "The total number of discarded packets on this module."
        ::= { axsPconTrafficEntry 10 }

-- axsVxlan group
-- axsVxlanStatsVniTable group

    axsVxlanStatsVniTable OBJECT-TYPE
        SYNTAX    SEQUENCE OF AxsVxlanStatsVniEntry
        ACCESS    not-accessible
        STATUS    mandatory
        DESCRIPTION
                  "A table containing statistics for VXLAN."
        ::= { axsVxlan 1 }

    axsVxlanStatsVniEntry OBJECT-TYPE
        SYNTAX    AxsVxlanStatsVniEntry
        ACCESS    not-accessible
        STATUS    mandatory
        DESCRIPTION
                  "An entry containing statistics for VXLAN."
        INDEX  { axsChassisIndex, axsVniIndex }
        ::= { axsVxlanStatsVniTable 1 }

    AxsVxlanStatsVniEntry ::= SEQUENCE {
            axsChassisIndex               INTEGER,
            axsVniIndex                   VniIndex,
            axsVxlanStatsVniEncapPackets  Counter32,
            axsVxlanStatsVniEncapOctets   Counter64,
            axsVxlanStatsVniDecapPackets  Counter32,
            axsVxlanStatsVniDecapOctets   Counter64,
            axsVxlanStatsVniAcsacsPackets Counter32,
            axsVxlanStatsVniAcsacsOctets  Counter64
        }

    axsChassisIndex OBJECT-TYPE
        SYNTAX    INTEGER
        ACCESS    not-accessible
        STATUS    mandatory
        DESCRIPTION
                  "The value of this object is switch number."
        ::= { axsVxlanStatsVniEntry 1 }

    axsVniIndex OBJECT-TYPE
        SYNTAX    VniIndex
        ACCESS    read-only
        STATUS    mandatory
        DESCRIPTION
                  "The value of this object is VNI ID."
        ::= { axsVxlanStatsVniEntry 2 }

    axsVxlanStatsVniEncapPackets OBJECT-TYPE
        SYNTAX    Counter32
        ACCESS    read-only
        STATUS    mandatory
        DESCRIPTION
                  "The number of encapsulated packet of VNI."
        ::= { axsVxlanStatsVniEntry 3 }

    axsVxlanStatsVniEncapOctets OBJECT-TYPE
        SYNTAX    Counter64
        ACCESS    read-only
        STATUS    mandatory
        DESCRIPTION
                  "The number of encapsulated octet of VNI."
        ::= { axsVxlanStatsVniEntry 4 }

    axsVxlanStatsVniDecapPackets OBJECT-TYPE
        SYNTAX    Counter32
        ACCESS    read-only
        STATUS    mandatory
        DESCRIPTION
                  "The number of decapsulated packet of VNI."
        ::= { axsVxlanStatsVniEntry 5 }

    axsVxlanStatsVniDecapOctets OBJECT-TYPE
        SYNTAX    Counter64
        ACCESS    read-only
        STATUS    mandatory
        DESCRIPTION
                  "The number of decapsulated octet of VNI."
        ::= { axsVxlanStatsVniEntry 6 }

    axsVxlanStatsVniAcsacsPackets OBJECT-TYPE
        SYNTAX    Counter32
        ACCESS    read-only
        STATUS    mandatory
        DESCRIPTION
                  "The number of access port-to-port communication packet of VNI."
        ::= { axsVxlanStatsVniEntry 7 }

    axsVxlanStatsVniAcsacsOctets OBJECT-TYPE
        SYNTAX    Counter64
        ACCESS    read-only
        STATUS    mandatory
        DESCRIPTION
                  "The number of access port-to-port communication octet of VNI."
        ::= { axsVxlanStatsVniEntry 8 }

-- axsVxlanStatsTunnelTable group

    axsVxlanStatsTunnelTable OBJECT-TYPE
        SYNTAX    SEQUENCE OF AxsVxlanStatsTunnelEntry
        ACCESS    not-accessible
        STATUS    mandatory
        DESCRIPTION
                  "A table containing statistics for tunnel of VXLAN."
        ::= { axsVxlan 2 }

    axsVxlanStatsTunnelEntry OBJECT-TYPE
        SYNTAX    AxsVxlanStatsTunnelEntry
        ACCESS    not-accessible
        STATUS    mandatory
        DESCRIPTION
                  "An entry containing statistics for tunnel of VXLAN."
        INDEX  { axsChassisIndex, axsTunnelAddress }
        ::= { axsVxlanStatsTunnelTable 1 }

    AxsVxlanStatsTunnelEntry ::= SEQUENCE {
            axsTunnelAddress                IpAddress,
            axsVxlanStatsTunnelEncapPackets Counter32,
            axsVxlanStatsTunnelEncapOctets  Counter64,
            axsVxlanStatsTunnelDecapPackets Counter32,
            axsVxlanStatsTunnelDecapOctets  Counter64
        }

    axsTunnelAddress OBJECT-TYPE
        SYNTAX    IpAddress
        ACCESS    read-only
        STATUS    mandatory
        DESCRIPTION
                  "The value of this object is the destination address of the tunnel interface."
        ::= { axsVxlanStatsTunnelEntry 1 }

    axsVxlanStatsTunnelEncapPackets OBJECT-TYPE
        SYNTAX    Counter32
        ACCESS    read-only
        STATUS    mandatory
        DESCRIPTION
                  "The number of encapsulated packet for tunnel of VXLAN."
        ::= { axsVxlanStatsTunnelEntry 2 }

    axsVxlanStatsTunnelEncapOctets OBJECT-TYPE
        SYNTAX    Counter64
        ACCESS    read-only
        STATUS    mandatory
        DESCRIPTION
                  "The number of encapsulated octet for tunnel of VXLAN."
        ::= { axsVxlanStatsTunnelEntry 3 }

    axsVxlanStatsTunnelDecapPackets OBJECT-TYPE
        SYNTAX    Counter32
        ACCESS    read-only
        STATUS    mandatory
        DESCRIPTION
                  "The number of decapsulated packet for tunnel of VXLAN."
        ::= { axsVxlanStatsTunnelEntry 4 }

    axsVxlanStatsTunnelDecapOctets OBJECT-TYPE
        SYNTAX    Counter64
        ACCESS    read-only
        STATUS    mandatory
        DESCRIPTION
                  "The number of decapsulated octet for tunnel of VXLAN."
        ::= { axsVxlanStatsTunnelEntry 5 }

-- ax3660sSwitch group

ax3660sModelType OBJECT-TYPE
    SYNTAX  INTEGER {
        model-AX3660S-24T4XW(2400),
        model-AX3660S-48T4XW(2401),
        model-AX3660S-48XT4QW(2402),
        model-AX3660S-48X4QW(2403),
        model-AX3660S-24T4X(2404),
        model-AX3660S-24S8XW(2405),
        model-AX3660S-16S4XW(2406),
        model-AX3660S-24X4QW(2407)
    }
    ACCESS  read-only
    STATUS  mandatory
    DESCRIPTION
        "Model type of this system."
    ::= { ax3660sSwitch 1 }

ax3660sSoftwareName OBJECT-TYPE
    SYNTAX  DisplayString (SIZE (0..16))
    ACCESS  read-only
    STATUS  mandatory
    DESCRIPTION
        "Software name of this system."
    ::= { ax3660sSoftware 1 }

ax3660sSoftwareAbbreviation OBJECT-TYPE
    SYNTAX  DisplayString (SIZE (0..36))
    ACCESS  read-only
    STATUS  mandatory
    DESCRIPTION
        "System software abbreviation."
    ::= { ax3660sSoftware 2 }

ax3660sSoftwareVersion OBJECT-TYPE
    SYNTAX  DisplayString (SIZE (0..16))
    ACCESS  read-only
    STATUS  mandatory
    DESCRIPTION
        "System software version."
    ::= { ax3660sSoftware 3 }

ax3660sSystemMsgText OBJECT-TYPE
    SYNTAX  DisplayString (SIZE (0..256))
    ACCESS  read-only
    STATUS  mandatory
    DESCRIPTION
        "The text of the system log message.For information about this code,
        see:  Operator's Manual. "
    ::= { ax3660sSystemMsg 1 }

ax3660sSystemMsgType OBJECT-TYPE
    SYNTAX  OCTET STRING (SIZE (1))
    ACCESS  read-only
    STATUS  mandatory
    DESCRIPTION
        "The event type. For information about this code, see:  Operator's Manual."
    ::= { ax3660sSystemMsg 2 }

ax3660sSystemMsgTimeStamp OBJECT-TYPE
    SYNTAX  DisplayString (SIZE (0..14))
    ACCESS  read-only
    STATUS  mandatory
    DESCRIPTION
        "The time that event occured. And that is expressed as type of
        MM/DD hh:mm:ss
            MM:month(01-12)
            DD:day(01-31)
            hh:hour(00-23)
            mm:minute(00-59)
            ss:second(00-59)
        Insert space between DD and hh."
    ::= { ax3660sSystemMsg 3 }

ax3660sSystemMsgLevel OBJECT-TYPE
    SYNTAX  OCTET STRING (SIZE (1))
    ACCESS  read-only
    STATUS  mandatory
    DESCRIPTION
        "The newest system message log level.For information about this code,
        see:  Operator's Manual. "
    ::= { ax3660sSystemMsg 4 }

ax3660sSystemMsgEventPoint OBJECT-TYPE
    SYNTAX  DisplayString (SIZE (0..8))
    ACCESS  read-only
    STATUS  mandatory
    DESCRIPTION
        "The code of part that system message error occured. For information
        about this code,see:  Operator's Manual. "
    ::= { ax3660sSystemMsg 5 }

ax3660sSystemMsgEventInterfaceID OBJECT-TYPE
    SYNTAX  DisplayString (SIZE (0..40))
    ACCESS  read-only
    STATUS  mandatory
    DESCRIPTION
        "Interface identification of system messages. For information
        about this code,see:  Operator's Manual."
    ::= { ax3660sSystemMsg 6 }

ax3660sSystemMsgEventCode OBJECT-TYPE
    SYNTAX  OCTET STRING (SIZE (4))
    ACCESS  read-only
    STATUS  mandatory
    DESCRIPTION
        "Event kind code of system messages. For information about this code,
        see:  Operator's Manual. "
    ::= { ax3660sSystemMsg 7 }

ax3660sSystemMsgAdditionalCode OBJECT-TYPE
    SYNTAX  OCTET STRING (SIZE (6))
    ACCESS  read-only
    STATUS  mandatory
    DESCRIPTION
        "Additional code of system messages. For information about this code,
        see:  Operator's Manual. "
    ::= { ax3660sSystemMsg 8 }

ax3660sSnmpSendReceiveSize OBJECT-TYPE
    SYNTAX  INTEGER
    ACCESS  read-only
    STATUS  mandatory
    DESCRIPTION
        "SNMP packet data size in Manager-to-Agent communication. The value is
        displayed in bytes."
    ::= { ax3660sSnmpAgent 1 }

ax3660sSnmpReceiveDelay OBJECT-TYPE
    SYNTAX  INTEGER
    ACCESS  read-only
    STATUS  mandatory
    DESCRIPTION
        "A recommendable interval to receive packets from Manager.The value is
        displayed in milliseconds."
    ::= { ax3660sSnmpAgent 2 }

ax3660sSnmpContinuousSend OBJECT-TYPE
    SYNTAX  INTEGER
    ACCESS  read-only
    STATUS  mandatory
    DESCRIPTION
        "Number of times that is recommendable continuous transmission
        packets."
    ::= { ax3660sSnmpAgent 3 }

ax3660sSnmpObjectMaxNumber OBJECT-TYPE
    SYNTAX  INTEGER
    ACCESS  read-only
    STATUS  mandatory
    DESCRIPTION
        "Max number of objects that contain SNMP packet."
    ::= { ax3660sSnmpAgent 4 }

ax3660sLicenseNumber OBJECT-TYPE
    SYNTAX  INTEGER
    ACCESS  read-only
    STATUS  mandatory
    DESCRIPTION
        "The number of the configured license serial numbers."
    ::= { ax3660sLicense 1 }

ax3660sLicenseTable OBJECT-TYPE
    SYNTAX  SEQUENCE OF Ax3660sLicenseTableEntry
    ACCESS  not-accessible
    STATUS  mandatory
    DESCRIPTION
        "The table containing the license information."
    ::= { ax3660sLicense 2 }

ax3660sLicenseEntry OBJECT-TYPE
    SYNTAX  Ax3660sLicenseTableEntry
    ACCESS  not-accessible
    STATUS  mandatory
    DESCRIPTION
        "The entry of license information."
    INDEX   { ax3660sLicenseIndex }
    ::= { ax3660sLicenseTable 1 }

    Ax3660sLicenseTableEntry ::= SEQUENCE {
        ax3660sLicenseIndex         INTEGER,
        ax3660sLicenseSerialNumber  DisplayString,
        ax3660sLicenseOptionNumber  INTEGER
    }

ax3660sLicenseIndex OBJECT-TYPE
    SYNTAX  INTEGER
    ACCESS  not-accessible
    STATUS  mandatory
    DESCRIPTION
        "The unique index number given for each serial number. The number is from 1 to ax3660sLicenseNumber."
    ::= { ax3660sLicenseEntry 1 }

ax3660sLicenseSerialNumber OBJECT-TYPE
    SYNTAX  DisplayString 
    ACCESS  read-only
    STATUS  mandatory
    DESCRIPTION
        "The serial number."
    ::= { ax3660sLicenseEntry 2 }

ax3660sLicenseOptionNumber OBJECT-TYPE
    SYNTAX  INTEGER 
    ACCESS  read-only
    STATUS  mandatory
    DESCRIPTION
        "The number of option licenses associated with the serial number."
    ::= { ax3660sLicenseEntry 3 }

ax3660sLicenseOptionTable OBJECT-TYPE
    SYNTAX  SEQUENCE OF Ax3660sLicenseOptionTableEntry
    ACCESS  not-accessible
    STATUS  mandatory
    DESCRIPTION
        "The table containing option licenses information associated with the serial number."
    ::= { ax3660sLicense 3 }

ax3660sLicenseOptionEntry OBJECT-TYPE
    SYNTAX  Ax3660sLicenseOptionTableEntry
    ACCESS  not-accessible
    STATUS  mandatory
    DESCRIPTION
        "The entry of the option license information associated with the serial number."
    INDEX   {
        ax3660sLicenseOptionIndex,
        ax3660sLicenseOptionNumberIndex
    }
    ::= { ax3660sLicenseOptionTable 1 }

    Ax3660sLicenseOptionTableEntry ::= SEQUENCE {
        ax3660sLicenseOptionIndex                 INTEGER,
        ax3660sLicenseOptionNumberIndex           INTEGER,
        ax3660sLicenseOptionSoftwareName          DisplayString,
        ax3660sLicenseOptionSoftwareAbbreviation  DisplayString
    }

ax3660sLicenseOptionIndex OBJECT-TYPE
    SYNTAX  INTEGER
    ACCESS  not-accessible
    STATUS  mandatory
    DESCRIPTION
        "The unique index number given for each serial number. The same number as ax3660sLicenseIndex."
    ::= { ax3660sLicenseOptionEntry 1 }

ax3660sLicenseOptionNumberIndex OBJECT-TYPE
    SYNTAX  INTEGER
    ACCESS  not-accessible
    STATUS  mandatory
    DESCRIPTION
        "The unique index number of option licenses information which is given for each serial number. The number is from 1 to ax3660sLicenseNumber."
    ::= { ax3660sLicenseOptionEntry 2 }

ax3660sLicenseOptionSoftwareName OBJECT-TYPE
    SYNTAX  DisplayString 
    ACCESS  read-only
    STATUS  mandatory
    DESCRIPTION
        "The software model name of the option license information associated with the serial number."
    ::= { ax3660sLicenseOptionEntry 3 }

ax3660sLicenseOptionSoftwareAbbreviation OBJECT-TYPE
    SYNTAX  DisplayString 
    ACCESS  read-only
    STATUS  mandatory
    DESCRIPTION
        "The software abbreviated name of the option license information associated with the serial number. "
    ::= { ax3660sLicenseOptionEntry 4 }

-- ax3660sDevice group

ax3660sChassisMaxNumber OBJECT-TYPE
    SYNTAX  INTEGER
    ACCESS  read-only
    STATUS  mandatory
    DESCRIPTION
        "Max number of cluster chassis that can connect to this router."
    ::= { ax3660sChassis 1 }


ax3660sChassisTable OBJECT-TYPE
    SYNTAX  SEQUENCE OF Ax3660sChassisTableEntry
    ACCESS  not-accessible
    STATUS  mandatory
    DESCRIPTION
        "A table containing chassis information."
    ::= { ax3660sChassis 2 }

ax3660sChassisEntry OBJECT-TYPE
    SYNTAX  Ax3660sChassisTableEntry
    ACCESS  not-accessible
    STATUS  mandatory
    DESCRIPTION
        "An entry containing specific chassis."
    INDEX   { ax3660sChassisIndex }
    ::= { ax3660sChassisTable 1 }

    Ax3660sChassisTableEntry ::= SEQUENCE {
        ax3660sChassisIndex             INTEGER,
        ax3660sChassisType              INTEGER,
        ax3660sChassisStatus            INTEGER,
        ax3660sStsLedStatus             INTEGER,
        ax3660sCpuName                  DisplayString,
        ax3660sCpuClock                 INTEGER,
        ax3660sMemoryTotalSize          INTEGER,
        ax3660sMemoryUsedSize           INTEGER,
        ax3660sMemoryFreeSize           INTEGER,
        ax3660sRomVersion               DisplayString,
        ax3660sCpuLoad1m                INTEGER,
        ax3660sFlashTotalSize           INTEGER,
        ax3660sFlashUsedSize            INTEGER,
        ax3660sFlashFreeSize            INTEGER,
        ax3660sSdCardStatus             INTEGER,
        ax3660sSdCardTotalSize          INTEGER,
        ax3660sSdCardUsedSize           INTEGER,
        ax3660sSdCardFreeSize           INTEGER,
        ax3660sPhysLineNumber           INTEGER,
        ax3660sTemperatureStatusNumber  INTEGER,
        ax3660sPowerUnitNumber          INTEGER,
        ax3660sRedundantPsNumber        INTEGER,
        ax3660sFanNumber                INTEGER,
        ax3660sTotalAccumRunTime        INTEGER,
        ax3660sCriticalAccumRunTime     INTEGER,
        ax3660sModuleSlotNumber         INTEGER,
        ax3660sMgmtPortStatus           INTEGER
    }

ax3660sChassisIndex OBJECT-TYPE
    SYNTAX  INTEGER
    ACCESS  not-accessible
    STATUS  mandatory
    DESCRIPTION
        "A number to specify ax3660sChassisEntry."
    ::= { ax3660sChassisEntry 1 }

ax3660sChassisType OBJECT-TYPE
    SYNTAX  INTEGER {
        model-AX3660S-24T4XW(2400),
        model-AX3660S-48T4XW(2401),
        model-AX3660S-48XT4QW(2402),
        model-AX3660S-48X4QW(2403),
        model-AX3660S-24T4X(2404),
        model-AX3660S-24S8XW(2405),
        model-AX3660S-16S4XW(2406),
        model-AX3660S-24X4QW(2407)
    }
    ACCESS  read-only
    STATUS  mandatory
    DESCRIPTION
        "Chassis type of this system."
    ::= { ax3660sChassisEntry 2 }

ax3660sChassisStatus OBJECT-TYPE
    SYNTAX  INTEGER {
        up(2)
    }
    ACCESS  read-only
    STATUS  mandatory
    DESCRIPTION
        "Current status of this chassis."
    ::= { ax3660sChassisEntry 3 }

ax3660sStsLedStatus OBJECT-TYPE
    SYNTAX  INTEGER {
        green-light-blink(1),
        green-light-on(2),
        red-light-blink(3),
        red-light-on(4),
        light-off(6)
    }
    ACCESS  read-only
    STATUS  mandatory
    DESCRIPTION
        "The state of STS LED of the device is shown."
    ::= { ax3660sChassisEntry 4 }

ax3660sCpuName OBJECT-TYPE
    SYNTAX  DisplayString
    ACCESS  read-only
    STATUS  mandatory
    DESCRIPTION
        "CPU name is shown by the character string of 16 characters or less." 
    ::= { ax3660sChassisEntry 5 }

ax3660sCpuClock OBJECT-TYPE
    SYNTAX  INTEGER
    ACCESS  read-only
    STATUS  mandatory
    DESCRIPTION
        "CPU clock is shown by the numerical value."
    ::= { ax3660sChassisEntry 6 }

ax3660sMemoryTotalSize OBJECT-TYPE
    SYNTAX  INTEGER
    ACCESS  read-only
    STATUS  mandatory
    DESCRIPTION
        "The installing memory size is shown by the numerical value. "
    ::= { ax3660sChassisEntry 7 }

ax3660sMemoryUsedSize OBJECT-TYPE
    SYNTAX  INTEGER
    ACCESS  read-only
    STATUS  mandatory
    DESCRIPTION
        "The use memory size is shown by the numerical value."
    ::= { ax3660sChassisEntry 8 }

ax3660sMemoryFreeSize OBJECT-TYPE
    SYNTAX  INTEGER
    ACCESS  read-only
    STATUS  mandatory
    DESCRIPTION
        "The unused memory size is shown by the numerical value."
    ::= { ax3660sChassisEntry 9 }

ax3660sRomVersion OBJECT-TYPE
    SYNTAX  DisplayString
    ACCESS  read-only
    STATUS  mandatory
    DESCRIPTION
        "The version of ROM equipped with BCU is shown by the character string."
    ::= { ax3660sChassisEntry 10 }

ax3660sCpuLoad1m OBJECT-TYPE
    SYNTAX  INTEGER
    ACCESS  read-only
    STATUS  mandatory
    DESCRIPTION
        "CPU utilization of one minute is shown by the numerical value."
    ::= { ax3660sChassisEntry 11 }

ax3660sFlashTotalSize OBJECT-TYPE
    SYNTAX  INTEGER
    ACCESS  read-only
    STATUS  mandatory
    DESCRIPTION
        "The total of filesystem use capacity and unused capacity in a built-in memory 
        is shown."
    ::= { ax3660sChassisEntry 12 }

ax3660sFlashUsedSize OBJECT-TYPE
    SYNTAX  INTEGER
    ACCESS  read-only
    STATUS  mandatory
    DESCRIPTION
        "The use capacity of the filesystem in a built-in memory is shown."
    ::= { ax3660sChassisEntry 13 }

ax3660sFlashFreeSize OBJECT-TYPE
    SYNTAX  INTEGER
    ACCESS  read-only
    STATUS  mandatory
    DESCRIPTION
        "The unused capacity of the filesystem in a built-in memory is shown. "
    ::= { ax3660sChassisEntry 14 }

ax3660sSdCardStatus OBJECT-TYPE
    SYNTAX  INTEGER {
        connected(2),
        disconnected(32)
    }
    ACCESS  read-only
    STATUS  mandatory
    DESCRIPTION
        "The SD card connection is shown."
    ::= { ax3660sChassisEntry 15 }

ax3660sSdCardTotalSize OBJECT-TYPE
    SYNTAX  INTEGER
    ACCESS  read-only
    STATUS  mandatory
    DESCRIPTION
        "Total capacity of the SD card is shown by the numerical value. It responds by -1 
        at the MC card unconnected."
    ::= { ax3660sChassisEntry 16 }

ax3660sSdCardUsedSize OBJECT-TYPE
    SYNTAX  INTEGER
    ACCESS  read-only
    STATUS  mandatory
    DESCRIPTION
        "The use capacity of the SD card is shown by the numerical value. It responds by -1 
        at the SD card unconnected. "
    ::= { ax3660sChassisEntry 17 }

ax3660sSdCardFreeSize OBJECT-TYPE
    SYNTAX  INTEGER
    ACCESS  read-only
    STATUS  mandatory
    DESCRIPTION
        "The remainder capacity of the SD card is shown by the numerical value. It
        responds by -1 at the SD card unconnected."
    ::= { ax3660sChassisEntry 18 }

ax3660sPhysLineNumber OBJECT-TYPE
    SYNTAX  INTEGER
    ACCESS  read-only
    STATUS  mandatory
    DESCRIPTION
        "Number of physical lines."
    ::= { ax3660sChassisEntry 19 }

ax3660sTemperatureStatusNumber OBJECT-TYPE
    SYNTAX  INTEGER
    ACCESS  read-only
    STATUS  mandatory
    DESCRIPTION
        "The maximum number of ax3660sTemperatureStatus in this chassis."
    ::= { ax3660sChassisEntry 20 }

ax3660sPowerUnitNumber OBJECT-TYPE
    SYNTAX  INTEGER
    ACCESS  read-only
    STATUS  mandatory
    DESCRIPTION
        "Number of maximum power switches that this router can connect its."
    ::= { ax3660sChassisEntry 21 }

ax3660sRedundantPsNumber OBJECT-TYPE
    SYNTAX  INTEGER
    ACCESS  read-only
    STATUS  mandatory
    DESCRIPTION
        "Number of external power switches that this router can connect its."
    ::= { ax3660sChassisEntry 22 }

ax3660sFanNumber OBJECT-TYPE
    SYNTAX  INTEGER
    ACCESS  read-only
    STATUS  mandatory
    DESCRIPTION
        "The maximum number of fans that can connect to this chassis."
    ::= { ax3660sChassisEntry 23 }

ax3660sTotalAccumRunTime OBJECT-TYPE
    SYNTAX  INTEGER
    ACCESS  read-only
    STATUS  mandatory
    DESCRIPTION
        "Total operation time after operation of device begins."
    ::= { ax3660sChassisEntry 24 }

ax3660sCriticalAccumRunTime OBJECT-TYPE
    SYNTAX  INTEGER
    ACCESS  read-only
    STATUS  mandatory
    DESCRIPTION
        "Operating time under environment of 50 degrees C or more."
    ::= { ax3660sChassisEntry 25 }

ax3660sModuleSlotNumber OBJECT-TYPE
    SYNTAX  INTEGER
    ACCESS  read-only
    STATUS  mandatory
    DESCRIPTION
        "The maximum number of redundant power module that can connect to this chassis."
    ::= { ax3660sChassisEntry 26 }

ax3660sMgmtPortStatus OBJECT-TYPE
    SYNTAX  INTEGER {
                disconnected(-1),
                active(2),
                down(4),
                disabled(6),
                maintenance(7),
                line-test(9),
                unused(10)
            }
    ACCESS  read-only
    STATUS  mandatory
    DESCRIPTION
        "The state of management-port status of the device."
    ::= { ax3660sChassisEntry 27 }

ax3660sTemperatureStatusTable OBJECT-TYPE
    SYNTAX  SEQUENCE OF Ax3660sTemperatureStatusEntry
    ACCESS  not-accessible
    STATUS  mandatory
    DESCRIPTION
        "The table of ambient temperature status maintained by the
        environmental monitor."
    ::= { ax3660sChassis 3 }

ax3660sTemperatureStatusEntry OBJECT-TYPE
    SYNTAX  Ax3660sTemperatureStatusEntry
    ACCESS  not-accessible
    STATUS  mandatory
    DESCRIPTION
        "An entry in the ambient temperature status table, representing
        the status of the associated testpoint maintained by the
        environmental monitor."
    INDEX  {
        ax3660sChassisIndex,
        ax3660sTemperatureStatusIndex
    }
    ::= { ax3660sTemperatureStatusTable 1 }

    Ax3660sTemperatureStatusEntry ::= SEQUENCE {
        ax3660sTemperatureStatusIndex  INTEGER,
        ax3660sTemperatureStatusDescr  DisplayString,
        ax3660sTemperatureStatusValue  Integer32,
        ax3660sTemperatureThreshold    Integer32,
        ax3660sTemperatureState        INTEGER
    }

ax3660sTemperatureStatusIndex OBJECT-TYPE
    SYNTAX  INTEGER
    ACCESS  not-accessible
    STATUS  mandatory
    DESCRIPTION
        "Unique index for the testpoint being instrumented.
        This index is for SNMP purposes only, and has no
        intrinsic meaning."
    ::= { ax3660sTemperatureStatusEntry 1 }

ax3660sTemperatureStatusDescr OBJECT-TYPE
    SYNTAX  DisplayString (SIZE(0..32))
    ACCESS  read-only
    STATUS  mandatory
    DESCRIPTION
        "Textual description of the testpoint being instrumented.
        This description is a short textual label, suitable as a
        human-sensible identification for the rest of the
        information in the entry."
    ::= { ax3660sTemperatureStatusEntry 2 }

ax3660sTemperatureStatusValue OBJECT-TYPE
    SYNTAX  Integer32
    ACCESS  read-only
    STATUS  mandatory
    DESCRIPTION
        "The current measurement of the testpoint being instrumented."
    ::= { ax3660sTemperatureStatusEntry 3 }

ax3660sTemperatureThreshold OBJECT-TYPE
    SYNTAX  Integer32
    ACCESS  read-only
    STATUS  mandatory
    DESCRIPTION
        "The highest value that the associated instance of the
        object ax3660sTemperatureStatusValue may obtain
        before an emergency shutdown of the managed device is
        initiated."
    ::= { ax3660sTemperatureStatusEntry 4 }

ax3660sTemperatureState OBJECT-TYPE
    SYNTAX  INTEGER {
        normal(1),
        caution(2),
        warning(3),
        fatal(4)
    }
    ACCESS  read-only
    STATUS  mandatory
    DESCRIPTION
        "The current state of the testpoint being instrumented."
    ::= { ax3660sTemperatureStatusEntry 5 }

ax3660sPowerUnitTable OBJECT-TYPE
    SYNTAX  SEQUENCE OF Ax3660sPowerUnitTableEntry
    ACCESS  not-accessible
    STATUS  mandatory
    DESCRIPTION
        "A table containing power unit information."
    ::= { ax3660sChassis 4 }

ax3660sPowerUnitEntry OBJECT-TYPE
    SYNTAX  Ax3660sPowerUnitTableEntry
    ACCESS  not-accessible
    STATUS  mandatory
    DESCRIPTION
        "An entry containing power unit information."
    INDEX   {
        ax3660sChassisIndex,
        ax3660sPowerUnitIndex
    }
    ::= { ax3660sPowerUnitTable 1 }

    Ax3660sPowerUnitTableEntry ::= SEQUENCE {
        ax3660sPowerUnitIndex      INTEGER,
        ax3660sPowerConnectStatus  INTEGER,
        ax3660sPowerSupplyStatus   INTEGER,
        ax3660sPowerSlotType       INTEGER,
        ax3660sPowerFanDirection   INTEGER
    }

ax3660sPowerUnitIndex OBJECT-TYPE
    SYNTAX  INTEGER
    ACCESS  not-accessible
    STATUS  mandatory
    DESCRIPTION
        "A number to position of the power units.The value from 1
         to ax3660sPowerUnitNumber."
    ::= { ax3660sPowerUnitEntry 1 }

ax3660sPowerConnectStatus OBJECT-TYPE
    SYNTAX  INTEGER {
        connected(2),
        disconnected(32)
    }
    ACCESS  read-only
    STATUS  mandatory
    DESCRIPTION
        "The current connection status of the power unit."
    ::= { ax3660sPowerUnitEntry 2 }

ax3660sPowerSupplyStatus OBJECT-TYPE
    SYNTAX  INTEGER {
        ok(2),
        fault(4),
        disconnected(-1)
    }
    ACCESS  read-only
    STATUS  mandatory
    DESCRIPTION
        "Status of power supply."
    ::= { ax3660sPowerUnitEntry 3 }

ax3660sPowerSlotType OBJECT-TYPE
    SYNTAX  INTEGER {
        powerModule-AC(1),
        powerModule-DC(2),
        unknown(-1)
    }
    ACCESS  read-only
    STATUS  mandatory
    DESCRIPTION
        "The type of power slot is shown."
    ::= { ax3660sPowerUnitEntry 4 }

ax3660sPowerFanDirection OBJECT-TYPE
    SYNTAX  INTEGER {
        front-to-rear(0),
        rear-to-front(1),
        unknown(-1)
    }
    ACCESS  read-only
    STATUS  mandatory
    DESCRIPTION
        "The direction of fan of power supply is shown."
    ::= { ax3660sPowerUnitEntry 5 }


ax3660sFanTable OBJECT-TYPE
    SYNTAX  SEQUENCE OF Ax3660sFanTableEntry
    ACCESS  not-accessible
    STATUS  mandatory
    DESCRIPTION
        "A table containing fan information."
    ::= { ax3660sChassis 5 }

ax3660sFanEntry OBJECT-TYPE
    SYNTAX  Ax3660sFanTableEntry
    ACCESS  not-accessible
    STATUS  mandatory
    DESCRIPTION
        "This entry containing information for a fan."
    INDEX   {
        ax3660sChassisIndex,
        ax3660sFanIndex
    }
    ::= { ax3660sFanTable 1 }

    Ax3660sFanTableEntry ::= SEQUENCE {
        ax3660sFanIndex   INTEGER,
        ax3660sFanStatus  INTEGER,
        ax3660sFanDirection INTEGER
    }

ax3660sFanIndex OBJECT-TYPE
    SYNTAX  INTEGER
    ACCESS  not-accessible
    STATUS  mandatory
    DESCRIPTION
        "Index to indicate position of fans."
    ::= { ax3660sFanEntry 1 }

ax3660sFanStatus OBJECT-TYPE
    SYNTAX  INTEGER {
        ok(2),
        high-speed(3),
        fault(4),
        notconnect(32)
    }
    ACCESS  read-only
    STATUS  mandatory
    DESCRIPTION
        "Status of fans."
    ::= { ax3660sFanEntry 2 }

ax3660sFanDirection OBJECT-TYPE
    SYNTAX  INTEGER {
        front-to-rear(0),
        rear-to-front(1),
        unknown(-1)
    }
    ACCESS  read-only
    STATUS  mandatory
    DESCRIPTION
        "The direction of main fan is shown."
    ::= { ax3660sFanEntry 3 }

ax3660sModuleSlotTable OBJECT-TYPE
    SYNTAX  SEQUENCE OF Ax3660sModuleSlotEntry
    ACCESS  not-accessible
    STATUS  mandatory
    DESCRIPTION
        "A table containing redundant power module information."
    ::= { ax3660sChassis 7 }

ax3660sModuleSlotEntry OBJECT-TYPE
    SYNTAX  Ax3660sModuleSlotEntry
    ACCESS  not-accessible
    STATUS  mandatory
    DESCRIPTION
        "An entry containing redundant power module information."
    INDEX   {
        ax3660sChassisIndex,
        ax3660sModuleSlotIndex
    }
    ::= { ax3660sModuleSlotTable 1 }

    Ax3660sModuleSlotEntry ::= SEQUENCE {
        ax3660sModuleSlotIndex   INTEGER,
        ax3660sModuleSlotStatus  INTEGER,
        ax3660sModuleSlotType    INTEGER
    }

ax3660sModuleSlotIndex OBJECT-TYPE
    SYNTAX  INTEGER
    ACCESS  not-accessible
    STATUS  mandatory
    DESCRIPTION
        "A number to position of the module slot units.The value from 1 to ax3660sModuleSlotNumber."
    ::= { ax3660sModuleSlotEntry 1 }

ax3660sModuleSlotStatus OBJECT-TYPE
    SYNTAX  INTEGER {
        connected(2),
        down(4),
        disconnected(32)
    }
    ACCESS  read-only
    STATUS  mandatory
    DESCRIPTION
        "Module slot status is shown."
    ::= { ax3660sModuleSlotEntry 2 }

ax3660sModuleSlotType OBJECT-TYPE
    SYNTAX  INTEGER {
        powerModule-AC(1),
        powerModule-DC(2),
        unknown(-1)
    }
    ACCESS  read-only
    STATUS  mandatory
    DESCRIPTION
        "The type of module slot is shown."
    ::= { ax3660sModuleSlotEntry 3 }	

ax3660sPhysLineTable OBJECT-TYPE
    SYNTAX  SEQUENCE OF Ax3660sPhysLineTableEntry
    ACCESS  not-accessible
    STATUS  mandatory
    DESCRIPTION
        "A table containing physical port information."
    ::= { ax3660sPhysLine 1 }

ax3660sPhysLineEntry OBJECT-TYPE
    SYNTAX  Ax3660sPhysLineTableEntry
    ACCESS  not-accessible
    STATUS  mandatory
    DESCRIPTION
        "An entry containing physical port."
    INDEX   {
        ax3660sChassisIndex,
        ax3660sPhysLineIndex
    }
    ::= { ax3660sPhysLineTable 1 }

    Ax3660sPhysLineTableEntry ::= SEQUENCE {
        ax3660sPhysLineIndex              INTEGER,
        ax3660sPhysLineConnectorType      INTEGER,
        ax3660sPhysLineOperStatus         INTEGER,
        ax3660sPhysLineIfIndexNumber      INTEGER,
        ax3660sPhysLineTransceiverStatus  INTEGER
    }

ax3660sPhysLineIndex OBJECT-TYPE
    SYNTAX  INTEGER
    ACCESS  not-accessible
    STATUS  mandatory
    DESCRIPTION
        "Physical port number. The value is from 1 to ax3660sPhysLineNumber."
    ::= { ax3660sPhysLineEntry 1 }

ax3660sPhysLineConnectorType OBJECT-TYPE
    SYNTAX  INTEGER {
        other(1),
        type1000BASE-LX(301),
        type1000BASE-SX(302),
        type1000BASE-LH(303),
        type1000BASE-BX10-D(304),
        type1000BASE-BX10-U(305),
        type1000BASE-BX40-D(306),
        type1000BASE-BX40-U(307),
        type1000BASE-UTP(309),
        type1000BASE-LHB(310),
        type10GBASE-SR(401),
        type10GBASE-LR(402),
        type10GBASE-ER(403),
        type10GBASE-ZR(404),
        type10GBASE-CU1M(405),
        type10GBASE-CU3M(406),
        type10GBASE-CU5M(407),
        type10GBASE-CU30CM(408),
        type10GBASE-BR10-D(409),
        type10GBASE-BR10-U(410),
        type10GBASE-BR40-D(411),
        type10GBASE-BR40-U(412),
        type40GBASE-SR4(501),
        type40GBASE-CU35CM(502),
        type40GBASE-CU1M(503),
        type40GBASE-CU3M(504),
        type40GBASE-CU5M(505),
        type40GBASE-LR4(506),
        type100GBASE-LR4(601),
        type100GBASE-CU35CM(602),
        type100GBASE-CU1M(603),
        type100GBASE-CU3M(604),
        type100GBASE-SR4(605),
        type100GBASE-CWDM4(606),
        type100GBASE-4WDM-40(607) 
    }
    ACCESS  read-only
    STATUS  mandatory
    DESCRIPTION
        "Connector type is connected physical port. The value is 1(other)
        when connector is disconnected or connector type is unknown."
    ::= { ax3660sPhysLineEntry 2 }

ax3660sPhysLineOperStatus OBJECT-TYPE
    SYNTAX  INTEGER {
        other(1),
        active(2),
        initialization(3),
        down(4),
        lock(6),
        close(7),
        line-fault(8),
        test(9),
        nothing-configuration(10),
        suspend(11)
    }
    ACCESS  read-only
    STATUS  mandatory
    DESCRIPTION
        "Status of physical port. The value is -1 when PSU or NIF board is
        disconnected."
    ::= { ax3660sPhysLineEntry 3 }

ax3660sPhysLineIfIndexNumber OBJECT-TYPE
    SYNTAX  INTEGER
    ACCESS  read-only
    STATUS  mandatory
    DESCRIPTION
        "Number of ifIndex which is included in physical port.The value is -1
        when PSU board or NIF board is disconnected."
    ::= { ax3660sPhysLineEntry 4 }

ax3660sPhysLineTransceiverStatus OBJECT-TYPE
    SYNTAX  INTEGER {
        unchangeable-transceiver(1),
        sfp-mounted(20),
        sfp-unmounted(21),
        unsupported-sfp-mounted(22),
        sfp-status-unknown(23),
        qsfp-mounted(50),
        qsfp-unmounted(51),
        unsupported-qsfp-mounted(52),
        qsfp-status-unknown(53)
    }
    ACCESS  read-only
    STATUS  mandatory
    DESCRIPTION
        "Type and status of replaceable transceiver."
    ::= { ax3660sPhysLineEntry 5 }

ax3660sPhysLineLaneTable OBJECT-TYPE
    SYNTAX  SEQUENCE OF Ax3660sPhysLineLaneTableEntry
    ACCESS  not-accessible
    STATUS  mandatory
    DESCRIPTION
        "A table containing lane information."
    ::= { ax3660sPhysLine 2 }

ax3660sPhysLineLaneEntry OBJECT-TYPE
    SYNTAX  Ax3660sPhysLineLaneTableEntry
    ACCESS  not-accessible
    STATUS  mandatory
    DESCRIPTION
        "An entry containing lane information."
    INDEX   {
        ax3660sChassisIndex,
        ax3660sPhysLineIndex,
        ax3660sPhysLineLaneIndex
    }
    ::= { ax3660sPhysLineLaneTable 1 }

    Ax3660sPhysLineLaneTableEntry ::= SEQUENCE {
        ax3660sPhysLineLaneIndex               INTEGER,
        ax3660sPhysLineLaneTransceiverTxPower  Integer32,
        ax3660sPhysLineLaneTransceiverRxPower  Integer32
    }

ax3660sPhysLineLaneIndex OBJECT-TYPE
    SYNTAX  INTEGER
    ACCESS  not-accessible
    STATUS  mandatory
    DESCRIPTION
        "Lane number. The value is from 1 to 4."
    ::= { ax3660sPhysLineLaneEntry 1 }

ax3660sPhysLineLaneTransceiverTxPower OBJECT-TYPE
    SYNTAX  Integer32
    ACCESS  read-only
    STATUS  mandatory
    DESCRIPTION
      "A value obtained by multiplying the transmitted optical power (dBm) by 10.
       The value is from -400 to 82 or 300."
    ::= { ax3660sPhysLineLaneEntry 2 }

ax3660sPhysLineLaneTransceiverRxPower OBJECT-TYPE
    SYNTAX  Integer32
    ACCESS  read-only
    STATUS  mandatory
    DESCRIPTION
      "A value obtained by multiplying the received optical power (dBm) by 10.
       The value is from -400 to 82 or 300."
    ::= { ax3660sPhysLineLaneEntry 3 }

-- ax3660sFdbClearMIB group

ax3660sFdbClearSet OBJECT-TYPE
    SYNTAX  INTEGER {
        initialValue(0),
        processing(1),
        failure(2),
        success(3)
    }
    ACCESS  read-write
    STATUS  mandatory
    DESCRIPTION
        "Fdb clear information. When want to clear fdb, 
        then set value of this MIB as 1."
    ::= { ax3660sFdbClearMIB 1 }

ax3660sFdbClearReqTime OBJECT-TYPE
    SYNTAX  TimeTicks
    ACCESS  read-only
    STATUS  mandatory
    DESCRIPTION
        "This object indicates the most recent time that
        received the demand to clear Fdb information.(sysUpTime)"
    ::= { ax3660sFdbClearMIB 2 }

ax3660sFdbClearSuccessTime OBJECT-TYPE
    SYNTAX  TimeTicks
    ACCESS  read-only
    STATUS  mandatory
    DESCRIPTION
        "This object indicates the time of the most recent
        Fdb clearing success.(sysUpTime)"
    ::= { ax3660sFdbClearMIB 3 }


-- Traps for use by AlaxalA networks AXS

-- Traps are defined using the conventions in RFC 1215.

axsStaticGatewayStateChange TRAP-TYPE
        ENTERPRISE    axsStaticTrap
        VARIABLES     { axsStaticGatewayAddr,
                        axsStaticGatewayState }
        DESCRIPTION
                  "static route gateway state change."
        ::= 1

axsStaticIpv6GatewayStateChange TRAP-TYPE
        ENTERPRISE      axsStaticTrap
        VARIABLES       { axsStaticIpv6Ifindex,
                          axsStaticIpv6GatewayAddr,
                          axsStaticIpv6GatewayState }
        DESCRIPTION
                  "ipv6 static route gateway state change."
        ::= 2

axsOspfVirtIfStateChange TRAP-TYPE
	ENTERPRISE      axsOspfTraps
	VARIABLES       { axsOspfVirtIfDomainNumber, axsOspfRouterId, axsOspfVirtIfAreaId, axsOspfVirtIfNeighbor, axsOspfVirtIfState }
	DESCRIPTION
		"An axsOspfIfStateChange trap signifies that there has  been a change 
		in the state of an OSPF virtual interface."
	::= 1

axsOspfNbrStateChange TRAP-TYPE
	ENTERPRISE      axsOspfTraps
	VARIABLES       { axsOspfNbrDomainNumber, axsOspfRouterId, axsOspfNbrIpAddr, axsOspfNbrAddressLessIndex, axsOspfNbrRtrId, axsOspfNbrState }
	DESCRIPTION
           "An axsOspfNbrStateChange trap signifies that
           there  has been a change in the state of a non-
           virtual OSPF neighbor.   This  trap  should  be
           generated  when  the  neighbor  state regresses
           (e.g., goes from Attempt or Full  to  1-Way  or
           Down)  or progresses to a terminal state (e.g.,
           2-Way or Full).  When an  neighbor  transitions
           from  or  to Full on non-broadcast multi-access
           and broadcast networks, the trap should be gen-
           erated  by the designated router.  A designated
           router transitioning to Down will be  noted  by
           axsOspfIfStateChange."
	::= 2

axsOspfVirtNbrStateChange TRAP-TYPE
	ENTERPRISE      axsOspfTraps
	VARIABLES       { axsOspfVirtNbrDomainNumber, axsOspfRouterId, axsOspfVirtNbrArea, axsOspfVirtNbrRtrId, axsOspfVirtNbrState }
	DESCRIPTION
           "An axsOspfIfStateChange trap signifies that there
           has  been a change in the state of an OSPF vir-
           tual neighbor.  This trap should  be  generated
           when  the  neighbor state regresses (e.g., goes
           from Attempt or  Full  to  1-Way  or  Down)  or
           progresses to a terminal state (e.g., Full)."
	::= 3

axsOspfIfConfigError TRAP-TYPE
	ENTERPRISE      axsOspfTraps
	VARIABLES       { axsOspfIfDomainNumber, axsOspfRouterId, axsOspfIfIpAddress, axsOspfAddressLessIf, axsOspfPacketSrc, axsOspfConfigErrorType, axsOspfPacketType }
	DESCRIPTION
           "An axsOspfIfConfigError  trap  signifies  that  a
           packet  has  been received on a non-virtual in-
           terface  from  a  router  whose   configuration
           parameters  conflict  with this router's confi-
           guration parameters.  Note that the  event  op-
           tionMismatch  should  cause  a  trap only if it
           prevents an adjacency from forming."
	::= 4

axsOspfVirtIfConfigError TRAP-TYPE
	ENTERPRISE      axsOspfTraps
	VARIABLES       { axsOspfVirtIfDomainNumber, axsOspfRouterId, axsOspfVirtIfAreaId, axsOspfVirtIfNeighbor, axsOspfConfigErrorType, axsOspfPacketType }
	DESCRIPTION
           "An axsOspfConfigError trap signifies that a pack-
           et  has  been  received  on a virtual interface
           from a router  whose  configuration  parameters
           conflict   with   this  router's  configuration
           parameters.  Note that the event optionMismatch
           should  cause a trap only if it prevents an ad-
           jacency from forming."
	::= 5

axsOspfIfAuthFailure TRAP-TYPE
	ENTERPRISE      axsOspfTraps
	VARIABLES       { axsOspfIfDomainNumber, axsOspfRouterId, axsOspfIfIpAddress, axsOspfAddressLessIf, axsOspfPacketSrc, axsOspfConfigErrorType, axsOspfPacketType }
	DESCRIPTION
           "An axsOspfIfAuthFailure  trap  signifies  that  a
           packet  has  been received on a non-virtual in-
           terface from a router whose authentication  key
           or  authentication  type  conflicts  with  this
           router's authentication key  or  authentication
           type."
	::= 6

axsOspfVirtIfAuthFailure TRAP-TYPE
	ENTERPRISE      axsOspfTraps
	VARIABLES       { axsOspfVirtIfDomainNumber, axsOspfRouterId, axsOspfVirtIfAreaId, axsOspfVirtIfNeighbor, axsOspfConfigErrorType, axsOspfPacketType }
	DESCRIPTION
           "An axsOspfVirtIfAuthFailure trap signifies that a
           packet has been received on a virtual interface
           from a router whose authentication key  or  au-
           thentication  type conflicts with this router's
           authentication key or authentication type."
	::= 7

axsOspfIfStateChange TRAP-TYPE
	ENTERPRISE      axsOspfTraps
	VARIABLES       { axsOspfIfDomainNumber, axsOspfRouterId, axsOspfIfIpAddress, axsOspfAddressLessIf, axsOspfIfState }
	DESCRIPTION
           "An axsOspfIfStateChange trap signifies that there
           has been a change in the state of a non-virtual
           OSPF interface. This trap should  be  generated
           when  the interface state regresses (e.g., goes
           from Dr to Down) or progresses  to  a  terminal
           state  (i.e.,  Point-to-Point, DR Other, Dr, or
           Backup)."
	::= 16 

axsOadpNeighborCachelastChangeTrap TRAP-TYPE
	ENTERPRISE      axsOadpMIBNotifications
	VARIABLES       { axsOadpNeighborCacheLastChange }
	DESCRIPTION
           "This trap indicates that information of OADP neighbor nodes is updated."
	::= 1 

axsPolicyBaseRoutingRouteChange TRAP-TYPE
    ENTERPRISE    axsPolicyBaseRouting
    VARIABLES     {axsPolicyBaseRoutingChangeListNumber , axsPolicyBaseRoutingChangeSequenceNumber}
    DESCRIPTION
           "When route of Policy Base Routing changed."
    ::= 1

axsTrackObjectStateUp TRAP-TYPE
    ENTERPRISE      axsTrackObjectTraps
    VARIABLES       { axsTrackObjectId, axsTrackObjectState, axsTrackObjectOperation,
                      axsTrackObjectType, axsTrackObjectNetIndex }
    DESCRIPTION
              "The track state changed to up."
    ::= 1

axsTrackObjectStateDown TRAP-TYPE
    ENTERPRISE      axsTrackObjectTraps
    VARIABLES       { axsTrackObjectId, axsTrackObjectState, axsTrackObjectOperation,
                      axsTrackObjectType, axsTrackObjectNetIndex }
    DESCRIPTION
              "The track state changed to down."
    ::= 2

END

AXS-AX3660S-TRAP DEFINITIONS     ::= BEGIN
IMPORTS
TRAP-TYPE
    FROM RFC-1215
ifIndex
    FROM RFC1213-MIB
axsGsrpGroupId, axsGsrpVlanGroupId, axsGsrpState,
axsL2ldPortIndex, axsL2ldPortIfIndex, axsL2ldPortSourcePortIfindex,
axsL2ldPortDestinationPortIfindex, axsL2ldPortSourceVlan,
axsUlrPortIfIndex, axsUlrPairedPortIfIndex,
axsLoginName, axsLoginTime, axsLogoutTime, axsLoginFailureTime,
axsLoginLocation, axsLoginLine, axsLogoutStatus,
axsAxrpGroupRingId, axsAxrpGroupMode, axsAxrpGroupRingAttribute, axsAxrpGroupMonitoringState,
axsAxrpGroupRingport1, axsAxrpGroupRingport2, axsAxrpGroupMultiFaultDetectionState,
ax3660s,
ax3660sSystemMsgType, ax3660sSystemMsgTimeStamp, ax3660sSystemMsgLevel,
ax3660sSystemMsgEventPoint, ax3660sSystemMsgEventInterfaceID,
ax3660sSystemMsgEventCode, ax3660sSystemMsgAdditionalCode, ax3660sSystemMsgText,
ax3660sChassisIndex,
ax3660sTemperatureStatusIndex, ax3660sTemperatureStatusDescr,
ax3660sTemperatureStatusValue, ax3660sTemperatureState,
axsQosFlowStatsInListName, axsQosFlowStatsInSequenceNumber
    FROM AX3660S
;

-- Traps for use by AlaxalA networks AX3660S
-- Traps are defined using the conventions in RFC 1215.

ax3660sSystemMsgTrap TRAP-TYPE
    ENTERPRISE   ax3660s
    VARIABLES    {
        ax3660sSystemMsgType,
        ax3660sSystemMsgTimeStamp,
        ax3660sSystemMsgLevel,
        ax3660sSystemMsgEventPoint,
        ax3660sSystemMsgEventInterfaceID,
        ax3660sSystemMsgEventCode,
        ax3660sSystemMsgAdditionalCode,
        ax3660sSystemMsgText
    }
    DESCRIPTION
        "System message is displayed."
    ::= 1

ax3660sTemperatureTrap TRAP-TYPE
    ENTERPRISE   ax3660s
    VARIABLES    {
        ax3660sChassisIndex,
        ax3660sTemperatureStatusIndex,
        ax3660sTemperatureStatusDescr,
        ax3660sTemperatureStatusValue,
        ax3660sTemperatureState
    }
    DESCRIPTION
        "An ax3660sTemperatureTrap is sent if the temperature 
        measured at a given testpoint falls outside the normal 
        range or recovers from that state. (i.e. when becoming 
        the warning, critical, or normal state)."
    ::= 4

ax3660sGsrpStateTransitionTrap TRAP-TYPE
    ENTERPRISE   ax3660s
    VARIABLES    {
        axsGsrpGroupId,
        axsGsrpVlanGroupId,
        axsGsrpState
    }
    DESCRIPTION
        "Changes of the VLAN group state of GSRP"
    ::= 6

ax3660sAirFanStopTrap TRAP-TYPE
    ENTERPRISE   ax3660s
    DESCRIPTION
        "This trap indicates a fan failure." 
    ::= 8 

ax3660sPowerSupplyFailureTrap TRAP-TYPE
    ENTERPRISE   ax3660s
    DESCRIPTION
        "This trap indicates one ( or more ) of power supplies failure." 
    ::= 9 

ax3660sLoginSuccessTrap TRAP-TYPE
    ENTERPRISE   ax3660s
    VARIABLES    {
        axsLoginName,
        axsLoginTime,
        axsLoginLocation,
        axsLoginLine
    }
    DESCRIPTION
        "This trap indicates success of user log in." 
    ::= 10 

ax3660sLoginFailureTrap TRAP-TYPE
    ENTERPRISE   ax3660s
    VARIABLES    {
        axsLoginName,
        axsLoginFailureTime,
        axsLoginLocation,
        axsLoginLine
    }
    DESCRIPTION
        "This trap indicates failure of user log in." 
    ::= 11

ax3660sLogoutTrap TRAP-TYPE
    ENTERPRISE   ax3660s
    VARIABLES    {
        axsLoginName,
        axsLoginTime,
        axsLogoutTime,
        axsLoginLocation,
        axsLoginLine,
        axsLogoutStatus
    }
    DESCRIPTION
        "This trap indicates success of following log out.
        'logout' command, 'exit' command, 'quit' command." 
    ::= 12

ax3660sMemoryUsageTrap  TRAP-TYPE
    ENTERPRISE   ax3660s
    DESCRIPTION
        "This indicates available memory is fewer than lower limit." 
    ::= 13

ax3660sFrameErrorReceiveTrap  TRAP-TYPE
    ENTERPRISE   ax3660s
    VARIABLES    {
        ifIndex
    }
    DESCRIPTION
        "This indicates frame receive error." 
    ::= 18

ax3660sFrameErrorSendTrap  TRAP-TYPE
    ENTERPRISE   ax3660s
    VARIABLES    {
        ifIndex
    }
    DESCRIPTION
        "This indicates frame send error." 
    ::= 19

ax3660sBroadcastStormDetectTrap TRAP-TYPE
    ENTERPRISE   ax3660s
    VARIABLES    {
        ifIndex
    }
    DESCRIPTION
        "This indicates detection on broad-cast storm." 
    ::= 20

ax3660sMulticastStormDetectTrap TRAP-TYPE
    ENTERPRISE   ax3660s
    VARIABLES    {
        ifIndex
    }
    DESCRIPTION
        "This indicates detection on multi-cast storm." 
    ::= 21

ax3660sUnicastStormDetectTrap TRAP-TYPE
    ENTERPRISE   ax3660s
    VARIABLES    {
        ifIndex
    }
    DESCRIPTION
        "This indicates detection on uni-cast storm." 
    ::= 22

ax3660sBroadcastStormPortInactivateTrap TRAP-TYPE
    ENTERPRISE   ax3660s
    VARIABLES    {
        ifIndex
    }
    DESCRIPTION
        "This indicates the port inactivated for detection on broad-cast storm." 
    ::= 23

ax3660sMulticastStormPortInactivateTrap TRAP-TYPE
    ENTERPRISE   ax3660s
    VARIABLES    {
        ifIndex
    }
    DESCRIPTION
        "This indicates the port inactivated for detection on multi-cast storm." 
    ::= 24

ax3660sUnicastStormPortInactivateTrap TRAP-TYPE
    ENTERPRISE   ax3660s
    VARIABLES    {
        ifIndex
    }
    DESCRIPTION
        "This indicates the port inactivated for detection on uni-cast storm." 
    ::= 25

ax3660sBroadcastStormRecoverTrap TRAP-TYPE
    ENTERPRISE   ax3660s
    VARIABLES    {
        ifIndex
    }
    DESCRIPTION
        "This indicates the end of broad-cast storm." 
    ::= 26

ax3660sMulticastStormRecoverTrap TRAP-TYPE
    ENTERPRISE   ax3660s
    VARIABLES    {
        ifIndex
    }
    DESCRIPTION
        "This indicates the end of multi-cast storm." 
    ::= 27

ax3660sUnicastStormRecoverTrap TRAP-TYPE
    ENTERPRISE   ax3660s
    VARIABLES    {
        ifIndex
    }
    DESCRIPTION
        "This indicates the end of uni-cast storm." 
    ::= 28

ax3660sEfmoamUdldPortInactivateTrap TRAP-TYPE
    ENTERPRISE   ax3660s
    VARIABLES    {
        ifIndex
    }
    DESCRIPTION
        "Efmoam udld port inactivate trap."
    ::= 29

ax3660sEfmoamLoopDetectPortInactivateTrap TRAP-TYPE
    ENTERPRISE   ax3660s
    VARIABLES    {
        ifIndex
    }
    DESCRIPTION
        "Efmoam loop detect port inactivate trap."
    ::= 30

ax3660sAxrpStateTransitionTrap TRAP-TYPE
    ENTERPRISE   ax3660s
    VARIABLES    {
        axsAxrpGroupRingId,
        axsAxrpGroupMode,
        axsAxrpGroupRingAttribute,
        axsAxrpGroupMonitoringState
    }
    DESCRIPTION
        "When the state of the ring of ALAXALA Ring Protocol (trouble watch and restoration watch) changes between each state. "
    ::= 36

ax3660sAxrpRingport1MonitoringStartTrap TRAP-TYPE
    ENTERPRISE   ax3660s
    VARIABLES    {
        axsAxrpGroupRingId,
        axsAxrpGroupMode,
        axsAxrpGroupRingAttribute,
        axsAxrpGroupRingport1
    }
    DESCRIPTION
        "When you make the link monitoring function of ring port 1 of Ring Protocol effective. "
    ::= 37

ax3660sAxrpRingport1DownTrap TRAP-TYPE
    ENTERPRISE   ax3660s
    VARIABLES    {
        axsAxrpGroupRingId,
        axsAxrpGroupMode,
        axsAxrpGroupRingAttribute,
        axsAxrpGroupRingport1
    }
    DESCRIPTION
        "When the link for the watch is cut when the link monitoring function of ring port 1 of Ring Protocol is made effective. "
    ::= 38

ax3660sAxrpRingport2MonitoringStartTrap TRAP-TYPE
    ENTERPRISE   ax3660s
    VARIABLES    {
        axsAxrpGroupRingId,
        axsAxrpGroupMode,
        axsAxrpGroupRingAttribute,
        axsAxrpGroupRingport2
    }
    DESCRIPTION
        "When you make the link monitoring function of ring port 2 of Ring Protocol effective. "
    ::= 39

ax3660sAxrpRingport2DownTrap TRAP-TYPE
    ENTERPRISE   ax3660s
    VARIABLES    {
        axsAxrpGroupRingId,
        axsAxrpGroupMode,
        axsAxrpGroupRingAttribute,
        axsAxrpGroupRingport2
    }
    DESCRIPTION
        "When the link for the watch is cut when the link monitoring function of ring port 2 of Ring Protocol is made effective. "
    ::= 40

ax3660sAxrpMultiFaultDetectionStartTrap TRAP-TYPE
    ENTERPRISE   ax3660s
    VARIABLES    {
        axsAxrpGroupRingId,
        axsAxrpGroupMode,
        axsAxrpGroupRingAttribute
    }
    DESCRIPTION
        "When the state of watching multiple trouble on ring started."
    ::= 41

ax3660sAxrpMultiFaultDetectionStateTransitionTrap TRAP-TYPE
    ENTERPRISE   ax3660s
    VARIABLES    {
        axsAxrpGroupRingId,
        axsAxrpGroupMode,
        axsAxrpGroupRingAttribute,
        axsAxrpGroupMultiFaultDetectionState
    }
    DESCRIPTION
        "When the state of the ring of ALAXALA Ring Protocol (multiple fault detection and restoration watch) changes between each state. "
    ::= 42

ax3660sL2ldLinkDown TRAP-TYPE
    ENTERPRISE   ax3660s
    VARIABLES    {
        axsL2ldPortIfIndex,
        axsL2ldPortSourcePortIfindex,
        axsL2ldPortDestinationPortIfindex,
        axsL2ldPortSourceVlan
    }
    DESCRIPTION
        "When the operation of the interface changes from ACTIVE(state that can be communicated)
        into DISABLE (state that cannot be communicated) by the L2 loop detection."
    ::= 51

ax3660sL2ldLinkUp TRAP-TYPE
    ENTERPRISE   ax3660s
    VARIABLES    {
        axsL2ldPortIfIndex
    }
    DESCRIPTION
        "When the operation of the interface changes from DISABLE (state that cannot be communicated)
        into ACTIVE (state that can be communicated) by the automatic restoration function of the L2 loop detection."
    ::= 52

ax3660sL2ldLoopDetection TRAP-TYPE
    ENTERPRISE   ax3660s
    VARIABLES    {
        axsL2ldPortIndex,
        axsL2ldPortIfIndex,
        axsL2ldPortSourcePortIfindex,
        axsL2ldPortSourceVlan
    }
    DESCRIPTION
        "When you detect the L2 loop. It notifies every 60 seconds when the state of the L2 loop continues."
    ::= 53

ax3660sUlrChangeSecondary TRAP-TYPE
    ENTERPRISE   ax3660s
    VARIABLES    {
        axsUlrPortIfIndex,
        axsUlrPairedPortIfIndex
    }
    DESCRIPTION
        "When secondary port changed to active port."
    ::= 87

ax3660sUlrChangePrimary TRAP-TYPE
    ENTERPRISE   ax3660s
    VARIABLES    {
        axsUlrPortIfIndex,
        axsUlrPairedPortIfIndex
    }
    DESCRIPTION
        "When primary port changed to active port."
    ::= 88

ax3660sUlrActivePortDown TRAP-TYPE
    ENTERPRISE   ax3660s
    VARIABLES    {
        axsUlrPortIfIndex,
        axsUlrPairedPortIfIndex
    }
    DESCRIPTION
        "When active port disappeared."
    ::= 89

ax3660sQosFlowListRateAlarmExceedTrap TRAP-TYPE
    ENTERPRISE   ax3660s
    VARIABLES    {
        ifIndex,
        axsQosFlowStatsInListName,
        axsQosFlowStatsInSequenceNumber
    }
    DESCRIPTION
        "When the QoS flow list exceeds the rate limit."
    ::= 90

ax3660sQosFlowListRateAlarmConformTrap TRAP-TYPE
    ENTERPRISE   ax3660s
    VARIABLES    {
        ifIndex,
        axsQosFlowStatsInListName,
        axsQosFlowStatsInSequenceNumber
    }
    DESCRIPTION
        "When the QoS flow list conforms the rate limit."
    ::= 91

END
