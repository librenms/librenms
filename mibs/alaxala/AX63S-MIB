--
-- Copyright(C) 2006-2017 ALAXALA Networks Corporation. All Rights Reserved.
--
-- AX63S.my: Switching Router System information MIB file
--
AX6300S DEFINITIONS ::= BEGIN

    IMPORTS
        enterprises, OBJECT-TYPE, NetworkAddress, IpAddress,
        Counter, Gauge, TimeTicks
            FROM RFC1155-SMI
        RouterID, AreaID, Status, BigMetric, DesignatedRouterPriority,
        HelloRange, Metric, PositiveInteger, UpToMaxAge
            FROM OSPF-MIB
        OBJECT-TYPE
            FROM RFC-1212
        TRAP-TYPE
            FROM RFC-1215
        ifIndex
            FROM IF-MIB
        DisplayString
            FROM RFC1213-MIB
        RowStatus, MacAddress, TruthValue, TimeStamp, PhysAddress
            FROM SNMPv2-TC
        InterfaceIndex
            FROM IF-MIB
        Ipv6IfIndex, Ipv6Address, Ipv6AddressPrefix
            FROM IPV6-TC
        BridgeId, Timeout
            FROM BRIDGE-MIB
        PortList
            FROM Q-BRIDGE-MIB
        InetAddressType,InetAddress
            FROM INET-ADDRESS-MIB
        Gauge32, Counter32, Counter64, Unsigned32, Integer32
            FROM SNMPv2-SMI
    ;

    VlanIndex ::= INTEGER (1..2147483647)
    VlanIdOrZero ::= INTEGER (0|1..4095)

-- object syntax difinition end

    alaxala                     OBJECT IDENTIFIER ::= { enterprises 21839 }
    alaxalaProductId            OBJECT IDENTIFIER ::= { alaxala 1 }
    axSwitch                    OBJECT IDENTIFIER ::= { alaxalaProductId 2 }
    ax6300s                     OBJECT IDENTIFIER ::= { axSwitch 8 }
    ax6700s                     OBJECT IDENTIFIER ::= { axSwitch 9 }
    ax6600s                     OBJECT IDENTIFIER ::= { axSwitch 12 }

    alaxalaMib                  OBJECT IDENTIFIER ::= { alaxala 2 }
    axsEx                       OBJECT IDENTIFIER ::= { alaxalaMib 2 }

    axsMib                      OBJECT IDENTIFIER ::= { axsEx 1 }
    ax6300sMib                  OBJECT IDENTIFIER ::= { axsEx 8 }
    ax6700sMib                  OBJECT IDENTIFIER ::= { axsEx 9 }
    ax6600sMib                  OBJECT IDENTIFIER ::= { axsEx 12 }

-- device independent

    axsStats                    OBJECT IDENTIFIER ::= { axsMib 1 }
    axsIfStats                  OBJECT IDENTIFIER ::= { axsStats 4 }
    axsQoS                      OBJECT IDENTIFIER ::= { axsStats 6 }
    axsEtherTxQoS               OBJECT IDENTIFIER ::= { axsQoS 1 }
    axsEthShaper                OBJECT IDENTIFIER ::= { axsQoS 4 }
    axsEthShaperAgQue           OBJECT IDENTIFIER ::= { axsQoS 5 }
    axsShaperUser               OBJECT IDENTIFIER ::= { axsQoS 6 }
    axsEtherRxQoS               OBJECT IDENTIFIER ::= { axsQoS 7 }
    axsEtherDistributionTxQoS   OBJECT IDENTIFIER ::= { axsQoS 8 }
    axsEtherDistributionRxQoS   OBJECT IDENTIFIER ::= { axsQoS 9 }
    axsToCpuQoS                 OBJECT IDENTIFIER ::= { axsQoS 11 }

    axsDHCP                     OBJECT IDENTIFIER ::= { axsStats 10 }
    axsUrpf                     OBJECT IDENTIFIER ::= { axsStats 13 }

    axsGsrp                     OBJECT IDENTIFIER ::= { axsMib 4 }
    axsFdb                      OBJECT IDENTIFIER ::= { axsMib 5 }
    axsVlan                     OBJECT IDENTIFIER ::= { axsMib 6 }
    axsVlanBridge               OBJECT IDENTIFIER ::= { axsVlan 1 }
    axsVlanBridgeBase           OBJECT IDENTIFIER ::= { axsVlanBridge 1 }
    axsVlanBridgeStp            OBJECT IDENTIFIER ::= { axsVlanBridge 2 }
    axsVlanBridgeTp             OBJECT IDENTIFIER ::= { axsVlanBridge 4 }
    axsVlanBridgeStatic         OBJECT IDENTIFIER ::= { axsVlanBridge 5 }
    axsVlanTagTranslation       OBJECT IDENTIFIER ::= { axsVlan 10 }

    axsOadp                     OBJECT IDENTIFIER ::= { axsMib 7 }
    axsOadpMIBObjects           OBJECT IDENTIFIER ::= { axsOadp 1 }
    axsOadpGlobalInfo           OBJECT IDENTIFIER ::= { axsOadpMIBObjects 1 }
    axsOadpPortInfo             OBJECT IDENTIFIER ::= { axsOadpMIBObjects 2 }
    axsOadpNeighborInfo         OBJECT IDENTIFIER ::= { axsOadpMIBObjects 3 }
    axsOadpMIBNotifications     OBJECT IDENTIFIER ::= { axsOadp 2 }

    axsFlow                     OBJECT IDENTIFIER ::= { axsMib 8 }
    axsAccessFilterStats        OBJECT IDENTIFIER ::= { axsFlow 9 }
    axsQosFlowStats             OBJECT IDENTIFIER ::= { axsFlow 11 }

    axsPortChannel              OBJECT IDENTIFIER ::= { axsMib 9 }
    axsPortChannelPort          OBJECT IDENTIFIER ::= { axsPortChannel 1 }

    axsL2ld                     OBJECT IDENTIFIER ::= { axsMib 10 }
    axsL2ldGlobalInfo           OBJECT IDENTIFIER ::= { axsL2ld 1 }

    axsVrf                      OBJECT IDENTIFIER ::= { axsMib 11 }
    axsVrfIp                    OBJECT IDENTIFIER ::= { axsVrf 1 }
    axsVrfIpForward             OBJECT IDENTIFIER ::= { axsVrf 2 }
    axsVrfIpv6                  OBJECT IDENTIFIER ::= { axsVrf 3 }
    axsVrfIpv6Forward           OBJECT IDENTIFIER ::= { axsVrf 4 }

    axsEoEVpnMonitor            OBJECT IDENTIFIER ::= { axsMib 12 }

    axsOspf                     OBJECT IDENTIFIER ::= { axsMib 14 }
    axsOspfTrap                 OBJECT IDENTIFIER ::= { axsOspf 16 }
    axsOspfTraps                OBJECT IDENTIFIER ::= { axsOspfTrap 2 }
    axsOspfv3                   OBJECT IDENTIFIER ::= { axsMib 15 }

    axsStatic                   OBJECT IDENTIFIER ::= { axsMib 38 }
    axsStaticTrap               OBJECT IDENTIFIER ::= { axsStatic 2 }

    axsTrack                   OBJECT IDENTIFIER ::= { axsMib 40 }
    axsTrackGeneralGroup       OBJECT IDENTIFIER ::= { axsTrack 1 }
    axsTrackTraps              OBJECT IDENTIFIER ::= { axsTrack 2 }

    axsTrackObject             OBJECT IDENTIFIER ::= { axsMib 41 }
    axsTrackObjectGeneralGroup OBJECT IDENTIFIER ::= { axsTrackObject 1 }
    axsTrackObjectTraps        OBJECT IDENTIFIER ::= { axsTrackObject 2 }

    axsPolicyBase               OBJECT IDENTIFIER ::= { axsMib 45 }
    axsPolicyBaseRouting        OBJECT IDENTIFIER ::= { axsPolicyBase 1 }
    axsPolicyBaseSwitching      OBJECT IDENTIFIER ::= { axsPolicyBase 2 }

    axsAxrp                     OBJECT IDENTIFIER ::= { axsMib 200 }

    axsBootManagement           OBJECT IDENTIFIER ::= { axsMib 51 }
    axsLogin                    OBJECT IDENTIFIER ::= { axsMib 52 }

    axslldp                     OBJECT IDENTIFIER ::= { axsMib 100 }
    axslldpConfiguration        OBJECT IDENTIFIER ::= { axslldp 1 }
    axslldpStats                OBJECT IDENTIFIER ::= { axslldp 2 }
    axslldpLocalSystemData      OBJECT IDENTIFIER ::= { axslldp 3 }
    axslldpRemoteSystemData     OBJECT IDENTIFIER ::= { axslldp 4 }
    axslldpRemoteOriginInfoData OBJECT IDENTIFIER ::= { axslldp 20 }

    axsPconMIB                  OBJECT IDENTIFIER ::= { axsMib 300 }
    axsPconObjects              OBJECT IDENTIFIER ::= { axsPconMIB 1 }
    axsPconModuleData           OBJECT IDENTIFIER ::= { axsPconObjects 1 }
    axsPconPowerCon             OBJECT IDENTIFIER ::= { axsPconObjects 2 }
    axsPconTraffic              OBJECT IDENTIFIER ::= { axsPconObjects 3 }

    ax6300sSwitch               OBJECT IDENTIFIER ::= { ax6300sMib 1 }
    ax6300sSoftware             OBJECT IDENTIFIER ::= { ax6300sSwitch 2 }
    ax6300sSystemMsg            OBJECT IDENTIFIER ::= { ax6300sSwitch 3 }
    ax6300sSnmpAgent            OBJECT IDENTIFIER ::= { ax6300sSwitch 4 }
    ax6300sLicense              OBJECT IDENTIFIER ::= { ax6300sSwitch 6 }
    ax6300sDevice               OBJECT IDENTIFIER ::= { ax6300sMib 2 }
    ax6300sChassis              OBJECT IDENTIFIER ::= { ax6300sDevice 1 }
    ax6300sMsuBoard             OBJECT IDENTIFIER ::= { ax6300sDevice 2 }
    ax6300sNifBoard             OBJECT IDENTIFIER ::= { ax6300sDevice 4 }
    ax6300sPhysLine             OBJECT IDENTIFIER ::= { ax6300sDevice 5 }
    ax6300sInterface            OBJECT IDENTIFIER ::= { ax6300sDevice 6 }
    ax6300sManagementMIB        OBJECT IDENTIFIER ::= { ax6300sMib 3 }
    ax6300sOperationCommand     OBJECT IDENTIFIER ::= { ax6300sManagementMIB 1 }
    ax6300sFdbClearMIB          OBJECT IDENTIFIER ::= { ax6300sOperationCommand 1 }

    ax6700sSwitch               OBJECT IDENTIFIER ::= { ax6700sMib 1 }
    ax6700sSoftware             OBJECT IDENTIFIER ::= { ax6700sSwitch 2 }
    ax6700sSystemMsg            OBJECT IDENTIFIER ::= { ax6700sSwitch 3 }
    ax6700sSnmpAgent            OBJECT IDENTIFIER ::= { ax6700sSwitch 4 }
    ax6700sLicense              OBJECT IDENTIFIER ::= { ax6700sSwitch 6 }
    ax6700sDevice               OBJECT IDENTIFIER ::= { ax6700sMib 2 }
    ax6700sChassis              OBJECT IDENTIFIER ::= { ax6700sDevice 1 }
    ax6700sBcuBoard             OBJECT IDENTIFIER ::= { ax6700sDevice 2 }
    ax6700sBsuBoard             OBJECT IDENTIFIER ::= { ax6700sDevice 3 }
    ax6700sNifBoard             OBJECT IDENTIFIER ::= { ax6700sDevice 4 }
    ax6700sPhysLine             OBJECT IDENTIFIER ::= { ax6700sDevice 5 }
    ax6700sInterface            OBJECT IDENTIFIER ::= { ax6700sDevice 6 }
    ax6700sForwardingEngine     OBJECT IDENTIFIER ::= { ax6700sDevice 7 }
    ax6700sManagementMIB        OBJECT IDENTIFIER ::= { ax6700sMib 3 }
    ax6700sOperationCommand     OBJECT IDENTIFIER ::= { ax6700sManagementMIB 1 }
    ax6700sFdbClearMIB          OBJECT IDENTIFIER ::= { ax6700sOperationCommand 1 }

    ax6600sSwitch               OBJECT IDENTIFIER ::= { ax6600sMib 1 }
    ax6600sSoftware             OBJECT IDENTIFIER ::= { ax6600sSwitch 2 }
    ax6600sSystemMsg            OBJECT IDENTIFIER ::= { ax6600sSwitch 3 }
    ax6600sSnmpAgent            OBJECT IDENTIFIER ::= { ax6600sSwitch 4 }
    ax6600sLicense              OBJECT IDENTIFIER ::= { ax6600sSwitch 6 }
    ax6600sDevice               OBJECT IDENTIFIER ::= { ax6600sMib 2 }
    ax6600sChassis              OBJECT IDENTIFIER ::= { ax6600sDevice 1 }
    ax6600sCsuBoard             OBJECT IDENTIFIER ::= { ax6600sDevice 2 }
    ax6600sNifBoard             OBJECT IDENTIFIER ::= { ax6600sDevice 4 }
    ax6600sPhysLine             OBJECT IDENTIFIER ::= { ax6600sDevice 5 }
    ax6600sInterface            OBJECT IDENTIFIER ::= { ax6600sDevice 6 }
    ax6600sManagementMIB        OBJECT IDENTIFIER ::= { ax6600sMib 3 }
    ax6600sOperationCommand     OBJECT IDENTIFIER ::= { ax6600sManagementMIB 1 }
    ax6600sFdbClearMIB          OBJECT IDENTIFIER ::= { ax6600sOperationCommand 1 }

    axsIfStatsTable OBJECT-TYPE
        SYNTAX    SEQUENCE OF AxsIfStatsTableEntry
        ACCESS    not-accessible
        STATUS    mandatory
        DESCRIPTION
                  "A table containing extension statistics for more than 100,000,000
                  bps interface."
        ::= { axsIfStats 1 }

    axsIfStatsEntry OBJECT-TYPE
        SYNTAX    AxsIfStatsTableEntry
        ACCESS    not-accessible
        STATUS    mandatory
        DESCRIPTION
                  "An entry containing extension statistics for interface."
        INDEX     { axsIfStatsIndex }
        ::= { axsIfStatsTable 1 }

    AxsIfStatsTableEntry ::= SEQUENCE {
        axsIfStatsIndex                   INTEGER,
        axsIfStatsName                    DisplayString,
        axsIfStatsInMegaOctets            Counter,
        axsIfStatsInUcastMegaPkts         Counter,
        axsIfStatsInMulticastMegaPkts     Counter,
        axsIfStatsInBroadcastMegaPkts     Counter,
        axsIfStatsOutMegaOctets           Counter,
        axsIfStatsOutUcastMegaPkts        Counter,
        axsIfStatsOutMulticastMegaPkts    Counter,
        axsIfStatsOutBroadcastMegaPkts    Counter,
        axsIfStatsHighSpeed               Counter
    }

    axsIfStatsIndex OBJECT-TYPE
        SYNTAX    INTEGER
        ACCESS    not-accessible
        STATUS    mandatory
        DESCRIPTION
                  "This object value is same as Ifindex which interface index
                  of a system."
        ::= { axsIfStatsEntry 1 }

    axsIfStatsName OBJECT-TYPE
        SYNTAX    DisplayString
        ACCESS    read-only
        STATUS    mandatory
        DESCRIPTION
                  "Interfaces name. Same as ifDescr."
        ::= { axsIfStatsEntry 2 }

    axsIfStatsInMegaOctets OBJECT-TYPE
        SYNTAX    Counter
        ACCESS    read-only
        STATUS    mandatory
        DESCRIPTION
                  "Number of octets that received on the interface. This value is
                  displayed in mega-octets(M). Value of 0 through 999,999 are rounded
                  down."
        ::= { axsIfStatsEntry 3 }

    axsIfStatsInUcastMegaPkts OBJECT-TYPE
        SYNTAX    Counter
        ACCESS    read-only
        STATUS    mandatory
        DESCRIPTION
                  "Number of subnetwork-unicast packets that received on the interface.
                  This value is displayed in mega-packets(M).Value of 0 through 999,999
                  are rounded down."
        ::= { axsIfStatsEntry 4 }

    axsIfStatsInMulticastMegaPkts OBJECT-TYPE
        SYNTAX    Counter
        ACCESS    read-only
        STATUS    mandatory
        DESCRIPTION
                  "Number of multicast mega-packets that received on the interface.
                  this value is displayed in mega-packets(M).Value of 0 through 999,999
                  are rounded down."
        ::= { axsIfStatsEntry 5 }

    axsIfStatsInBroadcastMegaPkts OBJECT-TYPE
        SYNTAX    Counter
        ACCESS    read-only
        STATUS    mandatory
        DESCRIPTION
                  "The number of non-unicast packets delivered to a higher-layer
                  protocol. The value is displayed in mega-packets (M). Value of 0
                  through 999,999 are rounded down. "
        ::= { axsIfStatsEntry 6 }

    axsIfStatsOutMegaOctets OBJECT-TYPE
        SYNTAX    Counter
        ACCESS    read-only
        STATUS    mandatory
        DESCRIPTION
                  "The total number of octets transmitted out of the interface.
                  The value is displayed in mega-octets(M). Value of 0 through 999,999
                  are rounded down."
        ::= { axsIfStatsEntry 7 }

    axsIfStatsOutUcastMegaPkts OBJECT-TYPE
        SYNTAX    Counter
        ACCESS    read-only
        STATUS    mandatory
        DESCRIPTION
                  "The total number of packets that higher-level protocols requested
                  be transmitted to a subnetwork-unicast address.The value is displayed
                  in mega packets(M). Value of 0 through 999,999 are rounded down."
        ::= { axsIfStatsEntry 8 }

    axsIfStatsOutMulticastMegaPkts OBJECT-TYPE
        SYNTAX    Counter
        ACCESS    read-only
        STATUS    mandatory
        DESCRIPTION
                  "Number of multicast packets that transmitted on the interface.
                  This value is displayed in mega-packets(M). Value of 0 through
                  999,999 are rounded down."
        ::= { axsIfStatsEntry 9 }

    axsIfStatsOutBroadcastMegaPkts OBJECT-TYPE
        SYNTAX    Counter
        ACCESS    read-only
        STATUS    mandatory
        DESCRIPTION
                  "Number of broadcast packets that transmitted on the interface.
                  This value is displayed in mega-packets(M). Value of 0 through
                  999,999 are rounded down. "
        ::= { axsIfStatsEntry 10 }

    axsIfStatsHighSpeed OBJECT-TYPE
        SYNTAX    Counter
        ACCESS    read-only
        STATUS    mandatory
        DESCRIPTION
                  "A circuit speed.This value is displayed in mega-bps[Mbps].
                  Round off the 1,000,000bps. "
        ::= { axsIfStatsEntry 11 }

-- QoS interface statistics Variables

    axsEtherTxQoSStatsTable OBJECT-TYPE
        SYNTAX    SEQUENCE OF AxsEtherTxQoSStatsEntry
        ACCESS    not-accessible
        STATUS    mandatory
        DESCRIPTION
                  "A collection of QoS statistics kept for a particular
                  Ethernet interface."
        ::= { axsEtherTxQoS 1 }

    axsEtherTxQoSStatsEntry OBJECT-TYPE
        SYNTAX    AxsEtherTxQoSStatsEntry
        ACCESS    not-accessible
        STATUS    mandatory
        DESCRIPTION
                  "An entry containing QoS statistics for a particular 
                  Ethernet interface."
        INDEX     { axsEtherTxQoSStatsIndex }
        ::= { axsEtherTxQoSStatsTable 1 }

    AxsEtherTxQoSStatsEntry ::= SEQUENCE {
        axsEtherTxQoSStatsIndex                 INTEGER,
        axsEtherTxQoSStatsMaxQnum               INTEGER,
        axsEtherTxQoSStatsLimitQlen             INTEGER,
        axsEtherTxQoSStatsTotalOutFrames        Counter,
        axsEtherTxQoSStatsTotalOutBytesHigh     Counter,
        axsEtherTxQoSStatsTotalOutBytesLow      Counter,
        axsEtherTxQoSStatsTotalDiscardFrames    Counter
    }

    axsEtherTxQoSStatsIndex OBJECT-TYPE
        SYNTAX    INTEGER
        ACCESS    not-accessible
        STATUS    mandatory
        DESCRIPTION
                  "Identified by a particular value of this
                  index is same value of ifIndex.Its value ranges
                  between 1 and the value of ifNumber."
        ::= { axsEtherTxQoSStatsEntry 1 }

    axsEtherTxQoSStatsMaxQnum OBJECT-TYPE
        SYNTAX    INTEGER
        ACCESS    read-only
        STATUS    mandatory
        DESCRIPTION
                  "Max length of queue for an ethernet interface."
        ::= { axsEtherTxQoSStatsEntry 2 }

    axsEtherTxQoSStatsLimitQlen OBJECT-TYPE
        SYNTAX    INTEGER
        ACCESS    read-only
        STATUS    mandatory
        DESCRIPTION
                  "The limit length of outband queue for an ethernet interface."
        ::= { axsEtherTxQoSStatsEntry 3 }

    axsEtherTxQoSStatsTotalOutFrames OBJECT-TYPE
        SYNTAX    Counter
        ACCESS    read-only
        STATUS    mandatory
        DESCRIPTION
                  "The total number of  packets transmitted out of the
                  interface."
        ::= { axsEtherTxQoSStatsEntry 4 }

    axsEtherTxQoSStatsTotalOutBytesHigh OBJECT-TYPE
        SYNTAX    Counter
        ACCESS    read-only
        STATUS    mandatory
        DESCRIPTION
                  "The total number of octets transmitted out of the
                  interface."
        ::= { axsEtherTxQoSStatsEntry 5 }

    axsEtherTxQoSStatsTotalOutBytesLow OBJECT-TYPE
        SYNTAX    Counter
        ACCESS    read-only
        STATUS    mandatory
        DESCRIPTION
                  "The total number of octets transmitted out of the
                  interface."
        ::= { axsEtherTxQoSStatsEntry 6 }

    axsEtherTxQoSStatsTotalDiscardFrames OBJECT-TYPE
        SYNTAX    Counter
        ACCESS    read-only
        STATUS    mandatory
        DESCRIPTION
                  "The number of outbound packets which were chosen
                  to be discarded ."
        ::= { axsEtherTxQoSStatsEntry 7 }

    axsEtherTxQoSStatsQueueTable OBJECT-TYPE
        SYNTAX    SEQUENCE OF AxsEtherTxQoSStatsQueueEntry
        ACCESS    not-accessible
        STATUS    mandatory
        DESCRIPTION
                  "A collection of priority queue statistics."
        ::= { axsEtherTxQoS 2 }

    axsEtherTxQoSStatsQueueEntry OBJECT-TYPE
        SYNTAX    AxsEtherTxQoSStatsQueueEntry
        ACCESS    not-accessible
        STATUS    mandatory
        DESCRIPTION
                  "A entry of priority queue statistics."
        INDEX     { axsEtherTxQoSStatsQueueIndex,
                    axsEtherTxQoSStatsQueueQueIndex }
        ::= { axsEtherTxQoSStatsQueueTable 1 }

    AxsEtherTxQoSStatsQueueEntry ::= SEQUENCE {
        axsEtherTxQoSStatsQueueIndex                  INTEGER,
        axsEtherTxQoSStatsQueueQueIndex               INTEGER,
        axsEtherTxQoSStatsQueueQlen                   INTEGER,
        axsEtherTxQoSStatsQueueMaxQlen                INTEGER,
        axsEtherTxQoSStatsQueueDiscardFramesClass1    Counter64,
        axsEtherTxQoSStatsQueueDiscardFramesClass2    Counter64,
        axsEtherTxQoSStatsQueueDiscardFramesClass3    Counter64,
        axsEtherTxQoSStatsQueueDiscardFramesClass4    Counter64
    }

    axsEtherTxQoSStatsQueueIndex OBJECT-TYPE
        SYNTAX    INTEGER
        ACCESS    not-accessible
        STATUS    mandatory
        DESCRIPTION
                  "Identified by a particular value of this
                  index is same value of ifIndex.Its value ranges
                  between 1 and the value of ifNumber."
        ::= { axsEtherTxQoSStatsQueueEntry 1 }

    axsEtherTxQoSStatsQueueQueIndex OBJECT-TYPE
        SYNTAX    INTEGER
        ACCESS    not-accessible
        STATUS    mandatory
        DESCRIPTION
                  "An index that uniquely identifies the particular
                  queue.Its value ranges between 1 and the value of
                  axsEtherTxQoSStatsMaxQnum."
        ::= { axsEtherTxQoSStatsQueueEntry 2 }

    axsEtherTxQoSStatsQueueQlen OBJECT-TYPE
        SYNTAX    INTEGER
        ACCESS    read-only
        STATUS    mandatory
        DESCRIPTION
                  "A length of outbound priority queue for a interface."
        ::= { axsEtherTxQoSStatsQueueEntry 3 }

    axsEtherTxQoSStatsQueueMaxQlen OBJECT-TYPE
        SYNTAX    INTEGER
        ACCESS    read-only
        STATUS    mandatory
        DESCRIPTION
                  "Max length of outband priority queue for a interface since
                  system was up."
        ::= { axsEtherTxQoSStatsQueueEntry 4 }

    axsEtherTxQoSStatsQueueDiscardFramesClass1 OBJECT-TYPE
        SYNTAX    Counter64
        ACCESS    read-only
        STATUS    mandatory
        DESCRIPTION
                  "The number of discard frames in the discard class 
                   1 of output priority queue."
        ::= { axsEtherTxQoSStatsQueueEntry 5 }

    axsEtherTxQoSStatsQueueDiscardFramesClass2 OBJECT-TYPE
        SYNTAX    Counter64
        ACCESS    read-only
        STATUS    mandatory
        DESCRIPTION
                  "The number of discard frames in the discard class 
                   2 of output priority queue."
        ::= { axsEtherTxQoSStatsQueueEntry 6 }

    axsEtherTxQoSStatsQueueDiscardFramesClass3 OBJECT-TYPE
        SYNTAX    Counter64
        ACCESS    read-only
        STATUS    mandatory
        DESCRIPTION
                  "The number of discard frames in the discard class 
                   3 of output priority queue."
        ::= { axsEtherTxQoSStatsQueueEntry 7 }

    axsEtherTxQoSStatsQueueDiscardFramesClass4 OBJECT-TYPE
        SYNTAX    Counter64
        ACCESS    read-only
        STATUS    mandatory
        DESCRIPTION
                  "The number of discard frames in the discard class 
                   4 of output priority queue."
        ::= { axsEtherTxQoSStatsQueueEntry 8 }

    axsShaperPortBufTable OBJECT-TYPE
        SYNTAX    SEQUENCE OF AxsShaperPortBufEntry
        ACCESS    not-accessible
        STATUS    mandatory
        DESCRIPTION
                  "Statistics of shaper port buffers."
        ::= { axsShaperUser 1 }

    axsShaperPortBufEntry OBJECT-TYPE
        SYNTAX    AxsShaperPortBufEntry
        ACCESS    not-accessible
        STATUS    mandatory
        DESCRIPTION
                  "Statistics of a shaper port buffer."
        INDEX     { axsShaperPortNifIndex,
                    axsShaperPortLineIndex,
                    axsShaperPortQosIndex }
        ::= { axsShaperPortBufTable 1 }

    AxsShaperPortBufEntry ::= SEQUENCE {
        axsShaperPortNifIndex       INTEGER,
        axsShaperPortLineIndex      INTEGER,
        axsShaperPortQosIndex       INTEGER,
        axsShaperPortBuffer         INTEGER,
        axsShaperPortPeakBuffer     INTEGER,
        axsShaperPortLimitBuffer    INTEGER
    }

    axsShaperPortNifIndex OBJECT-TYPE
        SYNTAX    INTEGER
        ACCESS    not-accessible
        STATUS    mandatory
        DESCRIPTION
                  "Slot number of a shaper port, ranging between 1 and ax6300sNifBoardNumber
                   or ax6600sNifBoardNumber or ax6700sNifBoardNumber."
        ::= { axsShaperPortBufEntry 1 }

    axsShaperPortLineIndex OBJECT-TYPE
        SYNTAX    INTEGER
        ACCESS    not-accessible
        STATUS    mandatory
        DESCRIPTION
                  "Slot number of a shaper port, ranging between 1 and ax6300sNifPhysLineNumber
                   or ax6600sNifPhysLineNumber or ax6700sNifPhysLineNumber."
        ::= { axsShaperPortBufEntry 2 }

    axsShaperPortQosIndex OBJECT-TYPE
        SYNTAX    INTEGER
        ACCESS    not-accessible
        STATUS    mandatory
        DESCRIPTION
                  "Queue identifier, ranging from 1 to 4(4 queue mode) or 8(8 queue mode)."
        ::= { axsShaperPortBufEntry 3 }

    axsShaperPortBuffer OBJECT-TYPE
        SYNTAX    INTEGER
        ACCESS    read-only
        STATUS    mandatory
        DESCRIPTION
                  "The number of packets in a shaper port buffer."
        ::= { axsShaperPortBufEntry 4 }

    axsShaperPortPeakBuffer OBJECT-TYPE
        SYNTAX    INTEGER
        ACCESS    read-only
        STATUS    mandatory
        DESCRIPTION
                  "The peak number of packets in a shaper port buffer."
        ::= { axsShaperPortBufEntry 5 }

    axsShaperPortLimitBuffer OBJECT-TYPE
        SYNTAX    INTEGER
        ACCESS    read-only
        STATUS    mandatory
        DESCRIPTION
                  "The upper limit number of packets in a shaper port buffer."
        ::= { axsShaperPortBufEntry 6 }

    axsShaperUserTable OBJECT-TYPE
        SYNTAX    SEQUENCE OF AxsShaperUserEntry
        ACCESS    not-accessible
        STATUS    mandatory
        DESCRIPTION
                  "Statistics of shaper users."
        ::= { axsShaperUser 3 }

    axsShaperUserEntry OBJECT-TYPE
        SYNTAX    AxsShaperUserEntry
        ACCESS    not-accessible
        STATUS    mandatory
        DESCRIPTION
                  "Statistics of a shaper user."
        INDEX     { axsShaperUserNifIndex,
                    axsShaperUserLineIndex,
                    axsShaperUserGroupId,
                    axsShaperUserId }
        ::= { axsShaperUserTable 1 }

    AxsShaperUserEntry ::= SEQUENCE {
        axsShaperUserNifIndex                   INTEGER,
        axsShaperUserLineIndex                  INTEGER,
        axsShaperUserGroupId                    INTEGER,
        axsShaperUserId                         INTEGER,
        axsShaperUserStatsTotalOutFrames        Counter64,
        axsShaperUserStatsTotalOutBytes         Counter64,
        axsShaperUserStatsTotalDiscardFrames    Counter64,
        axsShaperUserStatsTotalDiscardBytes     Counter64
    }

    axsShaperUserNifIndex OBJECT-TYPE
        SYNTAX    INTEGER
        ACCESS    not-accessible
        STATUS    mandatory
        DESCRIPTION
                  "Slot number of a shaper port, ranging between 1 and ax6300sNifBoardNumber
                   or ax6600sNifBoardNumber or ax6700sNifBoardNumber."
        ::= { axsShaperUserEntry 1 }

    axsShaperUserLineIndex OBJECT-TYPE
        SYNTAX    INTEGER
        ACCESS    not-accessible
        STATUS    mandatory
        DESCRIPTION
                  "Slot number of a shaper port, ranging between 1 and ax6300sNifPhysLineNumber
                   or ax6600sNifPhysLineNumber or ax6700sNifPhysLineNumber."
        ::= { axsShaperUserEntry 2 }

    axsShaperUserGroupId OBJECT-TYPE
        SYNTAX    INTEGER
        ACCESS    not-accessible
        STATUS    mandatory
        DESCRIPTION
                  "Shaper group identifier, fixed to 1."
        ::= { axsShaperUserEntry 3 }

    axsShaperUserId OBJECT-TYPE
        SYNTAX    INTEGER
        ACCESS    not-accessible
        STATUS    mandatory
        DESCRIPTION
                  "Shaper user identifier, ranging between 1 and 1024."
        ::= { axsShaperUserEntry 4 }

    axsShaperUserStatsTotalOutFrames OBJECT-TYPE
        SYNTAX    Counter64
        ACCESS    read-only
        STATUS    mandatory
        DESCRIPTION
                  "The total number of transmitted frames from a shaper user."
        ::= { axsShaperUserEntry 5 }

    axsShaperUserStatsTotalOutBytes OBJECT-TYPE
        SYNTAX    Counter64
        ACCESS    read-only
        STATUS    mandatory
        DESCRIPTION
                  "The total number of transmitted bytes from a shaper user."
        ::= { axsShaperUserEntry 6 }

    axsShaperUserStatsTotalDiscardFrames OBJECT-TYPE
        SYNTAX    Counter64
        ACCESS    read-only
        STATUS    mandatory
        DESCRIPTION
                  "The total number of discarded frames from a shaper user."
        ::= { axsShaperUserEntry 7 }

    axsShaperUserStatsTotalDiscardBytes OBJECT-TYPE
        SYNTAX    Counter64
        ACCESS    read-only
        STATUS    mandatory
        DESCRIPTION
                  "The total number of discarded bytes from a shaper user."
        ::= { axsShaperUserEntry 8 }

    axsShaperUserStatsQueueTable OBJECT-TYPE
        SYNTAX    SEQUENCE OF AxsShaperUserStatsQueueEntry
        ACCESS    not-accessible
        STATUS    mandatory
        DESCRIPTION
                  "Statistics of shaper user queues."
        ::= { axsShaperUser 4 }

    axsShaperUserStatsQueueEntry OBJECT-TYPE
        SYNTAX    AxsShaperUserStatsQueueEntry
        ACCESS    not-accessible
        STATUS    mandatory
        DESCRIPTION
                  "Statistics of a shaper user queue."
        INDEX     { axsShaperUserStatsQueueNifIndex,
                    axsShaperUserStatsQueueLineIndex,
                    axsShaperUserStatsQueueGroupId,
                    axsShaperUserStatsQueueUserId,
                    axsShaperUserStatsQueueNumber }
        ::= { axsShaperUserStatsQueueTable 1 }

    AxsShaperUserStatsQueueEntry ::= SEQUENCE {
        axsShaperUserStatsQueueNifIndex         INTEGER,
        axsShaperUserStatsQueueLineIndex        INTEGER,
        axsShaperUserStatsQueueGroupId          INTEGER,
        axsShaperUserStatsQueueUserId           INTEGER,
        axsShaperUserStatsQueueNumber           INTEGER,
        axsShaperUserStatsQueueOutFrames        Counter64,
        axsShaperUserStatsQueueOutBytes         Counter64,
        axsShaperUserStatsQueueDiscardFrames    Counter64,
        axsShaperUserStatsQueueDiscardBytes     Counter64,
        axsShaperUserStatsQueueQlen             Counter64,
        axsShaperUserStatsQueuePeakQlen         Counter64,
        axsShaperUserStatsQueueLimitQlen        Counter64
    }

    axsShaperUserStatsQueueNifIndex OBJECT-TYPE
        SYNTAX    INTEGER
        ACCESS    not-accessible
        STATUS    mandatory
        DESCRIPTION
                  "Slot number of a shaper port, ranging between 1 and ax6300sNifBoardNumber
                   or ax6600sNifBoardNumber or ax6700sNifBoardNumber."
        ::= { axsShaperUserStatsQueueEntry 1 }

    axsShaperUserStatsQueueLineIndex OBJECT-TYPE
        SYNTAX    INTEGER
        ACCESS    not-accessible
        STATUS    mandatory
        DESCRIPTION
                  "Slot number of a shaper port, ranging between 1 and ax6300sNifPhysLineNumber
                   or ax6600sNifPhysLineNumber or ax6700sNifPhysLineNumber."
        ::= { axsShaperUserStatsQueueEntry 2 }

    axsShaperUserStatsQueueGroupId OBJECT-TYPE
        SYNTAX    INTEGER
        ACCESS    not-accessible
        STATUS    mandatory
        DESCRIPTION
                  "Shaper group identifier, fixed to 1."
        ::= { axsShaperUserStatsQueueEntry 3 }

    axsShaperUserStatsQueueUserId OBJECT-TYPE
        SYNTAX    INTEGER
        ACCESS    not-accessible
        STATUS    mandatory
        DESCRIPTION
                  "Shaper user identifier, ranging between 1 and 1024."
        ::= { axsShaperUserStatsQueueEntry 4 }

    axsShaperUserStatsQueueNumber OBJECT-TYPE
        SYNTAX    INTEGER
        ACCESS    not-accessible
        STATUS    mandatory
        DESCRIPTION
                  "Queue identifier, ranging from 1 to 4(4 queue mode) or 8(8 queue mode)."
        ::= { axsShaperUserStatsQueueEntry 5 }

    axsShaperUserStatsQueueOutFrames OBJECT-TYPE
        SYNTAX    Counter64
        ACCESS    read-only
        STATUS    mandatory
        DESCRIPTION
                  "The number of transmitted frames from a shaper user queue."
        ::= { axsShaperUserStatsQueueEntry 6 }

    axsShaperUserStatsQueueOutBytes OBJECT-TYPE
        SYNTAX    Counter64
        ACCESS    read-only
        STATUS    mandatory
        DESCRIPTION
                  "The number of transmitted bytes from a shaper user queue."
        ::= { axsShaperUserStatsQueueEntry 7 }

    axsShaperUserStatsQueueDiscardFrames OBJECT-TYPE
        SYNTAX    Counter64
        ACCESS    read-only
        STATUS    mandatory
        DESCRIPTION
                  "The number of discarded frames in a shaper user queue."
        ::= { axsShaperUserStatsQueueEntry 8 }

    axsShaperUserStatsQueueDiscardBytes OBJECT-TYPE
        SYNTAX    Counter64
        ACCESS    read-only
        STATUS    mandatory
        DESCRIPTION
                  "The number of discarded bytes in a shaper user queue."
        ::= { axsShaperUserStatsQueueEntry 9 }

    axsShaperUserStatsQueueQlen OBJECT-TYPE
        SYNTAX    Counter64
        ACCESS    read-only
        STATUS    mandatory
        DESCRIPTION
                  "The number of packets in a shaper user queue."
        ::= { axsShaperUserStatsQueueEntry 10 }

    axsShaperUserStatsQueuePeakQlen OBJECT-TYPE
        SYNTAX    Counter64
        ACCESS    read-only
        STATUS    mandatory
        DESCRIPTION
                  "The peak number of packets in a shaper user queue."
        ::= { axsShaperUserStatsQueueEntry 11 }

    axsShaperUserStatsQueueLimitQlen OBJECT-TYPE
        SYNTAX    Counter64
        ACCESS    read-only
        STATUS    mandatory
        DESCRIPTION
                  "The upper limit number of packets in a shaper user queue."
        ::= { axsShaperUserStatsQueueEntry 12 }

    axsEtherRxQoSStatsTable OBJECT-TYPE
        SYNTAX    SEQUENCE OF AxsEtherRxQoSStatsEntry
        ACCESS    not-accessible
        STATUS    mandatory
        DESCRIPTION
                  "Table information on the QoS statistics about the port receiving queue."
        ::= { axsEtherRxQoS 1 }

    axsEtherRxQoSStatsEntry OBJECT-TYPE
        SYNTAX    AxsEtherRxQoSStatsEntry
        ACCESS    not-accessible
        STATUS    mandatory
        DESCRIPTION
                  "Entry concerning corresponding QoS statistics about the port receiving queue."
        INDEX     { axsEtherRxQoSStatsIndex }
        ::= { axsEtherRxQoSStatsTable 1 }

    AxsEtherRxQoSStatsEntry ::= SEQUENCE {
        axsEtherRxQoSStatsIndex                 INTEGER,
        axsEtherRxQoSStatsMaxQnum               INTEGER,
        axsEtherRxQoSStatsLimitQlen             INTEGER,
        axsEtherRxQoSStatsTotalOutFrames        Counter,
        axsEtherRxQoSStatsTotalOutBytesHigh     Counter,
        axsEtherRxQoSStatsTotalOutBytesLow      Counter,
        axsEtherRxQoSStatsTotalDiscardFrames    Counter
    }

    axsEtherRxQoSStatsIndex OBJECT-TYPE
        SYNTAX    INTEGER
        ACCESS    not-accessible
        STATUS    mandatory
        DESCRIPTION
                  "The index value (ifIndex value of an Ethernet interface) which identifies
                   the entry of this table. Values between 1 and ifNumber."
        ::= { axsEtherRxQoSStatsEntry 1 }

    axsEtherRxQoSStatsMaxQnum OBJECT-TYPE
        SYNTAX    INTEGER
        ACCESS    read-only
        STATUS    mandatory
        DESCRIPTION
                  "The number of queues of the port receiving queue."
        ::= { axsEtherRxQoSStatsEntry 2 }

    axsEtherRxQoSStatsLimitQlen OBJECT-TYPE
        SYNTAX    INTEGER
        ACCESS    read-only
        STATUS    mandatory
        DESCRIPTION
                  "The limit length of the priority queue of the port receiving queue."
        ::= { axsEtherRxQoSStatsEntry 3 }

    axsEtherRxQoSStatsTotalOutFrames OBJECT-TYPE
        SYNTAX    Counter
        ACCESS    read-only
        STATUS    mandatory
        DESCRIPTION
                  "The total number of received frames of the port receiving queue."
        ::= { axsEtherRxQoSStatsEntry 4 }

    axsEtherRxQoSStatsTotalOutBytesHigh OBJECT-TYPE
        SYNTAX    Counter
        ACCESS    read-only
        STATUS    mandatory
        DESCRIPTION
                  "The total number of received bytes (the high order 4-bytes) of the port receiving queue ."
        ::= { axsEtherRxQoSStatsEntry 5 }

    axsEtherRxQoSStatsTotalOutBytesLow OBJECT-TYPE
        SYNTAX    Counter
        ACCESS    read-only
        STATUS    mandatory
        DESCRIPTION
                  "The total number of received bytes (the low order 4-bytes) of the port receiving queue."
        ::= { axsEtherRxQoSStatsEntry 6 }

    axsEtherRxQoSStatsTotalDiscardFrames OBJECT-TYPE
        SYNTAX    Counter
        ACCESS    read-only
        STATUS    mandatory
        DESCRIPTION
                  "The total number of discarded frames of the port receiving queue."
        ::= { axsEtherRxQoSStatsEntry 7 }

    axsEtherRxQoSStatsQueueTable OBJECT-TYPE
        SYNTAX    SEQUENCE OF AxsEtherRxQoSStatsQueueEntry
        ACCESS    not-accessible
        STATUS    mandatory
        DESCRIPTION
                  "Table information on the QoS statistics of priority queue
                   about the port receiving queue ."
        ::= { axsEtherRxQoS 2 }

    axsEtherRxQoSStatsQueueEntry OBJECT-TYPE
        SYNTAX    AxsEtherRxQoSStatsQueueEntry
        ACCESS    not-accessible
        STATUS    mandatory
        DESCRIPTION
                  "Entry concerning corresponding QoS statistics of priority queue
                   about the port receiving queue."
        INDEX     { axsEtherRxQoSStatsQueueIndex,
                    axsEtherRxQoSStatsQueueQueIndex }
        ::= { axsEtherRxQoSStatsQueueTable 1 }

    AxsEtherRxQoSStatsQueueEntry ::= SEQUENCE {
        axsEtherRxQoSStatsQueueIndex                  INTEGER,
        axsEtherRxQoSStatsQueueQueIndex               INTEGER,
        axsEtherRxQoSStatsQueueQlen                   INTEGER,
        axsEtherRxQoSStatsQueueMaxQlen                INTEGER,
        axsEtherRxQoSStatsQueueDiscardFramesClass1    Counter64,
        axsEtherRxQoSStatsQueueDiscardFramesClass2    Counter64
    }

    axsEtherRxQoSStatsQueueIndex OBJECT-TYPE
        SYNTAX    INTEGER
        ACCESS    not-accessible
        STATUS    mandatory
        DESCRIPTION
                  "The index value (ifIndex value of an Ethernet interface) which
                   identifies the entry of this table. Values between 1 and ifNumber."
        ::= { axsEtherRxQoSStatsQueueEntry 1 }

    axsEtherRxQoSStatsQueueQueIndex OBJECT-TYPE
        SYNTAX    INTEGER
        ACCESS    not-accessible
        STATUS    mandatory
        DESCRIPTION
                  "The index value which identifies the entry of this table.
                   Values between 1 and axsEtherRxQoSStatsMaxQnum."
        ::= { axsEtherRxQoSStatsQueueEntry 2 }

    axsEtherRxQoSStatsQueueQlen OBJECT-TYPE
        SYNTAX    INTEGER
        ACCESS    read-only
        STATUS    mandatory
        DESCRIPTION
                  "A length of priority queue about the port receiving queue."
        ::= { axsEtherRxQoSStatsQueueEntry 3 }

    axsEtherRxQoSStatsQueueMaxQlen OBJECT-TYPE
        SYNTAX    INTEGER
        ACCESS    read-only
        STATUS    mandatory
        DESCRIPTION
                  "The highest queue length of priority queue about the port receiving queue
                   after being cleared or initialized."
        ::= { axsEtherRxQoSStatsQueueEntry 4 }

    axsEtherRxQoSStatsQueueDiscardFramesClass1 OBJECT-TYPE
        SYNTAX    Counter64
        ACCESS    read-only
        STATUS    mandatory
        DESCRIPTION
                  "The number of discarded frames in the discard class 1 of priority queue
                   about the port receiving queue."
        ::= { axsEtherRxQoSStatsQueueEntry 5 }

    axsEtherRxQoSStatsQueueDiscardFramesClass2 OBJECT-TYPE
        SYNTAX    Counter64
        ACCESS    read-only
        STATUS    mandatory
        DESCRIPTION
                  "The number of discarded frames in the discard class 2 of priority queue
                   about the port receiving queue."
        ::= { axsEtherRxQoSStatsQueueEntry 6 }

    axsEtherDistributionTxQoSStatsTable OBJECT-TYPE
        SYNTAX    SEQUENCE OF AxsEtherDistributionTxQoSStatsEntry
        ACCESS    not-accessible
        STATUS    mandatory
        DESCRIPTION
                  "Table information on the QoS statistics about the distribution sending queue."
        ::= { axsEtherDistributionTxQoS 1 }

    axsEtherDistributionTxQoSStatsEntry OBJECT-TYPE
        SYNTAX    AxsEtherDistributionTxQoSStatsEntry
        ACCESS    not-accessible
        STATUS    mandatory
        DESCRIPTION
                  "An entry containing QoS statistics for a particular Ethernet interface."
        INDEX     { axsEtherDistributionTxQoSStatsIndex,
                    axsEtherDistributionTxQoSStatsIfIndex }
        ::= { axsEtherDistributionTxQoSStatsTable 1 }

    AxsEtherDistributionTxQoSStatsEntry ::= SEQUENCE {
        axsEtherDistributionTxQoSStatsIndex                 INTEGER,
        axsEtherDistributionTxQoSStatsIfIndex               INTEGER,
        axsEtherDistributionTxQoS1StatsMaxQnum              INTEGER,
        axsEtherDistributionTxQoS1StatsLimitQlen            INTEGER,
        axsEtherDistributionTxQoS1StatsTotalOutFrames       Counter,
        axsEtherDistributionTxQoS1StatsTotalOutBytesHigh    Counter,
        axsEtherDistributionTxQoS1StatsTotalOutBytesLow     Counter,
        axsEtherDistributionTxQoS1StatsTotalDiscardFrames   Counter,
        axsEtherDistributionTxQoS2StatsMaxQnum              INTEGER,
        axsEtherDistributionTxQoS2StatsLimitQlen            INTEGER,
        axsEtherDistributionTxQoS2StatsTotalOutFrames       Counter,
        axsEtherDistributionTxQoS2StatsTotalOutBytesHigh    Counter,
        axsEtherDistributionTxQoS2StatsTotalOutBytesLow     Counter,
        axsEtherDistributionTxQoS2StatsTotalDiscardFrames   Counter
    }

    axsEtherDistributionTxQoSStatsIndex OBJECT-TYPE
        SYNTAX    INTEGER
        ACCESS    not-accessible
        STATUS    mandatory
        DESCRIPTION
                  "The number in the part in which the distribution sending queue exists."
        ::= { axsEtherDistributionTxQoSStatsEntry 1 }

    axsEtherDistributionTxQoSStatsIfIndex OBJECT-TYPE
        SYNTAX    INTEGER
        ACCESS    not-accessible
        STATUS    mandatory
        DESCRIPTION
                  "The index value (ifIndex value of an Ethernet interface)
                   which identifies the entry of this table. Values between 1 and ifNumber."
        ::= { axsEtherDistributionTxQoSStatsEntry 2 }

    axsEtherDistributionTxQoS1StatsMaxQnum OBJECT-TYPE
        SYNTAX    INTEGER
        ACCESS    read-only
        STATUS    mandatory
        DESCRIPTION
                  "The number of queues of the distribution sending queue 1."
        ::= { axsEtherDistributionTxQoSStatsEntry 3 }

    axsEtherDistributionTxQoS1StatsLimitQlen OBJECT-TYPE
        SYNTAX    INTEGER
        ACCESS    read-only
        STATUS    mandatory
        DESCRIPTION
                  "The limit length of the priority queue of the distribution sending queue 1."
        ::= { axsEtherDistributionTxQoSStatsEntry 4 }

    axsEtherDistributionTxQoS1StatsTotalOutFrames OBJECT-TYPE
        SYNTAX    Counter
        ACCESS    read-only
        STATUS    mandatory
        DESCRIPTION
                  "The total number of sent frames of the distribution sending queue 1."
        ::= { axsEtherDistributionTxQoSStatsEntry 5 }

    axsEtherDistributionTxQoS1StatsTotalOutBytesHigh OBJECT-TYPE
        SYNTAX    Counter
        ACCESS    read-only
        STATUS    mandatory
        DESCRIPTION
                  "The total number of sent bytes (the high order 4-bytes) of the distribution sending queue 1."
        ::= { axsEtherDistributionTxQoSStatsEntry 6 }

    axsEtherDistributionTxQoS1StatsTotalOutBytesLow OBJECT-TYPE
        SYNTAX    Counter
        ACCESS    read-only
        STATUS    mandatory
        DESCRIPTION
                  "The total number of sent bytes (the low order 4-bytes) of the distribution sending queue 1."
        ::= { axsEtherDistributionTxQoSStatsEntry 7 }

    axsEtherDistributionTxQoS1StatsTotalDiscardFrames OBJECT-TYPE
        SYNTAX    Counter
        ACCESS    read-only
        STATUS    mandatory
        DESCRIPTION
                  "The total number of discarded frames of the distribution sending queue 1."
        ::= { axsEtherDistributionTxQoSStatsEntry 8 }

    axsEtherDistributionTxQoS2StatsMaxQnum OBJECT-TYPE
        SYNTAX    INTEGER
        ACCESS    read-only
        STATUS    mandatory
        DESCRIPTION
                  "The number of queues of the distribution sending queue 2."
        ::= { axsEtherDistributionTxQoSStatsEntry 9 }

    axsEtherDistributionTxQoS2StatsLimitQlen OBJECT-TYPE
        SYNTAX    INTEGER
        ACCESS    read-only
        STATUS    mandatory
        DESCRIPTION
                  "The limit length of the priority queue of the distribution sending queue 2."
        ::= { axsEtherDistributionTxQoSStatsEntry 10 }

    axsEtherDistributionTxQoS2StatsTotalOutFrames OBJECT-TYPE
        SYNTAX    Counter
        ACCESS    read-only
        STATUS    mandatory
        DESCRIPTION
                  "The total number of sent frames of the distribution sending queue 2."
        ::= { axsEtherDistributionTxQoSStatsEntry 11 }

    axsEtherDistributionTxQoS2StatsTotalOutBytesHigh OBJECT-TYPE
        SYNTAX    Counter
        ACCESS    read-only
        STATUS    mandatory
        DESCRIPTION
                  "The total number of sent bytes (the high order 4-bytes) of the distribution sending queue 2."
        ::= { axsEtherDistributionTxQoSStatsEntry 12 }

    axsEtherDistributionTxQoS2StatsTotalOutBytesLow OBJECT-TYPE
        SYNTAX    Counter
        ACCESS    read-only
        STATUS    mandatory
        DESCRIPTION
                  "The total number of sent bytes (the low order 4-bytes) of the distribution sending queue 2."
        ::= { axsEtherDistributionTxQoSStatsEntry 13 }

    axsEtherDistributionTxQoS2StatsTotalDiscardFrames OBJECT-TYPE
        SYNTAX    Counter
        ACCESS    read-only
        STATUS    mandatory
        DESCRIPTION
                  "The total number of discarded frames of the distribution sending queue 2."
        ::= { axsEtherDistributionTxQoSStatsEntry 14 }

    axsEtherDistributionTxQoS1StatsQueueTable OBJECT-TYPE
        SYNTAX    SEQUENCE OF AxsEtherDistributionTxQoS1StatsQueueEntry
        ACCESS    not-accessible
        STATUS    mandatory
        DESCRIPTION
                  "Table information on the QoS statistics of priority queue
                   about the distribution sending queue 1."
        ::= { axsEtherDistributionTxQoS 2 }

    axsEtherDistributionTxQoS1StatsQueueEntry OBJECT-TYPE
        SYNTAX    AxsEtherDistributionTxQoS1StatsQueueEntry
        ACCESS    not-accessible
        STATUS    mandatory
        DESCRIPTION
                  "Entry concerning corresponding QoS statistics of priority queue
                   about the distribution sending queue 1."
        INDEX     { axsEtherDistributionTxQoS1StatsQueueIndex,
                    axsEtherDistributionTxQoS1StatsQueueIfIndex,
                    axsEtherDistributionTxQoS1StatsQueueQueIndex }
        ::= { axsEtherDistributionTxQoS1StatsQueueTable 1 }

    AxsEtherDistributionTxQoS1StatsQueueEntry ::= SEQUENCE {
        axsEtherDistributionTxQoS1StatsQueueIndex                  INTEGER,
        axsEtherDistributionTxQoS1StatsQueueIfIndex                INTEGER,
        axsEtherDistributionTxQoS1StatsQueueQueIndex               INTEGER,
        axsEtherDistributionTxQoS1StatsQueueQlen                   INTEGER,
        axsEtherDistributionTxQoS1StatsQueueMaxQlen                INTEGER,
        axsEtherDistributionTxQoS1StatsQueueDiscardFramesClass1    Counter64,
        axsEtherDistributionTxQoS1StatsQueueDiscardFramesClass2    Counter64,
        axsEtherDistributionTxQoS1StatsQueueDiscardFramesClass3    Counter64,
        axsEtherDistributionTxQoS1StatsQueueDiscardFramesClass4    Counter64
    }

    axsEtherDistributionTxQoS1StatsQueueIndex OBJECT-TYPE
        SYNTAX    INTEGER
        ACCESS    not-accessible
        STATUS    mandatory
        DESCRIPTION
                  "The number in the part in which distribution sending queue 1 exists."
        ::= { axsEtherDistributionTxQoS1StatsQueueEntry 1 }

    axsEtherDistributionTxQoS1StatsQueueIfIndex OBJECT-TYPE
        SYNTAX    INTEGER
        ACCESS    not-accessible
        STATUS    mandatory
        DESCRIPTION
                  "The index value (ifIndex value of an Ethernet interface)
                   which identifies the entry of this table. Values between 1 and ifNumber."
        ::= { axsEtherDistributionTxQoS1StatsQueueEntry 2 }

    axsEtherDistributionTxQoS1StatsQueueQueIndex OBJECT-TYPE
        SYNTAX    INTEGER
        ACCESS    not-accessible
        STATUS    mandatory
        DESCRIPTION
                  "The index value (ifIndex value of an Ethernet interface)
                   which identifies the entry of this table. Values between 1 and ifNumber."
        ::= { axsEtherDistributionTxQoS1StatsQueueEntry 3 }

    axsEtherDistributionTxQoS1StatsQueueQlen OBJECT-TYPE
        SYNTAX    INTEGER
        ACCESS    read-only
        STATUS    mandatory
        DESCRIPTION
                  "A length of priority queue about the distribution sending queue 1."
        ::= { axsEtherDistributionTxQoS1StatsQueueEntry 4 }

    axsEtherDistributionTxQoS1StatsQueueMaxQlen OBJECT-TYPE
        SYNTAX    INTEGER
        ACCESS    read-only
        STATUS    mandatory
        DESCRIPTION
                  "The highest queue length of priority queue about the distribution sending queue 1
                   after being cleared or initialized."
        ::= { axsEtherDistributionTxQoS1StatsQueueEntry 5 }

    axsEtherDistributionTxQoS1StatsQueueDiscardFramesClass1 OBJECT-TYPE
        SYNTAX    Counter64
        ACCESS    read-only
        STATUS    mandatory
        DESCRIPTION
                  "The number of discarded frames in the discard class 1 of priority queue
                   about the distribution sending queue 1."
        ::= { axsEtherDistributionTxQoS1StatsQueueEntry 6 }

    axsEtherDistributionTxQoS1StatsQueueDiscardFramesClass2 OBJECT-TYPE
        SYNTAX    Counter64
        ACCESS    read-only
        STATUS    mandatory
        DESCRIPTION
                  "The number of discarded frames in the discard class 2 of priority queue
                   about the distribution sending queue 1."
        ::= { axsEtherDistributionTxQoS1StatsQueueEntry 7 }

    axsEtherDistributionTxQoS1StatsQueueDiscardFramesClass3 OBJECT-TYPE
        SYNTAX    Counter64
        ACCESS    read-only
        STATUS    mandatory
        DESCRIPTION
                  "The number of discarded frames in the discard class 3 of priority queue
                   about the distribution sending queue 1."
        ::= { axsEtherDistributionTxQoS1StatsQueueEntry 8 }

    axsEtherDistributionTxQoS1StatsQueueDiscardFramesClass4 OBJECT-TYPE
        SYNTAX    Counter64
        ACCESS    read-only
        STATUS    mandatory
        DESCRIPTION
                  "The number of discarded frames in the discard class 4 of priority queue
                   about the distribution sending queue 1."
        ::= { axsEtherDistributionTxQoS1StatsQueueEntry 9 }

    axsEtherDistributionTxQoS2StatsQueueTable OBJECT-TYPE
        SYNTAX    SEQUENCE OF AxsEtherDistributionTxQoS2StatsQueueEntry
        ACCESS    not-accessible
        STATUS    mandatory
        DESCRIPTION
                  "Table information on the QoS statistics of priority queue
                   about the distribution sending queue 2."
        ::= { axsEtherDistributionTxQoS 3 }

    axsEtherDistributionTxQoS2StatsQueueEntry OBJECT-TYPE
        SYNTAX    AxsEtherDistributionTxQoS2StatsQueueEntry
        ACCESS    not-accessible
        STATUS    mandatory
        DESCRIPTION
                  "Entry concerning corresponding QoS statistics of priority queue
                   about the distribution sending queue 2."
        INDEX     { axsEtherDistributionTxQoS2StatsQueueIndex,
                    axsEtherDistributionTxQoS2StatsQueueIfIndex,
                    axsEtherDistributionTxQoS2StatsQueueQueIndex }
        ::= { axsEtherDistributionTxQoS2StatsQueueTable 1 }

    AxsEtherDistributionTxQoS2StatsQueueEntry ::= SEQUENCE {
        axsEtherDistributionTxQoS2StatsQueueIndex                  INTEGER,
        axsEtherDistributionTxQoS2StatsQueueIfIndex                INTEGER,
        axsEtherDistributionTxQoS2StatsQueueQueIndex               INTEGER,
        axsEtherDistributionTxQoS2StatsQueueQlen                   INTEGER,
        axsEtherDistributionTxQoS2StatsQueueMaxQlen                INTEGER,
        axsEtherDistributionTxQoS2StatsQueueDiscardFramesClass1    Counter64,
        axsEtherDistributionTxQoS2StatsQueueDiscardFramesClass2    Counter64,
        axsEtherDistributionTxQoS2StatsQueueDiscardFramesClass3    Counter64,
        axsEtherDistributionTxQoS2StatsQueueDiscardFramesClass4    Counter64
    }

    axsEtherDistributionTxQoS2StatsQueueIndex OBJECT-TYPE
        SYNTAX    INTEGER
        ACCESS    not-accessible
        STATUS    mandatory
        DESCRIPTION
                  "The number in the part in which the distribution sending queue 2 exists."
        ::= { axsEtherDistributionTxQoS2StatsQueueEntry 1 }

    axsEtherDistributionTxQoS2StatsQueueIfIndex OBJECT-TYPE
        SYNTAX    INTEGER
        ACCESS    not-accessible
        STATUS    mandatory
        DESCRIPTION
                  "The index value (ifIndex value of an Ethernet interface)
                   which identifies the entry of this table. Values between 1 and ifNumber."
        ::= { axsEtherDistributionTxQoS2StatsQueueEntry 2 }

    axsEtherDistributionTxQoS2StatsQueueQueIndex OBJECT-TYPE
        SYNTAX    INTEGER
        ACCESS    not-accessible
        STATUS    mandatory
        DESCRIPTION
                  "The index value which identifies the entry of this table.
                   Values between 1 and axsEtherDistributionTxQoS2StatsMaxQnum."
        ::= { axsEtherDistributionTxQoS2StatsQueueEntry 3 }

    axsEtherDistributionTxQoS2StatsQueueQlen OBJECT-TYPE
        SYNTAX    INTEGER
        ACCESS    read-only
        STATUS    mandatory
        DESCRIPTION
                  "A length of priority queue about the distribution sending queue 2."
        ::= { axsEtherDistributionTxQoS2StatsQueueEntry 4 }

    axsEtherDistributionTxQoS2StatsQueueMaxQlen OBJECT-TYPE
        SYNTAX    INTEGER
        ACCESS    read-only
        STATUS    mandatory
        DESCRIPTION
                  "The highest queue length of priority queue about the distribution sending queue 2
                   after being cleared or initialized."
        ::= { axsEtherDistributionTxQoS2StatsQueueEntry 5 }

    axsEtherDistributionTxQoS2StatsQueueDiscardFramesClass1 OBJECT-TYPE
        SYNTAX    Counter64
        ACCESS    read-only
        STATUS    mandatory
        DESCRIPTION
                  "The number of discarded frames in the discard class 1 of priority queue
                   about the distribution sending queue 2."
        ::= { axsEtherDistributionTxQoS2StatsQueueEntry 6 }

    axsEtherDistributionTxQoS2StatsQueueDiscardFramesClass2 OBJECT-TYPE
        SYNTAX    Counter64
        ACCESS    read-only
        STATUS    mandatory
        DESCRIPTION
                  "The number of discarded frames in the discard class 2 of priority queue
                   about the distribution sending queue 2."
        ::= { axsEtherDistributionTxQoS2StatsQueueEntry 7 }

    axsEtherDistributionTxQoS2StatsQueueDiscardFramesClass3 OBJECT-TYPE
        SYNTAX    Counter64
        ACCESS    read-only
        STATUS    mandatory
        DESCRIPTION
                  "The number of discarded frames in the discard class 3 of priority queue
                   about the distribution sending queue 2."
        ::= { axsEtherDistributionTxQoS2StatsQueueEntry 8 }

    axsEtherDistributionTxQoS2StatsQueueDiscardFramesClass4 OBJECT-TYPE
        SYNTAX    Counter64
        ACCESS    read-only
        STATUS    mandatory
        DESCRIPTION
                  "The number of discarded frames in the discard class 4 of priority queue
                   about the distribution sending queue 2."
        ::= { axsEtherDistributionTxQoS2StatsQueueEntry 9 }

    axsEtherDistributionRxQoSStatsTable OBJECT-TYPE
        SYNTAX    SEQUENCE OF AxsEtherDistributionRxQoSStatsEntry
        ACCESS    not-accessible
        STATUS    mandatory
        DESCRIPTION
                  "Table information on the QoS statistics about the distribution receiving queue."
        ::= { axsEtherDistributionRxQoS 1 }

    axsEtherDistributionRxQoSStatsEntry OBJECT-TYPE
        SYNTAX    AxsEtherDistributionRxQoSStatsEntry
        ACCESS    not-accessible
        STATUS    mandatory
        DESCRIPTION
                  "Entry concerning corresponding QoS statistics about the distribution receiving queue."
        INDEX     { axsEtherDistributionRxQoSStatsIndex,
                    axsEtherDistributionRxQoSStatsIfIndex }
        ::= { axsEtherDistributionRxQoSStatsTable 1 }

    AxsEtherDistributionRxQoSStatsEntry ::= SEQUENCE {
        axsEtherDistributionRxQoSStatsIndex                 INTEGER,
        axsEtherDistributionRxQoSStatsIfIndex               INTEGER,
        axsEtherDistributionRxQoS1StatsMaxQnum              INTEGER,
        axsEtherDistributionRxQoS1StatsLimitQlen            INTEGER,
        axsEtherDistributionRxQoS1StatsTotalOutFrames       Counter,
        axsEtherDistributionRxQoS1StatsTotalOutBytesHigh    Counter,
        axsEtherDistributionRxQoS1StatsTotalOutBytesLow     Counter,
        axsEtherDistributionRxQoS1StatsTotalDiscardFrames   Counter,
        axsEtherDistributionRxQoS2StatsMaxQnum              INTEGER,
        axsEtherDistributionRxQoS2StatsLimitQlen            INTEGER,
        axsEtherDistributionRxQoS2StatsTotalOutFrames       Counter,
        axsEtherDistributionRxQoS2StatsTotalOutBytesHigh    Counter,
        axsEtherDistributionRxQoS2StatsTotalOutBytesLow     Counter,
        axsEtherDistributionRxQoS2StatsTotalDiscardFrames   Counter
    }

    axsEtherDistributionRxQoSStatsIndex OBJECT-TYPE
        SYNTAX    INTEGER
        ACCESS    not-accessible
        STATUS    mandatory
        DESCRIPTION
                  "The number in the part in which the distribution receiving queue exists."
        ::= { axsEtherDistributionRxQoSStatsEntry 1 }

    axsEtherDistributionRxQoSStatsIfIndex OBJECT-TYPE
        SYNTAX    INTEGER
        ACCESS    not-accessible
        STATUS    mandatory
        DESCRIPTION
                  "The index value (ifIndex value of an Ethernet interface)
                   which identifies the entry of this table. Values between 1 and ifNumber."
        ::= { axsEtherDistributionRxQoSStatsEntry 2 }

    axsEtherDistributionRxQoS1StatsMaxQnum OBJECT-TYPE
        SYNTAX    INTEGER
        ACCESS    read-only
        STATUS    mandatory
        DESCRIPTION
                  "The number of queues of the distribution receiving queue 1."
        ::= { axsEtherDistributionRxQoSStatsEntry 3 }

    axsEtherDistributionRxQoS1StatsLimitQlen OBJECT-TYPE
        SYNTAX    INTEGER
        ACCESS    read-only
        STATUS    mandatory
        DESCRIPTION
                  "The limit length of distribution inbound queue for an ethernet interface."
        ::= { axsEtherDistributionRxQoSStatsEntry 4 }

    axsEtherDistributionRxQoS1StatsTotalOutFrames OBJECT-TYPE
        SYNTAX    Counter
        ACCESS    read-only
        STATUS    mandatory
        DESCRIPTION
                  "The total number of received frames of the distribution receiving queue 1."
        ::= { axsEtherDistributionRxQoSStatsEntry 5 }

    axsEtherDistributionRxQoS1StatsTotalOutBytesHigh OBJECT-TYPE
        SYNTAX    Counter
        ACCESS    read-only
        STATUS    mandatory
        DESCRIPTION
                  "The total number of received bytes (the high order 4-bytes) of the distribution receiving queue 1."
        ::= { axsEtherDistributionRxQoSStatsEntry 6 }

    axsEtherDistributionRxQoS1StatsTotalOutBytesLow OBJECT-TYPE
        SYNTAX    Counter
        ACCESS    read-only
        STATUS    mandatory
        DESCRIPTION
                  "The total number of received bytes (the low order 4-bytes) of the distribution receiving queue 1."
        ::= { axsEtherDistributionRxQoSStatsEntry 7 }

    axsEtherDistributionRxQoS1StatsTotalDiscardFrames OBJECT-TYPE
        SYNTAX    Counter
        ACCESS    read-only
        STATUS    mandatory
        DESCRIPTION
                  "The total number of discarded frames of the distribution receiving queue 1."
        ::= { axsEtherDistributionRxQoSStatsEntry 8 }


    axsEtherDistributionRxQoS2StatsMaxQnum OBJECT-TYPE
        SYNTAX    INTEGER
        ACCESS    read-only
        STATUS    mandatory
        DESCRIPTION
                  "The number of queues of the distribution receiving queue 2."
        ::= { axsEtherDistributionRxQoSStatsEntry 9 }

    axsEtherDistributionRxQoS2StatsLimitQlen OBJECT-TYPE
        SYNTAX    INTEGER
        ACCESS    read-only
        STATUS    mandatory
        DESCRIPTION
                  "The limit length of the priority queue of the distribution receiving queue 2."
        ::= { axsEtherDistributionRxQoSStatsEntry 10 }

    axsEtherDistributionRxQoS2StatsTotalOutFrames OBJECT-TYPE
        SYNTAX    Counter
        ACCESS    read-only
        STATUS    mandatory
        DESCRIPTION
                  "The total number of received frames of the distribution receiving queue 2."
        ::= { axsEtherDistributionRxQoSStatsEntry 11 }

    axsEtherDistributionRxQoS2StatsTotalOutBytesHigh OBJECT-TYPE
        SYNTAX    Counter
        ACCESS    read-only
        STATUS    mandatory
        DESCRIPTION
                  "The total number of received bytes (the high order 4-bytes) of the distribution receiving queue 2."
        ::= { axsEtherDistributionRxQoSStatsEntry 12 }

    axsEtherDistributionRxQoS2StatsTotalOutBytesLow OBJECT-TYPE
        SYNTAX    Counter
        ACCESS    read-only
        STATUS    mandatory
        DESCRIPTION
                  "The total number of received bytes (the low order 4-bytes) of the distribution receiving queue 2."
        ::= { axsEtherDistributionRxQoSStatsEntry 13 }

    axsEtherDistributionRxQoS2StatsTotalDiscardFrames OBJECT-TYPE
        SYNTAX    Counter
        ACCESS    read-only
        STATUS    mandatory
        DESCRIPTION
                  "The total number of discarded frames of the distribution receiving queue 2."
        ::= { axsEtherDistributionRxQoSStatsEntry 14 }

    axsEtherDistributionRxQoS1StatsQueueTable OBJECT-TYPE
        SYNTAX    SEQUENCE OF AxsEtherDistributionRxQoS1StatsQueueEntry
        ACCESS    not-accessible
        STATUS    mandatory
        DESCRIPTION
                  "Table information on the QoS statistics of priority queue
                   about the distribution receiving queue 1."
        ::= { axsEtherDistributionRxQoS 2 }

    axsEtherDistributionRxQoS1StatsQueueEntry OBJECT-TYPE
        SYNTAX    AxsEtherDistributionRxQoS1StatsQueueEntry
        ACCESS    not-accessible
        STATUS    mandatory
        DESCRIPTION
                  "Entry concerning corresponding QoS statistics of priority queue
                   about the distribution receiving queue 1."
        INDEX     { axsEtherDistributionRxQoS1StatsQueueIndex,
                    axsEtherDistributionRxQoS1StatsQueueIfIndex,
                    axsEtherDistributionRxQoS1StatsQueueQueIndex }
        ::= { axsEtherDistributionRxQoS1StatsQueueTable 1 }

    AxsEtherDistributionRxQoS1StatsQueueEntry ::= SEQUENCE {
        axsEtherDistributionRxQoS1StatsQueueIndex                  INTEGER,
        axsEtherDistributionRxQoS1StatsQueueIfIndex                INTEGER,
        axsEtherDistributionRxQoS1StatsQueueQueIndex               INTEGER,
        axsEtherDistributionRxQoS1StatsQueueQlen                   INTEGER,
        axsEtherDistributionRxQoS1StatsQueueMaxQlen                INTEGER
    }

    axsEtherDistributionRxQoS1StatsQueueIndex OBJECT-TYPE
        SYNTAX    INTEGER
        ACCESS    not-accessible
        STATUS    mandatory
        DESCRIPTION
                  "The number in the part in which the distribution receiving queue 1 exists."
        ::= { axsEtherDistributionRxQoS1StatsQueueEntry 1 }

    axsEtherDistributionRxQoS1StatsQueueIfIndex OBJECT-TYPE
        SYNTAX    INTEGER
        ACCESS    not-accessible
        STATUS    mandatory
        DESCRIPTION
                  "The index value (ifIndex value of an Ethernet interface)
                   which identifies the entry of this table. Values between 1 and ifNumber."
        ::= { axsEtherDistributionRxQoS1StatsQueueEntry 2 }

    axsEtherDistributionRxQoS1StatsQueueQueIndex OBJECT-TYPE
        SYNTAX    INTEGER
        ACCESS    not-accessible
        STATUS    mandatory
        DESCRIPTION
                  "The index value which identifies the entry of this table.
                   Values between 1 and axsEtherDistributionRxQoS1StatsMaxQnum."
        ::= { axsEtherDistributionRxQoS1StatsQueueEntry 3 }

    axsEtherDistributionRxQoS1StatsQueueQlen OBJECT-TYPE
        SYNTAX    INTEGER
        ACCESS    read-only
        STATUS    mandatory
        DESCRIPTION
                  "A length of priority queue about the distribution receiving queue 1."
        ::= { axsEtherDistributionRxQoS1StatsQueueEntry 4 }

    axsEtherDistributionRxQoS1StatsQueueMaxQlen OBJECT-TYPE
        SYNTAX    INTEGER
        ACCESS    read-only
        STATUS    mandatory
        DESCRIPTION
                  "The highest queue length of priority queue
                   about the distribution receiving queue 1 of an Ethernet interface
                   after being cleared or initialized."
        ::= { axsEtherDistributionRxQoS1StatsQueueEntry 5 }

    axsEtherDistributionRxQoS2StatsQueueTable OBJECT-TYPE
        SYNTAX    SEQUENCE OF AxsEtherDistributionRxQoS2StatsQueueEntry
        ACCESS    not-accessible
        STATUS    mandatory
        DESCRIPTION
                  "Table information on the QoS statistics of priority queue
                   about the distribution receiving queue 2."
        ::= { axsEtherDistributionRxQoS 3 }

    axsEtherDistributionRxQoS2StatsQueueEntry OBJECT-TYPE
        SYNTAX    AxsEtherDistributionRxQoS2StatsQueueEntry
        ACCESS    not-accessible
        STATUS    mandatory
        DESCRIPTION
                  "Entry concerning corresponding QoS statistics of priority queue
                   about the distribution receiving queue 2."
        INDEX     { axsEtherDistributionRxQoS2StatsQueueIndex,
                    axsEtherDistributionRxQoS2StatsQueueIfIndex,
                    axsEtherDistributionRxQoS2StatsQueueQueIndex }
        ::= { axsEtherDistributionRxQoS2StatsQueueTable 1 }

    AxsEtherDistributionRxQoS2StatsQueueEntry ::= SEQUENCE {
        axsEtherDistributionRxQoS2StatsQueueIndex                  INTEGER,
        axsEtherDistributionRxQoS2StatsQueueIfIndex                INTEGER,
        axsEtherDistributionRxQoS2StatsQueueQueIndex               INTEGER,
        axsEtherDistributionRxQoS2StatsQueueQlen                   INTEGER,
        axsEtherDistributionRxQoS2StatsQueueMaxQlen                INTEGER
    }

    axsEtherDistributionRxQoS2StatsQueueIndex OBJECT-TYPE
        SYNTAX    INTEGER
        ACCESS    not-accessible
        STATUS    mandatory
        DESCRIPTION
                  "The number in the part in which the distribution receiving queue 2 exists."
        ::= { axsEtherDistributionRxQoS2StatsQueueEntry 1 }

    axsEtherDistributionRxQoS2StatsQueueIfIndex OBJECT-TYPE
        SYNTAX    INTEGER
        ACCESS    not-accessible
        STATUS    mandatory
        DESCRIPTION
                  "The index value (ifIndex value of an Ethernet interface)
                   which identifies the entry of this table. Values between 1 and ifNumber."
        ::= { axsEtherDistributionRxQoS2StatsQueueEntry 2 }

    axsEtherDistributionRxQoS2StatsQueueQueIndex OBJECT-TYPE
        SYNTAX    INTEGER
        ACCESS    not-accessible
        STATUS    mandatory
        DESCRIPTION
                  "The index value which identifies the entry of this table.
                   Values between 1 and axsEtherDistributionRxQoS2StatsMaxQnum."
        ::= { axsEtherDistributionRxQoS2StatsQueueEntry 3 }

    axsEtherDistributionRxQoS2StatsQueueQlen OBJECT-TYPE
        SYNTAX    INTEGER
        ACCESS    read-only
        STATUS    mandatory
        DESCRIPTION
                  "A length of priority queue about the distribution receiving queue 2."
        ::= { axsEtherDistributionRxQoS2StatsQueueEntry 4 }

    axsEtherDistributionRxQoS2StatsQueueMaxQlen OBJECT-TYPE
        SYNTAX    INTEGER
        ACCESS    read-only
        STATUS    mandatory
        DESCRIPTION
                  "The highest queue length of priority queue
                   about the distribution receiving queue 2 of an Ethernet interface
                   after being cleared or initialized."
        ::= { axsEtherDistributionRxQoS2StatsQueueEntry 5 }

    axsToCpuQoSStatsTable OBJECT-TYPE
        SYNTAX    SEQUENCE OF AxsToCpuQoSStatsEntry
        ACCESS    not-accessible
        STATUS    mandatory
        DESCRIPTION
                  "Table information on the QoS statistics about the sending queue for cpu."
        ::= { axsToCpuQoS 1 }

    axsToCpuQoSStatsEntry OBJECT-TYPE
        SYNTAX    AxsToCpuQoSStatsEntry
        ACCESS    not-accessible
        STATUS    mandatory
        DESCRIPTION
                  "Entry concerning corresponding QoS statistics about the sending queue for cpu."
        INDEX     { axsToCpuQoSStatsIndex }
        ::= { axsToCpuQoSStatsTable 1 }

    AxsToCpuQoSStatsEntry ::= SEQUENCE {
        axsToCpuQoSStatsIndex                 INTEGER,
        axsToCpuQoSStatsMaxQnum               INTEGER,
        axsToCpuQoSStatsLimitQlen             INTEGER,
        axsToCpuQoSStatsTotalOutFrames        Counter,
        axsToCpuQoSStatsTotalOutBytesHigh     Counter,
        axsToCpuQoSStatsTotalOutBytesLow      Counter,
        axsToCpuQoSStatsTotalDiscardFrames    Counter
    }

    axsToCpuQoSStatsIndex OBJECT-TYPE
        SYNTAX    INTEGER
        ACCESS    not-accessible
        STATUS    mandatory
        DESCRIPTION
                  "The number in the part in which the sending queue for cpu exists."
        ::= { axsToCpuQoSStatsEntry 1 }

    axsToCpuQoSStatsMaxQnum OBJECT-TYPE
        SYNTAX    INTEGER
        ACCESS    read-only
        STATUS    mandatory
        DESCRIPTION
                  "The number of queues of the sending queue for cpu."
        ::= { axsToCpuQoSStatsEntry 2 }

    axsToCpuQoSStatsLimitQlen OBJECT-TYPE
        SYNTAX    INTEGER
        ACCESS    read-only
        STATUS    mandatory
        DESCRIPTION
                  "The limit length of the priority queue of the sending queue for cpu."
        ::= { axsToCpuQoSStatsEntry 3 }


    axsToCpuQoSStatsTotalOutFrames OBJECT-TYPE
        SYNTAX    Counter
        ACCESS    read-only
        STATUS    mandatory
        DESCRIPTION
                  "The total number of sent frames of the sending queue for cpu."
        ::= { axsToCpuQoSStatsEntry 4 }

    axsToCpuQoSStatsTotalOutBytesHigh OBJECT-TYPE
        SYNTAX    Counter
        ACCESS    read-only
        STATUS    mandatory
        DESCRIPTION
                  "The total number of sent bytes (the high order 4-bytes) of the sending queue for cpu."
        ::= { axsToCpuQoSStatsEntry 5 }

    axsToCpuQoSStatsTotalOutBytesLow OBJECT-TYPE
        SYNTAX    Counter
        ACCESS    read-only
        STATUS    mandatory
        DESCRIPTION
                  "The total number of sent bytes (the low order 4-bytes) of the sending queue for cpu."
        ::= { axsToCpuQoSStatsEntry 6 }

    axsToCpuQoSStatsTotalDiscardFrames OBJECT-TYPE
        SYNTAX    Counter
        ACCESS    read-only
        STATUS    mandatory
        DESCRIPTION
                  "The total number of discarded frames of the sending queue for cpu."
        ::= { axsToCpuQoSStatsEntry 7 }

    axsToCpuQoSStatsQueueTable OBJECT-TYPE
        SYNTAX    SEQUENCE OF AxsToCpuQoSStatsQueueEntry
        ACCESS    not-accessible
        STATUS    mandatory
        DESCRIPTION
                  "Table information on the QoS statistics of priority queue
                   about the sending queue for cpu."
        ::= { axsToCpuQoS 2 }

    axsToCpuQoSStatsQueueEntry OBJECT-TYPE
        SYNTAX    AxsToCpuQoSStatsQueueEntry
        ACCESS    not-accessible
        STATUS    mandatory
        DESCRIPTION
                  "Entry concerning corresponding QoS statistics of priority queue
                   about the sending queue for cpu."
        INDEX     { axsToCpuQoSStatsQueueIndex,
                    axsToCpuQoSStatsQueueQueIndex }
        ::= { axsToCpuQoSStatsQueueTable 1 }

    AxsToCpuQoSStatsQueueEntry ::= SEQUENCE {
        axsToCpuQoSStatsQueueIndex                  INTEGER,
        axsToCpuQoSStatsQueueQueIndex               INTEGER,
        axsToCpuQoSStatsQueueQlen                   INTEGER,
        axsToCpuQoSStatsQueueMaxQlen                INTEGER,
        axsToCpuQoSStatsQueueDiscardFramesClass1    Counter64,
        axsToCpuQoSStatsQueueDiscardFramesClass2    Counter64,
        axsToCpuQoSStatsQueueDiscardFramesClass3    Counter64,
        axsToCpuQoSStatsQueueDiscardFramesClass4    Counter64
    }

    axsToCpuQoSStatsQueueIndex OBJECT-TYPE
        SYNTAX    INTEGER
        ACCESS    not-accessible
        STATUS    mandatory
        DESCRIPTION
                  "The number in the part in which the sending queue for cpu exists."
        ::= { axsToCpuQoSStatsQueueEntry 1 }

    axsToCpuQoSStatsQueueQueIndex OBJECT-TYPE
        SYNTAX    INTEGER
        ACCESS    not-accessible
        STATUS    mandatory
        DESCRIPTION
                  "The index value which identifies the entry of this table.
                   Values between 1 and axsToCpuQoSStatsMaxQnum."
        ::= { axsToCpuQoSStatsQueueEntry 2 }

    axsToCpuQoSStatsQueueQlen OBJECT-TYPE
        SYNTAX    INTEGER
        ACCESS    read-only
        STATUS    mandatory
        DESCRIPTION
                  "A length of priority queue about the sending queue for cpu."
        ::= { axsToCpuQoSStatsQueueEntry 3 }

    axsToCpuQoSStatsQueueMaxQlen OBJECT-TYPE
        SYNTAX    INTEGER
        ACCESS    read-only
        STATUS    mandatory
        DESCRIPTION
                  "The highest queue length of priority queue about the sending queue for cpu
                   after being cleared or initialized."
        ::= { axsToCpuQoSStatsQueueEntry 4 }

    axsToCpuQoSStatsQueueDiscardFramesClass1 OBJECT-TYPE
        SYNTAX    Counter64
        ACCESS    read-only
        STATUS    mandatory
        DESCRIPTION
                  "The number of discarded frames in the discard class 1 of priority queue
                   about the sending queue for cpu."
        ::= { axsToCpuQoSStatsQueueEntry 5 }

    axsToCpuQoSStatsQueueDiscardFramesClass2 OBJECT-TYPE
        SYNTAX    Counter64
        ACCESS    read-only
        STATUS    mandatory
        DESCRIPTION
                  "The number of discarded frames in the discard class 2 of priority queue
                   about the sending queue for cpu."
        ::= { axsToCpuQoSStatsQueueEntry 6 }

    axsToCpuQoSStatsQueueDiscardFramesClass3 OBJECT-TYPE
        SYNTAX    Counter64
        ACCESS    read-only
        STATUS    mandatory
        DESCRIPTION
                  "The number of discarded frames in the discard class 3 of priority queue
                   about the sending queue for cpu."
        ::= { axsToCpuQoSStatsQueueEntry 7 }

    axsToCpuQoSStatsQueueDiscardFramesClass4 OBJECT-TYPE
        SYNTAX    Counter64
        ACCESS    read-only
        STATUS    mandatory
        DESCRIPTION
                  "The number of discarded frames in the discard class 4 of priority queue
                   about the sending queue for cpu."
        ::= { axsToCpuQoSStatsQueueEntry 8 }

-- axsDHCP group Variables

    axsDHCPAddrValue OBJECT-TYPE
        SYNTAX    INTEGER
        ACCESS    read-only
        STATUS    mandatory
        DESCRIPTION
                  "The number of IP addresses which are available
                  within this Router."
        ::= { axsDHCP 1 }

    axsDHCPFreeAddrValue OBJECT-TYPE
        SYNTAX    INTEGER
        ACCESS    read-only
        STATUS    mandatory
        DESCRIPTION
                  "The number of IP addresses which are available
                  within this Router. May be expressed as either
                  an absolute value."
        ::= { axsDHCP 2 }

-- axsUrpf group Variables

    axsUrpfIpv4DiscPkts OBJECT-TYPE
        SYNTAX    Counter64
        ACCESS    read-only
        STATUS    mandatory
        DESCRIPTION
                  "Number of IPv4 packets abandoned by uRPF
                  on the entire device"
        ::= { axsUrpf 1 }

    axsUrpfIpv6DiscPkts OBJECT-TYPE
        SYNTAX    Counter64
        ACCESS    read-only
        STATUS    mandatory
        DESCRIPTION
                  "Number of IPv6 packets abandoned by uRPF
                  on the entire device"
        ::= { axsUrpf 2 }

    axsUrpfIfStatsTable OBJECT-TYPE
        SYNTAX    SEQUENCE OF AxsUrpfIfStatsEntry
        ACCESS    not-accessible
        STATUS    mandatory
        DESCRIPTION
                  "uRPF statistical information on each VLAN"
        ::= { axsUrpf 3 }

    axsUrpfIfStatsEntry OBJECT-TYPE
        SYNTAX    AxsUrpfIfStatsEntry
        ACCESS    not-accessible
        STATUS    mandatory
        DESCRIPTION
                  "Entry of uRPF statistical information table on each VLAN"
        INDEX     { axsUrpfIfStatsIndex }
        ::= { axsUrpfIfStatsTable 1 }

    AxsUrpfIfStatsEntry ::= SEQUENCE {
        axsUrpfIfStatsIndex           INTEGER,
        axsUrpfIfStatsIpv4DiscPkts    Counter64,
        axsUrpfIfStatsIpv6DiscPkts    Counter64
    }

    axsUrpfIfStatsIndex OBJECT-TYPE
        SYNTAX    INTEGER
        ACCESS    not-accessible
        STATUS    mandatory
        DESCRIPTION
                  "VLAN ID"
        ::= { axsUrpfIfStatsEntry 1 }

    axsUrpfIfStatsIpv4DiscPkts OBJECT-TYPE
        SYNTAX    Counter64
        ACCESS    read-only
        STATUS    mandatory
        DESCRIPTION
                  "Number of IPv4 packets abandoned by uRPF on each VLAN"
        ::= { axsUrpfIfStatsEntry 2 }

    axsUrpfIfStatsIpv6DiscPkts OBJECT-TYPE
        SYNTAX    Counter64
        ACCESS    read-only
        STATUS    mandatory
        DESCRIPTION
                  "Number of IPv6 packets abandoned by uRPF on each VLAN"
        ::= { axsUrpfIfStatsEntry 3 }

-- axsGsrp Group

    axsGsrpGroupTable OBJECT-TYPE
        SYNTAX    SEQUENCE OF AxsGsrpGroupEntry
        ACCESS    not-accessible
        STATUS    mandatory
        DESCRIPTION
                  "The table containing GSRP group information."
        ::= { axsGsrp 1 }

    axsGsrpGroupEntry OBJECT-TYPE
        SYNTAX    AxsGsrpGroupEntry
        ACCESS    not-accessible
        STATUS    mandatory
        DESCRIPTION
                  "The list of GSRP group information."
        INDEX     { axsGsrpGroupId }
        ::= { axsGsrpGroupTable 1 }

    AxsGsrpGroupEntry ::= SEQUENCE {
        axsGsrpGroupId              INTEGER,
        axsGsrpGroupRowStatus       RowStatus,
        axsGsrpMacAddress           MacAddress,
        axsGsrpAdvertiseHoldTime    INTEGER,
        axsGsrpAdvertiseInterval    INTEGER,
        axsGsrpSelectionPattern     INTEGER,
        axsGsrpLayer3Redundancy     INTEGER
    }

    axsGsrpGroupId OBJECT-TYPE
        SYNTAX    INTEGER
        ACCESS    not-accessible
        STATUS    mandatory
        DESCRIPTION
                  "GSRP group identifier."
        ::= { axsGsrpGroupEntry 1 }

    axsGsrpGroupRowStatus OBJECT-TYPE
        SYNTAX    RowStatus
        ACCESS    read-only
        STATUS    mandatory
        DESCRIPTION
                  "Valid/Invalid state of this entry. Valid(1) fixed"
        ::= { axsGsrpGroupEntry 2 }

    axsGsrpMacAddress OBJECT-TYPE
        SYNTAX    MacAddress
        ACCESS    read-only
        STATUS    mandatory
        DESCRIPTION
                  "The Media Access Control Address of this equipment."
        ::= { axsGsrpGroupEntry 3 }

    axsGsrpAdvertiseHoldTime OBJECT-TYPE
        SYNTAX    INTEGER
        ACCESS    read-only
        STATUS    mandatory
        DESCRIPTION
                  "Holding time of the Advertise frame (milli second)."
        ::= { axsGsrpGroupEntry 4 }

    axsGsrpAdvertiseInterval OBJECT-TYPE
        SYNTAX    INTEGER
        ACCESS    read-only
        STATUS    mandatory
        DESCRIPTION
                  "Interval between transmitting the Advertise frame (milli second)."
        ::= { axsGsrpGroupEntry 5 }

    axsGsrpSelectionPattern OBJECT-TYPE
        SYNTAX    INTEGER {
                      ports-Priority-MAC(1),
                      priority-Ports-MAC(2)
                  }
        ACCESS    read-only
        STATUS    mandatory
        DESCRIPTION
                  "Master/Backup selection pattern. Ports-Priority-MAC(1)  Priority-Ports-MAC(2)"
        ::= { axsGsrpGroupEntry 6 }

    axsGsrpLayer3Redundancy OBJECT-TYPE
        SYNTAX    INTEGER {
                      off(1),
                      on(2)
                  }
        ACCESS    read-only
        STATUS    mandatory
        DESCRIPTION
                  "The status of layer 3 redundancy-change."
        ::= { axsGsrpGroupEntry 7 }

    axsGsrpVlanGroupTable OBJECT-TYPE
        SYNTAX    SEQUENCE OF AxsGsrpVlanGroupEntry
        ACCESS    not-accessible
        STATUS    mandatory
        DESCRIPTION
                  "The table containing GSRP VLAN group information."
        ::= { axsGsrp 2 }

    axsGsrpVlanGroupEntry OBJECT-TYPE
        SYNTAX    AxsGsrpVlanGroupEntry
        ACCESS    not-accessible
        STATUS    mandatory
        DESCRIPTION
                  "The list of GSRP VLAN group information."
        INDEX     { axsGsrpGroupId,
                    axsGsrpVlanGroupId }
        ::= { axsGsrpVlanGroupTable 1 }

    AxsGsrpVlanGroupEntry ::= SEQUENCE {
        axsGsrpVlanGroupId                   INTEGER,
        axsGsrpVlanGroupRowStatus            RowStatus,
        axsGsrpState                         INTEGER,
        axsGsrpPriority                      INTEGER,
        axsGsrpActivePorts                   INTEGER,
        axsGsrpTransitionToMasterCounts      INTEGER,
        axsGsrpTransitionFromMasterCounts    INTEGER,
        axsGsrpLastTransitionTime            TimeStamp,
        axsGsrpVirtualMacAddress             MacAddress
    }

    axsGsrpVlanGroupId OBJECT-TYPE
        SYNTAX    INTEGER
        ACCESS    not-accessible
        STATUS    mandatory
        DESCRIPTION
                  "GSRP VLAN group number(1~8)"
        ::= { axsGsrpVlanGroupEntry 1 }

    axsGsrpVlanGroupRowStatus OBJECT-TYPE
        SYNTAX    RowStatus
        ACCESS    read-only
        STATUS    mandatory
        DESCRIPTION
                  "Valid/Invalid state of this entry. Valid(1) fixed"
        ::= { axsGsrpVlanGroupEntry 2 }

    axsGsrpState OBJECT-TYPE
        SYNTAX    INTEGER {
                      backUp(1),
                      backUp-Waiting(2),
                      master(3),
                      backUp-No-Neighbor(4),
                      backUp-Lock(5)
                  }
        ACCESS    read-only
        STATUS    mandatory
        DESCRIPTION
                  "The state of GSRP group.."
        ::= { axsGsrpVlanGroupEntry 3 }

    axsGsrpPriority OBJECT-TYPE
        SYNTAX    INTEGER
        ACCESS    read-only
        STATUS    mandatory
        DESCRIPTION
                  "Configured priority."
        ::= { axsGsrpVlanGroupEntry 4 }

    axsGsrpActivePorts OBJECT-TYPE
        SYNTAX    INTEGER
        ACCESS    read-only
        STATUS    mandatory
        DESCRIPTION
                  "The number of port which is link-up  in monitored port."
        ::= { axsGsrpVlanGroupEntry 5 }

    axsGsrpTransitionToMasterCounts OBJECT-TYPE
        SYNTAX    INTEGER
        ACCESS    read-only
        STATUS    mandatory
        DESCRIPTION
                  "The number of times which shifted to the master state from the backup state."
        ::= { axsGsrpVlanGroupEntry 6 }

    axsGsrpTransitionFromMasterCounts OBJECT-TYPE
        SYNTAX    INTEGER
        ACCESS    read-only
        STATUS    mandatory
        DESCRIPTION
                  "The number of times which shifted to the backup state from the master state."
        ::= { axsGsrpVlanGroupEntry 7 }

    axsGsrpLastTransitionTime OBJECT-TYPE
        SYNTAX    TimeStamp
        ACCESS    read-only
        STATUS    mandatory
        DESCRIPTION
                  "The last time at which changed in the master state from the backup state or in the backup state from the master state."
        ::= { axsGsrpVlanGroupEntry 8 }

    axsGsrpVirtualMacAddress OBJECT-TYPE
        SYNTAX    MacAddress
        ACCESS    read-only
        STATUS    mandatory
        DESCRIPTION
                  "The virtual Media Access Control address of the GSRP VLAN group. If the status of layer 3 redundancy-change is off, return 00 00 00 00 00 00"
        ::= { axsGsrpVlanGroupEntry 9 }

    axsGsrpNeighborGroupTable OBJECT-TYPE
        SYNTAX    SEQUENCE OF AxsGsrpNeighborGroupEntry
        ACCESS    not-accessible
        STATUS    mandatory
        DESCRIPTION
                  "The table containing stores the GSRP group information on facing equipment."
        ::= { axsGsrp 3 }

    axsGsrpNeighborGroupEntry OBJECT-TYPE
        SYNTAX    AxsGsrpNeighborGroupEntry
        ACCESS    not-accessible
        STATUS    mandatory
        DESCRIPTION
                  "The table containing stores the GSRP group information on facing equipment."
        INDEX     { axsGsrpNeighborGroupId,
                    axsGsrpNeighborMacAddress }
        ::= { axsGsrpNeighborGroupTable 1 }

    AxsGsrpNeighborGroupEntry ::= SEQUENCE {
        axsGsrpNeighborGroupId              INTEGER,
        axsGsrpNeighborMacAddress           MacAddress,
        axsGsrpNeighborAdvertiseHoldTime    INTEGER,
        axsGsrpNeighborAdvertiseInterval    INTEGER,
        axsGsrpNeighborSelectionPattern     INTEGER
    }

    axsGsrpNeighborGroupId OBJECT-TYPE
        SYNTAX    INTEGER
        ACCESS    not-accessible
        STATUS    mandatory
        DESCRIPTION
                  "The GSRP group identifier on the facing equipment."
        ::= { axsGsrpNeighborGroupEntry 1 }

    axsGsrpNeighborMacAddress OBJECT-TYPE
        SYNTAX    MacAddress
        ACCESS    not-accessible
        STATUS    mandatory
        DESCRIPTION
                  "The Media Access Control Address of the facing equipment."
        ::= { axsGsrpNeighborGroupEntry 2 }

    axsGsrpNeighborAdvertiseHoldTime OBJECT-TYPE
        SYNTAX    INTEGER
        ACCESS    read-only
        STATUS    mandatory
        DESCRIPTION
                  "Holding time of the Advertise frame on opposite equipment (milli second)."
        ::= { axsGsrpNeighborGroupEntry 3 }

    axsGsrpNeighborAdvertiseInterval OBJECT-TYPE
        SYNTAX    INTEGER
        ACCESS    read-only
        STATUS    mandatory
        DESCRIPTION
                  "Interval between transmitting the Advertise frame on the facing equipment (milli second)."
        ::= { axsGsrpNeighborGroupEntry 4 }

    axsGsrpNeighborSelectionPattern OBJECT-TYPE
        SYNTAX    INTEGER {
                      port-Priority-MAC(1),
                      priority-Port-MAC(2)
                  }
        ACCESS    read-only
        STATUS    mandatory
        DESCRIPTION
                  "Master/Backup selection pattern on the facing equipment. Ports-Priority-MAC(1)  Priority-Ports-MAC(2)"
        ::= { axsGsrpNeighborGroupEntry 5 }

    axsGsrpNeighborVlanGroupTable OBJECT-TYPE
        SYNTAX    SEQUENCE OF AxsGsrpNeighborVlanGroupEntry
        ACCESS    not-accessible
        STATUS    mandatory
        DESCRIPTION
                  "The table containing the GSRP VLAN group information on facing equipment."
        ::= { axsGsrp 4 }

    axsGsrpNeighborVlanGroupEntry OBJECT-TYPE
        SYNTAX    AxsGsrpNeighborVlanGroupEntry
        ACCESS    not-accessible
        STATUS    mandatory
        DESCRIPTION
                  "The table containing the GSRP VLAN group information on facing equipment."
        INDEX     { axsGsrpNeighborGroupId,
                    axsGsrpNeighborVlanGroupId,
                    axsGsrpNeighborMacAddress }
        ::= { axsGsrpNeighborVlanGroupTable 1 }

    AxsGsrpNeighborVlanGroupEntry ::= SEQUENCE {
        axsGsrpNeighborVlanGroupId    INTEGER,
        axsGsrpNeighborState          INTEGER,
        axsGsrpNeighborPriority       INTEGER,
        axsGsrpNeighborActivePorts    INTEGER
    }

    axsGsrpNeighborVlanGroupId OBJECT-TYPE
        SYNTAX    INTEGER
        ACCESS    not-accessible
        STATUS    mandatory
        DESCRIPTION
                  "GSRP VLAN group number on the facing equipment (1~8)."
        ::= { axsGsrpNeighborVlanGroupEntry 1 }

    axsGsrpNeighborState OBJECT-TYPE
        SYNTAX    INTEGER {
                      backUp(1),
                      backUp-Waiting(2),
                      master(3),
                      backUp-No-Neighbor(4),
                      backUp-Lock(5)
                  }
        ACCESS    not-accessible
        STATUS    mandatory
        DESCRIPTION
                  "The state of GSRP group on the facing equipment."
        ::= { axsGsrpNeighborVlanGroupEntry 2 }

    axsGsrpNeighborPriority OBJECT-TYPE
        SYNTAX    INTEGER
        ACCESS    read-only
        STATUS    mandatory
        DESCRIPTION
                  "Configured priority on the facing equipment."
        ::= { axsGsrpNeighborVlanGroupEntry 3 }

    axsGsrpNeighborActivePorts OBJECT-TYPE
        SYNTAX    INTEGER
        ACCESS    read-only
        STATUS    mandatory
        DESCRIPTION
                  "The number of port which is link-up  in monitored port on the facing equipment."
        ::= { axsGsrpNeighborVlanGroupEntry 4 }

-- axsFdb group

    axsFdbCounterTable OBJECT-TYPE
        SYNTAX    SEQUENCE OF AxsFdbCounterEntry
        ACCESS    not-accessible
        STATUS    mandatory
        DESCRIPTION
                  "The table of FDB information."
        ::= { axsFdb 1 }

    axsFdbCounterEntry OBJECT-TYPE
        SYNTAX    AxsFdbCounterEntry
        ACCESS    not-accessible
        STATUS    mandatory
        DESCRIPTION
                  "The entry of FDB information."
        INDEX     { axsFdbCounterNifIndex,
                    axsFdbCounterLineIndex }
        ::= { axsFdbCounterTable 1 }

    AxsFdbCounterEntry ::= SEQUENCE {
        axsFdbCounterNifIndex     INTEGER,
        axsFdbCounterLineIndex    INTEGER,
        axsFdbCounterCounts       Counter32,
        axsFdbCounterType         INTEGER,
        axsFdbCounterLimits       Counter32
    }

    axsFdbCounterNifIndex OBJECT-TYPE
        SYNTAX    INTEGER
        ACCESS    not-accessible
        STATUS    mandatory
        DESCRIPTION
                  "Identified by a particular value of this index
                  is same value of NIF.Its value ranges between 1
                  and the value of ax6300sNifBoardNumber."
        ::= { axsFdbCounterEntry 1 }

    axsFdbCounterLineIndex OBJECT-TYPE
        SYNTAX    INTEGER
        ACCESS    not-accessible
        STATUS    mandatory
        DESCRIPTION
                  "Identified by a particular value of this index
                  is same value of Physical Line.Its value ranges
                  between 1 and the value of ax6300sNifLineNumber."
        ::= { axsFdbCounterEntry 2 }

    axsFdbCounterCounts OBJECT-TYPE
        SYNTAX    Counter32
        ACCESS    read-only
        STATUS    mandatory
        DESCRIPTION
                  "The number of FDB entries learned on the port."
        ::= { axsFdbCounterEntry 3 }

    axsFdbCounterType OBJECT-TYPE
        SYNTAX    INTEGER {
                      unlimited(0),
                      limited-and-Forward(1),
                      limited-and-Discard(2)
                  }
        ACCESS    read-only
        STATUS    mandatory
        DESCRIPTION
                  "The type of FDB entries learning."
        ::= { axsFdbCounterEntry 4 }

    axsFdbCounterLimits OBJECT-TYPE
        SYNTAX    Counter32
        ACCESS    read-only
        STATUS    mandatory
        DESCRIPTION
                  "The maximum number of FDB entries that can be learned on the port."
        ::= { axsFdbCounterEntry 5 }

-- axsVlan group

    axsVBBaseTable OBJECT-TYPE
        SYNTAX    SEQUENCE OF AxsVBBaseEntry
        ACCESS    not-accessible
        STATUS    mandatory
        DESCRIPTION
                  "An information table of dot1dBase by VLAN units."
        ::= { axsVlanBridgeBase 1 }

    axsVBBaseEntry OBJECT-TYPE
        SYNTAX    AxsVBBaseEntry
        ACCESS    not-accessible
        STATUS    mandatory
        DESCRIPTION
                  "An informatin entry of every VLAN ID of axsVBBaseTable."
        INDEX     { axsVBBaseIndex }
        ::= { axsVBBaseTable 1 }

    AxsVBBaseEntry ::= SEQUENCE {
        axsVBBaseIndex                    VlanIndex,
        axsVBBaseBridgeAddress            MacAddress,
        axsVBBaseNumPorts                 INTEGER,
        axsVBBaseType                     INTEGER,
        axsVBBaseVlanIfIndex              INTEGER,
        axsVBBaseVlanType                 INTEGER,
        axsVBBaseVlanID                   VlanIdOrZero,
        axsVBBaseAssociatedPrimaryVlan    VlanIdOrZero,
        axsVBBaseIfStatus                 INTEGER,
        axsVBBaseLastChange               TimeTicks,
        axsVBBasePrivateVlanType          INTEGER
    }

    axsVBBaseIndex OBJECT-TYPE
        SYNTAX    VlanIndex
        ACCESS    read-only
        STATUS    mandatory
        DESCRIPTION
                  "VLAN ID."
        ::= { axsVBBaseEntry 1 }

    axsVBBaseBridgeAddress OBJECT-TYPE
        SYNTAX    MacAddress
        ACCESS    read-only
        STATUS    mandatory
        DESCRIPTION
                  "MAC address of VLAN."
        ::= { axsVBBaseEntry 2 }

    axsVBBaseNumPorts OBJECT-TYPE
        SYNTAX    INTEGER
        ACCESS    read-only
        STATUS    mandatory
        DESCRIPTION
                  "The number of ports set at VLAN."
        ::= { axsVBBaseEntry 3 }

    axsVBBaseType OBJECT-TYPE
        SYNTAX    INTEGER {
                      unknown(1),
                      transparent-only(2),
                      sourceroute-only(3),
                      srt(4)
                  }
        ACCESS    read-only
        STATUS    mandatory
        DESCRIPTION
                  "A bridging type VLAN may perform."
        ::= { axsVBBaseEntry 4 }

    axsVBBaseVlanIfIndex OBJECT-TYPE
        SYNTAX    INTEGER
        ACCESS    read-only
        STATUS    mandatory
        DESCRIPTION
                  "Value of ifIndex of interface of VLAN."
        ::= { axsVBBaseEntry 5 }

    axsVBBaseVlanType OBJECT-TYPE
        SYNTAX    INTEGER {
                      port-based(1),
                      mac-based(2),
                      protocol-based(3),
                      ipsubnet-based(4)
                  }
        ACCESS    read-only
        STATUS    mandatory
        DESCRIPTION
                  "VLAN type."
        ::= { axsVBBaseEntry 6 }

    axsVBBaseVlanID OBJECT-TYPE
        SYNTAX    VlanIdOrZero
        ACCESS    read-only
        STATUS    mandatory
        DESCRIPTION
                  "Value of VID of VLAN-TAG corresponding VLAN."
        ::= { axsVBBaseEntry 7 }

    axsVBBaseAssociatedPrimaryVlan OBJECT-TYPE
        SYNTAX    VlanIdOrZero
        ACCESS    read-only
        STATUS    mandatory
        DESCRIPTION
                  "Returns VLAN ID of Primary VLAN when private VLAN is used and 
                  the same VLAN is set at secondary VLAN."
        ::= { axsVBBaseEntry 8 }

    axsVBBaseIfStatus OBJECT-TYPE
        SYNTAX    INTEGER {
                      up(1),
                      down(2)
                  }
        ACCESS    read-only
        STATUS    mandatory
        DESCRIPTION
                  "Status of interface against upper level protocol of VLAN."
        ::= { axsVBBaseEntry 9 }

    axsVBBaseLastChange OBJECT-TYPE
        SYNTAX    TimeTicks
        ACCESS    read-only
        STATUS    mandatory
        DESCRIPTION
                  "Value of sysUpTime which is set when VLAN topology changes."
        ::= { axsVBBaseEntry 10 }

    axsVBBasePrivateVlanType OBJECT-TYPE
        SYNTAX    INTEGER {
                      normal(1),
                      primary(2),
                      isolated(3),
                      community(4)
                  }
        ACCESS    read-only
        STATUS    mandatory
        DESCRIPTION
                  "A private VLAN type of VLAN."
        ::= { axsVBBaseEntry 11 }

    axsVBBasePortTable OBJECT-TYPE
        SYNTAX    SEQUENCE OF AxsVBBasePortEntry
        ACCESS    not-accessible
        STATUS    mandatory
        DESCRIPTION
                  "An information table of dot1dBasePortTable by VLAN units."
        ::= { axsVlanBridgeBase 2 }

    axsVBBasePortEntry OBJECT-TYPE
        SYNTAX    AxsVBBasePortEntry
        ACCESS    not-accessible
        STATUS    mandatory
        DESCRIPTION
                  "A configuration entry of axsVBBaseTable."
        INDEX     { axsVBBasePortIndex,
                    axsVBBasePort }
        ::= { axsVBBasePortTable 1 }

    AxsVBBasePortEntry ::= SEQUENCE {
        axsVBBasePortIndex                    VlanIndex,
        axsVBBasePort                         INTEGER,
        axsVBBasePortIfIndex                  INTEGER,
        axsVBBasePortCircuit                  OBJECT IDENTIFIER,
        axsVBBasePortDelayExceededDiscards    Counter,
        axsVBBasePortMtuExceededDiscards      Counter,
        axsVBBasePortState                    INTEGER,
        axsVBBasePortTaggedState              INTEGER,
        axsVBBasePortTranslatedTagID          VlanIdOrZero
    }

    axsVBBasePortIndex OBJECT-TYPE
        SYNTAX    VlanIndex
        ACCESS    read-only
        STATUS    mandatory
        DESCRIPTION
                  "VLAN ID."
        ::= { axsVBBasePortEntry 1 }

    axsVBBasePort OBJECT-TYPE
        SYNTAX    INTEGER
        ACCESS    read-only
        STATUS    mandatory
        DESCRIPTION
                  "Port number of ports set at VLAN."
        ::= { axsVBBasePortEntry 2 }

    axsVBBasePortIfIndex OBJECT-TYPE
        SYNTAX    INTEGER
        ACCESS    read-only
        STATUS    mandatory
        DESCRIPTION
                  "Value of ifIndex corresponding ports set at VLAN."
        ::= { axsVBBasePortEntry 3 }

    axsVBBasePortCircuit OBJECT-TYPE
        SYNTAX    OBJECT IDENTIFIER
        ACCESS    read-only
        STATUS    mandatory
        DESCRIPTION
                  "Identifier which identifieds ports when VLAN ports
                   have the same value as axsVBBasePortIfIndex."
        ::= { axsVBBasePortEntry 4 }

    axsVBBasePortDelayExceededDiscards OBJECT-TYPE
        SYNTAX    Counter
        ACCESS    read-only
        STATUS    mandatory
        DESCRIPTION
                  "Total number of discard frame caused by passing delay occured at VLAN ports."
        ::= { axsVBBasePortEntry 5 }

    axsVBBasePortMtuExceededDiscards OBJECT-TYPE
        SYNTAX    Counter
        ACCESS    read-only
        STATUS    mandatory
        DESCRIPTION
                  "Total number of discard frame caused by data over flow occured at VLAN ports."
        ::= { axsVBBasePortEntry 6 }

    axsVBBasePortState OBJECT-TYPE
        SYNTAX    INTEGER {
                      disabled(1),
                      blocking(2),
                      listening(3),
                      learning(4),
                      forwarding(5),
                      broken(6),
                      fix-forwarding(7)
                  }
        ACCESS    read-only
        STATUS    mandatory
        DESCRIPTION
                  "STP port status of port set at VLAN."
        ::= { axsVBBasePortEntry 7 }

    axsVBBasePortTaggedState OBJECT-TYPE
        SYNTAX    INTEGER {
                      untagged(1),
                      tagged(2)
                  }
        ACCESS    read-only
        STATUS    mandatory
        DESCRIPTION
                  "Status of VLAN-TAG configuration of ports set at VLAN."
        ::= { axsVBBasePortEntry 8 }

    axsVBBasePortTranslatedTagID OBJECT-TYPE
        SYNTAX    VlanIdOrZero
        ACCESS    read-only
        STATUS    mandatory
        DESCRIPTION
                  "Translated ID of VLAN when TAG translation is set."
        ::= { axsVBBasePortEntry 9 }

    axsVBStpTable OBJECT-TYPE
        SYNTAX    SEQUENCE OF AxsVBStpEntry
        ACCESS    not-accessible
        STATUS    mandatory
        DESCRIPTION
                  "An information table of dot1dStpTable by VLAN units."
        ::= { axsVlanBridgeStp 1 }

    axsVBStpEntry OBJECT-TYPE
        SYNTAX    AxsVBStpEntry
        ACCESS    not-accessible
        STATUS    mandatory
        DESCRIPTION
                  "A configuration entry of axsVBStpTable."
        INDEX     { axsVBStpIndex }
        ::= { axsVBStpTable 1 }

    AxsVBStpEntry ::= SEQUENCE {
        axsVBStpIndex                      VlanIndex,
        axsVBStpProtocolSpecification      INTEGER,
        axsVBStpPriority                   INTEGER,
        axsVBStpTimeSinceTopologyChange    TimeTicks,
        axsVBStpTopChanges                 Counter,
        axsVBStpDesignatedRoot             BridgeId,
        axsVBStpRootCost                   INTEGER,
        axsVBStpRootPort                   INTEGER,
        axsVBStpMaxAge                     Timeout,
        axsVBStpHelloTime                  Timeout,
        axsVBStpHoldTime                   INTEGER,
        axsVBStpForwardDelay               Timeout,
        axsVBStpBridgeMaxAge               Timeout,
        axsVBStpBridgeHelloTime            Timeout,
        axsVBStpBridgeForwardDelay         Timeout
    }

    axsVBStpIndex OBJECT-TYPE
        SYNTAX    VlanIndex
        ACCESS    read-only
        STATUS    mandatory
        DESCRIPTION
                  "VLAN ID."
        ::= { axsVBStpEntry 1 }

    axsVBStpProtocolSpecification OBJECT-TYPE
        SYNTAX    INTEGER {
                      unknown(1),
                      decLb100(2),
                      ieee8021d(3),
                      ieee8021w(4)
                  }
        ACCESS    read-only
        STATUS    mandatory
        DESCRIPTION
                  "A kind of spanning tree protocol by VLAN units."
        ::= { axsVBStpEntry 2 }

    axsVBStpPriority OBJECT-TYPE
        SYNTAX    INTEGER
        ACCESS    read-only
        STATUS    mandatory
        DESCRIPTION
                  "Priority value of spanning tree by VLAN units."
        ::= { axsVBStpEntry 3 }

    axsVBStpTimeSinceTopologyChange OBJECT-TYPE
        SYNTAX    TimeTicks
        ACCESS    read-only
        STATUS    mandatory
        DESCRIPTION
                  "Elapsed time since topology change of spanning tree by VLAN units."
        ::= { axsVBStpEntry 4 }

    axsVBStpTopChanges OBJECT-TYPE
        SYNTAX    Counter
        ACCESS    read-only
        STATUS    mandatory
        DESCRIPTION
                  "The number of times of topology changes of spanning tree by VLAN units."
        ::= { axsVBStpEntry 5 }

    axsVBStpDesignatedRoot OBJECT-TYPE
        SYNTAX    BridgeId
        ACCESS    read-only
        STATUS    mandatory
        DESCRIPTION
                  "Root bridge identifier of spanning tree by VLAN units."
        ::= { axsVBStpEntry 6 }

    axsVBStpRootCost OBJECT-TYPE
        SYNTAX    INTEGER
        ACCESS    read-only
        STATUS    mandatory
        DESCRIPTION
                  "Root path cost kept by spanning tree by VLAN units."
        ::= { axsVBStpEntry 7 }

    axsVBStpRootPort OBJECT-TYPE
        SYNTAX    INTEGER
        ACCESS    read-only
        STATUS    mandatory
        DESCRIPTION
                  "Root port value kept by spanning tree by VLAN units."
        ::= { axsVBStpEntry 8 }

    axsVBStpMaxAge OBJECT-TYPE
        SYNTAX    Timeout
        ACCESS    read-only
        STATUS    mandatory
        DESCRIPTION
                  "Maximum aging time kept by spanning tree by VLAN units."
        ::= { axsVBStpEntry 9 }

    axsVBStpHelloTime OBJECT-TYPE
        SYNTAX    Timeout
        ACCESS    read-only
        STATUS    mandatory
        DESCRIPTION
                  "Hello time kept by spanning tree by VLAN units."
        ::= { axsVBStpEntry 10 }

    axsVBStpHoldTime OBJECT-TYPE
        SYNTAX    INTEGER
        ACCESS    read-only
        STATUS    mandatory
        DESCRIPTION
                  "Hold time kept by spanning tree by VLAN units."
        ::= { axsVBStpEntry 11 }

    axsVBStpForwardDelay OBJECT-TYPE
        SYNTAX    Timeout
        ACCESS    read-only
        STATUS    mandatory
        DESCRIPTION
                  "Transfer delay time kept by spanning tree by VLAN units."
        ::= { axsVBStpEntry 12 }

    axsVBStpBridgeMaxAge OBJECT-TYPE
        SYNTAX    Timeout
        ACCESS    read-only
        STATUS    mandatory
        DESCRIPTION
                  "Maximum aging time used when spanning tree acts as a root bridge by VLAN units."
        ::= { axsVBStpEntry 13 }

    axsVBStpBridgeHelloTime OBJECT-TYPE
        SYNTAX    Timeout
        ACCESS    read-only
        STATUS    mandatory
        DESCRIPTION
                  "Hello time used when spanning tree act as a root bridge by VLAN units."
        ::= { axsVBStpEntry 14 }

    axsVBStpBridgeForwardDelay OBJECT-TYPE
        SYNTAX    Timeout
        ACCESS    read-only
        STATUS    mandatory
        DESCRIPTION
                  "Transfer delay time used when spanning tree act as a root bridge by VLAN units."
        ::= { axsVBStpEntry 15 }

    axsVBStpPortTable OBJECT-TYPE
        SYNTAX    SEQUENCE OF AxsVBStpPortEntry
        ACCESS    not-accessible
        STATUS    mandatory
        DESCRIPTION
                  "An information table of dot1dStpPortTable by VLAN units."
        ::= { axsVlanBridgeStp 2 }

    axsVBStpPortEntry OBJECT-TYPE
        SYNTAX    AxsVBStpPortEntry
        ACCESS    not-accessible
        STATUS    mandatory
        DESCRIPTION
                  "A configuration entry of axsVBStpPortTable."
        INDEX     { axsVBStpPortIndex,
                    axsVBStpPort }
        ::= { axsVBStpPortTable 1 }

    AxsVBStpPortEntry ::= SEQUENCE {
        axsVBStpPortIndex                 VlanIndex,
        axsVBStpPort                      INTEGER,
        axsVBStpPortPriority              INTEGER,
        axsVBStpPortState                 INTEGER,
        axsVBStpPortEnable                INTEGER,
        axsVBStpPortPathCost              INTEGER,
        axsVBStpPortDesignatedRoot        BridgeId,
        axsVBStpPortDesignatedCost        INTEGER,
        axsVBStpPortDesignatedBridge      BridgeId,
        axsVBStpPortDesignatedPort        OCTET STRING,
        axsVBStpPortForwardTransitions    Counter
    }

    axsVBStpPortIndex OBJECT-TYPE
        SYNTAX    VlanIndex
        ACCESS    read-only
        STATUS    mandatory
        DESCRIPTION
                  "VLAN ID."
        ::= { axsVBStpPortEntry 1 }

    axsVBStpPort OBJECT-TYPE
        SYNTAX    INTEGER
        ACCESS    read-only
        STATUS    mandatory
        DESCRIPTION
                  "Port number corresponding configuration entry."
        ::= { axsVBStpPortEntry 2 }

    axsVBStpPortPriority OBJECT-TYPE
        SYNTAX    INTEGER
        ACCESS    read-only
        STATUS    mandatory
        DESCRIPTION
                  "Priority of port by VLAN units."
        ::= { axsVBStpPortEntry 3 }

    axsVBStpPortState OBJECT-TYPE
        SYNTAX    INTEGER {
                      disabled(1),
                      blocking(2),
                      listening(3),
                      learning(4),
                      forwarding(5),
                      broken(6)
                  }
        ACCESS    read-only
        STATUS    mandatory
        DESCRIPTION
                  "Present status of port by VLAN units."
        ::= { axsVBStpPortEntry 4 }

    axsVBStpPortEnable OBJECT-TYPE
        SYNTAX    INTEGER {
                      enabled(1),
                      disabled(2)
                  }
        ACCESS    read-only
        STATUS    mandatory
        DESCRIPTION
                  "Value whether spanning tree is enabled or not at the port by VLAN units."
        ::= { axsVBStpPortEntry 5 }

    axsVBStpPortPathCost OBJECT-TYPE
        SYNTAX    INTEGER
        ACCESS    read-only
        STATUS    mandatory
        DESCRIPTION
                  "Path cost value of the port by VLAN units."
        ::= { axsVBStpPortEntry 6 }

    axsVBStpPortDesignatedRoot OBJECT-TYPE
        SYNTAX    BridgeId
        ACCESS    read-only
        STATUS    mandatory
        DESCRIPTION
                  "Value of root bridge identifier by VLAN units stored in BPDU from specified bridge."
        ::= { axsVBStpPortEntry 7 }

    axsVBStpPortDesignatedCost OBJECT-TYPE
        SYNTAX    INTEGER
        ACCESS    read-only
        STATUS    mandatory
        DESCRIPTION
                  "Path cost value of specified port connected to the port by VLAN units."
        ::= { axsVBStpPortEntry 8 }

    axsVBStpPortDesignatedBridge OBJECT-TYPE
        SYNTAX    BridgeId
        ACCESS    read-only
        STATUS    mandatory
        DESCRIPTION
                  "Bridge identifier of bridge which this port regards as specified bridge by VLAN units."
        ::= { axsVBStpPortEntry 9 }

    axsVBStpPortDesignatedPort OBJECT-TYPE
        SYNTAX    OCTET STRING
        ACCESS    read-only
        STATUS    mandatory
        DESCRIPTION
                  "Port identifier of specified bridge connected to this port by VLAN units."
        ::= { axsVBStpPortEntry 10 }

    axsVBStpPortForwardTransitions OBJECT-TYPE
        SYNTAX    Counter
        ACCESS    read-only
        STATUS    mandatory
        DESCRIPTION
                  "The number of times of changes from learning status into forwarding status."
        ::= { axsVBStpPortEntry 11 }

    axsVBTpTable OBJECT-TYPE
        SYNTAX    SEQUENCE OF AxsVBTpEntry
        ACCESS    not-accessible
        STATUS    mandatory
        DESCRIPTION
                  "A dot1dTp information table by VLAN units."
        ::= { axsVlanBridgeTp 1 }

    axsVBTpEntry OBJECT-TYPE
        SYNTAX    AxsVBTpEntry
        ACCESS    not-accessible
        STATUS    mandatory
        DESCRIPTION
                  "A configuration entry of axsVBTpTable."
        INDEX     { axsVBTpIndex }
        ::= { axsVBTpTable 1 }

    AxsVBTpEntry ::= SEQUENCE {
        axsVBTpIndex                   VlanIndex,
        axsVBTpLearnedEntryDiscards    Counter,
        axsVBTpAgingTime               INTEGER
    }

    axsVBTpIndex OBJECT-TYPE
        SYNTAX    VlanIndex
        ACCESS    read-only
        STATUS    mandatory
        DESCRIPTION
                  "VLAN ID."
        ::= { axsVBTpEntry 1 }

    axsVBTpLearnedEntryDiscards OBJECT-TYPE
        SYNTAX    Counter
        ACCESS    read-only
        STATUS    mandatory
        DESCRIPTION
                  "The number of discarded entries because of lack of
                  not-used domain in filtering data base."
        ::= { axsVBTpEntry 2 }

    axsVBTpAgingTime OBJECT-TYPE
        SYNTAX    INTEGER
        ACCESS    read-only
        STATUS    mandatory
        DESCRIPTION
                  "Time-out time to aging-out entry of filtering date base which is learned dynamically."
        ::= { axsVBTpEntry 3 }

    axsVBTpFdbTable OBJECT-TYPE
        SYNTAX    SEQUENCE OF AxsVBTpFdbEntry
        ACCESS    not-accessible
        STATUS    mandatory
        DESCRIPTION
                  "An information of dot1dTpFdbTable by VLAN units."
        ::= { axsVlanBridgeTp 2 }

    axsVBTpFdbEntry OBJECT-TYPE
        SYNTAX    AxsVBTpFdbEntry
        ACCESS    not-accessible
        STATUS    mandatory
        DESCRIPTION
                  "A configuration entry of axsVBTpFdbTable."
        INDEX     { axsVBTpFdbIndex,
                    axsVBTpFdbAddress }
        ::= { axsVBTpFdbTable 1 }

    AxsVBTpFdbEntry ::= SEQUENCE {
        axsVBTpFdbIndex      VlanIndex,
        axsVBTpFdbAddress    MacAddress,
        axsVBTpFdbPort       INTEGER,
        axsVBTpFdbStatus     INTEGER
    }

    axsVBTpFdbIndex OBJECT-TYPE
        SYNTAX    VlanIndex
        ACCESS    read-only
        STATUS    mandatory
        DESCRIPTION
                  "VLAN ID."
        ::= { axsVBTpFdbEntry 1 }

    axsVBTpFdbAddress OBJECT-TYPE
        SYNTAX    MacAddress
        ACCESS    read-only
        STATUS    mandatory
        DESCRIPTION
                  "Unicast MAC address of filtering data base entry."
        ::= { axsVBTpFdbEntry 2 }

    axsVBTpFdbPort OBJECT-TYPE
        SYNTAX    INTEGER
        ACCESS    read-only
        STATUS    mandatory
        DESCRIPTION
                  "Indicates that it hasn't learnt port number when
                  port number 0 receives frame having MAC address
                  as source address which axsVBTpFdbAddress indicates."
        ::= { axsVBTpFdbEntry 3 }

    axsVBTpFdbStatus OBJECT-TYPE
        SYNTAX    INTEGER {
                      other(1),
                      invalid(2),
                      learned(3),
                      self(4),
                      mgmt(5)
                  }
        ACCESS    read-only
        STATUS    mandatory
        DESCRIPTION
                  "Status of filtering data base."
        ::= { axsVBTpFdbEntry 4 }

    axsVBTpPortTable OBJECT-TYPE
        SYNTAX    SEQUENCE OF AxsVBTpPortEntry
        ACCESS    not-accessible
        STATUS    mandatory
        DESCRIPTION
                  "An information table of dot1dTpPortTable by VLAN units."
        ::= { axsVlanBridgeTp 3 }

    axsVBTpPortEntry OBJECT-TYPE
        SYNTAX    AxsVBTpPortEntry
        ACCESS    not-accessible
        STATUS    mandatory
        DESCRIPTION
                  "An information entry of axsVBTpPortTable of ports."
        INDEX { axsVBTpPortIndex,
                axsVBTpPort }
        ::= { axsVBTpPortTable 1 }

    AxsVBTpPortEntry ::= SEQUENCE {
        axsVBTpPortIndex         VlanIndex,
        axsVBTpPort              INTEGER,
        axsVBTpPortMaxInfo       INTEGER,
        axsVBTpPortInFrames      Counter,
        axsVBTpPortOutFrames     Counter,
        axsVBTpPortInDiscards    Counter
    }

    axsVBTpPortIndex OBJECT-TYPE
        SYNTAX    VlanIndex
        ACCESS    read-only
        STATUS    mandatory
        DESCRIPTION
                  "VLAN ID."
        ::= { axsVBTpPortEntry 1 }

    axsVBTpPort OBJECT-TYPE
        SYNTAX    INTEGER
        ACCESS    read-only
        STATUS    mandatory
        DESCRIPTION
                  "Port number that indicates which port management
                  information in the entry corresponds."
        ::= { axsVBTpPortEntry 2 }

    axsVBTpPortMaxInfo OBJECT-TYPE
        SYNTAX    INTEGER
        ACCESS    read-only
        STATUS    mandatory
        DESCRIPTION
                  "Maximum INFO field size of the port by VLAN units."
        ::= { axsVBTpPortEntry 3 }

    axsVBTpPortInFrames OBJECT-TYPE
        SYNTAX    Counter
        ACCESS    read-only
        STATUS    mandatory
        DESCRIPTION
                  "The number of reception frame of the port by VLAN units."
        ::= { axsVBTpPortEntry 4 }

    axsVBTpPortOutFrames OBJECT-TYPE
        SYNTAX    Counter
        ACCESS    read-only
        STATUS    mandatory
        DESCRIPTION
                  "The number of sending frame of the port by VLAN units."
        ::= { axsVBTpPortEntry 5 }

    axsVBTpPortInDiscards OBJECT-TYPE
        SYNTAX    Counter
        ACCESS    read-only
        STATUS    mandatory
        DESCRIPTION
                  "The number of reception frame of the port by VLAN units."
        ::= { axsVBTpPortEntry 6 }

    axsVBStaticTable OBJECT-TYPE
        SYNTAX    SEQUENCE OF AxsVBStaticEntry
        ACCESS    not-accessible
        STATUS    mandatory
        DESCRIPTION
                  "An information table of dot1dStaticTable by VLAN units."
        ::= { axsVlanBridgeStatic 1 }

    axsVBStaticEntry OBJECT-TYPE
        SYNTAX    AxsVBStaticEntry
        ACCESS    not-accessible
        STATUS    mandatory
        DESCRIPTION
                  "A configuration entry of axsVBStaticTable."
        INDEX { axsVBStaticIndex,
                axsVBStaticAddress }
        ::= { axsVBStaticTable 1 }

    AxsVBStaticEntry ::= SEQUENCE {
        axsVBStaticIndex            VlanIndex,
        axsVBStaticAddress          MacAddress,
        axsVBStaticReceivePort      INTEGER,
        axsVBStaticAllowedToGoTo    OCTET STRING,
        axsVBStaticStatus           INTEGER
    }

    axsVBStaticIndex OBJECT-TYPE
        SYNTAX    VlanIndex
        ACCESS    read-only
        STATUS    mandatory
        DESCRIPTION
                  "VLAN ID."
        ::= { axsVBStaticEntry 1 }

    axsVBStaticAddress OBJECT-TYPE
        SYNTAX    MacAddress
        ACCESS    read-only
        STATUS    mandatory
        DESCRIPTION
                  "MAC address of eather unicast, group or broadcast."
        ::= { axsVBStaticEntry 2 }

    axsVBStaticReceivePort OBJECT-TYPE
        SYNTAX    INTEGER
        ACCESS    read-only
        STATUS    mandatory
        DESCRIPTION
                  "Reception port number which is applied the entry."
        ::= { axsVBStaticEntry 3 }

    axsVBStaticAllowedToGoTo OBJECT-TYPE
        SYNTAX    OCTET STRING
        ACCESS    read-only
        STATUS    mandatory
        DESCRIPTION
                  "Bit map of port indicating destination port when transfering
                  frame whose destination is MAC address kept by this entry"
        ::= { axsVBStaticEntry 4 }

    axsVBStaticStatus OBJECT-TYPE
        SYNTAX    INTEGER {
                      other(1),
                      invalid(2),
                      permanent(3),
                      deleteOnReset(4),
                      deleteOnTimeout(5)
                  }
        ACCESS    read-only
        STATUS    mandatory
        DESCRIPTION
                  "Status of the entry."
        ::= { axsVBStaticEntry 5 }

    axsVlanBridgeMaxVlans OBJECT-TYPE
        SYNTAX    VlanIndex
        ACCESS    read-only
        STATUS    mandatory
        DESCRIPTION
                  "Maximum value of VLAN ID of this device."
        ::= { axsVlanBridge 101 }

    axsVlanBridgeMaxSpans OBJECT-TYPE
        SYNTAX    VlanIndex
        ACCESS    read-only
        STATUS    mandatory
        DESCRIPTION
                  "Maximum value of VLAN ID of VLAN which may operate
                  spanning tree in this device."
        ::= { axsVlanBridge 102 }

    axsVlanTagTranslationTable OBJECT-TYPE
        SYNTAX    SEQUENCE OF AxsVlanTagTranslationEntry
        ACCESS    not-accessible
        STATUS    mandatory
        DESCRIPTION
                  "The information table about a Tag conversion function"
        ::= { axsVlanTagTranslation 1 }

    axsVlanTagTranslationEntry OBJECT-TYPE
        SYNTAX    AxsVlanTagTranslationEntry
        ACCESS    not-accessible
        STATUS    mandatory
        DESCRIPTION
                  "The entry of the information table about a Tag conversion function"
        INDEX { axsVlanTagTranslationVlanId,
                axsVlanTagTranslationTranslatedId }
        ::= { axsVlanTagTranslationTable 1 }

    AxsVlanTagTranslationEntry ::= SEQUENCE {
        axsVlanTagTranslationVlanId          INTEGER,
        axsVlanTagTranslationTranslatedId    INTEGER,
        axsVlanTagTranslationPorts           PortList
    }

    axsVlanTagTranslationVlanId OBJECT-TYPE
        SYNTAX    INTEGER
        ACCESS    not-accessible
        STATUS    mandatory
        DESCRIPTION
                  "VLAN ID which has set up the Tag conversion function"
        ::= { axsVlanTagTranslationEntry 1 }

    axsVlanTagTranslationTranslatedId OBJECT-TYPE
        SYNTAX    INTEGER
        ACCESS    not-accessible
        STATUS    mandatory
        DESCRIPTION
                  "Translated ID set up by the Tag conversion function"
        ::= { axsVlanTagTranslationEntry 2 }

    axsVlanTagTranslationPorts OBJECT-TYPE
        SYNTAX    PortList
        ACCESS    read-only
        STATUS    mandatory
        DESCRIPTION
                  "The port list which has set up the same Translated ID by the same VLAN by the Tag conversion function"
        ::= { axsVlanTagTranslationEntry 3 }

-- OADP Group

    axsOadpGlobalActive  OBJECT-TYPE
        SYNTAX    TruthValue
        ACCESS    read-only
        STATUS    mandatory
        DESCRIPTION
                  "Operation status of OADP function. Status set
                  by enable or disable in Oadp configuration.
                  enable : 1
                  disable: 2"
        ::= { axsOadpGlobalInfo 1 }

    axsOadpGlobalCdpActive  OBJECT-TYPE
        SYNTAX    TruthValue
        ACCESS    read-only
        STATUS    mandatory
        DESCRIPTION
                  "Operation status of CDP reception function.
                  Status whether cdp-listener is set or not in oadp configuration.
                  cdp-listener           : 1
                  cdp-listener is not set: 2"
        ::= { axsOadpGlobalInfo 2 }

    axsOadpGlobalMessageInterval OBJECT-TYPE
        SYNTAX    INTEGER
        ACCESS    read-only
        STATUS    mandatory
        DESCRIPTION
                  "Sending interval of OADP frame. The value of interval-time in oadp configuration."
        ::= { axsOadpGlobalInfo 3 }

    axsOadpGlobalHoldTime OBJECT-TYPE
        SYNTAX    INTEGER
        ACCESS    read-only
        STATUS    mandatory
        DESCRIPTION
                  "Neighbor divice's holding time of OADP frame which this device send.
                  The value of hold-time in oadp configuration."
        ::= { axsOadpGlobalInfo 4 }

    axsOadpGlobalCacheLastChange OBJECT-TYPE
        SYNTAX    TimeTicks
        ACCESS    read-only
        STATUS    mandatory
        DESCRIPTION
                  "Value of sysUpTime which is set when axsOadpNeighborTable is updated."
        ::= { axsOadpGlobalInfo 5 }

    axsOadpGlobalName OBJECT-TYPE
        SYNTAX    DisplayString
        ACCESS    read-only
        STATUS    mandatory
        DESCRIPTION
                  "Device identifier."
        ::= { axsOadpGlobalInfo 6 }

    axsOadpGlobalNameType OBJECT-TYPE
        SYNTAX    INTEGER {
                      other(1),
                      sysName(2),
                      serialNumber(3),
                      macaddress(4)
                  }
        ACCESS    read-only
        STATUS    mandatory
        DESCRIPTION
                  "Kind of axsOadpGlobalName."
        ::= { axsOadpGlobalInfo 7 }

    axsOadpPortConfigTable OBJECT-TYPE
        SYNTAX    SEQUENCE OF AxsOadpPortConfigEntry
        ACCESS    not-accessible
        STATUS    mandatory
        DESCRIPTION
                  "A table of OADP port information."
        ::= { axsOadpPortInfo 1 }

    axsOadpPortConfigEntry OBJECT-TYPE
        SYNTAX    AxsOadpPortConfigEntry
        ACCESS    not-accessible
        STATUS    mandatory
        DESCRIPTION
                  "An entry of OADP port information."
        INDEX     { axsOadpPortConfigIfIndex }
        ::= { axsOadpPortConfigTable 1 }

    AxsOadpPortConfigEntry ::= SEQUENCE {
        axsOadpPortConfigIfIndex    InterfaceIndex,
        axsOadpPortConfigActive     TruthValue
    }

    axsOadpPortConfigIfIndex OBJECT-TYPE
        SYNTAX    InterfaceIndex
        ACCESS    read-only
        STATUS    mandatory
        DESCRIPTION
                  "Port identification index. The same value as ifIndex.
                  This is only for physical ports and LA ports which are given
                  ifIndex."
        ::= { axsOadpPortConfigEntry 1 }

    axsOadpPortConfigActive OBJECT-TYPE
        SYNTAX    TruthValue
        ACCESS    read-only
        STATUS    mandatory
        DESCRIPTION
                  "Status of specified port."
        ::= { axsOadpPortConfigEntry 2 }

    axsOadpNeighborTable OBJECT-TYPE
        SYNTAX    SEQUENCE OF AxsOadpNeighborEntry
        ACCESS    not-accessible
        STATUS    mandatory
        DESCRIPTION
                  "A table of OADP neighbor nodes."
        ::= { axsOadpNeighborInfo 1 }

    axsOadpNeighborEntry OBJECT-TYPE
        SYNTAX    AxsOadpNeighborEntry
        ACCESS    not-accessible
        STATUS    mandatory
        DESCRIPTION
                  "An entry of OADP neighbor nodes."
        INDEX     { axsOadpIfIndex,
                    axsOadpTagID,
                    axsOadpNeighborIndex,
                    axsOadpNeighborTagID }
        ::= { axsOadpNeighborTable 1 }

    AxsOadpNeighborEntry ::= SEQUENCE {
        axsOadpIfIndex                                  InterfaceIndex,
        axsOadpTagID                                    INTEGER, 
        axsOadpNeighborIndex                            INTEGER,
        axsOadpNeighborTagID                            INTEGER,
        axsOadpNeighborVendorType                       INTEGER,
        axsOadpNeighborSNMPAgentAddressType             INTEGER,
        axsOadpNeighborSNMPAgentAddress                 DisplayString,
        axsOadpNeighborDescr                            DisplayString,
        axsOadpNeighborDeviceID                         DisplayString,
        axsOadpNeighborSlotPort                         DisplayString,
        axsOadpNeighborIfIndex                          InterfaceIndex,
        axsOadpNeighborIfSpeed                          Gauge,
        axsOadpNeighborDeviceType                       DisplayString,
        axsOadpNeighborService                          OCTET STRING,
        axsOadpNeighborVTPMgmtDomain                    DisplayString,
        axsOadpNeighborNativeVLAN                       INTEGER,
        axsOadpNeighborDuplex                           INTEGER,
        axsOadpNeighborApplianceID                      Gauge,
        axsOadpNeighborVlanID                           Gauge,
        axsOadpNeighborPowerConsumption                 Gauge,
        axsOadpNeighborMTU                              Gauge,
        axsOadpNeighborSysName                          DisplayString,
        axsOadpNeighborSysObjectID                      OBJECT IDENTIFIER,
        axsOadpNeighborSecondarySNMPAgentAddressType    INTEGER,
        axsOadpNeighborSecondarySNMPAgentAddress        DisplayString,
        axsOadpNeighborPhysLocation                     DisplayString,
        axsOadpNeighborCacheLastChange                  TimeTicks,
        axsOadpNeighborIfHighSpeed                      Gauge
    }

    axsOadpIfIndex OBJECT-TYPE
        SYNTAX    InterfaceIndex
        ACCESS    read-only
        STATUS    mandatory
        DESCRIPTION
                  "ifIndex of reception interface."
        ::= { axsOadpNeighborEntry 1 }

    axsOadpTagID OBJECT-TYPE
        SYNTAX    INTEGER
        ACCESS    read-only
        STATUS    mandatory
        DESCRIPTION
                  "Tag ID of IEEE802.1Q which is attached MAC frame."
        ::= { axsOadpNeighborEntry 2 }

    axsOadpNeighborIndex OBJECT-TYPE
        SYNTAX    INTEGER
        ACCESS    read-only
        STATUS    mandatory
        DESCRIPTION
                  "Unique numeric which identifies neighbor nodes"
        ::= { axsOadpNeighborEntry 3 }

    axsOadpNeighborTagID OBJECT-TYPE
        SYNTAX    INTEGER
        ACCESS    read-only
        STATUS    mandatory
        DESCRIPTION
                  "Value set at TagID TLV in OADP PDU which is sent from neighbor node."
        ::= { axsOadpNeighborEntry 4 }

    axsOadpNeighborVendorType OBJECT-TYPE
        SYNTAX    INTEGER {
                      other(1),
                      oadp(2),
                      cdp(3)
                  }
        ACCESS    read-only
        STATUS    mandatory
        DESCRIPTION
                  "Protocol type used to find to neighbor nodes."
        ::= { axsOadpNeighborEntry 5 }

    axsOadpNeighborSNMPAgentAddressType OBJECT-TYPE
        SYNTAX    INTEGER {
                      ipv4(1),
                      ipv6(20),
                      other-notSupported(65535)
                  }
        ACCESS    read-only
        STATUS    mandatory
        DESCRIPTION
                  "A kind of agent address to get information by SNMP."
        ::= { axsOadpNeighborEntry 6 }

    axsOadpNeighborSNMPAgentAddress OBJECT-TYPE
        SYNTAX    DisplayString
        ACCESS    read-only
        STATUS    mandatory
        DESCRIPTION
                  "DisplayString formed information of agent address to get information by SNMP."
        ::= { axsOadpNeighborEntry 7 }

    axsOadpNeighborDescr OBJECT-TYPE
        SYNTAX    DisplayString
        ACCESS    read-only
        STATUS    mandatory
        DESCRIPTION
                  "String of sysDescr of neighbor node."
        ::= { axsOadpNeighborEntry 8 }

    axsOadpNeighborDeviceID OBJECT-TYPE
        SYNTAX    DisplayString
        ACCESS    read-only
        STATUS    mandatory
        DESCRIPTION
                  "Neighbor node's device identifier."
        ::= { axsOadpNeighborEntry 9 }

    axsOadpNeighborSlotPort OBJECT-TYPE
        SYNTAX    DisplayString
        ACCESS    read-only
        STATUS    mandatory
        DESCRIPTION
                  "Unique string which identifies neighbor's sending interface."
        ::= { axsOadpNeighborEntry 10 }

    axsOadpNeighborIfIndex OBJECT-TYPE
        SYNTAX    InterfaceIndex
        ACCESS    read-only
        STATUS    mandatory
        DESCRIPTION
                  "ifIndex of sending interface of neighbor node."
        ::= { axsOadpNeighborEntry 11 }

    axsOadpNeighborIfSpeed OBJECT-TYPE
        SYNTAX    Gauge
        ACCESS    read-only
        STATUS    mandatory
        DESCRIPTION
                  "ifSpeed of sending interface of neighbor node."
        ::= { axsOadpNeighborEntry 12 }

    axsOadpNeighborDeviceType OBJECT-TYPE
        SYNTAX    DisplayString
        ACCESS    read-only
        STATUS    mandatory
        DESCRIPTION
                  "Device name of neighbor node."
        ::= { axsOadpNeighborEntry 13 }

    axsOadpNeighborService OBJECT-TYPE
        SYNTAX    OCTET STRING
        ACCESS    read-only
        STATUS    mandatory
        DESCRIPTION
                  "Functions neighbor node can offer."
        ::= { axsOadpNeighborEntry 14 }

    axsOadpNeighborVTPMgmtDomain OBJECT-TYPE
        SYNTAX    DisplayString
        ACCESS    read-only
        STATUS    mandatory
        DESCRIPTION
                  "VTP Management Domain of sending interface of neighbor node."
        ::= { axsOadpNeighborEntry 15 }

    axsOadpNeighborNativeVLAN OBJECT-TYPE
        SYNTAX    INTEGER
        ACCESS    read-only
        STATUS    mandatory
        DESCRIPTION
                  "Native VLAN number of sending interface of neighbor node."
        ::= { axsOadpNeighborEntry 16 }

    axsOadpNeighborDuplex OBJECT-TYPE
        SYNTAX    INTEGER {
                      unknown(1),
                      half(2),
                      full(3)
                  }
        ACCESS    read-only
        STATUS    mandatory
        DESCRIPTION
                  "Duplex information of sending interface of neighbor node."
        ::= { axsOadpNeighborEntry 17 }

    axsOadpNeighborApplianceID OBJECT-TYPE
        SYNTAX    Gauge
        ACCESS    read-only
        STATUS    mandatory
        DESCRIPTION
                  "Appliance ID of neighbor node."
        ::= { axsOadpNeighborEntry 18 }

    axsOadpNeighborVlanID OBJECT-TYPE
        SYNTAX    Gauge
        ACCESS    read-only
        STATUS    mandatory
        DESCRIPTION
                  "VLAN ID for VoIP of neighbor node."
        ::= { axsOadpNeighborEntry 19 }

    axsOadpNeighborPowerConsumption OBJECT-TYPE
        SYNTAX    Gauge
        ACCESS    read-only
        STATUS    mandatory
        DESCRIPTION
                  "Electric power comsumption of neighbor node."
        ::= { axsOadpNeighborEntry 20 }

    axsOadpNeighborMTU OBJECT-TYPE
        SYNTAX    Gauge
        ACCESS    read-only
        STATUS    mandatory
        DESCRIPTION
                  "MTU of sending interface of neighbor node."
        ::= { axsOadpNeighborEntry 21 }

    axsOadpNeighborSysName OBJECT-TYPE
        SYNTAX    DisplayString
        ACCESS    read-only
        STATUS    mandatory
        DESCRIPTION
                  "sysName of neighbor node."
        ::= { axsOadpNeighborEntry 22 }

    axsOadpNeighborSysObjectID OBJECT-TYPE
        SYNTAX    OBJECT IDENTIFIER
        ACCESS    read-only
        STATUS    mandatory
        DESCRIPTION
                  "sysObjectID of neighbor node."
        ::= { axsOadpNeighborEntry 23 }

    axsOadpNeighborSecondarySNMPAgentAddressType OBJECT-TYPE
        SYNTAX    INTEGER {
                      ipv4(1),
                      ipv6(20),
                      other-notSupported(65535)
                  }
        ACCESS    read-only
        STATUS    mandatory
        DESCRIPTION
                  "A kind of agent secondary address to get information by SNMP."
        ::= { axsOadpNeighborEntry 24 }

    axsOadpNeighborSecondarySNMPAgentAddress OBJECT-TYPE
        SYNTAX    DisplayString
        ACCESS    read-only
        STATUS    mandatory
        DESCRIPTION
                  "DisplayString formed information of agent secondary address to get information by SNMP."
        ::= { axsOadpNeighborEntry 25 }

    axsOadpNeighborPhysLocation OBJECT-TYPE
        SYNTAX    DisplayString
        ACCESS    read-only
        STATUS    mandatory
        DESCRIPTION
                  "sysLocation of neighbor node."
        ::= { axsOadpNeighborEntry 26 }

    axsOadpNeighborCacheLastChange OBJECT-TYPE
        SYNTAX    TimeTicks
        ACCESS    read-only
        STATUS    mandatory
        DESCRIPTION
                  "Value of sysUpTime which is set when axsOadpNeighborEntry about neighbor node is updated."
        ::= { axsOadpNeighborEntry 27 }

    axsOadpNeighborIfHighSpeed OBJECT-TYPE
        SYNTAX    Gauge
        ACCESS    read-only
        STATUS    mandatory
        DESCRIPTION
                  "ifHighSpeed of sending interface of neighbor node."
        ::= { axsOadpNeighborEntry 28 }

-- axsFlow Group

    axsAccessFilterStatsL2InTable OBJECT-TYPE
        SYNTAX    SEQUENCE OF AxsAccessFilterStatsL2InEntry
        ACCESS    not-accessible
        STATUS    mandatory
        DESCRIPTION
                  "Table information on corresponding number of packets to flow detection condition 
                  and operation information set by access list."
        ::= { axsAccessFilterStats 3 }

    axsAccessFilterStatsL2InEntry OBJECT-TYPE
        SYNTAX    AxsAccessFilterStatsL2InEntry
        ACCESS    not-accessible
        STATUS    mandatory
        DESCRIPTION
                  "Entry concerning corresponding number of packets to flow detection condition and 
                  operation information set by access list."
        INDEX     { axsAccessFilterStatsL2InifIndex,
                    axsAccessFilterStatsL2InifIndexType,
                    axsAccessFilterStatsL2InListIndex,
                    axsAccessFilterStatsL2InSequenceNumber }
        ::= { axsAccessFilterStatsL2InTable 1 }

    AxsAccessFilterStatsL2InEntry ::= SEQUENCE {
        axsAccessFilterStatsL2InifIndex           INTEGER,
        axsAccessFilterStatsL2InifIndexType       INTEGER,
        axsAccessFilterStatsL2InListIndex         Unsigned32,
        axsAccessFilterStatsL2InSequenceNumber    Unsigned32,
        axsAccessFilterStatsL2InListName          DisplayString,
        axsAccessFilterStatsL2InMatchedPackets    Counter64
    }

    axsAccessFilterStatsL2InifIndex OBJECT-TYPE
        SYNTAX    INTEGER
        ACCESS    not-accessible
        STATUS    mandatory
        DESCRIPTION
                  "Index value in which entry of this table is identified."
        ::= { axsAccessFilterStatsL2InEntry 1 }

    axsAccessFilterStatsL2InifIndexType OBJECT-TYPE
        SYNTAX    INTEGER
        ACCESS    not-accessible
        STATUS    mandatory
        DESCRIPTION
                  "Indicates interface type. Physical port number : 1 Interface name : 2"
        ::= { axsAccessFilterStatsL2InEntry 2 }

    axsAccessFilterStatsL2InListIndex OBJECT-TYPE
        SYNTAX    Unsigned32
        ACCESS    not-accessible
        STATUS    mandatory
        DESCRIPTION
                  "Index value of access list that identifies entry of this table."
        ::= { axsAccessFilterStatsL2InEntry 3 }

    axsAccessFilterStatsL2InSequenceNumber OBJECT-TYPE
        SYNTAX    Unsigned32
        ACCESS    not-accessible
        STATUS    mandatory
        DESCRIPTION
                  "Sequence number of flow detection condition and operation information set to access list 
                  number or access list name."
        ::= { axsAccessFilterStatsL2InEntry 4 }

    axsAccessFilterStatsL2InListName OBJECT-TYPE
        SYNTAX    DisplayString
        ACCESS    read-only
        STATUS    mandatory
        DESCRIPTION
                  "Access list number or access list name corresponding to index of access list."
        ::= { axsAccessFilterStatsL2InEntry 5 }

    axsAccessFilterStatsL2InMatchedPackets OBJECT-TYPE
        SYNTAX    Counter64
        ACCESS    read-only
        STATUS    mandatory
        DESCRIPTION
                  "Corresponding number of packets to flow detection condition of access list. "
        ::= { axsAccessFilterStatsL2InEntry 6 }

    axsAccessFilterStatsL2OutTable OBJECT-TYPE
        SYNTAX    SEQUENCE OF AxsAccessFilterStatsL2OutEntry
        ACCESS    not-accessible
        STATUS    mandatory
        DESCRIPTION
                  "Table information on corresponding number of packets to flow detection condition 
                  and operation information set by access list."
        ::= { axsAccessFilterStats 4 }

    axsAccessFilterStatsL2OutEntry OBJECT-TYPE
        SYNTAX    AxsAccessFilterStatsL2OutEntry
        ACCESS    not-accessible
        STATUS    mandatory
        DESCRIPTION
                  "Entry concerning corresponding number of packets to flow detection condition and 
                  operation information set by access list."
        INDEX     { axsAccessFilterStatsL2OutifIndex,
                    axsAccessFilterStatsL2OutifIndexType,
                    axsAccessFilterStatsL2OutListIndex,
                    axsAccessFilterStatsL2OutSequenceNumber }
        ::= { axsAccessFilterStatsL2OutTable 1 }

    AxsAccessFilterStatsL2OutEntry ::= SEQUENCE {
        axsAccessFilterStatsL2OutifIndex           INTEGER,
        axsAccessFilterStatsL2OutifIndexType       INTEGER,
        axsAccessFilterStatsL2OutListIndex         Unsigned32,
        axsAccessFilterStatsL2OutSequenceNumber    Unsigned32,
        axsAccessFilterStatsL2OutListName          DisplayString,
        axsAccessFilterStatsL2OutMatchedPackets    Counter64
    }

    axsAccessFilterStatsL2OutifIndex OBJECT-TYPE
        SYNTAX    INTEGER
        ACCESS    not-accessible
        STATUS    mandatory
        DESCRIPTION
                  "Index value in which entry of this table is identified."
        ::= { axsAccessFilterStatsL2OutEntry 1 }

    axsAccessFilterStatsL2OutifIndexType OBJECT-TYPE
        SYNTAX    INTEGER
        ACCESS    not-accessible
        STATUS    mandatory
        DESCRIPTION
                  "Indicates interface type. Physical port number : 1 Interface name : 2"
        ::= { axsAccessFilterStatsL2OutEntry 2 }

    axsAccessFilterStatsL2OutListIndex OBJECT-TYPE
        SYNTAX    Unsigned32
        ACCESS    not-accessible
        STATUS    mandatory
        DESCRIPTION
                  "Index value of access list that identifies entry of this table."
        ::= { axsAccessFilterStatsL2OutEntry 3 }

    axsAccessFilterStatsL2OutSequenceNumber OBJECT-TYPE
        SYNTAX    Unsigned32
        ACCESS    not-accessible
        STATUS    mandatory
        DESCRIPTION
                  "Sequence number of flow detection condition and operation information set to access list 
                  number or access list name."
        ::= { axsAccessFilterStatsL2OutEntry 4 }

    axsAccessFilterStatsL2OutListName OBJECT-TYPE
        SYNTAX    DisplayString
        ACCESS    read-only
        STATUS    mandatory
        DESCRIPTION
                  "Access list number or access list name corresponding to index of access list."
        ::= { axsAccessFilterStatsL2OutEntry 5 }

    axsAccessFilterStatsL2OutMatchedPackets OBJECT-TYPE
        SYNTAX    Counter64
        ACCESS    read-only
        STATUS    mandatory
        DESCRIPTION
                  "Corresponding number of packets to flow detection condition of access list."
        ::= { axsAccessFilterStatsL2OutEntry 6 }

    axsAccessFilterStatsL3InTable OBJECT-TYPE
        SYNTAX    SEQUENCE OF AxsAccessFilterStatsL3InEntry
        ACCESS    not-accessible
        STATUS    mandatory
        DESCRIPTION
                  "Table information on corresponding number of packets to flow detection condition 
                  and operation information set by access list."
        ::= { axsAccessFilterStats 5 }

    axsAccessFilterStatsL3InEntry OBJECT-TYPE
        SYNTAX    AxsAccessFilterStatsL3InEntry
        ACCESS    not-accessible
        STATUS    mandatory
        DESCRIPTION
                  "Entry concerning corresponding number of packets to flow detection condition and 
                  operation information set by access list."
        INDEX     { axsAccessFilterStatsL3InifIndex,
                    axsAccessFilterStatsL3InifIndexType,
                    axsAccessFilterStatsL3InListIndex,
                    axsAccessFilterStatsL3InSequenceNumber }
        ::= { axsAccessFilterStatsL3InTable 1 }

    AxsAccessFilterStatsL3InEntry ::= SEQUENCE {
        axsAccessFilterStatsL3InifIndex           INTEGER,
        axsAccessFilterStatsL3InifIndexType       INTEGER,
        axsAccessFilterStatsL3InListIndex         Unsigned32,
        axsAccessFilterStatsL3InSequenceNumber    Unsigned32,
        axsAccessFilterStatsL3InListName          DisplayString,
        axsAccessFilterStatsL3InMatchedPackets    Counter64
    }

    axsAccessFilterStatsL3InifIndex OBJECT-TYPE
        SYNTAX    INTEGER
        ACCESS    not-accessible
        STATUS    mandatory
        DESCRIPTION
                  "Index value in which entry of this table is identified."
        ::= { axsAccessFilterStatsL3InEntry 1 }

    axsAccessFilterStatsL3InifIndexType OBJECT-TYPE
        SYNTAX    INTEGER
        ACCESS    not-accessible
        STATUS    mandatory
        DESCRIPTION
                  "Indicates interface type. Physical port number : 1 Interface name : 2"
        ::= { axsAccessFilterStatsL3InEntry 2 }

    axsAccessFilterStatsL3InListIndex OBJECT-TYPE
        SYNTAX    Unsigned32
        ACCESS    not-accessible
        STATUS    mandatory
        DESCRIPTION
                  "Index value of access list that identifies entry of this table."
        ::= { axsAccessFilterStatsL3InEntry 3 }

    axsAccessFilterStatsL3InSequenceNumber OBJECT-TYPE
        SYNTAX    Unsigned32
        ACCESS    not-accessible
        STATUS    mandatory
        DESCRIPTION
                  "Sequence number of flow detection condition and operation information set to access list 
                  number or access list name."
        ::= { axsAccessFilterStatsL3InEntry 4 }

    axsAccessFilterStatsL3InListName OBJECT-TYPE
        SYNTAX    DisplayString
        ACCESS    read-only
        STATUS    mandatory
        DESCRIPTION
                  "Access list number or access list name corresponding to index of access list."
        ::= { axsAccessFilterStatsL3InEntry 5 }

    axsAccessFilterStatsL3InMatchedPackets OBJECT-TYPE
        SYNTAX    Counter64
        ACCESS    read-only
        STATUS    mandatory
        DESCRIPTION
                  "Corresponding number of packets to flow detection condition of access list. "
        ::= { axsAccessFilterStatsL3InEntry 6 }

    axsAccessFilterStatsL3OutTable OBJECT-TYPE
        SYNTAX    SEQUENCE OF AxsAccessFilterStatsL3OutEntry
        ACCESS    not-accessible
        STATUS    mandatory
        DESCRIPTION
                  "Table information on corresponding number of packets to flow detection condition 
                  and operation information set by access list."
        ::= { axsAccessFilterStats 6 }

    axsAccessFilterStatsL3OutEntry OBJECT-TYPE
        SYNTAX    AxsAccessFilterStatsL3OutEntry
        ACCESS    not-accessible
        STATUS    mandatory
        DESCRIPTION
                  "Entry concerning corresponding number of packets to flow detection condition and 
                  operation information set by access list."
        INDEX     { axsAccessFilterStatsL3OutifIndex,
                    axsAccessFilterStatsL3OutifIndexType,
                    axsAccessFilterStatsL3OutListIndex,
                    axsAccessFilterStatsL3OutSequenceNumber }
        ::= { axsAccessFilterStatsL3OutTable 1 }

    AxsAccessFilterStatsL3OutEntry ::= SEQUENCE {
        axsAccessFilterStatsL3OutifIndex           INTEGER,
        axsAccessFilterStatsL3OutifIndexType       INTEGER,
        axsAccessFilterStatsL3OutListIndex         Unsigned32,
        axsAccessFilterStatsL3OutSequenceNumber    Unsigned32,
        axsAccessFilterStatsL3OutListName          DisplayString,
        axsAccessFilterStatsL3OutMatchedPackets    Counter64
    }

    axsAccessFilterStatsL3OutifIndex OBJECT-TYPE
        SYNTAX    INTEGER
        ACCESS    not-accessible
        STATUS    mandatory
        DESCRIPTION
                  "Index value in which entry of this table is identified."
        ::= { axsAccessFilterStatsL3OutEntry 1 }

    axsAccessFilterStatsL3OutifIndexType OBJECT-TYPE
        SYNTAX    INTEGER
        ACCESS    not-accessible
        STATUS    mandatory
        DESCRIPTION
                  "Indicates interface type. Physical port number : 1 Interface name : 2"
        ::= { axsAccessFilterStatsL3OutEntry 2 }

    axsAccessFilterStatsL3OutListIndex OBJECT-TYPE
        SYNTAX    Unsigned32
        ACCESS    not-accessible
        STATUS    mandatory
        DESCRIPTION
                  "Index value of access list that identifies entry of this table."
        ::= { axsAccessFilterStatsL3OutEntry 3 }

    axsAccessFilterStatsL3OutSequenceNumber OBJECT-TYPE
        SYNTAX    Unsigned32
        ACCESS    not-accessible
        STATUS    mandatory
        DESCRIPTION
                  "Sequence number of flow detection condition and operation information set to access list 
                  number or access list name."
        ::= { axsAccessFilterStatsL3OutEntry 4 }

    axsAccessFilterStatsL3OutListName OBJECT-TYPE
        SYNTAX    DisplayString
        ACCESS    read-only
        STATUS    mandatory
        DESCRIPTION
                  "Access list number or access list name corresponding to index of access list."
        ::= { axsAccessFilterStatsL3OutEntry 5 }

    axsAccessFilterStatsL3OutMatchedPackets OBJECT-TYPE
        SYNTAX    Counter64
        ACCESS    read-only
        STATUS    mandatory
        DESCRIPTION
                  "Corresponding number of packets to flow detection condition of access list. "
        ::= { axsAccessFilterStatsL3OutEntry 6 }
            
    axsAccessFilterStatsL2L3InTable OBJECT-TYPE
        SYNTAX    SEQUENCE OF AxsAccessFilterStatsL2L3InEntry
        ACCESS    not-accessible
        STATUS    mandatory
        DESCRIPTION
                  "Table information on corresponding number of packets to flow detection condition 
                  and operation information set by access list."
        ::= { axsAccessFilterStats 7 }

    axsAccessFilterStatsL2L3InEntry OBJECT-TYPE
        SYNTAX    AxsAccessFilterStatsL2L3InEntry
        ACCESS    not-accessible
        STATUS    mandatory
        DESCRIPTION
                  "Entry concerning corresponding number of packets to flow detection condition and 
                  operation information set by access list."
        INDEX     { axsAccessFilterStatsL2L3InifIndex,
                    axsAccessFilterStatsL2L3InifIndexType,
                    axsAccessFilterStatsL2L3InListIndex,
                    axsAccessFilterStatsL2L3InSequenceNumber }
        ::= { axsAccessFilterStatsL2L3InTable 1 }

    AxsAccessFilterStatsL2L3InEntry ::= SEQUENCE {
        axsAccessFilterStatsL2L3InifIndex           INTEGER,
        axsAccessFilterStatsL2L3InifIndexType       INTEGER,
        axsAccessFilterStatsL2L3InListIndex         Unsigned32,
        axsAccessFilterStatsL2L3InSequenceNumber    Unsigned32,
        axsAccessFilterStatsL2L3InListName          DisplayString,
        axsAccessFilterStatsL2L3InMatchedPackets    Counter64
    }

    axsAccessFilterStatsL2L3InifIndex OBJECT-TYPE
        SYNTAX    INTEGER
        ACCESS    not-accessible
        STATUS    mandatory
        DESCRIPTION
                  "Index value in which entry of this table is identified."
        ::= { axsAccessFilterStatsL2L3InEntry 1 }

    axsAccessFilterStatsL2L3InifIndexType OBJECT-TYPE
        SYNTAX    INTEGER
        ACCESS    not-accessible
        STATUS    mandatory
        DESCRIPTION
                  "Indicates interface type. Physical port number : 1 Interface name : 2"
        ::= { axsAccessFilterStatsL2L3InEntry 2 }

    axsAccessFilterStatsL2L3InListIndex OBJECT-TYPE
        SYNTAX    Unsigned32
        ACCESS    not-accessible
        STATUS    mandatory
        DESCRIPTION
                  "Index value of access list that identifies entry of this table."
        ::= { axsAccessFilterStatsL2L3InEntry 3 }

    axsAccessFilterStatsL2L3InSequenceNumber OBJECT-TYPE
        SYNTAX    Unsigned32
        ACCESS    not-accessible
        STATUS    mandatory
        DESCRIPTION
                  "Sequence number of flow detection condition and operation information set to access list 
                  number or access list name."
        ::= { axsAccessFilterStatsL2L3InEntry 4 }

    axsAccessFilterStatsL2L3InListName OBJECT-TYPE
        SYNTAX    DisplayString
        ACCESS    read-only
        STATUS    mandatory
        DESCRIPTION
                  "Access list number or access list name corresponding to index of access list."
        ::= { axsAccessFilterStatsL2L3InEntry 5 }

    axsAccessFilterStatsL2L3InMatchedPackets OBJECT-TYPE
        SYNTAX    Counter64
        ACCESS    read-only
        STATUS    mandatory
        DESCRIPTION
                  "Corresponding number of packets to flow detection condition of access list. "
        ::= { axsAccessFilterStatsL2L3InEntry 6 }

    axsAccessFilterStatsL2L3OutTable OBJECT-TYPE
        SYNTAX    SEQUENCE OF AxsAccessFilterStatsL2L3OutEntry
        ACCESS    not-accessible
        STATUS    mandatory
        DESCRIPTION
                  "Table information on corresponding number of packets to flow detection condition 
                  and operation information set by access list."
        ::= { axsAccessFilterStats 8 }

    axsAccessFilterStatsL2L3OutEntry OBJECT-TYPE
        SYNTAX    AxsAccessFilterStatsL2L3OutEntry
        ACCESS    not-accessible
        STATUS    mandatory
        DESCRIPTION
                  "Entry concerning corresponding number of packets to flow detection condition and 
                  operation information set by access list."
        INDEX     { axsAccessFilterStatsL2L3OutifIndex,
                    axsAccessFilterStatsL2L3OutifIndexType,
                    axsAccessFilterStatsL2L3OutListIndex,
                    axsAccessFilterStatsL2L3OutSequenceNumber }
        ::= { axsAccessFilterStatsL2L3OutTable 1 }

    AxsAccessFilterStatsL2L3OutEntry ::= SEQUENCE {
        axsAccessFilterStatsL2L3OutifIndex           INTEGER,
        axsAccessFilterStatsL2L3OutifIndexType       INTEGER,
        axsAccessFilterStatsL2L3OutListIndex         Unsigned32,
        axsAccessFilterStatsL2L3OutSequenceNumber    Unsigned32,
        axsAccessFilterStatsL2L3OutListName          DisplayString,
        axsAccessFilterStatsL2L3OutMatchedPackets    Counter64
    }

    axsAccessFilterStatsL2L3OutifIndex OBJECT-TYPE
        SYNTAX    INTEGER
        ACCESS    not-accessible
        STATUS    mandatory
        DESCRIPTION
                  "Index value in which entry of this table is identified."
        ::= { axsAccessFilterStatsL2L3OutEntry 1 }

    axsAccessFilterStatsL2L3OutifIndexType OBJECT-TYPE
        SYNTAX    INTEGER
        ACCESS    not-accessible
        STATUS    mandatory
        DESCRIPTION
                  "Indicates interface type. Physical port number : 1 Interface name : 2"
        ::= { axsAccessFilterStatsL2L3OutEntry 2 }

    axsAccessFilterStatsL2L3OutListIndex OBJECT-TYPE
        SYNTAX    Unsigned32
        ACCESS    not-accessible
        STATUS    mandatory
        DESCRIPTION
                  "Index value of access list that identifies entry of this table."
        ::= { axsAccessFilterStatsL2L3OutEntry 3 }

    axsAccessFilterStatsL2L3OutSequenceNumber OBJECT-TYPE
        SYNTAX    Unsigned32
        ACCESS    not-accessible
        STATUS    mandatory
        DESCRIPTION
                  "Sequence number of flow detection condition and operation information set to access list 
                  number or access list name."
        ::= { axsAccessFilterStatsL2L3OutEntry 4 }

    axsAccessFilterStatsL2L3OutListName OBJECT-TYPE
        SYNTAX    DisplayString
        ACCESS    read-only
        STATUS    mandatory
        DESCRIPTION
                  "Access list number or access list name corresponding to index of access list."
        ::= { axsAccessFilterStatsL2L3OutEntry 5 }

    axsAccessFilterStatsL2L3OutMatchedPackets OBJECT-TYPE
        SYNTAX    Counter64
        ACCESS    read-only
        STATUS    mandatory
        DESCRIPTION
                  "Corresponding number of packets to flow detection condition of access list."
        ::= { axsAccessFilterStatsL2L3OutEntry 6 }

    axsQosFlowStatsL2InTable OBJECT-TYPE
        SYNTAX    SEQUENCE OF AxsQosFlowStatsL2InEntry
        ACCESS    not-accessible
        STATUS    mandatory
        DESCRIPTION
                  "Table information on corresponding number of packets to QoS flow detection condition
                  and operation information set in QoS flow list."
        ::= { axsQosFlowStats 3 }

    axsQosFlowStatsL2InEntry OBJECT-TYPE
        SYNTAX    AxsQosFlowStatsL2InEntry
        ACCESS    not-accessible
        STATUS    mandatory
        DESCRIPTION
                  "Entry concerning corresponding number of packets to QoS flow detection condition
                  and operation information set in QoS Flower shop."
        INDEX     { axsQosFlowStatsL2InifIndex,
                    axsQosFlowStatsL2InifIndexType,
                    axsQosFlowStatsL2InListIndex,
                    axsQosFlowStatsL2InSequenceNumber }
        ::= { axsQosFlowStatsL2InTable 1 }

    AxsQosFlowStatsL2InEntry ::= SEQUENCE {
        axsQosFlowStatsL2InifIndex                     INTEGER,
        axsQosFlowStatsL2InifIndexType                 INTEGER,
        axsQosFlowStatsL2InListIndex                   Unsigned32,
        axsQosFlowStatsL2InSequenceNumber              Unsigned32,
        axsQosFlowStatsL2InListName                    DisplayString,
        axsQosFlowStatsL2InMatchedPackets              Counter64,
        axsQosFlowStatsL2InMatchedPacketsMinUnder      Counter64,
        axsQosFlowStatsL2InMatchedPacketsMinOver       Counter64,
        axsQosFlowStatsL2InMatchedPacketsMaxUnder      Counter64,
        axsQosFlowStatsL2InMatchedPacketsMaxOver       Counter64,
        axsQosFlowStatsL2InMatchedBytesMinUnder        Counter64,
        axsQosFlowStatsL2InMatchedBytesMinOver         Counter64,
        axsQosFlowStatsL2InMatchedBytesMaxUnder        Counter64,
        axsQosFlowStatsL2InMatchedBytesMaxOver         Counter64,
        axsQosFlowStatsL2InPremMatchedPacketsMinUnder  Counter64,
        axsQosFlowStatsL2InPremMatchedPacketsMinOver   Counter64,
        axsQosFlowStatsL2InPremMatchedPacketsMaxUnder  Counter64,
        axsQosFlowStatsL2InPremMatchedPacketsMaxOver   Counter64,
        axsQosFlowStatsL2InPremMatchedBytesMinUnder    Counter64,
        axsQosFlowStatsL2InPremMatchedBytesMinOver     Counter64,
        axsQosFlowStatsL2InPremMatchedBytesMaxUnder    Counter64,
        axsQosFlowStatsL2InPremMatchedBytesMaxOver     Counter64
    }

    axsQosFlowStatsL2InifIndex OBJECT-TYPE
        SYNTAX    INTEGER
        ACCESS    not-accessible
        STATUS    mandatory
        DESCRIPTION
                  "Index value in which entry of this table is identified."
        ::= { axsQosFlowStatsL2InEntry 1 }

    axsQosFlowStatsL2InifIndexType OBJECT-TYPE
        SYNTAX    INTEGER
        ACCESS    not-accessible
        STATUS    mandatory
        DESCRIPTION
                  "Indicates interface type. Physical port number : 1 Interface name : 2"
        ::= { axsQosFlowStatsL2InEntry 2 }

    axsQosFlowStatsL2InListIndex OBJECT-TYPE
        SYNTAX    Unsigned32
        ACCESS    not-accessible
        STATUS    mandatory
        DESCRIPTION
                  "Index value of QoS Flow list where entry of this table is identified."
        ::= { axsQosFlowStatsL2InEntry 3 }

    axsQosFlowStatsL2InSequenceNumber OBJECT-TYPE
        SYNTAX    Unsigned32
        ACCESS    not-accessible
        STATUS    mandatory
        DESCRIPTION
                  "Sequence number of flow detection condition and operation information set to QoS 
                  flow list name."
        ::= { axsQosFlowStatsL2InEntry 4 }

    axsQosFlowStatsL2InListName OBJECT-TYPE
        SYNTAX    DisplayString
        ACCESS    read-only
        STATUS    mandatory
        DESCRIPTION
                  "QoS flow list name corresponding to index of QoS flow list."
        ::= { axsQosFlowStatsL2InEntry 5 }

    axsQosFlowStatsL2InMatchedPackets OBJECT-TYPE
        SYNTAX    Counter64
        ACCESS    read-only
        STATUS    mandatory
        DESCRIPTION
                  "Corresponding number of packets to flow detection condition of QoS flow list."
        ::= { axsQosFlowStatsL2InEntry 6 }

    axsQosFlowStatsL2InMatchedPacketsMinUnder OBJECT-TYPE
        SYNTAX    Counter64
        ACCESS    read-only
        STATUS    mandatory
        DESCRIPTION
                  "Number of packets that obey the minimum bandwidth constraint in the flow 
                  detection condition."
        ::= { axsQosFlowStatsL2InEntry 7 }

    axsQosFlowStatsL2InMatchedPacketsMinOver OBJECT-TYPE
        SYNTAX    Counter64
        ACCESS    read-only
        STATUS    mandatory
        DESCRIPTION
                  "Number of packets that disobey the minimum bandwidth constraint in the flow 
                  detection condition."
        ::= { axsQosFlowStatsL2InEntry 8 }

    axsQosFlowStatsL2InMatchedPacketsMaxUnder OBJECT-TYPE
        SYNTAX    Counter64
        ACCESS    read-only
        STATUS    mandatory
        DESCRIPTION
                  "Number of packets that obey the maximum bandwidth constraint in the flow 
                  detection condition."
        ::= { axsQosFlowStatsL2InEntry 9 }

    axsQosFlowStatsL2InMatchedPacketsMaxOver OBJECT-TYPE
        SYNTAX    Counter64 
        ACCESS    read-only
        STATUS    mandatory
        DESCRIPTION
                  "Number of packets that disobey the maximum bandwidth constraint in the flow 
                  detection condition."
        ::= { axsQosFlowStatsL2InEntry 10 }

    axsQosFlowStatsL2InMatchedBytesMinUnder OBJECT-TYPE
        SYNTAX    Counter64
        ACCESS    read-only
        STATUS    mandatory
        DESCRIPTION
                  "Number of bytes that obey the minimum bandwidth constraint in the flow 
                  detection condition."
        ::= { axsQosFlowStatsL2InEntry 11 }

    axsQosFlowStatsL2InMatchedBytesMinOver OBJECT-TYPE
        SYNTAX    Counter64
        ACCESS    read-only
        STATUS    mandatory
        DESCRIPTION
                  "Number of bytes that disobey the minimum bandwidth constraint in the flow 
                  detection condition."
        ::= { axsQosFlowStatsL2InEntry 12 }

    axsQosFlowStatsL2InMatchedBytesMaxUnder OBJECT-TYPE
        SYNTAX    Counter64
        ACCESS    read-only
        STATUS    mandatory
        DESCRIPTION
                  "Number of bytes that obey the maximum bandwidth constraint in the flow 
                  detection condition."
        ::= { axsQosFlowStatsL2InEntry 13 }

    axsQosFlowStatsL2InMatchedBytesMaxOver OBJECT-TYPE
        SYNTAX    Counter64
        ACCESS    read-only
        STATUS    mandatory
        DESCRIPTION
                  "Number of bytes that disobey the maximum bandwidth constraint in the flow 
                  detection condition."
        ::= { axsQosFlowStatsL2InEntry 14 }

    axsQosFlowStatsL2InPremMatchedPacketsMinUnder OBJECT-TYPE
        SYNTAX    Counter64
        ACCESS    read-only
        STATUS    mandatory
        DESCRIPTION
                  "Number of packets that obey the minimum bandwidth constraint in the premium flow 
                  detection condition."
        ::= { axsQosFlowStatsL2InEntry 15 }

    axsQosFlowStatsL2InPremMatchedPacketsMinOver OBJECT-TYPE
        SYNTAX    Counter64
        ACCESS    read-only
        STATUS    mandatory
        DESCRIPTION
                  "Number of packets that disobey the minimum bandwidth constraint in the premium flow 
                  detection condition."
        ::= { axsQosFlowStatsL2InEntry 16 }

    axsQosFlowStatsL2InPremMatchedPacketsMaxUnder OBJECT-TYPE
        SYNTAX    Counter64
        ACCESS    read-only
        STATUS    mandatory
        DESCRIPTION
                  "Number of packets that obey the maximum bandwidth constraint in the premium flow 
                  detection condition."
        ::= { axsQosFlowStatsL2InEntry 17 }

    axsQosFlowStatsL2InPremMatchedPacketsMaxOver OBJECT-TYPE
        SYNTAX    Counter64
        ACCESS    read-only
        STATUS    mandatory
        DESCRIPTION
                  "Number of packets that disobey the maximum bandwidth constraint in the premium flow 
                  detection condition."
        ::= { axsQosFlowStatsL2InEntry 18 }

    axsQosFlowStatsL2InPremMatchedBytesMinUnder OBJECT-TYPE
        SYNTAX    Counter64
        ACCESS    read-only
        STATUS    mandatory
        DESCRIPTION
                  "Number of bytes that obey the minimum bandwidth constraint in the premium flow 
                  detection condition."
        ::= { axsQosFlowStatsL2InEntry 19 }

    axsQosFlowStatsL2InPremMatchedBytesMinOver OBJECT-TYPE
        SYNTAX    Counter64
        ACCESS    read-only
        STATUS    mandatory
        DESCRIPTION
                  "Number of bytes that disobey the minimum bandwidth constraint in the premium flow 
                  detection condition."
        ::= { axsQosFlowStatsL2InEntry 20 }

    axsQosFlowStatsL2InPremMatchedBytesMaxUnder OBJECT-TYPE
        SYNTAX    Counter64
        ACCESS    read-only
        STATUS    mandatory
        DESCRIPTION
                  "Number of bytes that obey the maximum bandwidth constraint in the premium flow 
                  detection condition."
        ::= { axsQosFlowStatsL2InEntry 21 }

    axsQosFlowStatsL2InPremMatchedBytesMaxOver OBJECT-TYPE
        SYNTAX    Counter64
        ACCESS    read-only
        STATUS    mandatory
        DESCRIPTION
                  "Number of bytes that disobey the maximum bandwidth constraint in the premium flow 
                  detection condition."
        ::= { axsQosFlowStatsL2InEntry 22 }

    axsQosFlowStatsL2OutTable OBJECT-TYPE
        SYNTAX    SEQUENCE OF AxsQosFlowStatsL2OutEntry
        ACCESS    not-accessible
        STATUS    mandatory
        DESCRIPTION
                  "Table information on corresponding number of packets to QoS flow detection condition
                  and operation information set in QoS flow list."
        ::= { axsQosFlowStats 4 }

    axsQosFlowStatsL2OutEntry OBJECT-TYPE
        SYNTAX    AxsQosFlowStatsL2OutEntry
        ACCESS    not-accessible
        STATUS    mandatory
        DESCRIPTION
                  "Entry concerning corresponding number of packets to QoS flow detection condition
                  and operation information set in QoS Flower shop."
        INDEX     { axsQosFlowStatsL2OutifIndex,
                    axsQosFlowStatsL2OutifIndexType,
                    axsQosFlowStatsL2OutListIndex,
                    axsQosFlowStatsL2OutSequenceNumber }
        ::= { axsQosFlowStatsL2OutTable 1 }

    AxsQosFlowStatsL2OutEntry ::= SEQUENCE {
        axsQosFlowStatsL2OutifIndex                       INTEGER,
        axsQosFlowStatsL2OutifIndexType                   INTEGER,
        axsQosFlowStatsL2OutListIndex                     Unsigned32,
        axsQosFlowStatsL2OutSequenceNumber                Unsigned32,
        axsQosFlowStatsL2OutListName                      DisplayString,
        axsQosFlowStatsL2OutMatchedPackets                Counter64,
        axsQosFlowStatsL2OutMatchedPacketsMinUnder        Counter64,
        axsQosFlowStatsL2OutMatchedPacketsMinOver         Counter64,
        axsQosFlowStatsL2OutMatchedPacketsMaxUnder        Counter64,
        axsQosFlowStatsL2OutMatchedPacketsMaxOver         Counter64,
        axsQosFlowStatsL2OutMatchedBytesMinUnder          Counter64,
        axsQosFlowStatsL2OutMatchedBytesMinOver           Counter64,
        axsQosFlowStatsL2OutMatchedBytesMaxUnder          Counter64,
        axsQosFlowStatsL2OutMatchedBytesMaxOver           Counter64,
        axsQosFlowStatsL2OutPremMatchedPacketsMinUnder    Counter64,
        axsQosFlowStatsL2OutPremMatchedPacketsMinOver     Counter64,
        axsQosFlowStatsL2OutPremMatchedPacketsMaxUnder    Counter64,
        axsQosFlowStatsL2OutPremMatchedPacketsMaxOver     Counter64,
        axsQosFlowStatsL2OutPremMatchedBytesMinUnder      Counter64,
        axsQosFlowStatsL2OutPremMatchedBytesMinOver       Counter64,
        axsQosFlowStatsL2OutPremMatchedBytesMaxUnder      Counter64,
        axsQosFlowStatsL2OutPremMatchedBytesMaxOver       Counter64
    }

    axsQosFlowStatsL2OutifIndex OBJECT-TYPE
        SYNTAX    INTEGER
        ACCESS    not-accessible
        STATUS    mandatory
        DESCRIPTION
                  "Index value in which entry of this table is identified."
        ::= { axsQosFlowStatsL2OutEntry 1 }

    axsQosFlowStatsL2OutifIndexType OBJECT-TYPE
        SYNTAX    INTEGER
        ACCESS    not-accessible
        STATUS    mandatory
        DESCRIPTION
                  "Indicates interface type. Physical port number : 1 Interface name : 2"
        ::= { axsQosFlowStatsL2OutEntry 2 }

    axsQosFlowStatsL2OutListIndex OBJECT-TYPE
        SYNTAX    Unsigned32
        ACCESS    not-accessible
        STATUS    mandatory
        DESCRIPTION
                  "Index value of QoS Flow list where entry of this table is identified."
        ::= { axsQosFlowStatsL2OutEntry 3 }

    axsQosFlowStatsL2OutSequenceNumber OBJECT-TYPE
        SYNTAX    Unsigned32
        ACCESS    not-accessible
        STATUS    mandatory
        DESCRIPTION
                  "Sequence number of flow detection condition and operation information set to QoS 
                  flow list name."
        ::= { axsQosFlowStatsL2OutEntry 4 }

    axsQosFlowStatsL2OutListName OBJECT-TYPE
        SYNTAX    DisplayString
        ACCESS    read-only
        STATUS    mandatory
        DESCRIPTION
                  "QoS flow list name corresponding to index of QoS flow list."
        ::= { axsQosFlowStatsL2OutEntry 5 }

    axsQosFlowStatsL2OutMatchedPackets OBJECT-TYPE
        SYNTAX    Counter64
        ACCESS    read-only
        STATUS    mandatory
        DESCRIPTION
                  "Corresponding number of packets to flow detection condition of QoS flow list."
        ::= { axsQosFlowStatsL2OutEntry 6 }

    axsQosFlowStatsL2OutMatchedPacketsMinUnder OBJECT-TYPE
        SYNTAX    Counter64
        ACCESS    read-only
        STATUS    mandatory
        DESCRIPTION
                  "Number of packets that obey the minimum bandwidth constraint in the flow 
                  detection condition"
        ::= { axsQosFlowStatsL2OutEntry 7 }

    axsQosFlowStatsL2OutMatchedPacketsMinOver OBJECT-TYPE
        SYNTAX    Counter64
        ACCESS    read-only
        STATUS    mandatory
        DESCRIPTION
                  "Number of packets that disobey the minimum bandwidth constraint in the flow 
                  detection condition."
        ::= { axsQosFlowStatsL2OutEntry 8 }

    axsQosFlowStatsL2OutMatchedPacketsMaxUnder OBJECT-TYPE
        SYNTAX    Counter64
        ACCESS    read-only
        STATUS    mandatory
        DESCRIPTION
                  "Number of packets that obey the maximum bandwidth constraint in the flow 
                  detection condition."
        ::= { axsQosFlowStatsL2OutEntry 9 }

    axsQosFlowStatsL2OutMatchedPacketsMaxOver OBJECT-TYPE
        SYNTAX    Counter64 
        ACCESS    read-only
        STATUS    mandatory
        DESCRIPTION
                  "Number of packets that disobey the maximum bandwidth constraint in the flow 
                  detection condition."
        ::= { axsQosFlowStatsL2OutEntry 10 }

    axsQosFlowStatsL2OutMatchedBytesMinUnder OBJECT-TYPE
        SYNTAX    Counter64 
        ACCESS    read-only
        STATUS    mandatory
        DESCRIPTION
                  "Number of bytes that obey the minimum bandwidth constraint in the flow 
                  detection condition."
        ::= { axsQosFlowStatsL2OutEntry 11 }

    axsQosFlowStatsL2OutMatchedBytesMinOver OBJECT-TYPE
        SYNTAX    Counter64 
        ACCESS    read-only
        STATUS    mandatory
        DESCRIPTION
                  "Number of bytes that disobey the minimum bandwidth constraint in the flow 
                  detection condition."
        ::= { axsQosFlowStatsL2OutEntry 12 }

    axsQosFlowStatsL2OutMatchedBytesMaxUnder OBJECT-TYPE
        SYNTAX    Counter64 
        ACCESS    read-only
        STATUS    mandatory
        DESCRIPTION
                  "Number of bytes that obey the maximum bandwidth constraint in the flow 
                  detection condition."
        ::= { axsQosFlowStatsL2OutEntry 13 }

    axsQosFlowStatsL2OutMatchedBytesMaxOver OBJECT-TYPE
        SYNTAX    Counter64 
        ACCESS    read-only
        STATUS    mandatory
        DESCRIPTION
                  "Number of bytes that disobey the maximum bandwidth constraint in the flow 
                  detection condition."
        ::= { axsQosFlowStatsL2OutEntry 14 }

    axsQosFlowStatsL2OutPremMatchedPacketsMinUnder OBJECT-TYPE
        SYNTAX    Counter64 
        ACCESS    read-only
        STATUS    mandatory
        DESCRIPTION
                  "Number of packets that obey the minimum bandwidth constraint in the premium flow 
                  detection condition."
        ::= { axsQosFlowStatsL2OutEntry 15 }

    axsQosFlowStatsL2OutPremMatchedPacketsMinOver OBJECT-TYPE
        SYNTAX    Counter64 
        ACCESS    read-only
        STATUS    mandatory
        DESCRIPTION
                  "Number of packets that disobey the minimum bandwidth constraint in the premium flow 
                  detection condition."
        ::= { axsQosFlowStatsL2OutEntry 16 }

    axsQosFlowStatsL2OutPremMatchedPacketsMaxUnder OBJECT-TYPE
        SYNTAX    Counter64 
        ACCESS    read-only
        STATUS    mandatory
        DESCRIPTION
                  "Number of packets that obey the maximum bandwidth constraint in the premium flow 
                  detection condition."
        ::= { axsQosFlowStatsL2OutEntry 17 }

    axsQosFlowStatsL2OutPremMatchedPacketsMaxOver OBJECT-TYPE
        SYNTAX    Counter64 
        ACCESS    read-only
        STATUS    mandatory
        DESCRIPTION
                  "Number of packets that disobey the maximum bandwidth constraint in the premium flow 
                  detection condition."
        ::= { axsQosFlowStatsL2OutEntry 18 }

    axsQosFlowStatsL2OutPremMatchedBytesMinUnder OBJECT-TYPE
        SYNTAX    Counter64 
        ACCESS    read-only
        STATUS    mandatory
        DESCRIPTION
                  "Number of bytes that obey the minimum bandwidth constraint in the premium flow 
                  detection condition."
        ::= { axsQosFlowStatsL2OutEntry 19 }

    axsQosFlowStatsL2OutPremMatchedBytesMinOver OBJECT-TYPE
        SYNTAX    Counter64 
        ACCESS    read-only
        STATUS    mandatory
        DESCRIPTION
                  "Number of bytes that disobey the minimum bandwidth constraint in the premium flow 
                  detection condition."
        ::= { axsQosFlowStatsL2OutEntry 20 }

    axsQosFlowStatsL2OutPremMatchedBytesMaxUnder OBJECT-TYPE
        SYNTAX    Counter64 
        ACCESS    read-only
        STATUS    mandatory
        DESCRIPTION
                  "Number of bytes that obey the maximum bandwidth constraint in the premium flow 
                  detection condition."
        ::= { axsQosFlowStatsL2OutEntry 21 }

    axsQosFlowStatsL2OutPremMatchedBytesMaxOver OBJECT-TYPE
        SYNTAX    Counter64 
        ACCESS    read-only
        STATUS    mandatory
        DESCRIPTION
                  "Number of bytes that disobey the maximum bandwidth constraint in the premium flow 
                  detection condition."
        ::= { axsQosFlowStatsL2OutEntry 22 }

    axsQosFlowStatsL3InTable OBJECT-TYPE
        SYNTAX    SEQUENCE OF AxsQosFlowStatsL3InEntry
        ACCESS    not-accessible
        STATUS    mandatory
        DESCRIPTION
                  "Table information on corresponding number of packets to QoS flow detection condition
                  and operation information set in QoS flow list."
        ::= { axsQosFlowStats 5 }

    axsQosFlowStatsL3InEntry OBJECT-TYPE
        SYNTAX    AxsQosFlowStatsL3InEntry
        ACCESS    not-accessible
        STATUS    mandatory
        DESCRIPTION
                  "Entry concerning corresponding number of packets to QoS flow detection condition
                  and operation information set in QoS Flower shop."
        INDEX     { axsQosFlowStatsL3InifIndex,
                    axsQosFlowStatsL3InifIndexType,
                    axsQosFlowStatsL3InListIndex,
                    axsQosFlowStatsL3InSequenceNumber }
        ::= { axsQosFlowStatsL3InTable 1 }

    AxsQosFlowStatsL3InEntry ::= SEQUENCE {
        axsQosFlowStatsL3InifIndex                       INTEGER,
        axsQosFlowStatsL3InifIndexType                   INTEGER,
        axsQosFlowStatsL3InListIndex                     Unsigned32,
        axsQosFlowStatsL3InSequenceNumber                Unsigned32,
        axsQosFlowStatsL3InListName                      DisplayString,
        axsQosFlowStatsL3InMatchedPackets                Counter64,
        axsQosFlowStatsL3InMatchedPacketsMinUnder        Counter64,
        axsQosFlowStatsL3InMatchedPacketsMinOver         Counter64,
        axsQosFlowStatsL3InMatchedPacketsMaxUnder        Counter64,
        axsQosFlowStatsL3InMatchedPacketsMaxOver         Counter64,
        axsQosFlowStatsL3InMatchedBytesMinUnder          Counter64,
        axsQosFlowStatsL3InMatchedBytesMinOver           Counter64,
        axsQosFlowStatsL3InMatchedBytesMaxUnder          Counter64,
        axsQosFlowStatsL3InMatchedBytesMaxOver           Counter64,
        axsQosFlowStatsL3InPremMatchedPacketsMinUnder    Counter64,
        axsQosFlowStatsL3InPremMatchedPacketsMinOver     Counter64,
        axsQosFlowStatsL3InPremMatchedPacketsMaxUnder    Counter64,
        axsQosFlowStatsL3InPremMatchedPacketsMaxOver     Counter64,
        axsQosFlowStatsL3InPremMatchedBytesMinUnder      Counter64,
        axsQosFlowStatsL3InPremMatchedBytesMinOver       Counter64,
        axsQosFlowStatsL3InPremMatchedBytesMaxUnder      Counter64,
        axsQosFlowStatsL3InPremMatchedBytesMaxOver       Counter64
    }

    axsQosFlowStatsL3InifIndex OBJECT-TYPE
        SYNTAX    INTEGER
        ACCESS    not-accessible
        STATUS    mandatory
        DESCRIPTION
                  "Index value in which entry of this table is identified."
        ::= { axsQosFlowStatsL3InEntry 1 }

    axsQosFlowStatsL3InifIndexType OBJECT-TYPE
        SYNTAX    INTEGER
        ACCESS    not-accessible
        STATUS    mandatory
        DESCRIPTION
                  "Indicates interface type. Physical port number : 1 Interface name : 2"
        ::= { axsQosFlowStatsL3InEntry 2 }

    axsQosFlowStatsL3InListIndex OBJECT-TYPE
        SYNTAX    Unsigned32
        ACCESS    not-accessible
        STATUS    mandatory
        DESCRIPTION
                  "Index value of QoS Flow list where entry of this table is identified."
        ::= { axsQosFlowStatsL3InEntry 3 }

    axsQosFlowStatsL3InSequenceNumber OBJECT-TYPE
        SYNTAX    Unsigned32
        ACCESS    not-accessible
        STATUS    mandatory
        DESCRIPTION
                  "Sequence number of flow detection condition and operation information set to QoS 
                  flow list name."
        ::= { axsQosFlowStatsL3InEntry 4 }

    axsQosFlowStatsL3InListName OBJECT-TYPE
        SYNTAX    DisplayString
        ACCESS    read-only
        STATUS    mandatory
        DESCRIPTION
                  "QoS flow list name corresponding to index of QoS flow list."
        ::= { axsQosFlowStatsL3InEntry 5 }

    axsQosFlowStatsL3InMatchedPackets OBJECT-TYPE
        SYNTAX    Counter64
        ACCESS    read-only
        STATUS    mandatory
        DESCRIPTION
                  "Corresponding number of packets to flow detection condition of QoS flow list."
        ::= { axsQosFlowStatsL3InEntry 6 }

    axsQosFlowStatsL3InMatchedPacketsMinUnder OBJECT-TYPE
        SYNTAX    Counter64
        ACCESS    read-only
        STATUS    mandatory
        DESCRIPTION
                  "Number of packets that obey the minimum bandwidth constraint in the flow 
                  detection condition."
        ::= { axsQosFlowStatsL3InEntry 7 }

    axsQosFlowStatsL3InMatchedPacketsMinOver OBJECT-TYPE
        SYNTAX    Counter64
        ACCESS    read-only
        STATUS    mandatory
        DESCRIPTION
                  "Number of packets that disobey the minimum bandwidth constraint in the flow 
                  detection condition."
        ::= { axsQosFlowStatsL3InEntry 8 }

    axsQosFlowStatsL3InMatchedPacketsMaxUnder OBJECT-TYPE
        SYNTAX    Counter64
        ACCESS    read-only
        STATUS    mandatory
        DESCRIPTION
                  "Number of packets that obey the maximum bandwidth constraint in the flow 
                  detection condition."
        ::= { axsQosFlowStatsL3InEntry 9 }

    axsQosFlowStatsL3InMatchedPacketsMaxOver OBJECT-TYPE
        SYNTAX    Counter64 
        ACCESS    read-only
        STATUS    mandatory
        DESCRIPTION
                  "Number of packets that disobey the maximum bandwidth constraint in the flow 
                  detection condition."
        ::= { axsQosFlowStatsL3InEntry 10 }

    axsQosFlowStatsL3InMatchedBytesMinUnder OBJECT-TYPE
        SYNTAX    Counter64 
        ACCESS    read-only
        STATUS    mandatory
        DESCRIPTION
                  "Number of bytes that obey the minimum bandwidth constraint in the flow 
                  detection condition."
        ::= { axsQosFlowStatsL3InEntry 11 }

    axsQosFlowStatsL3InMatchedBytesMinOver OBJECT-TYPE
        SYNTAX    Counter64 
        ACCESS    read-only
        STATUS    mandatory
        DESCRIPTION
                  "Number of bytes that disobey the minimum bandwidth constraint in the flow 
                  detection condition."
        ::= { axsQosFlowStatsL3InEntry 12 }

    axsQosFlowStatsL3InMatchedBytesMaxUnder OBJECT-TYPE
        SYNTAX    Counter64 
        ACCESS    read-only
        STATUS    mandatory
        DESCRIPTION
                  "Number of bytes that obey the maximum bandwidth constraint in the flow 
                  detection condition."
        ::= { axsQosFlowStatsL3InEntry 13 }

    axsQosFlowStatsL3InMatchedBytesMaxOver OBJECT-TYPE
        SYNTAX    Counter64 
        ACCESS    read-only
        STATUS    mandatory
        DESCRIPTION
                  "Number of bytes that disobey the maximum bandwidth constraint in the flow 
                  detection condition."
        ::= { axsQosFlowStatsL3InEntry 14 }

    axsQosFlowStatsL3InPremMatchedPacketsMinUnder OBJECT-TYPE
        SYNTAX    Counter64 
        ACCESS    read-only
        STATUS    mandatory
        DESCRIPTION
                  "Number of packets that obey the minimum bandwidth constraint in the premium flow 
                  detection condition."
        ::= { axsQosFlowStatsL3InEntry 15 }

    axsQosFlowStatsL3InPremMatchedPacketsMinOver OBJECT-TYPE
        SYNTAX    Counter64 
        ACCESS    read-only
        STATUS    mandatory
        DESCRIPTION
                  "Number of packets that disobey the minimum bandwidth constraint in the premium flow 
                  detection condition."
        ::= { axsQosFlowStatsL3InEntry 16 }

    axsQosFlowStatsL3InPremMatchedPacketsMaxUnder OBJECT-TYPE
        SYNTAX    Counter64 
        ACCESS    read-only
        STATUS    mandatory
        DESCRIPTION
                  "Number of packets that obey the maximum bandwidth constraint in the premium flow 
                  detection condition."
        ::= { axsQosFlowStatsL3InEntry 17 }

    axsQosFlowStatsL3InPremMatchedPacketsMaxOver OBJECT-TYPE
        SYNTAX    Counter64 
        ACCESS    read-only
        STATUS    mandatory
        DESCRIPTION
                  "Number of packets that disobey the maximum bandwidth constraint in the premium flow 
                  detection condition."
        ::= { axsQosFlowStatsL3InEntry 18 }

    axsQosFlowStatsL3InPremMatchedBytesMinUnder OBJECT-TYPE
        SYNTAX    Counter64 
        ACCESS    read-only
        STATUS    mandatory
        DESCRIPTION
                  "Number of bytes that obey the minimum bandwidth constraint in the premium flow 
                  detection condition."
        ::= { axsQosFlowStatsL3InEntry 19 }

    axsQosFlowStatsL3InPremMatchedBytesMinOver OBJECT-TYPE
        SYNTAX    Counter64 
        ACCESS    read-only
        STATUS    mandatory
        DESCRIPTION
                  "Number of bytes that disobey the minimum bandwidth constraint in the premium flow 
                  detection condition."
        ::= { axsQosFlowStatsL3InEntry 20 }

    axsQosFlowStatsL3InPremMatchedBytesMaxUnder OBJECT-TYPE
        SYNTAX    Counter64 
        ACCESS    read-only
        STATUS    mandatory
        DESCRIPTION
                  "Number of bytes that obey the maximum bandwidth constraint in the premium flow 
                  detection condition."
        ::= { axsQosFlowStatsL3InEntry 21 }

    axsQosFlowStatsL3InPremMatchedBytesMaxOver OBJECT-TYPE
        SYNTAX    Counter64 
        ACCESS    read-only
        STATUS    mandatory
        DESCRIPTION
                  "Number of bytes that disobey the maximum bandwidth constraint in the premium flow 
                  detection condition."
        ::= { axsQosFlowStatsL3InEntry 22 }

    axsQosFlowStatsL3OutTable OBJECT-TYPE
        SYNTAX    SEQUENCE OF AxsQosFlowStatsL3OutEntry
        ACCESS    not-accessible
        STATUS    mandatory
        DESCRIPTION
                  "Table information on corresponding number of packets to QoS flow detection condition
                  and operation information set in QoS flow list."
        ::= { axsQosFlowStats 6 }

    axsQosFlowStatsL3OutEntry OBJECT-TYPE
        SYNTAX    AxsQosFlowStatsL3OutEntry
        ACCESS    not-accessible
        STATUS    mandatory
        DESCRIPTION
                  "Entry concerning corresponding number of packets to QoS flow detection condition
                  and operation information set in QoS Flower shop."
        INDEX     { axsQosFlowStatsL3OutifIndex,
                    axsQosFlowStatsL3OutifIndexType,
                    axsQosFlowStatsL3OutListIndex,
                    axsQosFlowStatsL3OutSequenceNumber }
        ::= { axsQosFlowStatsL3OutTable 1 }

    AxsQosFlowStatsL3OutEntry ::= SEQUENCE {
        axsQosFlowStatsL3OutifIndex                       INTEGER,
        axsQosFlowStatsL3OutifIndexType                   INTEGER,
        axsQosFlowStatsL3OutListIndex                     Unsigned32,
        axsQosFlowStatsL3OutSequenceNumber                Unsigned32,
        axsQosFlowStatsL3OutListName                      DisplayString,
        axsQosFlowStatsL3OutMatchedPackets                Counter64,
        axsQosFlowStatsL3OutMatchedPacketsMinUnder        Counter64,
        axsQosFlowStatsL3OutMatchedPacketsMinOver         Counter64,
        axsQosFlowStatsL3OutMatchedPacketsMaxUnder        Counter64,
        axsQosFlowStatsL3OutMatchedPacketsMaxOver         Counter64,
        axsQosFlowStatsL3OutMatchedBytesMinUnder          Counter64,
        axsQosFlowStatsL3OutMatchedBytesMinOver           Counter64,
        axsQosFlowStatsL3OutMatchedBytesMaxUnder          Counter64,
        axsQosFlowStatsL3OutMatchedBytesMaxOver           Counter64,
        axsQosFlowStatsL3OutPremMatchedPacketsMinUnder    Counter64,
        axsQosFlowStatsL3OutPremMatchedPacketsMinOver     Counter64,
        axsQosFlowStatsL3OutPremMatchedPacketsMaxUnder    Counter64,
        axsQosFlowStatsL3OutPremMatchedPacketsMaxOver     Counter64,
        axsQosFlowStatsL3OutPremMatchedBytesMinUnder      Counter64,
        axsQosFlowStatsL3OutPremMatchedBytesMinOver       Counter64,
        axsQosFlowStatsL3OutPremMatchedBytesMaxUnder      Counter64,
        axsQosFlowStatsL3OutPremMatchedBytesMaxOver       Counter64
    }

    axsQosFlowStatsL3OutifIndex OBJECT-TYPE
        SYNTAX    INTEGER
        ACCESS    not-accessible
        STATUS    mandatory
        DESCRIPTION
                  "Index value in which entry of this table is identified."
        ::= { axsQosFlowStatsL3OutEntry 1 }

    axsQosFlowStatsL3OutifIndexType OBJECT-TYPE
        SYNTAX    INTEGER
        ACCESS    not-accessible
        STATUS    mandatory
        DESCRIPTION
                  "Indicates interface type. Physical port number : 1 Interface name : 2"
        ::= { axsQosFlowStatsL3OutEntry 2 }

    axsQosFlowStatsL3OutListIndex OBJECT-TYPE
        SYNTAX    Unsigned32
        ACCESS    not-accessible
        STATUS    mandatory
        DESCRIPTION
                  "Index value of QoS Flow list where entry of this table is identified."
        ::= { axsQosFlowStatsL3OutEntry 3 }

    axsQosFlowStatsL3OutSequenceNumber OBJECT-TYPE
        SYNTAX    Unsigned32
        ACCESS    not-accessible
        STATUS    mandatory
        DESCRIPTION
                  "Sequence number of flow detection condition and operation information set to QoS 
                  flow list name."
        ::= { axsQosFlowStatsL3OutEntry 4 }

    axsQosFlowStatsL3OutListName OBJECT-TYPE
        SYNTAX    DisplayString
        ACCESS    read-only
        STATUS    mandatory
        DESCRIPTION
                  "QoS flow list name corresponding to index of QoS flow list."
        ::= { axsQosFlowStatsL3OutEntry 5 }

    axsQosFlowStatsL3OutMatchedPackets OBJECT-TYPE
        SYNTAX    Counter64
        ACCESS    read-only
        STATUS    mandatory
        DESCRIPTION
                  "Corresponding number of packets to flow detection condition of QoS flow list."
        ::= { axsQosFlowStatsL3OutEntry 6 }

    axsQosFlowStatsL3OutMatchedPacketsMinUnder OBJECT-TYPE
        SYNTAX    Counter64
        ACCESS    read-only
        STATUS    mandatory
        DESCRIPTION
                  "Number of packets that obey the minimum bandwidth constraint in the flow 
                  detection condition."
        ::= { axsQosFlowStatsL3OutEntry 7 }

    axsQosFlowStatsL3OutMatchedPacketsMinOver OBJECT-TYPE
        SYNTAX    Counter64
        ACCESS    read-only
        STATUS    mandatory
        DESCRIPTION
                  "Number of packets that disobey the minimum bandwidth constraint in the flow 
                  detection condition."
        ::= { axsQosFlowStatsL3OutEntry 8 }

    axsQosFlowStatsL3OutMatchedPacketsMaxUnder OBJECT-TYPE
        SYNTAX    Counter64
        ACCESS    read-only
        STATUS    mandatory
        DESCRIPTION
                  "Number of packets that obey the maximum bandwidth constraint in the flow 
                  detection condition."
        ::= { axsQosFlowStatsL3OutEntry 9 }

    axsQosFlowStatsL3OutMatchedPacketsMaxOver OBJECT-TYPE
        SYNTAX    Counter64 
        ACCESS    read-only
        STATUS    mandatory
        DESCRIPTION
                  "Number of packets that disobey the maximum bandwidth constraint in the flow 
                  detection condition."
        ::= { axsQosFlowStatsL3OutEntry 10 }

    axsQosFlowStatsL3OutMatchedBytesMinUnder OBJECT-TYPE
        SYNTAX    Counter64 
        ACCESS    read-only
        STATUS    mandatory
        DESCRIPTION
                  "Number of bytes that obey the minimum bandwidth constraint in the flow 
                  detection condition."
        ::= { axsQosFlowStatsL3OutEntry 11 }

    axsQosFlowStatsL3OutMatchedBytesMinOver OBJECT-TYPE
        SYNTAX    Counter64 
        ACCESS    read-only
        STATUS    mandatory
        DESCRIPTION
                  "Number of bytes that disobey the minimum bandwidth constraint in the flow 
                  detection condition."
        ::= { axsQosFlowStatsL3OutEntry 12 }

    axsQosFlowStatsL3OutMatchedBytesMaxUnder OBJECT-TYPE
        SYNTAX    Counter64 
        ACCESS    read-only
        STATUS    mandatory
        DESCRIPTION
                  "Number of bytes that obey the maximum bandwidth constraint in the flow 
                  detection condition."
        ::= { axsQosFlowStatsL3OutEntry 13 }

    axsQosFlowStatsL3OutMatchedBytesMaxOver OBJECT-TYPE
        SYNTAX    Counter64 
        ACCESS    read-only
        STATUS    mandatory
        DESCRIPTION
                  "Number of bytes that disobey the maximum bandwidth constraint in the flow 
                  detection condition."
        ::= { axsQosFlowStatsL3OutEntry 14 }

    axsQosFlowStatsL3OutPremMatchedPacketsMinUnder OBJECT-TYPE
        SYNTAX    Counter64 
        ACCESS    read-only
        STATUS    mandatory
        DESCRIPTION
                  "Number of packets that obey the minimum bandwidth constraint in the premium flow 
                  detection condition."
        ::= { axsQosFlowStatsL3OutEntry 15 }

    axsQosFlowStatsL3OutPremMatchedPacketsMinOver OBJECT-TYPE
        SYNTAX    Counter64 
        ACCESS    read-only
        STATUS    mandatory
        DESCRIPTION
                  "Number of packets that disobey the minimum bandwidth constraint in the premium flow 
                  detection condition."
        ::= { axsQosFlowStatsL3OutEntry 16 }

    axsQosFlowStatsL3OutPremMatchedPacketsMaxUnder OBJECT-TYPE
        SYNTAX    Counter64 
        ACCESS    read-only
        STATUS    mandatory
        DESCRIPTION
                  "Number of packets that obey the maximum bandwidth constraint in the premium flow 
                  detection condition."
        ::= { axsQosFlowStatsL3OutEntry 17 }

    axsQosFlowStatsL3OutPremMatchedPacketsMaxOver OBJECT-TYPE
        SYNTAX    Counter64 
        ACCESS    read-only
        STATUS    mandatory
        DESCRIPTION
                  "Number of packets that disobey the maximum bandwidth constraint in the premium flow 
                  detection condition."
        ::= { axsQosFlowStatsL3OutEntry 18 }

    axsQosFlowStatsL3OutPremMatchedBytesMinUnder OBJECT-TYPE
        SYNTAX    Counter64 
        ACCESS    read-only
        STATUS    mandatory
        DESCRIPTION
                  "Number of bytes that obey the minimum bandwidth constraint in the premium flow 
                  detection condition."
        ::= { axsQosFlowStatsL3OutEntry 19 }

    axsQosFlowStatsL3OutPremMatchedBytesMinOver OBJECT-TYPE
        SYNTAX    Counter64 
        ACCESS    read-only
        STATUS    mandatory
        DESCRIPTION
                  "Number of bytes that disobey the minimum bandwidth constraint in the premium flow 
                  detection condition."
        ::= { axsQosFlowStatsL3OutEntry 20 }

    axsQosFlowStatsL3OutPremMatchedBytesMaxUnder OBJECT-TYPE
        SYNTAX    Counter64 
        ACCESS    read-only
        STATUS    mandatory
        DESCRIPTION
                  "Number of bytes that obey the maximum bandwidth constraint in the premium flow 
                  detection condition."
        ::= { axsQosFlowStatsL3OutEntry 21 }

    axsQosFlowStatsL3OutPremMatchedBytesMaxOver OBJECT-TYPE
        SYNTAX    Counter64 
        ACCESS    read-only
        STATUS    mandatory
        DESCRIPTION
                  "Number of bytes that disobey the maximum bandwidth constraint in the premium flow 
                  detection condition."
        ::= { axsQosFlowStatsL3OutEntry 22 }

    axsQosFlowStatsL2L3InTable OBJECT-TYPE
        SYNTAX    SEQUENCE OF AxsQosFlowStatsL2L3InEntry
        ACCESS    not-accessible
        STATUS    mandatory
        DESCRIPTION
                  "Table information on corresponding number of packets to QoS flow detection condition
                  and operation information set in QoS flow list."
        ::= { axsQosFlowStats 7 }

    axsQosFlowStatsL2L3InEntry OBJECT-TYPE
        SYNTAX    AxsQosFlowStatsL2L3InEntry
        ACCESS    not-accessible
        STATUS    mandatory
        DESCRIPTION
                  "Entry concerning corresponding number of packets to QoS flow detection condition
                  and operation information set in QoS Flower shop."
        INDEX     { axsQosFlowStatsL2L3InifIndex,
                    axsQosFlowStatsL2L3InifIndexType,
                    axsQosFlowStatsL2L3InListIndex,
                    axsQosFlowStatsL2L3InSequenceNumber }
        ::= { axsQosFlowStatsL2L3InTable 1 }

    AxsQosFlowStatsL2L3InEntry ::= SEQUENCE {
        axsQosFlowStatsL2L3InifIndex                       INTEGER,
        axsQosFlowStatsL2L3InifIndexType                   INTEGER,
        axsQosFlowStatsL2L3InListIndex                     Unsigned32,
        axsQosFlowStatsL2L3InSequenceNumber                Unsigned32,
        axsQosFlowStatsL2L3InListName                      DisplayString,
        axsQosFlowStatsL2L3InMatchedPackets                Counter64,
        axsQosFlowStatsL2L3InMatchedPacketsMinUnder        Counter64,
        axsQosFlowStatsL2L3InMatchedPacketsMinOver         Counter64,
        axsQosFlowStatsL2L3InMatchedPacketsMaxUnder        Counter64,
        axsQosFlowStatsL2L3InMatchedPacketsMaxOver         Counter64,
        axsQosFlowStatsL2L3InMatchedBytesMinUnder          Counter64,
        axsQosFlowStatsL2L3InMatchedBytesMinOver           Counter64,
        axsQosFlowStatsL2L3InMatchedBytesMaxUnder          Counter64,
        axsQosFlowStatsL2L3InMatchedBytesMaxOver           Counter64,
        axsQosFlowStatsL2L3InPremMatchedPacketsMinUnder    Counter64,
        axsQosFlowStatsL2L3InPremMatchedPacketsMinOver     Counter64,
        axsQosFlowStatsL2L3InPremMatchedPacketsMaxUnder    Counter64,
        axsQosFlowStatsL2L3InPremMatchedPacketsMaxOver     Counter64,
        axsQosFlowStatsL2L3InPremMatchedBytesMinUnder      Counter64,
        axsQosFlowStatsL2L3InPremMatchedBytesMinOver       Counter64,
        axsQosFlowStatsL2L3InPremMatchedBytesMaxUnder      Counter64,
        axsQosFlowStatsL2L3InPremMatchedBytesMaxOver       Counter64
    }

    axsQosFlowStatsL2L3InifIndex OBJECT-TYPE
        SYNTAX    INTEGER
        ACCESS    not-accessible
        STATUS    mandatory
        DESCRIPTION
                  "Index value in which entry of this table is identified."
        ::= { axsQosFlowStatsL2L3InEntry 1 }

    axsQosFlowStatsL2L3InifIndexType OBJECT-TYPE
        SYNTAX    INTEGER
        ACCESS    not-accessible
        STATUS    mandatory
        DESCRIPTION
                  "Indicates interface type. Physical port number : 1 Interface name : 2"
        ::= { axsQosFlowStatsL2L3InEntry 2 }

    axsQosFlowStatsL2L3InListIndex OBJECT-TYPE
        SYNTAX    Unsigned32
        ACCESS    not-accessible
        STATUS    mandatory
        DESCRIPTION
                  "Index value of QoS Flow list where entry of this table is identified."
        ::= { axsQosFlowStatsL2L3InEntry 3 }

    axsQosFlowStatsL2L3InSequenceNumber OBJECT-TYPE
        SYNTAX    Unsigned32
        ACCESS    not-accessible
        STATUS    mandatory
        DESCRIPTION
                  "Sequence number of flow detection condition and operation information set to QoS 
                  flow list name."
        ::= { axsQosFlowStatsL2L3InEntry 4 }

    axsQosFlowStatsL2L3InListName OBJECT-TYPE
        SYNTAX    DisplayString
        ACCESS    read-only
        STATUS    mandatory
        DESCRIPTION
                  "QoS flow list name corresponding to index of QoS flow list."
        ::= { axsQosFlowStatsL2L3InEntry 5 }

    axsQosFlowStatsL2L3InMatchedPackets OBJECT-TYPE
        SYNTAX    Counter64
        ACCESS    read-only
        STATUS    mandatory
        DESCRIPTION
                  "Corresponding number of packets to flow detection condition of QoS flow list."
        ::= { axsQosFlowStatsL2L3InEntry 6 }

    axsQosFlowStatsL2L3InMatchedPacketsMinUnder OBJECT-TYPE
        SYNTAX    Counter64
        ACCESS    read-only
        STATUS    mandatory
        DESCRIPTION
                  "Number of packets that obey the minimum bandwidth constraint in the flow 
                  detection condition."
        ::= { axsQosFlowStatsL2L3InEntry 7 }

    axsQosFlowStatsL2L3InMatchedPacketsMinOver OBJECT-TYPE
        SYNTAX    Counter64
        ACCESS    read-only
        STATUS    mandatory
        DESCRIPTION
                  "Number of packets that disobey the minimum bandwidth constraint in the flow 
                  detection condition."
        ::= { axsQosFlowStatsL2L3InEntry 8 }

    axsQosFlowStatsL2L3InMatchedPacketsMaxUnder OBJECT-TYPE
        SYNTAX    Counter64
        ACCESS    read-only
        STATUS    mandatory
        DESCRIPTION
                  "Number of packets that obey the maximum bandwidth constraint in the flow 
                  detection condition."
        ::= { axsQosFlowStatsL2L3InEntry 9 }

    axsQosFlowStatsL2L3InMatchedPacketsMaxOver OBJECT-TYPE
        SYNTAX    Counter64 
        ACCESS    read-only
        STATUS    mandatory
        DESCRIPTION
                  "Number of packets that disobey the maximum bandwidth constraint in the flow 
                  detection condition."
        ::= { axsQosFlowStatsL2L3InEntry 10 }

    axsQosFlowStatsL2L3InMatchedBytesMinUnder OBJECT-TYPE
        SYNTAX    Counter64 
        ACCESS    read-only
        STATUS    mandatory
        DESCRIPTION
                  "Number of bytes that obey the minimum bandwidth constraint in the flow 
                  detection condition."
        ::= { axsQosFlowStatsL2L3InEntry 11 }

    axsQosFlowStatsL2L3InMatchedBytesMinOver OBJECT-TYPE
        SYNTAX    Counter64 
        ACCESS    read-only
        STATUS    mandatory
        DESCRIPTION
                  "Number of bytes that disobey the minimum bandwidth constraint in the flow 
                  detection condition."
        ::= { axsQosFlowStatsL2L3InEntry 12 }

    axsQosFlowStatsL2L3InMatchedBytesMaxUnder OBJECT-TYPE
        SYNTAX    Counter64 
        ACCESS    read-only
        STATUS    mandatory
        DESCRIPTION
                  "Number of bytes that obey the maximum bandwidth constraint in the flow 
                  detection condition."
        ::= { axsQosFlowStatsL2L3InEntry 13 }

    axsQosFlowStatsL2L3InMatchedBytesMaxOver OBJECT-TYPE
        SYNTAX    Counter64 
        ACCESS    read-only
        STATUS    mandatory
        DESCRIPTION
                  "Number of bytes that disobey the maximum bandwidth constraint in the flow 
                  detection condition."
        ::= { axsQosFlowStatsL2L3InEntry 14 }

    axsQosFlowStatsL2L3InPremMatchedPacketsMinUnder OBJECT-TYPE
        SYNTAX    Counter64 
        ACCESS    read-only
        STATUS    mandatory
        DESCRIPTION
                  "Number of packets that obey the minimum bandwidth constraint in the premium flow 
                  detection condition."
        ::= { axsQosFlowStatsL2L3InEntry 15 }

    axsQosFlowStatsL2L3InPremMatchedPacketsMinOver OBJECT-TYPE
        SYNTAX    Counter64 
        ACCESS    read-only
        STATUS    mandatory
        DESCRIPTION
                  "Number of packets that disobey the minimum bandwidth constraint in the premium flow 
                  detection condition."
        ::= { axsQosFlowStatsL2L3InEntry 16 }

    axsQosFlowStatsL2L3InPremMatchedPacketsMaxUnder OBJECT-TYPE
        SYNTAX    Counter64 
        ACCESS    read-only
        STATUS    mandatory
        DESCRIPTION
                  "Number of packets that obey the maximum bandwidth constraint in the premium flow 
                  detection condition."
        ::= { axsQosFlowStatsL2L3InEntry 17 }

    axsQosFlowStatsL2L3InPremMatchedPacketsMaxOver OBJECT-TYPE
        SYNTAX    Counter64 
        ACCESS    read-only
        STATUS    mandatory
        DESCRIPTION
                  "Number of packets that disobey the maximum bandwidth constraint in the premium flow 
                  detection condition."
        ::= { axsQosFlowStatsL2L3InEntry 18 }

    axsQosFlowStatsL2L3InPremMatchedBytesMinUnder OBJECT-TYPE
        SYNTAX    Counter64 
        ACCESS    read-only
        STATUS    mandatory
        DESCRIPTION
                  "Number of bytes that obey the minimum bandwidth constraint in the premium flow 
                  detection condition."
        ::= { axsQosFlowStatsL2L3InEntry 19 }

    axsQosFlowStatsL2L3InPremMatchedBytesMinOver OBJECT-TYPE
        SYNTAX    Counter64 
        ACCESS    read-only
        STATUS    mandatory
        DESCRIPTION
                  "Number of bytes that disobey the minimum bandwidth constraint in the premium flow 
                  detection condition."
        ::= { axsQosFlowStatsL2L3InEntry 20 }

    axsQosFlowStatsL2L3InPremMatchedBytesMaxUnder OBJECT-TYPE
        SYNTAX    Counter64 
        ACCESS    read-only
        STATUS    mandatory
        DESCRIPTION
                  "Number of bytes that obey the maximum bandwidth constraint in the premium flow 
                  detection condition."
        ::= { axsQosFlowStatsL2L3InEntry 21 }

    axsQosFlowStatsL2L3InPremMatchedBytesMaxOver OBJECT-TYPE
        SYNTAX    Counter64 
        ACCESS    read-only
        STATUS    mandatory
        DESCRIPTION
                  "Number of bytes that disobey the maximum bandwidth constraint in the premium flow 
                  detection condition."
        ::= { axsQosFlowStatsL2L3InEntry 22 }

    axsQosFlowStatsL2L3OutTable OBJECT-TYPE
        SYNTAX    SEQUENCE OF AxsQosFlowStatsL2L3OutEntry
        ACCESS    not-accessible
        STATUS    mandatory
        DESCRIPTION
                  "Table information on corresponding number of packets to QoS flow detection condition
                  and operation information set in QoS flow list."
        ::= { axsQosFlowStats 8 }

    axsQosFlowStatsL2L3OutEntry OBJECT-TYPE
        SYNTAX    AxsQosFlowStatsL2L3OutEntry
        ACCESS    not-accessible
        STATUS    mandatory
        DESCRIPTION
                  "Entry concerning corresponding number of packets to QoS flow detection condition
                  and operation information set in QoS Flower shop."
        INDEX     { axsQosFlowStatsL2L3OutifIndex,
                    axsQosFlowStatsL2L3OutifIndexType,
                    axsQosFlowStatsL2L3OutListIndex,
                    axsQosFlowStatsL2L3OutSequenceNumber }
        ::= { axsQosFlowStatsL2L3OutTable 1 }

    AxsQosFlowStatsL2L3OutEntry ::= SEQUENCE {
        axsQosFlowStatsL2L3OutifIndex                       INTEGER,
        axsQosFlowStatsL2L3OutifIndexType                   INTEGER,
        axsQosFlowStatsL2L3OutListIndex                     Unsigned32,
        axsQosFlowStatsL2L3OutSequenceNumber                Unsigned32,
        axsQosFlowStatsL2L3OutListName                      DisplayString,
        axsQosFlowStatsL2L3OutMatchedPackets                Counter64,
        axsQosFlowStatsL2L3OutMatchedPacketsMinUnder        Counter64,
        axsQosFlowStatsL2L3OutMatchedPacketsMinOver         Counter64,
        axsQosFlowStatsL2L3OutMatchedPacketsMaxUnder        Counter64,
        axsQosFlowStatsL2L3OutMatchedPacketsMaxOver         Counter64,
        axsQosFlowStatsL2L3OutMatchedBytesMinUnder          Counter64,
        axsQosFlowStatsL2L3OutMatchedBytesMinOver           Counter64,
        axsQosFlowStatsL2L3OutMatchedBytesMaxUnder          Counter64,
        axsQosFlowStatsL2L3OutMatchedBytesMaxOver           Counter64,
        axsQosFlowStatsL2L3OutPremMatchedPacketsMinUnder    Counter64,
        axsQosFlowStatsL2L3OutPremMatchedPacketsMinOver     Counter64,
        axsQosFlowStatsL2L3OutPremMatchedPacketsMaxUnder    Counter64,
        axsQosFlowStatsL2L3OutPremMatchedPacketsMaxOver     Counter64,
        axsQosFlowStatsL2L3OutPremMatchedBytesMinUnder      Counter64,
        axsQosFlowStatsL2L3OutPremMatchedBytesMinOver       Counter64,
        axsQosFlowStatsL2L3OutPremMatchedBytesMaxUnder      Counter64,
        axsQosFlowStatsL2L3OutPremMatchedBytesMaxOver       Counter64
    }

    axsQosFlowStatsL2L3OutifIndex OBJECT-TYPE
        SYNTAX    INTEGER
        ACCESS    not-accessible
        STATUS    mandatory
        DESCRIPTION
                  "Index value in which entry of this table is identified."
        ::= { axsQosFlowStatsL2L3OutEntry 1 }

    axsQosFlowStatsL2L3OutifIndexType OBJECT-TYPE
        SYNTAX    INTEGER
        ACCESS    not-accessible
        STATUS    mandatory
        DESCRIPTION
                  "Indicates interface type. Physical port number : 1 Interface name : 2"
        ::= { axsQosFlowStatsL2L3OutEntry 2 }

    axsQosFlowStatsL2L3OutListIndex OBJECT-TYPE
        SYNTAX    Unsigned32
        ACCESS    not-accessible
        STATUS    mandatory
        DESCRIPTION
                  "Index value of QoS Flow list where entry of this table is identified."
        ::= { axsQosFlowStatsL2L3OutEntry 3 }

    axsQosFlowStatsL2L3OutSequenceNumber OBJECT-TYPE
        SYNTAX    Unsigned32
        ACCESS    not-accessible
        STATUS    mandatory
        DESCRIPTION
                  "Sequence number of flow detection condition and operation information set to QoS 
                  flow list name."
        ::= { axsQosFlowStatsL2L3OutEntry 4 }

    axsQosFlowStatsL2L3OutListName OBJECT-TYPE
        SYNTAX    DisplayString
        ACCESS    read-only
        STATUS    mandatory
        DESCRIPTION
                  "QoS flow list name corresponding to index of QoS flow list."
        ::= { axsQosFlowStatsL2L3OutEntry 5 }

    axsQosFlowStatsL2L3OutMatchedPackets OBJECT-TYPE
        SYNTAX    Counter64
        ACCESS    read-only
        STATUS    mandatory
        DESCRIPTION
                  "Corresponding number of packets to flow detection condition of QoS flow list."
        ::= { axsQosFlowStatsL2L3OutEntry 6 }

    axsQosFlowStatsL2L3OutMatchedPacketsMinUnder OBJECT-TYPE
        SYNTAX    Counter64
        ACCESS    read-only
        STATUS    mandatory
        DESCRIPTION
                  "Number of packets that obey the minimum bandwidth constraint in the flow 
                  detection condition."
        ::= { axsQosFlowStatsL2L3OutEntry 7 }

    axsQosFlowStatsL2L3OutMatchedPacketsMinOver OBJECT-TYPE
        SYNTAX    Counter64
        ACCESS    read-only
        STATUS    mandatory
        DESCRIPTION
                  "Number of packets that disobey the minimum bandwidth constraint in the flow 
                  detection condition."
        ::= { axsQosFlowStatsL2L3OutEntry 8 }

    axsQosFlowStatsL2L3OutMatchedPacketsMaxUnder OBJECT-TYPE
        SYNTAX    Counter64
        ACCESS    read-only
        STATUS    mandatory
        DESCRIPTION
                  "Number of packets that obey the maximum bandwidth constraint in the flow 
                  detection condition."
        ::= { axsQosFlowStatsL2L3OutEntry 9 }

    axsQosFlowStatsL2L3OutMatchedPacketsMaxOver OBJECT-TYPE
        SYNTAX    Counter64 
        ACCESS    read-only
        STATUS    mandatory
        DESCRIPTION
                  "Number of packets that disobey the maximum bandwidth constraint in the flow 
                  detection condition."
        ::= { axsQosFlowStatsL2L3OutEntry 10 }

    axsQosFlowStatsL2L3OutMatchedBytesMinUnder OBJECT-TYPE
        SYNTAX    Counter64 
        ACCESS    read-only
        STATUS    mandatory
        DESCRIPTION
                  "Number of bytes that obey the minimum bandwidth constraint in the flow 
                  detection condition."
        ::= { axsQosFlowStatsL2L3OutEntry 11 }

    axsQosFlowStatsL2L3OutMatchedBytesMinOver OBJECT-TYPE
        SYNTAX    Counter64 
        ACCESS    read-only
        STATUS    mandatory
        DESCRIPTION
                  "Number of bytes that disobey the minimum bandwidth constraint in the flow 
                  detection condition."
        ::= { axsQosFlowStatsL2L3OutEntry 12 }

    axsQosFlowStatsL2L3OutMatchedBytesMaxUnder OBJECT-TYPE
        SYNTAX    Counter64 
        ACCESS    read-only
        STATUS    mandatory
        DESCRIPTION
                  "Number of bytes that obey the maximum bandwidth constraint in the flow 
                  detection condition."
        ::= { axsQosFlowStatsL2L3OutEntry 13 }

    axsQosFlowStatsL2L3OutMatchedBytesMaxOver OBJECT-TYPE
        SYNTAX    Counter64 
        ACCESS    read-only
        STATUS    mandatory
        DESCRIPTION
                  "Number of bytes that disobey the maximum bandwidth constraint in the flow 
                  detection condition."
        ::= { axsQosFlowStatsL2L3OutEntry 14 }

    axsQosFlowStatsL2L3OutPremMatchedPacketsMinUnder OBJECT-TYPE
        SYNTAX    Counter64 
        ACCESS    read-only
        STATUS    mandatory
        DESCRIPTION
                  "Number of packets that obey the minimum bandwidth constraint in the premium flow 
                  detection condition."
        ::= { axsQosFlowStatsL2L3OutEntry 15 }

    axsQosFlowStatsL2L3OutPremMatchedPacketsMinOver OBJECT-TYPE
        SYNTAX    Counter64 
        ACCESS    read-only
        STATUS    mandatory
        DESCRIPTION
                  "Number of packets that disobey the minimum bandwidth constraint in the premium flow 
                  detection condition."
        ::= { axsQosFlowStatsL2L3OutEntry 16 }

    axsQosFlowStatsL2L3OutPremMatchedPacketsMaxUnder OBJECT-TYPE
        SYNTAX    Counter64 
        ACCESS    read-only
        STATUS    mandatory
        DESCRIPTION
                  "Number of packets that obey the maximum bandwidth constraint in the premium flow 
                  detection condition."
        ::= { axsQosFlowStatsL2L3OutEntry 17 }

    axsQosFlowStatsL2L3OutPremMatchedPacketsMaxOver OBJECT-TYPE
        SYNTAX    Counter64 
        ACCESS    read-only
        STATUS    mandatory
        DESCRIPTION
                  "Number of packets that disobey the maximum bandwidth constraint in the premium flow 
                  detection condition."
        ::= { axsQosFlowStatsL2L3OutEntry 18 }

    axsQosFlowStatsL2L3OutPremMatchedBytesMinUnder OBJECT-TYPE
        SYNTAX    Counter64 
        ACCESS    read-only
        STATUS    mandatory
        DESCRIPTION
                  "Number of bytes that obey the minimum bandwidth constraint in the premium flow 
                  detection condition."
        ::= { axsQosFlowStatsL2L3OutEntry 19 }

    axsQosFlowStatsL2L3OutPremMatchedBytesMinOver OBJECT-TYPE
        SYNTAX    Counter64 
        ACCESS    read-only
        STATUS    mandatory
        DESCRIPTION
                  "Number of bytes that disobey the minimum bandwidth constraint in the premium flow 
                  detection condition."
        ::= { axsQosFlowStatsL2L3OutEntry 20 }

    axsQosFlowStatsL2L3OutPremMatchedBytesMaxUnder OBJECT-TYPE
        SYNTAX    Counter64 
        ACCESS    read-only
        STATUS    mandatory
        DESCRIPTION
                  "Number of bytes that obey the maximum bandwidth constraint in the premium flow 
                  detection condition."
        ::= { axsQosFlowStatsL2L3OutEntry 21 }

    axsQosFlowStatsL2L3OutPremMatchedBytesMaxOver OBJECT-TYPE
        SYNTAX    Counter64 
        ACCESS    read-only
        STATUS    mandatory
        DESCRIPTION
                  "Number of bytes that disobey the maximum bandwidth constraint in the premium flow 
                  detection condition."
        ::= { axsQosFlowStatsL2L3OutEntry 22 }

-- axsPortChannel Group

    axsPortChannelPortTable OBJECT-TYPE
        SYNTAX    SEQUENCE OF AxsPortChannelPortEntry
        ACCESS    not-accessible
        STATUS    mandatory
        DESCRIPTION
                  "The table containing every port information of channel group."
        ::= { axsPortChannelPort 1 }

    axsPortChannelPortEntry OBJECT-TYPE
        SYNTAX    AxsPortChannelPortEntry
        ACCESS    not-accessible
        STATUS    mandatory
        DESCRIPTION
                  "The entry of each port information of channel group."
        INDEX { axsPortChannelPortIndex }
        ::= { axsPortChannelPortTable 1 }

    AxsPortChannelPortEntry ::= SEQUENCE {
        axsPortChannelPortIndex            INTEGER,
        axsPortChannelPortIfIndex          INTEGER,
        axsPortChannelPortStandbyState     INTEGER,
        axsPortChannelPortAdminPriority    INTEGER,
        axsPortChannelPortOperPriority     INTEGER
     }

    axsPortChannelPortIndex OBJECT-TYPE
        SYNTAX    INTEGER
        ACCESS    not-accessible
        STATUS    mandatory
        DESCRIPTION
                  "Number to identify this port."
        ::= { axsPortChannelPortEntry 1 }

    axsPortChannelPortIfIndex OBJECT-TYPE
        SYNTAX    INTEGER
        ACCESS    read-only
        STATUS    mandatory
        DESCRIPTION
                  "The ifIndex of the port."
        ::= { axsPortChannelPortEntry 2 }

    axsPortChannelPortStandbyState OBJECT-TYPE
        SYNTAX    INTEGER {
                       unreachable(1),
                       reachable(2),
                       non-standby(3)
                  }
        ACCESS    read-only
        STATUS    mandatory
        DESCRIPTION
                  "The standby state of port."
        ::= { axsPortChannelPortEntry 3 }

    axsPortChannelPortAdminPriority OBJECT-TYPE
        SYNTAX    INTEGER
        ACCESS    read-only
        STATUS    mandatory
        DESCRIPTION
                  "The priority of port on administration."
        ::= { axsPortChannelPortEntry 4 }

    axsPortChannelPortOperPriority OBJECT-TYPE
        SYNTAX    INTEGER
        ACCESS    read-only
        STATUS    mandatory
        DESCRIPTION
                  "The priority of port on operation."
        ::= { axsPortChannelPortEntry 5 }

-- axsL2ldMIB Group

    axsL2ldVersion OBJECT-TYPE
        SYNTAX    INTEGER
        ACCESS    read-only
        STATUS    mandatory
        DESCRIPTION
                  "The version of L2 loop detection."
        ::= { axsL2ldGlobalInfo 1 }

    axsL2ldLoopDetectionId OBJECT-TYPE
        SYNTAX    INTEGER
        ACCESS    read-only
        STATUS    mandatory
        DESCRIPTION
                  "L2 loop detection ID."
        ::= { axsL2ldGlobalInfo 2 }

    axsL2ldIntervalTime OBJECT-TYPE
        SYNTAX    INTEGER
        ACCESS    read-only
        STATUS    mandatory
        DESCRIPTION
                  "Sending interval of L2 loop detection frame."
        ::= { axsL2ldGlobalInfo 3 }

    axsL2ldOutputRate OBJECT-TYPE
        SYNTAX    INTEGER
        ACCESS    read-only
        STATUS    mandatory
        DESCRIPTION
                  "Sending rate of L2 loop detection frame."
        ::= { axsL2ldGlobalInfo 4 }

    axsL2ldThreshold OBJECT-TYPE
        SYNTAX    INTEGER
        ACCESS    read-only
        STATUS    mandatory
        DESCRIPTION
                  "Detection counts until port is put into state of inactive."
        ::= { axsL2ldGlobalInfo 5 }

    axsL2ldHoldTime OBJECT-TYPE
        SYNTAX    INTEGER
        ACCESS    read-only
        STATUS    mandatory
        DESCRIPTION
                  "Hold time of detection counts."
        ::= { axsL2ldGlobalInfo 6 }

    axsL2ldAutoRestoreTime OBJECT-TYPE
        SYNTAX    INTEGER
        ACCESS    read-only
        STATUS    mandatory
        DESCRIPTION
                  "Time until port put into state of inactive is put into state of
                  active by automatic operation."
        ::= { axsL2ldGlobalInfo 7 }

    axsL2ldConfigurationVlanPortCounts OBJECT-TYPE
        SYNTAX    INTEGER
        ACCESS    read-only
        STATUS    mandatory
        DESCRIPTION
                  "The number of VLAN ports set to send L2 loop detection frame."
        ::= { axsL2ldGlobalInfo 8 }

    axsL2ldCapacityVlanPortCounts OBJECT-TYPE
        SYNTAX    INTEGER
        ACCESS    read-only
        STATUS    mandatory
        DESCRIPTION
                  "The number of VLAN ports that can be sent by L2 loop detection
                  frame sending rate."
        ::= { axsL2ldGlobalInfo 9 }

    axsL2ldPortTable OBJECT-TYPE
        SYNTAX    SEQUENCE OF AxsL2ldPortEntry
        ACCESS    not-accessible
        STATUS    mandatory
        DESCRIPTION
                  "The table containing port information on L2 loop detection."
        ::= { axsL2ld 2 }

    axsL2ldPortEntry OBJECT-TYPE
        SYNTAX    AxsL2ldPortEntry
        ACCESS    not-accessible
        STATUS    mandatory
        DESCRIPTION
                  "The entry of port information on L2 loop detection."
        INDEX { axsL2ldPortIndex,
                axsL2ldPortIfIndex }
        ::= { axsL2ldPortTable 1 }

    AxsL2ldPortEntry ::= SEQUENCE {
        axsL2ldPortIndex                     INTEGER,
        axsL2ldPortIfIndex                   INTEGER,
        axsL2ldPortStatus                    INTEGER,
        axsL2ldPortType                      INTEGER,
        axsL2ldPortDetectCount               INTEGER,
        axsL2ldPortAutoRestoringTimer        INTEGER,
        axsL2ldPortSourcePortIfindex         INTEGER,
        axsL2ldPortDestinationPortIfindex    INTEGER,
        axsL2ldPortSourceVlan                INTEGER,
        axsL2ldPortHCInFrames                Counter64,
        axsL2ldPortHCOutFrames               Counter64,
        axsL2ldPortHCInDiscards              Counter64,
        axsL2ldPortInactiveCount             INTEGER,
        axsL2ldPortLastInactiveTime          TimeStamp,
        axsL2ldPortLastInFramesTime          TimeStamp
    }

    axsL2ldPortIndex OBJECT-TYPE
        SYNTAX    INTEGER
        ACCESS    read-only
        STATUS    mandatory
        DESCRIPTION
                  "Index of L2 loop detection port."
        ::= { axsL2ldPortEntry 1 }

    axsL2ldPortIfIndex OBJECT-TYPE
        SYNTAX    INTEGER
        ACCESS    read-only
        STATUS    mandatory
        DESCRIPTION
                  "ifIndex of L2 loop detection port."
        ::= { axsL2ldPortEntry 2 }

    axsL2ldPortStatus OBJECT-TYPE
        SYNTAX    INTEGER {
                      up(1),
                      down(2),
                      loopDown(3)
                  }
        ACCESS    read-only
        STATUS    mandatory
        DESCRIPTION
                  "State of L2 loop detection port."
        ::= { axsL2ldPortEntry 3 }

    axsL2ldPortType OBJECT-TYPE
        SYNTAX    INTEGER {
                      trap(1),
                      sendInact(2),
                      send(3),
                      upLink(4),
                      exception(5)
                  }
        ACCESS    read-only
        STATUS    mandatory
        DESCRIPTION
                  "Type of L2 loop detection port."
        ::= { axsL2ldPortEntry 4 }

    axsL2ldPortDetectCount OBJECT-TYPE
        SYNTAX    INTEGER
        ACCESS    read-only
        STATUS    mandatory
        DESCRIPTION
                  "The number of L2 loop detection. The number in which
                  L2 loop detection frame is received in hold time."
        ::= { axsL2ldPortEntry 5 }

    axsL2ldPortAutoRestoringTimer OBJECT-TYPE
        SYNTAX    INTEGER
        ACCESS    read-only
        STATUS    mandatory
        DESCRIPTION
                  "Time until restoring it automatically. The value is 0
                  when port is active."
        ::= { axsL2ldPortEntry 6 }

    axsL2ldPortSourcePortIfindex OBJECT-TYPE
        SYNTAX    INTEGER
        ACCESS    read-only
        STATUS    mandatory
        DESCRIPTION
                  "ifIndex of port transmitted when L2 loop detection frame
                  was received at the end."
        ::= { axsL2ldPortEntry 7 }

    axsL2ldPortDestinationPortIfindex OBJECT-TYPE
        SYNTAX    INTEGER
        ACCESS    read-only
        STATUS    mandatory
        DESCRIPTION
                  "ifIndex of port where L2 loop detection frame was
                  received at the end."
        ::= { axsL2ldPortEntry 8 }

    axsL2ldPortSourceVlan OBJECT-TYPE
        SYNTAX    INTEGER
        ACCESS    read-only
        STATUS    mandatory
        DESCRIPTION
                  "VLAN ID when transmitting when L2 loop detection frame
                  was received at the end."
        ::= { axsL2ldPortEntry 9 }

    axsL2ldPortHCInFrames OBJECT-TYPE
        SYNTAX    Counter64
        ACCESS    read-only
        STATUS    mandatory
        DESCRIPTION
                  "Number of receptions of L2 loop detection frames."
        ::= { axsL2ldPortEntry 10 }

    axsL2ldPortHCOutFrames OBJECT-TYPE
        SYNTAX    Counter64
        ACCESS    read-only
        STATUS    mandatory
        DESCRIPTION
                  "Number of transmissions of L2 loop detection frames."
        ::= { axsL2ldPortEntry 11 }

    axsL2ldPortHCInDiscards OBJECT-TYPE
        SYNTAX    Counter64
        ACCESS    read-only
        STATUS    mandatory
        DESCRIPTION
                  "Number of receptions of L2 loop detection discard frames."
        ::= { axsL2ldPortEntry 12 }

    axsL2ldPortInactiveCount OBJECT-TYPE
        SYNTAX    INTEGER
        ACCESS    read-only
        STATUS    mandatory
        DESCRIPTION
                  "The number of put into state of inactive."
        ::= { axsL2ldPortEntry 13 }

    axsL2ldPortLastInactiveTime OBJECT-TYPE
        SYNTAX    TimeStamp
        ACCESS    read-only
        STATUS    mandatory
        DESCRIPTION
                  "Time put into state of inactive at the end."
        ::= { axsL2ldPortEntry 14 }

    axsL2ldPortLastInFramesTime OBJECT-TYPE
        SYNTAX    TimeStamp
        ACCESS    read-only
        STATUS    mandatory
        DESCRIPTION
                  "Time to have received L2 loop detection frame at the end."
        ::= { axsL2ldPortEntry 15 }

-- AX VrfMIB Group

    axsVrfIpAddrTable OBJECT-TYPE
        SYNTAX    SEQUENCE OF AxsVrfIpAddrEntry
        ACCESS    not-accessible
        STATUS    mandatory
        DESCRIPTION
                  "The table of addressing information relevant to
                  this entity's IP addresses."
        ::= { axsVrfIp 1 }

    axsVrfIpAddrEntry OBJECT-TYPE
        SYNTAX    AxsVrfIpAddrEntry
        ACCESS    not-accessible
        STATUS    mandatory
        DESCRIPTION
                  "The addressing information for one of this
                  entity's IP addresses."
        INDEX { axsVrfIpAddrVrfIndex,
                axsVrfIpAdEntAddr }
        ::= { axsVrfIpAddrTable 1 }

    AxsVrfIpAddrEntry ::= SEQUENCE {
        axsVrfIpAddrVrfIndex         INTEGER,
        axsVrfIpAdEntAddr            IpAddress,
        axsVrfIpAdEntIfIndex         INTEGER,
        axsVrfIpAdEntNetMask         IpAddress,
        axsVrfIpAdEntBcastAddr       INTEGER,
        axsVrfIpAdEntReasmMaxSize    INTEGER,
        axsVrfIpAdEntDescr           DisplayString
    }

    axsVrfIpAddrVrfIndex OBJECT-TYPE
        SYNTAX    INTEGER
        ACCESS    read-only
        STATUS    mandatory
        DESCRIPTION
                  "The index value which identifies VRF number."
        ::= { axsVrfIpAddrEntry 1 }

    axsVrfIpAdEntAddr OBJECT-TYPE
        SYNTAX    IpAddress
        ACCESS    read-only
        STATUS    mandatory
        DESCRIPTION
                  "The IP address to which this entry's addressing
                  information pertains."
        ::= { axsVrfIpAddrEntry 2 }

    axsVrfIpAdEntIfIndex OBJECT-TYPE
        SYNTAX    INTEGER
        ACCESS    read-only
        STATUS    mandatory
        DESCRIPTION
                  "The index value which uniquely identifies the
                  interface to which this entry is applicable."
        ::= { axsVrfIpAddrEntry 3 }

    axsVrfIpAdEntNetMask OBJECT-TYPE
        SYNTAX    IpAddress
        ACCESS    read-only
        STATUS    mandatory
        DESCRIPTION
                  "The subnet mask associated with the IP address of
                  this entry."
        ::= { axsVrfIpAddrEntry 4 }

    axsVrfIpAdEntBcastAddr OBJECT-TYPE
        SYNTAX    INTEGER
        ACCESS    read-only
        STATUS    mandatory
        DESCRIPTION
                  "The value of the least-significant bit in the IP
                  broadcast address used for sending dataaxrams on
                  the (logical) interface associated with the IP
                  address of this entry."
        ::= { axsVrfIpAddrEntry 5 }

    axsVrfIpAdEntReasmMaxSize OBJECT-TYPE
        SYNTAX    INTEGER
        ACCESS    read-only
        STATUS    mandatory
        DESCRIPTION
                  "The size of the largest IP dataaxram which this
                  entity can re-assemble from incoming IP fragmented
                  dataaxrams received on this interface."
        ::= { axsVrfIpAddrEntry 6 }

    axsVrfIpAdEntDescr OBJECT-TYPE
        SYNTAX    DisplayString
        ACCESS    read-only
        STATUS    mandatory
        DESCRIPTION
                  "The Description of VRF. The VRF identification which user setting."
        ::= { axsVrfIpAddrEntry 7 }

    axsVrfIpNetToMediaTable OBJECT-TYPE
        SYNTAX    SEQUENCE OF AxsVrfIpNetToMediaEntry
        ACCESS    not-accessible
        STATUS    mandatory
        DESCRIPTION
                  "The IP Address Translation table used for mapping
                  from IP addresses to physical addresses."
        ::= { axsVrfIp 2 }

    axsVrfIpNetToMediaEntry OBJECT-TYPE
        SYNTAX    AxsVrfIpNetToMediaEntry
        ACCESS    not-accessible
        STATUS    mandatory
        DESCRIPTION
                  "Each entry contains one IpAddress to physical
                  address equivalence."
        INDEX { axsVrfIpNetMediaVrfIndex,
                axsVrfIpNetToMediaIfIndex,
                axsVrfIpNetToMediaNetAddress }
        ::= { axsVrfIpNetToMediaTable 1 }

    AxsVrfIpNetToMediaEntry ::= SEQUENCE {
        axsVrfIpNetMediaVrfIndex         INTEGER,
        axsVrfIpNetToMediaIfIndex        INTEGER,
        axsVrfIpNetToMediaPhysAddress    PhysAddress,
        axsVrfIpNetToMediaNetAddress     IpAddress,
        axsVrfIpNetToMediaType           INTEGER,
        axsVrfIpNetToMediaDescr          DisplayString
    }

    axsVrfIpNetMediaVrfIndex OBJECT-TYPE
        SYNTAX    INTEGER
        ACCESS    read-only
        STATUS    mandatory
        DESCRIPTION
                  "The index value which identifies VRF number."
        ::= { axsVrfIpNetToMediaEntry 1 }

    axsVrfIpNetToMediaIfIndex OBJECT-TYPE
        SYNTAX    INTEGER
        ACCESS    read-only
        STATUS    mandatory
        DESCRIPTION
                  "The interface on which this entry's equivalence
                  is effective. This index is same value of ifIndex."
        ::= { axsVrfIpNetToMediaEntry 2 }

    axsVrfIpNetToMediaPhysAddress OBJECT-TYPE
        SYNTAX    PhysAddress
        ACCESS    read-only
        STATUS    mandatory
        DESCRIPTION
                  "The media-dependent `physical' address."
        ::= { axsVrfIpNetToMediaEntry 3 }

    axsVrfIpNetToMediaNetAddress OBJECT-TYPE
        SYNTAX    IpAddress
        ACCESS    read-only
        STATUS    mandatory
        DESCRIPTION
                  "The IpAddress corresponding to the media-
                  dependent `physical' address."
        ::= { axsVrfIpNetToMediaEntry 4 }

    axsVrfIpNetToMediaType OBJECT-TYPE
        SYNTAX    INTEGER {
                      other(1),   -- none of the following ex. Inverse ARP
                      invalid(2), -- an invalidated mapping
                      dynamic(3),
                      static(4)
                  }
        ACCESS    read-only
        STATUS    mandatory
        DESCRIPTION
                  "The type of mapping."
        ::= { axsVrfIpNetToMediaEntry 5 }

    axsVrfIpNetToMediaDescr OBJECT-TYPE
        SYNTAX    DisplayString
        ACCESS    read-only
        STATUS    mandatory
        DESCRIPTION
                  "The Description of VRF. The VRF identification which user setting."
        ::= { axsVrfIpNetToMediaEntry 6 }

    axsVrfIpFwNoTable OBJECT-TYPE
        SYNTAX    SEQUENCE OF AxsVrfIpFwNoEntry
        ACCESS    not-accessible
        STATUS    mandatory
        DESCRIPTION
                  "This entity's number of IP Routing table about VRF."
        ::= { axsVrfIpForward 1 }

    axsVrfIpFwNoEntry OBJECT-TYPE
        SYNTAX    AxsVrfIpFwNoEntry
        ACCESS    not-accessible
        STATUS    mandatory
        DESCRIPTION
                  "This entity's IP Routing table about VRF."
        INDEX { axsVrfIpFwNoVRFIndex }
        ::= { axsVrfIpFwNoTable 1 }

    AxsVrfIpFwNoEntry ::= SEQUENCE {
        axsVrfIpFwNoVRFIndex    INTEGER,
        axsVrfIpFwNo            INTEGER,
        axsVrfIpFwNoDescr       DisplayString
    }

    axsVrfIpFwNoVRFIndex OBJECT-TYPE
        SYNTAX    INTEGER
        ACCESS    read-only
        STATUS    mandatory
        DESCRIPTION
                  "The index value which identifies VRF number."
        ::= { axsVrfIpFwNoEntry 1 }

    axsVrfIpFwNo OBJECT-TYPE
        SYNTAX    INTEGER
        ACCESS    read-only
        STATUS    mandatory
        DESCRIPTION
                  "The number of entry that is IP Routing table."
        ::= { axsVrfIpFwNoEntry 2 }

    axsVrfIpFwNoDescr OBJECT-TYPE
        SYNTAX    DisplayString
        ACCESS    read-only
        STATUS    mandatory
        DESCRIPTION
                  "The Description of VRF. The VRF identification which user setting."
        ::= { axsVrfIpFwNoEntry 3 }

    axsVrfIpFwTable OBJECT-TYPE
        SYNTAX    SEQUENCE OF AxsVrfIpFwEntry
        ACCESS    not-accessible
        STATUS    mandatory
        DESCRIPTION
                  "This entity's IP Routing table."
        ::= { axsVrfIpForward 2 }

    axsVrfIpFwEntry OBJECT-TYPE
        SYNTAX    AxsVrfIpFwEntry
        ACCESS    not-accessible
        STATUS    mandatory
        DESCRIPTION
                  "A particular route to a particular destination,
                  under a particular policy."
        INDEX { axsVrfIpFwVRFIndex,
                axsVrfIpFwDest,
                axsVrfIpFwProto,
                axsVrfIpFwPolicy,
                axsVrfIpFwNextHop }
        ::= { axsVrfIpFwTable 1 }

    AxsVrfIpFwEntry ::= SEQUENCE {
        axsVrfIpFwVRFIndex     INTEGER,
        axsVrfIpFwDest         IpAddress,
        axsVrfIpFwMask         IpAddress,
        axsVrfIpFwPolicy       INTEGER,
        axsVrfIpFwNextHop      IpAddress,
        axsVrfIpFwIfIndex      INTEGER,
        axsVrfIpFwType         INTEGER,
        axsVrfIpFwProto        INTEGER,
        axsVrfIpFwAge          INTEGER,
        axsVrfIpFwInfo         OBJECT IDENTIFIER,
        axsVrfIpFwNextHopAS    INTEGER,
        axsVrfIpFwMetric1      INTEGER,
        axsVrfIpFwMetric2      INTEGER,
        axsVrfIpFwMetric3      INTEGER,
        axsVrfIpFwMetric4      INTEGER,
        axsVrfIpFwMetric5      INTEGER,
        axsVrfIpFwDescr        DisplayString
    }

    axsVrfIpFwVRFIndex OBJECT-TYPE
        SYNTAX    INTEGER
        ACCESS    read-only
        STATUS    mandatory
        DESCRIPTION
                  "The index value which identifies VRF number."
        ::= { axsVrfIpFwEntry 1 }

    axsVrfIpFwDest OBJECT-TYPE
        SYNTAX    IpAddress
        ACCESS    read-only
        STATUS    mandatory
        DESCRIPTION
                  "The destination IP address of this route."
        ::= { axsVrfIpFwEntry 2 }

    axsVrfIpFwMask OBJECT-TYPE
        SYNTAX    IpAddress
        ACCESS    read-only
        STATUS    mandatory
        DESCRIPTION
                  "Indicate the mask to be logical-ANDed with the
                  destination address before being compared to
                  the value in the ipForwardDest field."
        ::= { axsVrfIpFwEntry 3 }

    axsVrfIpFwPolicy OBJECT-TYPE
        SYNTAX    INTEGER
        ACCESS    read-only
        STATUS    mandatory
        DESCRIPTION
                  "The general set of conditions that would cause
                  the selection of one multipath route (set of
                  next hops for a given destination) is referred
                  to as 'policy'."
        ::= { axsVrfIpFwEntry 4 }

    axsVrfIpFwNextHop OBJECT-TYPE
        SYNTAX    IpAddress
        ACCESS    read-only
        STATUS    mandatory
        DESCRIPTION
                  "On remote routes, the address of the next system en route."
        ::= { axsVrfIpFwEntry 5 }

    axsVrfIpFwIfIndex OBJECT-TYPE
        SYNTAX    INTEGER
        ACCESS    read-only
        STATUS    mandatory
        DESCRIPTION
                  "The ifIndex value which identifies the local
                  interface through which the next hop of this
                  route should be reached."
        ::= { axsVrfIpFwEntry 6 }

    axsVrfIpFwType OBJECT-TYPE
        SYNTAX    INTEGER{
                      other(1),   -- not specified by this MIB
                      invalid(2), -- logically deleted
                      local(3),   -- local interface
                      remote(4)   -- remote destination
                  }
        ACCESS    read-only
        STATUS    mandatory
        DESCRIPTION
                  "The type of route."
        ::= { axsVrfIpFwEntry 7 }

    axsVrfIpFwProto OBJECT-TYPE
        SYNTAX    INTEGER {
                      other(1),       -- not specified
                      local(2),       -- local interface
                      netmgmt(3),     -- static route
                      rip(8),         -- Berkeley RIP or RIP-II
                      ospf(13),       -- Open Shortest Path First
                      bgp(14)         -- Border Gateway Protocol
                  }
        ACCESS    read-only
        STATUS    mandatory
        DESCRIPTION
                  "The routing mechanism via which this route was
                  learned."
        ::= { axsVrfIpFwEntry 8 }

    axsVrfIpFwAge OBJECT-TYPE
        SYNTAX    INTEGER
        ACCESS    read-only
        STATUS    mandatory
        DESCRIPTION
                  "The number of seconds since this route was
                  last updated or otherwise determined to be
                  correct."
        ::= { axsVrfIpFwEntry 9 }

    axsVrfIpFwInfo OBJECT-TYPE
        SYNTAX    OBJECT IDENTIFIER
        ACCESS    read-only
        STATUS    mandatory
        DESCRIPTION
                  "A reference to MIB definitions specific to the
                  particular routing protocol which is responsible
                  for this route, as determined by the value
                  specified in the route's ipForwardProto value.
                  Its value be set to the OBJECT IDENTIFIER { 0 0 }."
        ::= { axsVrfIpFwEntry 10 }

    axsVrfIpFwNextHopAS OBJECT-TYPE
        SYNTAX    INTEGER
        ACCESS    read-only
        STATUS    mandatory
        DESCRIPTION
                  "The Autonomous System Number of the Next Hop."
        ::= { axsVrfIpFwEntry 11 }

    axsVrfIpFwMetric1 OBJECT-TYPE
        SYNTAX    INTEGER
        ACCESS    read-only
        STATUS    mandatory
        DESCRIPTION
                  "The primary routing metric for this route."
        ::= { axsVrfIpFwEntry 12 }

    axsVrfIpFwMetric2 OBJECT-TYPE
        SYNTAX    INTEGER
        ACCESS    read-only
        STATUS    mandatory
        DESCRIPTION
                  "An alternate routing metric for this route.
                  Its value is set to -1."
        ::= { axsVrfIpFwEntry 13 }

    axsVrfIpFwMetric3 OBJECT-TYPE
        SYNTAX    INTEGER
        ACCESS    read-only
        STATUS    mandatory
        DESCRIPTION
                  "An alternate routing metric for this route.
                  Its value is set to -1."
        ::= { axsVrfIpFwEntry 14 }

    axsVrfIpFwMetric4 OBJECT-TYPE
        SYNTAX    INTEGER
        ACCESS    read-only
        STATUS    mandatory
        DESCRIPTION
                  "An alternate routing metric for this route.
                  Its value is set to -1."
        ::= { axsVrfIpFwEntry 15 }

    axsVrfIpFwMetric5 OBJECT-TYPE
        SYNTAX    INTEGER
        ACCESS    read-only
        STATUS    mandatory
        DESCRIPTION
                  "An alternate routing metric for this route.
                  Its value is set to -1."
        ::= { axsVrfIpFwEntry 16 }

    axsVrfIpFwDescr OBJECT-TYPE
        SYNTAX    DisplayString
        ACCESS    read-only
        STATUS    mandatory
        DESCRIPTION
                  "The Description of VRF. The VRF identification which user setting."
        ::= { axsVrfIpFwEntry 17 }

    axsVrfIpv6AddrTable OBJECT-TYPE
        SYNTAX    SEQUENCE OF AxsVrfIpv6AddrEntry
        ACCESS    not-accessible
        STATUS    mandatory
        DESCRIPTION
                  "The table of addressing information relevant to
                  this node's interface IPv6 addresses per VRF."
        ::= { axsVrfIpv6 1 }

    axsVrfIpv6AddrEntry OBJECT-TYPE
        SYNTAX    AxsVrfIpv6AddrEntry
        ACCESS    not-accessible
        STATUS    mandatory
        DESCRIPTION
                  "The addressing information for one of this
                  entity's IPv6 addresses per VRF."
        INDEX { axsVrfIpv6AddrVrfIndex,
                axsVrfIpv6AddrIfIndex,
                axsVrfIpv6AddrAddress }
        ::= { axsVrfIpv6AddrTable 1 }

    AxsVrfIpv6AddrEntry ::= SEQUENCE {
        axsVrfIpv6AddrVrfIndex       INTEGER,
        axsVrfIpv6AddrIfIndex        INTEGER,
        axsVrfIpv6AddrAddress        Ipv6Address,
        axsVrfIpv6AddrPfxLength      INTEGER,
        axsVrfIpv6AddrType           INTEGER,
        axsVrfIpv6AddrAnycastFlag    TruthValue,
        axsVrfIpv6AddrStatus         INTEGER,
        axsVrfIpv6AddrDescr          DisplayString
    }

    axsVrfIpv6AddrVrfIndex OBJECT-TYPE
        SYNTAX    INTEGER
        ACCESS    read-only
        STATUS    mandatory
        DESCRIPTION
                  "The index value which identifies VRF number."
        ::= { axsVrfIpv6AddrEntry 1 }

    axsVrfIpv6AddrIfIndex OBJECT-TYPE
        SYNTAX    INTEGER
        ACCESS    read-only
        STATUS    mandatory
        DESCRIPTION
                  "The index value which uniquely identifies the
                  interface to which this entry is applicable."
        ::= { axsVrfIpv6AddrEntry 2 }

    axsVrfIpv6AddrAddress OBJECT-TYPE
        SYNTAX    Ipv6Address
        ACCESS    read-only
        STATUS    mandatory
        DESCRIPTION
                 "The IPv6 address to which this entry's addressing
                 information pertains."
        ::= { axsVrfIpv6AddrEntry 3 }

    axsVrfIpv6AddrPfxLength OBJECT-TYPE
        SYNTAX    INTEGER(0..128)
        ACCESS    read-only
        STATUS    mandatory
        DESCRIPTION
                  "The length of the prefix (in bits) associated with
                  the IPv6 address of this entry."
        ::= { axsVrfIpv6AddrEntry 4 }

    axsVrfIpv6AddrType OBJECT-TYPE
        SYNTAX    INTEGER {
                                     -- address has been formed
                                     -- using stateless
                      stateless(1),  -- autoconfiguration
                                     -- address has been acquired
                                     -- by stateful means
                                     -- (e.g. DHCPv6, manual
                      stateful(2),   -- configuration)
                                     -- type can not be determined
                      unknown(3)     -- for some reason.
                  }
        ACCESS    read-only
        STATUS    mandatory
        DESCRIPTION
                  "The type of address. Note that 'stateless(1)'
                  refers to an address that was statelessly
                  autoconfigured; 'stateful(2)' refers to a address
                  which was acquired by via a stateful protocol
                  (e.g. DHCPv6, manual configuration)."
        ::= { axsVrfIpv6AddrEntry 5 }

    axsVrfIpv6AddrAnycastFlag OBJECT-TYPE
        SYNTAX    TruthValue
        ACCESS    read-only
        STATUS    mandatory
        DESCRIPTION
                  "This object has the value 'true(1)', if this
                  address is an anycast address and the value
                  'false(2)' otherwise."
        ::= { axsVrfIpv6AddrEntry 6 }

    axsVrfIpv6AddrStatus OBJECT-TYPE
        SYNTAX    INTEGER {
                      preferred(1),
                      deprecated(2),
                      invalid(3),
                      inaccessible(4),
                      unknown(5)        -- status can not be determined
                                        -- for some reason.
                  }
        ACCESS    read-only
        STATUS    mandatory
        DESCRIPTION
                  "Address status.  The preferred(1) state indicates
                  that this is a valid address that can appear as
                  the destination or source address of a packet.
                  The deprecated(2) state indicates that this is
                  a valid but deprecated address that should no longer
                  be used as a source address in new communications,
                  but packets addressed to such an address are
                  processed as expected. The invalid(3) state indicates
                  that this is not valid address which should not
                  appear as the destination or source address of
                  a packet. The inaccessible(4) state indicates that
                  the address is not accessible because the interface
                  to which this address is assigned is not operational."
        ::= { axsVrfIpv6AddrEntry 7 }

    axsVrfIpv6AddrDescr OBJECT-TYPE
        SYNTAX    DisplayString
        ACCESS    read-only
        STATUS    mandatory
        DESCRIPTION
                  "The Description of VRF. The VRF identification which user setting."
        ::= { axsVrfIpv6AddrEntry 8 }

    axsVrfIpv6AddrPrefixTable OBJECT-TYPE
        SYNTAX    SEQUENCE OF AxsVrfIpv6AddrPrefixEntry
        ACCESS    not-accessible
        STATUS    mandatory
        DESCRIPTION
                  "The list of IPv6 address prefixes of
                  IPv6 interfaces."
        ::= { axsVrfIpv6 2 }

    axsVrfIpv6AddrPrefixEntry OBJECT-TYPE
        SYNTAX    AxsVrfIpv6AddrPrefixEntry
        ACCESS    not-accessible
        STATUS    mandatory
        DESCRIPTION
                  "An interface entry containing objects of
                  a particular IPv6 address prefix."
        INDEX { axsVrfIpv6AddrPrefixVrfIndex,
                axsVrfIpv6AddrPrefixIfIndex,
                axsVrfIpv6AddrPrefix,
                axsVrfIpv6AddrPrefixLength }
        ::= { axsVrfIpv6AddrPrefixTable 1 }

    AxsVrfIpv6AddrPrefixEntry ::= SEQUENCE {
        axsVrfIpv6AddrPrefixVrfIndex                INTEGER,
        axsVrfIpv6AddrPrefixIfIndex                 INTEGER,
        axsVrfIpv6AddrPrefix                        Ipv6AddressPrefix,
        axsVrfIpv6AddrPrefixLength                  INTEGER,
        axsVrfIpv6AddrPrefixOnLinkFlag              TruthValue,
        axsVrfIpv6AddrPrefixAutonomousFlag          TruthValue,
        axsVrfIpv6AddrPrefixAdvPreferredLifetime    Unsigned32,
        axsVrfIpv6AddrPrefixAdvValidLifetime        Unsigned32
    }

    axsVrfIpv6AddrPrefixVrfIndex OBJECT-TYPE
        SYNTAX    INTEGER
        ACCESS    not-accessible
        STATUS    mandatory
        DESCRIPTION
                  "The index value which identifies VRF number."
        ::= { axsVrfIpv6AddrPrefixEntry 1 }

    axsVrfIpv6AddrPrefixIfIndex OBJECT-TYPE
        SYNTAX    INTEGER
        ACCESS    not-accessible
        STATUS    mandatory
        DESCRIPTION
                  "The index value which uniquely identifies the
                  interface to which this entry is applicable."
        ::= { axsVrfIpv6AddrPrefixEntry 2 }

    axsVrfIpv6AddrPrefix OBJECT-TYPE
        SYNTAX    Ipv6AddressPrefix
        ACCESS    not-accessible
        STATUS    mandatory
        DESCRIPTION
                  "The prefix associated with the this interface."
        ::= { axsVrfIpv6AddrPrefixEntry 3 }

    axsVrfIpv6AddrPrefixLength OBJECT-TYPE
        SYNTAX    INTEGER (0..128)
        ACCESS    not-accessible
        STATUS    mandatory
        DESCRIPTION
                  "The length of the prefix (in bits)."
        ::= { axsVrfIpv6AddrPrefixEntry 4 }

    axsVrfIpv6AddrPrefixOnLinkFlag OBJECT-TYPE
        SYNTAX    TruthValue
        ACCESS    read-only
        STATUS    mandatory
        DESCRIPTION
                  "This object has the value 'true(1)', if this
                  prefix can be used  for on-link determination
                  and the value 'false(2)' otherwise."
        ::= { axsVrfIpv6AddrPrefixEntry 5 }

    axsVrfIpv6AddrPrefixAutonomousFlag OBJECT-TYPE
        SYNTAX    TruthValue
        ACCESS    read-only
        STATUS    mandatory
        DESCRIPTION
                  "Autonomous address configuration flag. When
                  true(1), indicates that this prefix can be used
                  for autonomous address configuration (i.e. can
                  be used to form a local interface address).
                  If false(2), it is not used to autoconfigure
                  a local interface address."
        ::= { axsVrfIpv6AddrPrefixEntry 6 }

    axsVrfIpv6AddrPrefixAdvPreferredLifetime OBJECT-TYPE
        SYNTAX    Unsigned32
        ACCESS    read-only
        STATUS    mandatory
        DESCRIPTION
                  "It is the length of time in seconds that this
                  prefix will remain preferred, i.e. time until
                  deprecation.  A value of 4,294,967,295 represents
                  infinity.

                  The address generated from a deprecated prefix
                  should no longer be used as a source address in
                  new communications, but packets received on such
                  an interface are processed as expected."
        ::= { axsVrfIpv6AddrPrefixEntry 7 }

    axsVrfIpv6AddrPrefixAdvValidLifetime OBJECT-TYPE
        SYNTAX    Unsigned32
        ACCESS    read-only
        STATUS    mandatory
        DESCRIPTION
                  "It is the length of time in seconds that this
                  prefix will remain valid, i.e. time until
                  invalidation.  A value of 4,294,967,295 represents
                  infinity.

                  The address generated from an invalidated prefix
                  should not appear as the destination or source
                  address of a packet."
        ::= { axsVrfIpv6AddrPrefixEntry 8 }

    axsVrfIpv6NetToMediaTable OBJECT-TYPE
        SYNTAX    SEQUENCE OF AxsVrfIpv6NetToMediaEntry
        ACCESS    not-accessible
        STATUS    mandatory
        DESCRIPTION
                  "The IPv6 Address Translation table used for
                  mapping from IPv6 addresses to physical addresses per VRF.

                  The IPv6 address translation table contain the
                  Ipv6Address to `physical' address equivalencies.
                  Some interfaces do not use translation tables
                  for determining address equivalencies; if all
                  interfaces are of this type, then the Address
                  Translation table is empty, i.e., has zero
                  entries."
        ::= { axsVrfIpv6 3 }

    axsVrfIpv6NetToMediaEntry OBJECT-TYPE
        SYNTAX    AxsVrfIpv6NetToMediaEntry
        ACCESS    not-accessible
        STATUS    mandatory
        DESCRIPTION
                  "Each entry contains one IPv6 address to `physical'
                  address equivalence per VRF."
        INDEX { axsVrfIpv6NetToMediaVrfIndex,
                axsVrfIpv6NetToMediaIfIndex,
                axsVrfIpv6NetToMediaNetAddress }
        ::= { axsVrfIpv6NetToMediaTable 1 }

    AxsVrfIpv6NetToMediaEntry ::= SEQUENCE {
        axsVrfIpv6NetToMediaVrfIndex         INTEGER,
        axsVrfIpv6NetToMediaIfIndex          INTEGER,
        axsVrfIpv6NetToMediaNetAddress       Ipv6Address,
        axsVrfIpv6NetToMediaPhysAddress      PhysAddress,
        axsVrfIpv6NetToMediaType             INTEGER,
        axsVrfIpv6IfNetToMediaState          INTEGER,
        axsVrfIpv6IfNetToMediaLastUpdated    TimeStamp,
        axsVrfIpv6NetToMediaValid            TruthValue,
        axsVrfIpv6NetToMediaDescr            DisplayString
    }

    axsVrfIpv6NetToMediaVrfIndex OBJECT-TYPE
        SYNTAX    INTEGER
        ACCESS    read-only
        STATUS    mandatory
        DESCRIPTION
                  "The index value which identifies VRF number."
        ::= { axsVrfIpv6NetToMediaEntry 1 }

    axsVrfIpv6NetToMediaIfIndex OBJECT-TYPE
        SYNTAX    INTEGER
        ACCESS    read-only
        STATUS    mandatory
        DESCRIPTION
                  "The index value which uniquely identifies the
                  interface to which this entry is applicable."
        ::= { axsVrfIpv6NetToMediaEntry 2 }

    axsVrfIpv6NetToMediaNetAddress OBJECT-TYPE
        SYNTAX    Ipv6Address
        ACCESS    read-only
        STATUS    mandatory
        DESCRIPTION
                  "The IPv6 Address corresponding to
                  the media-dependent `physical' address."
        ::= { axsVrfIpv6NetToMediaEntry 3 }

    axsVrfIpv6NetToMediaPhysAddress OBJECT-TYPE
        SYNTAX    PhysAddress
        ACCESS    read-only
        STATUS    mandatory
        DESCRIPTION
                  "The media-dependent `physical' address."
        ::= { axsVrfIpv6NetToMediaEntry 4 }

    axsVrfIpv6NetToMediaType OBJECT-TYPE
        SYNTAX    INTEGER {
                      other(1),    -- none of the following
                      dynamic(2),  -- dynamically resolved
                      static(3),   -- statically configured
                      local(4)     -- local interface
                  }
        ACCESS    read-only
        STATUS    mandatory
        DESCRIPTION
                  "The type of the mapping. The 'dynamic(2)' type
                  indicates that the IPv6 address to physical
                  addresses mapping has been dynamically
                  resolved using the IPv6 Neighbor Discovery
                  protocol. The static(3)' types indicates that
                  the mapping has been statically configured.
                  The local(4) indicates that the mapping is
                  provided for an entity's own interface address."
        ::= { axsVrfIpv6NetToMediaEntry 5 }

    axsVrfIpv6IfNetToMediaState OBJECT-TYPE
        SYNTAX    INTEGER {
                      reachable(1), -- confirmed reachability
                      stale(2),     -- unconfirmed reachability
                      delay(3),     -- waiting for reachability
                                    -- confirmation before entering
                                    -- the probe state
                      probe(4),     -- actively probing
                      invalid(5),   -- an invalidated mapping
                      unknown(6)    -- state can not be determined
                                    -- for some reason.
                  }
        ACCESS    read-only
        STATUS    mandatory
        DESCRIPTION
                  "The Neighbor Unreachability Detection [8] state
                  for the interface when the address mapping in
                  this entry is used."
        ::= { axsVrfIpv6NetToMediaEntry 6 }

    axsVrfIpv6IfNetToMediaLastUpdated OBJECT-TYPE
        SYNTAX    TimeStamp
        ACCESS    read-only
        STATUS    mandatory
        DESCRIPTION
                  "The value of sysUpTime at the time this entry
                  was last updated.  If this entry was updated prior
                  to the last re-initialization of the local network
                  management subsystem, then this object contains
                  a zero value."
        ::= { axsVrfIpv6NetToMediaEntry 7 }

    axsVrfIpv6NetToMediaValid OBJECT-TYPE
        SYNTAX    TruthValue
        ACCESS    read-only
        STATUS    mandatory
        DESCRIPTION
                  "Setting this object to the value 'false(2)' has
                  the effect of invalidating the corresponding entry
                  in the ipv6NetToMediaTable.  That is, it effectively
                  disassociates the interface identified with said
                  entry from the mapping identified with said entry.
                  It is an implementation-specific matter as to
                  whether the agent removes an invalidated entry
                  from the table.  Accordingly, management stations
                  must be prepared to receive tabular information
                  from agents that corresponds to entries not
                  currently in use.  Proper interpretation of such
                  entries requires examination of the relevant
                  ipv6NetToMediaValid object."
        ::= { axsVrfIpv6NetToMediaEntry 8 }

    axsVrfIpv6NetToMediaDescr OBJECT-TYPE
        SYNTAX    DisplayString
        ACCESS    read-only
        STATUS    mandatory
        DESCRIPTION
                  "The Description of VRF. The VRF identification which user setting."
        ::= { axsVrfIpv6NetToMediaEntry 9 }

    axsVrfIpv6FwNoTable OBJECT-TYPE
        SYNTAX    SEQUENCE OF AxsVrfIpv6FwNoEntry
        ACCESS    not-accessible
        STATUS    mandatory
        DESCRIPTION
                  "This entity's number of IPv6 Routing table about VRF."
        ::= { axsVrfIpv6Forward 1 }

    axsVrfIpv6FwNoEntry OBJECT-TYPE
        SYNTAX    AxsVrfIpv6FwNoEntry
        ACCESS    not-accessible
        STATUS    mandatory
        DESCRIPTION
                  "This entity's IPv6 Routing table about VRF."
        INDEX { axsVrfIpv6FwNoVRFIndex }
        ::= { axsVrfIpv6FwNoTable 1 }

    AxsVrfIpv6FwNoEntry ::= SEQUENCE {
        axsVrfIpv6FwNoVRFIndex    INTEGER,
        axsVrfIpv6FwNo            INTEGER,
        axsVrfIpv6FwNoDescr       DisplayString
    }

    axsVrfIpv6FwNoVRFIndex OBJECT-TYPE
        SYNTAX    INTEGER
        ACCESS    read-only
        STATUS    mandatory
        DESCRIPTION
                  "The index value which identifies VRF number."
        ::= { axsVrfIpv6FwNoEntry 1 }

    axsVrfIpv6FwNo OBJECT-TYPE
        SYNTAX    INTEGER
        ACCESS    read-only
        STATUS    mandatory
        DESCRIPTION
                  "The number of entry that is IPv6 Routing table."
        ::= { axsVrfIpv6FwNoEntry 2 }

    axsVrfIpv6FwNoDescr OBJECT-TYPE
        SYNTAX    DisplayString
        ACCESS    read-only
        STATUS    mandatory
        DESCRIPTION
                  "The Description of VRF. The VRF identification which user setting."
        ::= { axsVrfIpv6FwNoEntry 3 }

    axsVrfIpv6FwTable OBJECT-TYPE
        SYNTAX    SEQUENCE OF AxsVrfIpv6FwEntry
        ACCESS    not-accessible
        STATUS    mandatory
        DESCRIPTION
                  "This entity's IPv6 Routing table."
        ::= { axsVrfIpv6Forward 2 }

    axsVrfIpv6FwEntry OBJECT-TYPE
        SYNTAX    AxsVrfIpv6FwEntry
        ACCESS    not-accessible
        STATUS    mandatory
        DESCRIPTION
                  "A particular route to a particular destination,
                  under a particular policy."
        INDEX { axsVrfIpv6FwVrfIndex,
                axsVrfIpv6FwDest,
                axsVrfIpv6FwProto,
                axsVrfIpv6FwPolicy,
                axsVrfIpv6FwNextHop }
        ::= { axsVrfIpv6FwTable 1 }

    AxsVrfIpv6FwEntry ::= SEQUENCE {
        axsVrfIpv6FwVrfIndex     INTEGER,
        axsVrfIpv6FwDest         Ipv6Address,
        axsVrfIpv6FwPfxLength    INTEGER,
        axsVrfIpv6FwPolicy       INTEGER,
        axsVrfIpv6FwNextHop      Ipv6Address,
        axsVrfIpv6FwIfIndex      INTEGER,
        axsVrfIpv6FwType         INTEGER,
        axsVrfIpv6FwProto        INTEGER,
        axsVrfIpv6FwAge          INTEGER,
        axsVrfIpv6FwInfo         OBJECT IDENTIFIER,
        axsVrfIpv6FwNextHopAS    INTEGER,
        axsVrfIpv6FwMetric1      INTEGER,
        axsVrfIpv6FwMetric2      INTEGER,
        axsVrfIpv6FwMetric3      INTEGER,
        axsVrfIpv6FwMetric4      INTEGER,
        axsVrfIpv6FwMetric5      INTEGER,
        axsVrfIpv6FwDescr        DisplayString
    }

    axsVrfIpv6FwVrfIndex OBJECT-TYPE
        SYNTAX    INTEGER
        ACCESS    read-only
        STATUS    mandatory
        DESCRIPTION
                  "The index value which identifies VRF number."
        ::= { axsVrfIpv6FwEntry 1 }

    axsVrfIpv6FwDest OBJECT-TYPE
        SYNTAX    Ipv6Address
        ACCESS    read-only
        STATUS    mandatory
        DESCRIPTION
                  "The destination IPv6 address of this route."
        ::= { axsVrfIpv6FwEntry 2 }

    axsVrfIpv6FwPfxLength OBJECT-TYPE
        SYNTAX    INTEGER
        ACCESS    read-only
        STATUS    mandatory
        DESCRIPTION
                  "The length of the prefix (in bits) associated with
                  the IPv6 address of this entry."
        ::= { axsVrfIpv6FwEntry 3 }

    axsVrfIpv6FwPolicy OBJECT-TYPE
        SYNTAX    INTEGER
        ACCESS    read-only
        STATUS    mandatory
        DESCRIPTION
                  "The general set of conditions that would cause
                  the selection of one multipath route (set of
                  next hops for a given destination) is referred
                  to as 'policy'."
        ::= { axsVrfIpv6FwEntry 4 }

    axsVrfIpv6FwNextHop OBJECT-TYPE
        SYNTAX    Ipv6Address
        ACCESS    read-only
        STATUS    mandatory
        DESCRIPTION
                  "On remote routes, the address of the next system en route."
        ::= { axsVrfIpv6FwEntry 5 }

    axsVrfIpv6FwIfIndex OBJECT-TYPE
        SYNTAX    INTEGER
        ACCESS    read-only
        STATUS    mandatory
        DESCRIPTION
                  "The ifIndex value which identifies the local
                  interface through which the next hop of this
                  route should be reached."
        ::= { axsVrfIpv6FwEntry 6 }

    axsVrfIpv6FwType OBJECT-TYPE
        SYNTAX    INTEGER{
                      other(1),   -- not specified by this MIB
                      invalid(2), -- logically deleted
                      local(3),   -- local interface
                      remote(4)   -- remote destination
                  }
        ACCESS    read-only
        STATUS    mandatory
        DESCRIPTION
                  "The type of route."
        ::= { axsVrfIpv6FwEntry 7 }

    axsVrfIpv6FwProto OBJECT-TYPE
        SYNTAX    INTEGER {
                      other(1),       -- not specified
                      local(2),       -- local interface
                      netmgmt(3),     -- static route
                      rip(8),         -- Berkeley RIP or RIP-II
                      ospf(13),       -- Open Shortest Path First
                      bgp(14)         -- Border Gateway Protocol
                  }
        ACCESS    read-only
        STATUS    mandatory
        DESCRIPTION
                  "The routing mechanism via which this route was
                  learned."
        ::= { axsVrfIpv6FwEntry 8 }

    axsVrfIpv6FwAge OBJECT-TYPE
        SYNTAX    INTEGER
        ACCESS    read-only
        STATUS    mandatory
        DESCRIPTION
                  "The number of seconds since this route was
                  last updated or otherwise determined to be
                  correct."
        ::= { axsVrfIpv6FwEntry 9 }

    axsVrfIpv6FwInfo OBJECT-TYPE
        SYNTAX    OBJECT IDENTIFIER
        ACCESS    read-only
        STATUS    mandatory
        DESCRIPTION
                  "A reference to MIB definitions specific to the
                  particular routing protocol which is responsible
                  for this route, as determined by the value
                  specified in the route's axsVrfIpv6FwProto value.
                  Its value be set to the OBJECT IDENTIFIER { 0 0 }."
        ::= { axsVrfIpv6FwEntry 10 }

    axsVrfIpv6FwNextHopAS OBJECT-TYPE
        SYNTAX    INTEGER
        ACCESS    read-only
        STATUS    mandatory
        DESCRIPTION
                  "The Autonomous System Number of the Next Hop."
        ::= { axsVrfIpv6FwEntry 11 }

    axsVrfIpv6FwMetric1 OBJECT-TYPE
        SYNTAX    INTEGER
        ACCESS    read-only
        STATUS    mandatory
        DESCRIPTION
                  "The primary routing metric for this route."
        ::= { axsVrfIpv6FwEntry 12 }

    axsVrfIpv6FwMetric2 OBJECT-TYPE
        SYNTAX    INTEGER
        ACCESS    read-only
        STATUS    mandatory
        DESCRIPTION
                  "An alternate routing metric for this route.
                  Its value is set to -1."
        ::= { axsVrfIpv6FwEntry 13 }

    axsVrfIpv6FwMetric3 OBJECT-TYPE
        SYNTAX    INTEGER
        ACCESS    read-only
        STATUS    mandatory
        DESCRIPTION
                  "An alternate routing metric for this route.
                  Its value is set to -1."
        ::= { axsVrfIpv6FwEntry 14 }

    axsVrfIpv6FwMetric4 OBJECT-TYPE
        SYNTAX    INTEGER
        ACCESS    read-only
        STATUS    mandatory
        DESCRIPTION
                  "An alternate routing metric for this route.
                  Its value is set to -1."
        ::= { axsVrfIpv6FwEntry 15 }

    axsVrfIpv6FwMetric5 OBJECT-TYPE
        SYNTAX    INTEGER
        ACCESS    read-only
        STATUS    mandatory
        DESCRIPTION
                  "An alternate routing metric for this route.
                  Its value is set to -1."
        ::= { axsVrfIpv6FwEntry 16 }

    axsVrfIpv6FwDescr OBJECT-TYPE
        SYNTAX    DisplayString
        ACCESS    read-only
        STATUS    mandatory
        DESCRIPTION
                  "The Description of VRF. The VRF identification which user setting."
        ::= { axsVrfIpv6FwEntry 17 }

-- AX EoEVpnMonitor Group

    axsEoEVpnMonitorTable OBJECT-TYPE
        SYNTAX    SEQUENCE OF AxsEoEVpnMonitorEntry
        ACCESS    not-accessible
        STATUS    mandatory
        DESCRIPTION
                  "The Table of VPN statistical information."
        ::= { axsEoEVpnMonitor 1 }

    axsEoEVpnMonitorEntry OBJECT-TYPE
        SYNTAX    AxsEoEVpnMonitorEntry
        ACCESS    not-accessible
        STATUS    mandatory
        DESCRIPTION
                  "The Entry of VPN statistical information."
        INDEX { axsEoEVpnMonitorIndex }
        ::= { axsEoEVpnMonitorTable 1 }

    AxsEoEVpnMonitorEntry ::=SEQUENCE {
        axsEoEVpnMonitorIndex               INTEGER,
        axsEoEVpnMonitorStatus              INTEGER,
        axsEoEVpnMonitorEid                 INTEGER,
        axsEoEVpnMonitorVid                 INTEGER,
        axsEoEVpnMonitorIfIndex             InterfaceIndex,
        axsEoEVpnMonitorInPkts              Counter64,
        axsEoEVpnMonitorInOctets            Counter64,
        axsEoEVpnMonitorOutPkts             Counter64,
        axsEoEVpnMonitorOutOctets           Counter64,
        axsEoEVpnMonitorInDiscardPkts       Counter64,
        axsEoEVpnMonitorInDiscardOctets     Counter64,
        axsEoEVpnMonitorOutDiscardPkts      Counter64,
        axsEoEVpnMonitorOutDiscardOctets    Counter64
    }

    axsEoEVpnMonitorIndex OBJECT-TYPE
        SYNTAX    INTEGER
        ACCESS    read-only
        STATUS    mandatory
        DESCRIPTION
                  "Index that takes statistics of VPN."
        ::= { axsEoEVpnMonitorEntry 1 }

    axsEoEVpnMonitorStatus OBJECT-TYPE
        SYNTAX    INTEGER
        ACCESS    read-only
        STATUS    mandatory
        DESCRIPTION
                  "State of statistics of VPN. Active : 1 Inactive : 2"
        ::= { axsEoEVpnMonitorEntry 2 }

    axsEoEVpnMonitorEid OBJECT-TYPE
        SYNTAX    INTEGER
        ACCESS    read-only
        STATUS    mandatory
        DESCRIPTION
                  "EID of VPN."
        ::= { axsEoEVpnMonitorEntry 3 }

    axsEoEVpnMonitorVid OBJECT-TYPE
        SYNTAX    INTEGER
        ACCESS    read-only
        STATUS    mandatory
        DESCRIPTION
                  "VID of VPN."
        ::= { axsEoEVpnMonitorEntry 4 }

    axsEoEVpnMonitorIfIndex OBJECT-TYPE
        SYNTAX    InterfaceIndex
        ACCESS    read-only
        STATUS    mandatory
        DESCRIPTION
                  "Value of IfIndex in interface that takes statistics of VPN."
        ::= { axsEoEVpnMonitorEntry 5 }

    axsEoEVpnMonitorInPkts OBJECT-TYPE
        SYNTAX    Counter64
        ACCESS    read-only
        STATUS    mandatory
        DESCRIPTION
                  "Number of packets received on the interface that takes statistics of VPN."
        ::= { axsEoEVpnMonitorEntry 6 }

    axsEoEVpnMonitorInOctets OBJECT-TYPE
        SYNTAX    Counter64
        ACCESS    read-only
        STATUS    mandatory
        DESCRIPTION
                  "Number of octets received on the interface that takes statistics of VPN."
        ::= { axsEoEVpnMonitorEntry 7 }

    axsEoEVpnMonitorOutPkts OBJECT-TYPE
        SYNTAX    Counter64
        ACCESS    read-only
        STATUS    mandatory
        DESCRIPTION
                  "Number of packets transmitted out of the interface that takes statistics of VPN."
        ::= { axsEoEVpnMonitorEntry 8 }

    axsEoEVpnMonitorOutOctets OBJECT-TYPE
        SYNTAX    Counter64
        ACCESS    read-only
        STATUS    mandatory
        DESCRIPTION
                  "Number of octets transmitted out of the interface that takes statistics of VPN."
        ::= { axsEoEVpnMonitorEntry 9 }

    axsEoEVpnMonitorInDiscardPkts OBJECT-TYPE
        SYNTAX    Counter64
        ACCESS    read-only
        STATUS    mandatory
        DESCRIPTION
                  "Number of discarded packets received on the interface that takes statistics of VPN."
        ::= { axsEoEVpnMonitorEntry 10 }

    axsEoEVpnMonitorInDiscardOctets OBJECT-TYPE
        SYNTAX    Counter64
        ACCESS    read-only
        STATUS    mandatory
        DESCRIPTION
                  "Number of discarded octets received on the interface that takes statistics of VPN."
        ::= { axsEoEVpnMonitorEntry 11 }

    axsEoEVpnMonitorOutDiscardPkts OBJECT-TYPE
        SYNTAX    Counter64
        ACCESS    read-only
        STATUS    mandatory
        DESCRIPTION
                  "Number of discarded packets transmitted out of the interface that takes statistics of VPN."
        ::= { axsEoEVpnMonitorEntry 12 }

    axsEoEVpnMonitorOutDiscardOctets OBJECT-TYPE
        SYNTAX    Counter64
        ACCESS    read-only
        STATUS    mandatory
        DESCRIPTION
                  "Number of discarded octets transmitted out of the interface that takes statistics of VPN."
        ::= { axsEoEVpnMonitorEntry 13 }

-- OSPF General Variables

    axsOspfGeneralTable OBJECT-TYPE
        SYNTAX    SEQUENCE OF AxsOspfGeneralEntry
        ACCESS    not-accessible
        STATUS    mandatory
        DESCRIPTION
                  "The table of OSPF information."
        ::= { axsOspf 1 }

    axsOspfGeneralEntry OBJECT-TYPE
        SYNTAX    AxsOspfGeneralEntry
        ACCESS    not-accessible
        STATUS    mandatory
        DESCRIPTION
                  "The entry of OSPF information."
        INDEX     { axsOspfGeneralDomainNumber }
        ::= { axsOspfGeneralTable 1 }

    AxsOspfGeneralEntry ::= SEQUENCE {
        axsOspfGeneralDomainNumber    INTEGER,
        axsOspfRouterId               IpAddress,
        axsOspfAdminStat              INTEGER,
        axsOspfVersionNumber          INTEGER,
        axsOspfAreaBdrRtrStatus       INTEGER,
        axsOspfASBdrRtrStatus         INTEGER,
        axsOspfExternLsaCount         Gauge,
        axsOspfExternLsaCksumSum      INTEGER,
        axsOspfTOSSupport             INTEGER,
        axsOspfOriginateNewLsas       Counter,
        axsOspfRxNewLsas              Counter,
        axsOspfExtLsdbLimit           INTEGER,
        axsOspfMulticastExtensions    INTEGER
    }

    axsOspfGeneralDomainNumber OBJECT-TYPE
        SYNTAX    INTEGER
        ACCESS    read-only
        STATUS    mandatory
        DESCRIPTION
                  "Domain number in the Autonomous System."
        ::= { axsOspfGeneralEntry 1 }

    axsOspfRouterId OBJECT-TYPE
        SYNTAX    IpAddress
        ACCESS    read-only
        STATUS    mandatory
        DESCRIPTION
                  "A integer uniquely identifying the router
                  in the Autonomous System."
        ::= { axsOspfGeneralEntry 2 }

    axsOspfAdminStat OBJECT-TYPE
        SYNTAX    INTEGER   { 
                      enabled(1),
                      disabled(2)
                  }
        ACCESS    read-only
        STATUS    mandatory
        DESCRIPTION
                  "The  administrative  status  of  OSPF  in  the
                  router.  "
        ::= { axsOspfGeneralEntry 3 }

    axsOspfVersionNumber OBJECT-TYPE
        SYNTAX    INTEGER
        ACCESS    read-only
        STATUS    mandatory
        DESCRIPTION
                  "The current version number of the OSPF  
                  protocol is 2."
        ::= { axsOspfGeneralEntry 4 }

    axsOspfAreaBdrRtrStatus OBJECT-TYPE
        SYNTAX    INTEGER { 
                      true(1),
                      false(2)
                  }
        ACCESS    read-only
        STATUS    mandatory
        DESCRIPTION
                  "A flag to note whether this router is an  area
                  border router."
        ::= { axsOspfGeneralEntry 5 }

    axsOspfASBdrRtrStatus OBJECT-TYPE
        SYNTAX    INTEGER {
                      true(1),
                      false(2)
                  }
        ACCESS    read-only
        STATUS    mandatory
        DESCRIPTION
                  "A flag to note whether this router is  configured
                  as an Autonomous System border router."
        ::= { axsOspfGeneralEntry 6 }

    axsOspfExternLsaCount OBJECT-TYPE
        SYNTAX    Gauge
        ACCESS    read-only
        STATUS    mandatory
        DESCRIPTION
                  "The number of external (LS type 5)  link-state
                  advertisements in the link-state database."
        ::= { axsOspfGeneralEntry 7 }

    axsOspfExternLsaCksumSum OBJECT-TYPE
        SYNTAX    INTEGER
        ACCESS    read-only
        STATUS    mandatory
        DESCRIPTION
                  "The 32-bit unsigned sum of the LS checksums of
                  the  external  link-state  advertisements  contained
                  in the link-state  database."
        ::= { axsOspfGeneralEntry 8 }

    axsOspfTOSSupport OBJECT-TYPE
        SYNTAX    INTEGER {
                      true(1),
                      false(2)
                  }
        ACCESS    read-only
        STATUS    mandatory
        DESCRIPTION
                  "The router's support for type-of-service routing.
                   This value of false(2). "
        ::= { axsOspfGeneralEntry 9 }

    axsOspfOriginateNewLsas OBJECT-TYPE
        SYNTAX    Counter
        ACCESS    read-only
        STATUS    mandatory
        DESCRIPTION
                  "The number of  new  link-state  advertisements
                  that have been originated. "
        ::= { axsOspfGeneralEntry 10 }

    axsOspfRxNewLsas OBJECT-TYPE
        SYNTAX    Counter
        ACCESS    read-only
        STATUS    mandatory
        DESCRIPTION
                  "The number of  link-state  advertisements  received
                  determined  to  be  new instantiations."
        ::= { axsOspfGeneralEntry 11 }

    axsOspfExtLsdbLimit OBJECT-TYPE
        SYNTAX    INTEGER
        ACCESS    read-only
        STATUS    mandatory
        DESCRIPTION
                  "The maximum number of non-default AS-external-LSAs
                  entries that can be stored in the link-state database.
                  If the value is -1,  then there is no limit.
                  This value is -1"
        ::= { axsOspfGeneralEntry 12 }

    axsOspfMulticastExtensions OBJECT-TYPE
        SYNTAX    INTEGER
        ACCESS    read-only
        STATUS    mandatory
        DESCRIPTION
                  "A Bit Mask indicating whether  the  router  is
                  forwarding  IP  multicast  (Class  D) datagrams
                  based on the algorithms defined in  the  Multicast
                  Extensions to OSPF."
        ::= { axsOspfGeneralEntry 13 }

    axsOspfAreaTable OBJECT-TYPE
        SYNTAX    SEQUENCE OF AxsOspfAreaEntry
        ACCESS    not-accessible
        STATUS    mandatory
        DESCRIPTION
                  "The router's support for demand routing."
        ::= { axsOspf 2 }

    axsOspfAreaEntry OBJECT-TYPE
        SYNTAX    AxsOspfAreaEntry
        ACCESS    not-accessible
        STATUS    mandatory
        DESCRIPTION
                  "This entry contain ospf area information."
        INDEX     { axsOspfAreaDomainNumber,
                    axsOspfAreaId }
        ::= { axsOspfAreaTable 1 }

    AxsOspfAreaEntry ::= SEQUENCE {
        axsOspfAreaDomainNumber    INTEGER,
        axsOspfAreaId              IpAddress,
        axsOspfAuthType            INTEGER,
        axsOspfImportAsExtern      INTEGER,
        axsOspfSpfRuns             Counter,
        axsOspfAreaBdrRtrCount     Gauge,
        axsOspfAsBdrRtrCount       Gauge,
        axsOspfAreaLsaCount        Gauge,
        axsOspfAreaLsaCksumSum     INTEGER,
        axsOspfAreaSummary         INTEGER,
        axsOspfAreaStatus          INTEGER
    }

    axsOspfAreaDomainNumber OBJECT-TYPE
        SYNTAX    INTEGER
        ACCESS    read-only
        STATUS    mandatory
        DESCRIPTION
                  "An uniquely identifying number of domain."
        ::= { axsOspfAreaEntry 1 }

    axsOspfAreaId OBJECT-TYPE
        SYNTAX    IpAddress
        ACCESS    read-only
        STATUS    mandatory
        DESCRIPTION
                  "A 32-bit integer uniquely identifying an area."
        ::= { axsOspfAreaEntry 2 }

    axsOspfAuthType OBJECT-TYPE
        SYNTAX    INTEGER
                  -- none(0),
                  -- simplePassword(1),
                  -- md5(2)
        ACCESS    read-only
        STATUS    mandatory
        DESCRIPTION
                  "The authentication type specified for an area."
        ::= { axsOspfAreaEntry 3 }

    axsOspfImportAsExtern OBJECT-TYPE
        SYNTAX    INTEGER { 
                      importExternal(1),
                      importNoExternal(2),
                      importNssa(3)
                  }
        ACCESS    read-only
        STATUS    mandatory
        DESCRIPTION
                  "The area's support for importing  AS  external
                  link- state advertisements."
        ::= { axsOspfAreaEntry 4 }

    axsOspfSpfRuns OBJECT-TYPE
        SYNTAX    Counter
        ACCESS    read-only
        STATUS    mandatory
        DESCRIPTION
                  "The number of times that the intra-area  route
                  table  has  been  calculated  using this area's
                  link-state database."
        ::= { axsOspfAreaEntry 5 }

    axsOspfAreaBdrRtrCount OBJECT-TYPE
        SYNTAX    Gauge
        ACCESS    read-only
        STATUS    mandatory
        DESCRIPTION
                  "The total number of area border routers reachable
                  within this area."
        ::= { axsOspfAreaEntry 6 }

    axsOspfAsBdrRtrCount OBJECT-TYPE
        SYNTAX    Gauge
        ACCESS    read-only
        STATUS    mandatory
        DESCRIPTION
                  "The total number of AS area border routers reachable
                  within this area."
        ::= { axsOspfAreaEntry 7 }

    axsOspfAreaLsaCount OBJECT-TYPE
        SYNTAX    Gauge
        ACCESS    read-only
        STATUS    mandatory
        DESCRIPTION
                  "The total number of LSA(link-state  advertisements) 
                  in this area. Excluding AS External LSA's"
        ::= { axsOspfAreaEntry 8 }

    axsOspfAreaLsaCksumSum OBJECT-TYPE
        SYNTAX    INTEGER
        ACCESS    read-only
        STATUS    mandatory
        DESCRIPTION
                  "The sum of LSA's  LS  checksums  contained in this
                  area's link-state database."
        ::= { axsOspfAreaEntry 9 }

    axsOspfAreaSummary OBJECT-TYPE
        SYNTAX    INTEGER  {
                      noAreaSummary(1),
                      sendAreaSummary(2)
                  }
        ACCESS    read-only
        STATUS    mandatory
        DESCRIPTION
                  "he variable axsOspfAreaSummary controls the import
                  of summary LSAs into stub areas. Value is only 
                  sendAreaSummary(2)."
        ::= { axsOspfAreaEntry 10 }

    axsOspfAreaStatus OBJECT-TYPE
        SYNTAX    INTEGER {
                      active(1)
                  }
        ACCESS    read-only
        STATUS    mandatory
        DESCRIPTION
                  "This variable displays the status of  the  entry.
                  Value is only valid(1)."
        ::= { axsOspfAreaEntry 11 }

    axsOspfStubAreaTable OBJECT-TYPE
        SYNTAX    SEQUENCE OF AxsOspfStubAreaEntry
        ACCESS    not-accessible
        STATUS    mandatory
        DESCRIPTION
                  "The set of metrics that will be advertised  by
                  a default Area Border Router into a stub area."
        ::= { axsOspf 3 }

    axsOspfStubAreaEntry OBJECT-TYPE
        SYNTAX    AxsOspfStubAreaEntry
        ACCESS    not-accessible
        STATUS    mandatory
        DESCRIPTION
                  "The metric for a given Type  of  Service  that
                  will be advertised by a default Area Border Router 
                  into a stub area."
        INDEX     { axsOspfStubDomainNumber,
                    axsOspfStubAreaId,
                    axsOspfStubTOS }
        ::= { axsOspfStubAreaTable 1 }

    AxsOspfStubAreaEntry ::= SEQUENCE {
        axsOspfStubDomainNumber    INTEGER,
        axsOspfStubAreaId          IpAddress,
        axsOspfStubTOS             INTEGER,
        axsOspfStubMetric          INTEGER,
        axsOspfStubStatus          INTEGER,
        axsOspfStubMetricType      INTEGER
    }

    axsOspfStubDomainNumber OBJECT-TYPE
        SYNTAX    INTEGER
        ACCESS    read-only
        STATUS    mandatory
        DESCRIPTION
                  "The domain identifier for the Stub  Area."
        ::= { axsOspfStubAreaEntry 1 }

    axsOspfStubAreaId OBJECT-TYPE
        SYNTAX    IpAddress
        ACCESS    read-only
        STATUS    mandatory
        DESCRIPTION
                  "The identifier for the Stub  Area."
        ::= { axsOspfStubAreaEntry 2 }

    axsOspfStubTOS OBJECT-TYPE
        SYNTAX    INTEGER
        ACCESS    read-only
        STATUS    mandatory
        DESCRIPTION
                  "The Type of Service associated with the metric.
                  Value is only 0."
        ::= { axsOspfStubAreaEntry 3 }

    axsOspfStubMetric OBJECT-TYPE
        SYNTAX    INTEGER
        ACCESS    read-only
        STATUS    mandatory
        DESCRIPTION
                  "The metric value applied at the indicated type
                  of service."
        ::= { axsOspfStubAreaEntry 4 }

    axsOspfStubStatus OBJECT-TYPE
        SYNTAX    INTEGER {
                      active(1)
                  }
        ACCESS    read-only
        STATUS    mandatory
        DESCRIPTION
                  "This variable displays the status of the entry.
                  This value is only valid(1)."
        ::= { axsOspfStubAreaEntry 5 }

    axsOspfStubMetricType OBJECT-TYPE
        SYNTAX    INTEGER  {
                      ospfMetric(1),
                      comparableCost(2),
                      nonComparable(3)
                  }
        ACCESS    read-only
        STATUS    mandatory
        DESCRIPTION
                  "his variable displays the type of metric advertised
                  as a default route."
        ::= { axsOspfStubAreaEntry 6 }

    axsOspfLsdbTable OBJECT-TYPE
        SYNTAX    SEQUENCE OF AxsOspfLsdbEntry
        ACCESS    not-accessible
        STATUS    mandatory
        DESCRIPTION
                  "The OSPF Process's Link State Database."
        ::= { axsOspf 4 }

    axsOspfLsdbEntry OBJECT-TYPE
        SYNTAX    AxsOspfLsdbEntry
        ACCESS    not-accessible
        STATUS    mandatory
        DESCRIPTION
                   "A single Link State Advertisement."
        INDEX      { axsOspfLsdbDomainNumber,
                     axsOspfLsdbAreaId,
                     axsOspfLsdbType,
                     axsOspfLsdbLsid,
                     axsOspfLsdbRouterId }
        ::= { axsOspfLsdbTable 1 }

    AxsOspfLsdbEntry ::= SEQUENCE {
        axsOspfLsdbDomainNumber    INTEGER,
        axsOspfLsdbAreaId          IpAddress,
        axsOspfLsdbType            INTEGER,
        axsOspfLsdbLsid            IpAddress,
        axsOspfLsdbRouterId        IpAddress,
        axsOspfLsdbSequence        INTEGER,
        axsOspfLsdbAge             INTEGER,
        axsOspfLsdbChecksum        INTEGER,
        axsOspfLsdbAdvertisement   OCTET STRING
    }

    axsOspfLsdbDomainNumber OBJECT-TYPE
        SYNTAX    INTEGER
        ACCESS    read-only
        STATUS    mandatory
        DESCRIPTION
                  "The identifier of the domain from  which
                  the LSA was received."
        ::= { axsOspfLsdbEntry 1 }

    axsOspfLsdbAreaId OBJECT-TYPE
        SYNTAX    IpAddress
        ACCESS    read-only
        STATUS    mandatory
        DESCRIPTION
                  "The 32 bit identifier of the Area  from  which
                  the LSA was received."
        ::= { axsOspfLsdbEntry 2 }

    axsOspfLsdbType OBJECT-TYPE
        SYNTAX    INTEGER {
                       routerLink(1),
                       networkLink(2),
                       summaryLink(3),
                       asSummaryLink(4),
                       asExternalLink(5),  -- but see axsOspfExtLsdbTable
                       multicastLink(6),
                       nssaExternalLink(7)
                  }
        ACCESS    read-only
        STATUS    mandatory
        DESCRIPTION
                  "The type  of  the  link  state  advertisement."
        ::= { axsOspfLsdbEntry 3 }

    axsOspfLsdbLsid OBJECT-TYPE
        SYNTAX    IpAddress
        ACCESS    read-only
        STATUS    mandatory
        DESCRIPTION
                  "The Link State ID . It identifies the piece of the routing
                  domain that is being described by the advertisement."
        ::= { axsOspfLsdbEntry 4 }

    axsOspfLsdbRouterId OBJECT-TYPE
        SYNTAX    IpAddress
        ACCESS    read-only
        STATUS    mandatory
        DESCRIPTION
                  "The number that uniquely identifies the originating 
                  router in the Autonomous System."
        ::= { axsOspfLsdbEntry 5 }

    axsOspfLsdbSequence OBJECT-TYPE
        SYNTAX    INTEGER
        ACCESS    read-only
        STATUS    mandatory
        DESCRIPTION
                  "The sequence number field is a  signed  32-bit
                  integer."
        ::= { axsOspfLsdbEntry 6 }

    axsOspfLsdbAge OBJECT-TYPE
        SYNTAX    INTEGER
        ACCESS    read-only
        STATUS    mandatory
        DESCRIPTION
                  "This the age of the link state adver-
                  tisement in seconds."
        ::= { axsOspfLsdbEntry 7 }

    axsOspfLsdbChecksum OBJECT-TYPE
        SYNTAX    INTEGER
        ACCESS    read-only
        STATUS    mandatory
        DESCRIPTION
                  "This field is the  checksum  of  the  complete
                  contents  of  the  advertisement, excepting the
                  age field."
        ::= { axsOspfLsdbEntry 8 }

    axsOspfLsdbAdvertisement OBJECT-TYPE
        SYNTAX    OCTET STRING
        ACCESS    read-only
        STATUS    mandatory
        DESCRIPTION
                  "The entire Link State Advertisement, including
                  its header."
        ::= { axsOspfLsdbEntry 9 }

    axsOspfAreaRangeTable OBJECT-TYPE
        SYNTAX    SEQUENCE OF AxsOspfAreaRangeEntry
        ACCESS    not-accessible
        STATUS    mandatory
        DESCRIPTION
                  "A range if IP addresses  specified  by  an  IP
                  address/IP  network  mask  pair."
        ::= { axsOspf 5 }

    axsOspfAreaRangeEntry OBJECT-TYPE
        SYNTAX    AxsOspfAreaRangeEntry
        ACCESS    not-accessible
        STATUS    mandatory
        DESCRIPTION
                  "A range if IP addresses specified by an IP
                  address/IP network mask pair."
        INDEX { axsOspfAreaRangeDomainNumber,
                axsOspfAreaRangeAreaId,
                axsOspfAreaRangeNet }
        ::= { axsOspfAreaRangeTable 1 }

    AxsOspfAreaRangeEntry ::= SEQUENCE {
        axsOspfAreaRangeDomainNumber    INTEGER,
        axsOspfAreaRangeAreaId          IpAddress,
        axsOspfAreaRangeNet             IpAddress,
        axsOspfAreaRangeMask            IpAddress,
        axsOspfAreaRangeStatus          INTEGER,
        axsOspfAreaRangeEffect          INTEGER
    }

    axsOspfAreaRangeDomainNumber OBJECT-TYPE
        SYNTAX    INTEGER
        ACCESS    read-only
        STATUS    mandatory
        DESCRIPTION
                  "Domain number of the Area."
        ::= { axsOspfAreaRangeEntry 1 }

    axsOspfAreaRangeAreaId OBJECT-TYPE
        SYNTAX    IpAddress
        ACCESS    read-only
        STATUS    mandatory
        DESCRIPTION
                  "The Area the Address  Range  is  to  be  found
                  within."
        ::= { axsOspfAreaRangeEntry 2 }

    axsOspfAreaRangeNet OBJECT-TYPE
        SYNTAX    IpAddress
        ACCESS    read-only
        STATUS    mandatory
        DESCRIPTION
                  "The IP Address of the Net or Subnet  indicated
                  by the range."
        ::= { axsOspfAreaRangeEntry 3 }

    axsOspfAreaRangeMask OBJECT-TYPE
        SYNTAX    IpAddress
        ACCESS    read-only
        STATUS    mandatory
        DESCRIPTION
                  "The Subnet Mask that pertains to  the  Net  or
                  Subnet."
        ::= { axsOspfAreaRangeEntry 4 }

    axsOspfAreaRangeStatus OBJECT-TYPE
        SYNTAX    INTEGER    {
                      active(1),
                      inactive(2)
                  }
        ACCESS    read-only
        STATUS    mandatory
        DESCRIPTION
                  "This variable displays the status of  the  entry.
                  This value is only valid(1)."
        ::= { axsOspfAreaRangeEntry 5 }

    axsOspfAreaRangeEffect OBJECT-TYPE
        SYNTAX    INTEGER  {
                      advertiseMatching(1),
                      doNotAdvertiseMatching(2)
                  }
        ACCESS    read-only
        STATUS    mandatory
        DESCRIPTION
                  "Subnets subsumed by ranges either trigger  the
                  advertisement  of the indicated summary (adver-
                  tiseMatching), or result in  the  subnet's  not
                  being advertised at all outside the area."
        ::= { axsOspfAreaRangeEntry 6 }

    axsOspfIfTable OBJECT-TYPE
        SYNTAX    SEQUENCE OF AxsOspfIfEntry
        ACCESS    not-accessible
        STATUS    mandatory
        DESCRIPTION
                  "The OSPF Interface Table describes the interfaces
                  from the viewpoint of OSPF."
        ::= { axsOspf 7 }

    axsOspfIfEntry OBJECT-TYPE
        SYNTAX    AxsOspfIfEntry
        ACCESS    not-accessible
        STATUS    mandatory
        DESCRIPTION
                  "The OSPF Interface Entry describes one  interface
                  from the viewpoint of OSPF."
        INDEX     { axsOspfIfDomainNumber,
                    axsOspfIfIpAddress,
                    axsOspfAddressLessIf }
        ::= { axsOspfIfTable 1 }

    AxsOspfIfEntry ::= SEQUENCE {
        axsOspfIfDomainNumber              INTEGER,
        axsOspfIfIpAddress                 IpAddress,
        axsOspfAddressLessIf               INTEGER,
        axsOspfIfAreaId                    IpAddress,
        axsOspfIfType                      INTEGER,
        axsOspfIfAdminStat                 INTEGER,
        axsOspfIfRtrPriority               INTEGER,
        axsOspfIfTransitDelay              INTEGER,
        axsOspfIfRetransInterval           INTEGER,
        axsOspfIfHelloInterval             INTEGER,
        axsOspfIfRtrDeadInterval           INTEGER,
        axsOspfIfPollInterval              INTEGER,
        axsOspfIfState                     INTEGER,
        axsOspfIfDesignatedRouter          IpAddress,
        axsOspfIfEvents                    Counter,
        axsOspfIfAuthKey                   OCTET STRING,
        axsOspfIfStatus                    INTEGER,
        axsOspfIfMulticastForwarding       INTEGER,
        axsOspfIfBackupDesignatedRouter    IpAddress
    }

    axsOspfIfDomainNumber OBJECT-TYPE
        SYNTAX    INTEGER
        ACCESS    read-only
        STATUS    mandatory
        DESCRIPTION
                  "The domain number of this OSPF interface."
        ::= { axsOspfIfEntry 1 }

    axsOspfIfIpAddress OBJECT-TYPE
        SYNTAX    IpAddress
        ACCESS    read-only
        STATUS    mandatory
        DESCRIPTION
                  "The IP address of this OSPF interface."
        ::= { axsOspfIfEntry 2 }

    axsOspfAddressLessIf OBJECT-TYPE
        SYNTAX    INTEGER
        ACCESS    read-only
        STATUS    mandatory
        DESCRIPTION
                  "For the purpose of easing  the  instancing  of
                  addressed   and  addressless  interfaces;  This
                  variable takes the value 0 on  interfaces  with
                  IP  Addresses,  and  the corresponding value of
                  ifIndex for interfaces having no IP Address."
        ::= { axsOspfIfEntry 3 }

    axsOspfIfAreaId OBJECT-TYPE
        SYNTAX    IpAddress
        ACCESS    read-only
        STATUS    mandatory
        DESCRIPTION
                  "A integer uniquely identifying the area to which 
                  the interface connects."
        ::= { axsOspfIfEntry 4 }

    axsOspfIfType OBJECT-TYPE
        SYNTAX    INTEGER  {
                       broadcast(1),
                       nbma (2),
                       pointToPoint(3),
                       pointToMultipoint(5)
                  }
        ACCESS    read-only
        STATUS    mandatory
        DESCRIPTION
                  "The OSPF interface type."
        ::= { axsOspfIfEntry 5 }

    axsOspfIfAdminStat OBJECT-TYPE
        SYNTAX    INTEGER { 
                      enabled(1),
                      disabled(2)
                  }
        ACCESS    read-only
        STATUS    mandatory
        DESCRIPTION
                  "The OSPF  interface's  administrative  status."
        ::= { axsOspfIfEntry 6 }

    axsOspfIfRtrPriority OBJECT-TYPE
        SYNTAX    INTEGER
        ACCESS    read-only
        STATUS    mandatory
        DESCRIPTION
                  "The priority of this interface."
        ::= { axsOspfIfEntry 7 }

    axsOspfIfTransitDelay OBJECT-TYPE
        SYNTAX    INTEGER
        ACCESS    read-only
        STATUS    mandatory
        DESCRIPTION
                  "The estimated number of seconds  it  takes  to
                  transmit  a  link state update packet over this
                  interface."
        ::= { axsOspfIfEntry 8 }

    axsOspfIfRetransInterval OBJECT-TYPE
        SYNTAX    INTEGER
        ACCESS    read-only
        STATUS    mandatory
        DESCRIPTION
                  "The number of seconds between link-state ad-
                  vertisement retransmissions, for adjacencies
                  belonging to this  interface."
        ::= { axsOspfIfEntry 9 }

    axsOspfIfHelloInterval OBJECT-TYPE
        SYNTAX    INTEGER
        ACCESS    read-only
        STATUS    mandatory
        DESCRIPTION
                  "The length of time, in  seconds,  between the
                  Hello  packets that the router sends on the interface."
        ::= { axsOspfIfEntry 10 }

    axsOspfIfRtrDeadInterval OBJECT-TYPE
        SYNTAX  INTEGER
        ACCESS  read-only
        STATUS  mandatory
        DESCRIPTION
            "The number of seconds that  a  router's  Hello
            packets  have  not been seen before it's neighbors 
            declare the router down."
        ::= { axsOspfIfEntry 11 }

    axsOspfIfPollInterval OBJECT-TYPE
        SYNTAX  INTEGER
        ACCESS  read-only
        STATUS  mandatory
        DESCRIPTION
            "The larger time interval, in seconds,  between
            the  Hello  packets  sent  to  an inactive non-
            broadcast multi- access neighbor."
        ::= { axsOspfIfEntry 12 }

    axsOspfIfState OBJECT-TYPE
        SYNTAX    INTEGER {
                      down(1),
                      loopback(2),
                      waiting(3),
                      pointToPoint(4),
                      designatedRouter(5),
                      backupDesignatedRouter(6),
                      otherDesignatedRouter(7)
                  }
        ACCESS    read-only
        STATUS    mandatory
        DESCRIPTION
            "The OSPF Interface State."
        ::= { axsOspfIfEntry 13 }

    axsOspfIfDesignatedRouter OBJECT-TYPE
        SYNTAX    IpAddress
        ACCESS    read-only
        STATUS    mandatory
        DESCRIPTION
                  "The IP Address of the Designated Router."
        ::= { axsOspfIfEntry 14 }

    axsOspfIfEvents OBJECT-TYPE
        SYNTAX    Counter
        ACCESS    read-only
        STATUS    mandatory
        DESCRIPTION
                  "The number of times this  OSPF  interface  has
                  changed its state, or an error has occurred."
        ::= { axsOspfIfEntry 16 }

    axsOspfIfAuthKey OBJECT-TYPE
        SYNTAX    OCTET STRING
        ACCESS    read-only
        STATUS    mandatory
        DESCRIPTION
                  "The Authentication Key."
        ::= { axsOspfIfEntry 17 }

    axsOspfIfStatus OBJECT-TYPE
        SYNTAX    INTEGER   { 
                      active(1),
                      inactive(2)
                  }
        ACCESS    read-only
        STATUS    mandatory
        DESCRIPTION
                  "This variable displays the status of  the  entry.
                  this value is only valid(1)."
        ::= { axsOspfIfEntry 18 }

    axsOspfIfMulticastForwarding OBJECT-TYPE
        SYNTAX    INTEGER  {
                      blocked(1),   -- no multicast forwarding
                      multicast(2), -- using multicast address
                      unicast(3)    -- to each OSPF neighbor
                  }
        ACCESS    read-only
        STATUS    mandatory
        DESCRIPTION
                  "The way multicasts should  forwarded  on  this
                  interface;  not  forwarded,  forwarded  as data
                  link multicasts, or forwarded as data link unicasts."
        ::= { axsOspfIfEntry 19 }

    axsOspfIfBackupDesignatedRouter OBJECT-TYPE
        SYNTAX    IpAddress
        ACCESS    read-only
        STATUS    mandatory
        DESCRIPTION
                  "The IP Address of the Backup Designated Router."
        ::= { axsOspfIfEntry 15 }

    axsOspfIfMetricTable OBJECT-TYPE
        SYNTAX    SEQUENCE OF AxsOspfIfMetricEntry
        ACCESS    not-accessible
        STATUS    mandatory
        DESCRIPTION
                  "The TOS metrics for a non-virtual interface identified
                  by the interface index."
        ::= { axsOspf 8 }

    axsOspfIfMetricEntry OBJECT-TYPE
        SYNTAX    AxsOspfIfMetricEntry
        ACCESS    not-accessible
        STATUS    mandatory
        DESCRIPTION
                  "A particular TOS metric for a non-virtual interface
                  identified by the interface index."
        INDEX { axsOspfIfMetricDomainNumber,
                axsOspfIfMetricIpAddress,
                axsOspfIfMetricAddressLessIf,
                axsOspfIfMetricTOS }
        ::= { axsOspfIfMetricTable 1 }

    AxsOspfIfMetricEntry ::= SEQUENCE {
        axsOspfIfMetricDomainNumber     INTEGER,
        axsOspfIfMetricIpAddress        IpAddress,
        axsOspfIfMetricAddressLessIf    INTEGER,
        axsOspfIfMetricTOS              INTEGER,
        axsOspfIfMetricValue            INTEGER,
        axsOspfIfMetricStatus           INTEGER
    }

    axsOspfIfMetricDomainNumber OBJECT-TYPE
        SYNTAX    INTEGER
        ACCESS    read-only
        STATUS    mandatory
        DESCRIPTION
                  "The domain number of this OSPF interface."
        ::= { axsOspfIfMetricEntry 1 }

    axsOspfIfMetricIpAddress OBJECT-TYPE
        SYNTAX    IpAddress
        ACCESS    read-only
        STATUS    mandatory
        DESCRIPTION
                  "The IP address of this OSPF interface."
        ::= { axsOspfIfMetricEntry 2 }

    axsOspfIfMetricAddressLessIf OBJECT-TYPE
        SYNTAX    INTEGER
        ACCESS    read-only
        STATUS    mandatory
        DESCRIPTION
                  "For the purpose of easing  the  instancing  of
                  addressed   and  addressless  interfaces;  This
                  variable takes the value 0 on  interfaces  with
                  IP  Addresses, and the value of ifIndex for in-
                  terfaces having no IP Address."
        ::= { axsOspfIfMetricEntry 3 }

    axsOspfIfMetricTOS OBJECT-TYPE
        SYNTAX    INTEGER
        ACCESS    read-only
        STATUS    mandatory
        DESCRIPTION
                  "The type of service metric  being  referenced.
                  this value is only 0."
        ::= { axsOspfIfMetricEntry 4 }

    axsOspfIfMetricValue OBJECT-TYPE
        SYNTAX    INTEGER
        ACCESS    read-only
        STATUS    mandatory
        DESCRIPTION
                  "The metric of using this type  of  service  on
                  this interface."
        ::= { axsOspfIfMetricEntry 5 }

    axsOspfIfMetricStatus OBJECT-TYPE
        SYNTAX    INTEGER {
                      active(1)
                  }
        ACCESS    read-only
        STATUS    mandatory
        DESCRIPTION
                  "This variable displays the status of the entry.
                  This entry status is only valid(1)."
        ::= { axsOspfIfMetricEntry 6 }

    axsOspfVirtIfTable OBJECT-TYPE
        SYNTAX    SEQUENCE OF AxsOspfVirtIfEntry
        ACCESS    not-accessible
        STATUS    mandatory
        DESCRIPTION
                  "Information about this router's virtual interfaces."
        ::= { axsOspf 9 }

    axsOspfVirtIfEntry OBJECT-TYPE
        SYNTAX    AxsOspfVirtIfEntry
        ACCESS    not-accessible
        STATUS    mandatory
        DESCRIPTION
                  "Information about a single Virtual Interface."
        INDEX     { axsOspfVirtIfDomainNumber,
                    axsOspfVirtIfAreaId,
                    axsOspfVirtIfNeighbor }
        ::= { axsOspfVirtIfTable 1 }

    AxsOspfVirtIfEntry ::= SEQUENCE {
        axsOspfVirtIfDomainNumber       INTEGER,
        axsOspfVirtIfAreaId             IpAddress,
        axsOspfVirtIfNeighbor           IpAddress,
        axsOspfVirtIfTransitDelay       INTEGER,
        axsOspfVirtIfRetransInterval    INTEGER,
        axsOspfVirtIfHelloInterval      INTEGER,
        axsOspfVirtIfRtrDeadInterval    INTEGER,
        axsOspfVirtIfState              INTEGER,
        axsOspfVirtIfEvents             Counter,
        axsOspfVirtIfAuthKey            OCTET STRING,
        axsOspfVirtIfStatus             INTEGER
    }

    axsOspfVirtIfDomainNumber OBJECT-TYPE
        SYNTAX    INTEGER
        ACCESS    read-only
        STATUS    mandatory
        DESCRIPTION
                  "The domain number for this  Virtual Interface"
        ::= { axsOspfVirtIfEntry 1 }

    axsOspfVirtIfAreaId OBJECT-TYPE
        SYNTAX    IpAddress
        ACCESS    read-only
        STATUS    mandatory
        DESCRIPTION
                  "The Transit Area that the Virtual Link traverses."
        ::= { axsOspfVirtIfEntry 2 }

    axsOspfVirtIfNeighbor OBJECT-TYPE
        SYNTAX    IpAddress
        ACCESS    read-only
        STATUS    mandatory
        DESCRIPTION
                  "The Router ID of the Virtual Neighbor."
        ::= { axsOspfVirtIfEntry 3 }

    axsOspfVirtIfTransitDelay OBJECT-TYPE
        SYNTAX    INTEGER
        ACCESS    read-only
        STATUS    mandatory
        DESCRIPTION
                  "The estimated number of seconds  it  takes  to
                  transmit  a link- state update packet over this
                  interface."
        ::= { axsOspfVirtIfEntry 4 }

    axsOspfVirtIfRetransInterval OBJECT-TYPE
        SYNTAX    INTEGER
        ACCESS    read-only
        STATUS    mandatory
        DESCRIPTION
                  "The number of seconds between link-state advertisement
                  retransmissions, for adjacencies belonging to this
                  interface."
        ::= { axsOspfVirtIfEntry 5 }

    axsOspfVirtIfHelloInterval OBJECT-TYPE
        SYNTAX    INTEGER
        ACCESS    read-only
        STATUS    mandatory
        DESCRIPTION
                  "The length of time, in  seconds, between the
                  Hello  packets that the router sends on the in-
                  terface. "
        ::= { axsOspfVirtIfEntry 6 }

    axsOspfVirtIfRtrDeadInterval OBJECT-TYPE
        SYNTAX    INTEGER
        ACCESS    read-only
        STATUS    mandatory
        DESCRIPTION
                  "The number of seconds that  a  router's  Hello
                  packets  have  not been seen before it's neighbors
                  declare the router down."
        ::= { axsOspfVirtIfEntry 7 }

    axsOspfVirtIfState OBJECT-TYPE
        SYNTAX    INTEGER {
                      down(1),        -- these use the same encoding
                      pointToPoint(4) -- as the axsOspfIfTable
                  }
        ACCESS    read-only
        STATUS    mandatory
        DESCRIPTION
                  "OSPF virtual interface states."
        ::= { axsOspfVirtIfEntry 8 }

    axsOspfVirtIfEvents OBJECT-TYPE
        SYNTAX    Counter
        ACCESS    read-only
        STATUS    mandatory
        DESCRIPTION
                  "The number of state changes or error events on
                  this Virtual Link"
        ::= { axsOspfVirtIfEntry 9 }

    axsOspfVirtIfAuthKey OBJECT-TYPE
        SYNTAX    OCTET STRING
        ACCESS    read-only
        STATUS    mandatory
        DESCRIPTION
                  "Authentication key of this interface."
        ::= { axsOspfVirtIfEntry 10 }

    axsOspfVirtIfStatus OBJECT-TYPE
        SYNTAX    INTEGER { 
                      active(1),
                      inactive(2)
                  }
        ACCESS    read-only
        STATUS    mandatory
        DESCRIPTION
                  "This variable displays the status of  the  entry.
                  This entry is only valid(1)."
        ::= { axsOspfVirtIfEntry 11 }

    axsOspfNbrTable OBJECT-TYPE
        SYNTAX    SEQUENCE OF AxsOspfNbrEntry
        ACCESS    not-accessible
        STATUS    mandatory
        DESCRIPTION
                  "A table of non-virtual neighbor information."
        ::= { axsOspf 10 }

    axsOspfNbrEntry OBJECT-TYPE
        SYNTAX    AxsOspfNbrEntry
        ACCESS    not-accessible
        STATUS    mandatory
        DESCRIPTION
                  "The information regarding a single neighbor."
        INDEX     { axsOspfNbrDomainNumber,
                    axsOspfNbrIpAddr,
                    axsOspfNbrAddressLessIndex }
        ::= { axsOspfNbrTable 1 }

    AxsOspfNbrEntry ::= SEQUENCE {
        axsOspfNbrDomainNumber        INTEGER,
        axsOspfNbrIpAddr              IpAddress,
        axsOspfNbrAddressLessIndex    INTEGER,
        axsOspfNbrRtrId               IpAddress,
        axsOspfNbrOptions             INTEGER,
        axsOspfNbrPriority            INTEGER,
        axsOspfNbrState               INTEGER,
        axsOspfNbrEvents              Counter,
        axsOspfNbrLsRetransQLen       Gauge,
        axsOspfNbmaNbrStatus          INTEGER,
        axsOspfNbmaNbrPermanence      INTEGER
    }

    axsOspfNbrDomainNumber OBJECT-TYPE
        SYNTAX    INTEGER
        ACCESS    read-only
        STATUS    mandatory
        DESCRIPTION
                  "OSPF domain number of this neighbor."
        ::= { axsOspfNbrEntry 1 }

    axsOspfNbrIpAddr OBJECT-TYPE
        SYNTAX    IpAddress
        ACCESS    read-only
        STATUS    mandatory
        DESCRIPTION
                  "The IP address this neighbor is using  in  its
                  IP  Source  Address."
        ::= { axsOspfNbrEntry 2 }

    axsOspfNbrAddressLessIndex OBJECT-TYPE
        SYNTAX    INTEGER
        ACCESS    read-only
        STATUS    mandatory
        DESCRIPTION
                  "On an interface having an  IP  Address,  zero.
                  On  addressless  interfaces,  the corresponding
                  value of ifIndex in the Internet Standard  MIB."
        ::= { axsOspfNbrEntry 3 }

    axsOspfNbrRtrId OBJECT-TYPE
        SYNTAX    IpAddress
        ACCESS    read-only
        STATUS    mandatory
        DESCRIPTION
                  "The integer uniquely identifying the neighboring
                  router in the Autonomous System."
        ::= { axsOspfNbrEntry 4 }

    axsOspfNbrOptions OBJECT-TYPE
        SYNTAX    INTEGER
        ACCESS    read-only
        STATUS    mandatory
        DESCRIPTION
                  "A Bit Mask corresponding to the neighbor's op-
                  tions field.

                  Bit 0, if set, indicates that the  system  will
                  operate  on  Type of Service metrics other than
                  TOS 0.  If zero, the neighbor will  ignore  all
                  metrics except the TOS 0 metric.

                  Bit 1, if set, indicates  that  the  associated
                  area  accepts and operates on external informa-
                  tion; if zero, it is a stub area.

                  Bit 2, if set, indicates that the system is ca-
                  pable  of routing IP Multicast datagrams; i.e.,
                  that it implements the Multicast Extensions  to
                  OSPF.

                  Bit 3, if set, indicates  that  the  associated
                  area  is  an  NSSA.  These areas are capable of
                  carrying type 7 external advertisements,  which
                  are  translated into type 5 external advertise-
                  ments at NSSA borders."
        ::= { axsOspfNbrEntry 5 }

    axsOspfNbrPriority OBJECT-TYPE
        SYNTAX    INTEGER
        ACCESS    read-only
        STATUS    mandatory
        DESCRIPTION
                  "The priority of this neighbor."
        ::= { axsOspfNbrEntry 6 }

    axsOspfNbrState OBJECT-TYPE
        SYNTAX    INTEGER {
                      down(1),
                      attempt(2),
                      init(3),
                      twoWay(4),
                      exchangeStart(5),
                      exchange(6),
                      loading(7),
                      full(8)
                  }
        ACCESS    read-only
        STATUS    mandatory
        DESCRIPTION
                  "The State of the relationship with this Neighbor."
        ::= { axsOspfNbrEntry 7 }

    axsOspfNbrEvents OBJECT-TYPE
        SYNTAX    Counter
        ACCESS    read-only
        STATUS    mandatory
        DESCRIPTION
                  "The number of times this neighbor relationship
                  has changed state, or an error has occurred."
        ::= { axsOspfNbrEntry 8 }

    axsOspfNbrLsRetransQLen OBJECT-TYPE
        SYNTAX    Gauge
        ACCESS    read-only
        STATUS    mandatory
        DESCRIPTION
                  "The current length of the retransmission queue."
        ::= { axsOspfNbrEntry 9 }

    axsOspfNbmaNbrStatus OBJECT-TYPE
        SYNTAX    INTEGER {
                      active(1)
                  }
        ACCESS    read-only
        STATUS    mandatory
        DESCRIPTION
                  "This variable displays the status of the entry.
                  This entry value is only valid(1). And enable to response
                  this entry when axsOspfIfType is nbma."
        ::= { axsOspfNbrEntry 10 }

    axsOspfNbmaNbrPermanence OBJECT-TYPE
        SYNTAX    INTEGER  {
                      dynamic(1),  -- learned through protocol
                      permanent(2) -- configured address
                  }
        ACCESS    read-only
        STATUS    mandatory
        DESCRIPTION
                  "This variable displays the status of the entry."
        ::= { axsOspfNbrEntry 11 }

    axsOspfVirtNbrTable OBJECT-TYPE
        SYNTAX    SEQUENCE OF AxsOspfVirtNbrEntry
        ACCESS    not-accessible
        STATUS    mandatory
        DESCRIPTION
                  "A table of virtual neighbor information."
        ::= { axsOspf 11 }

    axsOspfVirtNbrEntry OBJECT-TYPE
        SYNTAX    AxsOspfVirtNbrEntry
        ACCESS    not-accessible
        STATUS    mandatory
        DESCRIPTION
                  "Virtual neighbor information."
        INDEX     { axsOspfVirtNbrDomainNumber,
                    axsOspfVirtNbrArea,
                    axsOspfVirtNbrRtrId }
        ::= { axsOspfVirtNbrTable 1 }

    AxsOspfVirtNbrEntry ::= SEQUENCE {
        axsOspfVirtNbrDomainNumber     INTEGER,
        axsOspfVirtNbrArea             IpAddress,
        axsOspfVirtNbrRtrId            IpAddress,
        axsOspfVirtNbrIpAddr           IpAddress,
        axsOspfVirtNbrOptions          INTEGER,
        axsOspfVirtNbrState            INTEGER,
        axsOspfVirtNbrEvents           Counter,
        axsOspfVirtNbrLsRetransQLen    Gauge
    }

    axsOspfVirtNbrDomainNumber OBJECT-TYPE
        SYNTAX    INTEGER
        ACCESS    read-only
        STATUS    mandatory
        DESCRIPTION
                  "The domain number."
        ::= { axsOspfVirtNbrEntry 1 }

    axsOspfVirtNbrArea OBJECT-TYPE
        SYNTAX    IpAddress
        ACCESS    read-only
        STATUS    mandatory
        DESCRIPTION
                  "The Transit Area Identifier."
        ::= { axsOspfVirtNbrEntry 2 }

    axsOspfVirtNbrRtrId OBJECT-TYPE
        SYNTAX    IpAddress
        ACCESS    read-only
        STATUS    mandatory
        DESCRIPTION
                  "A integer  uniquely  identifying  the neighboring
                  router in the Autonomous System."
        ::= { axsOspfVirtNbrEntry 3 }

    axsOspfVirtNbrIpAddr OBJECT-TYPE
        SYNTAX    IpAddress
        ACCESS    read-only
        STATUS    mandatory
        DESCRIPTION
                  "The IP address this Virtual Neighbor is using."
        ::= { axsOspfVirtNbrEntry 4 }

    axsOspfVirtNbrOptions OBJECT-TYPE
        SYNTAX    INTEGER
        ACCESS    read-only
        STATUS    mandatory
        DESCRIPTION
                  "A Bit Mask corresponding to the neighbor's options
                  field.

                  Bit 1, if set, indicates that the  system  will operate
                  on Type of Service metrics other than TOS 0. If zero,
                  the neighbor will  ignore  all metrics except the TOS
                  0 metric.

                  Bit 2, if set, indicates  that  the  system  is Network
                  Multicast  capable; ie, that it implements OSPF Multicast
                  Routing."
        ::= { axsOspfVirtNbrEntry 5 }

    axsOspfVirtNbrState OBJECT-TYPE
        SYNTAX    INTEGER {
                      down(1),
                      attempt(2),
                      init(3),
                      twoWay(4),
                      exchangeStart(5),
                      exchange(6),
                      loading(7),
                      full(8)
                  }
        ACCESS    read-only
        STATUS    mandatory
        DESCRIPTION
                  "The state of the  Virtual  Neighbor  Relationship."
        ::= { axsOspfVirtNbrEntry 6 }

    axsOspfVirtNbrEvents OBJECT-TYPE
        SYNTAX    Counter
        ACCESS    read-only
        STATUS    mandatory
        DESCRIPTION
                  "The number of times this virtual link has changed
                  its state, or an error has occurred."
        ::= { axsOspfVirtNbrEntry 7 }

    axsOspfVirtNbrLsRetransQLen OBJECT-TYPE
        SYNTAX    Gauge
        ACCESS    read-only
        STATUS    mandatory
        DESCRIPTION
                  "The current length of the retransmission queue."
        ::= { axsOspfVirtNbrEntry 8 }

    axsOspfExtLsdbTable OBJECT-TYPE
        SYNTAX    SEQUENCE OF AxsOspfExtLsdbEntry
        ACCESS    not-accessible
        STATUS    mandatory
        DESCRIPTION
                  "The OSPF Process's Links State Database."
        ::= { axsOspf 12 }

    axsOspfExtLsdbEntry OBJECT-TYPE
        SYNTAX    AxsOspfExtLsdbEntry
        ACCESS    not-accessible
        STATUS    mandatory
        DESCRIPTION
                  "A single Link State Advertisement."
        INDEX     { axsOspfExtLsdbDomainNumber,
                    axsOspfExtLsdbType,
                    axsOspfExtLsdbLsid,
                    axsOspfExtLsdbRouterId }
        ::= { axsOspfExtLsdbTable 1 }

    AxsOspfExtLsdbEntry ::= SEQUENCE {
        axsOspfExtLsdbDomainNumber    INTEGER,
        axsOspfExtLsdbType            INTEGER,
        axsOspfExtLsdbLsid            IpAddress,
        axsOspfExtLsdbRouterId        IpAddress,
        axsOspfExtLsdbSequence        INTEGER,
        axsOspfExtLsdbAge             INTEGER,
        axsOspfExtLsdbChecksum        INTEGER,
        axsOspfExtLsdbAdvertisement   OCTET STRING
    }

    axsOspfExtLsdbDomainNumber OBJECT-TYPE
        SYNTAX    INTEGER
        ACCESS    read-only
        STATUS    mandatory
        DESCRIPTION
                  "OSPF domain number."
        ::= { axsOspfExtLsdbEntry 1 }

    axsOspfExtLsdbType OBJECT-TYPE
        SYNTAX    INTEGER {
                      asExternalLink(5)
                  }
        ACCESS    read-only
        STATUS    mandatory
        DESCRIPTION
                  "The type  of  the  link  state  advertisement."
        ::= { axsOspfExtLsdbEntry 2 }

    axsOspfExtLsdbLsid OBJECT-TYPE
        SYNTAX    IpAddress
        ACCESS    read-only
        STATUS    mandatory
        DESCRIPTION
                  "The Link State ID is an LS Type Specific field
                  containing either a Router ID or an IP Address;
                  it identifies the piece of the  routing  domain
                  that is being described by the advertisement."
        ::= { axsOspfExtLsdbEntry 3 }

    axsOspfExtLsdbRouterId OBJECT-TYPE
        SYNTAX    IpAddress
        ACCESS    read-only
        STATUS    mandatory
        DESCRIPTION
                  "The 32 bit number that uniquely identifies the
                  originating router in the Autonomous System."
        ::= { axsOspfExtLsdbEntry 4 }

    axsOspfExtLsdbSequence OBJECT-TYPE
        SYNTAX    INTEGER
        ACCESS    read-only
        STATUS    mandatory
        DESCRIPTION
                  "The sequence number field is a  signed  32-bit integer."
        ::= { axsOspfExtLsdbEntry 5 }

    axsOspfExtLsdbAge OBJECT-TYPE
        SYNTAX    INTEGER
        ACCESS    read-only
        STATUS    mandatory
        DESCRIPTION
                  "The age of the link state advertisement in seconds."
        ::= { axsOspfExtLsdbEntry 6 }

    axsOspfExtLsdbChecksum OBJECT-TYPE
        SYNTAX    INTEGER
        ACCESS    read-only
        STATUS    mandatory
        DESCRIPTION
                  "This field is the  checksum  of  the  complete
                  contents  of  the  advertisement, excepting the
                  age field.  The age field is excepted  so  that
                  an   advertisement's  age  can  be  incremented
                  without updating the  checksum."
        ::= { axsOspfExtLsdbEntry 7 }

    axsOspfExtLsdbAdvertisement OBJECT-TYPE
        SYNTAX    OCTET STRING
        ACCESS    read-only
        STATUS    mandatory
        DESCRIPTION
                  "The entire Link State Advertisement, including its header."
        ::= { axsOspfExtLsdbEntry 8 }

    axsOspfAreaAggregateTable OBJECT-TYPE
        SYNTAX    SEQUENCE OF AxsOspfAreaAggregateEntry
        ACCESS    not-accessible
        STATUS    mandatory
        DESCRIPTION
                  "A range of IP addresses  specified  by  an  IP
                  address/IP  network  mask  pair."
        ::= { axsOspf 14 }

    axsOspfAreaAggregateEntry OBJECT-TYPE
        SYNTAX    AxsOspfAreaAggregateEntry
        ACCESS    not-accessible
        STATUS    mandatory
        DESCRIPTION
                  "A range of IP addresses  specified  by  an  IP
                  address/IP  network  mask  pair."
        INDEX     { axsOspfAreaAggregateDomainNumber,
                    axsOspfAreaAggregateAreaID,
                    axsOspfAreaAggregateLsdbType,
                    axsOspfAreaAggregateNet,
                    axsOspfAreaAggregateMask }
        ::= { axsOspfAreaAggregateTable 1 }

    AxsOspfAreaAggregateEntry ::= SEQUENCE {
        axsOspfAreaAggregateDomainNumber    INTEGER,
        axsOspfAreaAggregateAreaID          IpAddress,
        axsOspfAreaAggregateLsdbType        INTEGER,
        axsOspfAreaAggregateNet             IpAddress,
        axsOspfAreaAggregateMask            IpAddress,
        axsOspfAreaAggregateStatus          INTEGER,
        axsOspfAreaAggregateEffect          INTEGER
    }

    axsOspfAreaAggregateDomainNumber OBJECT-TYPE
        SYNTAX    INTEGER
        ACCESS    read-only
        STATUS    mandatory
        DESCRIPTION
                  "OSPF domain number."
        ::= { axsOspfAreaAggregateEntry 1 }

    axsOspfAreaAggregateAreaID OBJECT-TYPE
        SYNTAX    IpAddress
        ACCESS    read-only
        STATUS    mandatory
        DESCRIPTION
                  "The Area the Address Aggregate is to be found within."
        ::= { axsOspfAreaAggregateEntry 2 }

    axsOspfAreaAggregateLsdbType OBJECT-TYPE
        SYNTAX    INTEGER {
                      summaryLink(3),
                      nssaExternalLink(7)
                  }
        ACCESS    read-only
        STATUS    mandatory
        DESCRIPTION
                  "The type of the Address Aggregate. This field
                   specifies  the  Lsdb type that this Address 
                   Aggregate applies to."
        ::= { axsOspfAreaAggregateEntry 3 }

    axsOspfAreaAggregateNet OBJECT-TYPE
        SYNTAX    IpAddress
        ACCESS    read-only
        STATUS    mandatory
        DESCRIPTION
                  "The IP Address of the Net or Subnet indicated by the range."
        ::= { axsOspfAreaAggregateEntry 4 }

    axsOspfAreaAggregateMask OBJECT-TYPE
        SYNTAX    IpAddress
        ACCESS    read-only
        STATUS    mandatory
        DESCRIPTION
                  "The Subnet Mask that pertains to the Net or Subnet."
        ::= { axsOspfAreaAggregateEntry 5 }

    axsOspfAreaAggregateStatus OBJECT-TYPE
        SYNTAX    INTEGER {
                      active(1)
                  }
        ACCESS    read-only
        STATUS    mandatory
        DESCRIPTION
                  "This variable displays the status of  the  entry.
                  This entry value is only valid(1)."
        ::= { axsOspfAreaAggregateEntry 6 }

    axsOspfAreaAggregateEffect OBJECT-TYPE
        SYNTAX    INTEGER {
                      advertiseMatching(1),
                      doNotAdvertiseMatching(2)
                  }
        ACCESS    read-only
        STATUS    mandatory
        DESCRIPTION
                  "Subnets subsumed by ranges either trigger  the
                   advertisement  of  the indicated aggregate (ad-
                   vertiseMatching), or result in the subnet's not
                   being advertised at all outside the area."
        ::= { axsOspfAreaAggregateEntry 7 }

    axsOspfTrapControlTable OBJECT-TYPE
        SYNTAX    SEQUENCE OF AxsOspfTrapControlEntry
        ACCESS    not-accessible
        STATUS    mandatory
        DESCRIPTION
                  "The table about trap information."
        ::= { axsOspfTrap 1 }

    axsOspfTrapControlEntry OBJECT-TYPE
        SYNTAX    AxsOspfTrapControlEntry
        ACCESS    not-accessible
        STATUS    mandatory
        DESCRIPTION
                  "The Entry about trap information."
        INDEX     { axsOspfTrapDomainNumber }
        ::= { axsOspfTrapControlTable 1 }

    AxsOspfTrapControlEntry ::= SEQUENCE {
        axsOspfTrapDomainNumber    INTEGER,
        axsOspfSetTrap             OCTET STRING,
        axsOspfConfigErrorType     INTEGER,
        axsOspfPacketType          INTEGER,
        axsOspfPacketSrc           IpAddress
    }

    axsOspfTrapDomainNumber OBJECT-TYPE
        SYNTAX    INTEGER
        ACCESS    read-only
        STATUS    mandatory
        DESCRIPTION
                  "axsOspfTrap domain number."
        ::= { axsOspfTrapControlEntry 1 }

    axsOspfSetTrap OBJECT-TYPE
        SYNTAX    OCTET STRING
        ACCESS    read-write
        STATUS    mandatory
        DESCRIPTION
                  "A four-octet string serving as a bit  map  for
                  the trap events defined by the OSPF traps. This
                  object is used to enable and  disable  specific
                  OSPF   traps   where  a  1  in  the  bit  field
                  represents enabled.  The right-most bit  (least
                  significant) represents trap 0."
        ::= { axsOspfTrapControlEntry 2 }

    axsOspfConfigErrorType OBJECT-TYPE
        SYNTAX    INTEGER {
                      noError (0),
                      badVersion (1),
                      areaMismatch (2),
                      unknownNbmaNbr (3),        -- Router is Dr eligible
                      unknownVirtualNbr (4),
                      authTypeMismatch(5),
                      authFailure (6),
                      netMaskMismatch (7),
                      helloIntervalMismatch (8),
                      deadIntervalMismatch (9),
                      optionMismatch (10)
                  }
        ACCESS    read-only
        STATUS    mandatory
        DESCRIPTION
                  "Potential types  of  configuration  conflicts.
                  Used  by the ospfConfigError and ospfConfigVir-
                  tError traps."
        ::= { axsOspfTrapControlEntry 3 }

    axsOspfPacketType OBJECT-TYPE
        SYNTAX    INTEGER {
                      noError(0),
                      hello(1),
                      dbDescript(2),
                      lsReq(3),
                      lsUpdate(4),
                      lsAck(5)
                  }
        ACCESS    read-only
        STATUS    mandatory
        DESCRIPTION
                  "OSPF packet types."
        ::= { axsOspfTrapControlEntry 4 }

    axsOspfPacketSrc OBJECT-TYPE
        SYNTAX    IpAddress
        ACCESS    read-only
        STATUS    mandatory
        DESCRIPTION
                 "The IP address of an inbound packet that  can-
                 not be identified by a neighbor instance."
        ::= { axsOspfTrapControlEntry 5 }

-- axsOspfv3

    axsOspfv3GeneralTable OBJECT-TYPE
        SYNTAX    SEQUENCE OF AxsOspfv3GeneralEntry
        ACCESS    not-accessible
        STATUS    mandatory
        DESCRIPTION
                  "The table which ospfv3 information is stored in."
        ::= { axsOspfv3 1 }

    axsOspfv3GeneralEntry OBJECT-TYPE
        SYNTAX    AxsOspfv3GeneralEntry
        ACCESS    not-accessible
        STATUS    mandatory
        DESCRIPTION
                  "The list of the ospfv3 information."
        INDEX     { axsOspfv3GeneralDomainNumber }
        ::= { axsOspfv3GeneralTable 1 }

    AxsOspfv3GeneralEntry ::= SEQUENCE {
        axsOspfv3GeneralDomainNumber          INTEGER,
        axsOspfv3RouterId                     RouterID,
        axsOspfv3AdminStat                    Status,
        axsOspfv3VersionNumber                INTEGER,
        axsOspfv3AreaBdrRtrStatus             TruthValue,
        axsOspfv3ASBdrRtrStatus               TruthValue,
        axsOspfv3AsScopeLsaCount              Gauge32,
        axsOspfv3AsScopeLsaCksumSum           Integer32,
        axsOspfv3OriginateNewLsas             Counter32,
        axsOspfv3RxNewLsas                    Counter32,
        axsOspfv3ExtAreaLsdbLimit             Integer32,
        axsOspfv3MulticastExtensions          Integer32,
        axsOspfv3DemandExtensions             TruthValue,
        axsOspfv3TrafficEngineeringSupport    TruthValue
    }

    axsOspfv3GeneralDomainNumber OBJECT-TYPE
        SYNTAX    INTEGER
        ACCESS    read-only
        STATUS    mandatory
        DESCRIPTION
                  "ospfv3 domain number."
        ::= { axsOspfv3GeneralEntry 1 }

    axsOspfv3RouterId OBJECT-TYPE
        SYNTAX    RouterID
        ACCESS    read-only
        STATUS    mandatory
        DESCRIPTION
                  "A  32-bit  integer  uniquely  identifying  the
                  router in the Autonomous System.
                  By convention, to  ensure  uniqueness, this
                  should  default  to  the  value  of  one of the
                  router's IPv4 interface addresses if IPv4 is
                  configured."
        ::= { axsOspfv3GeneralEntry 2 }

    axsOspfv3AdminStat OBJECT-TYPE
        SYNTAX    Status
        ACCESS    read-only
        STATUS    mandatory
        DESCRIPTION
                  "The  administrative  status  of  axsOspfv3  in  the
                  router.  The  value 'enabled' denotes that the
                  axsOspfv3 Process is active on at least  one  inter-
                  face;  'disabled'  disables  it  on  all inter-
                  faces."
        ::= { axsOspfv3GeneralEntry 3 }

    axsOspfv3VersionNumber OBJECT-TYPE
        SYNTAX    INTEGER { version3 (3) }
        ACCESS    read-only
        STATUS    mandatory
        DESCRIPTION
                  "The version number of OSPF for IPv6 is 3."
        ::= { axsOspfv3GeneralEntry 4 }

    axsOspfv3AreaBdrRtrStatus OBJECT-TYPE
        SYNTAX    TruthValue
        ACCESS    read-only
        STATUS    mandatory
        DESCRIPTION
                  "A flag to note whether this router is an  area
                  border router."
        REFERENCE
                  "OSPF Version 2, Section 3 Splitting the AS into
                  Areas"
        ::= { axsOspfv3GeneralEntry 5 }

    axsOspfv3ASBdrRtrStatus OBJECT-TYPE
        SYNTAX    TruthValue
        ACCESS    read-only
        STATUS    mandatory
        DESCRIPTION
                  "A flag to note whether this router is  config-
                  ured as an Autonomous System border router."
        REFERENCE
                  "OSPF Version 2, Section 3.3  Classification  of
                  routers"
        ::= { axsOspfv3GeneralEntry 6 }

    axsOspfv3AsScopeLsaCount OBJECT-TYPE
        SYNTAX    Gauge32
        ACCESS    read-only
        STATUS    mandatory
        DESCRIPTION
                  "The number of AS-Scope (e.g. AS-External) link-state
                  advertisements in the link-state database."
        ::= { axsOspfv3GeneralEntry 7 }

    axsOspfv3AsScopeLsaCksumSum OBJECT-TYPE
        SYNTAX    Integer32
        ACCESS    read-only
        STATUS    mandatory
        DESCRIPTION
                  "The 32-bit unsigned sum of the LS checksums of
                  the  AS-scoped link-state advertisements  con-
                  tained in the link-state database. This sum
                  can  be  used  to determine if there has been a
                  change in a router's link state  database,  and
                  to  compare  the  link-state  database  of  two
                  routers."
        ::= { axsOspfv3GeneralEntry 8 }

    axsOspfv3OriginateNewLsas OBJECT-TYPE
        SYNTAX    Counter32
        ACCESS    read-only
        STATUS    mandatory
        DESCRIPTION
                  "The number of  new  link-state  advertisements
                  that  have been originated.  This number is in-
                  cremented each time the router originates a new
                  LSA."
        ::= { axsOspfv3GeneralEntry 9 }

    axsOspfv3RxNewLsas OBJECT-TYPE
        SYNTAX    Counter32
        ACCESS    read-only
        STATUS    mandatory
        DESCRIPTION
                  "The number of  link-state  advertisements  re-
                  ceived  determined  to  be  new instantiations.
                  This number does not include  newer  instantia-
                  tions  of self-originated link-state advertise-
                  ments."
        ::= { axsOspfv3GeneralEntry 10 }

    axsOspfv3ExtAreaLsdbLimit OBJECT-TYPE
        SYNTAX    Integer32 (-1..'7FFFFFFF'h)
        ACCESS    read-only
        STATUS    mandatory
        DESCRIPTION
                  "The  maximum   number   of   non-default   AS-
                  external-LSAs entries that can be stored in the
                  link-state database.  If the value is -1,  then
                  there is no limit.
                  When the number of non-default AS-external-LSAs
                  in  a  router's  link-state  database  reaches
                  axsOspfv3ExtAreaLsdbLimit, the router  enters  Overflow-
                  State.  The   router  never  holds  more  than
                  axsOspfv3ExtAreaLsdbLimit  non-default  AS-external-LSAs
                  in  its  database. OspfExtAreaLsdbLimit MUST be set
                  identically in all routers attached to the axsOspfv3
                  backbone  and/or  any regular axsOspfv3 area. (i.e.,
                  axsOspfv3 stub areas and NSSAs are excluded)."
        DEFVAL    { -1 }
        ::= { axsOspfv3GeneralEntry 11 }

    axsOspfv3MulticastExtensions OBJECT-TYPE
        SYNTAX    Integer32
        ACCESS    read-only
        STATUS    mandatory
        DESCRIPTION
                  "A Bit Mask indicating whether  the  router  is
                  forwarding  IPv6  multicast datagrams
                  based on the algorithms defined in  the  Multi-
                  cast Extensions to OSPF.
                  Bit 0, if set, indicates that  the  router  can
                  forward  IPv6 multicast datagrams in the router's
                  directly attached areas (called intra-area mul-
                  ticast routing).
                  Bit 1, if set, indicates that  the  router  can
                  forward  IPv6  multicast  datagrams  between axsOspfv3
                  areas (called inter-area multicast routing).
                  Bit 2, if set, indicates that  the  router  can
                  forward  IPv6  multicast  datagrams between Auto-
                  nomous Systems (called inter-AS multicast rout-
                  ing).
                  Only certain combinations of bit  settings are
                  allowed,  namely: 0 (no multicast forwarding is
                  enabled), 1 (intra-area multicasting  only),  3
                  (intra-area  and  inter-area  multicasting),  5
                  (intra-area and inter-AS  multicasting)  and  7
                  (multicasting  everywhere). By default, no mul-
                  ticast forwarding is enabled."
        DEFVAL    { 0 }
        ::= { axsOspfv3GeneralEntry 12 }

    axsOspfv3DemandExtensions OBJECT-TYPE
        SYNTAX    TruthValue
        ACCESS    read-only
        STATUS    mandatory
        DESCRIPTION
                  "The router's support for demand routing."
        REFERENCE
                  "OSPF Version 2, Appendix on Demand Routing"
        ::= { axsOspfv3GeneralEntry 14 }

    axsOspfv3TrafficEngineeringSupport OBJECT-TYPE
        SYNTAX    TruthValue
        ACCESS    read-only
        STATUS    mandatory
        DESCRIPTION
                  "The router's support for traffic engineering
                  extensions."
        ::= { axsOspfv3GeneralEntry 15 }

-- The axsOspfv3 Area Data Structure contains information
-- regarding the various areas. The interfaces and
-- virtual links are configured as part of these areas.
-- Area 0.0.0.0, by definition, is the Backbone Area

    axsOspfv3AreaTable OBJECT-TYPE
        SYNTAX    SEQUENCE OF AxsOspfv3AreaEntry
        ACCESS    not-accessible
        STATUS    mandatory
        DESCRIPTION
                  "Information describing the configured  parame-
                  ters  and cumulative statistics of the router's
                  attached areas."
        REFERENCE
                  "OSPF Version 2, Section 6  The Area Data Struc-
                  ture"
        ::= { axsOspfv3 2 }

    axsOspfv3AreaEntry OBJECT-TYPE
        SYNTAX    AxsOspfv3AreaEntry
        ACCESS    not-accessible
        STATUS    mandatory
        DESCRIPTION
                  "Information describing the configured  parame-
                  ters  and  cumulative  statistics of one of the
                  router's attached areas."
        INDEX     { axsOspfv3AreaDomainNumber,
                    axsOspfv3AreaId }
        ::= { axsOspfv3AreaTable 1 }

    AxsOspfv3AreaEntry ::= SEQUENCE {
        axsOspfv3AreaDomainNumber        INTEGER,
        axsOspfv3AreaId                  AreaID,
        axsOspfv3ImportAsExtern          INTEGER,
        axsOspfv3SpfRuns                 Counter32,
        axsOspfv3AreaBdrRtrCount         Gauge32,
        axsOspfv3AsBdrRtrCount           Gauge32,
        axsOspfv3AreaScopeLsaCount       Gauge32,
        axsOspfv3AreaScopeLsaCksumSum    Integer32,
        axsOspfv3AreaSummary             INTEGER,
        axsOspfv3AreaStatus              RowStatus,
        axsOspfv3StubMetric              BigMetric
    }

    axsOspfv3AreaDomainNumber OBJECT-TYPE
        SYNTAX    INTEGER
        ACCESS    read-only
        STATUS    mandatory
        DESCRIPTION
                  "ospfv3 domain number."
        ::= { axsOspfv3AreaEntry 1 }

    axsOspfv3AreaId OBJECT-TYPE
        SYNTAX    AreaID
        ACCESS    read-only
        STATUS    mandatory
        DESCRIPTION
                  "A 32-bit integer uniquely identifying an area.
                  Area ID 0.0.0.0 is used for the axsOspfv3 backbone."
        REFERENCE
                  "OSPF Version 2, Appendix C.2 Area parameters"
        ::= { axsOspfv3AreaEntry 2 }

    axsOspfv3ImportAsExtern OBJECT-TYPE
        SYNTAX    INTEGER {
                      importExternal(1),   -- normal area
                      importNoExternal(2), -- stub area
                      importNssa(3)        -- not-so-stubby-area
                  }
        ACCESS    read-only
        STATUS    mandatory
        DESCRIPTION
                  "Indicates whether an area is a Stub area, NSSA, or
                  standard area. AS-scope LSAs are not imported into Stub
                  Areas or NSSAs. NSSAs import AS-External data as Type-7
                  LSAs which have Area-scope"
        REFERENCE
                  "OSPF Version 2, Appendix C.2 Area parameters"
        DEFVAL    { importExternal }
        ::= { axsOspfv3AreaEntry 3 }

    axsOspfv3SpfRuns OBJECT-TYPE
        SYNTAX    Counter32
        ACCESS    read-only
        STATUS    mandatory
        DESCRIPTION
                  "The number of times that the intra-area  route
                  table  has  been  calculated  using this area's
                  link-state database.  This  is  typically  done
                  using Dijkstra's algorithm."
        ::= { axsOspfv3AreaEntry 4 }

    axsOspfv3AreaBdrRtrCount OBJECT-TYPE
        SYNTAX    Gauge32
        ACCESS    read-only
        STATUS    mandatory
        DESCRIPTION
                  "The total number of area border routers reach-
                  able within this area. This is initially zero,
                  and is calculated in each SPF Pass."
        ::= { axsOspfv3AreaEntry 5 }

    axsOspfv3AsBdrRtrCount OBJECT-TYPE
        SYNTAX    Gauge32
        ACCESS    read-only
        STATUS    mandatory
        DESCRIPTION
                  "The total number of Autonomous  System  border
                  routers  reachable  within  this area.  This is
                  initially zero, and is calculated in  each  SPF
                  Pass."
        ::= { axsOspfv3AreaEntry 6 }

    axsOspfv3AreaScopeLsaCount OBJECT-TYPE
        SYNTAX    Gauge32
        ACCESS    read-only
        STATUS    mandatory
        DESCRIPTION
                  "The total number of Area-Scope link-state
                  advertisements in  this  area's link-state
                  database."
        ::= { axsOspfv3AreaEntry 7 }

    axsOspfv3AreaScopeLsaCksumSum OBJECT-TYPE
        SYNTAX    Integer32
        ACCESS    read-only
        STATUS    mandatory
        DESCRIPTION
                  "The 32-bit unsigned sum of the Area-Scope link-state
                  advertisements'  LS  checksums  contained in this
                  area's link-state database.  The sum can be used
                  to determine if  there  has been  a  change  in a
                  router's link state database, and to compare the
                  link-state database of two routers."
                  DEFVAL  { 0 }
        ::= { axsOspfv3AreaEntry 8 }

    axsOspfv3AreaSummary OBJECT-TYPE
        SYNTAX    INTEGER {
                      noAreaSummary(1),
                      sendAreaSummary(2)
                  }
        ACCESS    read-only
        STATUS    mandatory
        DESCRIPTION
                  "The variable axsOspfv3AreaSummary controls the  im-
                  port  of  summary LSAs into stub areas.  It has
                  no effect on other areas.
                  If it is noAreaSummary, the router will neither
                  originate  nor  propagate summary LSAs into the
                  stub area.  It will rely entirely  on  its  de-
                  fault route.
                  If it is sendAreaSummary, the router will  both
                  summarize and propagate summary LSAs."
        DEFVAL    { noAreaSummary }
        ::= { axsOspfv3AreaEntry 9 }

    axsOspfv3AreaStatus OBJECT-TYPE
        SYNTAX    RowStatus
        ACCESS    read-only
        STATUS    mandatory
        DESCRIPTION
                  "This variable displays the status of  the  en-
                  try.  Setting it to 'invalid' has the effect of
                  rendering it inoperative.  The internal  effect
                  (row removal) is implementation dependent."
        ::= { axsOspfv3AreaEntry 10 }

    axsOspfv3StubMetric OBJECT-TYPE
        SYNTAX    BigMetric
--      ACCESS    read-create
        ACCESS    read-only
        STATUS    mandatory
        DESCRIPTION
                  "The metric value advertised for the default route
                  into Stub and NSSA areas."
        ::= { axsOspfv3AreaEntry 11 }

-- axsOspfv3 AS-Scope Link State Database
-- The Link State Database contains the AS-Scope Link State
-- Advertisements from throughout the areas that the
-- device is attached to.

    axsOspfv3AsLsdbTable OBJECT-TYPE
        SYNTAX    SEQUENCE OF AxsOspfv3AsLsdbEntry
        ACCESS    not-accessible
        STATUS    mandatory
        DESCRIPTION
                  "The axsOspfv3 Process's AS-Scope Link State Database."
        ::= { axsOspfv3 3 }

    axsOspfv3AsLsdbEntry OBJECT-TYPE
        SYNTAX    AxsOspfv3AsLsdbEntry
        ACCESS    not-accessible
        STATUS    mandatory
        DESCRIPTION
                  "A single AS-Scope Link State Advertisement."
        INDEX     { axsOspfv3AsLsdbDomainNumber,
                    axsOspfv3AsLsdbType,
                    axsOspfv3AsLsdbRouterId,
                    axsOspfv3AsLsdbLsid }
        ::= { axsOspfv3AsLsdbTable 1 }

    AxsOspfv3AsLsdbEntry ::= SEQUENCE {
        axsOspfv3AsLsdbDomainNumber     INTEGER,
        axsOspfv3AsLsdbType             INTEGER,
        axsOspfv3AsLsdbRouterId         RouterID,
        axsOspfv3AsLsdbLsid             IpAddress,
        axsOspfv3AsLsdbSequence         Integer32,
        axsOspfv3AsLsdbAge              Integer32,
        axsOspfv3AsLsdbChecksum         Integer32,
        axsOspfv3AsLsdbAdvertisement    OCTET STRING
    }

    axsOspfv3AsLsdbDomainNumber OBJECT-TYPE
        SYNTAX    INTEGER
        ACCESS    read-only
        STATUS    mandatory
        DESCRIPTION
                  "ospfv3 domain number."
        ::= { axsOspfv3AsLsdbEntry 1 }

    axsOspfv3AsLsdbType OBJECT-TYPE
        SYNTAX    INTEGER {
                      asExternalLink(16389) -- 0x4005
                  }
        ACCESS    read-only
        STATUS    mandatory
        DESCRIPTION
                  "The type  of  the  link  state  advertisement.
                  Each  link state type has a separate advertise-
                  ment format. Unrecognized AS-Scope LSAs with the
                  U-bit set are also store in this database."
        ::= { axsOspfv3AsLsdbEntry 2 }

    axsOspfv3AsLsdbRouterId OBJECT-TYPE
        SYNTAX    RouterID
        ACCESS    read-only
        STATUS    mandatory
        DESCRIPTION
                  "The 32 bit number that uniquely identifies the
                  originating router in the Autonomous System."
        REFERENCE
                  "OSPF Version 2, Appendix C.1 Global parameters"
        ::= { axsOspfv3AsLsdbEntry 3 }

    axsOspfv3AsLsdbLsid OBJECT-TYPE
        SYNTAX    IpAddress
        ACCESS    read-only
        STATUS    mandatory
        DESCRIPTION
                  "The Link State ID is an LS Type Specific field
                  containing either a Router ID or a unique identifier;
                  it identifies the piece of the  routing  domain
                  that is being described by the advertisement.
                  In contrast to OSPF for IPv4, the LSID has no
                  addressing semantics."
        ::= { axsOspfv3AsLsdbEntry 4 }

-- Note that the OSPF Sequence Number is a 32 bit signed
-- integer.  It starts with the value '80000001'h,
-- or -'7FFFFFFF'h, and increments until '7FFFFFFF'h
-- Thus, a typical sequence number will be very negative.

    axsOspfv3AsLsdbSequence OBJECT-TYPE
        SYNTAX    Integer32
        ACCESS    read-only
        STATUS    mandatory
        DESCRIPTION
                  "The sequence number field is a  signed  32-bit
                  integer.   It  is used to detect old and dupli-
                  cate link state advertisements.  The  space  of
                  sequence  numbers  is  linearly  ordered.  The
                  larger the sequence number the more recent  the
                  advertisement."
        REFERENCE
                  "OSPF Version  2,  Section  12.1.6  LS  sequence
                  number"
        ::= { axsOspfv3AsLsdbEntry 5 }

    axsOspfv3AsLsdbAge OBJECT-TYPE
        SYNTAX    Integer32 -- Should be 0..MaxAge
        ACCESS    read-only
        STATUS    mandatory
        DESCRIPTION
                  "This field is the age of the link state adver-
                  tisement in seconds."
        REFERENCE
                  "OSPF Version 2, Section 12.1.1 LS age"
        ::= { axsOspfv3AsLsdbEntry 6 }

    axsOspfv3AsLsdbChecksum OBJECT-TYPE
        SYNTAX    Integer32
        ACCESS    read-only
        STATUS    mandatory
        DESCRIPTION
                  "This field is the  checksum  of  the  complete
                  contents  of  the  advertisement, excepting the
                  age field.  The age field is excepted  so  that
                  an  advertisement's  age  can  be  incremented
                  without updating the  checksum.  The  checksum
                  used  is  the same that is used for ISO connec-
                  tionless datagrams; it is commonly referred  to
                  as the Fletcher checksum."
        REFERENCE
                  "OSPF Version 2, Section 12.1.7 LS checksum"
        ::= { axsOspfv3AsLsdbEntry 7 }

    axsOspfv3AsLsdbAdvertisement OBJECT-TYPE
        SYNTAX    OCTET STRING (SIZE (1..65535))
        ACCESS    read-only
        STATUS    mandatory
        DESCRIPTION
                  "The entire Link State Advertisement, including
                  its header."
        ::= { axsOspfv3AsLsdbEntry 8 }

-- axsOspfv3 Area-Scope Link State Database
-- The Link State Database contains the Area-Scope Link State
-- Advertisements from throughout the area that the
-- device is attached to.

    axsOspfv3AreaLsdbTable OBJECT-TYPE
        SYNTAX    SEQUENCE OF AxsOspfv3AreaLsdbEntry
        ACCESS    not-accessible
        STATUS    mandatory
        DESCRIPTION
                  "The axsOspfv3 Process's Area-Scope Link State Database."
        ::= { axsOspfv3 4 }

    axsOspfv3AreaLsdbEntry OBJECT-TYPE
        SYNTAX    AxsOspfv3AreaLsdbEntry
        ACCESS    not-accessible
        STATUS    mandatory
        DESCRIPTION
                  "A single Area-Scope Link State Advertisement."
        INDEX     { axsOspfv3AreaLsdbDomainNumber,
                    axsOspfv3AreaLsdbAreaId,
                    axsOspfv3AreaLsdbType,
                    axsOspfv3AreaLsdbRouterId,
                    axsOspfv3AreaLsdbLsid }
        ::= { axsOspfv3AreaLsdbTable 1 }

    AxsOspfv3AreaLsdbEntry ::= SEQUENCE {
        axsOspfv3AreaLsdbDomainNumber     INTEGER,
        axsOspfv3AreaLsdbAreaId           AreaID,
        axsOspfv3AreaLsdbType             INTEGER,
        axsOspfv3AreaLsdbRouterId         RouterID,
        axsOspfv3AreaLsdbLsid             IpAddress,
        axsOspfv3AreaLsdbSequence         Integer32,
        axsOspfv3AreaLsdbAge              Integer32,
        axsOspfv3AreaLsdbChecksum         Integer32,
        axsOspfv3AreaLsdbAdvertisement    OCTET STRING
    }

    axsOspfv3AreaLsdbDomainNumber OBJECT-TYPE
        SYNTAX    INTEGER
        ACCESS    read-only
        STATUS    mandatory
        DESCRIPTION
                  "ospfv3 domain number."
        ::= { axsOspfv3AreaLsdbEntry 1 }

    axsOspfv3AreaLsdbAreaId OBJECT-TYPE
        SYNTAX    AreaID
        ACCESS    read-only
        STATUS    mandatory
        DESCRIPTION
                  "The 32 bit identifier of the Area from which the
                  LSA was received."
        REFERENCE
                  "OSPF Version 2, Appendix C.2 Area parameters."
        ::= { axsOspfv3AreaLsdbEntry 2 }

    axsOspfv3AreaLsdbType OBJECT-TYPE
        SYNTAX    INTEGER {
                      routerLsa(8193),          -- 0x2001
                      networkLsa(8194),         -- 0x2002
                      interAreaPrefixLsa(8195), -- 0x2003
                      interAreaRouterLsa(8196), -- 0x2004
                      groupMembershipLsa(8198), -- 0x2006
                      nssaExternalLsa(8199),    -- 0x2007
                      intraAreaPrefixLsa(8201)  -- 0x2009
                  }
        ACCESS    read-only
        STATUS    mandatory
        DESCRIPTION
                  "The type  of  the  link  state  advertisement.
                  Each  link state type has a separate advertise-
                  ment format. Unrecognized Area-Scope LSAs with
                  the U-bit set are also stored in this database."
        ::= { axsOspfv3AreaLsdbEntry 3 }

    axsOspfv3AreaLsdbRouterId OBJECT-TYPE
        SYNTAX    RouterID
        ACCESS    read-only
        STATUS    mandatory
        DESCRIPTION
                  "The 32 bit number that uniquely identifies the
                  originating router in the Autonomous System."
        REFERENCE
                  "OSPF Version 2, Appendix C.1 Global parameters"
        ::= { axsOspfv3AreaLsdbEntry 4 }

    axsOspfv3AreaLsdbLsid OBJECT-TYPE
        SYNTAX    IpAddress
        ACCESS    read-only
        STATUS    mandatory
        DESCRIPTION
                  "The Link State ID is an LS Type Specific field
                  containing either a Router ID or a unique identifier;
                  it identifies the piece of the  routing  domain
                  that is being described by the advertisement.
                  In contrast to OSPF for IPv4, the LSID has no
                  addressing semantics."
        ::= { axsOspfv3AreaLsdbEntry 5 }

-- Note that the OSPF Sequence Number is a 32 bit signed
-- integer.  It starts with the value '80000001'h,
-- or -'7FFFFFFF'h, and increments until '7FFFFFFF'h
-- Thus, a typical sequence number will be very negative.

    axsOspfv3AreaLsdbSequence OBJECT-TYPE
        SYNTAX    Integer32
        ACCESS    read-only
        STATUS    mandatory
        DESCRIPTION
                  "The sequence number field is a  signed  32-bit
                  integer.   It  is used to detect old and dupli-
                  cate link state advertisements.  The  space  of
                  sequence  numbers  is  linearly  ordered.   The
                  larger the sequence number the more recent  the
                  advertisement."
        REFERENCE
                  "OSPF Version  2,  Section  12.1.6  LS  sequence
                  number"
        ::= { axsOspfv3AreaLsdbEntry 6 }

    axsOspfv3AreaLsdbAge OBJECT-TYPE
        SYNTAX    Integer32  -- Should be 0..MaxAge
        ACCESS    read-only
        STATUS    mandatory
        DESCRIPTION
                  "This field is the age of the link state adver-
                  tisement in seconds."
        REFERENCE
                  "OSPF Version 2, Section 12.1.1 LS age"
        ::= { axsOspfv3AreaLsdbEntry 7 }

    axsOspfv3AreaLsdbChecksum OBJECT-TYPE
        SYNTAX    Integer32
        ACCESS    read-only
        STATUS    mandatory
        DESCRIPTION
                  "This field is the  checksum  of  the  complete
                  contents  of  the  advertisement, excepting the
                  age field.  The age field is excepted  so  that
                  an  advertisement's  age  can  be  incremented
                  without updating the  checksum.  The  checksum
                  used  is  the same that is used for ISO connec-
                  tionless datagrams; it is commonly referred  to
                  as the Fletcher checksum."
        REFERENCE
                  "OSPF Version 2, Section 12.1.7 LS checksum"
        ::= { axsOspfv3AreaLsdbEntry 8 }

    axsOspfv3AreaLsdbAdvertisement OBJECT-TYPE
        SYNTAX    OCTET STRING (SIZE (1..65535))
        ACCESS    read-only
        STATUS    mandatory
        DESCRIPTION
                  "The entire Link State Advertisement, including
                  its header."
        ::= { axsOspfv3AreaLsdbEntry 9 }

-- axsOspfv3 Link-Scope Link State Database
--   The Link State Database contains the Link-Scope Link State
--   Advertisements from the links that the
--   device is attached to.

    axsOspfv3LinkLsdbTable OBJECT-TYPE
        SYNTAX    SEQUENCE OF AxsOspfv3LinkLsdbEntry
        ACCESS    not-accessible
        STATUS    mandatory
        DESCRIPTION
                  "The axsOspfv3 Process's Link-Scope Link State Database."
        ::= { axsOspfv3 5 }

    axsOspfv3LinkLsdbEntry OBJECT-TYPE
        SYNTAX    AxsOspfv3LinkLsdbEntry
        ACCESS    not-accessible
        STATUS    mandatory
        DESCRIPTION
                  "A single Link-Scope Link State Advertisement."
        INDEX     { axsOspfv3LinkLsdbDomainNumber,
                    axsOspfv3LinkLsdbIfIndex,
                    axsOspfv3LinkLsdbType,
                    axsOspfv3LinkLsdbRouterId,
                    axsOspfv3LinkLsdbLsid }
        ::= { axsOspfv3LinkLsdbTable 1 }

    AxsOspfv3LinkLsdbEntry ::= SEQUENCE {
        axsOspfv3LinkLsdbDomainNumber     INTEGER,
        axsOspfv3LinkLsdbIfIndex          Ipv6IfIndex,
        axsOspfv3LinkLsdbType             INTEGER,
        axsOspfv3LinkLsdbRouterId         RouterID,
        axsOspfv3LinkLsdbLsid             IpAddress,
        axsOspfv3LinkLsdbSequence         Integer32,
        axsOspfv3LinkLsdbAge              Integer32,
        axsOspfv3LinkLsdbChecksum         Integer32,
        axsOspfv3LinkLsdbAdvertisement    OCTET STRING
    }

    axsOspfv3LinkLsdbDomainNumber OBJECT-TYPE
        SYNTAX    INTEGER
        ACCESS    read-only
        STATUS    mandatory
        DESCRIPTION
                  "ospfv3 domain number."
        ::= { axsOspfv3LinkLsdbEntry 1 }

    axsOspfv3LinkLsdbIfIndex OBJECT-TYPE
        SYNTAX    Ipv6IfIndex
        ACCESS    read-only
        STATUS    mandatory
        DESCRIPTION
                  "The identifier of the link from which the LSA
                  was received."
        REFERENCE
                  "OSPF Version 2, Appendix C.2 Area parameters"
        ::= { axsOspfv3LinkLsdbEntry 2 }

    axsOspfv3LinkLsdbType OBJECT-TYPE
        SYNTAX    INTEGER  {
                      linkLsa(8) -- 0x0008
                  }
        ACCESS    read-only
        STATUS    mandatory
        DESCRIPTION
                  "The type  of  the  link  state  advertisement.
                  Each  link state type has a separate advertise-
                  ment format. Unrecognized Link-Scope LSAs with
                  the U-bit set are also stored in this database."
        ::= { axsOspfv3LinkLsdbEntry 3 }

    axsOspfv3LinkLsdbRouterId OBJECT-TYPE
        SYNTAX    RouterID
        ACCESS    read-only
        STATUS    mandatory
        DESCRIPTION
                  "The 32 bit number that uniquely identifies the
                  originating router in the Autonomous System."
        REFERENCE
                  "OSPF Version 2, Appendix C.1 Global parameters"
        ::= { axsOspfv3LinkLsdbEntry 4 }

    axsOspfv3LinkLsdbLsid OBJECT-TYPE
        SYNTAX  IpAddress
        ACCESS  read-only
        STATUS  mandatory
        DESCRIPTION
                  "The Link State ID is an LS Type Specific field
                  containing either a Router ID or a unique identifier;
                  it identifies the piece of the  routing  domain
                  that is being described by the advertisement.
                  In contrast to OSPF for IPv4, the LSID has no
                  addressing semantics."
        ::= { axsOspfv3LinkLsdbEntry 5 }

-- Note that the OSPF Sequence Number is a 32 bit signed
-- integer.  It starts with the value '80000001'h,
-- or -'7FFFFFFF'h, and increments until '7FFFFFFF'h
-- Thus, a typical sequence number will be very negative.

    axsOspfv3LinkLsdbSequence OBJECT-TYPE
        SYNTAX    Integer32
        ACCESS    read-only
        STATUS    mandatory
        DESCRIPTION
                  "The sequence number field is a  signed  32-bit
                  integer.   It  is used to detect old and dupli-
                  cate link state advertisements.  The  space  of
                  sequence  numbers  is  linearly  ordered.  The
                  larger the sequence number the more recent  the
                  advertisement."
        REFERENCE
                  "OSPF Version  2,  Section  12.1.6  LS  sequence
                  number"
        ::= { axsOspfv3LinkLsdbEntry 6 }

    axsOspfv3LinkLsdbAge OBJECT-TYPE
        SYNTAX    Integer32 -- Should be 0..MaxAge
        ACCESS    read-only
        STATUS    mandatory
        DESCRIPTION
                  "This field is the age of the link state adver-
                  tisement in seconds."
        REFERENCE
                  "OSPF Version 2, Section 12.1.1 LS age"
        ::= { axsOspfv3LinkLsdbEntry 7 }

    axsOspfv3LinkLsdbChecksum OBJECT-TYPE
        SYNTAX    Integer32
        ACCESS    read-only
        STATUS    mandatory
        DESCRIPTION
                  "This field is the  checksum  of  the  complete
                  contents  of  the  advertisement, excepting the
                  age field.  The age field is excepted  so  that
                  an  advertisement's  age  can  be  incremented
                  without updating the  checksum.  The  checksum
                  used  is  the same that is used for ISO connec-
                  tionless datagrams; it is commonly referred  to
                  as the Fletcher checksum."
        REFERENCE
                  "OSPF Version 2, Section 12.1.7 LS checksum"
        ::= { axsOspfv3LinkLsdbEntry 8 }

    axsOspfv3LinkLsdbAdvertisement OBJECT-TYPE
        SYNTAX    OCTET STRING (SIZE (1..65535))
        ACCESS    read-only
        STATUS    mandatory
        DESCRIPTION
                  "The entire Link State Advertisement, including
                  its header."
        ::= { axsOspfv3LinkLsdbEntry 9 }

-- OSPF Host Table
--   The Host/Metric Table indicates what hosts are directly
--   attached to the Router, and what metrics and types of
--   service should be advertised for them.
-- axsOspfv3 Interface Table

    axsOspfv3IfTable OBJECT-TYPE
        SYNTAX    SEQUENCE OF AxsOspfv3IfEntry
        ACCESS    not-accessible
        STATUS    mandatory
        DESCRIPTION
                  "The axsOspfv3 Interface Table describes the  inter-
                  faces from the viewpoint of axsOspfv3."
        REFERENCE
                  "OSPF Version 2, Appendix C.3  Router  interface
                  parameters"
        ::= { axsOspfv3 7 }

    axsOspfv3IfEntry OBJECT-TYPE
        SYNTAX    AxsOspfv3IfEntry
        ACCESS    not-accessible
        STATUS    mandatory
        DESCRIPTION
                  "The axsOspfv3 Interface Entry describes one  inter-
                  face from the viewpoint of axsOspfv3."
        INDEX     { axsOspfv3IfDomainNumber,
                    axsOspfv3IfIndex }
        ::= { axsOspfv3IfTable 1 }

    AxsOspfv3IfEntry ::= SEQUENCE {
        axsOspfv3IfDomainNumber              INTEGER,
        axsOspfv3IfIndex                     Ipv6IfIndex,
        axsOspfv3IfAreaId                    AreaID,
        axsOspfv3IfType                      INTEGER,
        axsOspfv3IfAdminStat                 Status,
        axsOspfv3IfRtrPriority               DesignatedRouterPriority,
        axsOspfv3IfTransitDelay              UpToMaxAge,
        axsOspfv3IfRetransInterval           UpToMaxAge,
        axsOspfv3IfHelloInterval             HelloRange,
        axsOspfv3IfRtrDeadInterval           PositiveInteger,
        axsOspfv3IfPollInterval              PositiveInteger,
        axsOspfv3IfState                     INTEGER,
        axsOspfv3IfDesignatedRouter          RouterID,
        axsOspfv3IfBackupDesignatedRouter    RouterID,
        axsOspfv3IfEvents                    Counter32,
        axsOspfv3IfStatus                    RowStatus,
        axsOspfv3IfMulticastForwarding       INTEGER,
        axsOspfv3IfDemand                    TruthValue,
        axsOspfv3IfMetricValue               Metric,
        axsOspfv3IfLinkScopeLsaCount         Gauge32,
        axsOspfv3IfLinkLsaCksumSum           Integer32,
        axsOspfv3IfInstId                    Integer32
    }

    axsOspfv3IfDomainNumber OBJECT-TYPE
        SYNTAX    INTEGER
        ACCESS    read-only
        STATUS    mandatory
        DESCRIPTION
                  "ospfv3 domain number."
        ::= { axsOspfv3IfEntry 1 }

    axsOspfv3IfIndex OBJECT-TYPE
        SYNTAX    Ipv6IfIndex
        ACCESS    read-only
        STATUS    mandatory
        DESCRIPTION
                  "The interface index of this axsOspfv3 interface.
                  It corresponds to the interface index of the
                  Ipv6 interface on which axsOspfv3 is configured."
        ::= { axsOspfv3IfEntry 2 }

    axsOspfv3IfAreaId OBJECT-TYPE
        SYNTAX    AreaID
        ACCESS    read-only
        STATUS    mandatory
        DESCRIPTION
                  "A 32-bit integer uniquely identifying the area
                  to  which  the  interface  connects.   Area  ID
                  0.0.0.0 is used for the axsOspfv3 backbone."
        DEFVAL    { '00000000'H } -- 0.0.0.0
        ::= { axsOspfv3IfEntry 3 }

    axsOspfv3IfType OBJECT-TYPE
        SYNTAX    INTEGER {
                      broadcast(1),
                      nbma(2),
                      pointToPoint(3),
                      pointToMultipoint(5)
                  }
        ACCESS    read-only
        STATUS    mandatory
        DESCRIPTION
                  "The axsOspfv3 interface type."
        ::= { axsOspfv3IfEntry 4 }

    axsOspfv3IfAdminStat OBJECT-TYPE
        SYNTAX    Status
        ACCESS    read-only
        STATUS    mandatory
        DESCRIPTION
                  "The axsOspfv3 interface's  administrative  status.
                  The  value formed on the interface, and the in-
                  terface will be advertised as an internal route
                  to  some  area.  The  value 'disabled' denotes
                  that the interface is external to axsOspfv3."
        DEFVAL    { enabled }
        ::= { axsOspfv3IfEntry 5 }

    axsOspfv3IfRtrPriority OBJECT-TYPE
        SYNTAX    DesignatedRouterPriority
        ACCESS    read-only
        STATUS    mandatory
        DESCRIPTION
                  "The  priority  of  this  interface.   Used  in
                  multi-access  networks,  this  field is used in
                  the designated router election algorithm.  The
                  value 0 signifies that the router is not eligi-
                  ble to become the  designated  router  on  this
                  particular  network.   In the event of a tie in
                  this value, routers will use their Router ID as
                  a tie breaker."
        DEFVAL    { 1 }
        ::= { axsOspfv3IfEntry 6 }

    axsOspfv3IfTransitDelay OBJECT-TYPE
        SYNTAX    UpToMaxAge
        ACCESS    read-only
        STATUS    mandatory
        DESCRIPTION
                  "The estimated number of seconds  it  takes  to
                  transmit  a  link state update packet over this
                  interface."
        DEFVAL    { 1 }
        ::= { axsOspfv3IfEntry 7 }

    axsOspfv3IfRetransInterval OBJECT-TYPE
        SYNTAX    UpToMaxAge
        ACCESS    read-only
        STATUS    mandatory
        DESCRIPTION
                  "The number of seconds between  link-state  ad-
                  vertisement  retransmissions,  for  adjacencies
                  belonging to this  interface.  This  value  is
                  also used when retransmitting database descrip-
                  tion and link-state request packets."
        DEFVAL    { 5 }
        ::= { axsOspfv3IfEntry 8 }

    axsOspfv3IfHelloInterval OBJECT-TYPE
        SYNTAX    HelloRange
        ACCESS    read-only
        STATUS    mandatory
        DESCRIPTION
                  "The length of time, in  seconds,  between  the
                  Hello  packets that the router sends on the in-
                  terface.  This value must be the same  for  all
                  routers attached to a common network."
        DEFVAL    { 10 }
        ::= { axsOspfv3IfEntry 9 }

    axsOspfv3IfRtrDeadInterval OBJECT-TYPE
        SYNTAX    PositiveInteger
        ACCESS    read-only
        STATUS    mandatory
        DESCRIPTION
                  "The number of seconds that  a  router's  Hello
                  packets  have  not been seen before it's neigh-
                  bors declare the router down.  This  should  be
                  some  multiple  of  the  Hello  interval.  This
                  value must be the same for all routers attached
                  to a common network."
        DEFVAL    { 40 }
        ::= { axsOspfv3IfEntry 10 }

    axsOspfv3IfPollInterval OBJECT-TYPE
        SYNTAX    PositiveInteger
        ACCESS    read-only
        STATUS    mandatory
        DESCRIPTION
                  "The larger time interval, in seconds,  between
                  the  Hello  packets  sent  to  an inactive non-
                  broadcast multi- access neighbor."
        DEFVAL    { 120 }
        ::= { axsOspfv3IfEntry 11 }

    axsOspfv3IfState OBJECT-TYPE
        SYNTAX    INTEGER {
                      down(1),
                      loopback(2),
                      waiting(3),
                      pointToPoint(4),
                      designatedRouter(5),
                      backupDesignatedRouter(6),
                      otherDesignatedRouter(7)
                  }
        ACCESS    read-only
        STATUS    mandatory
        DESCRIPTION
                  "The axsOspfv3 Interface State."
        DEFVAL    { down }
        ::= { axsOspfv3IfEntry 12 }

    axsOspfv3IfDesignatedRouter OBJECT-TYPE
        SYNTAX    RouterID
        ACCESS    read-only
        STATUS    mandatory
        DESCRIPTION
                  "The Router ID of the Designated Router."
        DEFVAL    { '00000000'H } -- 0.0.0.0
        ::= { axsOspfv3IfEntry 13 }

    axsOspfv3IfBackupDesignatedRouter OBJECT-TYPE
        SYNTAX    RouterID
        ACCESS    read-only
        STATUS    mandatory
        DESCRIPTION
                  "The  Router ID of  the  Backup   Designated
                  Router."
        DEFVAL    { '00000000'H } -- 0.0.0.0
        ::= { axsOspfv3IfEntry 15 }

    axsOspfv3IfEvents OBJECT-TYPE
        SYNTAX    Counter32
        ACCESS    read-only
        STATUS    mandatory
        DESCRIPTION
                  "The number of times this  OSPF  interface  has
                  changed its state, or an error has occurred."
        ::= { axsOspfv3IfEntry 16 }

    axsOspfv3IfStatus OBJECT-TYPE
        SYNTAX    RowStatus
        ACCESS    read-only
        STATUS    mandatory
        DESCRIPTION
                  "This variable displays the status of  the  en-
                  try.  Setting it to 'invalid' has the effect of
                  rendering it inoperative.  The internal  effect
                  (row removal) is implementation dependent."
        ::= { axsOspfv3IfEntry 18 }

    axsOspfv3IfMulticastForwarding OBJECT-TYPE
        SYNTAX    INTEGER {
                      blocked(1),   -- no multicast forwarding
                      multicast(2), -- using multicast address
                      unicast(3)    -- to each axsOspfv3 neighbor
                  }
        ACCESS    read-only
        STATUS    mandatory
        DESCRIPTION
                  "The way multicasts should  forwarded  on  this
                  interface;  not  forwarded,  forwarded  as data
                  link multicasts, or forwarded as data link uni-
                  casts.  Data link multicasting is not meaning-
                  ful on point to point and NBMA interfaces, and
                  setting axsOspfv3MulticastForwarding to 0 effective-
                  ly disables all multicast forwarding."
        DEFVAL    { blocked }
        ::= { axsOspfv3IfEntry 19 }

    axsOspfv3IfDemand OBJECT-TYPE
        SYNTAX    TruthValue
        ACCESS    read-only
        STATUS    mandatory
        DESCRIPTION
                  "Indicates whether Demand axsOspfv3 procedures (hel-
                  lo supression to FULL neighbors and setting the
                  DoNotAge flag on proogated LSAs) should be per-
                  formed on this interface."
        DEFVAL    { false }
        ::= { axsOspfv3IfEntry 20 }

    axsOspfv3IfMetricValue OBJECT-TYPE
        SYNTAX    Metric
        ACCESS    read-only
        STATUS    mandatory
        DESCRIPTION
                  "The metric assigned to this interface.
                  The default value of the Metric is
                  10^8 / ifSpeed."
        ::= { axsOspfv3IfEntry 21 }

    axsOspfv3IfLinkScopeLsaCount OBJECT-TYPE
        SYNTAX    Gauge32
        ACCESS    read-only
        STATUS    mandatory
        DESCRIPTION
                  "The total number of Link-Scope link-state
                  advertisements in  this  link's link-state database."
        ::= { axsOspfv3IfEntry 22 }

    axsOspfv3IfLinkLsaCksumSum OBJECT-TYPE
        SYNTAX    Integer32
        ACCESS    read-only
        STATUS    mandatory
        DESCRIPTION
                  "The 32-bit unsigned sum of the Link-Scope link-state
                  advertisements'  LS  checksums  contained in this
                  link's link-state database.  The sum can be used
                  to determine if  there  has been  a  change  in a
                  router's link state database, and to compare the
                  link-state database of two routers."
        DEFVAL    { 0 }
        ::= { axsOspfv3IfEntry 23 }

    axsOspfv3IfInstId OBJECT-TYPE
        SYNTAX    Integer32
        ACCESS    read-only
        STATUS    mandatory
        DESCRIPTION
                  "Enables multiple instances of axsOspfv3 to be run over
                  a single link. Each protocol instance would be assigned
                  a separate ID. This ID has local link significance
                  only."
        DEFVAL    { 0 }
        ::= { axsOspfv3IfEntry 24 }

-- axsOspfv3 Virtual Interface Table
--   The Virtual Interface Table describes the virtual
--   links that the axsOspfv3 Process is configured to
--   carry on.

    axsOspfv3VirtIfTable OBJECT-TYPE
        SYNTAX    SEQUENCE OF AxsOspfv3VirtIfEntry
        ACCESS    not-accessible
        STATUS    mandatory
        DESCRIPTION
                  "Information about this router's virtual inter-
                  faces."
        REFERENCE
                  "OSPF Version  2,  Appendix  C.4   Virtual  link
                  parameters"
        ::= { axsOspfv3 8 }

    axsOspfv3VirtIfEntry OBJECT-TYPE
        SYNTAX    AxsOspfv3VirtIfEntry
        ACCESS    not-accessible
        STATUS    mandatory
        DESCRIPTION
                  "Information about a single Virtual Interface."
        INDEX     { axsOspfv3VirtIfDomainNumber,
                    axsOspfv3VirtIfAreaId,
                    axsOspfv3VirtIfNeighbor }
        ::= { axsOspfv3VirtIfTable 1 }

    AxsOspfv3VirtIfEntry ::= SEQUENCE {
        axsOspfv3VirtIfDomainNumber         INTEGER,
        axsOspfv3VirtIfAreaId               AreaID,
        axsOspfv3VirtIfNeighbor             RouterID,
        axsOspfv3VirtIfIndex                Ipv6IfIndex,
        axsOspfv3VirtIfTransitDelay         UpToMaxAge,
        axsOspfv3VirtIfRetransInterval      UpToMaxAge,
        axsOspfv3VirtIfHelloInterval        HelloRange,
        axsOspfv3VirtIfRtrDeadInterval      PositiveInteger,
        axsOspfv3VirtIfState                INTEGER,
        axsOspfv3VirtIfEvents               Counter32,
        axsOspfv3VirtIfStatus               RowStatus,
        axsOspfv3VirtIfLinkScopeLsaCount    Gauge32,
        axsOspfv3VirtIfLinkLsaCksumSum      Integer32
    }

    axsOspfv3VirtIfDomainNumber OBJECT-TYPE
        SYNTAX    INTEGER
        ACCESS    read-only
        STATUS    mandatory
        DESCRIPTION
                  "ospfv3 domain number."
        ::= { axsOspfv3VirtIfEntry 1 }

    axsOspfv3VirtIfAreaId OBJECT-TYPE
        SYNTAX    AreaID
        ACCESS    read-only
        STATUS    mandatory
        DESCRIPTION
                  "The  Transit  Area  that  the   Virtual   Link
                  traverses.  By definition, this is not 0.0.0.0"
        ::= { axsOspfv3VirtIfEntry 2 }

    axsOspfv3VirtIfNeighbor OBJECT-TYPE
        SYNTAX    RouterID
        ACCESS    read-only
        STATUS   mandatory
        DESCRIPTION
                  "The Router ID of the Virtual Neighbor."
        ::= { axsOspfv3VirtIfEntry 3 }

    axsOspfv3VirtIfIndex OBJECT-TYPE
        SYNTAX    Ipv6IfIndex
        ACCESS    read-only
        STATUS    mandatory
        DESCRIPTION
                  "The interface index of this axsOspfv3 virtual interface.
                  It must be unique among all the interface indices
                  on the router."
        ::= { axsOspfv3VirtIfEntry 4 }

    axsOspfv3VirtIfTransitDelay OBJECT-TYPE
        SYNTAX    UpToMaxAge
        ACCESS    read-only
        STATUS    mandatory
        DESCRIPTION
                  "The estimated number of seconds  it  takes  to
                  transmit  a link- state update packet over this
                  interface."
        DEFVAL    { 1 }
        ::= { axsOspfv3VirtIfEntry 5 }

    axsOspfv3VirtIfRetransInterval OBJECT-TYPE
        SYNTAX    UpToMaxAge
        ACCESS    read-only
        STATUS    mandatory
        DESCRIPTION
                  "The number of seconds between  link-state  ad-
                  vertisement  retransmissions,  for  adjacencies
                  belonging to this  interface.  This  value  is
                  also used when retransmitting database descrip-
                  tion  and  link-state  request  packets.   This
                  value  should  be well over the expected round-
                  trip time."
        DEFVAL    { 5 }
        ::= { axsOspfv3VirtIfEntry 6 }

    axsOspfv3VirtIfHelloInterval OBJECT-TYPE
        SYNTAX    HelloRange
        ACCESS    read-only
        STATUS    mandatory
        DESCRIPTION
                  "The length of time, in  seconds,  between  the
                  Hello  packets that the router sends on the in-
                  terface.  This value must be the same  for  the
                  virtual neighbor."
        DEFVAL    { 10 }
        ::= { axsOspfv3VirtIfEntry 7 }

    axsOspfv3VirtIfRtrDeadInterval OBJECT-TYPE
        SYNTAX    PositiveInteger
        ACCESS    read-only
        STATUS    mandatory
        DESCRIPTION
                  "The number of seconds that  a  router's  Hello
                  packets  have  not been seen before it's neigh-
                  bors declare the router down.  This  should  be
                  some  multiple  of  the  Hello  interval.  This
                  value must be the same for the  virtual  neigh-
                  bor."
        DEFVAL    { 60 }
        ::= { axsOspfv3VirtIfEntry 8 }

    axsOspfv3VirtIfState OBJECT-TYPE
        SYNTAX    INTEGER {
                      down(1),        -- these use the same encoding
                      pointToPoint(4) -- as the axsOspfv3IfTable
                  }
        ACCESS    read-only
        STATUS    mandatory
        DESCRIPTION
                  "OSPF virtual interface states."
        DEFVAL    { down }
        ::= { axsOspfv3VirtIfEntry 9 }

    axsOspfv3VirtIfEvents OBJECT-TYPE
        SYNTAX    Counter32
        ACCESS    read-only
        STATUS    mandatory
        DESCRIPTION
                  "The number of state changes or error events on
                  this Virtual Link"
        ::= { axsOspfv3VirtIfEntry 10 }

    axsOspfv3VirtIfStatus OBJECT-TYPE
        SYNTAX    RowStatus
        ACCESS    read-only
        STATUS    mandatory
        DESCRIPTION
                  "This variable displays the status of  the  en-
                  try.  Setting it to 'invalid' has the effect of
                  rendering it inoperative.  The internal  effect
                  (row removal) is implementation dependent."
            ::= { axsOspfv3VirtIfEntry 11 }

    axsOspfv3VirtIfLinkScopeLsaCount OBJECT-TYPE
        SYNTAX    Gauge32
        ACCESS    read-only
        STATUS    mandatory
        DESCRIPTION
                  "The total number of Link-Scope link-state
                  advertisements in  this  virtual link's link-state
                  database."
        ::= { axsOspfv3VirtIfEntry 12 }

    axsOspfv3VirtIfLinkLsaCksumSum OBJECT-TYPE
        SYNTAX    Integer32
        ACCESS    read-only
        STATUS    mandatory
        DESCRIPTION
                  "The 32-bit unsigned sum of the Link-Scope link-state
                  advertisements'  LS  checksums  contained in this
                  virtual link's link-state database.  The sum can be used
                  to determine if  there  has been  a  change  in a
                  router's link state database, and to compare the
                  link-state database of two routers."
        DEFVAL    { 0 }
        ::= { axsOspfv3VirtIfEntry 13 }

-- axsOspfv3 Neighbor Table
--   The axsOspfv3 Neighbor Table describes all neighbors in
--   the locality of the subject router.

    axsOspfv3NbrTable OBJECT-TYPE
        SYNTAX    SEQUENCE OF AxsOspfv3NbrEntry
        ACCESS    not-accessible
        STATUS    mandatory
        DESCRIPTION
                  "A table of non-virtual neighbor information."
        REFERENCE
                  "OSPF Version 2, Section 10  The  Neighbor  Data
                  Structure"
        ::= { axsOspfv3 9 }

    axsOspfv3NbrEntry OBJECT-TYPE
        SYNTAX    AxsOspfv3NbrEntry
        ACCESS    not-accessible
        STATUS    mandatory
        DESCRIPTION
                  "The information regarding a single neighbor."
        REFERENCE
                  "OSPF Version 2, Section 10  The  Neighbor  Data
                  Structure"
        INDEX     { axsOspfv3NbrDomainNumber,
                    axsOspfv3NbrIfIndex,
                    axsOspfv3NbrIpv6Addr }
        ::= { axsOspfv3NbrTable 1 }

    AxsOspfv3NbrEntry ::= SEQUENCE {
        axsOspfv3NbrDomainNumber       INTEGER,
        axsOspfv3NbrIfIndex            Ipv6IfIndex,
        axsOspfv3NbrIpv6Addr           Ipv6Address,
        axsOspfv3NbrRtrId              RouterID,
        axsOspfv3NbrOptions            Integer32,
        axsOspfv3NbrPriority           DesignatedRouterPriority,
        axsOspfv3NbrState              INTEGER,
        axsOspfv3NbrEvents             Counter32,
        axsOspfv3NbrLsRetransQLen      Gauge32,
        axsOspfv3NbrHelloSuppressed    TruthValue,
        axsOspfv3NbrIfId               Ipv6IfIndex
    }

    axsOspfv3NbrDomainNumber OBJECT-TYPE
        SYNTAX    INTEGER
        ACCESS    read-only
        STATUS    mandatory
        DESCRIPTION
                  "ospfv3 domain number."
        ::= { axsOspfv3NbrEntry 1 }

    axsOspfv3NbrIfIndex OBJECT-TYPE
        SYNTAX    Ipv6IfIndex
        ACCESS    read-only
        STATUS    mandatory
        DESCRIPTION
                  "The local link ID of the link over which the
                  neighbor can be reached."
        ::= { axsOspfv3NbrEntry 2 }

    axsOspfv3NbrIpv6Addr OBJECT-TYPE
        SYNTAX    Ipv6Address
        ACCESS    read-only
        STATUS    mandatory
        DESCRIPTION
                  "The IPv6 address of the neighbor associated with
                  the local link."
        ::= { axsOspfv3NbrEntry 3 }

    axsOspfv3NbrRtrId OBJECT-TYPE
        SYNTAX    RouterID
        ACCESS    read-only
        STATUS    mandatory
        DESCRIPTION
                  "A 32-bit integer (represented as a type  IpAd-
                  dress)  uniquely  identifying  the  neighboring
                  router in the Autonomous System."
        ::= { axsOspfv3NbrEntry 4 }

    axsOspfv3NbrOptions OBJECT-TYPE
        SYNTAX    Integer32
        ACCESS    read-only
        STATUS    mandatory
        DESCRIPTION
                  "A Bit Mask corresponding to the neighbor's op-
                  tions field."
        DEFVAL    { 0 }
        ::= { axsOspfv3NbrEntry 5 }

    axsOspfv3NbrPriority OBJECT-TYPE
        SYNTAX    DesignatedRouterPriority
        ACCESS    read-only
        STATUS    mandatory
        DESCRIPTION
                  "The priority of this neighbor in the designat-
                  ed router election algorithm.  The value 0 sig-
                  nifies that the neighbor is not eligible to be-
                  come  the  designated router on this particular
                  network."
        DEFVAL    { 1 }
        ::= { axsOspfv3NbrEntry 6 }

    axsOspfv3NbrState OBJECT-TYPE
        SYNTAX    INTEGER {
                      down(1),
                      attempt(2),
                      init(3),
                      twoWay(4),
                      exchangeStart(5),
                      exchange(6),
                      loading(7),
                      full(8)
                  }
        ACCESS    read-only
        STATUS    mandatory
        DESCRIPTION
                  "The State of the relationship with this Neigh-
                  bor."
        REFERENCE
                  "OSPF Version 2, Section 10.1 Neighbor States"
        DEFVAL    { down }
        ::= { axsOspfv3NbrEntry 7 }

    axsOspfv3NbrEvents OBJECT-TYPE
        SYNTAX    Counter32
        ACCESS    read-only
        STATUS    mandatory
        DESCRIPTION
                  "The number of times this neighbor relationship
                  has changed state, or an error has occurred."
        ::= { axsOspfv3NbrEntry 8 }

    axsOspfv3NbrLsRetransQLen OBJECT-TYPE
        SYNTAX    Gauge32
        ACCESS    read-only
        STATUS    mandatory
        DESCRIPTION
                  "The  current  length  of  the   retransmission
                  queue."
        ::= { axsOspfv3NbrEntry 9 }

    axsOspfv3NbrHelloSuppressed OBJECT-TYPE
        SYNTAX    TruthValue
        ACCESS    read-only
        STATUS    mandatory
        DESCRIPTION
                  "Indicates whether Hellos are being  suppressed
                  to the neighbor"
        ::= { axsOspfv3NbrEntry 12 }

    axsOspfv3NbrIfId OBJECT-TYPE
        SYNTAX    Ipv6IfIndex
        ACCESS    read-only
        STATUS    mandatory
        DESCRIPTION
                  "The interface ID that the neighbor advertises
                  in its Hello Packets on this link, that is, the
                  neighbor's local interface index."
        ::= { axsOspfv3NbrEntry 13 }

-- axsOspfv3 Virtual Neighbor Table
--   This table describes all virtual neighbors.
--   Since Virtual Links are configured in the
--   virtual interface table, this table is read-only.

    axsOspfv3VirtNbrTable OBJECT-TYPE
        SYNTAX    SEQUENCE OF AxsOspfv3VirtNbrEntry
        ACCESS    not-accessible
        STATUS    mandatory
        DESCRIPTION
                  "A table of virtual neighbor information."
        REFERENCE
                  "OSPF Version 2, Section 15  Virtual Links"
        ::= { axsOspfv3 10 }

    axsOspfv3VirtNbrEntry OBJECT-TYPE
        SYNTAX    AxsOspfv3VirtNbrEntry
        ACCESS    not-accessible
        STATUS    mandatory
        DESCRIPTION
                  "Virtual neighbor information."
        INDEX     { axsOspfv3VirtNbrDomainNumber,
                    axsOspfv3VirtNbrArea,
                    axsOspfv3VirtNbrRtrId }
        ::= { axsOspfv3VirtNbrTable 1 }

    AxsOspfv3VirtNbrEntry ::= SEQUENCE {
        axsOspfv3VirtNbrDomainNumber       INTEGER,
        axsOspfv3VirtNbrArea               AreaID,
        axsOspfv3VirtNbrRtrId              RouterID,
        axsOspfv3VirtNbrIfIndex            Ipv6IfIndex,
        axsOspfv3VirtNbrIpv6Addr           Ipv6Address,
        axsOspfv3VirtNbrOptions            Integer32,
        axsOspfv3VirtNbrState              INTEGER,
        axsOspfv3VirtNbrEvents             Counter32,
        axsOspfv3VirtNbrLsRetransQLen      Gauge32,
        axsOspfv3VirtNbrHelloSuppressed    TruthValue,
        axsOspfv3VirtNbrIfId               Ipv6IfIndex
    }

    axsOspfv3VirtNbrDomainNumber OBJECT-TYPE
        SYNTAX    INTEGER
        ACCESS    read-only
        STATUS    mandatory
        DESCRIPTION
                  "ospfv3 domain number."
        ::= { axsOspfv3VirtNbrEntry 1 }

    axsOspfv3VirtNbrArea OBJECT-TYPE
        SYNTAX    AreaID
        ACCESS    read-only
        STATUS    mandatory
        DESCRIPTION
                  "The Transit Area Identifier."
        ::= { axsOspfv3VirtNbrEntry 2 }

    axsOspfv3VirtNbrRtrId OBJECT-TYPE
        SYNTAX    RouterID
        ACCESS    read-only
        STATUS    mandatory
        DESCRIPTION
                  "A  32-bit  integer  uniquely  identifying  the
                  neighboring router in the Autonomous System."
        ::= { axsOspfv3VirtNbrEntry 3 }

    axsOspfv3VirtNbrIfIndex OBJECT-TYPE
        SYNTAX    Ipv6IfIndex
        ACCESS    read-only
        STATUS    mandatory
        DESCRIPTION
                  "The local link ID for the virtual link over
                  which the neighbor can be reached."
        ::= { axsOspfv3VirtNbrEntry 4 }

    axsOspfv3VirtNbrIpv6Addr OBJECT-TYPE
        SYNTAX    Ipv6Address
        ACCESS    read-only
        STATUS    mandatory
        DESCRIPTION
                  "The IPv6 address used to reach this Virtual Neighbor.
                  It must be a Site-Local or Global scope address."
        ::= { axsOspfv3VirtNbrEntry 5 }

    axsOspfv3VirtNbrOptions OBJECT-TYPE
        SYNTAX    Integer32
        ACCESS    read-only
        STATUS    mandatory
        DESCRIPTION
                  "A Bit Mask corresponding to the neighbor's op-
                  tions field."
        ::= { axsOspfv3VirtNbrEntry 6 }

    axsOspfv3VirtNbrState OBJECT-TYPE
        SYNTAX    INTEGER {
                      down(1),
                      attempt(2),
                      init(3),
                      twoWay(4),
                      exchangeStart(5),
                      exchange(6),
                      loading(7),
                      full(8)
                  }
        ACCESS    read-only
        STATUS    mandatory
        DESCRIPTION
                  "The state of the  Virtual  Neighbor  Relation-
                  ship."
        ::= { axsOspfv3VirtNbrEntry 7 }

    axsOspfv3VirtNbrEvents OBJECT-TYPE
        SYNTAX    Counter32
        ACCESS    read-only
        STATUS    mandatory
        DESCRIPTION
                  "The number of  times  this  virtual  link  has
                  changed its state, or an error has occurred."
        ::= { axsOspfv3VirtNbrEntry 8 }

    axsOspfv3VirtNbrLsRetransQLen OBJECT-TYPE
        SYNTAX    Gauge32
        ACCESS    read-only
        STATUS    mandatory
        DESCRIPTION
                  "The  current  length  of  the   retransmission
                  queue."
        ::= { axsOspfv3VirtNbrEntry 9 }

    axsOspfv3VirtNbrHelloSuppressed OBJECT-TYPE
        SYNTAX    TruthValue
        ACCESS    read-only
        STATUS    mandatory
        DESCRIPTION
                  "Indicates whether Hellos are being  suppressed
                  to the neighbor"
        ::= { axsOspfv3VirtNbrEntry 10 }

    axsOspfv3VirtNbrIfId OBJECT-TYPE
        SYNTAX    Ipv6IfIndex
        ACCESS    read-only
        STATUS    mandatory
        DESCRIPTION
                  "The interface ID that the neighbor advertises
                  in its Hello Packets on this virtual link, that is,
                  the neighbor's local interface index."
        ::= { axsOspfv3VirtNbrEntry 11 }

--
-- The axsOspfv3 Area Aggregate Table
--

    axsOspfv3AreaAggregateTable OBJECT-TYPE
        SYNTAX    SEQUENCE OF AxsOspfv3AreaAggregateEntry
        ACCESS    not-accessible
        STATUS    mandatory
        DESCRIPTION
                  "A range of IPv6 prefixes specified by a
                  prefix/prefix length  pair. Note that if
                  ranges are configured such that one range sub-
                  sumes  another range the most specific match is
                  the preferred one."
        ::= { axsOspfv3 11 }

    axsOspfv3AreaAggregateEntry OBJECT-TYPE
        SYNTAX    AxsOspfv3AreaAggregateEntry
        ACCESS    not-accessible
        STATUS    mandatory
        DESCRIPTION
                  "A range of IPv6 prefixes specified by a
                  prefix/prefix length  pair. Note that if
                  ranges are configured such that one range sub-
                  sumes  another range the most specific match is
                  the preferred one."
        REFERENCE
                  "OSPF Version 2, Appendix C.2  Area parameters"
        INDEX     { axsOspfv3AreaAggregateDomainNumber,
                    axsOspfv3AreaAggregateAreaID,
                    axsOspfv3AreaAggregateAreaLsdbType,
                    axsOspfv3AreaAggregateIndex }
        ::= { axsOspfv3AreaAggregateTable 1 }

    AxsOspfv3AreaAggregateEntry ::= SEQUENCE {
        axsOspfv3AreaAggregateDomainNumber    INTEGER,
        axsOspfv3AreaAggregateAreaID          AreaID,
        axsOspfv3AreaAggregateAreaLsdbType    INTEGER,
        axsOspfv3AreaAggregateIndex           INTEGER,
        axsOspfv3AreaAggregatePrefix          Ipv6AddressPrefix,
        axsOspfv3AreaAggregatePrefixLen       INTEGER,
        axsOspfv3AreaAggregateStatus          RowStatus,
        axsOspfv3AreaAggregateEffect          INTEGER
    }

    axsOspfv3AreaAggregateDomainNumber OBJECT-TYPE
        SYNTAX    INTEGER
        ACCESS    read-only
        STATUS    mandatory
        DESCRIPTION
                  "ospfv3 domain number."
        ::= { axsOspfv3AreaAggregateEntry 1 }

    axsOspfv3AreaAggregateAreaID OBJECT-TYPE
        SYNTAX    AreaID
        ACCESS    read-only
        STATUS    mandatory
        DESCRIPTION
                  "The Area the Address Aggregate is to be  found
                  within."
        REFERENCE
                  "OSPF Version 2, Appendix C.2 Area parameters"
        ::= { axsOspfv3AreaAggregateEntry 2 }

    axsOspfv3AreaAggregateAreaLsdbType OBJECT-TYPE
        SYNTAX    INTEGER {
                      interAreaPrefixLsa(8195), -- 0x2003
                      nssaExternalLsa(8199)     -- 0x2007
                  }
        ACCESS    read-only
        STATUS    mandatory
        DESCRIPTION
                  "The type of the Address Aggregate.  This field
                  specifies  the  Area Lsdb type that this Address Ag-
                  gregate applies to."
        REFERENCE
                  "OSPF Version 2, Appendix A.4.1 The  Link  State
                  Advertisement header"
        ::= { axsOspfv3AreaAggregateEntry 3 }

    axsOspfv3AreaAggregateIndex OBJECT-TYPE
        SYNTAX    INTEGER (1..2147483647)
        ACCESS    read-only
        STATUS    mandatory
        DESCRIPTION
                  "A unique identifier for this aggregate table entry."
        ::= { axsOspfv3AreaAggregateEntry 4 }

    axsOspfv3AreaAggregatePrefix OBJECT-TYPE
        SYNTAX    Ipv6AddressPrefix
        ACCESS    read-only
        STATUS    mandatory
        DESCRIPTION
                  "The IPv6 Prefix."
        REFERENCE
                  "OSPF Version 2, Appendix C.2 Area parameters"
        ::= { axsOspfv3AreaAggregateEntry 5 }

    axsOspfv3AreaAggregatePrefixLen OBJECT-TYPE
        SYNTAX    INTEGER ( 3..128 )
--      UNITS     "bits"
        ACCESS    read-only
        STATUS    mandatory
        DESCRIPTION
                  "The length of the prefix (in bits). A prefix can
                  not be shorter than 3 bits."
        REFERENCE
                  "OSPF Version 2, Appendix C.2 Area parameters"
        ::= { axsOspfv3AreaAggregateEntry 6 }

    axsOspfv3AreaAggregateStatus OBJECT-TYPE
        SYNTAX    RowStatus
        ACCESS    read-only
        STATUS    mandatory
        DESCRIPTION
                  "This variable displays the status of  the  en-
                  try.  Setting it to 'invalid' has the effect of
                  rendering it inoperative.  The internal  effect
                  (row removal) is implementation dependent."
        ::= { axsOspfv3AreaAggregateEntry 7 }

    axsOspfv3AreaAggregateEffect OBJECT-TYPE
        SYNTAX    INTEGER {
                      advertiseMatching(1),
                      doNotAdvertiseMatching(2)
                  }
        ACCESS    read-only
        STATUS    mandatory
        DESCRIPTION
                  "Prefixes subsumed by ranges either trigger  the
                  advertisement  of  the indicated aggregate (ad-
                  vertiseMatching), or result in the prefix not
                  being advertised at all outside the area."
        DEFVAL    { advertiseMatching }
        ::= { axsOspfv3AreaAggregateEntry 8 }

-- axsStatic

    axsStaticTable OBJECT-TYPE
        SYNTAX    SEQUENCE OF AxsStaticGatewayEntry
        ACCESS    not-accessible
        STATUS    mandatory
        DESCRIPTION
                  "The set of instances of the static gateway state."
        ::= { axsStatic 1 }

    axsStaticGatewayEntry OBJECT-TYPE
        SYNTAX    AxsStaticGatewayEntry
        ACCESS    not-accessible
        STATUS    mandatory
        DESCRIPTION
                  "Each row defines information about static route gateway state."
        INDEX     { axsStaticGatewayAddr }
        ::= { axsStaticTable 1 }

    AxsStaticGatewayEntry ::= SEQUENCE {
        axsStaticGatewayAddr     IpAddress,
        axsStaticGatewayState    INTEGER
    }

    axsStaticGatewayAddr OBJECT-TYPE
        SYNTAX    IpAddress
        ACCESS    not-accessible
        STATUS    mandatory
        DESCRIPTION
                  "The static route gateway address."
        ::= { axsStaticGatewayEntry 1 }
        
    axsStaticGatewayState OBJECT-TYPE
        SYNTAX    INTEGER {
                      reachable(1),
                      unreachable(2)
                  }
        ACCESS    not-accessible
        STATUS    mandatory
        DESCRIPTION
                  "The state of static route gateway."
        ::= { axsStaticGatewayEntry 2 }

    axsStaticIpv6Table OBJECT-TYPE
        SYNTAX    SEQUENCE OF AxsStaticIpv6GatewayEntry
        ACCESS    not-accessible
        STATUS    mandatory
        DESCRIPTION
                  "The set of instances of the ipv6 static gateway state."
        ::= { axsStatic 3 }

    axsStaticIpv6GatewayEntry OBJECT-TYPE
        SYNTAX    AxsStaticIpv6GatewayEntry
        ACCESS    not-accessible
        STATUS    mandatory
        DESCRIPTION
                  "Each row defines information about ipv6 static route gateway state."
        INDEX { axsStaticIpv6Ifindex,
                axsStaticIpv6GatewayAddr }
        ::= { axsStaticIpv6Table 1 }

    AxsStaticIpv6GatewayEntry ::= SEQUENCE {
        axsStaticIpv6Ifindex        INTEGER,
        axsStaticIpv6GatewayAddr    Ipv6Address,
        axsStaticIpv6GatewayState   INTEGER
    }

    axsStaticIpv6Ifindex OBJECT-TYPE
        SYNTAX    INTEGER
        ACCESS    not-accessible
        STATUS    mandatory
        DESCRIPTION
                  "The ifIndex ralated static gateway address."
        ::= { axsStaticIpv6GatewayEntry 1 }

    axsStaticIpv6GatewayAddr OBJECT-TYPE
        SYNTAX    Ipv6Address
        ACCESS    not-accessible
        STATUS    mandatory
        DESCRIPTION
                  "The static route gateway address."
        ::= { axsStaticIpv6GatewayEntry 2 }

    axsStaticIpv6GatewayState OBJECT-TYPE
        SYNTAX    INTEGER {
                      reachable(1),
                      unreachable(2)
                  }
        ACCESS    not-accessible
        STATUS    mandatory
        DESCRIPTION
                  "The state of static route gateway."
        ::= { axsStaticIpv6GatewayEntry 3 }

-- axsTrack

    axsTrackGeneralLastChange OBJECT-TYPE
        SYNTAX    TimeTicks
        ACCESS    read-only
        STATUS    mandatory
        DESCRIPTION
                  "The last time that the tracking object state changed."
        ::= { axsTrackGeneralGroup 1 }
    
    axsTrackTable OBJECT-TYPE
        SYNTAX    SEQUENCE OF AxsTrackEntry
        ACCESS    not-accessible
        STATUS    mandatory
        DESCRIPTION
                  "This table containing the tracking information."
        ::= { axsTrack 3 }
    
    axsTrackEntry OBJECT-TYPE
        SYNTAX    AxsTrackEntry
        ACCESS    not-accessible
        STATUS    mandatory
        DESCRIPTION
                  "The entry of track information."
        INDEX { axsTrackId }
        ::= { axsTrackTable 1 }
    
    AxsTrackEntry ::= SEQUENCE {
        axsTrackId                   INTEGER,
        axsTrackState                INTEGER,
        axsTrackOperation            INTEGER,
        axsTrackType                 INTEGER,
        axsTrackListType             INTEGER,
        axsTrackVrfIndex             INTEGER
    }
    
    axsTrackId OBJECT-TYPE
        SYNTAX    INTEGER
        ACCESS    read-only
        STATUS    mandatory
        DESCRIPTION
                  "The unique index number given for each track-advanced settings."
        ::= { axsTrackEntry 1 }
    
    axsTrackState OBJECT-TYPE
        SYNTAX    INTEGER {
                      up(1),
                      down(2)
                  }
        ACCESS    read-only
        STATUS    mandatory
        DESCRIPTION
                  "The state of the track."
        ::= { axsTrackEntry 2 }
    
    axsTrackOperation OBJECT-TYPE
        SYNTAX    INTEGER {
                      active(1),
                      transit(2),
                      disabled(3),
                      init(4),
                      aging(5)
                  }
        ACCESS    read-only
        STATUS    mandatory
        DESCRIPTION
                  "The operation state of the track."
        ::= { axsTrackEntry 3 }
    
    axsTrackType OBJECT-TYPE
        SYNTAX    INTEGER {
                      list(1),
                      ipv4-icmp(2)
                  }
        ACCESS    read-only
        STATUS    mandatory
        DESCRIPTION
                  "The tracking type of the track."
        ::= { axsTrackEntry 4 }
    
    axsTrackListType OBJECT-TYPE
        SYNTAX    INTEGER {
                      other(0),
                      and(1),
                      or(2)
                  }
        ACCESS    read-only
        STATUS    mandatory
        DESCRIPTION
                  "The boolean type of the list tracking."
        ::= { axsTrackEntry 5 }
    
    axsTrackVrfIndex OBJECT-TYPE
        SYNTAX    INTEGER
        ACCESS    read-only
        STATUS    mandatory
        DESCRIPTION
                  "The VRF ID of the ICMP tracking object."
        ::= { axsTrackEntry 6 }

--  axsTrackObject

    axsTrackObjectGeneralLastChange OBJECT-TYPE
        SYNTAX    TimeTicks
        ACCESS    read-only
        STATUS    mandatory
        DESCRIPTION
                  "The last time that the tracking object state changed."
        ::= { axsTrackObjectGeneralGroup  1 }

    axsTrackObjectTable OBJECT-TYPE
        SYNTAX    SEQUENCE OF AxsTrackObjectEntry
        ACCESS    not-accessible
        STATUS    mandatory
        DESCRIPTION
                  "This table containing the tracking information."
        ::= { axsTrackObject 3 }

    axsTrackObjectEntry OBJECT-TYPE
        SYNTAX    AxsTrackObjectEntry
        ACCESS    not-accessible
        STATUS    mandatory
        DESCRIPTION
                  "The entry of track information."
        INDEX { axsTrackObjectId }
        ::= { axsTrackObjectTable 1 }
    
    AxsTrackObjectEntry ::= SEQUENCE {
        axsTrackObjectId             INTEGER,
        axsTrackObjectState          INTEGER,
        axsTrackObjectOperation      INTEGER,
        axsTrackObjectType           INTEGER,
        axsTrackObjectNetIndex       INTEGER
    }
    
    axsTrackObjectId OBJECT-TYPE
        SYNTAX    INTEGER
        ACCESS    read-only
        STATUS    mandatory
        DESCRIPTION
                  "The unique index number given for each track-object settings."
        ::= { axsTrackObjectEntry 1 }
    
    axsTrackObjectState OBJECT-TYPE
        SYNTAX    INTEGER {
                      up(1),
                      down(2)
                  }
        ACCESS    read-only
        STATUS    mandatory
        DESCRIPTION
                  "The state of the track."
        ::= { axsTrackObjectEntry 2 }
    
    axsTrackObjectOperation OBJECT-TYPE
        SYNTAX    INTEGER {
                      active(1),
                      transit(2),
                      disabled(3),
                      init(4),
                      aging(5)
                  }
        ACCESS    read-only
        STATUS    mandatory
        DESCRIPTION
                  "The operation state of the track."
        ::= { axsTrackObjectEntry 3 }
    
    axsTrackObjectType OBJECT-TYPE
        SYNTAX    INTEGER {
                      ipv4-icmp(1),
                      ipv4-tcp-polling(2)
                  }
        ACCESS    read-only
        STATUS    mandatory
        DESCRIPTION
                  "The tracking type of the track."
        ::= { axsTrackObjectEntry 4 }
    
    axsTrackObjectNetIndex OBJECT-TYPE
        SYNTAX    INTEGER
        ACCESS    read-only
        STATUS    mandatory
        DESCRIPTION
                  "The network ID of the ICMP tracking object."
        ::= { axsTrackObjectEntry 5 }

-- axsPolicyBase

    axsPolicyBaseRoutingChangeListNumber OBJECT-TYPE
        SYNTAX          Unsigned32
        ACCESS          not-accessible
        STATUS          mandatory
        DESCRIPTION
                  "List number change is generated by policy base routing."
        ::= { axsPolicyBaseRouting 1 }

    axsPolicyBaseRoutingChangeSequenceNumber OBJECT-TYPE
        SYNTAX          Unsigned32
        ACCESS          not-accessible
        STATUS          mandatory
        DESCRIPTION
                  "Priority changed by the list number of the policy base routing."
        ::= { axsPolicyBaseRouting 2 }

    axsPolicyBaseSwitchingChangeListNumber OBJECT-TYPE
        SYNTAX          Unsigned32
        ACCESS          not-accessible
        STATUS          mandatory
        DESCRIPTION
                  "List number change is generated by policy base switching."
        ::= { axsPolicyBaseSwitching 1 }

    axsPolicyBaseSwitchingChangeSequenceNumber OBJECT-TYPE
        SYNTAX          Unsigned32
        ACCESS          not-accessible
        STATUS          mandatory
        DESCRIPTION
                  "Priority changed by the list number of the policy base switching."
        ::= { axsPolicyBaseSwitching 2 }

--  axsLogin

    axsLoginName OBJECT-TYPE
        SYNTAX    DisplayString
        ACCESS    not-accessible
        STATUS    mandatory
        DESCRIPTION
                  "Log in user name."
        ::= { axsLogin 1 }

    axsLoginTime OBJECT-TYPE
        SYNTAX    DisplayString
        ACCESS    not-accessible
        STATUS    mandatory
        DESCRIPTION
                  "Date, time and time zone of user log in.
                           Format : YYYY/MM/DD hh:mm:ss XXXXXX(time zone)
                   Time zone format :
                     JST    : JST
                             GMT+09 : GMT + 09 hours
                             GMT+10 : GMT + 10 hours"
        ::= { axsLogin 2 }

    axsLogoutTime OBJECT-TYPE
        SYNTAX    DisplayString
        ACCESS    not-accessible
        STATUS    mandatory
        DESCRIPTION
                  "Date, time and time zone of user log out.
                  Format : YYYY/MM/DD hh:mm:ss XXXXXX(time zone)
                  Time zone format :
                    JST    : JST
                    GMT+09 : GMT + 09 hours
                    GMT+10 : GMT + 10 hours"
        ::= { axsLogin 3 }

    axsLoginFailureTime OBJECT-TYPE
        SYNTAX    DisplayString
        ACCESS    not-accessible
        STATUS    mandatory
        DESCRIPTION
                  "Date, time and time zone of user log in failure.
                  Format : YYYY/MM/DD hh:mm:ss XXXXXX(time zone)
                  Time zone format :
                    JST    : JST
                    GMT+09 : GMT + 09 hours
                    GMT+10 : GMT + 10 hours"
        ::= { axsLogin 4 }

    axsLoginLocation OBJECT-TYPE
        SYNTAX    DisplayString
        ACCESS    not-accessible
        STATUS    mandatory
        DESCRIPTION
                  "Terminal information of log in user.
                  The status will be 'console' or 'aux'.
                  If other, displays 'TERMINAL(APLLICATION)'.
                  ex. 'tty/1(telnet)'"
        ::= { axsLogin 5 }

    axsLoginLine OBJECT-TYPE
        SYNTAX    DisplayString
        ACCESS    not-accessible
        STATUS    mandatory
        DESCRIPTION
                  "Connection information of log in user.
                  The status will be 'console' or 'aux'.
                  If other, displays 'IPADDRESS(APLLICATION)'.
                  ex. '192.168.11.1(telnet)'"
        ::= { axsLogin 6 }

    axsLogoutStatus OBJECT-TYPE
        SYNTAX    INTEGER {
                      error(1),
                      success(2),
                      timeout(3),
                      disconnect(4),
                      force(5)
                  }
        ACCESS    not-accessible
        STATUS    mandatory
        DESCRIPTION
                  "Log out factor.
                   error(1)      : log out due to none of bellow
                   success(2)    : log out due to command
                   timeout(3)    : log out due to 'auto-logout'
                   disconnect(4) : log out due to line disconnection
                   force(5)      : log out due to other user's command"
        ::= { axsLogin 7 }

-- axsAxrp group

    axsAxrpGroupTable OBJECT-TYPE
        SYNTAX    SEQUENCE OF AxsAxrpGroupEntry
        ACCESS    not-accessible
        STATUS    mandatory
        DESCRIPTION
                  "The table containing AXRP group information."
        ::= { axsAxrp 1 }

    axsAxrpGroupEntry OBJECT-TYPE
        SYNTAX    AxsAxrpGroupEntry
        ACCESS    not-accessible
        STATUS    mandatory
        DESCRIPTION
                  "The list of AXRP group information."
        INDEX     { axsAxrpGroupRingId }
        ::= { axsAxrpGroupTable 1 }

    AxsAxrpGroupEntry ::= SEQUENCE {
        axsAxrpGroupRingId                      INTEGER,
        axsAxrpGroupRowStatus                   RowStatus,
        axsAxrpGroupMode                        INTEGER,
        axsAxrpGroupRingAttribute               INTEGER,
        axsAxrpGroupMonitoringState             INTEGER,
        axsAxrpGroupRingport1                   INTEGER,
        axsAxrpGroupRingport1Shared             INTEGER,
        axsAxrpGroupRingport2                   INTEGER,
        axsAxrpGroupRingport2Shared             INTEGER,
        axsAxrpGroupTransitionToFaultCounts     Counter,
        axsAxrpGroupTransitionToNormalCounts    Counter,
        axsAxrpGroupLastTransitionTime          TimeStamp
    }

    axsAxrpGroupRingId OBJECT-TYPE
        SYNTAX    INTEGER
        ACCESS    not-accessible
        STATUS    mandatory
        DESCRIPTION
                  "AXRP group ring identifier."
        ::= { axsAxrpGroupEntry 1 }

    axsAxrpGroupRowStatus OBJECT-TYPE
        SYNTAX    RowStatus
        ACCESS    read-only
        STATUS    mandatory
        DESCRIPTION
                  "Valid/Invalid state of this entry. Valid(1) fixed"
        ::= { axsAxrpGroupEntry 2 }

    axsAxrpGroupMode OBJECT-TYPE
        SYNTAX    INTEGER{
                      no-config(1),
                      master(2),
                      transit(3)
                  }
        ACCESS    read-only
        STATUS    mandatory
        DESCRIPTION
                  "Operation mode of each ring ID."
        ::= { axsAxrpGroupEntry 3 }

    axsAxrpGroupRingAttribute OBJECT-TYPE
        SYNTAX    INTEGER {
                      no-config(1),
                      rift-ring(2),
                      rift-ring-edge1(3),
                      rift-ring-edge2(4)
                  }
        ACCESS    read-only
        STATUS    mandatory
        DESCRIPTION
                  "When the multi ring is composed, it is an attribute of this device in the common link non-watch ring. "
        ::= { axsAxrpGroupEntry 4 }

    axsAxrpGroupMonitoringState OBJECT-TYPE
        SYNTAX    INTEGER{
                      init(1),
                      disable(2),
                      fault-monitoring(3),
                      recovery-monitoring(4),
                      flush-monitoring(5),
                      not-operating(6),
                      preempt-delay(8),
                      recovery-re-monitoring(9)
                  }
        ACCESS    read-only
        STATUS    mandatory
        DESCRIPTION
                  "Operation and state of watch of ring."
        ::= { axsAxrpGroupEntry 5 }

    axsAxrpGroupRingport1 OBJECT-TYPE
        SYNTAX    INTEGER
        ACCESS    read-only
        STATUS    mandatory
        DESCRIPTION
                  "IfIndex of ring port 1 (port in one where Ifindex is small)"
        ::= { axsAxrpGroupEntry 6 }

    axsAxrpGroupRingport1Shared OBJECT-TYPE
        SYNTAX    INTEGER {
                      no-config(1),
                      shared-edge(2),
                      shared(3)
                  }
        ACCESS    read-only
        STATUS    mandatory
        DESCRIPTION
                  "Ring port 1 is common port information."
        ::= { axsAxrpGroupEntry 7 }

    axsAxrpGroupRingport2 OBJECT-TYPE
        SYNTAX    INTEGER
        ACCESS    read-only
        STATUS    mandatory
        DESCRIPTION
                  "IfIndex of ring port 2 (port in one where Ifindex is large)"
        ::= { axsAxrpGroupEntry 8 }

    axsAxrpGroupRingport2Shared OBJECT-TYPE
        SYNTAX    INTEGER {
                      no-config(1),
                      shared-edge(2),
                      shared(3)
                  }
        ACCESS    read-only
        STATUS    mandatory
        DESCRIPTION
                  "Ring port 2 is common port information."
        ::= { axsAxrpGroupEntry 9 }

    axsAxrpGroupTransitionToFaultCounts OBJECT-TYPE
        SYNTAX    Counter
        ACCESS    read-only
        STATUS    mandatory
        DESCRIPTION
                  "Frequency that shifts from state of trouble watch in state of restoration watch."
        ::= { axsAxrpGroupEntry 10 }

    axsAxrpGroupTransitionToNormalCounts OBJECT-TYPE
        SYNTAX    Counter
        ACCESS    read-only
        STATUS    mandatory
        DESCRIPTION
                  "Frequency that shifts from state of restoration watch in state of trouble watch."
        ::= { axsAxrpGroupEntry 11 }

    axsAxrpGroupLastTransitionTime OBJECT-TYPE
        SYNTAX    TimeStamp
        ACCESS    read-only
        STATUS    mandatory
        DESCRIPTION
                  "It is changing the final time to restoration from the trouble or the trouble from restoration."
        ::= { axsAxrpGroupEntry 12 }

    axsAxrpVlanGroupTable OBJECT-TYPE
        SYNTAX    SEQUENCE OF AxsAxrpVlanGroupEntry
        ACCESS    not-accessible
        STATUS    mandatory
        DESCRIPTION
                  "The table containing AXRP VLAN group information."
        ::= { axsAxrp  2 }

    axsAxrpVlanGroupEntry OBJECT-TYPE
        SYNTAX    AxsAxrpVlanGroupEntry
        ACCESS    not-accessible
        STATUS    mandatory
        DESCRIPTION
                  "The list of AXRP VLAN group information."
        INDEX     { axsAxrpVlanGroupRingId,
                    axsAxrpVlanGroupId }
        ::= { axsAxrpVlanGroupTable 1 }

    AxsAxrpVlanGroupEntry ::= SEQUENCE {
        axsAxrpVlanGroupRingId                INTEGER,
        axsAxrpVlanGroupId                    INTEGER,
        axsAxrpVlanGroupRingport1             INTEGER,
        axsAxrpVlanGroupRingport1Role         INTEGER,
        axsAxrpVlanGroupRingport1OperState    INTEGER,
        axsAxrpVlanGroupRingport2             INTEGER,
        axsAxrpVlanGroupRingport2Role         INTEGER,
        axsAxrpVlanGroupRingport2OperState    INTEGER
    }

    axsAxrpVlanGroupRingId OBJECT-TYPE
        SYNTAX    INTEGER
        ACCESS    not-accessible
        STATUS    mandatory
        DESCRIPTION
                  "AXRP VLAN ring group number(1~8)"
        ::= { axsAxrpVlanGroupEntry  1 }

    axsAxrpVlanGroupId OBJECT-TYPE
        SYNTAX    INTEGER
        ACCESS    not-accessible
        STATUS    mandatory
        DESCRIPTION
                  "AXRP VLAN group number(1~8)"
        ::= { axsAxrpVlanGroupEntry  2 }

    axsAxrpVlanGroupRingport1 OBJECT-TYPE
        SYNTAX    INTEGER
        ACCESS    read-only
        STATUS    mandatory
        DESCRIPTION
                  "IfIndex of ring port 1 (port in one where Ifindex is small)"
        ::= { axsAxrpVlanGroupEntry 3 }

    axsAxrpVlanGroupRingport1Role OBJECT-TYPE
        SYNTAX    INTEGER {
                      primary(1),
                      secondary(2),
                      other(3)
                  }
        ACCESS    read-only
        STATUS    mandatory
        DESCRIPTION
                  "Role of ring port 1"
        ::= { axsAxrpVlanGroupEntry 4 }

    axsAxrpVlanGroupRingport1OperState OBJECT-TYPE
        SYNTAX    INTEGER {
                      forwarding(1),
                      blocking(2),
                      other(3),
                      down(4)
                  }
        ACCESS    read-only
        STATUS    mandatory
        DESCRIPTION
                  "Present of ring port 1"
        ::= { axsAxrpVlanGroupEntry 5 }

    axsAxrpVlanGroupRingport2 OBJECT-TYPE
        SYNTAX    INTEGER
        ACCESS    read-only
        STATUS    mandatory
        DESCRIPTION
                  "IfIndex of ring port 2 (port in one where Ifindex is small)"
        ::= { axsAxrpVlanGroupEntry 6 }

    axsAxrpVlanGroupRingport2Role OBJECT-TYPE
        SYNTAX    INTEGER {
                      primary(1),
                      secondary(2),
                      other(3)
                  }
        ACCESS    read-only
        STATUS    mandatory
        DESCRIPTION
                  "Role of ring port 2"
        ::= { axsAxrpVlanGroupEntry 7 }

    axsAxrpVlanGroupRingport2OperState OBJECT-TYPE
        SYNTAX    INTEGER {
                      forwarding(1),
                      blocking(2),
                      other(3),
                      down(4)
                  }
        ACCESS    read-only
        STATUS    mandatory
        DESCRIPTION
                  "Present of ring port 2"
        ::= { axsAxrpVlanGroupEntry 8 }

-- axsBootManagement group

    axsBootReason OBJECT-TYPE
        SYNTAX    INTEGER {
                      power-on(1),
                      reload(2),
                      system-fault(3),
                      system-stall(4),
                      reset(5),
                      fail-over(6),
                      default-restart(7),
                      auto-restart(8)
                  }
        ACCESS    read-only
        STATUS    mandatory
        DESCRIPTION
                  "Reason of system start."
        ::= { axsBootManagement 1 }

-- axslldp group
-- axslldpConfiguration group

    axslldpMessageTxInterval OBJECT-TYPE
        SYNTAX    INTEGER
        ACCESS    read-only
        STATUS    mandatory
        DESCRIPTION
                  "LDPDU transmitting interval"
        ::= { axslldpConfiguration 1 }

    axslldpMessageTxHoldMultiplier OBJECT-TYPE
        SYNTAX    INTEGER
        ACCESS    read-only
        STATUS    mandatory
        DESCRIPTION
                  "Time coefficient for contiguity equipment to hold about the LLDP frame which this equipment transmitted"
        ::= { axslldpConfiguration 2 }

    axslldpPortConfigTable OBJECT-TYPE
        SYNTAX    SEQUENCE OF AxslldpPortConfigEntry
        ACCESS    not-accessible
        STATUS    mandatory
        DESCRIPTION
                  "The table about LDPDU transmission"
        ::= { axslldpConfiguration 6 }

    axslldpPortConfigEntry OBJECT-TYPE
        SYNTAX    AxslldpPortConfigEntry
        ACCESS    not-accessible
        STATUS    mandatory
        DESCRIPTION
                  "The entry about LDPDU transmission"
        INDEX     { axslldpPortConfigPortNum }
        ::= { axslldpPortConfigTable 1 }

    AxslldpPortConfigEntry ::= SEQUENCE {
        axslldpPortConfigPortNum         INTEGER,
        axslldpPortConfigAdminStatus     INTEGER,
        axslldpPortConfigTLVsTxEnable    BITS,
        axslldpPortConfigRowStatus       RowStatus
    }

    axslldpPortConfigPortNum OBJECT-TYPE
        SYNTAX    INTEGER
        ACCESS    not-accessible
        STATUS    mandatory
        DESCRIPTION
                  "Port discernment index"
        ::= {axslldpPortConfigEntry 2 }

    axslldpPortConfigAdminStatus OBJECT-TYPE
        SYNTAX    INTEGER {
                      txOnly(1),
                      rxOnly(2),
                      txAndRx(3),
                      disabled(4)
                  }
        ACCESS    read-only
        STATUS    mandatory
        DESCRIPTION
                  "The port state of this equipment about transmission and reception of LDPDU"
        ::= {axslldpPortConfigEntry 3 }

    axslldpPortConfigTLVsTxEnable OBJECT-TYPE
        SYNTAX    BITS {
                      portDesc(4),
                      sysName(5),
                      sysDesc(6),
                      sysCap(7)
                  }
        ACCESS    read-only
        STATUS    mandatory
        DESCRIPTION
                  "The TLV state about the port concerned which can be transmitted"
        ::= {axslldpPortConfigEntry 4 }

    axslldpPortConfigRowStatus OBJECT-TYPE
        SYNTAX    RowStatus
        ACCESS    read-only
        STATUS    mandatory
        DESCRIPTION
                  "The state of this entry"
        ::= {axslldpPortConfigEntry 5 }

-- axslldpStats group

    axslldpStatsTable OBJECT-TYPE
        SYNTAX    SEQUENCE OF AxslldpStatsEntry
        ACCESS    not-accessible
        STATUS    mandatory
        DESCRIPTION
                  "The table about LLDP statistics information"
        ::= { axslldpStats 1 }

    axslldpStatsEntry OBJECT-TYPE
        SYNTAX    AxslldpStatsEntry
        ACCESS    not-accessible
        STATUS    mandatory
        DESCRIPTION
                  "The Entry about LLDP statistics information"
        INDEX     { axslldpStatsPortNum }
        ::= { axslldpStatsTable 1 }

    AxslldpStatsEntry ::= SEQUENCE {
        axslldpStatsPortNum               INTEGER,
        axslldpStatsOperStatus            INTEGER,
        axslldpStatsFramesInErrors        Counter,
        axslldpStatsFramesInTotal         Counter,
        axslldpStatsFramesOutTotal        Counter,
        axslldpStatsTLVsInErrors          Counter,
        axslldpStatsTLVsDiscardedTotal    Counter
    }

    axslldpStatsPortNum OBJECT-TYPE
        SYNTAX    INTEGER
        ACCESS    not-accessible
        STATUS    mandatory
        DESCRIPTION
                  "Port discernment index"
        ::= {axslldpStatsEntry 2 }

    axslldpStatsOperStatus OBJECT-TYPE
        SYNTAX    INTEGER
        ACCESS    read-only
        STATUS    mandatory
        DESCRIPTION
                  "The employment state about the port concerned"
        ::= {axslldpStatsEntry 3 }

    axslldpStatsFramesInErrors OBJECT-TYPE
        SYNTAX    Counter
        ACCESS    read-only
        STATUS    mandatory
        DESCRIPTION
                  "The number of inaccurate LDPDU reception about the port concerned"
        ::= {axslldpStatsEntry 4 }

    axslldpStatsFramesInTotal OBJECT-TYPE
        SYNTAX    Counter
        ACCESS    read-only
        STATUS    mandatory
        DESCRIPTION
                  "The total number of LDPDU reception about the port concerned"
        ::= {axslldpStatsEntry 5 }

    axslldpStatsFramesOutTotal OBJECT-TYPE
        SYNTAX    Counter
        ACCESS    read-only
        STATUS    mandatory
        DESCRIPTION
                  "The total number of LDPDU transmission about the port concerned"
        ::= {axslldpStatsEntry 6 }

    axslldpStatsTLVsInErrors OBJECT-TYPE
        SYNTAX    Counter
        ACCESS    read-only
        STATUS    mandatory
        DESCRIPTION
                  "The number of inaccurate TLV reception about the port concerned"
        ::= {axslldpStatsEntry 7 }

    axslldpStatsTLVsDiscardedTotal OBJECT-TYPE
        SYNTAX    Counter
        ACCESS    read-only
        STATUS    mandatory
        DESCRIPTION
                  "The total abandonment TLV number about the port concerned"
        ::= {axslldpStatsEntry 8 }

-- axslldpLocalSystemData group

    axslldpLocChassisType OBJECT-TYPE
        SYNTAX    INTEGER {
                      entPhysicalAlias(1),
                      ifAlias(2),
                      portEntPhysicalAlias(3),
                      backplaneEntPhysicalAlias(4),
                      macAddress(5),
                      networkAddress(6)
                  }
        ACCESS    read-only
        STATUS    mandatory
        DESCRIPTION
                  "The chassis type about this equipment"
        ::= {axslldpLocalSystemData 1 }

    axslldpLocChassisId OBJECT-TYPE
        SYNTAX    OCTET STRING 
        ACCESS    read-only
        STATUS    mandatory
        DESCRIPTION
                  "The chassis ID about this equipment"
        ::= {axslldpLocalSystemData 2 }

    axslldpLocSysName OBJECT-TYPE
        SYNTAX    OCTET STRING
        ACCESS    read-only
        STATUS    mandatory
        DESCRIPTION
                  "The chassis ID about this equipment"
        ::= {axslldpLocalSystemData 3 }

    axslldpLocSysDesc OBJECT-TYPE
        SYNTAX    DisplayString
        ACCESS    read-only
        STATUS    mandatory
        DESCRIPTION
                  "System information about this equipment"
        ::= {axslldpLocalSystemData 4 }

    axslldpLocPortTable OBJECT-TYPE
        SYNTAX    SEQUENCE OF AxslldpLocPortEntry
        ACCESS    not-accessible
        STATUS    mandatory
        DESCRIPTION
                  "The table about the port of this equipment"
        ::= { axslldpLocalSystemData 7 }

    axslldpLocPortEntry OBJECT-TYPE
        SYNTAX    AxslldpLocPortEntry
        ACCESS    not-accessible
        STATUS    mandatory
        DESCRIPTION
                  "The entry about the port of this equipment"
        INDEX     { axslldpLocPortNum }
        ::= { axslldpLocPortTable 1 }

    AxslldpLocPortEntry ::= SEQUENCE {
        axslldpLocPortNum     INTEGER,
        axslldpLocPortType    INTEGER,
        axslldpLocPortId      OCTET STRING,
        axslldpLocPortDesc    OCTET STRING
    }

    axslldpLocPortNum OBJECT-TYPE
        SYNTAX    INTEGER
        ACCESS    not-accessible
        STATUS    mandatory
        DESCRIPTION
                  "Port discernment index"
        ::= {axslldpLocPortEntry 1 }

    axslldpLocPortType OBJECT-TYPE
        SYNTAX    INTEGER {
                      ifAlias(1),
                      portEntPhysicalAlias(2),
                      backplaneEntPhysicalAlias(3),
                      macAddress(4),
                      networkAddress(5),
                      local(6)
                  }
        ACCESS    read-only
        STATUS    mandatory
        DESCRIPTION
                  "The port type about the port concerned of this equipment"
        ::= {axslldpLocPortEntry 2 }

    axslldpLocPortId OBJECT-TYPE
        SYNTAX    OCTET STRING
        ACCESS    read-only
        STATUS    mandatory
        DESCRIPTION
                  "The port ID about the port concerned of this equipment"
        ::= {axslldpLocPortEntry 3 }

    axslldpLocPortDesc OBJECT-TYPE
        SYNTAX    OCTET STRING
        ACCESS    read-only
        STATUS    mandatory
        DESCRIPTION
                  "Port information about the port concerned of this equipment"
        ::= {axslldpLocPortEntry 4 }

-- axslldpRemoteSystemData group

    axslldpRemTable OBJECT-TYPE
        SYNTAX    SEQUENCE OF AxslldpRemEntry
        ACCESS    not-accessible
        STATUS    mandatory
        DESCRIPTION
                  "The table about contiguity equipment"
        ::= { axslldpRemoteSystemData 1 }

    axslldpRemEntry OBJECT-TYPE
        SYNTAX    AxslldpRemEntry
        ACCESS    not-accessible
        STATUS    mandatory
        DESCRIPTION
                  "The entry about contiguity equipment"
        INDEX     { axslldpRemLocalPortNum,
                    axslldpRemIndex }
        ::= { axslldpRemTable 1 }

    AxslldpRemEntry ::= SEQUENCE {
        axslldpRemLocalPortNum         INTEGER,
        axslldpRemIndex                INTEGER,
        axslldpRemRemoteChassisType    INTEGER,
        axslldpRemRemoteChassis        OCTET STRING,
        axslldpRemRemotePortType       INTEGER,
        axslldpRemRemotePort           OCTET STRING,
        axslldpRemPortDesc             OCTET STRING,
        axslldpRemSysName              OCTET STRING,
        axslldpRemSysDesc              OCTET STRING
    }

    axslldpRemLocalPortNum OBJECT-TYPE
        SYNTAX    INTEGER
        ACCESS    not-accessible
        STATUS    mandatory
        DESCRIPTION
                  "The discernment index of the port of this equipment which received the information about contiguity equipment"
        ::= {axslldpRemEntry 2 }

    axslldpRemIndex OBJECT-TYPE
        SYNTAX    INTEGER
        ACCESS    not-accessible
        STATUS    mandatory
        DESCRIPTION
                  "The index about contiguity equipment"
        ::= {axslldpRemEntry 3 }

    axslldpRemRemoteChassisType OBJECT-TYPE
        SYNTAX    INTEGER {
                      entPhysicalAlias(1),
                      ifAlias(2),
                      portEntPhysicalAlias(3),
                      backplaneEntPhysicalAlias(4),
                      macAddress(5),
                      networkAddress(6)
                  }
        ACCESS    read-only
        STATUS    mandatory
        DESCRIPTION
                  "The chassis type about contiguity equipment"
        ::= {axslldpRemEntry 4 }

    axslldpRemRemoteChassis OBJECT-TYPE
        SYNTAX    OCTET STRING
        ACCESS    read-only
        STATUS    mandatory
        DESCRIPTION
                  "The chassis ID about contiguity equipment"
        ::= {axslldpRemEntry 5 }

    axslldpRemRemotePortType OBJECT-TYPE
        SYNTAX    INTEGER {
                      ifAlias(1),
                      portEntPhysicalAlias(2),
                      backplaneEntPhysicalAlias(3),
                      macAddress(4),
                      networkAddress(5),
                      local(6)
                  }
        ACCESS    read-only
        STATUS    mandatory
        DESCRIPTION
                  "The port type about the port concerned of contiguity equipment"
        ::= {axslldpRemEntry 6 }

    axslldpRemRemotePort OBJECT-TYPE
        SYNTAX    OCTET STRING
        ACCESS    read-only
        STATUS    mandatory
        DESCRIPTION
                  "The port ID about the port concerned of contiguity equipment"
        ::= {axslldpRemEntry 7 }

    axslldpRemPortDesc OBJECT-TYPE
        SYNTAX    OCTET STRING
        ACCESS    read-only
        STATUS    mandatory
        DESCRIPTION
                  "Information about the port concerned of contiguity equipment"
        ::= {axslldpRemEntry 8 }

    axslldpRemSysName OBJECT-TYPE
        SYNTAX    OCTET STRING
        ACCESS    read-only
        STATUS    mandatory
        DESCRIPTION
                  "The system name about contiguity equipment"
        ::= {axslldpRemEntry 9 }

    axslldpRemSysDesc OBJECT-TYPE
        SYNTAX    OCTET STRING
        ACCESS    read-only
        STATUS    mandatory
        DESCRIPTION
                  "System information about contiguity equipment"
        ::= {axslldpRemEntry 10 }

    axslldpRemOriginInfoTable OBJECT-TYPE
        SYNTAX    SEQUENCE OF AxslldpRemOriginInfoEntry
        ACCESS    not-accessible
        STATUS    mandatory
        DESCRIPTION
                  "The table about original with AlaxalA networks TLV of contiguity equipment"
        ::= { axslldpRemoteOriginInfoData 1 }

    axslldpRemOriginInfoEntry OBJECT-TYPE
        SYNTAX    AxslldpRemOriginInfoEntry
        ACCESS    not-accessible
        STATUS    mandatory
        DESCRIPTION
                  "The entry about original with AlaxalA networks TLV of contiguity equipment"
        INDEX     { axslldpRemOriginInfoPortNum,
                    axslldpRemOriginInfoIndex }
        ::= { axslldpRemOriginInfoTable 1 }

    AxslldpRemOriginInfoEntry ::= SEQUENCE {
        axslldpRemOriginInfoPortNum           INTEGER,
        axslldpRemOriginInfoIndex             INTEGER,
        axslldpRemOriginInfoLowerVlanList     OCTET STRING,
        axslldpRemOriginInfoHigherVlanList    OCTET STRING,
        axslldpRemOriginInfoIPv4Address       OCTET STRING,
        axslldpRemOriginInfoIPv4PortType      INTEGER,
        axslldpRemOriginInfoIPv4VlanId        INTEGER,
        axslldpRemOriginInfoIPv6Address       OCTET STRING,
        axslldpRemOriginInfoIPv6PortType      INTEGER,
        axslldpRemOriginInfoIPv6VlanId        INTEGER
    }

    axslldpRemOriginInfoPortNum OBJECT-TYPE
        SYNTAX    INTEGER
        ACCESS    not-accessible
        STATUS    mandatory
        DESCRIPTION
                  "The discernment index of the port of this equipment which received the information about contiguity equipment."
        ::= {axslldpRemOriginInfoEntry 1 }

    axslldpRemOriginInfoIndex OBJECT-TYPE
        SYNTAX    INTEGER
        ACCESS    not-accessible
        STATUS    mandatory
        DESCRIPTION
                  "The index about contiguity equipment"
        ::= {axslldpRemOriginInfoEntry 2 }

    axslldpRemOriginInfoLowerVlanList OBJECT-TYPE
        SYNTAX    OCTET STRING
        ACCESS    read-only
        STATUS    mandatory
        DESCRIPTION
                  "What expressed effective VLAN ID by the bit map by VLAN 1-2047 in the port concerned of contiguity equipment"
        ::= {axslldpRemOriginInfoEntry 3 }

    axslldpRemOriginInfoHigherVlanList OBJECT-TYPE
        SYNTAX    OCTET STRING
        ACCESS    read-only
        STATUS    mandatory
        DESCRIPTION
                  "What expressed effective VLAN ID by the bit map by VLAN 2048-4095 in the port concerned of contiguity equipment"
        ::= {axslldpRemOriginInfoEntry 4 }

    axslldpRemOriginInfoIPv4Address OBJECT-TYPE
        SYNTAX    OCTET STRING
        ACCESS    read-only
        STATUS    mandatory
        DESCRIPTION
                  "IPv4 address given to the port concerned of contiguity equipment"
        ::= {axslldpRemOriginInfoEntry 5 }

    axslldpRemOriginInfoIPv4PortType OBJECT-TYPE
        SYNTAX    INTEGER
        ACCESS    read-only
        STATUS    mandatory
        DESCRIPTION
                  "Port classification of the port of contiguity equipment concerned"
        ::= {axslldpRemOriginInfoEntry 6 }

    axslldpRemOriginInfoIPv4VlanId OBJECT-TYPE
        SYNTAX    INTEGER
        ACCESS    read-only
        STATUS    mandatory
        DESCRIPTION
                  "The smallest thing among VLAN ID to which IPv4 address is given"
        ::= {axslldpRemOriginInfoEntry 7 }

    axslldpRemOriginInfoIPv6Address OBJECT-TYPE
        SYNTAX    OCTET STRING
        ACCESS    read-only
        STATUS    mandatory
        DESCRIPTION
                  "The IPv6 address given to the port concerned of contiguity equipment"
        ::= {axslldpRemOriginInfoEntry 8 }

    axslldpRemOriginInfoIPv6PortType OBJECT-TYPE
        SYNTAX    INTEGER
        ACCESS    read-only
        STATUS    mandatory
        DESCRIPTION
                  "Port classification of the port of contiguity equipment concerned"
        ::= {axslldpRemOriginInfoEntry 9 }

    axslldpRemOriginInfoIPv6VlanId OBJECT-TYPE
        SYNTAX    INTEGER
        ACCESS    read-only
        STATUS    mandatory
        DESCRIPTION
                  "The smallest thing among VLAN ID to which the IPv6 address is given"
        ::= {axslldpRemOriginInfoEntry 10 }

-- axsPconMIB group
-- axsPconModuleData group
    axsPconModuleTable OBJECT-TYPE
        SYNTAX    SEQUENCE OF AxsPconModuleEntry
        ACCESS    not-accessible
        STATUS    mandatory
        DESCRIPTION
                  "A table containing electric power control information of module."
        ::= { axsPconModuleData 1 }

    axsPconModuleEntry OBJECT-TYPE
        SYNTAX    AxsPconModuleEntry
        ACCESS    not-accessible
        STATUS    mandatory
        DESCRIPTION
                  "An entry containing electric power control information of module."
        INDEX  { axsPconModuleIndex }
        ::= { axsPconModuleTable 1 }
        
    AxsPconModuleEntry ::= SEQUENCE {
        axsPconModuleIndex          Integer32,
        axsPconModuleType           INTEGER,
        axsPconModuleSlotNo         Integer32,
        axsPconModuleDescr          DisplayString,
        axsPconModuleStatus         INTEGER,
        axsPconModuleMode           INTEGER
    }

    axsPconModuleIndex OBJECT-TYPE
        SYNTAX    Integer32 (1..2147483647)
        ACCESS    not-accessible
        STATUS    mandatory
        DESCRIPTION
                  "A unique value for each module contained by the network device."
        ::= { axsPconModuleEntry 1 }

    axsPconModuleType OBJECT-TYPE
        SYNTAX    INTEGER {
                      all(1),
                      chassis(2),
                      bcu(3),
                      csu(4),
                      msu(5),
                      bsu(6),
                      nif(7)
                  }
        ACCESS    read-only
        STATUS    mandatory
        DESCRIPTION
                  "An indication of the type of module."
        ::= { axsPconModuleEntry 2 }
        
    axsPconModuleSlotNo OBJECT-TYPE
        SYNTAX    Integer32
        ACCESS    read-only
        STATUS    mandatory
        DESCRIPTION
                  "Position information of the module slots."
        ::= { axsPconModuleEntry 3 }
        
    axsPconModuleDescr OBJECT-TYPE
        SYNTAX    DisplayString
        ACCESS    read-only
        STATUS    mandatory
        DESCRIPTION
                  "The textual description of module."
        ::= { axsPconModuleEntry 4 }
        
    axsPconModuleStatus OBJECT-TYPE
        SYNTAX    INTEGER {
                      unsupported(-1),
                      disconnected(0),
                      active(1),
                      standby(2),
                      down(3)
                  }
        ACCESS    read-only
        STATUS    mandatory
        DESCRIPTION
                  "The module status of this axsPconModuleEntry."
        ::= { axsPconModuleEntry 5 }
        
    axsPconModuleMode OBJECT-TYPE
        SYNTAX    INTEGER {
                      unsupported(-1),
                      other(0),
                      normal(1),
                      saving-mode1(2),
                      saving-mode2(3),
                      saving(4),
                      changing(5)
                  }
        ACCESS    read-only
        STATUS    mandatory
        DESCRIPTION
                  "The module mode of this axsPconModuleEntry."
        ::= { axsPconModuleEntry 6 }
        
-- axsPconPowerCon group

    axsPconPowerConTable OBJECT-TYPE
        SYNTAX    SEQUENCE OF AxsPconPowerConEntry
        ACCESS    not-accessible
        STATUS    mandatory
        DESCRIPTION
                  "The power consumption information table."
        ::= { axsPconPowerCon 1 }
        
    axsPconPowerConEntry OBJECT-TYPE
        SYNTAX    AxsPconPowerConEntry
        ACCESS    not-accessible
        STATUS    mandatory
        DESCRIPTION
                  "The power consumption information entry."
        INDEX  { axsPconModuleIndex }
        ::= { axsPconPowerConTable 1 }

    AxsPconPowerConEntry ::= SEQUENCE {
        axsPconPowerConMaxPower          Gauge,
        axsPconPowerConPowerConsumption  Counter64,
        axsPconPowerConPowerMeter        Gauge
    }
        
    axsPconPowerConMaxPower OBJECT-TYPE
        SYNTAX    Gauge
        ACCESS    read-only
        STATUS    mandatory
        DESCRIPTION
                  "The maximum electric power of module."
        ::= { axsPconPowerConEntry 1 }
        
    axsPconPowerConPowerConsumption OBJECT-TYPE
        SYNTAX    Counter64
        ACCESS    read-only
        STATUS    mandatory
        DESCRIPTION
                  "The power consumption of module."
        ::= { axsPconPowerConEntry 2 }
        
    axsPconPowerConPowerMeter OBJECT-TYPE
        SYNTAX    Gauge
        ACCESS    read-only
        STATUS    mandatory
        DESCRIPTION
                  "The power meter of module."
        ::= { axsPconPowerConEntry 3 }

-- axsPconTraffic group

    axsPconTrafficTable OBJECT-TYPE
        SYNTAX    SEQUENCE OF AxsPconTrafficEntry
        ACCESS    not-accessible
        STATUS    mandatory
        DESCRIPTION
                  "The table containing traffic information."
        ::= { axsPconTraffic 1 }
        
    axsPconTrafficEntry OBJECT-TYPE
        SYNTAX    AxsPconTrafficEntry
        ACCESS    not-accessible
        STATUS    mandatory
        DESCRIPTION
                  "The entry containing traffic information for each module."
        INDEX  { axsPconModuleIndex }
        ::= { axsPconTrafficTable 1 }
        
    AxsPconTrafficEntry ::= SEQUENCE {
        axsPconTrafficMaxTransferCapacity     Gauge,
        axsPconTrafficTotalTransferCapacity   Gauge,
        axsPconTrafficInOctets                Counter64,
        axsPconTrafficOutOctets               Counter64,
        axsPconTrafficInPkts                  Counter64,
        axsPconTrafficOutPkts                 Counter64,
        axsPconTrafficCapacityOctets          Counter64,
        axsPconTrafficInPeakOctetsRate        Gauge,
        axsPconTrafficPeakTransferCapacity    Gauge,
        axsPconTrafficInDiscPkts              Counter64,
        axsPconTrafficOutDiscPkts             Counter64
    }

    axsPconTrafficMaxTransferCapacity OBJECT-TYPE
        SYNTAX    Gauge
        ACCESS    read-only
        STATUS    mandatory
        DESCRIPTION
                  "The maximum transfer capacity on the module."
        ::= { axsPconTrafficEntry 1 }
        
    axsPconTrafficTotalTransferCapacity OBJECT-TYPE
        SYNTAX    Gauge
        ACCESS    read-only
        STATUS    mandatory
        DESCRIPTION
                  "The total transfer capacity which depends on power control mode."
        ::= { axsPconTrafficEntry 2 }
        
    axsPconTrafficInOctets OBJECT-TYPE
        SYNTAX    Counter64
        ACCESS    read-only
        STATUS    mandatory
        DESCRIPTION
                  "The total number of octets received on the module."
        ::= { axsPconTrafficEntry 3 }
        
    axsPconTrafficOutOctets OBJECT-TYPE
        SYNTAX    Counter64
        ACCESS    read-only
        STATUS    mandatory
        DESCRIPTION
                  "The total number of octets transmitted out of the module."
        ::= { axsPconTrafficEntry 4 }
        
    axsPconTrafficInPkts OBJECT-TYPE
        SYNTAX    Counter64
        ACCESS    read-only
        STATUS    mandatory
        DESCRIPTION
                  "The total number of packets received on the module."
        ::= { axsPconTrafficEntry 5 }
        
    axsPconTrafficOutPkts OBJECT-TYPE
        SYNTAX    Counter64
        ACCESS    read-only
        STATUS    mandatory
        DESCRIPTION
                  "The total number of packets transmitted out of the module."
        ::= { axsPconTrafficEntry 6 }
        
    axsPconTrafficCapacityOctets OBJECT-TYPE
        SYNTAX    Counter64
        ACCESS    read-only
        STATUS    mandatory
        DESCRIPTION
                  "The maximum number of octets can be received on the module."
        ::= { axsPconTrafficEntry 7 }
        
    axsPconTrafficInPeakOctetsRate OBJECT-TYPE
        SYNTAX    Gauge
        ACCESS    read-only
        STATUS    mandatory
        DESCRIPTION
                  "The traffic rate when incoming traffic rate is peak."
        ::= { axsPconTrafficEntry 8 }
        
    axsPconTrafficPeakTransferCapacity OBJECT-TYPE
        SYNTAX    Gauge
        ACCESS    read-only
        STATUS    mandatory
        DESCRIPTION
                  "The total transfer capacity when incoming traffic rate is peak."
        ::= { axsPconTrafficEntry 9 }
        
    axsPconTrafficInDiscPkts OBJECT-TYPE
        SYNTAX    Counter64
        ACCESS    read-only
        STATUS    mandatory
        DESCRIPTION
                  "The total number of inbound packets which were chosen to be discarded."
        ::= { axsPconTrafficEntry 10 }
        
    axsPconTrafficOutDiscPkts OBJECT-TYPE
        SYNTAX    Counter64
        ACCESS    read-only
        STATUS    mandatory
        DESCRIPTION
                  "The total number of outbound packets which were chosen to be discarded."
        ::= { axsPconTrafficEntry 11 }

-- ax6300sSwitch group

    ax6300sModelType OBJECT-TYPE
        SYNTAX    INTEGER {
                      other(1),
                      model-AX6304S(600),
                      model-AX6308S(601)
                  }
        ACCESS    read-only
        STATUS    mandatory
        DESCRIPTION
                  "Model type of this system."
        ::= { ax6300sSwitch 1 }

--    ax6300sSoftware OBJECT-TYPE
--        SYNTAX    INTEGER
--        ACCESS    not-accessible
--        STATUS    mandatory
--        DESCRIPTION
--                  "Software information of this system."
--        ::= { ax6300sSwitch 2 }

    ax6300sSoftwareName OBJECT-TYPE
        SYNTAX    DisplayString (SIZE (0..16))
        ACCESS    read-only
        STATUS    mandatory
        DESCRIPTION
                  "Software name of this system."
        ::= { ax6300sSoftware 1 }

    ax6300sSoftwareAbbreviation OBJECT-TYPE
        SYNTAX    DisplayString (SIZE (0..16))
        ACCESS    read-only
        STATUS    mandatory
        DESCRIPTION
                  "System software abbreviation."
        ::= { ax6300sSoftware 2 }

    ax6300sSoftwareVersion OBJECT-TYPE
        SYNTAX    DisplayString (SIZE (0..16))
        ACCESS    read-only
        STATUS    mandatory
        DESCRIPTION
                  "System software version."
        ::= { ax6300sSoftware 3 }

    ax6300sSystemMsgText OBJECT-TYPE
        SYNTAX    DisplayString (SIZE (0..256))
        ACCESS    read-only
        STATUS    mandatory
        DESCRIPTION
                  "The text of the system log message.For information about this code,
                  see:  Operator's Manual."
        ::= { ax6300sSystemMsg 1 }

    ax6300sSystemMsgType OBJECT-TYPE
        SYNTAX    OCTET STRING (SIZE (1))
        ACCESS    read-only
        STATUS    mandatory
        DESCRIPTION
                  "The event type. For information about this code, see:  Operator's Manual."
        ::= { ax6300sSystemMsg 2 }

    ax6300sSystemMsgTimeStamp OBJECT-TYPE
        SYNTAX    DisplayString (SIZE (0..14))
        ACCESS    read-only
        STATUS    mandatory
        DESCRIPTION
                  "The time that event occured. And that is expressed as type of
                  MM/DD hh:mm:ss
                      MM:month(01-12)
                      DD:day(01-31)
                      hh:hour(00-23)
                      mm:minute(00-59)
                      ss:second(00-59)
                  Insert space between DD and hh."
        ::= { ax6300sSystemMsg 3 }

    ax6300sSystemMsgLevel OBJECT-TYPE
        SYNTAX    OCTET STRING (SIZE (1))
        ACCESS    read-only
        STATUS    mandatory
        DESCRIPTION
                  "The newest system message log level.For information about this code,
                  see:  Operator's Manual."
        ::= { ax6300sSystemMsg 4 }

    ax6300sSystemMsgEventPoint OBJECT-TYPE
        SYNTAX    DisplayString (SIZE (0..8))
        ACCESS    read-only
        STATUS    mandatory
        DESCRIPTION
                  "The code of part that system message error occured. For information
                  about this code,see:  Operator's Manual."
        ::= { ax6300sSystemMsg 5 }

    ax6300sSystemMsgEventInterfaceID OBJECT-TYPE
        SYNTAX    DisplayString (SIZE (0..40))
        ACCESS    read-only
        STATUS    mandatory
        DESCRIPTION
                  "Interface identification of system messages. For information
                  about this code,see:  Operator's Manual."
        ::= { ax6300sSystemMsg 6 }

    ax6300sSystemMsgEventCode OBJECT-TYPE
        SYNTAX    OCTET STRING (SIZE (4))
        ACCESS    read-only
        STATUS    mandatory
        DESCRIPTION
                  "Event kind code of system messages. For information about this code,
                  see:  Operator's Manual."
        ::= { ax6300sSystemMsg 7 }

    ax6300sSystemMsgAdditionalCode OBJECT-TYPE
        SYNTAX    OCTET STRING (SIZE (6))
        ACCESS    read-only
        STATUS    mandatory
        DESCRIPTION
                  "Additional code of system messages. For information about this code,
                  see:  Operator's Manual."
        ::= { ax6300sSystemMsg 8 }

    ax6300sSnmpSendReceiveSize OBJECT-TYPE
        SYNTAX    INTEGER
        ACCESS    read-only
        STATUS    mandatory
        DESCRIPTION
                  "SNMP packet data size in Manager-to-Agent communication. The value is
                  displayed in bytes."
        ::= { ax6300sSnmpAgent 1 }

    ax6300sSnmpReceiveDelay OBJECT-TYPE
        SYNTAX    INTEGER
        ACCESS    read-only
        STATUS    mandatory
        DESCRIPTION
                  "A recommendable interval to receive packets from Manager.The value is
                  displayed in milliseconds."
        ::= { ax6300sSnmpAgent 2 }

    ax6300sSnmpContinuousSend OBJECT-TYPE
        SYNTAX    INTEGER
        ACCESS    read-only
        STATUS    mandatory
        DESCRIPTION
                  "Number of times that is recommendable continuous transmission
                  packets."
        ::= { ax6300sSnmpAgent 3 }

    ax6300sSnmpObjectMaxNumber OBJECT-TYPE
        SYNTAX    INTEGER
        ACCESS    read-only
        STATUS    mandatory
        DESCRIPTION
                  "Max number of objects that contain SNMP packet."
        ::= { ax6300sSnmpAgent 4 }

    ax6300sLicenseNumber OBJECT-TYPE
        SYNTAX    INTEGER
        ACCESS    read-only
        STATUS    mandatory
        DESCRIPTION
                  "The number of the configured license serial numbers."
        ::= { ax6300sLicense 1 }

    ax6300sLicenseTable OBJECT-TYPE
        SYNTAX    SEQUENCE OF Ax6300sLicenseTableEntry
        ACCESS    not-accessible
        STATUS    mandatory
        DESCRIPTION
                  "The table containing the license information."
        ::= { ax6300sLicense 2 }

    ax6300sLicenseEntry OBJECT-TYPE
        SYNTAX    Ax6300sLicenseTableEntry
        ACCESS    not-accessible
        STATUS    mandatory
        DESCRIPTION
                  "The entry of license information."
        INDEX     { ax6300sLicenseIndex }
        ::= { ax6300sLicenseTable 1 }

    Ax6300sLicenseTableEntry ::= SEQUENCE {
        ax6300sLicenseIndex           INTEGER,
        ax6300sLicenseSerialNumber    DisplayString,
        ax6300sLicenseOptionNumber    INTEGER
    }

    ax6300sLicenseIndex OBJECT-TYPE
        SYNTAX    INTEGER
        ACCESS    not-accessible
        STATUS    mandatory
        DESCRIPTION
                  "The unique index number given for each serial number. The number is from 1 to ax6300sLicenseNumber."
        ::= { ax6300sLicenseEntry 1 }

    ax6300sLicenseSerialNumber OBJECT-TYPE
        SYNTAX    DisplayString 
        ACCESS    read-only
        STATUS    mandatory
        DESCRIPTION
                  "The serial number."
        ::= { ax6300sLicenseEntry 2 }

    ax6300sLicenseOptionNumber OBJECT-TYPE
        SYNTAX    INTEGER 
        ACCESS    read-only
        STATUS    mandatory
        DESCRIPTION
                  "The number of option licenses associated with the serial number."
        ::= { ax6300sLicenseEntry 3 }

    ax6300sLicenseOptionTable OBJECT-TYPE
        SYNTAX    SEQUENCE OF Ax6300sLicenseOptionTableEntry
        ACCESS    not-accessible
        STATUS    mandatory
        DESCRIPTION
                  "The table containing option licenses information associated with the serial number."
        ::= { ax6300sLicense 3 }

    ax6300sLicenseOptionEntry OBJECT-TYPE
        SYNTAX    Ax6300sLicenseOptionTableEntry
        ACCESS    not-accessible
        STATUS    mandatory
        DESCRIPTION
                  "The entry of the option license information associated with the serial number."
        INDEX     { ax6300sLicenseOptionIndex,
                    ax6300sLicenseOptionNumberIndex }
        ::= { ax6300sLicenseOptionTable 1 }

    Ax6300sLicenseOptionTableEntry ::= SEQUENCE {
        ax6300sLicenseOptionIndex                   INTEGER,
        ax6300sLicenseOptionNumberIndex             INTEGER,
        ax6300sLicenseOptionSoftwareName            DisplayString,
        ax6300sLicenseOptionSoftwareAbbreviation    DisplayString
    }

    ax6300sLicenseOptionIndex OBJECT-TYPE
        SYNTAX    INTEGER
        ACCESS    not-accessible
        STATUS    mandatory
        DESCRIPTION
                  "The unique index number given for each serial number. The same number as ax6300sLicenseIndex."
        ::= { ax6300sLicenseOptionEntry 1 }

    ax6300sLicenseOptionNumberIndex OBJECT-TYPE
        SYNTAX    INTEGER
        ACCESS    not-accessible
        STATUS    mandatory
        DESCRIPTION
                  "The unique index number of option licenses information which is given for each serial number. The number is from 1 to ax6300sLicenseNumber."
        ::= { ax6300sLicenseOptionEntry 2 }

    ax6300sLicenseOptionSoftwareName OBJECT-TYPE
        SYNTAX    DisplayString 
        ACCESS    read-only
        STATUS    mandatory
        DESCRIPTION
                  "The software model name of the option license information associated with the serial number."
        ::= { ax6300sLicenseOptionEntry 3 }

    ax6300sLicenseOptionSoftwareAbbreviation OBJECT-TYPE
        SYNTAX    DisplayString 
        ACCESS    read-only
        STATUS    mandatory
        DESCRIPTION
                  "The software abbreviated name of the option license information associated with the serial number. "
        ::= { ax6300sLicenseOptionEntry 4 }

-- ax6300sDevice group

    ax6300sChassisMaxNumber OBJECT-TYPE
        SYNTAX    INTEGER
        ACCESS    read-only
        STATUS    mandatory
        DESCRIPTION
                  "Max number of cluster chassis that can connect to this router."
        ::= { ax6300sChassis 1 }

    ax6300sChassisTable OBJECT-TYPE
        SYNTAX    SEQUENCE OF Ax6300sChassisTableEntry
        ACCESS    not-accessible
        STATUS    mandatory
        DESCRIPTION
                  "A table containing chassis information."
        ::= { ax6300sChassis 2 }

    ax6300sChassisEntry OBJECT-TYPE
        SYNTAX    Ax6300sChassisTableEntry
        ACCESS    not-accessible
        STATUS    mandatory
        DESCRIPTION
                  "An entry containing specific chassis."
        INDEX     { ax6300sChassisIndex }
        ::= { ax6300sChassisTable 1 }

    Ax6300sChassisTableEntry ::= SEQUENCE {
        ax6300sChassisIndex          INTEGER,
        ax6300sChassisType           INTEGER,
        ax6300sChassisStatus         INTEGER,
        ax6300sPowerUnitNumber       INTEGER,
        ax6300sFanNumber             INTEGER,
        ax6300sMsuBoardDuplexMode    INTEGER,
        ax6300sMsuBoardNumber        INTEGER,
        ax6300sNifBoardNumber        INTEGER,
        ax6300sPowerControl          INTEGER
    }

    ax6300sChassisIndex OBJECT-TYPE
        SYNTAX    INTEGER
        ACCESS    not-accessible
        STATUS    mandatory
        DESCRIPTION
                  "A number to specify ax6300sChassisEntry."
        ::= { ax6300sChassisEntry 1 }

    ax6300sChassisType OBJECT-TYPE
        SYNTAX    INTEGER {
                      other(1),
                      model-AX6304S(600),
                      model-AX6308S(601)
                  }
        ACCESS    read-only
        STATUS    mandatory
        DESCRIPTION
                  "Chassis type of this system."
        ::= { ax6300sChassisEntry 2 }

    ax6300sChassisStatus OBJECT-TYPE
        SYNTAX    INTEGER {
                      up(2)
                  }
        ACCESS    read-only
        STATUS    mandatory
        DESCRIPTION
                  "Current status of this chassis."
        ::= { ax6300sChassisEntry 3 }

    ax6300sPowerUnitNumber OBJECT-TYPE
        SYNTAX    INTEGER
        ACCESS    read-only
        STATUS    mandatory
        DESCRIPTION
                  "Number of maximum power switches that this router can connect its."
        ::= { ax6300sChassisEntry 21 }

    ax6300sFanNumber OBJECT-TYPE
        SYNTAX    INTEGER
        ACCESS    read-only
        STATUS    mandatory
        DESCRIPTION
                  "The maximum number of fans that can connect to this chassis."
        ::= { ax6300sChassisEntry 23 }

    ax6300sMsuBoardDuplexMode OBJECT-TYPE
        SYNTAX    INTEGER{
                      simplex-mode(1),
                      duplex-mode(2)
                  }
        ACCESS    read-only
        STATUS    mandatory
        DESCRIPTION
                  "The MSU duplex mode."
        ::= { ax6300sChassisEntry 26 }

    ax6300sMsuBoardNumber OBJECT-TYPE
        SYNTAX    INTEGER
        ACCESS    read-only
        STATUS    mandatory
        DESCRIPTION
                  "The maximum number of MSU that can connect to this chassis."
        ::= { ax6300sChassisEntry 27 }

    ax6300sNifBoardNumber OBJECT-TYPE
        SYNTAX    INTEGER
        ACCESS    read-only
        STATUS    mandatory
        DESCRIPTION
                  "The maximum number of NIF that can connect to this chassis."
        ::= { ax6300sChassisEntry 28 }

    ax6300sPowerControl OBJECT-TYPE
        SYNTAX    INTEGER{
                      normal-mode(1),
                      power-save-mode(2)
                  }
        ACCESS    read-only
        STATUS    mandatory
        DESCRIPTION
                  "The power mode of this chassis."
        ::= { ax6300sChassisEntry 29 }

    ax6300sPowerUnitTable OBJECT-TYPE
        SYNTAX    SEQUENCE OF Ax6300sPowerUnitTableEntry
        ACCESS    not-accessible
        STATUS    mandatory
        DESCRIPTION
                  "A table containing power unit information."
        ::= { ax6300sChassis 3 }

    ax6300sPowerUnitEntry OBJECT-TYPE
        SYNTAX    Ax6300sPowerUnitTableEntry
        ACCESS    not-accessible
        STATUS    mandatory
        DESCRIPTION
                  "An entry containing power unit information."
        INDEX     { ax6300sChassisIndex,
                    ax6300sPowerUnitIndex }
        ::= { ax6300sPowerUnitTable 1 }

    Ax6300sPowerUnitTableEntry ::= SEQUENCE {
        ax6300sPowerUnitIndex        INTEGER,
        ax6300sPowerConnectStatus    INTEGER,
        ax6300sPowerSupplyStatus     INTEGER
    }

    ax6300sPowerUnitIndex OBJECT-TYPE
        SYNTAX    INTEGER
        ACCESS    not-accessible
        STATUS    mandatory
        DESCRIPTION
                  "A number to position of the power units.The value from 1
                  to ax6300sPowerUnitNumber."
        ::= { ax6300sPowerUnitEntry 1 }
            
    ax6300sPowerConnectStatus OBJECT-TYPE
        SYNTAX    INTEGER {
                    connected(2),
                    disconnected(32)
                  }
        ACCESS    read-only
        STATUS    mandatory
        DESCRIPTION
                  "The current connection status of the power unit."
        ::= { ax6300sPowerUnitEntry 2 }

    ax6300sPowerSupplyStatus OBJECT-TYPE
        SYNTAX    INTEGER {
                      ok(2),
                      fault(4),
                      disconnected(-1)
                  }
        ACCESS    read-only
        STATUS    mandatory
        DESCRIPTION
                  "Status of power supply."
        ::= { ax6300sPowerUnitEntry 3 }

    ax6300sFanTable OBJECT-TYPE
        SYNTAX    SEQUENCE OF Ax6300sFanTableEntry
        ACCESS    not-accessible
        STATUS    mandatory
        DESCRIPTION
                  "A table containing fan information."
        ::= { ax6300sChassis 4 }

    ax6300sFanEntry OBJECT-TYPE
        SYNTAX    Ax6300sFanTableEntry
        ACCESS    not-accessible
        STATUS    mandatory
        DESCRIPTION
                  "This entry containing information for a fan."
        INDEX     { ax6300sChassisIndex,
                    ax6300sFanIndex }
        ::= { ax6300sFanTable 1 }

    Ax6300sFanTableEntry ::= SEQUENCE {
        ax6300sFanIndex     INTEGER,
        ax6300sFanStatus    INTEGER
    }

    ax6300sFanIndex OBJECT-TYPE
        SYNTAX    INTEGER
        ACCESS    not-accessible
        STATUS    mandatory
        DESCRIPTION
                  "Index to indicate position of fans."
        ::= { ax6300sFanEntry 1 }

    ax6300sFanStatus OBJECT-TYPE
        SYNTAX    INTEGER {
                      ok(2),
                      high-speed(3),
                      fault(4)
                  }
        ACCESS    read-only
        STATUS    mandatory
        DESCRIPTION
                  "Status of fans."
        ::= { ax6300sFanEntry 2 }

    ax6300sMsuBoardTable OBJECT-TYPE
        SYNTAX    SEQUENCE OF Ax6300sMsuBoardEntry
        ACCESS    not-accessible
        STATUS    mandatory
        DESCRIPTION
                  "The MSU information table."
        ::= { ax6300sMsuBoard 1 }

    ax6300sMsuBoardEntry OBJECT-TYPE
        SYNTAX    Ax6300sMsuBoardEntry
        ACCESS    not-accessible
        STATUS    mandatory
        DESCRIPTION
                  "The MSU information entry."
        INDEX     { ax6300sChassisIndex,
                    ax6300sMsuBoardIndex }
        ::= {ax6300sMsuBoardTable 1 }

    Ax6300sMsuBoardEntry ::= SEQUENCE{
        ax6300sMsuBoardIndex                 INTEGER,
        ax6300sMsuOperStatus                 INTEGER,
        ax6300sMsuOperModeStatus             BITS,
        ax6300sMsuActiveLedStatus            INTEGER,
        ax6300sMsuSystem1LedStatus           INTEGER,
        ax6300sMsuSystem2LedStatus           INTEGER,
        ax6300sMsuMgmtPortStatus             INTEGER,
        ax6300sMsuBoardName                  DisplayString,
        ax6300sMsuBoardAbbreviation          DisplayString,
        ax6300sMsuCpuName                    DisplayString,
        ax6300sMsuCpuClock                   INTEGER,
        ax6300sMsuMemoryTotalSize            INTEGER,
        ax6300sMsuMemoryUsedSize             INTEGER,
        ax6300sMsuMemoryFreeSize             INTEGER,
        ax6300sMsuRomVersion                 DisplayString,
        ax6300sMsuCpuLoad1m                  INTEGER,
        ax6300sMsuFlashTotalSize             INTEGER,
        ax6300sMsuFlashUsedSize              INTEGER,
        ax6300sMsuFlashFreeSize              INTEGER,
        ax6300sMsuTemperatureStatusNumber    INTEGER,
        ax6300sMsuSerialNumber               DisplayString,
        ax6300sMsuTotalAccumRunTime          INTEGER,
        ax6300sMsuCriticalAccumRunTime       INTEGER,
        ax6300sPspOperModeStatus             INTEGER
    }

    ax6300sMsuBoardIndex OBJECT-TYPE
        SYNTAX    INTEGER 
        ACCESS    not-accessible
        STATUS    mandatory
        DESCRIPTION
                  "The index of MSU information table."
        ::= { ax6300sMsuBoardEntry 1 }

    ax6300sMsuOperStatus OBJECT-TYPE
        SYNTAX    INTEGER {
                      initialized(1),
                      active(2),
                      disabled(3),
                      down(4),
                      power-off(6)
                  }
        ACCESS    read-only
        STATUS    mandatory
        DESCRIPTION
                  "The state of MSU STATUS LED of the device."
        ::= { ax6300sMsuBoardEntry 2 }

    ax6300sMsuOperModeStatus OBJECT-TYPE
        SYNTAX    BITS {
                      disconnected(0),
                      initialized(1),
                      active(2),
                      standby(3),
                      do-not-match-with-configure-mode(4),
                      do-not-match-with-software-mode(5),
                      do-not-match-with-license-info(6),
                      down(7),
                      maintenance(8)
                  }
        ACCESS    read-only
        STATUS    mandatory
        DESCRIPTION
                  "The state of operation status of the device."
        ::= { ax6300sMsuBoardEntry 3 }

    ax6300sMsuActiveLedStatus OBJECT-TYPE
        SYNTAX    INTEGER {
                      disconnected(-1),
                      green(2),
                      extinction(6)
                  }
        ACCESS    read-only
        STATUS    mandatory
        DESCRIPTION
                  "The state of ACTIVE LED status of the device."
        ::= { ax6300sMsuBoardEntry 4 }
        
    ax6300sMsuSystem1LedStatus OBJECT-TYPE
        SYNTAX    INTEGER {
                      disconnected(-1),
                      green(2),
                      orange(3),
                      red(4),
                      extinction(6)
                  }
        ACCESS    read-only
        STATUS    mandatory
        DESCRIPTION
                  "The state of SYSTEM LED status of the device."
        ::= { ax6300sMsuBoardEntry 5 }

    ax6300sMsuSystem2LedStatus OBJECT-TYPE
        SYNTAX    INTEGER {
                      disconnected(-1),
                      green-blink(1),
                      green(2),
                      extinction(6)
                  }
        ACCESS    read-only
        STATUS    mandatory
        DESCRIPTION
                  "The state of SYSTEM2 LED status of the device."
        ::= { ax6300sMsuBoardEntry 6 }

    ax6300sMsuMgmtPortStatus OBJECT-TYPE
        SYNTAX    INTEGER {
                      disconnected(-1),
                      other(1),
                      active(2),
                      down(4),
                      disabled(6),
                      maintenance(7),
                      line-test(9),
                      unused(10)
                  }
        ACCESS    read-only
        STATUS    mandatory
        DESCRIPTION
                  "The state of management-port status of the device."
        ::= { ax6300sMsuBoardEntry 7 }
        
    ax6300sMsuBoardName OBJECT-TYPE
        SYNTAX    DisplayString
        ACCESS    read-only
        STATUS    mandatory
        DESCRIPTION
                  "The product name of MSU Board. If MSU Board disconnected, return 0 length DisplayString."
        ::= { ax6300sMsuBoardEntry 8 }

    ax6300sMsuBoardAbbreviation OBJECT-TYPE
        SYNTAX    DisplayString
        ACCESS    read-only
        STATUS    mandatory
        DESCRIPTION
                  "The abbreviated name of MSU Board. If MSU Board disconnected, return 0 length DisplayString."
        ::= { ax6300sMsuBoardEntry 9 }
        
    ax6300sMsuCpuName OBJECT-TYPE
        SYNTAX    DisplayString
        ACCESS    read-only
        STATUS    mandatory
        DESCRIPTION
                  "The name of CPU on MSU board is shown by the character string of 16 characters or less.
                  If MSU Board disconnected, return 0 length DisplayString." 
        ::= { ax6300sMsuBoardEntry 10 }

    ax6300sMsuCpuClock OBJECT-TYPE
        SYNTAX    INTEGER
        ACCESS    read-only
        STATUS    mandatory
        DESCRIPTION
                  "CPU clock is shown by the numerical value.
                  If MSU Board disconnected, return -1."
        ::= { ax6300sMsuBoardEntry 11 }

    ax6300sMsuMemoryTotalSize OBJECT-TYPE
        SYNTAX    INTEGER
        ACCESS    read-only
        STATUS    mandatory
        DESCRIPTION
                  "The installing memory size is shown by the numerical value.
                  If MSU Board disconnected, return -1."
        ::= { ax6300sMsuBoardEntry 12 }

    ax6300sMsuMemoryUsedSize OBJECT-TYPE
        SYNTAX    INTEGER
        ACCESS    read-only
        STATUS    mandatory
        DESCRIPTION
                  "The use memory size is shown by the numerical value.
                  If MSU Board disconnected, return -1."
        ::= { ax6300sMsuBoardEntry 13 }

    ax6300sMsuMemoryFreeSize OBJECT-TYPE
        SYNTAX    INTEGER
        ACCESS    read-only
        STATUS    mandatory
        DESCRIPTION
                  "The unused memory size is shown by the numerical value.
                  If MSU Board disconnected, return -1."
        ::= { ax6300sMsuBoardEntry 14 }

    ax6300sMsuRomVersion OBJECT-TYPE
        SYNTAX    DisplayString
        ACCESS    read-only
        STATUS    mandatory
        DESCRIPTION
                  "The version of ROM equipped with BCU is shown by the character string.
                  If MSU Board disconnected, return 0 length DisplayString."
        ::= { ax6300sMsuBoardEntry 15 }

    ax6300sMsuCpuLoad1m OBJECT-TYPE
        SYNTAX    INTEGER
        ACCESS    read-only
        STATUS    mandatory
        DESCRIPTION
                  "CPU utilization of one minute is shown by the numerical value.
                  If MSU Board disconnected, return -1."
        ::= { ax6300sMsuBoardEntry 16 }

    ax6300sMsuFlashTotalSize OBJECT-TYPE
        SYNTAX    INTEGER
        ACCESS    read-only
        STATUS    mandatory
        DESCRIPTION
                  "The total of filesystem use capacity and unused capacity in a built-in memory 
                  is shown."
        ::= { ax6300sMsuBoardEntry 17 }

    ax6300sMsuFlashUsedSize OBJECT-TYPE
        SYNTAX    INTEGER
        ACCESS    read-only
        STATUS    mandatory
        DESCRIPTION
                  "The use capacity of the filesystem in a built-in memory is shown."
        ::= { ax6300sMsuBoardEntry 18 }

    ax6300sMsuFlashFreeSize OBJECT-TYPE
        SYNTAX    INTEGER
        ACCESS    read-only
        STATUS    mandatory
        DESCRIPTION
                  "The unused capacity of the filesystem in a built-in memory is shown. "
        ::= { ax6300sMsuBoardEntry 19 }

    ax6300sMsuTemperatureStatusNumber OBJECT-TYPE
        SYNTAX    INTEGER
        ACCESS    read-only
        STATUS    mandatory
        DESCRIPTION
                  "The maximum number of ax6300sTemperatureStatus in this chassis."
        ::= { ax6300sMsuBoardEntry 20 }

    ax6300sMsuSerialNumber OBJECT-TYPE
        SYNTAX    DisplayString
        ACCESS    read-only
        STATUS    mandatory
        DESCRIPTION
                  "The character string of the card management information of MSU package whose number is a maximum of 16. 
                  Its length is zero if not implemented or inactivated."
        ::= { ax6300sMsuBoardEntry 21 }

    ax6300sMsuTotalAccumRunTime OBJECT-TYPE
        SYNTAX    INTEGER
        ACCESS    read-only
        STATUS    mandatory
        DESCRIPTION
                  "Total operation time after operation of device begins."
        ::= { ax6300sMsuBoardEntry 22 }

    ax6300sMsuCriticalAccumRunTime OBJECT-TYPE
        SYNTAX    INTEGER
        ACCESS    read-only
        STATUS    mandatory
        DESCRIPTION
                  "Operating time under environment of 40 degrees C or more."
        ::= { ax6300sMsuBoardEntry 23 }

    ax6300sPspOperModeStatus OBJECT-TYPE
        SYNTAX    INTEGER {
                      disconnected(-1),
                      other(1),
                      active(2),
                      standby(3),
                      down(4),
                      initialized(5)
                  }
        ACCESS    read-only
        STATUS    mandatory
        DESCRIPTION
                  "Operating time under environment of 40C or more."
        ::= { ax6300sMsuBoardEntry 24 }
            
    ax6300sTemperatureStatusTable OBJECT-TYPE
        SYNTAX    SEQUENCE OF Ax6300sTemperatureStatusEntry
        ACCESS    not-accessible
        STATUS    mandatory
        DESCRIPTION
                  "The table of ambient temperature status maintained by the
                  environmental monitor."
        ::= { ax6300sMsuBoard 2 }

    ax6300sTemperatureStatusEntry OBJECT-TYPE
        SYNTAX    Ax6300sTemperatureStatusEntry
        ACCESS    not-accessible
        STATUS    mandatory
        DESCRIPTION
                  "An entry in the ambient temperature status table, representing
                  the status of the associated testpoint maintained by the
                  environmental monitor."
        INDEX    { ax6300sChassisIndex,
                   ax6300sMsuBoardIndex,
                   ax6300sTemperatureStatusIndex }
        ::= { ax6300sTemperatureStatusTable 1 }

    Ax6300sTemperatureStatusEntry ::= SEQUENCE {
        ax6300sTemperatureStatusIndex    INTEGER,
        ax6300sTemperatureStatusDescr    DisplayString,
        ax6300sTemperatureStatusValue    Integer32,
        ax6300sTemperatureThreshold      Integer32,
        ax6300sTemperatureState          INTEGER
    }

    ax6300sTemperatureStatusIndex OBJECT-TYPE
        SYNTAX    INTEGER
        ACCESS    not-accessible
        STATUS    mandatory
        DESCRIPTION
                  "Unique index for the testpoint being instrumented.
                  This index is for SNMP purposes only, and has no
                  intrinsic meaning."
        ::= { ax6300sTemperatureStatusEntry 1 }

    ax6300sTemperatureStatusDescr OBJECT-TYPE
        SYNTAX    DisplayString(SIZE(0..32))
        ACCESS    read-only
        STATUS    mandatory
        DESCRIPTION
                  "Textual description of the testpoint being instrumented.
                  This description is a short textual label, suitable as a
                  human-sensible identification for the rest of the
                  information in the entry."
        ::= { ax6300sTemperatureStatusEntry 2 }

    ax6300sTemperatureStatusValue OBJECT-TYPE
        SYNTAX    Integer32
        ACCESS    read-only
        STATUS    mandatory
        DESCRIPTION
                  "The current measurement of the testpoint being instrumented."
        ::= { ax6300sTemperatureStatusEntry 3 }

    ax6300sTemperatureThreshold OBJECT-TYPE
        SYNTAX    Integer32
        ACCESS    read-only
        STATUS    mandatory
        DESCRIPTION
                  "The highest value that the associated instance of the
                  object ax6300sTemperatureStatusValue may obtain
                  before an emergency shutdown of the managed device is
                  initiated."
        ::= { ax6300sTemperatureStatusEntry 4 }

    ax6300sTemperatureState OBJECT-TYPE
        SYNTAX    INTEGER {
                      normal(1),
                      caution(2),
                      warning(3),
                      fatal(4)
                  }
        ACCESS    read-only
        STATUS    mandatory
        DESCRIPTION
                  "The current state of the testpoint being instrumented."
        ::= { ax6300sTemperatureStatusEntry 5 }
            
    ax6300sSdCardTable OBJECT-TYPE
        SYNTAX    SEQUENCE OF Ax6300sSdCardEntry
        ACCESS    not-accessible
        STATUS    mandatory
        DESCRIPTION
                  "An table containing Sd-card information."
        ::= { ax6300sMsuBoard 3 }
            
    ax6300sSdCardEntry OBJECT-TYPE
        SYNTAX    Ax6300sSdCardEntry
        ACCESS    not-accessible
        STATUS    mandatory
        DESCRIPTION
                  "An entry containing SOP information."
        INDEX     { ax6300sChassisIndex,
                    ax6300sMsuBoardIndex,
                    ax6300sSdCardIndex }
        ::= { ax6300sSdCardTable 1 }

    Ax6300sSdCardEntry ::= SEQUENCE {
        ax6300sSdCardIndex         INTEGER,
        ax6300sSdCardConnection    INTEGER,
        ax6300sSdCardTotalSize     INTEGER,
        ax6300sSdCardUsedSize      INTEGER,
        ax6300sSdCardFreeSize      INTEGER
    }

    ax6300sSdCardIndex OBJECT-TYPE
        SYNTAX    INTEGER 
        ACCESS    not-accessible
        STATUS    mandatory
        DESCRIPTION
                  "The SD card index number."
        ::= { ax6300sSdCardEntry  1 }

    ax6300sSdCardConnection OBJECT-TYPE
        SYNTAX    INTEGER {
                      connected(2),
                      disconnected(32)
                  }
        ACCESS    read-only
        STATUS    mandatory
        DESCRIPTION
                  "The SD card connection is shown."
        ::= { ax6300sSdCardEntry 2 }

    ax6300sSdCardTotalSize OBJECT-TYPE
        SYNTAX    INTEGER
        ACCESS    read-only
        STATUS    mandatory
        DESCRIPTION
                  "Total capacity of the SD card is shown by the numerical value. It responds by -1
                  at the MC card unconnection."
        ::= { ax6300sSdCardEntry 3 }

    ax6300sSdCardUsedSize OBJECT-TYPE
        SYNTAX    INTEGER
        ACCESS    read-only
        STATUS    mandatory
        DESCRIPTION
                  "The use capacity of the SD card is shown by the numerical value. It responds by -1
                  at the SD card unconnection. "
        ::= { ax6300sSdCardEntry 4 }

    ax6300sSdCardFreeSize OBJECT-TYPE
        SYNTAX    INTEGER
        ACCESS    read-only
        STATUS    mandatory
        DESCRIPTION
                  "Total capacity of the SD card is shown by the numerical value. It responds by -1
                  at the MC card unconnection."
        ::= { ax6300sSdCardEntry  5 }

           
    ax6300sSopTable OBJECT-TYPE
        SYNTAX    SEQUENCE OF Ax6300sSopEntry
        ACCESS    not-accessible
        STATUS    mandatory
        DESCRIPTION
                  "A table containing SOP information."
        ::= { ax6300sMsuBoard  4 }

    ax6300sSopEntry OBJECT-TYPE
        SYNTAX    Ax6300sSopEntry
        ACCESS    not-accessible
        STATUS    mandatory
        DESCRIPTION
                  "An entry containing SOP information."
        INDEX   { ax6300sChassisIndex,
                  ax6300sMsuBoardIndex }
        ::= { ax6300sSopTable 1 }

    Ax6300sSopEntry ::= SEQUENCE {
        ax6300sSopAlarmLevel               DisplayString,
        ax6300sSopAlarmEventPoint          DisplayString,
        ax6300sSopAlarmEventCode           DisplayString,
        ax6300sSopAlarmEventInterfaceID    DisplayString,
        ax6300sSopAlarmMsgText             DisplayString
    }

    ax6300sSopAlarmLevel OBJECT-TYPE
        SYNTAX    DisplayString
        ACCESS    read-only
        STATUS    mandatory
        DESCRIPTION
                  "Error level displayed on a SOP window. When the BCU does not
                  support SOP, this will be an OCTET STRING of zero length.
                  For information about this code, see:  Operator's Manual."
        ::= { ax6300sSopEntry 1 }

    ax6300sSopAlarmEventPoint OBJECT-TYPE
        SYNTAX    DisplayString
        ACCESS    read-only
        STATUS    mandatory
        DESCRIPTION
                  "The code displayed on a SOP window, which stands for a device
                  part of the factor of the alarm message. When the BCU does not
                  support SOP, this will be an OCTET STRING of zero length.
                  For information about this code, see:  Operator's Manual."
        ::= { ax6300sSopEntry 2 }

    ax6300sSopAlarmEventCode OBJECT-TYPE
        SYNTAX    DisplayString
        ACCESS    read-only
        STATUS    mandatory
        DESCRIPTION
                  "Event kind code of alarm message displayed on a SOP window.
                  When the BCU does not support SOP, this will be an OCTET STRING
                  of zero length. For information about this code, see:  Operator's
                  Manual."
        ::= { ax6300sSopEntry 3 }

    ax6300sSopAlarmEventInterfaceID OBJECT-TYPE
        SYNTAX    DisplayString
        ACCESS    read-only
        STATUS    mandatory
        DESCRIPTION
                  "Interface identification of alarm messages on a SOP window.
                  When the BCU does not support SOP, this will be an OCTET STRING
                  of zero length. For information about this code, see:  Operator's
                  Manual."
        ::= { ax6300sSopEntry 4 }

    ax6300sSopAlarmMsgText OBJECT-TYPE
        SYNTAX    DisplayString
        ACCESS    read-only
        STATUS    mandatory
        DESCRIPTION
                  "The text of the alarm message on a SOP window. When the BCU does
                  not support SOP, this will be an OCTET STRING of zero length.
                  For more information about this code, see:  Operator's Manual."
        ::= { ax6300sSopEntry 5 }

    ax6300sNifBoardTable OBJECT-TYPE
        SYNTAX    SEQUENCE OF Ax6300sNifBoardTableEntry
        ACCESS    not-accessible
        STATUS    mandatory
        DESCRIPTION
                  "A table containing Network Interface cards (NIF) information that
                  slot is loaded."
        ::= { ax6300sNifBoard 1 }

    ax6300sNifBoardEntry OBJECT-TYPE
        SYNTAX    Ax6300sNifBoardTableEntry
        ACCESS    not-accessible
        STATUS    mandatory
        DESCRIPTION
                  "An entry containing NIF information about specific chassis."
        INDEX   { ax6300sChassisIndex,
                  ax6300sNifBoardSlotIndex }
        ::= { ax6300sNifBoardTable 1 }

    Ax6300sNifBoardTableEntry ::= SEQUENCE {
        ax6300sNifBoardSlotIndex       INTEGER,
        ax6300sNifBoardType            INTEGER,
        ax6300sNifBoardOperStatus      INTEGER,
        ax6300sNifBoardName            DisplayString,
        ax6300sNifBoardAbbreviation    DisplayString,
        ax6300sNifPhysLineNumber       INTEGER,
        ax6300sNifSerialNumber         DisplayString,
        ax6300sNifBoardTemperatureStatusValue   Integer32
    }

    ax6300sNifBoardSlotIndex OBJECT-TYPE
        SYNTAX    INTEGER
        ACCESS    not-accessible
        STATUS    mandatory
        DESCRIPTION
                  "Position information of NIF loading slot. The value is from 1
                  to ax6300sNifBoardNumber."
        ::= { ax6300sNifBoardEntry 1 }

    ax6300sNifBoardType OBJECT-TYPE
        SYNTAX    INTEGER {
                      disconnected(-1),
                      nif-48-port-10BASE-T-100BASE-TX-1000BASE-T(0),
                      nif-16-port-1000BASE-X-SFP(1),
                      nif-1-port-10GBASE-R-XFP(2),
                      nif-24-port-10BASE-T-100BASE-TX-1000BASE-T(3),
                      nif-24-port-1000BASE-X-SFP(4),
                      nif-4-port-10GBASE-R-XFP(5),
                      nif-8-port-10GBASE-R-XFP(6),
                      nif-1-port-10GBASE-R-XFP-Edge-EoE(12),
                      nif-4-port-SHAPER-plus-2-port-X-SFP-SHAPER(13),
                      nif-1-port-10GBASE-R-XFP-QinQ(16),
                      nif-4-port-SHAPER-or-SFP-SHAPER-plus-4-port-SFP-SHAPER-A(17),
                      nif-1-port-10GBASE-R-XFP-Excessive-Traffic-Controller(19),
                      nif-4-port-10GBASE-R-XFP-A(28),
                      nif-8-port-10GBASE-R-XFP-A(29)
                  }
        ACCESS    read-only
        STATUS    mandatory
        DESCRIPTION
                  "Type of connecting package.The value is register value of NIF package.
                  The value is -1 when the NIF is disconnected."
        ::= { ax6300sNifBoardEntry 2 }

    ax6300sNifBoardOperStatus OBJECT-TYPE
        SYNTAX    INTEGER {
                      other(1),
                      active(2),
                      initialization(3),
                      down(4),
                      closed(5),
                      lock(6),
                      disconnect(32)
                  }
        ACCESS    read-only
        STATUS    mandatory
        DESCRIPTION
                  "Operation status of NIF board.(STATUS LED)"
        ::= { ax6300sNifBoardEntry 3 }

    ax6300sNifBoardName OBJECT-TYPE
        SYNTAX    DisplayString (SIZE (0..16))
        ACCESS    read-only
        STATUS    mandatory
        DESCRIPTION
                  "NIF board name. When NIF board is disconnected
                  this will be an DisplayString of zero length."
        ::= { ax6300sNifBoardEntry 4 }

    ax6300sNifBoardAbbreviation OBJECT-TYPE
        SYNTAX    DisplayString (SIZE (0..16))
        ACCESS    read-only
        STATUS    mandatory
        DESCRIPTION
                  "The abbreviation name of NIF board. When NIF board is disconnected
                   this will be an OCTET STRING of zero length."
        ::= { ax6300sNifBoardEntry 5 }

    ax6300sNifPhysLineNumber OBJECT-TYPE
        SYNTAX    INTEGER
        ACCESS    read-only
        STATUS    mandatory
        DESCRIPTION
                  "Number of NIF's physical port.The max is 48.
                  The value is -1 when value of ax6300sNifBoardType is -1 or other(1)."
        ::= { ax6300sNifBoardEntry 7 }

    ax6300sNifSerialNumber OBJECT-TYPE
        SYNTAX    DisplayString (SIZE (0..30))
        ACCESS    read-only
        STATUS    mandatory
        DESCRIPTION
                  "Management information (SerialNumber) of NIF package.
                    When NIF board is disconnected
                   this will be an OCTET STRING of zero length."
        ::= { ax6300sNifBoardEntry 8 }

    ax6300sNifBoardTemperatureStatusValue OBJECT-TYPE
        SYNTAX    Integer32
        ACCESS    read-only
        STATUS    mandatory
        DESCRIPTION
                  "The current measurement of the testpoint being instrumented on NIF board.
                  The value is -2147483648 when the NIF is disconnected."
        ::= { ax6300sNifBoardEntry 10 }

    ax6300sPhysLineTable OBJECT-TYPE
        SYNTAX    SEQUENCE OF Ax6300sPhysLineTableEntry
        ACCESS    not-accessible
        STATUS    mandatory
        DESCRIPTION
                  "An table containing physical port."
        ::= { ax6300sPhysLine 1 }

    ax6300sPhysLineEntry OBJECT-TYPE
        SYNTAX    Ax6300sPhysLineTableEntry
        ACCESS    not-accessible
        STATUS    mandatory
        DESCRIPTION
                  "An entry containing physical port."
        INDEX     { ax6300sChassisIndex,
                    ax6300sNifBoardSlotIndex,
                    ax6300sPhysLineIndex }
        ::= { ax6300sPhysLineTable 1 }

    Ax6300sPhysLineTableEntry ::= SEQUENCE {
        ax6300sPhysLineIndex                INTEGER,
        ax6300sPhysLineConnectorType        INTEGER,
        ax6300sPhysLineOperStatus           INTEGER,
        ax6300sPhysLineIfIndexNumber        INTEGER,
        ax6300sPhysLineTransceiverStatus    INTEGER
    }

    ax6300sPhysLineIndex OBJECT-TYPE
        SYNTAX    INTEGER
        ACCESS    not-accessible
        STATUS    mandatory
        DESCRIPTION
                  "Physical port number. The value is from 1 to ax6300sNifLineNumber."
        ::= { ax6300sPhysLineEntry 1 }

    ax6300sPhysLineConnectorType OBJECT-TYPE
        SYNTAX    INTEGER {
                      other(1),
                      type1000BASE-LX(301),
                      type1000BASE-SX(302),
                      type1000BASE-LH(303),
                      type1000BASE-BX10-D(304),
                      type1000BASE-BX10-U(305),
                      type1000BASE-BX40-D(306),
                      type1000BASE-BX40-U(307),
                      type1000BASE-SX2(308),
                      type1000BASE-UTP(309),
                      type1000BASE-LHB(310),
                      type10GBASE-SR(401),
                      type10GBASE-LR(402),
                      type10GBASE-ER(403),
                      type10GBASE-ZR(404)
                  }
        ACCESS    read-only
        STATUS    mandatory
        DESCRIPTION
                  "Connector type is connected physical port. The value is 1(other)
                  when connector is disconnected or connector type is unknown."
        ::= { ax6300sPhysLineEntry 2 }

    ax6300sPhysLineOperStatus OBJECT-TYPE
        SYNTAX    INTEGER {
                      other(1),
                      active(2),
                      initialization(3),
                      down(4),
                      lock(6),
                      close(7),
                      line-fault(8),
                      test(9)
                  }
        ACCESS    read-only
        STATUS    mandatory
        DESCRIPTION
                  "Status of physical port. The value is -1 when PSU or NIF board is
                  disconnected."
        ::= { ax6300sPhysLineEntry 3 }

    ax6300sPhysLineIfIndexNumber OBJECT-TYPE
        SYNTAX    INTEGER
        ACCESS    read-only
        STATUS    mandatory
        DESCRIPTION
                  "Number of ifIndex which is included in physical port.The value is -1
                  when PSU board or NIF board is disconnected."
        ::= { ax6300sPhysLineEntry 4 }

    ax6300sPhysLineTransceiverStatus OBJECT-TYPE
        SYNTAX    INTEGER{
                      unchangeable-transceiver(1),
                      sfp-mounted(20),
                      sfp-unmounted(21),
                      unsupported-sfp-mounted(22),
                      sfp-fault(24),
                      xfp-mounted(30),
                      xfp-unmounted(31),
                      unsupported-xfp-mounted(32),
                      xfp-fault(34)
                  }
        ACCESS    read-only
        STATUS    mandatory
        DESCRIPTION
                  "Type and status of replaceable transceiver."
        ::= { ax6300sPhysLineEntry 5 }

    ax6300sLineIfTable OBJECT-TYPE
        SYNTAX    SEQUENCE OF Ax6300sLineIfTableEntry
        ACCESS    not-accessible
        STATUS    mandatory
        DESCRIPTION
                  "A table containing physical port correspond to ifIndex."
        ::= { ax6300sInterface 1 }

    ax6300sLineIfEntry OBJECT-TYPE
        SYNTAX    Ax6300sLineIfTableEntry
        ACCESS    not-accessible
        STATUS    mandatory
        DESCRIPTION
                  "An entry containing ifIndex is assigned to physical port."
        INDEX     { ax6300sChassisIndex,
                    ax6300sNifBoardSlotIndex,
                    ax6300sPhysLineIndex,
                    ax6300sLineIfIndex }
        ::= { ax6300sLineIfTable 1 }

    Ax6300sLineIfTableEntry ::= SEQUENCE {
        ax6300sLineIfIndex    INTEGER,
        ax6300sIfIndex        INTEGER
    }

    ax6300sLineIfIndex OBJECT-TYPE
        SYNTAX    INTEGER
        ACCESS    not-accessible
        STATUS    mandatory
        DESCRIPTION
                  "The value of ifIndex to distinguish entry of this table.The value is
                  from 1 to ax6300sPhysLineIfIndexNumber."
        ::= { ax6300sLineIfEntry 1 }

    ax6300sIfIndex OBJECT-TYPE
        SYNTAX    INTEGER
        ACCESS    read-only
        STATUS    mandatory
        DESCRIPTION
                  "The value of ifIndex which is assigned to this physical port.
                  The value is 0 when ifIndex is not assigned to this physical port."
        ::= { ax6300sLineIfEntry 2 }

--
-- ax6300sFdbClearMIB      OBJECT IDENTIFIER ::= { ax6300sOperationCommand 1 }
--

    ax6300sFdbClearSet OBJECT-TYPE
        SYNTAX    INTEGER {
                      initialValue(0),
                      processing(1),
                      failure(2),
                      success(3)
                  }
        ACCESS    read-write
        STATUS    mandatory
        DESCRIPTION
                  "Fdb clear information. When want to clear fdb, 
                  then set value of this MIB as 1."
        ::= { ax6300sFdbClearMIB 1 }

    ax6300sFdbClearReqTime OBJECT-TYPE
        SYNTAX    TimeTicks
        ACCESS    read-only
        STATUS    mandatory
        DESCRIPTION
                  "This object indicates the most recent time that
                  received the demand to clear Fdb information.(sysUpTime)"
        ::= { ax6300sFdbClearMIB 2 }

    ax6300sFdbClearSuccessTime OBJECT-TYPE
        SYNTAX    TimeTicks
        ACCESS    read-only
        STATUS    mandatory
        DESCRIPTION
                  "This object indicates the time of the most recent
                  Fdb clearing success.(sysUpTime)"
        ::= { ax6300sFdbClearMIB 3 }

-- ax6700sSwitch group

    ax6700sModelType OBJECT-TYPE
        SYNTAX    INTEGER {
                      other(1),
                      model-AX6708S(701)
                  }
        ACCESS    read-only
        STATUS    mandatory
        DESCRIPTION
                  "Model type of this system."
        ::= { ax6700sSwitch 1 }

--    ax6700sSoftware OBJECT-TYPE
--        SYNTAX    INTEGER
--        ACCESS    not-accessible
--        STATUS    mandatory
--        DESCRIPTION
--                 "Software information of this system."
--        ::= { ax6700sSwitch 2 }

    ax6700sSoftwareName OBJECT-TYPE
        SYNTAX    DisplayString (SIZE (0..16))
        ACCESS    read-only
        STATUS    mandatory
        DESCRIPTION
                  "Software name of this system."
        ::= { ax6700sSoftware 1 }

    ax6700sSoftwareAbbreviation OBJECT-TYPE
        SYNTAX    DisplayString (SIZE (0..16))
        ACCESS    read-only
        STATUS    mandatory
        DESCRIPTION
                  "System software abbreviation."
        ::= { ax6700sSoftware 2 }

    ax6700sSoftwareVersion OBJECT-TYPE
        SYNTAX    DisplayString (SIZE (0..16))
        ACCESS    read-only
        STATUS    mandatory
        DESCRIPTION
                  "System software version."
        ::= { ax6700sSoftware 3 }

    ax6700sSystemMsgText OBJECT-TYPE
        SYNTAX    DisplayString (SIZE (0..256))
        ACCESS    read-only
        STATUS    mandatory
        DESCRIPTION
                  "The text of the system log message.For information about this code,
                  see:  Operator's Manual. "
        ::= { ax6700sSystemMsg 1 }

    ax6700sSystemMsgType OBJECT-TYPE
        SYNTAX    OCTET STRING (SIZE (1))
        ACCESS    read-only
        STATUS    mandatory
        DESCRIPTION
                  "The event type. For information about this code, see:  Operator's Manual."
        ::= { ax6700sSystemMsg 2 }

    ax6700sSystemMsgTimeStamp OBJECT-TYPE
        SYNTAX    DisplayString (SIZE (0..14))
        ACCESS    read-only
        STATUS    mandatory
        DESCRIPTION
                  "The time that event occured. And that is expressed as type of
                  MM/DD hh:mm:ss
                      MM:month(01-12)
                      DD:day(01-31)
                      hh:hour(00-23)
                      mm:minute(00-59)
                      ss:second(00-59)
                  Insert space between DD and hh."
        ::= { ax6700sSystemMsg 3 }

    ax6700sSystemMsgLevel OBJECT-TYPE
        SYNTAX    OCTET STRING (SIZE (1))
        ACCESS    read-only
        STATUS    mandatory
        DESCRIPTION
                  "The newest system message log level.For information about this code,
                  see:  Operator's Manual. "
        ::= { ax6700sSystemMsg 4 }

    ax6700sSystemMsgEventPoint OBJECT-TYPE
        SYNTAX    DisplayString (SIZE (0..8))
        ACCESS    read-only
        STATUS    mandatory
        DESCRIPTION
                  "The code of part that system message error occured. For information
                  about this code,see:  Operator's Manual. "
        ::= { ax6700sSystemMsg 5 }

    ax6700sSystemMsgEventInterfaceID OBJECT-TYPE
        SYNTAX    DisplayString (SIZE (0..40))
        ACCESS    read-only
        STATUS    mandatory
        DESCRIPTION
                  "Interface identification of system messages. For information
                  about this code,see:  Operator's Manual."
        ::= { ax6700sSystemMsg 6 }

    ax6700sSystemMsgEventCode OBJECT-TYPE
        SYNTAX    OCTET STRING (SIZE (4))
        ACCESS    read-only
        STATUS    mandatory
        DESCRIPTION
                  "Event kind code of system messages. For information about this code,
                  see:  Operator's Manual. "
        ::= { ax6700sSystemMsg 7 }

    ax6700sSystemMsgAdditionalCode OBJECT-TYPE
        SYNTAX    OCTET STRING (SIZE (6))
        ACCESS    read-only
        STATUS    mandatory
        DESCRIPTION
                  "Additional code of system messages. For information about this code,
                  see:  Operator's Manual. "
        ::= { ax6700sSystemMsg 8 }

    ax6700sSnmpSendReceiveSize OBJECT-TYPE
        SYNTAX    INTEGER
        ACCESS    read-only
        STATUS    mandatory
        DESCRIPTION
                  "SNMP packet data size in Manager-to-Agent communication. The value is
                  displayed in bytes."
        ::= { ax6700sSnmpAgent 1 }

    ax6700sSnmpReceiveDelay OBJECT-TYPE
        SYNTAX    INTEGER
        ACCESS    read-only
        STATUS    mandatory
        DESCRIPTION
                  "A recommendable interval to receive packets from Manager.The value is
                  displayed in milliseconds."
        ::= { ax6700sSnmpAgent 2 }

    ax6700sSnmpContinuousSend OBJECT-TYPE
        SYNTAX    INTEGER
        ACCESS    read-only
        STATUS    mandatory
        DESCRIPTION
                  "Number of times that is recommendable continuous transmission
                  packets."
        ::= { ax6700sSnmpAgent 3 }

    ax6700sSnmpObjectMaxNumber OBJECT-TYPE
        SYNTAX    INTEGER
        ACCESS    read-only
        STATUS    mandatory
        DESCRIPTION
                  "Max number of objects that contain SNMP packet."
        ::= { ax6700sSnmpAgent 4 }

    ax6700sLicenseNumber OBJECT-TYPE
        SYNTAX    INTEGER
        ACCESS    read-only
        STATUS    mandatory
        DESCRIPTION
                  "The number of the configured license serial numbers."
        ::= { ax6700sLicense 1 }

    ax6700sLicenseTable OBJECT-TYPE
        SYNTAX    SEQUENCE OF Ax6700sLicenseTableEntry
        ACCESS    not-accessible
        STATUS    mandatory
        DESCRIPTION
                  "The table containing the license information."
        ::= { ax6700sLicense 2 }

    ax6700sLicenseEntry OBJECT-TYPE
        SYNTAX    Ax6700sLicenseTableEntry
        ACCESS    not-accessible
        STATUS    mandatory
        DESCRIPTION
                  "The entry of license information."
        INDEX     { ax6700sLicenseIndex }
        ::= { ax6700sLicenseTable 1 }

    Ax6700sLicenseTableEntry ::= SEQUENCE {
        ax6700sLicenseIndex           INTEGER,
        ax6700sLicenseSerialNumber    DisplayString,
        ax6700sLicenseOptionNumber    INTEGER
    }

    ax6700sLicenseIndex OBJECT-TYPE
        SYNTAX    INTEGER
        ACCESS    not-accessible
        STATUS    mandatory
        DESCRIPTION
                  "The unique index number given for each serial number. The number is from 1 to ax6700sLicenseNumber."
        ::= { ax6700sLicenseEntry 1 }

    ax6700sLicenseSerialNumber OBJECT-TYPE
        SYNTAX    DisplayString 
        ACCESS    read-only
        STATUS    mandatory
        DESCRIPTION
                  "The serial number."
        ::= { ax6700sLicenseEntry 2 }

    ax6700sLicenseOptionNumber OBJECT-TYPE
        SYNTAX    INTEGER 
        ACCESS    read-only
        STATUS    mandatory
        DESCRIPTION
                  "The number of option licenses associated with the serial number."
        ::= { ax6700sLicenseEntry 3 }

    ax6700sLicenseOptionTable OBJECT-TYPE
        SYNTAX    SEQUENCE OF Ax6700sLicenseOptionTableEntry
        ACCESS    not-accessible
        STATUS    mandatory
        DESCRIPTION
                  "The table containing option licenses information associated with the serial number."
        ::= { ax6700sLicense 3 }

    ax6700sLicenseOptionEntry OBJECT-TYPE
        SYNTAX    Ax6700sLicenseOptionTableEntry
        ACCESS    not-accessible
        STATUS    mandatory
        DESCRIPTION
                  "The entry of the option license information associated with the serial number."
        INDEX     { ax6700sLicenseOptionIndex,
                    ax6700sLicenseOptionNumberIndex }
        ::= { ax6700sLicenseOptionTable 1 }

    Ax6700sLicenseOptionTableEntry ::= SEQUENCE {
        ax6700sLicenseOptionIndex                   INTEGER,
        ax6700sLicenseOptionNumberIndex             INTEGER,
        ax6700sLicenseOptionSoftwareName            DisplayString,
        ax6700sLicenseOptionSoftwareAbbreviation    DisplayString
    }

    ax6700sLicenseOptionIndex OBJECT-TYPE
        SYNTAX    INTEGER
        ACCESS    not-accessible
        STATUS    mandatory
        DESCRIPTION
                  "The unique index number given for each serial number. The same number as ax6700sLicenseIndex."
        ::= { ax6700sLicenseOptionEntry 1 }

    ax6700sLicenseOptionNumberIndex OBJECT-TYPE
        SYNTAX    INTEGER
        ACCESS    not-accessible
        STATUS    mandatory
        DESCRIPTION
                  "The unique index number of option licenses information which is given for each serial number. The number is from 1 to ax6700sLicenseNumber."
        ::= { ax6700sLicenseOptionEntry 2 }

    ax6700sLicenseOptionSoftwareName OBJECT-TYPE
        SYNTAX    DisplayString 
        ACCESS    read-only
        STATUS    mandatory
        DESCRIPTION
                  "The software model name of the option license information associated with the serial number."
        ::= { ax6700sLicenseOptionEntry 3 }

    ax6700sLicenseOptionSoftwareAbbreviation OBJECT-TYPE
        SYNTAX    DisplayString 
        ACCESS    read-only
        STATUS    mandatory
        DESCRIPTION
                  "The software abbreviated name of the option license information associated with the serial number. "
        ::= { ax6700sLicenseOptionEntry 4 }

-- ax6700sDevice group

    ax6700sChassisMaxNumber OBJECT-TYPE
        SYNTAX    INTEGER
        ACCESS    read-only
        STATUS    mandatory
        DESCRIPTION
                  "Max number of cluster chassis that can connect to this router."
        ::= { ax6700sChassis 1 }

    ax6700sChassisTable OBJECT-TYPE
        SYNTAX    SEQUENCE OF Ax6700sChassisTableEntry
        ACCESS    not-accessible
        STATUS    mandatory
        DESCRIPTION
                  "A table containing chassis information."
        ::= { ax6700sChassis 2 }

    ax6700sChassisEntry OBJECT-TYPE
        SYNTAX    Ax6700sChassisTableEntry
        ACCESS    not-accessible
        STATUS    mandatory
        DESCRIPTION
                  "An entry containing specific chassis."
        INDEX     { ax6700sChassisIndex }
        ::= { ax6700sChassisTable 1 }

    Ax6700sChassisTableEntry ::= SEQUENCE {
        ax6700sChassisIndex                 INTEGER,
        ax6700sChassisType                  INTEGER,
        ax6700sChassisStatus                INTEGER,
        ax6700sPowerUnitNumber              INTEGER,
        ax6700sFanNumber                    INTEGER,
        ax6700sBcuBoardDuplexMode           INTEGER,
        ax6700sBcuBoardNumber               INTEGER,
        ax6700sNifBoardNumber               INTEGER,
        ax6700sPowerControl                 INTEGER,
        ax6700sBsuBoardDuplexActiveMode     INTEGER,
        ax6700sBsuBoardDuplexStandbyMode    INTEGER,
        ax6700sBsuBoardNumber               INTEGER
    }

    ax6700sChassisIndex OBJECT-TYPE
        SYNTAX    INTEGER
        ACCESS    not-accessible
        STATUS    mandatory
        DESCRIPTION
                  "A number to specify ax6700sChassisEntry."
        ::= { ax6700sChassisEntry 1 }

    ax6700sChassisType OBJECT-TYPE
        SYNTAX    INTEGER {
                      other(1),
                      model-AX6708S(701)
                  }
        ACCESS    read-only
        STATUS    mandatory
        DESCRIPTION
                  "Chassis type of this system."
        ::= { ax6700sChassisEntry 2 }

    ax6700sChassisStatus OBJECT-TYPE
        SYNTAX    INTEGER {
                      up(2)
                  }
        ACCESS    read-only
        STATUS    mandatory
        DESCRIPTION
                  "Current status of this chassis."
        ::= { ax6700sChassisEntry 3 }

    ax6700sPowerUnitNumber OBJECT-TYPE
        SYNTAX    INTEGER
        ACCESS    read-only
        STATUS    mandatory
        DESCRIPTION
                  "Number of maximum power switches that this router can connect its."
        ::= { ax6700sChassisEntry 21 }

    ax6700sFanNumber OBJECT-TYPE
        SYNTAX    INTEGER
        ACCESS    read-only
        STATUS    mandatory
        DESCRIPTION
                  "The maximum number of fans that can connect to this chassis."
        ::= { ax6700sChassisEntry 23 }

    ax6700sBcuBoardDuplexMode OBJECT-TYPE
        SYNTAX    INTEGER{
                      simplex-mode(1),
                      duplex-mode(2)
                  }
        ACCESS    read-only
        STATUS    mandatory
        DESCRIPTION
                  "The BCU duplex mode."
        ::= { ax6700sChassisEntry 26 }

    ax6700sBcuBoardNumber OBJECT-TYPE
        SYNTAX    INTEGER
        ACCESS    read-only
        STATUS    mandatory
        DESCRIPTION
                  "The maximum number of BCU that can connect to this chassis."
        ::= { ax6700sChassisEntry 27 }

    ax6700sNifBoardNumber OBJECT-TYPE
        SYNTAX    INTEGER
        ACCESS    read-only
        STATUS    mandatory
        DESCRIPTION
                  "The maximum number of NIF that can connect to this chassis."
        ::= { ax6700sChassisEntry 28 }

    ax6700sPowerControl OBJECT-TYPE
        SYNTAX    INTEGER{
                      normal-mode(1),
                      power-save-mode(2),
                      power-save-mode2(3),
                      change-mode(10)
                  }
        ACCESS    read-only
        STATUS    mandatory
        DESCRIPTION
                  "The power mode of this chassis."
        ::= { ax6700sChassisEntry 29 }

    ax6700sBsuBoardDuplexActiveMode  OBJECT-TYPE
        SYNTAX    INTEGER
        ACCESS    read-only
        STATUS    mandatory
        DESCRIPTION
                  "Number of BSU boards of active system."
        ::= { ax6700sChassisEntry 30 }

    ax6700sBsuBoardDuplexStandbyMode  OBJECT-TYPE
        SYNTAX    INTEGER
        ACCESS    read-only
        STATUS    mandatory
        DESCRIPTION
                  "Number of BSU boards of standby system."
        ::= { ax6700sChassisEntry 31 }

    ax6700sBsuBoardNumber  OBJECT-TYPE
        SYNTAX    INTEGER
        ACCESS    read-only
        STATUS    mandatory
        DESCRIPTION
                  "Number of Bsu boards that can connect to this chassis."
        ::= { ax6700sChassisEntry 32 }

    ax6700sPowerUnitTable OBJECT-TYPE
        SYNTAX    SEQUENCE OF Ax6700sPowerUnitTableEntry
        ACCESS    not-accessible
        STATUS    mandatory
        DESCRIPTION
                  "A table containing power unit information."
        ::= { ax6700sChassis 3 }

    ax6700sPowerUnitEntry OBJECT-TYPE
        SYNTAX    Ax6700sPowerUnitTableEntry
        ACCESS    not-accessible
        STATUS    mandatory
        DESCRIPTION
                  "An entry containing power unit information."
        INDEX     { ax6700sChassisIndex,
                    ax6700sPowerUnitIndex }
        ::= { ax6700sPowerUnitTable 1 }

    Ax6700sPowerUnitTableEntry ::= SEQUENCE {
        ax6700sPowerUnitIndex        INTEGER,
        ax6700sPowerConnectStatus    INTEGER,
        ax6700sPowerSupplyStatus     INTEGER
    }

    ax6700sPowerUnitIndex OBJECT-TYPE
        SYNTAX    INTEGER
        ACCESS    not-accessible
        STATUS    mandatory
        DESCRIPTION
                  "A number to position of the power units.The value from 1
                  to ax6700sPowerUnitNumber."
        ::= { ax6700sPowerUnitEntry 1 }
            
    ax6700sPowerConnectStatus OBJECT-TYPE
        SYNTAX    INTEGER {
                      connected(2),
                      disconnected(32)
                  }
        ACCESS    read-only
        STATUS    mandatory
        DESCRIPTION
                  "The current connection status of the power unit."
        ::= { ax6700sPowerUnitEntry 2 }

    ax6700sPowerSupplyStatus OBJECT-TYPE
        SYNTAX    INTEGER {
                      ok(2),
                      fault(4),
                      disconnected(-1)
                  }
        ACCESS    read-only
        STATUS    mandatory
        DESCRIPTION
                  "Status of power supply."
        ::= { ax6700sPowerUnitEntry 3 }

    ax6700sFanTable OBJECT-TYPE
        SYNTAX    SEQUENCE OF Ax6700sFanTableEntry
        ACCESS    not-accessible
        STATUS    mandatory
        DESCRIPTION
                  "A table containing fan information."
        ::= { ax6700sChassis 4 }

    ax6700sFanEntry OBJECT-TYPE
        SYNTAX    Ax6700sFanTableEntry
        ACCESS    not-accessible
        STATUS    mandatory
        DESCRIPTION
                  "This entry containing information for a fan."
        INDEX   { ax6700sChassisIndex,
                  ax6700sFanIndex }
        ::= { ax6700sFanTable 1 }

    Ax6700sFanTableEntry ::= SEQUENCE {
        ax6700sFanIndex     INTEGER,
        ax6700sFanStatus    INTEGER
    }

    ax6700sFanIndex OBJECT-TYPE
        SYNTAX    INTEGER
        ACCESS    not-accessible
        STATUS    mandatory
        DESCRIPTION
                  "Index to indicate position of fans."
        ::= { ax6700sFanEntry 1 }

    ax6700sFanStatus OBJECT-TYPE
        SYNTAX    INTEGER {
                      ok(2),
                      high-speed(3),
                      fault(4)
                  }
        ACCESS    read-only
        STATUS    mandatory
        DESCRIPTION
                  "Status of fans."
        ::= { ax6700sFanEntry 2 }

    ax6700sBcuBoardTable OBJECT-TYPE
        SYNTAX    SEQUENCE OF Ax6700sBcuBoardEntry
        ACCESS    not-accessible
        STATUS    mandatory
        DESCRIPTION
                  "The BCU information table."
        ::= { ax6700sBcuBoard 1 }

    ax6700sBcuBoardEntry OBJECT-TYPE
        SYNTAX    Ax6700sBcuBoardEntry
        ACCESS    not-accessible
        STATUS    mandatory
        DESCRIPTION
                  "The BCU information entry."
        INDEX     { ax6700sChassisIndex,
                    ax6700sBcuBoardIndex }
        ::= {ax6700sBcuBoardTable 1 }

    Ax6700sBcuBoardEntry ::= SEQUENCE{
        ax6700sBcuBoardIndex                 INTEGER,
        ax6700sBcuOperStatus                 INTEGER,
        ax6700sBcuOperModeStatus             BITS,
        ax6700sBcuActiveLedStatus            INTEGER,
        ax6700sBcuSystem1LedStatus           INTEGER,
        ax6700sBcuSystem2LedStatus           INTEGER,
        ax6700sBcuMgmtPortStatus             INTEGER,
        ax6700sBcuBoardName                  DisplayString,
        ax6700sBcuBoardAbbreviation          DisplayString,
        ax6700sBcuCpuName                    DisplayString,
        ax6700sBcuCpuClock                   INTEGER,
        ax6700sBcuMemoryTotalSize            INTEGER,
        ax6700sBcuMemoryUsedSize             INTEGER,
        ax6700sBcuMemoryFreeSize             INTEGER,
        ax6700sBcuRomVersion                 DisplayString,
        ax6700sBcuCpuLoad1m                  INTEGER,
        ax6700sBcuFlashTotalSize             INTEGER,
        ax6700sBcuFlashUsedSize              INTEGER,
        ax6700sBcuFlashFreeSize              INTEGER,
        ax6700sBcuTemperatureStatusNumber    INTEGER,
        ax6700sBcuSerialNumber               DisplayString,
        ax6700sBcuTotalAccumRunTime          INTEGER,
        ax6700sBcuCriticalAccumRunTime       INTEGER
    }

    ax6700sBcuBoardIndex OBJECT-TYPE
        SYNTAX    INTEGER 
        ACCESS    not-accessible
        STATUS    mandatory
        DESCRIPTION
                  "The index of BCU information table."
        ::= { ax6700sBcuBoardEntry 1 }

    ax6700sBcuOperStatus OBJECT-TYPE
        SYNTAX    INTEGER {
                      initialized(1),
                      active(2),
                      disabled(3),
                      down(4),
                      power-off(6)
                  }
        ACCESS    read-only
        STATUS    mandatory
        DESCRIPTION
                  "The state of BCU STATUS LED of the device."
        ::= { ax6700sBcuBoardEntry 2 }

    ax6700sBcuOperModeStatus OBJECT-TYPE
        SYNTAX    BITS {
                      disconnected(0),
                      initialized(1),
                      active(2),
                      standby(3),
                      do-not-match-with-configure-mode(4),
                      do-not-match-with-software-mode(5),
                      do-not-match-with-license-info(6),
                      down(7),
                      maintenance(8)
                  }
        ACCESS    read-only
        STATUS    mandatory
        DESCRIPTION
                  "The state of operation status of the device."
        ::= { ax6700sBcuBoardEntry 3 }

    ax6700sBcuActiveLedStatus OBJECT-TYPE
        SYNTAX    INTEGER {
                      disconnected(-1),
                      green(2),
                      extinction(6)
                  }
        ACCESS    read-only
        STATUS    mandatory
        DESCRIPTION
                  "The state of ACTIVE LED status of the device."
        ::= { ax6700sBcuBoardEntry 4 }
        
    ax6700sBcuSystem1LedStatus OBJECT-TYPE
        SYNTAX    INTEGER {
                      disconnected(-1),
                      green(2),
                      orange(3),
                      red(4),
                      extinction(6)
                  }
        ACCESS    read-only
        STATUS    mandatory
        DESCRIPTION
                  "The state of SYSTEM LED status of the device."
        ::= { ax6700sBcuBoardEntry 5 }

    ax6700sBcuSystem2LedStatus OBJECT-TYPE
        SYNTAX    INTEGER {
                      disconnected(-1),
                      green-blink(1),
                      green(2),
                      extinction(6)
                  }
        ACCESS    read-only
        STATUS    mandatory
        DESCRIPTION
                  "The state of SYSTEM2 LED status of the device."
        ::= { ax6700sBcuBoardEntry 6 }

    ax6700sBcuMgmtPortStatus OBJECT-TYPE
        SYNTAX    INTEGER {
                      disconnected(-1),
                      active(2),
                      down(4),
                      disabled(6),
                      maintenance(7),
                      line-test(9),
                      unused(10)
                  }
        ACCESS    read-only
        STATUS    mandatory
        DESCRIPTION
                  "The state of management-port status of the device."
        ::= { ax6700sBcuBoardEntry 7 }
        
    ax6700sBcuBoardName OBJECT-TYPE
        SYNTAX    DisplayString
        ACCESS    read-only
        STATUS    mandatory
        DESCRIPTION
                  "The product name of BCU Board. If BCU Board disconnected, return 0 length DisplayString."
        ::= { ax6700sBcuBoardEntry 8 }

    ax6700sBcuBoardAbbreviation OBJECT-TYPE
        SYNTAX    DisplayString
        ACCESS    read-only
        STATUS    mandatory
        DESCRIPTION
                  "The abbreviated name of BCU Board. If BCU Board disconnected, return 0 length DisplayString."
        ::= { ax6700sBcuBoardEntry 9 }
        
    ax6700sBcuCpuName OBJECT-TYPE
        SYNTAX    DisplayString
        ACCESS    read-only
        STATUS    mandatory
        DESCRIPTION
                  "The name of CPU on BCU board is shown by the character string of 16 characters or less.
                  If BCU Board disconnected, return 0 length DisplayString." 
        ::= { ax6700sBcuBoardEntry 10 }

    ax6700sBcuCpuClock OBJECT-TYPE
        SYNTAX    INTEGER
        ACCESS    read-only
        STATUS    mandatory
        DESCRIPTION
                  "CPU clock is shown by the numerical value.
                  If BCU Board disconnected, return -1."
        ::= { ax6700sBcuBoardEntry 11 }

    ax6700sBcuMemoryTotalSize OBJECT-TYPE
        SYNTAX    INTEGER
        ACCESS    read-only
        STATUS    mandatory
        DESCRIPTION
                  "The installing memory size is shown by the numerical value.
                  If BCU Board disconnected, return -1."
        ::= { ax6700sBcuBoardEntry 12 }

    ax6700sBcuMemoryUsedSize OBJECT-TYPE
        SYNTAX    INTEGER
        ACCESS    read-only
        STATUS    mandatory
        DESCRIPTION
                  "The use memory size is shown by the numerical value.
                  If BCU Board disconnected, return -1."
        ::= { ax6700sBcuBoardEntry 13 }

    ax6700sBcuMemoryFreeSize OBJECT-TYPE
        SYNTAX  INTEGER
        ACCESS  read-only
        STATUS  mandatory
        DESCRIPTION
            "The unused memory size is shown by the numerical value.
             If BCU Board disconnected, return -1."
        ::= { ax6700sBcuBoardEntry 14 }

    ax6700sBcuRomVersion OBJECT-TYPE
        SYNTAX    DisplayString
        ACCESS    read-only
        STATUS    mandatory
        DESCRIPTION
                  "The version of ROM equipped with BCU is shown by the character string.
                  If BCU Board disconnected, return 0 length DisplayString."
        ::= { ax6700sBcuBoardEntry 15 }

    ax6700sBcuCpuLoad1m OBJECT-TYPE
        SYNTAX    INTEGER
        ACCESS    read-only
        STATUS    mandatory
        DESCRIPTION
                  "CPU utilization of one minute is shown by the numerical value.
                  If BCU Board disconnected, return -1."
        ::= { ax6700sBcuBoardEntry 16 }

    ax6700sBcuFlashTotalSize OBJECT-TYPE
        SYNTAX    INTEGER
        ACCESS    read-only
        STATUS    mandatory
        DESCRIPTION
                  "The total of filesystem use capacity and unused capacity in a built-in memory 
                  is shown."
        ::= { ax6700sBcuBoardEntry 17 }

    ax6700sBcuFlashUsedSize OBJECT-TYPE
        SYNTAX    INTEGER
        ACCESS    read-only
        STATUS    mandatory
        DESCRIPTION
                  "The use capacity of the filesystem in a built-in memory is shown."
        ::= { ax6700sBcuBoardEntry 18 }

    ax6700sBcuFlashFreeSize OBJECT-TYPE
        SYNTAX    INTEGER
        ACCESS    read-only
        STATUS    mandatory
        DESCRIPTION
                  "The unused capacity of the filesystem in a built-in memory is shown. "
        ::= { ax6700sBcuBoardEntry 19 }

    ax6700sBcuTemperatureStatusNumber OBJECT-TYPE
        SYNTAX    INTEGER
        ACCESS    read-only
        STATUS    mandatory
        DESCRIPTION
                  "The maximum number of ax6700sTemperatureStatus in this chassis."
        ::= { ax6700sBcuBoardEntry 20 }

    ax6700sBcuSerialNumber OBJECT-TYPE
        SYNTAX    DisplayString
        ACCESS    read-only
        STATUS    mandatory
        DESCRIPTION
                  "The character string of the card management information of BCU package whose number is a maximum of 16. 
                  Its length is zero if not implemented or inactivated."
        ::= { ax6700sBcuBoardEntry 21 }

    ax6700sBcuTotalAccumRunTime OBJECT-TYPE
        SYNTAX    INTEGER
        ACCESS    read-only
        STATUS    mandatory
        DESCRIPTION
                  "Total operation time after operation of device begins."
        ::= { ax6700sBcuBoardEntry 22 }

    ax6700sBcuCriticalAccumRunTime OBJECT-TYPE
        SYNTAX    INTEGER
        ACCESS    read-only
        STATUS    mandatory
        DESCRIPTION
                  "Operating time under environment of 40 degrees C or more."
        ::= { ax6700sBcuBoardEntry 23 }
            
    ax6700sTemperatureStatusTable OBJECT-TYPE
        SYNTAX    SEQUENCE OF Ax6700sTemperatureStatusEntry
        ACCESS    not-accessible
        STATUS    mandatory
        DESCRIPTION
                  "The table of ambient temperature status maintained by the
                  environmental monitor."
        ::= { ax6700sBcuBoard 2 }

    ax6700sTemperatureStatusEntry OBJECT-TYPE
        SYNTAX    Ax6700sTemperatureStatusEntry
        ACCESS    not-accessible
        STATUS    mandatory
        DESCRIPTION
                  "An entry in the ambient temperature status table, representing
                  the status of the associated testpoint maintained by the
                  environmental monitor."
        INDEX     { ax6700sChassisIndex,
                    ax6700sBcuBoardIndex,
                    ax6700sTemperatureStatusIndex }
        ::= { ax6700sTemperatureStatusTable 1 }

    Ax6700sTemperatureStatusEntry ::= SEQUENCE {
        ax6700sTemperatureStatusIndex    INTEGER,
        ax6700sTemperatureStatusDescr    DisplayString,
        ax6700sTemperatureStatusValue    Integer32,
        ax6700sTemperatureThreshold      Integer32,
        ax6700sTemperatureState          INTEGER
    }

    ax6700sTemperatureStatusIndex OBJECT-TYPE
        SYNTAX    INTEGER
        ACCESS    not-accessible
        STATUS    mandatory
        DESCRIPTION
                  "Unique index for the testpoint being instrumented.
                  This index is for SNMP purposes only, and has no
                  intrinsic meaning."
        ::= { ax6700sTemperatureStatusEntry 1 }

    ax6700sTemperatureStatusDescr OBJECT-TYPE
        SYNTAX    DisplayString(SIZE(0..32))
        ACCESS    read-only
        STATUS    mandatory
        DESCRIPTION
                  "Textual description of the testpoint being instrumented.
                  This description is a short textual label, suitable as a
                  human-sensible identification for the rest of the
                  information in the entry."
        ::= { ax6700sTemperatureStatusEntry 2 }

    ax6700sTemperatureStatusValue OBJECT-TYPE
        SYNTAX    Integer32
        ACCESS    read-only
        STATUS    mandatory
        DESCRIPTION
                  "The current measurement of the testpoint being instrumented."
        ::= { ax6700sTemperatureStatusEntry 3 }

    ax6700sTemperatureThreshold OBJECT-TYPE
        SYNTAX    Integer32
        ACCESS    read-only
        STATUS    mandatory
        DESCRIPTION
                  "The highest value that the associated instance of the
                  object ax6700sTemperatureStatusValue may obtain
                  before an emergency shutdown of the managed device is
                  initiated."
        ::= { ax6700sTemperatureStatusEntry 4 }

    ax6700sTemperatureState OBJECT-TYPE
        SYNTAX    INTEGER {
                      normal(1),
                      caution(2),
                      warning(3),
                      fatal(4)
                  }
        ACCESS    read-only
        STATUS    mandatory
        DESCRIPTION
                  "The current state of the testpoint being instrumented."
        ::= { ax6700sTemperatureStatusEntry 5 }

    ax6700sSdCardTable OBJECT-TYPE
        SYNTAX    SEQUENCE OF Ax6700sSdCardEntry
        ACCESS    not-accessible
        STATUS    mandatory
        DESCRIPTION
                  "An table containing Sd-card information."
        ::= { ax6700sBcuBoard 3 }

    ax6700sSdCardEntry OBJECT-TYPE
        SYNTAX    Ax6700sSdCardEntry
        ACCESS    not-accessible
        STATUS    mandatory
        DESCRIPTION
                  "An entry containing SOP information."
        INDEX     { ax6700sChassisIndex,
                    ax6700sBcuBoardIndex,
                    ax6700sSdCardIndex }
        ::= { ax6700sSdCardTable 1 }

    Ax6700sSdCardEntry ::= SEQUENCE {
        ax6700sSdCardIndex         INTEGER,
        ax6700sSdCardConnection    INTEGER,
        ax6700sSdCardTotalSize     INTEGER,
        ax6700sSdCardUsedSize      INTEGER,
        ax6700sSdCardFreeSize      INTEGER
    }

    ax6700sSdCardIndex OBJECT-TYPE
        SYNTAX    INTEGER 
        ACCESS    not-accessible
        STATUS    mandatory
        DESCRIPTION
                  "The SD card index number."
        ::= { ax6700sSdCardEntry  1 }

    ax6700sSdCardConnection OBJECT-TYPE
        SYNTAX    INTEGER {
                      connected(2),
                      disconnected(32)
                  }
        ACCESS    read-only
        STATUS    mandatory
        DESCRIPTION
                  "The SD card connection is shown."
        ::= { ax6700sSdCardEntry 2 }

    ax6700sSdCardTotalSize OBJECT-TYPE
        SYNTAX    INTEGER
        ACCESS    read-only
        STATUS    mandatory
        DESCRIPTION
                  "Total capacity of the SD card is shown by the numerical value. It responds by -1
                  at the MC card unconnection."
        ::= { ax6700sSdCardEntry 3 }

    ax6700sSdCardUsedSize OBJECT-TYPE
        SYNTAX    INTEGER
        ACCESS    read-only
        STATUS    mandatory
        DESCRIPTION
                  "The use capacity of the SD card is shown by the numerical value. It responds by -1
                  at the SD card unconnection. "
        ::= { ax6700sSdCardEntry 4 }

    ax6700sSdCardFreeSize OBJECT-TYPE
        SYNTAX    INTEGER
        ACCESS    read-only
        STATUS    mandatory
        DESCRIPTION
                  "Total capacity of the SD card is shown by the numerical value. It responds by -1
                  at the MC card unconnection."
        ::= { ax6700sSdCardEntry  5 }

    ax6700sSopTable OBJECT-TYPE
        SYNTAX  SEQUENCE OF Ax6700sSopEntry
        ACCESS  not-accessible
        STATUS  mandatory
        DESCRIPTION
                "A table containing SOP information."
        ::= { ax6700sBcuBoard  4 }

    ax6700sSopEntry OBJECT-TYPE
        SYNTAX  Ax6700sSopEntry
        ACCESS  not-accessible
        STATUS  mandatory
        DESCRIPTION
                "An entry containing SOP information."
        INDEX   { ax6700sChassisIndex,
                  ax6700sBcuBoardIndex  }
        ::= { ax6700sSopTable 1 }

    Ax6700sSopEntry ::= SEQUENCE {
        ax6700sSopAlarmLevel               DisplayString,
        ax6700sSopAlarmEventPoint          DisplayString,
        ax6700sSopAlarmEventCode           DisplayString,
        ax6700sSopAlarmEventInterfaceID    DisplayString,
        ax6700sSopAlarmMsgText             DisplayString
    }

    ax6700sSopAlarmLevel OBJECT-TYPE
        SYNTAX    DisplayString
        ACCESS    read-only
        STATUS    mandatory
        DESCRIPTION
                  "Error level displayed on a SOP window. When the BCU does not
                  support SOP, this will be an OCTET STRING of zero length.
                  For information about this code, see:  Operator's Manual."
        ::= { ax6700sSopEntry 1 }

    ax6700sSopAlarmEventPoint OBJECT-TYPE
        SYNTAX    DisplayString
        ACCESS    read-only
        STATUS    mandatory
        DESCRIPTION
                  "The code displayed on a SOP window, which stands for a device
                  part of the factor of the alarm message. When the BCU does not
                  support SOP, this will be an OCTET STRING of zero length.
                  For information about this code, see:  Operator's Manual."
        ::= { ax6700sSopEntry 2 }

    ax6700sSopAlarmEventCode OBJECT-TYPE
        SYNTAX    DisplayString
        ACCESS    read-only
        STATUS    mandatory
        DESCRIPTION
                  "Event kind code of alarm message displayed on a SOP window.
                  When the BCU does not support SOP, this will be an OCTET STRING
                  of zero length. For information about this code, see:  Operator's
                  Manual."
        ::= { ax6700sSopEntry 3 }

    ax6700sSopAlarmEventInterfaceID OBJECT-TYPE
        SYNTAX    DisplayString
        ACCESS    read-only
        STATUS    mandatory
        DESCRIPTION
                  "Interface identification of alarm messages on a SOP window.
                  When the BCU does not support SOP, this will be an OCTET STRING
                  of zero length. For information about this code, see:  Operator's
                  Manual."
        ::= { ax6700sSopEntry 4 }

    ax6700sSopAlarmMsgText OBJECT-TYPE
        SYNTAX    DisplayString
        ACCESS    read-only
        STATUS    mandatory
        DESCRIPTION
                  "The text of the alarm message on a SOP window. When the BCU does
                  not support SOP, this will be an OCTET STRING of zero length.
                  For more information about this code, see:  Operator's Manual."
        ::= { ax6700sSopEntry 5 }
            
    ax6700sBsuBoardTable OBJECT-TYPE
        SYNTAX    SEQUENCE OF Ax6700sBsuBoardTableEntry
        ACCESS    not-accessible
        STATUS    mandatory
        DESCRIPTION
                  "A table containing BSU boards information about specific chassis."
        ::= { ax6700sBsuBoard 1 }

    ax6700sBsuBoardEntry OBJECT-TYPE
        SYNTAX    Ax6700sBsuBoardTableEntry
        ACCESS    not-accessible
        STATUS    mandatory
        DESCRIPTION
                  "An entry containing BSU boards about specific
                  chassis."
        INDEX     { ax6700sChassisIndex,
                    ax6700sBsuBoardIndex }
        ::= { ax6700sBsuBoardTable 1 }

    Ax6700sBsuBoardTableEntry ::= SEQUENCE {
        ax6700sBsuBoardIndex           INTEGER,
        ax6700sBsuBoardType            INTEGER,
        ax6700sBsuOperStatus           INTEGER,
        ax6700sBsuOperModeStatus       INTEGER,
        ax6700sBsuBoardName            DisplayString,
        ax6700sBsuBoardAbbreviation    DisplayString,
        ax6700sBsuSerialNumber         DisplayString,
        ax6700sForwardingEngineNumber  INTEGER,
        ax6700sBsuBoardTemperatureStatusValue   Integer32
    }

    ax6700sBsuBoardIndex OBJECT-TYPE
        SYNTAX    INTEGER
        ACCESS    not-accessible
        STATUS    mandatory
        DESCRIPTION
                  "Position information of the BSU slots. The value is from 1 to
                  ax6700sBsuBoardNumber."
        ::= { ax6700sBsuBoardEntry 1 }

    ax6700sBsuBoardType OBJECT-TYPE
        SYNTAX    INTEGER {
                      disconnected(-1),
                      bsu-LA(2),
                      bsu-LB(3),
                      bsu-LP(5)
                  }
        ACCESS    read-only
        STATUS    mandatory
        DESCRIPTION
                  "BSU boards ID.
                  The value is -1 when BSU board is disconnected."
        ::= { ax6700sBsuBoardEntry 2 }

    ax6700sBsuOperStatus OBJECT-TYPE
        SYNTAX    INTEGER {
                      other(1),
                      active(2),
                      initialization(3),
                      down(4),
                      closed(5),
                      inactive(6),
                      disconnect(32)
                  }
        ACCESS    read-only
        STATUS    mandatory
        DESCRIPTION
                  "Operation stasus of BSU board.(STATUS LED)"
        ::= { ax6700sBsuBoardEntry 3 }

    ax6700sBsuOperModeStatus OBJECT-TYPE
        SYNTAX    INTEGER {
                      disconnected(-1),
                      other(1),
                      active(2),
                      hot-standby(3),
                      cold-standby(4),
                      initialize(5),
                      down(6),
                      maintenance(7),
                      inactive(8),
                      cold-standby2(9)
                  }
        ACCESS    read-only
        STATUS    mandatory
        DESCRIPTION
                  "Operate status on BSU board. The value is -1 when BSU board is
                  disconnected."
        ::= { ax6700sBsuBoardEntry 4 }

    ax6700sBsuBoardName OBJECT-TYPE
        SYNTAX    DisplayString (SIZE (0..16))
        ACCESS    read-only
        STATUS    mandatory
        DESCRIPTION
                  "BSU board name. When BSU board is disconnected, this will be an OCTET
                  STRING of zero length."
        ::= { ax6700sBsuBoardEntry 5 }

    ax6700sBsuBoardAbbreviation OBJECT-TYPE
        SYNTAX    DisplayString (SIZE (0..16))
        ACCESS    read-only
        STATUS    mandatory
        DESCRIPTION
                  "The abbreviation name of BSU board. When BSU board is disconnected,
                  this will be an OCTET STRING of zero length."
        ::= { ax6700sBsuBoardEntry 6 }

    ax6700sBsuSerialNumber OBJECT-TYPE
        SYNTAX    DisplayString (SIZE (0..30))
        ACCESS    read-only
        STATUS    mandatory
        DESCRIPTION
                  "The character string of the card management information of BSU package whose number is a maximum of 30. 
                  Its length is zero if not implemented or closed."
        ::= { ax6700sBsuBoardEntry 7 }

    ax6700sForwardingEngineNumber OBJECT-TYPE
        SYNTAX    INTEGER
        ACCESS    read-only
        STATUS    mandatory
        DESCRIPTION
                  "The forwarding engine number embedded in BSU." 
        ::= { ax6700sBsuBoardEntry 8 }

    ax6700sBsuBoardTemperatureStatusValue OBJECT-TYPE
        SYNTAX    Integer32
        ACCESS    read-only
        STATUS    mandatory
        DESCRIPTION
                  "The current measurement of the testpoint being instrumented on BSU board.
                  The value is -2147483648 when BSU board is disconnected."
        ::= { ax6700sBsuBoardEntry 9 }

    ax6700sNifBoardTable OBJECT-TYPE
        SYNTAX    SEQUENCE OF Ax6700sNifBoardTableEntry
        ACCESS    not-accessible
        STATUS    mandatory
        DESCRIPTION
                  "A table containing Network Interface cards (NIF) information that
                  slot is loaded."
        ::= { ax6700sNifBoard 1 }

    ax6700sNifBoardEntry OBJECT-TYPE
        SYNTAX    Ax6700sNifBoardTableEntry
        ACCESS    not-accessible
        STATUS    mandatory
        DESCRIPTION
                  "An entry containing NIF information about specific chassis."
        INDEX     { ax6700sChassisIndex,
                    ax6700sNifBoardSlotIndex }
        ::= { ax6700sNifBoardTable 1 }

    Ax6700sNifBoardTableEntry ::= SEQUENCE {
        ax6700sNifBoardSlotIndex       INTEGER,
        ax6700sNifBoardType            INTEGER,
        ax6700sNifBoardOperStatus      INTEGER,
        ax6700sNifBoardName            DisplayString,
        ax6700sNifBoardAbbreviation    DisplayString,
        ax6700sNifPhysLineNumber       INTEGER,
        ax6700sNifSerialNumber         DisplayString,
        ax6700sNifBoardOperModeStatus  INTEGER,
        ax6700sNifBoardTemperatureStatusValue   Integer32
    }

    ax6700sNifBoardSlotIndex OBJECT-TYPE
        SYNTAX    INTEGER
        ACCESS    not-accessible
        STATUS    mandatory
        DESCRIPTION
                  "Position information of NIF loading slot. The value is from 1
                  to ax6700sNifBoardNumber."
        ::= { ax6700sNifBoardEntry 1 }

    ax6700sNifBoardType OBJECT-TYPE
        SYNTAX    INTEGER {
                      disconnected(-1),
                      nif-24-port-10BASE-T-100BASE-TX-1000BASE-T(7),
                      nif-24-port-1000BASE-X-SFP(8),
                      nif-4-port-10GBASE-R-XFP(9),
                      nif-8-port-10GBASE-R-XFP(10),
                      nif-4-port-SHAPER-or-SFP-SHAPER-plus-4-port-SFP-SHAPER(15),
                      nif-4-port-SHAPER-or-SFP-SHAPER-plus-4-port-SFP-SHAPER-A(18),
                      nif-2-port-10GBASE-R-SFPP-plus-1-port-10GBASE-R-SP(20),
                      nif-2-port-10GBASE-R-SFPP-plus-1-port-10GBASE-R-SP-A(21),
                      nif-2-port-10GBASE-R-SFPP-plus-1-port-10GBASE-R-SP-8GB(22),
                      nif-2-port-10GBASE-R-SP(23),
                      nif-2-port-10GBASE-R-SP-05(24),
                      nif-2-port-10GBASE-R-SP-05A(25),
                      nif-2-port-10GBASE-R-SP-05Z(26),
                      nif-2-port-10GBASE-R-SP-05B(27),
                      nif-4-port-10GBASE-R-XFP-A(30),
                      nif-8-port-10GBASE-R-XFP-A(31)
                  }
        ACCESS    read-only
        STATUS    mandatory
        DESCRIPTION
                  "Type of connecting package.The value is register value of NIF package.
                  The value is -1 when the NIF is disconnected."
        ::= { ax6700sNifBoardEntry 2 }

    ax6700sNifBoardOperStatus OBJECT-TYPE
        SYNTAX    INTEGER {
                      other(1),
                      active(2),
                      initialization(3),
                      down(4),
                      closed(5),
                      lock(6),
                      disconnect(32)
                  }
        ACCESS    read-only
        STATUS    mandatory
        DESCRIPTION
                  "Operation status of NIF board.(STATUS LED)"
        ::= { ax6700sNifBoardEntry 3 }

    ax6700sNifBoardName OBJECT-TYPE
        SYNTAX    DisplayString (SIZE (0..16))
        ACCESS    read-only
        STATUS    mandatory
        DESCRIPTION
                  "NIF board name. When NIF board is disconnected 
                  this will be an DisplayString of zero length."
        ::= { ax6700sNifBoardEntry 4 }

    ax6700sNifBoardAbbreviation OBJECT-TYPE
        SYNTAX    DisplayString (SIZE (0..16))
        ACCESS    read-only
        STATUS    mandatory
        DESCRIPTION
                  "The abbreviation name of NIF board. When NIF board is disconnected
                  this will be an OCTET STRING of zero length."
        ::= { ax6700sNifBoardEntry 5 }

    ax6700sNifPhysLineNumber OBJECT-TYPE
        SYNTAX    INTEGER
        ACCESS    read-only
        STATUS    mandatory
        DESCRIPTION
                  "Number of NIF's physical port.The max is 48.
                  The value is -1 when value of ax6700sNifBoardType is -1 or other(1)."
        ::= { ax6700sNifBoardEntry 7 }

    ax6700sNifSerialNumber OBJECT-TYPE
        SYNTAX    DisplayString (SIZE (0..30))
        ACCESS    read-only
        STATUS    mandatory
        DESCRIPTION
                  "Management information (SerialNumber) of NIF package.
                  When NIF board is disconnected
                  this will be an OCTET STRING of zero length."
        ::= { ax6700sNifBoardEntry 8 }

    ax6700sNifBoardOperModeStatus OBJECT-TYPE
        SYNTAX    INTEGER {
                      disconnect(-1),
                      other(1),
                      active(2),
                      initialization(3),
                      down(4),
                      closed(5),
                      lock(6),
                      standby(7)
                  }
        ACCESS    read-only
        STATUS    mandatory
        DESCRIPTION
                  "Operate status on NIF board. The value is -1 when NIF board is disconnected."
        ::= { ax6700sNifBoardEntry 9 }

    ax6700sNifBoardTemperatureStatusValue OBJECT-TYPE
        SYNTAX    Integer32
        ACCESS    read-only
        STATUS    mandatory
        DESCRIPTION
                  "The current measurement of the testpoint being instrumented on NIF board.
                  The value is -2147483648 when the NIF is disconnected."
        ::= { ax6700sNifBoardEntry 10 }

    ax6700sPhysLineTable OBJECT-TYPE
        SYNTAX    SEQUENCE OF Ax6700sPhysLineTableEntry
        ACCESS    not-accessible
        STATUS    mandatory
        DESCRIPTION
                  "An table containing physical port."
        ::= { ax6700sPhysLine 1 }
            
    ax6700sPhysLineEntry OBJECT-TYPE
        SYNTAX    Ax6700sPhysLineTableEntry
        ACCESS    not-accessible
        STATUS    mandatory
        DESCRIPTION
                  "An entry containing physical port."
        INDEX     { ax6700sChassisIndex,
                    ax6700sNifBoardSlotIndex,
                    ax6700sPhysLineIndex }
        ::= { ax6700sPhysLineTable 1 }

    Ax6700sPhysLineTableEntry ::= SEQUENCE {
        ax6700sPhysLineIndex                INTEGER,
        ax6700sPhysLineConnectorType        INTEGER,
        ax6700sPhysLineOperStatus           INTEGER,
        ax6700sPhysLineIfIndexNumber        INTEGER,
        ax6700sPhysLineTransceiverStatus    INTEGER
    }

    ax6700sPhysLineIndex OBJECT-TYPE
        SYNTAX    INTEGER
        ACCESS    not-accessible
        STATUS    mandatory
        DESCRIPTION
                  "Physical port number. The value is from 1 to ax6700sNifLineNumber."
        ::= { ax6700sPhysLineEntry 1 }

    ax6700sPhysLineConnectorType OBJECT-TYPE
        SYNTAX    INTEGER {
                      other(1),
                      type1000BASE-LX(301),
                      type1000BASE-SX(302),
                      type1000BASE-LH(303),
                      type1000BASE-BX10-D(304),
                      type1000BASE-BX10-U(305),
                      type1000BASE-BX40-D(306),
                      type1000BASE-BX40-U(307),
                      type1000BASE-SX2(308),
                      type1000BASE-UTP(309),
                      type1000BASE-LHB(310),
                      type10GBASE-SR(401),
                      type10GBASE-LR(402),
                      type10GBASE-ER(403),
                      type10GBASE-ZR(404)
                  }
        ACCESS    read-only
        STATUS    mandatory
        DESCRIPTION
                  "Connector type is connected physical port. The value is 1(other)
                  when connector is disconnected or connector type is unknown."
        ::= { ax6700sPhysLineEntry 2 }

    ax6700sPhysLineOperStatus OBJECT-TYPE
        SYNTAX    INTEGER {
                      other(1),
                      active(2),
                      initialization(3),
                      down(4),
                      lock(6),
                      close(7),
                      line-fault(8),
                      test(9)
                  }
        ACCESS    read-only
        STATUS    mandatory
        DESCRIPTION
                  "Status of physical port. The value is -1 when PSU or NIF board is
                  disconnected."
        ::= { ax6700sPhysLineEntry 3 }

    ax6700sPhysLineIfIndexNumber OBJECT-TYPE
        SYNTAX    INTEGER
        ACCESS    read-only
        STATUS    mandatory
        DESCRIPTION
                  "Number of ifIndex which is included in physical port.The value is -1
                  when PSU board or NIF board is disconnected."
        ::= { ax6700sPhysLineEntry 4 }

    ax6700sPhysLineTransceiverStatus OBJECT-TYPE
        SYNTAX    INTEGER{
                      unchangeable-transceiver(1),
                      sfp-mounted(20),
                      sfp-unmounted(21),
                      unsupported-sfp-mounted(22),
                      sfp-fault(24),
                      xfp-mounted(30),
                      xfp-unmounted(31),
                      unsupported-xfp-mounted(32),
                      xfp-fault(34),
                      sfpp-mounted(40),
                      sfpp-unmounted(41),
                      unsupported-sfpp-mounted(42),
                      sfpp-fault(44)
                  }
        ACCESS    read-only
        STATUS    mandatory
        DESCRIPTION
                  "Type and status of replaceable transceiver."
        ::= { ax6700sPhysLineEntry 5 }

    ax6700sLineIfTable OBJECT-TYPE
        SYNTAX    SEQUENCE OF Ax6700sLineIfTableEntry
        ACCESS    not-accessible
        STATUS    mandatory
        DESCRIPTION
                  "A table containing physical port correspond to ifIndex."
        ::= { ax6700sInterface 1 }

    ax6700sLineIfEntry OBJECT-TYPE
        SYNTAX    Ax6700sLineIfTableEntry
        ACCESS    not-accessible
        STATUS    mandatory
        DESCRIPTION
                  "An entry containing ifIndex is assigned to physical port."
        INDEX     { ax6700sChassisIndex,
                    ax6700sNifBoardSlotIndex,
                    ax6700sPhysLineIndex,
                    ax6700sLineIfIndex }
        ::= { ax6700sLineIfTable 1 }

    Ax6700sLineIfTableEntry ::= SEQUENCE {
        ax6700sLineIfIndex    INTEGER,
        ax6700sIfIndex        INTEGER
    }

    ax6700sLineIfIndex OBJECT-TYPE
        SYNTAX    INTEGER
        ACCESS    not-accessible
        STATUS    mandatory
        DESCRIPTION
                  "The value of ifIndex to distinguish entry of this table.The value is
                  from 1 to ax6700sPhysLineIfIndexNumber."
        ::= { ax6700sLineIfEntry 1 }

    ax6700sIfIndex OBJECT-TYPE
        SYNTAX    INTEGER
        ACCESS    read-only
        STATUS    mandatory
        DESCRIPTION
                  "The value of ifIndex which is assigned to this physical port.
                  The value is 0 when ifIndex is not assigned to this physical port."
        ::= { ax6700sLineIfEntry 2 }

    ax6700sForwardingEngineTable OBJECT-TYPE
        SYNTAX    SEQUENCE OF Ax6700sForwardingEngineEntry
        ACCESS    not-accessible
        STATUS    mandatory
        DESCRIPTION
                  "A table containing forwarding engine embedded in BSU."
        ::= { ax6700sForwardingEngine 1 }

    ax6700sForwardingEngineEntry OBJECT-TYPE
        SYNTAX    Ax6700sForwardingEngineEntry
        ACCESS    not-accessible
        STATUS    mandatory
        DESCRIPTION
                  "An entry containing forwarding engine of the chassis."
        INDEX     { ax6700sChassisIndex,
                    ax6700sBsuBoardIndex,
                    ax6700sForwardingEngineIndex }
        ::= { ax6700sForwardingEngineTable 1 }

    Ax6700sForwardingEngineEntry ::= SEQUENCE {
        ax6700sForwardingEngineIndex    INTEGER
    }

    ax6700sForwardingEngineIndex OBJECT-TYPE
        SYNTAX    INTEGER
        ACCESS    not-accessible
        STATUS    mandatory
        DESCRIPTION
                  "Forwarding engine number. The value is from 1 to ax6700sForwardingEngineNumber."
        ::= { ax6700sForwardingEngineEntry 1 }

--
-- ax6700sFdbClearMIB      OBJECT IDENTIFIER ::= { ax6700sOperationCommand 1 }
--

    ax6700sFdbClearSet OBJECT-TYPE
        SYNTAX    INTEGER {
                      initialValue(0),
                      processing(1),
                      failure(2),
                      success(3)
                  }
        ACCESS    read-write
        STATUS    mandatory
        DESCRIPTION
                  "Fdb clear information. When want to clear fdb, 
                  then set value of this MIB as 1."
        ::= { ax6700sFdbClearMIB 1 }

    ax6700sFdbClearReqTime OBJECT-TYPE
        SYNTAX    TimeTicks
        ACCESS    read-only
        STATUS    mandatory
        DESCRIPTION
                  "This object indicates the most recent time that
                  received the demand to clear Fdb information.(sysUpTime)"
        ::= { ax6700sFdbClearMIB 2 }

    ax6700sFdbClearSuccessTime OBJECT-TYPE
        SYNTAX    TimeTicks
        ACCESS    read-only
        STATUS    mandatory
        DESCRIPTION
                  "This object indicates the time of the most recent
                  Fdb clearing success.(sysUpTime)"
        ::= { ax6700sFdbClearMIB 3 }

-- ax6600sSwitch group

    ax6600sModelType OBJECT-TYPE
        SYNTAX    INTEGER {
                      other(1),
                      model-AX6604S(1100),
                      model-AX6608S(1101),
                      model-AXEA02S(1102),
                      model-AX6602S(1103)
                  }
        ACCESS    read-only
        STATUS    mandatory
        DESCRIPTION
                  "Model type of this system."
        ::= { ax6600sSwitch 1 }

--    ax6600sSoftware OBJECT-TYPE
--        SYNTAX    INTEGER
--        ACCESS    not-accessible
--        STATUS    mandatory
--        DESCRIPTION
--                  "Software information of this system."
--        ::= { ax6600sSwitch 2 }

    ax6600sSoftwareName OBJECT-TYPE
        SYNTAX    DisplayString (SIZE (0..16))
        ACCESS    read-only
        STATUS    mandatory
        DESCRIPTION
                  "Software name of this system."
        ::= { ax6600sSoftware 1 }

    ax6600sSoftwareAbbreviation OBJECT-TYPE
        SYNTAX    DisplayString (SIZE (0..16))
        ACCESS    read-only
        STATUS    mandatory
        DESCRIPTION
                  "System software abbreviation."
        ::= { ax6600sSoftware 2 }

    ax6600sSoftwareVersion OBJECT-TYPE
        SYNTAX    DisplayString (SIZE (0..16))
        ACCESS    read-only
        STATUS    mandatory
        DESCRIPTION
                  "System software version."
        ::= { ax6600sSoftware 3 }

    ax6600sSystemMsgText OBJECT-TYPE
        SYNTAX    DisplayString (SIZE (0..256))
        ACCESS    read-only
        STATUS    mandatory
        DESCRIPTION
                  "The text of the system log message.For information about this code,
                  see:  Operator's Manual."
        ::= { ax6600sSystemMsg 1 }

    ax6600sSystemMsgType OBJECT-TYPE
        SYNTAX    OCTET STRING (SIZE (1))
        ACCESS    read-only
        STATUS    mandatory
        DESCRIPTION
                  "The event type. For information about this code, see:  Operator's Manual."
        ::= { ax6600sSystemMsg 2 }

    ax6600sSystemMsgTimeStamp OBJECT-TYPE
        SYNTAX    DisplayString (SIZE (0..14))
        ACCESS    read-only
        STATUS    mandatory
        DESCRIPTION
                  "The time that event occured. And that is expressed as type of
                  MM/DD hh:mm:ss
                      MM:month(01-12)
                      DD:day(01-31)
                      hh:hour(00-23)
                      mm:minute(00-59)
                      ss:second(00-59)
                  Insert space between DD and hh."
        ::= { ax6600sSystemMsg 3 }

    ax6600sSystemMsgLevel OBJECT-TYPE
        SYNTAX    OCTET STRING (SIZE (1))
        ACCESS    read-only
        STATUS    mandatory
        DESCRIPTION
                  "The newest system message log level.For information about this code,
                  see:  Operator's Manual."
        ::= { ax6600sSystemMsg 4 }

    ax6600sSystemMsgEventPoint OBJECT-TYPE
        SYNTAX    DisplayString (SIZE (0..8))
        ACCESS    read-only
        STATUS    mandatory
        DESCRIPTION
                  "The code of part that system message error occured. For information
                  about this code,see:  Operator's Manual."
        ::= { ax6600sSystemMsg 5 }

    ax6600sSystemMsgEventInterfaceID OBJECT-TYPE
        SYNTAX    DisplayString (SIZE (0..40))
        ACCESS    read-only
        STATUS    mandatory
        DESCRIPTION
                  "Interface identification of system messages. For information
                  about this code,see:  Operator's Manual."
        ::= { ax6600sSystemMsg 6 }

    ax6600sSystemMsgEventCode OBJECT-TYPE
        SYNTAX    OCTET STRING (SIZE (4))
        ACCESS    read-only
        STATUS    mandatory
        DESCRIPTION
                  "Event kind code of system messages. For information about this code,
                  see:  Operator's Manual."
        ::= { ax6600sSystemMsg 7 }

    ax6600sSystemMsgAdditionalCode OBJECT-TYPE
        SYNTAX    OCTET STRING (SIZE (6))
        ACCESS    read-only
        STATUS    mandatory
        DESCRIPTION
                  "Additional code of system messages. For information about this code,
                  see:  Operator's Manual."
        ::= { ax6600sSystemMsg 8 }

    ax6600sSnmpSendReceiveSize OBJECT-TYPE
        SYNTAX    INTEGER
        ACCESS    read-only
        STATUS    mandatory
        DESCRIPTION
                  "SNMP packet data size in Manager-to-Agent communication. The value is
                  displayed in bytes."
        ::= { ax6600sSnmpAgent 1 }

    ax6600sSnmpReceiveDelay OBJECT-TYPE
        SYNTAX    INTEGER
        ACCESS    read-only
        STATUS    mandatory
        DESCRIPTION
                  "A recommendable interval to receive packets from Manager.The value is
                  displayed in milliseconds."
        ::= { ax6600sSnmpAgent 2 }

    ax6600sSnmpContinuousSend OBJECT-TYPE
        SYNTAX    INTEGER
        ACCESS    read-only
        STATUS    mandatory
        DESCRIPTION
                  "Number of times that is recommendable continuous transmission
                  packets."
        ::= { ax6600sSnmpAgent 3 }

    ax6600sSnmpObjectMaxNumber OBJECT-TYPE
        SYNTAX    INTEGER
        ACCESS    read-only
        STATUS    mandatory
        DESCRIPTION
                  "Max number of objects that contain SNMP packet."
        ::= { ax6600sSnmpAgent 4 }

    ax6600sLicenseNumber OBJECT-TYPE
        SYNTAX    INTEGER
        ACCESS    read-only
        STATUS    mandatory
        DESCRIPTION
                  "The number of the configured license serial numbers."
        ::= { ax6600sLicense 1 }

    ax6600sLicenseTable OBJECT-TYPE
        SYNTAX    SEQUENCE OF Ax6600sLicenseTableEntry
        ACCESS    not-accessible
        STATUS    mandatory
        DESCRIPTION
                  "The table containing the license information."
        ::= { ax6600sLicense 2 }

    ax6600sLicenseEntry OBJECT-TYPE
        SYNTAX    Ax6600sLicenseTableEntry
        ACCESS    not-accessible
        STATUS    mandatory
        DESCRIPTION
                  "The entry of license information."
        INDEX     { ax6600sLicenseIndex }
        ::= { ax6600sLicenseTable 1 }

    Ax6600sLicenseTableEntry ::= SEQUENCE {
        ax6600sLicenseIndex           INTEGER,
        ax6600sLicenseSerialNumber    DisplayString,
        ax6600sLicenseOptionNumber    INTEGER
    }

    ax6600sLicenseIndex OBJECT-TYPE
        SYNTAX    INTEGER
        ACCESS    not-accessible
        STATUS    mandatory
        DESCRIPTION
                  "The unique index number given for each serial number. The number is from 1 to ax6600sLicenseNumber."
        ::= { ax6600sLicenseEntry 1 }

    ax6600sLicenseSerialNumber OBJECT-TYPE
        SYNTAX    DisplayString 
        ACCESS    read-only
        STATUS    mandatory
        DESCRIPTION
                  "The serial number."
        ::= { ax6600sLicenseEntry 2 }

    ax6600sLicenseOptionNumber OBJECT-TYPE
        SYNTAX    INTEGER 
        ACCESS    read-only
        STATUS    mandatory
        DESCRIPTION
                  "The number of option licenses associated with the serial number."
        ::= { ax6600sLicenseEntry 3 }

    ax6600sLicenseOptionTable OBJECT-TYPE
        SYNTAX    SEQUENCE OF Ax6600sLicenseOptionTableEntry
        ACCESS    not-accessible
        STATUS    mandatory
        DESCRIPTION
                  "The table containing option licenses information associated with the serial number."
        ::= { ax6600sLicense 3 }

    ax6600sLicenseOptionEntry OBJECT-TYPE
        SYNTAX    Ax6600sLicenseOptionTableEntry
        ACCESS    not-accessible
        STATUS    mandatory
        DESCRIPTION
                  "The entry of the option license information associated with the serial number."
        INDEX     { ax6600sLicenseOptionIndex,
                    ax6600sLicenseOptionNumberIndex }
        ::= { ax6600sLicenseOptionTable 1 }

    Ax6600sLicenseOptionTableEntry ::= SEQUENCE {
        ax6600sLicenseOptionIndex                   INTEGER,
        ax6600sLicenseOptionNumberIndex             INTEGER,
        ax6600sLicenseOptionSoftwareName            DisplayString,
        ax6600sLicenseOptionSoftwareAbbreviation    DisplayString
    }

    ax6600sLicenseOptionIndex OBJECT-TYPE
        SYNTAX    INTEGER
        ACCESS    not-accessible
        STATUS    mandatory
        DESCRIPTION
                  "The unique index number given for each serial number. The same number as ax6600sLicenseIndex."
        ::= { ax6600sLicenseOptionEntry 1 }

    ax6600sLicenseOptionNumberIndex OBJECT-TYPE
        SYNTAX    INTEGER
        ACCESS    not-accessible
        STATUS    mandatory
        DESCRIPTION
                  "The unique index number of option licenses information which is given for each serial number. The number is from 1 to ax6600sLicenseNumber."
        ::= { ax6600sLicenseOptionEntry 2 }

    ax6600sLicenseOptionSoftwareName OBJECT-TYPE
        SYNTAX    DisplayString 
        ACCESS    read-only
        STATUS    mandatory
        DESCRIPTION
                  "The software model name of the option license information associated with the serial number."
        ::= { ax6600sLicenseOptionEntry 3 }

    ax6600sLicenseOptionSoftwareAbbreviation OBJECT-TYPE
        SYNTAX    DisplayString 
        ACCESS    read-only
        STATUS    mandatory
        DESCRIPTION
                  "The software abbreviated name of the option license information associated with the serial number. "
        ::= { ax6600sLicenseOptionEntry 4 }

-- ax6600sDevice group

    ax6600sChassisMaxNumber OBJECT-TYPE
        SYNTAX    INTEGER
        ACCESS    read-only
        STATUS    mandatory
        DESCRIPTION
                  "Max number of cluster chassis that can connect to this router."
        ::= { ax6600sChassis 1 }

    ax6600sChassisTable OBJECT-TYPE
        SYNTAX    SEQUENCE OF Ax6600sChassisTableEntry
        ACCESS    not-accessible
        STATUS    mandatory
        DESCRIPTION
                  "A table containing chassis information."
        ::= { ax6600sChassis 2 }

    ax6600sChassisEntry OBJECT-TYPE
        SYNTAX    Ax6600sChassisTableEntry
        ACCESS    not-accessible
        STATUS    mandatory
        DESCRIPTION
                  "An entry containing specific chassis."
        INDEX     { ax6600sChassisIndex }
        ::= { ax6600sChassisTable 1 }

    Ax6600sChassisTableEntry ::= SEQUENCE {
        ax6600sChassisIndex          INTEGER,
        ax6600sChassisType           INTEGER,
        ax6600sChassisStatus         INTEGER,
        ax6600sPowerUnitNumber       INTEGER,
        ax6600sFanNumber             INTEGER,
        ax6600sCsuBoardDuplexMode    INTEGER,
        ax6600sCsuBoardNumber        INTEGER,
        ax6600sNifBoardNumber        INTEGER,
        ax6600sPowerControl          INTEGER,
        ax6600sPspDuplexActiveMode   INTEGER,
        ax6600sPspDuplexStandbyMode  INTEGER
    }

    ax6600sChassisIndex OBJECT-TYPE
        SYNTAX    INTEGER
        ACCESS    not-accessible
        STATUS    mandatory
        DESCRIPTION
                  "A number to specify ax6600sChassisEntry."
        ::= { ax6600sChassisEntry 1 }

    ax6600sChassisType OBJECT-TYPE
        SYNTAX    INTEGER {
                      other(1),
                      model-AX6604S(1100),
                      model-AX6608S(1101),
                      model-AXEA02S(1102),
                      model-AX6602S(1103)
                  }
        ACCESS    read-only
        STATUS    mandatory
        DESCRIPTION
                  "Chassis type of this system."
        ::= { ax6600sChassisEntry 2 }

    ax6600sChassisStatus OBJECT-TYPE
        SYNTAX    INTEGER {
                      up(2)
                  }
        ACCESS    read-only
        STATUS    mandatory
        DESCRIPTION
                  "Current status of this chassis."
        ::= { ax6600sChassisEntry 3 }

    ax6600sPowerUnitNumber OBJECT-TYPE
        SYNTAX    INTEGER
        ACCESS    read-only
        STATUS    mandatory
        DESCRIPTION
                  "Number of maximum power switches that this router can connect its."
        ::= { ax6600sChassisEntry 21 }

    ax6600sFanNumber OBJECT-TYPE
        SYNTAX    INTEGER
        ACCESS    read-only
        STATUS    mandatory
        DESCRIPTION
                  "The maximum number of fans that can connect to this chassis."
        ::= { ax6600sChassisEntry 23 }

    ax6600sCsuBoardDuplexMode OBJECT-TYPE
        SYNTAX    INTEGER{
                      simplex-mode(1),
                      duplex-mode(2)
                  }
        ACCESS    read-only
        STATUS    mandatory
        DESCRIPTION
                  "The CSU duplex mode."
        ::= { ax6600sChassisEntry 26 }

    ax6600sCsuBoardNumber OBJECT-TYPE
        SYNTAX    INTEGER
        ACCESS    read-only
        STATUS    mandatory
        DESCRIPTION
                  "The maximum number of CSU that can connect to this chassis."
        ::= { ax6600sChassisEntry 27 }

    ax6600sNifBoardNumber OBJECT-TYPE
        SYNTAX    INTEGER
        ACCESS    read-only
        STATUS    mandatory
        DESCRIPTION
                  "The maximum number of NIF that can connect to this chassis."
        ::= { ax6600sChassisEntry 28 }

    ax6600sPowerControl OBJECT-TYPE
        SYNTAX    INTEGER{
                      normal-mode(1),
                      power-save-mode(2),
                      power-save-mode2(3),
                      change-mode(10)
                  }
        ACCESS    read-only
        STATUS    mandatory
        DESCRIPTION
                  "The power mode of this chassis."
        ::= { ax6600sChassisEntry 29 }

    ax6600sPspDuplexActiveMode OBJECT-TYPE
        SYNTAX    INTEGER
        ACCESS    read-only
        STATUS    mandatory
        DESCRIPTION
                  "Number of active Psp of this system."
        ::= { ax6600sChassisEntry 30 }

    ax6600sPspDuplexStandbyMode OBJECT-TYPE
        SYNTAX    INTEGER
        ACCESS    read-only
        STATUS    mandatory
        DESCRIPTION
                  "Number of standby Psp of this system."
        ::= { ax6600sChassisEntry 31 }

    ax6600sPowerUnitTable OBJECT-TYPE
        SYNTAX    SEQUENCE OF Ax6600sPowerUnitTableEntry
        ACCESS    not-accessible
        STATUS    mandatory
        DESCRIPTION
                  "A table containing power unit information."
        ::= { ax6600sChassis 3 }

    ax6600sPowerUnitEntry OBJECT-TYPE
        SYNTAX    Ax6600sPowerUnitTableEntry
        ACCESS    not-accessible
        STATUS    mandatory
        DESCRIPTION
                  "An entry containing power unit information."
        INDEX     { ax6600sChassisIndex,
                    ax6600sPowerUnitIndex }
        ::= { ax6600sPowerUnitTable 1 }

    Ax6600sPowerUnitTableEntry ::= SEQUENCE {
        ax6600sPowerUnitIndex        INTEGER,
        ax6600sPowerConnectStatus    INTEGER,
        ax6600sPowerSupplyStatus     INTEGER
    }

    ax6600sPowerUnitIndex OBJECT-TYPE
        SYNTAX    INTEGER
        ACCESS    not-accessible
        STATUS    mandatory
        DESCRIPTION
                  "A number to position of the power units.The value from 1
                  to ax6600sPowerUnitNumber."
        ::= { ax6600sPowerUnitEntry 1 }
            
    ax6600sPowerConnectStatus OBJECT-TYPE
        SYNTAX    INTEGER {
                    connected(2),
                    disconnected(32)
                  }
        ACCESS    read-only
        STATUS    mandatory
        DESCRIPTION
                  "The current connection status of the power unit."
        ::= { ax6600sPowerUnitEntry 2 }

    ax6600sPowerSupplyStatus OBJECT-TYPE
        SYNTAX    INTEGER {
                      ok(2),
                      fault(4),
                      disconnected(-1)
                  }
        ACCESS    read-only
        STATUS    mandatory
        DESCRIPTION
                  "Status of power supply."
        ::= { ax6600sPowerUnitEntry 3 }

    ax6600sFanTable OBJECT-TYPE
        SYNTAX    SEQUENCE OF Ax6600sFanTableEntry
        ACCESS    not-accessible
        STATUS    mandatory
        DESCRIPTION
                  "A table containing fan information."
        ::= { ax6600sChassis 4 }

    ax6600sFanEntry OBJECT-TYPE
        SYNTAX    Ax6600sFanTableEntry
        ACCESS    not-accessible
        STATUS    mandatory
        DESCRIPTION
                  "This entry containing information for a fan."
        INDEX     { ax6600sChassisIndex,
                    ax6600sFanIndex }
        ::= { ax6600sFanTable 1 }

    Ax6600sFanTableEntry ::= SEQUENCE {
        ax6600sFanIndex     INTEGER,
        ax6600sFanStatus    INTEGER
    }

    ax6600sFanIndex OBJECT-TYPE
        SYNTAX    INTEGER
        ACCESS    not-accessible
        STATUS    mandatory
        DESCRIPTION
                  "Index to indicate position of fans."
        ::= { ax6600sFanEntry 1 }

    ax6600sFanStatus OBJECT-TYPE
        SYNTAX    INTEGER {
                      ok(2),
                      high-speed(3),
                      fault(4)
                  }
        ACCESS    read-only
        STATUS    mandatory
        DESCRIPTION
                  "Status of fans."
        ::= { ax6600sFanEntry 2 }

    ax6600sCsuBoardTable OBJECT-TYPE
        SYNTAX    SEQUENCE OF Ax6600sCsuBoardEntry
        ACCESS    not-accessible
        STATUS    mandatory
        DESCRIPTION
                  "The CSU information table."
        ::= { ax6600sCsuBoard 1 }

    ax6600sCsuBoardEntry OBJECT-TYPE
        SYNTAX    Ax6600sCsuBoardEntry
        ACCESS    not-accessible
        STATUS    mandatory
        DESCRIPTION
                  "The CSU information entry."
        INDEX     { ax6600sChassisIndex,
                    ax6600sCsuBoardIndex }
        ::= {ax6600sCsuBoardTable 1 }

    Ax6600sCsuBoardEntry ::= SEQUENCE{
        ax6600sCsuBoardIndex                 INTEGER,
        ax6600sCsuOperStatus                 INTEGER,
        ax6600sCsuOperModeStatus             BITS,
        ax6600sCsuActiveLedStatus            INTEGER,
        ax6600sCsuSystem1LedStatus           INTEGER,
        ax6600sCsuSystem2LedStatus           INTEGER,
        ax6600sCsuMgmtPortStatus             INTEGER,
        ax6600sCsuBoardName                  DisplayString,
        ax6600sCsuBoardAbbreviation          DisplayString,
        ax6600sCsuCpuName                    DisplayString,
        ax6600sCsuCpuClock                   INTEGER,
        ax6600sCsuMemoryTotalSize            INTEGER,
        ax6600sCsuMemoryUsedSize             INTEGER,
        ax6600sCsuMemoryFreeSize             INTEGER,
        ax6600sCsuRomVersion                 DisplayString,
        ax6600sCsuCpuLoad1m                  INTEGER,
        ax6600sCsuFlashTotalSize             INTEGER,
        ax6600sCsuFlashUsedSize              INTEGER,
        ax6600sCsuFlashFreeSize              INTEGER,
        ax6600sCsuTemperatureStatusNumber    INTEGER,
        ax6600sCsuSerialNumber               DisplayString,
        ax6600sCsuTotalAccumRunTime          INTEGER,
        ax6600sCsuCriticalAccumRunTime       INTEGER,
        ax6600sPspOperModeStatus             INTEGER
    }

    ax6600sCsuBoardIndex OBJECT-TYPE
        SYNTAX    INTEGER 
        ACCESS    not-accessible
        STATUS    mandatory
        DESCRIPTION
                  "The index of CSU information table."
        ::= { ax6600sCsuBoardEntry 1 }

    ax6600sCsuOperStatus OBJECT-TYPE
        SYNTAX    INTEGER {
                      initialized(1),
                      active(2),
                      disabled(3),
                      down(4),
                      power-off(6)
                  }
        ACCESS    read-only
        STATUS    mandatory
        DESCRIPTION
                  "The state of CSU STATUS LED of the device."
        ::= { ax6600sCsuBoardEntry 2 }

    ax6600sCsuOperModeStatus OBJECT-TYPE
        SYNTAX    BITS {
                      disconnected(0),
                      initialized(1),
                      active(2),
                      standby(3),
                      do-not-match-with-configure-mode(4),
                      do-not-match-with-software-mode(5),
                      do-not-match-with-license-info(6),
                      down(7),
                      maintenance(8)
                  }
        ACCESS    read-only
        STATUS    mandatory
        DESCRIPTION
                  "The state of operation status of the device."
        ::= { ax6600sCsuBoardEntry 3 }

    ax6600sCsuActiveLedStatus OBJECT-TYPE
        SYNTAX    INTEGER {
                      disconnected(-1),
                      green(2),
                      extinction(6)
                  }
        ACCESS    read-only
        STATUS    mandatory
        DESCRIPTION
                  "The state of ACTIVE LED status of the device."
        ::= { ax6600sCsuBoardEntry 4 }
        
    ax6600sCsuSystem1LedStatus OBJECT-TYPE
        SYNTAX    INTEGER {
                      disconnected(-1),
                      green(2),
                      orange(3),
                      red(4),
                      extinction(6)
                  }
        ACCESS    read-only
        STATUS    mandatory
        DESCRIPTION
                  "The state of SYSTEM LED status of the device."
        ::= { ax6600sCsuBoardEntry 5 }

    ax6600sCsuSystem2LedStatus OBJECT-TYPE
        SYNTAX    INTEGER {
                      disconnected(-1),
                      green-blink(1),
                      green(2),
                      extinction(6)
                  }
        ACCESS    read-only
        STATUS    mandatory
        DESCRIPTION
                  "The state of SYSTEM2 LED status of the device."
        ::= { ax6600sCsuBoardEntry 6 }

    ax6600sCsuMgmtPortStatus OBJECT-TYPE
        SYNTAX    INTEGER {
                      disconnected(-1),
                      other(1),
                      active(2),
                      down(4),
                      disabled(6),
                      maintenance(7),
                      line-test(9),
                      unused(10)
                  }
        ACCESS    read-only
        STATUS    mandatory
        DESCRIPTION
                  "The state of management-port status of the device."
        ::= { ax6600sCsuBoardEntry 7 }
        
    ax6600sCsuBoardName OBJECT-TYPE
        SYNTAX    DisplayString
        ACCESS    read-only
        STATUS    mandatory
        DESCRIPTION
                  "The product name of CSU Board. If CSU Board disconnected, return 0 length DisplayString."
        ::= { ax6600sCsuBoardEntry 8 }

    ax6600sCsuBoardAbbreviation OBJECT-TYPE
        SYNTAX    DisplayString
        ACCESS    read-only
        STATUS    mandatory
        DESCRIPTION
                  "The abbreviated name of CSU Board. If CSU Board disconnected, return 0 length DisplayString."
        ::= { ax6600sCsuBoardEntry 9 }
        
    ax6600sCsuCpuName OBJECT-TYPE
        SYNTAX    DisplayString
        ACCESS    read-only
        STATUS    mandatory
        DESCRIPTION
                  "The name of CPU on CSU board is shown by the character string of 16 characters or less.
                  If CSU Board disconnected, return 0 length DisplayString." 
        ::= { ax6600sCsuBoardEntry 10 }

    ax6600sCsuCpuClock OBJECT-TYPE
        SYNTAX    INTEGER
        ACCESS    read-only
        STATUS    mandatory
        DESCRIPTION
                  "CPU clock is shown by the numerical value.
                  If CSU Board disconnected, return -1."
        ::= { ax6600sCsuBoardEntry 11 }

    ax6600sCsuMemoryTotalSize OBJECT-TYPE
        SYNTAX    INTEGER
        ACCESS    read-only
        STATUS    mandatory
        DESCRIPTION
                  "The installing memory size is shown by the numerical value.
                  If CSU Board disconnected, return -1."
        ::= { ax6600sCsuBoardEntry 12 }

    ax6600sCsuMemoryUsedSize OBJECT-TYPE
        SYNTAX    INTEGER
        ACCESS    read-only
        STATUS    mandatory
        DESCRIPTION
                  "The use memory size is shown by the numerical value.
                  If CSU Board disconnected, return -1."
        ::= { ax6600sCsuBoardEntry 13 }

    ax6600sCsuMemoryFreeSize OBJECT-TYPE
        SYNTAX    INTEGER
        ACCESS    read-only
        STATUS    mandatory
        DESCRIPTION
                  "The unused memory size is shown by the numerical value.
                  If CSU Board disconnected, return -1."
        ::= { ax6600sCsuBoardEntry 14 }

    ax6600sCsuRomVersion OBJECT-TYPE
        SYNTAX    DisplayString
        ACCESS    read-only
        STATUS    mandatory
        DESCRIPTION
                  "The version of ROM equipped with BCU is shown by the character string.
                  If CSU Board disconnected, return 0 length DisplayString."
        ::= { ax6600sCsuBoardEntry 15 }

    ax6600sCsuCpuLoad1m OBJECT-TYPE
        SYNTAX    INTEGER
        ACCESS    read-only
        STATUS    mandatory
        DESCRIPTION
                  "CPU utilization of one minute is shown by the numerical value.
                  If CSU Board disconnected, return -1."
        ::= { ax6600sCsuBoardEntry 16 }

    ax6600sCsuFlashTotalSize OBJECT-TYPE
        SYNTAX    INTEGER
        ACCESS    read-only
        STATUS    mandatory
        DESCRIPTION
                  "The total of filesystem use capacity and unused capacity in a built-in memory 
                  is shown."
        ::= { ax6600sCsuBoardEntry 17 }

    ax6600sCsuFlashUsedSize OBJECT-TYPE
        SYNTAX    INTEGER
        ACCESS    read-only
        STATUS    mandatory
        DESCRIPTION
                  "The use capacity of the filesystem in a built-in memory is shown."
        ::= { ax6600sCsuBoardEntry 18 }

    ax6600sCsuFlashFreeSize OBJECT-TYPE
        SYNTAX    INTEGER
        ACCESS    read-only
        STATUS    mandatory
        DESCRIPTION
                  "The unused capacity of the filesystem in a built-in memory is shown. "
        ::= { ax6600sCsuBoardEntry 19 }

    ax6600sCsuTemperatureStatusNumber OBJECT-TYPE
        SYNTAX    INTEGER
        ACCESS    read-only
        STATUS    mandatory
        DESCRIPTION
                  "The maximum number of ax6600sTemperatureStatus in this chassis."
        ::= { ax6600sCsuBoardEntry 20 }

    ax6600sCsuSerialNumber OBJECT-TYPE
        SYNTAX    DisplayString
        ACCESS    read-only
        STATUS    mandatory
        DESCRIPTION
                  "The character string of the card management information of CSU package whose number is a maximum of 16. 
                  Its length is zero if not implemented or inactivated."
        ::= { ax6600sCsuBoardEntry 21 }

    ax6600sCsuTotalAccumRunTime OBJECT-TYPE
        SYNTAX    INTEGER
        ACCESS    read-only
        STATUS    mandatory
        DESCRIPTION
                  "Total operation time after operation of device begins."
        ::= { ax6600sCsuBoardEntry 22 }

    ax6600sCsuCriticalAccumRunTime OBJECT-TYPE
        SYNTAX    INTEGER
        ACCESS    read-only
        STATUS    mandatory
        DESCRIPTION
                  "Operating time under environment of 40 degrees C or more."
        ::= { ax6600sCsuBoardEntry 23 }

    ax6600sPspOperModeStatus OBJECT-TYPE
        SYNTAX    INTEGER {
                      disconnected(-1),
                      other(1),
                      active(2),
                      hot-standby(3),
                      cold-standby2(4),
                      down(5),
                      initialized(6)
                  }
        ACCESS    read-only
        STATUS    mandatory
        DESCRIPTION
                  "Operating time under environment of 40C or more."
        ::= { ax6600sCsuBoardEntry 24 }
            
    ax6600sTemperatureStatusTable OBJECT-TYPE
        SYNTAX    SEQUENCE OF Ax6600sTemperatureStatusEntry
        ACCESS    not-accessible
        STATUS    mandatory
        DESCRIPTION
                  "The table of ambient temperature status maintained by the
                  environmental monitor."
        ::= { ax6600sCsuBoard 2 }

    ax6600sTemperatureStatusEntry OBJECT-TYPE
        SYNTAX    Ax6600sTemperatureStatusEntry
        ACCESS    not-accessible
        STATUS    mandatory
        DESCRIPTION
                  "An entry in the ambient temperature status table, representing
                  the status of the associated testpoint maintained by the
                  environmental monitor."
        INDEX    { ax6600sChassisIndex,
                   ax6600sCsuBoardIndex,
                   ax6600sTemperatureStatusIndex }
        ::= { ax6600sTemperatureStatusTable 1 }

    Ax6600sTemperatureStatusEntry ::= SEQUENCE {
        ax6600sTemperatureStatusIndex    INTEGER,
        ax6600sTemperatureStatusDescr    DisplayString,
        ax6600sTemperatureStatusValue    Integer32,
        ax6600sTemperatureThreshold      Integer32,
        ax6600sTemperatureState          INTEGER
    }

    ax6600sTemperatureStatusIndex OBJECT-TYPE
        SYNTAX    INTEGER
        ACCESS    not-accessible
        STATUS    mandatory
        DESCRIPTION
                  "Unique index for the testpoint being instrumented.
                  This index is for SNMP purposes only, and has no
                  intrinsic meaning."
        ::= { ax6600sTemperatureStatusEntry 1 }

    ax6600sTemperatureStatusDescr OBJECT-TYPE
        SYNTAX    DisplayString(SIZE(0..32))
        ACCESS    read-only
        STATUS    mandatory
        DESCRIPTION
                  "Textual description of the testpoint being instrumented.
                  This description is a short textual label, suitable as a
                  human-sensible identification for the rest of the
                  information in the entry."
        ::= { ax6600sTemperatureStatusEntry 2 }

    ax6600sTemperatureStatusValue OBJECT-TYPE
        SYNTAX    Integer32
        ACCESS    read-only
        STATUS    mandatory
        DESCRIPTION
                  "The current measurement of the testpoint being instrumented."
        ::= { ax6600sTemperatureStatusEntry 3 }

    ax6600sTemperatureThreshold OBJECT-TYPE
        SYNTAX    Integer32
        ACCESS    read-only
        STATUS    mandatory
        DESCRIPTION
                  "The highest value that the associated instance of the
                  object ax6600sTemperatureStatusValue may obtain
                  before an emergency shutdown of the managed device is
                  initiated."
        ::= { ax6600sTemperatureStatusEntry 4 }

    ax6600sTemperatureState OBJECT-TYPE
        SYNTAX    INTEGER {
                      normal(1),
                      caution(2),
                      warning(3),
                      fatal(4)
                  }
        ACCESS    read-only
        STATUS    mandatory
        DESCRIPTION
                  "The current state of the testpoint being instrumented."
        ::= { ax6600sTemperatureStatusEntry 5 }
            
    ax6600sSdCardTable OBJECT-TYPE
        SYNTAX    SEQUENCE OF Ax6600sSdCardEntry
        ACCESS    not-accessible
        STATUS    mandatory
        DESCRIPTION
                  "An table containing Sd-card information."
        ::= { ax6600sCsuBoard 3 }
            
    ax6600sSdCardEntry OBJECT-TYPE
        SYNTAX    Ax6600sSdCardEntry
        ACCESS    not-accessible
        STATUS    mandatory
        DESCRIPTION
                  "An entry containing SOP information."
        INDEX     { ax6600sChassisIndex,
                    ax6600sCsuBoardIndex,
                    ax6600sSdCardIndex }
        ::= { ax6600sSdCardTable 1 }

    Ax6600sSdCardEntry ::= SEQUENCE {
        ax6600sSdCardIndex         INTEGER,
        ax6600sSdCardConnection    INTEGER,
        ax6600sSdCardTotalSize     INTEGER,
        ax6600sSdCardUsedSize      INTEGER,
        ax6600sSdCardFreeSize      INTEGER
    }

    ax6600sSdCardIndex OBJECT-TYPE
        SYNTAX    INTEGER 
        ACCESS    not-accessible
        STATUS    mandatory
        DESCRIPTION
                  "The SD card index number."
        ::= { ax6600sSdCardEntry  1 }

    ax6600sSdCardConnection OBJECT-TYPE
        SYNTAX    INTEGER {
                      connected(2),
                      disconnected(32)
                  }
        ACCESS    read-only
        STATUS    mandatory
        DESCRIPTION
                  "The SD card connection is shown."
        ::= { ax6600sSdCardEntry 2 }

    ax6600sSdCardTotalSize OBJECT-TYPE
        SYNTAX    INTEGER
        ACCESS    read-only
        STATUS    mandatory
        DESCRIPTION
                  "Total capacity of the SD card is shown by the numerical value. It responds by -1
                  at the MC card unconnection."
        ::= { ax6600sSdCardEntry 3 }

    ax6600sSdCardUsedSize OBJECT-TYPE
        SYNTAX    INTEGER
        ACCESS    read-only
        STATUS    mandatory
        DESCRIPTION
                  "The use capacity of the SD card is shown by the numerical value. It responds by -1
                  at the SD card unconnection. "
        ::= { ax6600sSdCardEntry 4 }

    ax6600sSdCardFreeSize OBJECT-TYPE
        SYNTAX    INTEGER
        ACCESS    read-only
        STATUS    mandatory
        DESCRIPTION
                  "Total capacity of the SD card is shown by the numerical value. It responds by -1
                  at the MC card unconnection."
        ::= { ax6600sSdCardEntry  5 }

           
    ax6600sSopTable OBJECT-TYPE
        SYNTAX    SEQUENCE OF Ax6600sSopEntry
        ACCESS    not-accessible
        STATUS    mandatory
        DESCRIPTION
                  "A table containing SOP information."
        ::= { ax6600sCsuBoard  4 }

    ax6600sSopEntry OBJECT-TYPE
        SYNTAX    Ax6600sSopEntry
        ACCESS    not-accessible
        STATUS    mandatory
        DESCRIPTION
                  "An entry containing SOP information."
        INDEX   { ax6600sChassisIndex,
                  ax6600sCsuBoardIndex }
        ::= { ax6600sSopTable 1 }

    Ax6600sSopEntry ::= SEQUENCE {
        ax6600sSopAlarmLevel               DisplayString,
        ax6600sSopAlarmEventPoint          DisplayString,
        ax6600sSopAlarmEventCode           DisplayString,
        ax6600sSopAlarmEventInterfaceID    DisplayString,
        ax6600sSopAlarmMsgText             DisplayString
    }

    ax6600sSopAlarmLevel OBJECT-TYPE
        SYNTAX    DisplayString
        ACCESS    read-only
        STATUS    mandatory
        DESCRIPTION
                  "Error level displayed on a SOP window. When the BCU does not
                  support SOP, this will be an OCTET STRING of zero length.
                  For information about this code, see:  Operator's Manual."
        ::= { ax6600sSopEntry 1 }

    ax6600sSopAlarmEventPoint OBJECT-TYPE
        SYNTAX    DisplayString
        ACCESS    read-only
        STATUS    mandatory
        DESCRIPTION
                  "The code displayed on a SOP window, which stands for a device
                  part of the factor of the alarm message. When the BCU does not
                  support SOP, this will be an OCTET STRING of zero length.
                  For information about this code, see:  Operator's Manual."
        ::= { ax6600sSopEntry 2 }

    ax6600sSopAlarmEventCode OBJECT-TYPE
        SYNTAX    DisplayString
        ACCESS    read-only
        STATUS    mandatory
        DESCRIPTION
                  "Event kind code of alarm message displayed on a SOP window.
                  When the BCU does not support SOP, this will be an OCTET STRING
                  of zero length. For information about this code, see:  Operator's
                  Manual."
        ::= { ax6600sSopEntry 3 }

    ax6600sSopAlarmEventInterfaceID OBJECT-TYPE
        SYNTAX    DisplayString
        ACCESS    read-only
        STATUS    mandatory
        DESCRIPTION
                  "Interface identification of alarm messages on a SOP window.
                  When the BCU does not support SOP, this will be an OCTET STRING
                  of zero length. For information about this code, see:  Operator's
                  Manual."
        ::= { ax6600sSopEntry 4 }

    ax6600sSopAlarmMsgText OBJECT-TYPE
        SYNTAX    DisplayString
        ACCESS    read-only
        STATUS    mandatory
        DESCRIPTION
                  "The text of the alarm message on a SOP window. When the BCU does
                  not support SOP, this will be an OCTET STRING of zero length.
                  For more information about this code, see:  Operator's Manual."
        ::= { ax6600sSopEntry 5 }

    ax6600sNifBoardTable OBJECT-TYPE
        SYNTAX    SEQUENCE OF Ax6600sNifBoardTableEntry
        ACCESS    not-accessible
        STATUS    mandatory
        DESCRIPTION
                  "A table containing Network Interface cards (NIF) information that
                  slot is loaded."
        ::= { ax6600sNifBoard 1 }

    ax6600sNifBoardEntry OBJECT-TYPE
        SYNTAX    Ax6600sNifBoardTableEntry
        ACCESS    not-accessible
        STATUS    mandatory
        DESCRIPTION
                  "An entry containing NIF information about specific chassis."
        INDEX   { ax6600sChassisIndex,
                  ax6600sNifBoardSlotIndex }
        ::= { ax6600sNifBoardTable 1 }

    Ax6600sNifBoardTableEntry ::= SEQUENCE {
        ax6600sNifBoardSlotIndex       INTEGER,
        ax6600sNifBoardType            INTEGER,
        ax6600sNifBoardOperStatus      INTEGER,
        ax6600sNifBoardName            DisplayString,
        ax6600sNifBoardAbbreviation    DisplayString,
        ax6600sNifPhysLineNumber       INTEGER,
        ax6600sNifSerialNumber         DisplayString,
        ax6600sNifBoardOperModeStatus  INTEGER,
        ax6600sNifBoardTemperatureStatusValue   Integer32
    }

    ax6600sNifBoardSlotIndex OBJECT-TYPE
        SYNTAX    INTEGER
        ACCESS    not-accessible
        STATUS    mandatory
        DESCRIPTION
                  "Position information of NIF loading slot. The value is from 1
                  to ax6600sNifBoardNumber."
        ::= { ax6600sNifBoardEntry 1 }

    ax6600sNifBoardType OBJECT-TYPE
        SYNTAX    INTEGER {
                      disconnected(-1),
                      nif-24-port-10BASE-T-100BASE-TX-1000BASE-T(7),
                      nif-24-port-1000BASE-X-SFP(8),
                      nif-4-port-10GBASE-R-XFP(9),
                      nif-8-port-10GBASE-R-XFP(10),
                      nif-4-port-SHAPER-or-SFP-SHAPER-plus-4-port-SFP-SHAPER(15),
                      nif-2-port-10GBASE-R-SFPP-plus-1-port-10GBASE-R-SP(20),
                      nif-2-port-10GBASE-R-SFPP-plus-1-port-10GBASE-R-SP-A(21),
                      nif-2-port-10GBASE-R-SFPP-plus-1-port-10GBASE-R-SP-8GB(22),
                      nif-2-port-10GBASE-R-SP(23),
                      nif-2-port-10GBASE-R-SP-05(24),
                      nif-2-port-10GBASE-R-SP-05A(25),
                      nif-2-port-10GBASE-R-SP-05Z(26),
                      nif-4-port-10GBASE-R-XFP-A(30),
                      nif-8-port-10GBASE-R-XFP-A(31)
                  }
        ACCESS    read-only
        STATUS    mandatory
        DESCRIPTION
                  "Type of connecting package.The value is register value of NIF package.
                  The value is -1 when the NIF is disconnected."
        ::= { ax6600sNifBoardEntry 2 }

    ax6600sNifBoardOperStatus OBJECT-TYPE
        SYNTAX    INTEGER {
                      other(1),
                      active(2),
                      initialization(3),
                      down(4),
                      closed(5),
                      lock(6),
                      disconnect(32)
                  }
        ACCESS    read-only
        STATUS    mandatory
        DESCRIPTION
                  "Operation status of NIF board.(STATUS LED)"
        ::= { ax6600sNifBoardEntry 3 }

    ax6600sNifBoardName OBJECT-TYPE
        SYNTAX    DisplayString (SIZE (0..16))
        ACCESS    read-only
        STATUS    mandatory
        DESCRIPTION
                  "NIF board name. When NIF board is disconnected
                  this will be an DisplayString of zero length."
        ::= { ax6600sNifBoardEntry 4 }

    ax6600sNifBoardAbbreviation OBJECT-TYPE
        SYNTAX    DisplayString (SIZE (0..16))
        ACCESS    read-only
        STATUS    mandatory
        DESCRIPTION
                  "The abbreviation name of NIF board. When NIF board is disconnected
                   this will be an OCTET STRING of zero length."
        ::= { ax6600sNifBoardEntry 5 }

    ax6600sNifPhysLineNumber OBJECT-TYPE
        SYNTAX    INTEGER
        ACCESS    read-only
        STATUS    mandatory
        DESCRIPTION
                  "Number of NIF's physical port.The max is 48.
                  The value is -1 when value of ax6600sNifBoardType is -1 or other(1)."
        ::= { ax6600sNifBoardEntry 7 }

    ax6600sNifSerialNumber OBJECT-TYPE
        SYNTAX    DisplayString (SIZE (0..30))
        ACCESS    read-only
        STATUS    mandatory
        DESCRIPTION
                  "Management information (SerialNumber) of NIF package.
                    When NIF board is disconnected
                   this will be an OCTET STRING of zero length."
        ::= { ax6600sNifBoardEntry 8 }

    ax6600sNifBoardOperModeStatus OBJECT-TYPE
        SYNTAX    INTEGER {
                      disconnect(-1),
                      other(1),
                      active(2),
                      initialization(3),
                      down(4),
                      closed(5),
                      lock(6),
                      standby(7)
                  }
        ACCESS    read-only
        STATUS    mandatory
        DESCRIPTION
                  "Operate status on NIF board. The value is -1 when NIF board is disconnected."
        ::= { ax6600sNifBoardEntry 9 }

    ax6600sNifBoardTemperatureStatusValue OBJECT-TYPE
        SYNTAX    Integer32
        ACCESS    read-only
        STATUS    mandatory
        DESCRIPTION
                  "The current measurement of the testpoint being instrumented on NIF board.
                  The value is -2147483648 when the NIF is disconnected."
        ::= { ax6600sNifBoardEntry 10 }

    ax6600sPhysLineTable OBJECT-TYPE
        SYNTAX    SEQUENCE OF Ax6600sPhysLineTableEntry
        ACCESS    not-accessible
        STATUS    mandatory
        DESCRIPTION
                  "An table containing physical port."
        ::= { ax6600sPhysLine 1 }

    ax6600sPhysLineEntry OBJECT-TYPE
        SYNTAX    Ax6600sPhysLineTableEntry
        ACCESS    not-accessible
        STATUS    mandatory
        DESCRIPTION
                  "An entry containing physical port."
        INDEX     { ax6600sChassisIndex,
                    ax6600sNifBoardSlotIndex,
                    ax6600sPhysLineIndex }
        ::= { ax6600sPhysLineTable 1 }

    Ax6600sPhysLineTableEntry ::= SEQUENCE {
        ax6600sPhysLineIndex                INTEGER,
        ax6600sPhysLineConnectorType        INTEGER,
        ax6600sPhysLineOperStatus           INTEGER,
        ax6600sPhysLineIfIndexNumber        INTEGER,
        ax6600sPhysLineTransceiverStatus    INTEGER
    }

    ax6600sPhysLineIndex OBJECT-TYPE
        SYNTAX    INTEGER
        ACCESS    not-accessible
        STATUS    mandatory
        DESCRIPTION
                  "Physical port number. The value is from 1 to ax6600sNifLineNumber."
        ::= { ax6600sPhysLineEntry 1 }

    ax6600sPhysLineConnectorType OBJECT-TYPE
        SYNTAX    INTEGER {
                      other(1),
                      type1000BASE-LX(301),
                      type1000BASE-SX(302),
                      type1000BASE-LH(303),
                      type1000BASE-BX10-D(304),
                      type1000BASE-BX10-U(305),
                      type1000BASE-BX40-D(306),
                      type1000BASE-BX40-U(307),
                      type1000BASE-SX2(308),
                      type1000BASE-UTP(309),
                      type1000BASE-LHB(310),
                      type10GBASE-SR(401),
                      type10GBASE-LR(402),
                      type10GBASE-ER(403),
                      type10GBASE-ZR(404)
                  }
        ACCESS    read-only
        STATUS    mandatory
        DESCRIPTION
                  "Connector type is connected physical port. The value is 1(other)
                  when connector is disconnected or connector type is unknown."
        ::= { ax6600sPhysLineEntry 2 }

    ax6600sPhysLineOperStatus OBJECT-TYPE
        SYNTAX    INTEGER {
                      other(1),
                      active(2),
                      initialization(3),
                      down(4),
                      lock(6),
                      close(7),
                      line-fault(8),
                      test(9)
                  }
        ACCESS    read-only
        STATUS    mandatory
        DESCRIPTION
                  "Status of physical port. The value is -1 when PSU or NIF board is
                  disconnected."
        ::= { ax6600sPhysLineEntry 3 }

    ax6600sPhysLineIfIndexNumber OBJECT-TYPE
        SYNTAX    INTEGER
        ACCESS    read-only
        STATUS    mandatory
        DESCRIPTION
                  "Number of ifIndex which is included in physical port.The value is -1
                  when PSU board or NIF board is disconnected."
        ::= { ax6600sPhysLineEntry 4 }

    ax6600sPhysLineTransceiverStatus OBJECT-TYPE
        SYNTAX    INTEGER{
                      unchangeable-transceiver(1),
                      sfp-mounted(20),
                      sfp-unmounted(21),
                      unsupported-sfp-mounted(22),
                      sfp-fault(24),
                      xfp-mounted(30),
                      xfp-unmounted(31),
                      unsupported-xfp-mounted(32),
                      xfp-fault(34),
                      sfpp-mounted(40),
                      sfpp-unmounted(41),
                      unsupported-sfpp-mounted(42),
                      sfpp-fault(44)
                  }
        ACCESS    read-only
        STATUS    mandatory
        DESCRIPTION
                  "Type and status of replaceable transceiver."
        ::= { ax6600sPhysLineEntry 5 }

    ax6600sLineIfTable OBJECT-TYPE
        SYNTAX    SEQUENCE OF Ax6600sLineIfTableEntry
        ACCESS    not-accessible
        STATUS    mandatory
        DESCRIPTION
                  "A table containing physical port correspond to ifIndex."
        ::= { ax6600sInterface 1 }

    ax6600sLineIfEntry OBJECT-TYPE
        SYNTAX    Ax6600sLineIfTableEntry
        ACCESS    not-accessible
        STATUS    mandatory
        DESCRIPTION
                  "An entry containing ifIndex is assigned to physical port."
        INDEX     { ax6600sChassisIndex,
                    ax6600sNifBoardSlotIndex,
                    ax6600sPhysLineIndex,
                    ax6600sLineIfIndex }
        ::= { ax6600sLineIfTable 1 }

    Ax6600sLineIfTableEntry ::= SEQUENCE {
        ax6600sLineIfIndex    INTEGER,
        ax6600sIfIndex        INTEGER
    }

    ax6600sLineIfIndex OBJECT-TYPE
        SYNTAX    INTEGER
        ACCESS    not-accessible
        STATUS    mandatory
        DESCRIPTION
                  "The value of ifIndex to distinguish entry of this table.The value is
                  from 1 to ax6600sPhysLineIfIndexNumber."
        ::= { ax6600sLineIfEntry 1 }

    ax6600sIfIndex OBJECT-TYPE
        SYNTAX    INTEGER
        ACCESS    read-only
        STATUS    mandatory
        DESCRIPTION
                  "The value of ifIndex which is assigned to this physical port.
                  The value is 0 when ifIndex is not assigned to this physical port."
        ::= { ax6600sLineIfEntry 2 }

--
-- ax6600sFdbClearMIB      OBJECT IDENTIFIER ::= { ax6600sOperationCommand 1 }
--

    ax6600sFdbClearSet OBJECT-TYPE
        SYNTAX    INTEGER {
                      initialValue(0),
                      processing(1),
                      failure(2),
                      success(3)
                  }
        ACCESS    read-write
        STATUS    mandatory
        DESCRIPTION
                  "Fdb clear information. When want to clear fdb, 
                  then set value of this MIB as 1."
        ::= { ax6600sFdbClearMIB 1 }

    ax6600sFdbClearReqTime OBJECT-TYPE
        SYNTAX    TimeTicks
        ACCESS    read-only
        STATUS    mandatory
        DESCRIPTION
                  "This object indicates the most recent time that
                  received the demand to clear Fdb information.(sysUpTime)"
        ::= { ax6600sFdbClearMIB 2 }

    ax6600sFdbClearSuccessTime OBJECT-TYPE
        SYNTAX    TimeTicks
        ACCESS    read-only
        STATUS    mandatory
        DESCRIPTION
                  "This object indicates the time of the most recent
                  Fdb clearing success.(sysUpTime)"
        ::= { ax6600sFdbClearMIB 3 }

-- Traps for use by AlaxalA networks AXS

-- Traps are defined using the conventions in RFC 1215.

    axsStaticGatewayStateChange TRAP-TYPE
        ENTERPRISE    axsStaticTrap
        VARIABLES     { axsStaticGatewayAddr,
                        axsStaticGatewayState }
        DESCRIPTION
                  "static route gateway state change."
        ::= 1

    axsStaticIpv6GatewayStateChange TRAP-TYPE
        ENTERPRISE      axsStaticTrap
        VARIABLES       { axsStaticIpv6Ifindex,
                          axsStaticIpv6GatewayAddr,
                          axsStaticIpv6GatewayState }
        DESCRIPTION
                  "ipv6 static route gateway state change."
        ::= 2

    axsOspfVirtIfStateChange TRAP-TYPE
        ENTERPRISE    axsOspfTraps
        VARIABLES     { axsOspfVirtIfDomainNumber,
                        axsOspfRouterId,
                        axsOspfVirtIfAreaId,
                        axsOspfVirtIfNeighbor,
                        axsOspfVirtIfState }
        DESCRIPTION
                  "An axsOspfIfStateChange trap signifies that there has  been a change 
                  in the state of an OSPF virtual interface."
        ::= 1

    axsOspfNbrStateChange TRAP-TYPE
        ENTERPRISE    axsOspfTraps
        VARIABLES     { axsOspfNbrDomainNumber,
                        axsOspfRouterId,
                        axsOspfNbrIpAddr,
                        axsOspfNbrAddressLessIndex,
                        axsOspfNbrRtrId,
                        axsOspfNbrState }
        DESCRIPTION
                  "An axsOspfNbrStateChange trap signifies that
                  there  has been a change in the state of a non-
                  virtual OSPF neighbor.   This  trap  should  be
                  generated  when  the  neighbor  state regresses
                  (e.g., goes from Attempt or Full  to  1-Way  or
                  Down)  or progresses to a terminal state (e.g.,
                  2-Way or Full).  When an  neighbor  transitions
                  from  or  to Full on non-broadcast multi-access
                  and broadcast networks, the trap should be gen-
                  erated  by the designated router.  A designated
                  router transitioning to Down will be  noted  by
                  axsOspfIfStateChange."
        ::= 2

    axsOspfVirtNbrStateChange TRAP-TYPE
        ENTERPRISE    axsOspfTraps
        VARIABLES     { axsOspfVirtNbrDomainNumber,
                        axsOspfRouterId,
                        axsOspfVirtNbrArea,
                        axsOspfVirtNbrRtrId,
                        axsOspfVirtNbrState }
        DESCRIPTION
                  "An axsOspfIfStateChange trap signifies that there
                  has  been a change in the state of an OSPF vir-
                  tual neighbor.  This trap should  be  generated
                  when  the  neighbor state regresses (e.g., goes
                  from Attempt or  Full  to  1-Way  or  Down)  or
                  progresses to a terminal state (e.g., Full)."
        ::= 3

    axsOspfIfConfigError TRAP-TYPE
        ENTERPRISE    axsOspfTraps
        VARIABLES     { axsOspfIfDomainNumber,
                        axsOspfRouterId,
                        axsOspfIfIpAddress,
                        axsOspfAddressLessIf,
                        axsOspfPacketSrc,
                        axsOspfConfigErrorType,
                        axsOspfPacketType }
        DESCRIPTION
                  "An axsOspfIfConfigError  trap  signifies  that  a
                  packet  has  been received on a non-virtual in-
                  terface  from  a  router  whose   configuration
                  parameters  conflict  with this router's confi-
                  guration parameters.  Note that the  event  op-
                  tionMismatch  should  cause  a  trap only if it
                  prevents an adjacency from forming."
        ::= 4

    axsOspfVirtIfConfigError TRAP-TYPE
        ENTERPRISE    axsOspfTraps
        VARIABLES     { axsOspfVirtIfDomainNumber,
                        axsOspfRouterId,
                        axsOspfVirtIfAreaId,
                        axsOspfVirtIfNeighbor,
                        axsOspfConfigErrorType,
                        axsOspfPacketType }
        DESCRIPTION
                  "An axsOspfConfigError trap signifies that a pack-
                  et  has  been  received  on a virtual interface
                  from a router  whose  configuration  parameters
                  conflict   with   this  router's  configuration
                  parameters.  Note that the event optionMismatch
                  should  cause a trap only if it prevents an ad-
                  jacency from forming."
        ::= 5

    axsOspfIfAuthFailure TRAP-TYPE
        ENTERPRISE    axsOspfTraps
        VARIABLES     { axsOspfIfDomainNumber,
                        axsOspfRouterId,
                        axsOspfIfIpAddress,
                        axsOspfAddressLessIf,
                        axsOspfPacketSrc,
                        axsOspfConfigErrorType,
                        axsOspfPacketType }
        DESCRIPTION
                  "An axsOspfIfAuthFailure  trap  signifies  that  a
                  packet  has  been received on a non-virtual in-
                  terface from a router whose authentication  key
                  or  authentication  type  conflicts  with  this
                  router's authentication key  or  authentication
                  type."
        ::= 6

    axsOspfVirtIfAuthFailure TRAP-TYPE
        ENTERPRISE    axsOspfTraps
        VARIABLES     { axsOspfVirtIfDomainNumber,
                        axsOspfRouterId,
                        axsOspfVirtIfAreaId,
                        axsOspfVirtIfNeighbor,
                        axsOspfConfigErrorType,
                        axsOspfPacketType }
        DESCRIPTION
                  "An axsOspfVirtIfAuthFailure trap signifies that a
                  packet has been received on a virtual interface
                  from a router whose authentication key  or  au-
                  thentication  type conflicts with this router's
                  authentication key or authentication type."
        ::= 7

    axsOspfIfStateChange TRAP-TYPE
        ENTERPRISE    axsOspfTraps
        VARIABLES     { axsOspfIfDomainNumber,
                        axsOspfRouterId,
                        axsOspfIfIpAddress,
                        axsOspfAddressLessIf,
                        axsOspfIfState }
        DESCRIPTION
                  "An axsOspfIfStateChange trap signifies that there
                  has been a change in the state of a non-virtual
                  OSPF interface. This trap should  be  generated
                  when  the interface state regresses (e.g., goes
                  from Dr to Down) or progresses  to  a  terminal
                  state  (i.e.,  Point-to-Point, DR Other, Dr, or
                  Backup)."
        ::= 16

    axsOadpNeighborCachelastChangeTrap TRAP-TYPE
        ENTERPRISE    axsOadpMIBNotifications
        VARIABLES     { axsOadpNeighborCacheLastChange }
        DESCRIPTION
                  "This trap indicates that information of OADP neighbor nodes is updated."
        ::= 1

    axsTrackStateUp TRAP-TYPE
        ENTERPRISE      axsTrackTraps
        VARIABLES       { axsTrackId, axsTrackState, axsTrackOperation,
                          axsTrackType, axsTrackListType, axsTrackVrfIndex }
        DESCRIPTION
                  "The track state changed to up."
        ::= 1

    axsTrackStateDown TRAP-TYPE
        ENTERPRISE      axsTrackTraps
        VARIABLES       { axsTrackId, axsTrackState, axsTrackOperation,
                          axsTrackType, axsTrackListType, axsTrackVrfIndex }
        DESCRIPTION
                  "The track state changed to down."
        ::= 2

    axsPolicyBaseRoutingRouteChange TRAP-TYPE
        ENTERPRISE    axsPolicyBaseRouting
        VARIABLES     {axsPolicyBaseRoutingChangeListNumber , axsPolicyBaseRoutingChangeSequenceNumber}
        DESCRIPTION
               "When route of Policy Base Routing changed."
        ::= 1

    axsPolicyBaseSwitchingRouteChange TRAP-TYPE
        ENTERPRISE    axsPolicyBaseSwitching
        VARIABLES     {axsPolicyBaseSwitchingChangeListNumber , axsPolicyBaseSwitchingChangeSequenceNumber}
        DESCRIPTION
               "When route of Policy Base Switching changed."
        ::= 1

    axsTrackObjectStateUp TRAP-TYPE
        ENTERPRISE      axsTrackObjectTraps
        VARIABLES       { axsTrackObjectId, axsTrackObjectState, axsTrackObjectOperation,
                          axsTrackObjectType, axsTrackObjectNetIndex }
        DESCRIPTION
                  "The track state changed to up."
        ::= 1

    axsTrackObjectStateDown TRAP-TYPE
        ENTERPRISE      axsTrackObjectTraps
        VARIABLES       { axsTrackObjectId, axsTrackObjectState, axsTrackObjectOperation,
                          axsTrackObjectType, axsTrackObjectNetIndex }
        DESCRIPTION
                  "The track state changed to down."
        ::= 2

END

-- Traps for use by AlaxalA networks AX6300S

-- Traps are defined using the conventions in RFC 1215.

AXS-AX6300S-TRAP DEFINITIONS ::= BEGIN

    IMPORTS
        enterprises
            FROM RFC1155-SMI
        TRAP-TYPE
            FROM RFC-1215
        ifIndex
            FROM RFC1213-MIB
        ax6300s,
        ax6300sSystemMsgType,
        ax6300sSystemMsgTimeStamp,
        ax6300sSystemMsgLevel,
        ax6300sSystemMsgEventPoint,
        ax6300sSystemMsgEventInterfaceID,
        ax6300sSystemMsgEventCode,
        ax6300sSystemMsgAdditionalCode,
        ax6300sSystemMsgText,
        ax6300sChassisIndex,
        ax6300sMsuBoardIndex,
        ax6300sTemperatureStatusIndex,
        ax6300sTemperatureStatusDescr,
        ax6300sTemperatureStatusValue,
        ax6300sTemperatureState,
        axsGsrpGroupId,
        axsGsrpVlanGroupId,
        axsGsrpState,
        axsLoginName,
        axsLoginTime,
        axsLoginLocation,
        axsLoginLine,
        axsLoginFailureTime,
        axsLogoutTime,
        axsLogoutStatus,
        axsAxrpGroupRingId,
        axsAxrpGroupMode,
        axsAxrpGroupRingAttribute,
        axsAxrpGroupMonitoringState,
        axsL2ldPortIndex,
        axsL2ldPortIfIndex,
        axsL2ldPortSourcePortIfindex,
        axsL2ldPortDestinationPortIfindex,
        axsL2ldPortSourceVlan,
        axsPortChannelPortIfIndex,
        axsPortChannelPortStandbyState
            FROM AX6300S
    ;

    ax6300sSystemMsgTrap TRAP-TYPE
        ENTERPRISE    ax6300s
        VARIABLES     { ax6300sSystemMsgType,
                        ax6300sSystemMsgTimeStamp,
                        ax6300sSystemMsgLevel,
                        ax6300sSystemMsgEventPoint,
                        ax6300sSystemMsgEventInterfaceID,
                        ax6300sSystemMsgEventCode,
                        ax6300sSystemMsgAdditionalCode,
                        ax6300sSystemMsgText }
        DESCRIPTION
                  "System message is displayed."
        ::= 1

    ax6300sStandbySystemUpTrap TRAP-TYPE
        ENTERPRISE    ax6300s
        VARIABLES     { ax6300sChassisIndex,
                        ax6300sMsuBoardIndex }
        DESCRIPTION
                  "Standby system is restarted."
        ::= 2

    ax6300sStandbySystemDownTrap TRAP-TYPE
        ENTERPRISE    ax6300s
        VARIABLES     { ax6300sChassisIndex,
                        ax6300sMsuBoardIndex }
        DESCRIPTION
                  "Standby system is failed."
        ::= 3

    ax6300sTemperatureTrap TRAP-TYPE
        ENTERPRISE    ax6300s
        VARIABLES     { ax6300sChassisIndex,
                        ax6300sMsuBoardIndex,
                        ax6300sTemperatureStatusIndex,
                        ax6300sTemperatureStatusDescr,
                        ax6300sTemperatureStatusValue,
                        ax6300sTemperatureState }
        DESCRIPTION
                  "A ax6300sTemperatureTrap is sent if the 
                  temperature measured at a given testpoint is outside 
                  the normal range for the testpoint (i.e. is at the warning, 
                  critical, or shutdown stage)."
        ::= 4

--    axsGsrpStateTransitionTrap TRAP-TYPE
    ax6300sGsrpStateTransitionTrap TRAP-TYPE
        ENTERPRISE    ax6300s
        VARIABLES     { axsGsrpGroupId,
                        axsGsrpVlanGroupId,
                        axsGsrpState }
        DESCRIPTION
                  "Changes of the VLAN group state of GSRP"
        ::= 6

    ax6300sAirFanStopTrap TRAP-TYPE
        ENTERPRISE    ax6300s
        DESCRIPTION
                  "This trap indicates a fan failure."
        ::= 8

    ax6300sPowerSupplyFailureTrap TRAP-TYPE
        ENTERPRISE    ax6300s
        DESCRIPTION
                  "This trap indicates one ( or more ) of power supplies failure."
        ::= 9

    ax6300sLoginSuccessTrap TRAP-TYPE
        ENTERPRISE    ax6300s
        VARIABLES     { axsLoginName,
                        axsLoginTime,
                        axsLoginLocation,
                        axsLoginLine }
        DESCRIPTION
                  "This trap indicates success of user log in."
        ::= 10

    ax6300sLoginFailureTrap TRAP-TYPE
        ENTERPRISE    ax6300s
        VARIABLES     { axsLoginName,
                        axsLoginFailureTime,
                        axsLoginLocation,
                        axsLoginLine }
        DESCRIPTION
                  "This trap indicates failure of user log in."
        ::= 11

    ax6300sLogoutTrap TRAP-TYPE
        ENTERPRISE    ax6300s
        VARIABLES     { axsLoginName,
                        axsLoginTime,
                        axsLogoutTime,
                        axsLoginLocation,
                        axsLoginLine,
                        axsLogoutStatus }
        DESCRIPTION
                  "This trap indicates success of following log out.
                  'logout' command, 'exit' command, 'quit' command."
        ::= 12

    ax6300sMemoryUsageTrap TRAP-TYPE
        ENTERPRISE    ax6300s
        DESCRIPTION
                  "This indicates available memory is fewer than lower limit."
        ::= 13

    ax6300sFrameErrorReceiveTrap TRAP-TYPE
        ENTERPRISE    ax6300s
        VARIABLES     { ifIndex }
        DESCRIPTION
                  "This indicates frame receive error."
        ::= 18

    ax6300sFrameErrorSendTrap TRAP-TYPE
        ENTERPRISE    ax6300s
        VARIABLES     { ifIndex }
        DESCRIPTION
                  "This indicates frame send error."
        ::= 19

--    axsEfmoamUdldPortInactivateTrap TRAP-TYPE
    ax6300sEfmoamUdldPortInactivateTrap TRAP-TYPE
        ENTERPRISE    ax6300s
        VARIABLES     { ifIndex }
        DESCRIPTION
                  "Efmoam udld port inactivate trap."
        ::= 29

--    axsEfmoamLoopDetectPortInactivateTrap TRAP-TYPE
    ax6300sEfmoamLoopDetectPortInactivateTrap TRAP-TYPE
        ENTERPRISE    ax6300s
        VARIABLES     { ifIndex }
        DESCRIPTION
                 "Efmoam loop detect port inactivate trap."
        ::= 30

--    axsStormDetectTrap TRAP-TYPE
    ax6300sStormDetectTrap TRAP-TYPE
        ENTERPRISE    ax6300s
        VARIABLES     { ifIndex }
        DESCRIPTION
                  "This indicates decection on uni-cast storm."
        ::= 31

--    axsStormPortInactivateTrap TRAP-TYPE
    ax6300sStormPortInactivateTrap TRAP-TYPE
        ENTERPRISE    ax6300s
        VARIABLES     { ifIndex }
        DESCRIPTION
                  "This indicates the port inactivated for decection on uni-cast storm."
        ::= 32

--    axsStormRecoverTrap TRAP-TYPE
    ax6300sStormRecoverTrap TRAP-TYPE
        ENTERPRISE    ax6300s
        VARIABLES     { ifIndex }
        DESCRIPTION
                  "This indicates the end of broad-cast storm."
        ::= 33

--    axsAxrpStateTransitionTrap TRAP-TYPE
    ax6300sAxrpStateTransitionTrap TRAP-TYPE
        ENTERPRISE    ax6300s
        VARIABLES     { axsAxrpGroupRingId,
                        axsAxrpGroupMode,
                        axsAxrpGroupRingAttribute,
                        axsAxrpGroupMonitoringState }
        DESCRIPTION
                  "When the state of the ring of ALAXALA Ring Protocol (trouble watch and restoration watch) changes between each state."
        ::= 36

--    axsL2ldLinkDown TRAP-TYPE
    ax6300sL2ldLinkDown TRAP-TYPE
        ENTERPRISE    ax6300s
        VARIABLES     { axsL2ldPortIfIndex,
                        axsL2ldPortSourcePortIfindex,
                        axsL2ldPortDestinationPortIfindex,
                        axsL2ldPortSourceVlan }
        DESCRIPTION
                  "When the operation of the interface changes from ACTIVE(state that can be communicated)
                  into DISABLE (state that cannot be communicated) by the L2 loop detection."
        ::= 51

--    axsL2ldLinkUp TRAP-TYPE
    ax6300sL2ldLinkUp TRAP-TYPE
        ENTERPRISE    ax6300s
        VARIABLES     { axsL2ldPortIfIndex }
        DESCRIPTION
                  "When the operation of the interface changes from DISABLE (state that cannot be communicated)
                  into ACTIVE (state that can be communicated) by the automatic restoration function of the L2 loop detection."
        ::= 52

--    axsL2ldLoopDetection TRAP-TYPE
    ax6300sL2ldLoopDetection TRAP-TYPE
        ENTERPRISE    ax6300s
        VARIABLES     { axsL2ldPortIndex,
                        axsL2ldPortIfIndex,
                        axsL2ldPortSourcePortIfindex,
                        axsL2ldPortSourceVlan }
        DESCRIPTION
                  "When you detect the L2 loop. It notifies every 60 seconds when the state of the L2 loop continues."
        ::= 53

    ax6300sEoeTtlExpiredTrap TRAP-TYPE
        ENTERPRISE    ax6300s
        VARIABLES     { ax6300sSystemMsgType,
                        ax6300sSystemMsgTimeStamp,
                        ax6300sSystemMsgLevel,
                        ax6300sSystemMsgEventPoint,
                        ax6300sSystemMsgEventInterfaceID,
                        ax6300sSystemMsgEventCode,
                        ax6300sSystemMsgAdditionalCode,
                        ax6300sSystemMsgText }
        DESCRIPTION
                  "The notice of a message of EoE."
        ::= 61

    ax6300sEoeLoopDetectionTrap TRAP-TYPE
        ENTERPRISE    ax6300s
        VARIABLES     { ifIndex }
        DESCRIPTION
                  "When voluntary EoE frame is received, ifIndex based on a physical port is set."
        ::= 62

--    axsPortChannelStandbyStateChangeTrap TRAP-TYPE
    ax6300sPortChannelStandbyStateChangeTrap TRAP-TYPE
        ENTERPRISE    ax6300s
        VARIABLES     { axsPortChannelPortIfIndex,
                        axsPortChannelPortStandbyState }
        DESCRIPTION
                  "This indicates a change in the state of standby port of port channel."
        ::= 63

END

-- Traps for use by AlaxalA networks AX6700S

-- Traps are defined using the conventions in RFC 1215.

AXS-6700S-TRAP DEFINITIONS ::= BEGIN

    IMPORTS
        enterprises
            FROM RFC1155-SMI
        TRAP-TYPE
            FROM RFC-1215
        ifIndex
            FROM RFC1213-MIB
        ax6700s,
        ax6700sSystemMsgType,
        ax6700sSystemMsgTimeStamp,
        ax6700sSystemMsgLevel,
        ax6700sSystemMsgEventPoint,
        ax6700sSystemMsgEventInterfaceID,
        ax6700sSystemMsgEventCode,
        ax6700sSystemMsgAdditionalCode,
        ax6700sSystemMsgText,
        ax6700sChassisIndex,
        ax6700sBcuBoardIndex,
        ax6700sBsuBoardIndex,
        ax6700sTemperatureStatusIndex,
        ax6700sTemperatureStatusDescr,
        ax6700sTemperatureStatusValue,
        ax6700sTemperatureState,
        axsGsrpGroupId,
        axsGsrpVlanGroupId,
        axsGsrpState,
        axsLoginName,
        axsLoginTime,
        axsLoginLocation,
        axsLoginLine,
        axsLoginFailureTime,
        axsLogoutTime,
        axsLogoutStatus,
        axsAxrpGroupRingId,
        axsAxrpGroupMode,
        axsAxrpGroupRingAttribute,
        axsAxrpGroupMonitoringState,
        axsL2ldPortIndex,
        axsL2ldPortIfIndex,
        axsL2ldPortSourcePortIfindex,
        axsL2ldPortDestinationPortIfindex,
        axsL2ldPortSourceVlan,
        axsPortChannelPortIfIndex,
        axsPortChannelPortStandbyState,
        ax6700sBsuBoardIndex,
        ax6700sForwardingEngineIndex,
        ax6700sNifBoardSlotIndex
            FROM AX6300S
    ;

    ax6700sSystemMsgTrap TRAP-TYPE
        ENTERPRISE    ax6700s
        VARIABLES     { ax6700sSystemMsgType,
                        ax6700sSystemMsgTimeStamp,
                        ax6700sSystemMsgLevel,
                        ax6700sSystemMsgEventPoint,
                        ax6700sSystemMsgEventInterfaceID,
                        ax6700sSystemMsgEventCode,
                        ax6700sSystemMsgAdditionalCode,
                        ax6700sSystemMsgText }
        DESCRIPTION
                  "System message is displayed."
        ::= 1

    ax6700sStandbySystemUpTrap TRAP-TYPE
        ENTERPRISE    ax6700s
        VARIABLES     { ax6700sChassisIndex,
                        ax6700sBcuBoardIndex }
        DESCRIPTION
                  "Standby system is restarted."
        ::= 2

    ax6700sStandbySystemDownTrap TRAP-TYPE
        ENTERPRISE    ax6700s
        VARIABLES     { ax6700sChassisIndex,
                        ax6700sBcuBoardIndex }
        DESCRIPTION
                  "Standby system is failed."
        ::= 3

    ax6700sTemperatureTrap TRAP-TYPE
        ENTERPRISE    ax6700s
        VARIABLES     { ax6700sChassisIndex,
                        ax6700sBcuBoardIndex,
                        ax6700sTemperatureStatusIndex,
                        ax6700sTemperatureStatusDescr,
                        ax6700sTemperatureStatusValue,
                        ax6700sTemperatureState }
        DESCRIPTION
                  "A ax6700sTemperatureTrap is sent if the 
                  temperature measured at a given testpoint is outside 
                  the normal range for the testpoint (i.e. is at the warning, 
                  critical, or shutdown stage)."
        ::= 4

--    axsGsrpStateTransitionTrap TRAP-TYPE
    ax6700sGsrpStateTransitionTrap TRAP-TYPE
        ENTERPRISE    ax6700s
        VARIABLES     { axsGsrpGroupId,
                        axsGsrpVlanGroupId,
                        axsGsrpState }
        DESCRIPTION
                  "Changes of the VLAN group state of GSRP"
        ::= 6

    ax6700sAirFanStopTrap TRAP-TYPE
        ENTERPRISE    ax6700s
        DESCRIPTION
                  "This trap indicates a fan failure."
        ::= 8

    ax6700sPowerSupplyFailureTrap TRAP-TYPE
        ENTERPRISE    ax6700s
        DESCRIPTION
                  "This trap indicates one ( or more ) of power supplies failure."
        ::= 9

    ax6700sLoginSuccessTrap TRAP-TYPE
        ENTERPRISE    ax6700s
        VARIABLES     { axsLoginName,
                        axsLoginTime,
                        axsLoginLocation,
                        axsLoginLine }
        DESCRIPTION
                  "This trap indicates success of user log in."
        ::= 10

    ax6700sLoginFailureTrap TRAP-TYPE
        ENTERPRISE    ax6700s
        VARIABLES     { axsLoginName,
                        axsLoginFailureTime,
                        axsLoginLocation,
                        axsLoginLine }
        DESCRIPTION
                  "This trap indicates failure of user log in."
        ::= 11

    ax6700sLogoutTrap TRAP-TYPE
        ENTERPRISE    ax6700s
        VARIABLES     { axsLoginName,
                        axsLoginTime,
                        axsLogoutTime,
                        axsLoginLocation,
                        axsLoginLine,
                        axsLogoutStatus }
        DESCRIPTION
                  "This trap indicates success of following log out.
                  'logout' command, 'exit' command, 'quit' command." 
        ::= 12

    ax6700sMemoryUsageTrap TRAP-TYPE
        ENTERPRISE    ax6700s
        DESCRIPTION
                  "This indicates available memory is fewer than lower limit."
        ::= 13

    ax6700sFrameErrorReceiveTrap TRAP-TYPE
        ENTERPRISE    ax6700s
        VARIABLES     { ifIndex }
        DESCRIPTION
                  "This indicates frame receive error."
        ::= 18

    ax6700sFrameErrorSendTrap TRAP-TYPE
        ENTERPRISE    ax6700s
        VARIABLES     { ifIndex }
        DESCRIPTION
                  "This indicates frame send error."
        ::= 19

--    axsEfmoamUdldPortInactivateTrap TRAP-TYPE
    ax6700sEfmoamUdldPortInactivateTrap TRAP-TYPE
        ENTERPRISE    ax6700s
        VARIABLES     { ifIndex }
        DESCRIPTION
                  "Efmoam udld port inactivate trap."
        ::= 29

--    axsEfmoamLoopDetectPortInactivateTrap TRAP-TYPE
    ax6700sEfmoamLoopDetectPortInactivateTrap TRAP-TYPE
        ENTERPRISE    ax6700s
        VARIABLES     { ifIndex }
        DESCRIPTION
                  "Efmoam loop detect port inactivate trap."
        ::= 30

--    axsStormDetectTrap TRAP-TYPE
    ax6700sStormDetectTrap TRAP-TYPE
        ENTERPRISE    ax6700s
        VARIABLES     { ifIndex }
        DESCRIPTION
                  "This indicates decection on uni-cast storm."
        ::= 31

--    axsStormPortInactivateTrap TRAP-TYPE
    ax6700sStormPortInactivateTrap TRAP-TYPE
        ENTERPRISE    ax6700s
        VARIABLES     { ifIndex }
        DESCRIPTION
                  "This indicates the port inactivated for decection on uni-cast storm."
        ::= 32

--    axsStormRecoverTrap TRAP-TYPE
    ax6700sStormRecoverTrap TRAP-TYPE
        ENTERPRISE    ax6700s
        VARIABLES     { ifIndex }
        DESCRIPTION
                  "This indicates the end of broad-cast storm."
        ::= 33

    ax6700sStandbyBsuUpTrap TRAP-TYPE
        ENTERPRISE    ax6700s
        VARIABLES     { ax6700sChassisIndex,
                        ax6700sBsuBoardIndex }
        DESCRIPTION
                  "Standby system is restarted."
        ::= 34

    ax6700sStandbyBsuDownTrap TRAP-TYPE
        ENTERPRISE    ax6700s
        VARIABLES     { ax6700sChassisIndex,
                        ax6700sBsuBoardIndex }
        DESCRIPTION
                  "Standby system is failed."
        ::= 35

--    axsAxrpStateTransitionTrap TRAP-TYPE
    ax6700sAxrpStateTransitionTrap TRAP-TYPE
        ENTERPRISE    ax6700s
        VARIABLES     { axsAxrpGroupRingId,
                        axsAxrpGroupMode,
                        axsAxrpGroupRingAttribute,
                        axsAxrpGroupMonitoringState }
        DESCRIPTION
                  "When the state of the ring of ALAXALA Ring Protocol (trouble watch and restoration watch) changes between each state."
        ::= 36

--    axsL2ldLinkDown TRAP-TYPE
    ax6700sL2ldLinkDown TRAP-TYPE
        ENTERPRISE    ax6700s
        VARIABLES     { axsL2ldPortIfIndex,
                        axsL2ldPortSourcePortIfindex,
                        axsL2ldPortDestinationPortIfindex,
                        axsL2ldPortSourceVlan }
        DESCRIPTION
                  "When the operation of the interface changes from ACTIVE(state that can be communicated)
                  into DISABLE (state that cannot be communicated) by the L2 loop detection."
        ::= 51

--    axsL2ldLinkUp TRAP-TYPE
    ax6700sL2ldLinkUp TRAP-TYPE
        ENTERPRISE    ax6700s
        VARIABLES     { axsL2ldPortIfIndex }
        DESCRIPTION
                  "When the operation of the interface changes from DISABLE (state that cannot be communicated)
                  into ACTIVE (state that can be communicated) by the automatic restoration function of the L2 loop detection."
        ::= 52

--    axsL2ldLoopDetection TRAP-TYPE
    ax6700sL2ldLoopDetection TRAP-TYPE
        ENTERPRISE    ax6700s
        VARIABLES     { axsL2ldPortIndex,
                        axsL2ldPortIfIndex,
                        axsL2ldPortSourcePortIfindex,
                        axsL2ldPortSourceVlan }
        DESCRIPTION
                  "When you detect the L2 loop. It notifies every 60 seconds when the state of the L2 loop continues."
        ::= 53

    ax6700sEoeTtlExpiredTrap TRAP-TYPE
        ENTERPRISE    ax6700s
        VARIABLES     { ax6700sSystemMsgType,
                        ax6700sSystemMsgTimeStamp,
                        ax6700sSystemMsgLevel,
                        ax6700sSystemMsgEventPoint,
                        ax6700sSystemMsgEventInterfaceID,
                        ax6700sSystemMsgEventCode,
                        ax6700sSystemMsgAdditionalCode,
                        ax6700sSystemMsgText }
        DESCRIPTION
                  "The notice of a message of EoE."
        ::= 61

--    axsPortChannelStandbyStateChangeTrap TRAP-TYPE
    ax6700sPortChannelStandbyStateChangeTrap TRAP-TYPE
        ENTERPRISE    ax6700s
        VARIABLES     { axsPortChannelPortIfIndex,
                        axsPortChannelPortStandbyState }
        DESCRIPTION
                  "This indicates a change in the state of standby port of port channel."
        ::= 63

    ax6700sInboundPacketbusCongestionTrap  TRAP-TYPE
        ENTERPRISE    ax6700s
        VARIABLES     { ax6700sBsuBoardIndex,
                        ax6700sForwardingEngineIndex,
                        ax6700sNifBoardSlotIndex }
        DESCRIPTION
                  "The notice of a message of over threshold in bound packet bus."
        ::= 64

    ax6700sOutboundPacketbusCongestionTrap  TRAP-TYPE
        ENTERPRISE    ax6700s
        VARIABLES     { ax6700sBsuBoardIndex,
                        ax6700sForwardingEngineIndex,
                        ax6700sNifBoardSlotIndex }
        DESCRIPTION
                  "The notice of a message of over threshold out bound packet bus."
        ::= 65

    ax6700sInboundPacketbusRecoveryTrap  TRAP-TYPE
        ENTERPRISE    ax6700s
        VARIABLES     { ax6700sBsuBoardIndex,
                        ax6700sForwardingEngineIndex,
                        ax6700sNifBoardSlotIndex }
        DESCRIPTION
                  "The notice of a message of under threshold in bound packet bus."
        ::= 66

    ax6700sOutboundPacketbusRecoveryTrap  TRAP-TYPE
        ENTERPRISE    ax6700s
        VARIABLES     { ax6700sBsuBoardIndex,
                        ax6700sForwardingEngineIndex,
                        ax6700sNifBoardSlotIndex }
        DESCRIPTION
                  "The notice of a message of under threshold out bound packet bus."
        ::= 67

    ax6700sSpServiceStartTrap  TRAP-TYPE
        ENTERPRISE    ax6700s
        VARIABLES     { ifIndex }
        DESCRIPTION
                  "This indicates the start of SP service."
        ::= 83

    ax6700sSpServiceStopTrap  TRAP-TYPE
        ENTERPRISE    ax6700s
        VARIABLES     { ifIndex }
        DESCRIPTION
                  "This indicates the stop of SP service."
        ::= 84

    ax6700sPowerControlModeChangeStartTrap  TRAP-TYPE
        ENTERPRISE    ax6700s
        VARIABLES     { ax6700sChassisIndex }
        DESCRIPTION
                  "This indicates the start of changing the power control mode."
        ::= 85

    ax6700sPowerControlModeChangeCompleteTrap  TRAP-TYPE
        ENTERPRISE    ax6700s
        VARIABLES     { ax6700sChassisIndex }
        DESCRIPTION
                  "This indicates the completion of changing the power control mode."
        ::= 86

    ax6700sStandbyNifUpTrap  TRAP-TYPE
        ENTERPRISE    ax6700s
        VARIABLES     { ax6700sChassisIndex,
                        ax6700sNifBoardSlotIndex }
        DESCRIPTION
                  "This indicates standby nif is ready."
    ::= 90

    ax6700sStandbyNifDownTrap  TRAP-TYPE
        ENTERPRISE    ax6700s
        VARIABLES     { ax6700sChassisIndex,
                        ax6700sNifBoardSlotIndex }
        DESCRIPTION
                  "This indicates standby nif is not ready."
    ::= 91

END

-- Traps for use by AlaxalA networks AX6600S

-- Traps are defined using the conventions in RFC 1215.

AXS-AX6600S-TRAP DEFINITIONS ::= BEGIN

    IMPORTS
        enterprises
            FROM RFC1155-SMI
        TRAP-TYPE
            FROM RFC-1215
        ifIndex
            FROM RFC1213-MIB
        ax6600s,
        ax6600sSystemMsgType,
        ax6600sSystemMsgTimeStamp,
        ax6600sSystemMsgLevel,
        ax6600sSystemMsgEventPoint,
        ax6600sSystemMsgEventInterfaceID,
        ax6600sSystemMsgEventCode,
        ax6600sSystemMsgAdditionalCode,
        ax6600sSystemMsgText,
        ax6600sChassisIndex,
        ax6600sCsuBoardIndex,
        ax6600sTemperatureStatusIndex,
        ax6600sTemperatureStatusDescr,
        ax6600sTemperatureStatusValue,
        ax6600sTemperatureState,
        ax6600sNifBoardSlotIndex,
        axsGsrpGroupId,
        axsGsrpVlanGroupId,
        axsGsrpState,
        axsLoginName,
        axsLoginTime,
        axsLoginLocation,
        axsLoginLine,
        axsLoginFailureTime,
        axsLogoutTime,
        axsLogoutStatus,
        axsAxrpGroupRingId,
        axsAxrpGroupMode,
        axsAxrpGroupRingAttribute,
        axsAxrpGroupMonitoringState,
        axsL2ldPortIndex,
        axsL2ldPortIfIndex,
        axsL2ldPortSourcePortIfindex,
        axsL2ldPortDestinationPortIfindex,
        axsL2ldPortSourceVlan,
        axsPortChannelPortIfIndex,
        axsPortChannelPortStandbyState
            FROM AX6300S
    ;

    ax6600sSystemMsgTrap TRAP-TYPE
        ENTERPRISE    ax6600s
        VARIABLES     { ax6600sSystemMsgType,
                        ax6600sSystemMsgTimeStamp,
                        ax6600sSystemMsgLevel,
                        ax6600sSystemMsgEventPoint,
                        ax6600sSystemMsgEventInterfaceID,
                        ax6600sSystemMsgEventCode,
                        ax6600sSystemMsgAdditionalCode,
                        ax6600sSystemMsgText }
        DESCRIPTION
                  "System message is displayed."
        ::= 1

    ax6600sStandbySystemUpTrap TRAP-TYPE
        ENTERPRISE    ax6600s
        VARIABLES     { ax6600sChassisIndex,
                        ax6600sCsuBoardIndex }
        DESCRIPTION
                  "Standby system is restarted."
        ::= 2

    ax6600sStandbySystemDownTrap TRAP-TYPE
        ENTERPRISE    ax6600s
        VARIABLES     { ax6600sChassisIndex,
                        ax6600sCsuBoardIndex }
        DESCRIPTION
                  "Standby system is failed."
        ::= 3

    ax6600sTemperatureTrap TRAP-TYPE
        ENTERPRISE    ax6600s
        VARIABLES     { ax6600sChassisIndex,
                        ax6600sCsuBoardIndex,
                        ax6600sTemperatureStatusIndex,
                        ax6600sTemperatureStatusDescr,
                        ax6600sTemperatureStatusValue,
                        ax6600sTemperatureState }
        DESCRIPTION
                  "A ax6600sTemperatureTrap is sent if the 
                  temperature measured at a given testpoint is outside 
                  the normal range for the testpoint (i.e. is at the warning, 
                  critical, or shutdown stage)."
        ::= 4

    ax6600sGsrpStateTransitionTrap TRAP-TYPE
        ENTERPRISE    ax6600s
        VARIABLES     { axsGsrpGroupId,
                        axsGsrpVlanGroupId,
                        axsGsrpState }
        DESCRIPTION
                  "Changes of the VLAN group state of GSRP"
        ::= 6

    ax6600sAirFanStopTrap TRAP-TYPE
        ENTERPRISE    ax6600s
        DESCRIPTION
                  "This trap indicates a fan failure."
        ::= 8

    ax6600sPowerSupplyFailureTrap TRAP-TYPE
        ENTERPRISE    ax6600s
        DESCRIPTION
                  "This trap indicates one ( or more ) of power supplies failure."
        ::= 9

    ax6600sLoginSuccessTrap TRAP-TYPE
        ENTERPRISE    ax6600s
        VARIABLES     { axsLoginName,
                        axsLoginTime,
                        axsLoginLocation,
                        axsLoginLine }
        DESCRIPTION
                  "This trap indicates success of user log in."
        ::= 10

    ax6600sLoginFailureTrap TRAP-TYPE
        ENTERPRISE    ax6600s
        VARIABLES     { axsLoginName,
                        axsLoginFailureTime,
                        axsLoginLocation,
                        axsLoginLine }
        DESCRIPTION
                  "This trap indicates failure of user log in."
        ::= 11

    ax6600sLogoutTrap TRAP-TYPE
        ENTERPRISE    ax6600s
        VARIABLES     { axsLoginName,
                        axsLoginTime,
                        axsLogoutTime,
                        axsLoginLocation,
                        axsLoginLine,
                        axsLogoutStatus }
        DESCRIPTION
                  "This trap indicates success of following log out.
                  'logout' command, 'exit' command, 'quit' command."
        ::= 12

    ax6600sMemoryUsageTrap TRAP-TYPE
        ENTERPRISE    ax6600s
        DESCRIPTION
                  "This indicates available memory is fewer than lower limit."
        ::= 13

    ax6600sFrameErrorReceiveTrap TRAP-TYPE
        ENTERPRISE    ax6600s
        VARIABLES     { ifIndex }
        DESCRIPTION
                  "This indicates frame receive error."
        ::= 18

    ax6600sFrameErrorSendTrap TRAP-TYPE
        ENTERPRISE    ax6600s
        VARIABLES     { ifIndex }
        DESCRIPTION
                  "This indicates frame send error."
        ::= 19

    ax6600sEfmoamUdldPortInactivateTrap TRAP-TYPE
        ENTERPRISE    ax6600s
        VARIABLES     { ifIndex }
        DESCRIPTION
                  "Efmoam udld port inactivate trap."
        ::= 29

    ax6600sEfmoamLoopDetectPortInactivateTrap TRAP-TYPE
        ENTERPRISE    ax6600s
        VARIABLES     { ifIndex }
        DESCRIPTION
                 "Efmoam loop detect port inactivate trap."
        ::= 30

    ax6600sStormDetectTrap TRAP-TYPE
        ENTERPRISE    ax6600s
        VARIABLES     { ifIndex }
        DESCRIPTION
                  "This indicates decection on uni-cast storm."
        ::= 31

    ax6600sStormPortInactivateTrap TRAP-TYPE
        ENTERPRISE    ax6600s
        VARIABLES     { ifIndex }
        DESCRIPTION
                  "This indicates the port inactivated for decection on uni-cast storm."
        ::= 32

    ax6600sStormRecoverTrap TRAP-TYPE
        ENTERPRISE    ax6600s
        VARIABLES     { ifIndex }
        DESCRIPTION
                  "This indicates the end of broad-cast storm."
        ::= 33

    ax6600sAxrpStateTransitionTrap TRAP-TYPE
        ENTERPRISE    ax6600s
        VARIABLES     { axsAxrpGroupRingId,
                        axsAxrpGroupMode,
                        axsAxrpGroupRingAttribute,
                        axsAxrpGroupMonitoringState }
        DESCRIPTION
                  "When the state of the ring of ALAXALA Ring Protocol (trouble watch and restoration watch) changes between each state."
        ::= 36

    ax6600sL2ldLinkDown TRAP-TYPE
        ENTERPRISE    ax6600s
        VARIABLES     { axsL2ldPortIfIndex,
                        axsL2ldPortSourcePortIfindex,
                        axsL2ldPortDestinationPortIfindex,
                        axsL2ldPortSourceVlan }
        DESCRIPTION
                  "When the operation of the interface changes from ACTIVE(state that can be communicated)
                  into DISABLE (state that cannot be communicated) by the L2 loop detection."
        ::= 51

    ax6600sL2ldLinkUp TRAP-TYPE
        ENTERPRISE    ax6600s
        VARIABLES     { axsL2ldPortIfIndex }
        DESCRIPTION
                  "When the operation of the interface changes from DISABLE (state that cannot be communicated)
                  into ACTIVE (state that can be communicated) by the automatic restoration function of the L2 loop detection."
        ::= 52

    ax6600sL2ldLoopDetection TRAP-TYPE
        ENTERPRISE    ax6600s
        VARIABLES     { axsL2ldPortIndex,
                        axsL2ldPortIfIndex,
                        axsL2ldPortSourcePortIfindex,
                        axsL2ldPortSourceVlan }
        DESCRIPTION
                  "When you detect the L2 loop. It notifies every 60 seconds when the state of the L2 loop continues."
        ::= 53

    ax6600sSpServiceStartTrap  TRAP-TYPE
        ENTERPRISE    ax6600s
        VARIABLES     { ifIndex }
        DESCRIPTION
                  "This indicates the start of SP service."
        ::= 83

    ax6600sSpServiceStopTrap  TRAP-TYPE
        ENTERPRISE    ax6600s
        VARIABLES     { ifIndex }
        DESCRIPTION
                  "This indicates the stop of SP service."
        ::= 84

    ax6600sPowerControlModeChangeStartTrap  TRAP-TYPE
        ENTERPRISE    ax6600s
        VARIABLES     { ax6600sChassisIndex }
        DESCRIPTION
                  "This indicates the start of changing the power control mode."
        ::= 85

    ax6600sPowerControlModeChangeCompleteTrap  TRAP-TYPE
        ENTERPRISE    ax6600s
        VARIABLES     { ax6600sChassisIndex }
        DESCRIPTION
                  "This indicates the completion of changing the power control mode."
        ::= 86

    ax6600sStandbyNifUpTrap  TRAP-TYPE
        ENTERPRISE    ax6600s
        VARIABLES     { ax6600sChassisIndex,
                        ax6600sNifBoardSlotIndex }
        DESCRIPTION
                  "This indicates standby nif is ready."
    ::= 90

    ax6600sStandbyNifDownTrap  TRAP-TYPE
        ENTERPRISE    ax6600s
        VARIABLES     { ax6600sChassisIndex,
                        ax6600sNifBoardSlotIndex }
        DESCRIPTION
                  "This indicates standby nif is not ready."
    ::= 91

END
