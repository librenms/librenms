--
-- Copyright(C) 2005-2010 ALAXALA Networks Corporation. All Rights Reserved.
--
-- AX1230S-MIB.my: Switching Router System information MIB file
--
AX1230S DEFINITIONS ::= BEGIN

IMPORTS
enterprises,  IpAddress, --   NetworkAddress,
Counter, Gauge, TimeTicks
        FROM RFC1155-SMI
Counter64,Counter32,Unsigned32,Gauge32,Integer32,MODULE-IDENTITY,OBJECT-TYPE
        FROM SNMPv2-SMI
RouterID, AreaID, Status, BigMetric, DesignatedRouterPriority,
HelloRange, Metric, PositiveInteger, UpToMaxAge
        FROM OSPF-MIB
 DisplayString
        FROM RFC1213-MIB
RowStatus, MacAddress, TruthValue, TimeStamp
    FROM SNMPv2-TC
InterfaceIndex
    FROM IF-MIB
Ipv6IfIndex, Ipv6Address, Ipv6AddressPrefix
    FROM IPV6-TC
BridgeId, Timeout
    FROM BRIDGE-MIB
PortList
    FROM Q-BRIDGE-MIB
ifIndex 
   FROM  RFC1213-MIB
InterfaceIndex
    FROM IF-MIB
--      InetAddressType,InetAddress
--      FROM INET-ADDRESS-MIB
;

   alaxala MODULE-IDENTITY
       LAST-UPDATED "201002251300Z"
       ORGANIZATION "ALAXALA"
       CONTACT-INFO "ALAXALA Networks Corporation"
       DESCRIPTION
               "alaxa enterprises mib"
       ::= { enterprises 21839 }




VlanIndex ::= INTEGER (1..2147483647)
VlanIdOrZero ::= INTEGER (0|1..4094)
-- object syntax difinition end

--  alaxala            OBJECT IDENTIFIER ::= { enterprises 21839 }
alaxalaProductId   OBJECT IDENTIFIER ::= { alaxala 1 }
axSwitch           OBJECT IDENTIFIER ::= { alaxalaProductId 2 }
ax1230s            OBJECT IDENTIFIER ::= { axSwitch 10 }

alaxalaMib         OBJECT IDENTIFIER ::= { alaxala 2 }
axsEx              OBJECT IDENTIFIER ::= { alaxalaMib 2 }

axsMib             OBJECT IDENTIFIER ::= { axsEx 1 }
ax1230sMib         OBJECT IDENTIFIER ::= { axsEx 10 }
-- device independent
axsStats              OBJECT IDENTIFIER ::= { axsMib 1 }
axsIfStats            OBJECT IDENTIFIER ::= { axsStats 4 }
axsQoS                OBJECT IDENTIFIER ::= { axsStats 6 }
axsEtherTxQoS         OBJECT IDENTIFIER ::= { axsQoS 1 }
axsEthShaper          OBJECT IDENTIFIER ::= { axsQoS 4 }
axsEthShaperAgQue     OBJECT IDENTIFIER ::= { axsQoS 5 }
axsDHCP               OBJECT IDENTIFIER ::= { axsStats 10 }

axsGsrp               OBJECT IDENTIFIER ::= { axsMib 4 }
axsFdb                OBJECT IDENTIFIER ::= { axsMib 5 }
axsVlan               OBJECT IDENTIFIER ::= { axsMib 6 }
axsVlanBridge           OBJECT IDENTIFIER ::= { axsVlan 1 }
axsVlanBridgeBase       OBJECT IDENTIFIER ::= { axsVlanBridge 1 }
axsVlanBridgeStp        OBJECT IDENTIFIER ::= { axsVlanBridge 2 }
axsVlanBridgeTp         OBJECT IDENTIFIER ::= { axsVlanBridge 4 }
axsVlanBridgeStatic     OBJECT IDENTIFIER ::= { axsVlanBridge 5 }
axsVlanTagTranslation   OBJECT IDENTIFIER ::= { axsVlan 10 }

axsOadp                 OBJECT IDENTIFIER ::= { axsMib 7 }
axsOadpMIBObjects       OBJECT IDENTIFIER ::= { axsOadp 1 }
axsOadpGlobalInfo       OBJECT IDENTIFIER ::= { axsOadpMIBObjects 1 }
axsOadpPortInfo         OBJECT IDENTIFIER ::= { axsOadpMIBObjects 2 }
axsOadpNeighborInfo     OBJECT IDENTIFIER ::= { axsOadpMIBObjects 3 }
axsOadpMIBNotifications OBJECT IDENTIFIER ::= { axsOadp 2 }

axsFlow               OBJECT IDENTIFIER ::= { axsMib 8 }
axsAccessFilterStats  OBJECT IDENTIFIER ::= {axsFlow 9}
axsQosFlowStats       OBJECT IDENTIFIER ::= {axsFlow 11}

axsL2ld                OBJECT IDENTIFIER ::= {axsMib 10}
axsL2ldGlobalInfo      OBJECT IDENTIFIER ::= {axsL2ld 1}

axsOspf               OBJECT IDENTIFIER ::= { axsMib 14 }
axsOspfTrap           OBJECT IDENTIFIER ::= { axsOspf 16 }
axsOspfTraps          OBJECT IDENTIFIER ::= { axsOspfTrap 2 }
axsOspfv3             OBJECT IDENTIFIER ::= { axsMib 15 }

axsStatic              OBJECT IDENTIFIER ::= { axsMib 38 }
axsStaticTraps         OBJECT IDENTIFIER ::= { axsStatic 2 }

axsBootManagement    OBJECT IDENTIFIER ::= { axsMib 51 }
axsLogin             OBJECT IDENTIFIER ::= { axsMib 52 }

axslldp                      OBJECT IDENTIFIER ::= { axsMib 100 }
axslldpConfiguration         OBJECT IDENTIFIER ::= { axslldp 1 }
axslldpStats                 OBJECT IDENTIFIER ::= { axslldp 2 }
axslldpLocalSystemData       OBJECT IDENTIFIER ::= { axslldp 3 }
axslldpRemoteSystemData      OBJECT IDENTIFIER ::= { axslldp 4 }
axslldpRemoteOriginInfoData  OBJECT IDENTIFIER ::= { axslldp 20 }

ax1230sSwitch           OBJECT IDENTIFIER ::= { ax1230sMib 1 }
ax1230sSoftware         OBJECT IDENTIFIER ::= { ax1230sSwitch 2 }
ax1230sSystemMsg        OBJECT IDENTIFIER ::= { ax1230sSwitch 3 }
ax1230sSnmpAgent        OBJECT IDENTIFIER ::= { ax1230sSwitch 4 }
ax1230sLicense          OBJECT IDENTIFIER ::= { ax1230sSwitch 6 }
ax1230sDevice           OBJECT IDENTIFIER ::= { ax1230sMib 2 }
ax1230sChassis          OBJECT IDENTIFIER ::= { ax1230sDevice 1 }
ax1230sPhysLine         OBJECT IDENTIFIER ::= { ax1230sDevice 2 }
ax1230sManagementMIB    OBJECT IDENTIFIER ::= { ax1230sMib 3 }
ax1230sOperationCommand OBJECT IDENTIFIER ::= { ax1230sManagementMIB 1 }
ax1230sFdbClearMIB      OBJECT IDENTIFIER ::= { ax1230sOperationCommand 1 }
ax1230sAuth             OBJECT IDENTIFIER ::= { ax1230sMib 10 }
ax1230sAuthInfo         OBJECT IDENTIFIER ::= { ax1230sAuth 1 }
ax1230sDot1x            OBJECT IDENTIFIER ::= { ax1230sAuth 2 }
ax1230sWauth            OBJECT IDENTIFIER ::= { ax1230sAuth 3 }
ax1230sMauth            OBJECT IDENTIFIER ::= { ax1230sAuth 4 }

axsIfStatsTable OBJECT-TYPE
	SYNTAX  SEQUENCE OF AxsIfStatsTableEntry
	MAX-ACCESS  not-accessible
	STATUS  current
	DESCRIPTION
		"A table containing extension statistics for more than 100,000,000
		bps interface."
	::= { axsIfStats 1 }

axsIfStatsEntry OBJECT-TYPE
	SYNTAX  AxsIfStatsTableEntry
	MAX-ACCESS  not-accessible
	STATUS  current
	DESCRIPTION
		"An entry containing extension statistics for interface."
	INDEX   { axsIfStatsIndex }
	::= { axsIfStatsTable 1 }

	AxsIfStatsTableEntry ::=
		SEQUENCE {
		  axsIfStatsIndex
			INTEGER,
		  axsIfStatsName
			DisplayString,
		  axsIfStatsInMegaOctets
			Counter,
		  axsIfStatsInUcastMegaPkts
			Counter,
		  axsIfStatsInMulticastMegaPkts
			Counter,
		  axsIfStatsInBroadcastMegaPkts
			Counter,
		  axsIfStatsOutMegaOctets
			Counter,
		  axsIfStatsOutUcastMegaPkts
			Counter,
		  axsIfStatsOutMulticastMegaPkts
			Counter,
		  axsIfStatsOutBroadcastMegaPkts
			Counter,
		  axsIfStatsHighSpeed
			Counter
		}

axsIfStatsIndex OBJECT-TYPE
	SYNTAX  INTEGER
	MAX-ACCESS  not-accessible
	STATUS  current
	DESCRIPTION
		"This object value is same as Ifindex which interface index
		of a system."
	::= { axsIfStatsEntry 1 }

axsIfStatsName OBJECT-TYPE
	SYNTAX  DisplayString
	MAX-ACCESS  read-only
	STATUS  current
	DESCRIPTION
		"Interfaces name. Same as ifDescr."
	::= { axsIfStatsEntry 2 }

axsIfStatsInMegaOctets OBJECT-TYPE
	SYNTAX  Counter
	MAX-ACCESS  read-only
	STATUS  current
	DESCRIPTION
		"Number of octets that received on the interface. This value is
		displayed in mega-octets(M). Value of 0 through 999,999 are rounded
		down."
	::= { axsIfStatsEntry 3 }

axsIfStatsInUcastMegaPkts OBJECT-TYPE
	SYNTAX  Counter
	MAX-ACCESS  read-only
	STATUS  current
	DESCRIPTION
		"Number of subnetwork-unicast packets that received on the interface.
		This value is displayed in mega-packets(M).Value of 0 through 999,999
		are rounded down."
	::= { axsIfStatsEntry 4 }

axsIfStatsInMulticastMegaPkts OBJECT-TYPE
	SYNTAX  Counter
	MAX-ACCESS  read-only
	STATUS  current
	DESCRIPTION
		"Number of multicast mega-packets that received on the interface.
		this value is displayed in mega-packets(M).Value of 0 through 999,999
		are rounded down."
	::= { axsIfStatsEntry 5 }


axsIfStatsInBroadcastMegaPkts OBJECT-TYPE
	SYNTAX  Counter
	MAX-ACCESS  read-only
	STATUS  current
	DESCRIPTION
		"The number of non-unicast packets delivered to a higher-layer
		protocol. The value is displayed in mega-packets (M). Value of 0
		through 999,999 are rounded down. "
	::= { axsIfStatsEntry 6 }

axsIfStatsOutMegaOctets OBJECT-TYPE
	SYNTAX  Counter
	MAX-ACCESS  read-only
	STATUS  current
	DESCRIPTION
		"The total number of octets transmitted out of the interface.
		The value is displayed in mega-octets(M). Value of 0 through 999,999
		are rounded down."
	::= { axsIfStatsEntry 7 }

axsIfStatsOutUcastMegaPkts OBJECT-TYPE
	SYNTAX  Counter
	MAX-ACCESS  read-only
	STATUS  current
	DESCRIPTION
		"The total number of packets that higher-level protocols requested
		be transmitted to a subnetwork-unicast address.The value is displayed
		in mega packets(M). Value of 0 through 999,999 are rounded down."
	::= { axsIfStatsEntry 8 }

axsIfStatsOutMulticastMegaPkts OBJECT-TYPE
	SYNTAX  Counter
	MAX-ACCESS  read-only
	STATUS  current
	DESCRIPTION
		"Number of multicast packets that transmitted on the interface.
		This value is displayed in mega-packets(M). Value of 0 through
		999,999 are rounded down."
	::= { axsIfStatsEntry 9 }

axsIfStatsOutBroadcastMegaPkts OBJECT-TYPE
	SYNTAX  Counter
	MAX-ACCESS  read-only
	STATUS  current
	DESCRIPTION
		"Number of broadcast packets that transmitted on the interface.
		This value is displayed in mega-packets(M). Value of 0 through
		999,999 are rounded down. "
	::= { axsIfStatsEntry 10 }

axsIfStatsHighSpeed OBJECT-TYPE
	SYNTAX  Counter
	MAX-ACCESS  read-only
	STATUS  current
	DESCRIPTION
		"A circuit speed.This value is displayed in mega-bps[Mbps].
		Round off the 1,000,000bps. "
	::= { axsIfStatsEntry 11 }

--  QoS interface statistics Variables

axsEtherTxQoSStatsTable OBJECT-TYPE
	SYNTAX  SEQUENCE OF AxsEtherTxQoSStatsEntry
	MAX-ACCESS  not-accessible
	STATUS  current
	DESCRIPTION
		"A collection of QoS statistics kept for a particular
		Ethernet interface."
	::= { axsEtherTxQoS 1 }

axsEtherTxQoSStatsEntry OBJECT-TYPE
	SYNTAX  AxsEtherTxQoSStatsEntry
	MAX-ACCESS  not-accessible
	STATUS  current
	DESCRIPTION
		"An entry containing QoS statistics for a particular 
		Ethernet interface."
    INDEX { axsEtherTxQoSStatsIndex }
	::= { axsEtherTxQoSStatsTable 1 }

	AxsEtherTxQoSStatsEntry ::=
		SEQUENCE {
            axsEtherTxQoSStatsIndex	INTEGER,
            axsEtherTxQoSStatsMaxQnum	INTEGER,
            axsEtherTxQoSStatsLimitQlen	INTEGER,
            axsEtherTxQoSStatsTotalOutFrames	Counter,
            axsEtherTxQoSStatsTotalOutBytesHigh	Counter,
            axsEtherTxQoSStatsTotalOutBytesLow	Counter,
            axsEtherTxQoSStatsTotalDiscardFrames	Counter
		}

axsEtherTxQoSStatsIndex OBJECT-TYPE
	SYNTAX  INTEGER
	MAX-ACCESS  not-accessible
	STATUS  current
	DESCRIPTION
		"Identified by a particular value of this
		index is same value of ifIndex.Its value ranges
		between 1 and the value of ifNumber."
	::= { axsEtherTxQoSStatsEntry 1 }

axsEtherTxQoSStatsMaxQnum OBJECT-TYPE
	SYNTAX  INTEGER
	MAX-ACCESS  read-only
	STATUS  current
	DESCRIPTION
		"Max length of queue for an ethernet interface."
	::= { axsEtherTxQoSStatsEntry 2 }

axsEtherTxQoSStatsLimitQlen OBJECT-TYPE
	SYNTAX  INTEGER
	MAX-ACCESS  read-only
	STATUS  current
	DESCRIPTION
		"The limit length of outband queue for an ethernet interface."
	::= { axsEtherTxQoSStatsEntry 3 }

axsEtherTxQoSStatsTotalOutFrames OBJECT-TYPE
	SYNTAX  Counter
	MAX-ACCESS  read-only
	STATUS  current
	DESCRIPTION
		"The total number of  packets transmitted out of the
		interface."
	::= { axsEtherTxQoSStatsEntry 4 }

axsEtherTxQoSStatsTotalOutBytesHigh OBJECT-TYPE
	SYNTAX  Counter
	MAX-ACCESS  read-only
	STATUS  current
	DESCRIPTION
		"The total number of octets transmitted out of the
		interface."
	::= { axsEtherTxQoSStatsEntry 5 }

axsEtherTxQoSStatsTotalOutBytesLow OBJECT-TYPE
	SYNTAX  Counter
	MAX-ACCESS  read-only
	STATUS  current
	DESCRIPTION
		"The total number of octets transmitted out of the
		interface."
	::= { axsEtherTxQoSStatsEntry 6 }

axsEtherTxQoSStatsTotalDiscardFrames OBJECT-TYPE
	SYNTAX  Counter
	MAX-ACCESS  read-only
	STATUS  current
	DESCRIPTION
		"The number of outbound packets which were chosen
		to be discarded ."
	::= { axsEtherTxQoSStatsEntry 7 }

axsEtherTxQoSStatsQueueTable OBJECT-TYPE
	SYNTAX  SEQUENCE OF AxsEtherTxQoSStatsQueueEntry
	MAX-ACCESS  not-accessible
	STATUS  current
	DESCRIPTION
		"A collection of priority queue statistics."
	::= { axsEtherTxQoS 2 }

axsEtherTxQoSStatsQueueEntry OBJECT-TYPE
	SYNTAX  AxsEtherTxQoSStatsQueueEntry
	MAX-ACCESS  not-accessible
	STATUS  current
	DESCRIPTION
		"A entry of priority queue statistics."
    INDEX { axsEtherTxQoSStatsQueueIndex , axsEtherTxQoSStatsQueueQueIndex }
	::= { axsEtherTxQoSStatsQueueTable 1 }

	AxsEtherTxQoSStatsQueueEntry ::=
		SEQUENCE {
            axsEtherTxQoSStatsQueueIndex	        INTEGER,
            axsEtherTxQoSStatsQueueQueIndex	INTEGER,
            axsEtherTxQoSStatsQueueQlen	        INTEGER,
            axsEtherTxQoSStatsQueueMaxQlen	INTEGER,
            axsEtherTxQoSStatsQueueDiscardFramesClass1	Counter64,
            axsEtherTxQoSStatsQueueDiscardFramesClass2	Counter64,
            axsEtherTxQoSStatsQueueDiscardFramesClass3	Counter64,
            axsEtherTxQoSStatsQueueDiscardFramesClass4	Counter64
		}

axsEtherTxQoSStatsQueueIndex OBJECT-TYPE
	SYNTAX  INTEGER
	MAX-ACCESS  not-accessible
	STATUS  current
	DESCRIPTION
		"Identified by a particular value of this
		index is same value of ifIndex.Its value ranges
		between 1 and the value of ifNumber."
	::= { axsEtherTxQoSStatsQueueEntry 1 }

axsEtherTxQoSStatsQueueQueIndex OBJECT-TYPE
	SYNTAX  INTEGER
	MAX-ACCESS  not-accessible
	STATUS  current
	DESCRIPTION
		"An index that uniquely identifies the particular
		queue.Its value ranges between 1 and the value of
		axsEtherTxQoSStatsMaxQnum."
	::= { axsEtherTxQoSStatsQueueEntry 2 }

axsEtherTxQoSStatsQueueQlen OBJECT-TYPE
	SYNTAX  INTEGER
	MAX-ACCESS  read-only
	STATUS  current
	DESCRIPTION
		"A length of outbound priority queue for a interface."
	::= { axsEtherTxQoSStatsQueueEntry 3 }

axsEtherTxQoSStatsQueueMaxQlen OBJECT-TYPE
	SYNTAX  INTEGER
	MAX-ACCESS  read-only
	STATUS  current
	DESCRIPTION
		"Max length of outband priority queue for a interface since
		system was up."
	::= { axsEtherTxQoSStatsQueueEntry 4 }

axsEtherTxQoSStatsQueueDiscardFramesClass1 OBJECT-TYPE
	SYNTAX  Counter64
	MAX-ACCESS  read-only
	STATUS  current
	DESCRIPTION
		"The number of discard frames in the discard class 
		 1 of output priority queue."
	::= { axsEtherTxQoSStatsQueueEntry 5 }

axsEtherTxQoSStatsQueueDiscardFramesClass2 OBJECT-TYPE
	SYNTAX  Counter64
	MAX-ACCESS  read-only
	STATUS  current
	DESCRIPTION
		"The number of discard frames in the discard class 
		 2 of output priority queue."
	::= { axsEtherTxQoSStatsQueueEntry 6 }

axsEtherTxQoSStatsQueueDiscardFramesClass3 OBJECT-TYPE
	SYNTAX  Counter64
	MAX-ACCESS  read-only
	STATUS  current
	DESCRIPTION
		"The number of discard frames in the discard class 
		 3 of output priority queue."
	::= { axsEtherTxQoSStatsQueueEntry 7 }

axsEtherTxQoSStatsQueueDiscardFramesClass4 OBJECT-TYPE
	SYNTAX  Counter64
	MAX-ACCESS  read-only
	STATUS  current
	DESCRIPTION
		"The number of discard frames in the discard class 
		 4 of output priority queue."
	::= { axsEtherTxQoSStatsQueueEntry 8 }

--axsDHCP group Variables

axsDHCPAddrValue OBJECT-TYPE
	SYNTAX INTEGER
	MAX-ACCESS read-only
	STATUS current
	DESCRIPTION
		"The number of IP addresses which are available
		within this Router."
	::= { axsDHCP 1 }

axsDHCPFreeAddrValue OBJECT-TYPE
	SYNTAX INTEGER
	MAX-ACCESS read-only
	STATUS current
	DESCRIPTION
		"The number of IP addresses which are available
		within this Router. May be expressed as either
		an absolute value."
	::= { axsDHCP 2 }

--  axsGsrp Group

axsGsrpGroupTable OBJECT-TYPE
        SYNTAX  SEQUENCE OF AxsGsrpGroupEntry
        MAX-ACCESS  not-accessible
        STATUS  current
        DESCRIPTION
                "The table containing GSRP group information."
        ::= { axsGsrp 1 }

axsGsrpGroupEntry OBJECT-TYPE
        SYNTAX  AxsGsrpGroupEntry
        MAX-ACCESS  not-accessible
        STATUS  current
        DESCRIPTION
                "The list of GSRP group information."
    INDEX { axsGsrpGroupId }
        ::= { axsGsrpGroupTable 1 }

        AxsGsrpGroupEntry ::=
                SEQUENCE {
                    axsGsrpGroupId             INTEGER,
                    axsGsrpGroupRowStatus      RowStatus,
                    axsGsrpMacAddress          MacAddress,
                    axsGsrpAdvertiseHoldTime    INTEGER,
                    axsGsrpAdvertiseInterval    INTEGER,
                    axsGsrpSelectionPattern    INTEGER,
                    axsGsrpLayer3Redundancy    INTEGER
		}

axsGsrpGroupId OBJECT-TYPE
	SYNTAX  INTEGER
	MAX-ACCESS  not-accessible
	STATUS  current
	DESCRIPTION
		"GSRP group identifier."
	::= { axsGsrpGroupEntry 1 }

axsGsrpGroupRowStatus OBJECT-TYPE
	SYNTAX  RowStatus
	MAX-ACCESS  read-only
	STATUS  current
	DESCRIPTION
		"Valid/Invalid state of this entry. Valid(1) fixed"
	::= { axsGsrpGroupEntry 2 }

axsGsrpMacAddress OBJECT-TYPE
	SYNTAX  MacAddress
	MAX-ACCESS  read-only
	STATUS  current
	DESCRIPTION
		"The Media Access Control Address of this equipment."
	::= { axsGsrpGroupEntry 3 }

axsGsrpAdvertiseHoldTime OBJECT-TYPE
	SYNTAX  INTEGER
	MAX-ACCESS  read-only
	STATUS  current
	DESCRIPTION
		"Holding time of the Advertise frame (milli second)."
	::= { axsGsrpGroupEntry 4 }

axsGsrpAdvertiseInterval OBJECT-TYPE
	SYNTAX  INTEGER
	MAX-ACCESS  read-only
	STATUS  current
	DESCRIPTION
		"Interval between transmitting the Advertise frame (milli second)."
	::= { axsGsrpGroupEntry 5 }

axsGsrpSelectionPattern OBJECT-TYPE
	SYNTAX  INTEGER {
                ports-Priority-MAC(1),
                priority-Ports-MAC(2)
                }
	MAX-ACCESS  read-only
	STATUS  current
	DESCRIPTION
		"Master/Backup selection pattern. Ports-Priority-MAC(1)  Priority-Ports-MAC(2)"
	::= { axsGsrpGroupEntry 6 }

axsGsrpLayer3Redundancy OBJECT-TYPE
	SYNTAX  INTEGER {
                off(1),
                on(2)
                }
	MAX-ACCESS  read-only
	STATUS  current
	DESCRIPTION
		"The status of layer 3 redundancy-change."
	::= { axsGsrpGroupEntry 7 }

axsGsrpVlanGroupTable OBJECT-TYPE
        SYNTAX  SEQUENCE OF AxsGsrpVlanGroupEntry
        MAX-ACCESS  not-accessible
        STATUS  current
        DESCRIPTION
                "The table containing GSRP VLAN group information."
        ::= { axsGsrp 2 }

axsGsrpVlanGroupEntry OBJECT-TYPE
        SYNTAX  AxsGsrpVlanGroupEntry
        MAX-ACCESS  not-accessible
        STATUS  current
        DESCRIPTION
                "The list of GSRP VLAN group information."
    INDEX { axsGsrpGroupId, axsGsrpVlanGroupId }
        ::= { axsGsrpVlanGroupTable 1 }

        AxsGsrpVlanGroupEntry ::=
                SEQUENCE {
                    axsGsrpVlanGroupId                  INTEGER,
                    axsGsrpVlanGroupRowStatus           RowStatus,
                    axsGsrpState                        INTEGER,
                    axsGsrpPriority                     INTEGER,
                    axsGsrpActivePorts                  INTEGER,
                    axsGsrpTransitionToMasterCounts     INTEGER,
                    axsGsrpTransitionFromMasterCounts   INTEGER,
                    axsGsrpLastTransitionTime           TimeStamp,
		    axsGsrpVirtualMacAddress	       MacAddress
		}

axsGsrpVlanGroupId OBJECT-TYPE
	SYNTAX  INTEGER
	MAX-ACCESS  not-accessible
	STATUS  current
	DESCRIPTION
		"GSRP VLAN group number(1~8)"
	::= { axsGsrpVlanGroupEntry 1 }

axsGsrpVlanGroupRowStatus OBJECT-TYPE
	SYNTAX  RowStatus
	MAX-ACCESS  read-only
	STATUS  current
	DESCRIPTION
		"Valid/Invalid state of this entry. Valid(1) fixed"
	::= { axsGsrpVlanGroupEntry 2 }

axsGsrpState OBJECT-TYPE
	SYNTAX  INTEGER {
                backUp(1),
                backUp-Waiting(2),
                master(3),
                backUp-No-Neighbor(4),
		backUp-Lock(5)
                }
	MAX-ACCESS  read-only
	STATUS  current
	DESCRIPTION
		"The state of GSRP group.."
	::= { axsGsrpVlanGroupEntry 3 }

axsGsrpPriority OBJECT-TYPE
	SYNTAX  INTEGER
	MAX-ACCESS  read-only
	STATUS  current
	DESCRIPTION
		"Configured priority."
	::= { axsGsrpVlanGroupEntry 4 }

axsGsrpActivePorts OBJECT-TYPE
	SYNTAX  INTEGER
	MAX-ACCESS  read-only
	STATUS  current
	DESCRIPTION
		"The number of port which is link-up  in monitored port."
	::= { axsGsrpVlanGroupEntry 5 }

axsGsrpTransitionToMasterCounts OBJECT-TYPE
	SYNTAX  INTEGER
	MAX-ACCESS  read-only
	STATUS  current
	DESCRIPTION
		"The number of times which shifted to the master state from the backup state."
	::= { axsGsrpVlanGroupEntry 6 }

axsGsrpTransitionFromMasterCounts OBJECT-TYPE
	SYNTAX  INTEGER
	MAX-ACCESS  read-only
	STATUS  current
	DESCRIPTION
		"The number of times which shifted to the backup state from the master state."
	::= { axsGsrpVlanGroupEntry 7 }

axsGsrpLastTransitionTime OBJECT-TYPE
	SYNTAX  TimeStamp
	MAX-ACCESS  read-only
	STATUS  current
	DESCRIPTION
		"The last time at which changed in the master state from the backup state or in the backup state from the master state."
	::= { axsGsrpVlanGroupEntry 8 }

axsGsrpVirtualMacAddress OBJECT-TYPE
	SYNTAX  MacAddress
	MAX-ACCESS  read-only
	STATUS  current
	DESCRIPTION
		"The virtual Media Access Control address of the GSRP VLAN group. If the status of layer 3 redundancy-change is off, return 00 00 00 00 00 00"
	::= { axsGsrpVlanGroupEntry 9 }

axsGsrpNeighborGroupTable OBJECT-TYPE
        SYNTAX  SEQUENCE OF AxsGsrpNeighborGroupEntry
        MAX-ACCESS  not-accessible
        STATUS  current
        DESCRIPTION
                "The table containing stores the GSRP group information on facing equipment."
        ::= { axsGsrp 3 }

axsGsrpNeighborGroupEntry OBJECT-TYPE
        SYNTAX  AxsGsrpNeighborGroupEntry
        MAX-ACCESS  not-accessible
        STATUS  current
        DESCRIPTION
                "The table containing stores the GSRP group information on facing equipment."
    INDEX { axsGsrpNeighborGroupId, axsGsrpNeighborMacAddress }
        ::= { axsGsrpNeighborGroupTable 1 }

        AxsGsrpNeighborGroupEntry ::=
                SEQUENCE {
                    axsGsrpNeighborGroupId             INTEGER,
                    axsGsrpNeighborMacAddress          MacAddress,
                    axsGsrpNeighborAdvertiseHoldTime    INTEGER,
                    axsGsrpNeighborAdvertiseInterval    INTEGER,
                    axsGsrpNeighborSelectionPattern    INTEGER
		}

axsGsrpNeighborGroupId OBJECT-TYPE
	SYNTAX  INTEGER
	MAX-ACCESS  not-accessible
	STATUS  current
	DESCRIPTION
		"The GSRP group identifier on the facing equipment."
	::= { axsGsrpNeighborGroupEntry 1 }

axsGsrpNeighborMacAddress OBJECT-TYPE
	SYNTAX  MacAddress
	MAX-ACCESS  not-accessible
	STATUS  current
	DESCRIPTION
		"The Media Access Control Address of the facing equipment."
	::= { axsGsrpNeighborGroupEntry 2 }

axsGsrpNeighborAdvertiseHoldTime OBJECT-TYPE
	SYNTAX  INTEGER
	MAX-ACCESS  read-only
	STATUS  current
	DESCRIPTION
		"Holding time of the Advertise frame on opposite equipment (milli second)."
	::= { axsGsrpNeighborGroupEntry 3 }

axsGsrpNeighborAdvertiseInterval OBJECT-TYPE
	SYNTAX  INTEGER
	MAX-ACCESS  read-only
	STATUS  current
	DESCRIPTION
		"Interval between transmitting the Advertise frame on the facing equipment (milli second)."
	::= { axsGsrpNeighborGroupEntry 4 }

axsGsrpNeighborSelectionPattern OBJECT-TYPE
	SYNTAX  INTEGER {
                port-Priority-MAC(1),
                priority-Port-MAC(2)
                }
	MAX-ACCESS  read-only
	STATUS  current
	DESCRIPTION
		"Master/Backup selection pattern on the facing equipment. Ports-Priority-MAC(1)  Priority-Ports-MAC(2)"
	::= { axsGsrpNeighborGroupEntry 5 }

axsGsrpNeighborVlanGroupTable OBJECT-TYPE
        SYNTAX  SEQUENCE OF AxsGsrpNeighborVlanGroupEntry
        MAX-ACCESS  not-accessible
        STATUS  current
        DESCRIPTION
                "The table containing the GSRP VLAN group information on facing equipment."
        ::= { axsGsrp 4 }

axsGsrpNeighborVlanGroupEntry OBJECT-TYPE
        SYNTAX  AxsGsrpNeighborVlanGroupEntry
        MAX-ACCESS  not-accessible
        STATUS  current
        DESCRIPTION
                "The table containing the GSRP VLAN group information on facing equipment."
    INDEX { axsGsrpNeighborGroupId, axsGsrpNeighborVlanGroupId, axsGsrpNeighborMacAddress }
        ::= { axsGsrpNeighborVlanGroupTable 1 }

        AxsGsrpNeighborVlanGroupEntry ::=
                SEQUENCE {
                    axsGsrpNeighborVlanGroupId    INTEGER,
                    axsGsrpNeighborState          INTEGER,
                    axsGsrpNeighborPriority       INTEGER,
                    axsGsrpNeighborActivePorts    INTEGER
		}

axsGsrpNeighborVlanGroupId OBJECT-TYPE
	SYNTAX  INTEGER
	MAX-ACCESS  not-accessible
	STATUS  current
	DESCRIPTION
		"GSRP VLAN group number on the facing equipment (1~8)."
	::= { axsGsrpNeighborVlanGroupEntry 1 }

axsGsrpNeighborState OBJECT-TYPE
	SYNTAX  INTEGER {
                backUp(1),
                backUp-Waiting(2),
                master(3),
                backUp-No-Neighbor(4),
                backUp-Lock(5)
                }
	MAX-ACCESS  not-accessible
	STATUS  current
	DESCRIPTION
		"The state of GSRP group on the facing equipment."
	::= { axsGsrpNeighborVlanGroupEntry 2 }

axsGsrpNeighborPriority OBJECT-TYPE
	SYNTAX  INTEGER
	MAX-ACCESS  read-only
	STATUS  current
	DESCRIPTION
		"Configured priority on the facing equipment."
	::= { axsGsrpNeighborVlanGroupEntry 3 }

axsGsrpNeighborActivePorts OBJECT-TYPE
	SYNTAX  INTEGER
	MAX-ACCESS  read-only
	STATUS  current
	DESCRIPTION
		"The number of port which is link-up  in monitored port on the facing equipment."
	::= { axsGsrpNeighborVlanGroupEntry 4 }

--  axsFdb group

axsFdbCounterTable OBJECT-TYPE
	SYNTAX  SEQUENCE OF AxsFdbCounterEntry
	MAX-ACCESS  not-accessible
	STATUS  current
	DESCRIPTION
		"The table of FDB information."
	::= { axsFdb 1 }

axsFdbCounterEntry OBJECT-TYPE
	SYNTAX  AxsFdbCounterEntry
	MAX-ACCESS  not-accessible
	STATUS  current
	DESCRIPTION
		"The entry of FDB information."
    INDEX { axsFdbCounterNifIndex, axsFdbCounterLineIndex }
	::= { axsFdbCounterTable 1 }

	AxsFdbCounterEntry ::=
		SEQUENCE {
			axsFdbCounterNifIndex		INTEGER,
			axsFdbCounterLineIndex		INTEGER,
			axsFdbCounterCounts		Counter32,
			axsFdbCounterType		INTEGER,
			axsFdbCounterLimits		Counter32
		}

axsFdbCounterNifIndex OBJECT-TYPE
	SYNTAX  INTEGER
	MAX-ACCESS  not-accessible
	STATUS  current
	DESCRIPTION
		"Identified by a particular value of this index
		is same value of NIF.Its value ranges between 1
		and the value of ax1230sNifBoardNumber."
	::= { axsFdbCounterEntry 1 }

axsFdbCounterLineIndex OBJECT-TYPE
	SYNTAX  INTEGER
	MAX-ACCESS  not-accessible
	STATUS  current
	DESCRIPTION
		"Identified by a particular value of this index
		is same value of Physical Line.Its value ranges
		between 1 and the value of ax1230sNifLineNumber."
	::= { axsFdbCounterEntry 2 }

axsFdbCounterCounts OBJECT-TYPE
	SYNTAX  Counter32
	MAX-ACCESS  read-only
	STATUS  current
	DESCRIPTION
		"The number of FDB entries learned on the port."
	::= { axsFdbCounterEntry 3 }

axsFdbCounterType OBJECT-TYPE
	SYNTAX  INTEGER	{
				unlimited(0),
				limited-and-Forward(1),
				limited-and-Discard(2)
			}
	MAX-ACCESS  read-only
	STATUS  current
	DESCRIPTION
		"The type of FDB entries learning."
	::= { axsFdbCounterEntry 4 }

axsFdbCounterLimits OBJECT-TYPE
	SYNTAX  Counter32
	MAX-ACCESS  read-only
	STATUS  current
	DESCRIPTION
		"The maximum number of FDB entries that can be learned on the port."
	::= { axsFdbCounterEntry 5 }

--  axsVlan group

axsVBBaseTable OBJECT-TYPE
	SYNTAX  SEQUENCE OF AxsVBBaseEntry
	MAX-ACCESS  not-accessible
	STATUS  current
	DESCRIPTION
		"An information table of dot1dBase by VLAN units."
	::= { axsVlanBridgeBase 1 }

axsVBBaseEntry OBJECT-TYPE
	SYNTAX  AxsVBBaseEntry
	MAX-ACCESS  not-accessible
	STATUS  current
	DESCRIPTION
		"An informatin entry of every VLAN ID of axsVBBaseTable."
    INDEX { axsVBBaseIndex }
	::= { axsVBBaseTable 1 }

	AxsVBBaseEntry ::=
		SEQUENCE {
		    axsVBBaseIndex 			VlanIndex,
		    axsVBBaseBridgeAddress 		MacAddress,
		    axsVBBaseNumPorts 			INTEGER,
		    axsVBBaseType  			INTEGER,
		    axsVBBaseVlanIfIndex   		INTEGER,
		    axsVBBaseVlanType    		INTEGER,
		    axsVBBaseVlanID     			VlanIdOrZero,		
		    axsVBBaseAssociatedPrimaryVlan  	VlanIdOrZero,
		    axsVBBaseIfStatus      		INTEGER,
		    axsVBBaseLastChange       		TimeTicks,
		    axsVBBasePrivateVlanType       	INTEGER
                }

axsVBBaseIndex OBJECT-TYPE
	SYNTAX  VlanIndex
	MAX-ACCESS  read-only
	STATUS  current
	DESCRIPTION
		"VLAN ID."
	::= { axsVBBaseEntry 1 }

axsVBBaseBridgeAddress OBJECT-TYPE
	SYNTAX  MacAddress
	MAX-ACCESS  read-only
	STATUS  current
	DESCRIPTION
		"MAC address of VLAN."
	::= { axsVBBaseEntry 2 }

axsVBBaseNumPorts OBJECT-TYPE
	SYNTAX  INTEGER
	MAX-ACCESS  read-only
	STATUS  current
	DESCRIPTION
		"The number of ports set at VLAN."
	::= { axsVBBaseEntry 3 }

axsVBBaseType OBJECT-TYPE
	SYNTAX  INTEGER {
		unknown(1),
		transparent-only(2),
		sourceroute-only(3),
		srt(4)
	      }
	MAX-ACCESS  read-only
	STATUS  current
	DESCRIPTION
		"A bridging type VLAN may perform."
	::= { axsVBBaseEntry 4 }

axsVBBaseVlanIfIndex OBJECT-TYPE
	SYNTAX  INTEGER
	MAX-ACCESS  read-only
	STATUS  current
	DESCRIPTION
		"Value of ifIndex of interface of VLAN."
	::= { axsVBBaseEntry 5 }

axsVBBaseVlanType OBJECT-TYPE
	SYNTAX  INTEGER {
		port-based(1),
		mac-based(2),
		protocol-based(3),
		ipsubnet-based(4)
	      }
	MAX-ACCESS  read-only
	STATUS  current
	DESCRIPTION
		"VLAN type."
	::= { axsVBBaseEntry 6 }

axsVBBaseVlanID OBJECT-TYPE
	SYNTAX  VlanIdOrZero
	MAX-ACCESS  read-only
	STATUS  current
	DESCRIPTION
		"Value of VID of VLAN-TAG corresponding VLAN."
	::= { axsVBBaseEntry 7 }

axsVBBaseAssociatedPrimaryVlan OBJECT-TYPE
	SYNTAX  VlanIdOrZero
	MAX-ACCESS  read-only
	STATUS  current
	DESCRIPTION
		"Returns VLAN ID of Primary VLAN when private VLAN is used and 
		 the same VLAN is set at secondary VLAN."
	::= { axsVBBaseEntry 8 }

axsVBBaseIfStatus OBJECT-TYPE
	SYNTAX  INTEGER {
		up(1),
		down(2)
	      }
	MAX-ACCESS  read-only
	STATUS  current
	DESCRIPTION
		"Status of interface against upper level protocol of VLAN."
	::= { axsVBBaseEntry 9 }

axsVBBaseLastChange OBJECT-TYPE
	SYNTAX  TimeTicks
	MAX-ACCESS  read-only
	STATUS  current
	DESCRIPTION
		"Value of sysUpTime which is set when VLAN topology changes."
	::= { axsVBBaseEntry 10 }

axsVBBasePrivateVlanType OBJECT-TYPE
	SYNTAX  INTEGER {
		normal(1),
		primary(2),
		isolated(3),
		community(4)
	      }
	MAX-ACCESS  read-only
	STATUS  current
	DESCRIPTION
		"A private VLAN type of VLAN."
	::= { axsVBBaseEntry 11 }

axsVBBasePortTable OBJECT-TYPE
	SYNTAX  SEQUENCE OF AxsVBBasePortEntry
	MAX-ACCESS  not-accessible
	STATUS  current
	DESCRIPTION
		"An information table of dot1dBasePortTable by VLAN units."
	::= { axsVlanBridgeBase 2 }

axsVBBasePortEntry OBJECT-TYPE
	SYNTAX  AxsVBBasePortEntry
	MAX-ACCESS  not-accessible
	STATUS  current
	DESCRIPTION
		"A configuration entry of axsVBBaseTable."
    INDEX { axsVBBasePortIndex, axsVBBasePort }
	::= { axsVBBasePortTable 1 }

	AxsVBBasePortEntry ::=
		SEQUENCE {
		    axsVBBasePortIndex       		VlanIndex,
		    axsVBBasePort	       		INTEGER,
		    axsVBBasePortIfIndex			INTEGER,
		    axsVBBasePortCircuit			OBJECT IDENTIFIER,
		    axsVBBasePortDelayExceededDiscards	Counter,
		    axsVBBasePortMtuExceededDiscards		Counter,
		    axsVBBasePortState			INTEGER,
		    axsVBBasePortTaggedState		INTEGER,
		    axsVBBasePortTranslatedTagID		VlanIdOrZero
                }

axsVBBasePortIndex OBJECT-TYPE
	SYNTAX  VlanIndex
	MAX-ACCESS  read-only
	STATUS  current
	DESCRIPTION
		"VLAN ID."
	::= { axsVBBasePortEntry 1 }

axsVBBasePort OBJECT-TYPE
	SYNTAX  INTEGER
	MAX-ACCESS  read-only
	STATUS  current
	DESCRIPTION
		"Port number of ports set at VLAN."
	::= { axsVBBasePortEntry 2 }

axsVBBasePortIfIndex OBJECT-TYPE
	SYNTAX  INTEGER
	MAX-ACCESS  read-only
	STATUS  current
	DESCRIPTION
		"Value of ifIndex corresponding ports set at VLAN."
	::= { axsVBBasePortEntry 3 }

axsVBBasePortCircuit OBJECT-TYPE
	SYNTAX  OBJECT IDENTIFIER
	MAX-ACCESS  read-only
	STATUS  current
	DESCRIPTION
		"Identifier which identifieds ports when VLAN ports
		 have the same value as axsVBBasePortIfIndex."
	::= { axsVBBasePortEntry 4 }

axsVBBasePortDelayExceededDiscards OBJECT-TYPE
	SYNTAX  Counter
	MAX-ACCESS  read-only
	STATUS  current
	DESCRIPTION
		"Total number of discard frame caused by passing delay occured at VLAN ports."
	::= { axsVBBasePortEntry 5 }

axsVBBasePortMtuExceededDiscards OBJECT-TYPE
	SYNTAX  Counter
	MAX-ACCESS  read-only
	STATUS  current
	DESCRIPTION
		"Total number of discard frame caused by data over flow occured at VLAN ports."
	::= { axsVBBasePortEntry 6 }

axsVBBasePortState OBJECT-TYPE
	SYNTAX  INTEGER {
		disabled(1),
		blocking(2),
		listening(3),
		learning(4),
		forwarding(5),
		broken(6),
		fix-forwarding(7)
	      }
	MAX-ACCESS  read-only
	STATUS  current
	DESCRIPTION
		"STP port status of port set at VLAN."
	::= { axsVBBasePortEntry 7 }

axsVBBasePortTaggedState OBJECT-TYPE
	SYNTAX  INTEGER {
		untagged(1),
		tagged(2)
            }
	MAX-ACCESS  read-only
	STATUS  current
	DESCRIPTION
		"Status of VLAN-TAG configuration of ports set at VLAN."
	::= { axsVBBasePortEntry 8 }

axsVBBasePortTranslatedTagID OBJECT-TYPE
	SYNTAX  VlanIdOrZero
	MAX-ACCESS  read-only
	STATUS  current
	DESCRIPTION
		"Translated ID of VLAN when TAG translation is set."
	::= { axsVBBasePortEntry 9 }

axsVBStpTable OBJECT-TYPE
	SYNTAX  SEQUENCE OF AxsVBStpEntry
	MAX-ACCESS  not-accessible
	STATUS  current
	DESCRIPTION
		"An information table of dot1dStpTable by VLAN units."
	::= { axsVlanBridgeStp 1 }

axsVBStpEntry OBJECT-TYPE
	SYNTAX  AxsVBStpEntry
	MAX-ACCESS  not-accessible
	STATUS  current
	DESCRIPTION
		"A configuration entry of axsVBStpTable."
    INDEX { axsVBStpIndex }
	::= { axsVBStpTable 1 }

	AxsVBStpEntry ::=
		SEQUENCE {
		    axsVBStpIndex 			VlanIndex,
		    axsVBStpProtocolSpecification 	INTEGER,
		    axsVBStpPriority 			INTEGER,
		    axsVBStpTimeSinceTopologyChange	TimeTicks,
		    axsVBStpTopChanges			Counter,
		    axsVBStpDesignatedRoot		BridgeId,
		    axsVBStpRootCost			INTEGER,
		    axsVBStpRootPort			INTEGER,
		    axsVBStpMaxAge			Timeout,
		    axsVBStpHelloTime			Timeout,
		    axsVBStpHoldTime			INTEGER,
		    axsVBStpForwardDelay			Timeout,
		    axsVBStpBridgeMaxAge 		Timeout,
		    axsVBStpBridgeHelloTime 		Timeout,
		    axsVBStpBridgeForwardDelay 		Timeout
                }

axsVBStpIndex OBJECT-TYPE
	SYNTAX  VlanIndex
	MAX-ACCESS  read-only
	STATUS  current
	DESCRIPTION
		"VLAN ID."
	::= { axsVBStpEntry 1 }

axsVBStpProtocolSpecification OBJECT-TYPE
	SYNTAX  INTEGER {
		unknown(1),
		decLb100(2),
		ieee8021d(3),
		ieee8021w(4)
	      }
	MAX-ACCESS  read-only
	STATUS  current
	DESCRIPTION
		"A kind of spanning tree protocol by VLAN units."
	::= { axsVBStpEntry 2 }

axsVBStpPriority OBJECT-TYPE
	SYNTAX  INTEGER
	MAX-ACCESS  read-only
	STATUS  current
	DESCRIPTION
		"Priority value of spanning tree by VLAN units."
	::= { axsVBStpEntry 3 }

axsVBStpTimeSinceTopologyChange OBJECT-TYPE
	SYNTAX  TimeTicks
	MAX-ACCESS  read-only
	STATUS  current
	DESCRIPTION
		"Elapsed time since topology change of spanning tree by VLAN units."
	::= { axsVBStpEntry 4 }

axsVBStpTopChanges OBJECT-TYPE
	SYNTAX  Counter
	MAX-ACCESS  read-only
	STATUS  current
	DESCRIPTION
		"The number of times of topology changes of spanning tree by VLAN units."
	::= { axsVBStpEntry 5 }

axsVBStpDesignatedRoot OBJECT-TYPE
	SYNTAX  BridgeId
	MAX-ACCESS  read-only
	STATUS  current
	DESCRIPTION
		"Root bridge identifier of spanning tree by VLAN units."
	::= { axsVBStpEntry 6 }

axsVBStpRootCost OBJECT-TYPE
	SYNTAX  INTEGER
	MAX-ACCESS  read-only
	STATUS  current
	DESCRIPTION
		"Root path cost kept by spanning tree by VLAN units."
	::= { axsVBStpEntry 7 }

axsVBStpRootPort OBJECT-TYPE
	SYNTAX  INTEGER
	MAX-ACCESS  read-only
	STATUS  current
	DESCRIPTION
		"Root port value kept by spanning tree by VLAN units."
	::= { axsVBStpEntry 8 }

axsVBStpMaxAge OBJECT-TYPE
	SYNTAX  Timeout
	MAX-ACCESS  read-only
	STATUS  current
	DESCRIPTION
		"Maximum aging time kept by spanning tree by VLAN units."
	::= { axsVBStpEntry 9 }

axsVBStpHelloTime OBJECT-TYPE
	SYNTAX  Timeout
	MAX-ACCESS  read-only
	STATUS  current
	DESCRIPTION
		"Hello time kept by spanning tree by VLAN units."
	::= { axsVBStpEntry 10 }

axsVBStpHoldTime OBJECT-TYPE
	SYNTAX  INTEGER
	MAX-ACCESS  read-only
	STATUS  current
	DESCRIPTION
		"Hold time kept by spanning tree by VLAN units."
	::= { axsVBStpEntry 11 }

axsVBStpForwardDelay OBJECT-TYPE
	SYNTAX  Timeout
	MAX-ACCESS  read-only
	STATUS  current
	DESCRIPTION
		"Transfer delay time kept by spanning tree by VLAN units."
	::= { axsVBStpEntry 12 }

axsVBStpBridgeMaxAge OBJECT-TYPE
	SYNTAX  Timeout
	MAX-ACCESS  read-only
	STATUS  current
	DESCRIPTION
		"Maximum aging time used when spanning tree acts as a root bridge by VLAN units."
	::= { axsVBStpEntry 13 }

axsVBStpBridgeHelloTime OBJECT-TYPE
	SYNTAX  Timeout
	MAX-ACCESS  read-only
	STATUS  current
	DESCRIPTION
		"Hello time used when spanning tree act as a root bridge by VLAN units."
	::= { axsVBStpEntry 14 }

axsVBStpBridgeForwardDelay OBJECT-TYPE
	SYNTAX  Timeout
	MAX-ACCESS  read-only
	STATUS  current
	DESCRIPTION
		"Transfer delay time used when spanning tree act as a root bridge by VLAN units."
	::= { axsVBStpEntry 15 }

axsVBStpPortTable OBJECT-TYPE
	SYNTAX  SEQUENCE OF AxsVBStpPortEntry
	MAX-ACCESS  not-accessible
	STATUS  current
	DESCRIPTION
		"An information table of dot1dStpPortTable by VLAN units."
	::= { axsVlanBridgeStp 2 }

axsVBStpPortEntry OBJECT-TYPE
	SYNTAX  AxsVBStpPortEntry
	MAX-ACCESS  not-accessible
	STATUS  current
	DESCRIPTION
		"A configuration entry of axsVBStpPortTable."
        INDEX { axsVBStpPortIndex, axsVBStpPort }
	::= { axsVBStpPortTable 1 }

	AxsVBStpPortEntry ::=
		SEQUENCE {
		    axsVBStpPortIndex			VlanIndex,
		    axsVBStpPort				INTEGER,
		    axsVBStpPortPriority			INTEGER,
		    axsVBStpPortState			INTEGER,
		    axsVBStpPortEnable			INTEGER,
		    axsVBStpPortPathCost			INTEGER,
		    axsVBStpPortDesignatedRoot		BridgeId,
		    axsVBStpPortDesignatedCost		INTEGER,
		    axsVBStpPortDesignatedBridge		BridgeId,
		    axsVBStpPortDesignatedPort		OCTET STRING,
		    axsVBStpPortForwardTransitions	Counter
                }

axsVBStpPortIndex OBJECT-TYPE
	SYNTAX  VlanIndex
	MAX-ACCESS  read-only
	STATUS  current
	DESCRIPTION
		"VLAN ID."
	::= { axsVBStpPortEntry 1 }

axsVBStpPort OBJECT-TYPE
	SYNTAX  INTEGER
	MAX-ACCESS  read-only
	STATUS  current
	DESCRIPTION
		"Port number corresponding configuration entry."
	::= { axsVBStpPortEntry 2 }

axsVBStpPortPriority OBJECT-TYPE
	SYNTAX  INTEGER
	MAX-ACCESS  read-only
	STATUS  current
	DESCRIPTION
		"Priority of port by VLAN units."
	::= { axsVBStpPortEntry 3 }

axsVBStpPortState OBJECT-TYPE
	SYNTAX  INTEGER {
		disabled(1),
		blocking(2),
		listening(3),
		learning(4),
		forwarding(5),
		broken(6)
	      }
	MAX-ACCESS  read-only
	STATUS  current
	DESCRIPTION
		"Present status of port by VLAN units."
	::= { axsVBStpPortEntry 4 }

axsVBStpPortEnable OBJECT-TYPE
	SYNTAX  INTEGER {
		enabled(1),
		disabled(2)
	      }
	MAX-ACCESS  read-only
	STATUS  current
	DESCRIPTION
		"Value whether spanning tree is enabled or not at the port by VLAN units."
	::= { axsVBStpPortEntry 5 }

axsVBStpPortPathCost OBJECT-TYPE
	SYNTAX  INTEGER
	MAX-ACCESS  read-only
	STATUS  current
	DESCRIPTION
		"Path cost value of the port by VLAN units."
	::= { axsVBStpPortEntry 6 }

axsVBStpPortDesignatedRoot OBJECT-TYPE
	SYNTAX  BridgeId
	MAX-ACCESS  read-only
	STATUS  current
	DESCRIPTION
		"Value of root bridge identifier by VLAN units stored in BPDU from specified bridge."
	::= { axsVBStpPortEntry 7 }

axsVBStpPortDesignatedCost OBJECT-TYPE
	SYNTAX  INTEGER
	MAX-ACCESS  read-only
	STATUS  current
	DESCRIPTION
		"Path cost value of specified port connected to the port by VLAN units."
	::= { axsVBStpPortEntry 8 }

axsVBStpPortDesignatedBridge OBJECT-TYPE
	SYNTAX  BridgeId
	MAX-ACCESS  read-only
	STATUS  current
	DESCRIPTION
		"Bridge identifier of bridge which this port regards as specified bridge by VLAN units."
	::= { axsVBStpPortEntry 9 }

axsVBStpPortDesignatedPort OBJECT-TYPE
	SYNTAX  OCTET STRING
	MAX-ACCESS  read-only
	STATUS  current
	DESCRIPTION
		"Port identifier of specified bridge connected to this port by VLAN units."
	::= { axsVBStpPortEntry 10 }

axsVBStpPortForwardTransitions OBJECT-TYPE
	SYNTAX  Counter
	MAX-ACCESS  read-only
	STATUS  current
	DESCRIPTION
		"The number of times of changes from learning status into forwarding status."
	::= { axsVBStpPortEntry 11 }

axsVBTpTable OBJECT-TYPE
	SYNTAX  SEQUENCE OF AxsVBTpEntry
	MAX-ACCESS  not-accessible
	STATUS  current
	DESCRIPTION
		"A dot1dTp information table by VLAN units."
	::= { axsVlanBridgeTp 1 }

axsVBTpEntry OBJECT-TYPE
	SYNTAX  AxsVBTpEntry
	MAX-ACCESS  not-accessible
	STATUS  current
	DESCRIPTION
		"A configuration entry of axsVBTpTable."
    INDEX { axsVBTpIndex }
	::= { axsVBTpTable 1 }

	AxsVBTpEntry ::=
		SEQUENCE {
		    axsVBTpIndex				VlanIndex,
		    axsVBTpLearnedEntryDiscards		Counter,
		    axsVBTpAgingTime			INTEGER
                }

axsVBTpIndex OBJECT-TYPE
	SYNTAX  VlanIndex
	MAX-ACCESS  read-only
	STATUS  current
	DESCRIPTION
		"VLAN ID."
	::= { axsVBTpEntry 1 }

axsVBTpLearnedEntryDiscards OBJECT-TYPE
	SYNTAX  Counter
	MAX-ACCESS  read-only
	STATUS  current
	DESCRIPTION
		"The number of discarded entries because of lack of
		 not-used domain in filtering data base."
	::= { axsVBTpEntry 2 }

axsVBTpAgingTime OBJECT-TYPE
	SYNTAX  INTEGER
	MAX-ACCESS  read-only
	STATUS  current
	DESCRIPTION
		"Time-out time to aging-out entry of filtering date base which is learned dynamically."
	::= { axsVBTpEntry 3 }

axsVBTpFdbTable OBJECT-TYPE
	SYNTAX  SEQUENCE OF AxsVBTpFdbEntry
	MAX-ACCESS  not-accessible
	STATUS  current
	DESCRIPTION
		"An information of dot1dTpFdbTable by VLAN units."
	::= { axsVlanBridgeTp 2 }

axsVBTpFdbEntry OBJECT-TYPE
	SYNTAX  AxsVBTpFdbEntry
	MAX-ACCESS  not-accessible
	STATUS  current
	DESCRIPTION
		"A configuration entry of axsVBTpFdbTable."
    INDEX { axsVBTpFdbIndex, axsVBTpFdbAddress }
	::= { axsVBTpFdbTable 1 }

	AxsVBTpFdbEntry ::=
		SEQUENCE {
		    axsVBTpFdbIndex			VlanIndex,
		    axsVBTpFdbAddress			MacAddress,
		    axsVBTpFdbPort			INTEGER,
		    axsVBTpFdbStatus			INTEGER
                }

axsVBTpFdbIndex OBJECT-TYPE
	SYNTAX  VlanIndex
	MAX-ACCESS  read-only
	STATUS  current
	DESCRIPTION
		"VLAN ID."
	::= { axsVBTpFdbEntry 1 }

axsVBTpFdbAddress OBJECT-TYPE
	SYNTAX  MacAddress
	MAX-ACCESS  read-only
	STATUS  current
	DESCRIPTION
		"Unicast MAC address of filtering data base entry."
	::= { axsVBTpFdbEntry 2 }

axsVBTpFdbPort OBJECT-TYPE
	SYNTAX  INTEGER
	MAX-ACCESS  read-only
	STATUS  current
	DESCRIPTION
		"Indicates that it hasn't learnt port number when
		 port number 0 receives frame having MAC address
		 as source address which axsVBTpFdbAddress indicates."
	::= { axsVBTpFdbEntry 3 }

axsVBTpFdbStatus OBJECT-TYPE
	SYNTAX  INTEGER {
		other(1),
		invalid(2),
		learned(3),
		self(4),
		mgmt(5)
	      }
	MAX-ACCESS  read-only
	STATUS  current
	DESCRIPTION
		"Status of filtering data base."
	::= { axsVBTpFdbEntry 4 }

axsVBTpPortTable OBJECT-TYPE
	SYNTAX  SEQUENCE OF AxsVBTpPortEntry
	MAX-ACCESS  not-accessible
	STATUS  current
	DESCRIPTION
		"An information table of dot1dTpPortTable by VLAN units."
	::= { axsVlanBridgeTp 3 }

axsVBTpPortEntry OBJECT-TYPE
	SYNTAX  AxsVBTpPortEntry
	MAX-ACCESS  not-accessible
	STATUS  current
	DESCRIPTION
		"An information entry of axsVBTpPortTable of ports."
    INDEX { axsVBTpPortIndex, axsVBTpPort }
	::= { axsVBTpPortTable 1 }

	AxsVBTpPortEntry ::=
		SEQUENCE {
		    axsVBTpPortIndex			VlanIndex,
		    axsVBTpPort				INTEGER,
		    axsVBTpPortMaxInfo			INTEGER,
		    axsVBTpPortInFrames 		Counter,
		    axsVBTpPortOutFrames 		Counter,
		    axsVBTpPortInDiscards  		Counter
                }

axsVBTpPortIndex OBJECT-TYPE
	SYNTAX  VlanIndex
	MAX-ACCESS  read-only
	STATUS  current
	DESCRIPTION
		"VLAN ID."
	::= { axsVBTpPortEntry 1 }

axsVBTpPort OBJECT-TYPE
	SYNTAX  INTEGER
	MAX-ACCESS  read-only
	STATUS  current
	DESCRIPTION
		"Port number that indicates which port management
		 information in the entry corresponds."
	::= { axsVBTpPortEntry 2 }

axsVBTpPortMaxInfo OBJECT-TYPE
	SYNTAX  INTEGER
	MAX-ACCESS  read-only
	STATUS  current
	DESCRIPTION
		"Maximum INFO field size of the port by VLAN units."
	::= { axsVBTpPortEntry 3 }

axsVBTpPortInFrames OBJECT-TYPE
	SYNTAX  Counter
	MAX-ACCESS  read-only
	STATUS  current
	DESCRIPTION
		"The number of reception frame of the port by VLAN units."
	::= { axsVBTpPortEntry 4 }

axsVBTpPortOutFrames OBJECT-TYPE
	SYNTAX  Counter
	MAX-ACCESS  read-only
	STATUS  current
	DESCRIPTION
		"The number of sending frame of the port by VLAN units."
	::= { axsVBTpPortEntry 5 }

axsVBTpPortInDiscards OBJECT-TYPE
	SYNTAX  Counter
	MAX-ACCESS  read-only
	STATUS  current
	DESCRIPTION
		"The number of reception frame of the port by VLAN units."
	::= { axsVBTpPortEntry 6 }

axsVBStaticTable OBJECT-TYPE
	SYNTAX  SEQUENCE OF AxsVBStaticEntry
	MAX-ACCESS  not-accessible
	STATUS  current
	DESCRIPTION
		"An information table of dot1dStaticTable by VLAN units."
	::= { axsVlanBridgeStatic 1 }

axsVBStaticEntry OBJECT-TYPE
	SYNTAX  AxsVBStaticEntry
	MAX-ACCESS  not-accessible
	STATUS  current
	DESCRIPTION
		"A configuration entry of axsVBStaticTable."
    INDEX { axsVBStaticIndex, axsVBStaticAddress }
	::= { axsVBStaticTable 1 }

	AxsVBStaticEntry ::=
		SEQUENCE {
		    axsVBStaticIndex			VlanIndex,
		    axsVBStaticAddress			MacAddress,
		    axsVBStaticReceivePort		INTEGER,
		    axsVBStaticAllowedToGoTo		OCTET STRING,		
		    axsVBStaticStatus 	 		INTEGER
		}

axsVBStaticIndex OBJECT-TYPE
	SYNTAX  VlanIndex
	MAX-ACCESS  read-only
	STATUS  current
	DESCRIPTION
		"VLAN ID."
	::= { axsVBStaticEntry 1 }

axsVBStaticAddress OBJECT-TYPE
	SYNTAX  MacAddress
	MAX-ACCESS  read-only
	STATUS  current
	DESCRIPTION
		"MAC address of eather unicast, group or broadcast."
	::= { axsVBStaticEntry 2 }

axsVBStaticReceivePort OBJECT-TYPE
	SYNTAX  INTEGER
	MAX-ACCESS  read-only
	STATUS  current
	DESCRIPTION
		"Reception port number which is applied the entry."
	::= { axsVBStaticEntry 3 }

axsVBStaticAllowedToGoTo OBJECT-TYPE
	SYNTAX  OCTET STRING
	MAX-ACCESS  read-only
	STATUS  current
	DESCRIPTION
		"Bit map of port indicating destination port when transfering
		 frame whose destination is MAC address kept by this entry"
	::= { axsVBStaticEntry 4 }

axsVBStaticStatus OBJECT-TYPE
	SYNTAX  INTEGER {
		other(1),
		invalid(2),
		permanent(3),
		deleteOnReset(4),
		deleteOnTimeout(5)
	      }
	MAX-ACCESS  read-only
	STATUS  current
	DESCRIPTION
		"Status of the entry."
	::= { axsVBStaticEntry 5 }

axsVlanBridgeMaxVlans OBJECT-TYPE
	SYNTAX  VlanIndex
	MAX-ACCESS  read-only
	STATUS  current
	DESCRIPTION
		"Maximum value of VLAN ID of this device."
	::= { axsVlanBridge 101 }

axsVlanBridgeMaxSpans OBJECT-TYPE
	SYNTAX  VlanIndex
	MAX-ACCESS  read-only
	STATUS  current
	DESCRIPTION
		"Maximum value of VLAN ID of VLAN which may operate
		 spanning tree in this device."
	::= { axsVlanBridge 102 }

axsVlanTagTranslationTable OBJECT-TYPE
	SYNTAX  SEQUENCE OF AxsVlanTagTranslationEntry
	MAX-ACCESS  not-accessible
	STATUS  current
	DESCRIPTION
		"The information table about a Tag conversion function"
	::= { axsVlanTagTranslation 1 }

axsVlanTagTranslationEntry OBJECT-TYPE
	SYNTAX  AxsVlanTagTranslationEntry
	MAX-ACCESS  not-accessible
	STATUS  current
	DESCRIPTION
		"The entry of the information table about a Tag conversion function"
    INDEX { axsVlanTagTranslationVlanId,axsVlanTagTranslationTranslatedId }
	::= { axsVlanTagTranslationTable 1 }

	AxsVlanTagTranslationEntry ::=
		SEQUENCE {
		    axsVlanTagTranslationVlanId		INTEGER,
		    axsVlanTagTranslationTranslatedId	INTEGER,
		    axsVlanTagTranslationPorts		PortList
                }

axsVlanTagTranslationVlanId OBJECT-TYPE
	SYNTAX  INTEGER
	MAX-ACCESS  read-only
	STATUS  current
	DESCRIPTION
		"VLAN ID which has set up the Tag conversion function"
	::= { axsVlanTagTranslationEntry 1 }

axsVlanTagTranslationTranslatedId OBJECT-TYPE
	SYNTAX  INTEGER
	MAX-ACCESS  read-only
	STATUS  current
	DESCRIPTION
		"Translated ID set up by the Tag conversion function"
	::= { axsVlanTagTranslationEntry 2 }

axsVlanTagTranslationPorts OBJECT-TYPE
	SYNTAX  PortList
	MAX-ACCESS  read-only
	STATUS  current
	DESCRIPTION
		"The port list which has set up the same Translated ID by the same VLAN by the Tag conversion function"
	::= { axsVlanTagTranslationEntry 3 }

--  OADP Group

axsOadpGlobalActive  OBJECT-TYPE
	SYNTAX  TruthValue
	MAX-ACCESS  read-only
	STATUS  current
	DESCRIPTION
		"Operation status of OADP function. Status set
		 by enable or disable in Oadp configuration.
		 enable : 1
		 disable: 2"
	::= { axsOadpGlobalInfo 1 }

axsOadpGlobalCdpActive  OBJECT-TYPE
	SYNTAX  TruthValue
	MAX-ACCESS  read-only
	STATUS  current
	DESCRIPTION
		"Operation status of CDP reception function.
		 Status whether cdp-listener is set or not in oadp configuration.
		 cdp-listener           : 1
		 cdp-listener is not set: 2"
	::= { axsOadpGlobalInfo 2 }

axsOadpGlobalMessageInterval OBJECT-TYPE
	SYNTAX  INTEGER
	MAX-ACCESS  read-only
	STATUS  current
	DESCRIPTION
		"Sending interval of OADP frame. The value of interval-time in oadp configuration."
	::= { axsOadpGlobalInfo 3 }

axsOadpGlobalHoldTime OBJECT-TYPE
	SYNTAX  INTEGER
	MAX-ACCESS  read-only
	STATUS  current
	DESCRIPTION
		"Neighbor divice's holding time of OADP frame which this device send.
		 The value of hold-time in oadp configuration."
	::= { axsOadpGlobalInfo 4 }

axsOadpGlobalCacheLastChange OBJECT-TYPE
	SYNTAX  TimeTicks
	MAX-ACCESS  read-only
	STATUS  current
	DESCRIPTION
		"Value of sysUpTime which is set when axsOadpNeighborTable is updated."
	::= { axsOadpGlobalInfo 5 }

axsOadpGlobalName OBJECT-TYPE
	SYNTAX  DisplayString
	MAX-ACCESS  read-only
	STATUS  current
	DESCRIPTION
		"Device identifier."
	::= { axsOadpGlobalInfo 6 }

axsOadpGlobalNameType OBJECT-TYPE
	SYNTAX  INTEGER {
		other(1),
		sysName(2),
		serialNumber(3),
		macaddress(4)
    }
	MAX-ACCESS  read-only
	STATUS  current
	DESCRIPTION
		"Kind of axsOadpGlobalName."
	::= { axsOadpGlobalInfo 7 }

axsOadpPortConfigTable OBJECT-TYPE
	SYNTAX  SEQUENCE OF AxsOadpPortConfigEntry
	MAX-ACCESS  not-accessible
	STATUS  current
	DESCRIPTION
		"A table of OADP port information."
	::= { axsOadpPortInfo 1 }

axsOadpPortConfigEntry OBJECT-TYPE
	SYNTAX  AxsOadpPortConfigEntry
	MAX-ACCESS  not-accessible
	STATUS  current
	DESCRIPTION
		"An entry of OADP port information."
    INDEX { axsOadpPortConfigIfIndex }
	::= { axsOadpPortConfigTable 1 }

	AxsOadpPortConfigEntry ::=
		SEQUENCE {
		    axsOadpPortConfigIfIndex	InterfaceIndex,
		    axsOadpPortConfigActive	TruthValue
		}

axsOadpPortConfigIfIndex OBJECT-TYPE
	SYNTAX  InterfaceIndex
	MAX-ACCESS  read-only
	STATUS  current
	DESCRIPTION
		"Port identification index. The same value as ifIndex.
		 This is only for physical ports and LA ports which are given
		 ifIndex."
	::= { axsOadpPortConfigEntry 1 }

axsOadpPortConfigActive OBJECT-TYPE
	SYNTAX  TruthValue
	MAX-ACCESS  read-only
	STATUS  current
	DESCRIPTION
		"Status of specified port."
	::= { axsOadpPortConfigEntry 2 }

axsOadpNeighborTable OBJECT-TYPE
	SYNTAX  SEQUENCE OF AxsOadpNeighborEntry
	MAX-ACCESS  not-accessible
	STATUS  current
	DESCRIPTION
		"A table of OADP neighbor nodes."
	::= { axsOadpNeighborInfo 1 }

axsOadpNeighborEntry OBJECT-TYPE
	SYNTAX  AxsOadpNeighborEntry
	MAX-ACCESS  not-accessible
	STATUS  current
	DESCRIPTION
		"An entry of OADP neighbor nodes."
    INDEX { axsOadpIfIndex, axsOadpTagID, axsOadpNeighborIndex, axsOadpNeighborTagID }
	::= { axsOadpNeighborTable 1 }

	AxsOadpNeighborEntry ::=
		SEQUENCE {
		    axsOadpIfIndex			InterfaceIndex,
		    axsOadpTagID		 		INTEGER, 
		    axsOadpNeighborIndex  		INTEGER,
		    axsOadpNeighborTagID   		INTEGER,
		    axsOadpNeighborVendorType   		INTEGER,
		    axsOadpNeighborSNMPAgentAddressType 	INTEGER,
		    axsOadpNeighborSNMPAgentAddress  	DisplayString,
		    axsOadpNeighborDescr		   	DisplayString,
		    axsOadpNeighborDeviceID	   	DisplayString,
		    axsOadpNeighborSlotPort 	   	DisplayString,
		    axsOadpNeighborIfIndex  	   	InterfaceIndex,
		    axsOadpNeighborIfSpeed   	   	Gauge,
		    axsOadpNeighborDeviceType   	   	DisplayString,
		    axsOadpNeighborService   	   	OCTET STRING,
		    axsOadpNeighborVTPMgmtDomain    	DisplayString,
		    axsOadpNeighborNativeVLAN     	INTEGER,
		    axsOadpNeighborDuplex 	     	INTEGER,
		    axsOadpNeighborApplianceID  	     	Gauge,
		    axsOadpNeighborVlanID   	     	Gauge,
		    axsOadpNeighborPowerConsumption     	Gauge,
		    axsOadpNeighborMTU           	Gauge,
		    axsOadpNeighborSysName            	DisplayString,
		    axsOadpNeighborSysObjectID          	OBJECT IDENTIFIER,
		    axsOadpNeighborSecondarySNMPAgentAddressType  INTEGER,
		    axsOadpNeighborSecondarySNMPAgentAddress      DisplayString,
		    axsOadpNeighborPhysLocation          DisplayString,
		    axsOadpNeighborCacheLastChange       TimeTicks,
		    axsOadpNeighborIfHighSpeed           Gauge
		}

axsOadpIfIndex OBJECT-TYPE
	SYNTAX  InterfaceIndex
	MAX-ACCESS  read-only
	STATUS  current
	DESCRIPTION
		"ifIndex of reception interface."
	::= { axsOadpNeighborEntry 1 }

axsOadpTagID OBJECT-TYPE
	SYNTAX  INTEGER
	MAX-ACCESS  read-only
	STATUS  current
	DESCRIPTION
		"Tag ID of IEEE802.1Q which is attached MAC frame."
	::= { axsOadpNeighborEntry 2 }

axsOadpNeighborIndex OBJECT-TYPE
	SYNTAX  INTEGER
	MAX-ACCESS  read-only
	STATUS  current
	DESCRIPTION
		"Unique numeric which identifies neighbor nodes"
	::= { axsOadpNeighborEntry 3 }

axsOadpNeighborTagID OBJECT-TYPE
	SYNTAX  INTEGER
	MAX-ACCESS  read-only
	STATUS  current
	DESCRIPTION
		"Value set at TagID TLV in OADP PDU which is sent from neighbor node."
	::= { axsOadpNeighborEntry 4 }

axsOadpNeighborVendorType OBJECT-TYPE
	SYNTAX  INTEGER {
		other(1),
		oadp(2),
		cdp(3)
    }
	MAX-ACCESS  read-only
	STATUS  current
	DESCRIPTION
		"Protocol type used to find to neighbor nodes."
	::= { axsOadpNeighborEntry 5 }

axsOadpNeighborSNMPAgentAddressType OBJECT-TYPE
	SYNTAX  INTEGER {
		ipv4(1),
		ipv6(20),
		other-notSupported(65535)
    }
	MAX-ACCESS  read-only
	STATUS  current
	DESCRIPTION
		"A kind of agent address to get information by SNMP."
	::= { axsOadpNeighborEntry 6 }

axsOadpNeighborSNMPAgentAddress OBJECT-TYPE
	SYNTAX  DisplayString
	MAX-ACCESS  read-only
	STATUS  current
	DESCRIPTION
		"DisplayString formed information of agent address to get information by SNMP."
	::= { axsOadpNeighborEntry 7 }

axsOadpNeighborDescr OBJECT-TYPE
	SYNTAX  DisplayString
	MAX-ACCESS  read-only
	STATUS  current
	DESCRIPTION
		"String of sysDescr of neighbor node."
	::= { axsOadpNeighborEntry 8 }

axsOadpNeighborDeviceID OBJECT-TYPE
	SYNTAX  DisplayString
	MAX-ACCESS  read-only
	STATUS  current
	DESCRIPTION
		"Neighbor node's device identifier."
	::= { axsOadpNeighborEntry 9 }

axsOadpNeighborSlotPort OBJECT-TYPE
	SYNTAX  DisplayString
	MAX-ACCESS  read-only
	STATUS  current
	DESCRIPTION
		"Unique string which identifies neighbor's sending interface."
	::= { axsOadpNeighborEntry 10 }

axsOadpNeighborIfIndex OBJECT-TYPE
	SYNTAX  InterfaceIndex
	MAX-ACCESS  read-only
	STATUS  current
	DESCRIPTION
		"ifIndex of sending interface of neighbor node."
	::= { axsOadpNeighborEntry 11 }

axsOadpNeighborIfSpeed OBJECT-TYPE
	SYNTAX  Gauge
	MAX-ACCESS  read-only
	STATUS  current
	DESCRIPTION
		"ifSpeed of sending interface of neighbor node."
	::= { axsOadpNeighborEntry 12 }

axsOadpNeighborDeviceType OBJECT-TYPE
	SYNTAX  DisplayString
	MAX-ACCESS  read-only
	STATUS  current
	DESCRIPTION
		"Device name of neighbor node."
	::= { axsOadpNeighborEntry 13 }

axsOadpNeighborService OBJECT-TYPE
	SYNTAX  OCTET STRING
	MAX-ACCESS  read-only
	STATUS  current
	DESCRIPTION
		"Functions neighbor node can offer."
	::= { axsOadpNeighborEntry 14 }

axsOadpNeighborVTPMgmtDomain OBJECT-TYPE
	SYNTAX  DisplayString
	MAX-ACCESS  read-only
	STATUS  current
	DESCRIPTION
		"VTP Management Domain of sending interface of neighbor node."
	::= { axsOadpNeighborEntry 15 }

axsOadpNeighborNativeVLAN OBJECT-TYPE
	SYNTAX  INTEGER
	MAX-ACCESS  read-only
	STATUS  current
	DESCRIPTION
		"Native VLAN number of sending interface of neighbor node."
	::= { axsOadpNeighborEntry 16 }

axsOadpNeighborDuplex OBJECT-TYPE
	SYNTAX  INTEGER {
		unknown(1),
		half(2),
		full(3)
    }
	MAX-ACCESS  read-only
	STATUS  current
	DESCRIPTION
		"Duplex information of sending interface of neighbor node."
	::= { axsOadpNeighborEntry 17 }

axsOadpNeighborApplianceID OBJECT-TYPE
	SYNTAX  Gauge
	MAX-ACCESS  read-only
	STATUS  current
	DESCRIPTION
		"Appliance ID of neighbor node."
	::= { axsOadpNeighborEntry 18 }

axsOadpNeighborVlanID OBJECT-TYPE
	SYNTAX  Gauge
	MAX-ACCESS  read-only
	STATUS  current
	DESCRIPTION
		"VLAN ID for VoIP of neighbor node."
	::= { axsOadpNeighborEntry 19 }

axsOadpNeighborPowerConsumption OBJECT-TYPE
	SYNTAX  Gauge
	MAX-ACCESS  read-only
	STATUS  current
	DESCRIPTION
		"Electric power comsumption of neighbor node."
	::= { axsOadpNeighborEntry 20 }

axsOadpNeighborMTU OBJECT-TYPE
	SYNTAX  Gauge
	MAX-ACCESS  read-only
	STATUS  current
	DESCRIPTION
		"MTU of sending interface of neighbor node."
	::= { axsOadpNeighborEntry 21 }

axsOadpNeighborSysName OBJECT-TYPE
	SYNTAX  DisplayString
	MAX-ACCESS  read-only
	STATUS  current
	DESCRIPTION
		"sysName of neighbor node."
	::= { axsOadpNeighborEntry 22 }

axsOadpNeighborSysObjectID OBJECT-TYPE
	SYNTAX  OBJECT IDENTIFIER
	MAX-ACCESS  read-only
	STATUS  current
	DESCRIPTION
		"sysObjectID of neighbor node."
	::= { axsOadpNeighborEntry 23 }

axsOadpNeighborSecondarySNMPAgentAddressType OBJECT-TYPE
	SYNTAX  INTEGER {
		ipv4(1),
		ipv6(20),
		other-notSupported(65535)
    }
	MAX-ACCESS  read-only
	STATUS  current
	DESCRIPTION
		"A kind of agent secondary address to get information by SNMP."
	::= { axsOadpNeighborEntry 24 }

axsOadpNeighborSecondarySNMPAgentAddress OBJECT-TYPE
	SYNTAX  DisplayString
	MAX-ACCESS  read-only
	STATUS  current
	DESCRIPTION
		"DisplayString formed information of agent secondary address to get information by SNMP."
	::= { axsOadpNeighborEntry 25 }

axsOadpNeighborPhysLocation OBJECT-TYPE
	SYNTAX  DisplayString
	MAX-ACCESS  read-only
	STATUS  current
	DESCRIPTION
		"sysLocation of neighbor node."
	::= { axsOadpNeighborEntry 26 }

axsOadpNeighborCacheLastChange OBJECT-TYPE
	SYNTAX  TimeTicks
	MAX-ACCESS  read-only
	STATUS  current
	DESCRIPTION
		"Value of sysUpTime which is set when axsOadpNeighborEntry about neighbor node is updated."
	::= { axsOadpNeighborEntry 27 }

axsOadpNeighborIfHighSpeed OBJECT-TYPE
	SYNTAX  Gauge
	MAX-ACCESS  read-only
	STATUS  current
	DESCRIPTION
		"ifHighSpeed of sending interface of neighbor node."
	::= { axsOadpNeighborEntry 28 }

--  axsFlow Group

axsAccessFilterStatsInTable OBJECT-TYPE
        SYNTAX  SEQUENCE OF AxsAccessFilterStatsInEntry
        MAX-ACCESS  not-accessible
        STATUS  current
        DESCRIPTION
                "Table information on corresponding number of packets to flow detection condition 
                and operation information set by access list."
        ::= { axsAccessFilterStats 1 }

axsAccessFilterStatsInEntry OBJECT-TYPE
        SYNTAX  AxsAccessFilterStatsInEntry
        MAX-ACCESS  not-accessible
        STATUS  current
        DESCRIPTION
                "Entry concerning corresponding number of packets to flow detection condition and 
                operation information set by access list."
    INDEX { axsAccessFilterStatsInifIndex, axsAccessFilterStatsInifIndexType, axsAccessFilterStatsInListIndex,axsAccessFilterStatsInSequenceNumber }
        ::= { axsAccessFilterStatsInTable 1 }

        AxsAccessFilterStatsInEntry ::=
                SEQUENCE {
                  axsAccessFilterStatsInifIndex         INTEGER,
                  axsAccessFilterStatsInifIndexType     INTEGER,
                  axsAccessFilterStatsInListIndex       Unsigned32,
                  axsAccessFilterStatsInSequenceNumber  Unsigned32,
                  axsAccessFilterStatsInListName        DisplayString,
                  axsAccessFilterStatsInMatchedPackets  Counter64
                }

axsAccessFilterStatsInifIndex OBJECT-TYPE
        SYNTAX  INTEGER
        MAX-ACCESS  not-accessible
        STATUS  current
        DESCRIPTION
                "Index value in which entry of this table is identified."
        ::= { axsAccessFilterStatsInEntry 1 }

axsAccessFilterStatsInifIndexType OBJECT-TYPE
        SYNTAX  INTEGER
        MAX-ACCESS  not-accessible
        STATUS  current
        DESCRIPTION
                "Indicates interface type. Physical port number : 1 Interface name : 2"
        ::= { axsAccessFilterStatsInEntry 2 }

axsAccessFilterStatsInListIndex OBJECT-TYPE
        SYNTAX  Unsigned32
        MAX-ACCESS  not-accessible
        STATUS  current
        DESCRIPTION
                "Index value of access list that identifies entry of this table."
        ::= { axsAccessFilterStatsInEntry 3 }

axsAccessFilterStatsInSequenceNumber OBJECT-TYPE
        SYNTAX  Unsigned32
        MAX-ACCESS  not-accessible
        STATUS  current
        DESCRIPTION
                "Sequence number of flow detection condition and operation information set to access list 
                number or access list name. 
                "
        ::= { axsAccessFilterStatsInEntry 4 }

axsAccessFilterStatsInListName OBJECT-TYPE
        SYNTAX  DisplayString
        MAX-ACCESS  read-only
        STATUS  current
        DESCRIPTION
                "Access list number or access list name corresponding to index of access list."
        ::= { axsAccessFilterStatsInEntry 5 }

axsAccessFilterStatsInMatchedPackets OBJECT-TYPE
        SYNTAX  Counter64
        MAX-ACCESS  read-only
        STATUS  current
        DESCRIPTION
                "Corresponding number of packets to flow detection condition of access list. "
        ::= { axsAccessFilterStatsInEntry 6 }

axsQosFlowStatsInTable OBJECT-TYPE
        SYNTAX  SEQUENCE OF AxsQosFlowStatsInEntry
        MAX-ACCESS  not-accessible
        STATUS  current
        DESCRIPTION
                "Table information on corresponding number of packets to QoS flow detection condition
                and operation information set in QoS flow list."
        ::= { axsQosFlowStats 1 }

axsQosFlowStatsInEntry OBJECT-TYPE
        SYNTAX  AxsQosFlowStatsInEntry
        MAX-ACCESS  not-accessible
        STATUS  current
        DESCRIPTION
                "Entry concerning corresponding number of packets to QoS flow detection condition
                and operation information set in QoS Flower shop."
    INDEX { axsQosFlowStatsInifIndex, axsQosFlowStatsInifIndexType, axsQosFlowStatsInListIndex, axsQosFlowStatsInSequenceNumber }
        ::= { axsQosFlowStatsInTable 1 }

        AxsQosFlowStatsInEntry ::=
                SEQUENCE {
                  axsQosFlowStatsInifIndex                 INTEGER,
                  axsQosFlowStatsInifIndexType             INTEGER,
                  axsQosFlowStatsInListIndex               Unsigned32,
                  axsQosFlowStatsInSequenceNumber          Unsigned32,
                  axsQosFlowStatsInListName                DisplayString,
                  axsQosFlowStatsInMatchedPackets          Counter64,
                  axsQosFlowStatsInMatchedPacketsMinUnder  Counter64,
                  axsQosFlowStatsInMatchedPacketsMinOver   Counter64,
                  axsQosFlowStatsInMatchedPacketsMaxUnder  Counter64,
                  axsQosFlowStatsInMatchedPacketsMaxOver   Counter64
                }

axsQosFlowStatsInifIndex OBJECT-TYPE
        SYNTAX  INTEGER
        MAX-ACCESS  not-accessible
        STATUS  current
        DESCRIPTION
                "Index value in which entry of this table is identified."
        ::= { axsQosFlowStatsInEntry 1 }

axsQosFlowStatsInifIndexType OBJECT-TYPE
        SYNTAX  INTEGER
        MAX-ACCESS  not-accessible
        STATUS  current
        DESCRIPTION
                "Indicates interface type. Physical port number : 1 Interface name : 2"
        ::= { axsQosFlowStatsInEntry 2 }

axsQosFlowStatsInListIndex OBJECT-TYPE
        SYNTAX  Unsigned32
        MAX-ACCESS  not-accessible
        STATUS  current
        DESCRIPTION
                "Index value of QoS Flow list where entry of this table is identified."
        ::= { axsQosFlowStatsInEntry 3 }

axsQosFlowStatsInSequenceNumber OBJECT-TYPE
        SYNTAX  Unsigned32
        MAX-ACCESS  not-accessible
        STATUS  current
        DESCRIPTION
                "Sequence number of flow detection condition and operation information set to QoS 
                flow list name."
        ::= { axsQosFlowStatsInEntry 4 }

axsQosFlowStatsInListName OBJECT-TYPE
        SYNTAX  DisplayString
        MAX-ACCESS  read-only
        STATUS  current
        DESCRIPTION
                "QoS flow list name corresponding to index of QoS flow list."
        ::= { axsQosFlowStatsInEntry 5 }

axsQosFlowStatsInMatchedPackets OBJECT-TYPE
        SYNTAX  Counter64
        MAX-ACCESS  read-only
        STATUS  current
        DESCRIPTION
                "Corresponding number of packets to flow detection condition of QoS flow list."
        ::= { axsQosFlowStatsInEntry 6 }

axsQosFlowStatsInMatchedPacketsMinUnder OBJECT-TYPE
        SYNTAX  Counter64
        MAX-ACCESS  read-only
        STATUS  current
        DESCRIPTION
                "Number of packets in which it agrees to flow detection condition of QoS flow 
                list and the lowest band watch is observed."
        ::= { axsQosFlowStatsInEntry 7 }

axsQosFlowStatsInMatchedPacketsMinOver OBJECT-TYPE
        SYNTAX  Counter64
        MAX-ACCESS  read-only
        STATUS  current
        DESCRIPTION
                "Number of packets in which it agrees to flow detection condition of QoS flow 
                list and it violates the lowest band watch."
        ::= { axsQosFlowStatsInEntry 8 }

axsQosFlowStatsInMatchedPacketsMaxUnder OBJECT-TYPE
        SYNTAX  Counter64
        MAX-ACCESS  read-only
        STATUS  current
        DESCRIPTION
                "Number of packets in which it agrees to flow detection condition of QoS flow 
                list and the maximum band control is observed."
        ::= { axsQosFlowStatsInEntry 9 }

axsQosFlowStatsInMatchedPacketsMaxOver OBJECT-TYPE
        SYNTAX  Counter64 
        MAX-ACCESS  read-only
        STATUS  current
        DESCRIPTION
                "Number of packets in which it agrees to flow detection condition of QoS flow 
                list and it violates the maximum band control."
        ::= { axsQosFlowStatsInEntry 10 }

--  axsL2ldMIB Group

axsL2ldVersion OBJECT-TYPE
	SYNTAX  INTEGER
	ACCESS  read-only
	STATUS  mandatory
	DESCRIPTION
		"The version of L2 loop detection."
	::= { axsL2ldGlobalInfo 1 }

axsL2ldLoopDetectionId OBJECT-TYPE
	SYNTAX  INTEGER
	ACCESS  read-only
	STATUS  mandatory
	DESCRIPTION
		"L2 loop detection ID."
	::= { axsL2ldGlobalInfo 2 }

axsL2ldIntervalTime OBJECT-TYPE
	SYNTAX  INTEGER
	ACCESS  read-only
	STATUS  mandatory
	DESCRIPTION
		"Sending interval of L2 loop detection frame."
	::= { axsL2ldGlobalInfo 3 }

axsL2ldOutputRate OBJECT-TYPE
	SYNTAX  INTEGER
	ACCESS  read-only
	STATUS  mandatory
	DESCRIPTION
		"Sending rate of L2 loop detection frame."
	::= { axsL2ldGlobalInfo 4 }

axsL2ldThreshold OBJECT-TYPE
	SYNTAX  INTEGER
	ACCESS  read-only
	STATUS  mandatory
	DESCRIPTION
		"Detection counts until port is put into state of inactive."
	::= { axsL2ldGlobalInfo 5 }

axsL2ldHoldTime OBJECT-TYPE
	SYNTAX  INTEGER
	ACCESS  read-only
	STATUS  mandatory
	DESCRIPTION
		"Hold time of detection counts."
	::= { axsL2ldGlobalInfo 6 }

axsL2ldAutoRestoreTime OBJECT-TYPE
	SYNTAX  INTEGER
	ACCESS  read-only
	STATUS  mandatory
	DESCRIPTION
		"Time until port put into state of inactive is put into state of
		active by automatic operation."
	::= { axsL2ldGlobalInfo 7 }

axsL2ldConfigurationVlanPortCounts OBJECT-TYPE
	SYNTAX  INTEGER
	ACCESS  read-only
	STATUS  mandatory
	DESCRIPTION
		"The number of VLAN ports set to send L2 loop detection frame."
	::= { axsL2ldGlobalInfo 8 }

axsL2ldCapacityVlanPortCounts OBJECT-TYPE
	SYNTAX  INTEGER
	ACCESS  read-only
	STATUS  mandatory
	DESCRIPTION
		"The number of VLAN ports that can be sent by L2 loop detection
		frame sending rate."
	::= { axsL2ldGlobalInfo 9 }

axsL2ldPortTable OBJECT-TYPE
	SYNTAX  SEQUENCE OF AxsL2ldPortEntry
	ACCESS  not-accessible
	STATUS  mandatory
	DESCRIPTION
		"The table containing port information on L2 loop detection."
	::= { axsL2ld 2 }

axsL2ldPortEntry OBJECT-TYPE
	SYNTAX  AxsL2ldPortEntry
	ACCESS  not-accessible
	STATUS  mandatory
	DESCRIPTION
		"The entry of port information on L2 loop detection."
	INDEX { axsL2ldPortIndex,axsL2ldPortIfIndex }
	::= { axsL2ldPortTable 1 }

	AxsL2ldPortEntry ::=
		SEQUENCE {
			axsL2ldPortIndex					INTEGER,
			axsL2ldPortIfIndex					INTEGER,
			axsL2ldPortStatus					INTEGER,
			axsL2ldPortType						INTEGER,
			axsL2ldPortDetectCount				INTEGER,
			axsL2ldPortAutoRestoringTimer		INTEGER,
			axsL2ldPortSourcePortIfindex		INTEGER,
			axsL2ldPortDestinationPortIfindex	INTEGER,
			axsL2ldPortSourceVlan				INTEGER,
			axsL2ldPortHCInFrames				Counter64,
			axsL2ldPortHCOutFrames				Counter64,
			axsL2ldPortHCInDiscards				Counter64,
			axsL2ldPortInactiveCount			INTEGER,
			axsL2ldPortLastInactiveTime			TimeStamp,
			axsL2ldPortLastInFramesTime			TimeStamp
		}

axsL2ldPortIndex OBJECT-TYPE
	SYNTAX  INTEGER
	ACCESS  read-only
	STATUS  mandatory
	DESCRIPTION
		"Index of L2 loop detection port."
	::= { axsL2ldPortEntry 1 }

axsL2ldPortIfIndex OBJECT-TYPE
	SYNTAX  INTEGER
	ACCESS  read-only
	STATUS  mandatory
	DESCRIPTION
		"ifIndex of L2 loop detection port."
	::= { axsL2ldPortEntry 2 }

axsL2ldPortStatus OBJECT-TYPE
	SYNTAX  INTEGER {
				up (1),
				down (2),
				loopDown (3)
			}
	ACCESS  read-only
	STATUS  mandatory
	DESCRIPTION
		"State of L2 loop detection port."
	::= { axsL2ldPortEntry 3 }

axsL2ldPortType OBJECT-TYPE
	SYNTAX  INTEGER {
				trap (1),
				sendInact (2),
				send (3),
				upLink (4),
				exception (5)
			}
	ACCESS  read-only
	STATUS  mandatory
	DESCRIPTION
		"Type of L2 loop detection port."
	::= { axsL2ldPortEntry 4 }

axsL2ldPortDetectCount OBJECT-TYPE
	SYNTAX  INTEGER
	ACCESS  read-only
	STATUS  mandatory
	DESCRIPTION
		"The number of L2 loop detection. The number in which
		L2 loop detection frame is received in hold time."
	::= { axsL2ldPortEntry 5 }

axsL2ldPortAutoRestoringTimer OBJECT-TYPE
	SYNTAX  INTEGER
	ACCESS  read-only
	STATUS  mandatory
	DESCRIPTION
		"Time until restoring it automatically. The value is 0
		when port is active."
	::= { axsL2ldPortEntry 6 }

axsL2ldPortSourcePortIfindex OBJECT-TYPE
	SYNTAX  INTEGER
	ACCESS  read-only
	STATUS  mandatory
	DESCRIPTION
		"ifIndex of port transmitted when L2 loop detection frame
		was received at the end."
	::= { axsL2ldPortEntry 7 }

axsL2ldPortDestinationPortIfindex OBJECT-TYPE
	SYNTAX  INTEGER
	ACCESS  read-only
	STATUS  mandatory
	DESCRIPTION
		"ifIndex of port where L2 loop detection frame was
		received at the end."
	::= { axsL2ldPortEntry 8 }

axsL2ldPortSourceVlan OBJECT-TYPE
	SYNTAX  INTEGER
	ACCESS  read-only
	STATUS  mandatory
	DESCRIPTION
		"VLAN ID when transmitting when L2 loop detection frame
		was received at the end."
	::= { axsL2ldPortEntry 9 }

axsL2ldPortHCInFrames OBJECT-TYPE
	SYNTAX  Counter64
	ACCESS  read-only
	STATUS  mandatory
	DESCRIPTION
		"Number of receptions of L2 loop detection frames."
	::= { axsL2ldPortEntry 10 }

axsL2ldPortHCOutFrames OBJECT-TYPE
	SYNTAX  Counter64
	ACCESS  read-only
	STATUS  mandatory
	DESCRIPTION
		"Number of transmissions of L2 loop detection frames."
	::= { axsL2ldPortEntry 11 }

axsL2ldPortHCInDiscards OBJECT-TYPE
	SYNTAX  Counter64
	ACCESS  read-only
	STATUS  mandatory
	DESCRIPTION
		"Number of receptions of L2 loop detection discard frames."
	::= { axsL2ldPortEntry 12 }

axsL2ldPortInactiveCount OBJECT-TYPE
	SYNTAX  INTEGER
	ACCESS  read-only
	STATUS  mandatory
	DESCRIPTION
		"The number of put into state of inactive."
	::= { axsL2ldPortEntry 13 }

axsL2ldPortLastInactiveTime OBJECT-TYPE
	SYNTAX  TimeStamp
	ACCESS  read-only
	STATUS  mandatory
	DESCRIPTION
		"Time put into state of inactive at the end."
	::= { axsL2ldPortEntry 14 }

axsL2ldPortLastInFramesTime OBJECT-TYPE
	SYNTAX  TimeStamp
	ACCESS  read-only
	STATUS  mandatory
	DESCRIPTION
		"Time to have received L2 loop detection frame at the end."
	::= { axsL2ldPortEntry 15 }

--  OSPF General Variables

axsOspfGeneralTable OBJECT-TYPE
	SYNTAX  SEQUENCE OF AxsOspfGeneralEntry
	MAX-ACCESS  not-accessible
	STATUS  current
	DESCRIPTION
		"The table of OSPF information."
	::= { axsOspf 1 }

axsOspfGeneralEntry OBJECT-TYPE
	SYNTAX  AxsOspfGeneralEntry
	MAX-ACCESS  not-accessible
	STATUS  current
	DESCRIPTION
		"The entry of OSPF information."
    INDEX { axsOspfGeneralDomainNumber }
	::= { axsOspfGeneralTable 1 }

	AxsOspfGeneralEntry ::=
		SEQUENCE {
		    axsOspfGeneralDomainNumber	INTEGER,
		    axsOspfRouterId				IpAddress,
		    axsOspfAdminStat				INTEGER,
		    axsOspfVersionNumber			INTEGER,
		    axsOspfAreaBdrRtrStatus		INTEGER,
		    axsOspfASBdrRtrStatus		INTEGER,
		    axsOspfExternLsaCount		Gauge,
		    axsOspfExternLsaCksumSum		INTEGER,
		    axsOspfTOSSupport			INTEGER,
		    axsOspfOriginateNewLsas		Counter,
		    axsOspfRxNewLsas				Counter,
		    axsOspfExtLsdbLimit			INTEGER,
		    axsOspfMulticastExtensions	INTEGER
		}

axsOspfGeneralDomainNumber OBJECT-TYPE
	SYNTAX  INTEGER
	MAX-ACCESS  read-only
	STATUS  current
	DESCRIPTION
		"Domain number in the Autonomous System."
	::= { axsOspfGeneralEntry 1 }

axsOspfRouterId OBJECT-TYPE
	SYNTAX  IpAddress
	MAX-ACCESS  read-only
	STATUS  current
	DESCRIPTION
		"A integer uniquely identifying the router
		in the Autonomous System."
	::= { axsOspfGeneralEntry 2 }

axsOspfAdminStat OBJECT-TYPE
	SYNTAX  INTEGER   { 
				enabled(1),
				disabled(2)
		    }
	MAX-ACCESS  read-only
	STATUS  current
	DESCRIPTION
		"The  administrative  status  of  OSPF  in  the
		router.  "
	::= { axsOspfGeneralEntry 3 }

axsOspfVersionNumber OBJECT-TYPE
	SYNTAX  INTEGER
	MAX-ACCESS  read-only
	STATUS  current
	DESCRIPTION
		"The current version number of the OSPF  
		protocol is 2."
	::= { axsOspfGeneralEntry 4 }

axsOspfAreaBdrRtrStatus OBJECT-TYPE
	SYNTAX  INTEGER { 
				true(1),
				false(2)
			}
	MAX-ACCESS  read-only
	STATUS  current
	DESCRIPTION
		"A flag to note whether this router is an  area
		 border router."
	::= { axsOspfGeneralEntry 5 }

axsOspfASBdrRtrStatus OBJECT-TYPE
	SYNTAX  INTEGER {
				true(1),
				false(2)
			}
	MAX-ACCESS  read-only
	STATUS  current
	DESCRIPTION
		"A flag to note whether this router is  configured
		as an Autonomous System border router."
	::= { axsOspfGeneralEntry 6 }

axsOspfExternLsaCount OBJECT-TYPE
	SYNTAX  Gauge
	MAX-ACCESS  read-only
	STATUS  current
	DESCRIPTION
		"The number of external (LS type 5)  link-state
		advertisements in the link-state database."
	::= { axsOspfGeneralEntry 7 }

axsOspfExternLsaCksumSum OBJECT-TYPE
	SYNTAX  INTEGER
	MAX-ACCESS  read-only
	STATUS  current
	DESCRIPTION
		"The 32-bit unsigned sum of the LS checksums of
		the  external  link-state  advertisements  contained
		in the link-state  database."
	::= { axsOspfGeneralEntry 8 }

axsOspfTOSSupport OBJECT-TYPE
	SYNTAX  INTEGER {
                            true(1),
                            false(2)
                        }
	MAX-ACCESS  read-only
	STATUS  current
	DESCRIPTION
		"The router's support for type-of-service routing.
		 This value of false(2). "
	::= { axsOspfGeneralEntry 9 }

axsOspfOriginateNewLsas OBJECT-TYPE
	SYNTAX  Counter
	MAX-ACCESS  read-only
	STATUS  current
	DESCRIPTION
		"The number of  new  link-state  advertisements
		that have been originated. "
	::= { axsOspfGeneralEntry 10 }

axsOspfRxNewLsas OBJECT-TYPE
	SYNTAX  Counter
	MAX-ACCESS  read-only
	STATUS  current
	DESCRIPTION
		"The number of  link-state  advertisements  received
		determined  to  be  new instantiations."
	::= { axsOspfGeneralEntry 11 }

axsOspfExtLsdbLimit OBJECT-TYPE
	SYNTAX  INTEGER
	MAX-ACCESS  read-only
	STATUS  current
	DESCRIPTION
		"The maximum number of non-default AS-external-LSAs
		entries that can be stored in the link-state database.
		If the value is -1,  then there is no limit.
		This value is -1"
	::= { axsOspfGeneralEntry 12 }

axsOspfMulticastExtensions OBJECT-TYPE
	SYNTAX  INTEGER
	MAX-ACCESS  read-only
	STATUS  current
	DESCRIPTION
		"A Bit Mask indicating whether  the  router  is
		forwarding  IP  multicast  (Class  D) datagrams
		based on the algorithms defined in  the  Multicast
		Extensions to OSPF."
	::= { axsOspfGeneralEntry 13 }

axsOspfAreaTable OBJECT-TYPE
	SYNTAX  SEQUENCE OF AxsOspfAreaEntry
	MAX-ACCESS  not-accessible
	STATUS  current
	DESCRIPTION
		"The router's support for demand routing."
	::= { axsOspf 2 }

axsOspfAreaEntry OBJECT-TYPE
	SYNTAX  AxsOspfAreaEntry
	MAX-ACCESS  not-accessible
	STATUS  current
	DESCRIPTION
		"This entry contain ospf area information."
    INDEX { axsOspfAreaDomainNumber, axsOspfAreaId }
	::= { axsOspfAreaTable 1 }

	AxsOspfAreaEntry ::=
		SEQUENCE {
		    axsOspfAreaDomainNumber	INTEGER,
		    axsOspfAreaId			IpAddress,
		    axsOspfAuthType			INTEGER,
		    axsOspfImportAsExtern	INTEGER,
		    axsOspfSpfRuns			Counter,
		    axsOspfAreaBdrRtrCount	Gauge,
		    axsOspfAsBdrRtrCount		Gauge,
		    axsOspfAreaLsaCount		Gauge,
		    axsOspfAreaLsaCksumSum	INTEGER,
		    axsOspfAreaSummary		INTEGER,
		    axsOspfAreaStatus		INTEGER
		}

axsOspfAreaDomainNumber OBJECT-TYPE
	SYNTAX  INTEGER
	MAX-ACCESS  read-only
	STATUS  current
	DESCRIPTION
		"An uniquely identifying number of domain."
	::= { axsOspfAreaEntry 1 }

axsOspfAreaId OBJECT-TYPE
	SYNTAX  IpAddress
	MAX-ACCESS  read-only
	STATUS  current
	DESCRIPTION
		"A 32-bit integer uniquely identifying an area."
	::= { axsOspfAreaEntry 2 }

axsOspfAuthType OBJECT-TYPE
	SYNTAX  INTEGER
			-- none(0),
			-- simplePassword (1),
			-- md5(2)
	MAX-ACCESS  read-only
	STATUS  current
	DESCRIPTION
		"The authentication type specified for an area."
	::= { axsOspfAreaEntry 3 }

axsOspfImportAsExtern OBJECT-TYPE
	SYNTAX  INTEGER { 
				importExternal (1),
				importNoExternal (2),
				importNssa (3)
			}
	MAX-ACCESS  read-only
	STATUS  current
	DESCRIPTION
		"The area's support for importing  AS  external
		link- state advertisements."
	::= { axsOspfAreaEntry 4 }

axsOspfSpfRuns OBJECT-TYPE
	SYNTAX  Counter
	MAX-ACCESS  read-only
	STATUS  current
	DESCRIPTION
		"The number of times that the intra-area  route
		table  has  been  calculated  using this area's
		link-state database."
	::= { axsOspfAreaEntry 5 }

axsOspfAreaBdrRtrCount OBJECT-TYPE
	SYNTAX  Gauge
	MAX-ACCESS  read-only
	STATUS  current
	DESCRIPTION
		"The total number of area border routers reachable
		within this area."
	::= { axsOspfAreaEntry 6 }

axsOspfAsBdrRtrCount OBJECT-TYPE
	SYNTAX  Gauge
	MAX-ACCESS  read-only
	STATUS  current
	DESCRIPTION
		"The total number of AS area border routers reachable
		within this area."
	::= { axsOspfAreaEntry 7 }

axsOspfAreaLsaCount OBJECT-TYPE
	SYNTAX  Gauge
	MAX-ACCESS  read-only
	STATUS  current
	DESCRIPTION
		"The total number of LSA(link-state  advertisements) 
		in this area. Excluding AS External LSA's"
	::= { axsOspfAreaEntry 8 }

axsOspfAreaLsaCksumSum OBJECT-TYPE
	SYNTAX  INTEGER
	MAX-ACCESS  read-only
	STATUS  current
	DESCRIPTION
		"The sum of LSA's  LS  checksums  contained in this
		area's link-state database."
	::= { axsOspfAreaEntry 9 }

axsOspfAreaSummary OBJECT-TYPE
	SYNTAX  INTEGER  {
				    noAreaSummary (1),
				    sendAreaSummary (2)
		    }
	MAX-ACCESS  read-only
	STATUS  current
	DESCRIPTION
		"he variable axsOspfAreaSummary controls the import
		of summary LSAs into stub areas. Value is only 
		sendAreaSummary(2)."
	::= { axsOspfAreaEntry 10 }

axsOspfAreaStatus OBJECT-TYPE
	SYNTAX  INTEGER {
                            active(1)
                        }
	MAX-ACCESS  read-only
	STATUS  current
	DESCRIPTION
		"This variable displays the status of  the  entry.
		Value is only valid(1)."
	::= { axsOspfAreaEntry 11 }

axsOspfStubAreaTable OBJECT-TYPE
	SYNTAX  SEQUENCE OF AxsOspfStubAreaEntry
	MAX-ACCESS  not-accessible
	STATUS  current
	DESCRIPTION
		"The set of metrics that will be advertised  by
		a default Area Border Router into a stub area."
	::= { axsOspf 3 }

axsOspfStubAreaEntry OBJECT-TYPE
	SYNTAX  AxsOspfStubAreaEntry
	MAX-ACCESS  not-accessible
	STATUS  current
	DESCRIPTION
		"The metric for a given Type  of  Service  that
		will be advertised by a default Area Border Router 
		into a stub area."
    INDEX { axsOspfStubDomainNumber, axsOspfStubAreaId,
		    axsOspfStubTOS }
	::= { axsOspfStubAreaTable 1 }

	AxsOspfStubAreaEntry ::=
		SEQUENCE {
		    axsOspfStubDomainNumber	INTEGER,
		    axsOspfStubAreaId		IpAddress,
		    axsOspfStubTOS			INTEGER,
		    axsOspfStubMetric		INTEGER,
		    axsOspfStubStatus		INTEGER,
		    axsOspfStubMetricType	INTEGER
		}

axsOspfStubDomainNumber OBJECT-TYPE
	SYNTAX  INTEGER
	MAX-ACCESS  read-only
	STATUS  current
	DESCRIPTION
		"The domain identifier for the Stub  Area."
	::= { axsOspfStubAreaEntry 1 }

axsOspfStubAreaId OBJECT-TYPE
	SYNTAX  IpAddress
	MAX-ACCESS  read-only
	STATUS  current
	DESCRIPTION
		"The identifier for the Stub  Area."
	::= { axsOspfStubAreaEntry 2 }

axsOspfStubTOS OBJECT-TYPE
	SYNTAX  INTEGER
	MAX-ACCESS  read-only
	STATUS  current
	DESCRIPTION
		"The Type of Service associated with the metric.
		Value is only 0."
	::= { axsOspfStubAreaEntry 3 }

axsOspfStubMetric OBJECT-TYPE
	SYNTAX  INTEGER
	MAX-ACCESS  read-only
	STATUS  current
	DESCRIPTION
		"The metric value applied at the indicated type
		of service."
	::= { axsOspfStubAreaEntry 4 }

axsOspfStubStatus OBJECT-TYPE
	SYNTAX  INTEGER {
                            active(1)
                        }
	MAX-ACCESS  read-only
	STATUS  current
	DESCRIPTION
		"This variable displays the status of the entry.
		This value is only valid(1)."
	::= { axsOspfStubAreaEntry 5 }

axsOspfStubMetricType OBJECT-TYPE
	SYNTAX  INTEGER  {
				ospfMetric(1),
				comparableCost(2),
				nonComparable(3)
		    }
	MAX-ACCESS  read-only
	STATUS  current
	DESCRIPTION
		"his variable displays the type of metric advertised
		as a default route."
	::= { axsOspfStubAreaEntry 6 }

axsOspfLsdbTable OBJECT-TYPE
	SYNTAX  SEQUENCE OF AxsOspfLsdbEntry
	MAX-ACCESS  not-accessible
	STATUS  current
	DESCRIPTION
		"The OSPF Process's Link State Database."
	::= { axsOspf 4 }

axsOspfLsdbEntry OBJECT-TYPE
	SYNTAX  AxsOspfLsdbEntry
	MAX-ACCESS  not-accessible
	STATUS  current
	DESCRIPTION
		 "A single Link State Advertisement."
    INDEX { axsOspfLsdbDomainNumber, axsOspfLsdbAreaId,
		    axsOspfLsdbType, axsOspfLsdbLsid, axsOspfLsdbRouterId }
	::= { axsOspfLsdbTable 1 }

	AxsOspfLsdbEntry ::=
		SEQUENCE {
		    axsOspfLsdbDomainNumber	INTEGER,
		    axsOspfLsdbAreaId		IpAddress,
		    axsOspfLsdbType		INTEGER,
		    axsOspfLsdbLsid		IpAddress,
		    axsOspfLsdbRouterId		IpAddress,
		    axsOspfLsdbSequence		INTEGER,
		    axsOspfLsdbAge		INTEGER,
		    axsOspfLsdbChecksum		INTEGER,
		    axsOspfLsdbAdvertisement	OCTET STRING
		}

axsOspfLsdbDomainNumber OBJECT-TYPE
	SYNTAX  INTEGER
	MAX-ACCESS  read-only
	STATUS  current
	DESCRIPTION
		"The identifier of the domain from  which
		the LSA was received."
	::= { axsOspfLsdbEntry 1 }

axsOspfLsdbAreaId OBJECT-TYPE
	SYNTAX  IpAddress
	MAX-ACCESS  read-only
	STATUS  current
	DESCRIPTION
		"The 32 bit identifier of the Area  from  which
		the LSA was received."
	::= { axsOspfLsdbEntry 2 }

axsOspfLsdbType OBJECT-TYPE
	SYNTAX  INTEGER    {
		       routerLink (1),
		       networkLink (2),
		       summaryLink (3),
		       asSummaryLink (4),
		       asExternalLink (5), -- but see axsOspfExtLsdbTable
		       multicastLink (6),
		       nssaExternalLink (7)
		    }
	MAX-ACCESS  read-only
	STATUS  current
	DESCRIPTION
		"The type  of  the  link  state  advertisement."
	::= { axsOspfLsdbEntry 3 }

axsOspfLsdbLsid OBJECT-TYPE
	SYNTAX  IpAddress
	MAX-ACCESS  read-only
	STATUS  current
	DESCRIPTION
		"The Link State ID . It identifies the piece of the routing
		domain that is being described by the advertisement."
	::= { axsOspfLsdbEntry 4 }

axsOspfLsdbRouterId OBJECT-TYPE
	SYNTAX  IpAddress
	MAX-ACCESS  read-only
	STATUS  current
	DESCRIPTION
		"The number that uniquely identifies the originating 
		router in the Autonomous System."
	::= { axsOspfLsdbEntry 5 }

axsOspfLsdbSequence OBJECT-TYPE
	SYNTAX  INTEGER
	MAX-ACCESS  read-only
	STATUS  current
	DESCRIPTION
		"The sequence number field is a  signed  32-bit
		integer."
	::= { axsOspfLsdbEntry 6 }

axsOspfLsdbAge OBJECT-TYPE
	SYNTAX  INTEGER
	MAX-ACCESS  read-only
	STATUS  current
	DESCRIPTION
		"This the age of the link state adver-
		tisement in seconds."
	::= { axsOspfLsdbEntry 7 }

axsOspfLsdbChecksum OBJECT-TYPE
	SYNTAX  INTEGER
	MAX-ACCESS  read-only
	STATUS  current
	DESCRIPTION
		"This field is the  checksum  of  the  complete
		contents  of  the  advertisement, excepting the
		age field."
	::= { axsOspfLsdbEntry 8 }

axsOspfLsdbAdvertisement OBJECT-TYPE
	SYNTAX  OCTET STRING
	MAX-ACCESS  read-only
	STATUS  current
	DESCRIPTION
		"The entire Link State Advertisement, including
		its header."
	::= { axsOspfLsdbEntry 9 }

axsOspfAreaRangeTable OBJECT-TYPE
	SYNTAX  SEQUENCE OF AxsOspfAreaRangeEntry
	MAX-ACCESS  not-accessible
	STATUS  current
	DESCRIPTION
		"A range if IP addresses  specified  by  an  IP
		address/IP  network  mask  pair."
	::= { axsOspf 5 }

axsOspfAreaRangeEntry OBJECT-TYPE
	SYNTAX  AxsOspfAreaRangeEntry
	MAX-ACCESS  not-accessible
	STATUS  current
	DESCRIPTION
		"A range if IP addresses specified by an IP
		address/IP network mask pair."
    INDEX { axsOspfAreaRangeDomainNumber, axsOspfAreaRangeAreaId,
		    axsOspfAreaRangeNet }
	::= { axsOspfAreaRangeTable 1 }

	AxsOspfAreaRangeEntry ::=
		SEQUENCE {
		    axsOspfAreaRangeDomainNumber	INTEGER,
		    axsOspfAreaRangeAreaId	IpAddress,
		    axsOspfAreaRangeNet		IpAddress,
		    axsOspfAreaRangeMask		IpAddress,
		    axsOspfAreaRangeStatus	INTEGER,
		    axsOspfAreaRangeEffect	INTEGER
		}

axsOspfAreaRangeDomainNumber OBJECT-TYPE
	SYNTAX  INTEGER
	MAX-ACCESS  read-only
	STATUS  current
	DESCRIPTION
		"Domain number of the Area."
	::= { axsOspfAreaRangeEntry 1 }

axsOspfAreaRangeAreaId OBJECT-TYPE
	SYNTAX  IpAddress
	MAX-ACCESS  read-only
	STATUS  current
	DESCRIPTION
		"The Area the Address  Range  is  to  be  found
		within."
	::= { axsOspfAreaRangeEntry 2 }

axsOspfAreaRangeNet OBJECT-TYPE
	SYNTAX  IpAddress
	MAX-ACCESS  read-only
	STATUS  current
	DESCRIPTION
		"The IP Address of the Net or Subnet  indicated
		by the range."
	::= { axsOspfAreaRangeEntry 3 }

axsOspfAreaRangeMask OBJECT-TYPE
	SYNTAX  IpAddress
	MAX-ACCESS  read-only
	STATUS  current
	DESCRIPTION
		"The Subnet Mask that pertains to  the  Net  or
		Subnet."
	::= { axsOspfAreaRangeEntry 4 }

axsOspfAreaRangeStatus OBJECT-TYPE
	SYNTAX  INTEGER    {
		       active(1),
		       inactive(2)
		    }
	MAX-ACCESS  read-only
	STATUS  current
	DESCRIPTION
		"This variable displays the status of  the  entry.
		This value is only valid(1)."
	::= { axsOspfAreaRangeEntry 5 }

axsOspfAreaRangeEffect OBJECT-TYPE
	SYNTAX  INTEGER  {
				advertiseMatching (1),
				doNotAdvertiseMatching (2)
		    }
	MAX-ACCESS  read-only
	STATUS  current
	DESCRIPTION
		"Subnets subsumed by ranges either trigger  the
		advertisement  of the indicated summary (adver-
		tiseMatching), or result in  the  subnet's  not
		being advertised at all outside the area."
	::= { axsOspfAreaRangeEntry 6 }

axsOspfIfTable OBJECT-TYPE
	SYNTAX  SEQUENCE OF AxsOspfIfEntry
	MAX-ACCESS  not-accessible
	STATUS  current
	DESCRIPTION
		"The OSPF Interface Table describes the interfaces
		from the viewpoint of OSPF."
	::= { axsOspf 7 }

axsOspfIfEntry OBJECT-TYPE
	SYNTAX  AxsOspfIfEntry
	MAX-ACCESS  not-accessible
	STATUS  current
	DESCRIPTION
		"The OSPF Interface Entry describes one  interface
		from the viewpoint of OSPF."
    INDEX { axsOspfIfDomainNumber, axsOspfIfIpAddress, axsOspfAddressLessIf }
	::= { axsOspfIfTable 1 }

	AxsOspfIfEntry ::=
		SEQUENCE {
		    axsOspfIfDomainNumber			INTEGER,
		    axsOspfIfIpAddress				IpAddress,
		    axsOspfAddressLessIf				INTEGER,
		    axsOspfIfAreaId					IpAddress,
		    axsOspfIfType					INTEGER,
		    axsOspfIfAdminStat				INTEGER,
		    axsOspfIfRtrPriority				INTEGER,
		    axsOspfIfTransitDelay			INTEGER,
		    axsOspfIfRetransInterval			INTEGER,
		    axsOspfIfHelloInterval			INTEGER,
		    axsOspfIfRtrDeadInterval			INTEGER,
		    axsOspfIfPollInterval			INTEGER,
		    axsOspfIfState					INTEGER,
		    axsOspfIfDesignatedRouter		IpAddress,
		    axsOspfIfEvents					Counter,
		    axsOspfIfAuthKey					OCTET STRING,
		    axsOspfIfStatus					INTEGER,
		    axsOspfIfMulticastForwarding		INTEGER,
		    axsOspfIfBackupDesignatedRouter	IpAddress
		}

axsOspfIfDomainNumber OBJECT-TYPE
	SYNTAX  INTEGER
	MAX-ACCESS  read-only
	STATUS  current
	DESCRIPTION
		"The domain number of this OSPF interface."
	::= { axsOspfIfEntry 1 }

axsOspfIfIpAddress OBJECT-TYPE
	SYNTAX  IpAddress
	MAX-ACCESS  read-only
	STATUS  current
	DESCRIPTION
		"The IP address of this OSPF interface."
	::= { axsOspfIfEntry 2 }

axsOspfAddressLessIf OBJECT-TYPE
	SYNTAX  INTEGER
	MAX-ACCESS  read-only
	STATUS  current
	DESCRIPTION
		"For the purpose of easing  the  instancing  of
		addressed   and  addressless  interfaces;  This
		variable takes the value 0 on  interfaces  with
		IP  Addresses,  and  the corresponding value of
		ifIndex for interfaces having no IP Address."
	::= { axsOspfIfEntry 3 }

axsOspfIfAreaId OBJECT-TYPE
	SYNTAX  IpAddress
	MAX-ACCESS  read-only
	STATUS  current
	DESCRIPTION
		"A integer uniquely identifying the area to which 
		the interface connects."
	::= { axsOspfIfEntry 4 }

axsOspfIfType OBJECT-TYPE
	SYNTAX  INTEGER  {
				 broadcast (1),
				 nbma (2),
				 pointToPoint (3),
				 pointToMultipoint (5)
		    }
	MAX-ACCESS  read-only
	STATUS  current
	DESCRIPTION
		"The OSPF interface type."
	::= { axsOspfIfEntry 5 }

axsOspfIfAdminStat OBJECT-TYPE
	SYNTAX  INTEGER { 
				enabled(1),
				disabled(2)
		    }
	MAX-ACCESS  read-only
	STATUS  current
	DESCRIPTION
		"The OSPF  interface's  administrative  status."
	::= { axsOspfIfEntry 6 }

axsOspfIfRtrPriority OBJECT-TYPE
	SYNTAX  INTEGER
	MAX-ACCESS  read-only
	STATUS  current
	DESCRIPTION
		"The priority of this interface."
	::= { axsOspfIfEntry 7 }

axsOspfIfTransitDelay OBJECT-TYPE
	SYNTAX  INTEGER
	MAX-ACCESS  read-only
	STATUS  current
	DESCRIPTION
		"The estimated number of seconds  it  takes  to
		transmit  a  link state update packet over this
		interface."
	::= { axsOspfIfEntry 8 }

axsOspfIfRetransInterval OBJECT-TYPE
	SYNTAX  INTEGER
	MAX-ACCESS  read-only
	STATUS  current
	DESCRIPTION
		"The number of seconds between link-state ad-
		vertisement retransmissions, for adjacencies
		belonging to this  interface."
	::= { axsOspfIfEntry 9 }

axsOspfIfHelloInterval OBJECT-TYPE
	SYNTAX  INTEGER
	MAX-ACCESS  read-only
	STATUS  current
	DESCRIPTION
		"The length of time, in  seconds,  between the
		Hello  packets that the router sends on the interface."
	::= { axsOspfIfEntry 10 }

axsOspfIfRtrDeadInterval OBJECT-TYPE
	SYNTAX  INTEGER
	MAX-ACCESS  read-only
	STATUS  current
	DESCRIPTION
		"The number of seconds that  a  router's  Hello
		packets  have  not been seen before it's neighbors 
		declare the router down."
	::= { axsOspfIfEntry 11 }

axsOspfIfPollInterval OBJECT-TYPE
	SYNTAX  INTEGER
	MAX-ACCESS  read-only
	STATUS  current
	DESCRIPTION
		"The larger time interval, in seconds,  between
		the  Hello  packets  sent  to  an inactive non-
		broadcast multi- access neighbor."
	::= { axsOspfIfEntry 12 }

axsOspfIfState OBJECT-TYPE
	SYNTAX  INTEGER   {
				down (1),
				loopback (2),
				waiting (3),
				pointToPoint (4),
				designatedRouter (5),
				backupDesignatedRouter (6),
				otherDesignatedRouter (7)
		    }
	MAX-ACCESS  read-only
	STATUS  current
	DESCRIPTION
		"The OSPF Interface State."
	::= { axsOspfIfEntry 13 }

axsOspfIfDesignatedRouter OBJECT-TYPE
	SYNTAX  IpAddress
	MAX-ACCESS  read-only
	STATUS  current
	DESCRIPTION
		"The IP Address of the Designated Router."
	::= { axsOspfIfEntry 14 }

axsOspfIfEvents OBJECT-TYPE
	SYNTAX  Counter
	MAX-ACCESS  read-only
	STATUS  current
	DESCRIPTION
		"The number of times this  OSPF  interface  has
		changed its state, or an error has occurred."
	::= { axsOspfIfEntry 16 }

axsOspfIfAuthKey OBJECT-TYPE
	SYNTAX  OCTET STRING
	MAX-ACCESS  read-only
	STATUS  current
	DESCRIPTION
		"The Authentication Key."
	::= { axsOspfIfEntry 17 }

axsOspfIfStatus OBJECT-TYPE
	SYNTAX  INTEGER   { 
				active(1),
				inactive(2)
		    }
	MAX-ACCESS  read-only
	STATUS  current
	DESCRIPTION
		"This variable displays the status of  the  entry.
		this value is only valid(1)."
	::= { axsOspfIfEntry 18 }

axsOspfIfMulticastForwarding OBJECT-TYPE
	SYNTAX  INTEGER  {
				blocked (1),		-- no multicast forwarding
				multicast (2),     -- using multicast address
				unicast (3)		-- to each OSPF neighbor
		    }
	MAX-ACCESS  read-only
	STATUS  current
	DESCRIPTION
		"The way multicasts should  forwarded  on  this
		interface;  not  forwarded,  forwarded  as data
		link multicasts, or forwarded as data link unicasts."
	::= { axsOspfIfEntry 19 }

axsOspfIfBackupDesignatedRouter OBJECT-TYPE
	SYNTAX  IpAddress
	MAX-ACCESS  read-only
	STATUS  current
	DESCRIPTION
		"The IP Address of the Backup Designated Router."
	::= { axsOspfIfEntry 15 }

axsOspfIfMetricTable OBJECT-TYPE
	SYNTAX  SEQUENCE OF AxsOspfIfMetricEntry
	MAX-ACCESS  not-accessible
	STATUS  current
	DESCRIPTION
		"The TOS metrics for a non-virtual interface identified
		by the interface index."
	::= { axsOspf 8 }

axsOspfIfMetricEntry OBJECT-TYPE
	SYNTAX  AxsOspfIfMetricEntry
	MAX-ACCESS  not-accessible
	STATUS  current
	DESCRIPTION
		"A particular TOS metric for a non-virtual interface
		identified by the interface index."
    INDEX { axsOspfIfMetricDomainNumber, axsOspfIfMetricIpAddress,
		    axsOspfIfMetricAddressLessIf, axsOspfIfMetricTOS }
	::= { axsOspfIfMetricTable 1 }

	AxsOspfIfMetricEntry ::=
		SEQUENCE {
		    axsOspfIfMetricDomainNumber	INTEGER,
		    axsOspfIfMetricIpAddress		IpAddress,
		    axsOspfIfMetricAddressLessIf	INTEGER,
		    axsOspfIfMetricTOS			INTEGER,
		    axsOspfIfMetricValue			INTEGER,
		    axsOspfIfMetricStatus		INTEGER
		}

axsOspfIfMetricDomainNumber OBJECT-TYPE
	SYNTAX  INTEGER
	MAX-ACCESS  read-only
	STATUS  current
	DESCRIPTION
		"The domain number of this OSPF interface."
	::= { axsOspfIfMetricEntry 1 }

axsOspfIfMetricIpAddress OBJECT-TYPE
	SYNTAX  IpAddress
	MAX-ACCESS  read-only
	STATUS  current
	DESCRIPTION
		"The IP address of this OSPF interface."
	::= { axsOspfIfMetricEntry 2 }

axsOspfIfMetricAddressLessIf OBJECT-TYPE
	SYNTAX  INTEGER
	MAX-ACCESS  read-only
	STATUS  current
	DESCRIPTION
		"For the purpose of easing  the  instancing  of
		addressed   and  addressless  interfaces;  This
		variable takes the value 0 on  interfaces  with
		IP  Addresses, and the value of ifIndex for in-
		terfaces having no IP Address."
	::= { axsOspfIfMetricEntry 3 }

axsOspfIfMetricTOS OBJECT-TYPE
	SYNTAX  INTEGER
	MAX-ACCESS  read-only
	STATUS  current
	DESCRIPTION
		"The type of service metric  being  referenced.
		this value is only 0."
	::= { axsOspfIfMetricEntry 4 }

axsOspfIfMetricValue OBJECT-TYPE
	SYNTAX  INTEGER
	MAX-ACCESS  read-only
	STATUS  current
	DESCRIPTION
		"The metric of using this type  of  service  on
		this interface."
	::= { axsOspfIfMetricEntry 5 }

axsOspfIfMetricStatus OBJECT-TYPE
	SYNTAX  INTEGER {
                                active(1)
                        }
	MAX-ACCESS  read-only
	STATUS  current
	DESCRIPTION
		"This variable displays the status of the entry.
		This entry status is only valid(1)."
	::= { axsOspfIfMetricEntry 6 }

axsOspfVirtIfTable OBJECT-TYPE
	SYNTAX  SEQUENCE OF AxsOspfVirtIfEntry
	MAX-ACCESS  not-accessible
	STATUS  current
	DESCRIPTION
		"Information about this router's virtual interfaces."
	::= { axsOspf 9 }

axsOspfVirtIfEntry OBJECT-TYPE
	SYNTAX  AxsOspfVirtIfEntry
	MAX-ACCESS  not-accessible
	STATUS  current
	DESCRIPTION
		"Information about a single Virtual Interface."
    INDEX { axsOspfVirtIfDomainNumber, axsOspfVirtIfAreaId,
		    axsOspfVirtIfNeighbor }
	::= { axsOspfVirtIfTable 1 }

	AxsOspfVirtIfEntry ::=
		SEQUENCE {
		    axsOspfVirtIfDomainNumber	INTEGER,
		    axsOspfVirtIfAreaId			IpAddress,
		    axsOspfVirtIfNeighbor		IpAddress,
		    axsOspfVirtIfTransitDelay	INTEGER,
		    axsOspfVirtIfRetransInterval	INTEGER,
		    axsOspfVirtIfHelloInterval	INTEGER,
		    axsOspfVirtIfRtrDeadInterval	INTEGER,
		    axsOspfVirtIfState			INTEGER,
		    axsOspfVirtIfEvents			Counter,
		    axsOspfVirtIfAuthKey			OCTET STRING,
		    axsOspfVirtIfStatus			INTEGER
		}

axsOspfVirtIfDomainNumber OBJECT-TYPE
	SYNTAX  INTEGER
	MAX-ACCESS  read-only
	STATUS  current
	DESCRIPTION
		"The domain number for this  Virtual Interface"
	::= { axsOspfVirtIfEntry 1 }

axsOspfVirtIfAreaId OBJECT-TYPE
	SYNTAX  IpAddress
	MAX-ACCESS  read-only
	STATUS  current
	DESCRIPTION
		"The Transit Area that the Virtual Link traverses."
	::= { axsOspfVirtIfEntry 2 }

axsOspfVirtIfNeighbor OBJECT-TYPE
	SYNTAX  IpAddress
	MAX-ACCESS  read-only
	STATUS  current
	DESCRIPTION
		"The Router ID of the Virtual Neighbor."
	::= { axsOspfVirtIfEntry 3 }

axsOspfVirtIfTransitDelay OBJECT-TYPE
	SYNTAX  INTEGER
	MAX-ACCESS  read-only
	STATUS  current
	DESCRIPTION
		"The estimated number of seconds  it  takes  to
		transmit  a link- state update packet over this
		interface."
	::= { axsOspfVirtIfEntry 4 }

axsOspfVirtIfRetransInterval OBJECT-TYPE
	SYNTAX  INTEGER
	MAX-ACCESS  read-only
	STATUS  current
	DESCRIPTION
		"The number of seconds between link-state advertisement
		retransmissions, for adjacencies belonging to this
		interface."
	::= { axsOspfVirtIfEntry 5 }

axsOspfVirtIfHelloInterval OBJECT-TYPE
	SYNTAX  INTEGER
	MAX-ACCESS  read-only
	STATUS  current
	DESCRIPTION
		"The length of time, in  seconds, between the
		Hello  packets that the router sends on the in-
		terface. "
	::= { axsOspfVirtIfEntry 6 }

axsOspfVirtIfRtrDeadInterval OBJECT-TYPE
	SYNTAX  INTEGER
	MAX-ACCESS  read-only
	STATUS  current
	DESCRIPTION
		"The number of seconds that  a  router's  Hello
		packets  have  not been seen before it's neighbors
		declare the router down."
	::= { axsOspfVirtIfEntry 7 }

axsOspfVirtIfState OBJECT-TYPE
	SYNTAX  INTEGER    {
				down (1),		    -- these use the same encoding
				pointToPoint (4)     -- as the axsOspfIfTable
		    }
	MAX-ACCESS  read-only
	STATUS  current
	DESCRIPTION
		"OSPF virtual interface states."
	::= { axsOspfVirtIfEntry 8 }

axsOspfVirtIfEvents OBJECT-TYPE
	SYNTAX  Counter
	MAX-ACCESS  read-only
	STATUS  current
	DESCRIPTION
		"The number of state changes or error events on
		this Virtual Link"
	::= { axsOspfVirtIfEntry 9 }

axsOspfVirtIfAuthKey OBJECT-TYPE
	SYNTAX  OCTET STRING
	MAX-ACCESS  read-only
	STATUS  current
	DESCRIPTION
		"Authentication key of this interface."
	::= { axsOspfVirtIfEntry 10 }

axsOspfVirtIfStatus OBJECT-TYPE
	SYNTAX  INTEGER    { 
				active(1),
				inactive(2)
		    }
	MAX-ACCESS  read-only
	STATUS  current
	DESCRIPTION
		"This variable displays the status of  the  entry.
		This entry is only valid(1)."
	::= { axsOspfVirtIfEntry 11 }

axsOspfNbrTable OBJECT-TYPE
	SYNTAX  SEQUENCE OF AxsOspfNbrEntry
	MAX-ACCESS  not-accessible
	STATUS  current
	DESCRIPTION
		"A table of non-virtual neighbor information."
	::= { axsOspf 10 }

axsOspfNbrEntry OBJECT-TYPE
	SYNTAX  AxsOspfNbrEntry
	MAX-ACCESS  not-accessible
	STATUS  current
	DESCRIPTION
		"The information regarding a single neighbor."
    INDEX { axsOspfNbrDomainNumber, axsOspfNbrIpAddr, axsOspfNbrAddressLessIndex }
	::= { axsOspfNbrTable 1 }

	AxsOspfNbrEntry ::=
		SEQUENCE {
		    axsOspfNbrDomainNumber		INTEGER,
		    axsOspfNbrIpAddr				IpAddress,
		    axsOspfNbrAddressLessIndex	INTEGER,
		    axsOspfNbrRtrId				IpAddress,
		    axsOspfNbrOptions			INTEGER,
		    axsOspfNbrPriority			INTEGER,
		    axsOspfNbrState				INTEGER,
		    axsOspfNbrEvents				Counter,
		    axsOspfNbrLsRetransQLen		Gauge,
		    axsOspfNbmaNbrStatus			INTEGER,
		    axsOspfNbmaNbrPermanence		INTEGER
		}

axsOspfNbrDomainNumber OBJECT-TYPE
	SYNTAX  INTEGER
	MAX-ACCESS  read-only
	STATUS  current
	DESCRIPTION
		"OSPF domain number of this neighbor."
	::= { axsOspfNbrEntry 1 }

axsOspfNbrIpAddr OBJECT-TYPE
	SYNTAX  IpAddress
	MAX-ACCESS  read-only
	STATUS  current
	DESCRIPTION
		"The IP address this neighbor is using  in  its
		IP  Source  Address."
	::= { axsOspfNbrEntry 2 }

axsOspfNbrAddressLessIndex OBJECT-TYPE
	SYNTAX  INTEGER
	MAX-ACCESS  read-only
	STATUS  current
	DESCRIPTION
		"On an interface having an  IP  Address,  zero.
		On  addressless  interfaces,  the corresponding
		value of ifIndex in the Internet Standard  MIB."
	::= { axsOspfNbrEntry 3 }

axsOspfNbrRtrId OBJECT-TYPE
	SYNTAX  IpAddress
	MAX-ACCESS  read-only
	STATUS  current
	DESCRIPTION
		"The integer uniquely identifying the neighboring
		router in the Autonomous System."
	::= { axsOspfNbrEntry 4 }

axsOspfNbrOptions OBJECT-TYPE
	SYNTAX  INTEGER
	MAX-ACCESS  read-only
	STATUS  current
	DESCRIPTION
		"A Bit Mask corresponding to the neighbor's op-
		 tions field.

		 Bit 0, if set, indicates that the  system  will
		 operate  on  Type of Service metrics other than
		 TOS 0.  If zero, the neighbor will  ignore  all
		 metrics except the TOS 0 metric.

		 Bit 1, if set, indicates  that  the  associated
		 area  accepts and operates on external informa-
		 tion; if zero, it is a stub area.

		 Bit 2, if set, indicates that the system is ca-
		 pable  of routing IP Multicast datagrams; i.e.,
		 that it implements the Multicast Extensions  to
		 OSPF.

		 Bit 3, if set, indicates  that  the  associated
		 area  is  an  NSSA.  These areas are capable of
		 carrying type 7 external advertisements,  which
		 are  translated into type 5 external advertise-
		 ments at NSSA borders."
	::= { axsOspfNbrEntry 5 }

axsOspfNbrPriority OBJECT-TYPE
	SYNTAX  INTEGER
	MAX-ACCESS  read-only
	STATUS  current
	DESCRIPTION
		"The priority of this neighbor."
	::= { axsOspfNbrEntry 6 }

axsOspfNbrState OBJECT-TYPE
	SYNTAX  INTEGER   {
				down (1),
				attempt (2),
				init (3),
				twoWay (4),
				exchangeStart (5),
				exchange (6),
				loading (7),
				full (8)
		    }
	MAX-ACCESS  read-only
	STATUS  current
	DESCRIPTION
		"The State of the relationship with this Neighbor."
	::= { axsOspfNbrEntry 7 }

axsOspfNbrEvents OBJECT-TYPE
	SYNTAX  Counter
	MAX-ACCESS  read-only
	STATUS  current
	DESCRIPTION
		"The number of times this neighbor relationship
		has changed state, or an error has occurred."
	::= { axsOspfNbrEntry 8 }

axsOspfNbrLsRetransQLen OBJECT-TYPE
	SYNTAX  Gauge
	MAX-ACCESS  read-only
	STATUS  current
	DESCRIPTION
		"The current length of the retransmission queue."
	::= { axsOspfNbrEntry 9 }

axsOspfNbmaNbrStatus OBJECT-TYPE
	SYNTAX  INTEGER {
                               active(1)
                        }
	MAX-ACCESS  read-only
	STATUS  current
	DESCRIPTION
		"This variable displays the status of the entry.
		This entry value is only valid(1). And enable to response
		this entry when axsOspfIfType is nbma."
	::= { axsOspfNbrEntry 10 }

axsOspfNbmaNbrPermanence OBJECT-TYPE
	SYNTAX  INTEGER  {
				dynamic (1),		-- learned through protocol
				 permanent (2)       -- configured address
		    }
	MAX-ACCESS  read-only
	STATUS  current
	DESCRIPTION
		"This variable displays the status of the entry."
	::= { axsOspfNbrEntry 11 }

axsOspfVirtNbrTable OBJECT-TYPE
	SYNTAX  SEQUENCE OF AxsOspfVirtNbrEntry
	MAX-ACCESS  not-accessible
	STATUS  current
	DESCRIPTION
		"A table of virtual neighbor information."
	::= { axsOspf 11 }

axsOspfVirtNbrEntry OBJECT-TYPE
	SYNTAX  AxsOspfVirtNbrEntry
	MAX-ACCESS  not-accessible
	STATUS  current
	DESCRIPTION
		"Virtual neighbor information."
    INDEX { axsOspfVirtNbrDomainNumber, axsOspfVirtNbrArea,
		    axsOspfVirtNbrRtrId }
	::= { axsOspfVirtNbrTable 1 }

	AxsOspfVirtNbrEntry ::=
		SEQUENCE {
		    axsOspfVirtNbrDomainNumber		INTEGER,
		    axsOspfVirtNbrArea				IpAddress,
		    axsOspfVirtNbrRtrId				IpAddress,
		    axsOspfVirtNbrIpAddr				IpAddress,
		    axsOspfVirtNbrOptions			INTEGER,
		    axsOspfVirtNbrState				INTEGER,
		    axsOspfVirtNbrEvents				Counter,
		    axsOspfVirtNbrLsRetransQLen		Gauge
		}

axsOspfVirtNbrDomainNumber OBJECT-TYPE
	SYNTAX  INTEGER
	MAX-ACCESS  read-only
	STATUS  current
	DESCRIPTION
		"The domain number."
	::= { axsOspfVirtNbrEntry 1 }

axsOspfVirtNbrArea OBJECT-TYPE
	SYNTAX  IpAddress
	MAX-ACCESS  read-only
	STATUS  current
	DESCRIPTION
		"The Transit Area Identifier."
	::= { axsOspfVirtNbrEntry 2 }

axsOspfVirtNbrRtrId OBJECT-TYPE
	SYNTAX  IpAddress
	MAX-ACCESS  read-only
	STATUS  current
	DESCRIPTION
		"A integer  uniquely  identifying  the neighboring
		 router in the Autonomous System."
	::= { axsOspfVirtNbrEntry 3 }

axsOspfVirtNbrIpAddr OBJECT-TYPE
	SYNTAX  IpAddress
	MAX-ACCESS  read-only
	STATUS  current
	DESCRIPTION
		"The IP address this Virtual Neighbor is using."
	::= { axsOspfVirtNbrEntry 4 }

axsOspfVirtNbrOptions OBJECT-TYPE
	SYNTAX  INTEGER
	MAX-ACCESS  read-only
	STATUS  current
	DESCRIPTION
		"A Bit Mask corresponding to the neighbor's options
		 field.

		 Bit 1, if set, indicates that the  system  will operate
		 on Type of Service metrics other than TOS 0. If zero,
		 the neighbor will  ignore  all metrics except the TOS
		 0 metric.

		 Bit 2, if set, indicates  that  the  system  is Network
		 Multicast  capable; ie, that it implements OSPF Multicast
		 Routing."
	::= { axsOspfVirtNbrEntry 5 }

axsOspfVirtNbrState OBJECT-TYPE
	SYNTAX  INTEGER   {
				down (1),
				attempt (2),
				init (3),
				twoWay (4),
				exchangeStart (5),
				exchange (6),
				loading (7),
				full (8)
		    }
	MAX-ACCESS  read-only
	STATUS  current
	DESCRIPTION
		"The state of the  Virtual  Neighbor  Relationship."
	::= { axsOspfVirtNbrEntry 6 }

axsOspfVirtNbrEvents OBJECT-TYPE
	SYNTAX  Counter
	MAX-ACCESS  read-only
	STATUS  current
	DESCRIPTION
		"The number of times this virtual link has changed
		its state, or an error has occurred."
	::= { axsOspfVirtNbrEntry 7 }

axsOspfVirtNbrLsRetransQLen OBJECT-TYPE
	SYNTAX  Gauge
	MAX-ACCESS  read-only
	STATUS  current
	DESCRIPTION
		"The current length of the retransmission queue."
	::= { axsOspfVirtNbrEntry 8 }

axsOspfExtLsdbTable OBJECT-TYPE
	SYNTAX  SEQUENCE OF AxsOspfExtLsdbEntry
	MAX-ACCESS  not-accessible
	STATUS  current
	DESCRIPTION
		"The OSPF Process's Links State Database."
	::= { axsOspf 12 }

axsOspfExtLsdbEntry OBJECT-TYPE
	SYNTAX  AxsOspfExtLsdbEntry
	MAX-ACCESS  not-accessible
	STATUS  current
	DESCRIPTION
		"A single Link State Advertisement."
    INDEX { axsOspfExtLsdbDomainNumber, axsOspfExtLsdbType,
		    axsOspfExtLsdbLsid, axsOspfExtLsdbRouterId }
	::= { axsOspfExtLsdbTable 1 }

	AxsOspfExtLsdbEntry ::=
		SEQUENCE {
		    axsOspfExtLsdbDomainNumber	INTEGER,
		    axsOspfExtLsdbType			INTEGER,
		    axsOspfExtLsdbLsid			IpAddress,
		    axsOspfExtLsdbRouterId		IpAddress,
		    axsOspfExtLsdbSequence		INTEGER,
		    axsOspfExtLsdbAge			INTEGER,
		    axsOspfExtLsdbChecksum		INTEGER,
		    axsOspfExtLsdbAdvertisement	OCTET STRING
		}

axsOspfExtLsdbDomainNumber OBJECT-TYPE
	SYNTAX  INTEGER
	MAX-ACCESS  read-only
	STATUS  current
	DESCRIPTION
		"OSPF domain number."
	::= { axsOspfExtLsdbEntry 1 }

axsOspfExtLsdbType OBJECT-TYPE
	SYNTAX  INTEGER {
				asExternalLink (5)
		    }
	MAX-ACCESS  read-only
	STATUS  current
	DESCRIPTION
		"The type  of  the  link  state  advertisement."
	::= { axsOspfExtLsdbEntry 2 }

axsOspfExtLsdbLsid OBJECT-TYPE
	SYNTAX  IpAddress
	MAX-ACCESS  read-only
	STATUS  current
	DESCRIPTION
		"The Link State ID is an LS Type Specific field
		 containing either a Router ID or an IP Address;
		 it identifies the piece of the  routing  domain
		 that is being described by the advertisement."
	::= { axsOspfExtLsdbEntry 3 }

axsOspfExtLsdbRouterId OBJECT-TYPE
	SYNTAX  IpAddress
	MAX-ACCESS  read-only
	STATUS  current
	DESCRIPTION
		"The 32 bit number that uniquely identifies the
		originating router in the Autonomous System."
	::= { axsOspfExtLsdbEntry 4 }

axsOspfExtLsdbSequence OBJECT-TYPE
	SYNTAX  INTEGER
	MAX-ACCESS  read-only
	STATUS  current
	DESCRIPTION
		"The sequence number field is a  signed  32-bit integer."
	::= { axsOspfExtLsdbEntry 5 }

axsOspfExtLsdbAge OBJECT-TYPE
	SYNTAX  INTEGER
	MAX-ACCESS  read-only
	STATUS  current
	DESCRIPTION
		"The age of the link state advertisement in seconds."
	::= { axsOspfExtLsdbEntry 6 }

axsOspfExtLsdbChecksum OBJECT-TYPE
	SYNTAX  INTEGER
	MAX-ACCESS  read-only
	STATUS  current
	DESCRIPTION
		"This field is the  checksum  of  the  complete
		 contents  of  the  advertisement, excepting the
		 age field.  The age field is excepted  so  that
		 an   advertisement's  age  can  be  incremented
		 without updating the  checksum."
	::= { axsOspfExtLsdbEntry 7 }

axsOspfExtLsdbAdvertisement OBJECT-TYPE
	SYNTAX  OCTET STRING
	MAX-ACCESS  read-only
	STATUS  current
	DESCRIPTION
		"The entire Link State Advertisement, including its header."
	::= { axsOspfExtLsdbEntry 8 }

axsOspfAreaAggregateTable OBJECT-TYPE
	SYNTAX  SEQUENCE OF AxsOspfAreaAggregateEntry
	MAX-ACCESS  not-accessible
	STATUS  current
	DESCRIPTION
		"A range of IP addresses  specified  by  an  IP
		address/IP  network  mask  pair."
	::= { axsOspf 14 }

axsOspfAreaAggregateEntry OBJECT-TYPE
	SYNTAX  AxsOspfAreaAggregateEntry
	MAX-ACCESS  not-accessible
	STATUS  current
	DESCRIPTION
		"A range of IP addresses  specified  by  an  IP
		address/IP  network  mask  pair."
    INDEX { axsOspfAreaAggregateDomainNumber, axsOspfAreaAggregateAreaID,
		    axsOspfAreaAggregateLsdbType, axsOspfAreaAggregateNet,
		    axsOspfAreaAggregateMask }
	::= { axsOspfAreaAggregateTable 1 }

	AxsOspfAreaAggregateEntry ::=
		SEQUENCE {
		    axsOspfAreaAggregateDomainNumber	INTEGER,
		    axsOspfAreaAggregateAreaID		IpAddress,
		    axsOspfAreaAggregateLsdbType		INTEGER,
		    axsOspfAreaAggregateNet			IpAddress,
		    axsOspfAreaAggregateMask			IpAddress,
		    axsOspfAreaAggregateStatus		INTEGER,
		    axsOspfAreaAggregateEffect		INTEGER
		}

axsOspfAreaAggregateDomainNumber OBJECT-TYPE
	SYNTAX  INTEGER
	MAX-ACCESS  read-only
	STATUS  current
	DESCRIPTION
		"OSPF domain number."
	::= { axsOspfAreaAggregateEntry 1 }

axsOspfAreaAggregateAreaID OBJECT-TYPE
	SYNTAX  IpAddress
	MAX-ACCESS  read-only
	STATUS  current
	DESCRIPTION
		"The Area the Address Aggregate is to be found within."
	::= { axsOspfAreaAggregateEntry 2 }

axsOspfAreaAggregateLsdbType OBJECT-TYPE
	SYNTAX  INTEGER  {
				summaryLink (3),
				nssaExternalLink (7)
		    }
	MAX-ACCESS  read-only
	STATUS  current
	DESCRIPTION
		"The type of the Address Aggregate. This field
		 specifies  the  Lsdb type that this Address 
		 Aggregate applies to."
	::= { axsOspfAreaAggregateEntry 3 }

axsOspfAreaAggregateNet OBJECT-TYPE
	SYNTAX  IpAddress
	MAX-ACCESS  read-only
	STATUS  current
	DESCRIPTION
		"The IP Address of the Net or Subnet indicated by the range."
	::= { axsOspfAreaAggregateEntry 4 }

axsOspfAreaAggregateMask OBJECT-TYPE
	SYNTAX  IpAddress
	MAX-ACCESS  read-only
	STATUS  current
	DESCRIPTION
		"The Subnet Mask that pertains to the Net or Subnet."
	::= { axsOspfAreaAggregateEntry 5 }

axsOspfAreaAggregateStatus OBJECT-TYPE
	SYNTAX  INTEGER {
                                     active(1)
                        }
	MAX-ACCESS  read-only
	STATUS  current
	DESCRIPTION
		"This variable displays the status of  the  entry.
		This entry value is only valid(1)."
	::= { axsOspfAreaAggregateEntry 6 }

axsOspfAreaAggregateEffect OBJECT-TYPE
	SYNTAX  INTEGER   {
				advertiseMatching (1),
				doNotAdvertiseMatching (2)
		    }
	MAX-ACCESS  read-only
	STATUS  current
	DESCRIPTION
		"Subnets subsumed by ranges either trigger  the
		 advertisement  of  the indicated aggregate (ad-
		 vertiseMatching), or result in the subnet's not
		 being advertised at all outside the area."
	::= { axsOspfAreaAggregateEntry 7 }

axsOspfTrapControlTable OBJECT-TYPE
	SYNTAX  SEQUENCE OF AxsOspfTrapControlEntry
	MAX-ACCESS  not-accessible
	STATUS  current
	DESCRIPTION
		"The table about trap information."
	::= { axsOspfTrap 1 }

axsOspfTrapControlEntry OBJECT-TYPE
	SYNTAX  AxsOspfTrapControlEntry
	MAX-ACCESS  not-accessible
	STATUS  current
	DESCRIPTION
		"The Entry about trap information."
	INDEX { axsOspfTrapDomainNumber }
	::= { axsOspfTrapControlTable 1 }

	AxsOspfTrapControlEntry ::=
	SEQUENCE {
		axsOspfTrapDomainNumber
			INTEGER,
		axsOspfSetTrap	
			OCTET STRING,
		axsOspfConfigErrorType	
			INTEGER,
		axsOspfPacketType	
			INTEGER,
		axsOspfPacketSrc	
			IpAddress
                }

axsOspfTrapDomainNumber OBJECT-TYPE
	SYNTAX  INTEGER
	MAX-ACCESS  read-only
	STATUS  current
	DESCRIPTION
		"axsOspfTrap domain number."
	::= { axsOspfTrapControlEntry 1 }

axsOspfSetTrap OBJECT-TYPE
       SYNTAX   OCTET STRING
       MAX-ACCESS   read-write
       STATUS   current
       DESCRIPTION
           "A four-octet string serving as a bit  map  for
           the trap events defined by the OSPF traps. This
           object is used to enable and  disable  specific
           OSPF   traps   where  a  1  in  the  bit  field
           represents enabled.  The right-most bit  (least
           significant) represents trap 0."
       ::= { axsOspfTrapControlEntry 2 }

axsOspfConfigErrorType OBJECT-TYPE
       SYNTAX   INTEGER   {
                   badVersion (1),
                   areaMismatch (2),
                   unknownNbmaNbr (3), -- Router is Dr eligible
                   unknownVirtualNbr (4),
                   authTypeMismatch(5),
                   authFailure (6),
                   netMaskMismatch (7),
                   helloIntervalMismatch (8),
                   deadIntervalMismatch (9),
                   optionMismatch (10),
		   duplicateRouterId (12),
		   noError (13)}
       MAX-ACCESS   read-only
       STATUS   current
       DESCRIPTION
           "Potential types  of  configuration  conflicts.
           Used  by the ospfConfigError and ospfConfigVir-
           tError traps."
       ::= { axsOspfTrapControlEntry 3 }

axsOspfPacketType OBJECT-TYPE
        SYNTAX   INTEGER   {
                    hello (1),
                    dbDescript (2),
                    lsReq (3),
                    lsUpdate (4),
                    lsAck (5), 
		    nullPacket (6)}
        MAX-ACCESS   read-only
        STATUS   current
        DESCRIPTION
           "OSPF packet types."
   ::= { axsOspfTrapControlEntry 4 }

axsOspfPacketSrc OBJECT-TYPE
        SYNTAX   IpAddress
        MAX-ACCESS   read-only
        STATUS   current
        DESCRIPTION
           "The IP address of an inbound packet that  can-
           not be identified by a neighbor instance."
       ::= { axsOspfTrapControlEntry 5 }

-- axsOspfv3

axsOspfv3GeneralTable OBJECT-TYPE
	SYNTAX  SEQUENCE OF AxsOspfv3GeneralEntry
	MAX-ACCESS  not-accessible
	STATUS  current
	DESCRIPTION
		"The table which ospfv3 information is stored in."
	::= { axsOspfv3 1 }

axsOspfv3GeneralEntry OBJECT-TYPE
	SYNTAX  AxsOspfv3GeneralEntry
	MAX-ACCESS  not-accessible
	STATUS  current
	DESCRIPTION
		"The list of the ospfv3 information."
	INDEX { axsOspfv3GeneralDomainNumber }
	::= { axsOspfv3GeneralTable 1 }

	AxsOspfv3GeneralEntry ::=
	SEQUENCE {
		axsOspfv3GeneralDomainNumber
			INTEGER,
		axsOspfv3RouterId
			RouterID,
		axsOspfv3AdminStat
			Status,
		axsOspfv3VersionNumber
			INTEGER,
		axsOspfv3AreaBdrRtrStatus
			TruthValue,
		axsOspfv3ASBdrRtrStatus
			TruthValue,
		axsOspfv3AsScopeLsaCount
			Gauge32,
		axsOspfv3AsScopeLsaCksumSum
			Integer32,
		axsOspfv3OriginateNewLsas
			Counter32,
		axsOspfv3RxNewLsas
			Counter32,
		axsOspfv3ExtAreaLsdbLimit
			Integer32,
		axsOspfv3MulticastExtensions
			Integer32,
		axsOspfv3DemandExtensions
			TruthValue,
		axsOspfv3TrafficEngineeringSupport
			TruthValue
		}

axsOspfv3GeneralDomainNumber OBJECT-TYPE
	SYNTAX  INTEGER
	MAX-ACCESS  read-only
	STATUS  current
	DESCRIPTION
		"ospfv3 domain number."
	::= { axsOspfv3GeneralEntry 1 }

axsOspfv3RouterId OBJECT-TYPE
	SYNTAX  RouterID
	MAX-ACCESS  read-only
	STATUS  current
	DESCRIPTION
		"A  32-bit  integer  uniquely  identifying  the
		router in the Autonomous System.
		By convention, to  ensure  uniqueness, this
		should  default  to  the  value  of  one of the
		router's IPv4 interface addresses if IPv4 is
		configured."
	::= { axsOspfv3GeneralEntry 2 }

axsOspfv3AdminStat OBJECT-TYPE
	SYNTAX  Status
	MAX-ACCESS  read-only
	STATUS  current
	DESCRIPTION
		"The  administrative  status  of  axsOspfv3  in  the
		router.  The  value 'enabled' denotes that the
		axsOspfv3 Process is active on at least  one  inter-
		face;  'disabled'  disables  it  on  all inter-
		faces."
	::= { axsOspfv3GeneralEntry 3 }

axsOspfv3VersionNumber OBJECT-TYPE
	SYNTAX  INTEGER { version3 (3) }
	MAX-ACCESS  read-only
	STATUS  current
	DESCRIPTION
		"The version number of OSPF for IPv6 is 3."
	::= { axsOspfv3GeneralEntry 4 }

axsOspfv3AreaBdrRtrStatus OBJECT-TYPE
	SYNTAX  TruthValue
	MAX-ACCESS  read-only
	STATUS  current
	DESCRIPTION
		"A flag to note whether this router is an  area
		border router."
	REFERENCE
		"OSPF Version 2, Section 3 Splitting the AS into
		Areas"
	::= { axsOspfv3GeneralEntry 5 }

axsOspfv3ASBdrRtrStatus OBJECT-TYPE
	SYNTAX  TruthValue
	MAX-ACCESS  read-only
	STATUS  current
	DESCRIPTION
		"A flag to note whether this router is  config-
		ured as an Autonomous System border router."
	REFERENCE
		"OSPF Version 2, Section 3.3  Classification  of
		routers"
	::= { axsOspfv3GeneralEntry 6 }

axsOspfv3AsScopeLsaCount OBJECT-TYPE
	SYNTAX  Gauge32
	MAX-ACCESS  read-only
	STATUS  current
	DESCRIPTION
		"The number of AS-Scope (e.g. AS-External) link-state
		advertisements in the link-state database."
	::= { axsOspfv3GeneralEntry 7 }

axsOspfv3AsScopeLsaCksumSum OBJECT-TYPE
	SYNTAX  Integer32
	MAX-ACCESS  read-only
	STATUS  current
	DESCRIPTION
		"The 32-bit unsigned sum of the LS checksums of
		the  AS-scoped link-state advertisements  con-
		tained in the link-state database. This sum
		can  be  used  to determine if there has been a
		change in a router's link state  database,  and
		to  compare  the  link-state  database  of  two
		routers."
	::= { axsOspfv3GeneralEntry 8 }

axsOspfv3OriginateNewLsas OBJECT-TYPE
	SYNTAX  Counter32
	MAX-ACCESS  read-only
	STATUS  current
	DESCRIPTION
		"The number of  new  link-state  advertisements
		that  have been originated.  This number is in-
		cremented each time the router originates a new
		LSA."
	::= { axsOspfv3GeneralEntry 9 }

axsOspfv3RxNewLsas OBJECT-TYPE
	SYNTAX  Counter32
	MAX-ACCESS  read-only
	STATUS  current
	DESCRIPTION
		"The number of  link-state  advertisements  re-
		ceived  determined  to  be  new instantiations.
		This number does not include  newer  instantia-
		tions  of self-originated link-state advertise-
		ments."
	::= { axsOspfv3GeneralEntry 10 }

axsOspfv3ExtAreaLsdbLimit OBJECT-TYPE
	SYNTAX  Integer32 (-1..'7FFFFFFF'h)
	MAX-ACCESS  read-only
	STATUS  current
	DESCRIPTION
		"The  maximum   number   of   non-default   AS-
		external-LSAs entries that can be stored in the
		link-state database.  If the value is -1,  then
		there is no limit.
		When the number of non-default AS-external-LSAs
		in  a  router's  link-state  database  reaches
		axsOspfv3ExtAreaLsdbLimit, the router  enters  Overflow-
		State.  The   router  never  holds  more  than
		axsOspfv3ExtAreaLsdbLimit  non-default  AS-external-LSAs
		in  its  database. OspfExtAreaLsdbLimit MUST be set
		identically in all routers attached to the axsOspfv3
		backbone  and/or  any regular axsOspfv3 area. (i.e.,
		axsOspfv3 stub areas and NSSAs are excluded)."
	DEFVAL { -1 }
	::= { axsOspfv3GeneralEntry 11 }

axsOspfv3MulticastExtensions OBJECT-TYPE
	SYNTAX  Integer32
	MAX-ACCESS  read-only
	STATUS  current
	DESCRIPTION
		"A Bit Mask indicating whether  the  router  is
		forwarding  IPv6  multicast datagrams
		based on the algorithms defined in  the  Multi-
		cast Extensions to OSPF.
		Bit 0, if set, indicates that  the  router  can
		forward  IPv6 multicast datagrams in the router's
		directly attached areas (called intra-area mul-
		ticast routing).
		Bit 1, if set, indicates that  the  router  can
		forward  IPv6  multicast  datagrams  between axsOspfv3
		areas (called inter-area multicast routing).
		Bit 2, if set, indicates that  the  router  can
		forward  IPv6  multicast  datagrams between Auto-
		nomous Systems (called inter-AS multicast rout-
		ing).
		Only certain combinations of bit  settings are
		allowed,  namely: 0 (no multicast forwarding is
		enabled), 1 (intra-area multicasting  only),  3
		(intra-area  and  inter-area  multicasting),  5
		(intra-area and inter-AS  multicasting)  and  7
		(multicasting  everywhere). By default, no mul-
		ticast forwarding is enabled."
	DEFVAL { 0 }
	::= { axsOspfv3GeneralEntry 12 }

axsOspfv3DemandExtensions OBJECT-TYPE
	SYNTAX  TruthValue
	MAX-ACCESS  read-only
	STATUS  current
	DESCRIPTION
		"The router's support for demand routing."
	REFERENCE
		"OSPF Version 2, Appendix on Demand Routing"
	::= { axsOspfv3GeneralEntry 14 }

axsOspfv3TrafficEngineeringSupport OBJECT-TYPE
	SYNTAX  TruthValue
	MAX-ACCESS  read-only
	STATUS  current
	DESCRIPTION
		"The router's support for traffic engineering
		extensions."
	::= { axsOspfv3GeneralEntry 15 }

--  The axsOspfv3 Area Data Structure contains information
--  regarding the various areas. The interfaces and
--  virtual links are configured as part of these areas.
--  Area 0.0.0.0, by definition, is the Backbone Area

axsOspfv3AreaTable OBJECT-TYPE
	SYNTAX  SEQUENCE OF AxsOspfv3AreaEntry
	MAX-ACCESS  not-accessible
	STATUS  current
	DESCRIPTION
		"Information describing the configured  parame-
		ters  and cumulative statistics of the router's
		attached areas."
	REFERENCE
		"OSPF Version 2, Section 6  The Area Data Struc-
		ture"
	::= { axsOspfv3 2 }

axsOspfv3AreaEntry OBJECT-TYPE
	SYNTAX  AxsOspfv3AreaEntry
	MAX-ACCESS  not-accessible
	STATUS  current
	DESCRIPTION
		"Information describing the configured  parame-
		ters  and  cumulative  statistics of one of the
		router's attached areas."
		INDEX { axsOspfv3AreaId }
	::= { axsOspfv3AreaTable 1 }

	AxsOspfv3AreaEntry ::=
		SEQUENCE {
			axsOspfv3AreaDomainNumber
				INTEGER,
			axsOspfv3AreaId
				AreaID,
			axsOspfv3ImportAsExtern
				INTEGER,
			axsOspfv3SpfRuns
				Counter32,
			axsOspfv3AreaBdrRtrCount
				Gauge32,
			axsOspfv3AsBdrRtrCount
				Gauge32,
			axsOspfv3AreaScopeLsaCount
				Gauge32,
			axsOspfv3AreaScopeLsaCksumSum
				Integer32,
			axsOspfv3AreaSummary
				INTEGER,
			axsOspfv3AreaStatus
				RowStatus,
			axsOspfv3StubMetric
				BigMetric
		}

axsOspfv3AreaDomainNumber OBJECT-TYPE
	SYNTAX  INTEGER
	MAX-ACCESS  read-only
	STATUS  current
	DESCRIPTION
		"ospfv3 domain number."
	::= { axsOspfv3AreaEntry 1 }

axsOspfv3AreaId OBJECT-TYPE
	SYNTAX  AreaID
	MAX-ACCESS  read-only
	STATUS  current
	DESCRIPTION
		"A 32-bit integer uniquely identifying an area.
		Area ID 0.0.0.0 is used for the axsOspfv3 backbone."
	REFERENCE
		"OSPF Version 2, Appendix C.2 Area parameters"
	::= { axsOspfv3AreaEntry 2 }

axsOspfv3ImportAsExtern OBJECT-TYPE
	SYNTAX  INTEGER {
	importExternal (1),  -- normal area
	importNoExternal (2), -- stub area
	importNssa (3)        -- not-so-stubby-area
	}
	MAX-ACCESS  read-only
	STATUS  current
	DESCRIPTION
		"Indicates whether an area is a Stub area, NSSA, or
		standard area. AS-scope LSAs are not imported into Stub
		Areas or NSSAs. NSSAs import AS-External data as Type-7
		LSAs which have Area-scope"
	REFERENCE
		"OSPF Version 2, Appendix C.2 Area parameters"
		DEFVAL { importExternal }
	::= { axsOspfv3AreaEntry 3 }

axsOspfv3SpfRuns OBJECT-TYPE
	SYNTAX  Counter32
	MAX-ACCESS  read-only
	STATUS  current
	DESCRIPTION
		"The number of times that the intra-area  route
		table  has  been  calculated  using this area's
		link-state database.  This  is  typically  done
		using Dijkstra's algorithm."
	::= { axsOspfv3AreaEntry 4 }

axsOspfv3AreaBdrRtrCount OBJECT-TYPE
	SYNTAX  Gauge32
	MAX-ACCESS  read-only
	STATUS  current
	DESCRIPTION
		"The total number of area border routers reach-
		able within this area. This is initially zero,
		and is calculated in each SPF Pass."
	::= { axsOspfv3AreaEntry 5 }

axsOspfv3AsBdrRtrCount OBJECT-TYPE
	SYNTAX  Gauge32
	MAX-ACCESS  read-only
	STATUS  current
	DESCRIPTION
		"The total number of Autonomous  System  border
		routers  reachable  within  this area.  This is
		initially zero, and is calculated in  each  SPF
		Pass."
	::= { axsOspfv3AreaEntry 6 }

axsOspfv3AreaScopeLsaCount OBJECT-TYPE
	SYNTAX  Gauge32
	MAX-ACCESS  read-only
	STATUS  current
	DESCRIPTION
	"The total number of Area-Scope link-state
	advertisements in  this  area's link-state
	database."
	::= { axsOspfv3AreaEntry 7 }

axsOspfv3AreaScopeLsaCksumSum OBJECT-TYPE
	SYNTAX  Integer32
	MAX-ACCESS  read-only
	STATUS  current
	DESCRIPTION
		"The 32-bit unsigned sum of the Area-Scope link-state
		advertisements'  LS  checksums  contained in this
		area's link-state database.  The sum can be used
		to determine if  there  has been  a  change  in a
		router's link state database, and to compare the
		link-state database of two routers."
		DEFVAL  { 0 }
	::= { axsOspfv3AreaEntry 8 }

axsOspfv3AreaSummary OBJECT-TYPE
	SYNTAX  INTEGER {
		noAreaSummary (1),
		sendAreaSummary (2)
	}
	MAX-ACCESS  read-only
	STATUS  current
	DESCRIPTION
		"The variable axsOspfv3AreaSummary controls the  im-
		port  of  summary LSAs into stub areas.  It has
		no effect on other areas.
		If it is noAreaSummary, the router will neither
		originate  nor  propagate summary LSAs into the
		stub area.  It will rely entirely  on  its  de-
		fault route.
		If it is sendAreaSummary, the router will  both
		summarize and propagate summary LSAs."
		DEFVAL  { noAreaSummary }
	::= { axsOspfv3AreaEntry 9 }

axsOspfv3AreaStatus OBJECT-TYPE
	SYNTAX  RowStatus
	MAX-ACCESS  read-only
	STATUS  current
	DESCRIPTION
		"This variable displays the status of  the  en-
		try.  Setting it to 'invalid' has the effect of
		rendering it inoperative.  The internal  effect
		(row removal) is implementation dependent."
	::= { axsOspfv3AreaEntry 10 }

axsOspfv3StubMetric OBJECT-TYPE
	SYNTAX  BigMetric
--	MAX-ACCESS  read-create
	MAX-ACCESS  read-only
	STATUS  current
	DESCRIPTION
		"The metric value advertised for the default route
		into Stub and NSSA areas."
	::= { axsOspfv3AreaEntry 11 }

--	axsOspfv3 AS-Scope Link State Database
--		The Link State Database contains the AS-Scope Link State
--		Advertisements from throughout the areas that the
--		device is attached to.

axsOspfv3AsLsdbTable OBJECT-TYPE
	SYNTAX  SEQUENCE OF AxsOspfv3AsLsdbEntry
	MAX-ACCESS  not-accessible
	STATUS  current
	DESCRIPTION
		"The axsOspfv3 Process's AS-Scope Link State Database."
	::= { axsOspfv3 3 }

axsOspfv3AsLsdbEntry OBJECT-TYPE
	SYNTAX  AxsOspfv3AsLsdbEntry
	MAX-ACCESS  not-accessible
	STATUS  current
	DESCRIPTION
	"A single AS-Scope Link State Advertisement."
	INDEX { axsOspfv3AsLsdbType,
			axsOspfv3AsLsdbRouterId,
			axsOspfv3AsLsdbLsid }
	::= { axsOspfv3AsLsdbTable 1 }

	AxsOspfv3AsLsdbEntry ::=
		SEQUENCE {
			axsOspfv3AsLsdbDomainNumber
				INTEGER,
			axsOspfv3AsLsdbType
				INTEGER,
			axsOspfv3AsLsdbRouterId
				RouterID,
			axsOspfv3AsLsdbLsid
				IpAddress,
			axsOspfv3AsLsdbSequence
				Integer32,
			axsOspfv3AsLsdbAge
				Integer32,
			axsOspfv3AsLsdbChecksum
				Integer32,
			axsOspfv3AsLsdbAdvertisement
				OCTET STRING
			}

axsOspfv3AsLsdbDomainNumber OBJECT-TYPE
	SYNTAX  INTEGER
	MAX-ACCESS  read-only
	STATUS  current
	DESCRIPTION
		"ospfv3 domain number."
	::= { axsOspfv3AsLsdbEntry 1 }

axsOspfv3AsLsdbType OBJECT-TYPE
	SYNTAX  INTEGER {
		asExternalLink (16389)  -- 0x4005
	}
	MAX-ACCESS  read-only
	STATUS  current
	DESCRIPTION
		"The type  of  the  link  state  advertisement.
		Each  link state type has a separate advertise-
		ment format. Unrecognized AS-Scope LSAs with the
		U-bit set are also store in this database."
	::= { axsOspfv3AsLsdbEntry 2 }

axsOspfv3AsLsdbRouterId OBJECT-TYPE
	SYNTAX  RouterID
	MAX-ACCESS  read-only
	STATUS  current
	DESCRIPTION
		"The 32 bit number that uniquely identifies the
		originating router in the Autonomous System."
	REFERENCE
		"OSPF Version 2, Appendix C.1 Global parameters"
	::= { axsOspfv3AsLsdbEntry 3 }

axsOspfv3AsLsdbLsid OBJECT-TYPE
	SYNTAX  IpAddress
	MAX-ACCESS  read-only
	STATUS  current
	DESCRIPTION
	"The Link State ID is an LS Type Specific field
	containing either a Router ID or a unique identifier;
	it identifies the piece of the  routing  domain
	that is being described by the advertisement.
	In contrast to OSPF for IPv4, the LSID has no
	addressing semantics."
	::= { axsOspfv3AsLsdbEntry 4 }

--  Note that the OSPF Sequence Number is a 32 bit signed
--  integer.  It starts with the value '80000001'h,
--  or -'7FFFFFFF'h, and increments until '7FFFFFFF'h
--  Thus, a typical sequence number will be very negative.

axsOspfv3AsLsdbSequence OBJECT-TYPE
	SYNTAX  Integer32
	MAX-ACCESS  read-only
	STATUS  current
	DESCRIPTION
		"The sequence number field is a  signed  32-bit
		integer.   It  is used to detect old and dupli-
		cate link state advertisements.  The  space  of
		sequence  numbers  is  linearly  ordered.  The
		larger the sequence number the more recent  the
		advertisement."
	REFERENCE
		"OSPF Version  2,  Section  12.1.6  LS  sequence
		number"
	::= { axsOspfv3AsLsdbEntry 5 }

axsOspfv3AsLsdbAge OBJECT-TYPE
	SYNTAX  Integer32  -- Should be 0..MaxAge
	MAX-ACCESS  read-only
	STATUS  current
	DESCRIPTION
		"This field is the age of the link state adver-
		tisement in seconds."
	REFERENCE
		"OSPF Version 2, Section 12.1.1 LS age"
	::= { axsOspfv3AsLsdbEntry 6 }

axsOspfv3AsLsdbChecksum OBJECT-TYPE
	SYNTAX  Integer32
	MAX-ACCESS  read-only
	STATUS  current
	DESCRIPTION
		"This field is the  checksum  of  the  complete
		contents  of  the  advertisement, excepting the
		age field.  The age field is excepted  so  that
		an  advertisement's  age  can  be  incremented
		without updating the  checksum.  The  checksum
		used  is  the same that is used for ISO connec-
		tionless datagrams; it is commonly referred  to
		as the Fletcher checksum."
	REFERENCE
		"OSPF Version 2, Section 12.1.7 LS checksum"
	::= { axsOspfv3AsLsdbEntry 7 }

axsOspfv3AsLsdbAdvertisement OBJECT-TYPE
	SYNTAX  OCTET STRING (SIZE (1..65535))
	MAX-ACCESS  read-only
	STATUS  current
	DESCRIPTION
	"The entire Link State Advertisement, including
	its header."
	::= { axsOspfv3AsLsdbEntry 8 }

--  axsOspfv3 Area-Scope Link State Database
--  The Link State Database contains the Area-Scope Link State
--  Advertisements from throughout the area that the
--  device is attached to.

axsOspfv3AreaLsdbTable OBJECT-TYPE
	SYNTAX  SEQUENCE OF AxsOspfv3AreaLsdbEntry
	MAX-ACCESS  not-accessible
	STATUS  current
	DESCRIPTION
		"The axsOspfv3 Process's Area-Scope Link State Database."
	::= { axsOspfv3 4 }

axsOspfv3AreaLsdbEntry OBJECT-TYPE
	SYNTAX  AxsOspfv3AreaLsdbEntry
	MAX-ACCESS  not-accessible
	STATUS  current
	DESCRIPTION
		"A single Area-Scope Link State Advertisement."
	INDEX { axsOspfv3AreaLsdbAreaId,
		axsOspfv3AreaLsdbType,
		axsOspfv3AreaLsdbRouterId,
		axsOspfv3AreaLsdbLsid }
	::= { axsOspfv3AreaLsdbTable 1 }

	AxsOspfv3AreaLsdbEntry ::=
		SEQUENCE {
		axsOspfv3AreaLsdbDomainNumber
			INTEGER,
		axsOspfv3AreaLsdbAreaId
			AreaID,
		axsOspfv3AreaLsdbType
			INTEGER,
		axsOspfv3AreaLsdbRouterId
			RouterID,
		axsOspfv3AreaLsdbLsid
			IpAddress,
		axsOspfv3AreaLsdbSequence
			Integer32,
		axsOspfv3AreaLsdbAge
			Integer32,
		axsOspfv3AreaLsdbChecksum
			Integer32,
		axsOspfv3AreaLsdbAdvertisement
			OCTET STRING
	}

axsOspfv3AreaLsdbDomainNumber OBJECT-TYPE
	SYNTAX  INTEGER
	MAX-ACCESS  read-only
	STATUS  current
	DESCRIPTION
		"ospfv3 domain number."
	::= { axsOspfv3AreaLsdbEntry 1 }

axsOspfv3AreaLsdbAreaId OBJECT-TYPE
	SYNTAX  AreaID
	MAX-ACCESS  read-only
	STATUS  current
	DESCRIPTION
		"The 32 bit identifier of the Area from which the
		LSA was received."
	REFERENCE
		"OSPF Version 2, Appendix C.2 Area parameters."
	::= { axsOspfv3AreaLsdbEntry 2 }

axsOspfv3AreaLsdbType OBJECT-TYPE
	SYNTAX  INTEGER {
		routerLsa          (8193),  -- 0x2001
		networkLsa         (8194),  -- 0x2002
		interAreaPrefixLsa (8195),  -- 0x2003
		interAreaRouterLsa (8196),  -- 0x2004
		groupMembershipLsa (8198),  -- 0x2006
		nssaExternalLsa    (8199),  -- 0x2007
		intraAreaPrefixLsa (8201)   -- 0x2009
	}
	MAX-ACCESS  read-only
	STATUS  current
	DESCRIPTION
		"The type  of  the  link  state  advertisement.
		Each  link state type has a separate advertise-
		ment format. Unrecognized Area-Scope LSAs with
		the U-bit set are also stored in this database."
	::= { axsOspfv3AreaLsdbEntry 3 }

axsOspfv3AreaLsdbRouterId OBJECT-TYPE
	SYNTAX  RouterID
	MAX-ACCESS  read-only
	STATUS  current
	DESCRIPTION
		"The 32 bit number that uniquely identifies the
		originating router in the Autonomous System."
	REFERENCE
		"OSPF Version 2, Appendix C.1 Global parameters"
	::= { axsOspfv3AreaLsdbEntry 4 }

axsOspfv3AreaLsdbLsid OBJECT-TYPE
	SYNTAX  IpAddress
	MAX-ACCESS  read-only
	STATUS  current
	DESCRIPTION
		"The Link State ID is an LS Type Specific field
		containing either a Router ID or a unique identifier;
		it identifies the piece of the  routing  domain
		that is being described by the advertisement.
		In contrast to OSPF for IPv4, the LSID has no
		addressing semantics."
	::= { axsOspfv3AreaLsdbEntry 5 }

--  Note that the OSPF Sequence Number is a 32 bit signed
--  integer.  It starts with the value '80000001'h,
--  or -'7FFFFFFF'h, and increments until '7FFFFFFF'h
--  Thus, a typical sequence number will be very negative.

axsOspfv3AreaLsdbSequence OBJECT-TYPE
	SYNTAX  Integer32
	MAX-ACCESS  read-only
	STATUS  current
	DESCRIPTION
		"The sequence number field is a  signed  32-bit
		integer.   It  is used to detect old and dupli-
		cate link state advertisements.  The  space  of
		sequence  numbers  is  linearly  ordered.   The
		larger the sequence number the more recent  the
		advertisement."
	REFERENCE
		"OSPF Version  2,  Section  12.1.6  LS  sequence
		number"
	::= { axsOspfv3AreaLsdbEntry 6 }

axsOspfv3AreaLsdbAge OBJECT-TYPE
	SYNTAX  Integer32  -- Should be 0..MaxAge
	MAX-ACCESS  read-only
	STATUS  current
	DESCRIPTION
		"This field is the age of the link state adver-
		tisement in seconds."
	REFERENCE
		"OSPF Version 2, Section 12.1.1 LS age"
	::= { axsOspfv3AreaLsdbEntry 7 }

axsOspfv3AreaLsdbChecksum OBJECT-TYPE
	SYNTAX  Integer32
	MAX-ACCESS  read-only
	STATUS  current
	DESCRIPTION
		"This field is the  checksum  of  the  complete
		contents  of  the  advertisement, excepting the
		age field.  The age field is excepted  so  that
		an  advertisement's  age  can  be  incremented
		without updating the  checksum.  The  checksum
		used  is  the same that is used for ISO connec-
		tionless datagrams; it is commonly referred  to
		as the Fletcher checksum."
	REFERENCE
		"OSPF Version 2, Section 12.1.7 LS checksum"
	::= { axsOspfv3AreaLsdbEntry 8 }

axsOspfv3AreaLsdbAdvertisement OBJECT-TYPE
	SYNTAX  OCTET STRING (SIZE (1..65535))
	MAX-ACCESS  read-only
	STATUS  current
	DESCRIPTION
		"The entire Link State Advertisement, including
		its header."
	::= { axsOspfv3AreaLsdbEntry 9 }

--  axsOspfv3 Link-Scope Link State Database
--    The Link State Database contains the Link-Scope Link State
--    Advertisements from the links that the
--    device is attached to.

axsOspfv3LinkLsdbTable OBJECT-TYPE
	SYNTAX  SEQUENCE OF AxsOspfv3LinkLsdbEntry
	MAX-ACCESS  not-accessible
	STATUS  current
	DESCRIPTION
		"The axsOspfv3 Process's Link-Scope Link State Database."
	::= { axsOspfv3 5 }

axsOspfv3LinkLsdbEntry OBJECT-TYPE
	SYNTAX  AxsOspfv3LinkLsdbEntry
	MAX-ACCESS  not-accessible
	STATUS  current
	DESCRIPTION
		"A single Link-Scope Link State Advertisement."
	INDEX { axsOspfv3LinkLsdbIfIndex,
		axsOspfv3LinkLsdbType,
		axsOspfv3LinkLsdbRouterId,
		axsOspfv3LinkLsdbLsid }
	::= { axsOspfv3LinkLsdbTable 1 }

	AxsOspfv3LinkLsdbEntry ::=
		SEQUENCE {
			axsOspfv3LinkLsdbDomainNumber
				INTEGER,
			axsOspfv3LinkLsdbIfIndex
				Ipv6IfIndex,
			axsOspfv3LinkLsdbType
				INTEGER,
			axsOspfv3LinkLsdbRouterId
				RouterID,
			axsOspfv3LinkLsdbLsid
				IpAddress,
			axsOspfv3LinkLsdbSequence
				Integer32,
			axsOspfv3LinkLsdbAge
				Integer32,
			axsOspfv3LinkLsdbChecksum
				Integer32,
			axsOspfv3LinkLsdbAdvertisement
				OCTET STRING
		}

axsOspfv3LinkLsdbDomainNumber OBJECT-TYPE
	SYNTAX  INTEGER
	MAX-ACCESS  read-only
	STATUS  current
	DESCRIPTION
		"ospfv3 domain number."
	::= { axsOspfv3LinkLsdbEntry 1 }

axsOspfv3LinkLsdbIfIndex OBJECT-TYPE
	SYNTAX  Ipv6IfIndex
	MAX-ACCESS  read-only
	STATUS  current
	DESCRIPTION
		"The identifier of the link from which the LSA
		was received."
	REFERENCE
		"OSPF Version 2, Appendix C.2 Area parameters"
	::= { axsOspfv3LinkLsdbEntry 2 }

axsOspfv3LinkLsdbType OBJECT-TYPE
	SYNTAX  INTEGER  {
		linkLsa (8)  -- 0x0008
	}
	MAX-ACCESS  read-only
	STATUS  current
	DESCRIPTION
		"The type  of  the  link  state  advertisement.
		Each  link state type has a separate advertise-
		ment format. Unrecognized Link-Scope LSAs with
		the U-bit set are also stored in this database."
	::= { axsOspfv3LinkLsdbEntry 3 }

axsOspfv3LinkLsdbRouterId OBJECT-TYPE
	SYNTAX  RouterID
	MAX-ACCESS  read-only
	STATUS  current
	DESCRIPTION
		"The 32 bit number that uniquely identifies the
		originating router in the Autonomous System."
	REFERENCE
		"OSPF Version 2, Appendix C.1 Global parameters"
	::= { axsOspfv3LinkLsdbEntry 4 }

axsOspfv3LinkLsdbLsid OBJECT-TYPE
	SYNTAX  IpAddress
	MAX-ACCESS  read-only
	STATUS  current
	DESCRIPTION
		"The Link State ID is an LS Type Specific field
		containing either a Router ID or a unique identifier;
		it identifies the piece of the  routing  domain
		that is being described by the advertisement.
		In contrast to OSPF for IPv4, the LSID has no
		addressing semantics."
	::= { axsOspfv3LinkLsdbEntry 5 }

--  Note that the OSPF Sequence Number is a 32 bit signed
--  integer.  It starts with the value '80000001'h,
--  or -'7FFFFFFF'h, and increments until '7FFFFFFF'h
--  Thus, a typical sequence number will be very negative.

axsOspfv3LinkLsdbSequence OBJECT-TYPE
	SYNTAX  Integer32
	MAX-ACCESS  read-only
	STATUS  current
	DESCRIPTION
		"The sequence number field is a  signed  32-bit
		integer.   It  is used to detect old and dupli-
		cate link state advertisements.  The  space  of
		sequence  numbers  is  linearly  ordered.  The
		larger the sequence number the more recent  the
		advertisement."
	REFERENCE
		"OSPF Version  2,  Section  12.1.6  LS  sequence
		number"
	::= { axsOspfv3LinkLsdbEntry 6 }

axsOspfv3LinkLsdbAge OBJECT-TYPE
	SYNTAX  Integer32  -- Should be 0..MaxAge
	MAX-ACCESS  read-only
	STATUS   current
	DESCRIPTION
		"This field is the age of the link state adver-
		tisement in seconds."
	REFERENCE
		"OSPF Version 2, Section 12.1.1 LS age"
	::= { axsOspfv3LinkLsdbEntry 7 }

axsOspfv3LinkLsdbChecksum OBJECT-TYPE
	SYNTAX  Integer32
	MAX-ACCESS  read-only
	STATUS  current
	DESCRIPTION
		"This field is the  checksum  of  the  complete
		contents  of  the  advertisement, excepting the
		age field.  The age field is excepted  so  that
		an  advertisement's  age  can  be  incremented
		without updating the  checksum.  The  checksum
		used  is  the same that is used for ISO connec-
		tionless datagrams; it is commonly referred  to
		as the Fletcher checksum."
	REFERENCE
		"OSPF Version 2, Section 12.1.7 LS checksum"
	::= { axsOspfv3LinkLsdbEntry 8 }

axsOspfv3LinkLsdbAdvertisement OBJECT-TYPE
	SYNTAX  OCTET STRING (SIZE (1..65535))
	MAX-ACCESS  read-only
	STATUS  current
	DESCRIPTION
		"The entire Link State Advertisement, including
		its header."
	::= { axsOspfv3LinkLsdbEntry 9 }

--  OSPF Host Table
--    The Host/Metric Table indicates what hosts are directly
--    attached to the Router, and what metrics and types of
--    service should be advertised for them.
--  axsOspfv3 Interface Table

axsOspfv3IfTable OBJECT-TYPE
	SYNTAX  SEQUENCE OF AxsOspfv3IfEntry
	MAX-ACCESS  not-accessible
	STATUS  current
	DESCRIPTION
		"The axsOspfv3 Interface Table describes the  inter-
		faces from the viewpoint of axsOspfv3."
	REFERENCE
		"OSPF Version 2, Appendix C.3  Router  interface
		parameters"
	::= { axsOspfv3 7 }

axsOspfv3IfEntry OBJECT-TYPE
	SYNTAX  AxsOspfv3IfEntry
	MAX-ACCESS  not-accessible
	STATUS  current
	DESCRIPTION
		"The axsOspfv3 Interface Entry describes one  inter-
		face from the viewpoint of axsOspfv3."
	INDEX { axsOspfv3IfIndex }
	::= { axsOspfv3IfTable 1 }

	AxsOspfv3IfEntry ::=
		SEQUENCE {
			axsOspfv3IfDomainNumber
				INTEGER,
			axsOspfv3IfIndex
				Ipv6IfIndex,
			axsOspfv3IfAreaId
				AreaID,
			axsOspfv3IfType
				INTEGER,
			axsOspfv3IfAdminStat
				Status,
			axsOspfv3IfRtrPriority
				DesignatedRouterPriority,
			axsOspfv3IfTransitDelay
				UpToMaxAge,
			axsOspfv3IfRetransInterval
				UpToMaxAge,
			axsOspfv3IfHelloInterval
				HelloRange,
			axsOspfv3IfRtrDeadInterval
				PositiveInteger,
			axsOspfv3IfPollInterval
				PositiveInteger,
			axsOspfv3IfState
				INTEGER,
			axsOspfv3IfDesignatedRouter
				RouterID,
			axsOspfv3IfBackupDesignatedRouter
				RouterID,
			axsOspfv3IfEvents
				Counter32,
			axsOspfv3IfStatus
				RowStatus,
			axsOspfv3IfMulticastForwarding
				INTEGER,
			axsOspfv3IfDemand
				TruthValue,
			axsOspfv3IfMetricValue
				Metric,
			axsOspfv3IfLinkScopeLsaCount
				Gauge32,
			axsOspfv3IfLinkLsaCksumSum
				Integer32,
			axsOspfv3IfInstId
				Integer32
			}

axsOspfv3IfDomainNumber OBJECT-TYPE
	SYNTAX  INTEGER
	MAX-ACCESS  read-only
	STATUS  current
	DESCRIPTION
		"ospfv3 domain number."
	::= { axsOspfv3IfEntry 1 }

axsOspfv3IfIndex OBJECT-TYPE
	SYNTAX  Ipv6IfIndex
	MAX-ACCESS  read-only
	STATUS  current
	DESCRIPTION
		"The interface index of this axsOspfv3 interface.
		It corresponds to the interface index of the
		Ipv6 interface on which axsOspfv3 is configured."
	::= { axsOspfv3IfEntry 2 }

axsOspfv3IfAreaId OBJECT-TYPE
	SYNTAX  AreaID
	MAX-ACCESS  read-only
	STATUS  current
	DESCRIPTION
		"A 32-bit integer uniquely identifying the area
		to  which  the  interface  connects.   Area  ID
		0.0.0.0 is used for the axsOspfv3 backbone."
	DEFVAL   { '00000000'H }  -- 0.0.0.0
	::= { axsOspfv3IfEntry 3 }

axsOspfv3IfType OBJECT-TYPE
	SYNTAX  INTEGER {
		broadcast (1),
		nbma (2),
		pointToPoint (3),
		pointToMultipoint (5)
	}
	MAX-ACCESS  read-only
	STATUS  current
	DESCRIPTION
		"The axsOspfv3 interface type."
	::= { axsOspfv3IfEntry 4 }

axsOspfv3IfAdminStat OBJECT-TYPE
	SYNTAX  Status
	MAX-ACCESS  read-only
	STATUS  current
	DESCRIPTION
		"The axsOspfv3 interface's  administrative  status.
		The  value formed on the interface, and the in-
		terface will be advertised as an internal route
		to  some  area.  The  value 'disabled' denotes
		that the interface is external to axsOspfv3."
	DEFVAL { enabled }
	::= { axsOspfv3IfEntry 5 }

axsOspfv3IfRtrPriority OBJECT-TYPE
	SYNTAX  DesignatedRouterPriority
	MAX-ACCESS  read-only
	STATUS  current
	DESCRIPTION
		"The  priority  of  this  interface.   Used  in
		multi-MAX-ACCESS  networks,  this  field is used in
		the designated router election algorithm.  The
		value 0 signifies that the router is not eligi-
		ble to become the  designated  router  on  this
		particular  network.   In the event of a tie in
		this value, routers will use their Router ID as
		a tie breaker."
	DEFVAL { 1 }
	::= { axsOspfv3IfEntry 6 }

axsOspfv3IfTransitDelay OBJECT-TYPE
	SYNTAX  UpToMaxAge
	MAX-ACCESS  read-only
	STATUS  current
	DESCRIPTION
		"The estimated number of seconds  it  takes  to
		transmit  a  link state update packet over this
		interface."
	DEFVAL { 1 }
	::= { axsOspfv3IfEntry 7 }

axsOspfv3IfRetransInterval OBJECT-TYPE
	SYNTAX  UpToMaxAge
	MAX-ACCESS  read-only
	STATUS  current
	DESCRIPTION
		"The number of seconds between  link-state  ad-
		vertisement  retransmissions,  for  adjacencies
		belonging to this  interface.  This  value  is
		also used when retransmitting database descrip-
		tion and link-state request packets."
	DEFVAL { 5 }
	::= { axsOspfv3IfEntry 8 }

axsOspfv3IfHelloInterval OBJECT-TYPE
	SYNTAX  HelloRange
	MAX-ACCESS  read-only
	STATUS  current
	DESCRIPTION
		"The length of time, in  seconds,  between  the
		Hello  packets that the router sends on the in-
		terface.  This value must be the same  for  all
		routers attached to a common network."
	DEFVAL { 10 }
	::= { axsOspfv3IfEntry 9 }

axsOspfv3IfRtrDeadInterval OBJECT-TYPE
	SYNTAX  PositiveInteger
	MAX-ACCESS  read-only
	STATUS  current
	DESCRIPTION
		"The number of seconds that  a  router's  Hello
		packets  have  not been seen before it's neigh-
		bors declare the router down.  This  should  be
		some  multiple  of  the  Hello  interval.  This
		value must be the same for all routers attached
		to a common network."
	DEFVAL { 40 }
	::= { axsOspfv3IfEntry 10 }

axsOspfv3IfPollInterval OBJECT-TYPE
	SYNTAX  PositiveInteger
	MAX-ACCESS  read-only
	STATUS  current
	DESCRIPTION
		"The larger time interval, in seconds,  between
		the  Hello  packets  sent  to  an inactive non-
		broadcast multi- access neighbor."
	DEFVAL { 120 }
	::= { axsOspfv3IfEntry 11 }

axsOspfv3IfState OBJECT-TYPE
	SYNTAX  INTEGER {
		down (1),
		loopback (2),
		waiting (3),
		pointToPoint (4),
		designatedRouter (5),
		backupDesignatedRouter (6),
		otherDesignatedRouter (7)
	}
	MAX-ACCESS  read-only
	STATUS  current
	DESCRIPTION
		"The axsOspfv3 Interface State."
	DEFVAL { down }
	::= { axsOspfv3IfEntry 12 }

axsOspfv3IfDesignatedRouter OBJECT-TYPE
	SYNTAX  RouterID
	MAX-ACCESS  read-only
	STATUS  current
	DESCRIPTION
		"The Router ID of the Designated Router."
	DEFVAL  { '00000000'H }  -- 0.0.0.0
	::= { axsOspfv3IfEntry 13 }

axsOspfv3IfBackupDesignatedRouter OBJECT-TYPE
	SYNTAX  RouterID
	MAX-ACCESS  read-only
	STATUS  current
	DESCRIPTION
		"The  Router ID of  the  Backup   Designated
		Router."
	DEFVAL  { '00000000'H }  -- 0.0.0.0
	::= { axsOspfv3IfEntry 15 }

axsOspfv3IfEvents OBJECT-TYPE
	SYNTAX  Counter32
	MAX-ACCESS  read-only
	STATUS  current
	DESCRIPTION
		"The number of times this  OSPF  interface  has
		changed its state, or an error has occurred."
	::= { axsOspfv3IfEntry 16 }

axsOspfv3IfStatus OBJECT-TYPE
	SYNTAX  RowStatus
	MAX-ACCESS  read-only
	STATUS  current
	DESCRIPTION
		"This variable displays the status of  the  en-
		try.  Setting it to 'invalid' has the effect of
		rendering it inoperative.  The internal  effect
		(row removal) is implementation dependent."
	::= { axsOspfv3IfEntry 18 }

axsOspfv3IfMulticastForwarding OBJECT-TYPE
	SYNTAX  INTEGER {
		blocked (1),   -- no multicast forwarding
		multicast (2), -- using multicast address
		unicast (3)    -- to each axsOspfv3 neighbor
		}
	MAX-ACCESS  read-only
	STATUS  current
	DESCRIPTION
		"The way multicasts should  forwarded  on  this
		interface;  not  forwarded,  forwarded  as data
		link multicasts, or forwarded as data link uni-
		casts.  Data link multicasting is not meaning-
		ful on point to point and NBMA interfaces, and
		setting axsOspfv3MulticastForwarding to 0 effective-
		ly disables all multicast forwarding."
	DEFVAL { blocked }
	::= { axsOspfv3IfEntry 19 }

axsOspfv3IfDemand OBJECT-TYPE
	SYNTAX  TruthValue
	MAX-ACCESS  read-only
	STATUS  current
	DESCRIPTION
		"Indicates whether Demand axsOspfv3 procedures (hel-
		lo supression to FULL neighbors and setting the
		DoNotAge flag on proogated LSAs) should be per-
		formed on this interface."
	DEFVAL { false }
	::= { axsOspfv3IfEntry 20 }

axsOspfv3IfMetricValue OBJECT-TYPE
	SYNTAX  Metric
	MAX-ACCESS  read-only
	STATUS  current
	DESCRIPTION
		"The metric assigned to this interface.
		The default value of the Metric is
		10^8 / ifSpeed."
	::= { axsOspfv3IfEntry 21 }

axsOspfv3IfLinkScopeLsaCount OBJECT-TYPE
	SYNTAX  Gauge32
	MAX-ACCESS  read-only
	STATUS  current
	DESCRIPTION
		"The total number of Link-Scope link-state
		advertisements in  this  link's link-state database."
	::= { axsOspfv3IfEntry 22 }

axsOspfv3IfLinkLsaCksumSum OBJECT-TYPE
	SYNTAX  Integer32
	MAX-ACCESS  read-only
	STATUS  current
	DESCRIPTION
		"The 32-bit unsigned sum of the Link-Scope link-state
		advertisements'  LS  checksums  contained in this
		link's link-state database.  The sum can be used
		to determine if  there  has been  a  change  in a
		router's link state database, and to compare the
		link-state database of two routers."
	DEFVAL  { 0 }
	::= { axsOspfv3IfEntry 23 }

axsOspfv3IfInstId OBJECT-TYPE
	SYNTAX  Integer32
	MAX-ACCESS  read-only
	STATUS  current
	DESCRIPTION
		"Enables multiple instances of axsOspfv3 to be run over
		a single link. Each protocol instance would be assigned
		a separate ID. This ID has local link significance
		only."
	DEFVAL  { 0 }
	::= { axsOspfv3IfEntry 24 }

--  axsOspfv3 Virtual Interface Table
--    The Virtual Interface Table describes the virtual
--    links that the axsOspfv3 Process is configured to
--    carry on.

axsOspfv3VirtIfTable OBJECT-TYPE
	SYNTAX  SEQUENCE OF AxsOspfv3VirtIfEntry
	MAX-ACCESS  not-accessible
	STATUS  current
	DESCRIPTION
		"Information about this router's virtual inter-
		faces."
	REFERENCE
		"OSPF Version  2,  Appendix  C.4   Virtual  link
		parameters"
	::= { axsOspfv3 8 }

axsOspfv3VirtIfEntry OBJECT-TYPE
	SYNTAX  AxsOspfv3VirtIfEntry
	MAX-ACCESS  not-accessible
	STATUS  current
	DESCRIPTION
		"Information about a single Virtual Interface."
		INDEX { axsOspfv3VirtIfAreaId, axsOspfv3VirtIfNeighbor }
	::= { axsOspfv3VirtIfTable 1 }

	AxsOspfv3VirtIfEntry ::=
		SEQUENCE {
			axsOspfv3VirtIfDomainNumber
				INTEGER,
			axsOspfv3VirtIfAreaId
				AreaID,
			axsOspfv3VirtIfNeighbor
				RouterID,
			axsOspfv3VirtIfIndex
				Ipv6IfIndex,
			axsOspfv3VirtIfTransitDelay
				UpToMaxAge,
			axsOspfv3VirtIfRetransInterval
				UpToMaxAge,
			axsOspfv3VirtIfHelloInterval
				HelloRange,
			axsOspfv3VirtIfRtrDeadInterval
				PositiveInteger,
			axsOspfv3VirtIfState
				INTEGER,
			axsOspfv3VirtIfEvents
				Counter32,
			axsOspfv3VirtIfStatus
				RowStatus,
			axsOspfv3VirtIfLinkScopeLsaCount
				Gauge32,
			axsOspfv3VirtIfLinkLsaCksumSum
				Integer32
			}

axsOspfv3VirtIfDomainNumber OBJECT-TYPE
	SYNTAX  INTEGER
	MAX-ACCESS  read-only
	STATUS  current
	DESCRIPTION
		"ospfv3 domain number."
	::= { axsOspfv3VirtIfEntry 1 }

axsOspfv3VirtIfAreaId OBJECT-TYPE
	SYNTAX  AreaID
	MAX-ACCESS  read-only
	STATUS  current
	DESCRIPTION
		"The  Transit  Area  that  the   Virtual   Link
		traverses.  By definition, this is not 0.0.0.0"
	::= { axsOspfv3VirtIfEntry 2 }

axsOspfv3VirtIfNeighbor OBJECT-TYPE
	SYNTAX  RouterID
	MAX-ACCESS  read-only
	STATUS current
	DESCRIPTION
		"The Router ID of the Virtual Neighbor."
	::= { axsOspfv3VirtIfEntry 3 }

axsOspfv3VirtIfIndex OBJECT-TYPE
	SYNTAX  Ipv6IfIndex
	MAX-ACCESS  read-only
	STATUS  current
	DESCRIPTION
		"The interface index of this axsOspfv3 virtual interface.
		It must be unique among all the interface indices
		on the router."
		::= { axsOspfv3VirtIfEntry 4 }

axsOspfv3VirtIfTransitDelay OBJECT-TYPE
	SYNTAX  UpToMaxAge
	MAX-ACCESS  read-only
	STATUS  current
	DESCRIPTION
		"The estimated number of seconds  it  takes  to
		transmit  a link- state update packet over this
		interface."
	DEFVAL { 1 }
	::= { axsOspfv3VirtIfEntry 5 }

axsOspfv3VirtIfRetransInterval OBJECT-TYPE
	SYNTAX  UpToMaxAge
	MAX-ACCESS  read-only
	STATUS  current
	DESCRIPTION
		"The number of seconds between  link-state  ad-
		vertisement  retransmissions,  for  adjacencies
		belonging to this  interface.  This  value  is
		also used when retransmitting database descrip-
		tion  and  link-state  request  packets.   This
		value  should  be well over the expected round-
		trip time."
	DEFVAL { 5 }
	::= { axsOspfv3VirtIfEntry 6 }

axsOspfv3VirtIfHelloInterval OBJECT-TYPE
	SYNTAX  HelloRange
	MAX-ACCESS  read-only
	STATUS  current
	DESCRIPTION
		"The length of time, in  seconds,  between  the
		Hello  packets that the router sends on the in-
		terface.  This value must be the same  for  the
		virtual neighbor."
	DEFVAL { 10 }
	::= { axsOspfv3VirtIfEntry 7 }

axsOspfv3VirtIfRtrDeadInterval OBJECT-TYPE
	SYNTAX  PositiveInteger
	MAX-ACCESS  read-only
	STATUS  current
	DESCRIPTION
		"The number of seconds that  a  router's  Hello
		packets  have  not been seen before it's neigh-
		bors declare the router down.  This  should  be
		some  multiple  of  the  Hello  interval.  This
		value must be the same for the  virtual  neigh-
		bor."
	DEFVAL { 60 }
	::= { axsOspfv3VirtIfEntry 8 }

axsOspfv3VirtIfState OBJECT-TYPE
	SYNTAX  INTEGER {
		down (1),    -- these use the same encoding
		pointToPoint (4) -- as the axsOspfv3IfTable
	}
	MAX-ACCESS  read-only
	STATUS  current
	DESCRIPTION
		"OSPF virtual interface states."
	DEFVAL  { down }
	::= { axsOspfv3VirtIfEntry 9 }

axsOspfv3VirtIfEvents OBJECT-TYPE
	SYNTAX  Counter32
	MAX-ACCESS  read-only
	STATUS  current
	DESCRIPTION
		"The number of state changes or error events on
		this Virtual Link"
	::= { axsOspfv3VirtIfEntry 10 }

axsOspfv3VirtIfStatus OBJECT-TYPE
	SYNTAX  RowStatus
	MAX-ACCESS  read-only
	STATUS  current
	DESCRIPTION
		"This variable displays the status of  the  en-
		try.  Setting it to 'invalid' has the effect of
		rendering it inoperative.  The internal  effect
		(row removal) is implementation dependent."
		::= { axsOspfv3VirtIfEntry 11 }

axsOspfv3VirtIfLinkScopeLsaCount OBJECT-TYPE
	SYNTAX  Gauge32
	MAX-ACCESS  read-only
	STATUS  current
	DESCRIPTION
		"The total number of Link-Scope link-state
		advertisements in  this  virtual link's link-state
		database."
	::= { axsOspfv3VirtIfEntry 12 }

axsOspfv3VirtIfLinkLsaCksumSum OBJECT-TYPE
	SYNTAX  Integer32
	MAX-ACCESS  read-only
	STATUS  current
	DESCRIPTION
		"The 32-bit unsigned sum of the Link-Scope link-state
		advertisements'  LS  checksums  contained in this
		virtual link's link-state database.  The sum can be used
		to determine if  there  has been  a  change  in a
		router's link state database, and to compare the
		link-state database of two routers."
	DEFVAL  { 0 }
	::= { axsOspfv3VirtIfEntry 13 }

--  axsOspfv3 Neighbor Table
--    The axsOspfv3 Neighbor Table describes all neighbors in
--    the locality of the subject router.

axsOspfv3NbrTable OBJECT-TYPE
	SYNTAX  SEQUENCE OF AxsOspfv3NbrEntry
	MAX-ACCESS  not-accessible
	STATUS  current
	DESCRIPTION
		"A table of non-virtual neighbor information."
	REFERENCE
		"OSPF Version 2, Section 10  The  Neighbor  Data
		Structure"
	::= { axsOspfv3 9 }

axsOspfv3NbrEntry OBJECT-TYPE
	SYNTAX  AxsOspfv3NbrEntry
	MAX-ACCESS  not-accessible
	STATUS  current
	DESCRIPTION
		"The information regarding a single neighbor."
	REFERENCE
		"OSPF Version 2, Section 10  The  Neighbor  Data
		Structure"
	INDEX { axsOspfv3NbrIfIndex, axsOspfv3NbrIpv6Addr }
	::= { axsOspfv3NbrTable 1 }

	AxsOspfv3NbrEntry ::=
		SEQUENCE {
			axsOspfv3NbrDomainNumber
				INTEGER,
			axsOspfv3NbrIfIndex
				Ipv6IfIndex,
			axsOspfv3NbrIpv6Addr
				Ipv6Address,
			axsOspfv3NbrRtrId
				RouterID,
			axsOspfv3NbrOptions
				Integer32,
			axsOspfv3NbrPriority
				DesignatedRouterPriority,
			axsOspfv3NbrState
				INTEGER,
			axsOspfv3NbrEvents
				Counter32,
			axsOspfv3NbrLsRetransQLen
				Gauge32,
			axsOspfv3NbrHelloSuppressed
				TruthValue,
			axsOspfv3NbrIfId
				Ipv6IfIndex
			}

axsOspfv3NbrDomainNumber OBJECT-TYPE
	SYNTAX  INTEGER
	MAX-ACCESS  read-only
	STATUS  current
	DESCRIPTION
		"ospfv3 domain number."
	::= { axsOspfv3NbrEntry 1 }

axsOspfv3NbrIfIndex OBJECT-TYPE
	SYNTAX  Ipv6IfIndex
	MAX-ACCESS  read-only
	STATUS  current
	DESCRIPTION
		"The local link ID of the link over which the
		neighbor can be reached."
	::= { axsOspfv3NbrEntry 2 }

axsOspfv3NbrIpv6Addr OBJECT-TYPE
	SYNTAX  Ipv6Address
	MAX-ACCESS  read-only
	STATUS  current
	DESCRIPTION
		"The IPv6 address of the neighbor associated with
		the local link."
	::= { axsOspfv3NbrEntry 3 }

axsOspfv3NbrRtrId OBJECT-TYPE
	SYNTAX  RouterID
	MAX-ACCESS  read-only
	STATUS  current
	DESCRIPTION
		"A 32-bit integer (represented as a type  IpAd-
		dress)  uniquely  identifying  the  neighboring
		router in the Autonomous System."
	::= { axsOspfv3NbrEntry 4 }

axsOspfv3NbrOptions OBJECT-TYPE
	SYNTAX  Integer32
	MAX-ACCESS  read-only
	STATUS  current
	DESCRIPTION
		"A Bit Mask corresponding to the neighbor's op-
		tions field."
	DEFVAL { 0 }
	::= { axsOspfv3NbrEntry 5 }

axsOspfv3NbrPriority OBJECT-TYPE
	SYNTAX  DesignatedRouterPriority
	MAX-ACCESS  read-only
	STATUS  current
	DESCRIPTION
		"The priority of this neighbor in the designat-
		ed router election algorithm.  The value 0 sig-
		nifies that the neighbor is not eligible to be-
		come  the  designated router on this particular
		network."
	DEFVAL { 1 }
	::= { axsOspfv3NbrEntry 6 }

axsOspfv3NbrState OBJECT-TYPE
	SYNTAX  INTEGER {
		down (1),
		attempt (2),
		init (3),
		twoWay (4),
		exchangeStart (5),
		exchange (6),
		loading (7),
		full (8)
	}
	MAX-ACCESS  read-only
	STATUS  current
	DESCRIPTION
		"The State of the relationship with this Neigh-
		bor."
	REFERENCE
		"OSPF Version 2, Section 10.1 Neighbor States"
	DEFVAL  { down }
	::= { axsOspfv3NbrEntry 7 }

axsOspfv3NbrEvents OBJECT-TYPE
	SYNTAX  Counter32
	MAX-ACCESS  read-only
	STATUS  current
	DESCRIPTION
		"The number of times this neighbor relationship
		has changed state, or an error has occurred."
	::= { axsOspfv3NbrEntry 8 }

axsOspfv3NbrLsRetransQLen OBJECT-TYPE
	SYNTAX  Gauge32
	MAX-ACCESS  read-only
	STATUS  current
	DESCRIPTION
		"The  current  length  of  the   retransmission
		queue."
	::= { axsOspfv3NbrEntry 9 }

axsOspfv3NbrHelloSuppressed OBJECT-TYPE
	SYNTAX  TruthValue
	MAX-ACCESS  read-only
	STATUS  current
	DESCRIPTION
		"Indicates whether Hellos are being  suppressed
		to the neighbor"
	::= { axsOspfv3NbrEntry 12 }

axsOspfv3NbrIfId OBJECT-TYPE
	SYNTAX  Ipv6IfIndex
	MAX-ACCESS  read-only
	STATUS  current
	DESCRIPTION
		"The interface ID that the neighbor advertises
		in its Hello Packets on this link, that is, the
		neighbor's local interface index."
	::= { axsOspfv3NbrEntry 13 }

--  axsOspfv3 Virtual Neighbor Table
--    This table describes all virtual neighbors.
--    Since Virtual Links are configured in the
--    virtual interface table, this table is read-only.

axsOspfv3VirtNbrTable OBJECT-TYPE
	SYNTAX  SEQUENCE OF AxsOspfv3VirtNbrEntry
	MAX-ACCESS  not-accessible
	STATUS  current
	DESCRIPTION
		"A table of virtual neighbor information."
	REFERENCE
		"OSPF Version 2, Section 15  Virtual Links"
	::= { axsOspfv3 10 }

axsOspfv3VirtNbrEntry OBJECT-TYPE
	SYNTAX  AxsOspfv3VirtNbrEntry
	MAX-ACCESS  not-accessible
	STATUS  current
	DESCRIPTION
		"Virtual neighbor information."
	INDEX { axsOspfv3VirtNbrArea, axsOspfv3VirtNbrRtrId }
	::= { axsOspfv3VirtNbrTable 1 }

	AxsOspfv3VirtNbrEntry ::=
		SEQUENCE {
			axsOspfv3VirtNbrDomainNumber
				INTEGER,
			axsOspfv3VirtNbrArea
				AreaID,
			axsOspfv3VirtNbrRtrId
				RouterID,
			axsOspfv3VirtNbrIfIndex
				Ipv6IfIndex,
			axsOspfv3VirtNbrIpv6Addr
				Ipv6Address,
			axsOspfv3VirtNbrOptions
				Integer32,
			axsOspfv3VirtNbrState
				INTEGER,
			axsOspfv3VirtNbrEvents
				Counter32,
			axsOspfv3VirtNbrLsRetransQLen
				Gauge32,
			axsOspfv3VirtNbrHelloSuppressed
				TruthValue,
			axsOspfv3VirtNbrIfId
				Ipv6IfIndex
			}

axsOspfv3VirtNbrDomainNumber OBJECT-TYPE
	SYNTAX  INTEGER
	MAX-ACCESS  read-only
	STATUS  current
	DESCRIPTION
		"ospfv3 domain number."
	::= { axsOspfv3VirtNbrEntry 1 }

axsOspfv3VirtNbrArea OBJECT-TYPE
	SYNTAX  AreaID
	MAX-ACCESS  read-only
	STATUS  current
	DESCRIPTION
		"The Transit Area Identifier."
	::= { axsOspfv3VirtNbrEntry 2 }

axsOspfv3VirtNbrRtrId OBJECT-TYPE
	SYNTAX  RouterID
	MAX-ACCESS  read-only
	STATUS  current
	DESCRIPTION
		"A  32-bit  integer  uniquely  identifying  the
		neighboring router in the Autonomous System."
	::= { axsOspfv3VirtNbrEntry 3 }

axsOspfv3VirtNbrIfIndex OBJECT-TYPE
	SYNTAX  Ipv6IfIndex
	MAX-ACCESS  read-only
	STATUS  current
	DESCRIPTION
		"The local link ID for the virtual link over
		which the neighbor can be reached."
	::= { axsOspfv3VirtNbrEntry 4 }

axsOspfv3VirtNbrIpv6Addr OBJECT-TYPE
	SYNTAX  Ipv6Address
	MAX-ACCESS  read-only
	STATUS  current
	DESCRIPTION
		"The IPv6 address used to reach this Virtual Neighbor.
		It must be a Site-Local or Global scope address."
	::= { axsOspfv3VirtNbrEntry 5 }

axsOspfv3VirtNbrOptions OBJECT-TYPE
	SYNTAX  Integer32
	MAX-ACCESS  read-only
	STATUS  current
	DESCRIPTION
		"A Bit Mask corresponding to the neighbor's op-
		tions field."
	::= { axsOspfv3VirtNbrEntry 6 }

axsOspfv3VirtNbrState OBJECT-TYPE
	SYNTAX  INTEGER {
		down (1),
		attempt (2),
		init (3),
		twoWay (4),
		exchangeStart (5),
		exchange (6),
		loading (7),
		full (8)
	}
	MAX-ACCESS  read-only
	STATUS  current
	DESCRIPTION
		"The state of the  Virtual  Neighbor  Relation-
		ship."
	::= { axsOspfv3VirtNbrEntry 7 }

axsOspfv3VirtNbrEvents OBJECT-TYPE
	SYNTAX  Counter32
	MAX-ACCESS  read-only
	STATUS  current
	DESCRIPTION
		"The number of  times  this  virtual  link  has
		changed its state, or an error has occurred."
	::= { axsOspfv3VirtNbrEntry 8 }

axsOspfv3VirtNbrLsRetransQLen OBJECT-TYPE
	SYNTAX  Gauge32
	MAX-ACCESS  read-only
	STATUS  current
	DESCRIPTION
		"The  current  length  of  the   retransmission
		queue."
	::= { axsOspfv3VirtNbrEntry 9 }

axsOspfv3VirtNbrHelloSuppressed OBJECT-TYPE
	SYNTAX  TruthValue
	MAX-ACCESS  read-only
	STATUS  current
	DESCRIPTION
		"Indicates whether Hellos are being  suppressed
		to the neighbor"
	::= { axsOspfv3VirtNbrEntry 10 }

axsOspfv3VirtNbrIfId OBJECT-TYPE
	SYNTAX  Ipv6IfIndex
	MAX-ACCESS  read-only
	STATUS  current
	DESCRIPTION
		"The interface ID that the neighbor advertises
		in its Hello Packets on this virtual link, that is,
		the neighbor's local interface index."
	::= { axsOspfv3VirtNbrEntry 11 }

 --
 --    The axsOspfv3 Area Aggregate Table
 --

axsOspfv3AreaAggregateTable OBJECT-TYPE
	SYNTAX  SEQUENCE OF AxsOspfv3AreaAggregateEntry
	MAX-ACCESS  not-accessible
	STATUS  current
	DESCRIPTION
		"A range of IPv6 prefixes specified by a
		prefix/prefix length  pair. Note that if
		ranges are configured such that one range sub-
		sumes  another range the most specific match is
		the preferred one."
	::= { axsOspfv3 11 }

axsOspfv3AreaAggregateEntry OBJECT-TYPE
	SYNTAX  AxsOspfv3AreaAggregateEntry
	MAX-ACCESS  not-accessible
	STATUS  current
	DESCRIPTION
		"A range of IPv6 prefixes specified by a
		prefix/prefix length  pair. Note that if
		ranges are configured such that one range sub-
		sumes  another range the most specific match is
		the preferred one."
	REFERENCE
		"OSPF Version 2, Appendix C.2  Area parameters"
	INDEX { axsOspfv3AreaAggregateAreaID,
		axsOspfv3AreaAggregateAreaLsdbType,
		axsOspfv3AreaAggregateIndex }
	::= { axsOspfv3AreaAggregateTable 1 }

	AxsOspfv3AreaAggregateEntry ::=
		SEQUENCE {
			axsOspfv3AreaAggregateDomainNumber
				INTEGER,
			axsOspfv3AreaAggregateAreaID
				AreaID,
			axsOspfv3AreaAggregateAreaLsdbType
				INTEGER,
			axsOspfv3AreaAggregateIndex
				INTEGER,
			axsOspfv3AreaAggregatePrefix
				Ipv6AddressPrefix,
			axsOspfv3AreaAggregatePrefixLen
				INTEGER,
			axsOspfv3AreaAggregateStatus
				RowStatus,
			axsOspfv3AreaAggregateEffect
				INTEGER
			}

axsOspfv3AreaAggregateDomainNumber OBJECT-TYPE
	SYNTAX  INTEGER
	MAX-ACCESS  read-only
	STATUS  current
	DESCRIPTION
		"ospfv3 domain number."
	::= { axsOspfv3AreaAggregateEntry 1 }

axsOspfv3AreaAggregateAreaID OBJECT-TYPE
	SYNTAX  AreaID
	MAX-ACCESS  read-only
	STATUS  current
	DESCRIPTION
		"The Area the Address Aggregate is to be  found
		within."
	REFERENCE
		"OSPF Version 2, Appendix C.2 Area parameters"
	::= { axsOspfv3AreaAggregateEntry 2 }

axsOspfv3AreaAggregateAreaLsdbType OBJECT-TYPE
	SYNTAX  INTEGER {
		interAreaPrefixLsa (8195), -- 0x2003
		nssaExternalLsa    (8199)  -- 0x2007
	}
	MAX-ACCESS  read-only
	STATUS  current
	DESCRIPTION
		"The type of the Address Aggregate.  This field
		specifies  the  Area Lsdb type that this Address Ag-
		gregate applies to."
	REFERENCE
		"OSPF Version 2, Appendix A.4.1 The  Link  State
		Advertisement header"
	::= { axsOspfv3AreaAggregateEntry 3 }

axsOspfv3AreaAggregateIndex OBJECT-TYPE
	SYNTAX  INTEGER (1..2147483647)
	MAX-ACCESS  read-only
	STATUS  current
	DESCRIPTION
		"A unique identifier for this aggregate table entry."
	::= { axsOspfv3AreaAggregateEntry 4 }

axsOspfv3AreaAggregatePrefix OBJECT-TYPE
	SYNTAX  Ipv6AddressPrefix
	MAX-ACCESS  read-only
	STATUS  current
	DESCRIPTION
		"The IPv6 Prefix."
	REFERENCE
		"OSPF Version 2, Appendix C.2 Area parameters"
	::= { axsOspfv3AreaAggregateEntry 5 }

axsOspfv3AreaAggregatePrefixLen OBJECT-TYPE
	SYNTAX  INTEGER ( 3..128 )
--	UNITS  "BITS"
	MAX-ACCESS  read-only
	STATUS  current
	DESCRIPTION
		"The length of the prefix (in BITS). A prefix can
		not be shorter than 3 BITS."
	REFERENCE
		"OSPF Version 2, Appendix C.2 Area parameters"
	::= { axsOspfv3AreaAggregateEntry 6 }

axsOspfv3AreaAggregateStatus OBJECT-TYPE
	SYNTAX  RowStatus
	MAX-ACCESS  read-only
	STATUS  current
	DESCRIPTION
		"This variable displays the status of  the  en-
		try.  Setting it to 'invalid' has the effect of
		rendering it inoperative.  The internal  effect
		(row removal) is implementation dependent."
	::= { axsOspfv3AreaAggregateEntry 7 }

axsOspfv3AreaAggregateEffect OBJECT-TYPE
	SYNTAX  INTEGER {
		advertiseMatching (1),
		doNotAdvertiseMatching (2)
	}
	MAX-ACCESS  read-only
	STATUS  current
	DESCRIPTION
		"Prefixes subsumed by ranges either trigger  the
		advertisement  of  the indicated aggregate (ad-
		vertiseMatching), or result in the prefix not
		being advertised at all outside the area."
	DEFVAL  { advertiseMatching }
	::= { axsOspfv3AreaAggregateEntry 8 }

--  axsStatic
axsStaticTable OBJECT-TYPE
	SYNTAX  SEQUENCE OF AxsStaticGatewayEntry
	MAX-ACCESS  not-accessible
	STATUS  current
	DESCRIPTION
		"The set of instances of the static gateway state."
	::= { axsStatic 1 }

axsStaticGatewayEntry OBJECT-TYPE
	SYNTAX  AxsStaticGatewayEntry
	MAX-ACCESS  not-accessible
	STATUS  current
	DESCRIPTION
		"Each row defines information about static route gateway state."
    INDEX { axsStaticGatewayAddr }
	::= { axsStaticTable 1 }

	AxsStaticGatewayEntry ::=
		SEQUENCE {
		    axsStaticGatewayAddr		IpAddress,
		    axsStaticGatewayState		INTEGER
		}
		
axsStaticGatewayAddr OBJECT-TYPE
	SYNTAX  IpAddress
	MAX-ACCESS  not-accessible
	STATUS  current
	DESCRIPTION
		"The static route gateway address."
	::= { axsStaticGatewayEntry 1 }
	
axsStaticGatewayState OBJECT-TYPE
	SYNTAX  INTEGER
	MAX-ACCESS  not-accessible
	STATUS  current
	DESCRIPTION
		"The state of static route gateway."
	::= { axsStaticGatewayEntry 2 }	
	
--  axsLogin

axsLoginName OBJECT-TYPE
	SYNTAX  DisplayString
	MAX-ACCESS  not-accessible
	STATUS  current
	DESCRIPTION
		"Log in user name."
	::= { axsLogin 1 }

axsLoginTime OBJECT-TYPE
	SYNTAX  DisplayString
	MAX-ACCESS  not-accessible
	STATUS  current
	DESCRIPTION
		"Date, time and time zone of user log in.
                 Format : YYYY/MM/DD hh:mm:ss XXXXXX(time zone)
		 Time zone format :
		   JST    : JST
                   GMT+09 : GMT + 09 hours
                   GMT+10 : GMT + 10 hours"
	::= { axsLogin 2 }

axsLogoutTime OBJECT-TYPE
	SYNTAX  DisplayString
	MAX-ACCESS  not-accessible
	STATUS  current
	DESCRIPTION
		"Date, time and time zone of user log out.
		Format : YYYY/MM/DD hh:mm:ss XXXXXX(time zone)
		Time zone format :
		  JST    : JST
		  GMT+09 : GMT + 09 hours
		  GMT+10 : GMT + 10 hours"
	::= { axsLogin 3 }

axsLoginFailureTime OBJECT-TYPE
	SYNTAX  DisplayString
	MAX-ACCESS  not-accessible
	STATUS  current
	DESCRIPTION
		"Date, time and time zone of user log in failure.
		Format : YYYY/MM/DD hh:mm:ss XXXXXX(time zone)
		Time zone format :
		  JST    : JST
		  GMT+09 : GMT + 09 hours
		  GMT+10 : GMT + 10 hours"
	::= { axsLogin 4 }

axsLoginLocation OBJECT-TYPE
	SYNTAX  DisplayString
	MAX-ACCESS  not-accessible
	STATUS  current
	DESCRIPTION
		"Terminal information of log in user.
		The status will be 'console' or 'aux'.
		If other, displays 'TERMINAL(APLLICATION)'.
		ex. 'tty/1(telnet)'"
	::= { axsLogin 5 }

axsLoginLine OBJECT-TYPE
	SYNTAX  DisplayString
	MAX-ACCESS  not-accessible
	STATUS  current
	DESCRIPTION
		"Connection information of log in user.
		The status will be 'console' or 'aux'.
		If other, displays 'IPADDRESS(APLLICATION)'.
		ex. '192.168.11.1(telnet)'"
	::= { axsLogin 6 }

axsLogoutStatus OBJECT-TYPE
	SYNTAX  INTEGER {
		error(1),
		success(2),
		timeout(3),
		disconnect(4),
		force(5)
	      }
	MAX-ACCESS  not-accessible
	STATUS  current
	DESCRIPTION
		"Log out factor.
		 error(1)      : log out due to none of bellow
		 success(2)    : log out due to command
		 timeout(3)    : log out due to 'auto-logout'
		 disconnect(4) : log out due to line disconnection
		 force(5)      : log out due to other user's command"
	::= { axsLogin 7 }

--  axsBootManagement group

axsBootReason  OBJECT-TYPE
	SYNTAX  INTEGER {
		power-on(1),
		reload(2),
		system-fault(3),
		system-stall(4),
		reset(5),
		fail-over(6),
		default-restart(7)
	      }
	MAX-ACCESS  read-only
	STATUS  current
	DESCRIPTION
		"Reason of system start."
	::= { axsBootManagement 1 }

--  axslldp group
--  axslldpConfiguration group

axslldpMessageTxInterval OBJECT-TYPE
	SYNTAX  INTEGER
	MAX-ACCESS  read-only
	STATUS  current
	DESCRIPTION
		"LDPDU transmitting interval"
	::= { axslldpConfiguration 1 }

axslldpMessageTxHoldMultiplier OBJECT-TYPE
	SYNTAX  INTEGER
	MAX-ACCESS  read-only
	STATUS  current
	DESCRIPTION
		"Time coefficient for contiguity equipment to hold about the LLDP frame which this equipment transmitted"
	::= { axslldpConfiguration 2 }

axslldpPortConfigTable OBJECT-TYPE
	SYNTAX  SEQUENCE OF AxslldpPortConfigEntry
	MAX-ACCESS  not-accessible
	STATUS  current
	DESCRIPTION
		"The table about LDPDU transmission"
	::= { axslldpConfiguration 6 }

axslldpPortConfigEntry OBJECT-TYPE
	SYNTAX  AxslldpPortConfigEntry
	MAX-ACCESS  not-accessible
	STATUS  current
	DESCRIPTION
		"The entry about LDPDU transmission"
    INDEX { axslldpPortConfigPortNum }
	::= { axslldpPortConfigTable 1 }

	AxslldpPortConfigEntry ::=
		SEQUENCE {
		    axslldpPortConfigPortNum		INTEGER,
		    axslldpPortConfigAdminStatus		INTEGER,
		    axslldpPortConfigTLVsTxEnable	BITS,
		    axslldpPortConfigRowStatus		RowStatus
		}

axslldpPortConfigPortNum OBJECT-TYPE
	SYNTAX  INTEGER
	MAX-ACCESS  not-accessible
	STATUS  current
	DESCRIPTION
		"Port discernment index"
	::= {axslldpPortConfigEntry 2 }

axslldpPortConfigAdminStatus OBJECT-TYPE
	SYNTAX  INTEGER {
                                       txOnly(1),
                                       rxOnly(2),
                                       txAndRx(3),
                                       disabled(4)
                        }
	MAX-ACCESS  read-only
	STATUS  current
	DESCRIPTION
		"The port state of this equipment about transmission and reception of LDPDU"
	::= {axslldpPortConfigEntry 3 }

axslldpPortConfigTLVsTxEnable OBJECT-TYPE
	    SYNTAX      BITS {foo0(0),foo1(1),foo2(2),foo3(3),
                        portDesc(4),
                        sysName(5),
                        sysDesc(6),
                        sysCap(7)
                          }	
	MAX-ACCESS  read-only
	STATUS  current
	DESCRIPTION
		"The TLV state about the port concerned which can be transmitted"
	::= {axslldpPortConfigEntry 4 }

axslldpPortConfigRowStatus OBJECT-TYPE
	SYNTAX  RowStatus
	MAX-ACCESS  read-only
	STATUS  current
	DESCRIPTION
		"The state of this entry"
	::= {axslldpPortConfigEntry 5 }

-- axslldpStats group

axslldpStatsTable OBJECT-TYPE
	SYNTAX  SEQUENCE OF AxslldpStatsEntry
	MAX-ACCESS  not-accessible
	STATUS  current
	DESCRIPTION
		"The table about LLDP statistics information"
	::= { axslldpStats 1 }

axslldpStatsEntry OBJECT-TYPE
	SYNTAX  AxslldpStatsEntry
	MAX-ACCESS  not-accessible
	STATUS  current
	DESCRIPTION
		"The Entry about LLDP statistics information"
    INDEX { axslldpStatsPortNum }
	::= { axslldpStatsTable 1 }

	AxslldpStatsEntry ::=
		SEQUENCE {
		    axslldpStatsPortNum			INTEGER,
		    axslldpStatsOperStatus		INTEGER,
		    axslldpStatsFramesInErrors		Counter,
		    axslldpStatsFramesInTotal		Counter,
		    axslldpStatsFramesOutTotal		Counter,
		    axslldpStatsTLVsInErrors		Counter,
		    axslldpStatsTLVsDiscardedTotal	Counter
		}

axslldpStatsPortNum OBJECT-TYPE
	SYNTAX  INTEGER
	MAX-ACCESS  not-accessible
	STATUS  current
	DESCRIPTION
		"Port discernment index"
	::= {axslldpStatsEntry 2 }

axslldpStatsOperStatus OBJECT-TYPE
	SYNTAX  INTEGER
	MAX-ACCESS  read-only
	STATUS  current
	DESCRIPTION
		"The employment state about the port concerned"
	::= {axslldpStatsEntry 3 }

axslldpStatsFramesInErrors OBJECT-TYPE
	SYNTAX  Counter
	MAX-ACCESS  read-only
	STATUS  current
	DESCRIPTION
		"The number of inaccurate LDPDU reception about the port concerned"
	::= {axslldpStatsEntry 4 }

axslldpStatsFramesInTotal OBJECT-TYPE
	SYNTAX  Counter
	MAX-ACCESS  read-only
	STATUS  current
	DESCRIPTION
		"The total number of LDPDU reception about the port concerned"
	::= {axslldpStatsEntry 5 }

axslldpStatsFramesOutTotal OBJECT-TYPE
	SYNTAX  Counter
	MAX-ACCESS  read-only
	STATUS  current
	DESCRIPTION
		"The total number of LDPDU transmission about the port concerned"
	::= {axslldpStatsEntry 6 }

axslldpStatsTLVsInErrors OBJECT-TYPE
	SYNTAX  Counter
	MAX-ACCESS  read-only
	STATUS  current
	DESCRIPTION
		"The number of inaccurate TLV reception about the port concerned"
	::= {axslldpStatsEntry 7 }

axslldpStatsTLVsDiscardedTotal OBJECT-TYPE
	SYNTAX  Counter
	MAX-ACCESS  read-only
	STATUS  current
	DESCRIPTION
		"The total abandonment TLV number about the port concerned"
	::= {axslldpStatsEntry 8 }

-- axslldpLocalSystemData group

axslldpLocChassisType OBJECT-TYPE
	SYNTAX  INTEGER {
                                entPhysicalAlias(1),
                                ifAlias(2),
                                portEntPhysicalAlias(3),
                                backplaneEntPhysicalAlias(4),
                                macAddress(5),
                                networkAddress(6)
                        }
	MAX-ACCESS  read-only
	STATUS  current
	DESCRIPTION
		"The chassis type about this equipment"
	::= {axslldpLocalSystemData 1 }

axslldpLocChassisId OBJECT-TYPE
	SYNTAX  OCTET STRING 
	MAX-ACCESS  read-only
	STATUS  current
	DESCRIPTION
		"The chassis ID about this equipment"
	::= {axslldpLocalSystemData 2 }

axslldpLocSysName OBJECT-TYPE
	SYNTAX  OCTET STRING
	MAX-ACCESS  read-only
	STATUS  current
	DESCRIPTION
		"The chassis ID about this equipment"
	::= {axslldpLocalSystemData 3 }

axslldpLocSysDesc OBJECT-TYPE
	SYNTAX  DisplayString
	MAX-ACCESS  read-only
	STATUS  current
	DESCRIPTION
		"System information about this equipment"
	::= {axslldpLocalSystemData 4 }

axslldpLocPortTable OBJECT-TYPE
	SYNTAX  SEQUENCE OF AxslldpLocPortEntry
	MAX-ACCESS  not-accessible
	STATUS  current
	DESCRIPTION
		"The table about the port of this equipment"
	::= { axslldpLocalSystemData 7 }

axslldpLocPortEntry OBJECT-TYPE
	SYNTAX  AxslldpLocPortEntry
	MAX-ACCESS  not-accessible
	STATUS  current
	DESCRIPTION
		"The entry about the port of this equipment"
    INDEX { axslldpLocPortNum }
	::= { axslldpLocPortTable 1 }

	AxslldpLocPortEntry ::=
		SEQUENCE {
		    axslldpLocPortNum		INTEGER,
		    axslldpLocPortType		INTEGER,
		    axslldpLocPortId		OCTET STRING,
		    axslldpLocPortDesc		OCTET STRING
		}

axslldpLocPortNum OBJECT-TYPE
	SYNTAX  INTEGER
	MAX-ACCESS  not-accessible
	STATUS  current
	DESCRIPTION
		"Port discernment index"
	::= {axslldpLocPortEntry 1 }

axslldpLocPortType OBJECT-TYPE
	SYNTAX  INTEGER {
                             ifAlias(1),
                             portEntPhysicalAlias(2),
                             backplaneEntPhysicalAlias(3),
                             macAddress(4),
                             networkAddress(5),
                             local(6)
                        }
	MAX-ACCESS  read-only
	STATUS  current
	DESCRIPTION
		"The port type about the port concerned of this equipment"
	::= {axslldpLocPortEntry 2 }

axslldpLocPortId OBJECT-TYPE
	SYNTAX  OCTET STRING
	MAX-ACCESS  read-only
	STATUS  current
	DESCRIPTION
		"The port ID about the port concerned of this equipment"
	::= {axslldpLocPortEntry 3 }

axslldpLocPortDesc OBJECT-TYPE
	SYNTAX  OCTET STRING
	MAX-ACCESS  read-only
	STATUS  current
	DESCRIPTION
		"Port information about the port concerned of this equipment"
	::= {axslldpLocPortEntry 4 }

-- axslldpRemoteSystemData group

axslldpRemTable OBJECT-TYPE
	SYNTAX  SEQUENCE OF AxslldpRemEntry
	MAX-ACCESS  not-accessible
	STATUS  current
	DESCRIPTION
		"The table about contiguity equipment"
	::= { axslldpRemoteSystemData 1 }

axslldpRemEntry OBJECT-TYPE
	SYNTAX  AxslldpRemEntry
	MAX-ACCESS  not-accessible
	STATUS  current
	DESCRIPTION
		"The entry about contiguity equipment"
    INDEX { axslldpRemLocalPortNum,axslldpRemIndex }
	::= { axslldpRemTable 1 }

	AxslldpRemEntry ::=
		SEQUENCE {
		    axslldpRemLocalPortNum		INTEGER,
		    axslldpRemIndex			INTEGER,
		    axslldpRemRemoteChassisType		INTEGER,
		    axslldpRemRemoteChassis		OCTET STRING,
		    axslldpRemRemotePortType		INTEGER,
		    axslldpRemRemotePort			OCTET STRING,
		    axslldpRemPortDesc			OCTET STRING,
		    axslldpRemSysName			OCTET STRING,
		    axslldpRemSysDesc			OCTET STRING
		}

axslldpRemLocalPortNum OBJECT-TYPE
	SYNTAX  INTEGER
	MAX-ACCESS  read-only
	STATUS  current
	DESCRIPTION
		"The discernment index of the port of this equipment which received the information about contiguity equipment"
	::= {axslldpRemEntry 2 }

axslldpRemIndex OBJECT-TYPE
	SYNTAX  INTEGER
	MAX-ACCESS  read-only
	STATUS  current
	DESCRIPTION
		"The index about contiguity equipment"
	::= {axslldpRemEntry 3 }

axslldpRemRemoteChassisType OBJECT-TYPE
	SYNTAX  INTEGER {
                                      entPhysicalAlias(1),
                                      ifAlias(2),
                                      portEntPhysicalAlias(3),
                                      backplaneEntPhysicalAlias(4),
                                      macAddress(5),
                                      networkAddress(6)
                        }
	MAX-ACCESS  read-only
	STATUS  current
	DESCRIPTION
		"The chassis type about contiguity equipment"
	::= {axslldpRemEntry 4 }

axslldpRemRemoteChassis OBJECT-TYPE
	SYNTAX  OCTET STRING
	MAX-ACCESS  read-only
	STATUS  current
	DESCRIPTION
		"The chassis ID about contiguity equipment"
	::= {axslldpRemEntry 5 }

axslldpRemRemotePortType OBJECT-TYPE
	SYNTAX  INTEGER {
                                   ifAlias(1),
                                   portEntPhysicalAlias(2),
                                   backplaneEntPhysicalAlias(3),
                                   macAddress(4),
                                   networkAddress(5),
                                   local(6)
                        }
	MAX-ACCESS  read-only
	STATUS  current
	DESCRIPTION
		"The port type about the port concerned of contiguity equipment"
	::= {axslldpRemEntry 6 }

axslldpRemRemotePort OBJECT-TYPE
	SYNTAX  OCTET STRING
	MAX-ACCESS  read-only
	STATUS  current
	DESCRIPTION
		"The port ID about the port concerned of contiguity equipment"
	::= {axslldpRemEntry 7 }

axslldpRemPortDesc OBJECT-TYPE
	SYNTAX  OCTET STRING
	MAX-ACCESS  read-only
	STATUS  current
	DESCRIPTION
		"Information about the port concerned of contiguity equipment"
	::= {axslldpRemEntry 8 }

axslldpRemSysName OBJECT-TYPE
	SYNTAX  OCTET STRING
	MAX-ACCESS  read-only
	STATUS  current
	DESCRIPTION
		"The system name about contiguity equipment"
	::= {axslldpRemEntry 9 }

axslldpRemSysDesc OBJECT-TYPE
	SYNTAX  OCTET STRING
	MAX-ACCESS  read-only
	STATUS  current
	DESCRIPTION
		"System information about contiguity equipment"
	::= {axslldpRemEntry 10 }

axslldpRemOriginInfoTable OBJECT-TYPE
	SYNTAX  SEQUENCE OF AxslldpRemOriginInfoEntry
	MAX-ACCESS  not-accessible
	STATUS  current
	DESCRIPTION
		"The table about original with AlaxalA networks TLV of contiguity equipment"
	::= { axslldpRemoteOriginInfoData 1 }

axslldpRemOriginInfoEntry OBJECT-TYPE
	SYNTAX  AxslldpRemOriginInfoEntry
	MAX-ACCESS  not-accessible
	STATUS  current
	DESCRIPTION
		"The entry about original with AlaxalA networks TLV of contiguity equipment"
    INDEX { axslldpRemOriginInfoPortNum,axslldpRemOriginInfoIndex }
	::= { axslldpRemOriginInfoTable 1 }

	AxslldpRemOriginInfoEntry ::=
		SEQUENCE {
		    axslldpRemOriginInfoPortNum		INTEGER,
		    axslldpRemOriginInfoIndex		INTEGER,
		    axslldpRemOriginInfoLowerVlanList	OCTET STRING,
		    axslldpRemOriginInfoHigherVlanList	OCTET STRING,
		    axslldpRemOriginInfoIPv4Address	OCTET STRING,
		    axslldpRemOriginInfoIPv4PortType	INTEGER,
		    axslldpRemOriginInfoIPv4VlanId	INTEGER,
		    axslldpRemOriginInfoIPv6Address	OCTET STRING,
		    axslldpRemOriginInfoIPv6PortType	INTEGER,
		    axslldpRemOriginInfoIPv6VlanId	INTEGER
		}

axslldpRemOriginInfoPortNum OBJECT-TYPE
	SYNTAX  INTEGER
	MAX-ACCESS  not-accessible
	STATUS  current
	DESCRIPTION
		"The discernment index of the port of this equipment which received the information about contiguity equipment."
	::= {axslldpRemOriginInfoEntry 1 }

axslldpRemOriginInfoIndex OBJECT-TYPE
	SYNTAX  INTEGER
	MAX-ACCESS  not-accessible
	STATUS  current
	DESCRIPTION
		"The index about contiguity equipment"
	::= {axslldpRemOriginInfoEntry 2 }

axslldpRemOriginInfoLowerVlanList OBJECT-TYPE
	SYNTAX  OCTET STRING
	MAX-ACCESS  read-only
	STATUS  current
	DESCRIPTION
		"What expressed effective VLAN ID by the bit map by VLAN 1-2047 in the port concerned of contiguity equipment"
	::= {axslldpRemOriginInfoEntry 3 }

axslldpRemOriginInfoHigherVlanList OBJECT-TYPE
	SYNTAX  OCTET STRING
	MAX-ACCESS  read-only
	STATUS  current
	DESCRIPTION
		"What expressed effective VLAN ID by the bit map by VLAN 2048-4095 in the port concerned of contiguity equipment"
	::= {axslldpRemOriginInfoEntry 4 }

axslldpRemOriginInfoIPv4Address OBJECT-TYPE
	SYNTAX  OCTET STRING
	MAX-ACCESS  read-only
	STATUS  current
	DESCRIPTION
		"IPv4 address given to the port concerned of contiguity equipment"
	::= {axslldpRemOriginInfoEntry 5 }

axslldpRemOriginInfoIPv4PortType OBJECT-TYPE
	SYNTAX  INTEGER
	MAX-ACCESS  read-only
	STATUS  current
	DESCRIPTION
		"Port classification of the port of contiguity equipment concerned"
	::= {axslldpRemOriginInfoEntry 6 }

axslldpRemOriginInfoIPv4VlanId OBJECT-TYPE
	SYNTAX  INTEGER
	MAX-ACCESS  read-only
	STATUS  current
	DESCRIPTION
		"The smallest thing among VLAN ID to which IPv4 address is given"
	::= {axslldpRemOriginInfoEntry 7 }

axslldpRemOriginInfoIPv6Address OBJECT-TYPE
	SYNTAX  OCTET STRING
	MAX-ACCESS  read-only
	STATUS  current
	DESCRIPTION
		"The IPv6 address given to the port concerned of contiguity equipment"
	::= {axslldpRemOriginInfoEntry 8 }

axslldpRemOriginInfoIPv6PortType OBJECT-TYPE
	SYNTAX  INTEGER
	MAX-ACCESS  read-only
	STATUS  current
	DESCRIPTION
		"Port classification of the port of contiguity equipment concerned"
	::= {axslldpRemOriginInfoEntry 9 }

axslldpRemOriginInfoIPv6VlanId OBJECT-TYPE
	SYNTAX  INTEGER
	MAX-ACCESS  read-only
	STATUS  current
	DESCRIPTION
		"The smallest thing among VLAN ID to which the IPv6 address is given"
	::= {axslldpRemOriginInfoEntry 10 }

-- ax1230sSwitch group

ax1230sModelType OBJECT-TYPE
	SYNTAX  INTEGER {
                other(1),
		model-AX1230S-24T2C(300),
		model-AX1230S-48T2C(301),
		model-AX1230S-24P2C(302)
	      }
	MAX-ACCESS  read-only
	STATUS  current
	DESCRIPTION
		"Model type of this system."
	::= { ax1230sSwitch 1 }

--ax1230sSoftware OBJECT-TYPE
--	SYNTAX  INTEGER
--	MAX-ACCESS  not-accessible
--	STATUS  current
--	DESCRIPTION
--		"Software information of this system."
--	::= { ax1230sSwitch 2 }

ax1230sSoftwareName OBJECT-TYPE
	SYNTAX  DisplayString (SIZE (0..16))
	MAX-ACCESS  read-only
	STATUS  current
	DESCRIPTION
		"Software name of this system."
	::= { ax1230sSoftware 1 }

ax1230sSoftwareAbbreviation OBJECT-TYPE
	SYNTAX  DisplayString (SIZE (0..16))
	MAX-ACCESS  read-only
	STATUS  current
	DESCRIPTION
		"System software abbreviation."
	::= { ax1230sSoftware 2 }

ax1230sSoftwareVersion OBJECT-TYPE
	SYNTAX  DisplayString (SIZE (0..16))
	MAX-ACCESS  read-only
	STATUS  current
	DESCRIPTION
		"System software version."
	::= { ax1230sSoftware 3 }

--ax1230sSystemMsg OBJECT-TYPE
--	SYNTAX  INTEGER
--	MAX-ACCESS  not-accessible
--	STATUS  current
--	DESCRIPTION
--		"System messege group."
--	::= { ax1230sSwitch 3 }

ax1230sSystemMsgText OBJECT-TYPE
	SYNTAX  DisplayString (SIZE (0..256))
	MAX-ACCESS  read-only
	STATUS  current
	DESCRIPTION
		"The text of the system log message.For information about this code,
		see:  Operator's Manual. "
	::= { ax1230sSystemMsg 1 }

ax1230sSystemMsgType OBJECT-TYPE
	SYNTAX  OCTET STRING (SIZE (1))
	MAX-ACCESS  read-only
	STATUS  current
	DESCRIPTION
		"The event type. For information about this code, see:  Operator's Manual."
	::= { ax1230sSystemMsg 2 }

ax1230sSystemMsgTimeStamp OBJECT-TYPE
	SYNTAX  DisplayString (SIZE (0..14))
	MAX-ACCESS  read-only
	STATUS  current
	DESCRIPTION
		"The time that event occured. And that is expressed as type of
		MM/DD hh:mm:ss
			MM:month(01-12)
			DD:day(01-31)
			hh:hour(00-23)
			mm:minute(00-59)
			ss:second(00-59)
		Insert space between DD and hh."
	::= { ax1230sSystemMsg 3 }

ax1230sSystemMsgLevel OBJECT-TYPE
	SYNTAX  OCTET STRING (SIZE (1))
	MAX-ACCESS  read-only
	STATUS  current
	DESCRIPTION
		"The newest system message log level.For information about this code,
		see:  Operator's Manual. "
	::= { ax1230sSystemMsg 4 }

ax1230sSystemMsgEventPoint OBJECT-TYPE
	SYNTAX  DisplayString (SIZE (0..8))
	MAX-ACCESS  read-only
	STATUS  current
	DESCRIPTION
		"The code of part that system message error occured. For information
		about this code,see:  Operator's Manual. "
	::= { ax1230sSystemMsg 5 }

ax1230sSystemMsgEventInterfaceID OBJECT-TYPE
	SYNTAX  DisplayString (SIZE (0..40))
	MAX-ACCESS  read-only
	STATUS  current
	DESCRIPTION
		"Interface identification of system messages. For information
		about this code,see:  Operator's Manual."
	::= { ax1230sSystemMsg 6 }

ax1230sSystemMsgEventCode OBJECT-TYPE
	SYNTAX  OCTET STRING (SIZE (4))
	MAX-ACCESS  read-only
	STATUS  current
	DESCRIPTION
		"Event kind code of system messages. For information about this code,
		see:  Operator's Manual. "
	::= { ax1230sSystemMsg 7 }

ax1230sSystemMsgAdditionalCode OBJECT-TYPE
	SYNTAX  OCTET STRING (SIZE (6))
	MAX-ACCESS  read-only
	STATUS  current
	DESCRIPTION
		"Additional code of system messages. For information about this code,
		see:  Operator's Manual. "
	::= { ax1230sSystemMsg 8 }

--ax1230sSnmpAgent OBJECT-TYPE
--	SYNTAX  INTEGER
--	MAX-ACCESS  not-accessible
--	STATUS  current
--	DESCRIPTION
--		"Related information of SNMP agent."
--	::= { ax1230sSwitch 4 }

ax1230sSnmpSendReceiveSize OBJECT-TYPE
	SYNTAX  INTEGER
	MAX-ACCESS  read-only
	STATUS  current
	DESCRIPTION
		"SNMP packet data size in Manager-to-Agent communication. The value is
		displayed in bytes."
	::= { ax1230sSnmpAgent 1 }

ax1230sSnmpReceiveDelay OBJECT-TYPE
	SYNTAX  INTEGER
	MAX-ACCESS  read-only
	STATUS  current
	DESCRIPTION
		"A recommendable interval to receive packets from Manager.The value is
		displayed in milliseconds."
	::= { ax1230sSnmpAgent 2 }

ax1230sSnmpContinuousSend OBJECT-TYPE
	SYNTAX  INTEGER
	MAX-ACCESS  read-only
	STATUS  current
	DESCRIPTION
		"Number of times that is recommendable continuous transmission
		packets."
	::= { ax1230sSnmpAgent 3 }

ax1230sSnmpObjectMaxNumber OBJECT-TYPE
	SYNTAX  INTEGER
	MAX-ACCESS  read-only
	STATUS  current
	DESCRIPTION
		"Max number of objects that contain SNMP packet."
	::= { ax1230sSnmpAgent 4 }

--ax1230sSerialNumber OBJECT-TYPE
--        SYNTAX  DisplayString (SIZE (0..30))
--	MAX-ACCESS  read-only
--        STATUS  current
--        DESCRIPTION
--                "Management information (SerialNumber) of RMP2-CARD."
--        ::= { ax1230sSwitch 5 }

ax1230sLicenseNumber OBJECT-TYPE
        SYNTAX  INTEGER
	MAX-ACCESS  read-only
        STATUS  current
        DESCRIPTION
                "The number of the configured license serial numbers."
        ::= { ax1230sLicense 1 }

ax1230sLicenseTable OBJECT-TYPE
	SYNTAX  SEQUENCE OF Ax1230sLicenseTableEntry
	MAX-ACCESS  not-accessible
	STATUS  current
	DESCRIPTION
		"The table containing the license information."
	::= { ax1230sLicense 2 }

ax1230sLicenseEntry OBJECT-TYPE
	SYNTAX  Ax1230sLicenseTableEntry
	MAX-ACCESS  not-accessible
	STATUS  current
	DESCRIPTION
		"The entry of license information."
	INDEX   { ax1230sLicenseIndex }
	::= { ax1230sLicenseTable 1 }

	Ax1230sLicenseTableEntry ::=
		SEQUENCE {
		  ax1230sLicenseIndex
			INTEGER,
		  ax1230sLicenseSerialNumber
			DisplayString,
		  ax1230sLicenseOptionNumber
			INTEGER
                }

ax1230sLicenseIndex OBJECT-TYPE
	SYNTAX  INTEGER
	MAX-ACCESS  not-accessible
	STATUS  current
	DESCRIPTION
		"The unique index number given for each serial number. The number is from 1 to ax1230sLicenseNumber."
	::= { ax1230sLicenseEntry 1 }

ax1230sLicenseSerialNumber OBJECT-TYPE
	SYNTAX  DisplayString 
	MAX-ACCESS  read-only
	STATUS  current
	DESCRIPTION
		"The serial number."
	::= { ax1230sLicenseEntry 2 }

ax1230sLicenseOptionNumber OBJECT-TYPE
	SYNTAX  INTEGER 
	MAX-ACCESS  read-only
	STATUS  current
	DESCRIPTION
		"The number of option licenses associated with the serial number."
	::= { ax1230sLicenseEntry 3 }

ax1230sLicenseOptionTable OBJECT-TYPE
	SYNTAX  SEQUENCE OF Ax1230sLicenseOptionTableEntry
	MAX-ACCESS  not-accessible
	STATUS  current
	DESCRIPTION
		"The table containing option licenses information associated with the serial number."
	::= { ax1230sLicense 3 }

ax1230sLicenseOptionEntry OBJECT-TYPE
	SYNTAX  Ax1230sLicenseOptionTableEntry
	MAX-ACCESS  not-accessible
	STATUS  current
	DESCRIPTION
		"The entry of the option license information associated with the serial number."
	INDEX   { ax1230sLicenseOptionIndex,ax1230sLicenseOptionNumberIndex }
	::= { ax1230sLicenseOptionTable 1 }

	Ax1230sLicenseOptionTableEntry ::=
		SEQUENCE {
		  ax1230sLicenseOptionIndex
			INTEGER,
		  ax1230sLicenseOptionNumberIndex
			INTEGER,
		  ax1230sLicenseOptionSoftwareName
			DisplayString,
		  ax1230sLicenseOptionSoftwareAbbreviation
			DisplayString
                }

ax1230sLicenseOptionIndex OBJECT-TYPE
	SYNTAX  INTEGER
	MAX-ACCESS  not-accessible
	STATUS  current
	DESCRIPTION
		"The unique index number given for each serial number. The same number as ax1230sLicenseIndex."
	::= { ax1230sLicenseOptionEntry 1 }

ax1230sLicenseOptionNumberIndex OBJECT-TYPE
	SYNTAX  INTEGER
	MAX-ACCESS  not-accessible
	STATUS  current
	DESCRIPTION
		"The unique index number of option licenses information which is given for each serial number. The number is from 1 to ax1230sLicenseNumber."
	::= { ax1230sLicenseOptionEntry 2 }

ax1230sLicenseOptionSoftwareName OBJECT-TYPE
	SYNTAX  DisplayString 
	MAX-ACCESS  read-only
	STATUS  current
	DESCRIPTION
		"The software model name of the option license information associated with the serial number."
	::= { ax1230sLicenseOptionEntry 3 }

ax1230sLicenseOptionSoftwareAbbreviation OBJECT-TYPE
	SYNTAX  DisplayString 
	MAX-ACCESS  read-only
	STATUS  current
	DESCRIPTION
		"The software abbreviated name of the option license information associated with the serial number. "
	::= { ax1230sLicenseOptionEntry 4 }

-- ax1230sDevice group

ax1230sChassisMaxNumber OBJECT-TYPE
	SYNTAX  INTEGER
	MAX-ACCESS  read-only
	STATUS  current
	DESCRIPTION
		"Max number of cluster chassis that can connect to this router."
	::= { ax1230sChassis 1 }


ax1230sChassisTable OBJECT-TYPE
	SYNTAX  SEQUENCE OF Ax1230sChassisTableEntry
	MAX-ACCESS  not-accessible
	STATUS  current
	DESCRIPTION
		"A table containing chassis information."
	::= { ax1230sChassis 2 }

ax1230sChassisEntry OBJECT-TYPE
	SYNTAX  Ax1230sChassisTableEntry
	MAX-ACCESS  not-accessible
	STATUS  current
	DESCRIPTION
		"An entry containing specific chassis."
	INDEX   { ax1230sChassisIndex }
	::= { ax1230sChassisTable 1 }

	Ax1230sChassisTableEntry ::=
		SEQUENCE {
		  ax1230sChassisIndex
			INTEGER,
		  ax1230sChassisType
			INTEGER,
		  ax1230sChassisStatus
			INTEGER,
		  ax1230sStsLedStatus
			INTEGER,
                  ax1230sCpuName
                        DisplayString,
                  ax1230sCpuClock
                        INTEGER,
                  ax1230sMemoryTotalSize
                        INTEGER,
                  ax1230sMemoryUsedSize
                        INTEGER,
                  ax1230sMemoryFreeSize
                        INTEGER,
                  ax1230sRomVersion
                        DisplayString,
                  ax1230sCpuLoad1m
                        INTEGER,
                  ax1230sFlashTotalSize
                        INTEGER,
                  ax1230sFlashUsedSize
                        INTEGER,
                  ax1230sFlashFreeSize
                        INTEGER,
                  ax1230sSdCardStatus
                        INTEGER,
                  ax1230sSdCardTotalSize
                        INTEGER,
                  ax1230sSdCardUsedSize
                        INTEGER,
                  ax1230sSdCardFreeSize
                        INTEGER,
                  ax1230sPhysLineNumber
                        INTEGER,
                  ax1230sTemperatureStatusNumber
                        INTEGER,
		  ax1230sPowerUnitNumber
			INTEGER,
                  ax1230sRedundantPsNumber
                        INTEGER,
		  ax1230sFanNumber
			INTEGER,
                  ax1230sTotalAccumRunTime
                        INTEGER,
                  ax1230sCriticalAccumRunTime
                        INTEGER
		}

ax1230sChassisIndex OBJECT-TYPE
	SYNTAX  INTEGER
	MAX-ACCESS  not-accessible
	STATUS  current
	DESCRIPTION
		"A number to specify ax1230sChassisEntry."
	::= { ax1230sChassisEntry 1 }

ax1230sChassisType OBJECT-TYPE
	SYNTAX  INTEGER {
		other(1),
		model-AX1230S-24T2C(300),
		model-AX1230S-48T2C(301),
		model-AX1230S-24P2C(302)
	      }
	MAX-ACCESS  read-only
	STATUS  current
	DESCRIPTION
		"Chassis type of this system."
	::= { ax1230sChassisEntry 2 }

ax1230sChassisStatus OBJECT-TYPE
	SYNTAX  INTEGER {
		up(2)
	      }
	MAX-ACCESS  read-only
	STATUS  current
	DESCRIPTION
		"Current status of this chassis."
	::= { ax1230sChassisEntry 3 }

ax1230sStsLedStatus OBJECT-TYPE
	SYNTAX  INTEGER {
	            red-light-on(0),
	            red-light-off(1),
                orange-light-on(2),
                orange-light-off(3),
                green-light-off(4),
                green-light-on(5),
                light-off(6)
              }
	MAX-ACCESS  read-only
	STATUS  current
	DESCRIPTION
		"The state of STS LED of the device is shown."
	::= { ax1230sChassisEntry 4 }
        
ax1230sCpuName OBJECT-TYPE
	SYNTAX  DisplayString
	MAX-ACCESS  read-only
	STATUS  current
	DESCRIPTION
		"CPU name is shown by the character string of 16 characters or less." 
	::= { ax1230sChassisEntry 5 }

ax1230sCpuClock OBJECT-TYPE
	SYNTAX  INTEGER
	MAX-ACCESS  read-only
	STATUS  current
	DESCRIPTION
		"CPU clock is shown by the numerical value."
	::= { ax1230sChassisEntry 6 }

ax1230sMemoryTotalSize OBJECT-TYPE
	SYNTAX  INTEGER
	MAX-ACCESS  read-only
	STATUS  current
	DESCRIPTION
		"The installing memory size is shown by the numerical value. "
	::= { ax1230sChassisEntry 7 }

ax1230sMemoryUsedSize OBJECT-TYPE
	SYNTAX  INTEGER
	MAX-ACCESS  read-only
	STATUS  current
	DESCRIPTION
		"The use memory size is shown by the numerical value."
	::= { ax1230sChassisEntry 8 }

ax1230sMemoryFreeSize OBJECT-TYPE
	SYNTAX  INTEGER
	MAX-ACCESS  read-only
	STATUS  current
	DESCRIPTION
		"The unused memory size is shown by the numerical value."
	::= { ax1230sChassisEntry 9 }

ax1230sRomVersion OBJECT-TYPE
	SYNTAX  DisplayString
	MAX-ACCESS  read-only
	STATUS  current
	DESCRIPTION
		"The version of ROM equipped with BCU is shown by the character string."
	::= { ax1230sChassisEntry 10 }

ax1230sCpuLoad1m OBJECT-TYPE
	SYNTAX  INTEGER
	MAX-ACCESS  read-only
	STATUS  current
	DESCRIPTION
		"CPU utilization of one minute is shown by the numerical value."
	::= { ax1230sChassisEntry 11 }

ax1230sFlashTotalSize OBJECT-TYPE
	SYNTAX  INTEGER
	MAX-ACCESS  read-only
	STATUS  current
	DESCRIPTION
		"The total of filesystem use capacity and unused capacity in a built-in memory 
                is shown."
	::= { ax1230sChassisEntry 12 }

ax1230sFlashUsedSize OBJECT-TYPE
	SYNTAX  INTEGER
	MAX-ACCESS  read-only
	STATUS  current
	DESCRIPTION
		"The use capacity of the filesystem in a built-in memory is shown."
	::= { ax1230sChassisEntry 13 }

ax1230sFlashFreeSize OBJECT-TYPE
	SYNTAX  INTEGER
	MAX-ACCESS  read-only
	STATUS  current
	DESCRIPTION
		"The unused capacity of the filesystem in a built-in memory is shown. "
	::= { ax1230sChassisEntry 14 }

ax1230sSdCardStatus OBJECT-TYPE
	SYNTAX  INTEGER {
                  connected(2),
                  disconnected(32)
                }
	MAX-ACCESS  read-only
	STATUS  current
	DESCRIPTION
		"The SD card connection is shown."
	::= { ax1230sChassisEntry 15 }

ax1230sSdCardTotalSize OBJECT-TYPE
	SYNTAX  INTEGER
	MAX-ACCESS  read-only
	STATUS  current
	DESCRIPTION
		"Total capacity of the SD card is shown by the numerical value. It responds by -1 
                at the MC card unconnection."
	::= { ax1230sChassisEntry 16 }

ax1230sSdCardUsedSize OBJECT-TYPE
	SYNTAX  INTEGER
	MAX-ACCESS  read-only
	STATUS  current
	DESCRIPTION
		"The use capacity of the SD card is shown by the numerical value. It responds by -1 
                at the SD card unconnection. "
	::= { ax1230sChassisEntry 17 }

ax1230sSdCardFreeSize OBJECT-TYPE
	SYNTAX  INTEGER
	MAX-ACCESS  read-only
	STATUS  current
	DESCRIPTION
		"The remainder capacity of the SD card is shown by the numerical value. It
                responds by -1 at the SD card unconnection."
	::= { ax1230sChassisEntry 18 }

ax1230sPhysLineNumber OBJECT-TYPE
	SYNTAX  INTEGER
	MAX-ACCESS  read-only
	STATUS  current
	DESCRIPTION
		"Number of physical lines."
	::= { ax1230sChassisEntry 19 }

ax1230sTemperatureStatusNumber OBJECT-TYPE
	SYNTAX  INTEGER
	MAX-ACCESS  read-only
	STATUS  current
	DESCRIPTION
		"The maximum number of ax1230sTemperatureStatus in this chassis."
	::= { ax1230sChassisEntry 20 }

ax1230sPowerUnitNumber OBJECT-TYPE
	SYNTAX  INTEGER
	MAX-ACCESS  read-only
	STATUS  current
	DESCRIPTION
		"Number of maximum power switches that this router can connect its."
	::= { ax1230sChassisEntry 21 }

ax1230sRedundantPsNumber OBJECT-TYPE
        SYNTAX  INTEGER
        MAX-ACCESS  read-only
        STATUS  current
        DESCRIPTION
                "Number of external power switches that this router can connect its."
        ::= { ax1230sChassisEntry 22 }

ax1230sFanNumber OBJECT-TYPE
	SYNTAX  INTEGER
	MAX-ACCESS  read-only
	STATUS  current
	DESCRIPTION
		"The maximum number of fans that can connect to this chassis."
	::= { ax1230sChassisEntry 23 }

ax1230sTotalAccumRunTime OBJECT-TYPE
        SYNTAX  INTEGER
        MAX-ACCESS  read-only
        STATUS  current
        DESCRIPTION
                "Total operation time after operation of device begins."
        ::= { ax1230sChassisEntry 24 }

ax1230sCriticalAccumRunTime OBJECT-TYPE
        SYNTAX  INTEGER
        MAX-ACCESS  read-only
        STATUS  current
        DESCRIPTION
                "Operating time under environment of 40 degrees C or more."
        ::= { ax1230sChassisEntry 25 }
        
ax1230sTemperatureStatusTable OBJECT-TYPE
	SYNTAX  SEQUENCE OF Ax1230sTemperatureStatusEntry
	MAX-ACCESS  not-accessible
	STATUS  current
	DESCRIPTION
		"The table of ambient temperature status maintained by the
		environmental monitor."
	::= { ax1230sChassis 3 }

ax1230sTemperatureStatusEntry OBJECT-TYPE
	SYNTAX  Ax1230sTemperatureStatusEntry
	MAX-ACCESS  not-accessible
	STATUS  current
	DESCRIPTION
		"An entry in the ambient temperature status table, representing
		the status of the associated testpoint maintained by the
		environmental monitor."
	INDEX  { ax1230sChassisIndex, ax1230sTemperatureStatusIndex }
	::= { ax1230sTemperatureStatusTable 1 }

	Ax1230sTemperatureStatusEntry ::=
		SEQUENCE {
		  ax1230sTemperatureStatusIndex
			INTEGER,
		  ax1230sTemperatureStatusDescr
			DisplayString,
		  ax1230sTemperatureStatusValue
			Integer32,
		  ax1230sTemperatureThreshold
			Integer32,
		  ax1230sTemperatureState
			INTEGER
		}

ax1230sTemperatureStatusIndex OBJECT-TYPE
	SYNTAX  INTEGER
	MAX-ACCESS  not-accessible
	STATUS  current
	DESCRIPTION
		"Unique index for the testpoint being instrumented.
		This index is for SNMP purposes only, and has no
		intrinsic meaning."
	::= { ax1230sTemperatureStatusEntry 1 }

ax1230sTemperatureStatusDescr OBJECT-TYPE
	SYNTAX  DisplayString(SIZE(0..32))
	MAX-ACCESS  read-only
	STATUS  current
	DESCRIPTION
		"Textual description of the testpoint being instrumented.
		This description is a short textual label, suitable as a
		human-sensible identification for the rest of the
		information in the entry."
	::= { ax1230sTemperatureStatusEntry 2 }

ax1230sTemperatureStatusValue OBJECT-TYPE
	SYNTAX  Integer32
	MAX-ACCESS  read-only
	STATUS  current
	DESCRIPTION
		"The current measurement of the testpoint being instrumented."
	::= { ax1230sTemperatureStatusEntry 3 }

ax1230sTemperatureThreshold OBJECT-TYPE
	SYNTAX  Integer32
	MAX-ACCESS  read-only
	STATUS  current
	DESCRIPTION
		"The highest value that the associated instance of the
		object ax1230sTemperatureStatusValue may obtain
		before an emergency shutdown of the managed device is
		initiated."
	::= { ax1230sTemperatureStatusEntry 4 }

ax1230sTemperatureState OBJECT-TYPE
	SYNTAX  INTEGER {
		normal(1),
		caution(2),
		warning(3),
		fatal(4)
		}
	MAX-ACCESS  read-only
	STATUS  current
	DESCRIPTION
		"The current state of the testpoint being instrumented."
        ::= { ax1230sTemperatureStatusEntry 5 }

ax1230sPowerUnitTable OBJECT-TYPE
	SYNTAX  SEQUENCE OF Ax1230sPowerUnitTableEntry
	MAX-ACCESS  not-accessible
	STATUS  current
	DESCRIPTION
		"A table containing power unit information."
	::= { ax1230sChassis 4 }

ax1230sPowerUnitEntry OBJECT-TYPE
	SYNTAX  Ax1230sPowerUnitTableEntry
	MAX-ACCESS  not-accessible
	STATUS  current
	DESCRIPTION
		"An entry containing power unit information."
	INDEX   { ax1230sChassisIndex,ax1230sPowerUnitIndex }
	::= { ax1230sPowerUnitTable 1 }

	Ax1230sPowerUnitTableEntry ::=
		SEQUENCE {
		  ax1230sPowerUnitIndex
			INTEGER,
		  ax1230sPowerConnectStatus
			INTEGER,
		  ax1230sPowerSupplyStatus
			INTEGER
		}

ax1230sPowerUnitIndex OBJECT-TYPE
	SYNTAX  INTEGER
	MAX-ACCESS  not-accessible
	STATUS  current
	DESCRIPTION
		"A number to position of the power units.The value from 1
		to ax1230sPowerUnitNumber."
	::= { ax1230sPowerUnitEntry 1 }
        
ax1230sPowerConnectStatus OBJECT-TYPE
	SYNTAX  INTEGER {
		connected(2),
		disconnected(32)
	      }
	MAX-ACCESS  read-only
	STATUS  current
	DESCRIPTION
		"The current connection status of the power unit."
	::= { ax1230sPowerUnitEntry 2 }

ax1230sPowerSupplyStatus OBJECT-TYPE
	SYNTAX  INTEGER {
		ok(2),
		fault(4),
                disconnected(-1)
	      }
	MAX-ACCESS  read-only
	STATUS  current
	DESCRIPTION
		"Status of power supply."
	::= { ax1230sPowerUnitEntry 3 }


ax1230sFanTable OBJECT-TYPE
	SYNTAX  SEQUENCE OF Ax1230sFanTableEntry
	MAX-ACCESS  not-accessible
	STATUS  current
	DESCRIPTION
		"A table containing fan information."
	::= { ax1230sChassis 5 }

ax1230sFanEntry OBJECT-TYPE
	SYNTAX  Ax1230sFanTableEntry
	MAX-ACCESS  not-accessible
	STATUS  current
	DESCRIPTION
		"This entry containing information for a fan."
	INDEX   { ax1230sChassisIndex,ax1230sFanIndex }
	::= { ax1230sFanTable 1 }

	Ax1230sFanTableEntry ::=
		SEQUENCE {
		  ax1230sFanIndex
			INTEGER,
		  ax1230sFanStatus
			INTEGER
		}

ax1230sFanIndex OBJECT-TYPE
	SYNTAX  INTEGER
	MAX-ACCESS  not-accessible
	STATUS  current
	DESCRIPTION
		"Index to indicate position of fans."
	::= { ax1230sFanEntry 1 }

ax1230sFanStatus OBJECT-TYPE
	SYNTAX  INTEGER {
		ok(2),
                high-speed(3),
		fault(4)
	      }
	MAX-ACCESS  read-only
	STATUS  current
	DESCRIPTION
		"Status of fans."
	::= { ax1230sFanEntry 2 }

ax1230sRedundantPsTable OBJECT-TYPE
        SYNTAX  SEQUENCE OF Ax1230sRedundantPsEntry
        MAX-ACCESS  not-accessible
        STATUS  current
        DESCRIPTION
                "A table containing external power supply information."
        ::= { ax1230sChassis 6 }

ax1230sRedundantPsEntry OBJECT-TYPE
        SYNTAX  Ax1230sRedundantPsEntry
        MAX-ACCESS  not-accessible
        STATUS  current
        DESCRIPTION
                "An entry containing external power supply information."
        INDEX   { ax1230sChassisIndex, ax1230sRedundantPsIndex }
        ::= { ax1230sRedundantPsTable 1 }

        Ax1230sRedundantPsEntry ::=
                SEQUENCE {
                  ax1230sRedundantPsIndex
                        INTEGER,
                  ax1230sRedundantPsConnectStatus
                        INTEGER,
                  ax1230sRedundantPsStatus
                        INTEGER
                }

ax1230sRedundantPsIndex OBJECT-TYPE
        SYNTAX  INTEGER
        MAX-ACCESS  not-accessible
        STATUS  current
        DESCRIPTION
                "An index that shows the external power supply position.
                The value is from 1 to ax1230sRedundantPsNumber."
        ::= { ax1230sRedundantPsEntry 1 }

ax1230sRedundantPsConnectStatus OBJECT-TYPE
        SYNTAX  INTEGER {
                connected(2),
                disconnected(32)
              }
        MAX-ACCESS  read-only
        STATUS  current
        DESCRIPTION
                "Mounting an external power supply is shown."
        ::= { ax1230sRedundantPsEntry 2 }

ax1230sRedundantPsStatus OBJECT-TYPE
        SYNTAX  INTEGER {
                ok(2),
                fault(4),
                disconnected(-1)
              }
        MAX-ACCESS  read-only
        STATUS  current
        DESCRIPTION
                "The operation of an external power supply is shown."
        ::= { ax1230sRedundantPsEntry 3 }

ax1230sPhysLineTable OBJECT-TYPE
	SYNTAX  SEQUENCE OF Ax1230sPhysLineTableEntry
	MAX-ACCESS  not-accessible
	STATUS  current
	DESCRIPTION
		"A table containing physical port information."
	::= { ax1230sPhysLine 1 }

ax1230sPhysLineEntry OBJECT-TYPE
	SYNTAX  Ax1230sPhysLineTableEntry
	MAX-ACCESS  not-accessible
	STATUS  current
	DESCRIPTION
		"An entry containing physical port."
	INDEX   { ax1230sChassisIndex, ax1230sPhysLineIndex }
	::= { ax1230sPhysLineTable 1 }

	Ax1230sPhysLineTableEntry ::=
		SEQUENCE {
		  ax1230sPhysLineIndex
			INTEGER,
		  ax1230sPhysLineConnectorType
			INTEGER,
		  ax1230sPhysLineOperStatus
			INTEGER,
		  ax1230sPhysLineIfIndexNumber
			INTEGER,
		  ax1230sPhysLineTransceiverStatus
		    INTEGER
		}

ax1230sPhysLineIndex OBJECT-TYPE
	SYNTAX  INTEGER
	MAX-ACCESS  not-accessible
	STATUS  current
	DESCRIPTION
		"Physical port number. The value is from 1 to ax1230sNifLineNumber."
	::= { ax1230sPhysLineEntry 1 }

ax1230sPhysLineConnectorType OBJECT-TYPE
	SYNTAX  INTEGER {
		other(1),
		type1000BASE-LX(301),
		type1000BASE-SX(302),
		type1000BASE-LH(303),
		type1000BASE-BX10-D(304),
		type1000BASE-BX10-U(305),
		type1000BASE-BX40-D(306),
		type1000BASE-BX40-U(307),
		type1000BASE-SX2(308),
		type10GBASE-SR(401),
		type10GBASE-LR(402),
        type10GBASE-ER(403)
	      }
	MAX-ACCESS  read-only
	STATUS  current
	DESCRIPTION
		"Connector type is connected physical port. The value is 1(other)
		when connector is disconnected or connector type is unknown.When
		displaying in pannel, requests board name of NIF,then will display it.
		The value is -1	when PSU or NIF board is disconnected."
	::= { ax1230sPhysLineEntry 2 }

ax1230sPhysLineOperStatus OBJECT-TYPE
	SYNTAX  INTEGER {
		other(1),
		active(2),
		initialization(3),
		down(4),
		lock(6),
		line-fault(8),
		test(9),
		inactive(20)
	      }
	MAX-ACCESS  read-only
	STATUS  current
	DESCRIPTION
		"Status of physical port. The value is -1 when PSU or NIF board is
		disconnected."
	::= { ax1230sPhysLineEntry 3 }

ax1230sPhysLineIfIndexNumber OBJECT-TYPE
	SYNTAX  INTEGER
	MAX-ACCESS  read-only
	STATUS  current
	DESCRIPTION
		"Number of ifIndex which is included in physical port.The value is -1
		when PSU board or NIF board is disconnected."
	::= { ax1230sPhysLineEntry 4 }

ax1230sPhysLineTransceiverStatus OBJECT-TYPE
	SYNTAX  INTEGER{
			unchangeable-transceiver(1),
                        sfp-mounted(20),
                        sfp-unmounted(21),
                        unsupported-sfp-mounted(22),
                        sfp-status-unknown(23),
                        xfp-mounted(30),
                        xfp-unmounted(31),
                        unsupported-xfp-mounted(32),
                        xfp-status-unknown(33)
                        }
	MAX-ACCESS  read-only
	STATUS  current
	DESCRIPTION
		"Type and status of replaceable transceiver."
	::= { ax1230sPhysLineEntry 5 }
--
-- ax1230sFdbClearMIB      OBJECT IDENTIFIER ::= { ax1230sOperationCommand 1 }
--

ax1230sFdbClearSet OBJECT-TYPE
	SYNTAX  INTEGER {
                    initialValue(0),
                    processing(1),
                    failure(2),
                    success(3)
                }
	MAX-ACCESS  read-write
	STATUS  current
	DESCRIPTION
		"Fdb clear information. When want to clear fdb, 
		then set value of this MIB as 1."
	::= { ax1230sFdbClearMIB 1 }

ax1230sFdbClearReqTime OBJECT-TYPE
	SYNTAX  TimeTicks
	MAX-ACCESS  read-only
	STATUS  current
	DESCRIPTION
		"This object indicates the most recent time that
		received the demand to clear Fdb information.(sysUpTime)"
	::= { ax1230sFdbClearMIB 2 }

ax1230sFdbClearSuccessTime OBJECT-TYPE
	SYNTAX  TimeTicks
	MAX-ACCESS  read-only
	STATUS  current
	DESCRIPTION
		"This object indicates the time of the most recent
		 Fdb clearing success.(sysUpTime)"
	::= { ax1230sFdbClearMIB 3 }


-- Traps for use by AlaxalA networks AX1230S

-- Traps are defined using the conventions in RFC 1215.

axsStaticGatewayStateChange TRAP-TYPE
	ENTERPRISE      axsStaticTraps
	VARIABLES       { axsStaticGatewayAddr, axsStaticGatewayState }
	DESCRIPTION
		"static route gateway state change."
	::= 1

axsOspfVirtIfStateChange TRAP-TYPE
	ENTERPRISE      axsOspfTraps
	VARIABLES       { axsOspfVirtIfDomainNumber, axsOspfRouterId, axsOspfVirtIfAreaId, axsOspfVirtIfNeighbor, axsOspfVirtIfState }
	DESCRIPTION
		"An axsOspfIfStateChange trap signifies that there has  been a change 
		in the state of an OSPF virtual interface."
	::= 1

axsOspfNbrStateChange TRAP-TYPE
	ENTERPRISE      axsOspfTraps
	VARIABLES       { axsOspfNbrDomainNumber, axsOspfRouterId, axsOspfNbrIpAddr, axsOspfNbrAddressLessIndex, axsOspfNbrRtrId, axsOspfNbrState }
	DESCRIPTION
           "An axsOspfNbrStateChange trap signifies that
           there  has been a change in the state of a non-
           virtual OSPF neighbor.   This  trap  should  be
           generated  when  the  neighbor  state regresses
           (e.g., goes from Attempt or Full  to  1-Way  or
           Down)  or progresses to a terminal state (e.g.,
           2-Way or Full).  When an  neighbor  transitions
           from  or  to Full on non-broadcast multi-access
           and broadcast networks, the trap should be gen-
           erated  by the designated router.  A designated
           router transitioning to Down will be  noted  by
           axsOspfIfStateChange."
	::= 2

axsOspfVirtNbrStateChange TRAP-TYPE
	ENTERPRISE      axsOspfTraps
	VARIABLES       { axsOspfVirtNbrDomainNumber, axsOspfRouterId, axsOspfVirtNbrArea, axsOspfVirtNbrRtrId, axsOspfVirtNbrState }
	DESCRIPTION
           "An axsOspfIfStateChange trap signifies that there
           has  been a change in the state of an OSPF vir-
           tual neighbor.  This trap should  be  generated
           when  the  neighbor state regresses (e.g., goes
           from Attempt or  Full  to  1-Way  or  Down)  or
           progresses to a terminal state (e.g., Full)."
	::= 3

axsOspfIfConfigError TRAP-TYPE
	ENTERPRISE      axsOspfTraps
	VARIABLES       { axsOspfIfDomainNumber, axsOspfRouterId, axsOspfIfIpAddress, axsOspfAddressLessIf, axsOspfPacketSrc, axsOspfConfigErrorType, axsOspfPacketType }
	DESCRIPTION
           "An axsOspfIfConfigError  trap  signifies  that  a
           packet  has  been received on a non-virtual in-
           terface  from  a  router  whose   configuration
           parameters  conflict  with this router's confi-
           guration parameters.  Note that the  event  op-
           tionMismatch  should  cause  a  trap only if it
           prevents an adjacency from forming."
	::= 4

axsOspfVirtIfConfigError TRAP-TYPE
	ENTERPRISE      axsOspfTraps
	VARIABLES       { axsOspfVirtIfDomainNumber, axsOspfRouterId, axsOspfVirtIfAreaId, axsOspfVirtIfNeighbor, axsOspfConfigErrorType, axsOspfPacketType }
	DESCRIPTION
           "An axsOspfConfigError trap signifies that a pack-
           et  has  been  received  on a virtual interface
           from a router  whose  configuration  parameters
           conflict   with   this  router's  configuration
           parameters.  Note that the event optionMismatch
           should  cause a trap only if it prevents an ad-
           jacency from forming."
	::= 5

axsOspfIfAuthFailure TRAP-TYPE
	ENTERPRISE      axsOspfTraps
	VARIABLES       { axsOspfIfDomainNumber, axsOspfRouterId, axsOspfIfIpAddress, axsOspfAddressLessIf, axsOspfPacketSrc, axsOspfConfigErrorType, axsOspfPacketType }
	DESCRIPTION
           "An axsOspfIfAuthFailure  trap  signifies  that  a
           packet  has  been received on a non-virtual in-
           terface from a router whose authentication  key
           or  authentication  type  conflicts  with  this
           router's authentication key  or  authentication
           type."
	::= 6

axsOspfVirtIfAuthFailure TRAP-TYPE
	ENTERPRISE      axsOspfTraps
	VARIABLES       { axsOspfVirtIfDomainNumber, axsOspfRouterId, axsOspfVirtIfAreaId, axsOspfVirtIfNeighbor, axsOspfConfigErrorType, axsOspfPacketType }
	DESCRIPTION
           "An axsOspfVirtIfAuthFailure trap signifies that a
           packet has been received on a virtual interface
           from a router whose authentication key  or  au-
           thentication  type conflicts with this router's
           authentication key or authentication type."
	::= 7

axsOspfIfStateChange TRAP-TYPE
	ENTERPRISE      axsOspfTraps
	VARIABLES       { axsOspfIfDomainNumber, axsOspfRouterId, axsOspfIfIpAddress, axsOspfAddressLessIf, axsOspfIfState }
	DESCRIPTION
           "An axsOspfIfStateChange trap signifies that there
           has been a change in the state of a non-virtual
           OSPF interface. This trap should  be  generated
           when  the interface state regresses (e.g., goes
           from Dr to Down) or progresses  to  a  terminal
           state  (i.e.,  Point-to-Point, DR Other, Dr, or
           Backup)."
	::= 16 

axsOadpNeighborCachelastChangeTrap TRAP-TYPE
	ENTERPRISE      axsOadpMIBNotifications
	VARIABLES       { axsOadpNeighborCacheLastChange }
	DESCRIPTION
           "This trap indicates that information of OADP neighbor nodes is updated."
	::= 1 

-- ax1230sAuth group

--ax1230sAuthInfo OBJECT-TYPE
--	SYNTAX  INTEGER
--	MAX-ACCESS  not-accessible
--	STATUS  current
--	DESCRIPTION
--		"Private trap of Authentication."
--	::= { ax1230sAuth 1 }

ax1230sAuthSysName OBJECT-TYPE
	SYNTAX  DisplayString (SIZE (0..60))
	MAX-ACCESS  not-accessible
	STATUS  current
	DESCRIPTION
		"System name of authentication."
	::= { ax1230sAuthInfo 1 }

ax1230sAuthIfIndex OBJECT-TYPE
	SYNTAX  INTEGER
	MAX-ACCESS  not-accessible
	STATUS  current
	DESCRIPTION
		"ifIndex of authentication."
	::= { ax1230sAuthInfo 2 }

ax1230sAuthSupplicantMac OBJECT-TYPE
	SYNTAX  MacAddress
	MAX-ACCESS  not-accessible
	STATUS  current
	DESCRIPTION
		"Mac address of authentication."
	::= { ax1230sAuthInfo 3 }

ax1230sAuthMessage OBJECT-TYPE
	SYNTAX  DisplayString (SIZE (0..280))
	MAX-ACCESS  not-accessible
	STATUS  current
	DESCRIPTION
		"Message of authentication."
	::= { ax1230sAuthInfo 4 }

--ax1230sDot1x OBJECT-TYPE
--	SYNTAX  INTEGER
--	MAX-ACCESS  not-accessible
--	STATUS  current
--	DESCRIPTION
--		"Private trap of 802.1X authentication."
--	::= { ax1230sAuth 2 }

ax1230sDot1xFailure OBJECT-TYPE
	SYNTAX  SEQUENCE OF Ax1230sAuthInfoTableEntry
	MAX-ACCESS  not-accessible
	STATUS  current
	DESCRIPTION
		"Private trap of 802.1X authentication failure."
	::= { ax1230sDot1x 1 }

ax1230sDot1xEvent OBJECT-TYPE
	SYNTAX  SEQUENCE OF Ax1230sAuthInfoTableEntry
	MAX-ACCESS  not-accessible
	STATUS  current
	DESCRIPTION
		"Private trap of 802.1X authentication event."
	::= { ax1230sDot1x 2 }

ax1230sDot1xSystem OBJECT-TYPE
	SYNTAX  SEQUENCE OF Ax1230sAuthInfoTableEntry
	MAX-ACCESS  not-accessible
	STATUS  current
	DESCRIPTION
		"Private trap of 802.1X authentication system."
	::= { ax1230sDot1x 3 }

--ax1230sWauth OBJECT-TYPE
--	SYNTAX  INTEGER
--	MAX-ACCESS  not-accessible
--	STATUS  current
--	DESCRIPTION
--		"Private trap of Web authentication."
--	::= { ax1230sAuth 2 }

ax1230sWauthFailure OBJECT-TYPE
	SYNTAX  SEQUENCE OF Ax1230sAuthInfoTableEntry
	MAX-ACCESS  not-accessible
	STATUS  current
	DESCRIPTION
		"Private trap of Web authentication failure."
	::= { ax1230sWauth 1 }

ax1230sWauthEvent OBJECT-TYPE
	SYNTAX  SEQUENCE OF Ax1230sAuthInfoTableEntry
	MAX-ACCESS  not-accessible
	STATUS  current
	DESCRIPTION
		"Private trap of Web authentication event."
	::= { ax1230sWauth 2 }

ax1230sWauthSystem OBJECT-TYPE
	SYNTAX  SEQUENCE OF Ax1230sAuthInfoTableEntry
	MAX-ACCESS  not-accessible
	STATUS  current
	DESCRIPTION
		"Private trap of Web authentication system."
	::= { ax1230sWauth 3 }

--ax1230sMauth OBJECT-TYPE
--	SYNTAX  INTEGER
--	MAX-ACCESS  not-accessible
--	STATUS  current
--	DESCRIPTION
--		"Private trap of Mac authentication."
--	::= { ax1230sAuth 3 }

ax1230sMauthFailure OBJECT-TYPE
	SYNTAX  SEQUENCE OF Ax1230sAuthInfoTableEntry
	MAX-ACCESS  not-accessible
	STATUS  current
	DESCRIPTION
		"Private trap of Mac authentication failure."
	::= { ax1230sMauth 1 }

ax1230sMauthEvent OBJECT-TYPE
	SYNTAX  SEQUENCE OF Ax1230sAuthInfoTableEntry
	MAX-ACCESS  not-accessible
	STATUS  current
	DESCRIPTION
		"Private trap of Mac authentication event."
	::= { ax1230sMauth 2 }

ax1230sMauthSystem OBJECT-TYPE
	SYNTAX  SEQUENCE OF Ax1230sAuthInfoTableEntry
	MAX-ACCESS  not-accessible
	STATUS  current
	DESCRIPTION
		"Private trap of Mac authentication system."
	::= { ax1230sMauth 3 }

	Ax1230sAuthInfoTableEntry ::=
		SEQUENCE {
		  ax1230sAuthSysName
			DisplayString,
		  ax1230sAuthIfIndex
			INTEGER,
		  ax1230sAuthSupplicantMac
			MacAddress,
		  ax1230sAuthMessage
			DisplayString
		}

-- Traps for use by AlaxalA networks AX1230S

-- Traps are defined using the conventions in RFC 1215.

ax1230sSystemMsgTrap TRAP-TYPE
	ENTERPRISE      ax1230s
	VARIABLES       { ax1230sSystemMsgType, ax1230sSystemMsgTimeStamp,
                          ax1230sSystemMsgLevel, ax1230sSystemMsgEventPoint,
                          ax1230sSystemMsgEventInterfaceID, ax1230sSystemMsgEventCode,
                          ax1230sSystemMsgAdditionalCode, ax1230sSystemMsgText }
	DESCRIPTION
		"System message is displayed."
	::= 1

ax1230sStandbySystemUpTrap TRAP-TYPE
	ENTERPRISE      ax1230s
	VARIABLES       { ax1230sChassisIndex }
	DESCRIPTION
		"Standby system is restarted."
	::= 2

ax1230sStandbySystemDownTrap TRAP-TYPE
	ENTERPRISE      ax1230s
	VARIABLES       { ax1230sChassisIndex }
	DESCRIPTION
		"Standby system is failed."
	::= 3

ax1230sTemperatureTrap TRAP-TYPE
	ENTERPRISE ax1230s
	VARIABLES {
		ax1230sChassisIndex,
		ax1230sTemperatureStatusIndex,
		ax1230sTemperatureStatusDescr, 
		ax1230sTemperatureStatusValue, 
		ax1230sTemperatureState }
	DESCRIPTION
		"A ax1230sTemperatureTrap is sent if the 
		temperature measured at a given testpoint is outside 
		the normal range for the testpoint (i.e. is at the warning, 
		critical, or shutdown stage)."
	::= 4

ax1230sGsrpStateTransitionTrap TRAP-TYPE
	ENTERPRISE      ax1230s
	VARIABLES       { axsGsrpGroupId, axsGsrpVlanGroupId, axsGsrpState }
	DESCRIPTION
		"Changes of the VLAN group state of GSRP"
	::= 6

ax1230sEoeMsgTrap TRAP-TYPE
	ENTERPRISE      ax1230s
	VARIABLES       { ax1230sSystemMsgType, ax1230sSystemMsgTimeStamp, ax1230sSystemMsgLevel, ax1230sSystemMsgEventPoint, ax1230sSystemMsgEventInterfaceID, ax1230sSystemMsgEventCode, ax1230sSystemMsgAdditionalCode, ax1230sSystemMsgText }
	DESCRIPTION
		"The notice of a message of EoE"
	::= 7

ax1230sAirFanStopTrap TRAP-TYPE
	ENTERPRISE      ax1230s
	DESCRIPTION
             "This trap indicates a fan failure." 
	::= 8 

ax1230sPowerSupplyFailureTrap TRAP-TYPE
	ENTERPRISE      ax1230s
	DESCRIPTION
             "This trap indicates one ( or more ) of power supplies failure." 
	::= 9 

ax1230sLoginSuccessTrap TRAP-TYPE
	ENTERPRISE      ax1230s
	VARIABLES       { axsLoginName, axsLoginTime, axsLoginLocation, axsLoginLine }
	DESCRIPTION
             "This trap indicates success of user log in." 
	::= 10 

ax1230sLoginFailureTrap TRAP-TYPE
	ENTERPRISE      ax1230s
	VARIABLES       { axsLoginName, axsLoginFailureTime, 
                          axsLoginLocation, axsLoginLine }
	DESCRIPTION
             "This trap indicates failure of user log in." 
	::= 11

ax1230sLogoutTrap TRAP-TYPE
	ENTERPRISE      ax1230s
	VARIABLES       { axsLoginName, axsLoginTime, axsLogoutTime, 
                          axsLoginLocation, axsLoginLine, axsLogoutStatus }
	DESCRIPTION
             "This trap indicates success of following log out.
	       'logout' command, 'exit' command, 'quit' command." 
	::= 12

ax1230sMemoryUsageTrap  TRAP-TYPE
	ENTERPRISE      ax1230s
	DESCRIPTION
             "This indicates available memory is fewer than lower limit." 
	::= 13

ax1230sFrameErrorReceiveTrap  TRAP-TYPE
	ENTERPRISE      ax1230s
	VARIABLES       { ifIndex }
	DESCRIPTION
             "This indicates frame receive error." 
	::= 18

ax1230sFrameErrorSendTrap  TRAP-TYPE
	ENTERPRISE      ax1230s
	VARIABLES       { ifIndex }
	DESCRIPTION
             "This indicates frame send error." 
	::= 19

axsBroadcastStormDetectTrap TRAP-TYPE
	ENTERPRISE      ax1230s
	VARIABLES       { ifIndex }
	DESCRIPTION
             "This indicates decection on broad-cast storm." 
	::= 20

axsMulticastStormDetectTrap TRAP-TYPE
	ENTERPRISE      ax1230s
	VARIABLES       { ifIndex }
	DESCRIPTION
             "This indicates decection on multi-cast storm." 
	::= 21

axsUnicastStormDetectTrap TRAP-TYPE
	ENTERPRISE      ax1230s
	VARIABLES       { ifIndex }
	DESCRIPTION
             "This indicates decection on uni-cast storm." 
	::= 22

axsBroadcastStormPortInactivateTrap TRAP-TYPE
	ENTERPRISE      ax1230s
	VARIABLES       { ifIndex }
	DESCRIPTION
             "This indicates the port inactivated for decection on broad-cast storm." 
	::= 23

axsMulticastStormPortInactivateTrap TRAP-TYPE
	ENTERPRISE      ax1230s
	VARIABLES       { ifIndex }
	DESCRIPTION
             "This indicates the port inactivated for decection on multi-cast storm." 
	::= 24

axsUniticastStormPortInactivateTrap TRAP-TYPE
	ENTERPRISE      ax1230s
	VARIABLES       { ifIndex }
	DESCRIPTION
             "This indicates the port inactivated for decection on uni-cast storm." 
	::= 25

axsBroadcastStormRecoverTrap TRAP-TYPE
	ENTERPRISE      ax1230s
	VARIABLES       { ifIndex }
	DESCRIPTION
             "This indicates the end of broad-cast storm." 
	::= 26

axsMulticastStormRecoverTrap TRAP-TYPE
	ENTERPRISE      ax1230s
	VARIABLES       { ifIndex }
	DESCRIPTION
             "This indicates the end of multi-cast storm." 
	::= 27
	
axsUnicastStormRecoverTrap TRAP-TYPE
	ENTERPRISE      ax1230s
	VARIABLES       { ifIndex }
	DESCRIPTION
             "This indicates the end of multi-cast storm." 
	::= 28
	
axsEfmoamUdldPortInactivateTrap TRAP-TYPE
	ENTERPRISE      ax1230s
	VARIABLES       { ifIndex }
	DESCRIPTION
             "Efmoam udld port inactivate trap."
	::= 29

axsEfmoamLoopDetectPortInactivateTrap TRAP-TYPE
	ENTERPRISE      ax1230s
	VARIABLES       { ifIndex }
	DESCRIPTION
             "Efmoam loop detect port inactivate trap."
	::= 30

ax1230sDot1xFailureTrap  TRAP-TYPE
	ENTERPRISE      ax1230s
	VARIABLES       { ax1230sAuthSysName, ax1230sAuthIfIndex, ax1230sAuthSupplicantMac, ax1230sAuthMessage }
	DESCRIPTION
             "Private trap of 802.1X authentication failure." 
	::= 31

ax1230sDot1xEventTrap  TRAP-TYPE
	ENTERPRISE      ax1230s
	VARIABLES       { ax1230sAuthSysName, ax1230sAuthIfIndex, ax1230sAuthSupplicantMac, ax1230sAuthMessage }
	DESCRIPTION
             "Private trap of 802.1X authentication event." 
	::= 32

ax1230sWauthFailureTrap  TRAP-TYPE
	ENTERPRISE      ax1230s
	VARIABLES       { ax1230sAuthSysName, ax1230sAuthIfIndex, ax1230sAuthSupplicantMac, ax1230sAuthMessage }
	DESCRIPTION
             "Private trap of Web authentication failure." 
	::= 33

ax1230sWauthEventTrap  TRAP-TYPE
	ENTERPRISE      ax1230s
	VARIABLES       { ax1230sAuthSysName, ax1230sAuthIfIndex, ax1230sAuthSupplicantMac, ax1230sAuthMessage }
	DESCRIPTION
             "Private trap of Web authentication event." 
	::= 34

ax1230sMauthFailureTrap  TRAP-TYPE
	ENTERPRISE      ax1230s
	VARIABLES       { ax1230sAuthSysName, ax1230sAuthIfIndex, ax1230sAuthSupplicantMac, ax1230sAuthMessage }
	DESCRIPTION
             "Private trap of Mac authentication failure." 
	::= 35

ax1230sMauthEventTrap  TRAP-TYPE
	ENTERPRISE      ax1230s
	VARIABLES       { ax1230sAuthSysName, ax1230sAuthIfIndex, ax1230sAuthSupplicantMac, ax1230sAuthMessage }
	DESCRIPTION
             "Private trap of Mac authentication event." 
	::= 36

ax1230sDot1xSystemTrap  TRAP-TYPE
	ENTERPRISE      ax1230s
	VARIABLES       { ax1230sAuthSysName, ax1230sAuthIfIndex, ax1230sAuthSupplicantMac, ax1230sAuthMessage }
	DESCRIPTION
             "Private trap of 802.1X authentication system." 
	::= 37

ax1230sWauthSystemTrap  TRAP-TYPE
	ENTERPRISE      ax1230s
	VARIABLES       { ax1230sAuthSysName, ax1230sAuthIfIndex, ax1230sAuthSupplicantMac, ax1230sAuthMessage }
	DESCRIPTION
             "Private trap of Web authentication system." 
	::= 38

ax1230sMauthSystemTrap  TRAP-TYPE
	ENTERPRISE      ax1230s
	VARIABLES       { ax1230sAuthSysName, ax1230sAuthIfIndex, ax1230sAuthSupplicantMac, ax1230sAuthMessage }
	DESCRIPTION
             "Private trap of Mac authentication system." 
	::= 39
			
axsL2ldLinkDown TRAP-TYPE
	ENTERPRISE      ax1230s
	VARIABLES       { axsL2ldPortIfIndex,axsL2ldPortSourcePortIfindex,axsL2ldPortDestinationPortIfindex,axsL2ldPortSourceVlan }
	DESCRIPTION
           "When the operation of the interface changes from ACTIVE(state that can be communicated)
           into DISABLE (state that cannot be communicated) by the L2 loop detection."
	::= 51

axsL2ldLinkUp TRAP-TYPE
	ENTERPRISE      ax1230s
	VARIABLES       { axsL2ldPortIfIndex }
	DESCRIPTION
           "When the operation of the interface changes from DISABLE (state that cannot be communicated)
           into ACTIVE (state that can be communicated) by the automatic restoration function of the L2 loop detection."
	::= 52

axsL2ldLoopDetection TRAP-TYPE
	ENTERPRISE      ax1230s
	VARIABLES       { axsL2ldPortIndex,axsL2ldPortIfIndex,axsL2ldPortSourcePortIfindex,axsL2ldPortSourceVlan }
	DESCRIPTION
           "When you detect the L2 loop. It notifies every 60 seconds when the state of the L2 loop continues."
	::= 53

END
