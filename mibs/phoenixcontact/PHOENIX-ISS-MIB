-- Phoenix Contact ISS MIB (subset for LibreNMS)
-- Extracted from PHOENIX-ISS-MIB (fsiss.mib)
-- Enterprise OID: .1.3.6.1.4.1.4346
--
-- Copyright (C) 2018-2025 Phoenix Contact. All Rights Reserved.

PHOENIX-ISS-MIB DEFINITIONS ::= BEGIN

IMPORTS
    MODULE-IDENTITY, OBJECT-TYPE, Integer32, enterprises
        FROM SNMPv2-SMI
    DisplayString
        FROM SNMPv2-TC;

phoenixContact      OBJECT IDENTIFIER ::= { enterprises 4346 }
pxcOEM              OBJECT IDENTIFIER ::= { phoenixContact 99 }
pxcOEMIS5           OBJECT IDENTIFIER ::= { pxcOEM 1 }

iss MODULE-IDENTITY
    LAST-UPDATED    "202409040000Z"
    ORGANIZATION    "Phoenix Contact"
    CONTACT-INFO    "Phoenix Contact GmbH & Co. KG"
    DESCRIPTION     "Phoenix Contact ISS MIB for managed industrial switches."
    ::= { pxcOEMIS5 2 }

issSystem           OBJECT IDENTIFIER ::= { iss 121 }

-- System Information

issSwitchName OBJECT-TYPE
    SYNTAX      DisplayString (SIZE(1..15))
    MAX-ACCESS  read-only
    STATUS      current
    DESCRIPTION "System name of the switch."
    ::= { issSystem 1 }

issSwitchOrderNo OBJECT-TYPE
    SYNTAX      DisplayString
    MAX-ACCESS  read-only
    STATUS      current
    DESCRIPTION "Order number / part number of the switch."
    ::= { issSystem 2 }

-- Temperature Sensors

issSwitchMinThresholdTemperature OBJECT-TYPE
    SYNTAX      Integer32
    MAX-ACCESS  read-only
    STATUS      current
    DESCRIPTION "Minimum threshold temperature of the switch in celsius."
    ::= { issSystem 64 }

issSwitchMaxThresholdTemperature OBJECT-TYPE
    SYNTAX      Integer32
    MAX-ACCESS  read-only
    STATUS      current
    DESCRIPTION "Maximum threshold temperature of the switch in celsius."
    ::= { issSystem 65 }

issSwitchCurrentTemperature OBJECT-TYPE
    SYNTAX      Integer32
    MAX-ACCESS  read-only
    STATUS      current
    DESCRIPTION "Current temperature of the switch in celsius."
    ::= { issSystem 66 }

-- CPU

issSwitchMaxCPUThreshold OBJECT-TYPE
    SYNTAX      Integer32 (1..100)
    MAX-ACCESS  read-write
    STATUS      current
    DESCRIPTION "Maximum CPU usage threshold in percentage."
    ::= { issSystem 67 }

issSwitchCurrentCPUThreshold OBJECT-TYPE
    SYNTAX      Integer32
    MAX-ACCESS  read-only
    STATUS      current
    DESCRIPTION "Current CPU usage of the switch in percentage."
    ::= { issSystem 68 }

-- Power Supply

issSwitchPowerSurge OBJECT-TYPE
    SYNTAX      Integer32 (1..255)
    MAX-ACCESS  read-write
    STATUS      current
    DESCRIPTION "Maximum power supply voltage threshold in volts."
    ::= { issSystem 69 }

issSwitchPowerFailure OBJECT-TYPE
    SYNTAX      Integer32 (1..255)
    MAX-ACCESS  read-write
    STATUS      current
    DESCRIPTION "Minimum power supply voltage threshold in volts."
    ::= { issSystem 70 }

issSwitchCurrentPowerSupply OBJECT-TYPE
    SYNTAX      Integer32
    MAX-ACCESS  read-only
    STATUS      current
    DESCRIPTION "Current power supply voltage in volts."
    ::= { issSystem 71 }

-- RAM

issSwitchMaxRAMUsage OBJECT-TYPE
    SYNTAX      Integer32 (1..100)
    MAX-ACCESS  read-write
    STATUS      current
    DESCRIPTION "Maximum RAM usage threshold in percentage."
    ::= { issSystem 72 }

issSwitchCurrentRAMUsage OBJECT-TYPE
    SYNTAX      Integer32
    MAX-ACCESS  read-only
    STATUS      current
    DESCRIPTION "Current RAM usage of the switch in percentage."
    ::= { issSystem 73 }

-- Flash

issSwitchMaxFlashUsage OBJECT-TYPE
    SYNTAX      Integer32 (1..100)
    MAX-ACCESS  read-write
    STATUS      current
    DESCRIPTION "Maximum flash usage threshold in percentage."
    ::= { issSystem 74 }

issSwitchCurrentFlashUsage OBJECT-TYPE
    SYNTAX      Integer32
    MAX-ACCESS  read-only
    STATUS      current
    DESCRIPTION "Current flash usage of the switch in percentage."
    ::= { issSystem 75 }

-- Device Information

issSwitchModelName OBJECT-TYPE
    SYNTAX      DisplayString
    MAX-ACCESS  read-only
    STATUS      current
    DESCRIPTION "Hardware model name of the switch."
    ::= { issSystem 128 }

issSwitchHWRevision OBJECT-TYPE
    SYNTAX      DisplayString
    MAX-ACCESS  read-only
    STATUS      current
    DESCRIPTION "Hardware revision of the switch."
    ::= { issSystem 122 }

issSwitchSerialNo OBJECT-TYPE
    SYNTAX      DisplayString
    MAX-ACCESS  read-only
    STATUS      current
    DESCRIPTION "Serial number of the switch."
    ::= { issSystem 123 }

issSwitchFWVersion OBJECT-TYPE
    SYNTAX      DisplayString
    MAX-ACCESS  read-only
    STATUS      current
    DESCRIPTION "Firmware version of the switch."
    ::= { issSystem 124 }

issSwitchFullModelName OBJECT-TYPE
    SYNTAX      DisplayString
    MAX-ACCESS  read-only
    STATUS      current
    DESCRIPTION "Full hardware model name including variant."
    ::= { issSystem 121 }

issSwitchSysName OBJECT-TYPE
    SYNTAX      DisplayString
    MAX-ACCESS  read-only
    STATUS      current
    DESCRIPTION "Configured system name."
    ::= { issSystem 143 }

END
