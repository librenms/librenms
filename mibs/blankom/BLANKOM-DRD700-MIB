-- ****************************************************************************
-- * (c) Blankom Digital GmbH 2002-2012                                        
-- ****************************************************************************
                                                                               
BLANKOM-DRD700-MIB DEFINITIONS ::= BEGIN                                       
                                                                               
--  LAST-UPDATED "27.09.2012"                                                  
--                                                                             
--  ORGANIZATION "Blankom Digital GmbH"                                        
--                                                                             
--  CONTACT-INFO "Blankom Digital GmbH                                         
--                TecCenter                                                    
--                31162 Bad Salzdetfurth                                       
--                e-mail service@blankom-digital.de                            
--                Germany"                                                     
--                                                                             
--                                                                             
--  DESCRIPTION                                                                
--      "This MIB implements the Blankom DRD700-MIB"                           
--                                                                             
--  REVISION     "V00.09.00"                                                   
--  DESCRIPTION                                                                
--      "First release"                                                        
--                                                                             
                                                                               
IMPORTS                                                                        
digital, DisplayString, TruthValue,  NESlotValue,                              
PerceivedSeverityValue, InitPhaseValue                                         
FROM BLANKOM-ROOT-MIB;                                                         
                                                                               
--                                                                             
-- Node definitions                                                            
--                                                                             
drd700 OBJECT IDENTIFIER ::= { digital 45 }                                    
ne OBJECT IDENTIFIER ::= { drd700 1 }                                          
neCommon OBJECT IDENTIFIER ::= { ne 1 }
neConfig OBJECT IDENTIFIER ::= { ne 3 }
input OBJECT IDENTIFIER ::= { neConfig 10 }
ts1 OBJECT IDENTIFIER ::= { input 20 }
ts2 OBJECT IDENTIFIER ::= { input 25 }
ts3 OBJECT IDENTIFIER ::= { input 30 }
ts4 OBJECT IDENTIFIER ::= { input 35 }
dvb-s-s2 OBJECT IDENTIFIER ::= { input 200 }
dvb-t-t2 OBJECT IDENTIFIER ::= { input 210 }
dvb-c-c2 OBJECT IDENTIFIER ::= { input 220 }
input-ip OBJECT IDENTIFIER ::= { input 230 }
common-interface OBJECT IDENTIFIER ::= { neConfig 20 }
slot1 OBJECT IDENTIFIER ::= { common_interface 20 }
slot2 OBJECT IDENTIFIER ::= { common_interface 30 }
slot3 OBJECT IDENTIFIER ::= { common_interface 40 }
slot4 OBJECT IDENTIFIER ::= { common_interface 50 }
mux OBJECT IDENTIFIER ::= { neConfig 30 }
mux1 OBJECT IDENTIFIER ::= { mux 20 }
mux2 OBJECT IDENTIFIER ::= { mux 30 }
mux3 OBJECT IDENTIFIER ::= { mux 40 }
mux4 OBJECT IDENTIFIER ::= { mux 50 }
output OBJECT IDENTIFIER ::= { neConfig 40 }
output-ip OBJECT IDENTIFIER ::= { output 30 }
mpts OBJECT IDENTIFIER ::= { output_ip 10 }
spts OBJECT IDENTIFIER ::= { output_ip 50 }
output_asi OBJECT IDENTIFIER ::= { output 40 }
lan OBJECT IDENTIFIER ::= { neConfig 50 }
snmpv2 OBJECT IDENTIFIER ::= { lan 50 }
telnet OBJECT IDENTIFIER ::= { lan 60 }
redundancy OBJECT IDENTIFIER ::= { lan 70 }
system OBJECT IDENTIFIER ::= { neConfig 60 }
date-time OBJECT IDENTIFIER ::= { system 100 }
user_accounts OBJECT IDENTIFIER ::= { neConfig 70 }

--
-- Type definitions
--
ConfigNETypeValue ::= INTEGER
{
  headend1(1),
  ringhub1(20)
}

		neType OBJECT-TYPE
			SYNTAX DisplayString (SIZE (0..32))
			ACCESS read-only
			STATUS mandatory
			DESCRIPTION
				"Displays the type of the NE. Some agents have configurable types
				(neConfigNEtype), some agents have one fixed type."
			::= { neCommon 1 }

		neStates OBJECT IDENTIFIER ::= { ne 2 }

		neStatesBootloaderVersion OBJECT-TYPE
			SYNTAX DisplayString (SIZE (0..32))
			ACCESS read-only
			STATUS mandatory
			DESCRIPTION
				"Bootloader Version"
			::= { neStates 1 }

		neStatesApplicationVersion OBJECT-TYPE
			SYNTAX DisplayString (SIZE (0..32))
			ACCESS read-only
			STATUS mandatory
			DESCRIPTION
				"Application Version"
			::= { neStates 2 }

		neStatesFPGAVersion OBJECT-TYPE
			SYNTAX DisplayString (SIZE (0..32))
			ACCESS read-only
			STATUS mandatory
			DESCRIPTION
				"FPGA Version"
			::= { neStates 4 }

		neStatesFPGACpuVersion OBJECT-TYPE
			SYNTAX DisplayString (SIZE (0..32))
			ACCESS read-only
			STATUS mandatory
			DESCRIPTION
				"FPGA Cpu Version"
			::= { neStates 5 }

		neStatesDeviceStatus OBJECT-TYPE
			SYNTAX INTEGER
			ACCESS read-only
			STATUS mandatory
			DESCRIPTION
				"DeviceStatus ( 
						Bit#1  = DMS STATUS FAILURE
						Bit#2  = INPUT SIGNAL STATUS FAILURE
						Bit#3  = BER STATUS FAILURE
						Bit#4  = AFC STATUS FAILURE
						Bit#5  = FAN STATUS FAILURE
						Bit#6  = POWER STATUS_FAILURE
						Bit#7  = FPGA STATUS FAILURE
						Bit#8  = FE_BOARD_1 STATUS FAILURE
						Bit#9  = FE_BOARD_2 STATUS FAILURE
						Bit#10 = I2C STATUS FAILURE
						Bit#11 = DISPLAY STATUS FAILURE
						Bit#12 = unused
						Bit#13 = unused
						Bit#14 = unused
						Bit#15 = unused
						Bit#16 = unused
						Bit#17 = unused
						Bit#18 = unused
						Bit#19 = unused
						Bit#20 = unused
						Bit#21 = unused
						Bit#22 = unused
						Bit#23 = unused
						Bit#24 = unused
						Bit#25 = unused
						Bit#26 = unused
						Bit#27 = unused
						Bit#28 = unused
						Bit#29 = unused
						Bit#30 = unused
						Bit#31 = unused
						Bit#32 = unused
						)."
			::= { neStates 10  }

		neStatesMacAddress1 OBJECT-TYPE
			SYNTAX DisplayString (SIZE (0..16))
			ACCESS read-only
			STATUS mandatory
			DESCRIPTION
				"Mac Address 1"
			::= { neStates 11 }

		neStatesMacAddress2 OBJECT-TYPE
			SYNTAX DisplayString (SIZE (0..16))
			ACCESS read-only
			STATUS mandatory
			DESCRIPTION
				"Mac Address 2"
			::= { neStates 12 }

		neStatesDeviceSerialNumber OBJECT-TYPE
			SYNTAX DisplayString (SIZE (0..16))
			ACCESS read-only
			STATUS mandatory
			DESCRIPTION
				"Device Serial Number"
			::= { neStates 13 }

		neStatesDeviceType OBJECT-TYPE
			SYNTAX DisplayString (SIZE (0..16))
			ACCESS read-only
			STATUS mandatory
			DESCRIPTION
				"Device Type"
			::= { neStates 14 }

		neStatesDeviceLedInput OBJECT-TYPE
			SYNTAX INTEGER (1..4)
			ACCESS read-only
			STATUS mandatory
			DESCRIPTION
				"LED Input ( 1 = green, 2 = red, 3 = orange, 4 = off )."
			::= { neStates 15  }

		neStatesDeviceLedStatus OBJECT-TYPE
			SYNTAX INTEGER (1..4)
			ACCESS read-only
			STATUS mandatory
			DESCRIPTION
				"LED Status ( 1 = green, 2 = red, 3 = orange, 4 = off )."
			::= { neStates 16  }

		neStatesDeviceLedFault OBJECT-TYPE
			SYNTAX INTEGER (1..4)
			ACCESS read-only
			STATUS mandatory
			DESCRIPTION
				"LED Fault ( 1 = green, 2 = red, 3 = orange, 4 = off )."
			::= { neStates 17  }

		neLicenseTable OBJECT-TYPE
			SYNTAX SEQUENCE OF NeLicenseEntry
			ACCESS not-accessible
			STATUS mandatory
			DESCRIPTION
				"License."
			::= { neStates 40 }

		neLicenseEntry OBJECT-TYPE
			SYNTAX NeLicenseEntry
			ACCESS not-accessible
			STATUS mandatory
			DESCRIPTION
				"Logbook."
			INDEX { neLicenseIndex }
			::= { neLicenseTable 1 }

		NeLicenseEntry ::=
			SEQUENCE { 
				neLicenseIndex
					INTEGER,
				neLicenseDescription
					DisplayString,
				neLicenseStatus
					INTEGER
			 }

		neLicenseIndex OBJECT-TYPE
			SYNTAX INTEGER (1..256)
			ACCESS read-only
			STATUS mandatory
			DESCRIPTION
				"Index Position."
			::= { neLicenseEntry 1 }

		neLicenseDescription OBJECT-TYPE
			SYNTAX DisplayString (SIZE (0..64))
			ACCESS read-only
			STATUS mandatory
			DESCRIPTION
				"License: Description"
			::= { neLicenseEntry 2 }

		neLicenseStatus OBJECT-TYPE
			SYNTAX INTEGER (1..2)
			ACCESS read-only
			STATUS mandatory
			DESCRIPTION
				"License: disabled(1), enabled(2)"
			::= { neLicenseEntry 3 }

		neMessageTable OBJECT-TYPE
			SYNTAX SEQUENCE OF NeMessageEntry
			ACCESS not-accessible
			STATUS mandatory
			DESCRIPTION
				"License."
			::= { neStates 45 }

		neMessageEntry OBJECT-TYPE
			SYNTAX NeMessageEntry
			ACCESS not-accessible
			STATUS mandatory
			DESCRIPTION
				"Message."
			INDEX { neMessageIndex }
			::= { neMessageTable 1 }

		NeMessageEntry ::=
			SEQUENCE { 
				neMessageIndex
					INTEGER,
				neMessageSeverity
					INTEGER
			 }

		neMessageIndex OBJECT-TYPE
			SYNTAX INTEGER (1..256)
			ACCESS read-only
			STATUS mandatory
			DESCRIPTION
				"Index Position:
				
				 1  => INPUT
				 2  => STATUS
				 3  => FAULT
				"
			::= { neMessageEntry 1 }

		neMessageSeverity OBJECT-TYPE
			SYNTAX INTEGER (1..2)
			ACCESS read-only
			STATUS mandatory
			DESCRIPTION
				"Message Severity: Cleared(1), Alarm(2)"
			::= { neMessageEntry 2 }

		neLogbookTable OBJECT-TYPE
			SYNTAX SEQUENCE OF NeLogbookEntry
			ACCESS not-accessible
			STATUS mandatory
			DESCRIPTION
				"Logbook."
			::= { neStates 50 }

		neLogbookEntry OBJECT-TYPE
			SYNTAX NeLogbookEntry
			ACCESS not-accessible
			STATUS mandatory
			DESCRIPTION
				"Logbook."
			INDEX { neLogbookIndex }
			::= { neLogbookTable 1 }

		NeLogbookEntry ::=
			SEQUENCE { 
				neLogbookIndex
					INTEGER,
				neLogbookStatus
					DisplayString
			 }

		neLogbookIndex OBJECT-TYPE
			SYNTAX INTEGER (1..512)
			ACCESS read-only
			STATUS mandatory
			DESCRIPTION
				"Index Position."
			::= { neLogbookEntry 1 }

		neLogbookStatus OBJECT-TYPE
			SYNTAX DisplayString (SIZE (0..64))
			ACCESS read-only
			STATUS mandatory
			DESCRIPTION
				"Logbook: datum time event"
			::= { neLogbookEntry 2 }

		neTs1InputSource OBJECT-TYPE
			SYNTAX INTEGER (0..256)
			ACCESS read-write
			STATUS mandatory
			DESCRIPTION
				"Input Source: (see neTS1InputSourceIndex n)"
			::= { ts1 1 }

		neTs1InputSourceTable OBJECT-TYPE
			SYNTAX SEQUENCE OF NeTs1InputSourceEntry
			ACCESS not-accessible
			STATUS mandatory
			DESCRIPTION
				"TS1 Input Source Table."
			::= { ts1 2 }

		neTs1InputSourceEntry OBJECT-TYPE
			SYNTAX NeTs1InputSourceEntry
			ACCESS not-accessible
			STATUS mandatory
			DESCRIPTION
				"TS1 Input Source Table."
			INDEX { neTs1InputSourceIndex }
			::= { neTs1InputSourceTable 1 }

		NeTs1InputSourceEntry ::=
			SEQUENCE { 
				neTs1InputSourceIndex
					INTEGER,
				neTs1InputSourceName
					DisplayString
			 }

		neTs1InputSourceIndex OBJECT-TYPE
			SYNTAX INTEGER (0..255)
			ACCESS read-only
			STATUS mandatory
			DESCRIPTION
				"Index Position."
			::= { neTs1InputSourceEntry 1 }

		neTs1InputSourceName OBJECT-TYPE
			SYNTAX DisplayString (SIZE (0..63))
			ACCESS read-only
			STATUS mandatory
			DESCRIPTION
				"TS1 Input Source Name"
			::= { neTs1InputSourceEntry 2 }

		neTs1Status OBJECT-TYPE
			SYNTAX DisplayString (SIZE (0..32))
			ACCESS read-only
			STATUS mandatory
			DESCRIPTION
				"Status (LOCKED/UNLOCKED)"
			::= { ts1 20 }

 		neTs1TsidOnid OBJECT-TYPE
			SYNTAX DisplayString (SIZE (0..32))
			ACCESS read-only
			STATUS mandatory
			DESCRIPTION
				"TSID / ONID"
			::= { ts1 21 }

 		neTs1InputRate OBJECT-TYPE
			SYNTAX DisplayString (SIZE (0..32))
			ACCESS read-only
			STATUS mandatory
			DESCRIPTION
				"Input Rate (Payload)"
			::= { ts1 22 }

		neTs1TSServiceTable OBJECT-TYPE
			SYNTAX SEQUENCE OF NeTs1TSServiceEntry
			ACCESS not-accessible
			STATUS mandatory
			DESCRIPTION
				"TS Service Table."
			::= { ts1 50 }

		neTs1TSServiceEntry OBJECT-TYPE
			SYNTAX NeTs1TSServiceEntry
			ACCESS not-accessible
			STATUS mandatory
			DESCRIPTION
				"TS Service Table."
			INDEX { neTs1TSServiceIndex }
			::= { neTs1TSServiceTable 1 }

		NeTs1TSServiceEntry ::=
			SEQUENCE { 
				neTs1TSServiceIndex
					INTEGER,
				neTs1TSServiceServiceID
					DisplayString,
				neTs1TSServiceServiceType
					DisplayString,
				neTs1TSServiceMode
					DisplayString,
				neTs1TSServiceServiceName
					DisplayString
			 }

		neTs1TSServiceIndex OBJECT-TYPE
			SYNTAX INTEGER (1..256)
			ACCESS read-only
			STATUS mandatory
			DESCRIPTION
				"Index Position."
			::= { neTs1TSServiceEntry 1 }

		neTs1TSServiceServiceID OBJECT-TYPE
			SYNTAX DisplayString (SIZE (0..32))
			ACCESS read-only
			STATUS mandatory
			DESCRIPTION
				"TS Service ID"
			::= { neTs1TSServiceEntry 2 }

		neTs1TSServiceServiceType OBJECT-TYPE
			SYNTAX DisplayString (SIZE (0..32))
			ACCESS read-only
			STATUS mandatory
			DESCRIPTION
				"TS Service Type"
			::= { neTs1TSServiceEntry 3 }

		neTs1TSServiceMode OBJECT-TYPE
			SYNTAX DisplayString (SIZE (0..32))
			ACCESS read-only
			STATUS mandatory
			DESCRIPTION
				"TS Service Mode"
			::= { neTs1TSServiceEntry 4 }

		neTs1TSServiceServiceName OBJECT-TYPE
			SYNTAX DisplayString (SIZE (0..32))
			ACCESS read-only
			STATUS mandatory
			DESCRIPTION
				"TS Service Name"
			::= { neTs1TSServiceEntry 5 }

		neTs2InputSource OBJECT-TYPE
			SYNTAX INTEGER (0..256)
			ACCESS read-write
			STATUS mandatory
			DESCRIPTION
				"Input Source: (see neTS2InputSourceIndex n)"
			::= { ts2 1 }

		neTs2InputSourceTable OBJECT-TYPE
			SYNTAX SEQUENCE OF NeTs2InputSourceEntry
			ACCESS not-accessible
			STATUS mandatory
			DESCRIPTION
				"TS2 Input Source Table."
			::= { ts2 2 }

		neTs2InputSourceEntry OBJECT-TYPE
			SYNTAX NeTs2InputSourceEntry
			ACCESS not-accessible
			STATUS mandatory
			DESCRIPTION
				"TS2 Input Source Table."
			INDEX { neTs2InputSourceIndex }
			::= { neTs2InputSourceTable 1 }

		NeTs2InputSourceEntry ::=
			SEQUENCE { 
				neTs2InputSourceIndex
					INTEGER,
				neTs2InputSourceName
					DisplayString
			 }

		neTs2InputSourceIndex OBJECT-TYPE
			SYNTAX INTEGER (0..255)
			ACCESS read-only
			STATUS mandatory
			DESCRIPTION
				"Index Position."
			::= { neTs2InputSourceEntry 1 }

		neTs2InputSourceName OBJECT-TYPE
			SYNTAX DisplayString (SIZE (0..63))
			ACCESS read-only
			STATUS mandatory
			DESCRIPTION
				"TS2 Input Source Name"
			::= { neTs2InputSourceEntry 2 }

		neTs2Status OBJECT-TYPE
			SYNTAX DisplayString (SIZE (0..32))
			ACCESS read-only
			STATUS mandatory
			DESCRIPTION
				"Status (LOCKED/UNLOCKED)"
			::= { ts2 20 }

 		neTs2TsidOnid OBJECT-TYPE
			SYNTAX DisplayString (SIZE (0..32))
			ACCESS read-only
			STATUS mandatory
			DESCRIPTION
				"TSID / ONID"
			::= { ts2 21 }

 		neTs2InputRate OBJECT-TYPE
			SYNTAX DisplayString (SIZE (0..32))
			ACCESS read-only
			STATUS mandatory
			DESCRIPTION
				"Input Rate (Payload)"
			::= { ts2 22 }

		neTs2TSServiceTable OBJECT-TYPE
			SYNTAX SEQUENCE OF NeTs2TSServiceEntry
			ACCESS not-accessible
			STATUS mandatory
			DESCRIPTION
				"TS Service Table."
			::= { ts2 50 }

		neTs2TSServiceEntry OBJECT-TYPE
			SYNTAX NeTs2TSServiceEntry
			ACCESS not-accessible
			STATUS mandatory
			DESCRIPTION
				"TS Service Table."
			INDEX { neTs2TSServiceIndex }
			::= { neTs2TSServiceTable 1 }

		NeTs2TSServiceEntry ::=
			SEQUENCE { 
				neTs2TSServiceIndex
					INTEGER,
				neTs2TSServiceServiceID
					DisplayString,
				neTs2TSServiceServiceType
					DisplayString,
				neTs2TSServiceMode
					DisplayString,
				neTs2TSServiceServiceName
					DisplayString
			 }

		neTs2TSServiceIndex OBJECT-TYPE
			SYNTAX INTEGER (1..256)
			ACCESS read-only
			STATUS mandatory
			DESCRIPTION
				"Index Position."
			::= { neTs2TSServiceEntry 1 }

		neTs2TSServiceServiceID OBJECT-TYPE
			SYNTAX DisplayString (SIZE (0..32))
			ACCESS read-only
			STATUS mandatory
			DESCRIPTION
				"TS Service ID"
			::= { neTs2TSServiceEntry 2 }

		neTs2TSServiceServiceType OBJECT-TYPE
			SYNTAX DisplayString (SIZE (0..32))
			ACCESS read-only
			STATUS mandatory
			DESCRIPTION
				"TS Service Type"
			::= { neTs2TSServiceEntry 3 }

		neTs2TSServiceMode OBJECT-TYPE
			SYNTAX DisplayString (SIZE (0..32))
			ACCESS read-only
			STATUS mandatory
			DESCRIPTION
				"TS Service Mode"
			::= { neTs2TSServiceEntry 4 }

		neTs2TSServiceServiceName OBJECT-TYPE
			SYNTAX DisplayString (SIZE (0..32))
			ACCESS read-only
			STATUS mandatory
			DESCRIPTION
				"TS Service Name"
			::= { neTs2TSServiceEntry 5 }

		neTs3InputSource OBJECT-TYPE
			SYNTAX INTEGER (0..256)
			ACCESS read-write
			STATUS mandatory
			DESCRIPTION
				"Input Source: (see neTS2InputSourceIndex n)"
			::= { ts3 1 }

		neTs3InputSourceTable OBJECT-TYPE
			SYNTAX SEQUENCE OF NeTs3InputSourceEntry
			ACCESS not-accessible
			STATUS mandatory
			DESCRIPTION
				"TS3 Input Source Table."
			::= { ts3 2 }

		neTs3InputSourceEntry OBJECT-TYPE
			SYNTAX NeTs3InputSourceEntry
			ACCESS not-accessible
			STATUS mandatory
			DESCRIPTION
				"TS3 Input Source Table."
			INDEX { neTs3InputSourceIndex }
			::= { neTs3InputSourceTable 1 }

		NeTs3InputSourceEntry ::=
			SEQUENCE { 
				neTs3InputSourceIndex
					INTEGER,
				neTs3InputSourceName
					DisplayString
			 }

		neTs3InputSourceIndex OBJECT-TYPE
			SYNTAX INTEGER (0..255)
			ACCESS read-only
			STATUS mandatory
			DESCRIPTION
				"Index Position."
			::= { neTs3InputSourceEntry 1 }

		neTs3InputSourceName OBJECT-TYPE
			SYNTAX DisplayString (SIZE (0..63))
			ACCESS read-only
			STATUS mandatory
			DESCRIPTION
				"TS3 Input Source Name"
			::= { neTs3InputSourceEntry 2 }

		neTs3Status OBJECT-TYPE
			SYNTAX DisplayString (SIZE (0..32))
			ACCESS read-only
			STATUS mandatory
			DESCRIPTION
				"Status (LOCKED/UNLOCKED)"
			::= { ts3 20 }

 		neTs3TsidOnid OBJECT-TYPE
			SYNTAX DisplayString (SIZE (0..32))
			ACCESS read-only
			STATUS mandatory
			DESCRIPTION
				"TSID / ONID"
			::= { ts3 21 }

 		neTs3InputRate OBJECT-TYPE
			SYNTAX DisplayString (SIZE (0..32))
			ACCESS read-only
			STATUS mandatory
			DESCRIPTION
				"Input Rate (Payload)"
			::= { ts3 22 }

		neTs3TSServiceTable OBJECT-TYPE
			SYNTAX SEQUENCE OF NeTs3TSServiceEntry
			ACCESS not-accessible
			STATUS mandatory
			DESCRIPTION
				"TS Service Table."
			::= { ts3 50 }

		neTs3TSServiceEntry OBJECT-TYPE
			SYNTAX NeTs3TSServiceEntry
			ACCESS not-accessible
			STATUS mandatory
			DESCRIPTION
				"TS Service Table."
			INDEX { neTs3TSServiceIndex }
			::= { neTs3TSServiceTable 1 }

		NeTs3TSServiceEntry ::=
			SEQUENCE { 
				neTs3TSServiceIndex
					INTEGER,
				neTs3TSServiceServiceID
					DisplayString,
				neTs3TSServiceServiceType
					DisplayString,
				neTs3TSServiceMode
					DisplayString,
				neTs3TSServiceServiceName
					DisplayString
			 }

		neTs3TSServiceIndex OBJECT-TYPE
			SYNTAX INTEGER (1..256)
			ACCESS read-only
			STATUS mandatory
			DESCRIPTION
				"Index Position."
			::= { neTs3TSServiceEntry 1 }

		neTs3TSServiceServiceID OBJECT-TYPE
			SYNTAX DisplayString (SIZE (0..32))
			ACCESS read-only
			STATUS mandatory
			DESCRIPTION
				"TS Service ID"
			::= { neTs3TSServiceEntry 2 }

		neTs3TSServiceServiceType OBJECT-TYPE
			SYNTAX DisplayString (SIZE (0..32))
			ACCESS read-only
			STATUS mandatory
			DESCRIPTION
				"TS Service Type"
			::= { neTs3TSServiceEntry 3 }

		neTs3TSServiceMode OBJECT-TYPE
			SYNTAX DisplayString (SIZE (0..32))
			ACCESS read-only
			STATUS mandatory
			DESCRIPTION
				"TS Service Mode"
			::= { neTs3TSServiceEntry 4 }

		neTs3TSServiceServiceName OBJECT-TYPE
			SYNTAX DisplayString (SIZE (0..32))
			ACCESS read-only
			STATUS mandatory
			DESCRIPTION
				"TS Service Name"
			::= { neTs3TSServiceEntry 5 }

		neTs4InputSource OBJECT-TYPE
			SYNTAX INTEGER (0..256)
			ACCESS read-write
			STATUS mandatory
			DESCRIPTION
				"Input Source: (see neTS4InputSourceIndex n)"
			::= { ts4 1 }

		neTs4InputSourceTable OBJECT-TYPE
			SYNTAX SEQUENCE OF NeTs4InputSourceEntry
			ACCESS not-accessible
			STATUS mandatory
			DESCRIPTION
				"TS4 Input Source Table."
			::= { ts4 2 }

		neTs4InputSourceEntry OBJECT-TYPE
			SYNTAX NeTs4InputSourceEntry
			ACCESS not-accessible
			STATUS mandatory
			DESCRIPTION
				"TS4 Input Source Table."
			INDEX { neTs4InputSourceIndex }
			::= { neTs4InputSourceTable 1 }

		NeTs4InputSourceEntry ::=
			SEQUENCE { 
				neTs4InputSourceIndex
					INTEGER,
				neTs4InputSourceName
					DisplayString
			 }

		neTs4InputSourceIndex OBJECT-TYPE
			SYNTAX INTEGER (0..255)
			ACCESS read-only
			STATUS mandatory
			DESCRIPTION
				"Index Position."
			::= { neTs4InputSourceEntry 1 }

		neTs4InputSourceName OBJECT-TYPE
			SYNTAX DisplayString (SIZE (0..63))
			ACCESS read-only
			STATUS mandatory
			DESCRIPTION
				"TS4 Input Source Name"
			::= { neTs4InputSourceEntry 2 }

		neTs4Status OBJECT-TYPE
			SYNTAX DisplayString (SIZE (0..32))
			ACCESS read-only
			STATUS mandatory
			DESCRIPTION
				"Status (LOCKED/UNLOCKED)"
			::= { ts4 20 }

 		neTs4TsidOnid OBJECT-TYPE
			SYNTAX DisplayString (SIZE (0..32))
			ACCESS read-only
			STATUS mandatory
			DESCRIPTION
				"TSID / ONID"
			::= { ts4 21 }

 		neTs4InputRate OBJECT-TYPE
			SYNTAX DisplayString (SIZE (0..32))
			ACCESS read-only
			STATUS mandatory
			DESCRIPTION
				"Input Rate (Payload)"
			::= { ts4 22 }

		neTs4TSServiceTable OBJECT-TYPE
			SYNTAX SEQUENCE OF NeTs4TSServiceEntry
			ACCESS not-accessible
			STATUS mandatory
			DESCRIPTION
				"TS Service Table."
			::= { ts4 50 }

		neTs4TSServiceEntry OBJECT-TYPE
			SYNTAX NeTs4TSServiceEntry
			ACCESS not-accessible
			STATUS mandatory
			DESCRIPTION
				"TS Service Table."
			INDEX { neTs4TSServiceIndex }
			::= { neTs4TSServiceTable 1 }

		NeTs4TSServiceEntry ::=
			SEQUENCE { 
				neTs4TSServiceIndex
					INTEGER,
				neTs4TSServiceServiceID
					DisplayString,
				neTs4TSServiceServiceType
					DisplayString,
				neTs4TSServiceMode
					DisplayString,
				neTs4TSServiceServiceName
					DisplayString
			 }

		neTs4TSServiceIndex OBJECT-TYPE
			SYNTAX INTEGER (1..256)
			ACCESS read-only
			STATUS mandatory
			DESCRIPTION
				"Index Position."
			::= { neTs4TSServiceEntry 1 }

		neTs4TSServiceServiceID OBJECT-TYPE
			SYNTAX DisplayString (SIZE (0..32))
			ACCESS read-only
			STATUS mandatory
			DESCRIPTION
				"TS Service ID"
			::= { neTs4TSServiceEntry 2 }

		neTs4TSServiceServiceType OBJECT-TYPE
			SYNTAX DisplayString (SIZE (0..32))
			ACCESS read-only
			STATUS mandatory
			DESCRIPTION
				"TS Service Type"
			::= { neTs4TSServiceEntry 3 }

		neTs4TSServiceMode OBJECT-TYPE
			SYNTAX DisplayString (SIZE (0..32))
			ACCESS read-only
			STATUS mandatory
			DESCRIPTION
				"TS Service Mode"
			::= { neTs4TSServiceEntry 4 }

		neTs4TSServiceServiceName OBJECT-TYPE
			SYNTAX DisplayString (SIZE (0..32))
			ACCESS read-only
			STATUS mandatory
			DESCRIPTION
				"TS Service Name"
			::= { neTs4TSServiceEntry 5 }

		neDvbSTable OBJECT-TYPE
			SYNTAX SEQUENCE OF NeDvbSEntry
			ACCESS not-accessible
			STATUS mandatory
			DESCRIPTION
				"DVB Table."
			::= { dvb_s_s2 1 }

		neDvbSEntry OBJECT-TYPE
			SYNTAX NeDvbSEntry
			ACCESS not-accessible
			STATUS mandatory
			DESCRIPTION
				"DVB-S Table."
			INDEX { neDvbSIndex }
			::= { neDvbSTable 1 }

		NeDvbSEntry ::=
			SEQUENCE { 
				neDvbSIndex
					INTEGER,
				neDvbSFrequencyMode
					INTEGER,
				neDvbSSatFrequency
					INTEGER,
				neDvbSLnbFrequency
					INTEGER,
				neDvbSIfFrequency
					INTEGER,
				neDvbSSymbolRate
					INTEGER,
				neDvbSMode
					INTEGER,
				neDvbSLnbVoltage
					INTEGER,
				neDvbSLnb22khzTone
					INTEGER,
				neDvbSScpcMode
					INTEGER,
				neDvbSScpcTsid
					INTEGER,
				neDvbSMisIsi
					INTEGER,
				neDvbSApskMode
					INTEGER,
				neDvbSPlDescambling
					INTEGER,
				neDvbSGoldCode
					INTEGER,
				neDvbSBer
					DisplayString,
				neDvbSStandard
					DisplayString,
				neDvbSSatIfLevel
					DisplayString,
				neDvbSCoderateModcode
					DisplayString,
				neDvbSCtoN
					DisplayString,
				neDvbSSatIf
					DisplayString,
				neDvbSDiseqcMode
					INTEGER,
			 }

		neDvbSIndex OBJECT-TYPE
			SYNTAX INTEGER (0..255)
			ACCESS read-only
			STATUS mandatory
			DESCRIPTION
				"Index Position."
			::= { neDvbSEntry 1 }

 		neDvbSFrequencyMode OBJECT-TYPE
			SYNTAX INTEGER
			ACCESS read-write
			STATUS mandatory
			DESCRIPTION
				"Frequency Mode: SAT FREQUENCY(0), IF FREQUENCY(1)"
			::= { neDvbSEntry 2 }

 		neDvbSSatFrequency OBJECT-TYPE
			SYNTAX INTEGER
			ACCESS read-write
			STATUS mandatory
			DESCRIPTION
				"SAT Frequency: kHz"
			::= { neDvbSEntry 3 }

 		neDvbSLnbFrequency OBJECT-TYPE
			SYNTAX INTEGER
			ACCESS read-write
			STATUS mandatory
			DESCRIPTION
				"LNB Frequency: kHz"
			::= { neDvbSEntry 4 }

 		neDvbSIfFrequency OBJECT-TYPE
			SYNTAX INTEGER
			ACCESS read-write
			STATUS mandatory
			DESCRIPTION
				"IF Frequency: kHz"
			::= { neDvbSEntry 5 }

 		neDvbSSymbolRate OBJECT-TYPE
			SYNTAX INTEGER
			ACCESS read-write
			STATUS mandatory
			DESCRIPTION
				"Symbol Rate: Sps"
			::= { neDvbSEntry 6 }

 		neDvbSMode OBJECT-TYPE
			SYNTAX INTEGER (0..2)
			ACCESS read-write
			STATUS mandatory
			DESCRIPTION
				"DVB-s Mode: DVB-S/S2(0), DVB-S(1), DVB-S2(2)"
			::= { neDvbSEntry 7 }

 		neDvbSLnbVoltage OBJECT-TYPE
			SYNTAX INTEGER (0..2)
			ACCESS read-write
			STATUS mandatory
			DESCRIPTION
				"LNB Voltage: off(0), 13V(1), 18V(2)"
			::= { neDvbSEntry 8 }

 		neDvbSLnb22khzTone OBJECT-TYPE
			SYNTAX INTEGER (0..1)
			ACCESS read-write
			STATUS mandatory
			DESCRIPTION
				"LNB 22 kHz Tone: off(0), on(1)"
			::= { neDvbSEntry 9 }

 		neDvbSScpcMode OBJECT-TYPE
			SYNTAX INTEGER (0..1)
			ACCESS read-write
			STATUS mandatory
			DESCRIPTION
				"SCPC Mode: off(0), on(1)"
			::= { neDvbSEntry 10 }

 		neDvbSScpcTsid OBJECT-TYPE
			SYNTAX INTEGER (0..65535)
			ACCESS read-write
			STATUS mandatory
			DESCRIPTION
				"SCPC TSID:"
			::= { neDvbSEntry 11 }

 		neDvbSMisIsi OBJECT-TYPE
			SYNTAX INTEGER (0..255)
			ACCESS read-write
			STATUS mandatory
			DESCRIPTION
				"MIS ISI:"
			::= { neDvbSEntry 12 }

 		neDvbSApskMode OBJECT-TYPE
			SYNTAX INTEGER (0..1)
			ACCESS read-write
			STATUS mandatory
			DESCRIPTION
				"APSK Mode: off(0), on(1)"
			::= { neDvbSEntry 13 }

 		neDvbSPlDescambling OBJECT-TYPE
			SYNTAX INTEGER (0..1)
			ACCESS read-write
			STATUS mandatory
			DESCRIPTION
				"PL Descrambling: off(0), on(1)"
			::= { neDvbSEntry 14 }

 		neDvbSGoldCode OBJECT-TYPE
			SYNTAX INTEGER (0..262141)
			ACCESS read-write
			STATUS mandatory
			DESCRIPTION
				"Gold Code:"
			::= { neDvbSEntry 15 }

 		neDvbSBer OBJECT-TYPE
			SYNTAX DisplayString (SIZE (0..32))
			ACCESS read-only
			STATUS mandatory
			DESCRIPTION
				"BER"
			::= { neDvbSEntry 16 }

 		neDvbSStandard OBJECT-TYPE
			SYNTAX DisplayString (SIZE (0..32))
			ACCESS read-only
			STATUS mandatory
			DESCRIPTION
				"Standard"
			::= { neDvbSEntry 17 }

 		neDvbSSatIfLevel OBJECT-TYPE
			SYNTAX DisplayString (SIZE (0..32))
			ACCESS read-only
			STATUS mandatory
			DESCRIPTION
				"SAT-IF-Level"
			::= { neDvbSEntry 18 }

 		neDvbSCoderateModcode OBJECT-TYPE
			SYNTAX DisplayString (SIZE (0..32))
			ACCESS read-only
			STATUS mandatory
			DESCRIPTION
				"Coderate_Modcode"
			::= { neDvbSEntry 19 }

 		neDvbSCtoN OBJECT-TYPE
			SYNTAX DisplayString (SIZE (0..32))
			ACCESS read-only
			STATUS mandatory
			DESCRIPTION
				"C/N"
			::= { neDvbSEntry 20 }

 		neDvbSSatIf OBJECT-TYPE
			SYNTAX DisplayString (SIZE (0..32))
			ACCESS read-only
			STATUS mandatory
			DESCRIPTION
				"SAT-IF"
			::= { neDvbSEntry 21 }

		neDvbSDiseqcMode OBJECT-TYPE
			SYNTAX INTEGER (0..16)
			ACCESS read-write
			STATUS mandatory
			DESCRIPTION
				"DiSEqC Mode:
				OFF(0)
				LNB A - Vertical - Lowband(1)
				LNB A - Vertical - Highband(2)
				LNB A - Horizontal - Lowband(3)
				LNB A - Horizontal - Highband(4)
				LNB B - Vertical - Lowband(5)
				LNB B - Vertical - Highband(6)
				LNB B - Horizontal - Lowband(7)
				LNB B - Horizontal - Highband(8)
				LNB C - Vertical - Lowband(9)
				LNB C - Vertical - Highband(10)
				LNB C - Horizontal - Lowband(11)
				LNB C - Horizontal - Highband(12)
				LNB D - Vertical - Lowband(13)
				LNB D - Vertical - Highband(14)
				LNB D - Horizontal - Lowband(15)
				LNB D - Horizontal - Highband(16)"
			::= { neDvbSEntry 22 }

		neDvbTTable OBJECT-TYPE
			SYNTAX SEQUENCE OF NeDvbTEntry
			ACCESS not-accessible
			STATUS mandatory
			DESCRIPTION
				"DVB Table."
			::= { dvb_t_t2 1 }

		neDvbTEntry OBJECT-TYPE
			SYNTAX NeDvbTEntry
			ACCESS not-accessible
			STATUS mandatory
			DESCRIPTION
				"DVB-T Table."
			INDEX { neDvbTIndex }
			::= { neDvbTTable 1 }

		NeDvbTEntry ::=
			SEQUENCE { 
				neDvbTIndex
					INTEGER,
				neDvbTInputMode
					INTEGER,
				neDvbTFrequency
					INTEGER,
				neDvbTBandwidth
					INTEGER,
				neDvbTStandard
					DisplayString,
				neDvbTLevel
					DisplayString,
				neDvbTSnr
					DisplayString,
				neDvbTBer
					DisplayString,
				neDvbTConstellation
					DisplayString,
				neDvbTConstellationRotation
					DisplayString,
				neDvbTGuardInterval
					DisplayString,
				neDvbTFft
					DisplayString,
				neDvbTCodeRate
					DisplayString,
				neDvbTCellId
					DisplayString,
				neDvbTNetworkId
					DisplayString,
				neDvbTT2SystemId
					DisplayString,
				neDvbTPilotPattern
					DisplayString,
				neDvbTL1PostPlpFecType
					DisplayString
			 }

		neDvbTIndex OBJECT-TYPE
			SYNTAX INTEGER (0..255)
			ACCESS read-only
			STATUS mandatory
			DESCRIPTION
				"Index Position."
			::= { neDvbTEntry 1 }

		neDvbTInputMode OBJECT-TYPE
			SYNTAX INTEGER (0..2)
			ACCESS read-write
			STATUS mandatory
			DESCRIPTION
				"Input Mode: 
				 DVB-T(0), DVB-C(1)
				 or 
				 DVB-T/T2(0), DVB-T(1), DVB-T2(2)"
			::= { neDvbTEntry 2 }

 		neDvbTFrequency OBJECT-TYPE
			SYNTAX INTEGER
			ACCESS read-write
			STATUS mandatory
			DESCRIPTION
				"DVB-T Frequency: kHz"
			::= { neDvbTEntry 3 }

 		neDvbTBandwidth OBJECT-TYPE
			SYNTAX INTEGER (0..2)
			ACCESS read-write
			STATUS mandatory
			DESCRIPTION
				"Bandwidth: 6 MHz(0), 7 MHz(1), 8 MHz(2)"
			::= { neDvbTEntry 4 }

 		neDvbTStandard OBJECT-TYPE
			SYNTAX DisplayString (SIZE (0..32))
			ACCESS read-only
			STATUS mandatory
			DESCRIPTION
				"Standard: DVB-T or DVB-T2"
			::= { neDvbTEntry 5 }

 		neDvbTLevel OBJECT-TYPE
			SYNTAX DisplayString (SIZE (0..32))
			ACCESS read-only
			STATUS mandatory
			DESCRIPTION
				"Level"
			::= { neDvbTEntry 6 }

 		neDvbTSnr OBJECT-TYPE
			SYNTAX DisplayString (SIZE (0..32))
			ACCESS read-only
			STATUS mandatory
			DESCRIPTION
				"Signal/Noise Ratio"
			::= { neDvbTEntry 7 }

 		neDvbTBer OBJECT-TYPE
			SYNTAX DisplayString (SIZE (0..32))
			ACCESS read-only
			STATUS mandatory
			DESCRIPTION
				"BER"
			::= { neDvbTEntry 8 }

 		neDvbTConstellation OBJECT-TYPE
			SYNTAX DisplayString (SIZE (0..32))
			ACCESS read-only
			STATUS mandatory
			DESCRIPTION
				"Constellation"
			::= { neDvbTEntry 9 }

 		neDvbTConstellationRotation OBJECT-TYPE
			SYNTAX DisplayString (SIZE (0..32))
			ACCESS read-only
			STATUS mandatory
			DESCRIPTION
				"Constellation Rotation"
			::= { neDvbTEntry 10 }

 		neDvbTGuardInterval OBJECT-TYPE
			SYNTAX DisplayString (SIZE (0..32))
			ACCESS read-only
			STATUS mandatory
			DESCRIPTION
				"Guard Interval"
			::= { neDvbTEntry 11 }

 		neDvbTFft OBJECT-TYPE
			SYNTAX DisplayString (SIZE (0..32))
			ACCESS read-only
			STATUS mandatory
			DESCRIPTION
				"FFT"
			::= { neDvbTEntry 12 }

 		neDvbTCodeRate OBJECT-TYPE
			SYNTAX DisplayString (SIZE (0..32))
			ACCESS read-only
			STATUS mandatory
			DESCRIPTION
				"Code Rate"
			::= { neDvbTEntry 13 }

 		neDvbTCellId OBJECT-TYPE
			SYNTAX DisplayString (SIZE (0..32))
			ACCESS read-only
			STATUS mandatory
			DESCRIPTION
				"Cell ID"
			::= { neDvbTEntry 14 }

 		neDvbTNetworkId OBJECT-TYPE
			SYNTAX DisplayString (SIZE (0..32))
			ACCESS read-only
			STATUS mandatory
			DESCRIPTION
				"Network ID"
			::= { neDvbTEntry 15 }

 		neDvbTT2SystemId OBJECT-TYPE
			SYNTAX DisplayString (SIZE (0..32))
			ACCESS read-only
			STATUS mandatory
			DESCRIPTION
				"T2 System ID"
			::= { neDvbTEntry 16 }

 		neDvbTPilotPattern OBJECT-TYPE
			SYNTAX DisplayString (SIZE (0..32))
			ACCESS read-only
			STATUS mandatory
			DESCRIPTION
				"Pilot Pattern"
			::= { neDvbTEntry 17 }

 		neDvbTL1PostPlpFecType OBJECT-TYPE
			SYNTAX DisplayString (SIZE (0..32))
			ACCESS read-only
			STATUS mandatory
			DESCRIPTION
				"L1 POST PLP FEC Type"
			::= { neDvbTEntry 18 }

		neDvbCTable OBJECT-TYPE
			SYNTAX SEQUENCE OF NeDvbCEntry
			ACCESS not-accessible
			STATUS mandatory
			DESCRIPTION
				"DVB Table."
			::= { dvb_c_c2 1 }

		neDvbCEntry OBJECT-TYPE
			SYNTAX NeDvbCEntry
			ACCESS not-accessible
			STATUS mandatory
			DESCRIPTION
				"DVB-C Table."
			INDEX { neDvbCIndex }
			::= { neDvbCTable 1 }

		NeDvbCEntry ::=
			SEQUENCE { 
				neDvbCIndex
					INTEGER,
				neDvbCInputMode
					INTEGER,
				neDvbCFrequency
					INTEGER,
				neDvbCSymbolRate
					INTEGER,
				neDvbCQamMode
					INTEGER,
				neDvbCLevel
					DisplayString,
				neDvbCSnr
					DisplayString,
				neDvbCBer
					DisplayString
			 }

		neDvbCIndex OBJECT-TYPE
			SYNTAX INTEGER (0..255)
			ACCESS read-only
			STATUS mandatory
			DESCRIPTION
				"Index Position."
			::= { neDvbCEntry 1 }

		neDvbCInputMode OBJECT-TYPE
			SYNTAX INTEGER (0..1)
			ACCESS read-write
			STATUS mandatory
			DESCRIPTION
				"Input Mode: DVB-T(0), DVB-C(1)"
			::= { neDvbCEntry 2 }

 		neDvbCFrequency OBJECT-TYPE
			SYNTAX INTEGER
			ACCESS read-write
			STATUS mandatory
			DESCRIPTION
				"DVB-C Frequency: kHz"
			::= { neDvbCEntry 3 }

 		neDvbCSymbolRate OBJECT-TYPE
			SYNTAX INTEGER
			ACCESS read-write
			STATUS mandatory
			DESCRIPTION
				"DVB-C Symbol Rate: Sps"
			::= { neDvbCEntry 4 }

 		neDvbCQamMode OBJECT-TYPE
			SYNTAX INTEGER (0..4)
			ACCESS read-write
			STATUS mandatory
			DESCRIPTION
				"DVB-C QAM Mode:  16 QAM(0), 
				                  32 QAM(1), 
				                  64 QAM(2),
				                 128 QAM(3), 
				                 256 QAM(4)"
			::= { neDvbCEntry 5 }

 		neDvbCLevel OBJECT-TYPE
			SYNTAX DisplayString (SIZE (0..32))
			ACCESS read-only
			STATUS mandatory
			DESCRIPTION
				"Level"
			::= { neDvbCEntry 6 }

 		neDvbCSnr OBJECT-TYPE
			SYNTAX DisplayString (SIZE (0..32))
			ACCESS read-only
			STATUS mandatory
			DESCRIPTION
				"SNR"
			::= { neDvbCEntry 7 }

 		neDvbCBer OBJECT-TYPE
			SYNTAX DisplayString (SIZE (0..32))
			ACCESS read-only
			STATUS mandatory
			DESCRIPTION
				"BER"
			::= { neDvbCEntry 8 }

		neIPOutputMPTSTable OBJECT-TYPE
			SYNTAX SEQUENCE OF NeIPOutputMPTSEntry
			ACCESS not-accessible
			STATUS mandatory
			DESCRIPTION
				"IP Output MPTS Table."
			::= { mpts 1 }

		neIPOutputMPTSEntry OBJECT-TYPE
			SYNTAX NeIPOutputMPTSEntry
			ACCESS not-accessible
			STATUS mandatory
			DESCRIPTION
				"IP Output MPTS Table."
			INDEX { neIPOutputMPTSIndex }
			::= { neIPOutputMPTSTable 1 }

		NeIPOutputMPTSEntry ::=
			SEQUENCE { 
				neIPOutputMPTSIndex
					INTEGER,
				neIPOutputMPTSSource
					INTEGER,
				neIPOutputMPTSMode
					INTEGER,
				neIPOutputMPTSPortChannel
					INTEGER,
				neIPOutputMPTSDestinationAddress
					IpAddress,
				neIPOutputMPTSProtocol
					INTEGER,
				neIPOutputMPTSStatus
					DisplayString,
				neIPOutputMPTSTsidOnid
					DisplayString,
				neIPOutputMPTSOutputRate
					DisplayString
			 }

		neIPOutputMPTSIndex OBJECT-TYPE
			SYNTAX INTEGER (0..255)
			ACCESS read-only
			STATUS mandatory
			DESCRIPTION
				"Index Position."
			::= { neIPOutputMPTSEntry 1 }

 		neIPOutputMPTSSource OBJECT-TYPE
			SYNTAX INTEGER (0..3)
			ACCESS read-only
			STATUS mandatory
			DESCRIPTION
				"MPTS Source: TS1(0), TS2(1), TS3(2), TS4(3)"
			::= { neIPOutputMPTSEntry 2 }

 		neIPOutputMPTSMode OBJECT-TYPE
			SYNTAX INTEGER (0..1)
			ACCESS read-write
			STATUS mandatory
			DESCRIPTION
				"MPTS Mode: DISABLED(0), ENABLED(1)"
			::= { neIPOutputMPTSEntry 3 }

 		neIPOutputMPTSPortChannel OBJECT-TYPE
			SYNTAX INTEGER
			ACCESS read-write
			STATUS mandatory
			DESCRIPTION
				"MPTS Port Channel"
			::= { neIPOutputMPTSEntry 4 }

 		neIPOutputMPTSDestinationAddress OBJECT-TYPE
			SYNTAX IpAddress
			ACCESS read-write
			STATUS mandatory
			DESCRIPTION
				"MPTS Destination IP Address"
			::= { neIPOutputMPTSEntry 5 }

 		neIPOutputMPTSProtocol OBJECT-TYPE
			SYNTAX INTEGER (0..2)
			ACCESS read-write
			STATUS mandatory
			DESCRIPTION
				"MPTS Data Protocol: UDP(0), RTP(1), ProMPEG(2)"
			::= { neIPOutputMPTSEntry 6 }

 		neIPOutputMPTSStatus OBJECT-TYPE
			SYNTAX DisplayString (SIZE (0..32))
			ACCESS read-only
			STATUS mandatory
			DESCRIPTION
				"Status (LOCKED/UNLOCKED)"
			::= { neIPOutputMPTSEntry 7 }

 		neIPOutputMPTSTsidOnid OBJECT-TYPE
			SYNTAX DisplayString (SIZE (0..32))
			ACCESS read-only
			STATUS mandatory
			DESCRIPTION
				"TSID / ONID:"
			::= { neIPOutputMPTSEntry 8 }

 		neIPOutputMPTSOutputRate OBJECT-TYPE
			SYNTAX DisplayString (SIZE (0..32))
			ACCESS read-only
			STATUS mandatory
			DESCRIPTION
				"Output Rate (Payload)"
			::= { neIPOutputMPTSEntry 9 }

		neIPOutputMPTS1TSServiceTable OBJECT-TYPE
			SYNTAX SEQUENCE OF NeIPOutputMPTS1TSServiceEntry
			ACCESS not-accessible
			STATUS mandatory
			DESCRIPTION
				"TS Service Table."
			::= { mpts 50 }

		neIPOutputMPTS1TSServiceEntry OBJECT-TYPE
			SYNTAX NeIPOutputMPTS1TSServiceEntry
			ACCESS not-accessible
			STATUS mandatory
			DESCRIPTION
				"TS Service Table."
			INDEX { neIPOutputMPTS1TSServiceIndex }
			::= { neIPOutputMPTS1TSServiceTable 1 }

		NeIPOutputMPTS1TSServiceEntry ::=
			SEQUENCE { 
				neIPOutputMPTS1TSServiceIndex
					INTEGER,
				neIPOutputMPTS1TSServiceServiceID
					DisplayString,
				neIPOutputMPTS1TSServiceServiceType
					DisplayString,
				neIPOutputMPTS1TSServiceMode
					DisplayString,
				neIPOutputMPTS1TSServiceServiceName
					DisplayString,
			 }

		neIPOutputMPTS1TSServiceIndex OBJECT-TYPE
			SYNTAX INTEGER (1..256)
			ACCESS read-only
			STATUS mandatory
			DESCRIPTION
				"Index Position."
			::= { neIPOutputMPTS1TSServiceEntry 1 }

		neIPOutputMPTS1TSServiceServiceID OBJECT-TYPE
			SYNTAX DisplayString (SIZE (0..32))
			ACCESS read-only
			STATUS mandatory
			DESCRIPTION
				"TS Service ID"
			::= { neIPOutputMPTS1TSServiceEntry 2 }

		neIPOutputMPTS1TSServiceServiceType OBJECT-TYPE
			SYNTAX DisplayString (SIZE (0..32))
			ACCESS read-only
			STATUS mandatory
			DESCRIPTION
				"TS Service Type"
			::= { neIPOutputMPTS1TSServiceEntry 3 }

		neIPOutputMPTS1TSServiceMode OBJECT-TYPE
			SYNTAX DisplayString (SIZE (0..32))
			ACCESS read-only
			STATUS mandatory
			DESCRIPTION
				"TS Service Mode"
			::= { neIPOutputMPTS1TSServiceEntry 4 }

		neIPOutputMPTS1TSServiceServiceName OBJECT-TYPE
			SYNTAX DisplayString (SIZE (0..32))
			ACCESS read-only
			STATUS mandatory
			DESCRIPTION
				"TS Service Name"
			::= { neIPOutputMPTS1TSServiceEntry 5 }

		neIPOutputMPTS2TSServiceTable OBJECT-TYPE
			SYNTAX SEQUENCE OF NeIPOutputMPTS2TSServiceEntry
			ACCESS not-accessible
			STATUS mandatory
			DESCRIPTION
				"TS Service Table."
			::= { mpts 51 }

		neIPOutputMPTS2TSServiceEntry OBJECT-TYPE
			SYNTAX NeIPOutputMPTS2TSServiceEntry
			ACCESS not-accessible
			STATUS mandatory
			DESCRIPTION
				"TS Service Table."
			INDEX { neIPOutputMPTS2TSServiceIndex }
			::= { neIPOutputMPTS2TSServiceTable 1 }

		NeIPOutputMPTS2TSServiceEntry ::=
			SEQUENCE { 
				neIPOutputMPTS2TSServiceIndex
					INTEGER,
				neIPOutputMPTS2TSServiceServiceID
					DisplayString,
				neIPOutputMPTS2TSServiceServiceType
					DisplayString,
				neIPOutputMPTS2TSServiceMode
					DisplayString,
				neIPOutputMPTS2TSServiceServiceName
					DisplayString,
			 }

		neIPOutputMPTS2TSServiceIndex OBJECT-TYPE
			SYNTAX INTEGER (1..256)
			ACCESS read-only
			STATUS mandatory
			DESCRIPTION
				"Index Position."
			::= { neIPOutputMPTS2TSServiceEntry 1 }

		neIPOutputMPTS2TSServiceServiceID OBJECT-TYPE
			SYNTAX DisplayString (SIZE (0..32))
			ACCESS read-only
			STATUS mandatory
			DESCRIPTION
				"TS Service ID"
			::= { neIPOutputMPTS2TSServiceEntry 2 }

		neIPOutputMPTS2TSServiceServiceType OBJECT-TYPE
			SYNTAX DisplayString (SIZE (0..32))
			ACCESS read-only
			STATUS mandatory
			DESCRIPTION
				"TS Service Type"
			::= { neIPOutputMPTS2TSServiceEntry 3 }

		neIPOutputMPTS2TSServiceMode OBJECT-TYPE
			SYNTAX DisplayString (SIZE (0..32))
			ACCESS read-only
			STATUS mandatory
			DESCRIPTION
				"TS Service Mode"
			::= { neIPOutputMPTS2TSServiceEntry 4 }

		neIPOutputMPTS2TSServiceServiceName OBJECT-TYPE
			SYNTAX DisplayString (SIZE (0..32))
			ACCESS read-only
			STATUS mandatory
			DESCRIPTION
				"TS Service Name"
			::= { neIPOutputMPTS2TSServiceEntry 5 }

		neIPOutputMPTS3TSServiceTable OBJECT-TYPE
			SYNTAX SEQUENCE OF NeIPOutputMPTS3TSServiceEntry
			ACCESS not-accessible
			STATUS mandatory
			DESCRIPTION
				"TS Service Table."
			::= { mpts 52 }

		neIPOutputMPTS3TSServiceEntry OBJECT-TYPE
			SYNTAX NeIPOutputMPTS3TSServiceEntry
			ACCESS not-accessible
			STATUS mandatory
			DESCRIPTION
				"TS Service Table."
			INDEX { neIPOutputMPTS3TSServiceIndex }
			::= { neIPOutputMPTS3TSServiceTable 1 }

		NeIPOutputMPTS3TSServiceEntry ::=
			SEQUENCE { 
				neIPOutputMPTS3TSServiceIndex
					INTEGER,
				neIPOutputMPTS3TSServiceServiceID
					DisplayString,
				neIPOutputMPTS3TSServiceServiceType
					DisplayString,
				neIPOutputMPTS3TSServiceMode
					DisplayString,
				neIPOutputMPTS3TSServiceServiceName
					DisplayString,
			 }

		neIPOutputMPTS3TSServiceIndex OBJECT-TYPE
			SYNTAX INTEGER (1..256)
			ACCESS read-only
			STATUS mandatory
			DESCRIPTION
				"Index Position."
			::= { neIPOutputMPTS3TSServiceEntry 1 }

		neIPOutputMPTS3TSServiceServiceID OBJECT-TYPE
			SYNTAX DisplayString (SIZE (0..32))
			ACCESS read-only
			STATUS mandatory
			DESCRIPTION
				"TS Service ID"
			::= { neIPOutputMPTS3TSServiceEntry 2 }

		neIPOutputMPTS3TSServiceServiceType OBJECT-TYPE
			SYNTAX DisplayString (SIZE (0..32))
			ACCESS read-only
			STATUS mandatory
			DESCRIPTION
				"TS Service Type"
			::= { neIPOutputMPTS3TSServiceEntry 3 }

		neIPOutputMPTS3TSServiceMode OBJECT-TYPE
			SYNTAX DisplayString (SIZE (0..32))
			ACCESS read-only
			STATUS mandatory
			DESCRIPTION
				"TS Service Mode"
			::= { neIPOutputMPTS3TSServiceEntry 4 }

		neIPOutputMPTS3TSServiceServiceName OBJECT-TYPE
			SYNTAX DisplayString (SIZE (0..32))
			ACCESS read-only
			STATUS mandatory
			DESCRIPTION
				"TS Service Name"
			::= { neIPOutputMPTS3TSServiceEntry 5 }

		neIPOutputMPTS4TSServiceTable OBJECT-TYPE
			SYNTAX SEQUENCE OF NeIPOutputMPTS4TSServiceEntry
			ACCESS not-accessible
			STATUS mandatory
			DESCRIPTION
				"TS Service Table."
			::= { mpts 53 }

		neIPOutputMPTS4TSServiceEntry OBJECT-TYPE
			SYNTAX NeIPOutputMPTS4TSServiceEntry
			ACCESS not-accessible
			STATUS mandatory
			DESCRIPTION
				"TS Service Table."
			INDEX { neIPOutputMPTS4TSServiceIndex }
			::= { neIPOutputMPTS4TSServiceTable 1 }

		NeIPOutputMPTS4TSServiceEntry ::=
			SEQUENCE { 
				neIPOutputMPTS4TSServiceIndex
					INTEGER,
				neIPOutputMPTS4TSServiceServiceID
					DisplayString,
				neIPOutputMPTS4TSServiceServiceType
					DisplayString,
				neIPOutputMPTS4TSServiceMode
					DisplayString,
				neIPOutputMPTS4TSServiceServiceName
					DisplayString,
			 }

		neIPOutputMPTS4TSServiceIndex OBJECT-TYPE
			SYNTAX INTEGER (1..256)
			ACCESS read-only
			STATUS mandatory
			DESCRIPTION
				"Index Position."
			::= { neIPOutputMPTS4TSServiceEntry 1 }

		neIPOutputMPTS4TSServiceServiceID OBJECT-TYPE
			SYNTAX DisplayString (SIZE (0..32))
			ACCESS read-only
			STATUS mandatory
			DESCRIPTION
				"TS Service ID"
			::= { neIPOutputMPTS4TSServiceEntry 2 }

		neIPOutputMPTS4TSServiceServiceType OBJECT-TYPE
			SYNTAX DisplayString (SIZE (0..32))
			ACCESS read-only
			STATUS mandatory
			DESCRIPTION
				"TS Service Type"
			::= { neIPOutputMPTS4TSServiceEntry 3 }

		neIPOutputMPTS4TSServiceMode OBJECT-TYPE
			SYNTAX DisplayString (SIZE (0..32))
			ACCESS read-only
			STATUS mandatory
			DESCRIPTION
				"TS Service Mode"
			::= { neIPOutputMPTS4TSServiceEntry 4 }

		neIPOutputMPTS4TSServiceServiceName OBJECT-TYPE
			SYNTAX DisplayString (SIZE (0..32))
			ACCESS read-only
			STATUS mandatory
			DESCRIPTION
				"TS Service Name"
			::= { neIPOutputMPTS4TSServiceEntry 5 }

		neIPOutputSPTSTable OBJECT-TYPE
			SYNTAX SEQUENCE OF NeIPOutputSPTSEntry
			ACCESS not-accessible
			STATUS mandatory
			DESCRIPTION
				"IP Output SPTS Table."
			::= { spts 1 }

		neIPOutputSPTSEntry OBJECT-TYPE
			SYNTAX NeIPOutputSPTSEntry
			ACCESS not-accessible
			STATUS mandatory
			DESCRIPTION
				"IP Output SPTS Table."
			INDEX { neIPOutputSPTSIndex }
			::= { neIPOutputSPTSTable 1 }

		NeIPOutputSPTSEntry ::=
			SEQUENCE { 
				neIPOutputSPTSIndex
					INTEGER,
				neIPOutputSPTSTSSource
					INTEGER,
				neIPOutputSPTSServiceId
					INTEGER,
				neIPOutputSPTSMode
					INTEGER,
				neIPOutputSPTSPortChannel
					INTEGER,
				neIPOutputSPTSDestinationAddress
					IpAddress,
				neIPOutputSPTSProtocol
					INTEGER,
				neIPOutputSPTSStatus
					DisplayString,
				neIPOutputSPTSTsidOnid
					DisplayString,
				neIPOutputSPTSOutputRate
					DisplayString
			 }

		neIPOutputSPTSIndex OBJECT-TYPE
			SYNTAX INTEGER (0..255)
			ACCESS read-only
			STATUS mandatory
			DESCRIPTION
				"Index Position."
			::= { neIPOutputSPTSEntry 1 }

 		neIPOutputSPTSTSSource OBJECT-TYPE
			SYNTAX INTEGER (0..3)
			ACCESS read-write
			STATUS mandatory
			DESCRIPTION
				"SPTS TS Source: TS1(0), TS2(1), TS3(2), TS4(3)"
			::= { neIPOutputSPTSEntry 2 }

 		neIPOutputSPTSServiceId OBJECT-TYPE
			SYNTAX INTEGER
			ACCESS read-write
			STATUS mandatory
			DESCRIPTION
				"SPTS Service ID: see neIPOutputSPTSSourceTable"
			::= { neIPOutputSPTSEntry 3 }

 		neIPOutputSPTSMode OBJECT-TYPE
			SYNTAX INTEGER (0..1)
			ACCESS read-write
			STATUS mandatory
			DESCRIPTION
				"SPTS Mode: DISABLED(0), ENABLED(1)"
			::= { neIPOutputSPTSEntry 4 }

 		neIPOutputSPTSPortChannel OBJECT-TYPE
			SYNTAX INTEGER
			ACCESS read-write
			STATUS mandatory
			DESCRIPTION
				"SPTS Port Channel"
			::= { neIPOutputSPTSEntry 5 }

 		neIPOutputSPTSDestinationAddress OBJECT-TYPE
			SYNTAX IpAddress
			ACCESS read-write
			STATUS mandatory
			DESCRIPTION
				"MPTS Destination IP Address"
			::= { neIPOutputSPTSEntry 6 }

 		neIPOutputSPTSProtocol OBJECT-TYPE
			SYNTAX INTEGER (0..2)
			ACCESS read-write
			STATUS mandatory
			DESCRIPTION
				"SPTS Data Protocol: UDP(0), RTP(1), ProMPEG(2)"
			::= { neIPOutputSPTSEntry 7 }

 		neIPOutputSPTSStatus OBJECT-TYPE
			SYNTAX DisplayString (SIZE (0..32))
			ACCESS read-only
			STATUS mandatory
			DESCRIPTION
				"Status (LOCKED/UNLOCKED)"
			::= { neIPOutputSPTSEntry 8 }

 		neIPOutputSPTSTsidOnid OBJECT-TYPE
			SYNTAX DisplayString (SIZE (0..32))
			ACCESS read-only
			STATUS mandatory
			DESCRIPTION
				"TSID / ONID:"
			::= { neIPOutputSPTSEntry 9 }

 		neIPOutputSPTSOutputRate OBJECT-TYPE
			SYNTAX DisplayString (SIZE (0..32))
			ACCESS read-only
			STATUS mandatory
			DESCRIPTION
				"Output Rate (Payload)"
			::= { neIPOutputSPTSEntry 10 }

		neIPOutputSPTSSourceTable OBJECT-TYPE
			SYNTAX SEQUENCE OF NeIPOutputSPTSSourceEntry
			ACCESS not-accessible
			STATUS mandatory
			DESCRIPTION
				"TS Service Table."
			::= { spts 50 }

		neIPOutputSPTSSourceEntry OBJECT-TYPE
			SYNTAX NeIPOutputSPTSSourceEntry
			ACCESS not-accessible
			STATUS mandatory
			DESCRIPTION
				"TS Service Table."
			INDEX { neIPOutputSPTSSourceIndex }
			::= { neIPOutputSPTSSourceTable 1 }

		NeIPOutputSPTSSourceEntry ::=
			SEQUENCE { 
				neIPOutputSPTSSourceIndex
					INTEGER,
				neIPOutputSPTSSourceString
					DisplayString,
			 }

		neIPOutputSPTSSourceIndex OBJECT-TYPE
			SYNTAX INTEGER (1..1024)
			ACCESS read-only
			STATUS mandatory
			DESCRIPTION
				"Index Position."
			::= { neIPOutputSPTSSourceEntry 1 }

		neIPOutputSPTSSourceString OBJECT-TYPE
			SYNTAX DisplayString (SIZE (0..32))
			ACCESS read-only
			STATUS mandatory
			DESCRIPTION
				"TS Service"
			::= { neIPOutputSPTSSourceEntry 2 }

		neOutputASITable OBJECT-TYPE
			SYNTAX SEQUENCE OF NeOutputASIEntry
			ACCESS not-accessible
			STATUS mandatory
			DESCRIPTION
				"Output ASI Table."
			::= { output_asi 1 }

		neOutputASIEntry OBJECT-TYPE
			SYNTAX NeOutputASIEntry
			ACCESS not-accessible
			STATUS mandatory
			DESCRIPTION
				"Output ASI Table."
			INDEX { neOutputASIIndex }
			::= { neOutputASITable 1 }

		NeOutputASIEntry ::=
			SEQUENCE { 
				neOutputASIIndex
					INTEGER,
				neOutputASISource
					INTEGER,
				neOutputASIMode
					INTEGER,
				neOutputASIStatus
					DisplayString,
				neOutputASITsidOnid
					DisplayString,
				neOutputASIOutputRate
					DisplayString
			 }

		neOutputASIIndex OBJECT-TYPE
			SYNTAX INTEGER (0..255)
			ACCESS read-only
			STATUS mandatory
			DESCRIPTION
				"Index Position."
			::= { neOutputASIEntry 1 }

 		neOutputASISource OBJECT-TYPE
			SYNTAX INTEGER (0..3)
			ACCESS read-only
			STATUS mandatory
			DESCRIPTION
				"Source: TS1(0), TS2(1), TS3(2), TS4(3)"
			::= { neOutputASIEntry 2 }

 		neOutputASIMode OBJECT-TYPE
			SYNTAX INTEGER (0..1)
			ACCESS read-write
			STATUS mandatory
			DESCRIPTION
				"Mode: DISABLED(0), ENABLED(1)"
			::= { neOutputASIEntry 3 }

 		neOutputASIStatus OBJECT-TYPE
			SYNTAX DisplayString (SIZE (0..32))
			ACCESS read-only
			STATUS mandatory
			DESCRIPTION
				"Status (LOCKED/UNLOCKED)"
			::= { neOutputASIEntry 4 }

 		neOutputASITsidOnid OBJECT-TYPE
			SYNTAX DisplayString (SIZE (0..32))
			ACCESS read-only
			STATUS mandatory
			DESCRIPTION
				"TSID / ONID:"
			::= { neOutputASIEntry 5 }

 		neOutputASIOutputRate OBJECT-TYPE
			SYNTAX DisplayString (SIZE (0..32))
			ACCESS read-only
			STATUS mandatory
			DESCRIPTION
				"Output Rate (Payload)"
			::= { neOutputASIEntry 6 }

		neOutputASI1TSServiceTable OBJECT-TYPE
			SYNTAX SEQUENCE OF NeOutputASI1TSServiceEntry
			ACCESS not-accessible
			STATUS mandatory
			DESCRIPTION
				"TS Service Table."
			::= { output_asi 50 }

		neOutputASI1TSServiceEntry OBJECT-TYPE
			SYNTAX NeOutputASI1TSServiceEntry
			ACCESS not-accessible
			STATUS mandatory
			DESCRIPTION
				"TS Service Table."
			INDEX { neOutputASI1TSServiceIndex }
			::= { neOutputASI1TSServiceTable 1 }

		NeOutputASI1TSServiceEntry ::=
			SEQUENCE { 
				neOutputASI1TSServiceIndex
					INTEGER,
				neOutputASI1TSServiceServiceID
					DisplayString,
				neOutputASI1TSServiceServiceType
					DisplayString,
				neOutputASI1TSServiceMode
					DisplayString,
				neOutputASI1TSServiceServiceName
					DisplayString,
			 }

		neOutputASI1TSServiceIndex OBJECT-TYPE
			SYNTAX INTEGER (1..256)
			ACCESS read-only
			STATUS mandatory
			DESCRIPTION
				"Index Position."
			::= { neOutputASI1TSServiceEntry 1 }

		neOutputASI1TSServiceServiceID OBJECT-TYPE
			SYNTAX DisplayString (SIZE (0..32))
			ACCESS read-only
			STATUS mandatory
			DESCRIPTION
				"TS Service ID"
			::= { neOutputASI1TSServiceEntry 2 }

		neOutputASI1TSServiceServiceType OBJECT-TYPE
			SYNTAX DisplayString (SIZE (0..32))
			ACCESS read-only
			STATUS mandatory
			DESCRIPTION
				"TS Service Type"
			::= { neOutputASI1TSServiceEntry 3 }

		neOutputASI1TSServiceMode OBJECT-TYPE
			SYNTAX DisplayString (SIZE (0..32))
			ACCESS read-only
			STATUS mandatory
			DESCRIPTION
				"TS Service Mode"
			::= { neOutputASI1TSServiceEntry 4 }

		neOutputASI1TSServiceServiceName OBJECT-TYPE
			SYNTAX DisplayString (SIZE (0..32))
			ACCESS read-only
			STATUS mandatory
			DESCRIPTION
				"TS Service Name"
			::= { neOutputASI1TSServiceEntry 5 }

		neOutputASI2TSServiceTable OBJECT-TYPE
			SYNTAX SEQUENCE OF NeOutputASI2TSServiceEntry
			ACCESS not-accessible
			STATUS mandatory
			DESCRIPTION
				"TS Service Table."
			::= { output_asi 51 }

		neOutputASI2TSServiceEntry OBJECT-TYPE
			SYNTAX NeOutputASI2TSServiceEntry
			ACCESS not-accessible
			STATUS mandatory
			DESCRIPTION
				"TS Service Table."
			INDEX { neOutputASI2TSServiceIndex }
			::= { neOutputASI2TSServiceTable 1 }

		NeOutputASI2TSServiceEntry ::=
			SEQUENCE { 
				neOutputASI2TSServiceIndex
					INTEGER,
				neOutputASI2TSServiceServiceID
					DisplayString,
				neOutputASI2TSServiceServiceType
					DisplayString,
				neOutputASI2TSServiceMode
					DisplayString,
				neOutputASI2TSServiceServiceName
					DisplayString,
			 }

		neOutputASI2TSServiceIndex OBJECT-TYPE
			SYNTAX INTEGER (1..256)
			ACCESS read-only
			STATUS mandatory
			DESCRIPTION
				"Index Position."
			::= { neOutputASI2TSServiceEntry 1 }

		neOutputASI2TSServiceServiceID OBJECT-TYPE
			SYNTAX DisplayString (SIZE (0..32))
			ACCESS read-only
			STATUS mandatory
			DESCRIPTION
				"TS Service ID"
			::= { neOutputASI2TSServiceEntry 2 }

		neOutputASI2TSServiceServiceType OBJECT-TYPE
			SYNTAX DisplayString (SIZE (0..32))
			ACCESS read-only
			STATUS mandatory
			DESCRIPTION
				"TS Service Type"
			::= { neOutputASI2TSServiceEntry 3 }

		neOutputASI2TSServiceMode OBJECT-TYPE
			SYNTAX DisplayString (SIZE (0..32))
			ACCESS read-only
			STATUS mandatory
			DESCRIPTION
				"TS Service Mode"
			::= { neOutputASI2TSServiceEntry 4 }

		neOutputASI2TSServiceServiceName OBJECT-TYPE
			SYNTAX DisplayString (SIZE (0..32))
			ACCESS read-only
			STATUS mandatory
			DESCRIPTION
				"TS Service Name"
			::= { neOutputASI2TSServiceEntry 5 }

		neOutputASI3TSServiceTable OBJECT-TYPE
			SYNTAX SEQUENCE OF NeOutputASI3TSServiceEntry
			ACCESS not-accessible
			STATUS mandatory
			DESCRIPTION
				"TS Service Table."
			::= { output_asi 52 }

		neOutputASI3TSServiceEntry OBJECT-TYPE
			SYNTAX NeOutputASI3TSServiceEntry
			ACCESS not-accessible
			STATUS mandatory
			DESCRIPTION
				"TS Service Table."
			INDEX { neOutputASI3TSServiceIndex }
			::= { neOutputASI3TSServiceTable 1 }

		NeOutputASI3TSServiceEntry ::=
			SEQUENCE { 
				neOutputASI3TSServiceIndex
					INTEGER,
				neOutputASI3TSServiceServiceID
					DisplayString,
				neOutputASI3TSServiceServiceType
					DisplayString,
				neOutputASI3TSServiceMode
					DisplayString,
				neOutputASI3TSServiceServiceName
					DisplayString,
			 }

		neOutputASI3TSServiceIndex OBJECT-TYPE
			SYNTAX INTEGER (1..256)
			ACCESS read-only
			STATUS mandatory
			DESCRIPTION
				"Index Position."
			::= { neOutputASI3TSServiceEntry 1 }

		neOutputASI3TSServiceServiceID OBJECT-TYPE
			SYNTAX DisplayString (SIZE (0..32))
			ACCESS read-only
			STATUS mandatory
			DESCRIPTION
				"TS Service ID"
			::= { neOutputASI3TSServiceEntry 2 }

		neOutputASI3TSServiceServiceType OBJECT-TYPE
			SYNTAX DisplayString (SIZE (0..32))
			ACCESS read-only
			STATUS mandatory
			DESCRIPTION
				"TS Service Type"
			::= { neOutputASI3TSServiceEntry 3 }

		neOutputASI3TSServiceMode OBJECT-TYPE
			SYNTAX DisplayString (SIZE (0..32))
			ACCESS read-only
			STATUS mandatory
			DESCRIPTION
				"TS Service Mode"
			::= { neOutputASI3TSServiceEntry 4 }

		neOutputASI3TSServiceServiceName OBJECT-TYPE
			SYNTAX DisplayString (SIZE (0..32))
			ACCESS read-only
			STATUS mandatory
			DESCRIPTION
				"TS Service Name"
			::= { neOutputASI3TSServiceEntry 5 }

		neOutputASI4TSServiceTable OBJECT-TYPE
			SYNTAX SEQUENCE OF NeOutputASI4TSServiceEntry
			ACCESS not-accessible
			STATUS mandatory
			DESCRIPTION
				"TS Service Table."
			::= { output_asi 53 }

		neOutputASI4TSServiceEntry OBJECT-TYPE
			SYNTAX NeOutputASI4TSServiceEntry
			ACCESS not-accessible
			STATUS mandatory
			DESCRIPTION
				"TS Service Table."
			INDEX { neOutputASI4TSServiceIndex }
			::= { neOutputASI4TSServiceTable 1 }

		NeOutputASI4TSServiceEntry ::=
			SEQUENCE { 
				neOutputASI4TSServiceIndex
					INTEGER,
				neOutputASI4TSServiceServiceID
					DisplayString,
				neOutputASI4TSServiceServiceType
					DisplayString,
				neOutputASI4TSServiceMode
					DisplayString,
				neOutputASI4TSServiceServiceName
					DisplayString,
			 }

		neOutputASI4TSServiceIndex OBJECT-TYPE
			SYNTAX INTEGER (1..256)
			ACCESS read-only
			STATUS mandatory
			DESCRIPTION
				"Index Position."
			::= { neOutputASI4TSServiceEntry 1 }

		neOutputASI4TSServiceServiceID OBJECT-TYPE
			SYNTAX DisplayString (SIZE (0..32))
			ACCESS read-only
			STATUS mandatory
			DESCRIPTION
				"TS Service ID"
			::= { neOutputASI4TSServiceEntry 2 }

		neOutputASI4TSServiceServiceType OBJECT-TYPE
			SYNTAX DisplayString (SIZE (0..32))
			ACCESS read-only
			STATUS mandatory
			DESCRIPTION
				"TS Service Type"
			::= { neOutputASI4TSServiceEntry 3 }

		neOutputASI4TSServiceMode OBJECT-TYPE
			SYNTAX DisplayString (SIZE (0..32))
			ACCESS read-only
			STATUS mandatory
			DESCRIPTION
				"TS Service Mode"
			::= { neOutputASI4TSServiceEntry 4 }

		neOutputASI4TSServiceServiceName OBJECT-TYPE
			SYNTAX DisplayString (SIZE (0..32))
			ACCESS read-only
			STATUS mandatory
			DESCRIPTION
				"TS Service Name"
			::= { neOutputASI4TSServiceEntry 5 }

		neInputIPTable OBJECT-TYPE
			SYNTAX SEQUENCE OF NeInputIPEntry
			ACCESS not-accessible
			STATUS mandatory
			DESCRIPTION
				"Input IP Table."
			::= { input_ip 1 }

		neInputIPEntry OBJECT-TYPE
			SYNTAX NeInputIPEntry
			ACCESS not-accessible
			STATUS mandatory
			DESCRIPTION
				"Input IP Table."
			INDEX { neInputIPIndex }
			::= { neInputIPTable 1 }

		NeInputIPEntry ::=
			SEQUENCE { 
				neInputIPIndex
					INTEGER,
				neInputIP1DataProtocol
					INTEGER,
				neInputIP1DestinationPortChannel
					INTEGER,
				neInputIP1DestinationIpAddress
					IpAddress,
				neInputIP1SourceIpAddress 
					IpAddress,
				neInputIP2DataProtocol
					INTEGER,
				neInputIP2DestinationPortChannel
					INTEGER,
				neInputIP2DestinationIpAddress
					IpAddress,
				neInputIP2SourceIpAddress 
					IpAddress
			 }

		neInputIPIndex OBJECT-TYPE
			SYNTAX INTEGER (0..255)
			ACCESS read-only
			STATUS mandatory
			DESCRIPTION
				"Index Position."
			::= { neInputIPEntry 1 }

 		neInputIP1DataProtocol OBJECT-TYPE
			SYNTAX INTEGER (0..2)
			ACCESS read-write
			STATUS mandatory
			DESCRIPTION
				"Data Protocol SFP1: UDP(0), RTP(1), ProMPEG(2)"
			::= { neInputIPEntry 2 }

		neInputIP1DestinationPortChannel OBJECT-TYPE
			SYNTAX INTEGER (1..65535)
			ACCESS read-write
			STATUS mandatory
			DESCRIPTION
				"Destination Port Channel SFP1"
			::= { neInputIPEntry 3 }

 		neInputIP1DestinationIpAddress OBJECT-TYPE
			SYNTAX IpAddress
			ACCESS read-write
			STATUS mandatory
			DESCRIPTION
				"Destination IP Address SFP1"
			::= { neInputIPEntry 4 }

 		neInputIP1SourceIpAddress OBJECT-TYPE
			SYNTAX IpAddress
			ACCESS read-write
			STATUS mandatory
			DESCRIPTION
				"Source IP Address SFP1"
			::= { neInputIPEntry 5 }

 		neInputIP2DataProtocol OBJECT-TYPE
			SYNTAX INTEGER (0..2)
			ACCESS read-write
			STATUS mandatory
			DESCRIPTION
				"Data Protocol SFP2: UDP(0), RTP(1), ProMPEG(2)"
			::= { neInputIPEntry 6 }

		neInputIP2DestinationPortChannel OBJECT-TYPE
			SYNTAX INTEGER (1..65535)
			ACCESS read-write
			STATUS mandatory
			DESCRIPTION
				"Destination Port Channel SFP2"
			::= { neInputIPEntry 7 }

 		neInputIP2DestinationIpAddress OBJECT-TYPE
			SYNTAX IpAddress
			ACCESS read-write
			STATUS mandatory
			DESCRIPTION
				"Destination IP Address SFP2"
			::= { neInputIPEntry 8 }

 		neInputIP2SourceIpAddress OBJECT-TYPE
			SYNTAX IpAddress
			ACCESS read-write
			STATUS mandatory
			DESCRIPTION
				"Source IP Address SFP2"
			::= { neInputIPEntry 9 }

 		neSlot1CASource OBJECT-TYPE
			SYNTAX INTEGER (0..4)
			ACCESS read-write
			STATUS mandatory
			DESCRIPTION
				"Slot1 CA Source: OFF(0), TS1(1), TS2(2), TS3(3), TS4(4)"
			::= { slot1 1 }

 		neSlot1CAModul OBJECT-TYPE
			SYNTAX DisplayString (SIZE (0..64))
			ACCESS read-only
			STATUS mandatory
			DESCRIPTION
				"Slot1 CA Modul: "
			::= { slot1 10 }

 		neSlot1CASystemIds OBJECT-TYPE
			SYNTAX DisplayString (SIZE (0..64))
			ACCESS read-only
			STATUS mandatory
			DESCRIPTION
				"Slot1 CA System ID's: "
			::= { slot1 11 }

 		neSlot1CAStatus OBJECT-TYPE
			SYNTAX DisplayString (SIZE (0..64))
			ACCESS read-only
			STATUS mandatory
			DESCRIPTION
				"Slot1 CA Status: "
			::= { slot1 12 }

 		neSlot1CAPmtList OBJECT-TYPE
			SYNTAX INTEGER (0..1)
			ACCESS read-write
			STATUS mandatory
			DESCRIPTION
				"Slot1 CA PMT List: only - add(0), fist - more - last(1)"
			::= { slot1 13 }

		neSlot1CAReset OBJECT-TYPE
			SYNTAX TruthValue
			ACCESS read-write
			STATUS mandatory
			DESCRIPTION
				"Slot1 CA Reset: true(1), false(2)"
			::= { slot1 14 }

		neSlot1TSServiceTable OBJECT-TYPE
			SYNTAX SEQUENCE OF NeSlot1TSServiceEntry
			ACCESS not-accessible
			STATUS mandatory
			DESCRIPTION
				"TS Service Table."
			::= { slot1 50 }

		neSlot1TSServiceEntry OBJECT-TYPE
			SYNTAX NeSlot1TSServiceEntry
			ACCESS not-accessible
			STATUS mandatory
			DESCRIPTION
				"TS Service Table."
			INDEX { neSlot1TSServiceIndex }
			::= { neSlot1TSServiceTable 1 }

		NeSlot1TSServiceEntry ::=
			SEQUENCE { 
				neSlot1TSServiceIndex
					INTEGER,
				neSlot1TSServiceServiceID
					DisplayString,
				neSlot1TSServiceServiceType
					DisplayString,
				neSlot1TSServiceMode
					DisplayString,
				neSlot1TSServiceESPids
					DisplayString,
				neSlot1TSServiceServiceName
					DisplayString,
				neSlot1TSServiceCADecryption
					INTEGER
			 }

		neSlot1TSServiceIndex OBJECT-TYPE
			SYNTAX INTEGER (1..256)
			ACCESS read-only
			STATUS mandatory
			DESCRIPTION
				"Index Position."
			::= { neSlot1TSServiceEntry 1 }

		neSlot1TSServiceServiceID OBJECT-TYPE
			SYNTAX DisplayString (SIZE (0..32))
			ACCESS read-only
			STATUS mandatory
			DESCRIPTION
				"TS Service ID"
			::= { neSlot1TSServiceEntry 2 }

		neSlot1TSServiceServiceType OBJECT-TYPE
			SYNTAX DisplayString (SIZE (0..32))
			ACCESS read-only
			STATUS mandatory
			DESCRIPTION
				"TS Service Type"
			::= { neSlot1TSServiceEntry 3 }

		neSlot1TSServiceMode OBJECT-TYPE
			SYNTAX DisplayString (SIZE (0..32))
			ACCESS read-only
			STATUS mandatory
			DESCRIPTION
				"TS Service Mode)"
			::= { neSlot1TSServiceEntry 4 }

		neSlot1TSServiceESPids OBJECT-TYPE
			SYNTAX DisplayString (SIZE (0..32))
			ACCESS read-only
			STATUS mandatory
			DESCRIPTION
				"TS Service ES PIDs)"
			::= { neSlot1TSServiceEntry 5 }

		neSlot1TSServiceServiceName OBJECT-TYPE
			SYNTAX DisplayString (SIZE (0..32))
			ACCESS read-only
			STATUS mandatory
			DESCRIPTION
				"TS Service Name"
			::= { neSlot1TSServiceEntry 6 }

		neSlot1TSServiceCADecryption OBJECT-TYPE
			SYNTAX INTEGER (0..2)
			ACCESS read-write
			STATUS mandatory
			DESCRIPTION
				"Select ID: OFF(0), CI TOP(1), CI BOTTOM(2)"
			::= { neSlot1TSServiceEntry 7 }

 		neSlot2CASource OBJECT-TYPE
			SYNTAX INTEGER (0..4)
			ACCESS read-write
			STATUS mandatory
			DESCRIPTION
				"Slot2 CA Source: OFF(0), TS1(1), TS2(2), TS3(3), TS4(4)"
			::= { slot2 1 }

 		neSlot2CAModul OBJECT-TYPE
			SYNTAX DisplayString (SIZE (0..64))
			ACCESS read-only
			STATUS mandatory
			DESCRIPTION
				"Slot2 CA Modul: "
			::= { slot2 10 }

 		neSlot2CASystemIds OBJECT-TYPE
			SYNTAX DisplayString (SIZE (0..64))
			ACCESS read-only
			STATUS mandatory
			DESCRIPTION
				"Slot2 CA System ID's: "
			::= { slot2 11 }

 		neSlot2CAStatus OBJECT-TYPE
			SYNTAX DisplayString (SIZE (0..64))
			ACCESS read-only
			STATUS mandatory
			DESCRIPTION
				"Slot2 CA Status: "
			::= { slot2 12 }

 		neSlot2CAPmtList OBJECT-TYPE
			SYNTAX INTEGER (0..1)
			ACCESS read-write
			STATUS mandatory
			DESCRIPTION
				"Slot2 CA PMT List: only - add(0), fist - more - last(1)"
			::= { slot2 13 }

		neSlot2CAReset OBJECT-TYPE
			SYNTAX TruthValue
			ACCESS read-write
			STATUS mandatory
			DESCRIPTION
				"Slot2 CA Reset: true(1), false(2)"
			::= { slot2 14 }

		neSlot2TSServiceTable OBJECT-TYPE
			SYNTAX SEQUENCE OF NeSlot2TSServiceEntry
			ACCESS not-accessible
			STATUS mandatory
			DESCRIPTION
				"TS Service Table."
			::= { slot2 50 }

		neSlot2TSServiceEntry OBJECT-TYPE
			SYNTAX NeSlot2TSServiceEntry
			ACCESS not-accessible
			STATUS mandatory
			DESCRIPTION
				"TS Service Table."
			INDEX { neSlot2TSServiceIndex }
			::= { neSlot2TSServiceTable 1 }

		NeSlot2TSServiceEntry ::=
			SEQUENCE { 
				neSlot2TSServiceIndex
					INTEGER,
				neSlot2TSServiceServiceID
					DisplayString,
				neSlot2TSServiceServiceType
					DisplayString,
				neSlot2TSServiceMode
					DisplayString,
				neSlot2TSServiceESPids
					DisplayString,
				neSlot2TSServiceServiceName
					DisplayString,
				neSlot2TSServiceCADecryption
					INTEGER
			 }

		neSlot2TSServiceIndex OBJECT-TYPE
			SYNTAX INTEGER (1..256)
			ACCESS read-only
			STATUS mandatory
			DESCRIPTION
				"Index Position."
			::= { neSlot2TSServiceEntry 1 }

		neSlot2TSServiceServiceID OBJECT-TYPE
			SYNTAX DisplayString (SIZE (0..32))
			ACCESS read-only
			STATUS mandatory
			DESCRIPTION
				"TS Service ID"
			::= { neSlot2TSServiceEntry 2 }

		neSlot2TSServiceServiceType OBJECT-TYPE
			SYNTAX DisplayString (SIZE (0..32))
			ACCESS read-only
			STATUS mandatory
			DESCRIPTION
				"TS Service Type"
			::= { neSlot2TSServiceEntry 3 }

		neSlot2TSServiceMode OBJECT-TYPE
			SYNTAX DisplayString (SIZE (0..32))
			ACCESS read-only
			STATUS mandatory
			DESCRIPTION
				"TS Service Mode)"
			::= { neSlot2TSServiceEntry 4 }

		neSlot2TSServiceESPids OBJECT-TYPE
			SYNTAX DisplayString (SIZE (0..32))
			ACCESS read-only
			STATUS mandatory
			DESCRIPTION
				"TS Service ES PIDs)"
			::= { neSlot2TSServiceEntry 5 }

		neSlot2TSServiceServiceName OBJECT-TYPE
			SYNTAX DisplayString (SIZE (0..32))
			ACCESS read-only
			STATUS mandatory
			DESCRIPTION
				"TS Service Name"
			::= { neSlot2TSServiceEntry 6 }

		neSlot2TSServiceCADecryption OBJECT-TYPE
			SYNTAX INTEGER (0..2)
			ACCESS read-write
			STATUS mandatory
			DESCRIPTION
				"Select ID: OFF(0), CI TOP(1), CI BOTTOM(2)"
			::= { neSlot2TSServiceEntry 7 }

 		neSlot3CASource OBJECT-TYPE
			SYNTAX INTEGER (0..4)
			ACCESS read-write
			STATUS mandatory
			DESCRIPTION
				"Slot3 CA Source: OFF(0), TS1(1), TS2(2), TS3(3), TS4(4)"
			::= { slot3 1 }

 		neSlot3CAModul OBJECT-TYPE
			SYNTAX DisplayString (SIZE (0..64))
			ACCESS read-only
			STATUS mandatory
			DESCRIPTION
				"Slot3 CA Modul: "
			::= { slot3 10 }

 		neSlot3CASystemIds OBJECT-TYPE
			SYNTAX DisplayString (SIZE (0..64))
			ACCESS read-only
			STATUS mandatory
			DESCRIPTION
				"Slot3 CA System ID's: "
			::= { slot3 11 }

 		neSlot3CAStatus OBJECT-TYPE
			SYNTAX DisplayString (SIZE (0..64))
			ACCESS read-only
			STATUS mandatory
			DESCRIPTION
				"Slot3 CA Status: "
			::= { slot3 12 }

 		neSlot3CAPmtList OBJECT-TYPE
			SYNTAX INTEGER (0..1)
			ACCESS read-write
			STATUS mandatory
			DESCRIPTION
				"Slot3 CA PMT List: only - add(0), fist - more - last(1)"
			::= { slot3 13 }

		neSlot3CAReset OBJECT-TYPE
			SYNTAX TruthValue
			ACCESS read-write
			STATUS mandatory
			DESCRIPTION
				"Slot3 CA Reset: true(1), false(2)"
			::= { slot3 14 }

		neSlot3TSServiceTable OBJECT-TYPE
			SYNTAX SEQUENCE OF NeSlot3TSServiceEntry
			ACCESS not-accessible
			STATUS mandatory
			DESCRIPTION
				"TS Service Table."
			::= { slot3 50 }

		neSlot3TSServiceEntry OBJECT-TYPE
			SYNTAX NeSlot3TSServiceEntry
			ACCESS not-accessible
			STATUS mandatory
			DESCRIPTION
				"TS Service Table."
			INDEX { neSlot3TSServiceIndex }
			::= { neSlot3TSServiceTable 1 }

		NeSlot3TSServiceEntry ::=
			SEQUENCE { 
				neSlot3TSServiceIndex
					INTEGER,
				neSlot3TSServiceServiceID
					DisplayString,
				neSlot3TSServiceServiceType
					DisplayString,
				neSlot3TSServiceMode
					DisplayString,
				neSlot3TSServiceESPids
					DisplayString,
				neSlot3TSServiceServiceName
					DisplayString,
				neSlot3TSServiceCADecryption
					INTEGER
			 }

		neSlot3TSServiceIndex OBJECT-TYPE
			SYNTAX INTEGER (1..256)
			ACCESS read-only
			STATUS mandatory
			DESCRIPTION
				"Index Position."
			::= { neSlot3TSServiceEntry 1 }

		neSlot3TSServiceServiceID OBJECT-TYPE
			SYNTAX DisplayString (SIZE (0..32))
			ACCESS read-only
			STATUS mandatory
			DESCRIPTION
				"TS Service ID"
			::= { neSlot3TSServiceEntry 2 }

		neSlot3TSServiceServiceType OBJECT-TYPE
			SYNTAX DisplayString (SIZE (0..32))
			ACCESS read-only
			STATUS mandatory
			DESCRIPTION
				"TS Service Type"
			::= { neSlot3TSServiceEntry 3 }

		neSlot3TSServiceMode OBJECT-TYPE
			SYNTAX DisplayString (SIZE (0..32))
			ACCESS read-only
			STATUS mandatory
			DESCRIPTION
				"TS Service Mode)"
			::= { neSlot3TSServiceEntry 4 }

		neSlot3TSServiceESPids OBJECT-TYPE
			SYNTAX DisplayString (SIZE (0..32))
			ACCESS read-only
			STATUS mandatory
			DESCRIPTION
				"TS Service ES PIDs)"
			::= { neSlot3TSServiceEntry 5 }

		neSlot3TSServiceServiceName OBJECT-TYPE
			SYNTAX DisplayString (SIZE (0..32))
			ACCESS read-only
			STATUS mandatory
			DESCRIPTION
				"TS Service Name"
			::= { neSlot3TSServiceEntry 6 }

		neSlot3TSServiceCADecryption OBJECT-TYPE
			SYNTAX INTEGER (0..2)
			ACCESS read-write
			STATUS mandatory
			DESCRIPTION
				"Select ID: OFF(0), CI TOP(1), CI BOTTOM(2)"
			::= { neSlot3TSServiceEntry 7 }

 		neSlot4CASource OBJECT-TYPE
			SYNTAX INTEGER (0..4)
			ACCESS read-write
			STATUS mandatory
			DESCRIPTION
				"Slot4 CA Source: OFF(0), TS1(1), TS2(2), TS3(3), TS4(4)"
			::= { slot4 1 }

 		neSlot4CAModul OBJECT-TYPE
			SYNTAX DisplayString (SIZE (0..64))
			ACCESS read-only
			STATUS mandatory
			DESCRIPTION
				"Slot4 CA Modul: "
			::= { slot4 10 }

 		neSlot4CASystemIds OBJECT-TYPE
			SYNTAX DisplayString (SIZE (0..64))
			ACCESS read-only
			STATUS mandatory
			DESCRIPTION
				"Slot4 CA System ID's: "
			::= { slot4 11 }

 		neSlot4CAStatus OBJECT-TYPE
			SYNTAX DisplayString (SIZE (0..64))
			ACCESS read-only
			STATUS mandatory
			DESCRIPTION
				"Slot4 CA Status: "
			::= { slot4 12 }

 		neSlot4CAPmtList OBJECT-TYPE
			SYNTAX INTEGER (0..1)
			ACCESS read-write
			STATUS mandatory
			DESCRIPTION
				"Slot4 CA PMT List: only - add(0), fist - more - last(1)"
			::= { slot4 13 }

		neSlot4CAReset OBJECT-TYPE
			SYNTAX TruthValue
			ACCESS read-write
			STATUS mandatory
			DESCRIPTION
				"Slot4 CA Reset: true(1), false(2)"
			::= { slot4 14 }

		neSlot4TSServiceTable OBJECT-TYPE
			SYNTAX SEQUENCE OF NeSlot4TSServiceEntry
			ACCESS not-accessible
			STATUS mandatory
			DESCRIPTION
				"TS Service Table."
			::= { slot4 50 }

		neSlot4TSServiceEntry OBJECT-TYPE
			SYNTAX NeSlot4TSServiceEntry
			ACCESS not-accessible
			STATUS mandatory
			DESCRIPTION
				"TS Service Table."
			INDEX { neSlot4TSServiceIndex }
			::= { neSlot4TSServiceTable 1 }

		NeSlot4TSServiceEntry ::=
			SEQUENCE { 
				neSlot4TSServiceIndex
					INTEGER,
				neSlot4TSServiceServiceID
					DisplayString,
				neSlot4TSServiceServiceType
					DisplayString,
				neSlot4TSServiceMode
					DisplayString,
				neSlot4TSServiceESPids
					DisplayString,
				neSlot4TSServiceServiceName
					DisplayString,
				neSlot4TSServiceCADecryption
					INTEGER
			 }

		neSlot4TSServiceIndex OBJECT-TYPE
			SYNTAX INTEGER (1..256)
			ACCESS read-only
			STATUS mandatory
			DESCRIPTION
				"Index Position."
			::= { neSlot4TSServiceEntry 1 }

		neSlot4TSServiceServiceID OBJECT-TYPE
			SYNTAX DisplayString (SIZE (0..32))
			ACCESS read-only
			STATUS mandatory
			DESCRIPTION
				"TS Service ID"
			::= { neSlot4TSServiceEntry 2 }

		neSlot4TSServiceServiceType OBJECT-TYPE
			SYNTAX DisplayString (SIZE (0..32))
			ACCESS read-only
			STATUS mandatory
			DESCRIPTION
				"TS Service Type"
			::= { neSlot4TSServiceEntry 3 }

		neSlot4TSServiceMode OBJECT-TYPE
			SYNTAX DisplayString (SIZE (0..32))
			ACCESS read-only
			STATUS mandatory
			DESCRIPTION
				"TS Service Mode)"
			::= { neSlot4TSServiceEntry 4 }

		neSlot4TSServiceESPids OBJECT-TYPE
			SYNTAX DisplayString (SIZE (0..32))
			ACCESS read-only
			STATUS mandatory
			DESCRIPTION
				"TS Service ES PIDs)"
			::= { neSlot4TSServiceEntry 5 }

		neSlot4TSServiceServiceName OBJECT-TYPE
			SYNTAX DisplayString (SIZE (0..32))
			ACCESS read-only
			STATUS mandatory
			DESCRIPTION
				"TS Service Name"
			::= { neSlot4TSServiceEntry 6 }

		neSlot4TSServiceCADecryption OBJECT-TYPE
			SYNTAX INTEGER (0..2)
			ACCESS read-write
			STATUS mandatory
			DESCRIPTION
				"Select ID: OFF(0), CI TOP(1), CI BOTTOM(2)"
			::= { neSlot4TSServiceEntry 7 }

 		neConfigControlIPaddress OBJECT-TYPE
			SYNTAX IpAddress
			ACCESS read-write
			STATUS mandatory
			DESCRIPTION
				"Control: IP Address"
			::= { lan 1 }

 		neConfigControlSubnetMask OBJECT-TYPE
			SYNTAX IpAddress
			ACCESS read-write
			STATUS mandatory
			DESCRIPTION
				"Control: Subnet Mask"
			::= { lan 2 }

 		neConfigControlGatewayAddress OBJECT-TYPE
			SYNTAX IpAddress
			ACCESS read-write
			STATUS mandatory
			DESCRIPTION
				"Control: Gateway Address"
			::= { lan 3 }

 		neConfigDataIPaddress1 OBJECT-TYPE
			SYNTAX IpAddress
			ACCESS read-write
			STATUS mandatory
			DESCRIPTION
				"Data 1: IP Address"
			::= { lan 4 }

 		neConfigDataSubnetMask1 OBJECT-TYPE
			SYNTAX IpAddress
			ACCESS read-write
			STATUS mandatory
			DESCRIPTION
				"Data 1: Subnet Mask"
			::= { lan 5 }

 		neConfigDataGatewayAddress1 OBJECT-TYPE
			SYNTAX IpAddress
			ACCESS read-write
			STATUS mandatory
			DESCRIPTION
				"Data 1: Gateway Address"
			::= { lan 6 }

		neConfigDataSpeedDuplexMode1 OBJECT-TYPE
			SYNTAX INTEGER (0..4)
			ACCESS read-write
			STATUS mandatory
			DESCRIPTION
				"Speed/Duplex Mode 1: AUTO-NEGOTIATION(0),
				                      1000 MBIT FULL DUPLEX(1),
				                      1000 MBIT HALF DUPLEX(2),
				                      100 MBIT FULL DUPLEX(3),
				                      100 MBIT HALF DUPLEX(4)"
			::= { lan 7 }

 		neConfigDataIPaddress2 OBJECT-TYPE
			SYNTAX IpAddress
			ACCESS read-write
			STATUS mandatory
			DESCRIPTION
				"Data 2: IP Address"
			::= { lan 8 }

 		neConfigDataSubnetMask2 OBJECT-TYPE
			SYNTAX IpAddress
			ACCESS read-write
			STATUS mandatory
			DESCRIPTION
				"Data 2: Subnet Mask"
			::= { lan 9 }

 		neConfigDataGatewayAddress2 OBJECT-TYPE
			SYNTAX IpAddress
			ACCESS read-write
			STATUS mandatory
			DESCRIPTION
				"Data 2: Gateway Address"
			::= { lan 10 }

		neConfigDataSpeedDuplexMode2 OBJECT-TYPE
			SYNTAX INTEGER (0..4)
			ACCESS read-write
			STATUS mandatory
			DESCRIPTION
				"Speed/Duplex Mode 2: AUTO-NEGOTIATION(0),
				                      1000 MBIT FULL DUPLEX(1),
				                      1000 MBIT HALF DUPLEX(2),
				                      100 MBIT FULL DUPLEX(3),
				                      100 MBIT HALF DUPLEX(4)"
			::= { lan 11 }

		neConfigSFPModule1 OBJECT-TYPE
			SYNTAX DisplayString (SIZE (32))
			ACCESS read-only
			STATUS mandatory
			DESCRIPTION
				"SFP Module 1:"
			::= { lan 20 }

		neConfigSFPName1 OBJECT-TYPE
			SYNTAX DisplayString (SIZE (32))
			ACCESS read-only
			STATUS mandatory
			DESCRIPTION
				"SFP Module Name 1:"
			::= { lan 21 }

		neConfigSFPConnection1 OBJECT-TYPE
			SYNTAX DisplayString (SIZE (32))
			ACCESS read-only
			STATUS mandatory
			DESCRIPTION
				"SFP Module Connection 1:"
			::= { lan 22 }

		neConfigSFPModule2 OBJECT-TYPE
			SYNTAX DisplayString (SIZE (32))
			ACCESS read-only
			STATUS mandatory
			DESCRIPTION
				"SFP Module 2:"
			::= { lan 30 }

		neConfigSFPName2 OBJECT-TYPE
			SYNTAX DisplayString (SIZE (32))
			ACCESS read-only
			STATUS mandatory
			DESCRIPTION
				"SFP Module Name 2:"
			::= { lan 31 }

		neConfigSFPConnection2 OBJECT-TYPE
			SYNTAX DisplayString (SIZE (32))
			ACCESS read-only
			STATUS mandatory
			DESCRIPTION
				"SFP Module Connection 2:"
			::= { lan 32 }

		neConfigSNMPMode OBJECT-TYPE
			SYNTAX INTEGER (0..1)
			ACCESS read-write
			STATUS mandatory
			DESCRIPTION
				"SNMPv2c Mode: DISABLED(0), ENABLED(1)"
			::= { snmpv2 1 }

		neConfigSNMPReadCommunity OBJECT-TYPE
			SYNTAX DisplayString (SIZE (0..32))
			ACCESS read-write
			STATUS mandatory
			DESCRIPTION
				"Read Community:"
			::= { snmpv2 2 }

 		neConfigSNMPSetCommunity OBJECT-TYPE
			SYNTAX DisplayString (SIZE (0..32))
			ACCESS read-write
			STATUS mandatory
			DESCRIPTION
				"Set Community:"
			::= { snmpv2 3 }

		neTrapReceiverTable OBJECT-TYPE
			SYNTAX SEQUENCE OF NeTrapReceiverEntry
			ACCESS not-accessible
			STATUS mandatory
			DESCRIPTION
				"Table containing information about each Traps."
			::= { snmpv2 20 }

		neTrapReceiverEntry OBJECT-TYPE
			SYNTAX NeTrapReceiverEntry
			ACCESS not-accessible
			STATUS mandatory
			DESCRIPTION
				"List of information about each Traps."
			INDEX { neTrapReceiverIndex }
			::= { neTrapReceiverTable 1 }

		NeTrapReceiverEntry ::=
			SEQUENCE { 
				neTrapReceiverIndex
					INTEGER,
				neTrapReceiverNetworkAddress
					IpAddress,
				neTrapReceiverCommunityString
					DisplayString,
				neTrapReceiverRowStatus
					INTEGER
			 }

		neTrapReceiverIndex OBJECT-TYPE
			SYNTAX INTEGER (1..256)
			ACCESS read-only
			STATUS mandatory
			DESCRIPTION
				"Index Position."
			::= { neTrapReceiverEntry 1 }

		neTrapReceiverNetworkAddress OBJECT-TYPE
			SYNTAX IpAddress
			ACCESS read-write
			STATUS mandatory
			DESCRIPTION
				"The network-address of the manager that has to receive traps."
			::= { neTrapReceiverEntry 2 }

		neTrapReceiverCommunityString OBJECT-TYPE
			SYNTAX DisplayString (SIZE (0..32))
			ACCESS read-write
			STATUS mandatory
			DESCRIPTION
				"."
			::= { neTrapReceiverEntry 3 }

		neTrapReceiverRowStatus OBJECT-TYPE
			SYNTAX INTEGER (0..1)
			ACCESS read-write
			STATUS mandatory
			DESCRIPTION
				"Trap Mode: DISABLED(0), ENABLED(1)"
			::= { neTrapReceiverEntry 4 }

		neAlarmSeverityTable OBJECT-TYPE
			SYNTAX SEQUENCE OF NeAlarmSeverityEntry
			ACCESS not-accessible
			STATUS mandatory
			DESCRIPTION
				"Table containing information about each Traps."
			::= { snmpv2 30 }

		neAlarmSeverityEntry OBJECT-TYPE
			SYNTAX NeAlarmSeverityEntry
			ACCESS not-accessible
			STATUS mandatory
			DESCRIPTION
				"List of information about each Traps."
			INDEX { neAlarmSeverityIndex }
			::= { neAlarmSeverityTable 1 }

		NeAlarmSeverityEntry ::=
			SEQUENCE { 
				neAlarmSeverityIndex
					INTEGER,
				neAlarmSeverityName
					DisplayString,
				neAlarmSeverityLevel
					INTEGER
			 }

		neAlarmSeverityIndex OBJECT-TYPE
			SYNTAX INTEGER (1..256)
			ACCESS read-only
			STATUS mandatory
			DESCRIPTION
				"Index Position."
			::= { neAlarmSeverityEntry 1 }

		neAlarmSeverityName OBJECT-TYPE
			SYNTAX DisplayString (SIZE (0..32))
			ACCESS read-only
			STATUS mandatory
			DESCRIPTION
				"Alarm Severity Name:"
			::= { neAlarmSeverityEntry 2 }

		neAlarmSeverityLevel OBJECT-TYPE
			SYNTAX INTEGER (0..1)
			ACCESS read-write
			STATUS mandatory
			DESCRIPTION
				"Alarm Severity Level: DISABLED(0), ENABLED(1)"
			::= { neAlarmSeverityEntry 3 }

		neConfigTelnetMode OBJECT-TYPE
			SYNTAX INTEGER (0..1)
			ACCESS read-write
			STATUS mandatory
			DESCRIPTION
				"Telnet Mode: DISABLED(0), ENABLED(1)"
			::= { telnet 1 }

		neConfigRedundancyDataSource OBJECT-TYPE
			SYNTAX INTEGER (0..2)
			ACCESS read-write
			STATUS mandatory
			DESCRIPTION
				"Data Source: GbE - IP 1(0), GbE - IP 2(1), AUTO(2)"
			::= { redundancy 1 }

		neConfigRedundancySwitchDelay OBJECT-TYPE
			SYNTAX INTEGER (1..255)
			ACCESS read-write
			STATUS mandatory
			DESCRIPTION
				"Switch Delay: 1-255 sec"
			::= { redundancy 2 }

 		neConfigDeviceLabel OBJECT-TYPE
			SYNTAX DisplayString (SIZE (0..64))
			ACCESS read-write
			STATUS mandatory
			DESCRIPTION
				"Device Label:"
			::= { system 10 }

 		neConfigDisplayContrast OBJECT-TYPE
			SYNTAX INTEGER (0..15)
			ACCESS read-write
			STATUS mandatory
			DESCRIPTION
				"LCD Contrast: 100%(0), 93%(1), 86%(2) 80%(3), 73%(4), 66%(5) 60%(6),
				53%(7), 46%(8) 40%(9), 33%(10), 26%(11) 20%(12), 13%(13), 6%(14) 0%(15)"
			::= { system 11 }

		neConfigPsiIDDisplayFormat OBJECT-TYPE
			SYNTAX INTEGER (0..1)
			ACCESS read-write
			STATUS mandatory
			DESCRIPTION
				"PSI-ID Display Format: HEXADECIMAL(0), DECIMAL(1)"
			::= { system 12 }

		neConfigPowerSupplyCheck OBJECT-TYPE
			SYNTAX INTEGER (0..1)
			ACCESS read-write
			STATUS mandatory
			DESCRIPTION
				"Power Supply Check: OFF(0), ON(1)"
			::= { system 13 }

		neConfigReset OBJECT-TYPE
			SYNTAX INTEGER (0..1)
			ACCESS read-write
			STATUS mandatory
			DESCRIPTION
				"Reset: false(0), true(1)"
			::= { system 50 }

		neConfigFactorySetting OBJECT-TYPE
			SYNTAX INTEGER (0..1)
			ACCESS read-write
			STATUS mandatory
			DESCRIPTION
				"Factory setting: false(0), true(1)"
			::= { system 51 }

		neConfigClearLogbook OBJECT-TYPE
			SYNTAX INTEGER (0..1)
			ACCESS read-write
			STATUS mandatory
			DESCRIPTION
				"Clear Logbook: false(0), true(1)"
			::= { system 52 }

		neConfigDateTimeSyncMode OBJECT-TYPE
			SYNTAX INTEGER (0..5)
			ACCESS read-write
			STATUS mandatory
			DESCRIPTION
				"Date-Time Sync Mode: OFF(0), NTP SERVER(1), TS1(2), TS2(3), TS3(4), TS4(5)"
			::= { date_time 1 }

 		neConfigDate OBJECT-TYPE
			SYNTAX DisplayString (SIZE (0..16))
			ACCESS read-write
			STATUS mandatory
			DESCRIPTION
				"Date: dd.mm.yy"
			::= { date_time 2 }

 		neConfigTime OBJECT-TYPE
			SYNTAX DisplayString (SIZE (0..16))
			ACCESS read-write
			STATUS mandatory
			DESCRIPTION
				"Time: hh:mm:ss"
			::= { date_time 3 }

 		neConfigTimeOffset OBJECT-TYPE
			SYNTAX INTEGER (-24..24)
			ACCESS read-write
			STATUS mandatory
			DESCRIPTION
				"Time Offset: +12.0h(24),  +11.5h(23), +11.0h(22)  +10.5h(21),   +10.0h(20),   +9.5h(19),
				+9.0h(18),     +8.5h(17),  +8.0h(16)   +7.5h(15),   +7.0h(14),    +6.5h(13)    +6.0h(12),
				+5.5h(11),     +5.0h(10)   +4.5h(9),   +4.0h(8),    +3.5h(7),     +3.0h(6),    +2.5h(5),
				+2.0h(4),      +1.5h(3),   +1.0h(2)    +0.5h(1),    +0.0h(0),     -0.5h(-1),   -1.0h(-2),
				-1.5h(-3),     -2.0h(-4)   -2.5h(-5),  -3.0h(-6),   -3.5h(-7),    -4.0h(-8),   -4.5h(-9),
				-5.0h(-10),    -5.5h(-11), -6.0h(-12)  -6.5h(-13),  -7.0h(-14),   -7.5h(-15),  -8.0h(-16),
				-8.5h(-17),    -9.0h(-18)  -9.5h(-19), -10.0h(-20), -10.5h(-21), -11.0h(-22), -11.5h(-23),
				-12.0h(-24)"
			::= { date_time 4 }

		neConfigNtpServer1 OBJECT-TYPE
			SYNTAX IpAddress
			ACCESS read-write
			STATUS mandatory
			DESCRIPTION
				"NTP Server 1:"
			::= { date_time 5 }

		neConfigNtpServer2 OBJECT-TYPE
			SYNTAX IpAddress
			ACCESS read-write
			STATUS mandatory
			DESCRIPTION
				"NTP Server 2:"
			::= { date_time 6 }

		neConfigNtpSyncInterval OBJECT-TYPE
			SYNTAX INTEGER (1..9999)
			ACCESS read-write
			STATUS mandatory
			DESCRIPTION
				"NTP Sync Interval: 1-9999 min"
			::= { date_time 7 }

		neConfigDaylightSavingTime OBJECT-TYPE
			SYNTAX INTEGER (0..1)
			ACCESS read-write
			STATUS mandatory
			DESCRIPTION
				"Daylight Saving Time: OFF(0), EUROPEAN(1)"
			::= { date_time 8 }

		neConfigSyncThreshold OBJECT-TYPE
			SYNTAX INTEGER (1..99)
			ACCESS read-write
			STATUS mandatory
			DESCRIPTION
				"Sync Threshold: 1-99 sec"
			::= { date_time 9 }

 		neConfigFallbackTime OBJECT-TYPE
			SYNTAX INTEGER (0..10)
			ACCESS read-write
			STATUS mandatory
			DESCRIPTION
				"Fallback Time: 10 minutes(0), 20 minutes(1), 30 minutes(2), 40 minutes(3),
				50 minutes(4), 60 minutes(5), 120 minutes(6), 240 minutes(7), 360 minutes(8),
				480 minutes(9), 600 minutes(10)"
			::= { user_accounts 1 }

		neUserAccountTable OBJECT-TYPE
			SYNTAX SEQUENCE OF NeUserAccountEntry
			ACCESS not-accessible
			STATUS mandatory
			DESCRIPTION
				"Table containing information about each Users."
			::= { user_accounts 20 }

		neUserAccountEntry OBJECT-TYPE
			SYNTAX NeUserAccountEntry
			ACCESS not-accessible
			STATUS mandatory
			DESCRIPTION
				"List of information about each Users."
			INDEX { neUserAccountIndex }
			::= { neUserAccountTable 1 }

		NeUserAccountEntry ::=
			SEQUENCE { 
				neUserAccountIndex
					INTEGER,
				neUserAccountName
					DisplayString,
				neUserAccountPassword
					DisplayString,
				neUserAccountRowStatus
					INTEGER
			 }

		neUserAccountIndex OBJECT-TYPE
			SYNTAX INTEGER (1..256)
			ACCESS read-only
			STATUS mandatory
			DESCRIPTION
				"Index Position."
			::= { neUserAccountEntry 1 }

		neUserAccountName OBJECT-TYPE
			SYNTAX DisplayString (SIZE (0..32))
			ACCESS read-write
			STATUS mandatory
			DESCRIPTION
				"Name."
			::= { neUserAccountEntry 2 }

		neUserAccountPassword OBJECT-TYPE
			SYNTAX DisplayString (SIZE (0..32))
			ACCESS read-write
			STATUS mandatory
			DESCRIPTION
				"Password."
			::= { neUserAccountEntry 3 }

		neUserAccountRowStatus OBJECT-TYPE
			SYNTAX INTEGER (0..6)
			ACCESS read-write
			STATUS mandatory
			DESCRIPTION
				"OFF(0), ADMIN(1), READONLY(2), GROUP 1(3), GROUP 2(4), GROUP 3(5), GROUP 4(6)"
			::= { neUserAccountEntry 4 }

		neGroupAccessTable OBJECT-TYPE
			SYNTAX SEQUENCE OF NeGroupAccessEntry
			ACCESS not-accessible
			STATUS mandatory
			DESCRIPTION
				"Table containing information about each Users."
			::= { user_accounts 30 }

		neGroupAccessEntry OBJECT-TYPE
			SYNTAX NeGroupAccessEntry
			ACCESS not-accessible
			STATUS mandatory
			DESCRIPTION
				"List of information about each Users."
			INDEX { neUserAccountIndex }
			::= { neGroupAccessTable 1 }

		NeGroupAccessEntry ::=
			SEQUENCE { 
				neGroupAccessIndex
					INTEGER,
				neGroup1AccessPage
					DisplayString,
				neGroup1AccessLevel
					INTEGER,
				neGroup2AccessPage
					DisplayString,
				neGroup2AccessLevel
					INTEGER,
				neGroup3AccessPage
					DisplayString,
				neGroup3AccessLevel
					INTEGER,
				neGroup4AccessPage
					DisplayString,
				neGroup4AccessLevel
					INTEGER
			 }

		neGroupAccessIndex OBJECT-TYPE
			SYNTAX INTEGER (1..256)
			ACCESS read-only
			STATUS mandatory
			DESCRIPTION
				"Index Position."
			::= { neGroupAccessEntry 1 }

		neGroup1AccessPage OBJECT-TYPE
			SYNTAX DisplayString (SIZE (0..32))
			ACCESS read-only
			STATUS mandatory
			DESCRIPTION
				"Page."
			::= { neGroupAccessEntry 2 }

		neGroup1AccessLevel OBJECT-TYPE
			SYNTAX INTEGER (0..1)
			ACCESS read-write
			STATUS mandatory
			DESCRIPTION
				"READONLY(0), SET(1)"
			::= { neGroupAccessEntry 3 }

		neGroup2AccessPage OBJECT-TYPE
			SYNTAX DisplayString (SIZE (0..32))
			ACCESS read-only
			STATUS mandatory
			DESCRIPTION
				"Page."
			::= { neGroupAccessEntry 4 }

		neGroup2AccessLevel OBJECT-TYPE
			SYNTAX INTEGER (0..1)
			ACCESS read-write
			STATUS mandatory
			DESCRIPTION
				"READONLY(0), SET(1)"
			::= { neGroupAccessEntry 5 }

		neGroup3AccessPage OBJECT-TYPE
			SYNTAX DisplayString (SIZE (0..32))
			ACCESS read-only
			STATUS mandatory
			DESCRIPTION
				"Page."
			::= { neGroupAccessEntry 6 }

		neGroup3AccessLevel OBJECT-TYPE
			SYNTAX INTEGER (0..1)
			ACCESS read-write
			STATUS mandatory
			DESCRIPTION
				"READONLY(0), SET(1)"
			::= { neGroupAccessEntry 7 }

		neGroup4AccessPage OBJECT-TYPE
			SYNTAX DisplayString (SIZE (0..32))
			ACCESS read-only
			STATUS mandatory
			DESCRIPTION
				"Page."
			::= { neGroupAccessEntry 8 }

		neGroup4AccessLevel OBJECT-TYPE
			SYNTAX INTEGER (0..1)
			ACCESS read-write
			STATUS mandatory
			DESCRIPTION
				"READONLY(0), SET(1)"
			::= { neGroupAccessEntry 9 }

--
--  traps
--

    neAlarmEvent TRAP-TYPE
        ENTERPRISE      drd700
        VARIABLES {
                    neType, 
                    neStatesDeviceStatus,
                    neStatesDeviceLedInput,
                    neStatesDeviceLedStatus,
                    neStatesDeviceLedFault,
                  }
        DESCRIPTION
                "AlarmEvent"
        ::= 1

	END
