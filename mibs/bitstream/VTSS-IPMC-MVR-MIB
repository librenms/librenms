-- *****************************************************************
-- IPMC-MVR-MIB:  Vitesse private MIB
--
-- Copyright (c) 2002-2013 Vitesse Semiconductor Corporation "Vitesse".
-- All Rights Reserved.
--
-- ****************************************************************

VTSS-IPMC-MVR-MIB DEFINITIONS ::= BEGIN

IMPORTS
    MODULE-COMPLIANCE, OBJECT-GROUP
        FROM SNMPv2-CONF
    MODULE-IDENTITY, OBJECT-TYPE
        FROM SNMPv2-SMI
    TEXTUAL-CONVENTION
        FROM SNMPv2-TC
    vtssSwitchMgmt
        FROM VTSS-SMI
    InetAddressIPv6 FROM INET-ADDRESS-MIB
    IpAddress FROM SNMPv2-SMI
    Unsigned32 FROM SNMPv2-SMI
    TruthValue FROM SNMPv2-TC
    VTSSDisplayString FROM VTSS-TC
    VTSSInterfaceIndex FROM VTSS-TC
    VTSSPortList FROM VTSS-TC
    VTSSRowEditorState FROM VTSS-TC
    VTSSUnsigned8 FROM VTSS-TC
    ;

vtssIpmcMvrMib MODULE-IDENTITY
    LAST-UPDATED "201407010000Z"
    ORGANIZATION
        "Vitesse Semiconductor Corporation"
    CONTACT-INFO
        "Application support <application_support@vitesse.com>"
    DESCRIPTION
        "This is a private version of the IPMC MVR MIB"
    REVISION    "201407010000Z"
    DESCRIPTION
        "Initial version"
    ::= { vtssSwitchMgmt 68 }


VTSSIpmcMvrGroupSrcListGroupFilterMode ::= TEXTUAL-CONVENTION
    STATUS      current
    DESCRIPTION
        "This enumeration indicates the group filter mode for an IPMC group
         address."
    SYNTAX      INTEGER { exclude(0), include(1) }

VTSSIpmcMvrGroupSrcListSourceType ::= TEXTUAL-CONVENTION
    STATUS      current
    DESCRIPTION
        "This enumeration indicates the source filtering type from IPMC."
    SYNTAX      INTEGER { deny(0), permit(1) }

VTSSIpmcMvrInterfaceQuerierStatus ::= TEXTUAL-CONVENTION
    STATUS      current
    DESCRIPTION
        "This enumeration indicates the Querier status for MVR VLAN interface."
    SYNTAX      INTEGER { disabled(-1), initial(0), idle(1), active(2) }

VTSSIpmcMvrVlanInterfaceMode ::= TEXTUAL-CONVENTION
    STATUS      current
    DESCRIPTION
        "This enumeration indicates the MVR VLAN interface's operational mode."
    SYNTAX      INTEGER { dynamic(0), compatible(1) }

VTSSIpmcMvrVlanInterfacePortRole ::= TEXTUAL-CONVENTION
    STATUS      current
    DESCRIPTION
        "This enumeration indicates the MVR port's operational role."
    SYNTAX      INTEGER { inactive(0), source(1), receiver(2) }

VTSSIpmcMvrVlanInterfaceTagging ::= TEXTUAL-CONVENTION
    STATUS      current
    DESCRIPTION
        "This enumeration indicates the VLAN tagging for IPMC control frames in
         MVR."
    SYNTAX      INTEGER { untagged(0), tagging(1) }

vtssIpmcMvrMibObjects OBJECT IDENTIFIER
    ::= { vtssIpmcMvrMib 1 }

vtssIpmcMvrConfig OBJECT IDENTIFIER
    ::= { vtssIpmcMvrMibObjects 2 }

vtssIpmcMvrConfigGlobals OBJECT IDENTIFIER
    ::= { vtssIpmcMvrConfig 1 }

vtssIpmcMvrConfigGlobalsAdminState OBJECT-TYPE
    SYNTAX      TruthValue
    MAX-ACCESS  read-write
    STATUS      current
    DESCRIPTION 
        "Enable/Disable the IPMC MVR global functionality."
    ::= { vtssIpmcMvrConfigGlobals 1 }

vtssIpmcMvrConfigPortTable OBJECT-TYPE
    SYNTAX      SEQUENCE OF VTSSIpmcMvrConfigPortEntry
    MAX-ACCESS  not-accessible
    STATUS      current
    DESCRIPTION 
        "This is a table for managing extra MVR helper features per port basis."
    ::= { vtssIpmcMvrConfig 2 }

vtssIpmcMvrConfigPortEntry OBJECT-TYPE
    SYNTAX      VTSSIpmcMvrConfigPortEntry
    MAX-ACCESS  not-accessible
    STATUS      current
    DESCRIPTION 
        "Each port has a set of parameters."
    INDEX       { vtssIpmcMvrConfigPortPortIndex }
    ::= { vtssIpmcMvrConfigPortTable 1 }

VTSSIpmcMvrConfigPortEntry ::= SEQUENCE {
    vtssIpmcMvrConfigPortPortIndex      VTSSInterfaceIndex,
    vtssIpmcMvrConfigPortDoImmediateLeave   TruthValue
}

vtssIpmcMvrConfigPortPortIndex OBJECT-TYPE
    SYNTAX      VTSSInterfaceIndex
    MAX-ACCESS  not-accessible
    STATUS      current
    DESCRIPTION 
        "Logical interface number of the physical port."
    ::= { vtssIpmcMvrConfigPortEntry 1 }

vtssIpmcMvrConfigPortDoImmediateLeave OBJECT-TYPE
    SYNTAX      TruthValue
    MAX-ACCESS  read-write
    STATUS      current
    DESCRIPTION 
        "Enable/Disable the MVR immediate leave functionality."
    ::= { vtssIpmcMvrConfigPortEntry 2 }

vtssIpmcMvrConfigInterfaceTable OBJECT-TYPE
    SYNTAX      SEQUENCE OF VTSSIpmcMvrConfigInterfaceEntry
    MAX-ACCESS  not-accessible
    STATUS      current
    DESCRIPTION 
        "This is a table for managing MVR VLAN interface entries."
    ::= { vtssIpmcMvrConfig 3 }

vtssIpmcMvrConfigInterfaceEntry OBJECT-TYPE
    SYNTAX      VTSSIpmcMvrConfigInterfaceEntry
    MAX-ACCESS  not-accessible
    STATUS      current
    DESCRIPTION 
        "Each entry has a set of parameters"
    INDEX       { vtssIpmcMvrConfigInterfaceIfIndex }
    ::= { vtssIpmcMvrConfigInterfaceTable 1 }

VTSSIpmcMvrConfigInterfaceEntry ::= SEQUENCE {
    vtssIpmcMvrConfigInterfaceIfIndex   VTSSInterfaceIndex,
    vtssIpmcMvrConfigInterfaceName      VTSSDisplayString,
    vtssIpmcMvrConfigInterfaceIgmpQuerierAddress    IpAddress,
    vtssIpmcMvrConfigInterfaceMode      VTSSIpmcMvrVlanInterfaceMode,
    vtssIpmcMvrConfigInterfaceTagging   VTSSIpmcMvrVlanInterfaceTagging,
    vtssIpmcMvrConfigInterfacePriority      VTSSUnsigned8,
    vtssIpmcMvrConfigInterfaceLastListenerQueryInt      Unsigned32,
    vtssIpmcMvrConfigInterfaceChannelProfile    VTSSDisplayString,
    vtssIpmcMvrConfigInterfaceAction    VTSSRowEditorState
}

vtssIpmcMvrConfigInterfaceIfIndex OBJECT-TYPE
    SYNTAX      VTSSInterfaceIndex
    MAX-ACCESS  not-accessible
    STATUS      current
    DESCRIPTION 
        "Logical interface number of the VLAN interface."
    ::= { vtssIpmcMvrConfigInterfaceEntry 1 }

vtssIpmcMvrConfigInterfaceName OBJECT-TYPE
    SYNTAX      VTSSDisplayString (SIZE(0..16))
    MAX-ACCESS  read-write
    STATUS      current
    DESCRIPTION 
        "MVR Name is an optional attribute to indicate the name of the specific
         MVR VLAN that user could easily associate the MVR VLAN purpose with its
         name."
    ::= { vtssIpmcMvrConfigInterfaceEntry 2 }

vtssIpmcMvrConfigInterfaceIgmpQuerierAddress OBJECT-TYPE
    SYNTAX      IpAddress
    MAX-ACCESS  read-write
    STATUS      current
    DESCRIPTION 
        "The static IPv4 source address of the specific MVR interface for seding
         IGMP Query message with respect to IGMP Querier election."
    ::= { vtssIpmcMvrConfigInterfaceEntry 3 }

vtssIpmcMvrConfigInterfaceMode OBJECT-TYPE
    SYNTAX      VTSSIpmcMvrVlanInterfaceMode
    MAX-ACCESS  read-write
    STATUS      current
    DESCRIPTION 
        "In Dynamic mode, MVR allows dynamic MVR membership reports on source
         ports. In Compatible mode, MVR membership reports are forbidden on
         source ports."
    ::= { vtssIpmcMvrConfigInterfaceEntry 4 }

vtssIpmcMvrConfigInterfaceTagging OBJECT-TYPE
    SYNTAX      VTSSIpmcMvrVlanInterfaceTagging
    MAX-ACCESS  read-write
    STATUS      current
    DESCRIPTION 
        "Specify whether the traversed IGMP/MLD control frames will be sent as
         Untagged or Tagged with MVR VID."
    ::= { vtssIpmcMvrConfigInterfaceEntry 5 }

vtssIpmcMvrConfigInterfacePriority OBJECT-TYPE
    SYNTAX      VTSSUnsigned8
    MAX-ACCESS  read-write
    STATUS      current
    DESCRIPTION 
        "Specify how the traversed IGMP/MLD control frames will be sent in
         prioritized manner in VLAN tag."
    ::= { vtssIpmcMvrConfigInterfaceEntry 6 }

vtssIpmcMvrConfigInterfaceLastListenerQueryInt OBJECT-TYPE
    SYNTAX      Unsigned32
    MAX-ACCESS  read-write
    STATUS      current
    DESCRIPTION 
        "This setting Last Listener/Member Query Interval is used to control
         IGMP protocol stack for fast aging mechanism. It defines the maximum
         time to wait for IGMP/MLD report memberships on a port before removing
         the port from multicast group membership. The value is in units of
         tenths of a seconds. The range is from 0 to 31744."
    ::= { vtssIpmcMvrConfigInterfaceEntry 7 }

vtssIpmcMvrConfigInterfaceChannelProfile OBJECT-TYPE
    SYNTAX      VTSSDisplayString (SIZE(0..16))
    MAX-ACCESS  read-write
    STATUS      current
    DESCRIPTION 
        "The profile used for the channel filtering condition in the specific
         MVR VLAN. Profile selected for designated interface channel is not
         allowed to have overlapped permit group address by comparing with other
         MVR VLAN interface's channel."
    ::= { vtssIpmcMvrConfigInterfaceEntry 8 }

vtssIpmcMvrConfigInterfaceAction OBJECT-TYPE
    SYNTAX      VTSSRowEditorState
    MAX-ACCESS  read-write
    STATUS      current
    DESCRIPTION 
        "Action"
    ::= { vtssIpmcMvrConfigInterfaceEntry 100 }

vtssIpmcMvrConfigInterfaceTableRowEditor OBJECT IDENTIFIER
    ::= { vtssIpmcMvrConfig 4 }

vtssIpmcMvrConfigInterfaceTableRowEditorIfIndex OBJECT-TYPE
    SYNTAX      VTSSInterfaceIndex
    MAX-ACCESS  read-write
    STATUS      current
    DESCRIPTION 
        "Logical interface number of the VLAN interface."
    ::= { vtssIpmcMvrConfigInterfaceTableRowEditor 1 }

vtssIpmcMvrConfigInterfaceTableRowEditorName OBJECT-TYPE
    SYNTAX      VTSSDisplayString (SIZE(0..16))
    MAX-ACCESS  read-write
    STATUS      current
    DESCRIPTION 
        "MVR Name is an optional attribute to indicate the name of the specific
         MVR VLAN that user could easily associate the MVR VLAN purpose with its
         name."
    ::= { vtssIpmcMvrConfigInterfaceTableRowEditor 2 }

vtssIpmcMvrConfigInterfaceTableRowEditorIgmpQuerierAddress OBJECT-TYPE
    SYNTAX      IpAddress
    MAX-ACCESS  read-write
    STATUS      current
    DESCRIPTION 
        "The static IPv4 source address of the specific MVR interface for seding
         IGMP Query message with respect to IGMP Querier election."
    ::= { vtssIpmcMvrConfigInterfaceTableRowEditor 3 }

vtssIpmcMvrConfigInterfaceTableRowEditorMode OBJECT-TYPE
    SYNTAX      VTSSIpmcMvrVlanInterfaceMode
    MAX-ACCESS  read-write
    STATUS      current
    DESCRIPTION 
        "In Dynamic mode, MVR allows dynamic MVR membership reports on source
         ports. In Compatible mode, MVR membership reports are forbidden on
         source ports."
    ::= { vtssIpmcMvrConfigInterfaceTableRowEditor 4 }

vtssIpmcMvrConfigInterfaceTableRowEditorTagging OBJECT-TYPE
    SYNTAX      VTSSIpmcMvrVlanInterfaceTagging
    MAX-ACCESS  read-write
    STATUS      current
    DESCRIPTION 
        "Specify whether the traversed IGMP/MLD control frames will be sent as
         Untagged or Tagged with MVR VID."
    ::= { vtssIpmcMvrConfigInterfaceTableRowEditor 5 }

vtssIpmcMvrConfigInterfaceTableRowEditorPriority OBJECT-TYPE
    SYNTAX      VTSSUnsigned8
    MAX-ACCESS  read-write
    STATUS      current
    DESCRIPTION 
        "Specify how the traversed IGMP/MLD control frames will be sent in
         prioritized manner in VLAN tag."
    ::= { vtssIpmcMvrConfigInterfaceTableRowEditor 6 }

vtssIpmcMvrConfigInterfaceTableRowEditorLastListenerQueryInt OBJECT-TYPE
    SYNTAX      Unsigned32
    MAX-ACCESS  read-write
    STATUS      current
    DESCRIPTION 
        "This setting Last Listener/Member Query Interval is used to control
         IGMP protocol stack for fast aging mechanism. It defines the maximum
         time to wait for IGMP/MLD report memberships on a port before removing
         the port from multicast group membership. The value is in units of
         tenths of a seconds. The range is from 0 to 31744."
    ::= { vtssIpmcMvrConfigInterfaceTableRowEditor 7 }

vtssIpmcMvrConfigInterfaceTableRowEditorChannelProfile OBJECT-TYPE
    SYNTAX      VTSSDisplayString (SIZE(0..16))
    MAX-ACCESS  read-write
    STATUS      current
    DESCRIPTION 
        "The profile used for the channel filtering condition in the specific
         MVR VLAN. Profile selected for designated interface channel is not
         allowed to have overlapped permit group address by comparing with other
         MVR VLAN interface's channel."
    ::= { vtssIpmcMvrConfigInterfaceTableRowEditor 8 }

vtssIpmcMvrConfigInterfaceTableRowEditorAction OBJECT-TYPE
    SYNTAX      VTSSRowEditorState
    MAX-ACCESS  read-write
    STATUS      current
    DESCRIPTION 
        "Action"
    ::= { vtssIpmcMvrConfigInterfaceTableRowEditor 100 }

vtssIpmcMvrConfigVlanPortTable OBJECT-TYPE
    SYNTAX      SEQUENCE OF VTSSIpmcMvrConfigVlanPortEntry
    MAX-ACCESS  not-accessible
    STATUS      current
    DESCRIPTION 
        "This is a table for managing MVR port roles of a specific MVR VLAN
         interface."
    ::= { vtssIpmcMvrConfig 5 }

vtssIpmcMvrConfigVlanPortEntry OBJECT-TYPE
    SYNTAX      VTSSIpmcMvrConfigVlanPortEntry
    MAX-ACCESS  not-accessible
    STATUS      current
    DESCRIPTION 
        "Each port has a set of parameters."
    INDEX       { vtssIpmcMvrConfigVlanPortIfIndex, vtssIpmcMvrConfigVlanPortPortIndex }
    ::= { vtssIpmcMvrConfigVlanPortTable 1 }

VTSSIpmcMvrConfigVlanPortEntry ::= SEQUENCE {
    vtssIpmcMvrConfigVlanPortIfIndex    VTSSInterfaceIndex,
    vtssIpmcMvrConfigVlanPortPortIndex      VTSSInterfaceIndex,
    vtssIpmcMvrConfigVlanPortRole   VTSSIpmcMvrVlanInterfacePortRole
}

vtssIpmcMvrConfigVlanPortIfIndex OBJECT-TYPE
    SYNTAX      VTSSInterfaceIndex
    MAX-ACCESS  not-accessible
    STATUS      current
    DESCRIPTION 
        "Logical interface number of the VLAN interface."
    ::= { vtssIpmcMvrConfigVlanPortEntry 1 }

vtssIpmcMvrConfigVlanPortPortIndex OBJECT-TYPE
    SYNTAX      VTSSInterfaceIndex
    MAX-ACCESS  not-accessible
    STATUS      current
    DESCRIPTION 
        "Logical interface number of the physical port."
    ::= { vtssIpmcMvrConfigVlanPortEntry 2 }

vtssIpmcMvrConfigVlanPortRole OBJECT-TYPE
    SYNTAX      VTSSIpmcMvrVlanInterfacePortRole
    MAX-ACCESS  read-write
    STATUS      current
    DESCRIPTION 
        "Configure a MVR port of the designated MVR VLAN as one of the following
         roles: Inactive, Source or Receiver. An inactive port does not
         participate MVR operations. Configure uplink ports that receive and
         send multicast data as a source port, and multicast subscribers cannot
         be directly connected to source ports. Configure a port as a receiver
         port if it is a subscriber port and should only receive multicast data,
         and a receiver port does not receive data unless it becomes a member of
         the multicast group by issuing IGMP/MLD control messages. Be Caution:
         MVR source ports are not recommended to be overlapped with management
         VLAN ports."
    ::= { vtssIpmcMvrConfigVlanPortEntry 3 }

vtssIpmcMvrStatus OBJECT IDENTIFIER
    ::= { vtssIpmcMvrMibObjects 3 }

vtssIpmcMvrStatusGroupAddressCount OBJECT IDENTIFIER
    ::= { vtssIpmcMvrStatus 1 }

vtssIpmcMvrStatusGroupAddressCountFromIgmp OBJECT-TYPE
    SYNTAX      Unsigned32
    MAX-ACCESS  read-only
    STATUS      current
    DESCRIPTION 
        "It is used to denote the total number of registered multicast group
         address from IGMP learning in MVR."
    ::= { vtssIpmcMvrStatusGroupAddressCount 1 }

vtssIpmcMvrStatusGroupAddressCountFromMld OBJECT-TYPE
    SYNTAX      Unsigned32
    MAX-ACCESS  read-only
    STATUS      current
    DESCRIPTION 
        "It is used to denote the total number of registered multicast group
         address from MLD learning in MVR."
    ::= { vtssIpmcMvrStatusGroupAddressCount 2 }

vtssIpmcMvrStatusIgmpVlanTable OBJECT-TYPE
    SYNTAX      SEQUENCE OF VTSSIpmcMvrStatusIgmpVlanEntry
    MAX-ACCESS  not-accessible
    STATUS      current
    DESCRIPTION 
        "This is a table for displaying the per VLAN interface status in MVR
         from IGMP protocol."
    ::= { vtssIpmcMvrStatus 2 }

vtssIpmcMvrStatusIgmpVlanEntry OBJECT-TYPE
    SYNTAX      VTSSIpmcMvrStatusIgmpVlanEntry
    MAX-ACCESS  not-accessible
    STATUS      current
    DESCRIPTION 
        "Each entry has a set of parameters."
    INDEX       { vtssIpmcMvrStatusIgmpVlanIfIndex }
    ::= { vtssIpmcMvrStatusIgmpVlanTable 1 }

VTSSIpmcMvrStatusIgmpVlanEntry ::= SEQUENCE {
    vtssIpmcMvrStatusIgmpVlanIfIndex    VTSSInterfaceIndex,
    vtssIpmcMvrStatusIgmpVlanQuerierStatus      VTSSIpmcMvrInterfaceQuerierStatus,
    vtssIpmcMvrStatusIgmpVlanActiveQuerierAddress   IpAddress,
    vtssIpmcMvrStatusIgmpVlanQuerierUptime      Unsigned32,
    vtssIpmcMvrStatusIgmpVlanQueryInterval      Unsigned32,
    vtssIpmcMvrStatusIgmpVlanStartupQueryCount      Unsigned32,
    vtssIpmcMvrStatusIgmpVlanQuerierExpiryTime      Unsigned32,
    vtssIpmcMvrStatusIgmpVlanCounterTxQuery     Unsigned32,
    vtssIpmcMvrStatusIgmpVlanCounterTxSpecificQuery     Unsigned32,
    vtssIpmcMvrStatusIgmpVlanCounterRxQuery     Unsigned32,
    vtssIpmcMvrStatusIgmpVlanCounterRxV1Join    Unsigned32,
    vtssIpmcMvrStatusIgmpVlanCounterRxV2Join    Unsigned32,
    vtssIpmcMvrStatusIgmpVlanCounterRxV2Leave   Unsigned32,
    vtssIpmcMvrStatusIgmpVlanCounterRxV3Join    Unsigned32,
    vtssIpmcMvrStatusIgmpVlanCounterRxErrors    Unsigned32
}

vtssIpmcMvrStatusIgmpVlanIfIndex OBJECT-TYPE
    SYNTAX      VTSSInterfaceIndex
    MAX-ACCESS  not-accessible
    STATUS      current
    DESCRIPTION 
        "Logical interface number of the VLAN interface."
    ::= { vtssIpmcMvrStatusIgmpVlanEntry 1 }

vtssIpmcMvrStatusIgmpVlanQuerierStatus OBJECT-TYPE
    SYNTAX      VTSSIpmcMvrInterfaceQuerierStatus
    MAX-ACCESS  read-only
    STATUS      current
    DESCRIPTION 
        "The IGMP Querier status of the specific VLAN interface."
    ::= { vtssIpmcMvrStatusIgmpVlanEntry 2 }

vtssIpmcMvrStatusIgmpVlanActiveQuerierAddress OBJECT-TYPE
    SYNTAX      IpAddress
    MAX-ACCESS  read-only
    STATUS      current
    DESCRIPTION 
        "The active IGMP Querier address on the specific VLAN interface."
    ::= { vtssIpmcMvrStatusIgmpVlanEntry 3 }

vtssIpmcMvrStatusIgmpVlanQuerierUptime OBJECT-TYPE
    SYNTAX      Unsigned32
    MAX-ACCESS  read-only
    STATUS      current
    DESCRIPTION 
        "It presents the in operation timer for the specific interface act as a
         IGMP Querier."
    ::= { vtssIpmcMvrStatusIgmpVlanEntry 4 }

vtssIpmcMvrStatusIgmpVlanQueryInterval OBJECT-TYPE
    SYNTAX      Unsigned32
    MAX-ACCESS  read-only
    STATUS      current
    DESCRIPTION 
        "This setting is used to control IGMP protocol stack as stated in
         RFC-3376 8.2."
    ::= { vtssIpmcMvrStatusIgmpVlanEntry 5 }

vtssIpmcMvrStatusIgmpVlanStartupQueryCount OBJECT-TYPE
    SYNTAX      Unsigned32
    MAX-ACCESS  read-only
    STATUS      current
    DESCRIPTION 
        "This setting is used to control IGMP protocol stack as stated in
         RFC-3376 8.7."
    ::= { vtssIpmcMvrStatusIgmpVlanEntry 6 }

vtssIpmcMvrStatusIgmpVlanQuerierExpiryTime OBJECT-TYPE
    SYNTAX      Unsigned32
    MAX-ACCESS  read-only
    STATUS      current
    DESCRIPTION 
        "This setting is used to control IGMP protocol stack as stated in
         RFC-3376 8.5."
    ::= { vtssIpmcMvrStatusIgmpVlanEntry 7 }

vtssIpmcMvrStatusIgmpVlanCounterTxQuery OBJECT-TYPE
    SYNTAX      Unsigned32
    MAX-ACCESS  read-only
    STATUS      current
    DESCRIPTION 
        "It presents the current packet count on the specific IGMP interface for
         transmitting IGMP Query control frames."
    ::= { vtssIpmcMvrStatusIgmpVlanEntry 8 }

vtssIpmcMvrStatusIgmpVlanCounterTxSpecificQuery OBJECT-TYPE
    SYNTAX      Unsigned32
    MAX-ACCESS  read-only
    STATUS      current
    DESCRIPTION 
        "It presents the current packet count on the specific IGMP interface for
         transmitting IGMP Specific Query control frames."
    ::= { vtssIpmcMvrStatusIgmpVlanEntry 9 }

vtssIpmcMvrStatusIgmpVlanCounterRxQuery OBJECT-TYPE
    SYNTAX      Unsigned32
    MAX-ACCESS  read-only
    STATUS      current
    DESCRIPTION 
        "It presents the current packet count on the specific IGMP interface for
         receiving IGMP Query control frames."
    ::= { vtssIpmcMvrStatusIgmpVlanEntry 10 }

vtssIpmcMvrStatusIgmpVlanCounterRxV1Join OBJECT-TYPE
    SYNTAX      Unsigned32
    MAX-ACCESS  read-only
    STATUS      current
    DESCRIPTION 
        "It presents the current packet count on the specific IGMP interface for
         receiving IGMPv1 Join control frames."
    ::= { vtssIpmcMvrStatusIgmpVlanEntry 11 }

vtssIpmcMvrStatusIgmpVlanCounterRxV2Join OBJECT-TYPE
    SYNTAX      Unsigned32
    MAX-ACCESS  read-only
    STATUS      current
    DESCRIPTION 
        "It presents the current packet count on the specific IGMP interface for
         receiving IGMPv2 Join control frames."
    ::= { vtssIpmcMvrStatusIgmpVlanEntry 12 }

vtssIpmcMvrStatusIgmpVlanCounterRxV2Leave OBJECT-TYPE
    SYNTAX      Unsigned32
    MAX-ACCESS  read-only
    STATUS      current
    DESCRIPTION 
        "It presents the current packet count on the specific IGMP interface for
         receiving IGMPv2 Leave control frames."
    ::= { vtssIpmcMvrStatusIgmpVlanEntry 13 }

vtssIpmcMvrStatusIgmpVlanCounterRxV3Join OBJECT-TYPE
    SYNTAX      Unsigned32
    MAX-ACCESS  read-only
    STATUS      current
    DESCRIPTION 
        "It presents the current packet count on the specific IGMP interface for
         receiving IGMPv3 Join control frames."
    ::= { vtssIpmcMvrStatusIgmpVlanEntry 14 }

vtssIpmcMvrStatusIgmpVlanCounterRxErrors OBJECT-TYPE
    SYNTAX      Unsigned32
    MAX-ACCESS  read-only
    STATUS      current
    DESCRIPTION 
        "It presents the current packet count on the specific IGMP interface for
         receiving invalid IGMP control frames."
    ::= { vtssIpmcMvrStatusIgmpVlanEntry 15 }

vtssIpmcMvrStatusIgmpGroupAddressTable OBJECT-TYPE
    SYNTAX      SEQUENCE OF VTSSIpmcMvrStatusIgmpGroupAddressEntry
    MAX-ACCESS  not-accessible
    STATUS      current
    DESCRIPTION 
        "This is a table for displaying the registered IPv4 multicast group
         address status in IGMP from MVR."
    ::= { vtssIpmcMvrStatus 3 }

vtssIpmcMvrStatusIgmpGroupAddressEntry OBJECT-TYPE
    SYNTAX      VTSSIpmcMvrStatusIgmpGroupAddressEntry
    MAX-ACCESS  not-accessible
    STATUS      current
    DESCRIPTION 
        "Each entry has a set of parameters."
    INDEX       { vtssIpmcMvrStatusIgmpGroupAddressIfIndex, vtssIpmcMvrStatusIgmpGroupAddressGroupAddress }
    ::= { vtssIpmcMvrStatusIgmpGroupAddressTable 1 }

VTSSIpmcMvrStatusIgmpGroupAddressEntry ::= SEQUENCE {
    vtssIpmcMvrStatusIgmpGroupAddressIfIndex    VTSSInterfaceIndex,
    vtssIpmcMvrStatusIgmpGroupAddressGroupAddress   IpAddress,
    vtssIpmcMvrStatusIgmpGroupAddressMemberPorts    VTSSPortList,
    vtssIpmcMvrStatusIgmpGroupAddressHardwareSwitch     TruthValue
}

vtssIpmcMvrStatusIgmpGroupAddressIfIndex OBJECT-TYPE
    SYNTAX      VTSSInterfaceIndex
    MAX-ACCESS  not-accessible
    STATUS      current
    DESCRIPTION 
        "Logical interface number of the VLAN interface."
    ::= { vtssIpmcMvrStatusIgmpGroupAddressEntry 1 }

vtssIpmcMvrStatusIgmpGroupAddressGroupAddress OBJECT-TYPE
    SYNTAX      IpAddress
    MAX-ACCESS  not-accessible
    STATUS      current
    DESCRIPTION 
        "Assigned IPv4 multicast address."
    ::= { vtssIpmcMvrStatusIgmpGroupAddressEntry 2 }

vtssIpmcMvrStatusIgmpGroupAddressMemberPorts OBJECT-TYPE
    SYNTAX      VTSSPortList
    MAX-ACCESS  read-only
    STATUS      current
    DESCRIPTION 
        "It is used to denote the memberships of the registered multicast group
         address from MVR."
    ::= { vtssIpmcMvrStatusIgmpGroupAddressEntry 3 }

vtssIpmcMvrStatusIgmpGroupAddressHardwareSwitch OBJECT-TYPE
    SYNTAX      TruthValue
    MAX-ACCESS  read-only
    STATUS      current
    DESCRIPTION 
        "It is used to denote whether the multicast traffic destined to the
         registered group address could be forwarding by switch hardware or not."
    ::= { vtssIpmcMvrStatusIgmpGroupAddressEntry 4 }

vtssIpmcMvrStatusIgmpGroupSrcListTable OBJECT-TYPE
    SYNTAX      SEQUENCE OF VTSSIpmcMvrStatusIgmpGroupSrcListEntry
    MAX-ACCESS  not-accessible
    STATUS      current
    DESCRIPTION 
        "This is a table for displaying the address SFM (a.k.a Source List
         Multicast) status in source list of the registered IPv4 multicast group
         in IGMP from MVR."
    ::= { vtssIpmcMvrStatus 4 }

vtssIpmcMvrStatusIgmpGroupSrcListEntry OBJECT-TYPE
    SYNTAX      VTSSIpmcMvrStatusIgmpGroupSrcListEntry
    MAX-ACCESS  not-accessible
    STATUS      current
    DESCRIPTION 
        "Each entry has a set of parameters."
    INDEX       { vtssIpmcMvrStatusIgmpGroupSrcListIfIndex, vtssIpmcMvrStatusIgmpGroupSrcListGroupAddress, vtssIpmcMvrStatusIgmpGroupSrcListPortIndex, vtssIpmcMvrStatusIgmpGroupSrcListHostAddress }
    ::= { vtssIpmcMvrStatusIgmpGroupSrcListTable 1 }

VTSSIpmcMvrStatusIgmpGroupSrcListEntry ::= SEQUENCE {
    vtssIpmcMvrStatusIgmpGroupSrcListIfIndex    VTSSInterfaceIndex,
    vtssIpmcMvrStatusIgmpGroupSrcListGroupAddress   IpAddress,
    vtssIpmcMvrStatusIgmpGroupSrcListPortIndex      VTSSInterfaceIndex,
    vtssIpmcMvrStatusIgmpGroupSrcListHostAddress    IpAddress,
    vtssIpmcMvrStatusIgmpGroupSrcListGroupFilterMode    VTSSIpmcMvrGroupSrcListGroupFilterMode,
    vtssIpmcMvrStatusIgmpGroupSrcListFilterTimer    Unsigned32,
    vtssIpmcMvrStatusIgmpGroupSrcListSourceType     VTSSIpmcMvrGroupSrcListSourceType,
    vtssIpmcMvrStatusIgmpGroupSrcListSourceTimer    Unsigned32,
    vtssIpmcMvrStatusIgmpGroupSrcListHardwareFilter     TruthValue
}

vtssIpmcMvrStatusIgmpGroupSrcListIfIndex OBJECT-TYPE
    SYNTAX      VTSSInterfaceIndex
    MAX-ACCESS  not-accessible
    STATUS      current
    DESCRIPTION 
        "Logical interface number of the VLAN interface."
    ::= { vtssIpmcMvrStatusIgmpGroupSrcListEntry 1 }

vtssIpmcMvrStatusIgmpGroupSrcListGroupAddress OBJECT-TYPE
    SYNTAX      IpAddress
    MAX-ACCESS  not-accessible
    STATUS      current
    DESCRIPTION 
        "Assigned IPv4 multicast address."
    ::= { vtssIpmcMvrStatusIgmpGroupSrcListEntry 2 }

vtssIpmcMvrStatusIgmpGroupSrcListPortIndex OBJECT-TYPE
    SYNTAX      VTSSInterfaceIndex
    MAX-ACCESS  not-accessible
    STATUS      current
    DESCRIPTION 
        "Logical interface number of the physical port."
    ::= { vtssIpmcMvrStatusIgmpGroupSrcListEntry 3 }

vtssIpmcMvrStatusIgmpGroupSrcListHostAddress OBJECT-TYPE
    SYNTAX      IpAddress
    MAX-ACCESS  not-accessible
    STATUS      current
    DESCRIPTION 
        "Assigned IPv4 source address."
    ::= { vtssIpmcMvrStatusIgmpGroupSrcListEntry 4 }

vtssIpmcMvrStatusIgmpGroupSrcListGroupFilterMode OBJECT-TYPE
    SYNTAX      VTSSIpmcMvrGroupSrcListGroupFilterMode
    MAX-ACCESS  read-only
    STATUS      current
    DESCRIPTION 
        "It is used to denote the source filtering mode of the specific
         registered multicast group address from MVR."
    ::= { vtssIpmcMvrStatusIgmpGroupSrcListEntry 5 }

vtssIpmcMvrStatusIgmpGroupSrcListFilterTimer OBJECT-TYPE
    SYNTAX      Unsigned32
    MAX-ACCESS  read-only
    STATUS      current
    DESCRIPTION 
        "It is used to count down the timer for the specific multicast group's
         filtering mode transition."
    ::= { vtssIpmcMvrStatusIgmpGroupSrcListEntry 6 }

vtssIpmcMvrStatusIgmpGroupSrcListSourceType OBJECT-TYPE
    SYNTAX      VTSSIpmcMvrGroupSrcListSourceType
    MAX-ACCESS  read-only
    STATUS      current
    DESCRIPTION 
        "It is used to denote the filtering type of the specific source address
         in multicasting to the registered group address."
    ::= { vtssIpmcMvrStatusIgmpGroupSrcListEntry 7 }

vtssIpmcMvrStatusIgmpGroupSrcListSourceTimer OBJECT-TYPE
    SYNTAX      Unsigned32
    MAX-ACCESS  read-only
    STATUS      current
    DESCRIPTION 
        "It is used to count down the timer for purging the specific source
         address from the registered multicast group's source list."
    ::= { vtssIpmcMvrStatusIgmpGroupSrcListEntry 8 }

vtssIpmcMvrStatusIgmpGroupSrcListHardwareFilter OBJECT-TYPE
    SYNTAX      TruthValue
    MAX-ACCESS  read-only
    STATUS      current
    DESCRIPTION 
        "It is used to denote whether the traffic destined to the multicast
         group address from the specific source address could be forwarding by
         switch hardware or not."
    ::= { vtssIpmcMvrStatusIgmpGroupSrcListEntry 9 }

vtssIpmcMvrStatusMldVlanTable OBJECT-TYPE
    SYNTAX      SEQUENCE OF VTSSIpmcMvrStatusMldVlanEntry
    MAX-ACCESS  not-accessible
    STATUS      current
    DESCRIPTION 
        "This is a table for displaying the per VLAN interface status in MVR
         from MLD protocol."
    ::= { vtssIpmcMvrStatus 5 }

vtssIpmcMvrStatusMldVlanEntry OBJECT-TYPE
    SYNTAX      VTSSIpmcMvrStatusMldVlanEntry
    MAX-ACCESS  not-accessible
    STATUS      current
    DESCRIPTION 
        "Each entry has a set of parameters."
    INDEX       { vtssIpmcMvrStatusMldVlanIfIndex }
    ::= { vtssIpmcMvrStatusMldVlanTable 1 }

VTSSIpmcMvrStatusMldVlanEntry ::= SEQUENCE {
    vtssIpmcMvrStatusMldVlanIfIndex     VTSSInterfaceIndex,
    vtssIpmcMvrStatusMldVlanQuerierStatus   VTSSIpmcMvrInterfaceQuerierStatus,
    vtssIpmcMvrStatusMldVlanActiveQuerierAddress    InetAddressIPv6,
    vtssIpmcMvrStatusMldVlanQuerierUptime   Unsigned32,
    vtssIpmcMvrStatusMldVlanQueryInterval   Unsigned32,
    vtssIpmcMvrStatusMldVlanStartupQueryCount   Unsigned32,
    vtssIpmcMvrStatusMldVlanQuerierExpiryTime   Unsigned32,
    vtssIpmcMvrStatusMldVlanCounterTxQuery      Unsigned32,
    vtssIpmcMvrStatusMldVlanCounterTxSpecificQuery      Unsigned32,
    vtssIpmcMvrStatusMldVlanCounterRxQuery      Unsigned32,
    vtssIpmcMvrStatusMldVlanCounterRxV1Report   Unsigned32,
    vtssIpmcMvrStatusMldVlanCounterRxV1Done     Unsigned32,
    vtssIpmcMvrStatusMldVlanCounterRxV2Report   Unsigned32,
    vtssIpmcMvrStatusMldVlanCounterRxErrors     Unsigned32
}

vtssIpmcMvrStatusMldVlanIfIndex OBJECT-TYPE
    SYNTAX      VTSSInterfaceIndex
    MAX-ACCESS  not-accessible
    STATUS      current
    DESCRIPTION 
        "Logical interface number of the VLAN interface."
    ::= { vtssIpmcMvrStatusMldVlanEntry 1 }

vtssIpmcMvrStatusMldVlanQuerierStatus OBJECT-TYPE
    SYNTAX      VTSSIpmcMvrInterfaceQuerierStatus
    MAX-ACCESS  read-only
    STATUS      current
    DESCRIPTION 
        "The MLD Querier status of the specific VLAN interface."
    ::= { vtssIpmcMvrStatusMldVlanEntry 2 }

vtssIpmcMvrStatusMldVlanActiveQuerierAddress OBJECT-TYPE
    SYNTAX      InetAddressIPv6
    MAX-ACCESS  read-only
    STATUS      current
    DESCRIPTION 
        "The active MLD Querier address on the specific VLAN interface."
    ::= { vtssIpmcMvrStatusMldVlanEntry 3 }

vtssIpmcMvrStatusMldVlanQuerierUptime OBJECT-TYPE
    SYNTAX      Unsigned32
    MAX-ACCESS  read-only
    STATUS      current
    DESCRIPTION 
        "It presents the in operation timer for the specific interface act as a
         MLD Querier."
    ::= { vtssIpmcMvrStatusMldVlanEntry 4 }

vtssIpmcMvrStatusMldVlanQueryInterval OBJECT-TYPE
    SYNTAX      Unsigned32
    MAX-ACCESS  read-only
    STATUS      current
    DESCRIPTION 
        "This setting is used to control MLD protocol stack as stated in
         RFC-3810 9.2."
    ::= { vtssIpmcMvrStatusMldVlanEntry 5 }

vtssIpmcMvrStatusMldVlanStartupQueryCount OBJECT-TYPE
    SYNTAX      Unsigned32
    MAX-ACCESS  read-only
    STATUS      current
    DESCRIPTION 
        "This setting is used to control MLD protocol stack as stated in
         RFC-3810 9.7."
    ::= { vtssIpmcMvrStatusMldVlanEntry 6 }

vtssIpmcMvrStatusMldVlanQuerierExpiryTime OBJECT-TYPE
    SYNTAX      Unsigned32
    MAX-ACCESS  read-only
    STATUS      current
    DESCRIPTION 
        "This setting is used to control MLD protocol stack as stated in
         RFC-3810 9.5."
    ::= { vtssIpmcMvrStatusMldVlanEntry 7 }

vtssIpmcMvrStatusMldVlanCounterTxQuery OBJECT-TYPE
    SYNTAX      Unsigned32
    MAX-ACCESS  read-only
    STATUS      current
    DESCRIPTION 
        "It presents the current packet count on the specific MLD interface for
         transmitting MLD Query control frames."
    ::= { vtssIpmcMvrStatusMldVlanEntry 8 }

vtssIpmcMvrStatusMldVlanCounterTxSpecificQuery OBJECT-TYPE
    SYNTAX      Unsigned32
    MAX-ACCESS  read-only
    STATUS      current
    DESCRIPTION 
        "It presents the current packet count on the specific MLD interface for
         transmitting MLD Specific Query control frames."
    ::= { vtssIpmcMvrStatusMldVlanEntry 9 }

vtssIpmcMvrStatusMldVlanCounterRxQuery OBJECT-TYPE
    SYNTAX      Unsigned32
    MAX-ACCESS  read-only
    STATUS      current
    DESCRIPTION 
        "It presents the current packet count on the specific MLD interface for
         receiving MLD Query control frames."
    ::= { vtssIpmcMvrStatusMldVlanEntry 10 }

vtssIpmcMvrStatusMldVlanCounterRxV1Report OBJECT-TYPE
    SYNTAX      Unsigned32
    MAX-ACCESS  read-only
    STATUS      current
    DESCRIPTION 
        "It presents the current packet count on the specific MLD interface for
         receiving MLDv1 Report control frames."
    ::= { vtssIpmcMvrStatusMldVlanEntry 11 }

vtssIpmcMvrStatusMldVlanCounterRxV1Done OBJECT-TYPE
    SYNTAX      Unsigned32
    MAX-ACCESS  read-only
    STATUS      current
    DESCRIPTION 
        "It presents the current packet count on the specific MLD interface for
         receiving MLDv1 Done control frames."
    ::= { vtssIpmcMvrStatusMldVlanEntry 12 }

vtssIpmcMvrStatusMldVlanCounterRxV2Report OBJECT-TYPE
    SYNTAX      Unsigned32
    MAX-ACCESS  read-only
    STATUS      current
    DESCRIPTION 
        "It presents the current packet count on the specific MLD interface for
         receiving MLDv2 Report control frames."
    ::= { vtssIpmcMvrStatusMldVlanEntry 13 }

vtssIpmcMvrStatusMldVlanCounterRxErrors OBJECT-TYPE
    SYNTAX      Unsigned32
    MAX-ACCESS  read-only
    STATUS      current
    DESCRIPTION 
        "It presents the current packet count on the specific MLD interface for
         receiving invalid MLD control frames."
    ::= { vtssIpmcMvrStatusMldVlanEntry 14 }

vtssIpmcMvrStatusMldGroupAddressTable OBJECT-TYPE
    SYNTAX      SEQUENCE OF VTSSIpmcMvrStatusMldGroupAddressEntry
    MAX-ACCESS  not-accessible
    STATUS      current
    DESCRIPTION 
        "This is a table for displaying the registered IPv6 multicast group
         address status in MLD from MVR."
    ::= { vtssIpmcMvrStatus 6 }

vtssIpmcMvrStatusMldGroupAddressEntry OBJECT-TYPE
    SYNTAX      VTSSIpmcMvrStatusMldGroupAddressEntry
    MAX-ACCESS  not-accessible
    STATUS      current
    DESCRIPTION 
        "Each entry has a set of parameters."
    INDEX       { vtssIpmcMvrStatusMldGroupAddressIfIndex, vtssIpmcMvrStatusMldGroupAddressGroupAddress }
    ::= { vtssIpmcMvrStatusMldGroupAddressTable 1 }

VTSSIpmcMvrStatusMldGroupAddressEntry ::= SEQUENCE {
    vtssIpmcMvrStatusMldGroupAddressIfIndex     VTSSInterfaceIndex,
    vtssIpmcMvrStatusMldGroupAddressGroupAddress    InetAddressIPv6,
    vtssIpmcMvrStatusMldGroupAddressMemberPorts     VTSSPortList,
    vtssIpmcMvrStatusMldGroupAddressHardwareSwitch      TruthValue
}

vtssIpmcMvrStatusMldGroupAddressIfIndex OBJECT-TYPE
    SYNTAX      VTSSInterfaceIndex
    MAX-ACCESS  not-accessible
    STATUS      current
    DESCRIPTION 
        "Logical interface number of the VLAN interface."
    ::= { vtssIpmcMvrStatusMldGroupAddressEntry 1 }

vtssIpmcMvrStatusMldGroupAddressGroupAddress OBJECT-TYPE
    SYNTAX      InetAddressIPv6
    MAX-ACCESS  not-accessible
    STATUS      current
    DESCRIPTION 
        "Assigned IPv6 multicast address."
    ::= { vtssIpmcMvrStatusMldGroupAddressEntry 2 }

vtssIpmcMvrStatusMldGroupAddressMemberPorts OBJECT-TYPE
    SYNTAX      VTSSPortList
    MAX-ACCESS  read-only
    STATUS      current
    DESCRIPTION 
        "It is used to denote the memberships of the registered multicast group
         address from MVR."
    ::= { vtssIpmcMvrStatusMldGroupAddressEntry 3 }

vtssIpmcMvrStatusMldGroupAddressHardwareSwitch OBJECT-TYPE
    SYNTAX      TruthValue
    MAX-ACCESS  read-only
    STATUS      current
    DESCRIPTION 
        "It is used to denote whether the multicast traffic destined to the
         registered group address could be forwarding by switch hardware or not."
    ::= { vtssIpmcMvrStatusMldGroupAddressEntry 4 }

vtssIpmcMvrStatusMldGroupSrcListTable OBJECT-TYPE
    SYNTAX      SEQUENCE OF VTSSIpmcMvrStatusMldGroupSrcListEntry
    MAX-ACCESS  not-accessible
    STATUS      current
    DESCRIPTION 
        "This is a table for displaying the address SFM (a.k.a Source List
         Multicast) status in source list of the registered IPv6 multicast group
         in MLD from MVR."
    ::= { vtssIpmcMvrStatus 7 }

vtssIpmcMvrStatusMldGroupSrcListEntry OBJECT-TYPE
    SYNTAX      VTSSIpmcMvrStatusMldGroupSrcListEntry
    MAX-ACCESS  not-accessible
    STATUS      current
    DESCRIPTION 
        "Each entry has a set of parameters."
    INDEX       { vtssIpmcMvrStatusMldGroupSrcListIfIndex, vtssIpmcMvrStatusMldGroupSrcListGroupAddress, vtssIpmcMvrStatusMldGroupSrcListPortIndex, vtssIpmcMvrStatusMldGroupSrcListHostAddress }
    ::= { vtssIpmcMvrStatusMldGroupSrcListTable 1 }

VTSSIpmcMvrStatusMldGroupSrcListEntry ::= SEQUENCE {
    vtssIpmcMvrStatusMldGroupSrcListIfIndex     VTSSInterfaceIndex,
    vtssIpmcMvrStatusMldGroupSrcListGroupAddress    InetAddressIPv6,
    vtssIpmcMvrStatusMldGroupSrcListPortIndex   VTSSInterfaceIndex,
    vtssIpmcMvrStatusMldGroupSrcListHostAddress     InetAddressIPv6,
    vtssIpmcMvrStatusMldGroupSrcListGroupFilterMode     VTSSIpmcMvrGroupSrcListGroupFilterMode,
    vtssIpmcMvrStatusMldGroupSrcListFilterTimer     Unsigned32,
    vtssIpmcMvrStatusMldGroupSrcListSourceType      VTSSIpmcMvrGroupSrcListSourceType,
    vtssIpmcMvrStatusMldGroupSrcListSourceTimer     Unsigned32,
    vtssIpmcMvrStatusMldGroupSrcListHardwareFilter      TruthValue
}

vtssIpmcMvrStatusMldGroupSrcListIfIndex OBJECT-TYPE
    SYNTAX      VTSSInterfaceIndex
    MAX-ACCESS  not-accessible
    STATUS      current
    DESCRIPTION 
        "Logical interface number of the VLAN interface."
    ::= { vtssIpmcMvrStatusMldGroupSrcListEntry 1 }

vtssIpmcMvrStatusMldGroupSrcListGroupAddress OBJECT-TYPE
    SYNTAX      InetAddressIPv6
    MAX-ACCESS  not-accessible
    STATUS      current
    DESCRIPTION 
        "Assigned IPv6 multicast address."
    ::= { vtssIpmcMvrStatusMldGroupSrcListEntry 2 }

vtssIpmcMvrStatusMldGroupSrcListPortIndex OBJECT-TYPE
    SYNTAX      VTSSInterfaceIndex
    MAX-ACCESS  not-accessible
    STATUS      current
    DESCRIPTION 
        "Logical interface number of the physical port."
    ::= { vtssIpmcMvrStatusMldGroupSrcListEntry 3 }

vtssIpmcMvrStatusMldGroupSrcListHostAddress OBJECT-TYPE
    SYNTAX      InetAddressIPv6
    MAX-ACCESS  not-accessible
    STATUS      current
    DESCRIPTION 
        "Assigned IPv6 source address."
    ::= { vtssIpmcMvrStatusMldGroupSrcListEntry 4 }

vtssIpmcMvrStatusMldGroupSrcListGroupFilterMode OBJECT-TYPE
    SYNTAX      VTSSIpmcMvrGroupSrcListGroupFilterMode
    MAX-ACCESS  read-only
    STATUS      current
    DESCRIPTION 
        "It is used to denote the source filtering mode of the specific
         registered multicast group address from MVR."
    ::= { vtssIpmcMvrStatusMldGroupSrcListEntry 5 }

vtssIpmcMvrStatusMldGroupSrcListFilterTimer OBJECT-TYPE
    SYNTAX      Unsigned32
    MAX-ACCESS  read-only
    STATUS      current
    DESCRIPTION 
        "It is used to count down the timer for the specific multicast group's
         filtering mode transition."
    ::= { vtssIpmcMvrStatusMldGroupSrcListEntry 6 }

vtssIpmcMvrStatusMldGroupSrcListSourceType OBJECT-TYPE
    SYNTAX      VTSSIpmcMvrGroupSrcListSourceType
    MAX-ACCESS  read-only
    STATUS      current
    DESCRIPTION 
        "It is used to denote the filtering type of the specific source address
         in multicasting to the registered group address."
    ::= { vtssIpmcMvrStatusMldGroupSrcListEntry 7 }

vtssIpmcMvrStatusMldGroupSrcListSourceTimer OBJECT-TYPE
    SYNTAX      Unsigned32
    MAX-ACCESS  read-only
    STATUS      current
    DESCRIPTION 
        "It is used to count down the timer for purging the specific source
         address from the registered multicast group's source list."
    ::= { vtssIpmcMvrStatusMldGroupSrcListEntry 8 }

vtssIpmcMvrStatusMldGroupSrcListHardwareFilter OBJECT-TYPE
    SYNTAX      TruthValue
    MAX-ACCESS  read-only
    STATUS      current
    DESCRIPTION 
        "It is used to denote whether the traffic destined to the multicast
         group address from the specific source address could be forwarding by
         switch hardware or not."
    ::= { vtssIpmcMvrStatusMldGroupSrcListEntry 9 }

vtssIpmcMvrControl OBJECT IDENTIFIER
    ::= { vtssIpmcMvrMibObjects 4 }

vtssIpmcMvrControlStatisticsClear OBJECT IDENTIFIER
    ::= { vtssIpmcMvrControl 1 }

vtssIpmcMvrControlStatisticsClearIfIndex OBJECT-TYPE
    SYNTAX      VTSSInterfaceIndex
    MAX-ACCESS  read-write
    STATUS      current
    DESCRIPTION 
        "Logical interface number of the VLAN interface."
    ::= { vtssIpmcMvrControlStatisticsClear 1 }

vtssIpmcMvrMibConformance OBJECT IDENTIFIER
    ::= { vtssIpmcMvrMib 2 }

vtssIpmcMvrMibCompliances OBJECT IDENTIFIER
    ::= { vtssIpmcMvrMibConformance 1 }

vtssIpmcMvrMibGroups OBJECT IDENTIFIER
    ::= { vtssIpmcMvrMibConformance 2 }

vtssIpmcMvrConfigGlobalsInfoGroup OBJECT-GROUP
    OBJECTS     { vtssIpmcMvrConfigGlobalsAdminState }
    STATUS      current
    DESCRIPTION
        "A collection of objects suitable for bulk operations."
    ::= { vtssIpmcMvrMibGroups 1 }

vtssIpmcMvrConfigPortTableInfoGroup OBJECT-GROUP
    OBJECTS     { vtssIpmcMvrConfigPortDoImmediateLeave }
    STATUS      current
    DESCRIPTION
        "A collection of objects suitable for bulk operations."
    ::= { vtssIpmcMvrMibGroups 2 }

vtssIpmcMvrConfigInterfaceTableInfoGroup OBJECT-GROUP
    OBJECTS     { vtssIpmcMvrConfigInterfaceName, 
                  vtssIpmcMvrConfigInterfaceIgmpQuerierAddress, 
                  vtssIpmcMvrConfigInterfaceMode, 
                  vtssIpmcMvrConfigInterfaceTagging, 
                  vtssIpmcMvrConfigInterfacePriority, 
                  vtssIpmcMvrConfigInterfaceLastListenerQueryInt, 
                  vtssIpmcMvrConfigInterfaceChannelProfile, 
                  vtssIpmcMvrConfigInterfaceAction }
    STATUS      current
    DESCRIPTION
        "A collection of objects suitable for bulk operations."
    ::= { vtssIpmcMvrMibGroups 3 }

vtssIpmcMvrConfigInterfaceTableRowEditorInfoGroup OBJECT-GROUP
    OBJECTS     { vtssIpmcMvrConfigInterfaceTableRowEditorIfIndex, 
                  vtssIpmcMvrConfigInterfaceTableRowEditorName, 
                  vtssIpmcMvrConfigInterfaceTableRowEditorIgmpQuerierAddress, 
                  vtssIpmcMvrConfigInterfaceTableRowEditorMode, 
                  vtssIpmcMvrConfigInterfaceTableRowEditorTagging, 
                  vtssIpmcMvrConfigInterfaceTableRowEditorPriority, 
                  vtssIpmcMvrConfigInterfaceTableRowEditorLastListenerQueryInt, 
                  vtssIpmcMvrConfigInterfaceTableRowEditorChannelProfile, 
                  vtssIpmcMvrConfigInterfaceTableRowEditorAction }
    STATUS      current
    DESCRIPTION
        "A collection of objects suitable for bulk operations."
    ::= { vtssIpmcMvrMibGroups 4 }

vtssIpmcMvrConfigVlanPortTableInfoGroup OBJECT-GROUP
    OBJECTS     { vtssIpmcMvrConfigVlanPortRole }
    STATUS      current
    DESCRIPTION
        "A collection of objects suitable for bulk operations."
    ::= { vtssIpmcMvrMibGroups 5 }

vtssIpmcMvrStatusGroupAddressCountInfoGroup OBJECT-GROUP
    OBJECTS     { vtssIpmcMvrStatusGroupAddressCountFromIgmp, 
                  vtssIpmcMvrStatusGroupAddressCountFromMld }
    STATUS      current
    DESCRIPTION
        "A collection of objects suitable for bulk operations."
    ::= { vtssIpmcMvrMibGroups 6 }

vtssIpmcMvrStatusIgmpVlanTableInfoGroup OBJECT-GROUP
    OBJECTS     { vtssIpmcMvrStatusIgmpVlanQuerierStatus, 
                  vtssIpmcMvrStatusIgmpVlanActiveQuerierAddress, 
                  vtssIpmcMvrStatusIgmpVlanQuerierUptime, 
                  vtssIpmcMvrStatusIgmpVlanQueryInterval, 
                  vtssIpmcMvrStatusIgmpVlanStartupQueryCount, 
                  vtssIpmcMvrStatusIgmpVlanQuerierExpiryTime, 
                  vtssIpmcMvrStatusIgmpVlanCounterTxQuery, 
                  vtssIpmcMvrStatusIgmpVlanCounterTxSpecificQuery, 
                  vtssIpmcMvrStatusIgmpVlanCounterRxQuery, 
                  vtssIpmcMvrStatusIgmpVlanCounterRxV1Join, 
                  vtssIpmcMvrStatusIgmpVlanCounterRxV2Join, 
                  vtssIpmcMvrStatusIgmpVlanCounterRxV2Leave, 
                  vtssIpmcMvrStatusIgmpVlanCounterRxV3Join, 
                  vtssIpmcMvrStatusIgmpVlanCounterRxErrors }
    STATUS      current
    DESCRIPTION
        "A collection of objects suitable for bulk operations."
    ::= { vtssIpmcMvrMibGroups 7 }

vtssIpmcMvrStatusIgmpGroupAddressTableInfoGroup OBJECT-GROUP
    OBJECTS     { vtssIpmcMvrStatusIgmpGroupAddressMemberPorts, 
                  vtssIpmcMvrStatusIgmpGroupAddressHardwareSwitch }
    STATUS      current
    DESCRIPTION
        "A collection of objects suitable for bulk operations."
    ::= { vtssIpmcMvrMibGroups 8 }

vtssIpmcMvrStatusIgmpGroupSrcListTableInfoGroup OBJECT-GROUP
    OBJECTS     { vtssIpmcMvrStatusIgmpGroupSrcListGroupFilterMode, 
                  vtssIpmcMvrStatusIgmpGroupSrcListFilterTimer, 
                  vtssIpmcMvrStatusIgmpGroupSrcListSourceType, 
                  vtssIpmcMvrStatusIgmpGroupSrcListSourceTimer, 
                  vtssIpmcMvrStatusIgmpGroupSrcListHardwareFilter }
    STATUS      current
    DESCRIPTION
        "A collection of objects suitable for bulk operations."
    ::= { vtssIpmcMvrMibGroups 9 }

vtssIpmcMvrStatusMldVlanTableInfoGroup OBJECT-GROUP
    OBJECTS     { vtssIpmcMvrStatusMldVlanQuerierStatus, 
                  vtssIpmcMvrStatusMldVlanActiveQuerierAddress, 
                  vtssIpmcMvrStatusMldVlanQuerierUptime, 
                  vtssIpmcMvrStatusMldVlanQueryInterval, 
                  vtssIpmcMvrStatusMldVlanStartupQueryCount, 
                  vtssIpmcMvrStatusMldVlanQuerierExpiryTime, 
                  vtssIpmcMvrStatusMldVlanCounterTxQuery, 
                  vtssIpmcMvrStatusMldVlanCounterTxSpecificQuery, 
                  vtssIpmcMvrStatusMldVlanCounterRxQuery, 
                  vtssIpmcMvrStatusMldVlanCounterRxV1Report, 
                  vtssIpmcMvrStatusMldVlanCounterRxV1Done, 
                  vtssIpmcMvrStatusMldVlanCounterRxV2Report, 
                  vtssIpmcMvrStatusMldVlanCounterRxErrors }
    STATUS      current
    DESCRIPTION
        "A collection of objects suitable for bulk operations."
    ::= { vtssIpmcMvrMibGroups 10 }

vtssIpmcMvrStatusMldGroupAddressTableInfoGroup OBJECT-GROUP
    OBJECTS     { vtssIpmcMvrStatusMldGroupAddressMemberPorts, 
                  vtssIpmcMvrStatusMldGroupAddressHardwareSwitch }
    STATUS      current
    DESCRIPTION
        "A collection of objects suitable for bulk operations."
    ::= { vtssIpmcMvrMibGroups 11 }

vtssIpmcMvrStatusMldGroupSrcListTableInfoGroup OBJECT-GROUP
    OBJECTS     { vtssIpmcMvrStatusMldGroupSrcListGroupFilterMode, 
                  vtssIpmcMvrStatusMldGroupSrcListFilterTimer, 
                  vtssIpmcMvrStatusMldGroupSrcListSourceType, 
                  vtssIpmcMvrStatusMldGroupSrcListSourceTimer, 
                  vtssIpmcMvrStatusMldGroupSrcListHardwareFilter }
    STATUS      current
    DESCRIPTION
        "A collection of objects suitable for bulk operations."
    ::= { vtssIpmcMvrMibGroups 12 }

vtssIpmcMvrControlStatisticsClearInfoGroup OBJECT-GROUP
    OBJECTS     { vtssIpmcMvrControlStatisticsClearIfIndex }
    STATUS      current
    DESCRIPTION
        "A collection of objects suitable for bulk operations."
    ::= { vtssIpmcMvrMibGroups 13 }

vtssIpmcMvrMibCompliance MODULE-COMPLIANCE
    STATUS      current
    DESCRIPTION
        "The compliance statement for the implementation."

    MODULE      -- this module

        MANDATORY-GROUPS        { vtssIpmcMvrConfigGlobalsInfoGroup, 
                  vtssIpmcMvrConfigPortTableInfoGroup, 
                  vtssIpmcMvrConfigInterfaceTableInfoGroup, 
                  vtssIpmcMvrConfigInterfaceTableRowEditorInfoGroup, 
                  vtssIpmcMvrConfigVlanPortTableInfoGroup, 
                  vtssIpmcMvrStatusGroupAddressCountInfoGroup, 
                  vtssIpmcMvrStatusIgmpVlanTableInfoGroup, 
                  vtssIpmcMvrStatusIgmpGroupAddressTableInfoGroup, 
                  vtssIpmcMvrStatusIgmpGroupSrcListTableInfoGroup, 
                  vtssIpmcMvrStatusMldVlanTableInfoGroup, 
                  vtssIpmcMvrStatusMldGroupAddressTableInfoGroup, 
                  vtssIpmcMvrStatusMldGroupSrcListTableInfoGroup, 
                  vtssIpmcMvrControlStatisticsClearInfoGroup }

    ::= { vtssIpmcMvrMibCompliances 1 }

END
