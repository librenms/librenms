-- *****************************************************************
-- SYSUTIL-MIB:  Vitesse private MIB
--
-- Copyright (c) 2002-2013 Vitesse Semiconductor Corporation "Vitesse".
-- All Rights Reserved.
--
-- ****************************************************************

VTSS-SYSUTIL-MIB DEFINITIONS ::= BEGIN

IMPORTS
    MODULE-COMPLIANCE, OBJECT-GROUP
        FROM SNMPv2-CONF
    MODULE-IDENTITY, OBJECT-TYPE
        FROM SNMPv2-SMI
    TEXTUAL-CONVENTION
        FROM SNMPv2-TC
    vtssSwitchMgmt
        FROM VTSS-SMI
    Integer32 FROM SNMPv2-SMI
    Unsigned32 FROM SNMPv2-SMI
    TruthValue FROM SNMPv2-TC
    VTSSDisplayString FROM VTSS-TC
    ;

vtssSysutilMib MODULE-IDENTITY
    LAST-UPDATED "201410100000Z"
    ORGANIZATION
        "Vitesse Semiconductor Corporation"
    CONTACT-INFO
        "Application support <application_support@vitesse.com>"
    DESCRIPTION
        "This is a private version of SysUtil"
    REVISION    "201410100000Z"
    DESCRIPTION
        "Editorial changes"
    REVISION    "201407010000Z"
    DESCRIPTION
        "Initial version"
    ::= { vtssSwitchMgmt 24 }


VTSSSysutilPowerSupplyStateType ::= TEXTUAL-CONVENTION
    STATUS      current
    DESCRIPTION
        "This enumeration defines the type of power supply state."
    SYNTAX      INTEGER { active(0), standby(1), notPresent(2) }

VTSSSysutilRebootType ::= TEXTUAL-CONVENTION
    STATUS      current
    DESCRIPTION
        "This enumeration defines the type of reboot."
    SYNTAX      INTEGER { noReboot(0), coldReboot(1), warmReboot(2) }

vtssSysutilMibObjects OBJECT IDENTIFIER
    ::= { vtssSysutilMib 1 }

vtssSysutilCapabilities OBJECT IDENTIFIER
    ::= { vtssSysutilMibObjects 1 }

vtssSysutilCapabilitiesWarmRebootSupported OBJECT-TYPE
    SYNTAX      TruthValue
    MAX-ACCESS  read-only
    STATUS      current
    DESCRIPTION 
        "Indicate if warm restart is supported or not. true means it is
         supported. false means it is not supported."
    ::= { vtssSysutilCapabilities 1 }

vtssSysutilStatus OBJECT IDENTIFIER
    ::= { vtssSysutilMibObjects 3 }

vtssSysutilStatusCpuLoad OBJECT IDENTIFIER
    ::= { vtssSysutilStatus 1 }

vtssSysutilStatusCpuLoadAverage100msec OBJECT-TYPE
    SYNTAX      Unsigned32
    MAX-ACCESS  read-only
    STATUS      current
    DESCRIPTION 
        "Average CPU load (%) in 100 milli-seconds."
    ::= { vtssSysutilStatusCpuLoad 1 }

vtssSysutilStatusCpuLoadAverage1sec OBJECT-TYPE
    SYNTAX      Unsigned32
    MAX-ACCESS  read-only
    STATUS      current
    DESCRIPTION 
        "Average CPU load (%) in 1 second."
    ::= { vtssSysutilStatusCpuLoad 2 }

vtssSysutilStatusCpuLoadAverage10sec OBJECT-TYPE
    SYNTAX      Unsigned32
    MAX-ACCESS  read-only
    STATUS      current
    DESCRIPTION 
        "Average CPU load (%) in 10 seconds."
    ::= { vtssSysutilStatusCpuLoad 3 }

vtssSysutilStatusPowerSupplyTable OBJECT-TYPE
    SYNTAX      SEQUENCE OF VTSSSysutilStatusPowerSupplyEntry
    MAX-ACCESS  not-accessible
    STATUS      current
    DESCRIPTION 
        "Table of power supply status."
    ::= { vtssSysutilStatus 2 }

vtssSysutilStatusPowerSupplyEntry OBJECT-TYPE
    SYNTAX      VTSSSysutilStatusPowerSupplyEntry
    MAX-ACCESS  not-accessible
    STATUS      current
    DESCRIPTION 
        "Each row contains the power supply status."
    INDEX       { vtssSysutilStatusPowerSupplySwitchId, vtssSysutilStatusPowerSupplyPsuId }
    ::= { vtssSysutilStatusPowerSupplyTable 1 }

VTSSSysutilStatusPowerSupplyEntry ::= SEQUENCE {
    vtssSysutilStatusPowerSupplySwitchId    Integer32,
    vtssSysutilStatusPowerSupplyPsuId   Integer32,
    vtssSysutilStatusPowerSupplyState   VTSSSysutilPowerSupplyStateType,
    vtssSysutilStatusPowerSupplyDescription     VTSSDisplayString
}

vtssSysutilStatusPowerSupplySwitchId OBJECT-TYPE
    SYNTAX      Integer32 (1..16)
    MAX-ACCESS  not-accessible
    STATUS      current
    DESCRIPTION 
        "The identification of switch."
    ::= { vtssSysutilStatusPowerSupplyEntry 1 }

vtssSysutilStatusPowerSupplyPsuId OBJECT-TYPE
    SYNTAX      Integer32 (1..2)
    MAX-ACCESS  not-accessible
    STATUS      current
    DESCRIPTION 
        "The identification of power supply."
    ::= { vtssSysutilStatusPowerSupplyEntry 2 }

vtssSysutilStatusPowerSupplyState OBJECT-TYPE
    SYNTAX      VTSSSysutilPowerSupplyStateType
    MAX-ACCESS  read-only
    STATUS      current
    DESCRIPTION 
        "The state of power supply."
    ::= { vtssSysutilStatusPowerSupplyEntry 3 }

vtssSysutilStatusPowerSupplyDescription OBJECT-TYPE
    SYNTAX      VTSSDisplayString (SIZE(0..30))
    MAX-ACCESS  read-only
    STATUS      current
    DESCRIPTION 
        "The description of power supply."
    ::= { vtssSysutilStatusPowerSupplyEntry 4 }

vtssSysutilControl OBJECT IDENTIFIER
    ::= { vtssSysutilMibObjects 4 }

vtssSysutilControlRebootTable OBJECT-TYPE
    SYNTAX      SEQUENCE OF VTSSSysutilControlRebootEntry
    MAX-ACCESS  not-accessible
    STATUS      current
    DESCRIPTION 
        "This is a table to reboot a swicth"
    ::= { vtssSysutilControl 1 }

vtssSysutilControlRebootEntry OBJECT-TYPE
    SYNTAX      VTSSSysutilControlRebootEntry
    MAX-ACCESS  not-accessible
    STATUS      current
    DESCRIPTION 
        "Each switch has a set of parameters"
    INDEX       { vtssSysutilControlRebootSwitchId }
    ::= { vtssSysutilControlRebootTable 1 }

VTSSSysutilControlRebootEntry ::= SEQUENCE {
    vtssSysutilControlRebootSwitchId    Integer32,
    vtssSysutilControlRebootType    VTSSSysutilRebootType
}

vtssSysutilControlRebootSwitchId OBJECT-TYPE
    SYNTAX      Integer32 (1..16)
    MAX-ACCESS  not-accessible
    STATUS      current
    DESCRIPTION 
        "The identification of switch."
    ::= { vtssSysutilControlRebootEntry 1 }

vtssSysutilControlRebootType OBJECT-TYPE
    SYNTAX      VTSSSysutilRebootType
    MAX-ACCESS  read-write
    STATUS      current
    DESCRIPTION 
        "Type of reboot. noReboot(0) does not reboot. coldReboot(1) is to do
         cold reboot. warmReboot(2) is to do warm reboot, but this is optional.
         The OID of vtssSysutilCapabilitiesWarmRebootSupported tells if warm
         reboot is supported or not."
    ::= { vtssSysutilControlRebootEntry 2 }

vtssSysutilMibConformance OBJECT IDENTIFIER
    ::= { vtssSysutilMib 2 }

vtssSysutilMibCompliances OBJECT IDENTIFIER
    ::= { vtssSysutilMibConformance 1 }

vtssSysutilMibGroups OBJECT IDENTIFIER
    ::= { vtssSysutilMibConformance 2 }

vtssSysutilCapabilitiesInfoGroup OBJECT-GROUP
    OBJECTS     { vtssSysutilCapabilitiesWarmRebootSupported }
    STATUS      current
    DESCRIPTION
        "A collection of objects suitable for bulk operations."
    ::= { vtssSysutilMibGroups 1 }

vtssSysutilStatusCpuLoadInfoGroup OBJECT-GROUP
    OBJECTS     { vtssSysutilStatusCpuLoadAverage100msec, 
                  vtssSysutilStatusCpuLoadAverage1sec, 
                  vtssSysutilStatusCpuLoadAverage10sec }
    STATUS      current
    DESCRIPTION
        "A collection of objects suitable for bulk operations."
    ::= { vtssSysutilMibGroups 2 }

vtssSysutilStatusPowerSupplyInfoGroup OBJECT-GROUP
    OBJECTS     { vtssSysutilStatusPowerSupplyState, 
                  vtssSysutilStatusPowerSupplyDescription }
    STATUS      current
    DESCRIPTION
        "A collection of objects suitable for bulk operations."
    ::= { vtssSysutilMibGroups 3 }

vtssSysutilControlRebootInfoGroup OBJECT-GROUP
    OBJECTS     { vtssSysutilControlRebootType }
    STATUS      current
    DESCRIPTION
        "A collection of objects suitable for bulk operations."
    ::= { vtssSysutilMibGroups 4 }

vtssSysutilMibCompliance MODULE-COMPLIANCE
    STATUS      current
    DESCRIPTION
        "The compliance statement for the implementation."

    MODULE      -- this module

        MANDATORY-GROUPS        { vtssSysutilCapabilitiesInfoGroup, 
                  vtssSysutilStatusCpuLoadInfoGroup, 
                  vtssSysutilStatusPowerSupplyInfoGroup, 
                  vtssSysutilControlRebootInfoGroup }

    ::= { vtssSysutilMibCompliances 1 }

END
