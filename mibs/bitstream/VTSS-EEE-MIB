-- *****************************************************************
-- EEE-MIB:  Vitesse private MIB
--
-- Copyright (c) 2002-2013 Vitesse Semiconductor Corporation "Vitesse".
-- All Rights Reserved.
--
-- ****************************************************************

VTSS-EEE-MIB DEFINITIONS ::= BEGIN

IMPORTS
    MODULE-COMPLIANCE, OBJECT-GROUP
        FROM SNMPv2-CONF
    MODULE-IDENTITY, OBJECT-TYPE
        FROM SNMPv2-SMI
    TEXTUAL-CONVENTION
        FROM SNMPv2-TC
    vtssSwitchMgmt
        FROM VTSS-SMI
    Integer32 FROM SNMPv2-SMI
    TruthValue FROM SNMPv2-TC
    VTSSInterfaceIndex FROM VTSS-TC
    VTSSUnsigned8 FROM VTSS-TC
    ;

vtssEeeMib MODULE-IDENTITY
    LAST-UPDATED "201407240000Z"
    ORGANIZATION
        "Vitesse Semiconductor Corporation"
    CONTACT-INFO
        "Application support <application_support@vitesse.com>"
    DESCRIPTION
        "This is a private version of Energy Efficient Ethernet(EEE). "
    REVISION    "201407240000Z"
    DESCRIPTION
        "Initial version"
    ::= { vtssSwitchMgmt 74 }


VTSSEeePreference ::= TEXTUAL-CONVENTION
    STATUS      current
    DESCRIPTION
        "This enumeration defines the types of optimization preferences, either
         maximum power savings or low traffic latency."
    SYNTAX      INTEGER { latency(0), power(1) }

VTSSEeeQueueType ::= TEXTUAL-CONVENTION
    STATUS      current
    DESCRIPTION
        "This enumeration defines the types of egress port queues."
    SYNTAX      INTEGER { normal(0), urgent(1) }

VTSSEeeStatusType ::= TEXTUAL-CONVENTION
    STATUS      current
    DESCRIPTION
        "This enumeration defines the feature status."
    SYNTAX      INTEGER { no(0), yes(1), notSupported(2) }

vtssEeeMibObjects OBJECT IDENTIFIER
    ::= { vtssEeeMib 1 }

vtssEeeCapabilities OBJECT IDENTIFIER
    ::= { vtssEeeMibObjects 1 }

vtssEeeCapabilitiesGlobals OBJECT IDENTIFIER
    ::= { vtssEeeCapabilities 1 }

vtssEeeCapabilitiesGlobalsOptimizationPreferences OBJECT-TYPE
    SYNTAX      TruthValue
    MAX-ACCESS  read-only
    STATUS      current
    DESCRIPTION 
        "Indicates whether device supports optimization preferences, true means
         supported. false means not supported."
    ::= { vtssEeeCapabilitiesGlobals 1 }

vtssEeeCapabilitiesInterfaceTable OBJECT-TYPE
    SYNTAX      SEQUENCE OF VTSSEeeCapabilitiesInterfaceEntry
    MAX-ACCESS  not-accessible
    STATUS      current
    DESCRIPTION 
        "This is a table to interface capabilities"
    ::= { vtssEeeCapabilities 2 }

vtssEeeCapabilitiesInterfaceEntry OBJECT-TYPE
    SYNTAX      VTSSEeeCapabilitiesInterfaceEntry
    MAX-ACCESS  not-accessible
    STATUS      current
    DESCRIPTION 
        "Each interface has a set of capability parameters"
    INDEX       { vtssEeeCapabilitiesInterfaceIfIndex }
    ::= { vtssEeeCapabilitiesInterfaceTable 1 }

VTSSEeeCapabilitiesInterfaceEntry ::= SEQUENCE {
    vtssEeeCapabilitiesInterfaceIfIndex     VTSSInterfaceIndex,
    vtssEeeCapabilitiesInterfaceMaxEgressQueues     VTSSUnsigned8,
    vtssEeeCapabilitiesInterfaceEEE     TruthValue
}

vtssEeeCapabilitiesInterfaceIfIndex OBJECT-TYPE
    SYNTAX      VTSSInterfaceIndex
    MAX-ACCESS  not-accessible
    STATUS      current
    DESCRIPTION 
        "Logical interface number."
    ::= { vtssEeeCapabilitiesInterfaceEntry 1 }

vtssEeeCapabilitiesInterfaceMaxEgressQueues OBJECT-TYPE
    SYNTAX      VTSSUnsigned8
    MAX-ACCESS  read-only
    STATUS      current
    DESCRIPTION 
        "Maximum number of supported egress port queues."
    ::= { vtssEeeCapabilitiesInterfaceEntry 2 }

vtssEeeCapabilitiesInterfaceEEE OBJECT-TYPE
    SYNTAX      TruthValue
    MAX-ACCESS  read-only
    STATUS      current
    DESCRIPTION 
        "Indicates whether interface supports EEE(IEEE 802.3az). true means EEE
         supported. false means not supported."
    ::= { vtssEeeCapabilitiesInterfaceEntry 3 }

vtssEeeConfig OBJECT IDENTIFIER
    ::= { vtssEeeMibObjects 2 }

vtssEeeConfigGlobals OBJECT IDENTIFIER
    ::= { vtssEeeConfig 1 }

vtssEeeConfigGlobalsOptimizationPreferences OBJECT-TYPE
    SYNTAX      VTSSEeePreference
    MAX-ACCESS  read-write
    STATUS      current
    DESCRIPTION 
        "EEE optimization preferences, either maximum power saving or low
         traffic latency."
    ::= { vtssEeeConfigGlobals 1 }

vtssEeeConfigInterface OBJECT IDENTIFIER
    ::= { vtssEeeConfig 2 }

vtssEeeConfigInterfaceParamTable OBJECT-TYPE
    SYNTAX      SEQUENCE OF VTSSEeeConfigInterfaceParamEntry
    MAX-ACCESS  not-accessible
    STATUS      current
    DESCRIPTION 
        "This is a table to configure EEE configurations for a specific
         interface."
    ::= { vtssEeeConfigInterface 1 }

vtssEeeConfigInterfaceParamEntry OBJECT-TYPE
    SYNTAX      VTSSEeeConfigInterfaceParamEntry
    MAX-ACCESS  not-accessible
    STATUS      current
    DESCRIPTION 
        "Each interface has a set of EEE configurable parameters"
    INDEX       { vtssEeeConfigInterfaceParamIfIndex }
    ::= { vtssEeeConfigInterfaceParamTable 1 }

VTSSEeeConfigInterfaceParamEntry ::= SEQUENCE {
    vtssEeeConfigInterfaceParamIfIndex      VTSSInterfaceIndex,
    vtssEeeConfigInterfaceParamEnableEEE    TruthValue
}

vtssEeeConfigInterfaceParamIfIndex OBJECT-TYPE
    SYNTAX      VTSSInterfaceIndex
    MAX-ACCESS  not-accessible
    STATUS      current
    DESCRIPTION 
        "Logical interface number."
    ::= { vtssEeeConfigInterfaceParamEntry 1 }

vtssEeeConfigInterfaceParamEnableEEE OBJECT-TYPE
    SYNTAX      TruthValue
    MAX-ACCESS  read-write
    STATUS      current
    DESCRIPTION 
        "Enable EEE (IEEE 802.3az) feature at a interface. true is to advertize
         EEE(IEEE 802.3az) capabilities to partner device. false is to disable
         it."
    ::= { vtssEeeConfigInterfaceParamEntry 2 }

vtssEeeConfigInterfaceQueueTable OBJECT-TYPE
    SYNTAX      SEQUENCE OF VTSSEeeConfigInterfaceQueueEntry
    MAX-ACCESS  not-accessible
    STATUS      current
    DESCRIPTION 
        "This is a table to configure egress port queue type, whether urgent
         queue or normal queue. We can configure more than one egress queues as
         urgent queues. Queues configured as urgent, en-queued data will be
         transmitted with minimum latency. Queue configured as normal, en-queued
         data will be transmitted with latency depending upon traffic
         utilization."
    ::= { vtssEeeConfigInterface 2 }

vtssEeeConfigInterfaceQueueEntry OBJECT-TYPE
    SYNTAX      VTSSEeeConfigInterfaceQueueEntry
    MAX-ACCESS  not-accessible
    STATUS      current
    DESCRIPTION 
        "Each interface has set of egress queues"
    INDEX       { vtssEeeConfigInterfaceQueueIfIndex, vtssEeeConfigInterfaceQueueIndex }
    ::= { vtssEeeConfigInterfaceQueueTable 1 }

VTSSEeeConfigInterfaceQueueEntry ::= SEQUENCE {
    vtssEeeConfigInterfaceQueueIfIndex      VTSSInterfaceIndex,
    vtssEeeConfigInterfaceQueueIndex    Integer32,
    vtssEeeConfigInterfaceQueueEgressQueueType      VTSSEeeQueueType
}

vtssEeeConfigInterfaceQueueIfIndex OBJECT-TYPE
    SYNTAX      VTSSInterfaceIndex
    MAX-ACCESS  not-accessible
    STATUS      current
    DESCRIPTION 
        "Logical interface number."
    ::= { vtssEeeConfigInterfaceQueueEntry 1 }

vtssEeeConfigInterfaceQueueIndex OBJECT-TYPE
    SYNTAX      Integer32 (0..7)
    MAX-ACCESS  not-accessible
    STATUS      current
    DESCRIPTION 
        "Egress port queue index."
    ::= { vtssEeeConfigInterfaceQueueEntry 2 }

vtssEeeConfigInterfaceQueueEgressQueueType OBJECT-TYPE
    SYNTAX      VTSSEeeQueueType
    MAX-ACCESS  read-write
    STATUS      current
    DESCRIPTION 
        "Egress port queue is urgent queue or normal queue."
    ::= { vtssEeeConfigInterfaceQueueEntry 3 }

vtssEeeStatus OBJECT IDENTIFIER
    ::= { vtssEeeMibObjects 3 }

vtssEeeStatusInterfaceTable OBJECT-TYPE
    SYNTAX      SEQUENCE OF VTSSEeeStatusInterfaceEntry
    MAX-ACCESS  not-accessible
    STATUS      current
    DESCRIPTION 
        "This is a table to Energy Efficient Ethernet interface status"
    ::= { vtssEeeStatus 1 }

vtssEeeStatusInterfaceEntry OBJECT-TYPE
    SYNTAX      VTSSEeeStatusInterfaceEntry
    MAX-ACCESS  not-accessible
    STATUS      current
    DESCRIPTION 
        "Each interface has a set of status parameters"
    INDEX       { vtssEeeStatusInterfaceIfIndex }
    ::= { vtssEeeStatusInterfaceTable 1 }

VTSSEeeStatusInterfaceEntry ::= SEQUENCE {
    vtssEeeStatusInterfaceIfIndex   VTSSInterfaceIndex,
    vtssEeeStatusInterfacePartnerEEE    VTSSEeeStatusType,
    vtssEeeStatusInterfaceRxPowerSave   VTSSEeeStatusType
}

vtssEeeStatusInterfaceIfIndex OBJECT-TYPE
    SYNTAX      VTSSInterfaceIndex
    MAX-ACCESS  not-accessible
    STATUS      current
    DESCRIPTION 
        "Logical interface number."
    ::= { vtssEeeStatusInterfaceEntry 1 }

vtssEeeStatusInterfacePartnerEEE OBJECT-TYPE
    SYNTAX      VTSSEeeStatusType
    MAX-ACCESS  read-only
    STATUS      current
    DESCRIPTION 
        "Indicates whether link partner advertising EEE(IEEE 802.3az)
         capabilities."
    ::= { vtssEeeStatusInterfaceEntry 2 }

vtssEeeStatusInterfaceRxPowerSave OBJECT-TYPE
    SYNTAX      VTSSEeeStatusType
    MAX-ACCESS  read-only
    STATUS      current
    DESCRIPTION 
        "Indicates whether interfcae rx path currently in power save state."
    ::= { vtssEeeStatusInterfaceEntry 3 }

vtssEeeMibConformance OBJECT IDENTIFIER
    ::= { vtssEeeMib 2 }

vtssEeeMibCompliances OBJECT IDENTIFIER
    ::= { vtssEeeMibConformance 1 }

vtssEeeMibGroups OBJECT IDENTIFIER
    ::= { vtssEeeMibConformance 2 }

vtssEeeCapabilitiesGlobalsInfoGroup OBJECT-GROUP
    OBJECTS     { vtssEeeCapabilitiesGlobalsOptimizationPreferences }
    STATUS      current
    DESCRIPTION
        "A collection of objects suitable for bulk operations."
    ::= { vtssEeeMibGroups 1 }

vtssEeeCapabilitiesInterfaceInfoGroup OBJECT-GROUP
    OBJECTS     { vtssEeeCapabilitiesInterfaceMaxEgressQueues, 
                  vtssEeeCapabilitiesInterfaceEEE }
    STATUS      current
    DESCRIPTION
        "A collection of objects suitable for bulk operations."
    ::= { vtssEeeMibGroups 2 }

vtssEeeConfigGlobalsInfoGroup OBJECT-GROUP
    OBJECTS     { vtssEeeConfigGlobalsOptimizationPreferences }
    STATUS      current
    DESCRIPTION
        "A collection of objects suitable for bulk operations."
    ::= { vtssEeeMibGroups 3 }

vtssEeeConfigInterfaceParamTableInfoGroup OBJECT-GROUP
    OBJECTS     { vtssEeeConfigInterfaceParamEnableEEE }
    STATUS      current
    DESCRIPTION
        "A collection of objects suitable for bulk operations."
    ::= { vtssEeeMibGroups 4 }

vtssEeeConfigInterfaceQueueTableInfoGroup OBJECT-GROUP
    OBJECTS     { vtssEeeConfigInterfaceQueueEgressQueueType }
    STATUS      current
    DESCRIPTION
        "A collection of objects suitable for bulk operations."
    ::= { vtssEeeMibGroups 5 }

vtssEeeStatusInterfaceTableInfoGroup OBJECT-GROUP
    OBJECTS     { vtssEeeStatusInterfacePartnerEEE, 
                  vtssEeeStatusInterfaceRxPowerSave }
    STATUS      current
    DESCRIPTION
        "A collection of objects suitable for bulk operations."
    ::= { vtssEeeMibGroups 6 }

vtssEeeMibCompliance MODULE-COMPLIANCE
    STATUS      current
    DESCRIPTION
        "The compliance statement for the implementation."

    MODULE      -- this module

        MANDATORY-GROUPS        { vtssEeeCapabilitiesGlobalsInfoGroup, 
                  vtssEeeCapabilitiesInterfaceInfoGroup, 
                  vtssEeeConfigGlobalsInfoGroup, 
                  vtssEeeConfigInterfaceParamTableInfoGroup, 
                  vtssEeeConfigInterfaceQueueTableInfoGroup, 
                  vtssEeeStatusInterfaceTableInfoGroup }

    ::= { vtssEeeMibCompliances 1 }

END
