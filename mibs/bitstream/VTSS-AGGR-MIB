-- *****************************************************************
-- AGGR-MIB:  Vitesse private MIB
--
-- Copyright (c) 2002-2013 Vitesse Semiconductor Corporation "Vitesse".
-- All Rights Reserved.
--
-- ****************************************************************

VTSS-AGGR-MIB DEFINITIONS ::= BEGIN

IMPORTS
    MODULE-COMPLIANCE, OBJECT-GROUP
        FROM SNMPv2-CONF
    MODULE-IDENTITY, OBJECT-TYPE
        FROM SNMPv2-SMI
    TEXTUAL-CONVENTION
        FROM SNMPv2-TC
    vtssSwitchMgmt
        FROM VTSS-SMI
    TruthValue FROM SNMPv2-TC
    VTSSDisplayString FROM VTSS-TC
    VTSSInterfaceIndex FROM VTSS-TC
    VTSSPortList FROM VTSS-TC
    VTSSRowEditorState FROM VTSS-TC
    ;

vtssAggrMib MODULE-IDENTITY
    LAST-UPDATED "201411180000Z"
    ORGANIZATION
        "Vitesse Semiconductor Corporation"
    CONTACT-INFO
        "Application support <application_support@vitesse.com>"
    DESCRIPTION
        "This is a private mib of static aggregation"
    REVISION    "201411180000Z"
    DESCRIPTION
        "Added aggregation group status table"
    REVISION    "201407010000Z"
    DESCRIPTION
        "Initial version"
    ::= { vtssSwitchMgmt 19 }


VTSSAggrLinkSpeedStatusEnum ::= TEXTUAL-CONVENTION
    STATUS      current
    DESCRIPTION
        "This enum represents the link speed."
    SYNTAX      INTEGER { undefined(0), s10M(1), s100M(2), s1G(3), s2500M(4), s5G(5), s10G(6), s12G(7) }

vtssAggrMibObjects OBJECT IDENTIFIER
    ::= { vtssAggrMib 1 }

vtssAggrConfig OBJECT IDENTIFIER
    ::= { vtssAggrMibObjects 2 }

vtssAggrConfigModeGlobals OBJECT IDENTIFIER
    ::= { vtssAggrConfig 1 }

vtssAggrConfigModeGlobalsSmacAddr OBJECT-TYPE
    SYNTAX      TruthValue
    MAX-ACCESS  read-write
    STATUS      current
    DESCRIPTION 
        "Set to true to enable the use of the Source MAC address, or false to
         disable. By default, Source MAC Address is enabled."
    ::= { vtssAggrConfigModeGlobals 1 }

vtssAggrConfigModeGlobalsDmacAddr OBJECT-TYPE
    SYNTAX      TruthValue
    MAX-ACCESS  read-write
    STATUS      current
    DESCRIPTION 
        "Set to true to enable the use of the Destination MAC address, or false
         to disable. By default, Destination MAC Address is disabled."
    ::= { vtssAggrConfigModeGlobals 2 }

vtssAggrConfigModeGlobalsSourceAndDestinationIpAddr OBJECT-TYPE
    SYNTAX      TruthValue
    MAX-ACCESS  read-write
    STATUS      current
    DESCRIPTION 
        "Set to true to enable the use of the IP address, or false to disable.
         By default, Destination MAC Address is enabled."
    ::= { vtssAggrConfigModeGlobals 3 }

vtssAggrConfigModeGlobalsTcpOrUdpSportAndDportNo OBJECT-TYPE
    SYNTAX      TruthValue
    MAX-ACCESS  read-write
    STATUS      current
    DESCRIPTION 
        "Set to true to enable the use of the TCP/UDP Port Number, or false to
         disable. By default, TCP/UDP Port Number is enabled."
    ::= { vtssAggrConfigModeGlobals 4 }

vtssAggrConfigGroupTable OBJECT-TYPE
    SYNTAX      SEQUENCE OF VTSSAggrConfigGroupEntry
    MAX-ACCESS  not-accessible
    STATUS      current
    DESCRIPTION 
        "The table is static Link Aggregation Group configuration table. The
         index is Aggregration Group Identifier."
    ::= { vtssAggrConfig 2 }

vtssAggrConfigGroupEntry OBJECT-TYPE
    SYNTAX      VTSSAggrConfigGroupEntry
    MAX-ACCESS  not-accessible
    STATUS      current
    DESCRIPTION 
        "Each entry has a set of parameters"
    INDEX       { vtssAggrConfigGroupAggrIndexNo }
    ::= { vtssAggrConfigGroupTable 1 }

VTSSAggrConfigGroupEntry ::= SEQUENCE {
    vtssAggrConfigGroupAggrIndexNo      VTSSInterfaceIndex,
    vtssAggrConfigGroupPortMembers      VTSSPortList,
    vtssAggrConfigGroupAction   VTSSRowEditorState
}

vtssAggrConfigGroupAggrIndexNo OBJECT-TYPE
    SYNTAX      VTSSInterfaceIndex
    MAX-ACCESS  not-accessible
    STATUS      current
    DESCRIPTION 
        "Link Aggregation Group Identifier."
    ::= { vtssAggrConfigGroupEntry 1 }

vtssAggrConfigGroupPortMembers OBJECT-TYPE
    SYNTAX      VTSSPortList
    MAX-ACCESS  read-write
    STATUS      current
    DESCRIPTION 
        "The list of port members for this Link Aggregation Group."
    ::= { vtssAggrConfigGroupEntry 2 }

vtssAggrConfigGroupAction OBJECT-TYPE
    SYNTAX      VTSSRowEditorState
    MAX-ACCESS  read-write
    STATUS      current
    DESCRIPTION 
        "Action"
    ::= { vtssAggrConfigGroupEntry 100 }

vtssAggrConfigGroupTableRowEditor OBJECT IDENTIFIER
    ::= { vtssAggrConfig 3 }

vtssAggrConfigGroupTableRowEditorAggrIndexNo OBJECT-TYPE
    SYNTAX      VTSSInterfaceIndex
    MAX-ACCESS  read-write
    STATUS      current
    DESCRIPTION 
        "Link Aggregation Group Identifier."
    ::= { vtssAggrConfigGroupTableRowEditor 1 }

vtssAggrConfigGroupTableRowEditorPortMembers OBJECT-TYPE
    SYNTAX      VTSSPortList
    MAX-ACCESS  read-write
    STATUS      current
    DESCRIPTION 
        "The list of port members for this Link Aggregation Group."
    ::= { vtssAggrConfigGroupTableRowEditor 2 }

vtssAggrConfigGroupTableRowEditorAction OBJECT-TYPE
    SYNTAX      VTSSRowEditorState
    MAX-ACCESS  read-write
    STATUS      current
    DESCRIPTION 
        "Action"
    ::= { vtssAggrConfigGroupTableRowEditor 100 }

vtssAggrStatus OBJECT IDENTIFIER
    ::= { vtssAggrMibObjects 3 }

vtssAggrStatusGroupTable OBJECT-TYPE
    SYNTAX      SEQUENCE OF VTSSAggrStatusGroupEntry
    MAX-ACCESS  not-accessible
    STATUS      current
    DESCRIPTION 
        "The table is Aggregation Group status table. The index is Aggregration
         Group Identifier."
    ::= { vtssAggrStatus 1 }

vtssAggrStatusGroupEntry OBJECT-TYPE
    SYNTAX      VTSSAggrStatusGroupEntry
    MAX-ACCESS  not-accessible
    STATUS      current
    DESCRIPTION 
        "Each entry has a set of parameters"
    INDEX       { vtssAggrStatusGroupAggrIndexNo }
    ::= { vtssAggrStatusGroupTable 1 }

VTSSAggrStatusGroupEntry ::= SEQUENCE {
    vtssAggrStatusGroupAggrIndexNo      VTSSInterfaceIndex,
    vtssAggrStatusGroupConfiguredPorts      VTSSPortList,
    vtssAggrStatusGroupAggregatedPorts      VTSSPortList,
    vtssAggrStatusGroupSpeed    VTSSAggrLinkSpeedStatusEnum,
    vtssAggrStatusGroupType     VTSSDisplayString
}

vtssAggrStatusGroupAggrIndexNo OBJECT-TYPE
    SYNTAX      VTSSInterfaceIndex
    MAX-ACCESS  not-accessible
    STATUS      current
    DESCRIPTION 
        "Link Aggregation Group Identifier."
    ::= { vtssAggrStatusGroupEntry 1 }

vtssAggrStatusGroupConfiguredPorts OBJECT-TYPE
    SYNTAX      VTSSPortList
    MAX-ACCESS  read-only
    STATUS      current
    DESCRIPTION 
        "Configured member ports of the aggregation Group."
    ::= { vtssAggrStatusGroupEntry 2 }

vtssAggrStatusGroupAggregatedPorts OBJECT-TYPE
    SYNTAX      VTSSPortList
    MAX-ACCESS  read-only
    STATUS      current
    DESCRIPTION 
        "Aggregated member ports of the aggregation Group."
    ::= { vtssAggrStatusGroupEntry 3 }

vtssAggrStatusGroupSpeed OBJECT-TYPE
    SYNTAX      VTSSAggrLinkSpeedStatusEnum
    MAX-ACCESS  read-only
    STATUS      current
    DESCRIPTION 
        "Speed of the Aggregation Group."
    ::= { vtssAggrStatusGroupEntry 4 }

vtssAggrStatusGroupType OBJECT-TYPE
    SYNTAX      VTSSDisplayString (SIZE(0..6))
    MAX-ACCESS  read-only
    STATUS      current
    DESCRIPTION 
        "Type of the Aggregation Group."
    ::= { vtssAggrStatusGroupEntry 5 }

vtssAggrMibConformance OBJECT IDENTIFIER
    ::= { vtssAggrMib 2 }

vtssAggrMibCompliances OBJECT IDENTIFIER
    ::= { vtssAggrMibConformance 1 }

vtssAggrMibGroups OBJECT IDENTIFIER
    ::= { vtssAggrMibConformance 2 }

vtssAggrConfigModeGlobalsInfoGroup OBJECT-GROUP
    OBJECTS     { vtssAggrConfigModeGlobalsSmacAddr, 
                  vtssAggrConfigModeGlobalsDmacAddr, 
                  vtssAggrConfigModeGlobalsSourceAndDestinationIpAddr, 
                  vtssAggrConfigModeGlobalsTcpOrUdpSportAndDportNo }
    STATUS      current
    DESCRIPTION
        "A collection of objects suitable for bulk operations."
    ::= { vtssAggrMibGroups 1 }

vtssAggrConfigGroupTableInfoGroup OBJECT-GROUP
    OBJECTS     { vtssAggrConfigGroupPortMembers, vtssAggrConfigGroupAction }
    STATUS      current
    DESCRIPTION
        "A collection of objects suitable for bulk operations."
    ::= { vtssAggrMibGroups 2 }

vtssAggrConfigGroupTableRowEditorInfoGroup OBJECT-GROUP
    OBJECTS     { vtssAggrConfigGroupTableRowEditorAggrIndexNo, 
                  vtssAggrConfigGroupTableRowEditorPortMembers, 
                  vtssAggrConfigGroupTableRowEditorAction }
    STATUS      current
    DESCRIPTION
        "A collection of objects suitable for bulk operations."
    ::= { vtssAggrMibGroups 3 }

vtssAggrStatusGroupTableInfoGroup OBJECT-GROUP
    OBJECTS     { vtssAggrStatusGroupConfiguredPorts, 
                  vtssAggrStatusGroupAggregatedPorts, vtssAggrStatusGroupSpeed, 
                  vtssAggrStatusGroupType }
    STATUS      current
    DESCRIPTION
        "A collection of objects suitable for bulk operations."
    ::= { vtssAggrMibGroups 4 }

vtssAggrMibCompliance MODULE-COMPLIANCE
    STATUS      current
    DESCRIPTION
        "The compliance statement for the implementation."

    MODULE      -- this module

        MANDATORY-GROUPS        { vtssAggrConfigModeGlobalsInfoGroup, 
                  vtssAggrConfigGroupTableInfoGroup, 
                  vtssAggrConfigGroupTableRowEditorInfoGroup, 
                  vtssAggrStatusGroupTableInfoGroup }

    ::= { vtssAggrMibCompliances 1 }

END
