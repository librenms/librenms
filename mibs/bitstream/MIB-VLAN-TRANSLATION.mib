-- *****************************************************************
-- MIB-VLAN-TRANSLATION: BitStream ENT private MIB
-- ****************************************************************

MIB-VLAN-TRANSLATION DEFINITIONS ::= BEGIN

IMPORTS
    MODULE-COMPLIANCE, OBJECT-GROUP FROM SNMPv2-CONF
    MODULE-IDENTITY, OBJECT-TYPE FROM SNMPv2-SMI
    TEXTUAL-CONVENTION FROM SNMPv2-TC
    switchMgmt FROM BTS-SMI
    Integer32 FROM SNMPv2-SMI
    Unsigned32 FROM SNMPv2-SMI
    InterfaceIndex FROM BTS-TC
    RowEditorState FROM BTS-TC
    ;

vlanTranslationMib MODULE-IDENTITY
    LAST-UPDATED "202503200000Z"
    ORGANIZATION
        "BitStream Sp. z o.o."
    CONTACT-INFO
        "www.bitstream.pl"
    DESCRIPTION
        "Private VLAN TRANSLATION MIB."
    REVISION    "201406300000Z"
    DESCRIPTION
        "Initial version"
    ::= { switchMgmt 85 }


vlanTranslationMibObjects OBJECT IDENTIFIER
    ::= { vlanTranslationMib 1 }

vlanTranslationCapabilities OBJECT IDENTIFIER
    ::= { vlanTranslationMibObjects 1 }

vlanTranslationCapabilitiesMaxNumberOfTranslations OBJECT-TYPE
    SYNTAX      Unsigned32
    MAX-ACCESS  read-only
    STATUS      current
    DESCRIPTION
        "Maximum number of VLAN translation mappings the user can store in the
         VLAN Translation mapping table."
    ::= { vlanTranslationCapabilities 1 }

vlanTranslationConfig OBJECT IDENTIFIER
    ::= { vlanTranslationMibObjects 2 }

vlanTranslationConfigTranslation OBJECT IDENTIFIER
    ::= { vlanTranslationConfig 1 }

vlanTranslationConfigTranslationTable OBJECT-TYPE
    SYNTAX      SEQUENCE OF VlanTranslationConfigTranslationEntry
    MAX-ACCESS  not-accessible
    STATUS      current
    DESCRIPTION
        "This is the VLAN translation mapping table.
         
         Here the user stores VLAN translation mappings (VID->TVID) inside
         groups that can later be activated on specific switch interfaces"
    ::= { vlanTranslationConfigTranslation 1 }

vlanTranslationConfigTranslationEntry OBJECT-TYPE
    SYNTAX      VlanTranslationConfigTranslationEntry
    MAX-ACCESS  not-accessible
    STATUS      current
    DESCRIPTION
        "Each entry in this table represents a VLAN translation mapping stored
         inside a specific VLAN translation Group.
         
         The entry key is the Group ID and the source VLAN ID, while the value
         is the translated VID.
         
         "
    INDEX       { vlanTranslationConfigTranslationGroupId,
                  vlanTranslationConfigTranslationVlanId }
    ::= { vlanTranslationConfigTranslationTable 1 }

VlanTranslationConfigTranslationEntry ::= SEQUENCE {
    vlanTranslationConfigTranslationGroupId  Integer32,
    vlanTranslationConfigTranslationVlanId   Integer32,
    vlanTranslationConfigTranslationTVlanId  Integer32,
    vlanTranslationConfigTranslationAction   RowEditorState
}

vlanTranslationConfigTranslationGroupId OBJECT-TYPE
    SYNTAX      Integer32 (1..65535)
    MAX-ACCESS  not-accessible
    STATUS      current
    DESCRIPTION
        "Group ID of the VLAN translation mapping key."
    ::= { vlanTranslationConfigTranslationEntry 1 }

vlanTranslationConfigTranslationVlanId OBJECT-TYPE
    SYNTAX      Integer32 (1..4095)
    MAX-ACCESS  not-accessible
    STATUS      current
    DESCRIPTION
        "Vlan ID of the VLAN translation mapping key."
    ::= { vlanTranslationConfigTranslationEntry 2 }

vlanTranslationConfigTranslationTVlanId OBJECT-TYPE
    SYNTAX      Integer32 (1..4095)
    MAX-ACCESS  read-write
    STATUS      current
    DESCRIPTION
        "Translated VLAN ID of the VLAN translation mapping."
    ::= { vlanTranslationConfigTranslationEntry 3 }

vlanTranslationConfigTranslationAction OBJECT-TYPE
    SYNTAX      RowEditorState
    MAX-ACCESS  read-write
    STATUS      current
    DESCRIPTION
        "Action"
    ::= { vlanTranslationConfigTranslationEntry 100 }

vlanTranslationConfigTranslationRowEditor OBJECT IDENTIFIER
    ::= { vlanTranslationConfigTranslation 2 }

vlanTranslationConfigTranslationRowEditorGroupId OBJECT-TYPE
    SYNTAX      Integer32 (1..65535)
    MAX-ACCESS  read-write
    STATUS      current
    DESCRIPTION
        "Group ID of the VLAN translation mapping key."
    ::= { vlanTranslationConfigTranslationRowEditor 1 }

vlanTranslationConfigTranslationRowEditorVlanId OBJECT-TYPE
    SYNTAX      Integer32 (1..4095)
    MAX-ACCESS  read-write
    STATUS      current
    DESCRIPTION
        "Vlan ID of the VLAN translation mapping key."
    ::= { vlanTranslationConfigTranslationRowEditor 2 }

vlanTranslationConfigTranslationRowEditorTVlanId OBJECT-TYPE
    SYNTAX      Integer32 (1..4095)
    MAX-ACCESS  read-write
    STATUS      current
    DESCRIPTION
        "Translated VLAN ID of the VLAN translation mapping."
    ::= { vlanTranslationConfigTranslationRowEditor 3 }

vlanTranslationConfigTranslationRowEditorAction OBJECT-TYPE
    SYNTAX      RowEditorState
    MAX-ACCESS  read-write
    STATUS      current
    DESCRIPTION
        "Action"
    ::= { vlanTranslationConfigTranslationRowEditor 100 }

vlanTranslationConfigInterfaces OBJECT IDENTIFIER
    ::= { vlanTranslationConfig 2 }

vlanTranslationConfigInterfacesIfTable OBJECT-TYPE
    SYNTAX      SEQUENCE OF VlanTranslationConfigInterfacesIfEntry
    MAX-ACCESS  not-accessible
    STATUS      current
    DESCRIPTION
        "This is the VLAN translation interface table. The number of interfaces
         is the total number of ports available on the switch. Each one of these
         interfaces can be set to use a specific Group of VLAN translation
         mappings, identified by the respective Group ID."
    ::= { vlanTranslationConfigInterfaces 1 }

vlanTranslationConfigInterfacesIfEntry OBJECT-TYPE
    SYNTAX      VlanTranslationConfigInterfacesIfEntry
    MAX-ACCESS  not-accessible
    STATUS      current
    DESCRIPTION
        "Entries in this table represent switch interfaces and their matching
         VLAN translation Groups (identified through their Group IDs)"
    INDEX       { vlanTranslationConfigInterfacesIfIfIndex }
    ::= { vlanTranslationConfigInterfacesIfTable 1 }

VlanTranslationConfigInterfacesIfEntry ::= SEQUENCE {
    vlanTranslationConfigInterfacesIfIfIndex  InterfaceIndex,
    vlanTranslationConfigInterfacesIfGroupId  Integer32
}

vlanTranslationConfigInterfacesIfIfIndex OBJECT-TYPE
    SYNTAX      InterfaceIndex
    MAX-ACCESS  not-accessible
    STATUS      current
    DESCRIPTION
        "Interface index number."
    ::= { vlanTranslationConfigInterfacesIfEntry 1 }

vlanTranslationConfigInterfacesIfGroupId OBJECT-TYPE
    SYNTAX      Integer32 (1..65535)
    MAX-ACCESS  read-write
    STATUS      current
    DESCRIPTION
        "Group ID of the interface configuration."
    ::= { vlanTranslationConfigInterfacesIfEntry 2 }

vlanTranslationMibConformance OBJECT IDENTIFIER
    ::= { vlanTranslationMib 2 }

vlanTranslationMibCompliances OBJECT IDENTIFIER
    ::= { vlanTranslationMibConformance 1 }

vlanTranslationMibGroups OBJECT IDENTIFIER
    ::= { vlanTranslationMibConformance 2 }

vlanTranslationCapabilitiesInfoGroup OBJECT-GROUP
    OBJECTS     {                   vlanTranslationCapabilitiesMaxNumberOfTranslations }
    STATUS      current
    DESCRIPTION
        "A collection of objects suitable for bulk operations."
    ::= { vlanTranslationMibGroups 1 }

vlanTranslationConfigTranslationTableInfoGroup OBJECT-GROUP
    OBJECTS     { vlanTranslationConfigTranslationTVlanId,
                  vlanTranslationConfigTranslationAction }
    STATUS      current
    DESCRIPTION
        "A collection of objects suitable for bulk operations."
    ::= { vlanTranslationMibGroups 2 }

vlanTranslationConfigTranslationRowEditorInfoGroup OBJECT-GROUP
    OBJECTS     {                   vlanTranslationConfigTranslationRowEditorGroupId,
                  vlanTranslationConfigTranslationRowEditorVlanId,
                  vlanTranslationConfigTranslationRowEditorTVlanId,
                  vlanTranslationConfigTranslationRowEditorAction }
    STATUS      current
    DESCRIPTION
        "A collection of objects suitable for bulk operations."
    ::= { vlanTranslationMibGroups 3 }

vlanTranslationConfigInterfacesIfTableInfoGroup OBJECT-GROUP
    OBJECTS     { vlanTranslationConfigInterfacesIfGroupId }
    STATUS      current
    DESCRIPTION
        "A collection of objects suitable for bulk operations."
    ::= { vlanTranslationMibGroups 4 }

vlanTranslationMibCompliance MODULE-COMPLIANCE
    STATUS      current
    DESCRIPTION
        "The compliance statement for the implementation."

    MODULE      -- this module

    MANDATORY-GROUPS { vlanTranslationCapabilitiesInfoGroup,
                       vlanTranslationConfigTranslationTableInfoGroup,
                       vlanTranslationConfigTranslationRowEditorInfoGroup,
                       vlanTranslationConfigInterfacesIfTableInfoGroup }

    ::= { vlanTranslationMibCompliances 1 }

END
