-- *****************************************************************
-- PSEC-MIB:  Vitesse private MIB
--
-- Copyright (c) 2002-2013 Vitesse Semiconductor Corporation "Vitesse".
-- All Rights Reserved.
--
-- ****************************************************************

VTSS-PSEC-MIB DEFINITIONS ::= BEGIN

IMPORTS
    MODULE-COMPLIANCE, OBJECT-GROUP
        FROM SNMPv2-CONF
    MODULE-IDENTITY, OBJECT-TYPE
        FROM SNMPv2-SMI
    TEXTUAL-CONVENTION
        FROM SNMPv2-TC
    vtssSwitchMgmt
        FROM VTSS-SMI
    Unsigned32 FROM SNMPv2-SMI
    MacAddress FROM SNMPv2-TC
    TruthValue FROM SNMPv2-TC
    VTSSDisplayString FROM VTSS-TC
    VTSSInterfaceIndex FROM VTSS-TC
    VTSSUnsigned16 FROM VTSS-TC
    ;

vtssPsecMib MODULE-IDENTITY
    LAST-UPDATED "201412100000Z"
    ORGANIZATION
        "Vitesse Semiconductor Corporation"
    CONTACT-INFO
        "Application support <application_support@vitesse.com>"
    DESCRIPTION
        "This is a private version of the Port Security MIB"
    REVISION    "201412100000Z"
    DESCRIPTION
        "Remove user of DHCP snooping"
    REVISION    "201412080000Z"
    DESCRIPTION
        "Add users in status port table"
    REVISION    "201410130000Z"
    DESCRIPTION
        "Initial version"
    ::= { vtssSwitchMgmt 66 }


VTSSPsecLimitActionType ::= TEXTUAL-CONVENTION
    STATUS      current
    DESCRIPTION
        "This enumeration defines the Action type in psec function."
    SYNTAX      INTEGER { none(0), trap(1), shutdown(2), trapShutdown(3) }

VTSSPsecStateType ::= TEXTUAL-CONVENTION
    STATUS      current
    DESCRIPTION
        "This enumeration defines the state of Psec config."
    SYNTAX      INTEGER { forwarding(0), blocked(1) }

vtssPsecMibObjects OBJECT IDENTIFIER
    ::= { vtssPsecMib 1 }

vtssPsecConfig OBJECT IDENTIFIER
    ::= { vtssPsecMibObjects 2 }

vtssPsecConfigGlobals OBJECT IDENTIFIER
    ::= { vtssPsecConfig 1 }

vtssPsecConfigGlobalsEnabled OBJECT-TYPE
    SYNTAX      TruthValue
    MAX-ACCESS  read-write
    STATUS      current
    DESCRIPTION 
        "Globally enable/disable aging of secured entries. This doesn't affect
         aging of addresses secured by other modules."
    ::= { vtssPsecConfigGlobals 1 }

vtssPsecConfigGlobalsEnableAging OBJECT-TYPE
    SYNTAX      TruthValue
    MAX-ACCESS  read-write
    STATUS      current
    DESCRIPTION 
        "If aging is globally enabled, this is the aging period in seconds.
         Valid range is [10; 10000000] seconds(max is around 115 days)."
    ::= { vtssPsecConfigGlobals 2 }

vtssPsecConfigGlobalsAgingPeriodSecs OBJECT-TYPE
    SYNTAX      Unsigned32
    MAX-ACCESS  read-write
    STATUS      current
    DESCRIPTION 
        "If aging is globally enabled, this is the aging period in seconds.
         Valid range is [10; 10000000] seconds(max is around 115 days)."
    ::= { vtssPsecConfigGlobals 3 }

vtssPsecConfigPortTable OBJECT-TYPE
    SYNTAX      SEQUENCE OF VTSSPsecConfigPortEntry
    MAX-ACCESS  not-accessible
    STATUS      current
    DESCRIPTION 
        "This is a table of port configuration per session"
    ::= { vtssPsecConfig 2 }

vtssPsecConfigPortEntry OBJECT-TYPE
    SYNTAX      VTSSPsecConfigPortEntry
    MAX-ACCESS  not-accessible
    STATUS      current
    DESCRIPTION 
        "Each session has a set of parameters"
    INDEX       { vtssPsecConfigPortIfIndex }
    ::= { vtssPsecConfigPortTable 1 }

VTSSPsecConfigPortEntry ::= SEQUENCE {
    vtssPsecConfigPortIfIndex   VTSSInterfaceIndex,
    vtssPsecConfigPortEnabled   TruthValue,
    vtssPsecConfigPortLimit     Unsigned32,
    vtssPsecConfigPortAction    VTSSPsecLimitActionType
}

vtssPsecConfigPortIfIndex OBJECT-TYPE
    SYNTAX      VTSSInterfaceIndex
    MAX-ACCESS  not-accessible
    STATUS      current
    DESCRIPTION 
        "Logical interface number of the physical port."
    ::= { vtssPsecConfigPortEntry 1 }

vtssPsecConfigPortEnabled OBJECT-TYPE
    SYNTAX      TruthValue
    MAX-ACCESS  read-write
    STATUS      current
    DESCRIPTION 
        "Controls whether Port Security Limit Control is enabled for this port."
    ::= { vtssPsecConfigPortEntry 2 }

vtssPsecConfigPortLimit OBJECT-TYPE
    SYNTAX      Unsigned32
    MAX-ACCESS  read-write
    STATUS      current
    DESCRIPTION 
        "Maximum number of MAC addresses allowed on this port.Valid values =
         [PSEC_LIMIT_MIN; PSEC_LIMIT_MAX]."
    ::= { vtssPsecConfigPortEntry 3 }

vtssPsecConfigPortAction OBJECT-TYPE
    SYNTAX      VTSSPsecLimitActionType
    MAX-ACCESS  read-write
    STATUS      current
    DESCRIPTION 
        "Action to take if number of MAC addresses exceeds the limit. NONE(0) Do
         nothing, except disallowing further clients. TRAP(1) Send an SNMP trap
         notification. SHUTDOWN(2) Shut-down the port. TRAP_AND_SHUTDOWN(3) Send
         an SNMP trap notification and shut-down the port."
    ::= { vtssPsecConfigPortEntry 4 }

vtssPsecStatus OBJECT IDENTIFIER
    ::= { vtssPsecMibObjects 3 }

vtssPsecStatusPortTable OBJECT-TYPE
    SYNTAX      SEQUENCE OF VTSSPsecStatusPortEntry
    MAX-ACCESS  not-accessible
    STATUS      current
    DESCRIPTION 
        "This is a table of port configuration per session"
    ::= { vtssPsecStatus 1 }

vtssPsecStatusPortEntry OBJECT-TYPE
    SYNTAX      VTSSPsecStatusPortEntry
    MAX-ACCESS  not-accessible
    STATUS      current
    DESCRIPTION 
        "Each session has a set of parameters"
    INDEX       { vtssPsecStatusPortIfIndex }
    ::= { vtssPsecStatusPortTable 1 }

VTSSPsecStatusPortEntry ::= SEQUENCE {
    vtssPsecStatusPortIfIndex   VTSSInterfaceIndex,
    vtssPsecStatusPortUsers     Unsigned32,
    vtssPsecStatusPortLimitReached      TruthValue,
    vtssPsecStatusPortShutdown      TruthValue,
    vtssPsecStatusPortMacCount      Unsigned32
}

vtssPsecStatusPortIfIndex OBJECT-TYPE
    SYNTAX      VTSSInterfaceIndex
    MAX-ACCESS  not-accessible
    STATUS      current
    DESCRIPTION 
        "Logical interface number of the physical port."
    ::= { vtssPsecStatusPortEntry 1 }

vtssPsecStatusPortUsers OBJECT-TYPE
    SYNTAX      Unsigned32
    MAX-ACCESS  read-only
    STATUS      current
    DESCRIPTION 
        "Bit masks to indicate what users currently use port security on this
         port. Where bit 0 - port security limit, bit 1 - 802.1x, bit 2 - voice
         VLAN."
    ::= { vtssPsecStatusPortEntry 2 }

vtssPsecStatusPortLimitReached OBJECT-TYPE
    SYNTAX      TruthValue
    MAX-ACCESS  read-only
    STATUS      current
    DESCRIPTION 
        "TRUE if the limit is reached on the port, FALSE otherwise."
    ::= { vtssPsecStatusPortEntry 3 }

vtssPsecStatusPortShutdown OBJECT-TYPE
    SYNTAX      TruthValue
    MAX-ACCESS  read-only
    STATUS      current
    DESCRIPTION 
        "TRUE if the port is shut down, FALSE otherwise."
    ::= { vtssPsecStatusPortEntry 4 }

vtssPsecStatusPortMacCount OBJECT-TYPE
    SYNTAX      Unsigned32
    MAX-ACCESS  read-only
    STATUS      current
    DESCRIPTION 
        "Number of MAC addresses currently assigned to this port. The number
         does NOT include the number of entries that are held due to a H/W
         failure or S/W failure."
    ::= { vtssPsecStatusPortEntry 5 }

vtssPsecControl OBJECT IDENTIFIER
    ::= { vtssPsecMibObjects 4 }

vtssPsecControlPortReopenTable OBJECT-TYPE
    SYNTAX      SEQUENCE OF VTSSPsecControlPortReopenEntry
    MAX-ACCESS  not-accessible
    STATUS      current
    DESCRIPTION 
        "This is a table to re-open port and move it to ready state, if it was
         being disabled after limit was reached."
    ::= { vtssPsecControl 1 }

vtssPsecControlPortReopenEntry OBJECT-TYPE
    SYNTAX      VTSSPsecControlPortReopenEntry
    MAX-ACCESS  not-accessible
    STATUS      current
    DESCRIPTION 
        "Each session has a set of parameters"
    INDEX       { vtssPsecControlPortReopenIfIndex }
    ::= { vtssPsecControlPortReopenTable 1 }

VTSSPsecControlPortReopenEntry ::= SEQUENCE {
    vtssPsecControlPortReopenIfIndex    VTSSInterfaceIndex,
    vtssPsecControlPortReopenPortReOpen     TruthValue
}

vtssPsecControlPortReopenIfIndex OBJECT-TYPE
    SYNTAX      VTSSInterfaceIndex
    MAX-ACCESS  not-accessible
    STATUS      current
    DESCRIPTION 
        "Logical interface number of the physical port."
    ::= { vtssPsecControlPortReopenEntry 1 }

vtssPsecControlPortReopenPortReOpen OBJECT-TYPE
    SYNTAX      TruthValue
    MAX-ACCESS  read-write
    STATUS      current
    DESCRIPTION 
        "Set to true to reopen after it is shutdown"
    ::= { vtssPsecControlPortReopenEntry 2 }

vtssPsecStatistics OBJECT IDENTIFIER
    ::= { vtssPsecMibObjects 5 }

vtssPsecStatisticsPortTable OBJECT-TYPE
    SYNTAX      SEQUENCE OF VTSSPsecStatisticsPortEntry
    MAX-ACCESS  not-accessible
    STATUS      current
    DESCRIPTION 
        "This is a table of port statistics per session"
    ::= { vtssPsecStatistics 1 }

vtssPsecStatisticsPortEntry OBJECT-TYPE
    SYNTAX      VTSSPsecStatisticsPortEntry
    MAX-ACCESS  not-accessible
    STATUS      current
    DESCRIPTION 
        "Each session has a set of parameters"
    INDEX       { vtssPsecStatisticsPortIfIndex }
    ::= { vtssPsecStatisticsPortTable 1 }

VTSSPsecStatisticsPortEntry ::= SEQUENCE {
    vtssPsecStatisticsPortIfIndex   VTSSInterfaceIndex,
    vtssPsecStatisticsPortAgeOrHold     VTSSDisplayString,
    vtssPsecStatisticsPortCreationTime      VTSSDisplayString,
    vtssPsecStatisticsPortState     VTSSPsecStateType,
    vtssPsecStatisticsPortMacId     MacAddress,
    vtssPsecStatisticsPortVlanId    VTSSUnsigned16
}

vtssPsecStatisticsPortIfIndex OBJECT-TYPE
    SYNTAX      VTSSInterfaceIndex
    MAX-ACCESS  not-accessible
    STATUS      current
    DESCRIPTION 
        "Logical interface number of the physical port."
    ::= { vtssPsecStatisticsPortEntry 1 }

vtssPsecStatisticsPortAgeOrHold OBJECT-TYPE
    SYNTAX      VTSSDisplayString (SIZE(0..14))
    MAX-ACCESS  read-only
    STATUS      current
    DESCRIPTION 
        "Down-counter used in block and ageing process."
    ::= { vtssPsecStatisticsPortEntry 5 }

vtssPsecStatisticsPortCreationTime OBJECT-TYPE
    SYNTAX      VTSSDisplayString (SIZE(0..24))
    MAX-ACCESS  read-only
    STATUS      current
    DESCRIPTION 
        "Time when this entry was orignally added."
    ::= { vtssPsecStatisticsPortEntry 6 }

vtssPsecStatisticsPortState OBJECT-TYPE
    SYNTAX      VTSSPsecStateType
    MAX-ACCESS  read-only
    STATUS      current
    DESCRIPTION 
        "Current State of a entry, expected state can be either FORWARDING or
         BLOCKED."
    ::= { vtssPsecStatisticsPortEntry 7 }

vtssPsecStatisticsPortMacId OBJECT-TYPE
    SYNTAX      MacAddress
    MAX-ACCESS  read-only
    STATUS      current
    DESCRIPTION 
        "The MAC address that this is all about."
    ::= { vtssPsecStatisticsPortEntry 8 }

vtssPsecStatisticsPortVlanId OBJECT-TYPE
    SYNTAX      VTSSUnsigned16
    MAX-ACCESS  read-only
    STATUS      current
    DESCRIPTION 
        "The VID that this is all about."
    ::= { vtssPsecStatisticsPortEntry 9 }

vtssPsecMibConformance OBJECT IDENTIFIER
    ::= { vtssPsecMib 2 }

vtssPsecMibCompliances OBJECT IDENTIFIER
    ::= { vtssPsecMibConformance 1 }

vtssPsecMibGroups OBJECT IDENTIFIER
    ::= { vtssPsecMibConformance 2 }

vtssPsecConfigGlobalsInfoGroup OBJECT-GROUP
    OBJECTS     { vtssPsecConfigGlobalsEnabled, vtssPsecConfigGlobalsEnableAging, 
                  vtssPsecConfigGlobalsAgingPeriodSecs }
    STATUS      current
    DESCRIPTION
        "A collection of objects suitable for bulk operations."
    ::= { vtssPsecMibGroups 1 }

vtssPsecConfigPortTableInfoGroup OBJECT-GROUP
    OBJECTS     { vtssPsecConfigPortEnabled, vtssPsecConfigPortLimit, 
                  vtssPsecConfigPortAction }
    STATUS      current
    DESCRIPTION
        "A collection of objects suitable for bulk operations."
    ::= { vtssPsecMibGroups 2 }

vtssPsecStatusPortTableInfoGroup OBJECT-GROUP
    OBJECTS     { vtssPsecStatusPortUsers, vtssPsecStatusPortLimitReached, 
                  vtssPsecStatusPortShutdown, vtssPsecStatusPortMacCount }
    STATUS      current
    DESCRIPTION
        "A collection of objects suitable for bulk operations."
    ::= { vtssPsecMibGroups 3 }

vtssPsecControlPortReopenTableInfoGroup OBJECT-GROUP
    OBJECTS     { vtssPsecControlPortReopenPortReOpen }
    STATUS      current
    DESCRIPTION
        "A collection of objects suitable for bulk operations."
    ::= { vtssPsecMibGroups 4 }

vtssPsecStatisticsPortTableInfoGroup OBJECT-GROUP
    OBJECTS     { vtssPsecStatisticsPortAgeOrHold, 
                  vtssPsecStatisticsPortCreationTime, 
                  vtssPsecStatisticsPortState, vtssPsecStatisticsPortMacId, 
                  vtssPsecStatisticsPortVlanId }
    STATUS      current
    DESCRIPTION
        "A collection of objects suitable for bulk operations."
    ::= { vtssPsecMibGroups 5 }

vtssPsecMibCompliance MODULE-COMPLIANCE
    STATUS      current
    DESCRIPTION
        "The compliance statement for the implementation."

    MODULE      -- this module

        MANDATORY-GROUPS        { vtssPsecConfigGlobalsInfoGroup, 
                  vtssPsecConfigPortTableInfoGroup, 
                  vtssPsecStatusPortTableInfoGroup, 
                  vtssPsecControlPortReopenTableInfoGroup, 
                  vtssPsecStatisticsPortTableInfoGroup }

    ::= { vtssPsecMibCompliances 1 }

END
