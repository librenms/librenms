-- *****************************************************************
-- ACCESS-MANAGEMENT-MIB:  Vitesse private MIB
--
-- Copyright (c) 2002-2013 Vitesse Semiconductor Corporation "Vitesse".
-- All Rights Reserved.
--
-- ****************************************************************

VTSS-ACCESS-MANAGEMENT-MIB DEFINITIONS ::= BEGIN

IMPORTS
    MODULE-COMPLIANCE, OBJECT-GROUP
        FROM SNMPv2-CONF
    MODULE-IDENTITY, OBJECT-TYPE
        FROM SNMPv2-SMI
    TEXTUAL-CONVENTION
        FROM SNMPv2-TC
    vtssSwitchMgmt
        FROM VTSS-SMI
    InetAddressIPv6 FROM INET-ADDRESS-MIB
    Integer32 FROM SNMPv2-SMI
    IpAddress FROM SNMPv2-SMI
    Unsigned32 FROM SNMPv2-SMI
    TruthValue FROM SNMPv2-TC
    VTSSRowEditorState FROM VTSS-TC
    VTSSUnsigned16 FROM VTSS-TC
    ;

vtssAccessManagementMib MODULE-IDENTITY
    LAST-UPDATED "201407010000Z"
    ORGANIZATION
        "Vitesse Semiconductor Corporation"
    CONTACT-INFO
        "Application support <application_support@vitesse.com>"
    DESCRIPTION
        "This is a private version of the Access Management MIB"
    REVISION    "201407010000Z"
    DESCRIPTION
        "Initial version"
    ::= { vtssSwitchMgmt 51 }


vtssAccessManagementMibObjects OBJECT IDENTIFIER
    ::= { vtssAccessManagementMib 1 }

vtssAccessManagementConfig OBJECT IDENTIFIER
    ::= { vtssAccessManagementMibObjects 2 }

vtssAccessManagementConfigGlobals OBJECT IDENTIFIER
    ::= { vtssAccessManagementConfig 1 }

vtssAccessManagementConfigGlobalsAdminState OBJECT-TYPE
    SYNTAX      TruthValue
    MAX-ACCESS  read-write
    STATUS      current
    DESCRIPTION 
        "Enable/Disable the Access Management global functionality."
    ::= { vtssAccessManagementConfigGlobals 1 }

vtssAccessManagementConfigIpv4Table OBJECT-TYPE
    SYNTAX      SEQUENCE OF VTSSAccessManagementConfigIpv4Entry
    MAX-ACCESS  not-accessible
    STATUS      current
    DESCRIPTION 
        "This is a table for managing Access Management per IPv4 basis"
    ::= { vtssAccessManagementConfig 2 }

vtssAccessManagementConfigIpv4Entry OBJECT-TYPE
    SYNTAX      VTSSAccessManagementConfigIpv4Entry
    MAX-ACCESS  not-accessible
    STATUS      current
    DESCRIPTION 
        "Each entry has a set of parameters"
    INDEX       { vtssAccessManagementConfigIpv4AccessIndex }
    ::= { vtssAccessManagementConfigIpv4Table 1 }

VTSSAccessManagementConfigIpv4Entry ::= SEQUENCE {
    vtssAccessManagementConfigIpv4AccessIndex   Integer32,
    vtssAccessManagementConfigIpv4VlanId    VTSSUnsigned16,
    vtssAccessManagementConfigIpv4StartAddress      IpAddress,
    vtssAccessManagementConfigIpv4EndAddress    IpAddress,
    vtssAccessManagementConfigIpv4WebServices   TruthValue,
    vtssAccessManagementConfigIpv4SnmpServices      TruthValue,
    vtssAccessManagementConfigIpv4TelnetServices    TruthValue,
    vtssAccessManagementConfigIpv4Action    VTSSRowEditorState
}

vtssAccessManagementConfigIpv4AccessIndex OBJECT-TYPE
    SYNTAX      Integer32 (0..2147483647)
    MAX-ACCESS  not-accessible
    STATUS      current
    DESCRIPTION 
        "Index for Access Management IPv4/IPv6 table."
    ::= { vtssAccessManagementConfigIpv4Entry 1 }

vtssAccessManagementConfigIpv4VlanId OBJECT-TYPE
    SYNTAX      VTSSUnsigned16
    MAX-ACCESS  read-write
    STATUS      current
    DESCRIPTION 
        "The ID of specific VLAN interface that Access Management should take
         effect for IPv4."
    ::= { vtssAccessManagementConfigIpv4Entry 2 }

vtssAccessManagementConfigIpv4StartAddress OBJECT-TYPE
    SYNTAX      IpAddress
    MAX-ACCESS  read-write
    STATUS      current
    DESCRIPTION 
        "The starting IPv4 address of the range that Access Management performs
         checking."
    ::= { vtssAccessManagementConfigIpv4Entry 3 }

vtssAccessManagementConfigIpv4EndAddress OBJECT-TYPE
    SYNTAX      IpAddress
    MAX-ACCESS  read-write
    STATUS      current
    DESCRIPTION 
        "The ending IPv4 address of the range that Access Management performs
         checking."
    ::= { vtssAccessManagementConfigIpv4Entry 4 }

vtssAccessManagementConfigIpv4WebServices OBJECT-TYPE
    SYNTAX      TruthValue
    MAX-ACCESS  read-write
    STATUS      current
    DESCRIPTION 
        "Enable/Disable HTTP and HTTPS functionality via Access Management. At
         least one of WebServices/SnmpServices/TelnetServices has to be enabled
         for a specific AccessIndex in Access Management IPv4 table."
    ::= { vtssAccessManagementConfigIpv4Entry 5 }

vtssAccessManagementConfigIpv4SnmpServices OBJECT-TYPE
    SYNTAX      TruthValue
    MAX-ACCESS  read-write
    STATUS      current
    DESCRIPTION 
        "Enable/Disable SNMP functionality via Access Management. At least one
         of WebServices/SnmpServices/TelnetServices has to be enabled for a
         specific AccessIndex in Access Management IPv4 table."
    ::= { vtssAccessManagementConfigIpv4Entry 6 }

vtssAccessManagementConfigIpv4TelnetServices OBJECT-TYPE
    SYNTAX      TruthValue
    MAX-ACCESS  read-write
    STATUS      current
    DESCRIPTION 
        "Enable/Disable TELNET/SSH functionality via Access Management. At least
         one of WebServices/SnmpServices/TelnetServices has to be enabled for a
         specific AccessIndex in Access Management IPv4 table."
    ::= { vtssAccessManagementConfigIpv4Entry 7 }

vtssAccessManagementConfigIpv4Action OBJECT-TYPE
    SYNTAX      VTSSRowEditorState
    MAX-ACCESS  read-write
    STATUS      current
    DESCRIPTION 
        "Action"
    ::= { vtssAccessManagementConfigIpv4Entry 100 }

vtssAccessManagementConfigIpv4TableRowEditor OBJECT IDENTIFIER
    ::= { vtssAccessManagementConfig 3 }

vtssAccessManagementConfigIpv4TableRowEditorAccessIndex OBJECT-TYPE
    SYNTAX      Integer32 (0..2147483647)
    MAX-ACCESS  read-write
    STATUS      current
    DESCRIPTION 
        "Index for Access Management IPv4/IPv6 table."
    ::= { vtssAccessManagementConfigIpv4TableRowEditor 1 }

vtssAccessManagementConfigIpv4TableRowEditorVlanId OBJECT-TYPE
    SYNTAX      VTSSUnsigned16
    MAX-ACCESS  read-write
    STATUS      current
    DESCRIPTION 
        "The ID of specific VLAN interface that Access Management should take
         effect for IPv4."
    ::= { vtssAccessManagementConfigIpv4TableRowEditor 2 }

vtssAccessManagementConfigIpv4TableRowEditorStartAddress OBJECT-TYPE
    SYNTAX      IpAddress
    MAX-ACCESS  read-write
    STATUS      current
    DESCRIPTION 
        "The starting IPv4 address of the range that Access Management performs
         checking."
    ::= { vtssAccessManagementConfigIpv4TableRowEditor 3 }

vtssAccessManagementConfigIpv4TableRowEditorEndAddress OBJECT-TYPE
    SYNTAX      IpAddress
    MAX-ACCESS  read-write
    STATUS      current
    DESCRIPTION 
        "The ending IPv4 address of the range that Access Management performs
         checking."
    ::= { vtssAccessManagementConfigIpv4TableRowEditor 4 }

vtssAccessManagementConfigIpv4TableRowEditorWebServices OBJECT-TYPE
    SYNTAX      TruthValue
    MAX-ACCESS  read-write
    STATUS      current
    DESCRIPTION 
        "Enable/Disable HTTP and HTTPS functionality via Access Management. At
         least one of WebServices/SnmpServices/TelnetServices has to be enabled
         for a specific AccessIndex in Access Management IPv4 table."
    ::= { vtssAccessManagementConfigIpv4TableRowEditor 5 }

vtssAccessManagementConfigIpv4TableRowEditorSnmpServices OBJECT-TYPE
    SYNTAX      TruthValue
    MAX-ACCESS  read-write
    STATUS      current
    DESCRIPTION 
        "Enable/Disable SNMP functionality via Access Management. At least one
         of WebServices/SnmpServices/TelnetServices has to be enabled for a
         specific AccessIndex in Access Management IPv4 table."
    ::= { vtssAccessManagementConfigIpv4TableRowEditor 6 }

vtssAccessManagementConfigIpv4TableRowEditorTelnetServices OBJECT-TYPE
    SYNTAX      TruthValue
    MAX-ACCESS  read-write
    STATUS      current
    DESCRIPTION 
        "Enable/Disable TELNET/SSH functionality via Access Management. At least
         one of WebServices/SnmpServices/TelnetServices has to be enabled for a
         specific AccessIndex in Access Management IPv4 table."
    ::= { vtssAccessManagementConfigIpv4TableRowEditor 7 }

vtssAccessManagementConfigIpv4TableRowEditorAction OBJECT-TYPE
    SYNTAX      VTSSRowEditorState
    MAX-ACCESS  read-write
    STATUS      current
    DESCRIPTION 
        "Action"
    ::= { vtssAccessManagementConfigIpv4TableRowEditor 100 }

vtssAccessManagementConfigIpv6Table OBJECT-TYPE
    SYNTAX      SEQUENCE OF VTSSAccessManagementConfigIpv6Entry
    MAX-ACCESS  not-accessible
    STATUS      current
    DESCRIPTION 
        "This is a table for managing Access Management per IPv6 basis"
    ::= { vtssAccessManagementConfig 4 }

vtssAccessManagementConfigIpv6Entry OBJECT-TYPE
    SYNTAX      VTSSAccessManagementConfigIpv6Entry
    MAX-ACCESS  not-accessible
    STATUS      current
    DESCRIPTION 
        "Each entry has a set of parameters"
    INDEX       { vtssAccessManagementConfigIpv6AccessIndex }
    ::= { vtssAccessManagementConfigIpv6Table 1 }

VTSSAccessManagementConfigIpv6Entry ::= SEQUENCE {
    vtssAccessManagementConfigIpv6AccessIndex   Integer32,
    vtssAccessManagementConfigIpv6VlanId    VTSSUnsigned16,
    vtssAccessManagementConfigIpv6StartAddress      InetAddressIPv6,
    vtssAccessManagementConfigIpv6EndAddress    InetAddressIPv6,
    vtssAccessManagementConfigIpv6WebServices   TruthValue,
    vtssAccessManagementConfigIpv6SnmpServices      TruthValue,
    vtssAccessManagementConfigIpv6TelnetServices    TruthValue,
    vtssAccessManagementConfigIpv6Action    VTSSRowEditorState
}

vtssAccessManagementConfigIpv6AccessIndex OBJECT-TYPE
    SYNTAX      Integer32 (0..2147483647)
    MAX-ACCESS  not-accessible
    STATUS      current
    DESCRIPTION 
        "Index for Access Management IPv4/IPv6 table."
    ::= { vtssAccessManagementConfigIpv6Entry 1 }

vtssAccessManagementConfigIpv6VlanId OBJECT-TYPE
    SYNTAX      VTSSUnsigned16
    MAX-ACCESS  read-write
    STATUS      current
    DESCRIPTION 
        "The ID of specific VLAN interface that Access Management should take
         effect for IPv6."
    ::= { vtssAccessManagementConfigIpv6Entry 2 }

vtssAccessManagementConfigIpv6StartAddress OBJECT-TYPE
    SYNTAX      InetAddressIPv6
    MAX-ACCESS  read-write
    STATUS      current
    DESCRIPTION 
        "The starting IPv6 address of the range that Access Management performs
         checking."
    ::= { vtssAccessManagementConfigIpv6Entry 3 }

vtssAccessManagementConfigIpv6EndAddress OBJECT-TYPE
    SYNTAX      InetAddressIPv6
    MAX-ACCESS  read-write
    STATUS      current
    DESCRIPTION 
        "The ending IPv6 address of the range that Access Management performs
         checking."
    ::= { vtssAccessManagementConfigIpv6Entry 4 }

vtssAccessManagementConfigIpv6WebServices OBJECT-TYPE
    SYNTAX      TruthValue
    MAX-ACCESS  read-write
    STATUS      current
    DESCRIPTION 
        "Enable/Disable HTTP and HTTPS functionality via Access Management. At
         least one of WebServices/SnmpServices/TelnetServices has to be enabled
         for a specific AccessIndex in Access Management IPv6 table."
    ::= { vtssAccessManagementConfigIpv6Entry 5 }

vtssAccessManagementConfigIpv6SnmpServices OBJECT-TYPE
    SYNTAX      TruthValue
    MAX-ACCESS  read-write
    STATUS      current
    DESCRIPTION 
        "Enable/Disable SNMP functionality via Access Management. At least one
         of WebServices/SnmpServices/TelnetServices has to be enabled for a
         specific AccessIndex in Access Management IPv6 table."
    ::= { vtssAccessManagementConfigIpv6Entry 6 }

vtssAccessManagementConfigIpv6TelnetServices OBJECT-TYPE
    SYNTAX      TruthValue
    MAX-ACCESS  read-write
    STATUS      current
    DESCRIPTION 
        "Enable/Disable TELNET/SSH functionality via Access Management. At least
         one of WebServices/SnmpServices/TelnetServices has to be enabled for a
         specific AccessIndex in Access Management IPv6 table."
    ::= { vtssAccessManagementConfigIpv6Entry 7 }

vtssAccessManagementConfigIpv6Action OBJECT-TYPE
    SYNTAX      VTSSRowEditorState
    MAX-ACCESS  read-write
    STATUS      current
    DESCRIPTION 
        "Action"
    ::= { vtssAccessManagementConfigIpv6Entry 100 }

vtssAccessManagementConfigIpv6TableRowEditor OBJECT IDENTIFIER
    ::= { vtssAccessManagementConfig 5 }

vtssAccessManagementConfigIpv6TableRowEditorAccessIndex OBJECT-TYPE
    SYNTAX      Integer32 (0..2147483647)
    MAX-ACCESS  read-write
    STATUS      current
    DESCRIPTION 
        "Index for Access Management IPv4/IPv6 table."
    ::= { vtssAccessManagementConfigIpv6TableRowEditor 1 }

vtssAccessManagementConfigIpv6TableRowEditorVlanId OBJECT-TYPE
    SYNTAX      VTSSUnsigned16
    MAX-ACCESS  read-write
    STATUS      current
    DESCRIPTION 
        "The ID of specific VLAN interface that Access Management should take
         effect for IPv6."
    ::= { vtssAccessManagementConfigIpv6TableRowEditor 2 }

vtssAccessManagementConfigIpv6TableRowEditorStartAddress OBJECT-TYPE
    SYNTAX      InetAddressIPv6
    MAX-ACCESS  read-write
    STATUS      current
    DESCRIPTION 
        "The starting IPv6 address of the range that Access Management performs
         checking."
    ::= { vtssAccessManagementConfigIpv6TableRowEditor 3 }

vtssAccessManagementConfigIpv6TableRowEditorEndAddress OBJECT-TYPE
    SYNTAX      InetAddressIPv6
    MAX-ACCESS  read-write
    STATUS      current
    DESCRIPTION 
        "The ending IPv6 address of the range that Access Management performs
         checking."
    ::= { vtssAccessManagementConfigIpv6TableRowEditor 4 }

vtssAccessManagementConfigIpv6TableRowEditorWebServices OBJECT-TYPE
    SYNTAX      TruthValue
    MAX-ACCESS  read-write
    STATUS      current
    DESCRIPTION 
        "Enable/Disable HTTP and HTTPS functionality via Access Management. At
         least one of WebServices/SnmpServices/TelnetServices has to be enabled
         for a specific AccessIndex in Access Management IPv6 table."
    ::= { vtssAccessManagementConfigIpv6TableRowEditor 5 }

vtssAccessManagementConfigIpv6TableRowEditorSnmpServices OBJECT-TYPE
    SYNTAX      TruthValue
    MAX-ACCESS  read-write
    STATUS      current
    DESCRIPTION 
        "Enable/Disable SNMP functionality via Access Management. At least one
         of WebServices/SnmpServices/TelnetServices has to be enabled for a
         specific AccessIndex in Access Management IPv6 table."
    ::= { vtssAccessManagementConfigIpv6TableRowEditor 6 }

vtssAccessManagementConfigIpv6TableRowEditorTelnetServices OBJECT-TYPE
    SYNTAX      TruthValue
    MAX-ACCESS  read-write
    STATUS      current
    DESCRIPTION 
        "Enable/Disable TELNET/SSH functionality via Access Management. At least
         one of WebServices/SnmpServices/TelnetServices has to be enabled for a
         specific AccessIndex in Access Management IPv6 table."
    ::= { vtssAccessManagementConfigIpv6TableRowEditor 7 }

vtssAccessManagementConfigIpv6TableRowEditorAction OBJECT-TYPE
    SYNTAX      VTSSRowEditorState
    MAX-ACCESS  read-write
    STATUS      current
    DESCRIPTION 
        "Action"
    ::= { vtssAccessManagementConfigIpv6TableRowEditor 100 }

vtssAccessManagementStatus OBJECT IDENTIFIER
    ::= { vtssAccessManagementMibObjects 3 }

vtssAccessManagementControl OBJECT IDENTIFIER
    ::= { vtssAccessManagementMibObjects 4 }

vtssAccessManagementControlStatistics OBJECT IDENTIFIER
    ::= { vtssAccessManagementControl 1 }

vtssAccessManagementControlStatisticsClear OBJECT-TYPE
    SYNTAX      TruthValue
    MAX-ACCESS  read-write
    STATUS      current
    DESCRIPTION 
        "To trigger the control action (only) when TRUE."
    ::= { vtssAccessManagementControlStatistics 1 }

vtssAccessManagementStatistics OBJECT IDENTIFIER
    ::= { vtssAccessManagementMibObjects 5 }

vtssAccessManagementStatisticsHttpReceivedPkts OBJECT-TYPE
    SYNTAX      Unsigned32
    MAX-ACCESS  read-only
    STATUS      current
    DESCRIPTION 
        "Received count of frames via HTTP."
    ::= { vtssAccessManagementStatistics 1 }

vtssAccessManagementStatisticsHttpAllowedPkts OBJECT-TYPE
    SYNTAX      Unsigned32
    MAX-ACCESS  read-only
    STATUS      current
    DESCRIPTION 
        "Permit count of frames via HTTP."
    ::= { vtssAccessManagementStatistics 2 }

vtssAccessManagementStatisticsHttpDiscardedPkts OBJECT-TYPE
    SYNTAX      Unsigned32
    MAX-ACCESS  read-only
    STATUS      current
    DESCRIPTION 
        "Drop count of frames via HTTP."
    ::= { vtssAccessManagementStatistics 3 }

vtssAccessManagementStatisticsHttpsReceivedPkts OBJECT-TYPE
    SYNTAX      Unsigned32
    MAX-ACCESS  read-only
    STATUS      current
    DESCRIPTION 
        "Received count of frames via HTTPS."
    ::= { vtssAccessManagementStatistics 4 }

vtssAccessManagementStatisticsHttpsAllowedPkts OBJECT-TYPE
    SYNTAX      Unsigned32
    MAX-ACCESS  read-only
    STATUS      current
    DESCRIPTION 
        "Permit count of frames via HTTPS."
    ::= { vtssAccessManagementStatistics 5 }

vtssAccessManagementStatisticsHttpsDiscardedPkts OBJECT-TYPE
    SYNTAX      Unsigned32
    MAX-ACCESS  read-only
    STATUS      current
    DESCRIPTION 
        "Drop count of frames via HTTPS."
    ::= { vtssAccessManagementStatistics 6 }

vtssAccessManagementStatisticsSnmpReceivedPkts OBJECT-TYPE
    SYNTAX      Unsigned32
    MAX-ACCESS  read-only
    STATUS      current
    DESCRIPTION 
        "Received count of frames via SNMP."
    ::= { vtssAccessManagementStatistics 7 }

vtssAccessManagementStatisticsSnmpAllowedPkts OBJECT-TYPE
    SYNTAX      Unsigned32
    MAX-ACCESS  read-only
    STATUS      current
    DESCRIPTION 
        "Permit count of frames via SNMP."
    ::= { vtssAccessManagementStatistics 8 }

vtssAccessManagementStatisticsSnmpDiscardedPkts OBJECT-TYPE
    SYNTAX      Unsigned32
    MAX-ACCESS  read-only
    STATUS      current
    DESCRIPTION 
        "Drop count of frames via SNMP."
    ::= { vtssAccessManagementStatistics 9 }

vtssAccessManagementStatisticsTelnetReceivedPkts OBJECT-TYPE
    SYNTAX      Unsigned32
    MAX-ACCESS  read-only
    STATUS      current
    DESCRIPTION 
        "Received count of frames via TELNET."
    ::= { vtssAccessManagementStatistics 10 }

vtssAccessManagementStatisticsTelnetAllowedPkts OBJECT-TYPE
    SYNTAX      Unsigned32
    MAX-ACCESS  read-only
    STATUS      current
    DESCRIPTION 
        "Permit count of frames via TELNET."
    ::= { vtssAccessManagementStatistics 11 }

vtssAccessManagementStatisticsTelnetDiscardedPkts OBJECT-TYPE
    SYNTAX      Unsigned32
    MAX-ACCESS  read-only
    STATUS      current
    DESCRIPTION 
        "Drop count of frames via TELNET."
    ::= { vtssAccessManagementStatistics 12 }

vtssAccessManagementStatisticsSshReceivedPkts OBJECT-TYPE
    SYNTAX      Unsigned32
    MAX-ACCESS  read-only
    STATUS      current
    DESCRIPTION 
        "Received count of frames via SSH."
    ::= { vtssAccessManagementStatistics 13 }

vtssAccessManagementStatisticsSshAllowedPkts OBJECT-TYPE
    SYNTAX      Unsigned32
    MAX-ACCESS  read-only
    STATUS      current
    DESCRIPTION 
        "Permit count of frames via SSH."
    ::= { vtssAccessManagementStatistics 14 }

vtssAccessManagementStatisticsSshDiscardedPkts OBJECT-TYPE
    SYNTAX      Unsigned32
    MAX-ACCESS  read-only
    STATUS      current
    DESCRIPTION 
        "Drop count of frames via SSH."
    ::= { vtssAccessManagementStatistics 15 }

vtssAccessManagementMibConformance OBJECT IDENTIFIER
    ::= { vtssAccessManagementMib 2 }

vtssAccessManagementMibCompliances OBJECT IDENTIFIER
    ::= { vtssAccessManagementMibConformance 1 }

vtssAccessManagementMibGroups OBJECT IDENTIFIER
    ::= { vtssAccessManagementMibConformance 2 }

vtssAccessManagementConfigGlobalsInfoGroup OBJECT-GROUP
    OBJECTS     { vtssAccessManagementConfigGlobalsAdminState }
    STATUS      current
    DESCRIPTION
        "A collection of objects suitable for bulk operations."
    ::= { vtssAccessManagementMibGroups 1 }

vtssAccessManagementConfigIpv4TableInfoGroup OBJECT-GROUP
    OBJECTS     { vtssAccessManagementConfigIpv4VlanId, 
                  vtssAccessManagementConfigIpv4StartAddress, 
                  vtssAccessManagementConfigIpv4EndAddress, 
                  vtssAccessManagementConfigIpv4WebServices, 
                  vtssAccessManagementConfigIpv4SnmpServices, 
                  vtssAccessManagementConfigIpv4TelnetServices, 
                  vtssAccessManagementConfigIpv4Action }
    STATUS      current
    DESCRIPTION
        "A collection of objects suitable for bulk operations."
    ::= { vtssAccessManagementMibGroups 2 }

vtssAccessManagementConfigIpv4TableRowEditorInfoGroup OBJECT-GROUP
    OBJECTS     { vtssAccessManagementConfigIpv4TableRowEditorAccessIndex, 
                  vtssAccessManagementConfigIpv4TableRowEditorVlanId, 
                  vtssAccessManagementConfigIpv4TableRowEditorStartAddress, 
                  vtssAccessManagementConfigIpv4TableRowEditorEndAddress, 
                  vtssAccessManagementConfigIpv4TableRowEditorWebServices, 
                  vtssAccessManagementConfigIpv4TableRowEditorSnmpServices, 
                  vtssAccessManagementConfigIpv4TableRowEditorTelnetServices, 
                  vtssAccessManagementConfigIpv4TableRowEditorAction }
    STATUS      current
    DESCRIPTION
        "A collection of objects suitable for bulk operations."
    ::= { vtssAccessManagementMibGroups 3 }

vtssAccessManagementConfigIpv6TableInfoGroup OBJECT-GROUP
    OBJECTS     { vtssAccessManagementConfigIpv6VlanId, 
                  vtssAccessManagementConfigIpv6StartAddress, 
                  vtssAccessManagementConfigIpv6EndAddress, 
                  vtssAccessManagementConfigIpv6WebServices, 
                  vtssAccessManagementConfigIpv6SnmpServices, 
                  vtssAccessManagementConfigIpv6TelnetServices, 
                  vtssAccessManagementConfigIpv6Action }
    STATUS      current
    DESCRIPTION
        "A collection of objects suitable for bulk operations."
    ::= { vtssAccessManagementMibGroups 4 }

vtssAccessManagementConfigIpv6TableRowEditorInfoGroup OBJECT-GROUP
    OBJECTS     { vtssAccessManagementConfigIpv6TableRowEditorAccessIndex, 
                  vtssAccessManagementConfigIpv6TableRowEditorVlanId, 
                  vtssAccessManagementConfigIpv6TableRowEditorStartAddress, 
                  vtssAccessManagementConfigIpv6TableRowEditorEndAddress, 
                  vtssAccessManagementConfigIpv6TableRowEditorWebServices, 
                  vtssAccessManagementConfigIpv6TableRowEditorSnmpServices, 
                  vtssAccessManagementConfigIpv6TableRowEditorTelnetServices, 
                  vtssAccessManagementConfigIpv6TableRowEditorAction }
    STATUS      current
    DESCRIPTION
        "A collection of objects suitable for bulk operations."
    ::= { vtssAccessManagementMibGroups 5 }

vtssAccessManagementControlStatisticsInfoGroup OBJECT-GROUP
    OBJECTS     { vtssAccessManagementControlStatisticsClear }
    STATUS      current
    DESCRIPTION
        "A collection of objects suitable for bulk operations."
    ::= { vtssAccessManagementMibGroups 6 }

vtssAccessManagementStatisticsInfoGroup OBJECT-GROUP
    OBJECTS     { vtssAccessManagementStatisticsHttpReceivedPkts, 
                  vtssAccessManagementStatisticsHttpAllowedPkts, 
                  vtssAccessManagementStatisticsHttpDiscardedPkts, 
                  vtssAccessManagementStatisticsHttpsReceivedPkts, 
                  vtssAccessManagementStatisticsHttpsAllowedPkts, 
                  vtssAccessManagementStatisticsHttpsDiscardedPkts, 
                  vtssAccessManagementStatisticsSnmpReceivedPkts, 
                  vtssAccessManagementStatisticsSnmpAllowedPkts, 
                  vtssAccessManagementStatisticsSnmpDiscardedPkts, 
                  vtssAccessManagementStatisticsTelnetReceivedPkts, 
                  vtssAccessManagementStatisticsTelnetAllowedPkts, 
                  vtssAccessManagementStatisticsTelnetDiscardedPkts, 
                  vtssAccessManagementStatisticsSshReceivedPkts, 
                  vtssAccessManagementStatisticsSshAllowedPkts, 
                  vtssAccessManagementStatisticsSshDiscardedPkts }
    STATUS      current
    DESCRIPTION
        "A collection of objects suitable for bulk operations."
    ::= { vtssAccessManagementMibGroups 7 }

vtssAccessManagementMibCompliance MODULE-COMPLIANCE
    STATUS      current
    DESCRIPTION
        "The compliance statement for the implementation."

    MODULE      -- this module

        MANDATORY-GROUPS        { vtssAccessManagementConfigGlobalsInfoGroup, 
                  vtssAccessManagementConfigIpv4TableInfoGroup, 
                  vtssAccessManagementConfigIpv4TableRowEditorInfoGroup, 
                  vtssAccessManagementConfigIpv6TableInfoGroup, 
                  vtssAccessManagementConfigIpv6TableRowEditorInfoGroup, 
                  vtssAccessManagementControlStatisticsInfoGroup, 
                  vtssAccessManagementStatisticsInfoGroup }

    ::= { vtssAccessManagementMibCompliances 1 }

END
