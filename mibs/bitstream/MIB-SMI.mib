-- *****************************************************************
-- MIB-BTS-SMI:  BitStream enterprise structure 
-- ****************************************************************

BTS-SMI DEFINITIONS ::= BEGIN

IMPORTS
    MODULE-IDENTITY,
    OBJECT-IDENTITY,
    enterprises
        FROM SNMPv2-SMI;


bitstream MODULE-IDENTITY
    LAST-UPDATED    "202503200000Z"
    ORGANIZATION    "BitStream Sp. z o.o."
    CONTACT-INFO
            "www.bitstream.pl"
    DESCRIPTION
        "The Structure of Management Information for the
        Bitstream enterprise."
    REVISION        "202503200000Z"
    DESCRIPTION
        "Initial version of this MIB module."
    ::= { enterprises 19829 }


switchMgmt OBJECT-IDENTITY
    STATUS          current
    DESCRIPTION
        "switchMgmt is the root OBJECT IDENTIFIER from
         which object id values are assigned."
    ::= { bitstream 1 }



END
