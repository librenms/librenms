-- *****************************************************************
-- SSH-MIB:  Vitesse private MIB
--
-- Copyright (c) 2002-2013 Vitesse Semiconductor Corporation "Vitesse".
-- All Rights Reserved.
--
-- ****************************************************************

VTSS-SSH-MIB DEFINITIONS ::= BEGIN

IMPORTS
    MODULE-COMPLIANCE, OBJECT-GROUP
        FROM SNMPv2-CONF
    MODULE-IDENTITY, OBJECT-TYPE
        FROM SNMPv2-SMI
    TEXTUAL-CONVENTION
        FROM SNMPv2-TC
    vtssSwitchMgmt
        FROM VTSS-SMI
    TruthValue FROM SNMPv2-TC
    ;

vtssSshMib MODULE-IDENTITY
    LAST-UPDATED "201407010000Z"
    ORGANIZATION
        "Vitesse Semiconductor Corporation"
    CONTACT-INFO
        "Application support <application_support@vitesse.com>"
    DESCRIPTION
        "This is a private version of the SSH MIB"
    REVISION    "201407010000Z"
    DESCRIPTION
        "Initial version"
    ::= { vtssSwitchMgmt 49 }


vtssSshMibObjects OBJECT IDENTIFIER
    ::= { vtssSshMib 1 }

vtssSshConfig OBJECT IDENTIFIER
    ::= { vtssSshMibObjects 2 }

vtssSshConfigGlobals OBJECT IDENTIFIER
    ::= { vtssSshConfig 1 }

vtssSshConfigGlobalsAdminState OBJECT-TYPE
    SYNTAX      TruthValue
    MAX-ACCESS  read-write
    STATUS      current
    DESCRIPTION 
        "Enable/Disable the SSH functionality."
    ::= { vtssSshConfigGlobals 1 }

vtssSshMibConformance OBJECT IDENTIFIER
    ::= { vtssSshMib 2 }

vtssSshMibCompliances OBJECT IDENTIFIER
    ::= { vtssSshMibConformance 1 }

vtssSshMibGroups OBJECT IDENTIFIER
    ::= { vtssSshMibConformance 2 }

vtssSshConfigGlobalsInfoGroup OBJECT-GROUP
    OBJECTS     { vtssSshConfigGlobalsAdminState }
    STATUS      current
    DESCRIPTION
        "A collection of objects suitable for bulk operations."
    ::= { vtssSshMibGroups 1 }

vtssSshMibCompliance MODULE-COMPLIANCE
    STATUS      current
    DESCRIPTION
        "The compliance statement for the implementation."

    MODULE      -- this module

        MANDATORY-GROUPS        { vtssSshConfigGlobalsInfoGroup }

    ::= { vtssSshMibCompliances 1 }

END
