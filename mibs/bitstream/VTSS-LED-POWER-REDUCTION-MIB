-- *****************************************************************
-- LED-POWER-REDUCTION-MIB:  Vitesse private MIB
--
-- Copyright (c) 2002-2013 Vitesse Semiconductor Corporation "Vitesse".
-- All Rights Reserved.
--
-- ****************************************************************

VTSS-LED-POWER-REDUCTION-MIB DEFINITIONS ::= BEGIN

IMPORTS
    MODULE-COMPLIANCE, OBJECT-GROUP
        FROM SNMPv2-CONF
    MODULE-IDENTITY, OBJECT-TYPE
        FROM SNMPv2-SMI
    TEXTUAL-CONVENTION
        FROM SNMPv2-TC
    vtssSwitchMgmt
        FROM VTSS-SMI
    Integer32 FROM SNMPv2-SMI
    TruthValue FROM SNMPv2-TC
    VTSSUnsigned16 FROM VTSS-TC
    VTSSUnsigned8 FROM VTSS-TC
    ;

vtssLedPowerReductionMib MODULE-IDENTITY
    LAST-UPDATED "201410100000Z"
    ORGANIZATION
        "Vitesse Semiconductor Corporation"
    CONTACT-INFO
        "Application support <application_support@vitesse.com>"
    DESCRIPTION
        "This is a private version of LEDs power reduction. The LEDs power
         consumption can be reduced by lowering the LEDs intensity"
    REVISION    "201410100000Z"
    DESCRIPTION
        "Editorial changes"
    REVISION    "201407010000Z"
    DESCRIPTION
        "Initial version"
    ::= { vtssSwitchMgmt 77 }


vtssLedPowerReductionMibObjects OBJECT IDENTIFIER
    ::= { vtssLedPowerReductionMib 1 }

vtssLedPowerReductionConfig OBJECT IDENTIFIER
    ::= { vtssLedPowerReductionMibObjects 2 }

vtssLedPowerReductionConfigGlobals OBJECT IDENTIFIER
    ::= { vtssLedPowerReductionConfig 1 }

vtssLedPowerReductionConfigGlobalsMaintenanceDuration OBJECT-TYPE
    SYNTAX      VTSSUnsigned16 (0..65535)
    MAX-ACCESS  read-write
    STATUS      current
    DESCRIPTION 
        "The switch maintenance duration (in seconds). During switch maintenance
         LEDs will glow in full intensity after either a port has changed link
         state or the LED push button has been pushed."
    ::= { vtssLedPowerReductionConfigGlobals 1 }

vtssLedPowerReductionConfigGlobalsErrorEnable OBJECT-TYPE
    SYNTAX      TruthValue
    MAX-ACCESS  read-write
    STATUS      current
    DESCRIPTION 
        "Turned on LEDs at full brightness(100% intensity) when LED is blinking
         in red because of either software error or fatal occurred. true means
         LEDs will glow in full brightness, false means LEDs will not glow in
         full brightness."
    ::= { vtssLedPowerReductionConfigGlobals 2 }

vtssLedPowerReductionConfigGlobalsParamTable OBJECT-TYPE
    SYNTAX      SEQUENCE OF VTSSLedPowerReductionConfigGlobalsParamEntry
    MAX-ACCESS  not-accessible
    STATUS      current
    DESCRIPTION 
        "This is a table to assign led intensity level to each clock hour(based
         on 24-hour time notaion) of the day"
    ::= { vtssLedPowerReductionConfig 2 }

vtssLedPowerReductionConfigGlobalsParamEntry OBJECT-TYPE
    SYNTAX      VTSSLedPowerReductionConfigGlobalsParamEntry
    MAX-ACCESS  not-accessible
    STATUS      current
    DESCRIPTION 
        "Each clock hour of the day associates with led intensity level"
    INDEX       { vtssLedPowerReductionConfigGlobalsParamClockTimeHour }
    ::= { vtssLedPowerReductionConfigGlobalsParamTable 1 }

VTSSLedPowerReductionConfigGlobalsParamEntry ::= SEQUENCE {
    vtssLedPowerReductionConfigGlobalsParamClockTimeHour    Integer32,
    vtssLedPowerReductionConfigGlobalsParamIntensityLevel   VTSSUnsigned8
}

vtssLedPowerReductionConfigGlobalsParamClockTimeHour OBJECT-TYPE
    SYNTAX      Integer32 (0..23)
    MAX-ACCESS  not-accessible
    STATUS      current
    DESCRIPTION 
        "Clock time hour. Hour is based on 24-hour time notation. If hour is x
         then LEDs will start glow at clock time x:00 of the day with associated
         LEDs intensity level."
    ::= { vtssLedPowerReductionConfigGlobalsParamEntry 1 }

vtssLedPowerReductionConfigGlobalsParamIntensityLevel OBJECT-TYPE
    SYNTAX      VTSSUnsigned8 (0..100)
    MAX-ACCESS  read-write
    STATUS      current
    DESCRIPTION 
        "Led power intensity level. The LEDs brightness in percentage. 100 means
         full intensity(maximum power consumption), 0 means LEDs are off(no
         power consumption)."
    ::= { vtssLedPowerReductionConfigGlobalsParamEntry 2 }

vtssLedPowerReductionMibConformance OBJECT IDENTIFIER
    ::= { vtssLedPowerReductionMib 2 }

vtssLedPowerReductionMibCompliances OBJECT IDENTIFIER
    ::= { vtssLedPowerReductionMibConformance 1 }

vtssLedPowerReductionMibGroups OBJECT IDENTIFIER
    ::= { vtssLedPowerReductionMibConformance 2 }

vtssLedPowerReductionConfigGlobalsInfoGroup OBJECT-GROUP
    OBJECTS     { vtssLedPowerReductionConfigGlobalsMaintenanceDuration, 
                  vtssLedPowerReductionConfigGlobalsErrorEnable }
    STATUS      current
    DESCRIPTION
        "A collection of objects suitable for bulk operations."
    ::= { vtssLedPowerReductionMibGroups 1 }

vtssLedPowerReductionConfigGlobalsParamTableInfoGroup OBJECT-GROUP
    OBJECTS     { vtssLedPowerReductionConfigGlobalsParamIntensityLevel }
    STATUS      current
    DESCRIPTION
        "A collection of objects suitable for bulk operations."
    ::= { vtssLedPowerReductionMibGroups 2 }

vtssLedPowerReductionMibCompliance MODULE-COMPLIANCE
    STATUS      current
    DESCRIPTION
        "The compliance statement for the implementation."

    MODULE      -- this module

        MANDATORY-GROUPS        { 
                  vtssLedPowerReductionConfigGlobalsInfoGroup, 
                  vtssLedPowerReductionConfigGlobalsParamTableInfoGroup }

    ::= { vtssLedPowerReductionMibCompliances 1 }

END
