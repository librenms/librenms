-- *****************************************************************
-- MIB-MEP: BitStream ENT private MIB
-- ****************************************************************

MIB-MEP DEFINITIONS ::= BEGIN

IMPORTS
    MODULE-COMPLIANCE, OBJECT-GROUP FROM SNMPv2-CONF
    MODULE-IDENTITY, OBJECT-TYPE FROM SNMPv2-SMI
    TEXTUAL-CONVENTION FROM SNMPv2-TC
    switchMgmt FROM BTS-SMI
    Counter64 FROM SNMPv2-SMI
    Integer32 FROM SNMPv2-SMI
    IpAddress FROM SNMPv2-SMI
    Unsigned32 FROM SNMPv2-SMI
    MacAddress FROM SNMPv2-TC
    TruthValue FROM SNMPv2-TC
    DisplayString FROM BTS-TC
    InterfaceIndex FROM BTS-TC
    RowEditorState FROM BTS-TC
    Unsigned16 FROM BTS-TC
    Unsigned64 FROM BTS-TC
    Unsigned8 FROM BTS-TC
    ;

mepMib MODULE-IDENTITY
    LAST-UPDATED "202503200000Z"
    ORGANIZATION
        "BitStream Sp. z o.o."
    CONTACT-INFO
        "www.bitstream.pl"
    DESCRIPTION
        "This is a private service OAM (Y.1731/G802.1ag/G8113.1/G8113.2) MIB"
    REVISION    "201703290000Z"
    DESCRIPTION
        "Added support for specifying SLM Test ID."
    REVISION    "201610120000Z"
    DESCRIPTION
        "Added support for LM IntervalElapsed object"
    REVISION    "201501190000Z"
    DESCRIPTION
        "Added Loss Measurement Availability, High Loss Interval and Signal
         Degrade"
    REVISION    "201501020000Z"
    DESCRIPTION
        "Removed DEI"
    REVISION    "201412030000Z"
    DESCRIPTION
        "Adding Link State Tracking"
    REVISION    "201411260000Z"
    DESCRIPTION
        "Adding Loss Measurement OAM frame counting object"
    REVISION    "201411140000Z"
    DESCRIPTION
        "Refactoring regarding Ifindex. Domain element is removed and flow
         element is changed to be Ifindex containing domain"
    REVISION    "201409300000Z"
    DESCRIPTION
        "Added mepConfigRt and mepStatusRt for Route Trace configuration
         and status"
    REVISION    "201409030000Z"
    DESCRIPTION
        "Added mepConfigClientFlowDomain and mepConfigClientFlowFlowId
         to mepConfigClientFlowTable"
    REVISION    "201407010000Z"
    DESCRIPTION
        "Initial version"
    ::= { switchMgmt 46 }


MepApsType ::= TEXTUAL-CONVENTION
    STATUS      current
    DESCRIPTION
        "Type of APS."
    SYNTAX      INTEGER { invalidAps(0), linearAps(1), ringAps(2) }

MepBfdAuthenticationType ::= TEXTUAL-CONVENTION
    STATUS      current
    DESCRIPTION
        "BFD authentication type."
    SYNTAX      INTEGER { disabled(0), simplePwd(1), keyedMD5(2),
                          meticulousKeyedMD5(3), keyedSHA1(4),
                          meticulousKeyedSHA1(5) }

MepBfdDiagnosticCode ::= TEXTUAL-CONVENTION
    STATUS      current
    DESCRIPTION
        "BFD diagnostic code."
    SYNTAX      INTEGER { none(0), detectExpired(1), echoFailed(2),
                          remoteDown(3), fwdPlaneReset(4),
                          pathDown(5), concatPathDown(6),
                          adminDown(7), reverseConcatDown(8),
                          misconnectivity(9) }

MepBfdSessionState ::= TEXTUAL-CONVENTION
    STATUS      current
    DESCRIPTION
        "State of BFD session."
    SYNTAX      INTEGER { adminDown(0), down(1), init(2), up(3) }

MepCast ::= TEXTUAL-CONVENTION
    STATUS      current
    DESCRIPTION
        "Unicast or Multicast selection."
    SYNTAX      INTEGER { uniCast(0), multiCast(1) }

MepDmCalcWay ::= TEXTUAL-CONVENTION
    STATUS      current
    DESCRIPTION
        "Round trip or flow calculation way selection."
    SYNTAX      INTEGER { roundTrip(0), flow(1) }

MepDmOverflowAction ::= TEXTUAL-CONVENTION
    STATUS      current
    DESCRIPTION
        "Action when internal total delay counter overflow."
    SYNTAX      INTEGER { disableDm(0), continueDm(1) }

MepDmTimeUnit ::= TEXTUAL-CONVENTION
    STATUS      current
    DESCRIPTION
        "Calculation time unit."
    SYNTAX      INTEGER { microSeconds(0), nanoSeconds(1) }

MepEnded ::= TEXTUAL-CONVENTION
    STATUS      current
    DESCRIPTION
        "Dual/single ended selection."
    SYNTAX      INTEGER { singleEnded(0), dualEnded(1) }

MepInstanceDirection ::= TEXTUAL-CONVENTION
    STATUS      current
    DESCRIPTION
        "The instance direction."
    SYNTAX      INTEGER { down(0), up(1) }

MepInstanceMode ::= TEXTUAL-CONVENTION
    STATUS      current
    DESCRIPTION
        "The instance mode."
    SYNTAX      INTEGER { mep(0), mip(1) }

MepLmAvailState ::= TEXTUAL-CONVENTION
    STATUS      current
    DESCRIPTION
        "Loss Measurement Availability State."
    SYNTAX      INTEGER { available(0), unavailable(1) }

MepLtRelayAction ::= TEXTUAL-CONVENTION
    STATUS      current
    DESCRIPTION
        "The Link Trace relay action."
    SYNTAX      INTEGER { relayUnknown(0), relayHit(1), relayFdb(2),
                          relayMpdb(3) }

MepMegIdFormat ::= TEXTUAL-CONVENTION
    STATUS      current
    DESCRIPTION
        "The MEG-ID format."
    SYNTAX      INTEGER { ituIcc(0), ieeeString(1), ituCcIcc(2) }

MepOamCount ::= TEXTUAL-CONVENTION
    STATUS      current
    DESCRIPTION
        "Loss Measurement OAM frame counting selection."
    SYNTAX      INTEGER { countAsY1731(0), countNone(1), countAll(2) }

MepRtPadTlvType ::= TEXTUAL-CONVENTION
    STATUS      current
    DESCRIPTION
        "RT Pad TLV type."
    SYNTAX      INTEGER { none(0), drop(1), copy(2) }

MepRtReturnCode ::= TEXTUAL-CONVENTION
    STATUS      current
    DESCRIPTION
        "RT return code type."
    SYNTAX      INTEGER { none(0), malformed(1), tlvError(2),
                          isEgress(3), noMapping(4),
                          downMapMismatch(5), upIfUnknown(6),
                          labelSwitch(8), labelSwitchNoFwd(9),
                          mappingWrong(10), noLabel(11),
                          protocolError(12), premature(13) }

MepTstPattern ::= TEXTUAL-CONVENTION
    STATUS      current
    DESCRIPTION
        "Pattern in TST frame Data TLV."
    SYNTAX      INTEGER { allZero(0), allOne(1), hexAA(2) }

MepTxRate ::= TEXTUAL-CONVENTION
    STATUS      current
    DESCRIPTION
        "PDU transmission rate."
    SYNTAX      INTEGER { invalid(0), frames300PerSecond(1),
                          frames100PerSecond(2), frames10PerSecond(3),
                          frames1PerSecond(4), frames6PerMinute(5),
                          frames1PerMinute(6), frames6PerHour(7) }

mepMibObjects OBJECT IDENTIFIER
    ::= { mepMib 1 }

mepCapabilities OBJECT IDENTIFIER
    ::= { mepMibObjects 1 }

mepCapabilitiesInstanceMax OBJECT-TYPE
    SYNTAX      Unsigned32
    MAX-ACCESS  read-only
    STATUS      current
    DESCRIPTION
        "Max number of MEP instance"
    ::= { mepCapabilities 1 }

mepCapabilitiesPeerMax OBJECT-TYPE
    SYNTAX      Unsigned32
    MAX-ACCESS  read-only
    STATUS      current
    DESCRIPTION
        "Max number of peer MEP"
    ::= { mepCapabilities 2 }

mepCapabilitiesTransactionMax OBJECT-TYPE
    SYNTAX      Unsigned32
    MAX-ACCESS  read-only
    STATUS      current
    DESCRIPTION
        "Max number of Link Trace transaction"
    ::= { mepCapabilities 3 }

mepCapabilitiesReplyMax OBJECT-TYPE
    SYNTAX      Unsigned32
    MAX-ACCESS  read-only
    STATUS      current
    DESCRIPTION
        "Max number of reply in a transaction"
    ::= { mepCapabilities 4 }

mepCapabilitiesClientFlowsMax OBJECT-TYPE
    SYNTAX      Unsigned32
    MAX-ACCESS  read-only
    STATUS      current
    DESCRIPTION
        "Max number of client flows"
    ::= { mepCapabilities 5 }

mepCapabilitiesMacMength OBJECT-TYPE
    SYNTAX      Unsigned32
    MAX-ACCESS  read-only
    STATUS      current
    DESCRIPTION
        "MAC length"
    ::= { mepCapabilities 6 }

mepCapabilitiesMegCodeLength OBJECT-TYPE
    SYNTAX      Unsigned32
    MAX-ACCESS  read-only
    STATUS      current
    DESCRIPTION
        "MAX length of Both Maintenance Domain Name and MEG-ID include a NULL
         termination"
    ::= { mepCapabilities 7 }

mepCapabilitiesDmIntervalMin OBJECT-TYPE
    SYNTAX      Unsigned32
    MAX-ACCESS  read-only
    STATUS      current
    DESCRIPTION
        "MIN DM transmission interval "
    ::= { mepCapabilities 8 }

mepCapabilitiesDmIntervalMax OBJECT-TYPE
    SYNTAX      Unsigned32
    MAX-ACCESS  read-only
    STATUS      current
    DESCRIPTION
        "MAX DM transmission interval"
    ::= { mepCapabilities 9 }

mepCapabilitiesDmLastnMin OBJECT-TYPE
    SYNTAX      Unsigned32
    MAX-ACCESS  read-only
    STATUS      current
    DESCRIPTION
        "MIN number of DM LastN for average calculation"
    ::= { mepCapabilities 10 }

mepCapabilitiesDmLastnMax OBJECT-TYPE
    SYNTAX      Unsigned32
    MAX-ACCESS  read-only
    STATUS      current
    DESCRIPTION
        "MAX number of DM LastN for average calculation"
    ::= { mepCapabilities 11 }

mepCapabilitiesLbmSizeMax OBJECT-TYPE
    SYNTAX      Unsigned32
    MAX-ACCESS  read-only
    STATUS      current
    DESCRIPTION
        "The maximum LBM frame size"
    ::= { mepCapabilities 12 }

mepCapabilitiesLbmSizeMin OBJECT-TYPE
    SYNTAX      Unsigned32
    MAX-ACCESS  read-only
    STATUS      current
    DESCRIPTION
        "The minimum LBM frame size"
    ::= { mepCapabilities 13 }

mepCapabilitiesTstSizeMax OBJECT-TYPE
    SYNTAX      Unsigned32
    MAX-ACCESS  read-only
    STATUS      current
    DESCRIPTION
        "The maximum TST frame size"
    ::= { mepCapabilities 14 }

mepCapabilitiesTstSizeMin OBJECT-TYPE
    SYNTAX      Unsigned32
    MAX-ACCESS  read-only
    STATUS      current
    DESCRIPTION
        "The minimum TST frame size"
    ::= { mepCapabilities 15 }

mepCapabilitiesTstRateMax OBJECT-TYPE
    SYNTAX      Unsigned32
    MAX-ACCESS  read-only
    STATUS      current
    DESCRIPTION
        "The maximum TST bit rate"
    ::= { mepCapabilities 16 }

mepCapabilitiesClientPrioHighest OBJECT-TYPE
    SYNTAX      Unsigned32
    MAX-ACCESS  read-only
    STATUS      current
    DESCRIPTION
        "The highest possible client priority is requested"
    ::= { mepCapabilities 17 }

mepCapabilitiesItuG8113dot2 OBJECT-TYPE
    SYNTAX      TruthValue
    MAX-ACCESS  read-only
    STATUS      current
    DESCRIPTION
        "Indicates if ITU G8113.2 is supported on this system"
    ::= { mepCapabilities 18 }

mepCapabilitiesVoeSupport OBJECT-TYPE
    SYNTAX      TruthValue
    MAX-ACCESS  read-only
    STATUS      current
    DESCRIPTION
        "Indicates if VOE is supported on this system"
    ::= { mepCapabilities 19 }

mepCapabilitiesLbToSendInfinite OBJECT-TYPE
    SYNTAX      Unsigned32
    MAX-ACCESS  read-only
    STATUS      current
    DESCRIPTION
        "Send LBM infinite - test behaviour"
    ::= { mepCapabilities 20 }

mepCapabilitiesBfdAuthKeyMax OBJECT-TYPE
    SYNTAX      Unsigned32
    MAX-ACCESS  read-only
    STATUS      current
    DESCRIPTION
        "Maximum number of BFD authentication keys"
    ::= { mepCapabilities 21 }

mepCapabilitiesSlmSizeMax OBJECT-TYPE
    SYNTAX      Unsigned32
    MAX-ACCESS  read-only
    STATUS      current
    DESCRIPTION
        "The maximum SLM frame size"
    ::= { mepCapabilities 22 }

mepCapabilitiesSlmSizeMin OBJECT-TYPE
    SYNTAX      Unsigned32
    MAX-ACCESS  read-only
    STATUS      current
    DESCRIPTION
        "The minimum SLM frame size"
    ::= { mepCapabilities 23 }

mepConfig OBJECT IDENTIFIER
    ::= { mepMibObjects 2 }

mepConfigInstance OBJECT IDENTIFIER
    ::= { mepConfig 1 }

mepConfigInstanceTable OBJECT-TYPE
    SYNTAX      SEQUENCE OF MepConfigInstanceEntry
    MAX-ACCESS  not-accessible
    STATUS      current
    DESCRIPTION
        "This is a table of created instance configuration parameters"
    ::= { mepConfigInstance 1 }

mepConfigInstanceEntry OBJECT-TYPE
    SYNTAX      MepConfigInstanceEntry
    MAX-ACCESS  not-accessible
    STATUS      current
    DESCRIPTION
        "This is a created instance configuration parameters. Not all parameters
         can be changed"
    INDEX       { mepConfigInstanceId }
    ::= { mepConfigInstanceTable 1 }

MepConfigInstanceEntry ::= SEQUENCE {
    mepConfigInstanceId         Integer32,
    mepConfigInstanceMode       MepInstanceMode,
    mepConfigInstanceDirection  MepInstanceDirection,
    mepConfigInstanceFlow       InterfaceIndex,
    mepConfigInstancePort       InterfaceIndex,
    mepConfigInstanceLevel      Unsigned32,
    mepConfigInstanceVid        Unsigned16,
    mepConfigInstanceVoe        TruthValue,
    mepConfigInstanceMac        MacAddress,
    mepConfigInstanceFormat     MepMegIdFormat,
    mepConfigInstanceName       DisplayString,
    mepConfigInstanceMeg        DisplayString,
    mepConfigInstanceMep        Unsigned32,
    mepConfigInstanceEvcPag     Unsigned32,
    mepConfigInstanceEvcQos     Unsigned32,
    mepConfigInstanceAction     RowEditorState
}

mepConfigInstanceId OBJECT-TYPE
    SYNTAX      Integer32 (0..2147483647)
    MAX-ACCESS  not-accessible
    STATUS      current
    DESCRIPTION
        "The MEP instance ID"
    ::= { mepConfigInstanceEntry 1 }

mepConfigInstanceMode OBJECT-TYPE
    SYNTAX      MepInstanceMode
    MAX-ACCESS  read-write
    STATUS      current
    DESCRIPTION
        "The instance mode. Cannot be changed after creation."
    ::= { mepConfigInstanceEntry 2 }

mepConfigInstanceDirection OBJECT-TYPE
    SYNTAX      MepInstanceDirection
    MAX-ACCESS  read-write
    STATUS      current
    DESCRIPTION
        "The instance direction. Cannot be changed after creation."
    ::= { mepConfigInstanceEntry 3 }

mepConfigInstanceFlow OBJECT-TYPE
    SYNTAX      InterfaceIndex
    MAX-ACCESS  read-write
    STATUS      current
    DESCRIPTION
        "The flow instance (VLAN - EVC). Cannot be changed after creation."
    ::= { mepConfigInstanceEntry 4 }

mepConfigInstancePort OBJECT-TYPE
    SYNTAX      InterfaceIndex
    MAX-ACCESS  read-write
    STATUS      current
    DESCRIPTION
        "The instance residence port. Cannot be changed after creation."
    ::= { mepConfigInstanceEntry 5 }

mepConfigInstanceLevel OBJECT-TYPE
    SYNTAX      Unsigned32
    MAX-ACCESS  read-write
    STATUS      current
    DESCRIPTION
        "The instance level"
    ::= { mepConfigInstanceEntry 6 }

mepConfigInstanceVid OBJECT-TYPE
    SYNTAX      Unsigned16
    MAX-ACCESS  read-write
    STATUS      current
    DESCRIPTION
        "VID used for tagged Port domain OAM. Create a VLAN MEP instead - if
         possible"
    ::= { mepConfigInstanceEntry 7 }

mepConfigInstanceVoe OBJECT-TYPE
    SYNTAX      TruthValue
    MAX-ACCESS  read-write
    STATUS      current
    DESCRIPTION
        "Make the instance VOE based - if possible"
    ::= { mepConfigInstanceEntry 8 }

mepConfigInstanceMac OBJECT-TYPE
    SYNTAX      MacAddress
    MAX-ACCESS  read-write
    STATUS      current
    DESCRIPTION
        "The instance unicast MAC. If 'all zero' the residence port MAC is used"
    ::= { mepConfigInstanceEntry 9 }

mepConfigInstanceFormat OBJECT-TYPE
    SYNTAX      MepMegIdFormat
    MAX-ACCESS  read-write
    STATUS      current
    DESCRIPTION
        "The MEG-ID format"
    ::= { mepConfigInstanceEntry 10 }

mepConfigInstanceName OBJECT-TYPE
    SYNTAX      DisplayString (SIZE(0..16))
    MAX-ACCESS  read-write
    STATUS      current
    DESCRIPTION
        "IEEE Maintenance Domain Name (string)"
    ::= { mepConfigInstanceEntry 11 }

mepConfigInstanceMeg OBJECT-TYPE
    SYNTAX      DisplayString (SIZE(0..16))
    MAX-ACCESS  read-write
    STATUS      current
    DESCRIPTION
        "Unique MEG ID (string)"
    ::= { mepConfigInstanceEntry 12 }

mepConfigInstanceMep OBJECT-TYPE
    SYNTAX      Unsigned32
    MAX-ACCESS  read-write
    STATUS      current
    DESCRIPTION
        "MEP id of this instance"
    ::= { mepConfigInstanceEntry 13 }

mepConfigInstanceEvcPag OBJECT-TYPE
    SYNTAX      Unsigned32
    MAX-ACCESS  read-write
    STATUS      current
    DESCRIPTION
        "EVC generated policy PAG value. This is used as IS2 key"
    ::= { mepConfigInstanceEntry 14 }

mepConfigInstanceEvcQos OBJECT-TYPE
    SYNTAX      Unsigned32
    MAX-ACCESS  read-write
    STATUS      current
    DESCRIPTION
        "EVC QoS value. Used for getting queue frame LM counters."
    ::= { mepConfigInstanceEntry 15 }

mepConfigInstanceAction OBJECT-TYPE
    SYNTAX      RowEditorState
    MAX-ACCESS  read-write
    STATUS      current
    DESCRIPTION
        "Action"
    ::= { mepConfigInstanceEntry 100 }

mepConfigInstanceRowEditor OBJECT IDENTIFIER
    ::= { mepConfigInstance 2 }

mepConfigInstanceRowEditorId OBJECT-TYPE
    SYNTAX      Integer32 (0..2147483647)
    MAX-ACCESS  read-write
    STATUS      current
    DESCRIPTION
        "The MEP instance ID"
    ::= { mepConfigInstanceRowEditor 1 }

mepConfigInstanceRowEditorMode OBJECT-TYPE
    SYNTAX      MepInstanceMode
    MAX-ACCESS  read-write
    STATUS      current
    DESCRIPTION
        "The instance mode. Cannot be changed after creation."
    ::= { mepConfigInstanceRowEditor 2 }

mepConfigInstanceRowEditorDirection OBJECT-TYPE
    SYNTAX      MepInstanceDirection
    MAX-ACCESS  read-write
    STATUS      current
    DESCRIPTION
        "The instance direction. Cannot be changed after creation."
    ::= { mepConfigInstanceRowEditor 3 }

mepConfigInstanceRowEditorFlow OBJECT-TYPE
    SYNTAX      InterfaceIndex
    MAX-ACCESS  read-write
    STATUS      current
    DESCRIPTION
        "The flow instance (VLAN - EVC). Cannot be changed after creation."
    ::= { mepConfigInstanceRowEditor 4 }

mepConfigInstanceRowEditorPort OBJECT-TYPE
    SYNTAX      InterfaceIndex
    MAX-ACCESS  read-write
    STATUS      current
    DESCRIPTION
        "The instance residence port. Cannot be changed after creation."
    ::= { mepConfigInstanceRowEditor 5 }

mepConfigInstanceRowEditorLevel OBJECT-TYPE
    SYNTAX      Unsigned32
    MAX-ACCESS  read-write
    STATUS      current
    DESCRIPTION
        "The instance level"
    ::= { mepConfigInstanceRowEditor 6 }

mepConfigInstanceRowEditorVid OBJECT-TYPE
    SYNTAX      Unsigned16
    MAX-ACCESS  read-write
    STATUS      current
    DESCRIPTION
        "VID used for tagged Port domain OAM. Create a VLAN MEP instead - if
         possible"
    ::= { mepConfigInstanceRowEditor 7 }

mepConfigInstanceRowEditorVoe OBJECT-TYPE
    SYNTAX      TruthValue
    MAX-ACCESS  read-write
    STATUS      current
    DESCRIPTION
        "Make the instance VOE based - if possible"
    ::= { mepConfigInstanceRowEditor 8 }

mepConfigInstanceRowEditorMac OBJECT-TYPE
    SYNTAX      MacAddress
    MAX-ACCESS  read-write
    STATUS      current
    DESCRIPTION
        "The instance unicast MAC. If 'all zero' the residence port MAC is used"
    ::= { mepConfigInstanceRowEditor 9 }

mepConfigInstanceRowEditorFormat OBJECT-TYPE
    SYNTAX      MepMegIdFormat
    MAX-ACCESS  read-write
    STATUS      current
    DESCRIPTION
        "The MEG-ID format"
    ::= { mepConfigInstanceRowEditor 10 }

mepConfigInstanceRowEditorName OBJECT-TYPE
    SYNTAX      DisplayString (SIZE(0..16))
    MAX-ACCESS  read-write
    STATUS      current
    DESCRIPTION
        "IEEE Maintenance Domain Name (string)"
    ::= { mepConfigInstanceRowEditor 11 }

mepConfigInstanceRowEditorMeg OBJECT-TYPE
    SYNTAX      DisplayString (SIZE(0..16))
    MAX-ACCESS  read-write
    STATUS      current
    DESCRIPTION
        "Unique MEG ID (string)"
    ::= { mepConfigInstanceRowEditor 12 }

mepConfigInstanceRowEditorMep OBJECT-TYPE
    SYNTAX      Unsigned32
    MAX-ACCESS  read-write
    STATUS      current
    DESCRIPTION
        "MEP id of this instance"
    ::= { mepConfigInstanceRowEditor 13 }

mepConfigInstanceRowEditorEvcPag OBJECT-TYPE
    SYNTAX      Unsigned32
    MAX-ACCESS  read-write
    STATUS      current
    DESCRIPTION
        "EVC generated policy PAG value. This is used as IS2 key"
    ::= { mepConfigInstanceRowEditor 14 }

mepConfigInstanceRowEditorEvcQos OBJECT-TYPE
    SYNTAX      Unsigned32
    MAX-ACCESS  read-write
    STATUS      current
    DESCRIPTION
        "EVC QoS value. Used for getting queue frame LM counters."
    ::= { mepConfigInstanceRowEditor 15 }

mepConfigInstanceRowEditorAction OBJECT-TYPE
    SYNTAX      RowEditorState
    MAX-ACCESS  read-write
    STATUS      current
    DESCRIPTION
        "Action"
    ::= { mepConfigInstanceRowEditor 100 }

mepConfigInstancePeerTable OBJECT-TYPE
    SYNTAX      SEQUENCE OF MepConfigInstancePeerEntry
    MAX-ACCESS  not-accessible
    STATUS      current
    DESCRIPTION
        "This is a table of peer MEP configuration parameters"
    ::= { mepConfigInstance 3 }

mepConfigInstancePeerEntry OBJECT-TYPE
    SYNTAX      MepConfigInstancePeerEntry
    MAX-ACCESS  not-accessible
    STATUS      current
    DESCRIPTION
        "This is a peer MEP configuration parameters"
    INDEX       { mepConfigInstancePeerId,
                  mepConfigInstancePeerPeerId }
    ::= { mepConfigInstancePeerTable 1 }

MepConfigInstancePeerEntry ::= SEQUENCE {
    mepConfigInstancePeerId      Integer32,
    mepConfigInstancePeerPeerId  Integer32,
    mepConfigInstancePeerMac     MacAddress,
    mepConfigInstancePeerAction  RowEditorState
}

mepConfigInstancePeerId OBJECT-TYPE
    SYNTAX      Integer32 (0..2147483647)
    MAX-ACCESS  not-accessible
    STATUS      current
    DESCRIPTION
        "The MEP instance ID"
    ::= { mepConfigInstancePeerEntry 1 }

mepConfigInstancePeerPeerId OBJECT-TYPE
    SYNTAX      Integer32 (0..2147483647)
    MAX-ACCESS  not-accessible
    STATUS      current
    DESCRIPTION
        "The Peer MEP ID"
    ::= { mepConfigInstancePeerEntry 2 }

mepConfigInstancePeerMac OBJECT-TYPE
    SYNTAX      MacAddress
    MAX-ACCESS  read-write
    STATUS      current
    DESCRIPTION
        "The peer unicast MAC"
    ::= { mepConfigInstancePeerEntry 3 }

mepConfigInstancePeerAction OBJECT-TYPE
    SYNTAX      RowEditorState
    MAX-ACCESS  read-write
    STATUS      current
    DESCRIPTION
        "Action"
    ::= { mepConfigInstancePeerEntry 100 }

mepConfigInstancePeerRowEditor OBJECT IDENTIFIER
    ::= { mepConfigInstance 4 }

mepConfigInstancePeerRowEditorId OBJECT-TYPE
    SYNTAX      Integer32 (0..2147483647)
    MAX-ACCESS  read-write
    STATUS      current
    DESCRIPTION
        "The MEP instance ID"
    ::= { mepConfigInstancePeerRowEditor 1 }

mepConfigInstancePeerRowEditorPeerId OBJECT-TYPE
    SYNTAX      Integer32 (0..2147483647)
    MAX-ACCESS  read-write
    STATUS      current
    DESCRIPTION
        "The Peer MEP ID"
    ::= { mepConfigInstancePeerRowEditor 2 }

mepConfigInstancePeerRowEditorMac OBJECT-TYPE
    SYNTAX      MacAddress
    MAX-ACCESS  read-write
    STATUS      current
    DESCRIPTION
        "The peer unicast MAC"
    ::= { mepConfigInstancePeerRowEditor 3 }

mepConfigInstancePeerRowEditorAction OBJECT-TYPE
    SYNTAX      RowEditorState
    MAX-ACCESS  read-write
    STATUS      current
    DESCRIPTION
        "Action"
    ::= { mepConfigInstancePeerRowEditor 100 }

mepConfigPm OBJECT IDENTIFIER
    ::= { mepConfig 2 }

mepConfigPmTable OBJECT-TYPE
    SYNTAX      SEQUENCE OF MepConfigPmEntry
    MAX-ACCESS  not-accessible
    STATUS      current
    DESCRIPTION
        "This is a table of created instance Performance Monitoring
         configuration parameters"
    ::= { mepConfigPm 1 }

mepConfigPmEntry OBJECT-TYPE
    SYNTAX      MepConfigPmEntry
    MAX-ACCESS  not-accessible
    STATUS      current
    DESCRIPTION
        "This is a created instance Performance Monitoring configuration
         parameters"
    INDEX       { mepConfigPmId }
    ::= { mepConfigPmTable 1 }

MepConfigPmEntry ::= SEQUENCE {
    mepConfigPmId      Integer32,
    mepConfigPmEnable  TruthValue
}

mepConfigPmId OBJECT-TYPE
    SYNTAX      Integer32 (0..2147483647)
    MAX-ACCESS  not-accessible
    STATUS      current
    DESCRIPTION
        "The MEP instance ID"
    ::= { mepConfigPmEntry 1 }

mepConfigPmEnable OBJECT-TYPE
    SYNTAX      TruthValue
    MAX-ACCESS  read-write
    STATUS      current
    DESCRIPTION
        "The instance can enable contribution of LM and DM results to the
         Performance Monitoring "
    ::= { mepConfigPmEntry 2 }

mepConfigCc OBJECT IDENTIFIER
    ::= { mepConfig 3 }

mepConfigCcTable OBJECT-TYPE
    SYNTAX      SEQUENCE OF MepConfigCcEntry
    MAX-ACCESS  not-accessible
    STATUS      current
    DESCRIPTION
        "This is a table of created instance Continuity Check configuration
         parameters"
    ::= { mepConfigCc 1 }

mepConfigCcEntry OBJECT-TYPE
    SYNTAX      MepConfigCcEntry
    MAX-ACCESS  not-accessible
    STATUS      current
    DESCRIPTION
        "This is a created instance Continuity Check configuration parameters."
    INDEX       { mepConfigCcId }
    ::= { mepConfigCcTable 1 }

MepConfigCcEntry ::= SEQUENCE {
    mepConfigCcId      Integer32,
    mepConfigCcPrio    Unsigned32,
    mepConfigCcRate    MepTxRate,
    mepConfigCcTlv     TruthValue,
    mepConfigCcAction  RowEditorState
}

mepConfigCcId OBJECT-TYPE
    SYNTAX      Integer32 (0..2147483647)
    MAX-ACCESS  not-accessible
    STATUS      current
    DESCRIPTION
        "The MEP instance ID"
    ::= { mepConfigCcEntry 1 }

mepConfigCcPrio OBJECT-TYPE
    SYNTAX      Unsigned32
    MAX-ACCESS  read-write
    STATUS      current
    DESCRIPTION
        "Priority of the transmitted CCM. Range 0 to 7"
    ::= { mepConfigCcEntry 3 }

mepConfigCcRate OBJECT-TYPE
    SYNTAX      MepTxRate
    MAX-ACCESS  read-write
    STATUS      current
    DESCRIPTION
        "CCM transmission and expected reception rate"
    ::= { mepConfigCcEntry 4 }

mepConfigCcTlv OBJECT-TYPE
    SYNTAX      TruthValue
    MAX-ACCESS  read-write
    STATUS      current
    DESCRIPTION
        "Enable/disable insertion of TLV in CCM PDU. OS, PS and IS TLV are
         inserted"
    ::= { mepConfigCcEntry 5 }

mepConfigCcAction OBJECT-TYPE
    SYNTAX      RowEditorState
    MAX-ACCESS  read-write
    STATUS      current
    DESCRIPTION
        "Action"
    ::= { mepConfigCcEntry 100 }

mepConfigCcRowEditor OBJECT IDENTIFIER
    ::= { mepConfigCc 2 }

mepConfigCcRowEditorId OBJECT-TYPE
    SYNTAX      Integer32 (0..2147483647)
    MAX-ACCESS  read-write
    STATUS      current
    DESCRIPTION
        "The MEP instance ID"
    ::= { mepConfigCcRowEditor 1 }

mepConfigCcRowEditorPrio OBJECT-TYPE
    SYNTAX      Unsigned32
    MAX-ACCESS  read-write
    STATUS      current
    DESCRIPTION
        "Priority of the transmitted CCM. Range 0 to 7"
    ::= { mepConfigCcRowEditor 3 }

mepConfigCcRowEditorRate OBJECT-TYPE
    SYNTAX      MepTxRate
    MAX-ACCESS  read-write
    STATUS      current
    DESCRIPTION
        "CCM transmission and expected reception rate"
    ::= { mepConfigCcRowEditor 4 }

mepConfigCcRowEditorTlv OBJECT-TYPE
    SYNTAX      TruthValue
    MAX-ACCESS  read-write
    STATUS      current
    DESCRIPTION
        "Enable/disable insertion of TLV in CCM PDU. OS, PS and IS TLV are
         inserted"
    ::= { mepConfigCcRowEditor 5 }

mepConfigCcRowEditorAction OBJECT-TYPE
    SYNTAX      RowEditorState
    MAX-ACCESS  read-write
    STATUS      current
    DESCRIPTION
        "Action"
    ::= { mepConfigCcRowEditor 100 }

mepConfigLm OBJECT IDENTIFIER
    ::= { mepConfig 4 }

mepConfigLmTable OBJECT-TYPE
    SYNTAX      SEQUENCE OF MepConfigLmEntry
    MAX-ACCESS  not-accessible
    STATUS      current
    DESCRIPTION
        "This is a table of created instance Loss Measurement configuration
         parameters"
    ::= { mepConfigLm 1 }

mepConfigLmEntry OBJECT-TYPE
    SYNTAX      MepConfigLmEntry
    MAX-ACCESS  not-accessible
    STATUS      current
    DESCRIPTION
        "This is a created instance Loss Measurement parameters."
    INDEX       { mepConfigLmId }
    ::= { mepConfigLmTable 1 }

MepConfigLmEntry ::= SEQUENCE {
    mepConfigLmId                           Integer32,
    mepConfigLmEnable                       TruthValue,
    mepConfigLmEnded                        MepEnded,
    mepConfigLmPrio                         Unsigned32,
    mepConfigLmRate                         MepTxRate,
    mepConfigLmCast                         MepCast,
    mepConfigLmFlrInterval                  Unsigned32,
    mepConfigLmFlowCount                    TruthValue,
    mepConfigLmOamCount                     MepOamCount,
    mepConfigLmLossTh                       Unsigned32,
    mepConfigLmLossCounterIntHolddownTimer  Unsigned32,
    mepConfigLmLossThCntHolddownTimer       Unsigned32,
    mepConfigLmRxEnable                     TruthValue,
    mepConfigLmSynthetic                    TruthValue,
    mepConfigLmMep                          Unsigned32,
    mepConfigLmFrameSize                    Unsigned32,
    mepConfigLmMeasInterval                 Unsigned32,
    mepConfigLmSlmTestId                    Unsigned32
}

mepConfigLmId OBJECT-TYPE
    SYNTAX      Integer32 (0..2147483647)
    MAX-ACCESS  not-accessible
    STATUS      current
    DESCRIPTION
        "The MEP instance ID"
    ::= { mepConfigLmEntry 1 }

mepConfigLmEnable OBJECT-TYPE
    SYNTAX      TruthValue
    MAX-ACCESS  read-write
    STATUS      current
    DESCRIPTION
        "Loss Measurement is enabled"
    ::= { mepConfigLmEntry 2 }

mepConfigLmEnded OBJECT-TYPE
    SYNTAX      MepEnded
    MAX-ACCESS  read-write
    STATUS      current
    DESCRIPTION
        "Dual/single ended selection. CCM or LMM/LMR based. Cannot be changed
         after creation."
    ::= { mepConfigLmEntry 3 }

mepConfigLmPrio OBJECT-TYPE
    SYNTAX      Unsigned32
    MAX-ACCESS  read-write
    STATUS      current
    DESCRIPTION
        "Priority of the transmitted LM PDU. Range 0 to 7"
    ::= { mepConfigLmEntry 5 }

mepConfigLmRate OBJECT-TYPE
    SYNTAX      MepTxRate
    MAX-ACCESS  read-write
    STATUS      current
    DESCRIPTION
        "LM PDU transmission rate"
    ::= { mepConfigLmEntry 6 }

mepConfigLmCast OBJECT-TYPE
    SYNTAX      MepCast
    MAX-ACCESS  read-write
    STATUS      current
    DESCRIPTION
        "Uni/Multicast selection - on CCM based LM only multicast is possible"
    ::= { mepConfigLmEntry 7 }

mepConfigLmFlrInterval OBJECT-TYPE
    SYNTAX      Unsigned32
    MAX-ACCESS  read-write
    STATUS      current
    DESCRIPTION
        "Frame loss ratio interval in number of measurement intervals."
    ::= { mepConfigLmEntry 8 }

mepConfigLmFlowCount OBJECT-TYPE
    SYNTAX      TruthValue
    MAX-ACCESS  read-write
    STATUS      current
    DESCRIPTION
        "Traffic (service frames) are counted per flow - all priority in one"
    ::= { mepConfigLmEntry 9 }

mepConfigLmOamCount OBJECT-TYPE
    SYNTAX      MepOamCount
    MAX-ACCESS  read-write
    STATUS      current
    DESCRIPTION
        "Loss Measurement can count OAM frames in different ways."
    ::= { mepConfigLmEntry 10 }

mepConfigLmLossTh OBJECT-TYPE
    SYNTAX      Unsigned32
    MAX-ACCESS  read-write
    STATUS      current
    DESCRIPTION
        "Frame loss threshold. The loss threshold count NearEndLosThCnt /
         FarEndLosThCnt is incremented if a loss measurement is above this
         threshold."
    ::= { mepConfigLmEntry 11 }

mepConfigLmLossCounterIntHolddownTimer OBJECT-TYPE
    SYNTAX      Unsigned32
    MAX-ACCESS  read-write
    STATUS      current
    DESCRIPTION
        "Holddown timer in seconds for JSON notification updates for
         NearEndLosCounterInt and FarEndLosCounterInt."
    ::= { mepConfigLmEntry 12 }

mepConfigLmLossThCntHolddownTimer OBJECT-TYPE
    SYNTAX      Unsigned32
    MAX-ACCESS  read-write
    STATUS      current
    DESCRIPTION
        "Holddown timer in seconds for JSON notification updates for
         NearEndLosThCnt and FarEndLosThCnt."
    ::= { mepConfigLmEntry 13 }

mepConfigLmRxEnable OBJECT-TYPE
    SYNTAX      TruthValue
    MAX-ACCESS  read-write
    STATUS      current
    DESCRIPTION
        "This enables calculation of far-to-near loss when CCM/LMM/SLM/1SL is
         received. Can only be set TRUE when 'enable' is FALSE"
    ::= { mepConfigLmEntry 14 }

mepConfigLmSynthetic OBJECT-TYPE
    SYNTAX      TruthValue
    MAX-ACCESS  read-write
    STATUS      current
    DESCRIPTION
        "TRUE => LM based on synthetic frames (SLM/1SL). FALSE => LM based on
         service frames (LMM/CCM)."
    ::= { mepConfigLmEntry 15 }

mepConfigLmMep OBJECT-TYPE
    SYNTAX      Unsigned32
    MAX-ACCESS  read-write
    STATUS      current
    DESCRIPTION
        "Peer Mep to receive LM - only used if unicast. Value >
         APPL_MEP_ID_MAX can be used when only one peer-mep (default)."
    ::= { mepConfigLmEntry 16 }

mepConfigLmFrameSize OBJECT-TYPE
    SYNTAX      Unsigned32
    MAX-ACCESS  read-write
    STATUS      current
    DESCRIPTION
        "Size of SLM/1SL frame to send."
    ::= { mepConfigLmEntry 17 }

mepConfigLmMeasInterval OBJECT-TYPE
    SYNTAX      Unsigned32
    MAX-ACCESS  read-write
    STATUS      current
    DESCRIPTION
        "Synthetic LM measurement interval."
    ::= { mepConfigLmEntry 18 }

mepConfigLmSlmTestId OBJECT-TYPE
    SYNTAX      Unsigned32
    MAX-ACCESS  read-write
    STATUS      current
    DESCRIPTION
        "Test ID value to use in SLM PDUs."
    ::= { mepConfigLmEntry 19 }

mepConfigDm OBJECT IDENTIFIER
    ::= { mepConfig 5 }

mepConfigDmTable OBJECT-TYPE
    SYNTAX      SEQUENCE OF MepConfigDmEntry
    MAX-ACCESS  not-accessible
    STATUS      current
    DESCRIPTION
        "This is a table of created instance Delay Measurement configuration
         parameters"
    ::= { mepConfigDm 1 }

mepConfigDmEntry OBJECT-TYPE
    SYNTAX      MepConfigDmEntry
    MAX-ACCESS  not-accessible
    STATUS      current
    DESCRIPTION
        "This is a created instance Delay Measurement parameters."
    INDEX       { mepConfigDmId }
    ::= { mepConfigDmTable 1 }

MepConfigDmEntry ::= SEQUENCE {
    mepConfigDmId            Integer32,
    mepConfigDmEnable        TruthValue,
    mepConfigDmEnded         MepEnded,
    mepConfigDmPrio          Unsigned32,
    mepConfigDmCast          MepCast,
    mepConfigDmMep           Unsigned32,
    mepConfigDmCalcWay       MepDmCalcWay,
    mepConfigDmInterval      Unsigned32,
    mepConfigDmLastN         Unsigned32,
    mepConfigDmTimeUnit      MepDmTimeUnit,
    mepConfigDmOverflowAct   MepDmOverflowAction,
    mepConfigDmSynchronized  TruthValue
}

mepConfigDmId OBJECT-TYPE
    SYNTAX      Integer32 (0..2147483647)
    MAX-ACCESS  not-accessible
    STATUS      current
    DESCRIPTION
        "The MEP instance ID"
    ::= { mepConfigDmEntry 1 }

mepConfigDmEnable OBJECT-TYPE
    SYNTAX      TruthValue
    MAX-ACCESS  read-write
    STATUS      current
    DESCRIPTION
        "Delay Measurement is enabled"
    ::= { mepConfigDmEntry 2 }

mepConfigDmEnded OBJECT-TYPE
    SYNTAX      MepEnded
    MAX-ACCESS  read-write
    STATUS      current
    DESCRIPTION
        "Dual/single ended selection. CCM or LMM/LMR based. Cannot be changed
         after creation."
    ::= { mepConfigDmEntry 3 }

mepConfigDmPrio OBJECT-TYPE
    SYNTAX      Unsigned32
    MAX-ACCESS  read-write
    STATUS      current
    DESCRIPTION
        "Priority of the transmitted DM PDU. Range 0 to 7"
    ::= { mepConfigDmEntry 5 }

mepConfigDmCast OBJECT-TYPE
    SYNTAX      MepCast
    MAX-ACCESS  read-write
    STATUS      current
    DESCRIPTION
        "Uni/Multicast selection"
    ::= { mepConfigDmEntry 6 }

mepConfigDmMep OBJECT-TYPE
    SYNTAX      Unsigned32
    MAX-ACCESS  read-write
    STATUS      current
    DESCRIPTION
        "Peer MEP to receive DMM/1DM - only used if unicast"
    ::= { mepConfigDmEntry 7 }

mepConfigDmCalcWay OBJECT-TYPE
    SYNTAX      MepDmCalcWay
    MAX-ACCESS  read-write
    STATUS      current
    DESCRIPTION
        "Round trip or flow calculation way selection."
    ::= { mepConfigDmEntry 8 }

mepConfigDmInterval OBJECT-TYPE
    SYNTAX      Unsigned32
    MAX-ACCESS  read-write
    STATUS      current
    DESCRIPTION
        "Interval between 1DM/DMM in 10 ms. Range Capability dm_interval_min to
         dm_interval_max."
    ::= { mepConfigDmEntry 9 }

mepConfigDmLastN OBJECT-TYPE
    SYNTAX      Unsigned32
    MAX-ACCESS  read-write
    STATUS      current
    DESCRIPTION
        "The number of last N measurements used to calculate average delay and
         variation. Range Capability dm_lastn_min to dm_lastn_max."
    ::= { mepConfigDmEntry 10 }

mepConfigDmTimeUnit OBJECT-TYPE
    SYNTAX      MepDmTimeUnit
    MAX-ACCESS  read-write
    STATUS      current
    DESCRIPTION
        "Calculation time unit."
    ::= { mepConfigDmEntry 11 }

mepConfigDmOverflowAct OBJECT-TYPE
    SYNTAX      MepDmOverflowAction
    MAX-ACCESS  read-write
    STATUS      current
    DESCRIPTION
        "Action when internal total delay counter overflow."
    ::= { mepConfigDmEntry 12 }

mepConfigDmSynchronized OBJECT-TYPE
    SYNTAX      TruthValue
    MAX-ACCESS  read-write
    STATUS      current
    DESCRIPTION
        "Near-end and far-end is real-time synchronized. One-way DM calculation
         on receiving DMR."
    ::= { mepConfigDmEntry 13 }

mepConfigLb OBJECT IDENTIFIER
    ::= { mepConfig 6 }

mepConfigLbTable OBJECT-TYPE
    SYNTAX      SEQUENCE OF MepConfigLbEntry
    MAX-ACCESS  not-accessible
    STATUS      current
    DESCRIPTION
        "This is a table of created instance Loop Back configuration parameters"
    ::= { mepConfigLb 1 }

mepConfigLbEntry OBJECT-TYPE
    SYNTAX      MepConfigLbEntry
    MAX-ACCESS  not-accessible
    STATUS      current
    DESCRIPTION
        "This is a created instance Loop Back parameters. This cannot be changed"
    INDEX       { mepConfigLbId }
    ::= { mepConfigLbTable 1 }

MepConfigLbEntry ::= SEQUENCE {
    mepConfigLbId          Integer32,
    mepConfigLbDei         TruthValue,
    mepConfigLbPrio        Unsigned32,
    mepConfigLbCast        MepCast,
    mepConfigLbMep         Unsigned32,
    mepConfigLbMac         MacAddress,
    mepConfigLbToSend      Unsigned32,
    mepConfigLbSize        Unsigned32,
    mepConfigLbInterval    Unsigned32,
    mepConfigLbTimeToLive  Unsigned8,
    mepConfigLbAction      RowEditorState
}

mepConfigLbId OBJECT-TYPE
    SYNTAX      Integer32 (0..2147483647)
    MAX-ACCESS  not-accessible
    STATUS      current
    DESCRIPTION
        "The MEP instance ID"
    ::= { mepConfigLbEntry 1 }

mepConfigLbDei OBJECT-TYPE
    SYNTAX      TruthValue
    MAX-ACCESS  read-write
    STATUS      current
    DESCRIPTION
        "Drop Eligibility Indicator of transmitted LBM PDU"
    ::= { mepConfigLbEntry 2 }

mepConfigLbPrio OBJECT-TYPE
    SYNTAX      Unsigned32
    MAX-ACCESS  read-write
    STATUS      current
    DESCRIPTION
        "Priority of the transmitted LBM PDU. Range 0 to 7"
    ::= { mepConfigLbEntry 3 }

mepConfigLbCast OBJECT-TYPE
    SYNTAX      MepCast
    MAX-ACCESS  read-write
    STATUS      current
    DESCRIPTION
        "Uni/Multicast selection"
    ::= { mepConfigLbEntry 4 }

mepConfigLbMep OBJECT-TYPE
    SYNTAX      Unsigned32
    MAX-ACCESS  read-write
    STATUS      current
    DESCRIPTION
        "Peer MEP to receive LBM - only used if unicast and 'mac' is 'all zero'."
    ::= { mepConfigLbEntry 5 }

mepConfigLbMac OBJECT-TYPE
    SYNTAX      MacAddress
    MAX-ACCESS  read-write
    STATUS      current
    DESCRIPTION
        "Unicast MAC address to receive LBM - has to be used to send LBM to MIP."
    ::= { mepConfigLbEntry 6 }

mepConfigLbToSend OBJECT-TYPE
    SYNTAX      Unsigned32
    MAX-ACCESS  read-write
    STATUS      current
    DESCRIPTION
        "Number of LBM to send. Capability lb_to_send_infinite => test
         behaviour. Requires VOE."
    ::= { mepConfigLbEntry 7 }

mepConfigLbSize OBJECT-TYPE
    SYNTAX      Unsigned32
    MAX-ACCESS  read-write
    STATUS      current
    DESCRIPTION
        "Size of LBM frame to send - Range Capability lbm_size_min to
         lbm_size_max"
    ::= { mepConfigLbEntry 8 }

mepConfigLbInterval OBJECT-TYPE
    SYNTAX      Unsigned32
    MAX-ACCESS  read-write
    STATUS      current
    DESCRIPTION
        "Frame interval.
         
         If 'ToSend' != Capability lb_to_send_infinite then the 'Interval' is in
         10 ms. Max 1 s.
         
         If 'ToSend' == Capability lb_to_send_infinite then the 'Interval' is in
         1 us. Max 10 ms."
    ::= { mepConfigLbEntry 9 }

mepConfigLbTimeToLive OBJECT-TYPE
    SYNTAX      Unsigned8
    MAX-ACCESS  read-write
    STATUS      current
    DESCRIPTION
        "Time To Live."
    ::= { mepConfigLbEntry 10 }

mepConfigLbAction OBJECT-TYPE
    SYNTAX      RowEditorState
    MAX-ACCESS  read-write
    STATUS      current
    DESCRIPTION
        "Action"
    ::= { mepConfigLbEntry 101 }

mepConfigLbRowEditor OBJECT IDENTIFIER
    ::= { mepConfigLb 2 }

mepConfigLbRowEditorId OBJECT-TYPE
    SYNTAX      Integer32 (0..2147483647)
    MAX-ACCESS  read-write
    STATUS      current
    DESCRIPTION
        "The MEP instance ID"
    ::= { mepConfigLbRowEditor 1 }

mepConfigLbRowEditorDei OBJECT-TYPE
    SYNTAX      TruthValue
    MAX-ACCESS  read-write
    STATUS      current
    DESCRIPTION
        "Drop Eligibility Indicator of transmitted LBM PDU"
    ::= { mepConfigLbRowEditor 2 }

mepConfigLbRowEditorPrio OBJECT-TYPE
    SYNTAX      Unsigned32
    MAX-ACCESS  read-write
    STATUS      current
    DESCRIPTION
        "Priority of the transmitted LBM PDU. Range 0 to 7"
    ::= { mepConfigLbRowEditor 3 }

mepConfigLbRowEditorCast OBJECT-TYPE
    SYNTAX      MepCast
    MAX-ACCESS  read-write
    STATUS      current
    DESCRIPTION
        "Uni/Multicast selection"
    ::= { mepConfigLbRowEditor 4 }

mepConfigLbRowEditorMep OBJECT-TYPE
    SYNTAX      Unsigned32
    MAX-ACCESS  read-write
    STATUS      current
    DESCRIPTION
        "Peer MEP to receive LBM - only used if unicast and 'mac' is 'all zero'."
    ::= { mepConfigLbRowEditor 5 }

mepConfigLbRowEditorMac OBJECT-TYPE
    SYNTAX      MacAddress
    MAX-ACCESS  read-write
    STATUS      current
    DESCRIPTION
        "Unicast MAC address to receive LBM - has to be used to send LBM to MIP."
    ::= { mepConfigLbRowEditor 6 }

mepConfigLbRowEditorToSend OBJECT-TYPE
    SYNTAX      Unsigned32
    MAX-ACCESS  read-write
    STATUS      current
    DESCRIPTION
        "Number of LBM to send. Capability lb_to_send_infinite => test
         behaviour. Requires VOE."
    ::= { mepConfigLbRowEditor 7 }

mepConfigLbRowEditorSize OBJECT-TYPE
    SYNTAX      Unsigned32
    MAX-ACCESS  read-write
    STATUS      current
    DESCRIPTION
        "Size of LBM frame to send - Range Capability lbm_size_min to
         lbm_size_max"
    ::= { mepConfigLbRowEditor 8 }

mepConfigLbRowEditorInterval OBJECT-TYPE
    SYNTAX      Unsigned32
    MAX-ACCESS  read-write
    STATUS      current
    DESCRIPTION
        "Frame interval.
         
         If 'ToSend' != Capability lb_to_send_infinite then the 'Interval' is in
         10 ms. Max 1 s.
         
         If 'ToSend' == Capability lb_to_send_infinite then the 'Interval' is in
         1 us. Max 10 ms."
    ::= { mepConfigLbRowEditor 9 }

mepConfigLbRowEditorTimeToLive OBJECT-TYPE
    SYNTAX      Unsigned8
    MAX-ACCESS  read-write
    STATUS      current
    DESCRIPTION
        "Time To Live."
    ::= { mepConfigLbRowEditor 10 }

mepConfigLbRowEditorAction OBJECT-TYPE
    SYNTAX      RowEditorState
    MAX-ACCESS  read-write
    STATUS      current
    DESCRIPTION
        "Action"
    ::= { mepConfigLbRowEditor 101 }

mepConfigTst OBJECT IDENTIFIER
    ::= { mepConfig 7 }

mepConfigTstTable OBJECT-TYPE
    SYNTAX      SEQUENCE OF MepConfigTstEntry
    MAX-ACCESS  not-accessible
    STATUS      current
    DESCRIPTION
        "This is a table of created instance Test Signal configuration
         parameters"
    ::= { mepConfigTst 1 }

mepConfigTstEntry OBJECT-TYPE
    SYNTAX      MepConfigTstEntry
    MAX-ACCESS  not-accessible
    STATUS      current
    DESCRIPTION
        "This is a created instance Test Signal parameters."
    INDEX       { mepConfigTstId }
    ::= { mepConfigTstTable 1 }

MepConfigTstEntry ::= SEQUENCE {
    mepConfigTstId        Integer32,
    mepConfigTstTxEnable  TruthValue,
    mepConfigTstRxEnable  TruthValue,
    mepConfigTstDei       TruthValue,
    mepConfigTstPrio      Unsigned32,
    mepConfigTstMep       Unsigned32,
    mepConfigTstRate      Unsigned32,
    mepConfigTstSize      Unsigned32,
    mepConfigTstPattern   MepTstPattern,
    mepConfigTstSequence  TruthValue,
    mepConfigTstAction    RowEditorState
}

mepConfigTstId OBJECT-TYPE
    SYNTAX      Integer32 (0..2147483647)
    MAX-ACCESS  not-accessible
    STATUS      current
    DESCRIPTION
        "The MEP instance ID"
    ::= { mepConfigTstEntry 1 }

mepConfigTstTxEnable OBJECT-TYPE
    SYNTAX      TruthValue
    MAX-ACCESS  read-write
    STATUS      current
    DESCRIPTION
        "Enable/disable transmission of TST PDU."
    ::= { mepConfigTstEntry 2 }

mepConfigTstRxEnable OBJECT-TYPE
    SYNTAX      TruthValue
    MAX-ACCESS  read-write
    STATUS      current
    DESCRIPTION
        "Enable/disable reception and analyse of TST PDU."
    ::= { mepConfigTstEntry 3 }

mepConfigTstDei OBJECT-TYPE
    SYNTAX      TruthValue
    MAX-ACCESS  read-write
    STATUS      current
    DESCRIPTION
        "Drop Eligibility Indicator of transmitted TST PDU"
    ::= { mepConfigTstEntry 4 }

mepConfigTstPrio OBJECT-TYPE
    SYNTAX      Unsigned32
    MAX-ACCESS  read-write
    STATUS      current
    DESCRIPTION
        "Priority of the transmitted TST PDU. Range 0 to 7"
    ::= { mepConfigTstEntry 5 }

mepConfigTstMep OBJECT-TYPE
    SYNTAX      Unsigned32
    MAX-ACCESS  read-write
    STATUS      current
    DESCRIPTION
        "Peer MEP to receive TST"
    ::= { mepConfigTstEntry 6 }

mepConfigTstRate OBJECT-TYPE
    SYNTAX      Unsigned32
    MAX-ACCESS  read-write
    STATUS      current
    DESCRIPTION
        "The transmission rate in Kbps - Range 1 to Capability tst_rate_max."
    ::= { mepConfigTstEntry 7 }

mepConfigTstSize OBJECT-TYPE
    SYNTAX      Unsigned32
    MAX-ACCESS  read-write
    STATUS      current
    DESCRIPTION
        "Size of TST frame to send - Range Capability tst_size_min to
         tst_size_max."
    ::= { mepConfigTstEntry 8 }

mepConfigTstPattern OBJECT-TYPE
    SYNTAX      MepTstPattern
    MAX-ACCESS  read-write
    STATUS      current
    DESCRIPTION
        "Pattern in TST frame Data TLV."
    ::= { mepConfigTstEntry 9 }

mepConfigTstSequence OBJECT-TYPE
    SYNTAX      TruthValue
    MAX-ACCESS  read-write
    STATUS      current
    DESCRIPTION
        "Sequence number will be inserted - not checked in receiver on Caracal
         and Jaguar."
    ::= { mepConfigTstEntry 10 }

mepConfigTstAction OBJECT-TYPE
    SYNTAX      RowEditorState
    MAX-ACCESS  read-write
    STATUS      current
    DESCRIPTION
        "Action"
    ::= { mepConfigTstEntry 101 }

mepConfigTstRowEditor OBJECT IDENTIFIER
    ::= { mepConfigTst 2 }

mepConfigTstRowEditorId OBJECT-TYPE
    SYNTAX      Integer32 (0..2147483647)
    MAX-ACCESS  read-write
    STATUS      current
    DESCRIPTION
        "The MEP instance ID"
    ::= { mepConfigTstRowEditor 1 }

mepConfigTstRowEditorTxEnable OBJECT-TYPE
    SYNTAX      TruthValue
    MAX-ACCESS  read-write
    STATUS      current
    DESCRIPTION
        "Enable/disable transmission of TST PDU."
    ::= { mepConfigTstRowEditor 2 }

mepConfigTstRowEditorRxEnable OBJECT-TYPE
    SYNTAX      TruthValue
    MAX-ACCESS  read-write
    STATUS      current
    DESCRIPTION
        "Enable/disable reception and analyse of TST PDU."
    ::= { mepConfigTstRowEditor 3 }

mepConfigTstRowEditorDei OBJECT-TYPE
    SYNTAX      TruthValue
    MAX-ACCESS  read-write
    STATUS      current
    DESCRIPTION
        "Drop Eligibility Indicator of transmitted TST PDU"
    ::= { mepConfigTstRowEditor 4 }

mepConfigTstRowEditorPrio OBJECT-TYPE
    SYNTAX      Unsigned32
    MAX-ACCESS  read-write
    STATUS      current
    DESCRIPTION
        "Priority of the transmitted TST PDU. Range 0 to 7"
    ::= { mepConfigTstRowEditor 5 }

mepConfigTstRowEditorMep OBJECT-TYPE
    SYNTAX      Unsigned32
    MAX-ACCESS  read-write
    STATUS      current
    DESCRIPTION
        "Peer MEP to receive TST"
    ::= { mepConfigTstRowEditor 6 }

mepConfigTstRowEditorRate OBJECT-TYPE
    SYNTAX      Unsigned32
    MAX-ACCESS  read-write
    STATUS      current
    DESCRIPTION
        "The transmission rate in Kbps - Range 1 to Capability tst_rate_max."
    ::= { mepConfigTstRowEditor 7 }

mepConfigTstRowEditorSize OBJECT-TYPE
    SYNTAX      Unsigned32
    MAX-ACCESS  read-write
    STATUS      current
    DESCRIPTION
        "Size of TST frame to send - Range Capability tst_size_min to
         tst_size_max."
    ::= { mepConfigTstRowEditor 8 }

mepConfigTstRowEditorPattern OBJECT-TYPE
    SYNTAX      MepTstPattern
    MAX-ACCESS  read-write
    STATUS      current
    DESCRIPTION
        "Pattern in TST frame Data TLV."
    ::= { mepConfigTstRowEditor 9 }

mepConfigTstRowEditorSequence OBJECT-TYPE
    SYNTAX      TruthValue
    MAX-ACCESS  read-write
    STATUS      current
    DESCRIPTION
        "Sequence number will be inserted - not checked in receiver on Caracal
         and Jaguar."
    ::= { mepConfigTstRowEditor 10 }

mepConfigTstRowEditorAction OBJECT-TYPE
    SYNTAX      RowEditorState
    MAX-ACCESS  read-write
    STATUS      current
    DESCRIPTION
        "Action"
    ::= { mepConfigTstRowEditor 101 }

mepConfigLt OBJECT IDENTIFIER
    ::= { mepConfig 8 }

mepConfigLtTable OBJECT-TYPE
    SYNTAX      SEQUENCE OF MepConfigLtEntry
    MAX-ACCESS  not-accessible
    STATUS      current
    DESCRIPTION
        "This is a table of created instance Link Trace configuration parameters"
    ::= { mepConfigLt 1 }

mepConfigLtEntry OBJECT-TYPE
    SYNTAX      MepConfigLtEntry
    MAX-ACCESS  not-accessible
    STATUS      current
    DESCRIPTION
        "This is a created instance Link Trace parameters. This cannot be
         changed"
    INDEX       { mepConfigLtId }
    ::= { mepConfigLtTable 1 }

MepConfigLtEntry ::= SEQUENCE {
    mepConfigLtId          Integer32,
    mepConfigLtPrio        Unsigned32,
    mepConfigLtMep         Unsigned32,
    mepConfigLtMac         MacAddress,
    mepConfigLtTimeToLive  Unsigned32,
    mepConfigLtAction      RowEditorState
}

mepConfigLtId OBJECT-TYPE
    SYNTAX      Integer32 (0..2147483647)
    MAX-ACCESS  not-accessible
    STATUS      current
    DESCRIPTION
        "The MEP instance ID"
    ::= { mepConfigLtEntry 1 }

mepConfigLtPrio OBJECT-TYPE
    SYNTAX      Unsigned32
    MAX-ACCESS  read-write
    STATUS      current
    DESCRIPTION
        "Priority of the transmitted LTM PDU. Range 0 to 7"
    ::= { mepConfigLtEntry 3 }

mepConfigLtMep OBJECT-TYPE
    SYNTAX      Unsigned32
    MAX-ACCESS  read-write
    STATUS      current
    DESCRIPTION
        "Target Peer Mep to receive LTM - only used if 'mac' is 'all zero'"
    ::= { mepConfigLtEntry 4 }

mepConfigLtMac OBJECT-TYPE
    SYNTAX      MacAddress
    MAX-ACCESS  read-write
    STATUS      current
    DESCRIPTION
        "Unicast MAC address to receive LTM - has to be used to send LTM to MIP."
    ::= { mepConfigLtEntry 5 }

mepConfigLtTimeToLive OBJECT-TYPE
    SYNTAX      Unsigned32
    MAX-ACCESS  read-write
    STATUS      current
    DESCRIPTION
        "Time To Live."
    ::= { mepConfigLtEntry 6 }

mepConfigLtAction OBJECT-TYPE
    SYNTAX      RowEditorState
    MAX-ACCESS  read-write
    STATUS      current
    DESCRIPTION
        "Action"
    ::= { mepConfigLtEntry 101 }

mepConfigLtRowEditor OBJECT IDENTIFIER
    ::= { mepConfigLt 2 }

mepConfigLtRowEditorId OBJECT-TYPE
    SYNTAX      Integer32 (0..2147483647)
    MAX-ACCESS  read-write
    STATUS      current
    DESCRIPTION
        "The MEP instance ID"
    ::= { mepConfigLtRowEditor 1 }

mepConfigLtRowEditorPrio OBJECT-TYPE
    SYNTAX      Unsigned32
    MAX-ACCESS  read-write
    STATUS      current
    DESCRIPTION
        "Priority of the transmitted LTM PDU. Range 0 to 7"
    ::= { mepConfigLtRowEditor 3 }

mepConfigLtRowEditorMep OBJECT-TYPE
    SYNTAX      Unsigned32
    MAX-ACCESS  read-write
    STATUS      current
    DESCRIPTION
        "Target Peer Mep to receive LTM - only used if 'mac' is 'all zero'"
    ::= { mepConfigLtRowEditor 4 }

mepConfigLtRowEditorMac OBJECT-TYPE
    SYNTAX      MacAddress
    MAX-ACCESS  read-write
    STATUS      current
    DESCRIPTION
        "Unicast MAC address to receive LTM - has to be used to send LTM to MIP."
    ::= { mepConfigLtRowEditor 5 }

mepConfigLtRowEditorTimeToLive OBJECT-TYPE
    SYNTAX      Unsigned32
    MAX-ACCESS  read-write
    STATUS      current
    DESCRIPTION
        "Time To Live."
    ::= { mepConfigLtRowEditor 6 }

mepConfigLtRowEditorAction OBJECT-TYPE
    SYNTAX      RowEditorState
    MAX-ACCESS  read-write
    STATUS      current
    DESCRIPTION
        "Action"
    ::= { mepConfigLtRowEditor 101 }

mepConfigAps OBJECT IDENTIFIER
    ::= { mepConfig 9 }

mepConfigApsTable OBJECT-TYPE
    SYNTAX      SEQUENCE OF MepConfigApsEntry
    MAX-ACCESS  not-accessible
    STATUS      current
    DESCRIPTION
        "This is a table of created instance Automatic Protection Switching
         configuration parameters"
    ::= { mepConfigAps 1 }

mepConfigApsEntry OBJECT-TYPE
    SYNTAX      MepConfigApsEntry
    MAX-ACCESS  not-accessible
    STATUS      current
    DESCRIPTION
        "This is a created instance Automatic Protection Switching parameters."
    INDEX       { mepConfigApsId }
    ::= { mepConfigApsTable 1 }

MepConfigApsEntry ::= SEQUENCE {
    mepConfigApsId         Integer32,
    mepConfigApsPrio       Unsigned32,
    mepConfigApsApsType    MepApsType,
    mepConfigApsCast       MepCast,
    mepConfigApsRapsOctet  Unsigned32,
    mepConfigApsAction     RowEditorState
}

mepConfigApsId OBJECT-TYPE
    SYNTAX      Integer32 (0..2147483647)
    MAX-ACCESS  not-accessible
    STATUS      current
    DESCRIPTION
        "The MEP instance ID"
    ::= { mepConfigApsEntry 1 }

mepConfigApsPrio OBJECT-TYPE
    SYNTAX      Unsigned32
    MAX-ACCESS  read-write
    STATUS      current
    DESCRIPTION
        "Priority of the transmitted APS PDU. Range 0 to 7"
    ::= { mepConfigApsEntry 3 }

mepConfigApsApsType OBJECT-TYPE
    SYNTAX      MepApsType
    MAX-ACCESS  read-write
    STATUS      current
    DESCRIPTION
        "Type of APS"
    ::= { mepConfigApsEntry 4 }

mepConfigApsCast OBJECT-TYPE
    SYNTAX      MepCast
    MAX-ACCESS  read-write
    STATUS      current
    DESCRIPTION
        "Uni/multicast selection"
    ::= { mepConfigApsEntry 5 }

mepConfigApsRapsOctet OBJECT-TYPE
    SYNTAX      Unsigned32
    MAX-ACCESS  read-write
    STATUS      current
    DESCRIPTION
        "Last octet in the R-APS multicast DA"
    ::= { mepConfigApsEntry 6 }

mepConfigApsAction OBJECT-TYPE
    SYNTAX      RowEditorState
    MAX-ACCESS  read-write
    STATUS      current
    DESCRIPTION
        "Action"
    ::= { mepConfigApsEntry 101 }

mepConfigApsRowEditor OBJECT IDENTIFIER
    ::= { mepConfigAps 2 }

mepConfigApsRowEditorId OBJECT-TYPE
    SYNTAX      Integer32 (0..2147483647)
    MAX-ACCESS  read-write
    STATUS      current
    DESCRIPTION
        "The MEP instance ID"
    ::= { mepConfigApsRowEditor 1 }

mepConfigApsRowEditorPrio OBJECT-TYPE
    SYNTAX      Unsigned32
    MAX-ACCESS  read-write
    STATUS      current
    DESCRIPTION
        "Priority of the transmitted APS PDU. Range 0 to 7"
    ::= { mepConfigApsRowEditor 3 }

mepConfigApsRowEditorApsType OBJECT-TYPE
    SYNTAX      MepApsType
    MAX-ACCESS  read-write
    STATUS      current
    DESCRIPTION
        "Type of APS"
    ::= { mepConfigApsRowEditor 4 }

mepConfigApsRowEditorCast OBJECT-TYPE
    SYNTAX      MepCast
    MAX-ACCESS  read-write
    STATUS      current
    DESCRIPTION
        "Uni/multicast selection"
    ::= { mepConfigApsRowEditor 5 }

mepConfigApsRowEditorRapsOctet OBJECT-TYPE
    SYNTAX      Unsigned32
    MAX-ACCESS  read-write
    STATUS      current
    DESCRIPTION
        "Last octet in the R-APS multicast DA"
    ::= { mepConfigApsRowEditor 6 }

mepConfigApsRowEditorAction OBJECT-TYPE
    SYNTAX      RowEditorState
    MAX-ACCESS  read-write
    STATUS      current
    DESCRIPTION
        "Action"
    ::= { mepConfigApsRowEditor 101 }

mepConfigAis OBJECT IDENTIFIER
    ::= { mepConfig 10 }

mepConfigAisTable OBJECT-TYPE
    SYNTAX      SEQUENCE OF MepConfigAisEntry
    MAX-ACCESS  not-accessible
    STATUS      current
    DESCRIPTION
        "This is a table of created instance Alarm Indication Signal
         configuration parameters"
    ::= { mepConfigAis 1 }

mepConfigAisEntry OBJECT-TYPE
    SYNTAX      MepConfigAisEntry
    MAX-ACCESS  not-accessible
    STATUS      current
    DESCRIPTION
        "This is a created instance Alarm Indication Signal parameters."
    INDEX       { mepConfigAisId }
    ::= { mepConfigAisTable 1 }

MepConfigAisEntry ::= SEQUENCE {
    mepConfigAisId          Integer32,
    mepConfigAisProtection  TruthValue,
    mepConfigAisRate        MepTxRate,
    mepConfigAisAction      RowEditorState
}

mepConfigAisId OBJECT-TYPE
    SYNTAX      Integer32 (0..2147483647)
    MAX-ACCESS  not-accessible
    STATUS      current
    DESCRIPTION
        "The MEP instance ID"
    ::= { mepConfigAisEntry 1 }

mepConfigAisProtection OBJECT-TYPE
    SYNTAX      TruthValue
    MAX-ACCESS  read-write
    STATUS      current
    DESCRIPTION
        "The first three AIS frames are transmitted as fast as possible."
    ::= { mepConfigAisEntry 2 }

mepConfigAisRate OBJECT-TYPE
    SYNTAX      MepTxRate
    MAX-ACCESS  read-write
    STATUS      current
    DESCRIPTION
        "AIS transmission rate"
    ::= { mepConfigAisEntry 3 }

mepConfigAisAction OBJECT-TYPE
    SYNTAX      RowEditorState
    MAX-ACCESS  read-write
    STATUS      current
    DESCRIPTION
        "Action"
    ::= { mepConfigAisEntry 101 }

mepConfigAisRowEditor OBJECT IDENTIFIER
    ::= { mepConfigAis 2 }

mepConfigAisRowEditorId OBJECT-TYPE
    SYNTAX      Integer32 (0..2147483647)
    MAX-ACCESS  read-write
    STATUS      current
    DESCRIPTION
        "The MEP instance ID"
    ::= { mepConfigAisRowEditor 1 }

mepConfigAisRowEditorProtection OBJECT-TYPE
    SYNTAX      TruthValue
    MAX-ACCESS  read-write
    STATUS      current
    DESCRIPTION
        "The first three AIS frames are transmitted as fast as possible."
    ::= { mepConfigAisRowEditor 2 }

mepConfigAisRowEditorRate OBJECT-TYPE
    SYNTAX      MepTxRate
    MAX-ACCESS  read-write
    STATUS      current
    DESCRIPTION
        "AIS transmission rate"
    ::= { mepConfigAisRowEditor 3 }

mepConfigAisRowEditorAction OBJECT-TYPE
    SYNTAX      RowEditorState
    MAX-ACCESS  read-write
    STATUS      current
    DESCRIPTION
        "Action"
    ::= { mepConfigAisRowEditor 101 }

mepConfigLck OBJECT IDENTIFIER
    ::= { mepConfig 11 }

mepConfigLckTable OBJECT-TYPE
    SYNTAX      SEQUENCE OF MepConfigLckEntry
    MAX-ACCESS  not-accessible
    STATUS      current
    DESCRIPTION
        "This is a table of created instance Locked Signal configuration
         parameters"
    ::= { mepConfigLck 1 }

mepConfigLckEntry OBJECT-TYPE
    SYNTAX      MepConfigLckEntry
    MAX-ACCESS  not-accessible
    STATUS      current
    DESCRIPTION
        "This is a created instance Locked Signal parameters."
    INDEX       { mepConfigLckId }
    ::= { mepConfigLckTable 1 }

MepConfigLckEntry ::= SEQUENCE {
    mepConfigLckId      Integer32,
    mepConfigLckRate    MepTxRate,
    mepConfigLckAction  RowEditorState
}

mepConfigLckId OBJECT-TYPE
    SYNTAX      Integer32 (0..2147483647)
    MAX-ACCESS  not-accessible
    STATUS      current
    DESCRIPTION
        "The MEP instance ID"
    ::= { mepConfigLckEntry 1 }

mepConfigLckRate OBJECT-TYPE
    SYNTAX      MepTxRate
    MAX-ACCESS  read-write
    STATUS      current
    DESCRIPTION
        "LCK transmission rate"
    ::= { mepConfigLckEntry 2 }

mepConfigLckAction OBJECT-TYPE
    SYNTAX      RowEditorState
    MAX-ACCESS  read-write
    STATUS      current
    DESCRIPTION
        "Action"
    ::= { mepConfigLckEntry 101 }

mepConfigLckRowEditor OBJECT IDENTIFIER
    ::= { mepConfigLck 2 }

mepConfigLckRowEditorId OBJECT-TYPE
    SYNTAX      Integer32 (0..2147483647)
    MAX-ACCESS  read-write
    STATUS      current
    DESCRIPTION
        "The MEP instance ID"
    ::= { mepConfigLckRowEditor 1 }

mepConfigLckRowEditorRate OBJECT-TYPE
    SYNTAX      MepTxRate
    MAX-ACCESS  read-write
    STATUS      current
    DESCRIPTION
        "LCK transmission rate"
    ::= { mepConfigLckRowEditor 2 }

mepConfigLckRowEditorAction OBJECT-TYPE
    SYNTAX      RowEditorState
    MAX-ACCESS  read-write
    STATUS      current
    DESCRIPTION
        "Action"
    ::= { mepConfigLckRowEditor 101 }

mepConfigClient OBJECT IDENTIFIER
    ::= { mepConfig 12 }

mepConfigClientFlowTable OBJECT-TYPE
    SYNTAX      SEQUENCE OF MepConfigClientFlowEntry
    MAX-ACCESS  not-accessible
    STATUS      current
    DESCRIPTION
        "This is a table of client flow configuration parameters"
    ::= { mepConfigClient 2 }

mepConfigClientFlowEntry OBJECT-TYPE
    SYNTAX      MepConfigClientFlowEntry
    MAX-ACCESS  not-accessible
    STATUS      current
    DESCRIPTION
        "This is a client flow configuration parameters"
    INDEX       { mepConfigClientFlowId,
                  mepConfigClientFlowFlowId }
    ::= { mepConfigClientFlowTable 1 }

MepConfigClientFlowEntry ::= SEQUENCE {
    mepConfigClientFlowId       Integer32,
    mepConfigClientFlowFlowId   InterfaceIndex,
    mepConfigClientFlowAisPrio  Unsigned8,
    mepConfigClientFlowLckPrio  Unsigned8,
    mepConfigClientFlowLevel    Unsigned8,
    mepConfigClientFlowAction   RowEditorState
}

mepConfigClientFlowId OBJECT-TYPE
    SYNTAX      Integer32 (0..2147483647)
    MAX-ACCESS  not-accessible
    STATUS      current
    DESCRIPTION
        "The MEP instance ID"
    ::= { mepConfigClientFlowEntry 1 }

mepConfigClientFlowFlowId OBJECT-TYPE
    SYNTAX      InterfaceIndex
    MAX-ACCESS  not-accessible
    STATUS      current
    DESCRIPTION
        "The Client Flow id - ifindex"
    ::= { mepConfigClientFlowEntry 2 }

mepConfigClientFlowAisPrio OBJECT-TYPE
    SYNTAX      Unsigned8
    MAX-ACCESS  read-write
    STATUS      current
    DESCRIPTION
        "AIS Priority (EVC COS-ID) 0-7. Capability client_prio_highest indicate
         highest possible is requested"
    ::= { mepConfigClientFlowEntry 3 }

mepConfigClientFlowLckPrio OBJECT-TYPE
    SYNTAX      Unsigned8
    MAX-ACCESS  read-write
    STATUS      current
    DESCRIPTION
        "LCK Priority (EVC COS-ID) 0-7. Capability client_prio_highest indicate
         highest possible is requested"
    ::= { mepConfigClientFlowEntry 4 }

mepConfigClientFlowLevel OBJECT-TYPE
    SYNTAX      Unsigned8
    MAX-ACCESS  read-write
    STATUS      current
    DESCRIPTION
        "Client flow level"
    ::= { mepConfigClientFlowEntry 5 }

mepConfigClientFlowAction OBJECT-TYPE
    SYNTAX      RowEditorState
    MAX-ACCESS  read-write
    STATUS      current
    DESCRIPTION
        "Action"
    ::= { mepConfigClientFlowEntry 100 }

mepConfigClientFlowRowEditor OBJECT IDENTIFIER
    ::= { mepConfigClient 3 }

mepConfigClientFlowRowEditorId OBJECT-TYPE
    SYNTAX      Integer32 (0..2147483647)
    MAX-ACCESS  read-write
    STATUS      current
    DESCRIPTION
        "The MEP instance ID"
    ::= { mepConfigClientFlowRowEditor 1 }

mepConfigClientFlowRowEditorFlowId OBJECT-TYPE
    SYNTAX      InterfaceIndex
    MAX-ACCESS  read-write
    STATUS      current
    DESCRIPTION
        "The Client Flow id - ifindex"
    ::= { mepConfigClientFlowRowEditor 2 }

mepConfigClientFlowRowEditorAisPrio OBJECT-TYPE
    SYNTAX      Unsigned8
    MAX-ACCESS  read-write
    STATUS      current
    DESCRIPTION
        "AIS Priority (EVC COS-ID) 0-7. Capability client_prio_highest indicate
         highest possible is requested"
    ::= { mepConfigClientFlowRowEditor 3 }

mepConfigClientFlowRowEditorLckPrio OBJECT-TYPE
    SYNTAX      Unsigned8
    MAX-ACCESS  read-write
    STATUS      current
    DESCRIPTION
        "LCK Priority (EVC COS-ID) 0-7. Capability client_prio_highest indicate
         highest possible is requested"
    ::= { mepConfigClientFlowRowEditor 4 }

mepConfigClientFlowRowEditorLevel OBJECT-TYPE
    SYNTAX      Unsigned8
    MAX-ACCESS  read-write
    STATUS      current
    DESCRIPTION
        "Client flow level"
    ::= { mepConfigClientFlowRowEditor 5 }

mepConfigClientFlowRowEditorAction OBJECT-TYPE
    SYNTAX      RowEditorState
    MAX-ACCESS  read-write
    STATUS      current
    DESCRIPTION
        "Action"
    ::= { mepConfigClientFlowRowEditor 100 }

mepConfigSyslog OBJECT IDENTIFIER
    ::= { mepConfig 13 }

mepConfigSyslogTable OBJECT-TYPE
    SYNTAX      SEQUENCE OF MepConfigSyslogEntry
    MAX-ACCESS  not-accessible
    STATUS      current
    DESCRIPTION
        "This is a table of created instance Syslog configuration parameters"
    ::= { mepConfigSyslog 1 }

mepConfigSyslogEntry OBJECT-TYPE
    SYNTAX      MepConfigSyslogEntry
    MAX-ACCESS  not-accessible
    STATUS      current
    DESCRIPTION
        "This is a created instance Syslog configuration parameters"
    INDEX       { mepConfigSyslogId }
    ::= { mepConfigSyslogTable 1 }

MepConfigSyslogEntry ::= SEQUENCE {
    mepConfigSyslogId      Integer32,
    mepConfigSyslogEnable  TruthValue
}

mepConfigSyslogId OBJECT-TYPE
    SYNTAX      Integer32 (0..2147483647)
    MAX-ACCESS  not-accessible
    STATUS      current
    DESCRIPTION
        "The MEP instance ID"
    ::= { mepConfigSyslogEntry 1 }

mepConfigSyslogEnable OBJECT-TYPE
    SYNTAX      TruthValue
    MAX-ACCESS  read-write
    STATUS      current
    DESCRIPTION
        "The instance can enable generation of syslog entries "
    ::= { mepConfigSyslogEntry 2 }

mepConfigTlv OBJECT IDENTIFIER
    ::= { mepConfig 14 }

mepConfigTlvLeaf OBJECT IDENTIFIER
    ::= { mepConfigTlv 1 }

mepConfigTlvLeafOsTlvOuiFirst OBJECT-TYPE
    SYNTAX      Unsigned8
    MAX-ACCESS  read-write
    STATUS      current
    DESCRIPTION
        "Transmitted OS TLV - The OUI content first nibble"
    ::= { mepConfigTlvLeaf 2 }

mepConfigTlvLeafOsTlvOuiSecond OBJECT-TYPE
    SYNTAX      Unsigned8
    MAX-ACCESS  read-write
    STATUS      current
    DESCRIPTION
        "Transmitted OS TLV - The OUI content second nibble"
    ::= { mepConfigTlvLeaf 3 }

mepConfigTlvLeafOsTlvOuiThird OBJECT-TYPE
    SYNTAX      Unsigned8
    MAX-ACCESS  read-write
    STATUS      current
    DESCRIPTION
        "Transmitted OS TLV - The OUI content third nibble"
    ::= { mepConfigTlvLeaf 4 }

mepConfigTlvLeafOsTlvSubType OBJECT-TYPE
    SYNTAX      Unsigned8
    MAX-ACCESS  read-write
    STATUS      current
    DESCRIPTION
        "Transmitted OS TLV - The Sub-Type content"
    ::= { mepConfigTlvLeaf 5 }

mepConfigTlvLeafOsTlvValue OBJECT-TYPE
    SYNTAX      Unsigned8
    MAX-ACCESS  read-write
    STATUS      current
    DESCRIPTION
        "Transmitted OS TLV - The Value content"
    ::= { mepConfigTlvLeaf 6 }

mepConfigBfd OBJECT IDENTIFIER
    ::= { mepConfig 15 }

mepConfigBfdTable OBJECT-TYPE
    SYNTAX      SEQUENCE OF MepConfigBfdEntry
    MAX-ACCESS  not-accessible
    STATUS      current
    DESCRIPTION
        "This is a table of created instance Bidirectional Forwarding Detection
         configuration parameters"
    ::= { mepConfigBfd 1 }

mepConfigBfdEntry OBJECT-TYPE
    SYNTAX      MepConfigBfdEntry
    MAX-ACCESS  not-accessible
    STATUS      current
    DESCRIPTION
        "This is a created instance Bidirectional Forwarding Detection
         configuration parameters."
    INDEX       { mepConfigBfdId }
    ::= { mepConfigBfdTable 1 }

MepConfigBfdEntry ::= SEQUENCE {
    mepConfigBfdId             Integer32,
    mepConfigBfdEnable         TruthValue,
    mepConfigBfdIsIndependent  TruthValue,
    mepConfigBfdCcOnly         TruthValue,
    mepConfigBfdTxAuthEnabled  TruthValue,
    mepConfigBfdRxAuthEnabled  TruthValue,
    mepConfigBfdTxAuthKeyId    Unsigned8,
    mepConfigBfdCcPeriod       Unsigned32,
    mepConfigBfdRxFlow         Unsigned32,
    mepConfigBfdAction         RowEditorState
}

mepConfigBfdId OBJECT-TYPE
    SYNTAX      Integer32 (0..2147483647)
    MAX-ACCESS  not-accessible
    STATUS      current
    DESCRIPTION
        "The MEP instance ID"
    ::= { mepConfigBfdEntry 1 }

mepConfigBfdEnable OBJECT-TYPE
    SYNTAX      TruthValue
    MAX-ACCESS  read-write
    STATUS      current
    DESCRIPTION
        "CC/CV transmission and LOC detection is enabled if true."
    ::= { mepConfigBfdEntry 2 }

mepConfigBfdIsIndependent OBJECT-TYPE
    SYNTAX      TruthValue
    MAX-ACCESS  read-write
    STATUS      current
    DESCRIPTION
        "Independent mode if true, coordinated if false."
    ::= { mepConfigBfdEntry 3 }

mepConfigBfdCcOnly OBJECT-TYPE
    SYNTAX      TruthValue
    MAX-ACCESS  read-write
    STATUS      current
    DESCRIPTION
        "Only transmit CC frames (no CV frames) if true."
    ::= { mepConfigBfdEntry 4 }

mepConfigBfdTxAuthEnabled OBJECT-TYPE
    SYNTAX      TruthValue
    MAX-ACCESS  read-write
    STATUS      current
    DESCRIPTION
        "Authentication enabled for transmission of CC/CV frames to peer if
         true."
    ::= { mepConfigBfdEntry 5 }

mepConfigBfdRxAuthEnabled OBJECT-TYPE
    SYNTAX      TruthValue
    MAX-ACCESS  read-write
    STATUS      current
    DESCRIPTION
        "Authentication enabled for reception of CC/CV frames from peer if true."
    ::= { mepConfigBfdEntry 6 }

mepConfigBfdTxAuthKeyId OBJECT-TYPE
    SYNTAX      Unsigned8
    MAX-ACCESS  read-write
    STATUS      current
    DESCRIPTION
        "Authentication used for transmission of CC/CV frames to peer."
    ::= { mepConfigBfdEntry 7 }

mepConfigBfdCcPeriod OBJECT-TYPE
    SYNTAX      Unsigned32
    MAX-ACCESS  read-write
    STATUS      current
    DESCRIPTION
        "Desired CC transmission period in us, 1 us - 60 sec."
    ::= { mepConfigBfdEntry 8 }

mepConfigBfdRxFlow OBJECT-TYPE
    SYNTAX      Unsigned32
    MAX-ACCESS  read-write
    STATUS      current
    DESCRIPTION
        "Rx flow number (MPLS-TP link, MPLS-TP tunnel, MPLS-TP LSP or MPLS-TP
         Pseudo-Wire) for independent mode."
    ::= { mepConfigBfdEntry 9 }

mepConfigBfdAction OBJECT-TYPE
    SYNTAX      RowEditorState
    MAX-ACCESS  read-write
    STATUS      current
    DESCRIPTION
        "Action"
    ::= { mepConfigBfdEntry 100 }

mepConfigBfdRowEditor OBJECT IDENTIFIER
    ::= { mepConfigBfd 2 }

mepConfigBfdRowEditorId OBJECT-TYPE
    SYNTAX      Integer32 (0..2147483647)
    MAX-ACCESS  read-write
    STATUS      current
    DESCRIPTION
        "The MEP instance ID"
    ::= { mepConfigBfdRowEditor 1 }

mepConfigBfdRowEditorEnable OBJECT-TYPE
    SYNTAX      TruthValue
    MAX-ACCESS  read-write
    STATUS      current
    DESCRIPTION
        "CC/CV transmission and LOC detection is enabled if true."
    ::= { mepConfigBfdRowEditor 2 }

mepConfigBfdRowEditorIsIndependent OBJECT-TYPE
    SYNTAX      TruthValue
    MAX-ACCESS  read-write
    STATUS      current
    DESCRIPTION
        "Independent mode if true, coordinated if false."
    ::= { mepConfigBfdRowEditor 3 }

mepConfigBfdRowEditorCcOnly OBJECT-TYPE
    SYNTAX      TruthValue
    MAX-ACCESS  read-write
    STATUS      current
    DESCRIPTION
        "Only transmit CC frames (no CV frames) if true."
    ::= { mepConfigBfdRowEditor 4 }

mepConfigBfdRowEditorTxAuthEnabled OBJECT-TYPE
    SYNTAX      TruthValue
    MAX-ACCESS  read-write
    STATUS      current
    DESCRIPTION
        "Authentication enabled for transmission of CC/CV frames to peer if
         true."
    ::= { mepConfigBfdRowEditor 5 }

mepConfigBfdRowEditorRxAuthEnabled OBJECT-TYPE
    SYNTAX      TruthValue
    MAX-ACCESS  read-write
    STATUS      current
    DESCRIPTION
        "Authentication enabled for reception of CC/CV frames from peer if true."
    ::= { mepConfigBfdRowEditor 6 }

mepConfigBfdRowEditorTxAuthKeyId OBJECT-TYPE
    SYNTAX      Unsigned8
    MAX-ACCESS  read-write
    STATUS      current
    DESCRIPTION
        "Authentication used for transmission of CC/CV frames to peer."
    ::= { mepConfigBfdRowEditor 7 }

mepConfigBfdRowEditorCcPeriod OBJECT-TYPE
    SYNTAX      Unsigned32
    MAX-ACCESS  read-write
    STATUS      current
    DESCRIPTION
        "Desired CC transmission period in us, 1 us - 60 sec."
    ::= { mepConfigBfdRowEditor 8 }

mepConfigBfdRowEditorRxFlow OBJECT-TYPE
    SYNTAX      Unsigned32
    MAX-ACCESS  read-write
    STATUS      current
    DESCRIPTION
        "Rx flow number (MPLS-TP link, MPLS-TP tunnel, MPLS-TP LSP or MPLS-TP
         Pseudo-Wire) for independent mode."
    ::= { mepConfigBfdRowEditor 9 }

mepConfigBfdRowEditorAction OBJECT-TYPE
    SYNTAX      RowEditorState
    MAX-ACCESS  read-write
    STATUS      current
    DESCRIPTION
        "Action"
    ::= { mepConfigBfdRowEditor 100 }

mepConfigBfdAuth OBJECT IDENTIFIER
    ::= { mepConfig 16 }

mepConfigBfdAuthTable OBJECT-TYPE
    SYNTAX      SEQUENCE OF MepConfigBfdAuthEntry
    MAX-ACCESS  not-accessible
    STATUS      current
    DESCRIPTION
        "This is a table of created instance Bidirectional Forwarding Detection
         Authentication configuration parameters"
    ::= { mepConfigBfdAuth 1 }

mepConfigBfdAuthEntry OBJECT-TYPE
    SYNTAX      MepConfigBfdAuthEntry
    MAX-ACCESS  not-accessible
    STATUS      current
    DESCRIPTION
        "This is a created instance Bidirectional Forwarding Detection
         Authentication configuration parameters."
    INDEX       { mepConfigBfdAuthId }
    ::= { mepConfigBfdAuthTable 1 }

MepConfigBfdAuthEntry ::= SEQUENCE {
    mepConfigBfdAuthId       Integer32,
    mepConfigBfdAuthKeyType  MepBfdAuthenticationType,
    mepConfigBfdAuthKeyLen   Unsigned8,
    mepConfigBfdAuthKey      OCTET STRING,
    mepConfigBfdAuthAction   RowEditorState
}

mepConfigBfdAuthId OBJECT-TYPE
    SYNTAX      Integer32 (0..2147483647)
    MAX-ACCESS  not-accessible
    STATUS      current
    DESCRIPTION
        "The MEP instance ID"
    ::= { mepConfigBfdAuthEntry 1 }

mepConfigBfdAuthKeyType OBJECT-TYPE
    SYNTAX      MepBfdAuthenticationType
    MAX-ACCESS  read-write
    STATUS      current
    DESCRIPTION
        "Key type."
    ::= { mepConfigBfdAuthEntry 2 }

mepConfigBfdAuthKeyLen OBJECT-TYPE
    SYNTAX      Unsigned8
    MAX-ACCESS  read-write
    STATUS      current
    DESCRIPTION
        "Key length in bytes. 1-16 for Simple Password, 16 for MD5 and 20 for
         SHA1."
    ::= { mepConfigBfdAuthEntry 3 }

mepConfigBfdAuthKey OBJECT-TYPE
    SYNTAX      OCTET STRING (SIZE(20))
    MAX-ACCESS  read-write
    STATUS      current
    DESCRIPTION
        "Key value."
    ::= { mepConfigBfdAuthEntry 4 }

mepConfigBfdAuthAction OBJECT-TYPE
    SYNTAX      RowEditorState
    MAX-ACCESS  read-write
    STATUS      current
    DESCRIPTION
        "Action"
    ::= { mepConfigBfdAuthEntry 100 }

mepConfigBfdAuthRowEditor OBJECT IDENTIFIER
    ::= { mepConfigBfdAuth 2 }

mepConfigBfdAuthRowEditorId OBJECT-TYPE
    SYNTAX      Integer32 (0..2147483647)
    MAX-ACCESS  read-write
    STATUS      current
    DESCRIPTION
        "The MEP instance ID"
    ::= { mepConfigBfdAuthRowEditor 1 }

mepConfigBfdAuthRowEditorKeyType OBJECT-TYPE
    SYNTAX      MepBfdAuthenticationType
    MAX-ACCESS  read-write
    STATUS      current
    DESCRIPTION
        "Key type."
    ::= { mepConfigBfdAuthRowEditor 2 }

mepConfigBfdAuthRowEditorKeyLen OBJECT-TYPE
    SYNTAX      Unsigned8
    MAX-ACCESS  read-write
    STATUS      current
    DESCRIPTION
        "Key length in bytes. 1-16 for Simple Password, 16 for MD5 and 20 for
         SHA1."
    ::= { mepConfigBfdAuthRowEditor 3 }

mepConfigBfdAuthRowEditorKey OBJECT-TYPE
    SYNTAX      OCTET STRING (SIZE(20))
    MAX-ACCESS  read-write
    STATUS      current
    DESCRIPTION
        "Key value."
    ::= { mepConfigBfdAuthRowEditor 4 }

mepConfigBfdAuthRowEditorAction OBJECT-TYPE
    SYNTAX      RowEditorState
    MAX-ACCESS  read-write
    STATUS      current
    DESCRIPTION
        "Action"
    ::= { mepConfigBfdAuthRowEditor 100 }

mepConfigRt OBJECT IDENTIFIER
    ::= { mepConfig 17 }

mepConfigRtTable OBJECT-TYPE
    SYNTAX      SEQUENCE OF MepConfigRtEntry
    MAX-ACCESS  not-accessible
    STATUS      current
    DESCRIPTION
        "This is a table of created instance Route Trace configuration
         parameters"
    ::= { mepConfigRt 1 }

mepConfigRtEntry OBJECT-TYPE
    SYNTAX      MepConfigRtEntry
    MAX-ACCESS  not-accessible
    STATUS      current
    DESCRIPTION
        "This is a created instance Route Trace configuration parameters."
    INDEX       { mepConfigRtId }
    ::= { mepConfigRtTable 1 }

MepConfigRtEntry ::= SEQUENCE {
    mepConfigRtId             Integer32,
    mepConfigRtTrafficClass   Unsigned8,
    mepConfigRtSrcIdTlv       TruthValue,
    mepConfigRtDstIdTlv       TruthValue,
    mepConfigRtPadTlvType     MepRtPadTlvType,
    mepConfigRtPadTlvLen      Unsigned16,
    mepConfigRtFlags          Unsigned8,
    mepConfigRtMaxTimeToLive  Unsigned8,
    mepConfigRtAction         RowEditorState
}

mepConfigRtId OBJECT-TYPE
    SYNTAX      Integer32 (0..2147483647)
    MAX-ACCESS  not-accessible
    STATUS      current
    DESCRIPTION
        "The MEP instance ID"
    ::= { mepConfigRtEntry 1 }

mepConfigRtTrafficClass OBJECT-TYPE
    SYNTAX      Unsigned8
    MAX-ACCESS  read-write
    STATUS      current
    DESCRIPTION
        "Traffic class value used in the transmitted RT request PDU. Range 0 to
         7"
    ::= { mepConfigRtEntry 2 }

mepConfigRtSrcIdTlv OBJECT-TYPE
    SYNTAX      TruthValue
    MAX-ACCESS  read-write
    STATUS      current
    DESCRIPTION
        "Include Source ID TLV in the RT request"
    ::= { mepConfigRtEntry 3 }

mepConfigRtDstIdTlv OBJECT-TYPE
    SYNTAX      TruthValue
    MAX-ACCESS  read-write
    STATUS      current
    DESCRIPTION
        "Include Destination ID TLV in the RT request"
    ::= { mepConfigRtEntry 4 }

mepConfigRtPadTlvType OBJECT-TYPE
    SYNTAX      MepRtPadTlvType
    MAX-ACCESS  read-write
    STATUS      current
    DESCRIPTION
        "Pad TLV type"
    ::= { mepConfigRtEntry 5 }

mepConfigRtPadTlvLen OBJECT-TYPE
    SYNTAX      Unsigned16
    MAX-ACCESS  read-write
    STATUS      current
    DESCRIPTION
        "Pad TLV data length. Range 1 to 1024."
    ::= { mepConfigRtEntry 6 }

mepConfigRtFlags OBJECT-TYPE
    SYNTAX      Unsigned8
    MAX-ACCESS  read-write
    STATUS      current
    DESCRIPTION
        "Flags for RT request. Bit 0: V flag (Validate FEC stack), bit 1: T flag
         (Respond Only If TTL Expired), bit 2: R flag (Validate Reverse Path)"
    ::= { mepConfigRtEntry 7 }

mepConfigRtMaxTimeToLive OBJECT-TYPE
    SYNTAX      Unsigned8
    MAX-ACCESS  read-write
    STATUS      current
    DESCRIPTION
        "Max. Time To Live for RT request."
    ::= { mepConfigRtEntry 8 }

mepConfigRtAction OBJECT-TYPE
    SYNTAX      RowEditorState
    MAX-ACCESS  read-write
    STATUS      current
    DESCRIPTION
        "Action"
    ::= { mepConfigRtEntry 100 }

mepConfigRtRowEditor OBJECT IDENTIFIER
    ::= { mepConfigRt 2 }

mepConfigRtRowEditorId OBJECT-TYPE
    SYNTAX      Integer32 (0..2147483647)
    MAX-ACCESS  read-write
    STATUS      current
    DESCRIPTION
        "The MEP instance ID"
    ::= { mepConfigRtRowEditor 1 }

mepConfigRtRowEditorTrafficClass OBJECT-TYPE
    SYNTAX      Unsigned8
    MAX-ACCESS  read-write
    STATUS      current
    DESCRIPTION
        "Traffic class value used in the transmitted RT request PDU. Range 0 to
         7"
    ::= { mepConfigRtRowEditor 2 }

mepConfigRtRowEditorSrcIdTlv OBJECT-TYPE
    SYNTAX      TruthValue
    MAX-ACCESS  read-write
    STATUS      current
    DESCRIPTION
        "Include Source ID TLV in the RT request"
    ::= { mepConfigRtRowEditor 3 }

mepConfigRtRowEditorDstIdTlv OBJECT-TYPE
    SYNTAX      TruthValue
    MAX-ACCESS  read-write
    STATUS      current
    DESCRIPTION
        "Include Destination ID TLV in the RT request"
    ::= { mepConfigRtRowEditor 4 }

mepConfigRtRowEditorPadTlvType OBJECT-TYPE
    SYNTAX      MepRtPadTlvType
    MAX-ACCESS  read-write
    STATUS      current
    DESCRIPTION
        "Pad TLV type"
    ::= { mepConfigRtRowEditor 5 }

mepConfigRtRowEditorPadTlvLen OBJECT-TYPE
    SYNTAX      Unsigned16
    MAX-ACCESS  read-write
    STATUS      current
    DESCRIPTION
        "Pad TLV data length. Range 1 to 1024."
    ::= { mepConfigRtRowEditor 6 }

mepConfigRtRowEditorFlags OBJECT-TYPE
    SYNTAX      Unsigned8
    MAX-ACCESS  read-write
    STATUS      current
    DESCRIPTION
        "Flags for RT request. Bit 0: V flag (Validate FEC stack), bit 1: T flag
         (Respond Only If TTL Expired), bit 2: R flag (Validate Reverse Path)"
    ::= { mepConfigRtRowEditor 7 }

mepConfigRtRowEditorMaxTimeToLive OBJECT-TYPE
    SYNTAX      Unsigned8
    MAX-ACCESS  read-write
    STATUS      current
    DESCRIPTION
        "Max. Time To Live for RT request."
    ::= { mepConfigRtRowEditor 8 }

mepConfigRtRowEditorAction OBJECT-TYPE
    SYNTAX      RowEditorState
    MAX-ACCESS  read-write
    STATUS      current
    DESCRIPTION
        "Action"
    ::= { mepConfigRtRowEditor 100 }

mepConfigLst OBJECT IDENTIFIER
    ::= { mepConfig 18 }

mepConfigLstTable OBJECT-TYPE
    SYNTAX      SEQUENCE OF MepConfigLstEntry
    MAX-ACCESS  not-accessible
    STATUS      current
    DESCRIPTION
        "This is a table of created instance Link State Tracking configuration
         parameters"
    ::= { mepConfigLst 1 }

mepConfigLstEntry OBJECT-TYPE
    SYNTAX      MepConfigLstEntry
    MAX-ACCESS  not-accessible
    STATUS      current
    DESCRIPTION
        "This is a created instance Link State Tracking configuration parameters"
    INDEX       { mepConfigLstId }
    ::= { mepConfigLstTable 1 }

MepConfigLstEntry ::= SEQUENCE {
    mepConfigLstId      Integer32,
    mepConfigLstEnable  TruthValue
}

mepConfigLstId OBJECT-TYPE
    SYNTAX      Integer32 (0..2147483647)
    MAX-ACCESS  not-accessible
    STATUS      current
    DESCRIPTION
        "The MEP instance ID"
    ::= { mepConfigLstEntry 1 }

mepConfigLstEnable OBJECT-TYPE
    SYNTAX      TruthValue
    MAX-ACCESS  read-write
    STATUS      current
    DESCRIPTION
        "The instance can enable Link State Tracking. When LST is enabled, Local
         SF or received 'isDown' in CCM Interface Status TLV, will bring down
         the residence port. Only valid in Up-MEP."
    ::= { mepConfigLstEntry 2 }

mepConfigLmAvail OBJECT IDENTIFIER
    ::= { mepConfig 19 }

mepConfigLmAvailTable OBJECT-TYPE
    SYNTAX      SEQUENCE OF MepConfigLmAvailEntry
    MAX-ACCESS  not-accessible
    STATUS      current
    DESCRIPTION
        "This is a table of created instance Loss Measurement Availability
         configuration parameters"
    ::= { mepConfigLmAvail 1 }

mepConfigLmAvailEntry OBJECT-TYPE
    SYNTAX      MepConfigLmAvailEntry
    MAX-ACCESS  not-accessible
    STATUS      current
    DESCRIPTION
        "This is a created instance Loss Measurement Availability parameters."
    INDEX       { mepConfigLmAvailId }
    ::= { mepConfigLmAvailTable 1 }

MepConfigLmAvailEntry ::= SEQUENCE {
    mepConfigLmAvailId           Integer32,
    mepConfigLmAvailEnable       TruthValue,
    mepConfigLmAvailLosRatioThr  Unsigned32,
    mepConfigLmAvailInterval     Unsigned32,
    mepConfigLmAvailMaintenance  TruthValue
}

mepConfigLmAvailId OBJECT-TYPE
    SYNTAX      Integer32 (0..2147483647)
    MAX-ACCESS  not-accessible
    STATUS      current
    DESCRIPTION
        "The MEP instance ID"
    ::= { mepConfigLmAvailEntry 1 }

mepConfigLmAvailEnable OBJECT-TYPE
    SYNTAX      TruthValue
    MAX-ACCESS  read-write
    STATUS      current
    DESCRIPTION
        "Loss Measurement Availability is enabled"
    ::= { mepConfigLmAvailEntry 2 }

mepConfigLmAvailLosRatioThr OBJECT-TYPE
    SYNTAX      Unsigned32
    MAX-ACCESS  read-write
    STATUS      current
    DESCRIPTION
        "Availability frame loss ratio threshold in per mille."
    ::= { mepConfigLmAvailEntry 3 }

mepConfigLmAvailInterval OBJECT-TYPE
    SYNTAX      Unsigned32
    MAX-ACCESS  read-write
    STATUS      current
    DESCRIPTION
        "Availability interval - number of measurements with same availability
         in order to change Availability state."
    ::= { mepConfigLmAvailEntry 4 }

mepConfigLmAvailMaintenance OBJECT-TYPE
    SYNTAX      TruthValue
    MAX-ACCESS  read-write
    STATUS      current
    DESCRIPTION
        "Loss Measurement Availability Maintenance enable/disable"
    ::= { mepConfigLmAvailEntry 5 }

mepConfigLmHli OBJECT IDENTIFIER
    ::= { mepConfig 20 }

mepConfigLmHliTable OBJECT-TYPE
    SYNTAX      SEQUENCE OF MepConfigLmHliEntry
    MAX-ACCESS  not-accessible
    STATUS      current
    DESCRIPTION
        "This is a table of created instance Loss Measurement High Loss Interval
         configuration parameters"
    ::= { mepConfigLmHli 1 }

mepConfigLmHliEntry OBJECT-TYPE
    SYNTAX      MepConfigLmHliEntry
    MAX-ACCESS  not-accessible
    STATUS      current
    DESCRIPTION
        "This is a created instance Loss Measurement High Loss Interval
         parameters."
    INDEX       { mepConfigLmHliId }
    ::= { mepConfigLmHliTable 1 }

MepConfigLmHliEntry ::= SEQUENCE {
    mepConfigLmHliId                Integer32,
    mepConfigLmHliEnable            TruthValue,
    mepConfigLmHliHiLosRatioThr     Unsigned32,
    mepConfigLmHliConInterval       Unsigned32,
    mepConfigLmHliCntHolddownTimer  Unsigned32
}

mepConfigLmHliId OBJECT-TYPE
    SYNTAX      Integer32 (0..2147483647)
    MAX-ACCESS  not-accessible
    STATUS      current
    DESCRIPTION
        "The MEP instance ID"
    ::= { mepConfigLmHliEntry 1 }

mepConfigLmHliEnable OBJECT-TYPE
    SYNTAX      TruthValue
    MAX-ACCESS  read-write
    STATUS      current
    DESCRIPTION
        "Loss Measurement High Loss Interval is enabled"
    ::= { mepConfigLmHliEntry 2 }

mepConfigLmHliHiLosRatioThr OBJECT-TYPE
    SYNTAX      Unsigned32
    MAX-ACCESS  read-write
    STATUS      current
    DESCRIPTION
        "High Loss Interval frame loss ratio threshold in per mille."
    ::= { mepConfigLmHliEntry 3 }

mepConfigLmHliConInterval OBJECT-TYPE
    SYNTAX      Unsigned32
    MAX-ACCESS  read-write
    STATUS      current
    DESCRIPTION
        "High Loss Interval consecutive interval (number of measurements)."
    ::= { mepConfigLmHliEntry 4 }

mepConfigLmHliCntHolddownTimer OBJECT-TYPE
    SYNTAX      Unsigned32
    MAX-ACCESS  read-write
    STATUS      current
    DESCRIPTION
        "Holddown timer in seconds for JSON notification updates for High Loss
         Interval NearEndCnt and FarEndCnt."
    ::= { mepConfigLmHliEntry 5 }

mepConfigLmSdeg OBJECT IDENTIFIER
    ::= { mepConfig 21 }

mepConfigLmSdegTable OBJECT-TYPE
    SYNTAX      SEQUENCE OF MepConfigLmSdegEntry
    MAX-ACCESS  not-accessible
    STATUS      current
    DESCRIPTION
        "This is a table of created instance Loss Measurement Signal Degrade
         configuration parameters"
    ::= { mepConfigLmSdeg 1 }

mepConfigLmSdegEntry OBJECT-TYPE
    SYNTAX      MepConfigLmSdegEntry
    MAX-ACCESS  not-accessible
    STATUS      current
    DESCRIPTION
        "This is a created instance Loss Measurement Signal Degrade parameters."
    INDEX       { mepConfigLmSdegId }
    ::= { mepConfigLmSdegTable 1 }

MepConfigLmSdegEntry ::= SEQUENCE {
    mepConfigLmSdegId           Integer32,
    mepConfigLmSdegEnable       TruthValue,
    mepConfigLmSdegTxMin        Unsigned32,
    mepConfigLmSdegLosRatioThr  Unsigned32,
    mepConfigLmSdegBadThr       Unsigned32,
    mepConfigLmSdegGoodThr      Unsigned32
}

mepConfigLmSdegId OBJECT-TYPE
    SYNTAX      Integer32 (0..2147483647)
    MAX-ACCESS  not-accessible
    STATUS      current
    DESCRIPTION
        "The MEP instance ID"
    ::= { mepConfigLmSdegEntry 1 }

mepConfigLmSdegEnable OBJECT-TYPE
    SYNTAX      TruthValue
    MAX-ACCESS  read-write
    STATUS      current
    DESCRIPTION
        "Loss Measurement Signal Degrade is enabled"
    ::= { mepConfigLmSdegEntry 2 }

mepConfigLmSdegTxMin OBJECT-TYPE
    SYNTAX      Unsigned32
    MAX-ACCESS  read-write
    STATUS      current
    DESCRIPTION
        "Minimum number of frames that must be transmitted in a measurement
         before frame loss ratio is tested against LosRatioThr."
    ::= { mepConfigLmSdegEntry 3 }

mepConfigLmSdegLosRatioThr OBJECT-TYPE
    SYNTAX      Unsigned32
    MAX-ACCESS  read-write
    STATUS      current
    DESCRIPTION
        "Signal Degraded frame loss ratio threshold in per mille."
    ::= { mepConfigLmSdegEntry 4 }

mepConfigLmSdegBadThr OBJECT-TYPE
    SYNTAX      Unsigned32
    MAX-ACCESS  read-write
    STATUS      current
    DESCRIPTION
        "Number of consecutive bad interval measurements required to set degrade
         state."
    ::= { mepConfigLmSdegEntry 5 }

mepConfigLmSdegGoodThr OBJECT-TYPE
    SYNTAX      Unsigned32
    MAX-ACCESS  read-write
    STATUS      current
    DESCRIPTION
        "Number of consecutive good interval measurements required to clear
         degrade state."
    ::= { mepConfigLmSdegEntry 6 }

mepStatus OBJECT IDENTIFIER
    ::= { mepMibObjects 3 }

mepStatusInstance OBJECT IDENTIFIER
    ::= { mepStatus 1 }

mepStatusInstanceTable OBJECT-TYPE
    SYNTAX      SEQUENCE OF MepStatusInstanceEntry
    MAX-ACCESS  not-accessible
    STATUS      current
    DESCRIPTION
        "This is a table of created instance status"
    ::= { mepStatusInstance 1 }

mepStatusInstanceEntry OBJECT-TYPE
    SYNTAX      MepStatusInstanceEntry
    MAX-ACCESS  not-accessible
    STATUS      current
    DESCRIPTION
        "This is a created instance status"
    INDEX       { mepStatusInstanceId }
    ::= { mepStatusInstanceTable 1 }

MepStatusInstanceEntry ::= SEQUENCE {
    mepStatusInstanceId       Integer32,
    mepStatusInstanceClevel   TruthValue,
    mepStatusInstanceCmeg     TruthValue,
    mepStatusInstanceCmep     TruthValue,
    mepStatusInstanceCssf     TruthValue,
    mepStatusInstanceCais     TruthValue,
    mepStatusInstanceClck     TruthValue,
    mepStatusInstanceAtsf     TruthValue,
    mepStatusInstanceAtsd     TruthValue,
    mepStatusInstanceAblk     TruthValue,
    mepStatusInstanceCloop    TruthValue,
    mepStatusInstanceCconfig  TruthValue
}

mepStatusInstanceId OBJECT-TYPE
    SYNTAX      Integer32 (0..2147483647)
    MAX-ACCESS  not-accessible
    STATUS      current
    DESCRIPTION
        "The MEP instance ID"
    ::= { mepStatusInstanceEntry 1 }

mepStatusInstanceClevel OBJECT-TYPE
    SYNTAX      TruthValue
    MAX-ACCESS  read-only
    STATUS      current
    DESCRIPTION
        "Incorrect CCM level received"
    ::= { mepStatusInstanceEntry 2 }

mepStatusInstanceCmeg OBJECT-TYPE
    SYNTAX      TruthValue
    MAX-ACCESS  read-only
    STATUS      current
    DESCRIPTION
        "Incorrect CCM MEG id received"
    ::= { mepStatusInstanceEntry 3 }

mepStatusInstanceCmep OBJECT-TYPE
    SYNTAX      TruthValue
    MAX-ACCESS  read-only
    STATUS      current
    DESCRIPTION
        "Incorrect CCM MEP id received"
    ::= { mepStatusInstanceEntry 4 }

mepStatusInstanceCssf OBJECT-TYPE
    SYNTAX      TruthValue
    MAX-ACCESS  read-only
    STATUS      current
    DESCRIPTION
        "SSF state"
    ::= { mepStatusInstanceEntry 5 }

mepStatusInstanceCais OBJECT-TYPE
    SYNTAX      TruthValue
    MAX-ACCESS  read-only
    STATUS      current
    DESCRIPTION
        "AIS state. AIS is received."
    ::= { mepStatusInstanceEntry 6 }

mepStatusInstanceClck OBJECT-TYPE
    SYNTAX      TruthValue
    MAX-ACCESS  read-only
    STATUS      current
    DESCRIPTION
        "Locked State. LCK is received."
    ::= { mepStatusInstanceEntry 7 }

mepStatusInstanceAtsf OBJECT-TYPE
    SYNTAX      TruthValue
    MAX-ACCESS  read-only
    STATUS      current
    DESCRIPTION
        "Trail Signal fail consequent action is calculated"
    ::= { mepStatusInstanceEntry 8 }

mepStatusInstanceAtsd OBJECT-TYPE
    SYNTAX      TruthValue
    MAX-ACCESS  read-only
    STATUS      current
    DESCRIPTION
        "Trail Signal degrade consequent action is calculated"
    ::= { mepStatusInstanceEntry 9 }

mepStatusInstanceAblk OBJECT-TYPE
    SYNTAX      TruthValue
    MAX-ACCESS  read-only
    STATUS      current
    DESCRIPTION
        "Block consequent action is calculated"
    ::= { mepStatusInstanceEntry 10 }

mepStatusInstanceCloop OBJECT-TYPE
    SYNTAX      TruthValue
    MAX-ACCESS  read-only
    STATUS      current
    DESCRIPTION
        "Loop is detected. CCM is received with own MEP ID and SMAC."
    ::= { mepStatusInstanceEntry 11 }

mepStatusInstanceCconfig OBJECT-TYPE
    SYNTAX      TruthValue
    MAX-ACCESS  read-only
    STATUS      current
    DESCRIPTION
        "Configuration error detected. CCM is received with own MEP ID."
    ::= { mepStatusInstanceEntry 12 }

mepStatusInstancePeerTable OBJECT-TYPE
    SYNTAX      SEQUENCE OF MepStatusInstancePeerEntry
    MAX-ACCESS  not-accessible
    STATUS      current
    DESCRIPTION
        "This is a table of peer MEP status"
    ::= { mepStatusInstance 2 }

mepStatusInstancePeerEntry OBJECT-TYPE
    SYNTAX      MepStatusInstancePeerEntry
    MAX-ACCESS  not-accessible
    STATUS      current
    DESCRIPTION
        "This is a peer MEP status"
    INDEX       { mepStatusInstancePeerId,
                  mepStatusInstancePeerPeerId }
    ::= { mepStatusInstancePeerTable 1 }

MepStatusInstancePeerEntry ::= SEQUENCE {
    mepStatusInstancePeerId       Integer32,
    mepStatusInstancePeerPeerId   Integer32,
    mepStatusInstancePeerCloc     TruthValue,
    mepStatusInstancePeerCrdi     TruthValue,
    mepStatusInstancePeerCperiod  TruthValue,
    mepStatusInstancePeerCprio    TruthValue,
    mepStatusInstancePeerCdeg     TruthValue
}

mepStatusInstancePeerId OBJECT-TYPE
    SYNTAX      Integer32 (0..2147483647)
    MAX-ACCESS  not-accessible
    STATUS      current
    DESCRIPTION
        "The MEP instance ID"
    ::= { mepStatusInstancePeerEntry 1 }

mepStatusInstancePeerPeerId OBJECT-TYPE
    SYNTAX      Integer32 (0..2147483647)
    MAX-ACCESS  not-accessible
    STATUS      current
    DESCRIPTION
        "The Peer MEP ID"
    ::= { mepStatusInstancePeerEntry 2 }

mepStatusInstancePeerCloc OBJECT-TYPE
    SYNTAX      TruthValue
    MAX-ACCESS  read-only
    STATUS      current
    DESCRIPTION
        "CCM LOC state from peer MEP"
    ::= { mepStatusInstancePeerEntry 3 }

mepStatusInstancePeerCrdi OBJECT-TYPE
    SYNTAX      TruthValue
    MAX-ACCESS  read-only
    STATUS      current
    DESCRIPTION
        "CCM RDI state from peer MEP"
    ::= { mepStatusInstancePeerEntry 4 }

mepStatusInstancePeerCperiod OBJECT-TYPE
    SYNTAX      TruthValue
    MAX-ACCESS  read-only
    STATUS      current
    DESCRIPTION
        "CCM Period state from peer MEP"
    ::= { mepStatusInstancePeerEntry 5 }

mepStatusInstancePeerCprio OBJECT-TYPE
    SYNTAX      TruthValue
    MAX-ACCESS  read-only
    STATUS      current
    DESCRIPTION
        "CCM Priority state from peer MEP"
    ::= { mepStatusInstancePeerEntry 6 }

mepStatusInstancePeerCdeg OBJECT-TYPE
    SYNTAX      TruthValue
    MAX-ACCESS  read-only
    STATUS      current
    DESCRIPTION
        "Signal Degraded."
    ::= { mepStatusInstancePeerEntry 7 }

mepStatusLm OBJECT IDENTIFIER
    ::= { mepStatus 2 }

mepStatusLmTable OBJECT-TYPE
    SYNTAX      SEQUENCE OF MepStatusLmEntry
    MAX-ACCESS  not-accessible
    STATUS      current
    DESCRIPTION
        "This is a table of Loss Measurement status"
    ::= { mepStatusLm 1 }

mepStatusLmEntry OBJECT-TYPE
    SYNTAX      MepStatusLmEntry
    MAX-ACCESS  not-accessible
    STATUS      current
    DESCRIPTION
        "This is a Loss Measurement status"
    INDEX       { mepStatusLmId }
    ::= { mepStatusLmTable 1 }

MepStatusLmEntry ::= SEQUENCE {
    mepStatusLmId                    Integer32,
    mepStatusLmTxCounter             Unsigned32,
    mepStatusLmRxCounter             Unsigned32,
    mepStatusLmNearEndLosCounterTot  Integer32,
    mepStatusLmFarEndLosCounterTot   Integer32,
    mepStatusLmNearEndLosRatioInt    Unsigned32,
    mepStatusLmFarEndLosRatioInt     Unsigned32,
    mepStatusLmNearEndLosCounterInt  Integer32,
    mepStatusLmFarEndLosCounterInt   Integer32,
    mepStatusLmNearEndLosThCnt       Unsigned32,
    mepStatusLmFarEndLosThCnt        Unsigned32,
    mepStatusLmNearEndLosRatioTot    Unsigned32,
    mepStatusLmFarEndLosRatioTot     Unsigned32,
    mepStatusLmNearEndLosRatioMin    Unsigned32,
    mepStatusLmFarEndLosRatioMin     Unsigned32,
    mepStatusLmNearEndLosRatioMax    Unsigned32,
    mepStatusLmFarEndLosRatioMax     Unsigned32,
    mepStatusLmIntervalElapsed       Unsigned32
}

mepStatusLmId OBJECT-TYPE
    SYNTAX      Integer32 (0..2147483647)
    MAX-ACCESS  not-accessible
    STATUS      current
    DESCRIPTION
        "The MEP instance ID"
    ::= { mepStatusLmEntry 1 }

mepStatusLmTxCounter OBJECT-TYPE
    SYNTAX      Unsigned32
    MAX-ACCESS  read-only
    STATUS      current
    DESCRIPTION
        "Transmitted PDU (LMM - CCM) containing counters."
    ::= { mepStatusLmEntry 2 }

mepStatusLmRxCounter OBJECT-TYPE
    SYNTAX      Unsigned32
    MAX-ACCESS  read-only
    STATUS      current
    DESCRIPTION
        "Received PDU (LMM - CCM) containing counters."
    ::= { mepStatusLmEntry 3 }

mepStatusLmNearEndLosCounterTot OBJECT-TYPE
    SYNTAX      Integer32
    MAX-ACCESS  read-only
    STATUS      current
    DESCRIPTION
        "Near end total frame loss counter."
    ::= { mepStatusLmEntry 4 }

mepStatusLmFarEndLosCounterTot OBJECT-TYPE
    SYNTAX      Integer32
    MAX-ACCESS  read-only
    STATUS      current
    DESCRIPTION
        "Far end total frame loss counter."
    ::= { mepStatusLmEntry 5 }

mepStatusLmNearEndLosRatioInt OBJECT-TYPE
    SYNTAX      Unsigned32
    MAX-ACCESS  read-only
    STATUS      current
    DESCRIPTION
        "Near end frame loss ratio for interval in per mille."
    ::= { mepStatusLmEntry 6 }

mepStatusLmFarEndLosRatioInt OBJECT-TYPE
    SYNTAX      Unsigned32
    MAX-ACCESS  read-only
    STATUS      current
    DESCRIPTION
        "Far end frame loss ratio for interval in per mille."
    ::= { mepStatusLmEntry 7 }

mepStatusLmNearEndLosCounterInt OBJECT-TYPE
    SYNTAX      Integer32
    MAX-ACCESS  read-only
    STATUS      current
    DESCRIPTION
        "Near end frame loss counter for interval."
    ::= { mepStatusLmEntry 8 }

mepStatusLmFarEndLosCounterInt OBJECT-TYPE
    SYNTAX      Integer32
    MAX-ACCESS  read-only
    STATUS      current
    DESCRIPTION
        "Far end frame loss counter for interval."
    ::= { mepStatusLmEntry 9 }

mepStatusLmNearEndLosThCnt OBJECT-TYPE
    SYNTAX      Unsigned32
    MAX-ACCESS  read-only
    STATUS      current
    DESCRIPTION
        "Near end frame loss threshold count."
    ::= { mepStatusLmEntry 10 }

mepStatusLmFarEndLosThCnt OBJECT-TYPE
    SYNTAX      Unsigned32
    MAX-ACCESS  read-only
    STATUS      current
    DESCRIPTION
        "Far end frame loss threshold count."
    ::= { mepStatusLmEntry 11 }

mepStatusLmNearEndLosRatioTot OBJECT-TYPE
    SYNTAX      Unsigned32
    MAX-ACCESS  read-only
    STATUS      current
    DESCRIPTION
        "Near end total frame loss ratio in per mille (average since last
         clear)."
    ::= { mepStatusLmEntry 12 }

mepStatusLmFarEndLosRatioTot OBJECT-TYPE
    SYNTAX      Unsigned32
    MAX-ACCESS  read-only
    STATUS      current
    DESCRIPTION
        "Far end total frame loss ratio in per mille (average since last clear)."
    ::= { mepStatusLmEntry 13 }

mepStatusLmNearEndLosRatioMin OBJECT-TYPE
    SYNTAX      Unsigned32
    MAX-ACCESS  read-only
    STATUS      current
    DESCRIPTION
        "Near end minimum frame loss ratio in per mille (since last clear)."
    ::= { mepStatusLmEntry 14 }

mepStatusLmFarEndLosRatioMin OBJECT-TYPE
    SYNTAX      Unsigned32
    MAX-ACCESS  read-only
    STATUS      current
    DESCRIPTION
        "Far end minimum frame loss ratio in per mille (since last clear)."
    ::= { mepStatusLmEntry 15 }

mepStatusLmNearEndLosRatioMax OBJECT-TYPE
    SYNTAX      Unsigned32
    MAX-ACCESS  read-only
    STATUS      current
    DESCRIPTION
        "Near end maximum frame loss ratio in per mille (since last clear)."
    ::= { mepStatusLmEntry 16 }

mepStatusLmFarEndLosRatioMax OBJECT-TYPE
    SYNTAX      Unsigned32
    MAX-ACCESS  read-only
    STATUS      current
    DESCRIPTION
        "Far end maximum frame loss ratio in per mille (since last clear)."
    ::= { mepStatusLmEntry 17 }

mepStatusLmIntervalElapsed OBJECT-TYPE
    SYNTAX      Unsigned32
    MAX-ACCESS  read-only
    STATUS      current
    DESCRIPTION
        "Elapsed intervals since last clear."
    ::= { mepStatusLmEntry 18 }

mepStatusLmPeerTable OBJECT-TYPE
    SYNTAX      SEQUENCE OF MepStatusLmPeerEntry
    MAX-ACCESS  not-accessible
    STATUS      current
    DESCRIPTION
        "This is a table of Peer Loss Measurement status"
    ::= { mepStatusLm 2 }

mepStatusLmPeerEntry OBJECT-TYPE
    SYNTAX      MepStatusLmPeerEntry
    MAX-ACCESS  not-accessible
    STATUS      current
    DESCRIPTION
        "This is a Loss Measurement status"
    INDEX       { mepStatusLmPeerId, mepStatusLmPeerPeerId }
    ::= { mepStatusLmPeerTable 1 }

MepStatusLmPeerEntry ::= SEQUENCE {
    mepStatusLmPeerId                    Integer32,
    mepStatusLmPeerPeerId                Integer32,
    mepStatusLmPeerTxCounter             Unsigned32,
    mepStatusLmPeerRxCounter             Unsigned32,
    mepStatusLmPeerNearEndLosCounterTot  Integer32,
    mepStatusLmPeerFarEndLosCounterTot   Integer32,
    mepStatusLmPeerNearEndLosRatioInt    Unsigned32,
    mepStatusLmPeerFarEndLosRatioInt     Unsigned32,
    mepStatusLmPeerNearEndLosCounterInt  Integer32,
    mepStatusLmPeerFarEndLosCounterInt   Integer32,
    mepStatusLmPeerNearEndLosThCnt       Unsigned32,
    mepStatusLmPeerFarEndLosThCnt        Unsigned32,
    mepStatusLmPeerNearEndLosRatioTot    Unsigned32,
    mepStatusLmPeerFarEndLosRatioTot     Unsigned32,
    mepStatusLmPeerNearEndLosRatioMin    Unsigned32,
    mepStatusLmPeerFarEndLosRatioMin     Unsigned32,
    mepStatusLmPeerNearEndLosRatioMax    Unsigned32,
    mepStatusLmPeerFarEndLosRatioMax     Unsigned32,
    mepStatusLmPeerIntervalElapsed       Unsigned32
}

mepStatusLmPeerId OBJECT-TYPE
    SYNTAX      Integer32 (0..2147483647)
    MAX-ACCESS  not-accessible
    STATUS      current
    DESCRIPTION
        "The MEP instance ID"
    ::= { mepStatusLmPeerEntry 1 }

mepStatusLmPeerPeerId OBJECT-TYPE
    SYNTAX      Integer32 (0..2147483647)
    MAX-ACCESS  not-accessible
    STATUS      current
    DESCRIPTION
        "The Peer MEP ID"
    ::= { mepStatusLmPeerEntry 2 }

mepStatusLmPeerTxCounter OBJECT-TYPE
    SYNTAX      Unsigned32
    MAX-ACCESS  read-only
    STATUS      current
    DESCRIPTION
        "Transmitted PDU (LMM - CCM) containing counters."
    ::= { mepStatusLmPeerEntry 3 }

mepStatusLmPeerRxCounter OBJECT-TYPE
    SYNTAX      Unsigned32
    MAX-ACCESS  read-only
    STATUS      current
    DESCRIPTION
        "Received PDU (LMM - CCM) containing counters."
    ::= { mepStatusLmPeerEntry 4 }

mepStatusLmPeerNearEndLosCounterTot OBJECT-TYPE
    SYNTAX      Integer32
    MAX-ACCESS  read-only
    STATUS      current
    DESCRIPTION
        "Near end total frame loss counter."
    ::= { mepStatusLmPeerEntry 5 }

mepStatusLmPeerFarEndLosCounterTot OBJECT-TYPE
    SYNTAX      Integer32
    MAX-ACCESS  read-only
    STATUS      current
    DESCRIPTION
        "Far end total frame loss counter."
    ::= { mepStatusLmPeerEntry 6 }

mepStatusLmPeerNearEndLosRatioInt OBJECT-TYPE
    SYNTAX      Unsigned32
    MAX-ACCESS  read-only
    STATUS      current
    DESCRIPTION
        "Near end frame loss ratio for interval in per mille."
    ::= { mepStatusLmPeerEntry 7 }

mepStatusLmPeerFarEndLosRatioInt OBJECT-TYPE
    SYNTAX      Unsigned32
    MAX-ACCESS  read-only
    STATUS      current
    DESCRIPTION
        "Far end frame loss ratio for interval in per mille."
    ::= { mepStatusLmPeerEntry 8 }

mepStatusLmPeerNearEndLosCounterInt OBJECT-TYPE
    SYNTAX      Integer32
    MAX-ACCESS  read-only
    STATUS      current
    DESCRIPTION
        "Near end frame loss counter for interval."
    ::= { mepStatusLmPeerEntry 9 }

mepStatusLmPeerFarEndLosCounterInt OBJECT-TYPE
    SYNTAX      Integer32
    MAX-ACCESS  read-only
    STATUS      current
    DESCRIPTION
        "Far end frame loss counter for interval."
    ::= { mepStatusLmPeerEntry 10 }

mepStatusLmPeerNearEndLosThCnt OBJECT-TYPE
    SYNTAX      Unsigned32
    MAX-ACCESS  read-only
    STATUS      current
    DESCRIPTION
        "Near end frame loss threshold count."
    ::= { mepStatusLmPeerEntry 11 }

mepStatusLmPeerFarEndLosThCnt OBJECT-TYPE
    SYNTAX      Unsigned32
    MAX-ACCESS  read-only
    STATUS      current
    DESCRIPTION
        "Far end frame loss threshold count."
    ::= { mepStatusLmPeerEntry 12 }

mepStatusLmPeerNearEndLosRatioTot OBJECT-TYPE
    SYNTAX      Unsigned32
    MAX-ACCESS  read-only
    STATUS      current
    DESCRIPTION
        "Near end total frame loss ratio in per mille (average since last
         clear)."
    ::= { mepStatusLmPeerEntry 13 }

mepStatusLmPeerFarEndLosRatioTot OBJECT-TYPE
    SYNTAX      Unsigned32
    MAX-ACCESS  read-only
    STATUS      current
    DESCRIPTION
        "Far end total frame loss ratio in per mille (average since last clear)."
    ::= { mepStatusLmPeerEntry 14 }

mepStatusLmPeerNearEndLosRatioMin OBJECT-TYPE
    SYNTAX      Unsigned32
    MAX-ACCESS  read-only
    STATUS      current
    DESCRIPTION
        "Near end minimum frame loss ratio in per mille (since last clear)."
    ::= { mepStatusLmPeerEntry 15 }

mepStatusLmPeerFarEndLosRatioMin OBJECT-TYPE
    SYNTAX      Unsigned32
    MAX-ACCESS  read-only
    STATUS      current
    DESCRIPTION
        "Far end minimum frame loss ratio in per mille (since last clear)."
    ::= { mepStatusLmPeerEntry 16 }

mepStatusLmPeerNearEndLosRatioMax OBJECT-TYPE
    SYNTAX      Unsigned32
    MAX-ACCESS  read-only
    STATUS      current
    DESCRIPTION
        "Near end maximum frame loss ratio in per mille (since last clear)."
    ::= { mepStatusLmPeerEntry 17 }

mepStatusLmPeerFarEndLosRatioMax OBJECT-TYPE
    SYNTAX      Unsigned32
    MAX-ACCESS  read-only
    STATUS      current
    DESCRIPTION
        "Far end maximum frame loss ratio in per mille (since last clear)."
    ::= { mepStatusLmPeerEntry 18 }

mepStatusLmPeerIntervalElapsed OBJECT-TYPE
    SYNTAX      Unsigned32
    MAX-ACCESS  read-only
    STATUS      current
    DESCRIPTION
        "Elapsed intervals since last clear."
    ::= { mepStatusLmPeerEntry 19 }

mepStatusDm OBJECT IDENTIFIER
    ::= { mepStatus 3 }

mepStatusDmTwoWayTable OBJECT-TYPE
    SYNTAX      SEQUENCE OF MepStatusDmTwoWayEntry
    MAX-ACCESS  not-accessible
    STATUS      current
    DESCRIPTION
        "This is a table of Delay Measurement Two Way status"
    ::= { mepStatusDm 1 }

mepStatusDmTwoWayEntry OBJECT-TYPE
    SYNTAX      MepStatusDmTwoWayEntry
    MAX-ACCESS  not-accessible
    STATUS      current
    DESCRIPTION
        "This is a Delay Measurement Two Way status"
    INDEX       { mepStatusDmTwoWayId }
    ::= { mepStatusDmTwoWayTable 1 }

MepStatusDmTwoWayEntry ::= SEQUENCE {
    mepStatusDmTwoWayId                          Integer32,
    mepStatusDmTwoWayTxCounter                   Unsigned32,
    mepStatusDmTwoWayRxCounter                   Unsigned32,
    mepStatusDmTwoWayRxTimeOutCounter            Unsigned32,
    mepStatusDmTwoWayRxErrorCounter              Unsigned32,
    mepStatusDmTwoWayInternalOverflowCounter     Unsigned32,
    mepStatusDmTwoWayAverageDelay                Unsigned32,
    mepStatusDmTwoWayAverageLastnDelay           Unsigned32,
    mepStatusDmTwoWayAverageDelayVariation       Unsigned32,
    mepStatusDmTwoWayAverageLastnDelayVariation  Unsigned32,
    mepStatusDmTwoWayMinimumDelay                Unsigned32,
    mepStatusDmTwoWayMaximumDelay                Unsigned32,
    mepStatusDmTwoWayMinimumDelayVariation       Unsigned32,
    mepStatusDmTwoWayMaximumDelayVariation       Unsigned32,
    mepStatusDmTwoWayTimeUnit                    MepDmTimeUnit
}

mepStatusDmTwoWayId OBJECT-TYPE
    SYNTAX      Integer32 (0..2147483647)
    MAX-ACCESS  not-accessible
    STATUS      current
    DESCRIPTION
        "The MEP instance ID"
    ::= { mepStatusDmTwoWayEntry 1 }

mepStatusDmTwoWayTxCounter OBJECT-TYPE
    SYNTAX      Unsigned32
    MAX-ACCESS  read-only
    STATUS      current
    DESCRIPTION
        "Transmitted DMM/1DM frames."
    ::= { mepStatusDmTwoWayEntry 2 }

mepStatusDmTwoWayRxCounter OBJECT-TYPE
    SYNTAX      Unsigned32
    MAX-ACCESS  read-only
    STATUS      current
    DESCRIPTION
        "Received DMM/1DM frames."
    ::= { mepStatusDmTwoWayEntry 3 }

mepStatusDmTwoWayRxTimeOutCounter OBJECT-TYPE
    SYNTAX      Unsigned32
    MAX-ACCESS  read-only
    STATUS      current
    DESCRIPTION
        "Received DMR time-out. After transmission of DMM, the DMR is expected
         to be received within 1 sec."
    ::= { mepStatusDmTwoWayEntry 4 }

mepStatusDmTwoWayRxErrorCounter OBJECT-TYPE
    SYNTAX      Unsigned32
    MAX-ACCESS  read-only
    STATUS      current
    DESCRIPTION
        "Received error counter. It is considered an error if a delay is
         negative or above 1 sec."
    ::= { mepStatusDmTwoWayEntry 5 }

mepStatusDmTwoWayInternalOverflowCounter OBJECT-TYPE
    SYNTAX      Unsigned32
    MAX-ACCESS  read-only
    STATUS      current
    DESCRIPTION
        "The internal total delay counter overflow counter."
    ::= { mepStatusDmTwoWayEntry 6 }

mepStatusDmTwoWayAverageDelay OBJECT-TYPE
    SYNTAX      Unsigned32
    MAX-ACCESS  read-only
    STATUS      current
    DESCRIPTION
        "The total average delay."
    ::= { mepStatusDmTwoWayEntry 7 }

mepStatusDmTwoWayAverageLastnDelay OBJECT-TYPE
    SYNTAX      Unsigned32
    MAX-ACCESS  read-only
    STATUS      current
    DESCRIPTION
        "The last N average delay."
    ::= { mepStatusDmTwoWayEntry 8 }

mepStatusDmTwoWayAverageDelayVariation OBJECT-TYPE
    SYNTAX      Unsigned32
    MAX-ACCESS  read-only
    STATUS      current
    DESCRIPTION
        "The total average delay variation."
    ::= { mepStatusDmTwoWayEntry 9 }

mepStatusDmTwoWayAverageLastnDelayVariation OBJECT-TYPE
    SYNTAX      Unsigned32
    MAX-ACCESS  read-only
    STATUS      current
    DESCRIPTION
        "The last N average delay variation."
    ::= { mepStatusDmTwoWayEntry 10 }

mepStatusDmTwoWayMinimumDelay OBJECT-TYPE
    SYNTAX      Unsigned32
    MAX-ACCESS  read-only
    STATUS      current
    DESCRIPTION
        "The minimum delay measured."
    ::= { mepStatusDmTwoWayEntry 11 }

mepStatusDmTwoWayMaximumDelay OBJECT-TYPE
    SYNTAX      Unsigned32
    MAX-ACCESS  read-only
    STATUS      current
    DESCRIPTION
        "The maximum delay measured."
    ::= { mepStatusDmTwoWayEntry 12 }

mepStatusDmTwoWayMinimumDelayVariation OBJECT-TYPE
    SYNTAX      Unsigned32
    MAX-ACCESS  read-only
    STATUS      current
    DESCRIPTION
        "The minimum delay variation measured."
    ::= { mepStatusDmTwoWayEntry 13 }

mepStatusDmTwoWayMaximumDelayVariation OBJECT-TYPE
    SYNTAX      Unsigned32
    MAX-ACCESS  read-only
    STATUS      current
    DESCRIPTION
        "The maximum delay variation measured."
    ::= { mepStatusDmTwoWayEntry 14 }

mepStatusDmTwoWayTimeUnit OBJECT-TYPE
    SYNTAX      MepDmTimeUnit
    MAX-ACCESS  read-only
    STATUS      current
    DESCRIPTION
        "Calculation time unit."
    ::= { mepStatusDmTwoWayEntry 15 }

mepStatusDmOneWayFarNearTable OBJECT-TYPE
    SYNTAX      SEQUENCE OF MepStatusDmOneWayFarNearEntry
    MAX-ACCESS  not-accessible
    STATUS      current
    DESCRIPTION
        "This is a table of Delay Measurement One Way Far to Near status"
    ::= { mepStatusDm 2 }

mepStatusDmOneWayFarNearEntry OBJECT-TYPE
    SYNTAX      MepStatusDmOneWayFarNearEntry
    MAX-ACCESS  not-accessible
    STATUS      current
    DESCRIPTION
        "This is a Delay Measurement Two Way Far to Near status"
    INDEX       { mepStatusDmOneWayFarNearId }
    ::= { mepStatusDmOneWayFarNearTable 1 }

MepStatusDmOneWayFarNearEntry ::= SEQUENCE {
    mepStatusDmOneWayFarNearId                          Integer32,
    mepStatusDmOneWayFarNearTxCounter                   Unsigned32,
    mepStatusDmOneWayFarNearRxCounter                   Unsigned32,
    mepStatusDmOneWayFarNearRxTimeOutCounter            Unsigned32,
    mepStatusDmOneWayFarNearRxErrorCounter              Unsigned32,
    mepStatusDmOneWayFarNearInternalOverflowCounter     Unsigned32,
    mepStatusDmOneWayFarNearAverageDelay                Unsigned32,
    mepStatusDmOneWayFarNearAverageLastnDelay           Unsigned32,
    mepStatusDmOneWayFarNearAverageDelayVariation       Unsigned32,
    mepStatusDmOneWayFarNearAverageLastnDelayVariation  Unsigned32,
    mepStatusDmOneWayFarNearMinimumDelay                Unsigned32,
    mepStatusDmOneWayFarNearMaximumDelay                Unsigned32,
    mepStatusDmOneWayFarNearMinimumDelayVariation       Unsigned32,
    mepStatusDmOneWayFarNearMaximumDelayVariation       Unsigned32,
    mepStatusDmOneWayFarNearTimeUnit                    MepDmTimeUnit
}

mepStatusDmOneWayFarNearId OBJECT-TYPE
    SYNTAX      Integer32 (0..2147483647)
    MAX-ACCESS  not-accessible
    STATUS      current
    DESCRIPTION
        "The MEP instance ID"
    ::= { mepStatusDmOneWayFarNearEntry 1 }

mepStatusDmOneWayFarNearTxCounter OBJECT-TYPE
    SYNTAX      Unsigned32
    MAX-ACCESS  read-only
    STATUS      current
    DESCRIPTION
        "Transmitted DMM/1DM frames."
    ::= { mepStatusDmOneWayFarNearEntry 2 }

mepStatusDmOneWayFarNearRxCounter OBJECT-TYPE
    SYNTAX      Unsigned32
    MAX-ACCESS  read-only
    STATUS      current
    DESCRIPTION
        "Received DMM/1DM frames."
    ::= { mepStatusDmOneWayFarNearEntry 3 }

mepStatusDmOneWayFarNearRxTimeOutCounter OBJECT-TYPE
    SYNTAX      Unsigned32
    MAX-ACCESS  read-only
    STATUS      current
    DESCRIPTION
        "Received DMR time-out. After transmission of DMM, the DMR is expected
         to be received within 1 sec."
    ::= { mepStatusDmOneWayFarNearEntry 4 }

mepStatusDmOneWayFarNearRxErrorCounter OBJECT-TYPE
    SYNTAX      Unsigned32
    MAX-ACCESS  read-only
    STATUS      current
    DESCRIPTION
        "Received error counter. It is considered an error if a delay is
         negative or above 1 sec."
    ::= { mepStatusDmOneWayFarNearEntry 5 }

mepStatusDmOneWayFarNearInternalOverflowCounter OBJECT-TYPE
    SYNTAX      Unsigned32
    MAX-ACCESS  read-only
    STATUS      current
    DESCRIPTION
        "The internal total delay counter overflow counter."
    ::= { mepStatusDmOneWayFarNearEntry 6 }

mepStatusDmOneWayFarNearAverageDelay OBJECT-TYPE
    SYNTAX      Unsigned32
    MAX-ACCESS  read-only
    STATUS      current
    DESCRIPTION
        "The total average delay."
    ::= { mepStatusDmOneWayFarNearEntry 7 }

mepStatusDmOneWayFarNearAverageLastnDelay OBJECT-TYPE
    SYNTAX      Unsigned32
    MAX-ACCESS  read-only
    STATUS      current
    DESCRIPTION
        "The last N average delay."
    ::= { mepStatusDmOneWayFarNearEntry 8 }

mepStatusDmOneWayFarNearAverageDelayVariation OBJECT-TYPE
    SYNTAX      Unsigned32
    MAX-ACCESS  read-only
    STATUS      current
    DESCRIPTION
        "The total average delay variation."
    ::= { mepStatusDmOneWayFarNearEntry 9 }

mepStatusDmOneWayFarNearAverageLastnDelayVariation OBJECT-TYPE
    SYNTAX      Unsigned32
    MAX-ACCESS  read-only
    STATUS      current
    DESCRIPTION
        "The last N average delay variation."
    ::= { mepStatusDmOneWayFarNearEntry 10 }

mepStatusDmOneWayFarNearMinimumDelay OBJECT-TYPE
    SYNTAX      Unsigned32
    MAX-ACCESS  read-only
    STATUS      current
    DESCRIPTION
        "The minimum delay measured."
    ::= { mepStatusDmOneWayFarNearEntry 11 }

mepStatusDmOneWayFarNearMaximumDelay OBJECT-TYPE
    SYNTAX      Unsigned32
    MAX-ACCESS  read-only
    STATUS      current
    DESCRIPTION
        "The maximum delay measured."
    ::= { mepStatusDmOneWayFarNearEntry 12 }

mepStatusDmOneWayFarNearMinimumDelayVariation OBJECT-TYPE
    SYNTAX      Unsigned32
    MAX-ACCESS  read-only
    STATUS      current
    DESCRIPTION
        "The minimum delay variation measured."
    ::= { mepStatusDmOneWayFarNearEntry 13 }

mepStatusDmOneWayFarNearMaximumDelayVariation OBJECT-TYPE
    SYNTAX      Unsigned32
    MAX-ACCESS  read-only
    STATUS      current
    DESCRIPTION
        "The maximum delay variation measured."
    ::= { mepStatusDmOneWayFarNearEntry 14 }

mepStatusDmOneWayFarNearTimeUnit OBJECT-TYPE
    SYNTAX      MepDmTimeUnit
    MAX-ACCESS  read-only
    STATUS      current
    DESCRIPTION
        "Calculation time unit."
    ::= { mepStatusDmOneWayFarNearEntry 15 }

mepStatusDmOneWayNearFarTable OBJECT-TYPE
    SYNTAX      SEQUENCE OF MepStatusDmOneWayNearFarEntry
    MAX-ACCESS  not-accessible
    STATUS      current
    DESCRIPTION
        "This is a table of Delay Measurement One Way Near to Far status"
    ::= { mepStatusDm 3 }

mepStatusDmOneWayNearFarEntry OBJECT-TYPE
    SYNTAX      MepStatusDmOneWayNearFarEntry
    MAX-ACCESS  not-accessible
    STATUS      current
    DESCRIPTION
        "This is a Delay Measurement Two Way Near to Far status"
    INDEX       { mepStatusDmOneWayNearFarId }
    ::= { mepStatusDmOneWayNearFarTable 1 }

MepStatusDmOneWayNearFarEntry ::= SEQUENCE {
    mepStatusDmOneWayNearFarId                          Integer32,
    mepStatusDmOneWayNearFarTxCounter                   Unsigned32,
    mepStatusDmOneWayNearFarRxCounter                   Unsigned32,
    mepStatusDmOneWayNearFarRxTimeOutCounter            Unsigned32,
    mepStatusDmOneWayNearFarRxErrorCounter              Unsigned32,
    mepStatusDmOneWayNearFarInternalOverflowCounter     Unsigned32,
    mepStatusDmOneWayNearFarAverageDelay                Unsigned32,
    mepStatusDmOneWayNearFarAverageLastnDelay           Unsigned32,
    mepStatusDmOneWayNearFarAverageDelayVariation       Unsigned32,
    mepStatusDmOneWayNearFarAverageLastnDelayVariation  Unsigned32,
    mepStatusDmOneWayNearFarMinimumDelay                Unsigned32,
    mepStatusDmOneWayNearFarMaximumDelay                Unsigned32,
    mepStatusDmOneWayNearFarMinimumDelayVariation       Unsigned32,
    mepStatusDmOneWayNearFarMaximumDelayVariation       Unsigned32,
    mepStatusDmOneWayNearFarTimeUnit                    MepDmTimeUnit
}

mepStatusDmOneWayNearFarId OBJECT-TYPE
    SYNTAX      Integer32 (0..2147483647)
    MAX-ACCESS  not-accessible
    STATUS      current
    DESCRIPTION
        "The MEP instance ID"
    ::= { mepStatusDmOneWayNearFarEntry 1 }

mepStatusDmOneWayNearFarTxCounter OBJECT-TYPE
    SYNTAX      Unsigned32
    MAX-ACCESS  read-only
    STATUS      current
    DESCRIPTION
        "Transmitted DMM/1DM frames."
    ::= { mepStatusDmOneWayNearFarEntry 2 }

mepStatusDmOneWayNearFarRxCounter OBJECT-TYPE
    SYNTAX      Unsigned32
    MAX-ACCESS  read-only
    STATUS      current
    DESCRIPTION
        "Received DMM/1DM frames."
    ::= { mepStatusDmOneWayNearFarEntry 3 }

mepStatusDmOneWayNearFarRxTimeOutCounter OBJECT-TYPE
    SYNTAX      Unsigned32
    MAX-ACCESS  read-only
    STATUS      current
    DESCRIPTION
        "Received DMR time-out. After transmission of DMM, the DMR is expected
         to be received within 1 sec."
    ::= { mepStatusDmOneWayNearFarEntry 4 }

mepStatusDmOneWayNearFarRxErrorCounter OBJECT-TYPE
    SYNTAX      Unsigned32
    MAX-ACCESS  read-only
    STATUS      current
    DESCRIPTION
        "Received error counter. It is considered an error if a delay is
         negative or above 1 sec."
    ::= { mepStatusDmOneWayNearFarEntry 5 }

mepStatusDmOneWayNearFarInternalOverflowCounter OBJECT-TYPE
    SYNTAX      Unsigned32
    MAX-ACCESS  read-only
    STATUS      current
    DESCRIPTION
        "The internal total delay counter overflow counter."
    ::= { mepStatusDmOneWayNearFarEntry 6 }

mepStatusDmOneWayNearFarAverageDelay OBJECT-TYPE
    SYNTAX      Unsigned32
    MAX-ACCESS  read-only
    STATUS      current
    DESCRIPTION
        "The total average delay."
    ::= { mepStatusDmOneWayNearFarEntry 7 }

mepStatusDmOneWayNearFarAverageLastnDelay OBJECT-TYPE
    SYNTAX      Unsigned32
    MAX-ACCESS  read-only
    STATUS      current
    DESCRIPTION
        "The last N average delay."
    ::= { mepStatusDmOneWayNearFarEntry 8 }

mepStatusDmOneWayNearFarAverageDelayVariation OBJECT-TYPE
    SYNTAX      Unsigned32
    MAX-ACCESS  read-only
    STATUS      current
    DESCRIPTION
        "The total average delay variation."
    ::= { mepStatusDmOneWayNearFarEntry 9 }

mepStatusDmOneWayNearFarAverageLastnDelayVariation OBJECT-TYPE
    SYNTAX      Unsigned32
    MAX-ACCESS  read-only
    STATUS      current
    DESCRIPTION
        "The last N average delay variation."
    ::= { mepStatusDmOneWayNearFarEntry 10 }

mepStatusDmOneWayNearFarMinimumDelay OBJECT-TYPE
    SYNTAX      Unsigned32
    MAX-ACCESS  read-only
    STATUS      current
    DESCRIPTION
        "The minimum delay measured."
    ::= { mepStatusDmOneWayNearFarEntry 11 }

mepStatusDmOneWayNearFarMaximumDelay OBJECT-TYPE
    SYNTAX      Unsigned32
    MAX-ACCESS  read-only
    STATUS      current
    DESCRIPTION
        "The maximum delay measured."
    ::= { mepStatusDmOneWayNearFarEntry 12 }

mepStatusDmOneWayNearFarMinimumDelayVariation OBJECT-TYPE
    SYNTAX      Unsigned32
    MAX-ACCESS  read-only
    STATUS      current
    DESCRIPTION
        "The minimum delay variation measured."
    ::= { mepStatusDmOneWayNearFarEntry 13 }

mepStatusDmOneWayNearFarMaximumDelayVariation OBJECT-TYPE
    SYNTAX      Unsigned32
    MAX-ACCESS  read-only
    STATUS      current
    DESCRIPTION
        "The maximum delay variation measured."
    ::= { mepStatusDmOneWayNearFarEntry 14 }

mepStatusDmOneWayNearFarTimeUnit OBJECT-TYPE
    SYNTAX      MepDmTimeUnit
    MAX-ACCESS  read-only
    STATUS      current
    DESCRIPTION
        "Calculation time unit."
    ::= { mepStatusDmOneWayNearFarEntry 15 }

mepStatusLb OBJECT IDENTIFIER
    ::= { mepStatus 4 }

mepStatusLbTable OBJECT-TYPE
    SYNTAX      SEQUENCE OF MepStatusLbEntry
    MAX-ACCESS  not-accessible
    STATUS      current
    DESCRIPTION
        "This is a table of Loop Back status"
    ::= { mepStatusLb 1 }

mepStatusLbEntry OBJECT-TYPE
    SYNTAX      MepStatusLbEntry
    MAX-ACCESS  not-accessible
    STATUS      current
    DESCRIPTION
        "This is a Loop Back status"
    INDEX       { mepStatusLbId }
    ::= { mepStatusLbTable 1 }

MepStatusLbEntry ::= SEQUENCE {
    mepStatusLbId              Integer32,
    mepStatusLbTransactionId   Unsigned32,
    mepStatusLbReplyCounter    Unsigned32,
    mepStatusLbLbmTransmitted  Counter64
}

mepStatusLbId OBJECT-TYPE
    SYNTAX      Integer32 (0..2147483647)
    MAX-ACCESS  not-accessible
    STATUS      current
    DESCRIPTION
        "The MEP instance ID"
    ::= { mepStatusLbEntry 1 }

mepStatusLbTransactionId OBJECT-TYPE
    SYNTAX      Unsigned32
    MAX-ACCESS  read-only
    STATUS      current
    DESCRIPTION
        "This is the transaction id that is used to send the next LBM."
    ::= { mepStatusLbEntry 2 }

mepStatusLbReplyCounter OBJECT-TYPE
    SYNTAX      Unsigned32
    MAX-ACCESS  read-only
    STATUS      current
    DESCRIPTION
        "The number of replying MAC. In case of 'infinite' LBM there is only one
         reply."
    ::= { mepStatusLbEntry 3 }

mepStatusLbLbmTransmitted OBJECT-TYPE
    SYNTAX      Counter64
    MAX-ACCESS  read-only
    STATUS      current
    DESCRIPTION
        "The number of transmitted LBM."
    ::= { mepStatusLbEntry 4 }

mepStatusLbReplyTable OBJECT-TYPE
    SYNTAX      SEQUENCE OF MepStatusLbReplyEntry
    MAX-ACCESS  not-accessible
    STATUS      current
    DESCRIPTION
        "This is a table of Loop Back reply status"
    ::= { mepStatusLb 2 }

mepStatusLbReplyEntry OBJECT-TYPE
    SYNTAX      MepStatusLbReplyEntry
    MAX-ACCESS  not-accessible
    STATUS      current
    DESCRIPTION
        "This is a Loop Back reply status"
    INDEX       { mepStatusLbReplyId, mepStatusLbReplyReplyId }
    ::= { mepStatusLbReplyTable 1 }

MepStatusLbReplyEntry ::= SEQUENCE {
    mepStatusLbReplyId           Integer32,
    mepStatusLbReplyReplyId      Integer32,
    mepStatusLbReplyMac          MacAddress,
    mepStatusLbReplyLbrReceived  Counter64,
    mepStatusLbReplyOutOfOrder   Counter64,
    mepStatusLbReplyMepMipId     OCTET STRING
}

mepStatusLbReplyId OBJECT-TYPE
    SYNTAX      Integer32 (0..2147483647)
    MAX-ACCESS  not-accessible
    STATUS      current
    DESCRIPTION
        "The MEP instance ID"
    ::= { mepStatusLbReplyEntry 1 }

mepStatusLbReplyReplyId OBJECT-TYPE
    SYNTAX      Integer32 (0..2147483647)
    MAX-ACCESS  not-accessible
    STATUS      current
    DESCRIPTION
        "The LB or LT Reply id"
    ::= { mepStatusLbReplyEntry 2 }

mepStatusLbReplyMac OBJECT-TYPE
    SYNTAX      MacAddress
    MAX-ACCESS  read-only
    STATUS      current
    DESCRIPTION
        "LBR source MAC - this is only relevant if not 'infinite' LBM and not
         MPLS loopback"
    ::= { mepStatusLbReplyEntry 3 }

mepStatusLbReplyLbrReceived OBJECT-TYPE
    SYNTAX      Counter64
    MAX-ACCESS  read-only
    STATUS      current
    DESCRIPTION
        "Number LBR received from MAC."
    ::= { mepStatusLbReplyEntry 4 }

mepStatusLbReplyOutOfOrder OBJECT-TYPE
    SYNTAX      Counter64
    MAX-ACCESS  read-only
    STATUS      current
    DESCRIPTION
        "The OOO counter."
    ::= { mepStatusLbReplyEntry 5 }

mepStatusLbReplyMepMipId OBJECT-TYPE
    SYNTAX      OCTET STRING (SIZE(16))
    MAX-ACCESS  read-only
    STATUS      current
    DESCRIPTION
        "Replying MEP/MIP ID - only relevant for loopback on MPLS"
    ::= { mepStatusLbReplyEntry 6 }

mepStatusTst OBJECT IDENTIFIER
    ::= { mepStatus 5 }

mepStatusTstTable OBJECT-TYPE
    SYNTAX      SEQUENCE OF MepStatusTstEntry
    MAX-ACCESS  not-accessible
    STATUS      current
    DESCRIPTION
        "This is a table of Test Signal status"
    ::= { mepStatusTst 1 }

mepStatusTstEntry OBJECT-TYPE
    SYNTAX      MepStatusTstEntry
    MAX-ACCESS  not-accessible
    STATUS      current
    DESCRIPTION
        "This is a Test Signal status"
    INDEX       { mepStatusTstId }
    ::= { mepStatusTstTable 1 }

MepStatusTstEntry ::= SEQUENCE {
    mepStatusTstId                 Integer32,
    mepStatusTstTxCounter          Counter64,
    mepStatusTstRxCounter          Counter64,
    mepStatusTstOutOfOrderCounter  Counter64,
    mepStatusTstRxRate             Unsigned32,
    mepStatusTstTestTime           Unsigned32
}

mepStatusTstId OBJECT-TYPE
    SYNTAX      Integer32 (0..2147483647)
    MAX-ACCESS  not-accessible
    STATUS      current
    DESCRIPTION
        "The MEP instance ID"
    ::= { mepStatusTstEntry 1 }

mepStatusTstTxCounter OBJECT-TYPE
    SYNTAX      Counter64
    MAX-ACCESS  read-only
    STATUS      current
    DESCRIPTION
        "Transmitted TST frames counter."
    ::= { mepStatusTstEntry 2 }

mepStatusTstRxCounter OBJECT-TYPE
    SYNTAX      Counter64
    MAX-ACCESS  read-only
    STATUS      current
    DESCRIPTION
        "REceived TST frames counter."
    ::= { mepStatusTstEntry 3 }

mepStatusTstOutOfOrderCounter OBJECT-TYPE
    SYNTAX      Counter64
    MAX-ACCESS  read-only
    STATUS      current
    DESCRIPTION
        "Out of Order counter."
    ::= { mepStatusTstEntry 4 }

mepStatusTstRxRate OBJECT-TYPE
    SYNTAX      Unsigned32
    MAX-ACCESS  read-only
    STATUS      current
    DESCRIPTION
        "Receive bit rate in Kbit/s."
    ::= { mepStatusTstEntry 5 }

mepStatusTstTestTime OBJECT-TYPE
    SYNTAX      Unsigned32
    MAX-ACCESS  read-only
    STATUS      current
    DESCRIPTION
        "Test time in seconds. The elapsed time since last clear."
    ::= { mepStatusTstEntry 6 }

mepStatusLt OBJECT IDENTIFIER
    ::= { mepStatus 6 }

mepStatusLtTable OBJECT-TYPE
    SYNTAX      SEQUENCE OF MepStatusLtEntry
    MAX-ACCESS  not-accessible
    STATUS      current
    DESCRIPTION
        "This is a table of Link Trace status"
    ::= { mepStatusLt 1 }

mepStatusLtEntry OBJECT-TYPE
    SYNTAX      MepStatusLtEntry
    MAX-ACCESS  not-accessible
    STATUS      current
    DESCRIPTION
        "This is a Link Trace status"
    INDEX       { mepStatusLtId }
    ::= { mepStatusLtTable 1 }

MepStatusLtEntry ::= SEQUENCE {
    mepStatusLtId             Integer32,
    mepStatusLtTransactionId  Unsigned32,
    mepStatusLtReplyCount     Unsigned32
}

mepStatusLtId OBJECT-TYPE
    SYNTAX      Integer32 (0..2147483647)
    MAX-ACCESS  not-accessible
    STATUS      current
    DESCRIPTION
        "The MEP instance ID"
    ::= { mepStatusLtEntry 1 }

mepStatusLtTransactionId OBJECT-TYPE
    SYNTAX      Unsigned32
    MAX-ACCESS  read-only
    STATUS      current
    DESCRIPTION
        "The transaction id of the latest Link Trace."
    ::= { mepStatusLtEntry 2 }

mepStatusLtReplyCount OBJECT-TYPE
    SYNTAX      Unsigned32
    MAX-ACCESS  read-only
    STATUS      current
    DESCRIPTION
        "Number of replies for this Link Trace transaction."
    ::= { mepStatusLtEntry 3 }

mepStatusLtReplyTable OBJECT-TYPE
    SYNTAX      SEQUENCE OF MepStatusLtReplyEntry
    MAX-ACCESS  not-accessible
    STATUS      current
    DESCRIPTION
        "This is a table of Link Trace reply status"
    ::= { mepStatusLt 2 }

mepStatusLtReplyEntry OBJECT-TYPE
    SYNTAX      MepStatusLtReplyEntry
    MAX-ACCESS  not-accessible
    STATUS      current
    DESCRIPTION
        "This is a Link Trace reply status"
    INDEX       { mepStatusLtReplyId, mepStatusLtReplyReplyId }
    ::= { mepStatusLtReplyTable 1 }

MepStatusLtReplyEntry ::= SEQUENCE {
    mepStatusLtReplyId             Integer32,
    mepStatusLtReplyReplyId        Integer32,
    mepStatusLtReplyMode           MepInstanceMode,
    mepStatusLtReplyDirection      MepInstanceDirection,
    mepStatusLtReplyTtl            Unsigned8,
    mepStatusLtReplyForwarded      TruthValue,
    mepStatusLtReplyRelayAction    MepLtRelayAction,
    mepStatusLtReplyLastEgressMac  MacAddress,
    mepStatusLtReplyNextEgressMac  MacAddress
}

mepStatusLtReplyId OBJECT-TYPE
    SYNTAX      Integer32 (0..2147483647)
    MAX-ACCESS  not-accessible
    STATUS      current
    DESCRIPTION
        "The MEP instance ID"
    ::= { mepStatusLtReplyEntry 1 }

mepStatusLtReplyReplyId OBJECT-TYPE
    SYNTAX      Integer32 (0..2147483647)
    MAX-ACCESS  not-accessible
    STATUS      current
    DESCRIPTION
        "The LB or LT Reply id"
    ::= { mepStatusLtReplyEntry 2 }

mepStatusLtReplyMode OBJECT-TYPE
    SYNTAX      MepInstanceMode
    MAX-ACCESS  read-only
    STATUS      current
    DESCRIPTION
        "The reply is done by a MEP or a MIP."
    ::= { mepStatusLtReplyEntry 3 }

mepStatusLtReplyDirection OBJECT-TYPE
    SYNTAX      MepInstanceDirection
    MAX-ACCESS  read-only
    STATUS      current
    DESCRIPTION
        "The reply is done by a UP or a Down instance."
    ::= { mepStatusLtReplyEntry 4 }

mepStatusLtReplyTtl OBJECT-TYPE
    SYNTAX      Unsigned8
    MAX-ACCESS  read-only
    STATUS      current
    DESCRIPTION
        "The reply TTL value."
    ::= { mepStatusLtReplyEntry 5 }

mepStatusLtReplyForwarded OBJECT-TYPE
    SYNTAX      TruthValue
    MAX-ACCESS  read-only
    STATUS      current
    DESCRIPTION
        "The LTM was forwarded."
    ::= { mepStatusLtReplyEntry 6 }

mepStatusLtReplyRelayAction OBJECT-TYPE
    SYNTAX      MepLtRelayAction
    MAX-ACCESS  read-only
    STATUS      current
    DESCRIPTION
        "The relay action."
    ::= { mepStatusLtReplyEntry 7 }

mepStatusLtReplyLastEgressMac OBJECT-TYPE
    SYNTAX      MacAddress
    MAX-ACCESS  read-only
    STATUS      current
    DESCRIPTION
        "The Last Egress MAC for this reply."
    ::= { mepStatusLtReplyEntry 8 }

mepStatusLtReplyNextEgressMac OBJECT-TYPE
    SYNTAX      MacAddress
    MAX-ACCESS  read-only
    STATUS      current
    DESCRIPTION
        "The Next Egress MAC of this reply."
    ::= { mepStatusLtReplyEntry 9 }

mepStatusCc OBJECT IDENTIFIER
    ::= { mepStatus 7 }

mepStatusCcPeerTable OBJECT-TYPE
    SYNTAX      SEQUENCE OF MepStatusCcPeerEntry
    MAX-ACCESS  not-accessible
    STATUS      current
    DESCRIPTION
        "This is a table of peer MEP CC status"
    ::= { mepStatusCc 2 }

mepStatusCcPeerEntry OBJECT-TYPE
    SYNTAX      MepStatusCcPeerEntry
    MAX-ACCESS  not-accessible
    STATUS      current
    DESCRIPTION
        "This is a peer MEP CC status"
    INDEX       { mepStatusCcPeerId, mepStatusCcPeerPeerId }
    ::= { mepStatusCcPeerTable 1 }

MepStatusCcPeerEntry ::= SEQUENCE {
    mepStatusCcPeerId              Integer32,
    mepStatusCcPeerPeerId          Integer32,
    mepStatusCcPeerOsTlvOuiFirst   Unsigned8,
    mepStatusCcPeerOsTlvOuiSecond  Unsigned8,
    mepStatusCcPeerOsTlvOuiThird   Unsigned8,
    mepStatusCcPeerOsTlvSubType    Unsigned8,
    mepStatusCcPeerOsTlvValue      Unsigned8,
    mepStatusCcPeerIsTlvValue      Unsigned8,
    mepStatusCcPeerPsTlvValue      Unsigned8,
    mepStatusCcPeerOsTlvReceived   TruthValue,
    mepStatusCcPeerIsTlvReceived   TruthValue,
    mepStatusCcPeerPsTlvReceived   TruthValue
}

mepStatusCcPeerId OBJECT-TYPE
    SYNTAX      Integer32 (0..2147483647)
    MAX-ACCESS  not-accessible
    STATUS      current
    DESCRIPTION
        "The MEP instance ID"
    ::= { mepStatusCcPeerEntry 1 }

mepStatusCcPeerPeerId OBJECT-TYPE
    SYNTAX      Integer32 (0..2147483647)
    MAX-ACCESS  not-accessible
    STATUS      current
    DESCRIPTION
        "The Peer MEP ID"
    ::= { mepStatusCcPeerEntry 2 }

mepStatusCcPeerOsTlvOuiFirst OBJECT-TYPE
    SYNTAX      Unsigned8
    MAX-ACCESS  read-only
    STATUS      current
    DESCRIPTION
        "Last received OS TLV - The OUI content first nibble"
    ::= { mepStatusCcPeerEntry 3 }

mepStatusCcPeerOsTlvOuiSecond OBJECT-TYPE
    SYNTAX      Unsigned8
    MAX-ACCESS  read-only
    STATUS      current
    DESCRIPTION
        "Last received OS TLV - The OUI content second nibble"
    ::= { mepStatusCcPeerEntry 4 }

mepStatusCcPeerOsTlvOuiThird OBJECT-TYPE
    SYNTAX      Unsigned8
    MAX-ACCESS  read-only
    STATUS      current
    DESCRIPTION
        "Last received OS TLV - The OUI content third nibble"
    ::= { mepStatusCcPeerEntry 5 }

mepStatusCcPeerOsTlvSubType OBJECT-TYPE
    SYNTAX      Unsigned8
    MAX-ACCESS  read-only
    STATUS      current
    DESCRIPTION
        "Last received OS TLV - The Sub-Type content"
    ::= { mepStatusCcPeerEntry 6 }

mepStatusCcPeerOsTlvValue OBJECT-TYPE
    SYNTAX      Unsigned8
    MAX-ACCESS  read-only
    STATUS      current
    DESCRIPTION
        "Last received OS TLV - The Value content"
    ::= { mepStatusCcPeerEntry 7 }

mepStatusCcPeerIsTlvValue OBJECT-TYPE
    SYNTAX      Unsigned8
    MAX-ACCESS  read-only
    STATUS      current
    DESCRIPTION
        "Last received IS TLV - The Value content"
    ::= { mepStatusCcPeerEntry 8 }

mepStatusCcPeerPsTlvValue OBJECT-TYPE
    SYNTAX      Unsigned8
    MAX-ACCESS  read-only
    STATUS      current
    DESCRIPTION
        "Last received PS TLV - The Value content"
    ::= { mepStatusCcPeerEntry 9 }

mepStatusCcPeerOsTlvReceived OBJECT-TYPE
    SYNTAX      TruthValue
    MAX-ACCESS  read-only
    STATUS      current
    DESCRIPTION
        "Last received CCM PDU contained OS TLV"
    ::= { mepStatusCcPeerEntry 10 }

mepStatusCcPeerIsTlvReceived OBJECT-TYPE
    SYNTAX      TruthValue
    MAX-ACCESS  read-only
    STATUS      current
    DESCRIPTION
        "Last received CCM PDU contained IS TLV"
    ::= { mepStatusCcPeerEntry 11 }

mepStatusCcPeerPsTlvReceived OBJECT-TYPE
    SYNTAX      TruthValue
    MAX-ACCESS  read-only
    STATUS      current
    DESCRIPTION
        "Last received CCM PDU contained PS TLV"
    ::= { mepStatusCcPeerEntry 12 }

mepStatusBfd OBJECT IDENTIFIER
    ::= { mepStatus 8 }

mepStatusBfdTable OBJECT-TYPE
    SYNTAX      SEQUENCE OF MepStatusBfdEntry
    MAX-ACCESS  not-accessible
    STATUS      current
    DESCRIPTION
        "This is a table of MEP BFD status"
    ::= { mepStatusBfd 2 }

mepStatusBfdEntry OBJECT-TYPE
    SYNTAX      MepStatusBfdEntry
    MAX-ACCESS  not-accessible
    STATUS      current
    DESCRIPTION
        "This is a MEP BFD status"
    INDEX       { mepStatusBfdId }
    ::= { mepStatusBfdTable 1 }

MepStatusBfdEntry ::= SEQUENCE {
    mepStatusBfdId                  Integer32,
    mepStatusBfdCcTxCnt             Unsigned64,
    mepStatusBfdValidCcRxCnt        Unsigned64,
    mepStatusBfdInvalidCcRxCnt      Unsigned64,
    mepStatusBfdCvTxCnt             Unsigned64,
    mepStatusBfdValidCvRxCnt        Unsigned64,
    mepStatusBfdInvalidCvRxCnt      Unsigned64,
    mepStatusBfdMyDiscr             Unsigned32,
    mepStatusBfdSessionState0       MepBfdSessionState,
    mepStatusBfdSessionState1       MepBfdSessionState,
    mepStatusBfdLocalDiag           MepBfdDiagnosticCode,
    mepStatusBfdRemoteSessionState  MepBfdSessionState,
    mepStatusBfdRemoteDiag          MepBfdDiagnosticCode,
    mepStatusBfdRemoteDiscr         Unsigned32,
    mepStatusBfdRemoteMinRx         Unsigned32,
    mepStatusBfdRemoteFlags         Unsigned8,
    mepStatusBfdUnexpDiscr          Unsigned32,
    mepStatusBfdExpSrcMepIdTlv      OCTET STRING,
    mepStatusBfdUnexpSrcMepIdTlv    OCTET STRING
}

mepStatusBfdId OBJECT-TYPE
    SYNTAX      Integer32 (0..2147483647)
    MAX-ACCESS  not-accessible
    STATUS      current
    DESCRIPTION
        "The MEP instance ID"
    ::= { mepStatusBfdEntry 1 }

mepStatusBfdCcTxCnt OBJECT-TYPE
    SYNTAX      Unsigned64
    MAX-ACCESS  read-only
    STATUS      current
    DESCRIPTION
        "BFD CC transmitted."
    ::= { mepStatusBfdEntry 3 }

mepStatusBfdValidCcRxCnt OBJECT-TYPE
    SYNTAX      Unsigned64
    MAX-ACCESS  read-only
    STATUS      current
    DESCRIPTION
        "Valid BFD CC received."
    ::= { mepStatusBfdEntry 4 }

mepStatusBfdInvalidCcRxCnt OBJECT-TYPE
    SYNTAX      Unsigned64
    MAX-ACCESS  read-only
    STATUS      current
    DESCRIPTION
        "Invalid BFD CC received."
    ::= { mepStatusBfdEntry 5 }

mepStatusBfdCvTxCnt OBJECT-TYPE
    SYNTAX      Unsigned64
    MAX-ACCESS  read-only
    STATUS      current
    DESCRIPTION
        "BFD CV transmitted."
    ::= { mepStatusBfdEntry 6 }

mepStatusBfdValidCvRxCnt OBJECT-TYPE
    SYNTAX      Unsigned64
    MAX-ACCESS  read-only
    STATUS      current
    DESCRIPTION
        "Valid BFD CV received."
    ::= { mepStatusBfdEntry 7 }

mepStatusBfdInvalidCvRxCnt OBJECT-TYPE
    SYNTAX      Unsigned64
    MAX-ACCESS  read-only
    STATUS      current
    DESCRIPTION
        "Invalid BFD CV received."
    ::= { mepStatusBfdEntry 8 }

mepStatusBfdMyDiscr OBJECT-TYPE
    SYNTAX      Unsigned32
    MAX-ACCESS  read-only
    STATUS      current
    DESCRIPTION
        "Selected random 'My Discriminator' value, non-zero."
    ::= { mepStatusBfdEntry 9 }

mepStatusBfdSessionState0 OBJECT-TYPE
    SYNTAX      MepBfdSessionState
    MAX-ACCESS  read-only
    STATUS      current
    DESCRIPTION
        "Local BFD session state (for coordinated mode only SessionState0 is
         valid, for independent mode SessionState0 is sink, SessionState1 is
         source."
    ::= { mepStatusBfdEntry 10 }

mepStatusBfdSessionState1 OBJECT-TYPE
    SYNTAX      MepBfdSessionState
    MAX-ACCESS  read-only
    STATUS      current
    DESCRIPTION
        "Local BFD session state. Only valid in independent mode where
         SessionState0 is sink, SessionState1 is source."
    ::= { mepStatusBfdEntry 11 }

mepStatusBfdLocalDiag OBJECT-TYPE
    SYNTAX      MepBfdDiagnosticCode
    MAX-ACCESS  read-only
    STATUS      current
    DESCRIPTION
        "Local diagnostic code."
    ::= { mepStatusBfdEntry 12 }

mepStatusBfdRemoteSessionState OBJECT-TYPE
    SYNTAX      MepBfdSessionState
    MAX-ACCESS  read-only
    STATUS      current
    DESCRIPTION
        "BFD session state received from remote end."
    ::= { mepStatusBfdEntry 13 }

mepStatusBfdRemoteDiag OBJECT-TYPE
    SYNTAX      MepBfdDiagnosticCode
    MAX-ACCESS  read-only
    STATUS      current
    DESCRIPTION
        "Diagnostic code received from remote end."
    ::= { mepStatusBfdEntry 14 }

mepStatusBfdRemoteDiscr OBJECT-TYPE
    SYNTAX      Unsigned32
    MAX-ACCESS  read-only
    STATUS      current
    DESCRIPTION
        "Discriminator value received from remote end."
    ::= { mepStatusBfdEntry 15 }

mepStatusBfdRemoteMinRx OBJECT-TYPE
    SYNTAX      Unsigned32
    MAX-ACCESS  read-only
    STATUS      current
    DESCRIPTION
        "Required Min RX interval value received from remote end."
    ::= { mepStatusBfdEntry 16 }

mepStatusBfdRemoteFlags OBJECT-TYPE
    SYNTAX      Unsigned8
    MAX-ACCESS  read-only
    STATUS      current
    DESCRIPTION
        "Flags received from remote end."
    ::= { mepStatusBfdEntry 17 }

mepStatusBfdUnexpDiscr OBJECT-TYPE
    SYNTAX      Unsigned32
    MAX-ACCESS  read-only
    STATUS      current
    DESCRIPTION
        "Last received unexpected discriminator value (should be my configured)."
    ::= { mepStatusBfdEntry 18 }

mepStatusBfdExpSrcMepIdTlv OBJECT-TYPE
    SYNTAX      OCTET STRING (SIZE(28))
    MAX-ACCESS  read-only
    STATUS      current
    DESCRIPTION
        "Expected source MEP ID TLV."
    ::= { mepStatusBfdEntry 19 }

mepStatusBfdUnexpSrcMepIdTlv OBJECT-TYPE
    SYNTAX      OCTET STRING (SIZE(28))
    MAX-ACCESS  read-only
    STATUS      current
    DESCRIPTION
        "Last received unexpected source MEP ID TLV."
    ::= { mepStatusBfdEntry 20 }

mepStatusRt OBJECT IDENTIFIER
    ::= { mepStatus 9 }

mepStatusRtTable OBJECT-TYPE
    SYNTAX      SEQUENCE OF MepStatusRtEntry
    MAX-ACCESS  not-accessible
    STATUS      current
    DESCRIPTION
        "This is a table of Route Trace status"
    ::= { mepStatusRt 1 }

mepStatusRtEntry OBJECT-TYPE
    SYNTAX      MepStatusRtEntry
    MAX-ACCESS  not-accessible
    STATUS      current
    DESCRIPTION
        "This is a Route Trace status"
    INDEX       { mepStatusRtId }
    ::= { mepStatusRtTable 1 }

MepStatusRtEntry ::= SEQUENCE {
    mepStatusRtId            Integer32,
    mepStatusRtSeqNo         Unsigned32,
    mepStatusRtRequestCount  Unsigned32,
    mepStatusRtReplyCount    Unsigned32
}

mepStatusRtId OBJECT-TYPE
    SYNTAX      Integer32 (0..2147483647)
    MAX-ACCESS  not-accessible
    STATUS      current
    DESCRIPTION
        "The MEP instance ID"
    ::= { mepStatusRtEntry 1 }

mepStatusRtSeqNo OBJECT-TYPE
    SYNTAX      Unsigned32
    MAX-ACCESS  read-only
    STATUS      current
    DESCRIPTION
        "Sequence number of first RT request."
    ::= { mepStatusRtEntry 2 }

mepStatusRtRequestCount OBJECT-TYPE
    SYNTAX      Unsigned32
    MAX-ACCESS  read-only
    STATUS      current
    DESCRIPTION
        "Number of RT requests sent for current session."
    ::= { mepStatusRtEntry 3 }

mepStatusRtReplyCount OBJECT-TYPE
    SYNTAX      Unsigned32
    MAX-ACCESS  read-only
    STATUS      current
    DESCRIPTION
        "Number of replies received for this Route Trace session."
    ::= { mepStatusRtEntry 4 }

mepStatusRtReplyTable OBJECT-TYPE
    SYNTAX      SEQUENCE OF MepStatusRtReplyEntry
    MAX-ACCESS  not-accessible
    STATUS      current
    DESCRIPTION
        "This is a table of Route Trace reply status"
    ::= { mepStatusRt 2 }

mepStatusRtReplyEntry OBJECT-TYPE
    SYNTAX      MepStatusRtReplyEntry
    MAX-ACCESS  not-accessible
    STATUS      current
    DESCRIPTION
        "This is a Route Trace reply status"
    INDEX       { mepStatusRtReplyId, mepStatusRtReplySeqNo }
    ::= { mepStatusRtReplyTable 1 }

MepStatusRtReplyEntry ::= SEQUENCE {
    mepStatusRtReplyId              Integer32,
    mepStatusRtReplySeqNo           Unsigned32,
    mepStatusRtReplyReturnCode      MepRtReturnCode,
    mepStatusRtReplyReturnSubcode   Unsigned8,
    mepStatusRtReplyRttSec          Unsigned32,
    mepStatusRtReplyRttUsec         Unsigned32,
    mepStatusRtReplyTsSentSec       Unsigned32,
    mepStatusRtReplyTsSentUsec      Unsigned32,
    mepStatusRtReplyTsReceivedSec   Unsigned32,
    mepStatusRtReplyTsReceivedUsec  Unsigned32,
    mepStatusRtReplySrcGlobalId     Unsigned32,
    mepStatusRtReplySrcNodeId       IpAddress,
    mepStatusRtReplyFecSrcValue     Unsigned32,
    mepStatusRtReplyRxIfNum         Unsigned32,
    mepStatusRtReplyRxLabelCnt      Unsigned32,
    mepStatusRtReplyRxLabel1        Unsigned32,
    mepStatusRtReplyRxLabel2        Unsigned32,
    mepStatusRtReplyRxLabel3        Unsigned32,
    mepStatusRtReplyRxLabel4        Unsigned32,
    mepStatusRtReplyRxLabel5        Unsigned32,
    mepStatusRtReplyRxLabel6        Unsigned32,
    mepStatusRtReplyRxLabel7        Unsigned32,
    mepStatusRtReplyRxLabel8        Unsigned32
}

mepStatusRtReplyId OBJECT-TYPE
    SYNTAX      Integer32 (0..2147483647)
    MAX-ACCESS  not-accessible
    STATUS      current
    DESCRIPTION
        "The MEP instance ID"
    ::= { mepStatusRtReplyEntry 1 }

mepStatusRtReplySeqNo OBJECT-TYPE
    SYNTAX      Unsigned32 (0..4294967295)
    MAX-ACCESS  not-accessible
    STATUS      current
    DESCRIPTION
        "The RT sequence number"
    ::= { mepStatusRtReplyEntry 2 }

mepStatusRtReplyReturnCode OBJECT-TYPE
    SYNTAX      MepRtReturnCode
    MAX-ACCESS  read-only
    STATUS      current
    DESCRIPTION
        "Return code from reply."
    ::= { mepStatusRtReplyEntry 3 }

mepStatusRtReplyReturnSubcode OBJECT-TYPE
    SYNTAX      Unsigned8
    MAX-ACCESS  read-only
    STATUS      current
    DESCRIPTION
        "Return subcode from reply."
    ::= { mepStatusRtReplyEntry 4 }

mepStatusRtReplyRttSec OBJECT-TYPE
    SYNTAX      Unsigned32
    MAX-ACCESS  read-only
    STATUS      current
    DESCRIPTION
        "Round Trip Time (seconds)."
    ::= { mepStatusRtReplyEntry 5 }

mepStatusRtReplyRttUsec OBJECT-TYPE
    SYNTAX      Unsigned32
    MAX-ACCESS  read-only
    STATUS      current
    DESCRIPTION
        "Round Trip Time (microseconds)."
    ::= { mepStatusRtReplyEntry 6 }

mepStatusRtReplyTsSentSec OBJECT-TYPE
    SYNTAX      Unsigned32
    MAX-ACCESS  read-only
    STATUS      current
    DESCRIPTION
        "Timestamp sent (sender, seconds)."
    ::= { mepStatusRtReplyEntry 7 }

mepStatusRtReplyTsSentUsec OBJECT-TYPE
    SYNTAX      Unsigned32
    MAX-ACCESS  read-only
    STATUS      current
    DESCRIPTION
        "Timestamp sent (sender, microseconds)."
    ::= { mepStatusRtReplyEntry 8 }

mepStatusRtReplyTsReceivedSec OBJECT-TYPE
    SYNTAX      Unsigned32
    MAX-ACCESS  read-only
    STATUS      current
    DESCRIPTION
        "Timestamp received (receiver, seconds)."
    ::= { mepStatusRtReplyEntry 9 }

mepStatusRtReplyTsReceivedUsec OBJECT-TYPE
    SYNTAX      Unsigned32
    MAX-ACCESS  read-only
    STATUS      current
    DESCRIPTION
        "Timestamp received (receiver, microseconds)."
    ::= { mepStatusRtReplyEntry 10 }

mepStatusRtReplySrcGlobalId OBJECT-TYPE
    SYNTAX      Unsigned32
    MAX-ACCESS  read-only
    STATUS      current
    DESCRIPTION
        "Source global ID from received FEC or source ID TLV in RT reply."
    ::= { mepStatusRtReplyEntry 11 }

mepStatusRtReplySrcNodeId OBJECT-TYPE
    SYNTAX      IpAddress
    MAX-ACCESS  read-only
    STATUS      current
    DESCRIPTION
        "Source node ID from received FEC or source ID TLV in RT reply."
    ::= { mepStatusRtReplyEntry 12 }

mepStatusRtReplyFecSrcValue OBJECT-TYPE
    SYNTAX      Unsigned32
    MAX-ACCESS  read-only
    STATUS      current
    DESCRIPTION
        "For a reply from a PW MEP this is the source AC-ID from the received
         FEC in the RT reply. For a Tunnel MEP or LSP MIP bit 31:16 is the
         source tunnel number and bit 15:0 is the LSP number from the received
         FEC in the RT reply."
    ::= { mepStatusRtReplyEntry 13 }

mepStatusRtReplyRxIfNum OBJECT-TYPE
    SYNTAX      Unsigned32
    MAX-ACCESS  read-only
    STATUS      current
    DESCRIPTION
        "Receiver local interface index from reply."
    ::= { mepStatusRtReplyEntry 14 }

mepStatusRtReplyRxLabelCnt OBJECT-TYPE
    SYNTAX      Unsigned32
    MAX-ACCESS  read-only
    STATUS      current
    DESCRIPTION
        "Number of valid label values RxLabel1, RxLabel2 etc."
    ::= { mepStatusRtReplyEntry 15 }

mepStatusRtReplyRxLabel1 OBJECT-TYPE
    SYNTAX      Unsigned32
    MAX-ACCESS  read-only
    STATUS      current
    DESCRIPTION
        "1st MPLS label (top label) of Label Stack of RT request as seen by
         receiver."
    ::= { mepStatusRtReplyEntry 16 }

mepStatusRtReplyRxLabel2 OBJECT-TYPE
    SYNTAX      Unsigned32
    MAX-ACCESS  read-only
    STATUS      current
    DESCRIPTION
        "2nd MPLS label of Label Stack of RT request as seen by receiver."
    ::= { mepStatusRtReplyEntry 17 }

mepStatusRtReplyRxLabel3 OBJECT-TYPE
    SYNTAX      Unsigned32
    MAX-ACCESS  read-only
    STATUS      current
    DESCRIPTION
        "3rd MPLS label of Label Stack of RT request as seen by receiver."
    ::= { mepStatusRtReplyEntry 18 }

mepStatusRtReplyRxLabel4 OBJECT-TYPE
    SYNTAX      Unsigned32
    MAX-ACCESS  read-only
    STATUS      current
    DESCRIPTION
        "4th MPLS label of Label Stack of RT request as seen by receiver."
    ::= { mepStatusRtReplyEntry 19 }

mepStatusRtReplyRxLabel5 OBJECT-TYPE
    SYNTAX      Unsigned32
    MAX-ACCESS  read-only
    STATUS      current
    DESCRIPTION
        "5th MPLS label of Label Stack of RT request as seen by receiver."
    ::= { mepStatusRtReplyEntry 20 }

mepStatusRtReplyRxLabel6 OBJECT-TYPE
    SYNTAX      Unsigned32
    MAX-ACCESS  read-only
    STATUS      current
    DESCRIPTION
        "6th MPLS label of Label Stack of RT request as seen by receiver."
    ::= { mepStatusRtReplyEntry 21 }

mepStatusRtReplyRxLabel7 OBJECT-TYPE
    SYNTAX      Unsigned32
    MAX-ACCESS  read-only
    STATUS      current
    DESCRIPTION
        "7th MPLS label of Label Stack of RT request as seen by receiver."
    ::= { mepStatusRtReplyEntry 22 }

mepStatusRtReplyRxLabel8 OBJECT-TYPE
    SYNTAX      Unsigned32
    MAX-ACCESS  read-only
    STATUS      current
    DESCRIPTION
        "8th MPLS label of Label Stack of RT request as seen by receiver."
    ::= { mepStatusRtReplyEntry 23 }

mepStatusLmAvail OBJECT IDENTIFIER
    ::= { mepStatus 10 }

mepStatusLmAvailTable OBJECT-TYPE
    SYNTAX      SEQUENCE OF MepStatusLmAvailEntry
    MAX-ACCESS  not-accessible
    STATUS      current
    DESCRIPTION
        "This is a table of Loss Measurement Availability status"
    ::= { mepStatusLmAvail 1 }

mepStatusLmAvailEntry OBJECT-TYPE
    SYNTAX      MepStatusLmAvailEntry
    MAX-ACCESS  not-accessible
    STATUS      current
    DESCRIPTION
        "This is a Loss Measurement Availability status"
    INDEX       { mepStatusLmAvailId }
    ::= { mepStatusLmAvailTable 1 }

MepStatusLmAvailEntry ::= SEQUENCE {
    mepStatusLmAvailId                 Integer32,
    mepStatusLmAvailNearEndAvailState  MepLmAvailState,
    mepStatusLmAvailFarEndAvailState   MepLmAvailState,
    mepStatusLmAvailNearEndAvailCnt    Unsigned32,
    mepStatusLmAvailFarEndAvailCnt     Unsigned32,
    mepStatusLmAvailNearEndUnAvailCnt  Unsigned32,
    mepStatusLmAvailFarEndUnAvailCnt   Unsigned32
}

mepStatusLmAvailId OBJECT-TYPE
    SYNTAX      Integer32 (0..2147483647)
    MAX-ACCESS  not-accessible
    STATUS      current
    DESCRIPTION
        "The MEP instance ID"
    ::= { mepStatusLmAvailEntry 1 }

mepStatusLmAvailNearEndAvailState OBJECT-TYPE
    SYNTAX      MepLmAvailState
    MAX-ACCESS  read-only
    STATUS      current
    DESCRIPTION
        "Near end Availability State."
    ::= { mepStatusLmAvailEntry 2 }

mepStatusLmAvailFarEndAvailState OBJECT-TYPE
    SYNTAX      MepLmAvailState
    MAX-ACCESS  read-only
    STATUS      current
    DESCRIPTION
        "Far end Availability State."
    ::= { mepStatusLmAvailEntry 3 }

mepStatusLmAvailNearEndAvailCnt OBJECT-TYPE
    SYNTAX      Unsigned32
    MAX-ACCESS  read-only
    STATUS      current
    DESCRIPTION
        "Near end Availability Count."
    ::= { mepStatusLmAvailEntry 4 }

mepStatusLmAvailFarEndAvailCnt OBJECT-TYPE
    SYNTAX      Unsigned32
    MAX-ACCESS  read-only
    STATUS      current
    DESCRIPTION
        "Far end Availability Count."
    ::= { mepStatusLmAvailEntry 5 }

mepStatusLmAvailNearEndUnAvailCnt OBJECT-TYPE
    SYNTAX      Unsigned32
    MAX-ACCESS  read-only
    STATUS      current
    DESCRIPTION
        "Near end Unavailability Count."
    ::= { mepStatusLmAvailEntry 6 }

mepStatusLmAvailFarEndUnAvailCnt OBJECT-TYPE
    SYNTAX      Unsigned32
    MAX-ACCESS  read-only
    STATUS      current
    DESCRIPTION
        "Far end Unavailability Count."
    ::= { mepStatusLmAvailEntry 7 }

mepStatusLmAvailPeerTable OBJECT-TYPE
    SYNTAX      SEQUENCE OF MepStatusLmAvailPeerEntry
    MAX-ACCESS  not-accessible
    STATUS      current
    DESCRIPTION
        "This is a table of Loss Measurement Availability status"
    ::= { mepStatusLmAvail 2 }

mepStatusLmAvailPeerEntry OBJECT-TYPE
    SYNTAX      MepStatusLmAvailPeerEntry
    MAX-ACCESS  not-accessible
    STATUS      current
    DESCRIPTION
        "This is a Loss Measurement Availability status"
    INDEX       { mepStatusLmAvailPeerId,
                  mepStatusLmAvailPeerPeerId }
    ::= { mepStatusLmAvailPeerTable 1 }

MepStatusLmAvailPeerEntry ::= SEQUENCE {
    mepStatusLmAvailPeerId                 Integer32,
    mepStatusLmAvailPeerPeerId             Integer32,
    mepStatusLmAvailPeerNearEndAvailState  MepLmAvailState,
    mepStatusLmAvailPeerFarEndAvailState   MepLmAvailState,
    mepStatusLmAvailPeerNearEndAvailCnt    Unsigned32,
    mepStatusLmAvailPeerFarEndAvailCnt     Unsigned32,
    mepStatusLmAvailPeerNearEndUnAvailCnt  Unsigned32,
    mepStatusLmAvailPeerFarEndUnAvailCnt   Unsigned32
}

mepStatusLmAvailPeerId OBJECT-TYPE
    SYNTAX      Integer32 (0..2147483647)
    MAX-ACCESS  not-accessible
    STATUS      current
    DESCRIPTION
        "The MEP instance ID"
    ::= { mepStatusLmAvailPeerEntry 1 }

mepStatusLmAvailPeerPeerId OBJECT-TYPE
    SYNTAX      Integer32 (0..2147483647)
    MAX-ACCESS  not-accessible
    STATUS      current
    DESCRIPTION
        "The Peer MEP ID"
    ::= { mepStatusLmAvailPeerEntry 2 }

mepStatusLmAvailPeerNearEndAvailState OBJECT-TYPE
    SYNTAX      MepLmAvailState
    MAX-ACCESS  read-only
    STATUS      current
    DESCRIPTION
        "Near end Availability State."
    ::= { mepStatusLmAvailPeerEntry 3 }

mepStatusLmAvailPeerFarEndAvailState OBJECT-TYPE
    SYNTAX      MepLmAvailState
    MAX-ACCESS  read-only
    STATUS      current
    DESCRIPTION
        "Far end Availability State."
    ::= { mepStatusLmAvailPeerEntry 4 }

mepStatusLmAvailPeerNearEndAvailCnt OBJECT-TYPE
    SYNTAX      Unsigned32
    MAX-ACCESS  read-only
    STATUS      current
    DESCRIPTION
        "Near end Availability Count."
    ::= { mepStatusLmAvailPeerEntry 5 }

mepStatusLmAvailPeerFarEndAvailCnt OBJECT-TYPE
    SYNTAX      Unsigned32
    MAX-ACCESS  read-only
    STATUS      current
    DESCRIPTION
        "Far end Availability Count."
    ::= { mepStatusLmAvailPeerEntry 6 }

mepStatusLmAvailPeerNearEndUnAvailCnt OBJECT-TYPE
    SYNTAX      Unsigned32
    MAX-ACCESS  read-only
    STATUS      current
    DESCRIPTION
        "Near end Unavailability Count."
    ::= { mepStatusLmAvailPeerEntry 7 }

mepStatusLmAvailPeerFarEndUnAvailCnt OBJECT-TYPE
    SYNTAX      Unsigned32
    MAX-ACCESS  read-only
    STATUS      current
    DESCRIPTION
        "Far end Unavailability Count."
    ::= { mepStatusLmAvailPeerEntry 8 }

mepStatusLmHli OBJECT IDENTIFIER
    ::= { mepStatus 11 }

mepStatusLmHliTable OBJECT-TYPE
    SYNTAX      SEQUENCE OF MepStatusLmHliEntry
    MAX-ACCESS  not-accessible
    STATUS      current
    DESCRIPTION
        "This is a table of Loss Measurement High Loss Interval status"
    ::= { mepStatusLmHli 1 }

mepStatusLmHliEntry OBJECT-TYPE
    SYNTAX      MepStatusLmHliEntry
    MAX-ACCESS  not-accessible
    STATUS      current
    DESCRIPTION
        "This is a Loss Measurement High Loss Interval status"
    INDEX       { mepStatusLmHliId }
    ::= { mepStatusLmHliTable 1 }

MepStatusLmHliEntry ::= SEQUENCE {
    mepStatusLmHliId             Integer32,
    mepStatusLmHliNearEndCnt     Unsigned32,
    mepStatusLmHliFarEndCnt      Unsigned32,
    mepStatusLmHliNearEndConCnt  Unsigned32,
    mepStatusLmHliFarEndConCnt   Unsigned32
}

mepStatusLmHliId OBJECT-TYPE
    SYNTAX      Integer32 (0..2147483647)
    MAX-ACCESS  not-accessible
    STATUS      current
    DESCRIPTION
        "The MEP instance ID"
    ::= { mepStatusLmHliEntry 1 }

mepStatusLmHliNearEndCnt OBJECT-TYPE
    SYNTAX      Unsigned32
    MAX-ACCESS  read-only
    STATUS      current
    DESCRIPTION
        "Near end High Loss Interval count (number of measurements where
         Availability State is available and FLR is above HLI FLR threshold."
    ::= { mepStatusLmHliEntry 2 }

mepStatusLmHliFarEndCnt OBJECT-TYPE
    SYNTAX      Unsigned32
    MAX-ACCESS  read-only
    STATUS      current
    DESCRIPTION
        "Far end High Loss Interval count (number of measurements where
         Availability State is available and FLR is above HLI FLR threshold."
    ::= { mepStatusLmHliEntry 3 }

mepStatusLmHliNearEndConCnt OBJECT-TYPE
    SYNTAX      Unsigned32
    MAX-ACCESS  read-only
    STATUS      current
    DESCRIPTION
        "Near end High Loss Interval consecutive count."
    ::= { mepStatusLmHliEntry 4 }

mepStatusLmHliFarEndConCnt OBJECT-TYPE
    SYNTAX      Unsigned32
    MAX-ACCESS  read-only
    STATUS      current
    DESCRIPTION
        "Far end High Loss Interval consecutive count."
    ::= { mepStatusLmHliEntry 5 }

mepStatusLmHliPeerTable OBJECT-TYPE
    SYNTAX      SEQUENCE OF MepStatusLmHliPeerEntry
    MAX-ACCESS  not-accessible
    STATUS      current
    DESCRIPTION
        "This is a table of Loss Measurement High Loss Interval status"
    ::= { mepStatusLmHli 2 }

mepStatusLmHliPeerEntry OBJECT-TYPE
    SYNTAX      MepStatusLmHliPeerEntry
    MAX-ACCESS  not-accessible
    STATUS      current
    DESCRIPTION
        "This is a Loss Measurement High Loss Interval status"
    INDEX       { mepStatusLmHliPeerId,
                  mepStatusLmHliPeerPeerId }
    ::= { mepStatusLmHliPeerTable 1 }

MepStatusLmHliPeerEntry ::= SEQUENCE {
    mepStatusLmHliPeerId             Integer32,
    mepStatusLmHliPeerPeerId         Integer32,
    mepStatusLmHliPeerNearEndCnt     Unsigned32,
    mepStatusLmHliPeerFarEndCnt      Unsigned32,
    mepStatusLmHliPeerNearEndConCnt  Unsigned32,
    mepStatusLmHliPeerFarEndConCnt   Unsigned32
}

mepStatusLmHliPeerId OBJECT-TYPE
    SYNTAX      Integer32 (0..2147483647)
    MAX-ACCESS  not-accessible
    STATUS      current
    DESCRIPTION
        "The MEP instance ID"
    ::= { mepStatusLmHliPeerEntry 1 }

mepStatusLmHliPeerPeerId OBJECT-TYPE
    SYNTAX      Integer32 (0..2147483647)
    MAX-ACCESS  not-accessible
    STATUS      current
    DESCRIPTION
        "The Peer MEP ID"
    ::= { mepStatusLmHliPeerEntry 2 }

mepStatusLmHliPeerNearEndCnt OBJECT-TYPE
    SYNTAX      Unsigned32
    MAX-ACCESS  read-only
    STATUS      current
    DESCRIPTION
        "Near end High Loss Interval count (number of measurements where
         Availability State is available and FLR is above HLI FLR threshold."
    ::= { mepStatusLmHliPeerEntry 3 }

mepStatusLmHliPeerFarEndCnt OBJECT-TYPE
    SYNTAX      Unsigned32
    MAX-ACCESS  read-only
    STATUS      current
    DESCRIPTION
        "Far end High Loss Interval count (number of measurements where
         Availability State is available and FLR is above HLI FLR threshold."
    ::= { mepStatusLmHliPeerEntry 4 }

mepStatusLmHliPeerNearEndConCnt OBJECT-TYPE
    SYNTAX      Unsigned32
    MAX-ACCESS  read-only
    STATUS      current
    DESCRIPTION
        "Near end High Loss Interval consecutive count."
    ::= { mepStatusLmHliPeerEntry 5 }

mepStatusLmHliPeerFarEndConCnt OBJECT-TYPE
    SYNTAX      Unsigned32
    MAX-ACCESS  read-only
    STATUS      current
    DESCRIPTION
        "Far end High Loss Interval consecutive count."
    ::= { mepStatusLmHliPeerEntry 6 }

mepControl OBJECT IDENTIFIER
    ::= { mepMibObjects 4 }

mepControlLm OBJECT IDENTIFIER
    ::= { mepControl 1 }

mepControlLmTable OBJECT-TYPE
    SYNTAX      SEQUENCE OF MepControlLmEntry
    MAX-ACCESS  not-accessible
    STATUS      current
    DESCRIPTION
        "This is a table of created instance Loss Measurement control parameters"
    ::= { mepControlLm 1 }

mepControlLmEntry OBJECT-TYPE
    SYNTAX      MepControlLmEntry
    MAX-ACCESS  not-accessible
    STATUS      current
    DESCRIPTION
        "This is a created instance Loss Measurement control parameters"
    INDEX       { mepControlLmId }
    ::= { mepControlLmTable 1 }

MepControlLmEntry ::= SEQUENCE {
    mepControlLmId     Integer32,
    mepControlLmClear  TruthValue
}

mepControlLmId OBJECT-TYPE
    SYNTAX      Integer32 (0..2147483647)
    MAX-ACCESS  not-accessible
    STATUS      current
    DESCRIPTION
        "The MEP instance ID"
    ::= { mepControlLmEntry 1 }

mepControlLmClear OBJECT-TYPE
    SYNTAX      TruthValue
    MAX-ACCESS  read-write
    STATUS      current
    DESCRIPTION
        "Clear the LM results"
    ::= { mepControlLmEntry 2 }

mepControlDm OBJECT IDENTIFIER
    ::= { mepControl 2 }

mepControlDmTable OBJECT-TYPE
    SYNTAX      SEQUENCE OF MepControlDmEntry
    MAX-ACCESS  not-accessible
    STATUS      current
    DESCRIPTION
        "This is a table of created instance Delay Measurement control
         parameters"
    ::= { mepControlDm 1 }

mepControlDmEntry OBJECT-TYPE
    SYNTAX      MepControlDmEntry
    MAX-ACCESS  not-accessible
    STATUS      current
    DESCRIPTION
        "This is a created instance Delay Measurement control parameters"
    INDEX       { mepControlDmId }
    ::= { mepControlDmTable 1 }

MepControlDmEntry ::= SEQUENCE {
    mepControlDmId     Integer32,
    mepControlDmClear  TruthValue
}

mepControlDmId OBJECT-TYPE
    SYNTAX      Integer32 (0..2147483647)
    MAX-ACCESS  not-accessible
    STATUS      current
    DESCRIPTION
        "The MEP instance ID"
    ::= { mepControlDmEntry 1 }

mepControlDmClear OBJECT-TYPE
    SYNTAX      TruthValue
    MAX-ACCESS  read-write
    STATUS      current
    DESCRIPTION
        "Clear the DM results"
    ::= { mepControlDmEntry 2 }

mepControlTst OBJECT IDENTIFIER
    ::= { mepControl 3 }

mepControlTstTable OBJECT-TYPE
    SYNTAX      SEQUENCE OF MepControlTstEntry
    MAX-ACCESS  not-accessible
    STATUS      current
    DESCRIPTION
        "This is a table of created instance Test Signal control parameters"
    ::= { mepControlTst 1 }

mepControlTstEntry OBJECT-TYPE
    SYNTAX      MepControlTstEntry
    MAX-ACCESS  not-accessible
    STATUS      current
    DESCRIPTION
        "This is a created instance Test Signal control parameters"
    INDEX       { mepControlTstId }
    ::= { mepControlTstTable 1 }

MepControlTstEntry ::= SEQUENCE {
    mepControlTstId     Integer32,
    mepControlTstClear  TruthValue
}

mepControlTstId OBJECT-TYPE
    SYNTAX      Integer32 (0..2147483647)
    MAX-ACCESS  not-accessible
    STATUS      current
    DESCRIPTION
        "The MEP instance ID"
    ::= { mepControlTstEntry 1 }

mepControlTstClear OBJECT-TYPE
    SYNTAX      TruthValue
    MAX-ACCESS  read-write
    STATUS      current
    DESCRIPTION
        "Clear the TST results"
    ::= { mepControlTstEntry 2 }

mepControlBfd OBJECT IDENTIFIER
    ::= { mepControl 4 }

mepControlBfdTable OBJECT-TYPE
    SYNTAX      SEQUENCE OF MepControlBfdEntry
    MAX-ACCESS  not-accessible
    STATUS      current
    DESCRIPTION
        "This is a table of created instance BFD control parameters"
    ::= { mepControlBfd 1 }

mepControlBfdEntry OBJECT-TYPE
    SYNTAX      MepControlBfdEntry
    MAX-ACCESS  not-accessible
    STATUS      current
    DESCRIPTION
        "This is a created instance BFD control parameters"
    INDEX       { mepControlBfdId }
    ::= { mepControlBfdTable 1 }

MepControlBfdEntry ::= SEQUENCE {
    mepControlBfdId     Integer32,
    mepControlBfdClear  TruthValue
}

mepControlBfdId OBJECT-TYPE
    SYNTAX      Integer32 (0..2147483647)
    MAX-ACCESS  not-accessible
    STATUS      current
    DESCRIPTION
        "The MEP instance ID"
    ::= { mepControlBfdEntry 1 }

mepControlBfdClear OBJECT-TYPE
    SYNTAX      TruthValue
    MAX-ACCESS  read-write
    STATUS      current
    DESCRIPTION
        "Clear the BFD statistics counters"
    ::= { mepControlBfdEntry 2 }

mepMibConformance OBJECT IDENTIFIER
    ::= { mepMib 2 }

mepMibCompliances OBJECT IDENTIFIER
    ::= { mepMibConformance 1 }

mepMibGroups OBJECT IDENTIFIER
    ::= { mepMibConformance 2 }

mepCapabilitiesInfoGroup OBJECT-GROUP
    OBJECTS     { mepCapabilitiesInstanceMax,
                  mepCapabilitiesPeerMax,
                  mepCapabilitiesTransactionMax,
                  mepCapabilitiesReplyMax,
                  mepCapabilitiesClientFlowsMax,
                  mepCapabilitiesMacMength,
                  mepCapabilitiesMegCodeLength,
                  mepCapabilitiesDmIntervalMin,
                  mepCapabilitiesDmIntervalMax,
                  mepCapabilitiesDmLastnMin,
                  mepCapabilitiesDmLastnMax,
                  mepCapabilitiesLbmSizeMax,
                  mepCapabilitiesLbmSizeMin,
                  mepCapabilitiesTstSizeMax,
                  mepCapabilitiesTstSizeMin,
                  mepCapabilitiesTstRateMax,
                  mepCapabilitiesClientPrioHighest,
                  mepCapabilitiesItuG8113dot2,
                  mepCapabilitiesVoeSupport,
                  mepCapabilitiesLbToSendInfinite,
                  mepCapabilitiesBfdAuthKeyMax,
                  mepCapabilitiesSlmSizeMax,
                  mepCapabilitiesSlmSizeMin }
    STATUS      current
    DESCRIPTION
        "A collection of objects suitable for bulk operations."
    ::= { mepMibGroups 1 }

mepConfigInstanceTableInfoGroup OBJECT-GROUP
    OBJECTS     { mepConfigInstanceMode,
                  mepConfigInstanceDirection,
                  mepConfigInstanceFlow,
                  mepConfigInstancePort,
                  mepConfigInstanceLevel,
                  mepConfigInstanceVid, mepConfigInstanceVoe,
                  mepConfigInstanceMac,
                  mepConfigInstanceFormat,
                  mepConfigInstanceName, mepConfigInstanceMeg,
                  mepConfigInstanceMep,
                  mepConfigInstanceEvcPag,
                  mepConfigInstanceEvcQos,
                  mepConfigInstanceAction }
    STATUS      current
    DESCRIPTION
        "A collection of objects suitable for bulk operations."
    ::= { mepMibGroups 2 }

mepConfigInstanceRowEditorInfoGroup OBJECT-GROUP
    OBJECTS     { mepConfigInstanceRowEditorId,
                  mepConfigInstanceRowEditorMode,
                  mepConfigInstanceRowEditorDirection,
                  mepConfigInstanceRowEditorFlow,
                  mepConfigInstanceRowEditorPort,
                  mepConfigInstanceRowEditorLevel,
                  mepConfigInstanceRowEditorVid,
                  mepConfigInstanceRowEditorVoe,
                  mepConfigInstanceRowEditorMac,
                  mepConfigInstanceRowEditorFormat,
                  mepConfigInstanceRowEditorName,
                  mepConfigInstanceRowEditorMeg,
                  mepConfigInstanceRowEditorMep,
                  mepConfigInstanceRowEditorEvcPag,
                  mepConfigInstanceRowEditorEvcQos,
                  mepConfigInstanceRowEditorAction }
    STATUS      current
    DESCRIPTION
        "A collection of objects suitable for bulk operations."
    ::= { mepMibGroups 3 }

mepConfigInstancePeerTableInfoGroup OBJECT-GROUP
    OBJECTS     { mepConfigInstancePeerMac,
                  mepConfigInstancePeerAction }
    STATUS      current
    DESCRIPTION
        "A collection of objects suitable for bulk operations."
    ::= { mepMibGroups 4 }

mepConfigInstancePeerRowEditorInfoGroup OBJECT-GROUP
    OBJECTS     { mepConfigInstancePeerRowEditorId,
                  mepConfigInstancePeerRowEditorPeerId,
                  mepConfigInstancePeerRowEditorMac,
                  mepConfigInstancePeerRowEditorAction }
    STATUS      current
    DESCRIPTION
        "A collection of objects suitable for bulk operations."
    ::= { mepMibGroups 5 }

mepConfigPmTableInfoGroup OBJECT-GROUP
    OBJECTS     { mepConfigPmEnable }
    STATUS      current
    DESCRIPTION
        "A collection of objects suitable for bulk operations."
    ::= { mepMibGroups 6 }

mepConfigCcTableInfoGroup OBJECT-GROUP
    OBJECTS     { mepConfigCcPrio, mepConfigCcRate,
                  mepConfigCcTlv, mepConfigCcAction }
    STATUS      current
    DESCRIPTION
        "A collection of objects suitable for bulk operations."
    ::= { mepMibGroups 7 }

mepConfigCcRowEditorInfoGroup OBJECT-GROUP
    OBJECTS     { mepConfigCcRowEditorId,
                  mepConfigCcRowEditorPrio,
                  mepConfigCcRowEditorRate,
                  mepConfigCcRowEditorTlv,
                  mepConfigCcRowEditorAction }
    STATUS      current
    DESCRIPTION
        "A collection of objects suitable for bulk operations."
    ::= { mepMibGroups 8 }

mepConfigLmTableInfoGroup OBJECT-GROUP
    OBJECTS     { mepConfigLmEnable, mepConfigLmEnded,
                  mepConfigLmPrio, mepConfigLmRate,
                  mepConfigLmCast, mepConfigLmFlrInterval,
                  mepConfigLmFlowCount, mepConfigLmOamCount,
                  mepConfigLmLossTh,
                  mepConfigLmLossCounterIntHolddownTimer,
                  mepConfigLmLossThCntHolddownTimer,
                  mepConfigLmRxEnable, mepConfigLmSynthetic,
                  mepConfigLmMep, mepConfigLmFrameSize,
                  mepConfigLmMeasInterval,
                  mepConfigLmSlmTestId }
    STATUS      current
    DESCRIPTION
        "A collection of objects suitable for bulk operations."
    ::= { mepMibGroups 9 }

mepConfigDmTableInfoGroup OBJECT-GROUP
    OBJECTS     { mepConfigDmEnable, mepConfigDmEnded,
                  mepConfigDmPrio, mepConfigDmCast,
                  mepConfigDmMep, mepConfigDmCalcWay,
                  mepConfigDmInterval, mepConfigDmLastN,
                  mepConfigDmTimeUnit, mepConfigDmOverflowAct,
                  mepConfigDmSynchronized }
    STATUS      current
    DESCRIPTION
        "A collection of objects suitable for bulk operations."
    ::= { mepMibGroups 10 }

mepConfigLbTableInfoGroup OBJECT-GROUP
    OBJECTS     { mepConfigLbDei, mepConfigLbPrio,
                  mepConfigLbCast, mepConfigLbMep,
                  mepConfigLbMac, mepConfigLbToSend,
                  mepConfigLbSize, mepConfigLbInterval,
                  mepConfigLbTimeToLive, mepConfigLbAction }
    STATUS      current
    DESCRIPTION
        "A collection of objects suitable for bulk operations."
    ::= { mepMibGroups 11 }

mepConfigLbRowEditorInfoGroup OBJECT-GROUP
    OBJECTS     { mepConfigLbRowEditorId,
                  mepConfigLbRowEditorDei,
                  mepConfigLbRowEditorPrio,
                  mepConfigLbRowEditorCast,
                  mepConfigLbRowEditorMep,
                  mepConfigLbRowEditorMac,
                  mepConfigLbRowEditorToSend,
                  mepConfigLbRowEditorSize,
                  mepConfigLbRowEditorInterval,
                  mepConfigLbRowEditorTimeToLive,
                  mepConfigLbRowEditorAction }
    STATUS      current
    DESCRIPTION
        "A collection of objects suitable for bulk operations."
    ::= { mepMibGroups 12 }

mepConfigTstTableInfoGroup OBJECT-GROUP
    OBJECTS     { mepConfigTstTxEnable, mepConfigTstRxEnable,
                  mepConfigTstDei, mepConfigTstPrio,
                  mepConfigTstMep, mepConfigTstRate,
                  mepConfigTstSize, mepConfigTstPattern,
                  mepConfigTstSequence, mepConfigTstAction }
    STATUS      current
    DESCRIPTION
        "A collection of objects suitable for bulk operations."
    ::= { mepMibGroups 13 }

mepConfigTstRowEditorInfoGroup OBJECT-GROUP
    OBJECTS     { mepConfigTstRowEditorId,
                  mepConfigTstRowEditorTxEnable,
                  mepConfigTstRowEditorRxEnable,
                  mepConfigTstRowEditorDei,
                  mepConfigTstRowEditorPrio,
                  mepConfigTstRowEditorMep,
                  mepConfigTstRowEditorRate,
                  mepConfigTstRowEditorSize,
                  mepConfigTstRowEditorPattern,
                  mepConfigTstRowEditorSequence,
                  mepConfigTstRowEditorAction }
    STATUS      current
    DESCRIPTION
        "A collection of objects suitable for bulk operations."
    ::= { mepMibGroups 14 }

mepConfigLtTableInfoGroup OBJECT-GROUP
    OBJECTS     { mepConfigLtPrio, mepConfigLtMep,
                  mepConfigLtMac, mepConfigLtTimeToLive,
                  mepConfigLtAction }
    STATUS      current
    DESCRIPTION
        "A collection of objects suitable for bulk operations."
    ::= { mepMibGroups 15 }

mepConfigLtRowEditorInfoGroup OBJECT-GROUP
    OBJECTS     { mepConfigLtRowEditorId,
                  mepConfigLtRowEditorPrio,
                  mepConfigLtRowEditorMep,
                  mepConfigLtRowEditorMac,
                  mepConfigLtRowEditorTimeToLive,
                  mepConfigLtRowEditorAction }
    STATUS      current
    DESCRIPTION
        "A collection of objects suitable for bulk operations."
    ::= { mepMibGroups 16 }

mepConfigApsTableInfoGroup OBJECT-GROUP
    OBJECTS     { mepConfigApsPrio, mepConfigApsApsType,
                  mepConfigApsCast, mepConfigApsRapsOctet,
                  mepConfigApsAction }
    STATUS      current
    DESCRIPTION
        "A collection of objects suitable for bulk operations."
    ::= { mepMibGroups 17 }

mepConfigApsRowEditorInfoGroup OBJECT-GROUP
    OBJECTS     { mepConfigApsRowEditorId,
                  mepConfigApsRowEditorPrio,
                  mepConfigApsRowEditorApsType,
                  mepConfigApsRowEditorCast,
                  mepConfigApsRowEditorRapsOctet,
                  mepConfigApsRowEditorAction }
    STATUS      current
    DESCRIPTION
        "A collection of objects suitable for bulk operations."
    ::= { mepMibGroups 18 }

mepConfigAisTableInfoGroup OBJECT-GROUP
    OBJECTS     { mepConfigAisProtection, mepConfigAisRate,
                  mepConfigAisAction }
    STATUS      current
    DESCRIPTION
        "A collection of objects suitable for bulk operations."
    ::= { mepMibGroups 19 }

mepConfigAisRowEditorInfoGroup OBJECT-GROUP
    OBJECTS     { mepConfigAisRowEditorId,
                  mepConfigAisRowEditorProtection,
                  mepConfigAisRowEditorRate,
                  mepConfigAisRowEditorAction }
    STATUS      current
    DESCRIPTION
        "A collection of objects suitable for bulk operations."
    ::= { mepMibGroups 20 }

mepConfigLckTableInfoGroup OBJECT-GROUP
    OBJECTS     { mepConfigLckRate, mepConfigLckAction }
    STATUS      current
    DESCRIPTION
        "A collection of objects suitable for bulk operations."
    ::= { mepMibGroups 21 }

mepConfigLckRowEditorInfoGroup OBJECT-GROUP
    OBJECTS     { mepConfigLckRowEditorId,
                  mepConfigLckRowEditorRate,
                  mepConfigLckRowEditorAction }
    STATUS      current
    DESCRIPTION
        "A collection of objects suitable for bulk operations."
    ::= { mepMibGroups 22 }

mepConfigClientFlowTableInfoGroup OBJECT-GROUP
    OBJECTS     { mepConfigClientFlowAisPrio,
                  mepConfigClientFlowLckPrio,
                  mepConfigClientFlowLevel,
                  mepConfigClientFlowAction }
    STATUS      current
    DESCRIPTION
        "A collection of objects suitable for bulk operations."
    ::= { mepMibGroups 23 }

mepConfigClientFlowRowEditorInfoGroup OBJECT-GROUP
    OBJECTS     { mepConfigClientFlowRowEditorId,
                  mepConfigClientFlowRowEditorFlowId,
                  mepConfigClientFlowRowEditorAisPrio,
                  mepConfigClientFlowRowEditorLckPrio,
                  mepConfigClientFlowRowEditorLevel,
                  mepConfigClientFlowRowEditorAction }
    STATUS      current
    DESCRIPTION
        "A collection of objects suitable for bulk operations."
    ::= { mepMibGroups 24 }

mepConfigSyslogTableInfoGroup OBJECT-GROUP
    OBJECTS     { mepConfigSyslogEnable }
    STATUS      current
    DESCRIPTION
        "A collection of objects suitable for bulk operations."
    ::= { mepMibGroups 25 }

mepConfigTlvLeafInfoGroup OBJECT-GROUP
    OBJECTS     { mepConfigTlvLeafOsTlvOuiFirst,
                  mepConfigTlvLeafOsTlvOuiSecond,
                  mepConfigTlvLeafOsTlvOuiThird,
                  mepConfigTlvLeafOsTlvSubType,
                  mepConfigTlvLeafOsTlvValue }
    STATUS      current
    DESCRIPTION
        "A collection of objects suitable for bulk operations."
    ::= { mepMibGroups 26 }

mepConfigBfdTableInfoGroup OBJECT-GROUP
    OBJECTS     { mepConfigBfdEnable,
                  mepConfigBfdIsIndependent,
                  mepConfigBfdCcOnly,
                  mepConfigBfdTxAuthEnabled,
                  mepConfigBfdRxAuthEnabled,
                  mepConfigBfdTxAuthKeyId,
                  mepConfigBfdCcPeriod, mepConfigBfdRxFlow,
                  mepConfigBfdAction }
    STATUS      current
    DESCRIPTION
        "A collection of objects suitable for bulk operations."
    ::= { mepMibGroups 27 }

mepConfigBfdRowEditorInfoGroup OBJECT-GROUP
    OBJECTS     { mepConfigBfdRowEditorId,
                  mepConfigBfdRowEditorEnable,
                  mepConfigBfdRowEditorIsIndependent,
                  mepConfigBfdRowEditorCcOnly,
                  mepConfigBfdRowEditorTxAuthEnabled,
                  mepConfigBfdRowEditorRxAuthEnabled,
                  mepConfigBfdRowEditorTxAuthKeyId,
                  mepConfigBfdRowEditorCcPeriod,
                  mepConfigBfdRowEditorRxFlow,
                  mepConfigBfdRowEditorAction }
    STATUS      current
    DESCRIPTION
        "A collection of objects suitable for bulk operations."
    ::= { mepMibGroups 28 }

mepConfigBfdAuthTableInfoGroup OBJECT-GROUP
    OBJECTS     { mepConfigBfdAuthKeyType,
                  mepConfigBfdAuthKeyLen, mepConfigBfdAuthKey,
                  mepConfigBfdAuthAction }
    STATUS      current
    DESCRIPTION
        "A collection of objects suitable for bulk operations."
    ::= { mepMibGroups 29 }

mepConfigBfdAuthRowEditorInfoGroup OBJECT-GROUP
    OBJECTS     { mepConfigBfdAuthRowEditorId,
                  mepConfigBfdAuthRowEditorKeyType,
                  mepConfigBfdAuthRowEditorKeyLen,
                  mepConfigBfdAuthRowEditorKey,
                  mepConfigBfdAuthRowEditorAction }
    STATUS      current
    DESCRIPTION
        "A collection of objects suitable for bulk operations."
    ::= { mepMibGroups 30 }

mepConfigRtTableInfoGroup OBJECT-GROUP
    OBJECTS     { mepConfigRtTrafficClass,
                  mepConfigRtSrcIdTlv, mepConfigRtDstIdTlv,
                  mepConfigRtPadTlvType, mepConfigRtPadTlvLen,
                  mepConfigRtFlags, mepConfigRtMaxTimeToLive,
                  mepConfigRtAction }
    STATUS      current
    DESCRIPTION
        "A collection of objects suitable for bulk operations."
    ::= { mepMibGroups 31 }

mepConfigRtRowEditorInfoGroup OBJECT-GROUP
    OBJECTS     { mepConfigRtRowEditorId,
                  mepConfigRtRowEditorTrafficClass,
                  mepConfigRtRowEditorSrcIdTlv,
                  mepConfigRtRowEditorDstIdTlv,
                  mepConfigRtRowEditorPadTlvType,
                  mepConfigRtRowEditorPadTlvLen,
                  mepConfigRtRowEditorFlags,
                  mepConfigRtRowEditorMaxTimeToLive,
                  mepConfigRtRowEditorAction }
    STATUS      current
    DESCRIPTION
        "A collection of objects suitable for bulk operations."
    ::= { mepMibGroups 32 }

mepConfigLstTableInfoGroup OBJECT-GROUP
    OBJECTS     { mepConfigLstEnable }
    STATUS      current
    DESCRIPTION
        "A collection of objects suitable for bulk operations."
    ::= { mepMibGroups 33 }

mepConfigLmAvailTableInfoGroup OBJECT-GROUP
    OBJECTS     { mepConfigLmAvailEnable,
                  mepConfigLmAvailLosRatioThr,
                  mepConfigLmAvailInterval,
                  mepConfigLmAvailMaintenance }
    STATUS      current
    DESCRIPTION
        "A collection of objects suitable for bulk operations."
    ::= { mepMibGroups 34 }

mepConfigLmHliTableInfoGroup OBJECT-GROUP
    OBJECTS     { mepConfigLmHliEnable,
                  mepConfigLmHliHiLosRatioThr,
                  mepConfigLmHliConInterval,
                  mepConfigLmHliCntHolddownTimer }
    STATUS      current
    DESCRIPTION
        "A collection of objects suitable for bulk operations."
    ::= { mepMibGroups 35 }

mepConfigLmSdegTableInfoGroup OBJECT-GROUP
    OBJECTS     { mepConfigLmSdegEnable, mepConfigLmSdegTxMin,
                  mepConfigLmSdegLosRatioThr,
                  mepConfigLmSdegBadThr,
                  mepConfigLmSdegGoodThr }
    STATUS      current
    DESCRIPTION
        "A collection of objects suitable for bulk operations."
    ::= { mepMibGroups 36 }

mepStatusInstanceTableInfoGroup OBJECT-GROUP
    OBJECTS     { mepStatusInstanceClevel,
                  mepStatusInstanceCmeg,
                  mepStatusInstanceCmep,
                  mepStatusInstanceCssf,
                  mepStatusInstanceCais,
                  mepStatusInstanceClck,
                  mepStatusInstanceAtsf,
                  mepStatusInstanceAtsd,
                  mepStatusInstanceAblk,
                  mepStatusInstanceCloop,
                  mepStatusInstanceCconfig }
    STATUS      current
    DESCRIPTION
        "A collection of objects suitable for bulk operations."
    ::= { mepMibGroups 37 }

mepStatusInstancePeerTableInfoGroup OBJECT-GROUP
    OBJECTS     { mepStatusInstancePeerCloc,
                  mepStatusInstancePeerCrdi,
                  mepStatusInstancePeerCperiod,
                  mepStatusInstancePeerCprio,
                  mepStatusInstancePeerCdeg }
    STATUS      current
    DESCRIPTION
        "A collection of objects suitable for bulk operations."
    ::= { mepMibGroups 38 }

mepStatusLmTableInfoGroup OBJECT-GROUP
    OBJECTS     { mepStatusLmTxCounter, mepStatusLmRxCounter,
                  mepStatusLmNearEndLosCounterTot,
                  mepStatusLmFarEndLosCounterTot,
                  mepStatusLmNearEndLosRatioInt,
                  mepStatusLmFarEndLosRatioInt,
                  mepStatusLmNearEndLosCounterInt,
                  mepStatusLmFarEndLosCounterInt,
                  mepStatusLmNearEndLosThCnt,
                  mepStatusLmFarEndLosThCnt,
                  mepStatusLmNearEndLosRatioTot,
                  mepStatusLmFarEndLosRatioTot,
                  mepStatusLmNearEndLosRatioMin,
                  mepStatusLmFarEndLosRatioMin,
                  mepStatusLmNearEndLosRatioMax,
                  mepStatusLmFarEndLosRatioMax,
                  mepStatusLmIntervalElapsed }
    STATUS      current
    DESCRIPTION
        "A collection of objects suitable for bulk operations."
    ::= { mepMibGroups 39 }

mepStatusLmPeerTableInfoGroup OBJECT-GROUP
    OBJECTS     { mepStatusLmPeerTxCounter,
                  mepStatusLmPeerRxCounter,
                  mepStatusLmPeerNearEndLosCounterTot,
                  mepStatusLmPeerFarEndLosCounterTot,
                  mepStatusLmPeerNearEndLosRatioInt,
                  mepStatusLmPeerFarEndLosRatioInt,
                  mepStatusLmPeerNearEndLosCounterInt,
                  mepStatusLmPeerFarEndLosCounterInt,
                  mepStatusLmPeerNearEndLosThCnt,
                  mepStatusLmPeerFarEndLosThCnt,
                  mepStatusLmPeerNearEndLosRatioTot,
                  mepStatusLmPeerFarEndLosRatioTot,
                  mepStatusLmPeerNearEndLosRatioMin,
                  mepStatusLmPeerFarEndLosRatioMin,
                  mepStatusLmPeerNearEndLosRatioMax,
                  mepStatusLmPeerFarEndLosRatioMax,
                  mepStatusLmPeerIntervalElapsed }
    STATUS      current
    DESCRIPTION
        "A collection of objects suitable for bulk operations."
    ::= { mepMibGroups 40 }

mepStatusDmTwoWayTableInfoGroup OBJECT-GROUP
    OBJECTS     { mepStatusDmTwoWayTxCounter,
                  mepStatusDmTwoWayRxCounter,
                  mepStatusDmTwoWayRxTimeOutCounter,
                  mepStatusDmTwoWayRxErrorCounter,
                  mepStatusDmTwoWayInternalOverflowCounter,
                  mepStatusDmTwoWayAverageDelay,
                  mepStatusDmTwoWayAverageLastnDelay,
                  mepStatusDmTwoWayAverageDelayVariation,
                  mepStatusDmTwoWayAverageLastnDelayVariation,
                  mepStatusDmTwoWayMinimumDelay,
                  mepStatusDmTwoWayMaximumDelay,
                  mepStatusDmTwoWayMinimumDelayVariation,
                  mepStatusDmTwoWayMaximumDelayVariation,
                  mepStatusDmTwoWayTimeUnit }
    STATUS      current
    DESCRIPTION
        "A collection of objects suitable for bulk operations."
    ::= { mepMibGroups 41 }

mepStatusDmOneWayFarNearTableInfoGroup OBJECT-GROUP
    OBJECTS     { mepStatusDmOneWayFarNearTxCounter,
                  mepStatusDmOneWayFarNearRxCounter,
                  mepStatusDmOneWayFarNearRxTimeOutCounter,
                  mepStatusDmOneWayFarNearRxErrorCounter,
                  mepStatusDmOneWayFarNearInternalOverflowCounter,
                  mepStatusDmOneWayFarNearAverageDelay,
                  mepStatusDmOneWayFarNearAverageLastnDelay,
                  mepStatusDmOneWayFarNearAverageDelayVariation,
                  mepStatusDmOneWayFarNearAverageLastnDelayVariation,
                  mepStatusDmOneWayFarNearMinimumDelay,
                  mepStatusDmOneWayFarNearMaximumDelay,
                  mepStatusDmOneWayFarNearMinimumDelayVariation,
                  mepStatusDmOneWayFarNearMaximumDelayVariation,
                  mepStatusDmOneWayFarNearTimeUnit }
    STATUS      current
    DESCRIPTION
        "A collection of objects suitable for bulk operations."
    ::= { mepMibGroups 42 }

mepStatusDmOneWayNearFarTableInfoGroup OBJECT-GROUP
    OBJECTS     { mepStatusDmOneWayNearFarTxCounter,
                  mepStatusDmOneWayNearFarRxCounter,
                  mepStatusDmOneWayNearFarRxTimeOutCounter,
                  mepStatusDmOneWayNearFarRxErrorCounter,
                  mepStatusDmOneWayNearFarInternalOverflowCounter,
                  mepStatusDmOneWayNearFarAverageDelay,
                  mepStatusDmOneWayNearFarAverageLastnDelay,
                  mepStatusDmOneWayNearFarAverageDelayVariation,
                  mepStatusDmOneWayNearFarAverageLastnDelayVariation,
                  mepStatusDmOneWayNearFarMinimumDelay,
                  mepStatusDmOneWayNearFarMaximumDelay,
                  mepStatusDmOneWayNearFarMinimumDelayVariation,
                  mepStatusDmOneWayNearFarMaximumDelayVariation,
                  mepStatusDmOneWayNearFarTimeUnit }
    STATUS      current
    DESCRIPTION
        "A collection of objects suitable for bulk operations."
    ::= { mepMibGroups 43 }

mepStatusLbTableInfoGroup OBJECT-GROUP
    OBJECTS     { mepStatusLbTransactionId,
                  mepStatusLbReplyCounter,
                  mepStatusLbLbmTransmitted }
    STATUS      current
    DESCRIPTION
        "A collection of objects suitable for bulk operations."
    ::= { mepMibGroups 44 }

mepStatusLbReplyTableInfoGroup OBJECT-GROUP
    OBJECTS     { mepStatusLbReplyMac,
                  mepStatusLbReplyLbrReceived,
                  mepStatusLbReplyOutOfOrder,
                  mepStatusLbReplyMepMipId }
    STATUS      current
    DESCRIPTION
        "A collection of objects suitable for bulk operations."
    ::= { mepMibGroups 45 }

mepStatusTstTableInfoGroup OBJECT-GROUP
    OBJECTS     { mepStatusTstTxCounter,
                  mepStatusTstRxCounter,
                  mepStatusTstOutOfOrderCounter,
                  mepStatusTstRxRate, mepStatusTstTestTime }
    STATUS      current
    DESCRIPTION
        "A collection of objects suitable for bulk operations."
    ::= { mepMibGroups 46 }

mepStatusLtTableInfoGroup OBJECT-GROUP
    OBJECTS     { mepStatusLtTransactionId,
                  mepStatusLtReplyCount }
    STATUS      current
    DESCRIPTION
        "A collection of objects suitable for bulk operations."
    ::= { mepMibGroups 47 }

mepStatusLtReplyTableInfoGroup OBJECT-GROUP
    OBJECTS     { mepStatusLtReplyMode,
                  mepStatusLtReplyDirection,
                  mepStatusLtReplyTtl,
                  mepStatusLtReplyForwarded,
                  mepStatusLtReplyRelayAction,
                  mepStatusLtReplyLastEgressMac,
                  mepStatusLtReplyNextEgressMac }
    STATUS      current
    DESCRIPTION
        "A collection of objects suitable for bulk operations."
    ::= { mepMibGroups 48 }

mepStatusCcPeerTableInfoGroup OBJECT-GROUP
    OBJECTS     { mepStatusCcPeerOsTlvOuiFirst,
                  mepStatusCcPeerOsTlvOuiSecond,
                  mepStatusCcPeerOsTlvOuiThird,
                  mepStatusCcPeerOsTlvSubType,
                  mepStatusCcPeerOsTlvValue,
                  mepStatusCcPeerIsTlvValue,
                  mepStatusCcPeerPsTlvValue,
                  mepStatusCcPeerOsTlvReceived,
                  mepStatusCcPeerIsTlvReceived,
                  mepStatusCcPeerPsTlvReceived }
    STATUS      current
    DESCRIPTION
        "A collection of objects suitable for bulk operations."
    ::= { mepMibGroups 49 }

mepStatusBfdTableInfoGroup OBJECT-GROUP
    OBJECTS     { mepStatusBfdCcTxCnt,
                  mepStatusBfdValidCcRxCnt,
                  mepStatusBfdInvalidCcRxCnt,
                  mepStatusBfdCvTxCnt,
                  mepStatusBfdValidCvRxCnt,
                  mepStatusBfdInvalidCvRxCnt,
                  mepStatusBfdMyDiscr,
                  mepStatusBfdSessionState0,
                  mepStatusBfdSessionState1,
                  mepStatusBfdLocalDiag,
                  mepStatusBfdRemoteSessionState,
                  mepStatusBfdRemoteDiag,
                  mepStatusBfdRemoteDiscr,
                  mepStatusBfdRemoteMinRx,
                  mepStatusBfdRemoteFlags,
                  mepStatusBfdUnexpDiscr,
                  mepStatusBfdExpSrcMepIdTlv,
                  mepStatusBfdUnexpSrcMepIdTlv }
    STATUS      current
    DESCRIPTION
        "A collection of objects suitable for bulk operations."
    ::= { mepMibGroups 50 }

mepStatusRtTableInfoGroup OBJECT-GROUP
    OBJECTS     { mepStatusRtSeqNo, mepStatusRtRequestCount,
                  mepStatusRtReplyCount }
    STATUS      current
    DESCRIPTION
        "A collection of objects suitable for bulk operations."
    ::= { mepMibGroups 51 }

mepStatusRtReplyTableInfoGroup OBJECT-GROUP
    OBJECTS     { mepStatusRtReplyReturnCode,
                  mepStatusRtReplyReturnSubcode,
                  mepStatusRtReplyRttSec,
                  mepStatusRtReplyRttUsec,
                  mepStatusRtReplyTsSentSec,
                  mepStatusRtReplyTsSentUsec,
                  mepStatusRtReplyTsReceivedSec,
                  mepStatusRtReplyTsReceivedUsec,
                  mepStatusRtReplySrcGlobalId,
                  mepStatusRtReplySrcNodeId,
                  mepStatusRtReplyFecSrcValue,
                  mepStatusRtReplyRxIfNum,
                  mepStatusRtReplyRxLabelCnt,
                  mepStatusRtReplyRxLabel1,
                  mepStatusRtReplyRxLabel2,
                  mepStatusRtReplyRxLabel3,
                  mepStatusRtReplyRxLabel4,
                  mepStatusRtReplyRxLabel5,
                  mepStatusRtReplyRxLabel6,
                  mepStatusRtReplyRxLabel7,
                  mepStatusRtReplyRxLabel8 }
    STATUS      current
    DESCRIPTION
        "A collection of objects suitable for bulk operations."
    ::= { mepMibGroups 52 }

mepStatusLmAvailTableInfoGroup OBJECT-GROUP
    OBJECTS     { mepStatusLmAvailNearEndAvailState,
                  mepStatusLmAvailFarEndAvailState,
                  mepStatusLmAvailNearEndAvailCnt,
                  mepStatusLmAvailFarEndAvailCnt,
                  mepStatusLmAvailNearEndUnAvailCnt,
                  mepStatusLmAvailFarEndUnAvailCnt }
    STATUS      current
    DESCRIPTION
        "A collection of objects suitable for bulk operations."
    ::= { mepMibGroups 53 }

mepStatusLmAvailPeerTableInfoGroup OBJECT-GROUP
    OBJECTS     { mepStatusLmAvailPeerNearEndAvailState,
                  mepStatusLmAvailPeerFarEndAvailState,
                  mepStatusLmAvailPeerNearEndAvailCnt,
                  mepStatusLmAvailPeerFarEndAvailCnt,
                  mepStatusLmAvailPeerNearEndUnAvailCnt,
                  mepStatusLmAvailPeerFarEndUnAvailCnt }
    STATUS      current
    DESCRIPTION
        "A collection of objects suitable for bulk operations."
    ::= { mepMibGroups 54 }

mepStatusLmHliTableInfoGroup OBJECT-GROUP
    OBJECTS     { mepStatusLmHliNearEndCnt,
                  mepStatusLmHliFarEndCnt,
                  mepStatusLmHliNearEndConCnt,
                  mepStatusLmHliFarEndConCnt }
    STATUS      current
    DESCRIPTION
        "A collection of objects suitable for bulk operations."
    ::= { mepMibGroups 55 }

mepStatusLmHliPeerTableInfoGroup OBJECT-GROUP
    OBJECTS     { mepStatusLmHliPeerNearEndCnt,
                  mepStatusLmHliPeerFarEndCnt,
                  mepStatusLmHliPeerNearEndConCnt,
                  mepStatusLmHliPeerFarEndConCnt }
    STATUS      current
    DESCRIPTION
        "A collection of objects suitable for bulk operations."
    ::= { mepMibGroups 56 }

mepControlLmTableInfoGroup OBJECT-GROUP
    OBJECTS     { mepControlLmClear }
    STATUS      current
    DESCRIPTION
        "A collection of objects suitable for bulk operations."
    ::= { mepMibGroups 57 }

mepControlDmTableInfoGroup OBJECT-GROUP
    OBJECTS     { mepControlDmClear }
    STATUS      current
    DESCRIPTION
        "A collection of objects suitable for bulk operations."
    ::= { mepMibGroups 58 }

mepControlTstTableInfoGroup OBJECT-GROUP
    OBJECTS     { mepControlTstClear }
    STATUS      current
    DESCRIPTION
        "A collection of objects suitable for bulk operations."
    ::= { mepMibGroups 59 }

mepControlBfdTableInfoGroup OBJECT-GROUP
    OBJECTS     { mepControlBfdClear }
    STATUS      current
    DESCRIPTION
        "A collection of objects suitable for bulk operations."
    ::= { mepMibGroups 60 }

mepMibCompliance MODULE-COMPLIANCE
    STATUS      current
    DESCRIPTION
        "The compliance statement for the implementation."

    MODULE      -- this module

    MANDATORY-GROUPS { mepCapabilitiesInfoGroup,
                       mepConfigInstanceTableInfoGroup,
                       mepConfigInstanceRowEditorInfoGroup,
                       mepConfigInstancePeerTableInfoGroup,
                       mepConfigInstancePeerRowEditorInfoGroup,
                       mepConfigPmTableInfoGroup,
                       mepConfigCcTableInfoGroup,
                       mepConfigCcRowEditorInfoGroup,
                       mepConfigLmTableInfoGroup,
                       mepConfigDmTableInfoGroup,
                       mepConfigLbTableInfoGroup,
                       mepConfigLbRowEditorInfoGroup,
                       mepConfigTstTableInfoGroup,
                       mepConfigTstRowEditorInfoGroup,
                       mepConfigLtTableInfoGroup,
                       mepConfigLtRowEditorInfoGroup,
                       mepConfigApsTableInfoGroup,
                       mepConfigApsRowEditorInfoGroup,
                       mepConfigAisTableInfoGroup,
                       mepConfigAisRowEditorInfoGroup,
                       mepConfigLckTableInfoGroup,
                       mepConfigLckRowEditorInfoGroup,
                       mepConfigClientFlowTableInfoGroup,
                       mepConfigClientFlowRowEditorInfoGroup,
                       mepConfigSyslogTableInfoGroup,
                       mepConfigTlvLeafInfoGroup,
                       mepConfigBfdTableInfoGroup,
                       mepConfigBfdRowEditorInfoGroup,
                       mepConfigBfdAuthTableInfoGroup,
                       mepConfigBfdAuthRowEditorInfoGroup,
                       mepConfigRtTableInfoGroup,
                       mepConfigRtRowEditorInfoGroup,
                       mepConfigLstTableInfoGroup,
                       mepConfigLmAvailTableInfoGroup,
                       mepConfigLmHliTableInfoGroup,
                       mepConfigLmSdegTableInfoGroup,
                       mepStatusInstanceTableInfoGroup,
                       mepStatusInstancePeerTableInfoGroup,
                       mepStatusLmTableInfoGroup,
                       mepStatusLmPeerTableInfoGroup,
                       mepStatusDmTwoWayTableInfoGroup,
                       mepStatusDmOneWayFarNearTableInfoGroup,
                       mepStatusDmOneWayNearFarTableInfoGroup,
                       mepStatusLbTableInfoGroup,
                       mepStatusLbReplyTableInfoGroup,
                       mepStatusTstTableInfoGroup,
                       mepStatusLtTableInfoGroup,
                       mepStatusLtReplyTableInfoGroup,
                       mepStatusCcPeerTableInfoGroup,
                       mepStatusBfdTableInfoGroup,
                       mepStatusRtTableInfoGroup,
                       mepStatusRtReplyTableInfoGroup,
                       mepStatusLmAvailTableInfoGroup,
                       mepStatusLmAvailPeerTableInfoGroup,
                       mepStatusLmHliTableInfoGroup,
                       mepStatusLmHliPeerTableInfoGroup,
                       mepControlLmTableInfoGroup,
                       mepControlDmTableInfoGroup,
                       mepControlTstTableInfoGroup,
                       mepControlBfdTableInfoGroup }

    ::= { mepMibCompliances 1 }

END
