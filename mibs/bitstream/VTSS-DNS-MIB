-- *****************************************************************
-- DNS-MIB:  Vitesse private MIB
--
-- Copyright (c) 2002-2013 Vitesse Semiconductor Corporation "Vitesse".
-- All Rights Reserved.
--
-- ****************************************************************

VTSS-DNS-MIB DEFINITIONS ::= BEGIN

IMPORTS
    MODULE-COMPLIANCE, OBJECT-GROUP
        FROM SNMPv2-CONF
    MODULE-IDENTITY, OBJECT-TYPE
        FROM SNMPv2-SMI
    TEXTUAL-CONVENTION
        FROM SNMPv2-TC
    vtssSwitchMgmt
        FROM VTSS-SMI
    Unsigned32 FROM SNMPv2-SMI
    TruthValue FROM SNMPv2-TC
    VTSSDisplayString FROM VTSS-TC
    VTSSInterfaceIndex FROM VTSS-TC
    VTSSIpAddress FROM VTSS-TC
    ;

vtssDnsMib MODULE-IDENTITY
    LAST-UPDATED "201411250000Z"
    ORGANIZATION
        "Vitesse Semiconductor Corporation"
    CONTACT-INFO
        "Application support <application_support@vitesse.com>"
    DESCRIPTION
        "This is a private version of the DNS MIB."
    REVISION    "201411250000Z"
    DESCRIPTION
        "Support multiple DNS server settings and default domain name
         configuration."
    REVISION    "201407010000Z"
    DESCRIPTION
        "Initial version."
    ::= { vtssSwitchMgmt 53 }


VTSSDnsConfigType ::= TEXTUAL-CONVENTION
    STATUS      current
    DESCRIPTION
        "This enumeration indicates the configured DNS server type or default
         domain name type."
    SYNTAX      INTEGER { none(0), static(1), dhcpv4(2), dhcpv4Vlan(3), dhcpv6(4), dhcpv6Vlan(5) }

vtssDnsMibObjects OBJECT IDENTIFIER
    ::= { vtssDnsMib 1 }

vtssDnsCapabilities OBJECT IDENTIFIER
    ::= { vtssDnsMibObjects 1 }

vtssDnsCapabilitiesSupportDhcp4ConfigServer OBJECT-TYPE
    SYNTAX      TruthValue
    MAX-ACCESS  read-only
    STATUS      current
    DESCRIPTION 
        "The capability to support setting DNS server from DHCPv4."
    ::= { vtssDnsCapabilities 1 }

vtssDnsCapabilitiesSupportDhcp6ConfigServer OBJECT-TYPE
    SYNTAX      TruthValue
    MAX-ACCESS  read-only
    STATUS      current
    DESCRIPTION 
        "The capability to support setting DNS server from DHCPv6."
    ::= { vtssDnsCapabilities 2 }

vtssDnsCapabilitiesSupportDefaultDomainName OBJECT-TYPE
    SYNTAX      TruthValue
    MAX-ACCESS  read-only
    STATUS      current
    DESCRIPTION 
        "The capability to support setting default domain name."
    ::= { vtssDnsCapabilities 3 }

vtssDnsCapabilitiesSupportDhcp4DomainName OBJECT-TYPE
    SYNTAX      TruthValue
    MAX-ACCESS  read-only
    STATUS      current
    DESCRIPTION 
        "The capability to support setting default domain name from DHCPv4."
    ::= { vtssDnsCapabilities 4 }

vtssDnsCapabilitiesSupportDhcp6DomainName OBJECT-TYPE
    SYNTAX      TruthValue
    MAX-ACCESS  read-only
    STATUS      current
    DESCRIPTION 
        "The capability to support setting default domain name from DHCPv6."
    ::= { vtssDnsCapabilities 5 }

vtssDnsConfig OBJECT IDENTIFIER
    ::= { vtssDnsMibObjects 2 }

vtssDnsConfigGlobals OBJECT IDENTIFIER
    ::= { vtssDnsConfig 1 }

vtssDnsConfigGlobalsProxy OBJECT IDENTIFIER
    ::= { vtssDnsConfigGlobals 1 }

vtssDnsConfigGlobalsProxyAdminState OBJECT-TYPE
    SYNTAX      TruthValue
    MAX-ACCESS  read-write
    STATUS      current
    DESCRIPTION 
        "Enable/Disable the DNS-Proxy feature."
    ::= { vtssDnsConfigGlobalsProxy 1 }

vtssDnsConfigGlobalsDefaultDomainName OBJECT IDENTIFIER
    ::= { vtssDnsConfigGlobals 2 }

vtssDnsConfigGlobalsDefaultDomainNameSetting OBJECT-TYPE
    SYNTAX      VTSSDnsConfigType
    MAX-ACCESS  read-write
    STATUS      current
    DESCRIPTION 
        "Default domain name administrative type. A default domain name is used
         as the suffix of the given name in DNS lookup. none(0) means no default
         domain name is used and thus no domain name suffix is appended in DNS
         lookup. static(1) means the default domain name will be manually set.
         dhcpv4(2) means default domain name will be determined by DHCPv4
         discovery. dhcpv4Vlan(3) means default domain name will be determined
         by DHCPv4 discovery on a specific IP VLAN interface. dhcpv6(4) means
         default domain name will be determined by DHCPv6 discovery.
         dhcpv6Vlan(5) means default domain name will be determined by DHCPv6
         discovery on a specific IP VLAN interface."
    ::= { vtssDnsConfigGlobalsDefaultDomainName 1 }

vtssDnsConfigGlobalsDefaultDomainNameStaticName OBJECT-TYPE
    SYNTAX      VTSSDisplayString (SIZE(0..254))
    MAX-ACCESS  read-write
    STATUS      current
    DESCRIPTION 
        "The static default domain name. It will be a reference only when
         DomainNameSetting is static(1)."
    ::= { vtssDnsConfigGlobalsDefaultDomainName 2 }

vtssDnsConfigGlobalsDefaultDomainNameDhcpIfIndex OBJECT-TYPE
    SYNTAX      VTSSInterfaceIndex
    MAX-ACCESS  read-write
    STATUS      current
    DESCRIPTION 
        "The ifIndex of specific VLAN interface that default domain name will be
         retrieved from DHCP. It will be a reference only when DomainNameSetting
         is either dhcpv4Vlan(3) or dhcpv6Vlan(5)."
    ::= { vtssDnsConfigGlobalsDefaultDomainName 3 }

vtssDnsConfigServers OBJECT IDENTIFIER
    ::= { vtssDnsConfig 2 }

vtssDnsConfigServersTable OBJECT-TYPE
    SYNTAX      SEQUENCE OF VTSSDnsConfigServersEntry
    MAX-ACCESS  not-accessible
    STATUS      current
    DESCRIPTION 
        "This is a table for managing DNS server configuration."
    ::= { vtssDnsConfigServers 1 }

vtssDnsConfigServersEntry OBJECT-TYPE
    SYNTAX      VTSSDnsConfigServersEntry
    MAX-ACCESS  not-accessible
    STATUS      current
    DESCRIPTION 
        "Each entry has a set of parameters."
    INDEX       { vtssDnsConfigServersPrecedence }
    ::= { vtssDnsConfigServersTable 1 }

VTSSDnsConfigServersEntry ::= SEQUENCE {
    vtssDnsConfigServersPrecedence      Unsigned32,
    vtssDnsConfigServersSetting     VTSSDnsConfigType,
    vtssDnsConfigServersStaticIpAddress     VTSSIpAddress,
    vtssDnsConfigServersStaticIfIndex   VTSSInterfaceIndex
}

vtssDnsConfigServersPrecedence OBJECT-TYPE
    SYNTAX      Unsigned32 (0..3)
    MAX-ACCESS  not-accessible
    STATUS      current
    DESCRIPTION 
        "Table index also represents the precedence in selecting target DNS
         server: less index value means higher priority in round-robin
         selection. Only one server is working at a time, that is when the
         chosen server is active, system marks the designated server as target
         and stops selection. When the active server becomes inactive, system
         starts another round of selection starting from the next available
         server setting."
    ::= { vtssDnsConfigServersEntry 1 }

vtssDnsConfigServersSetting OBJECT-TYPE
    SYNTAX      VTSSDnsConfigType
    MAX-ACCESS  read-write
    STATUS      current
    DESCRIPTION 
        "Per precedence DNS server administrative type. The DNS server setting
         will be used in DNS lookup. none(0) denotes no DNS server is used and
         thus domain name lookup always fails. static(1) denotes the DNS server
         address will be manually set, in either IPv4 or IPv6 address form.
         dhcpv4(2) denotes DNS server address will be determined by DHCPv4
         discovery. dhcpv4Vlan(3) denotes DNS server address will be determined
         by DHCPv4 discovery on a specifc IP VLAN interface. dhcpv6(4) denotes
         DNS server address will be determined by DHCPv6 discovery.
         dhcpv6Vlan(5) denotes DNS server address will be determined by DHCPv6
         discovery on a specifc IP VLAN interface."
    ::= { vtssDnsConfigServersEntry 2 }

vtssDnsConfigServersStaticIpAddress OBJECT-TYPE
    SYNTAX      VTSSIpAddress
    MAX-ACCESS  read-write
    STATUS      current
    DESCRIPTION 
        "The static DNS server address. It will be a reference only when Setting
         is static(1)"
    ::= { vtssDnsConfigServersEntry 3 }

vtssDnsConfigServersStaticIfIndex OBJECT-TYPE
    SYNTAX      VTSSInterfaceIndex
    MAX-ACCESS  read-write
    STATUS      current
    DESCRIPTION 
        "The ifIndex of specific VLAN interface that DNS server address will be
         retrieved from DHCP and where the server resides. It will be a
         reference only when Setting is either dhcpv4Vlan(3) or dhcpv6Vlan(5)."
    ::= { vtssDnsConfigServersEntry 4 }

vtssDnsStatus OBJECT IDENTIFIER
    ::= { vtssDnsMibObjects 3 }

vtssDnsStatusGlobals OBJECT IDENTIFIER
    ::= { vtssDnsStatus 1 }

vtssDnsStatusGlobalsDefaultDomainName OBJECT IDENTIFIER
    ::= { vtssDnsStatusGlobals 1 }

vtssDnsStatusGlobalsDefaultDomainNameSuffix OBJECT-TYPE
    SYNTAX      VTSSDisplayString (SIZE(0..254))
    MAX-ACCESS  read-only
    STATUS      current
    DESCRIPTION 
        "The suffix of the given domain name used in DNS lookup."
    ::= { vtssDnsStatusGlobalsDefaultDomainName 1 }

vtssDnsStatusServers OBJECT IDENTIFIER
    ::= { vtssDnsStatus 2 }

vtssDnsStatusServersTable OBJECT-TYPE
    SYNTAX      SEQUENCE OF VTSSDnsStatusServersEntry
    MAX-ACCESS  not-accessible
    STATUS      current
    DESCRIPTION 
        "This is a table for displaying DNS server information."
    ::= { vtssDnsStatusServers 1 }

vtssDnsStatusServersEntry OBJECT-TYPE
    SYNTAX      VTSSDnsStatusServersEntry
    MAX-ACCESS  not-accessible
    STATUS      current
    DESCRIPTION 
        "Each entry has a set of parameters."
    INDEX       { vtssDnsStatusServersPrecedence }
    ::= { vtssDnsStatusServersTable 1 }

VTSSDnsStatusServersEntry ::= SEQUENCE {
    vtssDnsStatusServersPrecedence      Unsigned32,
    vtssDnsStatusServersConfiguredType      VTSSDnsConfigType,
    vtssDnsStatusServersReferenceIfIndex    VTSSInterfaceIndex,
    vtssDnsStatusServersIpAddress   VTSSIpAddress
}

vtssDnsStatusServersPrecedence OBJECT-TYPE
    SYNTAX      Unsigned32 (0..3)
    MAX-ACCESS  not-accessible
    STATUS      current
    DESCRIPTION 
        "Table index also represents the precedence in selecting target DNS
         server: less index value means higher priority in round-robin
         selection. Only one server is working at a time, that is when the
         chosen server is active, system marks the designated server as target
         and stops selection. When the active server becomes inactive, system
         starts another round of selection starting from the next available
         server setting."
    ::= { vtssDnsStatusServersEntry 1 }

vtssDnsStatusServersConfiguredType OBJECT-TYPE
    SYNTAX      VTSSDnsConfigType
    MAX-ACCESS  read-only
    STATUS      current
    DESCRIPTION 
        "Per precedence DNS server configured type.none(0) denotes no DNS server
         is used and thus domain name lookup always fails. static(1) denotes the
         DNS server address will be manually set, in either IPv4 or IPv6 address
         form. dhcpv4(2) denotes DNS server address will be determined by DHCPv4
         discovery. dhcpv4Vlan(3) denotes DNS server address will be determined
         by DHCPv4 discovery on a specifc IP VLAN interface. dhcpv6(4) denotes
         DNS server address will be determined by DHCPv6 discovery.
         dhcpv6Vlan(5) denotes DNS server address will be determined by DHCPv6
         discovery on a specifc IP VLAN interface."
    ::= { vtssDnsStatusServersEntry 2 }

vtssDnsStatusServersReferenceIfIndex OBJECT-TYPE
    SYNTAX      VTSSInterfaceIndex
    MAX-ACCESS  read-only
    STATUS      current
    DESCRIPTION 
        "The ifIndex of specific VLAN interface that DNS server address will be
         retrieved from DHCP and where the server resides. It will be a
         reference only when Setting is either dhcpv4Vlan(3) or dhcpv6Vlan(5)."
    ::= { vtssDnsStatusServersEntry 3 }

vtssDnsStatusServersIpAddress OBJECT-TYPE
    SYNTAX      VTSSIpAddress
    MAX-ACCESS  read-only
    STATUS      current
    DESCRIPTION 
        "The DNS server address that will be used for domain name lookup."
    ::= { vtssDnsStatusServersEntry 4 }

vtssDnsMibConformance OBJECT IDENTIFIER
    ::= { vtssDnsMib 2 }

vtssDnsMibCompliances OBJECT IDENTIFIER
    ::= { vtssDnsMibConformance 1 }

vtssDnsMibGroups OBJECT IDENTIFIER
    ::= { vtssDnsMibConformance 2 }

vtssDnsCapabilitiesInfoGroup OBJECT-GROUP
    OBJECTS     { vtssDnsCapabilitiesSupportDhcp4ConfigServer, 
                  vtssDnsCapabilitiesSupportDhcp6ConfigServer, 
                  vtssDnsCapabilitiesSupportDefaultDomainName, 
                  vtssDnsCapabilitiesSupportDhcp4DomainName, 
                  vtssDnsCapabilitiesSupportDhcp6DomainName }
    STATUS      current
    DESCRIPTION
        "A collection of objects suitable for bulk operations."
    ::= { vtssDnsMibGroups 1 }

vtssDnsConfigGlobalsProxyInfoGroup OBJECT-GROUP
    OBJECTS     { vtssDnsConfigGlobalsProxyAdminState }
    STATUS      current
    DESCRIPTION
        "A collection of objects suitable for bulk operations."
    ::= { vtssDnsMibGroups 2 }

vtssDnsConfigGlobalsDefaultDomainNameInfoGroup OBJECT-GROUP
    OBJECTS     { vtssDnsConfigGlobalsDefaultDomainNameSetting, 
                  vtssDnsConfigGlobalsDefaultDomainNameStaticName, 
                  vtssDnsConfigGlobalsDefaultDomainNameDhcpIfIndex }
    STATUS      current
    DESCRIPTION
        "A collection of objects suitable for bulk operations."
    ::= { vtssDnsMibGroups 3 }

vtssDnsConfigServersTableInfoGroup OBJECT-GROUP
    OBJECTS     { vtssDnsConfigServersSetting, 
                  vtssDnsConfigServersStaticIpAddress, 
                  vtssDnsConfigServersStaticIfIndex }
    STATUS      current
    DESCRIPTION
        "A collection of objects suitable for bulk operations."
    ::= { vtssDnsMibGroups 4 }

vtssDnsStatusGlobalsDefaultDomainNameInfoGroup OBJECT-GROUP
    OBJECTS     { vtssDnsStatusGlobalsDefaultDomainNameSuffix }
    STATUS      current
    DESCRIPTION
        "A collection of objects suitable for bulk operations."
    ::= { vtssDnsMibGroups 5 }

vtssDnsStatusServersTableInfoGroup OBJECT-GROUP
    OBJECTS     { vtssDnsStatusServersConfiguredType, 
                  vtssDnsStatusServersReferenceIfIndex, 
                  vtssDnsStatusServersIpAddress }
    STATUS      current
    DESCRIPTION
        "A collection of objects suitable for bulk operations."
    ::= { vtssDnsMibGroups 6 }

vtssDnsMibCompliance MODULE-COMPLIANCE
    STATUS      current
    DESCRIPTION
        "The compliance statement for the implementation."

    MODULE      -- this module

        MANDATORY-GROUPS        { vtssDnsCapabilitiesInfoGroup, 
                  vtssDnsConfigGlobalsProxyInfoGroup, 
                  vtssDnsConfigGlobalsDefaultDomainNameInfoGroup, 
                  vtssDnsConfigServersTableInfoGroup, 
                  vtssDnsStatusGlobalsDefaultDomainNameInfoGroup, 
                  vtssDnsStatusServersTableInfoGroup }

    ::= { vtssDnsMibCompliances 1 }

END
