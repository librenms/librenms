-- *****************************************************************
-- FAN-MIB:  Vitesse private MIB
--
-- Copyright (c) 2002-2013 Vitesse Semiconductor Corporation "Vitesse".
-- All Rights Reserved.
--
-- ****************************************************************

VTSS-FAN-MIB DEFINITIONS ::= BEGIN

IMPORTS
    MODULE-COMPLIANCE, OBJECT-GROUP
        FROM SNMPv2-CONF
    MODULE-IDENTITY, OBJECT-TYPE
        FROM SNMPv2-SMI
    TEXTUAL-CONVENTION
        FROM SNMPv2-TC
    vtssSwitchMgmt
        FROM VTSS-SMI
    VTSSUnsigned8 FROM VTSS-TC
    VTSSInteger16 FROM VTSS-TC
    Integer32 FROM SNMPv2-SMI
    VTSSUnsigned16 FROM VTSS-TC
    ;

vtssFanMib MODULE-IDENTITY
    LAST-UPDATED "201405220000Z"
    ORGANIZATION
        "Vitesse Semiconductor Corporation"
    CONTACT-INFO
        "Application Support <application_support@vitesse.com>"
    DESCRIPTION
        "This is a private MIB for controlling fan speed, in order to reduce
         noise and power consumption"
    REVISION    "201405220000Z"
    DESCRIPTION
        "Initial version"
    ::= { vtssSwitchMgmt 75 }


vtssFanMibObjects OBJECT IDENTIFIER
    ::= { vtssFanMib 1 }

vtssFanCapabilities OBJECT IDENTIFIER
    ::= { vtssFanMibObjects 1 }

vtssFanCapabilitiesSensorCount OBJECT-TYPE
    SYNTAX      VTSSUnsigned8
    MAX-ACCESS  read-only
    STATUS      current
    DESCRIPTION 
        "Maximum supported temperature sensors in a switch. "
    ::= { vtssFanCapabilities 1 }

vtssFanConfig OBJECT IDENTIFIER
    ::= { vtssFanMibObjects 2 }

vtssFanConfigGlobals OBJECT IDENTIFIER
    ::= { vtssFanConfig 1 }

vtssFanConfigGlobalsMaxSpeedTemperature OBJECT-TYPE
    SYNTAX      VTSSInteger16 (-127..127)
    MAX-ACCESS  read-write
    STATUS      current
    DESCRIPTION 
        "The temperature(in C) where fan shall be running at full speed (maximum
         cooling). Valid range:-127 to 127"
    ::= { vtssFanConfigGlobals 1 }

vtssFanConfigGlobalsOnTemperature OBJECT-TYPE
    SYNTAX      VTSSInteger16 (-127..127)
    MAX-ACCESS  read-write
    STATUS      current
    DESCRIPTION 
        "The temperature(in C) where cooling is needed (fan is started). Valid
         range:-127 to 127"
    ::= { vtssFanConfigGlobals 2 }

vtssFanStatus OBJECT IDENTIFIER
    ::= { vtssFanMibObjects 3 }

vtssFanStatusSpeedTable OBJECT-TYPE
    SYNTAX      SEQUENCE OF VTSSFanStatusSpeedEntry
    MAX-ACCESS  not-accessible
    STATUS      current
    DESCRIPTION 
        "This is a table for switch fan speed"
    ::= { vtssFanStatus 1 }

vtssFanStatusSpeedEntry OBJECT-TYPE
    SYNTAX      VTSSFanStatusSpeedEntry
    MAX-ACCESS  not-accessible
    STATUS      current
    DESCRIPTION 
        "Each switch have fan module"
    INDEX       { vtssFanStatusSpeedSwitchId }
    ::= { vtssFanStatusSpeedTable 1 }

VTSSFanStatusSpeedEntry ::= SEQUENCE {
    vtssFanStatusSpeedSwitchId      Integer32,
    vtssFanStatusSpeedRunning   VTSSUnsigned16
}

vtssFanStatusSpeedSwitchId OBJECT-TYPE
    SYNTAX      Integer32 (1..16)
    MAX-ACCESS  not-accessible
    STATUS      current
    DESCRIPTION 
        "The identification of switch. For non-stackable switch, the valid value
         is limited to 1."
    ::= { vtssFanStatusSpeedEntry 1 }

vtssFanStatusSpeedRunning OBJECT-TYPE
    SYNTAX      VTSSUnsigned16
    MAX-ACCESS  read-only
    STATUS      current
    DESCRIPTION 
        "The fan speed, currently running (in RPM)."
    ::= { vtssFanStatusSpeedEntry 3 }

vtssFanStatusSensorTable OBJECT-TYPE
    SYNTAX      SEQUENCE OF VTSSFanStatusSensorEntry
    MAX-ACCESS  not-accessible
    STATUS      current
    DESCRIPTION 
        "This is a table to chip temperature"
    ::= { vtssFanStatus 2 }

vtssFanStatusSensorEntry OBJECT-TYPE
    SYNTAX      VTSSFanStatusSensorEntry
    MAX-ACCESS  not-accessible
    STATUS      current
    DESCRIPTION 
        "Each switch have temperature sensor status"
    INDEX       { vtssFanStatusSensorSwitchId, vtssFanStatusSensorIndex }
    ::= { vtssFanStatusSensorTable 1 }

VTSSFanStatusSensorEntry ::= SEQUENCE {
    vtssFanStatusSensorSwitchId     Integer32,
    vtssFanStatusSensorIndex    Integer32,
    vtssFanStatusSensorChipTemp     VTSSInteger16
}

vtssFanStatusSensorSwitchId OBJECT-TYPE
    SYNTAX      Integer32 (1..16)
    MAX-ACCESS  not-accessible
    STATUS      current
    DESCRIPTION 
        "The identification of switch. For non-stackable switch, the valid value
         is limited to 1."
    ::= { vtssFanStatusSensorEntry 1 }

vtssFanStatusSensorIndex OBJECT-TYPE
    SYNTAX      Integer32 (0..4)
    MAX-ACCESS  not-accessible
    STATUS      current
    DESCRIPTION 
        "The temperature sensor index. Some switches may also have more than one
         temperature sensor."
    ::= { vtssFanStatusSensorEntry 2 }

vtssFanStatusSensorChipTemp OBJECT-TYPE
    SYNTAX      VTSSInteger16
    MAX-ACCESS  read-only
    STATUS      current
    DESCRIPTION 
        "Current chip temperature (in C)."
    ::= { vtssFanStatusSensorEntry 4 }

vtssFanMibConformance OBJECT IDENTIFIER
    ::= { vtssFanMib 2 }

vtssFanMibCompliances OBJECT IDENTIFIER
    ::= { vtssFanMibConformance 1 }

vtssFanMibGroups OBJECT IDENTIFIER
    ::= { vtssFanMibConformance 2 }

vtssFanCapabilitiesInfoGroup OBJECT-GROUP
    OBJECTS     { vtssFanCapabilitiesSensorCount }
    STATUS      current
    DESCRIPTION
        "A collection of objects suitable for bulk operations."
    ::= { vtssFanMibGroups 1 }

vtssFanConfigGlobalsInfoGroup OBJECT-GROUP
    OBJECTS     { vtssFanConfigGlobalsMaxSpeedTemperature, 
                  vtssFanConfigGlobalsOnTemperature }
    STATUS      current
    DESCRIPTION
        "A collection of objects suitable for bulk operations."
    ::= { vtssFanMibGroups 2 }

vtssFanStatusSpeedInfoGroup OBJECT-GROUP
    OBJECTS     { vtssFanStatusSpeedRunning }
    STATUS      current
    DESCRIPTION
        "A collection of objects suitable for bulk operations."
    ::= { vtssFanMibGroups 3 }

vtssFanStatusSensorInfoGroup OBJECT-GROUP
    OBJECTS     { vtssFanStatusSensorChipTemp }
    STATUS      current
    DESCRIPTION
        "A collection of objects suitable for bulk operations."
    ::= { vtssFanMibGroups 4 }

vtssFanMibCompliance MODULE-COMPLIANCE
    STATUS      current
    DESCRIPTION
        "The compliance statement for the implementation."

    MODULE      -- this module

        MANDATORY-GROUPS        { vtssFanCapabilitiesInfoGroup, 
                  vtssFanConfigGlobalsInfoGroup, vtssFanStatusSpeedInfoGroup, 
                  vtssFanStatusSensorInfoGroup }

    ::= { vtssFanMibCompliances 1 }

END
