-- *****************************************************************
-- POE-MIB:  Vitesse private MIB
--
-- Copyright (c) 2002-2013 Vitesse Semiconductor Corporation "Vitesse".
-- All Rights Reserved.
--
-- ****************************************************************

VTSS-POE-MIB DEFINITIONS ::= BEGIN

IMPORTS
    MODULE-COMPLIANCE, OBJECT-GROUP
        FROM SNMPv2-CONF
    MODULE-IDENTITY, OBJECT-TYPE
        FROM SNMPv2-SMI
    TEXTUAL-CONVENTION
        FROM SNMPv2-TC
    vtssSwitchMgmt
        FROM VTSS-SMI
    Integer32 FROM SNMPv2-SMI
    Unsigned32 FROM SNMPv2-SMI
    TruthValue FROM SNMPv2-TC
    VTSSInterfaceIndex FROM VTSS-TC
    ;

vtssPoeMib MODULE-IDENTITY
    LAST-UPDATED "201408200000Z"
    ORGANIZATION
        "Vitesse Semiconductor Corporation"
    CONTACT-INFO
        "Application support <application_support@vitesse.com>"
    DESCRIPTION
        "This is a private version of Power over Ethernet(PoE). "
    REVISION    "201408200000Z"
    DESCRIPTION
        "Initial version"
    ::= { vtssSwitchMgmt 43 }


VTSSpoeMgmtModeType ::= TEXTUAL-CONVENTION
    STATUS      current
    DESCRIPTION
        "This enumeration defines the types of PoE management mode."
    SYNTAX      INTEGER { classReservedPower(0), classConsumption(1), allocatedReservedPower(2), allocatedConsumption(3), lldpReservedPower(4), lldpConsumption(5) }

VTSSpoeModeType ::= TEXTUAL-CONVENTION
    STATUS      current
    DESCRIPTION
        "This enumeration defines the types of port PoE mode."
    SYNTAX      INTEGER { disable(0), poeDot3af(1), poePlusDot3at(2) }

VTSSpoePowerPriorityType ::= TEXTUAL-CONVENTION
    STATUS      current
    DESCRIPTION
        "This enumeration defines the port power priority."
    SYNTAX      INTEGER { low(0), high(1), critical(2) }

VTSSpoeStatusType ::= TEXTUAL-CONVENTION
    STATUS      current
    DESCRIPTION
        "This enumeration defines the feature status."
    SYNTAX      INTEGER { notSupported(0), budgetExceeded(1), noPoweredDeviceDetected(2), poweredDeviceOn(3), poweredDeviceOff(4), poweredDeviceOverloaded(5), unknownState(6), disabled(7) }

vtssPoeMibObjects OBJECT IDENTIFIER
    ::= { vtssPoeMib 1 }

vtssPoeCapabilities OBJECT IDENTIFIER
    ::= { vtssPoeMibObjects 1 }

vtssPoeCapabilitiesInterfaceTable OBJECT-TYPE
    SYNTAX      SEQUENCE OF VTSSPoeCapabilitiesInterfaceEntry
    MAX-ACCESS  not-accessible
    STATUS      current
    DESCRIPTION 
        "This is a table to interface capabilities"
    ::= { vtssPoeCapabilities 1 }

vtssPoeCapabilitiesInterfaceEntry OBJECT-TYPE
    SYNTAX      VTSSPoeCapabilitiesInterfaceEntry
    MAX-ACCESS  not-accessible
    STATUS      current
    DESCRIPTION 
        "Each interface has a set of capability parameters"
    INDEX       { vtssPoeCapabilitiesInterfaceIfIndex }
    ::= { vtssPoeCapabilitiesInterfaceTable 1 }

VTSSPoeCapabilitiesInterfaceEntry ::= SEQUENCE {
    vtssPoeCapabilitiesInterfaceIfIndex     VTSSInterfaceIndex,
    vtssPoeCapabilitiesInterfacePoE     TruthValue
}

vtssPoeCapabilitiesInterfaceIfIndex OBJECT-TYPE
    SYNTAX      VTSSInterfaceIndex
    MAX-ACCESS  not-accessible
    STATUS      current
    DESCRIPTION 
        "Logical interface number."
    ::= { vtssPoeCapabilitiesInterfaceEntry 1 }

vtssPoeCapabilitiesInterfacePoE OBJECT-TYPE
    SYNTAX      TruthValue
    MAX-ACCESS  read-only
    STATUS      current
    DESCRIPTION 
        "Indicates whether interface is PoE capable or not."
    ::= { vtssPoeCapabilitiesInterfaceEntry 2 }

vtssPoeConfig OBJECT IDENTIFIER
    ::= { vtssPoeMibObjects 2 }

vtssPoeConfigGlobals OBJECT IDENTIFIER
    ::= { vtssPoeConfig 1 }

vtssPoeConfigGlobalsManagementMode OBJECT-TYPE
    SYNTAX      VTSSpoeMgmtModeType
    MAX-ACCESS  read-write
    STATUS      current
    DESCRIPTION 
        "PoE management modes, six PoE management modes are supported.
         CLASS_RESERVED: Maximum port power determined by class, and power is
         managed according to power consumption. CLASS_CONSUMP: Maximum port
         power determined by class, and power is managed according to reserved
         power. ALLOCATED_RESERVED: Maximum port power determined by allocation,
         and power is managed according to power consumption. ALLOCATED_CONSUMP:
         Maximum port power determined by allocation, and power is managed
         according to reserved power. LLDPMED_RESERVED: Maximum port power
         determined by LLDP Media protocol, and power is managed according to
         reserved power. LLDPMED_CONSUMP: Maximum port power determined by LLDP
         Media protocol, and power is managed according to power consumption."
    ::= { vtssPoeConfigGlobals 1 }

vtssPoeConfigSwitch OBJECT IDENTIFIER
    ::= { vtssPoeConfig 2 }

vtssPoeConfigSwitchParamTable OBJECT-TYPE
    SYNTAX      SEQUENCE OF VTSSPoeConfigSwitchParamEntry
    MAX-ACCESS  not-accessible
    STATUS      current
    DESCRIPTION 
        "This is a table to configure PoE configurations for a switch."
    ::= { vtssPoeConfigSwitch 1 }

vtssPoeConfigSwitchParamEntry OBJECT-TYPE
    SYNTAX      VTSSPoeConfigSwitchParamEntry
    MAX-ACCESS  not-accessible
    STATUS      current
    DESCRIPTION 
        "Each switch has a set of PoE configurable parameters"
    INDEX       { vtssPoeConfigSwitchParamSwitchId }
    ::= { vtssPoeConfigSwitchParamTable 1 }

VTSSPoeConfigSwitchParamEntry ::= SEQUENCE {
    vtssPoeConfigSwitchParamSwitchId    Unsigned32,
    vtssPoeConfigSwitchParamMaxPower    Integer32,
    vtssPoeConfigSwitchParamCapacitorDetection      TruthValue
}

vtssPoeConfigSwitchParamSwitchId OBJECT-TYPE
    SYNTAX      Unsigned32 (1..16)
    MAX-ACCESS  not-accessible
    STATUS      current
    DESCRIPTION 
        "User Switch Id."
    ::= { vtssPoeConfigSwitchParamEntry 1 }

vtssPoeConfigSwitchParamMaxPower OBJECT-TYPE
    SYNTAX      Integer32 (0..2000)
    MAX-ACCESS  read-write
    STATUS      current
    DESCRIPTION 
        "The Maximum power(in Watt) that the power sourcing equipment(such as
         switch) can deliver."
    ::= { vtssPoeConfigSwitchParamEntry 2 }

vtssPoeConfigSwitchParamCapacitorDetection OBJECT-TYPE
    SYNTAX      TruthValue
    MAX-ACCESS  read-write
    STATUS      current
    DESCRIPTION 
        "Indicates whether switch capacitor detection feature is enabled or not."
    ::= { vtssPoeConfigSwitchParamEntry 3 }

vtssPoeConfigInterface OBJECT IDENTIFIER
    ::= { vtssPoeConfig 3 }

vtssPoeConfigInterfaceParamTable OBJECT-TYPE
    SYNTAX      SEQUENCE OF VTSSPoeConfigInterfaceParamEntry
    MAX-ACCESS  not-accessible
    STATUS      current
    DESCRIPTION 
        "This is a table to configure PoE configurations for a specific
         interface."
    ::= { vtssPoeConfigInterface 1 }

vtssPoeConfigInterfaceParamEntry OBJECT-TYPE
    SYNTAX      VTSSPoeConfigInterfaceParamEntry
    MAX-ACCESS  not-accessible
    STATUS      current
    DESCRIPTION 
        "Each interface has a set of PoE configurable parameters"
    INDEX       { vtssPoeConfigInterfaceParamIfIndex }
    ::= { vtssPoeConfigInterfaceParamTable 1 }

VTSSPoeConfigInterfaceParamEntry ::= SEQUENCE {
    vtssPoeConfigInterfaceParamIfIndex      VTSSInterfaceIndex,
    vtssPoeConfigInterfaceParamMode     VTSSpoeModeType,
    vtssPoeConfigInterfaceParamPriority     VTSSpoePowerPriorityType,
    vtssPoeConfigInterfaceParamMaxPower     Integer32
}

vtssPoeConfigInterfaceParamIfIndex OBJECT-TYPE
    SYNTAX      VTSSInterfaceIndex
    MAX-ACCESS  not-accessible
    STATUS      current
    DESCRIPTION 
        "Logical interface number."
    ::= { vtssPoeConfigInterfaceParamEntry 1 }

vtssPoeConfigInterfaceParamMode OBJECT-TYPE
    SYNTAX      VTSSpoeModeType
    MAX-ACCESS  read-write
    STATUS      current
    DESCRIPTION 
        "Set PoE mode or disable PoE feature, two PoE modes are supported. POE:
         Enables PoE based on IEEE 802.3af standard, and provides power up to
         15.4W(154 deciwatt) of DC power to powered device. When changing to
         standard mode the MaxPower is automatically adjust to 15.4 W, if it
         currently exceeds 15.4 W. POE_PLUS: Enabled PoE based on IEEE 802.3at
         standard, and provides power up to 30W(300 deciwatt) of DC power to
         powered device."
    ::= { vtssPoeConfigInterfaceParamEntry 2 }

vtssPoeConfigInterfaceParamPriority OBJECT-TYPE
    SYNTAX      VTSSpoePowerPriorityType
    MAX-ACCESS  read-write
    STATUS      current
    DESCRIPTION 
        "Set port power priority. Priority determines the order in which the
         interfaces will receive power. Interfaces with a higher priority will
         receive power before interfaces with a lower priority. PRIORITY_LOW
         means lowest priority. PRIORITY_HIGH means medium priority.
         PRIORITY_CRITICAL means highest priority."
    ::= { vtssPoeConfigInterfaceParamEntry 3 }

vtssPoeConfigInterfaceParamMaxPower OBJECT-TYPE
    SYNTAX      Integer32 (0..300)
    MAX-ACCESS  read-write
    STATUS      current
    DESCRIPTION 
        "Maximum port power(in deciwatt) that can be delivered to remote device.
         Maximum allowed values from 0 to 154 deciwatt in POE standard mode, and
         from 0 to 300 deciwatt in POE plus mode."
    ::= { vtssPoeConfigInterfaceParamEntry 4 }

vtssPoeStatus OBJECT IDENTIFIER
    ::= { vtssPoeMibObjects 3 }

vtssPoeStatusInterfaceTable OBJECT-TYPE
    SYNTAX      SEQUENCE OF VTSSPoeStatusInterfaceEntry
    MAX-ACCESS  not-accessible
    STATUS      current
    DESCRIPTION 
        "This is a table to Power over Ethernet interface status"
    ::= { vtssPoeStatus 1 }

vtssPoeStatusInterfaceEntry OBJECT-TYPE
    SYNTAX      VTSSPoeStatusInterfaceEntry
    MAX-ACCESS  not-accessible
    STATUS      current
    DESCRIPTION 
        "Each interface has a set of status parameters"
    INDEX       { vtssPoeStatusInterfaceIfIndex }
    ::= { vtssPoeStatusInterfaceTable 1 }

VTSSPoeStatusInterfaceEntry ::= SEQUENCE {
    vtssPoeStatusInterfaceIfIndex   VTSSInterfaceIndex,
    vtssPoeStatusInterfacePDClass   Integer32,
    vtssPoeStatusInterfaceCurrentState      VTSSpoeStatusType,
    vtssPoeStatusInterfacePowerConsumption      Integer32,
    vtssPoeStatusInterfaceCurrentConsumption    Integer32
}

vtssPoeStatusInterfaceIfIndex OBJECT-TYPE
    SYNTAX      VTSSInterfaceIndex
    MAX-ACCESS  not-accessible
    STATUS      current
    DESCRIPTION 
        "Logical interface number."
    ::= { vtssPoeStatusInterfaceEntry 1 }

vtssPoeStatusInterfacePDClass OBJECT-TYPE
    SYNTAX      Integer32
    MAX-ACCESS  read-only
    STATUS      current
    DESCRIPTION 
        "Powered device(PD) negotiates a power class with sourcing
         equipment(PSE) during the time of initial connection, each class have a
         maximum supported power. Class assigned to PD is based on PD electrical
         characteristics. Value -1 means either PD attached to the interface can
         not advertise its power class or no PD detected or PoE is not supported
         or PoE feature is disabled or unsupported PD class(classes 0-4 is
         supported)."
    ::= { vtssPoeStatusInterfaceEntry 2 }

vtssPoeStatusInterfaceCurrentState OBJECT-TYPE
    SYNTAX      VTSSpoeStatusType
    MAX-ACCESS  read-only
    STATUS      current
    DESCRIPTION 
        "Indicate port status. POWER_BUDGET_EXCEEDED: PoE is turned OFF due to
         power budget exceeded on PSE. NO_PD_DETECTED: No PD detected. PD_ON:
         PSE supplying power to PD through PoE. PD_OVERLOAD: PD consumes more
         power than the maximum limit configured on the PSE port."
    ::= { vtssPoeStatusInterfaceEntry 3 }

vtssPoeStatusInterfacePowerConsumption OBJECT-TYPE
    SYNTAX      Integer32
    MAX-ACCESS  read-only
    STATUS      current
    DESCRIPTION 
        "Indicates the power(in deciwatt) that the PD is consuming right now."
    ::= { vtssPoeStatusInterfaceEntry 4 }

vtssPoeStatusInterfaceCurrentConsumption OBJECT-TYPE
    SYNTAX      Integer32
    MAX-ACCESS  read-only
    STATUS      current
    DESCRIPTION 
        "Indicates the current(in mA) that the PD is consuming right now."
    ::= { vtssPoeStatusInterfaceEntry 5 }

vtssPoeMibConformance OBJECT IDENTIFIER
    ::= { vtssPoeMib 2 }

vtssPoeMibCompliances OBJECT IDENTIFIER
    ::= { vtssPoeMibConformance 1 }

vtssPoeMibGroups OBJECT IDENTIFIER
    ::= { vtssPoeMibConformance 2 }

vtssPoeCapabilitiesInterfaceInfoGroup OBJECT-GROUP
    OBJECTS     { vtssPoeCapabilitiesInterfacePoE }
    STATUS      current
    DESCRIPTION
        "A collection of objects suitable for bulk operations."
    ::= { vtssPoeMibGroups 1 }

vtssPoeConfigGlobalsInfoGroup OBJECT-GROUP
    OBJECTS     { vtssPoeConfigGlobalsManagementMode }
    STATUS      current
    DESCRIPTION
        "A collection of objects suitable for bulk operations."
    ::= { vtssPoeMibGroups 2 }

vtssPoeConfigSwitchParamTableInfoGroup OBJECT-GROUP
    OBJECTS     { vtssPoeConfigSwitchParamMaxPower, 
                  vtssPoeConfigSwitchParamCapacitorDetection }
    STATUS      current
    DESCRIPTION
        "A collection of objects suitable for bulk operations."
    ::= { vtssPoeMibGroups 3 }

vtssPoeConfigInterfaceParamTableInfoGroup OBJECT-GROUP
    OBJECTS     { vtssPoeConfigInterfaceParamMode, 
                  vtssPoeConfigInterfaceParamPriority, 
                  vtssPoeConfigInterfaceParamMaxPower }
    STATUS      current
    DESCRIPTION
        "A collection of objects suitable for bulk operations."
    ::= { vtssPoeMibGroups 4 }

vtssPoeStatusInterfaceTableInfoGroup OBJECT-GROUP
    OBJECTS     { vtssPoeStatusInterfacePDClass, 
                  vtssPoeStatusInterfaceCurrentState, 
                  vtssPoeStatusInterfacePowerConsumption, 
                  vtssPoeStatusInterfaceCurrentConsumption }
    STATUS      current
    DESCRIPTION
        "A collection of objects suitable for bulk operations."
    ::= { vtssPoeMibGroups 5 }

vtssPoeMibCompliance MODULE-COMPLIANCE
    STATUS      current
    DESCRIPTION
        "The compliance statement for the implementation."

    MODULE      -- this module

        MANDATORY-GROUPS        { vtssPoeCapabilitiesInterfaceInfoGroup, 
                  vtssPoeConfigGlobalsInfoGroup, 
                  vtssPoeConfigSwitchParamTableInfoGroup, 
                  vtssPoeConfigInterfaceParamTableInfoGroup, 
                  vtssPoeStatusInterfaceTableInfoGroup }

    ::= { vtssPoeMibCompliances 1 }

END
