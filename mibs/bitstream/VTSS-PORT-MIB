-- *****************************************************************
-- PORT-MIB:  Vitesse private MIB
--
-- Copyright (c) 2002-2013 Vitesse Semiconductor Corporation "Vitesse".
-- All Rights Reserved.
--
-- ****************************************************************

VTSS-PORT-MIB DEFINITIONS ::= BEGIN

IMPORTS
    MODULE-COMPLIANCE, OBJECT-GROUP
        FROM SNMPv2-CONF
    MODULE-IDENTITY, OBJECT-TYPE
        FROM SNMPv2-SMI
    TEXTUAL-CONVENTION
        FROM SNMPv2-TC
    vtssSwitchMgmt
        FROM VTSS-SMI
    Counter64 FROM SNMPv2-SMI
    Integer32 FROM SNMPv2-SMI
    Unsigned32 FROM SNMPv2-SMI
    TruthValue FROM SNMPv2-TC
    VTSSDisplayString FROM VTSS-TC
    VTSSInterfaceIndex FROM VTSS-TC
    VTSSSfpTransceiver FROM VTSS-TC
    VTSSUnsigned8 FROM VTSS-TC
    ;

vtssPortMib MODULE-IDENTITY
    LAST-UPDATED "201407010000Z"
    ORGANIZATION
        "Vitesse Semiconductor Corporation"
    CONTACT-INFO
        "Application support <application_support@vitesse.com>"
    DESCRIPTION
        "This is a private version of the PORT MIB"
    REVISION    "201407010000Z"
    DESCRIPTION
        "Initial version"
    ::= { vtssSwitchMgmt 11 }


VTSSPortFc ::= TEXTUAL-CONVENTION
    STATUS      current
    DESCRIPTION
        "This enumeration controls the interface flow control."
    SYNTAX      INTEGER { off(0), on(1) }

VTSSPortMedia ::= TEXTUAL-CONVENTION
    STATUS      current
    DESCRIPTION
        "This enumeration controls the interface media type."
    SYNTAX      INTEGER { rj45(0), sfp(1), dual(2) }

VTSSPortPhyVeriPhyStatus ::= TEXTUAL-CONVENTION
    STATUS      current
    DESCRIPTION
        "This enumerations show the VeriPhy status."
    SYNTAX      INTEGER { correctlyTerminatedPair(0), openPair(1), shortPair(2), abnormalTermination(4), crossPairShortToPairA(8), crossPairShortToPairB(9), crossPairShortToPairC(10), crossPairShortToPairD(11), abnormalCrossPairCouplingToPairA(12), abnormalCrossPairCouplingToPairB(13), abnormalCrossPairCouplingToPairC(14), abnormalCrossPairCouplingToPairD(15), unknownResult(16), veriPhyRunning(17) }

VTSSPortSpeed ::= TEXTUAL-CONVENTION
    STATUS      current
    DESCRIPTION
        "This enumeration controls the interface speed. E.g force10ModeFdx means
         force 10Mbs full duplex."
    SYNTAX      INTEGER { force10ModeFdx(0), force10ModeHdx(1), force100ModeFdx(2), force100ModeHdx(3), force1GModeFdx(4), autoNegMode(5), force2G5ModeFdx(6), force5GModeFdx(7), force10GModeFdx(8), force12GModeFdx(9) }

VTSSPortStatusSpeed ::= TEXTUAL-CONVENTION
    STATUS      current
    DESCRIPTION
        "This enumerations show the current interface speed."
    SYNTAX      INTEGER { undefined(0), speed10M(1), speed100M(2), speed1G(3), speed2G5(4), speed5G(5), speed10G(6), speed12G(7) }

vtssPortMibObjects OBJECT IDENTIFIER
    ::= { vtssPortMib 1 }

vtssPortConfig OBJECT IDENTIFIER
    ::= { vtssPortMibObjects 2 }

vtssPortConfigTable OBJECT-TYPE
    SYNTAX      SEQUENCE OF VTSSPortConfigEntry
    MAX-ACCESS  not-accessible
    STATUS      current
    DESCRIPTION 
        "This is a table of the port interface parameters"
    ::= { vtssPortConfig 1 }

vtssPortConfigEntry OBJECT-TYPE
    SYNTAX      VTSSPortConfigEntry
    MAX-ACCESS  not-accessible
    STATUS      current
    DESCRIPTION 
        "Each port interface has a set of parameters"
    INDEX       { vtssPortConfigIfIndex }
    ::= { vtssPortConfigTable 1 }

VTSSPortConfigEntry ::= SEQUENCE {
    vtssPortConfigIfIndex   VTSSInterfaceIndex,
    vtssPortConfigShutdown      TruthValue,
    vtssPortConfigSpeed     VTSSPortSpeed,
    vtssPortConfigAdvertiseDisabled     VTSSUnsigned8,
    vtssPortConfigMediaType     VTSSPortMedia,
    vtssPortConfigFC    VTSSPortFc,
    vtssPortConfigMTU   Unsigned32,
    vtssPortConfigExcessiveRestart      TruthValue,
    vtssPortConfigPFC   VTSSUnsigned8,
    vtssPortConfigFrameLengthCheck      TruthValue
}

vtssPortConfigIfIndex OBJECT-TYPE
    SYNTAX      VTSSInterfaceIndex
    MAX-ACCESS  not-accessible
    STATUS      current
    DESCRIPTION 
        "Logical interface number."
    ::= { vtssPortConfigEntry 1 }

vtssPortConfigShutdown OBJECT-TYPE
    SYNTAX      TruthValue
    MAX-ACCESS  read-write
    STATUS      current
    DESCRIPTION 
        "Controls whether interface is shutdown or powered up. Set to TRUE in
         order to power down the interface."
    ::= { vtssPortConfigEntry 2 }

vtssPortConfigSpeed OBJECT-TYPE
    SYNTAX      VTSSPortSpeed
    MAX-ACCESS  read-write
    STATUS      current
    DESCRIPTION 
        "Controls the port speed and duplex."
    ::= { vtssPortConfigEntry 3 }

vtssPortConfigAdvertiseDisabled OBJECT-TYPE
    SYNTAX      VTSSUnsigned8
    MAX-ACCESS  read-write
    STATUS      current
    DESCRIPTION 
        "In auto mode, bitmask that allows features not to be advertised.
         
         Bit 0: Disable half duplex advertising.
         
         Bit 1: Disable full duplex advertising.
         
         Bit 4: Disable 1G advertising.
         
         Bit 6: Disable 100M advertising.
         
         Bit 7: Disable 10M advertising.
         
         When not in auto mode, the value shall be zero."
    ::= { vtssPortConfigEntry 4 }

vtssPortConfigMediaType OBJECT-TYPE
    SYNTAX      VTSSPortMedia
    MAX-ACCESS  read-write
    STATUS      current
    DESCRIPTION 
        "Controls the port media type."
    ::= { vtssPortConfigEntry 5 }

vtssPortConfigFC OBJECT-TYPE
    SYNTAX      VTSSPortFc
    MAX-ACCESS  read-write
    STATUS      current
    DESCRIPTION 
        "Controls the port flow control mode."
    ::= { vtssPortConfigEntry 6 }

vtssPortConfigMTU OBJECT-TYPE
    SYNTAX      Unsigned32
    MAX-ACCESS  read-write
    STATUS      current
    DESCRIPTION 
        "Controls the port's Maximum Transmission Unit."
    ::= { vtssPortConfigEntry 7 }

vtssPortConfigExcessiveRestart OBJECT-TYPE
    SYNTAX      TruthValue
    MAX-ACCESS  read-write
    STATUS      current
    DESCRIPTION 
        "TRUE to restart half-duplex back-off algorithm after 16 collisions.
         FALSE to discard frame after 16 collisions"
    ::= { vtssPortConfigEntry 8 }

vtssPortConfigPFC OBJECT-TYPE
    SYNTAX      VTSSUnsigned8
    MAX-ACCESS  read-write
    STATUS      current
    DESCRIPTION 
        "802.1Qbb Priority Flow Control bitmask, one bit for each prioritet.E.g.
         0x01 = prio 0, 0x80 = prio 7, 0xFF = prio 0-7"
    ::= { vtssPortConfigEntry 9 }

vtssPortConfigFrameLengthCheck OBJECT-TYPE
    SYNTAX      TruthValue
    MAX-ACCESS  read-write
    STATUS      current
    DESCRIPTION 
        "TRUE to enforce 802.3 frame length check (from Ethertype field). If
         enabled frames with length that doesn't match the frame length field
         will be dropped."
    ::= { vtssPortConfigEntry 10 }

vtssPortStatus OBJECT IDENTIFIER
    ::= { vtssPortMibObjects 3 }

vtssPortStatusInformationTable OBJECT-TYPE
    SYNTAX      SEQUENCE OF VTSSPortStatusInformationEntry
    MAX-ACCESS  not-accessible
    STATUS      current
    DESCRIPTION 
        "This table represents the status of the ports"
    ::= { vtssPortStatus 1 }

vtssPortStatusInformationEntry OBJECT-TYPE
    SYNTAX      VTSSPortStatusInformationEntry
    MAX-ACCESS  not-accessible
    STATUS      current
    DESCRIPTION 
        "Each port interface has a set of status parameters"
    INDEX       { vtssPortStatusInformationIfIndex }
    ::= { vtssPortStatusInformationTable 1 }

VTSSPortStatusInformationEntry ::= SEQUENCE {
    vtssPortStatusInformationIfIndex    VTSSInterfaceIndex,
    vtssPortStatusInformationLink   TruthValue,
    vtssPortStatusInformationFdx    TruthValue,
    vtssPortStatusInformationFiber      TruthValue,
    vtssPortStatusInformationSpeed      VTSSPortStatusSpeed,
    vtssPortStatusInformationSFPType    VTSSSfpTransceiver,
    vtssPortStatusInformationSFPVendorName      VTSSDisplayString,
    vtssPortStatusInformationSFPVendorPN    VTSSDisplayString,
    vtssPortStatusInformationSFPVendorRev   VTSSDisplayString
}

vtssPortStatusInformationIfIndex OBJECT-TYPE
    SYNTAX      VTSSInterfaceIndex
    MAX-ACCESS  not-accessible
    STATUS      current
    DESCRIPTION 
        "Logical interface number."
    ::= { vtssPortStatusInformationEntry 1 }

vtssPortStatusInformationLink OBJECT-TYPE
    SYNTAX      TruthValue
    MAX-ACCESS  read-only
    STATUS      current
    DESCRIPTION 
        "Shows whether interface has link."
    ::= { vtssPortStatusInformationEntry 2 }

vtssPortStatusInformationFdx OBJECT-TYPE
    SYNTAX      TruthValue
    MAX-ACCESS  read-only
    STATUS      current
    DESCRIPTION 
        "Shows whether interface is running in full duplex."
    ::= { vtssPortStatusInformationEntry 3 }

vtssPortStatusInformationFiber OBJECT-TYPE
    SYNTAX      TruthValue
    MAX-ACCESS  read-only
    STATUS      current
    DESCRIPTION 
        "Shows whether interface is a fiber link (fiber SFP or cu SFP)."
    ::= { vtssPortStatusInformationEntry 4 }

vtssPortStatusInformationSpeed OBJECT-TYPE
    SYNTAX      VTSSPortStatusSpeed
    MAX-ACCESS  read-only
    STATUS      current
    DESCRIPTION 
        "Shows the current interface speed."
    ::= { vtssPortStatusInformationEntry 5 }

vtssPortStatusInformationSFPType OBJECT-TYPE
    SYNTAX      VTSSSfpTransceiver
    MAX-ACCESS  read-only
    STATUS      current
    DESCRIPTION 
        "Shows the current interface SFP type."
    ::= { vtssPortStatusInformationEntry 6 }

vtssPortStatusInformationSFPVendorName OBJECT-TYPE
    SYNTAX      VTSSDisplayString (SIZE(0..19))
    MAX-ACCESS  read-only
    STATUS      current
    DESCRIPTION 
        "Shows the SFP vendor name."
    ::= { vtssPortStatusInformationEntry 7 }

vtssPortStatusInformationSFPVendorPN OBJECT-TYPE
    SYNTAX      VTSSDisplayString (SIZE(0..19))
    MAX-ACCESS  read-only
    STATUS      current
    DESCRIPTION 
        "Shows the SFP vendor Product Number."
    ::= { vtssPortStatusInformationEntry 8 }

vtssPortStatusInformationSFPVendorRev OBJECT-TYPE
    SYNTAX      VTSSDisplayString (SIZE(0..5))
    MAX-ACCESS  read-only
    STATUS      current
    DESCRIPTION 
        "Shows the SFP vendor Revision."
    ::= { vtssPortStatusInformationEntry 9 }

vtssPortStatusVeriPhyResult OBJECT IDENTIFIER
    ::= { vtssPortStatus 3 }

vtssPortStatusVeriPhyResultTable OBJECT-TYPE
    SYNTAX      SEQUENCE OF VTSSPortStatusVeriPhyResultEntry
    MAX-ACCESS  not-accessible
    STATUS      current
    DESCRIPTION 
        "This table represents the VeriPhy result from the last VeriPhy run for
         the interface"
    ::= { vtssPortStatusVeriPhyResult 1 }

vtssPortStatusVeriPhyResultEntry OBJECT-TYPE
    SYNTAX      VTSSPortStatusVeriPhyResultEntry
    MAX-ACCESS  not-accessible
    STATUS      current
    DESCRIPTION 
        "Each port has a set of VeriPhy results"
    INDEX       { vtssPortStatusVeriPhyResultIfIndex }
    ::= { vtssPortStatusVeriPhyResultTable 1 }

VTSSPortStatusVeriPhyResultEntry ::= SEQUENCE {
    vtssPortStatusVeriPhyResultIfIndex      VTSSInterfaceIndex,
    vtssPortStatusVeriPhyResultVeriPhyStatusPairA   VTSSPortPhyVeriPhyStatus,
    vtssPortStatusVeriPhyResultVeriPhyStatusPairB   VTSSPortPhyVeriPhyStatus,
    vtssPortStatusVeriPhyResultVeriPhyStatusPairC   VTSSPortPhyVeriPhyStatus,
    vtssPortStatusVeriPhyResultVeriPhyStatusPairD   VTSSPortPhyVeriPhyStatus,
    vtssPortStatusVeriPhyResultVeriPhyLengthStatusPairA     VTSSUnsigned8,
    vtssPortStatusVeriPhyResultVeriPhyLengthStatusPairB     VTSSUnsigned8,
    vtssPortStatusVeriPhyResultVeriPhyLengthStatusPairC     VTSSUnsigned8,
    vtssPortStatusVeriPhyResultVeriPhyLengthStatusPairD     VTSSUnsigned8
}

vtssPortStatusVeriPhyResultIfIndex OBJECT-TYPE
    SYNTAX      VTSSInterfaceIndex
    MAX-ACCESS  not-accessible
    STATUS      current
    DESCRIPTION 
        "Logical interface number."
    ::= { vtssPortStatusVeriPhyResultEntry 1 }

vtssPortStatusVeriPhyResultVeriPhyStatusPairA OBJECT-TYPE
    SYNTAX      VTSSPortPhyVeriPhyStatus
    MAX-ACCESS  read-only
    STATUS      current
    DESCRIPTION 
        "VeriPhy status for the cable pair
         
         0 - Cable is Correctly terminated pair
         
         1 - Open pair
         
         2 - Shorted pair
         
         4 - Abnormal termination
         
         8 - Cross-pair short to pair A
         
         9 - Cross-pair short to pair B
         
         10 - Cross-pair short to pair C
         
         11 - Cross-pair short to pair D
         
         12 - Abnormal cross-pair coupling - pair A
         
         13 - Abnormal cross-pair coupling - pair B
         
         14 - Abnormal cross-pair coupling - pair C
         
         15 - Abnormal cross-pair coupling - pair D"
    ::= { vtssPortStatusVeriPhyResultEntry 2 }

vtssPortStatusVeriPhyResultVeriPhyStatusPairB OBJECT-TYPE
    SYNTAX      VTSSPortPhyVeriPhyStatus
    MAX-ACCESS  read-only
    STATUS      current
    DESCRIPTION 
        "VeriPhy status for the cable pair
         
         0 - Cable is Correctly terminated pair
         
         1 - Open pair
         
         2 - Shorted pair
         
         4 - Abnormal termination
         
         8 - Cross-pair short to pair A
         
         9 - Cross-pair short to pair B
         
         10 - Cross-pair short to pair C
         
         11 - Cross-pair short to pair D
         
         12 - Abnormal cross-pair coupling - pair A
         
         13 - Abnormal cross-pair coupling - pair B
         
         14 - Abnormal cross-pair coupling - pair C
         
         15 - Abnormal cross-pair coupling - pair D"
    ::= { vtssPortStatusVeriPhyResultEntry 3 }

vtssPortStatusVeriPhyResultVeriPhyStatusPairC OBJECT-TYPE
    SYNTAX      VTSSPortPhyVeriPhyStatus
    MAX-ACCESS  read-only
    STATUS      current
    DESCRIPTION 
        "VeriPhy status for the cable pair
         
         0 - Cable is Correctly terminated pair
         
         1 - Open pair
         
         2 - Shorted pair
         
         4 - Abnormal termination
         
         8 - Cross-pair short to pair A
         
         9 - Cross-pair short to pair B
         
         10 - Cross-pair short to pair C
         
         11 - Cross-pair short to pair D
         
         12 - Abnormal cross-pair coupling - pair A
         
         13 - Abnormal cross-pair coupling - pair B
         
         14 - Abnormal cross-pair coupling - pair C
         
         15 - Abnormal cross-pair coupling - pair D"
    ::= { vtssPortStatusVeriPhyResultEntry 4 }

vtssPortStatusVeriPhyResultVeriPhyStatusPairD OBJECT-TYPE
    SYNTAX      VTSSPortPhyVeriPhyStatus
    MAX-ACCESS  read-only
    STATUS      current
    DESCRIPTION 
        "VeriPhy status for the cable pair
         
         0 - Cable is Correctly terminated pair
         
         1 - Open pair
         
         2 - Shorted pair
         
         4 - Abnormal termination
         
         8 - Cross-pair short to pair A
         
         9 - Cross-pair short to pair B
         
         10 - Cross-pair short to pair C
         
         11 - Cross-pair short to pair D
         
         12 - Abnormal cross-pair coupling - pair A
         
         13 - Abnormal cross-pair coupling - pair B
         
         14 - Abnormal cross-pair coupling - pair C
         
         15 - Abnormal cross-pair coupling - pair D"
    ::= { vtssPortStatusVeriPhyResultEntry 5 }

vtssPortStatusVeriPhyResultVeriPhyLengthStatusPairA OBJECT-TYPE
    SYNTAX      VTSSUnsigned8
    MAX-ACCESS  read-only
    STATUS      current
    DESCRIPTION 
        "VeriPhy status cable length i meters for the cable pair. When VeriPhy
         is completed, the cable diagnostics results is shown in the VeriPhy
         status table. Note that VeriPHY is only accurate for cables of length 7
         - 140 meters.
         
         The resolution is 3 meters"
    ::= { vtssPortStatusVeriPhyResultEntry 6 }

vtssPortStatusVeriPhyResultVeriPhyLengthStatusPairB OBJECT-TYPE
    SYNTAX      VTSSUnsigned8
    MAX-ACCESS  read-only
    STATUS      current
    DESCRIPTION 
        "VeriPhy status cable length i meters for the cable pair. When VeriPhy
         is completed, the cable diagnostics results is shown in the VeriPhy
         status table. Note that VeriPHY is only accurate for cables of length 7
         - 140 meters.
         
         The resolution is 3 meters"
    ::= { vtssPortStatusVeriPhyResultEntry 7 }

vtssPortStatusVeriPhyResultVeriPhyLengthStatusPairC OBJECT-TYPE
    SYNTAX      VTSSUnsigned8
    MAX-ACCESS  read-only
    STATUS      current
    DESCRIPTION 
        "VeriPhy status cable length i meters for the cable pair. When VeriPhy
         is completed, the cable diagnostics results is shown in the VeriPhy
         status table. Note that VeriPHY is only accurate for cables of length 7
         - 140 meters.
         
         The resolution is 3 meters"
    ::= { vtssPortStatusVeriPhyResultEntry 8 }

vtssPortStatusVeriPhyResultVeriPhyLengthStatusPairD OBJECT-TYPE
    SYNTAX      VTSSUnsigned8
    MAX-ACCESS  read-only
    STATUS      current
    DESCRIPTION 
        "VeriPhy status cable length i meters for the cable pair. When VeriPhy
         is completed, the cable diagnostics results is shown in the VeriPhy
         status table. Note that VeriPHY is only accurate for cables of length 7
         - 140 meters.
         
         The resolution is 3 meters"
    ::= { vtssPortStatusVeriPhyResultEntry 9 }

vtssPortControl OBJECT IDENTIFIER
    ::= { vtssPortMibObjects 4 }

vtssPortControlStatisticsClear OBJECT IDENTIFIER
    ::= { vtssPortControl 1 }

vtssPortControlStatisticsClearTable OBJECT-TYPE
    SYNTAX      SEQUENCE OF VTSSPortControlStatisticsClearEntry
    MAX-ACCESS  not-accessible
    STATUS      current
    DESCRIPTION 
        "This is a table to clear port Interface statistics"
    ::= { vtssPortControlStatisticsClear 1 }

vtssPortControlStatisticsClearEntry OBJECT-TYPE
    SYNTAX      VTSSPortControlStatisticsClearEntry
    MAX-ACCESS  not-accessible
    STATUS      current
    DESCRIPTION 
        "Each port has a set of control parameters"
    INDEX       { vtssPortControlStatisticsClearIfIndex }
    ::= { vtssPortControlStatisticsClearTable 1 }

VTSSPortControlStatisticsClearEntry ::= SEQUENCE {
    vtssPortControlStatisticsClearIfIndex   VTSSInterfaceIndex,
    vtssPortControlStatisticsClearStatisticsClear   TruthValue
}

vtssPortControlStatisticsClearIfIndex OBJECT-TYPE
    SYNTAX      VTSSInterfaceIndex
    MAX-ACCESS  not-accessible
    STATUS      current
    DESCRIPTION 
        "Logical interface number."
    ::= { vtssPortControlStatisticsClearEntry 1 }

vtssPortControlStatisticsClearStatisticsClear OBJECT-TYPE
    SYNTAX      TruthValue
    MAX-ACCESS  read-write
    STATUS      current
    DESCRIPTION 
        "Set to TRUE to clear the statistics of an interface."
    ::= { vtssPortControlStatisticsClearEntry 2 }

vtssPortControlVeriPhyStart OBJECT IDENTIFIER
    ::= { vtssPortControl 2 }

vtssPortControlVeriPhyStartTable OBJECT-TYPE
    SYNTAX      SEQUENCE OF VTSSPortControlVeriPhyStartEntry
    MAX-ACCESS  not-accessible
    STATUS      current
    DESCRIPTION 
        "This is a table to start VeriPhy for the interface"
    ::= { vtssPortControlVeriPhyStart 1 }

vtssPortControlVeriPhyStartEntry OBJECT-TYPE
    SYNTAX      VTSSPortControlVeriPhyStartEntry
    MAX-ACCESS  not-accessible
    STATUS      current
    DESCRIPTION 
        "Each port has a set of control parameters"
    INDEX       { vtssPortControlVeriPhyStartIfIndex }
    ::= { vtssPortControlVeriPhyStartTable 1 }

VTSSPortControlVeriPhyStartEntry ::= SEQUENCE {
    vtssPortControlVeriPhyStartIfIndex      VTSSInterfaceIndex,
    vtssPortControlVeriPhyStartStart    TruthValue
}

vtssPortControlVeriPhyStartIfIndex OBJECT-TYPE
    SYNTAX      VTSSInterfaceIndex
    MAX-ACCESS  not-accessible
    STATUS      current
    DESCRIPTION 
        "Logical interface number."
    ::= { vtssPortControlVeriPhyStartEntry 1 }

vtssPortControlVeriPhyStartStart OBJECT-TYPE
    SYNTAX      TruthValue
    MAX-ACCESS  read-write
    STATUS      current
    DESCRIPTION 
        "Set to TRUE to start VeriPHy for the interface.
         
         When running 10 and 100 Mbps, ports will be linked down while running
         VeriPHY. Therefore, running VeriPHY on a 10 or 100 Mbps management port
         will cause the switch to stop responding until VeriPHY is complete."
    ::= { vtssPortControlVeriPhyStartEntry 2 }

vtssPortStatistics OBJECT IDENTIFIER
    ::= { vtssPortMibObjects 5 }

vtssPortStatisticsRmonStatisticsTable OBJECT-TYPE
    SYNTAX      SEQUENCE OF VTSSPortStatisticsRmonStatisticsEntry
    MAX-ACCESS  not-accessible
    STATUS      current
    DESCRIPTION 
        "This table represents the port interface RMON statistics counters"
    ::= { vtssPortStatistics 1 }

vtssPortStatisticsRmonStatisticsEntry OBJECT-TYPE
    SYNTAX      VTSSPortStatisticsRmonStatisticsEntry
    MAX-ACCESS  not-accessible
    STATUS      current
    DESCRIPTION 
        "Each port interface has a set of statistics counters"
    INDEX       { vtssPortStatisticsRmonStatisticsIfIndex }
    ::= { vtssPortStatisticsRmonStatisticsTable 1 }

VTSSPortStatisticsRmonStatisticsEntry ::= SEQUENCE {
    vtssPortStatisticsRmonStatisticsIfIndex     VTSSInterfaceIndex,
    vtssPortStatisticsRmonStatisticsRxDropEvents    Counter64,
    vtssPortStatisticsRmonStatisticsRxOctets    Counter64,
    vtssPortStatisticsRmonStatisticsRxPkts      Counter64,
    vtssPortStatisticsRmonStatisticsRxBroadcastPkts     Counter64,
    vtssPortStatisticsRmonStatisticsRxMulticastPkts     Counter64,
    vtssPortStatisticsRmonStatisticsRxCrcAlignErrPkts   Counter64,
    vtssPortStatisticsRmonStatisticsRxUndersizePkts     Counter64,
    vtssPortStatisticsRmonStatisticsRxOversizePkts      Counter64,
    vtssPortStatisticsRmonStatisticsRxFragmentsPkts     Counter64,
    vtssPortStatisticsRmonStatisticsRxJabbersPkts   Counter64,
    vtssPortStatisticsRmonStatisticsRx64Pkts    Counter64,
    vtssPortStatisticsRmonStatisticsRx65to127Pkts   Counter64,
    vtssPortStatisticsRmonStatisticsRx128to255Pkts      Counter64,
    vtssPortStatisticsRmonStatisticsRx256to511Pkts      Counter64,
    vtssPortStatisticsRmonStatisticsRx512to1023Pkts     Counter64,
    vtssPortStatisticsRmonStatisticsRx1024to1518Pkts    Counter64,
    vtssPortStatisticsRmonStatisticsRx1519PktsToMax     Counter64,
    vtssPortStatisticsRmonStatisticsTxDropEvents    Counter64,
    vtssPortStatisticsRmonStatisticsTxOctets    Counter64,
    vtssPortStatisticsRmonStatisticsTxPkts      Counter64,
    vtssPortStatisticsRmonStatisticsTxBroadcastPkts     Counter64,
    vtssPortStatisticsRmonStatisticsTxMulticastPkts     Counter64,
    vtssPortStatisticsRmonStatisticsTx64Pkts    Counter64,
    vtssPortStatisticsRmonStatisticsTx65to127Pkts   Counter64,
    vtssPortStatisticsRmonStatisticsTx128to255Pkts      Counter64,
    vtssPortStatisticsRmonStatisticsTx256to511Pkts      Counter64,
    vtssPortStatisticsRmonStatisticsTx512to1023Pkts     Counter64,
    vtssPortStatisticsRmonStatisticsTx1024to1518Pkts    Counter64,
    vtssPortStatisticsRmonStatisticsTx1519PktsToMax     Counter64
}

vtssPortStatisticsRmonStatisticsIfIndex OBJECT-TYPE
    SYNTAX      VTSSInterfaceIndex
    MAX-ACCESS  not-accessible
    STATUS      current
    DESCRIPTION 
        "Logical interface number."
    ::= { vtssPortStatisticsRmonStatisticsEntry 1 }

vtssPortStatisticsRmonStatisticsRxDropEvents OBJECT-TYPE
    SYNTAX      Counter64
    MAX-ACCESS  read-only
    STATUS      current
    DESCRIPTION 
        "Shows the number of frames discarded due to ingress congestion."
    ::= { vtssPortStatisticsRmonStatisticsEntry 2 }

vtssPortStatisticsRmonStatisticsRxOctets OBJECT-TYPE
    SYNTAX      Counter64
    MAX-ACCESS  read-only
    STATUS      current
    DESCRIPTION 
        "Shows the number of received (good and bad) bytes. Includes FCS, but
         excludes framing bits."
    ::= { vtssPortStatisticsRmonStatisticsEntry 3 }

vtssPortStatisticsRmonStatisticsRxPkts OBJECT-TYPE
    SYNTAX      Counter64
    MAX-ACCESS  read-only
    STATUS      current
    DESCRIPTION 
        "Shows the number of received (good and bad) packets."
    ::= { vtssPortStatisticsRmonStatisticsEntry 4 }

vtssPortStatisticsRmonStatisticsRxBroadcastPkts OBJECT-TYPE
    SYNTAX      Counter64
    MAX-ACCESS  read-only
    STATUS      current
    DESCRIPTION 
        "Shows the number of received (good and bad) broadcast packets."
    ::= { vtssPortStatisticsRmonStatisticsEntry 5 }

vtssPortStatisticsRmonStatisticsRxMulticastPkts OBJECT-TYPE
    SYNTAX      Counter64
    MAX-ACCESS  read-only
    STATUS      current
    DESCRIPTION 
        "Shows the number of received (good and bad) multicast packets."
    ::= { vtssPortStatisticsRmonStatisticsEntry 6 }

vtssPortStatisticsRmonStatisticsRxCrcAlignErrPkts OBJECT-TYPE
    SYNTAX      Counter64
    MAX-ACCESS  read-only
    STATUS      current
    DESCRIPTION 
        "Shows the number of frames received with CRC or alignment errors."
    ::= { vtssPortStatisticsRmonStatisticsEntry 7 }

vtssPortStatisticsRmonStatisticsRxUndersizePkts OBJECT-TYPE
    SYNTAX      Counter64
    MAX-ACCESS  read-only
    STATUS      current
    DESCRIPTION 
        "Shows the number of short frames (frames that are smaller than 64
         bytes) received with valid CRC."
    ::= { vtssPortStatisticsRmonStatisticsEntry 8 }

vtssPortStatisticsRmonStatisticsRxOversizePkts OBJECT-TYPE
    SYNTAX      Counter64
    MAX-ACCESS  read-only
    STATUS      current
    DESCRIPTION 
        "Shows the number of long frames received with valid CRC."
    ::= { vtssPortStatisticsRmonStatisticsEntry 9 }

vtssPortStatisticsRmonStatisticsRxFragmentsPkts OBJECT-TYPE
    SYNTAX      Counter64
    MAX-ACCESS  read-only
    STATUS      current
    DESCRIPTION 
        "Shows the number of short frames (frames that are smaller than 64
         bytes) received with invalid CRC."
    ::= { vtssPortStatisticsRmonStatisticsEntry 10 }

vtssPortStatisticsRmonStatisticsRxJabbersPkts OBJECT-TYPE
    SYNTAX      Counter64
    MAX-ACCESS  read-only
    STATUS      current
    DESCRIPTION 
        "The number of long frames (frames that are longer than the configured
         maximum frame length for this interface) received with invalid CRC."
    ::= { vtssPortStatisticsRmonStatisticsEntry 11 }

vtssPortStatisticsRmonStatisticsRx64Pkts OBJECT-TYPE
    SYNTAX      Counter64
    MAX-ACCESS  read-only
    STATUS      current
    DESCRIPTION 
        "The number of 64 bytes frames received."
    ::= { vtssPortStatisticsRmonStatisticsEntry 12 }

vtssPortStatisticsRmonStatisticsRx65to127Pkts OBJECT-TYPE
    SYNTAX      Counter64
    MAX-ACCESS  read-only
    STATUS      current
    DESCRIPTION 
        "The number of received frames with size within 65 to 127 bytes."
    ::= { vtssPortStatisticsRmonStatisticsEntry 13 }

vtssPortStatisticsRmonStatisticsRx128to255Pkts OBJECT-TYPE
    SYNTAX      Counter64
    MAX-ACCESS  read-only
    STATUS      current
    DESCRIPTION 
        "The number of received frames with size within 128 to 255 bytes."
    ::= { vtssPortStatisticsRmonStatisticsEntry 14 }

vtssPortStatisticsRmonStatisticsRx256to511Pkts OBJECT-TYPE
    SYNTAX      Counter64
    MAX-ACCESS  read-only
    STATUS      current
    DESCRIPTION 
        "The number of received frames with size within 256 to 511 bytes."
    ::= { vtssPortStatisticsRmonStatisticsEntry 15 }

vtssPortStatisticsRmonStatisticsRx512to1023Pkts OBJECT-TYPE
    SYNTAX      Counter64
    MAX-ACCESS  read-only
    STATUS      current
    DESCRIPTION 
        "The number of received frames with size within 512 to 1023 bytes."
    ::= { vtssPortStatisticsRmonStatisticsEntry 16 }

vtssPortStatisticsRmonStatisticsRx1024to1518Pkts OBJECT-TYPE
    SYNTAX      Counter64
    MAX-ACCESS  read-only
    STATUS      current
    DESCRIPTION 
        "The number of received frames with size within 1024 to 1518 bytes."
    ::= { vtssPortStatisticsRmonStatisticsEntry 17 }

vtssPortStatisticsRmonStatisticsRx1519PktsToMax OBJECT-TYPE
    SYNTAX      Counter64
    MAX-ACCESS  read-only
    STATUS      current
    DESCRIPTION 
        "The number of received frames with size larger than 1518 bytes."
    ::= { vtssPortStatisticsRmonStatisticsEntry 18 }

vtssPortStatisticsRmonStatisticsTxDropEvents OBJECT-TYPE
    SYNTAX      Counter64
    MAX-ACCESS  read-only
    STATUS      current
    DESCRIPTION 
        "Shows the number of frames discarded due to egress congestion."
    ::= { vtssPortStatisticsRmonStatisticsEntry 19 }

vtssPortStatisticsRmonStatisticsTxOctets OBJECT-TYPE
    SYNTAX      Counter64
    MAX-ACCESS  read-only
    STATUS      current
    DESCRIPTION 
        "Shows the number of transmitted (good and bad) bytes. Includes FCS, but
         excludes framing bits."
    ::= { vtssPortStatisticsRmonStatisticsEntry 20 }

vtssPortStatisticsRmonStatisticsTxPkts OBJECT-TYPE
    SYNTAX      Counter64
    MAX-ACCESS  read-only
    STATUS      current
    DESCRIPTION 
        "Shows the number of transmitted (good and bad) packets."
    ::= { vtssPortStatisticsRmonStatisticsEntry 21 }

vtssPortStatisticsRmonStatisticsTxBroadcastPkts OBJECT-TYPE
    SYNTAX      Counter64
    MAX-ACCESS  read-only
    STATUS      current
    DESCRIPTION 
        "Shows the number of transmitted (good and bad) broadcast packets."
    ::= { vtssPortStatisticsRmonStatisticsEntry 22 }

vtssPortStatisticsRmonStatisticsTxMulticastPkts OBJECT-TYPE
    SYNTAX      Counter64
    MAX-ACCESS  read-only
    STATUS      current
    DESCRIPTION 
        "Shows the number of transmitted (good and bad) multicast packets."
    ::= { vtssPortStatisticsRmonStatisticsEntry 23 }

vtssPortStatisticsRmonStatisticsTx64Pkts OBJECT-TYPE
    SYNTAX      Counter64
    MAX-ACCESS  read-only
    STATUS      current
    DESCRIPTION 
        "The number of 64 bytes frames transmitted."
    ::= { vtssPortStatisticsRmonStatisticsEntry 24 }

vtssPortStatisticsRmonStatisticsTx65to127Pkts OBJECT-TYPE
    SYNTAX      Counter64
    MAX-ACCESS  read-only
    STATUS      current
    DESCRIPTION 
        "The number of transmitted frames with size within 65 to 127 bytes."
    ::= { vtssPortStatisticsRmonStatisticsEntry 25 }

vtssPortStatisticsRmonStatisticsTx128to255Pkts OBJECT-TYPE
    SYNTAX      Counter64
    MAX-ACCESS  read-only
    STATUS      current
    DESCRIPTION 
        "The number of transmitted frames with size within 128 to 255 bytes."
    ::= { vtssPortStatisticsRmonStatisticsEntry 26 }

vtssPortStatisticsRmonStatisticsTx256to511Pkts OBJECT-TYPE
    SYNTAX      Counter64
    MAX-ACCESS  read-only
    STATUS      current
    DESCRIPTION 
        "The number of transmitted frames with size within 256 to 511 bytes."
    ::= { vtssPortStatisticsRmonStatisticsEntry 27 }

vtssPortStatisticsRmonStatisticsTx512to1023Pkts OBJECT-TYPE
    SYNTAX      Counter64
    MAX-ACCESS  read-only
    STATUS      current
    DESCRIPTION 
        "The number of transmitted frames with size within 512 to 1023 bytes."
    ::= { vtssPortStatisticsRmonStatisticsEntry 28 }

vtssPortStatisticsRmonStatisticsTx1024to1518Pkts OBJECT-TYPE
    SYNTAX      Counter64
    MAX-ACCESS  read-only
    STATUS      current
    DESCRIPTION 
        "The number of transmitted frames with size within 1024 to 1518 bytes."
    ::= { vtssPortStatisticsRmonStatisticsEntry 29 }

vtssPortStatisticsRmonStatisticsTx1519PktsToMax OBJECT-TYPE
    SYNTAX      Counter64
    MAX-ACCESS  read-only
    STATUS      current
    DESCRIPTION 
        "The number of transmitted frames with size larger than 1518 bytes."
    ::= { vtssPortStatisticsRmonStatisticsEntry 30 }

vtssPortStatisticsIfGroupStatisticsTable OBJECT-TYPE
    SYNTAX      SEQUENCE OF VTSSPortStatisticsIfGroupStatisticsEntry
    MAX-ACCESS  not-accessible
    STATUS      current
    DESCRIPTION 
        "This table represents the port interfaces group (RFC 2863) counters"
    ::= { vtssPortStatistics 2 }

vtssPortStatisticsIfGroupStatisticsEntry OBJECT-TYPE
    SYNTAX      VTSSPortStatisticsIfGroupStatisticsEntry
    MAX-ACCESS  not-accessible
    STATUS      current
    DESCRIPTION 
        "Each port interface has a set of statistics counters"
    INDEX       { vtssPortStatisticsIfGroupStatisticsIfIndex }
    ::= { vtssPortStatisticsIfGroupStatisticsTable 1 }

VTSSPortStatisticsIfGroupStatisticsEntry ::= SEQUENCE {
    vtssPortStatisticsIfGroupStatisticsIfIndex      VTSSInterfaceIndex,
    vtssPortStatisticsIfGroupStatisticsRxOctets     Counter64,
    vtssPortStatisticsIfGroupStatisticsRxUnicastPkts    Counter64,
    vtssPortStatisticsIfGroupStatisticsRxMulticastPkts      Counter64,
    vtssPortStatisticsIfGroupStatisticsRxBroadcastPkts      Counter64,
    vtssPortStatisticsIfGroupStatisticsRxNonUnicastPkts     Counter64,
    vtssPortStatisticsIfGroupStatisticsRxDiscards   Counter64,
    vtssPortStatisticsIfGroupStatisticsRxErrors     Counter64,
    vtssPortStatisticsIfGroupStatisticsTxOctets     Counter64,
    vtssPortStatisticsIfGroupStatisticsTxUnicastPkts    Counter64,
    vtssPortStatisticsIfGroupStatisticsTxMulticastPkts      Counter64,
    vtssPortStatisticsIfGroupStatisticsTxBroadcastPkts      Counter64,
    vtssPortStatisticsIfGroupStatisticsTxNonUnicastPkts     Counter64,
    vtssPortStatisticsIfGroupStatisticsTxDiscardPkts    Counter64,
    vtssPortStatisticsIfGroupStatisticsTxErrorPkts      Counter64
}

vtssPortStatisticsIfGroupStatisticsIfIndex OBJECT-TYPE
    SYNTAX      VTSSInterfaceIndex
    MAX-ACCESS  not-accessible
    STATUS      current
    DESCRIPTION 
        "Logical interface number."
    ::= { vtssPortStatisticsIfGroupStatisticsEntry 1 }

vtssPortStatisticsIfGroupStatisticsRxOctets OBJECT-TYPE
    SYNTAX      Counter64
    MAX-ACCESS  read-only
    STATUS      current
    DESCRIPTION 
        "Shows the number of bytes received."
    ::= { vtssPortStatisticsIfGroupStatisticsEntry 2 }

vtssPortStatisticsIfGroupStatisticsRxUnicastPkts OBJECT-TYPE
    SYNTAX      Counter64
    MAX-ACCESS  read-only
    STATUS      current
    DESCRIPTION 
        "Shows the number of uni-cast frames received."
    ::= { vtssPortStatisticsIfGroupStatisticsEntry 3 }

vtssPortStatisticsIfGroupStatisticsRxMulticastPkts OBJECT-TYPE
    SYNTAX      Counter64
    MAX-ACCESS  read-only
    STATUS      current
    DESCRIPTION 
        "Shows the number of multi-cast frames received."
    ::= { vtssPortStatisticsIfGroupStatisticsEntry 4 }

vtssPortStatisticsIfGroupStatisticsRxBroadcastPkts OBJECT-TYPE
    SYNTAX      Counter64
    MAX-ACCESS  read-only
    STATUS      current
    DESCRIPTION 
        "Shows the number of broad-cast frames received."
    ::= { vtssPortStatisticsIfGroupStatisticsEntry 5 }

vtssPortStatisticsIfGroupStatisticsRxNonUnicastPkts OBJECT-TYPE
    SYNTAX      Counter64
    MAX-ACCESS  read-only
    STATUS      current
    DESCRIPTION 
        "Shows the number of non uni-cast frames received."
    ::= { vtssPortStatisticsIfGroupStatisticsEntry 6 }

vtssPortStatisticsIfGroupStatisticsRxDiscards OBJECT-TYPE
    SYNTAX      Counter64
    MAX-ACCESS  read-only
    STATUS      current
    DESCRIPTION 
        "Shows the number of received frames discarded."
    ::= { vtssPortStatisticsIfGroupStatisticsEntry 7 }

vtssPortStatisticsIfGroupStatisticsRxErrors OBJECT-TYPE
    SYNTAX      Counter64
    MAX-ACCESS  read-only
    STATUS      current
    DESCRIPTION 
        "Shows the number of frames with errors received."
    ::= { vtssPortStatisticsIfGroupStatisticsEntry 8 }

vtssPortStatisticsIfGroupStatisticsTxOctets OBJECT-TYPE
    SYNTAX      Counter64
    MAX-ACCESS  read-only
    STATUS      current
    DESCRIPTION 
        "Shows the number of bytes transmitted."
    ::= { vtssPortStatisticsIfGroupStatisticsEntry 9 }

vtssPortStatisticsIfGroupStatisticsTxUnicastPkts OBJECT-TYPE
    SYNTAX      Counter64
    MAX-ACCESS  read-only
    STATUS      current
    DESCRIPTION 
        "Shows the number of uni-cast frames transmitted."
    ::= { vtssPortStatisticsIfGroupStatisticsEntry 10 }

vtssPortStatisticsIfGroupStatisticsTxMulticastPkts OBJECT-TYPE
    SYNTAX      Counter64
    MAX-ACCESS  read-only
    STATUS      current
    DESCRIPTION 
        "Shows the number of multi-cast frames transmitted."
    ::= { vtssPortStatisticsIfGroupStatisticsEntry 11 }

vtssPortStatisticsIfGroupStatisticsTxBroadcastPkts OBJECT-TYPE
    SYNTAX      Counter64
    MAX-ACCESS  read-only
    STATUS      current
    DESCRIPTION 
        "Shows the number of broad-cast frames transmitted."
    ::= { vtssPortStatisticsIfGroupStatisticsEntry 12 }

vtssPortStatisticsIfGroupStatisticsTxNonUnicastPkts OBJECT-TYPE
    SYNTAX      Counter64
    MAX-ACCESS  read-only
    STATUS      current
    DESCRIPTION 
        "Shows the number of non uni-cast frames transmitted."
    ::= { vtssPortStatisticsIfGroupStatisticsEntry 13 }

vtssPortStatisticsIfGroupStatisticsTxDiscardPkts OBJECT-TYPE
    SYNTAX      Counter64
    MAX-ACCESS  read-only
    STATUS      current
    DESCRIPTION 
        "Shows the number of discard frames which should been transmitted."
    ::= { vtssPortStatisticsIfGroupStatisticsEntry 14 }

vtssPortStatisticsIfGroupStatisticsTxErrorPkts OBJECT-TYPE
    SYNTAX      Counter64
    MAX-ACCESS  read-only
    STATUS      current
    DESCRIPTION 
        "Shows the number of frames transmit with error."
    ::= { vtssPortStatisticsIfGroupStatisticsEntry 15 }

vtssPortStatisticsEthernetLikeStatisticsTable OBJECT-TYPE
    SYNTAX      SEQUENCE OF VTSSPortStatisticsEthernetLikeStatisticsEntry
    MAX-ACCESS  not-accessible
    STATUS      current
    DESCRIPTION 
        "This table represents the port Ethernet-like interfaces counters"
    ::= { vtssPortStatistics 3 }

vtssPortStatisticsEthernetLikeStatisticsEntry OBJECT-TYPE
    SYNTAX      VTSSPortStatisticsEthernetLikeStatisticsEntry
    MAX-ACCESS  not-accessible
    STATUS      current
    DESCRIPTION 
        "Each port interface has a set of statistics counters"
    INDEX       { vtssPortStatisticsEthernetLikeStatisticsIfIndex }
    ::= { vtssPortStatisticsEthernetLikeStatisticsTable 1 }

VTSSPortStatisticsEthernetLikeStatisticsEntry ::= SEQUENCE {
    vtssPortStatisticsEthernetLikeStatisticsIfIndex     VTSSInterfaceIndex,
    vtssPortStatisticsEthernetLikeStatisticsRxPauseFrames   Counter64,
    vtssPortStatisticsEthernetLikeStatisticsTxPauseFrames   Counter64
}

vtssPortStatisticsEthernetLikeStatisticsIfIndex OBJECT-TYPE
    SYNTAX      VTSSInterfaceIndex
    MAX-ACCESS  not-accessible
    STATUS      current
    DESCRIPTION 
        "Logical interface number."
    ::= { vtssPortStatisticsEthernetLikeStatisticsEntry 1 }

vtssPortStatisticsEthernetLikeStatisticsRxPauseFrames OBJECT-TYPE
    SYNTAX      Counter64
    MAX-ACCESS  read-only
    STATUS      current
    DESCRIPTION 
        "The number of pause frames received."
    ::= { vtssPortStatisticsEthernetLikeStatisticsEntry 2 }

vtssPortStatisticsEthernetLikeStatisticsTxPauseFrames OBJECT-TYPE
    SYNTAX      Counter64
    MAX-ACCESS  read-only
    STATUS      current
    DESCRIPTION 
        "The number of pause frames transmitted."
    ::= { vtssPortStatisticsEthernetLikeStatisticsEntry 3 }

vtssPortStatisticsQueuesStatisticsTable OBJECT-TYPE
    SYNTAX      SEQUENCE OF VTSSPortStatisticsQueuesStatisticsEntry
    MAX-ACCESS  not-accessible
    STATUS      current
    DESCRIPTION 
        "This table represents the port interfaces queues counters"
    ::= { vtssPortStatistics 4 }

vtssPortStatisticsQueuesStatisticsEntry OBJECT-TYPE
    SYNTAX      VTSSPortStatisticsQueuesStatisticsEntry
    MAX-ACCESS  not-accessible
    STATUS      current
    DESCRIPTION 
        "Each port interface has a set of statistics counters"
    INDEX       { vtssPortStatisticsQueuesStatisticsIfIndex, vtssPortStatisticsQueuesStatisticsQueue }
    ::= { vtssPortStatisticsQueuesStatisticsTable 1 }

VTSSPortStatisticsQueuesStatisticsEntry ::= SEQUENCE {
    vtssPortStatisticsQueuesStatisticsIfIndex   VTSSInterfaceIndex,
    vtssPortStatisticsQueuesStatisticsQueue     Integer32,
    vtssPortStatisticsQueuesStatisticsRxPrio    Counter64,
    vtssPortStatisticsQueuesStatisticsTxPrio    Counter64
}

vtssPortStatisticsQueuesStatisticsIfIndex OBJECT-TYPE
    SYNTAX      VTSSInterfaceIndex
    MAX-ACCESS  not-accessible
    STATUS      current
    DESCRIPTION 
        "Logical interface number."
    ::= { vtssPortStatisticsQueuesStatisticsEntry 1 }

vtssPortStatisticsQueuesStatisticsQueue OBJECT-TYPE
    SYNTAX      Integer32 (0..7)
    MAX-ACCESS  not-accessible
    STATUS      current
    DESCRIPTION 
        "Queue index."
    ::= { vtssPortStatisticsQueuesStatisticsEntry 2 }

vtssPortStatisticsQueuesStatisticsRxPrio OBJECT-TYPE
    SYNTAX      Counter64
    MAX-ACCESS  read-only
    STATUS      current
    DESCRIPTION 
        "The number of frames received for the queue."
    ::= { vtssPortStatisticsQueuesStatisticsEntry 3 }

vtssPortStatisticsQueuesStatisticsTxPrio OBJECT-TYPE
    SYNTAX      Counter64
    MAX-ACCESS  read-only
    STATUS      current
    DESCRIPTION 
        "The number of frames transmitted for the queue."
    ::= { vtssPortStatisticsQueuesStatisticsEntry 4 }

vtssPortStatisticsBridgeStatisticsTable OBJECT-TYPE
    SYNTAX      SEQUENCE OF VTSSPortStatisticsBridgeStatisticsEntry
    MAX-ACCESS  not-accessible
    STATUS      current
    DESCRIPTION 
        "This table represents the port interface bridge counters"
    ::= { vtssPortStatistics 5 }

vtssPortStatisticsBridgeStatisticsEntry OBJECT-TYPE
    SYNTAX      VTSSPortStatisticsBridgeStatisticsEntry
    MAX-ACCESS  not-accessible
    STATUS      current
    DESCRIPTION 
        "Each port interface has a set of statistics counters"
    INDEX       { vtssPortStatisticsBridgeStatisticsIfIndex }
    ::= { vtssPortStatisticsBridgeStatisticsTable 1 }

VTSSPortStatisticsBridgeStatisticsEntry ::= SEQUENCE {
    vtssPortStatisticsBridgeStatisticsIfIndex   VTSSInterfaceIndex,
    vtssPortStatisticsBridgeStatisticsRxBridgeDiscard   Counter64
}

vtssPortStatisticsBridgeStatisticsIfIndex OBJECT-TYPE
    SYNTAX      VTSSInterfaceIndex
    MAX-ACCESS  not-accessible
    STATUS      current
    DESCRIPTION 
        "Logical interface number."
    ::= { vtssPortStatisticsBridgeStatisticsEntry 1 }

vtssPortStatisticsBridgeStatisticsRxBridgeDiscard OBJECT-TYPE
    SYNTAX      Counter64
    MAX-ACCESS  read-only
    STATUS      current
    DESCRIPTION 
        "The number of bridge frames discarded."
    ::= { vtssPortStatisticsBridgeStatisticsEntry 2 }

vtssPortMibConformance OBJECT IDENTIFIER
    ::= { vtssPortMib 2 }

vtssPortMibCompliances OBJECT IDENTIFIER
    ::= { vtssPortMibConformance 1 }

vtssPortMibGroups OBJECT IDENTIFIER
    ::= { vtssPortMibConformance 2 }

vtssPortConfigInfoGroup OBJECT-GROUP
    OBJECTS     { vtssPortConfigShutdown, vtssPortConfigSpeed, 
                  vtssPortConfigAdvertiseDisabled, vtssPortConfigMediaType, 
                  vtssPortConfigFC, vtssPortConfigMTU, 
                  vtssPortConfigExcessiveRestart, vtssPortConfigPFC, 
                  vtssPortConfigFrameLengthCheck }
    STATUS      current
    DESCRIPTION
        "A collection of objects suitable for bulk operations."
    ::= { vtssPortMibGroups 1 }

vtssPortStatusInformationTableInfoGroup OBJECT-GROUP
    OBJECTS     { vtssPortStatusInformationLink, vtssPortStatusInformationFdx, 
                  vtssPortStatusInformationFiber, vtssPortStatusInformationSpeed, 
                  vtssPortStatusInformationSFPType, 
                  vtssPortStatusInformationSFPVendorName, 
                  vtssPortStatusInformationSFPVendorPN, 
                  vtssPortStatusInformationSFPVendorRev }
    STATUS      current
    DESCRIPTION
        "A collection of objects suitable for bulk operations."
    ::= { vtssPortMibGroups 2 }

vtssPortStatusVeriPhyResultTableInfoGroup OBJECT-GROUP
    OBJECTS     { vtssPortStatusVeriPhyResultVeriPhyStatusPairA, 
                  vtssPortStatusVeriPhyResultVeriPhyStatusPairB, 
                  vtssPortStatusVeriPhyResultVeriPhyStatusPairC, 
                  vtssPortStatusVeriPhyResultVeriPhyStatusPairD, 
                  vtssPortStatusVeriPhyResultVeriPhyLengthStatusPairA, 
                  vtssPortStatusVeriPhyResultVeriPhyLengthStatusPairB, 
                  vtssPortStatusVeriPhyResultVeriPhyLengthStatusPairC, 
                  vtssPortStatusVeriPhyResultVeriPhyLengthStatusPairD }
    STATUS      current
    DESCRIPTION
        "A collection of objects suitable for bulk operations."
    ::= { vtssPortMibGroups 3 }

vtssPortControlStatisticsClearTableInfoGroup OBJECT-GROUP
    OBJECTS     { vtssPortControlStatisticsClearStatisticsClear }
    STATUS      current
    DESCRIPTION
        "A collection of objects suitable for bulk operations."
    ::= { vtssPortMibGroups 4 }

vtssPortControlVeriPhyStartTableInfoGroup OBJECT-GROUP
    OBJECTS     { vtssPortControlVeriPhyStartStart }
    STATUS      current
    DESCRIPTION
        "A collection of objects suitable for bulk operations."
    ::= { vtssPortMibGroups 5 }

vtssPortStatisticsRmonStatisticsTableInfoGroup OBJECT-GROUP
    OBJECTS     { vtssPortStatisticsRmonStatisticsRxDropEvents, 
                  vtssPortStatisticsRmonStatisticsRxOctets, 
                  vtssPortStatisticsRmonStatisticsRxPkts, 
                  vtssPortStatisticsRmonStatisticsRxBroadcastPkts, 
                  vtssPortStatisticsRmonStatisticsRxMulticastPkts, 
                  vtssPortStatisticsRmonStatisticsRxCrcAlignErrPkts, 
                  vtssPortStatisticsRmonStatisticsRxUndersizePkts, 
                  vtssPortStatisticsRmonStatisticsRxOversizePkts, 
                  vtssPortStatisticsRmonStatisticsRxFragmentsPkts, 
                  vtssPortStatisticsRmonStatisticsRxJabbersPkts, 
                  vtssPortStatisticsRmonStatisticsRx64Pkts, 
                  vtssPortStatisticsRmonStatisticsRx65to127Pkts, 
                  vtssPortStatisticsRmonStatisticsRx128to255Pkts, 
                  vtssPortStatisticsRmonStatisticsRx256to511Pkts, 
                  vtssPortStatisticsRmonStatisticsRx512to1023Pkts, 
                  vtssPortStatisticsRmonStatisticsRx1024to1518Pkts, 
                  vtssPortStatisticsRmonStatisticsRx1519PktsToMax, 
                  vtssPortStatisticsRmonStatisticsTxDropEvents, 
                  vtssPortStatisticsRmonStatisticsTxOctets, 
                  vtssPortStatisticsRmonStatisticsTxPkts, 
                  vtssPortStatisticsRmonStatisticsTxBroadcastPkts, 
                  vtssPortStatisticsRmonStatisticsTxMulticastPkts, 
                  vtssPortStatisticsRmonStatisticsTx64Pkts, 
                  vtssPortStatisticsRmonStatisticsTx65to127Pkts, 
                  vtssPortStatisticsRmonStatisticsTx128to255Pkts, 
                  vtssPortStatisticsRmonStatisticsTx256to511Pkts, 
                  vtssPortStatisticsRmonStatisticsTx512to1023Pkts, 
                  vtssPortStatisticsRmonStatisticsTx1024to1518Pkts, 
                  vtssPortStatisticsRmonStatisticsTx1519PktsToMax }
    STATUS      current
    DESCRIPTION
        "A collection of objects suitable for bulk operations."
    ::= { vtssPortMibGroups 6 }

vtssPortStatisticsIfGroupStatisticsTableInfoGroup OBJECT-GROUP
    OBJECTS     { vtssPortStatisticsIfGroupStatisticsRxOctets, 
                  vtssPortStatisticsIfGroupStatisticsRxUnicastPkts, 
                  vtssPortStatisticsIfGroupStatisticsRxMulticastPkts, 
                  vtssPortStatisticsIfGroupStatisticsRxBroadcastPkts, 
                  vtssPortStatisticsIfGroupStatisticsRxNonUnicastPkts, 
                  vtssPortStatisticsIfGroupStatisticsRxDiscards, 
                  vtssPortStatisticsIfGroupStatisticsRxErrors, 
                  vtssPortStatisticsIfGroupStatisticsTxOctets, 
                  vtssPortStatisticsIfGroupStatisticsTxUnicastPkts, 
                  vtssPortStatisticsIfGroupStatisticsTxMulticastPkts, 
                  vtssPortStatisticsIfGroupStatisticsTxBroadcastPkts, 
                  vtssPortStatisticsIfGroupStatisticsTxNonUnicastPkts, 
                  vtssPortStatisticsIfGroupStatisticsTxDiscardPkts, 
                  vtssPortStatisticsIfGroupStatisticsTxErrorPkts }
    STATUS      current
    DESCRIPTION
        "A collection of objects suitable for bulk operations."
    ::= { vtssPortMibGroups 7 }

vtssPortStatisticsEthernetLikeStatisticsTableInfoGroup OBJECT-GROUP
    OBJECTS     { vtssPortStatisticsEthernetLikeStatisticsRxPauseFrames, 
                  vtssPortStatisticsEthernetLikeStatisticsTxPauseFrames }
    STATUS      current
    DESCRIPTION
        "A collection of objects suitable for bulk operations."
    ::= { vtssPortMibGroups 8 }

vtssPortStatisticsQueuesStatisticsTableInfoGroup OBJECT-GROUP
    OBJECTS     { vtssPortStatisticsQueuesStatisticsRxPrio, 
                  vtssPortStatisticsQueuesStatisticsTxPrio }
    STATUS      current
    DESCRIPTION
        "A collection of objects suitable for bulk operations."
    ::= { vtssPortMibGroups 9 }

vtssPortStatisticsBridgeStatisticsTableInfoGroup OBJECT-GROUP
    OBJECTS     { vtssPortStatisticsBridgeStatisticsRxBridgeDiscard }
    STATUS      current
    DESCRIPTION
        "A collection of objects suitable for bulk operations."
    ::= { vtssPortMibGroups 10 }

vtssPortMibCompliance MODULE-COMPLIANCE
    STATUS      current
    DESCRIPTION
        "The compliance statement for the implementation."

    MODULE      -- this module

        MANDATORY-GROUPS        { vtssPortConfigInfoGroup, 
                  vtssPortStatusInformationTableInfoGroup, 
                  vtssPortStatusVeriPhyResultTableInfoGroup, 
                  vtssPortControlStatisticsClearTableInfoGroup, 
                  vtssPortControlVeriPhyStartTableInfoGroup, 
                  vtssPortStatisticsRmonStatisticsTableInfoGroup, 
                  vtssPortStatisticsIfGroupStatisticsTableInfoGroup, 
                  vtssPortStatisticsEthernetLikeStatisticsTableInfoGroup, 
                  vtssPortStatisticsQueuesStatisticsTableInfoGroup, 
                  vtssPortStatisticsBridgeStatisticsTableInfoGroup }

    ::= { vtssPortMibCompliances 1 }

END
