-- *****************************************************************
-- MIB-RFC2544: BitStream ENT private MIB
-- ****************************************************************

MIB-RFC2544 DEFINITIONS ::= BEGIN

IMPORTS
    MODULE-COMPLIANCE, OBJECT-GROUP FROM SNMPv2-CONF
    MODULE-IDENTITY, OBJECT-TYPE FROM SNMPv2-SMI
    TEXTUAL-CONVENTION FROM SNMPv2-TC
    switchMgmt FROM BTS-SMI
    Unsigned32 FROM SNMPv2-SMI
    MacAddress FROM SNMPv2-TC
    TruthValue FROM SNMPv2-TC
    DisplayString FROM BTS-TC
    InterfaceIndex FROM BTS-TC
    RowEditorState FROM BTS-TC
    Unsigned8 FROM BTS-TC
    VlanOrZero FROM BTS-TC
    ;

rfc2544Mib MODULE-IDENTITY
    LAST-UPDATED "202503200000Z"
    ORGANIZATION
        "BitStream Sp. z o.o."
    CONTACT-INFO
        "www.bitstream.pl"
    DESCRIPTION
        "This is a private version of the RFC2544 MIB"
    REVISION    "201510200000Z"
    DESCRIPTION
        "Initial version"
    ::= { switchMgmt 110 }


Rfc2544TestStatus ::= TEXTUAL-CONVENTION
    STATUS      current
    DESCRIPTION
        "An integer that indicates the test status."
    SYNTAX      INTEGER { inactive(0), executing(1), cancelling(2),
                          cancelled(3), passed(4), failed(5) }

rfc2544MibObjects OBJECT IDENTIFIER
    ::= { rfc2544Mib 1 }

rfc2544Capabilities OBJECT IDENTIFIER
    ::= { rfc2544MibObjects 1 }

rfc2544CapabilitiesProfileCntMax OBJECT-TYPE
    SYNTAX      Unsigned32
    MAX-ACCESS  read-only
    STATUS      current
    DESCRIPTION
        "Number of profiles that can be defined and saved to non-volatile
         memory."
    ::= { rfc2544Capabilities 1 }

rfc2544CapabilitiesReportCntMax OBJECT-TYPE
    SYNTAX      Unsigned32
    MAX-ACCESS  read-only
    STATUS      current
    DESCRIPTION
        "Number of reports that can be saved to non-volatile memory."
    ::= { rfc2544Capabilities 2 }

rfc2544CapabilitiesConcurrentTestMax OBJECT-TYPE
    SYNTAX      Unsigned32
    MAX-ACCESS  read-only
    STATUS      current
    DESCRIPTION
        "Maximum number of concurrently running tests."
    ::= { rfc2544Capabilities 3 }

rfc2544Config OBJECT IDENTIFIER
    ::= { rfc2544MibObjects 2 }

rfc2544ConfigProfile OBJECT IDENTIFIER
    ::= { rfc2544Config 3 }

rfc2544ConfigProfileTable OBJECT-TYPE
    SYNTAX      SEQUENCE OF Rfc2544ConfigProfileEntry
    MAX-ACCESS  not-accessible
    STATUS      current
    DESCRIPTION
        "This is a table for managing RFC2544 profile entries."
    ::= { rfc2544ConfigProfile 1 }

rfc2544ConfigProfileEntry OBJECT-TYPE
    SYNTAX      Rfc2544ConfigProfileEntry
    MAX-ACCESS  not-accessible
    STATUS      current
    DESCRIPTION
        "Each entry has a set of parameters"
    INDEX       { rfc2544ConfigProfileName }
    ::= { rfc2544ConfigProfileTable 1 }

Rfc2544ConfigProfileEntry ::= SEQUENCE {
    rfc2544ConfigProfileName                DisplayString,
    rfc2544ConfigProfileDescription         DisplayString,
    rfc2544ConfigProfileDstOamAware         TruthValue,
    rfc2544ConfigProfileVlanId              VlanOrZero,
    rfc2544ConfigProfileVlanPcp             Unsigned32,
    rfc2544ConfigProfileVlanDei             Unsigned8,
    rfc2544ConfigProfileEgressInterface     InterfaceIndex,
    rfc2544ConfigProfileMegLevel            Unsigned32,
    rfc2544ConfigProfileDmac                MacAddress,
    rfc2544ConfigProfileFrameSize64         TruthValue,
    rfc2544ConfigProfileFrameSize128        TruthValue,
    rfc2544ConfigProfileFrameSize256        TruthValue,
    rfc2544ConfigProfileFrameSize512        TruthValue,
    rfc2544ConfigProfileFrameSize1024       TruthValue,
    rfc2544ConfigProfileFrameSize1280       TruthValue,
    rfc2544ConfigProfileFrameSize1518       TruthValue,
    rfc2544ConfigProfileFrameSize2000       TruthValue,
    rfc2544ConfigProfileFrameSize9600       TruthValue,
    rfc2544ConfigProfileDwellTime           Unsigned32,
    rfc2544ConfigProfileSequenceCheck       TruthValue,
    rfc2544ConfigProfileTpEnable            TruthValue,
    rfc2544ConfigProfileTpTrialDuration     Unsigned32,
    rfc2544ConfigProfileTpRateMin           Unsigned32,
    rfc2544ConfigProfileTpRateMax           Unsigned32,
    rfc2544ConfigProfileTpRateStep          Unsigned32,
    rfc2544ConfigProfileTpAllowedFrameLoss  Unsigned32,
    rfc2544ConfigProfileLaEnable            TruthValue,
    rfc2544ConfigProfileLaTrialDuration     Unsigned32,
    rfc2544ConfigProfileLaDmInterval        Unsigned32,
    rfc2544ConfigProfileLaAllowedFrameLoss  Unsigned32,
    rfc2544ConfigProfileFlEnable            TruthValue,
    rfc2544ConfigProfileFlTrialDuration     Unsigned32,
    rfc2544ConfigProfileFlRateMin           Unsigned32,
    rfc2544ConfigProfileFlRateMax           Unsigned32,
    rfc2544ConfigProfileFlRateStep          Unsigned32,
    rfc2544ConfigProfileBbEnable            TruthValue,
    rfc2544ConfigProfileBbTrialDuration     Unsigned32,
    rfc2544ConfigProfileBbTrialCnt          Unsigned32,
    rfc2544ConfigProfileAction              RowEditorState
}

rfc2544ConfigProfileName OBJECT-TYPE
    SYNTAX      DisplayString (SIZE(0..32))
    MAX-ACCESS  not-accessible
    STATUS      current
    DESCRIPTION
        "The name of the RFC2544 profile."
    ::= { rfc2544ConfigProfileEntry 1 }

rfc2544ConfigProfileDescription OBJECT-TYPE
    SYNTAX      DisplayString (SIZE(0..128))
    MAX-ACCESS  read-write
    STATUS      current
    DESCRIPTION
        "The description of the RFC2544 profile."
    ::= { rfc2544ConfigProfileEntry 2 }

rfc2544ConfigProfileDstOamAware OBJECT-TYPE
    SYNTAX      TruthValue
    MAX-ACCESS  read-write
    STATUS      current
    DESCRIPTION
        "TRUE if DST is OAM aware."
    ::= { rfc2544ConfigProfileEntry 3 }

rfc2544ConfigProfileVlanId OBJECT-TYPE
    SYNTAX      VlanOrZero
    MAX-ACCESS  read-write
    STATUS      current
    DESCRIPTION
        "0 (zero) means Port Down-MEP and anything else means VLAN Down-MEP."
    ::= { rfc2544ConfigProfileEntry 4 }

rfc2544ConfigProfileVlanPcp OBJECT-TYPE
    SYNTAX      Unsigned32 (0..7)
    MAX-ACCESS  read-write
    STATUS      current
    DESCRIPTION
        "The PCP value used in VLAN Down-MEPs."
    ::= { rfc2544ConfigProfileEntry 5 }

rfc2544ConfigProfileVlanDei OBJECT-TYPE
    SYNTAX      Unsigned8 (0..1)
    MAX-ACCESS  read-write
    STATUS      current
    DESCRIPTION
        "The DEI value used in VLAN Down-MEPs."
    ::= { rfc2544ConfigProfileEntry 6 }

rfc2544ConfigProfileEgressInterface OBJECT-TYPE
    SYNTAX      InterfaceIndex
    MAX-ACCESS  read-write
    STATUS      current
    DESCRIPTION
        "The interface on which to generate traffic."
    ::= { rfc2544ConfigProfileEntry 7 }

rfc2544ConfigProfileMegLevel OBJECT-TYPE
    SYNTAX      Unsigned32 (0..7)
    MAX-ACCESS  read-write
    STATUS      current
    DESCRIPTION
        "The MEG level (0 - 7) used in the generated OAM frames."
    ::= { rfc2544ConfigProfileEntry 8 }

rfc2544ConfigProfileDmac OBJECT-TYPE
    SYNTAX      MacAddress
    MAX-ACCESS  read-write
    STATUS      current
    DESCRIPTION
        "The destination MAC address used in the generated frames."
    ::= { rfc2544ConfigProfileEntry 9 }

rfc2544ConfigProfileFrameSize64 OBJECT-TYPE
    SYNTAX      TruthValue
    MAX-ACCESS  read-write
    STATUS      current
    DESCRIPTION
        "Set to TRUE to enable test with 64-byte frames."
    ::= { rfc2544ConfigProfileEntry 10 }

rfc2544ConfigProfileFrameSize128 OBJECT-TYPE
    SYNTAX      TruthValue
    MAX-ACCESS  read-write
    STATUS      current
    DESCRIPTION
        "Set to TRUE to enable test with 128-byte frames."
    ::= { rfc2544ConfigProfileEntry 11 }

rfc2544ConfigProfileFrameSize256 OBJECT-TYPE
    SYNTAX      TruthValue
    MAX-ACCESS  read-write
    STATUS      current
    DESCRIPTION
        "Set to TRUE to enable test with 256-byte frames."
    ::= { rfc2544ConfigProfileEntry 12 }

rfc2544ConfigProfileFrameSize512 OBJECT-TYPE
    SYNTAX      TruthValue
    MAX-ACCESS  read-write
    STATUS      current
    DESCRIPTION
        "Set to TRUE to enable test with 512-byte frames."
    ::= { rfc2544ConfigProfileEntry 13 }

rfc2544ConfigProfileFrameSize1024 OBJECT-TYPE
    SYNTAX      TruthValue
    MAX-ACCESS  read-write
    STATUS      current
    DESCRIPTION
        "Set to TRUE to enable test with 1024-byte frames."
    ::= { rfc2544ConfigProfileEntry 14 }

rfc2544ConfigProfileFrameSize1280 OBJECT-TYPE
    SYNTAX      TruthValue
    MAX-ACCESS  read-write
    STATUS      current
    DESCRIPTION
        "Set to TRUE to enable test with 1280-byte frames."
    ::= { rfc2544ConfigProfileEntry 15 }

rfc2544ConfigProfileFrameSize1518 OBJECT-TYPE
    SYNTAX      TruthValue
    MAX-ACCESS  read-write
    STATUS      current
    DESCRIPTION
        "Set to TRUE to enable test with 1518-byte frames."
    ::= { rfc2544ConfigProfileEntry 16 }

rfc2544ConfigProfileFrameSize2000 OBJECT-TYPE
    SYNTAX      TruthValue
    MAX-ACCESS  read-write
    STATUS      current
    DESCRIPTION
        "Set to TRUE to enable test with 2000-byte frames."
    ::= { rfc2544ConfigProfileEntry 17 }

rfc2544ConfigProfileFrameSize9600 OBJECT-TYPE
    SYNTAX      TruthValue
    MAX-ACCESS  read-write
    STATUS      current
    DESCRIPTION
        "Set to TRUE to enable test with 9600-byte frames."
    ::= { rfc2544ConfigProfileEntry 18 }

rfc2544ConfigProfileDwellTime OBJECT-TYPE
    SYNTAX      Unsigned32
    MAX-ACCESS  read-write
    STATUS      current
    DESCRIPTION
        "The time (in milliseconds) to wait after each trial for the system to
         settle before acquiring counters and other statistics from hardware.
         
         The dwell time must be divisible by 1000."
    ::= { rfc2544ConfigProfileEntry 30 }

rfc2544ConfigProfileSequenceCheck OBJECT-TYPE
    SYNTAX      TruthValue
    MAX-ACCESS  read-write
    STATUS      current
    DESCRIPTION
        "When TRUE, generated OAM frames are sequence numbered, and looped
         frames are checked for correct order upon reception."
    ::= { rfc2544ConfigProfileEntry 31 }

rfc2544ConfigProfileTpEnable OBJECT-TYPE
    SYNTAX      TruthValue
    MAX-ACCESS  read-write
    STATUS      current
    DESCRIPTION
        "Controls whether the throughput test is enabled or not."
    ::= { rfc2544ConfigProfileEntry 100 }

rfc2544ConfigProfileTpTrialDuration OBJECT-TYPE
    SYNTAX      Unsigned32
    MAX-ACCESS  read-write
    STATUS      current
    DESCRIPTION
        "Time - in seconds - to run one trial."
    ::= { rfc2544ConfigProfileEntry 101 }

rfc2544ConfigProfileTpRateMin OBJECT-TYPE
    SYNTAX      Unsigned32
    MAX-ACCESS  read-write
    STATUS      current
    DESCRIPTION
        "Minimum rate measured in permille of the line rate."
    ::= { rfc2544ConfigProfileEntry 102 }

rfc2544ConfigProfileTpRateMax OBJECT-TYPE
    SYNTAX      Unsigned32
    MAX-ACCESS  read-write
    STATUS      current
    DESCRIPTION
        "Maximum rate measured in permille of the line rate."
    ::= { rfc2544ConfigProfileEntry 103 }

rfc2544ConfigProfileTpRateStep OBJECT-TYPE
    SYNTAX      Unsigned32
    MAX-ACCESS  read-write
    STATUS      current
    DESCRIPTION
        "The step to change rate between trials, measured in permille of the
         line rate."
    ::= { rfc2544ConfigProfileEntry 104 }

rfc2544ConfigProfileTpAllowedFrameLoss OBJECT-TYPE
    SYNTAX      Unsigned32
    MAX-ACCESS  read-write
    STATUS      current
    DESCRIPTION
        "Allowable frame loss (in permille) for the test to be considered
         passed."
    ::= { rfc2544ConfigProfileEntry 105 }

rfc2544ConfigProfileLaEnable OBJECT-TYPE
    SYNTAX      TruthValue
    MAX-ACCESS  read-write
    STATUS      current
    DESCRIPTION
        "Controls whether the latency test is enabled or not."
    ::= { rfc2544ConfigProfileEntry 200 }

rfc2544ConfigProfileLaTrialDuration OBJECT-TYPE
    SYNTAX      Unsigned32
    MAX-ACCESS  read-write
    STATUS      current
    DESCRIPTION
        "Time - in seconds - to run one trial."
    ::= { rfc2544ConfigProfileEntry 201 }

rfc2544ConfigProfileLaDmInterval OBJECT-TYPE
    SYNTAX      Unsigned32
    MAX-ACCESS  read-write
    STATUS      current
    DESCRIPTION
        "Delay measurement interval, that is, the time (in milliseconds) between
         transmission of a Y.1731 1DM/DMM test frame.
         
         The interval must be divisible by 1000.."
    ::= { rfc2544ConfigProfileEntry 202 }

rfc2544ConfigProfileLaAllowedFrameLoss OBJECT-TYPE
    SYNTAX      Unsigned32
    MAX-ACCESS  read-write
    STATUS      current
    DESCRIPTION
        "Allowable frame loss (in permille) for the test to be considered
         passed."
    ::= { rfc2544ConfigProfileEntry 203 }

rfc2544ConfigProfileFlEnable OBJECT-TYPE
    SYNTAX      TruthValue
    MAX-ACCESS  read-write
    STATUS      current
    DESCRIPTION
        "Controls whether the frame loss test is enabled or not."
    ::= { rfc2544ConfigProfileEntry 300 }

rfc2544ConfigProfileFlTrialDuration OBJECT-TYPE
    SYNTAX      Unsigned32
    MAX-ACCESS  read-write
    STATUS      current
    DESCRIPTION
        "Time - in seconds - to run one trial."
    ::= { rfc2544ConfigProfileEntry 301 }

rfc2544ConfigProfileFlRateMin OBJECT-TYPE
    SYNTAX      Unsigned32
    MAX-ACCESS  read-write
    STATUS      current
    DESCRIPTION
        "Minimum rate measured in permille of the line rate."
    ::= { rfc2544ConfigProfileEntry 302 }

rfc2544ConfigProfileFlRateMax OBJECT-TYPE
    SYNTAX      Unsigned32
    MAX-ACCESS  read-write
    STATUS      current
    DESCRIPTION
        "Maximum rate measured in permille of the line rate."
    ::= { rfc2544ConfigProfileEntry 303 }

rfc2544ConfigProfileFlRateStep OBJECT-TYPE
    SYNTAX      Unsigned32
    MAX-ACCESS  read-write
    STATUS      current
    DESCRIPTION
        "The step to change rate between trials, measured in permille of the
         line rate."
    ::= { rfc2544ConfigProfileEntry 304 }

rfc2544ConfigProfileBbEnable OBJECT-TYPE
    SYNTAX      TruthValue
    MAX-ACCESS  read-write
    STATUS      current
    DESCRIPTION
        "Controls whether the frame loss test is enabled or not."
    ::= { rfc2544ConfigProfileEntry 400 }

rfc2544ConfigProfileBbTrialDuration OBJECT-TYPE
    SYNTAX      Unsigned32
    MAX-ACCESS  read-write
    STATUS      current
    DESCRIPTION
        "Time - in milliseconds - to run one trial."
    ::= { rfc2544ConfigProfileEntry 401 }

rfc2544ConfigProfileBbTrialCnt OBJECT-TYPE
    SYNTAX      Unsigned32
    MAX-ACCESS  read-write
    STATUS      current
    DESCRIPTION
        "Number of times the trial will be executed."
    ::= { rfc2544ConfigProfileEntry 402 }

rfc2544ConfigProfileAction OBJECT-TYPE
    SYNTAX      RowEditorState
    MAX-ACCESS  read-write
    STATUS      current
    DESCRIPTION
        "Action"
    ::= { rfc2544ConfigProfileEntry 10000 }

rfc2544ConfigProfileTableRowEditor OBJECT IDENTIFIER
    ::= { rfc2544ConfigProfile 2 }

rfc2544ConfigProfileTableRowEditorName OBJECT-TYPE
    SYNTAX      DisplayString (SIZE(0..32))
    MAX-ACCESS  read-write
    STATUS      current
    DESCRIPTION
        "The name of the RFC2544 profile."
    ::= { rfc2544ConfigProfileTableRowEditor 1 }

rfc2544ConfigProfileTableRowEditorDescription OBJECT-TYPE
    SYNTAX      DisplayString (SIZE(0..128))
    MAX-ACCESS  read-write
    STATUS      current
    DESCRIPTION
        "The description of the RFC2544 profile."
    ::= { rfc2544ConfigProfileTableRowEditor 2 }

rfc2544ConfigProfileTableRowEditorDstOamAware OBJECT-TYPE
    SYNTAX      TruthValue
    MAX-ACCESS  read-write
    STATUS      current
    DESCRIPTION
        "TRUE if DST is OAM aware."
    ::= { rfc2544ConfigProfileTableRowEditor 3 }

rfc2544ConfigProfileTableRowEditorVlanId OBJECT-TYPE
    SYNTAX      VlanOrZero
    MAX-ACCESS  read-write
    STATUS      current
    DESCRIPTION
        "0 (zero) means Port Down-MEP and anything else means VLAN Down-MEP."
    ::= { rfc2544ConfigProfileTableRowEditor 4 }

rfc2544ConfigProfileTableRowEditorVlanPcp OBJECT-TYPE
    SYNTAX      Unsigned32 (0..7)
    MAX-ACCESS  read-write
    STATUS      current
    DESCRIPTION
        "The PCP value used in VLAN Down-MEPs."
    ::= { rfc2544ConfigProfileTableRowEditor 5 }

rfc2544ConfigProfileTableRowEditorVlanDei OBJECT-TYPE
    SYNTAX      Unsigned8 (0..1)
    MAX-ACCESS  read-write
    STATUS      current
    DESCRIPTION
        "The DEI value used in VLAN Down-MEPs."
    ::= { rfc2544ConfigProfileTableRowEditor 6 }

rfc2544ConfigProfileTableRowEditorEgressInterface OBJECT-TYPE
    SYNTAX      InterfaceIndex
    MAX-ACCESS  read-write
    STATUS      current
    DESCRIPTION
        "The interface on which to generate traffic."
    ::= { rfc2544ConfigProfileTableRowEditor 7 }

rfc2544ConfigProfileTableRowEditorMegLevel OBJECT-TYPE
    SYNTAX      Unsigned32 (0..7)
    MAX-ACCESS  read-write
    STATUS      current
    DESCRIPTION
        "The MEG level (0 - 7) used in the generated OAM frames."
    ::= { rfc2544ConfigProfileTableRowEditor 8 }

rfc2544ConfigProfileTableRowEditorDmac OBJECT-TYPE
    SYNTAX      MacAddress
    MAX-ACCESS  read-write
    STATUS      current
    DESCRIPTION
        "The destination MAC address used in the generated frames."
    ::= { rfc2544ConfigProfileTableRowEditor 9 }

rfc2544ConfigProfileTableRowEditorFrameSize64 OBJECT-TYPE
    SYNTAX      TruthValue
    MAX-ACCESS  read-write
    STATUS      current
    DESCRIPTION
        "Set to TRUE to enable test with 64-byte frames."
    ::= { rfc2544ConfigProfileTableRowEditor 10 }

rfc2544ConfigProfileTableRowEditorFrameSize128 OBJECT-TYPE
    SYNTAX      TruthValue
    MAX-ACCESS  read-write
    STATUS      current
    DESCRIPTION
        "Set to TRUE to enable test with 128-byte frames."
    ::= { rfc2544ConfigProfileTableRowEditor 11 }

rfc2544ConfigProfileTableRowEditorFrameSize256 OBJECT-TYPE
    SYNTAX      TruthValue
    MAX-ACCESS  read-write
    STATUS      current
    DESCRIPTION
        "Set to TRUE to enable test with 256-byte frames."
    ::= { rfc2544ConfigProfileTableRowEditor 12 }

rfc2544ConfigProfileTableRowEditorFrameSize512 OBJECT-TYPE
    SYNTAX      TruthValue
    MAX-ACCESS  read-write
    STATUS      current
    DESCRIPTION
        "Set to TRUE to enable test with 512-byte frames."
    ::= { rfc2544ConfigProfileTableRowEditor 13 }

rfc2544ConfigProfileTableRowEditorFrameSize1024 OBJECT-TYPE
    SYNTAX      TruthValue
    MAX-ACCESS  read-write
    STATUS      current
    DESCRIPTION
        "Set to TRUE to enable test with 1024-byte frames."
    ::= { rfc2544ConfigProfileTableRowEditor 14 }

rfc2544ConfigProfileTableRowEditorFrameSize1280 OBJECT-TYPE
    SYNTAX      TruthValue
    MAX-ACCESS  read-write
    STATUS      current
    DESCRIPTION
        "Set to TRUE to enable test with 1280-byte frames."
    ::= { rfc2544ConfigProfileTableRowEditor 15 }

rfc2544ConfigProfileTableRowEditorFrameSize1518 OBJECT-TYPE
    SYNTAX      TruthValue
    MAX-ACCESS  read-write
    STATUS      current
    DESCRIPTION
        "Set to TRUE to enable test with 1518-byte frames."
    ::= { rfc2544ConfigProfileTableRowEditor 16 }

rfc2544ConfigProfileTableRowEditorFrameSize2000 OBJECT-TYPE
    SYNTAX      TruthValue
    MAX-ACCESS  read-write
    STATUS      current
    DESCRIPTION
        "Set to TRUE to enable test with 2000-byte frames."
    ::= { rfc2544ConfigProfileTableRowEditor 17 }

rfc2544ConfigProfileTableRowEditorFrameSize9600 OBJECT-TYPE
    SYNTAX      TruthValue
    MAX-ACCESS  read-write
    STATUS      current
    DESCRIPTION
        "Set to TRUE to enable test with 9600-byte frames."
    ::= { rfc2544ConfigProfileTableRowEditor 18 }

rfc2544ConfigProfileTableRowEditorDwellTime OBJECT-TYPE
    SYNTAX      Unsigned32
    MAX-ACCESS  read-write
    STATUS      current
    DESCRIPTION
        "The time (in milliseconds) to wait after each trial for the system to
         settle before acquiring counters and other statistics from hardware.
         
         The dwell time must be divisible by 1000."
    ::= { rfc2544ConfigProfileTableRowEditor 30 }

rfc2544ConfigProfileTableRowEditorSequenceCheck OBJECT-TYPE
    SYNTAX      TruthValue
    MAX-ACCESS  read-write
    STATUS      current
    DESCRIPTION
        "When TRUE, generated OAM frames are sequence numbered, and looped
         frames are checked for correct order upon reception."
    ::= { rfc2544ConfigProfileTableRowEditor 31 }

rfc2544ConfigProfileTableRowEditorTpEnable OBJECT-TYPE
    SYNTAX      TruthValue
    MAX-ACCESS  read-write
    STATUS      current
    DESCRIPTION
        "Controls whether the throughput test is enabled or not."
    ::= { rfc2544ConfigProfileTableRowEditor 100 }

rfc2544ConfigProfileTableRowEditorTpTrialDuration OBJECT-TYPE
    SYNTAX      Unsigned32
    MAX-ACCESS  read-write
    STATUS      current
    DESCRIPTION
        "Time - in seconds - to run one trial."
    ::= { rfc2544ConfigProfileTableRowEditor 101 }

rfc2544ConfigProfileTableRowEditorTpRateMin OBJECT-TYPE
    SYNTAX      Unsigned32
    MAX-ACCESS  read-write
    STATUS      current
    DESCRIPTION
        "Minimum rate measured in permille of the line rate."
    ::= { rfc2544ConfigProfileTableRowEditor 102 }

rfc2544ConfigProfileTableRowEditorTpRateMax OBJECT-TYPE
    SYNTAX      Unsigned32
    MAX-ACCESS  read-write
    STATUS      current
    DESCRIPTION
        "Maximum rate measured in permille of the line rate."
    ::= { rfc2544ConfigProfileTableRowEditor 103 }

rfc2544ConfigProfileTableRowEditorTpRateStep OBJECT-TYPE
    SYNTAX      Unsigned32
    MAX-ACCESS  read-write
    STATUS      current
    DESCRIPTION
        "The step to change rate between trials, measured in permille of the
         line rate."
    ::= { rfc2544ConfigProfileTableRowEditor 104 }

rfc2544ConfigProfileTableRowEditorTpAllowedFrameLoss OBJECT-TYPE
    SYNTAX      Unsigned32
    MAX-ACCESS  read-write
    STATUS      current
    DESCRIPTION
        "Allowable frame loss (in permille) for the test to be considered
         passed."
    ::= { rfc2544ConfigProfileTableRowEditor 105 }

rfc2544ConfigProfileTableRowEditorLaEnable OBJECT-TYPE
    SYNTAX      TruthValue
    MAX-ACCESS  read-write
    STATUS      current
    DESCRIPTION
        "Controls whether the latency test is enabled or not."
    ::= { rfc2544ConfigProfileTableRowEditor 200 }

rfc2544ConfigProfileTableRowEditorLaTrialDuration OBJECT-TYPE
    SYNTAX      Unsigned32
    MAX-ACCESS  read-write
    STATUS      current
    DESCRIPTION
        "Time - in seconds - to run one trial."
    ::= { rfc2544ConfigProfileTableRowEditor 201 }

rfc2544ConfigProfileTableRowEditorLaDmInterval OBJECT-TYPE
    SYNTAX      Unsigned32
    MAX-ACCESS  read-write
    STATUS      current
    DESCRIPTION
        "Delay measurement interval, that is, the time (in milliseconds) between
         transmission of a Y.1731 1DM/DMM test frame.
         
         The interval must be divisible by 1000.."
    ::= { rfc2544ConfigProfileTableRowEditor 202 }

rfc2544ConfigProfileTableRowEditorLaAllowedFrameLoss OBJECT-TYPE
    SYNTAX      Unsigned32
    MAX-ACCESS  read-write
    STATUS      current
    DESCRIPTION
        "Allowable frame loss (in permille) for the test to be considered
         passed."
    ::= { rfc2544ConfigProfileTableRowEditor 203 }

rfc2544ConfigProfileTableRowEditorFlEnable OBJECT-TYPE
    SYNTAX      TruthValue
    MAX-ACCESS  read-write
    STATUS      current
    DESCRIPTION
        "Controls whether the frame loss test is enabled or not."
    ::= { rfc2544ConfigProfileTableRowEditor 300 }

rfc2544ConfigProfileTableRowEditorFlTrialDuration OBJECT-TYPE
    SYNTAX      Unsigned32
    MAX-ACCESS  read-write
    STATUS      current
    DESCRIPTION
        "Time - in seconds - to run one trial."
    ::= { rfc2544ConfigProfileTableRowEditor 301 }

rfc2544ConfigProfileTableRowEditorFlRateMin OBJECT-TYPE
    SYNTAX      Unsigned32
    MAX-ACCESS  read-write
    STATUS      current
    DESCRIPTION
        "Minimum rate measured in permille of the line rate."
    ::= { rfc2544ConfigProfileTableRowEditor 302 }

rfc2544ConfigProfileTableRowEditorFlRateMax OBJECT-TYPE
    SYNTAX      Unsigned32
    MAX-ACCESS  read-write
    STATUS      current
    DESCRIPTION
        "Maximum rate measured in permille of the line rate."
    ::= { rfc2544ConfigProfileTableRowEditor 303 }

rfc2544ConfigProfileTableRowEditorFlRateStep OBJECT-TYPE
    SYNTAX      Unsigned32
    MAX-ACCESS  read-write
    STATUS      current
    DESCRIPTION
        "The step to change rate between trials, measured in permille of the
         line rate."
    ::= { rfc2544ConfigProfileTableRowEditor 304 }

rfc2544ConfigProfileTableRowEditorBbEnable OBJECT-TYPE
    SYNTAX      TruthValue
    MAX-ACCESS  read-write
    STATUS      current
    DESCRIPTION
        "Controls whether the frame loss test is enabled or not."
    ::= { rfc2544ConfigProfileTableRowEditor 400 }

rfc2544ConfigProfileTableRowEditorBbTrialDuration OBJECT-TYPE
    SYNTAX      Unsigned32
    MAX-ACCESS  read-write
    STATUS      current
    DESCRIPTION
        "Time - in milliseconds - to run one trial."
    ::= { rfc2544ConfigProfileTableRowEditor 401 }

rfc2544ConfigProfileTableRowEditorBbTrialCnt OBJECT-TYPE
    SYNTAX      Unsigned32
    MAX-ACCESS  read-write
    STATUS      current
    DESCRIPTION
        "Number of times the trial will be executed."
    ::= { rfc2544ConfigProfileTableRowEditor 402 }

rfc2544ConfigProfileTableRowEditorAction OBJECT-TYPE
    SYNTAX      RowEditorState
    MAX-ACCESS  read-write
    STATUS      current
    DESCRIPTION
        "Action"
    ::= { rfc2544ConfigProfileTableRowEditor 10000 }

rfc2544Status OBJECT IDENTIFIER
    ::= { rfc2544MibObjects 3 }

rfc2544StatusReport OBJECT IDENTIFIER
    ::= { rfc2544Status 3 }

rfc2544StatusReportTable OBJECT-TYPE
    SYNTAX      SEQUENCE OF Rfc2544StatusReportEntry
    MAX-ACCESS  not-accessible
    STATUS      current
    DESCRIPTION
        "This table contains report information and is ordered by report name."
    ::= { rfc2544StatusReport 1 }

rfc2544StatusReportEntry OBJECT-TYPE
    SYNTAX      Rfc2544StatusReportEntry
    MAX-ACCESS  not-accessible
    STATUS      current
    DESCRIPTION
        "Each entry has a set of parameters"
    INDEX       { rfc2544StatusReportName }
    ::= { rfc2544StatusReportTable 1 }

Rfc2544StatusReportEntry ::= SEQUENCE {
    rfc2544StatusReportName          DisplayString,
    rfc2544StatusReportDescription   DisplayString,
    rfc2544StatusReportCreationTime  DisplayString,
    rfc2544StatusReportStatus        Rfc2544TestStatus,
    rfc2544StatusReportPath          DisplayString
}

rfc2544StatusReportName OBJECT-TYPE
    SYNTAX      DisplayString (SIZE(0..32))
    MAX-ACCESS  not-accessible
    STATUS      current
    DESCRIPTION
        "The name of the RFC2544 test report."
    ::= { rfc2544StatusReportEntry 1 }

rfc2544StatusReportDescription OBJECT-TYPE
    SYNTAX      DisplayString (SIZE(0..128))
    MAX-ACCESS  read-only
    STATUS      current
    DESCRIPTION
        "The description of the RFC2544 test report."
    ::= { rfc2544StatusReportEntry 2 }

rfc2544StatusReportCreationTime OBJECT-TYPE
    SYNTAX      DisplayString (SIZE(0..25))
    MAX-ACCESS  read-only
    STATUS      current
    DESCRIPTION
        "Time of creation of this report."
    ::= { rfc2544StatusReportEntry 3 }

rfc2544StatusReportStatus OBJECT-TYPE
    SYNTAX      Rfc2544TestStatus
    MAX-ACCESS  read-only
    STATUS      current
    DESCRIPTION
        "Execution status of this report."
    ::= { rfc2544StatusReportEntry 4 }

rfc2544StatusReportPath OBJECT-TYPE
    SYNTAX      DisplayString (SIZE(0..128))
    MAX-ACCESS  read-only
    STATUS      current
    DESCRIPTION
        "This is the file system location to retrieve this report."
    ::= { rfc2544StatusReportEntry 5 }

rfc2544Control OBJECT IDENTIFIER
    ::= { rfc2544MibObjects 4 }

rfc2544ControlReport OBJECT IDENTIFIER
    ::= { rfc2544Control 3 }

rfc2544ControlReportDelete OBJECT IDENTIFIER
    ::= { rfc2544ControlReport 1 }

rfc2544ControlReportDeleteName OBJECT-TYPE
    SYNTAX      DisplayString (SIZE(0..32))
    MAX-ACCESS  read-write
    STATUS      current
    DESCRIPTION
        "The name of the RFC2544 test report to delete."
    ::= { rfc2544ControlReportDelete 1 }

rfc2544ControlTest OBJECT IDENTIFIER
    ::= { rfc2544Control 4 }

rfc2544ControlTestTable OBJECT-TYPE
    SYNTAX      SEQUENCE OF Rfc2544ControlTestEntry
    MAX-ACCESS  not-accessible
    STATUS      current
    DESCRIPTION
        "This is a table for managing RFC2544 tests. Each entry represents a
         running test."
    ::= { rfc2544ControlTest 1 }

rfc2544ControlTestEntry OBJECT-TYPE
    SYNTAX      Rfc2544ControlTestEntry
    MAX-ACCESS  not-accessible
    STATUS      current
    DESCRIPTION
        "Each entry has a set of parameters that identifies the test.
         
         Start a new test by using the row editor to add a new entry.
         
         Stop a running test by setting the action object in an entry to 1.
         
         The other objects in an entry cannot be modified."
    INDEX       { rfc2544ControlTestName }
    ::= { rfc2544ControlTestTable 1 }

Rfc2544ControlTestEntry ::= SEQUENCE {
    rfc2544ControlTestName         DisplayString,
    rfc2544ControlTestDescription  DisplayString,
    rfc2544ControlTestProfileName  DisplayString,
    rfc2544ControlTestDmac         MacAddress,
    rfc2544ControlTestAction       RowEditorState
}

rfc2544ControlTestName OBJECT-TYPE
    SYNTAX      DisplayString (SIZE(0..32))
    MAX-ACCESS  not-accessible
    STATUS      current
    DESCRIPTION
        "The name of the RFC2544 test report."
    ::= { rfc2544ControlTestEntry 1 }

rfc2544ControlTestDescription OBJECT-TYPE
    SYNTAX      DisplayString (SIZE(0..128))
    MAX-ACCESS  read-write
    STATUS      current
    DESCRIPTION
        "The description of the RFC2544 test report."
    ::= { rfc2544ControlTestEntry 2 }

rfc2544ControlTestProfileName OBJECT-TYPE
    SYNTAX      DisplayString (SIZE(0..32))
    MAX-ACCESS  read-write
    STATUS      current
    DESCRIPTION
        "The name of the RFC2544 profile to use when performing the test."
    ::= { rfc2544ControlTestEntry 3 }

rfc2544ControlTestDmac OBJECT-TYPE
    SYNTAX      MacAddress
    MAX-ACCESS  read-write
    STATUS      current
    DESCRIPTION
        "The destination MAC address found in the profile is used as DMAC in the
         generated frames, unless overridden with this field.
         
         In order to override, the Dmac must be a non-zero unicast MAC address.
         
         In order not to override, set the Dmac to all-zeros."
    ::= { rfc2544ControlTestEntry 4 }

rfc2544ControlTestAction OBJECT-TYPE
    SYNTAX      RowEditorState
    MAX-ACCESS  read-write
    STATUS      current
    DESCRIPTION
        "Action"
    ::= { rfc2544ControlTestEntry 10000 }

rfc2544ControlTestTableRowEditor OBJECT IDENTIFIER
    ::= { rfc2544ControlTest 2 }

rfc2544ControlTestTableRowEditorName OBJECT-TYPE
    SYNTAX      DisplayString (SIZE(0..32))
    MAX-ACCESS  read-write
    STATUS      current
    DESCRIPTION
        "The name of the RFC2544 test report."
    ::= { rfc2544ControlTestTableRowEditor 1 }

rfc2544ControlTestTableRowEditorDescription OBJECT-TYPE
    SYNTAX      DisplayString (SIZE(0..128))
    MAX-ACCESS  read-write
    STATUS      current
    DESCRIPTION
        "The description of the RFC2544 test report."
    ::= { rfc2544ControlTestTableRowEditor 2 }

rfc2544ControlTestTableRowEditorProfileName OBJECT-TYPE
    SYNTAX      DisplayString (SIZE(0..32))
    MAX-ACCESS  read-write
    STATUS      current
    DESCRIPTION
        "The name of the RFC2544 profile to use when performing the test."
    ::= { rfc2544ControlTestTableRowEditor 3 }

rfc2544ControlTestTableRowEditorDmac OBJECT-TYPE
    SYNTAX      MacAddress
    MAX-ACCESS  read-write
    STATUS      current
    DESCRIPTION
        "The destination MAC address found in the profile is used as DMAC in the
         generated frames, unless overridden with this field.
         
         In order to override, the Dmac must be a non-zero unicast MAC address.
         
         In order not to override, set the Dmac to all-zeros."
    ::= { rfc2544ControlTestTableRowEditor 4 }

rfc2544ControlTestTableRowEditorAction OBJECT-TYPE
    SYNTAX      RowEditorState
    MAX-ACCESS  read-write
    STATUS      current
    DESCRIPTION
        "Action"
    ::= { rfc2544ControlTestTableRowEditor 10000 }

rfc2544ControlTestStart OBJECT IDENTIFIER
    ::= { rfc2544ControlTest 4 }

rfc2544ControlTestStartName OBJECT-TYPE
    SYNTAX      DisplayString (SIZE(0..32))
    MAX-ACCESS  read-write
    STATUS      current
    DESCRIPTION
        "The name of the RFC2544 test to start."
    ::= { rfc2544ControlTestStart 1 }

rfc2544ControlTestStop OBJECT IDENTIFIER
    ::= { rfc2544ControlTest 5 }

rfc2544ControlTestStopName OBJECT-TYPE
    SYNTAX      DisplayString (SIZE(0..32))
    MAX-ACCESS  read-write
    STATUS      current
    DESCRIPTION
        "The name of the RFC2544 test to stop."
    ::= { rfc2544ControlTestStop 1 }

rfc2544MibConformance OBJECT IDENTIFIER
    ::= { rfc2544Mib 2 }

rfc2544MibCompliances OBJECT IDENTIFIER
    ::= { rfc2544MibConformance 1 }

rfc2544MibGroups OBJECT IDENTIFIER
    ::= { rfc2544MibConformance 2 }

rfc2544CapabilitiesInfoGroup OBJECT-GROUP
    OBJECTS     { rfc2544CapabilitiesProfileCntMax,
                  rfc2544CapabilitiesReportCntMax,
                  rfc2544CapabilitiesConcurrentTestMax }
    STATUS      current
    DESCRIPTION
        "A collection of objects suitable for bulk operations."
    ::= { rfc2544MibGroups 1 }

rfc2544ConfigProfileTableInfoGroup OBJECT-GROUP
    OBJECTS     { rfc2544ConfigProfileDescription,
                  rfc2544ConfigProfileDstOamAware,
                  rfc2544ConfigProfileVlanId,
                  rfc2544ConfigProfileVlanPcp,
                  rfc2544ConfigProfileVlanDei,
                  rfc2544ConfigProfileEgressInterface,
                  rfc2544ConfigProfileMegLevel,
                  rfc2544ConfigProfileDmac,
                  rfc2544ConfigProfileFrameSize64,
                  rfc2544ConfigProfileFrameSize128,
                  rfc2544ConfigProfileFrameSize256,
                  rfc2544ConfigProfileFrameSize512,
                  rfc2544ConfigProfileFrameSize1024,
                  rfc2544ConfigProfileFrameSize1280,
                  rfc2544ConfigProfileFrameSize1518,
                  rfc2544ConfigProfileFrameSize2000,
                  rfc2544ConfigProfileFrameSize9600,
                  rfc2544ConfigProfileDwellTime,
                  rfc2544ConfigProfileSequenceCheck,
                  rfc2544ConfigProfileTpEnable,
                  rfc2544ConfigProfileTpTrialDuration,
                  rfc2544ConfigProfileTpRateMin,
                  rfc2544ConfigProfileTpRateMax,
                  rfc2544ConfigProfileTpRateStep,
                  rfc2544ConfigProfileTpAllowedFrameLoss,
                  rfc2544ConfigProfileLaEnable,
                  rfc2544ConfigProfileLaTrialDuration,
                  rfc2544ConfigProfileLaDmInterval,
                  rfc2544ConfigProfileLaAllowedFrameLoss,
                  rfc2544ConfigProfileFlEnable,
                  rfc2544ConfigProfileFlTrialDuration,
                  rfc2544ConfigProfileFlRateMin,
                  rfc2544ConfigProfileFlRateMax,
                  rfc2544ConfigProfileFlRateStep,
                  rfc2544ConfigProfileBbEnable,
                  rfc2544ConfigProfileBbTrialDuration,
                  rfc2544ConfigProfileBbTrialCnt,
                  rfc2544ConfigProfileAction }
    STATUS      current
    DESCRIPTION
        "A collection of objects suitable for bulk operations."
    ::= { rfc2544MibGroups 2 }

rfc2544ConfigProfileTableRowEditorInfoGroup OBJECT-GROUP
    OBJECTS     { rfc2544ConfigProfileTableRowEditorName,
                  rfc2544ConfigProfileTableRowEditorDescription,
                  rfc2544ConfigProfileTableRowEditorDstOamAware,
                  rfc2544ConfigProfileTableRowEditorVlanId,
                  rfc2544ConfigProfileTableRowEditorVlanPcp,
                  rfc2544ConfigProfileTableRowEditorVlanDei,
                  rfc2544ConfigProfileTableRowEditorEgressInterface,
                  rfc2544ConfigProfileTableRowEditorMegLevel,
                  rfc2544ConfigProfileTableRowEditorDmac,
                  rfc2544ConfigProfileTableRowEditorFrameSize64,
                  rfc2544ConfigProfileTableRowEditorFrameSize128,
                  rfc2544ConfigProfileTableRowEditorFrameSize256,
                  rfc2544ConfigProfileTableRowEditorFrameSize512,
                  rfc2544ConfigProfileTableRowEditorFrameSize1024,
                  rfc2544ConfigProfileTableRowEditorFrameSize1280,
                  rfc2544ConfigProfileTableRowEditorFrameSize1518,
                  rfc2544ConfigProfileTableRowEditorFrameSize2000,
                  rfc2544ConfigProfileTableRowEditorFrameSize9600,
                  rfc2544ConfigProfileTableRowEditorDwellTime,
                  rfc2544ConfigProfileTableRowEditorSequenceCheck,
                  rfc2544ConfigProfileTableRowEditorTpEnable,
                  rfc2544ConfigProfileTableRowEditorTpTrialDuration,
                  rfc2544ConfigProfileTableRowEditorTpRateMin,
                  rfc2544ConfigProfileTableRowEditorTpRateMax,
                  rfc2544ConfigProfileTableRowEditorTpRateStep,
                  rfc2544ConfigProfileTableRowEditorTpAllowedFrameLoss,
                  rfc2544ConfigProfileTableRowEditorLaEnable,
                  rfc2544ConfigProfileTableRowEditorLaTrialDuration,
                  rfc2544ConfigProfileTableRowEditorLaDmInterval,
                  rfc2544ConfigProfileTableRowEditorLaAllowedFrameLoss,
                  rfc2544ConfigProfileTableRowEditorFlEnable,
                  rfc2544ConfigProfileTableRowEditorFlTrialDuration,
                  rfc2544ConfigProfileTableRowEditorFlRateMin,
                  rfc2544ConfigProfileTableRowEditorFlRateMax,
                  rfc2544ConfigProfileTableRowEditorFlRateStep,
                  rfc2544ConfigProfileTableRowEditorBbEnable,
                  rfc2544ConfigProfileTableRowEditorBbTrialDuration,
                  rfc2544ConfigProfileTableRowEditorBbTrialCnt,
                  rfc2544ConfigProfileTableRowEditorAction }
    STATUS      current
    DESCRIPTION
        "A collection of objects suitable for bulk operations."
    ::= { rfc2544MibGroups 3 }

rfc2544StatusReportTableInfoGroup OBJECT-GROUP
    OBJECTS     { rfc2544StatusReportDescription,
                  rfc2544StatusReportCreationTime,
                  rfc2544StatusReportStatus,
                  rfc2544StatusReportPath }
    STATUS      current
    DESCRIPTION
        "A collection of objects suitable for bulk operations."
    ::= { rfc2544MibGroups 4 }

rfc2544ControlReportDeleteInfoGroup OBJECT-GROUP
    OBJECTS     { rfc2544ControlReportDeleteName }
    STATUS      current
    DESCRIPTION
        "A collection of objects suitable for bulk operations."
    ::= { rfc2544MibGroups 5 }

rfc2544ControlTestTableInfoGroup OBJECT-GROUP
    OBJECTS     { rfc2544ControlTestDescription,
                  rfc2544ControlTestProfileName,
                  rfc2544ControlTestDmac,
                  rfc2544ControlTestAction }
    STATUS      current
    DESCRIPTION
        "A collection of objects suitable for bulk operations."
    ::= { rfc2544MibGroups 6 }

rfc2544ControlTestTableRowEditorInfoGroup OBJECT-GROUP
    OBJECTS     { rfc2544ControlTestTableRowEditorName,
                  rfc2544ControlTestTableRowEditorDescription,
                  rfc2544ControlTestTableRowEditorProfileName,
                  rfc2544ControlTestTableRowEditorDmac,
                  rfc2544ControlTestTableRowEditorAction }
    STATUS      current
    DESCRIPTION
        "A collection of objects suitable for bulk operations."
    ::= { rfc2544MibGroups 7 }

rfc2544ControlTestStartInfoGroup OBJECT-GROUP
    OBJECTS     { rfc2544ControlTestStartName }
    STATUS      current
    DESCRIPTION
        "A collection of objects suitable for bulk operations."
    ::= { rfc2544MibGroups 8 }

rfc2544ControlTestStopInfoGroup OBJECT-GROUP
    OBJECTS     { rfc2544ControlTestStopName }
    STATUS      current
    DESCRIPTION
        "A collection of objects suitable for bulk operations."
    ::= { rfc2544MibGroups 9 }

rfc2544MibCompliance MODULE-COMPLIANCE
    STATUS      current
    DESCRIPTION
        "The compliance statement for the implementation."

    MODULE      -- this module

    MANDATORY-GROUPS { rfc2544CapabilitiesInfoGroup,
                       rfc2544ConfigProfileTableInfoGroup,
                       rfc2544ConfigProfileTableRowEditorInfoGroup,
                       rfc2544StatusReportTableInfoGroup,
                       rfc2544ControlReportDeleteInfoGroup,
                       rfc2544ControlTestTableInfoGroup,
                       rfc2544ControlTestTableRowEditorInfoGroup,
                       rfc2544ControlTestStartInfoGroup,
                       rfc2544ControlTestStopInfoGroup }

    ::= { rfc2544MibCompliances 1 }

END
