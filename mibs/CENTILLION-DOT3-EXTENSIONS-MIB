-- SECTION 1: Top Level Definitions


CENTILLION-DOT3-EXTENSIONS-MIB DEFINITIONS ::= BEGIN

-- Centillion IEEE 802.3 Ethernet Extensions MIB Release 2.0.0
-- Revision 05/16/96

-- Copyright 1996 Bay Networks, Inc.
-- All rights reserved.
-- This Bay Networks SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.


-- Imports

IMPORTS
        Gauge
                FROM RFC1155-SMI
	OBJECT-TYPE
		FROM RFC-1212
	extensions
		FROM CENTILLION-ROOT-MIB;


-- Groups

cnDot3Extensions OBJECT IDENTIFIER ::= { extensions 4 }


-- SECTION 2: Ethernet Extensions Table

cnDot3ExtnTable OBJECT-TYPE
	SYNTAX  SEQUENCE OF CnDot3ExtnEntry
	ACCESS  not-accessible
	STATUS  mandatory
	DESCRIPTION
		"This table contains Ethernet interface
                parameters and state variables, one entry
                per 802.3 interface."
	::= { cnDot3Extensions 1 }

cnDot3ExtnEntry OBJECT-TYPE
	SYNTAX  CnDot3ExtnEntry
	ACCESS  not-accessible
	STATUS  mandatory
	DESCRIPTION
		"A list of Ethernet status and parameter
        	 values for an 802.3 interface."
	INDEX   { cnDot3ExtnIfIndex }
	::= { cnDot3ExtnTable 1 }

CnDot3ExtnEntry ::= SEQUENCE {
	cnDot3ExtnIfIndex
		INTEGER,
	cnDot3ExtnIfAdminSpeed
		INTEGER,
	cnDot3ExtnIfOperSpeed
		Gauge,
	cnDot3ExtnIfAdminConnectionType
		INTEGER,
	cnDot3ExtnIfOperConnectionType
		INTEGER
	}

cnDot3ExtnIfIndex OBJECT-TYPE
	SYNTAX  INTEGER
	ACCESS  read-only
	STATUS  mandatory
	DESCRIPTION
		"The value of this object identifies the
		802.3 interface for which this entry
		contains management information. 
		This value should same as the Ifindex 
		in the interface table"
	::= { cnDot3ExtnEntry 1 }

cnDot3ExtnIfAdminSpeed OBJECT-TYPE
	SYNTAX	INTEGER {
		forced10(1),   -- forced 10Mbps
		forced100(2),  -- forced 100Mbps
		auto(3),       -- auto 10/100
		forced1000(4)  -- forced 1000Mbps 
		}
	ACCESS	read-write
	STATUS	mandatory
	DESCRIPTION
		"The configured speed of the interface.
		The default value for 10 Mbps interfaces is
		forced10(1).  The default value for 100 Mbps
		interfaces is auto(3). "
	::= { cnDot3ExtnEntry 2 }

cnDot3ExtnIfOperSpeed OBJECT-TYPE
	SYNTAX	Gauge
	ACCESS	read-only
	STATUS	mandatory
	DESCRIPTION
		"The operational speed of the interface in bits per
                second."
	::= { cnDot3ExtnEntry 3 }

cnDot3ExtnIfAdminConnectionType OBJECT-TYPE
	SYNTAX	INTEGER {
		halfDuplex(1),   -- forced half duplex
		fullDuplex(2),   -- forced full duplex 
		auto(3)          -- auto half/full duplex
		}
	ACCESS	read-write
	STATUS	mandatory
	DESCRIPTION
		"The administration connection type of the interface."
	::= { cnDot3ExtnEntry 4 }

cnDot3ExtnIfOperConnectionType OBJECT-TYPE
	SYNTAX	INTEGER {
		halfDuplex(1),   -- forced half duplex
		fullDuplex(2)    -- forced full duplex 
		}
	ACCESS	read-only
	STATUS	mandatory
	DESCRIPTION
		"The operational connection type of the interface."
	::= { cnDot3ExtnEntry 5 }

END
