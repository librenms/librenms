-- *****************************************************************
-- CISCO-VTP-CAPABILITY.my:
-- Cisco CISCO-VTP-MIB AGENT-CAPABILITIES
--   
-- August 2003, Wen Xu
--   
-- Copyright (c) 2003-2007 by Cisco Systems Inc.
-- All rights reserved.
--   
-- ****************************************************************

CISCO-VTP-CAPABILITY DEFINITIONS ::= BEGIN

IMPORTS
    MODULE-IDENTITY
        FROM SNMPv2-SMI
    AGENT-CAPABILITIES
        FROM SNMPv2-CONF
    ciscoAgentCapability
        FROM CISCO-SMI;


ciscoVtpCapability MODULE-IDENTITY
    LAST-UPDATED    "200707180000Z"
    ORGANIZATION    "Cisco Systems, Inc."
    CONTACT-INFO
            "Cisco Systems
            Customer Service

            Postal: 170 W Tasman Drive
            San Jose, CA  95134
            USA

            Tel: +1 800 553-NETS
            E-mail: cs-lan-switch-snmp@cisco.com"
    DESCRIPTION
        "The capabilities description of CISCO-VTP-MIB."
    REVISION        "200707180000Z"
    DESCRIPTION
        "Added capability statement
        ciscoVtpCapV12R0233SXHPCat6K."
    REVISION        "200603150000Z"
    DESCRIPTION
        "Added VARIATION clause for managementDomainLocalMode
        in capability statement ciscoVtpCapV12R0119ECat6K,
        ciscoVtpCapV12R0217SXCat6K,ciscoVtpCapV12R0217SXACat6K
        and ciscoVtpCapV12R0218SXECat6K."
    REVISION        "200503090000Z"
    DESCRIPTION
        "Added capability statement ciscoVtpCapV12R0218SXECat6K.

        Added VARIATION clause for vtpVlanTypeExt 
        and vtpVlanEditTypeExt2 in capability
        statement ciscoVtpCapV12R0119ECat6K, 
        ciscoVtpCapV12R0217SXCat6K and 
        ciscoVtpCapV12R0217SXACat6K."
    REVISION        "200404150000Z"
    DESCRIPTION
        "Added capability statement ciscoVtpCapV12R0217SXACat6K.

        Added a VARIATION statement for the object
        vlanTrunkPortDynamicStatus in capability
        statement ciscoVtpCapV12R0119ECat6K and
        ciscoVtpCapV12R0217SXCat6K."
    REVISION        "200312010000Z"
    DESCRIPTION
        "Added capability statement ciscoVtpCapCatOSV08R0301."
    REVISION        "200309150000Z"
    DESCRIPTION
        "Initial version of this MIB module."
    ::= { ciscoAgentCapability 329 }



ciscoVtpCapV12R0119ECat6K AGENT-CAPABILITIES
    PRODUCT-RELEASE "Cisco IOS 12.1(19E) on Catalyst 6000/6500
                    and Cisco 7600 series devices."
    STATUS          current
    DESCRIPTION
        "CISCO-VTP-MIB capabilities."

    SUPPORTS        CISCO-VTP-MIB
    INCLUDES        {
                        vtpBasicGroup,
                        vtpVlanInfoGroup,
                        vtpConfigNotificationsGroupRev1,
                        vtpStatsGroup,
                        vtpTrunkPortGroup,
                        vtpVersion2BasicGroup,
                        vtpVlanInfoEditGroup,
                        vtpTrunkPortGroup2,
                        vtpTrunkPortGroup3,
                        vtpDot1qTunnelGroup,
                        vtpTrunkPruningGroup,
                        vtpTrunkPruningGroup2,
                        vtpVlanIfIndexGroup,
                        vtpVlanInfoEditGroup2,
                        vtp4kVlanGroupRev1,
                        vtpConfigNotificationsGroup2,
                        vtpVlanNotifEnabledGroup,
                        vtpConfigNotificationsGroup3
                    }
    VARIATION       vtpVersion
    SYNTAX          INTEGER  {
                        one(1),
                        two(2)
                    }
    DESCRIPTION
        "Only limited set of enumerated values
        are supported."

    VARIATION       managementDomainRowStatus
    SYNTAX          INTEGER  {
                        active(1)
                    }
    DESCRIPTION
        "Only limited set of enumerated values
        are supported."

    VARIATION       vlanTrunkPortRowStatus
    SYNTAX          INTEGER  {
                        active(1)
                    }
    DESCRIPTION
        "Only limited set of enumerated values
        are supported."

    VARIATION       managementDomainVersionInUse
    SYNTAX          INTEGER  {
                        version1(1),
                        version2(2)
                    }
    DESCRIPTION
        "Only limited set of enumerated values
        are supported."

    VARIATION       vlanTrunkPortDynamicStatus
    SYNTAX          INTEGER  {
                        trunking(1)
                    }
    DESCRIPTION
        "Only limited set of enumerated values
        are supported.
        vlanTrunkPortTable only includes the
        trunking ports."

    VARIATION       vtpVlanTypeExt
    SYNTAX          BITS {
                        vtpmanageable(0),
                        rspan(3)
                    }
    DESCRIPTION
        "Only limited set of enumerated values are
        supported."

    VARIATION       vtpVlanEditTypeExt2
    SYNTAX          BITS {
                        vtpmanageable(0),
                        rspan(3)
                    }
    DESCRIPTION
        "Only limited set of enumerated values are
        supported."

    VARIATION       managementDomainLocalMode
    SYNTAX          INTEGER  {
                        client(1),
                        server(2),
                        transparent(3)
                    }
    DESCRIPTION
        "Only limited set of enumerated values are
        supported."

    ::= { ciscoVtpCapability 1 }

ciscoVtpCapV12R0217SXCat6K AGENT-CAPABILITIES
    PRODUCT-RELEASE "Cisco IOS 12.2(17)SX on Catalyst 6000/6500
                    and Cisco 7600 series devices."
    STATUS          current
    DESCRIPTION
        "CISCO-VTP-MIB capabilities."

    SUPPORTS        CISCO-VTP-MIB
    INCLUDES        {
                        vtpBasicGroup,
                        vtpVlanInfoGroup,
                        vtpConfigNotificationsGroupRev1,
                        vtpStatsGroup,
                        vtpTrunkPortGroup,
                        vtpVersion2BasicGroup,
                        vtpVlanInfoEditGroup,
                        vtpTrunkPortGroup2,
                        vtpTrunkPortGroup3,
                        vtpDot1qTunnelGroup,
                        vtpTrunkPruningGroup,
                        vtpTrunkPruningGroup2,
                        vtpVlanIfIndexGroup,
                        vtpVlanInfoEditGroup2,
                        vtp4kVlanGroupRev1,
                        vtpConfigNotificationsGroup2,
                        vtpVlanNotifEnabledGroup,
                        vtpConfigNotificationsGroup3
                    }
    VARIATION       vtpVersion
    SYNTAX          INTEGER  {
                        one(1),
                        two(2)
                    }
    DESCRIPTION
        "Only limited set of enumerated values
        are supported."

    VARIATION       managementDomainRowStatus
    SYNTAX          INTEGER  {
                        active(1)
                    }
    DESCRIPTION
        "Only limited set of enumerated values
        are supported."

    VARIATION       vlanTrunkPortRowStatus
    SYNTAX          INTEGER  {
                        active(1)
                    }
    DESCRIPTION
        "Only limited set of enumerated values
        are supported."

    VARIATION       managementDomainVersionInUse
    SYNTAX          INTEGER  {
                        version1(1),
                        version2(2)
                    }
    DESCRIPTION
        "Only limited set of enumerated values
        are supported."

    VARIATION       vlanTrunkPortDynamicStatus
    SYNTAX          INTEGER  {
                        trunking(1)
                    }
    DESCRIPTION
        "Only limited set of enumerated values
        are supported.
        vlanTrunkPortTable only includes the
        trunking ports."

    VARIATION       vtpVlanTypeExt
    SYNTAX          BITS {
                        vtpmanageable(0),
                        rspan(3)
                    }
    DESCRIPTION
        "Only limited set of enumerated values are
        supported."

    VARIATION       vtpVlanEditTypeExt2
    SYNTAX          BITS {
                        vtpmanageable(0),
                        rspan(3)
                    }
    DESCRIPTION
        "Only limited set of enumerated values are
        supported."

    VARIATION       managementDomainLocalMode
    SYNTAX          INTEGER  {
                        client(1),
                        server(2),
                        transparent(3)
                    }
    DESCRIPTION
        "Only limited set of enumerated values are
        supported."

    ::= { ciscoVtpCapability 2 }

ciscoVtpCapCatOSV08R0101 AGENT-CAPABILITIES
    PRODUCT-RELEASE "Cisco CatOS 8.1(1)."
    STATUS          current
    DESCRIPTION
        "CISCO-VTP-MIB capabilities."

    SUPPORTS        CISCO-VTP-MIB
    INCLUDES        {
                        vtpBasicGroup,
                        vtpVlanInfoGroup,
                        vtpConfigNotificationsGroupRev1,
                        vtpStatsGroup,
                        vtpTrunkPortGroup,
                        vtpVersion2BasicGroup,
                        vtpVlanInfoEditGroup,
                        vtpDot1qTunnelGroup,
                        vtpTrunkPortGroup2,
                        vtpTrunkPortGroup3,
                        vtpTrunkPruningGroup,
                        vtpTrunkPruningGroup2,
                        vtpVlanIfIndexGroup,
                        vtpVlanInfoEditGroup2,
                        vtp4kVlanGroup,
                        vtp4kVlanGroupRev1,
                        vtpConfigNotificationsGroup2,
                        vtpVlanNotifEnabledGroup,
                        vtpConfigNotificationsGroup3,
                        vtpDiscoverGroup,
                        vtpDatabaseGroup,
                        vtpAuthGroup
                    }
    VARIATION       vtpVersion
    SYNTAX          INTEGER  {
                        one(1),
                        two(2),
                        three(4)
                    }
    DESCRIPTION
        "Only limited set of enumerated values
        are supported."

    VARIATION       managementDomainRowStatus
    SYNTAX          INTEGER  {
                        active(1)
                    }
    DESCRIPTION
        "Only limited set of enumerated values
        are supported."

    VARIATION       vlanTrunkPortRowStatus
    SYNTAX          INTEGER  {
                        active(1)
                    }
    DESCRIPTION
        "Only limited set of enumerated values
        are supported."

    VARIATION       managementDomainVersionInUse
    SYNTAX          INTEGER  {
                        version1(1),
                        version2(2),
                        version3(4)
                    }
    DESCRIPTION
        "Only limited set of enumerated values
        are supported."

    ::= { ciscoVtpCapability 3 }

ciscoVtpCapCatOSV08R0301 AGENT-CAPABILITIES
    PRODUCT-RELEASE "Cisco CatOS 8.3(1)."
    STATUS          current
    DESCRIPTION
        "CISCO-VTP-MIB capabilities."

    SUPPORTS        CISCO-VTP-MIB
    INCLUDES        {
                        vtpBasicGroup,
                        vtpVlanInfoGroup,
                        vtpConfigNotificationsGroupRev1,
                        vtpStatsGroup,
                        vtpTrunkPortGroup,
                        vtpVersion2BasicGroup,
                        vtpVlanInfoEditGroup,
                        vtpDot1qTunnelGroup,
                        vtpTrunkPortGroup2,
                        vtpTrunkPortGroup3,
                        vtpTrunkPruningGroup,
                        vtpTrunkPruningGroup2,
                        vtpVlanIfIndexGroup,
                        vtpVlanInfoEditGroup2,
                        vtp4kVlanGroup,
                        vtp4kVlanGroupRev1,
                        vtpConfigNotificationsGroup2,
                        vtpVlanNotifEnabledGroup,
                        vtpConfigNotificationsGroup3,
                        vtpDiscoverGroup,
                        vtpDatabaseGroup,
                        vtpAuthGroup,
                        vtpInternalVlanGrp
                    }
    VARIATION       vtpVersion
    SYNTAX          INTEGER  {
                        one(1),
                        two(2),
                        three(4)
                    }
    DESCRIPTION
        "Only limited set of enumerated values
        are supported."

    VARIATION       managementDomainRowStatus
    SYNTAX          INTEGER  {
                        active(1)
                    }
    DESCRIPTION
        "Only limited set of enumerated values
        are supported."

    VARIATION       vlanTrunkPortRowStatus
    SYNTAX          INTEGER  {
                        active(1)
                    }
    DESCRIPTION
        "Only limited set of enumerated values
        are supported."

    VARIATION       managementDomainVersionInUse
    SYNTAX          INTEGER  {
                        version1(1),
                        version2(2),
                        version3(4)
                    }
    DESCRIPTION
        "Only limited set of enumerated values
        are supported."

    ::= { ciscoVtpCapability 4 }

ciscoVtpCapV12R0217SXACat6K AGENT-CAPABILITIES
    PRODUCT-RELEASE "Cisco IOS 12.2(17)SXA on Catalyst 6000/6500
                    and Cisco 7600 series devices."
    STATUS          current
    DESCRIPTION
        "CISCO-VTP-MIB capabilities."

    SUPPORTS        CISCO-VTP-MIB
    INCLUDES        {
                        vtpBasicGroup,
                        vtpVlanInfoGroup,
                        vtpConfigNotificationsGroupRev1,
                        vtpStatsGroup,
                        vtpTrunkPortGroup,
                        vtpVersion2BasicGroup,
                        vtpVlanInfoEditGroup,
                        vtpTrunkPortGroup2,
                        vtpTrunkPortGroup3,
                        vtpDot1qTunnelGroup,
                        vtpTrunkPruningGroup,
                        vtpTrunkPruningGroup2,
                        vtpVlanIfIndexGroup,
                        vtpVlanInfoEditGroup2,
                        vtp4kVlanGroupRev1,
                        vtpConfigNotificationsGroup2,
                        vtpVlanNotifEnabledGroup,
                        vtpConfigNotificationsGroup3
                    }
    VARIATION       vtpVersion
    SYNTAX          INTEGER  {
                        one(1),
                        two(2)
                    }
    DESCRIPTION
        "Only limited set of enumerated values
        are supported."

    VARIATION       managementDomainRowStatus
    SYNTAX          INTEGER  {
                        active(1)
                    }
    DESCRIPTION
        "Only limited set of enumerated values
        are supported."

    VARIATION       vlanTrunkPortRowStatus
    SYNTAX          INTEGER  {
                        active(1)
                    }
    DESCRIPTION
        "Only limited set of enumerated values
        are supported."

    VARIATION       managementDomainVersionInUse
    SYNTAX          INTEGER  {
                        version1(1),
                        version2(2)
                    }
    DESCRIPTION
        "Only limited set of enumerated values
        are supported."

    VARIATION       vtpVlanTypeExt
    SYNTAX          BITS {
                        vtpmanageable(0),
                        rspan(3)
                    }
    DESCRIPTION
        "Only limited set of enumerated values are
        supported."

    VARIATION       vtpVlanEditTypeExt2
    SYNTAX          BITS {
                        vtpmanageable(0),
                        rspan(3)
                    }
    DESCRIPTION
        "Only limited set of enumerated values are
        supported."

    VARIATION       managementDomainLocalMode
    SYNTAX          INTEGER  {
                        client(1),
                        server(2),
                        transparent(3)
                    }
    DESCRIPTION
        "Only limited set of enumerated values are
        supported."

    ::= { ciscoVtpCapability 5 }

ciscoVtpCapV12R0218SXECat6K AGENT-CAPABILITIES
    PRODUCT-RELEASE "Cisco IOS 12.2(18)SXE on Catalyst 6000/6500
                    and Cisco 7600 series devices."
    STATUS          current
    DESCRIPTION
        "CISCO-VTP-MIB capabilities."

    SUPPORTS        CISCO-VTP-MIB
    INCLUDES        {
                        vtpBasicGroup,
                        vtpVlanInfoGroup,
                        vtpConfigNotificationsGroupRev1,
                        vtpStatsGroup,
                        vtpTrunkPortGroup,
                        vtpVersion2BasicGroup,
                        vtpVlanInfoEditGroup,
                        vtpTrunkPortGroup2,
                        vtpTrunkPortGroup3,
                        vtpDot1qTunnelGroup,
                        vtpTrunkPruningGroup,
                        vtpTrunkPruningGroup2,
                        vtpVlanIfIndexGroup,
                        vtpVlanInfoEditGroup2,
                        vtp4kVlanGroupRev1,
                        vtpConfigNotificationsGroup2,
                        vtpVlanNotifEnabledGroup,
                        vtpConfigNotificationsGroup3,
                        vtpInternalVlanGrp
                    }
    VARIATION       vtpVersion
    SYNTAX          INTEGER  {
                        one(1),
                        two(2)
                    }
    DESCRIPTION
        "Only limited set of enumerated values
        are supported."

    VARIATION       managementDomainRowStatus
    SYNTAX          INTEGER  {
                        active(1)
                    }
    DESCRIPTION
        "Only limited set of enumerated values
        are supported."

    VARIATION       vlanTrunkPortRowStatus
    SYNTAX          INTEGER  {
                        active(1)
                    }
    DESCRIPTION
        "Only limited set of enumerated values
        are supported."

    VARIATION       managementDomainVersionInUse
    SYNTAX          INTEGER  {
                        version1(1),
                        version2(2)
                    }
    DESCRIPTION
        "Only limited set of enumerated values
        are supported."

    VARIATION       vtpVlanTypeExt
    SYNTAX          BITS {
                        vtpmanageable(0),
                        rspan(3)
                    }
    DESCRIPTION
        "Only limited set of enumerated values are
        supported."

    VARIATION       vtpVlanEditTypeExt2
    SYNTAX          BITS {
                        vtpmanageable(0),
                        rspan(3)
                    }
    DESCRIPTION
        "Only limited set of enumerated values are
        supported."

    VARIATION       managementDomainLocalMode
    SYNTAX          INTEGER  {
                        client(1),
                        server(2),
                        transparent(3)
                    }
    DESCRIPTION
        "Only limited set of enumerated values are
        supported."

    ::= { ciscoVtpCapability 6 }

ciscoVtpCapV12R0233SXHPCat6K AGENT-CAPABILITIES
    PRODUCT-RELEASE "Cisco IOS 12.2(33)SXH on Catalyst 6000/6500
                    and Cisco 7600 series devices."
    STATUS          current
    DESCRIPTION
        "CISCO-VTP-MIB capabilities."

    SUPPORTS        CISCO-VTP-MIB
    INCLUDES        {
                        vtpBasicGroup,
                        vtpVlanInfoGroup,
                        vtpConfigNotificationsGroupRev1,
                        vtpStatsGroup,
                        vtpTrunkPortGroup,
                        vtpVersion2BasicGroup,
                        vtpVlanInfoEditGroup,
                        vtpTrunkPortGroup2,
                        vtpTrunkPortGroup3,
                        vtpDot1qTunnelGroup,
                        vtpTrunkPruningGroup,
                        vtpTrunkPruningGroup2,
                        vtpVlanIfIndexGroup,
                        vtpVlanInfoEditGroup2,
                        vtp4kVlanGroupRev1,
                        vtpConfigNotificationsGroup2,
                        vtpVlanNotifEnabledGroup,
                        vtpConfigNotificationsGroup3,
                        vtpInternalVlanGrp
                    }
    VARIATION       vtpVersion
    SYNTAX          INTEGER  {
                        one(1),
                        two(2)
                    }
    DESCRIPTION
        "Only limited set of enumerated values
        are supported."

    VARIATION       managementDomainRowStatus
    SYNTAX          INTEGER  {
                        active(1)
                    }
    DESCRIPTION
        "Only limited set of enumerated values
        are supported."

    VARIATION       vlanTrunkPortRowStatus
    SYNTAX          INTEGER  {
                        active(1)
                    }
    DESCRIPTION
        "Only limited set of enumerated values
        are supported."

    VARIATION       managementDomainVersionInUse
    SYNTAX          INTEGER  {
                        version1(1),
                        version2(2)
                    }
    DESCRIPTION
        "Only limited set of enumerated values
        are supported."

    VARIATION       vtpVlanTypeExt
    SYNTAX          BITS {
                        vtpmanageable(0),
                        rspan(3)
                    }
    DESCRIPTION
        "Only limited set of enumerated values are
        supported."

    VARIATION       vtpVlanEditTypeExt2
    SYNTAX          BITS {
                        vtpmanageable(0),
                        rspan(3)
                    }
    DESCRIPTION
        "Only limited set of enumerated values are
        supported."

    VARIATION       managementDomainLocalMode
    SYNTAX          INTEGER  {
                        client(1),
                        server(2),
                        transparent(3),
                        off(4)
                    }
    DESCRIPTION
        "The enumerated values supported are all
        those defined at the time this clause
        was written."

    ::= { ciscoVtpCapability 7 }

END
