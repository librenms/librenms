-- *****************************************************************
-- AUTH-MIB:  Vitesse private MIB
--
-- Copyright (c) 2002-2013 Vitesse Semiconductor Corporation "Vitesse".
-- All Rights Reserved.
--
-- ****************************************************************

VTSS-AUTH-MIB DEFINITIONS ::= BEGIN

IMPORTS
    MODULE-COMPLIANCE, OBJECT-GROUP
        FROM SNMPv2-CONF
    MODULE-IDENTITY, OBJECT-TYPE
        FROM SNMPv2-SMI
    TEXTUAL-CONVENTION
        FROM SNMPv2-TC
    vtssSwitchMgmt
        FROM VTSS-SMI
    InetAddressIPv6 FROM INET-ADDRESS-MIB
    Integer32 FROM SNMPv2-SMI
    IpAddress FROM SNMPv2-SMI
    Unsigned32 FROM SNMPv2-SMI
    TruthValue FROM SNMPv2-TC
    VTSSDisplayString FROM VTSS-TC
    VTSSUnsigned8 FROM VTSS-TC
    ;

vtssAuthMib MODULE-IDENTITY
    LAST-UPDATED "201407010000Z"
    ORGANIZATION
        "Vitesse Semiconductor Corporation"
    CONTACT-INFO
        "Application support <application_support@vitesse.com>"
    DESCRIPTION
        "This is a private MIB for authentication"
    REVISION    "201407010000Z"
    DESCRIPTION
        "Initial version"
    ::= { vtssSwitchMgmt 48 }


VTSSAuthAcctMethod ::= TEXTUAL-CONVENTION
    STATUS      current
    DESCRIPTION
        "This enumeration defines the available accounting methods."
    SYNTAX      INTEGER { none(0), tacacs(3) }

VTSSAuthAuthenMethod ::= TEXTUAL-CONVENTION
    STATUS      current
    DESCRIPTION
        "This enumeration defines the available authentication methods."
    SYNTAX      INTEGER { none(0), local(1), radius(2), tacacs(3) }

VTSSAuthAuthorMethod ::= TEXTUAL-CONVENTION
    STATUS      current
    DESCRIPTION
        "This enumeration defines the available authorization methods."
    SYNTAX      INTEGER { none(0), tacacs(3) }

vtssAuthMibObjects OBJECT IDENTIFIER
    ::= { vtssAuthMib 1 }

vtssAuthConfig OBJECT IDENTIFIER
    ::= { vtssAuthMibObjects 2 }

vtssAuthConfigGlobals OBJECT IDENTIFIER
    ::= { vtssAuthConfig 1 }

vtssAuthConfigGlobalsAgents OBJECT IDENTIFIER
    ::= { vtssAuthConfigGlobals 1 }

vtssAuthConfigGlobalsAgentsConsoleAuthen OBJECT IDENTIFIER
    ::= { vtssAuthConfigGlobalsAgents 1 }

vtssAuthConfigGlobalsAgentsConsoleAuthenMethodsTable OBJECT-TYPE
    SYNTAX      SEQUENCE OF VTSSAuthConfigGlobalsAgentsConsoleAuthenMethodsEntry
    MAX-ACCESS  not-accessible
    STATUS      current
    DESCRIPTION 
        "This is an ordered table of methods used to authenticate console access"
    ::= { vtssAuthConfigGlobalsAgentsConsoleAuthen 1 }

vtssAuthConfigGlobalsAgentsConsoleAuthenMethodsEntry OBJECT-TYPE
    SYNTAX      VTSSAuthConfigGlobalsAgentsConsoleAuthenMethodsEntry
    MAX-ACCESS  not-accessible
    STATUS      current
    DESCRIPTION 
        "Each entry defines a method to be consulted with a priorty equal to the
         index"
    INDEX       { vtssAuthConfigGlobalsAgentsConsoleAuthenMethodsIndex }
    ::= { vtssAuthConfigGlobalsAgentsConsoleAuthenMethodsTable 1 }

VTSSAuthConfigGlobalsAgentsConsoleAuthenMethodsEntry ::= SEQUENCE {
    vtssAuthConfigGlobalsAgentsConsoleAuthenMethodsIndex    Integer32,
    vtssAuthConfigGlobalsAgentsConsoleAuthenMethodsMethod   VTSSAuthAuthenMethod
}

vtssAuthConfigGlobalsAgentsConsoleAuthenMethodsIndex OBJECT-TYPE
    SYNTAX      Integer32 (0..3)
    MAX-ACCESS  not-accessible
    STATUS      current
    DESCRIPTION 
        "Method priority index, from 0 to 3 where 0 is the highest priority
         index"
    ::= { vtssAuthConfigGlobalsAgentsConsoleAuthenMethodsEntry 1 }

vtssAuthConfigGlobalsAgentsConsoleAuthenMethodsMethod OBJECT-TYPE
    SYNTAX      VTSSAuthAuthenMethod
    MAX-ACCESS  read-write
    STATUS      current
    DESCRIPTION 
        "Authentication method"
    ::= { vtssAuthConfigGlobalsAgentsConsoleAuthenMethodsEntry 2 }

vtssAuthConfigGlobalsAgentsTelnetAuthen OBJECT IDENTIFIER
    ::= { vtssAuthConfigGlobalsAgents 2 }

vtssAuthConfigGlobalsAgentsTelnetAuthenMethodsTable OBJECT-TYPE
    SYNTAX      SEQUENCE OF VTSSAuthConfigGlobalsAgentsTelnetAuthenMethodsEntry
    MAX-ACCESS  not-accessible
    STATUS      current
    DESCRIPTION 
        "This is an ordered table of methods used to authenticate telnet access"
    ::= { vtssAuthConfigGlobalsAgentsTelnetAuthen 1 }

vtssAuthConfigGlobalsAgentsTelnetAuthenMethodsEntry OBJECT-TYPE
    SYNTAX      VTSSAuthConfigGlobalsAgentsTelnetAuthenMethodsEntry
    MAX-ACCESS  not-accessible
    STATUS      current
    DESCRIPTION 
        "Each entry defines a method to be consulted with a priorty equal to the
         index"
    INDEX       { vtssAuthConfigGlobalsAgentsTelnetAuthenMethodsIndex }
    ::= { vtssAuthConfigGlobalsAgentsTelnetAuthenMethodsTable 1 }

VTSSAuthConfigGlobalsAgentsTelnetAuthenMethodsEntry ::= SEQUENCE {
    vtssAuthConfigGlobalsAgentsTelnetAuthenMethodsIndex     Integer32,
    vtssAuthConfigGlobalsAgentsTelnetAuthenMethodsMethod    VTSSAuthAuthenMethod
}

vtssAuthConfigGlobalsAgentsTelnetAuthenMethodsIndex OBJECT-TYPE
    SYNTAX      Integer32 (0..3)
    MAX-ACCESS  not-accessible
    STATUS      current
    DESCRIPTION 
        "Method priority index, from 0 to 3 where 0 is the highest priority
         index"
    ::= { vtssAuthConfigGlobalsAgentsTelnetAuthenMethodsEntry 1 }

vtssAuthConfigGlobalsAgentsTelnetAuthenMethodsMethod OBJECT-TYPE
    SYNTAX      VTSSAuthAuthenMethod
    MAX-ACCESS  read-write
    STATUS      current
    DESCRIPTION 
        "Authentication method"
    ::= { vtssAuthConfigGlobalsAgentsTelnetAuthenMethodsEntry 2 }

vtssAuthConfigGlobalsAgentsSshAuthen OBJECT IDENTIFIER
    ::= { vtssAuthConfigGlobalsAgents 3 }

vtssAuthConfigGlobalsAgentsSshAuthenMethodsTable OBJECT-TYPE
    SYNTAX      SEQUENCE OF VTSSAuthConfigGlobalsAgentsSshAuthenMethodsEntry
    MAX-ACCESS  not-accessible
    STATUS      current
    DESCRIPTION 
        "This is an ordered table of methods used to authenticate ssh access"
    ::= { vtssAuthConfigGlobalsAgentsSshAuthen 1 }

vtssAuthConfigGlobalsAgentsSshAuthenMethodsEntry OBJECT-TYPE
    SYNTAX      VTSSAuthConfigGlobalsAgentsSshAuthenMethodsEntry
    MAX-ACCESS  not-accessible
    STATUS      current
    DESCRIPTION 
        "Each entry defines a method to be consulted with a priorty equal to the
         index"
    INDEX       { vtssAuthConfigGlobalsAgentsSshAuthenMethodsIndex }
    ::= { vtssAuthConfigGlobalsAgentsSshAuthenMethodsTable 1 }

VTSSAuthConfigGlobalsAgentsSshAuthenMethodsEntry ::= SEQUENCE {
    vtssAuthConfigGlobalsAgentsSshAuthenMethodsIndex    Integer32,
    vtssAuthConfigGlobalsAgentsSshAuthenMethodsMethod   VTSSAuthAuthenMethod
}

vtssAuthConfigGlobalsAgentsSshAuthenMethodsIndex OBJECT-TYPE
    SYNTAX      Integer32 (0..3)
    MAX-ACCESS  not-accessible
    STATUS      current
    DESCRIPTION 
        "Method priority index, from 0 to 3 where 0 is the highest priority
         index"
    ::= { vtssAuthConfigGlobalsAgentsSshAuthenMethodsEntry 1 }

vtssAuthConfigGlobalsAgentsSshAuthenMethodsMethod OBJECT-TYPE
    SYNTAX      VTSSAuthAuthenMethod
    MAX-ACCESS  read-write
    STATUS      current
    DESCRIPTION 
        "Authentication method"
    ::= { vtssAuthConfigGlobalsAgentsSshAuthenMethodsEntry 2 }

vtssAuthConfigGlobalsAgentsHttpAuthen OBJECT IDENTIFIER
    ::= { vtssAuthConfigGlobalsAgents 4 }

vtssAuthConfigGlobalsAgentsHttpAuthenMethodsTable OBJECT-TYPE
    SYNTAX      SEQUENCE OF VTSSAuthConfigGlobalsAgentsHttpAuthenMethodsEntry
    MAX-ACCESS  not-accessible
    STATUS      current
    DESCRIPTION 
        "This is an ordered table of methods used to authenticate HTTP access"
    ::= { vtssAuthConfigGlobalsAgentsHttpAuthen 1 }

vtssAuthConfigGlobalsAgentsHttpAuthenMethodsEntry OBJECT-TYPE
    SYNTAX      VTSSAuthConfigGlobalsAgentsHttpAuthenMethodsEntry
    MAX-ACCESS  not-accessible
    STATUS      current
    DESCRIPTION 
        "Each entry defines a method to be consulted with a priorty equal to the
         index"
    INDEX       { vtssAuthConfigGlobalsAgentsHttpAuthenMethodsIndex }
    ::= { vtssAuthConfigGlobalsAgentsHttpAuthenMethodsTable 1 }

VTSSAuthConfigGlobalsAgentsHttpAuthenMethodsEntry ::= SEQUENCE {
    vtssAuthConfigGlobalsAgentsHttpAuthenMethodsIndex   Integer32,
    vtssAuthConfigGlobalsAgentsHttpAuthenMethodsMethod      VTSSAuthAuthenMethod
}

vtssAuthConfigGlobalsAgentsHttpAuthenMethodsIndex OBJECT-TYPE
    SYNTAX      Integer32 (0..3)
    MAX-ACCESS  not-accessible
    STATUS      current
    DESCRIPTION 
        "Method priority index, from 0 to 3 where 0 is the highest priority
         index"
    ::= { vtssAuthConfigGlobalsAgentsHttpAuthenMethodsEntry 1 }

vtssAuthConfigGlobalsAgentsHttpAuthenMethodsMethod OBJECT-TYPE
    SYNTAX      VTSSAuthAuthenMethod
    MAX-ACCESS  read-write
    STATUS      current
    DESCRIPTION 
        "Authentication method"
    ::= { vtssAuthConfigGlobalsAgentsHttpAuthenMethodsEntry 2 }

vtssAuthConfigGlobalsAgentsConsoleAuthor OBJECT IDENTIFIER
    ::= { vtssAuthConfigGlobalsAgents 11 }

vtssAuthConfigGlobalsAgentsConsoleAuthorMethod OBJECT-TYPE
    SYNTAX      VTSSAuthAuthorMethod
    MAX-ACCESS  read-write
    STATUS      current
    DESCRIPTION 
        "Authorization method"
    ::= { vtssAuthConfigGlobalsAgentsConsoleAuthor 1 }

vtssAuthConfigGlobalsAgentsConsoleAuthorCmdEnable OBJECT-TYPE
    SYNTAX      TruthValue
    MAX-ACCESS  read-write
    STATUS      current
    DESCRIPTION 
        "Enable authorization of commands"
    ::= { vtssAuthConfigGlobalsAgentsConsoleAuthor 2 }

vtssAuthConfigGlobalsAgentsConsoleAuthorCmdPrivLvl OBJECT-TYPE
    SYNTAX      VTSSUnsigned8
    MAX-ACCESS  read-write
    STATUS      current
    DESCRIPTION 
        "Command privilege level. Authorize all commands with a privilege level
         higher than or equal to this level. Valid values are in the range 0 to
         15"
    ::= { vtssAuthConfigGlobalsAgentsConsoleAuthor 3 }

vtssAuthConfigGlobalsAgentsConsoleAuthorCfgCmdEnable OBJECT-TYPE
    SYNTAX      TruthValue
    MAX-ACCESS  read-write
    STATUS      current
    DESCRIPTION 
        "Also authorize configuration commands"
    ::= { vtssAuthConfigGlobalsAgentsConsoleAuthor 4 }

vtssAuthConfigGlobalsAgentsTelnetAuthor OBJECT IDENTIFIER
    ::= { vtssAuthConfigGlobalsAgents 12 }

vtssAuthConfigGlobalsAgentsTelnetAuthorMethod OBJECT-TYPE
    SYNTAX      VTSSAuthAuthorMethod
    MAX-ACCESS  read-write
    STATUS      current
    DESCRIPTION 
        "Authorization method"
    ::= { vtssAuthConfigGlobalsAgentsTelnetAuthor 1 }

vtssAuthConfigGlobalsAgentsTelnetAuthorCmdEnable OBJECT-TYPE
    SYNTAX      TruthValue
    MAX-ACCESS  read-write
    STATUS      current
    DESCRIPTION 
        "Enable authorization of commands"
    ::= { vtssAuthConfigGlobalsAgentsTelnetAuthor 2 }

vtssAuthConfigGlobalsAgentsTelnetAuthorCmdPrivLvl OBJECT-TYPE
    SYNTAX      VTSSUnsigned8
    MAX-ACCESS  read-write
    STATUS      current
    DESCRIPTION 
        "Command privilege level. Authorize all commands with a privilege level
         higher than or equal to this level. Valid values are in the range 0 to
         15"
    ::= { vtssAuthConfigGlobalsAgentsTelnetAuthor 3 }

vtssAuthConfigGlobalsAgentsTelnetAuthorCfgCmdEnable OBJECT-TYPE
    SYNTAX      TruthValue
    MAX-ACCESS  read-write
    STATUS      current
    DESCRIPTION 
        "Also authorize configuration commands"
    ::= { vtssAuthConfigGlobalsAgentsTelnetAuthor 4 }

vtssAuthConfigGlobalsAgentsSshAuthor OBJECT IDENTIFIER
    ::= { vtssAuthConfigGlobalsAgents 13 }

vtssAuthConfigGlobalsAgentsSshAuthorMethod OBJECT-TYPE
    SYNTAX      VTSSAuthAuthorMethod
    MAX-ACCESS  read-write
    STATUS      current
    DESCRIPTION 
        "Authorization method"
    ::= { vtssAuthConfigGlobalsAgentsSshAuthor 1 }

vtssAuthConfigGlobalsAgentsSshAuthorCmdEnable OBJECT-TYPE
    SYNTAX      TruthValue
    MAX-ACCESS  read-write
    STATUS      current
    DESCRIPTION 
        "Enable authorization of commands"
    ::= { vtssAuthConfigGlobalsAgentsSshAuthor 2 }

vtssAuthConfigGlobalsAgentsSshAuthorCmdPrivLvl OBJECT-TYPE
    SYNTAX      VTSSUnsigned8
    MAX-ACCESS  read-write
    STATUS      current
    DESCRIPTION 
        "Command privilege level. Authorize all commands with a privilege level
         higher than or equal to this level. Valid values are in the range 0 to
         15"
    ::= { vtssAuthConfigGlobalsAgentsSshAuthor 3 }

vtssAuthConfigGlobalsAgentsSshAuthorCfgCmdEnable OBJECT-TYPE
    SYNTAX      TruthValue
    MAX-ACCESS  read-write
    STATUS      current
    DESCRIPTION 
        "Also authorize configuration commands"
    ::= { vtssAuthConfigGlobalsAgentsSshAuthor 4 }

vtssAuthConfigGlobalsAgentsConsoleAcct OBJECT IDENTIFIER
    ::= { vtssAuthConfigGlobalsAgents 21 }

vtssAuthConfigGlobalsAgentsConsoleAcctMethod OBJECT-TYPE
    SYNTAX      VTSSAuthAcctMethod
    MAX-ACCESS  read-write
    STATUS      current
    DESCRIPTION 
        "Accounting method"
    ::= { vtssAuthConfigGlobalsAgentsConsoleAcct 1 }

vtssAuthConfigGlobalsAgentsConsoleAcctCmdEnable OBJECT-TYPE
    SYNTAX      TruthValue
    MAX-ACCESS  read-write
    STATUS      current
    DESCRIPTION 
        "Enable accounting of commands"
    ::= { vtssAuthConfigGlobalsAgentsConsoleAcct 2 }

vtssAuthConfigGlobalsAgentsConsoleAcctCmdPrivLvl OBJECT-TYPE
    SYNTAX      VTSSUnsigned8
    MAX-ACCESS  read-write
    STATUS      current
    DESCRIPTION 
        "Command privilege level. Log all commands with a privilege level higher
         than or equal to this level. Valid values are in the range 0 to 15"
    ::= { vtssAuthConfigGlobalsAgentsConsoleAcct 3 }

vtssAuthConfigGlobalsAgentsConsoleAcctExecEnable OBJECT-TYPE
    SYNTAX      TruthValue
    MAX-ACCESS  read-write
    STATUS      current
    DESCRIPTION 
        "Enable exec (login) accounting"
    ::= { vtssAuthConfigGlobalsAgentsConsoleAcct 4 }

vtssAuthConfigGlobalsAgentsTelnetAcct OBJECT IDENTIFIER
    ::= { vtssAuthConfigGlobalsAgents 22 }

vtssAuthConfigGlobalsAgentsTelnetAcctMethod OBJECT-TYPE
    SYNTAX      VTSSAuthAcctMethod
    MAX-ACCESS  read-write
    STATUS      current
    DESCRIPTION 
        "Accounting method"
    ::= { vtssAuthConfigGlobalsAgentsTelnetAcct 1 }

vtssAuthConfigGlobalsAgentsTelnetAcctCmdEnable OBJECT-TYPE
    SYNTAX      TruthValue
    MAX-ACCESS  read-write
    STATUS      current
    DESCRIPTION 
        "Enable accounting of commands"
    ::= { vtssAuthConfigGlobalsAgentsTelnetAcct 2 }

vtssAuthConfigGlobalsAgentsTelnetAcctCmdPrivLvl OBJECT-TYPE
    SYNTAX      VTSSUnsigned8
    MAX-ACCESS  read-write
    STATUS      current
    DESCRIPTION 
        "Command privilege level. Log all commands with a privilege level higher
         than or equal to this level. Valid values are in the range 0 to 15"
    ::= { vtssAuthConfigGlobalsAgentsTelnetAcct 3 }

vtssAuthConfigGlobalsAgentsTelnetAcctExecEnable OBJECT-TYPE
    SYNTAX      TruthValue
    MAX-ACCESS  read-write
    STATUS      current
    DESCRIPTION 
        "Enable exec (login) accounting"
    ::= { vtssAuthConfigGlobalsAgentsTelnetAcct 4 }

vtssAuthConfigGlobalsAgentsSshAcct OBJECT IDENTIFIER
    ::= { vtssAuthConfigGlobalsAgents 23 }

vtssAuthConfigGlobalsAgentsSshAcctMethod OBJECT-TYPE
    SYNTAX      VTSSAuthAcctMethod
    MAX-ACCESS  read-write
    STATUS      current
    DESCRIPTION 
        "Accounting method"
    ::= { vtssAuthConfigGlobalsAgentsSshAcct 1 }

vtssAuthConfigGlobalsAgentsSshAcctCmdEnable OBJECT-TYPE
    SYNTAX      TruthValue
    MAX-ACCESS  read-write
    STATUS      current
    DESCRIPTION 
        "Enable accounting of commands"
    ::= { vtssAuthConfigGlobalsAgentsSshAcct 2 }

vtssAuthConfigGlobalsAgentsSshAcctCmdPrivLvl OBJECT-TYPE
    SYNTAX      VTSSUnsigned8
    MAX-ACCESS  read-write
    STATUS      current
    DESCRIPTION 
        "Command privilege level. Log all commands with a privilege level higher
         than or equal to this level. Valid values are in the range 0 to 15"
    ::= { vtssAuthConfigGlobalsAgentsSshAcct 3 }

vtssAuthConfigGlobalsAgentsSshAcctExecEnable OBJECT-TYPE
    SYNTAX      TruthValue
    MAX-ACCESS  read-write
    STATUS      current
    DESCRIPTION 
        "Enable exec (login) accounting"
    ::= { vtssAuthConfigGlobalsAgentsSshAcct 4 }

vtssAuthConfigGlobalsRadius OBJECT IDENTIFIER
    ::= { vtssAuthConfigGlobals 2 }

vtssAuthConfigGlobalsRadiusGlobal OBJECT IDENTIFIER
    ::= { vtssAuthConfigGlobalsRadius 1 }

vtssAuthConfigGlobalsRadiusGlobalTimeout OBJECT-TYPE
    SYNTAX      Unsigned32
    MAX-ACCESS  read-write
    STATUS      current
    DESCRIPTION 
        "Global timeout for for RADIUS servers. Can be overridden by individual
         host entries. (1 to 1000 seconds)"
    ::= { vtssAuthConfigGlobalsRadiusGlobal 1 }

vtssAuthConfigGlobalsRadiusGlobalRetransmit OBJECT-TYPE
    SYNTAX      Unsigned32
    MAX-ACCESS  read-write
    STATUS      current
    DESCRIPTION 
        "Global retransmit count for RADIUS servers. Can be overridden by
         individual host entries. (1 to 1000 times)"
    ::= { vtssAuthConfigGlobalsRadiusGlobal 2 }

vtssAuthConfigGlobalsRadiusGlobalDeadtime OBJECT-TYPE
    SYNTAX      Unsigned32
    MAX-ACCESS  read-write
    STATUS      current
    DESCRIPTION 
        "Global deadtime for RADIUS servers. (0 to 1440 minutes)"
    ::= { vtssAuthConfigGlobalsRadiusGlobal 3 }

vtssAuthConfigGlobalsRadiusGlobalKey OBJECT-TYPE
    SYNTAX      VTSSDisplayString (SIZE(0..63))
    MAX-ACCESS  read-write
    STATUS      current
    DESCRIPTION 
        "Global secret key for RADIUS servers. Can be overridden by individual
         host entries."
    ::= { vtssAuthConfigGlobalsRadiusGlobal 4 }

vtssAuthConfigGlobalsRadiusGlobalNasIpv4Enable OBJECT-TYPE
    SYNTAX      TruthValue
    MAX-ACCESS  read-write
    STATUS      current
    DESCRIPTION 
        "Enable Global NAS IPv4 address"
    ::= { vtssAuthConfigGlobalsRadiusGlobal 11 }

vtssAuthConfigGlobalsRadiusGlobalNasIpv4Address OBJECT-TYPE
    SYNTAX      IpAddress
    MAX-ACCESS  read-write
    STATUS      current
    DESCRIPTION 
        "Global NAS IPv4 address"
    ::= { vtssAuthConfigGlobalsRadiusGlobal 12 }

vtssAuthConfigGlobalsRadiusGlobalNasIpv6Enable OBJECT-TYPE
    SYNTAX      TruthValue
    MAX-ACCESS  read-write
    STATUS      current
    DESCRIPTION 
        "Enable Global NAS IPv6 address"
    ::= { vtssAuthConfigGlobalsRadiusGlobal 13 }

vtssAuthConfigGlobalsRadiusGlobalNasIpv6Address OBJECT-TYPE
    SYNTAX      InetAddressIPv6
    MAX-ACCESS  read-write
    STATUS      current
    DESCRIPTION 
        "Global NAS IPv6 address"
    ::= { vtssAuthConfigGlobalsRadiusGlobal 14 }

vtssAuthConfigGlobalsRadiusGlobalNasIdentifier OBJECT-TYPE
    SYNTAX      VTSSDisplayString (SIZE(0..255))
    MAX-ACCESS  read-write
    STATUS      current
    DESCRIPTION 
        "Global NAS Identifier"
    ::= { vtssAuthConfigGlobalsRadiusGlobal 15 }

vtssAuthConfigGlobalsRadiusHostTable OBJECT-TYPE
    SYNTAX      SEQUENCE OF VTSSAuthConfigGlobalsRadiusHostEntry
    MAX-ACCESS  not-accessible
    STATUS      current
    DESCRIPTION 
        "This is a table of Radius servers useed to query for RADIUS
         authentication"
    ::= { vtssAuthConfigGlobalsRadius 3 }

vtssAuthConfigGlobalsRadiusHostEntry OBJECT-TYPE
    SYNTAX      VTSSAuthConfigGlobalsRadiusHostEntry
    MAX-ACCESS  not-accessible
    STATUS      current
    DESCRIPTION 
        "Each entry defines a RADIUS server, with attributes used for contacting
         it. Host entries are consulted in numerical order of the entry index"
    INDEX       { vtssAuthConfigGlobalsRadiusHostIndex }
    ::= { vtssAuthConfigGlobalsRadiusHostTable 1 }

VTSSAuthConfigGlobalsRadiusHostEntry ::= SEQUENCE {
    vtssAuthConfigGlobalsRadiusHostIndex    Integer32,
    vtssAuthConfigGlobalsRadiusHostAddress      VTSSDisplayString,
    vtssAuthConfigGlobalsRadiusHostAuthPort     Unsigned32,
    vtssAuthConfigGlobalsRadiusHostAcctPort     Unsigned32,
    vtssAuthConfigGlobalsRadiusHostTimeout      Unsigned32,
    vtssAuthConfigGlobalsRadiusHostRetransmit   Unsigned32,
    vtssAuthConfigGlobalsRadiusHostKey      VTSSDisplayString
}

vtssAuthConfigGlobalsRadiusHostIndex OBJECT-TYPE
    SYNTAX      Integer32 (0..2147483647)
    MAX-ACCESS  not-accessible
    STATUS      current
    DESCRIPTION 
        "Host entry index"
    ::= { vtssAuthConfigGlobalsRadiusHostEntry 1 }

vtssAuthConfigGlobalsRadiusHostAddress OBJECT-TYPE
    SYNTAX      VTSSDisplayString (SIZE(0..255))
    MAX-ACCESS  read-write
    STATUS      current
    DESCRIPTION 
        "IPv4/IPv6 address or hostname of this server"
    ::= { vtssAuthConfigGlobalsRadiusHostEntry 2 }

vtssAuthConfigGlobalsRadiusHostAuthPort OBJECT-TYPE
    SYNTAX      Unsigned32
    MAX-ACCESS  read-write
    STATUS      current
    DESCRIPTION 
        "Authentication port number (UDP) for use for this server"
    ::= { vtssAuthConfigGlobalsRadiusHostEntry 3 }

vtssAuthConfigGlobalsRadiusHostAcctPort OBJECT-TYPE
    SYNTAX      Unsigned32
    MAX-ACCESS  read-write
    STATUS      current
    DESCRIPTION 
        "Accounting port number (UDP) to use for this server"
    ::= { vtssAuthConfigGlobalsRadiusHostEntry 4 }

vtssAuthConfigGlobalsRadiusHostTimeout OBJECT-TYPE
    SYNTAX      Unsigned32
    MAX-ACCESS  read-write
    STATUS      current
    DESCRIPTION 
        "Seconds to wait for a response from this server. Use global timeout if
         zero"
    ::= { vtssAuthConfigGlobalsRadiusHostEntry 5 }

vtssAuthConfigGlobalsRadiusHostRetransmit OBJECT-TYPE
    SYNTAX      Unsigned32
    MAX-ACCESS  read-write
    STATUS      current
    DESCRIPTION 
        "Number of times a request is resent to an unresponding server. Use
         global retransmit if zero"
    ::= { vtssAuthConfigGlobalsRadiusHostEntry 6 }

vtssAuthConfigGlobalsRadiusHostKey OBJECT-TYPE
    SYNTAX      VTSSDisplayString (SIZE(0..63))
    MAX-ACCESS  read-write
    STATUS      current
    DESCRIPTION 
        "The secret key to use for this server. Use global key if empty"
    ::= { vtssAuthConfigGlobalsRadiusHostEntry 7 }

vtssAuthConfigGlobalsTacacs OBJECT IDENTIFIER
    ::= { vtssAuthConfigGlobals 3 }

vtssAuthConfigGlobalsTacacsGlobal OBJECT IDENTIFIER
    ::= { vtssAuthConfigGlobalsTacacs 1 }

vtssAuthConfigGlobalsTacacsGlobalTimeout OBJECT-TYPE
    SYNTAX      Unsigned32
    MAX-ACCESS  read-write
    STATUS      current
    DESCRIPTION 
        "Global timeout for for TACACS servers. Can be overridden by individual
         host entries. (1 to 1000 seconds)"
    ::= { vtssAuthConfigGlobalsTacacsGlobal 1 }

vtssAuthConfigGlobalsTacacsGlobalDeadtime OBJECT-TYPE
    SYNTAX      Unsigned32
    MAX-ACCESS  read-write
    STATUS      current
    DESCRIPTION 
        "Global deadtime for TACACS servers. (0 to 1440 minutes)"
    ::= { vtssAuthConfigGlobalsTacacsGlobal 2 }

vtssAuthConfigGlobalsTacacsGlobalKey OBJECT-TYPE
    SYNTAX      VTSSDisplayString (SIZE(0..63))
    MAX-ACCESS  read-write
    STATUS      current
    DESCRIPTION 
        "Global secret key for TACACS servers. Can be overridden by individual
         host entries."
    ::= { vtssAuthConfigGlobalsTacacsGlobal 3 }

vtssAuthConfigGlobalsTacacsHostTable OBJECT-TYPE
    SYNTAX      SEQUENCE OF VTSSAuthConfigGlobalsTacacsHostEntry
    MAX-ACCESS  not-accessible
    STATUS      current
    DESCRIPTION 
        "This is a table of Tacacs servers useed to query for TACACS
         authentication"
    ::= { vtssAuthConfigGlobalsTacacs 2 }

vtssAuthConfigGlobalsTacacsHostEntry OBJECT-TYPE
    SYNTAX      VTSSAuthConfigGlobalsTacacsHostEntry
    MAX-ACCESS  not-accessible
    STATUS      current
    DESCRIPTION 
        "Each entry defines a TACACS server, with attributes used for contacting
         it. Host entries are consulted in numerical order of the entry index"
    INDEX       { vtssAuthConfigGlobalsTacacsHostIndex }
    ::= { vtssAuthConfigGlobalsTacacsHostTable 1 }

VTSSAuthConfigGlobalsTacacsHostEntry ::= SEQUENCE {
    vtssAuthConfigGlobalsTacacsHostIndex    Integer32,
    vtssAuthConfigGlobalsTacacsHostAddress      VTSSDisplayString,
    vtssAuthConfigGlobalsTacacsHostAuthPort     Unsigned32,
    vtssAuthConfigGlobalsTacacsHostTimeout      Unsigned32,
    vtssAuthConfigGlobalsTacacsHostKey      VTSSDisplayString
}

vtssAuthConfigGlobalsTacacsHostIndex OBJECT-TYPE
    SYNTAX      Integer32 (0..2147483647)
    MAX-ACCESS  not-accessible
    STATUS      current
    DESCRIPTION 
        "Host entry index"
    ::= { vtssAuthConfigGlobalsTacacsHostEntry 1 }

vtssAuthConfigGlobalsTacacsHostAddress OBJECT-TYPE
    SYNTAX      VTSSDisplayString (SIZE(0..255))
    MAX-ACCESS  read-write
    STATUS      current
    DESCRIPTION 
        "IPv4/IPv6 address or hostname of this server"
    ::= { vtssAuthConfigGlobalsTacacsHostEntry 2 }

vtssAuthConfigGlobalsTacacsHostAuthPort OBJECT-TYPE
    SYNTAX      Unsigned32
    MAX-ACCESS  read-write
    STATUS      current
    DESCRIPTION 
        "Authentication port number (TCP) to use for this server"
    ::= { vtssAuthConfigGlobalsTacacsHostEntry 3 }

vtssAuthConfigGlobalsTacacsHostTimeout OBJECT-TYPE
    SYNTAX      Unsigned32
    MAX-ACCESS  read-write
    STATUS      current
    DESCRIPTION 
        "Seconds to wait for a response from this server. Use global timeout if
         zero"
    ::= { vtssAuthConfigGlobalsTacacsHostEntry 4 }

vtssAuthConfigGlobalsTacacsHostKey OBJECT-TYPE
    SYNTAX      VTSSDisplayString (SIZE(0..63))
    MAX-ACCESS  read-write
    STATUS      current
    DESCRIPTION 
        "The secret key to use for this server. Use global key if empty"
    ::= { vtssAuthConfigGlobalsTacacsHostEntry 5 }

vtssAuthMibConformance OBJECT IDENTIFIER
    ::= { vtssAuthMib 2 }

vtssAuthMibCompliances OBJECT IDENTIFIER
    ::= { vtssAuthMibConformance 1 }

vtssAuthMibGroups OBJECT IDENTIFIER
    ::= { vtssAuthMibConformance 2 }

vtssAuthConfigGlobalsAgentsConsoleAuthenMethodsTableInfoGroup OBJECT-GROUP
    OBJECTS     { vtssAuthConfigGlobalsAgentsConsoleAuthenMethodsMethod }
    STATUS      current
    DESCRIPTION
        "A collection of objects suitable for bulk operations."
    ::= { vtssAuthMibGroups 1 }

vtssAuthConfigGlobalsAgentsTelnetAuthenMethodsTableInfoGroup OBJECT-GROUP
    OBJECTS     { vtssAuthConfigGlobalsAgentsTelnetAuthenMethodsMethod }
    STATUS      current
    DESCRIPTION
        "A collection of objects suitable for bulk operations."
    ::= { vtssAuthMibGroups 2 }

vtssAuthConfigGlobalsAgentsSshAuthenMethodsTableInfoGroup OBJECT-GROUP
    OBJECTS     { vtssAuthConfigGlobalsAgentsSshAuthenMethodsMethod }
    STATUS      current
    DESCRIPTION
        "A collection of objects suitable for bulk operations."
    ::= { vtssAuthMibGroups 3 }

vtssAuthConfigGlobalsAgentsHttpAuthenMethodsTableInfoGroup OBJECT-GROUP
    OBJECTS     { vtssAuthConfigGlobalsAgentsHttpAuthenMethodsMethod }
    STATUS      current
    DESCRIPTION
        "A collection of objects suitable for bulk operations."
    ::= { vtssAuthMibGroups 4 }

vtssAuthConfigGlobalsAgentsConsoleAuthorInfoGroup OBJECT-GROUP
    OBJECTS     { vtssAuthConfigGlobalsAgentsConsoleAuthorMethod, 
                  vtssAuthConfigGlobalsAgentsConsoleAuthorCmdEnable, 
                  vtssAuthConfigGlobalsAgentsConsoleAuthorCmdPrivLvl, 
                  vtssAuthConfigGlobalsAgentsConsoleAuthorCfgCmdEnable }
    STATUS      current
    DESCRIPTION
        "A collection of objects suitable for bulk operations."
    ::= { vtssAuthMibGroups 5 }

vtssAuthConfigGlobalsAgentsTelnetAuthorInfoGroup OBJECT-GROUP
    OBJECTS     { vtssAuthConfigGlobalsAgentsTelnetAuthorMethod, 
                  vtssAuthConfigGlobalsAgentsTelnetAuthorCmdEnable, 
                  vtssAuthConfigGlobalsAgentsTelnetAuthorCmdPrivLvl, 
                  vtssAuthConfigGlobalsAgentsTelnetAuthorCfgCmdEnable }
    STATUS      current
    DESCRIPTION
        "A collection of objects suitable for bulk operations."
    ::= { vtssAuthMibGroups 6 }

vtssAuthConfigGlobalsAgentsSshAuthorInfoGroup OBJECT-GROUP
    OBJECTS     { vtssAuthConfigGlobalsAgentsSshAuthorMethod, 
                  vtssAuthConfigGlobalsAgentsSshAuthorCmdEnable, 
                  vtssAuthConfigGlobalsAgentsSshAuthorCmdPrivLvl, 
                  vtssAuthConfigGlobalsAgentsSshAuthorCfgCmdEnable }
    STATUS      current
    DESCRIPTION
        "A collection of objects suitable for bulk operations."
    ::= { vtssAuthMibGroups 7 }

vtssAuthConfigGlobalsAgentsConsoleAcctInfoGroup OBJECT-GROUP
    OBJECTS     { vtssAuthConfigGlobalsAgentsConsoleAcctMethod, 
                  vtssAuthConfigGlobalsAgentsConsoleAcctCmdEnable, 
                  vtssAuthConfigGlobalsAgentsConsoleAcctCmdPrivLvl, 
                  vtssAuthConfigGlobalsAgentsConsoleAcctExecEnable }
    STATUS      current
    DESCRIPTION
        "A collection of objects suitable for bulk operations."
    ::= { vtssAuthMibGroups 8 }

vtssAuthConfigGlobalsAgentsTelnetAcctInfoGroup OBJECT-GROUP
    OBJECTS     { vtssAuthConfigGlobalsAgentsTelnetAcctMethod, 
                  vtssAuthConfigGlobalsAgentsTelnetAcctCmdEnable, 
                  vtssAuthConfigGlobalsAgentsTelnetAcctCmdPrivLvl, 
                  vtssAuthConfigGlobalsAgentsTelnetAcctExecEnable }
    STATUS      current
    DESCRIPTION
        "A collection of objects suitable for bulk operations."
    ::= { vtssAuthMibGroups 9 }

vtssAuthConfigGlobalsAgentsSshAcctInfoGroup OBJECT-GROUP
    OBJECTS     { vtssAuthConfigGlobalsAgentsSshAcctMethod, 
                  vtssAuthConfigGlobalsAgentsSshAcctCmdEnable, 
                  vtssAuthConfigGlobalsAgentsSshAcctCmdPrivLvl, 
                  vtssAuthConfigGlobalsAgentsSshAcctExecEnable }
    STATUS      current
    DESCRIPTION
        "A collection of objects suitable for bulk operations."
    ::= { vtssAuthMibGroups 10 }

vtssAuthConfigGlobalsRadiusGlobalInfoGroup OBJECT-GROUP
    OBJECTS     { vtssAuthConfigGlobalsRadiusGlobalTimeout, 
                  vtssAuthConfigGlobalsRadiusGlobalRetransmit, 
                  vtssAuthConfigGlobalsRadiusGlobalDeadtime, 
                  vtssAuthConfigGlobalsRadiusGlobalKey, 
                  vtssAuthConfigGlobalsRadiusGlobalNasIpv4Enable, 
                  vtssAuthConfigGlobalsRadiusGlobalNasIpv4Address, 
                  vtssAuthConfigGlobalsRadiusGlobalNasIpv6Enable, 
                  vtssAuthConfigGlobalsRadiusGlobalNasIpv6Address, 
                  vtssAuthConfigGlobalsRadiusGlobalNasIdentifier }
    STATUS      current
    DESCRIPTION
        "A collection of objects suitable for bulk operations."
    ::= { vtssAuthMibGroups 11 }

vtssAuthConfigGlobalsRadiusHostTableInfoGroup OBJECT-GROUP
    OBJECTS     { vtssAuthConfigGlobalsRadiusHostAddress, 
                  vtssAuthConfigGlobalsRadiusHostAuthPort, 
                  vtssAuthConfigGlobalsRadiusHostAcctPort, 
                  vtssAuthConfigGlobalsRadiusHostTimeout, 
                  vtssAuthConfigGlobalsRadiusHostRetransmit, 
                  vtssAuthConfigGlobalsRadiusHostKey }
    STATUS      current
    DESCRIPTION
        "A collection of objects suitable for bulk operations."
    ::= { vtssAuthMibGroups 12 }

vtssAuthConfigGlobalsTacacsGlobalInfoGroup OBJECT-GROUP
    OBJECTS     { vtssAuthConfigGlobalsTacacsGlobalTimeout, 
                  vtssAuthConfigGlobalsTacacsGlobalDeadtime, 
                  vtssAuthConfigGlobalsTacacsGlobalKey }
    STATUS      current
    DESCRIPTION
        "A collection of objects suitable for bulk operations."
    ::= { vtssAuthMibGroups 13 }

vtssAuthConfigGlobalsTacacsHostTableInfoGroup OBJECT-GROUP
    OBJECTS     { vtssAuthConfigGlobalsTacacsHostAddress, 
                  vtssAuthConfigGlobalsTacacsHostAuthPort, 
                  vtssAuthConfigGlobalsTacacsHostTimeout, 
                  vtssAuthConfigGlobalsTacacsHostKey }
    STATUS      current
    DESCRIPTION
        "A collection of objects suitable for bulk operations."
    ::= { vtssAuthMibGroups 14 }

vtssAuthMibCompliance MODULE-COMPLIANCE
    STATUS      current
    DESCRIPTION
        "The compliance statement for the implementation."

    MODULE      -- this module

        MANDATORY-GROUPS        { 
                  vtssAuthConfigGlobalsAgentsConsoleAuthenMethodsTableInfoGroup, 
                  vtssAuthConfigGlobalsAgentsTelnetAuthenMethodsTableInfoGroup, 
                  vtssAuthConfigGlobalsAgentsSshAuthenMethodsTableInfoGroup, 
                  vtssAuthConfigGlobalsAgentsHttpAuthenMethodsTableInfoGroup, 
                  vtssAuthConfigGlobalsAgentsConsoleAuthorInfoGroup, 
                  vtssAuthConfigGlobalsAgentsTelnetAuthorInfoGroup, 
                  vtssAuthConfigGlobalsAgentsSshAuthorInfoGroup, 
                  vtssAuthConfigGlobalsAgentsConsoleAcctInfoGroup, 
                  vtssAuthConfigGlobalsAgentsTelnetAcctInfoGroup, 
                  vtssAuthConfigGlobalsAgentsSshAcctInfoGroup, 
                  vtssAuthConfigGlobalsRadiusGlobalInfoGroup, 
                  vtssAuthConfigGlobalsRadiusHostTableInfoGroup, 
                  vtssAuthConfigGlobalsTacacsGlobalInfoGroup, 
                  vtssAuthConfigGlobalsTacacsHostTableInfoGroup }

    ::= { vtssAuthMibCompliances 1 }

END
