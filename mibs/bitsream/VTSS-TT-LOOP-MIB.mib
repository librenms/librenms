-- *****************************************************************
-- TT-LOOP-MIB:  Vitesse private MIB
--
-- Copyright (c) 2002-2013 Vitesse Semiconductor Corporation "Vitesse".
-- All Rights Reserved.
--
-- ****************************************************************

VTSS-TT-LOOP-MIB DEFINITIONS ::= BEGIN

IMPORTS
    MODULE-COMPLIANCE, OBJECT-GROUP
        FROM SNMPv2-CONF
    MODULE-IDENTITY, OBJECT-TYPE
        FROM SNMPv2-SMI
    TEXTUAL-CONVENTION
        FROM SNMPv2-TC
    vtssSwitchMgmt
        FROM VTSS-SMI
    Integer32 FROM SNMPv2-SMI
    Unsigned32 FROM SNMPv2-SMI
    VTSSDisplayString FROM VTSS-TC
    VTSSInterfaceIndex FROM VTSS-TC
    VTSSRowEditorState FROM VTSS-TC
    ;

vtssTtLoopMib MODULE-IDENTITY
    LAST-UPDATED "201411140000Z"
    ORGANIZATION
        "Vitesse Semiconductor Corporation"
    CONTACT-INFO
        "Application support <application_support@vitesse.com>"
    DESCRIPTION
        "This is a private Traffic Test Loop MIB that can be used for RFC2544
         and Y.1564 (remote end) testing"
    REVISION    "201411140000Z"
    DESCRIPTION
        "Refactoring regarding Ifindex. Domain element is removed and flow
         element is changed to be Ifindex containing domain"
    REVISION    "201407010000Z"
    DESCRIPTION
        "Initial version"
    ::= { vtssSwitchMgmt 128 }


VTSSTtLoopInstanceAdminState ::= TEXTUAL-CONVENTION
    STATUS      current
    DESCRIPTION
        "The instance Administrative State."
    SYNTAX      INTEGER { adminDisabled(0), adminEnabled(1) }

VTSSTtLoopInstanceDirection ::= TEXTUAL-CONVENTION
    STATUS      current
    DESCRIPTION
        "The instance direction."
    SYNTAX      INTEGER { facility(0), terminal(1) }

VTSSTtLoopInstanceOperState ::= TEXTUAL-CONVENTION
    STATUS      current
    DESCRIPTION
        "The instance Operational State."
    SYNTAX      INTEGER { operDown(0), operUp(1) }

VTSSTtLoopInstanceSubscriber ::= TEXTUAL-CONVENTION
    STATUS      current
    DESCRIPTION
        "The instance subscriber mode."
    SYNTAX      INTEGER { none(0), all(1), test(2) }

VTSSTtLoopInstanceType ::= TEXTUAL-CONVENTION
    STATUS      current
    DESCRIPTION
        "The instance type."
    SYNTAX      INTEGER { macLoop(0), oamLoop(1) }

vtssTtLoopMibObjects OBJECT IDENTIFIER
    ::= { vtssTtLoopMib 1 }

vtssTtLoopCapabilities OBJECT IDENTIFIER
    ::= { vtssTtLoopMibObjects 1 }

vtssTtLoopCapabilitiesInstanceMax OBJECT-TYPE
    SYNTAX      Unsigned32
    MAX-ACCESS  read-only
    STATUS      current
    DESCRIPTION 
        "Max number of TT_LOOP instance"
    ::= { vtssTtLoopCapabilities 1 }

vtssTtLoopCapabilitiesNameMax OBJECT-TYPE
    SYNTAX      Unsigned32
    MAX-ACCESS  read-only
    STATUS      current
    DESCRIPTION 
        "Max length of instance name"
    ::= { vtssTtLoopCapabilities 2 }

vtssTtLoopConfig OBJECT IDENTIFIER
    ::= { vtssTtLoopMibObjects 2 }

vtssTtLoopConfigInstanceTable OBJECT-TYPE
    SYNTAX      SEQUENCE OF VTSSTtLoopConfigInstanceEntry
    MAX-ACCESS  not-accessible
    STATUS      current
    DESCRIPTION 
        "This is a table of created instance configuration parameters"
    ::= { vtssTtLoopConfig 1 }

vtssTtLoopConfigInstanceEntry OBJECT-TYPE
    SYNTAX      VTSSTtLoopConfigInstanceEntry
    MAX-ACCESS  not-accessible
    STATUS      current
    DESCRIPTION 
        "This is a created instance configuration parameters. Not all parameters
         can be changed"
    INDEX       { vtssTtLoopConfigInstanceId }
    ::= { vtssTtLoopConfigInstanceTable 1 }

VTSSTtLoopConfigInstanceEntry ::= SEQUENCE {
    vtssTtLoopConfigInstanceId      Integer32,
    vtssTtLoopConfigInstanceName    VTSSDisplayString,
    vtssTtLoopConfigInstanceType    VTSSTtLoopInstanceType,
    vtssTtLoopConfigInstanceDirection   VTSSTtLoopInstanceDirection,
    vtssTtLoopConfigInstanceFlow    VTSSInterfaceIndex,
    vtssTtLoopConfigInstancePort    VTSSInterfaceIndex,
    vtssTtLoopConfigInstanceLevel   Unsigned32,
    vtssTtLoopConfigInstanceSubscriber      VTSSTtLoopInstanceSubscriber,
    vtssTtLoopConfigInstanceAdminState      VTSSTtLoopInstanceAdminState,
    vtssTtLoopConfigInstanceAction      VTSSRowEditorState
}

vtssTtLoopConfigInstanceId OBJECT-TYPE
    SYNTAX      Integer32 (0..2147483647)
    MAX-ACCESS  not-accessible
    STATUS      current
    DESCRIPTION 
        "The TT_LOOP instance ID"
    ::= { vtssTtLoopConfigInstanceEntry 1 }

vtssTtLoopConfigInstanceName OBJECT-TYPE
    SYNTAX      VTSSDisplayString (SIZE(0..32))
    MAX-ACCESS  read-write
    STATUS      current
    DESCRIPTION 
        "Instance name"
    ::= { vtssTtLoopConfigInstanceEntry 2 }

vtssTtLoopConfigInstanceType OBJECT-TYPE
    SYNTAX      VTSSTtLoopInstanceType
    MAX-ACCESS  read-write
    STATUS      current
    DESCRIPTION 
        "The Traffic Test loop type. Currently OAM Loop is only supported in EVC
         domain."
    ::= { vtssTtLoopConfigInstanceEntry 3 }

vtssTtLoopConfigInstanceDirection OBJECT-TYPE
    SYNTAX      VTSSTtLoopInstanceDirection
    MAX-ACCESS  read-write
    STATUS      current
    DESCRIPTION 
        "The instance direction. Currently Terminal Loop is only supported in
         EVC domain."
    ::= { vtssTtLoopConfigInstanceEntry 4 }

vtssTtLoopConfigInstanceFlow OBJECT-TYPE
    SYNTAX      VTSSInterfaceIndex
    MAX-ACCESS  read-write
    STATUS      current
    DESCRIPTION 
        "The flow instance. Currently VLAN domain is not supported."
    ::= { vtssTtLoopConfigInstanceEntry 6 }

vtssTtLoopConfigInstancePort OBJECT-TYPE
    SYNTAX      VTSSInterfaceIndex
    MAX-ACCESS  read-write
    STATUS      current
    DESCRIPTION 
        "The instance residence port."
    ::= { vtssTtLoopConfigInstanceEntry 7 }

vtssTtLoopConfigInstanceLevel OBJECT-TYPE
    SYNTAX      Unsigned32
    MAX-ACCESS  read-write
    STATUS      current
    DESCRIPTION 
        "The instance MEG level"
    ::= { vtssTtLoopConfigInstanceEntry 8 }

vtssTtLoopConfigInstanceSubscriber OBJECT-TYPE
    SYNTAX      VTSSTtLoopInstanceSubscriber
    MAX-ACCESS  read-write
    STATUS      current
    DESCRIPTION 
        "The EVC OAM loop subscriber mode"
    ::= { vtssTtLoopConfigInstanceEntry 9 }

vtssTtLoopConfigInstanceAdminState OBJECT-TYPE
    SYNTAX      VTSSTtLoopInstanceAdminState
    MAX-ACCESS  read-write
    STATUS      current
    DESCRIPTION 
        "The instance Administrative state."
    ::= { vtssTtLoopConfigInstanceEntry 10 }

vtssTtLoopConfigInstanceAction OBJECT-TYPE
    SYNTAX      VTSSRowEditorState
    MAX-ACCESS  read-write
    STATUS      current
    DESCRIPTION 
        "Action"
    ::= { vtssTtLoopConfigInstanceEntry 100 }

vtssTtLoopConfigInstanceRowEditor OBJECT IDENTIFIER
    ::= { vtssTtLoopConfig 2 }

vtssTtLoopConfigInstanceRowEditorId OBJECT-TYPE
    SYNTAX      Integer32 (0..2147483647)
    MAX-ACCESS  read-write
    STATUS      current
    DESCRIPTION 
        "The TT_LOOP instance ID"
    ::= { vtssTtLoopConfigInstanceRowEditor 1 }

vtssTtLoopConfigInstanceRowEditorName OBJECT-TYPE
    SYNTAX      VTSSDisplayString (SIZE(0..32))
    MAX-ACCESS  read-write
    STATUS      current
    DESCRIPTION 
        "Instance name"
    ::= { vtssTtLoopConfigInstanceRowEditor 2 }

vtssTtLoopConfigInstanceRowEditorType OBJECT-TYPE
    SYNTAX      VTSSTtLoopInstanceType
    MAX-ACCESS  read-write
    STATUS      current
    DESCRIPTION 
        "The Traffic Test loop type. Currently OAM Loop is only supported in EVC
         domain."
    ::= { vtssTtLoopConfigInstanceRowEditor 3 }

vtssTtLoopConfigInstanceRowEditorDirection OBJECT-TYPE
    SYNTAX      VTSSTtLoopInstanceDirection
    MAX-ACCESS  read-write
    STATUS      current
    DESCRIPTION 
        "The instance direction. Currently Terminal Loop is only supported in
         EVC domain."
    ::= { vtssTtLoopConfigInstanceRowEditor 4 }

vtssTtLoopConfigInstanceRowEditorFlow OBJECT-TYPE
    SYNTAX      VTSSInterfaceIndex
    MAX-ACCESS  read-write
    STATUS      current
    DESCRIPTION 
        "The flow instance. Currently VLAN domain is not supported."
    ::= { vtssTtLoopConfigInstanceRowEditor 6 }

vtssTtLoopConfigInstanceRowEditorPort OBJECT-TYPE
    SYNTAX      VTSSInterfaceIndex
    MAX-ACCESS  read-write
    STATUS      current
    DESCRIPTION 
        "The instance residence port."
    ::= { vtssTtLoopConfigInstanceRowEditor 7 }

vtssTtLoopConfigInstanceRowEditorLevel OBJECT-TYPE
    SYNTAX      Unsigned32
    MAX-ACCESS  read-write
    STATUS      current
    DESCRIPTION 
        "The instance MEG level"
    ::= { vtssTtLoopConfigInstanceRowEditor 8 }

vtssTtLoopConfigInstanceRowEditorSubscriber OBJECT-TYPE
    SYNTAX      VTSSTtLoopInstanceSubscriber
    MAX-ACCESS  read-write
    STATUS      current
    DESCRIPTION 
        "The EVC OAM loop subscriber mode"
    ::= { vtssTtLoopConfigInstanceRowEditor 9 }

vtssTtLoopConfigInstanceRowEditorAdminState OBJECT-TYPE
    SYNTAX      VTSSTtLoopInstanceAdminState
    MAX-ACCESS  read-write
    STATUS      current
    DESCRIPTION 
        "The instance Administrative state."
    ::= { vtssTtLoopConfigInstanceRowEditor 10 }

vtssTtLoopConfigInstanceRowEditorAction OBJECT-TYPE
    SYNTAX      VTSSRowEditorState
    MAX-ACCESS  read-write
    STATUS      current
    DESCRIPTION 
        "Action"
    ::= { vtssTtLoopConfigInstanceRowEditor 100 }

vtssTtLoopStatus OBJECT IDENTIFIER
    ::= { vtssTtLoopMibObjects 3 }

vtssTtLoopStatusInstanceTable OBJECT-TYPE
    SYNTAX      SEQUENCE OF VTSSTtLoopStatusInstanceEntry
    MAX-ACCESS  not-accessible
    STATUS      current
    DESCRIPTION 
        "This is a table of created instance status"
    ::= { vtssTtLoopStatus 1 }

vtssTtLoopStatusInstanceEntry OBJECT-TYPE
    SYNTAX      VTSSTtLoopStatusInstanceEntry
    MAX-ACCESS  not-accessible
    STATUS      current
    DESCRIPTION 
        "This is a created instance status"
    INDEX       { vtssTtLoopStatusInstanceId }
    ::= { vtssTtLoopStatusInstanceTable 1 }

VTSSTtLoopStatusInstanceEntry ::= SEQUENCE {
    vtssTtLoopStatusInstanceId      Integer32,
    vtssTtLoopStatusInstanceOperState   VTSSTtLoopInstanceOperState
}

vtssTtLoopStatusInstanceId OBJECT-TYPE
    SYNTAX      Integer32 (0..2147483647)
    MAX-ACCESS  not-accessible
    STATUS      current
    DESCRIPTION 
        "The TT_LOOP instance ID"
    ::= { vtssTtLoopStatusInstanceEntry 1 }

vtssTtLoopStatusInstanceOperState OBJECT-TYPE
    SYNTAX      VTSSTtLoopInstanceOperState
    MAX-ACCESS  read-only
    STATUS      current
    DESCRIPTION 
        "The instance Operational state."
    ::= { vtssTtLoopStatusInstanceEntry 2 }

vtssTtLoopMibConformance OBJECT IDENTIFIER
    ::= { vtssTtLoopMib 2 }

vtssTtLoopMibCompliances OBJECT IDENTIFIER
    ::= { vtssTtLoopMibConformance 1 }

vtssTtLoopMibGroups OBJECT IDENTIFIER
    ::= { vtssTtLoopMibConformance 2 }

vtssTtLoopCapabilitiesInfoGroup OBJECT-GROUP
    OBJECTS     { vtssTtLoopCapabilitiesInstanceMax, 
                  vtssTtLoopCapabilitiesNameMax }
    STATUS      current
    DESCRIPTION
        "A collection of objects suitable for bulk operations."
    ::= { vtssTtLoopMibGroups 1 }

vtssTtLoopConfigInstanceTableInfoGroup OBJECT-GROUP
    OBJECTS     { vtssTtLoopConfigInstanceName, vtssTtLoopConfigInstanceType, 
                  vtssTtLoopConfigInstanceDirection, 
                  vtssTtLoopConfigInstanceFlow, vtssTtLoopConfigInstancePort, 
                  vtssTtLoopConfigInstanceLevel, 
                  vtssTtLoopConfigInstanceSubscriber, 
                  vtssTtLoopConfigInstanceAdminState, 
                  vtssTtLoopConfigInstanceAction }
    STATUS      current
    DESCRIPTION
        "A collection of objects suitable for bulk operations."
    ::= { vtssTtLoopMibGroups 2 }

vtssTtLoopConfigInstanceRowEditorInfoGroup OBJECT-GROUP
    OBJECTS     { vtssTtLoopConfigInstanceRowEditorId, 
                  vtssTtLoopConfigInstanceRowEditorName, 
                  vtssTtLoopConfigInstanceRowEditorType, 
                  vtssTtLoopConfigInstanceRowEditorDirection, 
                  vtssTtLoopConfigInstanceRowEditorFlow, 
                  vtssTtLoopConfigInstanceRowEditorPort, 
                  vtssTtLoopConfigInstanceRowEditorLevel, 
                  vtssTtLoopConfigInstanceRowEditorSubscriber, 
                  vtssTtLoopConfigInstanceRowEditorAdminState, 
                  vtssTtLoopConfigInstanceRowEditorAction }
    STATUS      current
    DESCRIPTION
        "A collection of objects suitable for bulk operations."
    ::= { vtssTtLoopMibGroups 3 }

vtssTtLoopStatusInstanceTableInfoGroup OBJECT-GROUP
    OBJECTS     { vtssTtLoopStatusInstanceOperState }
    STATUS      current
    DESCRIPTION
        "A collection of objects suitable for bulk operations."
    ::= { vtssTtLoopMibGroups 4 }

vtssTtLoopMibCompliance MODULE-COMPLIANCE
    STATUS      current
    DESCRIPTION
        "The compliance statement for the implementation."

    MODULE      -- this module

        MANDATORY-GROUPS        { vtssTtLoopCapabilitiesInfoGroup, 
                  vtssTtLoopConfigInstanceTableInfoGroup, 
                  vtssTtLoopConfigInstanceRowEditorInfoGroup, 
                  vtssTtLoopStatusInstanceTableInfoGroup }

    ::= { vtssTtLoopMibCompliances 1 }

END
