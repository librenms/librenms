-- *****************************************************************
-- MAC-MIB:  Vitesse private MIB
--
-- Copyright (c) 2002-2013 Vitesse Semiconductor Corporation "Vitesse".
-- All Rights Reserved.
--
-- ****************************************************************

VTSS-MAC-MIB DEFINITIONS ::= BEGIN

IMPORTS
    MODULE-COMPLIANCE, OBJECT-GROUP
        FROM SNMPv2-CONF
    MODULE-IDENTITY, OBJECT-TYPE
        FROM SNMPv2-SMI
    TEXTUAL-CONVENTION
        FROM SNMPv2-TC
    vtssSwitchMgmt
        FROM VTSS-SMI
    Unsigned32 FROM SNMPv2-SMI
    MacAddress FROM SNMPv2-TC
    TruthValue FROM SNMPv2-TC
    VTSSInterfaceIndex FROM VTSS-TC
    VTSSPortList FROM VTSS-TC
    VTSSRowEditorState FROM VTSS-TC
    VTSSUnsigned8 FROM VTSS-TC
    VTSSVlan FROM VTSS-TC
    ;

vtssMacMib MODULE-IDENTITY
    LAST-UPDATED "201408200000Z"
    ORGANIZATION
        "Vitesse Semiconductor Corporation"
    CONTACT-INFO
        "Application support <application_support@vitesse.com>"
    DESCRIPTION
        "This is a private version of the MAC MIB"
    REVISION    "201408200000Z"
    DESCRIPTION
        "Updated types"
    REVISION    "201407010000Z"
    DESCRIPTION
        "Initial version"
    ::= { vtssSwitchMgmt 12 }


VTSSMACPortLearnMode ::= TEXTUAL-CONVENTION
    STATUS      current
    DESCRIPTION
        "The learning mode of the port."
    SYNTAX      INTEGER { auto(0), disable(1), secure(2) }

vtssMacMibObjects OBJECT IDENTIFIER
    ::= { vtssMacMib 1 }

vtssMacCapabilities OBJECT IDENTIFIER
    ::= { vtssMacMibObjects 1 }

vtssMacCapabilitiesNonVolatileMax OBJECT-TYPE
    SYNTAX      Unsigned32
    MAX-ACCESS  read-only
    STATUS      current
    DESCRIPTION 
        "Max number of static non-volatile MAC addresses that can be stored in
         the system."
    ::= { vtssMacCapabilities 1 }

vtssMacConfig OBJECT IDENTIFIER
    ::= { vtssMacMibObjects 2 }

vtssMacConfigFdbGlobal OBJECT IDENTIFIER
    ::= { vtssMacConfig 1 }

vtssMacConfigFdbGlobalAgeTime OBJECT-TYPE
    SYNTAX      Unsigned32
    MAX-ACCESS  read-write
    STATUS      current
    DESCRIPTION 
        "Mac address aging time in the FDB."
    ::= { vtssMacConfigFdbGlobal 1 }

vtssMacConfigFdbTable OBJECT-TYPE
    SYNTAX      SEQUENCE OF VTSSMacConfigFdbEntry
    MAX-ACCESS  not-accessible
    STATUS      current
    DESCRIPTION 
        "This table represents static mac addresses added through the mgmt
         interface. "
    ::= { vtssMacConfig 2 }

vtssMacConfigFdbEntry OBJECT-TYPE
    SYNTAX      VTSSMacConfigFdbEntry
    MAX-ACCESS  not-accessible
    STATUS      current
    DESCRIPTION 
        "Each entry has a set of parameters"
    INDEX       { vtssMacConfigFdbVlanId, vtssMacConfigFdbMacAddress }
    ::= { vtssMacConfigFdbTable 1 }

VTSSMacConfigFdbEntry ::= SEQUENCE {
    vtssMacConfigFdbVlanId      VTSSVlan,
    vtssMacConfigFdbMacAddress      MacAddress,
    vtssMacConfigFdbPortList    VTSSPortList,
    vtssMacConfigFdbAction      VTSSRowEditorState
}

vtssMacConfigFdbVlanId OBJECT-TYPE
    SYNTAX      VTSSVlan
    MAX-ACCESS  not-accessible
    STATUS      current
    DESCRIPTION 
        "Vlan id used for indexing."
    ::= { vtssMacConfigFdbEntry 1 }

vtssMacConfigFdbMacAddress OBJECT-TYPE
    SYNTAX      MacAddress
    MAX-ACCESS  not-accessible
    STATUS      current
    DESCRIPTION 
        "The destination MAC address which this entry applies."
    ::= { vtssMacConfigFdbEntry 2 }

vtssMacConfigFdbPortList OBJECT-TYPE
    SYNTAX      VTSSPortList
    MAX-ACCESS  read-write
    STATUS      current
    DESCRIPTION 
        "List of destination ports for which frames with this DMAC is forwarded
         to."
    ::= { vtssMacConfigFdbEntry 3 }

vtssMacConfigFdbAction OBJECT-TYPE
    SYNTAX      VTSSRowEditorState
    MAX-ACCESS  read-write
    STATUS      current
    DESCRIPTION 
        "Action"
    ::= { vtssMacConfigFdbEntry 100 }

vtssMacConfigFdbTableRowEditor OBJECT IDENTIFIER
    ::= { vtssMacConfig 3 }

vtssMacConfigFdbTableRowEditorVlanId OBJECT-TYPE
    SYNTAX      VTSSVlan
    MAX-ACCESS  read-write
    STATUS      current
    DESCRIPTION 
        "Vlan id used for indexing."
    ::= { vtssMacConfigFdbTableRowEditor 1 }

vtssMacConfigFdbTableRowEditorMacAddress OBJECT-TYPE
    SYNTAX      MacAddress
    MAX-ACCESS  read-write
    STATUS      current
    DESCRIPTION 
        "The destination MAC address which this entry applies."
    ::= { vtssMacConfigFdbTableRowEditor 2 }

vtssMacConfigFdbTableRowEditorPortList OBJECT-TYPE
    SYNTAX      VTSSPortList
    MAX-ACCESS  read-write
    STATUS      current
    DESCRIPTION 
        "List of destination ports for which frames with this DMAC is forwarded
         to."
    ::= { vtssMacConfigFdbTableRowEditor 3 }

vtssMacConfigFdbTableRowEditorAction OBJECT-TYPE
    SYNTAX      VTSSRowEditorState
    MAX-ACCESS  read-write
    STATUS      current
    DESCRIPTION 
        "Action"
    ::= { vtssMacConfigFdbTableRowEditor 100 }

vtssMacConfigPortLearnTable OBJECT-TYPE
    SYNTAX      SEQUENCE OF VTSSMacConfigPortLearnEntry
    MAX-ACCESS  not-accessible
    STATUS      current
    DESCRIPTION 
        "This table represents the learning mode of each port"
    ::= { vtssMacConfig 4 }

vtssMacConfigPortLearnEntry OBJECT-TYPE
    SYNTAX      VTSSMacConfigPortLearnEntry
    MAX-ACCESS  not-accessible
    STATUS      current
    DESCRIPTION 
        "Each entry has a set of parameters"
    INDEX       { vtssMacConfigPortLearnIfIndex }
    ::= { vtssMacConfigPortLearnTable 1 }

VTSSMacConfigPortLearnEntry ::= SEQUENCE {
    vtssMacConfigPortLearnIfIndex   VTSSInterfaceIndex,
    vtssMacConfigPortLearnLearnMode     VTSSMACPortLearnMode,
    vtssMacConfigPortLearnChangeAllowed     TruthValue
}

vtssMacConfigPortLearnIfIndex OBJECT-TYPE
    SYNTAX      VTSSInterfaceIndex
    MAX-ACCESS  not-accessible
    STATUS      current
    DESCRIPTION 
        "Interface index."
    ::= { vtssMacConfigPortLearnEntry 1 }

vtssMacConfigPortLearnLearnMode OBJECT-TYPE
    SYNTAX      VTSSMACPortLearnMode
    MAX-ACCESS  read-write
    STATUS      current
    DESCRIPTION 
        "The learn mode of the port. Auto(0) means auto learning. Disable(1)
         means that learning is disabled. Secure(2) means that learning frames
         are discarded."
    ::= { vtssMacConfigPortLearnEntry 2 }

vtssMacConfigPortLearnChangeAllowed OBJECT-TYPE
    SYNTAX      TruthValue
    MAX-ACCESS  read-write
    STATUS      current
    DESCRIPTION 
        "If internal modules have changed the learned mode then the user is not
         allowed to change it from this interface. This entry tells you if the
         LearnMode can be changed (true) or not (false). This is a read only
         entry - write is ignored."
    ::= { vtssMacConfigPortLearnEntry 3 }

vtssMacConfigVlanLearnTable OBJECT-TYPE
    SYNTAX      SEQUENCE OF VTSSMacConfigVlanLearnEntry
    MAX-ACCESS  not-accessible
    STATUS      current
    DESCRIPTION 
        "This table represents the learning mode of each vlan 1-4095"
    ::= { vtssMacConfig 5 }

vtssMacConfigVlanLearnEntry OBJECT-TYPE
    SYNTAX      VTSSMacConfigVlanLearnEntry
    MAX-ACCESS  not-accessible
    STATUS      current
    DESCRIPTION 
        "Each entry has a set of parameters"
    INDEX       { vtssMacConfigVlanLearnVlanId }
    ::= { vtssMacConfigVlanLearnTable 1 }

VTSSMacConfigVlanLearnEntry ::= SEQUENCE {
    vtssMacConfigVlanLearnVlanId    VTSSVlan,
    vtssMacConfigVlanLearnMode      TruthValue
}

vtssMacConfigVlanLearnVlanId OBJECT-TYPE
    SYNTAX      VTSSVlan
    MAX-ACCESS  not-accessible
    STATUS      current
    DESCRIPTION 
        "Vlan id used for indexing."
    ::= { vtssMacConfigVlanLearnEntry 1 }

vtssMacConfigVlanLearnMode OBJECT-TYPE
    SYNTAX      TruthValue
    MAX-ACCESS  read-write
    STATUS      current
    DESCRIPTION 
        "Learn mode of the VLAN, True = Enabled, False = Disabled"
    ::= { vtssMacConfigVlanLearnEntry 2 }

vtssMacStatus OBJECT IDENTIFIER
    ::= { vtssMacMibObjects 3 }

vtssMacStatusFdbTable OBJECT-TYPE
    SYNTAX      SEQUENCE OF VTSSMacStatusFdbEntry
    MAX-ACCESS  not-accessible
    STATUS      current
    DESCRIPTION 
        "This table represents all mac addresses in the FDB"
    ::= { vtssMacStatus 1 }

vtssMacStatusFdbEntry OBJECT-TYPE
    SYNTAX      VTSSMacStatusFdbEntry
    MAX-ACCESS  not-accessible
    STATUS      current
    DESCRIPTION 
        "Each entry has a set of parameters"
    INDEX       { vtssMacStatusFdbVlanId, vtssMacStatusFdbMacAddress }
    ::= { vtssMacStatusFdbTable 1 }

VTSSMacStatusFdbEntry ::= SEQUENCE {
    vtssMacStatusFdbVlanId      VTSSVlan,
    vtssMacStatusFdbMacAddress      MacAddress,
    vtssMacStatusFdbPortList    VTSSPortList,
    vtssMacStatusFdbDynamic     VTSSUnsigned8,
    vtssMacStatusFdbCopyToCpu   VTSSUnsigned8
}

vtssMacStatusFdbVlanId OBJECT-TYPE
    SYNTAX      VTSSVlan
    MAX-ACCESS  not-accessible
    STATUS      current
    DESCRIPTION 
        "Vlan id used for indexing."
    ::= { vtssMacStatusFdbEntry 1 }

vtssMacStatusFdbMacAddress OBJECT-TYPE
    SYNTAX      MacAddress
    MAX-ACCESS  not-accessible
    STATUS      current
    DESCRIPTION 
        "The destination MAC address which this entry applies."
    ::= { vtssMacStatusFdbEntry 2 }

vtssMacStatusFdbPortList OBJECT-TYPE
    SYNTAX      VTSSPortList
    MAX-ACCESS  read-only
    STATUS      current
    DESCRIPTION 
        "List of destination ports for which frames with this DMAC is forwarded
         to."
    ::= { vtssMacStatusFdbEntry 3 }

vtssMacStatusFdbDynamic OBJECT-TYPE
    SYNTAX      VTSSUnsigned8
    MAX-ACCESS  read-only
    STATUS      current
    DESCRIPTION 
        "The entry is dynamically learned (True) or statically added (False)"
    ::= { vtssMacStatusFdbEntry 4 }

vtssMacStatusFdbCopyToCpu OBJECT-TYPE
    SYNTAX      VTSSUnsigned8
    MAX-ACCESS  read-only
    STATUS      current
    DESCRIPTION 
        "Copy this frame to the CPU (True) or not (False)"
    ::= { vtssMacStatusFdbEntry 5 }

vtssMacStatusFdbStaticTable OBJECT-TYPE
    SYNTAX      SEQUENCE OF VTSSMacStatusFdbStaticEntry
    MAX-ACCESS  not-accessible
    STATUS      current
    DESCRIPTION 
        "This table represents all static mac addresses in the FDB"
    ::= { vtssMacStatus 2 }

vtssMacStatusFdbStaticEntry OBJECT-TYPE
    SYNTAX      VTSSMacStatusFdbStaticEntry
    MAX-ACCESS  not-accessible
    STATUS      current
    DESCRIPTION 
        "Each entry has a set of parameters"
    INDEX       { vtssMacStatusFdbStaticVlanId, vtssMacStatusFdbStaticMacAddress }
    ::= { vtssMacStatusFdbStaticTable 1 }

VTSSMacStatusFdbStaticEntry ::= SEQUENCE {
    vtssMacStatusFdbStaticVlanId    VTSSVlan,
    vtssMacStatusFdbStaticMacAddress    MacAddress,
    vtssMacStatusFdbStaticPortList      VTSSPortList,
    vtssMacStatusFdbStaticDynamic   VTSSUnsigned8,
    vtssMacStatusFdbStaticCopyToCpu     VTSSUnsigned8
}

vtssMacStatusFdbStaticVlanId OBJECT-TYPE
    SYNTAX      VTSSVlan
    MAX-ACCESS  not-accessible
    STATUS      current
    DESCRIPTION 
        "Vlan id used for indexing."
    ::= { vtssMacStatusFdbStaticEntry 1 }

vtssMacStatusFdbStaticMacAddress OBJECT-TYPE
    SYNTAX      MacAddress
    MAX-ACCESS  not-accessible
    STATUS      current
    DESCRIPTION 
        "The destination MAC address which this entry applies."
    ::= { vtssMacStatusFdbStaticEntry 2 }

vtssMacStatusFdbStaticPortList OBJECT-TYPE
    SYNTAX      VTSSPortList
    MAX-ACCESS  read-only
    STATUS      current
    DESCRIPTION 
        "List of destination ports for which frames with this DMAC is forwarded
         to."
    ::= { vtssMacStatusFdbStaticEntry 3 }

vtssMacStatusFdbStaticDynamic OBJECT-TYPE
    SYNTAX      VTSSUnsigned8
    MAX-ACCESS  read-only
    STATUS      current
    DESCRIPTION 
        "The entry is dynamically learned (True) or statically added (False)"
    ::= { vtssMacStatusFdbStaticEntry 4 }

vtssMacStatusFdbStaticCopyToCpu OBJECT-TYPE
    SYNTAX      VTSSUnsigned8
    MAX-ACCESS  read-only
    STATUS      current
    DESCRIPTION 
        "Copy this frame to the CPU (True) or not (False)"
    ::= { vtssMacStatusFdbStaticEntry 5 }

vtssMacStatusFdbPortStatisticsTable OBJECT-TYPE
    SYNTAX      SEQUENCE OF VTSSMacStatusFdbPortStatisticsEntry
    MAX-ACCESS  not-accessible
    STATUS      current
    DESCRIPTION 
        "This table represent the statistics of the Port interfaces"
    ::= { vtssMacStatus 3 }

vtssMacStatusFdbPortStatisticsEntry OBJECT-TYPE
    SYNTAX      VTSSMacStatusFdbPortStatisticsEntry
    MAX-ACCESS  not-accessible
    STATUS      current
    DESCRIPTION 
        "Each port has a number of learned addresses"
    INDEX       { vtssMacStatusFdbPortStatisticsIfIndex }
    ::= { vtssMacStatusFdbPortStatisticsTable 1 }

VTSSMacStatusFdbPortStatisticsEntry ::= SEQUENCE {
    vtssMacStatusFdbPortStatisticsIfIndex   VTSSInterfaceIndex,
    vtssMacStatusFdbPortStatisticsDynamic   Unsigned32
}

vtssMacStatusFdbPortStatisticsIfIndex OBJECT-TYPE
    SYNTAX      VTSSInterfaceIndex
    MAX-ACCESS  not-accessible
    STATUS      current
    DESCRIPTION 
        "Interface index."
    ::= { vtssMacStatusFdbPortStatisticsEntry 1 }

vtssMacStatusFdbPortStatisticsDynamic OBJECT-TYPE
    SYNTAX      Unsigned32
    MAX-ACCESS  read-only
    STATUS      current
    DESCRIPTION 
        "Total number of dynamic learned addresses on the port"
    ::= { vtssMacStatusFdbPortStatisticsEntry 2 }

vtssMacStatusFdbStatistics OBJECT IDENTIFIER
    ::= { vtssMacStatus 4 }

vtssMacStatusFdbStatisticsTotalDynamic OBJECT-TYPE
    SYNTAX      Unsigned32
    MAX-ACCESS  read-only
    STATUS      current
    DESCRIPTION 
        "Total dynamic learned addresses in the FDB"
    ::= { vtssMacStatusFdbStatistics 1 }

vtssMacStatusFdbStatisticsTotalStatic OBJECT-TYPE
    SYNTAX      Unsigned32
    MAX-ACCESS  read-only
    STATUS      current
    DESCRIPTION 
        "Total static addresses in the FDB"
    ::= { vtssMacStatusFdbStatistics 2 }

vtssMacControl OBJECT IDENTIFIER
    ::= { vtssMacMibObjects 4 }

vtssMacControlFlushAll OBJECT-TYPE
    SYNTAX      TruthValue
    MAX-ACCESS  read-write
    STATUS      current
    DESCRIPTION 
        "Flush all dynamic learned Mac addresses. Set the value to 'true' to
         perform the action. Read will always return 'false'."
    ::= { vtssMacControl 1 }

vtssMacMibConformance OBJECT IDENTIFIER
    ::= { vtssMacMib 2 }

vtssMacMibCompliances OBJECT IDENTIFIER
    ::= { vtssMacMibConformance 1 }

vtssMacMibGroups OBJECT IDENTIFIER
    ::= { vtssMacMibConformance 2 }

vtssMacCapabilitiesInfoGroup OBJECT-GROUP
    OBJECTS     { vtssMacCapabilitiesNonVolatileMax }
    STATUS      current
    DESCRIPTION
        "A collection of objects suitable for bulk operations."
    ::= { vtssMacMibGroups 1 }

vtssMacConfigFdbGlobalInfoGroup OBJECT-GROUP
    OBJECTS     { vtssMacConfigFdbGlobalAgeTime }
    STATUS      current
    DESCRIPTION
        "A collection of objects suitable for bulk operations."
    ::= { vtssMacMibGroups 2 }

vtssMacConfigFdbTableInfoGroup OBJECT-GROUP
    OBJECTS     { vtssMacConfigFdbPortList, vtssMacConfigFdbAction }
    STATUS      current
    DESCRIPTION
        "A collection of objects suitable for bulk operations."
    ::= { vtssMacMibGroups 3 }

vtssMacConfigFdbTableRowEditorInfoGroup OBJECT-GROUP
    OBJECTS     { vtssMacConfigFdbTableRowEditorVlanId, 
                  vtssMacConfigFdbTableRowEditorMacAddress, 
                  vtssMacConfigFdbTableRowEditorPortList, 
                  vtssMacConfigFdbTableRowEditorAction }
    STATUS      current
    DESCRIPTION
        "A collection of objects suitable for bulk operations."
    ::= { vtssMacMibGroups 4 }

vtssMacConfigPortLearnInfoGroup OBJECT-GROUP
    OBJECTS     { vtssMacConfigPortLearnLearnMode, 
                  vtssMacConfigPortLearnChangeAllowed }
    STATUS      current
    DESCRIPTION
        "A collection of objects suitable for bulk operations."
    ::= { vtssMacMibGroups 5 }

vtssMacConfigVlanLearnInfoGroup OBJECT-GROUP
    OBJECTS     { vtssMacConfigVlanLearnMode }
    STATUS      current
    DESCRIPTION
        "A collection of objects suitable for bulk operations."
    ::= { vtssMacMibGroups 6 }

vtssMacStatusFdbTableInfoGroup OBJECT-GROUP
    OBJECTS     { vtssMacStatusFdbPortList, vtssMacStatusFdbDynamic, 
                  vtssMacStatusFdbCopyToCpu }
    STATUS      current
    DESCRIPTION
        "A collection of objects suitable for bulk operations."
    ::= { vtssMacMibGroups 7 }

vtssMacStatusFdbStaticTableInfoGroup OBJECT-GROUP
    OBJECTS     { vtssMacStatusFdbStaticPortList, vtssMacStatusFdbStaticDynamic, 
                  vtssMacStatusFdbStaticCopyToCpu }
    STATUS      current
    DESCRIPTION
        "A collection of objects suitable for bulk operations."
    ::= { vtssMacMibGroups 8 }

vtssMacStatusFdbPortStatisticsInfoGroup OBJECT-GROUP
    OBJECTS     { vtssMacStatusFdbPortStatisticsDynamic }
    STATUS      current
    DESCRIPTION
        "A collection of objects suitable for bulk operations."
    ::= { vtssMacMibGroups 9 }

vtssMacStatusFdbStatisticsInfoGroup OBJECT-GROUP
    OBJECTS     { vtssMacStatusFdbStatisticsTotalDynamic, 
                  vtssMacStatusFdbStatisticsTotalStatic }
    STATUS      current
    DESCRIPTION
        "A collection of objects suitable for bulk operations."
    ::= { vtssMacMibGroups 10 }

vtssMacControlInfoGroup OBJECT-GROUP
    OBJECTS     { vtssMacControlFlushAll }
    STATUS      current
    DESCRIPTION
        "A collection of objects suitable for bulk operations."
    ::= { vtssMacMibGroups 11 }

vtssMacMibCompliance MODULE-COMPLIANCE
    STATUS      current
    DESCRIPTION
        "The compliance statement for the implementation."

    MODULE      -- this module

        MANDATORY-GROUPS        { vtssMacCapabilitiesInfoGroup, 
                  vtssMacConfigFdbGlobalInfoGroup, 
                  vtssMacConfigFdbTableInfoGroup, 
                  vtssMacConfigFdbTableRowEditorInfoGroup, 
                  vtssMacConfigPortLearnInfoGroup, 
                  vtssMacConfigVlanLearnInfoGroup, 
                  vtssMacStatusFdbTableInfoGroup, 
                  vtssMacStatusFdbStaticTableInfoGroup, 
                  vtssMacStatusFdbPortStatisticsInfoGroup, 
                  vtssMacStatusFdbStatisticsInfoGroup, vtssMacControlInfoGroup }

    ::= { vtssMacMibCompliances 1 }

END
