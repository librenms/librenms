BTS-SMI DEFINITIONS ::= BEGIN

IMPORTS
    MODULE-IDENTITY,
    OBJECT-IDENTITY,
    enterprises
        FROM SNMPv2-SMI;


bitstream MODULE-IDENTITY
    LAST-UPDATED    "201812170000Z"
    ORGANIZATION    "BitStream Sp. z o.o."
    CONTACT-INFO
            "BitStream Sp. z o.o."
    DESCRIPTION
        "The Structure of Management Information for the
        Bitstream enterprise."
    REVISION        "201812170000Z"
    DESCRIPTION
        "Initial version of this MIB module."
    ::= { enterprises 6603 }


switchMgmt OBJECT-IDENTITY
    STATUS          current
    DESCRIPTION
        "switchMgmt is the root OBJECT IDENTIFIER from
         which object id values are assigned."
    ::= { bitstream 0 }



END
