-- *****************************************************************
-- DHCP-RELAY-MIB:  Vitesse private MIB
--
-- Copyright (c) 2002-2013 Vitesse Semiconductor Corporation "Vitesse".
-- All Rights Reserved.
--
-- ****************************************************************

VTSS-DHCP-RELAY-MIB DEFINITIONS ::= BEGIN

IMPORTS
    MODULE-COMPLIANCE, OBJECT-GROUP
        FROM SNMPv2-CONF
    MODULE-IDENTITY, OBJECT-TYPE
        FROM SNMPv2-SMI
    TEXTUAL-CONVENTION
        FROM SNMPv2-TC
    vtssSwitchMgmt
        FROM VTSS-SMI
    IpAddress FROM SNMPv2-SMI
    Unsigned32 FROM SNMPv2-SMI
    TruthValue FROM SNMPv2-TC
    ;

vtssDhcpRelayMib MODULE-IDENTITY
    LAST-UPDATED "201410100000Z"
    ORGANIZATION
        "Vitesse Semiconductor Corporation"
    CONTACT-INFO
        "Application support <application_support@vitesse.com>"
    DESCRIPTION
        "This is a private version of the DHCP Relay MIB"
    REVISION    "201410100000Z"
    DESCRIPTION
        "Editorial changes"
    REVISION    "201407010000Z"
    DESCRIPTION
        "Initial version"
    ::= { vtssSwitchMgmt 55 }


VTSSDhcpRelayInformationPolicyType ::= TEXTUAL-CONVENTION
    STATUS      current
    DESCRIPTION
        "This enumeration indicates the DHCP relay information policy type."
    SYNTAX      INTEGER { replace(0), keep(1), drop(2) }

vtssDhcpRelayMibObjects OBJECT IDENTIFIER
    ::= { vtssDhcpRelayMib 1 }

vtssDhcpRelayConfig OBJECT IDENTIFIER
    ::= { vtssDhcpRelayMibObjects 2 }

vtssDhcpRelayConfigGlobals OBJECT IDENTIFIER
    ::= { vtssDhcpRelayConfig 1 }

vtssDhcpRelayConfigGlobalsMode OBJECT-TYPE
    SYNTAX      TruthValue
    MAX-ACCESS  read-write
    STATUS      current
    DESCRIPTION 
        "Global mode of DHCP relay. true is to enable DHCP relay and false is to
         disable it."
    ::= { vtssDhcpRelayConfigGlobals 1 }

vtssDhcpRelayConfigGlobalsServerIpAddress OBJECT-TYPE
    SYNTAX      IpAddress
    MAX-ACCESS  read-write
    STATUS      current
    DESCRIPTION 
        "Server IP address. This IP address is for DHCP server where the DHCP
         relay will relay DHCP packets to."
    ::= { vtssDhcpRelayConfigGlobals 2 }

vtssDhcpRelayConfigGlobalsInformationMode OBJECT-TYPE
    SYNTAX      TruthValue
    MAX-ACCESS  read-write
    STATUS      current
    DESCRIPTION 
        "Indicates the DHCP relay information mode option operation. Possible
         modes are - Enabled: Enable DHCP relay information mode operation. When
         DHCP relay information mode operation is enabled, the agent inserts
         specific information (option 82) into a DHCP message when forwarding to
         DHCP server and removes it from a DHCP message when transferring to
         DHCP client. It only works when DHCP relay operation mode is enabled.
         Disabled: Disable DHCP relay information mode operation."
    ::= { vtssDhcpRelayConfigGlobals 3 }

vtssDhcpRelayConfigGlobalsInformationPolicy OBJECT-TYPE
    SYNTAX      VTSSDhcpRelayInformationPolicyType
    MAX-ACCESS  read-write
    STATUS      current
    DESCRIPTION 
        "Indicates the DHCP relay information option policy. When DHCP relay
         information mode operation is enabled, if the agent receives a DHCP
         message that already contains relay agent information it will enforce
         the policy. The 'Replace' policy is invalid when relay information mode
         is disabled."
    ::= { vtssDhcpRelayConfigGlobals 4 }

vtssDhcpRelayStatus OBJECT IDENTIFIER
    ::= { vtssDhcpRelayMibObjects 3 }

vtssDhcpRelayStatusStatistics OBJECT IDENTIFIER
    ::= { vtssDhcpRelayStatus 1 }

vtssDhcpRelayStatusStatisticsServerPacketsRelayed OBJECT-TYPE
    SYNTAX      Unsigned32
    MAX-ACCESS  read-only
    STATUS      current
    DESCRIPTION 
        "Packets relayed from server to client."
    ::= { vtssDhcpRelayStatusStatistics 1 }

vtssDhcpRelayStatusStatisticsServerPacketErrors OBJECT-TYPE
    SYNTAX      Unsigned32
    MAX-ACCESS  read-only
    STATUS      current
    DESCRIPTION 
        "Errors sending packets to servers."
    ::= { vtssDhcpRelayStatusStatistics 2 }

vtssDhcpRelayStatusStatisticsClientPacketsRelayed OBJECT-TYPE
    SYNTAX      Unsigned32
    MAX-ACCESS  read-only
    STATUS      current
    DESCRIPTION 
        "Packets relayed from client to server."
    ::= { vtssDhcpRelayStatusStatistics 3 }

vtssDhcpRelayStatusStatisticsClientPacketErrors OBJECT-TYPE
    SYNTAX      Unsigned32
    MAX-ACCESS  read-only
    STATUS      current
    DESCRIPTION 
        "Errors sending packets to clients."
    ::= { vtssDhcpRelayStatusStatistics 4 }

vtssDhcpRelayStatusStatisticsAgentOptionErrors OBJECT-TYPE
    SYNTAX      Unsigned32
    MAX-ACCESS  read-only
    STATUS      current
    DESCRIPTION 
        "Number of packets forwarded without agent options because there was no
         room."
    ::= { vtssDhcpRelayStatusStatistics 5 }

vtssDhcpRelayStatusStatisticsMissingAgentOption OBJECT-TYPE
    SYNTAX      Unsigned32
    MAX-ACCESS  read-only
    STATUS      current
    DESCRIPTION 
        "Number of packets dropped because no RAI option matching our ID was
         found."
    ::= { vtssDhcpRelayStatusStatistics 6 }

vtssDhcpRelayStatusStatisticsBadCircuitId OBJECT-TYPE
    SYNTAX      Unsigned32
    MAX-ACCESS  read-only
    STATUS      current
    DESCRIPTION 
        "Circuit ID option in matching RAI option did not match any known
         circuit ID."
    ::= { vtssDhcpRelayStatusStatistics 7 }

vtssDhcpRelayStatusStatisticsMissingCircuitId OBJECT-TYPE
    SYNTAX      Unsigned32
    MAX-ACCESS  read-only
    STATUS      current
    DESCRIPTION 
        "Circuit ID option in matching RAI option was missing."
    ::= { vtssDhcpRelayStatusStatistics 8 }

vtssDhcpRelayStatusStatisticsBadRemoteId OBJECT-TYPE
    SYNTAX      Unsigned32
    MAX-ACCESS  read-only
    STATUS      current
    DESCRIPTION 
        "Remote ID option in matching RAI option did not match any known remote
         ID."
    ::= { vtssDhcpRelayStatusStatistics 9 }

vtssDhcpRelayStatusStatisticsMissingRemoteId OBJECT-TYPE
    SYNTAX      Unsigned32
    MAX-ACCESS  read-only
    STATUS      current
    DESCRIPTION 
        "Remote ID option in matching RAI option was missing."
    ::= { vtssDhcpRelayStatusStatistics 10 }

vtssDhcpRelayStatusStatisticsReceiveServerPackets OBJECT-TYPE
    SYNTAX      Unsigned32
    MAX-ACCESS  read-only
    STATUS      current
    DESCRIPTION 
        "Receive DHCP message from server."
    ::= { vtssDhcpRelayStatusStatistics 11 }

vtssDhcpRelayStatusStatisticsReceiveClientPackets OBJECT-TYPE
    SYNTAX      Unsigned32
    MAX-ACCESS  read-only
    STATUS      current
    DESCRIPTION 
        "Receive DHCP message from client."
    ::= { vtssDhcpRelayStatusStatistics 12 }

vtssDhcpRelayStatusStatisticsReceiveClientAgentOption OBJECT-TYPE
    SYNTAX      Unsigned32
    MAX-ACCESS  read-only
    STATUS      current
    DESCRIPTION 
        "Receive relay agent information option from client."
    ::= { vtssDhcpRelayStatusStatistics 13 }

vtssDhcpRelayStatusStatisticsReplaceAgentOption OBJECT-TYPE
    SYNTAX      Unsigned32
    MAX-ACCESS  read-only
    STATUS      current
    DESCRIPTION 
        "Replace relay agent information option."
    ::= { vtssDhcpRelayStatusStatistics 14 }

vtssDhcpRelayStatusStatisticsKeepAgentOption OBJECT-TYPE
    SYNTAX      Unsigned32
    MAX-ACCESS  read-only
    STATUS      current
    DESCRIPTION 
        "Keep relay agent information option."
    ::= { vtssDhcpRelayStatusStatistics 15 }

vtssDhcpRelayStatusStatisticsDropAgentOption OBJECT-TYPE
    SYNTAX      Unsigned32
    MAX-ACCESS  read-only
    STATUS      current
    DESCRIPTION 
        "Drop relay agent information option."
    ::= { vtssDhcpRelayStatusStatistics 16 }

vtssDhcpRelayControl OBJECT IDENTIFIER
    ::= { vtssDhcpRelayMibObjects 4 }

vtssDhcpRelayControlClearStatistics OBJECT-TYPE
    SYNTAX      TruthValue
    MAX-ACCESS  read-write
    STATUS      current
    DESCRIPTION 
        "The action to clear statistics. true is to clear the statistics data.
         false, then, does nothing."
    ::= { vtssDhcpRelayControl 1 }

vtssDhcpRelayMibConformance OBJECT IDENTIFIER
    ::= { vtssDhcpRelayMib 2 }

vtssDhcpRelayMibCompliances OBJECT IDENTIFIER
    ::= { vtssDhcpRelayMibConformance 1 }

vtssDhcpRelayMibGroups OBJECT IDENTIFIER
    ::= { vtssDhcpRelayMibConformance 2 }

vtssDhcpRelayConfigGlobalsInfoGroup OBJECT-GROUP
    OBJECTS     { vtssDhcpRelayConfigGlobalsMode, 
                  vtssDhcpRelayConfigGlobalsServerIpAddress, 
                  vtssDhcpRelayConfigGlobalsInformationMode, 
                  vtssDhcpRelayConfigGlobalsInformationPolicy }
    STATUS      current
    DESCRIPTION
        "A collection of objects suitable for bulk operations."
    ::= { vtssDhcpRelayMibGroups 1 }

vtssDhcpRelayStatusStatisticsInfoGroup OBJECT-GROUP
    OBJECTS     { vtssDhcpRelayStatusStatisticsServerPacketsRelayed, 
                  vtssDhcpRelayStatusStatisticsServerPacketErrors, 
                  vtssDhcpRelayStatusStatisticsClientPacketsRelayed, 
                  vtssDhcpRelayStatusStatisticsClientPacketErrors, 
                  vtssDhcpRelayStatusStatisticsAgentOptionErrors, 
                  vtssDhcpRelayStatusStatisticsMissingAgentOption, 
                  vtssDhcpRelayStatusStatisticsBadCircuitId, 
                  vtssDhcpRelayStatusStatisticsMissingCircuitId, 
                  vtssDhcpRelayStatusStatisticsBadRemoteId, 
                  vtssDhcpRelayStatusStatisticsMissingRemoteId, 
                  vtssDhcpRelayStatusStatisticsReceiveServerPackets, 
                  vtssDhcpRelayStatusStatisticsReceiveClientPackets, 
                  vtssDhcpRelayStatusStatisticsReceiveClientAgentOption, 
                  vtssDhcpRelayStatusStatisticsReplaceAgentOption, 
                  vtssDhcpRelayStatusStatisticsKeepAgentOption, 
                  vtssDhcpRelayStatusStatisticsDropAgentOption }
    STATUS      current
    DESCRIPTION
        "A collection of objects suitable for bulk operations."
    ::= { vtssDhcpRelayMibGroups 2 }

vtssDhcpRelayControlInfoGroup OBJECT-GROUP
    OBJECTS     { vtssDhcpRelayControlClearStatistics }
    STATUS      current
    DESCRIPTION
        "A collection of objects suitable for bulk operations."
    ::= { vtssDhcpRelayMibGroups 3 }

vtssDhcpRelayMibCompliance MODULE-COMPLIANCE
    STATUS      current
    DESCRIPTION
        "The compliance statement for the implementation."

    MODULE      -- this module

        MANDATORY-GROUPS        { vtssDhcpRelayConfigGlobalsInfoGroup, 
                  vtssDhcpRelayStatusStatisticsInfoGroup, 
                  vtssDhcpRelayControlInfoGroup }

    ::= { vtssDhcpRelayMibCompliances 1 }

END
