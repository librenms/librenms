-- *****************************************************************
-- UPNP-MIB:  Vitesse private MIB
--
-- Copyright (c) 2002-2013 Vitesse Semiconductor Corporation "Vitesse".
-- All Rights Reserved.
--
-- ****************************************************************

VTSS-UPNP-MIB DEFINITIONS ::= BEGIN

IMPORTS
    MODULE-COMPLIANCE, OBJECT-GROUP
        FROM SNMPv2-CONF
    MODULE-IDENTITY, OBJECT-TYPE
        FROM SNMPv2-SMI
    TEXTUAL-CONVENTION
        FROM SNMPv2-TC
    vtssSwitchMgmt
        FROM VTSS-SMI
    Integer32 FROM SNMPv2-SMI
    TruthValue FROM SNMPv2-TC
    VTSSUnsigned8 FROM VTSS-TC
    ;

vtssUpnpMib MODULE-IDENTITY
    LAST-UPDATED "201410100000Z"
    ORGANIZATION
        "Vitesse Semiconductor Corporation"
    CONTACT-INFO
        "Application support <application_support@vitesse.com>"
    DESCRIPTION
        "This is a private version of UPnP"
    REVISION    "201410100000Z"
    DESCRIPTION
        "Editorial changes"
    REVISION    "201407010000Z"
    DESCRIPTION
        "Initial version"
    ::= { vtssSwitchMgmt 52 }


vtssUpnpMibObjects OBJECT IDENTIFIER
    ::= { vtssUpnpMib 1 }

vtssUpnpConfig OBJECT IDENTIFIER
    ::= { vtssUpnpMibObjects 2 }

vtssUpnpConfigGlobals OBJECT IDENTIFIER
    ::= { vtssUpnpConfig 1 }

vtssUpnpConfigGlobalsMode OBJECT-TYPE
    SYNTAX      TruthValue
    MAX-ACCESS  read-write
    STATUS      current
    DESCRIPTION 
        "Global mode of UPnP. true is to enable the functions of HTTPS and false
         is to disable it."
    ::= { vtssUpnpConfigGlobals 1 }

vtssUpnpConfigGlobalsTtl OBJECT-TYPE
    SYNTAX      VTSSUnsigned8 (1..255)
    MAX-ACCESS  read-write
    STATUS      current
    DESCRIPTION 
        "The TTL value is used by UPnP to send SSDP advertisement messages.Valid
         values are in the range 1 to 255. "
    ::= { vtssUpnpConfigGlobals 2 }

vtssUpnpConfigGlobalsAdvertisingDuration OBJECT-TYPE
    SYNTAX      Integer32 (100..86400)
    MAX-ACCESS  read-write
    STATUS      current
    DESCRIPTION 
        "The duration, carried in SSDP packets, is used to inform a control
         point or control points how often it or they should receive an SSDP
         advertisement message from this switch. If a control point does not
         receive any message within the duration, it will think that the switch
         no longer exists. Due to the unreliable nature of UDP, in the standard
         it is recommended that such refreshing of advertisements to be done at
         less than one-half of the advertising duration. In the implementation,
         the switch sends SSDP messages periodically at the interval one-half of
         the advertising duration minus 30 seconds. Valid values are in the
         range 100 to 86400. "
    ::= { vtssUpnpConfigGlobals 3 }

vtssUpnpMibConformance OBJECT IDENTIFIER
    ::= { vtssUpnpMib 2 }

vtssUpnpMibCompliances OBJECT IDENTIFIER
    ::= { vtssUpnpMibConformance 1 }

vtssUpnpMibGroups OBJECT IDENTIFIER
    ::= { vtssUpnpMibConformance 2 }

vtssUpnpConfigGlobalsInfoGroup OBJECT-GROUP
    OBJECTS     { vtssUpnpConfigGlobalsMode, vtssUpnpConfigGlobalsTtl, 
                  vtssUpnpConfigGlobalsAdvertisingDuration }
    STATUS      current
    DESCRIPTION
        "A collection of objects suitable for bulk operations."
    ::= { vtssUpnpMibGroups 1 }

vtssUpnpMibCompliance MODULE-COMPLIANCE
    STATUS      current
    DESCRIPTION
        "The compliance statement for the implementation."

    MODULE      -- this module

        MANDATORY-GROUPS        { vtssUpnpConfigGlobalsInfoGroup }

    ::= { vtssUpnpMibCompliances 1 }

END
