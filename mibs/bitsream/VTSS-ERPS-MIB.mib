-- *****************************************************************
-- ERPS-MIB:  Vitesse private MIB
--
-- Copyright (c) 2002-2013 Vitesse Semiconductor Corporation "Vitesse".
-- All Rights Reserved.
--
-- ****************************************************************

VTSS-ERPS-MIB DEFINITIONS ::= BEGIN

IMPORTS
    MODULE-COMPLIANCE, OBJECT-GROUP
        FROM SNMPv2-CONF
    MODULE-IDENTITY, OBJECT-TYPE
        FROM SNMPv2-SMI
    TEXTUAL-CONVENTION
        FROM SNMPv2-TC
    vtssSwitchMgmt
        FROM VTSS-SMI
    Counter64 FROM SNMPv2-SMI
    Integer32 FROM SNMPv2-SMI
    Unsigned32 FROM SNMPv2-SMI
    TruthValue FROM SNMPv2-TC
    VTSSInterfaceIndex FROM VTSS-TC
    VTSSRowEditorState FROM VTSS-TC
    VTSSVlanListQuarter FROM VTSS-TC
    ;

vtssErpsMib MODULE-IDENTITY
    LAST-UPDATED "201407010000Z"
    ORGANIZATION
        "Vitesse Semiconductor Corporation"
    CONTACT-INFO
        "Application support <application_support@vitesse.com>"
    DESCRIPTION
        "Private MIB for Ethernet Ring Protection Switching, ERPS."
    REVISION    "201407010000Z"
    DESCRIPTION
        "Initial version"
    ::= { vtssSwitchMgmt 72 }


VTSSErpsAdminCmd ::= TEXTUAL-CONVENTION
    STATUS      current
    DESCRIPTION
        "Specifies the Administrative command."
    SYNTAX      INTEGER { manualSwitch(1), forcedSwitch(2), clear(3) }

VTSSErpsControlCmd ::= TEXTUAL-CONVENTION
    STATUS      current
    DESCRIPTION
        "Specifies a control command."
    SYNTAX      INTEGER { none(0), admCmdForcedSwitch(1), admCmdManualSwitch(2), admCmdClear(3), statisticsClear(4) }

VTSSErpsPort ::= TEXTUAL-CONVENTION
    STATUS      current
    DESCRIPTION
        "Specifies a particular logical ring port."
    SYNTAX      INTEGER { port0(1), port1(2) }

VTSSErpsPortState ::= TEXTUAL-CONVENTION
    STATUS      current
    DESCRIPTION
        "Specifies the ring port state."
    SYNTAX      INTEGER { ok(1), signalFail(2) }

VTSSErpsProtectionState ::= TEXTUAL-CONVENTION
    STATUS      current
    DESCRIPTION
        "Specifies the ring protection state."
    SYNTAX      INTEGER { none(1), idle(2), protected(3), forcedSwitch(4), manualSwitch(5), pending(6) }

VTSSErpsRequestState ::= TEXTUAL-CONVENTION
    STATUS      current
    DESCRIPTION
        "Specifies a request/state."
    SYNTAX      INTEGER { none(1), manualSwitch(2), signalFail(3), forcedSwitch(4), event(5) }

VTSSErpsRingType ::= TEXTUAL-CONVENTION
    STATUS      current
    DESCRIPTION
        "Specifies the ERPS ring type."
    SYNTAX      INTEGER { major(1), sub(2) }

VTSSErpsRplMode ::= TEXTUAL-CONVENTION
    STATUS      current
    DESCRIPTION
        "Specifies the Ring Protection Link mode. Use 'none' if port is neither
         RPL owner nor neighbour."
    SYNTAX      INTEGER { none(1), owner(2), neighbour(3) }

VTSSErpsVersion ::= TEXTUAL-CONVENTION
    STATUS      current
    DESCRIPTION
        "Specifies the ERPS protocol version."
    SYNTAX      INTEGER { version1(1), version2(2) }

vtssErpsMibObjects OBJECT IDENTIFIER
    ::= { vtssErpsMib 1 }

vtssErpsCapabilities OBJECT IDENTIFIER
    ::= { vtssErpsMibObjects 1 }

vtssErpsCapabilitiesMaxGroups OBJECT-TYPE
    SYNTAX      Unsigned32
    MAX-ACCESS  read-only
    STATUS      current
    DESCRIPTION 
        "Maximum number of configured ERPS groups."
    ::= { vtssErpsCapabilities 1 }

vtssErpsCapabilitiesMaxVlansPerGroup OBJECT-TYPE
    SYNTAX      Unsigned32
    MAX-ACCESS  read-only
    STATUS      current
    DESCRIPTION 
        "Maximum number of protected VLANS per ERPS group."
    ::= { vtssErpsCapabilities 2 }

vtssErpsConfig OBJECT IDENTIFIER
    ::= { vtssErpsMibObjects 2 }

vtssErpsConfigTable OBJECT-TYPE
    SYNTAX      SEQUENCE OF VTSSErpsConfigEntry
    MAX-ACCESS  not-accessible
    STATUS      current
    DESCRIPTION 
        "This is the ERPS group configuration table."
    ::= { vtssErpsConfig 1 }

vtssErpsConfigEntry OBJECT-TYPE
    SYNTAX      VTSSErpsConfigEntry
    MAX-ACCESS  not-accessible
    STATUS      current
    DESCRIPTION 
        "Each entry in this table represents an ERPS group."
    INDEX       { vtssErpsConfigGroupIndex }
    ::= { vtssErpsConfigTable 1 }

VTSSErpsConfigEntry ::= SEQUENCE {
    vtssErpsConfigGroupIndex    Integer32,
    vtssErpsConfigRingType      VTSSErpsRingType,
    vtssErpsConfigPort0     VTSSInterfaceIndex,
    vtssErpsConfigPort1     VTSSInterfaceIndex,
    vtssErpsConfigInterconnectMajorRingGroupIndex   Unsigned32,
    vtssErpsConfigVirtualChannel    TruthValue,
    vtssErpsConfigPort0SignalFailMepIndex   Unsigned32,
    vtssErpsConfigPort0ApsMepIndex      Unsigned32,
    vtssErpsConfigPort1SignalFailMepIndex   Unsigned32,
    vtssErpsConfigPort1ApsMepIndex      Unsigned32,
    vtssErpsConfigHoldOffTime   Unsigned32,
    vtssErpsConfigWaitToRestoreTime     Unsigned32,
    vtssErpsConfigGuardTime     Unsigned32,
    vtssErpsConfigRplMode   VTSSErpsRplMode,
    vtssErpsConfigRplPort   VTSSErpsPort,
    vtssErpsConfigRevertive     TruthValue,
    vtssErpsConfigVersion   VTSSErpsVersion,
    vtssErpsConfigTopologyChange    TruthValue,
    vtssErpsConfigProtectedVlans0Kto1K      VTSSVlanListQuarter,
    vtssErpsConfigProtectedVlans1Kto2K      VTSSVlanListQuarter,
    vtssErpsConfigProtectedVlans2Kto3K      VTSSVlanListQuarter,
    vtssErpsConfigProtectedVlans3Kto4K      VTSSVlanListQuarter,
    vtssErpsConfigAction    VTSSRowEditorState
}

vtssErpsConfigGroupIndex OBJECT-TYPE
    SYNTAX      Integer32 (0..2147483647)
    MAX-ACCESS  not-accessible
    STATUS      current
    DESCRIPTION 
        "ERPS group index number. Valid range is (1..max groups). The maximum
         group number is platform-specific and can be retrieved from the ERPS
         capabilities."
    ::= { vtssErpsConfigEntry 1 }

vtssErpsConfigRingType OBJECT-TYPE
    SYNTAX      VTSSErpsRingType
    MAX-ACCESS  read-write
    STATUS      current
    DESCRIPTION 
        "Type of ring. Can only be set once for a ring instance."
    ::= { vtssErpsConfigEntry 2 }

vtssErpsConfigPort0 OBJECT-TYPE
    SYNTAX      VTSSInterfaceIndex
    MAX-ACCESS  read-write
    STATUS      current
    DESCRIPTION 
        "ifindex of ring protection port 0. Can only be set once for a ring
         instance."
    ::= { vtssErpsConfigEntry 3 }

vtssErpsConfigPort1 OBJECT-TYPE
    SYNTAX      VTSSInterfaceIndex
    MAX-ACCESS  read-write
    STATUS      current
    DESCRIPTION 
        "ifindex of ring protection Port 1. For interconnected sub-rings this
         value must be zero. Can only be set once for a ring instance."
    ::= { vtssErpsConfigEntry 4 }

vtssErpsConfigInterconnectMajorRingGroupIndex OBJECT-TYPE
    SYNTAX      Unsigned32
    MAX-ACCESS  read-write
    STATUS      current
    DESCRIPTION 
        "For sub-ring: zero = not interconnected; > zero = index of major ring
         group. For major ring: zero = not interconnected; > zero = is
         interconnected (i.e flag-like semantics). Can only be set once for a
         ring instance."
    ::= { vtssErpsConfigEntry 5 }

vtssErpsConfigVirtualChannel OBJECT-TYPE
    SYNTAX      TruthValue
    MAX-ACCESS  read-write
    STATUS      current
    DESCRIPTION 
        "Whether to use a virtual channel. Can only be set once for a ring
         instance."
    ::= { vtssErpsConfigEntry 6 }

vtssErpsConfigPort0SignalFailMepIndex OBJECT-TYPE
    SYNTAX      Unsigned32
    MAX-ACCESS  read-write
    STATUS      current
    DESCRIPTION 
        "Index of SignalFail MEP for Port 0. Zero if not set. To clear an ERPS
         group's MEP association, set this to zero; it affects all MEP indices."
    ::= { vtssErpsConfigEntry 7 }

vtssErpsConfigPort0ApsMepIndex OBJECT-TYPE
    SYNTAX      Unsigned32
    MAX-ACCESS  read-write
    STATUS      current
    DESCRIPTION 
        "Index of APS MEP for Port 0. Zero if not set."
    ::= { vtssErpsConfigEntry 8 }

vtssErpsConfigPort1SignalFailMepIndex OBJECT-TYPE
    SYNTAX      Unsigned32
    MAX-ACCESS  read-write
    STATUS      current
    DESCRIPTION 
        "Index of SignalFail MEP for Port 1. Zero if not set. Must be zero for
         interconnected sub-rings."
    ::= { vtssErpsConfigEntry 9 }

vtssErpsConfigPort1ApsMepIndex OBJECT-TYPE
    SYNTAX      Unsigned32
    MAX-ACCESS  read-write
    STATUS      current
    DESCRIPTION 
        "Index of APS MEP for Port 1. Zero if not set. Must be zero for
         interconnected sub-rings with virtual channel."
    ::= { vtssErpsConfigEntry 10 }

vtssErpsConfigHoldOffTime OBJECT-TYPE
    SYNTAX      Unsigned32
    MAX-ACCESS  read-write
    STATUS      current
    DESCRIPTION 
        "Hold off time in ms. Value is rounded down to 100ms precision. Valid
         range is 0-10000 ms"
    ::= { vtssErpsConfigEntry 11 }

vtssErpsConfigWaitToRestoreTime OBJECT-TYPE
    SYNTAX      Unsigned32
    MAX-ACCESS  read-write
    STATUS      current
    DESCRIPTION 
        "Wait-to-Restore time in ms. Valid range is 60000-720000 ms (1-12
         minutes)."
    ::= { vtssErpsConfigEntry 12 }

vtssErpsConfigGuardTime OBJECT-TYPE
    SYNTAX      Unsigned32
    MAX-ACCESS  read-write
    STATUS      current
    DESCRIPTION 
        "Guard time in ms. Valid range is 10-2000 ms."
    ::= { vtssErpsConfigEntry 13 }

vtssErpsConfigRplMode OBJECT-TYPE
    SYNTAX      VTSSErpsRplMode
    MAX-ACCESS  read-write
    STATUS      current
    DESCRIPTION 
        "Ring Protection Link mode."
    ::= { vtssErpsConfigEntry 14 }

vtssErpsConfigRplPort OBJECT-TYPE
    SYNTAX      VTSSErpsPort
    MAX-ACCESS  read-write
    STATUS      current
    DESCRIPTION 
        "RPL port. Only valid if the ERPS group is RPL owner or neighbour."
    ::= { vtssErpsConfigEntry 15 }

vtssErpsConfigRevertive OBJECT-TYPE
    SYNTAX      TruthValue
    MAX-ACCESS  read-write
    STATUS      current
    DESCRIPTION 
        "Revertive (true) or Non-revertive (false) mode."
    ::= { vtssErpsConfigEntry 16 }

vtssErpsConfigVersion OBJECT-TYPE
    SYNTAX      VTSSErpsVersion
    MAX-ACCESS  read-write
    STATUS      current
    DESCRIPTION 
        "ERPS protocol version."
    ::= { vtssErpsConfigEntry 17 }

vtssErpsConfigTopologyChange OBJECT-TYPE
    SYNTAX      TruthValue
    MAX-ACCESS  read-write
    STATUS      current
    DESCRIPTION 
        "Whether to enable Topology Change propagation; only valid for an
         interconnected node."
    ::= { vtssErpsConfigEntry 18 }

vtssErpsConfigProtectedVlans0Kto1K OBJECT-TYPE
    SYNTAX      VTSSVlanListQuarter
    MAX-ACCESS  read-write
    STATUS      current
    DESCRIPTION 
        "First quarter of bit-array indicating whether a VLAN is protected by
         this ring instance ('1') or not ('0')."
    ::= { vtssErpsConfigEntry 19 }

vtssErpsConfigProtectedVlans1Kto2K OBJECT-TYPE
    SYNTAX      VTSSVlanListQuarter
    MAX-ACCESS  read-write
    STATUS      current
    DESCRIPTION 
        "Second quarter of bit-array indicating whether a VLAN is protected by
         this ring instance ('1') or not ('0')."
    ::= { vtssErpsConfigEntry 20 }

vtssErpsConfigProtectedVlans2Kto3K OBJECT-TYPE
    SYNTAX      VTSSVlanListQuarter
    MAX-ACCESS  read-write
    STATUS      current
    DESCRIPTION 
        "Third quarter of bit-array indicating whether a VLAN is protected by
         this ring instance ('1') or not ('0')."
    ::= { vtssErpsConfigEntry 21 }

vtssErpsConfigProtectedVlans3Kto4K OBJECT-TYPE
    SYNTAX      VTSSVlanListQuarter
    MAX-ACCESS  read-write
    STATUS      current
    DESCRIPTION 
        "Fourth quarter of bit-array indicating whether a VLAN is protected by
         this ring instance ('1') or not ('0')."
    ::= { vtssErpsConfigEntry 22 }

vtssErpsConfigAction OBJECT-TYPE
    SYNTAX      VTSSRowEditorState
    MAX-ACCESS  read-write
    STATUS      current
    DESCRIPTION 
        "Action"
    ::= { vtssErpsConfigEntry 100 }

vtssErpsConfigRowEditor OBJECT IDENTIFIER
    ::= { vtssErpsConfig 2 }

vtssErpsConfigRowEditorGroupIndex OBJECT-TYPE
    SYNTAX      Integer32 (0..2147483647)
    MAX-ACCESS  read-write
    STATUS      current
    DESCRIPTION 
        "ERPS group index number. Valid range is (1..max groups). The maximum
         group number is platform-specific and can be retrieved from the ERPS
         capabilities."
    ::= { vtssErpsConfigRowEditor 1 }

vtssErpsConfigRowEditorRingType OBJECT-TYPE
    SYNTAX      VTSSErpsRingType
    MAX-ACCESS  read-write
    STATUS      current
    DESCRIPTION 
        "Type of ring. Can only be set once for a ring instance."
    ::= { vtssErpsConfigRowEditor 2 }

vtssErpsConfigRowEditorPort0 OBJECT-TYPE
    SYNTAX      VTSSInterfaceIndex
    MAX-ACCESS  read-write
    STATUS      current
    DESCRIPTION 
        "ifindex of ring protection port 0. Can only be set once for a ring
         instance."
    ::= { vtssErpsConfigRowEditor 3 }

vtssErpsConfigRowEditorPort1 OBJECT-TYPE
    SYNTAX      VTSSInterfaceIndex
    MAX-ACCESS  read-write
    STATUS      current
    DESCRIPTION 
        "ifindex of ring protection Port 1. For interconnected sub-rings this
         value must be zero. Can only be set once for a ring instance."
    ::= { vtssErpsConfigRowEditor 4 }

vtssErpsConfigRowEditorInterconnectMajorRingGroupIndex OBJECT-TYPE
    SYNTAX      Unsigned32
    MAX-ACCESS  read-write
    STATUS      current
    DESCRIPTION 
        "For sub-ring: zero = not interconnected; > zero = index of major ring
         group. For major ring: zero = not interconnected; > zero = is
         interconnected (i.e flag-like semantics). Can only be set once for a
         ring instance."
    ::= { vtssErpsConfigRowEditor 5 }

vtssErpsConfigRowEditorVirtualChannel OBJECT-TYPE
    SYNTAX      TruthValue
    MAX-ACCESS  read-write
    STATUS      current
    DESCRIPTION 
        "Whether to use a virtual channel. Can only be set once for a ring
         instance."
    ::= { vtssErpsConfigRowEditor 6 }

vtssErpsConfigRowEditorPort0SignalFailMepIndex OBJECT-TYPE
    SYNTAX      Unsigned32
    MAX-ACCESS  read-write
    STATUS      current
    DESCRIPTION 
        "Index of SignalFail MEP for Port 0. Zero if not set. To clear an ERPS
         group's MEP association, set this to zero; it affects all MEP indices."
    ::= { vtssErpsConfigRowEditor 7 }

vtssErpsConfigRowEditorPort0ApsMepIndex OBJECT-TYPE
    SYNTAX      Unsigned32
    MAX-ACCESS  read-write
    STATUS      current
    DESCRIPTION 
        "Index of APS MEP for Port 0. Zero if not set."
    ::= { vtssErpsConfigRowEditor 8 }

vtssErpsConfigRowEditorPort1SignalFailMepIndex OBJECT-TYPE
    SYNTAX      Unsigned32
    MAX-ACCESS  read-write
    STATUS      current
    DESCRIPTION 
        "Index of SignalFail MEP for Port 1. Zero if not set. Must be zero for
         interconnected sub-rings."
    ::= { vtssErpsConfigRowEditor 9 }

vtssErpsConfigRowEditorPort1ApsMepIndex OBJECT-TYPE
    SYNTAX      Unsigned32
    MAX-ACCESS  read-write
    STATUS      current
    DESCRIPTION 
        "Index of APS MEP for Port 1. Zero if not set. Must be zero for
         interconnected sub-rings with virtual channel."
    ::= { vtssErpsConfigRowEditor 10 }

vtssErpsConfigRowEditorHoldOffTime OBJECT-TYPE
    SYNTAX      Unsigned32
    MAX-ACCESS  read-write
    STATUS      current
    DESCRIPTION 
        "Hold off time in ms. Value is rounded down to 100ms precision. Valid
         range is 0-10000 ms"
    ::= { vtssErpsConfigRowEditor 11 }

vtssErpsConfigRowEditorWaitToRestoreTime OBJECT-TYPE
    SYNTAX      Unsigned32
    MAX-ACCESS  read-write
    STATUS      current
    DESCRIPTION 
        "Wait-to-Restore time in ms. Valid range is 60000-720000 ms (1-12
         minutes)."
    ::= { vtssErpsConfigRowEditor 12 }

vtssErpsConfigRowEditorGuardTime OBJECT-TYPE
    SYNTAX      Unsigned32
    MAX-ACCESS  read-write
    STATUS      current
    DESCRIPTION 
        "Guard time in ms. Valid range is 10-2000 ms."
    ::= { vtssErpsConfigRowEditor 13 }

vtssErpsConfigRowEditorRplMode OBJECT-TYPE
    SYNTAX      VTSSErpsRplMode
    MAX-ACCESS  read-write
    STATUS      current
    DESCRIPTION 
        "Ring Protection Link mode."
    ::= { vtssErpsConfigRowEditor 14 }

vtssErpsConfigRowEditorRplPort OBJECT-TYPE
    SYNTAX      VTSSErpsPort
    MAX-ACCESS  read-write
    STATUS      current
    DESCRIPTION 
        "RPL port. Only valid if the ERPS group is RPL owner or neighbour."
    ::= { vtssErpsConfigRowEditor 15 }

vtssErpsConfigRowEditorRevertive OBJECT-TYPE
    SYNTAX      TruthValue
    MAX-ACCESS  read-write
    STATUS      current
    DESCRIPTION 
        "Revertive (true) or Non-revertive (false) mode."
    ::= { vtssErpsConfigRowEditor 16 }

vtssErpsConfigRowEditorVersion OBJECT-TYPE
    SYNTAX      VTSSErpsVersion
    MAX-ACCESS  read-write
    STATUS      current
    DESCRIPTION 
        "ERPS protocol version."
    ::= { vtssErpsConfigRowEditor 17 }

vtssErpsConfigRowEditorTopologyChange OBJECT-TYPE
    SYNTAX      TruthValue
    MAX-ACCESS  read-write
    STATUS      current
    DESCRIPTION 
        "Whether to enable Topology Change propagation; only valid for an
         interconnected node."
    ::= { vtssErpsConfigRowEditor 18 }

vtssErpsConfigRowEditorProtectedVlans0Kto1K OBJECT-TYPE
    SYNTAX      VTSSVlanListQuarter
    MAX-ACCESS  read-write
    STATUS      current
    DESCRIPTION 
        "First quarter of bit-array indicating whether a VLAN is protected by
         this ring instance ('1') or not ('0')."
    ::= { vtssErpsConfigRowEditor 19 }

vtssErpsConfigRowEditorProtectedVlans1Kto2K OBJECT-TYPE
    SYNTAX      VTSSVlanListQuarter
    MAX-ACCESS  read-write
    STATUS      current
    DESCRIPTION 
        "Second quarter of bit-array indicating whether a VLAN is protected by
         this ring instance ('1') or not ('0')."
    ::= { vtssErpsConfigRowEditor 20 }

vtssErpsConfigRowEditorProtectedVlans2Kto3K OBJECT-TYPE
    SYNTAX      VTSSVlanListQuarter
    MAX-ACCESS  read-write
    STATUS      current
    DESCRIPTION 
        "Third quarter of bit-array indicating whether a VLAN is protected by
         this ring instance ('1') or not ('0')."
    ::= { vtssErpsConfigRowEditor 21 }

vtssErpsConfigRowEditorProtectedVlans3Kto4K OBJECT-TYPE
    SYNTAX      VTSSVlanListQuarter
    MAX-ACCESS  read-write
    STATUS      current
    DESCRIPTION 
        "Fourth quarter of bit-array indicating whether a VLAN is protected by
         this ring instance ('1') or not ('0')."
    ::= { vtssErpsConfigRowEditor 22 }

vtssErpsConfigRowEditorAction OBJECT-TYPE
    SYNTAX      VTSSRowEditorState
    MAX-ACCESS  read-write
    STATUS      current
    DESCRIPTION 
        "Action"
    ::= { vtssErpsConfigRowEditor 100 }

vtssErpsStatus OBJECT IDENTIFIER
    ::= { vtssErpsMibObjects 3 }

vtssErpsStatusTable OBJECT-TYPE
    SYNTAX      SEQUENCE OF VTSSErpsStatusEntry
    MAX-ACCESS  not-accessible
    STATUS      current
    DESCRIPTION 
        "This table contains status per EPRS group."
    ::= { vtssErpsStatus 1 }

vtssErpsStatusEntry OBJECT-TYPE
    SYNTAX      VTSSErpsStatusEntry
    MAX-ACCESS  not-accessible
    STATUS      current
    DESCRIPTION 
        "Status."
    INDEX       { vtssErpsStatusGroupIndex }
    ::= { vtssErpsStatusTable 1 }

VTSSErpsStatusEntry ::= SEQUENCE {
    vtssErpsStatusGroupIndex    Integer32,
    vtssErpsStatusActive    TruthValue,
    vtssErpsStatusProtectionState   VTSSErpsProtectionState,
    vtssErpsStatusRplBlocked    TruthValue,
    vtssErpsStatusWtrRemaining      Unsigned32,
    vtssErpsStatusAdminCmd      VTSSErpsAdminCmd,
    vtssErpsStatusFopAlarm      TruthValue,
    vtssErpsStatusTxActive      TruthValue,
    vtssErpsStatusTxRequestOrState      VTSSErpsRequestState,
    vtssErpsStatusTxRplBlocked      TruthValue,
    vtssErpsStatusTxDoNotFlush      TruthValue,
    vtssErpsStatusBlockedPortReference      VTSSErpsPort,
    vtssErpsStatusPort0Blocked      TruthValue,
    vtssErpsStatusPort0State    VTSSErpsPortState,
    vtssErpsStatusPort0RxActive     TruthValue,
    vtssErpsStatusPort0RxRequestOrState     VTSSErpsRequestState,
    vtssErpsStatusPort0RxRplBlocked     TruthValue,
    vtssErpsStatusPort0RxDoNotFlush     TruthValue,
    vtssErpsStatusPort0RxBlockedPortReference   VTSSErpsPort,
    vtssErpsStatusPort0RxNodeId     OCTET STRING,
    vtssErpsStatusPort1Blocked      TruthValue,
    vtssErpsStatusPort1State    VTSSErpsPortState,
    vtssErpsStatusPort1RxActive     TruthValue,
    vtssErpsStatusPort1RxRequestOrState     VTSSErpsRequestState,
    vtssErpsStatusPort1RxRplBlocked     TruthValue,
    vtssErpsStatusPort1RxDoNotFlush     TruthValue,
    vtssErpsStatusPort1RxBlockedPortReference   VTSSErpsPort,
    vtssErpsStatusPort1RxNodeId     OCTET STRING
}

vtssErpsStatusGroupIndex OBJECT-TYPE
    SYNTAX      Integer32 (0..2147483647)
    MAX-ACCESS  not-accessible
    STATUS      current
    DESCRIPTION 
        "ERPS group index number. Valid range is (1..max groups). The maximum
         group number is platform-specific and can be retrieved from the ERPS
         capabilities."
    ::= { vtssErpsStatusEntry 1 }

vtssErpsStatusActive OBJECT-TYPE
    SYNTAX      TruthValue
    MAX-ACCESS  read-only
    STATUS      current
    DESCRIPTION 
        "Specifies whether ERPS group is currently active or not."
    ::= { vtssErpsStatusEntry 2 }

vtssErpsStatusProtectionState OBJECT-TYPE
    SYNTAX      VTSSErpsProtectionState
    MAX-ACCESS  read-only
    STATUS      current
    DESCRIPTION 
        "Specifies current ERPS group protection state."
    ::= { vtssErpsStatusEntry 3 }

vtssErpsStatusRplBlocked OBJECT-TYPE
    SYNTAX      TruthValue
    MAX-ACCESS  read-only
    STATUS      current
    DESCRIPTION 
        "Specifies whether the RPL is currently blocked or not."
    ::= { vtssErpsStatusEntry 4 }

vtssErpsStatusWtrRemaining OBJECT-TYPE
    SYNTAX      Unsigned32
    MAX-ACCESS  read-only
    STATUS      current
    DESCRIPTION 
        "Specifies the remaining wait-time before restoring ring."
    ::= { vtssErpsStatusEntry 5 }

vtssErpsStatusAdminCmd OBJECT-TYPE
    SYNTAX      VTSSErpsAdminCmd
    MAX-ACCESS  read-only
    STATUS      current
    DESCRIPTION 
        "Specifies the currently active administrative command."
    ::= { vtssErpsStatusEntry 6 }

vtssErpsStatusFopAlarm OBJECT-TYPE
    SYNTAX      TruthValue
    MAX-ACCESS  read-only
    STATUS      current
    DESCRIPTION 
        "Specifies whether the FailureOfProtocol alarm is currently active or
         not."
    ::= { vtssErpsStatusEntry 7 }

vtssErpsStatusTxActive OBJECT-TYPE
    SYNTAX      TruthValue
    MAX-ACCESS  read-only
    STATUS      current
    DESCRIPTION 
        "Specifies whether R-APS transmission is currently active."
    ::= { vtssErpsStatusEntry 8 }

vtssErpsStatusTxRequestOrState OBJECT-TYPE
    SYNTAX      VTSSErpsRequestState
    MAX-ACCESS  read-only
    STATUS      current
    DESCRIPTION 
        "Specifies the currently transmitted request/state. Only relevant when
         Tx is active."
    ::= { vtssErpsStatusEntry 9 }

vtssErpsStatusTxRplBlocked OBJECT-TYPE
    SYNTAX      TruthValue
    MAX-ACCESS  read-only
    STATUS      current
    DESCRIPTION 
        "Specifies the currently transmitted RPL Blocked flag. Only relevant
         when Tx is active."
    ::= { vtssErpsStatusEntry 10 }

vtssErpsStatusTxDoNotFlush OBJECT-TYPE
    SYNTAX      TruthValue
    MAX-ACCESS  read-only
    STATUS      current
    DESCRIPTION 
        "Specifies the currently transmitted Do Not Flush flag. Only relevant
         when Tx is active."
    ::= { vtssErpsStatusEntry 11 }

vtssErpsStatusBlockedPortReference OBJECT-TYPE
    SYNTAX      VTSSErpsPort
    MAX-ACCESS  read-only
    STATUS      current
    DESCRIPTION 
        "Specifies the currently transmitted Blocked Port Reference. Only
         relevant when Tx is active."
    ::= { vtssErpsStatusEntry 12 }

vtssErpsStatusPort0Blocked OBJECT-TYPE
    SYNTAX      TruthValue
    MAX-ACCESS  read-only
    STATUS      current
    DESCRIPTION 
        "Specifies whether ring Port 0 is blocked or not."
    ::= { vtssErpsStatusEntry 13 }

vtssErpsStatusPort0State OBJECT-TYPE
    SYNTAX      VTSSErpsPortState
    MAX-ACCESS  read-only
    STATUS      current
    DESCRIPTION 
        "Specifies the state of ring Port 0."
    ::= { vtssErpsStatusEntry 14 }

vtssErpsStatusPort0RxActive OBJECT-TYPE
    SYNTAX      TruthValue
    MAX-ACCESS  read-only
    STATUS      current
    DESCRIPTION 
        "Specifies if ring Port0 receives R-APS."
    ::= { vtssErpsStatusEntry 15 }

vtssErpsStatusPort0RxRequestOrState OBJECT-TYPE
    SYNTAX      VTSSErpsRequestState
    MAX-ACCESS  read-only
    STATUS      current
    DESCRIPTION 
        "Specifies the most recently received request/state on ring Port 0. Only
         relevant when Rx is active."
    ::= { vtssErpsStatusEntry 16 }

vtssErpsStatusPort0RxRplBlocked OBJECT-TYPE
    SYNTAX      TruthValue
    MAX-ACCESS  read-only
    STATUS      current
    DESCRIPTION 
        "Specifies the most recently received RPL Blocked flag on ring Port 0.
         Only relevant when Rx is active."
    ::= { vtssErpsStatusEntry 17 }

vtssErpsStatusPort0RxDoNotFlush OBJECT-TYPE
    SYNTAX      TruthValue
    MAX-ACCESS  read-only
    STATUS      current
    DESCRIPTION 
        "Specifies the most recently received Do Not Flush flag on ring Port 0.
         Only relevant when Rx is active."
    ::= { vtssErpsStatusEntry 18 }

vtssErpsStatusPort0RxBlockedPortReference OBJECT-TYPE
    SYNTAX      VTSSErpsPort
    MAX-ACCESS  read-only
    STATUS      current
    DESCRIPTION 
        "Specifies the most recently received Blocked Port Reference on ring
         Port 0. Only relevant when Rx is active."
    ::= { vtssErpsStatusEntry 19 }

vtssErpsStatusPort0RxNodeId OBJECT-TYPE
    SYNTAX      OCTET STRING (SIZE(6))
    MAX-ACCESS  read-only
    STATUS      current
    DESCRIPTION 
        "Specifies the most recently received node ID on ring Port 0. Only
         relevant when Rx is active."
    ::= { vtssErpsStatusEntry 20 }

vtssErpsStatusPort1Blocked OBJECT-TYPE
    SYNTAX      TruthValue
    MAX-ACCESS  read-only
    STATUS      current
    DESCRIPTION 
        "Specifies whether ring Port 1 is blocked or not."
    ::= { vtssErpsStatusEntry 21 }

vtssErpsStatusPort1State OBJECT-TYPE
    SYNTAX      VTSSErpsPortState
    MAX-ACCESS  read-only
    STATUS      current
    DESCRIPTION 
        "Specifies the state of ring Port 1."
    ::= { vtssErpsStatusEntry 22 }

vtssErpsStatusPort1RxActive OBJECT-TYPE
    SYNTAX      TruthValue
    MAX-ACCESS  read-only
    STATUS      current
    DESCRIPTION 
        "Specifies if ring Port1 receives R-APS."
    ::= { vtssErpsStatusEntry 23 }

vtssErpsStatusPort1RxRequestOrState OBJECT-TYPE
    SYNTAX      VTSSErpsRequestState
    MAX-ACCESS  read-only
    STATUS      current
    DESCRIPTION 
        "Specifies the most recently received request/state on ring Port 1. Only
         relevant when Rx is active."
    ::= { vtssErpsStatusEntry 24 }

vtssErpsStatusPort1RxRplBlocked OBJECT-TYPE
    SYNTAX      TruthValue
    MAX-ACCESS  read-only
    STATUS      current
    DESCRIPTION 
        "Specifies the most recently received RPL Blocked flag on ring Port 1.
         Only relevant when Rx is active."
    ::= { vtssErpsStatusEntry 25 }

vtssErpsStatusPort1RxDoNotFlush OBJECT-TYPE
    SYNTAX      TruthValue
    MAX-ACCESS  read-only
    STATUS      current
    DESCRIPTION 
        "Specifies the most recently received Do Not Flush flag on ring Port 1.
         Only relevant when Rx is active."
    ::= { vtssErpsStatusEntry 26 }

vtssErpsStatusPort1RxBlockedPortReference OBJECT-TYPE
    SYNTAX      VTSSErpsPort
    MAX-ACCESS  read-only
    STATUS      current
    DESCRIPTION 
        "Specifies the most recently received Blocked Port Reference on ring
         Port 1. Only relevant when Rx is active."
    ::= { vtssErpsStatusEntry 27 }

vtssErpsStatusPort1RxNodeId OBJECT-TYPE
    SYNTAX      OCTET STRING (SIZE(6))
    MAX-ACCESS  read-only
    STATUS      current
    DESCRIPTION 
        "Specifies the most recently received node ID on ring Port 1. Only
         relevant when Rx is active."
    ::= { vtssErpsStatusEntry 28 }

vtssErpsControl OBJECT IDENTIFIER
    ::= { vtssErpsMibObjects 4 }

vtssErpsControlTable OBJECT-TYPE
    SYNTAX      SEQUENCE OF VTSSErpsControlEntry
    MAX-ACCESS  not-accessible
    STATUS      current
    DESCRIPTION 
        "This is the ERPS group control table."
    ::= { vtssErpsControl 1 }

vtssErpsControlEntry OBJECT-TYPE
    SYNTAX      VTSSErpsControlEntry
    MAX-ACCESS  not-accessible
    STATUS      current
    DESCRIPTION 
        "Each entry in this table represents dynamic control elements an ERPS
         group."
    INDEX       { vtssErpsControlGroupIndex }
    ::= { vtssErpsControlTable 1 }

VTSSErpsControlEntry ::= SEQUENCE {
    vtssErpsControlGroupIndex   Integer32,
    vtssErpsControlCommand      VTSSErpsControlCmd,
    vtssErpsControlPort     VTSSErpsPort
}

vtssErpsControlGroupIndex OBJECT-TYPE
    SYNTAX      Integer32 (0..2147483647)
    MAX-ACCESS  not-accessible
    STATUS      current
    DESCRIPTION 
        "ERPS group index number. Valid range is (1..max groups). The maximum
         group number is platform-specific and can be retrieved from the ERPS
         capabilities."
    ::= { vtssErpsControlEntry 1 }

vtssErpsControlCommand OBJECT-TYPE
    SYNTAX      VTSSErpsControlCmd
    MAX-ACCESS  read-write
    STATUS      current
    DESCRIPTION 
        "Control command to execute. Always returns none when read."
    ::= { vtssErpsControlEntry 2 }

vtssErpsControlPort OBJECT-TYPE
    SYNTAX      VTSSErpsPort
    MAX-ACCESS  read-write
    STATUS      current
    DESCRIPTION 
        "Ring port affected by control command. Only relevant for administrative
         commands. Always returns port0 when read."
    ::= { vtssErpsControlEntry 3 }

vtssErpsStatistics OBJECT IDENTIFIER
    ::= { vtssErpsMibObjects 5 }

vtssErpsStatisticsTable OBJECT-TYPE
    SYNTAX      SEQUENCE OF VTSSErpsStatisticsEntry
    MAX-ACCESS  not-accessible
    STATUS      current
    DESCRIPTION 
        "This table contains statistics per EPRS group."
    ::= { vtssErpsStatistics 1 }

vtssErpsStatisticsEntry OBJECT-TYPE
    SYNTAX      VTSSErpsStatisticsEntry
    MAX-ACCESS  not-accessible
    STATUS      current
    DESCRIPTION 
        "Various PDU and event counters."
    INDEX       { vtssErpsStatisticsGroupIndex }
    ::= { vtssErpsStatisticsTable 1 }

VTSSErpsStatisticsEntry ::= SEQUENCE {
    vtssErpsStatisticsGroupIndex    Integer32,
    vtssErpsStatisticsRapsTx    Counter64,
    vtssErpsStatisticsRapsRx    Counter64,
    vtssErpsStatisticsRapsRxDrop    Counter64,
    vtssErpsStatisticsLocalSF   Counter64,
    vtssErpsStatisticsLocalSFCleared    Counter64,
    vtssErpsStatisticsRemoteSF      Counter64,
    vtssErpsStatisticsNR    Counter64,
    vtssErpsStatisticsRemoteMS      Counter64,
    vtssErpsStatisticsLocalMS   Counter64,
    vtssErpsStatisticsRemoteFS      Counter64,
    vtssErpsStatisticsLocalFS   Counter64,
    vtssErpsStatisticsAdminClear    Counter64
}

vtssErpsStatisticsGroupIndex OBJECT-TYPE
    SYNTAX      Integer32 (0..2147483647)
    MAX-ACCESS  not-accessible
    STATUS      current
    DESCRIPTION 
        "ERPS group index number. Valid range is (1..max groups). The maximum
         group number is platform-specific and can be retrieved from the ERPS
         capabilities."
    ::= { vtssErpsStatisticsEntry 1 }

vtssErpsStatisticsRapsTx OBJECT-TYPE
    SYNTAX      Counter64
    MAX-ACCESS  read-only
    STATUS      current
    DESCRIPTION 
        "Number of transmitted RAPS PDUs."
    ::= { vtssErpsStatisticsEntry 2 }

vtssErpsStatisticsRapsRx OBJECT-TYPE
    SYNTAX      Counter64
    MAX-ACCESS  read-only
    STATUS      current
    DESCRIPTION 
        "Number of received RAPS PDUs."
    ::= { vtssErpsStatisticsEntry 3 }

vtssErpsStatisticsRapsRxDrop OBJECT-TYPE
    SYNTAX      Counter64
    MAX-ACCESS  read-only
    STATUS      current
    DESCRIPTION 
        "Number of received RAPS PDUs that were dropped."
    ::= { vtssErpsStatisticsEntry 4 }

vtssErpsStatisticsLocalSF OBJECT-TYPE
    SYNTAX      Counter64
    MAX-ACCESS  read-only
    STATUS      current
    DESCRIPTION 
        "Number of local SignalFail events."
    ::= { vtssErpsStatisticsEntry 5 }

vtssErpsStatisticsLocalSFCleared OBJECT-TYPE
    SYNTAX      Counter64
    MAX-ACCESS  read-only
    STATUS      current
    DESCRIPTION 
        "Number of local SignalFail clear events."
    ::= { vtssErpsStatisticsEntry 6 }

vtssErpsStatisticsRemoteSF OBJECT-TYPE
    SYNTAX      Counter64
    MAX-ACCESS  read-only
    STATUS      current
    DESCRIPTION 
        "Number of remote SignalFail events."
    ::= { vtssErpsStatisticsEntry 7 }

vtssErpsStatisticsNR OBJECT-TYPE
    SYNTAX      Counter64
    MAX-ACCESS  read-only
    STATUS      current
    DESCRIPTION 
        "Number of NoRequest events."
    ::= { vtssErpsStatisticsEntry 8 }

vtssErpsStatisticsRemoteMS OBJECT-TYPE
    SYNTAX      Counter64
    MAX-ACCESS  read-only
    STATUS      current
    DESCRIPTION 
        "Number of remote ManualSwitch events."
    ::= { vtssErpsStatisticsEntry 9 }

vtssErpsStatisticsLocalMS OBJECT-TYPE
    SYNTAX      Counter64
    MAX-ACCESS  read-only
    STATUS      current
    DESCRIPTION 
        "Number of local ManualSwitch events."
    ::= { vtssErpsStatisticsEntry 10 }

vtssErpsStatisticsRemoteFS OBJECT-TYPE
    SYNTAX      Counter64
    MAX-ACCESS  read-only
    STATUS      current
    DESCRIPTION 
        "Number of remote ForcedSwitch events."
    ::= { vtssErpsStatisticsEntry 11 }

vtssErpsStatisticsLocalFS OBJECT-TYPE
    SYNTAX      Counter64
    MAX-ACCESS  read-only
    STATUS      current
    DESCRIPTION 
        "Number of local ForcedSwitch events."
    ::= { vtssErpsStatisticsEntry 12 }

vtssErpsStatisticsAdminClear OBJECT-TYPE
    SYNTAX      Counter64
    MAX-ACCESS  read-only
    STATUS      current
    DESCRIPTION 
        "Number of AdminClear events."
    ::= { vtssErpsStatisticsEntry 13 }

vtssErpsMibConformance OBJECT IDENTIFIER
    ::= { vtssErpsMib 2 }

vtssErpsMibCompliances OBJECT IDENTIFIER
    ::= { vtssErpsMibConformance 1 }

vtssErpsMibGroups OBJECT IDENTIFIER
    ::= { vtssErpsMibConformance 2 }

vtssErpsCapabilitiesInfoGroup OBJECT-GROUP
    OBJECTS     { vtssErpsCapabilitiesMaxGroups, 
                  vtssErpsCapabilitiesMaxVlansPerGroup }
    STATUS      current
    DESCRIPTION
        "A collection of objects suitable for bulk operations."
    ::= { vtssErpsMibGroups 1 }

vtssErpsConfigTableInfoGroup OBJECT-GROUP
    OBJECTS     { vtssErpsConfigRingType, vtssErpsConfigPort0, vtssErpsConfigPort1, 
                  vtssErpsConfigInterconnectMajorRingGroupIndex, 
                  vtssErpsConfigVirtualChannel, 
                  vtssErpsConfigPort0SignalFailMepIndex, 
                  vtssErpsConfigPort0ApsMepIndex, 
                  vtssErpsConfigPort1SignalFailMepIndex, 
                  vtssErpsConfigPort1ApsMepIndex, vtssErpsConfigHoldOffTime, 
                  vtssErpsConfigWaitToRestoreTime, vtssErpsConfigGuardTime, 
                  vtssErpsConfigRplMode, vtssErpsConfigRplPort, 
                  vtssErpsConfigRevertive, vtssErpsConfigVersion, 
                  vtssErpsConfigTopologyChange, 
                  vtssErpsConfigProtectedVlans0Kto1K, 
                  vtssErpsConfigProtectedVlans1Kto2K, 
                  vtssErpsConfigProtectedVlans2Kto3K, 
                  vtssErpsConfigProtectedVlans3Kto4K, vtssErpsConfigAction }
    STATUS      current
    DESCRIPTION
        "A collection of objects suitable for bulk operations."
    ::= { vtssErpsMibGroups 2 }

vtssErpsConfigRowEditorInfoGroup OBJECT-GROUP
    OBJECTS     { vtssErpsConfigRowEditorGroupIndex, 
                  vtssErpsConfigRowEditorRingType, vtssErpsConfigRowEditorPort0, 
                  vtssErpsConfigRowEditorPort1, 
                  vtssErpsConfigRowEditorInterconnectMajorRingGroupIndex, 
                  vtssErpsConfigRowEditorVirtualChannel, 
                  vtssErpsConfigRowEditorPort0SignalFailMepIndex, 
                  vtssErpsConfigRowEditorPort0ApsMepIndex, 
                  vtssErpsConfigRowEditorPort1SignalFailMepIndex, 
                  vtssErpsConfigRowEditorPort1ApsMepIndex, 
                  vtssErpsConfigRowEditorHoldOffTime, 
                  vtssErpsConfigRowEditorWaitToRestoreTime, 
                  vtssErpsConfigRowEditorGuardTime, 
                  vtssErpsConfigRowEditorRplMode, vtssErpsConfigRowEditorRplPort, 
                  vtssErpsConfigRowEditorRevertive, 
                  vtssErpsConfigRowEditorVersion, 
                  vtssErpsConfigRowEditorTopologyChange, 
                  vtssErpsConfigRowEditorProtectedVlans0Kto1K, 
                  vtssErpsConfigRowEditorProtectedVlans1Kto2K, 
                  vtssErpsConfigRowEditorProtectedVlans2Kto3K, 
                  vtssErpsConfigRowEditorProtectedVlans3Kto4K, 
                  vtssErpsConfigRowEditorAction }
    STATUS      current
    DESCRIPTION
        "A collection of objects suitable for bulk operations."
    ::= { vtssErpsMibGroups 3 }

vtssErpsStatusTableInfoGroup OBJECT-GROUP
    OBJECTS     { vtssErpsStatusActive, vtssErpsStatusProtectionState, 
                  vtssErpsStatusRplBlocked, vtssErpsStatusWtrRemaining, 
                  vtssErpsStatusAdminCmd, vtssErpsStatusFopAlarm, 
                  vtssErpsStatusTxActive, vtssErpsStatusTxRequestOrState, 
                  vtssErpsStatusTxRplBlocked, vtssErpsStatusTxDoNotFlush, 
                  vtssErpsStatusBlockedPortReference, vtssErpsStatusPort0Blocked, 
                  vtssErpsStatusPort0State, vtssErpsStatusPort0RxActive, 
                  vtssErpsStatusPort0RxRequestOrState, 
                  vtssErpsStatusPort0RxRplBlocked, 
                  vtssErpsStatusPort0RxDoNotFlush, 
                  vtssErpsStatusPort0RxBlockedPortReference, 
                  vtssErpsStatusPort0RxNodeId, vtssErpsStatusPort1Blocked, 
                  vtssErpsStatusPort1State, vtssErpsStatusPort1RxActive, 
                  vtssErpsStatusPort1RxRequestOrState, 
                  vtssErpsStatusPort1RxRplBlocked, 
                  vtssErpsStatusPort1RxDoNotFlush, 
                  vtssErpsStatusPort1RxBlockedPortReference, 
                  vtssErpsStatusPort1RxNodeId }
    STATUS      current
    DESCRIPTION
        "A collection of objects suitable for bulk operations."
    ::= { vtssErpsMibGroups 4 }

vtssErpsControlTableInfoGroup OBJECT-GROUP
    OBJECTS     { vtssErpsControlCommand, vtssErpsControlPort }
    STATUS      current
    DESCRIPTION
        "A collection of objects suitable for bulk operations."
    ::= { vtssErpsMibGroups 5 }

vtssErpsStatisticsTableInfoGroup OBJECT-GROUP
    OBJECTS     { vtssErpsStatisticsRapsTx, vtssErpsStatisticsRapsRx, 
                  vtssErpsStatisticsRapsRxDrop, vtssErpsStatisticsLocalSF, 
                  vtssErpsStatisticsLocalSFCleared, vtssErpsStatisticsRemoteSF, 
                  vtssErpsStatisticsNR, vtssErpsStatisticsRemoteMS, 
                  vtssErpsStatisticsLocalMS, vtssErpsStatisticsRemoteFS, 
                  vtssErpsStatisticsLocalFS, vtssErpsStatisticsAdminClear }
    STATUS      current
    DESCRIPTION
        "A collection of objects suitable for bulk operations."
    ::= { vtssErpsMibGroups 6 }

vtssErpsMibCompliance MODULE-COMPLIANCE
    STATUS      current
    DESCRIPTION
        "The compliance statement for the implementation."

    MODULE      -- this module

        MANDATORY-GROUPS        { vtssErpsCapabilitiesInfoGroup, 
                  vtssErpsConfigTableInfoGroup, vtssErpsConfigRowEditorInfoGroup, 
                  vtssErpsStatusTableInfoGroup, vtssErpsControlTableInfoGroup, 
                  vtssErpsStatisticsTableInfoGroup }

    ::= { vtssErpsMibCompliances 1 }

END
