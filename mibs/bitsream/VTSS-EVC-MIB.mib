-- *****************************************************************
-- EVC-MIB:  Vitesse private MIB
--
-- Copyright (c) 2002-2013 Vitesse Semiconductor Corporation "Vitesse".
-- All Rights Reserved.
--
-- ****************************************************************

VTSS-EVC-MIB DEFINITIONS ::= BEGIN

IMPORTS
    MODULE-COMPLIANCE, OBJECT-GROUP
        FROM SNMPv2-CONF
    MODULE-IDENTITY, OBJECT-TYPE
        FROM SNMPv2-SMI
    TEXTUAL-CONVENTION
        FROM SNMPv2-TC
    vtssSwitchMgmt
        FROM VTSS-SMI
    InetAddressIPv6 FROM INET-ADDRESS-MIB
    Counter64 FROM SNMPv2-SMI
    Integer32 FROM SNMPv2-SMI
    IpAddress FROM SNMPv2-SMI
    Unsigned32 FROM SNMPv2-SMI
    MacAddress FROM SNMPv2-TC
    TruthValue FROM SNMPv2-TC
    VTSSBitType FROM VTSS-TC
    VTSSDestMacType FROM VTSS-TC
    VTSSInterfaceIndex FROM VTSS-TC
    VTSSPortList FROM VTSS-TC
    VTSSRowEditorState FROM VTSS-TC
    VTSSUnsigned16 FROM VTSS-TC
    VTSSUnsigned8 FROM VTSS-TC
    VTSSVcapKeyType FROM VTSS-TC
    VTSSVlanTagPriority FROM VTSS-TC
    VTSSVlanTagType FROM VTSS-TC
    ;

vtssEvcMib MODULE-IDENTITY
    LAST-UPDATED "201410300000Z"
    ORGANIZATION
        "Vitesse Semiconductor Corporation"
    CONTACT-INFO
        "Application support <application_support@vitesse.com>"
    DESCRIPTION
        "This is a private MIB for EVC"
    REVISION    "201410300000Z"
    DESCRIPTION
        "Added E-Tree support."
    REVISION    "201408130000Z"
    DESCRIPTION
        "Added MPLS PW table."
    REVISION    "201407290000Z"
    DESCRIPTION
        "Updated descriptions when referring to a capability."
    REVISION    "201407010000Z"
    DESCRIPTION
        "Initial version"
    ::= { vtssSwitchMgmt 62 }


VTSSevcDeiMode ::= TEXTUAL-CONVENTION
    STATUS      current
    DESCRIPTION
        "The ECE DEI mode."
    SYNTAX      INTEGER { classified(0), fixed(1), dp(2) }

VTSSevcDirection ::= TEXTUAL-CONVENTION
    STATUS      current
    DESCRIPTION
        "The ECE direction."
    SYNTAX      INTEGER { both(0), uniToNni(1), nniToUni(2) }

VTSSevcEceL2cpMode ::= TEXTUAL-CONVENTION
    STATUS      current
    DESCRIPTION
        "The ECE L2CP forward mode."
    SYNTAX      INTEGER { forward(0), discard(1), peer(2), tunnel(3) }

VTSSevcFrameType ::= TEXTUAL-CONVENTION
    STATUS      current
    DESCRIPTION
        "The ECE frame type."
    SYNTAX      INTEGER { any(0), etype(1), llc(2), snap(3), l2cp(4), ipv4(5), ipv6(6) }

VTSSevcInnerTagType ::= TEXTUAL-CONVENTION
    STATUS      current
    DESCRIPTION
        "The inner tag type."
    SYNTAX      INTEGER { none(0), cTagged(1), sTagged(2), sCustomTagged(3) }

VTSSevcL2cpDmac ::= TEXTUAL-CONVENTION
    STATUS      current
    DESCRIPTION
        "The ECE DMAC used for L2CP tunneling."
    SYNTAX      INTEGER { custom(0), cisco(1) }

VTSSevcL2cpMode ::= TEXTUAL-CONVENTION
    STATUS      current
    DESCRIPTION
        "The EVC port L2CP mode."
    SYNTAX      INTEGER { forward(0), discard(1), peer(2) }

VTSSevcL2cpType ::= TEXTUAL-CONVENTION
    STATUS      current
    DESCRIPTION
        "The L2CP type."
    SYNTAX      INTEGER { none(0), stp(1), pause(2), lacp(3), lamp(4), loam(5), dot1x(6), elmi(7), pb(8), pbGvrp(9), lldp(10), gmrp(11), gvrp(12), uld(13), pagp(14), pvst(15), ciscoVlan(16), cdp(17), vtp(18), dtp(19), ciscoStp(20), ciscoCfm(21) }

VTSSevcPcpMode ::= TEXTUAL-CONVENTION
    STATUS      current
    DESCRIPTION
        "The ECE PCP mode."
    SYNTAX      INTEGER { classified(0), fixed(1), mapped(2) }

VTSSevcPolicerMode ::= TEXTUAL-CONVENTION
    STATUS      current
    DESCRIPTION
        "The EVC policer mode."
    SYNTAX      INTEGER { coupled(0), aware(1), blind(2) }

VTSSevcPolicerOp ::= TEXTUAL-CONVENTION
    STATUS      current
    DESCRIPTION
        "The policer operator."
    SYNTAX      INTEGER { normal(0), none(1), discard(2), evc(3) }

VTSSevcPolicerType ::= TEXTUAL-CONVENTION
    STATUS      current
    DESCRIPTION
        "The EVC policer type."
    SYNTAX      INTEGER { mef(0), single(1) }

VTSSevcPopTag ::= TEXTUAL-CONVENTION
    STATUS      current
    DESCRIPTION
        "The number of tags popped."
    SYNTAX      INTEGER { zero(0), one(1), two(2) }

VTSSevcRuleType ::= TEXTUAL-CONVENTION
    STATUS      current
    DESCRIPTION
        "The ECE rule type."
    SYNTAX      INTEGER { both(0), rx(1), tx(2) }

VTSSevcTxLookup ::= TEXTUAL-CONVENTION
    STATUS      current
    DESCRIPTION
        "The ECE egress lookup key type."
    SYNTAX      INTEGER { vid(0), vidPcp(1), isdx(2) }

vtssEvcMibObjects OBJECT IDENTIFIER
    ::= { vtssEvcMib 1 }

vtssEvcCapabilities OBJECT IDENTIFIER
    ::= { vtssEvcMibObjects 1 }

vtssEvcCapabilitiesPolicerMax OBJECT-TYPE
    SYNTAX      Unsigned32
    MAX-ACCESS  read-only
    STATUS      current
    DESCRIPTION 
        "Maximum number of EVC policers."
    ::= { vtssEvcCapabilities 1 }

vtssEvcCapabilitiesEvcMax OBJECT-TYPE
    SYNTAX      Unsigned32
    MAX-ACCESS  read-only
    STATUS      current
    DESCRIPTION 
        "Maximum number of EVC rules."
    ::= { vtssEvcCapabilities 2 }

vtssEvcCapabilitiesEceMax OBJECT-TYPE
    SYNTAX      Unsigned32
    MAX-ACCESS  read-only
    STATUS      current
    DESCRIPTION 
        "Maximum number of ECE rules."
    ::= { vtssEvcCapabilities 3 }

vtssEvcCapabilitiesHasPortDeiColoring OBJECT-TYPE
    SYNTAX      TruthValue
    MAX-ACCESS  read-only
    STATUS      current
    DESCRIPTION 
        "If true, the platform supports NNI port DEI coloring."
    ::= { vtssEvcCapabilities 100 }

vtssEvcCapabilitiesHasPortInnerTag OBJECT-TYPE
    SYNTAX      TruthValue
    MAX-ACCESS  read-only
    STATUS      current
    DESCRIPTION 
        "If true, the platform supports NNI port inner tag classification."
    ::= { vtssEvcCapabilities 101 }

vtssEvcCapabilitiesHasPortAddrMode OBJECT-TYPE
    SYNTAX      TruthValue
    MAX-ACCESS  read-only
    STATUS      current
    DESCRIPTION 
        "If true, the platform supports port address mode (SMAC/SIP or
         DMAC/DIP)."
    ::= { vtssEvcCapabilities 102 }

vtssEvcCapabilitiesHasPortKey OBJECT-TYPE
    SYNTAX      TruthValue
    MAX-ACCESS  read-only
    STATUS      current
    DESCRIPTION 
        "If true, the platform supports port key type."
    ::= { vtssEvcCapabilities 103 }

vtssEvcCapabilitiesHasPolicerColorBlind OBJECT-TYPE
    SYNTAX      TruthValue
    MAX-ACCESS  read-only
    STATUS      current
    DESCRIPTION 
        "If true, the platform supports color-blind policing."
    ::= { vtssEvcCapabilities 200 }

vtssEvcCapabilitiesHasEvcPolicer OBJECT-TYPE
    SYNTAX      TruthValue
    MAX-ACCESS  read-only
    STATUS      current
    DESCRIPTION 
        "If true, the platform supports EVC policer mapping."
    ::= { vtssEvcCapabilities 300 }

vtssEvcCapabilitiesHasEvcUniVid OBJECT-TYPE
    SYNTAX      TruthValue
    MAX-ACCESS  read-only
    STATUS      current
    DESCRIPTION 
        "If true, the platform supports EVC UNI VLAN ID."
    ::= { vtssEvcCapabilities 301 }

vtssEvcCapabilitiesHasEvcItAdd OBJECT-TYPE
    SYNTAX      TruthValue
    MAX-ACCESS  read-only
    STATUS      current
    DESCRIPTION 
        "If true, the platform supports EVC inner tag adding."
    ::= { vtssEvcCapabilities 302 }

vtssEvcCapabilitiesHasEvcMpls OBJECT-TYPE
    SYNTAX      TruthValue
    MAX-ACCESS  read-only
    STATUS      current
    DESCRIPTION 
        "If true, the platform supports EVC MPLS."
    ::= { vtssEvcCapabilities 303 }

vtssEvcCapabilitiesHasEvcETree OBJECT-TYPE
    SYNTAX      TruthValue
    MAX-ACCESS  read-only
    STATUS      current
    DESCRIPTION 
        "If true, the platform supports E-Tree."
    ::= { vtssEvcCapabilities 304 }

vtssEvcCapabilitiesHasEceAdvLookup OBJECT-TYPE
    SYNTAX      TruthValue
    MAX-ACCESS  read-only
    STATUS      current
    DESCRIPTION 
        "If true, the platform supports ECE advanced lookup."
    ::= { vtssEvcCapabilities 400 }

vtssEvcCapabilitiesHasEceDestMacType OBJECT-TYPE
    SYNTAX      TruthValue
    MAX-ACCESS  read-only
    STATUS      current
    DESCRIPTION 
        "If true, the platform supports ECE DMAC type matching."
    ::= { vtssEvcCapabilities 401 }

vtssEvcCapabilitiesHasEceDestMac OBJECT-TYPE
    SYNTAX      TruthValue
    MAX-ACCESS  read-only
    STATUS      current
    DESCRIPTION 
        "If true, the platform supports ECE DMAC matching."
    ::= { vtssEvcCapabilities 402 }

vtssEvcCapabilitiesHasEceSrcMac OBJECT-TYPE
    SYNTAX      TruthValue
    MAX-ACCESS  read-only
    STATUS      current
    DESCRIPTION 
        "If true, the platform supports ECE SMAC matching."
    ::= { vtssEvcCapabilities 403 }

vtssEvcCapabilitiesHasEceInnerTag OBJECT-TYPE
    SYNTAX      TruthValue
    MAX-ACCESS  read-only
    STATUS      current
    DESCRIPTION 
        "If true, the platform supports ECE inner tag matching."
    ::= { vtssEvcCapabilities 404 }

vtssEvcCapabilitiesHasEceEtype OBJECT-TYPE
    SYNTAX      TruthValue
    MAX-ACCESS  read-only
    STATUS      current
    DESCRIPTION 
        "If true, the platform supports ECE Ethernet Type frame matching."
    ::= { vtssEvcCapabilities 405 }

vtssEvcCapabilitiesHasEceLlc OBJECT-TYPE
    SYNTAX      TruthValue
    MAX-ACCESS  read-only
    STATUS      current
    DESCRIPTION 
        "If true, the platform supports ECE LLC frame matching."
    ::= { vtssEvcCapabilities 406 }

vtssEvcCapabilitiesHasEceSnap OBJECT-TYPE
    SYNTAX      TruthValue
    MAX-ACCESS  read-only
    STATUS      current
    DESCRIPTION 
        "If true, the platform supports ECE SNAP frame matching."
    ::= { vtssEvcCapabilities 407 }

vtssEvcCapabilitiesHasEceL2cp OBJECT-TYPE
    SYNTAX      TruthValue
    MAX-ACCESS  read-only
    STATUS      current
    DESCRIPTION 
        "If true, the platform supports ECE LLC frame matching and forwarding."
    ::= { vtssEvcCapabilities 408 }

vtssEvcCapabilitiesHasEceIpv4Fragment OBJECT-TYPE
    SYNTAX      TruthValue
    MAX-ACCESS  read-only
    STATUS      current
    DESCRIPTION 
        "If true, the platform supports ECE IPv4 fragment matching."
    ::= { vtssEvcCapabilities 409 }

vtssEvcCapabilitiesHasEceIpProto OBJECT-TYPE
    SYNTAX      TruthValue
    MAX-ACCESS  read-only
    STATUS      current
    DESCRIPTION 
        "If true, the platform supports ECE IP protocol matching."
    ::= { vtssEvcCapabilities 410 }

vtssEvcCapabilitiesHasEceSrcIp OBJECT-TYPE
    SYNTAX      TruthValue
    MAX-ACCESS  read-only
    STATUS      current
    DESCRIPTION 
        "If true, the platform supports ECE source IP address matching."
    ::= { vtssEvcCapabilities 411 }

vtssEvcCapabilitiesHasEceDestIp OBJECT-TYPE
    SYNTAX      TruthValue
    MAX-ACCESS  read-only
    STATUS      current
    DESCRIPTION 
        "If true, the platform supports ECE destination IP address matching."
    ::= { vtssEvcCapabilities 412 }

vtssEvcCapabilitiesHasEceSrcPort OBJECT-TYPE
    SYNTAX      TruthValue
    MAX-ACCESS  read-only
    STATUS      current
    DESCRIPTION 
        "If true, the platform supports ECE source UDP/TCP port matching."
    ::= { vtssEvcCapabilities 413 }

vtssEvcCapabilitiesHasEceDestPort OBJECT-TYPE
    SYNTAX      TruthValue
    MAX-ACCESS  read-only
    STATUS      current
    DESCRIPTION 
        "If true, the platform supports ECE destination UDP/TCP port matching."
    ::= { vtssEvcCapabilities 414 }

vtssEvcCapabilitiesHasEceRuleType OBJECT-TYPE
    SYNTAX      TruthValue
    MAX-ACCESS  read-only
    STATUS      current
    DESCRIPTION 
        "If true, the platform supports ECE rule type."
    ::= { vtssEvcCapabilities 415 }

vtssEvcCapabilitiesHasEceTxLookup OBJECT-TYPE
    SYNTAX      TruthValue
    MAX-ACCESS  read-only
    STATUS      current
    DESCRIPTION 
        "If true, the platform supports ECE egress lookup type."
    ::= { vtssEvcCapabilities 416 }

vtssEvcCapabilitiesHasEceOtAddVid OBJECT-TYPE
    SYNTAX      TruthValue
    MAX-ACCESS  read-only
    STATUS      current
    DESCRIPTION 
        "If true, the platform supports ECE outer tag VID."
    ::= { vtssEvcCapabilities 417 }

vtssEvcCapabilitiesHasEcePcpMode OBJECT-TYPE
    SYNTAX      TruthValue
    MAX-ACCESS  read-only
    STATUS      current
    DESCRIPTION 
        "If true, the platform supports ECE PCP mode."
    ::= { vtssEvcCapabilities 418 }

vtssEvcCapabilitiesHasEcePcpDeiPreserve OBJECT-TYPE
    SYNTAX      TruthValue
    MAX-ACCESS  read-only
    STATUS      current
    DESCRIPTION 
        "If true, the platform supports ECE PCP/DEI preservation."
    ::= { vtssEvcCapabilities 419 }

vtssEvcCapabilitiesHasEceDeiMode OBJECT-TYPE
    SYNTAX      TruthValue
    MAX-ACCESS  read-only
    STATUS      current
    DESCRIPTION 
        "If true, the platform supports ECE DEI mode."
    ::= { vtssEvcCapabilities 420 }

vtssEvcCapabilitiesHasEceItAdd OBJECT-TYPE
    SYNTAX      TruthValue
    MAX-ACCESS  read-only
    STATUS      current
    DESCRIPTION 
        "If true, the platform supports ECE inner tag adding."
    ::= { vtssEvcCapabilities 421 }

vtssEvcCapabilitiesHasEcePolicer OBJECT-TYPE
    SYNTAX      TruthValue
    MAX-ACCESS  read-only
    STATUS      current
    DESCRIPTION 
        "If true, the platform supports ECE policer mapping."
    ::= { vtssEvcCapabilities 422 }

vtssEvcCapabilitiesHasEceCos OBJECT-TYPE
    SYNTAX      TruthValue
    MAX-ACCESS  read-only
    STATUS      current
    DESCRIPTION 
        "If true, the platform supports ECE CoS mapping."
    ::= { vtssEvcCapabilities 423 }

vtssEvcCapabilitiesHasEceDp OBJECT-TYPE
    SYNTAX      TruthValue
    MAX-ACCESS  read-only
    STATUS      current
    DESCRIPTION 
        "If true, the platform supports ECE Drop Precedence mapping."
    ::= { vtssEvcCapabilities 424 }

vtssEvcCapabilitiesHasEvcPortHqos OBJECT-TYPE
    SYNTAX      TruthValue
    MAX-ACCESS  read-only
    STATUS      current
    DESCRIPTION 
        "If true, the platform supports (EVC, port) HQoS ID mapping."
    ::= { vtssEvcCapabilities 500 }

vtssEvcCapabilitiesHasEvcPortCounters OBJECT-TYPE
    SYNTAX      TruthValue
    MAX-ACCESS  read-only
    STATUS      current
    DESCRIPTION 
        "If true, the platform supports (EVC, port) counters."
    ::= { vtssEvcCapabilities 501 }

vtssEvcConfig OBJECT IDENTIFIER
    ::= { vtssEvcMibObjects 2 }

vtssEvcConfigInterface OBJECT IDENTIFIER
    ::= { vtssEvcConfig 2 }

vtssEvcConfigInterfaceTable OBJECT-TYPE
    SYNTAX      SEQUENCE OF VTSSEvcConfigInterfaceEntry
    MAX-ACCESS  not-accessible
    STATUS      current
    DESCRIPTION 
        "This table provides EVC configuration for interfaces"
    ::= { vtssEvcConfigInterface 1 }

vtssEvcConfigInterfaceEntry OBJECT-TYPE
    SYNTAX      VTSSEvcConfigInterfaceEntry
    MAX-ACCESS  not-accessible
    STATUS      current
    DESCRIPTION 
        "Each row contains the configuration for an interface"
    INDEX       { vtssEvcConfigInterfaceIfIndex }
    ::= { vtssEvcConfigInterfaceTable 1 }

VTSSEvcConfigInterfaceEntry ::= SEQUENCE {
    vtssEvcConfigInterfaceIfIndex   VTSSInterfaceIndex,
    vtssEvcConfigInterfaceKey   VTSSVcapKeyType,
    vtssEvcConfigInterfaceKeyAdv    VTSSVcapKeyType,
    vtssEvcConfigInterfaceAddrMode      TruthValue,
    vtssEvcConfigInterfaceAddrModeAdv   TruthValue,
    vtssEvcConfigInterfaceDeiColoring   TruthValue,
    vtssEvcConfigInterfaceInnerTag      TruthValue
}

vtssEvcConfigInterfaceIfIndex OBJECT-TYPE
    SYNTAX      VTSSInterfaceIndex
    MAX-ACCESS  not-accessible
    STATUS      current
    DESCRIPTION 
        "Logical interface index."
    ::= { vtssEvcConfigInterfaceEntry 1 }

vtssEvcConfigInterfaceKey OBJECT-TYPE
    SYNTAX      VTSSVcapKeyType
    MAX-ACCESS  read-write
    STATUS      current
    DESCRIPTION 
        "The key type for the basic ingress lookup.
         
         This object is only available if the capability object
         'vtssEvcCapabilitiesHasPortKey' is True."
    ::= { vtssEvcConfigInterfaceEntry 2 }

vtssEvcConfigInterfaceKeyAdv OBJECT-TYPE
    SYNTAX      VTSSVcapKeyType
    MAX-ACCESS  read-write
    STATUS      current
    DESCRIPTION 
        "The key type for the advanced ingress lookup.
         
         This object is only available if the capability object
         'vtssEvcCapabilitiesHasPortKey' is True."
    ::= { vtssEvcConfigInterfaceEntry 3 }

vtssEvcConfigInterfaceAddrMode OBJECT-TYPE
    SYNTAX      TruthValue
    MAX-ACCESS  read-write
    STATUS      current
    DESCRIPTION 
        "If false, the basic ingress lookup is based on SMAC/SIP. If true, the
         basic ingress lookup is based on DMAC/DIP.
         
         This object is only available if the capability object
         'vtssEvcCapabilitiesHasPortAddrMode' is True."
    ::= { vtssEvcConfigInterfaceEntry 4 }

vtssEvcConfigInterfaceAddrModeAdv OBJECT-TYPE
    SYNTAX      TruthValue
    MAX-ACCESS  read-write
    STATUS      current
    DESCRIPTION 
        "If false, the advanced ingress lookup is based on SMAC/SIP. If true,
         the advanced ingress lookup is based on DMAC/DIP.
         
         This object is only available if the capability object
         'vtssEvcCapabilitiesHasPortKey' is True."
    ::= { vtssEvcConfigInterfaceEntry 5 }

vtssEvcConfigInterfaceDeiColoring OBJECT-TYPE
    SYNTAX      TruthValue
    MAX-ACCESS  read-write
    STATUS      current
    DESCRIPTION 
        "If false, DEI coloring for the NNI port is enabled. If true, DEI
         coloring for the NNI port is disabled.
         
         This object is only available if the capability object
         'vtssEvcCapabilitiesHasPortDeiColoring' is True."
    ::= { vtssEvcConfigInterfaceEntry 6 }

vtssEvcConfigInterfaceInnerTag OBJECT-TYPE
    SYNTAX      TruthValue
    MAX-ACCESS  read-write
    STATUS      current
    DESCRIPTION 
        "If false, the NNI port uses outer tag classification. If true, the NNI
         port uses inner tag classification.
         
         This object is only available if the capability object
         'vtssEvcCapabilitiesHasPortInnerTag' is True."
    ::= { vtssEvcConfigInterfaceEntry 7 }

vtssEvcConfigInterfaceL2cpTable OBJECT-TYPE
    SYNTAX      SEQUENCE OF VTSSEvcConfigInterfaceL2cpEntry
    MAX-ACCESS  not-accessible
    STATUS      current
    DESCRIPTION 
        "This table provides L2CP configuration for interfaces"
    ::= { vtssEvcConfigInterface 2 }

vtssEvcConfigInterfaceL2cpEntry OBJECT-TYPE
    SYNTAX      VTSSEvcConfigInterfaceL2cpEntry
    MAX-ACCESS  not-accessible
    STATUS      current
    DESCRIPTION 
        "Each row contains the configuration for an L2CP"
    INDEX       { vtssEvcConfigInterfaceL2cpIfIndex, vtssEvcConfigInterfaceL2cpL2cpId }
    ::= { vtssEvcConfigInterfaceL2cpTable 1 }

VTSSEvcConfigInterfaceL2cpEntry ::= SEQUENCE {
    vtssEvcConfigInterfaceL2cpIfIndex   VTSSInterfaceIndex,
    vtssEvcConfigInterfaceL2cpL2cpId    Integer32,
    vtssEvcConfigInterfaceL2cpL2cpMode      VTSSevcL2cpMode
}

vtssEvcConfigInterfaceL2cpIfIndex OBJECT-TYPE
    SYNTAX      VTSSInterfaceIndex
    MAX-ACCESS  not-accessible
    STATUS      current
    DESCRIPTION 
        "Logical interface index."
    ::= { vtssEvcConfigInterfaceL2cpEntry 1 }

vtssEvcConfigInterfaceL2cpL2cpId OBJECT-TYPE
    SYNTAX      Integer32 (0..31)
    MAX-ACCESS  not-accessible
    STATUS      current
    DESCRIPTION 
        "L2CP ID."
    ::= { vtssEvcConfigInterfaceL2cpEntry 2 }

vtssEvcConfigInterfaceL2cpL2cpMode OBJECT-TYPE
    SYNTAX      VTSSevcL2cpMode
    MAX-ACCESS  read-write
    STATUS      current
    DESCRIPTION 
        "The forwarding mode for the L2CP."
    ::= { vtssEvcConfigInterfaceL2cpEntry 3 }

vtssEvcConfigPolicerTable OBJECT-TYPE
    SYNTAX      SEQUENCE OF VTSSEvcConfigPolicerEntry
    MAX-ACCESS  not-accessible
    STATUS      current
    DESCRIPTION 
        "This table provides EVC policer configuration"
    ::= { vtssEvcConfig 3 }

vtssEvcConfigPolicerEntry OBJECT-TYPE
    SYNTAX      VTSSEvcConfigPolicerEntry
    MAX-ACCESS  not-accessible
    STATUS      current
    DESCRIPTION 
        "Each row contains the configuration for a policer"
    INDEX       { vtssEvcConfigPolicerPolicerId }
    ::= { vtssEvcConfigPolicerTable 1 }

VTSSEvcConfigPolicerEntry ::= SEQUENCE {
    vtssEvcConfigPolicerPolicerId   Integer32,
    vtssEvcConfigPolicerEnable      TruthValue,
    vtssEvcConfigPolicerPolicerType     VTSSevcPolicerType,
    vtssEvcConfigPolicerPolicerMode     VTSSevcPolicerMode,
    vtssEvcConfigPolicerLineRate    TruthValue,
    vtssEvcConfigPolicerCir     Unsigned32,
    vtssEvcConfigPolicerCbs     Unsigned32,
    vtssEvcConfigPolicerEir     Unsigned32,
    vtssEvcConfigPolicerEbs     Unsigned32
}

vtssEvcConfigPolicerPolicerId OBJECT-TYPE
    SYNTAX      Integer32 (0..4095)
    MAX-ACCESS  not-accessible
    STATUS      current
    DESCRIPTION 
        "Policer ID, allowed range is [0,PolicerMax[."
    ::= { vtssEvcConfigPolicerEntry 1 }

vtssEvcConfigPolicerEnable OBJECT-TYPE
    SYNTAX      TruthValue
    MAX-ACCESS  read-write
    STATUS      current
    DESCRIPTION 
        "Enable or disable policer."
    ::= { vtssEvcConfigPolicerEntry 2 }

vtssEvcConfigPolicerPolicerType OBJECT-TYPE
    SYNTAX      VTSSevcPolicerType
    MAX-ACCESS  read-write
    STATUS      current
    DESCRIPTION 
        "The EVC policer type."
    ::= { vtssEvcConfigPolicerEntry 3 }

vtssEvcConfigPolicerPolicerMode OBJECT-TYPE
    SYNTAX      VTSSevcPolicerMode
    MAX-ACCESS  read-write
    STATUS      current
    DESCRIPTION 
        "The EVC policer mode. Color-blind policing is only supported if
         HasPolicerColorBlind is true."
    ::= { vtssEvcConfigPolicerEntry 4 }

vtssEvcConfigPolicerLineRate OBJECT-TYPE
    SYNTAX      TruthValue
    MAX-ACCESS  read-write
    STATUS      current
    DESCRIPTION 
        "Enable or disable line rate policing."
    ::= { vtssEvcConfigPolicerEntry 5 }

vtssEvcConfigPolicerCir OBJECT-TYPE
    SYNTAX      Unsigned32
    MAX-ACCESS  read-write
    STATUS      current
    DESCRIPTION 
        "Committed Information Rate in kbps."
    ::= { vtssEvcConfigPolicerEntry 6 }

vtssEvcConfigPolicerCbs OBJECT-TYPE
    SYNTAX      Unsigned32
    MAX-ACCESS  read-write
    STATUS      current
    DESCRIPTION 
        "Committed Burst Size in bytes."
    ::= { vtssEvcConfigPolicerEntry 7 }

vtssEvcConfigPolicerEir OBJECT-TYPE
    SYNTAX      Unsigned32
    MAX-ACCESS  read-write
    STATUS      current
    DESCRIPTION 
        "Excess Information Rate in kbps."
    ::= { vtssEvcConfigPolicerEntry 8 }

vtssEvcConfigPolicerEbs OBJECT-TYPE
    SYNTAX      Unsigned32
    MAX-ACCESS  read-write
    STATUS      current
    DESCRIPTION 
        "Excess Burst Size in bytes."
    ::= { vtssEvcConfigPolicerEntry 9 }

vtssEvcConfigEvc OBJECT IDENTIFIER
    ::= { vtssEvcConfig 4 }

vtssEvcConfigEvcTable OBJECT-TYPE
    SYNTAX      SEQUENCE OF VTSSEvcConfigEvcEntry
    MAX-ACCESS  not-accessible
    STATUS      current
    DESCRIPTION 
        "This table contains the configuration of EVCs"
    ::= { vtssEvcConfigEvc 1 }

vtssEvcConfigEvcEntry OBJECT-TYPE
    SYNTAX      VTSSEvcConfigEvcEntry
    MAX-ACCESS  not-accessible
    STATUS      current
    DESCRIPTION 
        "Each row contains the configuration for an EVC"
    INDEX       { vtssEvcConfigEvcEvcId }
    ::= { vtssEvcConfigEvcTable 1 }

VTSSEvcConfigEvcEntry ::= SEQUENCE {
    vtssEvcConfigEvcEvcId   Integer32,
    vtssEvcConfigEvcVid     VTSSUnsigned16,
    vtssEvcConfigEvcIvid    VTSSUnsigned16,
    vtssEvcConfigEvcNniPortList     VTSSPortList,
    vtssEvcConfigEvcLearning    TruthValue,
    vtssEvcConfigEvcPolicerOp   VTSSevcPolicerOp,
    vtssEvcConfigEvcPolicerId   VTSSUnsigned16,
    vtssEvcConfigEvcUniVid      VTSSUnsigned16,
    vtssEvcConfigEvcItAddType   VTSSevcInnerTagType,
    vtssEvcConfigEvcItInnerVid      TruthValue,
    vtssEvcConfigEvcItAddVid    VTSSUnsigned16,
    vtssEvcConfigEvcItAddPcpDeiPreserve     TruthValue,
    vtssEvcConfigEvcItAddPcp    Unsigned32,
    vtssEvcConfigEvcItAddDei    VTSSUnsigned8,
    vtssEvcConfigEvcLeafVid     VTSSUnsigned16,
    vtssEvcConfigEvcLeafIvid    VTSSUnsigned16,
    vtssEvcConfigEvcLeafPortList    VTSSPortList,
    vtssEvcConfigEvcAction      VTSSRowEditorState
}

vtssEvcConfigEvcEvcId OBJECT-TYPE
    SYNTAX      Integer32 (0..4095)
    MAX-ACCESS  not-accessible
    STATUS      current
    DESCRIPTION 
        "EVC ID, allowed range is [0,EvcMax[."
    ::= { vtssEvcConfigEvcEntry 1 }

vtssEvcConfigEvcVid OBJECT-TYPE
    SYNTAX      VTSSUnsigned16
    MAX-ACCESS  read-write
    STATUS      current
    DESCRIPTION 
        "The VLAN ID used in the outer tag for the EVC."
    ::= { vtssEvcConfigEvcEntry 2 }

vtssEvcConfigEvcIvid OBJECT-TYPE
    SYNTAX      VTSSUnsigned16
    MAX-ACCESS  read-write
    STATUS      current
    DESCRIPTION 
        "The internal classified VLAN ID for the EVC."
    ::= { vtssEvcConfigEvcEntry 3 }

vtssEvcConfigEvcNniPortList OBJECT-TYPE
    SYNTAX      VTSSPortList
    MAX-ACCESS  read-write
    STATUS      current
    DESCRIPTION 
        "List of NNI ports for the EVC."
    ::= { vtssEvcConfigEvcEntry 4 }

vtssEvcConfigEvcLearning OBJECT-TYPE
    SYNTAX      TruthValue
    MAX-ACCESS  read-write
    STATUS      current
    DESCRIPTION 
        "Enable or disable MAC address learning for the EVC."
    ::= { vtssEvcConfigEvcEntry 5 }

vtssEvcConfigEvcPolicerOp OBJECT-TYPE
    SYNTAX      VTSSevcPolicerOp
    MAX-ACCESS  read-write
    STATUS      current
    DESCRIPTION 
        "Policer operator for the EVC.
         
         This object is only available if the capability object
         'vtssEvcCapabilitiesHasEvcPolicer' is True."
    ::= { vtssEvcConfigEvcEntry 6 }

vtssEvcConfigEvcPolicerId OBJECT-TYPE
    SYNTAX      VTSSUnsigned16
    MAX-ACCESS  read-write
    STATUS      current
    DESCRIPTION 
        "Policer ID for the EVC.
         
         This object is only available if the capability object
         'vtssEvcCapabilitiesHasEvcPolicer' is True."
    ::= { vtssEvcConfigEvcEntry 7 }

vtssEvcConfigEvcUniVid OBJECT-TYPE
    SYNTAX      VTSSUnsigned16
    MAX-ACCESS  read-write
    STATUS      current
    DESCRIPTION 
        "The VLAN ID used in the outer tag on the UNI.
         
         This object is only available if the capability object
         'vtssEvcCapabilitiesHasEvcUniVid' is True."
    ::= { vtssEvcConfigEvcEntry 8 }

vtssEvcConfigEvcItAddType OBJECT-TYPE
    SYNTAX      VTSSevcInnerTagType
    MAX-ACCESS  read-write
    STATUS      current
    DESCRIPTION 
        "The tag type for the inner tag pushed.
         
         This object is only available if the capability object
         'vtssEvcCapabilitiesHasEvcItAdd' is True."
    ::= { vtssEvcConfigEvcEntry 9 }

vtssEvcConfigEvcItInnerVid OBJECT-TYPE
    SYNTAX      TruthValue
    MAX-ACCESS  read-write
    STATUS      current
    DESCRIPTION 
        "Enable inner VLAN ID for EVC classification.
         
         This object is only available if the capability object
         'vtssEvcCapabilitiesHasEvcItAdd' is True."
    ::= { vtssEvcConfigEvcEntry 10 }

vtssEvcConfigEvcItAddVid OBJECT-TYPE
    SYNTAX      VTSSUnsigned16
    MAX-ACCESS  read-write
    STATUS      current
    DESCRIPTION 
        "The VLAN ID for the inner tag pushed
         
         This object is only available if the capability object
         'vtssEvcCapabilitiesHasEvcItAdd' is True."
    ::= { vtssEvcConfigEvcEntry 11 }

vtssEvcConfigEvcItAddPcpDeiPreserve OBJECT-TYPE
    SYNTAX      TruthValue
    MAX-ACCESS  read-write
    STATUS      current
    DESCRIPTION 
        "Enable PCP/DEI preservation for the inner tag pushed.
         
         This object is only available if the capability object
         'vtssEvcCapabilitiesHasEvcItAdd' is True."
    ::= { vtssEvcConfigEvcEntry 12 }

vtssEvcConfigEvcItAddPcp OBJECT-TYPE
    SYNTAX      Unsigned32
    MAX-ACCESS  read-write
    STATUS      current
    DESCRIPTION 
        "The PCP value for the inner tag pushed.
         
         This object is only available if the capability object
         'vtssEvcCapabilitiesHasEvcItAdd' is True."
    ::= { vtssEvcConfigEvcEntry 13 }

vtssEvcConfigEvcItAddDei OBJECT-TYPE
    SYNTAX      VTSSUnsigned8
    MAX-ACCESS  read-write
    STATUS      current
    DESCRIPTION 
        "The DEI value for the inner tag pushed.
         
         This object is only available if the capability object
         'vtssEvcCapabilitiesHasEvcItAdd' is True."
    ::= { vtssEvcConfigEvcEntry 14 }

vtssEvcConfigEvcLeafVid OBJECT-TYPE
    SYNTAX      VTSSUnsigned16
    MAX-ACCESS  read-write
    STATUS      current
    DESCRIPTION 
        "The leaf VLAN ID used in the outer tag for the EVC.
         
         This object is only available if the capability object
         'vtssEvcCapabilitiesHasEvcETree' is True."
    ::= { vtssEvcConfigEvcEntry 15 }

vtssEvcConfigEvcLeafIvid OBJECT-TYPE
    SYNTAX      VTSSUnsigned16
    MAX-ACCESS  read-write
    STATUS      current
    DESCRIPTION 
        "The leaf internal classified VLAN ID for the EVC.
         
         This object is only available if the capability object
         'vtssEvcCapabilitiesHasEvcETree' is True."
    ::= { vtssEvcConfigEvcEntry 16 }

vtssEvcConfigEvcLeafPortList OBJECT-TYPE
    SYNTAX      VTSSPortList
    MAX-ACCESS  read-write
    STATUS      current
    DESCRIPTION 
        "List of leaf ports for the EVC.
         
         This object is only available if the capability object
         'vtssEvcCapabilitiesHasEvcETree' is True."
    ::= { vtssEvcConfigEvcEntry 17 }

vtssEvcConfigEvcAction OBJECT-TYPE
    SYNTAX      VTSSRowEditorState
    MAX-ACCESS  read-write
    STATUS      current
    DESCRIPTION 
        "Action"
    ::= { vtssEvcConfigEvcEntry 10000 }

vtssEvcConfigEvcTableRowEditor OBJECT IDENTIFIER
    ::= { vtssEvcConfigEvc 2 }

vtssEvcConfigEvcTableRowEditorEvcId OBJECT-TYPE
    SYNTAX      Integer32 (0..4095)
    MAX-ACCESS  read-write
    STATUS      current
    DESCRIPTION 
        "EVC ID, allowed range is [0,EvcMax[."
    ::= { vtssEvcConfigEvcTableRowEditor 1 }

vtssEvcConfigEvcTableRowEditorVid OBJECT-TYPE
    SYNTAX      VTSSUnsigned16
    MAX-ACCESS  read-write
    STATUS      current
    DESCRIPTION 
        "The VLAN ID used in the outer tag for the EVC."
    ::= { vtssEvcConfigEvcTableRowEditor 2 }

vtssEvcConfigEvcTableRowEditorIvid OBJECT-TYPE
    SYNTAX      VTSSUnsigned16
    MAX-ACCESS  read-write
    STATUS      current
    DESCRIPTION 
        "The internal classified VLAN ID for the EVC."
    ::= { vtssEvcConfigEvcTableRowEditor 3 }

vtssEvcConfigEvcTableRowEditorNniPortList OBJECT-TYPE
    SYNTAX      VTSSPortList
    MAX-ACCESS  read-write
    STATUS      current
    DESCRIPTION 
        "List of NNI ports for the EVC."
    ::= { vtssEvcConfigEvcTableRowEditor 4 }

vtssEvcConfigEvcTableRowEditorLearning OBJECT-TYPE
    SYNTAX      TruthValue
    MAX-ACCESS  read-write
    STATUS      current
    DESCRIPTION 
        "Enable or disable MAC address learning for the EVC."
    ::= { vtssEvcConfigEvcTableRowEditor 5 }

vtssEvcConfigEvcTableRowEditorPolicerOp OBJECT-TYPE
    SYNTAX      VTSSevcPolicerOp
    MAX-ACCESS  read-write
    STATUS      current
    DESCRIPTION 
        "Policer operator for the EVC.
         
         This object is only available if the capability object
         'vtssEvcCapabilitiesHasEvcPolicer' is True."
    ::= { vtssEvcConfigEvcTableRowEditor 6 }

vtssEvcConfigEvcTableRowEditorPolicerId OBJECT-TYPE
    SYNTAX      VTSSUnsigned16
    MAX-ACCESS  read-write
    STATUS      current
    DESCRIPTION 
        "Policer ID for the EVC.
         
         This object is only available if the capability object
         'vtssEvcCapabilitiesHasEvcPolicer' is True."
    ::= { vtssEvcConfigEvcTableRowEditor 7 }

vtssEvcConfigEvcTableRowEditorUniVid OBJECT-TYPE
    SYNTAX      VTSSUnsigned16
    MAX-ACCESS  read-write
    STATUS      current
    DESCRIPTION 
        "The VLAN ID used in the outer tag on the UNI.
         
         This object is only available if the capability object
         'vtssEvcCapabilitiesHasEvcUniVid' is True."
    ::= { vtssEvcConfigEvcTableRowEditor 8 }

vtssEvcConfigEvcTableRowEditorItAddType OBJECT-TYPE
    SYNTAX      VTSSevcInnerTagType
    MAX-ACCESS  read-write
    STATUS      current
    DESCRIPTION 
        "The tag type for the inner tag pushed.
         
         This object is only available if the capability object
         'vtssEvcCapabilitiesHasEvcItAdd' is True."
    ::= { vtssEvcConfigEvcTableRowEditor 9 }

vtssEvcConfigEvcTableRowEditorItInnerVid OBJECT-TYPE
    SYNTAX      TruthValue
    MAX-ACCESS  read-write
    STATUS      current
    DESCRIPTION 
        "Enable inner VLAN ID for EVC classification.
         
         This object is only available if the capability object
         'vtssEvcCapabilitiesHasEvcItAdd' is True."
    ::= { vtssEvcConfigEvcTableRowEditor 10 }

vtssEvcConfigEvcTableRowEditorItAddVid OBJECT-TYPE
    SYNTAX      VTSSUnsigned16
    MAX-ACCESS  read-write
    STATUS      current
    DESCRIPTION 
        "The VLAN ID for the inner tag pushed
         
         This object is only available if the capability object
         'vtssEvcCapabilitiesHasEvcItAdd' is True."
    ::= { vtssEvcConfigEvcTableRowEditor 11 }

vtssEvcConfigEvcTableRowEditorItAddPcpDeiPreserve OBJECT-TYPE
    SYNTAX      TruthValue
    MAX-ACCESS  read-write
    STATUS      current
    DESCRIPTION 
        "Enable PCP/DEI preservation for the inner tag pushed.
         
         This object is only available if the capability object
         'vtssEvcCapabilitiesHasEvcItAdd' is True."
    ::= { vtssEvcConfigEvcTableRowEditor 12 }

vtssEvcConfigEvcTableRowEditorItAddPcp OBJECT-TYPE
    SYNTAX      Unsigned32
    MAX-ACCESS  read-write
    STATUS      current
    DESCRIPTION 
        "The PCP value for the inner tag pushed.
         
         This object is only available if the capability object
         'vtssEvcCapabilitiesHasEvcItAdd' is True."
    ::= { vtssEvcConfigEvcTableRowEditor 13 }

vtssEvcConfigEvcTableRowEditorItAddDei OBJECT-TYPE
    SYNTAX      VTSSUnsigned8
    MAX-ACCESS  read-write
    STATUS      current
    DESCRIPTION 
        "The DEI value for the inner tag pushed.
         
         This object is only available if the capability object
         'vtssEvcCapabilitiesHasEvcItAdd' is True."
    ::= { vtssEvcConfigEvcTableRowEditor 14 }

vtssEvcConfigEvcTableRowEditorLeafVid OBJECT-TYPE
    SYNTAX      VTSSUnsigned16
    MAX-ACCESS  read-write
    STATUS      current
    DESCRIPTION 
        "The leaf VLAN ID used in the outer tag for the EVC.
         
         This object is only available if the capability object
         'vtssEvcCapabilitiesHasEvcETree' is True."
    ::= { vtssEvcConfigEvcTableRowEditor 15 }

vtssEvcConfigEvcTableRowEditorLeafIvid OBJECT-TYPE
    SYNTAX      VTSSUnsigned16
    MAX-ACCESS  read-write
    STATUS      current
    DESCRIPTION 
        "The leaf internal classified VLAN ID for the EVC.
         
         This object is only available if the capability object
         'vtssEvcCapabilitiesHasEvcETree' is True."
    ::= { vtssEvcConfigEvcTableRowEditor 16 }

vtssEvcConfigEvcTableRowEditorLeafPortList OBJECT-TYPE
    SYNTAX      VTSSPortList
    MAX-ACCESS  read-write
    STATUS      current
    DESCRIPTION 
        "List of leaf ports for the EVC.
         
         This object is only available if the capability object
         'vtssEvcCapabilitiesHasEvcETree' is True."
    ::= { vtssEvcConfigEvcTableRowEditor 17 }

vtssEvcConfigEvcTableRowEditorAction OBJECT-TYPE
    SYNTAX      VTSSRowEditorState
    MAX-ACCESS  read-write
    STATUS      current
    DESCRIPTION 
        "Action"
    ::= { vtssEvcConfigEvcTableRowEditor 10000 }

vtssEvcConfigEce OBJECT IDENTIFIER
    ::= { vtssEvcConfig 5 }

vtssEvcConfigEceTable OBJECT-TYPE
    SYNTAX      SEQUENCE OF VTSSEvcConfigEceEntry
    MAX-ACCESS  not-accessible
    STATUS      current
    DESCRIPTION 
        "This table contains the configuration of ECEs"
    ::= { vtssEvcConfigEce 1 }

vtssEvcConfigEceEntry OBJECT-TYPE
    SYNTAX      VTSSEvcConfigEceEntry
    MAX-ACCESS  not-accessible
    STATUS      current
    DESCRIPTION 
        "Each row contains the configuration for an ECE"
    INDEX       { vtssEvcConfigEceEceId }
    ::= { vtssEvcConfigEceTable 1 }

VTSSEvcConfigEceEntry ::= SEQUENCE {
    vtssEvcConfigEceEceId   Integer32,
    vtssEvcConfigEceNextId      Unsigned32,
    vtssEvcConfigEceAdvLookup   TruthValue,
    vtssEvcConfigEceUniPortList     VTSSPortList,
    vtssEvcConfigEceSrcMac      MacAddress,
    vtssEvcConfigEceSrcMacMask      MacAddress,
    vtssEvcConfigEceDestMacType     VTSSDestMacType,
    vtssEvcConfigEceDestMac     MacAddress,
    vtssEvcConfigEceDestMacMask     MacAddress,
    vtssEvcConfigEceOtMatchType     VTSSVlanTagType,
    vtssEvcConfigEceOtMatchVid      Unsigned32,
    vtssEvcConfigEceOtMatchPcp      VTSSVlanTagPriority,
    vtssEvcConfigEceOtMatchDei      VTSSBitType,
    vtssEvcConfigEceItMatchType     VTSSVlanTagType,
    vtssEvcConfigEceItMatchVid      Unsigned32,
    vtssEvcConfigEceItMatchPcp      VTSSVlanTagPriority,
    vtssEvcConfigEceItMatchDei      VTSSBitType,
    vtssEvcConfigEceFrameType   VTSSevcFrameType,
    vtssEvcConfigEceEtype   VTSSUnsigned16,
    vtssEvcConfigEceEtypeMask   VTSSUnsigned16,
    vtssEvcConfigEceEtypeData   VTSSUnsigned16,
    vtssEvcConfigEceEtypeDataMask   VTSSUnsigned16,
    vtssEvcConfigEceLlcDsap     VTSSUnsigned8,
    vtssEvcConfigEceLlcDsapMask     VTSSUnsigned8,
    vtssEvcConfigEceLlcSsap     VTSSUnsigned8,
    vtssEvcConfigEceLlcSsapMask     VTSSUnsigned8,
    vtssEvcConfigEceLlcControl      VTSSUnsigned8,
    vtssEvcConfigEceLlcControlMask      VTSSUnsigned8,
    vtssEvcConfigEceLlcPid      VTSSUnsigned16,
    vtssEvcConfigEceLlcPidMask      VTSSUnsigned16,
    vtssEvcConfigEceSnapOui     Unsigned32,
    vtssEvcConfigEceSnapOuiMask     Unsigned32,
    vtssEvcConfigEceSnapPid     VTSSUnsigned16,
    vtssEvcConfigEceSnapPidMask     VTSSUnsigned16,
    vtssEvcConfigEceL2cpType    VTSSevcL2cpType,
    vtssEvcConfigEceIpv4Dscp    Unsigned32,
    vtssEvcConfigEceIpv4Proto   VTSSUnsigned8,
    vtssEvcConfigEceIpv4ProtoMask   VTSSUnsigned8,
    vtssEvcConfigEceIpv4Fragment    VTSSBitType,
    vtssEvcConfigEceIpv4SrcIp   IpAddress,
    vtssEvcConfigEceIpv4SrcIpMask   IpAddress,
    vtssEvcConfigEceIpv4DestIp      IpAddress,
    vtssEvcConfigEceIpv4DestIpMask      IpAddress,
    vtssEvcConfigEceIpv4SrcPort     Unsigned32,
    vtssEvcConfigEceIpv4DestPort    Unsigned32,
    vtssEvcConfigEceIpv6Dscp    Unsigned32,
    vtssEvcConfigEceIpv6Proto   VTSSUnsigned8,
    vtssEvcConfigEceIpv6ProtoMask   VTSSUnsigned8,
    vtssEvcConfigEceIpv6SrcIp   InetAddressIPv6,
    vtssEvcConfigEceIpv6SrcIpMask   InetAddressIPv6,
    vtssEvcConfigEceIpv6DestIp      InetAddressIPv6,
    vtssEvcConfigEceIpv6DestIpMask      InetAddressIPv6,
    vtssEvcConfigEceIpv6SrcPort     Unsigned32,
    vtssEvcConfigEceIpv6DestPort    Unsigned32,
    vtssEvcConfigEceDirection   VTSSevcDirection,
    vtssEvcConfigEceRuleType    VTSSevcRuleType,
    vtssEvcConfigEceTxLookup    VTSSevcTxLookup,
    vtssEvcConfigEcePopTag      VTSSevcPopTag,
    vtssEvcConfigEceOtAddEnable     TruthValue,
    vtssEvcConfigEceOtAddVid    VTSSUnsigned16,
    vtssEvcConfigEceOtAddPcpMode    VTSSevcPcpMode,
    vtssEvcConfigEceOtAddPcpDeiPreserve     TruthValue,
    vtssEvcConfigEceOtAddPcp    Unsigned32,
    vtssEvcConfigEceOtAddDeiMode    VTSSevcDeiMode,
    vtssEvcConfigEceOtAddDei    VTSSUnsigned8,
    vtssEvcConfigEceItAddType   VTSSevcInnerTagType,
    vtssEvcConfigEceItAddVid    VTSSUnsigned16,
    vtssEvcConfigEceItAddPcpMode    VTSSevcPcpMode,
    vtssEvcConfigEceItAddPcpDeiPreserve     TruthValue,
    vtssEvcConfigEceItAddPcp    Unsigned32,
    vtssEvcConfigEceItAddDeiMode    VTSSevcDeiMode,
    vtssEvcConfigEceItAddDei    VTSSUnsigned8,
    vtssEvcConfigEceEvcId   VTSSUnsigned16,
    vtssEvcConfigEcePolicerOp   VTSSevcPolicerOp,
    vtssEvcConfigEcePolicerId   VTSSUnsigned16,
    vtssEvcConfigEcePolicyNo    Unsigned32,
    vtssEvcConfigEceCosEnable   TruthValue,
    vtssEvcConfigEceCos     Unsigned32,
    vtssEvcConfigEceDpEnable    TruthValue,
    vtssEvcConfigEceDp      VTSSUnsigned8,
    vtssEvcConfigEceL2cpMode    VTSSevcEceL2cpMode,
    vtssEvcConfigEceL2cpDmac    VTSSevcL2cpDmac,
    vtssEvcConfigEceAction      VTSSRowEditorState
}

vtssEvcConfigEceEceId OBJECT-TYPE
    SYNTAX      Integer32 (1..4096)
    MAX-ACCESS  not-accessible
    STATUS      current
    DESCRIPTION 
        "ECE ID, allowed range is [1,EceMax]."
    ::= { vtssEvcConfigEceEntry 1 }

vtssEvcConfigEceNextId OBJECT-TYPE
    SYNTAX      Unsigned32
    MAX-ACCESS  read-write
    STATUS      current
    DESCRIPTION 
        "The ID of the next ECE."
    ::= { vtssEvcConfigEceEntry 2 }

vtssEvcConfigEceAdvLookup OBJECT-TYPE
    SYNTAX      TruthValue
    MAX-ACCESS  read-write
    STATUS      current
    DESCRIPTION 
        "Enable advanced ingress lookup.
         
         This object is only available if the capability object
         'vtssEvcCapabilitiesHasEceAdvLookup' is True."
    ::= { vtssEvcConfigEceEntry 3 }

vtssEvcConfigEceUniPortList OBJECT-TYPE
    SYNTAX      VTSSPortList
    MAX-ACCESS  read-write
    STATUS      current
    DESCRIPTION 
        "List of UNI ports for the ECE."
    ::= { vtssEvcConfigEceEntry 4 }

vtssEvcConfigEceSrcMac OBJECT-TYPE
    SYNTAX      MacAddress
    MAX-ACCESS  read-write
    STATUS      current
    DESCRIPTION 
        "The source MAC address to match.
         
         This object is only available if the capability object
         'vtssEvcCapabilitiesHasEceSrcMac' is True."
    ::= { vtssEvcConfigEceEntry 10 }

vtssEvcConfigEceSrcMacMask OBJECT-TYPE
    SYNTAX      MacAddress
    MAX-ACCESS  read-write
    STATUS      current
    DESCRIPTION 
        "The source MAC address mask.
         
         This object is only available if the capability object
         'vtssEvcCapabilitiesHasEceSrcMac' is True."
    ::= { vtssEvcConfigEceEntry 11 }

vtssEvcConfigEceDestMacType OBJECT-TYPE
    SYNTAX      VTSSDestMacType
    MAX-ACCESS  read-write
    STATUS      current
    DESCRIPTION 
        "The destination MAC address type to match.
         
         This object is only available if the capability object
         'vtssEvcCapabilitiesHasEceDestMacType' is True."
    ::= { vtssEvcConfigEceEntry 12 }

vtssEvcConfigEceDestMac OBJECT-TYPE
    SYNTAX      MacAddress
    MAX-ACCESS  read-write
    STATUS      current
    DESCRIPTION 
        "The destination MAC address to match.
         
         This object is only available if the capability object
         'vtssEvcCapabilitiesHasEceDestMac' is True."
    ::= { vtssEvcConfigEceEntry 13 }

vtssEvcConfigEceDestMacMask OBJECT-TYPE
    SYNTAX      MacAddress
    MAX-ACCESS  read-write
    STATUS      current
    DESCRIPTION 
        "The destination MAC address mask.
         
         This object is only available if the capability object
         'vtssEvcCapabilitiesHasEceDestMac' is True."
    ::= { vtssEvcConfigEceEntry 14 }

vtssEvcConfigEceOtMatchType OBJECT-TYPE
    SYNTAX      VTSSVlanTagType
    MAX-ACCESS  read-write
    STATUS      current
    DESCRIPTION 
        "The outer tag type to match."
    ::= { vtssEvcConfigEceEntry 20 }

vtssEvcConfigEceOtMatchVid OBJECT-TYPE
    SYNTAX      Unsigned32
    MAX-ACCESS  read-write
    STATUS      current
    DESCRIPTION 
        "The outer tag VLAN ID range to match. The minimum value is encoded in
         the 16 least significant bits. The maximum value is encoded in the 16
         most significant bits."
    ::= { vtssEvcConfigEceEntry 21 }

vtssEvcConfigEceOtMatchPcp OBJECT-TYPE
    SYNTAX      VTSSVlanTagPriority
    MAX-ACCESS  read-write
    STATUS      current
    DESCRIPTION 
        "The outer tag PCP to match."
    ::= { vtssEvcConfigEceEntry 22 }

vtssEvcConfigEceOtMatchDei OBJECT-TYPE
    SYNTAX      VTSSBitType
    MAX-ACCESS  read-write
    STATUS      current
    DESCRIPTION 
        "The outer tag DEI to match."
    ::= { vtssEvcConfigEceEntry 23 }

vtssEvcConfigEceItMatchType OBJECT-TYPE
    SYNTAX      VTSSVlanTagType
    MAX-ACCESS  read-write
    STATUS      current
    DESCRIPTION 
        "The inner tag type to match.
         
         This object is only available if the capability object
         'vtssEvcCapabilitiesHasEceInnerTag' is True."
    ::= { vtssEvcConfigEceEntry 30 }

vtssEvcConfigEceItMatchVid OBJECT-TYPE
    SYNTAX      Unsigned32
    MAX-ACCESS  read-write
    STATUS      current
    DESCRIPTION 
        "The inner tag VLAN ID range to match. The minimum value is encoded in
         the 16 least significant bits. The maximum value is encoded in the 16
         most significant bits.
         
         This object is only available if the capability object
         'vtssEvcCapabilitiesHasEceInnerTag' is True."
    ::= { vtssEvcConfigEceEntry 31 }

vtssEvcConfigEceItMatchPcp OBJECT-TYPE
    SYNTAX      VTSSVlanTagPriority
    MAX-ACCESS  read-write
    STATUS      current
    DESCRIPTION 
        "The inner tag PCP to match.
         
         This object is only available if the capability object
         'vtssEvcCapabilitiesHasEceInnerTag' is True."
    ::= { vtssEvcConfigEceEntry 32 }

vtssEvcConfigEceItMatchDei OBJECT-TYPE
    SYNTAX      VTSSBitType
    MAX-ACCESS  read-write
    STATUS      current
    DESCRIPTION 
        "The inner tag DEI to match.
         
         This object is only available if the capability object
         'vtssEvcCapabilitiesHasEceInnerTag' is True."
    ::= { vtssEvcConfigEceEntry 33 }

vtssEvcConfigEceFrameType OBJECT-TYPE
    SYNTAX      VTSSevcFrameType
    MAX-ACCESS  read-write
    STATUS      current
    DESCRIPTION 
        "The ECE frame type."
    ::= { vtssEvcConfigEceEntry 50 }

vtssEvcConfigEceEtype OBJECT-TYPE
    SYNTAX      VTSSUnsigned16
    MAX-ACCESS  read-write
    STATUS      current
    DESCRIPTION 
        "The Ethernet Type to match.
         
         This object is only available if the capability object
         'vtssEvcCapabilitiesHasEceEtype' is True."
    ::= { vtssEvcConfigEceEntry 100 }

vtssEvcConfigEceEtypeMask OBJECT-TYPE
    SYNTAX      VTSSUnsigned16
    MAX-ACCESS  read-write
    STATUS      current
    DESCRIPTION 
        "The Ethernet Type mask.
         
         This object is only available if the capability object
         'vtssEvcCapabilitiesHasEceEtype' is True."
    ::= { vtssEvcConfigEceEntry 101 }

vtssEvcConfigEceEtypeData OBJECT-TYPE
    SYNTAX      VTSSUnsigned16
    MAX-ACCESS  read-write
    STATUS      current
    DESCRIPTION 
        "The Ethernet Type data to match.
         
         This object is only available if the capability object
         'vtssEvcCapabilitiesHasEceEtype' is True."
    ::= { vtssEvcConfigEceEntry 102 }

vtssEvcConfigEceEtypeDataMask OBJECT-TYPE
    SYNTAX      VTSSUnsigned16
    MAX-ACCESS  read-write
    STATUS      current
    DESCRIPTION 
        "The Ethernet Type data mask.
         
         This object is only available if the capability object
         'vtssEvcCapabilitiesHasEceEtype' is True."
    ::= { vtssEvcConfigEceEntry 103 }

vtssEvcConfigEceLlcDsap OBJECT-TYPE
    SYNTAX      VTSSUnsigned8
    MAX-ACCESS  read-write
    STATUS      current
    DESCRIPTION 
        "The LLC DSAP field to match.
         
         This object is only available if the capability object
         'vtssEvcCapabilitiesHasEceLlc' is True."
    ::= { vtssEvcConfigEceEntry 200 }

vtssEvcConfigEceLlcDsapMask OBJECT-TYPE
    SYNTAX      VTSSUnsigned8
    MAX-ACCESS  read-write
    STATUS      current
    DESCRIPTION 
        "The LLC DSAP mask.
         
         This object is only available if the capability object
         'vtssEvcCapabilitiesHasEceLlc' is True."
    ::= { vtssEvcConfigEceEntry 201 }

vtssEvcConfigEceLlcSsap OBJECT-TYPE
    SYNTAX      VTSSUnsigned8
    MAX-ACCESS  read-write
    STATUS      current
    DESCRIPTION 
        "The LLC SSAP field to match.
         
         This object is only available if the capability object
         'vtssEvcCapabilitiesHasEceLlc' is True."
    ::= { vtssEvcConfigEceEntry 202 }

vtssEvcConfigEceLlcSsapMask OBJECT-TYPE
    SYNTAX      VTSSUnsigned8
    MAX-ACCESS  read-write
    STATUS      current
    DESCRIPTION 
        "The LLC SSAP mask.
         
         This object is only available if the capability object
         'vtssEvcCapabilitiesHasEceLlc' is True."
    ::= { vtssEvcConfigEceEntry 203 }

vtssEvcConfigEceLlcControl OBJECT-TYPE
    SYNTAX      VTSSUnsigned8
    MAX-ACCESS  read-write
    STATUS      current
    DESCRIPTION 
        "The LLC Control field to match.
         
         This object is only available if the capability object
         'vtssEvcCapabilitiesHasEceLlc' is True."
    ::= { vtssEvcConfigEceEntry 204 }

vtssEvcConfigEceLlcControlMask OBJECT-TYPE
    SYNTAX      VTSSUnsigned8
    MAX-ACCESS  read-write
    STATUS      current
    DESCRIPTION 
        "The LLC Control mask.
         
         This object is only available if the capability object
         'vtssEvcCapabilitiesHasEceLlc' is True."
    ::= { vtssEvcConfigEceEntry 205 }

vtssEvcConfigEceLlcPid OBJECT-TYPE
    SYNTAX      VTSSUnsigned16
    MAX-ACCESS  read-write
    STATUS      current
    DESCRIPTION 
        "The LLC Protocol ID to match.
         
         This object is only available if the capability object
         'vtssEvcCapabilitiesHasEceLlc' is True."
    ::= { vtssEvcConfigEceEntry 206 }

vtssEvcConfigEceLlcPidMask OBJECT-TYPE
    SYNTAX      VTSSUnsigned16
    MAX-ACCESS  read-write
    STATUS      current
    DESCRIPTION 
        "The LLC Protocol ID mask.
         
         This object is only available if the capability object
         'vtssEvcCapabilitiesHasEceLlc' is True."
    ::= { vtssEvcConfigEceEntry 207 }

vtssEvcConfigEceSnapOui OBJECT-TYPE
    SYNTAX      Unsigned32
    MAX-ACCESS  read-write
    STATUS      current
    DESCRIPTION 
        "The SNAP OUI to match.
         
         This object is only available if the capability object
         'vtssEvcCapabilitiesHasEceSnap' is True."
    ::= { vtssEvcConfigEceEntry 300 }

vtssEvcConfigEceSnapOuiMask OBJECT-TYPE
    SYNTAX      Unsigned32
    MAX-ACCESS  read-write
    STATUS      current
    DESCRIPTION 
        "The SNAP OUI mask.
         
         This object is only available if the capability object
         'vtssEvcCapabilitiesHasEceSnap' is True."
    ::= { vtssEvcConfigEceEntry 301 }

vtssEvcConfigEceSnapPid OBJECT-TYPE
    SYNTAX      VTSSUnsigned16
    MAX-ACCESS  read-write
    STATUS      current
    DESCRIPTION 
        "The SNAP Protocol ID to match.
         
         This object is only available if the capability object
         'vtssEvcCapabilitiesHasEceSnap' is True."
    ::= { vtssEvcConfigEceEntry 302 }

vtssEvcConfigEceSnapPidMask OBJECT-TYPE
    SYNTAX      VTSSUnsigned16
    MAX-ACCESS  read-write
    STATUS      current
    DESCRIPTION 
        "The SNAP Protocol ID mask.
         
         This object is only available if the capability object
         'vtssEvcCapabilitiesHasEceSnap' is True."
    ::= { vtssEvcConfigEceEntry 303 }

vtssEvcConfigEceL2cpType OBJECT-TYPE
    SYNTAX      VTSSevcL2cpType
    MAX-ACCESS  read-write
    STATUS      current
    DESCRIPTION 
        "The L2CP type to match. The value 'none' is not valid for SET
         operations.
         
         This object is only available if the capability object
         'vtssEvcCapabilitiesHasEceL2cp' is True."
    ::= { vtssEvcConfigEceEntry 400 }

vtssEvcConfigEceIpv4Dscp OBJECT-TYPE
    SYNTAX      Unsigned32
    MAX-ACCESS  read-write
    STATUS      current
    DESCRIPTION 
        "The IPv4 DSCP range to match. The minimum value is encoded in the 16
         least significant bits. The maximum value is encoded in the 16 most
         significant bits."
    ::= { vtssEvcConfigEceEntry 500 }

vtssEvcConfigEceIpv4Proto OBJECT-TYPE
    SYNTAX      VTSSUnsigned8
    MAX-ACCESS  read-write
    STATUS      current
    DESCRIPTION 
        "The IPv4 protocol number to match.
         
         This object is only available if the capability object
         'vtssEvcCapabilitiesHasEceIpProto' is True."
    ::= { vtssEvcConfigEceEntry 501 }

vtssEvcConfigEceIpv4ProtoMask OBJECT-TYPE
    SYNTAX      VTSSUnsigned8
    MAX-ACCESS  read-write
    STATUS      current
    DESCRIPTION 
        "The IPv4 protocol mask.
         
         This object is only available if the capability object
         'vtssEvcCapabilitiesHasEceIpProto' is True."
    ::= { vtssEvcConfigEceEntry 502 }

vtssEvcConfigEceIpv4Fragment OBJECT-TYPE
    SYNTAX      VTSSBitType
    MAX-ACCESS  read-write
    STATUS      current
    DESCRIPTION 
        "The IPv4 fragment match.
         
         This object is only available if the capability object
         'vtssEvcCapabilitiesHasEceIpv4Fragment' is True."
    ::= { vtssEvcConfigEceEntry 503 }

vtssEvcConfigEceIpv4SrcIp OBJECT-TYPE
    SYNTAX      IpAddress
    MAX-ACCESS  read-write
    STATUS      current
    DESCRIPTION 
        "The IPv4 source address.
         
         This object is only available if the capability object
         'vtssEvcCapabilitiesHasEceSrcIp' is True."
    ::= { vtssEvcConfigEceEntry 504 }

vtssEvcConfigEceIpv4SrcIpMask OBJECT-TYPE
    SYNTAX      IpAddress
    MAX-ACCESS  read-write
    STATUS      current
    DESCRIPTION 
        "The IPv4 source address mask.
         
         This object is only available if the capability object
         'vtssEvcCapabilitiesHasEceSrcIp' is True."
    ::= { vtssEvcConfigEceEntry 505 }

vtssEvcConfigEceIpv4DestIp OBJECT-TYPE
    SYNTAX      IpAddress
    MAX-ACCESS  read-write
    STATUS      current
    DESCRIPTION 
        "The IPv4 destination address.
         
         This object is only available if the capability object
         'vtssEvcCapabilitiesHasEceDestIp' is True."
    ::= { vtssEvcConfigEceEntry 506 }

vtssEvcConfigEceIpv4DestIpMask OBJECT-TYPE
    SYNTAX      IpAddress
    MAX-ACCESS  read-write
    STATUS      current
    DESCRIPTION 
        "The IPv4 destination address mask.
         
         This object is only available if the capability object
         'vtssEvcCapabilitiesHasEceDestIp' is True."
    ::= { vtssEvcConfigEceEntry 507 }

vtssEvcConfigEceIpv4SrcPort OBJECT-TYPE
    SYNTAX      Unsigned32
    MAX-ACCESS  read-write
    STATUS      current
    DESCRIPTION 
        "The IPv4 UDP/TCP source port range to match. The minimum value is
         encoded in the 16 least significant bits. The maximum value is encoded
         in the 16 most significant bits.
         
         This object is only available if the capability object
         'vtssEvcCapabilitiesHasEceSrcPort' is True."
    ::= { vtssEvcConfigEceEntry 508 }

vtssEvcConfigEceIpv4DestPort OBJECT-TYPE
    SYNTAX      Unsigned32
    MAX-ACCESS  read-write
    STATUS      current
    DESCRIPTION 
        "The IPv4 UDP/TCP destination port range to match. The minimum value is
         encoded in the 16 least significant bits. The maximum value is encoded
         in the 16 most significant bits.
         
         This object is only available if the capability object
         'vtssEvcCapabilitiesHasEceDestPort' is True."
    ::= { vtssEvcConfigEceEntry 509 }

vtssEvcConfigEceIpv6Dscp OBJECT-TYPE
    SYNTAX      Unsigned32
    MAX-ACCESS  read-write
    STATUS      current
    DESCRIPTION 
        "The IPv6 DSCP range to match. The minimum value is encoded in the 16
         least significant bits. The maximum value is encoded in the 16 most
         significant bits."
    ::= { vtssEvcConfigEceEntry 600 }

vtssEvcConfigEceIpv6Proto OBJECT-TYPE
    SYNTAX      VTSSUnsigned8
    MAX-ACCESS  read-write
    STATUS      current
    DESCRIPTION 
        "The IPv6 protocol number to match.
         
         This object is only available if the capability object
         'vtssEvcCapabilitiesHasEceIpProto' is True."
    ::= { vtssEvcConfigEceEntry 601 }

vtssEvcConfigEceIpv6ProtoMask OBJECT-TYPE
    SYNTAX      VTSSUnsigned8
    MAX-ACCESS  read-write
    STATUS      current
    DESCRIPTION 
        "The IPv6 protocol mask.
         
         This object is only available if the capability object
         'vtssEvcCapabilitiesHasEceIpProto' is True."
    ::= { vtssEvcConfigEceEntry 602 }

vtssEvcConfigEceIpv6SrcIp OBJECT-TYPE
    SYNTAX      InetAddressIPv6
    MAX-ACCESS  read-write
    STATUS      current
    DESCRIPTION 
        "The IPv6 source address.
         
         This object is only available if the capability object
         'vtssEvcCapabilitiesHasEceSrcIp' is True."
    ::= { vtssEvcConfigEceEntry 603 }

vtssEvcConfigEceIpv6SrcIpMask OBJECT-TYPE
    SYNTAX      InetAddressIPv6
    MAX-ACCESS  read-write
    STATUS      current
    DESCRIPTION 
        "The IPv6 source address mask.
         
         This object is only available if the capability object
         'vtssEvcCapabilitiesHasEceSrcIp' is True."
    ::= { vtssEvcConfigEceEntry 604 }

vtssEvcConfigEceIpv6DestIp OBJECT-TYPE
    SYNTAX      InetAddressIPv6
    MAX-ACCESS  read-write
    STATUS      current
    DESCRIPTION 
        "The IPv6 destination address.
         
         This object is only available if the capability object
         'vtssEvcCapabilitiesHasEceDestIp' is True."
    ::= { vtssEvcConfigEceEntry 605 }

vtssEvcConfigEceIpv6DestIpMask OBJECT-TYPE
    SYNTAX      InetAddressIPv6
    MAX-ACCESS  read-write
    STATUS      current
    DESCRIPTION 
        "The IPv6 destination address mask.
         
         This object is only available if the capability object
         'vtssEvcCapabilitiesHasEceDestIp' is True."
    ::= { vtssEvcConfigEceEntry 606 }

vtssEvcConfigEceIpv6SrcPort OBJECT-TYPE
    SYNTAX      Unsigned32
    MAX-ACCESS  read-write
    STATUS      current
    DESCRIPTION 
        "The IPv6 UDP/TCP source port range to match. The minimum value is
         encoded in the 16 least significant bits. The maximum value is encoded
         in the 16 most significant bits.
         
         This object is only available if the capability object
         'vtssEvcCapabilitiesHasEceSrcPort' is True."
    ::= { vtssEvcConfigEceEntry 607 }

vtssEvcConfigEceIpv6DestPort OBJECT-TYPE
    SYNTAX      Unsigned32
    MAX-ACCESS  read-write
    STATUS      current
    DESCRIPTION 
        "The IPv6 UDP/TCP destination port range to match. The minimum value is
         encoded in the 16 least significant bits. The maximum value is encoded
         in the 16 most significant bits.
         
         This object is only available if the capability object
         'vtssEvcCapabilitiesHasEceDestPort' is True."
    ::= { vtssEvcConfigEceEntry 608 }

vtssEvcConfigEceDirection OBJECT-TYPE
    SYNTAX      VTSSevcDirection
    MAX-ACCESS  read-write
    STATUS      current
    DESCRIPTION 
        "The ECE direction."
    ::= { vtssEvcConfigEceEntry 1000 }

vtssEvcConfigEceRuleType OBJECT-TYPE
    SYNTAX      VTSSevcRuleType
    MAX-ACCESS  read-write
    STATUS      current
    DESCRIPTION 
        "The ECE rule type.
         
         This object is only available if the capability object
         'vtssEvcCapabilitiesHasEceRuleType' is True."
    ::= { vtssEvcConfigEceEntry 1010 }

vtssEvcConfigEceTxLookup OBJECT-TYPE
    SYNTAX      VTSSevcTxLookup
    MAX-ACCESS  read-write
    STATUS      current
    DESCRIPTION 
        "The egress lookup key type.
         
         This object is only available if the capability object
         'vtssEvcCapabilitiesHasEceTxLookup' is True."
    ::= { vtssEvcConfigEceEntry 1011 }

vtssEvcConfigEcePopTag OBJECT-TYPE
    SYNTAX      VTSSevcPopTag
    MAX-ACCESS  read-write
    STATUS      current
    DESCRIPTION 
        "The number of tags popped."
    ::= { vtssEvcConfigEceEntry 1020 }

vtssEvcConfigEceOtAddEnable OBJECT-TYPE
    SYNTAX      TruthValue
    MAX-ACCESS  read-write
    STATUS      current
    DESCRIPTION 
        "Enable outer tag pushing for NNI-to-UNI direction."
    ::= { vtssEvcConfigEceEntry 1100 }

vtssEvcConfigEceOtAddVid OBJECT-TYPE
    SYNTAX      VTSSUnsigned16
    MAX-ACCESS  read-write
    STATUS      current
    DESCRIPTION 
        "The VLAN ID pushed for NNI-to-UNI direction.
         
         This object is only available if the capability object
         'vtssEvcCapabilitiesHasEceOtAddVid' is True."
    ::= { vtssEvcConfigEceEntry 1101 }

vtssEvcConfigEceOtAddPcpMode OBJECT-TYPE
    SYNTAX      VTSSevcPcpMode
    MAX-ACCESS  read-write
    STATUS      current
    DESCRIPTION 
        "The PCP mode for the outer tag pushed.
         
         This object is only available if the capability object
         'vtssEvcCapabilitiesHasEcePcpMode' is True."
    ::= { vtssEvcConfigEceEntry 1102 }

vtssEvcConfigEceOtAddPcpDeiPreserve OBJECT-TYPE
    SYNTAX      TruthValue
    MAX-ACCESS  read-write
    STATUS      current
    DESCRIPTION 
        "Enable PCP/DEI preservation for the outer tag pushed.
         
         This object is only available if the capability object
         'vtssEvcCapabilitiesHasEcePcpDeiPreserve' is True."
    ::= { vtssEvcConfigEceEntry 1103 }

vtssEvcConfigEceOtAddPcp OBJECT-TYPE
    SYNTAX      Unsigned32
    MAX-ACCESS  read-write
    STATUS      current
    DESCRIPTION 
        "The PCP value for the outer tag pushed."
    ::= { vtssEvcConfigEceEntry 1104 }

vtssEvcConfigEceOtAddDeiMode OBJECT-TYPE
    SYNTAX      VTSSevcDeiMode
    MAX-ACCESS  read-write
    STATUS      current
    DESCRIPTION 
        "The DEI mode for the outer tag pushed.
         
         This object is only available if the capability object
         'vtssEvcCapabilitiesHasEceDeiMode' is True."
    ::= { vtssEvcConfigEceEntry 1105 }

vtssEvcConfigEceOtAddDei OBJECT-TYPE
    SYNTAX      VTSSUnsigned8
    MAX-ACCESS  read-write
    STATUS      current
    DESCRIPTION 
        "The DEI value for the outer tag pushed."
    ::= { vtssEvcConfigEceEntry 1106 }

vtssEvcConfigEceItAddType OBJECT-TYPE
    SYNTAX      VTSSevcInnerTagType
    MAX-ACCESS  read-write
    STATUS      current
    DESCRIPTION 
        "The tag type for the inner tag pushed.
         
         This object is only available if the capability object
         'vtssEvcCapabilitiesHasEceItAdd' is True."
    ::= { vtssEvcConfigEceEntry 1200 }

vtssEvcConfigEceItAddVid OBJECT-TYPE
    SYNTAX      VTSSUnsigned16
    MAX-ACCESS  read-write
    STATUS      current
    DESCRIPTION 
        "The VLAN ID for the inner tag pushed.
         
         This object is only available if the capability object
         'vtssEvcCapabilitiesHasEceItAdd' is True."
    ::= { vtssEvcConfigEceEntry 1201 }

vtssEvcConfigEceItAddPcpMode OBJECT-TYPE
    SYNTAX      VTSSevcPcpMode
    MAX-ACCESS  read-write
    STATUS      current
    DESCRIPTION 
        "The PCP mode for the inner tag pushed.
         
         This object is only available if the capability object
         'vtssEvcCapabilitiesHasEcePcpMode' is True."
    ::= { vtssEvcConfigEceEntry 1202 }

vtssEvcConfigEceItAddPcpDeiPreserve OBJECT-TYPE
    SYNTAX      TruthValue
    MAX-ACCESS  read-write
    STATUS      current
    DESCRIPTION 
        "Enable PCP/DEI preservation for the inner tag pushed.
         
         This object is only available if the capability object
         'vtssEvcCapabilitiesHasEcePcpDeiPreserve' is True."
    ::= { vtssEvcConfigEceEntry 1203 }

vtssEvcConfigEceItAddPcp OBJECT-TYPE
    SYNTAX      Unsigned32
    MAX-ACCESS  read-write
    STATUS      current
    DESCRIPTION 
        "The PCP value for the inner tag pushed.
         
         This object is only available if the capability object
         'vtssEvcCapabilitiesHasEceItAdd' is True."
    ::= { vtssEvcConfigEceEntry 1204 }

vtssEvcConfigEceItAddDeiMode OBJECT-TYPE
    SYNTAX      VTSSevcDeiMode
    MAX-ACCESS  read-write
    STATUS      current
    DESCRIPTION 
        "The DEI mode for the inner tag pushed.
         
         This object is only available if the capability object
         'vtssEvcCapabilitiesHasEceDeiMode' is True."
    ::= { vtssEvcConfigEceEntry 1205 }

vtssEvcConfigEceItAddDei OBJECT-TYPE
    SYNTAX      VTSSUnsigned8
    MAX-ACCESS  read-write
    STATUS      current
    DESCRIPTION 
        "The DEI value for the inner tag pushed.
         
         This object is only available if the capability object
         'vtssEvcCapabilitiesHasEceItAdd' is True."
    ::= { vtssEvcConfigEceEntry 1206 }

vtssEvcConfigEceEvcId OBJECT-TYPE
    SYNTAX      VTSSUnsigned16
    MAX-ACCESS  read-write
    STATUS      current
    DESCRIPTION 
        "The EVC ID for the ECE."
    ::= { vtssEvcConfigEceEntry 1300 }

vtssEvcConfigEcePolicerOp OBJECT-TYPE
    SYNTAX      VTSSevcPolicerOp
    MAX-ACCESS  read-write
    STATUS      current
    DESCRIPTION 
        "The policer operator for the ECE.
         
         This object is only available if the capability object
         'vtssEvcCapabilitiesHasEcePolicer' is True."
    ::= { vtssEvcConfigEceEntry 1301 }

vtssEvcConfigEcePolicerId OBJECT-TYPE
    SYNTAX      VTSSUnsigned16
    MAX-ACCESS  read-write
    STATUS      current
    DESCRIPTION 
        "The policer ID for the ECE.
         
         This object is only available if the capability object
         'vtssEvcCapabilitiesHasEcePolicer' is True."
    ::= { vtssEvcConfigEceEntry 1302 }

vtssEvcConfigEcePolicyNo OBJECT-TYPE
    SYNTAX      Unsigned32
    MAX-ACCESS  read-write
    STATUS      current
    DESCRIPTION 
        "The ACL policy number for the ECE."
    ::= { vtssEvcConfigEceEntry 1310 }

vtssEvcConfigEceCosEnable OBJECT-TYPE
    SYNTAX      TruthValue
    MAX-ACCESS  read-write
    STATUS      current
    DESCRIPTION 
        "Enable CoS assignment.
         
         This object is only available if the capability object
         'vtssEvcCapabilitiesHasEceCos' is True."
    ::= { vtssEvcConfigEceEntry 1320 }

vtssEvcConfigEceCos OBJECT-TYPE
    SYNTAX      Unsigned32
    MAX-ACCESS  read-write
    STATUS      current
    DESCRIPTION 
        "The CoS value for the ECE.
         
         This object is only available if the capability object
         'vtssEvcCapabilitiesHasEceCos' is True."
    ::= { vtssEvcConfigEceEntry 1321 }

vtssEvcConfigEceDpEnable OBJECT-TYPE
    SYNTAX      TruthValue
    MAX-ACCESS  read-write
    STATUS      current
    DESCRIPTION 
        "Enable Drop Precendence assignment.
         
         This object is only available if the capability object
         'vtssEvcCapabilitiesHasEceDp' is True."
    ::= { vtssEvcConfigEceEntry 1330 }

vtssEvcConfigEceDp OBJECT-TYPE
    SYNTAX      VTSSUnsigned8
    MAX-ACCESS  read-write
    STATUS      current
    DESCRIPTION 
        "The Drop Precedence value for the ECE.
         
         This object is only available if the capability object
         'vtssEvcCapabilitiesHasEceDp' is True."
    ::= { vtssEvcConfigEceEntry 1331 }

vtssEvcConfigEceL2cpMode OBJECT-TYPE
    SYNTAX      VTSSevcEceL2cpMode
    MAX-ACCESS  read-write
    STATUS      current
    DESCRIPTION 
        "The L2CP forward mode for the ECE.
         
         This object is only available if the capability object
         'vtssEvcCapabilitiesHasEceL2cp' is True."
    ::= { vtssEvcConfigEceEntry 1332 }

vtssEvcConfigEceL2cpDmac OBJECT-TYPE
    SYNTAX      VTSSevcL2cpDmac
    MAX-ACCESS  read-write
    STATUS      current
    DESCRIPTION 
        "The DMAC used for L2CP tunneling for the ECE.
         
         This object is only available if the capability object
         'vtssEvcCapabilitiesHasEceL2cp' is True."
    ::= { vtssEvcConfigEceEntry 1333 }

vtssEvcConfigEceAction OBJECT-TYPE
    SYNTAX      VTSSRowEditorState
    MAX-ACCESS  read-write
    STATUS      current
    DESCRIPTION 
        "Action"
    ::= { vtssEvcConfigEceEntry 10000 }

vtssEvcConfigEceTableRowEditor OBJECT IDENTIFIER
    ::= { vtssEvcConfigEce 2 }

vtssEvcConfigEceTableRowEditorEceId OBJECT-TYPE
    SYNTAX      Integer32 (1..4096)
    MAX-ACCESS  read-write
    STATUS      current
    DESCRIPTION 
        "ECE ID, allowed range is [1,EceMax]."
    ::= { vtssEvcConfigEceTableRowEditor 1 }

vtssEvcConfigEceTableRowEditorNextId OBJECT-TYPE
    SYNTAX      Unsigned32
    MAX-ACCESS  read-write
    STATUS      current
    DESCRIPTION 
        "The ID of the next ECE."
    ::= { vtssEvcConfigEceTableRowEditor 2 }

vtssEvcConfigEceTableRowEditorAdvLookup OBJECT-TYPE
    SYNTAX      TruthValue
    MAX-ACCESS  read-write
    STATUS      current
    DESCRIPTION 
        "Enable advanced ingress lookup.
         
         This object is only available if the capability object
         'vtssEvcCapabilitiesHasEceAdvLookup' is True."
    ::= { vtssEvcConfigEceTableRowEditor 3 }

vtssEvcConfigEceTableRowEditorUniPortList OBJECT-TYPE
    SYNTAX      VTSSPortList
    MAX-ACCESS  read-write
    STATUS      current
    DESCRIPTION 
        "List of UNI ports for the ECE."
    ::= { vtssEvcConfigEceTableRowEditor 4 }

vtssEvcConfigEceTableRowEditorSrcMac OBJECT-TYPE
    SYNTAX      MacAddress
    MAX-ACCESS  read-write
    STATUS      current
    DESCRIPTION 
        "The source MAC address to match.
         
         This object is only available if the capability object
         'vtssEvcCapabilitiesHasEceSrcMac' is True."
    ::= { vtssEvcConfigEceTableRowEditor 10 }

vtssEvcConfigEceTableRowEditorSrcMacMask OBJECT-TYPE
    SYNTAX      MacAddress
    MAX-ACCESS  read-write
    STATUS      current
    DESCRIPTION 
        "The source MAC address mask.
         
         This object is only available if the capability object
         'vtssEvcCapabilitiesHasEceSrcMac' is True."
    ::= { vtssEvcConfigEceTableRowEditor 11 }

vtssEvcConfigEceTableRowEditorDestMacType OBJECT-TYPE
    SYNTAX      VTSSDestMacType
    MAX-ACCESS  read-write
    STATUS      current
    DESCRIPTION 
        "The destination MAC address type to match.
         
         This object is only available if the capability object
         'vtssEvcCapabilitiesHasEceDestMacType' is True."
    ::= { vtssEvcConfigEceTableRowEditor 12 }

vtssEvcConfigEceTableRowEditorDestMac OBJECT-TYPE
    SYNTAX      MacAddress
    MAX-ACCESS  read-write
    STATUS      current
    DESCRIPTION 
        "The destination MAC address to match.
         
         This object is only available if the capability object
         'vtssEvcCapabilitiesHasEceDestMac' is True."
    ::= { vtssEvcConfigEceTableRowEditor 13 }

vtssEvcConfigEceTableRowEditorDestMacMask OBJECT-TYPE
    SYNTAX      MacAddress
    MAX-ACCESS  read-write
    STATUS      current
    DESCRIPTION 
        "The destination MAC address mask.
         
         This object is only available if the capability object
         'vtssEvcCapabilitiesHasEceDestMac' is True."
    ::= { vtssEvcConfigEceTableRowEditor 14 }

vtssEvcConfigEceTableRowEditorOtMatchType OBJECT-TYPE
    SYNTAX      VTSSVlanTagType
    MAX-ACCESS  read-write
    STATUS      current
    DESCRIPTION 
        "The outer tag type to match."
    ::= { vtssEvcConfigEceTableRowEditor 20 }

vtssEvcConfigEceTableRowEditorOtMatchVid OBJECT-TYPE
    SYNTAX      Unsigned32
    MAX-ACCESS  read-write
    STATUS      current
    DESCRIPTION 
        "The outer tag VLAN ID range to match. The minimum value is encoded in
         the 16 least significant bits. The maximum value is encoded in the 16
         most significant bits."
    ::= { vtssEvcConfigEceTableRowEditor 21 }

vtssEvcConfigEceTableRowEditorOtMatchPcp OBJECT-TYPE
    SYNTAX      VTSSVlanTagPriority
    MAX-ACCESS  read-write
    STATUS      current
    DESCRIPTION 
        "The outer tag PCP to match."
    ::= { vtssEvcConfigEceTableRowEditor 22 }

vtssEvcConfigEceTableRowEditorOtMatchDei OBJECT-TYPE
    SYNTAX      VTSSBitType
    MAX-ACCESS  read-write
    STATUS      current
    DESCRIPTION 
        "The outer tag DEI to match."
    ::= { vtssEvcConfigEceTableRowEditor 23 }

vtssEvcConfigEceTableRowEditorItMatchType OBJECT-TYPE
    SYNTAX      VTSSVlanTagType
    MAX-ACCESS  read-write
    STATUS      current
    DESCRIPTION 
        "The inner tag type to match.
         
         This object is only available if the capability object
         'vtssEvcCapabilitiesHasEceInnerTag' is True."
    ::= { vtssEvcConfigEceTableRowEditor 30 }

vtssEvcConfigEceTableRowEditorItMatchVid OBJECT-TYPE
    SYNTAX      Unsigned32
    MAX-ACCESS  read-write
    STATUS      current
    DESCRIPTION 
        "The inner tag VLAN ID range to match. The minimum value is encoded in
         the 16 least significant bits. The maximum value is encoded in the 16
         most significant bits.
         
         This object is only available if the capability object
         'vtssEvcCapabilitiesHasEceInnerTag' is True."
    ::= { vtssEvcConfigEceTableRowEditor 31 }

vtssEvcConfigEceTableRowEditorItMatchPcp OBJECT-TYPE
    SYNTAX      VTSSVlanTagPriority
    MAX-ACCESS  read-write
    STATUS      current
    DESCRIPTION 
        "The inner tag PCP to match.
         
         This object is only available if the capability object
         'vtssEvcCapabilitiesHasEceInnerTag' is True."
    ::= { vtssEvcConfigEceTableRowEditor 32 }

vtssEvcConfigEceTableRowEditorItMatchDei OBJECT-TYPE
    SYNTAX      VTSSBitType
    MAX-ACCESS  read-write
    STATUS      current
    DESCRIPTION 
        "The inner tag DEI to match.
         
         This object is only available if the capability object
         'vtssEvcCapabilitiesHasEceInnerTag' is True."
    ::= { vtssEvcConfigEceTableRowEditor 33 }

vtssEvcConfigEceTableRowEditorFrameType OBJECT-TYPE
    SYNTAX      VTSSevcFrameType
    MAX-ACCESS  read-write
    STATUS      current
    DESCRIPTION 
        "The ECE frame type."
    ::= { vtssEvcConfigEceTableRowEditor 50 }

vtssEvcConfigEceTableRowEditorEtype OBJECT-TYPE
    SYNTAX      VTSSUnsigned16
    MAX-ACCESS  read-write
    STATUS      current
    DESCRIPTION 
        "The Ethernet Type to match.
         
         This object is only available if the capability object
         'vtssEvcCapabilitiesHasEceEtype' is True."
    ::= { vtssEvcConfigEceTableRowEditor 100 }

vtssEvcConfigEceTableRowEditorEtypeMask OBJECT-TYPE
    SYNTAX      VTSSUnsigned16
    MAX-ACCESS  read-write
    STATUS      current
    DESCRIPTION 
        "The Ethernet Type mask.
         
         This object is only available if the capability object
         'vtssEvcCapabilitiesHasEceEtype' is True."
    ::= { vtssEvcConfigEceTableRowEditor 101 }

vtssEvcConfigEceTableRowEditorEtypeData OBJECT-TYPE
    SYNTAX      VTSSUnsigned16
    MAX-ACCESS  read-write
    STATUS      current
    DESCRIPTION 
        "The Ethernet Type data to match.
         
         This object is only available if the capability object
         'vtssEvcCapabilitiesHasEceEtype' is True."
    ::= { vtssEvcConfigEceTableRowEditor 102 }

vtssEvcConfigEceTableRowEditorEtypeDataMask OBJECT-TYPE
    SYNTAX      VTSSUnsigned16
    MAX-ACCESS  read-write
    STATUS      current
    DESCRIPTION 
        "The Ethernet Type data mask.
         
         This object is only available if the capability object
         'vtssEvcCapabilitiesHasEceEtype' is True."
    ::= { vtssEvcConfigEceTableRowEditor 103 }

vtssEvcConfigEceTableRowEditorLlcDsap OBJECT-TYPE
    SYNTAX      VTSSUnsigned8
    MAX-ACCESS  read-write
    STATUS      current
    DESCRIPTION 
        "The LLC DSAP field to match.
         
         This object is only available if the capability object
         'vtssEvcCapabilitiesHasEceLlc' is True."
    ::= { vtssEvcConfigEceTableRowEditor 200 }

vtssEvcConfigEceTableRowEditorLlcDsapMask OBJECT-TYPE
    SYNTAX      VTSSUnsigned8
    MAX-ACCESS  read-write
    STATUS      current
    DESCRIPTION 
        "The LLC DSAP mask.
         
         This object is only available if the capability object
         'vtssEvcCapabilitiesHasEceLlc' is True."
    ::= { vtssEvcConfigEceTableRowEditor 201 }

vtssEvcConfigEceTableRowEditorLlcSsap OBJECT-TYPE
    SYNTAX      VTSSUnsigned8
    MAX-ACCESS  read-write
    STATUS      current
    DESCRIPTION 
        "The LLC SSAP field to match.
         
         This object is only available if the capability object
         'vtssEvcCapabilitiesHasEceLlc' is True."
    ::= { vtssEvcConfigEceTableRowEditor 202 }

vtssEvcConfigEceTableRowEditorLlcSsapMask OBJECT-TYPE
    SYNTAX      VTSSUnsigned8
    MAX-ACCESS  read-write
    STATUS      current
    DESCRIPTION 
        "The LLC SSAP mask.
         
         This object is only available if the capability object
         'vtssEvcCapabilitiesHasEceLlc' is True."
    ::= { vtssEvcConfigEceTableRowEditor 203 }

vtssEvcConfigEceTableRowEditorLlcControl OBJECT-TYPE
    SYNTAX      VTSSUnsigned8
    MAX-ACCESS  read-write
    STATUS      current
    DESCRIPTION 
        "The LLC Control field to match.
         
         This object is only available if the capability object
         'vtssEvcCapabilitiesHasEceLlc' is True."
    ::= { vtssEvcConfigEceTableRowEditor 204 }

vtssEvcConfigEceTableRowEditorLlcControlMask OBJECT-TYPE
    SYNTAX      VTSSUnsigned8
    MAX-ACCESS  read-write
    STATUS      current
    DESCRIPTION 
        "The LLC Control mask.
         
         This object is only available if the capability object
         'vtssEvcCapabilitiesHasEceLlc' is True."
    ::= { vtssEvcConfigEceTableRowEditor 205 }

vtssEvcConfigEceTableRowEditorLlcPid OBJECT-TYPE
    SYNTAX      VTSSUnsigned16
    MAX-ACCESS  read-write
    STATUS      current
    DESCRIPTION 
        "The LLC Protocol ID to match.
         
         This object is only available if the capability object
         'vtssEvcCapabilitiesHasEceLlc' is True."
    ::= { vtssEvcConfigEceTableRowEditor 206 }

vtssEvcConfigEceTableRowEditorLlcPidMask OBJECT-TYPE
    SYNTAX      VTSSUnsigned16
    MAX-ACCESS  read-write
    STATUS      current
    DESCRIPTION 
        "The LLC Protocol ID mask.
         
         This object is only available if the capability object
         'vtssEvcCapabilitiesHasEceLlc' is True."
    ::= { vtssEvcConfigEceTableRowEditor 207 }

vtssEvcConfigEceTableRowEditorSnapOui OBJECT-TYPE
    SYNTAX      Unsigned32
    MAX-ACCESS  read-write
    STATUS      current
    DESCRIPTION 
        "The SNAP OUI to match.
         
         This object is only available if the capability object
         'vtssEvcCapabilitiesHasEceSnap' is True."
    ::= { vtssEvcConfigEceTableRowEditor 300 }

vtssEvcConfigEceTableRowEditorSnapOuiMask OBJECT-TYPE
    SYNTAX      Unsigned32
    MAX-ACCESS  read-write
    STATUS      current
    DESCRIPTION 
        "The SNAP OUI mask.
         
         This object is only available if the capability object
         'vtssEvcCapabilitiesHasEceSnap' is True."
    ::= { vtssEvcConfigEceTableRowEditor 301 }

vtssEvcConfigEceTableRowEditorSnapPid OBJECT-TYPE
    SYNTAX      VTSSUnsigned16
    MAX-ACCESS  read-write
    STATUS      current
    DESCRIPTION 
        "The SNAP Protocol ID to match.
         
         This object is only available if the capability object
         'vtssEvcCapabilitiesHasEceSnap' is True."
    ::= { vtssEvcConfigEceTableRowEditor 302 }

vtssEvcConfigEceTableRowEditorSnapPidMask OBJECT-TYPE
    SYNTAX      VTSSUnsigned16
    MAX-ACCESS  read-write
    STATUS      current
    DESCRIPTION 
        "The SNAP Protocol ID mask.
         
         This object is only available if the capability object
         'vtssEvcCapabilitiesHasEceSnap' is True."
    ::= { vtssEvcConfigEceTableRowEditor 303 }

vtssEvcConfigEceTableRowEditorL2cpType OBJECT-TYPE
    SYNTAX      VTSSevcL2cpType
    MAX-ACCESS  read-write
    STATUS      current
    DESCRIPTION 
        "The L2CP type to match. The value 'none' is not valid for SET
         operations.
         
         This object is only available if the capability object
         'vtssEvcCapabilitiesHasEceL2cp' is True."
    ::= { vtssEvcConfigEceTableRowEditor 400 }

vtssEvcConfigEceTableRowEditorIpv4Dscp OBJECT-TYPE
    SYNTAX      Unsigned32
    MAX-ACCESS  read-write
    STATUS      current
    DESCRIPTION 
        "The IPv4 DSCP range to match. The minimum value is encoded in the 16
         least significant bits. The maximum value is encoded in the 16 most
         significant bits."
    ::= { vtssEvcConfigEceTableRowEditor 500 }

vtssEvcConfigEceTableRowEditorIpv4Proto OBJECT-TYPE
    SYNTAX      VTSSUnsigned8
    MAX-ACCESS  read-write
    STATUS      current
    DESCRIPTION 
        "The IPv4 protocol number to match.
         
         This object is only available if the capability object
         'vtssEvcCapabilitiesHasEceIpProto' is True."
    ::= { vtssEvcConfigEceTableRowEditor 501 }

vtssEvcConfigEceTableRowEditorIpv4ProtoMask OBJECT-TYPE
    SYNTAX      VTSSUnsigned8
    MAX-ACCESS  read-write
    STATUS      current
    DESCRIPTION 
        "The IPv4 protocol mask.
         
         This object is only available if the capability object
         'vtssEvcCapabilitiesHasEceIpProto' is True."
    ::= { vtssEvcConfigEceTableRowEditor 502 }

vtssEvcConfigEceTableRowEditorIpv4Fragment OBJECT-TYPE
    SYNTAX      VTSSBitType
    MAX-ACCESS  read-write
    STATUS      current
    DESCRIPTION 
        "The IPv4 fragment match.
         
         This object is only available if the capability object
         'vtssEvcCapabilitiesHasEceIpv4Fragment' is True."
    ::= { vtssEvcConfigEceTableRowEditor 503 }

vtssEvcConfigEceTableRowEditorIpv4SrcIp OBJECT-TYPE
    SYNTAX      IpAddress
    MAX-ACCESS  read-write
    STATUS      current
    DESCRIPTION 
        "The IPv4 source address.
         
         This object is only available if the capability object
         'vtssEvcCapabilitiesHasEceSrcIp' is True."
    ::= { vtssEvcConfigEceTableRowEditor 504 }

vtssEvcConfigEceTableRowEditorIpv4SrcIpMask OBJECT-TYPE
    SYNTAX      IpAddress
    MAX-ACCESS  read-write
    STATUS      current
    DESCRIPTION 
        "The IPv4 source address mask.
         
         This object is only available if the capability object
         'vtssEvcCapabilitiesHasEceSrcIp' is True."
    ::= { vtssEvcConfigEceTableRowEditor 505 }

vtssEvcConfigEceTableRowEditorIpv4DestIp OBJECT-TYPE
    SYNTAX      IpAddress
    MAX-ACCESS  read-write
    STATUS      current
    DESCRIPTION 
        "The IPv4 destination address.
         
         This object is only available if the capability object
         'vtssEvcCapabilitiesHasEceDestIp' is True."
    ::= { vtssEvcConfigEceTableRowEditor 506 }

vtssEvcConfigEceTableRowEditorIpv4DestIpMask OBJECT-TYPE
    SYNTAX      IpAddress
    MAX-ACCESS  read-write
    STATUS      current
    DESCRIPTION 
        "The IPv4 destination address mask.
         
         This object is only available if the capability object
         'vtssEvcCapabilitiesHasEceDestIp' is True."
    ::= { vtssEvcConfigEceTableRowEditor 507 }

vtssEvcConfigEceTableRowEditorIpv4SrcPort OBJECT-TYPE
    SYNTAX      Unsigned32
    MAX-ACCESS  read-write
    STATUS      current
    DESCRIPTION 
        "The IPv4 UDP/TCP source port range to match. The minimum value is
         encoded in the 16 least significant bits. The maximum value is encoded
         in the 16 most significant bits.
         
         This object is only available if the capability object
         'vtssEvcCapabilitiesHasEceSrcPort' is True."
    ::= { vtssEvcConfigEceTableRowEditor 508 }

vtssEvcConfigEceTableRowEditorIpv4DestPort OBJECT-TYPE
    SYNTAX      Unsigned32
    MAX-ACCESS  read-write
    STATUS      current
    DESCRIPTION 
        "The IPv4 UDP/TCP destination port range to match. The minimum value is
         encoded in the 16 least significant bits. The maximum value is encoded
         in the 16 most significant bits.
         
         This object is only available if the capability object
         'vtssEvcCapabilitiesHasEceDestPort' is True."
    ::= { vtssEvcConfigEceTableRowEditor 509 }

vtssEvcConfigEceTableRowEditorIpv6Dscp OBJECT-TYPE
    SYNTAX      Unsigned32
    MAX-ACCESS  read-write
    STATUS      current
    DESCRIPTION 
        "The IPv6 DSCP range to match. The minimum value is encoded in the 16
         least significant bits. The maximum value is encoded in the 16 most
         significant bits."
    ::= { vtssEvcConfigEceTableRowEditor 600 }

vtssEvcConfigEceTableRowEditorIpv6Proto OBJECT-TYPE
    SYNTAX      VTSSUnsigned8
    MAX-ACCESS  read-write
    STATUS      current
    DESCRIPTION 
        "The IPv6 protocol number to match.
         
         This object is only available if the capability object
         'vtssEvcCapabilitiesHasEceIpProto' is True."
    ::= { vtssEvcConfigEceTableRowEditor 601 }

vtssEvcConfigEceTableRowEditorIpv6ProtoMask OBJECT-TYPE
    SYNTAX      VTSSUnsigned8
    MAX-ACCESS  read-write
    STATUS      current
    DESCRIPTION 
        "The IPv6 protocol mask.
         
         This object is only available if the capability object
         'vtssEvcCapabilitiesHasEceIpProto' is True."
    ::= { vtssEvcConfigEceTableRowEditor 602 }

vtssEvcConfigEceTableRowEditorIpv6SrcIp OBJECT-TYPE
    SYNTAX      InetAddressIPv6
    MAX-ACCESS  read-write
    STATUS      current
    DESCRIPTION 
        "The IPv6 source address.
         
         This object is only available if the capability object
         'vtssEvcCapabilitiesHasEceSrcIp' is True."
    ::= { vtssEvcConfigEceTableRowEditor 603 }

vtssEvcConfigEceTableRowEditorIpv6SrcIpMask OBJECT-TYPE
    SYNTAX      InetAddressIPv6
    MAX-ACCESS  read-write
    STATUS      current
    DESCRIPTION 
        "The IPv6 source address mask.
         
         This object is only available if the capability object
         'vtssEvcCapabilitiesHasEceSrcIp' is True."
    ::= { vtssEvcConfigEceTableRowEditor 604 }

vtssEvcConfigEceTableRowEditorIpv6DestIp OBJECT-TYPE
    SYNTAX      InetAddressIPv6
    MAX-ACCESS  read-write
    STATUS      current
    DESCRIPTION 
        "The IPv6 destination address.
         
         This object is only available if the capability object
         'vtssEvcCapabilitiesHasEceDestIp' is True."
    ::= { vtssEvcConfigEceTableRowEditor 605 }

vtssEvcConfigEceTableRowEditorIpv6DestIpMask OBJECT-TYPE
    SYNTAX      InetAddressIPv6
    MAX-ACCESS  read-write
    STATUS      current
    DESCRIPTION 
        "The IPv6 destination address mask.
         
         This object is only available if the capability object
         'vtssEvcCapabilitiesHasEceDestIp' is True."
    ::= { vtssEvcConfigEceTableRowEditor 606 }

vtssEvcConfigEceTableRowEditorIpv6SrcPort OBJECT-TYPE
    SYNTAX      Unsigned32
    MAX-ACCESS  read-write
    STATUS      current
    DESCRIPTION 
        "The IPv6 UDP/TCP source port range to match. The minimum value is
         encoded in the 16 least significant bits. The maximum value is encoded
         in the 16 most significant bits.
         
         This object is only available if the capability object
         'vtssEvcCapabilitiesHasEceSrcPort' is True."
    ::= { vtssEvcConfigEceTableRowEditor 607 }

vtssEvcConfigEceTableRowEditorIpv6DestPort OBJECT-TYPE
    SYNTAX      Unsigned32
    MAX-ACCESS  read-write
    STATUS      current
    DESCRIPTION 
        "The IPv6 UDP/TCP destination port range to match. The minimum value is
         encoded in the 16 least significant bits. The maximum value is encoded
         in the 16 most significant bits.
         
         This object is only available if the capability object
         'vtssEvcCapabilitiesHasEceDestPort' is True."
    ::= { vtssEvcConfigEceTableRowEditor 608 }

vtssEvcConfigEceTableRowEditorDirection OBJECT-TYPE
    SYNTAX      VTSSevcDirection
    MAX-ACCESS  read-write
    STATUS      current
    DESCRIPTION 
        "The ECE direction."
    ::= { vtssEvcConfigEceTableRowEditor 1000 }

vtssEvcConfigEceTableRowEditorRuleType OBJECT-TYPE
    SYNTAX      VTSSevcRuleType
    MAX-ACCESS  read-write
    STATUS      current
    DESCRIPTION 
        "The ECE rule type.
         
         This object is only available if the capability object
         'vtssEvcCapabilitiesHasEceRuleType' is True."
    ::= { vtssEvcConfigEceTableRowEditor 1010 }

vtssEvcConfigEceTableRowEditorTxLookup OBJECT-TYPE
    SYNTAX      VTSSevcTxLookup
    MAX-ACCESS  read-write
    STATUS      current
    DESCRIPTION 
        "The egress lookup key type.
         
         This object is only available if the capability object
         'vtssEvcCapabilitiesHasEceTxLookup' is True."
    ::= { vtssEvcConfigEceTableRowEditor 1011 }

vtssEvcConfigEceTableRowEditorPopTag OBJECT-TYPE
    SYNTAX      VTSSevcPopTag
    MAX-ACCESS  read-write
    STATUS      current
    DESCRIPTION 
        "The number of tags popped."
    ::= { vtssEvcConfigEceTableRowEditor 1020 }

vtssEvcConfigEceTableRowEditorOtAddEnable OBJECT-TYPE
    SYNTAX      TruthValue
    MAX-ACCESS  read-write
    STATUS      current
    DESCRIPTION 
        "Enable outer tag pushing for NNI-to-UNI direction."
    ::= { vtssEvcConfigEceTableRowEditor 1100 }

vtssEvcConfigEceTableRowEditorOtAddVid OBJECT-TYPE
    SYNTAX      VTSSUnsigned16
    MAX-ACCESS  read-write
    STATUS      current
    DESCRIPTION 
        "The VLAN ID pushed for NNI-to-UNI direction.
         
         This object is only available if the capability object
         'vtssEvcCapabilitiesHasEceOtAddVid' is True."
    ::= { vtssEvcConfigEceTableRowEditor 1101 }

vtssEvcConfigEceTableRowEditorOtAddPcpMode OBJECT-TYPE
    SYNTAX      VTSSevcPcpMode
    MAX-ACCESS  read-write
    STATUS      current
    DESCRIPTION 
        "The PCP mode for the outer tag pushed.
         
         This object is only available if the capability object
         'vtssEvcCapabilitiesHasEcePcpMode' is True."
    ::= { vtssEvcConfigEceTableRowEditor 1102 }

vtssEvcConfigEceTableRowEditorOtAddPcpDeiPreserve OBJECT-TYPE
    SYNTAX      TruthValue
    MAX-ACCESS  read-write
    STATUS      current
    DESCRIPTION 
        "Enable PCP/DEI preservation for the outer tag pushed.
         
         This object is only available if the capability object
         'vtssEvcCapabilitiesHasEcePcpDeiPreserve' is True."
    ::= { vtssEvcConfigEceTableRowEditor 1103 }

vtssEvcConfigEceTableRowEditorOtAddPcp OBJECT-TYPE
    SYNTAX      Unsigned32
    MAX-ACCESS  read-write
    STATUS      current
    DESCRIPTION 
        "The PCP value for the outer tag pushed."
    ::= { vtssEvcConfigEceTableRowEditor 1104 }

vtssEvcConfigEceTableRowEditorOtAddDeiMode OBJECT-TYPE
    SYNTAX      VTSSevcDeiMode
    MAX-ACCESS  read-write
    STATUS      current
    DESCRIPTION 
        "The DEI mode for the outer tag pushed.
         
         This object is only available if the capability object
         'vtssEvcCapabilitiesHasEceDeiMode' is True."
    ::= { vtssEvcConfigEceTableRowEditor 1105 }

vtssEvcConfigEceTableRowEditorOtAddDei OBJECT-TYPE
    SYNTAX      VTSSUnsigned8
    MAX-ACCESS  read-write
    STATUS      current
    DESCRIPTION 
        "The DEI value for the outer tag pushed."
    ::= { vtssEvcConfigEceTableRowEditor 1106 }

vtssEvcConfigEceTableRowEditorItAddType OBJECT-TYPE
    SYNTAX      VTSSevcInnerTagType
    MAX-ACCESS  read-write
    STATUS      current
    DESCRIPTION 
        "The tag type for the inner tag pushed.
         
         This object is only available if the capability object
         'vtssEvcCapabilitiesHasEceItAdd' is True."
    ::= { vtssEvcConfigEceTableRowEditor 1200 }

vtssEvcConfigEceTableRowEditorItAddVid OBJECT-TYPE
    SYNTAX      VTSSUnsigned16
    MAX-ACCESS  read-write
    STATUS      current
    DESCRIPTION 
        "The VLAN ID for the inner tag pushed.
         
         This object is only available if the capability object
         'vtssEvcCapabilitiesHasEceItAdd' is True."
    ::= { vtssEvcConfigEceTableRowEditor 1201 }

vtssEvcConfigEceTableRowEditorItAddPcpMode OBJECT-TYPE
    SYNTAX      VTSSevcPcpMode
    MAX-ACCESS  read-write
    STATUS      current
    DESCRIPTION 
        "The PCP mode for the inner tag pushed.
         
         This object is only available if the capability object
         'vtssEvcCapabilitiesHasEcePcpMode' is True."
    ::= { vtssEvcConfigEceTableRowEditor 1202 }

vtssEvcConfigEceTableRowEditorItAddPcpDeiPreserve OBJECT-TYPE
    SYNTAX      TruthValue
    MAX-ACCESS  read-write
    STATUS      current
    DESCRIPTION 
        "Enable PCP/DEI preservation for the inner tag pushed.
         
         This object is only available if the capability object
         'vtssEvcCapabilitiesHasEcePcpDeiPreserve' is True."
    ::= { vtssEvcConfigEceTableRowEditor 1203 }

vtssEvcConfigEceTableRowEditorItAddPcp OBJECT-TYPE
    SYNTAX      Unsigned32
    MAX-ACCESS  read-write
    STATUS      current
    DESCRIPTION 
        "The PCP value for the inner tag pushed.
         
         This object is only available if the capability object
         'vtssEvcCapabilitiesHasEceItAdd' is True."
    ::= { vtssEvcConfigEceTableRowEditor 1204 }

vtssEvcConfigEceTableRowEditorItAddDeiMode OBJECT-TYPE
    SYNTAX      VTSSevcDeiMode
    MAX-ACCESS  read-write
    STATUS      current
    DESCRIPTION 
        "The DEI mode for the inner tag pushed.
         
         This object is only available if the capability object
         'vtssEvcCapabilitiesHasEceDeiMode' is True."
    ::= { vtssEvcConfigEceTableRowEditor 1205 }

vtssEvcConfigEceTableRowEditorItAddDei OBJECT-TYPE
    SYNTAX      VTSSUnsigned8
    MAX-ACCESS  read-write
    STATUS      current
    DESCRIPTION 
        "The DEI value for the inner tag pushed.
         
         This object is only available if the capability object
         'vtssEvcCapabilitiesHasEceItAdd' is True."
    ::= { vtssEvcConfigEceTableRowEditor 1206 }

vtssEvcConfigEceTableRowEditorEvcId OBJECT-TYPE
    SYNTAX      VTSSUnsigned16
    MAX-ACCESS  read-write
    STATUS      current
    DESCRIPTION 
        "The EVC ID for the ECE."
    ::= { vtssEvcConfigEceTableRowEditor 1300 }

vtssEvcConfigEceTableRowEditorPolicerOp OBJECT-TYPE
    SYNTAX      VTSSevcPolicerOp
    MAX-ACCESS  read-write
    STATUS      current
    DESCRIPTION 
        "The policer operator for the ECE.
         
         This object is only available if the capability object
         'vtssEvcCapabilitiesHasEcePolicer' is True."
    ::= { vtssEvcConfigEceTableRowEditor 1301 }

vtssEvcConfigEceTableRowEditorPolicerId OBJECT-TYPE
    SYNTAX      VTSSUnsigned16
    MAX-ACCESS  read-write
    STATUS      current
    DESCRIPTION 
        "The policer ID for the ECE.
         
         This object is only available if the capability object
         'vtssEvcCapabilitiesHasEcePolicer' is True."
    ::= { vtssEvcConfigEceTableRowEditor 1302 }

vtssEvcConfigEceTableRowEditorPolicyNo OBJECT-TYPE
    SYNTAX      Unsigned32
    MAX-ACCESS  read-write
    STATUS      current
    DESCRIPTION 
        "The ACL policy number for the ECE."
    ::= { vtssEvcConfigEceTableRowEditor 1310 }

vtssEvcConfigEceTableRowEditorCosEnable OBJECT-TYPE
    SYNTAX      TruthValue
    MAX-ACCESS  read-write
    STATUS      current
    DESCRIPTION 
        "Enable CoS assignment.
         
         This object is only available if the capability object
         'vtssEvcCapabilitiesHasEceCos' is True."
    ::= { vtssEvcConfigEceTableRowEditor 1320 }

vtssEvcConfigEceTableRowEditorCos OBJECT-TYPE
    SYNTAX      Unsigned32
    MAX-ACCESS  read-write
    STATUS      current
    DESCRIPTION 
        "The CoS value for the ECE.
         
         This object is only available if the capability object
         'vtssEvcCapabilitiesHasEceCos' is True."
    ::= { vtssEvcConfigEceTableRowEditor 1321 }

vtssEvcConfigEceTableRowEditorDpEnable OBJECT-TYPE
    SYNTAX      TruthValue
    MAX-ACCESS  read-write
    STATUS      current
    DESCRIPTION 
        "Enable Drop Precendence assignment.
         
         This object is only available if the capability object
         'vtssEvcCapabilitiesHasEceDp' is True."
    ::= { vtssEvcConfigEceTableRowEditor 1330 }

vtssEvcConfigEceTableRowEditorDp OBJECT-TYPE
    SYNTAX      VTSSUnsigned8
    MAX-ACCESS  read-write
    STATUS      current
    DESCRIPTION 
        "The Drop Precedence value for the ECE.
         
         This object is only available if the capability object
         'vtssEvcCapabilitiesHasEceDp' is True."
    ::= { vtssEvcConfigEceTableRowEditor 1331 }

vtssEvcConfigEceTableRowEditorL2cpMode OBJECT-TYPE
    SYNTAX      VTSSevcEceL2cpMode
    MAX-ACCESS  read-write
    STATUS      current
    DESCRIPTION 
        "The L2CP forward mode for the ECE.
         
         This object is only available if the capability object
         'vtssEvcCapabilitiesHasEceL2cp' is True."
    ::= { vtssEvcConfigEceTableRowEditor 1332 }

vtssEvcConfigEceTableRowEditorL2cpDmac OBJECT-TYPE
    SYNTAX      VTSSevcL2cpDmac
    MAX-ACCESS  read-write
    STATUS      current
    DESCRIPTION 
        "The DMAC used for L2CP tunneling for the ECE.
         
         This object is only available if the capability object
         'vtssEvcCapabilitiesHasEceL2cp' is True."
    ::= { vtssEvcConfigEceTableRowEditor 1333 }

vtssEvcConfigEceTableRowEditorAction OBJECT-TYPE
    SYNTAX      VTSSRowEditorState
    MAX-ACCESS  read-write
    STATUS      current
    DESCRIPTION 
        "Action"
    ::= { vtssEvcConfigEceTableRowEditor 10000 }

vtssEvcConfigEcePrecedenceTable OBJECT-TYPE
    SYNTAX      SEQUENCE OF VTSSEvcConfigEcePrecedenceEntry
    MAX-ACCESS  not-accessible
    STATUS      current
    DESCRIPTION 
        "This table contains the precedence of ECEs ordered by their position"
    ::= { vtssEvcConfigEce 3 }

vtssEvcConfigEcePrecedenceEntry OBJECT-TYPE
    SYNTAX      VTSSEvcConfigEcePrecedenceEntry
    MAX-ACCESS  not-accessible
    STATUS      current
    DESCRIPTION 
        "Each row contains the precedence for an ECE"
    INDEX       { vtssEvcConfigEcePrecedenceIndex }
    ::= { vtssEvcConfigEcePrecedenceTable 1 }

VTSSEvcConfigEcePrecedenceEntry ::= SEQUENCE {
    vtssEvcConfigEcePrecedenceIndex     Integer32,
    vtssEvcConfigEcePrecedenceEceId     Unsigned32
}

vtssEvcConfigEcePrecedenceIndex OBJECT-TYPE
    SYNTAX      Integer32 (0..4095)
    MAX-ACCESS  not-accessible
    STATUS      current
    DESCRIPTION 
        "ECE precedence index, allowed range is [0,EceMax[."
    ::= { vtssEvcConfigEcePrecedenceEntry 1 }

vtssEvcConfigEcePrecedenceEceId OBJECT-TYPE
    SYNTAX      Unsigned32
    MAX-ACCESS  read-only
    STATUS      current
    DESCRIPTION 
        "ECE ID."
    ::= { vtssEvcConfigEcePrecedenceEntry 2 }

vtssEvcConfigEvcInterfaceTable OBJECT-TYPE
    SYNTAX      SEQUENCE OF VTSSEvcConfigEvcInterfaceEntry
    MAX-ACCESS  not-accessible
    STATUS      current
    DESCRIPTION 
        "This table provides interface configuration for EVCs"
    ::= { vtssEvcConfig 6 }

vtssEvcConfigEvcInterfaceEntry OBJECT-TYPE
    SYNTAX      VTSSEvcConfigEvcInterfaceEntry
    MAX-ACCESS  not-accessible
    STATUS      current
    DESCRIPTION 
        "Each row contains the configuration for an interface on an EVC"
    INDEX       { vtssEvcConfigEvcInterfaceEvcId, vtssEvcConfigEvcInterfaceIfIndex }
    ::= { vtssEvcConfigEvcInterfaceTable 1 }

VTSSEvcConfigEvcInterfaceEntry ::= SEQUENCE {
    vtssEvcConfigEvcInterfaceEvcId      Integer32,
    vtssEvcConfigEvcInterfaceIfIndex    VTSSInterfaceIndex,
    vtssEvcConfigEvcInterfaceHqosId     VTSSUnsigned16
}

vtssEvcConfigEvcInterfaceEvcId OBJECT-TYPE
    SYNTAX      Integer32 (0..4095)
    MAX-ACCESS  not-accessible
    STATUS      current
    DESCRIPTION 
        "EVC ID, allowed range is [0,EvcMax[."
    ::= { vtssEvcConfigEvcInterfaceEntry 1 }

vtssEvcConfigEvcInterfaceIfIndex OBJECT-TYPE
    SYNTAX      VTSSInterfaceIndex
    MAX-ACCESS  not-accessible
    STATUS      current
    DESCRIPTION 
        "Logical interface index."
    ::= { vtssEvcConfigEvcInterfaceEntry 2 }

vtssEvcConfigEvcInterfaceHqosId OBJECT-TYPE
    SYNTAX      VTSSUnsigned16
    MAX-ACCESS  read-write
    STATUS      current
    DESCRIPTION 
        "HQoS ID mapping.
         
         This object is only available if the capability object
         'vtssEvcCapabilitiesHasEvcPortHqos' is True."
    ::= { vtssEvcConfigEvcInterfaceEntry 3 }

vtssEvcConfigMplsTp OBJECT IDENTIFIER
    ::= { vtssEvcConfig 7 }

vtssEvcConfigMplsTpPwTable OBJECT-TYPE
    SYNTAX      SEQUENCE OF VTSSEvcConfigMplsTpPwEntry
    MAX-ACCESS  not-accessible
    STATUS      current
    DESCRIPTION 
        "This table contains the set of MPLS-TP pseudo wires attached to an EVC."
    ::= { vtssEvcConfigMplsTp 1 }

vtssEvcConfigMplsTpPwEntry OBJECT-TYPE
    SYNTAX      VTSSEvcConfigMplsTpPwEntry
    MAX-ACCESS  not-accessible
    STATUS      current
    DESCRIPTION 
        "Each row contains the EVC-specific configuration for an MPLS-TP pseudo
         wire."
    INDEX       { vtssEvcConfigMplsTpPwEvcId, vtssEvcConfigMplsTpPwIfIndex }
    ::= { vtssEvcConfigMplsTpPwTable 1 }

VTSSEvcConfigMplsTpPwEntry ::= SEQUENCE {
    vtssEvcConfigMplsTpPwEvcId      Integer32,
    vtssEvcConfigMplsTpPwIfIndex    VTSSInterfaceIndex,
    vtssEvcConfigMplsTpPwSplitHorizon   TruthValue,
    vtssEvcConfigMplsTpPwAction     VTSSRowEditorState
}

vtssEvcConfigMplsTpPwEvcId OBJECT-TYPE
    SYNTAX      Integer32 (0..4095)
    MAX-ACCESS  not-accessible
    STATUS      current
    DESCRIPTION 
        "EVC ID, allowed range is [0,EvcMax[."
    ::= { vtssEvcConfigMplsTpPwEntry 1 }

vtssEvcConfigMplsTpPwIfIndex OBJECT-TYPE
    SYNTAX      VTSSInterfaceIndex
    MAX-ACCESS  not-accessible
    STATUS      current
    DESCRIPTION 
        "MPLS pseudo wire interface index. Zero = unused."
    ::= { vtssEvcConfigMplsTpPwEntry 2 }

vtssEvcConfigMplsTpPwSplitHorizon OBJECT-TYPE
    SYNTAX      TruthValue
    MAX-ACCESS  read-write
    STATUS      current
    DESCRIPTION 
        "True: Enable split-horizon for a PW. False: Disable split-horizon."
    ::= { vtssEvcConfigMplsTpPwEntry 4 }

vtssEvcConfigMplsTpPwAction OBJECT-TYPE
    SYNTAX      VTSSRowEditorState
    MAX-ACCESS  read-write
    STATUS      current
    DESCRIPTION 
        "Action"
    ::= { vtssEvcConfigMplsTpPwEntry 10000 }

vtssEvcConfigMplsTpPwTableRowEditor OBJECT IDENTIFIER
    ::= { vtssEvcConfigMplsTp 2 }

vtssEvcConfigMplsTpPwTableRowEditorEvcId OBJECT-TYPE
    SYNTAX      Integer32 (0..4095)
    MAX-ACCESS  read-write
    STATUS      current
    DESCRIPTION 
        "EVC ID, allowed range is [0,EvcMax[."
    ::= { vtssEvcConfigMplsTpPwTableRowEditor 1 }

vtssEvcConfigMplsTpPwTableRowEditorIfIndex OBJECT-TYPE
    SYNTAX      VTSSInterfaceIndex
    MAX-ACCESS  read-write
    STATUS      current
    DESCRIPTION 
        "MPLS pseudo wire interface index. Zero = unused."
    ::= { vtssEvcConfigMplsTpPwTableRowEditor 2 }

vtssEvcConfigMplsTpPwTableRowEditorSplitHorizon OBJECT-TYPE
    SYNTAX      TruthValue
    MAX-ACCESS  read-write
    STATUS      current
    DESCRIPTION 
        "True: Enable split-horizon for a PW. False: Disable split-horizon."
    ::= { vtssEvcConfigMplsTpPwTableRowEditor 4 }

vtssEvcConfigMplsTpPwTableRowEditorAction OBJECT-TYPE
    SYNTAX      VTSSRowEditorState
    MAX-ACCESS  read-write
    STATUS      current
    DESCRIPTION 
        "Action"
    ::= { vtssEvcConfigMplsTpPwTableRowEditor 10000 }

vtssEvcStatus OBJECT IDENTIFIER
    ::= { vtssEvcMibObjects 3 }

vtssEvcStatusEvcTable OBJECT-TYPE
    SYNTAX      SEQUENCE OF VTSSEvcStatusEvcEntry
    MAX-ACCESS  not-accessible
    STATUS      current
    DESCRIPTION 
        "This table contains the status of EVCs"
    ::= { vtssEvcStatus 3 }

vtssEvcStatusEvcEntry OBJECT-TYPE
    SYNTAX      VTSSEvcStatusEvcEntry
    MAX-ACCESS  not-accessible
    STATUS      current
    DESCRIPTION 
        "Each row contains the status for an EVC"
    INDEX       { vtssEvcStatusEvcEvcId }
    ::= { vtssEvcStatusEvcTable 1 }

VTSSEvcStatusEvcEntry ::= SEQUENCE {
    vtssEvcStatusEvcEvcId   Integer32,
    vtssEvcStatusEvcConflict    TruthValue
}

vtssEvcStatusEvcEvcId OBJECT-TYPE
    SYNTAX      Integer32 (0..4095)
    MAX-ACCESS  not-accessible
    STATUS      current
    DESCRIPTION 
        "EVC ID, allowed range is [0,EvcMax[."
    ::= { vtssEvcStatusEvcEntry 1 }

vtssEvcStatusEvcConflict OBJECT-TYPE
    SYNTAX      TruthValue
    MAX-ACCESS  read-only
    STATUS      current
    DESCRIPTION 
        "Resource conflict indication."
    ::= { vtssEvcStatusEvcEntry 2 }

vtssEvcStatusEceTable OBJECT-TYPE
    SYNTAX      SEQUENCE OF VTSSEvcStatusEceEntry
    MAX-ACCESS  not-accessible
    STATUS      current
    DESCRIPTION 
        "This table contains the status of ECEs"
    ::= { vtssEvcStatus 4 }

vtssEvcStatusEceEntry OBJECT-TYPE
    SYNTAX      VTSSEvcStatusEceEntry
    MAX-ACCESS  not-accessible
    STATUS      current
    DESCRIPTION 
        "Each row contains the status for an ECE"
    INDEX       { vtssEvcStatusEceIndex }
    ::= { vtssEvcStatusEceTable 1 }

VTSSEvcStatusEceEntry ::= SEQUENCE {
    vtssEvcStatusEceIndex   Integer32,
    vtssEvcStatusEceConflict    TruthValue
}

vtssEvcStatusEceIndex OBJECT-TYPE
    SYNTAX      Integer32 (0..4095)
    MAX-ACCESS  not-accessible
    STATUS      current
    DESCRIPTION 
        "ECE precedence index, allowed range is [0,EceMax[."
    ::= { vtssEvcStatusEceEntry 1 }

vtssEvcStatusEceConflict OBJECT-TYPE
    SYNTAX      TruthValue
    MAX-ACCESS  read-only
    STATUS      current
    DESCRIPTION 
        "Resource conflict indication."
    ::= { vtssEvcStatusEceEntry 2 }

vtssEvcStatusEvcInterfaceTable OBJECT-TYPE
    SYNTAX      SEQUENCE OF VTSSEvcStatusEvcInterfaceEntry
    MAX-ACCESS  not-accessible
    STATUS      current
    DESCRIPTION 
        "This table contains EVC interface statistics"
    ::= { vtssEvcStatus 5 }

vtssEvcStatusEvcInterfaceEntry OBJECT-TYPE
    SYNTAX      VTSSEvcStatusEvcInterfaceEntry
    MAX-ACCESS  not-accessible
    STATUS      current
    DESCRIPTION 
        "Each row contains the statistics for an EVC and interface"
    INDEX       { vtssEvcStatusEvcInterfaceEvcId, vtssEvcStatusEvcInterfaceIfIndex }
    ::= { vtssEvcStatusEvcInterfaceTable 1 }

VTSSEvcStatusEvcInterfaceEntry ::= SEQUENCE {
    vtssEvcStatusEvcInterfaceEvcId      Integer32,
    vtssEvcStatusEvcInterfaceIfIndex    VTSSInterfaceIndex,
    vtssEvcStatusEvcInterfaceRxGreenFrames      Counter64,
    vtssEvcStatusEvcInterfaceRxGreenBytes   Counter64,
    vtssEvcStatusEvcInterfaceRxYellowFrames     Counter64,
    vtssEvcStatusEvcInterfaceRxYellowBytes      Counter64,
    vtssEvcStatusEvcInterfaceRxRedFrames    Counter64,
    vtssEvcStatusEvcInterfaceRxRedBytes     Counter64,
    vtssEvcStatusEvcInterfaceRxDiscardFrames    Counter64,
    vtssEvcStatusEvcInterfaceRxDiscardBytes     Counter64,
    vtssEvcStatusEvcInterfaceTxGreenFrames      Counter64,
    vtssEvcStatusEvcInterfaceTxGreenBytes   Counter64,
    vtssEvcStatusEvcInterfaceTxYellowFrames     Counter64,
    vtssEvcStatusEvcInterfaceTxYellowBytes      Counter64,
    vtssEvcStatusEvcInterfaceTxDiscardFrames    Counter64,
    vtssEvcStatusEvcInterfaceTxDiscardBytes     Counter64
}

vtssEvcStatusEvcInterfaceEvcId OBJECT-TYPE
    SYNTAX      Integer32 (0..4095)
    MAX-ACCESS  not-accessible
    STATUS      current
    DESCRIPTION 
        "EVC ID, allowed range is [0,EvcMax[."
    ::= { vtssEvcStatusEvcInterfaceEntry 1 }

vtssEvcStatusEvcInterfaceIfIndex OBJECT-TYPE
    SYNTAX      VTSSInterfaceIndex
    MAX-ACCESS  not-accessible
    STATUS      current
    DESCRIPTION 
        "Logical interface index."
    ::= { vtssEvcStatusEvcInterfaceEntry 2 }

vtssEvcStatusEvcInterfaceRxGreenFrames OBJECT-TYPE
    SYNTAX      Counter64
    MAX-ACCESS  read-only
    STATUS      current
    DESCRIPTION 
        "Number of received green frames.
         
         This object is only available if the capability object
         'vtssEvcCapabilitiesHasEvcPortCounters' is True."
    ::= { vtssEvcStatusEvcInterfaceEntry 3 }

vtssEvcStatusEvcInterfaceRxGreenBytes OBJECT-TYPE
    SYNTAX      Counter64
    MAX-ACCESS  read-only
    STATUS      current
    DESCRIPTION 
        "Number of received green bytes.
         
         This object is only available if the capability object
         'vtssEvcCapabilitiesHasEvcPortCounters' is True."
    ::= { vtssEvcStatusEvcInterfaceEntry 4 }

vtssEvcStatusEvcInterfaceRxYellowFrames OBJECT-TYPE
    SYNTAX      Counter64
    MAX-ACCESS  read-only
    STATUS      current
    DESCRIPTION 
        "Number of received yellow frames.
         
         This object is only available if the capability object
         'vtssEvcCapabilitiesHasEvcPortCounters' is True."
    ::= { vtssEvcStatusEvcInterfaceEntry 5 }

vtssEvcStatusEvcInterfaceRxYellowBytes OBJECT-TYPE
    SYNTAX      Counter64
    MAX-ACCESS  read-only
    STATUS      current
    DESCRIPTION 
        "Number of received yellow bytes.
         
         This object is only available if the capability object
         'vtssEvcCapabilitiesHasEvcPortCounters' is True."
    ::= { vtssEvcStatusEvcInterfaceEntry 6 }

vtssEvcStatusEvcInterfaceRxRedFrames OBJECT-TYPE
    SYNTAX      Counter64
    MAX-ACCESS  read-only
    STATUS      current
    DESCRIPTION 
        "Number of received red frames.
         
         This object is only available if the capability object
         'vtssEvcCapabilitiesHasEvcPortCounters' is True."
    ::= { vtssEvcStatusEvcInterfaceEntry 7 }

vtssEvcStatusEvcInterfaceRxRedBytes OBJECT-TYPE
    SYNTAX      Counter64
    MAX-ACCESS  read-only
    STATUS      current
    DESCRIPTION 
        "Number of received red bytes.
         
         This object is only available if the capability object
         'vtssEvcCapabilitiesHasEvcPortCounters' is True."
    ::= { vtssEvcStatusEvcInterfaceEntry 8 }

vtssEvcStatusEvcInterfaceRxDiscardFrames OBJECT-TYPE
    SYNTAX      Counter64
    MAX-ACCESS  read-only
    STATUS      current
    DESCRIPTION 
        "Number of received discarded frames.
         
         This object is only available if the capability object
         'vtssEvcCapabilitiesHasEvcPortCounters' is True."
    ::= { vtssEvcStatusEvcInterfaceEntry 9 }

vtssEvcStatusEvcInterfaceRxDiscardBytes OBJECT-TYPE
    SYNTAX      Counter64
    MAX-ACCESS  read-only
    STATUS      current
    DESCRIPTION 
        "Number of received discarded bytes.
         
         This object is only available if the capability object
         'vtssEvcCapabilitiesHasEvcPortCounters' is True."
    ::= { vtssEvcStatusEvcInterfaceEntry 10 }

vtssEvcStatusEvcInterfaceTxGreenFrames OBJECT-TYPE
    SYNTAX      Counter64
    MAX-ACCESS  read-only
    STATUS      current
    DESCRIPTION 
        "Number of transmitted green frames.
         
         This object is only available if the capability object
         'vtssEvcCapabilitiesHasEvcPortCounters' is True."
    ::= { vtssEvcStatusEvcInterfaceEntry 100 }

vtssEvcStatusEvcInterfaceTxGreenBytes OBJECT-TYPE
    SYNTAX      Counter64
    MAX-ACCESS  read-only
    STATUS      current
    DESCRIPTION 
        "Number of transmitted green bytes.
         
         This object is only available if the capability object
         'vtssEvcCapabilitiesHasEvcPortCounters' is True."
    ::= { vtssEvcStatusEvcInterfaceEntry 101 }

vtssEvcStatusEvcInterfaceTxYellowFrames OBJECT-TYPE
    SYNTAX      Counter64
    MAX-ACCESS  read-only
    STATUS      current
    DESCRIPTION 
        "Number of transmitted yellow frames.
         
         This object is only available if the capability object
         'vtssEvcCapabilitiesHasEvcPortCounters' is True."
    ::= { vtssEvcStatusEvcInterfaceEntry 102 }

vtssEvcStatusEvcInterfaceTxYellowBytes OBJECT-TYPE
    SYNTAX      Counter64
    MAX-ACCESS  read-only
    STATUS      current
    DESCRIPTION 
        "Number of transmitted yellow bytes.
         
         This object is only available if the capability object
         'vtssEvcCapabilitiesHasEvcPortCounters' is True."
    ::= { vtssEvcStatusEvcInterfaceEntry 103 }

vtssEvcStatusEvcInterfaceTxDiscardFrames OBJECT-TYPE
    SYNTAX      Counter64
    MAX-ACCESS  read-only
    STATUS      current
    DESCRIPTION 
        "Number of egress discarded frames.
         
         This object is only available if the capability object
         'vtssEvcCapabilitiesHasEvcPortCounters' is True."
    ::= { vtssEvcStatusEvcInterfaceEntry 104 }

vtssEvcStatusEvcInterfaceTxDiscardBytes OBJECT-TYPE
    SYNTAX      Counter64
    MAX-ACCESS  read-only
    STATUS      current
    DESCRIPTION 
        "Number of egress discarded bytes.
         
         This object is only available if the capability object
         'vtssEvcCapabilitiesHasEvcPortCounters' is True."
    ::= { vtssEvcStatusEvcInterfaceEntry 105 }

vtssEvcStatusEceInterfaceTable OBJECT-TYPE
    SYNTAX      SEQUENCE OF VTSSEvcStatusEceInterfaceEntry
    MAX-ACCESS  not-accessible
    STATUS      current
    DESCRIPTION 
        "This table contains ECE interface statistics"
    ::= { vtssEvcStatus 6 }

vtssEvcStatusEceInterfaceEntry OBJECT-TYPE
    SYNTAX      VTSSEvcStatusEceInterfaceEntry
    MAX-ACCESS  not-accessible
    STATUS      current
    DESCRIPTION 
        "Each row contains the statistics for an ECE and interface"
    INDEX       { vtssEvcStatusEceInterfaceIndex, vtssEvcStatusEceInterfaceIfIndex }
    ::= { vtssEvcStatusEceInterfaceTable 1 }

VTSSEvcStatusEceInterfaceEntry ::= SEQUENCE {
    vtssEvcStatusEceInterfaceIndex      Integer32,
    vtssEvcStatusEceInterfaceIfIndex    VTSSInterfaceIndex,
    vtssEvcStatusEceInterfaceRxGreenFrames      Counter64,
    vtssEvcStatusEceInterfaceRxGreenBytes   Counter64,
    vtssEvcStatusEceInterfaceRxYellowFrames     Counter64,
    vtssEvcStatusEceInterfaceRxYellowBytes      Counter64,
    vtssEvcStatusEceInterfaceRxRedFrames    Counter64,
    vtssEvcStatusEceInterfaceRxRedBytes     Counter64,
    vtssEvcStatusEceInterfaceRxDiscardFrames    Counter64,
    vtssEvcStatusEceInterfaceRxDiscardBytes     Counter64,
    vtssEvcStatusEceInterfaceTxGreenFrames      Counter64,
    vtssEvcStatusEceInterfaceTxGreenBytes   Counter64,
    vtssEvcStatusEceInterfaceTxYellowFrames     Counter64,
    vtssEvcStatusEceInterfaceTxYellowBytes      Counter64,
    vtssEvcStatusEceInterfaceTxDiscardFrames    Counter64,
    vtssEvcStatusEceInterfaceTxDiscardBytes     Counter64
}

vtssEvcStatusEceInterfaceIndex OBJECT-TYPE
    SYNTAX      Integer32 (0..4095)
    MAX-ACCESS  not-accessible
    STATUS      current
    DESCRIPTION 
        "ECE precedence index, allowed range is [0,EceMax[."
    ::= { vtssEvcStatusEceInterfaceEntry 1 }

vtssEvcStatusEceInterfaceIfIndex OBJECT-TYPE
    SYNTAX      VTSSInterfaceIndex
    MAX-ACCESS  not-accessible
    STATUS      current
    DESCRIPTION 
        "Logical interface index."
    ::= { vtssEvcStatusEceInterfaceEntry 2 }

vtssEvcStatusEceInterfaceRxGreenFrames OBJECT-TYPE
    SYNTAX      Counter64
    MAX-ACCESS  read-only
    STATUS      current
    DESCRIPTION 
        "Number of received green frames.
         
         This object is only available if the capability object
         'vtssEvcCapabilitiesHasEvcPortCounters' is True."
    ::= { vtssEvcStatusEceInterfaceEntry 3 }

vtssEvcStatusEceInterfaceRxGreenBytes OBJECT-TYPE
    SYNTAX      Counter64
    MAX-ACCESS  read-only
    STATUS      current
    DESCRIPTION 
        "Number of received green bytes.
         
         This object is only available if the capability object
         'vtssEvcCapabilitiesHasEvcPortCounters' is True."
    ::= { vtssEvcStatusEceInterfaceEntry 4 }

vtssEvcStatusEceInterfaceRxYellowFrames OBJECT-TYPE
    SYNTAX      Counter64
    MAX-ACCESS  read-only
    STATUS      current
    DESCRIPTION 
        "Number of received yellow frames.
         
         This object is only available if the capability object
         'vtssEvcCapabilitiesHasEvcPortCounters' is True."
    ::= { vtssEvcStatusEceInterfaceEntry 5 }

vtssEvcStatusEceInterfaceRxYellowBytes OBJECT-TYPE
    SYNTAX      Counter64
    MAX-ACCESS  read-only
    STATUS      current
    DESCRIPTION 
        "Number of received yellow bytes.
         
         This object is only available if the capability object
         'vtssEvcCapabilitiesHasEvcPortCounters' is True."
    ::= { vtssEvcStatusEceInterfaceEntry 6 }

vtssEvcStatusEceInterfaceRxRedFrames OBJECT-TYPE
    SYNTAX      Counter64
    MAX-ACCESS  read-only
    STATUS      current
    DESCRIPTION 
        "Number of received red frames.
         
         This object is only available if the capability object
         'vtssEvcCapabilitiesHasEvcPortCounters' is True."
    ::= { vtssEvcStatusEceInterfaceEntry 7 }

vtssEvcStatusEceInterfaceRxRedBytes OBJECT-TYPE
    SYNTAX      Counter64
    MAX-ACCESS  read-only
    STATUS      current
    DESCRIPTION 
        "Number of received red bytes.
         
         This object is only available if the capability object
         'vtssEvcCapabilitiesHasEvcPortCounters' is True."
    ::= { vtssEvcStatusEceInterfaceEntry 8 }

vtssEvcStatusEceInterfaceRxDiscardFrames OBJECT-TYPE
    SYNTAX      Counter64
    MAX-ACCESS  read-only
    STATUS      current
    DESCRIPTION 
        "Number of received discarded frames.
         
         This object is only available if the capability object
         'vtssEvcCapabilitiesHasEvcPortCounters' is True."
    ::= { vtssEvcStatusEceInterfaceEntry 9 }

vtssEvcStatusEceInterfaceRxDiscardBytes OBJECT-TYPE
    SYNTAX      Counter64
    MAX-ACCESS  read-only
    STATUS      current
    DESCRIPTION 
        "Number of received discarded bytes.
         
         This object is only available if the capability object
         'vtssEvcCapabilitiesHasEvcPortCounters' is True."
    ::= { vtssEvcStatusEceInterfaceEntry 10 }

vtssEvcStatusEceInterfaceTxGreenFrames OBJECT-TYPE
    SYNTAX      Counter64
    MAX-ACCESS  read-only
    STATUS      current
    DESCRIPTION 
        "Number of transmitted green frames.
         
         This object is only available if the capability object
         'vtssEvcCapabilitiesHasEvcPortCounters' is True."
    ::= { vtssEvcStatusEceInterfaceEntry 100 }

vtssEvcStatusEceInterfaceTxGreenBytes OBJECT-TYPE
    SYNTAX      Counter64
    MAX-ACCESS  read-only
    STATUS      current
    DESCRIPTION 
        "Number of transmitted green bytes.
         
         This object is only available if the capability object
         'vtssEvcCapabilitiesHasEvcPortCounters' is True."
    ::= { vtssEvcStatusEceInterfaceEntry 101 }

vtssEvcStatusEceInterfaceTxYellowFrames OBJECT-TYPE
    SYNTAX      Counter64
    MAX-ACCESS  read-only
    STATUS      current
    DESCRIPTION 
        "Number of transmitted yellow frames.
         
         This object is only available if the capability object
         'vtssEvcCapabilitiesHasEvcPortCounters' is True."
    ::= { vtssEvcStatusEceInterfaceEntry 102 }

vtssEvcStatusEceInterfaceTxYellowBytes OBJECT-TYPE
    SYNTAX      Counter64
    MAX-ACCESS  read-only
    STATUS      current
    DESCRIPTION 
        "Number of transmitted yellow bytes.
         
         This object is only available if the capability object
         'vtssEvcCapabilitiesHasEvcPortCounters' is True."
    ::= { vtssEvcStatusEceInterfaceEntry 103 }

vtssEvcStatusEceInterfaceTxDiscardFrames OBJECT-TYPE
    SYNTAX      Counter64
    MAX-ACCESS  read-only
    STATUS      current
    DESCRIPTION 
        "Number of egress discarded frames.
         
         This object is only available if the capability object
         'vtssEvcCapabilitiesHasEvcPortCounters' is True."
    ::= { vtssEvcStatusEceInterfaceEntry 104 }

vtssEvcStatusEceInterfaceTxDiscardBytes OBJECT-TYPE
    SYNTAX      Counter64
    MAX-ACCESS  read-only
    STATUS      current
    DESCRIPTION 
        "Number of egress discarded bytes.
         
         This object is only available if the capability object
         'vtssEvcCapabilitiesHasEvcPortCounters' is True."
    ::= { vtssEvcStatusEceInterfaceEntry 105 }

vtssEvcControl OBJECT IDENTIFIER
    ::= { vtssEvcMibObjects 4 }

vtssEvcControlEvcInterfaceTable OBJECT-TYPE
    SYNTAX      SEQUENCE OF VTSSEvcControlEvcInterfaceEntry
    MAX-ACCESS  not-accessible
    STATUS      current
    DESCRIPTION 
        "This table provides EVC interface control"
    ::= { vtssEvcControl 5 }

vtssEvcControlEvcInterfaceEntry OBJECT-TYPE
    SYNTAX      VTSSEvcControlEvcInterfaceEntry
    MAX-ACCESS  not-accessible
    STATUS      current
    DESCRIPTION 
        "Each row controls an EVC and interface"
    INDEX       { vtssEvcControlEvcInterfaceEvcId, vtssEvcControlEvcInterfaceIfIndex }
    ::= { vtssEvcControlEvcInterfaceTable 1 }

VTSSEvcControlEvcInterfaceEntry ::= SEQUENCE {
    vtssEvcControlEvcInterfaceEvcId     Integer32,
    vtssEvcControlEvcInterfaceIfIndex   VTSSInterfaceIndex,
    vtssEvcControlEvcInterfaceClearStatistics   TruthValue
}

vtssEvcControlEvcInterfaceEvcId OBJECT-TYPE
    SYNTAX      Integer32 (0..4095)
    MAX-ACCESS  not-accessible
    STATUS      current
    DESCRIPTION 
        "EVC ID, allowed range is [0,EvcMax[."
    ::= { vtssEvcControlEvcInterfaceEntry 1 }

vtssEvcControlEvcInterfaceIfIndex OBJECT-TYPE
    SYNTAX      VTSSInterfaceIndex
    MAX-ACCESS  not-accessible
    STATUS      current
    DESCRIPTION 
        "Logical interface index."
    ::= { vtssEvcControlEvcInterfaceEntry 2 }

vtssEvcControlEvcInterfaceClearStatistics OBJECT-TYPE
    SYNTAX      TruthValue
    MAX-ACCESS  read-write
    STATUS      current
    DESCRIPTION 
        "Clear statistics by setting to true.
         
         This object is only available if the capability object
         'vtssEvcCapabilitiesHasEvcPortCounters' is True."
    ::= { vtssEvcControlEvcInterfaceEntry 3 }

vtssEvcControlEceInterfaceTable OBJECT-TYPE
    SYNTAX      SEQUENCE OF VTSSEvcControlEceInterfaceEntry
    MAX-ACCESS  not-accessible
    STATUS      current
    DESCRIPTION 
        "This table provides ECE interface control"
    ::= { vtssEvcControl 6 }

vtssEvcControlEceInterfaceEntry OBJECT-TYPE
    SYNTAX      VTSSEvcControlEceInterfaceEntry
    MAX-ACCESS  not-accessible
    STATUS      current
    DESCRIPTION 
        "Each row controls an ECE and interface"
    INDEX       { vtssEvcControlEceInterfaceIndex, vtssEvcControlEceInterfaceIfIndex }
    ::= { vtssEvcControlEceInterfaceTable 1 }

VTSSEvcControlEceInterfaceEntry ::= SEQUENCE {
    vtssEvcControlEceInterfaceIndex     Integer32,
    vtssEvcControlEceInterfaceIfIndex   VTSSInterfaceIndex,
    vtssEvcControlEceInterfaceClearStatistics   TruthValue
}

vtssEvcControlEceInterfaceIndex OBJECT-TYPE
    SYNTAX      Integer32 (0..4095)
    MAX-ACCESS  not-accessible
    STATUS      current
    DESCRIPTION 
        "ECE precedence index, allowed range is [0,EceMax[."
    ::= { vtssEvcControlEceInterfaceEntry 1 }

vtssEvcControlEceInterfaceIfIndex OBJECT-TYPE
    SYNTAX      VTSSInterfaceIndex
    MAX-ACCESS  not-accessible
    STATUS      current
    DESCRIPTION 
        "Logical interface index."
    ::= { vtssEvcControlEceInterfaceEntry 2 }

vtssEvcControlEceInterfaceClearStatistics OBJECT-TYPE
    SYNTAX      TruthValue
    MAX-ACCESS  read-write
    STATUS      current
    DESCRIPTION 
        "Clear statistics by setting to true.
         
         This object is only available if the capability object
         'vtssEvcCapabilitiesHasEvcPortCounters' is True."
    ::= { vtssEvcControlEceInterfaceEntry 3 }

vtssEvcMibConformance OBJECT IDENTIFIER
    ::= { vtssEvcMib 2 }

vtssEvcMibCompliances OBJECT IDENTIFIER
    ::= { vtssEvcMibConformance 1 }

vtssEvcMibGroups OBJECT IDENTIFIER
    ::= { vtssEvcMibConformance 2 }

vtssEvcCapabilitiesInfoGroup OBJECT-GROUP
    OBJECTS     { vtssEvcCapabilitiesPolicerMax, vtssEvcCapabilitiesEvcMax, 
                  vtssEvcCapabilitiesEceMax, 
                  vtssEvcCapabilitiesHasPortDeiColoring, 
                  vtssEvcCapabilitiesHasPortInnerTag, 
                  vtssEvcCapabilitiesHasPortAddrMode, 
                  vtssEvcCapabilitiesHasPortKey, 
                  vtssEvcCapabilitiesHasPolicerColorBlind, 
                  vtssEvcCapabilitiesHasEvcPolicer, 
                  vtssEvcCapabilitiesHasEvcUniVid, 
                  vtssEvcCapabilitiesHasEvcItAdd, vtssEvcCapabilitiesHasEvcMpls, 
                  vtssEvcCapabilitiesHasEvcETree, 
                  vtssEvcCapabilitiesHasEceAdvLookup, 
                  vtssEvcCapabilitiesHasEceDestMacType, 
                  vtssEvcCapabilitiesHasEceDestMac, 
                  vtssEvcCapabilitiesHasEceSrcMac, 
                  vtssEvcCapabilitiesHasEceInnerTag, 
                  vtssEvcCapabilitiesHasEceEtype, vtssEvcCapabilitiesHasEceLlc, 
                  vtssEvcCapabilitiesHasEceSnap, vtssEvcCapabilitiesHasEceL2cp, 
                  vtssEvcCapabilitiesHasEceIpv4Fragment, 
                  vtssEvcCapabilitiesHasEceIpProto, 
                  vtssEvcCapabilitiesHasEceSrcIp, 
                  vtssEvcCapabilitiesHasEceDestIp, 
                  vtssEvcCapabilitiesHasEceSrcPort, 
                  vtssEvcCapabilitiesHasEceDestPort, 
                  vtssEvcCapabilitiesHasEceRuleType, 
                  vtssEvcCapabilitiesHasEceTxLookup, 
                  vtssEvcCapabilitiesHasEceOtAddVid, 
                  vtssEvcCapabilitiesHasEcePcpMode, 
                  vtssEvcCapabilitiesHasEcePcpDeiPreserve, 
                  vtssEvcCapabilitiesHasEceDeiMode, 
                  vtssEvcCapabilitiesHasEceItAdd, 
                  vtssEvcCapabilitiesHasEcePolicer, vtssEvcCapabilitiesHasEceCos, 
                  vtssEvcCapabilitiesHasEceDp, vtssEvcCapabilitiesHasEvcPortHqos, 
                  vtssEvcCapabilitiesHasEvcPortCounters }
    STATUS      current
    DESCRIPTION
        "A collection of objects suitable for bulk operations."
    ::= { vtssEvcMibGroups 1 }

vtssEvcConfigInterfaceTableInfoGroup OBJECT-GROUP
    OBJECTS     { vtssEvcConfigInterfaceKey, vtssEvcConfigInterfaceKeyAdv, 
                  vtssEvcConfigInterfaceAddrMode, 
                  vtssEvcConfigInterfaceAddrModeAdv, 
                  vtssEvcConfigInterfaceDeiColoring, 
                  vtssEvcConfigInterfaceInnerTag }
    STATUS      current
    DESCRIPTION
        "A collection of objects suitable for bulk operations."
    ::= { vtssEvcMibGroups 2 }

vtssEvcConfigInterfaceL2cpTableInfoGroup OBJECT-GROUP
    OBJECTS     { vtssEvcConfigInterfaceL2cpL2cpMode }
    STATUS      current
    DESCRIPTION
        "A collection of objects suitable for bulk operations."
    ::= { vtssEvcMibGroups 3 }

vtssEvcConfigPolicerTableInfoGroup OBJECT-GROUP
    OBJECTS     { vtssEvcConfigPolicerEnable, vtssEvcConfigPolicerPolicerType, 
                  vtssEvcConfigPolicerPolicerMode, vtssEvcConfigPolicerLineRate, 
                  vtssEvcConfigPolicerCir, vtssEvcConfigPolicerCbs, 
                  vtssEvcConfigPolicerEir, vtssEvcConfigPolicerEbs }
    STATUS      current
    DESCRIPTION
        "A collection of objects suitable for bulk operations."
    ::= { vtssEvcMibGroups 4 }

vtssEvcConfigEvcTableInfoGroup OBJECT-GROUP
    OBJECTS     { vtssEvcConfigEvcVid, vtssEvcConfigEvcIvid, 
                  vtssEvcConfigEvcNniPortList, vtssEvcConfigEvcLearning, 
                  vtssEvcConfigEvcPolicerOp, vtssEvcConfigEvcPolicerId, 
                  vtssEvcConfigEvcUniVid, vtssEvcConfigEvcItAddType, 
                  vtssEvcConfigEvcItInnerVid, vtssEvcConfigEvcItAddVid, 
                  vtssEvcConfigEvcItAddPcpDeiPreserve, vtssEvcConfigEvcItAddPcp, 
                  vtssEvcConfigEvcItAddDei, vtssEvcConfigEvcLeafVid, 
                  vtssEvcConfigEvcLeafIvid, vtssEvcConfigEvcLeafPortList, 
                  vtssEvcConfigEvcAction }
    STATUS      current
    DESCRIPTION
        "A collection of objects suitable for bulk operations."
    ::= { vtssEvcMibGroups 5 }

vtssEvcConfigEvcTableRowEditorInfoGroup OBJECT-GROUP
    OBJECTS     { vtssEvcConfigEvcTableRowEditorEvcId, 
                  vtssEvcConfigEvcTableRowEditorVid, 
                  vtssEvcConfigEvcTableRowEditorIvid, 
                  vtssEvcConfigEvcTableRowEditorNniPortList, 
                  vtssEvcConfigEvcTableRowEditorLearning, 
                  vtssEvcConfigEvcTableRowEditorPolicerOp, 
                  vtssEvcConfigEvcTableRowEditorPolicerId, 
                  vtssEvcConfigEvcTableRowEditorUniVid, 
                  vtssEvcConfigEvcTableRowEditorItAddType, 
                  vtssEvcConfigEvcTableRowEditorItInnerVid, 
                  vtssEvcConfigEvcTableRowEditorItAddVid, 
                  vtssEvcConfigEvcTableRowEditorItAddPcpDeiPreserve, 
                  vtssEvcConfigEvcTableRowEditorItAddPcp, 
                  vtssEvcConfigEvcTableRowEditorItAddDei, 
                  vtssEvcConfigEvcTableRowEditorLeafVid, 
                  vtssEvcConfigEvcTableRowEditorLeafIvid, 
                  vtssEvcConfigEvcTableRowEditorLeafPortList, 
                  vtssEvcConfigEvcTableRowEditorAction }
    STATUS      current
    DESCRIPTION
        "A collection of objects suitable for bulk operations."
    ::= { vtssEvcMibGroups 6 }

vtssEvcConfigEceTableInfoGroup OBJECT-GROUP
    OBJECTS     { vtssEvcConfigEceNextId, vtssEvcConfigEceAdvLookup, 
                  vtssEvcConfigEceUniPortList, vtssEvcConfigEceSrcMac, 
                  vtssEvcConfigEceSrcMacMask, vtssEvcConfigEceDestMacType, 
                  vtssEvcConfigEceDestMac, vtssEvcConfigEceDestMacMask, 
                  vtssEvcConfigEceOtMatchType, vtssEvcConfigEceOtMatchVid, 
                  vtssEvcConfigEceOtMatchPcp, vtssEvcConfigEceOtMatchDei, 
                  vtssEvcConfigEceItMatchType, vtssEvcConfigEceItMatchVid, 
                  vtssEvcConfigEceItMatchPcp, vtssEvcConfigEceItMatchDei, 
                  vtssEvcConfigEceFrameType, vtssEvcConfigEceEtype, 
                  vtssEvcConfigEceEtypeMask, vtssEvcConfigEceEtypeData, 
                  vtssEvcConfigEceEtypeDataMask, vtssEvcConfigEceLlcDsap, 
                  vtssEvcConfigEceLlcDsapMask, vtssEvcConfigEceLlcSsap, 
                  vtssEvcConfigEceLlcSsapMask, vtssEvcConfigEceLlcControl, 
                  vtssEvcConfigEceLlcControlMask, vtssEvcConfigEceLlcPid, 
                  vtssEvcConfigEceLlcPidMask, vtssEvcConfigEceSnapOui, 
                  vtssEvcConfigEceSnapOuiMask, vtssEvcConfigEceSnapPid, 
                  vtssEvcConfigEceSnapPidMask, vtssEvcConfigEceL2cpType, 
                  vtssEvcConfigEceIpv4Dscp, vtssEvcConfigEceIpv4Proto, 
                  vtssEvcConfigEceIpv4ProtoMask, vtssEvcConfigEceIpv4Fragment, 
                  vtssEvcConfigEceIpv4SrcIp, vtssEvcConfigEceIpv4SrcIpMask, 
                  vtssEvcConfigEceIpv4DestIp, vtssEvcConfigEceIpv4DestIpMask, 
                  vtssEvcConfigEceIpv4SrcPort, vtssEvcConfigEceIpv4DestPort, 
                  vtssEvcConfigEceIpv6Dscp, vtssEvcConfigEceIpv6Proto, 
                  vtssEvcConfigEceIpv6ProtoMask, vtssEvcConfigEceIpv6SrcIp, 
                  vtssEvcConfigEceIpv6SrcIpMask, vtssEvcConfigEceIpv6DestIp, 
                  vtssEvcConfigEceIpv6DestIpMask, vtssEvcConfigEceIpv6SrcPort, 
                  vtssEvcConfigEceIpv6DestPort, vtssEvcConfigEceDirection, 
                  vtssEvcConfigEceRuleType, vtssEvcConfigEceTxLookup, 
                  vtssEvcConfigEcePopTag, vtssEvcConfigEceOtAddEnable, 
                  vtssEvcConfigEceOtAddVid, vtssEvcConfigEceOtAddPcpMode, 
                  vtssEvcConfigEceOtAddPcpDeiPreserve, vtssEvcConfigEceOtAddPcp, 
                  vtssEvcConfigEceOtAddDeiMode, vtssEvcConfigEceOtAddDei, 
                  vtssEvcConfigEceItAddType, vtssEvcConfigEceItAddVid, 
                  vtssEvcConfigEceItAddPcpMode, 
                  vtssEvcConfigEceItAddPcpDeiPreserve, vtssEvcConfigEceItAddPcp, 
                  vtssEvcConfigEceItAddDeiMode, vtssEvcConfigEceItAddDei, 
                  vtssEvcConfigEceEvcId, vtssEvcConfigEcePolicerOp, 
                  vtssEvcConfigEcePolicerId, vtssEvcConfigEcePolicyNo, 
                  vtssEvcConfigEceCosEnable, vtssEvcConfigEceCos, 
                  vtssEvcConfigEceDpEnable, vtssEvcConfigEceDp, 
                  vtssEvcConfigEceL2cpMode, vtssEvcConfigEceL2cpDmac, 
                  vtssEvcConfigEceAction }
    STATUS      current
    DESCRIPTION
        "A collection of objects suitable for bulk operations."
    ::= { vtssEvcMibGroups 7 }

vtssEvcConfigEceTableRowEditorInfoGroup OBJECT-GROUP
    OBJECTS     { vtssEvcConfigEceTableRowEditorEceId, 
                  vtssEvcConfigEceTableRowEditorNextId, 
                  vtssEvcConfigEceTableRowEditorAdvLookup, 
                  vtssEvcConfigEceTableRowEditorUniPortList, 
                  vtssEvcConfigEceTableRowEditorSrcMac, 
                  vtssEvcConfigEceTableRowEditorSrcMacMask, 
                  vtssEvcConfigEceTableRowEditorDestMacType, 
                  vtssEvcConfigEceTableRowEditorDestMac, 
                  vtssEvcConfigEceTableRowEditorDestMacMask, 
                  vtssEvcConfigEceTableRowEditorOtMatchType, 
                  vtssEvcConfigEceTableRowEditorOtMatchVid, 
                  vtssEvcConfigEceTableRowEditorOtMatchPcp, 
                  vtssEvcConfigEceTableRowEditorOtMatchDei, 
                  vtssEvcConfigEceTableRowEditorItMatchType, 
                  vtssEvcConfigEceTableRowEditorItMatchVid, 
                  vtssEvcConfigEceTableRowEditorItMatchPcp, 
                  vtssEvcConfigEceTableRowEditorItMatchDei, 
                  vtssEvcConfigEceTableRowEditorFrameType, 
                  vtssEvcConfigEceTableRowEditorEtype, 
                  vtssEvcConfigEceTableRowEditorEtypeMask, 
                  vtssEvcConfigEceTableRowEditorEtypeData, 
                  vtssEvcConfigEceTableRowEditorEtypeDataMask, 
                  vtssEvcConfigEceTableRowEditorLlcDsap, 
                  vtssEvcConfigEceTableRowEditorLlcDsapMask, 
                  vtssEvcConfigEceTableRowEditorLlcSsap, 
                  vtssEvcConfigEceTableRowEditorLlcSsapMask, 
                  vtssEvcConfigEceTableRowEditorLlcControl, 
                  vtssEvcConfigEceTableRowEditorLlcControlMask, 
                  vtssEvcConfigEceTableRowEditorLlcPid, 
                  vtssEvcConfigEceTableRowEditorLlcPidMask, 
                  vtssEvcConfigEceTableRowEditorSnapOui, 
                  vtssEvcConfigEceTableRowEditorSnapOuiMask, 
                  vtssEvcConfigEceTableRowEditorSnapPid, 
                  vtssEvcConfigEceTableRowEditorSnapPidMask, 
                  vtssEvcConfigEceTableRowEditorL2cpType, 
                  vtssEvcConfigEceTableRowEditorIpv4Dscp, 
                  vtssEvcConfigEceTableRowEditorIpv4Proto, 
                  vtssEvcConfigEceTableRowEditorIpv4ProtoMask, 
                  vtssEvcConfigEceTableRowEditorIpv4Fragment, 
                  vtssEvcConfigEceTableRowEditorIpv4SrcIp, 
                  vtssEvcConfigEceTableRowEditorIpv4SrcIpMask, 
                  vtssEvcConfigEceTableRowEditorIpv4DestIp, 
                  vtssEvcConfigEceTableRowEditorIpv4DestIpMask, 
                  vtssEvcConfigEceTableRowEditorIpv4SrcPort, 
                  vtssEvcConfigEceTableRowEditorIpv4DestPort, 
                  vtssEvcConfigEceTableRowEditorIpv6Dscp, 
                  vtssEvcConfigEceTableRowEditorIpv6Proto, 
                  vtssEvcConfigEceTableRowEditorIpv6ProtoMask, 
                  vtssEvcConfigEceTableRowEditorIpv6SrcIp, 
                  vtssEvcConfigEceTableRowEditorIpv6SrcIpMask, 
                  vtssEvcConfigEceTableRowEditorIpv6DestIp, 
                  vtssEvcConfigEceTableRowEditorIpv6DestIpMask, 
                  vtssEvcConfigEceTableRowEditorIpv6SrcPort, 
                  vtssEvcConfigEceTableRowEditorIpv6DestPort, 
                  vtssEvcConfigEceTableRowEditorDirection, 
                  vtssEvcConfigEceTableRowEditorRuleType, 
                  vtssEvcConfigEceTableRowEditorTxLookup, 
                  vtssEvcConfigEceTableRowEditorPopTag, 
                  vtssEvcConfigEceTableRowEditorOtAddEnable, 
                  vtssEvcConfigEceTableRowEditorOtAddVid, 
                  vtssEvcConfigEceTableRowEditorOtAddPcpMode, 
                  vtssEvcConfigEceTableRowEditorOtAddPcpDeiPreserve, 
                  vtssEvcConfigEceTableRowEditorOtAddPcp, 
                  vtssEvcConfigEceTableRowEditorOtAddDeiMode, 
                  vtssEvcConfigEceTableRowEditorOtAddDei, 
                  vtssEvcConfigEceTableRowEditorItAddType, 
                  vtssEvcConfigEceTableRowEditorItAddVid, 
                  vtssEvcConfigEceTableRowEditorItAddPcpMode, 
                  vtssEvcConfigEceTableRowEditorItAddPcpDeiPreserve, 
                  vtssEvcConfigEceTableRowEditorItAddPcp, 
                  vtssEvcConfigEceTableRowEditorItAddDeiMode, 
                  vtssEvcConfigEceTableRowEditorItAddDei, 
                  vtssEvcConfigEceTableRowEditorEvcId, 
                  vtssEvcConfigEceTableRowEditorPolicerOp, 
                  vtssEvcConfigEceTableRowEditorPolicerId, 
                  vtssEvcConfigEceTableRowEditorPolicyNo, 
                  vtssEvcConfigEceTableRowEditorCosEnable, 
                  vtssEvcConfigEceTableRowEditorCos, 
                  vtssEvcConfigEceTableRowEditorDpEnable, 
                  vtssEvcConfigEceTableRowEditorDp, 
                  vtssEvcConfigEceTableRowEditorL2cpMode, 
                  vtssEvcConfigEceTableRowEditorL2cpDmac, 
                  vtssEvcConfigEceTableRowEditorAction }
    STATUS      current
    DESCRIPTION
        "A collection of objects suitable for bulk operations."
    ::= { vtssEvcMibGroups 8 }

vtssEvcConfigEcePrecedenceTableInfoGroup OBJECT-GROUP
    OBJECTS     { vtssEvcConfigEcePrecedenceEceId }
    STATUS      current
    DESCRIPTION
        "A collection of objects suitable for bulk operations."
    ::= { vtssEvcMibGroups 9 }

vtssEvcConfigEvcInterfaceTableInfoGroup OBJECT-GROUP
    OBJECTS     { vtssEvcConfigEvcInterfaceHqosId }
    STATUS      current
    DESCRIPTION
        "A collection of objects suitable for bulk operations."
    ::= { vtssEvcMibGroups 10 }

vtssEvcConfigMplsTpPwTableInfoGroup OBJECT-GROUP
    OBJECTS     { vtssEvcConfigMplsTpPwSplitHorizon, vtssEvcConfigMplsTpPwAction }
    STATUS      current
    DESCRIPTION
        "A collection of objects suitable for bulk operations."
    ::= { vtssEvcMibGroups 11 }

vtssEvcConfigMplsTpPwTableRowEditorInfoGroup OBJECT-GROUP
    OBJECTS     { vtssEvcConfigMplsTpPwTableRowEditorEvcId, 
                  vtssEvcConfigMplsTpPwTableRowEditorIfIndex, 
                  vtssEvcConfigMplsTpPwTableRowEditorSplitHorizon, 
                  vtssEvcConfigMplsTpPwTableRowEditorAction }
    STATUS      current
    DESCRIPTION
        "A collection of objects suitable for bulk operations."
    ::= { vtssEvcMibGroups 12 }

vtssEvcStatusEvcTableInfoGroup OBJECT-GROUP
    OBJECTS     { vtssEvcStatusEvcConflict }
    STATUS      current
    DESCRIPTION
        "A collection of objects suitable for bulk operations."
    ::= { vtssEvcMibGroups 13 }

vtssEvcStatusEceTableInfoGroup OBJECT-GROUP
    OBJECTS     { vtssEvcStatusEceConflict }
    STATUS      current
    DESCRIPTION
        "A collection of objects suitable for bulk operations."
    ::= { vtssEvcMibGroups 14 }

vtssEvcStatusEvcInterfaceTableInfoGroup OBJECT-GROUP
    OBJECTS     { vtssEvcStatusEvcInterfaceRxGreenFrames, 
                  vtssEvcStatusEvcInterfaceRxGreenBytes, 
                  vtssEvcStatusEvcInterfaceRxYellowFrames, 
                  vtssEvcStatusEvcInterfaceRxYellowBytes, 
                  vtssEvcStatusEvcInterfaceRxRedFrames, 
                  vtssEvcStatusEvcInterfaceRxRedBytes, 
                  vtssEvcStatusEvcInterfaceRxDiscardFrames, 
                  vtssEvcStatusEvcInterfaceRxDiscardBytes, 
                  vtssEvcStatusEvcInterfaceTxGreenFrames, 
                  vtssEvcStatusEvcInterfaceTxGreenBytes, 
                  vtssEvcStatusEvcInterfaceTxYellowFrames, 
                  vtssEvcStatusEvcInterfaceTxYellowBytes, 
                  vtssEvcStatusEvcInterfaceTxDiscardFrames, 
                  vtssEvcStatusEvcInterfaceTxDiscardBytes }
    STATUS      current
    DESCRIPTION
        "A collection of objects suitable for bulk operations."
    ::= { vtssEvcMibGroups 15 }

vtssEvcStatusEceInterfaceTableInfoGroup OBJECT-GROUP
    OBJECTS     { vtssEvcStatusEceInterfaceRxGreenFrames, 
                  vtssEvcStatusEceInterfaceRxGreenBytes, 
                  vtssEvcStatusEceInterfaceRxYellowFrames, 
                  vtssEvcStatusEceInterfaceRxYellowBytes, 
                  vtssEvcStatusEceInterfaceRxRedFrames, 
                  vtssEvcStatusEceInterfaceRxRedBytes, 
                  vtssEvcStatusEceInterfaceRxDiscardFrames, 
                  vtssEvcStatusEceInterfaceRxDiscardBytes, 
                  vtssEvcStatusEceInterfaceTxGreenFrames, 
                  vtssEvcStatusEceInterfaceTxGreenBytes, 
                  vtssEvcStatusEceInterfaceTxYellowFrames, 
                  vtssEvcStatusEceInterfaceTxYellowBytes, 
                  vtssEvcStatusEceInterfaceTxDiscardFrames, 
                  vtssEvcStatusEceInterfaceTxDiscardBytes }
    STATUS      current
    DESCRIPTION
        "A collection of objects suitable for bulk operations."
    ::= { vtssEvcMibGroups 16 }

vtssEvcControlEvcInterfaceTableInfoGroup OBJECT-GROUP
    OBJECTS     { vtssEvcControlEvcInterfaceClearStatistics }
    STATUS      current
    DESCRIPTION
        "A collection of objects suitable for bulk operations."
    ::= { vtssEvcMibGroups 17 }

vtssEvcControlEceInterfaceTableInfoGroup OBJECT-GROUP
    OBJECTS     { vtssEvcControlEceInterfaceClearStatistics }
    STATUS      current
    DESCRIPTION
        "A collection of objects suitable for bulk operations."
    ::= { vtssEvcMibGroups 18 }

vtssEvcMibCompliance MODULE-COMPLIANCE
    STATUS      current
    DESCRIPTION
        "The compliance statement for the implementation."

    MODULE      -- this module

        MANDATORY-GROUPS        { vtssEvcCapabilitiesInfoGroup, 
                  vtssEvcConfigInterfaceTableInfoGroup, 
                  vtssEvcConfigInterfaceL2cpTableInfoGroup, 
                  vtssEvcConfigPolicerTableInfoGroup, 
                  vtssEvcConfigEvcTableInfoGroup, 
                  vtssEvcConfigEvcTableRowEditorInfoGroup, 
                  vtssEvcConfigEceTableInfoGroup, 
                  vtssEvcConfigEceTableRowEditorInfoGroup, 
                  vtssEvcConfigEcePrecedenceTableInfoGroup, 
                  vtssEvcConfigEvcInterfaceTableInfoGroup, 
                  vtssEvcConfigMplsTpPwTableInfoGroup, 
                  vtssEvcConfigMplsTpPwTableRowEditorInfoGroup, 
                  vtssEvcStatusEvcTableInfoGroup, vtssEvcStatusEceTableInfoGroup, 
                  vtssEvcStatusEvcInterfaceTableInfoGroup, 
                  vtssEvcStatusEceInterfaceTableInfoGroup, 
                  vtssEvcControlEvcInterfaceTableInfoGroup, 
                  vtssEvcControlEceInterfaceTableInfoGroup }

    ::= { vtssEvcMibCompliances 1 }

END
