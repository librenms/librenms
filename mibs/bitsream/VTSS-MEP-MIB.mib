-- *****************************************************************
-- MEP-MIB:  Vitesse private MIB
--
-- Copyright (c) 2002-2013 Vitesse Semiconductor Corporation "Vitesse".
-- All Rights Reserved.
--
-- ****************************************************************

VTSS-MEP-MIB DEFINITIONS ::= BEGIN

IMPORTS
    MODULE-COMPLIANCE, OBJECT-GROUP
        FROM SNMPv2-CONF
    MODULE-IDENTITY, OBJECT-TYPE
        FROM SNMPv2-SMI
    TEXTUAL-CONVENTION
        FROM SNMPv2-TC
    vtssSwitchMgmt
        FROM VTSS-SMI
    Counter64 FROM SNMPv2-SMI
    Integer32 FROM SNMPv2-SMI
    IpAddress FROM SNMPv2-SMI
    Unsigned32 FROM SNMPv2-SMI
    MacAddress FROM SNMPv2-TC
    TruthValue FROM SNMPv2-TC
    VTSSDisplayString FROM VTSS-TC
    VTSSInterfaceIndex FROM VTSS-TC
    VTSSRowEditorState FROM VTSS-TC
    VTSSUnsigned16 FROM VTSS-TC
    VTSSUnsigned64 FROM VTSS-TC
    VTSSUnsigned8 FROM VTSS-TC
    ;

vtssMepMib MODULE-IDENTITY
    LAST-UPDATED "201501190000Z"
    ORGANIZATION
        "Vitesse Semiconductor Corporation"
    CONTACT-INFO
        "Application support <application_support@vitesse.com>"
    DESCRIPTION
        "This is a private service OAM (Y.1731/G802.1ag/G8113.1/G8113.2) MIB"
    REVISION    "201501190000Z"
    DESCRIPTION
        "Added Loss Measurement Availability, High Loss Interval and Signal
         Degrade"
    REVISION    "201501020000Z"
    DESCRIPTION
        "Removed DEI"
    REVISION    "201412030000Z"
    DESCRIPTION
        "Adding Link State Tracking"
    REVISION    "201411260000Z"
    DESCRIPTION
        "Adding Loss Measurement OAM frame counting object"
    REVISION    "201411140000Z"
    DESCRIPTION
        "Refactoring regarding Ifindex. Domain element is removed and flow
         element is changed to be Ifindex containing domain"
    REVISION    "201409300000Z"
    DESCRIPTION
        "Added vtssMepConfigRt and vtssMepStatusRt for Route Trace configuration
         and status"
    REVISION    "201409030000Z"
    DESCRIPTION
        "Added vtssMepConfigClientFlowDomain and vtssMepConfigClientFlowFlowId
         to vtssMepConfigClientFlowTable"
    REVISION    "201407010000Z"
    DESCRIPTION
        "Initial version"
    ::= { vtssSwitchMgmt 46 }


VTSSMepApsType ::= TEXTUAL-CONVENTION
    STATUS      current
    DESCRIPTION
        "Type of APS."
    SYNTAX      INTEGER { invalidAps(0), linearAps(1), ringAps(2) }

VTSSMepBfdAuthenticationType ::= TEXTUAL-CONVENTION
    STATUS      current
    DESCRIPTION
        "BFD authentication type."
    SYNTAX      INTEGER { disabled(0), simplePwd(1), keyedMD5(2), meticulousKeyedMD5(3), keyedSHA1(4), meticulousKeyedSHA1(5) }

VTSSMepBfdDiagnosticCode ::= TEXTUAL-CONVENTION
    STATUS      current
    DESCRIPTION
        "BFD diagnostic code."
    SYNTAX      INTEGER { none(0), detectExpired(1), echoFailed(2), remoteDown(3), fwdPlaneReset(4), pathDown(5), concatPathDown(6), adminDown(7), reverseConcatDown(8), misconnectivity(9) }

VTSSMepBfdSessionState ::= TEXTUAL-CONVENTION
    STATUS      current
    DESCRIPTION
        "State of BFD session."
    SYNTAX      INTEGER { adminDown(0), down(1), init(2), up(3) }

VTSSMepCast ::= TEXTUAL-CONVENTION
    STATUS      current
    DESCRIPTION
        "Unicast or Multicast selection."
    SYNTAX      INTEGER { uniCast(0), multiCast(1) }

VTSSMepDmCalcWay ::= TEXTUAL-CONVENTION
    STATUS      current
    DESCRIPTION
        "Round trip or flow calculation way selection."
    SYNTAX      INTEGER { roundTrip(0), flow(1) }

VTSSMepDmOverflowAction ::= TEXTUAL-CONVENTION
    STATUS      current
    DESCRIPTION
        "Action when internal total delay counter overflow."
    SYNTAX      INTEGER { disableDm(0), continueDm(1) }

VTSSMepDmTimeUnit ::= TEXTUAL-CONVENTION
    STATUS      current
    DESCRIPTION
        "Calculation time unit."
    SYNTAX      INTEGER { microSeconds(0), nanoSeconds(1) }

VTSSMepEnded ::= TEXTUAL-CONVENTION
    STATUS      current
    DESCRIPTION
        "Dual/single ended selection."
    SYNTAX      INTEGER { singleEnded(0), dualEnded(1) }

VTSSMepInstanceDirection ::= TEXTUAL-CONVENTION
    STATUS      current
    DESCRIPTION
        "The instance direction."
    SYNTAX      INTEGER { down(0), up(1) }

VTSSMepInstanceMode ::= TEXTUAL-CONVENTION
    STATUS      current
    DESCRIPTION
        "The instance mode."
    SYNTAX      INTEGER { mep(0), mip(1) }

VTSSMepLmAvailState ::= TEXTUAL-CONVENTION
    STATUS      current
    DESCRIPTION
        "Loss Measurement Availability State."
    SYNTAX      INTEGER { available(0), unavailable(1) }

VTSSMepLtRelayAction ::= TEXTUAL-CONVENTION
    STATUS      current
    DESCRIPTION
        "The Link Trace relay action."
    SYNTAX      INTEGER { relayUnknown(0), relayHit(1), relayFdb(2), relayMpdb(3) }

VTSSMepMegIdFormat ::= TEXTUAL-CONVENTION
    STATUS      current
    DESCRIPTION
        "The MEG-ID format."
    SYNTAX      INTEGER { ituIcc(0), ieeeString(1), ituCcIcc(2) }

VTSSMepOamCount ::= TEXTUAL-CONVENTION
    STATUS      current
    DESCRIPTION
        "Loss Measurement OAM frame counting selection."
    SYNTAX      INTEGER { countAsY1731(0), countNone(1), countAll(2) }

VTSSMepRtPadTlvType ::= TEXTUAL-CONVENTION
    STATUS      current
    DESCRIPTION
        "RT Pad TLV type."
    SYNTAX      INTEGER { none(0), drop(1), copy(2) }

VTSSMepRtReturnCode ::= TEXTUAL-CONVENTION
    STATUS      current
    DESCRIPTION
        "RT return code type."
    SYNTAX      INTEGER { none(0), malformed(1), tlvError(2), isEgress(3), noMapping(4), downMapMismatch(5), upIfUnknown(6), labelSwitch(8), labelSwitchNoFwd(9), mappingWrong(10), noLabel(11), protocolError(12), premature(13) }

VTSSMepTstPattern ::= TEXTUAL-CONVENTION
    STATUS      current
    DESCRIPTION
        "Pattern in TST frame Data TLV."
    SYNTAX      INTEGER { allZero(0), allOne(1), hexAA(2) }

VTSSMepTxRate ::= TEXTUAL-CONVENTION
    STATUS      current
    DESCRIPTION
        "PDU transmission rate."
    SYNTAX      INTEGER { invalid(0), frames300PerSecond(1), frames100PerSecond(2), frames10PerSecond(3), frames1PerSecond(4), frames6PerMinute(5), frames1PerMinute(6), frames6PerHour(7) }

vtssMepMibObjects OBJECT IDENTIFIER
    ::= { vtssMepMib 1 }

vtssMepCapabilities OBJECT IDENTIFIER
    ::= { vtssMepMibObjects 1 }

vtssMepCapabilitiesInstanceMax OBJECT-TYPE
    SYNTAX      Unsigned32
    MAX-ACCESS  read-only
    STATUS      current
    DESCRIPTION 
        "Max number of MEP instance"
    ::= { vtssMepCapabilities 1 }

vtssMepCapabilitiesPeerMax OBJECT-TYPE
    SYNTAX      Unsigned32
    MAX-ACCESS  read-only
    STATUS      current
    DESCRIPTION 
        "Max number of peer MEP"
    ::= { vtssMepCapabilities 2 }

vtssMepCapabilitiesTransactionMax OBJECT-TYPE
    SYNTAX      Unsigned32
    MAX-ACCESS  read-only
    STATUS      current
    DESCRIPTION 
        "Max number of Link Trace transaction"
    ::= { vtssMepCapabilities 3 }

vtssMepCapabilitiesReplyMax OBJECT-TYPE
    SYNTAX      Unsigned32
    MAX-ACCESS  read-only
    STATUS      current
    DESCRIPTION 
        "Max number of reply in a transaction"
    ::= { vtssMepCapabilities 4 }

vtssMepCapabilitiesClientFlowsMax OBJECT-TYPE
    SYNTAX      Unsigned32
    MAX-ACCESS  read-only
    STATUS      current
    DESCRIPTION 
        "Max number of client flows"
    ::= { vtssMepCapabilities 5 }

vtssMepCapabilitiesMacMength OBJECT-TYPE
    SYNTAX      Unsigned32
    MAX-ACCESS  read-only
    STATUS      current
    DESCRIPTION 
        "MAC length"
    ::= { vtssMepCapabilities 6 }

vtssMepCapabilitiesMegCodeLength OBJECT-TYPE
    SYNTAX      Unsigned32
    MAX-ACCESS  read-only
    STATUS      current
    DESCRIPTION 
        "MAX length of Both Maintenance Domain Name and MEG-ID include a NULL
         termination"
    ::= { vtssMepCapabilities 7 }

vtssMepCapabilitiesDmIntervalMin OBJECT-TYPE
    SYNTAX      Unsigned32
    MAX-ACCESS  read-only
    STATUS      current
    DESCRIPTION 
        "MIN DM transmission interval "
    ::= { vtssMepCapabilities 8 }

vtssMepCapabilitiesDmIntervalMax OBJECT-TYPE
    SYNTAX      Unsigned32
    MAX-ACCESS  read-only
    STATUS      current
    DESCRIPTION 
        "MAX DM transmission interval"
    ::= { vtssMepCapabilities 9 }

vtssMepCapabilitiesDmLastnMin OBJECT-TYPE
    SYNTAX      Unsigned32
    MAX-ACCESS  read-only
    STATUS      current
    DESCRIPTION 
        "MIN number of DM LastN for average calculation"
    ::= { vtssMepCapabilities 10 }

vtssMepCapabilitiesDmLastnMax OBJECT-TYPE
    SYNTAX      Unsigned32
    MAX-ACCESS  read-only
    STATUS      current
    DESCRIPTION 
        "MAX number of DM LastN for average calculation"
    ::= { vtssMepCapabilities 11 }

vtssMepCapabilitiesLbmSizeMax OBJECT-TYPE
    SYNTAX      Unsigned32
    MAX-ACCESS  read-only
    STATUS      current
    DESCRIPTION 
        "The maximum LBM frame size"
    ::= { vtssMepCapabilities 12 }

vtssMepCapabilitiesLbmSizeMin OBJECT-TYPE
    SYNTAX      Unsigned32
    MAX-ACCESS  read-only
    STATUS      current
    DESCRIPTION 
        "The minimum LBM frame size"
    ::= { vtssMepCapabilities 13 }

vtssMepCapabilitiesTstSizeMax OBJECT-TYPE
    SYNTAX      Unsigned32
    MAX-ACCESS  read-only
    STATUS      current
    DESCRIPTION 
        "The maximum TST frame size"
    ::= { vtssMepCapabilities 14 }

vtssMepCapabilitiesTstSizeMin OBJECT-TYPE
    SYNTAX      Unsigned32
    MAX-ACCESS  read-only
    STATUS      current
    DESCRIPTION 
        "The minimum TST frame size"
    ::= { vtssMepCapabilities 15 }

vtssMepCapabilitiesTstRateMax OBJECT-TYPE
    SYNTAX      Unsigned32
    MAX-ACCESS  read-only
    STATUS      current
    DESCRIPTION 
        "The maximum TST bit rate"
    ::= { vtssMepCapabilities 16 }

vtssMepCapabilitiesClientPrioHighest OBJECT-TYPE
    SYNTAX      Unsigned32
    MAX-ACCESS  read-only
    STATUS      current
    DESCRIPTION 
        "The highest possible client priority is requested"
    ::= { vtssMepCapabilities 17 }

vtssMepCapabilitiesItuG8113dot2 OBJECT-TYPE
    SYNTAX      TruthValue
    MAX-ACCESS  read-only
    STATUS      current
    DESCRIPTION 
        "Indicates if ITU G8113.2 is supported on this system"
    ::= { vtssMepCapabilities 18 }

vtssMepCapabilitiesVoeSupport OBJECT-TYPE
    SYNTAX      TruthValue
    MAX-ACCESS  read-only
    STATUS      current
    DESCRIPTION 
        "Indicates if VOE is supported on this system"
    ::= { vtssMepCapabilities 19 }

vtssMepCapabilitiesLbToSendInfinite OBJECT-TYPE
    SYNTAX      Unsigned32
    MAX-ACCESS  read-only
    STATUS      current
    DESCRIPTION 
        "Send LBM infinite - test behaviour"
    ::= { vtssMepCapabilities 20 }

vtssMepCapabilitiesBfdAuthKeyMax OBJECT-TYPE
    SYNTAX      Unsigned32
    MAX-ACCESS  read-only
    STATUS      current
    DESCRIPTION 
        "Maximum number of BFD authentication keys"
    ::= { vtssMepCapabilities 21 }

vtssMepConfig OBJECT IDENTIFIER
    ::= { vtssMepMibObjects 2 }

vtssMepConfigInstance OBJECT IDENTIFIER
    ::= { vtssMepConfig 1 }

vtssMepConfigInstanceTable OBJECT-TYPE
    SYNTAX      SEQUENCE OF VTSSMepConfigInstanceEntry
    MAX-ACCESS  not-accessible
    STATUS      current
    DESCRIPTION 
        "This is a table of created instance configuration parameters"
    ::= { vtssMepConfigInstance 1 }

vtssMepConfigInstanceEntry OBJECT-TYPE
    SYNTAX      VTSSMepConfigInstanceEntry
    MAX-ACCESS  not-accessible
    STATUS      current
    DESCRIPTION 
        "This is a created instance configuration parameters. Not all parameters
         can be changed"
    INDEX       { vtssMepConfigInstanceId }
    ::= { vtssMepConfigInstanceTable 1 }

VTSSMepConfigInstanceEntry ::= SEQUENCE {
    vtssMepConfigInstanceId     Integer32,
    vtssMepConfigInstanceMode   VTSSMepInstanceMode,
    vtssMepConfigInstanceDirection      VTSSMepInstanceDirection,
    vtssMepConfigInstanceFlow   VTSSInterfaceIndex,
    vtssMepConfigInstancePort   VTSSInterfaceIndex,
    vtssMepConfigInstanceLevel      Unsigned32,
    vtssMepConfigInstanceVid    VTSSUnsigned16,
    vtssMepConfigInstanceVoe    TruthValue,
    vtssMepConfigInstanceMac    MacAddress,
    vtssMepConfigInstanceFormat     VTSSMepMegIdFormat,
    vtssMepConfigInstanceName   VTSSDisplayString,
    vtssMepConfigInstanceMeg    VTSSDisplayString,
    vtssMepConfigInstanceMep    Unsigned32,
    vtssMepConfigInstanceEvcPag     Unsigned32,
    vtssMepConfigInstanceEvcQos     Unsigned32,
    vtssMepConfigInstanceAction     VTSSRowEditorState
}

vtssMepConfigInstanceId OBJECT-TYPE
    SYNTAX      Integer32 (0..2147483647)
    MAX-ACCESS  not-accessible
    STATUS      current
    DESCRIPTION 
        "The MEP instance ID"
    ::= { vtssMepConfigInstanceEntry 1 }

vtssMepConfigInstanceMode OBJECT-TYPE
    SYNTAX      VTSSMepInstanceMode
    MAX-ACCESS  read-write
    STATUS      current
    DESCRIPTION 
        "The instance mode. Cannot be changed after creation."
    ::= { vtssMepConfigInstanceEntry 2 }

vtssMepConfigInstanceDirection OBJECT-TYPE
    SYNTAX      VTSSMepInstanceDirection
    MAX-ACCESS  read-write
    STATUS      current
    DESCRIPTION 
        "The instance direction. Cannot be changed after creation."
    ::= { vtssMepConfigInstanceEntry 3 }

vtssMepConfigInstanceFlow OBJECT-TYPE
    SYNTAX      VTSSInterfaceIndex
    MAX-ACCESS  read-write
    STATUS      current
    DESCRIPTION 
        "The flow instance (VLAN - EVC). Cannot be changed after creation."
    ::= { vtssMepConfigInstanceEntry 4 }

vtssMepConfigInstancePort OBJECT-TYPE
    SYNTAX      VTSSInterfaceIndex
    MAX-ACCESS  read-write
    STATUS      current
    DESCRIPTION 
        "The instance residence port. Cannot be changed after creation."
    ::= { vtssMepConfigInstanceEntry 5 }

vtssMepConfigInstanceLevel OBJECT-TYPE
    SYNTAX      Unsigned32
    MAX-ACCESS  read-write
    STATUS      current
    DESCRIPTION 
        "The instance level"
    ::= { vtssMepConfigInstanceEntry 6 }

vtssMepConfigInstanceVid OBJECT-TYPE
    SYNTAX      VTSSUnsigned16
    MAX-ACCESS  read-write
    STATUS      current
    DESCRIPTION 
        "VID used for tagged Port domain OAM. Create a VLAN MEP instead - if
         possible"
    ::= { vtssMepConfigInstanceEntry 7 }

vtssMepConfigInstanceVoe OBJECT-TYPE
    SYNTAX      TruthValue
    MAX-ACCESS  read-write
    STATUS      current
    DESCRIPTION 
        "Make the instance VOE based - if possible"
    ::= { vtssMepConfigInstanceEntry 8 }

vtssMepConfigInstanceMac OBJECT-TYPE
    SYNTAX      MacAddress
    MAX-ACCESS  read-write
    STATUS      current
    DESCRIPTION 
        "The instance unicast MAC. If 'all zero' the residence port MAC is used"
    ::= { vtssMepConfigInstanceEntry 9 }

vtssMepConfigInstanceFormat OBJECT-TYPE
    SYNTAX      VTSSMepMegIdFormat
    MAX-ACCESS  read-write
    STATUS      current
    DESCRIPTION 
        "The MEG-ID format"
    ::= { vtssMepConfigInstanceEntry 10 }

vtssMepConfigInstanceName OBJECT-TYPE
    SYNTAX      VTSSDisplayString (SIZE(0..16))
    MAX-ACCESS  read-write
    STATUS      current
    DESCRIPTION 
        "IEEE Maintenance Domain Name (string)"
    ::= { vtssMepConfigInstanceEntry 11 }

vtssMepConfigInstanceMeg OBJECT-TYPE
    SYNTAX      VTSSDisplayString (SIZE(0..16))
    MAX-ACCESS  read-write
    STATUS      current
    DESCRIPTION 
        "Unique MEG ID (string)"
    ::= { vtssMepConfigInstanceEntry 12 }

vtssMepConfigInstanceMep OBJECT-TYPE
    SYNTAX      Unsigned32
    MAX-ACCESS  read-write
    STATUS      current
    DESCRIPTION 
        "MEP id of this instance"
    ::= { vtssMepConfigInstanceEntry 13 }

vtssMepConfigInstanceEvcPag OBJECT-TYPE
    SYNTAX      Unsigned32
    MAX-ACCESS  read-write
    STATUS      current
    DESCRIPTION 
        "EVC generated policy PAG value. This is used as IS2 key"
    ::= { vtssMepConfigInstanceEntry 14 }

vtssMepConfigInstanceEvcQos OBJECT-TYPE
    SYNTAX      Unsigned32
    MAX-ACCESS  read-write
    STATUS      current
    DESCRIPTION 
        "EVC QoS value. Used for getting queue frame LM counters."
    ::= { vtssMepConfigInstanceEntry 15 }

vtssMepConfigInstanceAction OBJECT-TYPE
    SYNTAX      VTSSRowEditorState
    MAX-ACCESS  read-write
    STATUS      current
    DESCRIPTION 
        "Action"
    ::= { vtssMepConfigInstanceEntry 100 }

vtssMepConfigInstanceRowEditor OBJECT IDENTIFIER
    ::= { vtssMepConfigInstance 2 }

vtssMepConfigInstanceRowEditorId OBJECT-TYPE
    SYNTAX      Integer32 (0..2147483647)
    MAX-ACCESS  read-write
    STATUS      current
    DESCRIPTION 
        "The MEP instance ID"
    ::= { vtssMepConfigInstanceRowEditor 1 }

vtssMepConfigInstanceRowEditorMode OBJECT-TYPE
    SYNTAX      VTSSMepInstanceMode
    MAX-ACCESS  read-write
    STATUS      current
    DESCRIPTION 
        "The instance mode. Cannot be changed after creation."
    ::= { vtssMepConfigInstanceRowEditor 2 }

vtssMepConfigInstanceRowEditorDirection OBJECT-TYPE
    SYNTAX      VTSSMepInstanceDirection
    MAX-ACCESS  read-write
    STATUS      current
    DESCRIPTION 
        "The instance direction. Cannot be changed after creation."
    ::= { vtssMepConfigInstanceRowEditor 3 }

vtssMepConfigInstanceRowEditorFlow OBJECT-TYPE
    SYNTAX      VTSSInterfaceIndex
    MAX-ACCESS  read-write
    STATUS      current
    DESCRIPTION 
        "The flow instance (VLAN - EVC). Cannot be changed after creation."
    ::= { vtssMepConfigInstanceRowEditor 4 }

vtssMepConfigInstanceRowEditorPort OBJECT-TYPE
    SYNTAX      VTSSInterfaceIndex
    MAX-ACCESS  read-write
    STATUS      current
    DESCRIPTION 
        "The instance residence port. Cannot be changed after creation."
    ::= { vtssMepConfigInstanceRowEditor 5 }

vtssMepConfigInstanceRowEditorLevel OBJECT-TYPE
    SYNTAX      Unsigned32
    MAX-ACCESS  read-write
    STATUS      current
    DESCRIPTION 
        "The instance level"
    ::= { vtssMepConfigInstanceRowEditor 6 }

vtssMepConfigInstanceRowEditorVid OBJECT-TYPE
    SYNTAX      VTSSUnsigned16
    MAX-ACCESS  read-write
    STATUS      current
    DESCRIPTION 
        "VID used for tagged Port domain OAM. Create a VLAN MEP instead - if
         possible"
    ::= { vtssMepConfigInstanceRowEditor 7 }

vtssMepConfigInstanceRowEditorVoe OBJECT-TYPE
    SYNTAX      TruthValue
    MAX-ACCESS  read-write
    STATUS      current
    DESCRIPTION 
        "Make the instance VOE based - if possible"
    ::= { vtssMepConfigInstanceRowEditor 8 }

vtssMepConfigInstanceRowEditorMac OBJECT-TYPE
    SYNTAX      MacAddress
    MAX-ACCESS  read-write
    STATUS      current
    DESCRIPTION 
        "The instance unicast MAC. If 'all zero' the residence port MAC is used"
    ::= { vtssMepConfigInstanceRowEditor 9 }

vtssMepConfigInstanceRowEditorFormat OBJECT-TYPE
    SYNTAX      VTSSMepMegIdFormat
    MAX-ACCESS  read-write
    STATUS      current
    DESCRIPTION 
        "The MEG-ID format"
    ::= { vtssMepConfigInstanceRowEditor 10 }

vtssMepConfigInstanceRowEditorName OBJECT-TYPE
    SYNTAX      VTSSDisplayString (SIZE(0..16))
    MAX-ACCESS  read-write
    STATUS      current
    DESCRIPTION 
        "IEEE Maintenance Domain Name (string)"
    ::= { vtssMepConfigInstanceRowEditor 11 }

vtssMepConfigInstanceRowEditorMeg OBJECT-TYPE
    SYNTAX      VTSSDisplayString (SIZE(0..16))
    MAX-ACCESS  read-write
    STATUS      current
    DESCRIPTION 
        "Unique MEG ID (string)"
    ::= { vtssMepConfigInstanceRowEditor 12 }

vtssMepConfigInstanceRowEditorMep OBJECT-TYPE
    SYNTAX      Unsigned32
    MAX-ACCESS  read-write
    STATUS      current
    DESCRIPTION 
        "MEP id of this instance"
    ::= { vtssMepConfigInstanceRowEditor 13 }

vtssMepConfigInstanceRowEditorEvcPag OBJECT-TYPE
    SYNTAX      Unsigned32
    MAX-ACCESS  read-write
    STATUS      current
    DESCRIPTION 
        "EVC generated policy PAG value. This is used as IS2 key"
    ::= { vtssMepConfigInstanceRowEditor 14 }

vtssMepConfigInstanceRowEditorEvcQos OBJECT-TYPE
    SYNTAX      Unsigned32
    MAX-ACCESS  read-write
    STATUS      current
    DESCRIPTION 
        "EVC QoS value. Used for getting queue frame LM counters."
    ::= { vtssMepConfigInstanceRowEditor 15 }

vtssMepConfigInstanceRowEditorAction OBJECT-TYPE
    SYNTAX      VTSSRowEditorState
    MAX-ACCESS  read-write
    STATUS      current
    DESCRIPTION 
        "Action"
    ::= { vtssMepConfigInstanceRowEditor 100 }

vtssMepConfigInstancePeerTable OBJECT-TYPE
    SYNTAX      SEQUENCE OF VTSSMepConfigInstancePeerEntry
    MAX-ACCESS  not-accessible
    STATUS      current
    DESCRIPTION 
        "This is a table of peer MEP configuration parameters"
    ::= { vtssMepConfigInstance 3 }

vtssMepConfigInstancePeerEntry OBJECT-TYPE
    SYNTAX      VTSSMepConfigInstancePeerEntry
    MAX-ACCESS  not-accessible
    STATUS      current
    DESCRIPTION 
        "This is a peer MEP configuration parameters"
    INDEX       { vtssMepConfigInstancePeerId, vtssMepConfigInstancePeerPeerId }
    ::= { vtssMepConfigInstancePeerTable 1 }

VTSSMepConfigInstancePeerEntry ::= SEQUENCE {
    vtssMepConfigInstancePeerId     Integer32,
    vtssMepConfigInstancePeerPeerId     Integer32,
    vtssMepConfigInstancePeerMac    MacAddress,
    vtssMepConfigInstancePeerAction     VTSSRowEditorState
}

vtssMepConfigInstancePeerId OBJECT-TYPE
    SYNTAX      Integer32 (0..2147483647)
    MAX-ACCESS  not-accessible
    STATUS      current
    DESCRIPTION 
        "The MEP instance ID"
    ::= { vtssMepConfigInstancePeerEntry 1 }

vtssMepConfigInstancePeerPeerId OBJECT-TYPE
    SYNTAX      Integer32 (0..2147483647)
    MAX-ACCESS  not-accessible
    STATUS      current
    DESCRIPTION 
        "The Peer MEP ID"
    ::= { vtssMepConfigInstancePeerEntry 2 }

vtssMepConfigInstancePeerMac OBJECT-TYPE
    SYNTAX      MacAddress
    MAX-ACCESS  read-write
    STATUS      current
    DESCRIPTION 
        "The peer unicast MAC"
    ::= { vtssMepConfigInstancePeerEntry 3 }

vtssMepConfigInstancePeerAction OBJECT-TYPE
    SYNTAX      VTSSRowEditorState
    MAX-ACCESS  read-write
    STATUS      current
    DESCRIPTION 
        "Action"
    ::= { vtssMepConfigInstancePeerEntry 100 }

vtssMepConfigInstancePeerRowEditor OBJECT IDENTIFIER
    ::= { vtssMepConfigInstance 4 }

vtssMepConfigInstancePeerRowEditorId OBJECT-TYPE
    SYNTAX      Integer32 (0..2147483647)
    MAX-ACCESS  read-write
    STATUS      current
    DESCRIPTION 
        "The MEP instance ID"
    ::= { vtssMepConfigInstancePeerRowEditor 1 }

vtssMepConfigInstancePeerRowEditorPeerId OBJECT-TYPE
    SYNTAX      Integer32 (0..2147483647)
    MAX-ACCESS  read-write
    STATUS      current
    DESCRIPTION 
        "The Peer MEP ID"
    ::= { vtssMepConfigInstancePeerRowEditor 2 }

vtssMepConfigInstancePeerRowEditorMac OBJECT-TYPE
    SYNTAX      MacAddress
    MAX-ACCESS  read-write
    STATUS      current
    DESCRIPTION 
        "The peer unicast MAC"
    ::= { vtssMepConfigInstancePeerRowEditor 3 }

vtssMepConfigInstancePeerRowEditorAction OBJECT-TYPE
    SYNTAX      VTSSRowEditorState
    MAX-ACCESS  read-write
    STATUS      current
    DESCRIPTION 
        "Action"
    ::= { vtssMepConfigInstancePeerRowEditor 100 }

vtssMepConfigPm OBJECT IDENTIFIER
    ::= { vtssMepConfig 2 }

vtssMepConfigPmTable OBJECT-TYPE
    SYNTAX      SEQUENCE OF VTSSMepConfigPmEntry
    MAX-ACCESS  not-accessible
    STATUS      current
    DESCRIPTION 
        "This is a table of created instance Performance Monitoring
         configuration parameters"
    ::= { vtssMepConfigPm 1 }

vtssMepConfigPmEntry OBJECT-TYPE
    SYNTAX      VTSSMepConfigPmEntry
    MAX-ACCESS  not-accessible
    STATUS      current
    DESCRIPTION 
        "This is a created instance Performance Monitoring configuration
         parameters"
    INDEX       { vtssMepConfigPmId }
    ::= { vtssMepConfigPmTable 1 }

VTSSMepConfigPmEntry ::= SEQUENCE {
    vtssMepConfigPmId   Integer32,
    vtssMepConfigPmEnable   TruthValue
}

vtssMepConfigPmId OBJECT-TYPE
    SYNTAX      Integer32 (0..2147483647)
    MAX-ACCESS  not-accessible
    STATUS      current
    DESCRIPTION 
        "The MEP instance ID"
    ::= { vtssMepConfigPmEntry 1 }

vtssMepConfigPmEnable OBJECT-TYPE
    SYNTAX      TruthValue
    MAX-ACCESS  read-write
    STATUS      current
    DESCRIPTION 
        "The instance can enable contribution of LM and DM results to the
         Performance Monitoring "
    ::= { vtssMepConfigPmEntry 2 }

vtssMepConfigCc OBJECT IDENTIFIER
    ::= { vtssMepConfig 3 }

vtssMepConfigCcTable OBJECT-TYPE
    SYNTAX      SEQUENCE OF VTSSMepConfigCcEntry
    MAX-ACCESS  not-accessible
    STATUS      current
    DESCRIPTION 
        "This is a table of created instance Continuity Check configuration
         parameters"
    ::= { vtssMepConfigCc 1 }

vtssMepConfigCcEntry OBJECT-TYPE
    SYNTAX      VTSSMepConfigCcEntry
    MAX-ACCESS  not-accessible
    STATUS      current
    DESCRIPTION 
        "This is a created instance Continuity Check configuration parameters."
    INDEX       { vtssMepConfigCcId }
    ::= { vtssMepConfigCcTable 1 }

VTSSMepConfigCcEntry ::= SEQUENCE {
    vtssMepConfigCcId   Integer32,
    vtssMepConfigCcPrio     Unsigned32,
    vtssMepConfigCcRate     VTSSMepTxRate,
    vtssMepConfigCcTlv      TruthValue,
    vtssMepConfigCcAction   VTSSRowEditorState
}

vtssMepConfigCcId OBJECT-TYPE
    SYNTAX      Integer32 (0..2147483647)
    MAX-ACCESS  not-accessible
    STATUS      current
    DESCRIPTION 
        "The MEP instance ID"
    ::= { vtssMepConfigCcEntry 1 }

vtssMepConfigCcPrio OBJECT-TYPE
    SYNTAX      Unsigned32
    MAX-ACCESS  read-write
    STATUS      current
    DESCRIPTION 
        "Priority of the transmitted CCM. Range 0 to 7"
    ::= { vtssMepConfigCcEntry 3 }

vtssMepConfigCcRate OBJECT-TYPE
    SYNTAX      VTSSMepTxRate
    MAX-ACCESS  read-write
    STATUS      current
    DESCRIPTION 
        "CCM transmission and expected reception rate"
    ::= { vtssMepConfigCcEntry 4 }

vtssMepConfigCcTlv OBJECT-TYPE
    SYNTAX      TruthValue
    MAX-ACCESS  read-write
    STATUS      current
    DESCRIPTION 
        "Enable/disable insertion of TLV in CCM PDU. OS, PS and IS TLV are
         inserted"
    ::= { vtssMepConfigCcEntry 5 }

vtssMepConfigCcAction OBJECT-TYPE
    SYNTAX      VTSSRowEditorState
    MAX-ACCESS  read-write
    STATUS      current
    DESCRIPTION 
        "Action"
    ::= { vtssMepConfigCcEntry 100 }

vtssMepConfigCcRowEditor OBJECT IDENTIFIER
    ::= { vtssMepConfigCc 2 }

vtssMepConfigCcRowEditorId OBJECT-TYPE
    SYNTAX      Integer32 (0..2147483647)
    MAX-ACCESS  read-write
    STATUS      current
    DESCRIPTION 
        "The MEP instance ID"
    ::= { vtssMepConfigCcRowEditor 1 }

vtssMepConfigCcRowEditorPrio OBJECT-TYPE
    SYNTAX      Unsigned32
    MAX-ACCESS  read-write
    STATUS      current
    DESCRIPTION 
        "Priority of the transmitted CCM. Range 0 to 7"
    ::= { vtssMepConfigCcRowEditor 3 }

vtssMepConfigCcRowEditorRate OBJECT-TYPE
    SYNTAX      VTSSMepTxRate
    MAX-ACCESS  read-write
    STATUS      current
    DESCRIPTION 
        "CCM transmission and expected reception rate"
    ::= { vtssMepConfigCcRowEditor 4 }

vtssMepConfigCcRowEditorTlv OBJECT-TYPE
    SYNTAX      TruthValue
    MAX-ACCESS  read-write
    STATUS      current
    DESCRIPTION 
        "Enable/disable insertion of TLV in CCM PDU. OS, PS and IS TLV are
         inserted"
    ::= { vtssMepConfigCcRowEditor 5 }

vtssMepConfigCcRowEditorAction OBJECT-TYPE
    SYNTAX      VTSSRowEditorState
    MAX-ACCESS  read-write
    STATUS      current
    DESCRIPTION 
        "Action"
    ::= { vtssMepConfigCcRowEditor 100 }

vtssMepConfigLm OBJECT IDENTIFIER
    ::= { vtssMepConfig 4 }

vtssMepConfigLmTable OBJECT-TYPE
    SYNTAX      SEQUENCE OF VTSSMepConfigLmEntry
    MAX-ACCESS  not-accessible
    STATUS      current
    DESCRIPTION 
        "This is a table of created instance Loss Measurement configuration
         parameters"
    ::= { vtssMepConfigLm 1 }

vtssMepConfigLmEntry OBJECT-TYPE
    SYNTAX      VTSSMepConfigLmEntry
    MAX-ACCESS  not-accessible
    STATUS      current
    DESCRIPTION 
        "This is a created instance Loss Measurement parameters."
    INDEX       { vtssMepConfigLmId }
    ::= { vtssMepConfigLmTable 1 }

VTSSMepConfigLmEntry ::= SEQUENCE {
    vtssMepConfigLmId   Integer32,
    vtssMepConfigLmEnable   TruthValue,
    vtssMepConfigLmEnded    VTSSMepEnded,
    vtssMepConfigLmPrio     Unsigned32,
    vtssMepConfigLmRate     VTSSMepTxRate,
    vtssMepConfigLmCast     VTSSMepCast,
    vtssMepConfigLmFlrInterval      Unsigned32,
    vtssMepConfigLmFlowCount    TruthValue,
    vtssMepConfigLmOamCount     VTSSMepOamCount,
    vtssMepConfigLmLossTh   Unsigned32,
    vtssMepConfigLmLossCounterIntHolddownTimer      Unsigned32,
    vtssMepConfigLmLossThCntHolddownTimer   Unsigned32
}

vtssMepConfigLmId OBJECT-TYPE
    SYNTAX      Integer32 (0..2147483647)
    MAX-ACCESS  not-accessible
    STATUS      current
    DESCRIPTION 
        "The MEP instance ID"
    ::= { vtssMepConfigLmEntry 1 }

vtssMepConfigLmEnable OBJECT-TYPE
    SYNTAX      TruthValue
    MAX-ACCESS  read-write
    STATUS      current
    DESCRIPTION 
        "Loss Measurement is enabled"
    ::= { vtssMepConfigLmEntry 2 }

vtssMepConfigLmEnded OBJECT-TYPE
    SYNTAX      VTSSMepEnded
    MAX-ACCESS  read-write
    STATUS      current
    DESCRIPTION 
        "Dual/single ended selection. CCM or LMM/LMR based. Cannot be changed
         after creation."
    ::= { vtssMepConfigLmEntry 3 }

vtssMepConfigLmPrio OBJECT-TYPE
    SYNTAX      Unsigned32
    MAX-ACCESS  read-write
    STATUS      current
    DESCRIPTION 
        "Priority of the transmitted LM PDU. Range 0 to 7"
    ::= { vtssMepConfigLmEntry 5 }

vtssMepConfigLmRate OBJECT-TYPE
    SYNTAX      VTSSMepTxRate
    MAX-ACCESS  read-write
    STATUS      current
    DESCRIPTION 
        "LM PDU transmission rate"
    ::= { vtssMepConfigLmEntry 6 }

vtssMepConfigLmCast OBJECT-TYPE
    SYNTAX      VTSSMepCast
    MAX-ACCESS  read-write
    STATUS      current
    DESCRIPTION 
        "Uni/Multicast selection - on CCM based LM only multicast is possible"
    ::= { vtssMepConfigLmEntry 7 }

vtssMepConfigLmFlrInterval OBJECT-TYPE
    SYNTAX      Unsigned32
    MAX-ACCESS  read-write
    STATUS      current
    DESCRIPTION 
        "Frame loss ratio interval in number of measurements."
    ::= { vtssMepConfigLmEntry 8 }

vtssMepConfigLmFlowCount OBJECT-TYPE
    SYNTAX      TruthValue
    MAX-ACCESS  read-write
    STATUS      current
    DESCRIPTION 
        "Traffic (service frames) are counted per flow - all priority in one"
    ::= { vtssMepConfigLmEntry 9 }

vtssMepConfigLmOamCount OBJECT-TYPE
    SYNTAX      VTSSMepOamCount
    MAX-ACCESS  read-write
    STATUS      current
    DESCRIPTION 
        "Loss Measurement can count OAM frames in different ways."
    ::= { vtssMepConfigLmEntry 10 }

vtssMepConfigLmLossTh OBJECT-TYPE
    SYNTAX      Unsigned32
    MAX-ACCESS  read-write
    STATUS      current
    DESCRIPTION 
        "Frame loss threshold. The loss threshold count NearEndLosThCnt /
         FarEndLosThCnt is incremented if a loss measurement is above this
         threshold."
    ::= { vtssMepConfigLmEntry 11 }

vtssMepConfigLmLossCounterIntHolddownTimer OBJECT-TYPE
    SYNTAX      Unsigned32
    MAX-ACCESS  read-write
    STATUS      current
    DESCRIPTION 
        "Holddown timer in seconds for JSON notification updates for
         NearEndLosCounterInt and FarEndLosCounterInt."
    ::= { vtssMepConfigLmEntry 12 }

vtssMepConfigLmLossThCntHolddownTimer OBJECT-TYPE
    SYNTAX      Unsigned32
    MAX-ACCESS  read-write
    STATUS      current
    DESCRIPTION 
        "Holddown timer in seconds for JSON notification updates for
         NearEndLosThCnt and FarEndLosThCnt."
    ::= { vtssMepConfigLmEntry 13 }

vtssMepConfigDm OBJECT IDENTIFIER
    ::= { vtssMepConfig 5 }

vtssMepConfigDmTable OBJECT-TYPE
    SYNTAX      SEQUENCE OF VTSSMepConfigDmEntry
    MAX-ACCESS  not-accessible
    STATUS      current
    DESCRIPTION 
        "This is a table of created instance Delay Measurement configuration
         parameters"
    ::= { vtssMepConfigDm 1 }

vtssMepConfigDmEntry OBJECT-TYPE
    SYNTAX      VTSSMepConfigDmEntry
    MAX-ACCESS  not-accessible
    STATUS      current
    DESCRIPTION 
        "This is a created instance Delay Measurement parameters."
    INDEX       { vtssMepConfigDmId }
    ::= { vtssMepConfigDmTable 1 }

VTSSMepConfigDmEntry ::= SEQUENCE {
    vtssMepConfigDmId   Integer32,
    vtssMepConfigDmEnable   TruthValue,
    vtssMepConfigDmEnded    VTSSMepEnded,
    vtssMepConfigDmPrio     Unsigned32,
    vtssMepConfigDmCast     VTSSMepCast,
    vtssMepConfigDmMep      Unsigned32,
    vtssMepConfigDmCalcWay      VTSSMepDmCalcWay,
    vtssMepConfigDmInterval     Unsigned32,
    vtssMepConfigDmLastN    Unsigned32,
    vtssMepConfigDmTimeUnit     VTSSMepDmTimeUnit,
    vtssMepConfigDmOverflowAct      VTSSMepDmOverflowAction,
    vtssMepConfigDmSynchronized     TruthValue
}

vtssMepConfigDmId OBJECT-TYPE
    SYNTAX      Integer32 (0..2147483647)
    MAX-ACCESS  not-accessible
    STATUS      current
    DESCRIPTION 
        "The MEP instance ID"
    ::= { vtssMepConfigDmEntry 1 }

vtssMepConfigDmEnable OBJECT-TYPE
    SYNTAX      TruthValue
    MAX-ACCESS  read-write
    STATUS      current
    DESCRIPTION 
        "Delay Measurement is enabled"
    ::= { vtssMepConfigDmEntry 2 }

vtssMepConfigDmEnded OBJECT-TYPE
    SYNTAX      VTSSMepEnded
    MAX-ACCESS  read-write
    STATUS      current
    DESCRIPTION 
        "Dual/single ended selection. CCM or LMM/LMR based. Cannot be changed
         after creation."
    ::= { vtssMepConfigDmEntry 3 }

vtssMepConfigDmPrio OBJECT-TYPE
    SYNTAX      Unsigned32
    MAX-ACCESS  read-write
    STATUS      current
    DESCRIPTION 
        "Priority of the transmitted DM PDU. Range 0 to 7"
    ::= { vtssMepConfigDmEntry 5 }

vtssMepConfigDmCast OBJECT-TYPE
    SYNTAX      VTSSMepCast
    MAX-ACCESS  read-write
    STATUS      current
    DESCRIPTION 
        "Uni/Multicast selection"
    ::= { vtssMepConfigDmEntry 6 }

vtssMepConfigDmMep OBJECT-TYPE
    SYNTAX      Unsigned32
    MAX-ACCESS  read-write
    STATUS      current
    DESCRIPTION 
        "Peer MEP to receive DMM/1DM - only used if unicast"
    ::= { vtssMepConfigDmEntry 7 }

vtssMepConfigDmCalcWay OBJECT-TYPE
    SYNTAX      VTSSMepDmCalcWay
    MAX-ACCESS  read-write
    STATUS      current
    DESCRIPTION 
        "Round trip or flow calculation way selection."
    ::= { vtssMepConfigDmEntry 8 }

vtssMepConfigDmInterval OBJECT-TYPE
    SYNTAX      Unsigned32
    MAX-ACCESS  read-write
    STATUS      current
    DESCRIPTION 
        "Interval between 1DM/DMM in 10 ms. Range Capability dm_interval_min to
         dm_interval_max."
    ::= { vtssMepConfigDmEntry 9 }

vtssMepConfigDmLastN OBJECT-TYPE
    SYNTAX      Unsigned32
    MAX-ACCESS  read-write
    STATUS      current
    DESCRIPTION 
        "The number of last N measurements used to calculate average delay and
         variation. Range Capability dm_lastn_min to dm_lastn_max."
    ::= { vtssMepConfigDmEntry 10 }

vtssMepConfigDmTimeUnit OBJECT-TYPE
    SYNTAX      VTSSMepDmTimeUnit
    MAX-ACCESS  read-write
    STATUS      current
    DESCRIPTION 
        "Calculation time unit."
    ::= { vtssMepConfigDmEntry 11 }

vtssMepConfigDmOverflowAct OBJECT-TYPE
    SYNTAX      VTSSMepDmOverflowAction
    MAX-ACCESS  read-write
    STATUS      current
    DESCRIPTION 
        "Action when internal total delay counter overflow."
    ::= { vtssMepConfigDmEntry 12 }

vtssMepConfigDmSynchronized OBJECT-TYPE
    SYNTAX      TruthValue
    MAX-ACCESS  read-write
    STATUS      current
    DESCRIPTION 
        "Near-end and far-end is real-time synchronized. One-way DM calculation
         on receiving DMR."
    ::= { vtssMepConfigDmEntry 13 }

vtssMepConfigLb OBJECT IDENTIFIER
    ::= { vtssMepConfig 6 }

vtssMepConfigLbTable OBJECT-TYPE
    SYNTAX      SEQUENCE OF VTSSMepConfigLbEntry
    MAX-ACCESS  not-accessible
    STATUS      current
    DESCRIPTION 
        "This is a table of created instance Loop Back configuration parameters"
    ::= { vtssMepConfigLb 1 }

vtssMepConfigLbEntry OBJECT-TYPE
    SYNTAX      VTSSMepConfigLbEntry
    MAX-ACCESS  not-accessible
    STATUS      current
    DESCRIPTION 
        "This is a created instance Loop Back parameters. This cannot be changed"
    INDEX       { vtssMepConfigLbId }
    ::= { vtssMepConfigLbTable 1 }

VTSSMepConfigLbEntry ::= SEQUENCE {
    vtssMepConfigLbId   Integer32,
    vtssMepConfigLbDei      TruthValue,
    vtssMepConfigLbPrio     Unsigned32,
    vtssMepConfigLbCast     VTSSMepCast,
    vtssMepConfigLbMep      Unsigned32,
    vtssMepConfigLbMac      MacAddress,
    vtssMepConfigLbToSend   Unsigned32,
    vtssMepConfigLbSize     Unsigned32,
    vtssMepConfigLbInterval     Unsigned32,
    vtssMepConfigLbTimeToLive   VTSSUnsigned8,
    vtssMepConfigLbAction   VTSSRowEditorState
}

vtssMepConfigLbId OBJECT-TYPE
    SYNTAX      Integer32 (0..2147483647)
    MAX-ACCESS  not-accessible
    STATUS      current
    DESCRIPTION 
        "The MEP instance ID"
    ::= { vtssMepConfigLbEntry 1 }

vtssMepConfigLbDei OBJECT-TYPE
    SYNTAX      TruthValue
    MAX-ACCESS  read-write
    STATUS      current
    DESCRIPTION 
        "Drop Eligibility Indicator of transmitted LBM PDU"
    ::= { vtssMepConfigLbEntry 2 }

vtssMepConfigLbPrio OBJECT-TYPE
    SYNTAX      Unsigned32
    MAX-ACCESS  read-write
    STATUS      current
    DESCRIPTION 
        "Priority of the transmitted LBM PDU. Range 0 to 7"
    ::= { vtssMepConfigLbEntry 3 }

vtssMepConfigLbCast OBJECT-TYPE
    SYNTAX      VTSSMepCast
    MAX-ACCESS  read-write
    STATUS      current
    DESCRIPTION 
        "Uni/Multicast selection"
    ::= { vtssMepConfigLbEntry 4 }

vtssMepConfigLbMep OBJECT-TYPE
    SYNTAX      Unsigned32
    MAX-ACCESS  read-write
    STATUS      current
    DESCRIPTION 
        "Peer MEP to receive LBM - only used if unicast and 'mac' is 'all zero'."
    ::= { vtssMepConfigLbEntry 5 }

vtssMepConfigLbMac OBJECT-TYPE
    SYNTAX      MacAddress
    MAX-ACCESS  read-write
    STATUS      current
    DESCRIPTION 
        "Unicast MAC address to receive LBM - has to be used to send LBM to MIP."
    ::= { vtssMepConfigLbEntry 6 }

vtssMepConfigLbToSend OBJECT-TYPE
    SYNTAX      Unsigned32
    MAX-ACCESS  read-write
    STATUS      current
    DESCRIPTION 
        "Number of LBM to send. Capability lb_to_send_infinite => test
         behaviour. Requires VOE."
    ::= { vtssMepConfigLbEntry 7 }

vtssMepConfigLbSize OBJECT-TYPE
    SYNTAX      Unsigned32
    MAX-ACCESS  read-write
    STATUS      current
    DESCRIPTION 
        "Size of LBM frame to send - Range Capability lbm_size_min to
         lbm_size_max"
    ::= { vtssMepConfigLbEntry 8 }

vtssMepConfigLbInterval OBJECT-TYPE
    SYNTAX      Unsigned32
    MAX-ACCESS  read-write
    STATUS      current
    DESCRIPTION 
        "Frame interval.
         
         If 'ToSend' != Capability lb_to_send_infinite then the 'Interval' is in
         10 ms. Max 1 s.
         
         If 'ToSend' == Capability lb_to_send_infinite then the 'Interval' is in
         1 us. Max 10 ms."
    ::= { vtssMepConfigLbEntry 9 }

vtssMepConfigLbTimeToLive OBJECT-TYPE
    SYNTAX      VTSSUnsigned8
    MAX-ACCESS  read-write
    STATUS      current
    DESCRIPTION 
        "Time To Live."
    ::= { vtssMepConfigLbEntry 10 }

vtssMepConfigLbAction OBJECT-TYPE
    SYNTAX      VTSSRowEditorState
    MAX-ACCESS  read-write
    STATUS      current
    DESCRIPTION 
        "Action"
    ::= { vtssMepConfigLbEntry 101 }

vtssMepConfigLbRowEditor OBJECT IDENTIFIER
    ::= { vtssMepConfigLb 2 }

vtssMepConfigLbRowEditorId OBJECT-TYPE
    SYNTAX      Integer32 (0..2147483647)
    MAX-ACCESS  read-write
    STATUS      current
    DESCRIPTION 
        "The MEP instance ID"
    ::= { vtssMepConfigLbRowEditor 1 }

vtssMepConfigLbRowEditorDei OBJECT-TYPE
    SYNTAX      TruthValue
    MAX-ACCESS  read-write
    STATUS      current
    DESCRIPTION 
        "Drop Eligibility Indicator of transmitted LBM PDU"
    ::= { vtssMepConfigLbRowEditor 2 }

vtssMepConfigLbRowEditorPrio OBJECT-TYPE
    SYNTAX      Unsigned32
    MAX-ACCESS  read-write
    STATUS      current
    DESCRIPTION 
        "Priority of the transmitted LBM PDU. Range 0 to 7"
    ::= { vtssMepConfigLbRowEditor 3 }

vtssMepConfigLbRowEditorCast OBJECT-TYPE
    SYNTAX      VTSSMepCast
    MAX-ACCESS  read-write
    STATUS      current
    DESCRIPTION 
        "Uni/Multicast selection"
    ::= { vtssMepConfigLbRowEditor 4 }

vtssMepConfigLbRowEditorMep OBJECT-TYPE
    SYNTAX      Unsigned32
    MAX-ACCESS  read-write
    STATUS      current
    DESCRIPTION 
        "Peer MEP to receive LBM - only used if unicast and 'mac' is 'all zero'."
    ::= { vtssMepConfigLbRowEditor 5 }

vtssMepConfigLbRowEditorMac OBJECT-TYPE
    SYNTAX      MacAddress
    MAX-ACCESS  read-write
    STATUS      current
    DESCRIPTION 
        "Unicast MAC address to receive LBM - has to be used to send LBM to MIP."
    ::= { vtssMepConfigLbRowEditor 6 }

vtssMepConfigLbRowEditorToSend OBJECT-TYPE
    SYNTAX      Unsigned32
    MAX-ACCESS  read-write
    STATUS      current
    DESCRIPTION 
        "Number of LBM to send. Capability lb_to_send_infinite => test
         behaviour. Requires VOE."
    ::= { vtssMepConfigLbRowEditor 7 }

vtssMepConfigLbRowEditorSize OBJECT-TYPE
    SYNTAX      Unsigned32
    MAX-ACCESS  read-write
    STATUS      current
    DESCRIPTION 
        "Size of LBM frame to send - Range Capability lbm_size_min to
         lbm_size_max"
    ::= { vtssMepConfigLbRowEditor 8 }

vtssMepConfigLbRowEditorInterval OBJECT-TYPE
    SYNTAX      Unsigned32
    MAX-ACCESS  read-write
    STATUS      current
    DESCRIPTION 
        "Frame interval.
         
         If 'ToSend' != Capability lb_to_send_infinite then the 'Interval' is in
         10 ms. Max 1 s.
         
         If 'ToSend' == Capability lb_to_send_infinite then the 'Interval' is in
         1 us. Max 10 ms."
    ::= { vtssMepConfigLbRowEditor 9 }

vtssMepConfigLbRowEditorTimeToLive OBJECT-TYPE
    SYNTAX      VTSSUnsigned8
    MAX-ACCESS  read-write
    STATUS      current
    DESCRIPTION 
        "Time To Live."
    ::= { vtssMepConfigLbRowEditor 10 }

vtssMepConfigLbRowEditorAction OBJECT-TYPE
    SYNTAX      VTSSRowEditorState
    MAX-ACCESS  read-write
    STATUS      current
    DESCRIPTION 
        "Action"
    ::= { vtssMepConfigLbRowEditor 101 }

vtssMepConfigTst OBJECT IDENTIFIER
    ::= { vtssMepConfig 7 }

vtssMepConfigTstTable OBJECT-TYPE
    SYNTAX      SEQUENCE OF VTSSMepConfigTstEntry
    MAX-ACCESS  not-accessible
    STATUS      current
    DESCRIPTION 
        "This is a table of created instance Test Signal configuration
         parameters"
    ::= { vtssMepConfigTst 1 }

vtssMepConfigTstEntry OBJECT-TYPE
    SYNTAX      VTSSMepConfigTstEntry
    MAX-ACCESS  not-accessible
    STATUS      current
    DESCRIPTION 
        "This is a created instance Test Signal parameters."
    INDEX       { vtssMepConfigTstId }
    ::= { vtssMepConfigTstTable 1 }

VTSSMepConfigTstEntry ::= SEQUENCE {
    vtssMepConfigTstId      Integer32,
    vtssMepConfigTstTxEnable    TruthValue,
    vtssMepConfigTstRxEnable    TruthValue,
    vtssMepConfigTstDei     TruthValue,
    vtssMepConfigTstPrio    Unsigned32,
    vtssMepConfigTstMep     Unsigned32,
    vtssMepConfigTstRate    Unsigned32,
    vtssMepConfigTstSize    Unsigned32,
    vtssMepConfigTstPattern     VTSSMepTstPattern,
    vtssMepConfigTstSequence    TruthValue,
    vtssMepConfigTstAction      VTSSRowEditorState
}

vtssMepConfigTstId OBJECT-TYPE
    SYNTAX      Integer32 (0..2147483647)
    MAX-ACCESS  not-accessible
    STATUS      current
    DESCRIPTION 
        "The MEP instance ID"
    ::= { vtssMepConfigTstEntry 1 }

vtssMepConfigTstTxEnable OBJECT-TYPE
    SYNTAX      TruthValue
    MAX-ACCESS  read-write
    STATUS      current
    DESCRIPTION 
        "Enable/disable transmission of TST PDU."
    ::= { vtssMepConfigTstEntry 2 }

vtssMepConfigTstRxEnable OBJECT-TYPE
    SYNTAX      TruthValue
    MAX-ACCESS  read-write
    STATUS      current
    DESCRIPTION 
        "Enable/disable reception and analyse of TST PDU."
    ::= { vtssMepConfigTstEntry 3 }

vtssMepConfigTstDei OBJECT-TYPE
    SYNTAX      TruthValue
    MAX-ACCESS  read-write
    STATUS      current
    DESCRIPTION 
        "Drop Eligibility Indicator of transmitted TST PDU"
    ::= { vtssMepConfigTstEntry 4 }

vtssMepConfigTstPrio OBJECT-TYPE
    SYNTAX      Unsigned32
    MAX-ACCESS  read-write
    STATUS      current
    DESCRIPTION 
        "Priority of the transmitted TST PDU. Range 0 to 7"
    ::= { vtssMepConfigTstEntry 5 }

vtssMepConfigTstMep OBJECT-TYPE
    SYNTAX      Unsigned32
    MAX-ACCESS  read-write
    STATUS      current
    DESCRIPTION 
        "Peer MEP to receive TST"
    ::= { vtssMepConfigTstEntry 6 }

vtssMepConfigTstRate OBJECT-TYPE
    SYNTAX      Unsigned32
    MAX-ACCESS  read-write
    STATUS      current
    DESCRIPTION 
        "The transmission rate in Kbps - Range 1 to Capability tst_rate_max."
    ::= { vtssMepConfigTstEntry 7 }

vtssMepConfigTstSize OBJECT-TYPE
    SYNTAX      Unsigned32
    MAX-ACCESS  read-write
    STATUS      current
    DESCRIPTION 
        "Size of TST frame to send - Range Capability tst_size_min to
         tst_size_max."
    ::= { vtssMepConfigTstEntry 8 }

vtssMepConfigTstPattern OBJECT-TYPE
    SYNTAX      VTSSMepTstPattern
    MAX-ACCESS  read-write
    STATUS      current
    DESCRIPTION 
        "Pattern in TST frame Data TLV."
    ::= { vtssMepConfigTstEntry 9 }

vtssMepConfigTstSequence OBJECT-TYPE
    SYNTAX      TruthValue
    MAX-ACCESS  read-write
    STATUS      current
    DESCRIPTION 
        "Sequence number will be inserted - not checked in receiver on Caracal
         and Jaguar."
    ::= { vtssMepConfigTstEntry 10 }

vtssMepConfigTstAction OBJECT-TYPE
    SYNTAX      VTSSRowEditorState
    MAX-ACCESS  read-write
    STATUS      current
    DESCRIPTION 
        "Action"
    ::= { vtssMepConfigTstEntry 101 }

vtssMepConfigTstRowEditor OBJECT IDENTIFIER
    ::= { vtssMepConfigTst 2 }

vtssMepConfigTstRowEditorId OBJECT-TYPE
    SYNTAX      Integer32 (0..2147483647)
    MAX-ACCESS  read-write
    STATUS      current
    DESCRIPTION 
        "The MEP instance ID"
    ::= { vtssMepConfigTstRowEditor 1 }

vtssMepConfigTstRowEditorTxEnable OBJECT-TYPE
    SYNTAX      TruthValue
    MAX-ACCESS  read-write
    STATUS      current
    DESCRIPTION 
        "Enable/disable transmission of TST PDU."
    ::= { vtssMepConfigTstRowEditor 2 }

vtssMepConfigTstRowEditorRxEnable OBJECT-TYPE
    SYNTAX      TruthValue
    MAX-ACCESS  read-write
    STATUS      current
    DESCRIPTION 
        "Enable/disable reception and analyse of TST PDU."
    ::= { vtssMepConfigTstRowEditor 3 }

vtssMepConfigTstRowEditorDei OBJECT-TYPE
    SYNTAX      TruthValue
    MAX-ACCESS  read-write
    STATUS      current
    DESCRIPTION 
        "Drop Eligibility Indicator of transmitted TST PDU"
    ::= { vtssMepConfigTstRowEditor 4 }

vtssMepConfigTstRowEditorPrio OBJECT-TYPE
    SYNTAX      Unsigned32
    MAX-ACCESS  read-write
    STATUS      current
    DESCRIPTION 
        "Priority of the transmitted TST PDU. Range 0 to 7"
    ::= { vtssMepConfigTstRowEditor 5 }

vtssMepConfigTstRowEditorMep OBJECT-TYPE
    SYNTAX      Unsigned32
    MAX-ACCESS  read-write
    STATUS      current
    DESCRIPTION 
        "Peer MEP to receive TST"
    ::= { vtssMepConfigTstRowEditor 6 }

vtssMepConfigTstRowEditorRate OBJECT-TYPE
    SYNTAX      Unsigned32
    MAX-ACCESS  read-write
    STATUS      current
    DESCRIPTION 
        "The transmission rate in Kbps - Range 1 to Capability tst_rate_max."
    ::= { vtssMepConfigTstRowEditor 7 }

vtssMepConfigTstRowEditorSize OBJECT-TYPE
    SYNTAX      Unsigned32
    MAX-ACCESS  read-write
    STATUS      current
    DESCRIPTION 
        "Size of TST frame to send - Range Capability tst_size_min to
         tst_size_max."
    ::= { vtssMepConfigTstRowEditor 8 }

vtssMepConfigTstRowEditorPattern OBJECT-TYPE
    SYNTAX      VTSSMepTstPattern
    MAX-ACCESS  read-write
    STATUS      current
    DESCRIPTION 
        "Pattern in TST frame Data TLV."
    ::= { vtssMepConfigTstRowEditor 9 }

vtssMepConfigTstRowEditorSequence OBJECT-TYPE
    SYNTAX      TruthValue
    MAX-ACCESS  read-write
    STATUS      current
    DESCRIPTION 
        "Sequence number will be inserted - not checked in receiver on Caracal
         and Jaguar."
    ::= { vtssMepConfigTstRowEditor 10 }

vtssMepConfigTstRowEditorAction OBJECT-TYPE
    SYNTAX      VTSSRowEditorState
    MAX-ACCESS  read-write
    STATUS      current
    DESCRIPTION 
        "Action"
    ::= { vtssMepConfigTstRowEditor 101 }

vtssMepConfigLt OBJECT IDENTIFIER
    ::= { vtssMepConfig 8 }

vtssMepConfigLtTable OBJECT-TYPE
    SYNTAX      SEQUENCE OF VTSSMepConfigLtEntry
    MAX-ACCESS  not-accessible
    STATUS      current
    DESCRIPTION 
        "This is a table of created instance Link Trace configuration parameters"
    ::= { vtssMepConfigLt 1 }

vtssMepConfigLtEntry OBJECT-TYPE
    SYNTAX      VTSSMepConfigLtEntry
    MAX-ACCESS  not-accessible
    STATUS      current
    DESCRIPTION 
        "This is a created instance Link Trace parameters. This cannot be
         changed"
    INDEX       { vtssMepConfigLtId }
    ::= { vtssMepConfigLtTable 1 }

VTSSMepConfigLtEntry ::= SEQUENCE {
    vtssMepConfigLtId   Integer32,
    vtssMepConfigLtPrio     Unsigned32,
    vtssMepConfigLtMep      Unsigned32,
    vtssMepConfigLtMac      MacAddress,
    vtssMepConfigLtTimeToLive   Unsigned32,
    vtssMepConfigLtAction   VTSSRowEditorState
}

vtssMepConfigLtId OBJECT-TYPE
    SYNTAX      Integer32 (0..2147483647)
    MAX-ACCESS  not-accessible
    STATUS      current
    DESCRIPTION 
        "The MEP instance ID"
    ::= { vtssMepConfigLtEntry 1 }

vtssMepConfigLtPrio OBJECT-TYPE
    SYNTAX      Unsigned32
    MAX-ACCESS  read-write
    STATUS      current
    DESCRIPTION 
        "Priority of the transmitted LTM PDU. Range 0 to 7"
    ::= { vtssMepConfigLtEntry 3 }

vtssMepConfigLtMep OBJECT-TYPE
    SYNTAX      Unsigned32
    MAX-ACCESS  read-write
    STATUS      current
    DESCRIPTION 
        "Target Peer Mep to receive LTM - only used if 'mac' is 'all zero'"
    ::= { vtssMepConfigLtEntry 4 }

vtssMepConfigLtMac OBJECT-TYPE
    SYNTAX      MacAddress
    MAX-ACCESS  read-write
    STATUS      current
    DESCRIPTION 
        "Unicast MAC address to receive LTM - has to be used to send LTM to MIP."
    ::= { vtssMepConfigLtEntry 5 }

vtssMepConfigLtTimeToLive OBJECT-TYPE
    SYNTAX      Unsigned32
    MAX-ACCESS  read-write
    STATUS      current
    DESCRIPTION 
        "Time To Live."
    ::= { vtssMepConfigLtEntry 6 }

vtssMepConfigLtAction OBJECT-TYPE
    SYNTAX      VTSSRowEditorState
    MAX-ACCESS  read-write
    STATUS      current
    DESCRIPTION 
        "Action"
    ::= { vtssMepConfigLtEntry 101 }

vtssMepConfigLtRowEditor OBJECT IDENTIFIER
    ::= { vtssMepConfigLt 2 }

vtssMepConfigLtRowEditorId OBJECT-TYPE
    SYNTAX      Integer32 (0..2147483647)
    MAX-ACCESS  read-write
    STATUS      current
    DESCRIPTION 
        "The MEP instance ID"
    ::= { vtssMepConfigLtRowEditor 1 }

vtssMepConfigLtRowEditorPrio OBJECT-TYPE
    SYNTAX      Unsigned32
    MAX-ACCESS  read-write
    STATUS      current
    DESCRIPTION 
        "Priority of the transmitted LTM PDU. Range 0 to 7"
    ::= { vtssMepConfigLtRowEditor 3 }

vtssMepConfigLtRowEditorMep OBJECT-TYPE
    SYNTAX      Unsigned32
    MAX-ACCESS  read-write
    STATUS      current
    DESCRIPTION 
        "Target Peer Mep to receive LTM - only used if 'mac' is 'all zero'"
    ::= { vtssMepConfigLtRowEditor 4 }

vtssMepConfigLtRowEditorMac OBJECT-TYPE
    SYNTAX      MacAddress
    MAX-ACCESS  read-write
    STATUS      current
    DESCRIPTION 
        "Unicast MAC address to receive LTM - has to be used to send LTM to MIP."
    ::= { vtssMepConfigLtRowEditor 5 }

vtssMepConfigLtRowEditorTimeToLive OBJECT-TYPE
    SYNTAX      Unsigned32
    MAX-ACCESS  read-write
    STATUS      current
    DESCRIPTION 
        "Time To Live."
    ::= { vtssMepConfigLtRowEditor 6 }

vtssMepConfigLtRowEditorAction OBJECT-TYPE
    SYNTAX      VTSSRowEditorState
    MAX-ACCESS  read-write
    STATUS      current
    DESCRIPTION 
        "Action"
    ::= { vtssMepConfigLtRowEditor 101 }

vtssMepConfigAps OBJECT IDENTIFIER
    ::= { vtssMepConfig 9 }

vtssMepConfigApsTable OBJECT-TYPE
    SYNTAX      SEQUENCE OF VTSSMepConfigApsEntry
    MAX-ACCESS  not-accessible
    STATUS      current
    DESCRIPTION 
        "This is a table of created instance Automatic Protection Switching
         configuration parameters"
    ::= { vtssMepConfigAps 1 }

vtssMepConfigApsEntry OBJECT-TYPE
    SYNTAX      VTSSMepConfigApsEntry
    MAX-ACCESS  not-accessible
    STATUS      current
    DESCRIPTION 
        "This is a created instance Automatic Protection Switching parameters."
    INDEX       { vtssMepConfigApsId }
    ::= { vtssMepConfigApsTable 1 }

VTSSMepConfigApsEntry ::= SEQUENCE {
    vtssMepConfigApsId      Integer32,
    vtssMepConfigApsPrio    Unsigned32,
    vtssMepConfigApsApsType     VTSSMepApsType,
    vtssMepConfigApsCast    VTSSMepCast,
    vtssMepConfigApsRapsOctet   Unsigned32,
    vtssMepConfigApsAction      VTSSRowEditorState
}

vtssMepConfigApsId OBJECT-TYPE
    SYNTAX      Integer32 (0..2147483647)
    MAX-ACCESS  not-accessible
    STATUS      current
    DESCRIPTION 
        "The MEP instance ID"
    ::= { vtssMepConfigApsEntry 1 }

vtssMepConfigApsPrio OBJECT-TYPE
    SYNTAX      Unsigned32
    MAX-ACCESS  read-write
    STATUS      current
    DESCRIPTION 
        "Priority of the transmitted APS PDU. Range 0 to 7"
    ::= { vtssMepConfigApsEntry 3 }

vtssMepConfigApsApsType OBJECT-TYPE
    SYNTAX      VTSSMepApsType
    MAX-ACCESS  read-write
    STATUS      current
    DESCRIPTION 
        "Type of APS"
    ::= { vtssMepConfigApsEntry 4 }

vtssMepConfigApsCast OBJECT-TYPE
    SYNTAX      VTSSMepCast
    MAX-ACCESS  read-write
    STATUS      current
    DESCRIPTION 
        "Uni/multicast selection"
    ::= { vtssMepConfigApsEntry 5 }

vtssMepConfigApsRapsOctet OBJECT-TYPE
    SYNTAX      Unsigned32
    MAX-ACCESS  read-write
    STATUS      current
    DESCRIPTION 
        "Last octet in the R-APS multicast DA"
    ::= { vtssMepConfigApsEntry 6 }

vtssMepConfigApsAction OBJECT-TYPE
    SYNTAX      VTSSRowEditorState
    MAX-ACCESS  read-write
    STATUS      current
    DESCRIPTION 
        "Action"
    ::= { vtssMepConfigApsEntry 101 }

vtssMepConfigApsRowEditor OBJECT IDENTIFIER
    ::= { vtssMepConfigAps 2 }

vtssMepConfigApsRowEditorId OBJECT-TYPE
    SYNTAX      Integer32 (0..2147483647)
    MAX-ACCESS  read-write
    STATUS      current
    DESCRIPTION 
        "The MEP instance ID"
    ::= { vtssMepConfigApsRowEditor 1 }

vtssMepConfigApsRowEditorPrio OBJECT-TYPE
    SYNTAX      Unsigned32
    MAX-ACCESS  read-write
    STATUS      current
    DESCRIPTION 
        "Priority of the transmitted APS PDU. Range 0 to 7"
    ::= { vtssMepConfigApsRowEditor 3 }

vtssMepConfigApsRowEditorApsType OBJECT-TYPE
    SYNTAX      VTSSMepApsType
    MAX-ACCESS  read-write
    STATUS      current
    DESCRIPTION 
        "Type of APS"
    ::= { vtssMepConfigApsRowEditor 4 }

vtssMepConfigApsRowEditorCast OBJECT-TYPE
    SYNTAX      VTSSMepCast
    MAX-ACCESS  read-write
    STATUS      current
    DESCRIPTION 
        "Uni/multicast selection"
    ::= { vtssMepConfigApsRowEditor 5 }

vtssMepConfigApsRowEditorRapsOctet OBJECT-TYPE
    SYNTAX      Unsigned32
    MAX-ACCESS  read-write
    STATUS      current
    DESCRIPTION 
        "Last octet in the R-APS multicast DA"
    ::= { vtssMepConfigApsRowEditor 6 }

vtssMepConfigApsRowEditorAction OBJECT-TYPE
    SYNTAX      VTSSRowEditorState
    MAX-ACCESS  read-write
    STATUS      current
    DESCRIPTION 
        "Action"
    ::= { vtssMepConfigApsRowEditor 101 }

vtssMepConfigAis OBJECT IDENTIFIER
    ::= { vtssMepConfig 10 }

vtssMepConfigAisTable OBJECT-TYPE
    SYNTAX      SEQUENCE OF VTSSMepConfigAisEntry
    MAX-ACCESS  not-accessible
    STATUS      current
    DESCRIPTION 
        "This is a table of created instance Alarm Indication Signal
         configuration parameters"
    ::= { vtssMepConfigAis 1 }

vtssMepConfigAisEntry OBJECT-TYPE
    SYNTAX      VTSSMepConfigAisEntry
    MAX-ACCESS  not-accessible
    STATUS      current
    DESCRIPTION 
        "This is a created instance Alarm Indication Signal parameters."
    INDEX       { vtssMepConfigAisId }
    ::= { vtssMepConfigAisTable 1 }

VTSSMepConfigAisEntry ::= SEQUENCE {
    vtssMepConfigAisId      Integer32,
    vtssMepConfigAisProtection      TruthValue,
    vtssMepConfigAisRate    VTSSMepTxRate,
    vtssMepConfigAisAction      VTSSRowEditorState
}

vtssMepConfigAisId OBJECT-TYPE
    SYNTAX      Integer32 (0..2147483647)
    MAX-ACCESS  not-accessible
    STATUS      current
    DESCRIPTION 
        "The MEP instance ID"
    ::= { vtssMepConfigAisEntry 1 }

vtssMepConfigAisProtection OBJECT-TYPE
    SYNTAX      TruthValue
    MAX-ACCESS  read-write
    STATUS      current
    DESCRIPTION 
        "The first three AIS frames are transmitted as fast as possible."
    ::= { vtssMepConfigAisEntry 2 }

vtssMepConfigAisRate OBJECT-TYPE
    SYNTAX      VTSSMepTxRate
    MAX-ACCESS  read-write
    STATUS      current
    DESCRIPTION 
        "AIS transmission rate"
    ::= { vtssMepConfigAisEntry 3 }

vtssMepConfigAisAction OBJECT-TYPE
    SYNTAX      VTSSRowEditorState
    MAX-ACCESS  read-write
    STATUS      current
    DESCRIPTION 
        "Action"
    ::= { vtssMepConfigAisEntry 101 }

vtssMepConfigAisRowEditor OBJECT IDENTIFIER
    ::= { vtssMepConfigAis 2 }

vtssMepConfigAisRowEditorId OBJECT-TYPE
    SYNTAX      Integer32 (0..2147483647)
    MAX-ACCESS  read-write
    STATUS      current
    DESCRIPTION 
        "The MEP instance ID"
    ::= { vtssMepConfigAisRowEditor 1 }

vtssMepConfigAisRowEditorProtection OBJECT-TYPE
    SYNTAX      TruthValue
    MAX-ACCESS  read-write
    STATUS      current
    DESCRIPTION 
        "The first three AIS frames are transmitted as fast as possible."
    ::= { vtssMepConfigAisRowEditor 2 }

vtssMepConfigAisRowEditorRate OBJECT-TYPE
    SYNTAX      VTSSMepTxRate
    MAX-ACCESS  read-write
    STATUS      current
    DESCRIPTION 
        "AIS transmission rate"
    ::= { vtssMepConfigAisRowEditor 3 }

vtssMepConfigAisRowEditorAction OBJECT-TYPE
    SYNTAX      VTSSRowEditorState
    MAX-ACCESS  read-write
    STATUS      current
    DESCRIPTION 
        "Action"
    ::= { vtssMepConfigAisRowEditor 101 }

vtssMepConfigLck OBJECT IDENTIFIER
    ::= { vtssMepConfig 11 }

vtssMepConfigLckTable OBJECT-TYPE
    SYNTAX      SEQUENCE OF VTSSMepConfigLckEntry
    MAX-ACCESS  not-accessible
    STATUS      current
    DESCRIPTION 
        "This is a table of created instance Locked Signal configuration
         parameters"
    ::= { vtssMepConfigLck 1 }

vtssMepConfigLckEntry OBJECT-TYPE
    SYNTAX      VTSSMepConfigLckEntry
    MAX-ACCESS  not-accessible
    STATUS      current
    DESCRIPTION 
        "This is a created instance Locked Signal parameters."
    INDEX       { vtssMepConfigLckId }
    ::= { vtssMepConfigLckTable 1 }

VTSSMepConfigLckEntry ::= SEQUENCE {
    vtssMepConfigLckId      Integer32,
    vtssMepConfigLckRate    VTSSMepTxRate,
    vtssMepConfigLckAction      VTSSRowEditorState
}

vtssMepConfigLckId OBJECT-TYPE
    SYNTAX      Integer32 (0..2147483647)
    MAX-ACCESS  not-accessible
    STATUS      current
    DESCRIPTION 
        "The MEP instance ID"
    ::= { vtssMepConfigLckEntry 1 }

vtssMepConfigLckRate OBJECT-TYPE
    SYNTAX      VTSSMepTxRate
    MAX-ACCESS  read-write
    STATUS      current
    DESCRIPTION 
        "LCK transmission rate"
    ::= { vtssMepConfigLckEntry 2 }

vtssMepConfigLckAction OBJECT-TYPE
    SYNTAX      VTSSRowEditorState
    MAX-ACCESS  read-write
    STATUS      current
    DESCRIPTION 
        "Action"
    ::= { vtssMepConfigLckEntry 101 }

vtssMepConfigLckRowEditor OBJECT IDENTIFIER
    ::= { vtssMepConfigLck 2 }

vtssMepConfigLckRowEditorId OBJECT-TYPE
    SYNTAX      Integer32 (0..2147483647)
    MAX-ACCESS  read-write
    STATUS      current
    DESCRIPTION 
        "The MEP instance ID"
    ::= { vtssMepConfigLckRowEditor 1 }

vtssMepConfigLckRowEditorRate OBJECT-TYPE
    SYNTAX      VTSSMepTxRate
    MAX-ACCESS  read-write
    STATUS      current
    DESCRIPTION 
        "LCK transmission rate"
    ::= { vtssMepConfigLckRowEditor 2 }

vtssMepConfigLckRowEditorAction OBJECT-TYPE
    SYNTAX      VTSSRowEditorState
    MAX-ACCESS  read-write
    STATUS      current
    DESCRIPTION 
        "Action"
    ::= { vtssMepConfigLckRowEditor 101 }

vtssMepConfigClient OBJECT IDENTIFIER
    ::= { vtssMepConfig 12 }

vtssMepConfigClientFlowTable OBJECT-TYPE
    SYNTAX      SEQUENCE OF VTSSMepConfigClientFlowEntry
    MAX-ACCESS  not-accessible
    STATUS      current
    DESCRIPTION 
        "This is a table of client flow configuration parameters"
    ::= { vtssMepConfigClient 2 }

vtssMepConfigClientFlowEntry OBJECT-TYPE
    SYNTAX      VTSSMepConfigClientFlowEntry
    MAX-ACCESS  not-accessible
    STATUS      current
    DESCRIPTION 
        "This is a client flow configuration parameters"
    INDEX       { vtssMepConfigClientFlowId, vtssMepConfigClientFlowFlowId }
    ::= { vtssMepConfigClientFlowTable 1 }

VTSSMepConfigClientFlowEntry ::= SEQUENCE {
    vtssMepConfigClientFlowId   Integer32,
    vtssMepConfigClientFlowFlowId   VTSSInterfaceIndex,
    vtssMepConfigClientFlowAisPrio      VTSSUnsigned8,
    vtssMepConfigClientFlowLckPrio      VTSSUnsigned8,
    vtssMepConfigClientFlowLevel    VTSSUnsigned8,
    vtssMepConfigClientFlowAction   VTSSRowEditorState
}

vtssMepConfigClientFlowId OBJECT-TYPE
    SYNTAX      Integer32 (0..2147483647)
    MAX-ACCESS  not-accessible
    STATUS      current
    DESCRIPTION 
        "The MEP instance ID"
    ::= { vtssMepConfigClientFlowEntry 1 }

vtssMepConfigClientFlowFlowId OBJECT-TYPE
    SYNTAX      VTSSInterfaceIndex
    MAX-ACCESS  not-accessible
    STATUS      current
    DESCRIPTION 
        "The Client Flow id - ifindex"
    ::= { vtssMepConfigClientFlowEntry 2 }

vtssMepConfigClientFlowAisPrio OBJECT-TYPE
    SYNTAX      VTSSUnsigned8
    MAX-ACCESS  read-write
    STATUS      current
    DESCRIPTION 
        "AIS Priority (EVC COS-ID) 0-7. Capability client_prio_highest indicate
         highest possible is requested"
    ::= { vtssMepConfigClientFlowEntry 3 }

vtssMepConfigClientFlowLckPrio OBJECT-TYPE
    SYNTAX      VTSSUnsigned8
    MAX-ACCESS  read-write
    STATUS      current
    DESCRIPTION 
        "LCK Priority (EVC COS-ID) 0-7. Capability client_prio_highest indicate
         highest possible is requested"
    ::= { vtssMepConfigClientFlowEntry 4 }

vtssMepConfigClientFlowLevel OBJECT-TYPE
    SYNTAX      VTSSUnsigned8
    MAX-ACCESS  read-write
    STATUS      current
    DESCRIPTION 
        "Client flow level"
    ::= { vtssMepConfigClientFlowEntry 5 }

vtssMepConfigClientFlowAction OBJECT-TYPE
    SYNTAX      VTSSRowEditorState
    MAX-ACCESS  read-write
    STATUS      current
    DESCRIPTION 
        "Action"
    ::= { vtssMepConfigClientFlowEntry 100 }

vtssMepConfigClientFlowRowEditor OBJECT IDENTIFIER
    ::= { vtssMepConfigClient 3 }

vtssMepConfigClientFlowRowEditorId OBJECT-TYPE
    SYNTAX      Integer32 (0..2147483647)
    MAX-ACCESS  read-write
    STATUS      current
    DESCRIPTION 
        "The MEP instance ID"
    ::= { vtssMepConfigClientFlowRowEditor 1 }

vtssMepConfigClientFlowRowEditorFlowId OBJECT-TYPE
    SYNTAX      VTSSInterfaceIndex
    MAX-ACCESS  read-write
    STATUS      current
    DESCRIPTION 
        "The Client Flow id - ifindex"
    ::= { vtssMepConfigClientFlowRowEditor 2 }

vtssMepConfigClientFlowRowEditorAisPrio OBJECT-TYPE
    SYNTAX      VTSSUnsigned8
    MAX-ACCESS  read-write
    STATUS      current
    DESCRIPTION 
        "AIS Priority (EVC COS-ID) 0-7. Capability client_prio_highest indicate
         highest possible is requested"
    ::= { vtssMepConfigClientFlowRowEditor 3 }

vtssMepConfigClientFlowRowEditorLckPrio OBJECT-TYPE
    SYNTAX      VTSSUnsigned8
    MAX-ACCESS  read-write
    STATUS      current
    DESCRIPTION 
        "LCK Priority (EVC COS-ID) 0-7. Capability client_prio_highest indicate
         highest possible is requested"
    ::= { vtssMepConfigClientFlowRowEditor 4 }

vtssMepConfigClientFlowRowEditorLevel OBJECT-TYPE
    SYNTAX      VTSSUnsigned8
    MAX-ACCESS  read-write
    STATUS      current
    DESCRIPTION 
        "Client flow level"
    ::= { vtssMepConfigClientFlowRowEditor 5 }

vtssMepConfigClientFlowRowEditorAction OBJECT-TYPE
    SYNTAX      VTSSRowEditorState
    MAX-ACCESS  read-write
    STATUS      current
    DESCRIPTION 
        "Action"
    ::= { vtssMepConfigClientFlowRowEditor 100 }

vtssMepConfigSyslog OBJECT IDENTIFIER
    ::= { vtssMepConfig 13 }

vtssMepConfigSyslogTable OBJECT-TYPE
    SYNTAX      SEQUENCE OF VTSSMepConfigSyslogEntry
    MAX-ACCESS  not-accessible
    STATUS      current
    DESCRIPTION 
        "This is a table of created instance Syslog configuration parameters"
    ::= { vtssMepConfigSyslog 1 }

vtssMepConfigSyslogEntry OBJECT-TYPE
    SYNTAX      VTSSMepConfigSyslogEntry
    MAX-ACCESS  not-accessible
    STATUS      current
    DESCRIPTION 
        "This is a created instance Syslog configuration parameters"
    INDEX       { vtssMepConfigSyslogId }
    ::= { vtssMepConfigSyslogTable 1 }

VTSSMepConfigSyslogEntry ::= SEQUENCE {
    vtssMepConfigSyslogId   Integer32,
    vtssMepConfigSyslogEnable   TruthValue
}

vtssMepConfigSyslogId OBJECT-TYPE
    SYNTAX      Integer32 (0..2147483647)
    MAX-ACCESS  not-accessible
    STATUS      current
    DESCRIPTION 
        "The MEP instance ID"
    ::= { vtssMepConfigSyslogEntry 1 }

vtssMepConfigSyslogEnable OBJECT-TYPE
    SYNTAX      TruthValue
    MAX-ACCESS  read-write
    STATUS      current
    DESCRIPTION 
        "The instance can enable generation of syslog entries "
    ::= { vtssMepConfigSyslogEntry 2 }

vtssMepConfigTlv OBJECT IDENTIFIER
    ::= { vtssMepConfig 14 }

vtssMepConfigTlvLeaf OBJECT IDENTIFIER
    ::= { vtssMepConfigTlv 1 }

vtssMepConfigTlvLeafOsTlvOuiFirst OBJECT-TYPE
    SYNTAX      VTSSUnsigned8
    MAX-ACCESS  read-write
    STATUS      current
    DESCRIPTION 
        "Transmitted OS TLV - The OUI content first nibble"
    ::= { vtssMepConfigTlvLeaf 2 }

vtssMepConfigTlvLeafOsTlvOuiSecond OBJECT-TYPE
    SYNTAX      VTSSUnsigned8
    MAX-ACCESS  read-write
    STATUS      current
    DESCRIPTION 
        "Transmitted OS TLV - The OUI content second nibble"
    ::= { vtssMepConfigTlvLeaf 3 }

vtssMepConfigTlvLeafOsTlvOuiThird OBJECT-TYPE
    SYNTAX      VTSSUnsigned8
    MAX-ACCESS  read-write
    STATUS      current
    DESCRIPTION 
        "Transmitted OS TLV - The OUI content third nibble"
    ::= { vtssMepConfigTlvLeaf 4 }

vtssMepConfigTlvLeafOsTlvSubType OBJECT-TYPE
    SYNTAX      VTSSUnsigned8
    MAX-ACCESS  read-write
    STATUS      current
    DESCRIPTION 
        "Transmitted OS TLV - The Sub-Type content"
    ::= { vtssMepConfigTlvLeaf 5 }

vtssMepConfigTlvLeafOsTlvValue OBJECT-TYPE
    SYNTAX      VTSSUnsigned8
    MAX-ACCESS  read-write
    STATUS      current
    DESCRIPTION 
        "Transmitted OS TLV - The Value content"
    ::= { vtssMepConfigTlvLeaf 6 }

vtssMepConfigBfd OBJECT IDENTIFIER
    ::= { vtssMepConfig 15 }

vtssMepConfigBfdTable OBJECT-TYPE
    SYNTAX      SEQUENCE OF VTSSMepConfigBfdEntry
    MAX-ACCESS  not-accessible
    STATUS      current
    DESCRIPTION 
        "This is a table of created instance Bidirectional Forwarding Detection
         configuration parameters"
    ::= { vtssMepConfigBfd 1 }

vtssMepConfigBfdEntry OBJECT-TYPE
    SYNTAX      VTSSMepConfigBfdEntry
    MAX-ACCESS  not-accessible
    STATUS      current
    DESCRIPTION 
        "This is a created instance Bidirectional Forwarding Detection
         configuration parameters."
    INDEX       { vtssMepConfigBfdId }
    ::= { vtssMepConfigBfdTable 1 }

VTSSMepConfigBfdEntry ::= SEQUENCE {
    vtssMepConfigBfdId      Integer32,
    vtssMepConfigBfdEnable      TruthValue,
    vtssMepConfigBfdIsIndependent   TruthValue,
    vtssMepConfigBfdCcOnly      TruthValue,
    vtssMepConfigBfdTxAuthEnabled   TruthValue,
    vtssMepConfigBfdRxAuthEnabled   TruthValue,
    vtssMepConfigBfdTxAuthKeyId     VTSSUnsigned8,
    vtssMepConfigBfdCcPeriod    Unsigned32,
    vtssMepConfigBfdRxFlow      Unsigned32,
    vtssMepConfigBfdAction      VTSSRowEditorState
}

vtssMepConfigBfdId OBJECT-TYPE
    SYNTAX      Integer32 (0..2147483647)
    MAX-ACCESS  not-accessible
    STATUS      current
    DESCRIPTION 
        "The MEP instance ID"
    ::= { vtssMepConfigBfdEntry 1 }

vtssMepConfigBfdEnable OBJECT-TYPE
    SYNTAX      TruthValue
    MAX-ACCESS  read-write
    STATUS      current
    DESCRIPTION 
        "CC/CV transmission and LOC detection is enabled if true."
    ::= { vtssMepConfigBfdEntry 2 }

vtssMepConfigBfdIsIndependent OBJECT-TYPE
    SYNTAX      TruthValue
    MAX-ACCESS  read-write
    STATUS      current
    DESCRIPTION 
        "Independent mode if true, coordinated if false."
    ::= { vtssMepConfigBfdEntry 3 }

vtssMepConfigBfdCcOnly OBJECT-TYPE
    SYNTAX      TruthValue
    MAX-ACCESS  read-write
    STATUS      current
    DESCRIPTION 
        "Only transmit CC frames (no CV frames) if true."
    ::= { vtssMepConfigBfdEntry 4 }

vtssMepConfigBfdTxAuthEnabled OBJECT-TYPE
    SYNTAX      TruthValue
    MAX-ACCESS  read-write
    STATUS      current
    DESCRIPTION 
        "Authentication enabled for transmission of CC/CV frames to peer if
         true."
    ::= { vtssMepConfigBfdEntry 5 }

vtssMepConfigBfdRxAuthEnabled OBJECT-TYPE
    SYNTAX      TruthValue
    MAX-ACCESS  read-write
    STATUS      current
    DESCRIPTION 
        "Authentication enabled for reception of CC/CV frames from peer if true."
    ::= { vtssMepConfigBfdEntry 6 }

vtssMepConfigBfdTxAuthKeyId OBJECT-TYPE
    SYNTAX      VTSSUnsigned8
    MAX-ACCESS  read-write
    STATUS      current
    DESCRIPTION 
        "Authentication used for transmission of CC/CV frames to peer."
    ::= { vtssMepConfigBfdEntry 7 }

vtssMepConfigBfdCcPeriod OBJECT-TYPE
    SYNTAX      Unsigned32
    MAX-ACCESS  read-write
    STATUS      current
    DESCRIPTION 
        "Desired CC transmission period in us, 1 us - 60 sec."
    ::= { vtssMepConfigBfdEntry 8 }

vtssMepConfigBfdRxFlow OBJECT-TYPE
    SYNTAX      Unsigned32
    MAX-ACCESS  read-write
    STATUS      current
    DESCRIPTION 
        "Rx flow number (MPLS-TP link, MPLS-TP tunnel, MPLS-TP LSP or MPLS-TP
         Pseudo-Wire) for independent mode."
    ::= { vtssMepConfigBfdEntry 9 }

vtssMepConfigBfdAction OBJECT-TYPE
    SYNTAX      VTSSRowEditorState
    MAX-ACCESS  read-write
    STATUS      current
    DESCRIPTION 
        "Action"
    ::= { vtssMepConfigBfdEntry 100 }

vtssMepConfigBfdRowEditor OBJECT IDENTIFIER
    ::= { vtssMepConfigBfd 2 }

vtssMepConfigBfdRowEditorId OBJECT-TYPE
    SYNTAX      Integer32 (0..2147483647)
    MAX-ACCESS  read-write
    STATUS      current
    DESCRIPTION 
        "The MEP instance ID"
    ::= { vtssMepConfigBfdRowEditor 1 }

vtssMepConfigBfdRowEditorEnable OBJECT-TYPE
    SYNTAX      TruthValue
    MAX-ACCESS  read-write
    STATUS      current
    DESCRIPTION 
        "CC/CV transmission and LOC detection is enabled if true."
    ::= { vtssMepConfigBfdRowEditor 2 }

vtssMepConfigBfdRowEditorIsIndependent OBJECT-TYPE
    SYNTAX      TruthValue
    MAX-ACCESS  read-write
    STATUS      current
    DESCRIPTION 
        "Independent mode if true, coordinated if false."
    ::= { vtssMepConfigBfdRowEditor 3 }

vtssMepConfigBfdRowEditorCcOnly OBJECT-TYPE
    SYNTAX      TruthValue
    MAX-ACCESS  read-write
    STATUS      current
    DESCRIPTION 
        "Only transmit CC frames (no CV frames) if true."
    ::= { vtssMepConfigBfdRowEditor 4 }

vtssMepConfigBfdRowEditorTxAuthEnabled OBJECT-TYPE
    SYNTAX      TruthValue
    MAX-ACCESS  read-write
    STATUS      current
    DESCRIPTION 
        "Authentication enabled for transmission of CC/CV frames to peer if
         true."
    ::= { vtssMepConfigBfdRowEditor 5 }

vtssMepConfigBfdRowEditorRxAuthEnabled OBJECT-TYPE
    SYNTAX      TruthValue
    MAX-ACCESS  read-write
    STATUS      current
    DESCRIPTION 
        "Authentication enabled for reception of CC/CV frames from peer if true."
    ::= { vtssMepConfigBfdRowEditor 6 }

vtssMepConfigBfdRowEditorTxAuthKeyId OBJECT-TYPE
    SYNTAX      VTSSUnsigned8
    MAX-ACCESS  read-write
    STATUS      current
    DESCRIPTION 
        "Authentication used for transmission of CC/CV frames to peer."
    ::= { vtssMepConfigBfdRowEditor 7 }

vtssMepConfigBfdRowEditorCcPeriod OBJECT-TYPE
    SYNTAX      Unsigned32
    MAX-ACCESS  read-write
    STATUS      current
    DESCRIPTION 
        "Desired CC transmission period in us, 1 us - 60 sec."
    ::= { vtssMepConfigBfdRowEditor 8 }

vtssMepConfigBfdRowEditorRxFlow OBJECT-TYPE
    SYNTAX      Unsigned32
    MAX-ACCESS  read-write
    STATUS      current
    DESCRIPTION 
        "Rx flow number (MPLS-TP link, MPLS-TP tunnel, MPLS-TP LSP or MPLS-TP
         Pseudo-Wire) for independent mode."
    ::= { vtssMepConfigBfdRowEditor 9 }

vtssMepConfigBfdRowEditorAction OBJECT-TYPE
    SYNTAX      VTSSRowEditorState
    MAX-ACCESS  read-write
    STATUS      current
    DESCRIPTION 
        "Action"
    ::= { vtssMepConfigBfdRowEditor 100 }

vtssMepConfigBfdAuth OBJECT IDENTIFIER
    ::= { vtssMepConfig 16 }

vtssMepConfigBfdAuthTable OBJECT-TYPE
    SYNTAX      SEQUENCE OF VTSSMepConfigBfdAuthEntry
    MAX-ACCESS  not-accessible
    STATUS      current
    DESCRIPTION 
        "This is a table of created instance Bidirectional Forwarding Detection
         Authentication configuration parameters"
    ::= { vtssMepConfigBfdAuth 1 }

vtssMepConfigBfdAuthEntry OBJECT-TYPE
    SYNTAX      VTSSMepConfigBfdAuthEntry
    MAX-ACCESS  not-accessible
    STATUS      current
    DESCRIPTION 
        "This is a created instance Bidirectional Forwarding Detection
         Authentication configuration parameters."
    INDEX       { vtssMepConfigBfdAuthId }
    ::= { vtssMepConfigBfdAuthTable 1 }

VTSSMepConfigBfdAuthEntry ::= SEQUENCE {
    vtssMepConfigBfdAuthId      Integer32,
    vtssMepConfigBfdAuthKeyType     VTSSMepBfdAuthenticationType,
    vtssMepConfigBfdAuthKeyLen      VTSSUnsigned8,
    vtssMepConfigBfdAuthKey     OCTET STRING,
    vtssMepConfigBfdAuthAction      VTSSRowEditorState
}

vtssMepConfigBfdAuthId OBJECT-TYPE
    SYNTAX      Integer32 (0..2147483647)
    MAX-ACCESS  not-accessible
    STATUS      current
    DESCRIPTION 
        "The MEP instance ID"
    ::= { vtssMepConfigBfdAuthEntry 1 }

vtssMepConfigBfdAuthKeyType OBJECT-TYPE
    SYNTAX      VTSSMepBfdAuthenticationType
    MAX-ACCESS  read-write
    STATUS      current
    DESCRIPTION 
        "Key type."
    ::= { vtssMepConfigBfdAuthEntry 2 }

vtssMepConfigBfdAuthKeyLen OBJECT-TYPE
    SYNTAX      VTSSUnsigned8
    MAX-ACCESS  read-write
    STATUS      current
    DESCRIPTION 
        "Key length in bytes. 1-16 for Simple Password, 16 for MD5 and 20 for
         SHA1."
    ::= { vtssMepConfigBfdAuthEntry 3 }

vtssMepConfigBfdAuthKey OBJECT-TYPE
    SYNTAX      OCTET STRING (SIZE(20))
    MAX-ACCESS  read-write
    STATUS      current
    DESCRIPTION 
        "Key value."
    ::= { vtssMepConfigBfdAuthEntry 4 }

vtssMepConfigBfdAuthAction OBJECT-TYPE
    SYNTAX      VTSSRowEditorState
    MAX-ACCESS  read-write
    STATUS      current
    DESCRIPTION 
        "Action"
    ::= { vtssMepConfigBfdAuthEntry 100 }

vtssMepConfigBfdAuthRowEditor OBJECT IDENTIFIER
    ::= { vtssMepConfigBfdAuth 2 }

vtssMepConfigBfdAuthRowEditorId OBJECT-TYPE
    SYNTAX      Integer32 (0..2147483647)
    MAX-ACCESS  read-write
    STATUS      current
    DESCRIPTION 
        "The MEP instance ID"
    ::= { vtssMepConfigBfdAuthRowEditor 1 }

vtssMepConfigBfdAuthRowEditorKeyType OBJECT-TYPE
    SYNTAX      VTSSMepBfdAuthenticationType
    MAX-ACCESS  read-write
    STATUS      current
    DESCRIPTION 
        "Key type."
    ::= { vtssMepConfigBfdAuthRowEditor 2 }

vtssMepConfigBfdAuthRowEditorKeyLen OBJECT-TYPE
    SYNTAX      VTSSUnsigned8
    MAX-ACCESS  read-write
    STATUS      current
    DESCRIPTION 
        "Key length in bytes. 1-16 for Simple Password, 16 for MD5 and 20 for
         SHA1."
    ::= { vtssMepConfigBfdAuthRowEditor 3 }

vtssMepConfigBfdAuthRowEditorKey OBJECT-TYPE
    SYNTAX      OCTET STRING (SIZE(20))
    MAX-ACCESS  read-write
    STATUS      current
    DESCRIPTION 
        "Key value."
    ::= { vtssMepConfigBfdAuthRowEditor 4 }

vtssMepConfigBfdAuthRowEditorAction OBJECT-TYPE
    SYNTAX      VTSSRowEditorState
    MAX-ACCESS  read-write
    STATUS      current
    DESCRIPTION 
        "Action"
    ::= { vtssMepConfigBfdAuthRowEditor 100 }

vtssMepConfigRt OBJECT IDENTIFIER
    ::= { vtssMepConfig 17 }

vtssMepConfigRtTable OBJECT-TYPE
    SYNTAX      SEQUENCE OF VTSSMepConfigRtEntry
    MAX-ACCESS  not-accessible
    STATUS      current
    DESCRIPTION 
        "This is a table of created instance Route Trace configuration
         parameters"
    ::= { vtssMepConfigRt 1 }

vtssMepConfigRtEntry OBJECT-TYPE
    SYNTAX      VTSSMepConfigRtEntry
    MAX-ACCESS  not-accessible
    STATUS      current
    DESCRIPTION 
        "This is a created instance Route Trace configuration parameters."
    INDEX       { vtssMepConfigRtId }
    ::= { vtssMepConfigRtTable 1 }

VTSSMepConfigRtEntry ::= SEQUENCE {
    vtssMepConfigRtId   Integer32,
    vtssMepConfigRtTrafficClass     VTSSUnsigned8,
    vtssMepConfigRtSrcIdTlv     TruthValue,
    vtssMepConfigRtDstIdTlv     TruthValue,
    vtssMepConfigRtPadTlvType   VTSSMepRtPadTlvType,
    vtssMepConfigRtPadTlvLen    VTSSUnsigned16,
    vtssMepConfigRtFlags    VTSSUnsigned8,
    vtssMepConfigRtMaxTimeToLive    VTSSUnsigned8,
    vtssMepConfigRtAction   VTSSRowEditorState
}

vtssMepConfigRtId OBJECT-TYPE
    SYNTAX      Integer32 (0..2147483647)
    MAX-ACCESS  not-accessible
    STATUS      current
    DESCRIPTION 
        "The MEP instance ID"
    ::= { vtssMepConfigRtEntry 1 }

vtssMepConfigRtTrafficClass OBJECT-TYPE
    SYNTAX      VTSSUnsigned8
    MAX-ACCESS  read-write
    STATUS      current
    DESCRIPTION 
        "Traffic class value used in the transmitted RT request PDU. Range 0 to
         7"
    ::= { vtssMepConfigRtEntry 2 }

vtssMepConfigRtSrcIdTlv OBJECT-TYPE
    SYNTAX      TruthValue
    MAX-ACCESS  read-write
    STATUS      current
    DESCRIPTION 
        "Include Source ID TLV in the RT request"
    ::= { vtssMepConfigRtEntry 3 }

vtssMepConfigRtDstIdTlv OBJECT-TYPE
    SYNTAX      TruthValue
    MAX-ACCESS  read-write
    STATUS      current
    DESCRIPTION 
        "Include Destination ID TLV in the RT request"
    ::= { vtssMepConfigRtEntry 4 }

vtssMepConfigRtPadTlvType OBJECT-TYPE
    SYNTAX      VTSSMepRtPadTlvType
    MAX-ACCESS  read-write
    STATUS      current
    DESCRIPTION 
        "Pad TLV type"
    ::= { vtssMepConfigRtEntry 5 }

vtssMepConfigRtPadTlvLen OBJECT-TYPE
    SYNTAX      VTSSUnsigned16
    MAX-ACCESS  read-write
    STATUS      current
    DESCRIPTION 
        "Pad TLV data length. Range 1 to 1024."
    ::= { vtssMepConfigRtEntry 6 }

vtssMepConfigRtFlags OBJECT-TYPE
    SYNTAX      VTSSUnsigned8
    MAX-ACCESS  read-write
    STATUS      current
    DESCRIPTION 
        "Flags for RT request. Bit 0: V flag (Validate FEC stack), bit 1: T flag
         (Respond Only If TTL Expired), bit 2: R flag (Validate Reverse Path)"
    ::= { vtssMepConfigRtEntry 7 }

vtssMepConfigRtMaxTimeToLive OBJECT-TYPE
    SYNTAX      VTSSUnsigned8
    MAX-ACCESS  read-write
    STATUS      current
    DESCRIPTION 
        "Max. Time To Live for RT request."
    ::= { vtssMepConfigRtEntry 8 }

vtssMepConfigRtAction OBJECT-TYPE
    SYNTAX      VTSSRowEditorState
    MAX-ACCESS  read-write
    STATUS      current
    DESCRIPTION 
        "Action"
    ::= { vtssMepConfigRtEntry 100 }

vtssMepConfigRtRowEditor OBJECT IDENTIFIER
    ::= { vtssMepConfigRt 2 }

vtssMepConfigRtRowEditorId OBJECT-TYPE
    SYNTAX      Integer32 (0..2147483647)
    MAX-ACCESS  read-write
    STATUS      current
    DESCRIPTION 
        "The MEP instance ID"
    ::= { vtssMepConfigRtRowEditor 1 }

vtssMepConfigRtRowEditorTrafficClass OBJECT-TYPE
    SYNTAX      VTSSUnsigned8
    MAX-ACCESS  read-write
    STATUS      current
    DESCRIPTION 
        "Traffic class value used in the transmitted RT request PDU. Range 0 to
         7"
    ::= { vtssMepConfigRtRowEditor 2 }

vtssMepConfigRtRowEditorSrcIdTlv OBJECT-TYPE
    SYNTAX      TruthValue
    MAX-ACCESS  read-write
    STATUS      current
    DESCRIPTION 
        "Include Source ID TLV in the RT request"
    ::= { vtssMepConfigRtRowEditor 3 }

vtssMepConfigRtRowEditorDstIdTlv OBJECT-TYPE
    SYNTAX      TruthValue
    MAX-ACCESS  read-write
    STATUS      current
    DESCRIPTION 
        "Include Destination ID TLV in the RT request"
    ::= { vtssMepConfigRtRowEditor 4 }

vtssMepConfigRtRowEditorPadTlvType OBJECT-TYPE
    SYNTAX      VTSSMepRtPadTlvType
    MAX-ACCESS  read-write
    STATUS      current
    DESCRIPTION 
        "Pad TLV type"
    ::= { vtssMepConfigRtRowEditor 5 }

vtssMepConfigRtRowEditorPadTlvLen OBJECT-TYPE
    SYNTAX      VTSSUnsigned16
    MAX-ACCESS  read-write
    STATUS      current
    DESCRIPTION 
        "Pad TLV data length. Range 1 to 1024."
    ::= { vtssMepConfigRtRowEditor 6 }

vtssMepConfigRtRowEditorFlags OBJECT-TYPE
    SYNTAX      VTSSUnsigned8
    MAX-ACCESS  read-write
    STATUS      current
    DESCRIPTION 
        "Flags for RT request. Bit 0: V flag (Validate FEC stack), bit 1: T flag
         (Respond Only If TTL Expired), bit 2: R flag (Validate Reverse Path)"
    ::= { vtssMepConfigRtRowEditor 7 }

vtssMepConfigRtRowEditorMaxTimeToLive OBJECT-TYPE
    SYNTAX      VTSSUnsigned8
    MAX-ACCESS  read-write
    STATUS      current
    DESCRIPTION 
        "Max. Time To Live for RT request."
    ::= { vtssMepConfigRtRowEditor 8 }

vtssMepConfigRtRowEditorAction OBJECT-TYPE
    SYNTAX      VTSSRowEditorState
    MAX-ACCESS  read-write
    STATUS      current
    DESCRIPTION 
        "Action"
    ::= { vtssMepConfigRtRowEditor 100 }

vtssMepConfigLst OBJECT IDENTIFIER
    ::= { vtssMepConfig 18 }

vtssMepConfigLstTable OBJECT-TYPE
    SYNTAX      SEQUENCE OF VTSSMepConfigLstEntry
    MAX-ACCESS  not-accessible
    STATUS      current
    DESCRIPTION 
        "This is a table of created instance Link State Tracking configuration
         parameters"
    ::= { vtssMepConfigLst 1 }

vtssMepConfigLstEntry OBJECT-TYPE
    SYNTAX      VTSSMepConfigLstEntry
    MAX-ACCESS  not-accessible
    STATUS      current
    DESCRIPTION 
        "This is a created instance Link State Tracking configuration parameters"
    INDEX       { vtssMepConfigLstId }
    ::= { vtssMepConfigLstTable 1 }

VTSSMepConfigLstEntry ::= SEQUENCE {
    vtssMepConfigLstId      Integer32,
    vtssMepConfigLstEnable      TruthValue
}

vtssMepConfigLstId OBJECT-TYPE
    SYNTAX      Integer32 (0..2147483647)
    MAX-ACCESS  not-accessible
    STATUS      current
    DESCRIPTION 
        "The MEP instance ID"
    ::= { vtssMepConfigLstEntry 1 }

vtssMepConfigLstEnable OBJECT-TYPE
    SYNTAX      TruthValue
    MAX-ACCESS  read-write
    STATUS      current
    DESCRIPTION 
        "The instance can enable Link State Tracking. When LST is enabled, Local
         SF or received 'isDown' in CCM Interface Status TLV, will bring down
         the residence port. Only valid in Up-MEP."
    ::= { vtssMepConfigLstEntry 2 }

vtssMepConfigLmAvail OBJECT IDENTIFIER
    ::= { vtssMepConfig 19 }

vtssMepConfigLmAvailTable OBJECT-TYPE
    SYNTAX      SEQUENCE OF VTSSMepConfigLmAvailEntry
    MAX-ACCESS  not-accessible
    STATUS      current
    DESCRIPTION 
        "This is a table of created instance Loss Measurement Availability
         configuration parameters"
    ::= { vtssMepConfigLmAvail 1 }

vtssMepConfigLmAvailEntry OBJECT-TYPE
    SYNTAX      VTSSMepConfigLmAvailEntry
    MAX-ACCESS  not-accessible
    STATUS      current
    DESCRIPTION 
        "This is a created instance Loss Measurement Availability parameters."
    INDEX       { vtssMepConfigLmAvailId }
    ::= { vtssMepConfigLmAvailTable 1 }

VTSSMepConfigLmAvailEntry ::= SEQUENCE {
    vtssMepConfigLmAvailId      Integer32,
    vtssMepConfigLmAvailEnable      TruthValue,
    vtssMepConfigLmAvailLosRatioThr     Unsigned32,
    vtssMepConfigLmAvailInterval    Unsigned32,
    vtssMepConfigLmAvailMaintenance     TruthValue
}

vtssMepConfigLmAvailId OBJECT-TYPE
    SYNTAX      Integer32 (0..2147483647)
    MAX-ACCESS  not-accessible
    STATUS      current
    DESCRIPTION 
        "The MEP instance ID"
    ::= { vtssMepConfigLmAvailEntry 1 }

vtssMepConfigLmAvailEnable OBJECT-TYPE
    SYNTAX      TruthValue
    MAX-ACCESS  read-write
    STATUS      current
    DESCRIPTION 
        "Loss Measurement Availability is enabled"
    ::= { vtssMepConfigLmAvailEntry 2 }

vtssMepConfigLmAvailLosRatioThr OBJECT-TYPE
    SYNTAX      Unsigned32
    MAX-ACCESS  read-write
    STATUS      current
    DESCRIPTION 
        "Availability frame loss ratio threshold in per mille."
    ::= { vtssMepConfigLmAvailEntry 3 }

vtssMepConfigLmAvailInterval OBJECT-TYPE
    SYNTAX      Unsigned32
    MAX-ACCESS  read-write
    STATUS      current
    DESCRIPTION 
        "Availability interval - number of measurements with same availability
         in order to change Availability state."
    ::= { vtssMepConfigLmAvailEntry 4 }

vtssMepConfigLmAvailMaintenance OBJECT-TYPE
    SYNTAX      TruthValue
    MAX-ACCESS  read-write
    STATUS      current
    DESCRIPTION 
        "Loss Measurement Availability Maintenance enable/disable"
    ::= { vtssMepConfigLmAvailEntry 5 }

vtssMepConfigLmHli OBJECT IDENTIFIER
    ::= { vtssMepConfig 20 }

vtssMepConfigLmHliTable OBJECT-TYPE
    SYNTAX      SEQUENCE OF VTSSMepConfigLmHliEntry
    MAX-ACCESS  not-accessible
    STATUS      current
    DESCRIPTION 
        "This is a table of created instance Loss Measurement High Loss Interval
         configuration parameters"
    ::= { vtssMepConfigLmHli 1 }

vtssMepConfigLmHliEntry OBJECT-TYPE
    SYNTAX      VTSSMepConfigLmHliEntry
    MAX-ACCESS  not-accessible
    STATUS      current
    DESCRIPTION 
        "This is a created instance Loss Measurement High Loss Interval
         parameters."
    INDEX       { vtssMepConfigLmHliId }
    ::= { vtssMepConfigLmHliTable 1 }

VTSSMepConfigLmHliEntry ::= SEQUENCE {
    vtssMepConfigLmHliId    Integer32,
    vtssMepConfigLmHliEnable    TruthValue,
    vtssMepConfigLmHliHiLosRatioThr     Unsigned32,
    vtssMepConfigLmHliConInterval   Unsigned32,
    vtssMepConfigLmHliCntHolddownTimer      Unsigned32
}

vtssMepConfigLmHliId OBJECT-TYPE
    SYNTAX      Integer32 (0..2147483647)
    MAX-ACCESS  not-accessible
    STATUS      current
    DESCRIPTION 
        "The MEP instance ID"
    ::= { vtssMepConfigLmHliEntry 1 }

vtssMepConfigLmHliEnable OBJECT-TYPE
    SYNTAX      TruthValue
    MAX-ACCESS  read-write
    STATUS      current
    DESCRIPTION 
        "Loss Measurement High Loss Interval is enabled"
    ::= { vtssMepConfigLmHliEntry 2 }

vtssMepConfigLmHliHiLosRatioThr OBJECT-TYPE
    SYNTAX      Unsigned32
    MAX-ACCESS  read-write
    STATUS      current
    DESCRIPTION 
        "High Loss Interval frame loss ratio threshold in per mille."
    ::= { vtssMepConfigLmHliEntry 3 }

vtssMepConfigLmHliConInterval OBJECT-TYPE
    SYNTAX      Unsigned32
    MAX-ACCESS  read-write
    STATUS      current
    DESCRIPTION 
        "High Loss Interval consecutive interval (number of measurements)."
    ::= { vtssMepConfigLmHliEntry 4 }

vtssMepConfigLmHliCntHolddownTimer OBJECT-TYPE
    SYNTAX      Unsigned32
    MAX-ACCESS  read-write
    STATUS      current
    DESCRIPTION 
        "Holddown timer in seconds for JSON notification updates for High Loss
         Interval NearEndCnt and FarEndCnt."
    ::= { vtssMepConfigLmHliEntry 5 }

vtssMepConfigLmSdeg OBJECT IDENTIFIER
    ::= { vtssMepConfig 21 }

vtssMepConfigLmSdegTable OBJECT-TYPE
    SYNTAX      SEQUENCE OF VTSSMepConfigLmSdegEntry
    MAX-ACCESS  not-accessible
    STATUS      current
    DESCRIPTION 
        "This is a table of created instance Loss Measurement Signal Degrade
         configuration parameters"
    ::= { vtssMepConfigLmSdeg 1 }

vtssMepConfigLmSdegEntry OBJECT-TYPE
    SYNTAX      VTSSMepConfigLmSdegEntry
    MAX-ACCESS  not-accessible
    STATUS      current
    DESCRIPTION 
        "This is a created instance Loss Measurement Signal Degrade parameters."
    INDEX       { vtssMepConfigLmSdegId }
    ::= { vtssMepConfigLmSdegTable 1 }

VTSSMepConfigLmSdegEntry ::= SEQUENCE {
    vtssMepConfigLmSdegId   Integer32,
    vtssMepConfigLmSdegEnable   TruthValue,
    vtssMepConfigLmSdegTxMin    Unsigned32,
    vtssMepConfigLmSdegLosRatioThr      Unsigned32,
    vtssMepConfigLmSdegBadThr   Unsigned32,
    vtssMepConfigLmSdegGoodThr      Unsigned32
}

vtssMepConfigLmSdegId OBJECT-TYPE
    SYNTAX      Integer32 (0..2147483647)
    MAX-ACCESS  not-accessible
    STATUS      current
    DESCRIPTION 
        "The MEP instance ID"
    ::= { vtssMepConfigLmSdegEntry 1 }

vtssMepConfigLmSdegEnable OBJECT-TYPE
    SYNTAX      TruthValue
    MAX-ACCESS  read-write
    STATUS      current
    DESCRIPTION 
        "Loss Measurement Signal Degrade is enabled"
    ::= { vtssMepConfigLmSdegEntry 2 }

vtssMepConfigLmSdegTxMin OBJECT-TYPE
    SYNTAX      Unsigned32
    MAX-ACCESS  read-write
    STATUS      current
    DESCRIPTION 
        "Minimum number of frames that must be transmitted in a measurement
         before frame loss ratio is tested against LosRatioThr."
    ::= { vtssMepConfigLmSdegEntry 3 }

vtssMepConfigLmSdegLosRatioThr OBJECT-TYPE
    SYNTAX      Unsigned32
    MAX-ACCESS  read-write
    STATUS      current
    DESCRIPTION 
        "Signal Degraded frame loss ratio threshold in per mille."
    ::= { vtssMepConfigLmSdegEntry 4 }

vtssMepConfigLmSdegBadThr OBJECT-TYPE
    SYNTAX      Unsigned32
    MAX-ACCESS  read-write
    STATUS      current
    DESCRIPTION 
        "Number of consecutive bad interval measurements required to set degrade
         state."
    ::= { vtssMepConfigLmSdegEntry 5 }

vtssMepConfigLmSdegGoodThr OBJECT-TYPE
    SYNTAX      Unsigned32
    MAX-ACCESS  read-write
    STATUS      current
    DESCRIPTION 
        "Number of consecutive good interval measurements required to clear
         degrade state."
    ::= { vtssMepConfigLmSdegEntry 6 }

vtssMepStatus OBJECT IDENTIFIER
    ::= { vtssMepMibObjects 3 }

vtssMepStatusInstance OBJECT IDENTIFIER
    ::= { vtssMepStatus 1 }

vtssMepStatusInstanceTable OBJECT-TYPE
    SYNTAX      SEQUENCE OF VTSSMepStatusInstanceEntry
    MAX-ACCESS  not-accessible
    STATUS      current
    DESCRIPTION 
        "This is a table of created instance status"
    ::= { vtssMepStatusInstance 1 }

vtssMepStatusInstanceEntry OBJECT-TYPE
    SYNTAX      VTSSMepStatusInstanceEntry
    MAX-ACCESS  not-accessible
    STATUS      current
    DESCRIPTION 
        "This is a created instance status"
    INDEX       { vtssMepStatusInstanceId }
    ::= { vtssMepStatusInstanceTable 1 }

VTSSMepStatusInstanceEntry ::= SEQUENCE {
    vtssMepStatusInstanceId     Integer32,
    vtssMepStatusInstanceClevel     TruthValue,
    vtssMepStatusInstanceCmeg   TruthValue,
    vtssMepStatusInstanceCmep   TruthValue,
    vtssMepStatusInstanceCssf   TruthValue,
    vtssMepStatusInstanceCais   TruthValue,
    vtssMepStatusInstanceClck   TruthValue,
    vtssMepStatusInstanceAtsf   TruthValue,
    vtssMepStatusInstanceAtsd   TruthValue,
    vtssMepStatusInstanceAblk   TruthValue,
    vtssMepStatusInstanceCloop      TruthValue,
    vtssMepStatusInstanceCconfig    TruthValue,
    vtssMepStatusInstanceCdeg   TruthValue
}

vtssMepStatusInstanceId OBJECT-TYPE
    SYNTAX      Integer32 (0..2147483647)
    MAX-ACCESS  not-accessible
    STATUS      current
    DESCRIPTION 
        "The MEP instance ID"
    ::= { vtssMepStatusInstanceEntry 1 }

vtssMepStatusInstanceClevel OBJECT-TYPE
    SYNTAX      TruthValue
    MAX-ACCESS  read-only
    STATUS      current
    DESCRIPTION 
        "Incorrect CCM level received"
    ::= { vtssMepStatusInstanceEntry 2 }

vtssMepStatusInstanceCmeg OBJECT-TYPE
    SYNTAX      TruthValue
    MAX-ACCESS  read-only
    STATUS      current
    DESCRIPTION 
        "Incorrect CCM MEG id received"
    ::= { vtssMepStatusInstanceEntry 3 }

vtssMepStatusInstanceCmep OBJECT-TYPE
    SYNTAX      TruthValue
    MAX-ACCESS  read-only
    STATUS      current
    DESCRIPTION 
        "Incorrect CCM MEP id received"
    ::= { vtssMepStatusInstanceEntry 4 }

vtssMepStatusInstanceCssf OBJECT-TYPE
    SYNTAX      TruthValue
    MAX-ACCESS  read-only
    STATUS      current
    DESCRIPTION 
        "SSF state"
    ::= { vtssMepStatusInstanceEntry 5 }

vtssMepStatusInstanceCais OBJECT-TYPE
    SYNTAX      TruthValue
    MAX-ACCESS  read-only
    STATUS      current
    DESCRIPTION 
        "AIS state. AIS is received."
    ::= { vtssMepStatusInstanceEntry 6 }

vtssMepStatusInstanceClck OBJECT-TYPE
    SYNTAX      TruthValue
    MAX-ACCESS  read-only
    STATUS      current
    DESCRIPTION 
        "Locked State. LCK is received."
    ::= { vtssMepStatusInstanceEntry 7 }

vtssMepStatusInstanceAtsf OBJECT-TYPE
    SYNTAX      TruthValue
    MAX-ACCESS  read-only
    STATUS      current
    DESCRIPTION 
        "Trail Signal fail consequent action is calculated"
    ::= { vtssMepStatusInstanceEntry 8 }

vtssMepStatusInstanceAtsd OBJECT-TYPE
    SYNTAX      TruthValue
    MAX-ACCESS  read-only
    STATUS      current
    DESCRIPTION 
        "Trail Signal degrade consequent action is calculated"
    ::= { vtssMepStatusInstanceEntry 9 }

vtssMepStatusInstanceAblk OBJECT-TYPE
    SYNTAX      TruthValue
    MAX-ACCESS  read-only
    STATUS      current
    DESCRIPTION 
        "Block consequent action is calculated"
    ::= { vtssMepStatusInstanceEntry 10 }

vtssMepStatusInstanceCloop OBJECT-TYPE
    SYNTAX      TruthValue
    MAX-ACCESS  read-only
    STATUS      current
    DESCRIPTION 
        "Loop is detected. CCM is received with own MEP ID and SMAC."
    ::= { vtssMepStatusInstanceEntry 11 }

vtssMepStatusInstanceCconfig OBJECT-TYPE
    SYNTAX      TruthValue
    MAX-ACCESS  read-only
    STATUS      current
    DESCRIPTION 
        "Configuration error detected. CCM is received with own MEP ID."
    ::= { vtssMepStatusInstanceEntry 12 }

vtssMepStatusInstanceCdeg OBJECT-TYPE
    SYNTAX      TruthValue
    MAX-ACCESS  read-only
    STATUS      current
    DESCRIPTION 
        "Signal Degraded."
    ::= { vtssMepStatusInstanceEntry 13 }

vtssMepStatusInstancePeerTable OBJECT-TYPE
    SYNTAX      SEQUENCE OF VTSSMepStatusInstancePeerEntry
    MAX-ACCESS  not-accessible
    STATUS      current
    DESCRIPTION 
        "This is a table of peer MEP status"
    ::= { vtssMepStatusInstance 2 }

vtssMepStatusInstancePeerEntry OBJECT-TYPE
    SYNTAX      VTSSMepStatusInstancePeerEntry
    MAX-ACCESS  not-accessible
    STATUS      current
    DESCRIPTION 
        "This is a peer MEP status"
    INDEX       { vtssMepStatusInstancePeerId, vtssMepStatusInstancePeerPeerId }
    ::= { vtssMepStatusInstancePeerTable 1 }

VTSSMepStatusInstancePeerEntry ::= SEQUENCE {
    vtssMepStatusInstancePeerId     Integer32,
    vtssMepStatusInstancePeerPeerId     Integer32,
    vtssMepStatusInstancePeerCloc   TruthValue,
    vtssMepStatusInstancePeerCrdi   TruthValue,
    vtssMepStatusInstancePeerCperiod    TruthValue,
    vtssMepStatusInstancePeerCprio      TruthValue
}

vtssMepStatusInstancePeerId OBJECT-TYPE
    SYNTAX      Integer32 (0..2147483647)
    MAX-ACCESS  not-accessible
    STATUS      current
    DESCRIPTION 
        "The MEP instance ID"
    ::= { vtssMepStatusInstancePeerEntry 1 }

vtssMepStatusInstancePeerPeerId OBJECT-TYPE
    SYNTAX      Integer32 (0..2147483647)
    MAX-ACCESS  not-accessible
    STATUS      current
    DESCRIPTION 
        "The Peer MEP ID"
    ::= { vtssMepStatusInstancePeerEntry 2 }

vtssMepStatusInstancePeerCloc OBJECT-TYPE
    SYNTAX      TruthValue
    MAX-ACCESS  read-only
    STATUS      current
    DESCRIPTION 
        "CCM LOC state from peer MEP"
    ::= { vtssMepStatusInstancePeerEntry 3 }

vtssMepStatusInstancePeerCrdi OBJECT-TYPE
    SYNTAX      TruthValue
    MAX-ACCESS  read-only
    STATUS      current
    DESCRIPTION 
        "CCM RDI state from peer MEP"
    ::= { vtssMepStatusInstancePeerEntry 4 }

vtssMepStatusInstancePeerCperiod OBJECT-TYPE
    SYNTAX      TruthValue
    MAX-ACCESS  read-only
    STATUS      current
    DESCRIPTION 
        "CCM Period state from peer MEP"
    ::= { vtssMepStatusInstancePeerEntry 5 }

vtssMepStatusInstancePeerCprio OBJECT-TYPE
    SYNTAX      TruthValue
    MAX-ACCESS  read-only
    STATUS      current
    DESCRIPTION 
        "CCM Priority state from peer MEP"
    ::= { vtssMepStatusInstancePeerEntry 6 }

vtssMepStatusLm OBJECT IDENTIFIER
    ::= { vtssMepStatus 2 }

vtssMepStatusLmTable OBJECT-TYPE
    SYNTAX      SEQUENCE OF VTSSMepStatusLmEntry
    MAX-ACCESS  not-accessible
    STATUS      current
    DESCRIPTION 
        "This is a table of Loss Measurement status"
    ::= { vtssMepStatusLm 1 }

vtssMepStatusLmEntry OBJECT-TYPE
    SYNTAX      VTSSMepStatusLmEntry
    MAX-ACCESS  not-accessible
    STATUS      current
    DESCRIPTION 
        "This is a Loss Measurement status"
    INDEX       { vtssMepStatusLmId }
    ::= { vtssMepStatusLmTable 1 }

VTSSMepStatusLmEntry ::= SEQUENCE {
    vtssMepStatusLmId   Integer32,
    vtssMepStatusLmTxCounter    Unsigned32,
    vtssMepStatusLmRxCounter    Unsigned32,
    vtssMepStatusLmNearEndLosCounterTot     Integer32,
    vtssMepStatusLmFarEndLosCounterTot      Integer32,
    vtssMepStatusLmNearEndLosRatioInt   Unsigned32,
    vtssMepStatusLmFarEndLosRatioInt    Unsigned32,
    vtssMepStatusLmNearEndLosCounterInt     Integer32,
    vtssMepStatusLmFarEndLosCounterInt      Integer32,
    vtssMepStatusLmNearEndLosThCnt      Unsigned32,
    vtssMepStatusLmFarEndLosThCnt   Unsigned32,
    vtssMepStatusLmNearEndLosRatioTot   Unsigned32,
    vtssMepStatusLmFarEndLosRatioTot    Unsigned32,
    vtssMepStatusLmNearEndLosRatioMin   Unsigned32,
    vtssMepStatusLmFarEndLosRatioMin    Unsigned32,
    vtssMepStatusLmNearEndLosRatioMax   Unsigned32,
    vtssMepStatusLmFarEndLosRatioMax    Unsigned32
}

vtssMepStatusLmId OBJECT-TYPE
    SYNTAX      Integer32 (0..2147483647)
    MAX-ACCESS  not-accessible
    STATUS      current
    DESCRIPTION 
        "The MEP instance ID"
    ::= { vtssMepStatusLmEntry 1 }

vtssMepStatusLmTxCounter OBJECT-TYPE
    SYNTAX      Unsigned32
    MAX-ACCESS  read-only
    STATUS      current
    DESCRIPTION 
        "Transmitted PDU (LMM - CCM) containing counters."
    ::= { vtssMepStatusLmEntry 2 }

vtssMepStatusLmRxCounter OBJECT-TYPE
    SYNTAX      Unsigned32
    MAX-ACCESS  read-only
    STATUS      current
    DESCRIPTION 
        "Received PDU (LMM - CCM) containing counters."
    ::= { vtssMepStatusLmEntry 3 }

vtssMepStatusLmNearEndLosCounterTot OBJECT-TYPE
    SYNTAX      Integer32
    MAX-ACCESS  read-only
    STATUS      current
    DESCRIPTION 
        "Near end total frame loss counter."
    ::= { vtssMepStatusLmEntry 4 }

vtssMepStatusLmFarEndLosCounterTot OBJECT-TYPE
    SYNTAX      Integer32
    MAX-ACCESS  read-only
    STATUS      current
    DESCRIPTION 
        "Far end total frame loss counter."
    ::= { vtssMepStatusLmEntry 5 }

vtssMepStatusLmNearEndLosRatioInt OBJECT-TYPE
    SYNTAX      Unsigned32
    MAX-ACCESS  read-only
    STATUS      current
    DESCRIPTION 
        "Near end frame loss ratio for interval in per mille."
    ::= { vtssMepStatusLmEntry 6 }

vtssMepStatusLmFarEndLosRatioInt OBJECT-TYPE
    SYNTAX      Unsigned32
    MAX-ACCESS  read-only
    STATUS      current
    DESCRIPTION 
        "Far end frame loss ratio for interval in per mille."
    ::= { vtssMepStatusLmEntry 7 }

vtssMepStatusLmNearEndLosCounterInt OBJECT-TYPE
    SYNTAX      Integer32
    MAX-ACCESS  read-only
    STATUS      current
    DESCRIPTION 
        "Near end frame loss counter for interval."
    ::= { vtssMepStatusLmEntry 8 }

vtssMepStatusLmFarEndLosCounterInt OBJECT-TYPE
    SYNTAX      Integer32
    MAX-ACCESS  read-only
    STATUS      current
    DESCRIPTION 
        "Far end frame loss counter for interval."
    ::= { vtssMepStatusLmEntry 9 }

vtssMepStatusLmNearEndLosThCnt OBJECT-TYPE
    SYNTAX      Unsigned32
    MAX-ACCESS  read-only
    STATUS      current
    DESCRIPTION 
        "Near end frame loss threshold count."
    ::= { vtssMepStatusLmEntry 10 }

vtssMepStatusLmFarEndLosThCnt OBJECT-TYPE
    SYNTAX      Unsigned32
    MAX-ACCESS  read-only
    STATUS      current
    DESCRIPTION 
        "Far end frame loss threshold count."
    ::= { vtssMepStatusLmEntry 11 }

vtssMepStatusLmNearEndLosRatioTot OBJECT-TYPE
    SYNTAX      Unsigned32
    MAX-ACCESS  read-only
    STATUS      current
    DESCRIPTION 
        "Near end total frame loss ratio in per mille (average since last
         clear)."
    ::= { vtssMepStatusLmEntry 12 }

vtssMepStatusLmFarEndLosRatioTot OBJECT-TYPE
    SYNTAX      Unsigned32
    MAX-ACCESS  read-only
    STATUS      current
    DESCRIPTION 
        "Far end total frame loss ratio in per mille (average since last clear)."
    ::= { vtssMepStatusLmEntry 13 }

vtssMepStatusLmNearEndLosRatioMin OBJECT-TYPE
    SYNTAX      Unsigned32
    MAX-ACCESS  read-only
    STATUS      current
    DESCRIPTION 
        "Near end minimum frame loss ratio in per mille (since last clear)."
    ::= { vtssMepStatusLmEntry 14 }

vtssMepStatusLmFarEndLosRatioMin OBJECT-TYPE
    SYNTAX      Unsigned32
    MAX-ACCESS  read-only
    STATUS      current
    DESCRIPTION 
        "Far end minimum frame loss ratio in per mille (since last clear)."
    ::= { vtssMepStatusLmEntry 15 }

vtssMepStatusLmNearEndLosRatioMax OBJECT-TYPE
    SYNTAX      Unsigned32
    MAX-ACCESS  read-only
    STATUS      current
    DESCRIPTION 
        "Near end maximum frame loss ratio in per mille (since last clear)."
    ::= { vtssMepStatusLmEntry 16 }

vtssMepStatusLmFarEndLosRatioMax OBJECT-TYPE
    SYNTAX      Unsigned32
    MAX-ACCESS  read-only
    STATUS      current
    DESCRIPTION 
        "Far end maximum frame loss ratio in per mille (since last clear)."
    ::= { vtssMepStatusLmEntry 17 }

vtssMepStatusDm OBJECT IDENTIFIER
    ::= { vtssMepStatus 3 }

vtssMepStatusDmTwoWayTable OBJECT-TYPE
    SYNTAX      SEQUENCE OF VTSSMepStatusDmTwoWayEntry
    MAX-ACCESS  not-accessible
    STATUS      current
    DESCRIPTION 
        "This is a table of Delay Measurement Two Way status"
    ::= { vtssMepStatusDm 1 }

vtssMepStatusDmTwoWayEntry OBJECT-TYPE
    SYNTAX      VTSSMepStatusDmTwoWayEntry
    MAX-ACCESS  not-accessible
    STATUS      current
    DESCRIPTION 
        "This is a Delay Measurement Two Way status"
    INDEX       { vtssMepStatusDmTwoWayId }
    ::= { vtssMepStatusDmTwoWayTable 1 }

VTSSMepStatusDmTwoWayEntry ::= SEQUENCE {
    vtssMepStatusDmTwoWayId     Integer32,
    vtssMepStatusDmTwoWayTxCounter      Unsigned32,
    vtssMepStatusDmTwoWayRxCounter      Unsigned32,
    vtssMepStatusDmTwoWayRxTimeOutCounter   Unsigned32,
    vtssMepStatusDmTwoWayRxErrorCounter     Unsigned32,
    vtssMepStatusDmTwoWayInternalOverflowCounter    Unsigned32,
    vtssMepStatusDmTwoWayAverageDelay   Unsigned32,
    vtssMepStatusDmTwoWayAverageLastnDelay      Unsigned32,
    vtssMepStatusDmTwoWayAverageDelayVariation      Unsigned32,
    vtssMepStatusDmTwoWayAverageLastnDelayVariation     Unsigned32,
    vtssMepStatusDmTwoWayMinimumDelay   Unsigned32,
    vtssMepStatusDmTwoWayMaximumDelay   Unsigned32,
    vtssMepStatusDmTwoWayMinimumDelayVariation      Unsigned32,
    vtssMepStatusDmTwoWayMaximumDelayVariation      Unsigned32,
    vtssMepStatusDmTwoWayTimeUnit   VTSSMepDmTimeUnit
}

vtssMepStatusDmTwoWayId OBJECT-TYPE
    SYNTAX      Integer32 (0..2147483647)
    MAX-ACCESS  not-accessible
    STATUS      current
    DESCRIPTION 
        "The MEP instance ID"
    ::= { vtssMepStatusDmTwoWayEntry 1 }

vtssMepStatusDmTwoWayTxCounter OBJECT-TYPE
    SYNTAX      Unsigned32
    MAX-ACCESS  read-only
    STATUS      current
    DESCRIPTION 
        "Transmitted DMM/1DM frames."
    ::= { vtssMepStatusDmTwoWayEntry 2 }

vtssMepStatusDmTwoWayRxCounter OBJECT-TYPE
    SYNTAX      Unsigned32
    MAX-ACCESS  read-only
    STATUS      current
    DESCRIPTION 
        "Received DMM/1DM frames."
    ::= { vtssMepStatusDmTwoWayEntry 3 }

vtssMepStatusDmTwoWayRxTimeOutCounter OBJECT-TYPE
    SYNTAX      Unsigned32
    MAX-ACCESS  read-only
    STATUS      current
    DESCRIPTION 
        "Received DMR time-out. After transmission of DMM, the DMR is expected
         to be received within 1 sec."
    ::= { vtssMepStatusDmTwoWayEntry 4 }

vtssMepStatusDmTwoWayRxErrorCounter OBJECT-TYPE
    SYNTAX      Unsigned32
    MAX-ACCESS  read-only
    STATUS      current
    DESCRIPTION 
        "Received error counter. It is considered an error if a delay is
         negative or above 1 sec."
    ::= { vtssMepStatusDmTwoWayEntry 5 }

vtssMepStatusDmTwoWayInternalOverflowCounter OBJECT-TYPE
    SYNTAX      Unsigned32
    MAX-ACCESS  read-only
    STATUS      current
    DESCRIPTION 
        "The internal total delay counter overflow counter."
    ::= { vtssMepStatusDmTwoWayEntry 6 }

vtssMepStatusDmTwoWayAverageDelay OBJECT-TYPE
    SYNTAX      Unsigned32
    MAX-ACCESS  read-only
    STATUS      current
    DESCRIPTION 
        "The total average delay."
    ::= { vtssMepStatusDmTwoWayEntry 7 }

vtssMepStatusDmTwoWayAverageLastnDelay OBJECT-TYPE
    SYNTAX      Unsigned32
    MAX-ACCESS  read-only
    STATUS      current
    DESCRIPTION 
        "The last N average delay."
    ::= { vtssMepStatusDmTwoWayEntry 8 }

vtssMepStatusDmTwoWayAverageDelayVariation OBJECT-TYPE
    SYNTAX      Unsigned32
    MAX-ACCESS  read-only
    STATUS      current
    DESCRIPTION 
        "The total average delay variation."
    ::= { vtssMepStatusDmTwoWayEntry 9 }

vtssMepStatusDmTwoWayAverageLastnDelayVariation OBJECT-TYPE
    SYNTAX      Unsigned32
    MAX-ACCESS  read-only
    STATUS      current
    DESCRIPTION 
        "The last N average delay variation."
    ::= { vtssMepStatusDmTwoWayEntry 10 }

vtssMepStatusDmTwoWayMinimumDelay OBJECT-TYPE
    SYNTAX      Unsigned32
    MAX-ACCESS  read-only
    STATUS      current
    DESCRIPTION 
        "The minimum delay measured."
    ::= { vtssMepStatusDmTwoWayEntry 11 }

vtssMepStatusDmTwoWayMaximumDelay OBJECT-TYPE
    SYNTAX      Unsigned32
    MAX-ACCESS  read-only
    STATUS      current
    DESCRIPTION 
        "The maximum delay measured."
    ::= { vtssMepStatusDmTwoWayEntry 12 }

vtssMepStatusDmTwoWayMinimumDelayVariation OBJECT-TYPE
    SYNTAX      Unsigned32
    MAX-ACCESS  read-only
    STATUS      current
    DESCRIPTION 
        "The minimum delay variation measured."
    ::= { vtssMepStatusDmTwoWayEntry 13 }

vtssMepStatusDmTwoWayMaximumDelayVariation OBJECT-TYPE
    SYNTAX      Unsigned32
    MAX-ACCESS  read-only
    STATUS      current
    DESCRIPTION 
        "The maximum delay variation measured."
    ::= { vtssMepStatusDmTwoWayEntry 14 }

vtssMepStatusDmTwoWayTimeUnit OBJECT-TYPE
    SYNTAX      VTSSMepDmTimeUnit
    MAX-ACCESS  read-only
    STATUS      current
    DESCRIPTION 
        "Calculation time unit."
    ::= { vtssMepStatusDmTwoWayEntry 15 }

vtssMepStatusDmOneWayFarNearTable OBJECT-TYPE
    SYNTAX      SEQUENCE OF VTSSMepStatusDmOneWayFarNearEntry
    MAX-ACCESS  not-accessible
    STATUS      current
    DESCRIPTION 
        "This is a table of Delay Measurement One Way Far to Near status"
    ::= { vtssMepStatusDm 2 }

vtssMepStatusDmOneWayFarNearEntry OBJECT-TYPE
    SYNTAX      VTSSMepStatusDmOneWayFarNearEntry
    MAX-ACCESS  not-accessible
    STATUS      current
    DESCRIPTION 
        "This is a Delay Measurement Two Way Far to Near status"
    INDEX       { vtssMepStatusDmOneWayFarNearId }
    ::= { vtssMepStatusDmOneWayFarNearTable 1 }

VTSSMepStatusDmOneWayFarNearEntry ::= SEQUENCE {
    vtssMepStatusDmOneWayFarNearId      Integer32,
    vtssMepStatusDmOneWayFarNearTxCounter   Unsigned32,
    vtssMepStatusDmOneWayFarNearRxCounter   Unsigned32,
    vtssMepStatusDmOneWayFarNearRxTimeOutCounter    Unsigned32,
    vtssMepStatusDmOneWayFarNearRxErrorCounter      Unsigned32,
    vtssMepStatusDmOneWayFarNearInternalOverflowCounter     Unsigned32,
    vtssMepStatusDmOneWayFarNearAverageDelay    Unsigned32,
    vtssMepStatusDmOneWayFarNearAverageLastnDelay   Unsigned32,
    vtssMepStatusDmOneWayFarNearAverageDelayVariation   Unsigned32,
    vtssMepStatusDmOneWayFarNearAverageLastnDelayVariation      Unsigned32,
    vtssMepStatusDmOneWayFarNearMinimumDelay    Unsigned32,
    vtssMepStatusDmOneWayFarNearMaximumDelay    Unsigned32,
    vtssMepStatusDmOneWayFarNearMinimumDelayVariation   Unsigned32,
    vtssMepStatusDmOneWayFarNearMaximumDelayVariation   Unsigned32,
    vtssMepStatusDmOneWayFarNearTimeUnit    VTSSMepDmTimeUnit
}

vtssMepStatusDmOneWayFarNearId OBJECT-TYPE
    SYNTAX      Integer32 (0..2147483647)
    MAX-ACCESS  not-accessible
    STATUS      current
    DESCRIPTION 
        "The MEP instance ID"
    ::= { vtssMepStatusDmOneWayFarNearEntry 1 }

vtssMepStatusDmOneWayFarNearTxCounter OBJECT-TYPE
    SYNTAX      Unsigned32
    MAX-ACCESS  read-only
    STATUS      current
    DESCRIPTION 
        "Transmitted DMM/1DM frames."
    ::= { vtssMepStatusDmOneWayFarNearEntry 2 }

vtssMepStatusDmOneWayFarNearRxCounter OBJECT-TYPE
    SYNTAX      Unsigned32
    MAX-ACCESS  read-only
    STATUS      current
    DESCRIPTION 
        "Received DMM/1DM frames."
    ::= { vtssMepStatusDmOneWayFarNearEntry 3 }

vtssMepStatusDmOneWayFarNearRxTimeOutCounter OBJECT-TYPE
    SYNTAX      Unsigned32
    MAX-ACCESS  read-only
    STATUS      current
    DESCRIPTION 
        "Received DMR time-out. After transmission of DMM, the DMR is expected
         to be received within 1 sec."
    ::= { vtssMepStatusDmOneWayFarNearEntry 4 }

vtssMepStatusDmOneWayFarNearRxErrorCounter OBJECT-TYPE
    SYNTAX      Unsigned32
    MAX-ACCESS  read-only
    STATUS      current
    DESCRIPTION 
        "Received error counter. It is considered an error if a delay is
         negative or above 1 sec."
    ::= { vtssMepStatusDmOneWayFarNearEntry 5 }

vtssMepStatusDmOneWayFarNearInternalOverflowCounter OBJECT-TYPE
    SYNTAX      Unsigned32
    MAX-ACCESS  read-only
    STATUS      current
    DESCRIPTION 
        "The internal total delay counter overflow counter."
    ::= { vtssMepStatusDmOneWayFarNearEntry 6 }

vtssMepStatusDmOneWayFarNearAverageDelay OBJECT-TYPE
    SYNTAX      Unsigned32
    MAX-ACCESS  read-only
    STATUS      current
    DESCRIPTION 
        "The total average delay."
    ::= { vtssMepStatusDmOneWayFarNearEntry 7 }

vtssMepStatusDmOneWayFarNearAverageLastnDelay OBJECT-TYPE
    SYNTAX      Unsigned32
    MAX-ACCESS  read-only
    STATUS      current
    DESCRIPTION 
        "The last N average delay."
    ::= { vtssMepStatusDmOneWayFarNearEntry 8 }

vtssMepStatusDmOneWayFarNearAverageDelayVariation OBJECT-TYPE
    SYNTAX      Unsigned32
    MAX-ACCESS  read-only
    STATUS      current
    DESCRIPTION 
        "The total average delay variation."
    ::= { vtssMepStatusDmOneWayFarNearEntry 9 }

vtssMepStatusDmOneWayFarNearAverageLastnDelayVariation OBJECT-TYPE
    SYNTAX      Unsigned32
    MAX-ACCESS  read-only
    STATUS      current
    DESCRIPTION 
        "The last N average delay variation."
    ::= { vtssMepStatusDmOneWayFarNearEntry 10 }

vtssMepStatusDmOneWayFarNearMinimumDelay OBJECT-TYPE
    SYNTAX      Unsigned32
    MAX-ACCESS  read-only
    STATUS      current
    DESCRIPTION 
        "The minimum delay measured."
    ::= { vtssMepStatusDmOneWayFarNearEntry 11 }

vtssMepStatusDmOneWayFarNearMaximumDelay OBJECT-TYPE
    SYNTAX      Unsigned32
    MAX-ACCESS  read-only
    STATUS      current
    DESCRIPTION 
        "The maximum delay measured."
    ::= { vtssMepStatusDmOneWayFarNearEntry 12 }

vtssMepStatusDmOneWayFarNearMinimumDelayVariation OBJECT-TYPE
    SYNTAX      Unsigned32
    MAX-ACCESS  read-only
    STATUS      current
    DESCRIPTION 
        "The minimum delay variation measured."
    ::= { vtssMepStatusDmOneWayFarNearEntry 13 }

vtssMepStatusDmOneWayFarNearMaximumDelayVariation OBJECT-TYPE
    SYNTAX      Unsigned32
    MAX-ACCESS  read-only
    STATUS      current
    DESCRIPTION 
        "The maximum delay variation measured."
    ::= { vtssMepStatusDmOneWayFarNearEntry 14 }

vtssMepStatusDmOneWayFarNearTimeUnit OBJECT-TYPE
    SYNTAX      VTSSMepDmTimeUnit
    MAX-ACCESS  read-only
    STATUS      current
    DESCRIPTION 
        "Calculation time unit."
    ::= { vtssMepStatusDmOneWayFarNearEntry 15 }

vtssMepStatusDmOneWayNearFarTable OBJECT-TYPE
    SYNTAX      SEQUENCE OF VTSSMepStatusDmOneWayNearFarEntry
    MAX-ACCESS  not-accessible
    STATUS      current
    DESCRIPTION 
        "This is a table of Delay Measurement One Way Near to Far status"
    ::= { vtssMepStatusDm 3 }

vtssMepStatusDmOneWayNearFarEntry OBJECT-TYPE
    SYNTAX      VTSSMepStatusDmOneWayNearFarEntry
    MAX-ACCESS  not-accessible
    STATUS      current
    DESCRIPTION 
        "This is a Delay Measurement Two Way Near to Far status"
    INDEX       { vtssMepStatusDmOneWayNearFarId }
    ::= { vtssMepStatusDmOneWayNearFarTable 1 }

VTSSMepStatusDmOneWayNearFarEntry ::= SEQUENCE {
    vtssMepStatusDmOneWayNearFarId      Integer32,
    vtssMepStatusDmOneWayNearFarTxCounter   Unsigned32,
    vtssMepStatusDmOneWayNearFarRxCounter   Unsigned32,
    vtssMepStatusDmOneWayNearFarRxTimeOutCounter    Unsigned32,
    vtssMepStatusDmOneWayNearFarRxErrorCounter      Unsigned32,
    vtssMepStatusDmOneWayNearFarInternalOverflowCounter     Unsigned32,
    vtssMepStatusDmOneWayNearFarAverageDelay    Unsigned32,
    vtssMepStatusDmOneWayNearFarAverageLastnDelay   Unsigned32,
    vtssMepStatusDmOneWayNearFarAverageDelayVariation   Unsigned32,
    vtssMepStatusDmOneWayNearFarAverageLastnDelayVariation      Unsigned32,
    vtssMepStatusDmOneWayNearFarMinimumDelay    Unsigned32,
    vtssMepStatusDmOneWayNearFarMaximumDelay    Unsigned32,
    vtssMepStatusDmOneWayNearFarMinimumDelayVariation   Unsigned32,
    vtssMepStatusDmOneWayNearFarMaximumDelayVariation   Unsigned32,
    vtssMepStatusDmOneWayNearFarTimeUnit    VTSSMepDmTimeUnit
}

vtssMepStatusDmOneWayNearFarId OBJECT-TYPE
    SYNTAX      Integer32 (0..2147483647)
    MAX-ACCESS  not-accessible
    STATUS      current
    DESCRIPTION 
        "The MEP instance ID"
    ::= { vtssMepStatusDmOneWayNearFarEntry 1 }

vtssMepStatusDmOneWayNearFarTxCounter OBJECT-TYPE
    SYNTAX      Unsigned32
    MAX-ACCESS  read-only
    STATUS      current
    DESCRIPTION 
        "Transmitted DMM/1DM frames."
    ::= { vtssMepStatusDmOneWayNearFarEntry 2 }

vtssMepStatusDmOneWayNearFarRxCounter OBJECT-TYPE
    SYNTAX      Unsigned32
    MAX-ACCESS  read-only
    STATUS      current
    DESCRIPTION 
        "Received DMM/1DM frames."
    ::= { vtssMepStatusDmOneWayNearFarEntry 3 }

vtssMepStatusDmOneWayNearFarRxTimeOutCounter OBJECT-TYPE
    SYNTAX      Unsigned32
    MAX-ACCESS  read-only
    STATUS      current
    DESCRIPTION 
        "Received DMR time-out. After transmission of DMM, the DMR is expected
         to be received within 1 sec."
    ::= { vtssMepStatusDmOneWayNearFarEntry 4 }

vtssMepStatusDmOneWayNearFarRxErrorCounter OBJECT-TYPE
    SYNTAX      Unsigned32
    MAX-ACCESS  read-only
    STATUS      current
    DESCRIPTION 
        "Received error counter. It is considered an error if a delay is
         negative or above 1 sec."
    ::= { vtssMepStatusDmOneWayNearFarEntry 5 }

vtssMepStatusDmOneWayNearFarInternalOverflowCounter OBJECT-TYPE
    SYNTAX      Unsigned32
    MAX-ACCESS  read-only
    STATUS      current
    DESCRIPTION 
        "The internal total delay counter overflow counter."
    ::= { vtssMepStatusDmOneWayNearFarEntry 6 }

vtssMepStatusDmOneWayNearFarAverageDelay OBJECT-TYPE
    SYNTAX      Unsigned32
    MAX-ACCESS  read-only
    STATUS      current
    DESCRIPTION 
        "The total average delay."
    ::= { vtssMepStatusDmOneWayNearFarEntry 7 }

vtssMepStatusDmOneWayNearFarAverageLastnDelay OBJECT-TYPE
    SYNTAX      Unsigned32
    MAX-ACCESS  read-only
    STATUS      current
    DESCRIPTION 
        "The last N average delay."
    ::= { vtssMepStatusDmOneWayNearFarEntry 8 }

vtssMepStatusDmOneWayNearFarAverageDelayVariation OBJECT-TYPE
    SYNTAX      Unsigned32
    MAX-ACCESS  read-only
    STATUS      current
    DESCRIPTION 
        "The total average delay variation."
    ::= { vtssMepStatusDmOneWayNearFarEntry 9 }

vtssMepStatusDmOneWayNearFarAverageLastnDelayVariation OBJECT-TYPE
    SYNTAX      Unsigned32
    MAX-ACCESS  read-only
    STATUS      current
    DESCRIPTION 
        "The last N average delay variation."
    ::= { vtssMepStatusDmOneWayNearFarEntry 10 }

vtssMepStatusDmOneWayNearFarMinimumDelay OBJECT-TYPE
    SYNTAX      Unsigned32
    MAX-ACCESS  read-only
    STATUS      current
    DESCRIPTION 
        "The minimum delay measured."
    ::= { vtssMepStatusDmOneWayNearFarEntry 11 }

vtssMepStatusDmOneWayNearFarMaximumDelay OBJECT-TYPE
    SYNTAX      Unsigned32
    MAX-ACCESS  read-only
    STATUS      current
    DESCRIPTION 
        "The maximum delay measured."
    ::= { vtssMepStatusDmOneWayNearFarEntry 12 }

vtssMepStatusDmOneWayNearFarMinimumDelayVariation OBJECT-TYPE
    SYNTAX      Unsigned32
    MAX-ACCESS  read-only
    STATUS      current
    DESCRIPTION 
        "The minimum delay variation measured."
    ::= { vtssMepStatusDmOneWayNearFarEntry 13 }

vtssMepStatusDmOneWayNearFarMaximumDelayVariation OBJECT-TYPE
    SYNTAX      Unsigned32
    MAX-ACCESS  read-only
    STATUS      current
    DESCRIPTION 
        "The maximum delay variation measured."
    ::= { vtssMepStatusDmOneWayNearFarEntry 14 }

vtssMepStatusDmOneWayNearFarTimeUnit OBJECT-TYPE
    SYNTAX      VTSSMepDmTimeUnit
    MAX-ACCESS  read-only
    STATUS      current
    DESCRIPTION 
        "Calculation time unit."
    ::= { vtssMepStatusDmOneWayNearFarEntry 15 }

vtssMepStatusLb OBJECT IDENTIFIER
    ::= { vtssMepStatus 4 }

vtssMepStatusLbTable OBJECT-TYPE
    SYNTAX      SEQUENCE OF VTSSMepStatusLbEntry
    MAX-ACCESS  not-accessible
    STATUS      current
    DESCRIPTION 
        "This is a table of Loop Back status"
    ::= { vtssMepStatusLb 1 }

vtssMepStatusLbEntry OBJECT-TYPE
    SYNTAX      VTSSMepStatusLbEntry
    MAX-ACCESS  not-accessible
    STATUS      current
    DESCRIPTION 
        "This is a Loop Back status"
    INDEX       { vtssMepStatusLbId }
    ::= { vtssMepStatusLbTable 1 }

VTSSMepStatusLbEntry ::= SEQUENCE {
    vtssMepStatusLbId   Integer32,
    vtssMepStatusLbTransactionId    Unsigned32,
    vtssMepStatusLbReplyCounter     Unsigned32,
    vtssMepStatusLbLbmTransmitted   Counter64
}

vtssMepStatusLbId OBJECT-TYPE
    SYNTAX      Integer32 (0..2147483647)
    MAX-ACCESS  not-accessible
    STATUS      current
    DESCRIPTION 
        "The MEP instance ID"
    ::= { vtssMepStatusLbEntry 1 }

vtssMepStatusLbTransactionId OBJECT-TYPE
    SYNTAX      Unsigned32
    MAX-ACCESS  read-only
    STATUS      current
    DESCRIPTION 
        "This is the transaction id that is used to send the next LBM."
    ::= { vtssMepStatusLbEntry 2 }

vtssMepStatusLbReplyCounter OBJECT-TYPE
    SYNTAX      Unsigned32
    MAX-ACCESS  read-only
    STATUS      current
    DESCRIPTION 
        "The number of replying MAC. In case of 'infinite' LBM there is only one
         reply."
    ::= { vtssMepStatusLbEntry 3 }

vtssMepStatusLbLbmTransmitted OBJECT-TYPE
    SYNTAX      Counter64
    MAX-ACCESS  read-only
    STATUS      current
    DESCRIPTION 
        "The number of transmitted LBM."
    ::= { vtssMepStatusLbEntry 4 }

vtssMepStatusLbReplyTable OBJECT-TYPE
    SYNTAX      SEQUENCE OF VTSSMepStatusLbReplyEntry
    MAX-ACCESS  not-accessible
    STATUS      current
    DESCRIPTION 
        "This is a table of Loop Back reply status"
    ::= { vtssMepStatusLb 2 }

vtssMepStatusLbReplyEntry OBJECT-TYPE
    SYNTAX      VTSSMepStatusLbReplyEntry
    MAX-ACCESS  not-accessible
    STATUS      current
    DESCRIPTION 
        "This is a Loop Back reply status"
    INDEX       { vtssMepStatusLbReplyId, vtssMepStatusLbReplyReplyId }
    ::= { vtssMepStatusLbReplyTable 1 }

VTSSMepStatusLbReplyEntry ::= SEQUENCE {
    vtssMepStatusLbReplyId      Integer32,
    vtssMepStatusLbReplyReplyId     Integer32,
    vtssMepStatusLbReplyMac     MacAddress,
    vtssMepStatusLbReplyLbrReceived     Counter64,
    vtssMepStatusLbReplyOutOfOrder      Counter64,
    vtssMepStatusLbReplyMepMipId    OCTET STRING
}

vtssMepStatusLbReplyId OBJECT-TYPE
    SYNTAX      Integer32 (0..2147483647)
    MAX-ACCESS  not-accessible
    STATUS      current
    DESCRIPTION 
        "The MEP instance ID"
    ::= { vtssMepStatusLbReplyEntry 1 }

vtssMepStatusLbReplyReplyId OBJECT-TYPE
    SYNTAX      Integer32 (0..2147483647)
    MAX-ACCESS  not-accessible
    STATUS      current
    DESCRIPTION 
        "The LB or LT Reply id"
    ::= { vtssMepStatusLbReplyEntry 2 }

vtssMepStatusLbReplyMac OBJECT-TYPE
    SYNTAX      MacAddress
    MAX-ACCESS  read-only
    STATUS      current
    DESCRIPTION 
        "LBR source MAC - this is only relevant if not 'infinite' LBM and not
         MPLS loopback"
    ::= { vtssMepStatusLbReplyEntry 3 }

vtssMepStatusLbReplyLbrReceived OBJECT-TYPE
    SYNTAX      Counter64
    MAX-ACCESS  read-only
    STATUS      current
    DESCRIPTION 
        "Number LBR received from MAC."
    ::= { vtssMepStatusLbReplyEntry 4 }

vtssMepStatusLbReplyOutOfOrder OBJECT-TYPE
    SYNTAX      Counter64
    MAX-ACCESS  read-only
    STATUS      current
    DESCRIPTION 
        "The OOO counter."
    ::= { vtssMepStatusLbReplyEntry 5 }

vtssMepStatusLbReplyMepMipId OBJECT-TYPE
    SYNTAX      OCTET STRING (SIZE(16))
    MAX-ACCESS  read-only
    STATUS      current
    DESCRIPTION 
        "Replying MEP/MIP ID - only relevant for loopback on MPLS"
    ::= { vtssMepStatusLbReplyEntry 6 }

vtssMepStatusTst OBJECT IDENTIFIER
    ::= { vtssMepStatus 5 }

vtssMepStatusTstTable OBJECT-TYPE
    SYNTAX      SEQUENCE OF VTSSMepStatusTstEntry
    MAX-ACCESS  not-accessible
    STATUS      current
    DESCRIPTION 
        "This is a table of Test Signal status"
    ::= { vtssMepStatusTst 1 }

vtssMepStatusTstEntry OBJECT-TYPE
    SYNTAX      VTSSMepStatusTstEntry
    MAX-ACCESS  not-accessible
    STATUS      current
    DESCRIPTION 
        "This is a Test Signal status"
    INDEX       { vtssMepStatusTstId }
    ::= { vtssMepStatusTstTable 1 }

VTSSMepStatusTstEntry ::= SEQUENCE {
    vtssMepStatusTstId      Integer32,
    vtssMepStatusTstTxCounter   Counter64,
    vtssMepStatusTstRxCounter   Counter64,
    vtssMepStatusTstOutOfOrderCounter   Counter64,
    vtssMepStatusTstRxRate      Unsigned32,
    vtssMepStatusTstTestTime    Unsigned32
}

vtssMepStatusTstId OBJECT-TYPE
    SYNTAX      Integer32 (0..2147483647)
    MAX-ACCESS  not-accessible
    STATUS      current
    DESCRIPTION 
        "The MEP instance ID"
    ::= { vtssMepStatusTstEntry 1 }

vtssMepStatusTstTxCounter OBJECT-TYPE
    SYNTAX      Counter64
    MAX-ACCESS  read-only
    STATUS      current
    DESCRIPTION 
        "Transmitted TST frames counter."
    ::= { vtssMepStatusTstEntry 2 }

vtssMepStatusTstRxCounter OBJECT-TYPE
    SYNTAX      Counter64
    MAX-ACCESS  read-only
    STATUS      current
    DESCRIPTION 
        "REceived TST frames counter."
    ::= { vtssMepStatusTstEntry 3 }

vtssMepStatusTstOutOfOrderCounter OBJECT-TYPE
    SYNTAX      Counter64
    MAX-ACCESS  read-only
    STATUS      current
    DESCRIPTION 
        "Out of Order counter."
    ::= { vtssMepStatusTstEntry 4 }

vtssMepStatusTstRxRate OBJECT-TYPE
    SYNTAX      Unsigned32
    MAX-ACCESS  read-only
    STATUS      current
    DESCRIPTION 
        "Receive bit rate in Kbit/s."
    ::= { vtssMepStatusTstEntry 5 }

vtssMepStatusTstTestTime OBJECT-TYPE
    SYNTAX      Unsigned32
    MAX-ACCESS  read-only
    STATUS      current
    DESCRIPTION 
        "Test time in seconds. The elapsed time since last clear."
    ::= { vtssMepStatusTstEntry 6 }

vtssMepStatusLt OBJECT IDENTIFIER
    ::= { vtssMepStatus 6 }

vtssMepStatusLtTable OBJECT-TYPE
    SYNTAX      SEQUENCE OF VTSSMepStatusLtEntry
    MAX-ACCESS  not-accessible
    STATUS      current
    DESCRIPTION 
        "This is a table of Link Trace status"
    ::= { vtssMepStatusLt 1 }

vtssMepStatusLtEntry OBJECT-TYPE
    SYNTAX      VTSSMepStatusLtEntry
    MAX-ACCESS  not-accessible
    STATUS      current
    DESCRIPTION 
        "This is a Link Trace status"
    INDEX       { vtssMepStatusLtId }
    ::= { vtssMepStatusLtTable 1 }

VTSSMepStatusLtEntry ::= SEQUENCE {
    vtssMepStatusLtId   Integer32,
    vtssMepStatusLtTransactionId    Unsigned32,
    vtssMepStatusLtReplyCount   Unsigned32
}

vtssMepStatusLtId OBJECT-TYPE
    SYNTAX      Integer32 (0..2147483647)
    MAX-ACCESS  not-accessible
    STATUS      current
    DESCRIPTION 
        "The MEP instance ID"
    ::= { vtssMepStatusLtEntry 1 }

vtssMepStatusLtTransactionId OBJECT-TYPE
    SYNTAX      Unsigned32
    MAX-ACCESS  read-only
    STATUS      current
    DESCRIPTION 
        "The transaction id of the latest Link Trace."
    ::= { vtssMepStatusLtEntry 2 }

vtssMepStatusLtReplyCount OBJECT-TYPE
    SYNTAX      Unsigned32
    MAX-ACCESS  read-only
    STATUS      current
    DESCRIPTION 
        "Number of replies for this Link Trace transaction."
    ::= { vtssMepStatusLtEntry 3 }

vtssMepStatusLtReplyTable OBJECT-TYPE
    SYNTAX      SEQUENCE OF VTSSMepStatusLtReplyEntry
    MAX-ACCESS  not-accessible
    STATUS      current
    DESCRIPTION 
        "This is a table of Link Trace reply status"
    ::= { vtssMepStatusLt 2 }

vtssMepStatusLtReplyEntry OBJECT-TYPE
    SYNTAX      VTSSMepStatusLtReplyEntry
    MAX-ACCESS  not-accessible
    STATUS      current
    DESCRIPTION 
        "This is a Link Trace reply status"
    INDEX       { vtssMepStatusLtReplyId, vtssMepStatusLtReplyReplyId }
    ::= { vtssMepStatusLtReplyTable 1 }

VTSSMepStatusLtReplyEntry ::= SEQUENCE {
    vtssMepStatusLtReplyId      Integer32,
    vtssMepStatusLtReplyReplyId     Integer32,
    vtssMepStatusLtReplyMode    VTSSMepInstanceMode,
    vtssMepStatusLtReplyDirection   VTSSMepInstanceDirection,
    vtssMepStatusLtReplyTtl     VTSSUnsigned8,
    vtssMepStatusLtReplyForwarded   TruthValue,
    vtssMepStatusLtReplyRelayAction     VTSSMepLtRelayAction,
    vtssMepStatusLtReplyLastEgressMac   MacAddress,
    vtssMepStatusLtReplyNextEgressMac   MacAddress
}

vtssMepStatusLtReplyId OBJECT-TYPE
    SYNTAX      Integer32 (0..2147483647)
    MAX-ACCESS  not-accessible
    STATUS      current
    DESCRIPTION 
        "The MEP instance ID"
    ::= { vtssMepStatusLtReplyEntry 1 }

vtssMepStatusLtReplyReplyId OBJECT-TYPE
    SYNTAX      Integer32 (0..2147483647)
    MAX-ACCESS  not-accessible
    STATUS      current
    DESCRIPTION 
        "The LB or LT Reply id"
    ::= { vtssMepStatusLtReplyEntry 2 }

vtssMepStatusLtReplyMode OBJECT-TYPE
    SYNTAX      VTSSMepInstanceMode
    MAX-ACCESS  read-only
    STATUS      current
    DESCRIPTION 
        "The reply is done by a MEP or a MIP."
    ::= { vtssMepStatusLtReplyEntry 3 }

vtssMepStatusLtReplyDirection OBJECT-TYPE
    SYNTAX      VTSSMepInstanceDirection
    MAX-ACCESS  read-only
    STATUS      current
    DESCRIPTION 
        "The reply is done by a UP or a Down instance."
    ::= { vtssMepStatusLtReplyEntry 4 }

vtssMepStatusLtReplyTtl OBJECT-TYPE
    SYNTAX      VTSSUnsigned8
    MAX-ACCESS  read-only
    STATUS      current
    DESCRIPTION 
        "The reply TTL value."
    ::= { vtssMepStatusLtReplyEntry 5 }

vtssMepStatusLtReplyForwarded OBJECT-TYPE
    SYNTAX      TruthValue
    MAX-ACCESS  read-only
    STATUS      current
    DESCRIPTION 
        "The LTM was forwarded."
    ::= { vtssMepStatusLtReplyEntry 6 }

vtssMepStatusLtReplyRelayAction OBJECT-TYPE
    SYNTAX      VTSSMepLtRelayAction
    MAX-ACCESS  read-only
    STATUS      current
    DESCRIPTION 
        "The relay action."
    ::= { vtssMepStatusLtReplyEntry 7 }

vtssMepStatusLtReplyLastEgressMac OBJECT-TYPE
    SYNTAX      MacAddress
    MAX-ACCESS  read-only
    STATUS      current
    DESCRIPTION 
        "The Last Egress MAC for this reply."
    ::= { vtssMepStatusLtReplyEntry 8 }

vtssMepStatusLtReplyNextEgressMac OBJECT-TYPE
    SYNTAX      MacAddress
    MAX-ACCESS  read-only
    STATUS      current
    DESCRIPTION 
        "The Next Egress MAC of this reply."
    ::= { vtssMepStatusLtReplyEntry 9 }

vtssMepStatusCc OBJECT IDENTIFIER
    ::= { vtssMepStatus 7 }

vtssMepStatusCcPeerTable OBJECT-TYPE
    SYNTAX      SEQUENCE OF VTSSMepStatusCcPeerEntry
    MAX-ACCESS  not-accessible
    STATUS      current
    DESCRIPTION 
        "This is a table of peer MEP CC status"
    ::= { vtssMepStatusCc 2 }

vtssMepStatusCcPeerEntry OBJECT-TYPE
    SYNTAX      VTSSMepStatusCcPeerEntry
    MAX-ACCESS  not-accessible
    STATUS      current
    DESCRIPTION 
        "This is a peer MEP CC status"
    INDEX       { vtssMepStatusCcPeerId, vtssMepStatusCcPeerPeerId }
    ::= { vtssMepStatusCcPeerTable 1 }

VTSSMepStatusCcPeerEntry ::= SEQUENCE {
    vtssMepStatusCcPeerId   Integer32,
    vtssMepStatusCcPeerPeerId   Integer32,
    vtssMepStatusCcPeerOsTlvOuiFirst    VTSSUnsigned8,
    vtssMepStatusCcPeerOsTlvOuiSecond   VTSSUnsigned8,
    vtssMepStatusCcPeerOsTlvOuiThird    VTSSUnsigned8,
    vtssMepStatusCcPeerOsTlvSubType     VTSSUnsigned8,
    vtssMepStatusCcPeerOsTlvValue   VTSSUnsigned8,
    vtssMepStatusCcPeerIsTlvValue   VTSSUnsigned8,
    vtssMepStatusCcPeerPsTlvValue   VTSSUnsigned8,
    vtssMepStatusCcPeerOsTlvReceived    TruthValue,
    vtssMepStatusCcPeerIsTlvReceived    TruthValue,
    vtssMepStatusCcPeerPsTlvReceived    TruthValue
}

vtssMepStatusCcPeerId OBJECT-TYPE
    SYNTAX      Integer32 (0..2147483647)
    MAX-ACCESS  not-accessible
    STATUS      current
    DESCRIPTION 
        "The MEP instance ID"
    ::= { vtssMepStatusCcPeerEntry 1 }

vtssMepStatusCcPeerPeerId OBJECT-TYPE
    SYNTAX      Integer32 (0..2147483647)
    MAX-ACCESS  not-accessible
    STATUS      current
    DESCRIPTION 
        "The Peer MEP ID"
    ::= { vtssMepStatusCcPeerEntry 2 }

vtssMepStatusCcPeerOsTlvOuiFirst OBJECT-TYPE
    SYNTAX      VTSSUnsigned8
    MAX-ACCESS  read-only
    STATUS      current
    DESCRIPTION 
        "Last received OS TLV - The OUI content first nibble"
    ::= { vtssMepStatusCcPeerEntry 3 }

vtssMepStatusCcPeerOsTlvOuiSecond OBJECT-TYPE
    SYNTAX      VTSSUnsigned8
    MAX-ACCESS  read-only
    STATUS      current
    DESCRIPTION 
        "Last received OS TLV - The OUI content second nibble"
    ::= { vtssMepStatusCcPeerEntry 4 }

vtssMepStatusCcPeerOsTlvOuiThird OBJECT-TYPE
    SYNTAX      VTSSUnsigned8
    MAX-ACCESS  read-only
    STATUS      current
    DESCRIPTION 
        "Last received OS TLV - The OUI content third nibble"
    ::= { vtssMepStatusCcPeerEntry 5 }

vtssMepStatusCcPeerOsTlvSubType OBJECT-TYPE
    SYNTAX      VTSSUnsigned8
    MAX-ACCESS  read-only
    STATUS      current
    DESCRIPTION 
        "Last received OS TLV - The Sub-Type content"
    ::= { vtssMepStatusCcPeerEntry 6 }

vtssMepStatusCcPeerOsTlvValue OBJECT-TYPE
    SYNTAX      VTSSUnsigned8
    MAX-ACCESS  read-only
    STATUS      current
    DESCRIPTION 
        "Last received OS TLV - The Value content"
    ::= { vtssMepStatusCcPeerEntry 7 }

vtssMepStatusCcPeerIsTlvValue OBJECT-TYPE
    SYNTAX      VTSSUnsigned8
    MAX-ACCESS  read-only
    STATUS      current
    DESCRIPTION 
        "Last received IS TLV - The Value content"
    ::= { vtssMepStatusCcPeerEntry 8 }

vtssMepStatusCcPeerPsTlvValue OBJECT-TYPE
    SYNTAX      VTSSUnsigned8
    MAX-ACCESS  read-only
    STATUS      current
    DESCRIPTION 
        "Last received PS TLV - The Value content"
    ::= { vtssMepStatusCcPeerEntry 9 }

vtssMepStatusCcPeerOsTlvReceived OBJECT-TYPE
    SYNTAX      TruthValue
    MAX-ACCESS  read-only
    STATUS      current
    DESCRIPTION 
        "Last received CCM PDU contained OS TLV"
    ::= { vtssMepStatusCcPeerEntry 10 }

vtssMepStatusCcPeerIsTlvReceived OBJECT-TYPE
    SYNTAX      TruthValue
    MAX-ACCESS  read-only
    STATUS      current
    DESCRIPTION 
        "Last received CCM PDU contained IS TLV"
    ::= { vtssMepStatusCcPeerEntry 11 }

vtssMepStatusCcPeerPsTlvReceived OBJECT-TYPE
    SYNTAX      TruthValue
    MAX-ACCESS  read-only
    STATUS      current
    DESCRIPTION 
        "Last received CCM PDU contained PS TLV"
    ::= { vtssMepStatusCcPeerEntry 12 }

vtssMepStatusBfd OBJECT IDENTIFIER
    ::= { vtssMepStatus 8 }

vtssMepStatusBfdTable OBJECT-TYPE
    SYNTAX      SEQUENCE OF VTSSMepStatusBfdEntry
    MAX-ACCESS  not-accessible
    STATUS      current
    DESCRIPTION 
        "This is a table of MEP BFD status"
    ::= { vtssMepStatusBfd 2 }

vtssMepStatusBfdEntry OBJECT-TYPE
    SYNTAX      VTSSMepStatusBfdEntry
    MAX-ACCESS  not-accessible
    STATUS      current
    DESCRIPTION 
        "This is a MEP BFD status"
    INDEX       { vtssMepStatusBfdId }
    ::= { vtssMepStatusBfdTable 1 }

VTSSMepStatusBfdEntry ::= SEQUENCE {
    vtssMepStatusBfdId      Integer32,
    vtssMepStatusBfdCcTxCnt     VTSSUnsigned64,
    vtssMepStatusBfdValidCcRxCnt    VTSSUnsigned64,
    vtssMepStatusBfdInvalidCcRxCnt      VTSSUnsigned64,
    vtssMepStatusBfdCvTxCnt     VTSSUnsigned64,
    vtssMepStatusBfdValidCvRxCnt    VTSSUnsigned64,
    vtssMepStatusBfdInvalidCvRxCnt      VTSSUnsigned64,
    vtssMepStatusBfdMyDiscr     Unsigned32,
    vtssMepStatusBfdSessionState0   VTSSMepBfdSessionState,
    vtssMepStatusBfdSessionState1   VTSSMepBfdSessionState,
    vtssMepStatusBfdLocalDiag   VTSSMepBfdDiagnosticCode,
    vtssMepStatusBfdRemoteSessionState      VTSSMepBfdSessionState,
    vtssMepStatusBfdRemoteDiag      VTSSMepBfdDiagnosticCode,
    vtssMepStatusBfdRemoteDiscr     Unsigned32,
    vtssMepStatusBfdRemoteMinRx     Unsigned32,
    vtssMepStatusBfdRemoteFlags     VTSSUnsigned8,
    vtssMepStatusBfdUnexpDiscr      Unsigned32,
    vtssMepStatusBfdExpSrcMepIdTlv      OCTET STRING,
    vtssMepStatusBfdUnexpSrcMepIdTlv    OCTET STRING
}

vtssMepStatusBfdId OBJECT-TYPE
    SYNTAX      Integer32 (0..2147483647)
    MAX-ACCESS  not-accessible
    STATUS      current
    DESCRIPTION 
        "The MEP instance ID"
    ::= { vtssMepStatusBfdEntry 1 }

vtssMepStatusBfdCcTxCnt OBJECT-TYPE
    SYNTAX      VTSSUnsigned64
    MAX-ACCESS  read-only
    STATUS      current
    DESCRIPTION 
        "BFD CC transmitted."
    ::= { vtssMepStatusBfdEntry 3 }

vtssMepStatusBfdValidCcRxCnt OBJECT-TYPE
    SYNTAX      VTSSUnsigned64
    MAX-ACCESS  read-only
    STATUS      current
    DESCRIPTION 
        "Valid BFD CC received."
    ::= { vtssMepStatusBfdEntry 4 }

vtssMepStatusBfdInvalidCcRxCnt OBJECT-TYPE
    SYNTAX      VTSSUnsigned64
    MAX-ACCESS  read-only
    STATUS      current
    DESCRIPTION 
        "Invalid BFD CC received."
    ::= { vtssMepStatusBfdEntry 5 }

vtssMepStatusBfdCvTxCnt OBJECT-TYPE
    SYNTAX      VTSSUnsigned64
    MAX-ACCESS  read-only
    STATUS      current
    DESCRIPTION 
        "BFD CV transmitted."
    ::= { vtssMepStatusBfdEntry 6 }

vtssMepStatusBfdValidCvRxCnt OBJECT-TYPE
    SYNTAX      VTSSUnsigned64
    MAX-ACCESS  read-only
    STATUS      current
    DESCRIPTION 
        "Valid BFD CV received."
    ::= { vtssMepStatusBfdEntry 7 }

vtssMepStatusBfdInvalidCvRxCnt OBJECT-TYPE
    SYNTAX      VTSSUnsigned64
    MAX-ACCESS  read-only
    STATUS      current
    DESCRIPTION 
        "Invalid BFD CV received."
    ::= { vtssMepStatusBfdEntry 8 }

vtssMepStatusBfdMyDiscr OBJECT-TYPE
    SYNTAX      Unsigned32
    MAX-ACCESS  read-only
    STATUS      current
    DESCRIPTION 
        "Selected random 'My Discriminator' value, non-zero."
    ::= { vtssMepStatusBfdEntry 9 }

vtssMepStatusBfdSessionState0 OBJECT-TYPE
    SYNTAX      VTSSMepBfdSessionState
    MAX-ACCESS  read-only
    STATUS      current
    DESCRIPTION 
        "Local BFD session state (for coordinated mode only SessionState0 is
         valid, for independent mode SessionState0 is sink, SessionState1 is
         source."
    ::= { vtssMepStatusBfdEntry 10 }

vtssMepStatusBfdSessionState1 OBJECT-TYPE
    SYNTAX      VTSSMepBfdSessionState
    MAX-ACCESS  read-only
    STATUS      current
    DESCRIPTION 
        "Local BFD session state. Only valid in independent mode where
         SessionState0 is sink, SessionState1 is source."
    ::= { vtssMepStatusBfdEntry 11 }

vtssMepStatusBfdLocalDiag OBJECT-TYPE
    SYNTAX      VTSSMepBfdDiagnosticCode
    MAX-ACCESS  read-only
    STATUS      current
    DESCRIPTION 
        "Local diagnostic code."
    ::= { vtssMepStatusBfdEntry 12 }

vtssMepStatusBfdRemoteSessionState OBJECT-TYPE
    SYNTAX      VTSSMepBfdSessionState
    MAX-ACCESS  read-only
    STATUS      current
    DESCRIPTION 
        "BFD session state received from remote end."
    ::= { vtssMepStatusBfdEntry 13 }

vtssMepStatusBfdRemoteDiag OBJECT-TYPE
    SYNTAX      VTSSMepBfdDiagnosticCode
    MAX-ACCESS  read-only
    STATUS      current
    DESCRIPTION 
        "Diagnostic code received from remote end."
    ::= { vtssMepStatusBfdEntry 14 }

vtssMepStatusBfdRemoteDiscr OBJECT-TYPE
    SYNTAX      Unsigned32
    MAX-ACCESS  read-only
    STATUS      current
    DESCRIPTION 
        "Discriminator value received from remote end."
    ::= { vtssMepStatusBfdEntry 15 }

vtssMepStatusBfdRemoteMinRx OBJECT-TYPE
    SYNTAX      Unsigned32
    MAX-ACCESS  read-only
    STATUS      current
    DESCRIPTION 
        "Required Min RX interval value received from remote end."
    ::= { vtssMepStatusBfdEntry 16 }

vtssMepStatusBfdRemoteFlags OBJECT-TYPE
    SYNTAX      VTSSUnsigned8
    MAX-ACCESS  read-only
    STATUS      current
    DESCRIPTION 
        "Flags received from remote end."
    ::= { vtssMepStatusBfdEntry 17 }

vtssMepStatusBfdUnexpDiscr OBJECT-TYPE
    SYNTAX      Unsigned32
    MAX-ACCESS  read-only
    STATUS      current
    DESCRIPTION 
        "Last received unexpected discriminator value (should be my configured)."
    ::= { vtssMepStatusBfdEntry 18 }

vtssMepStatusBfdExpSrcMepIdTlv OBJECT-TYPE
    SYNTAX      OCTET STRING (SIZE(28))
    MAX-ACCESS  read-only
    STATUS      current
    DESCRIPTION 
        "Expected source MEP ID TLV."
    ::= { vtssMepStatusBfdEntry 19 }

vtssMepStatusBfdUnexpSrcMepIdTlv OBJECT-TYPE
    SYNTAX      OCTET STRING (SIZE(28))
    MAX-ACCESS  read-only
    STATUS      current
    DESCRIPTION 
        "Last received unexpected source MEP ID TLV."
    ::= { vtssMepStatusBfdEntry 20 }

vtssMepStatusRt OBJECT IDENTIFIER
    ::= { vtssMepStatus 9 }

vtssMepStatusRtTable OBJECT-TYPE
    SYNTAX      SEQUENCE OF VTSSMepStatusRtEntry
    MAX-ACCESS  not-accessible
    STATUS      current
    DESCRIPTION 
        "This is a table of Route Trace status"
    ::= { vtssMepStatusRt 1 }

vtssMepStatusRtEntry OBJECT-TYPE
    SYNTAX      VTSSMepStatusRtEntry
    MAX-ACCESS  not-accessible
    STATUS      current
    DESCRIPTION 
        "This is a Route Trace status"
    INDEX       { vtssMepStatusRtId }
    ::= { vtssMepStatusRtTable 1 }

VTSSMepStatusRtEntry ::= SEQUENCE {
    vtssMepStatusRtId   Integer32,
    vtssMepStatusRtSeqNo    Unsigned32,
    vtssMepStatusRtRequestCount     Unsigned32,
    vtssMepStatusRtReplyCount   Unsigned32
}

vtssMepStatusRtId OBJECT-TYPE
    SYNTAX      Integer32 (0..2147483647)
    MAX-ACCESS  not-accessible
    STATUS      current
    DESCRIPTION 
        "The MEP instance ID"
    ::= { vtssMepStatusRtEntry 1 }

vtssMepStatusRtSeqNo OBJECT-TYPE
    SYNTAX      Unsigned32
    MAX-ACCESS  read-only
    STATUS      current
    DESCRIPTION 
        "Sequence number of first RT request."
    ::= { vtssMepStatusRtEntry 2 }

vtssMepStatusRtRequestCount OBJECT-TYPE
    SYNTAX      Unsigned32
    MAX-ACCESS  read-only
    STATUS      current
    DESCRIPTION 
        "Number of RT requests sent for current session."
    ::= { vtssMepStatusRtEntry 3 }

vtssMepStatusRtReplyCount OBJECT-TYPE
    SYNTAX      Unsigned32
    MAX-ACCESS  read-only
    STATUS      current
    DESCRIPTION 
        "Number of replies received for this Route Trace session."
    ::= { vtssMepStatusRtEntry 4 }

vtssMepStatusRtReplyTable OBJECT-TYPE
    SYNTAX      SEQUENCE OF VTSSMepStatusRtReplyEntry
    MAX-ACCESS  not-accessible
    STATUS      current
    DESCRIPTION 
        "This is a table of Route Trace reply status"
    ::= { vtssMepStatusRt 2 }

vtssMepStatusRtReplyEntry OBJECT-TYPE
    SYNTAX      VTSSMepStatusRtReplyEntry
    MAX-ACCESS  not-accessible
    STATUS      current
    DESCRIPTION 
        "This is a Route Trace reply status"
    INDEX       { vtssMepStatusRtReplyId, vtssMepStatusRtReplySeqNo }
    ::= { vtssMepStatusRtReplyTable 1 }

VTSSMepStatusRtReplyEntry ::= SEQUENCE {
    vtssMepStatusRtReplyId      Integer32,
    vtssMepStatusRtReplySeqNo   Unsigned32,
    vtssMepStatusRtReplyReturnCode      VTSSMepRtReturnCode,
    vtssMepStatusRtReplyReturnSubcode   VTSSUnsigned8,
    vtssMepStatusRtReplyRttSec      Unsigned32,
    vtssMepStatusRtReplyRttUsec     Unsigned32,
    vtssMepStatusRtReplyTsSentSec   Unsigned32,
    vtssMepStatusRtReplyTsSentUsec      Unsigned32,
    vtssMepStatusRtReplyTsReceivedSec   Unsigned32,
    vtssMepStatusRtReplyTsReceivedUsec      Unsigned32,
    vtssMepStatusRtReplySrcGlobalId     Unsigned32,
    vtssMepStatusRtReplySrcNodeId   IpAddress,
    vtssMepStatusRtReplyFecSrcValue     Unsigned32,
    vtssMepStatusRtReplyRxIfNum     Unsigned32,
    vtssMepStatusRtReplyRxLabelCnt      Unsigned32,
    vtssMepStatusRtReplyRxLabel1    Unsigned32,
    vtssMepStatusRtReplyRxLabel2    Unsigned32,
    vtssMepStatusRtReplyRxLabel3    Unsigned32,
    vtssMepStatusRtReplyRxLabel4    Unsigned32,
    vtssMepStatusRtReplyRxLabel5    Unsigned32,
    vtssMepStatusRtReplyRxLabel6    Unsigned32,
    vtssMepStatusRtReplyRxLabel7    Unsigned32,
    vtssMepStatusRtReplyRxLabel8    Unsigned32
}

vtssMepStatusRtReplyId OBJECT-TYPE
    SYNTAX      Integer32 (0..2147483647)
    MAX-ACCESS  not-accessible
    STATUS      current
    DESCRIPTION 
        "The MEP instance ID"
    ::= { vtssMepStatusRtReplyEntry 1 }

vtssMepStatusRtReplySeqNo OBJECT-TYPE
    SYNTAX      Unsigned32 (0..4294967295)
    MAX-ACCESS  not-accessible
    STATUS      current
    DESCRIPTION 
        "The RT sequence number"
    ::= { vtssMepStatusRtReplyEntry 2 }

vtssMepStatusRtReplyReturnCode OBJECT-TYPE
    SYNTAX      VTSSMepRtReturnCode
    MAX-ACCESS  read-only
    STATUS      current
    DESCRIPTION 
        "Return code from reply."
    ::= { vtssMepStatusRtReplyEntry 3 }

vtssMepStatusRtReplyReturnSubcode OBJECT-TYPE
    SYNTAX      VTSSUnsigned8
    MAX-ACCESS  read-only
    STATUS      current
    DESCRIPTION 
        "Return subcode from reply."
    ::= { vtssMepStatusRtReplyEntry 4 }

vtssMepStatusRtReplyRttSec OBJECT-TYPE
    SYNTAX      Unsigned32
    MAX-ACCESS  read-only
    STATUS      current
    DESCRIPTION 
        "Round Trip Time (seconds)."
    ::= { vtssMepStatusRtReplyEntry 5 }

vtssMepStatusRtReplyRttUsec OBJECT-TYPE
    SYNTAX      Unsigned32
    MAX-ACCESS  read-only
    STATUS      current
    DESCRIPTION 
        "Round Trip Time (microseconds)."
    ::= { vtssMepStatusRtReplyEntry 6 }

vtssMepStatusRtReplyTsSentSec OBJECT-TYPE
    SYNTAX      Unsigned32
    MAX-ACCESS  read-only
    STATUS      current
    DESCRIPTION 
        "Timestamp sent (sender, seconds)."
    ::= { vtssMepStatusRtReplyEntry 7 }

vtssMepStatusRtReplyTsSentUsec OBJECT-TYPE
    SYNTAX      Unsigned32
    MAX-ACCESS  read-only
    STATUS      current
    DESCRIPTION 
        "Timestamp sent (sender, microseconds)."
    ::= { vtssMepStatusRtReplyEntry 8 }

vtssMepStatusRtReplyTsReceivedSec OBJECT-TYPE
    SYNTAX      Unsigned32
    MAX-ACCESS  read-only
    STATUS      current
    DESCRIPTION 
        "Timestamp received (receiver, seconds)."
    ::= { vtssMepStatusRtReplyEntry 9 }

vtssMepStatusRtReplyTsReceivedUsec OBJECT-TYPE
    SYNTAX      Unsigned32
    MAX-ACCESS  read-only
    STATUS      current
    DESCRIPTION 
        "Timestamp received (receiver, microseconds)."
    ::= { vtssMepStatusRtReplyEntry 10 }

vtssMepStatusRtReplySrcGlobalId OBJECT-TYPE
    SYNTAX      Unsigned32
    MAX-ACCESS  read-only
    STATUS      current
    DESCRIPTION 
        "Source global ID from received FEC or source ID TLV in RT reply."
    ::= { vtssMepStatusRtReplyEntry 11 }

vtssMepStatusRtReplySrcNodeId OBJECT-TYPE
    SYNTAX      IpAddress
    MAX-ACCESS  read-only
    STATUS      current
    DESCRIPTION 
        "Source node ID from received FEC or source ID TLV in RT reply."
    ::= { vtssMepStatusRtReplyEntry 12 }

vtssMepStatusRtReplyFecSrcValue OBJECT-TYPE
    SYNTAX      Unsigned32
    MAX-ACCESS  read-only
    STATUS      current
    DESCRIPTION 
        "For a reply from a PW MEP this is the source AC-ID from the received
         FEC in the RT reply. For a Tunnel MEP or LSP MIP bit 31:16 is the
         source tunnel number and bit 15:0 is the LSP number from the received
         FEC in the RT reply."
    ::= { vtssMepStatusRtReplyEntry 13 }

vtssMepStatusRtReplyRxIfNum OBJECT-TYPE
    SYNTAX      Unsigned32
    MAX-ACCESS  read-only
    STATUS      current
    DESCRIPTION 
        "Receiver local interface index from reply."
    ::= { vtssMepStatusRtReplyEntry 14 }

vtssMepStatusRtReplyRxLabelCnt OBJECT-TYPE
    SYNTAX      Unsigned32
    MAX-ACCESS  read-only
    STATUS      current
    DESCRIPTION 
        "Number of valid label values RxLabel1, RxLabel2 etc."
    ::= { vtssMepStatusRtReplyEntry 15 }

vtssMepStatusRtReplyRxLabel1 OBJECT-TYPE
    SYNTAX      Unsigned32
    MAX-ACCESS  read-only
    STATUS      current
    DESCRIPTION 
        "1st MPLS label (top label) of Label Stack of RT request as seen by
         receiver."
    ::= { vtssMepStatusRtReplyEntry 16 }

vtssMepStatusRtReplyRxLabel2 OBJECT-TYPE
    SYNTAX      Unsigned32
    MAX-ACCESS  read-only
    STATUS      current
    DESCRIPTION 
        "2nd MPLS label of Label Stack of RT request as seen by receiver."
    ::= { vtssMepStatusRtReplyEntry 17 }

vtssMepStatusRtReplyRxLabel3 OBJECT-TYPE
    SYNTAX      Unsigned32
    MAX-ACCESS  read-only
    STATUS      current
    DESCRIPTION 
        "3rd MPLS label of Label Stack of RT request as seen by receiver."
    ::= { vtssMepStatusRtReplyEntry 18 }

vtssMepStatusRtReplyRxLabel4 OBJECT-TYPE
    SYNTAX      Unsigned32
    MAX-ACCESS  read-only
    STATUS      current
    DESCRIPTION 
        "4th MPLS label of Label Stack of RT request as seen by receiver."
    ::= { vtssMepStatusRtReplyEntry 19 }

vtssMepStatusRtReplyRxLabel5 OBJECT-TYPE
    SYNTAX      Unsigned32
    MAX-ACCESS  read-only
    STATUS      current
    DESCRIPTION 
        "5th MPLS label of Label Stack of RT request as seen by receiver."
    ::= { vtssMepStatusRtReplyEntry 20 }

vtssMepStatusRtReplyRxLabel6 OBJECT-TYPE
    SYNTAX      Unsigned32
    MAX-ACCESS  read-only
    STATUS      current
    DESCRIPTION 
        "6th MPLS label of Label Stack of RT request as seen by receiver."
    ::= { vtssMepStatusRtReplyEntry 21 }

vtssMepStatusRtReplyRxLabel7 OBJECT-TYPE
    SYNTAX      Unsigned32
    MAX-ACCESS  read-only
    STATUS      current
    DESCRIPTION 
        "7th MPLS label of Label Stack of RT request as seen by receiver."
    ::= { vtssMepStatusRtReplyEntry 22 }

vtssMepStatusRtReplyRxLabel8 OBJECT-TYPE
    SYNTAX      Unsigned32
    MAX-ACCESS  read-only
    STATUS      current
    DESCRIPTION 
        "8th MPLS label of Label Stack of RT request as seen by receiver."
    ::= { vtssMepStatusRtReplyEntry 23 }

vtssMepStatusLmAvail OBJECT IDENTIFIER
    ::= { vtssMepStatus 10 }

vtssMepStatusLmAvailTable OBJECT-TYPE
    SYNTAX      SEQUENCE OF VTSSMepStatusLmAvailEntry
    MAX-ACCESS  not-accessible
    STATUS      current
    DESCRIPTION 
        "This is a table of Loss Measurement Availability status"
    ::= { vtssMepStatusLmAvail 1 }

vtssMepStatusLmAvailEntry OBJECT-TYPE
    SYNTAX      VTSSMepStatusLmAvailEntry
    MAX-ACCESS  not-accessible
    STATUS      current
    DESCRIPTION 
        "This is a Loss Measurement Availability status"
    INDEX       { vtssMepStatusLmAvailId }
    ::= { vtssMepStatusLmAvailTable 1 }

VTSSMepStatusLmAvailEntry ::= SEQUENCE {
    vtssMepStatusLmAvailId      Integer32,
    vtssMepStatusLmAvailNearEndAvailState   VTSSMepLmAvailState,
    vtssMepStatusLmAvailFarEndAvailState    VTSSMepLmAvailState,
    vtssMepStatusLmAvailNearEndAvailCnt     Unsigned32,
    vtssMepStatusLmAvailFarEndAvailCnt      Unsigned32,
    vtssMepStatusLmAvailNearEndUnAvailCnt   Unsigned32,
    vtssMepStatusLmAvailFarEndUnAvailCnt    Unsigned32
}

vtssMepStatusLmAvailId OBJECT-TYPE
    SYNTAX      Integer32 (0..2147483647)
    MAX-ACCESS  not-accessible
    STATUS      current
    DESCRIPTION 
        "The MEP instance ID"
    ::= { vtssMepStatusLmAvailEntry 1 }

vtssMepStatusLmAvailNearEndAvailState OBJECT-TYPE
    SYNTAX      VTSSMepLmAvailState
    MAX-ACCESS  read-only
    STATUS      current
    DESCRIPTION 
        "Near end Availability State."
    ::= { vtssMepStatusLmAvailEntry 2 }

vtssMepStatusLmAvailFarEndAvailState OBJECT-TYPE
    SYNTAX      VTSSMepLmAvailState
    MAX-ACCESS  read-only
    STATUS      current
    DESCRIPTION 
        "Far end Availability State."
    ::= { vtssMepStatusLmAvailEntry 3 }

vtssMepStatusLmAvailNearEndAvailCnt OBJECT-TYPE
    SYNTAX      Unsigned32
    MAX-ACCESS  read-only
    STATUS      current
    DESCRIPTION 
        "Near end Availability Count."
    ::= { vtssMepStatusLmAvailEntry 4 }

vtssMepStatusLmAvailFarEndAvailCnt OBJECT-TYPE
    SYNTAX      Unsigned32
    MAX-ACCESS  read-only
    STATUS      current
    DESCRIPTION 
        "Far end Availability Count."
    ::= { vtssMepStatusLmAvailEntry 5 }

vtssMepStatusLmAvailNearEndUnAvailCnt OBJECT-TYPE
    SYNTAX      Unsigned32
    MAX-ACCESS  read-only
    STATUS      current
    DESCRIPTION 
        "Near end Unavailability Count."
    ::= { vtssMepStatusLmAvailEntry 6 }

vtssMepStatusLmAvailFarEndUnAvailCnt OBJECT-TYPE
    SYNTAX      Unsigned32
    MAX-ACCESS  read-only
    STATUS      current
    DESCRIPTION 
        "Far end Unavailability Count."
    ::= { vtssMepStatusLmAvailEntry 7 }

vtssMepStatusLmHli OBJECT IDENTIFIER
    ::= { vtssMepStatus 11 }

vtssMepStatusLmHliTable OBJECT-TYPE
    SYNTAX      SEQUENCE OF VTSSMepStatusLmHliEntry
    MAX-ACCESS  not-accessible
    STATUS      current
    DESCRIPTION 
        "This is a table of Loss Measurement High Loss Interval status"
    ::= { vtssMepStatusLmHli 1 }

vtssMepStatusLmHliEntry OBJECT-TYPE
    SYNTAX      VTSSMepStatusLmHliEntry
    MAX-ACCESS  not-accessible
    STATUS      current
    DESCRIPTION 
        "This is a Loss Measurement High Loss Interval status"
    INDEX       { vtssMepStatusLmHliId }
    ::= { vtssMepStatusLmHliTable 1 }

VTSSMepStatusLmHliEntry ::= SEQUENCE {
    vtssMepStatusLmHliId    Integer32,
    vtssMepStatusLmHliNearEndCnt    Unsigned32,
    vtssMepStatusLmHliFarEndCnt     Unsigned32,
    vtssMepStatusLmHliNearEndConCnt     Unsigned32,
    vtssMepStatusLmHliFarEndConCnt      Unsigned32
}

vtssMepStatusLmHliId OBJECT-TYPE
    SYNTAX      Integer32 (0..2147483647)
    MAX-ACCESS  not-accessible
    STATUS      current
    DESCRIPTION 
        "The MEP instance ID"
    ::= { vtssMepStatusLmHliEntry 1 }

vtssMepStatusLmHliNearEndCnt OBJECT-TYPE
    SYNTAX      Unsigned32
    MAX-ACCESS  read-only
    STATUS      current
    DESCRIPTION 
        "Near end High Loss Interval count (number of measurements where
         Availability State is available and FLR is above HLI FLR threshold."
    ::= { vtssMepStatusLmHliEntry 2 }

vtssMepStatusLmHliFarEndCnt OBJECT-TYPE
    SYNTAX      Unsigned32
    MAX-ACCESS  read-only
    STATUS      current
    DESCRIPTION 
        "Far end High Loss Interval count (number of measurements where
         Availability State is available and FLR is above HLI FLR threshold."
    ::= { vtssMepStatusLmHliEntry 3 }

vtssMepStatusLmHliNearEndConCnt OBJECT-TYPE
    SYNTAX      Unsigned32
    MAX-ACCESS  read-only
    STATUS      current
    DESCRIPTION 
        "Near end High Loss Interval consecutive count."
    ::= { vtssMepStatusLmHliEntry 4 }

vtssMepStatusLmHliFarEndConCnt OBJECT-TYPE
    SYNTAX      Unsigned32
    MAX-ACCESS  read-only
    STATUS      current
    DESCRIPTION 
        "Far end High Loss Interval consecutive count."
    ::= { vtssMepStatusLmHliEntry 5 }

vtssMepControl OBJECT IDENTIFIER
    ::= { vtssMepMibObjects 4 }

vtssMepControlLm OBJECT IDENTIFIER
    ::= { vtssMepControl 1 }

vtssMepControlLmTable OBJECT-TYPE
    SYNTAX      SEQUENCE OF VTSSMepControlLmEntry
    MAX-ACCESS  not-accessible
    STATUS      current
    DESCRIPTION 
        "This is a table of created instance Loss Measurement control parameters"
    ::= { vtssMepControlLm 1 }

vtssMepControlLmEntry OBJECT-TYPE
    SYNTAX      VTSSMepControlLmEntry
    MAX-ACCESS  not-accessible
    STATUS      current
    DESCRIPTION 
        "This is a created instance Loss Measurement control parameters"
    INDEX       { vtssMepControlLmId }
    ::= { vtssMepControlLmTable 1 }

VTSSMepControlLmEntry ::= SEQUENCE {
    vtssMepControlLmId      Integer32,
    vtssMepControlLmClear   TruthValue
}

vtssMepControlLmId OBJECT-TYPE
    SYNTAX      Integer32 (0..2147483647)
    MAX-ACCESS  not-accessible
    STATUS      current
    DESCRIPTION 
        "The MEP instance ID"
    ::= { vtssMepControlLmEntry 1 }

vtssMepControlLmClear OBJECT-TYPE
    SYNTAX      TruthValue
    MAX-ACCESS  read-write
    STATUS      current
    DESCRIPTION 
        "Clear the LM results"
    ::= { vtssMepControlLmEntry 2 }

vtssMepControlDm OBJECT IDENTIFIER
    ::= { vtssMepControl 2 }

vtssMepControlDmTable OBJECT-TYPE
    SYNTAX      SEQUENCE OF VTSSMepControlDmEntry
    MAX-ACCESS  not-accessible
    STATUS      current
    DESCRIPTION 
        "This is a table of created instance Delay Measurement control
         parameters"
    ::= { vtssMepControlDm 1 }

vtssMepControlDmEntry OBJECT-TYPE
    SYNTAX      VTSSMepControlDmEntry
    MAX-ACCESS  not-accessible
    STATUS      current
    DESCRIPTION 
        "This is a created instance Delay Measurement control parameters"
    INDEX       { vtssMepControlDmId }
    ::= { vtssMepControlDmTable 1 }

VTSSMepControlDmEntry ::= SEQUENCE {
    vtssMepControlDmId      Integer32,
    vtssMepControlDmClear   TruthValue
}

vtssMepControlDmId OBJECT-TYPE
    SYNTAX      Integer32 (0..2147483647)
    MAX-ACCESS  not-accessible
    STATUS      current
    DESCRIPTION 
        "The MEP instance ID"
    ::= { vtssMepControlDmEntry 1 }

vtssMepControlDmClear OBJECT-TYPE
    SYNTAX      TruthValue
    MAX-ACCESS  read-write
    STATUS      current
    DESCRIPTION 
        "Clear the DM results"
    ::= { vtssMepControlDmEntry 2 }

vtssMepControlTst OBJECT IDENTIFIER
    ::= { vtssMepControl 3 }

vtssMepControlTstTable OBJECT-TYPE
    SYNTAX      SEQUENCE OF VTSSMepControlTstEntry
    MAX-ACCESS  not-accessible
    STATUS      current
    DESCRIPTION 
        "This is a table of created instance Test Signal control parameters"
    ::= { vtssMepControlTst 1 }

vtssMepControlTstEntry OBJECT-TYPE
    SYNTAX      VTSSMepControlTstEntry
    MAX-ACCESS  not-accessible
    STATUS      current
    DESCRIPTION 
        "This is a created instance Test Signal control parameters"
    INDEX       { vtssMepControlTstId }
    ::= { vtssMepControlTstTable 1 }

VTSSMepControlTstEntry ::= SEQUENCE {
    vtssMepControlTstId     Integer32,
    vtssMepControlTstClear      TruthValue
}

vtssMepControlTstId OBJECT-TYPE
    SYNTAX      Integer32 (0..2147483647)
    MAX-ACCESS  not-accessible
    STATUS      current
    DESCRIPTION 
        "The MEP instance ID"
    ::= { vtssMepControlTstEntry 1 }

vtssMepControlTstClear OBJECT-TYPE
    SYNTAX      TruthValue
    MAX-ACCESS  read-write
    STATUS      current
    DESCRIPTION 
        "Clear the TST results"
    ::= { vtssMepControlTstEntry 2 }

vtssMepControlBfd OBJECT IDENTIFIER
    ::= { vtssMepControl 4 }

vtssMepControlBfdTable OBJECT-TYPE
    SYNTAX      SEQUENCE OF VTSSMepControlBfdEntry
    MAX-ACCESS  not-accessible
    STATUS      current
    DESCRIPTION 
        "This is a table of created instance BFD control parameters"
    ::= { vtssMepControlBfd 1 }

vtssMepControlBfdEntry OBJECT-TYPE
    SYNTAX      VTSSMepControlBfdEntry
    MAX-ACCESS  not-accessible
    STATUS      current
    DESCRIPTION 
        "This is a created instance BFD control parameters"
    INDEX       { vtssMepControlBfdId }
    ::= { vtssMepControlBfdTable 1 }

VTSSMepControlBfdEntry ::= SEQUENCE {
    vtssMepControlBfdId     Integer32,
    vtssMepControlBfdClear      TruthValue
}

vtssMepControlBfdId OBJECT-TYPE
    SYNTAX      Integer32 (0..2147483647)
    MAX-ACCESS  not-accessible
    STATUS      current
    DESCRIPTION 
        "The MEP instance ID"
    ::= { vtssMepControlBfdEntry 1 }

vtssMepControlBfdClear OBJECT-TYPE
    SYNTAX      TruthValue
    MAX-ACCESS  read-write
    STATUS      current
    DESCRIPTION 
        "Clear the BFD statistics counters"
    ::= { vtssMepControlBfdEntry 2 }

vtssMepMibConformance OBJECT IDENTIFIER
    ::= { vtssMepMib 2 }

vtssMepMibCompliances OBJECT IDENTIFIER
    ::= { vtssMepMibConformance 1 }

vtssMepMibGroups OBJECT IDENTIFIER
    ::= { vtssMepMibConformance 2 }

vtssMepCapabilitiesInfoGroup OBJECT-GROUP
    OBJECTS     { vtssMepCapabilitiesInstanceMax, vtssMepCapabilitiesPeerMax, 
                  vtssMepCapabilitiesTransactionMax, vtssMepCapabilitiesReplyMax, 
                  vtssMepCapabilitiesClientFlowsMax, 
                  vtssMepCapabilitiesMacMength, vtssMepCapabilitiesMegCodeLength, 
                  vtssMepCapabilitiesDmIntervalMin, 
                  vtssMepCapabilitiesDmIntervalMax, 
                  vtssMepCapabilitiesDmLastnMin, vtssMepCapabilitiesDmLastnMax, 
                  vtssMepCapabilitiesLbmSizeMax, vtssMepCapabilitiesLbmSizeMin, 
                  vtssMepCapabilitiesTstSizeMax, vtssMepCapabilitiesTstSizeMin, 
                  vtssMepCapabilitiesTstRateMax, 
                  vtssMepCapabilitiesClientPrioHighest, 
                  vtssMepCapabilitiesItuG8113dot2, vtssMepCapabilitiesVoeSupport, 
                  vtssMepCapabilitiesLbToSendInfinite, 
                  vtssMepCapabilitiesBfdAuthKeyMax }
    STATUS      current
    DESCRIPTION
        "A collection of objects suitable for bulk operations."
    ::= { vtssMepMibGroups 1 }

vtssMepConfigInstanceTableInfoGroup OBJECT-GROUP
    OBJECTS     { vtssMepConfigInstanceMode, vtssMepConfigInstanceDirection, 
                  vtssMepConfigInstanceFlow, vtssMepConfigInstancePort, 
                  vtssMepConfigInstanceLevel, vtssMepConfigInstanceVid, 
                  vtssMepConfigInstanceVoe, vtssMepConfigInstanceMac, 
                  vtssMepConfigInstanceFormat, vtssMepConfigInstanceName, 
                  vtssMepConfigInstanceMeg, vtssMepConfigInstanceMep, 
                  vtssMepConfigInstanceEvcPag, vtssMepConfigInstanceEvcQos, 
                  vtssMepConfigInstanceAction }
    STATUS      current
    DESCRIPTION
        "A collection of objects suitable for bulk operations."
    ::= { vtssMepMibGroups 2 }

vtssMepConfigInstanceRowEditorInfoGroup OBJECT-GROUP
    OBJECTS     { vtssMepConfigInstanceRowEditorId, 
                  vtssMepConfigInstanceRowEditorMode, 
                  vtssMepConfigInstanceRowEditorDirection, 
                  vtssMepConfigInstanceRowEditorFlow, 
                  vtssMepConfigInstanceRowEditorPort, 
                  vtssMepConfigInstanceRowEditorLevel, 
                  vtssMepConfigInstanceRowEditorVid, 
                  vtssMepConfigInstanceRowEditorVoe, 
                  vtssMepConfigInstanceRowEditorMac, 
                  vtssMepConfigInstanceRowEditorFormat, 
                  vtssMepConfigInstanceRowEditorName, 
                  vtssMepConfigInstanceRowEditorMeg, 
                  vtssMepConfigInstanceRowEditorMep, 
                  vtssMepConfigInstanceRowEditorEvcPag, 
                  vtssMepConfigInstanceRowEditorEvcQos, 
                  vtssMepConfigInstanceRowEditorAction }
    STATUS      current
    DESCRIPTION
        "A collection of objects suitable for bulk operations."
    ::= { vtssMepMibGroups 3 }

vtssMepConfigInstancePeerTableInfoGroup OBJECT-GROUP
    OBJECTS     { vtssMepConfigInstancePeerMac, vtssMepConfigInstancePeerAction }
    STATUS      current
    DESCRIPTION
        "A collection of objects suitable for bulk operations."
    ::= { vtssMepMibGroups 4 }

vtssMepConfigInstancePeerRowEditorInfoGroup OBJECT-GROUP
    OBJECTS     { vtssMepConfigInstancePeerRowEditorId, 
                  vtssMepConfigInstancePeerRowEditorPeerId, 
                  vtssMepConfigInstancePeerRowEditorMac, 
                  vtssMepConfigInstancePeerRowEditorAction }
    STATUS      current
    DESCRIPTION
        "A collection of objects suitable for bulk operations."
    ::= { vtssMepMibGroups 5 }

vtssMepConfigPmTableInfoGroup OBJECT-GROUP
    OBJECTS     { vtssMepConfigPmEnable }
    STATUS      current
    DESCRIPTION
        "A collection of objects suitable for bulk operations."
    ::= { vtssMepMibGroups 6 }

vtssMepConfigCcTableInfoGroup OBJECT-GROUP
    OBJECTS     { vtssMepConfigCcPrio, vtssMepConfigCcRate, vtssMepConfigCcTlv, 
                  vtssMepConfigCcAction }
    STATUS      current
    DESCRIPTION
        "A collection of objects suitable for bulk operations."
    ::= { vtssMepMibGroups 7 }

vtssMepConfigCcRowEditorInfoGroup OBJECT-GROUP
    OBJECTS     { vtssMepConfigCcRowEditorId, vtssMepConfigCcRowEditorPrio, 
                  vtssMepConfigCcRowEditorRate, vtssMepConfigCcRowEditorTlv, 
                  vtssMepConfigCcRowEditorAction }
    STATUS      current
    DESCRIPTION
        "A collection of objects suitable for bulk operations."
    ::= { vtssMepMibGroups 8 }

vtssMepConfigLmTableInfoGroup OBJECT-GROUP
    OBJECTS     { vtssMepConfigLmEnable, vtssMepConfigLmEnded, vtssMepConfigLmPrio, 
                  vtssMepConfigLmRate, vtssMepConfigLmCast, 
                  vtssMepConfigLmFlrInterval, vtssMepConfigLmFlowCount, 
                  vtssMepConfigLmOamCount, vtssMepConfigLmLossTh, 
                  vtssMepConfigLmLossCounterIntHolddownTimer, 
                  vtssMepConfigLmLossThCntHolddownTimer }
    STATUS      current
    DESCRIPTION
        "A collection of objects suitable for bulk operations."
    ::= { vtssMepMibGroups 9 }

vtssMepConfigDmTableInfoGroup OBJECT-GROUP
    OBJECTS     { vtssMepConfigDmEnable, vtssMepConfigDmEnded, vtssMepConfigDmPrio, 
                  vtssMepConfigDmCast, vtssMepConfigDmMep, vtssMepConfigDmCalcWay, 
                  vtssMepConfigDmInterval, vtssMepConfigDmLastN, 
                  vtssMepConfigDmTimeUnit, vtssMepConfigDmOverflowAct, 
                  vtssMepConfigDmSynchronized }
    STATUS      current
    DESCRIPTION
        "A collection of objects suitable for bulk operations."
    ::= { vtssMepMibGroups 10 }

vtssMepConfigLbTableInfoGroup OBJECT-GROUP
    OBJECTS     { vtssMepConfigLbDei, vtssMepConfigLbPrio, vtssMepConfigLbCast, 
                  vtssMepConfigLbMep, vtssMepConfigLbMac, vtssMepConfigLbToSend, 
                  vtssMepConfigLbSize, vtssMepConfigLbInterval, 
                  vtssMepConfigLbTimeToLive, vtssMepConfigLbAction }
    STATUS      current
    DESCRIPTION
        "A collection of objects suitable for bulk operations."
    ::= { vtssMepMibGroups 11 }

vtssMepConfigLbRowEditorInfoGroup OBJECT-GROUP
    OBJECTS     { vtssMepConfigLbRowEditorId, vtssMepConfigLbRowEditorDei, 
                  vtssMepConfigLbRowEditorPrio, vtssMepConfigLbRowEditorCast, 
                  vtssMepConfigLbRowEditorMep, vtssMepConfigLbRowEditorMac, 
                  vtssMepConfigLbRowEditorToSend, vtssMepConfigLbRowEditorSize, 
                  vtssMepConfigLbRowEditorInterval, 
                  vtssMepConfigLbRowEditorTimeToLive, 
                  vtssMepConfigLbRowEditorAction }
    STATUS      current
    DESCRIPTION
        "A collection of objects suitable for bulk operations."
    ::= { vtssMepMibGroups 12 }

vtssMepConfigTstTableInfoGroup OBJECT-GROUP
    OBJECTS     { vtssMepConfigTstTxEnable, vtssMepConfigTstRxEnable, 
                  vtssMepConfigTstDei, vtssMepConfigTstPrio, vtssMepConfigTstMep, 
                  vtssMepConfigTstRate, vtssMepConfigTstSize, 
                  vtssMepConfigTstPattern, vtssMepConfigTstSequence, 
                  vtssMepConfigTstAction }
    STATUS      current
    DESCRIPTION
        "A collection of objects suitable for bulk operations."
    ::= { vtssMepMibGroups 13 }

vtssMepConfigTstRowEditorInfoGroup OBJECT-GROUP
    OBJECTS     { vtssMepConfigTstRowEditorId, vtssMepConfigTstRowEditorTxEnable, 
                  vtssMepConfigTstRowEditorRxEnable, 
                  vtssMepConfigTstRowEditorDei, vtssMepConfigTstRowEditorPrio, 
                  vtssMepConfigTstRowEditorMep, vtssMepConfigTstRowEditorRate, 
                  vtssMepConfigTstRowEditorSize, 
                  vtssMepConfigTstRowEditorPattern, 
                  vtssMepConfigTstRowEditorSequence, 
                  vtssMepConfigTstRowEditorAction }
    STATUS      current
    DESCRIPTION
        "A collection of objects suitable for bulk operations."
    ::= { vtssMepMibGroups 14 }

vtssMepConfigLtTableInfoGroup OBJECT-GROUP
    OBJECTS     { vtssMepConfigLtPrio, vtssMepConfigLtMep, vtssMepConfigLtMac, 
                  vtssMepConfigLtTimeToLive, vtssMepConfigLtAction }
    STATUS      current
    DESCRIPTION
        "A collection of objects suitable for bulk operations."
    ::= { vtssMepMibGroups 15 }

vtssMepConfigLtRowEditorInfoGroup OBJECT-GROUP
    OBJECTS     { vtssMepConfigLtRowEditorId, vtssMepConfigLtRowEditorPrio, 
                  vtssMepConfigLtRowEditorMep, vtssMepConfigLtRowEditorMac, 
                  vtssMepConfigLtRowEditorTimeToLive, 
                  vtssMepConfigLtRowEditorAction }
    STATUS      current
    DESCRIPTION
        "A collection of objects suitable for bulk operations."
    ::= { vtssMepMibGroups 16 }

vtssMepConfigApsTableInfoGroup OBJECT-GROUP
    OBJECTS     { vtssMepConfigApsPrio, vtssMepConfigApsApsType, 
                  vtssMepConfigApsCast, vtssMepConfigApsRapsOctet, 
                  vtssMepConfigApsAction }
    STATUS      current
    DESCRIPTION
        "A collection of objects suitable for bulk operations."
    ::= { vtssMepMibGroups 17 }

vtssMepConfigApsRowEditorInfoGroup OBJECT-GROUP
    OBJECTS     { vtssMepConfigApsRowEditorId, vtssMepConfigApsRowEditorPrio, 
                  vtssMepConfigApsRowEditorApsType, 
                  vtssMepConfigApsRowEditorCast, 
                  vtssMepConfigApsRowEditorRapsOctet, 
                  vtssMepConfigApsRowEditorAction }
    STATUS      current
    DESCRIPTION
        "A collection of objects suitable for bulk operations."
    ::= { vtssMepMibGroups 18 }

vtssMepConfigAisTableInfoGroup OBJECT-GROUP
    OBJECTS     { vtssMepConfigAisProtection, vtssMepConfigAisRate, 
                  vtssMepConfigAisAction }
    STATUS      current
    DESCRIPTION
        "A collection of objects suitable for bulk operations."
    ::= { vtssMepMibGroups 19 }

vtssMepConfigAisRowEditorInfoGroup OBJECT-GROUP
    OBJECTS     { vtssMepConfigAisRowEditorId, 
                  vtssMepConfigAisRowEditorProtection, 
                  vtssMepConfigAisRowEditorRate, vtssMepConfigAisRowEditorAction }
    STATUS      current
    DESCRIPTION
        "A collection of objects suitable for bulk operations."
    ::= { vtssMepMibGroups 20 }

vtssMepConfigLckTableInfoGroup OBJECT-GROUP
    OBJECTS     { vtssMepConfigLckRate, vtssMepConfigLckAction }
    STATUS      current
    DESCRIPTION
        "A collection of objects suitable for bulk operations."
    ::= { vtssMepMibGroups 21 }

vtssMepConfigLckRowEditorInfoGroup OBJECT-GROUP
    OBJECTS     { vtssMepConfigLckRowEditorId, vtssMepConfigLckRowEditorRate, 
                  vtssMepConfigLckRowEditorAction }
    STATUS      current
    DESCRIPTION
        "A collection of objects suitable for bulk operations."
    ::= { vtssMepMibGroups 22 }

vtssMepConfigClientFlowTableInfoGroup OBJECT-GROUP
    OBJECTS     { vtssMepConfigClientFlowAisPrio, vtssMepConfigClientFlowLckPrio, 
                  vtssMepConfigClientFlowLevel, vtssMepConfigClientFlowAction }
    STATUS      current
    DESCRIPTION
        "A collection of objects suitable for bulk operations."
    ::= { vtssMepMibGroups 23 }

vtssMepConfigClientFlowRowEditorInfoGroup OBJECT-GROUP
    OBJECTS     { vtssMepConfigClientFlowRowEditorId, 
                  vtssMepConfigClientFlowRowEditorFlowId, 
                  vtssMepConfigClientFlowRowEditorAisPrio, 
                  vtssMepConfigClientFlowRowEditorLckPrio, 
                  vtssMepConfigClientFlowRowEditorLevel, 
                  vtssMepConfigClientFlowRowEditorAction }
    STATUS      current
    DESCRIPTION
        "A collection of objects suitable for bulk operations."
    ::= { vtssMepMibGroups 24 }

vtssMepConfigSyslogTableInfoGroup OBJECT-GROUP
    OBJECTS     { vtssMepConfigSyslogEnable }
    STATUS      current
    DESCRIPTION
        "A collection of objects suitable for bulk operations."
    ::= { vtssMepMibGroups 25 }

vtssMepConfigTlvLeafInfoGroup OBJECT-GROUP
    OBJECTS     { vtssMepConfigTlvLeafOsTlvOuiFirst, 
                  vtssMepConfigTlvLeafOsTlvOuiSecond, 
                  vtssMepConfigTlvLeafOsTlvOuiThird, 
                  vtssMepConfigTlvLeafOsTlvSubType, 
                  vtssMepConfigTlvLeafOsTlvValue }
    STATUS      current
    DESCRIPTION
        "A collection of objects suitable for bulk operations."
    ::= { vtssMepMibGroups 26 }

vtssMepConfigBfdTableInfoGroup OBJECT-GROUP
    OBJECTS     { vtssMepConfigBfdEnable, vtssMepConfigBfdIsIndependent, 
                  vtssMepConfigBfdCcOnly, vtssMepConfigBfdTxAuthEnabled, 
                  vtssMepConfigBfdRxAuthEnabled, vtssMepConfigBfdTxAuthKeyId, 
                  vtssMepConfigBfdCcPeriod, vtssMepConfigBfdRxFlow, 
                  vtssMepConfigBfdAction }
    STATUS      current
    DESCRIPTION
        "A collection of objects suitable for bulk operations."
    ::= { vtssMepMibGroups 27 }

vtssMepConfigBfdRowEditorInfoGroup OBJECT-GROUP
    OBJECTS     { vtssMepConfigBfdRowEditorId, vtssMepConfigBfdRowEditorEnable, 
                  vtssMepConfigBfdRowEditorIsIndependent, 
                  vtssMepConfigBfdRowEditorCcOnly, 
                  vtssMepConfigBfdRowEditorTxAuthEnabled, 
                  vtssMepConfigBfdRowEditorRxAuthEnabled, 
                  vtssMepConfigBfdRowEditorTxAuthKeyId, 
                  vtssMepConfigBfdRowEditorCcPeriod, 
                  vtssMepConfigBfdRowEditorRxFlow, 
                  vtssMepConfigBfdRowEditorAction }
    STATUS      current
    DESCRIPTION
        "A collection of objects suitable for bulk operations."
    ::= { vtssMepMibGroups 28 }

vtssMepConfigBfdAuthTableInfoGroup OBJECT-GROUP
    OBJECTS     { vtssMepConfigBfdAuthKeyType, vtssMepConfigBfdAuthKeyLen, 
                  vtssMepConfigBfdAuthKey, vtssMepConfigBfdAuthAction }
    STATUS      current
    DESCRIPTION
        "A collection of objects suitable for bulk operations."
    ::= { vtssMepMibGroups 29 }

vtssMepConfigBfdAuthRowEditorInfoGroup OBJECT-GROUP
    OBJECTS     { vtssMepConfigBfdAuthRowEditorId, 
                  vtssMepConfigBfdAuthRowEditorKeyType, 
                  vtssMepConfigBfdAuthRowEditorKeyLen, 
                  vtssMepConfigBfdAuthRowEditorKey, 
                  vtssMepConfigBfdAuthRowEditorAction }
    STATUS      current
    DESCRIPTION
        "A collection of objects suitable for bulk operations."
    ::= { vtssMepMibGroups 30 }

vtssMepConfigRtTableInfoGroup OBJECT-GROUP
    OBJECTS     { vtssMepConfigRtTrafficClass, vtssMepConfigRtSrcIdTlv, 
                  vtssMepConfigRtDstIdTlv, vtssMepConfigRtPadTlvType, 
                  vtssMepConfigRtPadTlvLen, vtssMepConfigRtFlags, 
                  vtssMepConfigRtMaxTimeToLive, vtssMepConfigRtAction }
    STATUS      current
    DESCRIPTION
        "A collection of objects suitable for bulk operations."
    ::= { vtssMepMibGroups 31 }

vtssMepConfigRtRowEditorInfoGroup OBJECT-GROUP
    OBJECTS     { vtssMepConfigRtRowEditorId, 
                  vtssMepConfigRtRowEditorTrafficClass, 
                  vtssMepConfigRtRowEditorSrcIdTlv, 
                  vtssMepConfigRtRowEditorDstIdTlv, 
                  vtssMepConfigRtRowEditorPadTlvType, 
                  vtssMepConfigRtRowEditorPadTlvLen, 
                  vtssMepConfigRtRowEditorFlags, 
                  vtssMepConfigRtRowEditorMaxTimeToLive, 
                  vtssMepConfigRtRowEditorAction }
    STATUS      current
    DESCRIPTION
        "A collection of objects suitable for bulk operations."
    ::= { vtssMepMibGroups 32 }

vtssMepConfigLstTableInfoGroup OBJECT-GROUP
    OBJECTS     { vtssMepConfigLstEnable }
    STATUS      current
    DESCRIPTION
        "A collection of objects suitable for bulk operations."
    ::= { vtssMepMibGroups 33 }

vtssMepConfigLmAvailTableInfoGroup OBJECT-GROUP
    OBJECTS     { vtssMepConfigLmAvailEnable, vtssMepConfigLmAvailLosRatioThr, 
                  vtssMepConfigLmAvailInterval, vtssMepConfigLmAvailMaintenance }
    STATUS      current
    DESCRIPTION
        "A collection of objects suitable for bulk operations."
    ::= { vtssMepMibGroups 34 }

vtssMepConfigLmHliTableInfoGroup OBJECT-GROUP
    OBJECTS     { vtssMepConfigLmHliEnable, vtssMepConfigLmHliHiLosRatioThr, 
                  vtssMepConfigLmHliConInterval, 
                  vtssMepConfigLmHliCntHolddownTimer }
    STATUS      current
    DESCRIPTION
        "A collection of objects suitable for bulk operations."
    ::= { vtssMepMibGroups 35 }

vtssMepConfigLmSdegTableInfoGroup OBJECT-GROUP
    OBJECTS     { vtssMepConfigLmSdegEnable, vtssMepConfigLmSdegTxMin, 
                  vtssMepConfigLmSdegLosRatioThr, vtssMepConfigLmSdegBadThr, 
                  vtssMepConfigLmSdegGoodThr }
    STATUS      current
    DESCRIPTION
        "A collection of objects suitable for bulk operations."
    ::= { vtssMepMibGroups 36 }

vtssMepStatusInstanceTableInfoGroup OBJECT-GROUP
    OBJECTS     { vtssMepStatusInstanceClevel, vtssMepStatusInstanceCmeg, 
                  vtssMepStatusInstanceCmep, vtssMepStatusInstanceCssf, 
                  vtssMepStatusInstanceCais, vtssMepStatusInstanceClck, 
                  vtssMepStatusInstanceAtsf, vtssMepStatusInstanceAtsd, 
                  vtssMepStatusInstanceAblk, vtssMepStatusInstanceCloop, 
                  vtssMepStatusInstanceCconfig, vtssMepStatusInstanceCdeg }
    STATUS      current
    DESCRIPTION
        "A collection of objects suitable for bulk operations."
    ::= { vtssMepMibGroups 37 }

vtssMepStatusInstancePeerTableInfoGroup OBJECT-GROUP
    OBJECTS     { vtssMepStatusInstancePeerCloc, vtssMepStatusInstancePeerCrdi, 
                  vtssMepStatusInstancePeerCperiod, 
                  vtssMepStatusInstancePeerCprio }
    STATUS      current
    DESCRIPTION
        "A collection of objects suitable for bulk operations."
    ::= { vtssMepMibGroups 38 }

vtssMepStatusLmTableInfoGroup OBJECT-GROUP
    OBJECTS     { vtssMepStatusLmTxCounter, vtssMepStatusLmRxCounter, 
                  vtssMepStatusLmNearEndLosCounterTot, 
                  vtssMepStatusLmFarEndLosCounterTot, 
                  vtssMepStatusLmNearEndLosRatioInt, 
                  vtssMepStatusLmFarEndLosRatioInt, 
                  vtssMepStatusLmNearEndLosCounterInt, 
                  vtssMepStatusLmFarEndLosCounterInt, 
                  vtssMepStatusLmNearEndLosThCnt, vtssMepStatusLmFarEndLosThCnt, 
                  vtssMepStatusLmNearEndLosRatioTot, 
                  vtssMepStatusLmFarEndLosRatioTot, 
                  vtssMepStatusLmNearEndLosRatioMin, 
                  vtssMepStatusLmFarEndLosRatioMin, 
                  vtssMepStatusLmNearEndLosRatioMax, 
                  vtssMepStatusLmFarEndLosRatioMax }
    STATUS      current
    DESCRIPTION
        "A collection of objects suitable for bulk operations."
    ::= { vtssMepMibGroups 39 }

vtssMepStatusDmTwoWayTableInfoGroup OBJECT-GROUP
    OBJECTS     { vtssMepStatusDmTwoWayTxCounter, vtssMepStatusDmTwoWayRxCounter, 
                  vtssMepStatusDmTwoWayRxTimeOutCounter, 
                  vtssMepStatusDmTwoWayRxErrorCounter, 
                  vtssMepStatusDmTwoWayInternalOverflowCounter, 
                  vtssMepStatusDmTwoWayAverageDelay, 
                  vtssMepStatusDmTwoWayAverageLastnDelay, 
                  vtssMepStatusDmTwoWayAverageDelayVariation, 
                  vtssMepStatusDmTwoWayAverageLastnDelayVariation, 
                  vtssMepStatusDmTwoWayMinimumDelay, 
                  vtssMepStatusDmTwoWayMaximumDelay, 
                  vtssMepStatusDmTwoWayMinimumDelayVariation, 
                  vtssMepStatusDmTwoWayMaximumDelayVariation, 
                  vtssMepStatusDmTwoWayTimeUnit }
    STATUS      current
    DESCRIPTION
        "A collection of objects suitable for bulk operations."
    ::= { vtssMepMibGroups 40 }

vtssMepStatusDmOneWayFarNearTableInfoGroup OBJECT-GROUP
    OBJECTS     { vtssMepStatusDmOneWayFarNearTxCounter, 
                  vtssMepStatusDmOneWayFarNearRxCounter, 
                  vtssMepStatusDmOneWayFarNearRxTimeOutCounter, 
                  vtssMepStatusDmOneWayFarNearRxErrorCounter, 
                  vtssMepStatusDmOneWayFarNearInternalOverflowCounter, 
                  vtssMepStatusDmOneWayFarNearAverageDelay, 
                  vtssMepStatusDmOneWayFarNearAverageLastnDelay, 
                  vtssMepStatusDmOneWayFarNearAverageDelayVariation, 
                  vtssMepStatusDmOneWayFarNearAverageLastnDelayVariation, 
                  vtssMepStatusDmOneWayFarNearMinimumDelay, 
                  vtssMepStatusDmOneWayFarNearMaximumDelay, 
                  vtssMepStatusDmOneWayFarNearMinimumDelayVariation, 
                  vtssMepStatusDmOneWayFarNearMaximumDelayVariation, 
                  vtssMepStatusDmOneWayFarNearTimeUnit }
    STATUS      current
    DESCRIPTION
        "A collection of objects suitable for bulk operations."
    ::= { vtssMepMibGroups 41 }

vtssMepStatusDmOneWayNearFarTableInfoGroup OBJECT-GROUP
    OBJECTS     { vtssMepStatusDmOneWayNearFarTxCounter, 
                  vtssMepStatusDmOneWayNearFarRxCounter, 
                  vtssMepStatusDmOneWayNearFarRxTimeOutCounter, 
                  vtssMepStatusDmOneWayNearFarRxErrorCounter, 
                  vtssMepStatusDmOneWayNearFarInternalOverflowCounter, 
                  vtssMepStatusDmOneWayNearFarAverageDelay, 
                  vtssMepStatusDmOneWayNearFarAverageLastnDelay, 
                  vtssMepStatusDmOneWayNearFarAverageDelayVariation, 
                  vtssMepStatusDmOneWayNearFarAverageLastnDelayVariation, 
                  vtssMepStatusDmOneWayNearFarMinimumDelay, 
                  vtssMepStatusDmOneWayNearFarMaximumDelay, 
                  vtssMepStatusDmOneWayNearFarMinimumDelayVariation, 
                  vtssMepStatusDmOneWayNearFarMaximumDelayVariation, 
                  vtssMepStatusDmOneWayNearFarTimeUnit }
    STATUS      current
    DESCRIPTION
        "A collection of objects suitable for bulk operations."
    ::= { vtssMepMibGroups 42 }

vtssMepStatusLbTableInfoGroup OBJECT-GROUP
    OBJECTS     { vtssMepStatusLbTransactionId, vtssMepStatusLbReplyCounter, 
                  vtssMepStatusLbLbmTransmitted }
    STATUS      current
    DESCRIPTION
        "A collection of objects suitable for bulk operations."
    ::= { vtssMepMibGroups 43 }

vtssMepStatusLbReplyTableInfoGroup OBJECT-GROUP
    OBJECTS     { vtssMepStatusLbReplyMac, vtssMepStatusLbReplyLbrReceived, 
                  vtssMepStatusLbReplyOutOfOrder, vtssMepStatusLbReplyMepMipId }
    STATUS      current
    DESCRIPTION
        "A collection of objects suitable for bulk operations."
    ::= { vtssMepMibGroups 44 }

vtssMepStatusTstTableInfoGroup OBJECT-GROUP
    OBJECTS     { vtssMepStatusTstTxCounter, vtssMepStatusTstRxCounter, 
                  vtssMepStatusTstOutOfOrderCounter, vtssMepStatusTstRxRate, 
                  vtssMepStatusTstTestTime }
    STATUS      current
    DESCRIPTION
        "A collection of objects suitable for bulk operations."
    ::= { vtssMepMibGroups 45 }

vtssMepStatusLtTableInfoGroup OBJECT-GROUP
    OBJECTS     { vtssMepStatusLtTransactionId, vtssMepStatusLtReplyCount }
    STATUS      current
    DESCRIPTION
        "A collection of objects suitable for bulk operations."
    ::= { vtssMepMibGroups 46 }

vtssMepStatusLtReplyTableInfoGroup OBJECT-GROUP
    OBJECTS     { vtssMepStatusLtReplyMode, vtssMepStatusLtReplyDirection, 
                  vtssMepStatusLtReplyTtl, vtssMepStatusLtReplyForwarded, 
                  vtssMepStatusLtReplyRelayAction, 
                  vtssMepStatusLtReplyLastEgressMac, 
                  vtssMepStatusLtReplyNextEgressMac }
    STATUS      current
    DESCRIPTION
        "A collection of objects suitable for bulk operations."
    ::= { vtssMepMibGroups 47 }

vtssMepStatusCcPeerTableInfoGroup OBJECT-GROUP
    OBJECTS     { vtssMepStatusCcPeerOsTlvOuiFirst, 
                  vtssMepStatusCcPeerOsTlvOuiSecond, 
                  vtssMepStatusCcPeerOsTlvOuiThird, 
                  vtssMepStatusCcPeerOsTlvSubType, vtssMepStatusCcPeerOsTlvValue, 
                  vtssMepStatusCcPeerIsTlvValue, vtssMepStatusCcPeerPsTlvValue, 
                  vtssMepStatusCcPeerOsTlvReceived, 
                  vtssMepStatusCcPeerIsTlvReceived, 
                  vtssMepStatusCcPeerPsTlvReceived }
    STATUS      current
    DESCRIPTION
        "A collection of objects suitable for bulk operations."
    ::= { vtssMepMibGroups 48 }

vtssMepStatusBfdTableInfoGroup OBJECT-GROUP
    OBJECTS     { vtssMepStatusBfdCcTxCnt, vtssMepStatusBfdValidCcRxCnt, 
                  vtssMepStatusBfdInvalidCcRxCnt, vtssMepStatusBfdCvTxCnt, 
                  vtssMepStatusBfdValidCvRxCnt, vtssMepStatusBfdInvalidCvRxCnt, 
                  vtssMepStatusBfdMyDiscr, vtssMepStatusBfdSessionState0, 
                  vtssMepStatusBfdSessionState1, vtssMepStatusBfdLocalDiag, 
                  vtssMepStatusBfdRemoteSessionState, vtssMepStatusBfdRemoteDiag, 
                  vtssMepStatusBfdRemoteDiscr, vtssMepStatusBfdRemoteMinRx, 
                  vtssMepStatusBfdRemoteFlags, vtssMepStatusBfdUnexpDiscr, 
                  vtssMepStatusBfdExpSrcMepIdTlv, 
                  vtssMepStatusBfdUnexpSrcMepIdTlv }
    STATUS      current
    DESCRIPTION
        "A collection of objects suitable for bulk operations."
    ::= { vtssMepMibGroups 49 }

vtssMepStatusRtTableInfoGroup OBJECT-GROUP
    OBJECTS     { vtssMepStatusRtSeqNo, vtssMepStatusRtRequestCount, 
                  vtssMepStatusRtReplyCount }
    STATUS      current
    DESCRIPTION
        "A collection of objects suitable for bulk operations."
    ::= { vtssMepMibGroups 50 }

vtssMepStatusRtReplyTableInfoGroup OBJECT-GROUP
    OBJECTS     { vtssMepStatusRtReplyReturnCode, 
                  vtssMepStatusRtReplyReturnSubcode, vtssMepStatusRtReplyRttSec, 
                  vtssMepStatusRtReplyRttUsec, vtssMepStatusRtReplyTsSentSec, 
                  vtssMepStatusRtReplyTsSentUsec, 
                  vtssMepStatusRtReplyTsReceivedSec, 
                  vtssMepStatusRtReplyTsReceivedUsec, 
                  vtssMepStatusRtReplySrcGlobalId, vtssMepStatusRtReplySrcNodeId, 
                  vtssMepStatusRtReplyFecSrcValue, vtssMepStatusRtReplyRxIfNum, 
                  vtssMepStatusRtReplyRxLabelCnt, vtssMepStatusRtReplyRxLabel1, 
                  vtssMepStatusRtReplyRxLabel2, vtssMepStatusRtReplyRxLabel3, 
                  vtssMepStatusRtReplyRxLabel4, vtssMepStatusRtReplyRxLabel5, 
                  vtssMepStatusRtReplyRxLabel6, vtssMepStatusRtReplyRxLabel7, 
                  vtssMepStatusRtReplyRxLabel8 }
    STATUS      current
    DESCRIPTION
        "A collection of objects suitable for bulk operations."
    ::= { vtssMepMibGroups 51 }

vtssMepStatusLmAvailTableInfoGroup OBJECT-GROUP
    OBJECTS     { vtssMepStatusLmAvailNearEndAvailState, 
                  vtssMepStatusLmAvailFarEndAvailState, 
                  vtssMepStatusLmAvailNearEndAvailCnt, 
                  vtssMepStatusLmAvailFarEndAvailCnt, 
                  vtssMepStatusLmAvailNearEndUnAvailCnt, 
                  vtssMepStatusLmAvailFarEndUnAvailCnt }
    STATUS      current
    DESCRIPTION
        "A collection of objects suitable for bulk operations."
    ::= { vtssMepMibGroups 52 }

vtssMepStatusLmHliTableInfoGroup OBJECT-GROUP
    OBJECTS     { vtssMepStatusLmHliNearEndCnt, vtssMepStatusLmHliFarEndCnt, 
                  vtssMepStatusLmHliNearEndConCnt, 
                  vtssMepStatusLmHliFarEndConCnt }
    STATUS      current
    DESCRIPTION
        "A collection of objects suitable for bulk operations."
    ::= { vtssMepMibGroups 53 }

vtssMepControlLmTableInfoGroup OBJECT-GROUP
    OBJECTS     { vtssMepControlLmClear }
    STATUS      current
    DESCRIPTION
        "A collection of objects suitable for bulk operations."
    ::= { vtssMepMibGroups 54 }

vtssMepControlDmTableInfoGroup OBJECT-GROUP
    OBJECTS     { vtssMepControlDmClear }
    STATUS      current
    DESCRIPTION
        "A collection of objects suitable for bulk operations."
    ::= { vtssMepMibGroups 55 }

vtssMepControlTstTableInfoGroup OBJECT-GROUP
    OBJECTS     { vtssMepControlTstClear }
    STATUS      current
    DESCRIPTION
        "A collection of objects suitable for bulk operations."
    ::= { vtssMepMibGroups 56 }

vtssMepControlBfdTableInfoGroup OBJECT-GROUP
    OBJECTS     { vtssMepControlBfdClear }
    STATUS      current
    DESCRIPTION
        "A collection of objects suitable for bulk operations."
    ::= { vtssMepMibGroups 57 }

vtssMepMibCompliance MODULE-COMPLIANCE
    STATUS      current
    DESCRIPTION
        "The compliance statement for the implementation."

    MODULE      -- this module

        MANDATORY-GROUPS        { vtssMepCapabilitiesInfoGroup, 
                  vtssMepConfigInstanceTableInfoGroup, 
                  vtssMepConfigInstanceRowEditorInfoGroup, 
                  vtssMepConfigInstancePeerTableInfoGroup, 
                  vtssMepConfigInstancePeerRowEditorInfoGroup, 
                  vtssMepConfigPmTableInfoGroup, vtssMepConfigCcTableInfoGroup, 
                  vtssMepConfigCcRowEditorInfoGroup, 
                  vtssMepConfigLmTableInfoGroup, vtssMepConfigDmTableInfoGroup, 
                  vtssMepConfigLbTableInfoGroup, 
                  vtssMepConfigLbRowEditorInfoGroup, 
                  vtssMepConfigTstTableInfoGroup, 
                  vtssMepConfigTstRowEditorInfoGroup, 
                  vtssMepConfigLtTableInfoGroup, 
                  vtssMepConfigLtRowEditorInfoGroup, 
                  vtssMepConfigApsTableInfoGroup, 
                  vtssMepConfigApsRowEditorInfoGroup, 
                  vtssMepConfigAisTableInfoGroup, 
                  vtssMepConfigAisRowEditorInfoGroup, 
                  vtssMepConfigLckTableInfoGroup, 
                  vtssMepConfigLckRowEditorInfoGroup, 
                  vtssMepConfigClientFlowTableInfoGroup, 
                  vtssMepConfigClientFlowRowEditorInfoGroup, 
                  vtssMepConfigSyslogTableInfoGroup, 
                  vtssMepConfigTlvLeafInfoGroup, vtssMepConfigBfdTableInfoGroup, 
                  vtssMepConfigBfdRowEditorInfoGroup, 
                  vtssMepConfigBfdAuthTableInfoGroup, 
                  vtssMepConfigBfdAuthRowEditorInfoGroup, 
                  vtssMepConfigRtTableInfoGroup, 
                  vtssMepConfigRtRowEditorInfoGroup, 
                  vtssMepConfigLstTableInfoGroup, 
                  vtssMepConfigLmAvailTableInfoGroup, 
                  vtssMepConfigLmHliTableInfoGroup, 
                  vtssMepConfigLmSdegTableInfoGroup, 
                  vtssMepStatusInstanceTableInfoGroup, 
                  vtssMepStatusInstancePeerTableInfoGroup, 
                  vtssMepStatusLmTableInfoGroup, 
                  vtssMepStatusDmTwoWayTableInfoGroup, 
                  vtssMepStatusDmOneWayFarNearTableInfoGroup, 
                  vtssMepStatusDmOneWayNearFarTableInfoGroup, 
                  vtssMepStatusLbTableInfoGroup, 
                  vtssMepStatusLbReplyTableInfoGroup, 
                  vtssMepStatusTstTableInfoGroup, vtssMepStatusLtTableInfoGroup, 
                  vtssMepStatusLtReplyTableInfoGroup, 
                  vtssMepStatusCcPeerTableInfoGroup, 
                  vtssMepStatusBfdTableInfoGroup, vtssMepStatusRtTableInfoGroup, 
                  vtssMepStatusRtReplyTableInfoGroup, 
                  vtssMepStatusLmAvailTableInfoGroup, 
                  vtssMepStatusLmHliTableInfoGroup, 
                  vtssMepControlLmTableInfoGroup, vtssMepControlDmTableInfoGroup, 
                  vtssMepControlTstTableInfoGroup, 
                  vtssMepControlBfdTableInfoGroup }

    ::= { vtssMepMibCompliances 1 }

END
