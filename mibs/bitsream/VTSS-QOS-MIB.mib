-- *****************************************************************
-- QOS-MIB:  Vitesse private MIB
--
-- Copyright (c) 2002-2013 Vitesse Semiconductor Corporation "Vitesse".
-- All Rights Reserved.
--
-- ****************************************************************

VTSS-QOS-MIB DEFINITIONS ::= BEGIN

IMPORTS
    MODULE-COMPLIANCE, OBJECT-GROUP
        FROM SNMPv2-CONF
    MODULE-IDENTITY, OBJECT-TYPE
        FROM SNMPv2-SMI
    TEXTUAL-CONVENTION
        FROM SNMPv2-TC
    vtssSwitchMgmt
        FROM VTSS-SMI
    Dscp FROM DIFFSERV-DSCP-TC
    InetAddressIPv6 FROM INET-ADDRESS-MIB
    Integer32 FROM SNMPv2-SMI
    IpAddress FROM SNMPv2-SMI
    Unsigned32 FROM SNMPv2-SMI
    MacAddress FROM SNMPv2-TC
    TruthValue FROM SNMPv2-TC
    VTSSASRType FROM VTSS-TC
    VTSSBitType FROM VTSS-TC
    VTSSDestMacType FROM VTSS-TC
    VTSSEtherType FROM VTSS-TC
    VTSSInterfaceIndex FROM VTSS-TC
    VTSSPercent FROM VTSS-TC
    VTSSPortList FROM VTSS-TC
    VTSSRowEditorState FROM VTSS-TC
    VTSSUnsigned16 FROM VTSS-TC
    VTSSUnsigned8 FROM VTSS-TC
    VTSSVcapKeyType FROM VTSS-TC
    VTSSVlanTagPriority FROM VTSS-TC
    VTSSVlanTagType FROM VTSS-TC
    ;

vtssQosMib MODULE-IDENTITY
    LAST-UPDATED "201504070000Z"
    ORGANIZATION
        "Vitesse Semiconductor Corporation"
    CONTACT-INFO
        "Application support <application_support@vitesse.com>"
    DESCRIPTION
        "This is a private MIB for QoS"
    REVISION    "201504070000Z"
    DESCRIPTION
        "Added QosConfigInterfaceQueueShaperRateType,
         QosConfigInterfaceShaperRateType objects."
    REVISION    "201411060000Z"
    DESCRIPTION
        "Added new WredV3 related objects and adapted WredTable to WredV3."
    REVISION    "201410080000Z"
    DESCRIPTION
        "Removed QosCapabilitiesBitrateMin, QosCapabilitiesBitrateMax,
         QosCapabilitiesBurstSizeMin and QosCapabilitiesBurstSizeMax.
         
         Added policer and shaper specific min/max capabilities objects.
         
         Added QosConfigGlobalStormPolicersUnicastFrameRate,
         QosConfigGlobalStormPolicersMulticastFrameRate and
         QosConfigGlobalStormPolicersBroadcastFrameRate."
    REVISION    "201409170000Z"
    DESCRIPTION
        "Added QosCapabilitiesHasQueueShapersExcess object."
    REVISION    "201408120000Z"
    DESCRIPTION
        "Updated descriptions when referring to a capability."
    REVISION    "201407010000Z"
    DESCRIPTION
        "Initial version"
    ::= { vtssSwitchMgmt 14 }


VTSSQosDscpClassify ::= TEXTUAL-CONVENTION
    STATUS      current
    DESCRIPTION
        "An integer that indicates the DSCP classify mode."
    SYNTAX      INTEGER { none(0), zero(1), selected(2), all(3) }

VTSSQosDscpRemark ::= TEXTUAL-CONVENTION
    STATUS      current
    DESCRIPTION
        "An integer that indicates the DSCP remark mode."
    SYNTAX      INTEGER { disabled(0), rewrite(1), remap(2), remapDp(3) }

VTSSQosQceFrameType ::= TEXTUAL-CONVENTION
    STATUS      current
    DESCRIPTION
        "An integer that indicates the QCE frame type key."
    SYNTAX      INTEGER { any(0), etype(1), llc(2), snap(3), ipv4(4), ipv6(5) }

VTSSQosQceUserType ::= TEXTUAL-CONVENTION
    STATUS      current
    DESCRIPTION
        "An integer that indicates the QCE user type.
         
         If the value is zero it indicates a static configuration.
         
         If the value is non-zero it indicates a dynamic configuration made by
         another subsystem."
    SYNTAX      INTEGER { admin(0), voiceVlan(1) }

VTSSQosShaperRateType ::= TEXTUAL-CONVENTION
    STATUS      current
    DESCRIPTION
        "An integer that indicates the shaper rate type.
         
         If the value is zero, it indicates the shaper uses line-rate.
         
         If the value is one, it indicates the shaper uses data-rate.
         
         NOTE: For QoS Queue shapers, this configuration is valid only for
         Normal port mode. If the port is in Basic or Hierarchical mode, the
         rate-type will be stored and become active when the port is switched
         back to Normal Scheduling mode."
    SYNTAX      INTEGER { line(0), data(1) }

VTSSQosTagRemarkingMode ::= TEXTUAL-CONVENTION
    STATUS      current
    DESCRIPTION
        "An integer that indicates the tag remarking mode."
    SYNTAX      INTEGER { classified(0), default(2), mapped(3) }

VTSSQosWredMaxSelector ::= TEXTUAL-CONVENTION
    STATUS      current
    DESCRIPTION
        "An integer that selects between 'Maximum Drop Probability' or 'Maximum
         Fill Level'."
    SYNTAX      INTEGER { maximumDropProbability(0), maximumFillLevel(1) }

vtssQosMibObjects OBJECT IDENTIFIER
    ::= { vtssQosMib 1 }

vtssQosCapabilities OBJECT IDENTIFIER
    ::= { vtssQosMibObjects 1 }

vtssQosCapabilitiesClassMin OBJECT-TYPE
    SYNTAX      Unsigned32
    MAX-ACCESS  read-only
    STATUS      current
    DESCRIPTION 
        "Minimum allowed QoS class."
    ::= { vtssQosCapabilities 1 }

vtssQosCapabilitiesClassMax OBJECT-TYPE
    SYNTAX      Unsigned32
    MAX-ACCESS  read-only
    STATUS      current
    DESCRIPTION 
        "Maximum allowed QoS class."
    ::= { vtssQosCapabilities 2 }

vtssQosCapabilitiesDplMin OBJECT-TYPE
    SYNTAX      VTSSUnsigned8
    MAX-ACCESS  read-only
    STATUS      current
    DESCRIPTION 
        "Minimum allowed drop precedence level."
    ::= { vtssQosCapabilities 3 }

vtssQosCapabilitiesDplMax OBJECT-TYPE
    SYNTAX      VTSSUnsigned8
    MAX-ACCESS  read-only
    STATUS      current
    DESCRIPTION 
        "Maximum allowed drop precedence level."
    ::= { vtssQosCapabilities 4 }

vtssQosCapabilitiesWredGroupMin OBJECT-TYPE
    SYNTAX      Unsigned32
    MAX-ACCESS  read-only
    STATUS      current
    DESCRIPTION 
        "Minimum allowed WRED group number."
    ::= { vtssQosCapabilities 5 }

vtssQosCapabilitiesWredGroupMax OBJECT-TYPE
    SYNTAX      Unsigned32
    MAX-ACCESS  read-only
    STATUS      current
    DESCRIPTION 
        "Maximum allowed WRED group number."
    ::= { vtssQosCapabilities 6 }

vtssQosCapabilitiesWredDplMin OBJECT-TYPE
    SYNTAX      VTSSUnsigned8
    MAX-ACCESS  read-only
    STATUS      current
    DESCRIPTION 
        "Minimum allowed WRED drop precedence level."
    ::= { vtssQosCapabilities 7 }

vtssQosCapabilitiesWredDplMax OBJECT-TYPE
    SYNTAX      VTSSUnsigned8
    MAX-ACCESS  read-only
    STATUS      current
    DESCRIPTION 
        "Maximum allowed WRED drop precedence level."
    ::= { vtssQosCapabilities 8 }

vtssQosCapabilitiesQceIdMin OBJECT-TYPE
    SYNTAX      Unsigned32
    MAX-ACCESS  read-only
    STATUS      current
    DESCRIPTION 
        "Minimum allowed QCE Id."
    ::= { vtssQosCapabilities 9 }

vtssQosCapabilitiesQceIdMax OBJECT-TYPE
    SYNTAX      Unsigned32
    MAX-ACCESS  read-only
    STATUS      current
    DESCRIPTION 
        "Maximum allowed QCE Id."
    ::= { vtssQosCapabilities 10 }

vtssQosCapabilitiesPortPolicerBitRateMin OBJECT-TYPE
    SYNTAX      Unsigned32
    MAX-ACCESS  read-only
    STATUS      current
    DESCRIPTION 
        "Minimum supported bit rate in kbps for port policers using bit rate
         mode."
    ::= { vtssQosCapabilities 11 }

vtssQosCapabilitiesPortPolicerBitRateMax OBJECT-TYPE
    SYNTAX      Unsigned32
    MAX-ACCESS  read-only
    STATUS      current
    DESCRIPTION 
        "Maximum supported bit rate in kbps for port policers using bit rate
         mode.
         
         If zero, the port policers does not support bit rate mode."
    ::= { vtssQosCapabilities 12 }

vtssQosCapabilitiesPortPolicerBitBurstMin OBJECT-TYPE
    SYNTAX      Unsigned32
    MAX-ACCESS  read-only
    STATUS      current
    DESCRIPTION 
        "Minimum supported burst size in bytes for port policers using bit rate
         mode."
    ::= { vtssQosCapabilities 13 }

vtssQosCapabilitiesPortPolicerBitBurstMax OBJECT-TYPE
    SYNTAX      Unsigned32
    MAX-ACCESS  read-only
    STATUS      current
    DESCRIPTION 
        "Maximum supported burst size in bytes for port policers using bit rate
         mode."
    ::= { vtssQosCapabilities 14 }

vtssQosCapabilitiesPortPolicerFrameRateMin OBJECT-TYPE
    SYNTAX      Unsigned32
    MAX-ACCESS  read-only
    STATUS      current
    DESCRIPTION 
        "Minimum supported frame rate in fps for port policers using frame rate
         mode."
    ::= { vtssQosCapabilities 15 }

vtssQosCapabilitiesPortPolicerFrameRateMax OBJECT-TYPE
    SYNTAX      Unsigned32
    MAX-ACCESS  read-only
    STATUS      current
    DESCRIPTION 
        "Maximum supported frame rate in fps for port policers using frame rate
         mode.
         
         If zero, the port policers does not support frame rate mode."
    ::= { vtssQosCapabilities 16 }

vtssQosCapabilitiesPortPolicerFrameBurstMin OBJECT-TYPE
    SYNTAX      Unsigned32
    MAX-ACCESS  read-only
    STATUS      current
    DESCRIPTION 
        "Minimum supported burst size in frames for port policers using frame
         rate mode."
    ::= { vtssQosCapabilities 17 }

vtssQosCapabilitiesPortPolicerFrameBurstMax OBJECT-TYPE
    SYNTAX      Unsigned32
    MAX-ACCESS  read-only
    STATUS      current
    DESCRIPTION 
        "Maximum supported burst size in frames for port policers using frame
         rate mode."
    ::= { vtssQosCapabilities 18 }

vtssQosCapabilitiesQueuePolicerBitRateMin OBJECT-TYPE
    SYNTAX      Unsigned32
    MAX-ACCESS  read-only
    STATUS      current
    DESCRIPTION 
        "Minimum supported bit rate in kbps for queue policers using bit rate
         mode."
    ::= { vtssQosCapabilities 19 }

vtssQosCapabilitiesQueuePolicerBitRateMax OBJECT-TYPE
    SYNTAX      Unsigned32
    MAX-ACCESS  read-only
    STATUS      current
    DESCRIPTION 
        "Maximum supported bit rate in kbps for queue policers using bit rate
         mode.
         
         If zero, the queue policers does not support bit rate mode."
    ::= { vtssQosCapabilities 20 }

vtssQosCapabilitiesQueuePolicerBitBurstMin OBJECT-TYPE
    SYNTAX      Unsigned32
    MAX-ACCESS  read-only
    STATUS      current
    DESCRIPTION 
        "Minimum supported burst size in bytes for queue policers using bit rate
         mode."
    ::= { vtssQosCapabilities 21 }

vtssQosCapabilitiesQueuePolicerBitBurstMax OBJECT-TYPE
    SYNTAX      Unsigned32
    MAX-ACCESS  read-only
    STATUS      current
    DESCRIPTION 
        "Maximum supported burst size in bytes for queue policers using bit rate
         mode."
    ::= { vtssQosCapabilities 22 }

vtssQosCapabilitiesQueuePolicerFrameRateMin OBJECT-TYPE
    SYNTAX      Unsigned32
    MAX-ACCESS  read-only
    STATUS      current
    DESCRIPTION 
        "Minimum supported frame rate in fps for queue policers using frame rate
         mode."
    ::= { vtssQosCapabilities 23 }

vtssQosCapabilitiesQueuePolicerFrameRateMax OBJECT-TYPE
    SYNTAX      Unsigned32
    MAX-ACCESS  read-only
    STATUS      current
    DESCRIPTION 
        "Maximum supported frame rate in fps for queue policers using frame rate
         mode.
         
         If zero, the port policers does not support frame rate mode."
    ::= { vtssQosCapabilities 24 }

vtssQosCapabilitiesQueuePolicerFrameBurstMin OBJECT-TYPE
    SYNTAX      Unsigned32
    MAX-ACCESS  read-only
    STATUS      current
    DESCRIPTION 
        "Minimum supported burst size in frames for queue policers using frame
         rate mode."
    ::= { vtssQosCapabilities 25 }

vtssQosCapabilitiesQueuePolicerFrameBurstMax OBJECT-TYPE
    SYNTAX      Unsigned32
    MAX-ACCESS  read-only
    STATUS      current
    DESCRIPTION 
        "Maximum supported burst size in frames for queue policers using frame
         rate mode."
    ::= { vtssQosCapabilities 26 }

vtssQosCapabilitiesPortShaperBitRateMin OBJECT-TYPE
    SYNTAX      Unsigned32
    MAX-ACCESS  read-only
    STATUS      current
    DESCRIPTION 
        "Minimum supported bit rate in kbps for port shapers using bit rate
         mode."
    ::= { vtssQosCapabilities 27 }

vtssQosCapabilitiesPortShaperBitRateMax OBJECT-TYPE
    SYNTAX      Unsigned32
    MAX-ACCESS  read-only
    STATUS      current
    DESCRIPTION 
        "Maximum supported bit rate in kbps for port shapers using bit rate
         mode.
         
         If zero, the port shapers does not support bit rate mode."
    ::= { vtssQosCapabilities 28 }

vtssQosCapabilitiesPortShaperBitBurstMin OBJECT-TYPE
    SYNTAX      Unsigned32
    MAX-ACCESS  read-only
    STATUS      current
    DESCRIPTION 
        "Minimum supported burst size in bytes for port shapers using bit rate
         mode."
    ::= { vtssQosCapabilities 29 }

vtssQosCapabilitiesPortShaperBitBurstMax OBJECT-TYPE
    SYNTAX      Unsigned32
    MAX-ACCESS  read-only
    STATUS      current
    DESCRIPTION 
        "Maximum supported burst size in bytes for port shapers using bit rate
         mode."
    ::= { vtssQosCapabilities 30 }

vtssQosCapabilitiesPortShaperFrameRateMin OBJECT-TYPE
    SYNTAX      Unsigned32
    MAX-ACCESS  read-only
    STATUS      current
    DESCRIPTION 
        "Minimum supported frame rate in fps for port shapers using frame rate
         mode."
    ::= { vtssQosCapabilities 31 }

vtssQosCapabilitiesPortShaperFrameRateMax OBJECT-TYPE
    SYNTAX      Unsigned32
    MAX-ACCESS  read-only
    STATUS      current
    DESCRIPTION 
        "Maximum supported frame rate in fps for port shapers using frame rate
         mode.
         
         If zero, the port shapers does not support frame rate mode."
    ::= { vtssQosCapabilities 32 }

vtssQosCapabilitiesPortShaperFrameBurstMin OBJECT-TYPE
    SYNTAX      Unsigned32
    MAX-ACCESS  read-only
    STATUS      current
    DESCRIPTION 
        "Minimum supported burst size in frames for port shapers using frame
         rate mode."
    ::= { vtssQosCapabilities 33 }

vtssQosCapabilitiesPortShaperFrameBurstMax OBJECT-TYPE
    SYNTAX      Unsigned32
    MAX-ACCESS  read-only
    STATUS      current
    DESCRIPTION 
        "Maximum supported burst size in frames for port shapers using frame
         rate mode."
    ::= { vtssQosCapabilities 34 }

vtssQosCapabilitiesQueueShaperBitRateMin OBJECT-TYPE
    SYNTAX      Unsigned32
    MAX-ACCESS  read-only
    STATUS      current
    DESCRIPTION 
        "Minimum supported bit rate in kbps for queue shapers using bit rate
         mode."
    ::= { vtssQosCapabilities 35 }

vtssQosCapabilitiesQueueShaperBitRateMax OBJECT-TYPE
    SYNTAX      Unsigned32
    MAX-ACCESS  read-only
    STATUS      current
    DESCRIPTION 
        "Maximum supported bit rate in kbps for queue shapers using bit rate
         mode.
         
         If zero, the queue shapers does not support bit rate mode."
    ::= { vtssQosCapabilities 36 }

vtssQosCapabilitiesQueueShaperBitBurstMin OBJECT-TYPE
    SYNTAX      Unsigned32
    MAX-ACCESS  read-only
    STATUS      current
    DESCRIPTION 
        "Minimum supported burst size in bytes for queue shapers using bit rate
         mode."
    ::= { vtssQosCapabilities 37 }

vtssQosCapabilitiesQueueShaperBitBurstMax OBJECT-TYPE
    SYNTAX      Unsigned32
    MAX-ACCESS  read-only
    STATUS      current
    DESCRIPTION 
        "Maximum supported burst size in bytes for queue shapers using bit rate
         mode."
    ::= { vtssQosCapabilities 38 }

vtssQosCapabilitiesQueueShaperFrameRateMin OBJECT-TYPE
    SYNTAX      Unsigned32
    MAX-ACCESS  read-only
    STATUS      current
    DESCRIPTION 
        "Minimum supported frame rate in fps for queue shapers using frame rate
         mode."
    ::= { vtssQosCapabilities 39 }

vtssQosCapabilitiesQueueShaperFrameRateMax OBJECT-TYPE
    SYNTAX      Unsigned32
    MAX-ACCESS  read-only
    STATUS      current
    DESCRIPTION 
        "Maximum supported frame rate in fps for queue shapers using frame rate
         mode.
         
         If zero, the port shapers does not support frame rate mode."
    ::= { vtssQosCapabilities 40 }

vtssQosCapabilitiesQueueShaperFrameBurstMin OBJECT-TYPE
    SYNTAX      Unsigned32
    MAX-ACCESS  read-only
    STATUS      current
    DESCRIPTION 
        "Minimum supported burst size in frames for queue shapers using frame
         rate mode."
    ::= { vtssQosCapabilities 41 }

vtssQosCapabilitiesQueueShaperFrameBurstMax OBJECT-TYPE
    SYNTAX      Unsigned32
    MAX-ACCESS  read-only
    STATUS      current
    DESCRIPTION 
        "Maximum supported burst size in frames for queue shapers using frame
         rate mode."
    ::= { vtssQosCapabilities 42 }

vtssQosCapabilitiesGlobalStormBitRateMin OBJECT-TYPE
    SYNTAX      Unsigned32
    MAX-ACCESS  read-only
    STATUS      current
    DESCRIPTION 
        "Minimum supported bit rate in kbps for global storm policers using bit
         rate mode."
    ::= { vtssQosCapabilities 43 }

vtssQosCapabilitiesGlobalStormBitRateMax OBJECT-TYPE
    SYNTAX      Unsigned32
    MAX-ACCESS  read-only
    STATUS      current
    DESCRIPTION 
        "Maximum supported bit rate in kbps for global storm policers using bit
         rate mode.
         
         If zero, the global storm policers does not support bit rate mode."
    ::= { vtssQosCapabilities 44 }

vtssQosCapabilitiesGlobalStormBitBurstMin OBJECT-TYPE
    SYNTAX      Unsigned32
    MAX-ACCESS  read-only
    STATUS      current
    DESCRIPTION 
        "Minimum supported burst size in bytes for global storm policers using
         bit rate mode."
    ::= { vtssQosCapabilities 45 }

vtssQosCapabilitiesGlobalStormBitBurstMax OBJECT-TYPE
    SYNTAX      Unsigned32
    MAX-ACCESS  read-only
    STATUS      current
    DESCRIPTION 
        "Maximum supported burst size in bytes for global storm policers using
         bit rate mode."
    ::= { vtssQosCapabilities 46 }

vtssQosCapabilitiesGlobalStormFrameRateMin OBJECT-TYPE
    SYNTAX      Unsigned32
    MAX-ACCESS  read-only
    STATUS      current
    DESCRIPTION 
        "Minimum supported frame rate in fps for global storm policers using
         frame rate mode."
    ::= { vtssQosCapabilities 47 }

vtssQosCapabilitiesGlobalStormFrameRateMax OBJECT-TYPE
    SYNTAX      Unsigned32
    MAX-ACCESS  read-only
    STATUS      current
    DESCRIPTION 
        "Maximum supported frame rate in fps for global storm policers using
         frame rate mode.
         
         If zero, the global storm policers does not support frame rate mode."
    ::= { vtssQosCapabilities 48 }

vtssQosCapabilitiesGlobalStormFrameBurstMin OBJECT-TYPE
    SYNTAX      Unsigned32
    MAX-ACCESS  read-only
    STATUS      current
    DESCRIPTION 
        "Minimum supported burst size in frames for global storm policers using
         frame rate mode."
    ::= { vtssQosCapabilities 49 }

vtssQosCapabilitiesGlobalStormFrameBurstMax OBJECT-TYPE
    SYNTAX      Unsigned32
    MAX-ACCESS  read-only
    STATUS      current
    DESCRIPTION 
        "Maximum supported burst size in frames for global storm policers using
         frame rate mode."
    ::= { vtssQosCapabilities 50 }

vtssQosCapabilitiesPortStormBitRateMin OBJECT-TYPE
    SYNTAX      Unsigned32
    MAX-ACCESS  read-only
    STATUS      current
    DESCRIPTION 
        "Minimum supported bit rate in kbps for port storm policers using bit
         rate mode."
    ::= { vtssQosCapabilities 51 }

vtssQosCapabilitiesPortStormBitRateMax OBJECT-TYPE
    SYNTAX      Unsigned32
    MAX-ACCESS  read-only
    STATUS      current
    DESCRIPTION 
        "Maximum supported bit rate in kbps for port storm policers using bit
         rate mode.
         
         If zero, the port storm policers does not support bit rate mode."
    ::= { vtssQosCapabilities 52 }

vtssQosCapabilitiesPortStormBitBurstMin OBJECT-TYPE
    SYNTAX      Unsigned32
    MAX-ACCESS  read-only
    STATUS      current
    DESCRIPTION 
        "Minimum supported burst size in bytes for port storm policers using bit
         rate mode."
    ::= { vtssQosCapabilities 53 }

vtssQosCapabilitiesPortStormBitBurstMax OBJECT-TYPE
    SYNTAX      Unsigned32
    MAX-ACCESS  read-only
    STATUS      current
    DESCRIPTION 
        "Maximum supported burst size in bytes for port storm policers using bit
         rate mode."
    ::= { vtssQosCapabilities 54 }

vtssQosCapabilitiesPortStormFrameRateMin OBJECT-TYPE
    SYNTAX      Unsigned32
    MAX-ACCESS  read-only
    STATUS      current
    DESCRIPTION 
        "Minimum supported frame rate in fps for port storm policers using frame
         rate mode."
    ::= { vtssQosCapabilities 55 }

vtssQosCapabilitiesPortStormFrameRateMax OBJECT-TYPE
    SYNTAX      Unsigned32
    MAX-ACCESS  read-only
    STATUS      current
    DESCRIPTION 
        "Maximum supported frame rate in fps for port storm policers using frame
         rate mode.
         
         If zero, the port storm policers does not support frame rate mode."
    ::= { vtssQosCapabilities 56 }

vtssQosCapabilitiesPortStormFrameBurstMin OBJECT-TYPE
    SYNTAX      Unsigned32
    MAX-ACCESS  read-only
    STATUS      current
    DESCRIPTION 
        "Minimum supported burst size in frames for port storm policers using
         frame rate mode."
    ::= { vtssQosCapabilities 57 }

vtssQosCapabilitiesPortStormFrameBurstMax OBJECT-TYPE
    SYNTAX      Unsigned32
    MAX-ACCESS  read-only
    STATUS      current
    DESCRIPTION 
        "Maximum supported burst size in frames for port storm policers using
         frame rate mode."
    ::= { vtssQosCapabilities 58 }

vtssQosCapabilitiesDwrrCountMask OBJECT-TYPE
    SYNTAX      Unsigned32
    MAX-ACCESS  read-only
    STATUS      current
    DESCRIPTION 
        "A bitmask used to show allowed values of DwrrCount (zero is always
         allowed).
         
         Example:
         
         00100000 (0x20): Allowed values are 0 and 6
         
         11111110 (0xFE): Allowed values are 0 and 2..8"
    ::= { vtssQosCapabilities 101 }

vtssQosCapabilitiesHasGlobalStormPolicers OBJECT-TYPE
    SYNTAX      TruthValue
    MAX-ACCESS  read-only
    STATUS      current
    DESCRIPTION 
        "If true, the platform supports global storm policers."
    ::= { vtssQosCapabilities 201 }

vtssQosCapabilitiesHasPortStormPolicers OBJECT-TYPE
    SYNTAX      TruthValue
    MAX-ACCESS  read-only
    STATUS      current
    DESCRIPTION 
        "If true, the platform supports per port storm policers."
    ::= { vtssQosCapabilities 202 }

vtssQosCapabilitiesHasPortQueuePolicers OBJECT-TYPE
    SYNTAX      TruthValue
    MAX-ACCESS  read-only
    STATUS      current
    DESCRIPTION 
        "If true, the platform supports per port queue policers."
    ::= { vtssQosCapabilities 203 }

vtssQosCapabilitiesHasWredV1 OBJECT-TYPE
    SYNTAX      TruthValue
    MAX-ACCESS  read-only
    STATUS      current
    DESCRIPTION 
        "If true, the platform supports WRED version 1."
    ::= { vtssQosCapabilities 204 }

vtssQosCapabilitiesHasWredV2 OBJECT-TYPE
    SYNTAX      TruthValue
    MAX-ACCESS  read-only
    STATUS      current
    DESCRIPTION 
        "If true, the platform supports WRED version 2."
    ::= { vtssQosCapabilities 205 }

vtssQosCapabilitiesHasFixedTagCosMap OBJECT-TYPE
    SYNTAX      TruthValue
    MAX-ACCESS  read-only
    STATUS      current
    DESCRIPTION 
        "If true, the platform supports fixed tag to cos mapping only."
    ::= { vtssQosCapabilities 206 }

vtssQosCapabilitiesHasTagClassification OBJECT-TYPE
    SYNTAX      TruthValue
    MAX-ACCESS  read-only
    STATUS      current
    DESCRIPTION 
        "If true, the platform supports using VLAN tag for classification."
    ::= { vtssQosCapabilities 207 }

vtssQosCapabilitiesHasTagRemarking OBJECT-TYPE
    SYNTAX      TruthValue
    MAX-ACCESS  read-only
    STATUS      current
    DESCRIPTION 
        "If true, the platform supports VLAN tag remarking."
    ::= { vtssQosCapabilities 208 }

vtssQosCapabilitiesHasDscp OBJECT-TYPE
    SYNTAX      TruthValue
    MAX-ACCESS  read-only
    STATUS      current
    DESCRIPTION 
        "If true, the platform supports DSCP translation and remarking."
    ::= { vtssQosCapabilities 209 }

vtssQosCapabilitiesHasDscpDplClassification OBJECT-TYPE
    SYNTAX      TruthValue
    MAX-ACCESS  read-only
    STATUS      current
    DESCRIPTION 
        "If true, the platform supports DPL based DSCP classification."
    ::= { vtssQosCapabilities 210 }

vtssQosCapabilitiesHasDscpDplRemarking OBJECT-TYPE
    SYNTAX      TruthValue
    MAX-ACCESS  read-only
    STATUS      current
    DESCRIPTION 
        "If true, the platform supports DPL based DSCP remarking."
    ::= { vtssQosCapabilities 211 }

vtssQosCapabilitiesHasPortPolicersFc OBJECT-TYPE
    SYNTAX      TruthValue
    MAX-ACCESS  read-only
    STATUS      current
    DESCRIPTION 
        "If true, the platform supports flow control in port policers."
    ::= { vtssQosCapabilities 212 }

vtssQosCapabilitiesHasQueuePolicersFc OBJECT-TYPE
    SYNTAX      TruthValue
    MAX-ACCESS  read-only
    STATUS      current
    DESCRIPTION 
        "If true, the platform supports flow control in queue policers."
    ::= { vtssQosCapabilities 213 }

vtssQosCapabilitiesHasPortShapersDlb OBJECT-TYPE
    SYNTAX      TruthValue
    MAX-ACCESS  read-only
    STATUS      current
    DESCRIPTION 
        "If true, the platform supports dual leaky bucket egress port shapers."
    ::= { vtssQosCapabilities 214 }

vtssQosCapabilitiesHasQueueShapersDlb OBJECT-TYPE
    SYNTAX      TruthValue
    MAX-ACCESS  read-only
    STATUS      current
    DESCRIPTION 
        "If true, the platform supports dual leaky bucket egress queue shapers."
    ::= { vtssQosCapabilities 215 }

vtssQosCapabilitiesHasQueueShapersExcess OBJECT-TYPE
    SYNTAX      TruthValue
    MAX-ACCESS  read-only
    STATUS      current
    DESCRIPTION 
        "If true, the platform supports excess bandwidth in egress queue
         shapers."
    ::= { vtssQosCapabilities 216 }

vtssQosCapabilitiesHasWredV3 OBJECT-TYPE
    SYNTAX      TruthValue
    MAX-ACCESS  read-only
    STATUS      current
    DESCRIPTION 
        "If true, the platform supports WRED version 3."
    ::= { vtssQosCapabilities 217 }

vtssQosCapabilitiesHasQce OBJECT-TYPE
    SYNTAX      TruthValue
    MAX-ACCESS  read-only
    STATUS      current
    DESCRIPTION 
        "If true, the platform supports QCEs."
    ::= { vtssQosCapabilities 301 }

vtssQosCapabilitiesHasQceAddressMode OBJECT-TYPE
    SYNTAX      TruthValue
    MAX-ACCESS  read-only
    STATUS      current
    DESCRIPTION 
        "If true, the platform supports QCE address mode."
    ::= { vtssQosCapabilities 302 }

vtssQosCapabilitiesHasQceKeyType OBJECT-TYPE
    SYNTAX      TruthValue
    MAX-ACCESS  read-only
    STATUS      current
    DESCRIPTION 
        "If true, the platform supports QCE key type."
    ::= { vtssQosCapabilities 303 }

vtssQosCapabilitiesHasQceMacOui OBJECT-TYPE
    SYNTAX      TruthValue
    MAX-ACCESS  read-only
    STATUS      current
    DESCRIPTION 
        "If true, the platform supports QCE MAC OUI part only (24 most
         significant bits)."
    ::= { vtssQosCapabilities 304 }

vtssQosCapabilitiesHasQceDmac OBJECT-TYPE
    SYNTAX      TruthValue
    MAX-ACCESS  read-only
    STATUS      current
    DESCRIPTION 
        "If true, the platform supports QCE destination MAC keys."
    ::= { vtssQosCapabilities 305 }

vtssQosCapabilitiesHasQceDip OBJECT-TYPE
    SYNTAX      TruthValue
    MAX-ACCESS  read-only
    STATUS      current
    DESCRIPTION 
        "If true, the platform supports QCE destination IP keys."
    ::= { vtssQosCapabilities 306 }

vtssQosCapabilitiesHasQceCTag OBJECT-TYPE
    SYNTAX      TruthValue
    MAX-ACCESS  read-only
    STATUS      current
    DESCRIPTION 
        "If true, the platform supports QCE VLAN C-TAG keys."
    ::= { vtssQosCapabilities 307 }

vtssQosCapabilitiesHasQceSTag OBJECT-TYPE
    SYNTAX      TruthValue
    MAX-ACCESS  read-only
    STATUS      current
    DESCRIPTION 
        "If true, the platform supports QCE VLAN S-TAG keys."
    ::= { vtssQosCapabilities 308 }

vtssQosCapabilitiesHasQceInnerTag OBJECT-TYPE
    SYNTAX      TruthValue
    MAX-ACCESS  read-only
    STATUS      current
    DESCRIPTION 
        "If true, the platform supports QCE inner VLAN tag keys."
    ::= { vtssQosCapabilities 309 }

vtssQosCapabilitiesHasQceActionPcpDei OBJECT-TYPE
    SYNTAX      TruthValue
    MAX-ACCESS  read-only
    STATUS      current
    DESCRIPTION 
        "If true, the platform supports QCE PCP and DEI actions."
    ::= { vtssQosCapabilities 310 }

vtssQosCapabilitiesHasQceActionPolicy OBJECT-TYPE
    SYNTAX      TruthValue
    MAX-ACCESS  read-only
    STATUS      current
    DESCRIPTION 
        "If true, the platform supports QCE policy actions."
    ::= { vtssQosCapabilities 311 }

vtssQosCapabilitiesHasShapersRt OBJECT-TYPE
    SYNTAX      TruthValue
    MAX-ACCESS  read-only
    STATUS      current
    DESCRIPTION 
        "If true, the platform supports rate-type configurable egress shapers."
    ::= { vtssQosCapabilities 312 }

vtssQosConfig OBJECT IDENTIFIER
    ::= { vtssQosMibObjects 2 }

vtssQosConfigGlobals OBJECT IDENTIFIER
    ::= { vtssQosConfig 1 }

vtssQosConfigGlobalsStormPolicers OBJECT IDENTIFIER
    ::= { vtssQosConfigGlobals 1 }

vtssQosConfigGlobalsStormPolicersUnicast OBJECT IDENTIFIER
    ::= { vtssQosConfigGlobalsStormPolicers 1 }

vtssQosConfigGlobalsStormPolicersUnicastEnable OBJECT-TYPE
    SYNTAX      TruthValue
    MAX-ACCESS  read-write
    STATUS      current
    DESCRIPTION 
        "If true, the storm policer is enabled.
         
         This object is only valid if QosCapabilitiesHasGlobalStormPolicers is
         true."
    ::= { vtssQosConfigGlobalsStormPolicersUnicast 1 }

vtssQosConfigGlobalsStormPolicersUnicastRate OBJECT-TYPE
    SYNTAX      Unsigned32
    MAX-ACCESS  read-write
    STATUS      current
    DESCRIPTION 
        "Configure the storm policer rate.
         
         Valid range is from the smallest value of
         QosCapabilitiesGlobalStormBitRateMin and
         QosCapabilitiesGlobalStormFrameRateMin to the largest value of
         QosCapabilitiesGlobalStormBitRateMax and
         QosCapabilitiesGlobalStormFrameRateMax.
         
         This object is only valid if QosCapabilitiesHasGlobalStormPolicers is
         true."
    ::= { vtssQosConfigGlobalsStormPolicersUnicast 2 }

vtssQosConfigGlobalsStormPolicersUnicastFrameRate OBJECT-TYPE
    SYNTAX      TruthValue
    MAX-ACCESS  read-write
    STATUS      current
    DESCRIPTION 
        "If true, the rate is measured in fps instead of kbps.
         
         fps (FrameRate == TRUE) is only valid if
         QosCapabilitiesGlobalStormFrameRateMax is non-zero.
         
         kbps (FrameRate == FALSE) is only valid if
         QosCapabilitiesGlobalStormBitRateMax is non-zero.
         
         This object is only valid if QosCapabilitiesHasGlobalStormPolicers is
         true."
    ::= { vtssQosConfigGlobalsStormPolicersUnicast 3 }

vtssQosConfigGlobalsStormPolicersMulticast OBJECT IDENTIFIER
    ::= { vtssQosConfigGlobalsStormPolicers 2 }

vtssQosConfigGlobalsStormPolicersMulticastEnable OBJECT-TYPE
    SYNTAX      TruthValue
    MAX-ACCESS  read-write
    STATUS      current
    DESCRIPTION 
        "If true, the storm policer is enabled.
         
         This object is only valid if QosCapabilitiesHasGlobalStormPolicers is
         true."
    ::= { vtssQosConfigGlobalsStormPolicersMulticast 1 }

vtssQosConfigGlobalsStormPolicersMulticastRate OBJECT-TYPE
    SYNTAX      Unsigned32
    MAX-ACCESS  read-write
    STATUS      current
    DESCRIPTION 
        "Configure the storm policer rate.
         
         Valid range is from the smallest value of
         QosCapabilitiesGlobalStormBitRateMin and
         QosCapabilitiesGlobalStormFrameRateMin to the largest value of
         QosCapabilitiesGlobalStormBitRateMax and
         QosCapabilitiesGlobalStormFrameRateMax.
         
         This object is only valid if QosCapabilitiesHasGlobalStormPolicers is
         true."
    ::= { vtssQosConfigGlobalsStormPolicersMulticast 2 }

vtssQosConfigGlobalsStormPolicersMulticastFrameRate OBJECT-TYPE
    SYNTAX      TruthValue
    MAX-ACCESS  read-write
    STATUS      current
    DESCRIPTION 
        "If true, the rate is measured in fps instead of kbps.
         
         fps (FrameRate == TRUE) is only valid if
         QosCapabilitiesGlobalStormFrameRateMax is non-zero.
         
         kbps (FrameRate == FALSE) is only valid if
         QosCapabilitiesGlobalStormBitRateMax is non-zero.
         
         This object is only valid if QosCapabilitiesHasGlobalStormPolicers is
         true."
    ::= { vtssQosConfigGlobalsStormPolicersMulticast 3 }

vtssQosConfigGlobalsStormPolicersBroadcast OBJECT IDENTIFIER
    ::= { vtssQosConfigGlobalsStormPolicers 3 }

vtssQosConfigGlobalsStormPolicersBroadcastEnable OBJECT-TYPE
    SYNTAX      TruthValue
    MAX-ACCESS  read-write
    STATUS      current
    DESCRIPTION 
        "If true, the storm policer is enabled.
         
         This object is only valid if QosCapabilitiesHasGlobalStormPolicers is
         true."
    ::= { vtssQosConfigGlobalsStormPolicersBroadcast 1 }

vtssQosConfigGlobalsStormPolicersBroadcastRate OBJECT-TYPE
    SYNTAX      Unsigned32
    MAX-ACCESS  read-write
    STATUS      current
    DESCRIPTION 
        "Configure the storm policer rate.
         
         Valid range is from the smallest value of
         QosCapabilitiesGlobalStormBitRateMin and
         QosCapabilitiesGlobalStormFrameRateMin to the largest value of
         QosCapabilitiesGlobalStormBitRateMax and
         QosCapabilitiesGlobalStormFrameRateMax.
         
         This object is only valid if QosCapabilitiesHasGlobalStormPolicers is
         true."
    ::= { vtssQosConfigGlobalsStormPolicersBroadcast 2 }

vtssQosConfigGlobalsStormPolicersBroadcastFrameRate OBJECT-TYPE
    SYNTAX      TruthValue
    MAX-ACCESS  read-write
    STATUS      current
    DESCRIPTION 
        "If true, the rate is measured in fps instead of kbps.
         
         fps (FrameRate == TRUE) is only valid if
         QosCapabilitiesGlobalStormFrameRateMax is non-zero.
         
         kbps (FrameRate == FALSE) is only valid if
         QosCapabilitiesGlobalStormBitRateMax is non-zero.
         
         This object is only valid if QosCapabilitiesHasGlobalStormPolicers is
         true."
    ::= { vtssQosConfigGlobalsStormPolicersBroadcast 3 }

vtssQosConfigGlobalsWredTable OBJECT-TYPE
    SYNTAX      SEQUENCE OF VTSSQosConfigGlobalsWredEntry
    MAX-ACCESS  not-accessible
    STATUS      current
    DESCRIPTION 
        "This table contains the configuration of WRED (Weighted Random Early
         Discard).
         
         This is an optional table and is only present if
         qosCapabilitiesHasWredV1, qosCapabilitiesHasWredV2 or
         qosCapabilitiesHasWredV3 is true."
    ::= { vtssQosConfigGlobals 2 }

vtssQosConfigGlobalsWredEntry OBJECT-TYPE
    SYNTAX      VTSSQosConfigGlobalsWredEntry
    MAX-ACCESS  not-accessible
    STATUS      current
    DESCRIPTION 
        "Each row contains the configuration for a specific WRED profile"
    INDEX       { vtssQosConfigGlobalsWredGroup, vtssQosConfigGlobalsWredQueue, vtssQosConfigGlobalsWredDpl }
    ::= { vtssQosConfigGlobalsWredTable 1 }

VTSSQosConfigGlobalsWredEntry ::= SEQUENCE {
    vtssQosConfigGlobalsWredGroup   Integer32,
    vtssQosConfigGlobalsWredQueue   Integer32,
    vtssQosConfigGlobalsWredDpl     Integer32,
    vtssQosConfigGlobalsWredEnable      TruthValue,
    vtssQosConfigGlobalsWredMinimumFillLevel    VTSSPercent,
    vtssQosConfigGlobalsWredMaximum     VTSSPercent,
    vtssQosConfigGlobalsWredMaxSelector     VTSSQosWredMaxSelector,
    vtssQosConfigGlobalsWredMaximumDp1      VTSSPercent,
    vtssQosConfigGlobalsWredMaximumDp2      VTSSPercent,
    vtssQosConfigGlobalsWredMaximumDp3      VTSSPercent
}

vtssQosConfigGlobalsWredGroup OBJECT-TYPE
    SYNTAX      Integer32 (1..3)
    MAX-ACCESS  not-accessible
    STATUS      current
    DESCRIPTION 
        "WRED group index."
    ::= { vtssQosConfigGlobalsWredEntry 1 }

vtssQosConfigGlobalsWredQueue OBJECT-TYPE
    SYNTAX      Integer32 (0..7)
    MAX-ACCESS  not-accessible
    STATUS      current
    DESCRIPTION 
        "Queue index."
    ::= { vtssQosConfigGlobalsWredEntry 2 }

vtssQosConfigGlobalsWredDpl OBJECT-TYPE
    SYNTAX      Integer32 (0..3)
    MAX-ACCESS  not-accessible
    STATUS      current
    DESCRIPTION 
        "DPL index."
    ::= { vtssQosConfigGlobalsWredEntry 3 }

vtssQosConfigGlobalsWredEnable OBJECT-TYPE
    SYNTAX      TruthValue
    MAX-ACCESS  read-write
    STATUS      current
    DESCRIPTION 
        "If true, RED is enabled for this queue."
    ::= { vtssQosConfigGlobalsWredEntry 4 }

vtssQosConfigGlobalsWredMinimumFillLevel OBJECT-TYPE
    SYNTAX      VTSSPercent
    MAX-ACCESS  read-write
    STATUS      current
    DESCRIPTION 
        "Controls the lower RED fill level threshold in percent of the whole
         queue.
         
         If the queue filling level is below this threshold, the drop
         probability is zero.
         
         Valid range is 0-100."
    ::= { vtssQosConfigGlobalsWredEntry 5 }

vtssQosConfigGlobalsWredMaximum OBJECT-TYPE
    SYNTAX      VTSSPercent
    MAX-ACCESS  read-write
    STATUS      current
    DESCRIPTION 
        "Controls the upper RED drop probability or fill level threshold for
         frames marked with Drop Precedence Level 1 (yellow frames).
         
         Valid range is 1-100.
         
         This object is only valid if QosCapabilitiesHasWredV2 or
         QosCapabilitiesHasWredV3 is true."
    ::= { vtssQosConfigGlobalsWredEntry 6 }

vtssQosConfigGlobalsWredMaxSelector OBJECT-TYPE
    SYNTAX      VTSSQosWredMaxSelector
    MAX-ACCESS  read-write
    STATUS      current
    DESCRIPTION 
        "Selects whether 'Maximum' controls 'Maximum Drop Probability' or
         'Maximum Fill Level'.
         
         This object is only valid if QosCapabilitiesHasWredV2 or
         QosCapabilitiesHasWredV3 is true."
    ::= { vtssQosConfigGlobalsWredEntry 7 }

vtssQosConfigGlobalsWredMaximumDp1 OBJECT-TYPE
    SYNTAX      VTSSPercent
    MAX-ACCESS  read-write
    STATUS      current
    DESCRIPTION 
        "Controls the upper RED drop probability for frames marked with Drop
         Precedence Level 1 (yellow frames).
         
         Valid range is 0-100.
         
         This object is only valid if QosCapabilitiesHasWredV1 is true."
    ::= { vtssQosConfigGlobalsWredEntry 8 }

vtssQosConfigGlobalsWredMaximumDp2 OBJECT-TYPE
    SYNTAX      VTSSPercent
    MAX-ACCESS  read-write
    STATUS      current
    DESCRIPTION 
        "Controls the upper RED drop probability for frames marked with Drop
         Precedence Level 2 (yellow frames).
         
         Valid range is 0-100.
         
         This object is only valid if QosCapabilitiesHasWredV1 is true."
    ::= { vtssQosConfigGlobalsWredEntry 9 }

vtssQosConfigGlobalsWredMaximumDp3 OBJECT-TYPE
    SYNTAX      VTSSPercent
    MAX-ACCESS  read-write
    STATUS      current
    DESCRIPTION 
        "Controls the upper RED drop probability for frames marked with Drop
         Precedence Level 3 (yellow frames).
         
         Valid range is 0-100.
         
         This object is only valid if QosCapabilitiesHasWredV1 is true."
    ::= { vtssQosConfigGlobalsWredEntry 10 }

vtssQosConfigGlobalsDscpTable OBJECT-TYPE
    SYNTAX      SEQUENCE OF VTSSQosConfigGlobalsDscpEntry
    MAX-ACCESS  not-accessible
    STATUS      current
    DESCRIPTION 
        "This table has 64 entries, one for each DSCP value.
         
         This is an optional table and is only present if qosCapabilitiesHasDscp
         is true."
    ::= { vtssQosConfigGlobals 3 }

vtssQosConfigGlobalsDscpEntry OBJECT-TYPE
    SYNTAX      VTSSQosConfigGlobalsDscpEntry
    MAX-ACCESS  not-accessible
    STATUS      current
    DESCRIPTION 
        "Each row contains the configuration for a specific DSCP"
    INDEX       { vtssQosConfigGlobalsDscpDscp }
    ::= { vtssQosConfigGlobalsDscpTable 1 }

VTSSQosConfigGlobalsDscpEntry ::= SEQUENCE {
    vtssQosConfigGlobalsDscpDscp    Dscp,
    vtssQosConfigGlobalsDscpTrust   TruthValue,
    vtssQosConfigGlobalsDscpCos     Unsigned32,
    vtssQosConfigGlobalsDscpDpl     VTSSUnsigned8,
    vtssQosConfigGlobalsDscpIngressTranslation      Dscp,
    vtssQosConfigGlobalsDscpClassify    TruthValue,
    vtssQosConfigGlobalsDscpEgressTranslation   Dscp,
    vtssQosConfigGlobalsDscpEgressTranslationDp1    Dscp
}

vtssQosConfigGlobalsDscpDscp OBJECT-TYPE
    SYNTAX      Dscp
    MAX-ACCESS  not-accessible
    STATUS      current
    DESCRIPTION 
        "DSCP index."
    ::= { vtssQosConfigGlobalsDscpEntry 1 }

vtssQosConfigGlobalsDscpTrust OBJECT-TYPE
    SYNTAX      TruthValue
    MAX-ACCESS  read-write
    STATUS      current
    DESCRIPTION 
        "If true, this DSCP value is trusted. Packets arriving on interfaces
         where 'TrustDscp' is enabled will be classified to the corresponding
         CoS and DPL in this table."
    ::= { vtssQosConfigGlobalsDscpEntry 2 }

vtssQosConfigGlobalsDscpCos OBJECT-TYPE
    SYNTAX      Unsigned32
    MAX-ACCESS  read-write
    STATUS      current
    DESCRIPTION 
        "The CoS value which the DSCP value maps to.
         
         Valid range is qosCapabilitiesClassMin-qosCapabilitiesClassMax."
    ::= { vtssQosConfigGlobalsDscpEntry 3 }

vtssQosConfigGlobalsDscpDpl OBJECT-TYPE
    SYNTAX      VTSSUnsigned8
    MAX-ACCESS  read-write
    STATUS      current
    DESCRIPTION 
        "The DPL (Drop Precedence Level) which the DSCP value maps to.
         
         Valid range is qosCapabilitiesDplMin-qosCapabilitiesDplMax."
    ::= { vtssQosConfigGlobalsDscpEntry 4 }

vtssQosConfigGlobalsDscpIngressTranslation OBJECT-TYPE
    SYNTAX      Dscp
    MAX-ACCESS  read-write
    STATUS      current
    DESCRIPTION 
        "The new classified DSCP value which the original DSCP value is replaced
         with if 'DscpTranslate' is enabled on the interface"
    ::= { vtssQosConfigGlobalsDscpEntry 5 }

vtssQosConfigGlobalsDscpClassify OBJECT-TYPE
    SYNTAX      TruthValue
    MAX-ACCESS  read-write
    STATUS      current
    DESCRIPTION 
        "If true, then packets received on interfaces where 'DscpClassify' is
         set to 'selected' will be classified to a new DSCP value based on the
         values configured in the qosConfigGlobalsCosToDscpTable."
    ::= { vtssQosConfigGlobalsDscpEntry 6 }

vtssQosConfigGlobalsDscpEgressTranslation OBJECT-TYPE
    SYNTAX      Dscp
    MAX-ACCESS  read-write
    STATUS      current
    DESCRIPTION 
        "The new DSCP value that will be written into the packet at egress if
         'DscpRemark' on the interface is set to 'remap' or 'remap-dp'.
         
         If 'remap-dp' is set then only packets classified to Dpl 0 will use
         this table."
    ::= { vtssQosConfigGlobalsDscpEntry 7 }

vtssQosConfigGlobalsDscpEgressTranslationDp1 OBJECT-TYPE
    SYNTAX      Dscp
    MAX-ACCESS  read-write
    STATUS      current
    DESCRIPTION 
        "The new DSCP value that will be written into the packet at egress if
         'DscpRemark' on the interface is set to 'remap-dp'.
         
         Only packets classified to Dpl 1 will use this table.
         
         This object is only valid if QosCapabilitiesHasDscpDplRemarking is
         true."
    ::= { vtssQosConfigGlobalsDscpEntry 8 }

vtssQosConfigGlobalsCosToDscpTable OBJECT-TYPE
    SYNTAX      SEQUENCE OF VTSSQosConfigGlobalsCosToDscpEntry
    MAX-ACCESS  not-accessible
    STATUS      current
    DESCRIPTION 
        "This table has 8 entries, one for each Cos value.
         
         This is an optional table and is only present if qosCapabilitiesHasDscp
         is true."
    ::= { vtssQosConfigGlobals 4 }

vtssQosConfigGlobalsCosToDscpEntry OBJECT-TYPE
    SYNTAX      VTSSQosConfigGlobalsCosToDscpEntry
    MAX-ACCESS  not-accessible
    STATUS      current
    DESCRIPTION 
        "Each row contains the configuration for a specific Cos"
    INDEX       { vtssQosConfigGlobalsCosToDscpCos }
    ::= { vtssQosConfigGlobalsCosToDscpTable 1 }

VTSSQosConfigGlobalsCosToDscpEntry ::= SEQUENCE {
    vtssQosConfigGlobalsCosToDscpCos    Integer32,
    vtssQosConfigGlobalsCosToDscpDscp   Dscp,
    vtssQosConfigGlobalsCosToDscpDscpDp1    Dscp,
    vtssQosConfigGlobalsCosToDscpDscpDp2    Dscp,
    vtssQosConfigGlobalsCosToDscpDscpDp3    Dscp
}

vtssQosConfigGlobalsCosToDscpCos OBJECT-TYPE
    SYNTAX      Integer32 (0..7)
    MAX-ACCESS  not-accessible
    STATUS      current
    DESCRIPTION 
        "CoS index."
    ::= { vtssQosConfigGlobalsCosToDscpEntry 1 }

vtssQosConfigGlobalsCosToDscpDscp OBJECT-TYPE
    SYNTAX      Dscp
    MAX-ACCESS  read-write
    STATUS      current
    DESCRIPTION 
        "If qosCapabilitiesHasDscpDplClassification is true: This is the DSCP
         value which the classified CoS value maps to when the classified DPL is
         0.
         
         If qosCapabilitiesHasDscpDplClassification is false: This is the DSCP
         value which the classified CoS value maps to."
    ::= { vtssQosConfigGlobalsCosToDscpEntry 2 }

vtssQosConfigGlobalsCosToDscpDscpDp1 OBJECT-TYPE
    SYNTAX      Dscp
    MAX-ACCESS  read-write
    STATUS      current
    DESCRIPTION 
        "The DSCP value which the classified CoS value maps to when the
         classified DPL is 1.
         
         This object is only valid if QosCapabilitiesHasDscpDplClassification is
         true."
    ::= { vtssQosConfigGlobalsCosToDscpEntry 3 }

vtssQosConfigGlobalsCosToDscpDscpDp2 OBJECT-TYPE
    SYNTAX      Dscp
    MAX-ACCESS  read-write
    STATUS      current
    DESCRIPTION 
        "The DSCP value which the classified CoS value maps to when the
         classified DPL is 2.
         
         This object is only valid if QosCapabilitiesHasDscpDplClassification is
         true and QosCapabilitiesDplMax is greater than 1."
    ::= { vtssQosConfigGlobalsCosToDscpEntry 4 }

vtssQosConfigGlobalsCosToDscpDscpDp3 OBJECT-TYPE
    SYNTAX      Dscp
    MAX-ACCESS  read-write
    STATUS      current
    DESCRIPTION 
        "The DSCP value which the classified CoS value maps to when the
         classified DPL is 3.
         
         This object is only valid if QosCapabilitiesHasDscpDplClassification is
         true and QosCapabilitiesDplMax is greater than 2."
    ::= { vtssQosConfigGlobalsCosToDscpEntry 5 }

vtssQosConfigInterface OBJECT IDENTIFIER
    ::= { vtssQosConfig 2 }

vtssQosConfigInterfaceTable OBJECT-TYPE
    SYNTAX      SEQUENCE OF VTSSQosConfigInterfaceEntry
    MAX-ACCESS  not-accessible
    STATUS      current
    DESCRIPTION 
        "This table provides QoS configuration for QoS manageable interfaces"
    ::= { vtssQosConfigInterface 1 }

vtssQosConfigInterfaceEntry OBJECT-TYPE
    SYNTAX      VTSSQosConfigInterfaceEntry
    MAX-ACCESS  not-accessible
    STATUS      current
    DESCRIPTION 
        "Each row contains the configuration for a specific interface"
    INDEX       { vtssQosConfigInterfaceIfIndex }
    ::= { vtssQosConfigInterfaceTable 1 }

VTSSQosConfigInterfaceEntry ::= SEQUENCE {
    vtssQosConfigInterfaceIfIndex   VTSSInterfaceIndex,
    vtssQosConfigInterfaceCos   Unsigned32,
    vtssQosConfigInterfaceDpl   VTSSUnsigned8,
    vtssQosConfigInterfacePcp   Unsigned32,
    vtssQosConfigInterfaceDei   VTSSUnsigned8,
    vtssQosConfigInterfaceTrustTag      TruthValue,
    vtssQosConfigInterfaceTrustDscp     TruthValue,
    vtssQosConfigInterfaceDwrrCount     VTSSUnsigned8,
    vtssQosConfigInterfaceTagRemarkingMode      VTSSQosTagRemarkingMode,
    vtssQosConfigInterfaceTagPcp    Unsigned32,
    vtssQosConfigInterfaceTagDei    VTSSUnsigned8,
    vtssQosConfigInterfaceDscpTranslate     TruthValue,
    vtssQosConfigInterfaceDscpClassify      VTSSQosDscpClassify,
    vtssQosConfigInterfaceDscpRemark    VTSSQosDscpRemark,
    vtssQosConfigInterfaceQceAddressMode    TruthValue,
    vtssQosConfigInterfaceQceKeyType    VTSSVcapKeyType,
    vtssQosConfigInterfaceWredGroup     Unsigned32
}

vtssQosConfigInterfaceIfIndex OBJECT-TYPE
    SYNTAX      VTSSInterfaceIndex
    MAX-ACCESS  not-accessible
    STATUS      current
    DESCRIPTION 
        "Logical interface index."
    ::= { vtssQosConfigInterfaceEntry 1 }

vtssQosConfigInterfaceCos OBJECT-TYPE
    SYNTAX      Unsigned32
    MAX-ACCESS  read-write
    STATUS      current
    DESCRIPTION 
        "The default CoS value a packet is classified to.
         
         Valid range is qosCapabilitiesClassMin-qosCapabilitiesClassMax."
    ::= { vtssQosConfigInterfaceEntry 2 }

vtssQosConfigInterfaceDpl OBJECT-TYPE
    SYNTAX      VTSSUnsigned8
    MAX-ACCESS  read-write
    STATUS      current
    DESCRIPTION 
        "The default DPL (Drop Precedence Level) a packet is classified to.
         
         Valid range is qosCapabilitiesDplMin-qosCapabilitiesDplMax."
    ::= { vtssQosConfigInterfaceEntry 3 }

vtssQosConfigInterfacePcp OBJECT-TYPE
    SYNTAX      Unsigned32
    MAX-ACCESS  read-write
    STATUS      current
    DESCRIPTION 
        "The default PCP value a packet is classified to.
         
         Valid range is 0-7.
         
         This object is only valid if QosCapabilitiesHasFixedTagCosMap is false."
    ::= { vtssQosConfigInterfaceEntry 4 }

vtssQosConfigInterfaceDei OBJECT-TYPE
    SYNTAX      VTSSUnsigned8
    MAX-ACCESS  read-write
    STATUS      current
    DESCRIPTION 
        "The default DEI value a packet is classified to.
         
         Valid range is 0-1.
         
         This object is only valid if QosCapabilitiesHasFixedTagCosMap is false."
    ::= { vtssQosConfigInterfaceEntry 5 }

vtssQosConfigInterfaceTrustTag OBJECT-TYPE
    SYNTAX      TruthValue
    MAX-ACCESS  read-write
    STATUS      current
    DESCRIPTION 
        "If true and the packet is VLAN tagged, then the CoS and DPL assigned to
         the packet is the PCP and DEI value in the packet mapped to a CoS and
         DPL value defined in the qosConfigInterfaceTagToCosTable.
         
         This object is only valid if QosCapabilitiesHasFixedTagCosMap is false
         and QosCapabilitiesHasTagClassification is true."
    ::= { vtssQosConfigInterfaceEntry 6 }

vtssQosConfigInterfaceTrustDscp OBJECT-TYPE
    SYNTAX      TruthValue
    MAX-ACCESS  read-write
    STATUS      current
    DESCRIPTION 
        "If true and the packet type is IPv4 or IPv6 and the packet DSCP value
         is trusted in qosConfigGlobalsDscpTable, then the CoS and DPL assigned
         to the packet is the DSCP value in the packet mapped to a CoS and DPL
         value defined in the qosConfigGlobalsDscpTable.
         
         This object is only valid if QosCapabilitiesHasDscp is true."
    ::= { vtssQosConfigInterfaceEntry 7 }

vtssQosConfigInterfaceDwrrCount OBJECT-TYPE
    SYNTAX      VTSSUnsigned8
    MAX-ACCESS  read-write
    STATUS      current
    DESCRIPTION 
        "The number of queues that are running Deficit Weighted Round Robin
         scheduling.
         
         This value is restricted to 0 or one of the values defined by
         qosCapabilitiesDwrrCountMask."
    ::= { vtssQosConfigInterfaceEntry 8 }

vtssQosConfigInterfaceTagRemarkingMode OBJECT-TYPE
    SYNTAX      VTSSQosTagRemarkingMode
    MAX-ACCESS  read-write
    STATUS      current
    DESCRIPTION 
        "Selects the tag remarking mode for egress. Valid values are:
         
         'classified' : Remark the tag with the classified values of PCP and
         DEI.
         
         'default' : Remark the tag with the configured TagPcp and TagDei.
         
         'mapped' : Remark the tag with the values from the classified CoS and
         DPL mapped through the qosConfigInterfaceCosToTagTable.
         
         This object is only valid if QosCapabilitiesHasTagRemarking is true."
    ::= { vtssQosConfigInterfaceEntry 9 }

vtssQosConfigInterfaceTagPcp OBJECT-TYPE
    SYNTAX      Unsigned32
    MAX-ACCESS  read-write
    STATUS      current
    DESCRIPTION 
        "The PCP value to put in the packet if TagRemarkingMode is set to
         'default'.
         
         Valid range is 0-7.
         
         This object is only valid if QosCapabilitiesHasTagRemarking is true."
    ::= { vtssQosConfigInterfaceEntry 10 }

vtssQosConfigInterfaceTagDei OBJECT-TYPE
    SYNTAX      VTSSUnsigned8
    MAX-ACCESS  read-write
    STATUS      current
    DESCRIPTION 
        "The DEI value to put in the packet if TagRemarkingMode is set to
         'default'.
         
         Valid range is 0-1.
         
         This object is only valid if QosCapabilitiesHasTagRemarking is true."
    ::= { vtssQosConfigInterfaceEntry 11 }

vtssQosConfigInterfaceDscpTranslate OBJECT-TYPE
    SYNTAX      TruthValue
    MAX-ACCESS  read-write
    STATUS      current
    DESCRIPTION 
        "If true then the classified DSCP value is the DSCP value in the packed
         mapped to a new DSCP value defined in
         qosConfigGlobalsDscpTable.IngressTranslation.
         
         This object is only valid if QosCapabilitiesHasDscp is true."
    ::= { vtssQosConfigInterfaceEntry 12 }

vtssQosConfigInterfaceDscpClassify OBJECT-TYPE
    SYNTAX      VTSSQosDscpClassify
    MAX-ACCESS  read-write
    STATUS      current
    DESCRIPTION 
        "If qosCapabilitiesHasDscpDplClassification is true: Selects if and how
         the classified DSCP is based on the classified CoS and DPL for IPv4 and
         IPv6 packets on ingress.
         
         If a packet is selected for being classified to a new DSCP, the
         classification in based on the classified CoS mapped to a new DSCP
         value through the qosConfigGlobalsCosToDscpTable. If the classified DPL
         is 1, the new DSCP value is taken from the DscpDp1 entry, otherwise it
         is taken from the Dscp entry. Valid values are:
         
         'none' : Always classify to the DSCP value in the received packet and
         ignore the classified CoS and DPL.
         
         'zero' : If the DSCP value in the received packet is 0, then classify
         to a new DSCP value based on the classified CoS and DPL.
         
         'selected' : If the DSCP value in the received packet is enabled in
         qosConfigGlobalsDscpTable.Classify, then classify to a new DSCP value
         based on the classified CoS and DPL.
         
         'all' : Always classify to a new DSCP value based on the classified CoS
         and DPL.
         
         
         
         If qosCapabilitiesHasDscpDplClassification is false: Selects if and how
         the classified DSCP is based on the classified CoS for IPv4 and IPv6
         packets on ingress.
         
         If a packet is selected for being classified to a new DSCP, the
         classification in based on the classified CoS mapped to a new DSCP
         value through the qosConfigGlobalsCosToDscpTable.Dscp Valid values are:
         
         'none' : Always classify to the DSCP value in the received packet and
         ignore the classified CoS.
         
         'zero' : If the DSCP value in the received packet is 0, then classify
         to a new DSCP value based on the classified CoS.
         
         'selected' : If the DSCP value in the received packet is enabled in
         qosConfigGlobalsDscpTable.Classify, then classify to a new DSCP value
         based on the classified CoS.
         
         'all' : Always classify to a new DSCP value based on the classified
         CoS.
         
         This object is only valid if QosCapabilitiesHasDscp is true."
    ::= { vtssQosConfigInterfaceEntry 13 }

vtssQosConfigInterfaceDscpRemark OBJECT-TYPE
    SYNTAX      VTSSQosDscpRemark
    MAX-ACCESS  read-write
    STATUS      current
    DESCRIPTION 
        "If qosCapabilitiesHasDscpDplRemarking is true: Selects if and how the
         classified DSCP is written into the packet at egress. Valid values are:
         
         'disabled' : Do not write the classified DSCP into the packet.
         
         'rewrite' : Write the classified DSCP into the packet.
         
         'remap' : Remap the classified DSCP through qosConfigGlobalsDscpTable,
         and write the value from EgressTranslation into the packet.
         
         'remap-dp' : Remap the classified DSCP through
         qosConfigGlobalsDscpTable. If the classified DPL is 0 then write the
         value from EgressTranslation into the packet, otherwise write the value
         from EgressTranslationDp1 into the packet.
         
         If qosCapabilitiesHasDscpDplRemarking is false: Selects if and how the
         classified DSCP is written into the packet at egress. Valid values are:
         
         'disabled' : Do not write the classified DSCP into the packet.
         
         'rewrite' : Write the classified DSCP into the packet.
         
         'remap' : Remap the classified DSCP through qosConfigGlobalsDscpTable,
         and write the value from EgressTranslation into the packet.
         
         This object is only valid if QosCapabilitiesHasDscp is true."
    ::= { vtssQosConfigInterfaceEntry 14 }

vtssQosConfigInterfaceQceAddressMode OBJECT-TYPE
    SYNTAX      TruthValue
    MAX-ACCESS  read-write
    STATUS      current
    DESCRIPTION 
        "If false, the QCE classification for this interface is based on source
         (SMAC/SIP) addresses.
         
         If true, the QCE classification for this interface is based on
         destination (DMAC/DIP) addresses.
         
         This parameter is only used when QosCapabilitiesHasQceKeyType is false
         or QceKeyType is normal.
         
         This object is only valid if QosCapabilitiesHasQceAddressMode is true."
    ::= { vtssQosConfigInterfaceEntry 15 }

vtssQosConfigInterfaceQceKeyType OBJECT-TYPE
    SYNTAX      VTSSVcapKeyType
    MAX-ACCESS  read-write
    STATUS      current
    DESCRIPTION 
        "The key type specifying the key generated for packets received on the
         interface. Valid values are:
         
         'normal' : Half key, match outer tag, SIP and SMAC.
         
         'double-tag' : Quarter key, match inner and outer tag.
         
         'ip-addr' : Half key, match inner and outer tag, SIP and DIP. For
         non-IP frames, match outer tag only.
         
         'mac-ip-addr' : Full key, match inner and outer tag, SMAC, DMAC, SIP
         and DIP.
         
         Filtering on DMAC type (unicast/multicast/broadcast) is supported for
         any key type.
         
         This object is only valid if QosCapabilitiesHasQceKeyType is true."
    ::= { vtssQosConfigInterfaceEntry 16 }

vtssQosConfigInterfaceWredGroup OBJECT-TYPE
    SYNTAX      Unsigned32
    MAX-ACCESS  read-write
    STATUS      current
    DESCRIPTION 
        "The WRED group an interface is a member of.
         
         This object is only valid if QosCapabilitiesHasWredV3 is true."
    ::= { vtssQosConfigInterfaceEntry 17 }

vtssQosConfigInterfaceTagToCosTable OBJECT-TYPE
    SYNTAX      SEQUENCE OF VTSSQosConfigInterfaceTagToCosEntry
    MAX-ACCESS  not-accessible
    STATUS      current
    DESCRIPTION 
        "This table contains the mapping of (interface, PCP, DEI) to (CoS, DPL)
         values.
         
         The mappings given by this table is used for all tagged packets
         received on an interface if and only if that interface has the value of
         TrustTag set to 'true'
         
         This is an optional table and is only present if
         QosCapabilitiesHasFixedTagCosMap is false and
         QosCapabilitiesHasTagClassification is true."
    ::= { vtssQosConfigInterface 2 }

vtssQosConfigInterfaceTagToCosEntry OBJECT-TYPE
    SYNTAX      VTSSQosConfigInterfaceTagToCosEntry
    MAX-ACCESS  not-accessible
    STATUS      current
    DESCRIPTION 
        "Each row contains the mapping from (interface, PCP, DEI) to (CoS, DPL)
         values."
    INDEX       { vtssQosConfigInterfaceTagToCosIfIndex, vtssQosConfigInterfaceTagToCosPcp, vtssQosConfigInterfaceTagToCosDei }
    ::= { vtssQosConfigInterfaceTagToCosTable 1 }

VTSSQosConfigInterfaceTagToCosEntry ::= SEQUENCE {
    vtssQosConfigInterfaceTagToCosIfIndex   VTSSInterfaceIndex,
    vtssQosConfigInterfaceTagToCosPcp   Integer32,
    vtssQosConfigInterfaceTagToCosDei   Integer32,
    vtssQosConfigInterfaceTagToCosCos   Unsigned32,
    vtssQosConfigInterfaceTagToCosDpl   VTSSUnsigned8
}

vtssQosConfigInterfaceTagToCosIfIndex OBJECT-TYPE
    SYNTAX      VTSSInterfaceIndex
    MAX-ACCESS  not-accessible
    STATUS      current
    DESCRIPTION 
        "Logical interface index."
    ::= { vtssQosConfigInterfaceTagToCosEntry 1 }

vtssQosConfigInterfaceTagToCosPcp OBJECT-TYPE
    SYNTAX      Integer32 (0..7)
    MAX-ACCESS  not-accessible
    STATUS      current
    DESCRIPTION 
        "PCP index."
    ::= { vtssQosConfigInterfaceTagToCosEntry 2 }

vtssQosConfigInterfaceTagToCosDei OBJECT-TYPE
    SYNTAX      Integer32 (0..1)
    MAX-ACCESS  not-accessible
    STATUS      current
    DESCRIPTION 
        "DEI index."
    ::= { vtssQosConfigInterfaceTagToCosEntry 3 }

vtssQosConfigInterfaceTagToCosCos OBJECT-TYPE
    SYNTAX      Unsigned32
    MAX-ACCESS  read-write
    STATUS      current
    DESCRIPTION 
        "The CoS value which this entry maps to.
         
         Valid range is qosCapabilitiesClassMin-qosCapabilitiesClassMax."
    ::= { vtssQosConfigInterfaceTagToCosEntry 4 }

vtssQosConfigInterfaceTagToCosDpl OBJECT-TYPE
    SYNTAX      VTSSUnsigned8
    MAX-ACCESS  read-write
    STATUS      current
    DESCRIPTION 
        "The DPL (Drop Precedence Level) value which this entry maps to.
         
         Valid range is qosCapabilitiesDplMin-qosCapabilitiesDplMax."
    ::= { vtssQosConfigInterfaceTagToCosEntry 5 }

vtssQosConfigInterfaceCosToTagTable OBJECT-TYPE
    SYNTAX      SEQUENCE OF VTSSQosConfigInterfaceCosToTagEntry
    MAX-ACCESS  not-accessible
    STATUS      current
    DESCRIPTION 
        "This table contains the mapping of (interface, CoS, DPL) to (PCP, DEI)
         values.
         
         The mappings given by this table is used for packets transmitted on an
         interface if and only if that interface has the value of
         TagRemarkingMode set to 'mapped'
         
         This is an optional table and is only present if
         QosCapabilitiesHasTagRemarking is true."
    ::= { vtssQosConfigInterface 3 }

vtssQosConfigInterfaceCosToTagEntry OBJECT-TYPE
    SYNTAX      VTSSQosConfigInterfaceCosToTagEntry
    MAX-ACCESS  not-accessible
    STATUS      current
    DESCRIPTION 
        "Each row contains the mapping from (interface, CoS, DPL) to (PCP, DEI)
         values."
    INDEX       { vtssQosConfigInterfaceCosToTagIfIndex, vtssQosConfigInterfaceCosToTagCos, vtssQosConfigInterfaceCosToTagDpl }
    ::= { vtssQosConfigInterfaceCosToTagTable 1 }

VTSSQosConfigInterfaceCosToTagEntry ::= SEQUENCE {
    vtssQosConfigInterfaceCosToTagIfIndex   VTSSInterfaceIndex,
    vtssQosConfigInterfaceCosToTagCos   Integer32,
    vtssQosConfigInterfaceCosToTagDpl   Integer32,
    vtssQosConfigInterfaceCosToTagPcp   Unsigned32,
    vtssQosConfigInterfaceCosToTagDei   VTSSUnsigned8
}

vtssQosConfigInterfaceCosToTagIfIndex OBJECT-TYPE
    SYNTAX      VTSSInterfaceIndex
    MAX-ACCESS  not-accessible
    STATUS      current
    DESCRIPTION 
        "Logical interface index."
    ::= { vtssQosConfigInterfaceCosToTagEntry 1 }

vtssQosConfigInterfaceCosToTagCos OBJECT-TYPE
    SYNTAX      Integer32 (0..7)
    MAX-ACCESS  not-accessible
    STATUS      current
    DESCRIPTION 
        "CoS index."
    ::= { vtssQosConfigInterfaceCosToTagEntry 2 }

vtssQosConfigInterfaceCosToTagDpl OBJECT-TYPE
    SYNTAX      Integer32 (0..3)
    MAX-ACCESS  not-accessible
    STATUS      current
    DESCRIPTION 
        "DPL index."
    ::= { vtssQosConfigInterfaceCosToTagEntry 3 }

vtssQosConfigInterfaceCosToTagPcp OBJECT-TYPE
    SYNTAX      Unsigned32
    MAX-ACCESS  read-write
    STATUS      current
    DESCRIPTION 
        "The PCP value which this entry maps to.
         
         Valid range is 0-7."
    ::= { vtssQosConfigInterfaceCosToTagEntry 4 }

vtssQosConfigInterfaceCosToTagDei OBJECT-TYPE
    SYNTAX      VTSSUnsigned8
    MAX-ACCESS  read-write
    STATUS      current
    DESCRIPTION 
        "The DEI value which this entry maps to.
         
         Valid range is 0-1."
    ::= { vtssQosConfigInterfaceCosToTagEntry 5 }

vtssQosConfigInterfacePolicerTable OBJECT-TYPE
    SYNTAX      SEQUENCE OF VTSSQosConfigInterfacePolicerEntry
    MAX-ACCESS  not-accessible
    STATUS      current
    DESCRIPTION 
        "This table provides policer configuration for an interface"
    ::= { vtssQosConfigInterface 4 }

vtssQosConfigInterfacePolicerEntry OBJECT-TYPE
    SYNTAX      VTSSQosConfigInterfacePolicerEntry
    MAX-ACCESS  not-accessible
    STATUS      current
    DESCRIPTION 
        "Each row contains the configuration for a specific policer"
    INDEX       { vtssQosConfigInterfacePolicerIfIndex }
    ::= { vtssQosConfigInterfacePolicerTable 1 }

VTSSQosConfigInterfacePolicerEntry ::= SEQUENCE {
    vtssQosConfigInterfacePolicerIfIndex    VTSSInterfaceIndex,
    vtssQosConfigInterfacePolicerEnable     TruthValue,
    vtssQosConfigInterfacePolicerFrameRate      TruthValue,
    vtssQosConfigInterfacePolicerFlowControl    TruthValue,
    vtssQosConfigInterfacePolicerCir    Unsigned32
}

vtssQosConfigInterfacePolicerIfIndex OBJECT-TYPE
    SYNTAX      VTSSInterfaceIndex
    MAX-ACCESS  not-accessible
    STATUS      current
    DESCRIPTION 
        "Logical interface index."
    ::= { vtssQosConfigInterfacePolicerEntry 1 }

vtssQosConfigInterfacePolicerEnable OBJECT-TYPE
    SYNTAX      TruthValue
    MAX-ACCESS  read-write
    STATUS      current
    DESCRIPTION 
        "If true, the port policer is enabled."
    ::= { vtssQosConfigInterfacePolicerEntry 2 }

vtssQosConfigInterfacePolicerFrameRate OBJECT-TYPE
    SYNTAX      TruthValue
    MAX-ACCESS  read-write
    STATUS      current
    DESCRIPTION 
        "If true, the rate is measured in fps instead of kbps."
    ::= { vtssQosConfigInterfacePolicerEntry 3 }

vtssQosConfigInterfacePolicerFlowControl OBJECT-TYPE
    SYNTAX      TruthValue
    MAX-ACCESS  read-write
    STATUS      current
    DESCRIPTION 
        "If true, and flow control is enabled on the interface, then issue flow
         control pause frames instead of discarding frames.
         
         This object is only valid if QosCapabilitiesHasPortPolicersFc is true."
    ::= { vtssQosConfigInterfacePolicerEntry 4 }

vtssQosConfigInterfacePolicerCir OBJECT-TYPE
    SYNTAX      Unsigned32
    MAX-ACCESS  read-write
    STATUS      current
    DESCRIPTION 
        "Committed Information Rate. Measured in kbps if FrameRate is false and
         fps if FrameRate is true.
         
         Valid range is qosCapabilitiesBitrateMin-qosCapabilitiesBitrateMax"
    ::= { vtssQosConfigInterfacePolicerEntry 5 }

vtssQosConfigInterfaceQueuePolicerTable OBJECT-TYPE
    SYNTAX      SEQUENCE OF VTSSQosConfigInterfaceQueuePolicerEntry
    MAX-ACCESS  not-accessible
    STATUS      current
    DESCRIPTION 
        "This table provides queue policer configuration for interfaces
         
         This is an optional table and is only present if
         QosCapabilitiesHasPortQueuePolicers is true."
    ::= { vtssQosConfigInterface 5 }

vtssQosConfigInterfaceQueuePolicerEntry OBJECT-TYPE
    SYNTAX      VTSSQosConfigInterfaceQueuePolicerEntry
    MAX-ACCESS  not-accessible
    STATUS      current
    DESCRIPTION 
        "Each row contains the configuration for a specific queue policer"
    INDEX       { vtssQosConfigInterfaceQueuePolicerIfIndex, vtssQosConfigInterfaceQueuePolicerQueue }
    ::= { vtssQosConfigInterfaceQueuePolicerTable 1 }

VTSSQosConfigInterfaceQueuePolicerEntry ::= SEQUENCE {
    vtssQosConfigInterfaceQueuePolicerIfIndex   VTSSInterfaceIndex,
    vtssQosConfigInterfaceQueuePolicerQueue     Integer32,
    vtssQosConfigInterfaceQueuePolicerEnable    TruthValue,
    vtssQosConfigInterfaceQueuePolicerCir   Unsigned32
}

vtssQosConfigInterfaceQueuePolicerIfIndex OBJECT-TYPE
    SYNTAX      VTSSInterfaceIndex
    MAX-ACCESS  not-accessible
    STATUS      current
    DESCRIPTION 
        "Logical interface index."
    ::= { vtssQosConfigInterfaceQueuePolicerEntry 1 }

vtssQosConfigInterfaceQueuePolicerQueue OBJECT-TYPE
    SYNTAX      Integer32 (0..7)
    MAX-ACCESS  not-accessible
    STATUS      current
    DESCRIPTION 
        "Queue index."
    ::= { vtssQosConfigInterfaceQueuePolicerEntry 2 }

vtssQosConfigInterfaceQueuePolicerEnable OBJECT-TYPE
    SYNTAX      TruthValue
    MAX-ACCESS  read-write
    STATUS      current
    DESCRIPTION 
        "If true, the queue policer is enabled."
    ::= { vtssQosConfigInterfaceQueuePolicerEntry 3 }

vtssQosConfigInterfaceQueuePolicerCir OBJECT-TYPE
    SYNTAX      Unsigned32
    MAX-ACCESS  read-write
    STATUS      current
    DESCRIPTION 
        "Committed Information Rate. Measured in kbps.
         
         Valid range is qosCapabilitiesBitrateMin-qosCapabilitiesBitrateMax"
    ::= { vtssQosConfigInterfaceQueuePolicerEntry 6 }

vtssQosConfigInterfaceShaperTable OBJECT-TYPE
    SYNTAX      SEQUENCE OF VTSSQosConfigInterfaceShaperEntry
    MAX-ACCESS  not-accessible
    STATUS      current
    DESCRIPTION 
        "This table provides shaper configuration for an interface"
    ::= { vtssQosConfigInterface 6 }

vtssQosConfigInterfaceShaperEntry OBJECT-TYPE
    SYNTAX      VTSSQosConfigInterfaceShaperEntry
    MAX-ACCESS  not-accessible
    STATUS      current
    DESCRIPTION 
        "Each row contains the configuration for a specific shaper"
    INDEX       { vtssQosConfigInterfaceShaperIfIndex }
    ::= { vtssQosConfigInterfaceShaperTable 1 }

VTSSQosConfigInterfaceShaperEntry ::= SEQUENCE {
    vtssQosConfigInterfaceShaperIfIndex     VTSSInterfaceIndex,
    vtssQosConfigInterfaceShaperEnable      TruthValue,
    vtssQosConfigInterfaceShaperCir     Unsigned32,
    vtssQosConfigInterfaceShaperRateType    VTSSQosShaperRateType
}

vtssQosConfigInterfaceShaperIfIndex OBJECT-TYPE
    SYNTAX      VTSSInterfaceIndex
    MAX-ACCESS  not-accessible
    STATUS      current
    DESCRIPTION 
        "Logical interface index."
    ::= { vtssQosConfigInterfaceShaperEntry 1 }

vtssQosConfigInterfaceShaperEnable OBJECT-TYPE
    SYNTAX      TruthValue
    MAX-ACCESS  read-write
    STATUS      current
    DESCRIPTION 
        "If true, the port shaper is enabled."
    ::= { vtssQosConfigInterfaceShaperEntry 2 }

vtssQosConfigInterfaceShaperCir OBJECT-TYPE
    SYNTAX      Unsigned32
    MAX-ACCESS  read-write
    STATUS      current
    DESCRIPTION 
        "Committed Information Rate. Measured in kbps.
         
         Valid range is qosCapabilitiesBitrateMin-qosCapabilitiesBitrateMax"
    ::= { vtssQosConfigInterfaceShaperEntry 3 }

vtssQosConfigInterfaceShaperRateType OBJECT-TYPE
    SYNTAX      VTSSQosShaperRateType
    MAX-ACCESS  read-write
    STATUS      current
    DESCRIPTION 
        "Indicates the shaper's rate type.
         
         Valid selections are line-rate (0) and data-rate (1).
         
         This object is only valid if QosCapabilitiesHasShapersRt is true."
    ::= { vtssQosConfigInterfaceShaperEntry 4 }

vtssQosConfigInterfaceQueueShaperTable OBJECT-TYPE
    SYNTAX      SEQUENCE OF VTSSQosConfigInterfaceQueueShaperEntry
    MAX-ACCESS  not-accessible
    STATUS      current
    DESCRIPTION 
        "This table provides queue shaper configuration for interfaces"
    ::= { vtssQosConfigInterface 7 }

vtssQosConfigInterfaceQueueShaperEntry OBJECT-TYPE
    SYNTAX      VTSSQosConfigInterfaceQueueShaperEntry
    MAX-ACCESS  not-accessible
    STATUS      current
    DESCRIPTION 
        "Each row contains the configuration for a specific queue shaper"
    INDEX       { vtssQosConfigInterfaceQueueShaperIfIndex, vtssQosConfigInterfaceQueueShaperQueue }
    ::= { vtssQosConfigInterfaceQueueShaperTable 1 }

VTSSQosConfigInterfaceQueueShaperEntry ::= SEQUENCE {
    vtssQosConfigInterfaceQueueShaperIfIndex    VTSSInterfaceIndex,
    vtssQosConfigInterfaceQueueShaperQueue      Integer32,
    vtssQosConfigInterfaceQueueShaperEnable     TruthValue,
    vtssQosConfigInterfaceQueueShaperExcess     TruthValue,
    vtssQosConfigInterfaceQueueShaperCir    Unsigned32,
    vtssQosConfigInterfaceQueueShaperRateType   VTSSQosShaperRateType
}

vtssQosConfigInterfaceQueueShaperIfIndex OBJECT-TYPE
    SYNTAX      VTSSInterfaceIndex
    MAX-ACCESS  not-accessible
    STATUS      current
    DESCRIPTION 
        "Logical interface index."
    ::= { vtssQosConfigInterfaceQueueShaperEntry 1 }

vtssQosConfigInterfaceQueueShaperQueue OBJECT-TYPE
    SYNTAX      Integer32 (0..7)
    MAX-ACCESS  not-accessible
    STATUS      current
    DESCRIPTION 
        "Queue index."
    ::= { vtssQosConfigInterfaceQueueShaperEntry 2 }

vtssQosConfigInterfaceQueueShaperEnable OBJECT-TYPE
    SYNTAX      TruthValue
    MAX-ACCESS  read-write
    STATUS      current
    DESCRIPTION 
        "If true, the queue shaper is enabled."
    ::= { vtssQosConfigInterfaceQueueShaperEntry 3 }

vtssQosConfigInterfaceQueueShaperExcess OBJECT-TYPE
    SYNTAX      TruthValue
    MAX-ACCESS  read-write
    STATUS      current
    DESCRIPTION 
        "If true, then allow this queue to get a share of the excess bandwidth.
         
         Excess bandwidth is allowed if this shaper is closed and no other
         queues with open shapers have frames for transmission.
         
         This object is only valid if QosCapabilitiesHasQueueShapersExcess is
         true."
    ::= { vtssQosConfigInterfaceQueueShaperEntry 4 }

vtssQosConfigInterfaceQueueShaperCir OBJECT-TYPE
    SYNTAX      Unsigned32
    MAX-ACCESS  read-write
    STATUS      current
    DESCRIPTION 
        "Committed Information Rate. Measured in kbps.
         
         Valid range is qosCapabilitiesBitrateMin-qosCapabilitiesBitrateMax"
    ::= { vtssQosConfigInterfaceQueueShaperEntry 5 }

vtssQosConfigInterfaceQueueShaperRateType OBJECT-TYPE
    SYNTAX      VTSSQosShaperRateType
    MAX-ACCESS  read-write
    STATUS      current
    DESCRIPTION 
        "Indicates the shaper's rate type.
         
         Valid selections are line-rate (0) and data-rate (1).
         
         NOTE: This configuration is valid only for Normal port mode. If the
         port is in Basic or Hierarchical mode, the rate-type will be stored and
         become active when the port is switched back to Normal Scheduling mode.
         
         This object is only valid if QosCapabilitiesHasShapersRt is true."
    ::= { vtssQosConfigInterfaceQueueShaperEntry 6 }

vtssQosConfigInterfaceSchedulerTable OBJECT-TYPE
    SYNTAX      SEQUENCE OF VTSSQosConfigInterfaceSchedulerEntry
    MAX-ACCESS  not-accessible
    STATUS      current
    DESCRIPTION 
        "This table contains the mapping of (interface, queue) to weight values.
         
         The mappings given by this table is used when an interface has the
         value of DwrrCount greater than 0.
         
         Read the qosSchedulerStatusTable in order to get the 'real' weights in
         percent as used by the hardware."
    ::= { vtssQosConfigInterface 8 }

vtssQosConfigInterfaceSchedulerEntry OBJECT-TYPE
    SYNTAX      VTSSQosConfigInterfaceSchedulerEntry
    MAX-ACCESS  not-accessible
    STATUS      current
    DESCRIPTION 
        "Each row contains the scheduler configuration for a specific queue."
    INDEX       { vtssQosConfigInterfaceSchedulerIfIndex, vtssQosConfigInterfaceSchedulerQueue }
    ::= { vtssQosConfigInterfaceSchedulerTable 1 }

VTSSQosConfigInterfaceSchedulerEntry ::= SEQUENCE {
    vtssQosConfigInterfaceSchedulerIfIndex      VTSSInterfaceIndex,
    vtssQosConfigInterfaceSchedulerQueue    Integer32,
    vtssQosConfigInterfaceSchedulerWeight   VTSSPercent
}

vtssQosConfigInterfaceSchedulerIfIndex OBJECT-TYPE
    SYNTAX      VTSSInterfaceIndex
    MAX-ACCESS  not-accessible
    STATUS      current
    DESCRIPTION 
        "Logical interface index."
    ::= { vtssQosConfigInterfaceSchedulerEntry 1 }

vtssQosConfigInterfaceSchedulerQueue OBJECT-TYPE
    SYNTAX      Integer32 (0..7)
    MAX-ACCESS  not-accessible
    STATUS      current
    DESCRIPTION 
        "Queue index."
    ::= { vtssQosConfigInterfaceSchedulerEntry 2 }

vtssQosConfigInterfaceSchedulerWeight OBJECT-TYPE
    SYNTAX      VTSSPercent
    MAX-ACCESS  read-write
    STATUS      current
    DESCRIPTION 
        "The weight for this queue.
         
         Valid range is 1-100."
    ::= { vtssQosConfigInterfaceSchedulerEntry 3 }

vtssQosConfigInterfaceStormPolicerUnicastTable OBJECT-TYPE
    SYNTAX      SEQUENCE OF VTSSQosConfigInterfaceStormPolicerUnicastEntry
    MAX-ACCESS  not-accessible
    STATUS      current
    DESCRIPTION 
        "This table provides storm policer configuration for unicast packets
         received on an interface
         
         This is an optional table and is only present if
         QosCapabilitiesHasPortStormPolicers is true."
    ::= { vtssQosConfigInterface 9 }

vtssQosConfigInterfaceStormPolicerUnicastEntry OBJECT-TYPE
    SYNTAX      VTSSQosConfigInterfaceStormPolicerUnicastEntry
    MAX-ACCESS  not-accessible
    STATUS      current
    DESCRIPTION 
        "Each row contains the configuration for a specific storm policer"
    INDEX       { vtssQosConfigInterfaceStormPolicerUnicastIfIndex }
    ::= { vtssQosConfigInterfaceStormPolicerUnicastTable 1 }

VTSSQosConfigInterfaceStormPolicerUnicastEntry ::= SEQUENCE {
    vtssQosConfigInterfaceStormPolicerUnicastIfIndex    VTSSInterfaceIndex,
    vtssQosConfigInterfaceStormPolicerUnicastEnable     TruthValue,
    vtssQosConfigInterfaceStormPolicerUnicastFrameRate      TruthValue,
    vtssQosConfigInterfaceStormPolicerUnicastCir    Unsigned32
}

vtssQosConfigInterfaceStormPolicerUnicastIfIndex OBJECT-TYPE
    SYNTAX      VTSSInterfaceIndex
    MAX-ACCESS  not-accessible
    STATUS      current
    DESCRIPTION 
        "Logical interface index."
    ::= { vtssQosConfigInterfaceStormPolicerUnicastEntry 1 }

vtssQosConfigInterfaceStormPolicerUnicastEnable OBJECT-TYPE
    SYNTAX      TruthValue
    MAX-ACCESS  read-write
    STATUS      current
    DESCRIPTION 
        "If true, the storm policer is enabled.
         
         This object is only valid if QosCapabilitiesHasPortStormPolicers is
         true."
    ::= { vtssQosConfigInterfaceStormPolicerUnicastEntry 2 }

vtssQosConfigInterfaceStormPolicerUnicastFrameRate OBJECT-TYPE
    SYNTAX      TruthValue
    MAX-ACCESS  read-write
    STATUS      current
    DESCRIPTION 
        "If true, the rate is measured in fps instead of kbps.
         
         This object is only valid if QosCapabilitiesHasPortStormPolicers is
         true."
    ::= { vtssQosConfigInterfaceStormPolicerUnicastEntry 3 }

vtssQosConfigInterfaceStormPolicerUnicastCir OBJECT-TYPE
    SYNTAX      Unsigned32
    MAX-ACCESS  read-write
    STATUS      current
    DESCRIPTION 
        "Committed Information Rate. Measured in kbps if FrameRate is false and
         fps if FrameRate is true.
         
         Valid range is qosCapabilitiesBitrateMin-qosCapabilitiesBitrateMax.
         
         This object is only valid if QosCapabilitiesHasPortStormPolicers is
         true."
    ::= { vtssQosConfigInterfaceStormPolicerUnicastEntry 4 }

vtssQosConfigInterfaceStormPolicerBroadcastTable OBJECT-TYPE
    SYNTAX      SEQUENCE OF VTSSQosConfigInterfaceStormPolicerBroadcastEntry
    MAX-ACCESS  not-accessible
    STATUS      current
    DESCRIPTION 
        "This table provides storm policer configuration for broadcast packets
         received on an interface
         
         This is an optional table and is only present if
         QosCapabilitiesHasPortStormPolicers is true."
    ::= { vtssQosConfigInterface 10 }

vtssQosConfigInterfaceStormPolicerBroadcastEntry OBJECT-TYPE
    SYNTAX      VTSSQosConfigInterfaceStormPolicerBroadcastEntry
    MAX-ACCESS  not-accessible
    STATUS      current
    DESCRIPTION 
        "Each row contains the configuration for a specific storm policer"
    INDEX       { vtssQosConfigInterfaceStormPolicerBroadcastIfIndex }
    ::= { vtssQosConfigInterfaceStormPolicerBroadcastTable 1 }

VTSSQosConfigInterfaceStormPolicerBroadcastEntry ::= SEQUENCE {
    vtssQosConfigInterfaceStormPolicerBroadcastIfIndex      VTSSInterfaceIndex,
    vtssQosConfigInterfaceStormPolicerBroadcastEnable   TruthValue,
    vtssQosConfigInterfaceStormPolicerBroadcastFrameRate    TruthValue,
    vtssQosConfigInterfaceStormPolicerBroadcastCir      Unsigned32
}

vtssQosConfigInterfaceStormPolicerBroadcastIfIndex OBJECT-TYPE
    SYNTAX      VTSSInterfaceIndex
    MAX-ACCESS  not-accessible
    STATUS      current
    DESCRIPTION 
        "Logical interface index."
    ::= { vtssQosConfigInterfaceStormPolicerBroadcastEntry 1 }

vtssQosConfigInterfaceStormPolicerBroadcastEnable OBJECT-TYPE
    SYNTAX      TruthValue
    MAX-ACCESS  read-write
    STATUS      current
    DESCRIPTION 
        "If true, the storm policer is enabled.
         
         This object is only valid if QosCapabilitiesHasPortStormPolicers is
         true."
    ::= { vtssQosConfigInterfaceStormPolicerBroadcastEntry 2 }

vtssQosConfigInterfaceStormPolicerBroadcastFrameRate OBJECT-TYPE
    SYNTAX      TruthValue
    MAX-ACCESS  read-write
    STATUS      current
    DESCRIPTION 
        "If true, the rate is measured in fps instead of kbps.
         
         This object is only valid if QosCapabilitiesHasPortStormPolicers is
         true."
    ::= { vtssQosConfigInterfaceStormPolicerBroadcastEntry 3 }

vtssQosConfigInterfaceStormPolicerBroadcastCir OBJECT-TYPE
    SYNTAX      Unsigned32
    MAX-ACCESS  read-write
    STATUS      current
    DESCRIPTION 
        "Committed Information Rate. Measured in kbps if FrameRate is false and
         fps if FrameRate is true.
         
         Valid range is qosCapabilitiesBitrateMin-qosCapabilitiesBitrateMax.
         
         This object is only valid if QosCapabilitiesHasPortStormPolicers is
         true."
    ::= { vtssQosConfigInterfaceStormPolicerBroadcastEntry 4 }

vtssQosConfigInterfaceStormPolicerUnknownTable OBJECT-TYPE
    SYNTAX      SEQUENCE OF VTSSQosConfigInterfaceStormPolicerUnknownEntry
    MAX-ACCESS  not-accessible
    STATUS      current
    DESCRIPTION 
        "This table provides storm policer configuration for unknown (flooded)
         packets received on an interface
         
         This is an optional table and is only present if
         QosCapabilitiesHasPortStormPolicers is true."
    ::= { vtssQosConfigInterface 11 }

vtssQosConfigInterfaceStormPolicerUnknownEntry OBJECT-TYPE
    SYNTAX      VTSSQosConfigInterfaceStormPolicerUnknownEntry
    MAX-ACCESS  not-accessible
    STATUS      current
    DESCRIPTION 
        "Each row contains the configuration for a specific storm policer"
    INDEX       { vtssQosConfigInterfaceStormPolicerUnknownIfIndex }
    ::= { vtssQosConfigInterfaceStormPolicerUnknownTable 1 }

VTSSQosConfigInterfaceStormPolicerUnknownEntry ::= SEQUENCE {
    vtssQosConfigInterfaceStormPolicerUnknownIfIndex    VTSSInterfaceIndex,
    vtssQosConfigInterfaceStormPolicerUnknownEnable     TruthValue,
    vtssQosConfigInterfaceStormPolicerUnknownFrameRate      TruthValue,
    vtssQosConfigInterfaceStormPolicerUnknownCir    Unsigned32
}

vtssQosConfigInterfaceStormPolicerUnknownIfIndex OBJECT-TYPE
    SYNTAX      VTSSInterfaceIndex
    MAX-ACCESS  not-accessible
    STATUS      current
    DESCRIPTION 
        "Logical interface index."
    ::= { vtssQosConfigInterfaceStormPolicerUnknownEntry 1 }

vtssQosConfigInterfaceStormPolicerUnknownEnable OBJECT-TYPE
    SYNTAX      TruthValue
    MAX-ACCESS  read-write
    STATUS      current
    DESCRIPTION 
        "If true, the storm policer is enabled.
         
         This object is only valid if QosCapabilitiesHasPortStormPolicers is
         true."
    ::= { vtssQosConfigInterfaceStormPolicerUnknownEntry 2 }

vtssQosConfigInterfaceStormPolicerUnknownFrameRate OBJECT-TYPE
    SYNTAX      TruthValue
    MAX-ACCESS  read-write
    STATUS      current
    DESCRIPTION 
        "If true, the rate is measured in fps instead of kbps.
         
         This object is only valid if QosCapabilitiesHasPortStormPolicers is
         true."
    ::= { vtssQosConfigInterfaceStormPolicerUnknownEntry 3 }

vtssQosConfigInterfaceStormPolicerUnknownCir OBJECT-TYPE
    SYNTAX      Unsigned32
    MAX-ACCESS  read-write
    STATUS      current
    DESCRIPTION 
        "Committed Information Rate. Measured in kbps if FrameRate is false and
         fps if FrameRate is true.
         
         Valid range is qosCapabilitiesBitrateMin-qosCapabilitiesBitrateMax.
         
         This object is only valid if QosCapabilitiesHasPortStormPolicers is
         true."
    ::= { vtssQosConfigInterfaceStormPolicerUnknownEntry 4 }

vtssQosConfigQce OBJECT IDENTIFIER
    ::= { vtssQosConfig 3 }

vtssQosConfigQceTable OBJECT-TYPE
    SYNTAX      SEQUENCE OF VTSSQosConfigQceEntry
    MAX-ACCESS  not-accessible
    STATUS      current
    DESCRIPTION 
        "This table contains the configuration of QCEs. The index is QceId.
         
         This is an optional table and is only present if qosCapabilitiesHasQce
         is true."
    ::= { vtssQosConfigQce 1 }

vtssQosConfigQceEntry OBJECT-TYPE
    SYNTAX      VTSSQosConfigQceEntry
    MAX-ACCESS  not-accessible
    STATUS      current
    DESCRIPTION 
        "Each row contains the configuration of a single QCE."
    INDEX       { vtssQosConfigQceQceId }
    ::= { vtssQosConfigQceTable 1 }

VTSSQosConfigQceEntry ::= SEQUENCE {
    vtssQosConfigQceQceId   Integer32,
    vtssQosConfigQceNextQceId   Unsigned32,
    vtssQosConfigQceSwitchId    Unsigned32,
    vtssQosConfigQcePortList    VTSSPortList,
    vtssQosConfigQceDestMacType     VTSSDestMacType,
    vtssQosConfigQceDestMac     MacAddress,
    vtssQosConfigQceDestMacMask     MacAddress,
    vtssQosConfigQceSrcMac      MacAddress,
    vtssQosConfigQceSrcMacMask      MacAddress,
    vtssQosConfigQceVlanTagType     VTSSVlanTagType,
    vtssQosConfigQceVlanIdOp    VTSSASRType,
    vtssQosConfigQceVlanId      VTSSUnsigned16,
    vtssQosConfigQceVlanIdRange     VTSSUnsigned16,
    vtssQosConfigQcePcp     VTSSVlanTagPriority,
    vtssQosConfigQceDei     VTSSBitType,
    vtssQosConfigQceInnerVlanTagType    VTSSVlanTagType,
    vtssQosConfigQceInnerVlanIdOp   VTSSASRType,
    vtssQosConfigQceInnerVlanId     VTSSUnsigned16,
    vtssQosConfigQceInnerVlanIdRange    VTSSUnsigned16,
    vtssQosConfigQceInnerPcp    VTSSVlanTagPriority,
    vtssQosConfigQceInnerDei    VTSSBitType,
    vtssQosConfigQceFrameType   VTSSQosQceFrameType,
    vtssQosConfigQceEtype   VTSSEtherType,
    vtssQosConfigQceLlcDsap     VTSSUnsigned8,
    vtssQosConfigQceLlcDsapMask     VTSSUnsigned8,
    vtssQosConfigQceLlcSsap     VTSSUnsigned8,
    vtssQosConfigQceLlcSsapMask     VTSSUnsigned8,
    vtssQosConfigQceLlcControl      VTSSUnsigned8,
    vtssQosConfigQceLlcControlMask      VTSSUnsigned8,
    vtssQosConfigQceSnapPid     VTSSUnsigned16,
    vtssQosConfigQceSnapPidMask     VTSSUnsigned16,
    vtssQosConfigQceIpv4Fragment    VTSSBitType,
    vtssQosConfigQceIpv4DscpOp      VTSSASRType,
    vtssQosConfigQceIpv4Dscp    VTSSUnsigned16,
    vtssQosConfigQceIpv4DscpRange   VTSSUnsigned16,
    vtssQosConfigQceIpv4Protocol    VTSSUnsigned8,
    vtssQosConfigQceIpv4ProtocolMask    VTSSUnsigned8,
    vtssQosConfigQceIpv4SrcIp   IpAddress,
    vtssQosConfigQceIpv4SrcIpMask   IpAddress,
    vtssQosConfigQceIpv4DestIp      IpAddress,
    vtssQosConfigQceIpv4DestIpMask      IpAddress,
    vtssQosConfigQceIpv4SrcPortOp   VTSSASRType,
    vtssQosConfigQceIpv4SrcPort     VTSSUnsigned16,
    vtssQosConfigQceIpv4SrcPortRange    VTSSUnsigned16,
    vtssQosConfigQceIpv4DestPortOp      VTSSASRType,
    vtssQosConfigQceIpv4DestPort    VTSSUnsigned16,
    vtssQosConfigQceIpv4DestPortRange   VTSSUnsigned16,
    vtssQosConfigQceIpv6DscpOp      VTSSASRType,
    vtssQosConfigQceIpv6Dscp    VTSSUnsigned16,
    vtssQosConfigQceIpv6DscpRange   VTSSUnsigned16,
    vtssQosConfigQceIpv6Protocol    VTSSUnsigned8,
    vtssQosConfigQceIpv6ProtocolMask    VTSSUnsigned8,
    vtssQosConfigQceIpv6SrcIp   InetAddressIPv6,
    vtssQosConfigQceIpv6SrcIpMask   InetAddressIPv6,
    vtssQosConfigQceIpv6DestIp      InetAddressIPv6,
    vtssQosConfigQceIpv6DestIpMask      InetAddressIPv6,
    vtssQosConfigQceIpv6SrcPortOp   VTSSASRType,
    vtssQosConfigQceIpv6SrcPort     VTSSUnsigned16,
    vtssQosConfigQceIpv6SrcPortRange    VTSSUnsigned16,
    vtssQosConfigQceIpv6DestPortOp      VTSSASRType,
    vtssQosConfigQceIpv6DestPort    VTSSUnsigned16,
    vtssQosConfigQceIpv6DestPortRange   VTSSUnsigned16,
    vtssQosConfigQceActionCosEnable     TruthValue,
    vtssQosConfigQceActionCos   Unsigned32,
    vtssQosConfigQceActionDplEnable     TruthValue,
    vtssQosConfigQceActionDpl   VTSSUnsigned8,
    vtssQosConfigQceActionDscpEnable    TruthValue,
    vtssQosConfigQceActionDscp      VTSSUnsigned8,
    vtssQosConfigQceActionPcpDeiEnable      TruthValue,
    vtssQosConfigQceActionPcp   Unsigned32,
    vtssQosConfigQceActionDei   VTSSUnsigned8,
    vtssQosConfigQceActionPolicyEnable      TruthValue,
    vtssQosConfigQceActionPolicy    Unsigned32,
    vtssQosConfigQceAction      VTSSRowEditorState
}

vtssQosConfigQceQceId OBJECT-TYPE
    SYNTAX      Integer32 (0..2147483647)
    MAX-ACCESS  not-accessible
    STATUS      current
    DESCRIPTION 
        "QCE Id.
         
         Valid range is qosCapabilitiesQceIdMin-qosCapabilitiesQceIdMax or 0.
         
         Using a value of 0 when adding a new QCE, will assign the QCE Id in the
         new QCE to the first unused QCE Id."
    ::= { vtssQosConfigQceEntry 1 }

vtssQosConfigQceNextQceId OBJECT-TYPE
    SYNTAX      Unsigned32
    MAX-ACCESS  read-write
    STATUS      current
    DESCRIPTION 
        "QCE Id of the next QCE. Valid range is
         qosCapabilitiesQceIdMin-qosCapabilitiesQceIdMax or 0.
         
         The value 0, denotes the end of the list."
    ::= { vtssQosConfigQceEntry 2 }

vtssQosConfigQceSwitchId OBJECT-TYPE
    SYNTAX      Unsigned32
    MAX-ACCESS  read-write
    STATUS      current
    DESCRIPTION 
        "Indicates the switch on which this QCE is active.Valid range is
         documented in the Stacking MIB.
         
         This object is only valid on stacking platforms."
    ::= { vtssQosConfigQceEntry 3 }

vtssQosConfigQcePortList OBJECT-TYPE
    SYNTAX      VTSSPortList
    MAX-ACCESS  read-write
    STATUS      current
    DESCRIPTION 
        "List of ports that are member of this QCE."
    ::= { vtssQosConfigQceEntry 4 }

vtssQosConfigQceDestMacType OBJECT-TYPE
    SYNTAX      VTSSDestMacType
    MAX-ACCESS  read-write
    STATUS      current
    DESCRIPTION 
        "Indicates the destination MAC type to match."
    ::= { vtssQosConfigQceEntry 5 }

vtssQosConfigQceDestMac OBJECT-TYPE
    SYNTAX      MacAddress
    MAX-ACCESS  read-write
    STATUS      current
    DESCRIPTION 
        "Indicates the 48 bits destination MAC address.
         
         The packets destination address is AND-ed with the value of DestMacMask
         and then compared against the value of this object.
         
         If this object value and the value of DestMacMask is 00-00-00-00-00-00,
         this entry matches any destination MAC address.
         
         This object can only be configured if DestMacType is any(0) and
         DestMacMask is ff-ff-ff-ff-ff-ff.
         
         This object is only valid if QosCapabilitiesHasQceDmac is true."
    ::= { vtssQosConfigQceEntry 6 }

vtssQosConfigQceDestMacMask OBJECT-TYPE
    SYNTAX      MacAddress
    MAX-ACCESS  read-write
    STATUS      current
    DESCRIPTION 
        "Indicates the 48 bits destination MAC address mask.
         
         Valid values are 00-00-00-00-00-00 or ff-ff-ff-ff-ff-ff.
         
         This object is only valid if QosCapabilitiesHasQceDmac is true."
    ::= { vtssQosConfigQceEntry 7 }

vtssQosConfigQceSrcMac OBJECT-TYPE
    SYNTAX      MacAddress
    MAX-ACCESS  read-write
    STATUS      current
    DESCRIPTION 
        "Indicates the 48 bits source MAC address.
         
         The packets source address is AND-ed with the value of SrcMacMask and
         then compared against the value of this object.
         
         If this object value and the value of SrcMacMask is 00-00-00-00-00-00,
         this entry matches any source MAC address.
         
         This object can only be configured if SrcMacMask is ff-ff-ff-ff-ff-ff.
         
         If the value of qosCapabilitiesHasQceMacOui is true then only the OUI
         part of the MAC address (24 most significant bits) is used."
    ::= { vtssQosConfigQceEntry 8 }

vtssQosConfigQceSrcMacMask OBJECT-TYPE
    SYNTAX      MacAddress
    MAX-ACCESS  read-write
    STATUS      current
    DESCRIPTION 
        "Indicates the 48 bits source MAC address mask.
         
         Valid values are 00-00-00-00-00-00 or ff-ff-ff-ff-ff-ff."
    ::= { vtssQosConfigQceEntry 9 }

vtssQosConfigQceVlanTagType OBJECT-TYPE
    SYNTAX      VTSSVlanTagType
    MAX-ACCESS  read-write
    STATUS      current
    DESCRIPTION 
        "Indicates the VLAN tag type to match.
         
         The value cTagged(3) is only supported if qosCapabilitiesHasCTag is
         true.
         
         The value sTagged(3) is only supported if qosCapabilitiesHasSTag is
         true."
    ::= { vtssQosConfigQceEntry 10 }

vtssQosConfigQceVlanIdOp OBJECT-TYPE
    SYNTAX      VTSSASRType
    MAX-ACCESS  read-write
    STATUS      current
    DESCRIPTION 
        "Indicates how a packets's VLAN ID is to be compared."
    ::= { vtssQosConfigQceEntry 11 }

vtssQosConfigQceVlanId OBJECT-TYPE
    SYNTAX      VTSSUnsigned16
    MAX-ACCESS  read-write
    STATUS      current
    DESCRIPTION 
        "The VLAN ID to be compared.
         
         If the VlanIdOp object in the same row is range(2), this object will be
         the starting VLAN ID of the range.
         
         Valid range is vlanCapabilitiesVlanIdMin-vlanCapabilitiesVlanIdMax.
         
         This object can only be configured if VlanIdOp is not any(0)."
    ::= { vtssQosConfigQceEntry 12 }

vtssQosConfigQceVlanIdRange OBJECT-TYPE
    SYNTAX      VTSSUnsigned16
    MAX-ACCESS  read-write
    STATUS      current
    DESCRIPTION 
        "The VLAN ID to be compared.
         
         If the VlanIdOp object in the same row is range(2), this object will be
         the ending VLAN ID of the range.
         
         Valid range is vlanCapabilitiesVlanIdMin-vlanCapabilitiesVlanIdMax.
         
         This object can only be configured if VlanIdOp is range(2)."
    ::= { vtssQosConfigQceEntry 13 }

vtssQosConfigQcePcp OBJECT-TYPE
    SYNTAX      VTSSVlanTagPriority
    MAX-ACCESS  read-write
    STATUS      current
    DESCRIPTION 
        "The PCP value(s) to be compared."
    ::= { vtssQosConfigQceEntry 14 }

vtssQosConfigQceDei OBJECT-TYPE
    SYNTAX      VTSSBitType
    MAX-ACCESS  read-write
    STATUS      current
    DESCRIPTION 
        "The DEI value to be compared.
         
         Valid range is 0-1."
    ::= { vtssQosConfigQceEntry 15 }

vtssQosConfigQceInnerVlanTagType OBJECT-TYPE
    SYNTAX      VTSSVlanTagType
    MAX-ACCESS  read-write
    STATUS      current
    DESCRIPTION 
        "Indicates the inner VLAN tag type to match.
         
         This object is only valid if QosCapabilitiesHasQceInnerTag is true."
    ::= { vtssQosConfigQceEntry 16 }

vtssQosConfigQceInnerVlanIdOp OBJECT-TYPE
    SYNTAX      VTSSASRType
    MAX-ACCESS  read-write
    STATUS      current
    DESCRIPTION 
        "Indicates how a packets's inner VLAN ID is to be compared.
         
         This object is only valid if QosCapabilitiesHasQceInnerTag is true."
    ::= { vtssQosConfigQceEntry 17 }

vtssQosConfigQceInnerVlanId OBJECT-TYPE
    SYNTAX      VTSSUnsigned16
    MAX-ACCESS  read-write
    STATUS      current
    DESCRIPTION 
        "The inner VLAN ID to be compared.
         
         If the InnerVlanIdOp object in the same row is range(2), this object
         will be the starting VLAN ID of the range.
         
         Valid range is vlanCapabilitiesVlanIdMin-vlanCapabilitiesVlanIdMax.
         
         This object can only be configured if InnerVlanIdOp is not any(0).
         
         This object is only valid if QosCapabilitiesHasQceInnerTag is true."
    ::= { vtssQosConfigQceEntry 18 }

vtssQosConfigQceInnerVlanIdRange OBJECT-TYPE
    SYNTAX      VTSSUnsigned16
    MAX-ACCESS  read-write
    STATUS      current
    DESCRIPTION 
        "The inner VLAN ID to be compared.
         
         If the InnerVlanIdOp object in the same row is range(2), this object
         will be the ending VLAN ID of the range.
         
         Valid range is vlanCapabilitiesVlanIdMin-vlanCapabilitiesVlanIdMax.
         
         This object can only be configured if InnerVlanIdOp is range(2).
         
         This object is only valid if QosCapabilitiesHasQceInnerTag is true."
    ::= { vtssQosConfigQceEntry 19 }

vtssQosConfigQceInnerPcp OBJECT-TYPE
    SYNTAX      VTSSVlanTagPriority
    MAX-ACCESS  read-write
    STATUS      current
    DESCRIPTION 
        "The inner PCP value(s) to be compared.
         
         This object is only valid if QosCapabilitiesHasQceInnerTag is true."
    ::= { vtssQosConfigQceEntry 20 }

vtssQosConfigQceInnerDei OBJECT-TYPE
    SYNTAX      VTSSBitType
    MAX-ACCESS  read-write
    STATUS      current
    DESCRIPTION 
        "The inner DEI value to be compared.
         
         Valid range is 0-1.
         
         This object is only valid if QosCapabilitiesHasQceInnerTag is true."
    ::= { vtssQosConfigQceEntry 21 }

vtssQosConfigQceFrameType OBJECT-TYPE
    SYNTAX      VTSSQosQceFrameType
    MAX-ACCESS  read-write
    STATUS      current
    DESCRIPTION 
        "Indicates the packet's frame type.
         
         Modifying the frame type on an existing QCE will restore the content of
         all frame type dependent configuration to default."
    ::= { vtssQosConfigQceEntry 100 }

vtssQosConfigQceEtype OBJECT-TYPE
    SYNTAX      VTSSEtherType
    MAX-ACCESS  read-write
    STATUS      current
    DESCRIPTION 
        "Indicates the packet's 16 bit Ethernet type field.
         
         Valid values are: 0(match any), 0x600-0xFFFF but excluding 0x800(IPv4)
         and 0x86DD(IPv6).
         
         This object can only be configured if FrameType is etype(1)."
    ::= { vtssQosConfigQceEntry 101 }

vtssQosConfigQceLlcDsap OBJECT-TYPE
    SYNTAX      VTSSUnsigned8
    MAX-ACCESS  read-write
    STATUS      current
    DESCRIPTION 
        "Indicates the packets's 8 bit LLC DSAP field.
         
         The packets LLC DSAP field is AND-ed with the value of LlcDsapMask and
         then compared against the value of this object.
         
         If this object value and the value of LlcDsapMask is 0x00, this entry
         matches any LLC DSAP.
         
         Valid range is 0x00-0xFF.
         
         This object can only be configured if FrameType is llc(2)."
    ::= { vtssQosConfigQceEntry 200 }

vtssQosConfigQceLlcDsapMask OBJECT-TYPE
    SYNTAX      VTSSUnsigned8
    MAX-ACCESS  read-write
    STATUS      current
    DESCRIPTION 
        "Indicates the 8 bit LLC DSAP mask.
         
         Valid values are 0x00 or 0xFF.
         
         This object can only be configured if FrameType is llc(2)."
    ::= { vtssQosConfigQceEntry 201 }

vtssQosConfigQceLlcSsap OBJECT-TYPE
    SYNTAX      VTSSUnsigned8
    MAX-ACCESS  read-write
    STATUS      current
    DESCRIPTION 
        "Indicates the packets's 8 bit LLC SSAP field.
         
         The packets LLC SSAP field is AND-ed with the value of LlcSsapMask and
         then compared against the value of this object.
         
         If this object value and the value of LlcSsapMask is 0x00, this entry
         matches any LLC SSAP.
         
         Valid range is 0x00-0xFF.
         
         This object can only be configured if FrameType is llc(2)."
    ::= { vtssQosConfigQceEntry 202 }

vtssQosConfigQceLlcSsapMask OBJECT-TYPE
    SYNTAX      VTSSUnsigned8
    MAX-ACCESS  read-write
    STATUS      current
    DESCRIPTION 
        "Indicates the 8 bit LLC SSAP mask.
         
         Valid values are 0x00 or 0xFF.
         
         This object can only be configured if FrameType is llc(2)."
    ::= { vtssQosConfigQceEntry 203 }

vtssQosConfigQceLlcControl OBJECT-TYPE
    SYNTAX      VTSSUnsigned8
    MAX-ACCESS  read-write
    STATUS      current
    DESCRIPTION 
        "Indicates the packets's 8 bit LLC Control field.
         
         The packets LLC Control field is AND-ed with the value of
         LlcControlMask and then compared against the value of this object.
         
         If this object value and the value of LlcControlMask is 0x00, this
         entry matches any LLC Control.
         
         Valid range is 0x00-0xFF.
         
         This object can only be configured if FrameType is llc(2)."
    ::= { vtssQosConfigQceEntry 204 }

vtssQosConfigQceLlcControlMask OBJECT-TYPE
    SYNTAX      VTSSUnsigned8
    MAX-ACCESS  read-write
    STATUS      current
    DESCRIPTION 
        "Indicates the 8 bit LLC Control mask.
         
         Valid values are 0x00 or 0xFF.
         
         This object can only be configured if FrameType is llc(2)."
    ::= { vtssQosConfigQceEntry 205 }

vtssQosConfigQceSnapPid OBJECT-TYPE
    SYNTAX      VTSSUnsigned16
    MAX-ACCESS  read-write
    STATUS      current
    DESCRIPTION 
        "Indicates the packet's 16 bit SNAP PID field.
         
         The packets SNAP PID field is AND-ed with the value of SnapPidMask and
         then compared against the value of this object.
         
         If this object value and the value of SnapPidMask is 0x0000, this entry
         matches any ethertype.
         
         This object can only be configured if FrameType is snap(3)."
    ::= { vtssQosConfigQceEntry 302 }

vtssQosConfigQceSnapPidMask OBJECT-TYPE
    SYNTAX      VTSSUnsigned16
    MAX-ACCESS  read-write
    STATUS      current
    DESCRIPTION 
        "Indicates the 16 bit SNAP PID mask.
         
         Valid values are 0x0000 or 0xFFFF.
         
         This object can only be configured if FrameType is snap(3)."
    ::= { vtssQosConfigQceEntry 303 }

vtssQosConfigQceIpv4Fragment OBJECT-TYPE
    SYNTAX      VTSSBitType
    MAX-ACCESS  read-write
    STATUS      current
    DESCRIPTION 
        "Indicates how an IPv4 fragment bit is to be compared.
         
         This object can only be configured if FrameType is ipv4(4)."
    ::= { vtssQosConfigQceEntry 400 }

vtssQosConfigQceIpv4DscpOp OBJECT-TYPE
    SYNTAX      VTSSASRType
    MAX-ACCESS  read-write
    STATUS      current
    DESCRIPTION 
        "Indicates how an IPv4 DSCP field is to be compared.
         
         This object can only be configured if FrameType is ipv4(4)."
    ::= { vtssQosConfigQceEntry 401 }

vtssQosConfigQceIpv4Dscp OBJECT-TYPE
    SYNTAX      VTSSUnsigned16
    MAX-ACCESS  read-write
    STATUS      current
    DESCRIPTION 
        "The DSCP value to be compared.
         
         If the Ipv4DscpOp object in the same row is range(2), this object will
         be the starting DSCP value of the range.
         
         Valid range is 0-63.
         
         This object can only be configured if FrameType is ipv4(4) and
         Ipv4DscpOp is not any(0)."
    ::= { vtssQosConfigQceEntry 402 }

vtssQosConfigQceIpv4DscpRange OBJECT-TYPE
    SYNTAX      VTSSUnsigned16
    MAX-ACCESS  read-write
    STATUS      current
    DESCRIPTION 
        "The DSCP value to be compared.
         
         If the Ipv4DscpOp object in the same row is range(2), this object will
         be the ending DSCP value of the range.
         
         Valid range is 0-63.
         
         This object can only be configured if FrameType is ipv4(4) and
         Ipv4DscpOp is range(2)."
    ::= { vtssQosConfigQceEntry 403 }

vtssQosConfigQceIpv4Protocol OBJECT-TYPE
    SYNTAX      VTSSUnsigned8
    MAX-ACCESS  read-write
    STATUS      current
    DESCRIPTION 
        "The protocol number field in the IPv4 header used to indicate a higher
         layer protocol.
         
         The packets protocol number field is AND-ed with the value of
         Ipv4ProtocolMask and then compared with the value of this object.
         
         If Ipv4Protocol and Ipv4protocolMask are 0, this entry matches any IPv4
         protocol.
         
         Valid range is 0-255.
         
         This object can only be configured if FrameType is ipv4(4)."
    ::= { vtssQosConfigQceEntry 404 }

vtssQosConfigQceIpv4ProtocolMask OBJECT-TYPE
    SYNTAX      VTSSUnsigned8
    MAX-ACCESS  read-write
    STATUS      current
    DESCRIPTION 
        "The specified IPv4 protocol number mask.
         
         Valid values are 0 or 255.
         
         This object can only be configured if FrameType is ipv4(4)."
    ::= { vtssQosConfigQceEntry 405 }

vtssQosConfigQceIpv4SrcIp OBJECT-TYPE
    SYNTAX      IpAddress
    MAX-ACCESS  read-write
    STATUS      current
    DESCRIPTION 
        "The specified IPv4 source address.
         
         The packets source address is AND-ed with the value of Ipv4SrcIpMask
         and then compared with the value of this object.
         
         If Ipv4SrcIP and Ipv4SrcIpMask are 0.0.0.0, this entry matches any IPv4
         source address.
         
         This object can only be configured if FrameType is ipv4(4)."
    ::= { vtssQosConfigQceEntry 406 }

vtssQosConfigQceIpv4SrcIpMask OBJECT-TYPE
    SYNTAX      IpAddress
    MAX-ACCESS  read-write
    STATUS      current
    DESCRIPTION 
        "The specified IPv4 source address mask.
         
         This object can only be configured if FrameType is ipv4(4)."
    ::= { vtssQosConfigQceEntry 407 }

vtssQosConfigQceIpv4DestIp OBJECT-TYPE
    SYNTAX      IpAddress
    MAX-ACCESS  read-write
    STATUS      current
    DESCRIPTION 
        "The specified IPv4 destination address.
         
         The packets destination address is AND-ed with the value of
         Ipv4DestIpMask and then compared with the value of this object.
         
         If Ipv4DestIP and Ipv4DestIpMask are 0.0.0.0, this entry matches any
         IPv4 destination address.
         
         This object can only be configured if FrameType is ipv4(4).
         
         This object is only valid if QosCapabilitiesHasQceDip is true."
    ::= { vtssQosConfigQceEntry 408 }

vtssQosConfigQceIpv4DestIpMask OBJECT-TYPE
    SYNTAX      IpAddress
    MAX-ACCESS  read-write
    STATUS      current
    DESCRIPTION 
        "The specified IPv4 destination address mask.
         
         This object can only be configured if FrameType is ipv4(4).
         
         This object is only valid if QosCapabilitiesHasQceDip is true."
    ::= { vtssQosConfigQceEntry 409 }

vtssQosConfigQceIpv4SrcPortOp OBJECT-TYPE
    SYNTAX      VTSSASRType
    MAX-ACCESS  read-write
    STATUS      current
    DESCRIPTION 
        "Indicates how a packet's source TCP/UDP port number is to be compared.
         
         This object can only be configured if FrameType is ipv4(4)."
    ::= { vtssQosConfigQceEntry 410 }

vtssQosConfigQceIpv4SrcPort OBJECT-TYPE
    SYNTAX      VTSSUnsigned16
    MAX-ACCESS  read-write
    STATUS      current
    DESCRIPTION 
        "The source port number of the TCP or UDP protocol.
         
         If the Ipv4SrcPortOp object in the same row is range(2), this object
         will be the starting port number of the port range.
         
         Valid range is 0-65535.
         
         This object can only be configured if FrameType is ipv4(4) and
         Ipv4SrcPortOp is not any(0)."
    ::= { vtssQosConfigQceEntry 411 }

vtssQosConfigQceIpv4SrcPortRange OBJECT-TYPE
    SYNTAX      VTSSUnsigned16
    MAX-ACCESS  read-write
    STATUS      current
    DESCRIPTION 
        "The source port number of the TCP or UDP protocol.
         
         If the Ipv4SrcPortOp object in the same row is range(2), this object
         will be the ending port number of the port range.
         
         Valid range is 0-65535.
         
         This object can only be configured if FrameType is ipv4(4) and
         Ipv4SrcPortOp is range(2)."
    ::= { vtssQosConfigQceEntry 412 }

vtssQosConfigQceIpv4DestPortOp OBJECT-TYPE
    SYNTAX      VTSSASRType
    MAX-ACCESS  read-write
    STATUS      current
    DESCRIPTION 
        "Indicates how a packet's destination TCP/UDP port number is to be
         compared.
         
         This object can only be configured if FrameType is ipv4(4)."
    ::= { vtssQosConfigQceEntry 413 }

vtssQosConfigQceIpv4DestPort OBJECT-TYPE
    SYNTAX      VTSSUnsigned16
    MAX-ACCESS  read-write
    STATUS      current
    DESCRIPTION 
        "The destination port number of the TCP or UDP protocol.
         
         If the Ipv4DestPortOp object in the same row is range(2), this object
         will be the starting port number of the port range.
         
         Valid range is 0-65535.
         
         This object can only be configured if FrameType is ipv4(4) and
         Ipv4DestPortOp is not any(0)."
    ::= { vtssQosConfigQceEntry 414 }

vtssQosConfigQceIpv4DestPortRange OBJECT-TYPE
    SYNTAX      VTSSUnsigned16
    MAX-ACCESS  read-write
    STATUS      current
    DESCRIPTION 
        "The source port number of the TCP or UDP protocol.
         
         If the Ipv4DestPortOp object in the same row is range(2), this object
         will be the ending port number of the port range.
         
         Valid range is 0-65535.
         
         This object can only be configured if FrameType is ipv4(4) and
         Ipv4DestPortOp is range(2)."
    ::= { vtssQosConfigQceEntry 415 }

vtssQosConfigQceIpv6DscpOp OBJECT-TYPE
    SYNTAX      VTSSASRType
    MAX-ACCESS  read-write
    STATUS      current
    DESCRIPTION 
        "Indicates how an IPv6 DSCP field is to be compared.
         
         This object can only be configured if FrameType is ipv6(5)."
    ::= { vtssQosConfigQceEntry 500 }

vtssQosConfigQceIpv6Dscp OBJECT-TYPE
    SYNTAX      VTSSUnsigned16
    MAX-ACCESS  read-write
    STATUS      current
    DESCRIPTION 
        "The DSCP value to be compared.
         
         If the Ipv6DscpOp object in the same row is range(2), this object will
         be the starting DSCP value of the range.
         
         Valid range is 0-63.
         
         This object can only be configured if FrameType is ipv6(5) and
         Ipv6DscpOp is not any(0)."
    ::= { vtssQosConfigQceEntry 501 }

vtssQosConfigQceIpv6DscpRange OBJECT-TYPE
    SYNTAX      VTSSUnsigned16
    MAX-ACCESS  read-write
    STATUS      current
    DESCRIPTION 
        "The DSCP value to be compared.
         
         If the Ipv6DscpOp object in the same row is range(2), this object will
         be the ending DSCP value of the range.
         
         Valid range is 0-63.
         
         This object can only be configured if FrameType is ipv6(5) and
         Ipv6DscpOp is range(2)."
    ::= { vtssQosConfigQceEntry 502 }

vtssQosConfigQceIpv6Protocol OBJECT-TYPE
    SYNTAX      VTSSUnsigned8
    MAX-ACCESS  read-write
    STATUS      current
    DESCRIPTION 
        "The protocol number field in the IPv6 header used to indicate a higher
         layer protocol.
         
         The packets protocol number field is AND-ed with the value of
         Ipv6ProtocolMask and then compared with the value of this object.
         
         If Ipv46rotocol and Ipv6protocolMask are 0, this entry matches any IPv6
         protocol.
         
         Valid range is 0-255.
         
         This object can only be configured if FrameType is ipv6(5)."
    ::= { vtssQosConfigQceEntry 503 }

vtssQosConfigQceIpv6ProtocolMask OBJECT-TYPE
    SYNTAX      VTSSUnsigned8
    MAX-ACCESS  read-write
    STATUS      current
    DESCRIPTION 
        "The specified IPv6 protocol number mask.
         
         Valid values are 0 or 255.
         
         This object can only be configured if FrameType is ipv6(5)."
    ::= { vtssQosConfigQceEntry 504 }

vtssQosConfigQceIpv6SrcIp OBJECT-TYPE
    SYNTAX      InetAddressIPv6
    MAX-ACCESS  read-write
    STATUS      current
    DESCRIPTION 
        "The specified IPv6 source address.
         
         The packets source address is AND-ed with the value of Ipv6SrcIpMask
         and then compared with the value of this object.
         
         If Ipv6SrcIP and Ipv6SrcIpMask are all zeros, this entry matches any
         IPv6 source address.
         
         Only the least significant 32 bits of this object are used.
         
         This object can only be configured if FrameType is ipv6(5)."
    ::= { vtssQosConfigQceEntry 506 }

vtssQosConfigQceIpv6SrcIpMask OBJECT-TYPE
    SYNTAX      InetAddressIPv6
    MAX-ACCESS  read-write
    STATUS      current
    DESCRIPTION 
        "The specified IPv6 source address mask.
         
         Only the least significant 32 bits of this object are used.
         
         This object can only be configured if FrameType is ipv6(5)."
    ::= { vtssQosConfigQceEntry 508 }

vtssQosConfigQceIpv6DestIp OBJECT-TYPE
    SYNTAX      InetAddressIPv6
    MAX-ACCESS  read-write
    STATUS      current
    DESCRIPTION 
        "The specified IPv6 destination address.
         
         The packets destination address is AND-ed with the value of
         Ipv6DestIpMask and then compared with the value of this object.
         
         If Ipv6DestIP and Ipv6DestIpMask are all zeros, this entry matches any
         IPv6 destination address.
         
         Only the least significant 32 bits of this object are used.
         
         This object can only be configured if FrameType is ipv6(5).
         
         This object is only valid if QosCapabilitiesHasQceDip is true."
    ::= { vtssQosConfigQceEntry 510 }

vtssQosConfigQceIpv6DestIpMask OBJECT-TYPE
    SYNTAX      InetAddressIPv6
    MAX-ACCESS  read-write
    STATUS      current
    DESCRIPTION 
        "The specified IPv6 destination address mask.
         
         Only the least significant 32 bits of this object are used.
         
         This object can only be configured if FrameType is ipv6(5).
         
         This object is only valid if QosCapabilitiesHasQceDip is true."
    ::= { vtssQosConfigQceEntry 512 }

vtssQosConfigQceIpv6SrcPortOp OBJECT-TYPE
    SYNTAX      VTSSASRType
    MAX-ACCESS  read-write
    STATUS      current
    DESCRIPTION 
        "Indicates how a packet's source TCP/UDP port number is to be compared.
         
         This object can only be configured if FrameType is ipv6(5)."
    ::= { vtssQosConfigQceEntry 513 }

vtssQosConfigQceIpv6SrcPort OBJECT-TYPE
    SYNTAX      VTSSUnsigned16
    MAX-ACCESS  read-write
    STATUS      current
    DESCRIPTION 
        "The source port number of the TCP or UDP protocol.
         
         If the Ipv6SrcPortOp object in the same row is range(2), this object
         will be the starting port number of the port range.
         
         Valid range is 0-65535.
         
         This object can only be configured if FrameType is ipv6(5) and
         Ipv6SrcPortOp is not any(0)."
    ::= { vtssQosConfigQceEntry 514 }

vtssQosConfigQceIpv6SrcPortRange OBJECT-TYPE
    SYNTAX      VTSSUnsigned16
    MAX-ACCESS  read-write
    STATUS      current
    DESCRIPTION 
        "The source port number of the TCP or UDP protocol.
         
         If the Ipv6SrcPortOp object in the same row is range(2), this object
         will be the ending port number of the port range.
         
         Valid range is 0-65535.
         
         This object can only be configured if FrameType is ipv6(5) and
         Ipv6SrcPortOp is range(2)."
    ::= { vtssQosConfigQceEntry 515 }

vtssQosConfigQceIpv6DestPortOp OBJECT-TYPE
    SYNTAX      VTSSASRType
    MAX-ACCESS  read-write
    STATUS      current
    DESCRIPTION 
        "Indicates how a packet's destination TCP/UDP port number is to be
         compared.
         
         This object can only be configured if FrameType is ipv6(5)."
    ::= { vtssQosConfigQceEntry 516 }

vtssQosConfigQceIpv6DestPort OBJECT-TYPE
    SYNTAX      VTSSUnsigned16
    MAX-ACCESS  read-write
    STATUS      current
    DESCRIPTION 
        "The destination port number of the TCP or UDP protocol.
         
         If the Ipv6DestPortOp object in the same row is range(2), this object
         will be the starting port number of the port range.
         
         Valid range is 0-65535.
         
         This object can only be configured if FrameType is ipv6(5) and
         Ipv6DestPortOp is not any(0)."
    ::= { vtssQosConfigQceEntry 517 }

vtssQosConfigQceIpv6DestPortRange OBJECT-TYPE
    SYNTAX      VTSSUnsigned16
    MAX-ACCESS  read-write
    STATUS      current
    DESCRIPTION 
        "The source port number of the TCP or UDP protocol.
         
         If the Ipv6DestPortOp object in the same row is range(2), this object
         will be the ending port number of the port range.
         
         Valid range is 0-65535.
         
         This object can only be configured if FrameType is ipv6(5) and
         Ipv6DestPortOp is range(2)."
    ::= { vtssQosConfigQceEntry 518 }

vtssQosConfigQceActionCosEnable OBJECT-TYPE
    SYNTAX      TruthValue
    MAX-ACCESS  read-write
    STATUS      current
    DESCRIPTION 
        "If true, the packet is classified to the CoS value in ActionCos."
    ::= { vtssQosConfigQceEntry 1000 }

vtssQosConfigQceActionCos OBJECT-TYPE
    SYNTAX      Unsigned32
    MAX-ACCESS  read-write
    STATUS      current
    DESCRIPTION 
        "The CoS value used for classification.
         
         Valid range is qosCapabilitiesClassMin-qosCapabilitiesClassMax."
    ::= { vtssQosConfigQceEntry 1001 }

vtssQosConfigQceActionDplEnable OBJECT-TYPE
    SYNTAX      TruthValue
    MAX-ACCESS  read-write
    STATUS      current
    DESCRIPTION 
        "If true, the packet is classified to the DPL value in ActionDpl."
    ::= { vtssQosConfigQceEntry 1002 }

vtssQosConfigQceActionDpl OBJECT-TYPE
    SYNTAX      VTSSUnsigned8
    MAX-ACCESS  read-write
    STATUS      current
    DESCRIPTION 
        "The DPL value used for classification.
         
         Valid range is qosCapabilitiesDplMin-qosCapabilitiesDplMax."
    ::= { vtssQosConfigQceEntry 1003 }

vtssQosConfigQceActionDscpEnable OBJECT-TYPE
    SYNTAX      TruthValue
    MAX-ACCESS  read-write
    STATUS      current
    DESCRIPTION 
        "If true, the packet is classified to the DSCP value in ActionDscp."
    ::= { vtssQosConfigQceEntry 1004 }

vtssQosConfigQceActionDscp OBJECT-TYPE
    SYNTAX      VTSSUnsigned8
    MAX-ACCESS  read-write
    STATUS      current
    DESCRIPTION 
        "The DSCP value used for classification.
         
         Valid range is 0-63."
    ::= { vtssQosConfigQceEntry 1005 }

vtssQosConfigQceActionPcpDeiEnable OBJECT-TYPE
    SYNTAX      TruthValue
    MAX-ACCESS  read-write
    STATUS      current
    DESCRIPTION 
        "If true, the packet is classified to the PCP value in ActionPcp and the
         DEI value in ActionDei.
         
         This object is only valid if QosCapabilitiesHasQceActionPcpDei is true."
    ::= { vtssQosConfigQceEntry 1006 }

vtssQosConfigQceActionPcp OBJECT-TYPE
    SYNTAX      Unsigned32
    MAX-ACCESS  read-write
    STATUS      current
    DESCRIPTION 
        "The PCP value used for classification.
         
         Valid range is 0-7.
         
         This object is only valid if QosCapabilitiesHasQceActionPcpDei is true."
    ::= { vtssQosConfigQceEntry 1007 }

vtssQosConfigQceActionDei OBJECT-TYPE
    SYNTAX      VTSSUnsigned8
    MAX-ACCESS  read-write
    STATUS      current
    DESCRIPTION 
        "The DEI value used for classification.
         
         Valid range is 0-1.
         
         This object is only valid if QosCapabilitiesHasQceActionPcpDei is true."
    ::= { vtssQosConfigQceEntry 1008 }

vtssQosConfigQceActionPolicyEnable OBJECT-TYPE
    SYNTAX      TruthValue
    MAX-ACCESS  read-write
    STATUS      current
    DESCRIPTION 
        "If true, the packet is classified to the policy number in ActionPolicy.
         
         This object is only valid if QosCapabilitiesHasQceActionPolicy is true."
    ::= { vtssQosConfigQceEntry 1009 }

vtssQosConfigQceActionPolicy OBJECT-TYPE
    SYNTAX      Unsigned32
    MAX-ACCESS  read-write
    STATUS      current
    DESCRIPTION 
        "The policy number used for classification.
         
         Valid range is documented in the ACL MIB.
         
         This object is only valid if QosCapabilitiesHasQceActionPcpDei is true."
    ::= { vtssQosConfigQceEntry 1010 }

vtssQosConfigQceAction OBJECT-TYPE
    SYNTAX      VTSSRowEditorState
    MAX-ACCESS  read-write
    STATUS      current
    DESCRIPTION 
        "Action"
    ::= { vtssQosConfigQceEntry 10000 }

vtssQosConfigQceTableRowEditor OBJECT IDENTIFIER
    ::= { vtssQosConfigQce 2 }

vtssQosConfigQceTableRowEditorQceId OBJECT-TYPE
    SYNTAX      Integer32 (0..2147483647)
    MAX-ACCESS  read-write
    STATUS      current
    DESCRIPTION 
        "QCE Id.
         
         Valid range is qosCapabilitiesQceIdMin-qosCapabilitiesQceIdMax or 0.
         
         Using a value of 0 when adding a new QCE, will assign the QCE Id in the
         new QCE to the first unused QCE Id."
    ::= { vtssQosConfigQceTableRowEditor 1 }

vtssQosConfigQceTableRowEditorNextQceId OBJECT-TYPE
    SYNTAX      Unsigned32
    MAX-ACCESS  read-write
    STATUS      current
    DESCRIPTION 
        "QCE Id of the next QCE. Valid range is
         qosCapabilitiesQceIdMin-qosCapabilitiesQceIdMax or 0.
         
         The value 0, denotes the end of the list."
    ::= { vtssQosConfigQceTableRowEditor 2 }

vtssQosConfigQceTableRowEditorSwitchId OBJECT-TYPE
    SYNTAX      Unsigned32
    MAX-ACCESS  read-write
    STATUS      current
    DESCRIPTION 
        "Indicates the switch on which this QCE is active.Valid range is
         documented in the Stacking MIB.
         
         This object is only valid on stacking platforms."
    ::= { vtssQosConfigQceTableRowEditor 3 }

vtssQosConfigQceTableRowEditorPortList OBJECT-TYPE
    SYNTAX      VTSSPortList
    MAX-ACCESS  read-write
    STATUS      current
    DESCRIPTION 
        "List of ports that are member of this QCE."
    ::= { vtssQosConfigQceTableRowEditor 4 }

vtssQosConfigQceTableRowEditorDestMacType OBJECT-TYPE
    SYNTAX      VTSSDestMacType
    MAX-ACCESS  read-write
    STATUS      current
    DESCRIPTION 
        "Indicates the destination MAC type to match."
    ::= { vtssQosConfigQceTableRowEditor 5 }

vtssQosConfigQceTableRowEditorDestMac OBJECT-TYPE
    SYNTAX      MacAddress
    MAX-ACCESS  read-write
    STATUS      current
    DESCRIPTION 
        "Indicates the 48 bits destination MAC address.
         
         The packets destination address is AND-ed with the value of DestMacMask
         and then compared against the value of this object.
         
         If this object value and the value of DestMacMask is 00-00-00-00-00-00,
         this entry matches any destination MAC address.
         
         This object can only be configured if DestMacType is any(0) and
         DestMacMask is ff-ff-ff-ff-ff-ff.
         
         This object is only valid if QosCapabilitiesHasQceDmac is true."
    ::= { vtssQosConfigQceTableRowEditor 6 }

vtssQosConfigQceTableRowEditorDestMacMask OBJECT-TYPE
    SYNTAX      MacAddress
    MAX-ACCESS  read-write
    STATUS      current
    DESCRIPTION 
        "Indicates the 48 bits destination MAC address mask.
         
         Valid values are 00-00-00-00-00-00 or ff-ff-ff-ff-ff-ff.
         
         This object is only valid if QosCapabilitiesHasQceDmac is true."
    ::= { vtssQosConfigQceTableRowEditor 7 }

vtssQosConfigQceTableRowEditorSrcMac OBJECT-TYPE
    SYNTAX      MacAddress
    MAX-ACCESS  read-write
    STATUS      current
    DESCRIPTION 
        "Indicates the 48 bits source MAC address.
         
         The packets source address is AND-ed with the value of SrcMacMask and
         then compared against the value of this object.
         
         If this object value and the value of SrcMacMask is 00-00-00-00-00-00,
         this entry matches any source MAC address.
         
         This object can only be configured if SrcMacMask is ff-ff-ff-ff-ff-ff.
         
         If the value of qosCapabilitiesHasQceMacOui is true then only the OUI
         part of the MAC address (24 most significant bits) is used."
    ::= { vtssQosConfigQceTableRowEditor 8 }

vtssQosConfigQceTableRowEditorSrcMacMask OBJECT-TYPE
    SYNTAX      MacAddress
    MAX-ACCESS  read-write
    STATUS      current
    DESCRIPTION 
        "Indicates the 48 bits source MAC address mask.
         
         Valid values are 00-00-00-00-00-00 or ff-ff-ff-ff-ff-ff."
    ::= { vtssQosConfigQceTableRowEditor 9 }

vtssQosConfigQceTableRowEditorVlanTagType OBJECT-TYPE
    SYNTAX      VTSSVlanTagType
    MAX-ACCESS  read-write
    STATUS      current
    DESCRIPTION 
        "Indicates the VLAN tag type to match.
         
         The value cTagged(3) is only supported if qosCapabilitiesHasCTag is
         true.
         
         The value sTagged(3) is only supported if qosCapabilitiesHasSTag is
         true."
    ::= { vtssQosConfigQceTableRowEditor 10 }

vtssQosConfigQceTableRowEditorVlanIdOp OBJECT-TYPE
    SYNTAX      VTSSASRType
    MAX-ACCESS  read-write
    STATUS      current
    DESCRIPTION 
        "Indicates how a packets's VLAN ID is to be compared."
    ::= { vtssQosConfigQceTableRowEditor 11 }

vtssQosConfigQceTableRowEditorVlanId OBJECT-TYPE
    SYNTAX      VTSSUnsigned16
    MAX-ACCESS  read-write
    STATUS      current
    DESCRIPTION 
        "The VLAN ID to be compared.
         
         If the VlanIdOp object in the same row is range(2), this object will be
         the starting VLAN ID of the range.
         
         Valid range is vlanCapabilitiesVlanIdMin-vlanCapabilitiesVlanIdMax.
         
         This object can only be configured if VlanIdOp is not any(0)."
    ::= { vtssQosConfigQceTableRowEditor 12 }

vtssQosConfigQceTableRowEditorVlanIdRange OBJECT-TYPE
    SYNTAX      VTSSUnsigned16
    MAX-ACCESS  read-write
    STATUS      current
    DESCRIPTION 
        "The VLAN ID to be compared.
         
         If the VlanIdOp object in the same row is range(2), this object will be
         the ending VLAN ID of the range.
         
         Valid range is vlanCapabilitiesVlanIdMin-vlanCapabilitiesVlanIdMax.
         
         This object can only be configured if VlanIdOp is range(2)."
    ::= { vtssQosConfigQceTableRowEditor 13 }

vtssQosConfigQceTableRowEditorPcp OBJECT-TYPE
    SYNTAX      VTSSVlanTagPriority
    MAX-ACCESS  read-write
    STATUS      current
    DESCRIPTION 
        "The PCP value(s) to be compared."
    ::= { vtssQosConfigQceTableRowEditor 14 }

vtssQosConfigQceTableRowEditorDei OBJECT-TYPE
    SYNTAX      VTSSBitType
    MAX-ACCESS  read-write
    STATUS      current
    DESCRIPTION 
        "The DEI value to be compared.
         
         Valid range is 0-1."
    ::= { vtssQosConfigQceTableRowEditor 15 }

vtssQosConfigQceTableRowEditorInnerVlanTagType OBJECT-TYPE
    SYNTAX      VTSSVlanTagType
    MAX-ACCESS  read-write
    STATUS      current
    DESCRIPTION 
        "Indicates the inner VLAN tag type to match.
         
         This object is only valid if QosCapabilitiesHasQceInnerTag is true."
    ::= { vtssQosConfigQceTableRowEditor 16 }

vtssQosConfigQceTableRowEditorInnerVlanIdOp OBJECT-TYPE
    SYNTAX      VTSSASRType
    MAX-ACCESS  read-write
    STATUS      current
    DESCRIPTION 
        "Indicates how a packets's inner VLAN ID is to be compared.
         
         This object is only valid if QosCapabilitiesHasQceInnerTag is true."
    ::= { vtssQosConfigQceTableRowEditor 17 }

vtssQosConfigQceTableRowEditorInnerVlanId OBJECT-TYPE
    SYNTAX      VTSSUnsigned16
    MAX-ACCESS  read-write
    STATUS      current
    DESCRIPTION 
        "The inner VLAN ID to be compared.
         
         If the InnerVlanIdOp object in the same row is range(2), this object
         will be the starting VLAN ID of the range.
         
         Valid range is vlanCapabilitiesVlanIdMin-vlanCapabilitiesVlanIdMax.
         
         This object can only be configured if InnerVlanIdOp is not any(0).
         
         This object is only valid if QosCapabilitiesHasQceInnerTag is true."
    ::= { vtssQosConfigQceTableRowEditor 18 }

vtssQosConfigQceTableRowEditorInnerVlanIdRange OBJECT-TYPE
    SYNTAX      VTSSUnsigned16
    MAX-ACCESS  read-write
    STATUS      current
    DESCRIPTION 
        "The inner VLAN ID to be compared.
         
         If the InnerVlanIdOp object in the same row is range(2), this object
         will be the ending VLAN ID of the range.
         
         Valid range is vlanCapabilitiesVlanIdMin-vlanCapabilitiesVlanIdMax.
         
         This object can only be configured if InnerVlanIdOp is range(2).
         
         This object is only valid if QosCapabilitiesHasQceInnerTag is true."
    ::= { vtssQosConfigQceTableRowEditor 19 }

vtssQosConfigQceTableRowEditorInnerPcp OBJECT-TYPE
    SYNTAX      VTSSVlanTagPriority
    MAX-ACCESS  read-write
    STATUS      current
    DESCRIPTION 
        "The inner PCP value(s) to be compared.
         
         This object is only valid if QosCapabilitiesHasQceInnerTag is true."
    ::= { vtssQosConfigQceTableRowEditor 20 }

vtssQosConfigQceTableRowEditorInnerDei OBJECT-TYPE
    SYNTAX      VTSSBitType
    MAX-ACCESS  read-write
    STATUS      current
    DESCRIPTION 
        "The inner DEI value to be compared.
         
         Valid range is 0-1.
         
         This object is only valid if QosCapabilitiesHasQceInnerTag is true."
    ::= { vtssQosConfigQceTableRowEditor 21 }

vtssQosConfigQceTableRowEditorFrameType OBJECT-TYPE
    SYNTAX      VTSSQosQceFrameType
    MAX-ACCESS  read-write
    STATUS      current
    DESCRIPTION 
        "Indicates the packet's frame type.
         
         Modifying the frame type on an existing QCE will restore the content of
         all frame type dependent configuration to default."
    ::= { vtssQosConfigQceTableRowEditor 100 }

vtssQosConfigQceTableRowEditorEtype OBJECT-TYPE
    SYNTAX      VTSSEtherType
    MAX-ACCESS  read-write
    STATUS      current
    DESCRIPTION 
        "Indicates the packet's 16 bit Ethernet type field.
         
         Valid values are: 0(match any), 0x600-0xFFFF but excluding 0x800(IPv4)
         and 0x86DD(IPv6).
         
         This object can only be configured if FrameType is etype(1)."
    ::= { vtssQosConfigQceTableRowEditor 101 }

vtssQosConfigQceTableRowEditorLlcDsap OBJECT-TYPE
    SYNTAX      VTSSUnsigned8
    MAX-ACCESS  read-write
    STATUS      current
    DESCRIPTION 
        "Indicates the packets's 8 bit LLC DSAP field.
         
         The packets LLC DSAP field is AND-ed with the value of LlcDsapMask and
         then compared against the value of this object.
         
         If this object value and the value of LlcDsapMask is 0x00, this entry
         matches any LLC DSAP.
         
         Valid range is 0x00-0xFF.
         
         This object can only be configured if FrameType is llc(2)."
    ::= { vtssQosConfigQceTableRowEditor 200 }

vtssQosConfigQceTableRowEditorLlcDsapMask OBJECT-TYPE
    SYNTAX      VTSSUnsigned8
    MAX-ACCESS  read-write
    STATUS      current
    DESCRIPTION 
        "Indicates the 8 bit LLC DSAP mask.
         
         Valid values are 0x00 or 0xFF.
         
         This object can only be configured if FrameType is llc(2)."
    ::= { vtssQosConfigQceTableRowEditor 201 }

vtssQosConfigQceTableRowEditorLlcSsap OBJECT-TYPE
    SYNTAX      VTSSUnsigned8
    MAX-ACCESS  read-write
    STATUS      current
    DESCRIPTION 
        "Indicates the packets's 8 bit LLC SSAP field.
         
         The packets LLC SSAP field is AND-ed with the value of LlcSsapMask and
         then compared against the value of this object.
         
         If this object value and the value of LlcSsapMask is 0x00, this entry
         matches any LLC SSAP.
         
         Valid range is 0x00-0xFF.
         
         This object can only be configured if FrameType is llc(2)."
    ::= { vtssQosConfigQceTableRowEditor 202 }

vtssQosConfigQceTableRowEditorLlcSsapMask OBJECT-TYPE
    SYNTAX      VTSSUnsigned8
    MAX-ACCESS  read-write
    STATUS      current
    DESCRIPTION 
        "Indicates the 8 bit LLC SSAP mask.
         
         Valid values are 0x00 or 0xFF.
         
         This object can only be configured if FrameType is llc(2)."
    ::= { vtssQosConfigQceTableRowEditor 203 }

vtssQosConfigQceTableRowEditorLlcControl OBJECT-TYPE
    SYNTAX      VTSSUnsigned8
    MAX-ACCESS  read-write
    STATUS      current
    DESCRIPTION 
        "Indicates the packets's 8 bit LLC Control field.
         
         The packets LLC Control field is AND-ed with the value of
         LlcControlMask and then compared against the value of this object.
         
         If this object value and the value of LlcControlMask is 0x00, this
         entry matches any LLC Control.
         
         Valid range is 0x00-0xFF.
         
         This object can only be configured if FrameType is llc(2)."
    ::= { vtssQosConfigQceTableRowEditor 204 }

vtssQosConfigQceTableRowEditorLlcControlMask OBJECT-TYPE
    SYNTAX      VTSSUnsigned8
    MAX-ACCESS  read-write
    STATUS      current
    DESCRIPTION 
        "Indicates the 8 bit LLC Control mask.
         
         Valid values are 0x00 or 0xFF.
         
         This object can only be configured if FrameType is llc(2)."
    ::= { vtssQosConfigQceTableRowEditor 205 }

vtssQosConfigQceTableRowEditorSnapPid OBJECT-TYPE
    SYNTAX      VTSSUnsigned16
    MAX-ACCESS  read-write
    STATUS      current
    DESCRIPTION 
        "Indicates the packet's 16 bit SNAP PID field.
         
         The packets SNAP PID field is AND-ed with the value of SnapPidMask and
         then compared against the value of this object.
         
         If this object value and the value of SnapPidMask is 0x0000, this entry
         matches any ethertype.
         
         This object can only be configured if FrameType is snap(3)."
    ::= { vtssQosConfigQceTableRowEditor 302 }

vtssQosConfigQceTableRowEditorSnapPidMask OBJECT-TYPE
    SYNTAX      VTSSUnsigned16
    MAX-ACCESS  read-write
    STATUS      current
    DESCRIPTION 
        "Indicates the 16 bit SNAP PID mask.
         
         Valid values are 0x0000 or 0xFFFF.
         
         This object can only be configured if FrameType is snap(3)."
    ::= { vtssQosConfigQceTableRowEditor 303 }

vtssQosConfigQceTableRowEditorIpv4Fragment OBJECT-TYPE
    SYNTAX      VTSSBitType
    MAX-ACCESS  read-write
    STATUS      current
    DESCRIPTION 
        "Indicates how an IPv4 fragment bit is to be compared.
         
         This object can only be configured if FrameType is ipv4(4)."
    ::= { vtssQosConfigQceTableRowEditor 400 }

vtssQosConfigQceTableRowEditorIpv4DscpOp OBJECT-TYPE
    SYNTAX      VTSSASRType
    MAX-ACCESS  read-write
    STATUS      current
    DESCRIPTION 
        "Indicates how an IPv4 DSCP field is to be compared.
         
         This object can only be configured if FrameType is ipv4(4)."
    ::= { vtssQosConfigQceTableRowEditor 401 }

vtssQosConfigQceTableRowEditorIpv4Dscp OBJECT-TYPE
    SYNTAX      VTSSUnsigned16
    MAX-ACCESS  read-write
    STATUS      current
    DESCRIPTION 
        "The DSCP value to be compared.
         
         If the Ipv4DscpOp object in the same row is range(2), this object will
         be the starting DSCP value of the range.
         
         Valid range is 0-63.
         
         This object can only be configured if FrameType is ipv4(4) and
         Ipv4DscpOp is not any(0)."
    ::= { vtssQosConfigQceTableRowEditor 402 }

vtssQosConfigQceTableRowEditorIpv4DscpRange OBJECT-TYPE
    SYNTAX      VTSSUnsigned16
    MAX-ACCESS  read-write
    STATUS      current
    DESCRIPTION 
        "The DSCP value to be compared.
         
         If the Ipv4DscpOp object in the same row is range(2), this object will
         be the ending DSCP value of the range.
         
         Valid range is 0-63.
         
         This object can only be configured if FrameType is ipv4(4) and
         Ipv4DscpOp is range(2)."
    ::= { vtssQosConfigQceTableRowEditor 403 }

vtssQosConfigQceTableRowEditorIpv4Protocol OBJECT-TYPE
    SYNTAX      VTSSUnsigned8
    MAX-ACCESS  read-write
    STATUS      current
    DESCRIPTION 
        "The protocol number field in the IPv4 header used to indicate a higher
         layer protocol.
         
         The packets protocol number field is AND-ed with the value of
         Ipv4ProtocolMask and then compared with the value of this object.
         
         If Ipv4Protocol and Ipv4protocolMask are 0, this entry matches any IPv4
         protocol.
         
         Valid range is 0-255.
         
         This object can only be configured if FrameType is ipv4(4)."
    ::= { vtssQosConfigQceTableRowEditor 404 }

vtssQosConfigQceTableRowEditorIpv4ProtocolMask OBJECT-TYPE
    SYNTAX      VTSSUnsigned8
    MAX-ACCESS  read-write
    STATUS      current
    DESCRIPTION 
        "The specified IPv4 protocol number mask.
         
         Valid values are 0 or 255.
         
         This object can only be configured if FrameType is ipv4(4)."
    ::= { vtssQosConfigQceTableRowEditor 405 }

vtssQosConfigQceTableRowEditorIpv4SrcIp OBJECT-TYPE
    SYNTAX      IpAddress
    MAX-ACCESS  read-write
    STATUS      current
    DESCRIPTION 
        "The specified IPv4 source address.
         
         The packets source address is AND-ed with the value of Ipv4SrcIpMask
         and then compared with the value of this object.
         
         If Ipv4SrcIP and Ipv4SrcIpMask are 0.0.0.0, this entry matches any IPv4
         source address.
         
         This object can only be configured if FrameType is ipv4(4)."
    ::= { vtssQosConfigQceTableRowEditor 406 }

vtssQosConfigQceTableRowEditorIpv4SrcIpMask OBJECT-TYPE
    SYNTAX      IpAddress
    MAX-ACCESS  read-write
    STATUS      current
    DESCRIPTION 
        "The specified IPv4 source address mask.
         
         This object can only be configured if FrameType is ipv4(4)."
    ::= { vtssQosConfigQceTableRowEditor 407 }

vtssQosConfigQceTableRowEditorIpv4DestIp OBJECT-TYPE
    SYNTAX      IpAddress
    MAX-ACCESS  read-write
    STATUS      current
    DESCRIPTION 
        "The specified IPv4 destination address.
         
         The packets destination address is AND-ed with the value of
         Ipv4DestIpMask and then compared with the value of this object.
         
         If Ipv4DestIP and Ipv4DestIpMask are 0.0.0.0, this entry matches any
         IPv4 destination address.
         
         This object can only be configured if FrameType is ipv4(4).
         
         This object is only valid if QosCapabilitiesHasQceDip is true."
    ::= { vtssQosConfigQceTableRowEditor 408 }

vtssQosConfigQceTableRowEditorIpv4DestIpMask OBJECT-TYPE
    SYNTAX      IpAddress
    MAX-ACCESS  read-write
    STATUS      current
    DESCRIPTION 
        "The specified IPv4 destination address mask.
         
         This object can only be configured if FrameType is ipv4(4).
         
         This object is only valid if QosCapabilitiesHasQceDip is true."
    ::= { vtssQosConfigQceTableRowEditor 409 }

vtssQosConfigQceTableRowEditorIpv4SrcPortOp OBJECT-TYPE
    SYNTAX      VTSSASRType
    MAX-ACCESS  read-write
    STATUS      current
    DESCRIPTION 
        "Indicates how a packet's source TCP/UDP port number is to be compared.
         
         This object can only be configured if FrameType is ipv4(4)."
    ::= { vtssQosConfigQceTableRowEditor 410 }

vtssQosConfigQceTableRowEditorIpv4SrcPort OBJECT-TYPE
    SYNTAX      VTSSUnsigned16
    MAX-ACCESS  read-write
    STATUS      current
    DESCRIPTION 
        "The source port number of the TCP or UDP protocol.
         
         If the Ipv4SrcPortOp object in the same row is range(2), this object
         will be the starting port number of the port range.
         
         Valid range is 0-65535.
         
         This object can only be configured if FrameType is ipv4(4) and
         Ipv4SrcPortOp is not any(0)."
    ::= { vtssQosConfigQceTableRowEditor 411 }

vtssQosConfigQceTableRowEditorIpv4SrcPortRange OBJECT-TYPE
    SYNTAX      VTSSUnsigned16
    MAX-ACCESS  read-write
    STATUS      current
    DESCRIPTION 
        "The source port number of the TCP or UDP protocol.
         
         If the Ipv4SrcPortOp object in the same row is range(2), this object
         will be the ending port number of the port range.
         
         Valid range is 0-65535.
         
         This object can only be configured if FrameType is ipv4(4) and
         Ipv4SrcPortOp is range(2)."
    ::= { vtssQosConfigQceTableRowEditor 412 }

vtssQosConfigQceTableRowEditorIpv4DestPortOp OBJECT-TYPE
    SYNTAX      VTSSASRType
    MAX-ACCESS  read-write
    STATUS      current
    DESCRIPTION 
        "Indicates how a packet's destination TCP/UDP port number is to be
         compared.
         
         This object can only be configured if FrameType is ipv4(4)."
    ::= { vtssQosConfigQceTableRowEditor 413 }

vtssQosConfigQceTableRowEditorIpv4DestPort OBJECT-TYPE
    SYNTAX      VTSSUnsigned16
    MAX-ACCESS  read-write
    STATUS      current
    DESCRIPTION 
        "The destination port number of the TCP or UDP protocol.
         
         If the Ipv4DestPortOp object in the same row is range(2), this object
         will be the starting port number of the port range.
         
         Valid range is 0-65535.
         
         This object can only be configured if FrameType is ipv4(4) and
         Ipv4DestPortOp is not any(0)."
    ::= { vtssQosConfigQceTableRowEditor 414 }

vtssQosConfigQceTableRowEditorIpv4DestPortRange OBJECT-TYPE
    SYNTAX      VTSSUnsigned16
    MAX-ACCESS  read-write
    STATUS      current
    DESCRIPTION 
        "The source port number of the TCP or UDP protocol.
         
         If the Ipv4DestPortOp object in the same row is range(2), this object
         will be the ending port number of the port range.
         
         Valid range is 0-65535.
         
         This object can only be configured if FrameType is ipv4(4) and
         Ipv4DestPortOp is range(2)."
    ::= { vtssQosConfigQceTableRowEditor 415 }

vtssQosConfigQceTableRowEditorIpv6DscpOp OBJECT-TYPE
    SYNTAX      VTSSASRType
    MAX-ACCESS  read-write
    STATUS      current
    DESCRIPTION 
        "Indicates how an IPv6 DSCP field is to be compared.
         
         This object can only be configured if FrameType is ipv6(5)."
    ::= { vtssQosConfigQceTableRowEditor 500 }

vtssQosConfigQceTableRowEditorIpv6Dscp OBJECT-TYPE
    SYNTAX      VTSSUnsigned16
    MAX-ACCESS  read-write
    STATUS      current
    DESCRIPTION 
        "The DSCP value to be compared.
         
         If the Ipv6DscpOp object in the same row is range(2), this object will
         be the starting DSCP value of the range.
         
         Valid range is 0-63.
         
         This object can only be configured if FrameType is ipv6(5) and
         Ipv6DscpOp is not any(0)."
    ::= { vtssQosConfigQceTableRowEditor 501 }

vtssQosConfigQceTableRowEditorIpv6DscpRange OBJECT-TYPE
    SYNTAX      VTSSUnsigned16
    MAX-ACCESS  read-write
    STATUS      current
    DESCRIPTION 
        "The DSCP value to be compared.
         
         If the Ipv6DscpOp object in the same row is range(2), this object will
         be the ending DSCP value of the range.
         
         Valid range is 0-63.
         
         This object can only be configured if FrameType is ipv6(5) and
         Ipv6DscpOp is range(2)."
    ::= { vtssQosConfigQceTableRowEditor 502 }

vtssQosConfigQceTableRowEditorIpv6Protocol OBJECT-TYPE
    SYNTAX      VTSSUnsigned8
    MAX-ACCESS  read-write
    STATUS      current
    DESCRIPTION 
        "The protocol number field in the IPv6 header used to indicate a higher
         layer protocol.
         
         The packets protocol number field is AND-ed with the value of
         Ipv6ProtocolMask and then compared with the value of this object.
         
         If Ipv46rotocol and Ipv6protocolMask are 0, this entry matches any IPv6
         protocol.
         
         Valid range is 0-255.
         
         This object can only be configured if FrameType is ipv6(5)."
    ::= { vtssQosConfigQceTableRowEditor 503 }

vtssQosConfigQceTableRowEditorIpv6ProtocolMask OBJECT-TYPE
    SYNTAX      VTSSUnsigned8
    MAX-ACCESS  read-write
    STATUS      current
    DESCRIPTION 
        "The specified IPv6 protocol number mask.
         
         Valid values are 0 or 255.
         
         This object can only be configured if FrameType is ipv6(5)."
    ::= { vtssQosConfigQceTableRowEditor 504 }

vtssQosConfigQceTableRowEditorIpv6SrcIp OBJECT-TYPE
    SYNTAX      InetAddressIPv6
    MAX-ACCESS  read-write
    STATUS      current
    DESCRIPTION 
        "The specified IPv6 source address.
         
         The packets source address is AND-ed with the value of Ipv6SrcIpMask
         and then compared with the value of this object.
         
         If Ipv6SrcIP and Ipv6SrcIpMask are all zeros, this entry matches any
         IPv6 source address.
         
         Only the least significant 32 bits of this object are used.
         
         This object can only be configured if FrameType is ipv6(5)."
    ::= { vtssQosConfigQceTableRowEditor 506 }

vtssQosConfigQceTableRowEditorIpv6SrcIpMask OBJECT-TYPE
    SYNTAX      InetAddressIPv6
    MAX-ACCESS  read-write
    STATUS      current
    DESCRIPTION 
        "The specified IPv6 source address mask.
         
         Only the least significant 32 bits of this object are used.
         
         This object can only be configured if FrameType is ipv6(5)."
    ::= { vtssQosConfigQceTableRowEditor 508 }

vtssQosConfigQceTableRowEditorIpv6DestIp OBJECT-TYPE
    SYNTAX      InetAddressIPv6
    MAX-ACCESS  read-write
    STATUS      current
    DESCRIPTION 
        "The specified IPv6 destination address.
         
         The packets destination address is AND-ed with the value of
         Ipv6DestIpMask and then compared with the value of this object.
         
         If Ipv6DestIP and Ipv6DestIpMask are all zeros, this entry matches any
         IPv6 destination address.
         
         Only the least significant 32 bits of this object are used.
         
         This object can only be configured if FrameType is ipv6(5).
         
         This object is only valid if QosCapabilitiesHasQceDip is true."
    ::= { vtssQosConfigQceTableRowEditor 510 }

vtssQosConfigQceTableRowEditorIpv6DestIpMask OBJECT-TYPE
    SYNTAX      InetAddressIPv6
    MAX-ACCESS  read-write
    STATUS      current
    DESCRIPTION 
        "The specified IPv6 destination address mask.
         
         Only the least significant 32 bits of this object are used.
         
         This object can only be configured if FrameType is ipv6(5).
         
         This object is only valid if QosCapabilitiesHasQceDip is true."
    ::= { vtssQosConfigQceTableRowEditor 512 }

vtssQosConfigQceTableRowEditorIpv6SrcPortOp OBJECT-TYPE
    SYNTAX      VTSSASRType
    MAX-ACCESS  read-write
    STATUS      current
    DESCRIPTION 
        "Indicates how a packet's source TCP/UDP port number is to be compared.
         
         This object can only be configured if FrameType is ipv6(5)."
    ::= { vtssQosConfigQceTableRowEditor 513 }

vtssQosConfigQceTableRowEditorIpv6SrcPort OBJECT-TYPE
    SYNTAX      VTSSUnsigned16
    MAX-ACCESS  read-write
    STATUS      current
    DESCRIPTION 
        "The source port number of the TCP or UDP protocol.
         
         If the Ipv6SrcPortOp object in the same row is range(2), this object
         will be the starting port number of the port range.
         
         Valid range is 0-65535.
         
         This object can only be configured if FrameType is ipv6(5) and
         Ipv6SrcPortOp is not any(0)."
    ::= { vtssQosConfigQceTableRowEditor 514 }

vtssQosConfigQceTableRowEditorIpv6SrcPortRange OBJECT-TYPE
    SYNTAX      VTSSUnsigned16
    MAX-ACCESS  read-write
    STATUS      current
    DESCRIPTION 
        "The source port number of the TCP or UDP protocol.
         
         If the Ipv6SrcPortOp object in the same row is range(2), this object
         will be the ending port number of the port range.
         
         Valid range is 0-65535.
         
         This object can only be configured if FrameType is ipv6(5) and
         Ipv6SrcPortOp is range(2)."
    ::= { vtssQosConfigQceTableRowEditor 515 }

vtssQosConfigQceTableRowEditorIpv6DestPortOp OBJECT-TYPE
    SYNTAX      VTSSASRType
    MAX-ACCESS  read-write
    STATUS      current
    DESCRIPTION 
        "Indicates how a packet's destination TCP/UDP port number is to be
         compared.
         
         This object can only be configured if FrameType is ipv6(5)."
    ::= { vtssQosConfigQceTableRowEditor 516 }

vtssQosConfigQceTableRowEditorIpv6DestPort OBJECT-TYPE
    SYNTAX      VTSSUnsigned16
    MAX-ACCESS  read-write
    STATUS      current
    DESCRIPTION 
        "The destination port number of the TCP or UDP protocol.
         
         If the Ipv6DestPortOp object in the same row is range(2), this object
         will be the starting port number of the port range.
         
         Valid range is 0-65535.
         
         This object can only be configured if FrameType is ipv6(5) and
         Ipv6DestPortOp is not any(0)."
    ::= { vtssQosConfigQceTableRowEditor 517 }

vtssQosConfigQceTableRowEditorIpv6DestPortRange OBJECT-TYPE
    SYNTAX      VTSSUnsigned16
    MAX-ACCESS  read-write
    STATUS      current
    DESCRIPTION 
        "The source port number of the TCP or UDP protocol.
         
         If the Ipv6DestPortOp object in the same row is range(2), this object
         will be the ending port number of the port range.
         
         Valid range is 0-65535.
         
         This object can only be configured if FrameType is ipv6(5) and
         Ipv6DestPortOp is range(2)."
    ::= { vtssQosConfigQceTableRowEditor 518 }

vtssQosConfigQceTableRowEditorActionCosEnable OBJECT-TYPE
    SYNTAX      TruthValue
    MAX-ACCESS  read-write
    STATUS      current
    DESCRIPTION 
        "If true, the packet is classified to the CoS value in ActionCos."
    ::= { vtssQosConfigQceTableRowEditor 1000 }

vtssQosConfigQceTableRowEditorActionCos OBJECT-TYPE
    SYNTAX      Unsigned32
    MAX-ACCESS  read-write
    STATUS      current
    DESCRIPTION 
        "The CoS value used for classification.
         
         Valid range is qosCapabilitiesClassMin-qosCapabilitiesClassMax."
    ::= { vtssQosConfigQceTableRowEditor 1001 }

vtssQosConfigQceTableRowEditorActionDplEnable OBJECT-TYPE
    SYNTAX      TruthValue
    MAX-ACCESS  read-write
    STATUS      current
    DESCRIPTION 
        "If true, the packet is classified to the DPL value in ActionDpl."
    ::= { vtssQosConfigQceTableRowEditor 1002 }

vtssQosConfigQceTableRowEditorActionDpl OBJECT-TYPE
    SYNTAX      VTSSUnsigned8
    MAX-ACCESS  read-write
    STATUS      current
    DESCRIPTION 
        "The DPL value used for classification.
         
         Valid range is qosCapabilitiesDplMin-qosCapabilitiesDplMax."
    ::= { vtssQosConfigQceTableRowEditor 1003 }

vtssQosConfigQceTableRowEditorActionDscpEnable OBJECT-TYPE
    SYNTAX      TruthValue
    MAX-ACCESS  read-write
    STATUS      current
    DESCRIPTION 
        "If true, the packet is classified to the DSCP value in ActionDscp."
    ::= { vtssQosConfigQceTableRowEditor 1004 }

vtssQosConfigQceTableRowEditorActionDscp OBJECT-TYPE
    SYNTAX      VTSSUnsigned8
    MAX-ACCESS  read-write
    STATUS      current
    DESCRIPTION 
        "The DSCP value used for classification.
         
         Valid range is 0-63."
    ::= { vtssQosConfigQceTableRowEditor 1005 }

vtssQosConfigQceTableRowEditorActionPcpDeiEnable OBJECT-TYPE
    SYNTAX      TruthValue
    MAX-ACCESS  read-write
    STATUS      current
    DESCRIPTION 
        "If true, the packet is classified to the PCP value in ActionPcp and the
         DEI value in ActionDei.
         
         This object is only valid if QosCapabilitiesHasQceActionPcpDei is true."
    ::= { vtssQosConfigQceTableRowEditor 1006 }

vtssQosConfigQceTableRowEditorActionPcp OBJECT-TYPE
    SYNTAX      Unsigned32
    MAX-ACCESS  read-write
    STATUS      current
    DESCRIPTION 
        "The PCP value used for classification.
         
         Valid range is 0-7.
         
         This object is only valid if QosCapabilitiesHasQceActionPcpDei is true."
    ::= { vtssQosConfigQceTableRowEditor 1007 }

vtssQosConfigQceTableRowEditorActionDei OBJECT-TYPE
    SYNTAX      VTSSUnsigned8
    MAX-ACCESS  read-write
    STATUS      current
    DESCRIPTION 
        "The DEI value used for classification.
         
         Valid range is 0-1.
         
         This object is only valid if QosCapabilitiesHasQceActionPcpDei is true."
    ::= { vtssQosConfigQceTableRowEditor 1008 }

vtssQosConfigQceTableRowEditorActionPolicyEnable OBJECT-TYPE
    SYNTAX      TruthValue
    MAX-ACCESS  read-write
    STATUS      current
    DESCRIPTION 
        "If true, the packet is classified to the policy number in ActionPolicy.
         
         This object is only valid if QosCapabilitiesHasQceActionPolicy is true."
    ::= { vtssQosConfigQceTableRowEditor 1009 }

vtssQosConfigQceTableRowEditorActionPolicy OBJECT-TYPE
    SYNTAX      Unsigned32
    MAX-ACCESS  read-write
    STATUS      current
    DESCRIPTION 
        "The policy number used for classification.
         
         Valid range is documented in the ACL MIB.
         
         This object is only valid if QosCapabilitiesHasQceActionPcpDei is true."
    ::= { vtssQosConfigQceTableRowEditor 1010 }

vtssQosConfigQceTableRowEditorAction OBJECT-TYPE
    SYNTAX      VTSSRowEditorState
    MAX-ACCESS  read-write
    STATUS      current
    DESCRIPTION 
        "Action"
    ::= { vtssQosConfigQceTableRowEditor 10000 }

vtssQosConfigQcePrecedenceTable OBJECT-TYPE
    SYNTAX      SEQUENCE OF VTSSQosConfigQcePrecedenceEntry
    MAX-ACCESS  not-accessible
    STATUS      current
    DESCRIPTION 
        "This table contains the precedence of QCEs ordered by their position in
         the QCL.
         
         This is an optional table and is only present if qosCapabilitiesHasQce
         is true."
    ::= { vtssQosConfigQce 3 }

vtssQosConfigQcePrecedenceEntry OBJECT-TYPE
    SYNTAX      VTSSQosConfigQcePrecedenceEntry
    MAX-ACCESS  not-accessible
    STATUS      current
    DESCRIPTION 
        "Each row contains the precedence of a single QCE."
    INDEX       { vtssQosConfigQcePrecedenceIndex }
    ::= { vtssQosConfigQcePrecedenceTable 1 }

VTSSQosConfigQcePrecedenceEntry ::= SEQUENCE {
    vtssQosConfigQcePrecedenceIndex     Integer32,
    vtssQosConfigQcePrecedenceQceId     Unsigned32
}

vtssQosConfigQcePrecedenceIndex OBJECT-TYPE
    SYNTAX      Integer32 (0..2147483647)
    MAX-ACCESS  not-accessible
    STATUS      current
    DESCRIPTION 
        "QCE precedence index. Indicates the position in QCL."
    ::= { vtssQosConfigQcePrecedenceEntry 1 }

vtssQosConfigQcePrecedenceQceId OBJECT-TYPE
    SYNTAX      Unsigned32
    MAX-ACCESS  read-only
    STATUS      current
    DESCRIPTION 
        "QCE Id."
    ::= { vtssQosConfigQcePrecedenceEntry 2 }

vtssQosStatus OBJECT IDENTIFIER
    ::= { vtssQosMibObjects 3 }

vtssQosStatusInterface OBJECT IDENTIFIER
    ::= { vtssQosStatus 2 }

vtssQosStatusInterfaceTable OBJECT-TYPE
    SYNTAX      SEQUENCE OF VTSSQosStatusInterfaceEntry
    MAX-ACCESS  not-accessible
    STATUS      current
    DESCRIPTION 
        "This table provides QoS status for QoS manageable interfaces"
    ::= { vtssQosStatusInterface 1 }

vtssQosStatusInterfaceEntry OBJECT-TYPE
    SYNTAX      VTSSQosStatusInterfaceEntry
    MAX-ACCESS  not-accessible
    STATUS      current
    DESCRIPTION 
        "Each row contains the status for a specific interface"
    INDEX       { vtssQosStatusInterfaceIfIndex }
    ::= { vtssQosStatusInterfaceTable 1 }

VTSSQosStatusInterfaceEntry ::= SEQUENCE {
    vtssQosStatusInterfaceIfIndex   VTSSInterfaceIndex,
    vtssQosStatusInterfaceCos   Unsigned32
}

vtssQosStatusInterfaceIfIndex OBJECT-TYPE
    SYNTAX      VTSSInterfaceIndex
    MAX-ACCESS  not-accessible
    STATUS      current
    DESCRIPTION 
        "Logical interface index."
    ::= { vtssQosStatusInterfaceEntry 1 }

vtssQosStatusInterfaceCos OBJECT-TYPE
    SYNTAX      Unsigned32
    MAX-ACCESS  read-only
    STATUS      current
    DESCRIPTION 
        "Some subsystems are allowed to modify the default CoS value for an
         interface. This object shows the actual default CoS value a packet is
         classified to."
    ::= { vtssQosStatusInterfaceEntry 2 }

vtssQosStatusInterfaceSchedulerTable OBJECT-TYPE
    SYNTAX      SEQUENCE OF VTSSQosStatusInterfaceSchedulerEntry
    MAX-ACCESS  not-accessible
    STATUS      current
    DESCRIPTION 
        "This table contains the mapping of (interface, queue) to weight values.
         
         The mappings given by this table are the 'real' weights in percent as
         used by the hardware."
    ::= { vtssQosStatusInterface 2 }

vtssQosStatusInterfaceSchedulerEntry OBJECT-TYPE
    SYNTAX      VTSSQosStatusInterfaceSchedulerEntry
    MAX-ACCESS  not-accessible
    STATUS      current
    DESCRIPTION 
        "Each row contains the scheduler status for a specific queue."
    INDEX       { vtssQosStatusInterfaceSchedulerIfIndex, vtssQosStatusInterfaceSchedulerQueue }
    ::= { vtssQosStatusInterfaceSchedulerTable 1 }

VTSSQosStatusInterfaceSchedulerEntry ::= SEQUENCE {
    vtssQosStatusInterfaceSchedulerIfIndex      VTSSInterfaceIndex,
    vtssQosStatusInterfaceSchedulerQueue    Integer32,
    vtssQosStatusInterfaceSchedulerWeight   VTSSPercent
}

vtssQosStatusInterfaceSchedulerIfIndex OBJECT-TYPE
    SYNTAX      VTSSInterfaceIndex
    MAX-ACCESS  not-accessible
    STATUS      current
    DESCRIPTION 
        "Logical interface index."
    ::= { vtssQosStatusInterfaceSchedulerEntry 1 }

vtssQosStatusInterfaceSchedulerQueue OBJECT-TYPE
    SYNTAX      Integer32 (0..7)
    MAX-ACCESS  not-accessible
    STATUS      current
    DESCRIPTION 
        "Queue index."
    ::= { vtssQosStatusInterfaceSchedulerEntry 2 }

vtssQosStatusInterfaceSchedulerWeight OBJECT-TYPE
    SYNTAX      VTSSPercent
    MAX-ACCESS  read-only
    STATUS      current
    DESCRIPTION 
        "The weight for this queue.
         
         Valid range is 1-100."
    ::= { vtssQosStatusInterfaceSchedulerEntry 3 }

vtssQosStatusQce OBJECT IDENTIFIER
    ::= { vtssQosStatus 3 }

vtssQosStatusQceTable OBJECT-TYPE
    SYNTAX      SEQUENCE OF VTSSQosStatusQceEntry
    MAX-ACCESS  not-accessible
    STATUS      current
    DESCRIPTION 
        "This table contains the QCE status in the hardware table.
         
         This is an optional table and is only present if QosCapabilitiesHasQce
         is true."
    ::= { vtssQosStatusQce 1 }

vtssQosStatusQceEntry OBJECT-TYPE
    SYNTAX      VTSSQosStatusQceEntry
    MAX-ACCESS  not-accessible
    STATUS      current
    DESCRIPTION 
        "Each row contains the status of a single QCE."
    INDEX       { vtssQosStatusQceSwitchId, vtssQosStatusQceIndex }
    ::= { vtssQosStatusQceTable 1 }

VTSSQosStatusQceEntry ::= SEQUENCE {
    vtssQosStatusQceSwitchId    Unsigned32,
    vtssQosStatusQceIndex   Integer32,
    vtssQosStatusQceUserId      VTSSQosQceUserType,
    vtssQosStatusQceQceId   Unsigned32,
    vtssQosStatusQceConflict    TruthValue
}

vtssQosStatusQceSwitchId OBJECT-TYPE
    SYNTAX      Unsigned32
    MAX-ACCESS  not-accessible
    STATUS      current
    DESCRIPTION 
        "Switch Id index."
    ::= { vtssQosStatusQceEntry 1 }

vtssQosStatusQceIndex OBJECT-TYPE
    SYNTAX      Integer32 (0..2147483647)
    MAX-ACCESS  not-accessible
    STATUS      current
    DESCRIPTION 
        "QCE precedence index. Indicates the position in QCL."
    ::= { vtssQosStatusQceEntry 2 }

vtssQosStatusQceUserId OBJECT-TYPE
    SYNTAX      VTSSQosQceUserType
    MAX-ACCESS  read-only
    STATUS      current
    DESCRIPTION 
        "User Id."
    ::= { vtssQosStatusQceEntry 3 }

vtssQosStatusQceQceId OBJECT-TYPE
    SYNTAX      Unsigned32
    MAX-ACCESS  read-only
    STATUS      current
    DESCRIPTION 
        "QCE Id."
    ::= { vtssQosStatusQceEntry 4 }

vtssQosStatusQceConflict OBJECT-TYPE
    SYNTAX      TruthValue
    MAX-ACCESS  read-only
    STATUS      current
    DESCRIPTION 
        "If true, a resource conflict is detected."
    ::= { vtssQosStatusQceEntry 100 }

vtssQosControl OBJECT IDENTIFIER
    ::= { vtssQosMibObjects 4 }

vtssQosControlQce OBJECT IDENTIFIER
    ::= { vtssQosControl 3 }

vtssQosControlQceConflictResolve OBJECT-TYPE
    SYNTAX      TruthValue
    MAX-ACCESS  read-write
    STATUS      current
    DESCRIPTION 
        "Set to true to resolve resource conflicts.
         
         If different components competes for the same resources in the switch,
         it is possible that some of resources needed by one or more QCE are not
         available.
         
         These conflicts, if any, are shown in the qosStatusQceTable.
         
         To solve these conflicts, you must delete one or more of the competing
         settings and set ConflictResolve to true. The switch will then reapply
         the current QCE configuration.
         
         This object is only valid if QosCapabilitiesHasQce is true."
    ::= { vtssQosControlQce 1 }

vtssQosMibConformance OBJECT IDENTIFIER
    ::= { vtssQosMib 2 }

vtssQosMibCompliances OBJECT IDENTIFIER
    ::= { vtssQosMibConformance 1 }

vtssQosMibGroups OBJECT IDENTIFIER
    ::= { vtssQosMibConformance 2 }

vtssQosCapabilitiesInfoGroup OBJECT-GROUP
    OBJECTS     { vtssQosCapabilitiesClassMin, vtssQosCapabilitiesClassMax, 
                  vtssQosCapabilitiesDplMin, vtssQosCapabilitiesDplMax, 
                  vtssQosCapabilitiesWredGroupMin, 
                  vtssQosCapabilitiesWredGroupMax, vtssQosCapabilitiesWredDplMin, 
                  vtssQosCapabilitiesWredDplMax, vtssQosCapabilitiesQceIdMin, 
                  vtssQosCapabilitiesQceIdMax, 
                  vtssQosCapabilitiesPortPolicerBitRateMin, 
                  vtssQosCapabilitiesPortPolicerBitRateMax, 
                  vtssQosCapabilitiesPortPolicerBitBurstMin, 
                  vtssQosCapabilitiesPortPolicerBitBurstMax, 
                  vtssQosCapabilitiesPortPolicerFrameRateMin, 
                  vtssQosCapabilitiesPortPolicerFrameRateMax, 
                  vtssQosCapabilitiesPortPolicerFrameBurstMin, 
                  vtssQosCapabilitiesPortPolicerFrameBurstMax, 
                  vtssQosCapabilitiesQueuePolicerBitRateMin, 
                  vtssQosCapabilitiesQueuePolicerBitRateMax, 
                  vtssQosCapabilitiesQueuePolicerBitBurstMin, 
                  vtssQosCapabilitiesQueuePolicerBitBurstMax, 
                  vtssQosCapabilitiesQueuePolicerFrameRateMin, 
                  vtssQosCapabilitiesQueuePolicerFrameRateMax, 
                  vtssQosCapabilitiesQueuePolicerFrameBurstMin, 
                  vtssQosCapabilitiesQueuePolicerFrameBurstMax, 
                  vtssQosCapabilitiesPortShaperBitRateMin, 
                  vtssQosCapabilitiesPortShaperBitRateMax, 
                  vtssQosCapabilitiesPortShaperBitBurstMin, 
                  vtssQosCapabilitiesPortShaperBitBurstMax, 
                  vtssQosCapabilitiesPortShaperFrameRateMin, 
                  vtssQosCapabilitiesPortShaperFrameRateMax, 
                  vtssQosCapabilitiesPortShaperFrameBurstMin, 
                  vtssQosCapabilitiesPortShaperFrameBurstMax, 
                  vtssQosCapabilitiesQueueShaperBitRateMin, 
                  vtssQosCapabilitiesQueueShaperBitRateMax, 
                  vtssQosCapabilitiesQueueShaperBitBurstMin, 
                  vtssQosCapabilitiesQueueShaperBitBurstMax, 
                  vtssQosCapabilitiesQueueShaperFrameRateMin, 
                  vtssQosCapabilitiesQueueShaperFrameRateMax, 
                  vtssQosCapabilitiesQueueShaperFrameBurstMin, 
                  vtssQosCapabilitiesQueueShaperFrameBurstMax, 
                  vtssQosCapabilitiesGlobalStormBitRateMin, 
                  vtssQosCapabilitiesGlobalStormBitRateMax, 
                  vtssQosCapabilitiesGlobalStormBitBurstMin, 
                  vtssQosCapabilitiesGlobalStormBitBurstMax, 
                  vtssQosCapabilitiesGlobalStormFrameRateMin, 
                  vtssQosCapabilitiesGlobalStormFrameRateMax, 
                  vtssQosCapabilitiesGlobalStormFrameBurstMin, 
                  vtssQosCapabilitiesGlobalStormFrameBurstMax, 
                  vtssQosCapabilitiesPortStormBitRateMin, 
                  vtssQosCapabilitiesPortStormBitRateMax, 
                  vtssQosCapabilitiesPortStormBitBurstMin, 
                  vtssQosCapabilitiesPortStormBitBurstMax, 
                  vtssQosCapabilitiesPortStormFrameRateMin, 
                  vtssQosCapabilitiesPortStormFrameRateMax, 
                  vtssQosCapabilitiesPortStormFrameBurstMin, 
                  vtssQosCapabilitiesPortStormFrameBurstMax, 
                  vtssQosCapabilitiesDwrrCountMask, 
                  vtssQosCapabilitiesHasGlobalStormPolicers, 
                  vtssQosCapabilitiesHasPortStormPolicers, 
                  vtssQosCapabilitiesHasPortQueuePolicers, 
                  vtssQosCapabilitiesHasWredV1, vtssQosCapabilitiesHasWredV2, 
                  vtssQosCapabilitiesHasFixedTagCosMap, 
                  vtssQosCapabilitiesHasTagClassification, 
                  vtssQosCapabilitiesHasTagRemarking, vtssQosCapabilitiesHasDscp, 
                  vtssQosCapabilitiesHasDscpDplClassification, 
                  vtssQosCapabilitiesHasDscpDplRemarking, 
                  vtssQosCapabilitiesHasPortPolicersFc, 
                  vtssQosCapabilitiesHasQueuePolicersFc, 
                  vtssQosCapabilitiesHasPortShapersDlb, 
                  vtssQosCapabilitiesHasQueueShapersDlb, 
                  vtssQosCapabilitiesHasQueueShapersExcess, 
                  vtssQosCapabilitiesHasWredV3, vtssQosCapabilitiesHasQce, 
                  vtssQosCapabilitiesHasQceAddressMode, 
                  vtssQosCapabilitiesHasQceKeyType, 
                  vtssQosCapabilitiesHasQceMacOui, vtssQosCapabilitiesHasQceDmac, 
                  vtssQosCapabilitiesHasQceDip, vtssQosCapabilitiesHasQceCTag, 
                  vtssQosCapabilitiesHasQceSTag, 
                  vtssQosCapabilitiesHasQceInnerTag, 
                  vtssQosCapabilitiesHasQceActionPcpDei, 
                  vtssQosCapabilitiesHasQceActionPolicy, 
                  vtssQosCapabilitiesHasShapersRt }
    STATUS      current
    DESCRIPTION
        "A collection of objects suitable for bulk operations."
    ::= { vtssQosMibGroups 1 }

vtssQosConfigGlobalsStormPolicersUnicastInfoGroup OBJECT-GROUP
    OBJECTS     { vtssQosConfigGlobalsStormPolicersUnicastEnable, 
                  vtssQosConfigGlobalsStormPolicersUnicastRate, 
                  vtssQosConfigGlobalsStormPolicersUnicastFrameRate }
    STATUS      current
    DESCRIPTION
        "A collection of objects suitable for bulk operations."
    ::= { vtssQosMibGroups 2 }

vtssQosConfigGlobalsStormPolicersMulticastInfoGroup OBJECT-GROUP
    OBJECTS     { vtssQosConfigGlobalsStormPolicersMulticastEnable, 
                  vtssQosConfigGlobalsStormPolicersMulticastRate, 
                  vtssQosConfigGlobalsStormPolicersMulticastFrameRate }
    STATUS      current
    DESCRIPTION
        "A collection of objects suitable for bulk operations."
    ::= { vtssQosMibGroups 3 }

vtssQosConfigGlobalsStormPolicersBroadcastInfoGroup OBJECT-GROUP
    OBJECTS     { vtssQosConfigGlobalsStormPolicersBroadcastEnable, 
                  vtssQosConfigGlobalsStormPolicersBroadcastRate, 
                  vtssQosConfigGlobalsStormPolicersBroadcastFrameRate }
    STATUS      current
    DESCRIPTION
        "A collection of objects suitable for bulk operations."
    ::= { vtssQosMibGroups 4 }

vtssQosConfigGlobalsWredTableInfoGroup OBJECT-GROUP
    OBJECTS     { vtssQosConfigGlobalsWredEnable, 
                  vtssQosConfigGlobalsWredMinimumFillLevel, 
                  vtssQosConfigGlobalsWredMaximum, 
                  vtssQosConfigGlobalsWredMaxSelector, 
                  vtssQosConfigGlobalsWredMaximumDp1, 
                  vtssQosConfigGlobalsWredMaximumDp2, 
                  vtssQosConfigGlobalsWredMaximumDp3 }
    STATUS      current
    DESCRIPTION
        "A collection of objects suitable for bulk operations."
    ::= { vtssQosMibGroups 5 }

vtssQosConfigGlobalsDscpTableInfoGroup OBJECT-GROUP
    OBJECTS     { vtssQosConfigGlobalsDscpTrust, vtssQosConfigGlobalsDscpCos, 
                  vtssQosConfigGlobalsDscpDpl, 
                  vtssQosConfigGlobalsDscpIngressTranslation, 
                  vtssQosConfigGlobalsDscpClassify, 
                  vtssQosConfigGlobalsDscpEgressTranslation, 
                  vtssQosConfigGlobalsDscpEgressTranslationDp1 }
    STATUS      current
    DESCRIPTION
        "A collection of objects suitable for bulk operations."
    ::= { vtssQosMibGroups 6 }

vtssQosConfigGlobalsCosToDscpTableInfoGroup OBJECT-GROUP
    OBJECTS     { vtssQosConfigGlobalsCosToDscpDscp, 
                  vtssQosConfigGlobalsCosToDscpDscpDp1, 
                  vtssQosConfigGlobalsCosToDscpDscpDp2, 
                  vtssQosConfigGlobalsCosToDscpDscpDp3 }
    STATUS      current
    DESCRIPTION
        "A collection of objects suitable for bulk operations."
    ::= { vtssQosMibGroups 7 }

vtssQosConfigInterfaceTableInfoGroup OBJECT-GROUP
    OBJECTS     { vtssQosConfigInterfaceCos, vtssQosConfigInterfaceDpl, 
                  vtssQosConfigInterfacePcp, vtssQosConfigInterfaceDei, 
                  vtssQosConfigInterfaceTrustTag, 
                  vtssQosConfigInterfaceTrustDscp, 
                  vtssQosConfigInterfaceDwrrCount, 
                  vtssQosConfigInterfaceTagRemarkingMode, 
                  vtssQosConfigInterfaceTagPcp, vtssQosConfigInterfaceTagDei, 
                  vtssQosConfigInterfaceDscpTranslate, 
                  vtssQosConfigInterfaceDscpClassify, 
                  vtssQosConfigInterfaceDscpRemark, 
                  vtssQosConfigInterfaceQceAddressMode, 
                  vtssQosConfigInterfaceQceKeyType, 
                  vtssQosConfigInterfaceWredGroup }
    STATUS      current
    DESCRIPTION
        "A collection of objects suitable for bulk operations."
    ::= { vtssQosMibGroups 8 }

vtssQosConfigInterfaceTagToCosTableInfoGroup OBJECT-GROUP
    OBJECTS     { vtssQosConfigInterfaceTagToCosCos, 
                  vtssQosConfigInterfaceTagToCosDpl }
    STATUS      current
    DESCRIPTION
        "A collection of objects suitable for bulk operations."
    ::= { vtssQosMibGroups 9 }

vtssQosConfigInterfaceCosToTagTableInfoGroup OBJECT-GROUP
    OBJECTS     { vtssQosConfigInterfaceCosToTagPcp, 
                  vtssQosConfigInterfaceCosToTagDei }
    STATUS      current
    DESCRIPTION
        "A collection of objects suitable for bulk operations."
    ::= { vtssQosMibGroups 10 }

vtssQosConfigInterfacePolicerTableInfoGroup OBJECT-GROUP
    OBJECTS     { vtssQosConfigInterfacePolicerEnable, 
                  vtssQosConfigInterfacePolicerFrameRate, 
                  vtssQosConfigInterfacePolicerFlowControl, 
                  vtssQosConfigInterfacePolicerCir }
    STATUS      current
    DESCRIPTION
        "A collection of objects suitable for bulk operations."
    ::= { vtssQosMibGroups 11 }

vtssQosConfigInterfaceQueuePolicerTableInfoGroup OBJECT-GROUP
    OBJECTS     { vtssQosConfigInterfaceQueuePolicerEnable, 
                  vtssQosConfigInterfaceQueuePolicerCir }
    STATUS      current
    DESCRIPTION
        "A collection of objects suitable for bulk operations."
    ::= { vtssQosMibGroups 12 }

vtssQosConfigInterfaceShaperTableInfoGroup OBJECT-GROUP
    OBJECTS     { vtssQosConfigInterfaceShaperEnable, 
                  vtssQosConfigInterfaceShaperCir, 
                  vtssQosConfigInterfaceShaperRateType }
    STATUS      current
    DESCRIPTION
        "A collection of objects suitable for bulk operations."
    ::= { vtssQosMibGroups 13 }

vtssQosConfigInterfaceQueueShaperTableInfoGroup OBJECT-GROUP
    OBJECTS     { vtssQosConfigInterfaceQueueShaperEnable, 
                  vtssQosConfigInterfaceQueueShaperExcess, 
                  vtssQosConfigInterfaceQueueShaperCir, 
                  vtssQosConfigInterfaceQueueShaperRateType }
    STATUS      current
    DESCRIPTION
        "A collection of objects suitable for bulk operations."
    ::= { vtssQosMibGroups 14 }

vtssQosConfigInterfaceSchedulerTableInfoGroup OBJECT-GROUP
    OBJECTS     { vtssQosConfigInterfaceSchedulerWeight }
    STATUS      current
    DESCRIPTION
        "A collection of objects suitable for bulk operations."
    ::= { vtssQosMibGroups 15 }

vtssQosConfigInterfaceStormPolicerUnicastTableInfoGroup OBJECT-GROUP
    OBJECTS     { vtssQosConfigInterfaceStormPolicerUnicastEnable, 
                  vtssQosConfigInterfaceStormPolicerUnicastFrameRate, 
                  vtssQosConfigInterfaceStormPolicerUnicastCir }
    STATUS      current
    DESCRIPTION
        "A collection of objects suitable for bulk operations."
    ::= { vtssQosMibGroups 16 }

vtssQosConfigInterfaceStormPolicerBroadcastTableInfoGroup OBJECT-GROUP
    OBJECTS     { vtssQosConfigInterfaceStormPolicerBroadcastEnable, 
                  vtssQosConfigInterfaceStormPolicerBroadcastFrameRate, 
                  vtssQosConfigInterfaceStormPolicerBroadcastCir }
    STATUS      current
    DESCRIPTION
        "A collection of objects suitable for bulk operations."
    ::= { vtssQosMibGroups 17 }

vtssQosConfigInterfaceStormPolicerUnknownTableInfoGroup OBJECT-GROUP
    OBJECTS     { vtssQosConfigInterfaceStormPolicerUnknownEnable, 
                  vtssQosConfigInterfaceStormPolicerUnknownFrameRate, 
                  vtssQosConfigInterfaceStormPolicerUnknownCir }
    STATUS      current
    DESCRIPTION
        "A collection of objects suitable for bulk operations."
    ::= { vtssQosMibGroups 18 }

vtssQosConfigQceTableInfoGroup OBJECT-GROUP
    OBJECTS     { vtssQosConfigQceNextQceId, vtssQosConfigQceSwitchId, 
                  vtssQosConfigQcePortList, vtssQosConfigQceDestMacType, 
                  vtssQosConfigQceDestMac, vtssQosConfigQceDestMacMask, 
                  vtssQosConfigQceSrcMac, vtssQosConfigQceSrcMacMask, 
                  vtssQosConfigQceVlanTagType, vtssQosConfigQceVlanIdOp, 
                  vtssQosConfigQceVlanId, vtssQosConfigQceVlanIdRange, 
                  vtssQosConfigQcePcp, vtssQosConfigQceDei, 
                  vtssQosConfigQceInnerVlanTagType, 
                  vtssQosConfigQceInnerVlanIdOp, vtssQosConfigQceInnerVlanId, 
                  vtssQosConfigQceInnerVlanIdRange, vtssQosConfigQceInnerPcp, 
                  vtssQosConfigQceInnerDei, vtssQosConfigQceFrameType, 
                  vtssQosConfigQceEtype, vtssQosConfigQceLlcDsap, 
                  vtssQosConfigQceLlcDsapMask, vtssQosConfigQceLlcSsap, 
                  vtssQosConfigQceLlcSsapMask, vtssQosConfigQceLlcControl, 
                  vtssQosConfigQceLlcControlMask, vtssQosConfigQceSnapPid, 
                  vtssQosConfigQceSnapPidMask, vtssQosConfigQceIpv4Fragment, 
                  vtssQosConfigQceIpv4DscpOp, vtssQosConfigQceIpv4Dscp, 
                  vtssQosConfigQceIpv4DscpRange, vtssQosConfigQceIpv4Protocol, 
                  vtssQosConfigQceIpv4ProtocolMask, vtssQosConfigQceIpv4SrcIp, 
                  vtssQosConfigQceIpv4SrcIpMask, vtssQosConfigQceIpv4DestIp, 
                  vtssQosConfigQceIpv4DestIpMask, vtssQosConfigQceIpv4SrcPortOp, 
                  vtssQosConfigQceIpv4SrcPort, vtssQosConfigQceIpv4SrcPortRange, 
                  vtssQosConfigQceIpv4DestPortOp, vtssQosConfigQceIpv4DestPort, 
                  vtssQosConfigQceIpv4DestPortRange, vtssQosConfigQceIpv6DscpOp, 
                  vtssQosConfigQceIpv6Dscp, vtssQosConfigQceIpv6DscpRange, 
                  vtssQosConfigQceIpv6Protocol, vtssQosConfigQceIpv6ProtocolMask, 
                  vtssQosConfigQceIpv6SrcIp, vtssQosConfigQceIpv6SrcIpMask, 
                  vtssQosConfigQceIpv6DestIp, vtssQosConfigQceIpv6DestIpMask, 
                  vtssQosConfigQceIpv6SrcPortOp, vtssQosConfigQceIpv6SrcPort, 
                  vtssQosConfigQceIpv6SrcPortRange, 
                  vtssQosConfigQceIpv6DestPortOp, vtssQosConfigQceIpv6DestPort, 
                  vtssQosConfigQceIpv6DestPortRange, 
                  vtssQosConfigQceActionCosEnable, vtssQosConfigQceActionCos, 
                  vtssQosConfigQceActionDplEnable, vtssQosConfigQceActionDpl, 
                  vtssQosConfigQceActionDscpEnable, vtssQosConfigQceActionDscp, 
                  vtssQosConfigQceActionPcpDeiEnable, vtssQosConfigQceActionPcp, 
                  vtssQosConfigQceActionDei, vtssQosConfigQceActionPolicyEnable, 
                  vtssQosConfigQceActionPolicy, vtssQosConfigQceAction }
    STATUS      current
    DESCRIPTION
        "A collection of objects suitable for bulk operations."
    ::= { vtssQosMibGroups 19 }

vtssQosConfigQceTableRowEditorInfoGroup OBJECT-GROUP
    OBJECTS     { vtssQosConfigQceTableRowEditorQceId, 
                  vtssQosConfigQceTableRowEditorNextQceId, 
                  vtssQosConfigQceTableRowEditorSwitchId, 
                  vtssQosConfigQceTableRowEditorPortList, 
                  vtssQosConfigQceTableRowEditorDestMacType, 
                  vtssQosConfigQceTableRowEditorDestMac, 
                  vtssQosConfigQceTableRowEditorDestMacMask, 
                  vtssQosConfigQceTableRowEditorSrcMac, 
                  vtssQosConfigQceTableRowEditorSrcMacMask, 
                  vtssQosConfigQceTableRowEditorVlanTagType, 
                  vtssQosConfigQceTableRowEditorVlanIdOp, 
                  vtssQosConfigQceTableRowEditorVlanId, 
                  vtssQosConfigQceTableRowEditorVlanIdRange, 
                  vtssQosConfigQceTableRowEditorPcp, 
                  vtssQosConfigQceTableRowEditorDei, 
                  vtssQosConfigQceTableRowEditorInnerVlanTagType, 
                  vtssQosConfigQceTableRowEditorInnerVlanIdOp, 
                  vtssQosConfigQceTableRowEditorInnerVlanId, 
                  vtssQosConfigQceTableRowEditorInnerVlanIdRange, 
                  vtssQosConfigQceTableRowEditorInnerPcp, 
                  vtssQosConfigQceTableRowEditorInnerDei, 
                  vtssQosConfigQceTableRowEditorFrameType, 
                  vtssQosConfigQceTableRowEditorEtype, 
                  vtssQosConfigQceTableRowEditorLlcDsap, 
                  vtssQosConfigQceTableRowEditorLlcDsapMask, 
                  vtssQosConfigQceTableRowEditorLlcSsap, 
                  vtssQosConfigQceTableRowEditorLlcSsapMask, 
                  vtssQosConfigQceTableRowEditorLlcControl, 
                  vtssQosConfigQceTableRowEditorLlcControlMask, 
                  vtssQosConfigQceTableRowEditorSnapPid, 
                  vtssQosConfigQceTableRowEditorSnapPidMask, 
                  vtssQosConfigQceTableRowEditorIpv4Fragment, 
                  vtssQosConfigQceTableRowEditorIpv4DscpOp, 
                  vtssQosConfigQceTableRowEditorIpv4Dscp, 
                  vtssQosConfigQceTableRowEditorIpv4DscpRange, 
                  vtssQosConfigQceTableRowEditorIpv4Protocol, 
                  vtssQosConfigQceTableRowEditorIpv4ProtocolMask, 
                  vtssQosConfigQceTableRowEditorIpv4SrcIp, 
                  vtssQosConfigQceTableRowEditorIpv4SrcIpMask, 
                  vtssQosConfigQceTableRowEditorIpv4DestIp, 
                  vtssQosConfigQceTableRowEditorIpv4DestIpMask, 
                  vtssQosConfigQceTableRowEditorIpv4SrcPortOp, 
                  vtssQosConfigQceTableRowEditorIpv4SrcPort, 
                  vtssQosConfigQceTableRowEditorIpv4SrcPortRange, 
                  vtssQosConfigQceTableRowEditorIpv4DestPortOp, 
                  vtssQosConfigQceTableRowEditorIpv4DestPort, 
                  vtssQosConfigQceTableRowEditorIpv4DestPortRange, 
                  vtssQosConfigQceTableRowEditorIpv6DscpOp, 
                  vtssQosConfigQceTableRowEditorIpv6Dscp, 
                  vtssQosConfigQceTableRowEditorIpv6DscpRange, 
                  vtssQosConfigQceTableRowEditorIpv6Protocol, 
                  vtssQosConfigQceTableRowEditorIpv6ProtocolMask, 
                  vtssQosConfigQceTableRowEditorIpv6SrcIp, 
                  vtssQosConfigQceTableRowEditorIpv6SrcIpMask, 
                  vtssQosConfigQceTableRowEditorIpv6DestIp, 
                  vtssQosConfigQceTableRowEditorIpv6DestIpMask, 
                  vtssQosConfigQceTableRowEditorIpv6SrcPortOp, 
                  vtssQosConfigQceTableRowEditorIpv6SrcPort, 
                  vtssQosConfigQceTableRowEditorIpv6SrcPortRange, 
                  vtssQosConfigQceTableRowEditorIpv6DestPortOp, 
                  vtssQosConfigQceTableRowEditorIpv6DestPort, 
                  vtssQosConfigQceTableRowEditorIpv6DestPortRange, 
                  vtssQosConfigQceTableRowEditorActionCosEnable, 
                  vtssQosConfigQceTableRowEditorActionCos, 
                  vtssQosConfigQceTableRowEditorActionDplEnable, 
                  vtssQosConfigQceTableRowEditorActionDpl, 
                  vtssQosConfigQceTableRowEditorActionDscpEnable, 
                  vtssQosConfigQceTableRowEditorActionDscp, 
                  vtssQosConfigQceTableRowEditorActionPcpDeiEnable, 
                  vtssQosConfigQceTableRowEditorActionPcp, 
                  vtssQosConfigQceTableRowEditorActionDei, 
                  vtssQosConfigQceTableRowEditorActionPolicyEnable, 
                  vtssQosConfigQceTableRowEditorActionPolicy, 
                  vtssQosConfigQceTableRowEditorAction }
    STATUS      current
    DESCRIPTION
        "A collection of objects suitable for bulk operations."
    ::= { vtssQosMibGroups 20 }

vtssQosConfigQcePrecedenceTableInfoGroup OBJECT-GROUP
    OBJECTS     { vtssQosConfigQcePrecedenceQceId }
    STATUS      current
    DESCRIPTION
        "A collection of objects suitable for bulk operations."
    ::= { vtssQosMibGroups 21 }

vtssQosStatusInterfaceTableInfoGroup OBJECT-GROUP
    OBJECTS     { vtssQosStatusInterfaceCos }
    STATUS      current
    DESCRIPTION
        "A collection of objects suitable for bulk operations."
    ::= { vtssQosMibGroups 22 }

vtssQosStatusInterfaceSchedulerTableInfoGroup OBJECT-GROUP
    OBJECTS     { vtssQosStatusInterfaceSchedulerWeight }
    STATUS      current
    DESCRIPTION
        "A collection of objects suitable for bulk operations."
    ::= { vtssQosMibGroups 23 }

vtssQosStatusQceTableInfoGroup OBJECT-GROUP
    OBJECTS     { vtssQosStatusQceUserId, vtssQosStatusQceQceId, 
                  vtssQosStatusQceConflict }
    STATUS      current
    DESCRIPTION
        "A collection of objects suitable for bulk operations."
    ::= { vtssQosMibGroups 24 }

vtssQosControlQceInfoGroup OBJECT-GROUP
    OBJECTS     { vtssQosControlQceConflictResolve }
    STATUS      current
    DESCRIPTION
        "A collection of objects suitable for bulk operations."
    ::= { vtssQosMibGroups 25 }

vtssQosMibCompliance MODULE-COMPLIANCE
    STATUS      current
    DESCRIPTION
        "The compliance statement for the implementation."

    MODULE      -- this module

        MANDATORY-GROUPS        { vtssQosCapabilitiesInfoGroup, 
                  vtssQosConfigGlobalsStormPolicersUnicastInfoGroup, 
                  vtssQosConfigGlobalsStormPolicersMulticastInfoGroup, 
                  vtssQosConfigGlobalsStormPolicersBroadcastInfoGroup, 
                  vtssQosConfigGlobalsWredTableInfoGroup, 
                  vtssQosConfigGlobalsDscpTableInfoGroup, 
                  vtssQosConfigGlobalsCosToDscpTableInfoGroup, 
                  vtssQosConfigInterfaceTableInfoGroup, 
                  vtssQosConfigInterfaceTagToCosTableInfoGroup, 
                  vtssQosConfigInterfaceCosToTagTableInfoGroup, 
                  vtssQosConfigInterfacePolicerTableInfoGroup, 
                  vtssQosConfigInterfaceQueuePolicerTableInfoGroup, 
                  vtssQosConfigInterfaceShaperTableInfoGroup, 
                  vtssQosConfigInterfaceQueueShaperTableInfoGroup, 
                  vtssQosConfigInterfaceSchedulerTableInfoGroup, 
                  vtssQosConfigInterfaceStormPolicerUnicastTableInfoGroup, 
                  vtssQosConfigInterfaceStormPolicerBroadcastTableInfoGroup, 
                  vtssQosConfigInterfaceStormPolicerUnknownTableInfoGroup, 
                  vtssQosConfigQceTableInfoGroup, 
                  vtssQosConfigQceTableRowEditorInfoGroup, 
                  vtssQosConfigQcePrecedenceTableInfoGroup, 
                  vtssQosStatusInterfaceTableInfoGroup, 
                  vtssQosStatusInterfaceSchedulerTableInfoGroup, 
                  vtssQosStatusQceTableInfoGroup, vtssQosControlQceInfoGroup }

    ::= { vtssQosMibCompliances 1 }

END
