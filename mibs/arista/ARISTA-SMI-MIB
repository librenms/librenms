-- ARISTA-SMI_MIB: arista structure of management information
-- Copyright (c) 2008 Arista Networks, Inc.  All rights reserved.

ARISTA-SMI-MIB DEFINITIONS ::= BEGIN

IMPORTS
    MODULE-IDENTITY,
    OBJECT-IDENTITY,
    enterprises
        FROM SNMPv2-SMI;

arista MODULE-IDENTITY
    LAST-UPDATED "201408150000Z"
    ORGANIZATION "Arista Networks, Inc."
    CONTACT-INFO
        "Arista Networks, Inc.

         Postal: 5453 Great America Parkway
                 Santa Clara, CA 95054

         Tel: +1 408 547-5500

         E-mail: snmp@arista.com"
    DESCRIPTION
            "The Structure of Management Information for the
            Arista Networks enterprise."
        REVISION      "201408150000Z"
        DESCRIPTION
                "Updated postal and e-mail addresses"
        REVISION      "201103311300Z"
        DESCRIPTION
                "Updated postal address and telephone"
        REVISION      "200810271830Z"
        DESCRIPTION
                "Initial version."
        ::= { enterprises 30065 }        -- assigned by IANA

aristaProducts OBJECT-IDENTITY
    STATUS current
    DESCRIPTION
        "aristaProducts is the root object identifier from
         which sysObjectID values are assigned.  Values are
         defined in ARISTA-PRODUCTS-MIB."
    ::= { arista 1 }

aristaModules OBJECT-IDENTITY
    STATUS current
    DESCRIPTION
        "aristaModules provides a root object identifier
         from which MODULE-IDENTITY values may be assigned."
    ::= { arista 2 }

aristaMibs OBJECT-IDENTITY
    STATUS current
    DESCRIPTION
        "aristaMibs provides a root object identifier
         for management-related MIBs."
    ::= { arista 3 }

aristaExperiment OBJECT-IDENTITY
    STATUS current
    DESCRIPTION
        "aristaExperiment provides a root object identifier
         for experimental MIBs.  The structure of information
         for these MIBs can not be guaranteed between releases."
    ::= { arista 4 }

END
