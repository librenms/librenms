DMOS-MEM-NOTIFICATIONS-MIB DEFINITIONS ::= BEGIN

IMPORTS
    MODULE-IDENTITY,
    OBJECT-TYPE,
    NOTIFICATION-TYPE,
    Gauge32
        FROM SNMPv2-SMI
    OBJECT-GROUP,
    NOTIFICATION-GROUP
        FROM SNMPv2-CONF
    UnsignedPercent
        FROM DMOS-TC-MIB
    dmosNotifications,
    notificationTime,
    notificationName,
    notificationSourceType,
    notificationSourceValue,
    notificationSeverity,
    notificationInfo,
    notificationAlarmState
        FROM DMOS-NOTIFICATIONS-MIB;

dmosMemNotificationsMIB MODULE-IDENTITY
    LAST-UPDATED "201610200000Z"
    ORGANIZATION "DATACOM"
    CONTACT-INFO
                 "DATACOM

                 Postal: DATACOM
                     Rua America, 1000
                     Eldorado do Sul, RS
                     CEP 92990-000
                             BRAZIL

                 Tel:+55(51)3933 3000
                 Fax:+55(51)3933 3003

                 E-mail: datacom@datacom.ind.br "
    DESCRIPTION "The memory notifications designed to be used by notification manager"
    REVISION    "201610200000Z"
    DESCRIPTION "Initial revision"
    ::= { dmosNotifications 1 }

dmosMemNotificationObjects OBJECT IDENTIFIER ::= { dmosMemNotificationsMIB 1 }

dmosMemNotificationThreshold OBJECT-TYPE
    SYNTAX          Gauge32
    UNITS           "Bytes"
    MAX-ACCESS      accessible-for-notify
    STATUS          current
    DESCRIPTION     "Memory alarm threshold."
    ::= { dmosMemNotificationObjects 1 }

dmosMemNotificationInterval OBJECT-TYPE
    SYNTAX          Gauge32
    UNITS           "seconds"
    MAX-ACCESS      accessible-for-notify
    STATUS          current
    DESCRIPTION     "Time interval during which the memory value was above/below the threshold."
    ::= { dmosMemNotificationObjects 2 }

dmosMemNotificationGroups OBJECT IDENTIFIER ::= { dmosMemNotificationsMIB 2 }

dmosMemAlarmInfoGroup OBJECT-GROUP
    OBJECTS { dmosMemNotificationThreshold,
              dmosMemNotificationInterval }
    STATUS      current
    DESCRIPTION
        "A set of objects that provides more information about memory alarms."
    ::= { dmosMemNotificationGroups 1 }

dmosMemAlarmTrapsGroup NOTIFICATION-GROUP
    NOTIFICATIONS { memAvailableLowTrap }
    STATUS      current
    DESCRIPTION
        "Traps generated by memory alarms."
    ::= { dmosMemNotificationGroups 2 }

memAvailableLowTrap NOTIFICATION-TYPE
    OBJECTS {
        notificationTime,
        notificationName,
        notificationSourceType,
        notificationSourceValue,
        notificationSeverity,
        notificationInfo,
        notificationAlarmState,
        dmosMemNotificationThreshold,
        dmosMemNotificationInterval
    }
    STATUS current
    DESCRIPTION
        "Alarm trap for low memory available."
    ::= { dmosMemNotificationsMIB 3 }

END
