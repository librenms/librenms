IPV6-TC DEFINITIONS ::= BEGIN

IMPORTS
     Integer32, MODULE-IDENTITY,
      experimental               FROM SNMPv2-SMI
     TEXTUAL-CONVENTION          FROM SNMPv2-TC;

ipv6TC MODULE-IDENTITY
   LAST-UPDATED "199812010000Z"
   ORGANIZATION ""
   CONTACT-INFO ""
   DESCRIPTION
        "Extracted from RFC 2465.
         Tail-f added dummy MODULE-IDENTITY to make it a legal SMIv2 module."
   ::= { experimental 1 }



-- definition of textual conventions
Ipv6Address ::= TEXTUAL-CONVENTION
     DISPLAY-HINT "2x:"
     STATUS       current
     DESCRIPTION
       "This data type is used to model IPv6 addresses.
        This is a binary string of 16 octets in network
        byte-order."
     SYNTAX       OCTET STRING (SIZE (16))

Ipv6AddressPrefix ::= TEXTUAL-CONVENTION
     DISPLAY-HINT "2x:"
     STATUS       current
     DESCRIPTION
       "This data type is used to model IPv6 address
       prefixes. This is a binary string of up to 16
       octets in network byte-order."
     SYNTAX       OCTET STRING (SIZE (0..16))

Ipv6AddressIfIdentifier ::= TEXTUAL-CONVENTION
     DISPLAY-HINT "2x:"
     STATUS       current
     DESCRIPTION
       "This data type is used to model IPv6 address
       interface identifiers. This is a binary string
        of up to 8 octets in network byte-order."
     SYNTAX      OCTET STRING (SIZE (0..8))

Ipv6IfIndex ::= TEXTUAL-CONVENTION
     DISPLAY-HINT "d"
     STATUS       current
     DESCRIPTION
       "A unique value, greater than zero for each
       internetwork-layer interface in the managed
       system. It is recommended that values are assigned
       contiguously starting from 1. The value for each
       internetwork-layer interface must remain constant
       at least from one re-initialization of the entity's
       network management system to the next
       re-initialization."
     SYNTAX       Integer32 (1..2147483647)

Ipv6IfIndexOrZero ::= TEXTUAL-CONVENTION
     DISPLAY-HINT "d"
     STATUS       current
     DESCRIPTION
         "This textual convention is an extension of the
         Ipv6IfIndex convention.  The latter defines
         a greater than zero value used to identify an IPv6
         interface in the managed system.  This extension
         permits the additional value of zero.  The value
         zero is object-specific and must therefore be
         defined as part of the description of any object
         which uses this syntax.  Examples of the usage of
         zero might include situations where interface was
         unknown, or when none or all interfaces need to be
         referenced."
     SYNTAX       Integer32 (0..2147483647)

END
