DMOS-GPON-NOTIFICATIONS-MIB DEFINITIONS ::= BEGIN

IMPORTS
    MODULE-IDENTITY,
    OBJECT-TYPE,
    NOTIFICATION-TYPE,
    Integer32
        FROM SNMPv2-SMI
    OBJECT-GROUP,
    NOTIFICATION-GROUP
        FROM SNMPv2-CONF
    dmosNotifications,
    notificationTime,
    notificationName,
    notificationSourceType,
    notificationSourceValue,
    notificationSeverity,
    notificationInfo,
    notificationAlarmState
        FROM DMOS-NOTIFICATIONS-MIB;

dmosGponNotificationsMIB MODULE-IDENTITY
    LAST-UPDATED "201805280000Z"
    ORGANIZATION    "DATACOM"
    CONTACT-INFO
                "DATACOM

                 Postal: DATACOM
                     Rua America, 1000
                     Eldorado do Sul, RS
                     CEP 92990-000
                             BRAZIL

                 Tel:+55(51)3933 3000
                 Fax:+55(51)3933 3003

                 E-mail: datacom@datacom.com.br "
    DESCRIPTION
        "DmOS notifications related to GPON events."
    REVISION "201805280000Z"
    DESCRIPTION
        " First release "
    ::= { dmosNotifications 4 }

dmosGponNotificationGroups OBJECT IDENTIFIER ::= { dmosGponNotificationsMIB 1 }

dmosGponAlarmTrapsGroup NOTIFICATION-GROUP
    NOTIFICATIONS { gPonOnuAutoProvAddFailTrap }

    STATUS      current
    DESCRIPTION "Traps generated by GPON alarms."
    ::= { dmosGponNotificationGroups 1 }

gPonOnuAutoProvAddFailTrap    NOTIFICATION-TYPE
    OBJECTS {
        notificationTime,
        notificationName,
        notificationSourceType,
        notificationSourceValue,
        notificationSeverity,
        notificationInfo,
        notificationAlarmState }

    STATUS        current
    DESCRIPTION   "Failure adding ONU during auto provisioning on PON link."
    ::=  {  dmosGponNotificationsMIB 2 }

END
