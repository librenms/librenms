DMOS-HW-MONITOR-NOTIFICATIONS-MIB DEFINITIONS ::= BEGIN

IMPORTS
    MODULE-IDENTITY,
    OBJECT-TYPE,
    NOTIFICATION-TYPE,
    Integer32
        FROM SNMPv2-SMI
    OBJECT-GROUP,
    NOTIFICATION-GROUP
        FROM SNMPv2-CONF
    dmosNotifications,
    notificationTime,
    notificationName,
    notificationSourceType,
    notificationSourceValue,
    notificationSeverity,
    notificationInfo,
    notificationAlarmState
        FROM DMOS-NOTIFICATIONS-MIB;

dmosHwMonNotificationsMIB MODULE-IDENTITY
    LAST-UPDATED "201810110000Z"
    ORGANIZATION    "DATACOM"
    CONTACT-INFO
                "DATACOM

                 Postal: DATACOM
                     Rua America, 1000
                     Eldorado do Sul, RS
                     CEP 92990-000
                             BRAZIL

                 Tel:+55(51)3933 3000
                 Fax:+55(51)3933 3003

                 E-mail: datacom@datacom.ind.br "
    DESCRIPTION
        "This MIB file constains the definition of DmOS notifications related to the hardware monitoring."
    REVISION "201810110000Z"
    DESCRIPTION
        " Adds trap for PSU alarms: PSU status check error "
    REVISION "201809200000Z"
    DESCRIPTION
        " Adds traps for PSU alarms: Power Input Failure and Fuse Failure "
    REVISION "201701300000Z"
    DESCRIPTION
        " First release "
    ::= { dmosNotifications 2 }

dmosHwMonNotificationObjects OBJECT IDENTIFIER ::= { dmosHwMonNotificationsMIB 1 }

dmosHwMonValue OBJECT-TYPE
    SYNTAX      Integer32
    MAX-ACCESS  accessible-for-notify
    STATUS      current
    DESCRIPTION    "Current value that triggered the notification."
    ::= { dmosHwMonNotificationObjects 1 }

dmosHwMonLimitValue OBJECT-TYPE
    SYNTAX      Integer32
    MAX-ACCESS  accessible-for-notify
    STATUS      current
    DESCRIPTION    "Current limit that was overflow and that triggered the notification."
    ::= { dmosHwMonNotificationObjects 2 }

dmosHwMonNotificationGroups OBJECT IDENTIFIER ::= { dmosHwMonNotificationsMIB 2 }

dmosHwMonAlarmInfoGroup OBJECT-GROUP
    OBJECTS { dmosHwMonValue,
              dmosHwMonLimitValue }
    STATUS  current
    DESCRIPTION
        "A set of objects that provides more information about hardware monitoring alarms."
    ::= { dmosHwMonNotificationGroups 1 }

fanHighAlarmTrap    NOTIFICATION-TYPE
    OBJECTS {
        notificationTime,
        notificationName,
        notificationSourceType,
        notificationSourceValue,
        notificationSeverity,
        notificationInfo,
        notificationAlarmState,
        dmosHwMonValue,
        dmosHwMonLimitValue }

    STATUS        current
    DESCRIPTION   "Alarm for fan speed above the safe rpm speed."
    ::=  {  dmosHwMonNotificationsMIB 3 }

fanLowAlarmTrap    NOTIFICATION-TYPE
    OBJECTS {
        notificationTime,
        notificationName,
        notificationSourceType,
        notificationSourceValue,
        notificationSeverity,
        notificationInfo,
        notificationAlarmState,
        dmosHwMonValue,
        dmosHwMonLimitValue }

    STATUS        current
    DESCRIPTION   "Alarm for fan speed below the safe rpm speed."
    ::=  {  dmosHwMonNotificationsMIB 4 }

fanFailAlarmTrap    NOTIFICATION-TYPE
    OBJECTS {
        notificationTime,
        notificationName,
        notificationSourceType,
        notificationSourceValue,
        notificationSeverity,
        notificationInfo,
        notificationAlarmState }

    STATUS        current
    DESCRIPTION   "Alarm for fan in a fail condition. The fan must be checked."
    ::=  {  dmosHwMonNotificationsMIB 5 }

fanErrorAlarmTrap    NOTIFICATION-TYPE
    OBJECTS {
        notificationTime,
        notificationName,
        notificationSourceType,
        notificationSourceValue,
        notificationSeverity,
        notificationInfo,
        notificationAlarmState }

    STATUS        current
    DESCRIPTION   "Alarm to report that an error happened on fan status reading."
    ::=  {  dmosHwMonNotificationsMIB 6 }

dmosFanAlarmTrapsGroup NOTIFICATION-GROUP
    NOTIFICATIONS { fanHighAlarmTrap,
                    fanLowAlarmTrap,
                    fanErrorAlarmTrap,
                    fanFailAlarmTrap }

    STATUS      current
    DESCRIPTION
        "Traps generated by fan alarms."
    ::= { dmosHwMonNotificationGroups 2 }

tempHighAlarmTrap    NOTIFICATION-TYPE
    OBJECTS {
        notificationTime,
        notificationName,
        notificationSourceType,
        notificationSourceValue,
        notificationSeverity,
        notificationInfo,
        notificationAlarmState,
        dmosHwMonValue,
        dmosHwMonLimitValue }

    STATUS        current
    DESCRIPTION   "Alarm for high temperature of the device."
    ::=  {  dmosHwMonNotificationsMIB 7 }

tempLowAlarmTrap    NOTIFICATION-TYPE
    OBJECTS {
        notificationTime,
        notificationName,
        notificationSourceType,
        notificationSourceValue,
        notificationSeverity,
        notificationInfo,
        notificationAlarmState,
        dmosHwMonValue,
        dmosHwMonLimitValue }

    STATUS        current
    DESCRIPTION   "Alarm for low temperature of the device."
    ::=  {  dmosHwMonNotificationsMIB 8 }

tempErrorAlarmTrap    NOTIFICATION-TYPE
    OBJECTS {
        notificationTime,
        notificationName,
        notificationSourceType,
        notificationSourceValue,
        notificationSeverity,
        notificationInfo,
        notificationAlarmState }

    STATUS        current
    DESCRIPTION   "It was not possible to read the temperature sensor."
    ::=  {  dmosHwMonNotificationsMIB 9 }

tempCriticalAlarmTrap    NOTIFICATION-TYPE
    OBJECTS {
        notificationTime,
        notificationName,
        notificationSourceType,
        notificationSourceValue,
        notificationSeverity,
        notificationInfo,
        notificationAlarmState,
        dmosHwMonValue,
        dmosHwMonLimitValue }

    STATUS        current
    DESCRIPTION   "Alarm for critical temperature of the device."
    ::=  {  dmosHwMonNotificationsMIB 10 }

dmosTempAlarmTrapsGroup NOTIFICATION-GROUP
    NOTIFICATIONS { tempHighAlarmTrap,
                    tempLowAlarmTrap,
                    tempErrorAlarmTrap,
                    tempCriticalAlarmTrap }

    STATUS      current
    DESCRIPTION
        "Traps generated by temperature alarms."
    ::= { dmosHwMonNotificationGroups 3 }

psuPowerInputFailureAlarmTrap    NOTIFICATION-TYPE
    OBJECTS {
        notificationTime,
        notificationName,
        notificationSourceType,
        notificationSourceValue,
        notificationSeverity,
        notificationInfo,
        notificationAlarmState }

    STATUS        current
    DESCRIPTION   "Alarm for PSU power input failure."
    ::=  {  dmosHwMonNotificationsMIB 11 }

psuFuseFailureAlarmTrap    NOTIFICATION-TYPE
    OBJECTS {
        notificationTime,
        notificationName,
        notificationSourceType,
        notificationSourceValue,
        notificationSeverity,
        notificationInfo,
        notificationAlarmState }

    STATUS        current
    DESCRIPTION   "Alarm for PSU fuse failure."
    ::=  {  dmosHwMonNotificationsMIB 12 }

psuErrorAlarmTrap    NOTIFICATION-TYPE
    OBJECTS {
        notificationTime,
        notificationName,
        notificationSourceType,
        notificationSourceValue,
        notificationSeverity,
        notificationInfo,
        notificationAlarmState }

    STATUS        current
    DESCRIPTION   "Alarm for PSU status check error."
    ::=  {  dmosHwMonNotificationsMIB 13 }

dmosPsuAlarmTrapsGroup NOTIFICATION-GROUP
    NOTIFICATIONS { psuPowerInputFailureAlarmTrap,
                    psuFuseFailureAlarmTrap,
                    psuErrorAlarmTrap }

    STATUS      current
    DESCRIPTION
        "Traps generated by PSU alarms."
    ::= { dmosHwMonNotificationGroups 4 }

END
