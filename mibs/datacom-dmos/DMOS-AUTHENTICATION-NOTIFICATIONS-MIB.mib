DMOS-AUTHENTICATION-NOTIFICATIONS-MIB DEFINITIONS ::= BEGIN

IMPORTS
    MODULE-IDENTITY,
    NOTIFICATION-TYPE
        FROM SNMPv2-SMI
    dmosNotifications,
    notificationTime,
    notificationName,
    notificationSourceType,
    notificationSourceValue,
    notificationInfo
        FROM DMOS-NOTIFICATIONS-MIB;

dmosAuthenticationNotificationsMIB MODULE-IDENTITY
    LAST-UPDATED "202010190000Z"
    ORGANIZATION    "DATACOM"
    CONTACT-INFO
                "DATACOM

                 Postal: DATACOM
                     Rua America, 1000
                     Eldorado do Sul, RS
                     CEP 92990-000
                             BRAZIL

                 Tel:+55(51)3933 3000
                 Fax:+55(51)3933 3003

                 E-mail: datacom@datacom.ind.br "
    DESCRIPTION "DmOS MIB module for authentication notifications."
    REVISION "202010190000Z"
    DESCRIPTION " First release "
    ::= { dmosNotifications 7 }

dmosAuthenticationNotificationGroups OBJECT IDENTIFIER ::= { dmosAuthenticationNotificationsMIB 1 }

loginFail    NOTIFICATION-TYPE
    OBJECTS {
        notificationTime,
        notificationName,
        notificationSourceType,
        notificationSourceValue,
        notificationInfo }

    STATUS        current
    DESCRIPTION   "Login failure trap."
    ::=  {  dmosAuthenticationNotificationsMIB 2 }

loginSuccess    NOTIFICATION-TYPE
    OBJECTS {
        notificationTime,
        notificationName,
        notificationSourceType,
        notificationSourceValue,
        notificationInfo }

    STATUS        current
    DESCRIPTION   "Login success trap."
    ::=  {  dmosAuthenticationNotificationsMIB 3 }

END
