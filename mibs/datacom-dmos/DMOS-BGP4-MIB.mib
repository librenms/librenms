DMOS-BGP4-MIB DEFINITIONS ::= BEGIN
IMPORTS
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
    InetAddressType,
    InetAddress
        FROM INET-ADDRESS-MIB
    datacomDevicesMIBs
        FROM DATACOM-SMI
;

dmosBgpCountersMIB MODULE-IDENTITY
    LAST-UPDATED "202007070000Z"
    ORGANIZATION "DATACOM"
    CONTACT-INFO
                 "DATACOM

                 Postal: DATACOM
                     Rua America, 1000
                     Eldorado do Sul, RS
                     CEP 92990-000
                             BRAZIL

                 Tel:+55(51)3933 3000
                 Fax:+55(51)3933 3003

                 E-mail: datacom@datacom.ind.br "
    DESCRIPTION "The DmOS MIB module for the BGP-4 protocol."
    REVISION "202007070000Z"
    DESCRIPTION "Initial revision."
    ::= { datacomDevicesMIBs 13 }

BgpSafi ::= TEXTUAL-CONVENTION
    STATUS      current
    DESCRIPTION ""
    SYNTAX      INTEGER {none(0),unicast(1),mplsVpn(128)}

bgpPrefixCountersTable OBJECT-TYPE
    SYNTAX      SEQUENCE OF BgpPrefixCountersEntry
    MAX-ACCESS  not-accessible
    STATUS      current
    DESCRIPTION "BGP prefix counter table. This table contains the prefix counters for each peer."
    ::= { dmosBgpCountersMIB 1 }

bgpPrefixCountersEntry OBJECT-TYPE
    SYNTAX      BgpPrefixCountersEntry
    MAX-ACCESS  not-accessible
    STATUS      current
    DESCRIPTION ""
    INDEX { bgpPrefixCountersRemoteAddressType, bgpPrefixCountersRemoteAddress, bgpPrefixCountersFamilyAfi, bgpPrefixCountersFamilySafi }
        ::= { bgpPrefixCountersTable 1 }

BgpPrefixCountersEntry ::=
    SEQUENCE {
        bgpPrefixCountersRemoteAddressType InetAddressType,
        bgpPrefixCountersRemoteAddress InetAddress,
        bgpPrefixCountersFamilyAfi INTEGER,
        bgpPrefixCountersFamilySafi BgpSafi,
        bgpPrefixCountersInPrefixes Gauge32,
        bgpPrefixCountersInAcceptedPrefixes Gauge32,
        bgpPrefixCountersInRejectedPrefixes Gauge32,
        bgpPrefixCountersOutPrefixes Gauge32,
        bgpPrefixCountersOutAdvertisedPrefixes Gauge32,
        bgpPrefixCountersInActivePrefixes Gauge32,
        bgpPrefixCountersInPrefixesDeniedByPol Gauge32
    }

bgpPrefixCountersRemoteAddressType OBJECT-TYPE
    SYNTAX      InetAddressType
    MAX-ACCESS  not-accessible
    STATUS      current
    DESCRIPTION "The type of the remote address."
    ::= { bgpPrefixCountersEntry 1 }

bgpPrefixCountersRemoteAddress OBJECT-TYPE
    SYNTAX      InetAddress
    MAX-ACCESS  not-accessible
    STATUS      current
    DESCRIPTION "The peer IP address."
    ::= { bgpPrefixCountersEntry 2 }

bgpPrefixCountersFamilyAfi OBJECT-TYPE
    SYNTAX      INTEGER {unknown(0),ipv4(1),ipv6(2),ipv4z(3),ipv6z(4),dns(16)}
    MAX-ACCESS  not-accessible
    STATUS      current
    DESCRIPTION "The Address Family Identifier."
    ::= { bgpPrefixCountersEntry 3 }

bgpPrefixCountersFamilySafi OBJECT-TYPE
    SYNTAX      BgpSafi
    MAX-ACCESS  not-accessible
    STATUS      current
    DESCRIPTION "The Subsequent Address Family Identifiers."
    ::= { bgpPrefixCountersEntry 4 }

bgpPrefixCountersInPrefixes OBJECT-TYPE
    SYNTAX      Gauge32
    MAX-ACCESS  read-only
    STATUS      current
    DESCRIPTION "The number of prefixes received from a peer and are stored in the Adj-Ribs-In for that peer."
    ::= { bgpPrefixCountersEntry 5 }

bgpPrefixCountersInAcceptedPrefixes OBJECT-TYPE
    SYNTAX      Gauge32
    MAX-ACCESS  read-only
    STATUS      current
    DESCRIPTION "The number of prefixes for a peer that are installed in the Adj-Ribs-In and are eligible to become active in the Loc-Rib."
    ::= { bgpPrefixCountersEntry 6 }

bgpPrefixCountersInRejectedPrefixes OBJECT-TYPE
    SYNTAX      Gauge32
    MAX-ACCESS  read-only
    STATUS      current
    DESCRIPTION "The number of prefixes for a peer that are installed in the Adj-Ribs-In and are NOT eligible to become active in the Loc-Rib."
    ::= { bgpPrefixCountersEntry 7 }

bgpPrefixCountersOutPrefixes OBJECT-TYPE
    SYNTAX      Gauge32
    MAX-ACCESS  read-only
    STATUS      current
    DESCRIPTION "The number of prefixes for a peer that are installed in that peer's Adj-Ribs-Out."
    ::= { bgpPrefixCountersEntry 8 }

bgpPrefixCountersOutAdvertisedPrefixes OBJECT-TYPE
    SYNTAX      Gauge32
    MAX-ACCESS  read-only
    STATUS      current
    DESCRIPTION "The number of advertised prefixes currently associated with the peer."
    ::= { bgpPrefixCountersEntry 9 }

bgpPrefixCountersInActivePrefixes OBJECT-TYPE
    SYNTAX      Gauge32
    MAX-ACCESS  read-only
    STATUS      current
    DESCRIPTION "The number of prefixes for a peer that are installed in the Adj-RIB-In and are marked as 'active' in the Loc-Rib."
    ::= { bgpPrefixCountersEntry 10 }

bgpPrefixCountersInPrefixesDeniedByPol OBJECT-TYPE
    SYNTAX      Gauge32
    MAX-ACCESS  read-only
    STATUS      current
    DESCRIPTION "The number of times a received prefix has been denied, and therefore not installed in the Adj-RIB-In, because of local filter policy."
    ::= { bgpPrefixCountersEntry 11 }

END
