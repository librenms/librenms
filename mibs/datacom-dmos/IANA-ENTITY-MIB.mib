IANA-ENTITY-MIB DEFINITIONS ::= BEGIN

     IMPORTS
       MODULE-IDENTITY, mib-2
         FROM SNMPv2-SMI             -- RFC 2578
       TEXTUAL-CONVENTION
         FROM SNMPv2-TC              -- RFC 2579
       ;

     ianaEntityMIB MODULE-IDENTITY
       LAST-UPDATED "201304050000Z"  -- April 5, 2013
       ORGANIZATION "IANA"
       CONTACT-INFO
                    "Internet Assigned Numbers Authority
                     Postal: ICANN
                             12025 Waterfront Drive, Suite 300
                             Los Angeles, CA 90094-2536

                     Phone: +1-310-301-5800
                     EMail: iana@iana.org"





       DESCRIPTION
         "This MIB module defines a TEXTUAL-CONVENTION that provides
         an indication of the general hardware type of a particular
         physical entity.

         Copyright (c) 2013 IETF Trust and the persons identified as
         authors of the code.  All rights reserved.

         Redistribution and use in source and binary forms, with or
         without modification, is permitted pursuant to, and subject
         to the license terms contained in, the Simplified BSD
         License set forth in Section 4.c of the IETF Trust's Legal
         Provisions Relating to IETF Documents
         (http://trustee.ietf.org/license-info).

         The initial version of this MIB module was published in
         RFC 6933; for full legal notices see the RFC itself."

       REVISION     "201304050000Z"  -- April 5, 2013
       DESCRIPTION  "Initial version of this MIB as published in
                     RFC 6933."

       ::= { mib-2 216 }

     -- Textual Conventions

IANAPhysicalClass ::= TEXTUAL-CONVENTION
    STATUS            current
    DESCRIPTION
            "An enumerated value that provides an indication of the
            general hardware type of a particular physical entity.
            There are no restrictions as to the number of
            entPhysicalEntries of each entPhysicalClass, which must
            be instantiated by an agent.

            The enumeration 'other' is applicable if the physical
            entity class is known but does not match any of the
            supported values.

            The enumeration 'unknown' is applicable if the physical
            entity class is unknown to the agent.

            The enumeration 'chassis' is applicable if the physical
            entity class is an overall container for networking
            equipment.  Any class of physical entity, except a stack,
            may be contained within a chassis; a chassis may only
            be contained within a stack.



            The enumeration 'backplane' is applicable if the physical
            entity class is some sort of device for aggregating and
            forwarding networking traffic, such as a shared
            backplane in a modular ethernet switch.  Note that an
            agent may model a backplane as a single physical entity,
            which is actually implemented as multiple discrete
            physical components (within a chassis or stack).

            The enumeration 'container' is applicable if the
            physical entity class is capable of containing one or
            more removable physical entities, possibly of different
            types.  For example, each (empty or full) slot in a
            chassis will be modeled as a container.  Note that all
            removable physical entities should be modeled within
            a container entity, such as field-replaceable modules,
            fans, or power supplies.  Note that all known containers
            should be modeled by the agent, including empty
            containers.

            The enumeration 'powerSupply' is applicable if the
            physical entity class is a power-supplying component.

            The enumeration 'fan' is applicable if the physical
            entity class is a fan or other heat-reduction component.

            The enumeration 'sensor' is applicable if the physical
            entity class is some sort of sensor, such as a
            temperature sensor within a router chassis.

            The enumeration 'module' is applicable if the physical
            entity class is some sort of self-contained sub-system.
            If the enumeration 'module' is removable, then it should
            be modeled within a container entity; otherwise, it
            should be modeled directly within another physical
            entity (e.g., a chassis or another module).

            The enumeration 'port' is applicable if the physical
            entity class is some sort of networking port, capable
            of receiving and/or transmitting networking traffic.

            The enumeration 'stack' is applicable if the physical
            entity class is some sort of super-container (possibly
            virtual) intended to group together multiple chassis
            entities.  A stack may be realized by a 'virtual' cable,
            a real interconnect cable attached to multiple chassis,
            or multiple interconnect cables.  A stack should not be




            modeled within any other physical entities, but a stack
            may be contained within another stack.  Only chassis
            entities should be contained within a stack.

            The enumeration 'cpu' is applicable if the physical
            entity class is some sort of central processing unit.

            The enumeration 'energyObject' is applicable if the
            physical entity is some sort of energy object, i.e.,
            a piece of equipment that is part of or attached to
            a communications network that is monitored, controlled,
            or aids in the management of another device for Energy
            Management.

            The enumeration 'battery' is applicable if the physical
            entity class is some sort of battery."

    SYNTAX      INTEGER  {
       other(1),
       unknown(2),
       chassis(3),
       backplane(4),
       container(5), -- e.g., chassis slot or daughter-card holder
       powerSupply(6),
       fan(7),
       sensor(8),
       module(9),        -- e.g., plug-in card or daughter-card
       port(10),
       stack(11),        -- e.g., stack of multiple chassis entities
       cpu(12),
       energyObject(13),
       battery (14)
    }

END
