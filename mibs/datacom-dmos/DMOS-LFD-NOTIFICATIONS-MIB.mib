DMOS-LFD-NOTIFICATIONS-MIB DEFINITIONS ::= BEGIN

IMPORTS
    MODULE-IDENTITY,
    OBJECT-TYPE,
    NOTIFICATION-TYPE
        FROM SNMPv2-SMI
    OBJECT-GROUP,
    NOTIFICATION-GROUP
        FROM SNMPv2-CONF
    dmosNotifications,
    notificationTime,
    notificationName,
    notificationSourceType,
    notificationSourceValue,
    notificationSeverity,
    notificationInfo,
    notificationAlarmState
        FROM DMOS-NOTIFICATIONS-MIB;

dmosLfdNotificationsMIB MODULE-IDENTITY
    LAST-UPDATED "201905270000Z"
    ORGANIZATION    "DATACOM"
    CONTACT-INFO
                "DATACOM

                 Postal: DATACOM
                     Rua America, 1000
                     Eldorado do Sul, RS
                     CEP 92990-000
                             BRAZIL

                 Tel:+55(51)3933 3000
                 Fax:+55(51)3933 3003

                 E-mail: datacom@datacom.com.br "
    DESCRIPTION
        "DmOS notifications related to link flap detection events."
    REVISION "201905270000Z"
    DESCRIPTION
        " First release "
    ::= { dmosNotifications 7 }

dmosLfdNotificationGroups OBJECT IDENTIFIER ::= { dmosLfdNotificationsMIB 1 }

dmosLfdAlarmTrapsGroup NOTIFICATION-GROUP
    NOTIFICATIONS { linkFlapDetectedAlarmTrap }

    STATUS      current
    DESCRIPTION "Traps generated by link flap detection alarms."
    ::= { dmosLfdNotificationGroups 1 }

linkFlapDetectedAlarmTrap    NOTIFICATION-TYPE
    OBJECTS {
        notificationTime,
        notificationName,
        notificationSourceType,
        notificationSourceValue,
        notificationSeverity,
        notificationInfo,
        notificationAlarmState }

    STATUS        current
    DESCRIPTION   "Link flap detected alarm trap."
    ::=  {  dmosLfdNotificationsMIB 2 }

END
