DMOS-LBD-NOTIFICATIONS-MIB DEFINITIONS ::= BEGIN

IMPORTS
    MODULE-IDENTITY,
    OBJECT-TYPE,
    NOTIFICATION-TYPE
        FROM SNMPv2-SMI
    OBJECT-GROUP,
    NOTIFICATION-GROUP
        FROM SNMPv2-CONF
    dmosNotifications,
    notificationTime,
    notificationName,
    notificationSourceType,
    notificationSourceValue,
    notificationSeverity,
    notificationInfo,
    notificationAlarmState
        FROM DMOS-NOTIFICATIONS-MIB;

dmosLbdNotificationsMIB MODULE-IDENTITY
    LAST-UPDATED "201904220000Z"
    ORGANIZATION    "DATACOM"
    CONTACT-INFO
                "DATACOM

                 Postal: DATACOM
                     Rua America, 1000
                     Eldorado do Sul, RS
                     CEP 92990-000
                             BRAZIL

                 Tel:+55(51)3933 3000
                 Fax:+55(51)3933 3003

                 E-mail: datacom@datacom.com.br "
    DESCRIPTION
        "DmOS notifications related to loopback detection events."
    REVISION "201904220000Z"
    DESCRIPTION
        " First release "
    ::= { dmosNotifications 6 }

dmosLbdNotificationGroups OBJECT IDENTIFIER ::= { dmosLbdNotificationsMIB 1 }

dmosLbdAlarmTrapsGroup NOTIFICATION-GROUP
    NOTIFICATIONS { loopbackDetectedAlarmTrap }

    STATUS      current
    DESCRIPTION "Traps generated by loopback detection alarms."
    ::= { dmosLbdNotificationGroups 1 }

loopbackDetectedAlarmTrap    NOTIFICATION-TYPE
    OBJECTS {
        notificationTime,
        notificationName,
        notificationSourceType,
        notificationSourceValue,
        notificationSeverity,
        notificationInfo,
        notificationAlarmState }

    STATUS        current
    DESCRIPTION   "Loopback detected alarm trap."
    ::=  {  dmosLbdNotificationsMIB 2 }

END
