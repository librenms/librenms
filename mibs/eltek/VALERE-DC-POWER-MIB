VALERE-DC-POWER-MIB DEFINITIONS ::= BEGIN

	IMPORTS
	   MODULE-IDENTITY, OBJECT-TYPE, NOTIFICATION-TYPE,
	   OBJECT-IDENTITY, Counter32, Gauge32, Integer32,
	   enterprises
	       FROM SNMPv2-SMI
	   DisplayString, TimeStamp, TimeInterval, TestAndIncr,
	     AutonomousType, TEXTUAL-CONVENTION
	       FROM SNMPv2-TC
	   MODULE-COMPLIANCE, OBJECT-GROUP
	       FROM SNMPv2-CONF
	          sysUpTime		  FROM RFC1213-MIB;
	--
	-- date and time in UTC format YYMMDDHHmmZ
	--
	   vpwrDcPowerMgt	MODULE-IDENTITY
	                    LAST-UPDATED "0512020000Z"
	                    ORGANIZATION "Valere Power Inc."
	                    CONTACT-INFO
	                         "Contact: Valere Customer Support
	                          Postal:  661 N. Plano Road, Suite 300
	                                   Richardson, TX-75081
	                          Web:      http://www.valerepower.com
	                          email:    support@valerepower.com
	                          Phone     866-240-6614
	                         "
	                    DESCRIPTION

	                    " MIB Version 0.8
	                      Need description here.
	                      History
										Add table to retrieve module inventory info
						  MIB Version 0.7
						  Dec 1, 05		
						                Fixed HP Openview error
						                Fixed warnings generated by MG-SOFT
										Add table to retrieve rectifier inventory info
						  MIB Version 0.6				
	                      Feb 10, 2004  Added additional traps.
	                                    Defined Ringers and other modules.
	                      Feb 08, 2003  Changed vpwrTrapDestinationTable to vpwrTrapTable
	                                    Corrected entry for vpwrTrapTable to be VpwrTrapTableEntry
	                                    This fixes errors generated by MG-SOFT mib compiler.
	                      Oct 30, 2002  initial release - version 0.4
	                    "

	                    ::= {enterprises 13858}

	PositiveInteger ::= TEXTUAL-CONVENTION
	   DISPLAY-HINT "d"
	   STATUS       current
	   DESCRIPTION
	           "This data type is a non-zero and non-negative value."
	   SYNTAX       INTEGER (1..2147483647)

	NonNegativeInteger ::= TEXTUAL-CONVENTION
	   DISPLAY-HINT "d"
	   STATUS       current
	   DESCRIPTION
	           "This data type is a non-negative value."
	   SYNTAX       INTEGER (0..2147483647)



	   vpwrDcPowerProducts         OBJECT IDENTIFIER ::=  { vpwrDcPowerMgt 1 }
	   vpwrDcPowerSystem           OBJECT IDENTIFIER ::=  { vpwrDcPowerMgt 2 }
	   vpwrDcPowerRectifier        OBJECT IDENTIFIER ::=  { vpwrDcPowerMgt 3 }
	   vpwrDcPowerLvd              OBJECT IDENTIFIER ::=  { vpwrDcPowerMgt 4 }
	   vpwrDcPowerTest             OBJECT IDENTIFIER ::=  { vpwrDcPowerMgt 5 }
	   vpwrDcPowerModuleIdent      OBJECT IDENTIFIER ::=  { vpwrDcPowerMgt 6 }
	   vpwrDcPowerBatteryGroup     OBJECT IDENTIFIER ::=  { vpwrDcPowerMgt 7 }
	   vpwrDcPowerAlarmGroup       OBJECT IDENTIFIER ::=  { vpwrDcPowerMgt 8 }
	   vpwrDcPowerSnmpConfig       OBJECT IDENTIFIER ::=  { vpwrDcPowerMgt 9 }
	   vpwrDcPowerTraps            OBJECT IDENTIFIER ::=  { vpwrDcPowerMgt 10 }
	   vpwrDcPowerTrapsMsgString   OBJECT IDENTIFIER ::=  { vpwrDcPowerMgt 11 }

	   vpwrDcPowerRinger           OBJECT IDENTIFIER ::=  { vpwrDcPowerMgt 12 }
	   vpwrDcPowerDcDcConverter    OBJECT IDENTIFIER ::=  { vpwrDcPowerMgt 13 }
	   vpwrDcPowerDcAcInverter     OBJECT IDENTIFIER ::=  { vpwrDcPowerMgt 14 }
	   vpwrDcPowerBayController    OBJECT IDENTIFIER ::=  { vpwrDcPowerMgt 15 }
	   vpwrDcPowerIoModule         OBJECT IDENTIFIER ::=  { vpwrDcPowerMgt 16 }
	   vpwrDcPowerDist             OBJECT IDENTIFIER ::=  { vpwrDcPowerMgt 17 }
	   vpwrDcPowerTrio             OBJECT IDENTIFIER ::=  { vpwrDcPowerMgt 18 }

--       vpwrDcPowerTraps            OBJECT IDENTIFIER ::=  { vpwrDcPowerTrapsRoot 0 }

	   vpwrSystemIdentGroup        OBJECT IDENTIFIER ::=  { vpwrDcPowerSystem 1 }
	   vpwrSystemConfigGroup       OBJECT IDENTIFIER ::=  { vpwrDcPowerSystem 2 }
	   vpwrSystemParameterGroup    OBJECT IDENTIFIER ::=  { vpwrDcPowerSystem 3 }
	   vpwrSystemPanelIdentGroup   OBJECT IDENTIFIER ::=  { vpwrDcPowerSystem 4 }
	   vpwrSystemBayctrlIdentGroup OBJECT IDENTIFIER ::=  { vpwrDcPowerSystem 5 }

	   vpwrLvdConfigGroup          OBJECT IDENTIFIER ::=  { vpwrDcPowerLvd 1 }
	   vpwrLvdAlarmGroup           OBJECT IDENTIFIER ::=  { vpwrDcPowerLvd 2 }
	   vpwrLvdTestGroup            OBJECT IDENTIFIER ::=  { vpwrDcPowerLvd 3 }

	   vpwrRectifierConfigGroup    OBJECT IDENTIFIER ::=  { vpwrDcPowerRectifier 1 }
	   vpwrRectifierAlarmGroup     OBJECT IDENTIFIER ::=  { vpwrDcPowerRectifier 2 }
	   vpwrRectifierTestGroup      OBJECT IDENTIFIER ::=  { vpwrDcPowerRectifier 3 }

	   vpwrBatteryTempGroup                OBJECT IDENTIFIER ::=  { vpwrDcPowerBatteryGroup 1 }
	   vpwrBatteryCurrentGroup             OBJECT IDENTIFIER ::=  { vpwrDcPowerBatteryGroup 2 }
	   vpwrBatteryBoostGroup               OBJECT IDENTIFIER ::=  { vpwrDcPowerBatteryGroup 3 }
	   vpwrBatteryDischargeTestGroup       OBJECT IDENTIFIER ::=  { vpwrDcPowerBatteryGroup 4 }


	   vpwrRingerConfigGroup          OBJECT IDENTIFIER ::=  { vpwrDcPowerRinger 1 }
	   vpwrRingerAlarmGroup           OBJECT IDENTIFIER ::=  { vpwrDcPowerRinger 2 }
	   vpwrRingerTestGroup            OBJECT IDENTIFIER ::=  { vpwrDcPowerRinger 3 }

	   vpwrDcDcConverterConfigGroup    OBJECT IDENTIFIER ::=  { vpwrDcPowerDcDcConverter 1 }
	   vpwrDcDcConverterAlarmGroup     OBJECT IDENTIFIER ::=  { vpwrDcPowerDcDcConverter 2 }
	   vpwrDcDcConverterTestGroup      OBJECT IDENTIFIER ::=  { vpwrDcPowerDcDcConverter 3 }


	   vpwrDcAcInverterConfigGroup    OBJECT IDENTIFIER ::=  { vpwrDcPowerDcAcInverter 1 }
	   vpwrDcAcInverterAlarmGroup     OBJECT IDENTIFIER ::=  { vpwrDcPowerDcAcInverter 2 }
	   vpwrDcAcInverterTestGroup      OBJECT IDENTIFIER ::=  { vpwrDcPowerDcAcInverter 3 }

	   -- vpwrAcLineModuleConfigGroup    OBJECT IDENTIFIER ::=  { vpwrDcPowerAcLineModule 1 }
	   -- vpwrAcLineModuleAlarmGroup     OBJECT IDENTIFIER ::=  { vpwrDcPowerAcLineModule 2 }
	   -- vpwrAcLineModuleTestGroup      OBJECT IDENTIFIER ::=  { vpwrDcPowerAcLineModule 3 }

	   vpwrIoModuleConfigGroup        OBJECT IDENTIFIER ::=  { vpwrDcPowerIoModule 1 }
	   vpwrIoModuleAlarmGroup         OBJECT IDENTIFIER ::=  { vpwrDcPowerIoModule 2 }
	   vpwrIoModuleTestGroup          OBJECT IDENTIFIER ::=  { vpwrDcPowerIoModule 3 }

	--
	-- The Identification group.
	--


	vpwrIdentManufacturer OBJECT-TYPE
	   SYNTAX     DisplayString (SIZE (0..31))
	   MAX-ACCESS read-only
	   STATUS     current
	   DESCRIPTION
	           "The name of the DC Power manufacturer."
	   ::= { vpwrSystemIdentGroup 1 }

	vpwrIdentModel OBJECT-TYPE
	   SYNTAX     DisplayString (SIZE (0..15))
	   MAX-ACCESS read-only
	   STATUS     current
	   DESCRIPTION
	           "The DC Power Model designation."
	   ::= { vpwrSystemIdentGroup 2 }

	vpwrIdentControllerVersion OBJECT-TYPE
	   SYNTAX     DisplayString (SIZE (0..15))
	   MAX-ACCESS read-only
	   STATUS     current
	   DESCRIPTION
	           "The hardware/firmware version(s).  This variable
	           may or may not have the same value as
	           vpwrIdentAgentSoftwareVersion."
	   ::= { vpwrSystemIdentGroup 3 }

	vpwrIdentAgentSoftwareVersion OBJECT-TYPE
	   SYNTAX     DisplayString (SIZE (0..15))
	   MAX-ACCESS read-only
	   STATUS     current
	   DESCRIPTION
	           "The SNMP agent software version.  This variable may or
	           may not have the same value as
	           vpwrIdentControllerFirmwareVersion."
	   ::= { vpwrSystemIdentGroup 4 }

	vpwrIdentName OBJECT-TYPE
	   SYNTAX     DisplayString (SIZE(0..31))
	   MAX-ACCESS read-write
	   STATUS     current
	   DESCRIPTION
	           "A string identifying the system.  This object should be
	           set by the administrator."
	   ::= { vpwrSystemIdentGroup 5 }

	--
	-- The System Identifier group.
	--      All objects in this group are read-only. It describes
	--      various modules (rectifiers, converters, ringers, LVDs, etc.) that make up
	--      the power system and are inserted into a shelf(.1) or panel(.2)
	--
	vpwrSystemIdentTable OBJECT-TYPE
	   SYNTAX     SEQUENCE OF VpwrSystemIdentEntry
	   MAX-ACCESS not-accessible
	   STATUS     current
	   DESCRIPTION
	   " This table describes shelves and modules
	     that make up the sysetm.
	   "
	   ::= { vpwrSystemIdentGroup 6 }

	--
	-- The System Identifier Entry.  Defines the sequence for module tables.
	--
   vpwrSystemIdentEntry OBJECT-TYPE
       SYNTAX     VpwrSystemIdentEntry
       MAX-ACCESS not-accessible
       STATUS     current
       DESCRIPTION
               "An entry containing information applicable to a
               particular alarm."
       INDEX { vpwrBayIndex,  vpwrModuleIndex }
       ::= { vpwrSystemIdentTable 1 }


	VpwrSystemIdentEntry ::= SEQUENCE {
	   vpwrBayIndex         PositiveInteger,
	   vpwrModuleIndex      PositiveInteger,
	   vpwrModuleOID        OBJECT IDENTIFIER  ,
	   vpwrModuleCurrent    INTEGER ,
	   vpwrModuleOperStatus INTEGER ,
	   vpwrModuleCapacity   INTEGER 
	}

	--
	-- The System Shelf Identifier group.
	--
	--	vpwrShelfIdentEntry OBJECT-TYPE
	--	   SYNTAX     VpwrSystemIdentEntry
	--	   MAX-ACCESS not-accessible
	--	   STATUS     current
	--	   DESCRIPTION
	--	     "An entry containing information applicable to a
	--	      particular module making up the system."
	--	   INDEX { vpwrBayIndex  vpwrModuleIndex }
	--	   ::= { vpwrSystemIdentTable 1 }
	--
	   vpwrBayIndex OBJECT-TYPE
	           SYNTAX     PositiveInteger
	           MAX-ACCESS read-only
	           STATUS     current
	           DESCRIPTION
	             "Identifies Bay number that this module belongs to.
	              The possible values are 1 through 16 limited by vpwrSystemShelfCapacity."
	           ::= { vpwrSystemIdentEntry 1 }

	   vpwrModuleIndex OBJECT-TYPE
	           SYNTAX     PositiveInteger
	           MAX-ACCESS read-only
	           STATUS     current
	           DESCRIPTION
	             "This object identifies the module by its position in the shelf.
	              Module numbering is left to right starting with module 1.  So, the
	              module in the first slot has an index of 1, the next module is 2 and
	              so on."
	           ::= { vpwrSystemIdentEntry 2 }

	   vpwrModuleOID        OBJECT-TYPE
	           SYNTAX        OBJECT IDENTIFIER
	           MAX-ACCESS    read-only
	           STATUS        current
	           DESCRIPTION
	                               "It indicates the type of the module by specifiying its OID"
	           ::= { vpwrSystemIdentEntry 3}

	   vpwrModuleCurrent     OBJECT-TYPE
	           SYNTAX        INTEGER
	           MAX-ACCESS    read-only
	           STATUS        current
	           DESCRIPTION
	                               "The meaning of this object depends upon the module type
	                                which is indicated by vpwrModuleOID as follows
	                                  - Current for Rectifier module.
	                                  - Not Applicable for LVD module
	                               "
	           ::= { vpwrSystemIdentEntry 4}

	   vpwrModuleOperStatus   OBJECT-TYPE
	           SYNTAX        INTEGER {
	                              moduleStatusOK(0),
	                              moduleStatusAlarm(1),
	                              moduleStatusDisabled(2),
	                              moduleStatusRingerAOn(3),
	                              moduleStatusRingerBOn(4),
	                              moduleStatusUnknown(5)
	                         }
	           MAX-ACCESS    read-only
	           STATUS        current
	           DESCRIPTION
	                               "This object indicates current over all status of the module."
	           ::= { vpwrSystemIdentEntry 5}

	   vpwrModuleCapacity   OBJECT-TYPE
	           SYNTAX        INTEGER
	           MAX-ACCESS    read-only
	           STATUS        current
	           DESCRIPTION
	                               "The meaning of this object depends upon the module type
	                                which is indicated by vpwrModuleOID as follows
	                                  - Capacity for Rectifier module.
	                                  - Not Applicable for LVD module
	                               "
	           ::= { vpwrSystemIdentEntry 6}

	--
	-- The System Panel Identifier group.
	--
	vpwrPanelIdentTable OBJECT-TYPE
	   SYNTAX     SEQUENCE OF VpwrPanelIdentEntry
	   MAX-ACCESS not-accessible
	   STATUS     current
	   DESCRIPTION
	   " This table describes shelves and modules
	     that make up the panels.
	   "
	   ::= { vpwrSystemPanelIdentGroup 1 }


	vpwrPanelIdentEntry OBJECT-TYPE
	   SYNTAX     VpwrPanelIdentEntry
	   MAX-ACCESS not-accessible
	   STATUS     current
	   DESCRIPTION
	     "An entry containing information applicable to a
	      particular panel making up the system."
	   INDEX { vpwrPanelBayIndex,  vpwrPanelModuleIndex }
	   ::= { vpwrPanelIdentTable 1 }

	VpwrPanelIdentEntry ::= SEQUENCE {
	   vpwrPanelBayIndex       	   PositiveInteger,
	   vpwrPanelModuleIndex     PositiveInteger,
	   vpwrPanelModuleOID        		OBJECT IDENTIFIER  ,
	   vpwrPanelModuleCurrent    		INTEGER ,
	   vpwrPanelModuleOperStatus INTEGER ,
	   vpwrPanelModuleCapacity   INTEGER 
	}

	   vpwrPanelBayIndex OBJECT-TYPE
	           SYNTAX    PositiveInteger
	           MAX-ACCESS read-only
	           STATUS     current
	           DESCRIPTION
	             "Identifies bay number that this module belongs to.
	              The possible values are 1 through 16, starting from the top."
	           ::= { vpwrPanelIdentEntry 1 }
	   
	   vpwrPanelModuleIndex OBJECT-TYPE
	           SYNTAX     PositiveInteger
	           MAX-ACCESS read-only
	           STATUS     current
	           DESCRIPTION
	             "This object identifies the module within the panel.
	              The orentation of modules within the panel is mappable."
	           ::= { vpwrPanelIdentEntry 2 }

	   vpwrPanelModuleOID   OBJECT-TYPE
	           SYNTAX        OBJECT IDENTIFIER
	           MAX-ACCESS    read-only
	           STATUS        current
	           DESCRIPTION
	             "It indicates the type of the module by specifiying its OID"
	           ::= { vpwrPanelIdentEntry 3}

	    vpwrPanelModuleCurrent    OBJECT-TYPE
	           SYNTAX        INTEGER
	           MAX-ACCESS    read-only
	           STATUS        current
	           DESCRIPTION
	             "This is the Current of the first shunt of the module."
	           ::= { vpwrPanelIdentEntry 4}

	     vpwrPanelModuleOperStatus   OBJECT-TYPE
	           SYNTAX        INTEGER {
	                                 moduleStatusOK(0),
	                                 moduleStatusAlarm(1),
	                                 }
	           MAX-ACCESS    read-only
	           STATUS        current
	           DESCRIPTION
	             "This object indicates over all status of the module."
	           ::= { vpwrPanelIdentEntry 5}

	     vpwrPanelModuleCapacity   OBJECT-TYPE
	           SYNTAX        INTEGER
	           MAX-ACCESS    read-only
	           STATUS        current
	           DESCRIPTION
	             "This is the overall Capacity of the module and is for reference only."
	           ::= { vpwrPanelIdentEntry 6}

	--
	-- The System Bayctrl Identifier group.
	--
	vpwrBayctrlIdentTable OBJECT-TYPE
	   SYNTAX     SEQUENCE OF VpwrBayctrlIdentEntry
	   MAX-ACCESS not-accessible
	   STATUS     current
	   DESCRIPTION
	   " This table describes bay controllers
	     that make up the system.
	   "
	   ::= { vpwrSystemBayctrlIdentGroup 1 }


	vpwrBayctrlIdentEntry OBJECT-TYPE
	   SYNTAX     VpwrBayctrlIdentEntry
	   MAX-ACCESS not-accessible
	   STATUS     current
	   DESCRIPTION
	     "An entry containing information applicable to a
	      particular bay controller making up the system."
	   INDEX { vpwrBayctrlIndex}
	   ::= { vpwrBayctrlIdentTable 1 }

	VpwrBayctrlIdentEntry ::= SEQUENCE {
	   vpwrBayctrlIndex       	    PositiveInteger,
	   vpwrBayctrlOID        		OBJECT IDENTIFIER  ,
	   vpwrBayctrlCurrent    		INTEGER ,
	   vpwrBayctrlOperStatus INTEGER ,
	   vpwrBayctrlCapacity   INTEGER 
	}

	   vpwrBayctrlIndex OBJECT-TYPE
	           SYNTAX     PositiveInteger
	           MAX-ACCESS read-only
	           STATUS     current
	           DESCRIPTION
	             "Identifies bay number that this module belongs to.
	              The possible values are 0 through 15, starting from the top."
	           ::= { vpwrBayctrlIdentEntry 1 }
	   
	   vpwrBayctrlOID   OBJECT-TYPE
	           SYNTAX        OBJECT IDENTIFIER
	           MAX-ACCESS    read-only
	           STATUS        current
	           DESCRIPTION
	             "It indicates the type of the module by specifiying its OID"
	           ::= { vpwrBayctrlIdentEntry 2}

	    vpwrBayctrlCurrent    OBJECT-TYPE
	           SYNTAX        INTEGER
	           MAX-ACCESS    read-only
	           STATUS        current
	           DESCRIPTION
	             "This is the total output Current of the bay"
	           ::= { vpwrBayctrlIdentEntry 3}

	     vpwrBayctrlOperStatus   OBJECT-TYPE
	           SYNTAX        INTEGER {
	                                 moduleStatusOK(0),
	                                 moduleStatusAlarm(1),
	                                 }
	           MAX-ACCESS    read-only
	           STATUS        current
	           DESCRIPTION
	             "This object indicates over all status of the bay"
	           ::= { vpwrBayctrlIdentEntry 4}

	     vpwrBayctrlCapacity   OBJECT-TYPE
	           SYNTAX        INTEGER
	           MAX-ACCESS    read-only
	           STATUS        current
	           DESCRIPTION
	             "This is the overall Capacity of the bay and is for reference only."
	           ::= { vpwrBayctrlIdentEntry 5}


--	--
--The System Configuration Parameters group.
--	--

	        vpwrSystemTempCompensation OBJECT-TYPE
	                     SYNTAX INTEGER {
	                            tempCompDisabled(0),
	                            tempCompEnabled(1)
	                     }
	                     MAX-ACCESS read-write
	                     STATUS current
	                     DESCRIPTION
	                     "  This parameter enables/disables temperature compensation.
	                     "
	                     REFERENCE " "

	                     ::= {vpwrSystemConfigGroup 1}

	          vpwrSystemTempCompStartTemperature OBJECT-TYPE
	                     SYNTAX INTEGER (25 .. 60)
	                     UNITS  "degrees Centigrade"
	                     MAX-ACCESS read-write
	                     STATUS current
	                     DESCRIPTION
	                     "  The temperature at which temperature compensation becomes
	                        active.
	                     "
	                     REFERENCE " "
	                     ::= {vpwrSystemConfigGroup 2}

	           vpwrSystemTempCompStopVoltage OBJECT-TYPE
	                     SYNTAX INTEGER 
	                     UNITS  " *.01 Volts"
	                     MAX-ACCESS read-write
	                     STATUS current
	                     DESCRIPTION
	                     "  When temperature compensation is active, vpwrSystemTempCompStopVoltage is the
	                        limit to which float voltage will be reduced.
				    For example, to set this voltage to 51.75 volts enter a value of 5175.
	                     "
	                     REFERENCE " "
	                     ::= {vpwrSystemConfigGroup 3}

	           vpwrSystemTempCompensationSlope OBJECT-TYPE
	                     SYNTAX INTEGER (0 .. 250)
	                     UNITS  " milli-Volts per degrees Centigrade"
	                     MAX-ACCESS read-write
	                     STATUS current
	                     DESCRIPTION
	                     "  The rate at which float voltage is changed, within the specified limits,
	                        when temperature compensation is active.
	                     "
	                     REFERENCE " "
	                     ::= {vpwrSystemConfigGroup 4}

	          vpwrSystemThermalSenseType OBJECT-TYPE
	                     SYNTAX INTEGER {
	                            external(0),
	                            internal(1)
	                     }
	                     MAX-ACCESS read-write
	                     STATUS current
	                     DESCRIPTION
	                     "  This parameter selects the temperature sensing point for temperature
	                        compensation (in)activation.
	                     "
	                     REFERENCE " "
	                     ::= {vpwrSystemConfigGroup 5}

	     vpwrSystemHVAlarmSetpoint   OBJECT-TYPE
	                            SYNTAX        INTEGER
	                            UNITS  " *.01 Volts"
	                            MAX-ACCESS    read-write
	                            STATUS        current
	                            DESCRIPTION
	                               "System High voltage alarm voltage setting.
	                               "
	                       ::= { vpwrSystemConfigGroup 6}
	     vpwrSystemBDAlarmSetpoint   OBJECT-TYPE
	                            SYNTAX        INTEGER
	                            UNITS  " *.01 Volts"
	                            MAX-ACCESS    read-write
	                            STATUS        current
	                            DESCRIPTION
	                               "System Battery Discharge voltage setting."
	                       ::= { vpwrSystemConfigGroup 7}

--
-- Threshold for Internal Temperature Trap
--
	     vpwrSystemInternalTempLThreshold   OBJECT-TYPE
	                            SYNTAX        INTEGER
	                            UNITS         "degrees Centigrade"
	                            MAX-ACCESS    read-write
	                            STATUS        current
	                            DESCRIPTION
	                               "Temperature value at which temperature compensation inactive (clear)
	                                trap would be sent if temperature compensation was active when this 
	                                value is reached.
	                                "
	                       ::= { vpwrSystemConfigGroup 8}

	      vpwrSystemInternalTempUThreshold   OBJECT-TYPE
	                            SYNTAX        INTEGER
	                            UNITS         "degrees Centigrade"
	                            MAX-ACCESS    read-write
	                            STATUS        current
	                            DESCRIPTION
	                               "Temperature value at which temperature compensation active (set) trap 
	                                would be sent.
	                               "
	                       ::= { vpwrSystemConfigGroup 9}

	--
	-- The System Current Operating Parameters group.
	--


	    vpwrSystemShelfCapacity OBJECT-TYPE
	                     SYNTAX INTEGER (1 .. 16)
	                     MAX-ACCESS read-only
	                     STATUS current
	                     DESCRIPTION
	                     "  It describes the maximum number of shelves that can/are controlled
	                        by the controller. Each shelf is uniquely numbered in the range
	                        from 1 to  vpwrShelfCapacity.
	                     "
	                     REFERENCE " "
	                     ::= {vpwrSystemParameterGroup 1}
	                     
	     vpwrSystemVoltage OBJECT-TYPE
	                     SYNTAX INTEGER 
	                      UNITS  " *.01 Volts"
	                      MAX-ACCESS read-only
	                     STATUS current
	                     DESCRIPTION
	                     "  The current system voltage.
	                     "
	                     REFERENCE " "
	                     ::= {vpwrSystemParameterGroup 2}
	                     
	      vpwrSystemCurrent OBJECT-TYPE
	                     SYNTAX INTEGER
	                     UNITS  " Amperes"
	                     MAX-ACCESS read-only
	                     STATUS current
	                     DESCRIPTION
	                     "  The current system current.
	                     "
	                     REFERENCE " "
	                     ::= {vpwrSystemParameterGroup 3}
	                     
	       vpwrSystemControllerState OBJECT-TYPE
	                     SYNTAX INTEGER {
	                            systemControllerStateUnknown(0),
	                            systemControllerStateNormal(1),
	                            systemControllerStateChange(2) ,
	                            systemControllerStateAlarm(3),
	                            systemControllerStateMenu(4 ),
	                            systemControllerStateIrActive(5)
	                     }
	                     MAX-ACCESS read-only
	                     STATUS current
	                     DESCRIPTION
	                     "  Current System state as shown on the enhanced display.
	                     "
	                     REFERENCE " "
	                     ::= {vpwrSystemParameterGroup 4}


	            vpwrSystemInternalTemperature OBJECT-TYPE
	                     SYNTAX INTEGER 
	                     UNITS  "degrees Centigrade"
	                     MAX-ACCESS read-only
	                     STATUS current
	                     DESCRIPTION
	                     "  The current controller internal temperature.
	                     "
	                     REFERENCE " "
	                     ::= {vpwrSystemParameterGroup 5}
	                     
	             vpwrSystemTempCompensationState OBJECT-TYPE
	                     SYNTAX INTEGER {
	                            systemTempCompInactive(0),
	                            systemTempCompActive(1)
	                     }
	                     MAX-ACCESS read-only
	                     STATUS current
	                     DESCRIPTION
	                     "  Active or Inactive. Applicable only if temperature compensation is enabled.
	                        This means that the controller is temperature compensating the float voltage.
	                     "
	                     REFERENCE " "
	                     ::= {vpwrSystemParameterGroup 6}

	         vpwrSystemType OBJECT-TYPE
	                     SYNTAX     INTEGER {
			       sysTypeUnknow (0),
	                       sysType48V (1),
	                       sysType24V(2)  ,
	                        sysType12V(3)
	                    }
	                     MAX-ACCESS read-only
	                     STATUS     current
	                     DESCRIPTION
	                     "This parameter describes the type of the system being managed.
	                      This object is set by Valere Power Inc.
	                     "
	                     ::= { vpwrSystemParameterGroup 7 }

	--
	-- The System LVD Operating Setpoints group.
	--      

	     vpwrLvdWarningSetpoint   OBJECT-TYPE
	                            SYNTAX        INTEGER
	                            UNITS  " * .01 Volts"
	                            MAX-ACCESS    read-write
	                            STATUS        current
	                            DESCRIPTION
	                               "LVD Warning voltage setpoint."
	                       ::= { vpwrLvdConfigGroup 1}

	      vpwrLvdDisconnectSetpoint   OBJECT-TYPE
	                            SYNTAX        INTEGER
	                            UNITS  " *.01 Volts"
	                            MAX-ACCESS    read-write
	                            STATUS        current
	                            DESCRIPTION
	                               "LVD disconnect voltage setpoint."
	                       ::= { vpwrLvdConfigGroup 2}
	     vpwrLvdReconnectSetpoint   OBJECT-TYPE
	                            SYNTAX        INTEGER
	                            UNITS  " *.01 Volts"
	                            MAX-ACCESS    read-write
	                            STATUS        current
	                            DESCRIPTION
	                               "LVD Reconnect voltage setpoint."
	                       ::= { vpwrLvdConfigGroup 3}
	     vpwrLvdReconnectDelayTimer   OBJECT-TYPE
	                            SYNTAX        INTEGER (20..240)
	                            UNITS  " Seconds"
	                            MAX-ACCESS    read-write
	                            STATUS        current
	                            DESCRIPTION
	                               "The delay time, in seconds, before LVD is reconnected"
	                       ::= { vpwrLvdConfigGroup 4}
	                       
	vpwrLvdContactorConfigTable OBJECT-TYPE
	   SYNTAX     SEQUENCE OF VpwrLvdContactorConfigEntry
	   MAX-ACCESS not-accessible
	   STATUS     current
	   DESCRIPTION
	   " This table describes shelves and modules
	     that make up the sysetm.
	   "
	   ::= { vpwrLvdConfigGroup 5 }

	vpwrLvdContactorConfigEntry OBJECT-TYPE
	   SYNTAX     VpwrLvdContactorConfigEntry
	   MAX-ACCESS not-accessible
	   STATUS     current
	   DESCRIPTION
	           "An entry containing information applicable to a
	           particular module making up the system."

	   INDEX { vpwrBayIndex, vpwrModuleIndex,vpwrLvdContactorIndex }

	   ::= { vpwrLvdContactorConfigTable 1 }

	VpwrLvdContactorConfigEntry ::= SEQUENCE {
	   vpwrLvdContactorIndex                PositiveInteger,
	   vpwrLvdContactorWarningSetpoint      PositiveInteger ,
	   vpwrLvdContactorDisconnectSetpoint   PositiveInteger ,
	   vpwrLvdContactorReconnectSetpoint    PositiveInteger ,
	   vpwrLvdContactorReconnectDelayTimer  PositiveInteger ,
	   vpwrLvdContactorState                PositiveInteger
	}
	     vpwrLvdContactorIndex   OBJECT-TYPE
	                            SYNTAX        PositiveInteger
	                            UNITS  " None"
	                            MAX-ACCESS    read-only
	                            STATUS        current
	                            DESCRIPTION
	                               "contactor index"
	                       ::= { vpwrLvdContactorConfigEntry 1}

	     vpwrLvdContactorWarningSetpoint   OBJECT-TYPE
	                            SYNTAX        PositiveInteger
	                            UNITS  " * .01 Volts"
	                            MAX-ACCESS    read-write
	                            STATUS        current
	                            DESCRIPTION
	                               "LVD Warning voltage setpoint."
	                       ::= { vpwrLvdContactorConfigEntry 2}

	      vpwrLvdContactorDisconnectSetpoint   OBJECT-TYPE
	                            SYNTAX        PositiveInteger
	                            UNITS  " *.01 Volts"
	                            MAX-ACCESS    read-write
	                            STATUS        current
	                            DESCRIPTION
	                               "LVD disconnect voltage setpoint."
	                       ::= { vpwrLvdContactorConfigEntry 3}
	     vpwrLvdContactorReconnectSetpoint   OBJECT-TYPE
	                            SYNTAX        PositiveInteger
	                            UNITS  " *.01 Volts"
	                            MAX-ACCESS    read-write
	                            STATUS        current
	                            DESCRIPTION
	                               "LVD Reconnect voltage setpoint."
	                       ::= { vpwrLvdContactorConfigEntry 4}
	     vpwrLvdContactorReconnectDelayTimer   OBJECT-TYPE
	                            SYNTAX        PositiveInteger (0..240)
	                            UNITS  " Seconds"
	                            MAX-ACCESS    read-write
	                            STATUS        current
	                            DESCRIPTION
	                               "The delay time, in seconds, before LVD is reconnected"
	                       ::= { vpwrLvdContactorConfigEntry 5}
	      vpwrLvdContactorState   OBJECT-TYPE
	                             SYNTAX    INTEGER {
	                                  contactorOpen (0),
	                                 contactorClose(1)  
	                            }
	                            MAX-ACCESS    read-write
	                            STATUS        current
	                            DESCRIPTION
	                               "The delay time, in seconds, before LVD is reconnected"
	                       ::= { vpwrLvdContactorConfigEntry 6}


	--
	-- The Rectifier Operating Parameters group.
	--

	     vpwrRectifierFVSetpoint   OBJECT-TYPE
	                            SYNTAX        INTEGER
	                             UNITS  " *.01 Volts"
	                           MAX-ACCESS    read-write
	                            STATUS        current
	                            DESCRIPTION
	                               "System Float Voltage setting"
	                       ::= { vpwrRectifierConfigGroup 1}
	       vpwrRectifierHVSDSetpoint   OBJECT-TYPE
	                            SYNTAX        INTEGER
	                            UNITS  " *.01 Volts"
	                            MAX-ACCESS    read-write
	                            STATUS        current
	                            DESCRIPTION
	                               "System High Voltage Shutdown voltage setting"
	                       ::= { vpwrRectifierConfigGroup 2}

	vpwrRectifierCurrentLimitAdminState OBJECT-TYPE
	                     SYNTAX INTEGER {
	                            rectCurrentLimitDisabled(0),
	                            rectCurrentLimitEnabled(1)
	                    }
	                     MAX-ACCESS read-write
	                     STATUS current
	                     DESCRIPTION
	                     "  This parameter allows enabling or disabling boost.
	                     "
	                     REFERENCE " "

	                     ::= {vpwrRectifierConfigGroup 3}

	        vpwrRectifierCurrentLimit   OBJECT-TYPE
	                            SYNTAX        INTEGER (5 .. 200)
	                            UNITS  "Amperes"
	                            MAX-ACCESS    read-write
	                            STATUS        current
	                            DESCRIPTION
	                               "Rectifier current limit setpoint"
	                       ::= { vpwrRectifierConfigGroup 4}

	--
	-- The Alarm group.
	--


	vpwrAlarmsPresent OBJECT-TYPE
	   SYNTAX     Gauge32
	   MAX-ACCESS read-only
	   STATUS     current
	   DESCRIPTION
	           "The present number of active alarm conditions."
	   ::= { vpwrDcPowerAlarmGroup 1 }

	vpwrAlarmTable OBJECT-TYPE
	   SYNTAX     SEQUENCE OF VpwrAlarmEntry
	   MAX-ACCESS not-accessible
	   STATUS     current
	   DESCRIPTION
	           "A list of alarm table entries.  The table contains
	           zero, one, or many rows at any moment, depending upon
	           the number of alarm conditions in effect.  The table
	           is initially empty at agent startup.  The agent
	           creates a row in the table each time a condition is
	           detected and deletes that row when that condition no
	           longer pertains.  
	           The vpwrAlarmIndex, for each type of module starts at 1
	           and is limited by the total number of alarams that can be
	           generated by the module.

	           Alarms are named by an AutonomousType (OBJECT
	           IDENTIFIER), vpwrAlarmDescr, to allow a single table to
	           reflect alarms for different type of modules.

	           The number of rows in the table at any given time is
	           reflected by the value of vpwrAlarmsPresent."
	           
	   ::= { vpwrDcPowerAlarmGroup 2 }

	vpwrAlarmEntry OBJECT-TYPE
	   SYNTAX     VpwrAlarmEntry
	   MAX-ACCESS not-accessible
	   STATUS     current
	   DESCRIPTION
	           "An entry containing information applicable to a
	           particular alarm."
	   INDEX { vpwrAlarmIndex }
	   ::= { vpwrAlarmTable 1 }

	VpwrAlarmEntry ::= SEQUENCE {
	   vpwrAlarmIndex       PositiveInteger,
	   vpwrAlarmDescr       AutonomousType,
	   vpwrAlarmTime        TimeStamp
	}

	  vpwrAlarmIndex OBJECT-TYPE
	   SYNTAX     PositiveInteger
	   MAX-ACCESS read-only
	   STATUS     current
	   DESCRIPTION
	           "Identifies the alarm associated with the module. 
	            It is unique on per module type basis. For example,
	            multiple rectifiers can have the same alarm and therefore same
	            vpwrAlarmIndex active at any one time.
	           "
	   ::= { vpwrAlarmEntry 1 }
	   

	vpwrAlarmDescr OBJECT-TYPE
	   SYNTAX     AutonomousType
	   MAX-ACCESS read-only
	   STATUS     current
	   DESCRIPTION
	           "A reference to an alarm description object.  The
	           object referenced should not be accessible, but rather
	           be used to provide a unique description of the alarm
	           condition."
	   ::= { vpwrAlarmEntry 2 }

	vpwrAlarmTime OBJECT-TYPE
	   SYNTAX     TimeStamp
	   MAX-ACCESS read-only
	   STATUS     current
	   DESCRIPTION
	           "The value of sysUpTime when the alarm condition was
	           detected."

	   ::= { vpwrAlarmEntry 3 }



	--
	-- The Battery Group
	--



	vpwrBatteryTempTable OBJECT-TYPE
	   SYNTAX     SEQUENCE OF VpwrBatteryTempEntry
	   MAX-ACCESS not-accessible
	   STATUS     current
	   DESCRIPTION
	   "This table describes battery temperature probes.
	   "
	   ::= { vpwrBatteryTempGroup 1 }

	vpwrBatteryTempEntry OBJECT-TYPE
	   SYNTAX     VpwrBatteryTempEntry
	   MAX-ACCESS not-accessible
	   STATUS     current
	   DESCRIPTION
	           "An entry containing information applicable to a
	           particular temperature probe."
	   INDEX { vpwrBatteryTempIndex }
	   ::= { vpwrBatteryTempTable 1 }

	VpwrBatteryTempEntry ::= SEQUENCE {
	   vpwrBatteryTempIndex       INTEGER,
	   vpwrBatteryTempName      DisplayString,
	   vpwrBatteryTemp        INTEGER
	}

	     vpwrBatteryTempIndex   OBJECT-TYPE
	                            SYNTAX        INTEGER
	                            MAX-ACCESS    read-only
	                            STATUS        current
	                            DESCRIPTION
	                               "Index into temperature table"
	                       ::= { vpwrBatteryTempEntry 1}

	     vpwrBatteryTempName   OBJECT-TYPE
	                            SYNTAX        DisplayString (SIZE (1 .. 8))
	                            MAX-ACCESS    read-write
	                            STATUS        current
	                            DESCRIPTION
	                               "A string identifying probe location."
	                       ::= { vpwrBatteryTempEntry 2}

	     vpwrBatteryTemp   OBJECT-TYPE
	                            SYNTAX        INTEGER
	                            UNITS         "degrees Centigrade"
	                            MAX-ACCESS    read-only
	                            STATUS        current
	                            DESCRIPTION
	                               "Current temperature as recorded by the probe."
	                       ::= { vpwrBatteryTempEntry 3}


-- Threshold for Battery Temperature Trap

	     vpwrBatteryTempLThreshold   OBJECT-TYPE
	                            SYNTAX        INTEGER
	                            UNITS         "degrees Centigrade"
	                            MAX-ACCESS    read-write
	                            STATUS        current
	                            DESCRIPTION
	                               "Temperature value at which a clear trap would be sent.
	                                All three battery temperature must be at or below this value
	                                to trigger this trap.
	                                "
	                       ::= { vpwrBatteryTempGroup 2}

	      vpwrBatteryTempUThreshold   OBJECT-TYPE
	                            SYNTAX        INTEGER
	                            UNITS         "degrees Centigrade"
	                            MAX-ACCESS    read-write
	                            STATUS        current
	                            DESCRIPTION
	                               "Temperature value at which a set trap would be sent.
	                               Any one of the three battery temperatures at or exceeding this limit
	                               would trigger the trap.
	                               "
	                       ::= { vpwrBatteryTempGroup 3}

	        batteryTempCompensation OBJECT-TYPE
	                     SYNTAX INTEGER {
	                            tempCompDisabled(0),
	                            tempCompEnabled(1)
	                     }
	                     MAX-ACCESS read-write
	                     STATUS current
	                     DESCRIPTION
	                     "  This parameter enables/disables temperature compensation.
	                     "
	                     REFERENCE " "

	                     ::= {vpwrBatteryTempGroup 4}

	          batteryTempCompHighStartTemperature OBJECT-TYPE
	                     SYNTAX INTEGER (25 .. 60)
	                     UNITS  "degrees Centigrade"
	                     MAX-ACCESS read-write
	                     STATUS current
	                     DESCRIPTION
	                     "  The temperature at which temperature compensation becomes
	                        active.
	                     "
	                     REFERENCE " "
	                     ::= {vpwrBatteryTempGroup 5}

	           batteryTempCompHighStopVoltage OBJECT-TYPE
	                     SYNTAX INTEGER 
	                     UNITS  " *.01 Volts"
	                     MAX-ACCESS read-write
	                     STATUS current
	                     DESCRIPTION
	                     "  When temperature compensation is active, batteryTempCompHighStopVoltage is the
	                        limit to which float voltage will be reduced.
				    For example, to set this voltage to 51.75 volts enter a value of 5175.
	                     "
	                     REFERENCE " "
	                     ::= {vpwrBatteryTempGroup 6}

	           batteryTempCompHighSlope OBJECT-TYPE
	                     SYNTAX INTEGER (0 .. 250)
	                     UNITS  " milli-Volts per degrees Centigrade"
	                     MAX-ACCESS read-write
	                     STATUS current
	                     DESCRIPTION
	                     "  The rate at which float voltage is changed, within the specified limits,
	                        when temperature compensation is active.
	                     "
	                     REFERENCE " "
	                     ::= {vpwrBatteryTempGroup 7}


	          batteryTempCompLowStartTemperature OBJECT-TYPE
	                     SYNTAX INTEGER
	                     UNITS  "degrees Centigrade"
	                     MAX-ACCESS read-write
	                     STATUS current
	                     DESCRIPTION
	                     "  The temperature at which temperature compensation becomes
	                        active.
	                     "
	                     REFERENCE " "
	                     ::= {vpwrBatteryTempGroup 8}

	           batteryTempCompLowStopVoltage OBJECT-TYPE
	                     SYNTAX INTEGER
	                     UNITS  " *.01 Volts"
	                     MAX-ACCESS read-write
	                     STATUS current
	                     DESCRIPTION
	                     "  When temperature compensation is active, batteryTempCompLowStopVoltage is the
	                        limit to which float voltage will be reduced.
				    For example, to set this voltage to 51.75 volts enter a value of 5175.
	                     "
	                     REFERENCE " "
	                     ::= {vpwrBatteryTempGroup 9}

	           batteryTempCompLowSlope OBJECT-TYPE
	                     SYNTAX INTEGER (0 .. 250)
	                     UNITS  " milli-Volts per degrees Centigrade"
	                     MAX-ACCESS read-write
	                     STATUS current
	                     DESCRIPTION
	                     "  The rate at which float voltage is changed, within the specified limits,
	                        when temperature compensation is active.
	                     "
	                     REFERENCE " "
	                     ::= {vpwrBatteryTempGroup 10}

	            batteryTempCompRunawayTemperature OBJECT-TYPE
	                     SYNTAX INTEGER (25 .. 60)
	                     UNITS  "degrees Centigrade"
	                     MAX-ACCESS read-write
	                     STATUS current
	                     DESCRIPTION
	                     "  The temperature at which system voltage will be set to 
	                         batteryTempCompRunawayStopVoltage.
	                     "
	                   REFERENCE " "
	                     ::= {vpwrBatteryTempGroup 11}

	           batteryTempCompRunawayStopVoltage OBJECT-TYPE
	                     SYNTAX INTEGER
	                     UNITS  " *.01 Volts"
	                     MAX-ACCESS read-write
	                     STATUS current
	                     DESCRIPTION
	                     "  When temperature compensation is enabled, float voltage will be reduced to
	                         batteryTempCompRunawayStopVoltage if temperature
	                         reaches batteryTempCompRunawayTemperature.
	                     "
	                     REFERENCE " "
	                     ::= {vpwrBatteryTempGroup 12}

	          batteryTempCompSenseSource OBJECT-TYPE
	                     SYNTAX INTEGER {
	                            external(0),
	                            internal(1)
	                     }
	                     MAX-ACCESS read-write
	                     STATUS current
	                     DESCRIPTION
	                     "  This parameter selects the temperature sensing point for temperature
	                        compensation (in)activation.
	                     "
	                     REFERENCE " "
	                     ::= {vpwrBatteryTempGroup 13}
	                       
	          batteryTempCompRunawayState OBJECT-TYPE
	                     SYNTAX INTEGER {
	                            inactive(0),
	                            active(1)
	                     }
	                     MAX-ACCESS read-only
	                     STATUS current
	                     DESCRIPTION
	                     "  This parameter selects the temperature sensing point for temperature
	                        compensation (in)activation.
	                     "
	                     REFERENCE " "
	                     ::= {vpwrBatteryTempGroup 14}
	                     
	thermalProbeTable OBJECT-TYPE
	   SYNTAX     SEQUENCE OF ThermalProbeEntry
	   MAX-ACCESS not-accessible
	   STATUS     current
	   DESCRIPTION
	   "This table describes battery temperature probes.
	   "
	   ::= { vpwrBatteryTempGroup 15 }

	thermalProbeEntry OBJECT-TYPE
	   SYNTAX     ThermalProbeEntry
	   MAX-ACCESS not-accessible
	   STATUS     current
	   DESCRIPTION
	           "An entry containing information applicable to a
	           particular temperature probe."
--       INDEX { vpwrBatteryTempIndex }
	     AUGMENTS {vpwrBatteryTempEntry}
	   ::= { thermalProbeTable 1 }

	ThermalProbeEntry ::= SEQUENCE {
	   thermalProbeState        INTEGER
	}

	     thermalProbeState   OBJECT-TYPE
	                            SYNTAX        INTEGER {
	                                  notPresent(0),
	                                  present(1),
	                                  removed(2),
	                                  shorted(3)
	                            }
	                            MAX-ACCESS    read-only
	                            STATUS        current
	                            DESCRIPTION
	                               "State of thermal probe."
	                       ::= { thermalProbeEntry 1}


--
-- The SNMP Configuration Parameters
--

	vpwrTrapTable OBJECT-TYPE
	   SYNTAX     SEQUENCE OF VpwrTrapEntry
	   MAX-ACCESS not-accessible
	   STATUS     current
	   DESCRIPTION
	   "A list of possible trap destinations depending upon
	    the criticality of the trap.
	   "
	   ::= { vpwrDcPowerSnmpConfig 1 }

	vpwrTrapEntry OBJECT-TYPE
	   SYNTAX     VpwrTrapEntry
	   MAX-ACCESS not-accessible
	   STATUS     current
	   DESCRIPTION
	           "An entry containing information applicable to a
	           particular trap destination."
	   INDEX { vpwrTrapIpIndex }
	   ::= { vpwrTrapTable 1 }

	VpwrTrapEntry ::= SEQUENCE {
	   vpwrTrapIpIndex         INTEGER,
	   vpwrTrapIpAddress       IpAddress,
	   vpwrTrapCriticality      INTEGER
	}
	       vpwrTrapIpIndex   OBJECT-TYPE
	                            SYNTAX          INTEGER
	                            MAX-ACCESS    read-only
	                            STATUS        current
	                            DESCRIPTION
	                               "Trap Entry Index "
	                       ::= { vpwrTrapEntry 1}

	     vpwrTrapIpAddress   OBJECT-TYPE
	                            SYNTAX        IpAddress
	                            MAX-ACCESS    read-write
	                            STATUS        current
	                            DESCRIPTION
	                               "Trap destination IP Address"
	                       ::= { vpwrTrapEntry 2}

	     vpwrTrapCriticality   OBJECT-TYPE
	                            SYNTAX          INTEGER
	                            MAX-ACCESS    read-write
	                            STATUS        current
	                            DESCRIPTION
	                               "Criticality of traps sent to this IP Address"
	                       ::= { vpwrTrapEntry 3}


	    vpwrReadCommunityString OBJECT-TYPE
	                      SYNTAX     DisplayString(SIZE (3 .. 8))
	                      MAX-ACCESS read-write
	                      STATUS     current
	                      DESCRIPTION
	                     " This allows setting password to be able to do Get operations"
	                     ::= { vpwrDcPowerSnmpConfig 2 }

	   vpwrWriteCommunityString OBJECT-TYPE
	                      SYNTAX     DisplayString(SIZE (3 .. 8))
	                      MAX-ACCESS read-write
	                      STATUS     current
	                      DESCRIPTION
	                      " This allows setting password to be able to do Get and Set
	                        operations.
	                        The read-access is not allowed in the actual implementation.
	                      "
	                      ::= { vpwrDcPowerSnmpConfig 3 }

	  vpwrTrapCommunityString OBJECT-TYPE
	                       SYNTAX     DisplayString(SIZE (3 .. 8))
	                       MAX-ACCESS read-write
	                       STATUS     current
	                       DESCRIPTION
	                      " This allows setting community string required for the
	                        trap to be accepted at the destination.
	                      "
	                       ::= { vpwrDcPowerSnmpConfig 4 }

--
--  traps
--
	vpwrTrapPowerMajorAlarm TRAP-TYPE
	   ENTERPRISE      vpwrDcPowerTraps
	    VARIABLES { vpwrTrapsMsgString }
	                    DESCRIPTION
	                      "Major Alarm"
	                      ::= 1

	vpwrTrapPowerMinorAlarm   TRAP-TYPE
	   ENTERPRISE      vpwrDcPowerTraps
	    VARIABLES { vpwrTrapsMsgString }
	                          DESCRIPTION
	                          "Minor Alarm"
	                          ::= 2

	 vpwrTrapACFAlarm   TRAP-TYPE
	   ENTERPRISE      vpwrDcPowerTraps
	    VARIABLES { vpwrTrapsMsgString }
	                          DESCRIPTION
	                          "AC Fail Alarm"
	                          ::= 3

	vpwrTrapHVAlarm   TRAP-TYPE
	   ENTERPRISE      vpwrDcPowerTraps
	    VARIABLES { vpwrTrapsMsgString }
	                          DESCRIPTION
	                          "High Voltage Warning Alarm"
	                          ::= 4

	vpwrTrapHVSDAlarm   TRAP-TYPE
	   ENTERPRISE      vpwrDcPowerTraps
	    VARIABLES { vpwrTrapsMsgString }
	                          DESCRIPTION
	                          "High Voltage Shutdown Alarm"
	                          ::= 5
	vpwrTrapBDAlarm   TRAP-TYPE
	   ENTERPRISE      vpwrDcPowerTraps
	    VARIABLES { vpwrTrapsMsgString }
	                          DESCRIPTION
	                          "Battery on Discharge Alarm"
	                          ::= 6
	 vpwrTrapLVDWarningAlarm   TRAP-TYPE
	   ENTERPRISE      vpwrDcPowerTraps
	    VARIABLES { vpwrTrapsMsgString }
	                          DESCRIPTION
	                          "LVD Warning Alarm"
	                          ::= 7

	  vpwrTrapLVDOpenAlarm   TRAP-TYPE
	   ENTERPRISE      vpwrDcPowerTraps
	    VARIABLES { vpwrTrapsMsgString }
	                          DESCRIPTION
	                          "LVD Open Alarm"
	                          ::= 8

	 vpwrTrapDistAlarm   TRAP-TYPE
	   ENTERPRISE      vpwrDcPowerTraps
	    VARIABLES { vpwrTrapsMsgString }
	                          DESCRIPTION
	                          "Distribution Open Alarm"
	                          ::= 9

	 vpwrTrapAuxAlarm   TRAP-TYPE
	   ENTERPRISE      vpwrDcPowerTraps
	    VARIABLES { vpwrTrapsMsgString }
	                          DESCRIPTION
	                          "Auxiliary System Alarm"
	                          ::= 10

	 vpwrTrapSystemRedundancyAlarm   TRAP-TYPE
	   ENTERPRISE      vpwrDcPowerTraps
	    VARIABLES { vpwrTrapsMsgString }
	                          DESCRIPTION
	                          "System Redundant Capacity Alarm"
	                          ::=  11

	 vpwrTrapIShareAlarm   TRAP-TYPE
	   ENTERPRISE      vpwrDcPowerTraps
	    VARIABLES { vpwrTrapsMsgString }
	                          DESCRIPTION
	                          "Rectifier Current Share Alarm"
	                          ::=  12
	 vpwrTrapModuleFailAlarm   TRAP-TYPE
	   ENTERPRISE      vpwrDcPowerTraps
	    VARIABLES { vpwrTrapsMsgString }
	                          DESCRIPTION
	                          "Single Rectifier Fail Alarm"
	                          ::=  13

	 vpwrTrapMultipleModuleFailAlarm   TRAP-TYPE
	   ENTERPRISE      vpwrDcPowerTraps
	    VARIABLES { vpwrTrapsMsgString }
	                          DESCRIPTION
	                          "Multiple Rectifier Fail Alarm"
	                          ::= 14

	 vpwrTrapModuleCommAlarm   TRAP-TYPE
	   ENTERPRISE      vpwrDcPowerTraps
	    VARIABLES { vpwrTrapsMsgString }
	                          DESCRIPTION
	                          "Module Communication Alarm"
	                          ::=  15
	 vpwrTrapSystemOverTemperatureAlarm   TRAP-TYPE
	   ENTERPRISE      vpwrDcPowerTraps
	    VARIABLES { vpwrTrapsMsgString }
	                          DESCRIPTION
	                          "System Over Temperature Alarm"
	                          ::= 16
	 vpwrTrapSystemOK   TRAP-TYPE
	   ENTERPRISE      vpwrDcPowerTraps
	    VARIABLES { vpwrTrapsMsgString }
	                          DESCRIPTION
	                          "SYSTEM OK - No Active Alarms"
	                          ::=  17

	vpwrTrapModuleInserted TRAP-TYPE
	   ENTERPRISE      vpwrDcPowerTraps
	   VARIABLES { vpwrTrapsMsgString, vpwrBayIndex, vpwrModuleIndex }
	   DESCRIPTION
	           "A new module has been inserted into the system."
	 ::= 18

	vpwrTrapModuleRemoved TRAP-TYPE
	   ENTERPRISE      vpwrDcPowerTraps
	   VARIABLES { vpwrTrapsMsgString,vpwrBayIndex, vpwrModuleIndex }
	   DESCRIPTION
	           "A module has been removed from the system."
	 ::= 19


	vpwrTrapThermalCompActive   TRAP-TYPE
	   ENTERPRISE      vpwrDcPowerTraps
	    VARIABLES { vpwrTrapsMsgString }
	                          DESCRIPTION
	                          "Thermal compensation has become active."
	                          ::=  20

	vpwrTrapThermalCompInactive   TRAP-TYPE

	   ENTERPRISE      vpwrDcPowerTraps
	    VARIABLES { vpwrTrapsMsgString }
	                          DESCRIPTION
	                          "Thermal compensation has been de-activated."
	                          ::=  21

	vpwrTrapInternalTempAlarmSet   TRAP-TYPE

	   ENTERPRISE      vpwrDcPowerTraps
	    VARIABLES { vpwrTrapsMsgString }
	                          DESCRIPTION
	                          "Internal Temperature upper threshold exceeded."
	                          ::=  22

	vpwrTrapInternalTempAlarmCleared   TRAP-TYPE

	   ENTERPRISE      vpwrDcPowerTraps
	    VARIABLES { vpwrTrapsMsgString }
	                          DESCRIPTION
	                          "Internal Temperature within limits"
	                          ::=  23

	vpwrTrapBatteryTempAlarmSet   TRAP-TYPE

	   ENTERPRISE      vpwrDcPowerTraps
	    VARIABLES { vpwrTrapsMsgString }
	                          DESCRIPTION
	                          "At least one Battery Temperature exceeded upper threshold."
	                          ::=  24

	vpwrTrapBatteryTempAlarmCleared   TRAP-TYPE

	   ENTERPRISE      vpwrDcPowerTraps
	    VARIABLES { vpwrTrapsMsgString }
	                          DESCRIPTION
	                          "All Battery Temperatures within limits."
	                          ::=  25

	vpwrTrapLoginFail   TRAP-TYPE

	   ENTERPRISE      vpwrDcPowerTraps
	    VARIABLES { vpwrTrapsMsgString }
	                          DESCRIPTION
	                          "Admin login failed due to wrong username/password."
	                          ::=  26
	vpwrTrapLoginSuccess   TRAP-TYPE

	   ENTERPRISE      vpwrDcPowerTraps
	    VARIABLES { vpwrTrapsMsgString }
	                          DESCRIPTION
	                          "Admin login successful."
	                          ::=  27
	vpwrTrapLogout   TRAP-TYPE

	   ENTERPRISE      vpwrDcPowerTraps
	    VARIABLES { vpwrTrapsMsgString }
	                          DESCRIPTION
	                          "Admin logout."
	                          ::=  28
	                          
	vpwrTrapAdminPwdChange   TRAP-TYPE

	   ENTERPRISE      vpwrDcPowerTraps
	    VARIABLES { vpwrTrapsMsgString }
	                          DESCRIPTION
	                          "Config change submitted with invalid access."
	                          ::= 29


	vpwrTrapIllegalConfigSubmit   TRAP-TYPE

	   ENTERPRISE      vpwrDcPowerTraps
	    VARIABLES { vpwrTrapsMsgString }
	                          DESCRIPTION
	                          "Config change submitted with invalid access."
	                          ::=  30
	vpwrTrapCfgChange   TRAP-TYPE

	   ENTERPRISE      vpwrDcPowerTraps
	    VARIABLES { vpwrTrapsMsgString }
	                          DESCRIPTION
	                          "Config change submitted."
	                          ::=  31
	vpwrTrapClearEventHistory    TRAP-TYPE

	   ENTERPRISE      vpwrDcPowerTraps
	    VARIABLES { vpwrTrapsMsgString }
	                          DESCRIPTION
	                          "Clear Event history buffer clear request."
	                          ::=  32
	vpwrTrapSwDownloadNoReboot    TRAP-TYPE

	   ENTERPRISE      vpwrDcPowerTraps
	    VARIABLES { vpwrTrapsMsgString }
	                          DESCRIPTION
	                          "System software upgrade without reboot."
	                          ::=  33
	vpwrTrapSwDownloadAndReboot    TRAP-TYPE

	   ENTERPRISE      vpwrDcPowerTraps
	    VARIABLES { vpwrTrapsMsgString }
	                          DESCRIPTION
	                          "System reboot due to software upgrade."
	                          ::=  34

	vpwrTrapSystemClockChange    TRAP-TYPE

	   ENTERPRISE      vpwrDcPowerTraps
	    VARIABLES { vpwrTrapsMsgString }
	                          DESCRIPTION
	                          "System clock updated."
	                          ::=  35
	vpwrTrapModuleAlarm    TRAP-TYPE

	   ENTERPRISE      vpwrDcPowerTraps
	    VARIABLES { vpwrTrapsMsgString }
	                          DESCRIPTION
	                          "Module Alarm."
	                          ::=  36

	vpwrTrapOIDChange    TRAP-TYPE

	   ENTERPRISE      vpwrDcPowerTraps
	    VARIABLES { vpwrTrapsMsgString }
	                          DESCRIPTION
	                          "Change in OID."
	                          ::=  37

	vpwrTrapThermalRunaway    TRAP-TYPE

	   ENTERPRISE      vpwrDcPowerTraps
	    VARIABLES { vpwrTrapsMsgString }
	                          DESCRIPTION
	                          "Thermal Runaway Alarm."
	                          ::=  38

	 vpwrTrapBatteryDischargeTestAlarm    TRAP-TYPE

	   ENTERPRISE      vpwrDcPowerTraps
	    VARIABLES { vpwrTrapsMsgString }
	                          DESCRIPTION
	                          "System Voltage dropped to BDT Alarm Setpoint."
	                          ::=  39
	vpwrTrapRingerAAlarm    TRAP-TYPE

	   ENTERPRISE      vpwrDcPowerTraps
	    VARIABLES { vpwrTrapsMsgString }
	                          DESCRIPTION
	                          "Ringer A Fail Alarm."
	                          ::=  40
	vpwrTrapRingerBAlarm    TRAP-TYPE

	   ENTERPRISE      vpwrDcPowerTraps
	    VARIABLES { vpwrTrapsMsgString }
	                          DESCRIPTION
	                          "Ringer B Fail Alarm."
	                          ::=  41
	vpwrTrapSingleRingerAlarm    TRAP-TYPE

	   ENTERPRISE      vpwrDcPowerTraps
	    VARIABLES { vpwrTrapsMsgString }
	                          DESCRIPTION
	                          "Single Ringer Fail Alarm."
	                          ::=  42
	vpwrTrapMultipleRingerAlarm    TRAP-TYPE

	   ENTERPRISE      vpwrDcPowerTraps
	    VARIABLES { vpwrTrapsMsgString }
	                          DESCRIPTION
	                          "Multiple Ringer Fail Alarm."
	                          ::=  43
	vpwrTrapThermalProbeAlarm    TRAP-TYPE

	   ENTERPRISE      vpwrDcPowerTraps
	    VARIABLES { vpwrTrapsMsgString }
	                          DESCRIPTION
	                          "Thermal Probe Missing Alarm."
	                          ::=  44
	vpwrTrapRingerCommAlarm    TRAP-TYPE

	   ENTERPRISE      vpwrDcPowerTraps
	    VARIABLES { vpwrTrapsMsgString }
	                          DESCRIPTION
	                          "Ringer Communication Alarm."
	                          ::=  45
	vpwrTrapDistributionCommAlarm    TRAP-TYPE

	   ENTERPRISE      vpwrDcPowerTraps
	    VARIABLES { vpwrTrapsMsgString }
	                          DESCRIPTION
	                          "Distribution Communication Alarm."
	                          ::=  46
	vpwrTrapConverterAlarm    TRAP-TYPE

	   ENTERPRISE      vpwrDcPowerTraps
	    VARIABLES { vpwrTrapsMsgString }
	                          DESCRIPTION
	                          "Single Converter Fail Alarm."
	                          ::=  47
	vpwrTrapMultipleConvFailAlarm    TRAP-TYPE

	   ENTERPRISE      vpwrDcPowerTraps
	    VARIABLES { vpwrTrapsMsgString }
	                          DESCRIPTION
	                          "Multiple Converter Fail Alarm."
	                          ::=  48
	vpwrTrapUnmappedAddressAlarm    TRAP-TYPE

	   ENTERPRISE      vpwrDcPowerTraps
	    VARIABLES { vpwrTrapsMsgString }
	                          DESCRIPTION
	                          "Unmapped I2C Address."
	                          ::=  49

	 vpwrTrapConfigErrorAlarm    TRAP-TYPE

	   ENTERPRISE      vpwrDcPowerTraps
	    VARIABLES { vpwrTrapsMsgString }
	                          DESCRIPTION
	                          "Configuration Error."
	                          ::=  50
	vpwrTrapDisplayFirmwareMismatchAlarm    TRAP-TYPE

	   ENTERPRISE      vpwrDcPowerTraps
	    VARIABLES { vpwrTrapsMsgString }
	                          DESCRIPTION
	                          "Display Firmware Mismatch."
	                          ::=  51
	vpwrTrapConverterInputFailAlarm    TRAP-TYPE

	   ENTERPRISE      vpwrDcPowerTraps
	    VARIABLES { vpwrTrapsMsgString }
	                          DESCRIPTION
	                          "Converter Input Fail Alarm."
	                          ::=  52
	 vpwrTrapBatteryRechgIlimitFailAlarm    TRAP-TYPE

	   ENTERPRISE      vpwrDcPowerTraps
	    VARIABLES { vpwrTrapsMsgString }
	                          DESCRIPTION
	                         "Battery Recharge Current Limit Fail."
	                          ::=  53
	vpwrTrapSystemAlive    TRAP-TYPE

	   ENTERPRISE      vpwrDcPowerTraps
	    VARIABLES { vpwrTrapsMsgString }
	                          DESCRIPTION
	                          "Periodic Keepalive trap."
	                          ::=  54

--
--    LVD Alarm Group
--

	 vpwrLvdAlarmContactorOpen	OBJECT-IDENTITY
	                    STATUS  current
			DESCRIPTION
			"Contactor open"
			::= {vpwrLvdAlarmGroup 1   }


	 vpwrLvdAlarmCBOpen	OBJECT-IDENTITY
	                    STATUS  current
			DESCRIPTION
			"Circuit Breaker open"
			::= {vpwrLvdAlarmGroup 2   }

	 vpwrTrapLvdFuseOpen	OBJECT-IDENTITY
	                    STATUS  current
			DESCRIPTION
			"Fuse open"
			::= {vpwrLvdAlarmGroup 3   }
	 vpwrLvdAlarmWarning	OBJECT-IDENTITY
	                    STATUS  current
			DESCRIPTION
			"Plant Voltage below warning threshold"
			::= {vpwrLvdAlarmGroup 4   }

--
--    Rectifier Alarm Group
--

	vpwrRectAlarmDCFail   OBJECT-IDENTITY
	       STATUS          current
	       DESCRIPTION
	       "
	       "
	       ::= {vpwrRectifierAlarmGroup   1}

	vpwrRectAlarmBoostFail   OBJECT-IDENTITY
	       STATUS          current
	       DESCRIPTION
	       "
	       "
	       ::= {vpwrRectifierAlarmGroup   2}

	vpwrRectAlarmACFail   OBJECT-IDENTITY
	       STATUS          current
	       DESCRIPTION
	       "
	       "
	       ::= {vpwrRectifierAlarmGroup   3}

	vpwrRectAlarmHVSD   OBJECT-IDENTITY
	       STATUS          current
	       DESCRIPTION
	       "
	       "
	       ::= {vpwrRectifierAlarmGroup   4}

	vpwrRectAlarmFanFail   OBJECT-IDENTITY
	       STATUS          current
	       DESCRIPTION
	       "
	       "
	       ::= {vpwrRectifierAlarmGroup   5}

	vpwrRectAlarmAmbTemp   OBJECT-IDENTITY
	       STATUS          current
	       DESCRIPTION
	       "
	       "
	       ::= {vpwrRectifierAlarmGroup   6}
	vpwrRectAlarmIntTemp   OBJECT-IDENTITY
	       STATUS          current
	       DESCRIPTION
	       "
	       "
	       ::= {vpwrRectifierAlarmGroup   7}

	vpwrRectAlarmIShare   OBJECT-IDENTITY
	       STATUS          current
	       DESCRIPTION
	       "
	       "
	       ::= {vpwrRectifierAlarmGroup   8}

	vpwrRectAlarmUV   OBJECT-IDENTITY
	       STATUS          current
	       DESCRIPTION
	       "
	       "
	       ::= {vpwrRectifierAlarmGroup   9}

	vpwrRectAlarmLowVoltage   OBJECT-IDENTITY
	       STATUS          current
	       DESCRIPTION
	       "
	       "
	       ::= {vpwrRectifierAlarmGroup   10}

	vpwrRectAlarmReserved   OBJECT-IDENTITY
	       STATUS          current
	       DESCRIPTION
	       "
	       "
	       ::= {vpwrRectifierAlarmGroup   11}

	vpwrRectAlarmDCEnable   OBJECT-IDENTITY
	       STATUS          current
	       DESCRIPTION
	       "
	       "
	       ::= {vpwrRectifierAlarmGroup   12}

	vpwrRectAlarmRemoteShutdown   OBJECT-IDENTITY
	       STATUS          current
	       DESCRIPTION
	       "
	       "
	       ::= {vpwrRectifierAlarmGroup   13}

	vpwrRectAlarmModDisableShutdown   OBJECT-IDENTITY
	       STATUS          current
	       DESCRIPTION
	       "
	       "
	       ::= {vpwrRectifierAlarmGroup   14}

	vpwrRectAlarmShortPinShutdown   OBJECT-IDENTITY
	       STATUS          current
	       DESCRIPTION
	       "
	       "
	       ::= {vpwrRectifierAlarmGroup   15}

	vpwrRectAlarmBoostComm   OBJECT-IDENTITY
	       STATUS          current
	       DESCRIPTION
	       "
	       "
	       ::= {vpwrRectifierAlarmGroup   16}


	vpwrTrapsMsgString  OBJECT-TYPE
	                      SYNTAX     DisplayString(SIZE (0 .. 127))
	                      MAX-ACCESS not-accessible
	                      STATUS     current
	                      DESCRIPTION
	                     " Place holder for trap notification message string"
	                     ::= { vpwrDcPowerTrapsMsgString 1 }

	vpwrTrapUserIpAddress   OBJECT-TYPE
	                            SYNTAX        IpAddress
	                            MAX-ACCESS    not-accessible
	                            STATUS        current
	                            DESCRIPTION
	                               "Place holder for IP address of the user accessing the system"
	                       ::= { vpwrDcPowerTrapsMsgString 2}

	vpwrTrapEventTimeStamp   OBJECT-TYPE
	                            SYNTAX        IpAddress
	                            MAX-ACCESS    not-accessible
	                            STATUS        current
	                            DESCRIPTION
	                               "Place holder for time-stamp."
	                       ::= { vpwrDcPowerTrapsMsgString 3}

	sysRelayConfigTable OBJECT-TYPE
	   SYNTAX     SEQUENCE OF SysRelayConfigEntry
	   MAX-ACCESS not-accessible
	   STATUS     current
	   DESCRIPTION
	   "This table describes battery temperature probes.
	   "
	   ::= { vpwrDcPowerAlarmGroup 3  }

	sysRelayConfigEntry OBJECT-TYPE
	   SYNTAX     SysRelayConfigEntry
	   MAX-ACCESS not-accessible
	   STATUS     current
	   DESCRIPTION
	           "An entry containing information applicable to a
	           particular temperature probe."
	   INDEX { sysRelayIndex }
	   ::= { sysRelayConfigTable 1 }

	SysRelayConfigEntry ::= SEQUENCE {
	   sysRelayIndex       INTEGER,
	   sysRelayDefaultName        DisplayString,
	   sysRelayCustomName        DisplayString,
	   sysRelayAlarmSeverity        INTEGER
	}

	     sysRelayIndex              OBJECT-TYPE
	                            SYNTAX        INTEGER
	                            MAX-ACCESS    read-only
	                            STATUS        current
	                            DESCRIPTION
	                               "Index into temperature table"
	                       ::= { sysRelayConfigEntry 1}

	     sysRelayDefaultName   OBJECT-TYPE
	                            SYNTAX        DisplayString (SIZE (1 .. 8))
	                            MAX-ACCESS    read-only
	                            STATUS        current
	                            DESCRIPTION
	                               "A string identifying probe location."
	                       ::= { sysRelayConfigEntry 2}

	     sysRelayCustomName   OBJECT-TYPE
	                            SYNTAX        DisplayString (SIZE (1 .. 8))
	                            MAX-ACCESS    read-write
	                            STATUS        current
	                            DESCRIPTION
	                               "A string identifying probe location."
	                       ::= { sysRelayConfigEntry 3}

	     sysRelayAlarmSeverity   OBJECT-TYPE
	                          SYNTAX INTEGER {
	                                 alarmNone(0),
	                                 alarmMajor(1),
	                                 alarmMinor(2),
	                                 alarmMajorAndMinor(3)
	                                 }
	                            MAX-ACCESS    read-write
	                            STATUS        current
	                            DESCRIPTION
	                               "Current temperature as recorded by the probe."
	                       ::= { sysRelayConfigEntry 4}


	sysAlarmConfigTable OBJECT-TYPE
	   SYNTAX     SEQUENCE OF SysAlarmConfigEntry
	   MAX-ACCESS not-accessible
	   STATUS     current
	   DESCRIPTION
	   "This table describes battery temperature probes.
	   "
	   ::= { vpwrDcPowerAlarmGroup 4  }

	sysAlarmConfigEntry OBJECT-TYPE
	   SYNTAX     SysAlarmConfigEntry
	   MAX-ACCESS not-accessible
	   STATUS     current
	   DESCRIPTION
	           "An entry containing information applicable to a
	           particular temperature probe."
	   INDEX { sysAlarmIndex }
	   ::= { sysAlarmConfigTable 1 }

	SysAlarmConfigEntry ::= SEQUENCE {
	   sysAlarmIndex       INTEGER,
	   sysAlarmDefaultName        DisplayString,
	   sysAlarmCustomName        DisplayString,
	   sysAlarmSeverity        INTEGER   ,
	   sysAlarmToRelayMapping  DisplayString  ,
	   sysAlarmOperStatus      INTEGER
	}

	     sysAlarmIndex    OBJECT-TYPE
	                            SYNTAX        INTEGER
	                            MAX-ACCESS    read-only
	                            STATUS        current
	                            DESCRIPTION
	                               "Index into temperature table"
	                       ::= { sysAlarmConfigEntry 1}

	     sysAlarmDefaultName   OBJECT-TYPE
	                            SYNTAX        DisplayString (SIZE (1 .. 8))
	                            MAX-ACCESS    read-only
	                            STATUS        current
	                            DESCRIPTION
	                               "A string identifying probe location."
	                       ::= { sysAlarmConfigEntry 2}

	     sysAlarmCustomName   OBJECT-TYPE
	                            SYNTAX        DisplayString (SIZE (1 .. 8))
	                            MAX-ACCESS    read-write
	                            STATUS        current
	                            DESCRIPTION
	                               "A string identifying probe location."
	                       ::= { sysAlarmConfigEntry 3}

	     sysAlarmSeverity   OBJECT-TYPE
	                          SYNTAX INTEGER {
	                                 none(0),
	                                 major(1),
	                                 minor(2),
	                                 majorAndMinor(3)
	                                 }
	                            MAX-ACCESS    read-write
	                            STATUS        current
	                            DESCRIPTION
	                               "Alarm Severity as denoted by Major and Minor Alarm Mask"
	                       ::= { sysAlarmConfigEntry 4}

	       sysAlarmToRelayMapping   OBJECT-TYPE
	                            SYNTAX DisplayString (SIZE (1 .. 8))
	                            MAX-ACCESS    read-write
	                            STATUS        current
	                            DESCRIPTION
	                               "No additional mapping = 0
	                                Map to Relay A  = 1
	                                Map to Relay B  = 2
	                                Map to Relay C  = 4
	                                Map to Relay D  = 8
	                                Map to Relay E  = 16
	                                Map to Relay F  = 32
	                                Map to Relay A and B  = (1 + 2) and so on
	                                The major/minor classification of alarms automatically
	                                associates it with Major/Minor relay. Assigning a null
	                                mapping here does not override sysRelayAlarmSeverity for
	                                the alarm.
	                                It should be used to define mapping to additional relays.
	                               "
	                       ::= { sysAlarmConfigEntry 5}

	     sysAlarmOperStatus   OBJECT-TYPE
	                          SYNTAX INTEGER {
	                                 inactive(0),
	                                 active(1)
	                                }
	                            MAX-ACCESS    read-only
	                            STATUS        current
	                            DESCRIPTION
	                               "Indicates current alarm status"
	                       ::= { sysAlarmConfigEntry 6}


	sysAuxAlarmConfigTable OBJECT-TYPE
	   SYNTAX     SEQUENCE OF SysAuxAlarmConfigEntry
	   MAX-ACCESS not-accessible
	   STATUS     current
	   DESCRIPTION
	   "This table describes battery temperature probes.
	   "
	   ::= { vpwrDcPowerAlarmGroup 5  }

	sysAuxAlarmConfigEntry OBJECT-TYPE
	   SYNTAX     SysAuxAlarmConfigEntry
	   MAX-ACCESS not-accessible
	   STATUS     current
	   DESCRIPTION
	           "An entry containing information applicable to a
	           particular temperature probe."
	   INDEX { sysAuxAlarmIndex }
	   ::= { sysAuxAlarmConfigTable 1 }

	SysAuxAlarmConfigEntry ::= SEQUENCE {
	   sysAuxAlarmIndex       INTEGER,
	   sysAuxAlarmDefaultName        DisplayString,
	   sysAuxAlarmCustomName        DisplayString,
	   sysAuxAlarmSeverity        INTEGER   ,
	   sysAuxAlarmToRelayMapping  DisplayString  ,
	   sysAuxAlarmPolarity        INTEGER ,
	   sysAuxAlarmOperStatus      INTEGER
	}

	     sysAuxAlarmIndex    OBJECT-TYPE
	                            SYNTAX        INTEGER
	                            MAX-ACCESS    read-only
	                            STATUS        current
	                            DESCRIPTION
	                               "Index into temperature table"
	                       ::= { sysAuxAlarmConfigEntry 1}

	     sysAuxAlarmDefaultName   OBJECT-TYPE
	                            SYNTAX        DisplayString (SIZE (1 .. 8))
	                            MAX-ACCESS    read-only
	                            STATUS        current
	                            DESCRIPTION
	                               "A string identifying probe location."
	                       ::= { sysAuxAlarmConfigEntry 2}

	     sysAuxAlarmCustomName   OBJECT-TYPE
	                            SYNTAX        DisplayString (SIZE (1 .. 8))
	                            MAX-ACCESS    read-write
	                            STATUS        current
	                            DESCRIPTION
	                               "A string identifying probe location."
	                       ::= { sysAuxAlarmConfigEntry 3}

	     sysAuxAlarmSeverity   OBJECT-TYPE
	                          SYNTAX INTEGER {
	                                 none(0),
	                                 major(1),
	                                 minor(2),
	                                 majorAndMinor(3)
	                                 }
	                            MAX-ACCESS    read-write
	                            STATUS        current
	                            DESCRIPTION
	                               "Aux Alarm Severity"
	                       ::= { sysAuxAlarmConfigEntry 4}

	       sysAuxAlarmToRelayMapping   OBJECT-TYPE
	                            SYNTAX DisplayString (SIZE (1 .. 8))
	                            MAX-ACCESS    read-write
	                            STATUS        current
	                            DESCRIPTION
	                               "No additional mapping = 0
	                                Map to Relay A  = 1
	                                Map to Relay B  = 2
	                                Map to Relay C  = 4
	                                Map to Relay D  = 8
	                                Map to Relay E  = 16
	                                Map to Relay F  = 32
	                                Map to Relay A and B  = (1 + 2) and so on
	                                The major/minor classification of alarms automatically
	                                associates it with Major/Minor relay. Assigning a null
	                                mapping here does not override sysRelayAlarmSeverity for
	                                the alarm.
	                                It should be used to define mapping to additional relays.
	                               "
	                       ::= { sysAuxAlarmConfigEntry 5}

	     sysAuxAlarmPolarity   OBJECT-TYPE
	                          SYNTAX INTEGER {
	                                 alarmOnOpen(0),
	                                 alarmOnClose(1)
	                                }
	                            MAX-ACCESS    read-write
	                            STATUS        current
	                            DESCRIPTION
	                               "Current temperature as recorded by the probe."
	                       ::= { sysAuxAlarmConfigEntry 6}

	     sysAuxAlarmOperStatus   OBJECT-TYPE
	                          SYNTAX INTEGER {
	                                 inactive(0),
	                                 active(1)
	                                }
	                            MAX-ACCESS    read-only
	                            STATUS        current
	                            DESCRIPTION
	                               "Indicates current alarm status"
	                       ::= { sysAuxAlarmConfigEntry 7}

	     sysAlarmComFailState   OBJECT-TYPE
	                          SYNTAX INTEGER {
	                                 disabled(0),
	                                 enabled(1),
	                                 other(2)
	                                 }
	                            MAX-ACCESS    read-write
	                            STATUS        current
	                            DESCRIPTION
	                               "Enable/Disable generation of comm fail alarm."
	                       ::= { vpwrDcPowerAlarmGroup 6 }

	     sysAlarmIShareState   OBJECT-TYPE
	                          SYNTAX INTEGER {
	                                 disabled(0),
	                                 enabled(1),
	                                 other(2)
	                                 }
	                            MAX-ACCESS    read-write
	                            STATUS        current
	                            DESCRIPTION
	                               "Enable/Disable generation of current share alarm."
	                       ::= { vpwrDcPowerAlarmGroup 7}

	     sysAlarmRedundancyState   OBJECT-TYPE
	                          SYNTAX INTEGER {
	                                 disabled(0),
	                                 nPlus1(1),
	                                 nPlus2(2)
	                                 }
	                            MAX-ACCESS    read-write
	                            STATUS        current
	                            DESCRIPTION
	                               "Enable/Disable generation of redundancy alarm."
	                       ::= { vpwrDcPowerAlarmGroup 8}

	--
	-- The Ringer Configuration Parameters group.
	--


	vpwrRingerParameterTable OBJECT-TYPE
	   SYNTAX     SEQUENCE OF VpwrRingerParameterEntry
	   MAX-ACCESS not-accessible
	   STATUS     current
	   DESCRIPTION
	           "A list of alarm table entries.  The table contains
	           zero, one, or many rows at any moment, depending upon
	           the number of alarm conditions in effect.  The table
	           is initially empty at agent startup.  The agent
	           creates a row in the table each time a condition is
	           detected and deletes that row when that condition no
	           longer pertains.  
	           The vpwrAlarmIndex, for each type of module starts at 1
	           and is limited by the total number of alarams that can be
	           generated by the module.

	           Alarms are named by an AutonomousType (OBJECT
	           IDENTIFIER), vpwrAlarmDescr, to allow a single table to
	           reflect alarms for different type of modules.

	           The number of rows in the table at any given time is
	           reflected by the value of vpwrAlarmsPresent."
	           
	   ::= { vpwrRingerConfigGroup 1 }

	vpwrRingerParameterEntry OBJECT-TYPE
	   SYNTAX    VpwrRingerParameterEntry
	   MAX-ACCESS not-accessible
	   STATUS     current
	   DESCRIPTION
	           "An entry containing information applicable to a
	           particular alarm."
	   INDEX { vpwrModuleIndex,vpwrRingerIndex}
	   ::= { vpwrRingerParameterTable 1 }

	VpwrRingerParameterEntry ::= SEQUENCE {
	   vpwrRingerIndex       INTEGER,
	   vpwrRingerParameterAdminState       INTEGER,
	   vpwrRingerParameterAcVoltage        INTEGER,
	   vpwrRingerParameterDcVoltage        INTEGER,
	   vpwrRingerParameterFrequency        INTEGER
	 }
	         vpwrRingerIndex                OBJECT-TYPE
	                     SYNTAX INTEGER
	                     MAX-ACCESS read-only
	                     STATUS current
	                     DESCRIPTION
	                     "  This parameter allows selecting ringer A or Ringer B as the active ringer.
	                     "
	                     REFERENCE " "

	                     ::= {vpwrRingerParameterEntry 1}

	        vpwrRingerParameterAdminState OBJECT-TYPE
	                     SYNTAX INTEGER {
	                            ringerDisabled(0),
	                            ringerAOn(1) ,
	                             ringerBOn(2)
	                    }
	                     MAX-ACCESS read-write
	                     STATUS current
	                     DESCRIPTION
	                     "  This parameter allows selecting ringer A or Ringer B as the active ringer.
	                     "
	                     REFERENCE " "

	                     ::= {vpwrRingerParameterEntry 2}

	          vpwrRingerParameterAcVoltage OBJECT-TYPE
	                     SYNTAX INTEGER (7000 .. 11000)
	                     UNITS  " *.01 Volts"
	                     MAX-ACCESS read-write
	                     STATUS current
	                     DESCRIPTION
	                     "
	                     "
	                     REFERENCE " "
	                     ::= {vpwrRingerParameterEntry 3}

	           vpwrRingerParameterDcVoltage OBJECT-TYPE
	                     SYNTAX INTEGER (0 .. 5600 )
	                     UNITS  " *.01 Volts"
	                     MAX-ACCESS read-write
	                     STATUS current
	                     DESCRIPTION
	                     "
	                     "
	                     REFERENCE " "
	                     ::= {vpwrRingerParameterEntry 4}

	           vpwrRingerParameterFrequency OBJECT-TYPE
	                     SYNTAX INTEGER (17 .. 50)
	                     UNITS  " Hz"
	                     MAX-ACCESS read-write
	                     STATUS current
	                     DESCRIPTION
	                     "
	                     "
	                     REFERENCE " "
	                     ::= {vpwrRingerParameterEntry 5}

	vpwrRingerNumberPresent OBJECT-TYPE
	   SYNTAX     Gauge32
	   MAX-ACCESS read-only
	   STATUS     current
	   DESCRIPTION
	           "The present number of active alarm conditions."
	   ::= { vpwrRingerConfigGroup 2 }


--
--    ringer Alarm Group
--

	 vpwrRingerAlarmaAFailed	OBJECT-IDENTITY
	                    STATUS  current
			DESCRIPTION
			"Ringer A Failed"
			::= {vpwrRingerAlarmGroup 1   }

	 vpwrRingerAlarmAOTemp	OBJECT-IDENTITY
	                    STATUS  current
			DESCRIPTION
			"Ringer A Heatsink Over-Temperature"
			::= {vpwrRingerAlarmGroup 2   }

	 vpwrRingerAlarmAOCurrent	OBJECT-IDENTITY
	                    STATUS  current
			DESCRIPTION
			"Ringer A Over-Current protection"
			::= {vpwrRingerAlarmGroup 3   }

	  vpwrRingerAlarmaBFailed	OBJECT-IDENTITY
	                    STATUS  current
			DESCRIPTION
			"Ringer A Failed"
			::= {vpwrRingerAlarmGroup 4   }

	 vpwrRingerAlarmBOverTemp	OBJECT-IDENTITY
	                    STATUS  current
			DESCRIPTION
			"Ringer A Heatsink Over-Temperature"
			::= {vpwrRingerAlarmGroup 5   }

	 vpwrRingerAlarmBOverCurrent	OBJECT-IDENTITY
	                    STATUS  current
			DESCRIPTION
			"Ringer A Over-Current protection"
			::= {vpwrRingerAlarmGroup 6   }



	vpwrBoostAdminState OBJECT-TYPE
	                     SYNTAX INTEGER {
	                            boostDisabled(0),
	                            boostEnabled(1)
	                    }
	                     MAX-ACCESS read-write
	                     STATUS current
	                     DESCRIPTION
	                     "  This parameter allows enabling or disabling boost.
	                     "
	                     REFERENCE " "

	                     ::= {vpwrBatteryBoostGroup 1}

	  vpwrBoostVoltage OBJECT-TYPE
	                     SYNTAX INTEGER (7000 .. 11000)
	                     UNITS  " *.01 Volts"
	                     MAX-ACCESS read-write
	                     STATUS current
	                     DESCRIPTION
	                     "
	                     "
	                     REFERENCE " "
	                     ::= {vpwrBatteryBoostGroup 2}

	  vpwrBoostDuration    OBJECT-TYPE
	                     SYNTAX INTEGER (0 .. 100 )
	                     UNITS  "Hours"
	                     MAX-ACCESS read-write
	                     STATUS current
	                     DESCRIPTION
	                     "
	                     "
	                     REFERENCE " "
	                     ::= {vpwrBatteryBoostGroup 3}


	vpwrBoostOperState OBJECT-TYPE
	                     SYNTAX INTEGER {
	                            boostInactive(0),
	                            boostActive(1)
	                    }
	                     MAX-ACCESS read-write
	                     STATUS current
	                     DESCRIPTION
	                     "  This parameter allows starting or stoping boost if it is enabled.
	                     "
	                     REFERENCE " "

	                     ::= {vpwrBatteryBoostGroup 4}


	vpwrBatteryCurrentLimitAdminState OBJECT-TYPE
	                     SYNTAX INTEGER {
	                            battetyCurrentLimitDisabled(0),
	                            battetyCurrentLimitEnabled(1)
	                    }
	                     MAX-ACCESS read-write
	                     STATUS current
	                     DESCRIPTION
	                     "  This parameter allows enabling or disabling battery current limit.
	                     "
	                     REFERENCE " "

	                     ::= {vpwrBatteryCurrentGroup 1}

	  vpwrBattetyCurrentLimitValue OBJECT-TYPE
	                     SYNTAX INTEGER (5 .. 40)
	                     UNITS  "Ampere"
	                     MAX-ACCESS read-write
	                     STATUS current
	                     DESCRIPTION
	                     "
	                     "
	                     REFERENCE " "
	                     ::= {vpwrBatteryCurrentGroup 2}

	   vpwrBattetyCurrentValue OBJECT-TYPE
	                     SYNTAX INTEGER (5 .. 40)
	                     UNITS  "Ampere"
	                     MAX-ACCESS read-only
	                     STATUS current
	                     DESCRIPTION
	                     "
	                     "
	                     REFERENCE " "
	                     ::= {vpwrBatteryCurrentGroup 3}



	vpwrBDTAdminState OBJECT-TYPE
	                     SYNTAX INTEGER {
	                            bdtDisabled(0),
	                            bdtEnabled(1) 
	                    }
	                     MAX-ACCESS read-write
	                     STATUS current
	                     DESCRIPTION
	                     "  Enable /Disable Battery Discharge Test execution.
	                     "
	                     REFERENCE " "

	                     ::= {vpwrBatteryDischargeTestGroup 1}

	vpwrBDTDuration OBJECT-TYPE
	                     SYNTAX INTEGER (17 .. 50)
	                     UNITS  "Minutes"
	                     MAX-ACCESS read-write
	                     STATUS current
	                     DESCRIPTION
	                     "
	                     "
	                     REFERENCE " "
	                     ::= {vpwrBatteryDischargeTestGroup 2}
	 vpwrBDTAlarmVoltage OBJECT-TYPE
	                     SYNTAX INTEGER (7000 .. 11000)
	                     UNITS  " *.01 Volts"
	                     MAX-ACCESS read-write
	                     STATUS current
	                     DESCRIPTION
	                     "
	                     "
	                     REFERENCE " "
	                     ::= {vpwrBatteryDischargeTestGroup 3}

	   vpwrBDTAbortVoltage OBJECT-TYPE
	                     SYNTAX INTEGER (0 .. 5600 )
	                     UNITS  " *.01 Volts"
	                     MAX-ACCESS read-write
	                     STATUS current
	                     DESCRIPTION
	                     "
	                     "
	                     REFERENCE " "
	                     ::= {vpwrBatteryDischargeTestGroup 4}

	   vpwrBDTAlarmCoefficient OBJECT-TYPE
	                     SYNTAX INTEGER (0 .. 1 )
	                     UNITS  "None"
	                     MAX-ACCESS read-write
	                     STATUS current
	                     DESCRIPTION
	                     "
	                     "
	                     REFERENCE " "
	                     ::= {vpwrBatteryDischargeTestGroup 5}

	 vpwrBDTOperState OBJECT-TYPE
	                     SYNTAX INTEGER {
	                            bdtInactive(0),
	                            bdtActive(1)
	                    }
	                     MAX-ACCESS read-write
	                     STATUS current
	                     DESCRIPTION
	                     "  Start/Stop Battery Discharge Test execution.
	                     "
	                     REFERENCE " "

	                     ::= {vpwrBatteryDischargeTestGroup 6}

	  vpwrBDTClearAlarm OBJECT-TYPE
	                     SYNTAX INTEGER {
	                            bdtNoAlarm(0)
	                            bdtAlarmPresent(1)
	                    }
	                     MAX-ACCESS read-write
	                     STATUS current
	                     DESCRIPTION
	                     "  Clears any active bdt alarm.
	                     "
	                     REFERENCE " "

	                     ::= {vpwrBatteryDischargeTestGroup 7}

--
-- Module identification information
--
	vpwrModuleIdentTable OBJECT-TYPE
	   SYNTAX     SEQUENCE OF VpwrModuleIdentEntry
	   MAX-ACCESS not-accessible
	   STATUS     current
	   DESCRIPTION
	   " This table describes shelves and modules
	     that make up the sysetm.
	   "
	   ::= { vpwrDcPowerModuleIdent 1 }

	--
	-- The Module Identifier Entry.  Defines the sequence for module tables.
	--
   vpwrModuleIdentEntry OBJECT-TYPE
       SYNTAX     VpwrModuleIdentEntry
       MAX-ACCESS not-accessible
       STATUS     current
       DESCRIPTION
               "An entry containing information applicable to a
               particular Module."
	   AUGMENTS {vpwrSystemIdentEntry }
       ::= { vpwrModuleIdentTable 1 }


	VpwrModuleIdentEntry ::= SEQUENCE {
	   vpwrModuleSerialNumber     DisplayString  ,
	   vpwrModuleModelNumber      DisplayString ,
	   vpwrModuleFwVersion 		  DisplayString ,
	   vpwrModuleTestDate         DisplayString ,
	   vpwrModuleOperHours 		  Counter32
	}

	   vpwrModuleSerialNumber        OBJECT-TYPE
	           SYNTAX        DisplayString
	           MAX-ACCESS    read-only
	           STATUS        current
	           DESCRIPTION
	                               "Serial Number of the module"
	           ::= { vpwrModuleIdentEntry 1}

	   vpwrModuleModelNumber     OBJECT-TYPE
	           SYNTAX        DisplayString
	           MAX-ACCESS    read-only
	           STATUS        current
	           DESCRIPTION
	                               "Model Number of the module."
	           ::= { vpwrModuleIdentEntry 2}

	   vpwrModuleFwVersion   OBJECT-TYPE
	           SYNTAX        DisplayString 
	           MAX-ACCESS    read-only
	           STATUS        current
	           DESCRIPTION
	                               "Firmware version of the module."
	           ::= { vpwrModuleIdentEntry 3}

	   vpwrModuleTestDate   OBJECT-TYPE
	           SYNTAX        DisplayString
	           MAX-ACCESS    read-only
	           STATUS        current
	           DESCRIPTION
	                               "Date when the module was last tested."
	           ::= { vpwrModuleIdentEntry 4}

	   vpwrModuleOperHours   OBJECT-TYPE
	           SYNTAX        Counter32
	           MAX-ACCESS    read-only
	           STATUS        current
	           DESCRIPTION
	                               "Cumulative Operating Hours."
	           ::= { vpwrModuleIdentEntry 5}

--
-- Panel Module inventory info
--
	vpwrPanelModuleIdentTable OBJECT-TYPE
	   SYNTAX     SEQUENCE OF VpwrPanelModuleIdentEntry
	   MAX-ACCESS not-accessible
	   STATUS     current
	   DESCRIPTION
	   " This table describes shelves and modules
	     that make up the sysetm.
	   "
	   ::= { vpwrDcPowerModuleIdent 2 }

	--
	-- The Module Identifier Entry.  Defines the sequence for module tables.
	--
   vpwrPanelModuleIdentEntry OBJECT-TYPE
       SYNTAX     VpwrPanelModuleIdentEntry
       MAX-ACCESS not-accessible
       STATUS     current
       DESCRIPTION
               "An entry containing information applicable to a
               particular alarm."
	AUGMENTS {VpwrPanelIdentEntry }
       ::= { vpwrPanelModuleIdentTable 1 }


	VpwrPanelModuleIdentEntry ::= SEQUENCE {
	   vpwrPanelModuleSerialNumber     DisplayString  ,
	   vpwrPanelModuleModelNumber      DisplayString ,
	   vpwrPanelModuleFwVersion 		DisplayString ,
	   vpwrPanelModuleTestDate         DisplayString ,
	   vpwrPanelModuleOperHours 		  Counter32
	}

	   vpwrPanelModuleSerialNumber        OBJECT-TYPE
	           SYNTAX        DisplayString
	           MAX-ACCESS    read-only
	           STATUS        current
	           DESCRIPTION
	                               "Serial Number of the module"
	           ::= { vpwrPanelModuleIdentEntry 1}

	   vpwrPanelModuleModelNumber     OBJECT-TYPE
	           SYNTAX        DisplayString
	           MAX-ACCESS    read-only
	           STATUS        current
	           DESCRIPTION
	                               "Model Number of the module."
	           ::= { vpwrPanelModuleIdentEntry 2}

	   vpwrPanelModuleFwVersion   OBJECT-TYPE
	           SYNTAX        DisplayString 
	           MAX-ACCESS    read-only
	           STATUS        current
	           DESCRIPTION
	                               "Firmware version of the module."
	           ::= { vpwrPanelModuleIdentEntry 3}

	   vpwrPanelModuleTestDate   OBJECT-TYPE
	           SYNTAX        DisplayString
	           MAX-ACCESS    read-only
	           STATUS        current
	           DESCRIPTION
	                               "Date when the module was last tested."
	           ::= { vpwrPanelModuleIdentEntry 4}

	   vpwrPanelModuleOperHours   OBJECT-TYPE
	           SYNTAX        Counter32
	           MAX-ACCESS    read-only
	           STATUS        current
	           DESCRIPTION
	                               "Cumulative Operating Hours."
	           ::= { vpwrPanelModuleIdentEntry 5}
--
-- Bayctrl Module inventory info
--
	vpwrBayctrlModuleIdentTable OBJECT-TYPE
	   SYNTAX     SEQUENCE OF VpwrBayctrlModuleIdentEntry
	   MAX-ACCESS not-accessible
	   STATUS     current
	   DESCRIPTION
	   " This table describes bay controllers that make up the sysetm.
	   "
	   ::= { vpwrDcPowerModuleIdent 3 }

	--
	-- The Module Identifier Entry.  Defines the sequence for module tables.
	--
   vpwrBayctrlModuleIdentEntry OBJECT-TYPE
       SYNTAX     VpwrBayctrlModuleIdentEntry
       MAX-ACCESS not-accessible
       STATUS     current
       DESCRIPTION
               "An entry containing information applicable to a particular bay controller."
	AUGMENTS {VpwrBayctrlIdentEntry }
       ::= { vpwrBayctrlModuleIdentTable 1 }


	VpwrBayctrlModuleIdentEntry ::= SEQUENCE {
	   vpwrBayctrlSerialNumber     DisplayString  ,
	   vpwrBayctrlModelNumber      DisplayString ,
	   vpwrBayctrlFwVersion 		DisplayString ,
	   vpwrBayctrlTestDate         DisplayString ,
	   vpwrBayctrlOperHours 		  Counter32
	}

	   vpwrBayctrlSerialNumber        OBJECT-TYPE
	           SYNTAX        DisplayString
	           MAX-ACCESS    read-only
	           STATUS        current
	           DESCRIPTION
	                               "Serial Number of the bay controller"
	           ::= { vpwrBayctrlModuleIdentEntry 1}

	   vpwrBayctrlModelNumber     OBJECT-TYPE
	           SYNTAX        DisplayString
	           MAX-ACCESS    read-only
	           STATUS        current
	           DESCRIPTION
	                               "Model Number of the bay controller."
	           ::= { vpwrBayctrlModuleIdentEntry 2}

	   vpwrBayctrlFwVersion   OBJECT-TYPE
	           SYNTAX        DisplayString 
	           MAX-ACCESS    read-only
	           STATUS        current
	           DESCRIPTION
	                               "Firmware version of the bay controller."
	           ::= { vpwrBayctrlModuleIdentEntry 3}

	   vpwrBayctrlTestDate   OBJECT-TYPE
	           SYNTAX        DisplayString
	           MAX-ACCESS    read-only
	           STATUS        current
	           DESCRIPTION
	                               "Date when the bayctrl was last tested."
	           ::= { vpwrBayctrlModuleIdentEntry 4}

	   vpwrBayctrlOperHours   OBJECT-TYPE
	           SYNTAX        Counter32
	           MAX-ACCESS    read-only
	           STATUS        current
	           DESCRIPTION
	                               "Cumulative Operating Hours."
	           ::= { vpwrBayctrlModuleIdentEntry 5}



END
