AIRESPACE-REF-MIB DEFINITIONS ::= BEGIN

IMPORTS
     MODULE-IDENTITY,
     enterprises                 
         FROM SNMPv2-SMI;

airespace MODULE-IDENTITY
        LAST-UPDATED "200512190000Z"  -- December 19, 2005
        ORGANIZATION "Airespace, Inc."
        CONTACT-INFO
            "        Cisco Systems,
                     Customer Service
             Postal: 170 West Tasman Drive
                     San Jose, CA  95134
                     USA
                Tel: +1 800 553-NETS

              Email: cs-wnbu-snmp@cisco.com"
        DESCRIPTION
            "The Structure of Management Information for the
             Airespace enterprise."
        REVISION    "200512190000Z"  -- December 19, 2005
        DESCRIPTION
                   "Initial version of this MIB module."
        ::= { enterprises 14179 }  -- assigned by IANA

END
