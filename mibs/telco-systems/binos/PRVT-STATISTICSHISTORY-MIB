-- *********************************************************************
-- *********************************************************************
-- ** Filename: PRVT-STATISTICSHISTORY-MIB
-- *********************************************************************
-- *********************************************************************
-- ** Filename: PRVT-STATISTICSHISTORY-MIB
-- ** Project: T - Ethernet and Fast Ethernet IP Switches.
-- ** Purpose: Private MIB
-- *********************************************************************
-- (c) Copyright, 2001, BATM Advanced Communications. All rights reserved.
-- WARNING:
--
-- BY UTILIZING THIS FILE, YOU AGREE TO THE FOLLOWING:
--
-- This file is the property of BATM Advanced Communications.
-- BATM Advanced Communications retains all title and
-- ownership in the Specification, including any revisions.

-- BATM Advanced Communications grants all interested parties a non-exclusive
-- license to use and distribute an unmodified copy of this
-- Specification in connection with management of BATM Advanced Communications 
-- and Telco Systems products, and without fee, provided that the following
-- conditions are met:
-- 1. Redistributions of this specification must retain the above copyright
-- notice, this list of conditions and the following disclaimer.
-- 2. Redistributions in binary form must reproduce the above copyright
-- notice, this list of conditions and the following disclaimer in the
-- documentation and/or other materials provided with the distribution.
-- 3. The name of the BATM Advanced Communications MAY NOT be used to endorse
-- or promote products derived from this specification without specific prior written
-- permission.
--
-- EXCEPT AS RESTRICTED BY LAW, OR AS PROVIDED IN BATM'S LIMITED
-- WARRANTY, THE SPECIFICATIONS CONTAINED IN THIS FILE ARE
-- PROVIDED "AS IS" WITHOUT WARRANTY OF ANY KIND, EITHER EXPRESSED
-- OR IMPLIED, INCLUDING BUT NOT LIMITED TO, ANY IMPLIED WARRANTIES
-- OF MERCHANTABILITY OR FITNESS FOR A PARTICULAR PURPOSE.
-- IN NO EVENT SHALL BATM BE LIABLE FOR ANY DAMAGES WHATSOEVER
-- INCLUDING, WITHOUT LIMITATION, DAMAGES FOR LOSS OF BUSINESS
-- PROFITS, BUSINESS INTERRUPTION, LOSS OF BUSINESS INFORMATION OR
-- OTHER CONSEQUENTIAL DAMAGES ARISING OUT OF THE USE, OR INABILITY
-- TO USE, THE SPECIFICATION CONTAINED IN THIS FILE.
-- *********************************************************************
-- (c) Copyright, 2001, BATM Advanced Communications. All rights reserved.
-- WARNING:
--
-- BY UTILIZING THIS FILE, YOU AGREE TO THE FOLLOWING:
--
-- This file is the property of BATM Advanced Communications.
-- BATM Advanced Communications retains all title and
-- ownership in the Specification, including any revisions.

-- BATM Advanced Communications grants all interested parties a non-exclusive
-- license to use and distribute an unmodified copy of this
-- Specification in connection with management of BATM Advanced Communications 
-- and Telco Systems products, and without fee, provided that the following
-- conditions are met:
-- 1. Redistributions of this specification must retain the above copyright
-- notice, this list of conditions and the following disclaimer.
-- 2. Redistributions in binary form must reproduce the above copyright
-- notice, this list of conditions and the following disclaimer in the
-- documentation and/or other materials provided with the distribution.
-- 3. The name of the BATM Advanced Communications MAY NOT be used to endorse
-- or promote products derived from this specification without specific prior written
-- permission.
--
-- EXCEPT AS RESTRICTED BY LAW, OR AS PROVIDED IN BATM'S LIMITED
-- WARRANTY, THE SPECIFICATIONS CONTAINED IN THIS FILE ARE
-- PROVIDED "AS IS" WITHOUT WARRANTY OF ANY KIND, EITHER EXPRESSED
-- OR IMPLIED, INCLUDING BUT NOT LIMITED TO, ANY IMPLIED WARRANTIES
-- OF MERCHANTABILITY OR FITNESS FOR A PARTICULAR PURPOSE.
-- IN NO EVENT SHALL BATM BE LIABLE FOR ANY DAMAGES WHATSOEVER
-- INCLUDING, WITHOUT LIMITATION, DAMAGES FOR LOSS OF BUSINESS
-- PROFITS, BUSINESS INTERRUPTION, LOSS OF BUSINESS INFORMATION OR
-- OTHER CONSEQUENTIAL DAMAGES ARISING OUT OF THE USE, OR INABILITY
-- TO USE, THE SPECIFICATION CONTAINED IN THIS FILE.
PRVT-STATISTICSHISTORY-MIB DEFINITIONS ::= BEGIN

IMPORTS
MODULE-IDENTITY,
OBJECT-TYPE,
Counter32,
Unsigned32, 
Counter64,
Gauge32,
IpAddress
FROM SNMPv2-SMI

MODULE-COMPLIANCE, 
OBJECT-GROUP, 
NOTIFICATION-GROUP
FROM SNMPv2-CONF

DisplayString,
TruthValue
FROM SNMPv2-TC -- [RFC2579]

InterfaceIndex, ifIndex
FROM IF-MIB

switch
FROM PRVT-SWITCH-MIB;

    -------------------------------------------------------------------------------
    --     PRIVATE BRANCH 
    -------------------------------------------------------------------------------

prvtStatisticsHistoryMib MODULE-IDENTITY
    LAST-UPDATED "201002030000Z"
    ORGANIZATION "BATM Advanced Communication"
    CONTACT-INFO 
         "BATM/Telco Systems Support team
            Email: 
            For North America: techsupport@telco.com
            For North Europe: support@batm.de, info@batm.de
            For the rest of the world: techsupport@telco.com"
    DESCRIPTION
            "Management Information Base module for StatisticsHistory "

   -- revision history       
    REVISION     "201002030000Z"
    DESCRIPTION 
    "Initial revision."
   ::= { switch 140 }


prvtStatisticsHistoryNotifications            OBJECT IDENTIFIER ::= { prvtStatisticsHistoryMib 0 }
prvtStatisticsHistoryObjects                  OBJECT IDENTIFIER ::= { prvtStatisticsHistoryMib 1 }
prvtStatisticsHistoryConformance              OBJECT IDENTIFIER ::= { prvtStatisticsHistoryMib 2 }

--
-- STATISTICS HISTORY Objects
--

prvtStatisticsHistoryCfg            	OBJECT IDENTIFIER ::= { prvtStatisticsHistoryObjects 1 }
prvtStatHistDailySnapshotData	   		OBJECT IDENTIFIER ::= { prvtStatisticsHistoryObjects 2 }



-- 
-- ***********************************************************
-- 
--                 STATISTICS HISTORY CONFIG
-- 
-- *********************************************************** 
--
prvtStatHistAdminStatus OBJECT-TYPE
SYNTAX INTEGER {
enable(1),
disable(2)
}
MAX-ACCESS read-write
STATUS current
DESCRIPTION
"Enables or disables statistics history feature globally. 
The default value is disabled.
"
DEFVAL { disable }
::=  { prvtStatisticsHistoryCfg 1 }

prvtStatHistGetInterval OBJECT-TYPE
SYNTAX INTEGER {
interval15min(1),
interval30min(2),
interval60min(3)
}
UNITS       "minutes"   
MAX-ACCESS read-write
STATUS current
DESCRIPTION
"Configures statistics gathering interval.
If prvtStatHistAdminStatus object is disabled, then this object's value is irrelevant.
The default value is 15 minutes.
"
DEFVAL { interval15min }
::=  { prvtStatisticsHistoryCfg 2 } 



prvtStatHistWriteInterval OBJECT-TYPE
SYNTAX INTEGER {
interval1h(1),
interval6h(2),
interval12h(3),
interval24h(4)
}
UNITS       "hours"   
MAX-ACCESS read-write
STATUS current
DESCRIPTION
"Configures time when statistics history should be dumped to configured statistics file.
If prvtStatHistAdminStatus object is disabled, then this object's value is irrelevant. 
The default value is 1 hour.
"
DEFVAL { interval1h }
::=  { prvtStatisticsHistoryCfg 3 }

prvtStatHistPath OBJECT-TYPE
SYNTAX DisplayString (SIZE (0..40))
MAX-ACCESS read-write
STATUS current
DESCRIPTION
"Configures directory where statistics history files should be stored.
If prvtStatHistAdminStatus object is disabled, then this object's value is irrelevant. 
The default value is '/var/stats'.
"
DEFVAL { "/var/stats" }
::= { prvtStatisticsHistoryCfg 4 }     


--
-- prvtStatisticsHistoryInterfaceCfgTable: statistics history configuration on a per port basis
--

prvtStatisticsHistoryIntCfgTable   OBJECT-TYPE
    SYNTAX      SEQUENCE OF PrvtStatisticsHistoryIntCfgEntry
    MAX-ACCESS  not-accessible
    STATUS      current
    DESCRIPTION
            "The table that controls statistics history configuration on individual
            ports."
    ::= { prvtStatisticsHistoryCfg 5 }

prvtStatisticsHistoryIntCfgEntry   OBJECT-TYPE
    SYNTAX      PrvtStatisticsHistoryIntCfgEntry
    MAX-ACCESS  not-accessible
    STATUS      current
    DESCRIPTION
            "Statistics history configuration information for a particular port."
     INDEX { ifIndex }
    ::= { prvtStatisticsHistoryIntCfgTable 1 }

PrvtStatisticsHistoryIntCfgEntry ::= SEQUENCE {
      prvtStatHistIntAdminStatus        INTEGER
      } 

prvtStatHistIntAdminStatus   OBJECT-TYPE
SYNTAX INTEGER
{
enable (1),
disable (2)
}
MAX-ACCESS read-write
STATUS current
DESCRIPTION
" Enables or disables statistics-history feature per interface." 
::= { prvtStatisticsHistoryIntCfgEntry 1 }      


--
--  *********************************************************** 
--
--                   STATISTICS HISTORY DAILY SNAPSHOT DATA
--
--  *********************************************************** 
--

prvtStatHistDailySnapshotAdminStatus OBJECT-TYPE
SYNTAX INTEGER {
enable(1),
disable(2)
}   
MAX-ACCESS read-only
STATUS current
DESCRIPTION
"Shows if statistics history feature is globally enabled or disabled.
If prvtStatHistAdminStatus object is disabled, then this object's value is irrelevant.
Copied from configuration database when daily snapshot is created."
::=  { prvtStatHistDailySnapshotData 1 }

prvtStatHistDailySnapshotGetInterval OBJECT-TYPE
SYNTAX INTEGER {
interval15min(1),
interval30min(2),
interval60min(3)
}
UNITS       "minutes"   
MAX-ACCESS read-only
STATUS current
DESCRIPTION
"Statistics gathering interval.
If prvtStatHistAdminStatus object is disabled, then this object's value is irrelevant. 
Copied from configuration database when daily snapshot is created."
::=  { prvtStatHistDailySnapshotData 2 } 



prvtStatHistDailySnapshotWriteInterval OBJECT-TYPE
SYNTAX INTEGER {
interval1h(1),
interval6h(2),
interval12h(3),
interval24h(4)
}
UNITS       "hours"   
MAX-ACCESS read-only
STATUS current
DESCRIPTION
"Time when statistics history should be dumped to configured statistics file.
If prvtStatHistAdminStatus object is disabled, then this object's value is irrelevant.
Copied from configuration database when daily snapshot is created. 
"
DEFVAL { interval1h }
::=  { prvtStatHistDailySnapshotData 3 }

prvtStatHistDailySnapshotPath OBJECT-TYPE
SYNTAX DisplayString(SIZE (0..40))
MAX-ACCESS read-only
STATUS current
DESCRIPTION
"Directory where statistics history files should be stored.
If prvtStatHistAdminStatus object is disabled, then this object's value is irrelevant.   
Copied from configuration database when daily snapshot is created.
Format: [device/]path. 
"
::= { prvtStatHistDailySnapshotData 4 }     


--
-- prvtStatisticsHistoryDataTable: statistics history information
--

prvtStatisticsHistoryDataTable   OBJECT-TYPE
    SYNTAX      SEQUENCE OF PrvtStatisticsHistoryDataEntry
    MAX-ACCESS  not-accessible
    STATUS      current
    DESCRIPTION
            "The table that show statistics history information."
    ::= { prvtStatHistDailySnapshotData 5 }

prvtStatisticsHistoryDataEntry   OBJECT-TYPE
    SYNTAX      PrvtStatisticsHistoryDataEntry
    MAX-ACCESS  not-accessible
    STATUS      current
    DESCRIPTION
            "Statistics history information."
     INDEX {ifIndex, 
     		prvtStatHistInterval}
    ::= { prvtStatisticsHistoryDataTable 1 }

PrvtStatisticsHistoryDataEntry ::= SEQUENCE {              
		    prvtStatHistInterval											Unsigned32,
     		prvtStatHistLast5secInPkts										Counter32,
			prvtStatHistLast1minInPkts										Counter32,
			prvtStatHistLast5minInPkts										Counter32,
			prvtStatHistLast5secOutPkts										Counter32, 
			prvtStatHistLast1minOutPkts										Counter32,
			prvtStatHistLast5minOutPkts										Counter32, 			
			prvtStatHistLast5secInBps										Counter64,
			prvtStatHistLast1minInBps										Counter64,       			
			prvtStatHistLast5minInBps										Counter64,
			prvtStatHistLast5secOutBps										Counter64,
			prvtStatHistLast1minOutBps										Counter64,
			prvtStatHistLast5minOutBps										Counter64,
			prvtStatHistEtherStatsDropEvents	    						Counter32,			
    		prvtStatHistEtherStatsPkts										Counter32, 
			prvtStatHistEtherStatsBroadcastPkts								Counter32,
			prvtStatHistEtherStatsMulticastPkts								Counter32, 
			prvtStatHistEtherStatsCRCAlignErrors							Counter32,   			
			prvtStatHistEtherStatsUndersizePkts								Counter32,
			prvtStatHistEtherStatsOversizePkts								Counter32,
			prvtStatHistEtherStatsFragments									Counter32,
			prvtStatHistEtherStatsJabbers									Counter32, 
			prvtStatHistEtherStatsCollisions								Counter32,    
			prvtStatHistEtherStatsDroppedFrames								Counter32, 
			prvtStatHistEtherStatsHighCapacityOverflowPkts					Counter32, 
			prvtStatHistEtherStatsHighCapacityOverflowOctets				Counter32,  
			prvtStatHistEtherStatsHighCapacityPkts							Counter64,
			prvtStatHistEtherStatsHighCapacityOctets						Counter64,  
			prvtStatHistEtherStatsHighCapacityPkts64Octets					Counter64, 
			prvtStatHistEtherStatsHighCapacityPkts65to127Octets				Counter64,
			prvtStatHistEtherStatsHighCapacityPkts128to255Octets			Counter64,
			prvtStatHistEtherStatsHighCapacityPkts256to511Octets			Counter64, 
			prvtStatHistEtherStatsHighCapacityPkts512to1023Octets			Counter64, 
			prvtStatHistEtherStatsHighCapacityPkts1024to1518Octets			Counter64,   
			prvtStatHistDot3StatsAlignmentErrors							Counter32, 
    		prvtStatHistDot3StatsFCSErrors									Counter32, 
    		prvtStatHistDot3StatsSingleCollisionFrames 						Counter32,
    		prvtStatHistDot3StatsMultipleCollisionFrames 					Counter32,
    		prvtStatHistDot3StatsSQETestErrors								Counter32, 
    		prvtStatHistDot3StatsDeferredTransmissions						Counter32,
    		prvtStatHistDot3StatsLateCollisions								Counter32, 
    		prvtStatHistDot3StatsExcessiveCollisions						Counter32,
    		prvtStatHistDot3StatsInternalMacTransmitErrors					Counter32,
    		prvtStatHistDot3StatsCarrierSenseErrors							Counter32, 
    		prvtStatHistDot3StatsFrameTooLongs 								Counter32, 
    		prvtStatHistDot3StatsInternalMacReceiveErrors					Counter32,
    		prvtStatHistIfInDiscards										Counter32,  
			prvtStatHistIfInErrors											Counter32,
			prvtStatHistIfInUnknownProtos									Counter32, 
			prvtStatHistIfOutDiscards										Counter32,
			prvtStatHistIfOutErrors											Counter32,
    		prvtStatHistIfHCInOctets										Counter64, 
    		prvtStatHistIfHCInUcastPkts										Counter64,
    		prvtStatHistIfHCInMulticastPkts									Counter64,
    		prvtStatHistIfHCInBroadcastPkts									Counter64, 
    		prvtStatHistIfHCOutOctets										Counter64, 
    		prvtStatHistIfHCOutUcastPkts 									Counter64,
    		prvtStatHistIfHCOutMulticastPkts 								Counter64,
    		prvtStatHistIfHCOutBroadcastPkts								Counter64,
      		prvtStatHistValidInterval        								TruthValue
      } 
 
prvtStatHistInterval  OBJECT-TYPE
SYNTAX Unsigned32
MAX-ACCESS not-accessible
STATUS current
DESCRIPTION
"Number of statistics gathering interval.
All valid and invalid gathering intervals are supported. Check prvtStatHistValidInterval if true/false."
::= { prvtStatisticsHistoryDataEntry 1 }

prvtStatHistLast5secInPkts  OBJECT-TYPE
SYNTAX Counter32
MAX-ACCESS read-only
STATUS current
DESCRIPTION
"Value of last5secInPkts counter."
::= { prvtStatisticsHistoryDataEntry 2 } 

prvtStatHistLast1minInPkts  OBJECT-TYPE
SYNTAX Counter32
MAX-ACCESS read-only
STATUS current
DESCRIPTION
"Value of last1minInPkts counter."
::= { prvtStatisticsHistoryDataEntry 3 } 

prvtStatHistLast5minInPkts  OBJECT-TYPE
SYNTAX Counter32
MAX-ACCESS read-only
STATUS current
DESCRIPTION
"Value of last5minInPkts counter."
::= { prvtStatisticsHistoryDataEntry 4 }


prvtStatHistLast5secOutPkts  OBJECT-TYPE
SYNTAX Counter32
MAX-ACCESS read-only
STATUS current
DESCRIPTION
"Value of last5secOutPkts counter."
::= { prvtStatisticsHistoryDataEntry 5 }


prvtStatHistLast1minOutPkts  OBJECT-TYPE
SYNTAX Counter32
MAX-ACCESS read-only
STATUS current
DESCRIPTION
"Value of last1minOutPkts counter."
::= { prvtStatisticsHistoryDataEntry 6 }
  

prvtStatHistLast5minOutPkts  OBJECT-TYPE
SYNTAX Counter32
MAX-ACCESS read-only
STATUS current
DESCRIPTION
"Value of last5minOutPkts counter."
::= { prvtStatisticsHistoryDataEntry 7 }

prvtStatHistLast5secInBps  OBJECT-TYPE
SYNTAX Counter64
MAX-ACCESS read-only
STATUS current
DESCRIPTION
"Value of last5secInBps counter."
::= { prvtStatisticsHistoryDataEntry 8 }

prvtStatHistLast1minInBps  OBJECT-TYPE
SYNTAX Counter64
MAX-ACCESS read-only
STATUS current
DESCRIPTION
"Value of last1minInBps counter."
::= { prvtStatisticsHistoryDataEntry 9 }
  
prvtStatHistLast5minInBps  OBJECT-TYPE
SYNTAX Counter64
MAX-ACCESS read-only
STATUS current
DESCRIPTION
"Value of last5minInBps counter."
::= { prvtStatisticsHistoryDataEntry 10 }
  
prvtStatHistLast5secOutBps  OBJECT-TYPE
SYNTAX Counter64
MAX-ACCESS read-only
STATUS current
DESCRIPTION
"Value of last5secOutBps counter."
::= { prvtStatisticsHistoryDataEntry 11 }
              
prvtStatHistLast1minOutBps  OBJECT-TYPE
SYNTAX Counter64
MAX-ACCESS read-only
STATUS current
DESCRIPTION
"Value of last1minOutBps counter."
::= { prvtStatisticsHistoryDataEntry 12 }              
   
prvtStatHistLast5minOutBps  OBJECT-TYPE
SYNTAX Counter64
MAX-ACCESS read-only
STATUS current
DESCRIPTION
"Value of last5minOutBps counter."
::= { prvtStatisticsHistoryDataEntry 13 } 
       
       
prvtStatHistEtherStatsDropEvents  OBJECT-TYPE
SYNTAX Counter32
MAX-ACCESS read-only
STATUS current
DESCRIPTION
"Value of etherStatsDropEvents counter."
::= { prvtStatisticsHistoryDataEntry 14 }
  
  
prvtStatHistEtherStatsPkts  OBJECT-TYPE
SYNTAX Counter32
MAX-ACCESS read-only
STATUS current
DESCRIPTION
"Value of etherStatsPkts counter."
::= { prvtStatisticsHistoryDataEntry 15 }   

prvtStatHistEtherStatsBroadcastPkts  OBJECT-TYPE
SYNTAX Counter32
MAX-ACCESS read-only
STATUS current
DESCRIPTION
"Value of etherStatsBroadcastPkts counter."
::= { prvtStatisticsHistoryDataEntry 16 } 

prvtStatHistEtherStatsMulticastPkts  OBJECT-TYPE
SYNTAX Counter32
MAX-ACCESS read-only
STATUS current
DESCRIPTION
"Value of etherStatsMulticastPkts counter."
::= { prvtStatisticsHistoryDataEntry 17 }

prvtStatHistEtherStatsCRCAlignErrors  OBJECT-TYPE
SYNTAX Counter32
MAX-ACCESS read-only
STATUS current
DESCRIPTION
"Value of etherStatsCRCAlignErrors counter."
::= { prvtStatisticsHistoryDataEntry 18 } 

prvtStatHistEtherStatsUndersizePkts  OBJECT-TYPE
SYNTAX Counter32
MAX-ACCESS read-only
STATUS current
DESCRIPTION
"Value of etherStatsUndersizePkts counter."
::= { prvtStatisticsHistoryDataEntry 19 } 

prvtStatHistEtherStatsOversizePkts  OBJECT-TYPE
SYNTAX Counter32
MAX-ACCESS read-only
STATUS current
DESCRIPTION
"Value of etherStatsOversizePkts counter."
::= { prvtStatisticsHistoryDataEntry 20 } 

prvtStatHistEtherStatsFragments  OBJECT-TYPE
SYNTAX Counter32
MAX-ACCESS read-only
STATUS current
DESCRIPTION
"Value of etherStatsFragments counter."
::= { prvtStatisticsHistoryDataEntry 21 } 

prvtStatHistEtherStatsJabbers  OBJECT-TYPE
SYNTAX Counter32
MAX-ACCESS read-only
STATUS current
DESCRIPTION
"Value of etherStatsJabbers counter."
::= { prvtStatisticsHistoryDataEntry 22 } 

prvtStatHistEtherStatsCollisions  OBJECT-TYPE
SYNTAX Counter32
MAX-ACCESS read-only
STATUS current
DESCRIPTION
"Value of etherStatsCollisions counter."
::= { prvtStatisticsHistoryDataEntry 23 } 

prvtStatHistEtherStatsDroppedFrames  OBJECT-TYPE
SYNTAX Counter32
MAX-ACCESS read-only
STATUS current
DESCRIPTION
"Value of etherStatsDroppedFrames counter."
::= { prvtStatisticsHistoryDataEntry 24 } 

prvtStatHistEtherStatsHighCapacityOverflowPkts  OBJECT-TYPE
SYNTAX Counter32
MAX-ACCESS read-only
STATUS current
DESCRIPTION
"Value of etherStatsHighCapacityOverflowPkts counter."
::= { prvtStatisticsHistoryDataEntry 25 } 

prvtStatHistEtherStatsHighCapacityOverflowOctets  OBJECT-TYPE
SYNTAX Counter32
MAX-ACCESS read-only
STATUS current
DESCRIPTION
"Value of etherStatsHighCapacityOverflowOctets counter."
::= { prvtStatisticsHistoryDataEntry 26 } 

prvtStatHistEtherStatsHighCapacityPkts  OBJECT-TYPE
SYNTAX Counter64
MAX-ACCESS read-only
STATUS current
DESCRIPTION
"Value of etherStatsHighCapacityPkts counter."
::= { prvtStatisticsHistoryDataEntry 27 } 

prvtStatHistEtherStatsHighCapacityOctets  OBJECT-TYPE
SYNTAX Counter64
MAX-ACCESS read-only
STATUS current
DESCRIPTION
"Value of etherStatsHighCapacityOctets counter."
::= { prvtStatisticsHistoryDataEntry 28 } 

prvtStatHistEtherStatsHighCapacityPkts64Octets  OBJECT-TYPE
SYNTAX Counter64
MAX-ACCESS read-only
STATUS current
DESCRIPTION
"Value of etherStatsHighCapacityPkts64Octets counter."
::= { prvtStatisticsHistoryDataEntry 29 }

prvtStatHistEtherStatsHighCapacityPkts65to127Octets  OBJECT-TYPE
SYNTAX Counter64
MAX-ACCESS read-only
STATUS current
DESCRIPTION
"Value of etherStatsHighCapacityPkts65to127Octets counter."
::= { prvtStatisticsHistoryDataEntry 30 } 

prvtStatHistEtherStatsHighCapacityPkts128to255Octets  OBJECT-TYPE
SYNTAX Counter64
MAX-ACCESS read-only
STATUS current
DESCRIPTION
"Value of etherStatsHighCapacityPkts128to255Octets counter."
::= { prvtStatisticsHistoryDataEntry 31 } 

prvtStatHistEtherStatsHighCapacityPkts256to511Octets  OBJECT-TYPE
SYNTAX Counter64
MAX-ACCESS read-only
STATUS current
DESCRIPTION
"Value of etherStatsHighCapacityPkts256to511Octets counter."
::= { prvtStatisticsHistoryDataEntry 32 } 

prvtStatHistEtherStatsHighCapacityPkts512to1023Octets  OBJECT-TYPE
SYNTAX Counter64
MAX-ACCESS read-only
STATUS current
DESCRIPTION
"Value of etherStatsHighCapacityPkts512to1023Octets counter."
::= { prvtStatisticsHistoryDataEntry 33 }

prvtStatHistEtherStatsHighCapacityPkts1024to1518Octets  OBJECT-TYPE
SYNTAX Counter64
MAX-ACCESS read-only
STATUS current
DESCRIPTION
"Value of etherStatsHighCapacityPkts1024to1518Octets counter."
::= { prvtStatisticsHistoryDataEntry 34 }
   
prvtStatHistDot3StatsAlignmentErrors  OBJECT-TYPE
SYNTAX Counter32
MAX-ACCESS read-only
STATUS current
DESCRIPTION
"Value of dot3StatsAlignmentErrors counter."
::= { prvtStatisticsHistoryDataEntry 35 } 

prvtStatHistDot3StatsFCSErrors  OBJECT-TYPE
SYNTAX Counter32
MAX-ACCESS read-only
STATUS current
DESCRIPTION
"Value of dot3StatsFCSErrors counter."
::= { prvtStatisticsHistoryDataEntry 36 } 

prvtStatHistDot3StatsSingleCollisionFrames  OBJECT-TYPE
SYNTAX Counter32
MAX-ACCESS read-only
STATUS current
DESCRIPTION
"Value of dot3StatsSingleCollisionFrames counter."
::= { prvtStatisticsHistoryDataEntry 37 } 

prvtStatHistDot3StatsMultipleCollisionFrames  OBJECT-TYPE
SYNTAX Counter32
MAX-ACCESS read-only
STATUS current
DESCRIPTION
"Value of dot3StatsMultipleCollisionFrames counter."
::= { prvtStatisticsHistoryDataEntry 38 } 

prvtStatHistDot3StatsSQETestErrors  OBJECT-TYPE
SYNTAX Counter32
MAX-ACCESS read-only
STATUS current
DESCRIPTION
"Value of dot3StatsSQETestErrors counter."
::= { prvtStatisticsHistoryDataEntry 39 } 

prvtStatHistDot3StatsDeferredTransmissions  OBJECT-TYPE
SYNTAX Counter32
MAX-ACCESS read-only
STATUS current
DESCRIPTION
"Value of dot3StatsDeferredTransmissions counter."
::= { prvtStatisticsHistoryDataEntry 40 }

prvtStatHistDot3StatsLateCollisions  OBJECT-TYPE
SYNTAX Counter32
MAX-ACCESS read-only
STATUS current
DESCRIPTION
"Value of dot3StatsLateCollisions counter."
::= { prvtStatisticsHistoryDataEntry 41 } 

prvtStatHistDot3StatsExcessiveCollisions  OBJECT-TYPE
SYNTAX Counter32
MAX-ACCESS read-only
STATUS current
DESCRIPTION
"Value of dot3StatsExcessiveCollisions counter."
::= { prvtStatisticsHistoryDataEntry 42 } 

prvtStatHistDot3StatsInternalMacTransmitErrors  OBJECT-TYPE
SYNTAX Counter32
MAX-ACCESS read-only
STATUS current
DESCRIPTION
"Value of dot3StatsInternalMacTransmitErrors counter."
::= { prvtStatisticsHistoryDataEntry 43 }

prvtStatHistDot3StatsCarrierSenseErrors  OBJECT-TYPE
SYNTAX Counter32
MAX-ACCESS read-only
STATUS current
DESCRIPTION
"Value of dot3StatsCarrierSenseErrors counter."
::= { prvtStatisticsHistoryDataEntry 44 }

prvtStatHistDot3StatsFrameTooLongs  OBJECT-TYPE
SYNTAX Counter32
MAX-ACCESS read-only
STATUS current
DESCRIPTION
"Value of dot3StatsFrameTooLongs counter."
::= { prvtStatisticsHistoryDataEntry 45 } 

prvtStatHistDot3StatsInternalMacReceiveErrors  OBJECT-TYPE
SYNTAX Counter32
MAX-ACCESS read-only
STATUS current
DESCRIPTION
"Value of dot3StatsInternalMacReceiveErrors counter."
::= { prvtStatisticsHistoryDataEntry 46 } 

prvtStatHistIfInDiscards  OBJECT-TYPE
SYNTAX Counter32
MAX-ACCESS read-only
STATUS current
DESCRIPTION
"Value of ifInDiscards counter."
::= { prvtStatisticsHistoryDataEntry 47 } 

prvtStatHistIfInErrors  OBJECT-TYPE
SYNTAX Counter32
MAX-ACCESS read-only
STATUS current
DESCRIPTION
"Value of ifInErrors counter."
::= { prvtStatisticsHistoryDataEntry 48 } 

prvtStatHistIfInUnknownProtos  OBJECT-TYPE
SYNTAX Counter32
MAX-ACCESS read-only
STATUS current
DESCRIPTION
"Value of ifInUnknownProtos counter."
::= { prvtStatisticsHistoryDataEntry 49 }


prvtStatHistIfOutDiscards  OBJECT-TYPE
SYNTAX Counter32
MAX-ACCESS read-only
STATUS current
DESCRIPTION
"Value of ifOutDiscards counter."
::= { prvtStatisticsHistoryDataEntry 50 } 

prvtStatHistIfOutErrors  OBJECT-TYPE
SYNTAX Counter32
MAX-ACCESS read-only
STATUS current
DESCRIPTION
"Value of dot3StatsDeferredTransmissions counter."
::= { prvtStatisticsHistoryDataEntry 51 } 

prvtStatHistIfHCInOctets  OBJECT-TYPE
SYNTAX Counter64
MAX-ACCESS read-only
STATUS current
DESCRIPTION
"Value of ifHCInOctets counter."
::= { prvtStatisticsHistoryDataEntry 52 }

prvtStatHistIfHCInUcastPkts  OBJECT-TYPE
SYNTAX Counter64
MAX-ACCESS read-only
STATUS current
DESCRIPTION
"Value of ifHCInUcastPkts counter."
::= { prvtStatisticsHistoryDataEntry 53 } 

prvtStatHistIfHCInMulticastPkts  OBJECT-TYPE
SYNTAX Counter64
MAX-ACCESS read-only
STATUS current
DESCRIPTION
"Value of ifHCInMulticastPkts counter."
::= { prvtStatisticsHistoryDataEntry 54 } 

prvtStatHistIfHCInBroadcastPkts  OBJECT-TYPE
SYNTAX Counter64
MAX-ACCESS read-only
STATUS current
DESCRIPTION
"Value of prvtStatHistIfHCInBroadastPkts counter."
::= { prvtStatisticsHistoryDataEntry 55 }

prvtStatHistIfHCOutOctets  OBJECT-TYPE
SYNTAX Counter64
MAX-ACCESS read-only
STATUS current
DESCRIPTION
"Value of ifHCOutOctets counter."
::= { prvtStatisticsHistoryDataEntry 56 } 

prvtStatHistIfHCOutUcastPkts  OBJECT-TYPE
SYNTAX Counter64
MAX-ACCESS read-only
STATUS current
DESCRIPTION
"Value of ifHCOutUcastPkts counter."
::= { prvtStatisticsHistoryDataEntry 57 } 

prvtStatHistIfHCOutMulticastPkts  OBJECT-TYPE
SYNTAX Counter64
MAX-ACCESS read-only
STATUS current
DESCRIPTION
"Value of ifHCOutMulticastPkts counter."
::= { prvtStatisticsHistoryDataEntry 58 } 

prvtStatHistIfHCOutBroadcastPkts  OBJECT-TYPE
SYNTAX Counter64
MAX-ACCESS read-only
STATUS current
DESCRIPTION
"Value of ifHCOutBroadcastPkts counter."
::= { prvtStatisticsHistoryDataEntry 59 }

prvtStatHistValidInterval OBJECT-TYPE
SYNTAX TruthValue
MAX-ACCESS read-only
STATUS current
DESCRIPTION
"A boolean showing if the interval is valid."
::= { prvtStatisticsHistoryDataEntry 60 }


prvtStatisticsHistoryCompliances OBJECT IDENTIFIER ::= { prvtStatisticsHistoryConformance 1 }
prvtStatisticsHistoryGroups      OBJECT IDENTIFIER ::= { prvtStatisticsHistoryConformance 2 }

-- ******************************************************************
-- Units of conformance
-- ******************************************************************

prvtStatisticsHistoryIntCfgGroup OBJECT-GROUP
    OBJECTS {
	prvtStatHistIntAdminStatus
    }
    STATUS      current
    DESCRIPTION
       "Objects for the interface configuration group."
    ::= { prvtStatisticsHistoryGroups 1 }

prvtStatisticsHistoryDataGroup OBJECT-GROUP
    OBJECTS {
		prvtStatHistLast5secInPkts,
			prvtStatHistLast1minInPkts,
			prvtStatHistLast5minInPkts,
			prvtStatHistLast5secOutPkts,
			prvtStatHistLast1minOutPkts,
			prvtStatHistLast5minOutPkts,
			prvtStatHistLast5secInBps,
			prvtStatHistLast1minInBps,
			prvtStatHistLast5minInBps,
			prvtStatHistLast5secOutBps,
			prvtStatHistLast1minOutBps,
			prvtStatHistLast5minOutBps,
			prvtStatHistEtherStatsDropEvents,
    		prvtStatHistEtherStatsPkts,
			prvtStatHistEtherStatsBroadcastPkts,
			prvtStatHistEtherStatsMulticastPkts,
			prvtStatHistEtherStatsCRCAlignErrors,
			prvtStatHistEtherStatsUndersizePkts,
			prvtStatHistEtherStatsOversizePkts,
			prvtStatHistEtherStatsFragments,
			prvtStatHistEtherStatsJabbers,
			prvtStatHistEtherStatsCollisions,
			prvtStatHistEtherStatsDroppedFrames,
			prvtStatHistEtherStatsHighCapacityOverflowPkts,
			prvtStatHistEtherStatsHighCapacityOverflowOctets,
			prvtStatHistEtherStatsHighCapacityPkts,
			prvtStatHistEtherStatsHighCapacityOctets,
			prvtStatHistEtherStatsHighCapacityPkts64Octets,
			prvtStatHistEtherStatsHighCapacityPkts65to127Octets,
			prvtStatHistEtherStatsHighCapacityPkts128to255Octets,
			prvtStatHistEtherStatsHighCapacityPkts256to511Octets,
			prvtStatHistEtherStatsHighCapacityPkts512to1023Octets,
			prvtStatHistEtherStatsHighCapacityPkts1024to1518Octets,
			prvtStatHistDot3StatsAlignmentErrors,
    		prvtStatHistDot3StatsFCSErrors,
    		prvtStatHistDot3StatsSingleCollisionFrames,
    		prvtStatHistDot3StatsMultipleCollisionFrames,
    		prvtStatHistDot3StatsSQETestErrors,
    		prvtStatHistDot3StatsDeferredTransmissions,
    		prvtStatHistDot3StatsLateCollisions,
    		prvtStatHistDot3StatsExcessiveCollisions,
    		prvtStatHistDot3StatsInternalMacTransmitErrors,
    		prvtStatHistDot3StatsCarrierSenseErrors,
    		prvtStatHistDot3StatsFrameTooLongs,
    		prvtStatHistDot3StatsInternalMacReceiveErrors,
    		prvtStatHistIfInDiscards,
			prvtStatHistIfInErrors,
			prvtStatHistIfInUnknownProtos,
			prvtStatHistIfOutDiscards,
			prvtStatHistIfOutErrors,
    		prvtStatHistIfHCInOctets,
    		prvtStatHistIfHCInUcastPkts,
    		prvtStatHistIfHCInMulticastPkts,
    		prvtStatHistIfHCInBroadcastPkts,
    		prvtStatHistIfHCOutOctets,
    		prvtStatHistIfHCOutUcastPkts,
    		prvtStatHistIfHCOutMulticastPkts,
    		prvtStatHistIfHCOutBroadcastPkts,
      		prvtStatHistValidInterval
    }
    STATUS      current
    DESCRIPTION
       "Objects for the Statistics History Data group."
    ::= { prvtStatisticsHistoryGroups 2 }
    
prvtStatisticsHistoryCfgGroup OBJECT-GROUP
    OBJECTS {
	prvtStatHistAdminStatus,
	prvtStatHistGetInterval,
	prvtStatHistWriteInterval,
	prvtStatHistPath
    }
    STATUS      current
    DESCRIPTION
       "Objects for the global configuration group."
    ::= { prvtStatisticsHistoryGroups 3 }

prvtStatHistDailySnapshotDataGroup OBJECT-GROUP
    OBJECTS {
	prvtStatHistDailySnapshotAdminStatus,
	prvtStatHistDailySnapshotGetInterval,
	prvtStatHistDailySnapshotWriteInterval,
	prvtStatHistDailySnapshotPath
    }
    STATUS      current
    DESCRIPTION
       "Objects for the global configuration group."
    ::= { prvtStatisticsHistoryGroups 4 }

prvtStatisticsHistoryCompliance MODULE-COMPLIANCE
    STATUS      current
    DESCRIPTION
       "The compliance statement for support of the statistics history MIB module."
    MODULE
        MANDATORY-GROUPS {
            prvtStatisticsHistoryIntCfgGroup,
	    prvtStatisticsHistoryDataGroup,
	    prvtStatisticsHistoryCfgGroup,
	    prvtStatHistDailySnapshotDataGroup
            }

    ::= { prvtStatisticsHistoryCompliances 1 }



END
