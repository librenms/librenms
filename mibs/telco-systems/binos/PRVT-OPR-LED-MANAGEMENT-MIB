-- *********************************************************************
-- *********************************************************************
-- ** Filename: PRVT-OPR-LED-MANAGEMENT-MIB
-- ** Project: T - Ethernet and Fast Ethernet IP Switches.
-- ** Purpose: Private MIB
-- *********************************************************************
-- (c) Copyright, 2001, BATM Advanced Communications. All rights reserved.
-- WARNING:
--
-- BY UTILIZING THIS FILE, YOU AGREE TO THE FOLLOWING:
--
-- This file is the property of BATM Advanced Communications.
-- BATM Advanced Communications retains all title and
-- ownership in the Specification, including any revisions.

-- BATM Advanced Communications grants all interested parties a non-exclusive
-- license to use and distribute an unmodified copy of this
-- Specification in connection with management of BATM Advanced Communications
-- and Telco Systems products, and without fee, provided that the following
-- conditions are met:
-- 1. Redistributions of this specification must retain the above copyright
-- notice, this list of conditions and the following disclaimer.
-- 2. Redistributions in binary form must reproduce the above copyright
-- notice, this list of conditions and the following disclaimer in the
-- documentation and/or other materials provided with the distribution.
-- 3. The name of the BATM Advanced Communications MAY NOT be used to endorse
-- or promote products derived from this specification without specific prior written
-- permission.
--
-- EXCEPT AS RESTRICTED BY LAW, OR AS PROVIDED IN BATM'S LIMITED
-- WARRANTY, THE SPECIFICATIONS CONTAINED IN THIS FILE ARE
-- PROVIDED "AS IS" WITHOUT WARRANTY OF ANY KIND, EITHER EXPRESSED
-- OR IMPLIED, INCLUDING BUT NOT LIMITED TO, ANY IMPLIED WARRANTIES
-- OF MERCHANTABILITY OR FITNESS FOR A PARTICULAR PURPOSE.
-- IN NO EVENT SHALL BATM BE LIABLE FOR ANY DAMAGES WHATSOEVER
-- INCLUDING, WITHOUT LIMITATION, DAMAGES FOR LOSS OF BUSINESS
-- PROFITS, BUSINESS INTERRUPTION, LOSS OF BUSINESS INFORMATION OR
-- OTHER CONSEQUENTIAL DAMAGES ARISING OUT OF THE USE, OR INABILITY
-- TO USE, THE SPECIFICATION CONTAINED IN THIS FILE.
PRVT-OPR-LED-MANAGEMENT-MIB DEFINITIONS ::= BEGIN

IMPORTS
MODULE-IDENTITY,
OBJECT-TYPE
FROM SNMPv2-SMI

TEXTUAL-CONVENTION
FROM SNMPv2-TC

switch
FROM PRVT-SWITCH-MIB;

prvtOprLedMgmtMIB MODULE-IDENTITY
LAST-UPDATED "200607290000Z"
ORGANIZATION "BATM Advanced Communication"
CONTACT-INFO

"BATM/Telco Systems Support team
Email:
For North America: techsupport@telco.com
For North Europe: support@batm.de, info@batm.de
For the rest of the world: techsupport@telco.com"

DESCRIPTION
"Initial version. This MIB will provied a way to control
the status of the state OPR LED for certain switches"

-- Revision history.
REVISION "200607290000Z"
DESCRIPTION
"Initial revision history"

::= { switch 110 }

-- Textual Conventions

LedValues ::= TEXTUAL-CONVENTION
STATUS current
DESCRIPTION
"All possible led states"
SYNTAX INTEGER
{
green-stable (1),
green-blinking (2),
amber-stable (3),
amber-blinking (4),
red-stable (5),
red-blinking (6)
}

-- MIB objects

prvtOprLedMgmtObjects OBJECT IDENTIFIER ::= { prvtOprLedMgmtMIB 1 }
prvtOprLedMgmtNotifications OBJECT IDENTIFIER ::= { prvtOprLedMgmtMIB 2 }
prvtOprLedMgmtConformance OBJECT IDENTIFIER ::= { prvtOprLedMgmtMIB 3 }

prvtOprLedSatus OBJECT-TYPE
SYNTAX LedValues
MAX-ACCESS read-write
STATUS current
DESCRIPTION
"All possible led states. States red-stable and red-blinking
can not be set. States amber-stable and amber-blinking green-blinking can
be set only when the current state is green-stable. The object
has read-write access and its default value is green-stable"
DEFVAL { green-stable }
::= { prvtOprLedMgmtObjects 1 }

END
