-- *********************************************************************
-- *********************************************************************
-- ** Filename: PRVT-NETWORK-LOOPBACK-TEST-MIB
-- ** Project: Network Loopback Tester 
-- ** Purpose: Private MIB
-- *********************************************************************
-- (c) Copyright, 2001, BATM Advanced Communications. All rights reserved.
-- WARNING:
--
-- BY UTILIZING THIS FILE, YOU AGREE TO THE FOLLOWING:
--
-- This file is the property of BATM Advanced Communications.
-- BATM Advanced Communications retains all title and
-- ownership in the Specification, including any revisions.

-- BATM Advanced Communications grants all interested parties a non-exclusive
-- license to use and distribute an unmodified copy of this
-- Specification in connection with management of BATM Advanced Communications 
-- and Telco Systems products, and without fee, provided that the following
-- conditions are met:
-- 1. Redistributions of this specification must retain the above copyright
-- notice, this list of conditions and the following disclaimer.
-- 2. Redistributions in binary form must reproduce the above copyright
-- notice, this list of conditions and the following disclaimer in the
-- documentation and/or other materials provided with the distribution.
-- 3. The name of the BATM Advanced Communications MAY NOT be used to endorse
-- or promote products derived from this specification without specific prior written
-- permission.
--
-- EXCEPT AS RESTRICTED BY LAW, OR AS PROVIDED IN BATM'S LIMITED
-- WARRANTY, THE SPECIFICATIONS CONTAINED IN THIS FILE ARE
-- PROVIDED "AS IS" WITHOUT WARRANTY OF ANY KIND, EITHER EXPRESSED
-- OR IMPLIED, INCLUDING BUT NOT LIMITED TO, ANY IMPLIED WARRANTIES
-- OF MERCHANTABILITY OR FITNESS FOR A PARTICULAR PURPOSE.
-- IN NO EVENT SHALL BATM BE LIABLE FOR ANY DAMAGES WHATSOEVER
-- INCLUDING, WITHOUT LIMITATION, DAMAGES FOR LOSS OF BUSINESS
-- PROFITS, BUSINESS INTERRUPTION, LOSS OF BUSINESS INFORMATION OR
-- OTHER CONSEQUENTIAL DAMAGES ARISING OUT OF THE USE, OR INABILITY
-- TO USE, THE SPECIFICATION CONTAINED IN THIS FILE.
PRVT-MONITOR-SESSION-MIB DEFINITIONS ::= BEGIN

IMPORTS
MODULE-IDENTITY,
OBJECT-TYPE,
Integer32 
FROM SNMPv2-SMI         

    

MODULE-COMPLIANCE,
OBJECT-GROUP
FROM SNMPv2-CONF


                    -- [RFC2578]       

DisplayString,
TEXTUAL-CONVENTION
FROM SNMPv2-TC

PortList
FROM Q-BRIDGE-MIB

switch
FROM PRVT-SWITCH-MIB;   

-- The MONITOR SESSION MIB
prvtMonitorSessionMib MODULE-IDENTITY

LAST-UPDATED "201105230000Z"
ORGANIZATION "BATM Advanced Communication"
CONTACT-INFO
"BATM/Telco Systems Support team
Email: 
For North America: techsupport@telco.com
For North Europe: support@batm.de, info@batm.de
For the rest of the world: techsupport@telco.com"

DESCRIPTION
"This MIB contains manageable objects  for
encapsulating Switched Port Analyzer(SPAN) feature."
             
REVISION "201105230000Z"
DESCRIPTION
"Initial version."  

::= { switch 1000 }       


-- -------------------------------------------------------------
-- Textual Conventions
-- -------------------------------------------------------------
Direction ::= TEXTUAL-CONVENTION
    STATUS      current
    DESCRIPTION 
    "Monitor direction:
     tx- Transmit
     rx- Receive"
    SYNTAX INTEGER 
    {
    	rx(1),
    	tx(2)
    }
-- -------------------------------------------------------------
-- groups in the PRVT-MONITOR-SESSION MIB
-- -------------------------------------------------------------
prvtMonitorSessionNotification  	OBJECT IDENTIFIER  		::= { prvtMonitorSessionMib 0 } 
prvtMonitorSessionObjects      		OBJECT IDENTIFIER 		::= { prvtMonitorSessionMib 1 } 
prvtMonitorSessionConformance       OBJECT IDENTIFIER 		::= { prvtMonitorSessionMib 2 }
 
-- -------------------------------------------------------------
-- prvtMonitorSessionObjects group
-- -------------------------------------------------------------
prvtMonitorSessionTable OBJECT-TYPE
SYNTAX SEQUENCE OF PrvtMonitorSessionEntry
MAX-ACCESS not-accessible
STATUS current
DESCRIPTION
"This table contains object for enable and configure Enable Switched Port Analyzer."
::= { prvtMonitorSessionObjects	 1 }   

prvtMonitorSessionEntry  OBJECT-TYPE  
SYNTAX  PrvtMonitorSessionEntry
MAX-ACCESS not-accessible
STATUS current
DESCRIPTION
"An entry in the table will describe all parameteres of Switched Port Analyzer per each direction Rx or Tx "
INDEX { prvtMonitorSessionDirection } 
::= {prvtMonitorSessionTable 1}

PrvtMonitorSessionEntry ::=  SEQUENCE{  
prvtMonitorSessionDirection   	Direction,
prvtMonitorSessionSource 	  	PortList,
prvtMonitorSessionDestination   Integer32
}       

prvtMonitorSessionDirection  OBJECT-TYPE
SYNTAX  Direction  
MAX-ACCESS not-accessible
STATUS current
DESCRIPTION
"Direction recived/trasmitted of the monitored traffic."
::= {prvtMonitorSessionEntry 1}     

prvtMonitorSessionSource  OBJECT-TYPE
SYNTAX  PortList  
MAX-ACCESS read-write
STATUS current
DESCRIPTION
"Monitored source list representing the ports to be mirrored."
::= {prvtMonitorSessionEntry 2}  



prvtMonitorSessionDestination  OBJECT-TYPE
SYNTAX  Integer32   
MAX-ACCESS read-write
STATUS current
DESCRIPTION
"Analyzer port."
::= {prvtMonitorSessionEntry 3} 

prvtAnalyzerVLANTagTable OBJECT-TYPE
SYNTAX SEQUENCE OF PrvtAnalyzerVLANTagEntry
MAX-ACCESS not-accessible
STATUS current
DESCRIPTION
"This table contains object for enable and configure Remote Analyzer VLAN Tag"
::= { prvtMonitorSessionObjects	 2 }   

prvtAnalyzerVLANTagEntry  OBJECT-TYPE  
SYNTAX  PrvtAnalyzerVLANTagEntry
MAX-ACCESS not-accessible
STATUS current
DESCRIPTION
"An entry in the table will describe all parameteres of Remote Analyzer VLAN Tag per each direction Rx or Tx "
INDEX { prvtMonitorSessionDirection } 
::= {prvtAnalyzerVLANTagTable 1}    

PrvtAnalyzerVLANTagEntry ::= SEQUENCE{
prvtAnalyzerVLANTagEnable 	 INTEGER,
prvtAnalyzerVLANTagVID   	 Integer32, 
prvtAnalyzerVLANTagEtherType DisplayString,
prvtAnalyzerVLANTagCFI    	 INTEGER,
prvtAnalyzerVLANTagVPT	     INTEGER
}               

prvtAnalyzerVLANTagEnable OBJECT-TYPE
SYNTAX  INTEGER
{
enable(1),
disable(2)
}  
MAX-ACCESS read-write
STATUS current
DESCRIPTION
"Enable Remote Analyzer VLAN Tag."
::= {prvtAnalyzerVLANTagEntry 1}             

prvtAnalyzerVLANTagVID OBJECT-TYPE
SYNTAX  Integer32 (1..4095)
MAX-ACCESS read-write
STATUS current
DESCRIPTION
"The VLAN ID of the VLAN tag added to packet forwarded to Analyzer."
::= {prvtAnalyzerVLANTagEntry 2}   


prvtAnalyzerVLANTagEtherType OBJECT-TYPE
SYNTAX  DisplayString
MAX-ACCESS read-write
STATUS current
DESCRIPTION
"The Vlan ether type of the VLAN tag added to packet forwarded to Analyzer."
::= {prvtAnalyzerVLANTagEntry 3}
                                                    
                                                    
prvtAnalyzerVLANTagCFI OBJECT-TYPE
SYNTAX  INTEGER
{
clear(0),
set(1)
} 
MAX-ACCESS read-write
STATUS current
DESCRIPTION
"The CFI of the VLAN tag added to packet forwarded to Analyzer."
::= {prvtAnalyzerVLANTagEntry 4}         

prvtAnalyzerVLANTagVPT OBJECT-TYPE
SYNTAX  INTEGER
{
vpt-value0(0), 
vpt-value1(1), 
vpt-value2(2), 
vpt-value3(3), 
vpt-value4(4), 
vpt-value5(5), 
vpt-value6(6), 
vpt-value7(7), 
undefined(8) 
} 
MAX-ACCESS read-write
STATUS current
DESCRIPTION
"The VPT of the VLAN tag added to packet forwarded to Analyzer."
::= {prvtAnalyzerVLANTagEntry 5}

-- ----------------------------------------------------------------------------
-- Notifications
-- ----------------------------------------------------------------------------

-- ----------------------------------------------------------------------------
-- Conformance Information
-- ----------------------------------------------------------------------------
prvtMonitorSessionCompliances  OBJECT IDENTIFIER ::= {prvtMonitorSessionConformance 1}
prvtMonitorSessionGroups OBJECT IDENTIFIER ::= {prvtMonitorSessionConformance 2}

-- compliance statements   
prvtMonitorSessionCompliance MODULE-COMPLIANCE
STATUS current
DESCRIPTION
"The compliance statement for Switched Port Analyzer."
MODULE -- this module
MANDATORY-GROUPS {
prvtMonitorSessionMirroredGroup,
prvtMonitorSessionAnalyzerGroup
}      
::= {prvtMonitorSessionCompliances 1}  

prvtMonitorSessionMirroredGroup OBJECT-GROUP
OBJECTS { 
prvtMonitorSessionSource
} STATUS current
DESCRIPTION  
"The group of objects dedicated to mirrored source."
::= {prvtMonitorSessionGroups 1}  

prvtMonitorSessionAnalyzerGroup OBJECT-GROUP
OBJECTS { 
prvtMonitorSessionDestination,  
prvtAnalyzerVLANTagEnable
} STATUS current
DESCRIPTION  
"The group of objects dedicated to analyzer."
::= {prvtMonitorSessionGroups 2}

END
