-- *********************************************************************
-- **
-- ** BATM Advanced Communications.
-- **
-- *********************************************************************
-- ** Filename: PRVT-CR-LDP-MIB.mib
-- ** Project: T-Metro Switches.
-- ** Purpose: Private MIB
-- *********************************************************************
-- (c) Copyright, 2009, BATM Advanced Communications. All rights reserved.
-- WARNING:
--
-- BY UTILIZING THIS FILE, YOU AGREE TO THE FOLLOWING:
--
-- This file is the property of BATM Advanced Communications and contains
-- proprietary and confidential information. This file is made
-- available to authorized BATM customers on the express
-- condition that neither it, nor any of the information contained
-- therein, shall be disclosed to third parties or be used for any
-- purpose other than to replace, modify or upgrade firmware and/or
-- software components of BATM manufactured equipment within the
-- authorized customer's network, and that such transfer be
-- completed in accordance with the instructions provided by
-- BATM. Any other use is strictly prohibited.
--
-- EXCEPT AS RESTRICTED BY LAW, OR AS PROVIDED IN BATM'S LIMITED
-- WARRANTY, THE SOFTWARE PROGRAMS CONTAINED IN THIS FILE ARE
-- PROVIDED "AS IS" WITHOUT WARRANTY OF ANY KIND, EITHER EXPRESSED
-- OR IMPLIED, INCLUDING BUT NOT LIMITED TO, ANY IMPLIED WARRANTIES
-- OF MERCHANTABILITY OR FITNESS FOR A PARTICULAR PURPOSE.
--
-- IN NO EVENT SHALL BATM BE LIABLE FOR ANY DAMAGES WHATSOEVER
-- INCLUDING WITHOUT LIMITATION, DAMAGES FOR LOSS OF BUSINESS
-- PROFITS, BUSINESS INTERRUPTION, LOSS OF BUSINESS INFORMATION OR
-- OTHER CONSEQUENTIAL DAMAGES ARISING OUT OF THE USE, OR INABILITY
-- TO USE, THE SOFTWARE CONTAINED IN THIS FILE.
--
-- ----------------------------------------------------------------------------

PRVT-CR-LDP-MIB DEFINITIONS ::= BEGIN

IMPORTS
    mpls
        FROM PRVT-SWITCH-MIB
    MODULE-IDENTITY, OBJECT-TYPE, Unsigned32
        FROM SNMPv2-SMI
    RowStatus, TEXTUAL-CONVENTION
        FROM SNMPv2-TC;

prvtCrLdpMIB MODULE-IDENTITY
    LAST-UPDATED "200801010000Z"
    ORGANIZATION 
        "BATM Advanced Communication"
    CONTACT-INFO 
        "BATM/Telco Systems Support team
         Email:
         For North America: techsupport@telco.com
         For North Europe: support@batm.de, info@batm.de
         For the rest of the world: techsupport@telco.com"
    DESCRIPTION 
        "The MIB module for management of the PRVT-CR-LDP"
    REVISION    "200801010000Z"
    DESCRIPTION 
        "Initial"
    ::= { mpls 3 }


PrvtCrldpIndex ::= TEXTUAL-CONVENTION
    DISPLAY-HINT "d"
    STATUS      current
    DESCRIPTION 
        "A general purpose SNMP index into the prvtHafEntity table."
    SYNTAX      Unsigned32

prvtCrLdpObjects OBJECT IDENTIFIER
    ::= { prvtCrLdpMIB 1 }

prvtcrldpSigTable OBJECT-TYPE
    SYNTAX      SEQUENCE OF PrvtcrldpSigEntry
    MAX-ACCESS  not-accessible
    STATUS      current
    DESCRIPTION 
        "The table of active instances of PRVT-CR-LDP Signaling."
    ::= { prvtCrLdpObjects 1 }

prvtcrldpSigEntry OBJECT-TYPE
    SYNTAX      PrvtcrldpSigEntry
    MAX-ACCESS  not-accessible
    STATUS      current
    DESCRIPTION 
        "Each of these entries represents an instance of
         PRVT-CR-LDP Signaling running in the HAF. Some of these instances
         will be the primary, and others may be backups."
    INDEX       { prvtcrldpSigIndex }
    ::= { prvtcrldpSigTable 1 }

PrvtcrldpSigEntry ::= SEQUENCE {
    prvtcrldpSigIndex       PrvtCrldpIndex,
    prvtcrldpSigRowStatus   RowStatus
}

prvtcrldpSigIndex OBJECT-TYPE
    SYNTAX      PrvtCrldpIndex
    MAX-ACCESS  not-accessible
    STATUS      current
    DESCRIPTION 
        "The index of this prvtcrldpSigEntry. This is the
         HAF entity index passed on the product create
         parameters."
    ::= { prvtcrldpSigEntry 1 }

prvtcrldpSigRowStatus OBJECT-TYPE
    SYNTAX      RowStatus
    MAX-ACCESS  read-create
    STATUS      current
    DESCRIPTION 
        "Used to create and delete a PRVT-CR-LDP Signaling Table entry.
         When this object is set to 'active', only the
         prvtcrldpSigAdminStatus object in the row may be modified."
    ::= { prvtcrldpSigEntry 2 }

prvtcrldpPmTable OBJECT-TYPE
    SYNTAX      SEQUENCE OF PrvtcrldpPmEntry
    MAX-ACCESS  not-accessible
    STATUS      current
    DESCRIPTION 
        "The table of active instances of PRVT-CR-LDP Path Manager."
    ::= { prvtCrLdpObjects 2 }

prvtcrldpPmEntry OBJECT-TYPE
    SYNTAX      PrvtcrldpPmEntry
    MAX-ACCESS  not-accessible
    STATUS      current
    DESCRIPTION 
        "Each of these entries represents an instance of
         PRVT-CR-LDP Path Manager running in the HAF. Some of these instances
         will be the primary, and others may be backups."
    INDEX       { prvtcrldpPmIndex }
    ::= { prvtcrldpPmTable 1 }

PrvtcrldpPmEntry ::= SEQUENCE {
    prvtcrldpPmIndex        PrvtCrldpIndex,
    prvtcrldpPmRowStatus    RowStatus
}

prvtcrldpPmIndex OBJECT-TYPE
    SYNTAX      PrvtCrldpIndex
    MAX-ACCESS  not-accessible
    STATUS      current
    DESCRIPTION 
        "The index of this prvtcrldpPmEntry. This is the
         HAF entity index passed on the product create
         parameters."
    ::= { prvtcrldpPmEntry 1 }

prvtcrldpPmRowStatus OBJECT-TYPE
    SYNTAX      RowStatus
    MAX-ACCESS  read-create
    STATUS      current
    DESCRIPTION 
        "Used to create and delete a PRVT-CR-LDP Path Manager Table entry.
         When this object is set to 'active', only the
         prvtcrldpPmAdminStatus object in the row may be modified."
    ::= { prvtcrldpPmEntry 2 }

END -- end of module PRVT-CR-LDP-MIB.
