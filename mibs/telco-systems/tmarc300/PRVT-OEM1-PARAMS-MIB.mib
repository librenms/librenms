-- *********************************************************************
-- *********************************************************************
-- ** Filename: PRVT-OEM1-PARAMS-MIB
-- ** Project: T - Ethernet and Fast Ethernet IP Switches.
-- ** Purpose: Private MIB
-- *********************************************************************
-- (c) Copyright, 2001, BATM Advanced Communications. All rights reserved.
-- WARNING:
--
-- BY UTILIZING THIS FILE, YOU AGREE TO THE FOLLOWING:
--
-- This file is the property of BATM Advanced Communications.
-- BATM Advanced Communications retains all title and
-- ownership in the Specification, including any revisions.

-- BATM Advanced Communications grants all interested parties a non-exclusive
-- license to use and distribute an unmodified copy of this
-- Specification in connection with management of BATM Advanced Communications 
-- and Telco Systems products, and without fee, provided that the following
-- conditions are met:
-- 1. Redistributions of this specification must retain the above copyright
-- notice, this list of conditions and the following disclaimer.
-- 2. Redistributions in binary form must reproduce the above copyright
-- notice, this list of conditions and the following disclaimer in the
-- documentation and/or other materials provided with the distribution.
-- 3. The name of the BATM Advanced Communications MAY NOT be used to endorse
-- or promote products derived from this specification without specific prior written
-- permission.
--
-- EXCEPT AS RESTRICTED BY LAW, OR AS PROVIDED IN BATM'S LIMITED
-- WARRANTY, THE SPECIFICATIONS CONTAINED IN THIS FILE ARE
-- PROVIDED "AS IS" WITHOUT WARRANTY OF ANY KIND, EITHER EXPRESSED
-- OR IMPLIED, INCLUDING BUT NOT LIMITED TO, ANY IMPLIED WARRANTIES
-- OF MERCHANTABILITY OR FITNESS FOR A PARTICULAR PURPOSE.
-- IN NO EVENT SHALL BATM BE LIABLE FOR ANY DAMAGES WHATSOEVER
-- INCLUDING, WITHOUT LIMITATION, DAMAGES FOR LOSS OF BUSINESS
-- PROFITS, BUSINESS INTERRUPTION, LOSS OF BUSINESS INFORMATION OR
-- OTHER CONSEQUENTIAL DAMAGES ARISING OUT OF THE USE, OR INABILITY
-- TO USE, THE SPECIFICATION CONTAINED IN THIS FILE.
PRVT-OEM1-PARAMS-MIB DEFINITIONS ::= BEGIN

   IMPORTS
     MODULE-IDENTITY, OBJECT-TYPE FROM SNMPv2-SMI

     DisplayString FROM SNMPv2-TC

	 switch FROM PRVT-SWITCH-MIB; 
          
	prvtOem1ParamsMIB MODULE-IDENTITY
        LAST-UPDATED "200612270000Z"
        ORGANIZATION "BATM Advanced Communication"
        CONTACT-INFO   

        "BATM/Telco Systems Support team
				Email: 
				For North America: techsupport@telco.com
				For North Europe: support@batm.de, info@batm.de
				For the rest of the world: techsupport@telco.com"

        DESCRIPTION
        "Initial version. This MIB will provied a way to read 
        specific device parameters"
         
                -- Revision history.  
   REVISION "200612270000Z"
   DESCRIPTION
        "Initial revision history"
           
         
       ::= { switch 2110 }

-- MIB objects

    prvtOem1ParamsObjects OBJECT IDENTIFIER ::= { prvtOem1ParamsMIB 1 }
    prvtOem1ParamsNotifications  OBJECT IDENTIFIER ::= { prvtOem1ParamsMIB 2 }
    prvtOem1ParamsConformance    OBJECT IDENTIFIER ::= { prvtOem1ParamsMIB 3 }

    prvtSerialNumber OBJECT-TYPE
		SYNTAX  DisplayString
		MAX-ACCESS	read-only
		STATUS	current
		DESCRIPTION
			"Device serial number"
		::= { prvtOem1ParamsObjects 1 }

    prvtAssemblyNumber OBJECT-TYPE
		SYNTAX  DisplayString
		MAX-ACCESS	read-only
		STATUS	current
		DESCRIPTION
			"Device assembly number"
		::= { prvtOem1ParamsObjects 2 }

    prvtHardwareRevision OBJECT-TYPE
		SYNTAX  DisplayString
		MAX-ACCESS	read-only
		STATUS	current
		DESCRIPTION
			"Device hardware revision"
		::= { prvtOem1ParamsObjects 3 }

    prvtSwitchRevision OBJECT-TYPE
		SYNTAX  DisplayString
		MAX-ACCESS	read-only
		STATUS	current
		DESCRIPTION
			"Switch revision"
		::= { prvtOem1ParamsObjects 4 }

    prvtSwitchVersion OBJECT-TYPE
		SYNTAX  DisplayString
		MAX-ACCESS	read-only
		STATUS	current
		DESCRIPTION
			"Switch version"
		::= { prvtOem1ParamsObjects 5 }

    prvtSwitchEdition OBJECT-TYPE
		SYNTAX  DisplayString
		MAX-ACCESS	read-only
		STATUS	current
		DESCRIPTION
			"Switch edition"
		::= { prvtOem1ParamsObjects 6 }

    prvtSwitchRepair OBJECT-TYPE
		SYNTAX  DisplayString
		MAX-ACCESS	read-only
		STATUS	current
		DESCRIPTION
			"Switch repair"
		::= { prvtOem1ParamsObjects 7 }

    prvtHardwareAddress OBJECT-TYPE
		SYNTAX  DisplayString
		MAX-ACCESS	read-only
		STATUS	current
		DESCRIPTION
			"Switch hardware address"
		::= { prvtOem1ParamsObjects 8 }

    prvtCabinetRow OBJECT-TYPE
		SYNTAX  DisplayString
		MAX-ACCESS	read-only
		STATUS	current
		DESCRIPTION
			"Cabinet row location"
		::= { prvtOem1ParamsObjects 9 }

    prvtCabinetColumn OBJECT-TYPE
		SYNTAX  DisplayString
		MAX-ACCESS	read-only
		STATUS	current
		DESCRIPTION
			"Cabinet column location"
		::= { prvtOem1ParamsObjects 10 }

    prvtChassisVerticalDeviation OBJECT-TYPE
		SYNTAX  DisplayString
		MAX-ACCESS	read-only
		STATUS	current
		DESCRIPTION
			"Chassis vertical deviation location"
		::= { prvtOem1ParamsObjects 11 }

    prvtChassisHorizontalDeviatioin OBJECT-TYPE
		SYNTAX  DisplayString
		MAX-ACCESS	read-only
		STATUS	current
		DESCRIPTION
			"Chassis horizontal deviation location"
		::= { prvtOem1ParamsObjects 12 }

    prvtCabinetHMSNumber OBJECT-TYPE
		SYNTAX  DisplayString
		MAX-ACCESS	read-only
		STATUS	current
		DESCRIPTION
			"Cabinet HMS number"
		::= { prvtOem1ParamsObjects 13 }

    prvtSubrackHMSNumber OBJECT-TYPE
		SYNTAX  DisplayString
		MAX-ACCESS	read-only
		STATUS	current
		DESCRIPTION
			"Subrack HMS number"
		::= { prvtOem1ParamsObjects 14 }

    prvtModelNumber OBJECT-TYPE
		SYNTAX  INTEGER
		MAX-ACCESS	read-only
		STATUS	current
		DESCRIPTION
			"Model number"
		::= { prvtOem1ParamsObjects 15 }

    prvtPluginUID OBJECT-TYPE
		SYNTAX  INTEGER
		MAX-ACCESS	read-only
		STATUS	current
		DESCRIPTION
			"Plugin UID"
		::= { prvtOem1ParamsObjects 16 }
END
