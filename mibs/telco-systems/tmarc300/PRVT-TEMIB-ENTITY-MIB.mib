-- *********************************************************************
-- **
-- ** BATM Advanced Communications.
-- **
-- *********************************************************************
-- ** Filename:   mpls_temib.mib
-- ** Project:    T-Metro Switches.
-- ** Purpose:    Private MIB
-- *********************************************************************
-- (c) Copyright, 2006, BATM Advanced Communications.  All rights reserved.
--                             WARNING:
--
-- BY UTILIZING THIS FILE, YOU AGREE TO THE FOLLOWING:
--
-- This file is the property of BATM Advanced Communications and contains
-- proprietary and confidential information.  This file is made
-- available to authorized BATM customers on the express
-- condition that neither it, nor any of the information contained
-- therein, shall be disclosed to third parties or be used for any
-- purpose other than to replace, modify or upgrade firmware and/or
-- software components of BATM manufactured equipment within the
-- authorized customer's network, and that such transfer be
-- completed in accordance with the instructions provided by
-- BATM.  Any other use is strictly prohibited.
--
-- EXCEPT AS RESTRICTED BY LAW, OR AS PROVIDED IN BATM'S LIMITED
-- WARRANTY, THE SOFTWARE PROGRAMS CONTAINED IN THIS FILE ARE
-- PROVIDED "AS IS" WITHOUT WARRANTY OF ANY KIND, EITHER EXPRESSED
-- OR IMPLIED, INCLUDING BUT NOT LIMITED TO, ANY IMPLIED WARRANTIES
-- OF MERCHANTABILITY OR FITNESS FOR A PARTICULAR PURPOSE.
--
-- IN NO EVENT SHALL BATM BE LIABLE FOR ANY DAMAGES WHATSOEVER
-- INCLUDING WITHOUT LIMITATION, DAMAGES FOR LOSS OF BUSINESS
-- PROFITS, BUSINESS INTERRUPTION, LOSS OF BUSINESS INFORMATION OR
-- OTHER CONSEQUENTIAL DAMAGES ARISING OUT OF THE USE, OR INABILITY
-- TO USE, THE SOFTWARE CONTAINED IN THIS FILE.
--
-- ----------------------------------------------------------------------------

PRVT-TEMIB-ENTITY-MIB DEFINITIONS ::= BEGIN

  -- PRODUCT-SHORT-NAME MPLS

  IMPORTS
      MODULE-IDENTITY, OBJECT-TYPE,Integer32, Unsigned32    FROM SNMPv2-SMI

      MODULE-COMPLIANCE, OBJECT-GROUP                       FROM SNMPv2-CONF

      TEXTUAL-CONVENTION, RowStatus, TruthValue             FROM SNMPv2-TC

      PrvtLmgrIndex, PrvtLmgrPartnerStatus                  FROM PRVT-LMGR-MIB
      mpls                                                  FROM PRVT-CR-LDP-MIB;


  prvtTeMibEntityMib MODULE-IDENTITY
      LAST-UPDATED "200712060000Z" 
      ORGANIZATION "BATM Advanced Communication"
      CONTACT-INFO
                   " BATM/Telco Systems Support team
					Email: 
				For North America: techsupport@telco.com
				For North Europe: support@batm.de, info@batm.de
				For the rest of the world: techsupport@telco.com"      
      DESCRIPTION  "The MIB module for management of TE-MIB entities."
      
      REVISION "200712060000Z"  
       DESCRIPTION
          "Initial."
  ::= { mpls 8 }

  prvtTeMibEntityObjects OBJECT IDENTIFIER ::= { prvtTeMibEntityMib 1 } -- tables

-- Textual conventions

  PrvtTeMibAdminStatus ::= TEXTUAL-CONVENTION
      STATUS      current
      DESCRIPTION "The desired administrative state of a TE-MIB entity."
      SYNTAX      INTEGER {
                      up(1),          -- active
                      down(2)         -- inactive
                  }

  PrvtTeMibOperStatus ::= TEXTUAL-CONVENTION
      STATUS      current
      DESCRIPTION "The current operational state of a TE-MIB entity."
      SYNTAX      INTEGER {
                      up(1),          -- active
                      down(2),        -- inactive
                      goingUp(3),     -- activating
                      goingDown(4),   -- deactivating
                      actFailed(5)    -- activation failed
                  }

  PrvtTeMibEntityIndex ::= TEXTUAL-CONVENTION
      STATUS      current
      DESCRIPTION "The index value identifying a TE-MIB entity."
      SYNTAX      Unsigned32

  PrvtTeMibPartnerStatus ::= TEXTUAL-CONVENTION
      STATUS      current
      DESCRIPTION "The state of a TE-MIB entity partner."
      SYNTAX      INTEGER {
                      initial(0),     -- partner not active
                      activating(1),  -- partner activating
                      active(2),      -- partner active
                      deactivating(3),-- partner deactivating
                      failedOver(4),  -- partner failed, but recovering
                      failed(5),      -- partner failed, but recovering
                      unavailable(6)  -- partner unavailable
                  }

-- End of textual conventions

-- TE-MIB entity table
-- This table is used to create and manage TE-MIB entities.

  prvtMplsTeMibEntityTable OBJECT-TYPE
  -- FAMILY-SHORT-NAME temib
      SYNTAX      SEQUENCE OF PrvtMplsTeMibEntityEntry
      MAX-ACCESS  not-accessible
      STATUS      current
      DESCRIPTION
          "The table of TE-MIB entities."
      ::= { prvtTeMibEntityObjects 1 }

  prvtMplsTeMibEntityEntry OBJECT-TYPE
      SYNTAX      PrvtMplsTeMibEntityEntry
      MAX-ACCESS  not-accessible
      STATUS      current
      DESCRIPTION
          "Each entry represents a TE-MIB entity."
      INDEX { prvtMplsTeMibEntityIndex }
      ::= { prvtMplsTeMibEntityTable 1 }

  PrvtMplsTeMibEntityEntry ::= SEQUENCE {
          prvtMplsTeMibEntityIndex                 PrvtTeMibEntityIndex,
          prvtMplsTeMibEntityAdminStatus           PrvtTeMibAdminStatus,
          prvtMplsTeMibEntityOperStatus            PrvtTeMibOperStatus,
          prvtMplsTeMibEntityRowStatus             RowStatus,
          prvtMplsTeMibTunnelRetryInterval         Unsigned32,
          prvtMplsTeMibTunnelRetryDecayRate        Unsigned32,
          prvtMplsTeMibTunnelRetryMax              Integer32,
          prvtMplsTeMibTnnlBufPoolSize             Unsigned32,
          prvtMplsTeMibLsrIndex                    PrvtLmgrIndex,
          prvtMplsTeMibLdbStatus                   PrvtTeMibPartnerStatus,
          prvtMplsTeMibLraStatus                   PrvtLmgrPartnerStatus,
          prvtMplsTeMibLdiStatus                   PrvtTeMibPartnerStatus,
          prvtMplsTeMibRsvpEnable                  TruthValue,
          prvtMplsTeMibCrldpEnable                 TruthValue,
          prvtMplsTeMibCrldpIndex                  Unsigned32,
          prvtMplsTeMibUseRsvpResvConf             BITS,
          prvtMplsTeMibAllowGracefulDeletion       TruthValue,
          prvtMplsTeMibShowTransitTunnels          TruthValue,
          prvtMplsTeMibSupportCHopTable            TruthValue,
          prvtMplsTeMibNhrIndex                    Unsigned32,
          prvtMplsTeMibNhrBufPoolSize              Unsigned32,
          prvtMplsTeMibNhrStatus                   PrvtTeMibPartnerStatus,
          prvtMplsTeMibExtPrtSuppAdminStatus       PrvtTeMibAdminStatus,
          prvtMplsTeMibRsvpIpv6AdminStatus         PrvtTeMibAdminStatus,
          prvtMplsTeMibRsvpIpv6OperStatus          PrvtTeMibOperStatus,
          prvtMplsTeMibDynFacilityBypass           TruthValue
    }

  prvtMplsTeMibEntityIndex OBJECT-TYPE
      SYNTAX      PrvtTeMibEntityIndex
      MAX-ACCESS  not-accessible
      STATUS      current
      DESCRIPTION
          "The index of this TE-MIB entity table entry.  This is the
           HAF entity index passed on the entity create parameters."
      ::= { prvtMplsTeMibEntityEntry 1 }

  prvtMplsTeMibEntityAdminStatus OBJECT-TYPE
      SYNTAX      PrvtTeMibAdminStatus
      MAX-ACCESS  read-create
      STATUS      current
      DESCRIPTION
          "The desired administrative state of the TE-MIB entity.
           When prvtMplsTeMibEntityRowStatus is 'active' and
           prvtMplsTeMibEntityAdminStatus is 'up' the TE-MIB entity is active
           and only these two fields can be modified."
      DEFVAL { up }
      ::= { prvtMplsTeMibEntityEntry 2 }

  prvtMplsTeMibEntityOperStatus OBJECT-TYPE
      SYNTAX      PrvtTeMibOperStatus
      MAX-ACCESS  read-only
      STATUS      current
      DESCRIPTION
          "The current operational state of the TE-MIB entity."
      ::= { prvtMplsTeMibEntityEntry 3 }

  prvtMplsTeMibEntityRowStatus OBJECT-TYPE
      SYNTAX      RowStatus
      MAX-ACCESS  read-create
      STATUS      current
      DESCRIPTION
          "The row status for the TE-MIB entity table entry, used to create
           and destroy TE-MIB entities.
           When prvtMplsTeMibEntityRowStatus is 'active' and
           prvtMplsTeMibEntityAdminStatus is 'up' the TE-MIB entity is active
           and only these two fields can be modified."
      ::= { prvtMplsTeMibEntityEntry 4 }

  prvtMplsTeMibTunnelRetryInterval OBJECT-TYPE
      SYNTAX      Unsigned32 (0..65535)
      UNITS       "milliseconds"
      MAX-ACCESS  read-create
      STATUS      current
      DESCRIPTION
          "The persistent tunnel retry interval.
           This is the interval between the first failure of a persistent
           tunnel and the first attempt to re-establish the tunnel.
           A value of 0 indicates retrying is not supported.
           A management agent may preempt a retry by resetting
           mplsTunnelAdminStatus for the tunnel in question."
      DEFVAL      { 3000 }
      ::= { prvtMplsTeMibEntityEntry 5 }

  prvtMplsTeMibTunnelRetryDecayRate OBJECT-TYPE
      SYNTAX      Unsigned32 (0..100)
      MAX-ACCESS  read-create
      STATUS      current
      DESCRIPTION
          "The persistent tunnel decay rate.  This is a percentage.
           Thus a value of 10 increases the retry interval by ten per cent
           of the previous value.  A value of 0 indicates a constant
           retry rate."
       DEFVAL     { 50 }
      ::= { prvtMplsTeMibEntityEntry 6 }

  prvtMplsTeMibTunnelRetryMax OBJECT-TYPE
      SYNTAX      Integer32 (-1..255)
      MAX-ACCESS  read-create
      STATUS      current
      DESCRIPTION
          "The maximum number of retry attempts that will be made before a
           persistent tunnel is deemed inoperable.  Once in this state,
           a management agent should set mplsTunnelAdminStatus to 'up' to
           attempt to reestablish the tunnel.
           A value of -1 indicates infinite retry, so a persistent tunnel
           will continue to be retried until it is successfully
           established."
      DEFVAL      { 10 }
      ::= { prvtMplsTeMibEntityEntry 7 }

  prvtMplsTeMibTnnlBufPoolSize OBJECT-TYPE
      SYNTAX      Unsigned32 (0..2147483647)
      MAX-ACCESS  read-create
      STATUS      current
      DESCRIPTION
          "The maximum number of buffers available for tunnel management
           messages.  This is used to limit the number of tunnel management
           messages to avoid buffer shortage conditions."
      DEFVAL      { 8 }
      ::= { prvtMplsTeMibEntityEntry 8 }

  prvtMplsTeMibLsrIndex OBJECT-TYPE
      SYNTAX      PrvtLmgrIndex
      MAX-ACCESS  read-create
      STATUS      current
      DESCRIPTION
          "The index of the PRVT-LMGR product instance which this TE-MIB is to
           join to as its LDB interface provider. If this value is not
           specified, or the value of this object is 0, TE-MIB will use the
           prvtMplsTeMibEntityIndex value as the Lsr index when joining on the
           LDB interface."
      DEFVAL      { 0 }
      ::= { prvtMplsTeMibEntityEntry 9 }

   prvtMplsTeMibLdbStatus OBJECT-TYPE
       SYNTAX      PrvtTeMibPartnerStatus
       MAX-ACCESS  read-only
       STATUS      current
       DESCRIPTION
        "Diagnostic Field providing information about the status
         of the Label Database Interface user as seen by the
	 TE-MIB entity."
      ::= { prvtMplsTeMibEntityEntry 10 }

   prvtMplsTeMibLraStatus OBJECT-TYPE
       SYNTAX      PrvtLmgrPartnerStatus
       MAX-ACCESS  read-only
       STATUS      current
       DESCRIPTION
        "Diagnostic Field providing information about the status
         of the LRAPI user as seen by the TE-MIB entity."
      ::= { prvtMplsTeMibEntityEntry 11 }

   prvtMplsTeMibLdiStatus OBJECT-TYPE
       SYNTAX      PrvtTeMibPartnerStatus
       MAX-ACCESS  read-only
       STATUS      current
       DESCRIPTION
        "A diagnostic value which reports the state of the LDI
         join."
      ::= { prvtMplsTeMibEntityEntry 12 }

   prvtMplsTeMibRsvpEnable OBJECT-TYPE
       SYNTAX      TruthValue
       MAX-ACCESS  read-create
       STATUS      current
       DESCRIPTION
        "A boolean indicating whether the PRVT-TE-MIB should expect
         a join from PRVT-RSVP across the LRAPI.  This indicates
         whether RSVP-TE LSP tunnels are supported or not."
       DEFVAL { true }

      ::= { prvtMplsTeMibEntityEntry 13 }

   prvtMplsTeMibCrldpEnable OBJECT-TYPE
       SYNTAX      TruthValue
       MAX-ACCESS  read-create
       STATUS      current
       DESCRIPTION
        "A boolean indicating whether the PRVT-TE-MIB should join
         to PRVT-CR-LDP or not across the LDI, and therefore support
         CR-LDP LSP tunnels or not."
       DEFVAL { false }

      ::= { prvtMplsTeMibEntityEntry 14 }

   prvtMplsTeMibCrldpIndex OBJECT-TYPE
       SYNTAX      Unsigned32
       MAX-ACCESS  read-create
       STATUS      current
       DESCRIPTION
        "The index of the PRVT-MPLS product instance which this
         TE-MIB is to join to as its LDI interface provider.  If
         this value is not specified, or the value of this object
         is 0, TE-MIB will use the prvtMplsTeMibEntityIndex value as
         the CR-LDP product index when joining on the LDI
         interface."
       DEFVAL     { 0 }

      ::= { prvtMplsTeMibEntityEntry 15 }

   prvtMplsTeMibUseRsvpResvConf OBJECT-TYPE
       SYNTAX      BITS{
                       useResvConfForUNI(0),
                       useResvConfForGMPLS(1)
                       }
       MAX-ACCESS  read-create
       STATUS      current
       DESCRIPTION
        "Flags field indicating whether a RESV_CONFIRM object
         should be included in RSVP Resv messages.  The possible
         bit values are as follows.

         - useResvConfForUNI: RESV_CONFIRM objects should be
           inserted into all UNI Resv messages.
         - useResvConfForGMPLS: RESV_CONFIRM objects should be
           inserted into all standard GMPLS Resv messages."

      ::= { prvtMplsTeMibEntityEntry 16 }

   prvtMplsTeMibAllowGracefulDeletion OBJECT-TYPE
       SYNTAX      TruthValue
       MAX-ACCESS  read-create
       STATUS      current
       DESCRIPTION
        "A boolean indicating whether the TE-MIB should allow
         tunnels to be deleted using the graceful deletion
         procedure."
       DEFVAL { false }

      ::= { prvtMplsTeMibEntityEntry 17 }

   prvtMplsTeMibShowTransitTunnels OBJECT-TYPE
       SYNTAX      TruthValue
       MAX-ACCESS  read-create
       STATUS      current
       DESCRIPTION
         "A flag to indicate whether RSVP should inform TE-MIB about
          LSPs for which this node is transit."
       DEFVAL { false }

      ::= { prvtMplsTeMibEntityEntry 18 }

   prvtMplsTeMibSupportCHopTable OBJECT-TYPE
       SYNTAX      TruthValue
       MAX-ACCESS  read-create
       STATUS      current
       DESCRIPTION
         "A flag to indicate whether TE-MIB should support the
          mplsTunnelCHopTable."
       DEFVAL { false }
      ::= { prvtMplsTeMibEntityEntry 19 }

   prvtMplsTeMibNhrIndex OBJECT-TYPE
       SYNTAX      Unsigned32
       MAX-ACCESS  read-create
       STATUS      current
       DESCRIPTION
           "The index of the PRVT-MPLS product instance which this
            TE-MIB is to join to as its NHR interface provider.  If
            this value is not specified, or the value of this object
            is 0, TE-MIB will use the prvtMplsTeMibEntityIndex value as
            the LSR index when joining on the NHR interface."
       DEFVAL      { 0 }
       ::= { prvtMplsTeMibEntityEntry 20 }

   prvtMplsTeMibNhrBufPoolSize OBJECT-TYPE
       SYNTAX      Unsigned32 (0..2147483647)
       MAX-ACCESS  read-create
       STATUS      current
       DESCRIPTION
           "The maximum number of buffers available for Next Hop
            Routing Interface messages.  This is used to limit the
            number of tunnel management messages to avoid buffer
            shortage conditions."
       DEFVAL      { 8 }
       ::= { prvtMplsTeMibEntityEntry 21 }

   prvtMplsTeMibNhrStatus OBJECT-TYPE
       SYNTAX      PrvtTeMibPartnerStatus
       MAX-ACCESS  read-only
       STATUS      current
       DESCRIPTION
        "A diagnostic value which reports the state of the NHR
        join."
      ::= { prvtMplsTeMibEntityEntry 22 }

   prvtMplsTeMibExtPrtSuppAdminStatus OBJECT-TYPE
       SYNTAX      PrvtTeMibAdminStatus
       MAX-ACCESS  read-create
       STATUS      current
       DESCRIPTION
        "The desired operational state of support for the extended
         PROTECTION object defined in
         draft-lang-ccamp-gmpls-recovery-e2e-signaling."
       DEFVAL { down }
      ::= { prvtMplsTeMibEntityEntry 23 }

   prvtMplsTeMibRsvpIpv6AdminStatus OBJECT-TYPE
       SYNTAX      PrvtTeMibAdminStatus
       MAX-ACCESS  read-create
       STATUS      current
       DESCRIPTION
        "Specifies whether the local node supports IPv6 LSPs.

         Setting this to UP means that this node supports IPv6 LSPs
         being set up to, from and through this node.

         Setting this to DOWN means that IPv6 LSPs are NOT
         supported by this node.  Existing IPv6 LSPs for which this
         node is the ingress are torn down.

         This field can be modified while TE-MIB is oper_status UP
         or DOWN.

         The value of this field MUST match the value of the
         dcRsvpProductIpv6AdminStatus field in the
         dcRsvpProductTable."
       DEFVAL { down }
      ::= { prvtMplsTeMibEntityEntry 24 }

   prvtMplsTeMibRsvpIpv6OperStatus OBJECT-TYPE
       SYNTAX      PrvtTeMibOperStatus
       MAX-ACCESS  read-only
       STATUS      current
       DESCRIPTION
        "The current operational status for IPv6 support.  When
         this is UP IPv6 LSPs can be set up from this node.  When
         this is DOWN there will be no active IPv6 LSPs."
      ::= { prvtMplsTeMibEntityEntry 25 }

   prvtMplsTeMibDynFacilityBypass OBJECT-TYPE
       SYNTAX      TruthValue
       MAX-ACCESS  read-write
       STATUS      current
       DESCRIPTION
        "This object gives the user ability to globally enable/disable 
         automatically creation of bypass tunnels for all LSPs. Bypass 
         tunnels will be created on FRR tunnel request automatically.
         The default value is true. The creation of Dynamic bypass tunnels 
         is enabled"
       DEFVAL { true }
      ::= { prvtMplsTeMibEntityEntry 26 }

-- Module compliance.

-- Conformance Information.

  prvtTeMibEntityConformance   OBJECT IDENTIFIER ::= { prvtTeMibEntityMib 2 }

  prvtTeMibEntityCompliances OBJECT IDENTIFIER ::= { prvtTeMibEntityConformance 1 }
  prvtTeMibEntityGroups      OBJECT IDENTIFIER ::= { prvtTeMibEntityConformance 2 }

  prvtTeMibEntityMibCompliance MODULE-COMPLIANCE
    STATUS current
    DESCRIPTION
        "The compliance statement for the PRVT-TEMIB product."
    MODULE

    MANDATORY-GROUPS { mplsTeMibMandatoryGroup }

    GROUP mplsTeMibOptionalGroup
    DESCRIPTION
        "Optional TeMib objects."

    GROUP mplsTeMibCrldpGroup
    DESCRIPTION
        "Group of Objects relating to CR-LDP."

    ::= { prvtTeMibEntityCompliances 1 }


-- Units of conformance.

mplsTeMibMandatoryGroup OBJECT-GROUP
   OBJECTS {
      prvtMplsTeMibEntityRowStatus
   }
   STATUS  current
   DESCRIPTION
        "Mandatory Objects."
   ::= { prvtTeMibEntityGroups 2 }

mplsTeMibOptionalGroup OBJECT-GROUP
   OBJECTS {
      prvtMplsTeMibEntityAdminStatus,
      prvtMplsTeMibEntityOperStatus,
      prvtMplsTeMibTunnelRetryInterval,
      prvtMplsTeMibTunnelRetryDecayRate,
      prvtMplsTeMibTunnelRetryMax,
      prvtMplsTeMibTnnlBufPoolSize,
      prvtMplsTeMibLsrIndex,
      prvtMplsTeMibLdbStatus,
      prvtMplsTeMibLraStatus,
      prvtMplsTeMibRsvpEnable,
      prvtMplsTeMibUseRsvpResvConf,
      prvtMplsTeMibAllowGracefulDeletion,
      prvtMplsTeMibShowTransitTunnels,
      prvtMplsTeMibSupportCHopTable,
      prvtMplsTeMibNhrIndex,
      prvtMplsTeMibNhrBufPoolSize,
      prvtMplsTeMibNhrStatus,
      prvtMplsTeMibExtPrtSuppAdminStatus,
      prvtMplsTeMibRsvpIpv6AdminStatus,
      prvtMplsTeMibRsvpIpv6OperStatus,
      prvtMplsTeMibDynFacilityBypass
   }
   STATUS  current
   DESCRIPTION
        "Optional Objects."
   ::= { prvtTeMibEntityGroups 3 }

mplsTeMibCrldpGroup OBJECT-GROUP
   OBJECTS {
      prvtMplsTeMibLdiStatus,
      prvtMplsTeMibCrldpEnable,
      prvtMplsTeMibCrldpIndex
   }
   STATUS current
   DESCRIPTION
        "Group of objects relating to CR-LDP"
   ::= { prvtTeMibEntityGroups 4 }

END
