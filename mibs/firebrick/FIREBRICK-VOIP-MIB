-- *------------------------------------------------
-- * Firebrick 2900 VOIP MIB
-- *
-- * December 2021, Cliff Hones & David Honour
-- *
-- * Copyright (c) 2021 by Andrews & Arnold
-- *------------------------------------------------

FIREBRICK-VOIP-MIB DEFINITIONS ::= BEGIN

IMPORTS
    MODULE-IDENTITY,
    OBJECT-TYPE,
    Integer32,
    enterprises
        FROM SNMPv2-SMI
    DisplayString
        FROM SNMPv2-TC
    InetAddressType,
    InetAddress
        FROM INET-ADDRESS-MIB
    OBJECT-GROUP
        FROM SNMPv2-CONF
    firebrickNewStyle
        FROM FIREBRICK-MIB
        ;

fbSipMib MODULE-IDENTITY
    LAST-UPDATED "202207150000Z"
    ORGANIZATION "Andrews & Arnold Limited"
    CONTACT-INFO
        "Andrews & Arnold
        Unit 1&2, Enterprise Court
        Bracknell, Berkshire, RG12 1QS
        United Kingdom

        Tel: +44 3333 400 999
        Email: support@aa.net.uk"
    DESCRIPTION
        "Firebrick-specific structures for VoIP/SIP"
    REVISION "202207150000Z"
    DESCRIPTION "Additional validation"
    REVISION "202112080000Z"
    DESCRIPTION "Updated version of this MIB module with carrier count"
    REVISION "202006170000Z"
    DESCRIPTION "Initial version of this MIB module"
    ::= { firebrickNewStyle 5060 }

-- *  Global items

fbSipActiveLegs OBJECT-TYPE
    SYNTAX Integer32
    MAX-ACCESS read-only
    STATUS current
    DESCRIPTION
        "The total number of active call legs on this Firebrick"
    ::= { fbSipMib 1 }

fbSipRadiusRegs OBJECT-TYPE
    SYNTAX Integer32
    MAX-ACCESS read-only
    STATUS current
    DESCRIPTION
        "The number of RADIUS-based incoming registrations on this Firebrick"
    ::= { fbSipMib 2 }

fbSipMixerUsage OBJECT-TYPE
    SYNTAX Integer32
    MAX-ACCESS read-only
    STATUS current
    DESCRIPTION
        "The number of mixers in use on this Firebrick"
    ::= { fbSipMib 5 }

fbSipMixerHWM OBJECT-TYPE
    SYNTAX Integer32
    MAX-ACCESS read-only
    STATUS current
    DESCRIPTION
        "The maximum number of mixers simultaneously used at any time on this Firebrick"
    ::= { fbSipMib 6 }

fbSipCarriers OBJECT-TYPE
    SYNTAX Integer32
    MAX-ACCESS read-only
    STATUS current
    DESCRIPTION
        "The number of carriers on this Firebrick"
    ::= { fbSipMib 7 }

fbSipMixerMax OBJECT-TYPE
    SYNTAX Integer32
    MAX-ACCESS read-only
    STATUS current
    DESCRIPTION
        "The maximum number of mixers it is possible to have on this Firebrick"
    ::= { fbSipMib 8 }

-- *  Carriers Table

fbSipCarrierTable OBJECT-TYPE
    SYNTAX SEQUENCE OF FbSipCarrierEntry
    MAX-ACCESS not-accessible
    STATUS current
    DESCRIPTION
        "The list of VoIP carriers for this Firebrick"
    ::= { fbSipMib 3 }

fbSipCarrierEntry OBJECT-TYPE
    SYNTAX FbSipCarrierEntry
    MAX-ACCESS not-accessible
    STATUS current
    DESCRIPTION
        "An entry in the Carriers table"
    INDEX { fbSipCarrierIndex }
    ::= { fbSipCarrierTable 1 }

FbSipCarrierEntry ::= SEQUENCE {
    fbSipCarrierIndex           Integer32,
    fbSipCarrierName            DisplayString,
    fbSipCarrierTotalLegs       Integer32,
    fbSipCarrierConnectedLegs   Integer32
}

fbSipCarrierName OBJECT-TYPE
    SYNTAX  DisplayString
    MAX-ACCESS  read-only
    STATUS  current
    DESCRIPTION
        "The config name of this carrier"
    ::= { fbSipCarrierEntry 1 }

fbSipCarrierIndex OBJECT-TYPE
    SYNTAX Integer32 (0..255)
    MAX-ACCESS not-accessible
    STATUS current
    DESCRIPTION
        "The index of the SIP carrier in the carriers table"
    ::= { fbSipCarrierEntry 4 }

fbSipCarrierTotalLegs OBJECT-TYPE
    SYNTAX Integer32
    MAX-ACCESS read-only
    STATUS current
    DESCRIPTION
        "The total number of call legs for this carrier"
    ::= { fbSipCarrierEntry 2 }

fbSipCarrierConnectedLegs OBJECT-TYPE
    SYNTAX Integer32
    MAX-ACCESS read-only
    STATUS current
    DESCRIPTION
        "The number of connected call legs for this carrier"
    ::= { fbSipCarrierEntry 3 }

-- *  Telephone Table

fbSipPhoneTable OBJECT-TYPE
    SYNTAX SEQUENCE OF FbSipPhoneEntry
    MAX-ACCESS not-accessible
    STATUS current
    DESCRIPTION
        "The list of telephones on this Firebrick"
    ::= { fbSipMib 4 }

fbSipPhoneEntry OBJECT-TYPE
    SYNTAX FbSipPhoneEntry
    MAX-ACCESS not-accessible
    STATUS current
    DESCRIPTION
        "An entry in the telephone table"
    INDEX { fbSipPhoneIndex }
    ::= { fbSipPhoneTable 1 }

FbSipPhoneEntry ::= SEQUENCE {
    fbSipPhoneIndex           Integer32,
    fbSipPhoneName            DisplayString,
    fbSipPhoneTotalLegs       Integer32,
    fbSipPhoneConnectedLegs   Integer32
}

fbSipPhoneName OBJECT-TYPE
    SYNTAX  DisplayString
    MAX-ACCESS  read-only
    STATUS  current
    DESCRIPTION
        "The name of this telephone"
    ::= { fbSipPhoneEntry 1 }

fbSipPhoneIndex OBJECT-TYPE
    SYNTAX Integer32 (0..255)
    MAX-ACCESS not-accessible
    STATUS current
    DESCRIPTION
        "The index of the phone in the telephone table"
    ::= { fbSipPhoneEntry 4 }

fbSipPhoneTotalLegs OBJECT-TYPE
    SYNTAX Integer32
    MAX-ACCESS read-only
    STATUS current
    DESCRIPTION
        "The total number of call legs for this telephone"
    ::= { fbSipPhoneEntry 2 }

fbSipPhoneConnectedLegs OBJECT-TYPE
    SYNTAX Integer32
    MAX-ACCESS read-only
    STATUS current
    DESCRIPTION
        "The number of connected call legs for this telephone"
    ::= { fbSipPhoneEntry 3 }

END
