--
-- Chatsworth Products Inc.
-- Copyright (c) Chatsworth Products Inc., 1998-2019.
-- Version : 2.1.0.1 (netsnmp compliant)
-- ************************************************************************

CPI-UNITY-MIB DEFINITIONS ::= BEGIN

IMPORTS
    MODULE-IDENTITY,
    OBJECT-TYPE,
    NOTIFICATION-TYPE,
    IpAddress,
    Integer32,
    Counter64,
    enterprises
        FROM SNMPv2-SMI
    DisplayString
        FROM SNMPv2-TC
    MacAddress
        FROM SNMPv2-TC
    TruthValue
        FROM SNMPv2-TC
    Unsigned32
        FROM SNMPv2-SMI
    MODULE-COMPLIANCE,
    OBJECT-GROUP,
    NOTIFICATION-GROUP
        FROM SNMPv2-CONF;

products MODULE-IDENTITY
    LAST-UPDATED "201903011508Z"
    ORGANIZATION "Chatsworth Products Inc."
    CONTACT-INFO
        "Chatsworth Products, Inc.
        3004 South Austin Avenue
        Georgetown, TX 78626
        Tel: (800) 834-4969
        Email: techsupport@chatsworth.com"
    DESCRIPTION
     "The MIB module is used to register Chatsworth eConnect related 
      SNMP OIDs for all models.

      Copyright 2014-2019 Chatsworth Products, Inc. All rights reserved.
      Reproduction of this document is authorized on the condition
      that the forgoing copyright notice is included.

      This Specification is supplied 'AS IS' and Chatsworth Products, Inc
      makes no warranty, either express or implied, as to the use,
      operation, condition, or performance of the Specification."
    REVISION      "201903010000Z"
    DESCRIPTION
		"Consolidating Legacy MIBs into the Unity MIB base."
    REVISION "201408011508Z"
    DESCRIPTION
		"Initial version of the Unity SNMP OIDs"
    ::= { cpi 1 }

cpi OBJECT IDENTIFIER ::= { enterprises 30932 }

-- ######################################################################
-- ######################################################################
-- ######################################################################
--
--          Legacy MIBS Below
--
-- ######################################################################
-- ######################################################################
-- ######################################################################

cpiPDU OBJECT IDENTIFIER ::= { products 1 }

systemInfo OBJECT IDENTIFIER ::= { cpiPDU 1 }

version OBJECT-TYPE
    SYNTAX DisplayString (SIZE (0..14))
    MAX-ACCESS read-only
    STATUS current
    DESCRIPTION
        "Software Version."
    ::= { systemInfo 1 }

modelCode OBJECT-TYPE
    SYNTAX DisplayString (SIZE (0..14))
    MAX-ACCESS read-only
    STATUS current
    DESCRIPTION
        "Model code for the PDU."
    ::= { systemInfo 2 }

hwAddress OBJECT-TYPE
    SYNTAX DisplayString (SIZE (17))
    MAX-ACCESS read-only
    STATUS current
    DESCRIPTION
        "PDU hardware MAC address."
    ::= { systemInfo 3 }

configuration OBJECT IDENTIFIER ::= { cpiPDU 2 }

logInterval OBJECT-TYPE
    SYNTAX Integer32 (0..65535)
    MAX-ACCESS read-write
    STATUS current
    DESCRIPTION
        "The time interval in seconds for logging metrics (disabled if < 10)."
    ::= { configuration 1 }

alarmInterval OBJECT-TYPE
    SYNTAX Integer32 (0..65535)
    MAX-ACCESS read-write
    STATUS current
    DESCRIPTION
        "The time interval in seconds for alarm cycle (disabled if < 10)."
    ::= { configuration 2 }

logDifference OBJECT-TYPE
    SYNTAX Integer32 (0..2000)
    MAX-ACCESS read-write
    STATUS current
    DESCRIPTION
        "The current difference in 1/100 Amps that triggers logging metrics."
    ::= { configuration 3 }

pduIP OBJECT-TYPE
    SYNTAX IpAddress
    MAX-ACCESS read-write
    STATUS current
    DESCRIPTION
        "PDU IP address."
    ::= { configuration 4 }

netOptions OBJECT IDENTIFIER ::= { configuration 5 }

autoIP OBJECT-TYPE
    SYNTAX Integer32 (0..1)
    MAX-ACCESS read-write
    STATUS current
    DESCRIPTION
        "Select dynamic (Auto) or static IP, 0=static and 1=dynamic."
    ::= { netOptions 1 }

autoDNS OBJECT-TYPE
    SYNTAX Integer32 (0..1)
    MAX-ACCESS read-write
    STATUS current
    DESCRIPTION
        "Select dynamic (Auto) or static DNS, 0=static and 1=dynamic."
    ::= { netOptions 2 }

ipV4Enable OBJECT-TYPE
    SYNTAX Integer32 (0..1)
    MAX-ACCESS read-write
    STATUS current
    DESCRIPTION
        "Enable IPV4 Network, 0=disable and 1=enable."
    ::= { netOptions 3 }

snmpEnable OBJECT-TYPE
    SYNTAX Integer32 (0..1)
    MAX-ACCESS read-write
    STATUS current
    DESCRIPTION
        "Enable SNMP network service, 0=disable and 1=enable."
    ::= { netOptions 4 }

telnetEnable OBJECT-TYPE
    SYNTAX Integer32 (0..1)
    MAX-ACCESS read-write
    STATUS current
    DESCRIPTION
        "Enable Telnet service, 0=disable and 1=enable."
    ::= { netOptions 5 }

sshEnable OBJECT-TYPE
    SYNTAX Integer32 (0..1)
    MAX-ACCESS read-write
    STATUS current
    DESCRIPTION
        "Enable SSH Service, 0=disable and 1=enable."
    ::= { netOptions 6 }

httpEnable OBJECT-TYPE
    SYNTAX Integer32 (0..1)
    MAX-ACCESS read-write
    STATUS current
    DESCRIPTION
        "Enable HTTP Service, 0=disable and 1=enable."
    ::= { netOptions 7 }

httpsEnable OBJECT-TYPE
    SYNTAX Integer32 (0..1)
    MAX-ACCESS read-write
    STATUS current
    DESCRIPTION
        "Enable HTTPS Service, 0=disable and 1=enable."
    ::= { netOptions 8 }

subnetMask OBJECT-TYPE
    SYNTAX IpAddress
    MAX-ACCESS read-write
    STATUS current
    DESCRIPTION
        "PDU Subnet Mask."
    ::= { configuration 6 }

gateway OBJECT-TYPE
    SYNTAX IpAddress
    MAX-ACCESS read-write
    STATUS current
    DESCRIPTION
        "PDU Gateway Address."
    ::= { configuration 7 }

dnsHosts OBJECT IDENTIFIER ::= { configuration 8 }

dns1 OBJECT-TYPE
    SYNTAX IpAddress
    MAX-ACCESS read-write
    STATUS current
    DESCRIPTION
        "PDU DNS 1 IP."
    ::= { dnsHosts 1 }

dns2 OBJECT-TYPE
    SYNTAX IpAddress
    MAX-ACCESS read-write
    STATUS current
    DESCRIPTION
        "PDU DNS 2 IP."
    ::= { dnsHosts 2 }

dns3 OBJECT-TYPE
    SYNTAX IpAddress
    MAX-ACCESS read-write
    STATUS current
    DESCRIPTION
        "PDU DNS 3 IP."
    ::= { dnsHosts 3 }

snmpHosts OBJECT IDENTIFIER ::= { configuration 9 }

snmpHost1 OBJECT-TYPE
    SYNTAX IpAddress
    MAX-ACCESS read-write
    STATUS current
    DESCRIPTION
        "SNMP Host 1 IP address."
    ::= { snmpHosts 1 }

snmpHost2 OBJECT-TYPE
    SYNTAX IpAddress
    MAX-ACCESS read-write
    STATUS current
    DESCRIPTION
        "SNMP Host 2 IP address."
    ::= { snmpHosts 2 }

snmpHost3 OBJECT-TYPE
    SYNTAX IpAddress
    MAX-ACCESS read-write
    STATUS current
    DESCRIPTION
        "SNMP Host 3 IP address."
    ::= { snmpHosts 3 }

pduIPv6 OBJECT-TYPE
    SYNTAX DisplayString (SIZE (0..64))
    MAX-ACCESS read-write
    STATUS current
    DESCRIPTION
        "PDU IPV6 address."
    ::= { configuration 10 }

netOptionsIPv6 OBJECT IDENTIFIER ::= { configuration 11 }

autoIPv6 OBJECT-TYPE
    SYNTAX Integer32 (0..1)
    MAX-ACCESS read-write
    STATUS current
    DESCRIPTION
        "Select IPV6 dynamic (Auto) or static IP, 0=static and 1=dynamic."
    ::= { netOptionsIPv6 1 }

autoDNSIPv6 OBJECT-TYPE
    SYNTAX Integer32 (0..1)
    MAX-ACCESS read-write
    STATUS current
    DESCRIPTION
        "Select IPV6 dynamic (Auto) or static DNS, 0=static and 1=dynamic."
    ::= { netOptionsIPv6 2 }

ipv6Enable OBJECT-TYPE
    SYNTAX Integer32 (0..1)
    MAX-ACCESS read-write
    STATUS current
    DESCRIPTION
        "Enable IPV6 Network, 0=disable and 1=enable."
    ::= { netOptionsIPv6 3 }

linkLocalEnable OBJECT-TYPE
    SYNTAX Integer32 (0..1)
    MAX-ACCESS read-write
    STATUS current
    DESCRIPTION
        "Enable IPV6 Link-Local, 0=disable and 1=enable."
    ::= { netOptionsIPv6 4 }

globalAddrEnable OBJECT-TYPE
    SYNTAX Integer32 (0..1)
    MAX-ACCESS read-write
    STATUS current
    DESCRIPTION
        "Enable IPV6 Global Address, 0=disable and 1=enable."
    ::= { netOptionsIPv6 5 }

subnetMaskIPv6 OBJECT-TYPE
    SYNTAX Integer32 (0..127)
    MAX-ACCESS read-write
    STATUS current
    DESCRIPTION
        "PDU IPV6 Subnet Mask."
    ::= { configuration 12 }

gatewayIPv6 OBJECT-TYPE
    SYNTAX DisplayString (SIZE (0..64))
    MAX-ACCESS read-write
    STATUS current
    DESCRIPTION
        "PDU IPV6 Gateway Address."
    ::= { configuration 13 }

dnsHostIPv6 OBJECT IDENTIFIER ::= { configuration 14 }

dns1IPv6 OBJECT-TYPE
    SYNTAX DisplayString (SIZE (0..64))
    MAX-ACCESS read-write
    STATUS current
    DESCRIPTION
        "PDU DNS 2 for IPV6."
    ::= { dnsHostIPv6 1 }

dns2IPv6 OBJECT-TYPE
    SYNTAX DisplayString (SIZE (0..64))
    MAX-ACCESS read-write
    STATUS current
    DESCRIPTION
        "PDU DNS 3 for IPV6."
    ::= { dnsHostIPv6 2 }

dns3IPv6 OBJECT-TYPE
    SYNTAX DisplayString (SIZE (0..64))
    MAX-ACCESS read-write
    STATUS current
    DESCRIPTION
        "PDU DNS 4 for IPV6."
    ::= { dnsHostIPv6 3 }

snmpHostsIPv6 OBJECT IDENTIFIER ::= { configuration 15 }

snmpHost1IPv6 OBJECT-TYPE
    SYNTAX DisplayString (SIZE (0..64))
    MAX-ACCESS read-write
    STATUS current
    DESCRIPTION
        "SNMP Host 1 IPV6."
    ::= { snmpHostsIPv6 1 }

snmpHost2IPv6 OBJECT-TYPE
    SYNTAX DisplayString (SIZE (0..64))
    MAX-ACCESS read-write
    STATUS current
    DESCRIPTION
        "SNMP Host 2 IPV6."
    ::= { snmpHostsIPv6 2 }

snmpHost3IPv6 OBJECT-TYPE
    SYNTAX DisplayString (SIZE (0..64))
    MAX-ACCESS read-write
    STATUS current
    DESCRIPTION
        "SNMP Host 3 IPV6."
    ::= { snmpHostsIPv6 3 }

receptacleControl OBJECT IDENTIFIER ::= { configuration 16 }

outlet1Ctrl OBJECT-TYPE
    SYNTAX Integer32 (0..1)
    MAX-ACCESS read-write
    STATUS current
    DESCRIPTION
        "Outlet1 power state, 0=OFF, 1=ON."
    ::= { receptacleControl 1 }

outlet2Ctrl OBJECT-TYPE
    SYNTAX Integer32 (0..1)
    MAX-ACCESS read-write
    STATUS current
    DESCRIPTION
        "Outlet2 power state, 0=OFF, 1=ON."
    ::= { receptacleControl 2 }

outlet3Ctrl OBJECT-TYPE
    SYNTAX Integer32 (0..1)
    MAX-ACCESS read-write
    STATUS current
    DESCRIPTION
        "Outlet3 power state, 0=OFF, 1=ON."
    ::= { receptacleControl 3 }

outlet4Ctrl OBJECT-TYPE
    SYNTAX Integer32 (0..1)
    MAX-ACCESS read-write
    STATUS current
    DESCRIPTION
        "Outlet4 power state, 0=OFF, 1=ON."
    ::= { receptacleControl 4 }

outlet5Ctrl OBJECT-TYPE
    SYNTAX Integer32 (0..1)
    MAX-ACCESS read-write
    STATUS current
    DESCRIPTION
        "Outlet5 power state, 0=OFF, 1=ON."
    ::= { receptacleControl 5 }

outlet6Ctrl OBJECT-TYPE
    SYNTAX Integer32 (0..1)
    MAX-ACCESS read-write
    STATUS current
    DESCRIPTION
        "Outlet6 power state, 0=OFF, 1=ON."
    ::= { receptacleControl 6 }

outlet7Ctrl OBJECT-TYPE
    SYNTAX Integer32 (0..1)
    MAX-ACCESS read-write
    STATUS current
    DESCRIPTION
        "Outlet7 power state, 0=OFF, 1=ON."
    ::= { receptacleControl 7 }

outlet8Ctrl OBJECT-TYPE
    SYNTAX Integer32 (0..1)
    MAX-ACCESS read-write
    STATUS current
    DESCRIPTION
        "Outlet8 power state, 0=OFF, 1=ON."
    ::= { receptacleControl 8 }

outlet9Ctrl OBJECT-TYPE
    SYNTAX Integer32 (0..1)
    MAX-ACCESS read-write
    STATUS current
    DESCRIPTION
        "Outlet9 power state, 0=OFF, 1=ON."
    ::= { receptacleControl 9 }

outlet10Ctrl OBJECT-TYPE
    SYNTAX Integer32 (0..1)
    MAX-ACCESS read-write
    STATUS current
    DESCRIPTION
        "Outlet10 power state, 0=OFF, 1=ON."
    ::= { receptacleControl 10 }

outlet11Ctrl OBJECT-TYPE
    SYNTAX Integer32 (0..1)
    MAX-ACCESS read-write
    STATUS current
    DESCRIPTION
        "Outlet11 power state, 0=OFF, 1=ON."
    ::= { receptacleControl 11 }

outlet12Ctrl OBJECT-TYPE
    SYNTAX Integer32 (0..1)
    MAX-ACCESS read-write
    STATUS current
    DESCRIPTION
        "Outlet12 power state, 0=OFF, 1=ON."
    ::= { receptacleControl 12 }

outlet13Ctrl OBJECT-TYPE
    SYNTAX Integer32 (0..1)
    MAX-ACCESS read-write
    STATUS current
    DESCRIPTION
        "Outlet13 power state, 0=OFF, 1=ON."
    ::= { receptacleControl 13 }

outlet14Ctrl OBJECT-TYPE
    SYNTAX Integer32 (0..1)
    MAX-ACCESS read-write
    STATUS current
    DESCRIPTION
        "Outlet14 power state, 0=OFF, 1=ON."
    ::= { receptacleControl 14 }

outlet15Ctrl OBJECT-TYPE
    SYNTAX Integer32 (0..1)
    MAX-ACCESS read-write
    STATUS current
    DESCRIPTION
        "Outlet15 power state, 0=OFF, 1=ON."
    ::= { receptacleControl 15 }

outlet16Ctrl OBJECT-TYPE
    SYNTAX Integer32 (0..1)
    MAX-ACCESS read-write
    STATUS current
    DESCRIPTION
        "Outlet16 power state, 0=OFF, 1=ON."
    ::= { receptacleControl 16 }

outlet17Ctrl OBJECT-TYPE
    SYNTAX Integer32 (0..1)
    MAX-ACCESS read-write
    STATUS current
    DESCRIPTION
        "Outlet17 power state, 0=OFF, 1=ON."
    ::= { receptacleControl 17 }

outlet18Ctrl OBJECT-TYPE
    SYNTAX Integer32 (0..1)
    MAX-ACCESS read-write
    STATUS current
    DESCRIPTION
        "Outlet18 power state, 0=OFF, 1=ON."
    ::= { receptacleControl 18 }

outlet19Ctrl OBJECT-TYPE
    SYNTAX Integer32 (0..1)
    MAX-ACCESS read-write
    STATUS current
    DESCRIPTION
        "Outlet19 power state, 0=OFF, 1=ON."
    ::= { receptacleControl 19 }

outlet20Ctrl OBJECT-TYPE
    SYNTAX Integer32 (0..1)
    MAX-ACCESS read-write
    STATUS current
    DESCRIPTION
        "Outlet20 power state, 0=OFF, 1=ON."
    ::= { receptacleControl 20 }

outlet21Ctrl OBJECT-TYPE
    SYNTAX Integer32 (0..1)
    MAX-ACCESS read-write
    STATUS current
    DESCRIPTION
        "Outlet21 power state, 0=OFF, 1=ON."
    ::= { receptacleControl 21 }

outlet22Ctrl OBJECT-TYPE
    SYNTAX Integer32 (0..1)
    MAX-ACCESS read-write
    STATUS current
    DESCRIPTION
        "Outlet22 power state, 0=OFF, 1=ON."
    ::= { receptacleControl 22 }

outlet23Ctrl OBJECT-TYPE
    SYNTAX Integer32 (0..1)
    MAX-ACCESS read-write
    STATUS current
    DESCRIPTION
        "Outlet23 power state, 0=OFF, 1=ON."
    ::= { receptacleControl 23 }

outlet24Ctrl OBJECT-TYPE
    SYNTAX Integer32 (0..1)
    MAX-ACCESS read-write
    STATUS current
    DESCRIPTION
        "Outlet24 power state, 0=OFF, 1=ON."
    ::= { receptacleControl 24 }

receptacleONdelay OBJECT IDENTIFIER ::= { configuration 17 }

outlet1ONdly OBJECT-TYPE
    SYNTAX Integer32 (0..255)
    MAX-ACCESS read-write
    STATUS current
    DESCRIPTION
        "Outlet1 power-on delay in seconds."
    ::= { receptacleONdelay 1 }

outlet2ONdly OBJECT-TYPE
    SYNTAX Integer32 (0..255)
    MAX-ACCESS read-write
    STATUS current
    DESCRIPTION
        "Outlet2 power-on delay in seconds."
    ::= { receptacleONdelay 2 }

outlet3ONdly OBJECT-TYPE
    SYNTAX Integer32 (0..255)
    MAX-ACCESS read-write
    STATUS current
    DESCRIPTION
        "Outlet3 power-on delay in seconds."
    ::= { receptacleONdelay 3 }

outlet4ONdly OBJECT-TYPE
    SYNTAX Integer32 (0..255)
    MAX-ACCESS read-write
    STATUS current
    DESCRIPTION
        "Outlet4 power-on delay in seconds."
    ::= { receptacleONdelay 4 }

outlet5ONdly OBJECT-TYPE
    SYNTAX Integer32 (0..255)
    MAX-ACCESS read-write
    STATUS current
    DESCRIPTION
        "Outlet5 power-on delay in seconds."
    ::= { receptacleONdelay 5 }

outlet6ONdly OBJECT-TYPE
    SYNTAX Integer32 (0..255)
    MAX-ACCESS read-write
    STATUS current
    DESCRIPTION
        "Outlet6 power-on delay in seconds."
    ::= { receptacleONdelay 6 }

outlet7ONdly OBJECT-TYPE
    SYNTAX Integer32 (0..255)
    MAX-ACCESS read-write
    STATUS current
    DESCRIPTION
        "Outlet7 power-on delay in seconds."
    ::= { receptacleONdelay 7 }

outlet8ONdly OBJECT-TYPE
    SYNTAX Integer32 (0..255)
    MAX-ACCESS read-write
    STATUS current
    DESCRIPTION
        "Outlet8 power-on delay in seconds."
    ::= { receptacleONdelay 8 }

outlet9ONdly OBJECT-TYPE
    SYNTAX Integer32 (0..255)
    MAX-ACCESS read-write
    STATUS current
    DESCRIPTION
        "Outlet9 power-on delay in seconds."
    ::= { receptacleONdelay 9 }

outlet10ONdly OBJECT-TYPE
    SYNTAX Integer32 (0..255)
    MAX-ACCESS read-write
    STATUS current
    DESCRIPTION
        "Outlet10 power-on delay in seconds."
    ::= { receptacleONdelay 10 }

outlet11ONdly OBJECT-TYPE
    SYNTAX Integer32 (0..255)
    MAX-ACCESS read-write
    STATUS current
    DESCRIPTION
        "Outlet11 power-on delay in seconds."
    ::= { receptacleONdelay 11 }

outlet12ONdly OBJECT-TYPE
    SYNTAX Integer32 (0..255)
    MAX-ACCESS read-write
    STATUS current
    DESCRIPTION
        "Outlet12 power-on delay in seconds."
    ::= { receptacleONdelay 12 }

outlet13ONdly OBJECT-TYPE
    SYNTAX Integer32 (0..255)
    MAX-ACCESS read-write
    STATUS current
    DESCRIPTION
        "Outlet13 power-on delay in seconds."
    ::= { receptacleONdelay 13 }

outlet14ONdly OBJECT-TYPE
    SYNTAX Integer32 (0..255)
    MAX-ACCESS read-write
    STATUS current
    DESCRIPTION
        "Outlet14 power-on delay in seconds."
    ::= { receptacleONdelay 14 }

outlet15ONdly OBJECT-TYPE
    SYNTAX Integer32 (0..255)
    MAX-ACCESS read-write
    STATUS current
    DESCRIPTION
        "Outlet15 power-on delay in seconds."
    ::= { receptacleONdelay 15 }

outlet16ONdly OBJECT-TYPE
    SYNTAX Integer32 (0..255)
    MAX-ACCESS read-write
    STATUS current
    DESCRIPTION
        "Outlet16 power-on delay in seconds."
    ::= { receptacleONdelay 16 }

outlet17ONdly OBJECT-TYPE
    SYNTAX Integer32 (0..255)
    MAX-ACCESS read-write
    STATUS current
    DESCRIPTION
        "Outlet17 power-on delay in seconds."
    ::= { receptacleONdelay 17 }

outlet18ONdly OBJECT-TYPE
    SYNTAX Integer32 (0..255)
    MAX-ACCESS read-write
    STATUS current
    DESCRIPTION
        "Outlet18 power-on delay in seconds."
    ::= { receptacleONdelay 18 }

outlet19ONdly OBJECT-TYPE
    SYNTAX Integer32 (0..255)
    MAX-ACCESS read-write
    STATUS current
    DESCRIPTION
        "Outlet19 power-on delay in seconds."
    ::= { receptacleONdelay 19 }

outlet20ONdly OBJECT-TYPE
    SYNTAX Integer32 (0..255)
    MAX-ACCESS read-write
    STATUS current
    DESCRIPTION
        "Outlet20 power-on delay in seconds."
    ::= { receptacleONdelay 20 }

outlet21ONdly OBJECT-TYPE
    SYNTAX Integer32 (0..255)
    MAX-ACCESS read-write
    STATUS current
    DESCRIPTION
        "Outlet21 power-on delay in seconds."
    ::= { receptacleONdelay 21 }

outlet22ONdly OBJECT-TYPE
    SYNTAX Integer32 (0..255)
    MAX-ACCESS read-write
    STATUS current
    DESCRIPTION
        "Outlet22 power-on delay in seconds."
    ::= { receptacleONdelay 22 }

outlet23ONdly OBJECT-TYPE
    SYNTAX Integer32 (0..255)
    MAX-ACCESS read-write
    STATUS current
    DESCRIPTION
        "Outlet23 power-on delay in seconds."
    ::= { receptacleONdelay 23 }

outlet24ONdly OBJECT-TYPE
    SYNTAX Integer32 (0..255)
    MAX-ACCESS read-write
    STATUS current
    DESCRIPTION
        "Outlet24 power-on delay in seconds."
    ::= { receptacleONdelay 24 }

receptacleResetDelay OBJECT IDENTIFIER ::= { configuration 18 }

outlet1RESdly OBJECT-TYPE
    SYNTAX Integer32 (0..255)
    MAX-ACCESS read-write
    STATUS current
    DESCRIPTION
        "Outlet1 reset delay in seconds."
    ::= { receptacleResetDelay 1 }

outlet2RESdly OBJECT-TYPE
    SYNTAX Integer32 (0..255)
    MAX-ACCESS read-write
    STATUS current
    DESCRIPTION
        "Outlet2 reset delay in seconds."
    ::= { receptacleResetDelay 2 }

outlet3RESdly OBJECT-TYPE
    SYNTAX Integer32 (0..255)
    MAX-ACCESS read-write
    STATUS current
    DESCRIPTION
        "Outlet3 reset delay in seconds."
    ::= { receptacleResetDelay 3 }

outlet4RESdly OBJECT-TYPE
    SYNTAX Integer32 (0..255)
    MAX-ACCESS read-write
    STATUS current
    DESCRIPTION
        "Outlet4 reset delay in seconds."
    ::= { receptacleResetDelay 4 }

outlet5RESdly OBJECT-TYPE
    SYNTAX Integer32 (0..255)
    MAX-ACCESS read-write
    STATUS current
    DESCRIPTION
        "Outlet5 reset delay in seconds."
    ::= { receptacleResetDelay 5 }

outlet6RESdly OBJECT-TYPE
    SYNTAX Integer32 (0..255)
    MAX-ACCESS read-write
    STATUS current
    DESCRIPTION
        "Outlet6 reset delay in seconds."
    ::= { receptacleResetDelay 6 }

outlet7RESdly OBJECT-TYPE
    SYNTAX Integer32 (0..255)
    MAX-ACCESS read-write
    STATUS current
    DESCRIPTION
        "Outlet7 reset delay in seconds."
    ::= { receptacleResetDelay 7 }

outlet8RESdly OBJECT-TYPE
    SYNTAX Integer32 (0..255)
    MAX-ACCESS read-write
    STATUS current
    DESCRIPTION
        "Outlet8 reset delay in seconds."
    ::= { receptacleResetDelay 8 }

outlet9RESdly OBJECT-TYPE
    SYNTAX Integer32 (0..255)
    MAX-ACCESS read-write
    STATUS current
    DESCRIPTION
        "Outlet9 reset delay in seconds."
    ::= { receptacleResetDelay 9 }

outlet10RESdly OBJECT-TYPE
    SYNTAX Integer32 (0..255)
    MAX-ACCESS read-write
    STATUS current
    DESCRIPTION
        "Outlet10 reset delay in seconds."
    ::= { receptacleResetDelay 10 }

outlet11RESdly OBJECT-TYPE
    SYNTAX Integer32 (0..255)
    MAX-ACCESS read-write
    STATUS current
    DESCRIPTION
        "Outlet11 reset delay in seconds."
    ::= { receptacleResetDelay 11 }

outlet12RESdly OBJECT-TYPE
    SYNTAX Integer32 (0..255)
    MAX-ACCESS read-write
    STATUS current
    DESCRIPTION
        "Outlet12 reset delay in seconds."
    ::= { receptacleResetDelay 12 }

outlet13RESdly OBJECT-TYPE
    SYNTAX Integer32 (0..255)
    MAX-ACCESS read-write
    STATUS current
    DESCRIPTION
        "Outlet13 reset delay in seconds."
    ::= { receptacleResetDelay 13 }

outlet14RESdly OBJECT-TYPE
    SYNTAX Integer32 (0..255)
    MAX-ACCESS read-write
    STATUS current
    DESCRIPTION
        "Outlet14 reset delay in seconds."
    ::= { receptacleResetDelay 14 }

outlet15RESdly OBJECT-TYPE
    SYNTAX Integer32 (0..255)
    MAX-ACCESS read-write
    STATUS current
    DESCRIPTION
        "Outlet15 reset delay in seconds."
    ::= { receptacleResetDelay 15 }

outlet16RESdly OBJECT-TYPE
    SYNTAX Integer32 (0..255)
    MAX-ACCESS read-write
    STATUS current
    DESCRIPTION
        "Outlet16 reset delay in seconds."
    ::= { receptacleResetDelay 16 }

outlet17RESdly OBJECT-TYPE
    SYNTAX Integer32 (0..255)
    MAX-ACCESS read-write
    STATUS current
    DESCRIPTION
        "Outlet17 reset delay in seconds."
    ::= { receptacleResetDelay 17 }

outlet18RESdly OBJECT-TYPE
    SYNTAX Integer32 (0..255)
    MAX-ACCESS read-write
    STATUS current
    DESCRIPTION
        "Outlet18 reset delay in seconds."
    ::= { receptacleResetDelay 18 }

outlet19RESdly OBJECT-TYPE
    SYNTAX Integer32 (0..255)
    MAX-ACCESS read-write
    STATUS current
    DESCRIPTION
        "Outlet19 reset delay in seconds."
    ::= { receptacleResetDelay 19 }

outlet20RESdly OBJECT-TYPE
    SYNTAX Integer32 (0..255)
    MAX-ACCESS read-write
    STATUS current
    DESCRIPTION
        "Outlet20 reset delay in seconds."
    ::= { receptacleResetDelay 20 }

outlet21RESdly OBJECT-TYPE
    SYNTAX Integer32 (0..255)
    MAX-ACCESS read-write
    STATUS current
    DESCRIPTION
        "Outlet21 reset delay in seconds."
    ::= { receptacleResetDelay 21 }

outlet22RESdly OBJECT-TYPE
    SYNTAX Integer32 (0..255)
    MAX-ACCESS read-write
    STATUS current
    DESCRIPTION
        "Outlet22 reset delay in seconds."
    ::= { receptacleResetDelay 22 }

outlet23RESdly OBJECT-TYPE
    SYNTAX Integer32 (0..255)
    MAX-ACCESS read-write
    STATUS current
    DESCRIPTION
        "Outlet23 reset delay in seconds."
    ::= { receptacleResetDelay 23 }

outlet24RESdly OBJECT-TYPE
    SYNTAX Integer32 (0..255)
    MAX-ACCESS read-write
    STATUS current
    DESCRIPTION
        "Outlet24 reset delay in seconds."
    ::= { receptacleResetDelay 24 }

maxCurrentLimits OBJECT IDENTIFIER ::= { configuration 19 }

xy1MaxCurr OBJECT-TYPE
    SYNTAX Integer32 (0..2000)
    MAX-ACCESS read-write
    STATUS current
    DESCRIPTION
        "Maximum current that XY1 can draw in 1/100 Amps, 0=ignore."
    ::= { maxCurrentLimits 1 }

yz1MaxCurr OBJECT-TYPE
    SYNTAX Integer32 (0..2000)
    MAX-ACCESS read-write
    STATUS current
    DESCRIPTION
        "Maximum current that YZ1 can draw in 1/100 Amps, 0=ignore."
    ::= { maxCurrentLimits 2 }

zx1MaxCurr OBJECT-TYPE
    SYNTAX Integer32 (0..2000)
    MAX-ACCESS read-write
    STATUS current
    DESCRIPTION
        "Maximum current that ZX1 can draw in 1/100 Amps, 0=ignore."
    ::= { maxCurrentLimits 3 }

xy2MaxCurr OBJECT-TYPE
    SYNTAX Integer32 (0..2000)
    MAX-ACCESS read-write
    STATUS current
    DESCRIPTION
        "Maximum current that XY2 can draw in 1/100 Amps, 0=ignore."
    ::= { maxCurrentLimits 4 }

yz2MaxCurr OBJECT-TYPE
    SYNTAX Integer32 (0..2000)
    MAX-ACCESS read-write
    STATUS current
    DESCRIPTION
        "Maximum current that YZ2 can draw in 1/100 Amps, 0=ignore."
    ::= { maxCurrentLimits 5 }

zx2MaxCurr OBJECT-TYPE
    SYNTAX Integer32 (0..2000)
    MAX-ACCESS read-write
    STATUS current
    DESCRIPTION
        "Maximum current that ZX2 can draw in 1/100 Amps, 0=ignore."
    ::= { maxCurrentLimits 6 }

minCurrentLimits OBJECT IDENTIFIER ::= { configuration 20 }

xy1MinCurr OBJECT-TYPE
    SYNTAX Integer32 (0..2000)
    MAX-ACCESS read-write
    STATUS current
    DESCRIPTION
        "Minimum current that XY1 should draw in 1/100 Amps, 0=ignore."
    ::= { minCurrentLimits 1 }

yz1MinCurr OBJECT-TYPE
    SYNTAX Integer32 (0..2000)
    MAX-ACCESS read-write
    STATUS current
    DESCRIPTION
        "Minimum current that YZ1 should draw in 1/100 Amps, 0=ignore."
    ::= { minCurrentLimits 2 }

zx1MinCurr OBJECT-TYPE
    SYNTAX Integer32 (0..2000)
    MAX-ACCESS read-write
    STATUS current
    DESCRIPTION
        "Minimum current that ZX1 should draw in 1/100 Amps, 0=ignore."
    ::= { minCurrentLimits 3 }

xy2MinCurr OBJECT-TYPE
    SYNTAX Integer32 (0..2000)
    MAX-ACCESS read-write
    STATUS current
    DESCRIPTION
        "Minimum current that XY2 should draw in 1/100 Amps, 0=ignore."
    ::= { minCurrentLimits 4 }

yz2MinCurr OBJECT-TYPE
    SYNTAX Integer32 (0..2000)
    MAX-ACCESS read-write
    STATUS current
    DESCRIPTION
        "Minimum current that YZ2 should draw in 1/100 Amps, 0=ignore."
    ::= { minCurrentLimits 5 }

zx2MinCurr OBJECT-TYPE
    SYNTAX Integer32 (0..2000)
    MAX-ACCESS read-write
    STATUS current
    DESCRIPTION
        "Minimum current that ZX2 should draw in 1/100 Amps, 0=ignore."
    ::= { minCurrentLimits 6 }

warnHiCurrentLimits OBJECT IDENTIFIER ::= { configuration 21 }

xy1WarnHiCurr OBJECT-TYPE
    SYNTAX Integer32 (0..2000)
    MAX-ACCESS read-write
    STATUS current
    DESCRIPTION
        "Warning upper current limit that XY1 can draw in 1/100 Amps, 0=ignore."
    ::= { warnHiCurrentLimits 1 }

yz1WarnHiCurr OBJECT-TYPE
    SYNTAX Integer32 (0..2000)
    MAX-ACCESS read-write
    STATUS current
    DESCRIPTION
        "Warning upper current limit that YZ1 can draw in 1/100 Amps, 0=ignore."
    ::= { warnHiCurrentLimits 2 }

zx1WarnHiCurr OBJECT-TYPE
    SYNTAX Integer32 (0..2000)
    MAX-ACCESS read-write
    STATUS current
    DESCRIPTION
        "Warning upper current limit that ZX1 can draw in 1/100 Amps, 0=ignore."
    ::= { warnHiCurrentLimits 3 }

xy2WarnHiCurr OBJECT-TYPE
    SYNTAX Integer32 (0..2000)
    MAX-ACCESS read-write
    STATUS current
    DESCRIPTION
        "Warning upper current limit that XY2 can draw in 1/100 Amps, 0=ignore."
    ::= { warnHiCurrentLimits 4 }

yz2WarnHiCurr OBJECT-TYPE
    SYNTAX Integer32 (0..2000)
    MAX-ACCESS read-write
    STATUS current
    DESCRIPTION
        "Warning upper current limit that YZ2 can draw in 1/100 Amps, 0=ignore."
    ::= { warnHiCurrentLimits 5 }

zx2WarnHiCurr OBJECT-TYPE
    SYNTAX Integer32 (0..2000)
    MAX-ACCESS read-write
    STATUS current
    DESCRIPTION
        "Warning upper current limit that ZX2 can draw in 1/100 Amps, 0=ignore."
    ::= { warnHiCurrentLimits 6 }

warnLoCurrentLimits OBJECT IDENTIFIER ::= { configuration 22 }

xy1WarnLoCurr OBJECT-TYPE
    SYNTAX Integer32 (0..2000)
    MAX-ACCESS read-write
    STATUS current
    DESCRIPTION
        "Warning lower current limit that XY1 can draw in 1/100 Amps, 0=ignore."
    ::= { warnLoCurrentLimits 1 }

yz1WarnLoCurr OBJECT-TYPE
    SYNTAX Integer32 (0..2000)
    MAX-ACCESS read-write
    STATUS current
    DESCRIPTION
        "Warning lower current limit that YZ1 can draw in 1/100 Amps, 0=ignore."
    ::= { warnLoCurrentLimits 2 }

zx1WarnLoCurr OBJECT-TYPE
    SYNTAX Integer32 (0..2000)
    MAX-ACCESS read-write
    STATUS current
    DESCRIPTION
        "Warning lower current limit that ZX1 can draw in 1/100 Amps, 0=ignore."
    ::= { warnLoCurrentLimits 3 }

xy2WarnLoCurr OBJECT-TYPE
    SYNTAX Integer32 (0..2000)
    MAX-ACCESS read-write
    STATUS current
    DESCRIPTION
        "Warning lower current limit that XY2 can draw in 1/100 Amps, 0=ignore."
    ::= { warnLoCurrentLimits 4 }

yz2WarnLoCurr OBJECT-TYPE
    SYNTAX Integer32 (0..2000)
    MAX-ACCESS read-write
    STATUS current
    DESCRIPTION
        "Warning lower current limit that YZ2 can draw in 1/100 Amps, 0=ignore."
    ::= { warnLoCurrentLimits 5 }

zx2WarnLoCurr OBJECT-TYPE
    SYNTAX Integer32 (0..2000)
    MAX-ACCESS read-write
    STATUS current
    DESCRIPTION
        "Warning lower current limit that ZX2 can draw in 1/100 Amps, 0=ignore."
    ::= { warnLoCurrentLimits 6 }

maxVoltageLimits OBJECT IDENTIFIER ::= { configuration 24 }

xy1MaxVolt OBJECT-TYPE
    SYNTAX Integer32 (0..3120)
    MAX-ACCESS read-write
    STATUS current
    DESCRIPTION
        "Maximum voltage that XY1 can reach up to in volts, 0=ignore."
    ::= { maxVoltageLimits 1 }

yz1MaxVolt OBJECT-TYPE
    SYNTAX Integer32 (0..3120)
    MAX-ACCESS read-write
    STATUS current
    DESCRIPTION
        "Maximum voltage that YZ1 can reach up to in volts, 0=ignore."
    ::= { maxVoltageLimits 2 }

zx1MaxVolt OBJECT-TYPE
    SYNTAX Integer32 (0..3120)
    MAX-ACCESS read-write
    STATUS current
    DESCRIPTION
        "Maximum voltage that ZX1 can reach up to in volts, 0=ignore."
    ::= { maxVoltageLimits 3 }

xy2MaxVolt OBJECT-TYPE
    SYNTAX Integer32 (0..3120)
    MAX-ACCESS read-write
    STATUS current
    DESCRIPTION
        "Maximum voltage that XY2 can reach up to in volts, 0=ignore."
    ::= { maxVoltageLimits 4 }

yz2MaxVolt OBJECT-TYPE
    SYNTAX Integer32 (0..3120)
    MAX-ACCESS read-write
    STATUS current
    DESCRIPTION
        "Maximum voltage that YZ2 can reach up to in volts, 0=ignore."
    ::= { maxVoltageLimits 5 }

zx2MaxVolt OBJECT-TYPE
    SYNTAX Integer32 (0..3120)
    MAX-ACCESS read-write
    STATUS current
    DESCRIPTION
        "Maximum voltage that ZX2 can reach up to in volts, 0=ignore."
    ::= { maxVoltageLimits 6 }

minVoltageLimits OBJECT IDENTIFIER ::= { configuration 25 }

xy1MinVolt OBJECT-TYPE
    SYNTAX Integer32 (0..3120)
    MAX-ACCESS read-write
    STATUS current
    DESCRIPTION
        "Minimum voltage that XY1 can sag in volts, 0=ignore."
    ::= { minVoltageLimits 1 }

yz1MinVolt OBJECT-TYPE
    SYNTAX Integer32 (0..3120)
    MAX-ACCESS read-write
    STATUS current
    DESCRIPTION
        "Minimum voltage that YZ1 can sag in volts, 0=ignore."
    ::= { minVoltageLimits 2 }

zx1MinVolt OBJECT-TYPE
    SYNTAX Integer32 (0..3120)
    MAX-ACCESS read-write
    STATUS current
    DESCRIPTION
        "Minimum voltage that ZX1 can sag in volts, 0=ignore."
    ::= { minVoltageLimits 3 }

xy2MinVolt OBJECT-TYPE
    SYNTAX Integer32 (0..3120)
    MAX-ACCESS read-write
    STATUS current
    DESCRIPTION
        "Minimum voltage that XY2 can sag in volts, 0=ignore."
    ::= { minVoltageLimits 4 }

yz2MinVolt OBJECT-TYPE
    SYNTAX Integer32 (0..3120)
    MAX-ACCESS read-write
    STATUS current
    DESCRIPTION
        "Minimum voltage that YZ2 can sag in volts, 0=ignore."
    ::= { minVoltageLimits 5 }

zx2MinVolt OBJECT-TYPE
    SYNTAX Integer32 (0..3120)
    MAX-ACCESS read-write
    STATUS current
    DESCRIPTION
        "Minimum voltage that ZX2 can sag in volts, 0=ignore."
    ::= { minVoltageLimits 6 }

warnHiVoltageLimits OBJECT IDENTIFIER ::= { configuration 26 }

xy1WarnHiVolt OBJECT-TYPE
    SYNTAX Integer32 (0..3120)
    MAX-ACCESS read-write
    STATUS current
    DESCRIPTION
        "Warning High voltage in volts that XY1 can reach before triggering warning notifications, 0=ignore."
    ::= { warnHiVoltageLimits 1 }

yz1WarnHiVolt OBJECT-TYPE
    SYNTAX Integer32 (0..3120)
    MAX-ACCESS read-write
    STATUS current
    DESCRIPTION
        "Warning High voltage in volts that YZ1 can reach before triggering warning notifications, 0=ignore."
    ::= { warnHiVoltageLimits 2 }

zx1WarnHiVolt OBJECT-TYPE
    SYNTAX Integer32 (0..3120)
    MAX-ACCESS read-write
    STATUS current
    DESCRIPTION
        "Warning High voltage in volts that ZX1 can reach before triggering warning notifications, 0=ignore."
    ::= { warnHiVoltageLimits 3 }

xy2WarnHiVolt OBJECT-TYPE
    SYNTAX Integer32 (0..3120)
    MAX-ACCESS read-write
    STATUS current
    DESCRIPTION
        "Warning High voltage in volts that XY2 can reach before triggering warning notifications, 0=ignore."
    ::= { warnHiVoltageLimits 4 }

yz2WarnHiVolt OBJECT-TYPE
    SYNTAX Integer32 (0..3120)
    MAX-ACCESS read-write
    STATUS current
    DESCRIPTION
        "Warning High voltage in volts that YZ2 can reach before triggering warning notifications, 0=ignore."
    ::= { warnHiVoltageLimits 5 }

zx2WarnHiVolt OBJECT-TYPE
    SYNTAX Integer32 (0..3120)
    MAX-ACCESS read-write
    STATUS current
    DESCRIPTION
        "Warning High voltage in volts that ZX2 can reach before triggering warning notifications, 0=ignore."
    ::= { warnHiVoltageLimits 6 }

warnLoVoltageLimits OBJECT IDENTIFIER ::= { configuration 27 }

xy1WarnLoVolt OBJECT-TYPE
    SYNTAX Integer32 (0..3120)
    MAX-ACCESS read-write
    STATUS current
    DESCRIPTION
        "Warning Low voltage in volts that XY1 can sag before triggering notifications, 0=ignore."
    ::= { warnLoVoltageLimits 1 }

yz1WarnLoVolt OBJECT-TYPE
    SYNTAX Integer32 (0..3120)
    MAX-ACCESS read-write
    STATUS current
    DESCRIPTION
        "Warning Low voltage in volts that YZ1 can sag before triggering notifications, 0=ignore."
    ::= { warnLoVoltageLimits 2 }

zx1WarnLoVolt OBJECT-TYPE
    SYNTAX Integer32 (0..3120)
    MAX-ACCESS read-write
    STATUS current
    DESCRIPTION
        "Warning Low voltage in volts that ZX1 can sag before triggering notifications, 0=ignore."
    ::= { warnLoVoltageLimits 3 }

xy2WarnLoVolt OBJECT-TYPE
    SYNTAX Integer32 (0..3120)
    MAX-ACCESS read-write
    STATUS current
    DESCRIPTION
        "Warning Low voltage in volts that XY2 can sag before triggering notifications, 0=ignore."
    ::= { warnLoVoltageLimits 4 }

yz2WarnLoVolt OBJECT-TYPE
    SYNTAX Integer32 (0..3120)
    MAX-ACCESS read-write
    STATUS current
    DESCRIPTION
        "Warning Low voltage in volts that YZ2 can sag before triggering notifications, 0=ignore."
    ::= { warnLoVoltageLimits 5 }

zx2WarnLoVolt OBJECT-TYPE
    SYNTAX Integer32 (0..3120)
    MAX-ACCESS read-write
    STATUS current
    DESCRIPTION
        "Warning Low voltage in volts that ZX2 can sag before triggering notifications, 0=ignore."
    ::= { warnLoVoltageLimits 6 }

receptacleMaxCurrent OBJECT IDENTIFIER ::= { configuration 28 }

outlet1MaxCurr OBJECT-TYPE
    SYNTAX Integer32 (0..2000)
    MAX-ACCESS read-write
    STATUS current
    DESCRIPTION
        "Outlet1 maximum current in 1/100 Amps."
    ::= { receptacleMaxCurrent 1 }

outlet2MaxCurr OBJECT-TYPE
    SYNTAX Integer32 (0..2000)
    MAX-ACCESS read-write
    STATUS current
    DESCRIPTION
        "Outlet2 maximum current in 1/100 Amps."
    ::= { receptacleMaxCurrent 2 }

outlet3MaxCurr OBJECT-TYPE
    SYNTAX Integer32 (0..2000)
    MAX-ACCESS read-write
    STATUS current
    DESCRIPTION
        "Outlet3 maximum current in 1/100 Amps."
    ::= { receptacleMaxCurrent 3 }

outlet4MaxCurr OBJECT-TYPE
    SYNTAX Integer32 (0..2000)
    MAX-ACCESS read-write
    STATUS current
    DESCRIPTION
        "Outlet4 maximum current in 1/100 Amps."
    ::= { receptacleMaxCurrent 4 }

outlet5MaxCurr OBJECT-TYPE
    SYNTAX Integer32 (0..2000)
    MAX-ACCESS read-write
    STATUS current
    DESCRIPTION
        "Outlet5 maximum current in 1/100 Amps."
    ::= { receptacleMaxCurrent 5 }

outlet6MaxCurr OBJECT-TYPE
    SYNTAX Integer32 (0..2000)
    MAX-ACCESS read-write
    STATUS current
    DESCRIPTION
        "Outlet6 maximum current in 1/100 Amps."
    ::= { receptacleMaxCurrent 6 }

outlet7MaxCurr OBJECT-TYPE
    SYNTAX Integer32 (0..2000)
    MAX-ACCESS read-write
    STATUS current
    DESCRIPTION
        "Outlet7 maximum current in 1/100 Amps."
    ::= { receptacleMaxCurrent 7 }

outlet8MaxCurr OBJECT-TYPE
    SYNTAX Integer32 (0..2000)
    MAX-ACCESS read-write
    STATUS current
    DESCRIPTION
        "Outlet8 maximum current in 1/100 Amps."
    ::= { receptacleMaxCurrent 8 }

outlet9MaxCurr OBJECT-TYPE
    SYNTAX Integer32 (0..2000)
    MAX-ACCESS read-write
    STATUS current
    DESCRIPTION
        "Outlet9 maximum current in 1/100 Amps."
    ::= { receptacleMaxCurrent 9 }

outlet10MaxCurr OBJECT-TYPE
    SYNTAX Integer32 (0..2000)
    MAX-ACCESS read-write
    STATUS current
    DESCRIPTION
        "Outlet10 maximum current in 1/100 Amps."
    ::= { receptacleMaxCurrent 10 }

outlet11MaxCurr OBJECT-TYPE
    SYNTAX Integer32 (0..2000)
    MAX-ACCESS read-write
    STATUS current
    DESCRIPTION
        "Outlet11 maximum current in 1/100 Amps."
    ::= { receptacleMaxCurrent 11 }

outlet12MaxCurr OBJECT-TYPE
    SYNTAX Integer32 (0..2000)
    MAX-ACCESS read-write
    STATUS current
    DESCRIPTION
        "Outlet12 maximum current in 1/100 Amps."
    ::= { receptacleMaxCurrent 12 }

outlet13MaxCurr OBJECT-TYPE
    SYNTAX Integer32 (0..2000)
    MAX-ACCESS read-write
    STATUS current
    DESCRIPTION
        "Outlet13 maximum current in 1/100 Amps."
    ::= { receptacleMaxCurrent 13 }

outlet14MaxCurr OBJECT-TYPE
    SYNTAX Integer32 (0..2000)
    MAX-ACCESS read-write
    STATUS current
    DESCRIPTION
        "Outlet14 maximum current in 1/100 Amps."
    ::= { receptacleMaxCurrent 14 }

outlet15MaxCurr OBJECT-TYPE
    SYNTAX Integer32 (0..2000)
    MAX-ACCESS read-write
    STATUS current
    DESCRIPTION
        "Outlet15 maximum current in 1/100 Amps."
    ::= { receptacleMaxCurrent 15 }

outlet16MaxCurr OBJECT-TYPE
    SYNTAX Integer32 (0..2000)
    MAX-ACCESS read-write
    STATUS current
    DESCRIPTION
        "Outlet16 maximum current in 1/100 Amps."
    ::= { receptacleMaxCurrent 16 }

outlet17MaxCurr OBJECT-TYPE
    SYNTAX Integer32 (0..2000)
    MAX-ACCESS read-write
    STATUS current
    DESCRIPTION
        "Outlet17 maximum current in 1/100 Amps."
    ::= { receptacleMaxCurrent 17 }

outlet18MaxCurr OBJECT-TYPE
    SYNTAX Integer32 (0..2000)
    MAX-ACCESS read-write
    STATUS current
    DESCRIPTION
        "Outlet18 maximum current in 1/100 Amps."
    ::= { receptacleMaxCurrent 18 }

outlet19MaxCurr OBJECT-TYPE
    SYNTAX Integer32 (0..2000)
    MAX-ACCESS read-write
    STATUS current
    DESCRIPTION
        "Outlet19 maximum current in 1/100 Amps."
    ::= { receptacleMaxCurrent 19 }

outlet20MaxCurr OBJECT-TYPE
    SYNTAX Integer32 (0..2000)
    MAX-ACCESS read-write
    STATUS current
    DESCRIPTION
        "Outlet20 maximum current in 1/100 Amps."
    ::= { receptacleMaxCurrent 20 }

outlet21MaxCurr OBJECT-TYPE
    SYNTAX Integer32 (0..2000)
    MAX-ACCESS read-write
    STATUS current
    DESCRIPTION
        "Outlet21 maximum current in 1/100 Amps."
    ::= { receptacleMaxCurrent 21 }

outlet22MaxCurr OBJECT-TYPE
    SYNTAX Integer32 (0..2000)
    MAX-ACCESS read-write
    STATUS current
    DESCRIPTION
        "Outlet22 maximum current in 1/100 Amps."
    ::= { receptacleMaxCurrent 22 }

outlet23MaxCurr OBJECT-TYPE
    SYNTAX Integer32 (0..2000)
    MAX-ACCESS read-write
    STATUS current
    DESCRIPTION
        "Outlet23 maximum current in 1/100 Amps."
    ::= { receptacleMaxCurrent 23 }

outlet24MaxCurr OBJECT-TYPE
    SYNTAX Integer32 (0..2000)
    MAX-ACCESS read-write
    STATUS current
    DESCRIPTION
        "Outlet24 maximum current in 1/100 Amps."
    ::= { receptacleMaxCurrent 24 }

receptacleMinCurrent OBJECT IDENTIFIER ::= { configuration 29 }

outlet1MinCurr OBJECT-TYPE
    SYNTAX Integer32 (0..2000)
    MAX-ACCESS read-write
    STATUS current
    DESCRIPTION
        "Outlet1 minimum current in 1/100 Amps."
    ::= { receptacleMinCurrent 1 }

outlet2MinCurr OBJECT-TYPE
    SYNTAX Integer32 (0..2000)
    MAX-ACCESS read-write
    STATUS current
    DESCRIPTION
        "Outlet2 minimum current in 1/100 Amps."
    ::= { receptacleMinCurrent 2 }

outlet3MinCurr OBJECT-TYPE
    SYNTAX Integer32 (0..2000)
    MAX-ACCESS read-write
    STATUS current
    DESCRIPTION
        "Outlet3 minimum current in 1/100 Amps."
    ::= { receptacleMinCurrent 3 }

outlet4MinCurr OBJECT-TYPE
    SYNTAX Integer32 (0..2000)
    MAX-ACCESS read-write
    STATUS current
    DESCRIPTION
        "Outlet4 minimum current in 1/100 Amps."
    ::= { receptacleMinCurrent 4 }

outlet5MinCurr OBJECT-TYPE
    SYNTAX Integer32 (0..2000)
    MAX-ACCESS read-write
    STATUS current
    DESCRIPTION
        "Outlet5 minimum current in 1/100 Amps."
    ::= { receptacleMinCurrent 5 }

outlet6MinCurr OBJECT-TYPE
    SYNTAX Integer32 (0..2000)
    MAX-ACCESS read-write
    STATUS current
    DESCRIPTION
        "Outlet6 minimum current in 1/100 Amps."
    ::= { receptacleMinCurrent 6 }

outlet7MinCurr OBJECT-TYPE
    SYNTAX Integer32 (0..2000)
    MAX-ACCESS read-write
    STATUS current
    DESCRIPTION
        "Outlet7 minimum current in 1/100 Amps."
    ::= { receptacleMinCurrent 7 }

outlet8MinCurr OBJECT-TYPE
    SYNTAX Integer32 (0..2000)
    MAX-ACCESS read-write
    STATUS current
    DESCRIPTION
        "Outlet8 minimum current in 1/100 Amps."
    ::= { receptacleMinCurrent 8 }

outlet9MinCurr OBJECT-TYPE
    SYNTAX Integer32 (0..2000)
    MAX-ACCESS read-write
    STATUS current
    DESCRIPTION
        "Outlet9 minimum current in 1/100 Amps."
    ::= { receptacleMinCurrent 9 }

outlet10MinCurr OBJECT-TYPE
    SYNTAX Integer32 (0..2000)
    MAX-ACCESS read-write
    STATUS current
    DESCRIPTION
        "Outlet10 minimum current in 1/100 Amps."
    ::= { receptacleMinCurrent 10 }

outlet11MinCurr OBJECT-TYPE
    SYNTAX Integer32 (0..2000)
    MAX-ACCESS read-write
    STATUS current
    DESCRIPTION
        "Outlet11 minimum current in 1/100 Amps."
    ::= { receptacleMinCurrent 11 }

outlet12MinCurr OBJECT-TYPE
    SYNTAX Integer32 (0..2000)
    MAX-ACCESS read-write
    STATUS current
    DESCRIPTION
        "Outlet12 minimum current in 1/100 Amps."
    ::= { receptacleMinCurrent 12 }

outlet13MinCurr OBJECT-TYPE
    SYNTAX Integer32 (0..2000)
    MAX-ACCESS read-write
    STATUS current
    DESCRIPTION
        "Outlet13 minimum current in 1/100 Amps."
    ::= { receptacleMinCurrent 13 }

outlet14MinCurr OBJECT-TYPE
    SYNTAX Integer32 (0..2000)
    MAX-ACCESS read-write
    STATUS current
    DESCRIPTION
        "Outlet14 minimum current in 1/100 Amps."
    ::= { receptacleMinCurrent 14 }

outlet15MinCurr OBJECT-TYPE
    SYNTAX Integer32 (0..2000)
    MAX-ACCESS read-write
    STATUS current
    DESCRIPTION
        "Outlet15 minimum current in 1/100 Amps."
    ::= { receptacleMinCurrent 15 }

outlet16MinCurr OBJECT-TYPE
    SYNTAX Integer32 (0..2000)
    MAX-ACCESS read-write
    STATUS current
    DESCRIPTION
        "Outlet16 minimum current in 1/100 Amps."
    ::= { receptacleMinCurrent 16 }

outlet17MinCurr OBJECT-TYPE
    SYNTAX Integer32 (0..2000)
    MAX-ACCESS read-write
    STATUS current
    DESCRIPTION
        "Outlet17 minimum current in 1/100 Amps."
    ::= { receptacleMinCurrent 17 }

outlet18MinCurr OBJECT-TYPE
    SYNTAX Integer32 (0..2000)
    MAX-ACCESS read-write
    STATUS current
    DESCRIPTION
        "Outlet18 minimum current in 1/100 Amps."
    ::= { receptacleMinCurrent 18 }

outlet19MinCurr OBJECT-TYPE
    SYNTAX Integer32 (0..2000)
    MAX-ACCESS read-write
    STATUS current
    DESCRIPTION
        "Outlet19 minimum current in 1/100 Amps."
    ::= { receptacleMinCurrent 19 }

outlet20MinCurr OBJECT-TYPE
    SYNTAX Integer32 (0..2000)
    MAX-ACCESS read-write
    STATUS current
    DESCRIPTION
        "Outlet20 minimum current in 1/100 Amps."
    ::= { receptacleMinCurrent 20 }

outlet21MinCurr OBJECT-TYPE
    SYNTAX Integer32 (0..2000)
    MAX-ACCESS read-write
    STATUS current
    DESCRIPTION
        "Outlet21 minimum current in 1/100 Amps."
    ::= { receptacleMinCurrent 21 }

outlet22MinCurr OBJECT-TYPE
    SYNTAX Integer32 (0..2000)
    MAX-ACCESS read-write
    STATUS current
    DESCRIPTION
        "Outlet22 minimum current in 1/100 Amps."
    ::= { receptacleMinCurrent 22 }

outlet23MinCurr OBJECT-TYPE
    SYNTAX Integer32 (0..2000)
    MAX-ACCESS read-write
    STATUS current
    DESCRIPTION
        "Outlet23 minimum current in 1/100 Amps."
    ::= { receptacleMinCurrent 23 }

outlet24MinCurr OBJECT-TYPE
    SYNTAX Integer32 (0..2000)
    MAX-ACCESS read-write
    STATUS current
    DESCRIPTION
        "Outlet24 minimum current in 1/100 Amps."
    ::= { receptacleMinCurrent 24 }

receptacleWarnHiCurrent OBJECT IDENTIFIER ::= { configuration 30 }

outlet1WarnHiCurr OBJECT-TYPE
    SYNTAX Integer32 (0..2000)
    MAX-ACCESS read-write
    STATUS current
    DESCRIPTION
        "Outlet1 warning high current in 1/100 Amps."
    ::= { receptacleWarnHiCurrent 1 }

outlet2WarnHiCurr OBJECT-TYPE
    SYNTAX Integer32 (0..2000)
    MAX-ACCESS read-write
    STATUS current
    DESCRIPTION
        "Outlet2 warning high current in 1/100 Amps."
    ::= { receptacleWarnHiCurrent 2 }

outlet3WarnHiCurr OBJECT-TYPE
    SYNTAX Integer32 (0..2000)
    MAX-ACCESS read-write
    STATUS current
    DESCRIPTION
        "Outlet3 warning high current in 1/100 Amps."
    ::= { receptacleWarnHiCurrent 3 }

outlet4WarnHiCurr OBJECT-TYPE
    SYNTAX Integer32 (0..2000)
    MAX-ACCESS read-write
    STATUS current
    DESCRIPTION
        "Outlet4 warning high current in 1/100 Amps."
    ::= { receptacleWarnHiCurrent 4 }

outlet5WarnHiCurr OBJECT-TYPE
    SYNTAX Integer32 (0..2000)
    MAX-ACCESS read-write
    STATUS current
    DESCRIPTION
        "Outlet5 warning high current in 1/100 Amps."
    ::= { receptacleWarnHiCurrent 5 }

outlet6WarnHiCurr OBJECT-TYPE
    SYNTAX Integer32 (0..2000)
    MAX-ACCESS read-write
    STATUS current
    DESCRIPTION
        "Outlet6 warning high current in 1/100 Amps."
    ::= { receptacleWarnHiCurrent 6 }

outlet7WarnHiCurr OBJECT-TYPE
    SYNTAX Integer32 (0..2000)
    MAX-ACCESS read-write
    STATUS current
    DESCRIPTION
        "Outlet7 warning high current in 1/100 Amps."
    ::= { receptacleWarnHiCurrent 7 }

outlet8WarnHiCurr OBJECT-TYPE
    SYNTAX Integer32 (0..2000)
    MAX-ACCESS read-write
    STATUS current
    DESCRIPTION
        "Outlet8 warning high current in 1/100 Amps."
    ::= { receptacleWarnHiCurrent 8 }

outlet9WarnHiCurr OBJECT-TYPE
    SYNTAX Integer32 (0..2000)
    MAX-ACCESS read-write
    STATUS current
    DESCRIPTION
        "Outlet9 warning high current in 1/100 Amps."
    ::= { receptacleWarnHiCurrent 9 }

outlet10WarnHiCurr OBJECT-TYPE
    SYNTAX Integer32 (0..2000)
    MAX-ACCESS read-write
    STATUS current
    DESCRIPTION
        "Outlet10 warning high current in 1/100 Amps."
    ::= { receptacleWarnHiCurrent 10 }

outlet11WarnHiCurr OBJECT-TYPE
    SYNTAX Integer32 (0..2000)
    MAX-ACCESS read-write
    STATUS current
    DESCRIPTION
        "Outlet11 warning high current in 1/100 Amps."
    ::= { receptacleWarnHiCurrent 11 }

outlet12WarnHiCurr OBJECT-TYPE
    SYNTAX Integer32 (0..2000)
    MAX-ACCESS read-write
    STATUS current
    DESCRIPTION
        "Outlet12 warning high current in 1/100 Amps."
    ::= { receptacleWarnHiCurrent 12 }

outlet13WarnHiCurr OBJECT-TYPE
    SYNTAX Integer32 (0..2000)
    MAX-ACCESS read-write
    STATUS current
    DESCRIPTION
        "Outlet13 warning high current in 1/100 Amps."
    ::= { receptacleWarnHiCurrent 13 }

outlet14WarnHiCurr OBJECT-TYPE
    SYNTAX Integer32 (0..2000)
    MAX-ACCESS read-write
    STATUS current
    DESCRIPTION
        "Outlet14 warning high current in 1/100 Amps."
    ::= { receptacleWarnHiCurrent 14 }

outlet15WarnHiCurr OBJECT-TYPE
    SYNTAX Integer32 (0..2000)
    MAX-ACCESS read-write
    STATUS current
    DESCRIPTION
        "Outlet15 warning high current in 1/100 Amps."
    ::= { receptacleWarnHiCurrent 15 }

outlet16WarnHiCurr OBJECT-TYPE
    SYNTAX Integer32 (0..2000)
    MAX-ACCESS read-write
    STATUS current
    DESCRIPTION
        "Outlet16 warning high current in 1/100 Amps."
    ::= { receptacleWarnHiCurrent 16 }

outlet17WarnHiCurr OBJECT-TYPE
    SYNTAX Integer32 (0..2000)
    MAX-ACCESS read-write
    STATUS current
    DESCRIPTION
        "Outlet17 warning high current in 1/100 Amps."
    ::= { receptacleWarnHiCurrent 17 }

outlet18WarnHiCurr OBJECT-TYPE
    SYNTAX Integer32 (0..2000)
    MAX-ACCESS read-write
    STATUS current
    DESCRIPTION
        "Outlet18 warning high current in 1/100 Amps."
    ::= { receptacleWarnHiCurrent 18 }

outlet19WarnHiCurr OBJECT-TYPE
    SYNTAX Integer32 (0..2000)
    MAX-ACCESS read-write
    STATUS current
    DESCRIPTION
        "Outlet19 warning high current in 1/100 Amps."
    ::= { receptacleWarnHiCurrent 19 }

outlet20WarnHiCurr OBJECT-TYPE
    SYNTAX Integer32 (0..2000)
    MAX-ACCESS read-write
    STATUS current
    DESCRIPTION
        "Outlet20 warning high current in 1/100 Amps."
    ::= { receptacleWarnHiCurrent 20 }

outlet21WarnHiCurr OBJECT-TYPE
    SYNTAX Integer32 (0..2000)
    MAX-ACCESS read-write
    STATUS current
    DESCRIPTION
        "Outlet21 warning high current in 1/100 Amps."
    ::= { receptacleWarnHiCurrent 21 }

outlet22WarnHiCurr OBJECT-TYPE
    SYNTAX Integer32 (0..2000)
    MAX-ACCESS read-write
    STATUS current
    DESCRIPTION
        "Outlet22 warning high current in 1/100 Amps."
    ::= { receptacleWarnHiCurrent 22 }

outlet23WarnHiCurr OBJECT-TYPE
    SYNTAX Integer32 (0..2000)
    MAX-ACCESS read-write
    STATUS current
    DESCRIPTION
        "Outlet23 warning high current in 1/100 Amps."
    ::= { receptacleWarnHiCurrent 23 }

outlet24WarnHiCurr OBJECT-TYPE
    SYNTAX Integer32 (0..2000)
    MAX-ACCESS read-write
    STATUS current
    DESCRIPTION
        "Outlet24 warning high current in 1/100 Amps."
    ::= { receptacleWarnHiCurrent 24 }

receptacleWarnLoCurrent OBJECT IDENTIFIER ::= { configuration 31 }

outlet1WarnLoCurr OBJECT-TYPE
    SYNTAX Integer32 (0..2000)
    MAX-ACCESS read-write
    STATUS current
    DESCRIPTION
        "Outlet1 warning low current in 1/100 Amps."
    ::= { receptacleWarnLoCurrent 1 }

outlet2WarnLoCurr OBJECT-TYPE
    SYNTAX Integer32 (0..2000)
    MAX-ACCESS read-write
    STATUS current
    DESCRIPTION
        "Outlet2 warning low current in 1/100 Amps."
    ::= { receptacleWarnLoCurrent 2 }

outlet3WarnLoCurr OBJECT-TYPE
    SYNTAX Integer32 (0..2000)
    MAX-ACCESS read-write
    STATUS current
    DESCRIPTION
        "Outlet3 warning low current in 1/100 Amps."
    ::= { receptacleWarnLoCurrent 3 }

outlet4WarnLoCurr OBJECT-TYPE
    SYNTAX Integer32 (0..2000)
    MAX-ACCESS read-write
    STATUS current
    DESCRIPTION
        "Outlet4 warning low current in 1/100 Amps."
    ::= { receptacleWarnLoCurrent 4 }

outlet5WarnLoCurr OBJECT-TYPE
    SYNTAX Integer32 (0..2000)
    MAX-ACCESS read-write
    STATUS current
    DESCRIPTION
        "Outlet5 warning low current in 1/100 Amps."
    ::= { receptacleWarnLoCurrent 5 }

outlet6WarnLoCurr OBJECT-TYPE
    SYNTAX Integer32 (0..2000)
    MAX-ACCESS read-write
    STATUS current
    DESCRIPTION
        "Outlet6 warning low current in 1/100 Amps."
    ::= { receptacleWarnLoCurrent 6 }

outlet7WarnLoCurr OBJECT-TYPE
    SYNTAX Integer32 (0..2000)
    MAX-ACCESS read-write
    STATUS current
    DESCRIPTION
        "Outlet7 warning low current in 1/100 Amps."
    ::= { receptacleWarnLoCurrent 7 }

outlet8WarnLoCurr OBJECT-TYPE
    SYNTAX Integer32 (0..2000)
    MAX-ACCESS read-write
    STATUS current
    DESCRIPTION
        "Outlet8 warning low current in 1/100 Amps."
    ::= { receptacleWarnLoCurrent 8 }

outlet9WarnLoCurr OBJECT-TYPE
    SYNTAX Integer32 (0..2000)
    MAX-ACCESS read-write
    STATUS current
    DESCRIPTION
        "Outlet9 warning low current in 1/100 Amps."
    ::= { receptacleWarnLoCurrent 9 }

outlet10WarnLoCurr OBJECT-TYPE
    SYNTAX Integer32 (0..2000)
    MAX-ACCESS read-write
    STATUS current
    DESCRIPTION
        "Outlet10 warning low current in 1/100 Amps."
    ::= { receptacleWarnLoCurrent 10 }

outlet11WarnLoCurr OBJECT-TYPE
    SYNTAX Integer32 (0..2000)
    MAX-ACCESS read-write
    STATUS current
    DESCRIPTION
        "Outlet11 warning low current in 1/100 Amps."
    ::= { receptacleWarnLoCurrent 11 }

outlet12WarnLoCurr OBJECT-TYPE
    SYNTAX Integer32 (0..2000)
    MAX-ACCESS read-write
    STATUS current
    DESCRIPTION
        "Outlet12 warning low current in 1/100 Amps."
    ::= { receptacleWarnLoCurrent 12 }

outlet13WarnLoCurr OBJECT-TYPE
    SYNTAX Integer32 (0..2000)
    MAX-ACCESS read-write
    STATUS current
    DESCRIPTION
        "Outlet13 warning low current in 1/100 Amps."
    ::= { receptacleWarnLoCurrent 13 }

outlet14WarnLoCurr OBJECT-TYPE
    SYNTAX Integer32 (0..2000)
    MAX-ACCESS read-write
    STATUS current
    DESCRIPTION
        "Outlet14 warning low current in 1/100 Amps."
    ::= { receptacleWarnLoCurrent 14 }

outlet15WarnLoCurr OBJECT-TYPE
    SYNTAX Integer32 (0..2000)
    MAX-ACCESS read-write
    STATUS current
    DESCRIPTION
        "Outlet15 warning low current in 1/100 Amps."
    ::= { receptacleWarnLoCurrent 15 }

outlet16WarnLoCurr OBJECT-TYPE
    SYNTAX Integer32 (0..2000)
    MAX-ACCESS read-write
    STATUS current
    DESCRIPTION
        "Outlet16 warning low current in 1/100 Amps."
    ::= { receptacleWarnLoCurrent 16 }

outlet17WarnLoCurr OBJECT-TYPE
    SYNTAX Integer32 (0..2000)
    MAX-ACCESS read-write
    STATUS current
    DESCRIPTION
        "Outlet17 warning low current in 1/100 Amps."
    ::= { receptacleWarnLoCurrent 17 }

outlet18WarnLoCurr OBJECT-TYPE
    SYNTAX Integer32 (0..2000)
    MAX-ACCESS read-write
    STATUS current
    DESCRIPTION
        "Outlet18 warning low current in 1/100 Amps."
    ::= { receptacleWarnLoCurrent 18 }

outlet19WarnLoCurr OBJECT-TYPE
    SYNTAX Integer32 (0..2000)
    MAX-ACCESS read-write
    STATUS current
    DESCRIPTION
        "Outlet19 warning low current in 1/100 Amps."
    ::= { receptacleWarnLoCurrent 19 }

outlet20WarnLoCurr OBJECT-TYPE
    SYNTAX Integer32 (0..2000)
    MAX-ACCESS read-write
    STATUS current
    DESCRIPTION
        "Outlet20 warning low current in 1/100 Amps."
    ::= { receptacleWarnLoCurrent 20 }

outlet21WarnLoCurr OBJECT-TYPE
    SYNTAX Integer32 (0..2000)
    MAX-ACCESS read-write
    STATUS current
    DESCRIPTION
        "Outlet21 warning low current in 1/100 Amps."
    ::= { receptacleWarnLoCurrent 21 }

outlet22WarnLoCurr OBJECT-TYPE
    SYNTAX Integer32 (0..2000)
    MAX-ACCESS read-write
    STATUS current
    DESCRIPTION
        "Outlet22 warning low current in 1/100 Amps."
    ::= { receptacleWarnLoCurrent 22 }

outlet23WarnLoCurr OBJECT-TYPE
    SYNTAX Integer32 (0..2000)
    MAX-ACCESS read-write
    STATUS current
    DESCRIPTION
        "Outlet23 warning low current in 1/100 Amps."
    ::= { receptacleWarnLoCurrent 23 }

outlet24WarnLoCurr OBJECT-TYPE
    SYNTAX Integer32 (0..2000)
    MAX-ACCESS read-write
    STATUS current
    DESCRIPTION
        "Outlet24 warning low current in 1/100 Amps."
    ::= { receptacleWarnLoCurrent 24 }

maxTempLimits OBJECT IDENTIFIER ::= { configuration 32 }

maxTempProbe1 OBJECT-TYPE
    SYNTAX Integer32 (0..20000)
    MAX-ACCESS read-write
    STATUS current
    DESCRIPTION
        "Maximum temperature for Probe 1 in 1/100 of degrees Fahrenheit, 0=ignore."
    ::= { maxTempLimits 1 }

maxTempProbe2 OBJECT-TYPE
    SYNTAX Integer32 (0..20000)
    MAX-ACCESS read-write
    STATUS current
    DESCRIPTION
        "Maximum temperature for Probe 2 in 1/100 of degrees Fahrenheit, 0=ignore."
    ::= { maxTempLimits 2 }

minTempLimits OBJECT IDENTIFIER ::= { configuration 33 }

minTempProbe1 OBJECT-TYPE
    SYNTAX Integer32 (0..20000)
    MAX-ACCESS read-write
    STATUS current
    DESCRIPTION
        "Minimum temperature for Probe 1 in 1/100 of degrees Fahrenheit, 0=ignore."
    ::= { minTempLimits 1 }

minTempProbe2 OBJECT-TYPE
    SYNTAX Integer32 (0..20000)
    MAX-ACCESS read-write
    STATUS current
    DESCRIPTION
        "Minimum temperature for Probe 2 in 1/100 of degrees Fahrenheit, 0=ignore."
    ::= { minTempLimits 2 }

warnHiTempLimits OBJECT IDENTIFIER ::= { configuration 34 }

warnHiTempProbe1 OBJECT-TYPE
    SYNTAX Integer32 (0..20000)
    MAX-ACCESS read-write
    STATUS current
    DESCRIPTION
        "Warning High temperature for Probe 1 in 1/100 of degrees Fahrenheit, 0=ignore."
    ::= { warnHiTempLimits 1 }

warnHiTempProbe2 OBJECT-TYPE
    SYNTAX Integer32 (0..20000)
    MAX-ACCESS read-write
    STATUS current
    DESCRIPTION
        "Warning High temperature for Probe 2 in 1/100 of degrees Fahrenheit, 0=ignore."
    ::= { warnHiTempLimits 2 }

warnLoTempLimits OBJECT IDENTIFIER ::= { configuration 35 }

warnLoTempProbe1 OBJECT-TYPE
    SYNTAX Integer32 (0..20000)
    MAX-ACCESS read-write
    STATUS current
    DESCRIPTION
        "Warning Low temperature for Probe 1 in 1/100 of degrees Fahrenheit, 0=ignore."
    ::= { warnLoTempLimits 1 }

warnLoTempProbe2 OBJECT-TYPE
    SYNTAX Integer32 (0..20000)
    MAX-ACCESS read-write
    STATUS current
    DESCRIPTION
        "Warning Low temperature for Probe 2 in 1/100 of degrees Fahrenheit, 0=ignore."
    ::= { warnLoTempLimits 2 }

maxHumidityLimits OBJECT IDENTIFIER ::= { configuration 36 }

maxHumidProbe1 OBJECT-TYPE
    SYNTAX Integer32 (0..10000)
    MAX-ACCESS read-write
    STATUS current
    DESCRIPTION
        "Maximum humidity for Probe 1 in 1/100  of %, 0=ignore."
    ::= { maxHumidityLimits 1 }

maxHumidProbe2 OBJECT-TYPE
    SYNTAX Integer32 (0..10000)
    MAX-ACCESS read-write
    STATUS current
    DESCRIPTION
        "Maximum humidity for Probe 2 in 1/100  of %, 0=ignore."
    ::= { maxHumidityLimits 2 }

minHumidityLimits OBJECT IDENTIFIER ::= { configuration 37 }

minHumidProbe1 OBJECT-TYPE
    SYNTAX Integer32 (0..10000)
    MAX-ACCESS read-write
    STATUS current
    DESCRIPTION
        "Minimum humidity for Probe 1 in 1/100  of %, 0=ignore."
    ::= { minHumidityLimits 1 }

minHumidProbe2 OBJECT-TYPE
    SYNTAX Integer32 (0..10000)
    MAX-ACCESS read-write
    STATUS current
    DESCRIPTION
        "Minimum humidity for Probe 2 in 1/100  of %, 0=ignore."
    ::= { minHumidityLimits 2 }

warnHiHumidityLimits OBJECT IDENTIFIER ::= { configuration 38 }

warnHiHumidProbe1 OBJECT-TYPE
    SYNTAX Integer32 (0..10000)
    MAX-ACCESS read-write
    STATUS current
    DESCRIPTION
        "Warning High humidity for Probe 1 in 1/100  of %, 0=ignore."
    ::= { warnHiHumidityLimits 1 }

warnHiHumidProbe2 OBJECT-TYPE
    SYNTAX Integer32 (0..10000)
    MAX-ACCESS read-write
    STATUS current
    DESCRIPTION
        "Warning High humidity for Probe 2 in 1/100  of %, 0=ignore."
    ::= { warnHiHumidityLimits 2 }

warnLoHumidityLimits OBJECT IDENTIFIER ::= { configuration 39 }

warnLoHumidProbe1 OBJECT-TYPE
    SYNTAX Integer32 (0..10000)
    MAX-ACCESS read-write
    STATUS current
    DESCRIPTION
        "Warning Low humidity for Probe 1 in 1/100  of %, 0=ignore."
    ::= { warnLoHumidityLimits 1 }

warnLoHumidProbe2 OBJECT-TYPE
    SYNTAX Integer32 (0..10000)
    MAX-ACCESS read-write
    STATUS current
    DESCRIPTION
        "Warning Low humidity for Probe 2 in 1/100  of %, 0=ignore."
    ::= { warnLoHumidityLimits 2 }

pduName OBJECT-TYPE
    SYNTAX DisplayString (SIZE (0..64))
    MAX-ACCESS read-write
    STATUS current
    DESCRIPTION
        "PDU Name."
    ::= { configuration 40 }

pduDescrip OBJECT-TYPE
    SYNTAX DisplayString (SIZE (0..64))
    MAX-ACCESS read-write
    STATUS current
    DESCRIPTION
        "PDU Description."
    ::= { configuration 41 }

receptacleNames OBJECT IDENTIFIER ::= { configuration 42 }

outlet1Name OBJECT-TYPE
    SYNTAX DisplayString (SIZE (0..64))
    MAX-ACCESS read-write
    STATUS current
    DESCRIPTION
        "Outlet1 Name."
    ::= { receptacleNames 1 }

outlet2Name OBJECT-TYPE
    SYNTAX DisplayString (SIZE (0..64))
    MAX-ACCESS read-write
    STATUS current
    DESCRIPTION
        "Outlet2 Name."
    ::= { receptacleNames 2 }

outlet3Name OBJECT-TYPE
    SYNTAX DisplayString (SIZE (0..64))
    MAX-ACCESS read-write
    STATUS current
    DESCRIPTION
        "Outlet3 Name."
    ::= { receptacleNames 3 }

outlet4Name OBJECT-TYPE
    SYNTAX DisplayString (SIZE (0..64))
    MAX-ACCESS read-write
    STATUS current
    DESCRIPTION
        "Outlet4 Name."
    ::= { receptacleNames 4 }

outlet5Name OBJECT-TYPE
    SYNTAX DisplayString (SIZE (0..64))
    MAX-ACCESS read-write
    STATUS current
    DESCRIPTION
        "Outlet5 Name."
    ::= { receptacleNames 5 }

outlet6Name OBJECT-TYPE
    SYNTAX DisplayString (SIZE (0..64))
    MAX-ACCESS read-write
    STATUS current
    DESCRIPTION
        "Outlet6 Name."
    ::= { receptacleNames 6 }

outlet7Name OBJECT-TYPE
    SYNTAX DisplayString (SIZE (0..64))
    MAX-ACCESS read-write
    STATUS current
    DESCRIPTION
        "Outlet7 Name."
    ::= { receptacleNames 7 }

outlet8Name OBJECT-TYPE
    SYNTAX DisplayString (SIZE (0..64))
    MAX-ACCESS read-write
    STATUS current
    DESCRIPTION
        "Outlet8 Name."
    ::= { receptacleNames 8 }

outlet9Name OBJECT-TYPE
    SYNTAX DisplayString (SIZE (0..64))
    MAX-ACCESS read-write
    STATUS current
    DESCRIPTION
        "Outlet9 Name."
    ::= { receptacleNames 9 }

outlet10Name OBJECT-TYPE
    SYNTAX DisplayString (SIZE (0..64))
    MAX-ACCESS read-write
    STATUS current
    DESCRIPTION
        "Outlet10 Name."
    ::= { receptacleNames 10 }

outlet11Name OBJECT-TYPE
    SYNTAX DisplayString (SIZE (0..64))
    MAX-ACCESS read-write
    STATUS current
    DESCRIPTION
        "Outlet11 Name."
    ::= { receptacleNames 11 }

outlet12Name OBJECT-TYPE
    SYNTAX DisplayString (SIZE (0..64))
    MAX-ACCESS read-write
    STATUS current
    DESCRIPTION
        "Outlet12 Name."
    ::= { receptacleNames 12 }

outlet13Name OBJECT-TYPE
    SYNTAX DisplayString (SIZE (0..64))
    MAX-ACCESS read-write
    STATUS current
    DESCRIPTION
        "Outlet13 Name."
    ::= { receptacleNames 13 }

outlet14Name OBJECT-TYPE
    SYNTAX DisplayString (SIZE (0..64))
    MAX-ACCESS read-write
    STATUS current
    DESCRIPTION
        "Outlet14 Name."
    ::= { receptacleNames 14 }

outlet15Name OBJECT-TYPE
    SYNTAX DisplayString (SIZE (0..64))
    MAX-ACCESS read-write
    STATUS current
    DESCRIPTION
        "Outlet15 Name."
    ::= { receptacleNames 15 }

outlet16Name OBJECT-TYPE
    SYNTAX DisplayString (SIZE (0..64))
    MAX-ACCESS read-write
    STATUS current
    DESCRIPTION
        "Outlet16 Name."
    ::= { receptacleNames 16 }

outlet17Name OBJECT-TYPE
    SYNTAX DisplayString (SIZE (0..64))
    MAX-ACCESS read-write
    STATUS current
    DESCRIPTION
        "Outlet17 Name."
    ::= { receptacleNames 17 }

outlet18Name OBJECT-TYPE
    SYNTAX DisplayString (SIZE (0..64))
    MAX-ACCESS read-write
    STATUS current
    DESCRIPTION
        "Outlet18 Name."
    ::= { receptacleNames 18 }

outlet19Name OBJECT-TYPE
    SYNTAX DisplayString (SIZE (0..64))
    MAX-ACCESS read-write
    STATUS current
    DESCRIPTION
        "Outlet19 Name."
    ::= { receptacleNames 19 }

outlet20Name OBJECT-TYPE
    SYNTAX DisplayString (SIZE (0..64))
    MAX-ACCESS read-write
    STATUS current
    DESCRIPTION
        "Outlet20 Name."
    ::= { receptacleNames 20 }

outlet21Name OBJECT-TYPE
    SYNTAX DisplayString (SIZE (0..64))
    MAX-ACCESS read-write
    STATUS current
    DESCRIPTION
        "Outlet21 Name."
    ::= { receptacleNames 21 }

outlet22Name OBJECT-TYPE
    SYNTAX DisplayString (SIZE (0..64))
    MAX-ACCESS read-write
    STATUS current
    DESCRIPTION
        "Outlet22 Name."
    ::= { receptacleNames 22 }

outlet23Name OBJECT-TYPE
    SYNTAX DisplayString (SIZE (0..64))
    MAX-ACCESS read-write
    STATUS current
    DESCRIPTION
        "Outlet23 Name."
    ::= { receptacleNames 23 }

outlet24Name OBJECT-TYPE
    SYNTAX DisplayString (SIZE (0..64))
    MAX-ACCESS read-write
    STATUS current
    DESCRIPTION
        "Outlet24 Name."
    ::= { receptacleNames 24 }

receptacleDescrips OBJECT IDENTIFIER ::= { configuration 43 }

outlet1Descrip OBJECT-TYPE
    SYNTAX DisplayString (SIZE (0..64))
    MAX-ACCESS read-write
    STATUS current
    DESCRIPTION
        "Outlet1 Description."
    ::= { receptacleDescrips 1 }

outlet2Descrip OBJECT-TYPE
    SYNTAX DisplayString (SIZE (0..64))
    MAX-ACCESS read-write
    STATUS current
    DESCRIPTION
        "Outlet2 Description."
    ::= { receptacleDescrips 2 }

outlet3Descrip OBJECT-TYPE
    SYNTAX DisplayString (SIZE (0..64))
    MAX-ACCESS read-write
    STATUS current
    DESCRIPTION
        "Outlet3 Description."
    ::= { receptacleDescrips 3 }

outlet4Descrip OBJECT-TYPE
    SYNTAX DisplayString (SIZE (0..64))
    MAX-ACCESS read-write
    STATUS current
    DESCRIPTION
        "Outlet4 Description."
    ::= { receptacleDescrips 4 }

outlet5Descrip OBJECT-TYPE
    SYNTAX DisplayString (SIZE (0..64))
    MAX-ACCESS read-write
    STATUS current
    DESCRIPTION
        "Outlet5 Description."
    ::= { receptacleDescrips 5 }

outlet6Descrip OBJECT-TYPE
    SYNTAX DisplayString (SIZE (0..64))
    MAX-ACCESS read-write
    STATUS current
    DESCRIPTION
        "Outlet6 Description."
    ::= { receptacleDescrips 6 }

outlet7Descrip OBJECT-TYPE
    SYNTAX DisplayString (SIZE (0..64))
    MAX-ACCESS read-write
    STATUS current
    DESCRIPTION
        "Outlet7 Description."
    ::= { receptacleDescrips 7 }

outlet8Descrip OBJECT-TYPE
    SYNTAX DisplayString (SIZE (0..64))
    MAX-ACCESS read-write
    STATUS current
    DESCRIPTION
        "Outlet8 Description."
    ::= { receptacleDescrips 8 }

outlet9Descrip OBJECT-TYPE
    SYNTAX DisplayString (SIZE (0..64))
    MAX-ACCESS read-write
    STATUS current
    DESCRIPTION
        "Outlet9 Description."
    ::= { receptacleDescrips 9 }

outlet10Descrip OBJECT-TYPE
    SYNTAX DisplayString (SIZE (0..64))
    MAX-ACCESS read-write
    STATUS current
    DESCRIPTION
        "Outlet10 Description."
    ::= { receptacleDescrips 10 }

outlet11Descrip OBJECT-TYPE
    SYNTAX DisplayString (SIZE (0..64))
    MAX-ACCESS read-write
    STATUS current
    DESCRIPTION
        "Outlet11 Description."
    ::= { receptacleDescrips 11 }

outlet12Descrip OBJECT-TYPE
    SYNTAX DisplayString (SIZE (0..64))
    MAX-ACCESS read-write
    STATUS current
    DESCRIPTION
        "Outlet12 Description."
    ::= { receptacleDescrips 12 }

outlet13Descrip OBJECT-TYPE
    SYNTAX DisplayString (SIZE (0..64))
    MAX-ACCESS read-write
    STATUS current
    DESCRIPTION
        "Outlet13 Description."
    ::= { receptacleDescrips 13 }

outlet14Descrip OBJECT-TYPE
    SYNTAX DisplayString (SIZE (0..64))
    MAX-ACCESS read-write
    STATUS current
    DESCRIPTION
        "Outlet14 Description."
    ::= { receptacleDescrips 14 }

outlet15Descrip OBJECT-TYPE
    SYNTAX DisplayString (SIZE (0..64))
    MAX-ACCESS read-write
    STATUS current
    DESCRIPTION
        "Outlet15 Description."
    ::= { receptacleDescrips 15 }

outlet16Descrip OBJECT-TYPE
    SYNTAX DisplayString (SIZE (0..64))
    MAX-ACCESS read-write
    STATUS current
    DESCRIPTION
        "Outlet16 Description."
    ::= { receptacleDescrips 16 }

outlet17Descrip OBJECT-TYPE
    SYNTAX DisplayString (SIZE (0..64))
    MAX-ACCESS read-write
    STATUS current
    DESCRIPTION
        "Outlet17 Description."
    ::= { receptacleDescrips 17 }

outlet18Descrip OBJECT-TYPE
    SYNTAX DisplayString (SIZE (0..64))
    MAX-ACCESS read-write
    STATUS current
    DESCRIPTION
        "Outlet18 Description."
    ::= { receptacleDescrips 18 }

outlet19Descrip OBJECT-TYPE
    SYNTAX DisplayString (SIZE (0..64))
    MAX-ACCESS read-write
    STATUS current
    DESCRIPTION
        "Outlet19 Description."
    ::= { receptacleDescrips 19 }

outlet20Descrip OBJECT-TYPE
    SYNTAX DisplayString (SIZE (0..64))
    MAX-ACCESS read-write
    STATUS current
    DESCRIPTION
        "Outlet20 Description."
    ::= { receptacleDescrips 20 }

outlet21Descrip OBJECT-TYPE
    SYNTAX DisplayString (SIZE (0..64))
    MAX-ACCESS read-write
    STATUS current
    DESCRIPTION
        "Outlet21 Description."
    ::= { receptacleDescrips 21 }

outlet22Descrip OBJECT-TYPE
    SYNTAX DisplayString (SIZE (0..64))
    MAX-ACCESS read-write
    STATUS current
    DESCRIPTION
        "Outlet22 Description."
    ::= { receptacleDescrips 22 }

outlet23Descrip OBJECT-TYPE
    SYNTAX DisplayString (SIZE (0..64))
    MAX-ACCESS read-write
    STATUS current
    DESCRIPTION
        "Outlet23 Description."
    ::= { receptacleDescrips 23 }

outlet24Descrip OBJECT-TYPE
    SYNTAX DisplayString (SIZE (0..64))
    MAX-ACCESS read-write
    STATUS current
    DESCRIPTION
        "Outlet24 Description."
    ::= { receptacleDescrips 24 }

groupNames OBJECT IDENTIFIER ::= { configuration 50 }

group1Name OBJECT-TYPE
    SYNTAX DisplayString (SIZE (0..64))
    MAX-ACCESS read-write
    STATUS current
    DESCRIPTION
        "Name for GROUP 1 of receptacles."
    ::= { groupNames 1 }

group2Name OBJECT-TYPE
    SYNTAX DisplayString (SIZE (0..64))
    MAX-ACCESS read-write
    STATUS current
    DESCRIPTION
        "Name for GROUP 2 of receptacles."
    ::= { groupNames 2 }

group3Name OBJECT-TYPE
    SYNTAX DisplayString (SIZE (0..64))
    MAX-ACCESS read-write
    STATUS current
    DESCRIPTION
        "Name for GROUP 3 of receptacles."
    ::= { groupNames 3 }

group4Name OBJECT-TYPE
    SYNTAX DisplayString (SIZE (0..64))
    MAX-ACCESS read-write
    STATUS current
    DESCRIPTION
        "Name for GROUP 4 of receptacles."
    ::= { groupNames 4 }

group5Name OBJECT-TYPE
    SYNTAX DisplayString (SIZE (0..64))
    MAX-ACCESS read-write
    STATUS current
    DESCRIPTION
        "Name for GROUP 5 of receptacles."
    ::= { groupNames 5 }

group6Name OBJECT-TYPE
    SYNTAX DisplayString (SIZE (0..64))
    MAX-ACCESS read-write
    STATUS current
    DESCRIPTION
        "Name for GROUP 6 of receptacles."
    ::= { groupNames 6 }

group7Name OBJECT-TYPE
    SYNTAX DisplayString (SIZE (0..64))
    MAX-ACCESS read-write
    STATUS current
    DESCRIPTION
        "Name for GROUP 7 of receptacles."
    ::= { groupNames 7 }

group8Name OBJECT-TYPE
    SYNTAX DisplayString (SIZE (0..64))
    MAX-ACCESS read-write
    STATUS current
    DESCRIPTION
        "Name for GROUP 8 of receptacles."
    ::= { groupNames 8 }

group9Name OBJECT-TYPE
    SYNTAX DisplayString (SIZE (0..64))
    MAX-ACCESS read-write
    STATUS current
    DESCRIPTION
        "Name for GROUP 9 of receptacles."
    ::= { groupNames 9 }

group10Name OBJECT-TYPE
    SYNTAX DisplayString (SIZE (0..64))
    MAX-ACCESS read-write
    STATUS current
    DESCRIPTION
        "Name for GROUP 10 of receptacles."
    ::= { groupNames 10 }

group11Name OBJECT-TYPE
    SYNTAX DisplayString (SIZE (0..64))
    MAX-ACCESS read-write
    STATUS current
    DESCRIPTION
        "Name for GROUP 11 of receptacles."
    ::= { groupNames 11 }

group12Name OBJECT-TYPE
    SYNTAX DisplayString (SIZE (0..64))
    MAX-ACCESS read-write
    STATUS current
    DESCRIPTION
        "Name for GROUP 12 of receptacles."
    ::= { groupNames 12 }

group13Name OBJECT-TYPE
    SYNTAX DisplayString (SIZE (0..64))
    MAX-ACCESS read-write
    STATUS current
    DESCRIPTION
        "Name for GROUP 13 of receptacles."
    ::= { groupNames 13 }

group14Name OBJECT-TYPE
    SYNTAX DisplayString (SIZE (0..64))
    MAX-ACCESS read-write
    STATUS current
    DESCRIPTION
        "Name for GROUP 14 of receptacles."
    ::= { groupNames 14 }

group15Name OBJECT-TYPE
    SYNTAX DisplayString (SIZE (0..64))
    MAX-ACCESS read-write
    STATUS current
    DESCRIPTION
        "Name for GROUP 15 of receptacles."
    ::= { groupNames 15 }

group16Name OBJECT-TYPE
    SYNTAX DisplayString (SIZE (0..64))
    MAX-ACCESS read-write
    STATUS current
    DESCRIPTION
        "Name for GROUP 16 of receptacles."
    ::= { groupNames 16 }

groupMaps OBJECT IDENTIFIER ::= { configuration 51 }

group1Map OBJECT-TYPE
    SYNTAX OCTET STRING (SIZE (0..256))
    MAX-ACCESS read-write
    STATUS current
    DESCRIPTION
        "Map for Group 1 of receptacels."
    ::= { groupMaps 1 }

group2Map OBJECT-TYPE
    SYNTAX OCTET STRING (SIZE (0..256))
    MAX-ACCESS read-write
    STATUS current
    DESCRIPTION
        "Map for Group 2 of receptacels."
    ::= { groupMaps 2 }

group3Map OBJECT-TYPE
    SYNTAX OCTET STRING (SIZE (0..256))
    MAX-ACCESS read-write
    STATUS current
    DESCRIPTION
        "Map for Group 3 of receptacels."
    ::= { groupMaps 3 }

group4Map OBJECT-TYPE
    SYNTAX OCTET STRING (SIZE (0..256))
    MAX-ACCESS read-write
    STATUS current
    DESCRIPTION
        "Map for Group 4 of receptacels."
    ::= { groupMaps 4 }

group5Map OBJECT-TYPE
    SYNTAX OCTET STRING (SIZE (0..256))
    MAX-ACCESS read-write
    STATUS current
    DESCRIPTION
        "Map for Group 5 of receptacels."
    ::= { groupMaps 5 }

group6Map OBJECT-TYPE
    SYNTAX OCTET STRING (SIZE (0..256))
    MAX-ACCESS read-write
    STATUS current
    DESCRIPTION
        "Map for Group 6 of receptacels."
    ::= { groupMaps 6 }

group7Map OBJECT-TYPE
    SYNTAX OCTET STRING (SIZE (0..256))
    MAX-ACCESS read-write
    STATUS current
    DESCRIPTION
        "Map for Group 7 of receptacels."
    ::= { groupMaps 7 }

group8Map OBJECT-TYPE
    SYNTAX OCTET STRING (SIZE (0..256))
    MAX-ACCESS read-write
    STATUS current
    DESCRIPTION
        "Map for Group 8 of receptacels."
    ::= { groupMaps 8 }

group9Map OBJECT-TYPE
    SYNTAX OCTET STRING (SIZE (0..256))
    MAX-ACCESS read-write
    STATUS current
    DESCRIPTION
        "Map for Group 9 of receptacels."
    ::= { groupMaps 9 }

group10Map OBJECT-TYPE
    SYNTAX OCTET STRING (SIZE (0..256))
    MAX-ACCESS read-write
    STATUS current
    DESCRIPTION
        "Map for Group 10 of receptacels."
    ::= { groupMaps 10 }

group11Map OBJECT-TYPE
    SYNTAX OCTET STRING (SIZE (0..256))
    MAX-ACCESS read-write
    STATUS current
    DESCRIPTION
        "Map for Group 11 of receptacels."
    ::= { groupMaps 11 }

group12Map OBJECT-TYPE
    SYNTAX OCTET STRING (SIZE (0..256))
    MAX-ACCESS read-write
    STATUS current
    DESCRIPTION
        "Map for Group 12 of receptacels."
    ::= { groupMaps 12 }

group13Map OBJECT-TYPE
    SYNTAX OCTET STRING (SIZE (0..256))
    MAX-ACCESS read-write
    STATUS current
    DESCRIPTION
        "Map for Group 13 of receptacels."
    ::= { groupMaps 13 }

group14Map OBJECT-TYPE
    SYNTAX OCTET STRING (SIZE (0..256))
    MAX-ACCESS read-write
    STATUS current
    DESCRIPTION
        "Map for Group 14 of receptacels."
    ::= { groupMaps 14 }

group15Map OBJECT-TYPE
    SYNTAX OCTET STRING (SIZE (0..256))
    MAX-ACCESS read-write
    STATUS current
    DESCRIPTION
        "Map for Group 15 of receptacels."
    ::= { groupMaps 15 }

group16Map OBJECT-TYPE
    SYNTAX OCTET STRING (SIZE (0..256))
    MAX-ACCESS read-write
    STATUS current
    DESCRIPTION
        "Map for Group 16 of receptacels."
    ::= { groupMaps 16 }

dispTimeout OBJECT-TYPE
    SYNTAX Integer32 (1..90)
    MAX-ACCESS read-write
    STATUS current
    DESCRIPTION
        "Inactivity timeout in minutes to blank the local display (minimum is 1 minute)."
    ::= { configuration 55 }

loginTimeout OBJECT-TYPE
    SYNTAX Integer32 (1..60)
    MAX-ACCESS read-write
    STATUS current
    DESCRIPTION
        "Inactivity timeout in minutes to terminate a logged in session (minimum is 1 minute)."
    ::= { configuration 56 }

dispBrightness OBJECT-TYPE
    SYNTAX Integer32 (0..9)
    MAX-ACCESS read-write
    STATUS current
    DESCRIPTION
        "The relative brightness of the local display (0 in min, 9 is max)."
    ::= { configuration 57 }

pduOptions OBJECT IDENTIFIER ::= { configuration 58 }

inputTop OBJECT-TYPE
    SYNTAX Integer32 (0..1)
    MAX-ACCESS read-write
    STATUS current
    DESCRIPTION
        "Input cord entry orientation, 1 = top, 0 = bottom."
    ::= { pduOptions 1 }

pduRole OBJECT-TYPE
    SYNTAX Integer32 (0..1)
    MAX-ACCESS read-write
    STATUS current
    DESCRIPTION
        "PDU Role, 1 = primary, 0 = secondary."
    ::= { pduOptions 2 }

celsiusTemp OBJECT-TYPE
    SYNTAX Integer32 (0..1)
    MAX-ACCESS read-write
    STATUS current
    DESCRIPTION
        "Temperature units, 1=Celsius, 0=Fahrenheit."
    ::= { pduOptions 3 }

enableWeb OBJECT-TYPE
    SYNTAX Integer32 (0..1)
    MAX-ACCESS read-write
    STATUS current
    DESCRIPTION
        "Enable Web Access, 1 = enable, 0 = disable."
    ::= { pduOptions 4 }

snmpHostOnly OBJECT-TYPE
    SYNTAX Integer32 (0..1)
    MAX-ACCESS read-write
    STATUS current
    DESCRIPTION
        "Restrict access to SNMP via listed Hosts only, 1 = listed SNMP hosts only, 0 = any host."
    ::= { pduOptions 5 }

disLocalAuth OBJECT-TYPE
    SYNTAX Integer32 (0..1)
    MAX-ACCESS read-write
    STATUS current
    DESCRIPTION
        "Disable local authentication, 1 = disable, 0 = enable."
    ::= { pduOptions 6 }

enaRadiusAuth OBJECT-TYPE
    SYNTAX Integer32 (0..1)
    MAX-ACCESS read-write
    STATUS current
    DESCRIPTION
        "Enable Radius authentication, 1 = disable, 0 = enable."
    ::= { pduOptions 7 }

enaADAuth OBJECT-TYPE
    SYNTAX Integer32 (0..1)
    MAX-ACCESS read-write
    STATUS current
    DESCRIPTION
        "Enable Active Directory authentication, 1 = disable, 0 = enable."
    ::= { pduOptions 8 }

enaSMTP OBJECT-TYPE
    SYNTAX Integer32 (0..1)
    MAX-ACCESS read-write
    STATUS current
    DESCRIPTION
        "Enable Mail Notification, 1 = disable, 0 = enable."
    ::= { pduOptions 9 }

pduAltRole OBJECT-TYPE
    SYNTAX Integer32 (0..1)
    MAX-ACCESS read-write
    STATUS current
    DESCRIPTION
        "PDU Alternate Role, 1 = alternate, 0 = secondary."
    ::= { pduOptions 10 }

shareRole OBJECT-TYPE
    SYNTAX Integer32 (0..1)
    MAX-ACCESS read-write
    STATUS current
    DESCRIPTION
        "Allow sharing of PDU Primary and Alternate Roles, 1 = shared, 0 = backup only."
    ::= { pduOptions 11 }

outOfService OBJECT-TYPE
    SYNTAX Integer32 (0..1)
    MAX-ACCESS read-write
    STATUS current
    DESCRIPTION
        "Remove a PDU from normal operation, 1 = out of service, 0 = normal operation."
    ::= { pduOptions 12 }

missingPDUNotify OBJECT-TYPE
    SYNTAX Integer32 (0..1)
    MAX-ACCESS read-write
    STATUS current
    DESCRIPTION
        "Notify when a PDU is missing from the link, 1 = enable, 0 = disable."
    ::= { pduOptions 13 }

roleChangeNotify OBJECT-TYPE
    SYNTAX Integer32 (0..1)
    MAX-ACCESS read-write
    STATUS current
    DESCRIPTION
        "Notify when a PDU changes role in the link, 1 = enable, 0 = disable."
    ::= { pduOptions 14 }

sumAmp OBJECT-TYPE
    SYNTAX Integer32 (0..1)
    MAX-ACCESS read-write
    STATUS current
    DESCRIPTION
        "Display the sum of the current across branches, 1 = enable, 0 = disable."
    ::= { pduOptions 15 }

httpPorts OBJECT IDENTIFIER ::= { configuration 59 }

httpPort OBJECT-TYPE
    SYNTAX Integer32 (0..65535)
    MAX-ACCESS read-write
    STATUS current
    DESCRIPTION
        "Port for unsecure HTTP access."
    ::= { httpPorts 1 }

httpsPort OBJECT-TYPE
    SYNTAX Integer32 (0..65535)
    MAX-ACCESS read-write
    STATUS current
    DESCRIPTION
        "Port for secure HTTPS access."
    ::= { httpPorts 2 }

sshPorts OBJECT IDENTIFIER ::= { configuration 60 }

sshPort OBJECT-TYPE
    SYNTAX Integer32 (0..65535)
    MAX-ACCESS read-write
    STATUS current
    DESCRIPTION
        "Port for secure SSH access."
    ::= { sshPorts 1 }

telnetPort OBJECT-TYPE
    SYNTAX Integer32 (0..65535)
    MAX-ACCESS read-write
    STATUS current
    DESCRIPTION
        "Port for non secure Telnet access."
    ::= { sshPorts 2 }

snmpPorts OBJECT IDENTIFIER ::= { configuration 61 }

snmpQueryPort OBJECT-TYPE
    SYNTAX Integer32 (0..65535)
    MAX-ACCESS read-write
    STATUS current
    DESCRIPTION
        "Port for SNMP query access."
    ::= { snmpPorts 1 }

snmpTrapPort OBJECT-TYPE
    SYNTAX Integer32 (0..65535)
    MAX-ACCESS read-write
    STATUS current
    DESCRIPTION
        "Port for SNMP trap."
    ::= { snmpPorts 2 }

smtpPorts OBJECT IDENTIFIER ::= { configuration 62 }

smtpSendPort OBJECT-TYPE
    SYNTAX Integer32 (0..65535)
    MAX-ACCESS read-write
    STATUS current
    DESCRIPTION
        "Port for SMTP send."
    ::= { smtpPorts 1 }

smtpReceivePort OBJECT-TYPE
    SYNTAX Integer32 (0..65535)
    MAX-ACCESS read-write
    STATUS current
    DESCRIPTION
        "Port for SMTP Receive."
    ::= { smtpPorts 2 }

rfcTimeServer OBJECT-TYPE
    SYNTAX DisplayString (SIZE (0..64))
    MAX-ACCESS read-write
    STATUS current
    DESCRIPTION
        "RFC Time Server Address."
    ::= { configuration 63 }

ntpTimeServer OBJECT-TYPE
    SYNTAX DisplayString (SIZE (0..64))
    MAX-ACCESS read-write
    STATUS current
    DESCRIPTION
        "NTP Time Server Address."
    ::= { configuration 64 }

smtpServer OBJECT-TYPE
    SYNTAX DisplayString (SIZE (0..64))
    MAX-ACCESS read-write
    STATUS current
    DESCRIPTION
        "Email Server Address."
    ::= { configuration 65 }

snmpReadComm OBJECT-TYPE
    SYNTAX DisplayString (SIZE (0..64))
    MAX-ACCESS read-write
    STATUS current
    DESCRIPTION
        "SNMP Read Community."
    ::= { configuration 66 }

snmpWriteComm OBJECT-TYPE
    SYNTAX DisplayString (SIZE (0..64))
    MAX-ACCESS read-write
    STATUS current
    DESCRIPTION
        "SNMP Write Community."
    ::= { configuration 67 }

snmpUSMuserName OBJECT-TYPE
    SYNTAX DisplayString (SIZE (0..64))
    MAX-ACCESS read-write
    STATUS current
    DESCRIPTION
        "SNMP USM User Name."
    ::= { configuration 68 }

snmpSecurityLevelAlgorithm OBJECT IDENTIFIER ::= { configuration 69 }

snmpSecurityLevel OBJECT-TYPE
    SYNTAX Integer32 (0..4)
    MAX-ACCESS read-write
    STATUS current
    DESCRIPTION
        "Security Level for SNMP: 0 = v1, 1 = v2c, 2 = v3 no authentication,
        3 = v3 with authentication only, 4 = v3 with authentication and privacy"
    ::= { snmpSecurityLevelAlgorithm 1 }

snmpAuthAlgo OBJECT-TYPE
    SYNTAX Integer32 (0..1)
    MAX-ACCESS read-write
    STATUS current
    DESCRIPTION
        "Authentication Algorithm for SNMP: 0 = SHA, 1 = MD5."
    ::= { snmpSecurityLevelAlgorithm 2 }

snmpPrivAlgo OBJECT-TYPE
    SYNTAX Integer32 (0..1)
    MAX-ACCESS read-write
    STATUS current
    DESCRIPTION
        "Privacy Algorithm for SNMP: 0 = DES, 1 = AES."
    ::= { snmpSecurityLevelAlgorithm 3 }

snmpAuthPasswd OBJECT-TYPE
    SYNTAX DisplayString (SIZE (0..64))
    MAX-ACCESS read-write
    STATUS current
    DESCRIPTION
        "SNMP Authentication Password."
    ::= { configuration 70 }

snmpPrivPasswd OBJECT-TYPE
    SYNTAX DisplayString (SIZE (0..64))
    MAX-ACCESS read-write
    STATUS current
    DESCRIPTION
        "SNMP Privacy Password."
    ::= { configuration 71 }

snmpContextName OBJECT-TYPE
    SYNTAX DisplayString (SIZE (0..64))
    MAX-ACCESS read-write
    STATUS current
    DESCRIPTION
        "SNMP Context Name."
    ::= { configuration 72 }

snmpEngineID OBJECT-TYPE
    SYNTAX DisplayString (SIZE (0..64))
    MAX-ACCESS read-write
    STATUS current
    DESCRIPTION
        "SNMP Engine ID."
    ::= { configuration 73 }

snmpLocAuthKey OBJECT-TYPE
    SYNTAX DisplayString (SIZE (0..64))
    MAX-ACCESS read-write
    STATUS current
    DESCRIPTION
        "SNMP Local Authentication Key."
    ::= { configuration 74 }

snmpLocPrivKey OBJECT-TYPE
    SYNTAX DisplayString (SIZE (0..64))
    MAX-ACCESS read-write
    STATUS current
    DESCRIPTION
        "SNMP Local Privacy Key."
    ::= { configuration 75 }

smtpUserName OBJECT-TYPE
    SYNTAX DisplayString (SIZE (0..64))
    MAX-ACCESS read-write
    STATUS current
    DESCRIPTION
        "PDU Email User Login Name."
    ::= { configuration 76 }

smtpUserPasswd OBJECT-TYPE
    SYNTAX DisplayString (SIZE (0..64))
    MAX-ACCESS read-write
    STATUS current
    DESCRIPTION
        "PDU Email User Login Password."
    ::= { configuration 77 }

smtpEmailAddr OBJECT-TYPE
    SYNTAX DisplayString (SIZE (0..64))
    MAX-ACCESS read-write
    STATUS current
    DESCRIPTION
        "PDU Email address."
    ::= { configuration 78 }

smtpEmailDestinations OBJECT IDENTIFIER ::= { configuration 79 }

smtpEmailDestination1 OBJECT-TYPE
    SYNTAX DisplayString (SIZE (0..64))
    MAX-ACCESS read-write
    STATUS current
    DESCRIPTION
        "Email destination for recipient 0."
    ::= { smtpEmailDestinations 1 }

smtpEmailDestination2 OBJECT-TYPE
    SYNTAX DisplayString (SIZE (0..64))
    MAX-ACCESS read-write
    STATUS current
    DESCRIPTION
        "Email destination for recipient 1."
    ::= { smtpEmailDestinations 2 }

smtpEmailDestination3 OBJECT-TYPE
    SYNTAX DisplayString (SIZE (0..64))
    MAX-ACCESS read-write
    STATUS current
    DESCRIPTION
        "Email destination for recipient 2."
    ::= { smtpEmailDestinations 3 }

smtpServOptions OBJECT-TYPE
    SYNTAX Integer32 (0..2)
    MAX-ACCESS read-write
    STATUS current
    DESCRIPTION
        "SMTP Server Options."
    ::= { configuration 80 }

radiusServer OBJECT-TYPE
    SYNTAX DisplayString (SIZE (0..64))
    MAX-ACCESS read-write
    STATUS current
    DESCRIPTION
        "Radius Authentication Server."
    ::= { configuration 81 }

radiusSHSecret OBJECT-TYPE
    SYNTAX DisplayString (SIZE (0..64))
    MAX-ACCESS read-write
    STATUS current
    DESCRIPTION
        "Radius Shared Secret."
    ::= { configuration 82 }

radiusNASServer OBJECT-TYPE
    SYNTAX DisplayString (SIZE (0..64))
    MAX-ACCESS read-write
    STATUS current
    DESCRIPTION
        "Radius Network Access Service."
    ::= { configuration 83 }

radiusNASPorts OBJECT IDENTIFIER ::= { configuration 84 }

radiusPort OBJECT-TYPE
    SYNTAX Integer32 (0..65535)
    MAX-ACCESS read-write
    STATUS current
    DESCRIPTION
        "Port for radius authentication."
    ::= { radiusNASPorts 1 }

nasPort OBJECT-TYPE
    SYNTAX Integer32 (0..65535)
    MAX-ACCESS read-write
    STATUS current
    DESCRIPTION
        "Port for Radius Network Access Service."
    ::= { radiusNASPorts 2 }

adServer OBJECT-TYPE
    SYNTAX DisplayString (SIZE (0..64))
    MAX-ACCESS read-write
    STATUS current
    DESCRIPTION
        "Active Directory Server."
    ::= { configuration 85 }

adDomain OBJECT-TYPE
    SYNTAX DisplayString (SIZE (0..64))
    MAX-ACCESS read-write
    STATUS current
    DESCRIPTION
        "Active Directory Domain."
    ::= { configuration 86 }

adAllPorts OBJECT IDENTIFIER ::= { configuration 87 }

adPort OBJECT-TYPE
    SYNTAX Integer32 (0..65535)
    MAX-ACCESS read-write
    STATUS current
    DESCRIPTION
        "Port for Active Directory authentication."
    ::= { adAllPorts 1 }

adResvPort OBJECT-TYPE
    SYNTAX Integer32 (0..65535)
    MAX-ACCESS read-write
    STATUS current
    DESCRIPTION
        "Alternate or reserved port for Active Directory Authentication."
    ::= { adAllPorts 2 }

envProbeNames OBJECT IDENTIFIER ::= { configuration 88 }

probe1Name OBJECT-TYPE
    SYNTAX DisplayString (SIZE (0..64))
    MAX-ACCESS read-write
    STATUS current
    DESCRIPTION
        "Name for Environmental Probe 1."
    ::= { envProbeNames 1 }

probe2Name OBJECT-TYPE
    SYNTAX DisplayString (SIZE (0..64))
    MAX-ACCESS read-write
    STATUS current
    DESCRIPTION
        "Name for Environmental Probe 2."
    ::= { envProbeNames 2 }

dLogOptions OBJECT IDENTIFIER ::= { configuration 89 }

dLogEnable OBJECT-TYPE
    SYNTAX Integer32 (0..1)
    MAX-ACCESS read-write
    STATUS current
    DESCRIPTION
        "Enable data logging feature, 0=disable and 1=enable."
    ::= { dLogOptions 1 }

netservdLog OBJECT-TYPE
    SYNTAX Integer32 (0..1)
    MAX-ACCESS read-write
    STATUS current
    DESCRIPTION
        "Enable data logging to log server over network, 0=disable and 1=enable."
    ::= { dLogOptions 11 }

autonetLog OBJECT-TYPE
    SYNTAX Integer32 (0..1)
    MAX-ACCESS read-write
    STATUS current
    DESCRIPTION
        "Enable automatic transfer to log server every 6 hours, 0=disable and 1=enable."
    ::= { dLogOptions 12 }

stdmeterdLog OBJECT-TYPE
    SYNTAX Integer32 (0..1)
    MAX-ACCESS read-write
    STATUS current
    DESCRIPTION
        "Enable logging of branch, receptacle and environmental metrics, 0=disable and 1=enable."
    ::= { dLogOptions 2 }

groupmeterdLog OBJECT-TYPE
    SYNTAX Integer32 (0..1)
    MAX-ACCESS read-write
    STATUS current
    DESCRIPTION
        "Enable logging of grouped receptacle metrics, 0=disable and 1=enable."
    ::= { dLogOptions 3 }

alarmdLog OBJECT-TYPE
    SYNTAX Integer32 (0..1)
    MAX-ACCESS read-write
    STATUS current
    DESCRIPTION
        "Enable logging of alarm events, 0=disable and 1=enable."
    ::= { dLogOptions 4 }

userlogindLog OBJECT-TYPE
    SYNTAX Integer32 (0..1)
    MAX-ACCESS read-write
    STATUS current
    DESCRIPTION
        "Enable logging of user login events, 0=disable and 1=enable."
    ::= { dLogOptions 5 }

usersetupdLog OBJECT-TYPE
    SYNTAX Integer32 (0..1)
    MAX-ACCESS read-write
    STATUS current
    DESCRIPTION
        "Enable logging of user setup change events, 0=disable and 1=enable."
    ::= { dLogOptions 6 }

fwupdatedLog OBJECT-TYPE
    SYNTAX Integer32 (0..1)
    MAX-ACCESS read-write
    STATUS current
    DESCRIPTION
        "Enable data logging feature, 0=disable and 1=enable."
    ::= { dLogOptions 7 }

setupchangedLog OBJECT-TYPE
    SYNTAX Integer32 (0..1)
    MAX-ACCESS read-write
    STATUS current
    DESCRIPTION
        "Enable logging of setup change events, 0=disable and 1=enable."
    ::= { dLogOptions 8 }

recepchangedLog OBJECT-TYPE
    SYNTAX Integer32 (0..1)
    MAX-ACCESS read-write
    STATUS current
    DESCRIPTION
        "Enable logging of receptacle state changes, 0=disable and 1=enable."
    ::= { dLogOptions 9 }

pduopchangedLog OBJECT-TYPE
    SYNTAX Integer32 (0..1)
    MAX-ACCESS read-write
    STATUS current
    DESCRIPTION
        "Enable logging of PDU operation and state changes, 0=disable and 1=enable."
    ::= { dLogOptions 10 }

dLogCycle OBJECT-TYPE
    SYNTAX Integer32 (0..65535)
    MAX-ACCESS read-write
    STATUS current
    DESCRIPTION
        "The time interval in minutes for internal data logging to occur."
    ::= { configuration 90 }

dLogFullWarnLevel OBJECT-TYPE
    SYNTAX Integer32 (50..100)
    MAX-ACCESS read-write
    STATUS current
    DESCRIPTION
        "The warning threshold for percentage of storage full (min=50, max=100)."
    ::= { configuration 91 }

netdLogServer OBJECT-TYPE
    SYNTAX DisplayString (SIZE (0..64))
    MAX-ACCESS read-write
    STATUS current
    DESCRIPTION
        "The network address for the data log server."
    ::= { configuration 92 }

netdLogPort OBJECT-TYPE
    SYNTAX Integer32 (0..65535)
    MAX-ACCESS read-write
    STATUS current
    DESCRIPTION
        "The port used by the data log server."
    ::= { configuration 93 }

netdLogUser OBJECT-TYPE
    SYNTAX DisplayString (SIZE (0..64))
    MAX-ACCESS read-write
    STATUS current
    DESCRIPTION
        "The user name to access the data log server."
    ::= { configuration 94 }

netdLogPasswd OBJECT-TYPE
    SYNTAX DisplayString (SIZE (0..64))
    MAX-ACCESS read-write
    STATUS current
    DESCRIPTION
        "The user password to access the data log server."
    ::= { configuration 95 }

netdLogDestdir OBJECT-TYPE
    SYNTAX DisplayString (SIZE (0..64))
    MAX-ACCESS read-write
    STATUS current
    DESCRIPTION
        "The destination directory in the data log server."
    ::= { configuration 96 }

netdLogOptions OBJECT-TYPE
    SYNTAX DisplayString (SIZE (0..64))
    MAX-ACCESS read-write
    STATUS current
    DESCRIPTION
        "The options string when accessing the data log server."
    ::= { configuration 97 }

snmpTrapHosts OBJECT IDENTIFIER ::= { configuration 98 }

snmpTrapHost1 OBJECT-TYPE
    SYNTAX IpAddress
    MAX-ACCESS read-write
    STATUS current
    DESCRIPTION
        "SNMP Trap Host 1 IP address."
    ::= { snmpTrapHosts 1 }

snmpTrapHost2 OBJECT-TYPE
    SYNTAX IpAddress
    MAX-ACCESS read-write
    STATUS current
    DESCRIPTION
        "SNMP Trap Host 2 IP address."
    ::= { snmpTrapHosts 2 }

snmpTrapHost3 OBJECT-TYPE
    SYNTAX IpAddress
    MAX-ACCESS read-write
    STATUS current
    DESCRIPTION
        "SNMP Trap Host 3 IP address."
    ::= { snmpTrapHosts 3 }

snmpTrapHostsIPv6 OBJECT IDENTIFIER ::= { configuration 99 }

snmpTrapHost1IPv6 OBJECT-TYPE
    SYNTAX DisplayString (SIZE (0..64))
    MAX-ACCESS read-write
    STATUS current
    DESCRIPTION
        "SNMP Trap Host 1 IPV6."
    ::= { snmpTrapHostsIPv6 1 }

snmpTrapHost2IPv6 OBJECT-TYPE
    SYNTAX DisplayString (SIZE (0..64))
    MAX-ACCESS read-write
    STATUS current
    DESCRIPTION
        "SNMP Trap Host 2 IPV6."
    ::= { snmpTrapHostsIPv6 2 }

snmpTrapHost3IPv6 OBJECT-TYPE
    SYNTAX DisplayString (SIZE (0..64))
    MAX-ACCESS read-write
    STATUS current
    DESCRIPTION
        "SNMP Trap Host 3 IPV6."
    ::= { snmpTrapHostsIPv6 3 }

lnkAttachCount OBJECT-TYPE
    SYNTAX Integer32 (0..19)
    MAX-ACCESS read-write
    STATUS current
    DESCRIPTION
        "Count of secondary PDUs that are attached to the link."
    ::= { configuration 100 }

metrics OBJECT IDENTIFIER ::= { cpiPDU 3 }

mcurrent OBJECT IDENTIFIER ::= { metrics 1 }

currentxy1 OBJECT-TYPE
    SYNTAX Integer32 (0..2000)
    MAX-ACCESS read-only
    STATUS current
    DESCRIPTION
        "XY1 current draw in 1/100 Amps."
    ::= { mcurrent 1 }

currentyz1 OBJECT-TYPE
    SYNTAX Integer32 (0..2000)
    MAX-ACCESS read-only
    STATUS current
    DESCRIPTION
        "YZ1 current draw in 1/100 Amps."
    ::= { mcurrent 2 }

currentzx1 OBJECT-TYPE
    SYNTAX Integer32 (0..2000)
    MAX-ACCESS read-only
    STATUS current
    DESCRIPTION
        "ZX1 current draw in 1/100 Amps."
    ::= { mcurrent 3 }

currentxy2 OBJECT-TYPE
    SYNTAX Integer32 (0..2000)
    MAX-ACCESS read-only
    STATUS current
    DESCRIPTION
        "XY2 current draw in 1/100 Amps."
    ::= { mcurrent 4 }

currentyz2 OBJECT-TYPE
    SYNTAX Integer32 (0..2000)
    MAX-ACCESS read-only
    STATUS current
    DESCRIPTION
        "YZ2 current draw in 1/100 Amps."
    ::= { mcurrent 5 }

currentzx2 OBJECT-TYPE
    SYNTAX Integer32 (0..2000)
    MAX-ACCESS read-only
    STATUS current
    DESCRIPTION
        "ZX2 current draw in 1/100 Amps."
    ::= { mcurrent 6 }

mvoltage OBJECT IDENTIFIER ::= { metrics 2 }

voltagexy1 OBJECT-TYPE
    SYNTAX Integer32 (0..3120)
    MAX-ACCESS read-only
    STATUS current
    DESCRIPTION
        "XY1 voltage in 1/10 volts."
    ::= { mvoltage 1 }

voltageyz1 OBJECT-TYPE
    SYNTAX Integer32 (0..3120)
    MAX-ACCESS read-only
    STATUS current
    DESCRIPTION
        "YZ1 voltage in 1/10 volts."
    ::= { mvoltage 2 }

voltagezx1 OBJECT-TYPE
    SYNTAX Integer32 (0..3120)
    MAX-ACCESS read-only
    STATUS current
    DESCRIPTION
        "ZX1 voltage in 1/10 volts."
    ::= { mvoltage 3 }

voltagexy2 OBJECT-TYPE
    SYNTAX Integer32 (0..3120)
    MAX-ACCESS read-only
    STATUS current
    DESCRIPTION
        "XY2 voltage in 1/10 volts."
    ::= { mvoltage 4 }

voltageyz2 OBJECT-TYPE
    SYNTAX Integer32 (0..3120)
    MAX-ACCESS read-only
    STATUS current
    DESCRIPTION
        "YZ2 voltage in 1/10 volts."
    ::= { mvoltage 5 }

voltagezx2 OBJECT-TYPE
    SYNTAX Integer32 (0..3120)
    MAX-ACCESS read-only
    STATUS current
    DESCRIPTION
        "ZX2 voltage in 1/10 volts."
    ::= { mvoltage 6 }

mpower OBJECT IDENTIFIER ::= { metrics 3 }

powerxy1 OBJECT-TYPE
    SYNTAX Integer32 (0..6240)
    MAX-ACCESS read-only
    STATUS current
    DESCRIPTION
        "XY1 power consumption in Watts."
    ::= { mpower 1 }

poweryz1 OBJECT-TYPE
    SYNTAX Integer32 (0..6240)
    MAX-ACCESS read-only
    STATUS current
    DESCRIPTION
        "YZ1 power consumption in Watts."
    ::= { mpower 2 }

powerzx1 OBJECT-TYPE
    SYNTAX Integer32 (0..6240)
    MAX-ACCESS read-only
    STATUS current
    DESCRIPTION
        "ZX1 power consumption in Watts."
    ::= { mpower 3 }

powerxy2 OBJECT-TYPE
    SYNTAX Integer32 (0..6240)
    MAX-ACCESS read-only
    STATUS current
    DESCRIPTION
        "XY2 power consumption in Watts."
    ::= { mpower 4 }

poweryz2 OBJECT-TYPE
    SYNTAX Integer32 (0..6240)
    MAX-ACCESS read-only
    STATUS current
    DESCRIPTION
        "YZ2 power consumption in Watts."
    ::= { mpower 5 }

powerzx2 OBJECT-TYPE
    SYNTAX Integer32 (0..6240)
    MAX-ACCESS read-only
    STATUS current
    DESCRIPTION
        "ZX2 power consumption in Watts."
    ::= { mpower 6 }

mpowerFactor OBJECT IDENTIFIER ::= { metrics 4 }

powerFactxy1 OBJECT-TYPE
    SYNTAX Integer32 (-100..100)
    MAX-ACCESS read-only
    STATUS current
    DESCRIPTION
        "XY1 power factor x 100."
    ::= { mpowerFactor 1 }

powerFactyz1 OBJECT-TYPE
    SYNTAX Integer32 (-100..100)
    MAX-ACCESS read-only
    STATUS current
    DESCRIPTION
        "YZ1 power factor x 100."
    ::= { mpowerFactor 2 }

powerFactzx1 OBJECT-TYPE
    SYNTAX Integer32 (-100..100)
    MAX-ACCESS read-only
    STATUS current
    DESCRIPTION
        "ZX1 power factor x 100."
    ::= { mpowerFactor 3 }

powerFactxy2 OBJECT-TYPE
    SYNTAX Integer32 (-100..100)
    MAX-ACCESS read-only
    STATUS current
    DESCRIPTION
        "XY2 power factor x 100."
    ::= { mpowerFactor 4 }

powerFactyz2 OBJECT-TYPE
    SYNTAX Integer32 (-100..100)
    MAX-ACCESS read-only
    STATUS current
    DESCRIPTION
        "YZ2 power factor x 100."
    ::= { mpowerFactor 5 }

powerFactzx2 OBJECT-TYPE
    SYNTAX Integer32 (-100..100)
    MAX-ACCESS read-only
    STATUS current
    DESCRIPTION
        "ZX2 power factor x 100."
    ::= { mpowerFactor 6 }

receptacleCurrent OBJECT IDENTIFIER ::= { metrics 5 }

outlet1Current OBJECT-TYPE
    SYNTAX Integer32 (0..2000)
    MAX-ACCESS read-only
    STATUS current
    DESCRIPTION
        "Outlet1 current draw in 1/100 Amps."
    ::= { receptacleCurrent 1 }

outlet2Current OBJECT-TYPE
    SYNTAX Integer32 (0..2000)
    MAX-ACCESS read-only
    STATUS current
    DESCRIPTION
        "Outlet2 current draw in 1/100 Amps."
    ::= { receptacleCurrent 2 }

outlet3Current OBJECT-TYPE
    SYNTAX Integer32 (0..2000)
    MAX-ACCESS read-only
    STATUS current
    DESCRIPTION
        "Outlet3 current draw in 1/100 Amps."
    ::= { receptacleCurrent 3 }

outlet4Current OBJECT-TYPE
    SYNTAX Integer32 (0..2000)
    MAX-ACCESS read-only
    STATUS current
    DESCRIPTION
        "Outlet4 current draw in 1/100 Amps."
    ::= { receptacleCurrent 4 }

outlet5Current OBJECT-TYPE
    SYNTAX Integer32 (0..2000)
    MAX-ACCESS read-only
    STATUS current
    DESCRIPTION
        "Outlet5 current draw in 1/100 Amps."
    ::= { receptacleCurrent 5 }

outlet6Current OBJECT-TYPE
    SYNTAX Integer32 (0..2000)
    MAX-ACCESS read-only
    STATUS current
    DESCRIPTION
        "Outlet6 current draw in 1/100 Amps."
    ::= { receptacleCurrent 6 }

outlet7Current OBJECT-TYPE
    SYNTAX Integer32 (0..2000)
    MAX-ACCESS read-only
    STATUS current
    DESCRIPTION
        "Outlet7 current draw in 1/100 Amps."
    ::= { receptacleCurrent 7 }

outlet8Current OBJECT-TYPE
    SYNTAX Integer32 (0..2000)
    MAX-ACCESS read-only
    STATUS current
    DESCRIPTION
        "Outlet8 current draw in 1/100 Amps."
    ::= { receptacleCurrent 8 }

outlet9Current OBJECT-TYPE
    SYNTAX Integer32 (0..2000)
    MAX-ACCESS read-only
    STATUS current
    DESCRIPTION
        "Outlet9 current draw in 1/100 Amps."
    ::= { receptacleCurrent 9 }

outlet10Current OBJECT-TYPE
    SYNTAX Integer32 (0..2000)
    MAX-ACCESS read-only
    STATUS current
    DESCRIPTION
        "Outlet10 current draw in 1/100 Amps."
    ::= { receptacleCurrent 10 }

outlet11Current OBJECT-TYPE
    SYNTAX Integer32 (0..2000)
    MAX-ACCESS read-only
    STATUS current
    DESCRIPTION
        "Outlet11 current draw in 1/100 Amps."
    ::= { receptacleCurrent 11 }

outlet12Current OBJECT-TYPE
    SYNTAX Integer32 (0..2000)
    MAX-ACCESS read-only
    STATUS current
    DESCRIPTION
        "Outlet12 current draw in 1/100 Amps."
    ::= { receptacleCurrent 12 }

outlet13Current OBJECT-TYPE
    SYNTAX Integer32 (0..2000)
    MAX-ACCESS read-only
    STATUS current
    DESCRIPTION
        "Outlet13 current draw in 1/100 Amps."
    ::= { receptacleCurrent 13 }

outlet14Current OBJECT-TYPE
    SYNTAX Integer32 (0..2000)
    MAX-ACCESS read-only
    STATUS current
    DESCRIPTION
        "Outlet14 current draw in 1/100 Amps."
    ::= { receptacleCurrent 14 }

outlet15Current OBJECT-TYPE
    SYNTAX Integer32 (0..2000)
    MAX-ACCESS read-only
    STATUS current
    DESCRIPTION
        "Outlet15 current draw in 1/100 Amps."
    ::= { receptacleCurrent 15 }

outlet16Current OBJECT-TYPE
    SYNTAX Integer32 (0..2000)
    MAX-ACCESS read-only
    STATUS current
    DESCRIPTION
        "Outlet16 current draw in 1/100 Amps."
    ::= { receptacleCurrent 16 }

outlet17Current OBJECT-TYPE
    SYNTAX Integer32 (0..2000)
    MAX-ACCESS read-only
    STATUS current
    DESCRIPTION
        "Outlet17 current draw in 1/100 Amps."
    ::= { receptacleCurrent 17 }

outlet18Current OBJECT-TYPE
    SYNTAX Integer32 (0..2000)
    MAX-ACCESS read-only
    STATUS current
    DESCRIPTION
        "Outlet18 current draw in 1/100 Amps."
    ::= { receptacleCurrent 18 }

outlet19Current OBJECT-TYPE
    SYNTAX Integer32 (0..2000)
    MAX-ACCESS read-only
    STATUS current
    DESCRIPTION
        "Outlet19 current draw in 1/100 Amps."
    ::= { receptacleCurrent 19 }

outlet20Current OBJECT-TYPE
    SYNTAX Integer32 (0..2000)
    MAX-ACCESS read-only
    STATUS current
    DESCRIPTION
        "Outlet20 current draw in 1/100 Amps."
    ::= { receptacleCurrent 20 }

outlet21Current OBJECT-TYPE
    SYNTAX Integer32 (0..2000)
    MAX-ACCESS read-only
    STATUS current
    DESCRIPTION
        "Outlet21 current draw in 1/100 Amps."
    ::= { receptacleCurrent 21 }

outlet22Current OBJECT-TYPE
    SYNTAX Integer32 (0..2000)
    MAX-ACCESS read-only
    STATUS current
    DESCRIPTION
        "Outlet22 current draw in 1/100 Amps."
    ::= { receptacleCurrent 22 }

outlet23Current OBJECT-TYPE
    SYNTAX Integer32 (0..2000)
    MAX-ACCESS read-only
    STATUS current
    DESCRIPTION
        "Outlet23 current draw in 1/100 Amps."
    ::= { receptacleCurrent 23 }

outlet24Current OBJECT-TYPE
    SYNTAX Integer32 (0..2000)
    MAX-ACCESS read-only
    STATUS current
    DESCRIPTION
        "Outlet24 current draw in 1/100 Amps."
    ::= { receptacleCurrent 24 }

receptacleCurrentMap OBJECT-TYPE
    SYNTAX DisplayString (SIZE (0..120))
    MAX-ACCESS read-only
    STATUS current
    DESCRIPTION
        "Map of receptacle currents in ascending order and delimited by space."
    ::= { metrics 6 }

receptacleStatus OBJECT IDENTIFIER ::= { metrics 7 }

outlet1State OBJECT-TYPE
    SYNTAX Integer32 (0..1)
    MAX-ACCESS read-only
    STATUS current
    DESCRIPTION
        "Outlet1 power state, 0=OFF, 1=ON."
    ::= { receptacleStatus 1 }

outlet2State OBJECT-TYPE
    SYNTAX Integer32 (0..1)
    MAX-ACCESS read-only
    STATUS current
    DESCRIPTION
        "Outlet2 power state, 0=OFF, 1=ON."
    ::= { receptacleStatus 2 }

outlet3State OBJECT-TYPE
    SYNTAX Integer32 (0..1)
    MAX-ACCESS read-only
    STATUS current
    DESCRIPTION
        "Outlet3 power state, 0=OFF, 1=ON."
    ::= { receptacleStatus 3 }

outlet4State OBJECT-TYPE
    SYNTAX Integer32 (0..1)
    MAX-ACCESS read-only
    STATUS current
    DESCRIPTION
        "Outlet4 power state, 0=OFF, 1=ON."
    ::= { receptacleStatus 4 }

outlet5State OBJECT-TYPE
    SYNTAX Integer32 (0..1)
    MAX-ACCESS read-only
    STATUS current
    DESCRIPTION
        "Outlet5 power state, 0=OFF, 1=ON."
    ::= { receptacleStatus 5 }

outlet6State OBJECT-TYPE
    SYNTAX Integer32 (0..1)
    MAX-ACCESS read-only
    STATUS current
    DESCRIPTION
        "Outlet6 power state, 0=OFF, 1=ON."
    ::= { receptacleStatus 6 }

outlet7State OBJECT-TYPE
    SYNTAX Integer32 (0..1)
    MAX-ACCESS read-only
    STATUS current
    DESCRIPTION
        "Outlet7 power state, 0=OFF, 1=ON."
    ::= { receptacleStatus 7 }

outlet8State OBJECT-TYPE
    SYNTAX Integer32 (0..1)
    MAX-ACCESS read-only
    STATUS current
    DESCRIPTION
        "Outlet8 power state, 0=OFF, 1=ON."
    ::= { receptacleStatus 8 }

outlet9State OBJECT-TYPE
    SYNTAX Integer32 (0..1)
    MAX-ACCESS read-only
    STATUS current
    DESCRIPTION
        "Outlet9 power state, 0=OFF, 1=ON."
    ::= { receptacleStatus 9 }

outlet10State OBJECT-TYPE
    SYNTAX Integer32 (0..1)
    MAX-ACCESS read-only
    STATUS current
    DESCRIPTION
        "Outlet10 power state, 0=OFF, 1=ON."
    ::= { receptacleStatus 10 }

outlet11State OBJECT-TYPE
    SYNTAX Integer32 (0..1)
    MAX-ACCESS read-only
    STATUS current
    DESCRIPTION
        "Outlet11 power state, 0=OFF, 1=ON."
    ::= { receptacleStatus 11 }

outlet12State OBJECT-TYPE
    SYNTAX Integer32 (0..1)
    MAX-ACCESS read-only
    STATUS current
    DESCRIPTION
        "Outlet12 power state, 0=OFF, 1=ON."
    ::= { receptacleStatus 12 }

outlet13State OBJECT-TYPE
    SYNTAX Integer32 (0..1)
    MAX-ACCESS read-only
    STATUS current
    DESCRIPTION
        "Outlet13 power state, 0=OFF, 1=ON."
    ::= { receptacleStatus 13 }

outlet14State OBJECT-TYPE
    SYNTAX Integer32 (0..1)
    MAX-ACCESS read-only
    STATUS current
    DESCRIPTION
        "Outlet14 power state, 0=OFF, 1=ON."
    ::= { receptacleStatus 14 }

outlet15State OBJECT-TYPE
    SYNTAX Integer32 (0..1)
    MAX-ACCESS read-only
    STATUS current
    DESCRIPTION
        "Outlet15 power state, 0=OFF, 1=ON."
    ::= { receptacleStatus 15 }

outlet16State OBJECT-TYPE
    SYNTAX Integer32 (0..1)
    MAX-ACCESS read-only
    STATUS current
    DESCRIPTION
        "Outlet16 power state, 0=OFF, 1=ON."
    ::= { receptacleStatus 16 }

outlet17State OBJECT-TYPE
    SYNTAX Integer32 (0..1)
    MAX-ACCESS read-only
    STATUS current
    DESCRIPTION
        "Outlet17 power state, 0=OFF, 1=ON."
    ::= { receptacleStatus 17 }

outlet18State OBJECT-TYPE
    SYNTAX Integer32 (0..1)
    MAX-ACCESS read-only
    STATUS current
    DESCRIPTION
        "Outlet18 power state, 0=OFF, 1=ON."
    ::= { receptacleStatus 18 }

outlet19State OBJECT-TYPE
    SYNTAX Integer32 (0..1)
    MAX-ACCESS read-only
    STATUS current
    DESCRIPTION
        "Outlet19 power state, 0=OFF, 1=ON."
    ::= { receptacleStatus 19 }

outlet20State OBJECT-TYPE
    SYNTAX Integer32 (0..1)
    MAX-ACCESS read-only
    STATUS current
    DESCRIPTION
        "Outlet20 power state, 0=OFF, 1=ON."
    ::= { receptacleStatus 20 }

outlet21State OBJECT-TYPE
    SYNTAX Integer32 (0..1)
    MAX-ACCESS read-only
    STATUS current
    DESCRIPTION
        "Outlet21 power state, 0=OFF, 1=ON."
    ::= { receptacleStatus 21 }

outlet22State OBJECT-TYPE
    SYNTAX Integer32 (0..1)
    MAX-ACCESS read-only
    STATUS current
    DESCRIPTION
        "Outlet22 power state, 0=OFF, 1=ON."
    ::= { receptacleStatus 22 }

outlet23State OBJECT-TYPE
    SYNTAX Integer32 (0..1)
    MAX-ACCESS read-only
    STATUS current
    DESCRIPTION
        "Outlet23 power state, 0=OFF, 1=ON."
    ::= { receptacleStatus 23 }

outlet24State OBJECT-TYPE
    SYNTAX Integer32 (0..1)
    MAX-ACCESS read-only
    STATUS current
    DESCRIPTION
        "Outlet24 power state, 0=OFF, 1=ON."
    ::= { receptacleStatus 24 }

temperature OBJECT IDENTIFIER ::= { metrics 8 }

temperatureProbe1 OBJECT-TYPE
    SYNTAX Integer32 (0..20000)
    MAX-ACCESS read-only
    STATUS current
    DESCRIPTION
        "Probe 1 temperature in 1/100 degree Fahrenheit."
    ::= { temperature 1 }

temperatureProbe2 OBJECT-TYPE
    SYNTAX Integer32 (0..20000)
    MAX-ACCESS read-only
    STATUS current
    DESCRIPTION
        "Probe 2 temperature in 1/100 degree Fahrenheit."
    ::= { temperature 2 }

humidity OBJECT IDENTIFIER ::= { metrics 9 }

humidityProbe1 OBJECT-TYPE
    SYNTAX Integer32 (0..10000)
    MAX-ACCESS read-only
    STATUS current
    DESCRIPTION
        "Probe 1 humidity in 1/100 %."
    ::= { humidity 1 }

humidityProbe2 OBJECT-TYPE
    SYNTAX Integer32 (0..10000)
    MAX-ACCESS read-only
    STATUS current
    DESCRIPTION
        "Probe 2 humidity in 1/100 %."
    ::= { humidity 2 }

alarms OBJECT IDENTIFIER ::= { metrics 10 }

alarmsMaxMap OBJECT-TYPE
    SYNTAX Integer32
    MAX-ACCESS read-only
    STATUS current
    DESCRIPTION
        "Max threshold alarmed state bitmap: bit0=currA, bit1=currB, bit2=currC ...
        bit6=voltA, bit7=voltB, bit8=voltC ...
        bit12=temperature1, bit13=temperature2, bit14=humidity1, bit15=humidity2"
    ::= { alarms 1 }

alarmsMinMap OBJECT-TYPE
    SYNTAX Integer32
    MAX-ACCESS read-only
    STATUS current
    DESCRIPTION
        "Min threshold alarmed state bitmap: bit0=currA, bit1=currB, bit2=currC ...
        bit6=voltA, bit7=voltB, bit8=voltC ...
        bit12=temperature1, bit13=temperature2, bit14=humidity1, bit15=humidity2"
    ::= { alarms 2 }

alarmsWarnHiMap OBJECT-TYPE
    SYNTAX Integer32
    MAX-ACCESS read-only
    STATUS current
    DESCRIPTION
        "High threshold warning state bitmap: bit0=currA, bit1=currB, bit2=currC ...
        bit6=voltA, bit7=voltB, bit8=voltC ...
        bit12=temperature1, bit13=temperature2, bit14=humidity1, bit15=humidity2"
    ::= { alarms 3 }

alarmsWarnLoMap OBJECT-TYPE
    SYNTAX Integer32
    MAX-ACCESS read-only
    STATUS current
    DESCRIPTION
        "Low threshold warning state bitmap: bit0=currA, bit1=currB, bit2=currC ...
        bit6=voltA, bit7=voltB, bit8=voltC ...
        bit12=temperature1, bit13=temperature2, bit14=humidity1, bit15=humidity2"
    ::= { alarms 4 }

recep1To32AlarmsMaxMap OBJECT-TYPE
    SYNTAX Integer32
    MAX-ACCESS read-only
    STATUS current
    DESCRIPTION
        "Max threshold alarmed receptacle state bitmap: bit0=recep1, bit1=recep2, ... bit31=recep32"
    ::= { alarms 5 }

recep1To32AlarmsMinMap OBJECT-TYPE
    SYNTAX Integer32
    MAX-ACCESS read-only
    STATUS current
    DESCRIPTION
        "Min threshold alarmed receptacle state bitmap: bit0=recep1, bit1=recep2, ... bit31=recep32"
    ::= { alarms 7 }

recep1To32WarnHiMap OBJECT-TYPE
    SYNTAX Integer32
    MAX-ACCESS read-only
    STATUS current
    DESCRIPTION
        "High threshold warning receptacle state bitmap: bit0=recep1, bit1=recep2, ... bit31=recep32"
    ::= { alarms 9 }

recep1To32WarnLoMap OBJECT-TYPE
    SYNTAX Integer32
    MAX-ACCESS read-only
    STATUS current
    DESCRIPTION
        "Low threshold warning receptacle state bitmap: bit0=recep1, bit1=recep2, ... bit31=recep32"
    ::= { alarms 11 }

menergy OBJECT IDENTIFIER ::= { metrics 11 }

energyxy1s OBJECT-TYPE
    SYNTAX Counter64
    MAX-ACCESS read-only
    STATUS current
    DESCRIPTION
        "XY1 branch energy accumulated in decaWatt-secs, divide by 360 to obtain Watt-hr."
    ::= { menergy 1 }

energyyz1s OBJECT-TYPE
    SYNTAX Counter64
    MAX-ACCESS read-only
    STATUS current
    DESCRIPTION
        "YZ1 branch energy accumulated in decaWatt-secs, divide by 360 to obtain Watt-hr."
    ::= { menergy 2 }

energyzx1s OBJECT-TYPE
    SYNTAX Counter64
    MAX-ACCESS read-only
    STATUS current
    DESCRIPTION
        "ZX1 branch energy accumulated in decaWatt-secs, divide by 360 to obtain Watt-hr."
    ::= { menergy 3 }

energyxy2s OBJECT-TYPE
    SYNTAX Counter64
    MAX-ACCESS read-only
    STATUS current
    DESCRIPTION
        "XY2 branch energy accumulated in decaWatt-secs, divide by 360 to obtain Watt-hr."
    ::= { menergy 4 }

energyyz2s OBJECT-TYPE
    SYNTAX Counter64
    MAX-ACCESS read-only
    STATUS current
    DESCRIPTION
        "YZ2 branch energy accumulated in decaWatt-secs, divide by 360 to obtain Watt-hr."
    ::= { menergy 5 }

energyzx2s OBJECT-TYPE
    SYNTAX Counter64
    MAX-ACCESS read-only
    STATUS current
    DESCRIPTION
        "ZX2 branch energy accumulated in decaWatt-secs, divide by 360 to obtain Watt-hr."
    ::= { menergy 6 }

receptacleEnergy OBJECT IDENTIFIER ::= { metrics 12 }

receptacleEnergyoutlet1s OBJECT-TYPE
    SYNTAX Counter64
    MAX-ACCESS read-only
    STATUS current
    DESCRIPTION
        "Outlet1 receptacle energy accumulated in decaWatt-secs, divide by 360 to obtain Watt-hr."
    ::= { receptacleEnergy 1 }

receptacleEnergyoutlet2s OBJECT-TYPE
    SYNTAX Counter64
    MAX-ACCESS read-only
    STATUS current
    DESCRIPTION
        "Outlet2 receptacle energy accumulated in decaWatt-secs, divide by 360 to obtain Watt-hr."
    ::= { receptacleEnergy 2 }

receptacleEnergyoutlet3s OBJECT-TYPE
    SYNTAX Counter64
    MAX-ACCESS read-only
    STATUS current
    DESCRIPTION
        "Outlet3 receptacle energy accumulated in decaWatt-secs, divide by 360 to obtain Watt-hr."
    ::= { receptacleEnergy 3 }

receptacleEnergyoutlet4s OBJECT-TYPE
    SYNTAX Counter64
    MAX-ACCESS read-only
    STATUS current
    DESCRIPTION
        "Outlet4 receptacle energy accumulated in decaWatt-secs, divide by 360 to obtain Watt-hr."
    ::= { receptacleEnergy 4 }

receptacleEnergyoutlet5s OBJECT-TYPE
    SYNTAX Counter64
    MAX-ACCESS read-only
    STATUS current
    DESCRIPTION
        "Outlet5 receptacle energy accumulated in decaWatt-secs, divide by 360 to obtain Watt-hr."
    ::= { receptacleEnergy 5 }

receptacleEnergyoutlet6s OBJECT-TYPE
    SYNTAX Counter64
    MAX-ACCESS read-only
    STATUS current
    DESCRIPTION
        "Outlet6 receptacle energy accumulated in decaWatt-secs, divide by 360 to obtain Watt-hr."
    ::= { receptacleEnergy 6 }

receptacleEnergyoutlet7s OBJECT-TYPE
    SYNTAX Counter64
    MAX-ACCESS read-only
    STATUS current
    DESCRIPTION
        "Outlet7 receptacle energy accumulated in decaWatt-secs, divide by 360 to obtain Watt-hr."
    ::= { receptacleEnergy 7 }

receptacleEnergyoutlet8s OBJECT-TYPE
    SYNTAX Counter64
    MAX-ACCESS read-only
    STATUS current
    DESCRIPTION
        "Outlet8 receptacle energy accumulated in decaWatt-secs, divide by 360 to obtain Watt-hr."
    ::= { receptacleEnergy 8 }

receptacleEnergyoutlet9s OBJECT-TYPE
    SYNTAX Counter64
    MAX-ACCESS read-only
    STATUS current
    DESCRIPTION
        "Outlet9 receptacle energy accumulated in decaWatt-secs, divide by 360 to obtain Watt-hr."
    ::= { receptacleEnergy 9 }

receptacleEnergyoutlet10s OBJECT-TYPE
    SYNTAX Counter64
    MAX-ACCESS read-only
    STATUS current
    DESCRIPTION
        "Outlet10 receptacle energy accumulated in decaWatt-secs, divide by 360 to obtain Watt-hr."
    ::= { receptacleEnergy 10 }

receptacleEnergyoutlet11s OBJECT-TYPE
    SYNTAX Counter64
    MAX-ACCESS read-only
    STATUS current
    DESCRIPTION
        "Outlet11 receptacle energy accumulated in decaWatt-secs, divide by 360 to obtain Watt-hr."
    ::= { receptacleEnergy 11 }

receptacleEnergyoutlet12s OBJECT-TYPE
    SYNTAX Counter64
    MAX-ACCESS read-only
    STATUS current
    DESCRIPTION
        "Outlet12 receptacle energy accumulated in decaWatt-secs, divide by 360 to obtain Watt-hr."
    ::= { receptacleEnergy 12 }

receptacleEnergyoutlet13s OBJECT-TYPE
    SYNTAX Counter64
    MAX-ACCESS read-only
    STATUS current
    DESCRIPTION
        "Outlet13 receptacle energy accumulated in decaWatt-secs, divide by 360 to obtain Watt-hr."
    ::= { receptacleEnergy 13 }

receptacleEnergyoutlet14s OBJECT-TYPE
    SYNTAX Counter64
    MAX-ACCESS read-only
    STATUS current
    DESCRIPTION
        "Outlet14 receptacle energy accumulated in decaWatt-secs, divide by 360 to obtain Watt-hr."
    ::= { receptacleEnergy 14 }

receptacleEnergyoutlet15s OBJECT-TYPE
    SYNTAX Counter64
    MAX-ACCESS read-only
    STATUS current
    DESCRIPTION
        "Outlet15 receptacle energy accumulated in decaWatt-secs, divide by 360 to obtain Watt-hr."
    ::= { receptacleEnergy 15 }

receptacleEnergyoutlet16s OBJECT-TYPE
    SYNTAX Counter64
    MAX-ACCESS read-only
    STATUS current
    DESCRIPTION
        "Outlet16 receptacle energy accumulated in decaWatt-secs, divide by 360 to obtain Watt-hr."
    ::= { receptacleEnergy 16 }

receptacleEnergyoutlet17s OBJECT-TYPE
    SYNTAX Counter64
    MAX-ACCESS read-only
    STATUS current
    DESCRIPTION
        "Outlet17 receptacle energy accumulated in decaWatt-secs, divide by 360 to obtain Watt-hr."
    ::= { receptacleEnergy 17 }

receptacleEnergyoutlet18s OBJECT-TYPE
    SYNTAX Counter64
    MAX-ACCESS read-only
    STATUS current
    DESCRIPTION
        "Outlet18 receptacle energy accumulated in decaWatt-secs, divide by 360 to obtain Watt-hr."
    ::= { receptacleEnergy 18 }

receptacleEnergyoutlet19s OBJECT-TYPE
    SYNTAX Counter64
    MAX-ACCESS read-only
    STATUS current
    DESCRIPTION
        "Outlet19 receptacle energy accumulated in decaWatt-secs, divide by 360 to obtain Watt-hr."
    ::= { receptacleEnergy 19 }

receptacleEnergyoutlet20s OBJECT-TYPE
    SYNTAX Counter64
    MAX-ACCESS read-only
    STATUS current
    DESCRIPTION
        "Outlet20 receptacle energy accumulated in decaWatt-secs, divide by 360 to obtain Watt-hr."
    ::= { receptacleEnergy 20 }

receptacleEnergyoutlet21s OBJECT-TYPE
    SYNTAX Counter64
    MAX-ACCESS read-only
    STATUS current
    DESCRIPTION
        "Outlet21 receptacle energy accumulated in decaWatt-secs, divide by 360 to obtain Watt-hr."
    ::= { receptacleEnergy 21 }

receptacleEnergyoutlet22s OBJECT-TYPE
    SYNTAX Counter64
    MAX-ACCESS read-only
    STATUS current
    DESCRIPTION
        "Outlet22 receptacle energy accumulated in decaWatt-secs, divide by 360 to obtain Watt-hr."
    ::= { receptacleEnergy 22 }

receptacleEnergyoutlet23s OBJECT-TYPE
    SYNTAX Counter64
    MAX-ACCESS read-only
    STATUS current
    DESCRIPTION
        "Outlet23 receptacle energy accumulated in decaWatt-secs, divide by 360 to obtain Watt-hr."
    ::= { receptacleEnergy 23 }

receptacleEnergyoutlet24s OBJECT-TYPE
    SYNTAX Counter64
    MAX-ACCESS read-only
    STATUS current
    DESCRIPTION
        "Outlet24 receptacle energy accumulated in decaWatt-secs, divide by 360 to obtain Watt-hr."
    ::= { receptacleEnergy 24 }

mline OBJECT IDENTIFIER ::= { metrics 13 }

line1curr OBJECT-TYPE
    SYNTAX Integer32 (0..3000)
    MAX-ACCESS read-only
    STATUS current
    DESCRIPTION
        "Line 1 current draw in 1/100 Amps."
    ::= { mline 1 }

line2curr OBJECT-TYPE
    SYNTAX Integer32 (0..3000)
    MAX-ACCESS read-only
    STATUS current
    DESCRIPTION
        "Line 2 current draw in 1/100 Amps."
    ::= { mline 2 }

line3curr OBJECT-TYPE
    SYNTAX Integer32 (0..3000)
    MAX-ACCESS read-only
    STATUS current
    DESCRIPTION
        "Line 3 current draw in 1/100 Amps."
    ::= { mline 3 }

control OBJECT IDENTIFIER ::= { cpiPDU 4 }

creceptacleControl OBJECT IDENTIFIER ::= { control 1 }

outlet1ONOFF OBJECT-TYPE
    SYNTAX Integer32 (0..1)
    MAX-ACCESS read-write
    STATUS current
    DESCRIPTION
        "Turn ON or OFF power to Outlet1, 1=ON, 0=OFF."
    ::= { creceptacleControl 1 }

outlet2ONOFF OBJECT-TYPE
    SYNTAX Integer32 (0..1)
    MAX-ACCESS read-write
    STATUS current
    DESCRIPTION
        "Turn ON or OFF power to Outlet2, 1=ON, 0=OFF."
    ::= { creceptacleControl 2 }

outlet3ONOFF OBJECT-TYPE
    SYNTAX Integer32 (0..1)
    MAX-ACCESS read-write
    STATUS current
    DESCRIPTION
        "Turn ON or OFF power to Outlet3, 1=ON, 0=OFF."
    ::= { creceptacleControl 3 }

outlet4ONOFF OBJECT-TYPE
    SYNTAX Integer32 (0..1)
    MAX-ACCESS read-write
    STATUS current
    DESCRIPTION
        "Turn ON or OFF power to Outlet4, 1=ON, 0=OFF."
    ::= { creceptacleControl 4 }

outlet5ONOFF OBJECT-TYPE
    SYNTAX Integer32 (0..1)
    MAX-ACCESS read-write
    STATUS current
    DESCRIPTION
        "Turn ON or OFF power to Outlet5, 1=ON, 0=OFF."
    ::= { creceptacleControl 5 }

outlet6ONOFF OBJECT-TYPE
    SYNTAX Integer32 (0..1)
    MAX-ACCESS read-write
    STATUS current
    DESCRIPTION
        "Turn ON or OFF power to Outlet6, 1=ON, 0=OFF."
    ::= { creceptacleControl 6 }

outlet7ONOFF OBJECT-TYPE
    SYNTAX Integer32 (0..1)
    MAX-ACCESS read-write
    STATUS current
    DESCRIPTION
        "Turn ON or OFF power to Outlet7, 1=ON, 0=OFF."
    ::= { creceptacleControl 7 }

outlet8ONOFF OBJECT-TYPE
    SYNTAX Integer32 (0..1)
    MAX-ACCESS read-write
    STATUS current
    DESCRIPTION
        "Turn ON or OFF power to Outlet8, 1=ON, 0=OFF."
    ::= { creceptacleControl 8 }

outlet9ONOFF OBJECT-TYPE
    SYNTAX Integer32 (0..1)
    MAX-ACCESS read-write
    STATUS current
    DESCRIPTION
        "Turn ON or OFF power to Outlet9, 1=ON, 0=OFF."
    ::= { creceptacleControl 9 }

outlet10ONOFF OBJECT-TYPE
    SYNTAX Integer32 (0..1)
    MAX-ACCESS read-write
    STATUS current
    DESCRIPTION
        "Turn ON or OFF power to Outlet10, 1=ON, 0=OFF."
    ::= { creceptacleControl 10 }

outlet11ONOFF OBJECT-TYPE
    SYNTAX Integer32 (0..1)
    MAX-ACCESS read-write
    STATUS current
    DESCRIPTION
        "Turn ON or OFF power to Outlet11, 1=ON, 0=OFF."
    ::= { creceptacleControl 11 }

outlet12ONOFF OBJECT-TYPE
    SYNTAX Integer32 (0..1)
    MAX-ACCESS read-write
    STATUS current
    DESCRIPTION
        "Turn ON or OFF power to Outlet12, 1=ON, 0=OFF."
    ::= { creceptacleControl 12 }

outlet13ONOFF OBJECT-TYPE
    SYNTAX Integer32 (0..1)
    MAX-ACCESS read-write
    STATUS current
    DESCRIPTION
        "Turn ON or OFF power to Outlet13, 1=ON, 0=OFF."
    ::= { creceptacleControl 13 }

outlet14ONOFF OBJECT-TYPE
    SYNTAX Integer32 (0..1)
    MAX-ACCESS read-write
    STATUS current
    DESCRIPTION
        "Turn ON or OFF power to Outlet14, 1=ON, 0=OFF."
    ::= { creceptacleControl 14 }

outlet15ONOFF OBJECT-TYPE
    SYNTAX Integer32 (0..1)
    MAX-ACCESS read-write
    STATUS current
    DESCRIPTION
        "Turn ON or OFF power to Outlet15, 1=ON, 0=OFF."
    ::= { creceptacleControl 15 }

outlet16ONOFF OBJECT-TYPE
    SYNTAX Integer32 (0..1)
    MAX-ACCESS read-write
    STATUS current
    DESCRIPTION
        "Turn ON or OFF power to Outlet16, 1=ON, 0=OFF."
    ::= { creceptacleControl 16 }

outlet17ONOFF OBJECT-TYPE
    SYNTAX Integer32 (0..1)
    MAX-ACCESS read-write
    STATUS current
    DESCRIPTION
        "Turn ON or OFF power to Outlet17, 1=ON, 0=OFF."
    ::= { creceptacleControl 17 }

outlet18ONOFF OBJECT-TYPE
    SYNTAX Integer32 (0..1)
    MAX-ACCESS read-write
    STATUS current
    DESCRIPTION
        "Turn ON or OFF power to Outlet18, 1=ON, 0=OFF."
    ::= { creceptacleControl 18 }

outlet19ONOFF OBJECT-TYPE
    SYNTAX Integer32 (0..1)
    MAX-ACCESS read-write
    STATUS current
    DESCRIPTION
        "Turn ON or OFF power to Outlet19, 1=ON, 0=OFF."
    ::= { creceptacleControl 19 }

outlet20ONOFF OBJECT-TYPE
    SYNTAX Integer32 (0..1)
    MAX-ACCESS read-write
    STATUS current
    DESCRIPTION
        "Turn ON or OFF power to Outlet20, 1=ON, 0=OFF."
    ::= { creceptacleControl 20 }

outlet21ONOFF OBJECT-TYPE
    SYNTAX Integer32 (0..1)
    MAX-ACCESS read-write
    STATUS current
    DESCRIPTION
        "Turn ON or OFF power to Outlet21, 1=ON, 0=OFF."
    ::= { creceptacleControl 21 }

outlet22ONOFF OBJECT-TYPE
    SYNTAX Integer32 (0..1)
    MAX-ACCESS read-write
    STATUS current
    DESCRIPTION
        "Turn ON or OFF power to Outlet22, 1=ON, 0=OFF."
    ::= { creceptacleControl 22 }

outlet23ONOFF OBJECT-TYPE
    SYNTAX Integer32 (0..1)
    MAX-ACCESS read-write
    STATUS current
    DESCRIPTION
        "Turn ON or OFF power to Outlet23, 1=ON, 0=OFF."
    ::= { creceptacleControl 23 }

outlet24ONOFF OBJECT-TYPE
    SYNTAX Integer32 (0..1)
    MAX-ACCESS read-write
    STATUS current
    DESCRIPTION
        "Turn ON or OFF power to Outlet24, 1=ON, 0=OFF."
    ::= { creceptacleControl 24 }

receptacleReset OBJECT IDENTIFIER ::= { control 2 }

outlet1Reset OBJECT-TYPE
    SYNTAX Integer32 (0..1)
    MAX-ACCESS read-write
    STATUS current
    DESCRIPTION
        "Reset power to Outlet1, 1=reset."
    ::= { receptacleReset 1 }

outlet2Reset OBJECT-TYPE
    SYNTAX Integer32 (0..1)
    MAX-ACCESS read-write
    STATUS current
    DESCRIPTION
        "Reset power to Outlet2, 1=reset."
    ::= { receptacleReset 2 }

outlet3Reset OBJECT-TYPE
    SYNTAX Integer32 (0..1)
    MAX-ACCESS read-write
    STATUS current
    DESCRIPTION
        "Reset power to Outlet3, 1=reset."
    ::= { receptacleReset 3 }

outlet4Reset OBJECT-TYPE
    SYNTAX Integer32 (0..1)
    MAX-ACCESS read-write
    STATUS current
    DESCRIPTION
        "Reset power to Outlet4, 1=reset."
    ::= { receptacleReset 4 }

outlet5Reset OBJECT-TYPE
    SYNTAX Integer32 (0..1)
    MAX-ACCESS read-write
    STATUS current
    DESCRIPTION
        "Reset power to Outlet5, 1=reset."
    ::= { receptacleReset 5 }

outlet6Reset OBJECT-TYPE
    SYNTAX Integer32 (0..1)
    MAX-ACCESS read-write
    STATUS current
    DESCRIPTION
        "Reset power to Outlet6, 1=reset."
    ::= { receptacleReset 6 }

outlet7Reset OBJECT-TYPE
    SYNTAX Integer32 (0..1)
    MAX-ACCESS read-write
    STATUS current
    DESCRIPTION
        "Reset power to Outlet7, 1=reset."
    ::= { receptacleReset 7 }

outlet8Reset OBJECT-TYPE
    SYNTAX Integer32 (0..1)
    MAX-ACCESS read-write
    STATUS current
    DESCRIPTION
        "Reset power to Outlet8, 1=reset."
    ::= { receptacleReset 8 }

outlet9Reset OBJECT-TYPE
    SYNTAX Integer32 (0..1)
    MAX-ACCESS read-write
    STATUS current
    DESCRIPTION
        "Reset power to Outlet9, 1=reset."
    ::= { receptacleReset 9 }

outlet10Reset OBJECT-TYPE
    SYNTAX Integer32 (0..1)
    MAX-ACCESS read-write
    STATUS current
    DESCRIPTION
        "Reset power to Outlet10, 1=reset."
    ::= { receptacleReset 10 }

outlet11Reset OBJECT-TYPE
    SYNTAX Integer32 (0..1)
    MAX-ACCESS read-write
    STATUS current
    DESCRIPTION
        "Reset power to Outlet11, 1=reset."
    ::= { receptacleReset 11 }

outlet12Reset OBJECT-TYPE
    SYNTAX Integer32 (0..1)
    MAX-ACCESS read-write
    STATUS current
    DESCRIPTION
        "Reset power to Outlet12, 1=reset."
    ::= { receptacleReset 12 }

outlet13Reset OBJECT-TYPE
    SYNTAX Integer32 (0..1)
    MAX-ACCESS read-write
    STATUS current
    DESCRIPTION
        "Reset power to Outlet13, 1=reset."
    ::= { receptacleReset 13 }

outlet14Reset OBJECT-TYPE
    SYNTAX Integer32 (0..1)
    MAX-ACCESS read-write
    STATUS current
    DESCRIPTION
        "Reset power to Outlet14, 1=reset."
    ::= { receptacleReset 14 }

outlet15Reset OBJECT-TYPE
    SYNTAX Integer32 (0..1)
    MAX-ACCESS read-write
    STATUS current
    DESCRIPTION
        "Reset power to Outlet15, 1=reset."
    ::= { receptacleReset 15 }

outlet16Reset OBJECT-TYPE
    SYNTAX Integer32 (0..1)
    MAX-ACCESS read-write
    STATUS current
    DESCRIPTION
        "Reset power to Outlet16, 1=reset."
    ::= { receptacleReset 16 }

outlet17Reset OBJECT-TYPE
    SYNTAX Integer32 (0..1)
    MAX-ACCESS read-write
    STATUS current
    DESCRIPTION
        "Reset power to Outlet17, 1=reset."
    ::= { receptacleReset 17 }

outlet18Reset OBJECT-TYPE
    SYNTAX Integer32 (0..1)
    MAX-ACCESS read-write
    STATUS current
    DESCRIPTION
        "Reset power to Outlet18, 1=reset."
    ::= { receptacleReset 18 }

outlet19Reset OBJECT-TYPE
    SYNTAX Integer32 (0..1)
    MAX-ACCESS read-write
    STATUS current
    DESCRIPTION
        "Reset power to Outlet19, 1=reset."
    ::= { receptacleReset 19 }

outlet20Reset OBJECT-TYPE
    SYNTAX Integer32 (0..1)
    MAX-ACCESS read-write
    STATUS current
    DESCRIPTION
        "Reset power to Outlet20, 1=reset."
    ::= { receptacleReset 20 }

outlet21Reset OBJECT-TYPE
    SYNTAX Integer32 (0..1)
    MAX-ACCESS read-write
    STATUS current
    DESCRIPTION
        "Reset power to Outlet21, 1=reset."
    ::= { receptacleReset 21 }

outlet22Reset OBJECT-TYPE
    SYNTAX Integer32 (0..1)
    MAX-ACCESS read-write
    STATUS current
    DESCRIPTION
        "Reset power to Outlet22, 1=reset."
    ::= { receptacleReset 22 }

outlet23Reset OBJECT-TYPE
    SYNTAX Integer32 (0..1)
    MAX-ACCESS read-write
    STATUS current
    DESCRIPTION
        "Reset power to Outlet23, 1=reset."
    ::= { receptacleReset 23 }

outlet24Reset OBJECT-TYPE
    SYNTAX Integer32 (0..1)
    MAX-ACCESS read-write
    STATUS current
    DESCRIPTION
        "Reset power to Outlet24, 1=reset."
    ::= { receptacleReset 24 }

receptacleCtrlMap OBJECT-TYPE
    SYNTAX DisplayString (SIZE (0..24))
    MAX-ACCESS read-only
    STATUS current
    DESCRIPTION
        "Map of receptacle status in ascending order, 1=ON, 0=OFF."
    ::= { control 3 }

chained OBJECT IDENTIFIER ::= { cpiPDU 5 }

pduCount OBJECT-TYPE
    SYNTAX Integer32 (0..32)
    MAX-ACCESS read-only
    STATUS current
    DESCRIPTION
        "Count of number of PDUs in the chain."
    ::= { chained 1 }

pduMap OBJECT-TYPE
    SYNTAX OCTET STRING (SIZE (0..300))
    MAX-ACCESS read-only
    STATUS current
    DESCRIPTION
        "Table map of PDU IDs in the chain, each ID consists of 4 bytes."
    ::= { chained 2 }

pduSelect OBJECT-TYPE
    SYNTAX Integer32 (0..16777215)
    MAX-ACCESS read-write
    STATUS current
    DESCRIPTION
        "Selects the PDUs in the chain for access."
    ::= { chained 3 }

pduNamelist OBJECT-TYPE
    SYNTAX OCTET STRING (SIZE (0..2048))
    MAX-ACCESS read-only
    STATUS current
    DESCRIPTION
        "List of PDU Names in the chain link, delimited by '|' and in matching order with pduMap."
    ::= { chained 4 }

cpiTraps OBJECT IDENTIFIER ::= { cpiPDU 6 }

cpiSpecific OBJECT IDENTIFIER ::= { cpiTraps 0 }

maxCurrentxy1 NOTIFICATION-TYPE
    OBJECTS { pduSelect, currentxy1 }
    STATUS  current
    DESCRIPTION
        "Trap is sent when current in XY1 exceeds set limit."
    ::= { cpiSpecific 1 }

maxCurrentyz1 NOTIFICATION-TYPE
    OBJECTS { pduSelect, currentyz1 }
    STATUS  current
    DESCRIPTION
        "Trap is sent when current in YZ1 exceeds set limit."
    ::= { cpiSpecific 2 }

maxCurrentzx1 NOTIFICATION-TYPE
    OBJECTS { pduSelect, currentzx1 }
    STATUS  current
    DESCRIPTION
        "Trap is sent when current in ZX1 exceeds set limit."
    ::= { cpiSpecific 3 }

maxCurrentxy2 NOTIFICATION-TYPE
    OBJECTS { pduSelect, currentxy2 }
    STATUS  current
    DESCRIPTION
        "Trap is sent when current in XY2 exceeds set limit."
    ::= { cpiSpecific 4 }

maxCurrentyz2 NOTIFICATION-TYPE
    OBJECTS { pduSelect, currentyz2 }
    STATUS  current
    DESCRIPTION
        "Trap is sent when current in YZ2 exceeds set limit."
    ::= { cpiSpecific 5 }

maxCurrentzx2 NOTIFICATION-TYPE
    OBJECTS { pduSelect, currentzx2 }
    STATUS  current
    DESCRIPTION
        "Trap is sent when current in ZX2 exceeds set limit."
    ::= { cpiSpecific 6 }

minCurrentxy1 NOTIFICATION-TYPE
    OBJECTS { pduSelect, currentxy1 }
    STATUS  current
    DESCRIPTION
        "Trap is sent when current in XY1 drops below set limit."
    ::= { cpiSpecific 7 }

minCurrentyz1 NOTIFICATION-TYPE
    OBJECTS { pduSelect, currentyz1 }
    STATUS  current
    DESCRIPTION
        "Trap is sent when current in YZ1 drops below set limit."
    ::= { cpiSpecific 8 }

minCurrentzx1 NOTIFICATION-TYPE
    OBJECTS { pduSelect, currentzx1 }
    STATUS  current
    DESCRIPTION
        "Trap is sent when current in ZX1 drops below set limit."
    ::= { cpiSpecific 9 }

minCurrentxy2 NOTIFICATION-TYPE
    OBJECTS { pduSelect, currentxy2 }
    STATUS  current
    DESCRIPTION
        "Trap is sent when current in XY2 drops below set limit."
    ::= { cpiSpecific 10 }

minCurrentyz2 NOTIFICATION-TYPE
    OBJECTS { pduSelect, currentyz2 }
    STATUS  current
    DESCRIPTION
        "Trap is sent when current in YZ2 drops below set limit."
    ::= { cpiSpecific 11 }

minCurrentzx2 NOTIFICATION-TYPE
    OBJECTS { pduSelect, currentzx2 }
    STATUS  current
    DESCRIPTION
        "Trap is sent when current in ZX2 drops below set limit."
    ::= { cpiSpecific 12 }

maxVoltxy1 NOTIFICATION-TYPE
    OBJECTS { pduSelect, voltagexy1 }
    STATUS  current
    DESCRIPTION
        "Trap is sent when voltage in XY1 exceeds high limit."
    ::= { cpiSpecific 13 }

maxVoltyz1 NOTIFICATION-TYPE
    OBJECTS { pduSelect, voltageyz1 }
    STATUS  current
    DESCRIPTION
        "Trap is sent when voltage in YZ1 exceeds high limit."
    ::= { cpiSpecific 14 }

maxVoltzx1 NOTIFICATION-TYPE
    OBJECTS { pduSelect, voltagezx1 }
    STATUS  current
    DESCRIPTION
        "Trap is sent when voltage in ZX1 exceeds high limit."
    ::= { cpiSpecific 15 }

maxVoltxy2 NOTIFICATION-TYPE
    OBJECTS { pduSelect, voltagexy2 }
    STATUS  current
    DESCRIPTION
        "Trap is sent when voltage in XY2 exceeds high limit."
    ::= { cpiSpecific 16 }

maxVoltyz2 NOTIFICATION-TYPE
    OBJECTS { pduSelect, voltageyz2 }
    STATUS  current
    DESCRIPTION
        "Trap is sent when voltage in YZ2 exceeds high limit."
    ::= { cpiSpecific 17 }

maxVoltzx2 NOTIFICATION-TYPE
    OBJECTS { pduSelect, voltagezx2 }
    STATUS  current
    DESCRIPTION
        "Trap is sent when voltage in ZX2 exceeds high limit."
    ::= { cpiSpecific 18 }

minVoltxy1 NOTIFICATION-TYPE
    OBJECTS { pduSelect, voltagexy1 }
    STATUS  current
    DESCRIPTION
        "Trap is sent when voltage in XY1 drops below low limit."
    ::= { cpiSpecific 19 }

minVoltyz1 NOTIFICATION-TYPE
    OBJECTS { pduSelect, voltageyz1 }
    STATUS  current
    DESCRIPTION
        "Trap is sent when voltage in YZ1 drops below low limit."
    ::= { cpiSpecific 20 }

minVoltzx1 NOTIFICATION-TYPE
    OBJECTS { pduSelect, voltagezx1 }
    STATUS  current
    DESCRIPTION
        "Trap is sent when voltage in ZX1 drops below low limit."
    ::= { cpiSpecific 21 }

minVoltxy2 NOTIFICATION-TYPE
    OBJECTS { pduSelect, voltagexy2 }
    STATUS  current
    DESCRIPTION
        "Trap is sent when voltage in XY2 drops below low limit."
    ::= { cpiSpecific 22 }

minVoltyz2 NOTIFICATION-TYPE
    OBJECTS { pduSelect, voltageyz2 }
    STATUS  current
    DESCRIPTION
        "Trap is sent when voltage in YZ2 drops below low limit."
    ::= { cpiSpecific 23 }

minVoltzx2 NOTIFICATION-TYPE
    OBJECTS { pduSelect, voltagezx2 }
    STATUS  current
    DESCRIPTION
        "Trap is sent when voltage in ZX2 drops below low limit."
    ::= { cpiSpecific 24 }

maxTemperature1 NOTIFICATION-TYPE
    OBJECTS { pduSelect, temperatureProbe1 }
    STATUS  current
    DESCRIPTION
        "Trap is sent when temperature exceeds high limit."
    ::= { cpiSpecific 25 }

maxTemperature2 NOTIFICATION-TYPE
    OBJECTS { pduSelect, temperatureProbe2 }
    STATUS  current
    DESCRIPTION
        "Trap is sent when temperature exceeds high limit."
    ::= { cpiSpecific 26 }

minTemperature1 NOTIFICATION-TYPE
    OBJECTS { pduSelect, temperatureProbe1 }
    STATUS  current
    DESCRIPTION
        "Trap is sent when temperature drops below low limit."
    ::= { cpiSpecific 27 }

minTemperature2 NOTIFICATION-TYPE
    OBJECTS { pduSelect, temperatureProbe2 }
    STATUS  current
    DESCRIPTION
        "Trap is sent when temperature drops below low limit."
    ::= { cpiSpecific 28 }

maxHumidity1 NOTIFICATION-TYPE
    OBJECTS { pduSelect, humidityProbe1 }
    STATUS  current
    DESCRIPTION
        "Trap is sent when humidity exceeds high limit."
    ::= { cpiSpecific 29 }

maxHumidity2 NOTIFICATION-TYPE
    OBJECTS { pduSelect, humidityProbe2 }
    STATUS  current
    DESCRIPTION
        "Trap is sent when humidity exceeds high limit."
    ::= { cpiSpecific 30 }

minHumidity1 NOTIFICATION-TYPE
    OBJECTS { pduSelect, humidityProbe1 }
    STATUS  current
    DESCRIPTION
        "Trap is sent when humidity drops below low limit."
    ::= { cpiSpecific 31 }

minHumidity2 NOTIFICATION-TYPE
    OBJECTS { pduSelect, humidityProbe2 }
    STATUS  current
    DESCRIPTION
        "Trap is sent when humidity drops below low limit."
    ::= { cpiSpecific 32 }

changeLog NOTIFICATION-TYPE
    OBJECTS { pduSelect, 
        voltagexy1,
        voltageyz1,
        voltagezx1,
        voltagexy2,
        voltageyz2,
        voltagezx2,
        currentxy1,
        currentyz1,
        currentzx1,
        currentxy2,
        currentyz2,
        currentzx2,
        receptacleCurrentMap,
        receptacleCtrlMap,
        temperatureProbe1,
        humidityProbe1,
        temperatureProbe2,
        humidityProbe2,
        alarmsMaxMap, 
        alarmsMinMap, 
        alarmsWarnHiMap, 
        alarmsWarnLoMap, 
        recep1To32AlarmsMaxMap, 
        recep1To32AlarmsMinMap, 
        recep1To32WarnHiMap, 
        recep1To32WarnLoMap 
    }
    STATUS  current
    DESCRIPTION
        "Trap is sent when changes in current exceed the amount set in LOGDIFFERENCE."
    ::= { cpiSpecific 33 }

dataLog NOTIFICATION-TYPE
    OBJECTS { pduSelect, 
        voltagexy1,
        voltageyz1,
        voltagezx1,
        voltagexy2,
        voltageyz2,
        voltagezx2,
        currentxy1,
        currentyz1,
        currentzx1,
        currentxy2,
        currentyz2,
        currentzx2,
        receptacleCurrentMap,
        receptacleCtrlMap,
        temperatureProbe1,
        humidityProbe1,
        temperatureProbe2,
        humidityProbe2,
        alarmsMaxMap, 
        alarmsMinMap, 
        alarmsWarnHiMap, 
        alarmsWarnLoMap, 
        recep1To32AlarmsMaxMap, 
        recep1To32AlarmsMinMap, 
        recep1To32WarnHiMap, 
        recep1To32WarnLoMap 
    }
    STATUS  current
    DESCRIPTION
        "Trap is sent when the data logging interval time is reached"
    ::= { cpiSpecific 34 }

alarmChange NOTIFICATION-TYPE
    OBJECTS { pduSelect, 
        alarmsMaxMap, 
        alarmsMinMap, 
        alarmsWarnHiMap, 
        alarmsWarnLoMap, 
        recep1To32AlarmsMaxMap, 
        recep1To32AlarmsMinMap, 
        recep1To32WarnHiMap, 
        recep1To32WarnLoMap 
    }
    STATUS  current
    DESCRIPTION
        "Trap is sent when all alarms have been resolved/cleared"
    ::= { cpiSpecific 35 }

-- conformance information

cpiMIBConformance OBJECT IDENTIFIER ::= { products 2 }

cpiMIBCompliances OBJECT IDENTIFIER ::= { cpiMIBConformance 1 }

cpiMIBGroups OBJECT IDENTIFIER ::= { cpiMIBConformance 2 }

cpiMIBComplianceRev1 MODULE-COMPLIANCE
    STATUS current
    DESCRIPTION
        "The compliance statement for this MIB."
    MODULE  -- this module
        MANDATORY-GROUPS {
            cpiMIBGroupsObjects,
            cpiMIBGroupNotifications
            }
    ::= { cpiMIBCompliances 1 }

-- units of conformance

cpiMIBGroupsObjects OBJECT-GROUP
    OBJECTS {
        version,
        modelCode,
        hwAddress,
        logInterval,
        alarmInterval,
        logDifference,
        pduIP,
        autoIP,
        autoDNS,
        ipV4Enable,
        snmpEnable,
        telnetEnable,
        sshEnable,
        httpEnable,
        httpsEnable,
        subnetMask,
        gateway,
        dns1,
        dns2,
        dns3,
        snmpHost1,
        snmpHost2,
        snmpHost3,
        pduIPv6,
        autoIPv6,
        autoDNSIPv6,
        ipv6Enable,
        linkLocalEnable,
        globalAddrEnable,
        subnetMaskIPv6,
        gatewayIPv6,
        dns1IPv6,
        dns2IPv6,
        dns3IPv6,
        snmpHost1IPv6,
        snmpHost2IPv6,
        snmpHost3IPv6,
        outlet1Ctrl,
        outlet2Ctrl,
        outlet3Ctrl,
        outlet4Ctrl,
        outlet5Ctrl,
        outlet6Ctrl,
        outlet7Ctrl,
        outlet8Ctrl,
        outlet9Ctrl,
        outlet10Ctrl,
        outlet11Ctrl,
        outlet12Ctrl,
        outlet13Ctrl,
        outlet14Ctrl,
        outlet15Ctrl,
        outlet16Ctrl,
        outlet17Ctrl,
        outlet18Ctrl,
        outlet19Ctrl,
        outlet20Ctrl,
        outlet21Ctrl,
        outlet22Ctrl,
        outlet23Ctrl,
        outlet24Ctrl,
        outlet1ONdly,
        outlet2ONdly,
        outlet3ONdly,
        outlet4ONdly,
        outlet5ONdly,
        outlet6ONdly,
        outlet7ONdly,
        outlet8ONdly,
        outlet9ONdly,
        outlet10ONdly,
        outlet11ONdly,
        outlet12ONdly,
        outlet13ONdly,
        outlet14ONdly,
        outlet15ONdly,
        outlet16ONdly,
        outlet17ONdly,
        outlet18ONdly,
        outlet19ONdly,
        outlet20ONdly,
        outlet21ONdly,
        outlet22ONdly,
        outlet23ONdly,
        outlet24ONdly,
        outlet1RESdly,
        outlet2RESdly,
        outlet3RESdly,
        outlet4RESdly,
        outlet5RESdly,
        outlet6RESdly,
        outlet7RESdly,
        outlet8RESdly,
        outlet9RESdly,
        outlet10RESdly,
        outlet11RESdly,
        outlet12RESdly,
        outlet13RESdly,
        outlet14RESdly,
        outlet15RESdly,
        outlet16RESdly,
        outlet17RESdly,
        outlet18RESdly,
        outlet19RESdly,
        outlet20RESdly,
        outlet21RESdly,
        outlet22RESdly,
        outlet23RESdly,
        outlet24RESdly,
        xy1MaxCurr,
        yz1MaxCurr,
        zx1MaxCurr,
        xy2MaxCurr,
        yz2MaxCurr,
        zx2MaxCurr,
        xy1MinCurr,
        yz1MinCurr,
        zx1MinCurr,
        xy2MinCurr,
        yz2MinCurr,
        zx2MinCurr,
        xy1WarnHiCurr,
        yz1WarnHiCurr,
        zx1WarnHiCurr,
        xy2WarnHiCurr,
        yz2WarnHiCurr,
        zx2WarnHiCurr,
        xy1WarnLoCurr,
        yz1WarnLoCurr,
        zx1WarnLoCurr,
        xy2WarnLoCurr,
        yz2WarnLoCurr,
        zx2WarnLoCurr,
        xy1MaxVolt,
        yz1MaxVolt,
        zx1MaxVolt,
        xy2MaxVolt,
        yz2MaxVolt,
        zx2MaxVolt,
        xy1MinVolt,
        yz1MinVolt,
        zx1MinVolt,
        xy2MinVolt,
        yz2MinVolt,
        zx2MinVolt,
        xy1WarnHiVolt,
        yz1WarnHiVolt,
        zx1WarnHiVolt,
        xy2WarnHiVolt,
        yz2WarnHiVolt,
        zx2WarnHiVolt,
        xy1WarnLoVolt,
        yz1WarnLoVolt,
        zx1WarnLoVolt,
        xy2WarnLoVolt,
        yz2WarnLoVolt,
        zx2WarnLoVolt,
        outlet1MaxCurr,
        outlet2MaxCurr,
        outlet3MaxCurr,
        outlet4MaxCurr,
        outlet5MaxCurr,
        outlet6MaxCurr,
        outlet7MaxCurr,
        outlet8MaxCurr,
        outlet9MaxCurr,
        outlet10MaxCurr,
        outlet11MaxCurr,
        outlet12MaxCurr,
        outlet13MaxCurr,
        outlet14MaxCurr,
        outlet15MaxCurr,
        outlet16MaxCurr,
        outlet17MaxCurr,
        outlet18MaxCurr,
        outlet19MaxCurr,
        outlet20MaxCurr,
        outlet21MaxCurr,
        outlet22MaxCurr,
        outlet23MaxCurr,
        outlet24MaxCurr,
        outlet1MinCurr,
        outlet2MinCurr,
        outlet3MinCurr,
        outlet4MinCurr,
        outlet5MinCurr,
        outlet6MinCurr,
        outlet7MinCurr,
        outlet8MinCurr,
        outlet9MinCurr,
        outlet10MinCurr,
        outlet11MinCurr,
        outlet12MinCurr,
        outlet13MinCurr,
        outlet14MinCurr,
        outlet15MinCurr,
        outlet16MinCurr,
        outlet17MinCurr,
        outlet18MinCurr,
        outlet19MinCurr,
        outlet20MinCurr,
        outlet21MinCurr,
        outlet22MinCurr,
        outlet23MinCurr,
        outlet24MinCurr,
        outlet1WarnHiCurr,
        outlet2WarnHiCurr,
        outlet3WarnHiCurr,
        outlet4WarnHiCurr,
        outlet5WarnHiCurr,
        outlet6WarnHiCurr,
        outlet7WarnHiCurr,
        outlet8WarnHiCurr,
        outlet9WarnHiCurr,
        outlet10WarnHiCurr,
        outlet11WarnHiCurr,
        outlet12WarnHiCurr,
        outlet13WarnHiCurr,
        outlet14WarnHiCurr,
        outlet15WarnHiCurr,
        outlet16WarnHiCurr,
        outlet17WarnHiCurr,
        outlet18WarnHiCurr,
        outlet19WarnHiCurr,
        outlet20WarnHiCurr,
        outlet21WarnHiCurr,
        outlet22WarnHiCurr,
        outlet23WarnHiCurr,
        outlet24WarnHiCurr,
        outlet1WarnLoCurr,
        outlet2WarnLoCurr,
        outlet3WarnLoCurr,
        outlet4WarnLoCurr,
        outlet5WarnLoCurr,
        outlet6WarnLoCurr,
        outlet7WarnLoCurr,
        outlet8WarnLoCurr,
        outlet9WarnLoCurr,
        outlet10WarnLoCurr,
        outlet11WarnLoCurr,
        outlet12WarnLoCurr,
        outlet13WarnLoCurr,
        outlet14WarnLoCurr,
        outlet15WarnLoCurr,
        outlet16WarnLoCurr,
        outlet17WarnLoCurr,
        outlet18WarnLoCurr,
        outlet19WarnLoCurr,
        outlet20WarnLoCurr,
        outlet21WarnLoCurr,
        outlet22WarnLoCurr,
        outlet23WarnLoCurr,
        outlet24WarnLoCurr,
        maxTempProbe1,
        maxTempProbe2,
        minTempProbe1,
        minTempProbe2,
        warnHiTempProbe1,
        warnHiTempProbe2,
        warnLoTempProbe1,
        warnLoTempProbe2,
        maxHumidProbe1,
        maxHumidProbe2,
        minHumidProbe1,
        minHumidProbe2,
        warnHiHumidProbe1,
        warnHiHumidProbe2,
        warnLoHumidProbe1,
        warnLoHumidProbe2,
        pduName,
        pduDescrip,
        outlet1Name,
        outlet2Name,
        outlet3Name,
        outlet4Name,
        outlet5Name,
        outlet6Name,
        outlet7Name,
        outlet8Name,
        outlet9Name,
        outlet10Name,
        outlet11Name,
        outlet12Name,
        outlet13Name,
        outlet14Name,
        outlet15Name,
        outlet16Name,
        outlet17Name,
        outlet18Name,
        outlet19Name,
        outlet20Name,
        outlet21Name,
        outlet22Name,
        outlet23Name,
        outlet24Name,
        outlet1Descrip,
        outlet2Descrip,
        outlet3Descrip,
        outlet4Descrip,
        outlet5Descrip,
        outlet6Descrip,
        outlet7Descrip,
        outlet8Descrip,
        outlet9Descrip,
        outlet10Descrip,
        outlet11Descrip,
        outlet12Descrip,
        outlet13Descrip,
        outlet14Descrip,
        outlet15Descrip,
        outlet16Descrip,
        outlet17Descrip,
        outlet18Descrip,
        outlet19Descrip,
        outlet20Descrip,
        outlet21Descrip,
        outlet22Descrip,
        outlet23Descrip,
        outlet24Descrip,
        group1Name,
        group2Name,
        group3Name,
        group4Name,
        group5Name,
        group6Name,
        group7Name,
        group8Name,
        group9Name,
        group10Name,
        group11Name,
        group12Name,
        group13Name,
        group14Name,
        group15Name,
        group16Name,
        group1Map,
        group2Map,
        group3Map,
        group4Map,
        group5Map,
        group6Map,
        group7Map,
        group8Map,
        group9Map,
        group10Map,
        group11Map,
        group12Map,
        group13Map,
        group14Map,
        group15Map,
        group16Map,
        dispTimeout,
        loginTimeout,
        dispBrightness,
        inputTop,
        pduRole,
        celsiusTemp,
        enableWeb,
        snmpHostOnly,
        disLocalAuth,
        enaRadiusAuth,
        enaADAuth,
        enaSMTP,
        pduAltRole,
        shareRole,
        outOfService,
        missingPDUNotify,
        roleChangeNotify,
        httpPort,
        httpsPort,
        sshPort,
        telnetPort,
        snmpQueryPort,
        snmpTrapPort,
        smtpSendPort,
        smtpReceivePort,
        rfcTimeServer,
        ntpTimeServer,
        smtpServer,
        snmpReadComm,
        snmpWriteComm,
        snmpUSMuserName,
        snmpSecurityLevel,
        snmpAuthAlgo,
        snmpPrivAlgo,
        snmpAuthPasswd,
        snmpPrivPasswd,
        snmpContextName,
        snmpEngineID,
        snmpLocAuthKey,
        snmpLocPrivKey,
        smtpUserName,
        smtpUserPasswd,
        smtpEmailAddr,
        smtpEmailDestination1,
        smtpEmailDestination2,
        smtpEmailDestination3,
        smtpServOptions,
        radiusServer,
        radiusSHSecret,
        radiusNASServer,
        radiusPort,
        nasPort,
        adServer,
        adDomain,
        adPort,
        adResvPort,
        probe1Name,
        probe2Name,
        dLogEnable,
        netservdLog,
        autonetLog,
        stdmeterdLog,
        groupmeterdLog,
        alarmdLog,
        userlogindLog,
        usersetupdLog,
        fwupdatedLog,
        setupchangedLog,
        recepchangedLog,
        pduopchangedLog,
        dLogCycle,
        dLogFullWarnLevel,
        netdLogServer,
        netdLogPort,
        netdLogUser,
        netdLogPasswd,
        netdLogDestdir,
        netdLogOptions,
        snmpTrapHost1,
        snmpTrapHost2,
        snmpTrapHost3,
        snmpTrapHost1IPv6,
        snmpTrapHost2IPv6,
        snmpTrapHost3IPv6,
        lnkAttachCount,
        currentxy1,
        currentyz1,
        currentzx1,
        currentxy2,
        currentyz2,
        currentzx2,
        voltagexy1,
        voltageyz1,
        voltagezx1,
        voltagexy2,
        voltageyz2,
        voltagezx2,
        powerxy1,
        poweryz1,
        powerzx1,
        powerxy2,
        poweryz2,
        powerzx2,
        powerFactxy1,
        powerFactyz1,
        powerFactzx1,
        powerFactxy2,
        powerFactyz2,
        powerFactzx2,
        outlet1Current,
        outlet2Current,
        outlet3Current,
        outlet4Current,
        outlet5Current,
        outlet6Current,
        outlet7Current,
        outlet8Current,
        outlet9Current,
        outlet10Current,
        outlet11Current,
        outlet12Current,
        outlet13Current,
        outlet14Current,
        outlet15Current,
        outlet16Current,
        outlet17Current,
        outlet18Current,
        outlet19Current,
        outlet20Current,
        outlet21Current,
        outlet22Current,
        outlet23Current,
        outlet24Current,
        receptacleCurrentMap,
        outlet1State,
        outlet2State,
        outlet3State,
        outlet4State,
        outlet5State,
        outlet6State,
        outlet7State,
        outlet8State,
        outlet9State,
        outlet10State,
        outlet11State,
        outlet12State,
        outlet13State,
        outlet14State,
        outlet15State,
        outlet16State,
        outlet17State,
        outlet18State,
        outlet19State,
        outlet20State,
        outlet21State,
        outlet22State,
        outlet23State,
        outlet24State,
        temperatureProbe1,
        temperatureProbe2,
        humidityProbe1,
        humidityProbe2,
        alarmsMaxMap,
        alarmsMinMap,
        alarmsWarnHiMap,
        alarmsWarnLoMap,
        recep1To32AlarmsMaxMap,
        recep1To32AlarmsMinMap,
        recep1To32WarnHiMap,
        recep1To32WarnLoMap,
        energyxy1s,
        energyyz1s,
        energyzx1s,
        energyxy2s,
        energyyz2s,
        energyzx2s,
        receptacleEnergyoutlet1s,
        receptacleEnergyoutlet2s,
        receptacleEnergyoutlet3s,
        receptacleEnergyoutlet4s,
        receptacleEnergyoutlet5s,
        receptacleEnergyoutlet6s,
        receptacleEnergyoutlet7s,
        receptacleEnergyoutlet8s,
        receptacleEnergyoutlet9s,
        receptacleEnergyoutlet10s,
        receptacleEnergyoutlet11s,
        receptacleEnergyoutlet12s,
        receptacleEnergyoutlet13s,
        receptacleEnergyoutlet14s,
        receptacleEnergyoutlet15s,
        receptacleEnergyoutlet16s,
        receptacleEnergyoutlet17s,
        receptacleEnergyoutlet18s,
        receptacleEnergyoutlet19s,
        receptacleEnergyoutlet20s,
        receptacleEnergyoutlet21s,
        receptacleEnergyoutlet22s,
        receptacleEnergyoutlet23s,
        receptacleEnergyoutlet24s,
        line1curr,
        line2curr,
        line3curr,
        outlet1ONOFF,
        outlet2ONOFF,
        outlet3ONOFF,
        outlet4ONOFF,
        outlet5ONOFF,
        outlet6ONOFF,
        outlet7ONOFF,
        outlet8ONOFF,
        outlet9ONOFF,
        outlet10ONOFF,
        outlet11ONOFF,
        outlet12ONOFF,
        outlet13ONOFF,
        outlet14ONOFF,
        outlet15ONOFF,
        outlet16ONOFF,
        outlet17ONOFF,
        outlet18ONOFF,
        outlet19ONOFF,
        outlet20ONOFF,
        outlet21ONOFF,
        outlet22ONOFF,
        outlet23ONOFF,
        outlet24ONOFF,
        outlet1Reset,
        outlet2Reset,
        outlet3Reset,
        outlet4Reset,
        outlet5Reset,
        outlet6Reset,
        outlet7Reset,
        outlet8Reset,
        outlet9Reset,
        outlet10Reset,
        outlet11Reset,
        outlet12Reset,
        outlet13Reset,
        outlet14Reset,
        outlet15Reset,
        outlet16Reset,
        outlet17Reset,
        outlet18Reset,
        outlet19Reset,
        outlet20Reset,
        outlet21Reset,
        outlet22Reset,
        outlet23Reset,
        outlet24Reset,
        receptacleCtrlMap,
        pduCount,
        pduMap,
        pduSelect,
        pduNamelist
    }
    STATUS  current
    DESCRIPTION
        "A collection of objects for managing the PDU."
    ::= { cpiMIBGroups 1 }

cpiMIBGroupNotifications NOTIFICATION-GROUP
    NOTIFICATIONS {
        maxCurrentxy1,
        maxCurrentyz1,
        maxCurrentzx1,
        maxCurrentxy2,
        maxCurrentyz2,
        maxCurrentzx2,
        minCurrentxy1,
        minCurrentyz1,
        minCurrentzx1,
        minCurrentxy2,
        minCurrentyz2,
        minCurrentzx2,
        maxVoltxy1,
        maxVoltyz1,
        maxVoltzx1,
        maxVoltxy2,
        maxVoltyz2,
        maxVoltzx2,
        minVoltxy1,
        minVoltyz1,
        minVoltzx1,
        minVoltxy2,
        minVoltyz2,
        minVoltzx2,
        maxTemperature1,
        maxTemperature2,
        minTemperature1,
        minTemperature2,
        maxHumidity1,
        maxHumidity2,
        minHumidity1,
        minHumidity2,
        changeLog,
        dataLog
    }
    STATUS  current
    DESCRIPTION
        "A collection of notifications supported by PDU."
    ::= { cpiMIBGroups 2 }

-- ######################################################################
-- ######################################################################
-- ######################################################################
--
--          UNITY MIBS Below
--
-- ######################################################################
-- ######################################################################
-- ######################################################################
unity OBJECT IDENTIFIER ::= { products 10 }

econnect OBJECT IDENTIFIER ::= { unity 1 }

configuration OBJECT IDENTIFIER ::= { econnect 1 }

network OBJECT IDENTIFIER ::= { configuration 1 }

ipv4 OBJECT IDENTIFIER ::= { network 1 }

ipV4Enable OBJECT-TYPE
    SYNTAX INTEGER { disabled(0), enabled(1) }
    MAX-ACCESS read-write
    STATUS current
    DESCRIPTION
        "Controls whether the IPv4 network interface is enabled."
    ::= { ipv4 1 }

pduIP OBJECT-TYPE
    SYNTAX IpAddress
    MAX-ACCESS read-write
    STATUS current
    DESCRIPTION
        "Set or get the IPv4 address of the PDU."
    ::= { ipv4 2 }

autoIP OBJECT-TYPE
    SYNTAX INTEGER { static(0), dynamic(1) }
    MAX-ACCESS read-write
    STATUS current
    DESCRIPTION
        "Controls whether the IPv4 address is retrieved from a 
         DHCP server or is set statically."
    ::= { ipv4 3 }

autoDNS OBJECT-TYPE
    SYNTAX INTEGER { static(0), dynamic(1) }
    MAX-ACCESS read-write
    STATUS current
    DESCRIPTION
        "Controls whether the DNS addresses are retrieved from
        a DHCP server or are set statically."
    ::= { ipv4 4 }

subnetMask OBJECT-TYPE
    SYNTAX IpAddress
    MAX-ACCESS read-write
    STATUS current
    DESCRIPTION
        "The subnet mask associated with the IPv4 address of this 
        entry. The value of the mask is an IPv4 address with all the 
        network bits set to 1 and all the hosts bits set to 0."
    ::= { ipv4 5 }

gateway OBJECT-TYPE
    SYNTAX IpAddress
    MAX-ACCESS read-write
    STATUS current
    DESCRIPTION
        "Set or get the IPv4 address of the gateway router for the PDU."
    ::= { ipv4 6 }

dns1 OBJECT-TYPE
    SYNTAX IpAddress
    MAX-ACCESS read-write
    STATUS current
    DESCRIPTION
        "Set or get the IPv4 address of the first DNS entry for the PDU."
    ::= { ipv4 7 }

dns2 OBJECT-TYPE
    SYNTAX IpAddress
    MAX-ACCESS read-write
    STATUS current
    DESCRIPTION
        "Set or get the IPv4 address of the second DNS entry for the PDU."
    ::= { ipv4 8 }

dns3 OBJECT-TYPE
    SYNTAX IpAddress
    MAX-ACCESS read-write
    STATUS current
    DESCRIPTION
        "Set or get the IPv4 address of the third DNS entry for the PDU."
    ::= { ipv4 9 }

ipv6 OBJECT IDENTIFIER ::= { network 2 }

ipV6Enable OBJECT-TYPE
    SYNTAX INTEGER { disabled(0), enabled(1) }
    MAX-ACCESS read-write
    STATUS current
    DESCRIPTION
        "Controls whether the IPv6 network interface is enabled."
    ::= { ipv6 1 }

linkLocalEnable OBJECT-TYPE
    SYNTAX INTEGER { disabled(0), enabled(1) }
    MAX-ACCESS read-write
    STATUS current
    DESCRIPTION
        "Controls whether the IPv6 link-local address is enabled."
    ::= { ipv6 2 }

globalAddrEnable OBJECT-TYPE
    SYNTAX INTEGER { disabled(0), enabled(1) }
    MAX-ACCESS read-write
    STATUS current
    DESCRIPTION
        "Controls whether the IPv6 global address is enabled."
    ::= { ipv6 3 }

pduIPv6 OBJECT-TYPE
    SYNTAX DisplayString
    MAX-ACCESS read-write
    STATUS current
    DESCRIPTION
        "Set or get the IPv6 address of the PDU."
    ::= { ipv6 4 }

autoIPv6 OBJECT-TYPE
    SYNTAX INTEGER { static(0), dynamic(1) }
    MAX-ACCESS read-write
    STATUS current
    DESCRIPTION
        "Controls whether the IPv6 address is retrieved from a 
         DHCP server or is set statically."
    ::= { ipv6 5 }

autoDNSv6 OBJECT-TYPE
    SYNTAX Integer32 (0..1)
    MAX-ACCESS read-write
    STATUS current
    DESCRIPTION
        "Controls whether the DNS IPv6 address is retrieved from a 
         DHCP server or is set statically."
    ::= { ipv6 6 }

subnetMaskv6 OBJECT-TYPE
    SYNTAX DisplayString
    MAX-ACCESS read-write
    STATUS current
    DESCRIPTION
        "The subnet mask associated with the IPv6 address of this 
        entry. The value of the mask is an IPv6 address with all the 
        network bits set to 1 and all the hosts bits set to 0."
    ::= { ipv6 7 }

gatewayv6 OBJECT-TYPE
    SYNTAX DisplayString
    MAX-ACCESS read-write
    STATUS current
    DESCRIPTION
        "Set or get the IPv6 address of the gateway router for the PDU."
    ::= { ipv6 8 }

dns1v6 OBJECT-TYPE
    SYNTAX DisplayString
    MAX-ACCESS read-write
    STATUS current
    DESCRIPTION
        "Set or get the IPv6 address of the first DNS entry for the PDU."
    ::= { ipv6 9 }

dns2v6 OBJECT-TYPE
    SYNTAX DisplayString
    MAX-ACCESS read-write
    STATUS current
    DESCRIPTION
        "Set or get the IPv6 address of the second DNS entry for the PDU."
    ::= { ipv6 10 }

dns3v6 OBJECT-TYPE
    SYNTAX DisplayString
    MAX-ACCESS read-write
    STATUS current
    DESCRIPTION
        "Set or get the IPv6 address of the third DNS entry for the PDU."
    ::= { ipv6 11 }

time OBJECT IDENTIFIER ::= { network 3 }

rfcTimeServer OBJECT-TYPE
    SYNTAX      DisplayString
    MAX-ACCESS  read-write
    STATUS      current
    DESCRIPTION
        "Set or get the IP address of the RFC Time Server."
    ::= { time 1 }

ntpTimeServer OBJECT-TYPE
    SYNTAX      DisplayString
    MAX-ACCESS  read-write
    STATUS      current
    DESCRIPTION
        "Set or get the IP address of the NTP Time Server."
    ::= { time 2 }

interfaces OBJECT IDENTIFIER ::= { configuration 2 }

snmp OBJECT IDENTIFIER ::= { interfaces 1 }

snmpEnable OBJECT-TYPE
    SYNTAX INTEGER { disabled(0), enabled(1) }
    MAX-ACCESS read-write
    STATUS current
    DESCRIPTION
        "Controls whether the SNMP network service is enabled."
    ::= { snmp 1 }

snmpHosts OBJECT IDENTIFIER ::= { snmp 2 }

snmpHostOnly OBJECT-TYPE
    SYNTAX INTEGER { any(0), listed(1) }
    MAX-ACCESS read-write
    STATUS current
    DESCRIPTION
        "Controls whether access to the SNMP service responsed to
        the listed hosts (snmpHost1, snmpHost2, snmpHost3) or
        to any host requesting data."
    ::= { snmpHosts 1 }

snmpHost1 OBJECT-TYPE
    SYNTAX DisplayString
    MAX-ACCESS read-write
    STATUS current
    DESCRIPTION
        "Set or get the IPv4 address of the first host the SNMP service
        will reply to."
    ::= { snmpHosts 2 }

snmpHost2 OBJECT-TYPE
    SYNTAX DisplayString
    MAX-ACCESS read-write
    STATUS current
    DESCRIPTION
        "Set or get the IPv4 address of the second host the SNMP service
        will reply to."
    ::= { snmpHosts 3 }

snmpHost3 OBJECT-TYPE
    SYNTAX DisplayString
    MAX-ACCESS read-write
    STATUS current
    DESCRIPTION
        "Set or get the IPv4 address of the third host the SNMP service
        will reply to."
    ::= { snmpHosts 4 }
   
snmpHostIPv61 OBJECT-TYPE
    SYNTAX DisplayString
    MAX-ACCESS read-write
    STATUS current
    DESCRIPTION
        "Set or get the IPv6 address of the first host the SNMP service
        will reply to."
    ::= { snmpHosts 5 }

snmpHostIPv62 OBJECT-TYPE
    SYNTAX DisplayString
    MAX-ACCESS read-write
    STATUS current
    DESCRIPTION
        "Set or get the IPv6 address of the first host the SNMP service
        will reply to."
    ::= { snmpHosts 6 }

snmpHostIPV63 OBJECT-TYPE
    SYNTAX DisplayString
    MAX-ACCESS read-write
    STATUS current
    DESCRIPTION
        "Set or get the IPv6 address of the first host the SNMP service
        will reply to."
    ::= { snmpHosts 7 }

snmpQueryPort OBJECT-TYPE
    SYNTAX Integer32 (0..65535)
    MAX-ACCESS read-write
    STATUS current
    DESCRIPTION
        "Set or get the port for SNMP query access."
    ::= { snmp 3 }

snmpTrapPort OBJECT-TYPE
    SYNTAX Integer32 (0..65535)
    MAX-ACCESS read-write
    STATUS current
    DESCRIPTION
        "Set or get the port for SNMP traps."
    ::= { snmp 4 }

snmpReadComm OBJECT-TYPE
    SYNTAX DisplayString
    MAX-ACCESS read-write
    STATUS current
    DESCRIPTION
        "Set or get the SNMP Read Community."
    ::= { snmp 5 }

snmpWriteComm OBJECT-TYPE
    SYNTAX DisplayString
    MAX-ACCESS read-write
    STATUS current
    DESCRIPTION
        "Set or get the SNMP Write Community."
    ::= { snmp 6 }

snmpUSMuserName OBJECT-TYPE
    SYNTAX DisplayString
    MAX-ACCESS read-write
    STATUS current
    DESCRIPTION
        "Set or get the SNMP USM User Name."
    ::= { snmp 7 }

snmpSecurityLevel OBJECT-TYPE
    SYNTAX INTEGER { v1(0), v2c(1), v3(2), v3Auth(3), v3AuthPriv(4) }
    MAX-ACCESS read-write
    STATUS current
    DESCRIPTION
        "Set or get the security Level for SNMP: 0 = v1, 1 = v2c, 2 = v3 no authentication,
        3 = v3 with authentication only, 4 = v3 with authentication and privacy"
    ::= { snmp 8 }

snmpAuthAlgo OBJECT-TYPE
    SYNTAX INTEGER { sha(0), md5(1) }
    MAX-ACCESS read-write
    STATUS current
    DESCRIPTION
        "Set or get the Authentication Algorithm for SNMP."
    ::= { snmp 9 }

snmpPrivAlgo OBJECT-TYPE
    SYNTAX INTEGER { des(0), aes(1) }
    MAX-ACCESS read-write
    STATUS current
    DESCRIPTION
        "Get or get the Privacy Algorithm for SNMP."
    ::= { snmp 10 }

snmpAuthPasswd OBJECT-TYPE
    SYNTAX DisplayString (SIZE (0..64))
    MAX-ACCESS read-write
    STATUS current
    DESCRIPTION
        "Set or Get the SNMP Authentication Password."
    ::= { snmp 11 }

snmpPrivPasswd OBJECT-TYPE
    SYNTAX DisplayString (SIZE (0..64))
    MAX-ACCESS read-write
    STATUS current
    DESCRIPTION
        "Set or get the SNMP Privacy Password."
    ::= { snmp 12 }

snmpContextName OBJECT-TYPE
    SYNTAX DisplayString (SIZE (0..64))
    MAX-ACCESS read-write
    STATUS current
    DESCRIPTION
        "Set or get the SNMP Context Name."
    ::= { snmp 13 }

snmpEngineID OBJECT-TYPE
    SYNTAX DisplayString (SIZE (0..64))
    MAX-ACCESS read-write
    STATUS current
    DESCRIPTION
        "Set or get the SNMP Engine ID."
    ::= { snmp 14 }

snmpLocAuthKey OBJECT-TYPE
    SYNTAX DisplayString (SIZE (0..64))
    MAX-ACCESS read-write
    STATUS current
    DESCRIPTION
        "Set or get the SNMP Local Authentication Key."
    ::= { snmp 15 }

snmpLocPrivKey OBJECT-TYPE
    SYNTAX DisplayString (SIZE (0..64))
    MAX-ACCESS read-write
    STATUS current
    DESCRIPTION
        "Set or get the SNMP Local Privacy Key."
    ::= { snmp 16 }

snmpTrapHosts OBJECT IDENTIFIER ::= { snmp 17 }

snmpTrapHost1 OBJECT-TYPE
    SYNTAX DisplayString
    MAX-ACCESS read-write
    STATUS current
    DESCRIPTION
        "Set or get the IPv4 address of the first SNMP Trap Host."
    ::= { snmpTrapHosts 1 }

snmpTrapHost2 OBJECT-TYPE
    SYNTAX DisplayString
    MAX-ACCESS read-write
    STATUS current
    DESCRIPTION
        "Set or get the IPv4 address of the second SNMP Trap Host."
    ::= { snmpTrapHosts 2 }

snmpTrapHost3 OBJECT-TYPE
    SYNTAX DisplayString
    MAX-ACCESS read-write
    STATUS current
    DESCRIPTION
        "Set or get the IPv4 address of the third SNMP Trap Host."
    ::= { snmpTrapHosts 3 }

snmpTrapHostIPv61 OBJECT-TYPE
    SYNTAX DisplayString
    MAX-ACCESS read-write
    STATUS current
    DESCRIPTION
        "Set or get the IPv6 address of the first SNMP Trap Host."
    ::= { snmpTrapHosts 4 }

snmpTrapHostIPv62 OBJECT-TYPE
    SYNTAX DisplayString
    MAX-ACCESS read-write
    STATUS current
    DESCRIPTION
        "Set or get the IPv6 address of the second SNMP Trap Host."
    ::= { snmpTrapHosts 5 }

snmpTrapHostIPv63 OBJECT-TYPE
    SYNTAX DisplayString
    MAX-ACCESS read-write
    STATUS current
    DESCRIPTION
        "Set or get the IPv6 address of the third SNMP Trap Host."
    ::= { snmpTrapHosts 6 }

snmpControl OBJECT IDENTIFIER ::= { snmp 18 }

enableEASSNMPControl OBJECT-TYPE
    SYNTAX INTEGER { disabled(0), enabled(1) }
    MAX-ACCESS read-write
    STATUS current
    DESCRIPTION
        "Allows the use of SNMP to open/close the door locks.  It is recommended that this only be enabled with SNMP v3 configurations."
    ::= { snmpControl 5 }

http OBJECT IDENTIFIER ::= { interfaces 2 }

enableWeb OBJECT-TYPE
    SYNTAX INTEGER { disabled(0), enabled(1) }
    MAX-ACCESS read-write
    STATUS current
    DESCRIPTION
        "Controls whether the web interface is enabled."
    ::= { http 1 }

httpEnable OBJECT-TYPE
    SYNTAX INTEGER { disabled(0), enabled(1) }
    MAX-ACCESS read-write
    STATUS current
    DESCRIPTION
        "Controls whether the HTTP service is enabled."
    ::= { http 2 }

httpsEnable OBJECT-TYPE
    SYNTAX INTEGER { disabled(0), enabled(1) }
    MAX-ACCESS read-write
    STATUS current
    DESCRIPTION
        "Controls whether the HTTPS service is enabled."
    ::= { http 3 }

httpPort OBJECT-TYPE
    SYNTAX Integer32 (0..65535)
    MAX-ACCESS read-write
    STATUS current
    DESCRIPTION
        "Set or get the port for unsecure HTTP access."
    ::= { http 4 }

httpsPort OBJECT-TYPE
    SYNTAX Integer32 (0..65535)
    MAX-ACCESS read-write
    STATUS current
    DESCRIPTION
        "Set or get the port for secure HTTPS access."
    ::= { http 5 }

smtp OBJECT IDENTIFIER ::= { interfaces 3 }

enableSMTP OBJECT-TYPE
    SYNTAX INTEGER { disabled(0), enabled(1) }
    MAX-ACCESS read-write
    STATUS current
    DESCRIPTION
        "Controls whether the mail notification service is enabled.."
    ::= { smtp 1 }

smtpSendPort OBJECT-TYPE
    SYNTAX Integer32 (0..65535)
    MAX-ACCESS read-write
    STATUS current
    DESCRIPTION
        "Set or get the port for SMTP send."
    ::= { smtp 2 }

smtpReceivePort OBJECT-TYPE
    SYNTAX Integer32 (0..65535)
    MAX-ACCESS read-write
    STATUS current
    DESCRIPTION
        "Set or get the port for SMTP Receive."
    ::= { smtp 3 }

smtpServer OBJECT-TYPE
    SYNTAX DisplayString
    MAX-ACCESS read-write
    STATUS current
    DESCRIPTION
        "Set or get the IP address of the e-mail server."
    ::= { smtp 4 }

smtpUserName OBJECT-TYPE
    SYNTAX DisplayString
    MAX-ACCESS read-write
    STATUS current
    DESCRIPTION
        "Set or get the PDU e-mail user login name."
    ::= { smtp 5 }

smtpUserPasswd OBJECT-TYPE
    SYNTAX DisplayString
    MAX-ACCESS read-write
    STATUS current
    DESCRIPTION
        "Set or get the PDU e-mail user login password."
    ::= { smtp 6 }

smtpEmailAddr OBJECT-TYPE
    SYNTAX DisplayString
    MAX-ACCESS read-write
    STATUS current
    DESCRIPTION
        "Set or get the PDU e-mail address."
    ::= { smtp 7 }

smtpEmailDestination1 OBJECT-TYPE
    SYNTAX DisplayString (SIZE (0..64))
    MAX-ACCESS read-write
    STATUS current
    DESCRIPTION
        "Set or get the e-mail address of the first recipient."
    ::= { smtp 8 }

smtpEmailDestination2 OBJECT-TYPE
    SYNTAX DisplayString (SIZE (0..64))
    MAX-ACCESS read-write
    STATUS current
    DESCRIPTION
        "Set or get the e-mail address of the second recipient."
    ::= { smtp 9 }

smtpEmailDestination3 OBJECT-TYPE
    SYNTAX DisplayString (SIZE (0..64))
    MAX-ACCESS read-write
    STATUS current
    DESCRIPTION
        "Set or get the e-mail address of the third recipient."
    ::= { smtp 10 }

smtpServOptions OBJECT-TYPE
    SYNTAX Integer32 (0..2)
    MAX-ACCESS read-write
    STATUS current
    DESCRIPTION
        "Set or get the SMTP server options."
    ::= { smtp 11 }

logging OBJECT IDENTIFIER ::= { configuration 3 }

logEnable OBJECT-TYPE
    SYNTAX INTEGER { disabled(0), enabled(1) }
    MAX-ACCESS read-write
    STATUS current
    DESCRIPTION
        "Controls whether the data logging feature is enabled."
    ::= { logging 1 }

logInterval OBJECT-TYPE
    SYNTAX Integer32 (0..65535)
    MAX-ACCESS read-write
    STATUS current
    DESCRIPTION
        "Set or get the time interval in seconds for logging metrics (disabled if < 10)."
    ::= { logging 2 }

logDifference OBJECT-TYPE
    SYNTAX Integer32 (0..2000)
    MAX-ACCESS read-write
    STATUS current
    DESCRIPTION
        "Set or get the current difference in 1/100 Amps that triggers logging metrics."
    ::= { logging 3 }

netservdLog OBJECT-TYPE
    SYNTAX INTEGER { disabled(0), enabled(1) }
    MAX-ACCESS read-write
    STATUS current
    DESCRIPTION
        "Controls sending the data logs to log server over network."
    ::= { logging 4 }

autonetLog OBJECT-TYPE
    SYNTAX INTEGER { disabled(0), enabled(1) }
    MAX-ACCESS read-write
    STATUS current
    DESCRIPTION
        "Controls whether automatic transfer to log server every 6 hours is enabled."
    ::= { logging 5 }

stdmeterdLog OBJECT-TYPE
    SYNTAX INTEGER { disabled(0), enabled(1) }
    MAX-ACCESS read-write
    STATUS current
    DESCRIPTION
        "Controls whether logging of branch, receptacle and environmental metrics is enabled."
    ::= { logging 6 }

groupmeterdLog OBJECT-TYPE
    SYNTAX INTEGER { disabled(0), enabled(1) }
    MAX-ACCESS read-write
    STATUS current
    DESCRIPTION
        "Controls whether logging of grouped receptacle metrics is enabled."
    ::= { logging 7 }

alarmdLog OBJECT-TYPE
    SYNTAX INTEGER { disabled(0), enabled(1) }
    MAX-ACCESS read-write
    STATUS current
    DESCRIPTION
        "Controls whether logging of alarm events is enabled."
    ::= { logging 8 }

userlogindLog OBJECT-TYPE
    SYNTAX INTEGER { disabled(0), enabled(1) }
    MAX-ACCESS read-write
    STATUS current
    DESCRIPTION
        "Control whether logging of user login events is enabled."
    ::= { logging 9 }

usersetupdLog OBJECT-TYPE
    SYNTAX INTEGER { disabled(0), enabled(1) }
    MAX-ACCESS read-write
    STATUS current
    DESCRIPTION
        "Control whether logging of user setup change events is enabled."
    ::= { logging 10 }

fwupdatedLog OBJECT-TYPE
    SYNTAX INTEGER { disabled(0), enabled(1) }
    MAX-ACCESS read-write
    STATUS current
    DESCRIPTION
        "Control whether the logging of firmware updates is enabled."
    ::= { logging 11 }

setupchangedLog OBJECT-TYPE
    SYNTAX INTEGER { disabled(0), enabled(1) }
    MAX-ACCESS read-write
    STATUS current
    DESCRIPTION
        "Control whether the logging of setup change events is enabled."
    ::= { logging 12 }

recepchangedLog OBJECT-TYPE
    SYNTAX INTEGER { disabled(0), enabled(1) }
    MAX-ACCESS read-write
    STATUS current
    DESCRIPTION
        "Control whether logging of receptacle state changes is enabled."
    ::= { logging 13 }

pduopchangedLog OBJECT-TYPE
    SYNTAX INTEGER { disabled(0), enabled(1) }
    MAX-ACCESS read-write
    STATUS current
    DESCRIPTION
        "Control whether logging of PDU operation and state changes is enabled."
    ::= { logging 14 }

dLogCycle OBJECT-TYPE
    SYNTAX Integer32 (0..65535)
    MAX-ACCESS read-write
    STATUS current
    DESCRIPTION
        "Set or get the time interval in minutes for internal data logging to occur."
    ::= { logging 15 }

dLogFullWarnLevel OBJECT-TYPE
    SYNTAX Integer32 (50..100)
    MAX-ACCESS read-write
    STATUS current
    DESCRIPTION
        "Set or get the warning threshold for percentage of storage full (min=50, max=100)."
    ::= { logging 16 }

netdLogServer OBJECT-TYPE
    SYNTAX DisplayString (SIZE (0..64))
    MAX-ACCESS read-write
    STATUS current
    DESCRIPTION
        "Set or get the network address for the data server."
    ::= { logging 17 }

netdLogPort OBJECT-TYPE
    SYNTAX Integer32 (0..65535)
    MAX-ACCESS read-write
    STATUS current
    DESCRIPTION
        "Set or get the port used by the data server."
    ::= { logging 18 }

netdLogUser OBJECT-TYPE
    SYNTAX DisplayString (SIZE (0..64))
    MAX-ACCESS read-write
    STATUS current
    DESCRIPTION
        "Set or get the user name to access the data server."
    ::= { logging 19 }

netdLogPasswd OBJECT-TYPE
    SYNTAX DisplayString (SIZE (0..64))
    MAX-ACCESS read-write
    STATUS current
    DESCRIPTION
        "Set or get the user password to access the data server."
    ::= { logging 20 }

netdLogDestdir OBJECT-TYPE
    SYNTAX DisplayString (SIZE (0..64))
    MAX-ACCESS read-write
    STATUS current
    DESCRIPTION
        "Get or get the destination directory in the data server."
    ::= { logging 21 }

netdLogOptions OBJECT-TYPE
    SYNTAX DisplayString (SIZE (0..64))
    MAX-ACCESS read-write
    STATUS current
    DESCRIPTION
        "Get or set the options string when accessing the data server."        
    ::= { logging 22 }
    
sysLogIdentity OBJECT-TYPE
    SYNTAX DisplayString (SIZE (0..64))
    MAX-ACCESS read-write
    STATUS current
    DESCRIPTION
        "Get or set the identity to use with the syslog. The identity is an arbitrary identification string which  syslog will prefix to each message. This is intended to identify the source of the message."
    ::= { logging 23 }
    
sysLogFacility OBJECT-TYPE
    SYNTAX INTEGER { loglocal0(0), loglocal1(1), loglocal2(2), loglocal3(3), loglocal4(4), loglocal5(5), loglocal(6), loglocal7(7) }
    MAX-ACCESS read-write
    STATUS current
    DESCRIPTION
        "Get or set the facility to use with the syslog. The facility argument is used to specify what type of program is logging the message."
    ::= { logging 24 }
    
sysLogCentralServerAddr OBJECT-TYPE
    SYNTAX DisplayString (SIZE (0..64))
    MAX-ACCESS read-write
    STATUS current
    DESCRIPTION
        "Get or set the IP address for the central syslog server."
    ::= { logging 25 }

sysLogCentralServerPort OBJECT-TYPE
    SYNTAX INTEGER 
    MAX-ACCESS read-write
    STATUS current
    DESCRIPTION
        "Get or set the port for the central syslog server."
    ::= { logging 26 }

accesscontrol OBJECT IDENTIFIER ::= { configuration 4 }

ldap OBJECT IDENTIFIER ::= { accesscontrol 1 }

enableADAuth OBJECT-TYPE
    SYNTAX INTEGER { disabled(0), enabled(1) }
    MAX-ACCESS read-write
    STATUS current
    DESCRIPTION
        "Controls whether the Active Directory authentication is enabled."
    ::= { ldap 1 }

adServer OBJECT-TYPE
    SYNTAX DisplayString
    MAX-ACCESS read-write
    STATUS current
    DESCRIPTION
        "Set or get the IP address of the Active Directory Server."
    ::= { ldap 2 }

adDomain OBJECT-TYPE
    SYNTAX DisplayString
    MAX-ACCESS read-write
    STATUS current
    DESCRIPTION
        "Set or get the Active Directory Domain."
    ::= { ldap 3 }
    
adPort OBJECT-TYPE
    SYNTAX Integer32 (0..65535)
    MAX-ACCESS read-write
    STATUS current
    DESCRIPTION
        "Set or get the port for Active Directory authentication."
    ::= { ldap 4 }

adResvPort OBJECT-TYPE
    SYNTAX Integer32 (0..65535)
    MAX-ACCESS read-write
    STATUS current
    DESCRIPTION
        "Set or get the alternate or reserved port for Active Directory Authentication."
    ::= { ldap 5 }

radius OBJECT IDENTIFIER ::= { accesscontrol 2 }

enableRadiusAuth OBJECT-TYPE
    SYNTAX INTEGER { disabled(0), enabled(1) }
    MAX-ACCESS read-write
    STATUS current
    DESCRIPTION
        "Controls whether radius authentication is enabled."
    ::= { radius 1 }

radiusServer OBJECT-TYPE
    SYNTAX DisplayString
    MAX-ACCESS read-write
    STATUS current
    DESCRIPTION
        "Set or get the IP address of the Radius Authentication Server."
    ::= { radius 2 }

radiusSHSecret OBJECT-TYPE
    SYNTAX DisplayString
    MAX-ACCESS read-write
    STATUS current
    DESCRIPTION
        "Set or get the Radius Shared Secret."
    ::= { radius 3 }

radiusNASServer OBJECT-TYPE
    SYNTAX DisplayString
    MAX-ACCESS read-write
    STATUS current
    DESCRIPTION
        "Set or get the Radius Network Access Service."
    ::= { radius 4 }

radiusPort OBJECT-TYPE
    SYNTAX Integer32 (0..65535)
    MAX-ACCESS read-write
    STATUS current
    DESCRIPTION
        "Set or get the port for radius authentication."
    ::= { radius 5 }

nasPort OBJECT-TYPE
    SYNTAX Integer32 (0..65535)
    MAX-ACCESS read-write
    STATUS current
    DESCRIPTION
        "Set or get the port for Radius Network Access Service."
    ::= { radius 6 }
    
radiusip6 OBJECT-TYPE
    SYNTAX INTEGER { disabled(0), enabled(1) }
    MAX-ACCESS read-write
    STATUS current
    DESCRIPTION
        "Enable/Disable IPv6 for radius authentication."
    ::= { radius 7 }

radiuscardenable OBJECT-TYPE
    SYNTAX INTEGER { disabled(0), enabled(1) }
    MAX-ACCESS read-write
    STATUS current
    DESCRIPTION
        "Enable/Disable Radius for card authentication."
    ::= { radius 8 }
    
cardradiusserver OBJECT-TYPE
    SYNTAX DisplayString
    MAX-ACCESS read-write
    STATUS current
    DESCRIPTION
        "Set or get the IP address of the Primary Radius Card Authentication Server."
    ::= { radius 9 }

cardradiusshsecret OBJECT-TYPE
    SYNTAX DisplayString
    MAX-ACCESS read-write
    STATUS current
    DESCRIPTION
        "Set or get the Radius Card Shared Secret."
    ::= { radius 10 }
    
cardradiusPort OBJECT-TYPE
    SYNTAX Integer32 (0..65535)
    MAX-ACCESS read-write
    STATUS current
    DESCRIPTION
        "Set or get the port for Radius Card Authentication."
    ::= { radius 11 }

cardradiusip6 OBJECT-TYPE
    SYNTAX INTEGER { disabled(0), enabled(1) }
    MAX-ACCESS read-write
    STATUS current
    DESCRIPTION
        "Enable/Disable IPv6 for Radius Card Authentication."
    ::= { radius 12 }

radiusServer2 OBJECT-TYPE
    SYNTAX DisplayString
    MAX-ACCESS read-write
    STATUS current
    DESCRIPTION
        "Set or get the IP address of the Secondary Radius Authentication Server."
    ::= { radius 13 }

radiusPort2 OBJECT-TYPE
    SYNTAX Integer32 (0..65535)
    MAX-ACCESS read-write
    STATUS current
    DESCRIPTION
        "Set or get the port for Secondary Radius Authentication."
    ::= { radius 14 }
    
radiusServer3 OBJECT-TYPE
    SYNTAX DisplayString
    MAX-ACCESS read-write
    STATUS current
    DESCRIPTION
        "Set or get the IP address of the Tertiary Radius Authentication Server."
    ::= { radius 15 }

radiusPort3 OBJECT-TYPE
    SYNTAX Integer32 (0..65535)
    MAX-ACCESS read-write
    STATUS current
    DESCRIPTION
        "Set or get the port for Tertiary Radius Authentication."
    ::= { radius 16 }

cardradiusServer2 OBJECT-TYPE
    SYNTAX DisplayString
    MAX-ACCESS read-write
    STATUS current
    DESCRIPTION
        "Set or get the IP address of the Secondary Radius Card Authentication Server."
    ::= { radius 17 }

cardradiusPort2 OBJECT-TYPE
    SYNTAX Integer32 (0..65535)
    MAX-ACCESS read-write
    STATUS current
    DESCRIPTION
        "Set or get the port for Secondary Radius Card Authentication."
    ::= { radius 18 }
    
cardradiusServer3 OBJECT-TYPE
    SYNTAX DisplayString
    MAX-ACCESS read-write
    STATUS current
    DESCRIPTION
        "Set or get the IP address of the Tertiary Radius Card Authentication Server."
    ::= { radius 19 }

cardradiusPort3 OBJECT-TYPE
    SYNTAX Integer32 (0..65535)
    MAX-ACCESS read-write
    STATUS current
    DESCRIPTION
        "Set or get the port for Tertiary Radius Card Authentication."
    ::= { radius 20 }
    
pdu OBJECT IDENTIFIER ::= { configuration 6 }

inputTop OBJECT-TYPE
    SYNTAX INTEGER { bottom(0), top(1) }
    MAX-ACCESS read-write
    STATUS current
    DESCRIPTION
        "Set or get the input cord entry orientation."
    ::= { pdu 1 }

celsiusTemp OBJECT-TYPE
    SYNTAX INTEGER { fahrenheit(0), celsius(1) }
    MAX-ACCESS read-write
    STATUS current
    DESCRIPTION
        "Set or get the temperature units."
    ::= { pdu 2 }

shareRole OBJECT-TYPE
    SYNTAX INTEGER { backup(0), shared(1) }
    MAX-ACCESS read-write
    STATUS current
    DESCRIPTION
        "Controls whether to allow sharing of PDU Primary and Alternate Roles."
    ::= { pdu 3 }

missingPDUNotify OBJECT-TYPE
    SYNTAX INTEGER { disabled(0), enabled(1) }
    MAX-ACCESS read-write
    STATUS current
    DESCRIPTION
        "Controls whether to notify when a PDU is missing from the link."
    ::= { pdu 4 }

roleChangeNotify OBJECT-TYPE
    SYNTAX INTEGER { disabled(0), enabled(1) }
    MAX-ACCESS read-write
    STATUS current
    DESCRIPTION
        "Control whether to notify when a PDU changes role in the link."
    ::= { pdu 5 }

dispTimeout OBJECT-TYPE
    SYNTAX Integer32 (1..90)
    MAX-ACCESS read-write
    STATUS current
    DESCRIPTION
        "Set or get the inactivity timeout in minutes to blank the local display (minimum is 1 minute)."
    ::= { pdu 6 }

loginTimeout OBJECT-TYPE
    SYNTAX Integer32 (1..60)
    MAX-ACCESS read-write
    STATUS current
    DESCRIPTION
        "Set or get the inactivity timeout in minutes to terminate a logged in session (minimum is 1 minute)."
    ::= { pdu 7 }

dispBrightness OBJECT-TYPE
    SYNTAX Integer32 (0..9)
    MAX-ACCESS read-write
    STATUS current
    DESCRIPTION
        "Set or get the relative brightness of the local display (0 in min, 9 is max)."
    ::= { pdu 8 }

sumAmps OBJECT-TYPE
    SYNTAX INTEGER { disabled(0), enabled(1) }
    MAX-ACCESS read-write
    STATUS current
    DESCRIPTION
        "Control whether the PDU displays the amperage sum of all branchs."
    ::= { pdu 9 }

alerts OBJECT IDENTIFIER ::= { configuration 7 }

alarmInterval OBJECT-TYPE
    SYNTAX Integer32 (0..65535)
    MAX-ACCESS read-write
    STATUS current
    DESCRIPTION
        "Set or get the time interval in seconds for alarm cycle (disabled if < 10)."
    ::= { alerts 1 }
    
routing OBJECT IDENTIFIER ::= { configuration 8 }

eventLogRouting OBJECT IDENTIFIER ::= { routing 1 }

logBranchCritLowVoltage OBJECT-TYPE
    SYNTAX INTEGER { disabled(0), enabled(1) }
    MAX-ACCESS read-write
    STATUS current
    DESCRIPTION
        "Enable/Disable logging of Critical Low Voltage on the Branch to the event log."
    ::= { eventLogRouting 1 }

logBranchWarnLowVoltage OBJECT-TYPE
    SYNTAX INTEGER { disabled(0), enabled(1) }
    MAX-ACCESS read-write
    STATUS current
    DESCRIPTION
        "Enable/Disable logging of Warning Low Voltage on the Branch to the event log."
    ::= { eventLogRouting 2 }
    
logBranchWarnHighVoltage OBJECT-TYPE
    SYNTAX INTEGER { disabled(0), enabled(1) }
    MAX-ACCESS read-write
    STATUS current
    DESCRIPTION
        "Enable/Disable logging of Warning High Voltage on the Branch to the event log."
    ::= { eventLogRouting 3 }
    
logBranchCritHighVoltage OBJECT-TYPE
    SYNTAX INTEGER { disabled(0), enabled(1) }
    MAX-ACCESS read-write
    STATUS current
    DESCRIPTION
        "Enable/Disable logging of Critical High Voltage on the Branch to the event log."
    ::= { eventLogRouting 4 }
    
logBranchCritLowCurrent OBJECT-TYPE
    SYNTAX INTEGER { disabled(0), enabled(1) }
    MAX-ACCESS read-write
    STATUS current
    DESCRIPTION
        "Enable/Disable logging of Critical Low Current on the Branch to the event log."
    ::= { eventLogRouting 5 }

logBranchWarnLowCurrent OBJECT-TYPE
    SYNTAX INTEGER { disabled(0), enabled(1) }
    MAX-ACCESS read-write
    STATUS current
    DESCRIPTION
        "Enable/Disable logging of Warning Low Current on the Branch to the event log."
    ::= { eventLogRouting 6 }
    
logBranchWarnHighCurrent OBJECT-TYPE
    SYNTAX INTEGER { disabled(0), enabled(1) }
    MAX-ACCESS read-write
    STATUS current
    DESCRIPTION
        "Enable/Disable logging of Warning High Current on the Branch to the event log."
    ::= { eventLogRouting 7 }
    
logBranchCritHighCurrent OBJECT-TYPE
    SYNTAX INTEGER { disabled(0), enabled(1) }
    MAX-ACCESS read-write
    STATUS current
    DESCRIPTION
        "Enable/Disable logging of Critical High Current on the Branch to the event log."
    ::= { eventLogRouting 8 }
    
logOutletCritLowCurrent OBJECT-TYPE
    SYNTAX INTEGER { disabled(0), enabled(1) }
    MAX-ACCESS read-write
    STATUS current
    DESCRIPTION
        "Enable/Disable logging of Critical Low Current on the Outlet to the event log."
    ::= { eventLogRouting 9 }

logOutletWarnLowCurrent OBJECT-TYPE
    SYNTAX INTEGER { disabled(0), enabled(1) }
    MAX-ACCESS read-write
    STATUS current
    DESCRIPTION
        "Enable/Disable logging of Warning Low Current on the Outlet to the event log."
    ::= { eventLogRouting 10 }
    
logOutletWarnHighCurrent OBJECT-TYPE
    SYNTAX INTEGER { disabled(0), enabled(1) }
    MAX-ACCESS read-write
    STATUS current
    DESCRIPTION
        "Enable/Disable logging of Warning High Current on the Outlet to the event log."
    ::= { eventLogRouting 11 }
    
logOutletCritHighCurrent OBJECT-TYPE
    SYNTAX INTEGER { disabled(0), enabled(1) }
    MAX-ACCESS read-write
    STATUS current
    DESCRIPTION
        "Enable/Disable logging of Critical High Current to the event log."
    ::= { eventLogRouting 12 }
    
logTempCritLow OBJECT-TYPE
    SYNTAX INTEGER { disabled(0), enabled(1) }
    MAX-ACCESS read-write
    STATUS current
    DESCRIPTION
        "Enable/Disable logging of Critical Low Temperature to the event log."
    ::= { eventLogRouting 13 }

logTempWarnLow OBJECT-TYPE
    SYNTAX INTEGER { disabled(0), enabled(1) }
    MAX-ACCESS read-write
    STATUS current
    DESCRIPTION
        "Enable/Disable logging of Warning Low Temperature to the event log."
    ::= { eventLogRouting 14 }
    
logTempWarnHigh OBJECT-TYPE
    SYNTAX INTEGER { disabled(0), enabled(1) }
    MAX-ACCESS read-write
    STATUS current
    DESCRIPTION
        "Enable/Disable logging of Warning High Temperature to the event log."
    ::= { eventLogRouting 15 }
    
logTempCritHigh OBJECT-TYPE
    SYNTAX INTEGER { disabled(0), enabled(1) }
    MAX-ACCESS read-write
    STATUS current
    DESCRIPTION
        "Enable/Disable logging of Critical High Temperature to the event log."
    ::= { eventLogRouting 16 }
 
logHumidCritLow OBJECT-TYPE
    SYNTAX INTEGER { disabled(0), enabled(1) }
    MAX-ACCESS read-write
    STATUS current
    DESCRIPTION
        "Enable/Disable logging of Critical Low Humidity to the event log."
    ::= { eventLogRouting 17 }

logHumidWarnLow OBJECT-TYPE
    SYNTAX INTEGER { disabled(0), enabled(1) }
    MAX-ACCESS read-write
    STATUS current
    DESCRIPTION
        "Enable/Disable logging of Warning Low Humidity to the event log."
    ::= { eventLogRouting 18 }
    
logHumidWarnHigh OBJECT-TYPE
    SYNTAX INTEGER { disabled(0), enabled(1) }
    MAX-ACCESS read-write
    STATUS current
    DESCRIPTION
        "Enable/Disable logging of Warning High Humidity to the event log."
    ::= { eventLogRouting 19 }
    
logHumidCritHigh OBJECT-TYPE
    SYNTAX INTEGER { disabled(0), enabled(1) }
    MAX-ACCESS read-write
    STATUS current
    DESCRIPTION
        "Enable/Disable logging of Critical High Humidity to the event log."
    ::= { eventLogRouting 20 }
    
logScanPass OBJECT-TYPE
    SYNTAX INTEGER { disabled(0), enabled(1) }
    MAX-ACCESS read-write
    STATUS current
    DESCRIPTION
        "Enable/Disable logging of successful card scan events to the event log."
    ::= { eventLogRouting 21 }

logScanFail OBJECT-TYPE
    SYNTAX INTEGER { disabled(0), enabled(1) }
    MAX-ACCESS read-write
    STATUS current
    DESCRIPTION
        "Enable/Disable logging of failed card scan events to the event log."
    ::= { eventLogRouting 22 }
    
logDoorState OBJECT-TYPE
    SYNTAX INTEGER { disabled(0), enabled(1) }
    MAX-ACCESS read-write
    STATUS current
    DESCRIPTION
        "Enable/Disable logging of Door Open/Close events to the event log."
    ::= { eventLogRouting 23 }
    
logLockState OBJECT-TYPE
    SYNTAX INTEGER { disabled(0), enabled(1) }
    MAX-ACCESS read-write
    STATUS current
    DESCRIPTION
        "Enable/Disable logging of Lock Open/Close events to the event log."
    ::= { eventLogRouting 24 }
    
logExtendedOpen OBJECT-TYPE
    SYNTAX INTEGER { disabled(0), enabled(1) }
    MAX-ACCESS read-write
    STATUS current
    DESCRIPTION
        "Enable/Disable logging of extended door open events to the event log."
    ::= { eventLogRouting 25 }
    
logFirmareUpdate OBJECT-TYPE
    SYNTAX INTEGER { disabled(0), enabled(1) }
    MAX-ACCESS read-write
    STATUS current
    DESCRIPTION
        "Enable/Disable logging of Firmare Update events to the event log."
    ::= { eventLogRouting 26 }
    
logConfigUpdate OBJECT-TYPE
    SYNTAX INTEGER { disabled(0), enabled(1) }
    MAX-ACCESS read-write
    STATUS current
    DESCRIPTION
        "Enable/Disable logging of configuration change events to the event log."
    ::= { eventLogRouting 27 }
    
logRecepChange OBJECT-TYPE
    SYNTAX INTEGER { disabled(0), enabled(1) }
    MAX-ACCESS read-write
    STATUS current
    DESCRIPTION
        "Enable/Disable logging of receptacle change events to the event log."
    ::= { eventLogRouting 28 }
    
logSystem OBJECT-TYPE
    SYNTAX INTEGER { disabled(0), enabled(1) }
    MAX-ACCESS read-write
    STATUS current
    DESCRIPTION
        "Enable/Disable logging of system events to the event log."
    ::= { eventLogRouting 29 }
    
logPduAccess OBJECT-TYPE
    SYNTAX INTEGER { disabled(0), enabled(1) }
    MAX-ACCESS read-write
    STATUS current
    DESCRIPTION
        "Enable/Disable logging of access to PDU events to the event log."
    ::= { eventLogRouting 30 }
    
logSecureArray OBJECT-TYPE
    SYNTAX INTEGER { disabled(0), enabled(1) }
    MAX-ACCESS read-write
    STATUS current
    DESCRIPTION
        "Enable/Disable logging of SecureArray events to the event log."
    ::= { eventLogRouting 31 }
 
emailRouting OBJECT IDENTIFIER ::= { routing 2 }

emailBranchCritLowVoltage OBJECT-TYPE
    SYNTAX INTEGER { disabled(0), enabled(1) }
    MAX-ACCESS read-write
    STATUS current
    DESCRIPTION
        "Enable/Disable notification of Critical Low Voltage on the Branch in an email."
    ::= { emailRouting 1 }

emailBranchWarnLowVoltage OBJECT-TYPE
    SYNTAX INTEGER { disabled(0), enabled(1) }
    MAX-ACCESS read-write
    STATUS current
    DESCRIPTION
        "Enable/Disable notification of Warning Low Voltage on the Branch in an email."
    ::= { emailRouting 2 }
    
emailBranchWarnHighVoltage OBJECT-TYPE
    SYNTAX INTEGER { disabled(0), enabled(1) }
    MAX-ACCESS read-write
    STATUS current
    DESCRIPTION
        "Enable/Disable notification of Warning High Voltage on the Branch in an email."
    ::= { emailRouting 3 }
    
emailBranchCritHighVoltage OBJECT-TYPE
    SYNTAX INTEGER { disabled(0), enabled(1) }
    MAX-ACCESS read-write
    STATUS current
    DESCRIPTION
        "Enable/Disable notification of Critical High Voltage on the Branch in an email."
    ::= { emailRouting 4 }
    
emailBranchCritLowCurrent OBJECT-TYPE
    SYNTAX INTEGER { disabled(0), enabled(1) }
    MAX-ACCESS read-write
    STATUS current
    DESCRIPTION
        "Enable/Disable notification of Critical Low Current on the Branch in an email."
    ::= { emailRouting 5 }

emailBranchWarnLowCurrent OBJECT-TYPE
    SYNTAX INTEGER { disabled(0), enabled(1) }
    MAX-ACCESS read-write
    STATUS current
    DESCRIPTION
        "Enable/Disable notification of Warning Low Current on the Branch in an email."
    ::= { emailRouting 6 }
    
emailBranchWarnHighCurrent OBJECT-TYPE
    SYNTAX INTEGER { disabled(0), enabled(1) }
    MAX-ACCESS read-write
    STATUS current
    DESCRIPTION
        "Enable/Disable notification of Warning High Current on the Branch in an email."
    ::= { emailRouting 7 }
    
emailBranchCritHighCurrent OBJECT-TYPE
    SYNTAX INTEGER { disabled(0), enabled(1) }
    MAX-ACCESS read-write
    STATUS current
    DESCRIPTION
        "Enable/Disable notification of Critical High Current on the Branch in an email."
    ::= { emailRouting 8 }
    
emailOutletCritLowCurrent OBJECT-TYPE
    SYNTAX INTEGER { disabled(0), enabled(1) }
    MAX-ACCESS read-write
    STATUS current
    DESCRIPTION
        "Enable/Disable notification of Critical Low Current on the Outlet in an email."
    ::= { emailRouting 9 }

emailOutletWarnLowCurrent OBJECT-TYPE
    SYNTAX INTEGER { disabled(0), enabled(1) }
    MAX-ACCESS read-write
    STATUS current
    DESCRIPTION
        "Enable/Disable notification of Warning Low Current on the Outlet in an email."
    ::= { emailRouting 10 }
    
emailOutletWarnHighCurrent OBJECT-TYPE
    SYNTAX INTEGER { disabled(0), enabled(1) }
    MAX-ACCESS read-write
    STATUS current
    DESCRIPTION
        "Enable/Disable notification of Warning High Current on the Outlet in an email."
    ::= { emailRouting 11 }
    
emailOutletCritHighCurrent OBJECT-TYPE
    SYNTAX INTEGER { disabled(0), enabled(1) }
    MAX-ACCESS read-write
    STATUS current
    DESCRIPTION
        "Enable/Disable notification of Critical High Current in an email."
    ::= { emailRouting 12 }
    
emailTempCritLow OBJECT-TYPE
    SYNTAX INTEGER { disabled(0), enabled(1) }
    MAX-ACCESS read-write
    STATUS current
    DESCRIPTION
        "Enable/Disable notification of Critical Low Temperature in an email."
    ::= { emailRouting 13 }

emailTempWarnLow OBJECT-TYPE
    SYNTAX INTEGER { disabled(0), enabled(1) }
    MAX-ACCESS read-write
    STATUS current
    DESCRIPTION
        "Enable/Disable notification of Warning Low Temperature in an email."
    ::= { emailRouting 14 }
    
emailTempWarnHigh OBJECT-TYPE
    SYNTAX INTEGER { disabled(0), enabled(1) }
    MAX-ACCESS read-write
    STATUS current
    DESCRIPTION
        "Enable/Disable notification of Warning High Temperature in an email."
    ::= { emailRouting 15 }
    
emailTempCritHigh OBJECT-TYPE
    SYNTAX INTEGER { disabled(0), enabled(1) }
    MAX-ACCESS read-write
    STATUS current
    DESCRIPTION
        "Enable/Disable notification of Critical High Temperature in an email."
    ::= { emailRouting 16 }
 
emailHumidCritLow OBJECT-TYPE
    SYNTAX INTEGER { disabled(0), enabled(1) }
    MAX-ACCESS read-write
    STATUS current
    DESCRIPTION
        "Enable/Disable notification of Critical Low Humidity in an email."
    ::= { emailRouting 17 }

emailHumidWarnLow OBJECT-TYPE
    SYNTAX INTEGER { disabled(0), enabled(1) }
    MAX-ACCESS read-write
    STATUS current
    DESCRIPTION
        "Enable/Disable notification of Warning Low Humidity in an email."
    ::= { emailRouting 18 }
    
emailHumidWarnHigh OBJECT-TYPE
    SYNTAX INTEGER { disabled(0), enabled(1) }
    MAX-ACCESS read-write
    STATUS current
    DESCRIPTION
        "Enable/Disable notification of Warning High Humidity in an email."
    ::= { emailRouting 19 }
    
emailHumidCritHigh OBJECT-TYPE
    SYNTAX INTEGER { disabled(0), enabled(1) }
    MAX-ACCESS read-write
    STATUS current
    DESCRIPTION
        "Enable/Disable notification of Critical High Humidity in an email."
    ::= { emailRouting 20 }
    
emailScanPass OBJECT-TYPE
    SYNTAX INTEGER { disabled(0), enabled(1) }
    MAX-ACCESS read-write
    STATUS current
    DESCRIPTION
        "Enable/Disable notification of successful card scan events in an email."
    ::= { emailRouting 21 }

emailScanFail OBJECT-TYPE
    SYNTAX INTEGER { disabled(0), enabled(1) }
    MAX-ACCESS read-write
    STATUS current
    DESCRIPTION
        "Enable/Disable notification of failed card scan events in an email."
    ::= { emailRouting 22 }
    
emailDoorState OBJECT-TYPE
    SYNTAX INTEGER { disabled(0), enabled(1) }
    MAX-ACCESS read-write
    STATUS current
    DESCRIPTION
        "Enable/Disable notification of Door Open/Close events in an email."
    ::= { emailRouting 23 }
    
emailLockState OBJECT-TYPE
    SYNTAX INTEGER { disabled(0), enabled(1) }
    MAX-ACCESS read-write
    STATUS current
    DESCRIPTION
        "Enable/Disable notification of Lock Open/Close events in an email."
    ::= { emailRouting 24 }
    
emailExtendedOpen OBJECT-TYPE
    SYNTAX INTEGER { disabled(0), enabled(1) }
    MAX-ACCESS read-write
    STATUS current
    DESCRIPTION
        "Enable/Disable notification of extended door open events in an email."
    ::= { emailRouting 25 }
    
emailFirmareUpdate OBJECT-TYPE
    SYNTAX INTEGER { disabled(0), enabled(1) }
    MAX-ACCESS read-write
    STATUS current
    DESCRIPTION
        "Enable/Disable notification of Firmare Update events in an email."
    ::= { emailRouting 26 }
    
emailConfigUpdate OBJECT-TYPE
    SYNTAX INTEGER { disabled(0), enabled(1) }
    MAX-ACCESS read-write
    STATUS current
    DESCRIPTION
        "Enable/Disable notification of configuration change events in an email."
    ::= { emailRouting 27 }
    
emailRecepChange OBJECT-TYPE
    SYNTAX INTEGER { disabled(0), enabled(1) }
    MAX-ACCESS read-write
    STATUS current
    DESCRIPTION
        "Enable/Disable notification of receptacle change events in an email."
    ::= { emailRouting 28 }
    
emailSystem OBJECT-TYPE
    SYNTAX INTEGER { disabled(0), enabled(1) }
    MAX-ACCESS read-write
    STATUS current
    DESCRIPTION
        "Enable/Disable notification of system events in an email."
    ::= { emailRouting 29 }
    
emailPduAccess OBJECT-TYPE
    SYNTAX INTEGER { disabled(0), enabled(1) }
    MAX-ACCESS read-write
    STATUS current
    DESCRIPTION
        "Enable/Disable notification of access to PDU events in an email."
    ::= { emailRouting 30 }
    
emailSecureArray OBJECT-TYPE
    SYNTAX INTEGER { disabled(0), enabled(1) }
    MAX-ACCESS read-write
    STATUS current
    DESCRIPTION
        "Enable/Disable notification of SecureArray events in an email."
    ::= { emailRouting 31 }

trapRouting OBJECT IDENTIFIER ::= { routing 3 }

trapBranchCritLowVoltage OBJECT-TYPE
    SYNTAX INTEGER { disabled(0), enabled(1) }
    MAX-ACCESS read-write
    STATUS current
    DESCRIPTION
        "Enable/Disable notification of Critical Low Voltage on the Branch in a trap."
    ::= { trapRouting 1 }

trapBranchWarnLowVoltage OBJECT-TYPE
    SYNTAX INTEGER { disabled(0), enabled(1) }
    MAX-ACCESS read-write
    STATUS current
    DESCRIPTION
        "Enable/Disable notification of Warning Low Voltage on the Branch in a trap."
    ::= { trapRouting 2 }
    
trapBranchWarnHighVoltage OBJECT-TYPE
    SYNTAX INTEGER { disabled(0), enabled(1) }
    MAX-ACCESS read-write
    STATUS current
    DESCRIPTION
        "Enable/Disable notification of Warning High Voltage on the Branch in a trap."
    ::= { trapRouting 3 }
    
trapBranchCritHighVoltage OBJECT-TYPE
    SYNTAX INTEGER { disabled(0), enabled(1) }
    MAX-ACCESS read-write
    STATUS current
    DESCRIPTION
        "Enable/Disable notification of Critical High Voltage on the Branch in a trap."
    ::= { trapRouting 4 }
    
trapBranchCritLowCurrent OBJECT-TYPE
    SYNTAX INTEGER { disabled(0), enabled(1) }
    MAX-ACCESS read-write
    STATUS current
    DESCRIPTION
        "Enable/Disable notification of Critical Low Current on the Branch in a trap."
    ::= { trapRouting 5 }

trapBranchWarnLowCurrent OBJECT-TYPE
    SYNTAX INTEGER { disabled(0), enabled(1) }
    MAX-ACCESS read-write
    STATUS current
    DESCRIPTION
        "Enable/Disable notification of Warning Low Current on the Branch in a trap."
    ::= { trapRouting 6 }
    
trapBranchWarnHighCurrent OBJECT-TYPE
    SYNTAX INTEGER { disabled(0), enabled(1) }
    MAX-ACCESS read-write
    STATUS current
    DESCRIPTION
        "Enable/Disable notification of Warning High Current on the Branch in a trap."
    ::= { trapRouting 7 }
    
trapBranchCritHighCurrent OBJECT-TYPE
    SYNTAX INTEGER { disabled(0), enabled(1) }
    MAX-ACCESS read-write
    STATUS current
    DESCRIPTION
        "Enable/Disable notification of Critical High Current on the Branch in a trap."
    ::= { trapRouting 8 }
    
trapOutletCritLowCurrent OBJECT-TYPE
    SYNTAX INTEGER { disabled(0), enabled(1) }
    MAX-ACCESS read-write
    STATUS current
    DESCRIPTION
        "Enable/Disable notification of Critical Low Current on the Outlet in a trap."
    ::= { trapRouting 9 }

trapOutletWarnLowCurrent OBJECT-TYPE
    SYNTAX INTEGER { disabled(0), enabled(1) }
    MAX-ACCESS read-write
    STATUS current
    DESCRIPTION
        "Enable/Disable notification of Warning Low Current on the Outlet in a trap."
    ::= { trapRouting 10 }
    
trapOutletWarnHighCurrent OBJECT-TYPE
    SYNTAX INTEGER { disabled(0), enabled(1) }
    MAX-ACCESS read-write
    STATUS current
    DESCRIPTION
        "Enable/Disable notification of Warning High Current on the Outlet in a trap."
    ::= { trapRouting 11 }
    
trapOutletCritHighCurrent OBJECT-TYPE
    SYNTAX INTEGER { disabled(0), enabled(1) }
    MAX-ACCESS read-write
    STATUS current
    DESCRIPTION
        "Enable/Disable notification of Critical High Current in a trap."
    ::= { trapRouting 12 }
    
trapTempCritLow OBJECT-TYPE
    SYNTAX INTEGER { disabled(0), enabled(1) }
    MAX-ACCESS read-write
    STATUS current
    DESCRIPTION
        "Enable/Disable notification of Critical Low Temperature in a trap."
    ::= { trapRouting 13 }

trapTempWarnLow OBJECT-TYPE
    SYNTAX INTEGER { disabled(0), enabled(1) }
    MAX-ACCESS read-write
    STATUS current
    DESCRIPTION
        "Enable/Disable notification of Warning Low Temperature in a trap."
    ::= { trapRouting 14 }
    
trapTempWarnHigh OBJECT-TYPE
    SYNTAX INTEGER { disabled(0), enabled(1) }
    MAX-ACCESS read-write
    STATUS current
    DESCRIPTION
        "Enable/Disable notification of Warning High Temperature in a trap."
    ::= { trapRouting 15 }
    
trapTempCritHigh OBJECT-TYPE
    SYNTAX INTEGER { disabled(0), enabled(1) }
    MAX-ACCESS read-write
    STATUS current
    DESCRIPTION
        "Enable/Disable notification of Critical High Temperature in a trap."
    ::= { trapRouting 16 }
 
trapHumidCritLow OBJECT-TYPE
    SYNTAX INTEGER { disabled(0), enabled(1) }
    MAX-ACCESS read-write
    STATUS current
    DESCRIPTION
        "Enable/Disable notification of Critical Low Humidity in a trap."
    ::= { trapRouting 17 }

trapHumidWarnLow OBJECT-TYPE
    SYNTAX INTEGER { disabled(0), enabled(1) }
    MAX-ACCESS read-write
    STATUS current
    DESCRIPTION
        "Enable/Disable notification of Warning Low Humidity in a trap."
    ::= { trapRouting 18 }
    
trapHumidWarnHigh OBJECT-TYPE
    SYNTAX INTEGER { disabled(0), enabled(1) }
    MAX-ACCESS read-write
    STATUS current
    DESCRIPTION
        "Enable/Disable notification of Warning High Humidity in a trap."
    ::= { trapRouting 19 }
    
trapHumidCritHigh OBJECT-TYPE
    SYNTAX INTEGER { disabled(0), enabled(1) }
    MAX-ACCESS read-write
    STATUS current
    DESCRIPTION
        "Enable/Disable notification of Critical High Humidity in a trap."
    ::= { trapRouting 20 }
    
trapScanPass OBJECT-TYPE
    SYNTAX INTEGER { disabled(0), enabled(1) }
    MAX-ACCESS read-write
    STATUS current
    DESCRIPTION
        "Enable/Disable notification of successful card ID scans in a trap."
    ::= { trapRouting 21 }
    
trapScanFail OBJECT-TYPE
    SYNTAX INTEGER { disabled(0), enabled(1) }
    MAX-ACCESS read-write
    STATUS current
    DESCRIPTION
        "Enable/Disable notification of failed card ID scans in a trap."
    ::= { trapRouting 22 }

trapDoorState OBJECT-TYPE
    SYNTAX INTEGER { disabled(0), enabled(1) }
    MAX-ACCESS read-write
    STATUS current
    DESCRIPTION
        "Enable/Disable notification of Door Open/Closed events in a trap."
    ::= { trapRouting 23 }

trapLockState OBJECT-TYPE
    SYNTAX INTEGER { disabled(0), enabled(1) }
    MAX-ACCESS read-write
    STATUS current
    DESCRIPTION
        "Enable/Disable notification of Lock Open/Closed events in a trap."
    ::= { trapRouting 24 }
    
trapExtendedOpen OBJECT-TYPE
    SYNTAX INTEGER { disabled(0), enabled(1) }
    MAX-ACCESS read-write
    STATUS current
    DESCRIPTION
        "Enable/Disable notification of extended door open events in an trap."
    ::= { trapRouting 25 }

trapFirmareUpdate OBJECT-TYPE
    SYNTAX INTEGER { disabled(0), enabled(1) }
    MAX-ACCESS read-write
    STATUS current
    DESCRIPTION
        "Enable/Disable notification of Firmare Update events in a trap."
    ::= { trapRouting 26 }
    
trapConfigUpdate OBJECT-TYPE
    SYNTAX INTEGER { disabled(0), enabled(1) }
    MAX-ACCESS read-write
    STATUS current
    DESCRIPTION
        "Enable/Disable notification of configuration change events in a trap."
    ::= { trapRouting 27 }
    
trapRecepChange OBJECT-TYPE
    SYNTAX INTEGER { disabled(0), enabled(1) }
    MAX-ACCESS read-write
    STATUS current
    DESCRIPTION
        "Enable/Disable notification of receptacle change events in a trap."
    ::= { trapRouting 28 }
    
trapSystem OBJECT-TYPE
    SYNTAX INTEGER { disabled(0), enabled(1) }
    MAX-ACCESS read-write
    STATUS current
    DESCRIPTION
        "Enable/Disable notification of system events in a trap."
    ::= { trapRouting 29 }
    
trapPduAccess OBJECT-TYPE
    SYNTAX INTEGER { disabled(0), enabled(1) }
    MAX-ACCESS read-write
    STATUS current
    DESCRIPTION
        "Enable/Disable notification of access to PDU events in a trap."
    ::= { trapRouting 30 }
    
trapSecureArray OBJECT-TYPE
    SYNTAX INTEGER { disabled(0), enabled(1) }
    MAX-ACCESS read-write
    STATUS current
    DESCRIPTION
        "Enable/Disable notification of SecureArray events in a trap."
    ::= { trapRouting 31 }

systeminfo OBJECT IDENTIFIER ::= { econnect 2 }

cpiPduTableCount OBJECT-TYPE
    SYNTAX      Unsigned32
    UNITS       "Count"
    MAX-ACCESS  read-only
    STATUS      current
    DESCRIPTION
        "Get the number of PDUs being monitored by this PDU.  This is the 
         number of entries in the cpiPduTable."
    ::= { systeminfo 1 }

cpiPduTable OBJECT-TYPE
    SYNTAX      SEQUENCE OF CpiPduEntry
    MAX-ACCESS  not-accessible
    STATUS      current
    DESCRIPTION
        "This table contains a list of PDU entries that are being monitored
        by the PDU. 
        
        The table contains one, or many rows, depending upon the 
        number of PDUs being monitored. Each row in the table represents a PDU 
        in the daisy chain.
        
        This table always contains at least one entry and a maximum of 32 entries.
        The MAC address is used as an index on the table to allow data collectors
        to ensure that information can be retrieved for a specific PDU."
    ::= { systeminfo 10 }

    cpiPduEntry OBJECT-TYPE
        SYNTAX      CpiPduEntry
        MAX-ACCESS  not-accessible
        STATUS      current
        DESCRIPTION
            "This entry defines the columns to be populated in the
             'cpiPduTable'.  Each column represents an attribute of a PDU.
             This table is indexed by the PDU MAC that is globally unique."

        INDEX
        { 
            cpiPduMac 
        }
        ::= { cpiPduTable 1 }

    CpiPduEntry ::= SEQUENCE 
    {
        cpiPduMac			    MacAddress,
        cpiPduModel			    DisplayString,	
        cpiPduName			    DisplayString,
        cpiPduDescription		DisplayString,
        cpiPduHasBranchMonitor	Integer32,
        cpiPduHasOutletMonitor	Integer32,
        cpiPduHasOutletControl	Integer32,
        cpiPduNumberBranches    Integer32,
        cpiPduNumberOutlets		Integer32,
        cpiPduVersion			DisplayString,
        cpiPduUpgrade			Integer32,
        cpiPduChainRole			Integer32,
        cpiPduOutOfService		Integer32,
        cpiPduIp			    IpAddress,
        cpiPduIpv6			    DisplayString,
	cpiPduTotalPower	Integer32,
	cpiPduCabinetId         DisplayString,
	cpiPduSerialNum         DisplayString
    }

    cpiPduMac OBJECT-TYPE
        SYNTAX      MacAddress
        MAX-ACCESS  read-only
        STATUS      current
        DESCRIPTION
            "Get the MAC address of the PDU."
        ::= { cpiPduEntry 1 }

    cpiPduModel OBJECT-TYPE
        SYNTAX      DisplayString
        MAX-ACCESS  read-only
        STATUS      current
        DESCRIPTION
            "Get the model number of the PDU."
        ::= { cpiPduEntry 2 }

    cpiPduName OBJECT-TYPE
        SYNTAX      DisplayString
        MAX-ACCESS  read-write
        STATUS      current
        DESCRIPTION
            "Set or get the user assigned name of the PDU."
        ::= { cpiPduEntry 3 }

    cpiPduDescription OBJECT-TYPE
        SYNTAX      DisplayString
        MAX-ACCESS  read-write
        STATUS      current
        DESCRIPTION
            "Set or get the user assigned description of the PDU."
        ::= { cpiPduEntry 4 }

    cpiPduHasBranchMonitor OBJECT-TYPE
        SYNTAX      INTEGER { notsupported(0), supported(1) }
        MAX-ACCESS  read-only
        STATUS      current
        DESCRIPTION
            "An indicator if the PDU supports monitoring voltage, and current on branches in the PDU."
        ::= { cpiPduEntry 5 }

    cpiPduHasOutletMonitor OBJECT-TYPE
        SYNTAX      INTEGER { notsupported(0), supported(1) }
        MAX-ACCESS  read-only
        STATUS      current
        DESCRIPTION
            "An indicator if the PDU supports monitoring current on the individual outlets in the PDU."
        ::= { cpiPduEntry 6 }

    cpiPduHasOutletControl OBJECT-TYPE
        SYNTAX      INTEGER { notsupported(0), supported(1) }
        MAX-ACCESS  read-only
        STATUS      current
        DESCRIPTION
            "An indicator if the PDU supports control (turn on/off) individual outlets in the PDU."
        ::= { cpiPduEntry 7 }

    cpiPduNumberBranches OBJECT-TYPE
        SYNTAX      Integer32 (0..6)
        MAX-ACCESS  read-only
        STATUS      current
        DESCRIPTION
            "Get the number of branches (breakers) in the PDU."
        ::= { cpiPduEntry 8 }

    cpiPduNumberOutlets OBJECT-TYPE
        SYNTAX      Integer32 (0..48)
        MAX-ACCESS  read-only
        STATUS      current
        DESCRIPTION
            "Get the number of outlets in the PDU."
        ::= { cpiPduEntry 9 }

    cpiPduOutOfService OBJECT-TYPE
        SYNTAX      INTEGER { inservice(0), outofservice(1) }
        MAX-ACCESS  read-write
        STATUS      current
        DESCRIPTION
            "Set or get whether the PDU is in-service."
        ::= { cpiPduEntry 10 }

    cpiPduVersion OBJECT-TYPE
        SYNTAX      DisplayString
        MAX-ACCESS  read-only
        STATUS      current
        DESCRIPTION
            "Get the firmware version number of the PDU."
        ::= { cpiPduEntry 11 }

    cpiPduUpgrade OBJECT-TYPE
        SYNTAX      INTEGER { no(0), yes(1) }
        MAX-ACCESS  read-only
        STATUS      current
        DESCRIPTION
            "An indicator if the PDU firmware is being upgraded."
        ::= { cpiPduEntry 12 }

    cpiPduChainRole OBJECT-TYPE
        SYNTAX      INTEGER { secondary(0), primary(1), alternate(2) }
        MAX-ACCESS  read-write
        STATUS      current
        DESCRIPTION
            "Get the role of the PDU in a daisy chain."
        ::= { cpiPduEntry 13 }

    cpiPduIp OBJECT-TYPE
        SYNTAX      IpAddress
        MAX-ACCESS  read-only
        STATUS      current
        DESCRIPTION
            "Get IP address of the PDU."
        ::= { cpiPduEntry 14 }

    cpiPduIpv6 OBJECT-TYPE
        SYNTAX      DisplayString
        MAX-ACCESS  read-only
        STATUS      current
        DESCRIPTION
            "Get the IPv6 address of the PDU."
        ::= { cpiPduEntry 15 }

    cpiPduTotalPower OBJECT-TYPE
        SYNTAX      Integer32
        MAX-ACCESS  read-only
        STATUS      current
        DESCRIPTION
            "Get the power in volt-amps for the entire PDU."
        ::= { cpiPduEntry 16 }
        
    cpiPduCabinetId OBJECT-TYPE
        SYNTAX      DisplayString
        MAX-ACCESS  read-only
        STATUS      current
        DESCRIPTION
            "Get/set the name of the cabinet the PDU is in."
        ::= { cpiPduEntry 17 }
        
    cpiPduSerialNum OBJECT-TYPE
        SYNTAX      DisplayString
        MAX-ACCESS  read-only
        STATUS      current
        DESCRIPTION
            "Get the serial number of the PDU."
        ::= { cpiPduEntry 18 }

branch OBJECT IDENTIFIER ::= { econnect 3 }

cpiLineTableCount OBJECT-TYPE
    SYNTAX      Unsigned32
    UNITS       "Count"
    MAX-ACCESS  read-only
    STATUS      current
    DESCRIPTION
        "Get the number of PDU input lines being monitored by this PDU.  
         This is the number of entries in the cpiLineTable and accounts
         for all input lines in a daisy chain."
    ::= { branch 1 }

cpiPduLineTable OBJECT-TYPE
    SYNTAX      SEQUENCE OF CpiPduLineEntry
    MAX-ACCESS  not-accessible
    STATUS      current
    DESCRIPTION
        "This table contains a list of PDU line entries that are being
         monitored by the PDU.

         The table contains one, or many rows, depending upon the number
         of PDUs being monitored and the number of input lines. Each row 
         in the table represents a PDU line in the daisy chain.
         
         The table is indexed based on the corresponding Line Input ID and
         the source PDU MAC."
    ::= { branch 10 }

    cpiPduLineEntry OBJECT-TYPE
        SYNTAX      CpiPduLineEntry
        MAX-ACCESS  not-accessible
        STATUS      current
        DESCRIPTION
            "This entry defines the columns to be populated in the
             'cpiPduLineTable'.  Each column represents an attribute of a PDU.
             This table is indexed by the PDU Line identifier that is unique 
             within the PDU."

        INDEX
        { 
            cpiPduLineId,
            cpiPduLineMac 
        }
        ::= { cpiPduLineTable 1 }

    CpiPduLineEntry ::= SEQUENCE 
    {
        cpiPduLineMac			DisplayString,
        cpiPduLineId			DisplayString,	
        cpiPduLineCurrent		Integer32
    }

    cpiPduLineMac OBJECT-TYPE
        SYNTAX      MacAddress
        MAX-ACCESS  read-only
        STATUS      current
        DESCRIPTION
            "Get the MAC address of the PDU that owns the input line."
        ::= { cpiPduLineEntry 1 }

    cpiPduLineId OBJECT-TYPE
        SYNTAX      Integer32
        MAX-ACCESS  read-only
        STATUS      current
        DESCRIPTION
            "Get the ID of the input line on the PDU."
        ::= { cpiPduLineEntry 2 }

    cpiPduLineCurrent OBJECT-TYPE
        SYNTAX      Integer32
        MAX-ACCESS  read-only
        STATUS      current
        DESCRIPTION
            "Get current draw in 1/100 amp of the line on the PDU.  Convert the value by dividing by 100."
        ::= { cpiPduLineEntry 3 }

cpiBranchTableCount OBJECT-TYPE
    SYNTAX      Unsigned32
    UNITS       "Count"
    MAX-ACCESS  read-only
    STATUS      current
    DESCRIPTION
        "Get the number of PDU branches being monitored by this PDU.  This is the 
         number of entries in the cpiPduBranchTable."
    ::= { branch 100 }

cpiPduBranchTable OBJECT-TYPE
    SYNTAX      SEQUENCE OF CpiPduBranchEntry
    MAX-ACCESS  not-accessible
    STATUS      current
    DESCRIPTION
        "This table contains a list of PDU branch entries that are being
         monitored by the PDU.
         
         The table contains one, or many rows, depending upon the number
         of PDUs being monitored and the number of branches per PDU. Each row 
         in the table represents a PDU branch in the daisy chain.
         
         The table is indexed based on the corresponding Branch ID and
         the source PDU MAC."
    ::= { branch 110 }

    cpiPduBranchEntry OBJECT-TYPE
        SYNTAX      CpiPduBranchEntry
        MAX-ACCESS  not-accessible
        STATUS      current
        DESCRIPTION
            "This entry defines the columns to be populated in the
             'cpiPduBranchTable'.  Each column represents an attribute of a PDU.
             This table is indexed by the PDU Line identifier that is unique 
             within the PDU."

        INDEX
        { 
            cpiPduBranchId,
            cpiPduBranchMac
        }
        ::= { cpiPduBranchTable 1 }

    CpiPduBranchEntry ::= SEQUENCE 
    {
        cpiPduBranchMac			    MacAddress,
        cpiPduBranchId			    DisplayString,	
        cpiPduBranchCurrent		    Integer32,
        cpiPduBranchMaxCurrent		Integer32,
        cpiPduBranchVoltage		    Integer32,
        cpiPduBranchPower 		    Integer32,
        cpiPduBranchPowerFactor		Integer32,
        cpiPduBranchStatus		    Integer32,
        cpiPduBranchEnergy		    Counter64
    }

    cpiPduBranchMac OBJECT-TYPE
        SYNTAX      MacAddress
        MAX-ACCESS  read-only
        STATUS      current
        DESCRIPTION
            "Get the MAC address of the PDU that owns the branch."
        ::= { cpiPduBranchEntry 1 }

    cpiPduBranchId OBJECT-TYPE
        SYNTAX      Integer32
        MAX-ACCESS  read-only
        STATUS      current
        DESCRIPTION
            "Get the ID of the branch on the owning PDU."
        ::= { cpiPduBranchEntry 2 }

    cpiPduBranchCurrent OBJECT-TYPE
        SYNTAX      Integer32
        MAX-ACCESS  read-only
        STATUS      current
        DESCRIPTION
            "Get the current draw in 1/100 amp of the branch on the PDU.  Convert the value by dividing by 100."
        ::= { cpiPduBranchEntry 3 }

    cpiPduBranchMaxCurrent OBJECT-TYPE
        SYNTAX      Integer32
        MAX-ACCESS  read-only
        STATUS      current
        DESCRIPTION
            "Get the maximum current draw in 1/100 amp of the branch on the PDU.  Convert the value by dividing by 100."
        ::= { cpiPduBranchEntry 4 }

    cpiPduBranchVoltage OBJECT-TYPE
        SYNTAX      Integer32
        MAX-ACCESS  read-only
        STATUS      current
        DESCRIPTION
            "Get the voltage in 1/10 volts of the branch on the PDU.  Convert the value by dividing by 10."
        ::= { cpiPduBranchEntry 5 }

    cpiPduBranchPower OBJECT-TYPE
        SYNTAX      Integer32
        MAX-ACCESS  read-only
        STATUS      current
        DESCRIPTION
            "Get the power in volt-amps for the branch."
        ::= { cpiPduBranchEntry 6 }

    cpiPduBranchPowerFactor OBJECT-TYPE
        SYNTAX      Integer32
        MAX-ACCESS  read-only
        STATUS      current
        DESCRIPTION
            "Get the power factor for the branch."
        ::= { cpiPduBranchEntry 7 }

    cpiPduBranchStatus OBJECT-TYPE
        SYNTAX      INTEGER { noalarm(0), warning(1), alarm(2) }
        MAX-ACCESS  read-only
        STATUS      current
        DESCRIPTION
            "Get the alarm status of the branch."
        ::= { cpiPduBranchEntry 8 }

    cpiPduBranchEnergy OBJECT-TYPE
        SYNTAX      Counter64
        MAX-ACCESS  read-only
        STATUS      current
        DESCRIPTION
            "Get the branch energy accumulated in decaVA-secs, divide by 360 to obtain VA-hr."
        ::= { cpiPduBranchEntry 9 }

cpiPduBranchAlertTable OBJECT-TYPE
    SYNTAX      SEQUENCE OF CpiPduBranchAlertEntry
    MAX-ACCESS  not-accessible
    STATUS      current
    DESCRIPTION
        "This table contains a list of PDU branch alert entries that are
         being monitored by the PDU.

         The table contains one, or many rows, depending upon the number
         of PDUs being monitored and the number of branches per PDU. Each row 
         in the table represents a PDU branch in the daisy chain.
         
         The table is indexed based on the corresponding Branch ID and the
         source PDU MAC."
    ::= { branch 210 }

    cpiPduBranchAlertEntry OBJECT-TYPE
        SYNTAX      CpiPduBranchAlertEntry
        MAX-ACCESS  not-accessible
        STATUS      current
        DESCRIPTION
            "This entry defines the columns to be populated in the
             'cpiPduBranchAlertTable'.  Each column represents an alert attribute of a PDU.
             This table is indexed by the PDU Line identifier that is unique 
             within the PDU."

        INDEX
        { 
            cpiPduBranchAlertIndex 
        }
        ::= { cpiPduBranchAlertTable 1 }

    CpiPduBranchAlertEntry ::= SEQUENCE 
    {
        cpiPduBranchAlertIndex              Unsigned32,
        cpiPduBranchAlertMac		        MacAddress,
        cpiPduBranchAlertBranchId		    Integer32,
        cpiPduBranchAlertWarnLoCurrent      Integer32,
        cpiPduBranchAlertWarnHiCurrent      Integer32,
        cpiPduBranchAlertLoCurrent          Integer32,
        cpiPduBranchAlertHiCurrent          Integer32,
        cpiPduBranchAlertCriticalCurrent    Integer32,
        cpiPduBranchAlertWarnLoVolt         Integer32,
        cpiPduBranchAlertWarnHiVolt         Integer32,
        cpiPduBranchAlertLoVolt             Integer32,
        cpiPduBranchAlertHiVolt             Integer32
    }
    
    cpiPduBranchAlertMac OBJECT-TYPE
        SYNTAX      MacAddress
        MAX-ACCESS  read-only
        STATUS      current
        DESCRIPTION
            "Get the MAC address of the PDU."
        ::= { cpiPduBranchAlertEntry 1 }

    cpiPduBranchAlertBranchId OBJECT-TYPE
        SYNTAX      Integer32
        MAX-ACCESS  read-only
        STATUS      current
        DESCRIPTION
            "Get the branch ID on the PDU."
        ::= { cpiPduBranchAlertEntry 2 }

    cpiPduBranchAlertWarnLoCurrent OBJECT-TYPE
        SYNTAX      Integer32
        MAX-ACCESS  read-write
        STATUS      current
        DESCRIPTION
            "Set or get the current draw in 1/100 amp of the branch on 
            the PDU that triggers a warning condition.  Convert the 
            value by dividing by 100."
        ::= { cpiPduBranchAlertEntry 3 }

    cpiPduBranchAlertWarnHiCurrent OBJECT-TYPE
        SYNTAX      Integer32
        MAX-ACCESS  read-write
        STATUS      current
        DESCRIPTION
            "Set or get the current draw in 1/100 amp of the branch on 
            the PDU that triggers a warning condition.  Convert the 
            value by dividing by 100."
        ::= { cpiPduBranchAlertEntry 4 }

    cpiPduBranchAlertLoCurrent OBJECT-TYPE
        SYNTAX      Integer32
        MAX-ACCESS  read-write
        STATUS      current
        DESCRIPTION
            "Set or get the current draw in 1/100 amp of the branch on 
            the PDU that triggers an alarm condition.  Convert the 
            value by dividing by 100."
        ::= { cpiPduBranchAlertEntry 5 }

    cpiPduBranchAlertHiCurrent OBJECT-TYPE
        SYNTAX      Integer32
        MAX-ACCESS  read-write
        STATUS      current
        DESCRIPTION
            "Set or get the current draw in 1/100 amp of the branch on 
            the PDU, that triggers an alarm condition.  Convert the 
            value by dividing by 100."
        ::= { cpiPduBranchAlertEntry 6 }

    cpiPduBranchAlertCriticalCurrent OBJECT-TYPE
        SYNTAX      Integer32
        MAX-ACCESS  read-write
        STATUS      current
        DESCRIPTION
            "Set or get the critical current draw in 1/100 amp of the 
            branch on the PDU.  Convert the value by dividing by 100."
        ::= { cpiPduBranchAlertEntry 7 }

    cpiPduBranchAlertWarnLoVolt OBJECT-TYPE
        SYNTAX      Integer32
        MAX-ACCESS  read-write
        STATUS      current
        DESCRIPTION
            "Set or get the minimum voltage that the branch can reach 
            up to in 1/10th volts, 0=ignore.  Convert the value by 
            dividing by 10."
        ::= { cpiPduBranchAlertEntry 8 }

    cpiPduBranchAlertWarnHiVolt OBJECT-TYPE
        SYNTAX      Integer32
        MAX-ACCESS  read-write
        STATUS      current
        DESCRIPTION
            "Set or get the maximum voltage that the branch can reach 
            up to in 1/10th volts, 0=ignore.  Convert the value by 
            dividing by 10."
        ::= { cpiPduBranchAlertEntry 9 }

    cpiPduBranchAlertLoVolt OBJECT-TYPE
        SYNTAX      Integer32
        MAX-ACCESS  read-write
        STATUS      current
        DESCRIPTION
            "Set or get the minimum voltage that the branch can reach 
            up to in 1/10th volts, 0=ignore.  Convert the value by 
            dividing by 10."
        ::= { cpiPduBranchAlertEntry 10 }

    cpiPduBranchAlertHiVolt OBJECT-TYPE
        SYNTAX      Integer32
        MAX-ACCESS  read-write
        STATUS      current
        DESCRIPTION
            "Set or get the maximum voltage that the branch can reach 
            up to in 1/10th volts, 0=ignore.  Convert the value by 
            dividing by 10."
        ::= { cpiPduBranchAlertEntry 11 }
        
    cpiPduBranchAlertIndex OBJECT-TYPE
        SYNTAX      Unsigned32
        MAX-ACCESS  read-only
        STATUS      current
        DESCRIPTION
            "Index for branch aler"
        ::= { cpiPduBranchAlertEntry 12 }
        
    cpiPduBranchAlertIndex OBJECT-TYPE
        SYNTAX      Unsigned32
        MAX-ACCESS  read-only
        STATUS      current
        DESCRIPTION
            "Index for branch alert."
        ::= { cpiPduBranchAlertEntry 13 }

outlet OBJECT IDENTIFIER ::= { econnect 4 }

cpiOutletTableCount OBJECT-TYPE
    SYNTAX      Unsigned32
    UNITS       "Count"
    MAX-ACCESS  read-only
    STATUS      current
    DESCRIPTION
        "Get the number of PDU outlets being monitored by this PDU. This 
         is the number of entries in the cpiPduOutletTable."
    ::= { outlet 1 }

cpiPduOutletTable OBJECT-TYPE
    SYNTAX      SEQUENCE OF CpiPduOutletEntry
    MAX-ACCESS  not-accessible
    STATUS      current
    DESCRIPTION
        "This table contains a list of PDU outlet entries that are being
         monitored by the PDU.

         The table contains one, or many rows, depending upon the number
         of PDUs being monitored and the number of outlets on each PDU. 
         Each row in the table represents a PDU outlet in the daisy chain.
         
         The table is indexed based on the corresponding Outlet ID and
         the source PDU MAC."
    ::= { outlet 10 }

    cpiPduOutletEntry OBJECT-TYPE
        SYNTAX      CpiPduOutletEntry
        MAX-ACCESS  not-accessible
        STATUS      current
        DESCRIPTION
            "This entry defines the columns to be populated in the
             'cpiPduOutletTable'.  Each column represents an outlet of a PDU.
             This table is indexed by the PDU Outlet identifier that is unique 
             within the PDU."

        INDEX
        { 
            cpiPduOutletId, 
            cpiPduOutletMac
        }
        ::= { cpiPduOutletTable 1 }

    CpiPduOutletEntry ::= SEQUENCE 
    {
        cpiPduOutletMac		    	MacAddress,
        cpiPduOutletId		    	Integer32,
        cpiPduOutletBranchId    	Integer32,
        cpiPduOutletName	    	DisplayString,
        cpiPduOutletDescription    	DisplayString,
        cpiPduOutletCurrent		    Integer32,	    
        cpiPduOutletVoltage		    Integer32,
        cpiPduOutletPower		    Integer32,	    
        cpiPduOutletStatus		    Integer32,
        cpiPduOutletEnergy		    Counter64,
        cpiPduOutletControl		    Integer32,
        cpiPduOutletReset		    Integer32
    }

    cpiPduOutletMac OBJECT-TYPE
        SYNTAX      MacAddress
        MAX-ACCESS  read-only
        STATUS      current
        DESCRIPTION
            "Get the MAC address of the source PDU."
        ::= { cpiPduOutletEntry 1 }

    cpiPduOutletId OBJECT-TYPE
        SYNTAX      Integer32
        MAX-ACCESS  read-only
        STATUS      current
        DESCRIPTION
            "Get the ID of the outlet on the PDU."
        ::= { cpiPduOutletEntry 2 }

    cpiPduOutletBranchId OBJECT-TYPE
        SYNTAX      Integer32
        MAX-ACCESS  read-only
        STATUS      current
        DESCRIPTION
            "Get the ID of the branch the outlet is associated with on the PDU."
        ::= { cpiPduOutletEntry 3 }

    cpiPduOutletName OBJECT-TYPE
        SYNTAX      DisplayString
        MAX-ACCESS  read-write
        STATUS      current
        DESCRIPTION
            "Set or get the user supplied name of the outlet on the PDU."
        ::= { cpiPduOutletEntry 4 }

    cpiPduOutletDescription OBJECT-TYPE
        SYNTAX      DisplayString
        MAX-ACCESS  read-write
        STATUS      current
        DESCRIPTION
            "Set or get the user supplied description of the outlet on the PDU."
        ::= { cpiPduOutletEntry 5 }

    cpiPduOutletCurrent OBJECT-TYPE
        SYNTAX      Integer32
        MAX-ACCESS  read-only
        STATUS      current
        DESCRIPTION
            "Get the current draw in 1/100 amp of the outlet on the PDU.  Convert 
            the value by dividing by 100."
        ::= { cpiPduOutletEntry 6 }

    cpiPduOutletVoltage OBJECT-TYPE
        SYNTAX      Integer32
        MAX-ACCESS  read-only
        STATUS      current
        DESCRIPTION
            "Get the voltage in 1/10 volts of the outlet on the PDU.  Convert the 
            value by dividing by 10."
        ::= { cpiPduOutletEntry 7 }

    cpiPduOutletPower OBJECT-TYPE
        SYNTAX      Integer32
        MAX-ACCESS  read-only
        STATUS      current
        DESCRIPTION
            "The power in Volt-Amps of the outlet on the PDU."
        ::= { cpiPduOutletEntry 8 }

    cpiPduOutletStatus OBJECT-TYPE
        SYNTAX      INTEGER { noalarm(0), warning(1), alarm(2) }
        MAX-ACCESS  read-only
        STATUS      current
        DESCRIPTION
            "Get the alarm status of the outlet."
        ::= { cpiPduOutletEntry 9 }

    cpiPduOutletEnergy OBJECT-TYPE
        SYNTAX      Counter64
        MAX-ACCESS  read-only
        STATUS      current
        DESCRIPTION
            "Get the outlet energy accumulated in decaWatt-secs, divide by 360 to obtain Watt-hr."
        ::= { cpiPduOutletEntry 10 }

    cpiPduOutletControl OBJECT-TYPE
        SYNTAX      INTEGER { off(0), on(1) }
        MAX-ACCESS  read-write
        STATUS      current
        DESCRIPTION
            "Set or get power control to the outlet."
        ::= { cpiPduOutletEntry 11 }

    cpiPduOutletReset OBJECT-TYPE
        SYNTAX      INTEGER { nominal(0), reset(1) }
        MAX-ACCESS  read-write
        STATUS      current
        DESCRIPTION
            "Set or get reset power to the outlet."
        ::= { cpiPduOutletEntry 12 }

cpiPduOutletConfigTable OBJECT-TYPE
    SYNTAX      SEQUENCE OF CpiPduOutletConfigEntry
    MAX-ACCESS  not-accessible
    STATUS      current
    DESCRIPTION
        "This table contains a list of PDU outlet configuration entries
        that are being monitored by the PDU.

         The table contains one, or many rows, depending upon the number
         of PDUs being monitored and the number of outlets per PDU. Each row 
         in the table represents a PDU outlet in the daisy chain.
         
         The table is indexed based on the corresponding Outlet ID and
         the source PDU MAC."
    ::= { outlet 210 }

    cpiPduOutletConfigEntry OBJECT-TYPE
        SYNTAX      CpiPduOutletConfigEntry
        MAX-ACCESS  not-accessible
        STATUS      current
        DESCRIPTION
            "This entry defines the columns to be populated in the
             'cpiPduOutletConfigTable'.  Each column represents an 
             configurable attribute of an outlet in the PDU. This 
             table is indexed by the PDU Line identifier that is 
             unique within the PDU."

        INDEX
        { 
            cpiPduOutletConfigOutletId,
            cpiPduOutletConfigMac
        }
        ::= { cpiPduOutletConfigTable 1 }

    CpiPduOutletConfigEntry ::= SEQUENCE 
    {
        cpiPduOutletConfigMac		        MacAddress,
        cpiPduOutletConfigOutletId		    Integer32,
        cpiPduOutletConfigOnDelay           Integer32,
        cpiPduOutletConfigResetDelay        Integer32
    }

    cpiPduOutletConfigMac OBJECT-TYPE
        SYNTAX      MacAddress
        MAX-ACCESS  read-only
        STATUS      current
        DESCRIPTION
            "Get the MAC address of the PDU."
        ::= { cpiPduOutletConfigEntry 1 }

    cpiPduOutletConfigOutletId OBJECT-TYPE
        SYNTAX      Integer32
        MAX-ACCESS  read-only
        STATUS      current
        DESCRIPTION
            "Get the ID of the outlet on the PDU."
        ::= { cpiPduOutletConfigEntry 2 }

    cpiPduOutletConfigOnDelay OBJECT-TYPE
        SYNTAX Integer32 (0..255)
        MAX-ACCESS read-write
        STATUS current
        DESCRIPTION
            "Set or get the outlet power-on delay in seconds."
        ::= { cpiPduOutletConfigEntry 3 }

    cpiPduOutletConfigResetDelay OBJECT-TYPE
        SYNTAX Integer32 (0..255)
        MAX-ACCESS read-write
        STATUS current
        DESCRIPTION
            "Set or get the outlet reset delay in seconds."
        ::= { cpiPduOutletConfigEntry 4 }

cpiPduOutletAlertTable OBJECT-TYPE
    SYNTAX      SEQUENCE OF CpiPduOutletAlertEntry
    MAX-ACCESS  not-accessible
    STATUS      current
    DESCRIPTION
        "This table contains a list of PDU outlet alert entries that are
        being monitored by the PDU.

         The table contains one, or many rows, depending upon the number
         of PDUs being monitored and the number of outlets per PDU. Each row 
         in the table represents a PDU outlet in the daisy chain.
         
         The table is indexed based on the corresponding Outlet ID and the
         source PDU MAC."
    ::= { outlet 310 }

    cpiPduOutletAlertEntry OBJECT-TYPE
        SYNTAX      CpiPduOutletAlertEntry
        MAX-ACCESS  not-accessible
        STATUS      current
        DESCRIPTION
            "This entry defines the columns to be populated in the
             'cpiPduOutletAlertTable'.  Each column represents an alert attribute of a PDU.
             This table is indexed by the PDU Line identifier that is unique 
             within the PDU."

        INDEX
        { 
            cpiPduOutletAlertOutletId,
            cpiPduOutletAlertMac
        }
        ::= { cpiPduOutletAlertTable 1 }

    CpiPduOutletAlertEntry ::= SEQUENCE 
    {
        cpiPduOutletAlertMac		        MacAddress,
        cpiPduOutletAlertOutletId	        Integer32,
        cpiPduOutletAlertWarnLoCurrent      Integer32,
        cpiPduOutletAlertWarnHiCurrent      Integer32,
        cpiPduOutletAlertLoCurrent          Integer32,
        cpiPduOutletAlertHiCurrent          Integer32,
        cpiPduOutletAlertCriticalCurrent    Integer32
    }

    cpiPduOutletAlertMac OBJECT-TYPE
        SYNTAX      MacAddress
        MAX-ACCESS  read-only
        STATUS      current
        DESCRIPTION
            "Get the MAC address of the PDU."
        ::= { cpiPduOutletAlertEntry 1 }

    cpiPduOutletAlertOutletId OBJECT-TYPE
        SYNTAX      DisplayString
        MAX-ACCESS  read-only
        STATUS      current
        DESCRIPTION
            "Get the outlet ID on the PDU."
        ::= { cpiPduOutletAlertEntry 2 }

    cpiPduOutletAlertWarnLoCurrent OBJECT-TYPE
        SYNTAX      Integer32
        MAX-ACCESS  read-write
        STATUS      current
        DESCRIPTION
            "Set or get the current draw in 1/100 amp of the branch on 
            the PDU that triggers a warning condition.  Convert the 
            value by dividing by 100."
        ::= { cpiPduOutletAlertEntry 3 }

    cpiPduOutletAlertWarnHiCurrent OBJECT-TYPE
        SYNTAX      Integer32
        MAX-ACCESS  read-write
        STATUS      current
        DESCRIPTION
            "Set or get the current draw in 1/100 amp of the branch on 
            the PDU that triggers a warning condition.  Convert the 
            value by dividing by 100."
        ::= { cpiPduOutletAlertEntry 4 }

    cpiPduOutletAlertLoCurrent OBJECT-TYPE
        SYNTAX      Integer32
        MAX-ACCESS  read-write
        STATUS      current
        DESCRIPTION
            "Set or get the current draw in 1/100 amp of the branch on 
            the PDU that triggers an alarm condition.  Convert the 
            value by dividing by 100."
        ::= { cpiPduOutletAlertEntry 5 }

    cpiPduOutletAlertHiCurrent OBJECT-TYPE
        SYNTAX      Integer32
        MAX-ACCESS  read-write
        STATUS      current
        DESCRIPTION
            "Set or get the current draw in 1/100 amp of the branch on 
            the PDU, that triggers an alarm condition.  Convert the 
            value by dividing by 100."
        ::= { cpiPduOutletAlertEntry 6 }

    cpiPduOutletAlertCriticalCurrent OBJECT-TYPE
        SYNTAX      Integer32
        MAX-ACCESS  read-write
        STATUS      current
        DESCRIPTION
            "Set or get the critical current draw in 1/100 amp of the 
            outlet on the PDU.  Convert the value by dividing by 100."
        ::= { cpiPduOutletAlertEntry 7 }

sensors OBJECT IDENTIFIER ::= { econnect 5 }

cpiPduSensorCount OBJECT-TYPE
    SYNTAX      Unsigned32
    UNITS       "Count"
    MAX-ACCESS  read-only
    STATUS      current
    DESCRIPTION
        "Get the number of PDU sensors being monitored by this PDU.  This is the 
         number of entries in the cpiPduSensorTable."
    ::= { sensors 1 }

cpiPduProbeTable OBJECT-TYPE
    SYNTAX      SEQUENCE OF CpiPduProbeEntry
    MAX-ACCESS  not-accessible
    STATUS      current
    DESCRIPTION
        "This table contains a list of PDU probes that are being monitored
         by the PDU.

         The table contains zero, one, or many rows, depending upon the number
         of PDUs being monitored and the number of probes attached to the PDUs in
         the daisy chain. Each row in the table represents a probe in the daisy chain.
         
         The table is index based on the corresponding Probe ID and the source
         PDU MAC."
    ::= { sensors 5 }

    cpiPduProbeEntry OBJECT-TYPE
        SYNTAX      CpiPduProbeEntry
        MAX-ACCESS  not-accessible
        STATUS      current
        DESCRIPTION
            "This entry defines the columns to be populated in the
            'cpiPduProbeTable'. Each column represents an attribute of a PDU probe.
            This table is indexed by the PDU identifier that is unique 
            within the PDU and the probe ID."

        INDEX
        { 
            cpiPduProbeId, 
            cpiPduProbeMac
        }
        ::= { cpiPduProbeTable 1 }

    CpiPduProbeEntry ::= SEQUENCE 
    {
        cpiPduProbeMac	MacAddress,
        cpiPduProbeId	Integer32,
        cpiPduProbeName	DisplayString
    }
	
    cpiPduProbeMac OBJECT-TYPE
        SYNTAX      MacAddress
        MAX-ACCESS  read-only
        STATUS      current
        DESCRIPTION
            "Get the MAC address of the PDU."
        ::= { cpiPduProbeEntry 1 }

    cpiPduProbeId OBJECT-TYPE
        SYNTAX      Integer32
        MAX-ACCESS  read-only
        STATUS      current
        DESCRIPTION
            "Get the probe ID on the PDU."
        ::= { cpiPduProbeEntry 2 }

    cpiPduProbeName OBJECT-TYPE
        SYNTAX      DisplayString
        MAX-ACCESS  read-write
        STATUS      current
        DESCRIPTION
            "Set or get the user defined name of the probe."
        ::= { cpiPduProbeEntry 3 }
		
cpiPduSensorTable OBJECT-TYPE
    SYNTAX      SEQUENCE OF CpiPduSensorEntry
    MAX-ACCESS  not-accessible
    STATUS      current
    DESCRIPTION
        "This table contains a list of PDU sensor entries that are being monitored
         by the PDU.

         The table contains zero, one, or many rows, depending upon the number
         of PDUs being monitored and the number of sensors attached to the PDUs in
         the daisy chain. Each row in the table represents a sensor in the daisy chain.
         
         The table is index based on the corresponding Sensor ID and the source
         PDU MAC."
    ::= { sensors 10 }

    cpiPduSensorEntry OBJECT-TYPE
        SYNTAX      CpiPduSensorEntry
        MAX-ACCESS  not-accessible
        STATUS      current
        DESCRIPTION
            "This entry defines the columns to be populated in the 'cpiPduSensorTable'. 
			Each column represents an attribute of a PDU sensor. This table is indexed 
			by the PDU identifier that is unique within the PDU and the sensor ID."

        INDEX
        { 
            cpiPduSensorId, 
            cpiPduSensorMac
        }
        ::= { cpiPduSensorTable 1 }

    CpiPduSensorEntry ::= SEQUENCE 
    {
        cpiPduSensorMac		MacAddress,
        cpiPduSensorId		Integer32,
        cpiPduSensorName	DisplayString,
        cpiPduSensorType	Integer32,
        cpiPduSensorValue	Integer32
    }

    cpiPduSensorMac OBJECT-TYPE
        SYNTAX      MacAddress
        MAX-ACCESS  read-only
        STATUS      current
        DESCRIPTION
            "Get the MAC address of the PDU."
        ::= { cpiPduSensorEntry 1 }

    cpiPduSensorId OBJECT-TYPE
        SYNTAX      Integer32
        MAX-ACCESS  read-only
        STATUS      current
        DESCRIPTION
            "Get the sensor ID on the PDU."
        ::= { cpiPduSensorEntry 2 }

    cpiPduSensorName OBJECT-TYPE
        SYNTAX      DisplayString
        MAX-ACCESS  read-only
        STATUS      current
        DESCRIPTION
            "Set or get the user defined name of the sensor."
        ::= { cpiPduSensorEntry 3 }

    cpiPduSensorType OBJECT-TYPE
        SYNTAX      INTEGER { temperature(1), humidity(2) }
        MAX-ACCESS  read-only
        STATUS      current
        DESCRIPTION
            "Get the type of sensor for the entry."
        ::= { cpiPduSensorEntry 4 }

    cpiPduSensorValue OBJECT-TYPE
        SYNTAX      Integer32
        MAX-ACCESS  read-only
        STATUS      current
        DESCRIPTION
            "Get the value of the sensor. For temperature the value is in degrees 
			Fahrenheit and for humidity the value is percent humidity."
        ::= { cpiPduSensorEntry 5 }

cpiPduSensorAlertTable OBJECT-TYPE
    SYNTAX      SEQUENCE OF CpiPduSensorAlertEntry
    MAX-ACCESS  not-accessible
    STATUS      current
    DESCRIPTION
        "This table contains a list of PDU sensor alert entries that are
         being monitored by the PDU.

         The table contains zero, one, or many rows, depending upon the number
         of PDUs being monitored and the number of sensors attached to the PDUs in
         the daisy chain. Each row in the table represents a sensor in the daisy chain.
         
         The table is index based on the corresponding Sonsor ID and the source
         PDU MAC."
    ::= { sensors 110 }

    cpiPduSensorAlertEntry OBJECT-TYPE
        SYNTAX      CpiPduSensorAlertEntry
        MAX-ACCESS  not-accessible
        STATUS      current
        DESCRIPTION
            "This entry defines the columns to be populated in the 'cpiPduSensorAlertTable'. 
			Each column represents an attribute of a PDU sensor alert. This table 
			is indexed by the PDU identifier that is unique within the PDU."

        INDEX
        { 
            cpiPduSensorAlertSensorId,
            cpiPduSensorAlertMac
        }
        ::= { cpiPduSensorAlertTable 1 }

    CpiPduSensorAlertEntry ::= SEQUENCE 
    {
        cpiPduSensorAlertMac		        MacAddress,		
        cpiPduSensorAlertSensorId	        Integer32,
        cpiPduSensorAlertWarnMin	        Integer32,
        cpiPduSensorAlertWarnMax	        Integer32,
        cpiPduSensorAlertMin	            Integer32,
        cpiPduSensorAlertMax	            Integer32
    }

    cpiPduSensorAlertMac OBJECT-TYPE
        SYNTAX      MacAddress
        MAX-ACCESS  read-only
        STATUS      current
        DESCRIPTION
            "Get the MAC address of the PDU."
        ::= { cpiPduSensorAlertEntry 1 }

    cpiPduSensorAlertSensorId OBJECT-TYPE
        SYNTAX      Integer32
        MAX-ACCESS  read-only
        STATUS      current
        DESCRIPTION
            "Get the id of the sensor."
        ::= { cpiPduSensorAlertEntry 2 }

    cpiPduSensorAlertWarnMin OBJECT-TYPE
        SYNTAX      Integer32
        MAX-ACCESS  read-write
        STATUS      current
        DESCRIPTION
            "Set or get the minimum warning value of the sensor."
        ::= { cpiPduSensorAlertEntry 3 }

    cpiPduSensorAlertWarnMax OBJECT-TYPE
        SYNTAX      Integer32
        MAX-ACCESS  read-write
        STATUS      current
        DESCRIPTION
            "Set or get the maximum warning value of the sensor."
        ::= { cpiPduSensorAlertEntry 4 }

    cpiPduSensorAlertMin OBJECT-TYPE
        SYNTAX      Integer32
        MAX-ACCESS  read-write
        STATUS      current
        DESCRIPTION
            "Set or get the minimum alarm value of the sensor."
        ::= { cpiPduSensorAlertEntry 5 }

    cpiPduSensorAlertMax OBJECT-TYPE
        SYNTAX      Integer32
        MAX-ACCESS  read-write
        STATUS      current
        DESCRIPTION
            "Set or get the maximum alarm value of the sensor."
        ::= { cpiPduSensorAlertEntry 6 }

group OBJECT IDENTIFIER ::= { econnect 6 }

cpiPduGroupCount OBJECT-TYPE
    SYNTAX      Unsigned32
    UNITS       "Count"
    MAX-ACCESS  read-only
    STATUS      current
    DESCRIPTION
        "Get the number of supported groups by the PDU. Value from 0 to 16."
    ::= { group 1 }

cpiPduGroupOutletCount OBJECT-TYPE
    SYNTAX      Unsigned32
    UNITS       "Count"
    MAX-ACCESS  read-only
    STATUS      current
    DESCRIPTION
        "Get the number of outlets in the Group Outlet Table."
    ::= { group 2 }

cpiGroupTable OBJECT-TYPE
    SYNTAX      SEQUENCE OF CpiGroupEntry
    MAX-ACCESS  not-accessible
    STATUS      current
    DESCRIPTION
        "This table contains a list of PDU group entries that are being monitored
        by the PDU.
         
         The table contains one, or many rows, depending upon the number
         of groups that have been configured. Each row in the table represents a
         group."
    ::= { group 10 }

    cpiGroupEntry OBJECT-TYPE
        SYNTAX      CpiGroupEntry
        MAX-ACCESS  not-accessible
        STATUS      current
        DESCRIPTION
            "This entry defines the columns to be populated in the
             'cpiGroupTable'.  This table is indexed by the group identifier that 
             is unique within the PDU."

        INDEX
        { 
            cpiGroupEntryIndex 
        }
        ::= { cpiGroupTable 1 }

    CpiGroupEntry ::= SEQUENCE 
    {
        cpiGroupEntryIndex      Unsigned32,
        cpiGroupName		    DisplayString
    }

    cpiGroupEntryIndex OBJECT-TYPE
        SYNTAX      Unsigned32
        MAX-ACCESS  read-only
        STATUS      current
        DESCRIPTION
            "This is the index that indicates the row of the 'cpiPduTable'."
        ::= { cpiGroupEntry 1 }

    cpiGroupName OBJECT-TYPE
        SYNTAX      DisplayString
        MAX-ACCESS  read-write
        STATUS      current
        DESCRIPTION
            "Name for GROUP 1 of receptacles."
        ::= { cpiGroupEntry 2 }
        

cpiGroupOutletTable OBJECT-TYPE
    SYNTAX      SEQUENCE OF CpiGroupOutletEntry
    MAX-ACCESS  not-accessible
    STATUS      current
    DESCRIPTION
        "This table contains a list of PDU group entries.
         The table contains zero, one, or many rows, depending upon the number
         of groups that have been configured. Each row in the table represents a
         group."
    ::= { group 20 }

    cpiGroupOutletEntry OBJECT-TYPE
        SYNTAX      CpiGroupOutletEntry
        MAX-ACCESS  not-accessible
        STATUS      current
        DESCRIPTION
            "This entry defines the columns to be populated in the
             'cpiGroupTable'.  This table is indexed by the group identifier that 
             is unique within the PDU."

        INDEX
        { 
            cpiGroupOutletEntryIndex 
        }
        ::= { cpiGroupOutletTable 1 }
        
    CpiGroupOutletEntry ::= SEQUENCE 
    {
        cpiGroupOutletEntryIndex    Unsigned32,
        cpiGroupOutletGroupID		Unsigned32,
        cpiGroupOutletPDUMac        MacAddress,
        cpiGroupOutletOutletId		Integer32
    }

    cpiGroupOutletEntryIndex OBJECT-TYPE
        SYNTAX      Unsigned32
        MAX-ACCESS  read-only
        STATUS      current
        DESCRIPTION
            "This is the index that indicates the row of the 'cpiGroupOutletTable'."
        ::= { cpiGroupOutletEntry 1 }

    cpiGroupOutletGroupID OBJECT-TYPE
        SYNTAX      Unsigned32
        MAX-ACCESS  read-only
        STATUS      current
        DESCRIPTION
            "Name for GROUP 1 of receptacles."
        ::= { cpiGroupOutletEntry 2 }

    cpiGroupOutletPDUMac OBJECT-TYPE
        SYNTAX		MacAddress
        MAX-ACCESS	read-write
        STATUS		current
        DESCRIPTION
            "MAC of PDU the outlet is on."
        ::= { cpiGroupOutletEntry 3 }
        
    cpiGroupOutletOutletId OBJECT-TYPE
        SYNTAX		Integer32
        MAX-ACCESS	read-write
        STATUS		current
        DESCRIPTION
            "The ID of the outlet on the PDU."
        ::= { cpiGroupOutletEntry 4 }

easData OBJECT IDENTIFIER ::= { econnect 7 }

cpiEasCount OBJECT-TYPE
    SYNTAX      Unsigned32
    UNITS       "Count"
    MAX-ACCESS  read-only
    STATUS      current
    DESCRIPTION
        "Get the number of locks connected to the PDU.  This includes the PDUs on the daisy chain."
    ::= { easData 1 }
	
cpiEasConfigTable OBJECT-TYPE
    SYNTAX      SEQUENCE OF CpiEasConfigEntry
    MAX-ACCESS  not-accessible
    STATUS      current
    DESCRIPTION
        "This table contains a list of electronic locks that are connected to the PDU
		and allows for the configuration of the various settings associated with the
		EAS (electronic access system).

         The table contains zero, one, or many rows, depending upon the number
         of PDUs being monitored and the number of locks attached to the PDUs in
         the daisy chain. Each row in the table represents a lock in the daisy chain.
         
         The table is index based on the corresponding lock ID and the source
         PDU MAC."
    ::= { easData 90 }

    cpiEasConfigEntry OBJECT-TYPE
        SYNTAX      CpiEasConfigEntry
        MAX-ACCESS  not-accessible
        STATUS      current
        DESCRIPTION
            "This entry defines the columns to be populated in the 'cpiEasTable'. 
			Each column represents an attribute of a PDU lock. This table is indexed 
			by the PDU identifier that is unique within the PDU and the lock ID."

        INDEX
        { 
            cpiEasConfigLockMac
        }
        ::= { cpiEasConfigTable 1 }

    CpiEasConfigEntry ::= SEQUENCE 
    {
        cpiEasConfigLockMac		MacAddress,
		cpiEasConfigEnabled		Integer32,
        cpiEasFrontLockEnabled	Integer32,
        cpiEasRearLockEnabled	Integer32,
        cpiEasLockHoldOpenTime	Integer32,
		cpiEasDoorOpenAlarmTime	Integer32
    }
	
	cpiEasConfigLockMac OBJECT-TYPE
        SYNTAX      MacAddress
        MAX-ACCESS  read-only
        STATUS      current
        DESCRIPTION
            "Get the MAC address of the PDU."
        ::= { cpiEasConfigEntry 1 }

	cpiEasConfigEnabled OBJECT-TYPE
		SYNTAX INTEGER { not-available(0), available(1) }
		MAX-ACCESS read-only
		STATUS current
		DESCRIPTION
			"Indicates whether the Electronic Access System (EAS) is available on the PDU."
		::= { cpiEasConfigEntry 2 }

	cpiEasFrontLockEnabled OBJECT-TYPE
		SYNTAX INTEGER { disabled(0), enabled(1) }
		MAX-ACCESS read-write
		STATUS current
		DESCRIPTION
			"Enables the front lock on the EAS."
		::= { cpiEasConfigEntry 3 }

	cpiEasRearLockEnabled OBJECT-TYPE
		SYNTAX INTEGER { disabled(0), enabled(1) }
		MAX-ACCESS read-write
		STATUS current
		DESCRIPTION
			"Enables the rear lock on the EAS."
		::= { cpiEasConfigEntry 4 }

	cpiEasLockHoldOpenTime OBJECT-TYPE
		SYNTAX INTEGER
		MAX-ACCESS read-write
		STATUS current
		DESCRIPTION
			"The length of time in seconds to hold open the lock after a successful card scan."
		::= { cpiEasConfigEntry 5 }

	cpiEasDoorOpenAlarmTime OBJECT-TYPE
		SYNTAX INTEGER
		MAX-ACCESS read-write
		STATUS current
		DESCRIPTION
			"The length of time in minutes before alerting that the door is open."
		::= { cpiEasConfigEntry 6 }
	
cpiEasTable OBJECT-TYPE
    SYNTAX      SEQUENCE OF CpiEasEntry
    MAX-ACCESS  not-accessible
    STATUS      current
    DESCRIPTION
        "This table contains a list of electronic locks that are connected to the PDU

         The table contains zero, one, or many rows, depending upon the number
         of PDUs being monitored and the number of locks attached to the PDUs in
         the daisy chain. Each row in the table represents a lock in the daisy chain.
         
         The table is index based on the corresponding lock ID and the source
         PDU MAC."
    ::= { easData 100 }

    cpiEasEntry OBJECT-TYPE
        SYNTAX      CpiEasEntry
        MAX-ACCESS  not-accessible
        STATUS      current
        DESCRIPTION
            "This entry defines the columns to be populated in the 'cpiEasTable'. 
			Each column represents an attribute of a PDU lock. This table is indexed 
			by the PDU identifier that is unique within the PDU and the lock ID."

        INDEX
        { 
            cpiPduLockId, 
            cpiPduLockMac
        }
        ::= { cpiEasTable 1 }

    CpiEasEntry ::= SEQUENCE 
    {
        cpiPduLockMac		MacAddress,
        cpiPduLockId		Integer32,
        cpiPduEasStatus		Integer32,
        cpiPduDoorStatus	Integer32,
        cpiPduLockStatus	Integer32,
        cpiPduTamperStatus	Integer32,
		cpiEasError			Integer32,
        cpiPduLockCtrl		Integer32
    }

    cpiPduLockMac OBJECT-TYPE
        SYNTAX      MacAddress
        MAX-ACCESS  read-only
        STATUS      current
        DESCRIPTION
            "Get the MAC address of the PDU."
        ::= { cpiEasEntry 1 }

    cpiPduLockId OBJECT-TYPE
        SYNTAX      INTEGER { front(1), rear(2) }
        MAX-ACCESS  read-only
        STATUS      current
        DESCRIPTION
            "Get the lock ID on the PDU."
        ::= { cpiEasEntry 2 }

    cpiPduEasStatus OBJECT-TYPE
        SYNTAX      INTEGER { inactive(0), ready(1), error(2) }
        MAX-ACCESS  read-only
        STATUS      current
        DESCRIPTION
            "Indicates if the Electronic Access Control system is ready, inactive, or in an error state.
            
            If the status is Inactive, then the lock is not enabled on the PDU.
            If the status is Error, then the cpiEasError field will have an error code to help diagnose the issue.
            If the status is Ready, then the lock at the door is enabled and ready."
        ::= { cpiEasEntry 3 }

    cpiPduDoorStatus OBJECT-TYPE
        SYNTAX      INTEGER { closed(0), open(1) }
        MAX-ACCESS  read-only
        STATUS      current
        DESCRIPTION
            "Indicates if the door sensor is closed or open."
        ::= { cpiEasEntry 4 }

    cpiPduLockStatus OBJECT-TYPE
        SYNTAX      INTEGER { closed(0), open(1) }
        MAX-ACCESS  read-only
        STATUS      current
        DESCRIPTION
            "Indicates if the lock is closed or open."
        ::= { cpiEasEntry 5 }

    cpiPduForceStatus OBJECT-TYPE
        SYNTAX      INTEGER { normal(0), force(1) }
        MAX-ACCESS  read-only
        STATUS      current
        DESCRIPTION
            "Indicates if the cabinet was forced open by a command from the webUI or SNMP interfaces."
        ::= { cpiEasEntry 6 }
        
    cpiPduTamperStatus OBJECT-TYPE
        SYNTAX      INTEGER { normal(0), tamper(1) }
        MAX-ACCESS  read-only
        STATUS      current
        DESCRIPTION
            "Indicates if the cabinet is currently unlocked/opened without an authorization scan."
        ::= { cpiEasEntry 7 }

    cpiEasError OBJECT-TYPE
            SYNTAX      Unsigned32
            MAX-ACCESS  read-only
            STATUS      current
            DESCRIPTION
                    "Gets the error code associated for the electronic lock system. The possible error codes are:
                    
                    196608 (0x00030000
) - No error, the lock is working and ready.
                    167968771 (0x0a030003
) - The lock is not enabled. Enable the lock through the cpiEasConfigTable.
                    167837698 (0x0a010002
) - The lock is not responding.  Ensure that the lock is connected to the PDU,
                                             and is recieving power. Try to disable and re-enable the lock in the
                                             cpiEasConfigTable."
            ::= { cpiEasEntry 8 }
            
    cpiEasLockVer OBJECT-TYPE
            SYNTAX		DisplayString
            MAX-ACCESS	read-only
            STATUS		current
            DESCRIPTION
                    "Gets the version of the electronic lock control."
            ::= { cpiEasEntry 9 }
            
    cpiEasLockSerialNumber OBJECT-TYPE
            SYNTAX		DisplayString
            MAX-ACCESS	read-only
            STATUS		current
            DESCRIPTION
                    "Get the serial number of the electronic lock control."
            ::= { cpiEasEntry 10 }

    cpiPduLockCtrl OBJECT-TYPE
        SYNTAX      INTEGER { close(0), open(1) }
        MAX-ACCESS  read-write
        STATUS      current
        DESCRIPTION
            "Tells the system to open the locks on the cabinet."
        ::= { cpiEasEntry 11 }

traps OBJECT IDENTIFIER ::= { econnect 500 }

trapInformation OBJECT IDENTIFIER ::= { traps 0 }

trapInfoUserName OBJECT-TYPE
	SYNTAX      DisplayString
	MAX-ACCESS  not-accessible
	STATUS      current
	DESCRIPTION
		"The user Id associated with the action."
	::= { trapInformation 1 }
	
trapInfoCardId OBJECT-TYPE
	SYNTAX      DisplayString
	MAX-ACCESS  not-accessible
	STATUS      current
	DESCRIPTION
		"The card Id associated with the action."
	::= { trapInformation 2 }
	
trapInfoConfigName OBJECT-TYPE
	SYNTAX      DisplayString
	MAX-ACCESS  not-accessible
	STATUS      current
	DESCRIPTION
		"The configuration value that was changed."
	::= { trapInformation 3 }
	
trapInfoInterface OBJECT-TYPE
	SYNTAX      INTEGER { serial(0), webgui(1), snmp(2), unkown(3), lcd(4), internal(5), bulk(6) }
	MAX-ACCESS  not-accessible
	STATUS      current
	DESCRIPTION
		"An identifier for the affected interface."
	::= { trapInformation 4 }

trapInfoVarId OBJECT-TYPE
	SYNTAX      OBJECT IDENTIFIER
	MAX-ACCESS  not-accessible
	STATUS      current
	DESCRIPTION
		"An identifier for the value that was changed."
	::= { trapInformation 5 }
	
trapInfoBootType  OBJECT-TYPE
	SYNTAX      INTEGER { cold(0), warm(1), restart(2), reboot(3) }
	MAX-ACCESS  not-accessible
	STATUS      current
	DESCRIPTION
		"Indicates that type of boot up occurring. A Cold boot is done from a complete power off. A Warm boot
		was not a loss in power, but just a reboot of the control module."
	::= { trapInformation 6 }
	
trapInfoProgress OBJECT-TYPE
	SYNTAX Integer32 (0..100)
	MAX-ACCESS  not-accessible
	STATUS      current
	DESCRIPTION
		"Indicates the percent complete of an operation."
	::= { trapInformation 7 }
	
trapInfoResult OBJECT-TYPE
	SYNTAX      INTEGER { success(0), failure(1) }
	MAX-ACCESS  not-accessible
	STATUS      current
	DESCRIPTION
		"Indicates the result of an operation."
	::= { trapInformation 8 }
	
trapInfoErrorCode OBJECT-TYPE
	SYNTAX      INTEGER
	MAX-ACCESS  not-accessible
	STATUS      current
	DESCRIPTION
		"Indicates the error code of an operation.  See the operation for details.
		
		Firmware Update Operation Error Codes: 
                     151060481 - Error: Insufficient space available on the PDU to complete the operation.
                     151060482 - Error: Too many packets were lost in the transfer process.  Please try the operation again.
                     151060483 - Error: The firmware file is corrupted and can not be used.
                     151060484 - Error: There was a failure in writing the firmware data out to internal memory.
                     151060485 - Error: The firmware file could not be opened and processed correctly.
                     151060489 - Error: A unknown failure occured while performing a firmware upgrade.
                     
                     151060490 - Info: A firmware update is in progress.  No issue currently.
                     151191558 - Info: A firmware upgrade has completed and does not need to reboot.
                     151191559 - Info: A firmware upgrade has compelted and will reboot.
                     151191560 - Info: A firmware upgrade has compelted and it was not needed. PDU will not reboot."
	::= { trapInformation 9 }
	
trapInfoGroupName OBJECT-TYPE
	SYNTAX      DisplayString
	MAX-ACCESS  not-accessible
	STATUS      current
	DESCRIPTION
		"The user group Id associated with the action."
	::= { trapInformation 10 }


systemNotifications OBJECT IDENTIFIER ::= { traps 1 }
	-- config changes notification

systemConfigChangeAlert NOTIFICATION-TYPE
	OBJECTS {
		-- pdu cabinet
		cpiPduCabinetId,
		-- pdu Mac
		cpiPduMac,
		-- pdu name
		cpiPduName,
                trapInfoConfigName,
                trapInfoUserName,
                trapInfoInterface
	}
	STATUS current
	DESCRIPTION
            "Notification that a configuration value was changed on the PDU."
	::= { systemNotifications 1 }

	-- system booting notification
systemBootAlert NOTIFICATION-TYPE
	OBJECTS {
		-- pdu cabinet
		cpiPduCabinetId,
		-- pdu Mac
		cpiPduMac,
		-- pdu name
		cpiPduName,
		trapInfoUserName,
                trapInfoBootType
	}
	STATUS current
	DESCRIPTION
            "Notification that a PDU is booting up."
	::= { systemNotifications 2 }
	
	-- firmware update start notification
systemFWUpdateStartAlert NOTIFICATION-TYPE
	OBJECTS {
		-- pdu cabinet
		cpiPduCabinetId,
		-- pdu Mac
		cpiPduMac,
		-- pdu name
		cpiPduName,
		trapInfoUserName
	}
	STATUS current
	DESCRIPTION
            "Notification that a firmware update has been initiated."
	::= { systemNotifications 3 }

	-- firmware update status notification
systemFWUpdateStatusAlert NOTIFICATION-TYPE
	OBJECTS {
		-- pdu cabinet
		cpiPduCabinetId,
		-- pdu Mac
		cpiPduMac,
		-- pdu name
		cpiPduName,
		trapInfoProgress
	}
	STATUS current
	DESCRIPTION
            "Notification that about the progress of the firmware update."
	::= { systemNotifications 4 }
	
	-- firmware update complete notification
systemFWUpdateCompleteAlert NOTIFICATION-TYPE
	OBJECTS {
		-- pdu cabinet
		cpiPduCabinetId,
		-- pdu Mac
		cpiPduMac,
		-- pdu name
		cpiPduName,
		trapInfoResult,
		trapInfoErrorCode
	}
	STATUS current
	DESCRIPTION
            "Notification that about the progress of the firmware update."
	::= { systemNotifications 5 }

	-- SecureArray failover notification
systemSecureArrayFailoverAlert NOTIFICATION-TYPE
	OBJECTS {
		-- pdu cabinet
		cpiPduCabinetId,
		-- pdu Mac
		cpiPduMac,
		-- pdu name
		cpiPduName
	}
	STATUS current
	DESCRIPTION
            "Notification that the SecureArray is being managed by the identified PDU."
	::= { systemNotifications 6 }

	-- SecureArray Pdu disconnected notification
systemSecureArrayDisconnectAlert NOTIFICATION-TYPE
	OBJECTS {
		-- pdu cabinet
		cpiPduCabinetId,
		-- pdu Mac
		cpiPduMac,
		-- pdu name
		cpiPduName
	}
	STATUS current
	DESCRIPTION
            "Notification that the specified PDU disconnected from the SecureArray."
	::= { systemNotifications 7 }
	
	-- SecureArray Pdu connected notification
systemSecureArrayConnectAlert NOTIFICATION-TYPE
	OBJECTS {
		-- pdu cabinet
		cpiPduCabinetId,
		-- pdu Mac
		cpiPduMac,
		-- pdu name
		cpiPduName
	}
	STATUS current
	DESCRIPTION
            "Notification that the specified PDU connected to the SecureArray."
	::= { systemNotifications 8 }
	
systemConfigCertAlert NOTIFICATION-TYPE
	OBJECTS {
		-- pdu cabinet
		cpiPduCabinetId,
		-- pdu Mac
		cpiPduMac,
		-- pdu name
		cpiPduName,                
                trapInfoUserName,
                trapInfoInterface
	}
	STATUS current
	DESCRIPTION
            "Notification that the HTTPS certificate was changed on the PDU."
	::= { systemNotifications 9 }


userNotifications OBJECT IDENTIFIER ::= { traps 2 }
	-- user login notification
userLoginAlert NOTIFICATION-TYPE
	OBJECTS {
		-- pdu cabinet
		cpiPduCabinetId,
		-- pdu Mac
		cpiPduMac,
		-- pdu name
		cpiPduName,
		trapInfoUserName,
		trapInfoInterface
	}
	STATUS current
	DESCRIPTION
            "Notification that a user logged onto the PDU."
	::= { userNotifications 1 }

	-- login fail notification
userLoginFailAlert NOTIFICATION-TYPE
	OBJECTS {
		-- pdu cabinet
		cpiPduCabinetId,
		-- pdu Mac
		cpiPduMac,
		-- pdu name
		cpiPduName,
		trapInfoUserName,
		trapInfoInterface
	}
	STATUS current
	DESCRIPTION
            "Notification that a user failed to log onto the PDU."
	::= { userNotifications 2 }

	-- user add notification
userAddAlert NOTIFICATION-TYPE
	OBJECTS {
		-- pdu cabinet
		cpiPduCabinetId,
		-- pdu Mac
		cpiPduMac,
		-- pdu name
		cpiPduName,
		trapInfoUserName,
		trapInfoInterface
	}
	STATUS current
	DESCRIPTION
            "Notification that a user was added to the PDU."
	::= { userNotifications 3 }

	-- user deleted notification
userDeleteAlert NOTIFICATION-TYPE
	OBJECTS {
		-- pdu cabinet
		cpiPduCabinetId,
		-- pdu Mac
		cpiPduMac,
		-- pdu name
		cpiPduName,
		trapInfoUserName,
		trapInfoInterface
	}
	STATUS current
	DESCRIPTION
            "Notification that a user was deleted from the PDU."
	::= { userNotifications 4 }
	
	-- user modified notification
userModifiedAlert NOTIFICATION-TYPE
	OBJECTS {
		-- pdu cabinet
		cpiPduCabinetId,
		-- pdu Mac
		cpiPduMac,
		-- pdu name
		cpiPduName,
		trapInfoUserName,
		trapInfoInterface
	}
	STATUS current
	DESCRIPTION
            "Notification that a user was modified on the PDU."
	::= { userNotifications 5 }
	
	-- group add notification
userGroupAddAlert NOTIFICATION-TYPE
	OBJECTS {
		-- pdu cabinet
		cpiPduCabinetId,
		-- pdu Mac
		cpiPduMac,
		-- pdu name
		cpiPduName,
		trapInfoGroupName,
		trapInfoInterface
	}
	STATUS current
	DESCRIPTION
            "Notification that a user group was added to the PDU."
	::= { userNotifications 6 }
	
	-- group deleted notification
userGroupDeleteAlert NOTIFICATION-TYPE
	OBJECTS {
		-- pdu cabinet
		cpiPduCabinetId,
		-- pdu Mac
		cpiPduMac,
		-- pdu name
		cpiPduName,
		trapInfoGroupName,
		trapInfoInterface
	}
	STATUS current
	DESCRIPTION
            "Notification that a user group was deleted from the PDU."
	::= { userNotifications 7 }
	
	-- group modified notification
userGroupModifyAlert NOTIFICATION-TYPE
	OBJECTS {
		-- pdu cabinet
		cpiPduCabinetId,
		-- pdu Mac
		cpiPduMac,
		-- pdu name
		cpiPduName,
		trapInfoGroupName,
		trapInfoInterface
	}
	STATUS current
	DESCRIPTION
            "Notification that a user group was modified on the PDU."
	::= { userNotifications 8 }
	
inletNotifications OBJECT IDENTIFIER ::= { traps 3 }
	-- inlet max current
	-- inlet min current
	-- inlet critical current

branchNotifications OBJECT IDENTIFIER ::= { traps 4 }
	-- branch critical current
	-- branch max current
	-- branch min current
	-- branch max voltage
	-- branch min voltage
	-- branch max power
	-- branch min power
	-- branch current delta
	-- branch power delta

outletNotifications OBJECT IDENTIFIER ::= { traps 5 }
	-- outlet state change
	-- outlet max current
	-- outlet min current
	-- outlet max voltage
	-- outlet min voltage
	-- outlet max power
	-- outlet min power
	-- outlet current delta
	-- outlet power delta
	
outletStateChangeAlert NOTIFICATION-TYPE
	OBJECTS {
		-- pdu cabinet
		cpiPduCabinetId,
		-- pdu Mac
		cpiPduMac,
		-- pdu name
		cpiPduName,
		cpiPduOutletId,
		cpiPudOutletName,
                cpiPduOutletStatus
	}
	STATUS current
	DESCRIPTION
            "The outlet state has changed."
	::= { outletNotifications 1 }

environNotification OBJECT IDENTIFIER ::= { traps 6 }
	-- environ max temp
environMaxTempAlert NOTIFICATION-TYPE
	OBJECTS {
		-- pdu cabinet
		cpiPduCabinetId,
		-- pdu Mac
		cpiPduMac,
		-- pdu name
		cpiPduName,
                cpiPduSensorId,
                cpiPduSensorName,
                cpiPduSensorType,
                cpiPduSensorValue
	}
	STATUS current
	DESCRIPTION
            "The temperature sensor reached the Maximum limit."
	::= { environNotification 1 }

	-- environ min temp
environMinTempAlert NOTIFICATION-TYPE
	OBJECTS {
		-- pdu cabinet
		cpiPduCabinetId,
		-- pdu Mac
		cpiPduMac,
		-- pdu name
		cpiPduName,
                cpiPduSensorId,
                cpiPduSensorName,
                cpiPduSensorType,
                cpiPduSensorValue
	}
	STATUS current
	DESCRIPTION
            "The temperature sensor reached the minimum limit."
	::= { environNotification 2 }
	
	-- environ max humidity
environMaxHumidAlert NOTIFICATION-TYPE
	OBJECTS {
		-- pdu cabinet
		cpiPduCabinetId,
		-- pdu Mac
		cpiPduMac,
		-- pdu name
		cpiPduName,
                cpiPduSensorId,
                cpiPduSensorName,
                cpiPduSensorType,
                cpiPduSensorValue
	}
	STATUS current
	DESCRIPTION
            "The humidity sensor reached the maximum limit."
	::= { environNotification 3 }
	
	-- environ min humidity
environMinHumidAlert NOTIFICATION-TYPE
	OBJECTS {
		-- pdu cabinet
		cpiPduCabinetId,
		-- pdu Mac
		cpiPduMac,
		-- pdu name
		cpiPduName,
                cpiPduSensorId,
                cpiPduSensorName,
                cpiPduSensorType,
                cpiPduSensorValue
	}
	STATUS current
	DESCRIPTION
            "The humidity sensor reached the maximum limit."
	::= { environNotification 4 }
	
	-- environ max temp
environMaxWarnTempAlert NOTIFICATION-TYPE
	OBJECTS {
		-- pdu cabinet
		cpiPduCabinetId,
		-- pdu Mac
		cpiPduMac,
		-- pdu name
		cpiPduName,
                cpiPduSensorId,
                cpiPduSensorName,
                cpiPduSensorType,
                cpiPduSensorValue
	}
	STATUS current
	DESCRIPTION
            "The temperature sensor reached the Maximum limit."
	::= { environNotification 5 }

	-- environ min temp
environMinWarnTempAlert NOTIFICATION-TYPE
	OBJECTS {
		-- pdu cabinet
		cpiPduCabinetId,
		-- pdu Mac
		cpiPduMac,
		-- pdu name
		cpiPduName,
                cpiPduSensorId,
                cpiPduSensorName,
                cpiPduSensorType,
                cpiPduSensorValue
	}
	STATUS current
	DESCRIPTION
            "The temperature sensor reached the minimum limit."
	::= { environNotification 6 }
	
	-- environ max humidity
environMaxWarnHumidAlert NOTIFICATION-TYPE
	OBJECTS {
		-- pdu cabinet
		cpiPduCabinetId,
		-- pdu Mac
		cpiPduMac,
		-- pdu name
		cpiPduName,
                cpiPduSensorId,
                cpiPduSensorName,
                cpiPduSensorType,
                cpiPduSensorValue
	}
	STATUS current
	DESCRIPTION
            "The humidity sensor reached the maximum limit."
	::= { environNotification 7 }
	
	-- environ min humidity
environMinWarnHumidAlert NOTIFICATION-TYPE
	OBJECTS {
		-- pdu cabinet
		cpiPduCabinetId,
		-- pdu Mac
		cpiPduMac,
		-- pdu name
		cpiPduName,
                cpiPduSensorId,
                cpiPduSensorName,
                cpiPduSensorType,
                cpiPduSensorValue
	}
	STATUS current
	DESCRIPTION
            "The humidity sensor reached the maximum limit."
	::= { environNotification 8 }

easNotification OBJECT IDENTIFIER ::= { traps 7 }
	-- scan pass notification

easScanPassAlert NOTIFICATION-TYPE
	OBJECTS {
		-- pdu cabinet
		cpiPduCabinetId,
		-- pdu Mac
		cpiPduMac,
		-- username
		trapInfoUserName,
		-- pdu name
		cpiPduName
	}
	STATUS current
	DESCRIPTION
            "A card was scanned and the associated user was authenticated and authorized to access the cabinet."
	::= { easNotification 1 }
	
	-- scan fail notification
 easScanFailAlert NOTIFICATION-TYPE
	OBJECTS {
		-- pdu cabinet
		cpiPduCabinetId,
		-- pdu Mac
		cpiPduMac,
		-- pdu name
		cpiPduName
	}
	STATUS current
	DESCRIPTION
            "A card was scanned but was not authenticated or authorized to access the cabinet."
	::= { easNotification 2 }
	
	-- door open notification
 easDoorOpenAlert NOTIFICATION-TYPE
	OBJECTS {
		-- pdu cabinet
		cpiPduCabinetId,
		-- pdu Mac
		cpiPduMac,
		-- pdu name
		cpiPduName,
		-- door position
		cpiPduLockId,
		-- door status
		cpiPduDoorStatus,
		-- lock status
		cpiPduLockStatus,
		-- force status
		cpiPduForceStatus,
		-- tamper indicator
		cpiPduTamperStatus
	}
	STATUS current
	DESCRIPTION
            "Notification that a door was opened."
	::= { easNotification 3 }
	
	-- door close notification
easDoorCloseAlert NOTIFICATION-TYPE
	OBJECTS {
		-- pdu cabinet
		cpiPduCabinetId,
		-- pdu Mac
		cpiPduMac,
		-- pdu name
		cpiPduName,
		-- door position
		cpiPduLockId,
		-- door status
		cpiPduDoorStatus,
		-- lock status
		cpiPduLockStatus,
		-- force status
		cpiPduForceStatus,
		-- tamper indicator
		cpiPduTamperStatus
	}
	STATUS current
	DESCRIPTION
            "Notification that a door was closed."
	::= { easNotification 4 }
	
	-- handle open notification
easLockOpenAlert NOTIFICATION-TYPE
	OBJECTS {
		-- pdu cabinet
		cpiPduCabinetId,
		-- pdu Mac
		cpiPduMac,
		-- pdu name
		cpiPduName,
		-- door position
		cpiPduLockId,
		-- lock status
		cpiPduLockStatus,
		-- door status
		cpiPduDoorStatus,
		-- force status
		cpiPduForceStatus,
		-- tamper indicator
		cpiPduTamperStatus
	}
	STATUS current
	DESCRIPTION
            "Notification that a lock was opened."
	::= { easNotification 5 }
	
	-- handle close notification
easLockCloseAlert NOTIFICATION-TYPE
	OBJECTS {
		-- pdu cabinet
		cpiPduCabinetId,
		-- pdu Mac
		cpiPduMac,
		-- pdu name
		cpiPduName,
		-- door position
		cpiPduLockId,
		-- lock status
		cpiPduLockStatus,
		-- door status
		cpiPduDoorStatus,
		-- force status
		cpiPduForceStatus,
		-- tamper indicator
		cpiPduTamperStatus
	}
	STATUS current
	DESCRIPTION
            "Notification that a lock was closed."
	::= { easNotification 6 }
	
	-- extended door open notification
 easDoorExtOpenAlert NOTIFICATION-TYPE
	OBJECTS {
		-- pdu cabinet
		cpiPduCabinetId,
		-- pdu Mac
		cpiPduMac,
		-- pdu name
		cpiPduName,
		-- door position
		cpiPduLockId,
		-- door status
		cpiPduDoorStatus,
		-- lock status
		cpiPduLockStatus,
		-- force status
		cpiPduForceStatus,
		-- tamper indicator
		cpiPduTamperStatus
	}
	STATUS current
	DESCRIPTION
            "Notification that a door was open for longer that the time set in cpiEasDoorOpenAlarmTime setting."
	::= { easNotification 7 }
	
	-- clear extended door open notification
 easDoorExtOpenClearAlert NOTIFICATION-TYPE
	OBJECTS {
		-- pdu cabinet
		cpiPduCabinetId,
		-- pdu Mac
		cpiPduMac,
		-- pdu name
		cpiPduName,
		-- door position
		cpiPduLockId,
		-- door status
		cpiPduDoorStatus,
		-- lock status
		cpiPduLockStatus,
		-- force status
		cpiPduForceStatus,
		-- tamper indicator
		cpiPduTamperStatus
	}
	STATUS current
	DESCRIPTION
            "Notification that a door was open for longer that the time set in cpiEasDoorOpenAlarmTime setting."
	::= { easNotification 8 }
	
        -- clear extended door open notification
 easForceUnlockAlert NOTIFICATION-TYPE
	OBJECTS {
		-- pdu cabinet
		cpiPduCabinetId,
		-- pdu Mac
		cpiPduMac,
		-- pdu name
		cpiPduName,
		-- username
		trapInfoUserName,
		-- door position
		cpiPduLockId
	}
	STATUS current
	DESCRIPTION
            "Notification that a door was open for longer that the time set in cpiEasDoorOpenAlarmTime setting."
	::= { easNotification 9 }

mibconformance OBJECT IDENTIFIER ::= { econnect 600 }

END
